CONEL-MBUS-MIB DEFINITIONS ::= BEGIN

IMPORTS
			enterprises, Gauge
				FROM RFC1155-SMI
			OBJECT-TYPE
				FROM RFC-1212;

conel			OBJECT IDENTIFIER ::= { enterprises 30140 }

protocols		OBJECT IDENTIFIER ::= { conel 2 }

mbus			OBJECT IDENTIFIER ::= { protocols 2 }

mbus00			OBJECT IDENTIFIER ::= { mbus 0 }

mbus00IdNumber		OBJECT-TYPE
			SYNTAX	Gauge
			ACCESS	read-only
			STATUS	current
	DESCRIPTION ""
			::= { mbus00 1 }

mbus00Manufacturer	OBJECT-TYPE
			SYNTAX	Gauge
			ACCESS	read-only
			STATUS	current
	DESCRIPTION ""
			::= { mbus00 2 }

mbus00Version		OBJECT-TYPE
			SYNTAX	Gauge
			ACCESS	read-only
			STATUS	current
	DESCRIPTION ""
			::= { mbus00 3 }

mbus00Medium		OBJECT-TYPE
			SYNTAX	Gauge
			ACCESS	read-only
			STATUS	current
	DESCRIPTION ""
			::= { mbus00 4 }

mbus00Status		OBJECT-TYPE
			SYNTAX	Gauge
			ACCESS	read-only
			STATUS	current
	DESCRIPTION ""
			::= { mbus00 5 }

mbus00VIF00		OBJECT-TYPE
			SYNTAX	INTEGER
			ACCESS	read-only
			STATUS	current
	DESCRIPTION ""
			::= { mbus00 6 }

mbus00Value00		OBJECT-TYPE
			SYNTAX	INTEGER
			ACCESS	read-only
			STATUS	current
	DESCRIPTION ""
			::= { mbus00 7 }

mbus00VIF01		OBJECT-TYPE
			SYNTAX	INTEGER
			ACCESS	read-only
			STATUS	current
	DESCRIPTION ""
			::= { mbus00 8 }

mbus00Value01		OBJECT-TYPE
			SYNTAX	INTEGER
			ACCESS	read-only
			STATUS	current
	DESCRIPTION ""
			::= { mbus00 9 }

mbus00VIF02		OBJECT-TYPE
			SYNTAX	INTEGER
			ACCESS	read-only
			STATUS	current
	DESCRIPTION ""
			::= { mbus00 10 }

mbus00Value02		OBJECT-TYPE
			SYNTAX	INTEGER
			ACCESS	read-only
			STATUS	current
	DESCRIPTION ""
			::= { mbus00 11 }

mbus00VIF03		OBJECT-TYPE
			SYNTAX	INTEGER
			ACCESS	read-only
			STATUS	current
	DESCRIPTION ""
			::= { mbus00 12 }

mbus00Value03		OBJECT-TYPE
			SYNTAX	INTEGER
			ACCESS	read-only
			STATUS	current
	DESCRIPTION ""
			::= { mbus00 13 }

mbus00VIF04		OBJECT-TYPE
			SYNTAX	INTEGER
			ACCESS	read-only
			STATUS	current
	DESCRIPTION ""
			::= { mbus00 14 }

mbus00Value04		OBJECT-TYPE
			SYNTAX	INTEGER
			ACCESS	read-only
			STATUS	current
	DESCRIPTION ""
			::= { mbus00 15 }

mbus00VIF05		OBJECT-TYPE
			SYNTAX	INTEGER
			ACCESS	read-only
			STATUS	current
	DESCRIPTION ""
			::= { mbus00 16 }

mbus00Value05		OBJECT-TYPE
			SYNTAX	INTEGER
			ACCESS	read-only
			STATUS	current
	DESCRIPTION ""
			::= { mbus00 17 }

mbus00VIF06		OBJECT-TYPE
			SYNTAX	INTEGER
			ACCESS	read-only
			STATUS	current
	DESCRIPTION ""
			::= { mbus00 18 }

mbus00Value06		OBJECT-TYPE
			SYNTAX	INTEGER
			ACCESS	read-only
			STATUS	current
	DESCRIPTION ""
			::= { mbus00 19 }

mbus00VIF07		OBJECT-TYPE
			SYNTAX	INTEGER
			ACCESS	read-only
			STATUS	current
	DESCRIPTION ""
			::= { mbus00 20 }

mbus00Value07		OBJECT-TYPE
			SYNTAX	INTEGER
			ACCESS	read-only
			STATUS	current
	DESCRIPTION ""
			::= { mbus00 21 }

mbus00VIF08		OBJECT-TYPE
			SYNTAX	INTEGER
			ACCESS	read-only
			STATUS	current
	DESCRIPTION ""
			::= { mbus00 22 }

mbus00Value08		OBJECT-TYPE
			SYNTAX	INTEGER
			ACCESS	read-only
			STATUS	current
	DESCRIPTION ""
			::= { mbus00 23 }

mbus00VIF09		OBJECT-TYPE
			SYNTAX	INTEGER
			ACCESS	read-only
			STATUS	current
	DESCRIPTION ""
			::= { mbus00 24 }

mbus00Value09		OBJECT-TYPE
			SYNTAX	INTEGER
			ACCESS	read-only
			STATUS	current
	DESCRIPTION ""
			::= { mbus00 25 }

mbus00VIF0A		OBJECT-TYPE
			SYNTAX	INTEGER
			ACCESS	read-only
			STATUS	current
	DESCRIPTION ""
			::= { mbus00 26 }

mbus00Value0A		OBJECT-TYPE
			SYNTAX	INTEGER
			ACCESS	read-only
			STATUS	current
	DESCRIPTION ""
			::= { mbus00 27 }

mbus00VIF0B		OBJECT-TYPE
			SYNTAX	INTEGER
			ACCESS	read-only
			STATUS	current
	DESCRIPTION ""
			::= { mbus00 28 }

mbus00Value0B		OBJECT-TYPE
			SYNTAX	INTEGER
			ACCESS	read-only
			STATUS	current
	DESCRIPTION ""
			::= { mbus00 29 }

mbus00VIF0C		OBJECT-TYPE
			SYNTAX	INTEGER
			ACCESS	read-only
			STATUS	current
	DESCRIPTION ""
			::= { mbus00 30 }

mbus00Value0C		OBJECT-TYPE
			SYNTAX	INTEGER
			ACCESS	read-only
			STATUS	current
	DESCRIPTION ""
			::= { mbus00 31 }

mbus00VIF0D		OBJECT-TYPE
			SYNTAX	INTEGER
			ACCESS	read-only
			STATUS	current
	DESCRIPTION ""
			::= { mbus00 32 }

mbus00Value0D		OBJECT-TYPE
			SYNTAX	INTEGER
			ACCESS	read-only
			STATUS	current
	DESCRIPTION ""
			::= { mbus00 33 }

mbus00VIF0E		OBJECT-TYPE
			SYNTAX	INTEGER
			ACCESS	read-only
			STATUS	current
	DESCRIPTION ""
			::= { mbus00 34 }

mbus00Value0E		OBJECT-TYPE
			SYNTAX	INTEGER
			ACCESS	read-only
			STATUS	current
	DESCRIPTION ""
			::= { mbus00 35 }

mbus00VIF0F		OBJECT-TYPE
			SYNTAX	INTEGER
			ACCESS	read-only
			STATUS	current
	DESCRIPTION ""
			::= { mbus00 36 }

mbus00Value0F		OBJECT-TYPE
			SYNTAX	INTEGER
			ACCESS	read-only
			STATUS	current
	DESCRIPTION ""
			::= { mbus00 37 }

mbus00VIF10		OBJECT-TYPE
			SYNTAX	INTEGER
			ACCESS	read-only
			STATUS	current
	DESCRIPTION ""
			::= { mbus00 38 }

mbus00Value10		OBJECT-TYPE
			SYNTAX	INTEGER
			ACCESS	read-only
			STATUS	current
	DESCRIPTION ""
			::= { mbus00 39 }

mbus00VIF11		OBJECT-TYPE
			SYNTAX	INTEGER
			ACCESS	read-only
			STATUS	current
	DESCRIPTION ""
			::= { mbus00 40 }

mbus00Value11		OBJECT-TYPE
			SYNTAX	INTEGER
			ACCESS	read-only
			STATUS	current
	DESCRIPTION ""
			::= { mbus00 41 }

mbus00VIF12		OBJECT-TYPE
			SYNTAX	INTEGER
			ACCESS	read-only
			STATUS	current
	DESCRIPTION ""
			::= { mbus00 42 }

mbus00Value12		OBJECT-TYPE
			SYNTAX	INTEGER
			ACCESS	read-only
			STATUS	current
	DESCRIPTION ""
			::= { mbus00 43 }

mbus00VIF13		OBJECT-TYPE
			SYNTAX	INTEGER
			ACCESS	read-only
			STATUS	current
	DESCRIPTION ""
			::= { mbus00 44 }

mbus00Value13		OBJECT-TYPE
			SYNTAX	INTEGER
			ACCESS	read-only
			STATUS	current
	DESCRIPTION ""
			::= { mbus00 45 }

mbus00VIF14		OBJECT-TYPE
			SYNTAX	INTEGER
			ACCESS	read-only
			STATUS	current
	DESCRIPTION ""
			::= { mbus00 46 }

mbus00Value14		OBJECT-TYPE
			SYNTAX	INTEGER
			ACCESS	read-only
			STATUS	current
	DESCRIPTION ""
			::= { mbus00 47 }

mbus00VIF15		OBJECT-TYPE
			SYNTAX	INTEGER
			ACCESS	read-only
			STATUS	current
	DESCRIPTION ""
			::= { mbus00 48 }

mbus00Value15		OBJECT-TYPE
			SYNTAX	INTEGER
			ACCESS	read-only
			STATUS	current
	DESCRIPTION ""
			::= { mbus00 49 }

mbus00VIF16		OBJECT-TYPE
			SYNTAX	INTEGER
			ACCESS	read-only
			STATUS	current
	DESCRIPTION ""
			::= { mbus00 50 }

mbus00Value16		OBJECT-TYPE
			SYNTAX	INTEGER
			ACCESS	read-only
			STATUS	current
	DESCRIPTION ""
			::= { mbus00 51 }

mbus00VIF17		OBJECT-TYPE
			SYNTAX	INTEGER
			ACCESS	read-only
			STATUS	current
	DESCRIPTION ""
			::= { mbus00 52 }

mbus00Value17		OBJECT-TYPE
			SYNTAX	INTEGER
			ACCESS	read-only
			STATUS	current
	DESCRIPTION ""
			::= { mbus00 53 }

mbus00VIF18		OBJECT-TYPE
			SYNTAX	INTEGER
			ACCESS	read-only
			STATUS	current
	DESCRIPTION ""
			::= { mbus00 54 }

mbus00Value18		OBJECT-TYPE
			SYNTAX	INTEGER
			ACCESS	read-only
			STATUS	current
	DESCRIPTION ""
			::= { mbus00 55 }

mbus00VIF19		OBJECT-TYPE
			SYNTAX	INTEGER
			ACCESS	read-only
			STATUS	current
	DESCRIPTION ""
			::= { mbus00 56 }

mbus00Value19		OBJECT-TYPE
			SYNTAX	INTEGER
			ACCESS	read-only
			STATUS	current
	DESCRIPTION ""
			::= { mbus00 57 }

mbus00VIF1A		OBJECT-TYPE
			SYNTAX	INTEGER
			ACCESS	read-only
			STATUS	current
	DESCRIPTION ""
			::= { mbus00 58 }

mbus00Value1A		OBJECT-TYPE
			SYNTAX	INTEGER
			ACCESS	read-only
			STATUS	current
	DESCRIPTION ""
			::= { mbus00 59 }

mbus00VIF1B		OBJECT-TYPE
			SYNTAX	INTEGER
			ACCESS	read-only
			STATUS	current
	DESCRIPTION ""
			::= { mbus00 60 }

mbus00Value1B		OBJECT-TYPE
			SYNTAX	INTEGER
			ACCESS	read-only
			STATUS	current
	DESCRIPTION ""
			::= { mbus00 61 }

mbus00VIF1C		OBJECT-TYPE
			SYNTAX	INTEGER
			ACCESS	read-only
			STATUS	current
	DESCRIPTION ""
			::= { mbus00 62 }

mbus00Value1C		OBJECT-TYPE
			SYNTAX	INTEGER
			ACCESS	read-only
			STATUS	current
	DESCRIPTION ""
			::= { mbus00 63 }

mbus00VIF1D		OBJECT-TYPE
			SYNTAX	INTEGER
			ACCESS	read-only
			STATUS	current
	DESCRIPTION ""
			::= { mbus00 64 }

mbus00Value1D		OBJECT-TYPE
			SYNTAX	INTEGER
			ACCESS	read-only
			STATUS	current
	DESCRIPTION ""
			::= { mbus00 65 }

mbus00VIF1E		OBJECT-TYPE
			SYNTAX	INTEGER
			ACCESS	read-only
			STATUS	current
	DESCRIPTION ""
			::= { mbus00 66 }

mbus00Value1E		OBJECT-TYPE
			SYNTAX	INTEGER
			ACCESS	read-only
			STATUS	current
	DESCRIPTION ""
			::= { mbus00 67 }

mbus00VIF1F		OBJECT-TYPE
			SYNTAX	INTEGER
			ACCESS	read-only
			STATUS	current
	DESCRIPTION ""
			::= { mbus00 68 }

mbus00Value1F		OBJECT-TYPE
			SYNTAX	INTEGER
			ACCESS	read-only
			STATUS	current
	DESCRIPTION ""
			::= { mbus00 69 }

mbus00VIF20		OBJECT-TYPE
			SYNTAX	INTEGER
			ACCESS	read-only
			STATUS	current
	DESCRIPTION ""
			::= { mbus00 70 }

mbus00Value20		OBJECT-TYPE
			SYNTAX	INTEGER
			ACCESS	read-only
			STATUS	current
	DESCRIPTION ""
			::= { mbus00 71 }

mbus00VIF21		OBJECT-TYPE
			SYNTAX	INTEGER
			ACCESS	read-only
			STATUS	current
	DESCRIPTION ""
			::= { mbus00 72 }

mbus00Value21		OBJECT-TYPE
			SYNTAX	INTEGER
			ACCESS	read-only
			STATUS	current
	DESCRIPTION ""
			::= { mbus00 73 }

mbus00VIF22		OBJECT-TYPE
			SYNTAX	INTEGER
			ACCESS	read-only
			STATUS	current
	DESCRIPTION ""
			::= { mbus00 74 }

mbus00Value22		OBJECT-TYPE
			SYNTAX	INTEGER
			ACCESS	read-only
			STATUS	current
	DESCRIPTION ""
			::= { mbus00 75 }

mbus00VIF23		OBJECT-TYPE
			SYNTAX	INTEGER
			ACCESS	read-only
			STATUS	current
	DESCRIPTION ""
			::= { mbus00 76 }

mbus00Value23		OBJECT-TYPE
			SYNTAX	INTEGER
			ACCESS	read-only
			STATUS	current
	DESCRIPTION ""
			::= { mbus00 77 }

mbus00VIF24		OBJECT-TYPE
			SYNTAX	INTEGER
			ACCESS	read-only
			STATUS	current
	DESCRIPTION ""
			::= { mbus00 78 }

mbus00Value24		OBJECT-TYPE
			SYNTAX	INTEGER
			ACCESS	read-only
			STATUS	current
	DESCRIPTION ""
			::= { mbus00 79 }

mbus00VIF25		OBJECT-TYPE
			SYNTAX	INTEGER
			ACCESS	read-only
			STATUS	current
	DESCRIPTION ""
			::= { mbus00 80 }

mbus00Value25		OBJECT-TYPE
			SYNTAX	INTEGER
			ACCESS	read-only
			STATUS	current
	DESCRIPTION ""
			::= { mbus00 81 }

mbus00VIF26		OBJECT-TYPE
			SYNTAX	INTEGER
			ACCESS	read-only
			STATUS	current
	DESCRIPTION ""
			::= { mbus00 82 }

mbus00Value26		OBJECT-TYPE
			SYNTAX	INTEGER
			ACCESS	read-only
			STATUS	current
	DESCRIPTION ""
			::= { mbus00 83 }

mbus00VIF27		OBJECT-TYPE
			SYNTAX	INTEGER
			ACCESS	read-only
			STATUS	current
	DESCRIPTION ""
			::= { mbus00 84 }

mbus00Value27		OBJECT-TYPE
			SYNTAX	INTEGER
			ACCESS	read-only
			STATUS	current
	DESCRIPTION ""
			::= { mbus00 85 }

mbus00VIF28		OBJECT-TYPE
			SYNTAX	INTEGER
			ACCESS	read-only
			STATUS	current
	DESCRIPTION ""
			::= { mbus00 86 }

mbus00Value28		OBJECT-TYPE
			SYNTAX	INTEGER
			ACCESS	read-only
			STATUS	current
	DESCRIPTION ""
			::= { mbus00 87 }

mbus00VIF29		OBJECT-TYPE
			SYNTAX	INTEGER
			ACCESS	read-only
			STATUS	current
	DESCRIPTION ""
			::= { mbus00 88 }

mbus00Value29		OBJECT-TYPE
			SYNTAX	INTEGER
			ACCESS	read-only
			STATUS	current
	DESCRIPTION ""
			::= { mbus00 89 }

mbus00VIF2A		OBJECT-TYPE
			SYNTAX	INTEGER
			ACCESS	read-only
			STATUS	current
	DESCRIPTION ""
			::= { mbus00 90 }

mbus00Value2A		OBJECT-TYPE
			SYNTAX	INTEGER
			ACCESS	read-only
			STATUS	current
	DESCRIPTION ""
			::= { mbus00 91 }

mbus00VIF2B		OBJECT-TYPE
			SYNTAX	INTEGER
			ACCESS	read-only
			STATUS	current
	DESCRIPTION ""
			::= { mbus00 92 }

mbus00Value2B		OBJECT-TYPE
			SYNTAX	INTEGER
			ACCESS	read-only
			STATUS	current
	DESCRIPTION ""
			::= { mbus00 93 }

mbus00VIF2C		OBJECT-TYPE
			SYNTAX	INTEGER
			ACCESS	read-only
			STATUS	current
	DESCRIPTION ""
			::= { mbus00 94 }

mbus00Value2C		OBJECT-TYPE
			SYNTAX	INTEGER
			ACCESS	read-only
			STATUS	current
	DESCRIPTION ""
			::= { mbus00 95 }

mbus00VIF2D		OBJECT-TYPE
			SYNTAX	INTEGER
			ACCESS	read-only
			STATUS	current
	DESCRIPTION ""
			::= { mbus00 96 }

mbus00Value2D		OBJECT-TYPE
			SYNTAX	INTEGER
			ACCESS	read-only
			STATUS	current
	DESCRIPTION ""
			::= { mbus00 97 }

mbus00VIF2E		OBJECT-TYPE
			SYNTAX	INTEGER
			ACCESS	read-only
			STATUS	current
	DESCRIPTION ""
			::= { mbus00 98 }

mbus00Value2E		OBJECT-TYPE
			SYNTAX	INTEGER
			ACCESS	read-only
			STATUS	current
	DESCRIPTION ""
			::= { mbus00 99 }

mbus00VIF2F		OBJECT-TYPE
			SYNTAX	INTEGER
			ACCESS	read-only
			STATUS	current
	DESCRIPTION ""
			::= { mbus00 100 }

mbus00Value2F		OBJECT-TYPE
			SYNTAX	INTEGER
			ACCESS	read-only
			STATUS	current
	DESCRIPTION ""
			::= { mbus00 101 }

mbus01			OBJECT IDENTIFIER ::= { mbus 1 }

mbus01IdNumber		OBJECT-TYPE
			SYNTAX	Gauge
			ACCESS	read-only
			STATUS	current
	DESCRIPTION ""
			::= { mbus01 1 }

mbus01Manufacturer	OBJECT-TYPE
			SYNTAX	Gauge
			ACCESS	read-only
			STATUS	current
	DESCRIPTION ""
			::= { mbus01 2 }

mbus01Version		OBJECT-TYPE
			SYNTAX	Gauge
			ACCESS	read-only
			STATUS	current
	DESCRIPTION ""
			::= { mbus01 3 }

mbus01Medium		OBJECT-TYPE
			SYNTAX	Gauge
			ACCESS	read-only
			STATUS	current
	DESCRIPTION ""
			::= { mbus01 4 }

mbus01Status		OBJECT-TYPE
			SYNTAX	Gauge
			ACCESS	read-only
			STATUS	current
	DESCRIPTION ""
			::= { mbus01 5 }

mbus01VIF00		OBJECT-TYPE
			SYNTAX	INTEGER
			ACCESS	read-only
			STATUS	current
	DESCRIPTION ""
			::= { mbus01 6 }

mbus01Value00		OBJECT-TYPE
			SYNTAX	INTEGER
			ACCESS	read-only
			STATUS	current
	DESCRIPTION ""
			::= { mbus01 7 }

mbus01VIF01		OBJECT-TYPE
			SYNTAX	INTEGER
			ACCESS	read-only
			STATUS	current
	DESCRIPTION ""
			::= { mbus01 8 }

mbus01Value01		OBJECT-TYPE
			SYNTAX	INTEGER
			ACCESS	read-only
			STATUS	current
	DESCRIPTION ""
			::= { mbus01 9 }

mbus01VIF02		OBJECT-TYPE
			SYNTAX	INTEGER
			ACCESS	read-only
			STATUS	current
	DESCRIPTION ""
			::= { mbus01 10 }

mbus01Value02		OBJECT-TYPE
			SYNTAX	INTEGER
			ACCESS	read-only
			STATUS	current
	DESCRIPTION ""
			::= { mbus01 11 }

mbus01VIF03		OBJECT-TYPE
			SYNTAX	INTEGER
			ACCESS	read-only
			STATUS	current
	DESCRIPTION ""
			::= { mbus01 12 }

mbus01Value03		OBJECT-TYPE
			SYNTAX	INTEGER
			ACCESS	read-only
			STATUS	current
	DESCRIPTION ""
			::= { mbus01 13 }

mbus01VIF04		OBJECT-TYPE
			SYNTAX	INTEGER
			ACCESS	read-only
			STATUS	current
	DESCRIPTION ""
			::= { mbus01 14 }

mbus01Value04		OBJECT-TYPE
			SYNTAX	INTEGER
			ACCESS	read-only
			STATUS	current
	DESCRIPTION ""
			::= { mbus01 15 }

mbus01VIF05		OBJECT-TYPE
			SYNTAX	INTEGER
			ACCESS	read-only
			STATUS	current
	DESCRIPTION ""
			::= { mbus01 16 }

mbus01Value05		OBJECT-TYPE
			SYNTAX	INTEGER
			ACCESS	read-only
			STATUS	current
	DESCRIPTION ""
			::= { mbus01 17 }

mbus01VIF06		OBJECT-TYPE
			SYNTAX	INTEGER
			ACCESS	read-only
			STATUS	current
	DESCRIPTION ""
			::= { mbus01 18 }

mbus01Value06		OBJECT-TYPE
			SYNTAX	INTEGER
			ACCESS	read-only
			STATUS	current
	DESCRIPTION ""
			::= { mbus01 19 }

mbus01VIF07		OBJECT-TYPE
			SYNTAX	INTEGER
			ACCESS	read-only
			STATUS	current
	DESCRIPTION ""
			::= { mbus01 20 }

mbus01Value07		OBJECT-TYPE
			SYNTAX	INTEGER
			ACCESS	read-only
			STATUS	current
	DESCRIPTION ""
			::= { mbus01 21 }

mbus01VIF08		OBJECT-TYPE
			SYNTAX	INTEGER
			ACCESS	read-only
			STATUS	current
	DESCRIPTION ""
			::= { mbus01 22 }

mbus01Value08		OBJECT-TYPE
			SYNTAX	INTEGER
			ACCESS	read-only
			STATUS	current
	DESCRIPTION ""
			::= { mbus01 23 }

mbus01VIF09		OBJECT-TYPE
			SYNTAX	INTEGER
			ACCESS	read-only
			STATUS	current
	DESCRIPTION ""
			::= { mbus01 24 }

mbus01Value09		OBJECT-TYPE
			SYNTAX	INTEGER
			ACCESS	read-only
			STATUS	current
	DESCRIPTION ""
			::= { mbus01 25 }

mbus01VIF0A		OBJECT-TYPE
			SYNTAX	INTEGER
			ACCESS	read-only
			STATUS	current
	DESCRIPTION ""
			::= { mbus01 26 }

mbus01Value0A		OBJECT-TYPE
			SYNTAX	INTEGER
			ACCESS	read-only
			STATUS	current
	DESCRIPTION ""
			::= { mbus01 27 }

mbus01VIF0B		OBJECT-TYPE
			SYNTAX	INTEGER
			ACCESS	read-only
			STATUS	current
	DESCRIPTION ""
			::= { mbus01 28 }

mbus01Value0B		OBJECT-TYPE
			SYNTAX	INTEGER
			ACCESS	read-only
			STATUS	current
	DESCRIPTION ""
			::= { mbus01 29 }

mbus01VIF0C		OBJECT-TYPE
			SYNTAX	INTEGER
			ACCESS	read-only
			STATUS	current
	DESCRIPTION ""
			::= { mbus01 30 }

mbus01Value0C		OBJECT-TYPE
			SYNTAX	INTEGER
			ACCESS	read-only
			STATUS	current
	DESCRIPTION ""
			::= { mbus01 31 }

mbus01VIF0D		OBJECT-TYPE
			SYNTAX	INTEGER
			ACCESS	read-only
			STATUS	current
	DESCRIPTION ""
			::= { mbus01 32 }

mbus01Value0D		OBJECT-TYPE
			SYNTAX	INTEGER
			ACCESS	read-only
			STATUS	current
	DESCRIPTION ""
			::= { mbus01 33 }

mbus01VIF0E		OBJECT-TYPE
			SYNTAX	INTEGER
			ACCESS	read-only
			STATUS	current
	DESCRIPTION ""
			::= { mbus01 34 }

mbus01Value0E		OBJECT-TYPE
			SYNTAX	INTEGER
			ACCESS	read-only
			STATUS	current
	DESCRIPTION ""
			::= { mbus01 35 }

mbus01VIF0F		OBJECT-TYPE
			SYNTAX	INTEGER
			ACCESS	read-only
			STATUS	current
	DESCRIPTION ""
			::= { mbus01 36 }

mbus01Value0F		OBJECT-TYPE
			SYNTAX	INTEGER
			ACCESS	read-only
			STATUS	current
	DESCRIPTION ""
			::= { mbus01 37 }

mbus01VIF10		OBJECT-TYPE
			SYNTAX	INTEGER
			ACCESS	read-only
			STATUS	current
	DESCRIPTION ""
			::= { mbus01 38 }

mbus01Value10		OBJECT-TYPE
			SYNTAX	INTEGER
			ACCESS	read-only
			STATUS	current
	DESCRIPTION ""
			::= { mbus01 39 }

mbus01VIF11		OBJECT-TYPE
			SYNTAX	INTEGER
			ACCESS	read-only
			STATUS	current
	DESCRIPTION ""
			::= { mbus01 40 }

mbus01Value11		OBJECT-TYPE
			SYNTAX	INTEGER
			ACCESS	read-only
			STATUS	current
	DESCRIPTION ""
			::= { mbus01 41 }

mbus01VIF12		OBJECT-TYPE
			SYNTAX	INTEGER
			ACCESS	read-only
			STATUS	current
	DESCRIPTION ""
			::= { mbus01 42 }

mbus01Value12		OBJECT-TYPE
			SYNTAX	INTEGER
			ACCESS	read-only
			STATUS	current
	DESCRIPTION ""
			::= { mbus01 43 }

mbus01VIF13		OBJECT-TYPE
			SYNTAX	INTEGER
			ACCESS	read-only
			STATUS	current
	DESCRIPTION ""
			::= { mbus01 44 }

mbus01Value13		OBJECT-TYPE
			SYNTAX	INTEGER
			ACCESS	read-only
			STATUS	current
	DESCRIPTION ""
			::= { mbus01 45 }

mbus01VIF14		OBJECT-TYPE
			SYNTAX	INTEGER
			ACCESS	read-only
			STATUS	current
	DESCRIPTION ""
			::= { mbus01 46 }

mbus01Value14		OBJECT-TYPE
			SYNTAX	INTEGER
			ACCESS	read-only
			STATUS	current
	DESCRIPTION ""
			::= { mbus01 47 }

mbus01VIF15		OBJECT-TYPE
			SYNTAX	INTEGER
			ACCESS	read-only
			STATUS	current
	DESCRIPTION ""
			::= { mbus01 48 }

mbus01Value15		OBJECT-TYPE
			SYNTAX	INTEGER
			ACCESS	read-only
			STATUS	current
	DESCRIPTION ""
			::= { mbus01 49 }

mbus01VIF16		OBJECT-TYPE
			SYNTAX	INTEGER
			ACCESS	read-only
			STATUS	current
	DESCRIPTION ""
			::= { mbus01 50 }

mbus01Value16		OBJECT-TYPE
			SYNTAX	INTEGER
			ACCESS	read-only
			STATUS	current
	DESCRIPTION ""
			::= { mbus01 51 }

mbus01VIF17		OBJECT-TYPE
			SYNTAX	INTEGER
			ACCESS	read-only
			STATUS	current
	DESCRIPTION ""
			::= { mbus01 52 }

mbus01Value17		OBJECT-TYPE
			SYNTAX	INTEGER
			ACCESS	read-only
			STATUS	current
	DESCRIPTION ""
			::= { mbus01 53 }

mbus01VIF18		OBJECT-TYPE
			SYNTAX	INTEGER
			ACCESS	read-only
			STATUS	current
	DESCRIPTION ""
			::= { mbus01 54 }

mbus01Value18		OBJECT-TYPE
			SYNTAX	INTEGER
			ACCESS	read-only
			STATUS	current
	DESCRIPTION ""
			::= { mbus01 55 }

mbus01VIF19		OBJECT-TYPE
			SYNTAX	INTEGER
			ACCESS	read-only
			STATUS	current
	DESCRIPTION ""
			::= { mbus01 56 }

mbus01Value19		OBJECT-TYPE
			SYNTAX	INTEGER
			ACCESS	read-only
			STATUS	current
	DESCRIPTION ""
			::= { mbus01 57 }

mbus01VIF1A		OBJECT-TYPE
			SYNTAX	INTEGER
			ACCESS	read-only
			STATUS	current
	DESCRIPTION ""
			::= { mbus01 58 }

mbus01Value1A		OBJECT-TYPE
			SYNTAX	INTEGER
			ACCESS	read-only
			STATUS	current
	DESCRIPTION ""
			::= { mbus01 59 }

mbus01VIF1B		OBJECT-TYPE
			SYNTAX	INTEGER
			ACCESS	read-only
			STATUS	current
	DESCRIPTION ""
			::= { mbus01 60 }

mbus01Value1B		OBJECT-TYPE
			SYNTAX	INTEGER
			ACCESS	read-only
			STATUS	current
	DESCRIPTION ""
			::= { mbus01 61 }

mbus01VIF1C		OBJECT-TYPE
			SYNTAX	INTEGER
			ACCESS	read-only
			STATUS	current
	DESCRIPTION ""
			::= { mbus01 62 }

mbus01Value1C		OBJECT-TYPE
			SYNTAX	INTEGER
			ACCESS	read-only
			STATUS	current
	DESCRIPTION ""
			::= { mbus01 63 }

mbus01VIF1D		OBJECT-TYPE
			SYNTAX	INTEGER
			ACCESS	read-only
			STATUS	current
	DESCRIPTION ""
			::= { mbus01 64 }

mbus01Value1D		OBJECT-TYPE
			SYNTAX	INTEGER
			ACCESS	read-only
			STATUS	current
	DESCRIPTION ""
			::= { mbus01 65 }

mbus01VIF1E		OBJECT-TYPE
			SYNTAX	INTEGER
			ACCESS	read-only
			STATUS	current
	DESCRIPTION ""
			::= { mbus01 66 }

mbus01Value1E		OBJECT-TYPE
			SYNTAX	INTEGER
			ACCESS	read-only
			STATUS	current
	DESCRIPTION ""
			::= { mbus01 67 }

mbus01VIF1F		OBJECT-TYPE
			SYNTAX	INTEGER
			ACCESS	read-only
			STATUS	current
	DESCRIPTION ""
			::= { mbus01 68 }

mbus01Value1F		OBJECT-TYPE
			SYNTAX	INTEGER
			ACCESS	read-only
			STATUS	current
	DESCRIPTION ""
			::= { mbus01 69 }

mbus01VIF20		OBJECT-TYPE
			SYNTAX	INTEGER
			ACCESS	read-only
			STATUS	current
	DESCRIPTION ""
			::= { mbus01 70 }

mbus01Value20		OBJECT-TYPE
			SYNTAX	INTEGER
			ACCESS	read-only
			STATUS	current
	DESCRIPTION ""
			::= { mbus01 71 }

mbus01VIF21		OBJECT-TYPE
			SYNTAX	INTEGER
			ACCESS	read-only
			STATUS	current
	DESCRIPTION ""
			::= { mbus01 72 }

mbus01Value21		OBJECT-TYPE
			SYNTAX	INTEGER
			ACCESS	read-only
			STATUS	current
	DESCRIPTION ""
			::= { mbus01 73 }

mbus01VIF22		OBJECT-TYPE
			SYNTAX	INTEGER
			ACCESS	read-only
			STATUS	current
	DESCRIPTION ""
			::= { mbus01 74 }

mbus01Value22		OBJECT-TYPE
			SYNTAX	INTEGER
			ACCESS	read-only
			STATUS	current
	DESCRIPTION ""
			::= { mbus01 75 }

mbus01VIF23		OBJECT-TYPE
			SYNTAX	INTEGER
			ACCESS	read-only
			STATUS	current
	DESCRIPTION ""
			::= { mbus01 76 }

mbus01Value23		OBJECT-TYPE
			SYNTAX	INTEGER
			ACCESS	read-only
			STATUS	current
	DESCRIPTION ""
			::= { mbus01 77 }

mbus01VIF24		OBJECT-TYPE
			SYNTAX	INTEGER
			ACCESS	read-only
			STATUS	current
	DESCRIPTION ""
			::= { mbus01 78 }

mbus01Value24		OBJECT-TYPE
			SYNTAX	INTEGER
			ACCESS	read-only
			STATUS	current
	DESCRIPTION ""
			::= { mbus01 79 }

mbus01VIF25		OBJECT-TYPE
			SYNTAX	INTEGER
			ACCESS	read-only
			STATUS	current
	DESCRIPTION ""
			::= { mbus01 80 }

mbus01Value25		OBJECT-TYPE
			SYNTAX	INTEGER
			ACCESS	read-only
			STATUS	current
	DESCRIPTION ""
			::= { mbus01 81 }

mbus01VIF26		OBJECT-TYPE
			SYNTAX	INTEGER
			ACCESS	read-only
			STATUS	current
	DESCRIPTION ""
			::= { mbus01 82 }

mbus01Value26		OBJECT-TYPE
			SYNTAX	INTEGER
			ACCESS	read-only
			STATUS	current
	DESCRIPTION ""
			::= { mbus01 83 }

mbus01VIF27		OBJECT-TYPE
			SYNTAX	INTEGER
			ACCESS	read-only
			STATUS	current
	DESCRIPTION ""
			::= { mbus01 84 }

mbus01Value27		OBJECT-TYPE
			SYNTAX	INTEGER
			ACCESS	read-only
			STATUS	current
	DESCRIPTION ""
			::= { mbus01 85 }

mbus01VIF28		OBJECT-TYPE
			SYNTAX	INTEGER
			ACCESS	read-only
			STATUS	current
	DESCRIPTION ""
			::= { mbus01 86 }

mbus01Value28		OBJECT-TYPE
			SYNTAX	INTEGER
			ACCESS	read-only
			STATUS	current
	DESCRIPTION ""
			::= { mbus01 87 }

mbus01VIF29		OBJECT-TYPE
			SYNTAX	INTEGER
			ACCESS	read-only
			STATUS	current
	DESCRIPTION ""
			::= { mbus01 88 }

mbus01Value29		OBJECT-TYPE
			SYNTAX	INTEGER
			ACCESS	read-only
			STATUS	current
	DESCRIPTION ""
			::= { mbus01 89 }

mbus01VIF2A		OBJECT-TYPE
			SYNTAX	INTEGER
			ACCESS	read-only
			STATUS	current
	DESCRIPTION ""
			::= { mbus01 90 }

mbus01Value2A		OBJECT-TYPE
			SYNTAX	INTEGER
			ACCESS	read-only
			STATUS	current
	DESCRIPTION ""
			::= { mbus01 91 }

mbus01VIF2B		OBJECT-TYPE
			SYNTAX	INTEGER
			ACCESS	read-only
			STATUS	current
	DESCRIPTION ""
			::= { mbus01 92 }

mbus01Value2B		OBJECT-TYPE
			SYNTAX	INTEGER
			ACCESS	read-only
			STATUS	current
	DESCRIPTION ""
			::= { mbus01 93 }

mbus01VIF2C		OBJECT-TYPE
			SYNTAX	INTEGER
			ACCESS	read-only
			STATUS	current
	DESCRIPTION ""
			::= { mbus01 94 }

mbus01Value2C		OBJECT-TYPE
			SYNTAX	INTEGER
			ACCESS	read-only
			STATUS	current
	DESCRIPTION ""
			::= { mbus01 95 }

mbus01VIF2D		OBJECT-TYPE
			SYNTAX	INTEGER
			ACCESS	read-only
			STATUS	current
	DESCRIPTION ""
			::= { mbus01 96 }

mbus01Value2D		OBJECT-TYPE
			SYNTAX	INTEGER
			ACCESS	read-only
			STATUS	current
	DESCRIPTION ""
			::= { mbus01 97 }

mbus01VIF2E		OBJECT-TYPE
			SYNTAX	INTEGER
			ACCESS	read-only
			STATUS	current
	DESCRIPTION ""
			::= { mbus01 98 }

mbus01Value2E		OBJECT-TYPE
			SYNTAX	INTEGER
			ACCESS	read-only
			STATUS	current
	DESCRIPTION ""
			::= { mbus01 99 }

mbus01VIF2F		OBJECT-TYPE
			SYNTAX	INTEGER
			ACCESS	read-only
			STATUS	current
	DESCRIPTION ""
			::= { mbus01 100 }

mbus01Value2F		OBJECT-TYPE
			SYNTAX	INTEGER
			ACCESS	read-only
			STATUS	current
	DESCRIPTION ""
			::= { mbus01 101 }

mbus02			OBJECT IDENTIFIER ::= { mbus 2 }

mbus02IdNumber		OBJECT-TYPE
			SYNTAX	Gauge
			ACCESS	read-only
			STATUS	current
	DESCRIPTION ""
			::= { mbus02 1 }

mbus02Manufacturer	OBJECT-TYPE
			SYNTAX	Gauge
			ACCESS	read-only
			STATUS	current
	DESCRIPTION ""
			::= { mbus02 2 }

mbus02Version		OBJECT-TYPE
			SYNTAX	Gauge
			ACCESS	read-only
			STATUS	current
	DESCRIPTION ""
			::= { mbus02 3 }

mbus02Medium		OBJECT-TYPE
			SYNTAX	Gauge
			ACCESS	read-only
			STATUS	current
	DESCRIPTION ""
			::= { mbus02 4 }

mbus02Status		OBJECT-TYPE
			SYNTAX	Gauge
			ACCESS	read-only
			STATUS	current
	DESCRIPTION ""
			::= { mbus02 5 }

mbus02VIF00		OBJECT-TYPE
			SYNTAX	INTEGER
			ACCESS	read-only
			STATUS	current
	DESCRIPTION ""
			::= { mbus02 6 }

mbus02Value00		OBJECT-TYPE
			SYNTAX	INTEGER
			ACCESS	read-only
			STATUS	current
	DESCRIPTION ""
			::= { mbus02 7 }

mbus02VIF01		OBJECT-TYPE
			SYNTAX	INTEGER
			ACCESS	read-only
			STATUS	current
	DESCRIPTION ""
			::= { mbus02 8 }

mbus02Value01		OBJECT-TYPE
			SYNTAX	INTEGER
			ACCESS	read-only
			STATUS	current
	DESCRIPTION ""
			::= { mbus02 9 }

mbus02VIF02		OBJECT-TYPE
			SYNTAX	INTEGER
			ACCESS	read-only
			STATUS	current
	DESCRIPTION ""
			::= { mbus02 10 }

mbus02Value02		OBJECT-TYPE
			SYNTAX	INTEGER
			ACCESS	read-only
			STATUS	current
	DESCRIPTION ""
			::= { mbus02 11 }

mbus02VIF03		OBJECT-TYPE
			SYNTAX	INTEGER
			ACCESS	read-only
			STATUS	current
	DESCRIPTION ""
			::= { mbus02 12 }

mbus02Value03		OBJECT-TYPE
			SYNTAX	INTEGER
			ACCESS	read-only
			STATUS	current
	DESCRIPTION ""
			::= { mbus02 13 }

mbus02VIF04		OBJECT-TYPE
			SYNTAX	INTEGER
			ACCESS	read-only
			STATUS	current
	DESCRIPTION ""
			::= { mbus02 14 }

mbus02Value04		OBJECT-TYPE
			SYNTAX	INTEGER
			ACCESS	read-only
			STATUS	current
	DESCRIPTION ""
			::= { mbus02 15 }

mbus02VIF05		OBJECT-TYPE
			SYNTAX	INTEGER
			ACCESS	read-only
			STATUS	current
	DESCRIPTION ""
			::= { mbus02 16 }

mbus02Value05		OBJECT-TYPE
			SYNTAX	INTEGER
			ACCESS	read-only
			STATUS	current
	DESCRIPTION ""
			::= { mbus02 17 }

mbus02VIF06		OBJECT-TYPE
			SYNTAX	INTEGER
			ACCESS	read-only
			STATUS	current
	DESCRIPTION ""
			::= { mbus02 18 }

mbus02Value06		OBJECT-TYPE
			SYNTAX	INTEGER
			ACCESS	read-only
			STATUS	current
	DESCRIPTION ""
			::= { mbus02 19 }

mbus02VIF07		OBJECT-TYPE
			SYNTAX	INTEGER
			ACCESS	read-only
			STATUS	current
	DESCRIPTION ""
			::= { mbus02 20 }

mbus02Value07		OBJECT-TYPE
			SYNTAX	INTEGER
			ACCESS	read-only
			STATUS	current
	DESCRIPTION ""
			::= { mbus02 21 }

mbus02VIF08		OBJECT-TYPE
			SYNTAX	INTEGER
			ACCESS	read-only
			STATUS	current
	DESCRIPTION ""
			::= { mbus02 22 }

mbus02Value08		OBJECT-TYPE
			SYNTAX	INTEGER
			ACCESS	read-only
			STATUS	current
	DESCRIPTION ""
			::= { mbus02 23 }

mbus02VIF09		OBJECT-TYPE
			SYNTAX	INTEGER
			ACCESS	read-only
			STATUS	current
	DESCRIPTION ""
			::= { mbus02 24 }

mbus02Value09		OBJECT-TYPE
			SYNTAX	INTEGER
			ACCESS	read-only
			STATUS	current
	DESCRIPTION ""
			::= { mbus02 25 }

mbus02VIF0A		OBJECT-TYPE
			SYNTAX	INTEGER
			ACCESS	read-only
			STATUS	current
	DESCRIPTION ""
			::= { mbus02 26 }

mbus02Value0A		OBJECT-TYPE
			SYNTAX	INTEGER
			ACCESS	read-only
			STATUS	current
	DESCRIPTION ""
			::= { mbus02 27 }

mbus02VIF0B		OBJECT-TYPE
			SYNTAX	INTEGER
			ACCESS	read-only
			STATUS	current
	DESCRIPTION ""
			::= { mbus02 28 }

mbus02Value0B		OBJECT-TYPE
			SYNTAX	INTEGER
			ACCESS	read-only
			STATUS	current
	DESCRIPTION ""
			::= { mbus02 29 }

mbus02VIF0C		OBJECT-TYPE
			SYNTAX	INTEGER
			ACCESS	read-only
			STATUS	current
	DESCRIPTION ""
			::= { mbus02 30 }

mbus02Value0C		OBJECT-TYPE
			SYNTAX	INTEGER
			ACCESS	read-only
			STATUS	current
	DESCRIPTION ""
			::= { mbus02 31 }

mbus02VIF0D		OBJECT-TYPE
			SYNTAX	INTEGER
			ACCESS	read-only
			STATUS	current
	DESCRIPTION ""
			::= { mbus02 32 }

mbus02Value0D		OBJECT-TYPE
			SYNTAX	INTEGER
			ACCESS	read-only
			STATUS	current
	DESCRIPTION ""
			::= { mbus02 33 }

mbus02VIF0E		OBJECT-TYPE
			SYNTAX	INTEGER
			ACCESS	read-only
			STATUS	current
	DESCRIPTION ""
			::= { mbus02 34 }

mbus02Value0E		OBJECT-TYPE
			SYNTAX	INTEGER
			ACCESS	read-only
			STATUS	current
	DESCRIPTION ""
			::= { mbus02 35 }

mbus02VIF0F		OBJECT-TYPE
			SYNTAX	INTEGER
			ACCESS	read-only
			STATUS	current
	DESCRIPTION ""
			::= { mbus02 36 }

mbus02Value0F		OBJECT-TYPE
			SYNTAX	INTEGER
			ACCESS	read-only
			STATUS	current
	DESCRIPTION ""
			::= { mbus02 37 }

mbus02VIF10		OBJECT-TYPE
			SYNTAX	INTEGER
			ACCESS	read-only
			STATUS	current
	DESCRIPTION ""
			::= { mbus02 38 }

mbus02Value10		OBJECT-TYPE
			SYNTAX	INTEGER
			ACCESS	read-only
			STATUS	current
	DESCRIPTION ""
			::= { mbus02 39 }

mbus02VIF11		OBJECT-TYPE
			SYNTAX	INTEGER
			ACCESS	read-only
			STATUS	current
	DESCRIPTION ""
			::= { mbus02 40 }

mbus02Value11		OBJECT-TYPE
			SYNTAX	INTEGER
			ACCESS	read-only
			STATUS	current
	DESCRIPTION ""
			::= { mbus02 41 }

mbus02VIF12		OBJECT-TYPE
			SYNTAX	INTEGER
			ACCESS	read-only
			STATUS	current
	DESCRIPTION ""
			::= { mbus02 42 }

mbus02Value12		OBJECT-TYPE
			SYNTAX	INTEGER
			ACCESS	read-only
			STATUS	current
	DESCRIPTION ""
			::= { mbus02 43 }

mbus02VIF13		OBJECT-TYPE
			SYNTAX	INTEGER
			ACCESS	read-only
			STATUS	current
	DESCRIPTION ""
			::= { mbus02 44 }

mbus02Value13		OBJECT-TYPE
			SYNTAX	INTEGER
			ACCESS	read-only
			STATUS	current
	DESCRIPTION ""
			::= { mbus02 45 }

mbus02VIF14		OBJECT-TYPE
			SYNTAX	INTEGER
			ACCESS	read-only
			STATUS	current
	DESCRIPTION ""
			::= { mbus02 46 }

mbus02Value14		OBJECT-TYPE
			SYNTAX	INTEGER
			ACCESS	read-only
			STATUS	current
	DESCRIPTION ""
			::= { mbus02 47 }

mbus02VIF15		OBJECT-TYPE
			SYNTAX	INTEGER
			ACCESS	read-only
			STATUS	current
	DESCRIPTION ""
			::= { mbus02 48 }

mbus02Value15		OBJECT-TYPE
			SYNTAX	INTEGER
			ACCESS	read-only
			STATUS	current
	DESCRIPTION ""
			::= { mbus02 49 }

mbus02VIF16		OBJECT-TYPE
			SYNTAX	INTEGER
			ACCESS	read-only
			STATUS	current
	DESCRIPTION ""
			::= { mbus02 50 }

mbus02Value16		OBJECT-TYPE
			SYNTAX	INTEGER
			ACCESS	read-only
			STATUS	current
	DESCRIPTION ""
			::= { mbus02 51 }

mbus02VIF17		OBJECT-TYPE
			SYNTAX	INTEGER
			ACCESS	read-only
			STATUS	current
	DESCRIPTION ""
			::= { mbus02 52 }

mbus02Value17		OBJECT-TYPE
			SYNTAX	INTEGER
			ACCESS	read-only
			STATUS	current
	DESCRIPTION ""
			::= { mbus02 53 }

mbus02VIF18		OBJECT-TYPE
			SYNTAX	INTEGER
			ACCESS	read-only
			STATUS	current
	DESCRIPTION ""
			::= { mbus02 54 }

mbus02Value18		OBJECT-TYPE
			SYNTAX	INTEGER
			ACCESS	read-only
			STATUS	current
	DESCRIPTION ""
			::= { mbus02 55 }

mbus02VIF19		OBJECT-TYPE
			SYNTAX	INTEGER
			ACCESS	read-only
			STATUS	current
	DESCRIPTION ""
			::= { mbus02 56 }

mbus02Value19		OBJECT-TYPE
			SYNTAX	INTEGER
			ACCESS	read-only
			STATUS	current
	DESCRIPTION ""
			::= { mbus02 57 }

mbus02VIF1A		OBJECT-TYPE
			SYNTAX	INTEGER
			ACCESS	read-only
			STATUS	current
	DESCRIPTION ""
			::= { mbus02 58 }

mbus02Value1A		OBJECT-TYPE
			SYNTAX	INTEGER
			ACCESS	read-only
			STATUS	current
	DESCRIPTION ""
			::= { mbus02 59 }

mbus02VIF1B		OBJECT-TYPE
			SYNTAX	INTEGER
			ACCESS	read-only
			STATUS	current
	DESCRIPTION ""
			::= { mbus02 60 }

mbus02Value1B		OBJECT-TYPE
			SYNTAX	INTEGER
			ACCESS	read-only
			STATUS	current
	DESCRIPTION ""
			::= { mbus02 61 }

mbus02VIF1C		OBJECT-TYPE
			SYNTAX	INTEGER
			ACCESS	read-only
			STATUS	current
	DESCRIPTION ""
			::= { mbus02 62 }

mbus02Value1C		OBJECT-TYPE
			SYNTAX	INTEGER
			ACCESS	read-only
			STATUS	current
	DESCRIPTION ""
			::= { mbus02 63 }

mbus02VIF1D		OBJECT-TYPE
			SYNTAX	INTEGER
			ACCESS	read-only
			STATUS	current
	DESCRIPTION ""
			::= { mbus02 64 }

mbus02Value1D		OBJECT-TYPE
			SYNTAX	INTEGER
			ACCESS	read-only
			STATUS	current
	DESCRIPTION ""
			::= { mbus02 65 }

mbus02VIF1E		OBJECT-TYPE
			SYNTAX	INTEGER
			ACCESS	read-only
			STATUS	current
	DESCRIPTION ""
			::= { mbus02 66 }

mbus02Value1E		OBJECT-TYPE
			SYNTAX	INTEGER
			ACCESS	read-only
			STATUS	current
	DESCRIPTION ""
			::= { mbus02 67 }

mbus02VIF1F		OBJECT-TYPE
			SYNTAX	INTEGER
			ACCESS	read-only
			STATUS	current
	DESCRIPTION ""
			::= { mbus02 68 }

mbus02Value1F		OBJECT-TYPE
			SYNTAX	INTEGER
			ACCESS	read-only
			STATUS	current
	DESCRIPTION ""
			::= { mbus02 69 }

mbus02VIF20		OBJECT-TYPE
			SYNTAX	INTEGER
			ACCESS	read-only
			STATUS	current
	DESCRIPTION ""
			::= { mbus02 70 }

mbus02Value20		OBJECT-TYPE
			SYNTAX	INTEGER
			ACCESS	read-only
			STATUS	current
	DESCRIPTION ""
			::= { mbus02 71 }

mbus02VIF21		OBJECT-TYPE
			SYNTAX	INTEGER
			ACCESS	read-only
			STATUS	current
	DESCRIPTION ""
			::= { mbus02 72 }

mbus02Value21		OBJECT-TYPE
			SYNTAX	INTEGER
			ACCESS	read-only
			STATUS	current
	DESCRIPTION ""
			::= { mbus02 73 }

mbus02VIF22		OBJECT-TYPE
			SYNTAX	INTEGER
			ACCESS	read-only
			STATUS	current
	DESCRIPTION ""
			::= { mbus02 74 }

mbus02Value22		OBJECT-TYPE
			SYNTAX	INTEGER
			ACCESS	read-only
			STATUS	current
	DESCRIPTION ""
			::= { mbus02 75 }

mbus02VIF23		OBJECT-TYPE
			SYNTAX	INTEGER
			ACCESS	read-only
			STATUS	current
	DESCRIPTION ""
			::= { mbus02 76 }

mbus02Value23		OBJECT-TYPE
			SYNTAX	INTEGER
			ACCESS	read-only
			STATUS	current
	DESCRIPTION ""
			::= { mbus02 77 }

mbus02VIF24		OBJECT-TYPE
			SYNTAX	INTEGER
			ACCESS	read-only
			STATUS	current
	DESCRIPTION ""
			::= { mbus02 78 }

mbus02Value24		OBJECT-TYPE
			SYNTAX	INTEGER
			ACCESS	read-only
			STATUS	current
	DESCRIPTION ""
			::= { mbus02 79 }

mbus02VIF25		OBJECT-TYPE
			SYNTAX	INTEGER
			ACCESS	read-only
			STATUS	current
	DESCRIPTION ""
			::= { mbus02 80 }

mbus02Value25		OBJECT-TYPE
			SYNTAX	INTEGER
			ACCESS	read-only
			STATUS	current
	DESCRIPTION ""
			::= { mbus02 81 }

mbus02VIF26		OBJECT-TYPE
			SYNTAX	INTEGER
			ACCESS	read-only
			STATUS	current
	DESCRIPTION ""
			::= { mbus02 82 }

mbus02Value26		OBJECT-TYPE
			SYNTAX	INTEGER
			ACCESS	read-only
			STATUS	current
	DESCRIPTION ""
			::= { mbus02 83 }

mbus02VIF27		OBJECT-TYPE
			SYNTAX	INTEGER
			ACCESS	read-only
			STATUS	current
	DESCRIPTION ""
			::= { mbus02 84 }

mbus02Value27		OBJECT-TYPE
			SYNTAX	INTEGER
			ACCESS	read-only
			STATUS	current
	DESCRIPTION ""
			::= { mbus02 85 }

mbus02VIF28		OBJECT-TYPE
			SYNTAX	INTEGER
			ACCESS	read-only
			STATUS	current
	DESCRIPTION ""
			::= { mbus02 86 }

mbus02Value28		OBJECT-TYPE
			SYNTAX	INTEGER
			ACCESS	read-only
			STATUS	current
	DESCRIPTION ""
			::= { mbus02 87 }

mbus02VIF29		OBJECT-TYPE
			SYNTAX	INTEGER
			ACCESS	read-only
			STATUS	current
	DESCRIPTION ""
			::= { mbus02 88 }

mbus02Value29		OBJECT-TYPE
			SYNTAX	INTEGER
			ACCESS	read-only
			STATUS	current
	DESCRIPTION ""
			::= { mbus02 89 }

mbus02VIF2A		OBJECT-TYPE
			SYNTAX	INTEGER
			ACCESS	read-only
			STATUS	current
	DESCRIPTION ""
			::= { mbus02 90 }

mbus02Value2A		OBJECT-TYPE
			SYNTAX	INTEGER
			ACCESS	read-only
			STATUS	current
	DESCRIPTION ""
			::= { mbus02 91 }

mbus02VIF2B		OBJECT-TYPE
			SYNTAX	INTEGER
			ACCESS	read-only
			STATUS	current
	DESCRIPTION ""
			::= { mbus02 92 }

mbus02Value2B		OBJECT-TYPE
			SYNTAX	INTEGER
			ACCESS	read-only
			STATUS	current
	DESCRIPTION ""
			::= { mbus02 93 }

mbus02VIF2C		OBJECT-TYPE
			SYNTAX	INTEGER
			ACCESS	read-only
			STATUS	current
	DESCRIPTION ""
			::= { mbus02 94 }

mbus02Value2C		OBJECT-TYPE
			SYNTAX	INTEGER
			ACCESS	read-only
			STATUS	current
	DESCRIPTION ""
			::= { mbus02 95 }

mbus02VIF2D		OBJECT-TYPE
			SYNTAX	INTEGER
			ACCESS	read-only
			STATUS	current
	DESCRIPTION ""
			::= { mbus02 96 }

mbus02Value2D		OBJECT-TYPE
			SYNTAX	INTEGER
			ACCESS	read-only
			STATUS	current
	DESCRIPTION ""
			::= { mbus02 97 }

mbus02VIF2E		OBJECT-TYPE
			SYNTAX	INTEGER
			ACCESS	read-only
			STATUS	current
	DESCRIPTION ""
			::= { mbus02 98 }

mbus02Value2E		OBJECT-TYPE
			SYNTAX	INTEGER
			ACCESS	read-only
			STATUS	current
	DESCRIPTION ""
			::= { mbus02 99 }

mbus02VIF2F		OBJECT-TYPE
			SYNTAX	INTEGER
			ACCESS	read-only
			STATUS	current
	DESCRIPTION ""
			::= { mbus02 100 }

mbus02Value2F		OBJECT-TYPE
			SYNTAX	INTEGER
			ACCESS	read-only
			STATUS	current
	DESCRIPTION ""
			::= { mbus02 101 }

mbus03			OBJECT IDENTIFIER ::= { mbus 3 }

mbus03IdNumber		OBJECT-TYPE
			SYNTAX	Gauge
			ACCESS	read-only
			STATUS	current
	DESCRIPTION ""
			::= { mbus03 1 }

mbus03Manufacturer	OBJECT-TYPE
			SYNTAX	Gauge
			ACCESS	read-only
			STATUS	current
	DESCRIPTION ""
			::= { mbus03 2 }

mbus03Version		OBJECT-TYPE
			SYNTAX	Gauge
			ACCESS	read-only
			STATUS	current
	DESCRIPTION ""
			::= { mbus03 3 }

mbus03Medium		OBJECT-TYPE
			SYNTAX	Gauge
			ACCESS	read-only
			STATUS	current
	DESCRIPTION ""
			::= { mbus03 4 }

mbus03Status		OBJECT-TYPE
			SYNTAX	Gauge
			ACCESS	read-only
			STATUS	current
	DESCRIPTION ""
			::= { mbus03 5 }

mbus03VIF00		OBJECT-TYPE
			SYNTAX	INTEGER
			ACCESS	read-only
			STATUS	current
	DESCRIPTION ""
			::= { mbus03 6 }

mbus03Value00		OBJECT-TYPE
			SYNTAX	INTEGER
			ACCESS	read-only
			STATUS	current
	DESCRIPTION ""
			::= { mbus03 7 }

mbus03VIF01		OBJECT-TYPE
			SYNTAX	INTEGER
			ACCESS	read-only
			STATUS	current
	DESCRIPTION ""
			::= { mbus03 8 }

mbus03Value01		OBJECT-TYPE
			SYNTAX	INTEGER
			ACCESS	read-only
			STATUS	current
	DESCRIPTION ""
			::= { mbus03 9 }

mbus03VIF02		OBJECT-TYPE
			SYNTAX	INTEGER
			ACCESS	read-only
			STATUS	current
	DESCRIPTION ""
			::= { mbus03 10 }

mbus03Value02		OBJECT-TYPE
			SYNTAX	INTEGER
			ACCESS	read-only
			STATUS	current
	DESCRIPTION ""
			::= { mbus03 11 }

mbus03VIF03		OBJECT-TYPE
			SYNTAX	INTEGER
			ACCESS	read-only
			STATUS	current
	DESCRIPTION ""
			::= { mbus03 12 }

mbus03Value03		OBJECT-TYPE
			SYNTAX	INTEGER
			ACCESS	read-only
			STATUS	current
	DESCRIPTION ""
			::= { mbus03 13 }

mbus03VIF04		OBJECT-TYPE
			SYNTAX	INTEGER
			ACCESS	read-only
			STATUS	current
	DESCRIPTION ""
			::= { mbus03 14 }

mbus03Value04		OBJECT-TYPE
			SYNTAX	INTEGER
			ACCESS	read-only
			STATUS	current
	DESCRIPTION ""
			::= { mbus03 15 }

mbus03VIF05		OBJECT-TYPE
			SYNTAX	INTEGER
			ACCESS	read-only
			STATUS	current
	DESCRIPTION ""
			::= { mbus03 16 }

mbus03Value05		OBJECT-TYPE
			SYNTAX	INTEGER
			ACCESS	read-only
			STATUS	current
	DESCRIPTION ""
			::= { mbus03 17 }

mbus03VIF06		OBJECT-TYPE
			SYNTAX	INTEGER
			ACCESS	read-only
			STATUS	current
	DESCRIPTION ""
			::= { mbus03 18 }

mbus03Value06		OBJECT-TYPE
			SYNTAX	INTEGER
			ACCESS	read-only
			STATUS	current
	DESCRIPTION ""
			::= { mbus03 19 }

mbus03VIF07		OBJECT-TYPE
			SYNTAX	INTEGER
			ACCESS	read-only
			STATUS	current
	DESCRIPTION ""
			::= { mbus03 20 }

mbus03Value07		OBJECT-TYPE
			SYNTAX	INTEGER
			ACCESS	read-only
			STATUS	current
	DESCRIPTION ""
			::= { mbus03 21 }

mbus03VIF08		OBJECT-TYPE
			SYNTAX	INTEGER
			ACCESS	read-only
			STATUS	current
	DESCRIPTION ""
			::= { mbus03 22 }

mbus03Value08		OBJECT-TYPE
			SYNTAX	INTEGER
			ACCESS	read-only
			STATUS	current
	DESCRIPTION ""
			::= { mbus03 23 }

mbus03VIF09		OBJECT-TYPE
			SYNTAX	INTEGER
			ACCESS	read-only
			STATUS	current
	DESCRIPTION ""
			::= { mbus03 24 }

mbus03Value09		OBJECT-TYPE
			SYNTAX	INTEGER
			ACCESS	read-only
			STATUS	current
	DESCRIPTION ""
			::= { mbus03 25 }

mbus03VIF0A		OBJECT-TYPE
			SYNTAX	INTEGER
			ACCESS	read-only
			STATUS	current
	DESCRIPTION ""
			::= { mbus03 26 }

mbus03Value0A		OBJECT-TYPE
			SYNTAX	INTEGER
			ACCESS	read-only
			STATUS	current
	DESCRIPTION ""
			::= { mbus03 27 }

mbus03VIF0B		OBJECT-TYPE
			SYNTAX	INTEGER
			ACCESS	read-only
			STATUS	current
	DESCRIPTION ""
			::= { mbus03 28 }

mbus03Value0B		OBJECT-TYPE
			SYNTAX	INTEGER
			ACCESS	read-only
			STATUS	current
	DESCRIPTION ""
			::= { mbus03 29 }

mbus03VIF0C		OBJECT-TYPE
			SYNTAX	INTEGER
			ACCESS	read-only
			STATUS	current
	DESCRIPTION ""
			::= { mbus03 30 }

mbus03Value0C		OBJECT-TYPE
			SYNTAX	INTEGER
			ACCESS	read-only
			STATUS	current
	DESCRIPTION ""
			::= { mbus03 31 }

mbus03VIF0D		OBJECT-TYPE
			SYNTAX	INTEGER
			ACCESS	read-only
			STATUS	current
	DESCRIPTION ""
			::= { mbus03 32 }

mbus03Value0D		OBJECT-TYPE
			SYNTAX	INTEGER
			ACCESS	read-only
			STATUS	current
	DESCRIPTION ""
			::= { mbus03 33 }

mbus03VIF0E		OBJECT-TYPE
			SYNTAX	INTEGER
			ACCESS	read-only
			STATUS	current
	DESCRIPTION ""
			::= { mbus03 34 }

mbus03Value0E		OBJECT-TYPE
			SYNTAX	INTEGER
			ACCESS	read-only
			STATUS	current
	DESCRIPTION ""
			::= { mbus03 35 }

mbus03VIF0F		OBJECT-TYPE
			SYNTAX	INTEGER
			ACCESS	read-only
			STATUS	current
	DESCRIPTION ""
			::= { mbus03 36 }

mbus03Value0F		OBJECT-TYPE
			SYNTAX	INTEGER
			ACCESS	read-only
			STATUS	current
	DESCRIPTION ""
			::= { mbus03 37 }

mbus03VIF10		OBJECT-TYPE
			SYNTAX	INTEGER
			ACCESS	read-only
			STATUS	current
	DESCRIPTION ""
			::= { mbus03 38 }

mbus03Value10		OBJECT-TYPE
			SYNTAX	INTEGER
			ACCESS	read-only
			STATUS	current
	DESCRIPTION ""
			::= { mbus03 39 }

mbus03VIF11		OBJECT-TYPE
			SYNTAX	INTEGER
			ACCESS	read-only
			STATUS	current
	DESCRIPTION ""
			::= { mbus03 40 }

mbus03Value11		OBJECT-TYPE
			SYNTAX	INTEGER
			ACCESS	read-only
			STATUS	current
	DESCRIPTION ""
			::= { mbus03 41 }

mbus03VIF12		OBJECT-TYPE
			SYNTAX	INTEGER
			ACCESS	read-only
			STATUS	current
	DESCRIPTION ""
			::= { mbus03 42 }

mbus03Value12		OBJECT-TYPE
			SYNTAX	INTEGER
			ACCESS	read-only
			STATUS	current
	DESCRIPTION ""
			::= { mbus03 43 }

mbus03VIF13		OBJECT-TYPE
			SYNTAX	INTEGER
			ACCESS	read-only
			STATUS	current
	DESCRIPTION ""
			::= { mbus03 44 }

mbus03Value13		OBJECT-TYPE
			SYNTAX	INTEGER
			ACCESS	read-only
			STATUS	current
	DESCRIPTION ""
			::= { mbus03 45 }

mbus03VIF14		OBJECT-TYPE
			SYNTAX	INTEGER
			ACCESS	read-only
			STATUS	current
	DESCRIPTION ""
			::= { mbus03 46 }

mbus03Value14		OBJECT-TYPE
			SYNTAX	INTEGER
			ACCESS	read-only
			STATUS	current
	DESCRIPTION ""
			::= { mbus03 47 }

mbus03VIF15		OBJECT-TYPE
			SYNTAX	INTEGER
			ACCESS	read-only
			STATUS	current
	DESCRIPTION ""
			::= { mbus03 48 }

mbus03Value15		OBJECT-TYPE
			SYNTAX	INTEGER
			ACCESS	read-only
			STATUS	current
	DESCRIPTION ""
			::= { mbus03 49 }

mbus03VIF16		OBJECT-TYPE
			SYNTAX	INTEGER
			ACCESS	read-only
			STATUS	current
	DESCRIPTION ""
			::= { mbus03 50 }

mbus03Value16		OBJECT-TYPE
			SYNTAX	INTEGER
			ACCESS	read-only
			STATUS	current
	DESCRIPTION ""
			::= { mbus03 51 }

mbus03VIF17		OBJECT-TYPE
			SYNTAX	INTEGER
			ACCESS	read-only
			STATUS	current
	DESCRIPTION ""
			::= { mbus03 52 }

mbus03Value17		OBJECT-TYPE
			SYNTAX	INTEGER
			ACCESS	read-only
			STATUS	current
	DESCRIPTION ""
			::= { mbus03 53 }

mbus03VIF18		OBJECT-TYPE
			SYNTAX	INTEGER
			ACCESS	read-only
			STATUS	current
	DESCRIPTION ""
			::= { mbus03 54 }

mbus03Value18		OBJECT-TYPE
			SYNTAX	INTEGER
			ACCESS	read-only
			STATUS	current
	DESCRIPTION ""
			::= { mbus03 55 }

mbus03VIF19		OBJECT-TYPE
			SYNTAX	INTEGER
			ACCESS	read-only
			STATUS	current
	DESCRIPTION ""
			::= { mbus03 56 }

mbus03Value19		OBJECT-TYPE
			SYNTAX	INTEGER
			ACCESS	read-only
			STATUS	current
	DESCRIPTION ""
			::= { mbus03 57 }

mbus03VIF1A		OBJECT-TYPE
			SYNTAX	INTEGER
			ACCESS	read-only
			STATUS	current
	DESCRIPTION ""
			::= { mbus03 58 }

mbus03Value1A		OBJECT-TYPE
			SYNTAX	INTEGER
			ACCESS	read-only
			STATUS	current
	DESCRIPTION ""
			::= { mbus03 59 }

mbus03VIF1B		OBJECT-TYPE
			SYNTAX	INTEGER
			ACCESS	read-only
			STATUS	current
	DESCRIPTION ""
			::= { mbus03 60 }

mbus03Value1B		OBJECT-TYPE
			SYNTAX	INTEGER
			ACCESS	read-only
			STATUS	current
	DESCRIPTION ""
			::= { mbus03 61 }

mbus03VIF1C		OBJECT-TYPE
			SYNTAX	INTEGER
			ACCESS	read-only
			STATUS	current
	DESCRIPTION ""
			::= { mbus03 62 }

mbus03Value1C		OBJECT-TYPE
			SYNTAX	INTEGER
			ACCESS	read-only
			STATUS	current
	DESCRIPTION ""
			::= { mbus03 63 }

mbus03VIF1D		OBJECT-TYPE
			SYNTAX	INTEGER
			ACCESS	read-only
			STATUS	current
	DESCRIPTION ""
			::= { mbus03 64 }

mbus03Value1D		OBJECT-TYPE
			SYNTAX	INTEGER
			ACCESS	read-only
			STATUS	current
	DESCRIPTION ""
			::= { mbus03 65 }

mbus03VIF1E		OBJECT-TYPE
			SYNTAX	INTEGER
			ACCESS	read-only
			STATUS	current
	DESCRIPTION ""
			::= { mbus03 66 }

mbus03Value1E		OBJECT-TYPE
			SYNTAX	INTEGER
			ACCESS	read-only
			STATUS	current
	DESCRIPTION ""
			::= { mbus03 67 }

mbus03VIF1F		OBJECT-TYPE
			SYNTAX	INTEGER
			ACCESS	read-only
			STATUS	current
	DESCRIPTION ""
			::= { mbus03 68 }

mbus03Value1F		OBJECT-TYPE
			SYNTAX	INTEGER
			ACCESS	read-only
			STATUS	current
	DESCRIPTION ""
			::= { mbus03 69 }

mbus03VIF20		OBJECT-TYPE
			SYNTAX	INTEGER
			ACCESS	read-only
			STATUS	current
	DESCRIPTION ""
			::= { mbus03 70 }

mbus03Value20		OBJECT-TYPE
			SYNTAX	INTEGER
			ACCESS	read-only
			STATUS	current
	DESCRIPTION ""
			::= { mbus03 71 }

mbus03VIF21		OBJECT-TYPE
			SYNTAX	INTEGER
			ACCESS	read-only
			STATUS	current
	DESCRIPTION ""
			::= { mbus03 72 }

mbus03Value21		OBJECT-TYPE
			SYNTAX	INTEGER
			ACCESS	read-only
			STATUS	current
	DESCRIPTION ""
			::= { mbus03 73 }

mbus03VIF22		OBJECT-TYPE
			SYNTAX	INTEGER
			ACCESS	read-only
			STATUS	current
	DESCRIPTION ""
			::= { mbus03 74 }

mbus03Value22		OBJECT-TYPE
			SYNTAX	INTEGER
			ACCESS	read-only
			STATUS	current
	DESCRIPTION ""
			::= { mbus03 75 }

mbus03VIF23		OBJECT-TYPE
			SYNTAX	INTEGER
			ACCESS	read-only
			STATUS	current
	DESCRIPTION ""
			::= { mbus03 76 }

mbus03Value23		OBJECT-TYPE
			SYNTAX	INTEGER
			ACCESS	read-only
			STATUS	current
	DESCRIPTION ""
			::= { mbus03 77 }

mbus03VIF24		OBJECT-TYPE
			SYNTAX	INTEGER
			ACCESS	read-only
			STATUS	current
	DESCRIPTION ""
			::= { mbus03 78 }

mbus03Value24		OBJECT-TYPE
			SYNTAX	INTEGER
			ACCESS	read-only
			STATUS	current
	DESCRIPTION ""
			::= { mbus03 79 }

mbus03VIF25		OBJECT-TYPE
			SYNTAX	INTEGER
			ACCESS	read-only
			STATUS	current
	DESCRIPTION ""
			::= { mbus03 80 }

mbus03Value25		OBJECT-TYPE
			SYNTAX	INTEGER
			ACCESS	read-only
			STATUS	current
	DESCRIPTION ""
			::= { mbus03 81 }

mbus03VIF26		OBJECT-TYPE
			SYNTAX	INTEGER
			ACCESS	read-only
			STATUS	current
	DESCRIPTION ""
			::= { mbus03 82 }

mbus03Value26		OBJECT-TYPE
			SYNTAX	INTEGER
			ACCESS	read-only
			STATUS	current
	DESCRIPTION ""
			::= { mbus03 83 }

mbus03VIF27		OBJECT-TYPE
			SYNTAX	INTEGER
			ACCESS	read-only
			STATUS	current
	DESCRIPTION ""
			::= { mbus03 84 }

mbus03Value27		OBJECT-TYPE
			SYNTAX	INTEGER
			ACCESS	read-only
			STATUS	current
	DESCRIPTION ""
			::= { mbus03 85 }

mbus03VIF28		OBJECT-TYPE
			SYNTAX	INTEGER
			ACCESS	read-only
			STATUS	current
	DESCRIPTION ""
			::= { mbus03 86 }

mbus03Value28		OBJECT-TYPE
			SYNTAX	INTEGER
			ACCESS	read-only
			STATUS	current
	DESCRIPTION ""
			::= { mbus03 87 }

mbus03VIF29		OBJECT-TYPE
			SYNTAX	INTEGER
			ACCESS	read-only
			STATUS	current
	DESCRIPTION ""
			::= { mbus03 88 }

mbus03Value29		OBJECT-TYPE
			SYNTAX	INTEGER
			ACCESS	read-only
			STATUS	current
	DESCRIPTION ""
			::= { mbus03 89 }

mbus03VIF2A		OBJECT-TYPE
			SYNTAX	INTEGER
			ACCESS	read-only
			STATUS	current
	DESCRIPTION ""
			::= { mbus03 90 }

mbus03Value2A		OBJECT-TYPE
			SYNTAX	INTEGER
			ACCESS	read-only
			STATUS	current
	DESCRIPTION ""
			::= { mbus03 91 }

mbus03VIF2B		OBJECT-TYPE
			SYNTAX	INTEGER
			ACCESS	read-only
			STATUS	current
	DESCRIPTION ""
			::= { mbus03 92 }

mbus03Value2B		OBJECT-TYPE
			SYNTAX	INTEGER
			ACCESS	read-only
			STATUS	current
	DESCRIPTION ""
			::= { mbus03 93 }

mbus03VIF2C		OBJECT-TYPE
			SYNTAX	INTEGER
			ACCESS	read-only
			STATUS	current
	DESCRIPTION ""
			::= { mbus03 94 }

mbus03Value2C		OBJECT-TYPE
			SYNTAX	INTEGER
			ACCESS	read-only
			STATUS	current
	DESCRIPTION ""
			::= { mbus03 95 }

mbus03VIF2D		OBJECT-TYPE
			SYNTAX	INTEGER
			ACCESS	read-only
			STATUS	current
	DESCRIPTION ""
			::= { mbus03 96 }

mbus03Value2D		OBJECT-TYPE
			SYNTAX	INTEGER
			ACCESS	read-only
			STATUS	current
	DESCRIPTION ""
			::= { mbus03 97 }

mbus03VIF2E		OBJECT-TYPE
			SYNTAX	INTEGER
			ACCESS	read-only
			STATUS	current
	DESCRIPTION ""
			::= { mbus03 98 }

mbus03Value2E		OBJECT-TYPE
			SYNTAX	INTEGER
			ACCESS	read-only
			STATUS	current
	DESCRIPTION ""
			::= { mbus03 99 }

mbus03VIF2F		OBJECT-TYPE
			SYNTAX	INTEGER
			ACCESS	read-only
			STATUS	current
	DESCRIPTION ""
			::= { mbus03 100 }

mbus03Value2F		OBJECT-TYPE
			SYNTAX	INTEGER
			ACCESS	read-only
			STATUS	current
	DESCRIPTION ""
			::= { mbus03 101 }

mbus04			OBJECT IDENTIFIER ::= { mbus 4 }

mbus04IdNumber		OBJECT-TYPE
			SYNTAX	Gauge
			ACCESS	read-only
			STATUS	current
	DESCRIPTION ""
			::= { mbus04 1 }

mbus04Manufacturer	OBJECT-TYPE
			SYNTAX	Gauge
			ACCESS	read-only
			STATUS	current
	DESCRIPTION ""
			::= { mbus04 2 }

mbus04Version		OBJECT-TYPE
			SYNTAX	Gauge
			ACCESS	read-only
			STATUS	current
	DESCRIPTION ""
			::= { mbus04 3 }

mbus04Medium		OBJECT-TYPE
			SYNTAX	Gauge
			ACCESS	read-only
			STATUS	current
	DESCRIPTION ""
			::= { mbus04 4 }

mbus04Status		OBJECT-TYPE
			SYNTAX	Gauge
			ACCESS	read-only
			STATUS	current
	DESCRIPTION ""
			::= { mbus04 5 }

mbus04VIF00		OBJECT-TYPE
			SYNTAX	INTEGER
			ACCESS	read-only
			STATUS	current
	DESCRIPTION ""
			::= { mbus04 6 }

mbus04Value00		OBJECT-TYPE
			SYNTAX	INTEGER
			ACCESS	read-only
			STATUS	current
	DESCRIPTION ""
			::= { mbus04 7 }

mbus04VIF01		OBJECT-TYPE
			SYNTAX	INTEGER
			ACCESS	read-only
			STATUS	current
	DESCRIPTION ""
			::= { mbus04 8 }

mbus04Value01		OBJECT-TYPE
			SYNTAX	INTEGER
			ACCESS	read-only
			STATUS	current
	DESCRIPTION ""
			::= { mbus04 9 }

mbus04VIF02		OBJECT-TYPE
			SYNTAX	INTEGER
			ACCESS	read-only
			STATUS	current
	DESCRIPTION ""
			::= { mbus04 10 }

mbus04Value02		OBJECT-TYPE
			SYNTAX	INTEGER
			ACCESS	read-only
			STATUS	current
	DESCRIPTION ""
			::= { mbus04 11 }

mbus04VIF03		OBJECT-TYPE
			SYNTAX	INTEGER
			ACCESS	read-only
			STATUS	current
	DESCRIPTION ""
			::= { mbus04 12 }

mbus04Value03		OBJECT-TYPE
			SYNTAX	INTEGER
			ACCESS	read-only
			STATUS	current
	DESCRIPTION ""
			::= { mbus04 13 }

mbus04VIF04		OBJECT-TYPE
			SYNTAX	INTEGER
			ACCESS	read-only
			STATUS	current
	DESCRIPTION ""
			::= { mbus04 14 }

mbus04Value04		OBJECT-TYPE
			SYNTAX	INTEGER
			ACCESS	read-only
			STATUS	current
	DESCRIPTION ""
			::= { mbus04 15 }

mbus04VIF05		OBJECT-TYPE
			SYNTAX	INTEGER
			ACCESS	read-only
			STATUS	current
	DESCRIPTION ""
			::= { mbus04 16 }

mbus04Value05		OBJECT-TYPE
			SYNTAX	INTEGER
			ACCESS	read-only
			STATUS	current
	DESCRIPTION ""
			::= { mbus04 17 }

mbus04VIF06		OBJECT-TYPE
			SYNTAX	INTEGER
			ACCESS	read-only
			STATUS	current
	DESCRIPTION ""
			::= { mbus04 18 }

mbus04Value06		OBJECT-TYPE
			SYNTAX	INTEGER
			ACCESS	read-only
			STATUS	current
	DESCRIPTION ""
			::= { mbus04 19 }

mbus04VIF07		OBJECT-TYPE
			SYNTAX	INTEGER
			ACCESS	read-only
			STATUS	current
	DESCRIPTION ""
			::= { mbus04 20 }

mbus04Value07		OBJECT-TYPE
			SYNTAX	INTEGER
			ACCESS	read-only
			STATUS	current
	DESCRIPTION ""
			::= { mbus04 21 }

mbus04VIF08		OBJECT-TYPE
			SYNTAX	INTEGER
			ACCESS	read-only
			STATUS	current
	DESCRIPTION ""
			::= { mbus04 22 }

mbus04Value08		OBJECT-TYPE
			SYNTAX	INTEGER
			ACCESS	read-only
			STATUS	current
	DESCRIPTION ""
			::= { mbus04 23 }

mbus04VIF09		OBJECT-TYPE
			SYNTAX	INTEGER
			ACCESS	read-only
			STATUS	current
	DESCRIPTION ""
			::= { mbus04 24 }

mbus04Value09		OBJECT-TYPE
			SYNTAX	INTEGER
			ACCESS	read-only
			STATUS	current
	DESCRIPTION ""
			::= { mbus04 25 }

mbus04VIF0A		OBJECT-TYPE
			SYNTAX	INTEGER
			ACCESS	read-only
			STATUS	current
	DESCRIPTION ""
			::= { mbus04 26 }

mbus04Value0A		OBJECT-TYPE
			SYNTAX	INTEGER
			ACCESS	read-only
			STATUS	current
	DESCRIPTION ""
			::= { mbus04 27 }

mbus04VIF0B		OBJECT-TYPE
			SYNTAX	INTEGER
			ACCESS	read-only
			STATUS	current
	DESCRIPTION ""
			::= { mbus04 28 }

mbus04Value0B		OBJECT-TYPE
			SYNTAX	INTEGER
			ACCESS	read-only
			STATUS	current
	DESCRIPTION ""
			::= { mbus04 29 }

mbus04VIF0C		OBJECT-TYPE
			SYNTAX	INTEGER
			ACCESS	read-only
			STATUS	current
	DESCRIPTION ""
			::= { mbus04 30 }

mbus04Value0C		OBJECT-TYPE
			SYNTAX	INTEGER
			ACCESS	read-only
			STATUS	current
	DESCRIPTION ""
			::= { mbus04 31 }

mbus04VIF0D		OBJECT-TYPE
			SYNTAX	INTEGER
			ACCESS	read-only
			STATUS	current
	DESCRIPTION ""
			::= { mbus04 32 }

mbus04Value0D		OBJECT-TYPE
			SYNTAX	INTEGER
			ACCESS	read-only
			STATUS	current
	DESCRIPTION ""
			::= { mbus04 33 }

mbus04VIF0E		OBJECT-TYPE
			SYNTAX	INTEGER
			ACCESS	read-only
			STATUS	current
	DESCRIPTION ""
			::= { mbus04 34 }

mbus04Value0E		OBJECT-TYPE
			SYNTAX	INTEGER
			ACCESS	read-only
			STATUS	current
	DESCRIPTION ""
			::= { mbus04 35 }

mbus04VIF0F		OBJECT-TYPE
			SYNTAX	INTEGER
			ACCESS	read-only
			STATUS	current
	DESCRIPTION ""
			::= { mbus04 36 }

mbus04Value0F		OBJECT-TYPE
			SYNTAX	INTEGER
			ACCESS	read-only
			STATUS	current
	DESCRIPTION ""
			::= { mbus04 37 }

mbus04VIF10		OBJECT-TYPE
			SYNTAX	INTEGER
			ACCESS	read-only
			STATUS	current
	DESCRIPTION ""
			::= { mbus04 38 }

mbus04Value10		OBJECT-TYPE
			SYNTAX	INTEGER
			ACCESS	read-only
			STATUS	current
	DESCRIPTION ""
			::= { mbus04 39 }

mbus04VIF11		OBJECT-TYPE
			SYNTAX	INTEGER
			ACCESS	read-only
			STATUS	current
	DESCRIPTION ""
			::= { mbus04 40 }

mbus04Value11		OBJECT-TYPE
			SYNTAX	INTEGER
			ACCESS	read-only
			STATUS	current
	DESCRIPTION ""
			::= { mbus04 41 }

mbus04VIF12		OBJECT-TYPE
			SYNTAX	INTEGER
			ACCESS	read-only
			STATUS	current
	DESCRIPTION ""
			::= { mbus04 42 }

mbus04Value12		OBJECT-TYPE
			SYNTAX	INTEGER
			ACCESS	read-only
			STATUS	current
	DESCRIPTION ""
			::= { mbus04 43 }

mbus04VIF13		OBJECT-TYPE
			SYNTAX	INTEGER
			ACCESS	read-only
			STATUS	current
	DESCRIPTION ""
			::= { mbus04 44 }

mbus04Value13		OBJECT-TYPE
			SYNTAX	INTEGER
			ACCESS	read-only
			STATUS	current
	DESCRIPTION ""
			::= { mbus04 45 }

mbus04VIF14		OBJECT-TYPE
			SYNTAX	INTEGER
			ACCESS	read-only
			STATUS	current
	DESCRIPTION ""
			::= { mbus04 46 }

mbus04Value14		OBJECT-TYPE
			SYNTAX	INTEGER
			ACCESS	read-only
			STATUS	current
	DESCRIPTION ""
			::= { mbus04 47 }

mbus04VIF15		OBJECT-TYPE
			SYNTAX	INTEGER
			ACCESS	read-only
			STATUS	current
	DESCRIPTION ""
			::= { mbus04 48 }

mbus04Value15		OBJECT-TYPE
			SYNTAX	INTEGER
			ACCESS	read-only
			STATUS	current
	DESCRIPTION ""
			::= { mbus04 49 }

mbus04VIF16		OBJECT-TYPE
			SYNTAX	INTEGER
			ACCESS	read-only
			STATUS	current
	DESCRIPTION ""
			::= { mbus04 50 }

mbus04Value16		OBJECT-TYPE
			SYNTAX	INTEGER
			ACCESS	read-only
			STATUS	current
	DESCRIPTION ""
			::= { mbus04 51 }

mbus04VIF17		OBJECT-TYPE
			SYNTAX	INTEGER
			ACCESS	read-only
			STATUS	current
	DESCRIPTION ""
			::= { mbus04 52 }

mbus04Value17		OBJECT-TYPE
			SYNTAX	INTEGER
			ACCESS	read-only
			STATUS	current
	DESCRIPTION ""
			::= { mbus04 53 }

mbus04VIF18		OBJECT-TYPE
			SYNTAX	INTEGER
			ACCESS	read-only
			STATUS	current
	DESCRIPTION ""
			::= { mbus04 54 }

mbus04Value18		OBJECT-TYPE
			SYNTAX	INTEGER
			ACCESS	read-only
			STATUS	current
	DESCRIPTION ""
			::= { mbus04 55 }

mbus04VIF19		OBJECT-TYPE
			SYNTAX	INTEGER
			ACCESS	read-only
			STATUS	current
	DESCRIPTION ""
			::= { mbus04 56 }

mbus04Value19		OBJECT-TYPE
			SYNTAX	INTEGER
			ACCESS	read-only
			STATUS	current
	DESCRIPTION ""
			::= { mbus04 57 }

mbus04VIF1A		OBJECT-TYPE
			SYNTAX	INTEGER
			ACCESS	read-only
			STATUS	current
	DESCRIPTION ""
			::= { mbus04 58 }

mbus04Value1A		OBJECT-TYPE
			SYNTAX	INTEGER
			ACCESS	read-only
			STATUS	current
	DESCRIPTION ""
			::= { mbus04 59 }

mbus04VIF1B		OBJECT-TYPE
			SYNTAX	INTEGER
			ACCESS	read-only
			STATUS	current
	DESCRIPTION ""
			::= { mbus04 60 }

mbus04Value1B		OBJECT-TYPE
			SYNTAX	INTEGER
			ACCESS	read-only
			STATUS	current
	DESCRIPTION ""
			::= { mbus04 61 }

mbus04VIF1C		OBJECT-TYPE
			SYNTAX	INTEGER
			ACCESS	read-only
			STATUS	current
	DESCRIPTION ""
			::= { mbus04 62 }

mbus04Value1C		OBJECT-TYPE
			SYNTAX	INTEGER
			ACCESS	read-only
			STATUS	current
	DESCRIPTION ""
			::= { mbus04 63 }

mbus04VIF1D		OBJECT-TYPE
			SYNTAX	INTEGER
			ACCESS	read-only
			STATUS	current
	DESCRIPTION ""
			::= { mbus04 64 }

mbus04Value1D		OBJECT-TYPE
			SYNTAX	INTEGER
			ACCESS	read-only
			STATUS	current
	DESCRIPTION ""
			::= { mbus04 65 }

mbus04VIF1E		OBJECT-TYPE
			SYNTAX	INTEGER
			ACCESS	read-only
			STATUS	current
	DESCRIPTION ""
			::= { mbus04 66 }

mbus04Value1E		OBJECT-TYPE
			SYNTAX	INTEGER
			ACCESS	read-only
			STATUS	current
	DESCRIPTION ""
			::= { mbus04 67 }

mbus04VIF1F		OBJECT-TYPE
			SYNTAX	INTEGER
			ACCESS	read-only
			STATUS	current
	DESCRIPTION ""
			::= { mbus04 68 }

mbus04Value1F		OBJECT-TYPE
			SYNTAX	INTEGER
			ACCESS	read-only
			STATUS	current
	DESCRIPTION ""
			::= { mbus04 69 }

mbus04VIF20		OBJECT-TYPE
			SYNTAX	INTEGER
			ACCESS	read-only
			STATUS	current
	DESCRIPTION ""
			::= { mbus04 70 }

mbus04Value20		OBJECT-TYPE
			SYNTAX	INTEGER
			ACCESS	read-only
			STATUS	current
	DESCRIPTION ""
			::= { mbus04 71 }

mbus04VIF21		OBJECT-TYPE
			SYNTAX	INTEGER
			ACCESS	read-only
			STATUS	current
	DESCRIPTION ""
			::= { mbus04 72 }

mbus04Value21		OBJECT-TYPE
			SYNTAX	INTEGER
			ACCESS	read-only
			STATUS	current
	DESCRIPTION ""
			::= { mbus04 73 }

mbus04VIF22		OBJECT-TYPE
			SYNTAX	INTEGER
			ACCESS	read-only
			STATUS	current
	DESCRIPTION ""
			::= { mbus04 74 }

mbus04Value22		OBJECT-TYPE
			SYNTAX	INTEGER
			ACCESS	read-only
			STATUS	current
	DESCRIPTION ""
			::= { mbus04 75 }

mbus04VIF23		OBJECT-TYPE
			SYNTAX	INTEGER
			ACCESS	read-only
			STATUS	current
	DESCRIPTION ""
			::= { mbus04 76 }

mbus04Value23		OBJECT-TYPE
			SYNTAX	INTEGER
			ACCESS	read-only
			STATUS	current
	DESCRIPTION ""
			::= { mbus04 77 }

mbus04VIF24		OBJECT-TYPE
			SYNTAX	INTEGER
			ACCESS	read-only
			STATUS	current
	DESCRIPTION ""
			::= { mbus04 78 }

mbus04Value24		OBJECT-TYPE
			SYNTAX	INTEGER
			ACCESS	read-only
			STATUS	current
	DESCRIPTION ""
			::= { mbus04 79 }

mbus04VIF25		OBJECT-TYPE
			SYNTAX	INTEGER
			ACCESS	read-only
			STATUS	current
	DESCRIPTION ""
			::= { mbus04 80 }

mbus04Value25		OBJECT-TYPE
			SYNTAX	INTEGER
			ACCESS	read-only
			STATUS	current
	DESCRIPTION ""
			::= { mbus04 81 }

mbus04VIF26		OBJECT-TYPE
			SYNTAX	INTEGER
			ACCESS	read-only
			STATUS	current
	DESCRIPTION ""
			::= { mbus04 82 }

mbus04Value26		OBJECT-TYPE
			SYNTAX	INTEGER
			ACCESS	read-only
			STATUS	current
	DESCRIPTION ""
			::= { mbus04 83 }

mbus04VIF27		OBJECT-TYPE
			SYNTAX	INTEGER
			ACCESS	read-only
			STATUS	current
	DESCRIPTION ""
			::= { mbus04 84 }

mbus04Value27		OBJECT-TYPE
			SYNTAX	INTEGER
			ACCESS	read-only
			STATUS	current
	DESCRIPTION ""
			::= { mbus04 85 }

mbus04VIF28		OBJECT-TYPE
			SYNTAX	INTEGER
			ACCESS	read-only
			STATUS	current
	DESCRIPTION ""
			::= { mbus04 86 }

mbus04Value28		OBJECT-TYPE
			SYNTAX	INTEGER
			ACCESS	read-only
			STATUS	current
	DESCRIPTION ""
			::= { mbus04 87 }

mbus04VIF29		OBJECT-TYPE
			SYNTAX	INTEGER
			ACCESS	read-only
			STATUS	current
	DESCRIPTION ""
			::= { mbus04 88 }

mbus04Value29		OBJECT-TYPE
			SYNTAX	INTEGER
			ACCESS	read-only
			STATUS	current
	DESCRIPTION ""
			::= { mbus04 89 }

mbus04VIF2A		OBJECT-TYPE
			SYNTAX	INTEGER
			ACCESS	read-only
			STATUS	current
	DESCRIPTION ""
			::= { mbus04 90 }

mbus04Value2A		OBJECT-TYPE
			SYNTAX	INTEGER
			ACCESS	read-only
			STATUS	current
	DESCRIPTION ""
			::= { mbus04 91 }

mbus04VIF2B		OBJECT-TYPE
			SYNTAX	INTEGER
			ACCESS	read-only
			STATUS	current
	DESCRIPTION ""
			::= { mbus04 92 }

mbus04Value2B		OBJECT-TYPE
			SYNTAX	INTEGER
			ACCESS	read-only
			STATUS	current
	DESCRIPTION ""
			::= { mbus04 93 }

mbus04VIF2C		OBJECT-TYPE
			SYNTAX	INTEGER
			ACCESS	read-only
			STATUS	current
	DESCRIPTION ""
			::= { mbus04 94 }

mbus04Value2C		OBJECT-TYPE
			SYNTAX	INTEGER
			ACCESS	read-only
			STATUS	current
	DESCRIPTION ""
			::= { mbus04 95 }

mbus04VIF2D		OBJECT-TYPE
			SYNTAX	INTEGER
			ACCESS	read-only
			STATUS	current
	DESCRIPTION ""
			::= { mbus04 96 }

mbus04Value2D		OBJECT-TYPE
			SYNTAX	INTEGER
			ACCESS	read-only
			STATUS	current
	DESCRIPTION ""
			::= { mbus04 97 }

mbus04VIF2E		OBJECT-TYPE
			SYNTAX	INTEGER
			ACCESS	read-only
			STATUS	current
	DESCRIPTION ""
			::= { mbus04 98 }

mbus04Value2E		OBJECT-TYPE
			SYNTAX	INTEGER
			ACCESS	read-only
			STATUS	current
	DESCRIPTION ""
			::= { mbus04 99 }

mbus04VIF2F		OBJECT-TYPE
			SYNTAX	INTEGER
			ACCESS	read-only
			STATUS	current
	DESCRIPTION ""
			::= { mbus04 100 }

mbus04Value2F		OBJECT-TYPE
			SYNTAX	INTEGER
			ACCESS	read-only
			STATUS	current
	DESCRIPTION ""
			::= { mbus04 101 }

mbus05			OBJECT IDENTIFIER ::= { mbus 5 }

mbus05IdNumber		OBJECT-TYPE
			SYNTAX	Gauge
			ACCESS	read-only
			STATUS	current
	DESCRIPTION ""
			::= { mbus05 1 }

mbus05Manufacturer	OBJECT-TYPE
			SYNTAX	Gauge
			ACCESS	read-only
			STATUS	current
	DESCRIPTION ""
			::= { mbus05 2 }

mbus05Version		OBJECT-TYPE
			SYNTAX	Gauge
			ACCESS	read-only
			STATUS	current
	DESCRIPTION ""
			::= { mbus05 3 }

mbus05Medium		OBJECT-TYPE
			SYNTAX	Gauge
			ACCESS	read-only
			STATUS	current
	DESCRIPTION ""
			::= { mbus05 4 }

mbus05Status		OBJECT-TYPE
			SYNTAX	Gauge
			ACCESS	read-only
			STATUS	current
	DESCRIPTION ""
			::= { mbus05 5 }

mbus05VIF00		OBJECT-TYPE
			SYNTAX	INTEGER
			ACCESS	read-only
			STATUS	current
	DESCRIPTION ""
			::= { mbus05 6 }

mbus05Value00		OBJECT-TYPE
			SYNTAX	INTEGER
			ACCESS	read-only
			STATUS	current
	DESCRIPTION ""
			::= { mbus05 7 }

mbus05VIF01		OBJECT-TYPE
			SYNTAX	INTEGER
			ACCESS	read-only
			STATUS	current
	DESCRIPTION ""
			::= { mbus05 8 }

mbus05Value01		OBJECT-TYPE
			SYNTAX	INTEGER
			ACCESS	read-only
			STATUS	current
	DESCRIPTION ""
			::= { mbus05 9 }

mbus05VIF02		OBJECT-TYPE
			SYNTAX	INTEGER
			ACCESS	read-only
			STATUS	current
	DESCRIPTION ""
			::= { mbus05 10 }

mbus05Value02		OBJECT-TYPE
			SYNTAX	INTEGER
			ACCESS	read-only
			STATUS	current
	DESCRIPTION ""
			::= { mbus05 11 }

mbus05VIF03		OBJECT-TYPE
			SYNTAX	INTEGER
			ACCESS	read-only
			STATUS	current
	DESCRIPTION ""
			::= { mbus05 12 }

mbus05Value03		OBJECT-TYPE
			SYNTAX	INTEGER
			ACCESS	read-only
			STATUS	current
	DESCRIPTION ""
			::= { mbus05 13 }

mbus05VIF04		OBJECT-TYPE
			SYNTAX	INTEGER
			ACCESS	read-only
			STATUS	current
	DESCRIPTION ""
			::= { mbus05 14 }

mbus05Value04		OBJECT-TYPE
			SYNTAX	INTEGER
			ACCESS	read-only
			STATUS	current
	DESCRIPTION ""
			::= { mbus05 15 }

mbus05VIF05		OBJECT-TYPE
			SYNTAX	INTEGER
			ACCESS	read-only
			STATUS	current
	DESCRIPTION ""
			::= { mbus05 16 }

mbus05Value05		OBJECT-TYPE
			SYNTAX	INTEGER
			ACCESS	read-only
			STATUS	current
	DESCRIPTION ""
			::= { mbus05 17 }

mbus05VIF06		OBJECT-TYPE
			SYNTAX	INTEGER
			ACCESS	read-only
			STATUS	current
	DESCRIPTION ""
			::= { mbus05 18 }

mbus05Value06		OBJECT-TYPE
			SYNTAX	INTEGER
			ACCESS	read-only
			STATUS	current
	DESCRIPTION ""
			::= { mbus05 19 }

mbus05VIF07		OBJECT-TYPE
			SYNTAX	INTEGER
			ACCESS	read-only
			STATUS	current
	DESCRIPTION ""
			::= { mbus05 20 }

mbus05Value07		OBJECT-TYPE
			SYNTAX	INTEGER
			ACCESS	read-only
			STATUS	current
	DESCRIPTION ""
			::= { mbus05 21 }

mbus05VIF08		OBJECT-TYPE
			SYNTAX	INTEGER
			ACCESS	read-only
			STATUS	current
	DESCRIPTION ""
			::= { mbus05 22 }

mbus05Value08		OBJECT-TYPE
			SYNTAX	INTEGER
			ACCESS	read-only
			STATUS	current
	DESCRIPTION ""
			::= { mbus05 23 }

mbus05VIF09		OBJECT-TYPE
			SYNTAX	INTEGER
			ACCESS	read-only
			STATUS	current
	DESCRIPTION ""
			::= { mbus05 24 }

mbus05Value09		OBJECT-TYPE
			SYNTAX	INTEGER
			ACCESS	read-only
			STATUS	current
	DESCRIPTION ""
			::= { mbus05 25 }

mbus05VIF0A		OBJECT-TYPE
			SYNTAX	INTEGER
			ACCESS	read-only
			STATUS	current
	DESCRIPTION ""
			::= { mbus05 26 }

mbus05Value0A		OBJECT-TYPE
			SYNTAX	INTEGER
			ACCESS	read-only
			STATUS	current
	DESCRIPTION ""
			::= { mbus05 27 }

mbus05VIF0B		OBJECT-TYPE
			SYNTAX	INTEGER
			ACCESS	read-only
			STATUS	current
	DESCRIPTION ""
			::= { mbus05 28 }

mbus05Value0B		OBJECT-TYPE
			SYNTAX	INTEGER
			ACCESS	read-only
			STATUS	current
	DESCRIPTION ""
			::= { mbus05 29 }

mbus05VIF0C		OBJECT-TYPE
			SYNTAX	INTEGER
			ACCESS	read-only
			STATUS	current
	DESCRIPTION ""
			::= { mbus05 30 }

mbus05Value0C		OBJECT-TYPE
			SYNTAX	INTEGER
			ACCESS	read-only
			STATUS	current
	DESCRIPTION ""
			::= { mbus05 31 }

mbus05VIF0D		OBJECT-TYPE
			SYNTAX	INTEGER
			ACCESS	read-only
			STATUS	current
	DESCRIPTION ""
			::= { mbus05 32 }

mbus05Value0D		OBJECT-TYPE
			SYNTAX	INTEGER
			ACCESS	read-only
			STATUS	current
	DESCRIPTION ""
			::= { mbus05 33 }

mbus05VIF0E		OBJECT-TYPE
			SYNTAX	INTEGER
			ACCESS	read-only
			STATUS	current
	DESCRIPTION ""
			::= { mbus05 34 }

mbus05Value0E		OBJECT-TYPE
			SYNTAX	INTEGER
			ACCESS	read-only
			STATUS	current
	DESCRIPTION ""
			::= { mbus05 35 }

mbus05VIF0F		OBJECT-TYPE
			SYNTAX	INTEGER
			ACCESS	read-only
			STATUS	current
	DESCRIPTION ""
			::= { mbus05 36 }

mbus05Value0F		OBJECT-TYPE
			SYNTAX	INTEGER
			ACCESS	read-only
			STATUS	current
	DESCRIPTION ""
			::= { mbus05 37 }

mbus05VIF10		OBJECT-TYPE
			SYNTAX	INTEGER
			ACCESS	read-only
			STATUS	current
	DESCRIPTION ""
			::= { mbus05 38 }

mbus05Value10		OBJECT-TYPE
			SYNTAX	INTEGER
			ACCESS	read-only
			STATUS	current
	DESCRIPTION ""
			::= { mbus05 39 }

mbus05VIF11		OBJECT-TYPE
			SYNTAX	INTEGER
			ACCESS	read-only
			STATUS	current
	DESCRIPTION ""
			::= { mbus05 40 }

mbus05Value11		OBJECT-TYPE
			SYNTAX	INTEGER
			ACCESS	read-only
			STATUS	current
	DESCRIPTION ""
			::= { mbus05 41 }

mbus05VIF12		OBJECT-TYPE
			SYNTAX	INTEGER
			ACCESS	read-only
			STATUS	current
	DESCRIPTION ""
			::= { mbus05 42 }

mbus05Value12		OBJECT-TYPE
			SYNTAX	INTEGER
			ACCESS	read-only
			STATUS	current
	DESCRIPTION ""
			::= { mbus05 43 }

mbus05VIF13		OBJECT-TYPE
			SYNTAX	INTEGER
			ACCESS	read-only
			STATUS	current
	DESCRIPTION ""
			::= { mbus05 44 }

mbus05Value13		OBJECT-TYPE
			SYNTAX	INTEGER
			ACCESS	read-only
			STATUS	current
	DESCRIPTION ""
			::= { mbus05 45 }

mbus05VIF14		OBJECT-TYPE
			SYNTAX	INTEGER
			ACCESS	read-only
			STATUS	current
	DESCRIPTION ""
			::= { mbus05 46 }

mbus05Value14		OBJECT-TYPE
			SYNTAX	INTEGER
			ACCESS	read-only
			STATUS	current
	DESCRIPTION ""
			::= { mbus05 47 }

mbus05VIF15		OBJECT-TYPE
			SYNTAX	INTEGER
			ACCESS	read-only
			STATUS	current
	DESCRIPTION ""
			::= { mbus05 48 }

mbus05Value15		OBJECT-TYPE
			SYNTAX	INTEGER
			ACCESS	read-only
			STATUS	current
	DESCRIPTION ""
			::= { mbus05 49 }

mbus05VIF16		OBJECT-TYPE
			SYNTAX	INTEGER
			ACCESS	read-only
			STATUS	current
	DESCRIPTION ""
			::= { mbus05 50 }

mbus05Value16		OBJECT-TYPE
			SYNTAX	INTEGER
			ACCESS	read-only
			STATUS	current
	DESCRIPTION ""
			::= { mbus05 51 }

mbus05VIF17		OBJECT-TYPE
			SYNTAX	INTEGER
			ACCESS	read-only
			STATUS	current
	DESCRIPTION ""
			::= { mbus05 52 }

mbus05Value17		OBJECT-TYPE
			SYNTAX	INTEGER
			ACCESS	read-only
			STATUS	current
	DESCRIPTION ""
			::= { mbus05 53 }

mbus05VIF18		OBJECT-TYPE
			SYNTAX	INTEGER
			ACCESS	read-only
			STATUS	current
	DESCRIPTION ""
			::= { mbus05 54 }

mbus05Value18		OBJECT-TYPE
			SYNTAX	INTEGER
			ACCESS	read-only
			STATUS	current
	DESCRIPTION ""
			::= { mbus05 55 }

mbus05VIF19		OBJECT-TYPE
			SYNTAX	INTEGER
			ACCESS	read-only
			STATUS	current
	DESCRIPTION ""
			::= { mbus05 56 }

mbus05Value19		OBJECT-TYPE
			SYNTAX	INTEGER
			ACCESS	read-only
			STATUS	current
	DESCRIPTION ""
			::= { mbus05 57 }

mbus05VIF1A		OBJECT-TYPE
			SYNTAX	INTEGER
			ACCESS	read-only
			STATUS	current
	DESCRIPTION ""
			::= { mbus05 58 }

mbus05Value1A		OBJECT-TYPE
			SYNTAX	INTEGER
			ACCESS	read-only
			STATUS	current
	DESCRIPTION ""
			::= { mbus05 59 }

mbus05VIF1B		OBJECT-TYPE
			SYNTAX	INTEGER
			ACCESS	read-only
			STATUS	current
	DESCRIPTION ""
			::= { mbus05 60 }

mbus05Value1B		OBJECT-TYPE
			SYNTAX	INTEGER
			ACCESS	read-only
			STATUS	current
	DESCRIPTION ""
			::= { mbus05 61 }

mbus05VIF1C		OBJECT-TYPE
			SYNTAX	INTEGER
			ACCESS	read-only
			STATUS	current
	DESCRIPTION ""
			::= { mbus05 62 }

mbus05Value1C		OBJECT-TYPE
			SYNTAX	INTEGER
			ACCESS	read-only
			STATUS	current
	DESCRIPTION ""
			::= { mbus05 63 }

mbus05VIF1D		OBJECT-TYPE
			SYNTAX	INTEGER
			ACCESS	read-only
			STATUS	current
	DESCRIPTION ""
			::= { mbus05 64 }

mbus05Value1D		OBJECT-TYPE
			SYNTAX	INTEGER
			ACCESS	read-only
			STATUS	current
	DESCRIPTION ""
			::= { mbus05 65 }

mbus05VIF1E		OBJECT-TYPE
			SYNTAX	INTEGER
			ACCESS	read-only
			STATUS	current
	DESCRIPTION ""
			::= { mbus05 66 }

mbus05Value1E		OBJECT-TYPE
			SYNTAX	INTEGER
			ACCESS	read-only
			STATUS	current
	DESCRIPTION ""
			::= { mbus05 67 }

mbus05VIF1F		OBJECT-TYPE
			SYNTAX	INTEGER
			ACCESS	read-only
			STATUS	current
	DESCRIPTION ""
			::= { mbus05 68 }

mbus05Value1F		OBJECT-TYPE
			SYNTAX	INTEGER
			ACCESS	read-only
			STATUS	current
	DESCRIPTION ""
			::= { mbus05 69 }

mbus05VIF20		OBJECT-TYPE
			SYNTAX	INTEGER
			ACCESS	read-only
			STATUS	current
	DESCRIPTION ""
			::= { mbus05 70 }

mbus05Value20		OBJECT-TYPE
			SYNTAX	INTEGER
			ACCESS	read-only
			STATUS	current
	DESCRIPTION ""
			::= { mbus05 71 }

mbus05VIF21		OBJECT-TYPE
			SYNTAX	INTEGER
			ACCESS	read-only
			STATUS	current
	DESCRIPTION ""
			::= { mbus05 72 }

mbus05Value21		OBJECT-TYPE
			SYNTAX	INTEGER
			ACCESS	read-only
			STATUS	current
	DESCRIPTION ""
			::= { mbus05 73 }

mbus05VIF22		OBJECT-TYPE
			SYNTAX	INTEGER
			ACCESS	read-only
			STATUS	current
	DESCRIPTION ""
			::= { mbus05 74 }

mbus05Value22		OBJECT-TYPE
			SYNTAX	INTEGER
			ACCESS	read-only
			STATUS	current
	DESCRIPTION ""
			::= { mbus05 75 }

mbus05VIF23		OBJECT-TYPE
			SYNTAX	INTEGER
			ACCESS	read-only
			STATUS	current
	DESCRIPTION ""
			::= { mbus05 76 }

mbus05Value23		OBJECT-TYPE
			SYNTAX	INTEGER
			ACCESS	read-only
			STATUS	current
	DESCRIPTION ""
			::= { mbus05 77 }

mbus05VIF24		OBJECT-TYPE
			SYNTAX	INTEGER
			ACCESS	read-only
			STATUS	current
	DESCRIPTION ""
			::= { mbus05 78 }

mbus05Value24		OBJECT-TYPE
			SYNTAX	INTEGER
			ACCESS	read-only
			STATUS	current
	DESCRIPTION ""
			::= { mbus05 79 }

mbus05VIF25		OBJECT-TYPE
			SYNTAX	INTEGER
			ACCESS	read-only
			STATUS	current
	DESCRIPTION ""
			::= { mbus05 80 }

mbus05Value25		OBJECT-TYPE
			SYNTAX	INTEGER
			ACCESS	read-only
			STATUS	current
	DESCRIPTION ""
			::= { mbus05 81 }

mbus05VIF26		OBJECT-TYPE
			SYNTAX	INTEGER
			ACCESS	read-only
			STATUS	current
	DESCRIPTION ""
			::= { mbus05 82 }

mbus05Value26		OBJECT-TYPE
			SYNTAX	INTEGER
			ACCESS	read-only
			STATUS	current
	DESCRIPTION ""
			::= { mbus05 83 }

mbus05VIF27		OBJECT-TYPE
			SYNTAX	INTEGER
			ACCESS	read-only
			STATUS	current
	DESCRIPTION ""
			::= { mbus05 84 }

mbus05Value27		OBJECT-TYPE
			SYNTAX	INTEGER
			ACCESS	read-only
			STATUS	current
	DESCRIPTION ""
			::= { mbus05 85 }

mbus05VIF28		OBJECT-TYPE
			SYNTAX	INTEGER
			ACCESS	read-only
			STATUS	current
	DESCRIPTION ""
			::= { mbus05 86 }

mbus05Value28		OBJECT-TYPE
			SYNTAX	INTEGER
			ACCESS	read-only
			STATUS	current
	DESCRIPTION ""
			::= { mbus05 87 }

mbus05VIF29		OBJECT-TYPE
			SYNTAX	INTEGER
			ACCESS	read-only
			STATUS	current
	DESCRIPTION ""
			::= { mbus05 88 }

mbus05Value29		OBJECT-TYPE
			SYNTAX	INTEGER
			ACCESS	read-only
			STATUS	current
	DESCRIPTION ""
			::= { mbus05 89 }

mbus05VIF2A		OBJECT-TYPE
			SYNTAX	INTEGER
			ACCESS	read-only
			STATUS	current
	DESCRIPTION ""
			::= { mbus05 90 }

mbus05Value2A		OBJECT-TYPE
			SYNTAX	INTEGER
			ACCESS	read-only
			STATUS	current
	DESCRIPTION ""
			::= { mbus05 91 }

mbus05VIF2B		OBJECT-TYPE
			SYNTAX	INTEGER
			ACCESS	read-only
			STATUS	current
	DESCRIPTION ""
			::= { mbus05 92 }

mbus05Value2B		OBJECT-TYPE
			SYNTAX	INTEGER
			ACCESS	read-only
			STATUS	current
	DESCRIPTION ""
			::= { mbus05 93 }

mbus05VIF2C		OBJECT-TYPE
			SYNTAX	INTEGER
			ACCESS	read-only
			STATUS	current
	DESCRIPTION ""
			::= { mbus05 94 }

mbus05Value2C		OBJECT-TYPE
			SYNTAX	INTEGER
			ACCESS	read-only
			STATUS	current
	DESCRIPTION ""
			::= { mbus05 95 }

mbus05VIF2D		OBJECT-TYPE
			SYNTAX	INTEGER
			ACCESS	read-only
			STATUS	current
	DESCRIPTION ""
			::= { mbus05 96 }

mbus05Value2D		OBJECT-TYPE
			SYNTAX	INTEGER
			ACCESS	read-only
			STATUS	current
	DESCRIPTION ""
			::= { mbus05 97 }

mbus05VIF2E		OBJECT-TYPE
			SYNTAX	INTEGER
			ACCESS	read-only
			STATUS	current
	DESCRIPTION ""
			::= { mbus05 98 }

mbus05Value2E		OBJECT-TYPE
			SYNTAX	INTEGER
			ACCESS	read-only
			STATUS	current
	DESCRIPTION ""
			::= { mbus05 99 }

mbus05VIF2F		OBJECT-TYPE
			SYNTAX	INTEGER
			ACCESS	read-only
			STATUS	current
	DESCRIPTION ""
			::= { mbus05 100 }

mbus05Value2F		OBJECT-TYPE
			SYNTAX	INTEGER
			ACCESS	read-only
			STATUS	current
	DESCRIPTION ""
			::= { mbus05 101 }

mbus06			OBJECT IDENTIFIER ::= { mbus 6 }

mbus06IdNumber		OBJECT-TYPE
			SYNTAX	Gauge
			ACCESS	read-only
			STATUS	current
	DESCRIPTION ""
			::= { mbus06 1 }

mbus06Manufacturer	OBJECT-TYPE
			SYNTAX	Gauge
			ACCESS	read-only
			STATUS	current
	DESCRIPTION ""
			::= { mbus06 2 }

mbus06Version		OBJECT-TYPE
			SYNTAX	Gauge
			ACCESS	read-only
			STATUS	current
	DESCRIPTION ""
			::= { mbus06 3 }

mbus06Medium		OBJECT-TYPE
			SYNTAX	Gauge
			ACCESS	read-only
			STATUS	current
	DESCRIPTION ""
			::= { mbus06 4 }

mbus06Status		OBJECT-TYPE
			SYNTAX	Gauge
			ACCESS	read-only
			STATUS	current
	DESCRIPTION ""
			::= { mbus06 5 }

mbus06VIF00		OBJECT-TYPE
			SYNTAX	INTEGER
			ACCESS	read-only
			STATUS	current
	DESCRIPTION ""
			::= { mbus06 6 }

mbus06Value00		OBJECT-TYPE
			SYNTAX	INTEGER
			ACCESS	read-only
			STATUS	current
	DESCRIPTION ""
			::= { mbus06 7 }

mbus06VIF01		OBJECT-TYPE
			SYNTAX	INTEGER
			ACCESS	read-only
			STATUS	current
	DESCRIPTION ""
			::= { mbus06 8 }

mbus06Value01		OBJECT-TYPE
			SYNTAX	INTEGER
			ACCESS	read-only
			STATUS	current
	DESCRIPTION ""
			::= { mbus06 9 }

mbus06VIF02		OBJECT-TYPE
			SYNTAX	INTEGER
			ACCESS	read-only
			STATUS	current
	DESCRIPTION ""
			::= { mbus06 10 }

mbus06Value02		OBJECT-TYPE
			SYNTAX	INTEGER
			ACCESS	read-only
			STATUS	current
	DESCRIPTION ""
			::= { mbus06 11 }

mbus06VIF03		OBJECT-TYPE
			SYNTAX	INTEGER
			ACCESS	read-only
			STATUS	current
	DESCRIPTION ""
			::= { mbus06 12 }

mbus06Value03		OBJECT-TYPE
			SYNTAX	INTEGER
			ACCESS	read-only
			STATUS	current
	DESCRIPTION ""
			::= { mbus06 13 }

mbus06VIF04		OBJECT-TYPE
			SYNTAX	INTEGER
			ACCESS	read-only
			STATUS	current
	DESCRIPTION ""
			::= { mbus06 14 }

mbus06Value04		OBJECT-TYPE
			SYNTAX	INTEGER
			ACCESS	read-only
			STATUS	current
	DESCRIPTION ""
			::= { mbus06 15 }

mbus06VIF05		OBJECT-TYPE
			SYNTAX	INTEGER
			ACCESS	read-only
			STATUS	current
	DESCRIPTION ""
			::= { mbus06 16 }

mbus06Value05		OBJECT-TYPE
			SYNTAX	INTEGER
			ACCESS	read-only
			STATUS	current
	DESCRIPTION ""
			::= { mbus06 17 }

mbus06VIF06		OBJECT-TYPE
			SYNTAX	INTEGER
			ACCESS	read-only
			STATUS	current
	DESCRIPTION ""
			::= { mbus06 18 }

mbus06Value06		OBJECT-TYPE
			SYNTAX	INTEGER
			ACCESS	read-only
			STATUS	current
	DESCRIPTION ""
			::= { mbus06 19 }

mbus06VIF07		OBJECT-TYPE
			SYNTAX	INTEGER
			ACCESS	read-only
			STATUS	current
	DESCRIPTION ""
			::= { mbus06 20 }

mbus06Value07		OBJECT-TYPE
			SYNTAX	INTEGER
			ACCESS	read-only
			STATUS	current
	DESCRIPTION ""
			::= { mbus06 21 }

mbus06VIF08		OBJECT-TYPE
			SYNTAX	INTEGER
			ACCESS	read-only
			STATUS	current
	DESCRIPTION ""
			::= { mbus06 22 }

mbus06Value08		OBJECT-TYPE
			SYNTAX	INTEGER
			ACCESS	read-only
			STATUS	current
	DESCRIPTION ""
			::= { mbus06 23 }

mbus06VIF09		OBJECT-TYPE
			SYNTAX	INTEGER
			ACCESS	read-only
			STATUS	current
	DESCRIPTION ""
			::= { mbus06 24 }

mbus06Value09		OBJECT-TYPE
			SYNTAX	INTEGER
			ACCESS	read-only
			STATUS	current
	DESCRIPTION ""
			::= { mbus06 25 }

mbus06VIF0A		OBJECT-TYPE
			SYNTAX	INTEGER
			ACCESS	read-only
			STATUS	current
	DESCRIPTION ""
			::= { mbus06 26 }

mbus06Value0A		OBJECT-TYPE
			SYNTAX	INTEGER
			ACCESS	read-only
			STATUS	current
	DESCRIPTION ""
			::= { mbus06 27 }

mbus06VIF0B		OBJECT-TYPE
			SYNTAX	INTEGER
			ACCESS	read-only
			STATUS	current
	DESCRIPTION ""
			::= { mbus06 28 }

mbus06Value0B		OBJECT-TYPE
			SYNTAX	INTEGER
			ACCESS	read-only
			STATUS	current
	DESCRIPTION ""
			::= { mbus06 29 }

mbus06VIF0C		OBJECT-TYPE
			SYNTAX	INTEGER
			ACCESS	read-only
			STATUS	current
	DESCRIPTION ""
			::= { mbus06 30 }

mbus06Value0C		OBJECT-TYPE
			SYNTAX	INTEGER
			ACCESS	read-only
			STATUS	current
	DESCRIPTION ""
			::= { mbus06 31 }

mbus06VIF0D		OBJECT-TYPE
			SYNTAX	INTEGER
			ACCESS	read-only
			STATUS	current
	DESCRIPTION ""
			::= { mbus06 32 }

mbus06Value0D		OBJECT-TYPE
			SYNTAX	INTEGER
			ACCESS	read-only
			STATUS	current
	DESCRIPTION ""
			::= { mbus06 33 }

mbus06VIF0E		OBJECT-TYPE
			SYNTAX	INTEGER
			ACCESS	read-only
			STATUS	current
	DESCRIPTION ""
			::= { mbus06 34 }

mbus06Value0E		OBJECT-TYPE
			SYNTAX	INTEGER
			ACCESS	read-only
			STATUS	current
	DESCRIPTION ""
			::= { mbus06 35 }

mbus06VIF0F		OBJECT-TYPE
			SYNTAX	INTEGER
			ACCESS	read-only
			STATUS	current
	DESCRIPTION ""
			::= { mbus06 36 }

mbus06Value0F		OBJECT-TYPE
			SYNTAX	INTEGER
			ACCESS	read-only
			STATUS	current
	DESCRIPTION ""
			::= { mbus06 37 }

mbus06VIF10		OBJECT-TYPE
			SYNTAX	INTEGER
			ACCESS	read-only
			STATUS	current
	DESCRIPTION ""
			::= { mbus06 38 }

mbus06Value10		OBJECT-TYPE
			SYNTAX	INTEGER
			ACCESS	read-only
			STATUS	current
	DESCRIPTION ""
			::= { mbus06 39 }

mbus06VIF11		OBJECT-TYPE
			SYNTAX	INTEGER
			ACCESS	read-only
			STATUS	current
	DESCRIPTION ""
			::= { mbus06 40 }

mbus06Value11		OBJECT-TYPE
			SYNTAX	INTEGER
			ACCESS	read-only
			STATUS	current
	DESCRIPTION ""
			::= { mbus06 41 }

mbus06VIF12		OBJECT-TYPE
			SYNTAX	INTEGER
			ACCESS	read-only
			STATUS	current
	DESCRIPTION ""
			::= { mbus06 42 }

mbus06Value12		OBJECT-TYPE
			SYNTAX	INTEGER
			ACCESS	read-only
			STATUS	current
	DESCRIPTION ""
			::= { mbus06 43 }

mbus06VIF13		OBJECT-TYPE
			SYNTAX	INTEGER
			ACCESS	read-only
			STATUS	current
	DESCRIPTION ""
			::= { mbus06 44 }

mbus06Value13		OBJECT-TYPE
			SYNTAX	INTEGER
			ACCESS	read-only
			STATUS	current
	DESCRIPTION ""
			::= { mbus06 45 }

mbus06VIF14		OBJECT-TYPE
			SYNTAX	INTEGER
			ACCESS	read-only
			STATUS	current
	DESCRIPTION ""
			::= { mbus06 46 }

mbus06Value14		OBJECT-TYPE
			SYNTAX	INTEGER
			ACCESS	read-only
			STATUS	current
	DESCRIPTION ""
			::= { mbus06 47 }

mbus06VIF15		OBJECT-TYPE
			SYNTAX	INTEGER
			ACCESS	read-only
			STATUS	current
	DESCRIPTION ""
			::= { mbus06 48 }

mbus06Value15		OBJECT-TYPE
			SYNTAX	INTEGER
			ACCESS	read-only
			STATUS	current
	DESCRIPTION ""
			::= { mbus06 49 }

mbus06VIF16		OBJECT-TYPE
			SYNTAX	INTEGER
			ACCESS	read-only
			STATUS	current
	DESCRIPTION ""
			::= { mbus06 50 }

mbus06Value16		OBJECT-TYPE
			SYNTAX	INTEGER
			ACCESS	read-only
			STATUS	current
	DESCRIPTION ""
			::= { mbus06 51 }

mbus06VIF17		OBJECT-TYPE
			SYNTAX	INTEGER
			ACCESS	read-only
			STATUS	current
	DESCRIPTION ""
			::= { mbus06 52 }

mbus06Value17		OBJECT-TYPE
			SYNTAX	INTEGER
			ACCESS	read-only
			STATUS	current
	DESCRIPTION ""
			::= { mbus06 53 }

mbus06VIF18		OBJECT-TYPE
			SYNTAX	INTEGER
			ACCESS	read-only
			STATUS	current
	DESCRIPTION ""
			::= { mbus06 54 }

mbus06Value18		OBJECT-TYPE
			SYNTAX	INTEGER
			ACCESS	read-only
			STATUS	current
	DESCRIPTION ""
			::= { mbus06 55 }

mbus06VIF19		OBJECT-TYPE
			SYNTAX	INTEGER
			ACCESS	read-only
			STATUS	current
	DESCRIPTION ""
			::= { mbus06 56 }

mbus06Value19		OBJECT-TYPE
			SYNTAX	INTEGER
			ACCESS	read-only
			STATUS	current
	DESCRIPTION ""
			::= { mbus06 57 }

mbus06VIF1A		OBJECT-TYPE
			SYNTAX	INTEGER
			ACCESS	read-only
			STATUS	current
	DESCRIPTION ""
			::= { mbus06 58 }

mbus06Value1A		OBJECT-TYPE
			SYNTAX	INTEGER
			ACCESS	read-only
			STATUS	current
	DESCRIPTION ""
			::= { mbus06 59 }

mbus06VIF1B		OBJECT-TYPE
			SYNTAX	INTEGER
			ACCESS	read-only
			STATUS	current
	DESCRIPTION ""
			::= { mbus06 60 }

mbus06Value1B		OBJECT-TYPE
			SYNTAX	INTEGER
			ACCESS	read-only
			STATUS	current
	DESCRIPTION ""
			::= { mbus06 61 }

mbus06VIF1C		OBJECT-TYPE
			SYNTAX	INTEGER
			ACCESS	read-only
			STATUS	current
	DESCRIPTION ""
			::= { mbus06 62 }

mbus06Value1C		OBJECT-TYPE
			SYNTAX	INTEGER
			ACCESS	read-only
			STATUS	current
	DESCRIPTION ""
			::= { mbus06 63 }

mbus06VIF1D		OBJECT-TYPE
			SYNTAX	INTEGER
			ACCESS	read-only
			STATUS	current
	DESCRIPTION ""
			::= { mbus06 64 }

mbus06Value1D		OBJECT-TYPE
			SYNTAX	INTEGER
			ACCESS	read-only
			STATUS	current
	DESCRIPTION ""
			::= { mbus06 65 }

mbus06VIF1E		OBJECT-TYPE
			SYNTAX	INTEGER
			ACCESS	read-only
			STATUS	current
	DESCRIPTION ""
			::= { mbus06 66 }

mbus06Value1E		OBJECT-TYPE
			SYNTAX	INTEGER
			ACCESS	read-only
			STATUS	current
	DESCRIPTION ""
			::= { mbus06 67 }

mbus06VIF1F		OBJECT-TYPE
			SYNTAX	INTEGER
			ACCESS	read-only
			STATUS	current
	DESCRIPTION ""
			::= { mbus06 68 }

mbus06Value1F		OBJECT-TYPE
			SYNTAX	INTEGER
			ACCESS	read-only
			STATUS	current
	DESCRIPTION ""
			::= { mbus06 69 }

mbus06VIF20		OBJECT-TYPE
			SYNTAX	INTEGER
			ACCESS	read-only
			STATUS	current
	DESCRIPTION ""
			::= { mbus06 70 }

mbus06Value20		OBJECT-TYPE
			SYNTAX	INTEGER
			ACCESS	read-only
			STATUS	current
	DESCRIPTION ""
			::= { mbus06 71 }

mbus06VIF21		OBJECT-TYPE
			SYNTAX	INTEGER
			ACCESS	read-only
			STATUS	current
	DESCRIPTION ""
			::= { mbus06 72 }

mbus06Value21		OBJECT-TYPE
			SYNTAX	INTEGER
			ACCESS	read-only
			STATUS	current
	DESCRIPTION ""
			::= { mbus06 73 }

mbus06VIF22		OBJECT-TYPE
			SYNTAX	INTEGER
			ACCESS	read-only
			STATUS	current
	DESCRIPTION ""
			::= { mbus06 74 }

mbus06Value22		OBJECT-TYPE
			SYNTAX	INTEGER
			ACCESS	read-only
			STATUS	current
	DESCRIPTION ""
			::= { mbus06 75 }

mbus06VIF23		OBJECT-TYPE
			SYNTAX	INTEGER
			ACCESS	read-only
			STATUS	current
	DESCRIPTION ""
			::= { mbus06 76 }

mbus06Value23		OBJECT-TYPE
			SYNTAX	INTEGER
			ACCESS	read-only
			STATUS	current
	DESCRIPTION ""
			::= { mbus06 77 }

mbus06VIF24		OBJECT-TYPE
			SYNTAX	INTEGER
			ACCESS	read-only
			STATUS	current
	DESCRIPTION ""
			::= { mbus06 78 }

mbus06Value24		OBJECT-TYPE
			SYNTAX	INTEGER
			ACCESS	read-only
			STATUS	current
	DESCRIPTION ""
			::= { mbus06 79 }

mbus06VIF25		OBJECT-TYPE
			SYNTAX	INTEGER
			ACCESS	read-only
			STATUS	current
	DESCRIPTION ""
			::= { mbus06 80 }

mbus06Value25		OBJECT-TYPE
			SYNTAX	INTEGER
			ACCESS	read-only
			STATUS	current
	DESCRIPTION ""
			::= { mbus06 81 }

mbus06VIF26		OBJECT-TYPE
			SYNTAX	INTEGER
			ACCESS	read-only
			STATUS	current
	DESCRIPTION ""
			::= { mbus06 82 }

mbus06Value26		OBJECT-TYPE
			SYNTAX	INTEGER
			ACCESS	read-only
			STATUS	current
	DESCRIPTION ""
			::= { mbus06 83 }

mbus06VIF27		OBJECT-TYPE
			SYNTAX	INTEGER
			ACCESS	read-only
			STATUS	current
	DESCRIPTION ""
			::= { mbus06 84 }

mbus06Value27		OBJECT-TYPE
			SYNTAX	INTEGER
			ACCESS	read-only
			STATUS	current
	DESCRIPTION ""
			::= { mbus06 85 }

mbus06VIF28		OBJECT-TYPE
			SYNTAX	INTEGER
			ACCESS	read-only
			STATUS	current
	DESCRIPTION ""
			::= { mbus06 86 }

mbus06Value28		OBJECT-TYPE
			SYNTAX	INTEGER
			ACCESS	read-only
			STATUS	current
	DESCRIPTION ""
			::= { mbus06 87 }

mbus06VIF29		OBJECT-TYPE
			SYNTAX	INTEGER
			ACCESS	read-only
			STATUS	current
	DESCRIPTION ""
			::= { mbus06 88 }

mbus06Value29		OBJECT-TYPE
			SYNTAX	INTEGER
			ACCESS	read-only
			STATUS	current
	DESCRIPTION ""
			::= { mbus06 89 }

mbus06VIF2A		OBJECT-TYPE
			SYNTAX	INTEGER
			ACCESS	read-only
			STATUS	current
	DESCRIPTION ""
			::= { mbus06 90 }

mbus06Value2A		OBJECT-TYPE
			SYNTAX	INTEGER
			ACCESS	read-only
			STATUS	current
	DESCRIPTION ""
			::= { mbus06 91 }

mbus06VIF2B		OBJECT-TYPE
			SYNTAX	INTEGER
			ACCESS	read-only
			STATUS	current
	DESCRIPTION ""
			::= { mbus06 92 }

mbus06Value2B		OBJECT-TYPE
			SYNTAX	INTEGER
			ACCESS	read-only
			STATUS	current
	DESCRIPTION ""
			::= { mbus06 93 }

mbus06VIF2C		OBJECT-TYPE
			SYNTAX	INTEGER
			ACCESS	read-only
			STATUS	current
	DESCRIPTION ""
			::= { mbus06 94 }

mbus06Value2C		OBJECT-TYPE
			SYNTAX	INTEGER
			ACCESS	read-only
			STATUS	current
	DESCRIPTION ""
			::= { mbus06 95 }

mbus06VIF2D		OBJECT-TYPE
			SYNTAX	INTEGER
			ACCESS	read-only
			STATUS	current
	DESCRIPTION ""
			::= { mbus06 96 }

mbus06Value2D		OBJECT-TYPE
			SYNTAX	INTEGER
			ACCESS	read-only
			STATUS	current
	DESCRIPTION ""
			::= { mbus06 97 }

mbus06VIF2E		OBJECT-TYPE
			SYNTAX	INTEGER
			ACCESS	read-only
			STATUS	current
	DESCRIPTION ""
			::= { mbus06 98 }

mbus06Value2E		OBJECT-TYPE
			SYNTAX	INTEGER
			ACCESS	read-only
			STATUS	current
	DESCRIPTION ""
			::= { mbus06 99 }

mbus06VIF2F		OBJECT-TYPE
			SYNTAX	INTEGER
			ACCESS	read-only
			STATUS	current
	DESCRIPTION ""
			::= { mbus06 100 }

mbus06Value2F		OBJECT-TYPE
			SYNTAX	INTEGER
			ACCESS	read-only
			STATUS	current
	DESCRIPTION ""
			::= { mbus06 101 }

mbus07			OBJECT IDENTIFIER ::= { mbus 7 }

mbus07IdNumber		OBJECT-TYPE
			SYNTAX	Gauge
			ACCESS	read-only
			STATUS	current
	DESCRIPTION ""
			::= { mbus07 1 }

mbus07Manufacturer	OBJECT-TYPE
			SYNTAX	Gauge
			ACCESS	read-only
			STATUS	current
	DESCRIPTION ""
			::= { mbus07 2 }

mbus07Version		OBJECT-TYPE
			SYNTAX	Gauge
			ACCESS	read-only
			STATUS	current
	DESCRIPTION ""
			::= { mbus07 3 }

mbus07Medium		OBJECT-TYPE
			SYNTAX	Gauge
			ACCESS	read-only
			STATUS	current
	DESCRIPTION ""
			::= { mbus07 4 }

mbus07Status		OBJECT-TYPE
			SYNTAX	Gauge
			ACCESS	read-only
			STATUS	current
	DESCRIPTION ""
			::= { mbus07 5 }

mbus07VIF00		OBJECT-TYPE
			SYNTAX	INTEGER
			ACCESS	read-only
			STATUS	current
	DESCRIPTION ""
			::= { mbus07 6 }

mbus07Value00		OBJECT-TYPE
			SYNTAX	INTEGER
			ACCESS	read-only
			STATUS	current
	DESCRIPTION ""
			::= { mbus07 7 }

mbus07VIF01		OBJECT-TYPE
			SYNTAX	INTEGER
			ACCESS	read-only
			STATUS	current
	DESCRIPTION ""
			::= { mbus07 8 }

mbus07Value01		OBJECT-TYPE
			SYNTAX	INTEGER
			ACCESS	read-only
			STATUS	current
	DESCRIPTION ""
			::= { mbus07 9 }

mbus07VIF02		OBJECT-TYPE
			SYNTAX	INTEGER
			ACCESS	read-only
			STATUS	current
	DESCRIPTION ""
			::= { mbus07 10 }

mbus07Value02		OBJECT-TYPE
			SYNTAX	INTEGER
			ACCESS	read-only
			STATUS	current
	DESCRIPTION ""
			::= { mbus07 11 }

mbus07VIF03		OBJECT-TYPE
			SYNTAX	INTEGER
			ACCESS	read-only
			STATUS	current
	DESCRIPTION ""
			::= { mbus07 12 }

mbus07Value03		OBJECT-TYPE
			SYNTAX	INTEGER
			ACCESS	read-only
			STATUS	current
	DESCRIPTION ""
			::= { mbus07 13 }

mbus07VIF04		OBJECT-TYPE
			SYNTAX	INTEGER
			ACCESS	read-only
			STATUS	current
	DESCRIPTION ""
			::= { mbus07 14 }

mbus07Value04		OBJECT-TYPE
			SYNTAX	INTEGER
			ACCESS	read-only
			STATUS	current
	DESCRIPTION ""
			::= { mbus07 15 }

mbus07VIF05		OBJECT-TYPE
			SYNTAX	INTEGER
			ACCESS	read-only
			STATUS	current
	DESCRIPTION ""
			::= { mbus07 16 }

mbus07Value05		OBJECT-TYPE
			SYNTAX	INTEGER
			ACCESS	read-only
			STATUS	current
	DESCRIPTION ""
			::= { mbus07 17 }

mbus07VIF06		OBJECT-TYPE
			SYNTAX	INTEGER
			ACCESS	read-only
			STATUS	current
	DESCRIPTION ""
			::= { mbus07 18 }

mbus07Value06		OBJECT-TYPE
			SYNTAX	INTEGER
			ACCESS	read-only
			STATUS	current
	DESCRIPTION ""
			::= { mbus07 19 }

mbus07VIF07		OBJECT-TYPE
			SYNTAX	INTEGER
			ACCESS	read-only
			STATUS	current
	DESCRIPTION ""
			::= { mbus07 20 }

mbus07Value07		OBJECT-TYPE
			SYNTAX	INTEGER
			ACCESS	read-only
			STATUS	current
	DESCRIPTION ""
			::= { mbus07 21 }

mbus07VIF08		OBJECT-TYPE
			SYNTAX	INTEGER
			ACCESS	read-only
			STATUS	current
	DESCRIPTION ""
			::= { mbus07 22 }

mbus07Value08		OBJECT-TYPE
			SYNTAX	INTEGER
			ACCESS	read-only
			STATUS	current
	DESCRIPTION ""
			::= { mbus07 23 }

mbus07VIF09		OBJECT-TYPE
			SYNTAX	INTEGER
			ACCESS	read-only
			STATUS	current
	DESCRIPTION ""
			::= { mbus07 24 }

mbus07Value09		OBJECT-TYPE
			SYNTAX	INTEGER
			ACCESS	read-only
			STATUS	current
	DESCRIPTION ""
			::= { mbus07 25 }

mbus07VIF0A		OBJECT-TYPE
			SYNTAX	INTEGER
			ACCESS	read-only
			STATUS	current
	DESCRIPTION ""
			::= { mbus07 26 }

mbus07Value0A		OBJECT-TYPE
			SYNTAX	INTEGER
			ACCESS	read-only
			STATUS	current
	DESCRIPTION ""
			::= { mbus07 27 }

mbus07VIF0B		OBJECT-TYPE
			SYNTAX	INTEGER
			ACCESS	read-only
			STATUS	current
	DESCRIPTION ""
			::= { mbus07 28 }

mbus07Value0B		OBJECT-TYPE
			SYNTAX	INTEGER
			ACCESS	read-only
			STATUS	current
	DESCRIPTION ""
			::= { mbus07 29 }

mbus07VIF0C		OBJECT-TYPE
			SYNTAX	INTEGER
			ACCESS	read-only
			STATUS	current
	DESCRIPTION ""
			::= { mbus07 30 }

mbus07Value0C		OBJECT-TYPE
			SYNTAX	INTEGER
			ACCESS	read-only
			STATUS	current
	DESCRIPTION ""
			::= { mbus07 31 }

mbus07VIF0D		OBJECT-TYPE
			SYNTAX	INTEGER
			ACCESS	read-only
			STATUS	current
	DESCRIPTION ""
			::= { mbus07 32 }

mbus07Value0D		OBJECT-TYPE
			SYNTAX	INTEGER
			ACCESS	read-only
			STATUS	current
	DESCRIPTION ""
			::= { mbus07 33 }

mbus07VIF0E		OBJECT-TYPE
			SYNTAX	INTEGER
			ACCESS	read-only
			STATUS	current
	DESCRIPTION ""
			::= { mbus07 34 }

mbus07Value0E		OBJECT-TYPE
			SYNTAX	INTEGER
			ACCESS	read-only
			STATUS	current
	DESCRIPTION ""
			::= { mbus07 35 }

mbus07VIF0F		OBJECT-TYPE
			SYNTAX	INTEGER
			ACCESS	read-only
			STATUS	current
	DESCRIPTION ""
			::= { mbus07 36 }

mbus07Value0F		OBJECT-TYPE
			SYNTAX	INTEGER
			ACCESS	read-only
			STATUS	current
	DESCRIPTION ""
			::= { mbus07 37 }

mbus07VIF10		OBJECT-TYPE
			SYNTAX	INTEGER
			ACCESS	read-only
			STATUS	current
	DESCRIPTION ""
			::= { mbus07 38 }

mbus07Value10		OBJECT-TYPE
			SYNTAX	INTEGER
			ACCESS	read-only
			STATUS	current
	DESCRIPTION ""
			::= { mbus07 39 }

mbus07VIF11		OBJECT-TYPE
			SYNTAX	INTEGER
			ACCESS	read-only
			STATUS	current
	DESCRIPTION ""
			::= { mbus07 40 }

mbus07Value11		OBJECT-TYPE
			SYNTAX	INTEGER
			ACCESS	read-only
			STATUS	current
	DESCRIPTION ""
			::= { mbus07 41 }

mbus07VIF12		OBJECT-TYPE
			SYNTAX	INTEGER
			ACCESS	read-only
			STATUS	current
	DESCRIPTION ""
			::= { mbus07 42 }

mbus07Value12		OBJECT-TYPE
			SYNTAX	INTEGER
			ACCESS	read-only
			STATUS	current
	DESCRIPTION ""
			::= { mbus07 43 }

mbus07VIF13		OBJECT-TYPE
			SYNTAX	INTEGER
			ACCESS	read-only
			STATUS	current
	DESCRIPTION ""
			::= { mbus07 44 }

mbus07Value13		OBJECT-TYPE
			SYNTAX	INTEGER
			ACCESS	read-only
			STATUS	current
	DESCRIPTION ""
			::= { mbus07 45 }

mbus07VIF14		OBJECT-TYPE
			SYNTAX	INTEGER
			ACCESS	read-only
			STATUS	current
	DESCRIPTION ""
			::= { mbus07 46 }

mbus07Value14		OBJECT-TYPE
			SYNTAX	INTEGER
			ACCESS	read-only
			STATUS	current
	DESCRIPTION ""
			::= { mbus07 47 }

mbus07VIF15		OBJECT-TYPE
			SYNTAX	INTEGER
			ACCESS	read-only
			STATUS	current
	DESCRIPTION ""
			::= { mbus07 48 }

mbus07Value15		OBJECT-TYPE
			SYNTAX	INTEGER
			ACCESS	read-only
			STATUS	current
	DESCRIPTION ""
			::= { mbus07 49 }

mbus07VIF16		OBJECT-TYPE
			SYNTAX	INTEGER
			ACCESS	read-only
			STATUS	current
	DESCRIPTION ""
			::= { mbus07 50 }

mbus07Value16		OBJECT-TYPE
			SYNTAX	INTEGER
			ACCESS	read-only
			STATUS	current
	DESCRIPTION ""
			::= { mbus07 51 }

mbus07VIF17		OBJECT-TYPE
			SYNTAX	INTEGER
			ACCESS	read-only
			STATUS	current
	DESCRIPTION ""
			::= { mbus07 52 }

mbus07Value17		OBJECT-TYPE
			SYNTAX	INTEGER
			ACCESS	read-only
			STATUS	current
	DESCRIPTION ""
			::= { mbus07 53 }

mbus07VIF18		OBJECT-TYPE
			SYNTAX	INTEGER
			ACCESS	read-only
			STATUS	current
	DESCRIPTION ""
			::= { mbus07 54 }

mbus07Value18		OBJECT-TYPE
			SYNTAX	INTEGER
			ACCESS	read-only
			STATUS	current
	DESCRIPTION ""
			::= { mbus07 55 }

mbus07VIF19		OBJECT-TYPE
			SYNTAX	INTEGER
			ACCESS	read-only
			STATUS	current
	DESCRIPTION ""
			::= { mbus07 56 }

mbus07Value19		OBJECT-TYPE
			SYNTAX	INTEGER
			ACCESS	read-only
			STATUS	current
	DESCRIPTION ""
			::= { mbus07 57 }

mbus07VIF1A		OBJECT-TYPE
			SYNTAX	INTEGER
			ACCESS	read-only
			STATUS	current
	DESCRIPTION ""
			::= { mbus07 58 }

mbus07Value1A		OBJECT-TYPE
			SYNTAX	INTEGER
			ACCESS	read-only
			STATUS	current
	DESCRIPTION ""
			::= { mbus07 59 }

mbus07VIF1B		OBJECT-TYPE
			SYNTAX	INTEGER
			ACCESS	read-only
			STATUS	current
	DESCRIPTION ""
			::= { mbus07 60 }

mbus07Value1B		OBJECT-TYPE
			SYNTAX	INTEGER
			ACCESS	read-only
			STATUS	current
	DESCRIPTION ""
			::= { mbus07 61 }

mbus07VIF1C		OBJECT-TYPE
			SYNTAX	INTEGER
			ACCESS	read-only
			STATUS	current
	DESCRIPTION ""
			::= { mbus07 62 }

mbus07Value1C		OBJECT-TYPE
			SYNTAX	INTEGER
			ACCESS	read-only
			STATUS	current
	DESCRIPTION ""
			::= { mbus07 63 }

mbus07VIF1D		OBJECT-TYPE
			SYNTAX	INTEGER
			ACCESS	read-only
			STATUS	current
	DESCRIPTION ""
			::= { mbus07 64 }

mbus07Value1D		OBJECT-TYPE
			SYNTAX	INTEGER
			ACCESS	read-only
			STATUS	current
	DESCRIPTION ""
			::= { mbus07 65 }

mbus07VIF1E		OBJECT-TYPE
			SYNTAX	INTEGER
			ACCESS	read-only
			STATUS	current
	DESCRIPTION ""
			::= { mbus07 66 }

mbus07Value1E		OBJECT-TYPE
			SYNTAX	INTEGER
			ACCESS	read-only
			STATUS	current
	DESCRIPTION ""
			::= { mbus07 67 }

mbus07VIF1F		OBJECT-TYPE
			SYNTAX	INTEGER
			ACCESS	read-only
			STATUS	current
	DESCRIPTION ""
			::= { mbus07 68 }

mbus07Value1F		OBJECT-TYPE
			SYNTAX	INTEGER
			ACCESS	read-only
			STATUS	current
	DESCRIPTION ""
			::= { mbus07 69 }

mbus07VIF20		OBJECT-TYPE
			SYNTAX	INTEGER
			ACCESS	read-only
			STATUS	current
	DESCRIPTION ""
			::= { mbus07 70 }

mbus07Value20		OBJECT-TYPE
			SYNTAX	INTEGER
			ACCESS	read-only
			STATUS	current
	DESCRIPTION ""
			::= { mbus07 71 }

mbus07VIF21		OBJECT-TYPE
			SYNTAX	INTEGER
			ACCESS	read-only
			STATUS	current
	DESCRIPTION ""
			::= { mbus07 72 }

mbus07Value21		OBJECT-TYPE
			SYNTAX	INTEGER
			ACCESS	read-only
			STATUS	current
	DESCRIPTION ""
			::= { mbus07 73 }

mbus07VIF22		OBJECT-TYPE
			SYNTAX	INTEGER
			ACCESS	read-only
			STATUS	current
	DESCRIPTION ""
			::= { mbus07 74 }

mbus07Value22		OBJECT-TYPE
			SYNTAX	INTEGER
			ACCESS	read-only
			STATUS	current
	DESCRIPTION ""
			::= { mbus07 75 }

mbus07VIF23		OBJECT-TYPE
			SYNTAX	INTEGER
			ACCESS	read-only
			STATUS	current
	DESCRIPTION ""
			::= { mbus07 76 }

mbus07Value23		OBJECT-TYPE
			SYNTAX	INTEGER
			ACCESS	read-only
			STATUS	current
	DESCRIPTION ""
			::= { mbus07 77 }

mbus07VIF24		OBJECT-TYPE
			SYNTAX	INTEGER
			ACCESS	read-only
			STATUS	current
	DESCRIPTION ""
			::= { mbus07 78 }

mbus07Value24		OBJECT-TYPE
			SYNTAX	INTEGER
			ACCESS	read-only
			STATUS	current
	DESCRIPTION ""
			::= { mbus07 79 }

mbus07VIF25		OBJECT-TYPE
			SYNTAX	INTEGER
			ACCESS	read-only
			STATUS	current
	DESCRIPTION ""
			::= { mbus07 80 }

mbus07Value25		OBJECT-TYPE
			SYNTAX	INTEGER
			ACCESS	read-only
			STATUS	current
	DESCRIPTION ""
			::= { mbus07 81 }

mbus07VIF26		OBJECT-TYPE
			SYNTAX	INTEGER
			ACCESS	read-only
			STATUS	current
	DESCRIPTION ""
			::= { mbus07 82 }

mbus07Value26		OBJECT-TYPE
			SYNTAX	INTEGER
			ACCESS	read-only
			STATUS	current
	DESCRIPTION ""
			::= { mbus07 83 }

mbus07VIF27		OBJECT-TYPE
			SYNTAX	INTEGER
			ACCESS	read-only
			STATUS	current
	DESCRIPTION ""
			::= { mbus07 84 }

mbus07Value27		OBJECT-TYPE
			SYNTAX	INTEGER
			ACCESS	read-only
			STATUS	current
	DESCRIPTION ""
			::= { mbus07 85 }

mbus07VIF28		OBJECT-TYPE
			SYNTAX	INTEGER
			ACCESS	read-only
			STATUS	current
	DESCRIPTION ""
			::= { mbus07 86 }

mbus07Value28		OBJECT-TYPE
			SYNTAX	INTEGER
			ACCESS	read-only
			STATUS	current
	DESCRIPTION ""
			::= { mbus07 87 }

mbus07VIF29		OBJECT-TYPE
			SYNTAX	INTEGER
			ACCESS	read-only
			STATUS	current
	DESCRIPTION ""
			::= { mbus07 88 }

mbus07Value29		OBJECT-TYPE
			SYNTAX	INTEGER
			ACCESS	read-only
			STATUS	current
	DESCRIPTION ""
			::= { mbus07 89 }

mbus07VIF2A		OBJECT-TYPE
			SYNTAX	INTEGER
			ACCESS	read-only
			STATUS	current
	DESCRIPTION ""
			::= { mbus07 90 }

mbus07Value2A		OBJECT-TYPE
			SYNTAX	INTEGER
			ACCESS	read-only
			STATUS	current
	DESCRIPTION ""
			::= { mbus07 91 }

mbus07VIF2B		OBJECT-TYPE
			SYNTAX	INTEGER
			ACCESS	read-only
			STATUS	current
	DESCRIPTION ""
			::= { mbus07 92 }

mbus07Value2B		OBJECT-TYPE
			SYNTAX	INTEGER
			ACCESS	read-only
			STATUS	current
	DESCRIPTION ""
			::= { mbus07 93 }

mbus07VIF2C		OBJECT-TYPE
			SYNTAX	INTEGER
			ACCESS	read-only
			STATUS	current
	DESCRIPTION ""
			::= { mbus07 94 }

mbus07Value2C		OBJECT-TYPE
			SYNTAX	INTEGER
			ACCESS	read-only
			STATUS	current
	DESCRIPTION ""
			::= { mbus07 95 }

mbus07VIF2D		OBJECT-TYPE
			SYNTAX	INTEGER
			ACCESS	read-only
			STATUS	current
	DESCRIPTION ""
			::= { mbus07 96 }

mbus07Value2D		OBJECT-TYPE
			SYNTAX	INTEGER
			ACCESS	read-only
			STATUS	current
	DESCRIPTION ""
			::= { mbus07 97 }

mbus07VIF2E		OBJECT-TYPE
			SYNTAX	INTEGER
			ACCESS	read-only
			STATUS	current
	DESCRIPTION ""
			::= { mbus07 98 }

mbus07Value2E		OBJECT-TYPE
			SYNTAX	INTEGER
			ACCESS	read-only
			STATUS	current
	DESCRIPTION ""
			::= { mbus07 99 }

mbus07VIF2F		OBJECT-TYPE
			SYNTAX	INTEGER
			ACCESS	read-only
			STATUS	current
	DESCRIPTION ""
			::= { mbus07 100 }

mbus07Value2F		OBJECT-TYPE
			SYNTAX	INTEGER
			ACCESS	read-only
			STATUS	current
	DESCRIPTION ""
			::= { mbus07 101 }

mbus08			OBJECT IDENTIFIER ::= { mbus 8 }

mbus08IdNumber		OBJECT-TYPE
			SYNTAX	Gauge
			ACCESS	read-only
			STATUS	current
	DESCRIPTION ""
			::= { mbus08 1 }

mbus08Manufacturer	OBJECT-TYPE
			SYNTAX	Gauge
			ACCESS	read-only
			STATUS	current
	DESCRIPTION ""
			::= { mbus08 2 }

mbus08Version		OBJECT-TYPE
			SYNTAX	Gauge
			ACCESS	read-only
			STATUS	current
	DESCRIPTION ""
			::= { mbus08 3 }

mbus08Medium		OBJECT-TYPE
			SYNTAX	Gauge
			ACCESS	read-only
			STATUS	current
	DESCRIPTION ""
			::= { mbus08 4 }

mbus08Status		OBJECT-TYPE
			SYNTAX	Gauge
			ACCESS	read-only
			STATUS	current
	DESCRIPTION ""
			::= { mbus08 5 }

mbus08VIF00		OBJECT-TYPE
			SYNTAX	INTEGER
			ACCESS	read-only
			STATUS	current
	DESCRIPTION ""
			::= { mbus08 6 }

mbus08Value00		OBJECT-TYPE
			SYNTAX	INTEGER
			ACCESS	read-only
			STATUS	current
	DESCRIPTION ""
			::= { mbus08 7 }

mbus08VIF01		OBJECT-TYPE
			SYNTAX	INTEGER
			ACCESS	read-only
			STATUS	current
	DESCRIPTION ""
			::= { mbus08 8 }

mbus08Value01		OBJECT-TYPE
			SYNTAX	INTEGER
			ACCESS	read-only
			STATUS	current
	DESCRIPTION ""
			::= { mbus08 9 }

mbus08VIF02		OBJECT-TYPE
			SYNTAX	INTEGER
			ACCESS	read-only
			STATUS	current
	DESCRIPTION ""
			::= { mbus08 10 }

mbus08Value02		OBJECT-TYPE
			SYNTAX	INTEGER
			ACCESS	read-only
			STATUS	current
	DESCRIPTION ""
			::= { mbus08 11 }

mbus08VIF03		OBJECT-TYPE
			SYNTAX	INTEGER
			ACCESS	read-only
			STATUS	current
	DESCRIPTION ""
			::= { mbus08 12 }

mbus08Value03		OBJECT-TYPE
			SYNTAX	INTEGER
			ACCESS	read-only
			STATUS	current
	DESCRIPTION ""
			::= { mbus08 13 }

mbus08VIF04		OBJECT-TYPE
			SYNTAX	INTEGER
			ACCESS	read-only
			STATUS	current
	DESCRIPTION ""
			::= { mbus08 14 }

mbus08Value04		OBJECT-TYPE
			SYNTAX	INTEGER
			ACCESS	read-only
			STATUS	current
	DESCRIPTION ""
			::= { mbus08 15 }

mbus08VIF05		OBJECT-TYPE
			SYNTAX	INTEGER
			ACCESS	read-only
			STATUS	current
	DESCRIPTION ""
			::= { mbus08 16 }

mbus08Value05		OBJECT-TYPE
			SYNTAX	INTEGER
			ACCESS	read-only
			STATUS	current
	DESCRIPTION ""
			::= { mbus08 17 }

mbus08VIF06		OBJECT-TYPE
			SYNTAX	INTEGER
			ACCESS	read-only
			STATUS	current
	DESCRIPTION ""
			::= { mbus08 18 }

mbus08Value06		OBJECT-TYPE
			SYNTAX	INTEGER
			ACCESS	read-only
			STATUS	current
	DESCRIPTION ""
			::= { mbus08 19 }

mbus08VIF07		OBJECT-TYPE
			SYNTAX	INTEGER
			ACCESS	read-only
			STATUS	current
	DESCRIPTION ""
			::= { mbus08 20 }

mbus08Value07		OBJECT-TYPE
			SYNTAX	INTEGER
			ACCESS	read-only
			STATUS	current
	DESCRIPTION ""
			::= { mbus08 21 }

mbus08VIF08		OBJECT-TYPE
			SYNTAX	INTEGER
			ACCESS	read-only
			STATUS	current
	DESCRIPTION ""
			::= { mbus08 22 }

mbus08Value08		OBJECT-TYPE
			SYNTAX	INTEGER
			ACCESS	read-only
			STATUS	current
	DESCRIPTION ""
			::= { mbus08 23 }

mbus08VIF09		OBJECT-TYPE
			SYNTAX	INTEGER
			ACCESS	read-only
			STATUS	current
	DESCRIPTION ""
			::= { mbus08 24 }

mbus08Value09		OBJECT-TYPE
			SYNTAX	INTEGER
			ACCESS	read-only
			STATUS	current
	DESCRIPTION ""
			::= { mbus08 25 }

mbus08VIF0A		OBJECT-TYPE
			SYNTAX	INTEGER
			ACCESS	read-only
			STATUS	current
	DESCRIPTION ""
			::= { mbus08 26 }

mbus08Value0A		OBJECT-TYPE
			SYNTAX	INTEGER
			ACCESS	read-only
			STATUS	current
	DESCRIPTION ""
			::= { mbus08 27 }

mbus08VIF0B		OBJECT-TYPE
			SYNTAX	INTEGER
			ACCESS	read-only
			STATUS	current
	DESCRIPTION ""
			::= { mbus08 28 }

mbus08Value0B		OBJECT-TYPE
			SYNTAX	INTEGER
			ACCESS	read-only
			STATUS	current
	DESCRIPTION ""
			::= { mbus08 29 }

mbus08VIF0C		OBJECT-TYPE
			SYNTAX	INTEGER
			ACCESS	read-only
			STATUS	current
	DESCRIPTION ""
			::= { mbus08 30 }

mbus08Value0C		OBJECT-TYPE
			SYNTAX	INTEGER
			ACCESS	read-only
			STATUS	current
	DESCRIPTION ""
			::= { mbus08 31 }

mbus08VIF0D		OBJECT-TYPE
			SYNTAX	INTEGER
			ACCESS	read-only
			STATUS	current
	DESCRIPTION ""
			::= { mbus08 32 }

mbus08Value0D		OBJECT-TYPE
			SYNTAX	INTEGER
			ACCESS	read-only
			STATUS	current
	DESCRIPTION ""
			::= { mbus08 33 }

mbus08VIF0E		OBJECT-TYPE
			SYNTAX	INTEGER
			ACCESS	read-only
			STATUS	current
	DESCRIPTION ""
			::= { mbus08 34 }

mbus08Value0E		OBJECT-TYPE
			SYNTAX	INTEGER
			ACCESS	read-only
			STATUS	current
	DESCRIPTION ""
			::= { mbus08 35 }

mbus08VIF0F		OBJECT-TYPE
			SYNTAX	INTEGER
			ACCESS	read-only
			STATUS	current
	DESCRIPTION ""
			::= { mbus08 36 }

mbus08Value0F		OBJECT-TYPE
			SYNTAX	INTEGER
			ACCESS	read-only
			STATUS	current
	DESCRIPTION ""
			::= { mbus08 37 }

mbus08VIF10		OBJECT-TYPE
			SYNTAX	INTEGER
			ACCESS	read-only
			STATUS	current
	DESCRIPTION ""
			::= { mbus08 38 }

mbus08Value10		OBJECT-TYPE
			SYNTAX	INTEGER
			ACCESS	read-only
			STATUS	current
	DESCRIPTION ""
			::= { mbus08 39 }

mbus08VIF11		OBJECT-TYPE
			SYNTAX	INTEGER
			ACCESS	read-only
			STATUS	current
	DESCRIPTION ""
			::= { mbus08 40 }

mbus08Value11		OBJECT-TYPE
			SYNTAX	INTEGER
			ACCESS	read-only
			STATUS	current
	DESCRIPTION ""
			::= { mbus08 41 }

mbus08VIF12		OBJECT-TYPE
			SYNTAX	INTEGER
			ACCESS	read-only
			STATUS	current
	DESCRIPTION ""
			::= { mbus08 42 }

mbus08Value12		OBJECT-TYPE
			SYNTAX	INTEGER
			ACCESS	read-only
			STATUS	current
	DESCRIPTION ""
			::= { mbus08 43 }

mbus08VIF13		OBJECT-TYPE
			SYNTAX	INTEGER
			ACCESS	read-only
			STATUS	current
	DESCRIPTION ""
			::= { mbus08 44 }

mbus08Value13		OBJECT-TYPE
			SYNTAX	INTEGER
			ACCESS	read-only
			STATUS	current
	DESCRIPTION ""
			::= { mbus08 45 }

mbus08VIF14		OBJECT-TYPE
			SYNTAX	INTEGER
			ACCESS	read-only
			STATUS	current
	DESCRIPTION ""
			::= { mbus08 46 }

mbus08Value14		OBJECT-TYPE
			SYNTAX	INTEGER
			ACCESS	read-only
			STATUS	current
	DESCRIPTION ""
			::= { mbus08 47 }

mbus08VIF15		OBJECT-TYPE
			SYNTAX	INTEGER
			ACCESS	read-only
			STATUS	current
	DESCRIPTION ""
			::= { mbus08 48 }

mbus08Value15		OBJECT-TYPE
			SYNTAX	INTEGER
			ACCESS	read-only
			STATUS	current
	DESCRIPTION ""
			::= { mbus08 49 }

mbus08VIF16		OBJECT-TYPE
			SYNTAX	INTEGER
			ACCESS	read-only
			STATUS	current
	DESCRIPTION ""
			::= { mbus08 50 }

mbus08Value16		OBJECT-TYPE
			SYNTAX	INTEGER
			ACCESS	read-only
			STATUS	current
	DESCRIPTION ""
			::= { mbus08 51 }

mbus08VIF17		OBJECT-TYPE
			SYNTAX	INTEGER
			ACCESS	read-only
			STATUS	current
	DESCRIPTION ""
			::= { mbus08 52 }

mbus08Value17		OBJECT-TYPE
			SYNTAX	INTEGER
			ACCESS	read-only
			STATUS	current
	DESCRIPTION ""
			::= { mbus08 53 }

mbus08VIF18		OBJECT-TYPE
			SYNTAX	INTEGER
			ACCESS	read-only
			STATUS	current
	DESCRIPTION ""
			::= { mbus08 54 }

mbus08Value18		OBJECT-TYPE
			SYNTAX	INTEGER
			ACCESS	read-only
			STATUS	current
	DESCRIPTION ""
			::= { mbus08 55 }

mbus08VIF19		OBJECT-TYPE
			SYNTAX	INTEGER
			ACCESS	read-only
			STATUS	current
	DESCRIPTION ""
			::= { mbus08 56 }

mbus08Value19		OBJECT-TYPE
			SYNTAX	INTEGER
			ACCESS	read-only
			STATUS	current
	DESCRIPTION ""
			::= { mbus08 57 }

mbus08VIF1A		OBJECT-TYPE
			SYNTAX	INTEGER
			ACCESS	read-only
			STATUS	current
	DESCRIPTION ""
			::= { mbus08 58 }

mbus08Value1A		OBJECT-TYPE
			SYNTAX	INTEGER
			ACCESS	read-only
			STATUS	current
	DESCRIPTION ""
			::= { mbus08 59 }

mbus08VIF1B		OBJECT-TYPE
			SYNTAX	INTEGER
			ACCESS	read-only
			STATUS	current
	DESCRIPTION ""
			::= { mbus08 60 }

mbus08Value1B		OBJECT-TYPE
			SYNTAX	INTEGER
			ACCESS	read-only
			STATUS	current
	DESCRIPTION ""
			::= { mbus08 61 }

mbus08VIF1C		OBJECT-TYPE
			SYNTAX	INTEGER
			ACCESS	read-only
			STATUS	current
	DESCRIPTION ""
			::= { mbus08 62 }

mbus08Value1C		OBJECT-TYPE
			SYNTAX	INTEGER
			ACCESS	read-only
			STATUS	current
	DESCRIPTION ""
			::= { mbus08 63 }

mbus08VIF1D		OBJECT-TYPE
			SYNTAX	INTEGER
			ACCESS	read-only
			STATUS	current
	DESCRIPTION ""
			::= { mbus08 64 }

mbus08Value1D		OBJECT-TYPE
			SYNTAX	INTEGER
			ACCESS	read-only
			STATUS	current
	DESCRIPTION ""
			::= { mbus08 65 }

mbus08VIF1E		OBJECT-TYPE
			SYNTAX	INTEGER
			ACCESS	read-only
			STATUS	current
	DESCRIPTION ""
			::= { mbus08 66 }

mbus08Value1E		OBJECT-TYPE
			SYNTAX	INTEGER
			ACCESS	read-only
			STATUS	current
	DESCRIPTION ""
			::= { mbus08 67 }

mbus08VIF1F		OBJECT-TYPE
			SYNTAX	INTEGER
			ACCESS	read-only
			STATUS	current
	DESCRIPTION ""
			::= { mbus08 68 }

mbus08Value1F		OBJECT-TYPE
			SYNTAX	INTEGER
			ACCESS	read-only
			STATUS	current
	DESCRIPTION ""
			::= { mbus08 69 }

mbus08VIF20		OBJECT-TYPE
			SYNTAX	INTEGER
			ACCESS	read-only
			STATUS	current
	DESCRIPTION ""
			::= { mbus08 70 }

mbus08Value20		OBJECT-TYPE
			SYNTAX	INTEGER
			ACCESS	read-only
			STATUS	current
	DESCRIPTION ""
			::= { mbus08 71 }

mbus08VIF21		OBJECT-TYPE
			SYNTAX	INTEGER
			ACCESS	read-only
			STATUS	current
	DESCRIPTION ""
			::= { mbus08 72 }

mbus08Value21		OBJECT-TYPE
			SYNTAX	INTEGER
			ACCESS	read-only
			STATUS	current
	DESCRIPTION ""
			::= { mbus08 73 }

mbus08VIF22		OBJECT-TYPE
			SYNTAX	INTEGER
			ACCESS	read-only
			STATUS	current
	DESCRIPTION ""
			::= { mbus08 74 }

mbus08Value22		OBJECT-TYPE
			SYNTAX	INTEGER
			ACCESS	read-only
			STATUS	current
	DESCRIPTION ""
			::= { mbus08 75 }

mbus08VIF23		OBJECT-TYPE
			SYNTAX	INTEGER
			ACCESS	read-only
			STATUS	current
	DESCRIPTION ""
			::= { mbus08 76 }

mbus08Value23		OBJECT-TYPE
			SYNTAX	INTEGER
			ACCESS	read-only
			STATUS	current
	DESCRIPTION ""
			::= { mbus08 77 }

mbus08VIF24		OBJECT-TYPE
			SYNTAX	INTEGER
			ACCESS	read-only
			STATUS	current
	DESCRIPTION ""
			::= { mbus08 78 }

mbus08Value24		OBJECT-TYPE
			SYNTAX	INTEGER
			ACCESS	read-only
			STATUS	current
	DESCRIPTION ""
			::= { mbus08 79 }

mbus08VIF25		OBJECT-TYPE
			SYNTAX	INTEGER
			ACCESS	read-only
			STATUS	current
	DESCRIPTION ""
			::= { mbus08 80 }

mbus08Value25		OBJECT-TYPE
			SYNTAX	INTEGER
			ACCESS	read-only
			STATUS	current
	DESCRIPTION ""
			::= { mbus08 81 }

mbus08VIF26		OBJECT-TYPE
			SYNTAX	INTEGER
			ACCESS	read-only
			STATUS	current
	DESCRIPTION ""
			::= { mbus08 82 }

mbus08Value26		OBJECT-TYPE
			SYNTAX	INTEGER
			ACCESS	read-only
			STATUS	current
	DESCRIPTION ""
			::= { mbus08 83 }

mbus08VIF27		OBJECT-TYPE
			SYNTAX	INTEGER
			ACCESS	read-only
			STATUS	current
	DESCRIPTION ""
			::= { mbus08 84 }

mbus08Value27		OBJECT-TYPE
			SYNTAX	INTEGER
			ACCESS	read-only
			STATUS	current
	DESCRIPTION ""
			::= { mbus08 85 }

mbus08VIF28		OBJECT-TYPE
			SYNTAX	INTEGER
			ACCESS	read-only
			STATUS	current
	DESCRIPTION ""
			::= { mbus08 86 }

mbus08Value28		OBJECT-TYPE
			SYNTAX	INTEGER
			ACCESS	read-only
			STATUS	current
	DESCRIPTION ""
			::= { mbus08 87 }

mbus08VIF29		OBJECT-TYPE
			SYNTAX	INTEGER
			ACCESS	read-only
			STATUS	current
	DESCRIPTION ""
			::= { mbus08 88 }

mbus08Value29		OBJECT-TYPE
			SYNTAX	INTEGER
			ACCESS	read-only
			STATUS	current
	DESCRIPTION ""
			::= { mbus08 89 }

mbus08VIF2A		OBJECT-TYPE
			SYNTAX	INTEGER
			ACCESS	read-only
			STATUS	current
	DESCRIPTION ""
			::= { mbus08 90 }

mbus08Value2A		OBJECT-TYPE
			SYNTAX	INTEGER
			ACCESS	read-only
			STATUS	current
	DESCRIPTION ""
			::= { mbus08 91 }

mbus08VIF2B		OBJECT-TYPE
			SYNTAX	INTEGER
			ACCESS	read-only
			STATUS	current
	DESCRIPTION ""
			::= { mbus08 92 }

mbus08Value2B		OBJECT-TYPE
			SYNTAX	INTEGER
			ACCESS	read-only
			STATUS	current
	DESCRIPTION ""
			::= { mbus08 93 }

mbus08VIF2C		OBJECT-TYPE
			SYNTAX	INTEGER
			ACCESS	read-only
			STATUS	current
	DESCRIPTION ""
			::= { mbus08 94 }

mbus08Value2C		OBJECT-TYPE
			SYNTAX	INTEGER
			ACCESS	read-only
			STATUS	current
	DESCRIPTION ""
			::= { mbus08 95 }

mbus08VIF2D		OBJECT-TYPE
			SYNTAX	INTEGER
			ACCESS	read-only
			STATUS	current
	DESCRIPTION ""
			::= { mbus08 96 }

mbus08Value2D		OBJECT-TYPE
			SYNTAX	INTEGER
			ACCESS	read-only
			STATUS	current
	DESCRIPTION ""
			::= { mbus08 97 }

mbus08VIF2E		OBJECT-TYPE
			SYNTAX	INTEGER
			ACCESS	read-only
			STATUS	current
	DESCRIPTION ""
			::= { mbus08 98 }

mbus08Value2E		OBJECT-TYPE
			SYNTAX	INTEGER
			ACCESS	read-only
			STATUS	current
	DESCRIPTION ""
			::= { mbus08 99 }

mbus08VIF2F		OBJECT-TYPE
			SYNTAX	INTEGER
			ACCESS	read-only
			STATUS	current
	DESCRIPTION ""
			::= { mbus08 100 }

mbus08Value2F		OBJECT-TYPE
			SYNTAX	INTEGER
			ACCESS	read-only
			STATUS	current
	DESCRIPTION ""
			::= { mbus08 101 }

mbus09			OBJECT IDENTIFIER ::= { mbus 9 }

mbus09IdNumber		OBJECT-TYPE
			SYNTAX	Gauge
			ACCESS	read-only
			STATUS	current
	DESCRIPTION ""
			::= { mbus09 1 }

mbus09Manufacturer	OBJECT-TYPE
			SYNTAX	Gauge
			ACCESS	read-only
			STATUS	current
	DESCRIPTION ""
			::= { mbus09 2 }

mbus09Version		OBJECT-TYPE
			SYNTAX	Gauge
			ACCESS	read-only
			STATUS	current
	DESCRIPTION ""
			::= { mbus09 3 }

mbus09Medium		OBJECT-TYPE
			SYNTAX	Gauge
			ACCESS	read-only
			STATUS	current
	DESCRIPTION ""
			::= { mbus09 4 }

mbus09Status		OBJECT-TYPE
			SYNTAX	Gauge
			ACCESS	read-only
			STATUS	current
	DESCRIPTION ""
			::= { mbus09 5 }

mbus09VIF00		OBJECT-TYPE
			SYNTAX	INTEGER
			ACCESS	read-only
			STATUS	current
	DESCRIPTION ""
			::= { mbus09 6 }

mbus09Value00		OBJECT-TYPE
			SYNTAX	INTEGER
			ACCESS	read-only
			STATUS	current
	DESCRIPTION ""
			::= { mbus09 7 }

mbus09VIF01		OBJECT-TYPE
			SYNTAX	INTEGER
			ACCESS	read-only
			STATUS	current
	DESCRIPTION ""
			::= { mbus09 8 }

mbus09Value01		OBJECT-TYPE
			SYNTAX	INTEGER
			ACCESS	read-only
			STATUS	current
	DESCRIPTION ""
			::= { mbus09 9 }

mbus09VIF02		OBJECT-TYPE
			SYNTAX	INTEGER
			ACCESS	read-only
			STATUS	current
	DESCRIPTION ""
			::= { mbus09 10 }

mbus09Value02		OBJECT-TYPE
			SYNTAX	INTEGER
			ACCESS	read-only
			STATUS	current
	DESCRIPTION ""
			::= { mbus09 11 }

mbus09VIF03		OBJECT-TYPE
			SYNTAX	INTEGER
			ACCESS	read-only
			STATUS	current
	DESCRIPTION ""
			::= { mbus09 12 }

mbus09Value03		OBJECT-TYPE
			SYNTAX	INTEGER
			ACCESS	read-only
			STATUS	current
	DESCRIPTION ""
			::= { mbus09 13 }

mbus09VIF04		OBJECT-TYPE
			SYNTAX	INTEGER
			ACCESS	read-only
			STATUS	current
	DESCRIPTION ""
			::= { mbus09 14 }

mbus09Value04		OBJECT-TYPE
			SYNTAX	INTEGER
			ACCESS	read-only
			STATUS	current
	DESCRIPTION ""
			::= { mbus09 15 }

mbus09VIF05		OBJECT-TYPE
			SYNTAX	INTEGER
			ACCESS	read-only
			STATUS	current
	DESCRIPTION ""
			::= { mbus09 16 }

mbus09Value05		OBJECT-TYPE
			SYNTAX	INTEGER
			ACCESS	read-only
			STATUS	current
	DESCRIPTION ""
			::= { mbus09 17 }

mbus09VIF06		OBJECT-TYPE
			SYNTAX	INTEGER
			ACCESS	read-only
			STATUS	current
	DESCRIPTION ""
			::= { mbus09 18 }

mbus09Value06		OBJECT-TYPE
			SYNTAX	INTEGER
			ACCESS	read-only
			STATUS	current
	DESCRIPTION ""
			::= { mbus09 19 }

mbus09VIF07		OBJECT-TYPE
			SYNTAX	INTEGER
			ACCESS	read-only
			STATUS	current
	DESCRIPTION ""
			::= { mbus09 20 }

mbus09Value07		OBJECT-TYPE
			SYNTAX	INTEGER
			ACCESS	read-only
			STATUS	current
	DESCRIPTION ""
			::= { mbus09 21 }

mbus09VIF08		OBJECT-TYPE
			SYNTAX	INTEGER
			ACCESS	read-only
			STATUS	current
	DESCRIPTION ""
			::= { mbus09 22 }

mbus09Value08		OBJECT-TYPE
			SYNTAX	INTEGER
			ACCESS	read-only
			STATUS	current
	DESCRIPTION ""
			::= { mbus09 23 }

mbus09VIF09		OBJECT-TYPE
			SYNTAX	INTEGER
			ACCESS	read-only
			STATUS	current
	DESCRIPTION ""
			::= { mbus09 24 }

mbus09Value09		OBJECT-TYPE
			SYNTAX	INTEGER
			ACCESS	read-only
			STATUS	current
	DESCRIPTION ""
			::= { mbus09 25 }

mbus09VIF0A		OBJECT-TYPE
			SYNTAX	INTEGER
			ACCESS	read-only
			STATUS	current
	DESCRIPTION ""
			::= { mbus09 26 }

mbus09Value0A		OBJECT-TYPE
			SYNTAX	INTEGER
			ACCESS	read-only
			STATUS	current
	DESCRIPTION ""
			::= { mbus09 27 }

mbus09VIF0B		OBJECT-TYPE
			SYNTAX	INTEGER
			ACCESS	read-only
			STATUS	current
	DESCRIPTION ""
			::= { mbus09 28 }

mbus09Value0B		OBJECT-TYPE
			SYNTAX	INTEGER
			ACCESS	read-only
			STATUS	current
	DESCRIPTION ""
			::= { mbus09 29 }

mbus09VIF0C		OBJECT-TYPE
			SYNTAX	INTEGER
			ACCESS	read-only
			STATUS	current
	DESCRIPTION ""
			::= { mbus09 30 }

mbus09Value0C		OBJECT-TYPE
			SYNTAX	INTEGER
			ACCESS	read-only
			STATUS	current
	DESCRIPTION ""
			::= { mbus09 31 }

mbus09VIF0D		OBJECT-TYPE
			SYNTAX	INTEGER
			ACCESS	read-only
			STATUS	current
	DESCRIPTION ""
			::= { mbus09 32 }

mbus09Value0D		OBJECT-TYPE
			SYNTAX	INTEGER
			ACCESS	read-only
			STATUS	current
	DESCRIPTION ""
			::= { mbus09 33 }

mbus09VIF0E		OBJECT-TYPE
			SYNTAX	INTEGER
			ACCESS	read-only
			STATUS	current
	DESCRIPTION ""
			::= { mbus09 34 }

mbus09Value0E		OBJECT-TYPE
			SYNTAX	INTEGER
			ACCESS	read-only
			STATUS	current
	DESCRIPTION ""
			::= { mbus09 35 }

mbus09VIF0F		OBJECT-TYPE
			SYNTAX	INTEGER
			ACCESS	read-only
			STATUS	current
	DESCRIPTION ""
			::= { mbus09 36 }

mbus09Value0F		OBJECT-TYPE
			SYNTAX	INTEGER
			ACCESS	read-only
			STATUS	current
	DESCRIPTION ""
			::= { mbus09 37 }

mbus09VIF10		OBJECT-TYPE
			SYNTAX	INTEGER
			ACCESS	read-only
			STATUS	current
	DESCRIPTION ""
			::= { mbus09 38 }

mbus09Value10		OBJECT-TYPE
			SYNTAX	INTEGER
			ACCESS	read-only
			STATUS	current
	DESCRIPTION ""
			::= { mbus09 39 }

mbus09VIF11		OBJECT-TYPE
			SYNTAX	INTEGER
			ACCESS	read-only
			STATUS	current
	DESCRIPTION ""
			::= { mbus09 40 }

mbus09Value11		OBJECT-TYPE
			SYNTAX	INTEGER
			ACCESS	read-only
			STATUS	current
	DESCRIPTION ""
			::= { mbus09 41 }

mbus09VIF12		OBJECT-TYPE
			SYNTAX	INTEGER
			ACCESS	read-only
			STATUS	current
	DESCRIPTION ""
			::= { mbus09 42 }

mbus09Value12		OBJECT-TYPE
			SYNTAX	INTEGER
			ACCESS	read-only
			STATUS	current
	DESCRIPTION ""
			::= { mbus09 43 }

mbus09VIF13		OBJECT-TYPE
			SYNTAX	INTEGER
			ACCESS	read-only
			STATUS	current
	DESCRIPTION ""
			::= { mbus09 44 }

mbus09Value13		OBJECT-TYPE
			SYNTAX	INTEGER
			ACCESS	read-only
			STATUS	current
	DESCRIPTION ""
			::= { mbus09 45 }

mbus09VIF14		OBJECT-TYPE
			SYNTAX	INTEGER
			ACCESS	read-only
			STATUS	current
	DESCRIPTION ""
			::= { mbus09 46 }

mbus09Value14		OBJECT-TYPE
			SYNTAX	INTEGER
			ACCESS	read-only
			STATUS	current
	DESCRIPTION ""
			::= { mbus09 47 }

mbus09VIF15		OBJECT-TYPE
			SYNTAX	INTEGER
			ACCESS	read-only
			STATUS	current
	DESCRIPTION ""
			::= { mbus09 48 }

mbus09Value15		OBJECT-TYPE
			SYNTAX	INTEGER
			ACCESS	read-only
			STATUS	current
	DESCRIPTION ""
			::= { mbus09 49 }

mbus09VIF16		OBJECT-TYPE
			SYNTAX	INTEGER
			ACCESS	read-only
			STATUS	current
	DESCRIPTION ""
			::= { mbus09 50 }

mbus09Value16		OBJECT-TYPE
			SYNTAX	INTEGER
			ACCESS	read-only
			STATUS	current
	DESCRIPTION ""
			::= { mbus09 51 }

mbus09VIF17		OBJECT-TYPE
			SYNTAX	INTEGER
			ACCESS	read-only
			STATUS	current
	DESCRIPTION ""
			::= { mbus09 52 }

mbus09Value17		OBJECT-TYPE
			SYNTAX	INTEGER
			ACCESS	read-only
			STATUS	current
	DESCRIPTION ""
			::= { mbus09 53 }

mbus09VIF18		OBJECT-TYPE
			SYNTAX	INTEGER
			ACCESS	read-only
			STATUS	current
	DESCRIPTION ""
			::= { mbus09 54 }

mbus09Value18		OBJECT-TYPE
			SYNTAX	INTEGER
			ACCESS	read-only
			STATUS	current
	DESCRIPTION ""
			::= { mbus09 55 }

mbus09VIF19		OBJECT-TYPE
			SYNTAX	INTEGER
			ACCESS	read-only
			STATUS	current
	DESCRIPTION ""
			::= { mbus09 56 }

mbus09Value19		OBJECT-TYPE
			SYNTAX	INTEGER
			ACCESS	read-only
			STATUS	current
	DESCRIPTION ""
			::= { mbus09 57 }

mbus09VIF1A		OBJECT-TYPE
			SYNTAX	INTEGER
			ACCESS	read-only
			STATUS	current
	DESCRIPTION ""
			::= { mbus09 58 }

mbus09Value1A		OBJECT-TYPE
			SYNTAX	INTEGER
			ACCESS	read-only
			STATUS	current
	DESCRIPTION ""
			::= { mbus09 59 }

mbus09VIF1B		OBJECT-TYPE
			SYNTAX	INTEGER
			ACCESS	read-only
			STATUS	current
	DESCRIPTION ""
			::= { mbus09 60 }

mbus09Value1B		OBJECT-TYPE
			SYNTAX	INTEGER
			ACCESS	read-only
			STATUS	current
	DESCRIPTION ""
			::= { mbus09 61 }

mbus09VIF1C		OBJECT-TYPE
			SYNTAX	INTEGER
			ACCESS	read-only
			STATUS	current
	DESCRIPTION ""
			::= { mbus09 62 }

mbus09Value1C		OBJECT-TYPE
			SYNTAX	INTEGER
			ACCESS	read-only
			STATUS	current
	DESCRIPTION ""
			::= { mbus09 63 }

mbus09VIF1D		OBJECT-TYPE
			SYNTAX	INTEGER
			ACCESS	read-only
			STATUS	current
	DESCRIPTION ""
			::= { mbus09 64 }

mbus09Value1D		OBJECT-TYPE
			SYNTAX	INTEGER
			ACCESS	read-only
			STATUS	current
	DESCRIPTION ""
			::= { mbus09 65 }

mbus09VIF1E		OBJECT-TYPE
			SYNTAX	INTEGER
			ACCESS	read-only
			STATUS	current
	DESCRIPTION ""
			::= { mbus09 66 }

mbus09Value1E		OBJECT-TYPE
			SYNTAX	INTEGER
			ACCESS	read-only
			STATUS	current
	DESCRIPTION ""
			::= { mbus09 67 }

mbus09VIF1F		OBJECT-TYPE
			SYNTAX	INTEGER
			ACCESS	read-only
			STATUS	current
	DESCRIPTION ""
			::= { mbus09 68 }

mbus09Value1F		OBJECT-TYPE
			SYNTAX	INTEGER
			ACCESS	read-only
			STATUS	current
	DESCRIPTION ""
			::= { mbus09 69 }

mbus09VIF20		OBJECT-TYPE
			SYNTAX	INTEGER
			ACCESS	read-only
			STATUS	current
	DESCRIPTION ""
			::= { mbus09 70 }

mbus09Value20		OBJECT-TYPE
			SYNTAX	INTEGER
			ACCESS	read-only
			STATUS	current
	DESCRIPTION ""
			::= { mbus09 71 }

mbus09VIF21		OBJECT-TYPE
			SYNTAX	INTEGER
			ACCESS	read-only
			STATUS	current
	DESCRIPTION ""
			::= { mbus09 72 }

mbus09Value21		OBJECT-TYPE
			SYNTAX	INTEGER
			ACCESS	read-only
			STATUS	current
	DESCRIPTION ""
			::= { mbus09 73 }

mbus09VIF22		OBJECT-TYPE
			SYNTAX	INTEGER
			ACCESS	read-only
			STATUS	current
	DESCRIPTION ""
			::= { mbus09 74 }

mbus09Value22		OBJECT-TYPE
			SYNTAX	INTEGER
			ACCESS	read-only
			STATUS	current
	DESCRIPTION ""
			::= { mbus09 75 }

mbus09VIF23		OBJECT-TYPE
			SYNTAX	INTEGER
			ACCESS	read-only
			STATUS	current
	DESCRIPTION ""
			::= { mbus09 76 }

mbus09Value23		OBJECT-TYPE
			SYNTAX	INTEGER
			ACCESS	read-only
			STATUS	current
	DESCRIPTION ""
			::= { mbus09 77 }

mbus09VIF24		OBJECT-TYPE
			SYNTAX	INTEGER
			ACCESS	read-only
			STATUS	current
	DESCRIPTION ""
			::= { mbus09 78 }

mbus09Value24		OBJECT-TYPE
			SYNTAX	INTEGER
			ACCESS	read-only
			STATUS	current
	DESCRIPTION ""
			::= { mbus09 79 }

mbus09VIF25		OBJECT-TYPE
			SYNTAX	INTEGER
			ACCESS	read-only
			STATUS	current
	DESCRIPTION ""
			::= { mbus09 80 }

mbus09Value25		OBJECT-TYPE
			SYNTAX	INTEGER
			ACCESS	read-only
			STATUS	current
	DESCRIPTION ""
			::= { mbus09 81 }

mbus09VIF26		OBJECT-TYPE
			SYNTAX	INTEGER
			ACCESS	read-only
			STATUS	current
	DESCRIPTION ""
			::= { mbus09 82 }

mbus09Value26		OBJECT-TYPE
			SYNTAX	INTEGER
			ACCESS	read-only
			STATUS	current
	DESCRIPTION ""
			::= { mbus09 83 }

mbus09VIF27		OBJECT-TYPE
			SYNTAX	INTEGER
			ACCESS	read-only
			STATUS	current
	DESCRIPTION ""
			::= { mbus09 84 }

mbus09Value27		OBJECT-TYPE
			SYNTAX	INTEGER
			ACCESS	read-only
			STATUS	current
	DESCRIPTION ""
			::= { mbus09 85 }

mbus09VIF28		OBJECT-TYPE
			SYNTAX	INTEGER
			ACCESS	read-only
			STATUS	current
	DESCRIPTION ""
			::= { mbus09 86 }

mbus09Value28		OBJECT-TYPE
			SYNTAX	INTEGER
			ACCESS	read-only
			STATUS	current
	DESCRIPTION ""
			::= { mbus09 87 }

mbus09VIF29		OBJECT-TYPE
			SYNTAX	INTEGER
			ACCESS	read-only
			STATUS	current
	DESCRIPTION ""
			::= { mbus09 88 }

mbus09Value29		OBJECT-TYPE
			SYNTAX	INTEGER
			ACCESS	read-only
			STATUS	current
	DESCRIPTION ""
			::= { mbus09 89 }

mbus09VIF2A		OBJECT-TYPE
			SYNTAX	INTEGER
			ACCESS	read-only
			STATUS	current
	DESCRIPTION ""
			::= { mbus09 90 }

mbus09Value2A		OBJECT-TYPE
			SYNTAX	INTEGER
			ACCESS	read-only
			STATUS	current
	DESCRIPTION ""
			::= { mbus09 91 }

mbus09VIF2B		OBJECT-TYPE
			SYNTAX	INTEGER
			ACCESS	read-only
			STATUS	current
	DESCRIPTION ""
			::= { mbus09 92 }

mbus09Value2B		OBJECT-TYPE
			SYNTAX	INTEGER
			ACCESS	read-only
			STATUS	current
	DESCRIPTION ""
			::= { mbus09 93 }

mbus09VIF2C		OBJECT-TYPE
			SYNTAX	INTEGER
			ACCESS	read-only
			STATUS	current
	DESCRIPTION ""
			::= { mbus09 94 }

mbus09Value2C		OBJECT-TYPE
			SYNTAX	INTEGER
			ACCESS	read-only
			STATUS	current
	DESCRIPTION ""
			::= { mbus09 95 }

mbus09VIF2D		OBJECT-TYPE
			SYNTAX	INTEGER
			ACCESS	read-only
			STATUS	current
	DESCRIPTION ""
			::= { mbus09 96 }

mbus09Value2D		OBJECT-TYPE
			SYNTAX	INTEGER
			ACCESS	read-only
			STATUS	current
	DESCRIPTION ""
			::= { mbus09 97 }

mbus09VIF2E		OBJECT-TYPE
			SYNTAX	INTEGER
			ACCESS	read-only
			STATUS	current
	DESCRIPTION ""
			::= { mbus09 98 }

mbus09Value2E		OBJECT-TYPE
			SYNTAX	INTEGER
			ACCESS	read-only
			STATUS	current
	DESCRIPTION ""
			::= { mbus09 99 }

mbus09VIF2F		OBJECT-TYPE
			SYNTAX	INTEGER
			ACCESS	read-only
			STATUS	current
	DESCRIPTION ""
			::= { mbus09 100 }

mbus09Value2F		OBJECT-TYPE
			SYNTAX	INTEGER
			ACCESS	read-only
			STATUS	current
	DESCRIPTION ""
			::= { mbus09 101 }

mbus0A			OBJECT IDENTIFIER ::= { mbus 10 }

mbus0AIdNumber		OBJECT-TYPE
			SYNTAX	Gauge
			ACCESS	read-only
			STATUS	current
	DESCRIPTION ""
			::= { mbus0A 1 }

mbus0AManufacturer	OBJECT-TYPE
			SYNTAX	Gauge
			ACCESS	read-only
			STATUS	current
	DESCRIPTION ""
			::= { mbus0A 2 }

mbus0AVersion		OBJECT-TYPE
			SYNTAX	Gauge
			ACCESS	read-only
			STATUS	current
	DESCRIPTION ""
			::= { mbus0A 3 }

mbus0AMedium		OBJECT-TYPE
			SYNTAX	Gauge
			ACCESS	read-only
			STATUS	current
	DESCRIPTION ""
			::= { mbus0A 4 }

mbus0AStatus		OBJECT-TYPE
			SYNTAX	Gauge
			ACCESS	read-only
			STATUS	current
	DESCRIPTION ""
			::= { mbus0A 5 }

mbus0AVIF00		OBJECT-TYPE
			SYNTAX	INTEGER
			ACCESS	read-only
			STATUS	current
	DESCRIPTION ""
			::= { mbus0A 6 }

mbus0AValue00		OBJECT-TYPE
			SYNTAX	INTEGER
			ACCESS	read-only
			STATUS	current
	DESCRIPTION ""
			::= { mbus0A 7 }

mbus0AVIF01		OBJECT-TYPE
			SYNTAX	INTEGER
			ACCESS	read-only
			STATUS	current
	DESCRIPTION ""
			::= { mbus0A 8 }

mbus0AValue01		OBJECT-TYPE
			SYNTAX	INTEGER
			ACCESS	read-only
			STATUS	current
	DESCRIPTION ""
			::= { mbus0A 9 }

mbus0AVIF02		OBJECT-TYPE
			SYNTAX	INTEGER
			ACCESS	read-only
			STATUS	current
	DESCRIPTION ""
			::= { mbus0A 10 }

mbus0AValue02		OBJECT-TYPE
			SYNTAX	INTEGER
			ACCESS	read-only
			STATUS	current
	DESCRIPTION ""
			::= { mbus0A 11 }

mbus0AVIF03		OBJECT-TYPE
			SYNTAX	INTEGER
			ACCESS	read-only
			STATUS	current
	DESCRIPTION ""
			::= { mbus0A 12 }

mbus0AValue03		OBJECT-TYPE
			SYNTAX	INTEGER
			ACCESS	read-only
			STATUS	current
	DESCRIPTION ""
			::= { mbus0A 13 }

mbus0AVIF04		OBJECT-TYPE
			SYNTAX	INTEGER
			ACCESS	read-only
			STATUS	current
	DESCRIPTION ""
			::= { mbus0A 14 }

mbus0AValue04		OBJECT-TYPE
			SYNTAX	INTEGER
			ACCESS	read-only
			STATUS	current
	DESCRIPTION ""
			::= { mbus0A 15 }

mbus0AVIF05		OBJECT-TYPE
			SYNTAX	INTEGER
			ACCESS	read-only
			STATUS	current
	DESCRIPTION ""
			::= { mbus0A 16 }

mbus0AValue05		OBJECT-TYPE
			SYNTAX	INTEGER
			ACCESS	read-only
			STATUS	current
	DESCRIPTION ""
			::= { mbus0A 17 }

mbus0AVIF06		OBJECT-TYPE
			SYNTAX	INTEGER
			ACCESS	read-only
			STATUS	current
	DESCRIPTION ""
			::= { mbus0A 18 }

mbus0AValue06		OBJECT-TYPE
			SYNTAX	INTEGER
			ACCESS	read-only
			STATUS	current
	DESCRIPTION ""
			::= { mbus0A 19 }

mbus0AVIF07		OBJECT-TYPE
			SYNTAX	INTEGER
			ACCESS	read-only
			STATUS	current
	DESCRIPTION ""
			::= { mbus0A 20 }

mbus0AValue07		OBJECT-TYPE
			SYNTAX	INTEGER
			ACCESS	read-only
			STATUS	current
	DESCRIPTION ""
			::= { mbus0A 21 }

mbus0AVIF08		OBJECT-TYPE
			SYNTAX	INTEGER
			ACCESS	read-only
			STATUS	current
	DESCRIPTION ""
			::= { mbus0A 22 }

mbus0AValue08		OBJECT-TYPE
			SYNTAX	INTEGER
			ACCESS	read-only
			STATUS	current
	DESCRIPTION ""
			::= { mbus0A 23 }

mbus0AVIF09		OBJECT-TYPE
			SYNTAX	INTEGER
			ACCESS	read-only
			STATUS	current
	DESCRIPTION ""
			::= { mbus0A 24 }

mbus0AValue09		OBJECT-TYPE
			SYNTAX	INTEGER
			ACCESS	read-only
			STATUS	current
	DESCRIPTION ""
			::= { mbus0A 25 }

mbus0AVIF0A		OBJECT-TYPE
			SYNTAX	INTEGER
			ACCESS	read-only
			STATUS	current
	DESCRIPTION ""
			::= { mbus0A 26 }

mbus0AValue0A		OBJECT-TYPE
			SYNTAX	INTEGER
			ACCESS	read-only
			STATUS	current
	DESCRIPTION ""
			::= { mbus0A 27 }

mbus0AVIF0B		OBJECT-TYPE
			SYNTAX	INTEGER
			ACCESS	read-only
			STATUS	current
	DESCRIPTION ""
			::= { mbus0A 28 }

mbus0AValue0B		OBJECT-TYPE
			SYNTAX	INTEGER
			ACCESS	read-only
			STATUS	current
	DESCRIPTION ""
			::= { mbus0A 29 }

mbus0AVIF0C		OBJECT-TYPE
			SYNTAX	INTEGER
			ACCESS	read-only
			STATUS	current
	DESCRIPTION ""
			::= { mbus0A 30 }

mbus0AValue0C		OBJECT-TYPE
			SYNTAX	INTEGER
			ACCESS	read-only
			STATUS	current
	DESCRIPTION ""
			::= { mbus0A 31 }

mbus0AVIF0D		OBJECT-TYPE
			SYNTAX	INTEGER
			ACCESS	read-only
			STATUS	current
	DESCRIPTION ""
			::= { mbus0A 32 }

mbus0AValue0D		OBJECT-TYPE
			SYNTAX	INTEGER
			ACCESS	read-only
			STATUS	current
	DESCRIPTION ""
			::= { mbus0A 33 }

mbus0AVIF0E		OBJECT-TYPE
			SYNTAX	INTEGER
			ACCESS	read-only
			STATUS	current
	DESCRIPTION ""
			::= { mbus0A 34 }

mbus0AValue0E		OBJECT-TYPE
			SYNTAX	INTEGER
			ACCESS	read-only
			STATUS	current
	DESCRIPTION ""
			::= { mbus0A 35 }

mbus0AVIF0F		OBJECT-TYPE
			SYNTAX	INTEGER
			ACCESS	read-only
			STATUS	current
	DESCRIPTION ""
			::= { mbus0A 36 }

mbus0AValue0F		OBJECT-TYPE
			SYNTAX	INTEGER
			ACCESS	read-only
			STATUS	current
	DESCRIPTION ""
			::= { mbus0A 37 }

mbus0AVIF10		OBJECT-TYPE
			SYNTAX	INTEGER
			ACCESS	read-only
			STATUS	current
	DESCRIPTION ""
			::= { mbus0A 38 }

mbus0AValue10		OBJECT-TYPE
			SYNTAX	INTEGER
			ACCESS	read-only
			STATUS	current
	DESCRIPTION ""
			::= { mbus0A 39 }

mbus0AVIF11		OBJECT-TYPE
			SYNTAX	INTEGER
			ACCESS	read-only
			STATUS	current
	DESCRIPTION ""
			::= { mbus0A 40 }

mbus0AValue11		OBJECT-TYPE
			SYNTAX	INTEGER
			ACCESS	read-only
			STATUS	current
	DESCRIPTION ""
			::= { mbus0A 41 }

mbus0AVIF12		OBJECT-TYPE
			SYNTAX	INTEGER
			ACCESS	read-only
			STATUS	current
	DESCRIPTION ""
			::= { mbus0A 42 }

mbus0AValue12		OBJECT-TYPE
			SYNTAX	INTEGER
			ACCESS	read-only
			STATUS	current
	DESCRIPTION ""
			::= { mbus0A 43 }

mbus0AVIF13		OBJECT-TYPE
			SYNTAX	INTEGER
			ACCESS	read-only
			STATUS	current
	DESCRIPTION ""
			::= { mbus0A 44 }

mbus0AValue13		OBJECT-TYPE
			SYNTAX	INTEGER
			ACCESS	read-only
			STATUS	current
	DESCRIPTION ""
			::= { mbus0A 45 }

mbus0AVIF14		OBJECT-TYPE
			SYNTAX	INTEGER
			ACCESS	read-only
			STATUS	current
	DESCRIPTION ""
			::= { mbus0A 46 }

mbus0AValue14		OBJECT-TYPE
			SYNTAX	INTEGER
			ACCESS	read-only
			STATUS	current
	DESCRIPTION ""
			::= { mbus0A 47 }

mbus0AVIF15		OBJECT-TYPE
			SYNTAX	INTEGER
			ACCESS	read-only
			STATUS	current
	DESCRIPTION ""
			::= { mbus0A 48 }

mbus0AValue15		OBJECT-TYPE
			SYNTAX	INTEGER
			ACCESS	read-only
			STATUS	current
	DESCRIPTION ""
			::= { mbus0A 49 }

mbus0AVIF16		OBJECT-TYPE
			SYNTAX	INTEGER
			ACCESS	read-only
			STATUS	current
	DESCRIPTION ""
			::= { mbus0A 50 }

mbus0AValue16		OBJECT-TYPE
			SYNTAX	INTEGER
			ACCESS	read-only
			STATUS	current
	DESCRIPTION ""
			::= { mbus0A 51 }

mbus0AVIF17		OBJECT-TYPE
			SYNTAX	INTEGER
			ACCESS	read-only
			STATUS	current
	DESCRIPTION ""
			::= { mbus0A 52 }

mbus0AValue17		OBJECT-TYPE
			SYNTAX	INTEGER
			ACCESS	read-only
			STATUS	current
	DESCRIPTION ""
			::= { mbus0A 53 }

mbus0AVIF18		OBJECT-TYPE
			SYNTAX	INTEGER
			ACCESS	read-only
			STATUS	current
	DESCRIPTION ""
			::= { mbus0A 54 }

mbus0AValue18		OBJECT-TYPE
			SYNTAX	INTEGER
			ACCESS	read-only
			STATUS	current
	DESCRIPTION ""
			::= { mbus0A 55 }

mbus0AVIF19		OBJECT-TYPE
			SYNTAX	INTEGER
			ACCESS	read-only
			STATUS	current
	DESCRIPTION ""
			::= { mbus0A 56 }

mbus0AValue19		OBJECT-TYPE
			SYNTAX	INTEGER
			ACCESS	read-only
			STATUS	current
	DESCRIPTION ""
			::= { mbus0A 57 }

mbus0AVIF1A		OBJECT-TYPE
			SYNTAX	INTEGER
			ACCESS	read-only
			STATUS	current
	DESCRIPTION ""
			::= { mbus0A 58 }

mbus0AValue1A		OBJECT-TYPE
			SYNTAX	INTEGER
			ACCESS	read-only
			STATUS	current
	DESCRIPTION ""
			::= { mbus0A 59 }

mbus0AVIF1B		OBJECT-TYPE
			SYNTAX	INTEGER
			ACCESS	read-only
			STATUS	current
	DESCRIPTION ""
			::= { mbus0A 60 }

mbus0AValue1B		OBJECT-TYPE
			SYNTAX	INTEGER
			ACCESS	read-only
			STATUS	current
	DESCRIPTION ""
			::= { mbus0A 61 }

mbus0AVIF1C		OBJECT-TYPE
			SYNTAX	INTEGER
			ACCESS	read-only
			STATUS	current
	DESCRIPTION ""
			::= { mbus0A 62 }

mbus0AValue1C		OBJECT-TYPE
			SYNTAX	INTEGER
			ACCESS	read-only
			STATUS	current
	DESCRIPTION ""
			::= { mbus0A 63 }

mbus0AVIF1D		OBJECT-TYPE
			SYNTAX	INTEGER
			ACCESS	read-only
			STATUS	current
	DESCRIPTION ""
			::= { mbus0A 64 }

mbus0AValue1D		OBJECT-TYPE
			SYNTAX	INTEGER
			ACCESS	read-only
			STATUS	current
	DESCRIPTION ""
			::= { mbus0A 65 }

mbus0AVIF1E		OBJECT-TYPE
			SYNTAX	INTEGER
			ACCESS	read-only
			STATUS	current
	DESCRIPTION ""
			::= { mbus0A 66 }

mbus0AValue1E		OBJECT-TYPE
			SYNTAX	INTEGER
			ACCESS	read-only
			STATUS	current
	DESCRIPTION ""
			::= { mbus0A 67 }

mbus0AVIF1F		OBJECT-TYPE
			SYNTAX	INTEGER
			ACCESS	read-only
			STATUS	current
	DESCRIPTION ""
			::= { mbus0A 68 }

mbus0AValue1F		OBJECT-TYPE
			SYNTAX	INTEGER
			ACCESS	read-only
			STATUS	current
	DESCRIPTION ""
			::= { mbus0A 69 }

mbus0AVIF20		OBJECT-TYPE
			SYNTAX	INTEGER
			ACCESS	read-only
			STATUS	current
	DESCRIPTION ""
			::= { mbus0A 70 }

mbus0AValue20		OBJECT-TYPE
			SYNTAX	INTEGER
			ACCESS	read-only
			STATUS	current
	DESCRIPTION ""
			::= { mbus0A 71 }

mbus0AVIF21		OBJECT-TYPE
			SYNTAX	INTEGER
			ACCESS	read-only
			STATUS	current
	DESCRIPTION ""
			::= { mbus0A 72 }

mbus0AValue21		OBJECT-TYPE
			SYNTAX	INTEGER
			ACCESS	read-only
			STATUS	current
	DESCRIPTION ""
			::= { mbus0A 73 }

mbus0AVIF22		OBJECT-TYPE
			SYNTAX	INTEGER
			ACCESS	read-only
			STATUS	current
	DESCRIPTION ""
			::= { mbus0A 74 }

mbus0AValue22		OBJECT-TYPE
			SYNTAX	INTEGER
			ACCESS	read-only
			STATUS	current
	DESCRIPTION ""
			::= { mbus0A 75 }

mbus0AVIF23		OBJECT-TYPE
			SYNTAX	INTEGER
			ACCESS	read-only
			STATUS	current
	DESCRIPTION ""
			::= { mbus0A 76 }

mbus0AValue23		OBJECT-TYPE
			SYNTAX	INTEGER
			ACCESS	read-only
			STATUS	current
	DESCRIPTION ""
			::= { mbus0A 77 }

mbus0AVIF24		OBJECT-TYPE
			SYNTAX	INTEGER
			ACCESS	read-only
			STATUS	current
	DESCRIPTION ""
			::= { mbus0A 78 }

mbus0AValue24		OBJECT-TYPE
			SYNTAX	INTEGER
			ACCESS	read-only
			STATUS	current
	DESCRIPTION ""
			::= { mbus0A 79 }

mbus0AVIF25		OBJECT-TYPE
			SYNTAX	INTEGER
			ACCESS	read-only
			STATUS	current
	DESCRIPTION ""
			::= { mbus0A 80 }

mbus0AValue25		OBJECT-TYPE
			SYNTAX	INTEGER
			ACCESS	read-only
			STATUS	current
	DESCRIPTION ""
			::= { mbus0A 81 }

mbus0AVIF26		OBJECT-TYPE
			SYNTAX	INTEGER
			ACCESS	read-only
			STATUS	current
	DESCRIPTION ""
			::= { mbus0A 82 }

mbus0AValue26		OBJECT-TYPE
			SYNTAX	INTEGER
			ACCESS	read-only
			STATUS	current
	DESCRIPTION ""
			::= { mbus0A 83 }

mbus0AVIF27		OBJECT-TYPE
			SYNTAX	INTEGER
			ACCESS	read-only
			STATUS	current
	DESCRIPTION ""
			::= { mbus0A 84 }

mbus0AValue27		OBJECT-TYPE
			SYNTAX	INTEGER
			ACCESS	read-only
			STATUS	current
	DESCRIPTION ""
			::= { mbus0A 85 }

mbus0AVIF28		OBJECT-TYPE
			SYNTAX	INTEGER
			ACCESS	read-only
			STATUS	current
	DESCRIPTION ""
			::= { mbus0A 86 }

mbus0AValue28		OBJECT-TYPE
			SYNTAX	INTEGER
			ACCESS	read-only
			STATUS	current
	DESCRIPTION ""
			::= { mbus0A 87 }

mbus0AVIF29		OBJECT-TYPE
			SYNTAX	INTEGER
			ACCESS	read-only
			STATUS	current
	DESCRIPTION ""
			::= { mbus0A 88 }

mbus0AValue29		OBJECT-TYPE
			SYNTAX	INTEGER
			ACCESS	read-only
			STATUS	current
	DESCRIPTION ""
			::= { mbus0A 89 }

mbus0AVIF2A		OBJECT-TYPE
			SYNTAX	INTEGER
			ACCESS	read-only
			STATUS	current
	DESCRIPTION ""
			::= { mbus0A 90 }

mbus0AValue2A		OBJECT-TYPE
			SYNTAX	INTEGER
			ACCESS	read-only
			STATUS	current
	DESCRIPTION ""
			::= { mbus0A 91 }

mbus0AVIF2B		OBJECT-TYPE
			SYNTAX	INTEGER
			ACCESS	read-only
			STATUS	current
	DESCRIPTION ""
			::= { mbus0A 92 }

mbus0AValue2B		OBJECT-TYPE
			SYNTAX	INTEGER
			ACCESS	read-only
			STATUS	current
	DESCRIPTION ""
			::= { mbus0A 93 }

mbus0AVIF2C		OBJECT-TYPE
			SYNTAX	INTEGER
			ACCESS	read-only
			STATUS	current
	DESCRIPTION ""
			::= { mbus0A 94 }

mbus0AValue2C		OBJECT-TYPE
			SYNTAX	INTEGER
			ACCESS	read-only
			STATUS	current
	DESCRIPTION ""
			::= { mbus0A 95 }

mbus0AVIF2D		OBJECT-TYPE
			SYNTAX	INTEGER
			ACCESS	read-only
			STATUS	current
	DESCRIPTION ""
			::= { mbus0A 96 }

mbus0AValue2D		OBJECT-TYPE
			SYNTAX	INTEGER
			ACCESS	read-only
			STATUS	current
	DESCRIPTION ""
			::= { mbus0A 97 }

mbus0AVIF2E		OBJECT-TYPE
			SYNTAX	INTEGER
			ACCESS	read-only
			STATUS	current
	DESCRIPTION ""
			::= { mbus0A 98 }

mbus0AValue2E		OBJECT-TYPE
			SYNTAX	INTEGER
			ACCESS	read-only
			STATUS	current
	DESCRIPTION ""
			::= { mbus0A 99 }

mbus0AVIF2F		OBJECT-TYPE
			SYNTAX	INTEGER
			ACCESS	read-only
			STATUS	current
	DESCRIPTION ""
			::= { mbus0A 100 }

mbus0AValue2F		OBJECT-TYPE
			SYNTAX	INTEGER
			ACCESS	read-only
			STATUS	current
	DESCRIPTION ""
			::= { mbus0A 101 }

mbus0B			OBJECT IDENTIFIER ::= { mbus 11 }

mbus0BIdNumber		OBJECT-TYPE
			SYNTAX	Gauge
			ACCESS	read-only
			STATUS	current
	DESCRIPTION ""
			::= { mbus0B 1 }

mbus0BManufacturer	OBJECT-TYPE
			SYNTAX	Gauge
			ACCESS	read-only
			STATUS	current
	DESCRIPTION ""
			::= { mbus0B 2 }

mbus0BVersion		OBJECT-TYPE
			SYNTAX	Gauge
			ACCESS	read-only
			STATUS	current
	DESCRIPTION ""
			::= { mbus0B 3 }

mbus0BMedium		OBJECT-TYPE
			SYNTAX	Gauge
			ACCESS	read-only
			STATUS	current
	DESCRIPTION ""
			::= { mbus0B 4 }

mbus0BStatus		OBJECT-TYPE
			SYNTAX	Gauge
			ACCESS	read-only
			STATUS	current
	DESCRIPTION ""
			::= { mbus0B 5 }

mbus0BVIF00		OBJECT-TYPE
			SYNTAX	INTEGER
			ACCESS	read-only
			STATUS	current
	DESCRIPTION ""
			::= { mbus0B 6 }

mbus0BValue00		OBJECT-TYPE
			SYNTAX	INTEGER
			ACCESS	read-only
			STATUS	current
	DESCRIPTION ""
			::= { mbus0B 7 }

mbus0BVIF01		OBJECT-TYPE
			SYNTAX	INTEGER
			ACCESS	read-only
			STATUS	current
	DESCRIPTION ""
			::= { mbus0B 8 }

mbus0BValue01		OBJECT-TYPE
			SYNTAX	INTEGER
			ACCESS	read-only
			STATUS	current
	DESCRIPTION ""
			::= { mbus0B 9 }

mbus0BVIF02		OBJECT-TYPE
			SYNTAX	INTEGER
			ACCESS	read-only
			STATUS	current
	DESCRIPTION ""
			::= { mbus0B 10 }

mbus0BValue02		OBJECT-TYPE
			SYNTAX	INTEGER
			ACCESS	read-only
			STATUS	current
	DESCRIPTION ""
			::= { mbus0B 11 }

mbus0BVIF03		OBJECT-TYPE
			SYNTAX	INTEGER
			ACCESS	read-only
			STATUS	current
	DESCRIPTION ""
			::= { mbus0B 12 }

mbus0BValue03		OBJECT-TYPE
			SYNTAX	INTEGER
			ACCESS	read-only
			STATUS	current
	DESCRIPTION ""
			::= { mbus0B 13 }

mbus0BVIF04		OBJECT-TYPE
			SYNTAX	INTEGER
			ACCESS	read-only
			STATUS	current
	DESCRIPTION ""
			::= { mbus0B 14 }

mbus0BValue04		OBJECT-TYPE
			SYNTAX	INTEGER
			ACCESS	read-only
			STATUS	current
	DESCRIPTION ""
			::= { mbus0B 15 }

mbus0BVIF05		OBJECT-TYPE
			SYNTAX	INTEGER
			ACCESS	read-only
			STATUS	current
	DESCRIPTION ""
			::= { mbus0B 16 }

mbus0BValue05		OBJECT-TYPE
			SYNTAX	INTEGER
			ACCESS	read-only
			STATUS	current
	DESCRIPTION ""
			::= { mbus0B 17 }

mbus0BVIF06		OBJECT-TYPE
			SYNTAX	INTEGER
			ACCESS	read-only
			STATUS	current
	DESCRIPTION ""
			::= { mbus0B 18 }

mbus0BValue06		OBJECT-TYPE
			SYNTAX	INTEGER
			ACCESS	read-only
			STATUS	current
	DESCRIPTION ""
			::= { mbus0B 19 }

mbus0BVIF07		OBJECT-TYPE
			SYNTAX	INTEGER
			ACCESS	read-only
			STATUS	current
	DESCRIPTION ""
			::= { mbus0B 20 }

mbus0BValue07		OBJECT-TYPE
			SYNTAX	INTEGER
			ACCESS	read-only
			STATUS	current
	DESCRIPTION ""
			::= { mbus0B 21 }

mbus0BVIF08		OBJECT-TYPE
			SYNTAX	INTEGER
			ACCESS	read-only
			STATUS	current
	DESCRIPTION ""
			::= { mbus0B 22 }

mbus0BValue08		OBJECT-TYPE
			SYNTAX	INTEGER
			ACCESS	read-only
			STATUS	current
	DESCRIPTION ""
			::= { mbus0B 23 }

mbus0BVIF09		OBJECT-TYPE
			SYNTAX	INTEGER
			ACCESS	read-only
			STATUS	current
	DESCRIPTION ""
			::= { mbus0B 24 }

mbus0BValue09		OBJECT-TYPE
			SYNTAX	INTEGER
			ACCESS	read-only
			STATUS	current
	DESCRIPTION ""
			::= { mbus0B 25 }

mbus0BVIF0A		OBJECT-TYPE
			SYNTAX	INTEGER
			ACCESS	read-only
			STATUS	current
	DESCRIPTION ""
			::= { mbus0B 26 }

mbus0BValue0A		OBJECT-TYPE
			SYNTAX	INTEGER
			ACCESS	read-only
			STATUS	current
	DESCRIPTION ""
			::= { mbus0B 27 }

mbus0BVIF0B		OBJECT-TYPE
			SYNTAX	INTEGER
			ACCESS	read-only
			STATUS	current
	DESCRIPTION ""
			::= { mbus0B 28 }

mbus0BValue0B		OBJECT-TYPE
			SYNTAX	INTEGER
			ACCESS	read-only
			STATUS	current
	DESCRIPTION ""
			::= { mbus0B 29 }

mbus0BVIF0C		OBJECT-TYPE
			SYNTAX	INTEGER
			ACCESS	read-only
			STATUS	current
	DESCRIPTION ""
			::= { mbus0B 30 }

mbus0BValue0C		OBJECT-TYPE
			SYNTAX	INTEGER
			ACCESS	read-only
			STATUS	current
	DESCRIPTION ""
			::= { mbus0B 31 }

mbus0BVIF0D		OBJECT-TYPE
			SYNTAX	INTEGER
			ACCESS	read-only
			STATUS	current
	DESCRIPTION ""
			::= { mbus0B 32 }

mbus0BValue0D		OBJECT-TYPE
			SYNTAX	INTEGER
			ACCESS	read-only
			STATUS	current
	DESCRIPTION ""
			::= { mbus0B 33 }

mbus0BVIF0E		OBJECT-TYPE
			SYNTAX	INTEGER
			ACCESS	read-only
			STATUS	current
	DESCRIPTION ""
			::= { mbus0B 34 }

mbus0BValue0E		OBJECT-TYPE
			SYNTAX	INTEGER
			ACCESS	read-only
			STATUS	current
	DESCRIPTION ""
			::= { mbus0B 35 }

mbus0BVIF0F		OBJECT-TYPE
			SYNTAX	INTEGER
			ACCESS	read-only
			STATUS	current
	DESCRIPTION ""
			::= { mbus0B 36 }

mbus0BValue0F		OBJECT-TYPE
			SYNTAX	INTEGER
			ACCESS	read-only
			STATUS	current
	DESCRIPTION ""
			::= { mbus0B 37 }

mbus0BVIF10		OBJECT-TYPE
			SYNTAX	INTEGER
			ACCESS	read-only
			STATUS	current
	DESCRIPTION ""
			::= { mbus0B 38 }

mbus0BValue10		OBJECT-TYPE
			SYNTAX	INTEGER
			ACCESS	read-only
			STATUS	current
	DESCRIPTION ""
			::= { mbus0B 39 }

mbus0BVIF11		OBJECT-TYPE
			SYNTAX	INTEGER
			ACCESS	read-only
			STATUS	current
	DESCRIPTION ""
			::= { mbus0B 40 }

mbus0BValue11		OBJECT-TYPE
			SYNTAX	INTEGER
			ACCESS	read-only
			STATUS	current
	DESCRIPTION ""
			::= { mbus0B 41 }

mbus0BVIF12		OBJECT-TYPE
			SYNTAX	INTEGER
			ACCESS	read-only
			STATUS	current
	DESCRIPTION ""
			::= { mbus0B 42 }

mbus0BValue12		OBJECT-TYPE
			SYNTAX	INTEGER
			ACCESS	read-only
			STATUS	current
	DESCRIPTION ""
			::= { mbus0B 43 }

mbus0BVIF13		OBJECT-TYPE
			SYNTAX	INTEGER
			ACCESS	read-only
			STATUS	current
	DESCRIPTION ""
			::= { mbus0B 44 }

mbus0BValue13		OBJECT-TYPE
			SYNTAX	INTEGER
			ACCESS	read-only
			STATUS	current
	DESCRIPTION ""
			::= { mbus0B 45 }

mbus0BVIF14		OBJECT-TYPE
			SYNTAX	INTEGER
			ACCESS	read-only
			STATUS	current
	DESCRIPTION ""
			::= { mbus0B 46 }

mbus0BValue14		OBJECT-TYPE
			SYNTAX	INTEGER
			ACCESS	read-only
			STATUS	current
	DESCRIPTION ""
			::= { mbus0B 47 }

mbus0BVIF15		OBJECT-TYPE
			SYNTAX	INTEGER
			ACCESS	read-only
			STATUS	current
	DESCRIPTION ""
			::= { mbus0B 48 }

mbus0BValue15		OBJECT-TYPE
			SYNTAX	INTEGER
			ACCESS	read-only
			STATUS	current
	DESCRIPTION ""
			::= { mbus0B 49 }

mbus0BVIF16		OBJECT-TYPE
			SYNTAX	INTEGER
			ACCESS	read-only
			STATUS	current
	DESCRIPTION ""
			::= { mbus0B 50 }

mbus0BValue16		OBJECT-TYPE
			SYNTAX	INTEGER
			ACCESS	read-only
			STATUS	current
	DESCRIPTION ""
			::= { mbus0B 51 }

mbus0BVIF17		OBJECT-TYPE
			SYNTAX	INTEGER
			ACCESS	read-only
			STATUS	current
	DESCRIPTION ""
			::= { mbus0B 52 }

mbus0BValue17		OBJECT-TYPE
			SYNTAX	INTEGER
			ACCESS	read-only
			STATUS	current
	DESCRIPTION ""
			::= { mbus0B 53 }

mbus0BVIF18		OBJECT-TYPE
			SYNTAX	INTEGER
			ACCESS	read-only
			STATUS	current
	DESCRIPTION ""
			::= { mbus0B 54 }

mbus0BValue18		OBJECT-TYPE
			SYNTAX	INTEGER
			ACCESS	read-only
			STATUS	current
	DESCRIPTION ""
			::= { mbus0B 55 }

mbus0BVIF19		OBJECT-TYPE
			SYNTAX	INTEGER
			ACCESS	read-only
			STATUS	current
	DESCRIPTION ""
			::= { mbus0B 56 }

mbus0BValue19		OBJECT-TYPE
			SYNTAX	INTEGER
			ACCESS	read-only
			STATUS	current
	DESCRIPTION ""
			::= { mbus0B 57 }

mbus0BVIF1A		OBJECT-TYPE
			SYNTAX	INTEGER
			ACCESS	read-only
			STATUS	current
	DESCRIPTION ""
			::= { mbus0B 58 }

mbus0BValue1A		OBJECT-TYPE
			SYNTAX	INTEGER
			ACCESS	read-only
			STATUS	current
	DESCRIPTION ""
			::= { mbus0B 59 }

mbus0BVIF1B		OBJECT-TYPE
			SYNTAX	INTEGER
			ACCESS	read-only
			STATUS	current
	DESCRIPTION ""
			::= { mbus0B 60 }

mbus0BValue1B		OBJECT-TYPE
			SYNTAX	INTEGER
			ACCESS	read-only
			STATUS	current
	DESCRIPTION ""
			::= { mbus0B 61 }

mbus0BVIF1C		OBJECT-TYPE
			SYNTAX	INTEGER
			ACCESS	read-only
			STATUS	current
	DESCRIPTION ""
			::= { mbus0B 62 }

mbus0BValue1C		OBJECT-TYPE
			SYNTAX	INTEGER
			ACCESS	read-only
			STATUS	current
	DESCRIPTION ""
			::= { mbus0B 63 }

mbus0BVIF1D		OBJECT-TYPE
			SYNTAX	INTEGER
			ACCESS	read-only
			STATUS	current
	DESCRIPTION ""
			::= { mbus0B 64 }

mbus0BValue1D		OBJECT-TYPE
			SYNTAX	INTEGER
			ACCESS	read-only
			STATUS	current
	DESCRIPTION ""
			::= { mbus0B 65 }

mbus0BVIF1E		OBJECT-TYPE
			SYNTAX	INTEGER
			ACCESS	read-only
			STATUS	current
	DESCRIPTION ""
			::= { mbus0B 66 }

mbus0BValue1E		OBJECT-TYPE
			SYNTAX	INTEGER
			ACCESS	read-only
			STATUS	current
	DESCRIPTION ""
			::= { mbus0B 67 }

mbus0BVIF1F		OBJECT-TYPE
			SYNTAX	INTEGER
			ACCESS	read-only
			STATUS	current
	DESCRIPTION ""
			::= { mbus0B 68 }

mbus0BValue1F		OBJECT-TYPE
			SYNTAX	INTEGER
			ACCESS	read-only
			STATUS	current
	DESCRIPTION ""
			::= { mbus0B 69 }

mbus0BVIF20		OBJECT-TYPE
			SYNTAX	INTEGER
			ACCESS	read-only
			STATUS	current
	DESCRIPTION ""
			::= { mbus0B 70 }

mbus0BValue20		OBJECT-TYPE
			SYNTAX	INTEGER
			ACCESS	read-only
			STATUS	current
	DESCRIPTION ""
			::= { mbus0B 71 }

mbus0BVIF21		OBJECT-TYPE
			SYNTAX	INTEGER
			ACCESS	read-only
			STATUS	current
	DESCRIPTION ""
			::= { mbus0B 72 }

mbus0BValue21		OBJECT-TYPE
			SYNTAX	INTEGER
			ACCESS	read-only
			STATUS	current
	DESCRIPTION ""
			::= { mbus0B 73 }

mbus0BVIF22		OBJECT-TYPE
			SYNTAX	INTEGER
			ACCESS	read-only
			STATUS	current
	DESCRIPTION ""
			::= { mbus0B 74 }

mbus0BValue22		OBJECT-TYPE
			SYNTAX	INTEGER
			ACCESS	read-only
			STATUS	current
	DESCRIPTION ""
			::= { mbus0B 75 }

mbus0BVIF23		OBJECT-TYPE
			SYNTAX	INTEGER
			ACCESS	read-only
			STATUS	current
	DESCRIPTION ""
			::= { mbus0B 76 }

mbus0BValue23		OBJECT-TYPE
			SYNTAX	INTEGER
			ACCESS	read-only
			STATUS	current
	DESCRIPTION ""
			::= { mbus0B 77 }

mbus0BVIF24		OBJECT-TYPE
			SYNTAX	INTEGER
			ACCESS	read-only
			STATUS	current
	DESCRIPTION ""
			::= { mbus0B 78 }

mbus0BValue24		OBJECT-TYPE
			SYNTAX	INTEGER
			ACCESS	read-only
			STATUS	current
	DESCRIPTION ""
			::= { mbus0B 79 }

mbus0BVIF25		OBJECT-TYPE
			SYNTAX	INTEGER
			ACCESS	read-only
			STATUS	current
	DESCRIPTION ""
			::= { mbus0B 80 }

mbus0BValue25		OBJECT-TYPE
			SYNTAX	INTEGER
			ACCESS	read-only
			STATUS	current
	DESCRIPTION ""
			::= { mbus0B 81 }

mbus0BVIF26		OBJECT-TYPE
			SYNTAX	INTEGER
			ACCESS	read-only
			STATUS	current
	DESCRIPTION ""
			::= { mbus0B 82 }

mbus0BValue26		OBJECT-TYPE
			SYNTAX	INTEGER
			ACCESS	read-only
			STATUS	current
	DESCRIPTION ""
			::= { mbus0B 83 }

mbus0BVIF27		OBJECT-TYPE
			SYNTAX	INTEGER
			ACCESS	read-only
			STATUS	current
	DESCRIPTION ""
			::= { mbus0B 84 }

mbus0BValue27		OBJECT-TYPE
			SYNTAX	INTEGER
			ACCESS	read-only
			STATUS	current
	DESCRIPTION ""
			::= { mbus0B 85 }

mbus0BVIF28		OBJECT-TYPE
			SYNTAX	INTEGER
			ACCESS	read-only
			STATUS	current
	DESCRIPTION ""
			::= { mbus0B 86 }

mbus0BValue28		OBJECT-TYPE
			SYNTAX	INTEGER
			ACCESS	read-only
			STATUS	current
	DESCRIPTION ""
			::= { mbus0B 87 }

mbus0BVIF29		OBJECT-TYPE
			SYNTAX	INTEGER
			ACCESS	read-only
			STATUS	current
	DESCRIPTION ""
			::= { mbus0B 88 }

mbus0BValue29		OBJECT-TYPE
			SYNTAX	INTEGER
			ACCESS	read-only
			STATUS	current
	DESCRIPTION ""
			::= { mbus0B 89 }

mbus0BVIF2A		OBJECT-TYPE
			SYNTAX	INTEGER
			ACCESS	read-only
			STATUS	current
	DESCRIPTION ""
			::= { mbus0B 90 }

mbus0BValue2A		OBJECT-TYPE
			SYNTAX	INTEGER
			ACCESS	read-only
			STATUS	current
	DESCRIPTION ""
			::= { mbus0B 91 }

mbus0BVIF2B		OBJECT-TYPE
			SYNTAX	INTEGER
			ACCESS	read-only
			STATUS	current
	DESCRIPTION ""
			::= { mbus0B 92 }

mbus0BValue2B		OBJECT-TYPE
			SYNTAX	INTEGER
			ACCESS	read-only
			STATUS	current
	DESCRIPTION ""
			::= { mbus0B 93 }

mbus0BVIF2C		OBJECT-TYPE
			SYNTAX	INTEGER
			ACCESS	read-only
			STATUS	current
	DESCRIPTION ""
			::= { mbus0B 94 }

mbus0BValue2C		OBJECT-TYPE
			SYNTAX	INTEGER
			ACCESS	read-only
			STATUS	current
	DESCRIPTION ""
			::= { mbus0B 95 }

mbus0BVIF2D		OBJECT-TYPE
			SYNTAX	INTEGER
			ACCESS	read-only
			STATUS	current
	DESCRIPTION ""
			::= { mbus0B 96 }

mbus0BValue2D		OBJECT-TYPE
			SYNTAX	INTEGER
			ACCESS	read-only
			STATUS	current
	DESCRIPTION ""
			::= { mbus0B 97 }

mbus0BVIF2E		OBJECT-TYPE
			SYNTAX	INTEGER
			ACCESS	read-only
			STATUS	current
	DESCRIPTION ""
			::= { mbus0B 98 }

mbus0BValue2E		OBJECT-TYPE
			SYNTAX	INTEGER
			ACCESS	read-only
			STATUS	current
	DESCRIPTION ""
			::= { mbus0B 99 }

mbus0BVIF2F		OBJECT-TYPE
			SYNTAX	INTEGER
			ACCESS	read-only
			STATUS	current
	DESCRIPTION ""
			::= { mbus0B 100 }

mbus0BValue2F		OBJECT-TYPE
			SYNTAX	INTEGER
			ACCESS	read-only
			STATUS	current
	DESCRIPTION ""
			::= { mbus0B 101 }

mbus0C			OBJECT IDENTIFIER ::= { mbus 12 }

mbus0CIdNumber		OBJECT-TYPE
			SYNTAX	Gauge
			ACCESS	read-only
			STATUS	current
	DESCRIPTION ""
			::= { mbus0C 1 }

mbus0CManufacturer	OBJECT-TYPE
			SYNTAX	Gauge
			ACCESS	read-only
			STATUS	current
	DESCRIPTION ""
			::= { mbus0C 2 }

mbus0CVersion		OBJECT-TYPE
			SYNTAX	Gauge
			ACCESS	read-only
			STATUS	current
	DESCRIPTION ""
			::= { mbus0C 3 }

mbus0CMedium		OBJECT-TYPE
			SYNTAX	Gauge
			ACCESS	read-only
			STATUS	current
	DESCRIPTION ""
			::= { mbus0C 4 }

mbus0CStatus		OBJECT-TYPE
			SYNTAX	Gauge
			ACCESS	read-only
			STATUS	current
	DESCRIPTION ""
			::= { mbus0C 5 }

mbus0CVIF00		OBJECT-TYPE
			SYNTAX	INTEGER
			ACCESS	read-only
			STATUS	current
	DESCRIPTION ""
			::= { mbus0C 6 }

mbus0CValue00		OBJECT-TYPE
			SYNTAX	INTEGER
			ACCESS	read-only
			STATUS	current
	DESCRIPTION ""
			::= { mbus0C 7 }

mbus0CVIF01		OBJECT-TYPE
			SYNTAX	INTEGER
			ACCESS	read-only
			STATUS	current
	DESCRIPTION ""
			::= { mbus0C 8 }

mbus0CValue01		OBJECT-TYPE
			SYNTAX	INTEGER
			ACCESS	read-only
			STATUS	current
	DESCRIPTION ""
			::= { mbus0C 9 }

mbus0CVIF02		OBJECT-TYPE
			SYNTAX	INTEGER
			ACCESS	read-only
			STATUS	current
	DESCRIPTION ""
			::= { mbus0C 10 }

mbus0CValue02		OBJECT-TYPE
			SYNTAX	INTEGER
			ACCESS	read-only
			STATUS	current
	DESCRIPTION ""
			::= { mbus0C 11 }

mbus0CVIF03		OBJECT-TYPE
			SYNTAX	INTEGER
			ACCESS	read-only
			STATUS	current
	DESCRIPTION ""
			::= { mbus0C 12 }

mbus0CValue03		OBJECT-TYPE
			SYNTAX	INTEGER
			ACCESS	read-only
			STATUS	current
	DESCRIPTION ""
			::= { mbus0C 13 }

mbus0CVIF04		OBJECT-TYPE
			SYNTAX	INTEGER
			ACCESS	read-only
			STATUS	current
	DESCRIPTION ""
			::= { mbus0C 14 }

mbus0CValue04		OBJECT-TYPE
			SYNTAX	INTEGER
			ACCESS	read-only
			STATUS	current
	DESCRIPTION ""
			::= { mbus0C 15 }

mbus0CVIF05		OBJECT-TYPE
			SYNTAX	INTEGER
			ACCESS	read-only
			STATUS	current
	DESCRIPTION ""
			::= { mbus0C 16 }

mbus0CValue05		OBJECT-TYPE
			SYNTAX	INTEGER
			ACCESS	read-only
			STATUS	current
	DESCRIPTION ""
			::= { mbus0C 17 }

mbus0CVIF06		OBJECT-TYPE
			SYNTAX	INTEGER
			ACCESS	read-only
			STATUS	current
	DESCRIPTION ""
			::= { mbus0C 18 }

mbus0CValue06		OBJECT-TYPE
			SYNTAX	INTEGER
			ACCESS	read-only
			STATUS	current
	DESCRIPTION ""
			::= { mbus0C 19 }

mbus0CVIF07		OBJECT-TYPE
			SYNTAX	INTEGER
			ACCESS	read-only
			STATUS	current
	DESCRIPTION ""
			::= { mbus0C 20 }

mbus0CValue07		OBJECT-TYPE
			SYNTAX	INTEGER
			ACCESS	read-only
			STATUS	current
	DESCRIPTION ""
			::= { mbus0C 21 }

mbus0CVIF08		OBJECT-TYPE
			SYNTAX	INTEGER
			ACCESS	read-only
			STATUS	current
	DESCRIPTION ""
			::= { mbus0C 22 }

mbus0CValue08		OBJECT-TYPE
			SYNTAX	INTEGER
			ACCESS	read-only
			STATUS	current
	DESCRIPTION ""
			::= { mbus0C 23 }

mbus0CVIF09		OBJECT-TYPE
			SYNTAX	INTEGER
			ACCESS	read-only
			STATUS	current
	DESCRIPTION ""
			::= { mbus0C 24 }

mbus0CValue09		OBJECT-TYPE
			SYNTAX	INTEGER
			ACCESS	read-only
			STATUS	current
	DESCRIPTION ""
			::= { mbus0C 25 }

mbus0CVIF0A		OBJECT-TYPE
			SYNTAX	INTEGER
			ACCESS	read-only
			STATUS	current
	DESCRIPTION ""
			::= { mbus0C 26 }

mbus0CValue0A		OBJECT-TYPE
			SYNTAX	INTEGER
			ACCESS	read-only
			STATUS	current
	DESCRIPTION ""
			::= { mbus0C 27 }

mbus0CVIF0B		OBJECT-TYPE
			SYNTAX	INTEGER
			ACCESS	read-only
			STATUS	current
	DESCRIPTION ""
			::= { mbus0C 28 }

mbus0CValue0B		OBJECT-TYPE
			SYNTAX	INTEGER
			ACCESS	read-only
			STATUS	current
	DESCRIPTION ""
			::= { mbus0C 29 }

mbus0CVIF0C		OBJECT-TYPE
			SYNTAX	INTEGER
			ACCESS	read-only
			STATUS	current
	DESCRIPTION ""
			::= { mbus0C 30 }

mbus0CValue0C		OBJECT-TYPE
			SYNTAX	INTEGER
			ACCESS	read-only
			STATUS	current
	DESCRIPTION ""
			::= { mbus0C 31 }

mbus0CVIF0D		OBJECT-TYPE
			SYNTAX	INTEGER
			ACCESS	read-only
			STATUS	current
	DESCRIPTION ""
			::= { mbus0C 32 }

mbus0CValue0D		OBJECT-TYPE
			SYNTAX	INTEGER
			ACCESS	read-only
			STATUS	current
	DESCRIPTION ""
			::= { mbus0C 33 }

mbus0CVIF0E		OBJECT-TYPE
			SYNTAX	INTEGER
			ACCESS	read-only
			STATUS	current
	DESCRIPTION ""
			::= { mbus0C 34 }

mbus0CValue0E		OBJECT-TYPE
			SYNTAX	INTEGER
			ACCESS	read-only
			STATUS	current
	DESCRIPTION ""
			::= { mbus0C 35 }

mbus0CVIF0F		OBJECT-TYPE
			SYNTAX	INTEGER
			ACCESS	read-only
			STATUS	current
	DESCRIPTION ""
			::= { mbus0C 36 }

mbus0CValue0F		OBJECT-TYPE
			SYNTAX	INTEGER
			ACCESS	read-only
			STATUS	current
	DESCRIPTION ""
			::= { mbus0C 37 }

mbus0CVIF10		OBJECT-TYPE
			SYNTAX	INTEGER
			ACCESS	read-only
			STATUS	current
	DESCRIPTION ""
			::= { mbus0C 38 }

mbus0CValue10		OBJECT-TYPE
			SYNTAX	INTEGER
			ACCESS	read-only
			STATUS	current
	DESCRIPTION ""
			::= { mbus0C 39 }

mbus0CVIF11		OBJECT-TYPE
			SYNTAX	INTEGER
			ACCESS	read-only
			STATUS	current
	DESCRIPTION ""
			::= { mbus0C 40 }

mbus0CValue11		OBJECT-TYPE
			SYNTAX	INTEGER
			ACCESS	read-only
			STATUS	current
	DESCRIPTION ""
			::= { mbus0C 41 }

mbus0CVIF12		OBJECT-TYPE
			SYNTAX	INTEGER
			ACCESS	read-only
			STATUS	current
	DESCRIPTION ""
			::= { mbus0C 42 }

mbus0CValue12		OBJECT-TYPE
			SYNTAX	INTEGER
			ACCESS	read-only
			STATUS	current
	DESCRIPTION ""
			::= { mbus0C 43 }

mbus0CVIF13		OBJECT-TYPE
			SYNTAX	INTEGER
			ACCESS	read-only
			STATUS	current
	DESCRIPTION ""
			::= { mbus0C 44 }

mbus0CValue13		OBJECT-TYPE
			SYNTAX	INTEGER
			ACCESS	read-only
			STATUS	current
	DESCRIPTION ""
			::= { mbus0C 45 }

mbus0CVIF14		OBJECT-TYPE
			SYNTAX	INTEGER
			ACCESS	read-only
			STATUS	current
	DESCRIPTION ""
			::= { mbus0C 46 }

mbus0CValue14		OBJECT-TYPE
			SYNTAX	INTEGER
			ACCESS	read-only
			STATUS	current
	DESCRIPTION ""
			::= { mbus0C 47 }

mbus0CVIF15		OBJECT-TYPE
			SYNTAX	INTEGER
			ACCESS	read-only
			STATUS	current
	DESCRIPTION ""
			::= { mbus0C 48 }

mbus0CValue15		OBJECT-TYPE
			SYNTAX	INTEGER
			ACCESS	read-only
			STATUS	current
	DESCRIPTION ""
			::= { mbus0C 49 }

mbus0CVIF16		OBJECT-TYPE
			SYNTAX	INTEGER
			ACCESS	read-only
			STATUS	current
	DESCRIPTION ""
			::= { mbus0C 50 }

mbus0CValue16		OBJECT-TYPE
			SYNTAX	INTEGER
			ACCESS	read-only
			STATUS	current
	DESCRIPTION ""
			::= { mbus0C 51 }

mbus0CVIF17		OBJECT-TYPE
			SYNTAX	INTEGER
			ACCESS	read-only
			STATUS	current
	DESCRIPTION ""
			::= { mbus0C 52 }

mbus0CValue17		OBJECT-TYPE
			SYNTAX	INTEGER
			ACCESS	read-only
			STATUS	current
	DESCRIPTION ""
			::= { mbus0C 53 }

mbus0CVIF18		OBJECT-TYPE
			SYNTAX	INTEGER
			ACCESS	read-only
			STATUS	current
	DESCRIPTION ""
			::= { mbus0C 54 }

mbus0CValue18		OBJECT-TYPE
			SYNTAX	INTEGER
			ACCESS	read-only
			STATUS	current
	DESCRIPTION ""
			::= { mbus0C 55 }

mbus0CVIF19		OBJECT-TYPE
			SYNTAX	INTEGER
			ACCESS	read-only
			STATUS	current
	DESCRIPTION ""
			::= { mbus0C 56 }

mbus0CValue19		OBJECT-TYPE
			SYNTAX	INTEGER
			ACCESS	read-only
			STATUS	current
	DESCRIPTION ""
			::= { mbus0C 57 }

mbus0CVIF1A		OBJECT-TYPE
			SYNTAX	INTEGER
			ACCESS	read-only
			STATUS	current
	DESCRIPTION ""
			::= { mbus0C 58 }

mbus0CValue1A		OBJECT-TYPE
			SYNTAX	INTEGER
			ACCESS	read-only
			STATUS	current
	DESCRIPTION ""
			::= { mbus0C 59 }

mbus0CVIF1B		OBJECT-TYPE
			SYNTAX	INTEGER
			ACCESS	read-only
			STATUS	current
	DESCRIPTION ""
			::= { mbus0C 60 }

mbus0CValue1B		OBJECT-TYPE
			SYNTAX	INTEGER
			ACCESS	read-only
			STATUS	current
	DESCRIPTION ""
			::= { mbus0C 61 }

mbus0CVIF1C		OBJECT-TYPE
			SYNTAX	INTEGER
			ACCESS	read-only
			STATUS	current
	DESCRIPTION ""
			::= { mbus0C 62 }

mbus0CValue1C		OBJECT-TYPE
			SYNTAX	INTEGER
			ACCESS	read-only
			STATUS	current
	DESCRIPTION ""
			::= { mbus0C 63 }

mbus0CVIF1D		OBJECT-TYPE
			SYNTAX	INTEGER
			ACCESS	read-only
			STATUS	current
	DESCRIPTION ""
			::= { mbus0C 64 }

mbus0CValue1D		OBJECT-TYPE
			SYNTAX	INTEGER
			ACCESS	read-only
			STATUS	current
	DESCRIPTION ""
			::= { mbus0C 65 }

mbus0CVIF1E		OBJECT-TYPE
			SYNTAX	INTEGER
			ACCESS	read-only
			STATUS	current
	DESCRIPTION ""
			::= { mbus0C 66 }

mbus0CValue1E		OBJECT-TYPE
			SYNTAX	INTEGER
			ACCESS	read-only
			STATUS	current
	DESCRIPTION ""
			::= { mbus0C 67 }

mbus0CVIF1F		OBJECT-TYPE
			SYNTAX	INTEGER
			ACCESS	read-only
			STATUS	current
	DESCRIPTION ""
			::= { mbus0C 68 }

mbus0CValue1F		OBJECT-TYPE
			SYNTAX	INTEGER
			ACCESS	read-only
			STATUS	current
	DESCRIPTION ""
			::= { mbus0C 69 }

mbus0CVIF20		OBJECT-TYPE
			SYNTAX	INTEGER
			ACCESS	read-only
			STATUS	current
	DESCRIPTION ""
			::= { mbus0C 70 }

mbus0CValue20		OBJECT-TYPE
			SYNTAX	INTEGER
			ACCESS	read-only
			STATUS	current
	DESCRIPTION ""
			::= { mbus0C 71 }

mbus0CVIF21		OBJECT-TYPE
			SYNTAX	INTEGER
			ACCESS	read-only
			STATUS	current
	DESCRIPTION ""
			::= { mbus0C 72 }

mbus0CValue21		OBJECT-TYPE
			SYNTAX	INTEGER
			ACCESS	read-only
			STATUS	current
	DESCRIPTION ""
			::= { mbus0C 73 }

mbus0CVIF22		OBJECT-TYPE
			SYNTAX	INTEGER
			ACCESS	read-only
			STATUS	current
	DESCRIPTION ""
			::= { mbus0C 74 }

mbus0CValue22		OBJECT-TYPE
			SYNTAX	INTEGER
			ACCESS	read-only
			STATUS	current
	DESCRIPTION ""
			::= { mbus0C 75 }

mbus0CVIF23		OBJECT-TYPE
			SYNTAX	INTEGER
			ACCESS	read-only
			STATUS	current
	DESCRIPTION ""
			::= { mbus0C 76 }

mbus0CValue23		OBJECT-TYPE
			SYNTAX	INTEGER
			ACCESS	read-only
			STATUS	current
	DESCRIPTION ""
			::= { mbus0C 77 }

mbus0CVIF24		OBJECT-TYPE
			SYNTAX	INTEGER
			ACCESS	read-only
			STATUS	current
	DESCRIPTION ""
			::= { mbus0C 78 }

mbus0CValue24		OBJECT-TYPE
			SYNTAX	INTEGER
			ACCESS	read-only
			STATUS	current
	DESCRIPTION ""
			::= { mbus0C 79 }

mbus0CVIF25		OBJECT-TYPE
			SYNTAX	INTEGER
			ACCESS	read-only
			STATUS	current
	DESCRIPTION ""
			::= { mbus0C 80 }

mbus0CValue25		OBJECT-TYPE
			SYNTAX	INTEGER
			ACCESS	read-only
			STATUS	current
	DESCRIPTION ""
			::= { mbus0C 81 }

mbus0CVIF26		OBJECT-TYPE
			SYNTAX	INTEGER
			ACCESS	read-only
			STATUS	current
	DESCRIPTION ""
			::= { mbus0C 82 }

mbus0CValue26		OBJECT-TYPE
			SYNTAX	INTEGER
			ACCESS	read-only
			STATUS	current
	DESCRIPTION ""
			::= { mbus0C 83 }

mbus0CVIF27		OBJECT-TYPE
			SYNTAX	INTEGER
			ACCESS	read-only
			STATUS	current
	DESCRIPTION ""
			::= { mbus0C 84 }

mbus0CValue27		OBJECT-TYPE
			SYNTAX	INTEGER
			ACCESS	read-only
			STATUS	current
	DESCRIPTION ""
			::= { mbus0C 85 }

mbus0CVIF28		OBJECT-TYPE
			SYNTAX	INTEGER
			ACCESS	read-only
			STATUS	current
	DESCRIPTION ""
			::= { mbus0C 86 }

mbus0CValue28		OBJECT-TYPE
			SYNTAX	INTEGER
			ACCESS	read-only
			STATUS	current
	DESCRIPTION ""
			::= { mbus0C 87 }

mbus0CVIF29		OBJECT-TYPE
			SYNTAX	INTEGER
			ACCESS	read-only
			STATUS	current
	DESCRIPTION ""
			::= { mbus0C 88 }

mbus0CValue29		OBJECT-TYPE
			SYNTAX	INTEGER
			ACCESS	read-only
			STATUS	current
	DESCRIPTION ""
			::= { mbus0C 89 }

mbus0CVIF2A		OBJECT-TYPE
			SYNTAX	INTEGER
			ACCESS	read-only
			STATUS	current
	DESCRIPTION ""
			::= { mbus0C 90 }

mbus0CValue2A		OBJECT-TYPE
			SYNTAX	INTEGER
			ACCESS	read-only
			STATUS	current
	DESCRIPTION ""
			::= { mbus0C 91 }

mbus0CVIF2B		OBJECT-TYPE
			SYNTAX	INTEGER
			ACCESS	read-only
			STATUS	current
	DESCRIPTION ""
			::= { mbus0C 92 }

mbus0CValue2B		OBJECT-TYPE
			SYNTAX	INTEGER
			ACCESS	read-only
			STATUS	current
	DESCRIPTION ""
			::= { mbus0C 93 }

mbus0CVIF2C		OBJECT-TYPE
			SYNTAX	INTEGER
			ACCESS	read-only
			STATUS	current
	DESCRIPTION ""
			::= { mbus0C 94 }

mbus0CValue2C		OBJECT-TYPE
			SYNTAX	INTEGER
			ACCESS	read-only
			STATUS	current
	DESCRIPTION ""
			::= { mbus0C 95 }

mbus0CVIF2D		OBJECT-TYPE
			SYNTAX	INTEGER
			ACCESS	read-only
			STATUS	current
	DESCRIPTION ""
			::= { mbus0C 96 }

mbus0CValue2D		OBJECT-TYPE
			SYNTAX	INTEGER
			ACCESS	read-only
			STATUS	current
	DESCRIPTION ""
			::= { mbus0C 97 }

mbus0CVIF2E		OBJECT-TYPE
			SYNTAX	INTEGER
			ACCESS	read-only
			STATUS	current
	DESCRIPTION ""
			::= { mbus0C 98 }

mbus0CValue2E		OBJECT-TYPE
			SYNTAX	INTEGER
			ACCESS	read-only
			STATUS	current
	DESCRIPTION ""
			::= { mbus0C 99 }

mbus0CVIF2F		OBJECT-TYPE
			SYNTAX	INTEGER
			ACCESS	read-only
			STATUS	current
	DESCRIPTION ""
			::= { mbus0C 100 }

mbus0CValue2F		OBJECT-TYPE
			SYNTAX	INTEGER
			ACCESS	read-only
			STATUS	current
	DESCRIPTION ""
			::= { mbus0C 101 }

mbus0D			OBJECT IDENTIFIER ::= { mbus 13 }

mbus0DIdNumber		OBJECT-TYPE
			SYNTAX	Gauge
			ACCESS	read-only
			STATUS	current
	DESCRIPTION ""
			::= { mbus0D 1 }

mbus0DManufacturer	OBJECT-TYPE
			SYNTAX	Gauge
			ACCESS	read-only
			STATUS	current
	DESCRIPTION ""
			::= { mbus0D 2 }

mbus0DVersion		OBJECT-TYPE
			SYNTAX	Gauge
			ACCESS	read-only
			STATUS	current
	DESCRIPTION ""
			::= { mbus0D 3 }

mbus0DMedium		OBJECT-TYPE
			SYNTAX	Gauge
			ACCESS	read-only
			STATUS	current
	DESCRIPTION ""
			::= { mbus0D 4 }

mbus0DStatus		OBJECT-TYPE
			SYNTAX	Gauge
			ACCESS	read-only
			STATUS	current
	DESCRIPTION ""
			::= { mbus0D 5 }

mbus0DVIF00		OBJECT-TYPE
			SYNTAX	INTEGER
			ACCESS	read-only
			STATUS	current
	DESCRIPTION ""
			::= { mbus0D 6 }

mbus0DValue00		OBJECT-TYPE
			SYNTAX	INTEGER
			ACCESS	read-only
			STATUS	current
	DESCRIPTION ""
			::= { mbus0D 7 }

mbus0DVIF01		OBJECT-TYPE
			SYNTAX	INTEGER
			ACCESS	read-only
			STATUS	current
	DESCRIPTION ""
			::= { mbus0D 8 }

mbus0DValue01		OBJECT-TYPE
			SYNTAX	INTEGER
			ACCESS	read-only
			STATUS	current
	DESCRIPTION ""
			::= { mbus0D 9 }

mbus0DVIF02		OBJECT-TYPE
			SYNTAX	INTEGER
			ACCESS	read-only
			STATUS	current
	DESCRIPTION ""
			::= { mbus0D 10 }

mbus0DValue02		OBJECT-TYPE
			SYNTAX	INTEGER
			ACCESS	read-only
			STATUS	current
	DESCRIPTION ""
			::= { mbus0D 11 }

mbus0DVIF03		OBJECT-TYPE
			SYNTAX	INTEGER
			ACCESS	read-only
			STATUS	current
	DESCRIPTION ""
			::= { mbus0D 12 }

mbus0DValue03		OBJECT-TYPE
			SYNTAX	INTEGER
			ACCESS	read-only
			STATUS	current
	DESCRIPTION ""
			::= { mbus0D 13 }

mbus0DVIF04		OBJECT-TYPE
			SYNTAX	INTEGER
			ACCESS	read-only
			STATUS	current
	DESCRIPTION ""
			::= { mbus0D 14 }

mbus0DValue04		OBJECT-TYPE
			SYNTAX	INTEGER
			ACCESS	read-only
			STATUS	current
	DESCRIPTION ""
			::= { mbus0D 15 }

mbus0DVIF05		OBJECT-TYPE
			SYNTAX	INTEGER
			ACCESS	read-only
			STATUS	current
	DESCRIPTION ""
			::= { mbus0D 16 }

mbus0DValue05		OBJECT-TYPE
			SYNTAX	INTEGER
			ACCESS	read-only
			STATUS	current
	DESCRIPTION ""
			::= { mbus0D 17 }

mbus0DVIF06		OBJECT-TYPE
			SYNTAX	INTEGER
			ACCESS	read-only
			STATUS	current
	DESCRIPTION ""
			::= { mbus0D 18 }

mbus0DValue06		OBJECT-TYPE
			SYNTAX	INTEGER
			ACCESS	read-only
			STATUS	current
	DESCRIPTION ""
			::= { mbus0D 19 }

mbus0DVIF07		OBJECT-TYPE
			SYNTAX	INTEGER
			ACCESS	read-only
			STATUS	current
	DESCRIPTION ""
			::= { mbus0D 20 }

mbus0DValue07		OBJECT-TYPE
			SYNTAX	INTEGER
			ACCESS	read-only
			STATUS	current
	DESCRIPTION ""
			::= { mbus0D 21 }

mbus0DVIF08		OBJECT-TYPE
			SYNTAX	INTEGER
			ACCESS	read-only
			STATUS	current
	DESCRIPTION ""
			::= { mbus0D 22 }

mbus0DValue08		OBJECT-TYPE
			SYNTAX	INTEGER
			ACCESS	read-only
			STATUS	current
	DESCRIPTION ""
			::= { mbus0D 23 }

mbus0DVIF09		OBJECT-TYPE
			SYNTAX	INTEGER
			ACCESS	read-only
			STATUS	current
	DESCRIPTION ""
			::= { mbus0D 24 }

mbus0DValue09		OBJECT-TYPE
			SYNTAX	INTEGER
			ACCESS	read-only
			STATUS	current
	DESCRIPTION ""
			::= { mbus0D 25 }

mbus0DVIF0A		OBJECT-TYPE
			SYNTAX	INTEGER
			ACCESS	read-only
			STATUS	current
	DESCRIPTION ""
			::= { mbus0D 26 }

mbus0DValue0A		OBJECT-TYPE
			SYNTAX	INTEGER
			ACCESS	read-only
			STATUS	current
	DESCRIPTION ""
			::= { mbus0D 27 }

mbus0DVIF0B		OBJECT-TYPE
			SYNTAX	INTEGER
			ACCESS	read-only
			STATUS	current
	DESCRIPTION ""
			::= { mbus0D 28 }

mbus0DValue0B		OBJECT-TYPE
			SYNTAX	INTEGER
			ACCESS	read-only
			STATUS	current
	DESCRIPTION ""
			::= { mbus0D 29 }

mbus0DVIF0C		OBJECT-TYPE
			SYNTAX	INTEGER
			ACCESS	read-only
			STATUS	current
	DESCRIPTION ""
			::= { mbus0D 30 }

mbus0DValue0C		OBJECT-TYPE
			SYNTAX	INTEGER
			ACCESS	read-only
			STATUS	current
	DESCRIPTION ""
			::= { mbus0D 31 }

mbus0DVIF0D		OBJECT-TYPE
			SYNTAX	INTEGER
			ACCESS	read-only
			STATUS	current
	DESCRIPTION ""
			::= { mbus0D 32 }

mbus0DValue0D		OBJECT-TYPE
			SYNTAX	INTEGER
			ACCESS	read-only
			STATUS	current
	DESCRIPTION ""
			::= { mbus0D 33 }

mbus0DVIF0E		OBJECT-TYPE
			SYNTAX	INTEGER
			ACCESS	read-only
			STATUS	current
	DESCRIPTION ""
			::= { mbus0D 34 }

mbus0DValue0E		OBJECT-TYPE
			SYNTAX	INTEGER
			ACCESS	read-only
			STATUS	current
	DESCRIPTION ""
			::= { mbus0D 35 }

mbus0DVIF0F		OBJECT-TYPE
			SYNTAX	INTEGER
			ACCESS	read-only
			STATUS	current
	DESCRIPTION ""
			::= { mbus0D 36 }

mbus0DValue0F		OBJECT-TYPE
			SYNTAX	INTEGER
			ACCESS	read-only
			STATUS	current
	DESCRIPTION ""
			::= { mbus0D 37 }

mbus0DVIF10		OBJECT-TYPE
			SYNTAX	INTEGER
			ACCESS	read-only
			STATUS	current
	DESCRIPTION ""
			::= { mbus0D 38 }

mbus0DValue10		OBJECT-TYPE
			SYNTAX	INTEGER
			ACCESS	read-only
			STATUS	current
	DESCRIPTION ""
			::= { mbus0D 39 }

mbus0DVIF11		OBJECT-TYPE
			SYNTAX	INTEGER
			ACCESS	read-only
			STATUS	current
	DESCRIPTION ""
			::= { mbus0D 40 }

mbus0DValue11		OBJECT-TYPE
			SYNTAX	INTEGER
			ACCESS	read-only
			STATUS	current
	DESCRIPTION ""
			::= { mbus0D 41 }

mbus0DVIF12		OBJECT-TYPE
			SYNTAX	INTEGER
			ACCESS	read-only
			STATUS	current
	DESCRIPTION ""
			::= { mbus0D 42 }

mbus0DValue12		OBJECT-TYPE
			SYNTAX	INTEGER
			ACCESS	read-only
			STATUS	current
	DESCRIPTION ""
			::= { mbus0D 43 }

mbus0DVIF13		OBJECT-TYPE
			SYNTAX	INTEGER
			ACCESS	read-only
			STATUS	current
	DESCRIPTION ""
			::= { mbus0D 44 }

mbus0DValue13		OBJECT-TYPE
			SYNTAX	INTEGER
			ACCESS	read-only
			STATUS	current
	DESCRIPTION ""
			::= { mbus0D 45 }

mbus0DVIF14		OBJECT-TYPE
			SYNTAX	INTEGER
			ACCESS	read-only
			STATUS	current
	DESCRIPTION ""
			::= { mbus0D 46 }

mbus0DValue14		OBJECT-TYPE
			SYNTAX	INTEGER
			ACCESS	read-only
			STATUS	current
	DESCRIPTION ""
			::= { mbus0D 47 }

mbus0DVIF15		OBJECT-TYPE
			SYNTAX	INTEGER
			ACCESS	read-only
			STATUS	current
	DESCRIPTION ""
			::= { mbus0D 48 }

mbus0DValue15		OBJECT-TYPE
			SYNTAX	INTEGER
			ACCESS	read-only
			STATUS	current
	DESCRIPTION ""
			::= { mbus0D 49 }

mbus0DVIF16		OBJECT-TYPE
			SYNTAX	INTEGER
			ACCESS	read-only
			STATUS	current
	DESCRIPTION ""
			::= { mbus0D 50 }

mbus0DValue16		OBJECT-TYPE
			SYNTAX	INTEGER
			ACCESS	read-only
			STATUS	current
	DESCRIPTION ""
			::= { mbus0D 51 }

mbus0DVIF17		OBJECT-TYPE
			SYNTAX	INTEGER
			ACCESS	read-only
			STATUS	current
	DESCRIPTION ""
			::= { mbus0D 52 }

mbus0DValue17		OBJECT-TYPE
			SYNTAX	INTEGER
			ACCESS	read-only
			STATUS	current
	DESCRIPTION ""
			::= { mbus0D 53 }

mbus0DVIF18		OBJECT-TYPE
			SYNTAX	INTEGER
			ACCESS	read-only
			STATUS	current
	DESCRIPTION ""
			::= { mbus0D 54 }

mbus0DValue18		OBJECT-TYPE
			SYNTAX	INTEGER
			ACCESS	read-only
			STATUS	current
	DESCRIPTION ""
			::= { mbus0D 55 }

mbus0DVIF19		OBJECT-TYPE
			SYNTAX	INTEGER
			ACCESS	read-only
			STATUS	current
	DESCRIPTION ""
			::= { mbus0D 56 }

mbus0DValue19		OBJECT-TYPE
			SYNTAX	INTEGER
			ACCESS	read-only
			STATUS	current
	DESCRIPTION ""
			::= { mbus0D 57 }

mbus0DVIF1A		OBJECT-TYPE
			SYNTAX	INTEGER
			ACCESS	read-only
			STATUS	current
	DESCRIPTION ""
			::= { mbus0D 58 }

mbus0DValue1A		OBJECT-TYPE
			SYNTAX	INTEGER
			ACCESS	read-only
			STATUS	current
	DESCRIPTION ""
			::= { mbus0D 59 }

mbus0DVIF1B		OBJECT-TYPE
			SYNTAX	INTEGER
			ACCESS	read-only
			STATUS	current
	DESCRIPTION ""
			::= { mbus0D 60 }

mbus0DValue1B		OBJECT-TYPE
			SYNTAX	INTEGER
			ACCESS	read-only
			STATUS	current
	DESCRIPTION ""
			::= { mbus0D 61 }

mbus0DVIF1C		OBJECT-TYPE
			SYNTAX	INTEGER
			ACCESS	read-only
			STATUS	current
	DESCRIPTION ""
			::= { mbus0D 62 }

mbus0DValue1C		OBJECT-TYPE
			SYNTAX	INTEGER
			ACCESS	read-only
			STATUS	current
	DESCRIPTION ""
			::= { mbus0D 63 }

mbus0DVIF1D		OBJECT-TYPE
			SYNTAX	INTEGER
			ACCESS	read-only
			STATUS	current
	DESCRIPTION ""
			::= { mbus0D 64 }

mbus0DValue1D		OBJECT-TYPE
			SYNTAX	INTEGER
			ACCESS	read-only
			STATUS	current
	DESCRIPTION ""
			::= { mbus0D 65 }

mbus0DVIF1E		OBJECT-TYPE
			SYNTAX	INTEGER
			ACCESS	read-only
			STATUS	current
	DESCRIPTION ""
			::= { mbus0D 66 }

mbus0DValue1E		OBJECT-TYPE
			SYNTAX	INTEGER
			ACCESS	read-only
			STATUS	current
	DESCRIPTION ""
			::= { mbus0D 67 }

mbus0DVIF1F		OBJECT-TYPE
			SYNTAX	INTEGER
			ACCESS	read-only
			STATUS	current
	DESCRIPTION ""
			::= { mbus0D 68 }

mbus0DValue1F		OBJECT-TYPE
			SYNTAX	INTEGER
			ACCESS	read-only
			STATUS	current
	DESCRIPTION ""
			::= { mbus0D 69 }

mbus0DVIF20		OBJECT-TYPE
			SYNTAX	INTEGER
			ACCESS	read-only
			STATUS	current
	DESCRIPTION ""
			::= { mbus0D 70 }

mbus0DValue20		OBJECT-TYPE
			SYNTAX	INTEGER
			ACCESS	read-only
			STATUS	current
	DESCRIPTION ""
			::= { mbus0D 71 }

mbus0DVIF21		OBJECT-TYPE
			SYNTAX	INTEGER
			ACCESS	read-only
			STATUS	current
	DESCRIPTION ""
			::= { mbus0D 72 }

mbus0DValue21		OBJECT-TYPE
			SYNTAX	INTEGER
			ACCESS	read-only
			STATUS	current
	DESCRIPTION ""
			::= { mbus0D 73 }

mbus0DVIF22		OBJECT-TYPE
			SYNTAX	INTEGER
			ACCESS	read-only
			STATUS	current
	DESCRIPTION ""
			::= { mbus0D 74 }

mbus0DValue22		OBJECT-TYPE
			SYNTAX	INTEGER
			ACCESS	read-only
			STATUS	current
	DESCRIPTION ""
			::= { mbus0D 75 }

mbus0DVIF23		OBJECT-TYPE
			SYNTAX	INTEGER
			ACCESS	read-only
			STATUS	current
	DESCRIPTION ""
			::= { mbus0D 76 }

mbus0DValue23		OBJECT-TYPE
			SYNTAX	INTEGER
			ACCESS	read-only
			STATUS	current
	DESCRIPTION ""
			::= { mbus0D 77 }

mbus0DVIF24		OBJECT-TYPE
			SYNTAX	INTEGER
			ACCESS	read-only
			STATUS	current
	DESCRIPTION ""
			::= { mbus0D 78 }

mbus0DValue24		OBJECT-TYPE
			SYNTAX	INTEGER
			ACCESS	read-only
			STATUS	current
	DESCRIPTION ""
			::= { mbus0D 79 }

mbus0DVIF25		OBJECT-TYPE
			SYNTAX	INTEGER
			ACCESS	read-only
			STATUS	current
	DESCRIPTION ""
			::= { mbus0D 80 }

mbus0DValue25		OBJECT-TYPE
			SYNTAX	INTEGER
			ACCESS	read-only
			STATUS	current
	DESCRIPTION ""
			::= { mbus0D 81 }

mbus0DVIF26		OBJECT-TYPE
			SYNTAX	INTEGER
			ACCESS	read-only
			STATUS	current
	DESCRIPTION ""
			::= { mbus0D 82 }

mbus0DValue26		OBJECT-TYPE
			SYNTAX	INTEGER
			ACCESS	read-only
			STATUS	current
	DESCRIPTION ""
			::= { mbus0D 83 }

mbus0DVIF27		OBJECT-TYPE
			SYNTAX	INTEGER
			ACCESS	read-only
			STATUS	current
	DESCRIPTION ""
			::= { mbus0D 84 }

mbus0DValue27		OBJECT-TYPE
			SYNTAX	INTEGER
			ACCESS	read-only
			STATUS	current
	DESCRIPTION ""
			::= { mbus0D 85 }

mbus0DVIF28		OBJECT-TYPE
			SYNTAX	INTEGER
			ACCESS	read-only
			STATUS	current
	DESCRIPTION ""
			::= { mbus0D 86 }

mbus0DValue28		OBJECT-TYPE
			SYNTAX	INTEGER
			ACCESS	read-only
			STATUS	current
	DESCRIPTION ""
			::= { mbus0D 87 }

mbus0DVIF29		OBJECT-TYPE
			SYNTAX	INTEGER
			ACCESS	read-only
			STATUS	current
	DESCRIPTION ""
			::= { mbus0D 88 }

mbus0DValue29		OBJECT-TYPE
			SYNTAX	INTEGER
			ACCESS	read-only
			STATUS	current
	DESCRIPTION ""
			::= { mbus0D 89 }

mbus0DVIF2A		OBJECT-TYPE
			SYNTAX	INTEGER
			ACCESS	read-only
			STATUS	current
	DESCRIPTION ""
			::= { mbus0D 90 }

mbus0DValue2A		OBJECT-TYPE
			SYNTAX	INTEGER
			ACCESS	read-only
			STATUS	current
	DESCRIPTION ""
			::= { mbus0D 91 }

mbus0DVIF2B		OBJECT-TYPE
			SYNTAX	INTEGER
			ACCESS	read-only
			STATUS	current
	DESCRIPTION ""
			::= { mbus0D 92 }

mbus0DValue2B		OBJECT-TYPE
			SYNTAX	INTEGER
			ACCESS	read-only
			STATUS	current
	DESCRIPTION ""
			::= { mbus0D 93 }

mbus0DVIF2C		OBJECT-TYPE
			SYNTAX	INTEGER
			ACCESS	read-only
			STATUS	current
	DESCRIPTION ""
			::= { mbus0D 94 }

mbus0DValue2C		OBJECT-TYPE
			SYNTAX	INTEGER
			ACCESS	read-only
			STATUS	current
	DESCRIPTION ""
			::= { mbus0D 95 }

mbus0DVIF2D		OBJECT-TYPE
			SYNTAX	INTEGER
			ACCESS	read-only
			STATUS	current
	DESCRIPTION ""
			::= { mbus0D 96 }

mbus0DValue2D		OBJECT-TYPE
			SYNTAX	INTEGER
			ACCESS	read-only
			STATUS	current
	DESCRIPTION ""
			::= { mbus0D 97 }

mbus0DVIF2E		OBJECT-TYPE
			SYNTAX	INTEGER
			ACCESS	read-only
			STATUS	current
	DESCRIPTION ""
			::= { mbus0D 98 }

mbus0DValue2E		OBJECT-TYPE
			SYNTAX	INTEGER
			ACCESS	read-only
			STATUS	current
	DESCRIPTION ""
			::= { mbus0D 99 }

mbus0DVIF2F		OBJECT-TYPE
			SYNTAX	INTEGER
			ACCESS	read-only
			STATUS	current
	DESCRIPTION ""
			::= { mbus0D 100 }

mbus0DValue2F		OBJECT-TYPE
			SYNTAX	INTEGER
			ACCESS	read-only
			STATUS	current
	DESCRIPTION ""
			::= { mbus0D 101 }

mbus0E			OBJECT IDENTIFIER ::= { mbus 14 }

mbus0EIdNumber		OBJECT-TYPE
			SYNTAX	Gauge
			ACCESS	read-only
			STATUS	current
	DESCRIPTION ""
			::= { mbus0E 1 }

mbus0EManufacturer	OBJECT-TYPE
			SYNTAX	Gauge
			ACCESS	read-only
			STATUS	current
	DESCRIPTION ""
			::= { mbus0E 2 }

mbus0EVersion		OBJECT-TYPE
			SYNTAX	Gauge
			ACCESS	read-only
			STATUS	current
	DESCRIPTION ""
			::= { mbus0E 3 }

mbus0EMedium		OBJECT-TYPE
			SYNTAX	Gauge
			ACCESS	read-only
			STATUS	current
	DESCRIPTION ""
			::= { mbus0E 4 }

mbus0EStatus		OBJECT-TYPE
			SYNTAX	Gauge
			ACCESS	read-only
			STATUS	current
	DESCRIPTION ""
			::= { mbus0E 5 }

mbus0EVIF00		OBJECT-TYPE
			SYNTAX	INTEGER
			ACCESS	read-only
			STATUS	current
	DESCRIPTION ""
			::= { mbus0E 6 }

mbus0EValue00		OBJECT-TYPE
			SYNTAX	INTEGER
			ACCESS	read-only
			STATUS	current
	DESCRIPTION ""
			::= { mbus0E 7 }

mbus0EVIF01		OBJECT-TYPE
			SYNTAX	INTEGER
			ACCESS	read-only
			STATUS	current
	DESCRIPTION ""
			::= { mbus0E 8 }

mbus0EValue01		OBJECT-TYPE
			SYNTAX	INTEGER
			ACCESS	read-only
			STATUS	current
	DESCRIPTION ""
			::= { mbus0E 9 }

mbus0EVIF02		OBJECT-TYPE
			SYNTAX	INTEGER
			ACCESS	read-only
			STATUS	current
	DESCRIPTION ""
			::= { mbus0E 10 }

mbus0EValue02		OBJECT-TYPE
			SYNTAX	INTEGER
			ACCESS	read-only
			STATUS	current
	DESCRIPTION ""
			::= { mbus0E 11 }

mbus0EVIF03		OBJECT-TYPE
			SYNTAX	INTEGER
			ACCESS	read-only
			STATUS	current
	DESCRIPTION ""
			::= { mbus0E 12 }

mbus0EValue03		OBJECT-TYPE
			SYNTAX	INTEGER
			ACCESS	read-only
			STATUS	current
	DESCRIPTION ""
			::= { mbus0E 13 }

mbus0EVIF04		OBJECT-TYPE
			SYNTAX	INTEGER
			ACCESS	read-only
			STATUS	current
	DESCRIPTION ""
			::= { mbus0E 14 }

mbus0EValue04		OBJECT-TYPE
			SYNTAX	INTEGER
			ACCESS	read-only
			STATUS	current
	DESCRIPTION ""
			::= { mbus0E 15 }

mbus0EVIF05		OBJECT-TYPE
			SYNTAX	INTEGER
			ACCESS	read-only
			STATUS	current
	DESCRIPTION ""
			::= { mbus0E 16 }

mbus0EValue05		OBJECT-TYPE
			SYNTAX	INTEGER
			ACCESS	read-only
			STATUS	current
	DESCRIPTION ""
			::= { mbus0E 17 }

mbus0EVIF06		OBJECT-TYPE
			SYNTAX	INTEGER
			ACCESS	read-only
			STATUS	current
	DESCRIPTION ""
			::= { mbus0E 18 }

mbus0EValue06		OBJECT-TYPE
			SYNTAX	INTEGER
			ACCESS	read-only
			STATUS	current
	DESCRIPTION ""
			::= { mbus0E 19 }

mbus0EVIF07		OBJECT-TYPE
			SYNTAX	INTEGER
			ACCESS	read-only
			STATUS	current
	DESCRIPTION ""
			::= { mbus0E 20 }

mbus0EValue07		OBJECT-TYPE
			SYNTAX	INTEGER
			ACCESS	read-only
			STATUS	current
	DESCRIPTION ""
			::= { mbus0E 21 }

mbus0EVIF08		OBJECT-TYPE
			SYNTAX	INTEGER
			ACCESS	read-only
			STATUS	current
	DESCRIPTION ""
			::= { mbus0E 22 }

mbus0EValue08		OBJECT-TYPE
			SYNTAX	INTEGER
			ACCESS	read-only
			STATUS	current
	DESCRIPTION ""
			::= { mbus0E 23 }

mbus0EVIF09		OBJECT-TYPE
			SYNTAX	INTEGER
			ACCESS	read-only
			STATUS	current
	DESCRIPTION ""
			::= { mbus0E 24 }

mbus0EValue09		OBJECT-TYPE
			SYNTAX	INTEGER
			ACCESS	read-only
			STATUS	current
	DESCRIPTION ""
			::= { mbus0E 25 }

mbus0EVIF0A		OBJECT-TYPE
			SYNTAX	INTEGER
			ACCESS	read-only
			STATUS	current
	DESCRIPTION ""
			::= { mbus0E 26 }

mbus0EValue0A		OBJECT-TYPE
			SYNTAX	INTEGER
			ACCESS	read-only
			STATUS	current
	DESCRIPTION ""
			::= { mbus0E 27 }

mbus0EVIF0B		OBJECT-TYPE
			SYNTAX	INTEGER
			ACCESS	read-only
			STATUS	current
	DESCRIPTION ""
			::= { mbus0E 28 }

mbus0EValue0B		OBJECT-TYPE
			SYNTAX	INTEGER
			ACCESS	read-only
			STATUS	current
	DESCRIPTION ""
			::= { mbus0E 29 }

mbus0EVIF0C		OBJECT-TYPE
			SYNTAX	INTEGER
			ACCESS	read-only
			STATUS	current
	DESCRIPTION ""
			::= { mbus0E 30 }

mbus0EValue0C		OBJECT-TYPE
			SYNTAX	INTEGER
			ACCESS	read-only
			STATUS	current
	DESCRIPTION ""
			::= { mbus0E 31 }

mbus0EVIF0D		OBJECT-TYPE
			SYNTAX	INTEGER
			ACCESS	read-only
			STATUS	current
	DESCRIPTION ""
			::= { mbus0E 32 }

mbus0EValue0D		OBJECT-TYPE
			SYNTAX	INTEGER
			ACCESS	read-only
			STATUS	current
	DESCRIPTION ""
			::= { mbus0E 33 }

mbus0EVIF0E		OBJECT-TYPE
			SYNTAX	INTEGER
			ACCESS	read-only
			STATUS	current
	DESCRIPTION ""
			::= { mbus0E 34 }

mbus0EValue0E		OBJECT-TYPE
			SYNTAX	INTEGER
			ACCESS	read-only
			STATUS	current
	DESCRIPTION ""
			::= { mbus0E 35 }

mbus0EVIF0F		OBJECT-TYPE
			SYNTAX	INTEGER
			ACCESS	read-only
			STATUS	current
	DESCRIPTION ""
			::= { mbus0E 36 }

mbus0EValue0F		OBJECT-TYPE
			SYNTAX	INTEGER
			ACCESS	read-only
			STATUS	current
	DESCRIPTION ""
			::= { mbus0E 37 }

mbus0EVIF10		OBJECT-TYPE
			SYNTAX	INTEGER
			ACCESS	read-only
			STATUS	current
	DESCRIPTION ""
			::= { mbus0E 38 }

mbus0EValue10		OBJECT-TYPE
			SYNTAX	INTEGER
			ACCESS	read-only
			STATUS	current
	DESCRIPTION ""
			::= { mbus0E 39 }

mbus0EVIF11		OBJECT-TYPE
			SYNTAX	INTEGER
			ACCESS	read-only
			STATUS	current
	DESCRIPTION ""
			::= { mbus0E 40 }

mbus0EValue11		OBJECT-TYPE
			SYNTAX	INTEGER
			ACCESS	read-only
			STATUS	current
	DESCRIPTION ""
			::= { mbus0E 41 }

mbus0EVIF12		OBJECT-TYPE
			SYNTAX	INTEGER
			ACCESS	read-only
			STATUS	current
	DESCRIPTION ""
			::= { mbus0E 42 }

mbus0EValue12		OBJECT-TYPE
			SYNTAX	INTEGER
			ACCESS	read-only
			STATUS	current
	DESCRIPTION ""
			::= { mbus0E 43 }

mbus0EVIF13		OBJECT-TYPE
			SYNTAX	INTEGER
			ACCESS	read-only
			STATUS	current
	DESCRIPTION ""
			::= { mbus0E 44 }

mbus0EValue13		OBJECT-TYPE
			SYNTAX	INTEGER
			ACCESS	read-only
			STATUS	current
	DESCRIPTION ""
			::= { mbus0E 45 }

mbus0EVIF14		OBJECT-TYPE
			SYNTAX	INTEGER
			ACCESS	read-only
			STATUS	current
	DESCRIPTION ""
			::= { mbus0E 46 }

mbus0EValue14		OBJECT-TYPE
			SYNTAX	INTEGER
			ACCESS	read-only
			STATUS	current
	DESCRIPTION ""
			::= { mbus0E 47 }

mbus0EVIF15		OBJECT-TYPE
			SYNTAX	INTEGER
			ACCESS	read-only
			STATUS	current
	DESCRIPTION ""
			::= { mbus0E 48 }

mbus0EValue15		OBJECT-TYPE
			SYNTAX	INTEGER
			ACCESS	read-only
			STATUS	current
	DESCRIPTION ""
			::= { mbus0E 49 }

mbus0EVIF16		OBJECT-TYPE
			SYNTAX	INTEGER
			ACCESS	read-only
			STATUS	current
	DESCRIPTION ""
			::= { mbus0E 50 }

mbus0EValue16		OBJECT-TYPE
			SYNTAX	INTEGER
			ACCESS	read-only
			STATUS	current
	DESCRIPTION ""
			::= { mbus0E 51 }

mbus0EVIF17		OBJECT-TYPE
			SYNTAX	INTEGER
			ACCESS	read-only
			STATUS	current
	DESCRIPTION ""
			::= { mbus0E 52 }

mbus0EValue17		OBJECT-TYPE
			SYNTAX	INTEGER
			ACCESS	read-only
			STATUS	current
	DESCRIPTION ""
			::= { mbus0E 53 }

mbus0EVIF18		OBJECT-TYPE
			SYNTAX	INTEGER
			ACCESS	read-only
			STATUS	current
	DESCRIPTION ""
			::= { mbus0E 54 }

mbus0EValue18		OBJECT-TYPE
			SYNTAX	INTEGER
			ACCESS	read-only
			STATUS	current
	DESCRIPTION ""
			::= { mbus0E 55 }

mbus0EVIF19		OBJECT-TYPE
			SYNTAX	INTEGER
			ACCESS	read-only
			STATUS	current
	DESCRIPTION ""
			::= { mbus0E 56 }

mbus0EValue19		OBJECT-TYPE
			SYNTAX	INTEGER
			ACCESS	read-only
			STATUS	current
	DESCRIPTION ""
			::= { mbus0E 57 }

mbus0EVIF1A		OBJECT-TYPE
			SYNTAX	INTEGER
			ACCESS	read-only
			STATUS	current
	DESCRIPTION ""
			::= { mbus0E 58 }

mbus0EValue1A		OBJECT-TYPE
			SYNTAX	INTEGER
			ACCESS	read-only
			STATUS	current
	DESCRIPTION ""
			::= { mbus0E 59 }

mbus0EVIF1B		OBJECT-TYPE
			SYNTAX	INTEGER
			ACCESS	read-only
			STATUS	current
	DESCRIPTION ""
			::= { mbus0E 60 }

mbus0EValue1B		OBJECT-TYPE
			SYNTAX	INTEGER
			ACCESS	read-only
			STATUS	current
	DESCRIPTION ""
			::= { mbus0E 61 }

mbus0EVIF1C		OBJECT-TYPE
			SYNTAX	INTEGER
			ACCESS	read-only
			STATUS	current
	DESCRIPTION ""
			::= { mbus0E 62 }

mbus0EValue1C		OBJECT-TYPE
			SYNTAX	INTEGER
			ACCESS	read-only
			STATUS	current
	DESCRIPTION ""
			::= { mbus0E 63 }

mbus0EVIF1D		OBJECT-TYPE
			SYNTAX	INTEGER
			ACCESS	read-only
			STATUS	current
	DESCRIPTION ""
			::= { mbus0E 64 }

mbus0EValue1D		OBJECT-TYPE
			SYNTAX	INTEGER
			ACCESS	read-only
			STATUS	current
	DESCRIPTION ""
			::= { mbus0E 65 }

mbus0EVIF1E		OBJECT-TYPE
			SYNTAX	INTEGER
			ACCESS	read-only
			STATUS	current
	DESCRIPTION ""
			::= { mbus0E 66 }

mbus0EValue1E		OBJECT-TYPE
			SYNTAX	INTEGER
			ACCESS	read-only
			STATUS	current
	DESCRIPTION ""
			::= { mbus0E 67 }

mbus0EVIF1F		OBJECT-TYPE
			SYNTAX	INTEGER
			ACCESS	read-only
			STATUS	current
	DESCRIPTION ""
			::= { mbus0E 68 }

mbus0EValue1F		OBJECT-TYPE
			SYNTAX	INTEGER
			ACCESS	read-only
			STATUS	current
	DESCRIPTION ""
			::= { mbus0E 69 }

mbus0EVIF20		OBJECT-TYPE
			SYNTAX	INTEGER
			ACCESS	read-only
			STATUS	current
	DESCRIPTION ""
			::= { mbus0E 70 }

mbus0EValue20		OBJECT-TYPE
			SYNTAX	INTEGER
			ACCESS	read-only
			STATUS	current
	DESCRIPTION ""
			::= { mbus0E 71 }

mbus0EVIF21		OBJECT-TYPE
			SYNTAX	INTEGER
			ACCESS	read-only
			STATUS	current
	DESCRIPTION ""
			::= { mbus0E 72 }

mbus0EValue21		OBJECT-TYPE
			SYNTAX	INTEGER
			ACCESS	read-only
			STATUS	current
	DESCRIPTION ""
			::= { mbus0E 73 }

mbus0EVIF22		OBJECT-TYPE
			SYNTAX	INTEGER
			ACCESS	read-only
			STATUS	current
	DESCRIPTION ""
			::= { mbus0E 74 }

mbus0EValue22		OBJECT-TYPE
			SYNTAX	INTEGER
			ACCESS	read-only
			STATUS	current
	DESCRIPTION ""
			::= { mbus0E 75 }

mbus0EVIF23		OBJECT-TYPE
			SYNTAX	INTEGER
			ACCESS	read-only
			STATUS	current
	DESCRIPTION ""
			::= { mbus0E 76 }

mbus0EValue23		OBJECT-TYPE
			SYNTAX	INTEGER
			ACCESS	read-only
			STATUS	current
	DESCRIPTION ""
			::= { mbus0E 77 }

mbus0EVIF24		OBJECT-TYPE
			SYNTAX	INTEGER
			ACCESS	read-only
			STATUS	current
	DESCRIPTION ""
			::= { mbus0E 78 }

mbus0EValue24		OBJECT-TYPE
			SYNTAX	INTEGER
			ACCESS	read-only
			STATUS	current
	DESCRIPTION ""
			::= { mbus0E 79 }

mbus0EVIF25		OBJECT-TYPE
			SYNTAX	INTEGER
			ACCESS	read-only
			STATUS	current
	DESCRIPTION ""
			::= { mbus0E 80 }

mbus0EValue25		OBJECT-TYPE
			SYNTAX	INTEGER
			ACCESS	read-only
			STATUS	current
	DESCRIPTION ""
			::= { mbus0E 81 }

mbus0EVIF26		OBJECT-TYPE
			SYNTAX	INTEGER
			ACCESS	read-only
			STATUS	current
	DESCRIPTION ""
			::= { mbus0E 82 }

mbus0EValue26		OBJECT-TYPE
			SYNTAX	INTEGER
			ACCESS	read-only
			STATUS	current
	DESCRIPTION ""
			::= { mbus0E 83 }

mbus0EVIF27		OBJECT-TYPE
			SYNTAX	INTEGER
			ACCESS	read-only
			STATUS	current
	DESCRIPTION ""
			::= { mbus0E 84 }

mbus0EValue27		OBJECT-TYPE
			SYNTAX	INTEGER
			ACCESS	read-only
			STATUS	current
	DESCRIPTION ""
			::= { mbus0E 85 }

mbus0EVIF28		OBJECT-TYPE
			SYNTAX	INTEGER
			ACCESS	read-only
			STATUS	current
	DESCRIPTION ""
			::= { mbus0E 86 }

mbus0EValue28		OBJECT-TYPE
			SYNTAX	INTEGER
			ACCESS	read-only
			STATUS	current
	DESCRIPTION ""
			::= { mbus0E 87 }

mbus0EVIF29		OBJECT-TYPE
			SYNTAX	INTEGER
			ACCESS	read-only
			STATUS	current
	DESCRIPTION ""
			::= { mbus0E 88 }

mbus0EValue29		OBJECT-TYPE
			SYNTAX	INTEGER
			ACCESS	read-only
			STATUS	current
	DESCRIPTION ""
			::= { mbus0E 89 }

mbus0EVIF2A		OBJECT-TYPE
			SYNTAX	INTEGER
			ACCESS	read-only
			STATUS	current
	DESCRIPTION ""
			::= { mbus0E 90 }

mbus0EValue2A		OBJECT-TYPE
			SYNTAX	INTEGER
			ACCESS	read-only
			STATUS	current
	DESCRIPTION ""
			::= { mbus0E 91 }

mbus0EVIF2B		OBJECT-TYPE
			SYNTAX	INTEGER
			ACCESS	read-only
			STATUS	current
	DESCRIPTION ""
			::= { mbus0E 92 }

mbus0EValue2B		OBJECT-TYPE
			SYNTAX	INTEGER
			ACCESS	read-only
			STATUS	current
	DESCRIPTION ""
			::= { mbus0E 93 }

mbus0EVIF2C		OBJECT-TYPE
			SYNTAX	INTEGER
			ACCESS	read-only
			STATUS	current
	DESCRIPTION ""
			::= { mbus0E 94 }

mbus0EValue2C		OBJECT-TYPE
			SYNTAX	INTEGER
			ACCESS	read-only
			STATUS	current
	DESCRIPTION ""
			::= { mbus0E 95 }

mbus0EVIF2D		OBJECT-TYPE
			SYNTAX	INTEGER
			ACCESS	read-only
			STATUS	current
	DESCRIPTION ""
			::= { mbus0E 96 }

mbus0EValue2D		OBJECT-TYPE
			SYNTAX	INTEGER
			ACCESS	read-only
			STATUS	current
	DESCRIPTION ""
			::= { mbus0E 97 }

mbus0EVIF2E		OBJECT-TYPE
			SYNTAX	INTEGER
			ACCESS	read-only
			STATUS	current
	DESCRIPTION ""
			::= { mbus0E 98 }

mbus0EValue2E		OBJECT-TYPE
			SYNTAX	INTEGER
			ACCESS	read-only
			STATUS	current
	DESCRIPTION ""
			::= { mbus0E 99 }

mbus0EVIF2F		OBJECT-TYPE
			SYNTAX	INTEGER
			ACCESS	read-only
			STATUS	current
	DESCRIPTION ""
			::= { mbus0E 100 }

mbus0EValue2F		OBJECT-TYPE
			SYNTAX	INTEGER
			ACCESS	read-only
			STATUS	current
	DESCRIPTION ""
			::= { mbus0E 101 }

mbus0F			OBJECT IDENTIFIER ::= { mbus 15 }

mbus0FIdNumber		OBJECT-TYPE
			SYNTAX	Gauge
			ACCESS	read-only
			STATUS	current
	DESCRIPTION ""
			::= { mbus0F 1 }

mbus0FManufacturer	OBJECT-TYPE
			SYNTAX	Gauge
			ACCESS	read-only
			STATUS	current
	DESCRIPTION ""
			::= { mbus0F 2 }

mbus0FVersion		OBJECT-TYPE
			SYNTAX	Gauge
			ACCESS	read-only
			STATUS	current
	DESCRIPTION ""
			::= { mbus0F 3 }

mbus0FMedium		OBJECT-TYPE
			SYNTAX	Gauge
			ACCESS	read-only
			STATUS	current
	DESCRIPTION ""
			::= { mbus0F 4 }

mbus0FStatus		OBJECT-TYPE
			SYNTAX	Gauge
			ACCESS	read-only
			STATUS	current
	DESCRIPTION ""
			::= { mbus0F 5 }

mbus0FVIF00		OBJECT-TYPE
			SYNTAX	INTEGER
			ACCESS	read-only
			STATUS	current
	DESCRIPTION ""
			::= { mbus0F 6 }

mbus0FValue00		OBJECT-TYPE
			SYNTAX	INTEGER
			ACCESS	read-only
			STATUS	current
	DESCRIPTION ""
			::= { mbus0F 7 }

mbus0FVIF01		OBJECT-TYPE
			SYNTAX	INTEGER
			ACCESS	read-only
			STATUS	current
	DESCRIPTION ""
			::= { mbus0F 8 }

mbus0FValue01		OBJECT-TYPE
			SYNTAX	INTEGER
			ACCESS	read-only
			STATUS	current
	DESCRIPTION ""
			::= { mbus0F 9 }

mbus0FVIF02		OBJECT-TYPE
			SYNTAX	INTEGER
			ACCESS	read-only
			STATUS	current
	DESCRIPTION ""
			::= { mbus0F 10 }

mbus0FValue02		OBJECT-TYPE
			SYNTAX	INTEGER
			ACCESS	read-only
			STATUS	current
	DESCRIPTION ""
			::= { mbus0F 11 }

mbus0FVIF03		OBJECT-TYPE
			SYNTAX	INTEGER
			ACCESS	read-only
			STATUS	current
	DESCRIPTION ""
			::= { mbus0F 12 }

mbus0FValue03		OBJECT-TYPE
			SYNTAX	INTEGER
			ACCESS	read-only
			STATUS	current
	DESCRIPTION ""
			::= { mbus0F 13 }

mbus0FVIF04		OBJECT-TYPE
			SYNTAX	INTEGER
			ACCESS	read-only
			STATUS	current
	DESCRIPTION ""
			::= { mbus0F 14 }

mbus0FValue04		OBJECT-TYPE
			SYNTAX	INTEGER
			ACCESS	read-only
			STATUS	current
	DESCRIPTION ""
			::= { mbus0F 15 }

mbus0FVIF05		OBJECT-TYPE
			SYNTAX	INTEGER
			ACCESS	read-only
			STATUS	current
	DESCRIPTION ""
			::= { mbus0F 16 }

mbus0FValue05		OBJECT-TYPE
			SYNTAX	INTEGER
			ACCESS	read-only
			STATUS	current
	DESCRIPTION ""
			::= { mbus0F 17 }

mbus0FVIF06		OBJECT-TYPE
			SYNTAX	INTEGER
			ACCESS	read-only
			STATUS	current
	DESCRIPTION ""
			::= { mbus0F 18 }

mbus0FValue06		OBJECT-TYPE
			SYNTAX	INTEGER
			ACCESS	read-only
			STATUS	current
	DESCRIPTION ""
			::= { mbus0F 19 }

mbus0FVIF07		OBJECT-TYPE
			SYNTAX	INTEGER
			ACCESS	read-only
			STATUS	current
	DESCRIPTION ""
			::= { mbus0F 20 }

mbus0FValue07		OBJECT-TYPE
			SYNTAX	INTEGER
			ACCESS	read-only
			STATUS	current
	DESCRIPTION ""
			::= { mbus0F 21 }

mbus0FVIF08		OBJECT-TYPE
			SYNTAX	INTEGER
			ACCESS	read-only
			STATUS	current
	DESCRIPTION ""
			::= { mbus0F 22 }

mbus0FValue08		OBJECT-TYPE
			SYNTAX	INTEGER
			ACCESS	read-only
			STATUS	current
	DESCRIPTION ""
			::= { mbus0F 23 }

mbus0FVIF09		OBJECT-TYPE
			SYNTAX	INTEGER
			ACCESS	read-only
			STATUS	current
	DESCRIPTION ""
			::= { mbus0F 24 }

mbus0FValue09		OBJECT-TYPE
			SYNTAX	INTEGER
			ACCESS	read-only
			STATUS	current
	DESCRIPTION ""
			::= { mbus0F 25 }

mbus0FVIF0A		OBJECT-TYPE
			SYNTAX	INTEGER
			ACCESS	read-only
			STATUS	current
	DESCRIPTION ""
			::= { mbus0F 26 }

mbus0FValue0A		OBJECT-TYPE
			SYNTAX	INTEGER
			ACCESS	read-only
			STATUS	current
	DESCRIPTION ""
			::= { mbus0F 27 }

mbus0FVIF0B		OBJECT-TYPE
			SYNTAX	INTEGER
			ACCESS	read-only
			STATUS	current
	DESCRIPTION ""
			::= { mbus0F 28 }

mbus0FValue0B		OBJECT-TYPE
			SYNTAX	INTEGER
			ACCESS	read-only
			STATUS	current
	DESCRIPTION ""
			::= { mbus0F 29 }

mbus0FVIF0C		OBJECT-TYPE
			SYNTAX	INTEGER
			ACCESS	read-only
			STATUS	current
	DESCRIPTION ""
			::= { mbus0F 30 }

mbus0FValue0C		OBJECT-TYPE
			SYNTAX	INTEGER
			ACCESS	read-only
			STATUS	current
	DESCRIPTION ""
			::= { mbus0F 31 }

mbus0FVIF0D		OBJECT-TYPE
			SYNTAX	INTEGER
			ACCESS	read-only
			STATUS	current
	DESCRIPTION ""
			::= { mbus0F 32 }

mbus0FValue0D		OBJECT-TYPE
			SYNTAX	INTEGER
			ACCESS	read-only
			STATUS	current
	DESCRIPTION ""
			::= { mbus0F 33 }

mbus0FVIF0E		OBJECT-TYPE
			SYNTAX	INTEGER
			ACCESS	read-only
			STATUS	current
	DESCRIPTION ""
			::= { mbus0F 34 }

mbus0FValue0E		OBJECT-TYPE
			SYNTAX	INTEGER
			ACCESS	read-only
			STATUS	current
	DESCRIPTION ""
			::= { mbus0F 35 }

mbus0FVIF0F		OBJECT-TYPE
			SYNTAX	INTEGER
			ACCESS	read-only
			STATUS	current
	DESCRIPTION ""
			::= { mbus0F 36 }

mbus0FValue0F		OBJECT-TYPE
			SYNTAX	INTEGER
			ACCESS	read-only
			STATUS	current
	DESCRIPTION ""
			::= { mbus0F 37 }

mbus0FVIF10		OBJECT-TYPE
			SYNTAX	INTEGER
			ACCESS	read-only
			STATUS	current
	DESCRIPTION ""
			::= { mbus0F 38 }

mbus0FValue10		OBJECT-TYPE
			SYNTAX	INTEGER
			ACCESS	read-only
			STATUS	current
	DESCRIPTION ""
			::= { mbus0F 39 }

mbus0FVIF11		OBJECT-TYPE
			SYNTAX	INTEGER
			ACCESS	read-only
			STATUS	current
	DESCRIPTION ""
			::= { mbus0F 40 }

mbus0FValue11		OBJECT-TYPE
			SYNTAX	INTEGER
			ACCESS	read-only
			STATUS	current
	DESCRIPTION ""
			::= { mbus0F 41 }

mbus0FVIF12		OBJECT-TYPE
			SYNTAX	INTEGER
			ACCESS	read-only
			STATUS	current
	DESCRIPTION ""
			::= { mbus0F 42 }

mbus0FValue12		OBJECT-TYPE
			SYNTAX	INTEGER
			ACCESS	read-only
			STATUS	current
	DESCRIPTION ""
			::= { mbus0F 43 }

mbus0FVIF13		OBJECT-TYPE
			SYNTAX	INTEGER
			ACCESS	read-only
			STATUS	current
	DESCRIPTION ""
			::= { mbus0F 44 }

mbus0FValue13		OBJECT-TYPE
			SYNTAX	INTEGER
			ACCESS	read-only
			STATUS	current
	DESCRIPTION ""
			::= { mbus0F 45 }

mbus0FVIF14		OBJECT-TYPE
			SYNTAX	INTEGER
			ACCESS	read-only
			STATUS	current
	DESCRIPTION ""
			::= { mbus0F 46 }

mbus0FValue14		OBJECT-TYPE
			SYNTAX	INTEGER
			ACCESS	read-only
			STATUS	current
	DESCRIPTION ""
			::= { mbus0F 47 }

mbus0FVIF15		OBJECT-TYPE
			SYNTAX	INTEGER
			ACCESS	read-only
			STATUS	current
	DESCRIPTION ""
			::= { mbus0F 48 }

mbus0FValue15		OBJECT-TYPE
			SYNTAX	INTEGER
			ACCESS	read-only
			STATUS	current
	DESCRIPTION ""
			::= { mbus0F 49 }

mbus0FVIF16		OBJECT-TYPE
			SYNTAX	INTEGER
			ACCESS	read-only
			STATUS	current
	DESCRIPTION ""
			::= { mbus0F 50 }

mbus0FValue16		OBJECT-TYPE
			SYNTAX	INTEGER
			ACCESS	read-only
			STATUS	current
	DESCRIPTION ""
			::= { mbus0F 51 }

mbus0FVIF17		OBJECT-TYPE
			SYNTAX	INTEGER
			ACCESS	read-only
			STATUS	current
	DESCRIPTION ""
			::= { mbus0F 52 }

mbus0FValue17		OBJECT-TYPE
			SYNTAX	INTEGER
			ACCESS	read-only
			STATUS	current
	DESCRIPTION ""
			::= { mbus0F 53 }

mbus0FVIF18		OBJECT-TYPE
			SYNTAX	INTEGER
			ACCESS	read-only
			STATUS	current
	DESCRIPTION ""
			::= { mbus0F 54 }

mbus0FValue18		OBJECT-TYPE
			SYNTAX	INTEGER
			ACCESS	read-only
			STATUS	current
	DESCRIPTION ""
			::= { mbus0F 55 }

mbus0FVIF19		OBJECT-TYPE
			SYNTAX	INTEGER
			ACCESS	read-only
			STATUS	current
	DESCRIPTION ""
			::= { mbus0F 56 }

mbus0FValue19		OBJECT-TYPE
			SYNTAX	INTEGER
			ACCESS	read-only
			STATUS	current
	DESCRIPTION ""
			::= { mbus0F 57 }

mbus0FVIF1A		OBJECT-TYPE
			SYNTAX	INTEGER
			ACCESS	read-only
			STATUS	current
	DESCRIPTION ""
			::= { mbus0F 58 }

mbus0FValue1A		OBJECT-TYPE
			SYNTAX	INTEGER
			ACCESS	read-only
			STATUS	current
	DESCRIPTION ""
			::= { mbus0F 59 }

mbus0FVIF1B		OBJECT-TYPE
			SYNTAX	INTEGER
			ACCESS	read-only
			STATUS	current
	DESCRIPTION ""
			::= { mbus0F 60 }

mbus0FValue1B		OBJECT-TYPE
			SYNTAX	INTEGER
			ACCESS	read-only
			STATUS	current
	DESCRIPTION ""
			::= { mbus0F 61 }

mbus0FVIF1C		OBJECT-TYPE
			SYNTAX	INTEGER
			ACCESS	read-only
			STATUS	current
	DESCRIPTION ""
			::= { mbus0F 62 }

mbus0FValue1C		OBJECT-TYPE
			SYNTAX	INTEGER
			ACCESS	read-only
			STATUS	current
	DESCRIPTION ""
			::= { mbus0F 63 }

mbus0FVIF1D		OBJECT-TYPE
			SYNTAX	INTEGER
			ACCESS	read-only
			STATUS	current
	DESCRIPTION ""
			::= { mbus0F 64 }

mbus0FValue1D		OBJECT-TYPE
			SYNTAX	INTEGER
			ACCESS	read-only
			STATUS	current
	DESCRIPTION ""
			::= { mbus0F 65 }

mbus0FVIF1E		OBJECT-TYPE
			SYNTAX	INTEGER
			ACCESS	read-only
			STATUS	current
	DESCRIPTION ""
			::= { mbus0F 66 }

mbus0FValue1E		OBJECT-TYPE
			SYNTAX	INTEGER
			ACCESS	read-only
			STATUS	current
	DESCRIPTION ""
			::= { mbus0F 67 }

mbus0FVIF1F		OBJECT-TYPE
			SYNTAX	INTEGER
			ACCESS	read-only
			STATUS	current
	DESCRIPTION ""
			::= { mbus0F 68 }

mbus0FValue1F		OBJECT-TYPE
			SYNTAX	INTEGER
			ACCESS	read-only
			STATUS	current
	DESCRIPTION ""
			::= { mbus0F 69 }

mbus0FVIF20		OBJECT-TYPE
			SYNTAX	INTEGER
			ACCESS	read-only
			STATUS	current
	DESCRIPTION ""
			::= { mbus0F 70 }

mbus0FValue20		OBJECT-TYPE
			SYNTAX	INTEGER
			ACCESS	read-only
			STATUS	current
	DESCRIPTION ""
			::= { mbus0F 71 }

mbus0FVIF21		OBJECT-TYPE
			SYNTAX	INTEGER
			ACCESS	read-only
			STATUS	current
	DESCRIPTION ""
			::= { mbus0F 72 }

mbus0FValue21		OBJECT-TYPE
			SYNTAX	INTEGER
			ACCESS	read-only
			STATUS	current
	DESCRIPTION ""
			::= { mbus0F 73 }

mbus0FVIF22		OBJECT-TYPE
			SYNTAX	INTEGER
			ACCESS	read-only
			STATUS	current
	DESCRIPTION ""
			::= { mbus0F 74 }

mbus0FValue22		OBJECT-TYPE
			SYNTAX	INTEGER
			ACCESS	read-only
			STATUS	current
	DESCRIPTION ""
			::= { mbus0F 75 }

mbus0FVIF23		OBJECT-TYPE
			SYNTAX	INTEGER
			ACCESS	read-only
			STATUS	current
	DESCRIPTION ""
			::= { mbus0F 76 }

mbus0FValue23		OBJECT-TYPE
			SYNTAX	INTEGER
			ACCESS	read-only
			STATUS	current
	DESCRIPTION ""
			::= { mbus0F 77 }

mbus0FVIF24		OBJECT-TYPE
			SYNTAX	INTEGER
			ACCESS	read-only
			STATUS	current
	DESCRIPTION ""
			::= { mbus0F 78 }

mbus0FValue24		OBJECT-TYPE
			SYNTAX	INTEGER
			ACCESS	read-only
			STATUS	current
	DESCRIPTION ""
			::= { mbus0F 79 }

mbus0FVIF25		OBJECT-TYPE
			SYNTAX	INTEGER
			ACCESS	read-only
			STATUS	current
	DESCRIPTION ""
			::= { mbus0F 80 }

mbus0FValue25		OBJECT-TYPE
			SYNTAX	INTEGER
			ACCESS	read-only
			STATUS	current
	DESCRIPTION ""
			::= { mbus0F 81 }

mbus0FVIF26		OBJECT-TYPE
			SYNTAX	INTEGER
			ACCESS	read-only
			STATUS	current
	DESCRIPTION ""
			::= { mbus0F 82 }

mbus0FValue26		OBJECT-TYPE
			SYNTAX	INTEGER
			ACCESS	read-only
			STATUS	current
	DESCRIPTION ""
			::= { mbus0F 83 }

mbus0FVIF27		OBJECT-TYPE
			SYNTAX	INTEGER
			ACCESS	read-only
			STATUS	current
	DESCRIPTION ""
			::= { mbus0F 84 }

mbus0FValue27		OBJECT-TYPE
			SYNTAX	INTEGER
			ACCESS	read-only
			STATUS	current
	DESCRIPTION ""
			::= { mbus0F 85 }

mbus0FVIF28		OBJECT-TYPE
			SYNTAX	INTEGER
			ACCESS	read-only
			STATUS	current
	DESCRIPTION ""
			::= { mbus0F 86 }

mbus0FValue28		OBJECT-TYPE
			SYNTAX	INTEGER
			ACCESS	read-only
			STATUS	current
	DESCRIPTION ""
			::= { mbus0F 87 }

mbus0FVIF29		OBJECT-TYPE
			SYNTAX	INTEGER
			ACCESS	read-only
			STATUS	current
	DESCRIPTION ""
			::= { mbus0F 88 }

mbus0FValue29		OBJECT-TYPE
			SYNTAX	INTEGER
			ACCESS	read-only
			STATUS	current
	DESCRIPTION ""
			::= { mbus0F 89 }

mbus0FVIF2A		OBJECT-TYPE
			SYNTAX	INTEGER
			ACCESS	read-only
			STATUS	current
	DESCRIPTION ""
			::= { mbus0F 90 }

mbus0FValue2A		OBJECT-TYPE
			SYNTAX	INTEGER
			ACCESS	read-only
			STATUS	current
	DESCRIPTION ""
			::= { mbus0F 91 }

mbus0FVIF2B		OBJECT-TYPE
			SYNTAX	INTEGER
			ACCESS	read-only
			STATUS	current
	DESCRIPTION ""
			::= { mbus0F 92 }

mbus0FValue2B		OBJECT-TYPE
			SYNTAX	INTEGER
			ACCESS	read-only
			STATUS	current
	DESCRIPTION ""
			::= { mbus0F 93 }

mbus0FVIF2C		OBJECT-TYPE
			SYNTAX	INTEGER
			ACCESS	read-only
			STATUS	current
	DESCRIPTION ""
			::= { mbus0F 94 }

mbus0FValue2C		OBJECT-TYPE
			SYNTAX	INTEGER
			ACCESS	read-only
			STATUS	current
	DESCRIPTION ""
			::= { mbus0F 95 }

mbus0FVIF2D		OBJECT-TYPE
			SYNTAX	INTEGER
			ACCESS	read-only
			STATUS	current
	DESCRIPTION ""
			::= { mbus0F 96 }

mbus0FValue2D		OBJECT-TYPE
			SYNTAX	INTEGER
			ACCESS	read-only
			STATUS	current
	DESCRIPTION ""
			::= { mbus0F 97 }

mbus0FVIF2E		OBJECT-TYPE
			SYNTAX	INTEGER
			ACCESS	read-only
			STATUS	current
	DESCRIPTION ""
			::= { mbus0F 98 }

mbus0FValue2E		OBJECT-TYPE
			SYNTAX	INTEGER
			ACCESS	read-only
			STATUS	current
	DESCRIPTION ""
			::= { mbus0F 99 }

mbus0FVIF2F		OBJECT-TYPE
			SYNTAX	INTEGER
			ACCESS	read-only
			STATUS	current
	DESCRIPTION ""
			::= { mbus0F 100 }

mbus0FValue2F		OBJECT-TYPE
			SYNTAX	INTEGER
			ACCESS	read-only
			STATUS	current
	DESCRIPTION ""
			::= { mbus0F 101 }

mbus10			OBJECT IDENTIFIER ::= { mbus 16 }

mbus10IdNumber		OBJECT-TYPE
			SYNTAX	Gauge
			ACCESS	read-only
			STATUS	current
	DESCRIPTION ""
			::= { mbus10 1 }

mbus10Manufacturer	OBJECT-TYPE
			SYNTAX	Gauge
			ACCESS	read-only
			STATUS	current
	DESCRIPTION ""
			::= { mbus10 2 }

mbus10Version		OBJECT-TYPE
			SYNTAX	Gauge
			ACCESS	read-only
			STATUS	current
	DESCRIPTION ""
			::= { mbus10 3 }

mbus10Medium		OBJECT-TYPE
			SYNTAX	Gauge
			ACCESS	read-only
			STATUS	current
	DESCRIPTION ""
			::= { mbus10 4 }

mbus10Status		OBJECT-TYPE
			SYNTAX	Gauge
			ACCESS	read-only
			STATUS	current
	DESCRIPTION ""
			::= { mbus10 5 }

mbus10VIF00		OBJECT-TYPE
			SYNTAX	INTEGER
			ACCESS	read-only
			STATUS	current
	DESCRIPTION ""
			::= { mbus10 6 }

mbus10Value00		OBJECT-TYPE
			SYNTAX	INTEGER
			ACCESS	read-only
			STATUS	current
	DESCRIPTION ""
			::= { mbus10 7 }

mbus10VIF01		OBJECT-TYPE
			SYNTAX	INTEGER
			ACCESS	read-only
			STATUS	current
	DESCRIPTION ""
			::= { mbus10 8 }

mbus10Value01		OBJECT-TYPE
			SYNTAX	INTEGER
			ACCESS	read-only
			STATUS	current
	DESCRIPTION ""
			::= { mbus10 9 }

mbus10VIF02		OBJECT-TYPE
			SYNTAX	INTEGER
			ACCESS	read-only
			STATUS	current
	DESCRIPTION ""
			::= { mbus10 10 }

mbus10Value02		OBJECT-TYPE
			SYNTAX	INTEGER
			ACCESS	read-only
			STATUS	current
	DESCRIPTION ""
			::= { mbus10 11 }

mbus10VIF03		OBJECT-TYPE
			SYNTAX	INTEGER
			ACCESS	read-only
			STATUS	current
	DESCRIPTION ""
			::= { mbus10 12 }

mbus10Value03		OBJECT-TYPE
			SYNTAX	INTEGER
			ACCESS	read-only
			STATUS	current
	DESCRIPTION ""
			::= { mbus10 13 }

mbus10VIF04		OBJECT-TYPE
			SYNTAX	INTEGER
			ACCESS	read-only
			STATUS	current
	DESCRIPTION ""
			::= { mbus10 14 }

mbus10Value04		OBJECT-TYPE
			SYNTAX	INTEGER
			ACCESS	read-only
			STATUS	current
	DESCRIPTION ""
			::= { mbus10 15 }

mbus10VIF05		OBJECT-TYPE
			SYNTAX	INTEGER
			ACCESS	read-only
			STATUS	current
	DESCRIPTION ""
			::= { mbus10 16 }

mbus10Value05		OBJECT-TYPE
			SYNTAX	INTEGER
			ACCESS	read-only
			STATUS	current
	DESCRIPTION ""
			::= { mbus10 17 }

mbus10VIF06		OBJECT-TYPE
			SYNTAX	INTEGER
			ACCESS	read-only
			STATUS	current
	DESCRIPTION ""
			::= { mbus10 18 }

mbus10Value06		OBJECT-TYPE
			SYNTAX	INTEGER
			ACCESS	read-only
			STATUS	current
	DESCRIPTION ""
			::= { mbus10 19 }

mbus10VIF07		OBJECT-TYPE
			SYNTAX	INTEGER
			ACCESS	read-only
			STATUS	current
	DESCRIPTION ""
			::= { mbus10 20 }

mbus10Value07		OBJECT-TYPE
			SYNTAX	INTEGER
			ACCESS	read-only
			STATUS	current
	DESCRIPTION ""
			::= { mbus10 21 }

mbus10VIF08		OBJECT-TYPE
			SYNTAX	INTEGER
			ACCESS	read-only
			STATUS	current
	DESCRIPTION ""
			::= { mbus10 22 }

mbus10Value08		OBJECT-TYPE
			SYNTAX	INTEGER
			ACCESS	read-only
			STATUS	current
	DESCRIPTION ""
			::= { mbus10 23 }

mbus10VIF09		OBJECT-TYPE
			SYNTAX	INTEGER
			ACCESS	read-only
			STATUS	current
	DESCRIPTION ""
			::= { mbus10 24 }

mbus10Value09		OBJECT-TYPE
			SYNTAX	INTEGER
			ACCESS	read-only
			STATUS	current
	DESCRIPTION ""
			::= { mbus10 25 }

mbus10VIF0A		OBJECT-TYPE
			SYNTAX	INTEGER
			ACCESS	read-only
			STATUS	current
	DESCRIPTION ""
			::= { mbus10 26 }

mbus10Value0A		OBJECT-TYPE
			SYNTAX	INTEGER
			ACCESS	read-only
			STATUS	current
	DESCRIPTION ""
			::= { mbus10 27 }

mbus10VIF0B		OBJECT-TYPE
			SYNTAX	INTEGER
			ACCESS	read-only
			STATUS	current
	DESCRIPTION ""
			::= { mbus10 28 }

mbus10Value0B		OBJECT-TYPE
			SYNTAX	INTEGER
			ACCESS	read-only
			STATUS	current
	DESCRIPTION ""
			::= { mbus10 29 }

mbus10VIF0C		OBJECT-TYPE
			SYNTAX	INTEGER
			ACCESS	read-only
			STATUS	current
	DESCRIPTION ""
			::= { mbus10 30 }

mbus10Value0C		OBJECT-TYPE
			SYNTAX	INTEGER
			ACCESS	read-only
			STATUS	current
	DESCRIPTION ""
			::= { mbus10 31 }

mbus10VIF0D		OBJECT-TYPE
			SYNTAX	INTEGER
			ACCESS	read-only
			STATUS	current
	DESCRIPTION ""
			::= { mbus10 32 }

mbus10Value0D		OBJECT-TYPE
			SYNTAX	INTEGER
			ACCESS	read-only
			STATUS	current
	DESCRIPTION ""
			::= { mbus10 33 }

mbus10VIF0E		OBJECT-TYPE
			SYNTAX	INTEGER
			ACCESS	read-only
			STATUS	current
	DESCRIPTION ""
			::= { mbus10 34 }

mbus10Value0E		OBJECT-TYPE
			SYNTAX	INTEGER
			ACCESS	read-only
			STATUS	current
	DESCRIPTION ""
			::= { mbus10 35 }

mbus10VIF0F		OBJECT-TYPE
			SYNTAX	INTEGER
			ACCESS	read-only
			STATUS	current
	DESCRIPTION ""
			::= { mbus10 36 }

mbus10Value0F		OBJECT-TYPE
			SYNTAX	INTEGER
			ACCESS	read-only
			STATUS	current
	DESCRIPTION ""
			::= { mbus10 37 }

mbus10VIF10		OBJECT-TYPE
			SYNTAX	INTEGER
			ACCESS	read-only
			STATUS	current
	DESCRIPTION ""
			::= { mbus10 38 }

mbus10Value10		OBJECT-TYPE
			SYNTAX	INTEGER
			ACCESS	read-only
			STATUS	current
	DESCRIPTION ""
			::= { mbus10 39 }

mbus10VIF11		OBJECT-TYPE
			SYNTAX	INTEGER
			ACCESS	read-only
			STATUS	current
	DESCRIPTION ""
			::= { mbus10 40 }

mbus10Value11		OBJECT-TYPE
			SYNTAX	INTEGER
			ACCESS	read-only
			STATUS	current
	DESCRIPTION ""
			::= { mbus10 41 }

mbus10VIF12		OBJECT-TYPE
			SYNTAX	INTEGER
			ACCESS	read-only
			STATUS	current
	DESCRIPTION ""
			::= { mbus10 42 }

mbus10Value12		OBJECT-TYPE
			SYNTAX	INTEGER
			ACCESS	read-only
			STATUS	current
	DESCRIPTION ""
			::= { mbus10 43 }

mbus10VIF13		OBJECT-TYPE
			SYNTAX	INTEGER
			ACCESS	read-only
			STATUS	current
	DESCRIPTION ""
			::= { mbus10 44 }

mbus10Value13		OBJECT-TYPE
			SYNTAX	INTEGER
			ACCESS	read-only
			STATUS	current
	DESCRIPTION ""
			::= { mbus10 45 }

mbus10VIF14		OBJECT-TYPE
			SYNTAX	INTEGER
			ACCESS	read-only
			STATUS	current
	DESCRIPTION ""
			::= { mbus10 46 }

mbus10Value14		OBJECT-TYPE
			SYNTAX	INTEGER
			ACCESS	read-only
			STATUS	current
	DESCRIPTION ""
			::= { mbus10 47 }

mbus10VIF15		OBJECT-TYPE
			SYNTAX	INTEGER
			ACCESS	read-only
			STATUS	current
	DESCRIPTION ""
			::= { mbus10 48 }

mbus10Value15		OBJECT-TYPE
			SYNTAX	INTEGER
			ACCESS	read-only
			STATUS	current
	DESCRIPTION ""
			::= { mbus10 49 }

mbus10VIF16		OBJECT-TYPE
			SYNTAX	INTEGER
			ACCESS	read-only
			STATUS	current
	DESCRIPTION ""
			::= { mbus10 50 }

mbus10Value16		OBJECT-TYPE
			SYNTAX	INTEGER
			ACCESS	read-only
			STATUS	current
	DESCRIPTION ""
			::= { mbus10 51 }

mbus10VIF17		OBJECT-TYPE
			SYNTAX	INTEGER
			ACCESS	read-only
			STATUS	current
	DESCRIPTION ""
			::= { mbus10 52 }

mbus10Value17		OBJECT-TYPE
			SYNTAX	INTEGER
			ACCESS	read-only
			STATUS	current
	DESCRIPTION ""
			::= { mbus10 53 }

mbus10VIF18		OBJECT-TYPE
			SYNTAX	INTEGER
			ACCESS	read-only
			STATUS	current
	DESCRIPTION ""
			::= { mbus10 54 }

mbus10Value18		OBJECT-TYPE
			SYNTAX	INTEGER
			ACCESS	read-only
			STATUS	current
	DESCRIPTION ""
			::= { mbus10 55 }

mbus10VIF19		OBJECT-TYPE
			SYNTAX	INTEGER
			ACCESS	read-only
			STATUS	current
	DESCRIPTION ""
			::= { mbus10 56 }

mbus10Value19		OBJECT-TYPE
			SYNTAX	INTEGER
			ACCESS	read-only
			STATUS	current
	DESCRIPTION ""
			::= { mbus10 57 }

mbus10VIF1A		OBJECT-TYPE
			SYNTAX	INTEGER
			ACCESS	read-only
			STATUS	current
	DESCRIPTION ""
			::= { mbus10 58 }

mbus10Value1A		OBJECT-TYPE
			SYNTAX	INTEGER
			ACCESS	read-only
			STATUS	current
	DESCRIPTION ""
			::= { mbus10 59 }

mbus10VIF1B		OBJECT-TYPE
			SYNTAX	INTEGER
			ACCESS	read-only
			STATUS	current
	DESCRIPTION ""
			::= { mbus10 60 }

mbus10Value1B		OBJECT-TYPE
			SYNTAX	INTEGER
			ACCESS	read-only
			STATUS	current
	DESCRIPTION ""
			::= { mbus10 61 }

mbus10VIF1C		OBJECT-TYPE
			SYNTAX	INTEGER
			ACCESS	read-only
			STATUS	current
	DESCRIPTION ""
			::= { mbus10 62 }

mbus10Value1C		OBJECT-TYPE
			SYNTAX	INTEGER
			ACCESS	read-only
			STATUS	current
	DESCRIPTION ""
			::= { mbus10 63 }

mbus10VIF1D		OBJECT-TYPE
			SYNTAX	INTEGER
			ACCESS	read-only
			STATUS	current
	DESCRIPTION ""
			::= { mbus10 64 }

mbus10Value1D		OBJECT-TYPE
			SYNTAX	INTEGER
			ACCESS	read-only
			STATUS	current
	DESCRIPTION ""
			::= { mbus10 65 }

mbus10VIF1E		OBJECT-TYPE
			SYNTAX	INTEGER
			ACCESS	read-only
			STATUS	current
	DESCRIPTION ""
			::= { mbus10 66 }

mbus10Value1E		OBJECT-TYPE
			SYNTAX	INTEGER
			ACCESS	read-only
			STATUS	current
	DESCRIPTION ""
			::= { mbus10 67 }

mbus10VIF1F		OBJECT-TYPE
			SYNTAX	INTEGER
			ACCESS	read-only
			STATUS	current
	DESCRIPTION ""
			::= { mbus10 68 }

mbus10Value1F		OBJECT-TYPE
			SYNTAX	INTEGER
			ACCESS	read-only
			STATUS	current
	DESCRIPTION ""
			::= { mbus10 69 }

mbus10VIF20		OBJECT-TYPE
			SYNTAX	INTEGER
			ACCESS	read-only
			STATUS	current
	DESCRIPTION ""
			::= { mbus10 70 }

mbus10Value20		OBJECT-TYPE
			SYNTAX	INTEGER
			ACCESS	read-only
			STATUS	current
	DESCRIPTION ""
			::= { mbus10 71 }

mbus10VIF21		OBJECT-TYPE
			SYNTAX	INTEGER
			ACCESS	read-only
			STATUS	current
	DESCRIPTION ""
			::= { mbus10 72 }

mbus10Value21		OBJECT-TYPE
			SYNTAX	INTEGER
			ACCESS	read-only
			STATUS	current
	DESCRIPTION ""
			::= { mbus10 73 }

mbus10VIF22		OBJECT-TYPE
			SYNTAX	INTEGER
			ACCESS	read-only
			STATUS	current
	DESCRIPTION ""
			::= { mbus10 74 }

mbus10Value22		OBJECT-TYPE
			SYNTAX	INTEGER
			ACCESS	read-only
			STATUS	current
	DESCRIPTION ""
			::= { mbus10 75 }

mbus10VIF23		OBJECT-TYPE
			SYNTAX	INTEGER
			ACCESS	read-only
			STATUS	current
	DESCRIPTION ""
			::= { mbus10 76 }

mbus10Value23		OBJECT-TYPE
			SYNTAX	INTEGER
			ACCESS	read-only
			STATUS	current
	DESCRIPTION ""
			::= { mbus10 77 }

mbus10VIF24		OBJECT-TYPE
			SYNTAX	INTEGER
			ACCESS	read-only
			STATUS	current
	DESCRIPTION ""
			::= { mbus10 78 }

mbus10Value24		OBJECT-TYPE
			SYNTAX	INTEGER
			ACCESS	read-only
			STATUS	current
	DESCRIPTION ""
			::= { mbus10 79 }

mbus10VIF25		OBJECT-TYPE
			SYNTAX	INTEGER
			ACCESS	read-only
			STATUS	current
	DESCRIPTION ""
			::= { mbus10 80 }

mbus10Value25		OBJECT-TYPE
			SYNTAX	INTEGER
			ACCESS	read-only
			STATUS	current
	DESCRIPTION ""
			::= { mbus10 81 }

mbus10VIF26		OBJECT-TYPE
			SYNTAX	INTEGER
			ACCESS	read-only
			STATUS	current
	DESCRIPTION ""
			::= { mbus10 82 }

mbus10Value26		OBJECT-TYPE
			SYNTAX	INTEGER
			ACCESS	read-only
			STATUS	current
	DESCRIPTION ""
			::= { mbus10 83 }

mbus10VIF27		OBJECT-TYPE
			SYNTAX	INTEGER
			ACCESS	read-only
			STATUS	current
	DESCRIPTION ""
			::= { mbus10 84 }

mbus10Value27		OBJECT-TYPE
			SYNTAX	INTEGER
			ACCESS	read-only
			STATUS	current
	DESCRIPTION ""
			::= { mbus10 85 }

mbus10VIF28		OBJECT-TYPE
			SYNTAX	INTEGER
			ACCESS	read-only
			STATUS	current
	DESCRIPTION ""
			::= { mbus10 86 }

mbus10Value28		OBJECT-TYPE
			SYNTAX	INTEGER
			ACCESS	read-only
			STATUS	current
	DESCRIPTION ""
			::= { mbus10 87 }

mbus10VIF29		OBJECT-TYPE
			SYNTAX	INTEGER
			ACCESS	read-only
			STATUS	current
	DESCRIPTION ""
			::= { mbus10 88 }

mbus10Value29		OBJECT-TYPE
			SYNTAX	INTEGER
			ACCESS	read-only
			STATUS	current
	DESCRIPTION ""
			::= { mbus10 89 }

mbus10VIF2A		OBJECT-TYPE
			SYNTAX	INTEGER
			ACCESS	read-only
			STATUS	current
	DESCRIPTION ""
			::= { mbus10 90 }

mbus10Value2A		OBJECT-TYPE
			SYNTAX	INTEGER
			ACCESS	read-only
			STATUS	current
	DESCRIPTION ""
			::= { mbus10 91 }

mbus10VIF2B		OBJECT-TYPE
			SYNTAX	INTEGER
			ACCESS	read-only
			STATUS	current
	DESCRIPTION ""
			::= { mbus10 92 }

mbus10Value2B		OBJECT-TYPE
			SYNTAX	INTEGER
			ACCESS	read-only
			STATUS	current
	DESCRIPTION ""
			::= { mbus10 93 }

mbus10VIF2C		OBJECT-TYPE
			SYNTAX	INTEGER
			ACCESS	read-only
			STATUS	current
	DESCRIPTION ""
			::= { mbus10 94 }

mbus10Value2C		OBJECT-TYPE
			SYNTAX	INTEGER
			ACCESS	read-only
			STATUS	current
	DESCRIPTION ""
			::= { mbus10 95 }

mbus10VIF2D		OBJECT-TYPE
			SYNTAX	INTEGER
			ACCESS	read-only
			STATUS	current
	DESCRIPTION ""
			::= { mbus10 96 }

mbus10Value2D		OBJECT-TYPE
			SYNTAX	INTEGER
			ACCESS	read-only
			STATUS	current
	DESCRIPTION ""
			::= { mbus10 97 }

mbus10VIF2E		OBJECT-TYPE
			SYNTAX	INTEGER
			ACCESS	read-only
			STATUS	current
	DESCRIPTION ""
			::= { mbus10 98 }

mbus10Value2E		OBJECT-TYPE
			SYNTAX	INTEGER
			ACCESS	read-only
			STATUS	current
	DESCRIPTION ""
			::= { mbus10 99 }

mbus10VIF2F		OBJECT-TYPE
			SYNTAX	INTEGER
			ACCESS	read-only
			STATUS	current
	DESCRIPTION ""
			::= { mbus10 100 }

mbus10Value2F		OBJECT-TYPE
			SYNTAX	INTEGER
			ACCESS	read-only
			STATUS	current
	DESCRIPTION ""
			::= { mbus10 101 }

mbus11			OBJECT IDENTIFIER ::= { mbus 17 }

mbus11IdNumber		OBJECT-TYPE
			SYNTAX	Gauge
			ACCESS	read-only
			STATUS	current
	DESCRIPTION ""
			::= { mbus11 1 }

mbus11Manufacturer	OBJECT-TYPE
			SYNTAX	Gauge
			ACCESS	read-only
			STATUS	current
	DESCRIPTION ""
			::= { mbus11 2 }

mbus11Version		OBJECT-TYPE
			SYNTAX	Gauge
			ACCESS	read-only
			STATUS	current
	DESCRIPTION ""
			::= { mbus11 3 }

mbus11Medium		OBJECT-TYPE
			SYNTAX	Gauge
			ACCESS	read-only
			STATUS	current
	DESCRIPTION ""
			::= { mbus11 4 }

mbus11Status		OBJECT-TYPE
			SYNTAX	Gauge
			ACCESS	read-only
			STATUS	current
	DESCRIPTION ""
			::= { mbus11 5 }

mbus11VIF00		OBJECT-TYPE
			SYNTAX	INTEGER
			ACCESS	read-only
			STATUS	current
	DESCRIPTION ""
			::= { mbus11 6 }

mbus11Value00		OBJECT-TYPE
			SYNTAX	INTEGER
			ACCESS	read-only
			STATUS	current
	DESCRIPTION ""
			::= { mbus11 7 }

mbus11VIF01		OBJECT-TYPE
			SYNTAX	INTEGER
			ACCESS	read-only
			STATUS	current
	DESCRIPTION ""
			::= { mbus11 8 }

mbus11Value01		OBJECT-TYPE
			SYNTAX	INTEGER
			ACCESS	read-only
			STATUS	current
	DESCRIPTION ""
			::= { mbus11 9 }

mbus11VIF02		OBJECT-TYPE
			SYNTAX	INTEGER
			ACCESS	read-only
			STATUS	current
	DESCRIPTION ""
			::= { mbus11 10 }

mbus11Value02		OBJECT-TYPE
			SYNTAX	INTEGER
			ACCESS	read-only
			STATUS	current
	DESCRIPTION ""
			::= { mbus11 11 }

mbus11VIF03		OBJECT-TYPE
			SYNTAX	INTEGER
			ACCESS	read-only
			STATUS	current
	DESCRIPTION ""
			::= { mbus11 12 }

mbus11Value03		OBJECT-TYPE
			SYNTAX	INTEGER
			ACCESS	read-only
			STATUS	current
	DESCRIPTION ""
			::= { mbus11 13 }

mbus11VIF04		OBJECT-TYPE
			SYNTAX	INTEGER
			ACCESS	read-only
			STATUS	current
	DESCRIPTION ""
			::= { mbus11 14 }

mbus11Value04		OBJECT-TYPE
			SYNTAX	INTEGER
			ACCESS	read-only
			STATUS	current
	DESCRIPTION ""
			::= { mbus11 15 }

mbus11VIF05		OBJECT-TYPE
			SYNTAX	INTEGER
			ACCESS	read-only
			STATUS	current
	DESCRIPTION ""
			::= { mbus11 16 }

mbus11Value05		OBJECT-TYPE
			SYNTAX	INTEGER
			ACCESS	read-only
			STATUS	current
	DESCRIPTION ""
			::= { mbus11 17 }

mbus11VIF06		OBJECT-TYPE
			SYNTAX	INTEGER
			ACCESS	read-only
			STATUS	current
	DESCRIPTION ""
			::= { mbus11 18 }

mbus11Value06		OBJECT-TYPE
			SYNTAX	INTEGER
			ACCESS	read-only
			STATUS	current
	DESCRIPTION ""
			::= { mbus11 19 }

mbus11VIF07		OBJECT-TYPE
			SYNTAX	INTEGER
			ACCESS	read-only
			STATUS	current
	DESCRIPTION ""
			::= { mbus11 20 }

mbus11Value07		OBJECT-TYPE
			SYNTAX	INTEGER
			ACCESS	read-only
			STATUS	current
	DESCRIPTION ""
			::= { mbus11 21 }

mbus11VIF08		OBJECT-TYPE
			SYNTAX	INTEGER
			ACCESS	read-only
			STATUS	current
	DESCRIPTION ""
			::= { mbus11 22 }

mbus11Value08		OBJECT-TYPE
			SYNTAX	INTEGER
			ACCESS	read-only
			STATUS	current
	DESCRIPTION ""
			::= { mbus11 23 }

mbus11VIF09		OBJECT-TYPE
			SYNTAX	INTEGER
			ACCESS	read-only
			STATUS	current
	DESCRIPTION ""
			::= { mbus11 24 }

mbus11Value09		OBJECT-TYPE
			SYNTAX	INTEGER
			ACCESS	read-only
			STATUS	current
	DESCRIPTION ""
			::= { mbus11 25 }

mbus11VIF0A		OBJECT-TYPE
			SYNTAX	INTEGER
			ACCESS	read-only
			STATUS	current
	DESCRIPTION ""
			::= { mbus11 26 }

mbus11Value0A		OBJECT-TYPE
			SYNTAX	INTEGER
			ACCESS	read-only
			STATUS	current
	DESCRIPTION ""
			::= { mbus11 27 }

mbus11VIF0B		OBJECT-TYPE
			SYNTAX	INTEGER
			ACCESS	read-only
			STATUS	current
	DESCRIPTION ""
			::= { mbus11 28 }

mbus11Value0B		OBJECT-TYPE
			SYNTAX	INTEGER
			ACCESS	read-only
			STATUS	current
	DESCRIPTION ""
			::= { mbus11 29 }

mbus11VIF0C		OBJECT-TYPE
			SYNTAX	INTEGER
			ACCESS	read-only
			STATUS	current
	DESCRIPTION ""
			::= { mbus11 30 }

mbus11Value0C		OBJECT-TYPE
			SYNTAX	INTEGER
			ACCESS	read-only
			STATUS	current
	DESCRIPTION ""
			::= { mbus11 31 }

mbus11VIF0D		OBJECT-TYPE
			SYNTAX	INTEGER
			ACCESS	read-only
			STATUS	current
	DESCRIPTION ""
			::= { mbus11 32 }

mbus11Value0D		OBJECT-TYPE
			SYNTAX	INTEGER
			ACCESS	read-only
			STATUS	current
	DESCRIPTION ""
			::= { mbus11 33 }

mbus11VIF0E		OBJECT-TYPE
			SYNTAX	INTEGER
			ACCESS	read-only
			STATUS	current
	DESCRIPTION ""
			::= { mbus11 34 }

mbus11Value0E		OBJECT-TYPE
			SYNTAX	INTEGER
			ACCESS	read-only
			STATUS	current
	DESCRIPTION ""
			::= { mbus11 35 }

mbus11VIF0F		OBJECT-TYPE
			SYNTAX	INTEGER
			ACCESS	read-only
			STATUS	current
	DESCRIPTION ""
			::= { mbus11 36 }

mbus11Value0F		OBJECT-TYPE
			SYNTAX	INTEGER
			ACCESS	read-only
			STATUS	current
	DESCRIPTION ""
			::= { mbus11 37 }

mbus11VIF10		OBJECT-TYPE
			SYNTAX	INTEGER
			ACCESS	read-only
			STATUS	current
	DESCRIPTION ""
			::= { mbus11 38 }

mbus11Value10		OBJECT-TYPE
			SYNTAX	INTEGER
			ACCESS	read-only
			STATUS	current
	DESCRIPTION ""
			::= { mbus11 39 }

mbus11VIF11		OBJECT-TYPE
			SYNTAX	INTEGER
			ACCESS	read-only
			STATUS	current
	DESCRIPTION ""
			::= { mbus11 40 }

mbus11Value11		OBJECT-TYPE
			SYNTAX	INTEGER
			ACCESS	read-only
			STATUS	current
	DESCRIPTION ""
			::= { mbus11 41 }

mbus11VIF12		OBJECT-TYPE
			SYNTAX	INTEGER
			ACCESS	read-only
			STATUS	current
	DESCRIPTION ""
			::= { mbus11 42 }

mbus11Value12		OBJECT-TYPE
			SYNTAX	INTEGER
			ACCESS	read-only
			STATUS	current
	DESCRIPTION ""
			::= { mbus11 43 }

mbus11VIF13		OBJECT-TYPE
			SYNTAX	INTEGER
			ACCESS	read-only
			STATUS	current
	DESCRIPTION ""
			::= { mbus11 44 }

mbus11Value13		OBJECT-TYPE
			SYNTAX	INTEGER
			ACCESS	read-only
			STATUS	current
	DESCRIPTION ""
			::= { mbus11 45 }

mbus11VIF14		OBJECT-TYPE
			SYNTAX	INTEGER
			ACCESS	read-only
			STATUS	current
	DESCRIPTION ""
			::= { mbus11 46 }

mbus11Value14		OBJECT-TYPE
			SYNTAX	INTEGER
			ACCESS	read-only
			STATUS	current
	DESCRIPTION ""
			::= { mbus11 47 }

mbus11VIF15		OBJECT-TYPE
			SYNTAX	INTEGER
			ACCESS	read-only
			STATUS	current
	DESCRIPTION ""
			::= { mbus11 48 }

mbus11Value15		OBJECT-TYPE
			SYNTAX	INTEGER
			ACCESS	read-only
			STATUS	current
	DESCRIPTION ""
			::= { mbus11 49 }

mbus11VIF16		OBJECT-TYPE
			SYNTAX	INTEGER
			ACCESS	read-only
			STATUS	current
	DESCRIPTION ""
			::= { mbus11 50 }

mbus11Value16		OBJECT-TYPE
			SYNTAX	INTEGER
			ACCESS	read-only
			STATUS	current
	DESCRIPTION ""
			::= { mbus11 51 }

mbus11VIF17		OBJECT-TYPE
			SYNTAX	INTEGER
			ACCESS	read-only
			STATUS	current
	DESCRIPTION ""
			::= { mbus11 52 }

mbus11Value17		OBJECT-TYPE
			SYNTAX	INTEGER
			ACCESS	read-only
			STATUS	current
	DESCRIPTION ""
			::= { mbus11 53 }

mbus11VIF18		OBJECT-TYPE
			SYNTAX	INTEGER
			ACCESS	read-only
			STATUS	current
	DESCRIPTION ""
			::= { mbus11 54 }

mbus11Value18		OBJECT-TYPE
			SYNTAX	INTEGER
			ACCESS	read-only
			STATUS	current
	DESCRIPTION ""
			::= { mbus11 55 }

mbus11VIF19		OBJECT-TYPE
			SYNTAX	INTEGER
			ACCESS	read-only
			STATUS	current
	DESCRIPTION ""
			::= { mbus11 56 }

mbus11Value19		OBJECT-TYPE
			SYNTAX	INTEGER
			ACCESS	read-only
			STATUS	current
	DESCRIPTION ""
			::= { mbus11 57 }

mbus11VIF1A		OBJECT-TYPE
			SYNTAX	INTEGER
			ACCESS	read-only
			STATUS	current
	DESCRIPTION ""
			::= { mbus11 58 }

mbus11Value1A		OBJECT-TYPE
			SYNTAX	INTEGER
			ACCESS	read-only
			STATUS	current
	DESCRIPTION ""
			::= { mbus11 59 }

mbus11VIF1B		OBJECT-TYPE
			SYNTAX	INTEGER
			ACCESS	read-only
			STATUS	current
	DESCRIPTION ""
			::= { mbus11 60 }

mbus11Value1B		OBJECT-TYPE
			SYNTAX	INTEGER
			ACCESS	read-only
			STATUS	current
	DESCRIPTION ""
			::= { mbus11 61 }

mbus11VIF1C		OBJECT-TYPE
			SYNTAX	INTEGER
			ACCESS	read-only
			STATUS	current
	DESCRIPTION ""
			::= { mbus11 62 }

mbus11Value1C		OBJECT-TYPE
			SYNTAX	INTEGER
			ACCESS	read-only
			STATUS	current
	DESCRIPTION ""
			::= { mbus11 63 }

mbus11VIF1D		OBJECT-TYPE
			SYNTAX	INTEGER
			ACCESS	read-only
			STATUS	current
	DESCRIPTION ""
			::= { mbus11 64 }

mbus11Value1D		OBJECT-TYPE
			SYNTAX	INTEGER
			ACCESS	read-only
			STATUS	current
	DESCRIPTION ""
			::= { mbus11 65 }

mbus11VIF1E		OBJECT-TYPE
			SYNTAX	INTEGER
			ACCESS	read-only
			STATUS	current
	DESCRIPTION ""
			::= { mbus11 66 }

mbus11Value1E		OBJECT-TYPE
			SYNTAX	INTEGER
			ACCESS	read-only
			STATUS	current
	DESCRIPTION ""
			::= { mbus11 67 }

mbus11VIF1F		OBJECT-TYPE
			SYNTAX	INTEGER
			ACCESS	read-only
			STATUS	current
	DESCRIPTION ""
			::= { mbus11 68 }

mbus11Value1F		OBJECT-TYPE
			SYNTAX	INTEGER
			ACCESS	read-only
			STATUS	current
	DESCRIPTION ""
			::= { mbus11 69 }

mbus11VIF20		OBJECT-TYPE
			SYNTAX	INTEGER
			ACCESS	read-only
			STATUS	current
	DESCRIPTION ""
			::= { mbus11 70 }

mbus11Value20		OBJECT-TYPE
			SYNTAX	INTEGER
			ACCESS	read-only
			STATUS	current
	DESCRIPTION ""
			::= { mbus11 71 }

mbus11VIF21		OBJECT-TYPE
			SYNTAX	INTEGER
			ACCESS	read-only
			STATUS	current
	DESCRIPTION ""
			::= { mbus11 72 }

mbus11Value21		OBJECT-TYPE
			SYNTAX	INTEGER
			ACCESS	read-only
			STATUS	current
	DESCRIPTION ""
			::= { mbus11 73 }

mbus11VIF22		OBJECT-TYPE
			SYNTAX	INTEGER
			ACCESS	read-only
			STATUS	current
	DESCRIPTION ""
			::= { mbus11 74 }

mbus11Value22		OBJECT-TYPE
			SYNTAX	INTEGER
			ACCESS	read-only
			STATUS	current
	DESCRIPTION ""
			::= { mbus11 75 }

mbus11VIF23		OBJECT-TYPE
			SYNTAX	INTEGER
			ACCESS	read-only
			STATUS	current
	DESCRIPTION ""
			::= { mbus11 76 }

mbus11Value23		OBJECT-TYPE
			SYNTAX	INTEGER
			ACCESS	read-only
			STATUS	current
	DESCRIPTION ""
			::= { mbus11 77 }

mbus11VIF24		OBJECT-TYPE
			SYNTAX	INTEGER
			ACCESS	read-only
			STATUS	current
	DESCRIPTION ""
			::= { mbus11 78 }

mbus11Value24		OBJECT-TYPE
			SYNTAX	INTEGER
			ACCESS	read-only
			STATUS	current
	DESCRIPTION ""
			::= { mbus11 79 }

mbus11VIF25		OBJECT-TYPE
			SYNTAX	INTEGER
			ACCESS	read-only
			STATUS	current
	DESCRIPTION ""
			::= { mbus11 80 }

mbus11Value25		OBJECT-TYPE
			SYNTAX	INTEGER
			ACCESS	read-only
			STATUS	current
	DESCRIPTION ""
			::= { mbus11 81 }

mbus11VIF26		OBJECT-TYPE
			SYNTAX	INTEGER
			ACCESS	read-only
			STATUS	current
	DESCRIPTION ""
			::= { mbus11 82 }

mbus11Value26		OBJECT-TYPE
			SYNTAX	INTEGER
			ACCESS	read-only
			STATUS	current
	DESCRIPTION ""
			::= { mbus11 83 }

mbus11VIF27		OBJECT-TYPE
			SYNTAX	INTEGER
			ACCESS	read-only
			STATUS	current
	DESCRIPTION ""
			::= { mbus11 84 }

mbus11Value27		OBJECT-TYPE
			SYNTAX	INTEGER
			ACCESS	read-only
			STATUS	current
	DESCRIPTION ""
			::= { mbus11 85 }

mbus11VIF28		OBJECT-TYPE
			SYNTAX	INTEGER
			ACCESS	read-only
			STATUS	current
	DESCRIPTION ""
			::= { mbus11 86 }

mbus11Value28		OBJECT-TYPE
			SYNTAX	INTEGER
			ACCESS	read-only
			STATUS	current
	DESCRIPTION ""
			::= { mbus11 87 }

mbus11VIF29		OBJECT-TYPE
			SYNTAX	INTEGER
			ACCESS	read-only
			STATUS	current
	DESCRIPTION ""
			::= { mbus11 88 }

mbus11Value29		OBJECT-TYPE
			SYNTAX	INTEGER
			ACCESS	read-only
			STATUS	current
	DESCRIPTION ""
			::= { mbus11 89 }

mbus11VIF2A		OBJECT-TYPE
			SYNTAX	INTEGER
			ACCESS	read-only
			STATUS	current
	DESCRIPTION ""
			::= { mbus11 90 }

mbus11Value2A		OBJECT-TYPE
			SYNTAX	INTEGER
			ACCESS	read-only
			STATUS	current
	DESCRIPTION ""
			::= { mbus11 91 }

mbus11VIF2B		OBJECT-TYPE
			SYNTAX	INTEGER
			ACCESS	read-only
			STATUS	current
	DESCRIPTION ""
			::= { mbus11 92 }

mbus11Value2B		OBJECT-TYPE
			SYNTAX	INTEGER
			ACCESS	read-only
			STATUS	current
	DESCRIPTION ""
			::= { mbus11 93 }

mbus11VIF2C		OBJECT-TYPE
			SYNTAX	INTEGER
			ACCESS	read-only
			STATUS	current
	DESCRIPTION ""
			::= { mbus11 94 }

mbus11Value2C		OBJECT-TYPE
			SYNTAX	INTEGER
			ACCESS	read-only
			STATUS	current
	DESCRIPTION ""
			::= { mbus11 95 }

mbus11VIF2D		OBJECT-TYPE
			SYNTAX	INTEGER
			ACCESS	read-only
			STATUS	current
	DESCRIPTION ""
			::= { mbus11 96 }

mbus11Value2D		OBJECT-TYPE
			SYNTAX	INTEGER
			ACCESS	read-only
			STATUS	current
	DESCRIPTION ""
			::= { mbus11 97 }

mbus11VIF2E		OBJECT-TYPE
			SYNTAX	INTEGER
			ACCESS	read-only
			STATUS	current
	DESCRIPTION ""
			::= { mbus11 98 }

mbus11Value2E		OBJECT-TYPE
			SYNTAX	INTEGER
			ACCESS	read-only
			STATUS	current
	DESCRIPTION ""
			::= { mbus11 99 }

mbus11VIF2F		OBJECT-TYPE
			SYNTAX	INTEGER
			ACCESS	read-only
			STATUS	current
	DESCRIPTION ""
			::= { mbus11 100 }

mbus11Value2F		OBJECT-TYPE
			SYNTAX	INTEGER
			ACCESS	read-only
			STATUS	current
	DESCRIPTION ""
			::= { mbus11 101 }

mbus12			OBJECT IDENTIFIER ::= { mbus 18 }

mbus12IdNumber		OBJECT-TYPE
			SYNTAX	Gauge
			ACCESS	read-only
			STATUS	current
	DESCRIPTION ""
			::= { mbus12 1 }

mbus12Manufacturer	OBJECT-TYPE
			SYNTAX	Gauge
			ACCESS	read-only
			STATUS	current
	DESCRIPTION ""
			::= { mbus12 2 }

mbus12Version		OBJECT-TYPE
			SYNTAX	Gauge
			ACCESS	read-only
			STATUS	current
	DESCRIPTION ""
			::= { mbus12 3 }

mbus12Medium		OBJECT-TYPE
			SYNTAX	Gauge
			ACCESS	read-only
			STATUS	current
	DESCRIPTION ""
			::= { mbus12 4 }

mbus12Status		OBJECT-TYPE
			SYNTAX	Gauge
			ACCESS	read-only
			STATUS	current
	DESCRIPTION ""
			::= { mbus12 5 }

mbus12VIF00		OBJECT-TYPE
			SYNTAX	INTEGER
			ACCESS	read-only
			STATUS	current
	DESCRIPTION ""
			::= { mbus12 6 }

mbus12Value00		OBJECT-TYPE
			SYNTAX	INTEGER
			ACCESS	read-only
			STATUS	current
	DESCRIPTION ""
			::= { mbus12 7 }

mbus12VIF01		OBJECT-TYPE
			SYNTAX	INTEGER
			ACCESS	read-only
			STATUS	current
	DESCRIPTION ""
			::= { mbus12 8 }

mbus12Value01		OBJECT-TYPE
			SYNTAX	INTEGER
			ACCESS	read-only
			STATUS	current
	DESCRIPTION ""
			::= { mbus12 9 }

mbus12VIF02		OBJECT-TYPE
			SYNTAX	INTEGER
			ACCESS	read-only
			STATUS	current
	DESCRIPTION ""
			::= { mbus12 10 }

mbus12Value02		OBJECT-TYPE
			SYNTAX	INTEGER
			ACCESS	read-only
			STATUS	current
	DESCRIPTION ""
			::= { mbus12 11 }

mbus12VIF03		OBJECT-TYPE
			SYNTAX	INTEGER
			ACCESS	read-only
			STATUS	current
	DESCRIPTION ""
			::= { mbus12 12 }

mbus12Value03		OBJECT-TYPE
			SYNTAX	INTEGER
			ACCESS	read-only
			STATUS	current
	DESCRIPTION ""
			::= { mbus12 13 }

mbus12VIF04		OBJECT-TYPE
			SYNTAX	INTEGER
			ACCESS	read-only
			STATUS	current
	DESCRIPTION ""
			::= { mbus12 14 }

mbus12Value04		OBJECT-TYPE
			SYNTAX	INTEGER
			ACCESS	read-only
			STATUS	current
	DESCRIPTION ""
			::= { mbus12 15 }

mbus12VIF05		OBJECT-TYPE
			SYNTAX	INTEGER
			ACCESS	read-only
			STATUS	current
	DESCRIPTION ""
			::= { mbus12 16 }

mbus12Value05		OBJECT-TYPE
			SYNTAX	INTEGER
			ACCESS	read-only
			STATUS	current
	DESCRIPTION ""
			::= { mbus12 17 }

mbus12VIF06		OBJECT-TYPE
			SYNTAX	INTEGER
			ACCESS	read-only
			STATUS	current
	DESCRIPTION ""
			::= { mbus12 18 }

mbus12Value06		OBJECT-TYPE
			SYNTAX	INTEGER
			ACCESS	read-only
			STATUS	current
	DESCRIPTION ""
			::= { mbus12 19 }

mbus12VIF07		OBJECT-TYPE
			SYNTAX	INTEGER
			ACCESS	read-only
			STATUS	current
	DESCRIPTION ""
			::= { mbus12 20 }

mbus12Value07		OBJECT-TYPE
			SYNTAX	INTEGER
			ACCESS	read-only
			STATUS	current
	DESCRIPTION ""
			::= { mbus12 21 }

mbus12VIF08		OBJECT-TYPE
			SYNTAX	INTEGER
			ACCESS	read-only
			STATUS	current
	DESCRIPTION ""
			::= { mbus12 22 }

mbus12Value08		OBJECT-TYPE
			SYNTAX	INTEGER
			ACCESS	read-only
			STATUS	current
	DESCRIPTION ""
			::= { mbus12 23 }

mbus12VIF09		OBJECT-TYPE
			SYNTAX	INTEGER
			ACCESS	read-only
			STATUS	current
	DESCRIPTION ""
			::= { mbus12 24 }

mbus12Value09		OBJECT-TYPE
			SYNTAX	INTEGER
			ACCESS	read-only
			STATUS	current
	DESCRIPTION ""
			::= { mbus12 25 }

mbus12VIF0A		OBJECT-TYPE
			SYNTAX	INTEGER
			ACCESS	read-only
			STATUS	current
	DESCRIPTION ""
			::= { mbus12 26 }

mbus12Value0A		OBJECT-TYPE
			SYNTAX	INTEGER
			ACCESS	read-only
			STATUS	current
	DESCRIPTION ""
			::= { mbus12 27 }

mbus12VIF0B		OBJECT-TYPE
			SYNTAX	INTEGER
			ACCESS	read-only
			STATUS	current
	DESCRIPTION ""
			::= { mbus12 28 }

mbus12Value0B		OBJECT-TYPE
			SYNTAX	INTEGER
			ACCESS	read-only
			STATUS	current
	DESCRIPTION ""
			::= { mbus12 29 }

mbus12VIF0C		OBJECT-TYPE
			SYNTAX	INTEGER
			ACCESS	read-only
			STATUS	current
	DESCRIPTION ""
			::= { mbus12 30 }

mbus12Value0C		OBJECT-TYPE
			SYNTAX	INTEGER
			ACCESS	read-only
			STATUS	current
	DESCRIPTION ""
			::= { mbus12 31 }

mbus12VIF0D		OBJECT-TYPE
			SYNTAX	INTEGER
			ACCESS	read-only
			STATUS	current
	DESCRIPTION ""
			::= { mbus12 32 }

mbus12Value0D		OBJECT-TYPE
			SYNTAX	INTEGER
			ACCESS	read-only
			STATUS	current
	DESCRIPTION ""
			::= { mbus12 33 }

mbus12VIF0E		OBJECT-TYPE
			SYNTAX	INTEGER
			ACCESS	read-only
			STATUS	current
	DESCRIPTION ""
			::= { mbus12 34 }

mbus12Value0E		OBJECT-TYPE
			SYNTAX	INTEGER
			ACCESS	read-only
			STATUS	current
	DESCRIPTION ""
			::= { mbus12 35 }

mbus12VIF0F		OBJECT-TYPE
			SYNTAX	INTEGER
			ACCESS	read-only
			STATUS	current
	DESCRIPTION ""
			::= { mbus12 36 }

mbus12Value0F		OBJECT-TYPE
			SYNTAX	INTEGER
			ACCESS	read-only
			STATUS	current
	DESCRIPTION ""
			::= { mbus12 37 }

mbus12VIF10		OBJECT-TYPE
			SYNTAX	INTEGER
			ACCESS	read-only
			STATUS	current
	DESCRIPTION ""
			::= { mbus12 38 }

mbus12Value10		OBJECT-TYPE
			SYNTAX	INTEGER
			ACCESS	read-only
			STATUS	current
	DESCRIPTION ""
			::= { mbus12 39 }

mbus12VIF11		OBJECT-TYPE
			SYNTAX	INTEGER
			ACCESS	read-only
			STATUS	current
	DESCRIPTION ""
			::= { mbus12 40 }

mbus12Value11		OBJECT-TYPE
			SYNTAX	INTEGER
			ACCESS	read-only
			STATUS	current
	DESCRIPTION ""
			::= { mbus12 41 }

mbus12VIF12		OBJECT-TYPE
			SYNTAX	INTEGER
			ACCESS	read-only
			STATUS	current
	DESCRIPTION ""
			::= { mbus12 42 }

mbus12Value12		OBJECT-TYPE
			SYNTAX	INTEGER
			ACCESS	read-only
			STATUS	current
	DESCRIPTION ""
			::= { mbus12 43 }

mbus12VIF13		OBJECT-TYPE
			SYNTAX	INTEGER
			ACCESS	read-only
			STATUS	current
	DESCRIPTION ""
			::= { mbus12 44 }

mbus12Value13		OBJECT-TYPE
			SYNTAX	INTEGER
			ACCESS	read-only
			STATUS	current
	DESCRIPTION ""
			::= { mbus12 45 }

mbus12VIF14		OBJECT-TYPE
			SYNTAX	INTEGER
			ACCESS	read-only
			STATUS	current
	DESCRIPTION ""
			::= { mbus12 46 }

mbus12Value14		OBJECT-TYPE
			SYNTAX	INTEGER
			ACCESS	read-only
			STATUS	current
	DESCRIPTION ""
			::= { mbus12 47 }

mbus12VIF15		OBJECT-TYPE
			SYNTAX	INTEGER
			ACCESS	read-only
			STATUS	current
	DESCRIPTION ""
			::= { mbus12 48 }

mbus12Value15		OBJECT-TYPE
			SYNTAX	INTEGER
			ACCESS	read-only
			STATUS	current
	DESCRIPTION ""
			::= { mbus12 49 }

mbus12VIF16		OBJECT-TYPE
			SYNTAX	INTEGER
			ACCESS	read-only
			STATUS	current
	DESCRIPTION ""
			::= { mbus12 50 }

mbus12Value16		OBJECT-TYPE
			SYNTAX	INTEGER
			ACCESS	read-only
			STATUS	current
	DESCRIPTION ""
			::= { mbus12 51 }

mbus12VIF17		OBJECT-TYPE
			SYNTAX	INTEGER
			ACCESS	read-only
			STATUS	current
	DESCRIPTION ""
			::= { mbus12 52 }

mbus12Value17		OBJECT-TYPE
			SYNTAX	INTEGER
			ACCESS	read-only
			STATUS	current
	DESCRIPTION ""
			::= { mbus12 53 }

mbus12VIF18		OBJECT-TYPE
			SYNTAX	INTEGER
			ACCESS	read-only
			STATUS	current
	DESCRIPTION ""
			::= { mbus12 54 }

mbus12Value18		OBJECT-TYPE
			SYNTAX	INTEGER
			ACCESS	read-only
			STATUS	current
	DESCRIPTION ""
			::= { mbus12 55 }

mbus12VIF19		OBJECT-TYPE
			SYNTAX	INTEGER
			ACCESS	read-only
			STATUS	current
	DESCRIPTION ""
			::= { mbus12 56 }

mbus12Value19		OBJECT-TYPE
			SYNTAX	INTEGER
			ACCESS	read-only
			STATUS	current
	DESCRIPTION ""
			::= { mbus12 57 }

mbus12VIF1A		OBJECT-TYPE
			SYNTAX	INTEGER
			ACCESS	read-only
			STATUS	current
	DESCRIPTION ""
			::= { mbus12 58 }

mbus12Value1A		OBJECT-TYPE
			SYNTAX	INTEGER
			ACCESS	read-only
			STATUS	current
	DESCRIPTION ""
			::= { mbus12 59 }

mbus12VIF1B		OBJECT-TYPE
			SYNTAX	INTEGER
			ACCESS	read-only
			STATUS	current
	DESCRIPTION ""
			::= { mbus12 60 }

mbus12Value1B		OBJECT-TYPE
			SYNTAX	INTEGER
			ACCESS	read-only
			STATUS	current
	DESCRIPTION ""
			::= { mbus12 61 }

mbus12VIF1C		OBJECT-TYPE
			SYNTAX	INTEGER
			ACCESS	read-only
			STATUS	current
	DESCRIPTION ""
			::= { mbus12 62 }

mbus12Value1C		OBJECT-TYPE
			SYNTAX	INTEGER
			ACCESS	read-only
			STATUS	current
	DESCRIPTION ""
			::= { mbus12 63 }

mbus12VIF1D		OBJECT-TYPE
			SYNTAX	INTEGER
			ACCESS	read-only
			STATUS	current
	DESCRIPTION ""
			::= { mbus12 64 }

mbus12Value1D		OBJECT-TYPE
			SYNTAX	INTEGER
			ACCESS	read-only
			STATUS	current
	DESCRIPTION ""
			::= { mbus12 65 }

mbus12VIF1E		OBJECT-TYPE
			SYNTAX	INTEGER
			ACCESS	read-only
			STATUS	current
	DESCRIPTION ""
			::= { mbus12 66 }

mbus12Value1E		OBJECT-TYPE
			SYNTAX	INTEGER
			ACCESS	read-only
			STATUS	current
	DESCRIPTION ""
			::= { mbus12 67 }

mbus12VIF1F		OBJECT-TYPE
			SYNTAX	INTEGER
			ACCESS	read-only
			STATUS	current
	DESCRIPTION ""
			::= { mbus12 68 }

mbus12Value1F		OBJECT-TYPE
			SYNTAX	INTEGER
			ACCESS	read-only
			STATUS	current
	DESCRIPTION ""
			::= { mbus12 69 }

mbus12VIF20		OBJECT-TYPE
			SYNTAX	INTEGER
			ACCESS	read-only
			STATUS	current
	DESCRIPTION ""
			::= { mbus12 70 }

mbus12Value20		OBJECT-TYPE
			SYNTAX	INTEGER
			ACCESS	read-only
			STATUS	current
	DESCRIPTION ""
			::= { mbus12 71 }

mbus12VIF21		OBJECT-TYPE
			SYNTAX	INTEGER
			ACCESS	read-only
			STATUS	current
	DESCRIPTION ""
			::= { mbus12 72 }

mbus12Value21		OBJECT-TYPE
			SYNTAX	INTEGER
			ACCESS	read-only
			STATUS	current
	DESCRIPTION ""
			::= { mbus12 73 }

mbus12VIF22		OBJECT-TYPE
			SYNTAX	INTEGER
			ACCESS	read-only
			STATUS	current
	DESCRIPTION ""
			::= { mbus12 74 }

mbus12Value22		OBJECT-TYPE
			SYNTAX	INTEGER
			ACCESS	read-only
			STATUS	current
	DESCRIPTION ""
			::= { mbus12 75 }

mbus12VIF23		OBJECT-TYPE
			SYNTAX	INTEGER
			ACCESS	read-only
			STATUS	current
	DESCRIPTION ""
			::= { mbus12 76 }

mbus12Value23		OBJECT-TYPE
			SYNTAX	INTEGER
			ACCESS	read-only
			STATUS	current
	DESCRIPTION ""
			::= { mbus12 77 }

mbus12VIF24		OBJECT-TYPE
			SYNTAX	INTEGER
			ACCESS	read-only
			STATUS	current
	DESCRIPTION ""
			::= { mbus12 78 }

mbus12Value24		OBJECT-TYPE
			SYNTAX	INTEGER
			ACCESS	read-only
			STATUS	current
	DESCRIPTION ""
			::= { mbus12 79 }

mbus12VIF25		OBJECT-TYPE
			SYNTAX	INTEGER
			ACCESS	read-only
			STATUS	current
	DESCRIPTION ""
			::= { mbus12 80 }

mbus12Value25		OBJECT-TYPE
			SYNTAX	INTEGER
			ACCESS	read-only
			STATUS	current
	DESCRIPTION ""
			::= { mbus12 81 }

mbus12VIF26		OBJECT-TYPE
			SYNTAX	INTEGER
			ACCESS	read-only
			STATUS	current
	DESCRIPTION ""
			::= { mbus12 82 }

mbus12Value26		OBJECT-TYPE
			SYNTAX	INTEGER
			ACCESS	read-only
			STATUS	current
	DESCRIPTION ""
			::= { mbus12 83 }

mbus12VIF27		OBJECT-TYPE
			SYNTAX	INTEGER
			ACCESS	read-only
			STATUS	current
	DESCRIPTION ""
			::= { mbus12 84 }

mbus12Value27		OBJECT-TYPE
			SYNTAX	INTEGER
			ACCESS	read-only
			STATUS	current
	DESCRIPTION ""
			::= { mbus12 85 }

mbus12VIF28		OBJECT-TYPE
			SYNTAX	INTEGER
			ACCESS	read-only
			STATUS	current
	DESCRIPTION ""
			::= { mbus12 86 }

mbus12Value28		OBJECT-TYPE
			SYNTAX	INTEGER
			ACCESS	read-only
			STATUS	current
	DESCRIPTION ""
			::= { mbus12 87 }

mbus12VIF29		OBJECT-TYPE
			SYNTAX	INTEGER
			ACCESS	read-only
			STATUS	current
	DESCRIPTION ""
			::= { mbus12 88 }

mbus12Value29		OBJECT-TYPE
			SYNTAX	INTEGER
			ACCESS	read-only
			STATUS	current
	DESCRIPTION ""
			::= { mbus12 89 }

mbus12VIF2A		OBJECT-TYPE
			SYNTAX	INTEGER
			ACCESS	read-only
			STATUS	current
	DESCRIPTION ""
			::= { mbus12 90 }

mbus12Value2A		OBJECT-TYPE
			SYNTAX	INTEGER
			ACCESS	read-only
			STATUS	current
	DESCRIPTION ""
			::= { mbus12 91 }

mbus12VIF2B		OBJECT-TYPE
			SYNTAX	INTEGER
			ACCESS	read-only
			STATUS	current
	DESCRIPTION ""
			::= { mbus12 92 }

mbus12Value2B		OBJECT-TYPE
			SYNTAX	INTEGER
			ACCESS	read-only
			STATUS	current
	DESCRIPTION ""
			::= { mbus12 93 }

mbus12VIF2C		OBJECT-TYPE
			SYNTAX	INTEGER
			ACCESS	read-only
			STATUS	current
	DESCRIPTION ""
			::= { mbus12 94 }

mbus12Value2C		OBJECT-TYPE
			SYNTAX	INTEGER
			ACCESS	read-only
			STATUS	current
	DESCRIPTION ""
			::= { mbus12 95 }

mbus12VIF2D		OBJECT-TYPE
			SYNTAX	INTEGER
			ACCESS	read-only
			STATUS	current
	DESCRIPTION ""
			::= { mbus12 96 }

mbus12Value2D		OBJECT-TYPE
			SYNTAX	INTEGER
			ACCESS	read-only
			STATUS	current
	DESCRIPTION ""
			::= { mbus12 97 }

mbus12VIF2E		OBJECT-TYPE
			SYNTAX	INTEGER
			ACCESS	read-only
			STATUS	current
	DESCRIPTION ""
			::= { mbus12 98 }

mbus12Value2E		OBJECT-TYPE
			SYNTAX	INTEGER
			ACCESS	read-only
			STATUS	current
	DESCRIPTION ""
			::= { mbus12 99 }

mbus12VIF2F		OBJECT-TYPE
			SYNTAX	INTEGER
			ACCESS	read-only
			STATUS	current
	DESCRIPTION ""
			::= { mbus12 100 }

mbus12Value2F		OBJECT-TYPE
			SYNTAX	INTEGER
			ACCESS	read-only
			STATUS	current
	DESCRIPTION ""
			::= { mbus12 101 }

mbus13			OBJECT IDENTIFIER ::= { mbus 19 }

mbus13IdNumber		OBJECT-TYPE
			SYNTAX	Gauge
			ACCESS	read-only
			STATUS	current
	DESCRIPTION ""
			::= { mbus13 1 }

mbus13Manufacturer	OBJECT-TYPE
			SYNTAX	Gauge
			ACCESS	read-only
			STATUS	current
	DESCRIPTION ""
			::= { mbus13 2 }

mbus13Version		OBJECT-TYPE
			SYNTAX	Gauge
			ACCESS	read-only
			STATUS	current
	DESCRIPTION ""
			::= { mbus13 3 }

mbus13Medium		OBJECT-TYPE
			SYNTAX	Gauge
			ACCESS	read-only
			STATUS	current
	DESCRIPTION ""
			::= { mbus13 4 }

mbus13Status		OBJECT-TYPE
			SYNTAX	Gauge
			ACCESS	read-only
			STATUS	current
	DESCRIPTION ""
			::= { mbus13 5 }

mbus13VIF00		OBJECT-TYPE
			SYNTAX	INTEGER
			ACCESS	read-only
			STATUS	current
	DESCRIPTION ""
			::= { mbus13 6 }

mbus13Value00		OBJECT-TYPE
			SYNTAX	INTEGER
			ACCESS	read-only
			STATUS	current
	DESCRIPTION ""
			::= { mbus13 7 }

mbus13VIF01		OBJECT-TYPE
			SYNTAX	INTEGER
			ACCESS	read-only
			STATUS	current
	DESCRIPTION ""
			::= { mbus13 8 }

mbus13Value01		OBJECT-TYPE
			SYNTAX	INTEGER
			ACCESS	read-only
			STATUS	current
	DESCRIPTION ""
			::= { mbus13 9 }

mbus13VIF02		OBJECT-TYPE
			SYNTAX	INTEGER
			ACCESS	read-only
			STATUS	current
	DESCRIPTION ""
			::= { mbus13 10 }

mbus13Value02		OBJECT-TYPE
			SYNTAX	INTEGER
			ACCESS	read-only
			STATUS	current
	DESCRIPTION ""
			::= { mbus13 11 }

mbus13VIF03		OBJECT-TYPE
			SYNTAX	INTEGER
			ACCESS	read-only
			STATUS	current
	DESCRIPTION ""
			::= { mbus13 12 }

mbus13Value03		OBJECT-TYPE
			SYNTAX	INTEGER
			ACCESS	read-only
			STATUS	current
	DESCRIPTION ""
			::= { mbus13 13 }

mbus13VIF04		OBJECT-TYPE
			SYNTAX	INTEGER
			ACCESS	read-only
			STATUS	current
	DESCRIPTION ""
			::= { mbus13 14 }

mbus13Value04		OBJECT-TYPE
			SYNTAX	INTEGER
			ACCESS	read-only
			STATUS	current
	DESCRIPTION ""
			::= { mbus13 15 }

mbus13VIF05		OBJECT-TYPE
			SYNTAX	INTEGER
			ACCESS	read-only
			STATUS	current
	DESCRIPTION ""
			::= { mbus13 16 }

mbus13Value05		OBJECT-TYPE
			SYNTAX	INTEGER
			ACCESS	read-only
			STATUS	current
	DESCRIPTION ""
			::= { mbus13 17 }

mbus13VIF06		OBJECT-TYPE
			SYNTAX	INTEGER
			ACCESS	read-only
			STATUS	current
	DESCRIPTION ""
			::= { mbus13 18 }

mbus13Value06		OBJECT-TYPE
			SYNTAX	INTEGER
			ACCESS	read-only
			STATUS	current
	DESCRIPTION ""
			::= { mbus13 19 }

mbus13VIF07		OBJECT-TYPE
			SYNTAX	INTEGER
			ACCESS	read-only
			STATUS	current
	DESCRIPTION ""
			::= { mbus13 20 }

mbus13Value07		OBJECT-TYPE
			SYNTAX	INTEGER
			ACCESS	read-only
			STATUS	current
	DESCRIPTION ""
			::= { mbus13 21 }

mbus13VIF08		OBJECT-TYPE
			SYNTAX	INTEGER
			ACCESS	read-only
			STATUS	current
	DESCRIPTION ""
			::= { mbus13 22 }

mbus13Value08		OBJECT-TYPE
			SYNTAX	INTEGER
			ACCESS	read-only
			STATUS	current
	DESCRIPTION ""
			::= { mbus13 23 }

mbus13VIF09		OBJECT-TYPE
			SYNTAX	INTEGER
			ACCESS	read-only
			STATUS	current
	DESCRIPTION ""
			::= { mbus13 24 }

mbus13Value09		OBJECT-TYPE
			SYNTAX	INTEGER
			ACCESS	read-only
			STATUS	current
	DESCRIPTION ""
			::= { mbus13 25 }

mbus13VIF0A		OBJECT-TYPE
			SYNTAX	INTEGER
			ACCESS	read-only
			STATUS	current
	DESCRIPTION ""
			::= { mbus13 26 }

mbus13Value0A		OBJECT-TYPE
			SYNTAX	INTEGER
			ACCESS	read-only
			STATUS	current
	DESCRIPTION ""
			::= { mbus13 27 }

mbus13VIF0B		OBJECT-TYPE
			SYNTAX	INTEGER
			ACCESS	read-only
			STATUS	current
	DESCRIPTION ""
			::= { mbus13 28 }

mbus13Value0B		OBJECT-TYPE
			SYNTAX	INTEGER
			ACCESS	read-only
			STATUS	current
	DESCRIPTION ""
			::= { mbus13 29 }

mbus13VIF0C		OBJECT-TYPE
			SYNTAX	INTEGER
			ACCESS	read-only
			STATUS	current
	DESCRIPTION ""
			::= { mbus13 30 }

mbus13Value0C		OBJECT-TYPE
			SYNTAX	INTEGER
			ACCESS	read-only
			STATUS	current
	DESCRIPTION ""
			::= { mbus13 31 }

mbus13VIF0D		OBJECT-TYPE
			SYNTAX	INTEGER
			ACCESS	read-only
			STATUS	current
	DESCRIPTION ""
			::= { mbus13 32 }

mbus13Value0D		OBJECT-TYPE
			SYNTAX	INTEGER
			ACCESS	read-only
			STATUS	current
	DESCRIPTION ""
			::= { mbus13 33 }

mbus13VIF0E		OBJECT-TYPE
			SYNTAX	INTEGER
			ACCESS	read-only
			STATUS	current
	DESCRIPTION ""
			::= { mbus13 34 }

mbus13Value0E		OBJECT-TYPE
			SYNTAX	INTEGER
			ACCESS	read-only
			STATUS	current
	DESCRIPTION ""
			::= { mbus13 35 }

mbus13VIF0F		OBJECT-TYPE
			SYNTAX	INTEGER
			ACCESS	read-only
			STATUS	current
	DESCRIPTION ""
			::= { mbus13 36 }

mbus13Value0F		OBJECT-TYPE
			SYNTAX	INTEGER
			ACCESS	read-only
			STATUS	current
	DESCRIPTION ""
			::= { mbus13 37 }

mbus13VIF10		OBJECT-TYPE
			SYNTAX	INTEGER
			ACCESS	read-only
			STATUS	current
	DESCRIPTION ""
			::= { mbus13 38 }

mbus13Value10		OBJECT-TYPE
			SYNTAX	INTEGER
			ACCESS	read-only
			STATUS	current
	DESCRIPTION ""
			::= { mbus13 39 }

mbus13VIF11		OBJECT-TYPE
			SYNTAX	INTEGER
			ACCESS	read-only
			STATUS	current
	DESCRIPTION ""
			::= { mbus13 40 }

mbus13Value11		OBJECT-TYPE
			SYNTAX	INTEGER
			ACCESS	read-only
			STATUS	current
	DESCRIPTION ""
			::= { mbus13 41 }

mbus13VIF12		OBJECT-TYPE
			SYNTAX	INTEGER
			ACCESS	read-only
			STATUS	current
	DESCRIPTION ""
			::= { mbus13 42 }

mbus13Value12		OBJECT-TYPE
			SYNTAX	INTEGER
			ACCESS	read-only
			STATUS	current
	DESCRIPTION ""
			::= { mbus13 43 }

mbus13VIF13		OBJECT-TYPE
			SYNTAX	INTEGER
			ACCESS	read-only
			STATUS	current
	DESCRIPTION ""
			::= { mbus13 44 }

mbus13Value13		OBJECT-TYPE
			SYNTAX	INTEGER
			ACCESS	read-only
			STATUS	current
	DESCRIPTION ""
			::= { mbus13 45 }

mbus13VIF14		OBJECT-TYPE
			SYNTAX	INTEGER
			ACCESS	read-only
			STATUS	current
	DESCRIPTION ""
			::= { mbus13 46 }

mbus13Value14		OBJECT-TYPE
			SYNTAX	INTEGER
			ACCESS	read-only
			STATUS	current
	DESCRIPTION ""
			::= { mbus13 47 }

mbus13VIF15		OBJECT-TYPE
			SYNTAX	INTEGER
			ACCESS	read-only
			STATUS	current
	DESCRIPTION ""
			::= { mbus13 48 }

mbus13Value15		OBJECT-TYPE
			SYNTAX	INTEGER
			ACCESS	read-only
			STATUS	current
	DESCRIPTION ""
			::= { mbus13 49 }

mbus13VIF16		OBJECT-TYPE
			SYNTAX	INTEGER
			ACCESS	read-only
			STATUS	current
	DESCRIPTION ""
			::= { mbus13 50 }

mbus13Value16		OBJECT-TYPE
			SYNTAX	INTEGER
			ACCESS	read-only
			STATUS	current
	DESCRIPTION ""
			::= { mbus13 51 }

mbus13VIF17		OBJECT-TYPE
			SYNTAX	INTEGER
			ACCESS	read-only
			STATUS	current
	DESCRIPTION ""
			::= { mbus13 52 }

mbus13Value17		OBJECT-TYPE
			SYNTAX	INTEGER
			ACCESS	read-only
			STATUS	current
	DESCRIPTION ""
			::= { mbus13 53 }

mbus13VIF18		OBJECT-TYPE
			SYNTAX	INTEGER
			ACCESS	read-only
			STATUS	current
	DESCRIPTION ""
			::= { mbus13 54 }

mbus13Value18		OBJECT-TYPE
			SYNTAX	INTEGER
			ACCESS	read-only
			STATUS	current
	DESCRIPTION ""
			::= { mbus13 55 }

mbus13VIF19		OBJECT-TYPE
			SYNTAX	INTEGER
			ACCESS	read-only
			STATUS	current
	DESCRIPTION ""
			::= { mbus13 56 }

mbus13Value19		OBJECT-TYPE
			SYNTAX	INTEGER
			ACCESS	read-only
			STATUS	current
	DESCRIPTION ""
			::= { mbus13 57 }

mbus13VIF1A		OBJECT-TYPE
			SYNTAX	INTEGER
			ACCESS	read-only
			STATUS	current
	DESCRIPTION ""
			::= { mbus13 58 }

mbus13Value1A		OBJECT-TYPE
			SYNTAX	INTEGER
			ACCESS	read-only
			STATUS	current
	DESCRIPTION ""
			::= { mbus13 59 }

mbus13VIF1B		OBJECT-TYPE
			SYNTAX	INTEGER
			ACCESS	read-only
			STATUS	current
	DESCRIPTION ""
			::= { mbus13 60 }

mbus13Value1B		OBJECT-TYPE
			SYNTAX	INTEGER
			ACCESS	read-only
			STATUS	current
	DESCRIPTION ""
			::= { mbus13 61 }

mbus13VIF1C		OBJECT-TYPE
			SYNTAX	INTEGER
			ACCESS	read-only
			STATUS	current
	DESCRIPTION ""
			::= { mbus13 62 }

mbus13Value1C		OBJECT-TYPE
			SYNTAX	INTEGER
			ACCESS	read-only
			STATUS	current
	DESCRIPTION ""
			::= { mbus13 63 }

mbus13VIF1D		OBJECT-TYPE
			SYNTAX	INTEGER
			ACCESS	read-only
			STATUS	current
	DESCRIPTION ""
			::= { mbus13 64 }

mbus13Value1D		OBJECT-TYPE
			SYNTAX	INTEGER
			ACCESS	read-only
			STATUS	current
	DESCRIPTION ""
			::= { mbus13 65 }

mbus13VIF1E		OBJECT-TYPE
			SYNTAX	INTEGER
			ACCESS	read-only
			STATUS	current
	DESCRIPTION ""
			::= { mbus13 66 }

mbus13Value1E		OBJECT-TYPE
			SYNTAX	INTEGER
			ACCESS	read-only
			STATUS	current
	DESCRIPTION ""
			::= { mbus13 67 }

mbus13VIF1F		OBJECT-TYPE
			SYNTAX	INTEGER
			ACCESS	read-only
			STATUS	current
	DESCRIPTION ""
			::= { mbus13 68 }

mbus13Value1F		OBJECT-TYPE
			SYNTAX	INTEGER
			ACCESS	read-only
			STATUS	current
	DESCRIPTION ""
			::= { mbus13 69 }

mbus13VIF20		OBJECT-TYPE
			SYNTAX	INTEGER
			ACCESS	read-only
			STATUS	current
	DESCRIPTION ""
			::= { mbus13 70 }

mbus13Value20		OBJECT-TYPE
			SYNTAX	INTEGER
			ACCESS	read-only
			STATUS	current
	DESCRIPTION ""
			::= { mbus13 71 }

mbus13VIF21		OBJECT-TYPE
			SYNTAX	INTEGER
			ACCESS	read-only
			STATUS	current
	DESCRIPTION ""
			::= { mbus13 72 }

mbus13Value21		OBJECT-TYPE
			SYNTAX	INTEGER
			ACCESS	read-only
			STATUS	current
	DESCRIPTION ""
			::= { mbus13 73 }

mbus13VIF22		OBJECT-TYPE
			SYNTAX	INTEGER
			ACCESS	read-only
			STATUS	current
	DESCRIPTION ""
			::= { mbus13 74 }

mbus13Value22		OBJECT-TYPE
			SYNTAX	INTEGER
			ACCESS	read-only
			STATUS	current
	DESCRIPTION ""
			::= { mbus13 75 }

mbus13VIF23		OBJECT-TYPE
			SYNTAX	INTEGER
			ACCESS	read-only
			STATUS	current
	DESCRIPTION ""
			::= { mbus13 76 }

mbus13Value23		OBJECT-TYPE
			SYNTAX	INTEGER
			ACCESS	read-only
			STATUS	current
	DESCRIPTION ""
			::= { mbus13 77 }

mbus13VIF24		OBJECT-TYPE
			SYNTAX	INTEGER
			ACCESS	read-only
			STATUS	current
	DESCRIPTION ""
			::= { mbus13 78 }

mbus13Value24		OBJECT-TYPE
			SYNTAX	INTEGER
			ACCESS	read-only
			STATUS	current
	DESCRIPTION ""
			::= { mbus13 79 }

mbus13VIF25		OBJECT-TYPE
			SYNTAX	INTEGER
			ACCESS	read-only
			STATUS	current
	DESCRIPTION ""
			::= { mbus13 80 }

mbus13Value25		OBJECT-TYPE
			SYNTAX	INTEGER
			ACCESS	read-only
			STATUS	current
	DESCRIPTION ""
			::= { mbus13 81 }

mbus13VIF26		OBJECT-TYPE
			SYNTAX	INTEGER
			ACCESS	read-only
			STATUS	current
	DESCRIPTION ""
			::= { mbus13 82 }

mbus13Value26		OBJECT-TYPE
			SYNTAX	INTEGER
			ACCESS	read-only
			STATUS	current
	DESCRIPTION ""
			::= { mbus13 83 }

mbus13VIF27		OBJECT-TYPE
			SYNTAX	INTEGER
			ACCESS	read-only
			STATUS	current
	DESCRIPTION ""
			::= { mbus13 84 }

mbus13Value27		OBJECT-TYPE
			SYNTAX	INTEGER
			ACCESS	read-only
			STATUS	current
	DESCRIPTION ""
			::= { mbus13 85 }

mbus13VIF28		OBJECT-TYPE
			SYNTAX	INTEGER
			ACCESS	read-only
			STATUS	current
	DESCRIPTION ""
			::= { mbus13 86 }

mbus13Value28		OBJECT-TYPE
			SYNTAX	INTEGER
			ACCESS	read-only
			STATUS	current
	DESCRIPTION ""
			::= { mbus13 87 }

mbus13VIF29		OBJECT-TYPE
			SYNTAX	INTEGER
			ACCESS	read-only
			STATUS	current
	DESCRIPTION ""
			::= { mbus13 88 }

mbus13Value29		OBJECT-TYPE
			SYNTAX	INTEGER
			ACCESS	read-only
			STATUS	current
	DESCRIPTION ""
			::= { mbus13 89 }

mbus13VIF2A		OBJECT-TYPE
			SYNTAX	INTEGER
			ACCESS	read-only
			STATUS	current
	DESCRIPTION ""
			::= { mbus13 90 }

mbus13Value2A		OBJECT-TYPE
			SYNTAX	INTEGER
			ACCESS	read-only
			STATUS	current
	DESCRIPTION ""
			::= { mbus13 91 }

mbus13VIF2B		OBJECT-TYPE
			SYNTAX	INTEGER
			ACCESS	read-only
			STATUS	current
	DESCRIPTION ""
			::= { mbus13 92 }

mbus13Value2B		OBJECT-TYPE
			SYNTAX	INTEGER
			ACCESS	read-only
			STATUS	current
	DESCRIPTION ""
			::= { mbus13 93 }

mbus13VIF2C		OBJECT-TYPE
			SYNTAX	INTEGER
			ACCESS	read-only
			STATUS	current
	DESCRIPTION ""
			::= { mbus13 94 }

mbus13Value2C		OBJECT-TYPE
			SYNTAX	INTEGER
			ACCESS	read-only
			STATUS	current
	DESCRIPTION ""
			::= { mbus13 95 }

mbus13VIF2D		OBJECT-TYPE
			SYNTAX	INTEGER
			ACCESS	read-only
			STATUS	current
	DESCRIPTION ""
			::= { mbus13 96 }

mbus13Value2D		OBJECT-TYPE
			SYNTAX	INTEGER
			ACCESS	read-only
			STATUS	current
	DESCRIPTION ""
			::= { mbus13 97 }

mbus13VIF2E		OBJECT-TYPE
			SYNTAX	INTEGER
			ACCESS	read-only
			STATUS	current
	DESCRIPTION ""
			::= { mbus13 98 }

mbus13Value2E		OBJECT-TYPE
			SYNTAX	INTEGER
			ACCESS	read-only
			STATUS	current
	DESCRIPTION ""
			::= { mbus13 99 }

mbus13VIF2F		OBJECT-TYPE
			SYNTAX	INTEGER
			ACCESS	read-only
			STATUS	current
	DESCRIPTION ""
			::= { mbus13 100 }

mbus13Value2F		OBJECT-TYPE
			SYNTAX	INTEGER
			ACCESS	read-only
			STATUS	current
	DESCRIPTION ""
			::= { mbus13 101 }

mbus14			OBJECT IDENTIFIER ::= { mbus 20 }

mbus14IdNumber		OBJECT-TYPE
			SYNTAX	Gauge
			ACCESS	read-only
			STATUS	current
	DESCRIPTION ""
			::= { mbus14 1 }

mbus14Manufacturer	OBJECT-TYPE
			SYNTAX	Gauge
			ACCESS	read-only
			STATUS	current
	DESCRIPTION ""
			::= { mbus14 2 }

mbus14Version		OBJECT-TYPE
			SYNTAX	Gauge
			ACCESS	read-only
			STATUS	current
	DESCRIPTION ""
			::= { mbus14 3 }

mbus14Medium		OBJECT-TYPE
			SYNTAX	Gauge
			ACCESS	read-only
			STATUS	current
	DESCRIPTION ""
			::= { mbus14 4 }

mbus14Status		OBJECT-TYPE
			SYNTAX	Gauge
			ACCESS	read-only
			STATUS	current
	DESCRIPTION ""
			::= { mbus14 5 }

mbus14VIF00		OBJECT-TYPE
			SYNTAX	INTEGER
			ACCESS	read-only
			STATUS	current
	DESCRIPTION ""
			::= { mbus14 6 }

mbus14Value00		OBJECT-TYPE
			SYNTAX	INTEGER
			ACCESS	read-only
			STATUS	current
	DESCRIPTION ""
			::= { mbus14 7 }

mbus14VIF01		OBJECT-TYPE
			SYNTAX	INTEGER
			ACCESS	read-only
			STATUS	current
	DESCRIPTION ""
			::= { mbus14 8 }

mbus14Value01		OBJECT-TYPE
			SYNTAX	INTEGER
			ACCESS	read-only
			STATUS	current
	DESCRIPTION ""
			::= { mbus14 9 }

mbus14VIF02		OBJECT-TYPE
			SYNTAX	INTEGER
			ACCESS	read-only
			STATUS	current
	DESCRIPTION ""
			::= { mbus14 10 }

mbus14Value02		OBJECT-TYPE
			SYNTAX	INTEGER
			ACCESS	read-only
			STATUS	current
	DESCRIPTION ""
			::= { mbus14 11 }

mbus14VIF03		OBJECT-TYPE
			SYNTAX	INTEGER
			ACCESS	read-only
			STATUS	current
	DESCRIPTION ""
			::= { mbus14 12 }

mbus14Value03		OBJECT-TYPE
			SYNTAX	INTEGER
			ACCESS	read-only
			STATUS	current
	DESCRIPTION ""
			::= { mbus14 13 }

mbus14VIF04		OBJECT-TYPE
			SYNTAX	INTEGER
			ACCESS	read-only
			STATUS	current
	DESCRIPTION ""
			::= { mbus14 14 }

mbus14Value04		OBJECT-TYPE
			SYNTAX	INTEGER
			ACCESS	read-only
			STATUS	current
	DESCRIPTION ""
			::= { mbus14 15 }

mbus14VIF05		OBJECT-TYPE
			SYNTAX	INTEGER
			ACCESS	read-only
			STATUS	current
	DESCRIPTION ""
			::= { mbus14 16 }

mbus14Value05		OBJECT-TYPE
			SYNTAX	INTEGER
			ACCESS	read-only
			STATUS	current
	DESCRIPTION ""
			::= { mbus14 17 }

mbus14VIF06		OBJECT-TYPE
			SYNTAX	INTEGER
			ACCESS	read-only
			STATUS	current
	DESCRIPTION ""
			::= { mbus14 18 }

mbus14Value06		OBJECT-TYPE
			SYNTAX	INTEGER
			ACCESS	read-only
			STATUS	current
	DESCRIPTION ""
			::= { mbus14 19 }

mbus14VIF07		OBJECT-TYPE
			SYNTAX	INTEGER
			ACCESS	read-only
			STATUS	current
	DESCRIPTION ""
			::= { mbus14 20 }

mbus14Value07		OBJECT-TYPE
			SYNTAX	INTEGER
			ACCESS	read-only
			STATUS	current
	DESCRIPTION ""
			::= { mbus14 21 }

mbus14VIF08		OBJECT-TYPE
			SYNTAX	INTEGER
			ACCESS	read-only
			STATUS	current
	DESCRIPTION ""
			::= { mbus14 22 }

mbus14Value08		OBJECT-TYPE
			SYNTAX	INTEGER
			ACCESS	read-only
			STATUS	current
	DESCRIPTION ""
			::= { mbus14 23 }

mbus14VIF09		OBJECT-TYPE
			SYNTAX	INTEGER
			ACCESS	read-only
			STATUS	current
	DESCRIPTION ""
			::= { mbus14 24 }

mbus14Value09		OBJECT-TYPE
			SYNTAX	INTEGER
			ACCESS	read-only
			STATUS	current
	DESCRIPTION ""
			::= { mbus14 25 }

mbus14VIF0A		OBJECT-TYPE
			SYNTAX	INTEGER
			ACCESS	read-only
			STATUS	current
	DESCRIPTION ""
			::= { mbus14 26 }

mbus14Value0A		OBJECT-TYPE
			SYNTAX	INTEGER
			ACCESS	read-only
			STATUS	current
	DESCRIPTION ""
			::= { mbus14 27 }

mbus14VIF0B		OBJECT-TYPE
			SYNTAX	INTEGER
			ACCESS	read-only
			STATUS	current
	DESCRIPTION ""
			::= { mbus14 28 }

mbus14Value0B		OBJECT-TYPE
			SYNTAX	INTEGER
			ACCESS	read-only
			STATUS	current
	DESCRIPTION ""
			::= { mbus14 29 }

mbus14VIF0C		OBJECT-TYPE
			SYNTAX	INTEGER
			ACCESS	read-only
			STATUS	current
	DESCRIPTION ""
			::= { mbus14 30 }

mbus14Value0C		OBJECT-TYPE
			SYNTAX	INTEGER
			ACCESS	read-only
			STATUS	current
	DESCRIPTION ""
			::= { mbus14 31 }

mbus14VIF0D		OBJECT-TYPE
			SYNTAX	INTEGER
			ACCESS	read-only
			STATUS	current
	DESCRIPTION ""
			::= { mbus14 32 }

mbus14Value0D		OBJECT-TYPE
			SYNTAX	INTEGER
			ACCESS	read-only
			STATUS	current
	DESCRIPTION ""
			::= { mbus14 33 }

mbus14VIF0E		OBJECT-TYPE
			SYNTAX	INTEGER
			ACCESS	read-only
			STATUS	current
	DESCRIPTION ""
			::= { mbus14 34 }

mbus14Value0E		OBJECT-TYPE
			SYNTAX	INTEGER
			ACCESS	read-only
			STATUS	current
	DESCRIPTION ""
			::= { mbus14 35 }

mbus14VIF0F		OBJECT-TYPE
			SYNTAX	INTEGER
			ACCESS	read-only
			STATUS	current
	DESCRIPTION ""
			::= { mbus14 36 }

mbus14Value0F		OBJECT-TYPE
			SYNTAX	INTEGER
			ACCESS	read-only
			STATUS	current
	DESCRIPTION ""
			::= { mbus14 37 }

mbus14VIF10		OBJECT-TYPE
			SYNTAX	INTEGER
			ACCESS	read-only
			STATUS	current
	DESCRIPTION ""
			::= { mbus14 38 }

mbus14Value10		OBJECT-TYPE
			SYNTAX	INTEGER
			ACCESS	read-only
			STATUS	current
	DESCRIPTION ""
			::= { mbus14 39 }

mbus14VIF11		OBJECT-TYPE
			SYNTAX	INTEGER
			ACCESS	read-only
			STATUS	current
	DESCRIPTION ""
			::= { mbus14 40 }

mbus14Value11		OBJECT-TYPE
			SYNTAX	INTEGER
			ACCESS	read-only
			STATUS	current
	DESCRIPTION ""
			::= { mbus14 41 }

mbus14VIF12		OBJECT-TYPE
			SYNTAX	INTEGER
			ACCESS	read-only
			STATUS	current
	DESCRIPTION ""
			::= { mbus14 42 }

mbus14Value12		OBJECT-TYPE
			SYNTAX	INTEGER
			ACCESS	read-only
			STATUS	current
	DESCRIPTION ""
			::= { mbus14 43 }

mbus14VIF13		OBJECT-TYPE
			SYNTAX	INTEGER
			ACCESS	read-only
			STATUS	current
	DESCRIPTION ""
			::= { mbus14 44 }

mbus14Value13		OBJECT-TYPE
			SYNTAX	INTEGER
			ACCESS	read-only
			STATUS	current
	DESCRIPTION ""
			::= { mbus14 45 }

mbus14VIF14		OBJECT-TYPE
			SYNTAX	INTEGER
			ACCESS	read-only
			STATUS	current
	DESCRIPTION ""
			::= { mbus14 46 }

mbus14Value14		OBJECT-TYPE
			SYNTAX	INTEGER
			ACCESS	read-only
			STATUS	current
	DESCRIPTION ""
			::= { mbus14 47 }

mbus14VIF15		OBJECT-TYPE
			SYNTAX	INTEGER
			ACCESS	read-only
			STATUS	current
	DESCRIPTION ""
			::= { mbus14 48 }

mbus14Value15		OBJECT-TYPE
			SYNTAX	INTEGER
			ACCESS	read-only
			STATUS	current
	DESCRIPTION ""
			::= { mbus14 49 }

mbus14VIF16		OBJECT-TYPE
			SYNTAX	INTEGER
			ACCESS	read-only
			STATUS	current
	DESCRIPTION ""
			::= { mbus14 50 }

mbus14Value16		OBJECT-TYPE
			SYNTAX	INTEGER
			ACCESS	read-only
			STATUS	current
	DESCRIPTION ""
			::= { mbus14 51 }

mbus14VIF17		OBJECT-TYPE
			SYNTAX	INTEGER
			ACCESS	read-only
			STATUS	current
	DESCRIPTION ""
			::= { mbus14 52 }

mbus14Value17		OBJECT-TYPE
			SYNTAX	INTEGER
			ACCESS	read-only
			STATUS	current
	DESCRIPTION ""
			::= { mbus14 53 }

mbus14VIF18		OBJECT-TYPE
			SYNTAX	INTEGER
			ACCESS	read-only
			STATUS	current
	DESCRIPTION ""
			::= { mbus14 54 }

mbus14Value18		OBJECT-TYPE
			SYNTAX	INTEGER
			ACCESS	read-only
			STATUS	current
	DESCRIPTION ""
			::= { mbus14 55 }

mbus14VIF19		OBJECT-TYPE
			SYNTAX	INTEGER
			ACCESS	read-only
			STATUS	current
	DESCRIPTION ""
			::= { mbus14 56 }

mbus14Value19		OBJECT-TYPE
			SYNTAX	INTEGER
			ACCESS	read-only
			STATUS	current
	DESCRIPTION ""
			::= { mbus14 57 }

mbus14VIF1A		OBJECT-TYPE
			SYNTAX	INTEGER
			ACCESS	read-only
			STATUS	current
	DESCRIPTION ""
			::= { mbus14 58 }

mbus14Value1A		OBJECT-TYPE
			SYNTAX	INTEGER
			ACCESS	read-only
			STATUS	current
	DESCRIPTION ""
			::= { mbus14 59 }

mbus14VIF1B		OBJECT-TYPE
			SYNTAX	INTEGER
			ACCESS	read-only
			STATUS	current
	DESCRIPTION ""
			::= { mbus14 60 }

mbus14Value1B		OBJECT-TYPE
			SYNTAX	INTEGER
			ACCESS	read-only
			STATUS	current
	DESCRIPTION ""
			::= { mbus14 61 }

mbus14VIF1C		OBJECT-TYPE
			SYNTAX	INTEGER
			ACCESS	read-only
			STATUS	current
	DESCRIPTION ""
			::= { mbus14 62 }

mbus14Value1C		OBJECT-TYPE
			SYNTAX	INTEGER
			ACCESS	read-only
			STATUS	current
	DESCRIPTION ""
			::= { mbus14 63 }

mbus14VIF1D		OBJECT-TYPE
			SYNTAX	INTEGER
			ACCESS	read-only
			STATUS	current
	DESCRIPTION ""
			::= { mbus14 64 }

mbus14Value1D		OBJECT-TYPE
			SYNTAX	INTEGER
			ACCESS	read-only
			STATUS	current
	DESCRIPTION ""
			::= { mbus14 65 }

mbus14VIF1E		OBJECT-TYPE
			SYNTAX	INTEGER
			ACCESS	read-only
			STATUS	current
	DESCRIPTION ""
			::= { mbus14 66 }

mbus14Value1E		OBJECT-TYPE
			SYNTAX	INTEGER
			ACCESS	read-only
			STATUS	current
	DESCRIPTION ""
			::= { mbus14 67 }

mbus14VIF1F		OBJECT-TYPE
			SYNTAX	INTEGER
			ACCESS	read-only
			STATUS	current
	DESCRIPTION ""
			::= { mbus14 68 }

mbus14Value1F		OBJECT-TYPE
			SYNTAX	INTEGER
			ACCESS	read-only
			STATUS	current
	DESCRIPTION ""
			::= { mbus14 69 }

mbus14VIF20		OBJECT-TYPE
			SYNTAX	INTEGER
			ACCESS	read-only
			STATUS	current
	DESCRIPTION ""
			::= { mbus14 70 }

mbus14Value20		OBJECT-TYPE
			SYNTAX	INTEGER
			ACCESS	read-only
			STATUS	current
	DESCRIPTION ""
			::= { mbus14 71 }

mbus14VIF21		OBJECT-TYPE
			SYNTAX	INTEGER
			ACCESS	read-only
			STATUS	current
	DESCRIPTION ""
			::= { mbus14 72 }

mbus14Value21		OBJECT-TYPE
			SYNTAX	INTEGER
			ACCESS	read-only
			STATUS	current
	DESCRIPTION ""
			::= { mbus14 73 }

mbus14VIF22		OBJECT-TYPE
			SYNTAX	INTEGER
			ACCESS	read-only
			STATUS	current
	DESCRIPTION ""
			::= { mbus14 74 }

mbus14Value22		OBJECT-TYPE
			SYNTAX	INTEGER
			ACCESS	read-only
			STATUS	current
	DESCRIPTION ""
			::= { mbus14 75 }

mbus14VIF23		OBJECT-TYPE
			SYNTAX	INTEGER
			ACCESS	read-only
			STATUS	current
	DESCRIPTION ""
			::= { mbus14 76 }

mbus14Value23		OBJECT-TYPE
			SYNTAX	INTEGER
			ACCESS	read-only
			STATUS	current
	DESCRIPTION ""
			::= { mbus14 77 }

mbus14VIF24		OBJECT-TYPE
			SYNTAX	INTEGER
			ACCESS	read-only
			STATUS	current
	DESCRIPTION ""
			::= { mbus14 78 }

mbus14Value24		OBJECT-TYPE
			SYNTAX	INTEGER
			ACCESS	read-only
			STATUS	current
	DESCRIPTION ""
			::= { mbus14 79 }

mbus14VIF25		OBJECT-TYPE
			SYNTAX	INTEGER
			ACCESS	read-only
			STATUS	current
	DESCRIPTION ""
			::= { mbus14 80 }

mbus14Value25		OBJECT-TYPE
			SYNTAX	INTEGER
			ACCESS	read-only
			STATUS	current
	DESCRIPTION ""
			::= { mbus14 81 }

mbus14VIF26		OBJECT-TYPE
			SYNTAX	INTEGER
			ACCESS	read-only
			STATUS	current
	DESCRIPTION ""
			::= { mbus14 82 }

mbus14Value26		OBJECT-TYPE
			SYNTAX	INTEGER
			ACCESS	read-only
			STATUS	current
	DESCRIPTION ""
			::= { mbus14 83 }

mbus14VIF27		OBJECT-TYPE
			SYNTAX	INTEGER
			ACCESS	read-only
			STATUS	current
	DESCRIPTION ""
			::= { mbus14 84 }

mbus14Value27		OBJECT-TYPE
			SYNTAX	INTEGER
			ACCESS	read-only
			STATUS	current
	DESCRIPTION ""
			::= { mbus14 85 }

mbus14VIF28		OBJECT-TYPE
			SYNTAX	INTEGER
			ACCESS	read-only
			STATUS	current
	DESCRIPTION ""
			::= { mbus14 86 }

mbus14Value28		OBJECT-TYPE
			SYNTAX	INTEGER
			ACCESS	read-only
			STATUS	current
	DESCRIPTION ""
			::= { mbus14 87 }

mbus14VIF29		OBJECT-TYPE
			SYNTAX	INTEGER
			ACCESS	read-only
			STATUS	current
	DESCRIPTION ""
			::= { mbus14 88 }

mbus14Value29		OBJECT-TYPE
			SYNTAX	INTEGER
			ACCESS	read-only
			STATUS	current
	DESCRIPTION ""
			::= { mbus14 89 }

mbus14VIF2A		OBJECT-TYPE
			SYNTAX	INTEGER
			ACCESS	read-only
			STATUS	current
	DESCRIPTION ""
			::= { mbus14 90 }

mbus14Value2A		OBJECT-TYPE
			SYNTAX	INTEGER
			ACCESS	read-only
			STATUS	current
	DESCRIPTION ""
			::= { mbus14 91 }

mbus14VIF2B		OBJECT-TYPE
			SYNTAX	INTEGER
			ACCESS	read-only
			STATUS	current
	DESCRIPTION ""
			::= { mbus14 92 }

mbus14Value2B		OBJECT-TYPE
			SYNTAX	INTEGER
			ACCESS	read-only
			STATUS	current
	DESCRIPTION ""
			::= { mbus14 93 }

mbus14VIF2C		OBJECT-TYPE
			SYNTAX	INTEGER
			ACCESS	read-only
			STATUS	current
	DESCRIPTION ""
			::= { mbus14 94 }

mbus14Value2C		OBJECT-TYPE
			SYNTAX	INTEGER
			ACCESS	read-only
			STATUS	current
	DESCRIPTION ""
			::= { mbus14 95 }

mbus14VIF2D		OBJECT-TYPE
			SYNTAX	INTEGER
			ACCESS	read-only
			STATUS	current
	DESCRIPTION ""
			::= { mbus14 96 }

mbus14Value2D		OBJECT-TYPE
			SYNTAX	INTEGER
			ACCESS	read-only
			STATUS	current
	DESCRIPTION ""
			::= { mbus14 97 }

mbus14VIF2E		OBJECT-TYPE
			SYNTAX	INTEGER
			ACCESS	read-only
			STATUS	current
	DESCRIPTION ""
			::= { mbus14 98 }

mbus14Value2E		OBJECT-TYPE
			SYNTAX	INTEGER
			ACCESS	read-only
			STATUS	current
	DESCRIPTION ""
			::= { mbus14 99 }

mbus14VIF2F		OBJECT-TYPE
			SYNTAX	INTEGER
			ACCESS	read-only
			STATUS	current
	DESCRIPTION ""
			::= { mbus14 100 }

mbus14Value2F		OBJECT-TYPE
			SYNTAX	INTEGER
			ACCESS	read-only
			STATUS	current
	DESCRIPTION ""
			::= { mbus14 101 }

mbus15			OBJECT IDENTIFIER ::= { mbus 21 }

mbus15IdNumber		OBJECT-TYPE
			SYNTAX	Gauge
			ACCESS	read-only
			STATUS	current
	DESCRIPTION ""
			::= { mbus15 1 }

mbus15Manufacturer	OBJECT-TYPE
			SYNTAX	Gauge
			ACCESS	read-only
			STATUS	current
	DESCRIPTION ""
			::= { mbus15 2 }

mbus15Version		OBJECT-TYPE
			SYNTAX	Gauge
			ACCESS	read-only
			STATUS	current
	DESCRIPTION ""
			::= { mbus15 3 }

mbus15Medium		OBJECT-TYPE
			SYNTAX	Gauge
			ACCESS	read-only
			STATUS	current
	DESCRIPTION ""
			::= { mbus15 4 }

mbus15Status		OBJECT-TYPE
			SYNTAX	Gauge
			ACCESS	read-only
			STATUS	current
	DESCRIPTION ""
			::= { mbus15 5 }

mbus15VIF00		OBJECT-TYPE
			SYNTAX	INTEGER
			ACCESS	read-only
			STATUS	current
	DESCRIPTION ""
			::= { mbus15 6 }

mbus15Value00		OBJECT-TYPE
			SYNTAX	INTEGER
			ACCESS	read-only
			STATUS	current
	DESCRIPTION ""
			::= { mbus15 7 }

mbus15VIF01		OBJECT-TYPE
			SYNTAX	INTEGER
			ACCESS	read-only
			STATUS	current
	DESCRIPTION ""
			::= { mbus15 8 }

mbus15Value01		OBJECT-TYPE
			SYNTAX	INTEGER
			ACCESS	read-only
			STATUS	current
	DESCRIPTION ""
			::= { mbus15 9 }

mbus15VIF02		OBJECT-TYPE
			SYNTAX	INTEGER
			ACCESS	read-only
			STATUS	current
	DESCRIPTION ""
			::= { mbus15 10 }

mbus15Value02		OBJECT-TYPE
			SYNTAX	INTEGER
			ACCESS	read-only
			STATUS	current
	DESCRIPTION ""
			::= { mbus15 11 }

mbus15VIF03		OBJECT-TYPE
			SYNTAX	INTEGER
			ACCESS	read-only
			STATUS	current
	DESCRIPTION ""
			::= { mbus15 12 }

mbus15Value03		OBJECT-TYPE
			SYNTAX	INTEGER
			ACCESS	read-only
			STATUS	current
	DESCRIPTION ""
			::= { mbus15 13 }

mbus15VIF04		OBJECT-TYPE
			SYNTAX	INTEGER
			ACCESS	read-only
			STATUS	current
	DESCRIPTION ""
			::= { mbus15 14 }

mbus15Value04		OBJECT-TYPE
			SYNTAX	INTEGER
			ACCESS	read-only
			STATUS	current
	DESCRIPTION ""
			::= { mbus15 15 }

mbus15VIF05		OBJECT-TYPE
			SYNTAX	INTEGER
			ACCESS	read-only
			STATUS	current
	DESCRIPTION ""
			::= { mbus15 16 }

mbus15Value05		OBJECT-TYPE
			SYNTAX	INTEGER
			ACCESS	read-only
			STATUS	current
	DESCRIPTION ""
			::= { mbus15 17 }

mbus15VIF06		OBJECT-TYPE
			SYNTAX	INTEGER
			ACCESS	read-only
			STATUS	current
	DESCRIPTION ""
			::= { mbus15 18 }

mbus15Value06		OBJECT-TYPE
			SYNTAX	INTEGER
			ACCESS	read-only
			STATUS	current
	DESCRIPTION ""
			::= { mbus15 19 }

mbus15VIF07		OBJECT-TYPE
			SYNTAX	INTEGER
			ACCESS	read-only
			STATUS	current
	DESCRIPTION ""
			::= { mbus15 20 }

mbus15Value07		OBJECT-TYPE
			SYNTAX	INTEGER
			ACCESS	read-only
			STATUS	current
	DESCRIPTION ""
			::= { mbus15 21 }

mbus15VIF08		OBJECT-TYPE
			SYNTAX	INTEGER
			ACCESS	read-only
			STATUS	current
	DESCRIPTION ""
			::= { mbus15 22 }

mbus15Value08		OBJECT-TYPE
			SYNTAX	INTEGER
			ACCESS	read-only
			STATUS	current
	DESCRIPTION ""
			::= { mbus15 23 }

mbus15VIF09		OBJECT-TYPE
			SYNTAX	INTEGER
			ACCESS	read-only
			STATUS	current
	DESCRIPTION ""
			::= { mbus15 24 }

mbus15Value09		OBJECT-TYPE
			SYNTAX	INTEGER
			ACCESS	read-only
			STATUS	current
	DESCRIPTION ""
			::= { mbus15 25 }

mbus15VIF0A		OBJECT-TYPE
			SYNTAX	INTEGER
			ACCESS	read-only
			STATUS	current
	DESCRIPTION ""
			::= { mbus15 26 }

mbus15Value0A		OBJECT-TYPE
			SYNTAX	INTEGER
			ACCESS	read-only
			STATUS	current
	DESCRIPTION ""
			::= { mbus15 27 }

mbus15VIF0B		OBJECT-TYPE
			SYNTAX	INTEGER
			ACCESS	read-only
			STATUS	current
	DESCRIPTION ""
			::= { mbus15 28 }

mbus15Value0B		OBJECT-TYPE
			SYNTAX	INTEGER
			ACCESS	read-only
			STATUS	current
	DESCRIPTION ""
			::= { mbus15 29 }

mbus15VIF0C		OBJECT-TYPE
			SYNTAX	INTEGER
			ACCESS	read-only
			STATUS	current
	DESCRIPTION ""
			::= { mbus15 30 }

mbus15Value0C		OBJECT-TYPE
			SYNTAX	INTEGER
			ACCESS	read-only
			STATUS	current
	DESCRIPTION ""
			::= { mbus15 31 }

mbus15VIF0D		OBJECT-TYPE
			SYNTAX	INTEGER
			ACCESS	read-only
			STATUS	current
	DESCRIPTION ""
			::= { mbus15 32 }

mbus15Value0D		OBJECT-TYPE
			SYNTAX	INTEGER
			ACCESS	read-only
			STATUS	current
	DESCRIPTION ""
			::= { mbus15 33 }

mbus15VIF0E		OBJECT-TYPE
			SYNTAX	INTEGER
			ACCESS	read-only
			STATUS	current
	DESCRIPTION ""
			::= { mbus15 34 }

mbus15Value0E		OBJECT-TYPE
			SYNTAX	INTEGER
			ACCESS	read-only
			STATUS	current
	DESCRIPTION ""
			::= { mbus15 35 }

mbus15VIF0F		OBJECT-TYPE
			SYNTAX	INTEGER
			ACCESS	read-only
			STATUS	current
	DESCRIPTION ""
			::= { mbus15 36 }

mbus15Value0F		OBJECT-TYPE
			SYNTAX	INTEGER
			ACCESS	read-only
			STATUS	current
	DESCRIPTION ""
			::= { mbus15 37 }

mbus15VIF10		OBJECT-TYPE
			SYNTAX	INTEGER
			ACCESS	read-only
			STATUS	current
	DESCRIPTION ""
			::= { mbus15 38 }

mbus15Value10		OBJECT-TYPE
			SYNTAX	INTEGER
			ACCESS	read-only
			STATUS	current
	DESCRIPTION ""
			::= { mbus15 39 }

mbus15VIF11		OBJECT-TYPE
			SYNTAX	INTEGER
			ACCESS	read-only
			STATUS	current
	DESCRIPTION ""
			::= { mbus15 40 }

mbus15Value11		OBJECT-TYPE
			SYNTAX	INTEGER
			ACCESS	read-only
			STATUS	current
	DESCRIPTION ""
			::= { mbus15 41 }

mbus15VIF12		OBJECT-TYPE
			SYNTAX	INTEGER
			ACCESS	read-only
			STATUS	current
	DESCRIPTION ""
			::= { mbus15 42 }

mbus15Value12		OBJECT-TYPE
			SYNTAX	INTEGER
			ACCESS	read-only
			STATUS	current
	DESCRIPTION ""
			::= { mbus15 43 }

mbus15VIF13		OBJECT-TYPE
			SYNTAX	INTEGER
			ACCESS	read-only
			STATUS	current
	DESCRIPTION ""
			::= { mbus15 44 }

mbus15Value13		OBJECT-TYPE
			SYNTAX	INTEGER
			ACCESS	read-only
			STATUS	current
	DESCRIPTION ""
			::= { mbus15 45 }

mbus15VIF14		OBJECT-TYPE
			SYNTAX	INTEGER
			ACCESS	read-only
			STATUS	current
	DESCRIPTION ""
			::= { mbus15 46 }

mbus15Value14		OBJECT-TYPE
			SYNTAX	INTEGER
			ACCESS	read-only
			STATUS	current
	DESCRIPTION ""
			::= { mbus15 47 }

mbus15VIF15		OBJECT-TYPE
			SYNTAX	INTEGER
			ACCESS	read-only
			STATUS	current
	DESCRIPTION ""
			::= { mbus15 48 }

mbus15Value15		OBJECT-TYPE
			SYNTAX	INTEGER
			ACCESS	read-only
			STATUS	current
	DESCRIPTION ""
			::= { mbus15 49 }

mbus15VIF16		OBJECT-TYPE
			SYNTAX	INTEGER
			ACCESS	read-only
			STATUS	current
	DESCRIPTION ""
			::= { mbus15 50 }

mbus15Value16		OBJECT-TYPE
			SYNTAX	INTEGER
			ACCESS	read-only
			STATUS	current
	DESCRIPTION ""
			::= { mbus15 51 }

mbus15VIF17		OBJECT-TYPE
			SYNTAX	INTEGER
			ACCESS	read-only
			STATUS	current
	DESCRIPTION ""
			::= { mbus15 52 }

mbus15Value17		OBJECT-TYPE
			SYNTAX	INTEGER
			ACCESS	read-only
			STATUS	current
	DESCRIPTION ""
			::= { mbus15 53 }

mbus15VIF18		OBJECT-TYPE
			SYNTAX	INTEGER
			ACCESS	read-only
			STATUS	current
	DESCRIPTION ""
			::= { mbus15 54 }

mbus15Value18		OBJECT-TYPE
			SYNTAX	INTEGER
			ACCESS	read-only
			STATUS	current
	DESCRIPTION ""
			::= { mbus15 55 }

mbus15VIF19		OBJECT-TYPE
			SYNTAX	INTEGER
			ACCESS	read-only
			STATUS	current
	DESCRIPTION ""
			::= { mbus15 56 }

mbus15Value19		OBJECT-TYPE
			SYNTAX	INTEGER
			ACCESS	read-only
			STATUS	current
	DESCRIPTION ""
			::= { mbus15 57 }

mbus15VIF1A		OBJECT-TYPE
			SYNTAX	INTEGER
			ACCESS	read-only
			STATUS	current
	DESCRIPTION ""
			::= { mbus15 58 }

mbus15Value1A		OBJECT-TYPE
			SYNTAX	INTEGER
			ACCESS	read-only
			STATUS	current
	DESCRIPTION ""
			::= { mbus15 59 }

mbus15VIF1B		OBJECT-TYPE
			SYNTAX	INTEGER
			ACCESS	read-only
			STATUS	current
	DESCRIPTION ""
			::= { mbus15 60 }

mbus15Value1B		OBJECT-TYPE
			SYNTAX	INTEGER
			ACCESS	read-only
			STATUS	current
	DESCRIPTION ""
			::= { mbus15 61 }

mbus15VIF1C		OBJECT-TYPE
			SYNTAX	INTEGER
			ACCESS	read-only
			STATUS	current
	DESCRIPTION ""
			::= { mbus15 62 }

mbus15Value1C		OBJECT-TYPE
			SYNTAX	INTEGER
			ACCESS	read-only
			STATUS	current
	DESCRIPTION ""
			::= { mbus15 63 }

mbus15VIF1D		OBJECT-TYPE
			SYNTAX	INTEGER
			ACCESS	read-only
			STATUS	current
	DESCRIPTION ""
			::= { mbus15 64 }

mbus15Value1D		OBJECT-TYPE
			SYNTAX	INTEGER
			ACCESS	read-only
			STATUS	current
	DESCRIPTION ""
			::= { mbus15 65 }

mbus15VIF1E		OBJECT-TYPE
			SYNTAX	INTEGER
			ACCESS	read-only
			STATUS	current
	DESCRIPTION ""
			::= { mbus15 66 }

mbus15Value1E		OBJECT-TYPE
			SYNTAX	INTEGER
			ACCESS	read-only
			STATUS	current
	DESCRIPTION ""
			::= { mbus15 67 }

mbus15VIF1F		OBJECT-TYPE
			SYNTAX	INTEGER
			ACCESS	read-only
			STATUS	current
	DESCRIPTION ""
			::= { mbus15 68 }

mbus15Value1F		OBJECT-TYPE
			SYNTAX	INTEGER
			ACCESS	read-only
			STATUS	current
	DESCRIPTION ""
			::= { mbus15 69 }

mbus15VIF20		OBJECT-TYPE
			SYNTAX	INTEGER
			ACCESS	read-only
			STATUS	current
	DESCRIPTION ""
			::= { mbus15 70 }

mbus15Value20		OBJECT-TYPE
			SYNTAX	INTEGER
			ACCESS	read-only
			STATUS	current
	DESCRIPTION ""
			::= { mbus15 71 }

mbus15VIF21		OBJECT-TYPE
			SYNTAX	INTEGER
			ACCESS	read-only
			STATUS	current
	DESCRIPTION ""
			::= { mbus15 72 }

mbus15Value21		OBJECT-TYPE
			SYNTAX	INTEGER
			ACCESS	read-only
			STATUS	current
	DESCRIPTION ""
			::= { mbus15 73 }

mbus15VIF22		OBJECT-TYPE
			SYNTAX	INTEGER
			ACCESS	read-only
			STATUS	current
	DESCRIPTION ""
			::= { mbus15 74 }

mbus15Value22		OBJECT-TYPE
			SYNTAX	INTEGER
			ACCESS	read-only
			STATUS	current
	DESCRIPTION ""
			::= { mbus15 75 }

mbus15VIF23		OBJECT-TYPE
			SYNTAX	INTEGER
			ACCESS	read-only
			STATUS	current
	DESCRIPTION ""
			::= { mbus15 76 }

mbus15Value23		OBJECT-TYPE
			SYNTAX	INTEGER
			ACCESS	read-only
			STATUS	current
	DESCRIPTION ""
			::= { mbus15 77 }

mbus15VIF24		OBJECT-TYPE
			SYNTAX	INTEGER
			ACCESS	read-only
			STATUS	current
	DESCRIPTION ""
			::= { mbus15 78 }

mbus15Value24		OBJECT-TYPE
			SYNTAX	INTEGER
			ACCESS	read-only
			STATUS	current
	DESCRIPTION ""
			::= { mbus15 79 }

mbus15VIF25		OBJECT-TYPE
			SYNTAX	INTEGER
			ACCESS	read-only
			STATUS	current
	DESCRIPTION ""
			::= { mbus15 80 }

mbus15Value25		OBJECT-TYPE
			SYNTAX	INTEGER
			ACCESS	read-only
			STATUS	current
	DESCRIPTION ""
			::= { mbus15 81 }

mbus15VIF26		OBJECT-TYPE
			SYNTAX	INTEGER
			ACCESS	read-only
			STATUS	current
	DESCRIPTION ""
			::= { mbus15 82 }

mbus15Value26		OBJECT-TYPE
			SYNTAX	INTEGER
			ACCESS	read-only
			STATUS	current
	DESCRIPTION ""
			::= { mbus15 83 }

mbus15VIF27		OBJECT-TYPE
			SYNTAX	INTEGER
			ACCESS	read-only
			STATUS	current
	DESCRIPTION ""
			::= { mbus15 84 }

mbus15Value27		OBJECT-TYPE
			SYNTAX	INTEGER
			ACCESS	read-only
			STATUS	current
	DESCRIPTION ""
			::= { mbus15 85 }

mbus15VIF28		OBJECT-TYPE
			SYNTAX	INTEGER
			ACCESS	read-only
			STATUS	current
	DESCRIPTION ""
			::= { mbus15 86 }

mbus15Value28		OBJECT-TYPE
			SYNTAX	INTEGER
			ACCESS	read-only
			STATUS	current
	DESCRIPTION ""
			::= { mbus15 87 }

mbus15VIF29		OBJECT-TYPE
			SYNTAX	INTEGER
			ACCESS	read-only
			STATUS	current
	DESCRIPTION ""
			::= { mbus15 88 }

mbus15Value29		OBJECT-TYPE
			SYNTAX	INTEGER
			ACCESS	read-only
			STATUS	current
	DESCRIPTION ""
			::= { mbus15 89 }

mbus15VIF2A		OBJECT-TYPE
			SYNTAX	INTEGER
			ACCESS	read-only
			STATUS	current
	DESCRIPTION ""
			::= { mbus15 90 }

mbus15Value2A		OBJECT-TYPE
			SYNTAX	INTEGER
			ACCESS	read-only
			STATUS	current
	DESCRIPTION ""
			::= { mbus15 91 }

mbus15VIF2B		OBJECT-TYPE
			SYNTAX	INTEGER
			ACCESS	read-only
			STATUS	current
	DESCRIPTION ""
			::= { mbus15 92 }

mbus15Value2B		OBJECT-TYPE
			SYNTAX	INTEGER
			ACCESS	read-only
			STATUS	current
	DESCRIPTION ""
			::= { mbus15 93 }

mbus15VIF2C		OBJECT-TYPE
			SYNTAX	INTEGER
			ACCESS	read-only
			STATUS	current
	DESCRIPTION ""
			::= { mbus15 94 }

mbus15Value2C		OBJECT-TYPE
			SYNTAX	INTEGER
			ACCESS	read-only
			STATUS	current
	DESCRIPTION ""
			::= { mbus15 95 }

mbus15VIF2D		OBJECT-TYPE
			SYNTAX	INTEGER
			ACCESS	read-only
			STATUS	current
	DESCRIPTION ""
			::= { mbus15 96 }

mbus15Value2D		OBJECT-TYPE
			SYNTAX	INTEGER
			ACCESS	read-only
			STATUS	current
	DESCRIPTION ""
			::= { mbus15 97 }

mbus15VIF2E		OBJECT-TYPE
			SYNTAX	INTEGER
			ACCESS	read-only
			STATUS	current
	DESCRIPTION ""
			::= { mbus15 98 }

mbus15Value2E		OBJECT-TYPE
			SYNTAX	INTEGER
			ACCESS	read-only
			STATUS	current
	DESCRIPTION ""
			::= { mbus15 99 }

mbus15VIF2F		OBJECT-TYPE
			SYNTAX	INTEGER
			ACCESS	read-only
			STATUS	current
	DESCRIPTION ""
			::= { mbus15 100 }

mbus15Value2F		OBJECT-TYPE
			SYNTAX	INTEGER
			ACCESS	read-only
			STATUS	current
	DESCRIPTION ""
			::= { mbus15 101 }

mbus16			OBJECT IDENTIFIER ::= { mbus 22 }

mbus16IdNumber		OBJECT-TYPE
			SYNTAX	Gauge
			ACCESS	read-only
			STATUS	current
	DESCRIPTION ""
			::= { mbus16 1 }

mbus16Manufacturer	OBJECT-TYPE
			SYNTAX	Gauge
			ACCESS	read-only
			STATUS	current
	DESCRIPTION ""
			::= { mbus16 2 }

mbus16Version		OBJECT-TYPE
			SYNTAX	Gauge
			ACCESS	read-only
			STATUS	current
	DESCRIPTION ""
			::= { mbus16 3 }

mbus16Medium		OBJECT-TYPE
			SYNTAX	Gauge
			ACCESS	read-only
			STATUS	current
	DESCRIPTION ""
			::= { mbus16 4 }

mbus16Status		OBJECT-TYPE
			SYNTAX	Gauge
			ACCESS	read-only
			STATUS	current
	DESCRIPTION ""
			::= { mbus16 5 }

mbus16VIF00		OBJECT-TYPE
			SYNTAX	INTEGER
			ACCESS	read-only
			STATUS	current
	DESCRIPTION ""
			::= { mbus16 6 }

mbus16Value00		OBJECT-TYPE
			SYNTAX	INTEGER
			ACCESS	read-only
			STATUS	current
	DESCRIPTION ""
			::= { mbus16 7 }

mbus16VIF01		OBJECT-TYPE
			SYNTAX	INTEGER
			ACCESS	read-only
			STATUS	current
	DESCRIPTION ""
			::= { mbus16 8 }

mbus16Value01		OBJECT-TYPE
			SYNTAX	INTEGER
			ACCESS	read-only
			STATUS	current
	DESCRIPTION ""
			::= { mbus16 9 }

mbus16VIF02		OBJECT-TYPE
			SYNTAX	INTEGER
			ACCESS	read-only
			STATUS	current
	DESCRIPTION ""
			::= { mbus16 10 }

mbus16Value02		OBJECT-TYPE
			SYNTAX	INTEGER
			ACCESS	read-only
			STATUS	current
	DESCRIPTION ""
			::= { mbus16 11 }

mbus16VIF03		OBJECT-TYPE
			SYNTAX	INTEGER
			ACCESS	read-only
			STATUS	current
	DESCRIPTION ""
			::= { mbus16 12 }

mbus16Value03		OBJECT-TYPE
			SYNTAX	INTEGER
			ACCESS	read-only
			STATUS	current
	DESCRIPTION ""
			::= { mbus16 13 }

mbus16VIF04		OBJECT-TYPE
			SYNTAX	INTEGER
			ACCESS	read-only
			STATUS	current
	DESCRIPTION ""
			::= { mbus16 14 }

mbus16Value04		OBJECT-TYPE
			SYNTAX	INTEGER
			ACCESS	read-only
			STATUS	current
	DESCRIPTION ""
			::= { mbus16 15 }

mbus16VIF05		OBJECT-TYPE
			SYNTAX	INTEGER
			ACCESS	read-only
			STATUS	current
	DESCRIPTION ""
			::= { mbus16 16 }

mbus16Value05		OBJECT-TYPE
			SYNTAX	INTEGER
			ACCESS	read-only
			STATUS	current
	DESCRIPTION ""
			::= { mbus16 17 }

mbus16VIF06		OBJECT-TYPE
			SYNTAX	INTEGER
			ACCESS	read-only
			STATUS	current
	DESCRIPTION ""
			::= { mbus16 18 }

mbus16Value06		OBJECT-TYPE
			SYNTAX	INTEGER
			ACCESS	read-only
			STATUS	current
	DESCRIPTION ""
			::= { mbus16 19 }

mbus16VIF07		OBJECT-TYPE
			SYNTAX	INTEGER
			ACCESS	read-only
			STATUS	current
	DESCRIPTION ""
			::= { mbus16 20 }

mbus16Value07		OBJECT-TYPE
			SYNTAX	INTEGER
			ACCESS	read-only
			STATUS	current
	DESCRIPTION ""
			::= { mbus16 21 }

mbus16VIF08		OBJECT-TYPE
			SYNTAX	INTEGER
			ACCESS	read-only
			STATUS	current
	DESCRIPTION ""
			::= { mbus16 22 }

mbus16Value08		OBJECT-TYPE
			SYNTAX	INTEGER
			ACCESS	read-only
			STATUS	current
	DESCRIPTION ""
			::= { mbus16 23 }

mbus16VIF09		OBJECT-TYPE
			SYNTAX	INTEGER
			ACCESS	read-only
			STATUS	current
	DESCRIPTION ""
			::= { mbus16 24 }

mbus16Value09		OBJECT-TYPE
			SYNTAX	INTEGER
			ACCESS	read-only
			STATUS	current
	DESCRIPTION ""
			::= { mbus16 25 }

mbus16VIF0A		OBJECT-TYPE
			SYNTAX	INTEGER
			ACCESS	read-only
			STATUS	current
	DESCRIPTION ""
			::= { mbus16 26 }

mbus16Value0A		OBJECT-TYPE
			SYNTAX	INTEGER
			ACCESS	read-only
			STATUS	current
	DESCRIPTION ""
			::= { mbus16 27 }

mbus16VIF0B		OBJECT-TYPE
			SYNTAX	INTEGER
			ACCESS	read-only
			STATUS	current
	DESCRIPTION ""
			::= { mbus16 28 }

mbus16Value0B		OBJECT-TYPE
			SYNTAX	INTEGER
			ACCESS	read-only
			STATUS	current
	DESCRIPTION ""
			::= { mbus16 29 }

mbus16VIF0C		OBJECT-TYPE
			SYNTAX	INTEGER
			ACCESS	read-only
			STATUS	current
	DESCRIPTION ""
			::= { mbus16 30 }

mbus16Value0C		OBJECT-TYPE
			SYNTAX	INTEGER
			ACCESS	read-only
			STATUS	current
	DESCRIPTION ""
			::= { mbus16 31 }

mbus16VIF0D		OBJECT-TYPE
			SYNTAX	INTEGER
			ACCESS	read-only
			STATUS	current
	DESCRIPTION ""
			::= { mbus16 32 }

mbus16Value0D		OBJECT-TYPE
			SYNTAX	INTEGER
			ACCESS	read-only
			STATUS	current
	DESCRIPTION ""
			::= { mbus16 33 }

mbus16VIF0E		OBJECT-TYPE
			SYNTAX	INTEGER
			ACCESS	read-only
			STATUS	current
	DESCRIPTION ""
			::= { mbus16 34 }

mbus16Value0E		OBJECT-TYPE
			SYNTAX	INTEGER
			ACCESS	read-only
			STATUS	current
	DESCRIPTION ""
			::= { mbus16 35 }

mbus16VIF0F		OBJECT-TYPE
			SYNTAX	INTEGER
			ACCESS	read-only
			STATUS	current
	DESCRIPTION ""
			::= { mbus16 36 }

mbus16Value0F		OBJECT-TYPE
			SYNTAX	INTEGER
			ACCESS	read-only
			STATUS	current
	DESCRIPTION ""
			::= { mbus16 37 }

mbus16VIF10		OBJECT-TYPE
			SYNTAX	INTEGER
			ACCESS	read-only
			STATUS	current
	DESCRIPTION ""
			::= { mbus16 38 }

mbus16Value10		OBJECT-TYPE
			SYNTAX	INTEGER
			ACCESS	read-only
			STATUS	current
	DESCRIPTION ""
			::= { mbus16 39 }

mbus16VIF11		OBJECT-TYPE
			SYNTAX	INTEGER
			ACCESS	read-only
			STATUS	current
	DESCRIPTION ""
			::= { mbus16 40 }

mbus16Value11		OBJECT-TYPE
			SYNTAX	INTEGER
			ACCESS	read-only
			STATUS	current
	DESCRIPTION ""
			::= { mbus16 41 }

mbus16VIF12		OBJECT-TYPE
			SYNTAX	INTEGER
			ACCESS	read-only
			STATUS	current
	DESCRIPTION ""
			::= { mbus16 42 }

mbus16Value12		OBJECT-TYPE
			SYNTAX	INTEGER
			ACCESS	read-only
			STATUS	current
	DESCRIPTION ""
			::= { mbus16 43 }

mbus16VIF13		OBJECT-TYPE
			SYNTAX	INTEGER
			ACCESS	read-only
			STATUS	current
	DESCRIPTION ""
			::= { mbus16 44 }

mbus16Value13		OBJECT-TYPE
			SYNTAX	INTEGER
			ACCESS	read-only
			STATUS	current
	DESCRIPTION ""
			::= { mbus16 45 }

mbus16VIF14		OBJECT-TYPE
			SYNTAX	INTEGER
			ACCESS	read-only
			STATUS	current
	DESCRIPTION ""
			::= { mbus16 46 }

mbus16Value14		OBJECT-TYPE
			SYNTAX	INTEGER
			ACCESS	read-only
			STATUS	current
	DESCRIPTION ""
			::= { mbus16 47 }

mbus16VIF15		OBJECT-TYPE
			SYNTAX	INTEGER
			ACCESS	read-only
			STATUS	current
	DESCRIPTION ""
			::= { mbus16 48 }

mbus16Value15		OBJECT-TYPE
			SYNTAX	INTEGER
			ACCESS	read-only
			STATUS	current
	DESCRIPTION ""
			::= { mbus16 49 }

mbus16VIF16		OBJECT-TYPE
			SYNTAX	INTEGER
			ACCESS	read-only
			STATUS	current
	DESCRIPTION ""
			::= { mbus16 50 }

mbus16Value16		OBJECT-TYPE
			SYNTAX	INTEGER
			ACCESS	read-only
			STATUS	current
	DESCRIPTION ""
			::= { mbus16 51 }

mbus16VIF17		OBJECT-TYPE
			SYNTAX	INTEGER
			ACCESS	read-only
			STATUS	current
	DESCRIPTION ""
			::= { mbus16 52 }

mbus16Value17		OBJECT-TYPE
			SYNTAX	INTEGER
			ACCESS	read-only
			STATUS	current
	DESCRIPTION ""
			::= { mbus16 53 }

mbus16VIF18		OBJECT-TYPE
			SYNTAX	INTEGER
			ACCESS	read-only
			STATUS	current
	DESCRIPTION ""
			::= { mbus16 54 }

mbus16Value18		OBJECT-TYPE
			SYNTAX	INTEGER
			ACCESS	read-only
			STATUS	current
	DESCRIPTION ""
			::= { mbus16 55 }

mbus16VIF19		OBJECT-TYPE
			SYNTAX	INTEGER
			ACCESS	read-only
			STATUS	current
	DESCRIPTION ""
			::= { mbus16 56 }

mbus16Value19		OBJECT-TYPE
			SYNTAX	INTEGER
			ACCESS	read-only
			STATUS	current
	DESCRIPTION ""
			::= { mbus16 57 }

mbus16VIF1A		OBJECT-TYPE
			SYNTAX	INTEGER
			ACCESS	read-only
			STATUS	current
	DESCRIPTION ""
			::= { mbus16 58 }

mbus16Value1A		OBJECT-TYPE
			SYNTAX	INTEGER
			ACCESS	read-only
			STATUS	current
	DESCRIPTION ""
			::= { mbus16 59 }

mbus16VIF1B		OBJECT-TYPE
			SYNTAX	INTEGER
			ACCESS	read-only
			STATUS	current
	DESCRIPTION ""
			::= { mbus16 60 }

mbus16Value1B		OBJECT-TYPE
			SYNTAX	INTEGER
			ACCESS	read-only
			STATUS	current
	DESCRIPTION ""
			::= { mbus16 61 }

mbus16VIF1C		OBJECT-TYPE
			SYNTAX	INTEGER
			ACCESS	read-only
			STATUS	current
	DESCRIPTION ""
			::= { mbus16 62 }

mbus16Value1C		OBJECT-TYPE
			SYNTAX	INTEGER
			ACCESS	read-only
			STATUS	current
	DESCRIPTION ""
			::= { mbus16 63 }

mbus16VIF1D		OBJECT-TYPE
			SYNTAX	INTEGER
			ACCESS	read-only
			STATUS	current
	DESCRIPTION ""
			::= { mbus16 64 }

mbus16Value1D		OBJECT-TYPE
			SYNTAX	INTEGER
			ACCESS	read-only
			STATUS	current
	DESCRIPTION ""
			::= { mbus16 65 }

mbus16VIF1E		OBJECT-TYPE
			SYNTAX	INTEGER
			ACCESS	read-only
			STATUS	current
	DESCRIPTION ""
			::= { mbus16 66 }

mbus16Value1E		OBJECT-TYPE
			SYNTAX	INTEGER
			ACCESS	read-only
			STATUS	current
	DESCRIPTION ""
			::= { mbus16 67 }

mbus16VIF1F		OBJECT-TYPE
			SYNTAX	INTEGER
			ACCESS	read-only
			STATUS	current
	DESCRIPTION ""
			::= { mbus16 68 }

mbus16Value1F		OBJECT-TYPE
			SYNTAX	INTEGER
			ACCESS	read-only
			STATUS	current
	DESCRIPTION ""
			::= { mbus16 69 }

mbus16VIF20		OBJECT-TYPE
			SYNTAX	INTEGER
			ACCESS	read-only
			STATUS	current
	DESCRIPTION ""
			::= { mbus16 70 }

mbus16Value20		OBJECT-TYPE
			SYNTAX	INTEGER
			ACCESS	read-only
			STATUS	current
	DESCRIPTION ""
			::= { mbus16 71 }

mbus16VIF21		OBJECT-TYPE
			SYNTAX	INTEGER
			ACCESS	read-only
			STATUS	current
	DESCRIPTION ""
			::= { mbus16 72 }

mbus16Value21		OBJECT-TYPE
			SYNTAX	INTEGER
			ACCESS	read-only
			STATUS	current
	DESCRIPTION ""
			::= { mbus16 73 }

mbus16VIF22		OBJECT-TYPE
			SYNTAX	INTEGER
			ACCESS	read-only
			STATUS	current
	DESCRIPTION ""
			::= { mbus16 74 }

mbus16Value22		OBJECT-TYPE
			SYNTAX	INTEGER
			ACCESS	read-only
			STATUS	current
	DESCRIPTION ""
			::= { mbus16 75 }

mbus16VIF23		OBJECT-TYPE
			SYNTAX	INTEGER
			ACCESS	read-only
			STATUS	current
	DESCRIPTION ""
			::= { mbus16 76 }

mbus16Value23		OBJECT-TYPE
			SYNTAX	INTEGER
			ACCESS	read-only
			STATUS	current
	DESCRIPTION ""
			::= { mbus16 77 }

mbus16VIF24		OBJECT-TYPE
			SYNTAX	INTEGER
			ACCESS	read-only
			STATUS	current
	DESCRIPTION ""
			::= { mbus16 78 }

mbus16Value24		OBJECT-TYPE
			SYNTAX	INTEGER
			ACCESS	read-only
			STATUS	current
	DESCRIPTION ""
			::= { mbus16 79 }

mbus16VIF25		OBJECT-TYPE
			SYNTAX	INTEGER
			ACCESS	read-only
			STATUS	current
	DESCRIPTION ""
			::= { mbus16 80 }

mbus16Value25		OBJECT-TYPE
			SYNTAX	INTEGER
			ACCESS	read-only
			STATUS	current
	DESCRIPTION ""
			::= { mbus16 81 }

mbus16VIF26		OBJECT-TYPE
			SYNTAX	INTEGER
			ACCESS	read-only
			STATUS	current
	DESCRIPTION ""
			::= { mbus16 82 }

mbus16Value26		OBJECT-TYPE
			SYNTAX	INTEGER
			ACCESS	read-only
			STATUS	current
	DESCRIPTION ""
			::= { mbus16 83 }

mbus16VIF27		OBJECT-TYPE
			SYNTAX	INTEGER
			ACCESS	read-only
			STATUS	current
	DESCRIPTION ""
			::= { mbus16 84 }

mbus16Value27		OBJECT-TYPE
			SYNTAX	INTEGER
			ACCESS	read-only
			STATUS	current
	DESCRIPTION ""
			::= { mbus16 85 }

mbus16VIF28		OBJECT-TYPE
			SYNTAX	INTEGER
			ACCESS	read-only
			STATUS	current
	DESCRIPTION ""
			::= { mbus16 86 }

mbus16Value28		OBJECT-TYPE
			SYNTAX	INTEGER
			ACCESS	read-only
			STATUS	current
	DESCRIPTION ""
			::= { mbus16 87 }

mbus16VIF29		OBJECT-TYPE
			SYNTAX	INTEGER
			ACCESS	read-only
			STATUS	current
	DESCRIPTION ""
			::= { mbus16 88 }

mbus16Value29		OBJECT-TYPE
			SYNTAX	INTEGER
			ACCESS	read-only
			STATUS	current
	DESCRIPTION ""
			::= { mbus16 89 }

mbus16VIF2A		OBJECT-TYPE
			SYNTAX	INTEGER
			ACCESS	read-only
			STATUS	current
	DESCRIPTION ""
			::= { mbus16 90 }

mbus16Value2A		OBJECT-TYPE
			SYNTAX	INTEGER
			ACCESS	read-only
			STATUS	current
	DESCRIPTION ""
			::= { mbus16 91 }

mbus16VIF2B		OBJECT-TYPE
			SYNTAX	INTEGER
			ACCESS	read-only
			STATUS	current
	DESCRIPTION ""
			::= { mbus16 92 }

mbus16Value2B		OBJECT-TYPE
			SYNTAX	INTEGER
			ACCESS	read-only
			STATUS	current
	DESCRIPTION ""
			::= { mbus16 93 }

mbus16VIF2C		OBJECT-TYPE
			SYNTAX	INTEGER
			ACCESS	read-only
			STATUS	current
	DESCRIPTION ""
			::= { mbus16 94 }

mbus16Value2C		OBJECT-TYPE
			SYNTAX	INTEGER
			ACCESS	read-only
			STATUS	current
	DESCRIPTION ""
			::= { mbus16 95 }

mbus16VIF2D		OBJECT-TYPE
			SYNTAX	INTEGER
			ACCESS	read-only
			STATUS	current
	DESCRIPTION ""
			::= { mbus16 96 }

mbus16Value2D		OBJECT-TYPE
			SYNTAX	INTEGER
			ACCESS	read-only
			STATUS	current
	DESCRIPTION ""
			::= { mbus16 97 }

mbus16VIF2E		OBJECT-TYPE
			SYNTAX	INTEGER
			ACCESS	read-only
			STATUS	current
	DESCRIPTION ""
			::= { mbus16 98 }

mbus16Value2E		OBJECT-TYPE
			SYNTAX	INTEGER
			ACCESS	read-only
			STATUS	current
	DESCRIPTION ""
			::= { mbus16 99 }

mbus16VIF2F		OBJECT-TYPE
			SYNTAX	INTEGER
			ACCESS	read-only
			STATUS	current
	DESCRIPTION ""
			::= { mbus16 100 }

mbus16Value2F		OBJECT-TYPE
			SYNTAX	INTEGER
			ACCESS	read-only
			STATUS	current
	DESCRIPTION ""
			::= { mbus16 101 }

mbus17			OBJECT IDENTIFIER ::= { mbus 23 }

mbus17IdNumber		OBJECT-TYPE
			SYNTAX	Gauge
			ACCESS	read-only
			STATUS	current
	DESCRIPTION ""
			::= { mbus17 1 }

mbus17Manufacturer	OBJECT-TYPE
			SYNTAX	Gauge
			ACCESS	read-only
			STATUS	current
	DESCRIPTION ""
			::= { mbus17 2 }

mbus17Version		OBJECT-TYPE
			SYNTAX	Gauge
			ACCESS	read-only
			STATUS	current
	DESCRIPTION ""
			::= { mbus17 3 }

mbus17Medium		OBJECT-TYPE
			SYNTAX	Gauge
			ACCESS	read-only
			STATUS	current
	DESCRIPTION ""
			::= { mbus17 4 }

mbus17Status		OBJECT-TYPE
			SYNTAX	Gauge
			ACCESS	read-only
			STATUS	current
	DESCRIPTION ""
			::= { mbus17 5 }

mbus17VIF00		OBJECT-TYPE
			SYNTAX	INTEGER
			ACCESS	read-only
			STATUS	current
	DESCRIPTION ""
			::= { mbus17 6 }

mbus17Value00		OBJECT-TYPE
			SYNTAX	INTEGER
			ACCESS	read-only
			STATUS	current
	DESCRIPTION ""
			::= { mbus17 7 }

mbus17VIF01		OBJECT-TYPE
			SYNTAX	INTEGER
			ACCESS	read-only
			STATUS	current
	DESCRIPTION ""
			::= { mbus17 8 }

mbus17Value01		OBJECT-TYPE
			SYNTAX	INTEGER
			ACCESS	read-only
			STATUS	current
	DESCRIPTION ""
			::= { mbus17 9 }

mbus17VIF02		OBJECT-TYPE
			SYNTAX	INTEGER
			ACCESS	read-only
			STATUS	current
	DESCRIPTION ""
			::= { mbus17 10 }

mbus17Value02		OBJECT-TYPE
			SYNTAX	INTEGER
			ACCESS	read-only
			STATUS	current
	DESCRIPTION ""
			::= { mbus17 11 }

mbus17VIF03		OBJECT-TYPE
			SYNTAX	INTEGER
			ACCESS	read-only
			STATUS	current
	DESCRIPTION ""
			::= { mbus17 12 }

mbus17Value03		OBJECT-TYPE
			SYNTAX	INTEGER
			ACCESS	read-only
			STATUS	current
	DESCRIPTION ""
			::= { mbus17 13 }

mbus17VIF04		OBJECT-TYPE
			SYNTAX	INTEGER
			ACCESS	read-only
			STATUS	current
	DESCRIPTION ""
			::= { mbus17 14 }

mbus17Value04		OBJECT-TYPE
			SYNTAX	INTEGER
			ACCESS	read-only
			STATUS	current
	DESCRIPTION ""
			::= { mbus17 15 }

mbus17VIF05		OBJECT-TYPE
			SYNTAX	INTEGER
			ACCESS	read-only
			STATUS	current
	DESCRIPTION ""
			::= { mbus17 16 }

mbus17Value05		OBJECT-TYPE
			SYNTAX	INTEGER
			ACCESS	read-only
			STATUS	current
	DESCRIPTION ""
			::= { mbus17 17 }

mbus17VIF06		OBJECT-TYPE
			SYNTAX	INTEGER
			ACCESS	read-only
			STATUS	current
	DESCRIPTION ""
			::= { mbus17 18 }

mbus17Value06		OBJECT-TYPE
			SYNTAX	INTEGER
			ACCESS	read-only
			STATUS	current
	DESCRIPTION ""
			::= { mbus17 19 }

mbus17VIF07		OBJECT-TYPE
			SYNTAX	INTEGER
			ACCESS	read-only
			STATUS	current
	DESCRIPTION ""
			::= { mbus17 20 }

mbus17Value07		OBJECT-TYPE
			SYNTAX	INTEGER
			ACCESS	read-only
			STATUS	current
	DESCRIPTION ""
			::= { mbus17 21 }

mbus17VIF08		OBJECT-TYPE
			SYNTAX	INTEGER
			ACCESS	read-only
			STATUS	current
	DESCRIPTION ""
			::= { mbus17 22 }

mbus17Value08		OBJECT-TYPE
			SYNTAX	INTEGER
			ACCESS	read-only
			STATUS	current
	DESCRIPTION ""
			::= { mbus17 23 }

mbus17VIF09		OBJECT-TYPE
			SYNTAX	INTEGER
			ACCESS	read-only
			STATUS	current
	DESCRIPTION ""
			::= { mbus17 24 }

mbus17Value09		OBJECT-TYPE
			SYNTAX	INTEGER
			ACCESS	read-only
			STATUS	current
	DESCRIPTION ""
			::= { mbus17 25 }

mbus17VIF0A		OBJECT-TYPE
			SYNTAX	INTEGER
			ACCESS	read-only
			STATUS	current
	DESCRIPTION ""
			::= { mbus17 26 }

mbus17Value0A		OBJECT-TYPE
			SYNTAX	INTEGER
			ACCESS	read-only
			STATUS	current
	DESCRIPTION ""
			::= { mbus17 27 }

mbus17VIF0B		OBJECT-TYPE
			SYNTAX	INTEGER
			ACCESS	read-only
			STATUS	current
	DESCRIPTION ""
			::= { mbus17 28 }

mbus17Value0B		OBJECT-TYPE
			SYNTAX	INTEGER
			ACCESS	read-only
			STATUS	current
	DESCRIPTION ""
			::= { mbus17 29 }

mbus17VIF0C		OBJECT-TYPE
			SYNTAX	INTEGER
			ACCESS	read-only
			STATUS	current
	DESCRIPTION ""
			::= { mbus17 30 }

mbus17Value0C		OBJECT-TYPE
			SYNTAX	INTEGER
			ACCESS	read-only
			STATUS	current
	DESCRIPTION ""
			::= { mbus17 31 }

mbus17VIF0D		OBJECT-TYPE
			SYNTAX	INTEGER
			ACCESS	read-only
			STATUS	current
	DESCRIPTION ""
			::= { mbus17 32 }

mbus17Value0D		OBJECT-TYPE
			SYNTAX	INTEGER
			ACCESS	read-only
			STATUS	current
	DESCRIPTION ""
			::= { mbus17 33 }

mbus17VIF0E		OBJECT-TYPE
			SYNTAX	INTEGER
			ACCESS	read-only
			STATUS	current
	DESCRIPTION ""
			::= { mbus17 34 }

mbus17Value0E		OBJECT-TYPE
			SYNTAX	INTEGER
			ACCESS	read-only
			STATUS	current
	DESCRIPTION ""
			::= { mbus17 35 }

mbus17VIF0F		OBJECT-TYPE
			SYNTAX	INTEGER
			ACCESS	read-only
			STATUS	current
	DESCRIPTION ""
			::= { mbus17 36 }

mbus17Value0F		OBJECT-TYPE
			SYNTAX	INTEGER
			ACCESS	read-only
			STATUS	current
	DESCRIPTION ""
			::= { mbus17 37 }

mbus17VIF10		OBJECT-TYPE
			SYNTAX	INTEGER
			ACCESS	read-only
			STATUS	current
	DESCRIPTION ""
			::= { mbus17 38 }

mbus17Value10		OBJECT-TYPE
			SYNTAX	INTEGER
			ACCESS	read-only
			STATUS	current
	DESCRIPTION ""
			::= { mbus17 39 }

mbus17VIF11		OBJECT-TYPE
			SYNTAX	INTEGER
			ACCESS	read-only
			STATUS	current
	DESCRIPTION ""
			::= { mbus17 40 }

mbus17Value11		OBJECT-TYPE
			SYNTAX	INTEGER
			ACCESS	read-only
			STATUS	current
	DESCRIPTION ""
			::= { mbus17 41 }

mbus17VIF12		OBJECT-TYPE
			SYNTAX	INTEGER
			ACCESS	read-only
			STATUS	current
	DESCRIPTION ""
			::= { mbus17 42 }

mbus17Value12		OBJECT-TYPE
			SYNTAX	INTEGER
			ACCESS	read-only
			STATUS	current
	DESCRIPTION ""
			::= { mbus17 43 }

mbus17VIF13		OBJECT-TYPE
			SYNTAX	INTEGER
			ACCESS	read-only
			STATUS	current
	DESCRIPTION ""
			::= { mbus17 44 }

mbus17Value13		OBJECT-TYPE
			SYNTAX	INTEGER
			ACCESS	read-only
			STATUS	current
	DESCRIPTION ""
			::= { mbus17 45 }

mbus17VIF14		OBJECT-TYPE
			SYNTAX	INTEGER
			ACCESS	read-only
			STATUS	current
	DESCRIPTION ""
			::= { mbus17 46 }

mbus17Value14		OBJECT-TYPE
			SYNTAX	INTEGER
			ACCESS	read-only
			STATUS	current
	DESCRIPTION ""
			::= { mbus17 47 }

mbus17VIF15		OBJECT-TYPE
			SYNTAX	INTEGER
			ACCESS	read-only
			STATUS	current
	DESCRIPTION ""
			::= { mbus17 48 }

mbus17Value15		OBJECT-TYPE
			SYNTAX	INTEGER
			ACCESS	read-only
			STATUS	current
	DESCRIPTION ""
			::= { mbus17 49 }

mbus17VIF16		OBJECT-TYPE
			SYNTAX	INTEGER
			ACCESS	read-only
			STATUS	current
	DESCRIPTION ""
			::= { mbus17 50 }

mbus17Value16		OBJECT-TYPE
			SYNTAX	INTEGER
			ACCESS	read-only
			STATUS	current
	DESCRIPTION ""
			::= { mbus17 51 }

mbus17VIF17		OBJECT-TYPE
			SYNTAX	INTEGER
			ACCESS	read-only
			STATUS	current
	DESCRIPTION ""
			::= { mbus17 52 }

mbus17Value17		OBJECT-TYPE
			SYNTAX	INTEGER
			ACCESS	read-only
			STATUS	current
	DESCRIPTION ""
			::= { mbus17 53 }

mbus17VIF18		OBJECT-TYPE
			SYNTAX	INTEGER
			ACCESS	read-only
			STATUS	current
	DESCRIPTION ""
			::= { mbus17 54 }

mbus17Value18		OBJECT-TYPE
			SYNTAX	INTEGER
			ACCESS	read-only
			STATUS	current
	DESCRIPTION ""
			::= { mbus17 55 }

mbus17VIF19		OBJECT-TYPE
			SYNTAX	INTEGER
			ACCESS	read-only
			STATUS	current
	DESCRIPTION ""
			::= { mbus17 56 }

mbus17Value19		OBJECT-TYPE
			SYNTAX	INTEGER
			ACCESS	read-only
			STATUS	current
	DESCRIPTION ""
			::= { mbus17 57 }

mbus17VIF1A		OBJECT-TYPE
			SYNTAX	INTEGER
			ACCESS	read-only
			STATUS	current
	DESCRIPTION ""
			::= { mbus17 58 }

mbus17Value1A		OBJECT-TYPE
			SYNTAX	INTEGER
			ACCESS	read-only
			STATUS	current
	DESCRIPTION ""
			::= { mbus17 59 }

mbus17VIF1B		OBJECT-TYPE
			SYNTAX	INTEGER
			ACCESS	read-only
			STATUS	current
	DESCRIPTION ""
			::= { mbus17 60 }

mbus17Value1B		OBJECT-TYPE
			SYNTAX	INTEGER
			ACCESS	read-only
			STATUS	current
	DESCRIPTION ""
			::= { mbus17 61 }

mbus17VIF1C		OBJECT-TYPE
			SYNTAX	INTEGER
			ACCESS	read-only
			STATUS	current
	DESCRIPTION ""
			::= { mbus17 62 }

mbus17Value1C		OBJECT-TYPE
			SYNTAX	INTEGER
			ACCESS	read-only
			STATUS	current
	DESCRIPTION ""
			::= { mbus17 63 }

mbus17VIF1D		OBJECT-TYPE
			SYNTAX	INTEGER
			ACCESS	read-only
			STATUS	current
	DESCRIPTION ""
			::= { mbus17 64 }

mbus17Value1D		OBJECT-TYPE
			SYNTAX	INTEGER
			ACCESS	read-only
			STATUS	current
	DESCRIPTION ""
			::= { mbus17 65 }

mbus17VIF1E		OBJECT-TYPE
			SYNTAX	INTEGER
			ACCESS	read-only
			STATUS	current
	DESCRIPTION ""
			::= { mbus17 66 }

mbus17Value1E		OBJECT-TYPE
			SYNTAX	INTEGER
			ACCESS	read-only
			STATUS	current
	DESCRIPTION ""
			::= { mbus17 67 }

mbus17VIF1F		OBJECT-TYPE
			SYNTAX	INTEGER
			ACCESS	read-only
			STATUS	current
	DESCRIPTION ""
			::= { mbus17 68 }

mbus17Value1F		OBJECT-TYPE
			SYNTAX	INTEGER
			ACCESS	read-only
			STATUS	current
	DESCRIPTION ""
			::= { mbus17 69 }

mbus17VIF20		OBJECT-TYPE
			SYNTAX	INTEGER
			ACCESS	read-only
			STATUS	current
	DESCRIPTION ""
			::= { mbus17 70 }

mbus17Value20		OBJECT-TYPE
			SYNTAX	INTEGER
			ACCESS	read-only
			STATUS	current
	DESCRIPTION ""
			::= { mbus17 71 }

mbus17VIF21		OBJECT-TYPE
			SYNTAX	INTEGER
			ACCESS	read-only
			STATUS	current
	DESCRIPTION ""
			::= { mbus17 72 }

mbus17Value21		OBJECT-TYPE
			SYNTAX	INTEGER
			ACCESS	read-only
			STATUS	current
	DESCRIPTION ""
			::= { mbus17 73 }

mbus17VIF22		OBJECT-TYPE
			SYNTAX	INTEGER
			ACCESS	read-only
			STATUS	current
	DESCRIPTION ""
			::= { mbus17 74 }

mbus17Value22		OBJECT-TYPE
			SYNTAX	INTEGER
			ACCESS	read-only
			STATUS	current
	DESCRIPTION ""
			::= { mbus17 75 }

mbus17VIF23		OBJECT-TYPE
			SYNTAX	INTEGER
			ACCESS	read-only
			STATUS	current
	DESCRIPTION ""
			::= { mbus17 76 }

mbus17Value23		OBJECT-TYPE
			SYNTAX	INTEGER
			ACCESS	read-only
			STATUS	current
	DESCRIPTION ""
			::= { mbus17 77 }

mbus17VIF24		OBJECT-TYPE
			SYNTAX	INTEGER
			ACCESS	read-only
			STATUS	current
	DESCRIPTION ""
			::= { mbus17 78 }

mbus17Value24		OBJECT-TYPE
			SYNTAX	INTEGER
			ACCESS	read-only
			STATUS	current
	DESCRIPTION ""
			::= { mbus17 79 }

mbus17VIF25		OBJECT-TYPE
			SYNTAX	INTEGER
			ACCESS	read-only
			STATUS	current
	DESCRIPTION ""
			::= { mbus17 80 }

mbus17Value25		OBJECT-TYPE
			SYNTAX	INTEGER
			ACCESS	read-only
			STATUS	current
	DESCRIPTION ""
			::= { mbus17 81 }

mbus17VIF26		OBJECT-TYPE
			SYNTAX	INTEGER
			ACCESS	read-only
			STATUS	current
	DESCRIPTION ""
			::= { mbus17 82 }

mbus17Value26		OBJECT-TYPE
			SYNTAX	INTEGER
			ACCESS	read-only
			STATUS	current
	DESCRIPTION ""
			::= { mbus17 83 }

mbus17VIF27		OBJECT-TYPE
			SYNTAX	INTEGER
			ACCESS	read-only
			STATUS	current
	DESCRIPTION ""
			::= { mbus17 84 }

mbus17Value27		OBJECT-TYPE
			SYNTAX	INTEGER
			ACCESS	read-only
			STATUS	current
	DESCRIPTION ""
			::= { mbus17 85 }

mbus17VIF28		OBJECT-TYPE
			SYNTAX	INTEGER
			ACCESS	read-only
			STATUS	current
	DESCRIPTION ""
			::= { mbus17 86 }

mbus17Value28		OBJECT-TYPE
			SYNTAX	INTEGER
			ACCESS	read-only
			STATUS	current
	DESCRIPTION ""
			::= { mbus17 87 }

mbus17VIF29		OBJECT-TYPE
			SYNTAX	INTEGER
			ACCESS	read-only
			STATUS	current
	DESCRIPTION ""
			::= { mbus17 88 }

mbus17Value29		OBJECT-TYPE
			SYNTAX	INTEGER
			ACCESS	read-only
			STATUS	current
	DESCRIPTION ""
			::= { mbus17 89 }

mbus17VIF2A		OBJECT-TYPE
			SYNTAX	INTEGER
			ACCESS	read-only
			STATUS	current
	DESCRIPTION ""
			::= { mbus17 90 }

mbus17Value2A		OBJECT-TYPE
			SYNTAX	INTEGER
			ACCESS	read-only
			STATUS	current
	DESCRIPTION ""
			::= { mbus17 91 }

mbus17VIF2B		OBJECT-TYPE
			SYNTAX	INTEGER
			ACCESS	read-only
			STATUS	current
	DESCRIPTION ""
			::= { mbus17 92 }

mbus17Value2B		OBJECT-TYPE
			SYNTAX	INTEGER
			ACCESS	read-only
			STATUS	current
	DESCRIPTION ""
			::= { mbus17 93 }

mbus17VIF2C		OBJECT-TYPE
			SYNTAX	INTEGER
			ACCESS	read-only
			STATUS	current
	DESCRIPTION ""
			::= { mbus17 94 }

mbus17Value2C		OBJECT-TYPE
			SYNTAX	INTEGER
			ACCESS	read-only
			STATUS	current
	DESCRIPTION ""
			::= { mbus17 95 }

mbus17VIF2D		OBJECT-TYPE
			SYNTAX	INTEGER
			ACCESS	read-only
			STATUS	current
	DESCRIPTION ""
			::= { mbus17 96 }

mbus17Value2D		OBJECT-TYPE
			SYNTAX	INTEGER
			ACCESS	read-only
			STATUS	current
	DESCRIPTION ""
			::= { mbus17 97 }

mbus17VIF2E		OBJECT-TYPE
			SYNTAX	INTEGER
			ACCESS	read-only
			STATUS	current
	DESCRIPTION ""
			::= { mbus17 98 }

mbus17Value2E		OBJECT-TYPE
			SYNTAX	INTEGER
			ACCESS	read-only
			STATUS	current
	DESCRIPTION ""
			::= { mbus17 99 }

mbus17VIF2F		OBJECT-TYPE
			SYNTAX	INTEGER
			ACCESS	read-only
			STATUS	current
	DESCRIPTION ""
			::= { mbus17 100 }

mbus17Value2F		OBJECT-TYPE
			SYNTAX	INTEGER
			ACCESS	read-only
			STATUS	current
	DESCRIPTION ""
			::= { mbus17 101 }

mbus18			OBJECT IDENTIFIER ::= { mbus 24 }

mbus18IdNumber		OBJECT-TYPE
			SYNTAX	Gauge
			ACCESS	read-only
			STATUS	current
	DESCRIPTION ""
			::= { mbus18 1 }

mbus18Manufacturer	OBJECT-TYPE
			SYNTAX	Gauge
			ACCESS	read-only
			STATUS	current
	DESCRIPTION ""
			::= { mbus18 2 }

mbus18Version		OBJECT-TYPE
			SYNTAX	Gauge
			ACCESS	read-only
			STATUS	current
	DESCRIPTION ""
			::= { mbus18 3 }

mbus18Medium		OBJECT-TYPE
			SYNTAX	Gauge
			ACCESS	read-only
			STATUS	current
	DESCRIPTION ""
			::= { mbus18 4 }

mbus18Status		OBJECT-TYPE
			SYNTAX	Gauge
			ACCESS	read-only
			STATUS	current
	DESCRIPTION ""
			::= { mbus18 5 }

mbus18VIF00		OBJECT-TYPE
			SYNTAX	INTEGER
			ACCESS	read-only
			STATUS	current
	DESCRIPTION ""
			::= { mbus18 6 }

mbus18Value00		OBJECT-TYPE
			SYNTAX	INTEGER
			ACCESS	read-only
			STATUS	current
	DESCRIPTION ""
			::= { mbus18 7 }

mbus18VIF01		OBJECT-TYPE
			SYNTAX	INTEGER
			ACCESS	read-only
			STATUS	current
	DESCRIPTION ""
			::= { mbus18 8 }

mbus18Value01		OBJECT-TYPE
			SYNTAX	INTEGER
			ACCESS	read-only
			STATUS	current
	DESCRIPTION ""
			::= { mbus18 9 }

mbus18VIF02		OBJECT-TYPE
			SYNTAX	INTEGER
			ACCESS	read-only
			STATUS	current
	DESCRIPTION ""
			::= { mbus18 10 }

mbus18Value02		OBJECT-TYPE
			SYNTAX	INTEGER
			ACCESS	read-only
			STATUS	current
	DESCRIPTION ""
			::= { mbus18 11 }

mbus18VIF03		OBJECT-TYPE
			SYNTAX	INTEGER
			ACCESS	read-only
			STATUS	current
	DESCRIPTION ""
			::= { mbus18 12 }

mbus18Value03		OBJECT-TYPE
			SYNTAX	INTEGER
			ACCESS	read-only
			STATUS	current
	DESCRIPTION ""
			::= { mbus18 13 }

mbus18VIF04		OBJECT-TYPE
			SYNTAX	INTEGER
			ACCESS	read-only
			STATUS	current
	DESCRIPTION ""
			::= { mbus18 14 }

mbus18Value04		OBJECT-TYPE
			SYNTAX	INTEGER
			ACCESS	read-only
			STATUS	current
	DESCRIPTION ""
			::= { mbus18 15 }

mbus18VIF05		OBJECT-TYPE
			SYNTAX	INTEGER
			ACCESS	read-only
			STATUS	current
	DESCRIPTION ""
			::= { mbus18 16 }

mbus18Value05		OBJECT-TYPE
			SYNTAX	INTEGER
			ACCESS	read-only
			STATUS	current
	DESCRIPTION ""
			::= { mbus18 17 }

mbus18VIF06		OBJECT-TYPE
			SYNTAX	INTEGER
			ACCESS	read-only
			STATUS	current
	DESCRIPTION ""
			::= { mbus18 18 }

mbus18Value06		OBJECT-TYPE
			SYNTAX	INTEGER
			ACCESS	read-only
			STATUS	current
	DESCRIPTION ""
			::= { mbus18 19 }

mbus18VIF07		OBJECT-TYPE
			SYNTAX	INTEGER
			ACCESS	read-only
			STATUS	current
	DESCRIPTION ""
			::= { mbus18 20 }

mbus18Value07		OBJECT-TYPE
			SYNTAX	INTEGER
			ACCESS	read-only
			STATUS	current
	DESCRIPTION ""
			::= { mbus18 21 }

mbus18VIF08		OBJECT-TYPE
			SYNTAX	INTEGER
			ACCESS	read-only
			STATUS	current
	DESCRIPTION ""
			::= { mbus18 22 }

mbus18Value08		OBJECT-TYPE
			SYNTAX	INTEGER
			ACCESS	read-only
			STATUS	current
	DESCRIPTION ""
			::= { mbus18 23 }

mbus18VIF09		OBJECT-TYPE
			SYNTAX	INTEGER
			ACCESS	read-only
			STATUS	current
	DESCRIPTION ""
			::= { mbus18 24 }

mbus18Value09		OBJECT-TYPE
			SYNTAX	INTEGER
			ACCESS	read-only
			STATUS	current
	DESCRIPTION ""
			::= { mbus18 25 }

mbus18VIF0A		OBJECT-TYPE
			SYNTAX	INTEGER
			ACCESS	read-only
			STATUS	current
	DESCRIPTION ""
			::= { mbus18 26 }

mbus18Value0A		OBJECT-TYPE
			SYNTAX	INTEGER
			ACCESS	read-only
			STATUS	current
	DESCRIPTION ""
			::= { mbus18 27 }

mbus18VIF0B		OBJECT-TYPE
			SYNTAX	INTEGER
			ACCESS	read-only
			STATUS	current
	DESCRIPTION ""
			::= { mbus18 28 }

mbus18Value0B		OBJECT-TYPE
			SYNTAX	INTEGER
			ACCESS	read-only
			STATUS	current
	DESCRIPTION ""
			::= { mbus18 29 }

mbus18VIF0C		OBJECT-TYPE
			SYNTAX	INTEGER
			ACCESS	read-only
			STATUS	current
	DESCRIPTION ""
			::= { mbus18 30 }

mbus18Value0C		OBJECT-TYPE
			SYNTAX	INTEGER
			ACCESS	read-only
			STATUS	current
	DESCRIPTION ""
			::= { mbus18 31 }

mbus18VIF0D		OBJECT-TYPE
			SYNTAX	INTEGER
			ACCESS	read-only
			STATUS	current
	DESCRIPTION ""
			::= { mbus18 32 }

mbus18Value0D		OBJECT-TYPE
			SYNTAX	INTEGER
			ACCESS	read-only
			STATUS	current
	DESCRIPTION ""
			::= { mbus18 33 }

mbus18VIF0E		OBJECT-TYPE
			SYNTAX	INTEGER
			ACCESS	read-only
			STATUS	current
	DESCRIPTION ""
			::= { mbus18 34 }

mbus18Value0E		OBJECT-TYPE
			SYNTAX	INTEGER
			ACCESS	read-only
			STATUS	current
	DESCRIPTION ""
			::= { mbus18 35 }

mbus18VIF0F		OBJECT-TYPE
			SYNTAX	INTEGER
			ACCESS	read-only
			STATUS	current
	DESCRIPTION ""
			::= { mbus18 36 }

mbus18Value0F		OBJECT-TYPE
			SYNTAX	INTEGER
			ACCESS	read-only
			STATUS	current
	DESCRIPTION ""
			::= { mbus18 37 }

mbus18VIF10		OBJECT-TYPE
			SYNTAX	INTEGER
			ACCESS	read-only
			STATUS	current
	DESCRIPTION ""
			::= { mbus18 38 }

mbus18Value10		OBJECT-TYPE
			SYNTAX	INTEGER
			ACCESS	read-only
			STATUS	current
	DESCRIPTION ""
			::= { mbus18 39 }

mbus18VIF11		OBJECT-TYPE
			SYNTAX	INTEGER
			ACCESS	read-only
			STATUS	current
	DESCRIPTION ""
			::= { mbus18 40 }

mbus18Value11		OBJECT-TYPE
			SYNTAX	INTEGER
			ACCESS	read-only
			STATUS	current
	DESCRIPTION ""
			::= { mbus18 41 }

mbus18VIF12		OBJECT-TYPE
			SYNTAX	INTEGER
			ACCESS	read-only
			STATUS	current
	DESCRIPTION ""
			::= { mbus18 42 }

mbus18Value12		OBJECT-TYPE
			SYNTAX	INTEGER
			ACCESS	read-only
			STATUS	current
	DESCRIPTION ""
			::= { mbus18 43 }

mbus18VIF13		OBJECT-TYPE
			SYNTAX	INTEGER
			ACCESS	read-only
			STATUS	current
	DESCRIPTION ""
			::= { mbus18 44 }

mbus18Value13		OBJECT-TYPE
			SYNTAX	INTEGER
			ACCESS	read-only
			STATUS	current
	DESCRIPTION ""
			::= { mbus18 45 }

mbus18VIF14		OBJECT-TYPE
			SYNTAX	INTEGER
			ACCESS	read-only
			STATUS	current
	DESCRIPTION ""
			::= { mbus18 46 }

mbus18Value14		OBJECT-TYPE
			SYNTAX	INTEGER
			ACCESS	read-only
			STATUS	current
	DESCRIPTION ""
			::= { mbus18 47 }

mbus18VIF15		OBJECT-TYPE
			SYNTAX	INTEGER
			ACCESS	read-only
			STATUS	current
	DESCRIPTION ""
			::= { mbus18 48 }

mbus18Value15		OBJECT-TYPE
			SYNTAX	INTEGER
			ACCESS	read-only
			STATUS	current
	DESCRIPTION ""
			::= { mbus18 49 }

mbus18VIF16		OBJECT-TYPE
			SYNTAX	INTEGER
			ACCESS	read-only
			STATUS	current
	DESCRIPTION ""
			::= { mbus18 50 }

mbus18Value16		OBJECT-TYPE
			SYNTAX	INTEGER
			ACCESS	read-only
			STATUS	current
	DESCRIPTION ""
			::= { mbus18 51 }

mbus18VIF17		OBJECT-TYPE
			SYNTAX	INTEGER
			ACCESS	read-only
			STATUS	current
	DESCRIPTION ""
			::= { mbus18 52 }

mbus18Value17		OBJECT-TYPE
			SYNTAX	INTEGER
			ACCESS	read-only
			STATUS	current
	DESCRIPTION ""
			::= { mbus18 53 }

mbus18VIF18		OBJECT-TYPE
			SYNTAX	INTEGER
			ACCESS	read-only
			STATUS	current
	DESCRIPTION ""
			::= { mbus18 54 }

mbus18Value18		OBJECT-TYPE
			SYNTAX	INTEGER
			ACCESS	read-only
			STATUS	current
	DESCRIPTION ""
			::= { mbus18 55 }

mbus18VIF19		OBJECT-TYPE
			SYNTAX	INTEGER
			ACCESS	read-only
			STATUS	current
	DESCRIPTION ""
			::= { mbus18 56 }

mbus18Value19		OBJECT-TYPE
			SYNTAX	INTEGER
			ACCESS	read-only
			STATUS	current
	DESCRIPTION ""
			::= { mbus18 57 }

mbus18VIF1A		OBJECT-TYPE
			SYNTAX	INTEGER
			ACCESS	read-only
			STATUS	current
	DESCRIPTION ""
			::= { mbus18 58 }

mbus18Value1A		OBJECT-TYPE
			SYNTAX	INTEGER
			ACCESS	read-only
			STATUS	current
	DESCRIPTION ""
			::= { mbus18 59 }

mbus18VIF1B		OBJECT-TYPE
			SYNTAX	INTEGER
			ACCESS	read-only
			STATUS	current
	DESCRIPTION ""
			::= { mbus18 60 }

mbus18Value1B		OBJECT-TYPE
			SYNTAX	INTEGER
			ACCESS	read-only
			STATUS	current
	DESCRIPTION ""
			::= { mbus18 61 }

mbus18VIF1C		OBJECT-TYPE
			SYNTAX	INTEGER
			ACCESS	read-only
			STATUS	current
	DESCRIPTION ""
			::= { mbus18 62 }

mbus18Value1C		OBJECT-TYPE
			SYNTAX	INTEGER
			ACCESS	read-only
			STATUS	current
	DESCRIPTION ""
			::= { mbus18 63 }

mbus18VIF1D		OBJECT-TYPE
			SYNTAX	INTEGER
			ACCESS	read-only
			STATUS	current
	DESCRIPTION ""
			::= { mbus18 64 }

mbus18Value1D		OBJECT-TYPE
			SYNTAX	INTEGER
			ACCESS	read-only
			STATUS	current
	DESCRIPTION ""
			::= { mbus18 65 }

mbus18VIF1E		OBJECT-TYPE
			SYNTAX	INTEGER
			ACCESS	read-only
			STATUS	current
	DESCRIPTION ""
			::= { mbus18 66 }

mbus18Value1E		OBJECT-TYPE
			SYNTAX	INTEGER
			ACCESS	read-only
			STATUS	current
	DESCRIPTION ""
			::= { mbus18 67 }

mbus18VIF1F		OBJECT-TYPE
			SYNTAX	INTEGER
			ACCESS	read-only
			STATUS	current
	DESCRIPTION ""
			::= { mbus18 68 }

mbus18Value1F		OBJECT-TYPE
			SYNTAX	INTEGER
			ACCESS	read-only
			STATUS	current
	DESCRIPTION ""
			::= { mbus18 69 }

mbus18VIF20		OBJECT-TYPE
			SYNTAX	INTEGER
			ACCESS	read-only
			STATUS	current
	DESCRIPTION ""
			::= { mbus18 70 }

mbus18Value20		OBJECT-TYPE
			SYNTAX	INTEGER
			ACCESS	read-only
			STATUS	current
	DESCRIPTION ""
			::= { mbus18 71 }

mbus18VIF21		OBJECT-TYPE
			SYNTAX	INTEGER
			ACCESS	read-only
			STATUS	current
	DESCRIPTION ""
			::= { mbus18 72 }

mbus18Value21		OBJECT-TYPE
			SYNTAX	INTEGER
			ACCESS	read-only
			STATUS	current
	DESCRIPTION ""
			::= { mbus18 73 }

mbus18VIF22		OBJECT-TYPE
			SYNTAX	INTEGER
			ACCESS	read-only
			STATUS	current
	DESCRIPTION ""
			::= { mbus18 74 }

mbus18Value22		OBJECT-TYPE
			SYNTAX	INTEGER
			ACCESS	read-only
			STATUS	current
	DESCRIPTION ""
			::= { mbus18 75 }

mbus18VIF23		OBJECT-TYPE
			SYNTAX	INTEGER
			ACCESS	read-only
			STATUS	current
	DESCRIPTION ""
			::= { mbus18 76 }

mbus18Value23		OBJECT-TYPE
			SYNTAX	INTEGER
			ACCESS	read-only
			STATUS	current
	DESCRIPTION ""
			::= { mbus18 77 }

mbus18VIF24		OBJECT-TYPE
			SYNTAX	INTEGER
			ACCESS	read-only
			STATUS	current
	DESCRIPTION ""
			::= { mbus18 78 }

mbus18Value24		OBJECT-TYPE
			SYNTAX	INTEGER
			ACCESS	read-only
			STATUS	current
	DESCRIPTION ""
			::= { mbus18 79 }

mbus18VIF25		OBJECT-TYPE
			SYNTAX	INTEGER
			ACCESS	read-only
			STATUS	current
	DESCRIPTION ""
			::= { mbus18 80 }

mbus18Value25		OBJECT-TYPE
			SYNTAX	INTEGER
			ACCESS	read-only
			STATUS	current
	DESCRIPTION ""
			::= { mbus18 81 }

mbus18VIF26		OBJECT-TYPE
			SYNTAX	INTEGER
			ACCESS	read-only
			STATUS	current
	DESCRIPTION ""
			::= { mbus18 82 }

mbus18Value26		OBJECT-TYPE
			SYNTAX	INTEGER
			ACCESS	read-only
			STATUS	current
	DESCRIPTION ""
			::= { mbus18 83 }

mbus18VIF27		OBJECT-TYPE
			SYNTAX	INTEGER
			ACCESS	read-only
			STATUS	current
	DESCRIPTION ""
			::= { mbus18 84 }

mbus18Value27		OBJECT-TYPE
			SYNTAX	INTEGER
			ACCESS	read-only
			STATUS	current
	DESCRIPTION ""
			::= { mbus18 85 }

mbus18VIF28		OBJECT-TYPE
			SYNTAX	INTEGER
			ACCESS	read-only
			STATUS	current
	DESCRIPTION ""
			::= { mbus18 86 }

mbus18Value28		OBJECT-TYPE
			SYNTAX	INTEGER
			ACCESS	read-only
			STATUS	current
	DESCRIPTION ""
			::= { mbus18 87 }

mbus18VIF29		OBJECT-TYPE
			SYNTAX	INTEGER
			ACCESS	read-only
			STATUS	current
	DESCRIPTION ""
			::= { mbus18 88 }

mbus18Value29		OBJECT-TYPE
			SYNTAX	INTEGER
			ACCESS	read-only
			STATUS	current
	DESCRIPTION ""
			::= { mbus18 89 }

mbus18VIF2A		OBJECT-TYPE
			SYNTAX	INTEGER
			ACCESS	read-only
			STATUS	current
	DESCRIPTION ""
			::= { mbus18 90 }

mbus18Value2A		OBJECT-TYPE
			SYNTAX	INTEGER
			ACCESS	read-only
			STATUS	current
	DESCRIPTION ""
			::= { mbus18 91 }

mbus18VIF2B		OBJECT-TYPE
			SYNTAX	INTEGER
			ACCESS	read-only
			STATUS	current
	DESCRIPTION ""
			::= { mbus18 92 }

mbus18Value2B		OBJECT-TYPE
			SYNTAX	INTEGER
			ACCESS	read-only
			STATUS	current
	DESCRIPTION ""
			::= { mbus18 93 }

mbus18VIF2C		OBJECT-TYPE
			SYNTAX	INTEGER
			ACCESS	read-only
			STATUS	current
	DESCRIPTION ""
			::= { mbus18 94 }

mbus18Value2C		OBJECT-TYPE
			SYNTAX	INTEGER
			ACCESS	read-only
			STATUS	current
	DESCRIPTION ""
			::= { mbus18 95 }

mbus18VIF2D		OBJECT-TYPE
			SYNTAX	INTEGER
			ACCESS	read-only
			STATUS	current
	DESCRIPTION ""
			::= { mbus18 96 }

mbus18Value2D		OBJECT-TYPE
			SYNTAX	INTEGER
			ACCESS	read-only
			STATUS	current
	DESCRIPTION ""
			::= { mbus18 97 }

mbus18VIF2E		OBJECT-TYPE
			SYNTAX	INTEGER
			ACCESS	read-only
			STATUS	current
	DESCRIPTION ""
			::= { mbus18 98 }

mbus18Value2E		OBJECT-TYPE
			SYNTAX	INTEGER
			ACCESS	read-only
			STATUS	current
	DESCRIPTION ""
			::= { mbus18 99 }

mbus18VIF2F		OBJECT-TYPE
			SYNTAX	INTEGER
			ACCESS	read-only
			STATUS	current
	DESCRIPTION ""
			::= { mbus18 100 }

mbus18Value2F		OBJECT-TYPE
			SYNTAX	INTEGER
			ACCESS	read-only
			STATUS	current
	DESCRIPTION ""
			::= { mbus18 101 }

mbus19			OBJECT IDENTIFIER ::= { mbus 25 }

mbus19IdNumber		OBJECT-TYPE
			SYNTAX	Gauge
			ACCESS	read-only
			STATUS	current
	DESCRIPTION ""
			::= { mbus19 1 }

mbus19Manufacturer	OBJECT-TYPE
			SYNTAX	Gauge
			ACCESS	read-only
			STATUS	current
	DESCRIPTION ""
			::= { mbus19 2 }

mbus19Version		OBJECT-TYPE
			SYNTAX	Gauge
			ACCESS	read-only
			STATUS	current
	DESCRIPTION ""
			::= { mbus19 3 }

mbus19Medium		OBJECT-TYPE
			SYNTAX	Gauge
			ACCESS	read-only
			STATUS	current
	DESCRIPTION ""
			::= { mbus19 4 }

mbus19Status		OBJECT-TYPE
			SYNTAX	Gauge
			ACCESS	read-only
			STATUS	current
	DESCRIPTION ""
			::= { mbus19 5 }

mbus19VIF00		OBJECT-TYPE
			SYNTAX	INTEGER
			ACCESS	read-only
			STATUS	current
	DESCRIPTION ""
			::= { mbus19 6 }

mbus19Value00		OBJECT-TYPE
			SYNTAX	INTEGER
			ACCESS	read-only
			STATUS	current
	DESCRIPTION ""
			::= { mbus19 7 }

mbus19VIF01		OBJECT-TYPE
			SYNTAX	INTEGER
			ACCESS	read-only
			STATUS	current
	DESCRIPTION ""
			::= { mbus19 8 }

mbus19Value01		OBJECT-TYPE
			SYNTAX	INTEGER
			ACCESS	read-only
			STATUS	current
	DESCRIPTION ""
			::= { mbus19 9 }

mbus19VIF02		OBJECT-TYPE
			SYNTAX	INTEGER
			ACCESS	read-only
			STATUS	current
	DESCRIPTION ""
			::= { mbus19 10 }

mbus19Value02		OBJECT-TYPE
			SYNTAX	INTEGER
			ACCESS	read-only
			STATUS	current
	DESCRIPTION ""
			::= { mbus19 11 }

mbus19VIF03		OBJECT-TYPE
			SYNTAX	INTEGER
			ACCESS	read-only
			STATUS	current
	DESCRIPTION ""
			::= { mbus19 12 }

mbus19Value03		OBJECT-TYPE
			SYNTAX	INTEGER
			ACCESS	read-only
			STATUS	current
	DESCRIPTION ""
			::= { mbus19 13 }

mbus19VIF04		OBJECT-TYPE
			SYNTAX	INTEGER
			ACCESS	read-only
			STATUS	current
	DESCRIPTION ""
			::= { mbus19 14 }

mbus19Value04		OBJECT-TYPE
			SYNTAX	INTEGER
			ACCESS	read-only
			STATUS	current
	DESCRIPTION ""
			::= { mbus19 15 }

mbus19VIF05		OBJECT-TYPE
			SYNTAX	INTEGER
			ACCESS	read-only
			STATUS	current
	DESCRIPTION ""
			::= { mbus19 16 }

mbus19Value05		OBJECT-TYPE
			SYNTAX	INTEGER
			ACCESS	read-only
			STATUS	current
	DESCRIPTION ""
			::= { mbus19 17 }

mbus19VIF06		OBJECT-TYPE
			SYNTAX	INTEGER
			ACCESS	read-only
			STATUS	current
	DESCRIPTION ""
			::= { mbus19 18 }

mbus19Value06		OBJECT-TYPE
			SYNTAX	INTEGER
			ACCESS	read-only
			STATUS	current
	DESCRIPTION ""
			::= { mbus19 19 }

mbus19VIF07		OBJECT-TYPE
			SYNTAX	INTEGER
			ACCESS	read-only
			STATUS	current
	DESCRIPTION ""
			::= { mbus19 20 }

mbus19Value07		OBJECT-TYPE
			SYNTAX	INTEGER
			ACCESS	read-only
			STATUS	current
	DESCRIPTION ""
			::= { mbus19 21 }

mbus19VIF08		OBJECT-TYPE
			SYNTAX	INTEGER
			ACCESS	read-only
			STATUS	current
	DESCRIPTION ""
			::= { mbus19 22 }

mbus19Value08		OBJECT-TYPE
			SYNTAX	INTEGER
			ACCESS	read-only
			STATUS	current
	DESCRIPTION ""
			::= { mbus19 23 }

mbus19VIF09		OBJECT-TYPE
			SYNTAX	INTEGER
			ACCESS	read-only
			STATUS	current
	DESCRIPTION ""
			::= { mbus19 24 }

mbus19Value09		OBJECT-TYPE
			SYNTAX	INTEGER
			ACCESS	read-only
			STATUS	current
	DESCRIPTION ""
			::= { mbus19 25 }

mbus19VIF0A		OBJECT-TYPE
			SYNTAX	INTEGER
			ACCESS	read-only
			STATUS	current
	DESCRIPTION ""
			::= { mbus19 26 }

mbus19Value0A		OBJECT-TYPE
			SYNTAX	INTEGER
			ACCESS	read-only
			STATUS	current
	DESCRIPTION ""
			::= { mbus19 27 }

mbus19VIF0B		OBJECT-TYPE
			SYNTAX	INTEGER
			ACCESS	read-only
			STATUS	current
	DESCRIPTION ""
			::= { mbus19 28 }

mbus19Value0B		OBJECT-TYPE
			SYNTAX	INTEGER
			ACCESS	read-only
			STATUS	current
	DESCRIPTION ""
			::= { mbus19 29 }

mbus19VIF0C		OBJECT-TYPE
			SYNTAX	INTEGER
			ACCESS	read-only
			STATUS	current
	DESCRIPTION ""
			::= { mbus19 30 }

mbus19Value0C		OBJECT-TYPE
			SYNTAX	INTEGER
			ACCESS	read-only
			STATUS	current
	DESCRIPTION ""
			::= { mbus19 31 }

mbus19VIF0D		OBJECT-TYPE
			SYNTAX	INTEGER
			ACCESS	read-only
			STATUS	current
	DESCRIPTION ""
			::= { mbus19 32 }

mbus19Value0D		OBJECT-TYPE
			SYNTAX	INTEGER
			ACCESS	read-only
			STATUS	current
	DESCRIPTION ""
			::= { mbus19 33 }

mbus19VIF0E		OBJECT-TYPE
			SYNTAX	INTEGER
			ACCESS	read-only
			STATUS	current
	DESCRIPTION ""
			::= { mbus19 34 }

mbus19Value0E		OBJECT-TYPE
			SYNTAX	INTEGER
			ACCESS	read-only
			STATUS	current
	DESCRIPTION ""
			::= { mbus19 35 }

mbus19VIF0F		OBJECT-TYPE
			SYNTAX	INTEGER
			ACCESS	read-only
			STATUS	current
	DESCRIPTION ""
			::= { mbus19 36 }

mbus19Value0F		OBJECT-TYPE
			SYNTAX	INTEGER
			ACCESS	read-only
			STATUS	current
	DESCRIPTION ""
			::= { mbus19 37 }

mbus19VIF10		OBJECT-TYPE
			SYNTAX	INTEGER
			ACCESS	read-only
			STATUS	current
	DESCRIPTION ""
			::= { mbus19 38 }

mbus19Value10		OBJECT-TYPE
			SYNTAX	INTEGER
			ACCESS	read-only
			STATUS	current
	DESCRIPTION ""
			::= { mbus19 39 }

mbus19VIF11		OBJECT-TYPE
			SYNTAX	INTEGER
			ACCESS	read-only
			STATUS	current
	DESCRIPTION ""
			::= { mbus19 40 }

mbus19Value11		OBJECT-TYPE
			SYNTAX	INTEGER
			ACCESS	read-only
			STATUS	current
	DESCRIPTION ""
			::= { mbus19 41 }

mbus19VIF12		OBJECT-TYPE
			SYNTAX	INTEGER
			ACCESS	read-only
			STATUS	current
	DESCRIPTION ""
			::= { mbus19 42 }

mbus19Value12		OBJECT-TYPE
			SYNTAX	INTEGER
			ACCESS	read-only
			STATUS	current
	DESCRIPTION ""
			::= { mbus19 43 }

mbus19VIF13		OBJECT-TYPE
			SYNTAX	INTEGER
			ACCESS	read-only
			STATUS	current
	DESCRIPTION ""
			::= { mbus19 44 }

mbus19Value13		OBJECT-TYPE
			SYNTAX	INTEGER
			ACCESS	read-only
			STATUS	current
	DESCRIPTION ""
			::= { mbus19 45 }

mbus19VIF14		OBJECT-TYPE
			SYNTAX	INTEGER
			ACCESS	read-only
			STATUS	current
	DESCRIPTION ""
			::= { mbus19 46 }

mbus19Value14		OBJECT-TYPE
			SYNTAX	INTEGER
			ACCESS	read-only
			STATUS	current
	DESCRIPTION ""
			::= { mbus19 47 }

mbus19VIF15		OBJECT-TYPE
			SYNTAX	INTEGER
			ACCESS	read-only
			STATUS	current
	DESCRIPTION ""
			::= { mbus19 48 }

mbus19Value15		OBJECT-TYPE
			SYNTAX	INTEGER
			ACCESS	read-only
			STATUS	current
	DESCRIPTION ""
			::= { mbus19 49 }

mbus19VIF16		OBJECT-TYPE
			SYNTAX	INTEGER
			ACCESS	read-only
			STATUS	current
	DESCRIPTION ""
			::= { mbus19 50 }

mbus19Value16		OBJECT-TYPE
			SYNTAX	INTEGER
			ACCESS	read-only
			STATUS	current
	DESCRIPTION ""
			::= { mbus19 51 }

mbus19VIF17		OBJECT-TYPE
			SYNTAX	INTEGER
			ACCESS	read-only
			STATUS	current
	DESCRIPTION ""
			::= { mbus19 52 }

mbus19Value17		OBJECT-TYPE
			SYNTAX	INTEGER
			ACCESS	read-only
			STATUS	current
	DESCRIPTION ""
			::= { mbus19 53 }

mbus19VIF18		OBJECT-TYPE
			SYNTAX	INTEGER
			ACCESS	read-only
			STATUS	current
	DESCRIPTION ""
			::= { mbus19 54 }

mbus19Value18		OBJECT-TYPE
			SYNTAX	INTEGER
			ACCESS	read-only
			STATUS	current
	DESCRIPTION ""
			::= { mbus19 55 }

mbus19VIF19		OBJECT-TYPE
			SYNTAX	INTEGER
			ACCESS	read-only
			STATUS	current
	DESCRIPTION ""
			::= { mbus19 56 }

mbus19Value19		OBJECT-TYPE
			SYNTAX	INTEGER
			ACCESS	read-only
			STATUS	current
	DESCRIPTION ""
			::= { mbus19 57 }

mbus19VIF1A		OBJECT-TYPE
			SYNTAX	INTEGER
			ACCESS	read-only
			STATUS	current
	DESCRIPTION ""
			::= { mbus19 58 }

mbus19Value1A		OBJECT-TYPE
			SYNTAX	INTEGER
			ACCESS	read-only
			STATUS	current
	DESCRIPTION ""
			::= { mbus19 59 }

mbus19VIF1B		OBJECT-TYPE
			SYNTAX	INTEGER
			ACCESS	read-only
			STATUS	current
	DESCRIPTION ""
			::= { mbus19 60 }

mbus19Value1B		OBJECT-TYPE
			SYNTAX	INTEGER
			ACCESS	read-only
			STATUS	current
	DESCRIPTION ""
			::= { mbus19 61 }

mbus19VIF1C		OBJECT-TYPE
			SYNTAX	INTEGER
			ACCESS	read-only
			STATUS	current
	DESCRIPTION ""
			::= { mbus19 62 }

mbus19Value1C		OBJECT-TYPE
			SYNTAX	INTEGER
			ACCESS	read-only
			STATUS	current
	DESCRIPTION ""
			::= { mbus19 63 }

mbus19VIF1D		OBJECT-TYPE
			SYNTAX	INTEGER
			ACCESS	read-only
			STATUS	current
	DESCRIPTION ""
			::= { mbus19 64 }

mbus19Value1D		OBJECT-TYPE
			SYNTAX	INTEGER
			ACCESS	read-only
			STATUS	current
	DESCRIPTION ""
			::= { mbus19 65 }

mbus19VIF1E		OBJECT-TYPE
			SYNTAX	INTEGER
			ACCESS	read-only
			STATUS	current
	DESCRIPTION ""
			::= { mbus19 66 }

mbus19Value1E		OBJECT-TYPE
			SYNTAX	INTEGER
			ACCESS	read-only
			STATUS	current
	DESCRIPTION ""
			::= { mbus19 67 }

mbus19VIF1F		OBJECT-TYPE
			SYNTAX	INTEGER
			ACCESS	read-only
			STATUS	current
	DESCRIPTION ""
			::= { mbus19 68 }

mbus19Value1F		OBJECT-TYPE
			SYNTAX	INTEGER
			ACCESS	read-only
			STATUS	current
	DESCRIPTION ""
			::= { mbus19 69 }

mbus19VIF20		OBJECT-TYPE
			SYNTAX	INTEGER
			ACCESS	read-only
			STATUS	current
	DESCRIPTION ""
			::= { mbus19 70 }

mbus19Value20		OBJECT-TYPE
			SYNTAX	INTEGER
			ACCESS	read-only
			STATUS	current
	DESCRIPTION ""
			::= { mbus19 71 }

mbus19VIF21		OBJECT-TYPE
			SYNTAX	INTEGER
			ACCESS	read-only
			STATUS	current
	DESCRIPTION ""
			::= { mbus19 72 }

mbus19Value21		OBJECT-TYPE
			SYNTAX	INTEGER
			ACCESS	read-only
			STATUS	current
	DESCRIPTION ""
			::= { mbus19 73 }

mbus19VIF22		OBJECT-TYPE
			SYNTAX	INTEGER
			ACCESS	read-only
			STATUS	current
	DESCRIPTION ""
			::= { mbus19 74 }

mbus19Value22		OBJECT-TYPE
			SYNTAX	INTEGER
			ACCESS	read-only
			STATUS	current
	DESCRIPTION ""
			::= { mbus19 75 }

mbus19VIF23		OBJECT-TYPE
			SYNTAX	INTEGER
			ACCESS	read-only
			STATUS	current
	DESCRIPTION ""
			::= { mbus19 76 }

mbus19Value23		OBJECT-TYPE
			SYNTAX	INTEGER
			ACCESS	read-only
			STATUS	current
	DESCRIPTION ""
			::= { mbus19 77 }

mbus19VIF24		OBJECT-TYPE
			SYNTAX	INTEGER
			ACCESS	read-only
			STATUS	current
	DESCRIPTION ""
			::= { mbus19 78 }

mbus19Value24		OBJECT-TYPE
			SYNTAX	INTEGER
			ACCESS	read-only
			STATUS	current
	DESCRIPTION ""
			::= { mbus19 79 }

mbus19VIF25		OBJECT-TYPE
			SYNTAX	INTEGER
			ACCESS	read-only
			STATUS	current
	DESCRIPTION ""
			::= { mbus19 80 }

mbus19Value25		OBJECT-TYPE
			SYNTAX	INTEGER
			ACCESS	read-only
			STATUS	current
	DESCRIPTION ""
			::= { mbus19 81 }

mbus19VIF26		OBJECT-TYPE
			SYNTAX	INTEGER
			ACCESS	read-only
			STATUS	current
	DESCRIPTION ""
			::= { mbus19 82 }

mbus19Value26		OBJECT-TYPE
			SYNTAX	INTEGER
			ACCESS	read-only
			STATUS	current
	DESCRIPTION ""
			::= { mbus19 83 }

mbus19VIF27		OBJECT-TYPE
			SYNTAX	INTEGER
			ACCESS	read-only
			STATUS	current
	DESCRIPTION ""
			::= { mbus19 84 }

mbus19Value27		OBJECT-TYPE
			SYNTAX	INTEGER
			ACCESS	read-only
			STATUS	current
	DESCRIPTION ""
			::= { mbus19 85 }

mbus19VIF28		OBJECT-TYPE
			SYNTAX	INTEGER
			ACCESS	read-only
			STATUS	current
	DESCRIPTION ""
			::= { mbus19 86 }

mbus19Value28		OBJECT-TYPE
			SYNTAX	INTEGER
			ACCESS	read-only
			STATUS	current
	DESCRIPTION ""
			::= { mbus19 87 }

mbus19VIF29		OBJECT-TYPE
			SYNTAX	INTEGER
			ACCESS	read-only
			STATUS	current
	DESCRIPTION ""
			::= { mbus19 88 }

mbus19Value29		OBJECT-TYPE
			SYNTAX	INTEGER
			ACCESS	read-only
			STATUS	current
	DESCRIPTION ""
			::= { mbus19 89 }

mbus19VIF2A		OBJECT-TYPE
			SYNTAX	INTEGER
			ACCESS	read-only
			STATUS	current
	DESCRIPTION ""
			::= { mbus19 90 }

mbus19Value2A		OBJECT-TYPE
			SYNTAX	INTEGER
			ACCESS	read-only
			STATUS	current
	DESCRIPTION ""
			::= { mbus19 91 }

mbus19VIF2B		OBJECT-TYPE
			SYNTAX	INTEGER
			ACCESS	read-only
			STATUS	current
	DESCRIPTION ""
			::= { mbus19 92 }

mbus19Value2B		OBJECT-TYPE
			SYNTAX	INTEGER
			ACCESS	read-only
			STATUS	current
	DESCRIPTION ""
			::= { mbus19 93 }

mbus19VIF2C		OBJECT-TYPE
			SYNTAX	INTEGER
			ACCESS	read-only
			STATUS	current
	DESCRIPTION ""
			::= { mbus19 94 }

mbus19Value2C		OBJECT-TYPE
			SYNTAX	INTEGER
			ACCESS	read-only
			STATUS	current
	DESCRIPTION ""
			::= { mbus19 95 }

mbus19VIF2D		OBJECT-TYPE
			SYNTAX	INTEGER
			ACCESS	read-only
			STATUS	current
	DESCRIPTION ""
			::= { mbus19 96 }

mbus19Value2D		OBJECT-TYPE
			SYNTAX	INTEGER
			ACCESS	read-only
			STATUS	current
	DESCRIPTION ""
			::= { mbus19 97 }

mbus19VIF2E		OBJECT-TYPE
			SYNTAX	INTEGER
			ACCESS	read-only
			STATUS	current
	DESCRIPTION ""
			::= { mbus19 98 }

mbus19Value2E		OBJECT-TYPE
			SYNTAX	INTEGER
			ACCESS	read-only
			STATUS	current
	DESCRIPTION ""
			::= { mbus19 99 }

mbus19VIF2F		OBJECT-TYPE
			SYNTAX	INTEGER
			ACCESS	read-only
			STATUS	current
	DESCRIPTION ""
			::= { mbus19 100 }

mbus19Value2F		OBJECT-TYPE
			SYNTAX	INTEGER
			ACCESS	read-only
			STATUS	current
	DESCRIPTION ""
			::= { mbus19 101 }

mbus1A			OBJECT IDENTIFIER ::= { mbus 26 }

mbus1AIdNumber		OBJECT-TYPE
			SYNTAX	Gauge
			ACCESS	read-only
			STATUS	current
	DESCRIPTION ""
			::= { mbus1A 1 }

mbus1AManufacturer	OBJECT-TYPE
			SYNTAX	Gauge
			ACCESS	read-only
			STATUS	current
	DESCRIPTION ""
			::= { mbus1A 2 }

mbus1AVersion		OBJECT-TYPE
			SYNTAX	Gauge
			ACCESS	read-only
			STATUS	current
	DESCRIPTION ""
			::= { mbus1A 3 }

mbus1AMedium		OBJECT-TYPE
			SYNTAX	Gauge
			ACCESS	read-only
			STATUS	current
	DESCRIPTION ""
			::= { mbus1A 4 }

mbus1AStatus		OBJECT-TYPE
			SYNTAX	Gauge
			ACCESS	read-only
			STATUS	current
	DESCRIPTION ""
			::= { mbus1A 5 }

mbus1AVIF00		OBJECT-TYPE
			SYNTAX	INTEGER
			ACCESS	read-only
			STATUS	current
	DESCRIPTION ""
			::= { mbus1A 6 }

mbus1AValue00		OBJECT-TYPE
			SYNTAX	INTEGER
			ACCESS	read-only
			STATUS	current
	DESCRIPTION ""
			::= { mbus1A 7 }

mbus1AVIF01		OBJECT-TYPE
			SYNTAX	INTEGER
			ACCESS	read-only
			STATUS	current
	DESCRIPTION ""
			::= { mbus1A 8 }

mbus1AValue01		OBJECT-TYPE
			SYNTAX	INTEGER
			ACCESS	read-only
			STATUS	current
	DESCRIPTION ""
			::= { mbus1A 9 }

mbus1AVIF02		OBJECT-TYPE
			SYNTAX	INTEGER
			ACCESS	read-only
			STATUS	current
	DESCRIPTION ""
			::= { mbus1A 10 }

mbus1AValue02		OBJECT-TYPE
			SYNTAX	INTEGER
			ACCESS	read-only
			STATUS	current
	DESCRIPTION ""
			::= { mbus1A 11 }

mbus1AVIF03		OBJECT-TYPE
			SYNTAX	INTEGER
			ACCESS	read-only
			STATUS	current
	DESCRIPTION ""
			::= { mbus1A 12 }

mbus1AValue03		OBJECT-TYPE
			SYNTAX	INTEGER
			ACCESS	read-only
			STATUS	current
	DESCRIPTION ""
			::= { mbus1A 13 }

mbus1AVIF04		OBJECT-TYPE
			SYNTAX	INTEGER
			ACCESS	read-only
			STATUS	current
	DESCRIPTION ""
			::= { mbus1A 14 }

mbus1AValue04		OBJECT-TYPE
			SYNTAX	INTEGER
			ACCESS	read-only
			STATUS	current
	DESCRIPTION ""
			::= { mbus1A 15 }

mbus1AVIF05		OBJECT-TYPE
			SYNTAX	INTEGER
			ACCESS	read-only
			STATUS	current
	DESCRIPTION ""
			::= { mbus1A 16 }

mbus1AValue05		OBJECT-TYPE
			SYNTAX	INTEGER
			ACCESS	read-only
			STATUS	current
	DESCRIPTION ""
			::= { mbus1A 17 }

mbus1AVIF06		OBJECT-TYPE
			SYNTAX	INTEGER
			ACCESS	read-only
			STATUS	current
	DESCRIPTION ""
			::= { mbus1A 18 }

mbus1AValue06		OBJECT-TYPE
			SYNTAX	INTEGER
			ACCESS	read-only
			STATUS	current
	DESCRIPTION ""
			::= { mbus1A 19 }

mbus1AVIF07		OBJECT-TYPE
			SYNTAX	INTEGER
			ACCESS	read-only
			STATUS	current
	DESCRIPTION ""
			::= { mbus1A 20 }

mbus1AValue07		OBJECT-TYPE
			SYNTAX	INTEGER
			ACCESS	read-only
			STATUS	current
	DESCRIPTION ""
			::= { mbus1A 21 }

mbus1AVIF08		OBJECT-TYPE
			SYNTAX	INTEGER
			ACCESS	read-only
			STATUS	current
	DESCRIPTION ""
			::= { mbus1A 22 }

mbus1AValue08		OBJECT-TYPE
			SYNTAX	INTEGER
			ACCESS	read-only
			STATUS	current
	DESCRIPTION ""
			::= { mbus1A 23 }

mbus1AVIF09		OBJECT-TYPE
			SYNTAX	INTEGER
			ACCESS	read-only
			STATUS	current
	DESCRIPTION ""
			::= { mbus1A 24 }

mbus1AValue09		OBJECT-TYPE
			SYNTAX	INTEGER
			ACCESS	read-only
			STATUS	current
	DESCRIPTION ""
			::= { mbus1A 25 }

mbus1AVIF0A		OBJECT-TYPE
			SYNTAX	INTEGER
			ACCESS	read-only
			STATUS	current
	DESCRIPTION ""
			::= { mbus1A 26 }

mbus1AValue0A		OBJECT-TYPE
			SYNTAX	INTEGER
			ACCESS	read-only
			STATUS	current
	DESCRIPTION ""
			::= { mbus1A 27 }

mbus1AVIF0B		OBJECT-TYPE
			SYNTAX	INTEGER
			ACCESS	read-only
			STATUS	current
	DESCRIPTION ""
			::= { mbus1A 28 }

mbus1AValue0B		OBJECT-TYPE
			SYNTAX	INTEGER
			ACCESS	read-only
			STATUS	current
	DESCRIPTION ""
			::= { mbus1A 29 }

mbus1AVIF0C		OBJECT-TYPE
			SYNTAX	INTEGER
			ACCESS	read-only
			STATUS	current
	DESCRIPTION ""
			::= { mbus1A 30 }

mbus1AValue0C		OBJECT-TYPE
			SYNTAX	INTEGER
			ACCESS	read-only
			STATUS	current
	DESCRIPTION ""
			::= { mbus1A 31 }

mbus1AVIF0D		OBJECT-TYPE
			SYNTAX	INTEGER
			ACCESS	read-only
			STATUS	current
	DESCRIPTION ""
			::= { mbus1A 32 }

mbus1AValue0D		OBJECT-TYPE
			SYNTAX	INTEGER
			ACCESS	read-only
			STATUS	current
	DESCRIPTION ""
			::= { mbus1A 33 }

mbus1AVIF0E		OBJECT-TYPE
			SYNTAX	INTEGER
			ACCESS	read-only
			STATUS	current
	DESCRIPTION ""
			::= { mbus1A 34 }

mbus1AValue0E		OBJECT-TYPE
			SYNTAX	INTEGER
			ACCESS	read-only
			STATUS	current
	DESCRIPTION ""
			::= { mbus1A 35 }

mbus1AVIF0F		OBJECT-TYPE
			SYNTAX	INTEGER
			ACCESS	read-only
			STATUS	current
	DESCRIPTION ""
			::= { mbus1A 36 }

mbus1AValue0F		OBJECT-TYPE
			SYNTAX	INTEGER
			ACCESS	read-only
			STATUS	current
	DESCRIPTION ""
			::= { mbus1A 37 }

mbus1AVIF10		OBJECT-TYPE
			SYNTAX	INTEGER
			ACCESS	read-only
			STATUS	current
	DESCRIPTION ""
			::= { mbus1A 38 }

mbus1AValue10		OBJECT-TYPE
			SYNTAX	INTEGER
			ACCESS	read-only
			STATUS	current
	DESCRIPTION ""
			::= { mbus1A 39 }

mbus1AVIF11		OBJECT-TYPE
			SYNTAX	INTEGER
			ACCESS	read-only
			STATUS	current
	DESCRIPTION ""
			::= { mbus1A 40 }

mbus1AValue11		OBJECT-TYPE
			SYNTAX	INTEGER
			ACCESS	read-only
			STATUS	current
	DESCRIPTION ""
			::= { mbus1A 41 }

mbus1AVIF12		OBJECT-TYPE
			SYNTAX	INTEGER
			ACCESS	read-only
			STATUS	current
	DESCRIPTION ""
			::= { mbus1A 42 }

mbus1AValue12		OBJECT-TYPE
			SYNTAX	INTEGER
			ACCESS	read-only
			STATUS	current
	DESCRIPTION ""
			::= { mbus1A 43 }

mbus1AVIF13		OBJECT-TYPE
			SYNTAX	INTEGER
			ACCESS	read-only
			STATUS	current
	DESCRIPTION ""
			::= { mbus1A 44 }

mbus1AValue13		OBJECT-TYPE
			SYNTAX	INTEGER
			ACCESS	read-only
			STATUS	current
	DESCRIPTION ""
			::= { mbus1A 45 }

mbus1AVIF14		OBJECT-TYPE
			SYNTAX	INTEGER
			ACCESS	read-only
			STATUS	current
	DESCRIPTION ""
			::= { mbus1A 46 }

mbus1AValue14		OBJECT-TYPE
			SYNTAX	INTEGER
			ACCESS	read-only
			STATUS	current
	DESCRIPTION ""
			::= { mbus1A 47 }

mbus1AVIF15		OBJECT-TYPE
			SYNTAX	INTEGER
			ACCESS	read-only
			STATUS	current
	DESCRIPTION ""
			::= { mbus1A 48 }

mbus1AValue15		OBJECT-TYPE
			SYNTAX	INTEGER
			ACCESS	read-only
			STATUS	current
	DESCRIPTION ""
			::= { mbus1A 49 }

mbus1AVIF16		OBJECT-TYPE
			SYNTAX	INTEGER
			ACCESS	read-only
			STATUS	current
	DESCRIPTION ""
			::= { mbus1A 50 }

mbus1AValue16		OBJECT-TYPE
			SYNTAX	INTEGER
			ACCESS	read-only
			STATUS	current
	DESCRIPTION ""
			::= { mbus1A 51 }

mbus1AVIF17		OBJECT-TYPE
			SYNTAX	INTEGER
			ACCESS	read-only
			STATUS	current
	DESCRIPTION ""
			::= { mbus1A 52 }

mbus1AValue17		OBJECT-TYPE
			SYNTAX	INTEGER
			ACCESS	read-only
			STATUS	current
	DESCRIPTION ""
			::= { mbus1A 53 }

mbus1AVIF18		OBJECT-TYPE
			SYNTAX	INTEGER
			ACCESS	read-only
			STATUS	current
	DESCRIPTION ""
			::= { mbus1A 54 }

mbus1AValue18		OBJECT-TYPE
			SYNTAX	INTEGER
			ACCESS	read-only
			STATUS	current
	DESCRIPTION ""
			::= { mbus1A 55 }

mbus1AVIF19		OBJECT-TYPE
			SYNTAX	INTEGER
			ACCESS	read-only
			STATUS	current
	DESCRIPTION ""
			::= { mbus1A 56 }

mbus1AValue19		OBJECT-TYPE
			SYNTAX	INTEGER
			ACCESS	read-only
			STATUS	current
	DESCRIPTION ""
			::= { mbus1A 57 }

mbus1AVIF1A		OBJECT-TYPE
			SYNTAX	INTEGER
			ACCESS	read-only
			STATUS	current
	DESCRIPTION ""
			::= { mbus1A 58 }

mbus1AValue1A		OBJECT-TYPE
			SYNTAX	INTEGER
			ACCESS	read-only
			STATUS	current
	DESCRIPTION ""
			::= { mbus1A 59 }

mbus1AVIF1B		OBJECT-TYPE
			SYNTAX	INTEGER
			ACCESS	read-only
			STATUS	current
	DESCRIPTION ""
			::= { mbus1A 60 }

mbus1AValue1B		OBJECT-TYPE
			SYNTAX	INTEGER
			ACCESS	read-only
			STATUS	current
	DESCRIPTION ""
			::= { mbus1A 61 }

mbus1AVIF1C		OBJECT-TYPE
			SYNTAX	INTEGER
			ACCESS	read-only
			STATUS	current
	DESCRIPTION ""
			::= { mbus1A 62 }

mbus1AValue1C		OBJECT-TYPE
			SYNTAX	INTEGER
			ACCESS	read-only
			STATUS	current
	DESCRIPTION ""
			::= { mbus1A 63 }

mbus1AVIF1D		OBJECT-TYPE
			SYNTAX	INTEGER
			ACCESS	read-only
			STATUS	current
	DESCRIPTION ""
			::= { mbus1A 64 }

mbus1AValue1D		OBJECT-TYPE
			SYNTAX	INTEGER
			ACCESS	read-only
			STATUS	current
	DESCRIPTION ""
			::= { mbus1A 65 }

mbus1AVIF1E		OBJECT-TYPE
			SYNTAX	INTEGER
			ACCESS	read-only
			STATUS	current
	DESCRIPTION ""
			::= { mbus1A 66 }

mbus1AValue1E		OBJECT-TYPE
			SYNTAX	INTEGER
			ACCESS	read-only
			STATUS	current
	DESCRIPTION ""
			::= { mbus1A 67 }

mbus1AVIF1F		OBJECT-TYPE
			SYNTAX	INTEGER
			ACCESS	read-only
			STATUS	current
	DESCRIPTION ""
			::= { mbus1A 68 }

mbus1AValue1F		OBJECT-TYPE
			SYNTAX	INTEGER
			ACCESS	read-only
			STATUS	current
	DESCRIPTION ""
			::= { mbus1A 69 }

mbus1AVIF20		OBJECT-TYPE
			SYNTAX	INTEGER
			ACCESS	read-only
			STATUS	current
	DESCRIPTION ""
			::= { mbus1A 70 }

mbus1AValue20		OBJECT-TYPE
			SYNTAX	INTEGER
			ACCESS	read-only
			STATUS	current
	DESCRIPTION ""
			::= { mbus1A 71 }

mbus1AVIF21		OBJECT-TYPE
			SYNTAX	INTEGER
			ACCESS	read-only
			STATUS	current
	DESCRIPTION ""
			::= { mbus1A 72 }

mbus1AValue21		OBJECT-TYPE
			SYNTAX	INTEGER
			ACCESS	read-only
			STATUS	current
	DESCRIPTION ""
			::= { mbus1A 73 }

mbus1AVIF22		OBJECT-TYPE
			SYNTAX	INTEGER
			ACCESS	read-only
			STATUS	current
	DESCRIPTION ""
			::= { mbus1A 74 }

mbus1AValue22		OBJECT-TYPE
			SYNTAX	INTEGER
			ACCESS	read-only
			STATUS	current
	DESCRIPTION ""
			::= { mbus1A 75 }

mbus1AVIF23		OBJECT-TYPE
			SYNTAX	INTEGER
			ACCESS	read-only
			STATUS	current
	DESCRIPTION ""
			::= { mbus1A 76 }

mbus1AValue23		OBJECT-TYPE
			SYNTAX	INTEGER
			ACCESS	read-only
			STATUS	current
	DESCRIPTION ""
			::= { mbus1A 77 }

mbus1AVIF24		OBJECT-TYPE
			SYNTAX	INTEGER
			ACCESS	read-only
			STATUS	current
	DESCRIPTION ""
			::= { mbus1A 78 }

mbus1AValue24		OBJECT-TYPE
			SYNTAX	INTEGER
			ACCESS	read-only
			STATUS	current
	DESCRIPTION ""
			::= { mbus1A 79 }

mbus1AVIF25		OBJECT-TYPE
			SYNTAX	INTEGER
			ACCESS	read-only
			STATUS	current
	DESCRIPTION ""
			::= { mbus1A 80 }

mbus1AValue25		OBJECT-TYPE
			SYNTAX	INTEGER
			ACCESS	read-only
			STATUS	current
	DESCRIPTION ""
			::= { mbus1A 81 }

mbus1AVIF26		OBJECT-TYPE
			SYNTAX	INTEGER
			ACCESS	read-only
			STATUS	current
	DESCRIPTION ""
			::= { mbus1A 82 }

mbus1AValue26		OBJECT-TYPE
			SYNTAX	INTEGER
			ACCESS	read-only
			STATUS	current
	DESCRIPTION ""
			::= { mbus1A 83 }

mbus1AVIF27		OBJECT-TYPE
			SYNTAX	INTEGER
			ACCESS	read-only
			STATUS	current
	DESCRIPTION ""
			::= { mbus1A 84 }

mbus1AValue27		OBJECT-TYPE
			SYNTAX	INTEGER
			ACCESS	read-only
			STATUS	current
	DESCRIPTION ""
			::= { mbus1A 85 }

mbus1AVIF28		OBJECT-TYPE
			SYNTAX	INTEGER
			ACCESS	read-only
			STATUS	current
	DESCRIPTION ""
			::= { mbus1A 86 }

mbus1AValue28		OBJECT-TYPE
			SYNTAX	INTEGER
			ACCESS	read-only
			STATUS	current
	DESCRIPTION ""
			::= { mbus1A 87 }

mbus1AVIF29		OBJECT-TYPE
			SYNTAX	INTEGER
			ACCESS	read-only
			STATUS	current
	DESCRIPTION ""
			::= { mbus1A 88 }

mbus1AValue29		OBJECT-TYPE
			SYNTAX	INTEGER
			ACCESS	read-only
			STATUS	current
	DESCRIPTION ""
			::= { mbus1A 89 }

mbus1AVIF2A		OBJECT-TYPE
			SYNTAX	INTEGER
			ACCESS	read-only
			STATUS	current
	DESCRIPTION ""
			::= { mbus1A 90 }

mbus1AValue2A		OBJECT-TYPE
			SYNTAX	INTEGER
			ACCESS	read-only
			STATUS	current
	DESCRIPTION ""
			::= { mbus1A 91 }

mbus1AVIF2B		OBJECT-TYPE
			SYNTAX	INTEGER
			ACCESS	read-only
			STATUS	current
	DESCRIPTION ""
			::= { mbus1A 92 }

mbus1AValue2B		OBJECT-TYPE
			SYNTAX	INTEGER
			ACCESS	read-only
			STATUS	current
	DESCRIPTION ""
			::= { mbus1A 93 }

mbus1AVIF2C		OBJECT-TYPE
			SYNTAX	INTEGER
			ACCESS	read-only
			STATUS	current
	DESCRIPTION ""
			::= { mbus1A 94 }

mbus1AValue2C		OBJECT-TYPE
			SYNTAX	INTEGER
			ACCESS	read-only
			STATUS	current
	DESCRIPTION ""
			::= { mbus1A 95 }

mbus1AVIF2D		OBJECT-TYPE
			SYNTAX	INTEGER
			ACCESS	read-only
			STATUS	current
	DESCRIPTION ""
			::= { mbus1A 96 }

mbus1AValue2D		OBJECT-TYPE
			SYNTAX	INTEGER
			ACCESS	read-only
			STATUS	current
	DESCRIPTION ""
			::= { mbus1A 97 }

mbus1AVIF2E		OBJECT-TYPE
			SYNTAX	INTEGER
			ACCESS	read-only
			STATUS	current
	DESCRIPTION ""
			::= { mbus1A 98 }

mbus1AValue2E		OBJECT-TYPE
			SYNTAX	INTEGER
			ACCESS	read-only
			STATUS	current
	DESCRIPTION ""
			::= { mbus1A 99 }

mbus1AVIF2F		OBJECT-TYPE
			SYNTAX	INTEGER
			ACCESS	read-only
			STATUS	current
	DESCRIPTION ""
			::= { mbus1A 100 }

mbus1AValue2F		OBJECT-TYPE
			SYNTAX	INTEGER
			ACCESS	read-only
			STATUS	current
	DESCRIPTION ""
			::= { mbus1A 101 }

mbus1B			OBJECT IDENTIFIER ::= { mbus 27 }

mbus1BIdNumber		OBJECT-TYPE
			SYNTAX	Gauge
			ACCESS	read-only
			STATUS	current
	DESCRIPTION ""
			::= { mbus1B 1 }

mbus1BManufacturer	OBJECT-TYPE
			SYNTAX	Gauge
			ACCESS	read-only
			STATUS	current
	DESCRIPTION ""
			::= { mbus1B 2 }

mbus1BVersion		OBJECT-TYPE
			SYNTAX	Gauge
			ACCESS	read-only
			STATUS	current
	DESCRIPTION ""
			::= { mbus1B 3 }

mbus1BMedium		OBJECT-TYPE
			SYNTAX	Gauge
			ACCESS	read-only
			STATUS	current
	DESCRIPTION ""
			::= { mbus1B 4 }

mbus1BStatus		OBJECT-TYPE
			SYNTAX	Gauge
			ACCESS	read-only
			STATUS	current
	DESCRIPTION ""
			::= { mbus1B 5 }

mbus1BVIF00		OBJECT-TYPE
			SYNTAX	INTEGER
			ACCESS	read-only
			STATUS	current
	DESCRIPTION ""
			::= { mbus1B 6 }

mbus1BValue00		OBJECT-TYPE
			SYNTAX	INTEGER
			ACCESS	read-only
			STATUS	current
	DESCRIPTION ""
			::= { mbus1B 7 }

mbus1BVIF01		OBJECT-TYPE
			SYNTAX	INTEGER
			ACCESS	read-only
			STATUS	current
	DESCRIPTION ""
			::= { mbus1B 8 }

mbus1BValue01		OBJECT-TYPE
			SYNTAX	INTEGER
			ACCESS	read-only
			STATUS	current
	DESCRIPTION ""
			::= { mbus1B 9 }

mbus1BVIF02		OBJECT-TYPE
			SYNTAX	INTEGER
			ACCESS	read-only
			STATUS	current
	DESCRIPTION ""
			::= { mbus1B 10 }

mbus1BValue02		OBJECT-TYPE
			SYNTAX	INTEGER
			ACCESS	read-only
			STATUS	current
	DESCRIPTION ""
			::= { mbus1B 11 }

mbus1BVIF03		OBJECT-TYPE
			SYNTAX	INTEGER
			ACCESS	read-only
			STATUS	current
	DESCRIPTION ""
			::= { mbus1B 12 }

mbus1BValue03		OBJECT-TYPE
			SYNTAX	INTEGER
			ACCESS	read-only
			STATUS	current
	DESCRIPTION ""
			::= { mbus1B 13 }

mbus1BVIF04		OBJECT-TYPE
			SYNTAX	INTEGER
			ACCESS	read-only
			STATUS	current
	DESCRIPTION ""
			::= { mbus1B 14 }

mbus1BValue04		OBJECT-TYPE
			SYNTAX	INTEGER
			ACCESS	read-only
			STATUS	current
	DESCRIPTION ""
			::= { mbus1B 15 }

mbus1BVIF05		OBJECT-TYPE
			SYNTAX	INTEGER
			ACCESS	read-only
			STATUS	current
	DESCRIPTION ""
			::= { mbus1B 16 }

mbus1BValue05		OBJECT-TYPE
			SYNTAX	INTEGER
			ACCESS	read-only
			STATUS	current
	DESCRIPTION ""
			::= { mbus1B 17 }

mbus1BVIF06		OBJECT-TYPE
			SYNTAX	INTEGER
			ACCESS	read-only
			STATUS	current
	DESCRIPTION ""
			::= { mbus1B 18 }

mbus1BValue06		OBJECT-TYPE
			SYNTAX	INTEGER
			ACCESS	read-only
			STATUS	current
	DESCRIPTION ""
			::= { mbus1B 19 }

mbus1BVIF07		OBJECT-TYPE
			SYNTAX	INTEGER
			ACCESS	read-only
			STATUS	current
	DESCRIPTION ""
			::= { mbus1B 20 }

mbus1BValue07		OBJECT-TYPE
			SYNTAX	INTEGER
			ACCESS	read-only
			STATUS	current
	DESCRIPTION ""
			::= { mbus1B 21 }

mbus1BVIF08		OBJECT-TYPE
			SYNTAX	INTEGER
			ACCESS	read-only
			STATUS	current
	DESCRIPTION ""
			::= { mbus1B 22 }

mbus1BValue08		OBJECT-TYPE
			SYNTAX	INTEGER
			ACCESS	read-only
			STATUS	current
	DESCRIPTION ""
			::= { mbus1B 23 }

mbus1BVIF09		OBJECT-TYPE
			SYNTAX	INTEGER
			ACCESS	read-only
			STATUS	current
	DESCRIPTION ""
			::= { mbus1B 24 }

mbus1BValue09		OBJECT-TYPE
			SYNTAX	INTEGER
			ACCESS	read-only
			STATUS	current
	DESCRIPTION ""
			::= { mbus1B 25 }

mbus1BVIF0A		OBJECT-TYPE
			SYNTAX	INTEGER
			ACCESS	read-only
			STATUS	current
	DESCRIPTION ""
			::= { mbus1B 26 }

mbus1BValue0A		OBJECT-TYPE
			SYNTAX	INTEGER
			ACCESS	read-only
			STATUS	current
	DESCRIPTION ""
			::= { mbus1B 27 }

mbus1BVIF0B		OBJECT-TYPE
			SYNTAX	INTEGER
			ACCESS	read-only
			STATUS	current
	DESCRIPTION ""
			::= { mbus1B 28 }

mbus1BValue0B		OBJECT-TYPE
			SYNTAX	INTEGER
			ACCESS	read-only
			STATUS	current
	DESCRIPTION ""
			::= { mbus1B 29 }

mbus1BVIF0C		OBJECT-TYPE
			SYNTAX	INTEGER
			ACCESS	read-only
			STATUS	current
	DESCRIPTION ""
			::= { mbus1B 30 }

mbus1BValue0C		OBJECT-TYPE
			SYNTAX	INTEGER
			ACCESS	read-only
			STATUS	current
	DESCRIPTION ""
			::= { mbus1B 31 }

mbus1BVIF0D		OBJECT-TYPE
			SYNTAX	INTEGER
			ACCESS	read-only
			STATUS	current
	DESCRIPTION ""
			::= { mbus1B 32 }

mbus1BValue0D		OBJECT-TYPE
			SYNTAX	INTEGER
			ACCESS	read-only
			STATUS	current
	DESCRIPTION ""
			::= { mbus1B 33 }

mbus1BVIF0E		OBJECT-TYPE
			SYNTAX	INTEGER
			ACCESS	read-only
			STATUS	current
	DESCRIPTION ""
			::= { mbus1B 34 }

mbus1BValue0E		OBJECT-TYPE
			SYNTAX	INTEGER
			ACCESS	read-only
			STATUS	current
	DESCRIPTION ""
			::= { mbus1B 35 }

mbus1BVIF0F		OBJECT-TYPE
			SYNTAX	INTEGER
			ACCESS	read-only
			STATUS	current
	DESCRIPTION ""
			::= { mbus1B 36 }

mbus1BValue0F		OBJECT-TYPE
			SYNTAX	INTEGER
			ACCESS	read-only
			STATUS	current
	DESCRIPTION ""
			::= { mbus1B 37 }

mbus1BVIF10		OBJECT-TYPE
			SYNTAX	INTEGER
			ACCESS	read-only
			STATUS	current
	DESCRIPTION ""
			::= { mbus1B 38 }

mbus1BValue10		OBJECT-TYPE
			SYNTAX	INTEGER
			ACCESS	read-only
			STATUS	current
	DESCRIPTION ""
			::= { mbus1B 39 }

mbus1BVIF11		OBJECT-TYPE
			SYNTAX	INTEGER
			ACCESS	read-only
			STATUS	current
	DESCRIPTION ""
			::= { mbus1B 40 }

mbus1BValue11		OBJECT-TYPE
			SYNTAX	INTEGER
			ACCESS	read-only
			STATUS	current
	DESCRIPTION ""
			::= { mbus1B 41 }

mbus1BVIF12		OBJECT-TYPE
			SYNTAX	INTEGER
			ACCESS	read-only
			STATUS	current
	DESCRIPTION ""
			::= { mbus1B 42 }

mbus1BValue12		OBJECT-TYPE
			SYNTAX	INTEGER
			ACCESS	read-only
			STATUS	current
	DESCRIPTION ""
			::= { mbus1B 43 }

mbus1BVIF13		OBJECT-TYPE
			SYNTAX	INTEGER
			ACCESS	read-only
			STATUS	current
	DESCRIPTION ""
			::= { mbus1B 44 }

mbus1BValue13		OBJECT-TYPE
			SYNTAX	INTEGER
			ACCESS	read-only
			STATUS	current
	DESCRIPTION ""
			::= { mbus1B 45 }

mbus1BVIF14		OBJECT-TYPE
			SYNTAX	INTEGER
			ACCESS	read-only
			STATUS	current
	DESCRIPTION ""
			::= { mbus1B 46 }

mbus1BValue14		OBJECT-TYPE
			SYNTAX	INTEGER
			ACCESS	read-only
			STATUS	current
	DESCRIPTION ""
			::= { mbus1B 47 }

mbus1BVIF15		OBJECT-TYPE
			SYNTAX	INTEGER
			ACCESS	read-only
			STATUS	current
	DESCRIPTION ""
			::= { mbus1B 48 }

mbus1BValue15		OBJECT-TYPE
			SYNTAX	INTEGER
			ACCESS	read-only
			STATUS	current
	DESCRIPTION ""
			::= { mbus1B 49 }

mbus1BVIF16		OBJECT-TYPE
			SYNTAX	INTEGER
			ACCESS	read-only
			STATUS	current
	DESCRIPTION ""
			::= { mbus1B 50 }

mbus1BValue16		OBJECT-TYPE
			SYNTAX	INTEGER
			ACCESS	read-only
			STATUS	current
	DESCRIPTION ""
			::= { mbus1B 51 }

mbus1BVIF17		OBJECT-TYPE
			SYNTAX	INTEGER
			ACCESS	read-only
			STATUS	current
	DESCRIPTION ""
			::= { mbus1B 52 }

mbus1BValue17		OBJECT-TYPE
			SYNTAX	INTEGER
			ACCESS	read-only
			STATUS	current
	DESCRIPTION ""
			::= { mbus1B 53 }

mbus1BVIF18		OBJECT-TYPE
			SYNTAX	INTEGER
			ACCESS	read-only
			STATUS	current
	DESCRIPTION ""
			::= { mbus1B 54 }

mbus1BValue18		OBJECT-TYPE
			SYNTAX	INTEGER
			ACCESS	read-only
			STATUS	current
	DESCRIPTION ""
			::= { mbus1B 55 }

mbus1BVIF19		OBJECT-TYPE
			SYNTAX	INTEGER
			ACCESS	read-only
			STATUS	current
	DESCRIPTION ""
			::= { mbus1B 56 }

mbus1BValue19		OBJECT-TYPE
			SYNTAX	INTEGER
			ACCESS	read-only
			STATUS	current
	DESCRIPTION ""
			::= { mbus1B 57 }

mbus1BVIF1A		OBJECT-TYPE
			SYNTAX	INTEGER
			ACCESS	read-only
			STATUS	current
	DESCRIPTION ""
			::= { mbus1B 58 }

mbus1BValue1A		OBJECT-TYPE
			SYNTAX	INTEGER
			ACCESS	read-only
			STATUS	current
	DESCRIPTION ""
			::= { mbus1B 59 }

mbus1BVIF1B		OBJECT-TYPE
			SYNTAX	INTEGER
			ACCESS	read-only
			STATUS	current
	DESCRIPTION ""
			::= { mbus1B 60 }

mbus1BValue1B		OBJECT-TYPE
			SYNTAX	INTEGER
			ACCESS	read-only
			STATUS	current
	DESCRIPTION ""
			::= { mbus1B 61 }

mbus1BVIF1C		OBJECT-TYPE
			SYNTAX	INTEGER
			ACCESS	read-only
			STATUS	current
	DESCRIPTION ""
			::= { mbus1B 62 }

mbus1BValue1C		OBJECT-TYPE
			SYNTAX	INTEGER
			ACCESS	read-only
			STATUS	current
	DESCRIPTION ""
			::= { mbus1B 63 }

mbus1BVIF1D		OBJECT-TYPE
			SYNTAX	INTEGER
			ACCESS	read-only
			STATUS	current
	DESCRIPTION ""
			::= { mbus1B 64 }

mbus1BValue1D		OBJECT-TYPE
			SYNTAX	INTEGER
			ACCESS	read-only
			STATUS	current
	DESCRIPTION ""
			::= { mbus1B 65 }

mbus1BVIF1E		OBJECT-TYPE
			SYNTAX	INTEGER
			ACCESS	read-only
			STATUS	current
	DESCRIPTION ""
			::= { mbus1B 66 }

mbus1BValue1E		OBJECT-TYPE
			SYNTAX	INTEGER
			ACCESS	read-only
			STATUS	current
	DESCRIPTION ""
			::= { mbus1B 67 }

mbus1BVIF1F		OBJECT-TYPE
			SYNTAX	INTEGER
			ACCESS	read-only
			STATUS	current
	DESCRIPTION ""
			::= { mbus1B 68 }

mbus1BValue1F		OBJECT-TYPE
			SYNTAX	INTEGER
			ACCESS	read-only
			STATUS	current
	DESCRIPTION ""
			::= { mbus1B 69 }

mbus1BVIF20		OBJECT-TYPE
			SYNTAX	INTEGER
			ACCESS	read-only
			STATUS	current
	DESCRIPTION ""
			::= { mbus1B 70 }

mbus1BValue20		OBJECT-TYPE
			SYNTAX	INTEGER
			ACCESS	read-only
			STATUS	current
	DESCRIPTION ""
			::= { mbus1B 71 }

mbus1BVIF21		OBJECT-TYPE
			SYNTAX	INTEGER
			ACCESS	read-only
			STATUS	current
	DESCRIPTION ""
			::= { mbus1B 72 }

mbus1BValue21		OBJECT-TYPE
			SYNTAX	INTEGER
			ACCESS	read-only
			STATUS	current
	DESCRIPTION ""
			::= { mbus1B 73 }

mbus1BVIF22		OBJECT-TYPE
			SYNTAX	INTEGER
			ACCESS	read-only
			STATUS	current
	DESCRIPTION ""
			::= { mbus1B 74 }

mbus1BValue22		OBJECT-TYPE
			SYNTAX	INTEGER
			ACCESS	read-only
			STATUS	current
	DESCRIPTION ""
			::= { mbus1B 75 }

mbus1BVIF23		OBJECT-TYPE
			SYNTAX	INTEGER
			ACCESS	read-only
			STATUS	current
	DESCRIPTION ""
			::= { mbus1B 76 }

mbus1BValue23		OBJECT-TYPE
			SYNTAX	INTEGER
			ACCESS	read-only
			STATUS	current
	DESCRIPTION ""
			::= { mbus1B 77 }

mbus1BVIF24		OBJECT-TYPE
			SYNTAX	INTEGER
			ACCESS	read-only
			STATUS	current
	DESCRIPTION ""
			::= { mbus1B 78 }

mbus1BValue24		OBJECT-TYPE
			SYNTAX	INTEGER
			ACCESS	read-only
			STATUS	current
	DESCRIPTION ""
			::= { mbus1B 79 }

mbus1BVIF25		OBJECT-TYPE
			SYNTAX	INTEGER
			ACCESS	read-only
			STATUS	current
	DESCRIPTION ""
			::= { mbus1B 80 }

mbus1BValue25		OBJECT-TYPE
			SYNTAX	INTEGER
			ACCESS	read-only
			STATUS	current
	DESCRIPTION ""
			::= { mbus1B 81 }

mbus1BVIF26		OBJECT-TYPE
			SYNTAX	INTEGER
			ACCESS	read-only
			STATUS	current
	DESCRIPTION ""
			::= { mbus1B 82 }

mbus1BValue26		OBJECT-TYPE
			SYNTAX	INTEGER
			ACCESS	read-only
			STATUS	current
	DESCRIPTION ""
			::= { mbus1B 83 }

mbus1BVIF27		OBJECT-TYPE
			SYNTAX	INTEGER
			ACCESS	read-only
			STATUS	current
	DESCRIPTION ""
			::= { mbus1B 84 }

mbus1BValue27		OBJECT-TYPE
			SYNTAX	INTEGER
			ACCESS	read-only
			STATUS	current
	DESCRIPTION ""
			::= { mbus1B 85 }

mbus1BVIF28		OBJECT-TYPE
			SYNTAX	INTEGER
			ACCESS	read-only
			STATUS	current
	DESCRIPTION ""
			::= { mbus1B 86 }

mbus1BValue28		OBJECT-TYPE
			SYNTAX	INTEGER
			ACCESS	read-only
			STATUS	current
	DESCRIPTION ""
			::= { mbus1B 87 }

mbus1BVIF29		OBJECT-TYPE
			SYNTAX	INTEGER
			ACCESS	read-only
			STATUS	current
	DESCRIPTION ""
			::= { mbus1B 88 }

mbus1BValue29		OBJECT-TYPE
			SYNTAX	INTEGER
			ACCESS	read-only
			STATUS	current
	DESCRIPTION ""
			::= { mbus1B 89 }

mbus1BVIF2A		OBJECT-TYPE
			SYNTAX	INTEGER
			ACCESS	read-only
			STATUS	current
	DESCRIPTION ""
			::= { mbus1B 90 }

mbus1BValue2A		OBJECT-TYPE
			SYNTAX	INTEGER
			ACCESS	read-only
			STATUS	current
	DESCRIPTION ""
			::= { mbus1B 91 }

mbus1BVIF2B		OBJECT-TYPE
			SYNTAX	INTEGER
			ACCESS	read-only
			STATUS	current
	DESCRIPTION ""
			::= { mbus1B 92 }

mbus1BValue2B		OBJECT-TYPE
			SYNTAX	INTEGER
			ACCESS	read-only
			STATUS	current
	DESCRIPTION ""
			::= { mbus1B 93 }

mbus1BVIF2C		OBJECT-TYPE
			SYNTAX	INTEGER
			ACCESS	read-only
			STATUS	current
	DESCRIPTION ""
			::= { mbus1B 94 }

mbus1BValue2C		OBJECT-TYPE
			SYNTAX	INTEGER
			ACCESS	read-only
			STATUS	current
	DESCRIPTION ""
			::= { mbus1B 95 }

mbus1BVIF2D		OBJECT-TYPE
			SYNTAX	INTEGER
			ACCESS	read-only
			STATUS	current
	DESCRIPTION ""
			::= { mbus1B 96 }

mbus1BValue2D		OBJECT-TYPE
			SYNTAX	INTEGER
			ACCESS	read-only
			STATUS	current
	DESCRIPTION ""
			::= { mbus1B 97 }

mbus1BVIF2E		OBJECT-TYPE
			SYNTAX	INTEGER
			ACCESS	read-only
			STATUS	current
	DESCRIPTION ""
			::= { mbus1B 98 }

mbus1BValue2E		OBJECT-TYPE
			SYNTAX	INTEGER
			ACCESS	read-only
			STATUS	current
	DESCRIPTION ""
			::= { mbus1B 99 }

mbus1BVIF2F		OBJECT-TYPE
			SYNTAX	INTEGER
			ACCESS	read-only
			STATUS	current
	DESCRIPTION ""
			::= { mbus1B 100 }

mbus1BValue2F		OBJECT-TYPE
			SYNTAX	INTEGER
			ACCESS	read-only
			STATUS	current
	DESCRIPTION ""
			::= { mbus1B 101 }

mbus1C			OBJECT IDENTIFIER ::= { mbus 28 }

mbus1CIdNumber		OBJECT-TYPE
			SYNTAX	Gauge
			ACCESS	read-only
			STATUS	current
	DESCRIPTION ""
			::= { mbus1C 1 }

mbus1CManufacturer	OBJECT-TYPE
			SYNTAX	Gauge
			ACCESS	read-only
			STATUS	current
	DESCRIPTION ""
			::= { mbus1C 2 }

mbus1CVersion		OBJECT-TYPE
			SYNTAX	Gauge
			ACCESS	read-only
			STATUS	current
	DESCRIPTION ""
			::= { mbus1C 3 }

mbus1CMedium		OBJECT-TYPE
			SYNTAX	Gauge
			ACCESS	read-only
			STATUS	current
	DESCRIPTION ""
			::= { mbus1C 4 }

mbus1CStatus		OBJECT-TYPE
			SYNTAX	Gauge
			ACCESS	read-only
			STATUS	current
	DESCRIPTION ""
			::= { mbus1C 5 }

mbus1CVIF00		OBJECT-TYPE
			SYNTAX	INTEGER
			ACCESS	read-only
			STATUS	current
	DESCRIPTION ""
			::= { mbus1C 6 }

mbus1CValue00		OBJECT-TYPE
			SYNTAX	INTEGER
			ACCESS	read-only
			STATUS	current
	DESCRIPTION ""
			::= { mbus1C 7 }

mbus1CVIF01		OBJECT-TYPE
			SYNTAX	INTEGER
			ACCESS	read-only
			STATUS	current
	DESCRIPTION ""
			::= { mbus1C 8 }

mbus1CValue01		OBJECT-TYPE
			SYNTAX	INTEGER
			ACCESS	read-only
			STATUS	current
	DESCRIPTION ""
			::= { mbus1C 9 }

mbus1CVIF02		OBJECT-TYPE
			SYNTAX	INTEGER
			ACCESS	read-only
			STATUS	current
	DESCRIPTION ""
			::= { mbus1C 10 }

mbus1CValue02		OBJECT-TYPE
			SYNTAX	INTEGER
			ACCESS	read-only
			STATUS	current
	DESCRIPTION ""
			::= { mbus1C 11 }

mbus1CVIF03		OBJECT-TYPE
			SYNTAX	INTEGER
			ACCESS	read-only
			STATUS	current
	DESCRIPTION ""
			::= { mbus1C 12 }

mbus1CValue03		OBJECT-TYPE
			SYNTAX	INTEGER
			ACCESS	read-only
			STATUS	current
	DESCRIPTION ""
			::= { mbus1C 13 }

mbus1CVIF04		OBJECT-TYPE
			SYNTAX	INTEGER
			ACCESS	read-only
			STATUS	current
	DESCRIPTION ""
			::= { mbus1C 14 }

mbus1CValue04		OBJECT-TYPE
			SYNTAX	INTEGER
			ACCESS	read-only
			STATUS	current
	DESCRIPTION ""
			::= { mbus1C 15 }

mbus1CVIF05		OBJECT-TYPE
			SYNTAX	INTEGER
			ACCESS	read-only
			STATUS	current
	DESCRIPTION ""
			::= { mbus1C 16 }

mbus1CValue05		OBJECT-TYPE
			SYNTAX	INTEGER
			ACCESS	read-only
			STATUS	current
	DESCRIPTION ""
			::= { mbus1C 17 }

mbus1CVIF06		OBJECT-TYPE
			SYNTAX	INTEGER
			ACCESS	read-only
			STATUS	current
	DESCRIPTION ""
			::= { mbus1C 18 }

mbus1CValue06		OBJECT-TYPE
			SYNTAX	INTEGER
			ACCESS	read-only
			STATUS	current
	DESCRIPTION ""
			::= { mbus1C 19 }

mbus1CVIF07		OBJECT-TYPE
			SYNTAX	INTEGER
			ACCESS	read-only
			STATUS	current
	DESCRIPTION ""
			::= { mbus1C 20 }

mbus1CValue07		OBJECT-TYPE
			SYNTAX	INTEGER
			ACCESS	read-only
			STATUS	current
	DESCRIPTION ""
			::= { mbus1C 21 }

mbus1CVIF08		OBJECT-TYPE
			SYNTAX	INTEGER
			ACCESS	read-only
			STATUS	current
	DESCRIPTION ""
			::= { mbus1C 22 }

mbus1CValue08		OBJECT-TYPE
			SYNTAX	INTEGER
			ACCESS	read-only
			STATUS	current
	DESCRIPTION ""
			::= { mbus1C 23 }

mbus1CVIF09		OBJECT-TYPE
			SYNTAX	INTEGER
			ACCESS	read-only
			STATUS	current
	DESCRIPTION ""
			::= { mbus1C 24 }

mbus1CValue09		OBJECT-TYPE
			SYNTAX	INTEGER
			ACCESS	read-only
			STATUS	current
	DESCRIPTION ""
			::= { mbus1C 25 }

mbus1CVIF0A		OBJECT-TYPE
			SYNTAX	INTEGER
			ACCESS	read-only
			STATUS	current
	DESCRIPTION ""
			::= { mbus1C 26 }

mbus1CValue0A		OBJECT-TYPE
			SYNTAX	INTEGER
			ACCESS	read-only
			STATUS	current
	DESCRIPTION ""
			::= { mbus1C 27 }

mbus1CVIF0B		OBJECT-TYPE
			SYNTAX	INTEGER
			ACCESS	read-only
			STATUS	current
	DESCRIPTION ""
			::= { mbus1C 28 }

mbus1CValue0B		OBJECT-TYPE
			SYNTAX	INTEGER
			ACCESS	read-only
			STATUS	current
	DESCRIPTION ""
			::= { mbus1C 29 }

mbus1CVIF0C		OBJECT-TYPE
			SYNTAX	INTEGER
			ACCESS	read-only
			STATUS	current
	DESCRIPTION ""
			::= { mbus1C 30 }

mbus1CValue0C		OBJECT-TYPE
			SYNTAX	INTEGER
			ACCESS	read-only
			STATUS	current
	DESCRIPTION ""
			::= { mbus1C 31 }

mbus1CVIF0D		OBJECT-TYPE
			SYNTAX	INTEGER
			ACCESS	read-only
			STATUS	current
	DESCRIPTION ""
			::= { mbus1C 32 }

mbus1CValue0D		OBJECT-TYPE
			SYNTAX	INTEGER
			ACCESS	read-only
			STATUS	current
	DESCRIPTION ""
			::= { mbus1C 33 }

mbus1CVIF0E		OBJECT-TYPE
			SYNTAX	INTEGER
			ACCESS	read-only
			STATUS	current
	DESCRIPTION ""
			::= { mbus1C 34 }

mbus1CValue0E		OBJECT-TYPE
			SYNTAX	INTEGER
			ACCESS	read-only
			STATUS	current
	DESCRIPTION ""
			::= { mbus1C 35 }

mbus1CVIF0F		OBJECT-TYPE
			SYNTAX	INTEGER
			ACCESS	read-only
			STATUS	current
	DESCRIPTION ""
			::= { mbus1C 36 }

mbus1CValue0F		OBJECT-TYPE
			SYNTAX	INTEGER
			ACCESS	read-only
			STATUS	current
	DESCRIPTION ""
			::= { mbus1C 37 }

mbus1CVIF10		OBJECT-TYPE
			SYNTAX	INTEGER
			ACCESS	read-only
			STATUS	current
	DESCRIPTION ""
			::= { mbus1C 38 }

mbus1CValue10		OBJECT-TYPE
			SYNTAX	INTEGER
			ACCESS	read-only
			STATUS	current
	DESCRIPTION ""
			::= { mbus1C 39 }

mbus1CVIF11		OBJECT-TYPE
			SYNTAX	INTEGER
			ACCESS	read-only
			STATUS	current
	DESCRIPTION ""
			::= { mbus1C 40 }

mbus1CValue11		OBJECT-TYPE
			SYNTAX	INTEGER
			ACCESS	read-only
			STATUS	current
	DESCRIPTION ""
			::= { mbus1C 41 }

mbus1CVIF12		OBJECT-TYPE
			SYNTAX	INTEGER
			ACCESS	read-only
			STATUS	current
	DESCRIPTION ""
			::= { mbus1C 42 }

mbus1CValue12		OBJECT-TYPE
			SYNTAX	INTEGER
			ACCESS	read-only
			STATUS	current
	DESCRIPTION ""
			::= { mbus1C 43 }

mbus1CVIF13		OBJECT-TYPE
			SYNTAX	INTEGER
			ACCESS	read-only
			STATUS	current
	DESCRIPTION ""
			::= { mbus1C 44 }

mbus1CValue13		OBJECT-TYPE
			SYNTAX	INTEGER
			ACCESS	read-only
			STATUS	current
	DESCRIPTION ""
			::= { mbus1C 45 }

mbus1CVIF14		OBJECT-TYPE
			SYNTAX	INTEGER
			ACCESS	read-only
			STATUS	current
	DESCRIPTION ""
			::= { mbus1C 46 }

mbus1CValue14		OBJECT-TYPE
			SYNTAX	INTEGER
			ACCESS	read-only
			STATUS	current
	DESCRIPTION ""
			::= { mbus1C 47 }

mbus1CVIF15		OBJECT-TYPE
			SYNTAX	INTEGER
			ACCESS	read-only
			STATUS	current
	DESCRIPTION ""
			::= { mbus1C 48 }

mbus1CValue15		OBJECT-TYPE
			SYNTAX	INTEGER
			ACCESS	read-only
			STATUS	current
	DESCRIPTION ""
			::= { mbus1C 49 }

mbus1CVIF16		OBJECT-TYPE
			SYNTAX	INTEGER
			ACCESS	read-only
			STATUS	current
	DESCRIPTION ""
			::= { mbus1C 50 }

mbus1CValue16		OBJECT-TYPE
			SYNTAX	INTEGER
			ACCESS	read-only
			STATUS	current
	DESCRIPTION ""
			::= { mbus1C 51 }

mbus1CVIF17		OBJECT-TYPE
			SYNTAX	INTEGER
			ACCESS	read-only
			STATUS	current
	DESCRIPTION ""
			::= { mbus1C 52 }

mbus1CValue17		OBJECT-TYPE
			SYNTAX	INTEGER
			ACCESS	read-only
			STATUS	current
	DESCRIPTION ""
			::= { mbus1C 53 }

mbus1CVIF18		OBJECT-TYPE
			SYNTAX	INTEGER
			ACCESS	read-only
			STATUS	current
	DESCRIPTION ""
			::= { mbus1C 54 }

mbus1CValue18		OBJECT-TYPE
			SYNTAX	INTEGER
			ACCESS	read-only
			STATUS	current
	DESCRIPTION ""
			::= { mbus1C 55 }

mbus1CVIF19		OBJECT-TYPE
			SYNTAX	INTEGER
			ACCESS	read-only
			STATUS	current
	DESCRIPTION ""
			::= { mbus1C 56 }

mbus1CValue19		OBJECT-TYPE
			SYNTAX	INTEGER
			ACCESS	read-only
			STATUS	current
	DESCRIPTION ""
			::= { mbus1C 57 }

mbus1CVIF1A		OBJECT-TYPE
			SYNTAX	INTEGER
			ACCESS	read-only
			STATUS	current
	DESCRIPTION ""
			::= { mbus1C 58 }

mbus1CValue1A		OBJECT-TYPE
			SYNTAX	INTEGER
			ACCESS	read-only
			STATUS	current
	DESCRIPTION ""
			::= { mbus1C 59 }

mbus1CVIF1B		OBJECT-TYPE
			SYNTAX	INTEGER
			ACCESS	read-only
			STATUS	current
	DESCRIPTION ""
			::= { mbus1C 60 }

mbus1CValue1B		OBJECT-TYPE
			SYNTAX	INTEGER
			ACCESS	read-only
			STATUS	current
	DESCRIPTION ""
			::= { mbus1C 61 }

mbus1CVIF1C		OBJECT-TYPE
			SYNTAX	INTEGER
			ACCESS	read-only
			STATUS	current
	DESCRIPTION ""
			::= { mbus1C 62 }

mbus1CValue1C		OBJECT-TYPE
			SYNTAX	INTEGER
			ACCESS	read-only
			STATUS	current
	DESCRIPTION ""
			::= { mbus1C 63 }

mbus1CVIF1D		OBJECT-TYPE
			SYNTAX	INTEGER
			ACCESS	read-only
			STATUS	current
	DESCRIPTION ""
			::= { mbus1C 64 }

mbus1CValue1D		OBJECT-TYPE
			SYNTAX	INTEGER
			ACCESS	read-only
			STATUS	current
	DESCRIPTION ""
			::= { mbus1C 65 }

mbus1CVIF1E		OBJECT-TYPE
			SYNTAX	INTEGER
			ACCESS	read-only
			STATUS	current
	DESCRIPTION ""
			::= { mbus1C 66 }

mbus1CValue1E		OBJECT-TYPE
			SYNTAX	INTEGER
			ACCESS	read-only
			STATUS	current
	DESCRIPTION ""
			::= { mbus1C 67 }

mbus1CVIF1F		OBJECT-TYPE
			SYNTAX	INTEGER
			ACCESS	read-only
			STATUS	current
	DESCRIPTION ""
			::= { mbus1C 68 }

mbus1CValue1F		OBJECT-TYPE
			SYNTAX	INTEGER
			ACCESS	read-only
			STATUS	current
	DESCRIPTION ""
			::= { mbus1C 69 }

mbus1CVIF20		OBJECT-TYPE
			SYNTAX	INTEGER
			ACCESS	read-only
			STATUS	current
	DESCRIPTION ""
			::= { mbus1C 70 }

mbus1CValue20		OBJECT-TYPE
			SYNTAX	INTEGER
			ACCESS	read-only
			STATUS	current
	DESCRIPTION ""
			::= { mbus1C 71 }

mbus1CVIF21		OBJECT-TYPE
			SYNTAX	INTEGER
			ACCESS	read-only
			STATUS	current
	DESCRIPTION ""
			::= { mbus1C 72 }

mbus1CValue21		OBJECT-TYPE
			SYNTAX	INTEGER
			ACCESS	read-only
			STATUS	current
	DESCRIPTION ""
			::= { mbus1C 73 }

mbus1CVIF22		OBJECT-TYPE
			SYNTAX	INTEGER
			ACCESS	read-only
			STATUS	current
	DESCRIPTION ""
			::= { mbus1C 74 }

mbus1CValue22		OBJECT-TYPE
			SYNTAX	INTEGER
			ACCESS	read-only
			STATUS	current
	DESCRIPTION ""
			::= { mbus1C 75 }

mbus1CVIF23		OBJECT-TYPE
			SYNTAX	INTEGER
			ACCESS	read-only
			STATUS	current
	DESCRIPTION ""
			::= { mbus1C 76 }

mbus1CValue23		OBJECT-TYPE
			SYNTAX	INTEGER
			ACCESS	read-only
			STATUS	current
	DESCRIPTION ""
			::= { mbus1C 77 }

mbus1CVIF24		OBJECT-TYPE
			SYNTAX	INTEGER
			ACCESS	read-only
			STATUS	current
	DESCRIPTION ""
			::= { mbus1C 78 }

mbus1CValue24		OBJECT-TYPE
			SYNTAX	INTEGER
			ACCESS	read-only
			STATUS	current
	DESCRIPTION ""
			::= { mbus1C 79 }

mbus1CVIF25		OBJECT-TYPE
			SYNTAX	INTEGER
			ACCESS	read-only
			STATUS	current
	DESCRIPTION ""
			::= { mbus1C 80 }

mbus1CValue25		OBJECT-TYPE
			SYNTAX	INTEGER
			ACCESS	read-only
			STATUS	current
	DESCRIPTION ""
			::= { mbus1C 81 }

mbus1CVIF26		OBJECT-TYPE
			SYNTAX	INTEGER
			ACCESS	read-only
			STATUS	current
	DESCRIPTION ""
			::= { mbus1C 82 }

mbus1CValue26		OBJECT-TYPE
			SYNTAX	INTEGER
			ACCESS	read-only
			STATUS	current
	DESCRIPTION ""
			::= { mbus1C 83 }

mbus1CVIF27		OBJECT-TYPE
			SYNTAX	INTEGER
			ACCESS	read-only
			STATUS	current
	DESCRIPTION ""
			::= { mbus1C 84 }

mbus1CValue27		OBJECT-TYPE
			SYNTAX	INTEGER
			ACCESS	read-only
			STATUS	current
	DESCRIPTION ""
			::= { mbus1C 85 }

mbus1CVIF28		OBJECT-TYPE
			SYNTAX	INTEGER
			ACCESS	read-only
			STATUS	current
	DESCRIPTION ""
			::= { mbus1C 86 }

mbus1CValue28		OBJECT-TYPE
			SYNTAX	INTEGER
			ACCESS	read-only
			STATUS	current
	DESCRIPTION ""
			::= { mbus1C 87 }

mbus1CVIF29		OBJECT-TYPE
			SYNTAX	INTEGER
			ACCESS	read-only
			STATUS	current
	DESCRIPTION ""
			::= { mbus1C 88 }

mbus1CValue29		OBJECT-TYPE
			SYNTAX	INTEGER
			ACCESS	read-only
			STATUS	current
	DESCRIPTION ""
			::= { mbus1C 89 }

mbus1CVIF2A		OBJECT-TYPE
			SYNTAX	INTEGER
			ACCESS	read-only
			STATUS	current
	DESCRIPTION ""
			::= { mbus1C 90 }

mbus1CValue2A		OBJECT-TYPE
			SYNTAX	INTEGER
			ACCESS	read-only
			STATUS	current
	DESCRIPTION ""
			::= { mbus1C 91 }

mbus1CVIF2B		OBJECT-TYPE
			SYNTAX	INTEGER
			ACCESS	read-only
			STATUS	current
	DESCRIPTION ""
			::= { mbus1C 92 }

mbus1CValue2B		OBJECT-TYPE
			SYNTAX	INTEGER
			ACCESS	read-only
			STATUS	current
	DESCRIPTION ""
			::= { mbus1C 93 }

mbus1CVIF2C		OBJECT-TYPE
			SYNTAX	INTEGER
			ACCESS	read-only
			STATUS	current
	DESCRIPTION ""
			::= { mbus1C 94 }

mbus1CValue2C		OBJECT-TYPE
			SYNTAX	INTEGER
			ACCESS	read-only
			STATUS	current
	DESCRIPTION ""
			::= { mbus1C 95 }

mbus1CVIF2D		OBJECT-TYPE
			SYNTAX	INTEGER
			ACCESS	read-only
			STATUS	current
	DESCRIPTION ""
			::= { mbus1C 96 }

mbus1CValue2D		OBJECT-TYPE
			SYNTAX	INTEGER
			ACCESS	read-only
			STATUS	current
	DESCRIPTION ""
			::= { mbus1C 97 }

mbus1CVIF2E		OBJECT-TYPE
			SYNTAX	INTEGER
			ACCESS	read-only
			STATUS	current
	DESCRIPTION ""
			::= { mbus1C 98 }

mbus1CValue2E		OBJECT-TYPE
			SYNTAX	INTEGER
			ACCESS	read-only
			STATUS	current
	DESCRIPTION ""
			::= { mbus1C 99 }

mbus1CVIF2F		OBJECT-TYPE
			SYNTAX	INTEGER
			ACCESS	read-only
			STATUS	current
	DESCRIPTION ""
			::= { mbus1C 100 }

mbus1CValue2F		OBJECT-TYPE
			SYNTAX	INTEGER
			ACCESS	read-only
			STATUS	current
	DESCRIPTION ""
			::= { mbus1C 101 }

mbus1D			OBJECT IDENTIFIER ::= { mbus 29 }

mbus1DIdNumber		OBJECT-TYPE
			SYNTAX	Gauge
			ACCESS	read-only
			STATUS	current
	DESCRIPTION ""
			::= { mbus1D 1 }

mbus1DManufacturer	OBJECT-TYPE
			SYNTAX	Gauge
			ACCESS	read-only
			STATUS	current
	DESCRIPTION ""
			::= { mbus1D 2 }

mbus1DVersion		OBJECT-TYPE
			SYNTAX	Gauge
			ACCESS	read-only
			STATUS	current
	DESCRIPTION ""
			::= { mbus1D 3 }

mbus1DMedium		OBJECT-TYPE
			SYNTAX	Gauge
			ACCESS	read-only
			STATUS	current
	DESCRIPTION ""
			::= { mbus1D 4 }

mbus1DStatus		OBJECT-TYPE
			SYNTAX	Gauge
			ACCESS	read-only
			STATUS	current
	DESCRIPTION ""
			::= { mbus1D 5 }

mbus1DVIF00		OBJECT-TYPE
			SYNTAX	INTEGER
			ACCESS	read-only
			STATUS	current
	DESCRIPTION ""
			::= { mbus1D 6 }

mbus1DValue00		OBJECT-TYPE
			SYNTAX	INTEGER
			ACCESS	read-only
			STATUS	current
	DESCRIPTION ""
			::= { mbus1D 7 }

mbus1DVIF01		OBJECT-TYPE
			SYNTAX	INTEGER
			ACCESS	read-only
			STATUS	current
	DESCRIPTION ""
			::= { mbus1D 8 }

mbus1DValue01		OBJECT-TYPE
			SYNTAX	INTEGER
			ACCESS	read-only
			STATUS	current
	DESCRIPTION ""
			::= { mbus1D 9 }

mbus1DVIF02		OBJECT-TYPE
			SYNTAX	INTEGER
			ACCESS	read-only
			STATUS	current
	DESCRIPTION ""
			::= { mbus1D 10 }

mbus1DValue02		OBJECT-TYPE
			SYNTAX	INTEGER
			ACCESS	read-only
			STATUS	current
	DESCRIPTION ""
			::= { mbus1D 11 }

mbus1DVIF03		OBJECT-TYPE
			SYNTAX	INTEGER
			ACCESS	read-only
			STATUS	current
	DESCRIPTION ""
			::= { mbus1D 12 }

mbus1DValue03		OBJECT-TYPE
			SYNTAX	INTEGER
			ACCESS	read-only
			STATUS	current
	DESCRIPTION ""
			::= { mbus1D 13 }

mbus1DVIF04		OBJECT-TYPE
			SYNTAX	INTEGER
			ACCESS	read-only
			STATUS	current
	DESCRIPTION ""
			::= { mbus1D 14 }

mbus1DValue04		OBJECT-TYPE
			SYNTAX	INTEGER
			ACCESS	read-only
			STATUS	current
	DESCRIPTION ""
			::= { mbus1D 15 }

mbus1DVIF05		OBJECT-TYPE
			SYNTAX	INTEGER
			ACCESS	read-only
			STATUS	current
	DESCRIPTION ""
			::= { mbus1D 16 }

mbus1DValue05		OBJECT-TYPE
			SYNTAX	INTEGER
			ACCESS	read-only
			STATUS	current
	DESCRIPTION ""
			::= { mbus1D 17 }

mbus1DVIF06		OBJECT-TYPE
			SYNTAX	INTEGER
			ACCESS	read-only
			STATUS	current
	DESCRIPTION ""
			::= { mbus1D 18 }

mbus1DValue06		OBJECT-TYPE
			SYNTAX	INTEGER
			ACCESS	read-only
			STATUS	current
	DESCRIPTION ""
			::= { mbus1D 19 }

mbus1DVIF07		OBJECT-TYPE
			SYNTAX	INTEGER
			ACCESS	read-only
			STATUS	current
	DESCRIPTION ""
			::= { mbus1D 20 }

mbus1DValue07		OBJECT-TYPE
			SYNTAX	INTEGER
			ACCESS	read-only
			STATUS	current
	DESCRIPTION ""
			::= { mbus1D 21 }

mbus1DVIF08		OBJECT-TYPE
			SYNTAX	INTEGER
			ACCESS	read-only
			STATUS	current
	DESCRIPTION ""
			::= { mbus1D 22 }

mbus1DValue08		OBJECT-TYPE
			SYNTAX	INTEGER
			ACCESS	read-only
			STATUS	current
	DESCRIPTION ""
			::= { mbus1D 23 }

mbus1DVIF09		OBJECT-TYPE
			SYNTAX	INTEGER
			ACCESS	read-only
			STATUS	current
	DESCRIPTION ""
			::= { mbus1D 24 }

mbus1DValue09		OBJECT-TYPE
			SYNTAX	INTEGER
			ACCESS	read-only
			STATUS	current
	DESCRIPTION ""
			::= { mbus1D 25 }

mbus1DVIF0A		OBJECT-TYPE
			SYNTAX	INTEGER
			ACCESS	read-only
			STATUS	current
	DESCRIPTION ""
			::= { mbus1D 26 }

mbus1DValue0A		OBJECT-TYPE
			SYNTAX	INTEGER
			ACCESS	read-only
			STATUS	current
	DESCRIPTION ""
			::= { mbus1D 27 }

mbus1DVIF0B		OBJECT-TYPE
			SYNTAX	INTEGER
			ACCESS	read-only
			STATUS	current
	DESCRIPTION ""
			::= { mbus1D 28 }

mbus1DValue0B		OBJECT-TYPE
			SYNTAX	INTEGER
			ACCESS	read-only
			STATUS	current
	DESCRIPTION ""
			::= { mbus1D 29 }

mbus1DVIF0C		OBJECT-TYPE
			SYNTAX	INTEGER
			ACCESS	read-only
			STATUS	current
	DESCRIPTION ""
			::= { mbus1D 30 }

mbus1DValue0C		OBJECT-TYPE
			SYNTAX	INTEGER
			ACCESS	read-only
			STATUS	current
	DESCRIPTION ""
			::= { mbus1D 31 }

mbus1DVIF0D		OBJECT-TYPE
			SYNTAX	INTEGER
			ACCESS	read-only
			STATUS	current
	DESCRIPTION ""
			::= { mbus1D 32 }

mbus1DValue0D		OBJECT-TYPE
			SYNTAX	INTEGER
			ACCESS	read-only
			STATUS	current
	DESCRIPTION ""
			::= { mbus1D 33 }

mbus1DVIF0E		OBJECT-TYPE
			SYNTAX	INTEGER
			ACCESS	read-only
			STATUS	current
	DESCRIPTION ""
			::= { mbus1D 34 }

mbus1DValue0E		OBJECT-TYPE
			SYNTAX	INTEGER
			ACCESS	read-only
			STATUS	current
	DESCRIPTION ""
			::= { mbus1D 35 }

mbus1DVIF0F		OBJECT-TYPE
			SYNTAX	INTEGER
			ACCESS	read-only
			STATUS	current
	DESCRIPTION ""
			::= { mbus1D 36 }

mbus1DValue0F		OBJECT-TYPE
			SYNTAX	INTEGER
			ACCESS	read-only
			STATUS	current
	DESCRIPTION ""
			::= { mbus1D 37 }

mbus1DVIF10		OBJECT-TYPE
			SYNTAX	INTEGER
			ACCESS	read-only
			STATUS	current
	DESCRIPTION ""
			::= { mbus1D 38 }

mbus1DValue10		OBJECT-TYPE
			SYNTAX	INTEGER
			ACCESS	read-only
			STATUS	current
	DESCRIPTION ""
			::= { mbus1D 39 }

mbus1DVIF11		OBJECT-TYPE
			SYNTAX	INTEGER
			ACCESS	read-only
			STATUS	current
	DESCRIPTION ""
			::= { mbus1D 40 }

mbus1DValue11		OBJECT-TYPE
			SYNTAX	INTEGER
			ACCESS	read-only
			STATUS	current
	DESCRIPTION ""
			::= { mbus1D 41 }

mbus1DVIF12		OBJECT-TYPE
			SYNTAX	INTEGER
			ACCESS	read-only
			STATUS	current
	DESCRIPTION ""
			::= { mbus1D 42 }

mbus1DValue12		OBJECT-TYPE
			SYNTAX	INTEGER
			ACCESS	read-only
			STATUS	current
	DESCRIPTION ""
			::= { mbus1D 43 }

mbus1DVIF13		OBJECT-TYPE
			SYNTAX	INTEGER
			ACCESS	read-only
			STATUS	current
	DESCRIPTION ""
			::= { mbus1D 44 }

mbus1DValue13		OBJECT-TYPE
			SYNTAX	INTEGER
			ACCESS	read-only
			STATUS	current
	DESCRIPTION ""
			::= { mbus1D 45 }

mbus1DVIF14		OBJECT-TYPE
			SYNTAX	INTEGER
			ACCESS	read-only
			STATUS	current
	DESCRIPTION ""
			::= { mbus1D 46 }

mbus1DValue14		OBJECT-TYPE
			SYNTAX	INTEGER
			ACCESS	read-only
			STATUS	current
	DESCRIPTION ""
			::= { mbus1D 47 }

mbus1DVIF15		OBJECT-TYPE
			SYNTAX	INTEGER
			ACCESS	read-only
			STATUS	current
	DESCRIPTION ""
			::= { mbus1D 48 }

mbus1DValue15		OBJECT-TYPE
			SYNTAX	INTEGER
			ACCESS	read-only
			STATUS	current
	DESCRIPTION ""
			::= { mbus1D 49 }

mbus1DVIF16		OBJECT-TYPE
			SYNTAX	INTEGER
			ACCESS	read-only
			STATUS	current
	DESCRIPTION ""
			::= { mbus1D 50 }

mbus1DValue16		OBJECT-TYPE
			SYNTAX	INTEGER
			ACCESS	read-only
			STATUS	current
	DESCRIPTION ""
			::= { mbus1D 51 }

mbus1DVIF17		OBJECT-TYPE
			SYNTAX	INTEGER
			ACCESS	read-only
			STATUS	current
	DESCRIPTION ""
			::= { mbus1D 52 }

mbus1DValue17		OBJECT-TYPE
			SYNTAX	INTEGER
			ACCESS	read-only
			STATUS	current
	DESCRIPTION ""
			::= { mbus1D 53 }

mbus1DVIF18		OBJECT-TYPE
			SYNTAX	INTEGER
			ACCESS	read-only
			STATUS	current
	DESCRIPTION ""
			::= { mbus1D 54 }

mbus1DValue18		OBJECT-TYPE
			SYNTAX	INTEGER
			ACCESS	read-only
			STATUS	current
	DESCRIPTION ""
			::= { mbus1D 55 }

mbus1DVIF19		OBJECT-TYPE
			SYNTAX	INTEGER
			ACCESS	read-only
			STATUS	current
	DESCRIPTION ""
			::= { mbus1D 56 }

mbus1DValue19		OBJECT-TYPE
			SYNTAX	INTEGER
			ACCESS	read-only
			STATUS	current
	DESCRIPTION ""
			::= { mbus1D 57 }

mbus1DVIF1A		OBJECT-TYPE
			SYNTAX	INTEGER
			ACCESS	read-only
			STATUS	current
	DESCRIPTION ""
			::= { mbus1D 58 }

mbus1DValue1A		OBJECT-TYPE
			SYNTAX	INTEGER
			ACCESS	read-only
			STATUS	current
	DESCRIPTION ""
			::= { mbus1D 59 }

mbus1DVIF1B		OBJECT-TYPE
			SYNTAX	INTEGER
			ACCESS	read-only
			STATUS	current
	DESCRIPTION ""
			::= { mbus1D 60 }

mbus1DValue1B		OBJECT-TYPE
			SYNTAX	INTEGER
			ACCESS	read-only
			STATUS	current
	DESCRIPTION ""
			::= { mbus1D 61 }

mbus1DVIF1C		OBJECT-TYPE
			SYNTAX	INTEGER
			ACCESS	read-only
			STATUS	current
	DESCRIPTION ""
			::= { mbus1D 62 }

mbus1DValue1C		OBJECT-TYPE
			SYNTAX	INTEGER
			ACCESS	read-only
			STATUS	current
	DESCRIPTION ""
			::= { mbus1D 63 }

mbus1DVIF1D		OBJECT-TYPE
			SYNTAX	INTEGER
			ACCESS	read-only
			STATUS	current
	DESCRIPTION ""
			::= { mbus1D 64 }

mbus1DValue1D		OBJECT-TYPE
			SYNTAX	INTEGER
			ACCESS	read-only
			STATUS	current
	DESCRIPTION ""
			::= { mbus1D 65 }

mbus1DVIF1E		OBJECT-TYPE
			SYNTAX	INTEGER
			ACCESS	read-only
			STATUS	current
	DESCRIPTION ""
			::= { mbus1D 66 }

mbus1DValue1E		OBJECT-TYPE
			SYNTAX	INTEGER
			ACCESS	read-only
			STATUS	current
	DESCRIPTION ""
			::= { mbus1D 67 }

mbus1DVIF1F		OBJECT-TYPE
			SYNTAX	INTEGER
			ACCESS	read-only
			STATUS	current
	DESCRIPTION ""
			::= { mbus1D 68 }

mbus1DValue1F		OBJECT-TYPE
			SYNTAX	INTEGER
			ACCESS	read-only
			STATUS	current
	DESCRIPTION ""
			::= { mbus1D 69 }

mbus1DVIF20		OBJECT-TYPE
			SYNTAX	INTEGER
			ACCESS	read-only
			STATUS	current
	DESCRIPTION ""
			::= { mbus1D 70 }

mbus1DValue20		OBJECT-TYPE
			SYNTAX	INTEGER
			ACCESS	read-only
			STATUS	current
	DESCRIPTION ""
			::= { mbus1D 71 }

mbus1DVIF21		OBJECT-TYPE
			SYNTAX	INTEGER
			ACCESS	read-only
			STATUS	current
	DESCRIPTION ""
			::= { mbus1D 72 }

mbus1DValue21		OBJECT-TYPE
			SYNTAX	INTEGER
			ACCESS	read-only
			STATUS	current
	DESCRIPTION ""
			::= { mbus1D 73 }

mbus1DVIF22		OBJECT-TYPE
			SYNTAX	INTEGER
			ACCESS	read-only
			STATUS	current
	DESCRIPTION ""
			::= { mbus1D 74 }

mbus1DValue22		OBJECT-TYPE
			SYNTAX	INTEGER
			ACCESS	read-only
			STATUS	current
	DESCRIPTION ""
			::= { mbus1D 75 }

mbus1DVIF23		OBJECT-TYPE
			SYNTAX	INTEGER
			ACCESS	read-only
			STATUS	current
	DESCRIPTION ""
			::= { mbus1D 76 }

mbus1DValue23		OBJECT-TYPE
			SYNTAX	INTEGER
			ACCESS	read-only
			STATUS	current
	DESCRIPTION ""
			::= { mbus1D 77 }

mbus1DVIF24		OBJECT-TYPE
			SYNTAX	INTEGER
			ACCESS	read-only
			STATUS	current
	DESCRIPTION ""
			::= { mbus1D 78 }

mbus1DValue24		OBJECT-TYPE
			SYNTAX	INTEGER
			ACCESS	read-only
			STATUS	current
	DESCRIPTION ""
			::= { mbus1D 79 }

mbus1DVIF25		OBJECT-TYPE
			SYNTAX	INTEGER
			ACCESS	read-only
			STATUS	current
	DESCRIPTION ""
			::= { mbus1D 80 }

mbus1DValue25		OBJECT-TYPE
			SYNTAX	INTEGER
			ACCESS	read-only
			STATUS	current
	DESCRIPTION ""
			::= { mbus1D 81 }

mbus1DVIF26		OBJECT-TYPE
			SYNTAX	INTEGER
			ACCESS	read-only
			STATUS	current
	DESCRIPTION ""
			::= { mbus1D 82 }

mbus1DValue26		OBJECT-TYPE
			SYNTAX	INTEGER
			ACCESS	read-only
			STATUS	current
	DESCRIPTION ""
			::= { mbus1D 83 }

mbus1DVIF27		OBJECT-TYPE
			SYNTAX	INTEGER
			ACCESS	read-only
			STATUS	current
	DESCRIPTION ""
			::= { mbus1D 84 }

mbus1DValue27		OBJECT-TYPE
			SYNTAX	INTEGER
			ACCESS	read-only
			STATUS	current
	DESCRIPTION ""
			::= { mbus1D 85 }

mbus1DVIF28		OBJECT-TYPE
			SYNTAX	INTEGER
			ACCESS	read-only
			STATUS	current
	DESCRIPTION ""
			::= { mbus1D 86 }

mbus1DValue28		OBJECT-TYPE
			SYNTAX	INTEGER
			ACCESS	read-only
			STATUS	current
	DESCRIPTION ""
			::= { mbus1D 87 }

mbus1DVIF29		OBJECT-TYPE
			SYNTAX	INTEGER
			ACCESS	read-only
			STATUS	current
	DESCRIPTION ""
			::= { mbus1D 88 }

mbus1DValue29		OBJECT-TYPE
			SYNTAX	INTEGER
			ACCESS	read-only
			STATUS	current
	DESCRIPTION ""
			::= { mbus1D 89 }

mbus1DVIF2A		OBJECT-TYPE
			SYNTAX	INTEGER
			ACCESS	read-only
			STATUS	current
	DESCRIPTION ""
			::= { mbus1D 90 }

mbus1DValue2A		OBJECT-TYPE
			SYNTAX	INTEGER
			ACCESS	read-only
			STATUS	current
	DESCRIPTION ""
			::= { mbus1D 91 }

mbus1DVIF2B		OBJECT-TYPE
			SYNTAX	INTEGER
			ACCESS	read-only
			STATUS	current
	DESCRIPTION ""
			::= { mbus1D 92 }

mbus1DValue2B		OBJECT-TYPE
			SYNTAX	INTEGER
			ACCESS	read-only
			STATUS	current
	DESCRIPTION ""
			::= { mbus1D 93 }

mbus1DVIF2C		OBJECT-TYPE
			SYNTAX	INTEGER
			ACCESS	read-only
			STATUS	current
	DESCRIPTION ""
			::= { mbus1D 94 }

mbus1DValue2C		OBJECT-TYPE
			SYNTAX	INTEGER
			ACCESS	read-only
			STATUS	current
	DESCRIPTION ""
			::= { mbus1D 95 }

mbus1DVIF2D		OBJECT-TYPE
			SYNTAX	INTEGER
			ACCESS	read-only
			STATUS	current
	DESCRIPTION ""
			::= { mbus1D 96 }

mbus1DValue2D		OBJECT-TYPE
			SYNTAX	INTEGER
			ACCESS	read-only
			STATUS	current
	DESCRIPTION ""
			::= { mbus1D 97 }

mbus1DVIF2E		OBJECT-TYPE
			SYNTAX	INTEGER
			ACCESS	read-only
			STATUS	current
	DESCRIPTION ""
			::= { mbus1D 98 }

mbus1DValue2E		OBJECT-TYPE
			SYNTAX	INTEGER
			ACCESS	read-only
			STATUS	current
	DESCRIPTION ""
			::= { mbus1D 99 }

mbus1DVIF2F		OBJECT-TYPE
			SYNTAX	INTEGER
			ACCESS	read-only
			STATUS	current
	DESCRIPTION ""
			::= { mbus1D 100 }

mbus1DValue2F		OBJECT-TYPE
			SYNTAX	INTEGER
			ACCESS	read-only
			STATUS	current
	DESCRIPTION ""
			::= { mbus1D 101 }

mbus1E			OBJECT IDENTIFIER ::= { mbus 30 }

mbus1EIdNumber		OBJECT-TYPE
			SYNTAX	Gauge
			ACCESS	read-only
			STATUS	current
	DESCRIPTION ""
			::= { mbus1E 1 }

mbus1EManufacturer	OBJECT-TYPE
			SYNTAX	Gauge
			ACCESS	read-only
			STATUS	current
	DESCRIPTION ""
			::= { mbus1E 2 }

mbus1EVersion		OBJECT-TYPE
			SYNTAX	Gauge
			ACCESS	read-only
			STATUS	current
	DESCRIPTION ""
			::= { mbus1E 3 }

mbus1EMedium		OBJECT-TYPE
			SYNTAX	Gauge
			ACCESS	read-only
			STATUS	current
	DESCRIPTION ""
			::= { mbus1E 4 }

mbus1EStatus		OBJECT-TYPE
			SYNTAX	Gauge
			ACCESS	read-only
			STATUS	current
	DESCRIPTION ""
			::= { mbus1E 5 }

mbus1EVIF00		OBJECT-TYPE
			SYNTAX	INTEGER
			ACCESS	read-only
			STATUS	current
	DESCRIPTION ""
			::= { mbus1E 6 }

mbus1EValue00		OBJECT-TYPE
			SYNTAX	INTEGER
			ACCESS	read-only
			STATUS	current
	DESCRIPTION ""
			::= { mbus1E 7 }

mbus1EVIF01		OBJECT-TYPE
			SYNTAX	INTEGER
			ACCESS	read-only
			STATUS	current
	DESCRIPTION ""
			::= { mbus1E 8 }

mbus1EValue01		OBJECT-TYPE
			SYNTAX	INTEGER
			ACCESS	read-only
			STATUS	current
	DESCRIPTION ""
			::= { mbus1E 9 }

mbus1EVIF02		OBJECT-TYPE
			SYNTAX	INTEGER
			ACCESS	read-only
			STATUS	current
	DESCRIPTION ""
			::= { mbus1E 10 }

mbus1EValue02		OBJECT-TYPE
			SYNTAX	INTEGER
			ACCESS	read-only
			STATUS	current
	DESCRIPTION ""
			::= { mbus1E 11 }

mbus1EVIF03		OBJECT-TYPE
			SYNTAX	INTEGER
			ACCESS	read-only
			STATUS	current
	DESCRIPTION ""
			::= { mbus1E 12 }

mbus1EValue03		OBJECT-TYPE
			SYNTAX	INTEGER
			ACCESS	read-only
			STATUS	current
	DESCRIPTION ""
			::= { mbus1E 13 }

mbus1EVIF04		OBJECT-TYPE
			SYNTAX	INTEGER
			ACCESS	read-only
			STATUS	current
	DESCRIPTION ""
			::= { mbus1E 14 }

mbus1EValue04		OBJECT-TYPE
			SYNTAX	INTEGER
			ACCESS	read-only
			STATUS	current
	DESCRIPTION ""
			::= { mbus1E 15 }

mbus1EVIF05		OBJECT-TYPE
			SYNTAX	INTEGER
			ACCESS	read-only
			STATUS	current
	DESCRIPTION ""
			::= { mbus1E 16 }

mbus1EValue05		OBJECT-TYPE
			SYNTAX	INTEGER
			ACCESS	read-only
			STATUS	current
	DESCRIPTION ""
			::= { mbus1E 17 }

mbus1EVIF06		OBJECT-TYPE
			SYNTAX	INTEGER
			ACCESS	read-only
			STATUS	current
	DESCRIPTION ""
			::= { mbus1E 18 }

mbus1EValue06		OBJECT-TYPE
			SYNTAX	INTEGER
			ACCESS	read-only
			STATUS	current
	DESCRIPTION ""
			::= { mbus1E 19 }

mbus1EVIF07		OBJECT-TYPE
			SYNTAX	INTEGER
			ACCESS	read-only
			STATUS	current
	DESCRIPTION ""
			::= { mbus1E 20 }

mbus1EValue07		OBJECT-TYPE
			SYNTAX	INTEGER
			ACCESS	read-only
			STATUS	current
	DESCRIPTION ""
			::= { mbus1E 21 }

mbus1EVIF08		OBJECT-TYPE
			SYNTAX	INTEGER
			ACCESS	read-only
			STATUS	current
	DESCRIPTION ""
			::= { mbus1E 22 }

mbus1EValue08		OBJECT-TYPE
			SYNTAX	INTEGER
			ACCESS	read-only
			STATUS	current
	DESCRIPTION ""
			::= { mbus1E 23 }

mbus1EVIF09		OBJECT-TYPE
			SYNTAX	INTEGER
			ACCESS	read-only
			STATUS	current
	DESCRIPTION ""
			::= { mbus1E 24 }

mbus1EValue09		OBJECT-TYPE
			SYNTAX	INTEGER
			ACCESS	read-only
			STATUS	current
	DESCRIPTION ""
			::= { mbus1E 25 }

mbus1EVIF0A		OBJECT-TYPE
			SYNTAX	INTEGER
			ACCESS	read-only
			STATUS	current
	DESCRIPTION ""
			::= { mbus1E 26 }

mbus1EValue0A		OBJECT-TYPE
			SYNTAX	INTEGER
			ACCESS	read-only
			STATUS	current
	DESCRIPTION ""
			::= { mbus1E 27 }

mbus1EVIF0B		OBJECT-TYPE
			SYNTAX	INTEGER
			ACCESS	read-only
			STATUS	current
	DESCRIPTION ""
			::= { mbus1E 28 }

mbus1EValue0B		OBJECT-TYPE
			SYNTAX	INTEGER
			ACCESS	read-only
			STATUS	current
	DESCRIPTION ""
			::= { mbus1E 29 }

mbus1EVIF0C		OBJECT-TYPE
			SYNTAX	INTEGER
			ACCESS	read-only
			STATUS	current
	DESCRIPTION ""
			::= { mbus1E 30 }

mbus1EValue0C		OBJECT-TYPE
			SYNTAX	INTEGER
			ACCESS	read-only
			STATUS	current
	DESCRIPTION ""
			::= { mbus1E 31 }

mbus1EVIF0D		OBJECT-TYPE
			SYNTAX	INTEGER
			ACCESS	read-only
			STATUS	current
	DESCRIPTION ""
			::= { mbus1E 32 }

mbus1EValue0D		OBJECT-TYPE
			SYNTAX	INTEGER
			ACCESS	read-only
			STATUS	current
	DESCRIPTION ""
			::= { mbus1E 33 }

mbus1EVIF0E		OBJECT-TYPE
			SYNTAX	INTEGER
			ACCESS	read-only
			STATUS	current
	DESCRIPTION ""
			::= { mbus1E 34 }

mbus1EValue0E		OBJECT-TYPE
			SYNTAX	INTEGER
			ACCESS	read-only
			STATUS	current
	DESCRIPTION ""
			::= { mbus1E 35 }

mbus1EVIF0F		OBJECT-TYPE
			SYNTAX	INTEGER
			ACCESS	read-only
			STATUS	current
	DESCRIPTION ""
			::= { mbus1E 36 }

mbus1EValue0F		OBJECT-TYPE
			SYNTAX	INTEGER
			ACCESS	read-only
			STATUS	current
	DESCRIPTION ""
			::= { mbus1E 37 }

mbus1EVIF10		OBJECT-TYPE
			SYNTAX	INTEGER
			ACCESS	read-only
			STATUS	current
	DESCRIPTION ""
			::= { mbus1E 38 }

mbus1EValue10		OBJECT-TYPE
			SYNTAX	INTEGER
			ACCESS	read-only
			STATUS	current
	DESCRIPTION ""
			::= { mbus1E 39 }

mbus1EVIF11		OBJECT-TYPE
			SYNTAX	INTEGER
			ACCESS	read-only
			STATUS	current
	DESCRIPTION ""
			::= { mbus1E 40 }

mbus1EValue11		OBJECT-TYPE
			SYNTAX	INTEGER
			ACCESS	read-only
			STATUS	current
	DESCRIPTION ""
			::= { mbus1E 41 }

mbus1EVIF12		OBJECT-TYPE
			SYNTAX	INTEGER
			ACCESS	read-only
			STATUS	current
	DESCRIPTION ""
			::= { mbus1E 42 }

mbus1EValue12		OBJECT-TYPE
			SYNTAX	INTEGER
			ACCESS	read-only
			STATUS	current
	DESCRIPTION ""
			::= { mbus1E 43 }

mbus1EVIF13		OBJECT-TYPE
			SYNTAX	INTEGER
			ACCESS	read-only
			STATUS	current
	DESCRIPTION ""
			::= { mbus1E 44 }

mbus1EValue13		OBJECT-TYPE
			SYNTAX	INTEGER
			ACCESS	read-only
			STATUS	current
	DESCRIPTION ""
			::= { mbus1E 45 }

mbus1EVIF14		OBJECT-TYPE
			SYNTAX	INTEGER
			ACCESS	read-only
			STATUS	current
	DESCRIPTION ""
			::= { mbus1E 46 }

mbus1EValue14		OBJECT-TYPE
			SYNTAX	INTEGER
			ACCESS	read-only
			STATUS	current
	DESCRIPTION ""
			::= { mbus1E 47 }

mbus1EVIF15		OBJECT-TYPE
			SYNTAX	INTEGER
			ACCESS	read-only
			STATUS	current
	DESCRIPTION ""
			::= { mbus1E 48 }

mbus1EValue15		OBJECT-TYPE
			SYNTAX	INTEGER
			ACCESS	read-only
			STATUS	current
	DESCRIPTION ""
			::= { mbus1E 49 }

mbus1EVIF16		OBJECT-TYPE
			SYNTAX	INTEGER
			ACCESS	read-only
			STATUS	current
	DESCRIPTION ""
			::= { mbus1E 50 }

mbus1EValue16		OBJECT-TYPE
			SYNTAX	INTEGER
			ACCESS	read-only
			STATUS	current
	DESCRIPTION ""
			::= { mbus1E 51 }

mbus1EVIF17		OBJECT-TYPE
			SYNTAX	INTEGER
			ACCESS	read-only
			STATUS	current
	DESCRIPTION ""
			::= { mbus1E 52 }

mbus1EValue17		OBJECT-TYPE
			SYNTAX	INTEGER
			ACCESS	read-only
			STATUS	current
	DESCRIPTION ""
			::= { mbus1E 53 }

mbus1EVIF18		OBJECT-TYPE
			SYNTAX	INTEGER
			ACCESS	read-only
			STATUS	current
	DESCRIPTION ""
			::= { mbus1E 54 }

mbus1EValue18		OBJECT-TYPE
			SYNTAX	INTEGER
			ACCESS	read-only
			STATUS	current
	DESCRIPTION ""
			::= { mbus1E 55 }

mbus1EVIF19		OBJECT-TYPE
			SYNTAX	INTEGER
			ACCESS	read-only
			STATUS	current
	DESCRIPTION ""
			::= { mbus1E 56 }

mbus1EValue19		OBJECT-TYPE
			SYNTAX	INTEGER
			ACCESS	read-only
			STATUS	current
	DESCRIPTION ""
			::= { mbus1E 57 }

mbus1EVIF1A		OBJECT-TYPE
			SYNTAX	INTEGER
			ACCESS	read-only
			STATUS	current
	DESCRIPTION ""
			::= { mbus1E 58 }

mbus1EValue1A		OBJECT-TYPE
			SYNTAX	INTEGER
			ACCESS	read-only
			STATUS	current
	DESCRIPTION ""
			::= { mbus1E 59 }

mbus1EVIF1B		OBJECT-TYPE
			SYNTAX	INTEGER
			ACCESS	read-only
			STATUS	current
	DESCRIPTION ""
			::= { mbus1E 60 }

mbus1EValue1B		OBJECT-TYPE
			SYNTAX	INTEGER
			ACCESS	read-only
			STATUS	current
	DESCRIPTION ""
			::= { mbus1E 61 }

mbus1EVIF1C		OBJECT-TYPE
			SYNTAX	INTEGER
			ACCESS	read-only
			STATUS	current
	DESCRIPTION ""
			::= { mbus1E 62 }

mbus1EValue1C		OBJECT-TYPE
			SYNTAX	INTEGER
			ACCESS	read-only
			STATUS	current
	DESCRIPTION ""
			::= { mbus1E 63 }

mbus1EVIF1D		OBJECT-TYPE
			SYNTAX	INTEGER
			ACCESS	read-only
			STATUS	current
	DESCRIPTION ""
			::= { mbus1E 64 }

mbus1EValue1D		OBJECT-TYPE
			SYNTAX	INTEGER
			ACCESS	read-only
			STATUS	current
	DESCRIPTION ""
			::= { mbus1E 65 }

mbus1EVIF1E		OBJECT-TYPE
			SYNTAX	INTEGER
			ACCESS	read-only
			STATUS	current
	DESCRIPTION ""
			::= { mbus1E 66 }

mbus1EValue1E		OBJECT-TYPE
			SYNTAX	INTEGER
			ACCESS	read-only
			STATUS	current
	DESCRIPTION ""
			::= { mbus1E 67 }

mbus1EVIF1F		OBJECT-TYPE
			SYNTAX	INTEGER
			ACCESS	read-only
			STATUS	current
	DESCRIPTION ""
			::= { mbus1E 68 }

mbus1EValue1F		OBJECT-TYPE
			SYNTAX	INTEGER
			ACCESS	read-only
			STATUS	current
	DESCRIPTION ""
			::= { mbus1E 69 }

mbus1EVIF20		OBJECT-TYPE
			SYNTAX	INTEGER
			ACCESS	read-only
			STATUS	current
	DESCRIPTION ""
			::= { mbus1E 70 }

mbus1EValue20		OBJECT-TYPE
			SYNTAX	INTEGER
			ACCESS	read-only
			STATUS	current
	DESCRIPTION ""
			::= { mbus1E 71 }

mbus1EVIF21		OBJECT-TYPE
			SYNTAX	INTEGER
			ACCESS	read-only
			STATUS	current
	DESCRIPTION ""
			::= { mbus1E 72 }

mbus1EValue21		OBJECT-TYPE
			SYNTAX	INTEGER
			ACCESS	read-only
			STATUS	current
	DESCRIPTION ""
			::= { mbus1E 73 }

mbus1EVIF22		OBJECT-TYPE
			SYNTAX	INTEGER
			ACCESS	read-only
			STATUS	current
	DESCRIPTION ""
			::= { mbus1E 74 }

mbus1EValue22		OBJECT-TYPE
			SYNTAX	INTEGER
			ACCESS	read-only
			STATUS	current
	DESCRIPTION ""
			::= { mbus1E 75 }

mbus1EVIF23		OBJECT-TYPE
			SYNTAX	INTEGER
			ACCESS	read-only
			STATUS	current
	DESCRIPTION ""
			::= { mbus1E 76 }

mbus1EValue23		OBJECT-TYPE
			SYNTAX	INTEGER
			ACCESS	read-only
			STATUS	current
	DESCRIPTION ""
			::= { mbus1E 77 }

mbus1EVIF24		OBJECT-TYPE
			SYNTAX	INTEGER
			ACCESS	read-only
			STATUS	current
	DESCRIPTION ""
			::= { mbus1E 78 }

mbus1EValue24		OBJECT-TYPE
			SYNTAX	INTEGER
			ACCESS	read-only
			STATUS	current
	DESCRIPTION ""
			::= { mbus1E 79 }

mbus1EVIF25		OBJECT-TYPE
			SYNTAX	INTEGER
			ACCESS	read-only
			STATUS	current
	DESCRIPTION ""
			::= { mbus1E 80 }

mbus1EValue25		OBJECT-TYPE
			SYNTAX	INTEGER
			ACCESS	read-only
			STATUS	current
	DESCRIPTION ""
			::= { mbus1E 81 }

mbus1EVIF26		OBJECT-TYPE
			SYNTAX	INTEGER
			ACCESS	read-only
			STATUS	current
	DESCRIPTION ""
			::= { mbus1E 82 }

mbus1EValue26		OBJECT-TYPE
			SYNTAX	INTEGER
			ACCESS	read-only
			STATUS	current
	DESCRIPTION ""
			::= { mbus1E 83 }

mbus1EVIF27		OBJECT-TYPE
			SYNTAX	INTEGER
			ACCESS	read-only
			STATUS	current
	DESCRIPTION ""
			::= { mbus1E 84 }

mbus1EValue27		OBJECT-TYPE
			SYNTAX	INTEGER
			ACCESS	read-only
			STATUS	current
	DESCRIPTION ""
			::= { mbus1E 85 }

mbus1EVIF28		OBJECT-TYPE
			SYNTAX	INTEGER
			ACCESS	read-only
			STATUS	current
	DESCRIPTION ""
			::= { mbus1E 86 }

mbus1EValue28		OBJECT-TYPE
			SYNTAX	INTEGER
			ACCESS	read-only
			STATUS	current
	DESCRIPTION ""
			::= { mbus1E 87 }

mbus1EVIF29		OBJECT-TYPE
			SYNTAX	INTEGER
			ACCESS	read-only
			STATUS	current
	DESCRIPTION ""
			::= { mbus1E 88 }

mbus1EValue29		OBJECT-TYPE
			SYNTAX	INTEGER
			ACCESS	read-only
			STATUS	current
	DESCRIPTION ""
			::= { mbus1E 89 }

mbus1EVIF2A		OBJECT-TYPE
			SYNTAX	INTEGER
			ACCESS	read-only
			STATUS	current
	DESCRIPTION ""
			::= { mbus1E 90 }

mbus1EValue2A		OBJECT-TYPE
			SYNTAX	INTEGER
			ACCESS	read-only
			STATUS	current
	DESCRIPTION ""
			::= { mbus1E 91 }

mbus1EVIF2B		OBJECT-TYPE
			SYNTAX	INTEGER
			ACCESS	read-only
			STATUS	current
	DESCRIPTION ""
			::= { mbus1E 92 }

mbus1EValue2B		OBJECT-TYPE
			SYNTAX	INTEGER
			ACCESS	read-only
			STATUS	current
	DESCRIPTION ""
			::= { mbus1E 93 }

mbus1EVIF2C		OBJECT-TYPE
			SYNTAX	INTEGER
			ACCESS	read-only
			STATUS	current
	DESCRIPTION ""
			::= { mbus1E 94 }

mbus1EValue2C		OBJECT-TYPE
			SYNTAX	INTEGER
			ACCESS	read-only
			STATUS	current
	DESCRIPTION ""
			::= { mbus1E 95 }

mbus1EVIF2D		OBJECT-TYPE
			SYNTAX	INTEGER
			ACCESS	read-only
			STATUS	current
	DESCRIPTION ""
			::= { mbus1E 96 }

mbus1EValue2D		OBJECT-TYPE
			SYNTAX	INTEGER
			ACCESS	read-only
			STATUS	current
	DESCRIPTION ""
			::= { mbus1E 97 }

mbus1EVIF2E		OBJECT-TYPE
			SYNTAX	INTEGER
			ACCESS	read-only
			STATUS	current
	DESCRIPTION ""
			::= { mbus1E 98 }

mbus1EValue2E		OBJECT-TYPE
			SYNTAX	INTEGER
			ACCESS	read-only
			STATUS	current
	DESCRIPTION ""
			::= { mbus1E 99 }

mbus1EVIF2F		OBJECT-TYPE
			SYNTAX	INTEGER
			ACCESS	read-only
			STATUS	current
	DESCRIPTION ""
			::= { mbus1E 100 }

mbus1EValue2F		OBJECT-TYPE
			SYNTAX	INTEGER
			ACCESS	read-only
			STATUS	current
	DESCRIPTION ""
			::= { mbus1E 101 }

mbus1F			OBJECT IDENTIFIER ::= { mbus 31 }

mbus1FIdNumber		OBJECT-TYPE
			SYNTAX	Gauge
			ACCESS	read-only
			STATUS	current
	DESCRIPTION ""
			::= { mbus1F 1 }

mbus1FManufacturer	OBJECT-TYPE
			SYNTAX	Gauge
			ACCESS	read-only
			STATUS	current
	DESCRIPTION ""
			::= { mbus1F 2 }

mbus1FVersion		OBJECT-TYPE
			SYNTAX	Gauge
			ACCESS	read-only
			STATUS	current
	DESCRIPTION ""
			::= { mbus1F 3 }

mbus1FMedium		OBJECT-TYPE
			SYNTAX	Gauge
			ACCESS	read-only
			STATUS	current
	DESCRIPTION ""
			::= { mbus1F 4 }

mbus1FStatus		OBJECT-TYPE
			SYNTAX	Gauge
			ACCESS	read-only
			STATUS	current
	DESCRIPTION ""
			::= { mbus1F 5 }

mbus1FVIF00		OBJECT-TYPE
			SYNTAX	INTEGER
			ACCESS	read-only
			STATUS	current
	DESCRIPTION ""
			::= { mbus1F 6 }

mbus1FValue00		OBJECT-TYPE
			SYNTAX	INTEGER
			ACCESS	read-only
			STATUS	current
	DESCRIPTION ""
			::= { mbus1F 7 }

mbus1FVIF01		OBJECT-TYPE
			SYNTAX	INTEGER
			ACCESS	read-only
			STATUS	current
	DESCRIPTION ""
			::= { mbus1F 8 }

mbus1FValue01		OBJECT-TYPE
			SYNTAX	INTEGER
			ACCESS	read-only
			STATUS	current
	DESCRIPTION ""
			::= { mbus1F 9 }

mbus1FVIF02		OBJECT-TYPE
			SYNTAX	INTEGER
			ACCESS	read-only
			STATUS	current
	DESCRIPTION ""
			::= { mbus1F 10 }

mbus1FValue02		OBJECT-TYPE
			SYNTAX	INTEGER
			ACCESS	read-only
			STATUS	current
	DESCRIPTION ""
			::= { mbus1F 11 }

mbus1FVIF03		OBJECT-TYPE
			SYNTAX	INTEGER
			ACCESS	read-only
			STATUS	current
	DESCRIPTION ""
			::= { mbus1F 12 }

mbus1FValue03		OBJECT-TYPE
			SYNTAX	INTEGER
			ACCESS	read-only
			STATUS	current
	DESCRIPTION ""
			::= { mbus1F 13 }

mbus1FVIF04		OBJECT-TYPE
			SYNTAX	INTEGER
			ACCESS	read-only
			STATUS	current
	DESCRIPTION ""
			::= { mbus1F 14 }

mbus1FValue04		OBJECT-TYPE
			SYNTAX	INTEGER
			ACCESS	read-only
			STATUS	current
	DESCRIPTION ""
			::= { mbus1F 15 }

mbus1FVIF05		OBJECT-TYPE
			SYNTAX	INTEGER
			ACCESS	read-only
			STATUS	current
	DESCRIPTION ""
			::= { mbus1F 16 }

mbus1FValue05		OBJECT-TYPE
			SYNTAX	INTEGER
			ACCESS	read-only
			STATUS	current
	DESCRIPTION ""
			::= { mbus1F 17 }

mbus1FVIF06		OBJECT-TYPE
			SYNTAX	INTEGER
			ACCESS	read-only
			STATUS	current
	DESCRIPTION ""
			::= { mbus1F 18 }

mbus1FValue06		OBJECT-TYPE
			SYNTAX	INTEGER
			ACCESS	read-only
			STATUS	current
	DESCRIPTION ""
			::= { mbus1F 19 }

mbus1FVIF07		OBJECT-TYPE
			SYNTAX	INTEGER
			ACCESS	read-only
			STATUS	current
	DESCRIPTION ""
			::= { mbus1F 20 }

mbus1FValue07		OBJECT-TYPE
			SYNTAX	INTEGER
			ACCESS	read-only
			STATUS	current
	DESCRIPTION ""
			::= { mbus1F 21 }

mbus1FVIF08		OBJECT-TYPE
			SYNTAX	INTEGER
			ACCESS	read-only
			STATUS	current
	DESCRIPTION ""
			::= { mbus1F 22 }

mbus1FValue08		OBJECT-TYPE
			SYNTAX	INTEGER
			ACCESS	read-only
			STATUS	current
	DESCRIPTION ""
			::= { mbus1F 23 }

mbus1FVIF09		OBJECT-TYPE
			SYNTAX	INTEGER
			ACCESS	read-only
			STATUS	current
	DESCRIPTION ""
			::= { mbus1F 24 }

mbus1FValue09		OBJECT-TYPE
			SYNTAX	INTEGER
			ACCESS	read-only
			STATUS	current
	DESCRIPTION ""
			::= { mbus1F 25 }

mbus1FVIF0A		OBJECT-TYPE
			SYNTAX	INTEGER
			ACCESS	read-only
			STATUS	current
	DESCRIPTION ""
			::= { mbus1F 26 }

mbus1FValue0A		OBJECT-TYPE
			SYNTAX	INTEGER
			ACCESS	read-only
			STATUS	current
	DESCRIPTION ""
			::= { mbus1F 27 }

mbus1FVIF0B		OBJECT-TYPE
			SYNTAX	INTEGER
			ACCESS	read-only
			STATUS	current
	DESCRIPTION ""
			::= { mbus1F 28 }

mbus1FValue0B		OBJECT-TYPE
			SYNTAX	INTEGER
			ACCESS	read-only
			STATUS	current
	DESCRIPTION ""
			::= { mbus1F 29 }

mbus1FVIF0C		OBJECT-TYPE
			SYNTAX	INTEGER
			ACCESS	read-only
			STATUS	current
	DESCRIPTION ""
			::= { mbus1F 30 }

mbus1FValue0C		OBJECT-TYPE
			SYNTAX	INTEGER
			ACCESS	read-only
			STATUS	current
	DESCRIPTION ""
			::= { mbus1F 31 }

mbus1FVIF0D		OBJECT-TYPE
			SYNTAX	INTEGER
			ACCESS	read-only
			STATUS	current
	DESCRIPTION ""
			::= { mbus1F 32 }

mbus1FValue0D		OBJECT-TYPE
			SYNTAX	INTEGER
			ACCESS	read-only
			STATUS	current
	DESCRIPTION ""
			::= { mbus1F 33 }

mbus1FVIF0E		OBJECT-TYPE
			SYNTAX	INTEGER
			ACCESS	read-only
			STATUS	current
	DESCRIPTION ""
			::= { mbus1F 34 }

mbus1FValue0E		OBJECT-TYPE
			SYNTAX	INTEGER
			ACCESS	read-only
			STATUS	current
	DESCRIPTION ""
			::= { mbus1F 35 }

mbus1FVIF0F		OBJECT-TYPE
			SYNTAX	INTEGER
			ACCESS	read-only
			STATUS	current
	DESCRIPTION ""
			::= { mbus1F 36 }

mbus1FValue0F		OBJECT-TYPE
			SYNTAX	INTEGER
			ACCESS	read-only
			STATUS	current
	DESCRIPTION ""
			::= { mbus1F 37 }

mbus1FVIF10		OBJECT-TYPE
			SYNTAX	INTEGER
			ACCESS	read-only
			STATUS	current
	DESCRIPTION ""
			::= { mbus1F 38 }

mbus1FValue10		OBJECT-TYPE
			SYNTAX	INTEGER
			ACCESS	read-only
			STATUS	current
	DESCRIPTION ""
			::= { mbus1F 39 }

mbus1FVIF11		OBJECT-TYPE
			SYNTAX	INTEGER
			ACCESS	read-only
			STATUS	current
	DESCRIPTION ""
			::= { mbus1F 40 }

mbus1FValue11		OBJECT-TYPE
			SYNTAX	INTEGER
			ACCESS	read-only
			STATUS	current
	DESCRIPTION ""
			::= { mbus1F 41 }

mbus1FVIF12		OBJECT-TYPE
			SYNTAX	INTEGER
			ACCESS	read-only
			STATUS	current
	DESCRIPTION ""
			::= { mbus1F 42 }

mbus1FValue12		OBJECT-TYPE
			SYNTAX	INTEGER
			ACCESS	read-only
			STATUS	current
	DESCRIPTION ""
			::= { mbus1F 43 }

mbus1FVIF13		OBJECT-TYPE
			SYNTAX	INTEGER
			ACCESS	read-only
			STATUS	current
	DESCRIPTION ""
			::= { mbus1F 44 }

mbus1FValue13		OBJECT-TYPE
			SYNTAX	INTEGER
			ACCESS	read-only
			STATUS	current
	DESCRIPTION ""
			::= { mbus1F 45 }

mbus1FVIF14		OBJECT-TYPE
			SYNTAX	INTEGER
			ACCESS	read-only
			STATUS	current
	DESCRIPTION ""
			::= { mbus1F 46 }

mbus1FValue14		OBJECT-TYPE
			SYNTAX	INTEGER
			ACCESS	read-only
			STATUS	current
	DESCRIPTION ""
			::= { mbus1F 47 }

mbus1FVIF15		OBJECT-TYPE
			SYNTAX	INTEGER
			ACCESS	read-only
			STATUS	current
	DESCRIPTION ""
			::= { mbus1F 48 }

mbus1FValue15		OBJECT-TYPE
			SYNTAX	INTEGER
			ACCESS	read-only
			STATUS	current
	DESCRIPTION ""
			::= { mbus1F 49 }

mbus1FVIF16		OBJECT-TYPE
			SYNTAX	INTEGER
			ACCESS	read-only
			STATUS	current
	DESCRIPTION ""
			::= { mbus1F 50 }

mbus1FValue16		OBJECT-TYPE
			SYNTAX	INTEGER
			ACCESS	read-only
			STATUS	current
	DESCRIPTION ""
			::= { mbus1F 51 }

mbus1FVIF17		OBJECT-TYPE
			SYNTAX	INTEGER
			ACCESS	read-only
			STATUS	current
	DESCRIPTION ""
			::= { mbus1F 52 }

mbus1FValue17		OBJECT-TYPE
			SYNTAX	INTEGER
			ACCESS	read-only
			STATUS	current
	DESCRIPTION ""
			::= { mbus1F 53 }

mbus1FVIF18		OBJECT-TYPE
			SYNTAX	INTEGER
			ACCESS	read-only
			STATUS	current
	DESCRIPTION ""
			::= { mbus1F 54 }

mbus1FValue18		OBJECT-TYPE
			SYNTAX	INTEGER
			ACCESS	read-only
			STATUS	current
	DESCRIPTION ""
			::= { mbus1F 55 }

mbus1FVIF19		OBJECT-TYPE
			SYNTAX	INTEGER
			ACCESS	read-only
			STATUS	current
	DESCRIPTION ""
			::= { mbus1F 56 }

mbus1FValue19		OBJECT-TYPE
			SYNTAX	INTEGER
			ACCESS	read-only
			STATUS	current
	DESCRIPTION ""
			::= { mbus1F 57 }

mbus1FVIF1A		OBJECT-TYPE
			SYNTAX	INTEGER
			ACCESS	read-only
			STATUS	current
	DESCRIPTION ""
			::= { mbus1F 58 }

mbus1FValue1A		OBJECT-TYPE
			SYNTAX	INTEGER
			ACCESS	read-only
			STATUS	current
	DESCRIPTION ""
			::= { mbus1F 59 }

mbus1FVIF1B		OBJECT-TYPE
			SYNTAX	INTEGER
			ACCESS	read-only
			STATUS	current
	DESCRIPTION ""
			::= { mbus1F 60 }

mbus1FValue1B		OBJECT-TYPE
			SYNTAX	INTEGER
			ACCESS	read-only
			STATUS	current
	DESCRIPTION ""
			::= { mbus1F 61 }

mbus1FVIF1C		OBJECT-TYPE
			SYNTAX	INTEGER
			ACCESS	read-only
			STATUS	current
	DESCRIPTION ""
			::= { mbus1F 62 }

mbus1FValue1C		OBJECT-TYPE
			SYNTAX	INTEGER
			ACCESS	read-only
			STATUS	current
	DESCRIPTION ""
			::= { mbus1F 63 }

mbus1FVIF1D		OBJECT-TYPE
			SYNTAX	INTEGER
			ACCESS	read-only
			STATUS	current
	DESCRIPTION ""
			::= { mbus1F 64 }

mbus1FValue1D		OBJECT-TYPE
			SYNTAX	INTEGER
			ACCESS	read-only
			STATUS	current
	DESCRIPTION ""
			::= { mbus1F 65 }

mbus1FVIF1E		OBJECT-TYPE
			SYNTAX	INTEGER
			ACCESS	read-only
			STATUS	current
	DESCRIPTION ""
			::= { mbus1F 66 }

mbus1FValue1E		OBJECT-TYPE
			SYNTAX	INTEGER
			ACCESS	read-only
			STATUS	current
	DESCRIPTION ""
			::= { mbus1F 67 }

mbus1FVIF1F		OBJECT-TYPE
			SYNTAX	INTEGER
			ACCESS	read-only
			STATUS	current
	DESCRIPTION ""
			::= { mbus1F 68 }

mbus1FValue1F		OBJECT-TYPE
			SYNTAX	INTEGER
			ACCESS	read-only
			STATUS	current
	DESCRIPTION ""
			::= { mbus1F 69 }

mbus1FVIF20		OBJECT-TYPE
			SYNTAX	INTEGER
			ACCESS	read-only
			STATUS	current
	DESCRIPTION ""
			::= { mbus1F 70 }

mbus1FValue20		OBJECT-TYPE
			SYNTAX	INTEGER
			ACCESS	read-only
			STATUS	current
	DESCRIPTION ""
			::= { mbus1F 71 }

mbus1FVIF21		OBJECT-TYPE
			SYNTAX	INTEGER
			ACCESS	read-only
			STATUS	current
	DESCRIPTION ""
			::= { mbus1F 72 }

mbus1FValue21		OBJECT-TYPE
			SYNTAX	INTEGER
			ACCESS	read-only
			STATUS	current
	DESCRIPTION ""
			::= { mbus1F 73 }

mbus1FVIF22		OBJECT-TYPE
			SYNTAX	INTEGER
			ACCESS	read-only
			STATUS	current
	DESCRIPTION ""
			::= { mbus1F 74 }

mbus1FValue22		OBJECT-TYPE
			SYNTAX	INTEGER
			ACCESS	read-only
			STATUS	current
	DESCRIPTION ""
			::= { mbus1F 75 }

mbus1FVIF23		OBJECT-TYPE
			SYNTAX	INTEGER
			ACCESS	read-only
			STATUS	current
	DESCRIPTION ""
			::= { mbus1F 76 }

mbus1FValue23		OBJECT-TYPE
			SYNTAX	INTEGER
			ACCESS	read-only
			STATUS	current
	DESCRIPTION ""
			::= { mbus1F 77 }

mbus1FVIF24		OBJECT-TYPE
			SYNTAX	INTEGER
			ACCESS	read-only
			STATUS	current
	DESCRIPTION ""
			::= { mbus1F 78 }

mbus1FValue24		OBJECT-TYPE
			SYNTAX	INTEGER
			ACCESS	read-only
			STATUS	current
	DESCRIPTION ""
			::= { mbus1F 79 }

mbus1FVIF25		OBJECT-TYPE
			SYNTAX	INTEGER
			ACCESS	read-only
			STATUS	current
	DESCRIPTION ""
			::= { mbus1F 80 }

mbus1FValue25		OBJECT-TYPE
			SYNTAX	INTEGER
			ACCESS	read-only
			STATUS	current
	DESCRIPTION ""
			::= { mbus1F 81 }

mbus1FVIF26		OBJECT-TYPE
			SYNTAX	INTEGER
			ACCESS	read-only
			STATUS	current
	DESCRIPTION ""
			::= { mbus1F 82 }

mbus1FValue26		OBJECT-TYPE
			SYNTAX	INTEGER
			ACCESS	read-only
			STATUS	current
	DESCRIPTION ""
			::= { mbus1F 83 }

mbus1FVIF27		OBJECT-TYPE
			SYNTAX	INTEGER
			ACCESS	read-only
			STATUS	current
	DESCRIPTION ""
			::= { mbus1F 84 }

mbus1FValue27		OBJECT-TYPE
			SYNTAX	INTEGER
			ACCESS	read-only
			STATUS	current
	DESCRIPTION ""
			::= { mbus1F 85 }

mbus1FVIF28		OBJECT-TYPE
			SYNTAX	INTEGER
			ACCESS	read-only
			STATUS	current
	DESCRIPTION ""
			::= { mbus1F 86 }

mbus1FValue28		OBJECT-TYPE
			SYNTAX	INTEGER
			ACCESS	read-only
			STATUS	current
	DESCRIPTION ""
			::= { mbus1F 87 }

mbus1FVIF29		OBJECT-TYPE
			SYNTAX	INTEGER
			ACCESS	read-only
			STATUS	current
	DESCRIPTION ""
			::= { mbus1F 88 }

mbus1FValue29		OBJECT-TYPE
			SYNTAX	INTEGER
			ACCESS	read-only
			STATUS	current
	DESCRIPTION ""
			::= { mbus1F 89 }

mbus1FVIF2A		OBJECT-TYPE
			SYNTAX	INTEGER
			ACCESS	read-only
			STATUS	current
	DESCRIPTION ""
			::= { mbus1F 90 }

mbus1FValue2A		OBJECT-TYPE
			SYNTAX	INTEGER
			ACCESS	read-only
			STATUS	current
	DESCRIPTION ""
			::= { mbus1F 91 }

mbus1FVIF2B		OBJECT-TYPE
			SYNTAX	INTEGER
			ACCESS	read-only
			STATUS	current
	DESCRIPTION ""
			::= { mbus1F 92 }

mbus1FValue2B		OBJECT-TYPE
			SYNTAX	INTEGER
			ACCESS	read-only
			STATUS	current
	DESCRIPTION ""
			::= { mbus1F 93 }

mbus1FVIF2C		OBJECT-TYPE
			SYNTAX	INTEGER
			ACCESS	read-only
			STATUS	current
	DESCRIPTION ""
			::= { mbus1F 94 }

mbus1FValue2C		OBJECT-TYPE
			SYNTAX	INTEGER
			ACCESS	read-only
			STATUS	current
	DESCRIPTION ""
			::= { mbus1F 95 }

mbus1FVIF2D		OBJECT-TYPE
			SYNTAX	INTEGER
			ACCESS	read-only
			STATUS	current
	DESCRIPTION ""
			::= { mbus1F 96 }

mbus1FValue2D		OBJECT-TYPE
			SYNTAX	INTEGER
			ACCESS	read-only
			STATUS	current
	DESCRIPTION ""
			::= { mbus1F 97 }

mbus1FVIF2E		OBJECT-TYPE
			SYNTAX	INTEGER
			ACCESS	read-only
			STATUS	current
	DESCRIPTION ""
			::= { mbus1F 98 }

mbus1FValue2E		OBJECT-TYPE
			SYNTAX	INTEGER
			ACCESS	read-only
			STATUS	current
	DESCRIPTION ""
			::= { mbus1F 99 }

mbus1FVIF2F		OBJECT-TYPE
			SYNTAX	INTEGER
			ACCESS	read-only
			STATUS	current
	DESCRIPTION ""
			::= { mbus1F 100 }

mbus1FValue2F		OBJECT-TYPE
			SYNTAX	INTEGER
			ACCESS	read-only
			STATUS	current
	DESCRIPTION ""
			::= { mbus1F 101 }

mbus20			OBJECT IDENTIFIER ::= { mbus 32 }

mbus20IdNumber		OBJECT-TYPE
			SYNTAX	Gauge
			ACCESS	read-only
			STATUS	current
	DESCRIPTION ""
			::= { mbus20 1 }

mbus20Manufacturer	OBJECT-TYPE
			SYNTAX	Gauge
			ACCESS	read-only
			STATUS	current
	DESCRIPTION ""
			::= { mbus20 2 }

mbus20Version		OBJECT-TYPE
			SYNTAX	Gauge
			ACCESS	read-only
			STATUS	current
	DESCRIPTION ""
			::= { mbus20 3 }

mbus20Medium		OBJECT-TYPE
			SYNTAX	Gauge
			ACCESS	read-only
			STATUS	current
	DESCRIPTION ""
			::= { mbus20 4 }

mbus20Status		OBJECT-TYPE
			SYNTAX	Gauge
			ACCESS	read-only
			STATUS	current
	DESCRIPTION ""
			::= { mbus20 5 }

mbus20VIF00		OBJECT-TYPE
			SYNTAX	INTEGER
			ACCESS	read-only
			STATUS	current
	DESCRIPTION ""
			::= { mbus20 6 }

mbus20Value00		OBJECT-TYPE
			SYNTAX	INTEGER
			ACCESS	read-only
			STATUS	current
	DESCRIPTION ""
			::= { mbus20 7 }

mbus20VIF01		OBJECT-TYPE
			SYNTAX	INTEGER
			ACCESS	read-only
			STATUS	current
	DESCRIPTION ""
			::= { mbus20 8 }

mbus20Value01		OBJECT-TYPE
			SYNTAX	INTEGER
			ACCESS	read-only
			STATUS	current
	DESCRIPTION ""
			::= { mbus20 9 }

mbus20VIF02		OBJECT-TYPE
			SYNTAX	INTEGER
			ACCESS	read-only
			STATUS	current
	DESCRIPTION ""
			::= { mbus20 10 }

mbus20Value02		OBJECT-TYPE
			SYNTAX	INTEGER
			ACCESS	read-only
			STATUS	current
	DESCRIPTION ""
			::= { mbus20 11 }

mbus20VIF03		OBJECT-TYPE
			SYNTAX	INTEGER
			ACCESS	read-only
			STATUS	current
	DESCRIPTION ""
			::= { mbus20 12 }

mbus20Value03		OBJECT-TYPE
			SYNTAX	INTEGER
			ACCESS	read-only
			STATUS	current
	DESCRIPTION ""
			::= { mbus20 13 }

mbus20VIF04		OBJECT-TYPE
			SYNTAX	INTEGER
			ACCESS	read-only
			STATUS	current
	DESCRIPTION ""
			::= { mbus20 14 }

mbus20Value04		OBJECT-TYPE
			SYNTAX	INTEGER
			ACCESS	read-only
			STATUS	current
	DESCRIPTION ""
			::= { mbus20 15 }

mbus20VIF05		OBJECT-TYPE
			SYNTAX	INTEGER
			ACCESS	read-only
			STATUS	current
	DESCRIPTION ""
			::= { mbus20 16 }

mbus20Value05		OBJECT-TYPE
			SYNTAX	INTEGER
			ACCESS	read-only
			STATUS	current
	DESCRIPTION ""
			::= { mbus20 17 }

mbus20VIF06		OBJECT-TYPE
			SYNTAX	INTEGER
			ACCESS	read-only
			STATUS	current
	DESCRIPTION ""
			::= { mbus20 18 }

mbus20Value06		OBJECT-TYPE
			SYNTAX	INTEGER
			ACCESS	read-only
			STATUS	current
	DESCRIPTION ""
			::= { mbus20 19 }

mbus20VIF07		OBJECT-TYPE
			SYNTAX	INTEGER
			ACCESS	read-only
			STATUS	current
	DESCRIPTION ""
			::= { mbus20 20 }

mbus20Value07		OBJECT-TYPE
			SYNTAX	INTEGER
			ACCESS	read-only
			STATUS	current
	DESCRIPTION ""
			::= { mbus20 21 }

mbus20VIF08		OBJECT-TYPE
			SYNTAX	INTEGER
			ACCESS	read-only
			STATUS	current
	DESCRIPTION ""
			::= { mbus20 22 }

mbus20Value08		OBJECT-TYPE
			SYNTAX	INTEGER
			ACCESS	read-only
			STATUS	current
	DESCRIPTION ""
			::= { mbus20 23 }

mbus20VIF09		OBJECT-TYPE
			SYNTAX	INTEGER
			ACCESS	read-only
			STATUS	current
	DESCRIPTION ""
			::= { mbus20 24 }

mbus20Value09		OBJECT-TYPE
			SYNTAX	INTEGER
			ACCESS	read-only
			STATUS	current
	DESCRIPTION ""
			::= { mbus20 25 }

mbus20VIF0A		OBJECT-TYPE
			SYNTAX	INTEGER
			ACCESS	read-only
			STATUS	current
	DESCRIPTION ""
			::= { mbus20 26 }

mbus20Value0A		OBJECT-TYPE
			SYNTAX	INTEGER
			ACCESS	read-only
			STATUS	current
	DESCRIPTION ""
			::= { mbus20 27 }

mbus20VIF0B		OBJECT-TYPE
			SYNTAX	INTEGER
			ACCESS	read-only
			STATUS	current
	DESCRIPTION ""
			::= { mbus20 28 }

mbus20Value0B		OBJECT-TYPE
			SYNTAX	INTEGER
			ACCESS	read-only
			STATUS	current
	DESCRIPTION ""
			::= { mbus20 29 }

mbus20VIF0C		OBJECT-TYPE
			SYNTAX	INTEGER
			ACCESS	read-only
			STATUS	current
	DESCRIPTION ""
			::= { mbus20 30 }

mbus20Value0C		OBJECT-TYPE
			SYNTAX	INTEGER
			ACCESS	read-only
			STATUS	current
	DESCRIPTION ""
			::= { mbus20 31 }

mbus20VIF0D		OBJECT-TYPE
			SYNTAX	INTEGER
			ACCESS	read-only
			STATUS	current
	DESCRIPTION ""
			::= { mbus20 32 }

mbus20Value0D		OBJECT-TYPE
			SYNTAX	INTEGER
			ACCESS	read-only
			STATUS	current
	DESCRIPTION ""
			::= { mbus20 33 }

mbus20VIF0E		OBJECT-TYPE
			SYNTAX	INTEGER
			ACCESS	read-only
			STATUS	current
	DESCRIPTION ""
			::= { mbus20 34 }

mbus20Value0E		OBJECT-TYPE
			SYNTAX	INTEGER
			ACCESS	read-only
			STATUS	current
	DESCRIPTION ""
			::= { mbus20 35 }

mbus20VIF0F		OBJECT-TYPE
			SYNTAX	INTEGER
			ACCESS	read-only
			STATUS	current
	DESCRIPTION ""
			::= { mbus20 36 }

mbus20Value0F		OBJECT-TYPE
			SYNTAX	INTEGER
			ACCESS	read-only
			STATUS	current
	DESCRIPTION ""
			::= { mbus20 37 }

mbus20VIF10		OBJECT-TYPE
			SYNTAX	INTEGER
			ACCESS	read-only
			STATUS	current
	DESCRIPTION ""
			::= { mbus20 38 }

mbus20Value10		OBJECT-TYPE
			SYNTAX	INTEGER
			ACCESS	read-only
			STATUS	current
	DESCRIPTION ""
			::= { mbus20 39 }

mbus20VIF11		OBJECT-TYPE
			SYNTAX	INTEGER
			ACCESS	read-only
			STATUS	current
	DESCRIPTION ""
			::= { mbus20 40 }

mbus20Value11		OBJECT-TYPE
			SYNTAX	INTEGER
			ACCESS	read-only
			STATUS	current
	DESCRIPTION ""
			::= { mbus20 41 }

mbus20VIF12		OBJECT-TYPE
			SYNTAX	INTEGER
			ACCESS	read-only
			STATUS	current
	DESCRIPTION ""
			::= { mbus20 42 }

mbus20Value12		OBJECT-TYPE
			SYNTAX	INTEGER
			ACCESS	read-only
			STATUS	current
	DESCRIPTION ""
			::= { mbus20 43 }

mbus20VIF13		OBJECT-TYPE
			SYNTAX	INTEGER
			ACCESS	read-only
			STATUS	current
	DESCRIPTION ""
			::= { mbus20 44 }

mbus20Value13		OBJECT-TYPE
			SYNTAX	INTEGER
			ACCESS	read-only
			STATUS	current
	DESCRIPTION ""
			::= { mbus20 45 }

mbus20VIF14		OBJECT-TYPE
			SYNTAX	INTEGER
			ACCESS	read-only
			STATUS	current
	DESCRIPTION ""
			::= { mbus20 46 }

mbus20Value14		OBJECT-TYPE
			SYNTAX	INTEGER
			ACCESS	read-only
			STATUS	current
	DESCRIPTION ""
			::= { mbus20 47 }

mbus20VIF15		OBJECT-TYPE
			SYNTAX	INTEGER
			ACCESS	read-only
			STATUS	current
	DESCRIPTION ""
			::= { mbus20 48 }

mbus20Value15		OBJECT-TYPE
			SYNTAX	INTEGER
			ACCESS	read-only
			STATUS	current
	DESCRIPTION ""
			::= { mbus20 49 }

mbus20VIF16		OBJECT-TYPE
			SYNTAX	INTEGER
			ACCESS	read-only
			STATUS	current
	DESCRIPTION ""
			::= { mbus20 50 }

mbus20Value16		OBJECT-TYPE
			SYNTAX	INTEGER
			ACCESS	read-only
			STATUS	current
	DESCRIPTION ""
			::= { mbus20 51 }

mbus20VIF17		OBJECT-TYPE
			SYNTAX	INTEGER
			ACCESS	read-only
			STATUS	current
	DESCRIPTION ""
			::= { mbus20 52 }

mbus20Value17		OBJECT-TYPE
			SYNTAX	INTEGER
			ACCESS	read-only
			STATUS	current
	DESCRIPTION ""
			::= { mbus20 53 }

mbus20VIF18		OBJECT-TYPE
			SYNTAX	INTEGER
			ACCESS	read-only
			STATUS	current
	DESCRIPTION ""
			::= { mbus20 54 }

mbus20Value18		OBJECT-TYPE
			SYNTAX	INTEGER
			ACCESS	read-only
			STATUS	current
	DESCRIPTION ""
			::= { mbus20 55 }

mbus20VIF19		OBJECT-TYPE
			SYNTAX	INTEGER
			ACCESS	read-only
			STATUS	current
	DESCRIPTION ""
			::= { mbus20 56 }

mbus20Value19		OBJECT-TYPE
			SYNTAX	INTEGER
			ACCESS	read-only
			STATUS	current
	DESCRIPTION ""
			::= { mbus20 57 }

mbus20VIF1A		OBJECT-TYPE
			SYNTAX	INTEGER
			ACCESS	read-only
			STATUS	current
	DESCRIPTION ""
			::= { mbus20 58 }

mbus20Value1A		OBJECT-TYPE
			SYNTAX	INTEGER
			ACCESS	read-only
			STATUS	current
	DESCRIPTION ""
			::= { mbus20 59 }

mbus20VIF1B		OBJECT-TYPE
			SYNTAX	INTEGER
			ACCESS	read-only
			STATUS	current
	DESCRIPTION ""
			::= { mbus20 60 }

mbus20Value1B		OBJECT-TYPE
			SYNTAX	INTEGER
			ACCESS	read-only
			STATUS	current
	DESCRIPTION ""
			::= { mbus20 61 }

mbus20VIF1C		OBJECT-TYPE
			SYNTAX	INTEGER
			ACCESS	read-only
			STATUS	current
	DESCRIPTION ""
			::= { mbus20 62 }

mbus20Value1C		OBJECT-TYPE
			SYNTAX	INTEGER
			ACCESS	read-only
			STATUS	current
	DESCRIPTION ""
			::= { mbus20 63 }

mbus20VIF1D		OBJECT-TYPE
			SYNTAX	INTEGER
			ACCESS	read-only
			STATUS	current
	DESCRIPTION ""
			::= { mbus20 64 }

mbus20Value1D		OBJECT-TYPE
			SYNTAX	INTEGER
			ACCESS	read-only
			STATUS	current
	DESCRIPTION ""
			::= { mbus20 65 }

mbus20VIF1E		OBJECT-TYPE
			SYNTAX	INTEGER
			ACCESS	read-only
			STATUS	current
	DESCRIPTION ""
			::= { mbus20 66 }

mbus20Value1E		OBJECT-TYPE
			SYNTAX	INTEGER
			ACCESS	read-only
			STATUS	current
	DESCRIPTION ""
			::= { mbus20 67 }

mbus20VIF1F		OBJECT-TYPE
			SYNTAX	INTEGER
			ACCESS	read-only
			STATUS	current
	DESCRIPTION ""
			::= { mbus20 68 }

mbus20Value1F		OBJECT-TYPE
			SYNTAX	INTEGER
			ACCESS	read-only
			STATUS	current
	DESCRIPTION ""
			::= { mbus20 69 }

mbus20VIF20		OBJECT-TYPE
			SYNTAX	INTEGER
			ACCESS	read-only
			STATUS	current
	DESCRIPTION ""
			::= { mbus20 70 }

mbus20Value20		OBJECT-TYPE
			SYNTAX	INTEGER
			ACCESS	read-only
			STATUS	current
	DESCRIPTION ""
			::= { mbus20 71 }

mbus20VIF21		OBJECT-TYPE
			SYNTAX	INTEGER
			ACCESS	read-only
			STATUS	current
	DESCRIPTION ""
			::= { mbus20 72 }

mbus20Value21		OBJECT-TYPE
			SYNTAX	INTEGER
			ACCESS	read-only
			STATUS	current
	DESCRIPTION ""
			::= { mbus20 73 }

mbus20VIF22		OBJECT-TYPE
			SYNTAX	INTEGER
			ACCESS	read-only
			STATUS	current
	DESCRIPTION ""
			::= { mbus20 74 }

mbus20Value22		OBJECT-TYPE
			SYNTAX	INTEGER
			ACCESS	read-only
			STATUS	current
	DESCRIPTION ""
			::= { mbus20 75 }

mbus20VIF23		OBJECT-TYPE
			SYNTAX	INTEGER
			ACCESS	read-only
			STATUS	current
	DESCRIPTION ""
			::= { mbus20 76 }

mbus20Value23		OBJECT-TYPE
			SYNTAX	INTEGER
			ACCESS	read-only
			STATUS	current
	DESCRIPTION ""
			::= { mbus20 77 }

mbus20VIF24		OBJECT-TYPE
			SYNTAX	INTEGER
			ACCESS	read-only
			STATUS	current
	DESCRIPTION ""
			::= { mbus20 78 }

mbus20Value24		OBJECT-TYPE
			SYNTAX	INTEGER
			ACCESS	read-only
			STATUS	current
	DESCRIPTION ""
			::= { mbus20 79 }

mbus20VIF25		OBJECT-TYPE
			SYNTAX	INTEGER
			ACCESS	read-only
			STATUS	current
	DESCRIPTION ""
			::= { mbus20 80 }

mbus20Value25		OBJECT-TYPE
			SYNTAX	INTEGER
			ACCESS	read-only
			STATUS	current
	DESCRIPTION ""
			::= { mbus20 81 }

mbus20VIF26		OBJECT-TYPE
			SYNTAX	INTEGER
			ACCESS	read-only
			STATUS	current
	DESCRIPTION ""
			::= { mbus20 82 }

mbus20Value26		OBJECT-TYPE
			SYNTAX	INTEGER
			ACCESS	read-only
			STATUS	current
	DESCRIPTION ""
			::= { mbus20 83 }

mbus20VIF27		OBJECT-TYPE
			SYNTAX	INTEGER
			ACCESS	read-only
			STATUS	current
	DESCRIPTION ""
			::= { mbus20 84 }

mbus20Value27		OBJECT-TYPE
			SYNTAX	INTEGER
			ACCESS	read-only
			STATUS	current
	DESCRIPTION ""
			::= { mbus20 85 }

mbus20VIF28		OBJECT-TYPE
			SYNTAX	INTEGER
			ACCESS	read-only
			STATUS	current
	DESCRIPTION ""
			::= { mbus20 86 }

mbus20Value28		OBJECT-TYPE
			SYNTAX	INTEGER
			ACCESS	read-only
			STATUS	current
	DESCRIPTION ""
			::= { mbus20 87 }

mbus20VIF29		OBJECT-TYPE
			SYNTAX	INTEGER
			ACCESS	read-only
			STATUS	current
	DESCRIPTION ""
			::= { mbus20 88 }

mbus20Value29		OBJECT-TYPE
			SYNTAX	INTEGER
			ACCESS	read-only
			STATUS	current
	DESCRIPTION ""
			::= { mbus20 89 }

mbus20VIF2A		OBJECT-TYPE
			SYNTAX	INTEGER
			ACCESS	read-only
			STATUS	current
	DESCRIPTION ""
			::= { mbus20 90 }

mbus20Value2A		OBJECT-TYPE
			SYNTAX	INTEGER
			ACCESS	read-only
			STATUS	current
	DESCRIPTION ""
			::= { mbus20 91 }

mbus20VIF2B		OBJECT-TYPE
			SYNTAX	INTEGER
			ACCESS	read-only
			STATUS	current
	DESCRIPTION ""
			::= { mbus20 92 }

mbus20Value2B		OBJECT-TYPE
			SYNTAX	INTEGER
			ACCESS	read-only
			STATUS	current
	DESCRIPTION ""
			::= { mbus20 93 }

mbus20VIF2C		OBJECT-TYPE
			SYNTAX	INTEGER
			ACCESS	read-only
			STATUS	current
	DESCRIPTION ""
			::= { mbus20 94 }

mbus20Value2C		OBJECT-TYPE
			SYNTAX	INTEGER
			ACCESS	read-only
			STATUS	current
	DESCRIPTION ""
			::= { mbus20 95 }

mbus20VIF2D		OBJECT-TYPE
			SYNTAX	INTEGER
			ACCESS	read-only
			STATUS	current
	DESCRIPTION ""
			::= { mbus20 96 }

mbus20Value2D		OBJECT-TYPE
			SYNTAX	INTEGER
			ACCESS	read-only
			STATUS	current
	DESCRIPTION ""
			::= { mbus20 97 }

mbus20VIF2E		OBJECT-TYPE
			SYNTAX	INTEGER
			ACCESS	read-only
			STATUS	current
	DESCRIPTION ""
			::= { mbus20 98 }

mbus20Value2E		OBJECT-TYPE
			SYNTAX	INTEGER
			ACCESS	read-only
			STATUS	current
	DESCRIPTION ""
			::= { mbus20 99 }

mbus20VIF2F		OBJECT-TYPE
			SYNTAX	INTEGER
			ACCESS	read-only
			STATUS	current
	DESCRIPTION ""
			::= { mbus20 100 }

mbus20Value2F		OBJECT-TYPE
			SYNTAX	INTEGER
			ACCESS	read-only
			STATUS	current
	DESCRIPTION ""
			::= { mbus20 101 }

mbus21			OBJECT IDENTIFIER ::= { mbus 33 }

mbus21IdNumber		OBJECT-TYPE
			SYNTAX	Gauge
			ACCESS	read-only
			STATUS	current
	DESCRIPTION ""
			::= { mbus21 1 }

mbus21Manufacturer	OBJECT-TYPE
			SYNTAX	Gauge
			ACCESS	read-only
			STATUS	current
	DESCRIPTION ""
			::= { mbus21 2 }

mbus21Version		OBJECT-TYPE
			SYNTAX	Gauge
			ACCESS	read-only
			STATUS	current
	DESCRIPTION ""
			::= { mbus21 3 }

mbus21Medium		OBJECT-TYPE
			SYNTAX	Gauge
			ACCESS	read-only
			STATUS	current
	DESCRIPTION ""
			::= { mbus21 4 }

mbus21Status		OBJECT-TYPE
			SYNTAX	Gauge
			ACCESS	read-only
			STATUS	current
	DESCRIPTION ""
			::= { mbus21 5 }

mbus21VIF00		OBJECT-TYPE
			SYNTAX	INTEGER
			ACCESS	read-only
			STATUS	current
	DESCRIPTION ""
			::= { mbus21 6 }

mbus21Value00		OBJECT-TYPE
			SYNTAX	INTEGER
			ACCESS	read-only
			STATUS	current
	DESCRIPTION ""
			::= { mbus21 7 }

mbus21VIF01		OBJECT-TYPE
			SYNTAX	INTEGER
			ACCESS	read-only
			STATUS	current
	DESCRIPTION ""
			::= { mbus21 8 }

mbus21Value01		OBJECT-TYPE
			SYNTAX	INTEGER
			ACCESS	read-only
			STATUS	current
	DESCRIPTION ""
			::= { mbus21 9 }

mbus21VIF02		OBJECT-TYPE
			SYNTAX	INTEGER
			ACCESS	read-only
			STATUS	current
	DESCRIPTION ""
			::= { mbus21 10 }

mbus21Value02		OBJECT-TYPE
			SYNTAX	INTEGER
			ACCESS	read-only
			STATUS	current
	DESCRIPTION ""
			::= { mbus21 11 }

mbus21VIF03		OBJECT-TYPE
			SYNTAX	INTEGER
			ACCESS	read-only
			STATUS	current
	DESCRIPTION ""
			::= { mbus21 12 }

mbus21Value03		OBJECT-TYPE
			SYNTAX	INTEGER
			ACCESS	read-only
			STATUS	current
	DESCRIPTION ""
			::= { mbus21 13 }

mbus21VIF04		OBJECT-TYPE
			SYNTAX	INTEGER
			ACCESS	read-only
			STATUS	current
	DESCRIPTION ""
			::= { mbus21 14 }

mbus21Value04		OBJECT-TYPE
			SYNTAX	INTEGER
			ACCESS	read-only
			STATUS	current
	DESCRIPTION ""
			::= { mbus21 15 }

mbus21VIF05		OBJECT-TYPE
			SYNTAX	INTEGER
			ACCESS	read-only
			STATUS	current
	DESCRIPTION ""
			::= { mbus21 16 }

mbus21Value05		OBJECT-TYPE
			SYNTAX	INTEGER
			ACCESS	read-only
			STATUS	current
	DESCRIPTION ""
			::= { mbus21 17 }

mbus21VIF06		OBJECT-TYPE
			SYNTAX	INTEGER
			ACCESS	read-only
			STATUS	current
	DESCRIPTION ""
			::= { mbus21 18 }

mbus21Value06		OBJECT-TYPE
			SYNTAX	INTEGER
			ACCESS	read-only
			STATUS	current
	DESCRIPTION ""
			::= { mbus21 19 }

mbus21VIF07		OBJECT-TYPE
			SYNTAX	INTEGER
			ACCESS	read-only
			STATUS	current
	DESCRIPTION ""
			::= { mbus21 20 }

mbus21Value07		OBJECT-TYPE
			SYNTAX	INTEGER
			ACCESS	read-only
			STATUS	current
	DESCRIPTION ""
			::= { mbus21 21 }

mbus21VIF08		OBJECT-TYPE
			SYNTAX	INTEGER
			ACCESS	read-only
			STATUS	current
	DESCRIPTION ""
			::= { mbus21 22 }

mbus21Value08		OBJECT-TYPE
			SYNTAX	INTEGER
			ACCESS	read-only
			STATUS	current
	DESCRIPTION ""
			::= { mbus21 23 }

mbus21VIF09		OBJECT-TYPE
			SYNTAX	INTEGER
			ACCESS	read-only
			STATUS	current
	DESCRIPTION ""
			::= { mbus21 24 }

mbus21Value09		OBJECT-TYPE
			SYNTAX	INTEGER
			ACCESS	read-only
			STATUS	current
	DESCRIPTION ""
			::= { mbus21 25 }

mbus21VIF0A		OBJECT-TYPE
			SYNTAX	INTEGER
			ACCESS	read-only
			STATUS	current
	DESCRIPTION ""
			::= { mbus21 26 }

mbus21Value0A		OBJECT-TYPE
			SYNTAX	INTEGER
			ACCESS	read-only
			STATUS	current
	DESCRIPTION ""
			::= { mbus21 27 }

mbus21VIF0B		OBJECT-TYPE
			SYNTAX	INTEGER
			ACCESS	read-only
			STATUS	current
	DESCRIPTION ""
			::= { mbus21 28 }

mbus21Value0B		OBJECT-TYPE
			SYNTAX	INTEGER
			ACCESS	read-only
			STATUS	current
	DESCRIPTION ""
			::= { mbus21 29 }

mbus21VIF0C		OBJECT-TYPE
			SYNTAX	INTEGER
			ACCESS	read-only
			STATUS	current
	DESCRIPTION ""
			::= { mbus21 30 }

mbus21Value0C		OBJECT-TYPE
			SYNTAX	INTEGER
			ACCESS	read-only
			STATUS	current
	DESCRIPTION ""
			::= { mbus21 31 }

mbus21VIF0D		OBJECT-TYPE
			SYNTAX	INTEGER
			ACCESS	read-only
			STATUS	current
	DESCRIPTION ""
			::= { mbus21 32 }

mbus21Value0D		OBJECT-TYPE
			SYNTAX	INTEGER
			ACCESS	read-only
			STATUS	current
	DESCRIPTION ""
			::= { mbus21 33 }

mbus21VIF0E		OBJECT-TYPE
			SYNTAX	INTEGER
			ACCESS	read-only
			STATUS	current
	DESCRIPTION ""
			::= { mbus21 34 }

mbus21Value0E		OBJECT-TYPE
			SYNTAX	INTEGER
			ACCESS	read-only
			STATUS	current
	DESCRIPTION ""
			::= { mbus21 35 }

mbus21VIF0F		OBJECT-TYPE
			SYNTAX	INTEGER
			ACCESS	read-only
			STATUS	current
	DESCRIPTION ""
			::= { mbus21 36 }

mbus21Value0F		OBJECT-TYPE
			SYNTAX	INTEGER
			ACCESS	read-only
			STATUS	current
	DESCRIPTION ""
			::= { mbus21 37 }

mbus21VIF10		OBJECT-TYPE
			SYNTAX	INTEGER
			ACCESS	read-only
			STATUS	current
	DESCRIPTION ""
			::= { mbus21 38 }

mbus21Value10		OBJECT-TYPE
			SYNTAX	INTEGER
			ACCESS	read-only
			STATUS	current
	DESCRIPTION ""
			::= { mbus21 39 }

mbus21VIF11		OBJECT-TYPE
			SYNTAX	INTEGER
			ACCESS	read-only
			STATUS	current
	DESCRIPTION ""
			::= { mbus21 40 }

mbus21Value11		OBJECT-TYPE
			SYNTAX	INTEGER
			ACCESS	read-only
			STATUS	current
	DESCRIPTION ""
			::= { mbus21 41 }

mbus21VIF12		OBJECT-TYPE
			SYNTAX	INTEGER
			ACCESS	read-only
			STATUS	current
	DESCRIPTION ""
			::= { mbus21 42 }

mbus21Value12		OBJECT-TYPE
			SYNTAX	INTEGER
			ACCESS	read-only
			STATUS	current
	DESCRIPTION ""
			::= { mbus21 43 }

mbus21VIF13		OBJECT-TYPE
			SYNTAX	INTEGER
			ACCESS	read-only
			STATUS	current
	DESCRIPTION ""
			::= { mbus21 44 }

mbus21Value13		OBJECT-TYPE
			SYNTAX	INTEGER
			ACCESS	read-only
			STATUS	current
	DESCRIPTION ""
			::= { mbus21 45 }

mbus21VIF14		OBJECT-TYPE
			SYNTAX	INTEGER
			ACCESS	read-only
			STATUS	current
	DESCRIPTION ""
			::= { mbus21 46 }

mbus21Value14		OBJECT-TYPE
			SYNTAX	INTEGER
			ACCESS	read-only
			STATUS	current
	DESCRIPTION ""
			::= { mbus21 47 }

mbus21VIF15		OBJECT-TYPE
			SYNTAX	INTEGER
			ACCESS	read-only
			STATUS	current
	DESCRIPTION ""
			::= { mbus21 48 }

mbus21Value15		OBJECT-TYPE
			SYNTAX	INTEGER
			ACCESS	read-only
			STATUS	current
	DESCRIPTION ""
			::= { mbus21 49 }

mbus21VIF16		OBJECT-TYPE
			SYNTAX	INTEGER
			ACCESS	read-only
			STATUS	current
	DESCRIPTION ""
			::= { mbus21 50 }

mbus21Value16		OBJECT-TYPE
			SYNTAX	INTEGER
			ACCESS	read-only
			STATUS	current
	DESCRIPTION ""
			::= { mbus21 51 }

mbus21VIF17		OBJECT-TYPE
			SYNTAX	INTEGER
			ACCESS	read-only
			STATUS	current
	DESCRIPTION ""
			::= { mbus21 52 }

mbus21Value17		OBJECT-TYPE
			SYNTAX	INTEGER
			ACCESS	read-only
			STATUS	current
	DESCRIPTION ""
			::= { mbus21 53 }

mbus21VIF18		OBJECT-TYPE
			SYNTAX	INTEGER
			ACCESS	read-only
			STATUS	current
	DESCRIPTION ""
			::= { mbus21 54 }

mbus21Value18		OBJECT-TYPE
			SYNTAX	INTEGER
			ACCESS	read-only
			STATUS	current
	DESCRIPTION ""
			::= { mbus21 55 }

mbus21VIF19		OBJECT-TYPE
			SYNTAX	INTEGER
			ACCESS	read-only
			STATUS	current
	DESCRIPTION ""
			::= { mbus21 56 }

mbus21Value19		OBJECT-TYPE
			SYNTAX	INTEGER
			ACCESS	read-only
			STATUS	current
	DESCRIPTION ""
			::= { mbus21 57 }

mbus21VIF1A		OBJECT-TYPE
			SYNTAX	INTEGER
			ACCESS	read-only
			STATUS	current
	DESCRIPTION ""
			::= { mbus21 58 }

mbus21Value1A		OBJECT-TYPE
			SYNTAX	INTEGER
			ACCESS	read-only
			STATUS	current
	DESCRIPTION ""
			::= { mbus21 59 }

mbus21VIF1B		OBJECT-TYPE
			SYNTAX	INTEGER
			ACCESS	read-only
			STATUS	current
	DESCRIPTION ""
			::= { mbus21 60 }

mbus21Value1B		OBJECT-TYPE
			SYNTAX	INTEGER
			ACCESS	read-only
			STATUS	current
	DESCRIPTION ""
			::= { mbus21 61 }

mbus21VIF1C		OBJECT-TYPE
			SYNTAX	INTEGER
			ACCESS	read-only
			STATUS	current
	DESCRIPTION ""
			::= { mbus21 62 }

mbus21Value1C		OBJECT-TYPE
			SYNTAX	INTEGER
			ACCESS	read-only
			STATUS	current
	DESCRIPTION ""
			::= { mbus21 63 }

mbus21VIF1D		OBJECT-TYPE
			SYNTAX	INTEGER
			ACCESS	read-only
			STATUS	current
	DESCRIPTION ""
			::= { mbus21 64 }

mbus21Value1D		OBJECT-TYPE
			SYNTAX	INTEGER
			ACCESS	read-only
			STATUS	current
	DESCRIPTION ""
			::= { mbus21 65 }

mbus21VIF1E		OBJECT-TYPE
			SYNTAX	INTEGER
			ACCESS	read-only
			STATUS	current
	DESCRIPTION ""
			::= { mbus21 66 }

mbus21Value1E		OBJECT-TYPE
			SYNTAX	INTEGER
			ACCESS	read-only
			STATUS	current
	DESCRIPTION ""
			::= { mbus21 67 }

mbus21VIF1F		OBJECT-TYPE
			SYNTAX	INTEGER
			ACCESS	read-only
			STATUS	current
	DESCRIPTION ""
			::= { mbus21 68 }

mbus21Value1F		OBJECT-TYPE
			SYNTAX	INTEGER
			ACCESS	read-only
			STATUS	current
	DESCRIPTION ""
			::= { mbus21 69 }

mbus21VIF20		OBJECT-TYPE
			SYNTAX	INTEGER
			ACCESS	read-only
			STATUS	current
	DESCRIPTION ""
			::= { mbus21 70 }

mbus21Value20		OBJECT-TYPE
			SYNTAX	INTEGER
			ACCESS	read-only
			STATUS	current
	DESCRIPTION ""
			::= { mbus21 71 }

mbus21VIF21		OBJECT-TYPE
			SYNTAX	INTEGER
			ACCESS	read-only
			STATUS	current
	DESCRIPTION ""
			::= { mbus21 72 }

mbus21Value21		OBJECT-TYPE
			SYNTAX	INTEGER
			ACCESS	read-only
			STATUS	current
	DESCRIPTION ""
			::= { mbus21 73 }

mbus21VIF22		OBJECT-TYPE
			SYNTAX	INTEGER
			ACCESS	read-only
			STATUS	current
	DESCRIPTION ""
			::= { mbus21 74 }

mbus21Value22		OBJECT-TYPE
			SYNTAX	INTEGER
			ACCESS	read-only
			STATUS	current
	DESCRIPTION ""
			::= { mbus21 75 }

mbus21VIF23		OBJECT-TYPE
			SYNTAX	INTEGER
			ACCESS	read-only
			STATUS	current
	DESCRIPTION ""
			::= { mbus21 76 }

mbus21Value23		OBJECT-TYPE
			SYNTAX	INTEGER
			ACCESS	read-only
			STATUS	current
	DESCRIPTION ""
			::= { mbus21 77 }

mbus21VIF24		OBJECT-TYPE
			SYNTAX	INTEGER
			ACCESS	read-only
			STATUS	current
	DESCRIPTION ""
			::= { mbus21 78 }

mbus21Value24		OBJECT-TYPE
			SYNTAX	INTEGER
			ACCESS	read-only
			STATUS	current
	DESCRIPTION ""
			::= { mbus21 79 }

mbus21VIF25		OBJECT-TYPE
			SYNTAX	INTEGER
			ACCESS	read-only
			STATUS	current
	DESCRIPTION ""
			::= { mbus21 80 }

mbus21Value25		OBJECT-TYPE
			SYNTAX	INTEGER
			ACCESS	read-only
			STATUS	current
	DESCRIPTION ""
			::= { mbus21 81 }

mbus21VIF26		OBJECT-TYPE
			SYNTAX	INTEGER
			ACCESS	read-only
			STATUS	current
	DESCRIPTION ""
			::= { mbus21 82 }

mbus21Value26		OBJECT-TYPE
			SYNTAX	INTEGER
			ACCESS	read-only
			STATUS	current
	DESCRIPTION ""
			::= { mbus21 83 }

mbus21VIF27		OBJECT-TYPE
			SYNTAX	INTEGER
			ACCESS	read-only
			STATUS	current
	DESCRIPTION ""
			::= { mbus21 84 }

mbus21Value27		OBJECT-TYPE
			SYNTAX	INTEGER
			ACCESS	read-only
			STATUS	current
	DESCRIPTION ""
			::= { mbus21 85 }

mbus21VIF28		OBJECT-TYPE
			SYNTAX	INTEGER
			ACCESS	read-only
			STATUS	current
	DESCRIPTION ""
			::= { mbus21 86 }

mbus21Value28		OBJECT-TYPE
			SYNTAX	INTEGER
			ACCESS	read-only
			STATUS	current
	DESCRIPTION ""
			::= { mbus21 87 }

mbus21VIF29		OBJECT-TYPE
			SYNTAX	INTEGER
			ACCESS	read-only
			STATUS	current
	DESCRIPTION ""
			::= { mbus21 88 }

mbus21Value29		OBJECT-TYPE
			SYNTAX	INTEGER
			ACCESS	read-only
			STATUS	current
	DESCRIPTION ""
			::= { mbus21 89 }

mbus21VIF2A		OBJECT-TYPE
			SYNTAX	INTEGER
			ACCESS	read-only
			STATUS	current
	DESCRIPTION ""
			::= { mbus21 90 }

mbus21Value2A		OBJECT-TYPE
			SYNTAX	INTEGER
			ACCESS	read-only
			STATUS	current
	DESCRIPTION ""
			::= { mbus21 91 }

mbus21VIF2B		OBJECT-TYPE
			SYNTAX	INTEGER
			ACCESS	read-only
			STATUS	current
	DESCRIPTION ""
			::= { mbus21 92 }

mbus21Value2B		OBJECT-TYPE
			SYNTAX	INTEGER
			ACCESS	read-only
			STATUS	current
	DESCRIPTION ""
			::= { mbus21 93 }

mbus21VIF2C		OBJECT-TYPE
			SYNTAX	INTEGER
			ACCESS	read-only
			STATUS	current
	DESCRIPTION ""
			::= { mbus21 94 }

mbus21Value2C		OBJECT-TYPE
			SYNTAX	INTEGER
			ACCESS	read-only
			STATUS	current
	DESCRIPTION ""
			::= { mbus21 95 }

mbus21VIF2D		OBJECT-TYPE
			SYNTAX	INTEGER
			ACCESS	read-only
			STATUS	current
	DESCRIPTION ""
			::= { mbus21 96 }

mbus21Value2D		OBJECT-TYPE
			SYNTAX	INTEGER
			ACCESS	read-only
			STATUS	current
	DESCRIPTION ""
			::= { mbus21 97 }

mbus21VIF2E		OBJECT-TYPE
			SYNTAX	INTEGER
			ACCESS	read-only
			STATUS	current
	DESCRIPTION ""
			::= { mbus21 98 }

mbus21Value2E		OBJECT-TYPE
			SYNTAX	INTEGER
			ACCESS	read-only
			STATUS	current
	DESCRIPTION ""
			::= { mbus21 99 }

mbus21VIF2F		OBJECT-TYPE
			SYNTAX	INTEGER
			ACCESS	read-only
			STATUS	current
	DESCRIPTION ""
			::= { mbus21 100 }

mbus21Value2F		OBJECT-TYPE
			SYNTAX	INTEGER
			ACCESS	read-only
			STATUS	current
	DESCRIPTION ""
			::= { mbus21 101 }

mbus22			OBJECT IDENTIFIER ::= { mbus 34 }

mbus22IdNumber		OBJECT-TYPE
			SYNTAX	Gauge
			ACCESS	read-only
			STATUS	current
	DESCRIPTION ""
			::= { mbus22 1 }

mbus22Manufacturer	OBJECT-TYPE
			SYNTAX	Gauge
			ACCESS	read-only
			STATUS	current
	DESCRIPTION ""
			::= { mbus22 2 }

mbus22Version		OBJECT-TYPE
			SYNTAX	Gauge
			ACCESS	read-only
			STATUS	current
	DESCRIPTION ""
			::= { mbus22 3 }

mbus22Medium		OBJECT-TYPE
			SYNTAX	Gauge
			ACCESS	read-only
			STATUS	current
	DESCRIPTION ""
			::= { mbus22 4 }

mbus22Status		OBJECT-TYPE
			SYNTAX	Gauge
			ACCESS	read-only
			STATUS	current
	DESCRIPTION ""
			::= { mbus22 5 }

mbus22VIF00		OBJECT-TYPE
			SYNTAX	INTEGER
			ACCESS	read-only
			STATUS	current
	DESCRIPTION ""
			::= { mbus22 6 }

mbus22Value00		OBJECT-TYPE
			SYNTAX	INTEGER
			ACCESS	read-only
			STATUS	current
	DESCRIPTION ""
			::= { mbus22 7 }

mbus22VIF01		OBJECT-TYPE
			SYNTAX	INTEGER
			ACCESS	read-only
			STATUS	current
	DESCRIPTION ""
			::= { mbus22 8 }

mbus22Value01		OBJECT-TYPE
			SYNTAX	INTEGER
			ACCESS	read-only
			STATUS	current
	DESCRIPTION ""
			::= { mbus22 9 }

mbus22VIF02		OBJECT-TYPE
			SYNTAX	INTEGER
			ACCESS	read-only
			STATUS	current
	DESCRIPTION ""
			::= { mbus22 10 }

mbus22Value02		OBJECT-TYPE
			SYNTAX	INTEGER
			ACCESS	read-only
			STATUS	current
	DESCRIPTION ""
			::= { mbus22 11 }

mbus22VIF03		OBJECT-TYPE
			SYNTAX	INTEGER
			ACCESS	read-only
			STATUS	current
	DESCRIPTION ""
			::= { mbus22 12 }

mbus22Value03		OBJECT-TYPE
			SYNTAX	INTEGER
			ACCESS	read-only
			STATUS	current
	DESCRIPTION ""
			::= { mbus22 13 }

mbus22VIF04		OBJECT-TYPE
			SYNTAX	INTEGER
			ACCESS	read-only
			STATUS	current
	DESCRIPTION ""
			::= { mbus22 14 }

mbus22Value04		OBJECT-TYPE
			SYNTAX	INTEGER
			ACCESS	read-only
			STATUS	current
	DESCRIPTION ""
			::= { mbus22 15 }

mbus22VIF05		OBJECT-TYPE
			SYNTAX	INTEGER
			ACCESS	read-only
			STATUS	current
	DESCRIPTION ""
			::= { mbus22 16 }

mbus22Value05		OBJECT-TYPE
			SYNTAX	INTEGER
			ACCESS	read-only
			STATUS	current
	DESCRIPTION ""
			::= { mbus22 17 }

mbus22VIF06		OBJECT-TYPE
			SYNTAX	INTEGER
			ACCESS	read-only
			STATUS	current
	DESCRIPTION ""
			::= { mbus22 18 }

mbus22Value06		OBJECT-TYPE
			SYNTAX	INTEGER
			ACCESS	read-only
			STATUS	current
	DESCRIPTION ""
			::= { mbus22 19 }

mbus22VIF07		OBJECT-TYPE
			SYNTAX	INTEGER
			ACCESS	read-only
			STATUS	current
	DESCRIPTION ""
			::= { mbus22 20 }

mbus22Value07		OBJECT-TYPE
			SYNTAX	INTEGER
			ACCESS	read-only
			STATUS	current
	DESCRIPTION ""
			::= { mbus22 21 }

mbus22VIF08		OBJECT-TYPE
			SYNTAX	INTEGER
			ACCESS	read-only
			STATUS	current
	DESCRIPTION ""
			::= { mbus22 22 }

mbus22Value08		OBJECT-TYPE
			SYNTAX	INTEGER
			ACCESS	read-only
			STATUS	current
	DESCRIPTION ""
			::= { mbus22 23 }

mbus22VIF09		OBJECT-TYPE
			SYNTAX	INTEGER
			ACCESS	read-only
			STATUS	current
	DESCRIPTION ""
			::= { mbus22 24 }

mbus22Value09		OBJECT-TYPE
			SYNTAX	INTEGER
			ACCESS	read-only
			STATUS	current
	DESCRIPTION ""
			::= { mbus22 25 }

mbus22VIF0A		OBJECT-TYPE
			SYNTAX	INTEGER
			ACCESS	read-only
			STATUS	current
	DESCRIPTION ""
			::= { mbus22 26 }

mbus22Value0A		OBJECT-TYPE
			SYNTAX	INTEGER
			ACCESS	read-only
			STATUS	current
	DESCRIPTION ""
			::= { mbus22 27 }

mbus22VIF0B		OBJECT-TYPE
			SYNTAX	INTEGER
			ACCESS	read-only
			STATUS	current
	DESCRIPTION ""
			::= { mbus22 28 }

mbus22Value0B		OBJECT-TYPE
			SYNTAX	INTEGER
			ACCESS	read-only
			STATUS	current
	DESCRIPTION ""
			::= { mbus22 29 }

mbus22VIF0C		OBJECT-TYPE
			SYNTAX	INTEGER
			ACCESS	read-only
			STATUS	current
	DESCRIPTION ""
			::= { mbus22 30 }

mbus22Value0C		OBJECT-TYPE
			SYNTAX	INTEGER
			ACCESS	read-only
			STATUS	current
	DESCRIPTION ""
			::= { mbus22 31 }

mbus22VIF0D		OBJECT-TYPE
			SYNTAX	INTEGER
			ACCESS	read-only
			STATUS	current
	DESCRIPTION ""
			::= { mbus22 32 }

mbus22Value0D		OBJECT-TYPE
			SYNTAX	INTEGER
			ACCESS	read-only
			STATUS	current
	DESCRIPTION ""
			::= { mbus22 33 }

mbus22VIF0E		OBJECT-TYPE
			SYNTAX	INTEGER
			ACCESS	read-only
			STATUS	current
	DESCRIPTION ""
			::= { mbus22 34 }

mbus22Value0E		OBJECT-TYPE
			SYNTAX	INTEGER
			ACCESS	read-only
			STATUS	current
	DESCRIPTION ""
			::= { mbus22 35 }

mbus22VIF0F		OBJECT-TYPE
			SYNTAX	INTEGER
			ACCESS	read-only
			STATUS	current
	DESCRIPTION ""
			::= { mbus22 36 }

mbus22Value0F		OBJECT-TYPE
			SYNTAX	INTEGER
			ACCESS	read-only
			STATUS	current
	DESCRIPTION ""
			::= { mbus22 37 }

mbus22VIF10		OBJECT-TYPE
			SYNTAX	INTEGER
			ACCESS	read-only
			STATUS	current
	DESCRIPTION ""
			::= { mbus22 38 }

mbus22Value10		OBJECT-TYPE
			SYNTAX	INTEGER
			ACCESS	read-only
			STATUS	current
	DESCRIPTION ""
			::= { mbus22 39 }

mbus22VIF11		OBJECT-TYPE
			SYNTAX	INTEGER
			ACCESS	read-only
			STATUS	current
	DESCRIPTION ""
			::= { mbus22 40 }

mbus22Value11		OBJECT-TYPE
			SYNTAX	INTEGER
			ACCESS	read-only
			STATUS	current
	DESCRIPTION ""
			::= { mbus22 41 }

mbus22VIF12		OBJECT-TYPE
			SYNTAX	INTEGER
			ACCESS	read-only
			STATUS	current
	DESCRIPTION ""
			::= { mbus22 42 }

mbus22Value12		OBJECT-TYPE
			SYNTAX	INTEGER
			ACCESS	read-only
			STATUS	current
	DESCRIPTION ""
			::= { mbus22 43 }

mbus22VIF13		OBJECT-TYPE
			SYNTAX	INTEGER
			ACCESS	read-only
			STATUS	current
	DESCRIPTION ""
			::= { mbus22 44 }

mbus22Value13		OBJECT-TYPE
			SYNTAX	INTEGER
			ACCESS	read-only
			STATUS	current
	DESCRIPTION ""
			::= { mbus22 45 }

mbus22VIF14		OBJECT-TYPE
			SYNTAX	INTEGER
			ACCESS	read-only
			STATUS	current
	DESCRIPTION ""
			::= { mbus22 46 }

mbus22Value14		OBJECT-TYPE
			SYNTAX	INTEGER
			ACCESS	read-only
			STATUS	current
	DESCRIPTION ""
			::= { mbus22 47 }

mbus22VIF15		OBJECT-TYPE
			SYNTAX	INTEGER
			ACCESS	read-only
			STATUS	current
	DESCRIPTION ""
			::= { mbus22 48 }

mbus22Value15		OBJECT-TYPE
			SYNTAX	INTEGER
			ACCESS	read-only
			STATUS	current
	DESCRIPTION ""
			::= { mbus22 49 }

mbus22VIF16		OBJECT-TYPE
			SYNTAX	INTEGER
			ACCESS	read-only
			STATUS	current
	DESCRIPTION ""
			::= { mbus22 50 }

mbus22Value16		OBJECT-TYPE
			SYNTAX	INTEGER
			ACCESS	read-only
			STATUS	current
	DESCRIPTION ""
			::= { mbus22 51 }

mbus22VIF17		OBJECT-TYPE
			SYNTAX	INTEGER
			ACCESS	read-only
			STATUS	current
	DESCRIPTION ""
			::= { mbus22 52 }

mbus22Value17		OBJECT-TYPE
			SYNTAX	INTEGER
			ACCESS	read-only
			STATUS	current
	DESCRIPTION ""
			::= { mbus22 53 }

mbus22VIF18		OBJECT-TYPE
			SYNTAX	INTEGER
			ACCESS	read-only
			STATUS	current
	DESCRIPTION ""
			::= { mbus22 54 }

mbus22Value18		OBJECT-TYPE
			SYNTAX	INTEGER
			ACCESS	read-only
			STATUS	current
	DESCRIPTION ""
			::= { mbus22 55 }

mbus22VIF19		OBJECT-TYPE
			SYNTAX	INTEGER
			ACCESS	read-only
			STATUS	current
	DESCRIPTION ""
			::= { mbus22 56 }

mbus22Value19		OBJECT-TYPE
			SYNTAX	INTEGER
			ACCESS	read-only
			STATUS	current
	DESCRIPTION ""
			::= { mbus22 57 }

mbus22VIF1A		OBJECT-TYPE
			SYNTAX	INTEGER
			ACCESS	read-only
			STATUS	current
	DESCRIPTION ""
			::= { mbus22 58 }

mbus22Value1A		OBJECT-TYPE
			SYNTAX	INTEGER
			ACCESS	read-only
			STATUS	current
	DESCRIPTION ""
			::= { mbus22 59 }

mbus22VIF1B		OBJECT-TYPE
			SYNTAX	INTEGER
			ACCESS	read-only
			STATUS	current
	DESCRIPTION ""
			::= { mbus22 60 }

mbus22Value1B		OBJECT-TYPE
			SYNTAX	INTEGER
			ACCESS	read-only
			STATUS	current
	DESCRIPTION ""
			::= { mbus22 61 }

mbus22VIF1C		OBJECT-TYPE
			SYNTAX	INTEGER
			ACCESS	read-only
			STATUS	current
	DESCRIPTION ""
			::= { mbus22 62 }

mbus22Value1C		OBJECT-TYPE
			SYNTAX	INTEGER
			ACCESS	read-only
			STATUS	current
	DESCRIPTION ""
			::= { mbus22 63 }

mbus22VIF1D		OBJECT-TYPE
			SYNTAX	INTEGER
			ACCESS	read-only
			STATUS	current
	DESCRIPTION ""
			::= { mbus22 64 }

mbus22Value1D		OBJECT-TYPE
			SYNTAX	INTEGER
			ACCESS	read-only
			STATUS	current
	DESCRIPTION ""
			::= { mbus22 65 }

mbus22VIF1E		OBJECT-TYPE
			SYNTAX	INTEGER
			ACCESS	read-only
			STATUS	current
	DESCRIPTION ""
			::= { mbus22 66 }

mbus22Value1E		OBJECT-TYPE
			SYNTAX	INTEGER
			ACCESS	read-only
			STATUS	current
	DESCRIPTION ""
			::= { mbus22 67 }

mbus22VIF1F		OBJECT-TYPE
			SYNTAX	INTEGER
			ACCESS	read-only
			STATUS	current
	DESCRIPTION ""
			::= { mbus22 68 }

mbus22Value1F		OBJECT-TYPE
			SYNTAX	INTEGER
			ACCESS	read-only
			STATUS	current
	DESCRIPTION ""
			::= { mbus22 69 }

mbus22VIF20		OBJECT-TYPE
			SYNTAX	INTEGER
			ACCESS	read-only
			STATUS	current
	DESCRIPTION ""
			::= { mbus22 70 }

mbus22Value20		OBJECT-TYPE
			SYNTAX	INTEGER
			ACCESS	read-only
			STATUS	current
	DESCRIPTION ""
			::= { mbus22 71 }

mbus22VIF21		OBJECT-TYPE
			SYNTAX	INTEGER
			ACCESS	read-only
			STATUS	current
	DESCRIPTION ""
			::= { mbus22 72 }

mbus22Value21		OBJECT-TYPE
			SYNTAX	INTEGER
			ACCESS	read-only
			STATUS	current
	DESCRIPTION ""
			::= { mbus22 73 }

mbus22VIF22		OBJECT-TYPE
			SYNTAX	INTEGER
			ACCESS	read-only
			STATUS	current
	DESCRIPTION ""
			::= { mbus22 74 }

mbus22Value22		OBJECT-TYPE
			SYNTAX	INTEGER
			ACCESS	read-only
			STATUS	current
	DESCRIPTION ""
			::= { mbus22 75 }

mbus22VIF23		OBJECT-TYPE
			SYNTAX	INTEGER
			ACCESS	read-only
			STATUS	current
	DESCRIPTION ""
			::= { mbus22 76 }

mbus22Value23		OBJECT-TYPE
			SYNTAX	INTEGER
			ACCESS	read-only
			STATUS	current
	DESCRIPTION ""
			::= { mbus22 77 }

mbus22VIF24		OBJECT-TYPE
			SYNTAX	INTEGER
			ACCESS	read-only
			STATUS	current
	DESCRIPTION ""
			::= { mbus22 78 }

mbus22Value24		OBJECT-TYPE
			SYNTAX	INTEGER
			ACCESS	read-only
			STATUS	current
	DESCRIPTION ""
			::= { mbus22 79 }

mbus22VIF25		OBJECT-TYPE
			SYNTAX	INTEGER
			ACCESS	read-only
			STATUS	current
	DESCRIPTION ""
			::= { mbus22 80 }

mbus22Value25		OBJECT-TYPE
			SYNTAX	INTEGER
			ACCESS	read-only
			STATUS	current
	DESCRIPTION ""
			::= { mbus22 81 }

mbus22VIF26		OBJECT-TYPE
			SYNTAX	INTEGER
			ACCESS	read-only
			STATUS	current
	DESCRIPTION ""
			::= { mbus22 82 }

mbus22Value26		OBJECT-TYPE
			SYNTAX	INTEGER
			ACCESS	read-only
			STATUS	current
	DESCRIPTION ""
			::= { mbus22 83 }

mbus22VIF27		OBJECT-TYPE
			SYNTAX	INTEGER
			ACCESS	read-only
			STATUS	current
	DESCRIPTION ""
			::= { mbus22 84 }

mbus22Value27		OBJECT-TYPE
			SYNTAX	INTEGER
			ACCESS	read-only
			STATUS	current
	DESCRIPTION ""
			::= { mbus22 85 }

mbus22VIF28		OBJECT-TYPE
			SYNTAX	INTEGER
			ACCESS	read-only
			STATUS	current
	DESCRIPTION ""
			::= { mbus22 86 }

mbus22Value28		OBJECT-TYPE
			SYNTAX	INTEGER
			ACCESS	read-only
			STATUS	current
	DESCRIPTION ""
			::= { mbus22 87 }

mbus22VIF29		OBJECT-TYPE
			SYNTAX	INTEGER
			ACCESS	read-only
			STATUS	current
	DESCRIPTION ""
			::= { mbus22 88 }

mbus22Value29		OBJECT-TYPE
			SYNTAX	INTEGER
			ACCESS	read-only
			STATUS	current
	DESCRIPTION ""
			::= { mbus22 89 }

mbus22VIF2A		OBJECT-TYPE
			SYNTAX	INTEGER
			ACCESS	read-only
			STATUS	current
	DESCRIPTION ""
			::= { mbus22 90 }

mbus22Value2A		OBJECT-TYPE
			SYNTAX	INTEGER
			ACCESS	read-only
			STATUS	current
	DESCRIPTION ""
			::= { mbus22 91 }

mbus22VIF2B		OBJECT-TYPE
			SYNTAX	INTEGER
			ACCESS	read-only
			STATUS	current
	DESCRIPTION ""
			::= { mbus22 92 }

mbus22Value2B		OBJECT-TYPE
			SYNTAX	INTEGER
			ACCESS	read-only
			STATUS	current
	DESCRIPTION ""
			::= { mbus22 93 }

mbus22VIF2C		OBJECT-TYPE
			SYNTAX	INTEGER
			ACCESS	read-only
			STATUS	current
	DESCRIPTION ""
			::= { mbus22 94 }

mbus22Value2C		OBJECT-TYPE
			SYNTAX	INTEGER
			ACCESS	read-only
			STATUS	current
	DESCRIPTION ""
			::= { mbus22 95 }

mbus22VIF2D		OBJECT-TYPE
			SYNTAX	INTEGER
			ACCESS	read-only
			STATUS	current
	DESCRIPTION ""
			::= { mbus22 96 }

mbus22Value2D		OBJECT-TYPE
			SYNTAX	INTEGER
			ACCESS	read-only
			STATUS	current
	DESCRIPTION ""
			::= { mbus22 97 }

mbus22VIF2E		OBJECT-TYPE
			SYNTAX	INTEGER
			ACCESS	read-only
			STATUS	current
	DESCRIPTION ""
			::= { mbus22 98 }

mbus22Value2E		OBJECT-TYPE
			SYNTAX	INTEGER
			ACCESS	read-only
			STATUS	current
	DESCRIPTION ""
			::= { mbus22 99 }

mbus22VIF2F		OBJECT-TYPE
			SYNTAX	INTEGER
			ACCESS	read-only
			STATUS	current
	DESCRIPTION ""
			::= { mbus22 100 }

mbus22Value2F		OBJECT-TYPE
			SYNTAX	INTEGER
			ACCESS	read-only
			STATUS	current
	DESCRIPTION ""
			::= { mbus22 101 }

mbus23			OBJECT IDENTIFIER ::= { mbus 35 }

mbus23IdNumber		OBJECT-TYPE
			SYNTAX	Gauge
			ACCESS	read-only
			STATUS	current
	DESCRIPTION ""
			::= { mbus23 1 }

mbus23Manufacturer	OBJECT-TYPE
			SYNTAX	Gauge
			ACCESS	read-only
			STATUS	current
	DESCRIPTION ""
			::= { mbus23 2 }

mbus23Version		OBJECT-TYPE
			SYNTAX	Gauge
			ACCESS	read-only
			STATUS	current
	DESCRIPTION ""
			::= { mbus23 3 }

mbus23Medium		OBJECT-TYPE
			SYNTAX	Gauge
			ACCESS	read-only
			STATUS	current
	DESCRIPTION ""
			::= { mbus23 4 }

mbus23Status		OBJECT-TYPE
			SYNTAX	Gauge
			ACCESS	read-only
			STATUS	current
	DESCRIPTION ""
			::= { mbus23 5 }

mbus23VIF00		OBJECT-TYPE
			SYNTAX	INTEGER
			ACCESS	read-only
			STATUS	current
	DESCRIPTION ""
			::= { mbus23 6 }

mbus23Value00		OBJECT-TYPE
			SYNTAX	INTEGER
			ACCESS	read-only
			STATUS	current
	DESCRIPTION ""
			::= { mbus23 7 }

mbus23VIF01		OBJECT-TYPE
			SYNTAX	INTEGER
			ACCESS	read-only
			STATUS	current
	DESCRIPTION ""
			::= { mbus23 8 }

mbus23Value01		OBJECT-TYPE
			SYNTAX	INTEGER
			ACCESS	read-only
			STATUS	current
	DESCRIPTION ""
			::= { mbus23 9 }

mbus23VIF02		OBJECT-TYPE
			SYNTAX	INTEGER
			ACCESS	read-only
			STATUS	current
	DESCRIPTION ""
			::= { mbus23 10 }

mbus23Value02		OBJECT-TYPE
			SYNTAX	INTEGER
			ACCESS	read-only
			STATUS	current
	DESCRIPTION ""
			::= { mbus23 11 }

mbus23VIF03		OBJECT-TYPE
			SYNTAX	INTEGER
			ACCESS	read-only
			STATUS	current
	DESCRIPTION ""
			::= { mbus23 12 }

mbus23Value03		OBJECT-TYPE
			SYNTAX	INTEGER
			ACCESS	read-only
			STATUS	current
	DESCRIPTION ""
			::= { mbus23 13 }

mbus23VIF04		OBJECT-TYPE
			SYNTAX	INTEGER
			ACCESS	read-only
			STATUS	current
	DESCRIPTION ""
			::= { mbus23 14 }

mbus23Value04		OBJECT-TYPE
			SYNTAX	INTEGER
			ACCESS	read-only
			STATUS	current
	DESCRIPTION ""
			::= { mbus23 15 }

mbus23VIF05		OBJECT-TYPE
			SYNTAX	INTEGER
			ACCESS	read-only
			STATUS	current
	DESCRIPTION ""
			::= { mbus23 16 }

mbus23Value05		OBJECT-TYPE
			SYNTAX	INTEGER
			ACCESS	read-only
			STATUS	current
	DESCRIPTION ""
			::= { mbus23 17 }

mbus23VIF06		OBJECT-TYPE
			SYNTAX	INTEGER
			ACCESS	read-only
			STATUS	current
	DESCRIPTION ""
			::= { mbus23 18 }

mbus23Value06		OBJECT-TYPE
			SYNTAX	INTEGER
			ACCESS	read-only
			STATUS	current
	DESCRIPTION ""
			::= { mbus23 19 }

mbus23VIF07		OBJECT-TYPE
			SYNTAX	INTEGER
			ACCESS	read-only
			STATUS	current
	DESCRIPTION ""
			::= { mbus23 20 }

mbus23Value07		OBJECT-TYPE
			SYNTAX	INTEGER
			ACCESS	read-only
			STATUS	current
	DESCRIPTION ""
			::= { mbus23 21 }

mbus23VIF08		OBJECT-TYPE
			SYNTAX	INTEGER
			ACCESS	read-only
			STATUS	current
	DESCRIPTION ""
			::= { mbus23 22 }

mbus23Value08		OBJECT-TYPE
			SYNTAX	INTEGER
			ACCESS	read-only
			STATUS	current
	DESCRIPTION ""
			::= { mbus23 23 }

mbus23VIF09		OBJECT-TYPE
			SYNTAX	INTEGER
			ACCESS	read-only
			STATUS	current
	DESCRIPTION ""
			::= { mbus23 24 }

mbus23Value09		OBJECT-TYPE
			SYNTAX	INTEGER
			ACCESS	read-only
			STATUS	current
	DESCRIPTION ""
			::= { mbus23 25 }

mbus23VIF0A		OBJECT-TYPE
			SYNTAX	INTEGER
			ACCESS	read-only
			STATUS	current
	DESCRIPTION ""
			::= { mbus23 26 }

mbus23Value0A		OBJECT-TYPE
			SYNTAX	INTEGER
			ACCESS	read-only
			STATUS	current
	DESCRIPTION ""
			::= { mbus23 27 }

mbus23VIF0B		OBJECT-TYPE
			SYNTAX	INTEGER
			ACCESS	read-only
			STATUS	current
	DESCRIPTION ""
			::= { mbus23 28 }

mbus23Value0B		OBJECT-TYPE
			SYNTAX	INTEGER
			ACCESS	read-only
			STATUS	current
	DESCRIPTION ""
			::= { mbus23 29 }

mbus23VIF0C		OBJECT-TYPE
			SYNTAX	INTEGER
			ACCESS	read-only
			STATUS	current
	DESCRIPTION ""
			::= { mbus23 30 }

mbus23Value0C		OBJECT-TYPE
			SYNTAX	INTEGER
			ACCESS	read-only
			STATUS	current
	DESCRIPTION ""
			::= { mbus23 31 }

mbus23VIF0D		OBJECT-TYPE
			SYNTAX	INTEGER
			ACCESS	read-only
			STATUS	current
	DESCRIPTION ""
			::= { mbus23 32 }

mbus23Value0D		OBJECT-TYPE
			SYNTAX	INTEGER
			ACCESS	read-only
			STATUS	current
	DESCRIPTION ""
			::= { mbus23 33 }

mbus23VIF0E		OBJECT-TYPE
			SYNTAX	INTEGER
			ACCESS	read-only
			STATUS	current
	DESCRIPTION ""
			::= { mbus23 34 }

mbus23Value0E		OBJECT-TYPE
			SYNTAX	INTEGER
			ACCESS	read-only
			STATUS	current
	DESCRIPTION ""
			::= { mbus23 35 }

mbus23VIF0F		OBJECT-TYPE
			SYNTAX	INTEGER
			ACCESS	read-only
			STATUS	current
	DESCRIPTION ""
			::= { mbus23 36 }

mbus23Value0F		OBJECT-TYPE
			SYNTAX	INTEGER
			ACCESS	read-only
			STATUS	current
	DESCRIPTION ""
			::= { mbus23 37 }

mbus23VIF10		OBJECT-TYPE
			SYNTAX	INTEGER
			ACCESS	read-only
			STATUS	current
	DESCRIPTION ""
			::= { mbus23 38 }

mbus23Value10		OBJECT-TYPE
			SYNTAX	INTEGER
			ACCESS	read-only
			STATUS	current
	DESCRIPTION ""
			::= { mbus23 39 }

mbus23VIF11		OBJECT-TYPE
			SYNTAX	INTEGER
			ACCESS	read-only
			STATUS	current
	DESCRIPTION ""
			::= { mbus23 40 }

mbus23Value11		OBJECT-TYPE
			SYNTAX	INTEGER
			ACCESS	read-only
			STATUS	current
	DESCRIPTION ""
			::= { mbus23 41 }

mbus23VIF12		OBJECT-TYPE
			SYNTAX	INTEGER
			ACCESS	read-only
			STATUS	current
	DESCRIPTION ""
			::= { mbus23 42 }

mbus23Value12		OBJECT-TYPE
			SYNTAX	INTEGER
			ACCESS	read-only
			STATUS	current
	DESCRIPTION ""
			::= { mbus23 43 }

mbus23VIF13		OBJECT-TYPE
			SYNTAX	INTEGER
			ACCESS	read-only
			STATUS	current
	DESCRIPTION ""
			::= { mbus23 44 }

mbus23Value13		OBJECT-TYPE
			SYNTAX	INTEGER
			ACCESS	read-only
			STATUS	current
	DESCRIPTION ""
			::= { mbus23 45 }

mbus23VIF14		OBJECT-TYPE
			SYNTAX	INTEGER
			ACCESS	read-only
			STATUS	current
	DESCRIPTION ""
			::= { mbus23 46 }

mbus23Value14		OBJECT-TYPE
			SYNTAX	INTEGER
			ACCESS	read-only
			STATUS	current
	DESCRIPTION ""
			::= { mbus23 47 }

mbus23VIF15		OBJECT-TYPE
			SYNTAX	INTEGER
			ACCESS	read-only
			STATUS	current
	DESCRIPTION ""
			::= { mbus23 48 }

mbus23Value15		OBJECT-TYPE
			SYNTAX	INTEGER
			ACCESS	read-only
			STATUS	current
	DESCRIPTION ""
			::= { mbus23 49 }

mbus23VIF16		OBJECT-TYPE
			SYNTAX	INTEGER
			ACCESS	read-only
			STATUS	current
	DESCRIPTION ""
			::= { mbus23 50 }

mbus23Value16		OBJECT-TYPE
			SYNTAX	INTEGER
			ACCESS	read-only
			STATUS	current
	DESCRIPTION ""
			::= { mbus23 51 }

mbus23VIF17		OBJECT-TYPE
			SYNTAX	INTEGER
			ACCESS	read-only
			STATUS	current
	DESCRIPTION ""
			::= { mbus23 52 }

mbus23Value17		OBJECT-TYPE
			SYNTAX	INTEGER
			ACCESS	read-only
			STATUS	current
	DESCRIPTION ""
			::= { mbus23 53 }

mbus23VIF18		OBJECT-TYPE
			SYNTAX	INTEGER
			ACCESS	read-only
			STATUS	current
	DESCRIPTION ""
			::= { mbus23 54 }

mbus23Value18		OBJECT-TYPE
			SYNTAX	INTEGER
			ACCESS	read-only
			STATUS	current
	DESCRIPTION ""
			::= { mbus23 55 }

mbus23VIF19		OBJECT-TYPE
			SYNTAX	INTEGER
			ACCESS	read-only
			STATUS	current
	DESCRIPTION ""
			::= { mbus23 56 }

mbus23Value19		OBJECT-TYPE
			SYNTAX	INTEGER
			ACCESS	read-only
			STATUS	current
	DESCRIPTION ""
			::= { mbus23 57 }

mbus23VIF1A		OBJECT-TYPE
			SYNTAX	INTEGER
			ACCESS	read-only
			STATUS	current
	DESCRIPTION ""
			::= { mbus23 58 }

mbus23Value1A		OBJECT-TYPE
			SYNTAX	INTEGER
			ACCESS	read-only
			STATUS	current
	DESCRIPTION ""
			::= { mbus23 59 }

mbus23VIF1B		OBJECT-TYPE
			SYNTAX	INTEGER
			ACCESS	read-only
			STATUS	current
	DESCRIPTION ""
			::= { mbus23 60 }

mbus23Value1B		OBJECT-TYPE
			SYNTAX	INTEGER
			ACCESS	read-only
			STATUS	current
	DESCRIPTION ""
			::= { mbus23 61 }

mbus23VIF1C		OBJECT-TYPE
			SYNTAX	INTEGER
			ACCESS	read-only
			STATUS	current
	DESCRIPTION ""
			::= { mbus23 62 }

mbus23Value1C		OBJECT-TYPE
			SYNTAX	INTEGER
			ACCESS	read-only
			STATUS	current
	DESCRIPTION ""
			::= { mbus23 63 }

mbus23VIF1D		OBJECT-TYPE
			SYNTAX	INTEGER
			ACCESS	read-only
			STATUS	current
	DESCRIPTION ""
			::= { mbus23 64 }

mbus23Value1D		OBJECT-TYPE
			SYNTAX	INTEGER
			ACCESS	read-only
			STATUS	current
	DESCRIPTION ""
			::= { mbus23 65 }

mbus23VIF1E		OBJECT-TYPE
			SYNTAX	INTEGER
			ACCESS	read-only
			STATUS	current
	DESCRIPTION ""
			::= { mbus23 66 }

mbus23Value1E		OBJECT-TYPE
			SYNTAX	INTEGER
			ACCESS	read-only
			STATUS	current
	DESCRIPTION ""
			::= { mbus23 67 }

mbus23VIF1F		OBJECT-TYPE
			SYNTAX	INTEGER
			ACCESS	read-only
			STATUS	current
	DESCRIPTION ""
			::= { mbus23 68 }

mbus23Value1F		OBJECT-TYPE
			SYNTAX	INTEGER
			ACCESS	read-only
			STATUS	current
	DESCRIPTION ""
			::= { mbus23 69 }

mbus23VIF20		OBJECT-TYPE
			SYNTAX	INTEGER
			ACCESS	read-only
			STATUS	current
	DESCRIPTION ""
			::= { mbus23 70 }

mbus23Value20		OBJECT-TYPE
			SYNTAX	INTEGER
			ACCESS	read-only
			STATUS	current
	DESCRIPTION ""
			::= { mbus23 71 }

mbus23VIF21		OBJECT-TYPE
			SYNTAX	INTEGER
			ACCESS	read-only
			STATUS	current
	DESCRIPTION ""
			::= { mbus23 72 }

mbus23Value21		OBJECT-TYPE
			SYNTAX	INTEGER
			ACCESS	read-only
			STATUS	current
	DESCRIPTION ""
			::= { mbus23 73 }

mbus23VIF22		OBJECT-TYPE
			SYNTAX	INTEGER
			ACCESS	read-only
			STATUS	current
	DESCRIPTION ""
			::= { mbus23 74 }

mbus23Value22		OBJECT-TYPE
			SYNTAX	INTEGER
			ACCESS	read-only
			STATUS	current
	DESCRIPTION ""
			::= { mbus23 75 }

mbus23VIF23		OBJECT-TYPE
			SYNTAX	INTEGER
			ACCESS	read-only
			STATUS	current
	DESCRIPTION ""
			::= { mbus23 76 }

mbus23Value23		OBJECT-TYPE
			SYNTAX	INTEGER
			ACCESS	read-only
			STATUS	current
	DESCRIPTION ""
			::= { mbus23 77 }

mbus23VIF24		OBJECT-TYPE
			SYNTAX	INTEGER
			ACCESS	read-only
			STATUS	current
	DESCRIPTION ""
			::= { mbus23 78 }

mbus23Value24		OBJECT-TYPE
			SYNTAX	INTEGER
			ACCESS	read-only
			STATUS	current
	DESCRIPTION ""
			::= { mbus23 79 }

mbus23VIF25		OBJECT-TYPE
			SYNTAX	INTEGER
			ACCESS	read-only
			STATUS	current
	DESCRIPTION ""
			::= { mbus23 80 }

mbus23Value25		OBJECT-TYPE
			SYNTAX	INTEGER
			ACCESS	read-only
			STATUS	current
	DESCRIPTION ""
			::= { mbus23 81 }

mbus23VIF26		OBJECT-TYPE
			SYNTAX	INTEGER
			ACCESS	read-only
			STATUS	current
	DESCRIPTION ""
			::= { mbus23 82 }

mbus23Value26		OBJECT-TYPE
			SYNTAX	INTEGER
			ACCESS	read-only
			STATUS	current
	DESCRIPTION ""
			::= { mbus23 83 }

mbus23VIF27		OBJECT-TYPE
			SYNTAX	INTEGER
			ACCESS	read-only
			STATUS	current
	DESCRIPTION ""
			::= { mbus23 84 }

mbus23Value27		OBJECT-TYPE
			SYNTAX	INTEGER
			ACCESS	read-only
			STATUS	current
	DESCRIPTION ""
			::= { mbus23 85 }

mbus23VIF28		OBJECT-TYPE
			SYNTAX	INTEGER
			ACCESS	read-only
			STATUS	current
	DESCRIPTION ""
			::= { mbus23 86 }

mbus23Value28		OBJECT-TYPE
			SYNTAX	INTEGER
			ACCESS	read-only
			STATUS	current
	DESCRIPTION ""
			::= { mbus23 87 }

mbus23VIF29		OBJECT-TYPE
			SYNTAX	INTEGER
			ACCESS	read-only
			STATUS	current
	DESCRIPTION ""
			::= { mbus23 88 }

mbus23Value29		OBJECT-TYPE
			SYNTAX	INTEGER
			ACCESS	read-only
			STATUS	current
	DESCRIPTION ""
			::= { mbus23 89 }

mbus23VIF2A		OBJECT-TYPE
			SYNTAX	INTEGER
			ACCESS	read-only
			STATUS	current
	DESCRIPTION ""
			::= { mbus23 90 }

mbus23Value2A		OBJECT-TYPE
			SYNTAX	INTEGER
			ACCESS	read-only
			STATUS	current
	DESCRIPTION ""
			::= { mbus23 91 }

mbus23VIF2B		OBJECT-TYPE
			SYNTAX	INTEGER
			ACCESS	read-only
			STATUS	current
	DESCRIPTION ""
			::= { mbus23 92 }

mbus23Value2B		OBJECT-TYPE
			SYNTAX	INTEGER
			ACCESS	read-only
			STATUS	current
	DESCRIPTION ""
			::= { mbus23 93 }

mbus23VIF2C		OBJECT-TYPE
			SYNTAX	INTEGER
			ACCESS	read-only
			STATUS	current
	DESCRIPTION ""
			::= { mbus23 94 }

mbus23Value2C		OBJECT-TYPE
			SYNTAX	INTEGER
			ACCESS	read-only
			STATUS	current
	DESCRIPTION ""
			::= { mbus23 95 }

mbus23VIF2D		OBJECT-TYPE
			SYNTAX	INTEGER
			ACCESS	read-only
			STATUS	current
	DESCRIPTION ""
			::= { mbus23 96 }

mbus23Value2D		OBJECT-TYPE
			SYNTAX	INTEGER
			ACCESS	read-only
			STATUS	current
	DESCRIPTION ""
			::= { mbus23 97 }

mbus23VIF2E		OBJECT-TYPE
			SYNTAX	INTEGER
			ACCESS	read-only
			STATUS	current
	DESCRIPTION ""
			::= { mbus23 98 }

mbus23Value2E		OBJECT-TYPE
			SYNTAX	INTEGER
			ACCESS	read-only
			STATUS	current
	DESCRIPTION ""
			::= { mbus23 99 }

mbus23VIF2F		OBJECT-TYPE
			SYNTAX	INTEGER
			ACCESS	read-only
			STATUS	current
	DESCRIPTION ""
			::= { mbus23 100 }

mbus23Value2F		OBJECT-TYPE
			SYNTAX	INTEGER
			ACCESS	read-only
			STATUS	current
	DESCRIPTION ""
			::= { mbus23 101 }

mbus24			OBJECT IDENTIFIER ::= { mbus 36 }

mbus24IdNumber		OBJECT-TYPE
			SYNTAX	Gauge
			ACCESS	read-only
			STATUS	current
	DESCRIPTION ""
			::= { mbus24 1 }

mbus24Manufacturer	OBJECT-TYPE
			SYNTAX	Gauge
			ACCESS	read-only
			STATUS	current
	DESCRIPTION ""
			::= { mbus24 2 }

mbus24Version		OBJECT-TYPE
			SYNTAX	Gauge
			ACCESS	read-only
			STATUS	current
	DESCRIPTION ""
			::= { mbus24 3 }

mbus24Medium		OBJECT-TYPE
			SYNTAX	Gauge
			ACCESS	read-only
			STATUS	current
	DESCRIPTION ""
			::= { mbus24 4 }

mbus24Status		OBJECT-TYPE
			SYNTAX	Gauge
			ACCESS	read-only
			STATUS	current
	DESCRIPTION ""
			::= { mbus24 5 }

mbus24VIF00		OBJECT-TYPE
			SYNTAX	INTEGER
			ACCESS	read-only
			STATUS	current
	DESCRIPTION ""
			::= { mbus24 6 }

mbus24Value00		OBJECT-TYPE
			SYNTAX	INTEGER
			ACCESS	read-only
			STATUS	current
	DESCRIPTION ""
			::= { mbus24 7 }

mbus24VIF01		OBJECT-TYPE
			SYNTAX	INTEGER
			ACCESS	read-only
			STATUS	current
	DESCRIPTION ""
			::= { mbus24 8 }

mbus24Value01		OBJECT-TYPE
			SYNTAX	INTEGER
			ACCESS	read-only
			STATUS	current
	DESCRIPTION ""
			::= { mbus24 9 }

mbus24VIF02		OBJECT-TYPE
			SYNTAX	INTEGER
			ACCESS	read-only
			STATUS	current
	DESCRIPTION ""
			::= { mbus24 10 }

mbus24Value02		OBJECT-TYPE
			SYNTAX	INTEGER
			ACCESS	read-only
			STATUS	current
	DESCRIPTION ""
			::= { mbus24 11 }

mbus24VIF03		OBJECT-TYPE
			SYNTAX	INTEGER
			ACCESS	read-only
			STATUS	current
	DESCRIPTION ""
			::= { mbus24 12 }

mbus24Value03		OBJECT-TYPE
			SYNTAX	INTEGER
			ACCESS	read-only
			STATUS	current
	DESCRIPTION ""
			::= { mbus24 13 }

mbus24VIF04		OBJECT-TYPE
			SYNTAX	INTEGER
			ACCESS	read-only
			STATUS	current
	DESCRIPTION ""
			::= { mbus24 14 }

mbus24Value04		OBJECT-TYPE
			SYNTAX	INTEGER
			ACCESS	read-only
			STATUS	current
	DESCRIPTION ""
			::= { mbus24 15 }

mbus24VIF05		OBJECT-TYPE
			SYNTAX	INTEGER
			ACCESS	read-only
			STATUS	current
	DESCRIPTION ""
			::= { mbus24 16 }

mbus24Value05		OBJECT-TYPE
			SYNTAX	INTEGER
			ACCESS	read-only
			STATUS	current
	DESCRIPTION ""
			::= { mbus24 17 }

mbus24VIF06		OBJECT-TYPE
			SYNTAX	INTEGER
			ACCESS	read-only
			STATUS	current
	DESCRIPTION ""
			::= { mbus24 18 }

mbus24Value06		OBJECT-TYPE
			SYNTAX	INTEGER
			ACCESS	read-only
			STATUS	current
	DESCRIPTION ""
			::= { mbus24 19 }

mbus24VIF07		OBJECT-TYPE
			SYNTAX	INTEGER
			ACCESS	read-only
			STATUS	current
	DESCRIPTION ""
			::= { mbus24 20 }

mbus24Value07		OBJECT-TYPE
			SYNTAX	INTEGER
			ACCESS	read-only
			STATUS	current
	DESCRIPTION ""
			::= { mbus24 21 }

mbus24VIF08		OBJECT-TYPE
			SYNTAX	INTEGER
			ACCESS	read-only
			STATUS	current
	DESCRIPTION ""
			::= { mbus24 22 }

mbus24Value08		OBJECT-TYPE
			SYNTAX	INTEGER
			ACCESS	read-only
			STATUS	current
	DESCRIPTION ""
			::= { mbus24 23 }

mbus24VIF09		OBJECT-TYPE
			SYNTAX	INTEGER
			ACCESS	read-only
			STATUS	current
	DESCRIPTION ""
			::= { mbus24 24 }

mbus24Value09		OBJECT-TYPE
			SYNTAX	INTEGER
			ACCESS	read-only
			STATUS	current
	DESCRIPTION ""
			::= { mbus24 25 }

mbus24VIF0A		OBJECT-TYPE
			SYNTAX	INTEGER
			ACCESS	read-only
			STATUS	current
	DESCRIPTION ""
			::= { mbus24 26 }

mbus24Value0A		OBJECT-TYPE
			SYNTAX	INTEGER
			ACCESS	read-only
			STATUS	current
	DESCRIPTION ""
			::= { mbus24 27 }

mbus24VIF0B		OBJECT-TYPE
			SYNTAX	INTEGER
			ACCESS	read-only
			STATUS	current
	DESCRIPTION ""
			::= { mbus24 28 }

mbus24Value0B		OBJECT-TYPE
			SYNTAX	INTEGER
			ACCESS	read-only
			STATUS	current
	DESCRIPTION ""
			::= { mbus24 29 }

mbus24VIF0C		OBJECT-TYPE
			SYNTAX	INTEGER
			ACCESS	read-only
			STATUS	current
	DESCRIPTION ""
			::= { mbus24 30 }

mbus24Value0C		OBJECT-TYPE
			SYNTAX	INTEGER
			ACCESS	read-only
			STATUS	current
	DESCRIPTION ""
			::= { mbus24 31 }

mbus24VIF0D		OBJECT-TYPE
			SYNTAX	INTEGER
			ACCESS	read-only
			STATUS	current
	DESCRIPTION ""
			::= { mbus24 32 }

mbus24Value0D		OBJECT-TYPE
			SYNTAX	INTEGER
			ACCESS	read-only
			STATUS	current
	DESCRIPTION ""
			::= { mbus24 33 }

mbus24VIF0E		OBJECT-TYPE
			SYNTAX	INTEGER
			ACCESS	read-only
			STATUS	current
	DESCRIPTION ""
			::= { mbus24 34 }

mbus24Value0E		OBJECT-TYPE
			SYNTAX	INTEGER
			ACCESS	read-only
			STATUS	current
	DESCRIPTION ""
			::= { mbus24 35 }

mbus24VIF0F		OBJECT-TYPE
			SYNTAX	INTEGER
			ACCESS	read-only
			STATUS	current
	DESCRIPTION ""
			::= { mbus24 36 }

mbus24Value0F		OBJECT-TYPE
			SYNTAX	INTEGER
			ACCESS	read-only
			STATUS	current
	DESCRIPTION ""
			::= { mbus24 37 }

mbus24VIF10		OBJECT-TYPE
			SYNTAX	INTEGER
			ACCESS	read-only
			STATUS	current
	DESCRIPTION ""
			::= { mbus24 38 }

mbus24Value10		OBJECT-TYPE
			SYNTAX	INTEGER
			ACCESS	read-only
			STATUS	current
	DESCRIPTION ""
			::= { mbus24 39 }

mbus24VIF11		OBJECT-TYPE
			SYNTAX	INTEGER
			ACCESS	read-only
			STATUS	current
	DESCRIPTION ""
			::= { mbus24 40 }

mbus24Value11		OBJECT-TYPE
			SYNTAX	INTEGER
			ACCESS	read-only
			STATUS	current
	DESCRIPTION ""
			::= { mbus24 41 }

mbus24VIF12		OBJECT-TYPE
			SYNTAX	INTEGER
			ACCESS	read-only
			STATUS	current
	DESCRIPTION ""
			::= { mbus24 42 }

mbus24Value12		OBJECT-TYPE
			SYNTAX	INTEGER
			ACCESS	read-only
			STATUS	current
	DESCRIPTION ""
			::= { mbus24 43 }

mbus24VIF13		OBJECT-TYPE
			SYNTAX	INTEGER
			ACCESS	read-only
			STATUS	current
	DESCRIPTION ""
			::= { mbus24 44 }

mbus24Value13		OBJECT-TYPE
			SYNTAX	INTEGER
			ACCESS	read-only
			STATUS	current
	DESCRIPTION ""
			::= { mbus24 45 }

mbus24VIF14		OBJECT-TYPE
			SYNTAX	INTEGER
			ACCESS	read-only
			STATUS	current
	DESCRIPTION ""
			::= { mbus24 46 }

mbus24Value14		OBJECT-TYPE
			SYNTAX	INTEGER
			ACCESS	read-only
			STATUS	current
	DESCRIPTION ""
			::= { mbus24 47 }

mbus24VIF15		OBJECT-TYPE
			SYNTAX	INTEGER
			ACCESS	read-only
			STATUS	current
	DESCRIPTION ""
			::= { mbus24 48 }

mbus24Value15		OBJECT-TYPE
			SYNTAX	INTEGER
			ACCESS	read-only
			STATUS	current
	DESCRIPTION ""
			::= { mbus24 49 }

mbus24VIF16		OBJECT-TYPE
			SYNTAX	INTEGER
			ACCESS	read-only
			STATUS	current
	DESCRIPTION ""
			::= { mbus24 50 }

mbus24Value16		OBJECT-TYPE
			SYNTAX	INTEGER
			ACCESS	read-only
			STATUS	current
	DESCRIPTION ""
			::= { mbus24 51 }

mbus24VIF17		OBJECT-TYPE
			SYNTAX	INTEGER
			ACCESS	read-only
			STATUS	current
	DESCRIPTION ""
			::= { mbus24 52 }

mbus24Value17		OBJECT-TYPE
			SYNTAX	INTEGER
			ACCESS	read-only
			STATUS	current
	DESCRIPTION ""
			::= { mbus24 53 }

mbus24VIF18		OBJECT-TYPE
			SYNTAX	INTEGER
			ACCESS	read-only
			STATUS	current
	DESCRIPTION ""
			::= { mbus24 54 }

mbus24Value18		OBJECT-TYPE
			SYNTAX	INTEGER
			ACCESS	read-only
			STATUS	current
	DESCRIPTION ""
			::= { mbus24 55 }

mbus24VIF19		OBJECT-TYPE
			SYNTAX	INTEGER
			ACCESS	read-only
			STATUS	current
	DESCRIPTION ""
			::= { mbus24 56 }

mbus24Value19		OBJECT-TYPE
			SYNTAX	INTEGER
			ACCESS	read-only
			STATUS	current
	DESCRIPTION ""
			::= { mbus24 57 }

mbus24VIF1A		OBJECT-TYPE
			SYNTAX	INTEGER
			ACCESS	read-only
			STATUS	current
	DESCRIPTION ""
			::= { mbus24 58 }

mbus24Value1A		OBJECT-TYPE
			SYNTAX	INTEGER
			ACCESS	read-only
			STATUS	current
	DESCRIPTION ""
			::= { mbus24 59 }

mbus24VIF1B		OBJECT-TYPE
			SYNTAX	INTEGER
			ACCESS	read-only
			STATUS	current
	DESCRIPTION ""
			::= { mbus24 60 }

mbus24Value1B		OBJECT-TYPE
			SYNTAX	INTEGER
			ACCESS	read-only
			STATUS	current
	DESCRIPTION ""
			::= { mbus24 61 }

mbus24VIF1C		OBJECT-TYPE
			SYNTAX	INTEGER
			ACCESS	read-only
			STATUS	current
	DESCRIPTION ""
			::= { mbus24 62 }

mbus24Value1C		OBJECT-TYPE
			SYNTAX	INTEGER
			ACCESS	read-only
			STATUS	current
	DESCRIPTION ""
			::= { mbus24 63 }

mbus24VIF1D		OBJECT-TYPE
			SYNTAX	INTEGER
			ACCESS	read-only
			STATUS	current
	DESCRIPTION ""
			::= { mbus24 64 }

mbus24Value1D		OBJECT-TYPE
			SYNTAX	INTEGER
			ACCESS	read-only
			STATUS	current
	DESCRIPTION ""
			::= { mbus24 65 }

mbus24VIF1E		OBJECT-TYPE
			SYNTAX	INTEGER
			ACCESS	read-only
			STATUS	current
	DESCRIPTION ""
			::= { mbus24 66 }

mbus24Value1E		OBJECT-TYPE
			SYNTAX	INTEGER
			ACCESS	read-only
			STATUS	current
	DESCRIPTION ""
			::= { mbus24 67 }

mbus24VIF1F		OBJECT-TYPE
			SYNTAX	INTEGER
			ACCESS	read-only
			STATUS	current
	DESCRIPTION ""
			::= { mbus24 68 }

mbus24Value1F		OBJECT-TYPE
			SYNTAX	INTEGER
			ACCESS	read-only
			STATUS	current
	DESCRIPTION ""
			::= { mbus24 69 }

mbus24VIF20		OBJECT-TYPE
			SYNTAX	INTEGER
			ACCESS	read-only
			STATUS	current
	DESCRIPTION ""
			::= { mbus24 70 }

mbus24Value20		OBJECT-TYPE
			SYNTAX	INTEGER
			ACCESS	read-only
			STATUS	current
	DESCRIPTION ""
			::= { mbus24 71 }

mbus24VIF21		OBJECT-TYPE
			SYNTAX	INTEGER
			ACCESS	read-only
			STATUS	current
	DESCRIPTION ""
			::= { mbus24 72 }

mbus24Value21		OBJECT-TYPE
			SYNTAX	INTEGER
			ACCESS	read-only
			STATUS	current
	DESCRIPTION ""
			::= { mbus24 73 }

mbus24VIF22		OBJECT-TYPE
			SYNTAX	INTEGER
			ACCESS	read-only
			STATUS	current
	DESCRIPTION ""
			::= { mbus24 74 }

mbus24Value22		OBJECT-TYPE
			SYNTAX	INTEGER
			ACCESS	read-only
			STATUS	current
	DESCRIPTION ""
			::= { mbus24 75 }

mbus24VIF23		OBJECT-TYPE
			SYNTAX	INTEGER
			ACCESS	read-only
			STATUS	current
	DESCRIPTION ""
			::= { mbus24 76 }

mbus24Value23		OBJECT-TYPE
			SYNTAX	INTEGER
			ACCESS	read-only
			STATUS	current
	DESCRIPTION ""
			::= { mbus24 77 }

mbus24VIF24		OBJECT-TYPE
			SYNTAX	INTEGER
			ACCESS	read-only
			STATUS	current
	DESCRIPTION ""
			::= { mbus24 78 }

mbus24Value24		OBJECT-TYPE
			SYNTAX	INTEGER
			ACCESS	read-only
			STATUS	current
	DESCRIPTION ""
			::= { mbus24 79 }

mbus24VIF25		OBJECT-TYPE
			SYNTAX	INTEGER
			ACCESS	read-only
			STATUS	current
	DESCRIPTION ""
			::= { mbus24 80 }

mbus24Value25		OBJECT-TYPE
			SYNTAX	INTEGER
			ACCESS	read-only
			STATUS	current
	DESCRIPTION ""
			::= { mbus24 81 }

mbus24VIF26		OBJECT-TYPE
			SYNTAX	INTEGER
			ACCESS	read-only
			STATUS	current
	DESCRIPTION ""
			::= { mbus24 82 }

mbus24Value26		OBJECT-TYPE
			SYNTAX	INTEGER
			ACCESS	read-only
			STATUS	current
	DESCRIPTION ""
			::= { mbus24 83 }

mbus24VIF27		OBJECT-TYPE
			SYNTAX	INTEGER
			ACCESS	read-only
			STATUS	current
	DESCRIPTION ""
			::= { mbus24 84 }

mbus24Value27		OBJECT-TYPE
			SYNTAX	INTEGER
			ACCESS	read-only
			STATUS	current
	DESCRIPTION ""
			::= { mbus24 85 }

mbus24VIF28		OBJECT-TYPE
			SYNTAX	INTEGER
			ACCESS	read-only
			STATUS	current
	DESCRIPTION ""
			::= { mbus24 86 }

mbus24Value28		OBJECT-TYPE
			SYNTAX	INTEGER
			ACCESS	read-only
			STATUS	current
	DESCRIPTION ""
			::= { mbus24 87 }

mbus24VIF29		OBJECT-TYPE
			SYNTAX	INTEGER
			ACCESS	read-only
			STATUS	current
	DESCRIPTION ""
			::= { mbus24 88 }

mbus24Value29		OBJECT-TYPE
			SYNTAX	INTEGER
			ACCESS	read-only
			STATUS	current
	DESCRIPTION ""
			::= { mbus24 89 }

mbus24VIF2A		OBJECT-TYPE
			SYNTAX	INTEGER
			ACCESS	read-only
			STATUS	current
	DESCRIPTION ""
			::= { mbus24 90 }

mbus24Value2A		OBJECT-TYPE
			SYNTAX	INTEGER
			ACCESS	read-only
			STATUS	current
	DESCRIPTION ""
			::= { mbus24 91 }

mbus24VIF2B		OBJECT-TYPE
			SYNTAX	INTEGER
			ACCESS	read-only
			STATUS	current
	DESCRIPTION ""
			::= { mbus24 92 }

mbus24Value2B		OBJECT-TYPE
			SYNTAX	INTEGER
			ACCESS	read-only
			STATUS	current
	DESCRIPTION ""
			::= { mbus24 93 }

mbus24VIF2C		OBJECT-TYPE
			SYNTAX	INTEGER
			ACCESS	read-only
			STATUS	current
	DESCRIPTION ""
			::= { mbus24 94 }

mbus24Value2C		OBJECT-TYPE
			SYNTAX	INTEGER
			ACCESS	read-only
			STATUS	current
	DESCRIPTION ""
			::= { mbus24 95 }

mbus24VIF2D		OBJECT-TYPE
			SYNTAX	INTEGER
			ACCESS	read-only
			STATUS	current
	DESCRIPTION ""
			::= { mbus24 96 }

mbus24Value2D		OBJECT-TYPE
			SYNTAX	INTEGER
			ACCESS	read-only
			STATUS	current
	DESCRIPTION ""
			::= { mbus24 97 }

mbus24VIF2E		OBJECT-TYPE
			SYNTAX	INTEGER
			ACCESS	read-only
			STATUS	current
	DESCRIPTION ""
			::= { mbus24 98 }

mbus24Value2E		OBJECT-TYPE
			SYNTAX	INTEGER
			ACCESS	read-only
			STATUS	current
	DESCRIPTION ""
			::= { mbus24 99 }

mbus24VIF2F		OBJECT-TYPE
			SYNTAX	INTEGER
			ACCESS	read-only
			STATUS	current
	DESCRIPTION ""
			::= { mbus24 100 }

mbus24Value2F		OBJECT-TYPE
			SYNTAX	INTEGER
			ACCESS	read-only
			STATUS	current
	DESCRIPTION ""
			::= { mbus24 101 }

mbus25			OBJECT IDENTIFIER ::= { mbus 37 }

mbus25IdNumber		OBJECT-TYPE
			SYNTAX	Gauge
			ACCESS	read-only
			STATUS	current
	DESCRIPTION ""
			::= { mbus25 1 }

mbus25Manufacturer	OBJECT-TYPE
			SYNTAX	Gauge
			ACCESS	read-only
			STATUS	current
	DESCRIPTION ""
			::= { mbus25 2 }

mbus25Version		OBJECT-TYPE
			SYNTAX	Gauge
			ACCESS	read-only
			STATUS	current
	DESCRIPTION ""
			::= { mbus25 3 }

mbus25Medium		OBJECT-TYPE
			SYNTAX	Gauge
			ACCESS	read-only
			STATUS	current
	DESCRIPTION ""
			::= { mbus25 4 }

mbus25Status		OBJECT-TYPE
			SYNTAX	Gauge
			ACCESS	read-only
			STATUS	current
	DESCRIPTION ""
			::= { mbus25 5 }

mbus25VIF00		OBJECT-TYPE
			SYNTAX	INTEGER
			ACCESS	read-only
			STATUS	current
	DESCRIPTION ""
			::= { mbus25 6 }

mbus25Value00		OBJECT-TYPE
			SYNTAX	INTEGER
			ACCESS	read-only
			STATUS	current
	DESCRIPTION ""
			::= { mbus25 7 }

mbus25VIF01		OBJECT-TYPE
			SYNTAX	INTEGER
			ACCESS	read-only
			STATUS	current
	DESCRIPTION ""
			::= { mbus25 8 }

mbus25Value01		OBJECT-TYPE
			SYNTAX	INTEGER
			ACCESS	read-only
			STATUS	current
	DESCRIPTION ""
			::= { mbus25 9 }

mbus25VIF02		OBJECT-TYPE
			SYNTAX	INTEGER
			ACCESS	read-only
			STATUS	current
	DESCRIPTION ""
			::= { mbus25 10 }

mbus25Value02		OBJECT-TYPE
			SYNTAX	INTEGER
			ACCESS	read-only
			STATUS	current
	DESCRIPTION ""
			::= { mbus25 11 }

mbus25VIF03		OBJECT-TYPE
			SYNTAX	INTEGER
			ACCESS	read-only
			STATUS	current
	DESCRIPTION ""
			::= { mbus25 12 }

mbus25Value03		OBJECT-TYPE
			SYNTAX	INTEGER
			ACCESS	read-only
			STATUS	current
	DESCRIPTION ""
			::= { mbus25 13 }

mbus25VIF04		OBJECT-TYPE
			SYNTAX	INTEGER
			ACCESS	read-only
			STATUS	current
	DESCRIPTION ""
			::= { mbus25 14 }

mbus25Value04		OBJECT-TYPE
			SYNTAX	INTEGER
			ACCESS	read-only
			STATUS	current
	DESCRIPTION ""
			::= { mbus25 15 }

mbus25VIF05		OBJECT-TYPE
			SYNTAX	INTEGER
			ACCESS	read-only
			STATUS	current
	DESCRIPTION ""
			::= { mbus25 16 }

mbus25Value05		OBJECT-TYPE
			SYNTAX	INTEGER
			ACCESS	read-only
			STATUS	current
	DESCRIPTION ""
			::= { mbus25 17 }

mbus25VIF06		OBJECT-TYPE
			SYNTAX	INTEGER
			ACCESS	read-only
			STATUS	current
	DESCRIPTION ""
			::= { mbus25 18 }

mbus25Value06		OBJECT-TYPE
			SYNTAX	INTEGER
			ACCESS	read-only
			STATUS	current
	DESCRIPTION ""
			::= { mbus25 19 }

mbus25VIF07		OBJECT-TYPE
			SYNTAX	INTEGER
			ACCESS	read-only
			STATUS	current
	DESCRIPTION ""
			::= { mbus25 20 }

mbus25Value07		OBJECT-TYPE
			SYNTAX	INTEGER
			ACCESS	read-only
			STATUS	current
	DESCRIPTION ""
			::= { mbus25 21 }

mbus25VIF08		OBJECT-TYPE
			SYNTAX	INTEGER
			ACCESS	read-only
			STATUS	current
	DESCRIPTION ""
			::= { mbus25 22 }

mbus25Value08		OBJECT-TYPE
			SYNTAX	INTEGER
			ACCESS	read-only
			STATUS	current
	DESCRIPTION ""
			::= { mbus25 23 }

mbus25VIF09		OBJECT-TYPE
			SYNTAX	INTEGER
			ACCESS	read-only
			STATUS	current
	DESCRIPTION ""
			::= { mbus25 24 }

mbus25Value09		OBJECT-TYPE
			SYNTAX	INTEGER
			ACCESS	read-only
			STATUS	current
	DESCRIPTION ""
			::= { mbus25 25 }

mbus25VIF0A		OBJECT-TYPE
			SYNTAX	INTEGER
			ACCESS	read-only
			STATUS	current
	DESCRIPTION ""
			::= { mbus25 26 }

mbus25Value0A		OBJECT-TYPE
			SYNTAX	INTEGER
			ACCESS	read-only
			STATUS	current
	DESCRIPTION ""
			::= { mbus25 27 }

mbus25VIF0B		OBJECT-TYPE
			SYNTAX	INTEGER
			ACCESS	read-only
			STATUS	current
	DESCRIPTION ""
			::= { mbus25 28 }

mbus25Value0B		OBJECT-TYPE
			SYNTAX	INTEGER
			ACCESS	read-only
			STATUS	current
	DESCRIPTION ""
			::= { mbus25 29 }

mbus25VIF0C		OBJECT-TYPE
			SYNTAX	INTEGER
			ACCESS	read-only
			STATUS	current
	DESCRIPTION ""
			::= { mbus25 30 }

mbus25Value0C		OBJECT-TYPE
			SYNTAX	INTEGER
			ACCESS	read-only
			STATUS	current
	DESCRIPTION ""
			::= { mbus25 31 }

mbus25VIF0D		OBJECT-TYPE
			SYNTAX	INTEGER
			ACCESS	read-only
			STATUS	current
	DESCRIPTION ""
			::= { mbus25 32 }

mbus25Value0D		OBJECT-TYPE
			SYNTAX	INTEGER
			ACCESS	read-only
			STATUS	current
	DESCRIPTION ""
			::= { mbus25 33 }

mbus25VIF0E		OBJECT-TYPE
			SYNTAX	INTEGER
			ACCESS	read-only
			STATUS	current
	DESCRIPTION ""
			::= { mbus25 34 }

mbus25Value0E		OBJECT-TYPE
			SYNTAX	INTEGER
			ACCESS	read-only
			STATUS	current
	DESCRIPTION ""
			::= { mbus25 35 }

mbus25VIF0F		OBJECT-TYPE
			SYNTAX	INTEGER
			ACCESS	read-only
			STATUS	current
	DESCRIPTION ""
			::= { mbus25 36 }

mbus25Value0F		OBJECT-TYPE
			SYNTAX	INTEGER
			ACCESS	read-only
			STATUS	current
	DESCRIPTION ""
			::= { mbus25 37 }

mbus25VIF10		OBJECT-TYPE
			SYNTAX	INTEGER
			ACCESS	read-only
			STATUS	current
	DESCRIPTION ""
			::= { mbus25 38 }

mbus25Value10		OBJECT-TYPE
			SYNTAX	INTEGER
			ACCESS	read-only
			STATUS	current
	DESCRIPTION ""
			::= { mbus25 39 }

mbus25VIF11		OBJECT-TYPE
			SYNTAX	INTEGER
			ACCESS	read-only
			STATUS	current
	DESCRIPTION ""
			::= { mbus25 40 }

mbus25Value11		OBJECT-TYPE
			SYNTAX	INTEGER
			ACCESS	read-only
			STATUS	current
	DESCRIPTION ""
			::= { mbus25 41 }

mbus25VIF12		OBJECT-TYPE
			SYNTAX	INTEGER
			ACCESS	read-only
			STATUS	current
	DESCRIPTION ""
			::= { mbus25 42 }

mbus25Value12		OBJECT-TYPE
			SYNTAX	INTEGER
			ACCESS	read-only
			STATUS	current
	DESCRIPTION ""
			::= { mbus25 43 }

mbus25VIF13		OBJECT-TYPE
			SYNTAX	INTEGER
			ACCESS	read-only
			STATUS	current
	DESCRIPTION ""
			::= { mbus25 44 }

mbus25Value13		OBJECT-TYPE
			SYNTAX	INTEGER
			ACCESS	read-only
			STATUS	current
	DESCRIPTION ""
			::= { mbus25 45 }

mbus25VIF14		OBJECT-TYPE
			SYNTAX	INTEGER
			ACCESS	read-only
			STATUS	current
	DESCRIPTION ""
			::= { mbus25 46 }

mbus25Value14		OBJECT-TYPE
			SYNTAX	INTEGER
			ACCESS	read-only
			STATUS	current
	DESCRIPTION ""
			::= { mbus25 47 }

mbus25VIF15		OBJECT-TYPE
			SYNTAX	INTEGER
			ACCESS	read-only
			STATUS	current
	DESCRIPTION ""
			::= { mbus25 48 }

mbus25Value15		OBJECT-TYPE
			SYNTAX	INTEGER
			ACCESS	read-only
			STATUS	current
	DESCRIPTION ""
			::= { mbus25 49 }

mbus25VIF16		OBJECT-TYPE
			SYNTAX	INTEGER
			ACCESS	read-only
			STATUS	current
	DESCRIPTION ""
			::= { mbus25 50 }

mbus25Value16		OBJECT-TYPE
			SYNTAX	INTEGER
			ACCESS	read-only
			STATUS	current
	DESCRIPTION ""
			::= { mbus25 51 }

mbus25VIF17		OBJECT-TYPE
			SYNTAX	INTEGER
			ACCESS	read-only
			STATUS	current
	DESCRIPTION ""
			::= { mbus25 52 }

mbus25Value17		OBJECT-TYPE
			SYNTAX	INTEGER
			ACCESS	read-only
			STATUS	current
	DESCRIPTION ""
			::= { mbus25 53 }

mbus25VIF18		OBJECT-TYPE
			SYNTAX	INTEGER
			ACCESS	read-only
			STATUS	current
	DESCRIPTION ""
			::= { mbus25 54 }

mbus25Value18		OBJECT-TYPE
			SYNTAX	INTEGER
			ACCESS	read-only
			STATUS	current
	DESCRIPTION ""
			::= { mbus25 55 }

mbus25VIF19		OBJECT-TYPE
			SYNTAX	INTEGER
			ACCESS	read-only
			STATUS	current
	DESCRIPTION ""
			::= { mbus25 56 }

mbus25Value19		OBJECT-TYPE
			SYNTAX	INTEGER
			ACCESS	read-only
			STATUS	current
	DESCRIPTION ""
			::= { mbus25 57 }

mbus25VIF1A		OBJECT-TYPE
			SYNTAX	INTEGER
			ACCESS	read-only
			STATUS	current
	DESCRIPTION ""
			::= { mbus25 58 }

mbus25Value1A		OBJECT-TYPE
			SYNTAX	INTEGER
			ACCESS	read-only
			STATUS	current
	DESCRIPTION ""
			::= { mbus25 59 }

mbus25VIF1B		OBJECT-TYPE
			SYNTAX	INTEGER
			ACCESS	read-only
			STATUS	current
	DESCRIPTION ""
			::= { mbus25 60 }

mbus25Value1B		OBJECT-TYPE
			SYNTAX	INTEGER
			ACCESS	read-only
			STATUS	current
	DESCRIPTION ""
			::= { mbus25 61 }

mbus25VIF1C		OBJECT-TYPE
			SYNTAX	INTEGER
			ACCESS	read-only
			STATUS	current
	DESCRIPTION ""
			::= { mbus25 62 }

mbus25Value1C		OBJECT-TYPE
			SYNTAX	INTEGER
			ACCESS	read-only
			STATUS	current
	DESCRIPTION ""
			::= { mbus25 63 }

mbus25VIF1D		OBJECT-TYPE
			SYNTAX	INTEGER
			ACCESS	read-only
			STATUS	current
	DESCRIPTION ""
			::= { mbus25 64 }

mbus25Value1D		OBJECT-TYPE
			SYNTAX	INTEGER
			ACCESS	read-only
			STATUS	current
	DESCRIPTION ""
			::= { mbus25 65 }

mbus25VIF1E		OBJECT-TYPE
			SYNTAX	INTEGER
			ACCESS	read-only
			STATUS	current
	DESCRIPTION ""
			::= { mbus25 66 }

mbus25Value1E		OBJECT-TYPE
			SYNTAX	INTEGER
			ACCESS	read-only
			STATUS	current
	DESCRIPTION ""
			::= { mbus25 67 }

mbus25VIF1F		OBJECT-TYPE
			SYNTAX	INTEGER
			ACCESS	read-only
			STATUS	current
	DESCRIPTION ""
			::= { mbus25 68 }

mbus25Value1F		OBJECT-TYPE
			SYNTAX	INTEGER
			ACCESS	read-only
			STATUS	current
	DESCRIPTION ""
			::= { mbus25 69 }

mbus25VIF20		OBJECT-TYPE
			SYNTAX	INTEGER
			ACCESS	read-only
			STATUS	current
	DESCRIPTION ""
			::= { mbus25 70 }

mbus25Value20		OBJECT-TYPE
			SYNTAX	INTEGER
			ACCESS	read-only
			STATUS	current
	DESCRIPTION ""
			::= { mbus25 71 }

mbus25VIF21		OBJECT-TYPE
			SYNTAX	INTEGER
			ACCESS	read-only
			STATUS	current
	DESCRIPTION ""
			::= { mbus25 72 }

mbus25Value21		OBJECT-TYPE
			SYNTAX	INTEGER
			ACCESS	read-only
			STATUS	current
	DESCRIPTION ""
			::= { mbus25 73 }

mbus25VIF22		OBJECT-TYPE
			SYNTAX	INTEGER
			ACCESS	read-only
			STATUS	current
	DESCRIPTION ""
			::= { mbus25 74 }

mbus25Value22		OBJECT-TYPE
			SYNTAX	INTEGER
			ACCESS	read-only
			STATUS	current
	DESCRIPTION ""
			::= { mbus25 75 }

mbus25VIF23		OBJECT-TYPE
			SYNTAX	INTEGER
			ACCESS	read-only
			STATUS	current
	DESCRIPTION ""
			::= { mbus25 76 }

mbus25Value23		OBJECT-TYPE
			SYNTAX	INTEGER
			ACCESS	read-only
			STATUS	current
	DESCRIPTION ""
			::= { mbus25 77 }

mbus25VIF24		OBJECT-TYPE
			SYNTAX	INTEGER
			ACCESS	read-only
			STATUS	current
	DESCRIPTION ""
			::= { mbus25 78 }

mbus25Value24		OBJECT-TYPE
			SYNTAX	INTEGER
			ACCESS	read-only
			STATUS	current
	DESCRIPTION ""
			::= { mbus25 79 }

mbus25VIF25		OBJECT-TYPE
			SYNTAX	INTEGER
			ACCESS	read-only
			STATUS	current
	DESCRIPTION ""
			::= { mbus25 80 }

mbus25Value25		OBJECT-TYPE
			SYNTAX	INTEGER
			ACCESS	read-only
			STATUS	current
	DESCRIPTION ""
			::= { mbus25 81 }

mbus25VIF26		OBJECT-TYPE
			SYNTAX	INTEGER
			ACCESS	read-only
			STATUS	current
	DESCRIPTION ""
			::= { mbus25 82 }

mbus25Value26		OBJECT-TYPE
			SYNTAX	INTEGER
			ACCESS	read-only
			STATUS	current
	DESCRIPTION ""
			::= { mbus25 83 }

mbus25VIF27		OBJECT-TYPE
			SYNTAX	INTEGER
			ACCESS	read-only
			STATUS	current
	DESCRIPTION ""
			::= { mbus25 84 }

mbus25Value27		OBJECT-TYPE
			SYNTAX	INTEGER
			ACCESS	read-only
			STATUS	current
	DESCRIPTION ""
			::= { mbus25 85 }

mbus25VIF28		OBJECT-TYPE
			SYNTAX	INTEGER
			ACCESS	read-only
			STATUS	current
	DESCRIPTION ""
			::= { mbus25 86 }

mbus25Value28		OBJECT-TYPE
			SYNTAX	INTEGER
			ACCESS	read-only
			STATUS	current
	DESCRIPTION ""
			::= { mbus25 87 }

mbus25VIF29		OBJECT-TYPE
			SYNTAX	INTEGER
			ACCESS	read-only
			STATUS	current
	DESCRIPTION ""
			::= { mbus25 88 }

mbus25Value29		OBJECT-TYPE
			SYNTAX	INTEGER
			ACCESS	read-only
			STATUS	current
	DESCRIPTION ""
			::= { mbus25 89 }

mbus25VIF2A		OBJECT-TYPE
			SYNTAX	INTEGER
			ACCESS	read-only
			STATUS	current
	DESCRIPTION ""
			::= { mbus25 90 }

mbus25Value2A		OBJECT-TYPE
			SYNTAX	INTEGER
			ACCESS	read-only
			STATUS	current
	DESCRIPTION ""
			::= { mbus25 91 }

mbus25VIF2B		OBJECT-TYPE
			SYNTAX	INTEGER
			ACCESS	read-only
			STATUS	current
	DESCRIPTION ""
			::= { mbus25 92 }

mbus25Value2B		OBJECT-TYPE
			SYNTAX	INTEGER
			ACCESS	read-only
			STATUS	current
	DESCRIPTION ""
			::= { mbus25 93 }

mbus25VIF2C		OBJECT-TYPE
			SYNTAX	INTEGER
			ACCESS	read-only
			STATUS	current
	DESCRIPTION ""
			::= { mbus25 94 }

mbus25Value2C		OBJECT-TYPE
			SYNTAX	INTEGER
			ACCESS	read-only
			STATUS	current
	DESCRIPTION ""
			::= { mbus25 95 }

mbus25VIF2D		OBJECT-TYPE
			SYNTAX	INTEGER
			ACCESS	read-only
			STATUS	current
	DESCRIPTION ""
			::= { mbus25 96 }

mbus25Value2D		OBJECT-TYPE
			SYNTAX	INTEGER
			ACCESS	read-only
			STATUS	current
	DESCRIPTION ""
			::= { mbus25 97 }

mbus25VIF2E		OBJECT-TYPE
			SYNTAX	INTEGER
			ACCESS	read-only
			STATUS	current
	DESCRIPTION ""
			::= { mbus25 98 }

mbus25Value2E		OBJECT-TYPE
			SYNTAX	INTEGER
			ACCESS	read-only
			STATUS	current
	DESCRIPTION ""
			::= { mbus25 99 }

mbus25VIF2F		OBJECT-TYPE
			SYNTAX	INTEGER
			ACCESS	read-only
			STATUS	current
	DESCRIPTION ""
			::= { mbus25 100 }

mbus25Value2F		OBJECT-TYPE
			SYNTAX	INTEGER
			ACCESS	read-only
			STATUS	current
	DESCRIPTION ""
			::= { mbus25 101 }

mbus26			OBJECT IDENTIFIER ::= { mbus 38 }

mbus26IdNumber		OBJECT-TYPE
			SYNTAX	Gauge
			ACCESS	read-only
			STATUS	current
	DESCRIPTION ""
			::= { mbus26 1 }

mbus26Manufacturer	OBJECT-TYPE
			SYNTAX	Gauge
			ACCESS	read-only
			STATUS	current
	DESCRIPTION ""
			::= { mbus26 2 }

mbus26Version		OBJECT-TYPE
			SYNTAX	Gauge
			ACCESS	read-only
			STATUS	current
	DESCRIPTION ""
			::= { mbus26 3 }

mbus26Medium		OBJECT-TYPE
			SYNTAX	Gauge
			ACCESS	read-only
			STATUS	current
	DESCRIPTION ""
			::= { mbus26 4 }

mbus26Status		OBJECT-TYPE
			SYNTAX	Gauge
			ACCESS	read-only
			STATUS	current
	DESCRIPTION ""
			::= { mbus26 5 }

mbus26VIF00		OBJECT-TYPE
			SYNTAX	INTEGER
			ACCESS	read-only
			STATUS	current
	DESCRIPTION ""
			::= { mbus26 6 }

mbus26Value00		OBJECT-TYPE
			SYNTAX	INTEGER
			ACCESS	read-only
			STATUS	current
	DESCRIPTION ""
			::= { mbus26 7 }

mbus26VIF01		OBJECT-TYPE
			SYNTAX	INTEGER
			ACCESS	read-only
			STATUS	current
	DESCRIPTION ""
			::= { mbus26 8 }

mbus26Value01		OBJECT-TYPE
			SYNTAX	INTEGER
			ACCESS	read-only
			STATUS	current
	DESCRIPTION ""
			::= { mbus26 9 }

mbus26VIF02		OBJECT-TYPE
			SYNTAX	INTEGER
			ACCESS	read-only
			STATUS	current
	DESCRIPTION ""
			::= { mbus26 10 }

mbus26Value02		OBJECT-TYPE
			SYNTAX	INTEGER
			ACCESS	read-only
			STATUS	current
	DESCRIPTION ""
			::= { mbus26 11 }

mbus26VIF03		OBJECT-TYPE
			SYNTAX	INTEGER
			ACCESS	read-only
			STATUS	current
	DESCRIPTION ""
			::= { mbus26 12 }

mbus26Value03		OBJECT-TYPE
			SYNTAX	INTEGER
			ACCESS	read-only
			STATUS	current
	DESCRIPTION ""
			::= { mbus26 13 }

mbus26VIF04		OBJECT-TYPE
			SYNTAX	INTEGER
			ACCESS	read-only
			STATUS	current
	DESCRIPTION ""
			::= { mbus26 14 }

mbus26Value04		OBJECT-TYPE
			SYNTAX	INTEGER
			ACCESS	read-only
			STATUS	current
	DESCRIPTION ""
			::= { mbus26 15 }

mbus26VIF05		OBJECT-TYPE
			SYNTAX	INTEGER
			ACCESS	read-only
			STATUS	current
	DESCRIPTION ""
			::= { mbus26 16 }

mbus26Value05		OBJECT-TYPE
			SYNTAX	INTEGER
			ACCESS	read-only
			STATUS	current
	DESCRIPTION ""
			::= { mbus26 17 }

mbus26VIF06		OBJECT-TYPE
			SYNTAX	INTEGER
			ACCESS	read-only
			STATUS	current
	DESCRIPTION ""
			::= { mbus26 18 }

mbus26Value06		OBJECT-TYPE
			SYNTAX	INTEGER
			ACCESS	read-only
			STATUS	current
	DESCRIPTION ""
			::= { mbus26 19 }

mbus26VIF07		OBJECT-TYPE
			SYNTAX	INTEGER
			ACCESS	read-only
			STATUS	current
	DESCRIPTION ""
			::= { mbus26 20 }

mbus26Value07		OBJECT-TYPE
			SYNTAX	INTEGER
			ACCESS	read-only
			STATUS	current
	DESCRIPTION ""
			::= { mbus26 21 }

mbus26VIF08		OBJECT-TYPE
			SYNTAX	INTEGER
			ACCESS	read-only
			STATUS	current
	DESCRIPTION ""
			::= { mbus26 22 }

mbus26Value08		OBJECT-TYPE
			SYNTAX	INTEGER
			ACCESS	read-only
			STATUS	current
	DESCRIPTION ""
			::= { mbus26 23 }

mbus26VIF09		OBJECT-TYPE
			SYNTAX	INTEGER
			ACCESS	read-only
			STATUS	current
	DESCRIPTION ""
			::= { mbus26 24 }

mbus26Value09		OBJECT-TYPE
			SYNTAX	INTEGER
			ACCESS	read-only
			STATUS	current
	DESCRIPTION ""
			::= { mbus26 25 }

mbus26VIF0A		OBJECT-TYPE
			SYNTAX	INTEGER
			ACCESS	read-only
			STATUS	current
	DESCRIPTION ""
			::= { mbus26 26 }

mbus26Value0A		OBJECT-TYPE
			SYNTAX	INTEGER
			ACCESS	read-only
			STATUS	current
	DESCRIPTION ""
			::= { mbus26 27 }

mbus26VIF0B		OBJECT-TYPE
			SYNTAX	INTEGER
			ACCESS	read-only
			STATUS	current
	DESCRIPTION ""
			::= { mbus26 28 }

mbus26Value0B		OBJECT-TYPE
			SYNTAX	INTEGER
			ACCESS	read-only
			STATUS	current
	DESCRIPTION ""
			::= { mbus26 29 }

mbus26VIF0C		OBJECT-TYPE
			SYNTAX	INTEGER
			ACCESS	read-only
			STATUS	current
	DESCRIPTION ""
			::= { mbus26 30 }

mbus26Value0C		OBJECT-TYPE
			SYNTAX	INTEGER
			ACCESS	read-only
			STATUS	current
	DESCRIPTION ""
			::= { mbus26 31 }

mbus26VIF0D		OBJECT-TYPE
			SYNTAX	INTEGER
			ACCESS	read-only
			STATUS	current
	DESCRIPTION ""
			::= { mbus26 32 }

mbus26Value0D		OBJECT-TYPE
			SYNTAX	INTEGER
			ACCESS	read-only
			STATUS	current
	DESCRIPTION ""
			::= { mbus26 33 }

mbus26VIF0E		OBJECT-TYPE
			SYNTAX	INTEGER
			ACCESS	read-only
			STATUS	current
	DESCRIPTION ""
			::= { mbus26 34 }

mbus26Value0E		OBJECT-TYPE
			SYNTAX	INTEGER
			ACCESS	read-only
			STATUS	current
	DESCRIPTION ""
			::= { mbus26 35 }

mbus26VIF0F		OBJECT-TYPE
			SYNTAX	INTEGER
			ACCESS	read-only
			STATUS	current
	DESCRIPTION ""
			::= { mbus26 36 }

mbus26Value0F		OBJECT-TYPE
			SYNTAX	INTEGER
			ACCESS	read-only
			STATUS	current
	DESCRIPTION ""
			::= { mbus26 37 }

mbus26VIF10		OBJECT-TYPE
			SYNTAX	INTEGER
			ACCESS	read-only
			STATUS	current
	DESCRIPTION ""
			::= { mbus26 38 }

mbus26Value10		OBJECT-TYPE
			SYNTAX	INTEGER
			ACCESS	read-only
			STATUS	current
	DESCRIPTION ""
			::= { mbus26 39 }

mbus26VIF11		OBJECT-TYPE
			SYNTAX	INTEGER
			ACCESS	read-only
			STATUS	current
	DESCRIPTION ""
			::= { mbus26 40 }

mbus26Value11		OBJECT-TYPE
			SYNTAX	INTEGER
			ACCESS	read-only
			STATUS	current
	DESCRIPTION ""
			::= { mbus26 41 }

mbus26VIF12		OBJECT-TYPE
			SYNTAX	INTEGER
			ACCESS	read-only
			STATUS	current
	DESCRIPTION ""
			::= { mbus26 42 }

mbus26Value12		OBJECT-TYPE
			SYNTAX	INTEGER
			ACCESS	read-only
			STATUS	current
	DESCRIPTION ""
			::= { mbus26 43 }

mbus26VIF13		OBJECT-TYPE
			SYNTAX	INTEGER
			ACCESS	read-only
			STATUS	current
	DESCRIPTION ""
			::= { mbus26 44 }

mbus26Value13		OBJECT-TYPE
			SYNTAX	INTEGER
			ACCESS	read-only
			STATUS	current
	DESCRIPTION ""
			::= { mbus26 45 }

mbus26VIF14		OBJECT-TYPE
			SYNTAX	INTEGER
			ACCESS	read-only
			STATUS	current
	DESCRIPTION ""
			::= { mbus26 46 }

mbus26Value14		OBJECT-TYPE
			SYNTAX	INTEGER
			ACCESS	read-only
			STATUS	current
	DESCRIPTION ""
			::= { mbus26 47 }

mbus26VIF15		OBJECT-TYPE
			SYNTAX	INTEGER
			ACCESS	read-only
			STATUS	current
	DESCRIPTION ""
			::= { mbus26 48 }

mbus26Value15		OBJECT-TYPE
			SYNTAX	INTEGER
			ACCESS	read-only
			STATUS	current
	DESCRIPTION ""
			::= { mbus26 49 }

mbus26VIF16		OBJECT-TYPE
			SYNTAX	INTEGER
			ACCESS	read-only
			STATUS	current
	DESCRIPTION ""
			::= { mbus26 50 }

mbus26Value16		OBJECT-TYPE
			SYNTAX	INTEGER
			ACCESS	read-only
			STATUS	current
	DESCRIPTION ""
			::= { mbus26 51 }

mbus26VIF17		OBJECT-TYPE
			SYNTAX	INTEGER
			ACCESS	read-only
			STATUS	current
	DESCRIPTION ""
			::= { mbus26 52 }

mbus26Value17		OBJECT-TYPE
			SYNTAX	INTEGER
			ACCESS	read-only
			STATUS	current
	DESCRIPTION ""
			::= { mbus26 53 }

mbus26VIF18		OBJECT-TYPE
			SYNTAX	INTEGER
			ACCESS	read-only
			STATUS	current
	DESCRIPTION ""
			::= { mbus26 54 }

mbus26Value18		OBJECT-TYPE
			SYNTAX	INTEGER
			ACCESS	read-only
			STATUS	current
	DESCRIPTION ""
			::= { mbus26 55 }

mbus26VIF19		OBJECT-TYPE
			SYNTAX	INTEGER
			ACCESS	read-only
			STATUS	current
	DESCRIPTION ""
			::= { mbus26 56 }

mbus26Value19		OBJECT-TYPE
			SYNTAX	INTEGER
			ACCESS	read-only
			STATUS	current
	DESCRIPTION ""
			::= { mbus26 57 }

mbus26VIF1A		OBJECT-TYPE
			SYNTAX	INTEGER
			ACCESS	read-only
			STATUS	current
	DESCRIPTION ""
			::= { mbus26 58 }

mbus26Value1A		OBJECT-TYPE
			SYNTAX	INTEGER
			ACCESS	read-only
			STATUS	current
	DESCRIPTION ""
			::= { mbus26 59 }

mbus26VIF1B		OBJECT-TYPE
			SYNTAX	INTEGER
			ACCESS	read-only
			STATUS	current
	DESCRIPTION ""
			::= { mbus26 60 }

mbus26Value1B		OBJECT-TYPE
			SYNTAX	INTEGER
			ACCESS	read-only
			STATUS	current
	DESCRIPTION ""
			::= { mbus26 61 }

mbus26VIF1C		OBJECT-TYPE
			SYNTAX	INTEGER
			ACCESS	read-only
			STATUS	current
	DESCRIPTION ""
			::= { mbus26 62 }

mbus26Value1C		OBJECT-TYPE
			SYNTAX	INTEGER
			ACCESS	read-only
			STATUS	current
	DESCRIPTION ""
			::= { mbus26 63 }

mbus26VIF1D		OBJECT-TYPE
			SYNTAX	INTEGER
			ACCESS	read-only
			STATUS	current
	DESCRIPTION ""
			::= { mbus26 64 }

mbus26Value1D		OBJECT-TYPE
			SYNTAX	INTEGER
			ACCESS	read-only
			STATUS	current
	DESCRIPTION ""
			::= { mbus26 65 }

mbus26VIF1E		OBJECT-TYPE
			SYNTAX	INTEGER
			ACCESS	read-only
			STATUS	current
	DESCRIPTION ""
			::= { mbus26 66 }

mbus26Value1E		OBJECT-TYPE
			SYNTAX	INTEGER
			ACCESS	read-only
			STATUS	current
	DESCRIPTION ""
			::= { mbus26 67 }

mbus26VIF1F		OBJECT-TYPE
			SYNTAX	INTEGER
			ACCESS	read-only
			STATUS	current
	DESCRIPTION ""
			::= { mbus26 68 }

mbus26Value1F		OBJECT-TYPE
			SYNTAX	INTEGER
			ACCESS	read-only
			STATUS	current
	DESCRIPTION ""
			::= { mbus26 69 }

mbus26VIF20		OBJECT-TYPE
			SYNTAX	INTEGER
			ACCESS	read-only
			STATUS	current
	DESCRIPTION ""
			::= { mbus26 70 }

mbus26Value20		OBJECT-TYPE
			SYNTAX	INTEGER
			ACCESS	read-only
			STATUS	current
	DESCRIPTION ""
			::= { mbus26 71 }

mbus26VIF21		OBJECT-TYPE
			SYNTAX	INTEGER
			ACCESS	read-only
			STATUS	current
	DESCRIPTION ""
			::= { mbus26 72 }

mbus26Value21		OBJECT-TYPE
			SYNTAX	INTEGER
			ACCESS	read-only
			STATUS	current
	DESCRIPTION ""
			::= { mbus26 73 }

mbus26VIF22		OBJECT-TYPE
			SYNTAX	INTEGER
			ACCESS	read-only
			STATUS	current
	DESCRIPTION ""
			::= { mbus26 74 }

mbus26Value22		OBJECT-TYPE
			SYNTAX	INTEGER
			ACCESS	read-only
			STATUS	current
	DESCRIPTION ""
			::= { mbus26 75 }

mbus26VIF23		OBJECT-TYPE
			SYNTAX	INTEGER
			ACCESS	read-only
			STATUS	current
	DESCRIPTION ""
			::= { mbus26 76 }

mbus26Value23		OBJECT-TYPE
			SYNTAX	INTEGER
			ACCESS	read-only
			STATUS	current
	DESCRIPTION ""
			::= { mbus26 77 }

mbus26VIF24		OBJECT-TYPE
			SYNTAX	INTEGER
			ACCESS	read-only
			STATUS	current
	DESCRIPTION ""
			::= { mbus26 78 }

mbus26Value24		OBJECT-TYPE
			SYNTAX	INTEGER
			ACCESS	read-only
			STATUS	current
	DESCRIPTION ""
			::= { mbus26 79 }

mbus26VIF25		OBJECT-TYPE
			SYNTAX	INTEGER
			ACCESS	read-only
			STATUS	current
	DESCRIPTION ""
			::= { mbus26 80 }

mbus26Value25		OBJECT-TYPE
			SYNTAX	INTEGER
			ACCESS	read-only
			STATUS	current
	DESCRIPTION ""
			::= { mbus26 81 }

mbus26VIF26		OBJECT-TYPE
			SYNTAX	INTEGER
			ACCESS	read-only
			STATUS	current
	DESCRIPTION ""
			::= { mbus26 82 }

mbus26Value26		OBJECT-TYPE
			SYNTAX	INTEGER
			ACCESS	read-only
			STATUS	current
	DESCRIPTION ""
			::= { mbus26 83 }

mbus26VIF27		OBJECT-TYPE
			SYNTAX	INTEGER
			ACCESS	read-only
			STATUS	current
	DESCRIPTION ""
			::= { mbus26 84 }

mbus26Value27		OBJECT-TYPE
			SYNTAX	INTEGER
			ACCESS	read-only
			STATUS	current
	DESCRIPTION ""
			::= { mbus26 85 }

mbus26VIF28		OBJECT-TYPE
			SYNTAX	INTEGER
			ACCESS	read-only
			STATUS	current
	DESCRIPTION ""
			::= { mbus26 86 }

mbus26Value28		OBJECT-TYPE
			SYNTAX	INTEGER
			ACCESS	read-only
			STATUS	current
	DESCRIPTION ""
			::= { mbus26 87 }

mbus26VIF29		OBJECT-TYPE
			SYNTAX	INTEGER
			ACCESS	read-only
			STATUS	current
	DESCRIPTION ""
			::= { mbus26 88 }

mbus26Value29		OBJECT-TYPE
			SYNTAX	INTEGER
			ACCESS	read-only
			STATUS	current
	DESCRIPTION ""
			::= { mbus26 89 }

mbus26VIF2A		OBJECT-TYPE
			SYNTAX	INTEGER
			ACCESS	read-only
			STATUS	current
	DESCRIPTION ""
			::= { mbus26 90 }

mbus26Value2A		OBJECT-TYPE
			SYNTAX	INTEGER
			ACCESS	read-only
			STATUS	current
	DESCRIPTION ""
			::= { mbus26 91 }

mbus26VIF2B		OBJECT-TYPE
			SYNTAX	INTEGER
			ACCESS	read-only
			STATUS	current
	DESCRIPTION ""
			::= { mbus26 92 }

mbus26Value2B		OBJECT-TYPE
			SYNTAX	INTEGER
			ACCESS	read-only
			STATUS	current
	DESCRIPTION ""
			::= { mbus26 93 }

mbus26VIF2C		OBJECT-TYPE
			SYNTAX	INTEGER
			ACCESS	read-only
			STATUS	current
	DESCRIPTION ""
			::= { mbus26 94 }

mbus26Value2C		OBJECT-TYPE
			SYNTAX	INTEGER
			ACCESS	read-only
			STATUS	current
	DESCRIPTION ""
			::= { mbus26 95 }

mbus26VIF2D		OBJECT-TYPE
			SYNTAX	INTEGER
			ACCESS	read-only
			STATUS	current
	DESCRIPTION ""
			::= { mbus26 96 }

mbus26Value2D		OBJECT-TYPE
			SYNTAX	INTEGER
			ACCESS	read-only
			STATUS	current
	DESCRIPTION ""
			::= { mbus26 97 }

mbus26VIF2E		OBJECT-TYPE
			SYNTAX	INTEGER
			ACCESS	read-only
			STATUS	current
	DESCRIPTION ""
			::= { mbus26 98 }

mbus26Value2E		OBJECT-TYPE
			SYNTAX	INTEGER
			ACCESS	read-only
			STATUS	current
	DESCRIPTION ""
			::= { mbus26 99 }

mbus26VIF2F		OBJECT-TYPE
			SYNTAX	INTEGER
			ACCESS	read-only
			STATUS	current
	DESCRIPTION ""
			::= { mbus26 100 }

mbus26Value2F		OBJECT-TYPE
			SYNTAX	INTEGER
			ACCESS	read-only
			STATUS	current
	DESCRIPTION ""
			::= { mbus26 101 }

mbus27			OBJECT IDENTIFIER ::= { mbus 39 }

mbus27IdNumber		OBJECT-TYPE
			SYNTAX	Gauge
			ACCESS	read-only
			STATUS	current
	DESCRIPTION ""
			::= { mbus27 1 }

mbus27Manufacturer	OBJECT-TYPE
			SYNTAX	Gauge
			ACCESS	read-only
			STATUS	current
	DESCRIPTION ""
			::= { mbus27 2 }

mbus27Version		OBJECT-TYPE
			SYNTAX	Gauge
			ACCESS	read-only
			STATUS	current
	DESCRIPTION ""
			::= { mbus27 3 }

mbus27Medium		OBJECT-TYPE
			SYNTAX	Gauge
			ACCESS	read-only
			STATUS	current
	DESCRIPTION ""
			::= { mbus27 4 }

mbus27Status		OBJECT-TYPE
			SYNTAX	Gauge
			ACCESS	read-only
			STATUS	current
	DESCRIPTION ""
			::= { mbus27 5 }

mbus27VIF00		OBJECT-TYPE
			SYNTAX	INTEGER
			ACCESS	read-only
			STATUS	current
	DESCRIPTION ""
			::= { mbus27 6 }

mbus27Value00		OBJECT-TYPE
			SYNTAX	INTEGER
			ACCESS	read-only
			STATUS	current
	DESCRIPTION ""
			::= { mbus27 7 }

mbus27VIF01		OBJECT-TYPE
			SYNTAX	INTEGER
			ACCESS	read-only
			STATUS	current
	DESCRIPTION ""
			::= { mbus27 8 }

mbus27Value01		OBJECT-TYPE
			SYNTAX	INTEGER
			ACCESS	read-only
			STATUS	current
	DESCRIPTION ""
			::= { mbus27 9 }

mbus27VIF02		OBJECT-TYPE
			SYNTAX	INTEGER
			ACCESS	read-only
			STATUS	current
	DESCRIPTION ""
			::= { mbus27 10 }

mbus27Value02		OBJECT-TYPE
			SYNTAX	INTEGER
			ACCESS	read-only
			STATUS	current
	DESCRIPTION ""
			::= { mbus27 11 }

mbus27VIF03		OBJECT-TYPE
			SYNTAX	INTEGER
			ACCESS	read-only
			STATUS	current
	DESCRIPTION ""
			::= { mbus27 12 }

mbus27Value03		OBJECT-TYPE
			SYNTAX	INTEGER
			ACCESS	read-only
			STATUS	current
	DESCRIPTION ""
			::= { mbus27 13 }

mbus27VIF04		OBJECT-TYPE
			SYNTAX	INTEGER
			ACCESS	read-only
			STATUS	current
	DESCRIPTION ""
			::= { mbus27 14 }

mbus27Value04		OBJECT-TYPE
			SYNTAX	INTEGER
			ACCESS	read-only
			STATUS	current
	DESCRIPTION ""
			::= { mbus27 15 }

mbus27VIF05		OBJECT-TYPE
			SYNTAX	INTEGER
			ACCESS	read-only
			STATUS	current
	DESCRIPTION ""
			::= { mbus27 16 }

mbus27Value05		OBJECT-TYPE
			SYNTAX	INTEGER
			ACCESS	read-only
			STATUS	current
	DESCRIPTION ""
			::= { mbus27 17 }

mbus27VIF06		OBJECT-TYPE
			SYNTAX	INTEGER
			ACCESS	read-only
			STATUS	current
	DESCRIPTION ""
			::= { mbus27 18 }

mbus27Value06		OBJECT-TYPE
			SYNTAX	INTEGER
			ACCESS	read-only
			STATUS	current
	DESCRIPTION ""
			::= { mbus27 19 }

mbus27VIF07		OBJECT-TYPE
			SYNTAX	INTEGER
			ACCESS	read-only
			STATUS	current
	DESCRIPTION ""
			::= { mbus27 20 }

mbus27Value07		OBJECT-TYPE
			SYNTAX	INTEGER
			ACCESS	read-only
			STATUS	current
	DESCRIPTION ""
			::= { mbus27 21 }

mbus27VIF08		OBJECT-TYPE
			SYNTAX	INTEGER
			ACCESS	read-only
			STATUS	current
	DESCRIPTION ""
			::= { mbus27 22 }

mbus27Value08		OBJECT-TYPE
			SYNTAX	INTEGER
			ACCESS	read-only
			STATUS	current
	DESCRIPTION ""
			::= { mbus27 23 }

mbus27VIF09		OBJECT-TYPE
			SYNTAX	INTEGER
			ACCESS	read-only
			STATUS	current
	DESCRIPTION ""
			::= { mbus27 24 }

mbus27Value09		OBJECT-TYPE
			SYNTAX	INTEGER
			ACCESS	read-only
			STATUS	current
	DESCRIPTION ""
			::= { mbus27 25 }

mbus27VIF0A		OBJECT-TYPE
			SYNTAX	INTEGER
			ACCESS	read-only
			STATUS	current
	DESCRIPTION ""
			::= { mbus27 26 }

mbus27Value0A		OBJECT-TYPE
			SYNTAX	INTEGER
			ACCESS	read-only
			STATUS	current
	DESCRIPTION ""
			::= { mbus27 27 }

mbus27VIF0B		OBJECT-TYPE
			SYNTAX	INTEGER
			ACCESS	read-only
			STATUS	current
	DESCRIPTION ""
			::= { mbus27 28 }

mbus27Value0B		OBJECT-TYPE
			SYNTAX	INTEGER
			ACCESS	read-only
			STATUS	current
	DESCRIPTION ""
			::= { mbus27 29 }

mbus27VIF0C		OBJECT-TYPE
			SYNTAX	INTEGER
			ACCESS	read-only
			STATUS	current
	DESCRIPTION ""
			::= { mbus27 30 }

mbus27Value0C		OBJECT-TYPE
			SYNTAX	INTEGER
			ACCESS	read-only
			STATUS	current
	DESCRIPTION ""
			::= { mbus27 31 }

mbus27VIF0D		OBJECT-TYPE
			SYNTAX	INTEGER
			ACCESS	read-only
			STATUS	current
	DESCRIPTION ""
			::= { mbus27 32 }

mbus27Value0D		OBJECT-TYPE
			SYNTAX	INTEGER
			ACCESS	read-only
			STATUS	current
	DESCRIPTION ""
			::= { mbus27 33 }

mbus27VIF0E		OBJECT-TYPE
			SYNTAX	INTEGER
			ACCESS	read-only
			STATUS	current
	DESCRIPTION ""
			::= { mbus27 34 }

mbus27Value0E		OBJECT-TYPE
			SYNTAX	INTEGER
			ACCESS	read-only
			STATUS	current
	DESCRIPTION ""
			::= { mbus27 35 }

mbus27VIF0F		OBJECT-TYPE
			SYNTAX	INTEGER
			ACCESS	read-only
			STATUS	current
	DESCRIPTION ""
			::= { mbus27 36 }

mbus27Value0F		OBJECT-TYPE
			SYNTAX	INTEGER
			ACCESS	read-only
			STATUS	current
	DESCRIPTION ""
			::= { mbus27 37 }

mbus27VIF10		OBJECT-TYPE
			SYNTAX	INTEGER
			ACCESS	read-only
			STATUS	current
	DESCRIPTION ""
			::= { mbus27 38 }

mbus27Value10		OBJECT-TYPE
			SYNTAX	INTEGER
			ACCESS	read-only
			STATUS	current
	DESCRIPTION ""
			::= { mbus27 39 }

mbus27VIF11		OBJECT-TYPE
			SYNTAX	INTEGER
			ACCESS	read-only
			STATUS	current
	DESCRIPTION ""
			::= { mbus27 40 }

mbus27Value11		OBJECT-TYPE
			SYNTAX	INTEGER
			ACCESS	read-only
			STATUS	current
	DESCRIPTION ""
			::= { mbus27 41 }

mbus27VIF12		OBJECT-TYPE
			SYNTAX	INTEGER
			ACCESS	read-only
			STATUS	current
	DESCRIPTION ""
			::= { mbus27 42 }

mbus27Value12		OBJECT-TYPE
			SYNTAX	INTEGER
			ACCESS	read-only
			STATUS	current
	DESCRIPTION ""
			::= { mbus27 43 }

mbus27VIF13		OBJECT-TYPE
			SYNTAX	INTEGER
			ACCESS	read-only
			STATUS	current
	DESCRIPTION ""
			::= { mbus27 44 }

mbus27Value13		OBJECT-TYPE
			SYNTAX	INTEGER
			ACCESS	read-only
			STATUS	current
	DESCRIPTION ""
			::= { mbus27 45 }

mbus27VIF14		OBJECT-TYPE
			SYNTAX	INTEGER
			ACCESS	read-only
			STATUS	current
	DESCRIPTION ""
			::= { mbus27 46 }

mbus27Value14		OBJECT-TYPE
			SYNTAX	INTEGER
			ACCESS	read-only
			STATUS	current
	DESCRIPTION ""
			::= { mbus27 47 }

mbus27VIF15		OBJECT-TYPE
			SYNTAX	INTEGER
			ACCESS	read-only
			STATUS	current
	DESCRIPTION ""
			::= { mbus27 48 }

mbus27Value15		OBJECT-TYPE
			SYNTAX	INTEGER
			ACCESS	read-only
			STATUS	current
	DESCRIPTION ""
			::= { mbus27 49 }

mbus27VIF16		OBJECT-TYPE
			SYNTAX	INTEGER
			ACCESS	read-only
			STATUS	current
	DESCRIPTION ""
			::= { mbus27 50 }

mbus27Value16		OBJECT-TYPE
			SYNTAX	INTEGER
			ACCESS	read-only
			STATUS	current
	DESCRIPTION ""
			::= { mbus27 51 }

mbus27VIF17		OBJECT-TYPE
			SYNTAX	INTEGER
			ACCESS	read-only
			STATUS	current
	DESCRIPTION ""
			::= { mbus27 52 }

mbus27Value17		OBJECT-TYPE
			SYNTAX	INTEGER
			ACCESS	read-only
			STATUS	current
	DESCRIPTION ""
			::= { mbus27 53 }

mbus27VIF18		OBJECT-TYPE
			SYNTAX	INTEGER
			ACCESS	read-only
			STATUS	current
	DESCRIPTION ""
			::= { mbus27 54 }

mbus27Value18		OBJECT-TYPE
			SYNTAX	INTEGER
			ACCESS	read-only
			STATUS	current
	DESCRIPTION ""
			::= { mbus27 55 }

mbus27VIF19		OBJECT-TYPE
			SYNTAX	INTEGER
			ACCESS	read-only
			STATUS	current
	DESCRIPTION ""
			::= { mbus27 56 }

mbus27Value19		OBJECT-TYPE
			SYNTAX	INTEGER
			ACCESS	read-only
			STATUS	current
	DESCRIPTION ""
			::= { mbus27 57 }

mbus27VIF1A		OBJECT-TYPE
			SYNTAX	INTEGER
			ACCESS	read-only
			STATUS	current
	DESCRIPTION ""
			::= { mbus27 58 }

mbus27Value1A		OBJECT-TYPE
			SYNTAX	INTEGER
			ACCESS	read-only
			STATUS	current
	DESCRIPTION ""
			::= { mbus27 59 }

mbus27VIF1B		OBJECT-TYPE
			SYNTAX	INTEGER
			ACCESS	read-only
			STATUS	current
	DESCRIPTION ""
			::= { mbus27 60 }

mbus27Value1B		OBJECT-TYPE
			SYNTAX	INTEGER
			ACCESS	read-only
			STATUS	current
	DESCRIPTION ""
			::= { mbus27 61 }

mbus27VIF1C		OBJECT-TYPE
			SYNTAX	INTEGER
			ACCESS	read-only
			STATUS	current
	DESCRIPTION ""
			::= { mbus27 62 }

mbus27Value1C		OBJECT-TYPE
			SYNTAX	INTEGER
			ACCESS	read-only
			STATUS	current
	DESCRIPTION ""
			::= { mbus27 63 }

mbus27VIF1D		OBJECT-TYPE
			SYNTAX	INTEGER
			ACCESS	read-only
			STATUS	current
	DESCRIPTION ""
			::= { mbus27 64 }

mbus27Value1D		OBJECT-TYPE
			SYNTAX	INTEGER
			ACCESS	read-only
			STATUS	current
	DESCRIPTION ""
			::= { mbus27 65 }

mbus27VIF1E		OBJECT-TYPE
			SYNTAX	INTEGER
			ACCESS	read-only
			STATUS	current
	DESCRIPTION ""
			::= { mbus27 66 }

mbus27Value1E		OBJECT-TYPE
			SYNTAX	INTEGER
			ACCESS	read-only
			STATUS	current
	DESCRIPTION ""
			::= { mbus27 67 }

mbus27VIF1F		OBJECT-TYPE
			SYNTAX	INTEGER
			ACCESS	read-only
			STATUS	current
	DESCRIPTION ""
			::= { mbus27 68 }

mbus27Value1F		OBJECT-TYPE
			SYNTAX	INTEGER
			ACCESS	read-only
			STATUS	current
	DESCRIPTION ""
			::= { mbus27 69 }

mbus27VIF20		OBJECT-TYPE
			SYNTAX	INTEGER
			ACCESS	read-only
			STATUS	current
	DESCRIPTION ""
			::= { mbus27 70 }

mbus27Value20		OBJECT-TYPE
			SYNTAX	INTEGER
			ACCESS	read-only
			STATUS	current
	DESCRIPTION ""
			::= { mbus27 71 }

mbus27VIF21		OBJECT-TYPE
			SYNTAX	INTEGER
			ACCESS	read-only
			STATUS	current
	DESCRIPTION ""
			::= { mbus27 72 }

mbus27Value21		OBJECT-TYPE
			SYNTAX	INTEGER
			ACCESS	read-only
			STATUS	current
	DESCRIPTION ""
			::= { mbus27 73 }

mbus27VIF22		OBJECT-TYPE
			SYNTAX	INTEGER
			ACCESS	read-only
			STATUS	current
	DESCRIPTION ""
			::= { mbus27 74 }

mbus27Value22		OBJECT-TYPE
			SYNTAX	INTEGER
			ACCESS	read-only
			STATUS	current
	DESCRIPTION ""
			::= { mbus27 75 }

mbus27VIF23		OBJECT-TYPE
			SYNTAX	INTEGER
			ACCESS	read-only
			STATUS	current
	DESCRIPTION ""
			::= { mbus27 76 }

mbus27Value23		OBJECT-TYPE
			SYNTAX	INTEGER
			ACCESS	read-only
			STATUS	current
	DESCRIPTION ""
			::= { mbus27 77 }

mbus27VIF24		OBJECT-TYPE
			SYNTAX	INTEGER
			ACCESS	read-only
			STATUS	current
	DESCRIPTION ""
			::= { mbus27 78 }

mbus27Value24		OBJECT-TYPE
			SYNTAX	INTEGER
			ACCESS	read-only
			STATUS	current
	DESCRIPTION ""
			::= { mbus27 79 }

mbus27VIF25		OBJECT-TYPE
			SYNTAX	INTEGER
			ACCESS	read-only
			STATUS	current
	DESCRIPTION ""
			::= { mbus27 80 }

mbus27Value25		OBJECT-TYPE
			SYNTAX	INTEGER
			ACCESS	read-only
			STATUS	current
	DESCRIPTION ""
			::= { mbus27 81 }

mbus27VIF26		OBJECT-TYPE
			SYNTAX	INTEGER
			ACCESS	read-only
			STATUS	current
	DESCRIPTION ""
			::= { mbus27 82 }

mbus27Value26		OBJECT-TYPE
			SYNTAX	INTEGER
			ACCESS	read-only
			STATUS	current
	DESCRIPTION ""
			::= { mbus27 83 }

mbus27VIF27		OBJECT-TYPE
			SYNTAX	INTEGER
			ACCESS	read-only
			STATUS	current
	DESCRIPTION ""
			::= { mbus27 84 }

mbus27Value27		OBJECT-TYPE
			SYNTAX	INTEGER
			ACCESS	read-only
			STATUS	current
	DESCRIPTION ""
			::= { mbus27 85 }

mbus27VIF28		OBJECT-TYPE
			SYNTAX	INTEGER
			ACCESS	read-only
			STATUS	current
	DESCRIPTION ""
			::= { mbus27 86 }

mbus27Value28		OBJECT-TYPE
			SYNTAX	INTEGER
			ACCESS	read-only
			STATUS	current
	DESCRIPTION ""
			::= { mbus27 87 }

mbus27VIF29		OBJECT-TYPE
			SYNTAX	INTEGER
			ACCESS	read-only
			STATUS	current
	DESCRIPTION ""
			::= { mbus27 88 }

mbus27Value29		OBJECT-TYPE
			SYNTAX	INTEGER
			ACCESS	read-only
			STATUS	current
	DESCRIPTION ""
			::= { mbus27 89 }

mbus27VIF2A		OBJECT-TYPE
			SYNTAX	INTEGER
			ACCESS	read-only
			STATUS	current
	DESCRIPTION ""
			::= { mbus27 90 }

mbus27Value2A		OBJECT-TYPE
			SYNTAX	INTEGER
			ACCESS	read-only
			STATUS	current
	DESCRIPTION ""
			::= { mbus27 91 }

mbus27VIF2B		OBJECT-TYPE
			SYNTAX	INTEGER
			ACCESS	read-only
			STATUS	current
	DESCRIPTION ""
			::= { mbus27 92 }

mbus27Value2B		OBJECT-TYPE
			SYNTAX	INTEGER
			ACCESS	read-only
			STATUS	current
	DESCRIPTION ""
			::= { mbus27 93 }

mbus27VIF2C		OBJECT-TYPE
			SYNTAX	INTEGER
			ACCESS	read-only
			STATUS	current
	DESCRIPTION ""
			::= { mbus27 94 }

mbus27Value2C		OBJECT-TYPE
			SYNTAX	INTEGER
			ACCESS	read-only
			STATUS	current
	DESCRIPTION ""
			::= { mbus27 95 }

mbus27VIF2D		OBJECT-TYPE
			SYNTAX	INTEGER
			ACCESS	read-only
			STATUS	current
	DESCRIPTION ""
			::= { mbus27 96 }

mbus27Value2D		OBJECT-TYPE
			SYNTAX	INTEGER
			ACCESS	read-only
			STATUS	current
	DESCRIPTION ""
			::= { mbus27 97 }

mbus27VIF2E		OBJECT-TYPE
			SYNTAX	INTEGER
			ACCESS	read-only
			STATUS	current
	DESCRIPTION ""
			::= { mbus27 98 }

mbus27Value2E		OBJECT-TYPE
			SYNTAX	INTEGER
			ACCESS	read-only
			STATUS	current
	DESCRIPTION ""
			::= { mbus27 99 }

mbus27VIF2F		OBJECT-TYPE
			SYNTAX	INTEGER
			ACCESS	read-only
			STATUS	current
	DESCRIPTION ""
			::= { mbus27 100 }

mbus27Value2F		OBJECT-TYPE
			SYNTAX	INTEGER
			ACCESS	read-only
			STATUS	current
	DESCRIPTION ""
			::= { mbus27 101 }

mbus28			OBJECT IDENTIFIER ::= { mbus 40 }

mbus28IdNumber		OBJECT-TYPE
			SYNTAX	Gauge
			ACCESS	read-only
			STATUS	current
	DESCRIPTION ""
			::= { mbus28 1 }

mbus28Manufacturer	OBJECT-TYPE
			SYNTAX	Gauge
			ACCESS	read-only
			STATUS	current
	DESCRIPTION ""
			::= { mbus28 2 }

mbus28Version		OBJECT-TYPE
			SYNTAX	Gauge
			ACCESS	read-only
			STATUS	current
	DESCRIPTION ""
			::= { mbus28 3 }

mbus28Medium		OBJECT-TYPE
			SYNTAX	Gauge
			ACCESS	read-only
			STATUS	current
	DESCRIPTION ""
			::= { mbus28 4 }

mbus28Status		OBJECT-TYPE
			SYNTAX	Gauge
			ACCESS	read-only
			STATUS	current
	DESCRIPTION ""
			::= { mbus28 5 }

mbus28VIF00		OBJECT-TYPE
			SYNTAX	INTEGER
			ACCESS	read-only
			STATUS	current
	DESCRIPTION ""
			::= { mbus28 6 }

mbus28Value00		OBJECT-TYPE
			SYNTAX	INTEGER
			ACCESS	read-only
			STATUS	current
	DESCRIPTION ""
			::= { mbus28 7 }

mbus28VIF01		OBJECT-TYPE
			SYNTAX	INTEGER
			ACCESS	read-only
			STATUS	current
	DESCRIPTION ""
			::= { mbus28 8 }

mbus28Value01		OBJECT-TYPE
			SYNTAX	INTEGER
			ACCESS	read-only
			STATUS	current
	DESCRIPTION ""
			::= { mbus28 9 }

mbus28VIF02		OBJECT-TYPE
			SYNTAX	INTEGER
			ACCESS	read-only
			STATUS	current
	DESCRIPTION ""
			::= { mbus28 10 }

mbus28Value02		OBJECT-TYPE
			SYNTAX	INTEGER
			ACCESS	read-only
			STATUS	current
	DESCRIPTION ""
			::= { mbus28 11 }

mbus28VIF03		OBJECT-TYPE
			SYNTAX	INTEGER
			ACCESS	read-only
			STATUS	current
	DESCRIPTION ""
			::= { mbus28 12 }

mbus28Value03		OBJECT-TYPE
			SYNTAX	INTEGER
			ACCESS	read-only
			STATUS	current
	DESCRIPTION ""
			::= { mbus28 13 }

mbus28VIF04		OBJECT-TYPE
			SYNTAX	INTEGER
			ACCESS	read-only
			STATUS	current
	DESCRIPTION ""
			::= { mbus28 14 }

mbus28Value04		OBJECT-TYPE
			SYNTAX	INTEGER
			ACCESS	read-only
			STATUS	current
	DESCRIPTION ""
			::= { mbus28 15 }

mbus28VIF05		OBJECT-TYPE
			SYNTAX	INTEGER
			ACCESS	read-only
			STATUS	current
	DESCRIPTION ""
			::= { mbus28 16 }

mbus28Value05		OBJECT-TYPE
			SYNTAX	INTEGER
			ACCESS	read-only
			STATUS	current
	DESCRIPTION ""
			::= { mbus28 17 }

mbus28VIF06		OBJECT-TYPE
			SYNTAX	INTEGER
			ACCESS	read-only
			STATUS	current
	DESCRIPTION ""
			::= { mbus28 18 }

mbus28Value06		OBJECT-TYPE
			SYNTAX	INTEGER
			ACCESS	read-only
			STATUS	current
	DESCRIPTION ""
			::= { mbus28 19 }

mbus28VIF07		OBJECT-TYPE
			SYNTAX	INTEGER
			ACCESS	read-only
			STATUS	current
	DESCRIPTION ""
			::= { mbus28 20 }

mbus28Value07		OBJECT-TYPE
			SYNTAX	INTEGER
			ACCESS	read-only
			STATUS	current
	DESCRIPTION ""
			::= { mbus28 21 }

mbus28VIF08		OBJECT-TYPE
			SYNTAX	INTEGER
			ACCESS	read-only
			STATUS	current
	DESCRIPTION ""
			::= { mbus28 22 }

mbus28Value08		OBJECT-TYPE
			SYNTAX	INTEGER
			ACCESS	read-only
			STATUS	current
	DESCRIPTION ""
			::= { mbus28 23 }

mbus28VIF09		OBJECT-TYPE
			SYNTAX	INTEGER
			ACCESS	read-only
			STATUS	current
	DESCRIPTION ""
			::= { mbus28 24 }

mbus28Value09		OBJECT-TYPE
			SYNTAX	INTEGER
			ACCESS	read-only
			STATUS	current
	DESCRIPTION ""
			::= { mbus28 25 }

mbus28VIF0A		OBJECT-TYPE
			SYNTAX	INTEGER
			ACCESS	read-only
			STATUS	current
	DESCRIPTION ""
			::= { mbus28 26 }

mbus28Value0A		OBJECT-TYPE
			SYNTAX	INTEGER
			ACCESS	read-only
			STATUS	current
	DESCRIPTION ""
			::= { mbus28 27 }

mbus28VIF0B		OBJECT-TYPE
			SYNTAX	INTEGER
			ACCESS	read-only
			STATUS	current
	DESCRIPTION ""
			::= { mbus28 28 }

mbus28Value0B		OBJECT-TYPE
			SYNTAX	INTEGER
			ACCESS	read-only
			STATUS	current
	DESCRIPTION ""
			::= { mbus28 29 }

mbus28VIF0C		OBJECT-TYPE
			SYNTAX	INTEGER
			ACCESS	read-only
			STATUS	current
	DESCRIPTION ""
			::= { mbus28 30 }

mbus28Value0C		OBJECT-TYPE
			SYNTAX	INTEGER
			ACCESS	read-only
			STATUS	current
	DESCRIPTION ""
			::= { mbus28 31 }

mbus28VIF0D		OBJECT-TYPE
			SYNTAX	INTEGER
			ACCESS	read-only
			STATUS	current
	DESCRIPTION ""
			::= { mbus28 32 }

mbus28Value0D		OBJECT-TYPE
			SYNTAX	INTEGER
			ACCESS	read-only
			STATUS	current
	DESCRIPTION ""
			::= { mbus28 33 }

mbus28VIF0E		OBJECT-TYPE
			SYNTAX	INTEGER
			ACCESS	read-only
			STATUS	current
	DESCRIPTION ""
			::= { mbus28 34 }

mbus28Value0E		OBJECT-TYPE
			SYNTAX	INTEGER
			ACCESS	read-only
			STATUS	current
	DESCRIPTION ""
			::= { mbus28 35 }

mbus28VIF0F		OBJECT-TYPE
			SYNTAX	INTEGER
			ACCESS	read-only
			STATUS	current
	DESCRIPTION ""
			::= { mbus28 36 }

mbus28Value0F		OBJECT-TYPE
			SYNTAX	INTEGER
			ACCESS	read-only
			STATUS	current
	DESCRIPTION ""
			::= { mbus28 37 }

mbus28VIF10		OBJECT-TYPE
			SYNTAX	INTEGER
			ACCESS	read-only
			STATUS	current
	DESCRIPTION ""
			::= { mbus28 38 }

mbus28Value10		OBJECT-TYPE
			SYNTAX	INTEGER
			ACCESS	read-only
			STATUS	current
	DESCRIPTION ""
			::= { mbus28 39 }

mbus28VIF11		OBJECT-TYPE
			SYNTAX	INTEGER
			ACCESS	read-only
			STATUS	current
	DESCRIPTION ""
			::= { mbus28 40 }

mbus28Value11		OBJECT-TYPE
			SYNTAX	INTEGER
			ACCESS	read-only
			STATUS	current
	DESCRIPTION ""
			::= { mbus28 41 }

mbus28VIF12		OBJECT-TYPE
			SYNTAX	INTEGER
			ACCESS	read-only
			STATUS	current
	DESCRIPTION ""
			::= { mbus28 42 }

mbus28Value12		OBJECT-TYPE
			SYNTAX	INTEGER
			ACCESS	read-only
			STATUS	current
	DESCRIPTION ""
			::= { mbus28 43 }

mbus28VIF13		OBJECT-TYPE
			SYNTAX	INTEGER
			ACCESS	read-only
			STATUS	current
	DESCRIPTION ""
			::= { mbus28 44 }

mbus28Value13		OBJECT-TYPE
			SYNTAX	INTEGER
			ACCESS	read-only
			STATUS	current
	DESCRIPTION ""
			::= { mbus28 45 }

mbus28VIF14		OBJECT-TYPE
			SYNTAX	INTEGER
			ACCESS	read-only
			STATUS	current
	DESCRIPTION ""
			::= { mbus28 46 }

mbus28Value14		OBJECT-TYPE
			SYNTAX	INTEGER
			ACCESS	read-only
			STATUS	current
	DESCRIPTION ""
			::= { mbus28 47 }

mbus28VIF15		OBJECT-TYPE
			SYNTAX	INTEGER
			ACCESS	read-only
			STATUS	current
	DESCRIPTION ""
			::= { mbus28 48 }

mbus28Value15		OBJECT-TYPE
			SYNTAX	INTEGER
			ACCESS	read-only
			STATUS	current
	DESCRIPTION ""
			::= { mbus28 49 }

mbus28VIF16		OBJECT-TYPE
			SYNTAX	INTEGER
			ACCESS	read-only
			STATUS	current
	DESCRIPTION ""
			::= { mbus28 50 }

mbus28Value16		OBJECT-TYPE
			SYNTAX	INTEGER
			ACCESS	read-only
			STATUS	current
	DESCRIPTION ""
			::= { mbus28 51 }

mbus28VIF17		OBJECT-TYPE
			SYNTAX	INTEGER
			ACCESS	read-only
			STATUS	current
	DESCRIPTION ""
			::= { mbus28 52 }

mbus28Value17		OBJECT-TYPE
			SYNTAX	INTEGER
			ACCESS	read-only
			STATUS	current
	DESCRIPTION ""
			::= { mbus28 53 }

mbus28VIF18		OBJECT-TYPE
			SYNTAX	INTEGER
			ACCESS	read-only
			STATUS	current
	DESCRIPTION ""
			::= { mbus28 54 }

mbus28Value18		OBJECT-TYPE
			SYNTAX	INTEGER
			ACCESS	read-only
			STATUS	current
	DESCRIPTION ""
			::= { mbus28 55 }

mbus28VIF19		OBJECT-TYPE
			SYNTAX	INTEGER
			ACCESS	read-only
			STATUS	current
	DESCRIPTION ""
			::= { mbus28 56 }

mbus28Value19		OBJECT-TYPE
			SYNTAX	INTEGER
			ACCESS	read-only
			STATUS	current
	DESCRIPTION ""
			::= { mbus28 57 }

mbus28VIF1A		OBJECT-TYPE
			SYNTAX	INTEGER
			ACCESS	read-only
			STATUS	current
	DESCRIPTION ""
			::= { mbus28 58 }

mbus28Value1A		OBJECT-TYPE
			SYNTAX	INTEGER
			ACCESS	read-only
			STATUS	current
	DESCRIPTION ""
			::= { mbus28 59 }

mbus28VIF1B		OBJECT-TYPE
			SYNTAX	INTEGER
			ACCESS	read-only
			STATUS	current
	DESCRIPTION ""
			::= { mbus28 60 }

mbus28Value1B		OBJECT-TYPE
			SYNTAX	INTEGER
			ACCESS	read-only
			STATUS	current
	DESCRIPTION ""
			::= { mbus28 61 }

mbus28VIF1C		OBJECT-TYPE
			SYNTAX	INTEGER
			ACCESS	read-only
			STATUS	current
	DESCRIPTION ""
			::= { mbus28 62 }

mbus28Value1C		OBJECT-TYPE
			SYNTAX	INTEGER
			ACCESS	read-only
			STATUS	current
	DESCRIPTION ""
			::= { mbus28 63 }

mbus28VIF1D		OBJECT-TYPE
			SYNTAX	INTEGER
			ACCESS	read-only
			STATUS	current
	DESCRIPTION ""
			::= { mbus28 64 }

mbus28Value1D		OBJECT-TYPE
			SYNTAX	INTEGER
			ACCESS	read-only
			STATUS	current
	DESCRIPTION ""
			::= { mbus28 65 }

mbus28VIF1E		OBJECT-TYPE
			SYNTAX	INTEGER
			ACCESS	read-only
			STATUS	current
	DESCRIPTION ""
			::= { mbus28 66 }

mbus28Value1E		OBJECT-TYPE
			SYNTAX	INTEGER
			ACCESS	read-only
			STATUS	current
	DESCRIPTION ""
			::= { mbus28 67 }

mbus28VIF1F		OBJECT-TYPE
			SYNTAX	INTEGER
			ACCESS	read-only
			STATUS	current
	DESCRIPTION ""
			::= { mbus28 68 }

mbus28Value1F		OBJECT-TYPE
			SYNTAX	INTEGER
			ACCESS	read-only
			STATUS	current
	DESCRIPTION ""
			::= { mbus28 69 }

mbus28VIF20		OBJECT-TYPE
			SYNTAX	INTEGER
			ACCESS	read-only
			STATUS	current
	DESCRIPTION ""
			::= { mbus28 70 }

mbus28Value20		OBJECT-TYPE
			SYNTAX	INTEGER
			ACCESS	read-only
			STATUS	current
	DESCRIPTION ""
			::= { mbus28 71 }

mbus28VIF21		OBJECT-TYPE
			SYNTAX	INTEGER
			ACCESS	read-only
			STATUS	current
	DESCRIPTION ""
			::= { mbus28 72 }

mbus28Value21		OBJECT-TYPE
			SYNTAX	INTEGER
			ACCESS	read-only
			STATUS	current
	DESCRIPTION ""
			::= { mbus28 73 }

mbus28VIF22		OBJECT-TYPE
			SYNTAX	INTEGER
			ACCESS	read-only
			STATUS	current
	DESCRIPTION ""
			::= { mbus28 74 }

mbus28Value22		OBJECT-TYPE
			SYNTAX	INTEGER
			ACCESS	read-only
			STATUS	current
	DESCRIPTION ""
			::= { mbus28 75 }

mbus28VIF23		OBJECT-TYPE
			SYNTAX	INTEGER
			ACCESS	read-only
			STATUS	current
	DESCRIPTION ""
			::= { mbus28 76 }

mbus28Value23		OBJECT-TYPE
			SYNTAX	INTEGER
			ACCESS	read-only
			STATUS	current
	DESCRIPTION ""
			::= { mbus28 77 }

mbus28VIF24		OBJECT-TYPE
			SYNTAX	INTEGER
			ACCESS	read-only
			STATUS	current
	DESCRIPTION ""
			::= { mbus28 78 }

mbus28Value24		OBJECT-TYPE
			SYNTAX	INTEGER
			ACCESS	read-only
			STATUS	current
	DESCRIPTION ""
			::= { mbus28 79 }

mbus28VIF25		OBJECT-TYPE
			SYNTAX	INTEGER
			ACCESS	read-only
			STATUS	current
	DESCRIPTION ""
			::= { mbus28 80 }

mbus28Value25		OBJECT-TYPE
			SYNTAX	INTEGER
			ACCESS	read-only
			STATUS	current
	DESCRIPTION ""
			::= { mbus28 81 }

mbus28VIF26		OBJECT-TYPE
			SYNTAX	INTEGER
			ACCESS	read-only
			STATUS	current
	DESCRIPTION ""
			::= { mbus28 82 }

mbus28Value26		OBJECT-TYPE
			SYNTAX	INTEGER
			ACCESS	read-only
			STATUS	current
	DESCRIPTION ""
			::= { mbus28 83 }

mbus28VIF27		OBJECT-TYPE
			SYNTAX	INTEGER
			ACCESS	read-only
			STATUS	current
	DESCRIPTION ""
			::= { mbus28 84 }

mbus28Value27		OBJECT-TYPE
			SYNTAX	INTEGER
			ACCESS	read-only
			STATUS	current
	DESCRIPTION ""
			::= { mbus28 85 }

mbus28VIF28		OBJECT-TYPE
			SYNTAX	INTEGER
			ACCESS	read-only
			STATUS	current
	DESCRIPTION ""
			::= { mbus28 86 }

mbus28Value28		OBJECT-TYPE
			SYNTAX	INTEGER
			ACCESS	read-only
			STATUS	current
	DESCRIPTION ""
			::= { mbus28 87 }

mbus28VIF29		OBJECT-TYPE
			SYNTAX	INTEGER
			ACCESS	read-only
			STATUS	current
	DESCRIPTION ""
			::= { mbus28 88 }

mbus28Value29		OBJECT-TYPE
			SYNTAX	INTEGER
			ACCESS	read-only
			STATUS	current
	DESCRIPTION ""
			::= { mbus28 89 }

mbus28VIF2A		OBJECT-TYPE
			SYNTAX	INTEGER
			ACCESS	read-only
			STATUS	current
	DESCRIPTION ""
			::= { mbus28 90 }

mbus28Value2A		OBJECT-TYPE
			SYNTAX	INTEGER
			ACCESS	read-only
			STATUS	current
	DESCRIPTION ""
			::= { mbus28 91 }

mbus28VIF2B		OBJECT-TYPE
			SYNTAX	INTEGER
			ACCESS	read-only
			STATUS	current
	DESCRIPTION ""
			::= { mbus28 92 }

mbus28Value2B		OBJECT-TYPE
			SYNTAX	INTEGER
			ACCESS	read-only
			STATUS	current
	DESCRIPTION ""
			::= { mbus28 93 }

mbus28VIF2C		OBJECT-TYPE
			SYNTAX	INTEGER
			ACCESS	read-only
			STATUS	current
	DESCRIPTION ""
			::= { mbus28 94 }

mbus28Value2C		OBJECT-TYPE
			SYNTAX	INTEGER
			ACCESS	read-only
			STATUS	current
	DESCRIPTION ""
			::= { mbus28 95 }

mbus28VIF2D		OBJECT-TYPE
			SYNTAX	INTEGER
			ACCESS	read-only
			STATUS	current
	DESCRIPTION ""
			::= { mbus28 96 }

mbus28Value2D		OBJECT-TYPE
			SYNTAX	INTEGER
			ACCESS	read-only
			STATUS	current
	DESCRIPTION ""
			::= { mbus28 97 }

mbus28VIF2E		OBJECT-TYPE
			SYNTAX	INTEGER
			ACCESS	read-only
			STATUS	current
	DESCRIPTION ""
			::= { mbus28 98 }

mbus28Value2E		OBJECT-TYPE
			SYNTAX	INTEGER
			ACCESS	read-only
			STATUS	current
	DESCRIPTION ""
			::= { mbus28 99 }

mbus28VIF2F		OBJECT-TYPE
			SYNTAX	INTEGER
			ACCESS	read-only
			STATUS	current
	DESCRIPTION ""
			::= { mbus28 100 }

mbus28Value2F		OBJECT-TYPE
			SYNTAX	INTEGER
			ACCESS	read-only
			STATUS	current
	DESCRIPTION ""
			::= { mbus28 101 }

mbus29			OBJECT IDENTIFIER ::= { mbus 41 }

mbus29IdNumber		OBJECT-TYPE
			SYNTAX	Gauge
			ACCESS	read-only
			STATUS	current
	DESCRIPTION ""
			::= { mbus29 1 }

mbus29Manufacturer	OBJECT-TYPE
			SYNTAX	Gauge
			ACCESS	read-only
			STATUS	current
	DESCRIPTION ""
			::= { mbus29 2 }

mbus29Version		OBJECT-TYPE
			SYNTAX	Gauge
			ACCESS	read-only
			STATUS	current
	DESCRIPTION ""
			::= { mbus29 3 }

mbus29Medium		OBJECT-TYPE
			SYNTAX	Gauge
			ACCESS	read-only
			STATUS	current
	DESCRIPTION ""
			::= { mbus29 4 }

mbus29Status		OBJECT-TYPE
			SYNTAX	Gauge
			ACCESS	read-only
			STATUS	current
	DESCRIPTION ""
			::= { mbus29 5 }

mbus29VIF00		OBJECT-TYPE
			SYNTAX	INTEGER
			ACCESS	read-only
			STATUS	current
	DESCRIPTION ""
			::= { mbus29 6 }

mbus29Value00		OBJECT-TYPE
			SYNTAX	INTEGER
			ACCESS	read-only
			STATUS	current
	DESCRIPTION ""
			::= { mbus29 7 }

mbus29VIF01		OBJECT-TYPE
			SYNTAX	INTEGER
			ACCESS	read-only
			STATUS	current
	DESCRIPTION ""
			::= { mbus29 8 }

mbus29Value01		OBJECT-TYPE
			SYNTAX	INTEGER
			ACCESS	read-only
			STATUS	current
	DESCRIPTION ""
			::= { mbus29 9 }

mbus29VIF02		OBJECT-TYPE
			SYNTAX	INTEGER
			ACCESS	read-only
			STATUS	current
	DESCRIPTION ""
			::= { mbus29 10 }

mbus29Value02		OBJECT-TYPE
			SYNTAX	INTEGER
			ACCESS	read-only
			STATUS	current
	DESCRIPTION ""
			::= { mbus29 11 }

mbus29VIF03		OBJECT-TYPE
			SYNTAX	INTEGER
			ACCESS	read-only
			STATUS	current
	DESCRIPTION ""
			::= { mbus29 12 }

mbus29Value03		OBJECT-TYPE
			SYNTAX	INTEGER
			ACCESS	read-only
			STATUS	current
	DESCRIPTION ""
			::= { mbus29 13 }

mbus29VIF04		OBJECT-TYPE
			SYNTAX	INTEGER
			ACCESS	read-only
			STATUS	current
	DESCRIPTION ""
			::= { mbus29 14 }

mbus29Value04		OBJECT-TYPE
			SYNTAX	INTEGER
			ACCESS	read-only
			STATUS	current
	DESCRIPTION ""
			::= { mbus29 15 }

mbus29VIF05		OBJECT-TYPE
			SYNTAX	INTEGER
			ACCESS	read-only
			STATUS	current
	DESCRIPTION ""
			::= { mbus29 16 }

mbus29Value05		OBJECT-TYPE
			SYNTAX	INTEGER
			ACCESS	read-only
			STATUS	current
	DESCRIPTION ""
			::= { mbus29 17 }

mbus29VIF06		OBJECT-TYPE
			SYNTAX	INTEGER
			ACCESS	read-only
			STATUS	current
	DESCRIPTION ""
			::= { mbus29 18 }

mbus29Value06		OBJECT-TYPE
			SYNTAX	INTEGER
			ACCESS	read-only
			STATUS	current
	DESCRIPTION ""
			::= { mbus29 19 }

mbus29VIF07		OBJECT-TYPE
			SYNTAX	INTEGER
			ACCESS	read-only
			STATUS	current
	DESCRIPTION ""
			::= { mbus29 20 }

mbus29Value07		OBJECT-TYPE
			SYNTAX	INTEGER
			ACCESS	read-only
			STATUS	current
	DESCRIPTION ""
			::= { mbus29 21 }

mbus29VIF08		OBJECT-TYPE
			SYNTAX	INTEGER
			ACCESS	read-only
			STATUS	current
	DESCRIPTION ""
			::= { mbus29 22 }

mbus29Value08		OBJECT-TYPE
			SYNTAX	INTEGER
			ACCESS	read-only
			STATUS	current
	DESCRIPTION ""
			::= { mbus29 23 }

mbus29VIF09		OBJECT-TYPE
			SYNTAX	INTEGER
			ACCESS	read-only
			STATUS	current
	DESCRIPTION ""
			::= { mbus29 24 }

mbus29Value09		OBJECT-TYPE
			SYNTAX	INTEGER
			ACCESS	read-only
			STATUS	current
	DESCRIPTION ""
			::= { mbus29 25 }

mbus29VIF0A		OBJECT-TYPE
			SYNTAX	INTEGER
			ACCESS	read-only
			STATUS	current
	DESCRIPTION ""
			::= { mbus29 26 }

mbus29Value0A		OBJECT-TYPE
			SYNTAX	INTEGER
			ACCESS	read-only
			STATUS	current
	DESCRIPTION ""
			::= { mbus29 27 }

mbus29VIF0B		OBJECT-TYPE
			SYNTAX	INTEGER
			ACCESS	read-only
			STATUS	current
	DESCRIPTION ""
			::= { mbus29 28 }

mbus29Value0B		OBJECT-TYPE
			SYNTAX	INTEGER
			ACCESS	read-only
			STATUS	current
	DESCRIPTION ""
			::= { mbus29 29 }

mbus29VIF0C		OBJECT-TYPE
			SYNTAX	INTEGER
			ACCESS	read-only
			STATUS	current
	DESCRIPTION ""
			::= { mbus29 30 }

mbus29Value0C		OBJECT-TYPE
			SYNTAX	INTEGER
			ACCESS	read-only
			STATUS	current
	DESCRIPTION ""
			::= { mbus29 31 }

mbus29VIF0D		OBJECT-TYPE
			SYNTAX	INTEGER
			ACCESS	read-only
			STATUS	current
	DESCRIPTION ""
			::= { mbus29 32 }

mbus29Value0D		OBJECT-TYPE
			SYNTAX	INTEGER
			ACCESS	read-only
			STATUS	current
	DESCRIPTION ""
			::= { mbus29 33 }

mbus29VIF0E		OBJECT-TYPE
			SYNTAX	INTEGER
			ACCESS	read-only
			STATUS	current
	DESCRIPTION ""
			::= { mbus29 34 }

mbus29Value0E		OBJECT-TYPE
			SYNTAX	INTEGER
			ACCESS	read-only
			STATUS	current
	DESCRIPTION ""
			::= { mbus29 35 }

mbus29VIF0F		OBJECT-TYPE
			SYNTAX	INTEGER
			ACCESS	read-only
			STATUS	current
	DESCRIPTION ""
			::= { mbus29 36 }

mbus29Value0F		OBJECT-TYPE
			SYNTAX	INTEGER
			ACCESS	read-only
			STATUS	current
	DESCRIPTION ""
			::= { mbus29 37 }

mbus29VIF10		OBJECT-TYPE
			SYNTAX	INTEGER
			ACCESS	read-only
			STATUS	current
	DESCRIPTION ""
			::= { mbus29 38 }

mbus29Value10		OBJECT-TYPE
			SYNTAX	INTEGER
			ACCESS	read-only
			STATUS	current
	DESCRIPTION ""
			::= { mbus29 39 }

mbus29VIF11		OBJECT-TYPE
			SYNTAX	INTEGER
			ACCESS	read-only
			STATUS	current
	DESCRIPTION ""
			::= { mbus29 40 }

mbus29Value11		OBJECT-TYPE
			SYNTAX	INTEGER
			ACCESS	read-only
			STATUS	current
	DESCRIPTION ""
			::= { mbus29 41 }

mbus29VIF12		OBJECT-TYPE
			SYNTAX	INTEGER
			ACCESS	read-only
			STATUS	current
	DESCRIPTION ""
			::= { mbus29 42 }

mbus29Value12		OBJECT-TYPE
			SYNTAX	INTEGER
			ACCESS	read-only
			STATUS	current
	DESCRIPTION ""
			::= { mbus29 43 }

mbus29VIF13		OBJECT-TYPE
			SYNTAX	INTEGER
			ACCESS	read-only
			STATUS	current
	DESCRIPTION ""
			::= { mbus29 44 }

mbus29Value13		OBJECT-TYPE
			SYNTAX	INTEGER
			ACCESS	read-only
			STATUS	current
	DESCRIPTION ""
			::= { mbus29 45 }

mbus29VIF14		OBJECT-TYPE
			SYNTAX	INTEGER
			ACCESS	read-only
			STATUS	current
	DESCRIPTION ""
			::= { mbus29 46 }

mbus29Value14		OBJECT-TYPE
			SYNTAX	INTEGER
			ACCESS	read-only
			STATUS	current
	DESCRIPTION ""
			::= { mbus29 47 }

mbus29VIF15		OBJECT-TYPE
			SYNTAX	INTEGER
			ACCESS	read-only
			STATUS	current
	DESCRIPTION ""
			::= { mbus29 48 }

mbus29Value15		OBJECT-TYPE
			SYNTAX	INTEGER
			ACCESS	read-only
			STATUS	current
	DESCRIPTION ""
			::= { mbus29 49 }

mbus29VIF16		OBJECT-TYPE
			SYNTAX	INTEGER
			ACCESS	read-only
			STATUS	current
	DESCRIPTION ""
			::= { mbus29 50 }

mbus29Value16		OBJECT-TYPE
			SYNTAX	INTEGER
			ACCESS	read-only
			STATUS	current
	DESCRIPTION ""
			::= { mbus29 51 }

mbus29VIF17		OBJECT-TYPE
			SYNTAX	INTEGER
			ACCESS	read-only
			STATUS	current
	DESCRIPTION ""
			::= { mbus29 52 }

mbus29Value17		OBJECT-TYPE
			SYNTAX	INTEGER
			ACCESS	read-only
			STATUS	current
	DESCRIPTION ""
			::= { mbus29 53 }

mbus29VIF18		OBJECT-TYPE
			SYNTAX	INTEGER
			ACCESS	read-only
			STATUS	current
	DESCRIPTION ""
			::= { mbus29 54 }

mbus29Value18		OBJECT-TYPE
			SYNTAX	INTEGER
			ACCESS	read-only
			STATUS	current
	DESCRIPTION ""
			::= { mbus29 55 }

mbus29VIF19		OBJECT-TYPE
			SYNTAX	INTEGER
			ACCESS	read-only
			STATUS	current
	DESCRIPTION ""
			::= { mbus29 56 }

mbus29Value19		OBJECT-TYPE
			SYNTAX	INTEGER
			ACCESS	read-only
			STATUS	current
	DESCRIPTION ""
			::= { mbus29 57 }

mbus29VIF1A		OBJECT-TYPE
			SYNTAX	INTEGER
			ACCESS	read-only
			STATUS	current
	DESCRIPTION ""
			::= { mbus29 58 }

mbus29Value1A		OBJECT-TYPE
			SYNTAX	INTEGER
			ACCESS	read-only
			STATUS	current
	DESCRIPTION ""
			::= { mbus29 59 }

mbus29VIF1B		OBJECT-TYPE
			SYNTAX	INTEGER
			ACCESS	read-only
			STATUS	current
	DESCRIPTION ""
			::= { mbus29 60 }

mbus29Value1B		OBJECT-TYPE
			SYNTAX	INTEGER
			ACCESS	read-only
			STATUS	current
	DESCRIPTION ""
			::= { mbus29 61 }

mbus29VIF1C		OBJECT-TYPE
			SYNTAX	INTEGER
			ACCESS	read-only
			STATUS	current
	DESCRIPTION ""
			::= { mbus29 62 }

mbus29Value1C		OBJECT-TYPE
			SYNTAX	INTEGER
			ACCESS	read-only
			STATUS	current
	DESCRIPTION ""
			::= { mbus29 63 }

mbus29VIF1D		OBJECT-TYPE
			SYNTAX	INTEGER
			ACCESS	read-only
			STATUS	current
	DESCRIPTION ""
			::= { mbus29 64 }

mbus29Value1D		OBJECT-TYPE
			SYNTAX	INTEGER
			ACCESS	read-only
			STATUS	current
	DESCRIPTION ""
			::= { mbus29 65 }

mbus29VIF1E		OBJECT-TYPE
			SYNTAX	INTEGER
			ACCESS	read-only
			STATUS	current
	DESCRIPTION ""
			::= { mbus29 66 }

mbus29Value1E		OBJECT-TYPE
			SYNTAX	INTEGER
			ACCESS	read-only
			STATUS	current
	DESCRIPTION ""
			::= { mbus29 67 }

mbus29VIF1F		OBJECT-TYPE
			SYNTAX	INTEGER
			ACCESS	read-only
			STATUS	current
	DESCRIPTION ""
			::= { mbus29 68 }

mbus29Value1F		OBJECT-TYPE
			SYNTAX	INTEGER
			ACCESS	read-only
			STATUS	current
	DESCRIPTION ""
			::= { mbus29 69 }

mbus29VIF20		OBJECT-TYPE
			SYNTAX	INTEGER
			ACCESS	read-only
			STATUS	current
	DESCRIPTION ""
			::= { mbus29 70 }

mbus29Value20		OBJECT-TYPE
			SYNTAX	INTEGER
			ACCESS	read-only
			STATUS	current
	DESCRIPTION ""
			::= { mbus29 71 }

mbus29VIF21		OBJECT-TYPE
			SYNTAX	INTEGER
			ACCESS	read-only
			STATUS	current
	DESCRIPTION ""
			::= { mbus29 72 }

mbus29Value21		OBJECT-TYPE
			SYNTAX	INTEGER
			ACCESS	read-only
			STATUS	current
	DESCRIPTION ""
			::= { mbus29 73 }

mbus29VIF22		OBJECT-TYPE
			SYNTAX	INTEGER
			ACCESS	read-only
			STATUS	current
	DESCRIPTION ""
			::= { mbus29 74 }

mbus29Value22		OBJECT-TYPE
			SYNTAX	INTEGER
			ACCESS	read-only
			STATUS	current
	DESCRIPTION ""
			::= { mbus29 75 }

mbus29VIF23		OBJECT-TYPE
			SYNTAX	INTEGER
			ACCESS	read-only
			STATUS	current
	DESCRIPTION ""
			::= { mbus29 76 }

mbus29Value23		OBJECT-TYPE
			SYNTAX	INTEGER
			ACCESS	read-only
			STATUS	current
	DESCRIPTION ""
			::= { mbus29 77 }

mbus29VIF24		OBJECT-TYPE
			SYNTAX	INTEGER
			ACCESS	read-only
			STATUS	current
	DESCRIPTION ""
			::= { mbus29 78 }

mbus29Value24		OBJECT-TYPE
			SYNTAX	INTEGER
			ACCESS	read-only
			STATUS	current
	DESCRIPTION ""
			::= { mbus29 79 }

mbus29VIF25		OBJECT-TYPE
			SYNTAX	INTEGER
			ACCESS	read-only
			STATUS	current
	DESCRIPTION ""
			::= { mbus29 80 }

mbus29Value25		OBJECT-TYPE
			SYNTAX	INTEGER
			ACCESS	read-only
			STATUS	current
	DESCRIPTION ""
			::= { mbus29 81 }

mbus29VIF26		OBJECT-TYPE
			SYNTAX	INTEGER
			ACCESS	read-only
			STATUS	current
	DESCRIPTION ""
			::= { mbus29 82 }

mbus29Value26		OBJECT-TYPE
			SYNTAX	INTEGER
			ACCESS	read-only
			STATUS	current
	DESCRIPTION ""
			::= { mbus29 83 }

mbus29VIF27		OBJECT-TYPE
			SYNTAX	INTEGER
			ACCESS	read-only
			STATUS	current
	DESCRIPTION ""
			::= { mbus29 84 }

mbus29Value27		OBJECT-TYPE
			SYNTAX	INTEGER
			ACCESS	read-only
			STATUS	current
	DESCRIPTION ""
			::= { mbus29 85 }

mbus29VIF28		OBJECT-TYPE
			SYNTAX	INTEGER
			ACCESS	read-only
			STATUS	current
	DESCRIPTION ""
			::= { mbus29 86 }

mbus29Value28		OBJECT-TYPE
			SYNTAX	INTEGER
			ACCESS	read-only
			STATUS	current
	DESCRIPTION ""
			::= { mbus29 87 }

mbus29VIF29		OBJECT-TYPE
			SYNTAX	INTEGER
			ACCESS	read-only
			STATUS	current
	DESCRIPTION ""
			::= { mbus29 88 }

mbus29Value29		OBJECT-TYPE
			SYNTAX	INTEGER
			ACCESS	read-only
			STATUS	current
	DESCRIPTION ""
			::= { mbus29 89 }

mbus29VIF2A		OBJECT-TYPE
			SYNTAX	INTEGER
			ACCESS	read-only
			STATUS	current
	DESCRIPTION ""
			::= { mbus29 90 }

mbus29Value2A		OBJECT-TYPE
			SYNTAX	INTEGER
			ACCESS	read-only
			STATUS	current
	DESCRIPTION ""
			::= { mbus29 91 }

mbus29VIF2B		OBJECT-TYPE
			SYNTAX	INTEGER
			ACCESS	read-only
			STATUS	current
	DESCRIPTION ""
			::= { mbus29 92 }

mbus29Value2B		OBJECT-TYPE
			SYNTAX	INTEGER
			ACCESS	read-only
			STATUS	current
	DESCRIPTION ""
			::= { mbus29 93 }

mbus29VIF2C		OBJECT-TYPE
			SYNTAX	INTEGER
			ACCESS	read-only
			STATUS	current
	DESCRIPTION ""
			::= { mbus29 94 }

mbus29Value2C		OBJECT-TYPE
			SYNTAX	INTEGER
			ACCESS	read-only
			STATUS	current
	DESCRIPTION ""
			::= { mbus29 95 }

mbus29VIF2D		OBJECT-TYPE
			SYNTAX	INTEGER
			ACCESS	read-only
			STATUS	current
	DESCRIPTION ""
			::= { mbus29 96 }

mbus29Value2D		OBJECT-TYPE
			SYNTAX	INTEGER
			ACCESS	read-only
			STATUS	current
	DESCRIPTION ""
			::= { mbus29 97 }

mbus29VIF2E		OBJECT-TYPE
			SYNTAX	INTEGER
			ACCESS	read-only
			STATUS	current
	DESCRIPTION ""
			::= { mbus29 98 }

mbus29Value2E		OBJECT-TYPE
			SYNTAX	INTEGER
			ACCESS	read-only
			STATUS	current
	DESCRIPTION ""
			::= { mbus29 99 }

mbus29VIF2F		OBJECT-TYPE
			SYNTAX	INTEGER
			ACCESS	read-only
			STATUS	current
	DESCRIPTION ""
			::= { mbus29 100 }

mbus29Value2F		OBJECT-TYPE
			SYNTAX	INTEGER
			ACCESS	read-only
			STATUS	current
	DESCRIPTION ""
			::= { mbus29 101 }

mbus2A			OBJECT IDENTIFIER ::= { mbus 42 }

mbus2AIdNumber		OBJECT-TYPE
			SYNTAX	Gauge
			ACCESS	read-only
			STATUS	current
	DESCRIPTION ""
			::= { mbus2A 1 }

mbus2AManufacturer	OBJECT-TYPE
			SYNTAX	Gauge
			ACCESS	read-only
			STATUS	current
	DESCRIPTION ""
			::= { mbus2A 2 }

mbus2AVersion		OBJECT-TYPE
			SYNTAX	Gauge
			ACCESS	read-only
			STATUS	current
	DESCRIPTION ""
			::= { mbus2A 3 }

mbus2AMedium		OBJECT-TYPE
			SYNTAX	Gauge
			ACCESS	read-only
			STATUS	current
	DESCRIPTION ""
			::= { mbus2A 4 }

mbus2AStatus		OBJECT-TYPE
			SYNTAX	Gauge
			ACCESS	read-only
			STATUS	current
	DESCRIPTION ""
			::= { mbus2A 5 }

mbus2AVIF00		OBJECT-TYPE
			SYNTAX	INTEGER
			ACCESS	read-only
			STATUS	current
	DESCRIPTION ""
			::= { mbus2A 6 }

mbus2AValue00		OBJECT-TYPE
			SYNTAX	INTEGER
			ACCESS	read-only
			STATUS	current
	DESCRIPTION ""
			::= { mbus2A 7 }

mbus2AVIF01		OBJECT-TYPE
			SYNTAX	INTEGER
			ACCESS	read-only
			STATUS	current
	DESCRIPTION ""
			::= { mbus2A 8 }

mbus2AValue01		OBJECT-TYPE
			SYNTAX	INTEGER
			ACCESS	read-only
			STATUS	current
	DESCRIPTION ""
			::= { mbus2A 9 }

mbus2AVIF02		OBJECT-TYPE
			SYNTAX	INTEGER
			ACCESS	read-only
			STATUS	current
	DESCRIPTION ""
			::= { mbus2A 10 }

mbus2AValue02		OBJECT-TYPE
			SYNTAX	INTEGER
			ACCESS	read-only
			STATUS	current
	DESCRIPTION ""
			::= { mbus2A 11 }

mbus2AVIF03		OBJECT-TYPE
			SYNTAX	INTEGER
			ACCESS	read-only
			STATUS	current
	DESCRIPTION ""
			::= { mbus2A 12 }

mbus2AValue03		OBJECT-TYPE
			SYNTAX	INTEGER
			ACCESS	read-only
			STATUS	current
	DESCRIPTION ""
			::= { mbus2A 13 }

mbus2AVIF04		OBJECT-TYPE
			SYNTAX	INTEGER
			ACCESS	read-only
			STATUS	current
	DESCRIPTION ""
			::= { mbus2A 14 }

mbus2AValue04		OBJECT-TYPE
			SYNTAX	INTEGER
			ACCESS	read-only
			STATUS	current
	DESCRIPTION ""
			::= { mbus2A 15 }

mbus2AVIF05		OBJECT-TYPE
			SYNTAX	INTEGER
			ACCESS	read-only
			STATUS	current
	DESCRIPTION ""
			::= { mbus2A 16 }

mbus2AValue05		OBJECT-TYPE
			SYNTAX	INTEGER
			ACCESS	read-only
			STATUS	current
	DESCRIPTION ""
			::= { mbus2A 17 }

mbus2AVIF06		OBJECT-TYPE
			SYNTAX	INTEGER
			ACCESS	read-only
			STATUS	current
	DESCRIPTION ""
			::= { mbus2A 18 }

mbus2AValue06		OBJECT-TYPE
			SYNTAX	INTEGER
			ACCESS	read-only
			STATUS	current
	DESCRIPTION ""
			::= { mbus2A 19 }

mbus2AVIF07		OBJECT-TYPE
			SYNTAX	INTEGER
			ACCESS	read-only
			STATUS	current
	DESCRIPTION ""
			::= { mbus2A 20 }

mbus2AValue07		OBJECT-TYPE
			SYNTAX	INTEGER
			ACCESS	read-only
			STATUS	current
	DESCRIPTION ""
			::= { mbus2A 21 }

mbus2AVIF08		OBJECT-TYPE
			SYNTAX	INTEGER
			ACCESS	read-only
			STATUS	current
	DESCRIPTION ""
			::= { mbus2A 22 }

mbus2AValue08		OBJECT-TYPE
			SYNTAX	INTEGER
			ACCESS	read-only
			STATUS	current
	DESCRIPTION ""
			::= { mbus2A 23 }

mbus2AVIF09		OBJECT-TYPE
			SYNTAX	INTEGER
			ACCESS	read-only
			STATUS	current
	DESCRIPTION ""
			::= { mbus2A 24 }

mbus2AValue09		OBJECT-TYPE
			SYNTAX	INTEGER
			ACCESS	read-only
			STATUS	current
	DESCRIPTION ""
			::= { mbus2A 25 }

mbus2AVIF0A		OBJECT-TYPE
			SYNTAX	INTEGER
			ACCESS	read-only
			STATUS	current
	DESCRIPTION ""
			::= { mbus2A 26 }

mbus2AValue0A		OBJECT-TYPE
			SYNTAX	INTEGER
			ACCESS	read-only
			STATUS	current
	DESCRIPTION ""
			::= { mbus2A 27 }

mbus2AVIF0B		OBJECT-TYPE
			SYNTAX	INTEGER
			ACCESS	read-only
			STATUS	current
	DESCRIPTION ""
			::= { mbus2A 28 }

mbus2AValue0B		OBJECT-TYPE
			SYNTAX	INTEGER
			ACCESS	read-only
			STATUS	current
	DESCRIPTION ""
			::= { mbus2A 29 }

mbus2AVIF0C		OBJECT-TYPE
			SYNTAX	INTEGER
			ACCESS	read-only
			STATUS	current
	DESCRIPTION ""
			::= { mbus2A 30 }

mbus2AValue0C		OBJECT-TYPE
			SYNTAX	INTEGER
			ACCESS	read-only
			STATUS	current
	DESCRIPTION ""
			::= { mbus2A 31 }

mbus2AVIF0D		OBJECT-TYPE
			SYNTAX	INTEGER
			ACCESS	read-only
			STATUS	current
	DESCRIPTION ""
			::= { mbus2A 32 }

mbus2AValue0D		OBJECT-TYPE
			SYNTAX	INTEGER
			ACCESS	read-only
			STATUS	current
	DESCRIPTION ""
			::= { mbus2A 33 }

mbus2AVIF0E		OBJECT-TYPE
			SYNTAX	INTEGER
			ACCESS	read-only
			STATUS	current
	DESCRIPTION ""
			::= { mbus2A 34 }

mbus2AValue0E		OBJECT-TYPE
			SYNTAX	INTEGER
			ACCESS	read-only
			STATUS	current
	DESCRIPTION ""
			::= { mbus2A 35 }

mbus2AVIF0F		OBJECT-TYPE
			SYNTAX	INTEGER
			ACCESS	read-only
			STATUS	current
	DESCRIPTION ""
			::= { mbus2A 36 }

mbus2AValue0F		OBJECT-TYPE
			SYNTAX	INTEGER
			ACCESS	read-only
			STATUS	current
	DESCRIPTION ""
			::= { mbus2A 37 }

mbus2AVIF10		OBJECT-TYPE
			SYNTAX	INTEGER
			ACCESS	read-only
			STATUS	current
	DESCRIPTION ""
			::= { mbus2A 38 }

mbus2AValue10		OBJECT-TYPE
			SYNTAX	INTEGER
			ACCESS	read-only
			STATUS	current
	DESCRIPTION ""
			::= { mbus2A 39 }

mbus2AVIF11		OBJECT-TYPE
			SYNTAX	INTEGER
			ACCESS	read-only
			STATUS	current
	DESCRIPTION ""
			::= { mbus2A 40 }

mbus2AValue11		OBJECT-TYPE
			SYNTAX	INTEGER
			ACCESS	read-only
			STATUS	current
	DESCRIPTION ""
			::= { mbus2A 41 }

mbus2AVIF12		OBJECT-TYPE
			SYNTAX	INTEGER
			ACCESS	read-only
			STATUS	current
	DESCRIPTION ""
			::= { mbus2A 42 }

mbus2AValue12		OBJECT-TYPE
			SYNTAX	INTEGER
			ACCESS	read-only
			STATUS	current
	DESCRIPTION ""
			::= { mbus2A 43 }

mbus2AVIF13		OBJECT-TYPE
			SYNTAX	INTEGER
			ACCESS	read-only
			STATUS	current
	DESCRIPTION ""
			::= { mbus2A 44 }

mbus2AValue13		OBJECT-TYPE
			SYNTAX	INTEGER
			ACCESS	read-only
			STATUS	current
	DESCRIPTION ""
			::= { mbus2A 45 }

mbus2AVIF14		OBJECT-TYPE
			SYNTAX	INTEGER
			ACCESS	read-only
			STATUS	current
	DESCRIPTION ""
			::= { mbus2A 46 }

mbus2AValue14		OBJECT-TYPE
			SYNTAX	INTEGER
			ACCESS	read-only
			STATUS	current
	DESCRIPTION ""
			::= { mbus2A 47 }

mbus2AVIF15		OBJECT-TYPE
			SYNTAX	INTEGER
			ACCESS	read-only
			STATUS	current
	DESCRIPTION ""
			::= { mbus2A 48 }

mbus2AValue15		OBJECT-TYPE
			SYNTAX	INTEGER
			ACCESS	read-only
			STATUS	current
	DESCRIPTION ""
			::= { mbus2A 49 }

mbus2AVIF16		OBJECT-TYPE
			SYNTAX	INTEGER
			ACCESS	read-only
			STATUS	current
	DESCRIPTION ""
			::= { mbus2A 50 }

mbus2AValue16		OBJECT-TYPE
			SYNTAX	INTEGER
			ACCESS	read-only
			STATUS	current
	DESCRIPTION ""
			::= { mbus2A 51 }

mbus2AVIF17		OBJECT-TYPE
			SYNTAX	INTEGER
			ACCESS	read-only
			STATUS	current
	DESCRIPTION ""
			::= { mbus2A 52 }

mbus2AValue17		OBJECT-TYPE
			SYNTAX	INTEGER
			ACCESS	read-only
			STATUS	current
	DESCRIPTION ""
			::= { mbus2A 53 }

mbus2AVIF18		OBJECT-TYPE
			SYNTAX	INTEGER
			ACCESS	read-only
			STATUS	current
	DESCRIPTION ""
			::= { mbus2A 54 }

mbus2AValue18		OBJECT-TYPE
			SYNTAX	INTEGER
			ACCESS	read-only
			STATUS	current
	DESCRIPTION ""
			::= { mbus2A 55 }

mbus2AVIF19		OBJECT-TYPE
			SYNTAX	INTEGER
			ACCESS	read-only
			STATUS	current
	DESCRIPTION ""
			::= { mbus2A 56 }

mbus2AValue19		OBJECT-TYPE
			SYNTAX	INTEGER
			ACCESS	read-only
			STATUS	current
	DESCRIPTION ""
			::= { mbus2A 57 }

mbus2AVIF1A		OBJECT-TYPE
			SYNTAX	INTEGER
			ACCESS	read-only
			STATUS	current
	DESCRIPTION ""
			::= { mbus2A 58 }

mbus2AValue1A		OBJECT-TYPE
			SYNTAX	INTEGER
			ACCESS	read-only
			STATUS	current
	DESCRIPTION ""
			::= { mbus2A 59 }

mbus2AVIF1B		OBJECT-TYPE
			SYNTAX	INTEGER
			ACCESS	read-only
			STATUS	current
	DESCRIPTION ""
			::= { mbus2A 60 }

mbus2AValue1B		OBJECT-TYPE
			SYNTAX	INTEGER
			ACCESS	read-only
			STATUS	current
	DESCRIPTION ""
			::= { mbus2A 61 }

mbus2AVIF1C		OBJECT-TYPE
			SYNTAX	INTEGER
			ACCESS	read-only
			STATUS	current
	DESCRIPTION ""
			::= { mbus2A 62 }

mbus2AValue1C		OBJECT-TYPE
			SYNTAX	INTEGER
			ACCESS	read-only
			STATUS	current
	DESCRIPTION ""
			::= { mbus2A 63 }

mbus2AVIF1D		OBJECT-TYPE
			SYNTAX	INTEGER
			ACCESS	read-only
			STATUS	current
	DESCRIPTION ""
			::= { mbus2A 64 }

mbus2AValue1D		OBJECT-TYPE
			SYNTAX	INTEGER
			ACCESS	read-only
			STATUS	current
	DESCRIPTION ""
			::= { mbus2A 65 }

mbus2AVIF1E		OBJECT-TYPE
			SYNTAX	INTEGER
			ACCESS	read-only
			STATUS	current
	DESCRIPTION ""
			::= { mbus2A 66 }

mbus2AValue1E		OBJECT-TYPE
			SYNTAX	INTEGER
			ACCESS	read-only
			STATUS	current
	DESCRIPTION ""
			::= { mbus2A 67 }

mbus2AVIF1F		OBJECT-TYPE
			SYNTAX	INTEGER
			ACCESS	read-only
			STATUS	current
	DESCRIPTION ""
			::= { mbus2A 68 }

mbus2AValue1F		OBJECT-TYPE
			SYNTAX	INTEGER
			ACCESS	read-only
			STATUS	current
	DESCRIPTION ""
			::= { mbus2A 69 }

mbus2AVIF20		OBJECT-TYPE
			SYNTAX	INTEGER
			ACCESS	read-only
			STATUS	current
	DESCRIPTION ""
			::= { mbus2A 70 }

mbus2AValue20		OBJECT-TYPE
			SYNTAX	INTEGER
			ACCESS	read-only
			STATUS	current
	DESCRIPTION ""
			::= { mbus2A 71 }

mbus2AVIF21		OBJECT-TYPE
			SYNTAX	INTEGER
			ACCESS	read-only
			STATUS	current
	DESCRIPTION ""
			::= { mbus2A 72 }

mbus2AValue21		OBJECT-TYPE
			SYNTAX	INTEGER
			ACCESS	read-only
			STATUS	current
	DESCRIPTION ""
			::= { mbus2A 73 }

mbus2AVIF22		OBJECT-TYPE
			SYNTAX	INTEGER
			ACCESS	read-only
			STATUS	current
	DESCRIPTION ""
			::= { mbus2A 74 }

mbus2AValue22		OBJECT-TYPE
			SYNTAX	INTEGER
			ACCESS	read-only
			STATUS	current
	DESCRIPTION ""
			::= { mbus2A 75 }

mbus2AVIF23		OBJECT-TYPE
			SYNTAX	INTEGER
			ACCESS	read-only
			STATUS	current
	DESCRIPTION ""
			::= { mbus2A 76 }

mbus2AValue23		OBJECT-TYPE
			SYNTAX	INTEGER
			ACCESS	read-only
			STATUS	current
	DESCRIPTION ""
			::= { mbus2A 77 }

mbus2AVIF24		OBJECT-TYPE
			SYNTAX	INTEGER
			ACCESS	read-only
			STATUS	current
	DESCRIPTION ""
			::= { mbus2A 78 }

mbus2AValue24		OBJECT-TYPE
			SYNTAX	INTEGER
			ACCESS	read-only
			STATUS	current
	DESCRIPTION ""
			::= { mbus2A 79 }

mbus2AVIF25		OBJECT-TYPE
			SYNTAX	INTEGER
			ACCESS	read-only
			STATUS	current
	DESCRIPTION ""
			::= { mbus2A 80 }

mbus2AValue25		OBJECT-TYPE
			SYNTAX	INTEGER
			ACCESS	read-only
			STATUS	current
	DESCRIPTION ""
			::= { mbus2A 81 }

mbus2AVIF26		OBJECT-TYPE
			SYNTAX	INTEGER
			ACCESS	read-only
			STATUS	current
	DESCRIPTION ""
			::= { mbus2A 82 }

mbus2AValue26		OBJECT-TYPE
			SYNTAX	INTEGER
			ACCESS	read-only
			STATUS	current
	DESCRIPTION ""
			::= { mbus2A 83 }

mbus2AVIF27		OBJECT-TYPE
			SYNTAX	INTEGER
			ACCESS	read-only
			STATUS	current
	DESCRIPTION ""
			::= { mbus2A 84 }

mbus2AValue27		OBJECT-TYPE
			SYNTAX	INTEGER
			ACCESS	read-only
			STATUS	current
	DESCRIPTION ""
			::= { mbus2A 85 }

mbus2AVIF28		OBJECT-TYPE
			SYNTAX	INTEGER
			ACCESS	read-only
			STATUS	current
	DESCRIPTION ""
			::= { mbus2A 86 }

mbus2AValue28		OBJECT-TYPE
			SYNTAX	INTEGER
			ACCESS	read-only
			STATUS	current
	DESCRIPTION ""
			::= { mbus2A 87 }

mbus2AVIF29		OBJECT-TYPE
			SYNTAX	INTEGER
			ACCESS	read-only
			STATUS	current
	DESCRIPTION ""
			::= { mbus2A 88 }

mbus2AValue29		OBJECT-TYPE
			SYNTAX	INTEGER
			ACCESS	read-only
			STATUS	current
	DESCRIPTION ""
			::= { mbus2A 89 }

mbus2AVIF2A		OBJECT-TYPE
			SYNTAX	INTEGER
			ACCESS	read-only
			STATUS	current
	DESCRIPTION ""
			::= { mbus2A 90 }

mbus2AValue2A		OBJECT-TYPE
			SYNTAX	INTEGER
			ACCESS	read-only
			STATUS	current
	DESCRIPTION ""
			::= { mbus2A 91 }

mbus2AVIF2B		OBJECT-TYPE
			SYNTAX	INTEGER
			ACCESS	read-only
			STATUS	current
	DESCRIPTION ""
			::= { mbus2A 92 }

mbus2AValue2B		OBJECT-TYPE
			SYNTAX	INTEGER
			ACCESS	read-only
			STATUS	current
	DESCRIPTION ""
			::= { mbus2A 93 }

mbus2AVIF2C		OBJECT-TYPE
			SYNTAX	INTEGER
			ACCESS	read-only
			STATUS	current
	DESCRIPTION ""
			::= { mbus2A 94 }

mbus2AValue2C		OBJECT-TYPE
			SYNTAX	INTEGER
			ACCESS	read-only
			STATUS	current
	DESCRIPTION ""
			::= { mbus2A 95 }

mbus2AVIF2D		OBJECT-TYPE
			SYNTAX	INTEGER
			ACCESS	read-only
			STATUS	current
	DESCRIPTION ""
			::= { mbus2A 96 }

mbus2AValue2D		OBJECT-TYPE
			SYNTAX	INTEGER
			ACCESS	read-only
			STATUS	current
	DESCRIPTION ""
			::= { mbus2A 97 }

mbus2AVIF2E		OBJECT-TYPE
			SYNTAX	INTEGER
			ACCESS	read-only
			STATUS	current
	DESCRIPTION ""
			::= { mbus2A 98 }

mbus2AValue2E		OBJECT-TYPE
			SYNTAX	INTEGER
			ACCESS	read-only
			STATUS	current
	DESCRIPTION ""
			::= { mbus2A 99 }

mbus2AVIF2F		OBJECT-TYPE
			SYNTAX	INTEGER
			ACCESS	read-only
			STATUS	current
	DESCRIPTION ""
			::= { mbus2A 100 }

mbus2AValue2F		OBJECT-TYPE
			SYNTAX	INTEGER
			ACCESS	read-only
			STATUS	current
	DESCRIPTION ""
			::= { mbus2A 101 }

mbus2B			OBJECT IDENTIFIER ::= { mbus 43 }

mbus2BIdNumber		OBJECT-TYPE
			SYNTAX	Gauge
			ACCESS	read-only
			STATUS	current
	DESCRIPTION ""
			::= { mbus2B 1 }

mbus2BManufacturer	OBJECT-TYPE
			SYNTAX	Gauge
			ACCESS	read-only
			STATUS	current
	DESCRIPTION ""
			::= { mbus2B 2 }

mbus2BVersion		OBJECT-TYPE
			SYNTAX	Gauge
			ACCESS	read-only
			STATUS	current
	DESCRIPTION ""
			::= { mbus2B 3 }

mbus2BMedium		OBJECT-TYPE
			SYNTAX	Gauge
			ACCESS	read-only
			STATUS	current
	DESCRIPTION ""
			::= { mbus2B 4 }

mbus2BStatus		OBJECT-TYPE
			SYNTAX	Gauge
			ACCESS	read-only
			STATUS	current
	DESCRIPTION ""
			::= { mbus2B 5 }

mbus2BVIF00		OBJECT-TYPE
			SYNTAX	INTEGER
			ACCESS	read-only
			STATUS	current
	DESCRIPTION ""
			::= { mbus2B 6 }

mbus2BValue00		OBJECT-TYPE
			SYNTAX	INTEGER
			ACCESS	read-only
			STATUS	current
	DESCRIPTION ""
			::= { mbus2B 7 }

mbus2BVIF01		OBJECT-TYPE
			SYNTAX	INTEGER
			ACCESS	read-only
			STATUS	current
	DESCRIPTION ""
			::= { mbus2B 8 }

mbus2BValue01		OBJECT-TYPE
			SYNTAX	INTEGER
			ACCESS	read-only
			STATUS	current
	DESCRIPTION ""
			::= { mbus2B 9 }

mbus2BVIF02		OBJECT-TYPE
			SYNTAX	INTEGER
			ACCESS	read-only
			STATUS	current
	DESCRIPTION ""
			::= { mbus2B 10 }

mbus2BValue02		OBJECT-TYPE
			SYNTAX	INTEGER
			ACCESS	read-only
			STATUS	current
	DESCRIPTION ""
			::= { mbus2B 11 }

mbus2BVIF03		OBJECT-TYPE
			SYNTAX	INTEGER
			ACCESS	read-only
			STATUS	current
	DESCRIPTION ""
			::= { mbus2B 12 }

mbus2BValue03		OBJECT-TYPE
			SYNTAX	INTEGER
			ACCESS	read-only
			STATUS	current
	DESCRIPTION ""
			::= { mbus2B 13 }

mbus2BVIF04		OBJECT-TYPE
			SYNTAX	INTEGER
			ACCESS	read-only
			STATUS	current
	DESCRIPTION ""
			::= { mbus2B 14 }

mbus2BValue04		OBJECT-TYPE
			SYNTAX	INTEGER
			ACCESS	read-only
			STATUS	current
	DESCRIPTION ""
			::= { mbus2B 15 }

mbus2BVIF05		OBJECT-TYPE
			SYNTAX	INTEGER
			ACCESS	read-only
			STATUS	current
	DESCRIPTION ""
			::= { mbus2B 16 }

mbus2BValue05		OBJECT-TYPE
			SYNTAX	INTEGER
			ACCESS	read-only
			STATUS	current
	DESCRIPTION ""
			::= { mbus2B 17 }

mbus2BVIF06		OBJECT-TYPE
			SYNTAX	INTEGER
			ACCESS	read-only
			STATUS	current
	DESCRIPTION ""
			::= { mbus2B 18 }

mbus2BValue06		OBJECT-TYPE
			SYNTAX	INTEGER
			ACCESS	read-only
			STATUS	current
	DESCRIPTION ""
			::= { mbus2B 19 }

mbus2BVIF07		OBJECT-TYPE
			SYNTAX	INTEGER
			ACCESS	read-only
			STATUS	current
	DESCRIPTION ""
			::= { mbus2B 20 }

mbus2BValue07		OBJECT-TYPE
			SYNTAX	INTEGER
			ACCESS	read-only
			STATUS	current
	DESCRIPTION ""
			::= { mbus2B 21 }

mbus2BVIF08		OBJECT-TYPE
			SYNTAX	INTEGER
			ACCESS	read-only
			STATUS	current
	DESCRIPTION ""
			::= { mbus2B 22 }

mbus2BValue08		OBJECT-TYPE
			SYNTAX	INTEGER
			ACCESS	read-only
			STATUS	current
	DESCRIPTION ""
			::= { mbus2B 23 }

mbus2BVIF09		OBJECT-TYPE
			SYNTAX	INTEGER
			ACCESS	read-only
			STATUS	current
	DESCRIPTION ""
			::= { mbus2B 24 }

mbus2BValue09		OBJECT-TYPE
			SYNTAX	INTEGER
			ACCESS	read-only
			STATUS	current
	DESCRIPTION ""
			::= { mbus2B 25 }

mbus2BVIF0A		OBJECT-TYPE
			SYNTAX	INTEGER
			ACCESS	read-only
			STATUS	current
	DESCRIPTION ""
			::= { mbus2B 26 }

mbus2BValue0A		OBJECT-TYPE
			SYNTAX	INTEGER
			ACCESS	read-only
			STATUS	current
	DESCRIPTION ""
			::= { mbus2B 27 }

mbus2BVIF0B		OBJECT-TYPE
			SYNTAX	INTEGER
			ACCESS	read-only
			STATUS	current
	DESCRIPTION ""
			::= { mbus2B 28 }

mbus2BValue0B		OBJECT-TYPE
			SYNTAX	INTEGER
			ACCESS	read-only
			STATUS	current
	DESCRIPTION ""
			::= { mbus2B 29 }

mbus2BVIF0C		OBJECT-TYPE
			SYNTAX	INTEGER
			ACCESS	read-only
			STATUS	current
	DESCRIPTION ""
			::= { mbus2B 30 }

mbus2BValue0C		OBJECT-TYPE
			SYNTAX	INTEGER
			ACCESS	read-only
			STATUS	current
	DESCRIPTION ""
			::= { mbus2B 31 }

mbus2BVIF0D		OBJECT-TYPE
			SYNTAX	INTEGER
			ACCESS	read-only
			STATUS	current
	DESCRIPTION ""
			::= { mbus2B 32 }

mbus2BValue0D		OBJECT-TYPE
			SYNTAX	INTEGER
			ACCESS	read-only
			STATUS	current
	DESCRIPTION ""
			::= { mbus2B 33 }

mbus2BVIF0E		OBJECT-TYPE
			SYNTAX	INTEGER
			ACCESS	read-only
			STATUS	current
	DESCRIPTION ""
			::= { mbus2B 34 }

mbus2BValue0E		OBJECT-TYPE
			SYNTAX	INTEGER
			ACCESS	read-only
			STATUS	current
	DESCRIPTION ""
			::= { mbus2B 35 }

mbus2BVIF0F		OBJECT-TYPE
			SYNTAX	INTEGER
			ACCESS	read-only
			STATUS	current
	DESCRIPTION ""
			::= { mbus2B 36 }

mbus2BValue0F		OBJECT-TYPE
			SYNTAX	INTEGER
			ACCESS	read-only
			STATUS	current
	DESCRIPTION ""
			::= { mbus2B 37 }

mbus2BVIF10		OBJECT-TYPE
			SYNTAX	INTEGER
			ACCESS	read-only
			STATUS	current
	DESCRIPTION ""
			::= { mbus2B 38 }

mbus2BValue10		OBJECT-TYPE
			SYNTAX	INTEGER
			ACCESS	read-only
			STATUS	current
	DESCRIPTION ""
			::= { mbus2B 39 }

mbus2BVIF11		OBJECT-TYPE
			SYNTAX	INTEGER
			ACCESS	read-only
			STATUS	current
	DESCRIPTION ""
			::= { mbus2B 40 }

mbus2BValue11		OBJECT-TYPE
			SYNTAX	INTEGER
			ACCESS	read-only
			STATUS	current
	DESCRIPTION ""
			::= { mbus2B 41 }

mbus2BVIF12		OBJECT-TYPE
			SYNTAX	INTEGER
			ACCESS	read-only
			STATUS	current
	DESCRIPTION ""
			::= { mbus2B 42 }

mbus2BValue12		OBJECT-TYPE
			SYNTAX	INTEGER
			ACCESS	read-only
			STATUS	current
	DESCRIPTION ""
			::= { mbus2B 43 }

mbus2BVIF13		OBJECT-TYPE
			SYNTAX	INTEGER
			ACCESS	read-only
			STATUS	current
	DESCRIPTION ""
			::= { mbus2B 44 }

mbus2BValue13		OBJECT-TYPE
			SYNTAX	INTEGER
			ACCESS	read-only
			STATUS	current
	DESCRIPTION ""
			::= { mbus2B 45 }

mbus2BVIF14		OBJECT-TYPE
			SYNTAX	INTEGER
			ACCESS	read-only
			STATUS	current
	DESCRIPTION ""
			::= { mbus2B 46 }

mbus2BValue14		OBJECT-TYPE
			SYNTAX	INTEGER
			ACCESS	read-only
			STATUS	current
	DESCRIPTION ""
			::= { mbus2B 47 }

mbus2BVIF15		OBJECT-TYPE
			SYNTAX	INTEGER
			ACCESS	read-only
			STATUS	current
	DESCRIPTION ""
			::= { mbus2B 48 }

mbus2BValue15		OBJECT-TYPE
			SYNTAX	INTEGER
			ACCESS	read-only
			STATUS	current
	DESCRIPTION ""
			::= { mbus2B 49 }

mbus2BVIF16		OBJECT-TYPE
			SYNTAX	INTEGER
			ACCESS	read-only
			STATUS	current
	DESCRIPTION ""
			::= { mbus2B 50 }

mbus2BValue16		OBJECT-TYPE
			SYNTAX	INTEGER
			ACCESS	read-only
			STATUS	current
	DESCRIPTION ""
			::= { mbus2B 51 }

mbus2BVIF17		OBJECT-TYPE
			SYNTAX	INTEGER
			ACCESS	read-only
			STATUS	current
	DESCRIPTION ""
			::= { mbus2B 52 }

mbus2BValue17		OBJECT-TYPE
			SYNTAX	INTEGER
			ACCESS	read-only
			STATUS	current
	DESCRIPTION ""
			::= { mbus2B 53 }

mbus2BVIF18		OBJECT-TYPE
			SYNTAX	INTEGER
			ACCESS	read-only
			STATUS	current
	DESCRIPTION ""
			::= { mbus2B 54 }

mbus2BValue18		OBJECT-TYPE
			SYNTAX	INTEGER
			ACCESS	read-only
			STATUS	current
	DESCRIPTION ""
			::= { mbus2B 55 }

mbus2BVIF19		OBJECT-TYPE
			SYNTAX	INTEGER
			ACCESS	read-only
			STATUS	current
	DESCRIPTION ""
			::= { mbus2B 56 }

mbus2BValue19		OBJECT-TYPE
			SYNTAX	INTEGER
			ACCESS	read-only
			STATUS	current
	DESCRIPTION ""
			::= { mbus2B 57 }

mbus2BVIF1A		OBJECT-TYPE
			SYNTAX	INTEGER
			ACCESS	read-only
			STATUS	current
	DESCRIPTION ""
			::= { mbus2B 58 }

mbus2BValue1A		OBJECT-TYPE
			SYNTAX	INTEGER
			ACCESS	read-only
			STATUS	current
	DESCRIPTION ""
			::= { mbus2B 59 }

mbus2BVIF1B		OBJECT-TYPE
			SYNTAX	INTEGER
			ACCESS	read-only
			STATUS	current
	DESCRIPTION ""
			::= { mbus2B 60 }

mbus2BValue1B		OBJECT-TYPE
			SYNTAX	INTEGER
			ACCESS	read-only
			STATUS	current
	DESCRIPTION ""
			::= { mbus2B 61 }

mbus2BVIF1C		OBJECT-TYPE
			SYNTAX	INTEGER
			ACCESS	read-only
			STATUS	current
	DESCRIPTION ""
			::= { mbus2B 62 }

mbus2BValue1C		OBJECT-TYPE
			SYNTAX	INTEGER
			ACCESS	read-only
			STATUS	current
	DESCRIPTION ""
			::= { mbus2B 63 }

mbus2BVIF1D		OBJECT-TYPE
			SYNTAX	INTEGER
			ACCESS	read-only
			STATUS	current
	DESCRIPTION ""
			::= { mbus2B 64 }

mbus2BValue1D		OBJECT-TYPE
			SYNTAX	INTEGER
			ACCESS	read-only
			STATUS	current
	DESCRIPTION ""
			::= { mbus2B 65 }

mbus2BVIF1E		OBJECT-TYPE
			SYNTAX	INTEGER
			ACCESS	read-only
			STATUS	current
	DESCRIPTION ""
			::= { mbus2B 66 }

mbus2BValue1E		OBJECT-TYPE
			SYNTAX	INTEGER
			ACCESS	read-only
			STATUS	current
	DESCRIPTION ""
			::= { mbus2B 67 }

mbus2BVIF1F		OBJECT-TYPE
			SYNTAX	INTEGER
			ACCESS	read-only
			STATUS	current
	DESCRIPTION ""
			::= { mbus2B 68 }

mbus2BValue1F		OBJECT-TYPE
			SYNTAX	INTEGER
			ACCESS	read-only
			STATUS	current
	DESCRIPTION ""
			::= { mbus2B 69 }

mbus2BVIF20		OBJECT-TYPE
			SYNTAX	INTEGER
			ACCESS	read-only
			STATUS	current
	DESCRIPTION ""
			::= { mbus2B 70 }

mbus2BValue20		OBJECT-TYPE
			SYNTAX	INTEGER
			ACCESS	read-only
			STATUS	current
	DESCRIPTION ""
			::= { mbus2B 71 }

mbus2BVIF21		OBJECT-TYPE
			SYNTAX	INTEGER
			ACCESS	read-only
			STATUS	current
	DESCRIPTION ""
			::= { mbus2B 72 }

mbus2BValue21		OBJECT-TYPE
			SYNTAX	INTEGER
			ACCESS	read-only
			STATUS	current
	DESCRIPTION ""
			::= { mbus2B 73 }

mbus2BVIF22		OBJECT-TYPE
			SYNTAX	INTEGER
			ACCESS	read-only
			STATUS	current
	DESCRIPTION ""
			::= { mbus2B 74 }

mbus2BValue22		OBJECT-TYPE
			SYNTAX	INTEGER
			ACCESS	read-only
			STATUS	current
	DESCRIPTION ""
			::= { mbus2B 75 }

mbus2BVIF23		OBJECT-TYPE
			SYNTAX	INTEGER
			ACCESS	read-only
			STATUS	current
	DESCRIPTION ""
			::= { mbus2B 76 }

mbus2BValue23		OBJECT-TYPE
			SYNTAX	INTEGER
			ACCESS	read-only
			STATUS	current
	DESCRIPTION ""
			::= { mbus2B 77 }

mbus2BVIF24		OBJECT-TYPE
			SYNTAX	INTEGER
			ACCESS	read-only
			STATUS	current
	DESCRIPTION ""
			::= { mbus2B 78 }

mbus2BValue24		OBJECT-TYPE
			SYNTAX	INTEGER
			ACCESS	read-only
			STATUS	current
	DESCRIPTION ""
			::= { mbus2B 79 }

mbus2BVIF25		OBJECT-TYPE
			SYNTAX	INTEGER
			ACCESS	read-only
			STATUS	current
	DESCRIPTION ""
			::= { mbus2B 80 }

mbus2BValue25		OBJECT-TYPE
			SYNTAX	INTEGER
			ACCESS	read-only
			STATUS	current
	DESCRIPTION ""
			::= { mbus2B 81 }

mbus2BVIF26		OBJECT-TYPE
			SYNTAX	INTEGER
			ACCESS	read-only
			STATUS	current
	DESCRIPTION ""
			::= { mbus2B 82 }

mbus2BValue26		OBJECT-TYPE
			SYNTAX	INTEGER
			ACCESS	read-only
			STATUS	current
	DESCRIPTION ""
			::= { mbus2B 83 }

mbus2BVIF27		OBJECT-TYPE
			SYNTAX	INTEGER
			ACCESS	read-only
			STATUS	current
	DESCRIPTION ""
			::= { mbus2B 84 }

mbus2BValue27		OBJECT-TYPE
			SYNTAX	INTEGER
			ACCESS	read-only
			STATUS	current
	DESCRIPTION ""
			::= { mbus2B 85 }

mbus2BVIF28		OBJECT-TYPE
			SYNTAX	INTEGER
			ACCESS	read-only
			STATUS	current
	DESCRIPTION ""
			::= { mbus2B 86 }

mbus2BValue28		OBJECT-TYPE
			SYNTAX	INTEGER
			ACCESS	read-only
			STATUS	current
	DESCRIPTION ""
			::= { mbus2B 87 }

mbus2BVIF29		OBJECT-TYPE
			SYNTAX	INTEGER
			ACCESS	read-only
			STATUS	current
	DESCRIPTION ""
			::= { mbus2B 88 }

mbus2BValue29		OBJECT-TYPE
			SYNTAX	INTEGER
			ACCESS	read-only
			STATUS	current
	DESCRIPTION ""
			::= { mbus2B 89 }

mbus2BVIF2A		OBJECT-TYPE
			SYNTAX	INTEGER
			ACCESS	read-only
			STATUS	current
	DESCRIPTION ""
			::= { mbus2B 90 }

mbus2BValue2A		OBJECT-TYPE
			SYNTAX	INTEGER
			ACCESS	read-only
			STATUS	current
	DESCRIPTION ""
			::= { mbus2B 91 }

mbus2BVIF2B		OBJECT-TYPE
			SYNTAX	INTEGER
			ACCESS	read-only
			STATUS	current
	DESCRIPTION ""
			::= { mbus2B 92 }

mbus2BValue2B		OBJECT-TYPE
			SYNTAX	INTEGER
			ACCESS	read-only
			STATUS	current
	DESCRIPTION ""
			::= { mbus2B 93 }

mbus2BVIF2C		OBJECT-TYPE
			SYNTAX	INTEGER
			ACCESS	read-only
			STATUS	current
	DESCRIPTION ""
			::= { mbus2B 94 }

mbus2BValue2C		OBJECT-TYPE
			SYNTAX	INTEGER
			ACCESS	read-only
			STATUS	current
	DESCRIPTION ""
			::= { mbus2B 95 }

mbus2BVIF2D		OBJECT-TYPE
			SYNTAX	INTEGER
			ACCESS	read-only
			STATUS	current
	DESCRIPTION ""
			::= { mbus2B 96 }

mbus2BValue2D		OBJECT-TYPE
			SYNTAX	INTEGER
			ACCESS	read-only
			STATUS	current
	DESCRIPTION ""
			::= { mbus2B 97 }

mbus2BVIF2E		OBJECT-TYPE
			SYNTAX	INTEGER
			ACCESS	read-only
			STATUS	current
	DESCRIPTION ""
			::= { mbus2B 98 }

mbus2BValue2E		OBJECT-TYPE
			SYNTAX	INTEGER
			ACCESS	read-only
			STATUS	current
	DESCRIPTION ""
			::= { mbus2B 99 }

mbus2BVIF2F		OBJECT-TYPE
			SYNTAX	INTEGER
			ACCESS	read-only
			STATUS	current
	DESCRIPTION ""
			::= { mbus2B 100 }

mbus2BValue2F		OBJECT-TYPE
			SYNTAX	INTEGER
			ACCESS	read-only
			STATUS	current
	DESCRIPTION ""
			::= { mbus2B 101 }

mbus2C			OBJECT IDENTIFIER ::= { mbus 44 }

mbus2CIdNumber		OBJECT-TYPE
			SYNTAX	Gauge
			ACCESS	read-only
			STATUS	current
	DESCRIPTION ""
			::= { mbus2C 1 }

mbus2CManufacturer	OBJECT-TYPE
			SYNTAX	Gauge
			ACCESS	read-only
			STATUS	current
	DESCRIPTION ""
			::= { mbus2C 2 }

mbus2CVersion		OBJECT-TYPE
			SYNTAX	Gauge
			ACCESS	read-only
			STATUS	current
	DESCRIPTION ""
			::= { mbus2C 3 }

mbus2CMedium		OBJECT-TYPE
			SYNTAX	Gauge
			ACCESS	read-only
			STATUS	current
	DESCRIPTION ""
			::= { mbus2C 4 }

mbus2CStatus		OBJECT-TYPE
			SYNTAX	Gauge
			ACCESS	read-only
			STATUS	current
	DESCRIPTION ""
			::= { mbus2C 5 }

mbus2CVIF00		OBJECT-TYPE
			SYNTAX	INTEGER
			ACCESS	read-only
			STATUS	current
	DESCRIPTION ""
			::= { mbus2C 6 }

mbus2CValue00		OBJECT-TYPE
			SYNTAX	INTEGER
			ACCESS	read-only
			STATUS	current
	DESCRIPTION ""
			::= { mbus2C 7 }

mbus2CVIF01		OBJECT-TYPE
			SYNTAX	INTEGER
			ACCESS	read-only
			STATUS	current
	DESCRIPTION ""
			::= { mbus2C 8 }

mbus2CValue01		OBJECT-TYPE
			SYNTAX	INTEGER
			ACCESS	read-only
			STATUS	current
	DESCRIPTION ""
			::= { mbus2C 9 }

mbus2CVIF02		OBJECT-TYPE
			SYNTAX	INTEGER
			ACCESS	read-only
			STATUS	current
	DESCRIPTION ""
			::= { mbus2C 10 }

mbus2CValue02		OBJECT-TYPE
			SYNTAX	INTEGER
			ACCESS	read-only
			STATUS	current
	DESCRIPTION ""
			::= { mbus2C 11 }

mbus2CVIF03		OBJECT-TYPE
			SYNTAX	INTEGER
			ACCESS	read-only
			STATUS	current
	DESCRIPTION ""
			::= { mbus2C 12 }

mbus2CValue03		OBJECT-TYPE
			SYNTAX	INTEGER
			ACCESS	read-only
			STATUS	current
	DESCRIPTION ""
			::= { mbus2C 13 }

mbus2CVIF04		OBJECT-TYPE
			SYNTAX	INTEGER
			ACCESS	read-only
			STATUS	current
	DESCRIPTION ""
			::= { mbus2C 14 }

mbus2CValue04		OBJECT-TYPE
			SYNTAX	INTEGER
			ACCESS	read-only
			STATUS	current
	DESCRIPTION ""
			::= { mbus2C 15 }

mbus2CVIF05		OBJECT-TYPE
			SYNTAX	INTEGER
			ACCESS	read-only
			STATUS	current
	DESCRIPTION ""
			::= { mbus2C 16 }

mbus2CValue05		OBJECT-TYPE
			SYNTAX	INTEGER
			ACCESS	read-only
			STATUS	current
	DESCRIPTION ""
			::= { mbus2C 17 }

mbus2CVIF06		OBJECT-TYPE
			SYNTAX	INTEGER
			ACCESS	read-only
			STATUS	current
	DESCRIPTION ""
			::= { mbus2C 18 }

mbus2CValue06		OBJECT-TYPE
			SYNTAX	INTEGER
			ACCESS	read-only
			STATUS	current
	DESCRIPTION ""
			::= { mbus2C 19 }

mbus2CVIF07		OBJECT-TYPE
			SYNTAX	INTEGER
			ACCESS	read-only
			STATUS	current
	DESCRIPTION ""
			::= { mbus2C 20 }

mbus2CValue07		OBJECT-TYPE
			SYNTAX	INTEGER
			ACCESS	read-only
			STATUS	current
	DESCRIPTION ""
			::= { mbus2C 21 }

mbus2CVIF08		OBJECT-TYPE
			SYNTAX	INTEGER
			ACCESS	read-only
			STATUS	current
	DESCRIPTION ""
			::= { mbus2C 22 }

mbus2CValue08		OBJECT-TYPE
			SYNTAX	INTEGER
			ACCESS	read-only
			STATUS	current
	DESCRIPTION ""
			::= { mbus2C 23 }

mbus2CVIF09		OBJECT-TYPE
			SYNTAX	INTEGER
			ACCESS	read-only
			STATUS	current
	DESCRIPTION ""
			::= { mbus2C 24 }

mbus2CValue09		OBJECT-TYPE
			SYNTAX	INTEGER
			ACCESS	read-only
			STATUS	current
	DESCRIPTION ""
			::= { mbus2C 25 }

mbus2CVIF0A		OBJECT-TYPE
			SYNTAX	INTEGER
			ACCESS	read-only
			STATUS	current
	DESCRIPTION ""
			::= { mbus2C 26 }

mbus2CValue0A		OBJECT-TYPE
			SYNTAX	INTEGER
			ACCESS	read-only
			STATUS	current
	DESCRIPTION ""
			::= { mbus2C 27 }

mbus2CVIF0B		OBJECT-TYPE
			SYNTAX	INTEGER
			ACCESS	read-only
			STATUS	current
	DESCRIPTION ""
			::= { mbus2C 28 }

mbus2CValue0B		OBJECT-TYPE
			SYNTAX	INTEGER
			ACCESS	read-only
			STATUS	current
	DESCRIPTION ""
			::= { mbus2C 29 }

mbus2CVIF0C		OBJECT-TYPE
			SYNTAX	INTEGER
			ACCESS	read-only
			STATUS	current
	DESCRIPTION ""
			::= { mbus2C 30 }

mbus2CValue0C		OBJECT-TYPE
			SYNTAX	INTEGER
			ACCESS	read-only
			STATUS	current
	DESCRIPTION ""
			::= { mbus2C 31 }

mbus2CVIF0D		OBJECT-TYPE
			SYNTAX	INTEGER
			ACCESS	read-only
			STATUS	current
	DESCRIPTION ""
			::= { mbus2C 32 }

mbus2CValue0D		OBJECT-TYPE
			SYNTAX	INTEGER
			ACCESS	read-only
			STATUS	current
	DESCRIPTION ""
			::= { mbus2C 33 }

mbus2CVIF0E		OBJECT-TYPE
			SYNTAX	INTEGER
			ACCESS	read-only
			STATUS	current
	DESCRIPTION ""
			::= { mbus2C 34 }

mbus2CValue0E		OBJECT-TYPE
			SYNTAX	INTEGER
			ACCESS	read-only
			STATUS	current
	DESCRIPTION ""
			::= { mbus2C 35 }

mbus2CVIF0F		OBJECT-TYPE
			SYNTAX	INTEGER
			ACCESS	read-only
			STATUS	current
	DESCRIPTION ""
			::= { mbus2C 36 }

mbus2CValue0F		OBJECT-TYPE
			SYNTAX	INTEGER
			ACCESS	read-only
			STATUS	current
	DESCRIPTION ""
			::= { mbus2C 37 }

mbus2CVIF10		OBJECT-TYPE
			SYNTAX	INTEGER
			ACCESS	read-only
			STATUS	current
	DESCRIPTION ""
			::= { mbus2C 38 }

mbus2CValue10		OBJECT-TYPE
			SYNTAX	INTEGER
			ACCESS	read-only
			STATUS	current
	DESCRIPTION ""
			::= { mbus2C 39 }

mbus2CVIF11		OBJECT-TYPE
			SYNTAX	INTEGER
			ACCESS	read-only
			STATUS	current
	DESCRIPTION ""
			::= { mbus2C 40 }

mbus2CValue11		OBJECT-TYPE
			SYNTAX	INTEGER
			ACCESS	read-only
			STATUS	current
	DESCRIPTION ""
			::= { mbus2C 41 }

mbus2CVIF12		OBJECT-TYPE
			SYNTAX	INTEGER
			ACCESS	read-only
			STATUS	current
	DESCRIPTION ""
			::= { mbus2C 42 }

mbus2CValue12		OBJECT-TYPE
			SYNTAX	INTEGER
			ACCESS	read-only
			STATUS	current
	DESCRIPTION ""
			::= { mbus2C 43 }

mbus2CVIF13		OBJECT-TYPE
			SYNTAX	INTEGER
			ACCESS	read-only
			STATUS	current
	DESCRIPTION ""
			::= { mbus2C 44 }

mbus2CValue13		OBJECT-TYPE
			SYNTAX	INTEGER
			ACCESS	read-only
			STATUS	current
	DESCRIPTION ""
			::= { mbus2C 45 }

mbus2CVIF14		OBJECT-TYPE
			SYNTAX	INTEGER
			ACCESS	read-only
			STATUS	current
	DESCRIPTION ""
			::= { mbus2C 46 }

mbus2CValue14		OBJECT-TYPE
			SYNTAX	INTEGER
			ACCESS	read-only
			STATUS	current
	DESCRIPTION ""
			::= { mbus2C 47 }

mbus2CVIF15		OBJECT-TYPE
			SYNTAX	INTEGER
			ACCESS	read-only
			STATUS	current
	DESCRIPTION ""
			::= { mbus2C 48 }

mbus2CValue15		OBJECT-TYPE
			SYNTAX	INTEGER
			ACCESS	read-only
			STATUS	current
	DESCRIPTION ""
			::= { mbus2C 49 }

mbus2CVIF16		OBJECT-TYPE
			SYNTAX	INTEGER
			ACCESS	read-only
			STATUS	current
	DESCRIPTION ""
			::= { mbus2C 50 }

mbus2CValue16		OBJECT-TYPE
			SYNTAX	INTEGER
			ACCESS	read-only
			STATUS	current
	DESCRIPTION ""
			::= { mbus2C 51 }

mbus2CVIF17		OBJECT-TYPE
			SYNTAX	INTEGER
			ACCESS	read-only
			STATUS	current
	DESCRIPTION ""
			::= { mbus2C 52 }

mbus2CValue17		OBJECT-TYPE
			SYNTAX	INTEGER
			ACCESS	read-only
			STATUS	current
	DESCRIPTION ""
			::= { mbus2C 53 }

mbus2CVIF18		OBJECT-TYPE
			SYNTAX	INTEGER
			ACCESS	read-only
			STATUS	current
	DESCRIPTION ""
			::= { mbus2C 54 }

mbus2CValue18		OBJECT-TYPE
			SYNTAX	INTEGER
			ACCESS	read-only
			STATUS	current
	DESCRIPTION ""
			::= { mbus2C 55 }

mbus2CVIF19		OBJECT-TYPE
			SYNTAX	INTEGER
			ACCESS	read-only
			STATUS	current
	DESCRIPTION ""
			::= { mbus2C 56 }

mbus2CValue19		OBJECT-TYPE
			SYNTAX	INTEGER
			ACCESS	read-only
			STATUS	current
	DESCRIPTION ""
			::= { mbus2C 57 }

mbus2CVIF1A		OBJECT-TYPE
			SYNTAX	INTEGER
			ACCESS	read-only
			STATUS	current
	DESCRIPTION ""
			::= { mbus2C 58 }

mbus2CValue1A		OBJECT-TYPE
			SYNTAX	INTEGER
			ACCESS	read-only
			STATUS	current
	DESCRIPTION ""
			::= { mbus2C 59 }

mbus2CVIF1B		OBJECT-TYPE
			SYNTAX	INTEGER
			ACCESS	read-only
			STATUS	current
	DESCRIPTION ""
			::= { mbus2C 60 }

mbus2CValue1B		OBJECT-TYPE
			SYNTAX	INTEGER
			ACCESS	read-only
			STATUS	current
	DESCRIPTION ""
			::= { mbus2C 61 }

mbus2CVIF1C		OBJECT-TYPE
			SYNTAX	INTEGER
			ACCESS	read-only
			STATUS	current
	DESCRIPTION ""
			::= { mbus2C 62 }

mbus2CValue1C		OBJECT-TYPE
			SYNTAX	INTEGER
			ACCESS	read-only
			STATUS	current
	DESCRIPTION ""
			::= { mbus2C 63 }

mbus2CVIF1D		OBJECT-TYPE
			SYNTAX	INTEGER
			ACCESS	read-only
			STATUS	current
	DESCRIPTION ""
			::= { mbus2C 64 }

mbus2CValue1D		OBJECT-TYPE
			SYNTAX	INTEGER
			ACCESS	read-only
			STATUS	current
	DESCRIPTION ""
			::= { mbus2C 65 }

mbus2CVIF1E		OBJECT-TYPE
			SYNTAX	INTEGER
			ACCESS	read-only
			STATUS	current
	DESCRIPTION ""
			::= { mbus2C 66 }

mbus2CValue1E		OBJECT-TYPE
			SYNTAX	INTEGER
			ACCESS	read-only
			STATUS	current
	DESCRIPTION ""
			::= { mbus2C 67 }

mbus2CVIF1F		OBJECT-TYPE
			SYNTAX	INTEGER
			ACCESS	read-only
			STATUS	current
	DESCRIPTION ""
			::= { mbus2C 68 }

mbus2CValue1F		OBJECT-TYPE
			SYNTAX	INTEGER
			ACCESS	read-only
			STATUS	current
	DESCRIPTION ""
			::= { mbus2C 69 }

mbus2CVIF20		OBJECT-TYPE
			SYNTAX	INTEGER
			ACCESS	read-only
			STATUS	current
	DESCRIPTION ""
			::= { mbus2C 70 }

mbus2CValue20		OBJECT-TYPE
			SYNTAX	INTEGER
			ACCESS	read-only
			STATUS	current
	DESCRIPTION ""
			::= { mbus2C 71 }

mbus2CVIF21		OBJECT-TYPE
			SYNTAX	INTEGER
			ACCESS	read-only
			STATUS	current
	DESCRIPTION ""
			::= { mbus2C 72 }

mbus2CValue21		OBJECT-TYPE
			SYNTAX	INTEGER
			ACCESS	read-only
			STATUS	current
	DESCRIPTION ""
			::= { mbus2C 73 }

mbus2CVIF22		OBJECT-TYPE
			SYNTAX	INTEGER
			ACCESS	read-only
			STATUS	current
	DESCRIPTION ""
			::= { mbus2C 74 }

mbus2CValue22		OBJECT-TYPE
			SYNTAX	INTEGER
			ACCESS	read-only
			STATUS	current
	DESCRIPTION ""
			::= { mbus2C 75 }

mbus2CVIF23		OBJECT-TYPE
			SYNTAX	INTEGER
			ACCESS	read-only
			STATUS	current
	DESCRIPTION ""
			::= { mbus2C 76 }

mbus2CValue23		OBJECT-TYPE
			SYNTAX	INTEGER
			ACCESS	read-only
			STATUS	current
	DESCRIPTION ""
			::= { mbus2C 77 }

mbus2CVIF24		OBJECT-TYPE
			SYNTAX	INTEGER
			ACCESS	read-only
			STATUS	current
	DESCRIPTION ""
			::= { mbus2C 78 }

mbus2CValue24		OBJECT-TYPE
			SYNTAX	INTEGER
			ACCESS	read-only
			STATUS	current
	DESCRIPTION ""
			::= { mbus2C 79 }

mbus2CVIF25		OBJECT-TYPE
			SYNTAX	INTEGER
			ACCESS	read-only
			STATUS	current
	DESCRIPTION ""
			::= { mbus2C 80 }

mbus2CValue25		OBJECT-TYPE
			SYNTAX	INTEGER
			ACCESS	read-only
			STATUS	current
	DESCRIPTION ""
			::= { mbus2C 81 }

mbus2CVIF26		OBJECT-TYPE
			SYNTAX	INTEGER
			ACCESS	read-only
			STATUS	current
	DESCRIPTION ""
			::= { mbus2C 82 }

mbus2CValue26		OBJECT-TYPE
			SYNTAX	INTEGER
			ACCESS	read-only
			STATUS	current
	DESCRIPTION ""
			::= { mbus2C 83 }

mbus2CVIF27		OBJECT-TYPE
			SYNTAX	INTEGER
			ACCESS	read-only
			STATUS	current
	DESCRIPTION ""
			::= { mbus2C 84 }

mbus2CValue27		OBJECT-TYPE
			SYNTAX	INTEGER
			ACCESS	read-only
			STATUS	current
	DESCRIPTION ""
			::= { mbus2C 85 }

mbus2CVIF28		OBJECT-TYPE
			SYNTAX	INTEGER
			ACCESS	read-only
			STATUS	current
	DESCRIPTION ""
			::= { mbus2C 86 }

mbus2CValue28		OBJECT-TYPE
			SYNTAX	INTEGER
			ACCESS	read-only
			STATUS	current
	DESCRIPTION ""
			::= { mbus2C 87 }

mbus2CVIF29		OBJECT-TYPE
			SYNTAX	INTEGER
			ACCESS	read-only
			STATUS	current
	DESCRIPTION ""
			::= { mbus2C 88 }

mbus2CValue29		OBJECT-TYPE
			SYNTAX	INTEGER
			ACCESS	read-only
			STATUS	current
	DESCRIPTION ""
			::= { mbus2C 89 }

mbus2CVIF2A		OBJECT-TYPE
			SYNTAX	INTEGER
			ACCESS	read-only
			STATUS	current
	DESCRIPTION ""
			::= { mbus2C 90 }

mbus2CValue2A		OBJECT-TYPE
			SYNTAX	INTEGER
			ACCESS	read-only
			STATUS	current
	DESCRIPTION ""
			::= { mbus2C 91 }

mbus2CVIF2B		OBJECT-TYPE
			SYNTAX	INTEGER
			ACCESS	read-only
			STATUS	current
	DESCRIPTION ""
			::= { mbus2C 92 }

mbus2CValue2B		OBJECT-TYPE
			SYNTAX	INTEGER
			ACCESS	read-only
			STATUS	current
	DESCRIPTION ""
			::= { mbus2C 93 }

mbus2CVIF2C		OBJECT-TYPE
			SYNTAX	INTEGER
			ACCESS	read-only
			STATUS	current
	DESCRIPTION ""
			::= { mbus2C 94 }

mbus2CValue2C		OBJECT-TYPE
			SYNTAX	INTEGER
			ACCESS	read-only
			STATUS	current
	DESCRIPTION ""
			::= { mbus2C 95 }

mbus2CVIF2D		OBJECT-TYPE
			SYNTAX	INTEGER
			ACCESS	read-only
			STATUS	current
	DESCRIPTION ""
			::= { mbus2C 96 }

mbus2CValue2D		OBJECT-TYPE
			SYNTAX	INTEGER
			ACCESS	read-only
			STATUS	current
	DESCRIPTION ""
			::= { mbus2C 97 }

mbus2CVIF2E		OBJECT-TYPE
			SYNTAX	INTEGER
			ACCESS	read-only
			STATUS	current
	DESCRIPTION ""
			::= { mbus2C 98 }

mbus2CValue2E		OBJECT-TYPE
			SYNTAX	INTEGER
			ACCESS	read-only
			STATUS	current
	DESCRIPTION ""
			::= { mbus2C 99 }

mbus2CVIF2F		OBJECT-TYPE
			SYNTAX	INTEGER
			ACCESS	read-only
			STATUS	current
	DESCRIPTION ""
			::= { mbus2C 100 }

mbus2CValue2F		OBJECT-TYPE
			SYNTAX	INTEGER
			ACCESS	read-only
			STATUS	current
	DESCRIPTION ""
			::= { mbus2C 101 }

mbus2D			OBJECT IDENTIFIER ::= { mbus 45 }

mbus2DIdNumber		OBJECT-TYPE
			SYNTAX	Gauge
			ACCESS	read-only
			STATUS	current
	DESCRIPTION ""
			::= { mbus2D 1 }

mbus2DManufacturer	OBJECT-TYPE
			SYNTAX	Gauge
			ACCESS	read-only
			STATUS	current
	DESCRIPTION ""
			::= { mbus2D 2 }

mbus2DVersion		OBJECT-TYPE
			SYNTAX	Gauge
			ACCESS	read-only
			STATUS	current
	DESCRIPTION ""
			::= { mbus2D 3 }

mbus2DMedium		OBJECT-TYPE
			SYNTAX	Gauge
			ACCESS	read-only
			STATUS	current
	DESCRIPTION ""
			::= { mbus2D 4 }

mbus2DStatus		OBJECT-TYPE
			SYNTAX	Gauge
			ACCESS	read-only
			STATUS	current
	DESCRIPTION ""
			::= { mbus2D 5 }

mbus2DVIF00		OBJECT-TYPE
			SYNTAX	INTEGER
			ACCESS	read-only
			STATUS	current
	DESCRIPTION ""
			::= { mbus2D 6 }

mbus2DValue00		OBJECT-TYPE
			SYNTAX	INTEGER
			ACCESS	read-only
			STATUS	current
	DESCRIPTION ""
			::= { mbus2D 7 }

mbus2DVIF01		OBJECT-TYPE
			SYNTAX	INTEGER
			ACCESS	read-only
			STATUS	current
	DESCRIPTION ""
			::= { mbus2D 8 }

mbus2DValue01		OBJECT-TYPE
			SYNTAX	INTEGER
			ACCESS	read-only
			STATUS	current
	DESCRIPTION ""
			::= { mbus2D 9 }

mbus2DVIF02		OBJECT-TYPE
			SYNTAX	INTEGER
			ACCESS	read-only
			STATUS	current
	DESCRIPTION ""
			::= { mbus2D 10 }

mbus2DValue02		OBJECT-TYPE
			SYNTAX	INTEGER
			ACCESS	read-only
			STATUS	current
	DESCRIPTION ""
			::= { mbus2D 11 }

mbus2DVIF03		OBJECT-TYPE
			SYNTAX	INTEGER
			ACCESS	read-only
			STATUS	current
	DESCRIPTION ""
			::= { mbus2D 12 }

mbus2DValue03		OBJECT-TYPE
			SYNTAX	INTEGER
			ACCESS	read-only
			STATUS	current
	DESCRIPTION ""
			::= { mbus2D 13 }

mbus2DVIF04		OBJECT-TYPE
			SYNTAX	INTEGER
			ACCESS	read-only
			STATUS	current
	DESCRIPTION ""
			::= { mbus2D 14 }

mbus2DValue04		OBJECT-TYPE
			SYNTAX	INTEGER
			ACCESS	read-only
			STATUS	current
	DESCRIPTION ""
			::= { mbus2D 15 }

mbus2DVIF05		OBJECT-TYPE
			SYNTAX	INTEGER
			ACCESS	read-only
			STATUS	current
	DESCRIPTION ""
			::= { mbus2D 16 }

mbus2DValue05		OBJECT-TYPE
			SYNTAX	INTEGER
			ACCESS	read-only
			STATUS	current
	DESCRIPTION ""
			::= { mbus2D 17 }

mbus2DVIF06		OBJECT-TYPE
			SYNTAX	INTEGER
			ACCESS	read-only
			STATUS	current
	DESCRIPTION ""
			::= { mbus2D 18 }

mbus2DValue06		OBJECT-TYPE
			SYNTAX	INTEGER
			ACCESS	read-only
			STATUS	current
	DESCRIPTION ""
			::= { mbus2D 19 }

mbus2DVIF07		OBJECT-TYPE
			SYNTAX	INTEGER
			ACCESS	read-only
			STATUS	current
	DESCRIPTION ""
			::= { mbus2D 20 }

mbus2DValue07		OBJECT-TYPE
			SYNTAX	INTEGER
			ACCESS	read-only
			STATUS	current
	DESCRIPTION ""
			::= { mbus2D 21 }

mbus2DVIF08		OBJECT-TYPE
			SYNTAX	INTEGER
			ACCESS	read-only
			STATUS	current
	DESCRIPTION ""
			::= { mbus2D 22 }

mbus2DValue08		OBJECT-TYPE
			SYNTAX	INTEGER
			ACCESS	read-only
			STATUS	current
	DESCRIPTION ""
			::= { mbus2D 23 }

mbus2DVIF09		OBJECT-TYPE
			SYNTAX	INTEGER
			ACCESS	read-only
			STATUS	current
	DESCRIPTION ""
			::= { mbus2D 24 }

mbus2DValue09		OBJECT-TYPE
			SYNTAX	INTEGER
			ACCESS	read-only
			STATUS	current
	DESCRIPTION ""
			::= { mbus2D 25 }

mbus2DVIF0A		OBJECT-TYPE
			SYNTAX	INTEGER
			ACCESS	read-only
			STATUS	current
	DESCRIPTION ""
			::= { mbus2D 26 }

mbus2DValue0A		OBJECT-TYPE
			SYNTAX	INTEGER
			ACCESS	read-only
			STATUS	current
	DESCRIPTION ""
			::= { mbus2D 27 }

mbus2DVIF0B		OBJECT-TYPE
			SYNTAX	INTEGER
			ACCESS	read-only
			STATUS	current
	DESCRIPTION ""
			::= { mbus2D 28 }

mbus2DValue0B		OBJECT-TYPE
			SYNTAX	INTEGER
			ACCESS	read-only
			STATUS	current
	DESCRIPTION ""
			::= { mbus2D 29 }

mbus2DVIF0C		OBJECT-TYPE
			SYNTAX	INTEGER
			ACCESS	read-only
			STATUS	current
	DESCRIPTION ""
			::= { mbus2D 30 }

mbus2DValue0C		OBJECT-TYPE
			SYNTAX	INTEGER
			ACCESS	read-only
			STATUS	current
	DESCRIPTION ""
			::= { mbus2D 31 }

mbus2DVIF0D		OBJECT-TYPE
			SYNTAX	INTEGER
			ACCESS	read-only
			STATUS	current
	DESCRIPTION ""
			::= { mbus2D 32 }

mbus2DValue0D		OBJECT-TYPE
			SYNTAX	INTEGER
			ACCESS	read-only
			STATUS	current
	DESCRIPTION ""
			::= { mbus2D 33 }

mbus2DVIF0E		OBJECT-TYPE
			SYNTAX	INTEGER
			ACCESS	read-only
			STATUS	current
	DESCRIPTION ""
			::= { mbus2D 34 }

mbus2DValue0E		OBJECT-TYPE
			SYNTAX	INTEGER
			ACCESS	read-only
			STATUS	current
	DESCRIPTION ""
			::= { mbus2D 35 }

mbus2DVIF0F		OBJECT-TYPE
			SYNTAX	INTEGER
			ACCESS	read-only
			STATUS	current
	DESCRIPTION ""
			::= { mbus2D 36 }

mbus2DValue0F		OBJECT-TYPE
			SYNTAX	INTEGER
			ACCESS	read-only
			STATUS	current
	DESCRIPTION ""
			::= { mbus2D 37 }

mbus2DVIF10		OBJECT-TYPE
			SYNTAX	INTEGER
			ACCESS	read-only
			STATUS	current
	DESCRIPTION ""
			::= { mbus2D 38 }

mbus2DValue10		OBJECT-TYPE
			SYNTAX	INTEGER
			ACCESS	read-only
			STATUS	current
	DESCRIPTION ""
			::= { mbus2D 39 }

mbus2DVIF11		OBJECT-TYPE
			SYNTAX	INTEGER
			ACCESS	read-only
			STATUS	current
	DESCRIPTION ""
			::= { mbus2D 40 }

mbus2DValue11		OBJECT-TYPE
			SYNTAX	INTEGER
			ACCESS	read-only
			STATUS	current
	DESCRIPTION ""
			::= { mbus2D 41 }

mbus2DVIF12		OBJECT-TYPE
			SYNTAX	INTEGER
			ACCESS	read-only
			STATUS	current
	DESCRIPTION ""
			::= { mbus2D 42 }

mbus2DValue12		OBJECT-TYPE
			SYNTAX	INTEGER
			ACCESS	read-only
			STATUS	current
	DESCRIPTION ""
			::= { mbus2D 43 }

mbus2DVIF13		OBJECT-TYPE
			SYNTAX	INTEGER
			ACCESS	read-only
			STATUS	current
	DESCRIPTION ""
			::= { mbus2D 44 }

mbus2DValue13		OBJECT-TYPE
			SYNTAX	INTEGER
			ACCESS	read-only
			STATUS	current
	DESCRIPTION ""
			::= { mbus2D 45 }

mbus2DVIF14		OBJECT-TYPE
			SYNTAX	INTEGER
			ACCESS	read-only
			STATUS	current
	DESCRIPTION ""
			::= { mbus2D 46 }

mbus2DValue14		OBJECT-TYPE
			SYNTAX	INTEGER
			ACCESS	read-only
			STATUS	current
	DESCRIPTION ""
			::= { mbus2D 47 }

mbus2DVIF15		OBJECT-TYPE
			SYNTAX	INTEGER
			ACCESS	read-only
			STATUS	current
	DESCRIPTION ""
			::= { mbus2D 48 }

mbus2DValue15		OBJECT-TYPE
			SYNTAX	INTEGER
			ACCESS	read-only
			STATUS	current
	DESCRIPTION ""
			::= { mbus2D 49 }

mbus2DVIF16		OBJECT-TYPE
			SYNTAX	INTEGER
			ACCESS	read-only
			STATUS	current
	DESCRIPTION ""
			::= { mbus2D 50 }

mbus2DValue16		OBJECT-TYPE
			SYNTAX	INTEGER
			ACCESS	read-only
			STATUS	current
	DESCRIPTION ""
			::= { mbus2D 51 }

mbus2DVIF17		OBJECT-TYPE
			SYNTAX	INTEGER
			ACCESS	read-only
			STATUS	current
	DESCRIPTION ""
			::= { mbus2D 52 }

mbus2DValue17		OBJECT-TYPE
			SYNTAX	INTEGER
			ACCESS	read-only
			STATUS	current
	DESCRIPTION ""
			::= { mbus2D 53 }

mbus2DVIF18		OBJECT-TYPE
			SYNTAX	INTEGER
			ACCESS	read-only
			STATUS	current
	DESCRIPTION ""
			::= { mbus2D 54 }

mbus2DValue18		OBJECT-TYPE
			SYNTAX	INTEGER
			ACCESS	read-only
			STATUS	current
	DESCRIPTION ""
			::= { mbus2D 55 }

mbus2DVIF19		OBJECT-TYPE
			SYNTAX	INTEGER
			ACCESS	read-only
			STATUS	current
	DESCRIPTION ""
			::= { mbus2D 56 }

mbus2DValue19		OBJECT-TYPE
			SYNTAX	INTEGER
			ACCESS	read-only
			STATUS	current
	DESCRIPTION ""
			::= { mbus2D 57 }

mbus2DVIF1A		OBJECT-TYPE
			SYNTAX	INTEGER
			ACCESS	read-only
			STATUS	current
	DESCRIPTION ""
			::= { mbus2D 58 }

mbus2DValue1A		OBJECT-TYPE
			SYNTAX	INTEGER
			ACCESS	read-only
			STATUS	current
	DESCRIPTION ""
			::= { mbus2D 59 }

mbus2DVIF1B		OBJECT-TYPE
			SYNTAX	INTEGER
			ACCESS	read-only
			STATUS	current
	DESCRIPTION ""
			::= { mbus2D 60 }

mbus2DValue1B		OBJECT-TYPE
			SYNTAX	INTEGER
			ACCESS	read-only
			STATUS	current
	DESCRIPTION ""
			::= { mbus2D 61 }

mbus2DVIF1C		OBJECT-TYPE
			SYNTAX	INTEGER
			ACCESS	read-only
			STATUS	current
	DESCRIPTION ""
			::= { mbus2D 62 }

mbus2DValue1C		OBJECT-TYPE
			SYNTAX	INTEGER
			ACCESS	read-only
			STATUS	current
	DESCRIPTION ""
			::= { mbus2D 63 }

mbus2DVIF1D		OBJECT-TYPE
			SYNTAX	INTEGER
			ACCESS	read-only
			STATUS	current
	DESCRIPTION ""
			::= { mbus2D 64 }

mbus2DValue1D		OBJECT-TYPE
			SYNTAX	INTEGER
			ACCESS	read-only
			STATUS	current
	DESCRIPTION ""
			::= { mbus2D 65 }

mbus2DVIF1E		OBJECT-TYPE
			SYNTAX	INTEGER
			ACCESS	read-only
			STATUS	current
	DESCRIPTION ""
			::= { mbus2D 66 }

mbus2DValue1E		OBJECT-TYPE
			SYNTAX	INTEGER
			ACCESS	read-only
			STATUS	current
	DESCRIPTION ""
			::= { mbus2D 67 }

mbus2DVIF1F		OBJECT-TYPE
			SYNTAX	INTEGER
			ACCESS	read-only
			STATUS	current
	DESCRIPTION ""
			::= { mbus2D 68 }

mbus2DValue1F		OBJECT-TYPE
			SYNTAX	INTEGER
			ACCESS	read-only
			STATUS	current
	DESCRIPTION ""
			::= { mbus2D 69 }

mbus2DVIF20		OBJECT-TYPE
			SYNTAX	INTEGER
			ACCESS	read-only
			STATUS	current
	DESCRIPTION ""
			::= { mbus2D 70 }

mbus2DValue20		OBJECT-TYPE
			SYNTAX	INTEGER
			ACCESS	read-only
			STATUS	current
	DESCRIPTION ""
			::= { mbus2D 71 }

mbus2DVIF21		OBJECT-TYPE
			SYNTAX	INTEGER
			ACCESS	read-only
			STATUS	current
	DESCRIPTION ""
			::= { mbus2D 72 }

mbus2DValue21		OBJECT-TYPE
			SYNTAX	INTEGER
			ACCESS	read-only
			STATUS	current
	DESCRIPTION ""
			::= { mbus2D 73 }

mbus2DVIF22		OBJECT-TYPE
			SYNTAX	INTEGER
			ACCESS	read-only
			STATUS	current
	DESCRIPTION ""
			::= { mbus2D 74 }

mbus2DValue22		OBJECT-TYPE
			SYNTAX	INTEGER
			ACCESS	read-only
			STATUS	current
	DESCRIPTION ""
			::= { mbus2D 75 }

mbus2DVIF23		OBJECT-TYPE
			SYNTAX	INTEGER
			ACCESS	read-only
			STATUS	current
	DESCRIPTION ""
			::= { mbus2D 76 }

mbus2DValue23		OBJECT-TYPE
			SYNTAX	INTEGER
			ACCESS	read-only
			STATUS	current
	DESCRIPTION ""
			::= { mbus2D 77 }

mbus2DVIF24		OBJECT-TYPE
			SYNTAX	INTEGER
			ACCESS	read-only
			STATUS	current
	DESCRIPTION ""
			::= { mbus2D 78 }

mbus2DValue24		OBJECT-TYPE
			SYNTAX	INTEGER
			ACCESS	read-only
			STATUS	current
	DESCRIPTION ""
			::= { mbus2D 79 }

mbus2DVIF25		OBJECT-TYPE
			SYNTAX	INTEGER
			ACCESS	read-only
			STATUS	current
	DESCRIPTION ""
			::= { mbus2D 80 }

mbus2DValue25		OBJECT-TYPE
			SYNTAX	INTEGER
			ACCESS	read-only
			STATUS	current
	DESCRIPTION ""
			::= { mbus2D 81 }

mbus2DVIF26		OBJECT-TYPE
			SYNTAX	INTEGER
			ACCESS	read-only
			STATUS	current
	DESCRIPTION ""
			::= { mbus2D 82 }

mbus2DValue26		OBJECT-TYPE
			SYNTAX	INTEGER
			ACCESS	read-only
			STATUS	current
	DESCRIPTION ""
			::= { mbus2D 83 }

mbus2DVIF27		OBJECT-TYPE
			SYNTAX	INTEGER
			ACCESS	read-only
			STATUS	current
	DESCRIPTION ""
			::= { mbus2D 84 }

mbus2DValue27		OBJECT-TYPE
			SYNTAX	INTEGER
			ACCESS	read-only
			STATUS	current
	DESCRIPTION ""
			::= { mbus2D 85 }

mbus2DVIF28		OBJECT-TYPE
			SYNTAX	INTEGER
			ACCESS	read-only
			STATUS	current
	DESCRIPTION ""
			::= { mbus2D 86 }

mbus2DValue28		OBJECT-TYPE
			SYNTAX	INTEGER
			ACCESS	read-only
			STATUS	current
	DESCRIPTION ""
			::= { mbus2D 87 }

mbus2DVIF29		OBJECT-TYPE
			SYNTAX	INTEGER
			ACCESS	read-only
			STATUS	current
	DESCRIPTION ""
			::= { mbus2D 88 }

mbus2DValue29		OBJECT-TYPE
			SYNTAX	INTEGER
			ACCESS	read-only
			STATUS	current
	DESCRIPTION ""
			::= { mbus2D 89 }

mbus2DVIF2A		OBJECT-TYPE
			SYNTAX	INTEGER
			ACCESS	read-only
			STATUS	current
	DESCRIPTION ""
			::= { mbus2D 90 }

mbus2DValue2A		OBJECT-TYPE
			SYNTAX	INTEGER
			ACCESS	read-only
			STATUS	current
	DESCRIPTION ""
			::= { mbus2D 91 }

mbus2DVIF2B		OBJECT-TYPE
			SYNTAX	INTEGER
			ACCESS	read-only
			STATUS	current
	DESCRIPTION ""
			::= { mbus2D 92 }

mbus2DValue2B		OBJECT-TYPE
			SYNTAX	INTEGER
			ACCESS	read-only
			STATUS	current
	DESCRIPTION ""
			::= { mbus2D 93 }

mbus2DVIF2C		OBJECT-TYPE
			SYNTAX	INTEGER
			ACCESS	read-only
			STATUS	current
	DESCRIPTION ""
			::= { mbus2D 94 }

mbus2DValue2C		OBJECT-TYPE
			SYNTAX	INTEGER
			ACCESS	read-only
			STATUS	current
	DESCRIPTION ""
			::= { mbus2D 95 }

mbus2DVIF2D		OBJECT-TYPE
			SYNTAX	INTEGER
			ACCESS	read-only
			STATUS	current
	DESCRIPTION ""
			::= { mbus2D 96 }

mbus2DValue2D		OBJECT-TYPE
			SYNTAX	INTEGER
			ACCESS	read-only
			STATUS	current
	DESCRIPTION ""
			::= { mbus2D 97 }

mbus2DVIF2E		OBJECT-TYPE
			SYNTAX	INTEGER
			ACCESS	read-only
			STATUS	current
	DESCRIPTION ""
			::= { mbus2D 98 }

mbus2DValue2E		OBJECT-TYPE
			SYNTAX	INTEGER
			ACCESS	read-only
			STATUS	current
	DESCRIPTION ""
			::= { mbus2D 99 }

mbus2DVIF2F		OBJECT-TYPE
			SYNTAX	INTEGER
			ACCESS	read-only
			STATUS	current
	DESCRIPTION ""
			::= { mbus2D 100 }

mbus2DValue2F		OBJECT-TYPE
			SYNTAX	INTEGER
			ACCESS	read-only
			STATUS	current
	DESCRIPTION ""
			::= { mbus2D 101 }

mbus2E			OBJECT IDENTIFIER ::= { mbus 46 }

mbus2EIdNumber		OBJECT-TYPE
			SYNTAX	Gauge
			ACCESS	read-only
			STATUS	current
	DESCRIPTION ""
			::= { mbus2E 1 }

mbus2EManufacturer	OBJECT-TYPE
			SYNTAX	Gauge
			ACCESS	read-only
			STATUS	current
	DESCRIPTION ""
			::= { mbus2E 2 }

mbus2EVersion		OBJECT-TYPE
			SYNTAX	Gauge
			ACCESS	read-only
			STATUS	current
	DESCRIPTION ""
			::= { mbus2E 3 }

mbus2EMedium		OBJECT-TYPE
			SYNTAX	Gauge
			ACCESS	read-only
			STATUS	current
	DESCRIPTION ""
			::= { mbus2E 4 }

mbus2EStatus		OBJECT-TYPE
			SYNTAX	Gauge
			ACCESS	read-only
			STATUS	current
	DESCRIPTION ""
			::= { mbus2E 5 }

mbus2EVIF00		OBJECT-TYPE
			SYNTAX	INTEGER
			ACCESS	read-only
			STATUS	current
	DESCRIPTION ""
			::= { mbus2E 6 }

mbus2EValue00		OBJECT-TYPE
			SYNTAX	INTEGER
			ACCESS	read-only
			STATUS	current
	DESCRIPTION ""
			::= { mbus2E 7 }

mbus2EVIF01		OBJECT-TYPE
			SYNTAX	INTEGER
			ACCESS	read-only
			STATUS	current
	DESCRIPTION ""
			::= { mbus2E 8 }

mbus2EValue01		OBJECT-TYPE
			SYNTAX	INTEGER
			ACCESS	read-only
			STATUS	current
	DESCRIPTION ""
			::= { mbus2E 9 }

mbus2EVIF02		OBJECT-TYPE
			SYNTAX	INTEGER
			ACCESS	read-only
			STATUS	current
	DESCRIPTION ""
			::= { mbus2E 10 }

mbus2EValue02		OBJECT-TYPE
			SYNTAX	INTEGER
			ACCESS	read-only
			STATUS	current
	DESCRIPTION ""
			::= { mbus2E 11 }

mbus2EVIF03		OBJECT-TYPE
			SYNTAX	INTEGER
			ACCESS	read-only
			STATUS	current
	DESCRIPTION ""
			::= { mbus2E 12 }

mbus2EValue03		OBJECT-TYPE
			SYNTAX	INTEGER
			ACCESS	read-only
			STATUS	current
	DESCRIPTION ""
			::= { mbus2E 13 }

mbus2EVIF04		OBJECT-TYPE
			SYNTAX	INTEGER
			ACCESS	read-only
			STATUS	current
	DESCRIPTION ""
			::= { mbus2E 14 }

mbus2EValue04		OBJECT-TYPE
			SYNTAX	INTEGER
			ACCESS	read-only
			STATUS	current
	DESCRIPTION ""
			::= { mbus2E 15 }

mbus2EVIF05		OBJECT-TYPE
			SYNTAX	INTEGER
			ACCESS	read-only
			STATUS	current
	DESCRIPTION ""
			::= { mbus2E 16 }

mbus2EValue05		OBJECT-TYPE
			SYNTAX	INTEGER
			ACCESS	read-only
			STATUS	current
	DESCRIPTION ""
			::= { mbus2E 17 }

mbus2EVIF06		OBJECT-TYPE
			SYNTAX	INTEGER
			ACCESS	read-only
			STATUS	current
	DESCRIPTION ""
			::= { mbus2E 18 }

mbus2EValue06		OBJECT-TYPE
			SYNTAX	INTEGER
			ACCESS	read-only
			STATUS	current
	DESCRIPTION ""
			::= { mbus2E 19 }

mbus2EVIF07		OBJECT-TYPE
			SYNTAX	INTEGER
			ACCESS	read-only
			STATUS	current
	DESCRIPTION ""
			::= { mbus2E 20 }

mbus2EValue07		OBJECT-TYPE
			SYNTAX	INTEGER
			ACCESS	read-only
			STATUS	current
	DESCRIPTION ""
			::= { mbus2E 21 }

mbus2EVIF08		OBJECT-TYPE
			SYNTAX	INTEGER
			ACCESS	read-only
			STATUS	current
	DESCRIPTION ""
			::= { mbus2E 22 }

mbus2EValue08		OBJECT-TYPE
			SYNTAX	INTEGER
			ACCESS	read-only
			STATUS	current
	DESCRIPTION ""
			::= { mbus2E 23 }

mbus2EVIF09		OBJECT-TYPE
			SYNTAX	INTEGER
			ACCESS	read-only
			STATUS	current
	DESCRIPTION ""
			::= { mbus2E 24 }

mbus2EValue09		OBJECT-TYPE
			SYNTAX	INTEGER
			ACCESS	read-only
			STATUS	current
	DESCRIPTION ""
			::= { mbus2E 25 }

mbus2EVIF0A		OBJECT-TYPE
			SYNTAX	INTEGER
			ACCESS	read-only
			STATUS	current
	DESCRIPTION ""
			::= { mbus2E 26 }

mbus2EValue0A		OBJECT-TYPE
			SYNTAX	INTEGER
			ACCESS	read-only
			STATUS	current
	DESCRIPTION ""
			::= { mbus2E 27 }

mbus2EVIF0B		OBJECT-TYPE
			SYNTAX	INTEGER
			ACCESS	read-only
			STATUS	current
	DESCRIPTION ""
			::= { mbus2E 28 }

mbus2EValue0B		OBJECT-TYPE
			SYNTAX	INTEGER
			ACCESS	read-only
			STATUS	current
	DESCRIPTION ""
			::= { mbus2E 29 }

mbus2EVIF0C		OBJECT-TYPE
			SYNTAX	INTEGER
			ACCESS	read-only
			STATUS	current
	DESCRIPTION ""
			::= { mbus2E 30 }

mbus2EValue0C		OBJECT-TYPE
			SYNTAX	INTEGER
			ACCESS	read-only
			STATUS	current
	DESCRIPTION ""
			::= { mbus2E 31 }

mbus2EVIF0D		OBJECT-TYPE
			SYNTAX	INTEGER
			ACCESS	read-only
			STATUS	current
	DESCRIPTION ""
			::= { mbus2E 32 }

mbus2EValue0D		OBJECT-TYPE
			SYNTAX	INTEGER
			ACCESS	read-only
			STATUS	current
	DESCRIPTION ""
			::= { mbus2E 33 }

mbus2EVIF0E		OBJECT-TYPE
			SYNTAX	INTEGER
			ACCESS	read-only
			STATUS	current
	DESCRIPTION ""
			::= { mbus2E 34 }

mbus2EValue0E		OBJECT-TYPE
			SYNTAX	INTEGER
			ACCESS	read-only
			STATUS	current
	DESCRIPTION ""
			::= { mbus2E 35 }

mbus2EVIF0F		OBJECT-TYPE
			SYNTAX	INTEGER
			ACCESS	read-only
			STATUS	current
	DESCRIPTION ""
			::= { mbus2E 36 }

mbus2EValue0F		OBJECT-TYPE
			SYNTAX	INTEGER
			ACCESS	read-only
			STATUS	current
	DESCRIPTION ""
			::= { mbus2E 37 }

mbus2EVIF10		OBJECT-TYPE
			SYNTAX	INTEGER
			ACCESS	read-only
			STATUS	current
	DESCRIPTION ""
			::= { mbus2E 38 }

mbus2EValue10		OBJECT-TYPE
			SYNTAX	INTEGER
			ACCESS	read-only
			STATUS	current
	DESCRIPTION ""
			::= { mbus2E 39 }

mbus2EVIF11		OBJECT-TYPE
			SYNTAX	INTEGER
			ACCESS	read-only
			STATUS	current
	DESCRIPTION ""
			::= { mbus2E 40 }

mbus2EValue11		OBJECT-TYPE
			SYNTAX	INTEGER
			ACCESS	read-only
			STATUS	current
	DESCRIPTION ""
			::= { mbus2E 41 }

mbus2EVIF12		OBJECT-TYPE
			SYNTAX	INTEGER
			ACCESS	read-only
			STATUS	current
	DESCRIPTION ""
			::= { mbus2E 42 }

mbus2EValue12		OBJECT-TYPE
			SYNTAX	INTEGER
			ACCESS	read-only
			STATUS	current
	DESCRIPTION ""
			::= { mbus2E 43 }

mbus2EVIF13		OBJECT-TYPE
			SYNTAX	INTEGER
			ACCESS	read-only
			STATUS	current
	DESCRIPTION ""
			::= { mbus2E 44 }

mbus2EValue13		OBJECT-TYPE
			SYNTAX	INTEGER
			ACCESS	read-only
			STATUS	current
	DESCRIPTION ""
			::= { mbus2E 45 }

mbus2EVIF14		OBJECT-TYPE
			SYNTAX	INTEGER
			ACCESS	read-only
			STATUS	current
	DESCRIPTION ""
			::= { mbus2E 46 }

mbus2EValue14		OBJECT-TYPE
			SYNTAX	INTEGER
			ACCESS	read-only
			STATUS	current
	DESCRIPTION ""
			::= { mbus2E 47 }

mbus2EVIF15		OBJECT-TYPE
			SYNTAX	INTEGER
			ACCESS	read-only
			STATUS	current
	DESCRIPTION ""
			::= { mbus2E 48 }

mbus2EValue15		OBJECT-TYPE
			SYNTAX	INTEGER
			ACCESS	read-only
			STATUS	current
	DESCRIPTION ""
			::= { mbus2E 49 }

mbus2EVIF16		OBJECT-TYPE
			SYNTAX	INTEGER
			ACCESS	read-only
			STATUS	current
	DESCRIPTION ""
			::= { mbus2E 50 }

mbus2EValue16		OBJECT-TYPE
			SYNTAX	INTEGER
			ACCESS	read-only
			STATUS	current
	DESCRIPTION ""
			::= { mbus2E 51 }

mbus2EVIF17		OBJECT-TYPE
			SYNTAX	INTEGER
			ACCESS	read-only
			STATUS	current
	DESCRIPTION ""
			::= { mbus2E 52 }

mbus2EValue17		OBJECT-TYPE
			SYNTAX	INTEGER
			ACCESS	read-only
			STATUS	current
	DESCRIPTION ""
			::= { mbus2E 53 }

mbus2EVIF18		OBJECT-TYPE
			SYNTAX	INTEGER
			ACCESS	read-only
			STATUS	current
	DESCRIPTION ""
			::= { mbus2E 54 }

mbus2EValue18		OBJECT-TYPE
			SYNTAX	INTEGER
			ACCESS	read-only
			STATUS	current
	DESCRIPTION ""
			::= { mbus2E 55 }

mbus2EVIF19		OBJECT-TYPE
			SYNTAX	INTEGER
			ACCESS	read-only
			STATUS	current
	DESCRIPTION ""
			::= { mbus2E 56 }

mbus2EValue19		OBJECT-TYPE
			SYNTAX	INTEGER
			ACCESS	read-only
			STATUS	current
	DESCRIPTION ""
			::= { mbus2E 57 }

mbus2EVIF1A		OBJECT-TYPE
			SYNTAX	INTEGER
			ACCESS	read-only
			STATUS	current
	DESCRIPTION ""
			::= { mbus2E 58 }

mbus2EValue1A		OBJECT-TYPE
			SYNTAX	INTEGER
			ACCESS	read-only
			STATUS	current
	DESCRIPTION ""
			::= { mbus2E 59 }

mbus2EVIF1B		OBJECT-TYPE
			SYNTAX	INTEGER
			ACCESS	read-only
			STATUS	current
	DESCRIPTION ""
			::= { mbus2E 60 }

mbus2EValue1B		OBJECT-TYPE
			SYNTAX	INTEGER
			ACCESS	read-only
			STATUS	current
	DESCRIPTION ""
			::= { mbus2E 61 }

mbus2EVIF1C		OBJECT-TYPE
			SYNTAX	INTEGER
			ACCESS	read-only
			STATUS	current
	DESCRIPTION ""
			::= { mbus2E 62 }

mbus2EValue1C		OBJECT-TYPE
			SYNTAX	INTEGER
			ACCESS	read-only
			STATUS	current
	DESCRIPTION ""
			::= { mbus2E 63 }

mbus2EVIF1D		OBJECT-TYPE
			SYNTAX	INTEGER
			ACCESS	read-only
			STATUS	current
	DESCRIPTION ""
			::= { mbus2E 64 }

mbus2EValue1D		OBJECT-TYPE
			SYNTAX	INTEGER
			ACCESS	read-only
			STATUS	current
	DESCRIPTION ""
			::= { mbus2E 65 }

mbus2EVIF1E		OBJECT-TYPE
			SYNTAX	INTEGER
			ACCESS	read-only
			STATUS	current
	DESCRIPTION ""
			::= { mbus2E 66 }

mbus2EValue1E		OBJECT-TYPE
			SYNTAX	INTEGER
			ACCESS	read-only
			STATUS	current
	DESCRIPTION ""
			::= { mbus2E 67 }

mbus2EVIF1F		OBJECT-TYPE
			SYNTAX	INTEGER
			ACCESS	read-only
			STATUS	current
	DESCRIPTION ""
			::= { mbus2E 68 }

mbus2EValue1F		OBJECT-TYPE
			SYNTAX	INTEGER
			ACCESS	read-only
			STATUS	current
	DESCRIPTION ""
			::= { mbus2E 69 }

mbus2EVIF20		OBJECT-TYPE
			SYNTAX	INTEGER
			ACCESS	read-only
			STATUS	current
	DESCRIPTION ""
			::= { mbus2E 70 }

mbus2EValue20		OBJECT-TYPE
			SYNTAX	INTEGER
			ACCESS	read-only
			STATUS	current
	DESCRIPTION ""
			::= { mbus2E 71 }

mbus2EVIF21		OBJECT-TYPE
			SYNTAX	INTEGER
			ACCESS	read-only
			STATUS	current
	DESCRIPTION ""
			::= { mbus2E 72 }

mbus2EValue21		OBJECT-TYPE
			SYNTAX	INTEGER
			ACCESS	read-only
			STATUS	current
	DESCRIPTION ""
			::= { mbus2E 73 }

mbus2EVIF22		OBJECT-TYPE
			SYNTAX	INTEGER
			ACCESS	read-only
			STATUS	current
	DESCRIPTION ""
			::= { mbus2E 74 }

mbus2EValue22		OBJECT-TYPE
			SYNTAX	INTEGER
			ACCESS	read-only
			STATUS	current
	DESCRIPTION ""
			::= { mbus2E 75 }

mbus2EVIF23		OBJECT-TYPE
			SYNTAX	INTEGER
			ACCESS	read-only
			STATUS	current
	DESCRIPTION ""
			::= { mbus2E 76 }

mbus2EValue23		OBJECT-TYPE
			SYNTAX	INTEGER
			ACCESS	read-only
			STATUS	current
	DESCRIPTION ""
			::= { mbus2E 77 }

mbus2EVIF24		OBJECT-TYPE
			SYNTAX	INTEGER
			ACCESS	read-only
			STATUS	current
	DESCRIPTION ""
			::= { mbus2E 78 }

mbus2EValue24		OBJECT-TYPE
			SYNTAX	INTEGER
			ACCESS	read-only
			STATUS	current
	DESCRIPTION ""
			::= { mbus2E 79 }

mbus2EVIF25		OBJECT-TYPE
			SYNTAX	INTEGER
			ACCESS	read-only
			STATUS	current
	DESCRIPTION ""
			::= { mbus2E 80 }

mbus2EValue25		OBJECT-TYPE
			SYNTAX	INTEGER
			ACCESS	read-only
			STATUS	current
	DESCRIPTION ""
			::= { mbus2E 81 }

mbus2EVIF26		OBJECT-TYPE
			SYNTAX	INTEGER
			ACCESS	read-only
			STATUS	current
	DESCRIPTION ""
			::= { mbus2E 82 }

mbus2EValue26		OBJECT-TYPE
			SYNTAX	INTEGER
			ACCESS	read-only
			STATUS	current
	DESCRIPTION ""
			::= { mbus2E 83 }

mbus2EVIF27		OBJECT-TYPE
			SYNTAX	INTEGER
			ACCESS	read-only
			STATUS	current
	DESCRIPTION ""
			::= { mbus2E 84 }

mbus2EValue27		OBJECT-TYPE
			SYNTAX	INTEGER
			ACCESS	read-only
			STATUS	current
	DESCRIPTION ""
			::= { mbus2E 85 }

mbus2EVIF28		OBJECT-TYPE
			SYNTAX	INTEGER
			ACCESS	read-only
			STATUS	current
	DESCRIPTION ""
			::= { mbus2E 86 }

mbus2EValue28		OBJECT-TYPE
			SYNTAX	INTEGER
			ACCESS	read-only
			STATUS	current
	DESCRIPTION ""
			::= { mbus2E 87 }

mbus2EVIF29		OBJECT-TYPE
			SYNTAX	INTEGER
			ACCESS	read-only
			STATUS	current
	DESCRIPTION ""
			::= { mbus2E 88 }

mbus2EValue29		OBJECT-TYPE
			SYNTAX	INTEGER
			ACCESS	read-only
			STATUS	current
	DESCRIPTION ""
			::= { mbus2E 89 }

mbus2EVIF2A		OBJECT-TYPE
			SYNTAX	INTEGER
			ACCESS	read-only
			STATUS	current
	DESCRIPTION ""
			::= { mbus2E 90 }

mbus2EValue2A		OBJECT-TYPE
			SYNTAX	INTEGER
			ACCESS	read-only
			STATUS	current
	DESCRIPTION ""
			::= { mbus2E 91 }

mbus2EVIF2B		OBJECT-TYPE
			SYNTAX	INTEGER
			ACCESS	read-only
			STATUS	current
	DESCRIPTION ""
			::= { mbus2E 92 }

mbus2EValue2B		OBJECT-TYPE
			SYNTAX	INTEGER
			ACCESS	read-only
			STATUS	current
	DESCRIPTION ""
			::= { mbus2E 93 }

mbus2EVIF2C		OBJECT-TYPE
			SYNTAX	INTEGER
			ACCESS	read-only
			STATUS	current
	DESCRIPTION ""
			::= { mbus2E 94 }

mbus2EValue2C		OBJECT-TYPE
			SYNTAX	INTEGER
			ACCESS	read-only
			STATUS	current
	DESCRIPTION ""
			::= { mbus2E 95 }

mbus2EVIF2D		OBJECT-TYPE
			SYNTAX	INTEGER
			ACCESS	read-only
			STATUS	current
	DESCRIPTION ""
			::= { mbus2E 96 }

mbus2EValue2D		OBJECT-TYPE
			SYNTAX	INTEGER
			ACCESS	read-only
			STATUS	current
	DESCRIPTION ""
			::= { mbus2E 97 }

mbus2EVIF2E		OBJECT-TYPE
			SYNTAX	INTEGER
			ACCESS	read-only
			STATUS	current
	DESCRIPTION ""
			::= { mbus2E 98 }

mbus2EValue2E		OBJECT-TYPE
			SYNTAX	INTEGER
			ACCESS	read-only
			STATUS	current
	DESCRIPTION ""
			::= { mbus2E 99 }

mbus2EVIF2F		OBJECT-TYPE
			SYNTAX	INTEGER
			ACCESS	read-only
			STATUS	current
	DESCRIPTION ""
			::= { mbus2E 100 }

mbus2EValue2F		OBJECT-TYPE
			SYNTAX	INTEGER
			ACCESS	read-only
			STATUS	current
	DESCRIPTION ""
			::= { mbus2E 101 }

mbus2F			OBJECT IDENTIFIER ::= { mbus 47 }

mbus2FIdNumber		OBJECT-TYPE
			SYNTAX	Gauge
			ACCESS	read-only
			STATUS	current
	DESCRIPTION ""
			::= { mbus2F 1 }

mbus2FManufacturer	OBJECT-TYPE
			SYNTAX	Gauge
			ACCESS	read-only
			STATUS	current
	DESCRIPTION ""
			::= { mbus2F 2 }

mbus2FVersion		OBJECT-TYPE
			SYNTAX	Gauge
			ACCESS	read-only
			STATUS	current
	DESCRIPTION ""
			::= { mbus2F 3 }

mbus2FMedium		OBJECT-TYPE
			SYNTAX	Gauge
			ACCESS	read-only
			STATUS	current
	DESCRIPTION ""
			::= { mbus2F 4 }

mbus2FStatus		OBJECT-TYPE
			SYNTAX	Gauge
			ACCESS	read-only
			STATUS	current
	DESCRIPTION ""
			::= { mbus2F 5 }

mbus2FVIF00		OBJECT-TYPE
			SYNTAX	INTEGER
			ACCESS	read-only
			STATUS	current
	DESCRIPTION ""
			::= { mbus2F 6 }

mbus2FValue00		OBJECT-TYPE
			SYNTAX	INTEGER
			ACCESS	read-only
			STATUS	current
	DESCRIPTION ""
			::= { mbus2F 7 }

mbus2FVIF01		OBJECT-TYPE
			SYNTAX	INTEGER
			ACCESS	read-only
			STATUS	current
	DESCRIPTION ""
			::= { mbus2F 8 }

mbus2FValue01		OBJECT-TYPE
			SYNTAX	INTEGER
			ACCESS	read-only
			STATUS	current
	DESCRIPTION ""
			::= { mbus2F 9 }

mbus2FVIF02		OBJECT-TYPE
			SYNTAX	INTEGER
			ACCESS	read-only
			STATUS	current
	DESCRIPTION ""
			::= { mbus2F 10 }

mbus2FValue02		OBJECT-TYPE
			SYNTAX	INTEGER
			ACCESS	read-only
			STATUS	current
	DESCRIPTION ""
			::= { mbus2F 11 }

mbus2FVIF03		OBJECT-TYPE
			SYNTAX	INTEGER
			ACCESS	read-only
			STATUS	current
	DESCRIPTION ""
			::= { mbus2F 12 }

mbus2FValue03		OBJECT-TYPE
			SYNTAX	INTEGER
			ACCESS	read-only
			STATUS	current
	DESCRIPTION ""
			::= { mbus2F 13 }

mbus2FVIF04		OBJECT-TYPE
			SYNTAX	INTEGER
			ACCESS	read-only
			STATUS	current
	DESCRIPTION ""
			::= { mbus2F 14 }

mbus2FValue04		OBJECT-TYPE
			SYNTAX	INTEGER
			ACCESS	read-only
			STATUS	current
	DESCRIPTION ""
			::= { mbus2F 15 }

mbus2FVIF05		OBJECT-TYPE
			SYNTAX	INTEGER
			ACCESS	read-only
			STATUS	current
	DESCRIPTION ""
			::= { mbus2F 16 }

mbus2FValue05		OBJECT-TYPE
			SYNTAX	INTEGER
			ACCESS	read-only
			STATUS	current
	DESCRIPTION ""
			::= { mbus2F 17 }

mbus2FVIF06		OBJECT-TYPE
			SYNTAX	INTEGER
			ACCESS	read-only
			STATUS	current
	DESCRIPTION ""
			::= { mbus2F 18 }

mbus2FValue06		OBJECT-TYPE
			SYNTAX	INTEGER
			ACCESS	read-only
			STATUS	current
	DESCRIPTION ""
			::= { mbus2F 19 }

mbus2FVIF07		OBJECT-TYPE
			SYNTAX	INTEGER
			ACCESS	read-only
			STATUS	current
	DESCRIPTION ""
			::= { mbus2F 20 }

mbus2FValue07		OBJECT-TYPE
			SYNTAX	INTEGER
			ACCESS	read-only
			STATUS	current
	DESCRIPTION ""
			::= { mbus2F 21 }

mbus2FVIF08		OBJECT-TYPE
			SYNTAX	INTEGER
			ACCESS	read-only
			STATUS	current
	DESCRIPTION ""
			::= { mbus2F 22 }

mbus2FValue08		OBJECT-TYPE
			SYNTAX	INTEGER
			ACCESS	read-only
			STATUS	current
	DESCRIPTION ""
			::= { mbus2F 23 }

mbus2FVIF09		OBJECT-TYPE
			SYNTAX	INTEGER
			ACCESS	read-only
			STATUS	current
	DESCRIPTION ""
			::= { mbus2F 24 }

mbus2FValue09		OBJECT-TYPE
			SYNTAX	INTEGER
			ACCESS	read-only
			STATUS	current
	DESCRIPTION ""
			::= { mbus2F 25 }

mbus2FVIF0A		OBJECT-TYPE
			SYNTAX	INTEGER
			ACCESS	read-only
			STATUS	current
	DESCRIPTION ""
			::= { mbus2F 26 }

mbus2FValue0A		OBJECT-TYPE
			SYNTAX	INTEGER
			ACCESS	read-only
			STATUS	current
	DESCRIPTION ""
			::= { mbus2F 27 }

mbus2FVIF0B		OBJECT-TYPE
			SYNTAX	INTEGER
			ACCESS	read-only
			STATUS	current
	DESCRIPTION ""
			::= { mbus2F 28 }

mbus2FValue0B		OBJECT-TYPE
			SYNTAX	INTEGER
			ACCESS	read-only
			STATUS	current
	DESCRIPTION ""
			::= { mbus2F 29 }

mbus2FVIF0C		OBJECT-TYPE
			SYNTAX	INTEGER
			ACCESS	read-only
			STATUS	current
	DESCRIPTION ""
			::= { mbus2F 30 }

mbus2FValue0C		OBJECT-TYPE
			SYNTAX	INTEGER
			ACCESS	read-only
			STATUS	current
	DESCRIPTION ""
			::= { mbus2F 31 }

mbus2FVIF0D		OBJECT-TYPE
			SYNTAX	INTEGER
			ACCESS	read-only
			STATUS	current
	DESCRIPTION ""
			::= { mbus2F 32 }

mbus2FValue0D		OBJECT-TYPE
			SYNTAX	INTEGER
			ACCESS	read-only
			STATUS	current
	DESCRIPTION ""
			::= { mbus2F 33 }

mbus2FVIF0E		OBJECT-TYPE
			SYNTAX	INTEGER
			ACCESS	read-only
			STATUS	current
	DESCRIPTION ""
			::= { mbus2F 34 }

mbus2FValue0E		OBJECT-TYPE
			SYNTAX	INTEGER
			ACCESS	read-only
			STATUS	current
	DESCRIPTION ""
			::= { mbus2F 35 }

mbus2FVIF0F		OBJECT-TYPE
			SYNTAX	INTEGER
			ACCESS	read-only
			STATUS	current
	DESCRIPTION ""
			::= { mbus2F 36 }

mbus2FValue0F		OBJECT-TYPE
			SYNTAX	INTEGER
			ACCESS	read-only
			STATUS	current
	DESCRIPTION ""
			::= { mbus2F 37 }

mbus2FVIF10		OBJECT-TYPE
			SYNTAX	INTEGER
			ACCESS	read-only
			STATUS	current
	DESCRIPTION ""
			::= { mbus2F 38 }

mbus2FValue10		OBJECT-TYPE
			SYNTAX	INTEGER
			ACCESS	read-only
			STATUS	current
	DESCRIPTION ""
			::= { mbus2F 39 }

mbus2FVIF11		OBJECT-TYPE
			SYNTAX	INTEGER
			ACCESS	read-only
			STATUS	current
	DESCRIPTION ""
			::= { mbus2F 40 }

mbus2FValue11		OBJECT-TYPE
			SYNTAX	INTEGER
			ACCESS	read-only
			STATUS	current
	DESCRIPTION ""
			::= { mbus2F 41 }

mbus2FVIF12		OBJECT-TYPE
			SYNTAX	INTEGER
			ACCESS	read-only
			STATUS	current
	DESCRIPTION ""
			::= { mbus2F 42 }

mbus2FValue12		OBJECT-TYPE
			SYNTAX	INTEGER
			ACCESS	read-only
			STATUS	current
	DESCRIPTION ""
			::= { mbus2F 43 }

mbus2FVIF13		OBJECT-TYPE
			SYNTAX	INTEGER
			ACCESS	read-only
			STATUS	current
	DESCRIPTION ""
			::= { mbus2F 44 }

mbus2FValue13		OBJECT-TYPE
			SYNTAX	INTEGER
			ACCESS	read-only
			STATUS	current
	DESCRIPTION ""
			::= { mbus2F 45 }

mbus2FVIF14		OBJECT-TYPE
			SYNTAX	INTEGER
			ACCESS	read-only
			STATUS	current
	DESCRIPTION ""
			::= { mbus2F 46 }

mbus2FValue14		OBJECT-TYPE
			SYNTAX	INTEGER
			ACCESS	read-only
			STATUS	current
	DESCRIPTION ""
			::= { mbus2F 47 }

mbus2FVIF15		OBJECT-TYPE
			SYNTAX	INTEGER
			ACCESS	read-only
			STATUS	current
	DESCRIPTION ""
			::= { mbus2F 48 }

mbus2FValue15		OBJECT-TYPE
			SYNTAX	INTEGER
			ACCESS	read-only
			STATUS	current
	DESCRIPTION ""
			::= { mbus2F 49 }

mbus2FVIF16		OBJECT-TYPE
			SYNTAX	INTEGER
			ACCESS	read-only
			STATUS	current
	DESCRIPTION ""
			::= { mbus2F 50 }

mbus2FValue16		OBJECT-TYPE
			SYNTAX	INTEGER
			ACCESS	read-only
			STATUS	current
	DESCRIPTION ""
			::= { mbus2F 51 }

mbus2FVIF17		OBJECT-TYPE
			SYNTAX	INTEGER
			ACCESS	read-only
			STATUS	current
	DESCRIPTION ""
			::= { mbus2F 52 }

mbus2FValue17		OBJECT-TYPE
			SYNTAX	INTEGER
			ACCESS	read-only
			STATUS	current
	DESCRIPTION ""
			::= { mbus2F 53 }

mbus2FVIF18		OBJECT-TYPE
			SYNTAX	INTEGER
			ACCESS	read-only
			STATUS	current
	DESCRIPTION ""
			::= { mbus2F 54 }

mbus2FValue18		OBJECT-TYPE
			SYNTAX	INTEGER
			ACCESS	read-only
			STATUS	current
	DESCRIPTION ""
			::= { mbus2F 55 }

mbus2FVIF19		OBJECT-TYPE
			SYNTAX	INTEGER
			ACCESS	read-only
			STATUS	current
	DESCRIPTION ""
			::= { mbus2F 56 }

mbus2FValue19		OBJECT-TYPE
			SYNTAX	INTEGER
			ACCESS	read-only
			STATUS	current
	DESCRIPTION ""
			::= { mbus2F 57 }

mbus2FVIF1A		OBJECT-TYPE
			SYNTAX	INTEGER
			ACCESS	read-only
			STATUS	current
	DESCRIPTION ""
			::= { mbus2F 58 }

mbus2FValue1A		OBJECT-TYPE
			SYNTAX	INTEGER
			ACCESS	read-only
			STATUS	current
	DESCRIPTION ""
			::= { mbus2F 59 }

mbus2FVIF1B		OBJECT-TYPE
			SYNTAX	INTEGER
			ACCESS	read-only
			STATUS	current
	DESCRIPTION ""
			::= { mbus2F 60 }

mbus2FValue1B		OBJECT-TYPE
			SYNTAX	INTEGER
			ACCESS	read-only
			STATUS	current
	DESCRIPTION ""
			::= { mbus2F 61 }

mbus2FVIF1C		OBJECT-TYPE
			SYNTAX	INTEGER
			ACCESS	read-only
			STATUS	current
	DESCRIPTION ""
			::= { mbus2F 62 }

mbus2FValue1C		OBJECT-TYPE
			SYNTAX	INTEGER
			ACCESS	read-only
			STATUS	current
	DESCRIPTION ""
			::= { mbus2F 63 }

mbus2FVIF1D		OBJECT-TYPE
			SYNTAX	INTEGER
			ACCESS	read-only
			STATUS	current
	DESCRIPTION ""
			::= { mbus2F 64 }

mbus2FValue1D		OBJECT-TYPE
			SYNTAX	INTEGER
			ACCESS	read-only
			STATUS	current
	DESCRIPTION ""
			::= { mbus2F 65 }

mbus2FVIF1E		OBJECT-TYPE
			SYNTAX	INTEGER
			ACCESS	read-only
			STATUS	current
	DESCRIPTION ""
			::= { mbus2F 66 }

mbus2FValue1E		OBJECT-TYPE
			SYNTAX	INTEGER
			ACCESS	read-only
			STATUS	current
	DESCRIPTION ""
			::= { mbus2F 67 }

mbus2FVIF1F		OBJECT-TYPE
			SYNTAX	INTEGER
			ACCESS	read-only
			STATUS	current
	DESCRIPTION ""
			::= { mbus2F 68 }

mbus2FValue1F		OBJECT-TYPE
			SYNTAX	INTEGER
			ACCESS	read-only
			STATUS	current
	DESCRIPTION ""
			::= { mbus2F 69 }

mbus2FVIF20		OBJECT-TYPE
			SYNTAX	INTEGER
			ACCESS	read-only
			STATUS	current
	DESCRIPTION ""
			::= { mbus2F 70 }

mbus2FValue20		OBJECT-TYPE
			SYNTAX	INTEGER
			ACCESS	read-only
			STATUS	current
	DESCRIPTION ""
			::= { mbus2F 71 }

mbus2FVIF21		OBJECT-TYPE
			SYNTAX	INTEGER
			ACCESS	read-only
			STATUS	current
	DESCRIPTION ""
			::= { mbus2F 72 }

mbus2FValue21		OBJECT-TYPE
			SYNTAX	INTEGER
			ACCESS	read-only
			STATUS	current
	DESCRIPTION ""
			::= { mbus2F 73 }

mbus2FVIF22		OBJECT-TYPE
			SYNTAX	INTEGER
			ACCESS	read-only
			STATUS	current
	DESCRIPTION ""
			::= { mbus2F 74 }

mbus2FValue22		OBJECT-TYPE
			SYNTAX	INTEGER
			ACCESS	read-only
			STATUS	current
	DESCRIPTION ""
			::= { mbus2F 75 }

mbus2FVIF23		OBJECT-TYPE
			SYNTAX	INTEGER
			ACCESS	read-only
			STATUS	current
	DESCRIPTION ""
			::= { mbus2F 76 }

mbus2FValue23		OBJECT-TYPE
			SYNTAX	INTEGER
			ACCESS	read-only
			STATUS	current
	DESCRIPTION ""
			::= { mbus2F 77 }

mbus2FVIF24		OBJECT-TYPE
			SYNTAX	INTEGER
			ACCESS	read-only
			STATUS	current
	DESCRIPTION ""
			::= { mbus2F 78 }

mbus2FValue24		OBJECT-TYPE
			SYNTAX	INTEGER
			ACCESS	read-only
			STATUS	current
	DESCRIPTION ""
			::= { mbus2F 79 }

mbus2FVIF25		OBJECT-TYPE
			SYNTAX	INTEGER
			ACCESS	read-only
			STATUS	current
	DESCRIPTION ""
			::= { mbus2F 80 }

mbus2FValue25		OBJECT-TYPE
			SYNTAX	INTEGER
			ACCESS	read-only
			STATUS	current
	DESCRIPTION ""
			::= { mbus2F 81 }

mbus2FVIF26		OBJECT-TYPE
			SYNTAX	INTEGER
			ACCESS	read-only
			STATUS	current
	DESCRIPTION ""
			::= { mbus2F 82 }

mbus2FValue26		OBJECT-TYPE
			SYNTAX	INTEGER
			ACCESS	read-only
			STATUS	current
	DESCRIPTION ""
			::= { mbus2F 83 }

mbus2FVIF27		OBJECT-TYPE
			SYNTAX	INTEGER
			ACCESS	read-only
			STATUS	current
	DESCRIPTION ""
			::= { mbus2F 84 }

mbus2FValue27		OBJECT-TYPE
			SYNTAX	INTEGER
			ACCESS	read-only
			STATUS	current
	DESCRIPTION ""
			::= { mbus2F 85 }

mbus2FVIF28		OBJECT-TYPE
			SYNTAX	INTEGER
			ACCESS	read-only
			STATUS	current
	DESCRIPTION ""
			::= { mbus2F 86 }

mbus2FValue28		OBJECT-TYPE
			SYNTAX	INTEGER
			ACCESS	read-only
			STATUS	current
	DESCRIPTION ""
			::= { mbus2F 87 }

mbus2FVIF29		OBJECT-TYPE
			SYNTAX	INTEGER
			ACCESS	read-only
			STATUS	current
	DESCRIPTION ""
			::= { mbus2F 88 }

mbus2FValue29		OBJECT-TYPE
			SYNTAX	INTEGER
			ACCESS	read-only
			STATUS	current
	DESCRIPTION ""
			::= { mbus2F 89 }

mbus2FVIF2A		OBJECT-TYPE
			SYNTAX	INTEGER
			ACCESS	read-only
			STATUS	current
	DESCRIPTION ""
			::= { mbus2F 90 }

mbus2FValue2A		OBJECT-TYPE
			SYNTAX	INTEGER
			ACCESS	read-only
			STATUS	current
	DESCRIPTION ""
			::= { mbus2F 91 }

mbus2FVIF2B		OBJECT-TYPE
			SYNTAX	INTEGER
			ACCESS	read-only
			STATUS	current
	DESCRIPTION ""
			::= { mbus2F 92 }

mbus2FValue2B		OBJECT-TYPE
			SYNTAX	INTEGER
			ACCESS	read-only
			STATUS	current
	DESCRIPTION ""
			::= { mbus2F 93 }

mbus2FVIF2C		OBJECT-TYPE
			SYNTAX	INTEGER
			ACCESS	read-only
			STATUS	current
	DESCRIPTION ""
			::= { mbus2F 94 }

mbus2FValue2C		OBJECT-TYPE
			SYNTAX	INTEGER
			ACCESS	read-only
			STATUS	current
	DESCRIPTION ""
			::= { mbus2F 95 }

mbus2FVIF2D		OBJECT-TYPE
			SYNTAX	INTEGER
			ACCESS	read-only
			STATUS	current
	DESCRIPTION ""
			::= { mbus2F 96 }

mbus2FValue2D		OBJECT-TYPE
			SYNTAX	INTEGER
			ACCESS	read-only
			STATUS	current
	DESCRIPTION ""
			::= { mbus2F 97 }

mbus2FVIF2E		OBJECT-TYPE
			SYNTAX	INTEGER
			ACCESS	read-only
			STATUS	current
	DESCRIPTION ""
			::= { mbus2F 98 }

mbus2FValue2E		OBJECT-TYPE
			SYNTAX	INTEGER
			ACCESS	read-only
			STATUS	current
	DESCRIPTION ""
			::= { mbus2F 99 }

mbus2FVIF2F		OBJECT-TYPE
			SYNTAX	INTEGER
			ACCESS	read-only
			STATUS	current
	DESCRIPTION ""
			::= { mbus2F 100 }

mbus2FValue2F		OBJECT-TYPE
			SYNTAX	INTEGER
			ACCESS	read-only
			STATUS	current
	DESCRIPTION ""
			::= { mbus2F 101 }

mbus30			OBJECT IDENTIFIER ::= { mbus 48 }

mbus30IdNumber		OBJECT-TYPE
			SYNTAX	Gauge
			ACCESS	read-only
			STATUS	current
	DESCRIPTION ""
			::= { mbus30 1 }

mbus30Manufacturer	OBJECT-TYPE
			SYNTAX	Gauge
			ACCESS	read-only
			STATUS	current
	DESCRIPTION ""
			::= { mbus30 2 }

mbus30Version		OBJECT-TYPE
			SYNTAX	Gauge
			ACCESS	read-only
			STATUS	current
	DESCRIPTION ""
			::= { mbus30 3 }

mbus30Medium		OBJECT-TYPE
			SYNTAX	Gauge
			ACCESS	read-only
			STATUS	current
	DESCRIPTION ""
			::= { mbus30 4 }

mbus30Status		OBJECT-TYPE
			SYNTAX	Gauge
			ACCESS	read-only
			STATUS	current
	DESCRIPTION ""
			::= { mbus30 5 }

mbus30VIF00		OBJECT-TYPE
			SYNTAX	INTEGER
			ACCESS	read-only
			STATUS	current
	DESCRIPTION ""
			::= { mbus30 6 }

mbus30Value00		OBJECT-TYPE
			SYNTAX	INTEGER
			ACCESS	read-only
			STATUS	current
	DESCRIPTION ""
			::= { mbus30 7 }

mbus30VIF01		OBJECT-TYPE
			SYNTAX	INTEGER
			ACCESS	read-only
			STATUS	current
	DESCRIPTION ""
			::= { mbus30 8 }

mbus30Value01		OBJECT-TYPE
			SYNTAX	INTEGER
			ACCESS	read-only
			STATUS	current
	DESCRIPTION ""
			::= { mbus30 9 }

mbus30VIF02		OBJECT-TYPE
			SYNTAX	INTEGER
			ACCESS	read-only
			STATUS	current
	DESCRIPTION ""
			::= { mbus30 10 }

mbus30Value02		OBJECT-TYPE
			SYNTAX	INTEGER
			ACCESS	read-only
			STATUS	current
	DESCRIPTION ""
			::= { mbus30 11 }

mbus30VIF03		OBJECT-TYPE
			SYNTAX	INTEGER
			ACCESS	read-only
			STATUS	current
	DESCRIPTION ""
			::= { mbus30 12 }

mbus30Value03		OBJECT-TYPE
			SYNTAX	INTEGER
			ACCESS	read-only
			STATUS	current
	DESCRIPTION ""
			::= { mbus30 13 }

mbus30VIF04		OBJECT-TYPE
			SYNTAX	INTEGER
			ACCESS	read-only
			STATUS	current
	DESCRIPTION ""
			::= { mbus30 14 }

mbus30Value04		OBJECT-TYPE
			SYNTAX	INTEGER
			ACCESS	read-only
			STATUS	current
	DESCRIPTION ""
			::= { mbus30 15 }

mbus30VIF05		OBJECT-TYPE
			SYNTAX	INTEGER
			ACCESS	read-only
			STATUS	current
	DESCRIPTION ""
			::= { mbus30 16 }

mbus30Value05		OBJECT-TYPE
			SYNTAX	INTEGER
			ACCESS	read-only
			STATUS	current
	DESCRIPTION ""
			::= { mbus30 17 }

mbus30VIF06		OBJECT-TYPE
			SYNTAX	INTEGER
			ACCESS	read-only
			STATUS	current
	DESCRIPTION ""
			::= { mbus30 18 }

mbus30Value06		OBJECT-TYPE
			SYNTAX	INTEGER
			ACCESS	read-only
			STATUS	current
	DESCRIPTION ""
			::= { mbus30 19 }

mbus30VIF07		OBJECT-TYPE
			SYNTAX	INTEGER
			ACCESS	read-only
			STATUS	current
	DESCRIPTION ""
			::= { mbus30 20 }

mbus30Value07		OBJECT-TYPE
			SYNTAX	INTEGER
			ACCESS	read-only
			STATUS	current
	DESCRIPTION ""
			::= { mbus30 21 }

mbus30VIF08		OBJECT-TYPE
			SYNTAX	INTEGER
			ACCESS	read-only
			STATUS	current
	DESCRIPTION ""
			::= { mbus30 22 }

mbus30Value08		OBJECT-TYPE
			SYNTAX	INTEGER
			ACCESS	read-only
			STATUS	current
	DESCRIPTION ""
			::= { mbus30 23 }

mbus30VIF09		OBJECT-TYPE
			SYNTAX	INTEGER
			ACCESS	read-only
			STATUS	current
	DESCRIPTION ""
			::= { mbus30 24 }

mbus30Value09		OBJECT-TYPE
			SYNTAX	INTEGER
			ACCESS	read-only
			STATUS	current
	DESCRIPTION ""
			::= { mbus30 25 }

mbus30VIF0A		OBJECT-TYPE
			SYNTAX	INTEGER
			ACCESS	read-only
			STATUS	current
	DESCRIPTION ""
			::= { mbus30 26 }

mbus30Value0A		OBJECT-TYPE
			SYNTAX	INTEGER
			ACCESS	read-only
			STATUS	current
	DESCRIPTION ""
			::= { mbus30 27 }

mbus30VIF0B		OBJECT-TYPE
			SYNTAX	INTEGER
			ACCESS	read-only
			STATUS	current
	DESCRIPTION ""
			::= { mbus30 28 }

mbus30Value0B		OBJECT-TYPE
			SYNTAX	INTEGER
			ACCESS	read-only
			STATUS	current
	DESCRIPTION ""
			::= { mbus30 29 }

mbus30VIF0C		OBJECT-TYPE
			SYNTAX	INTEGER
			ACCESS	read-only
			STATUS	current
	DESCRIPTION ""
			::= { mbus30 30 }

mbus30Value0C		OBJECT-TYPE
			SYNTAX	INTEGER
			ACCESS	read-only
			STATUS	current
	DESCRIPTION ""
			::= { mbus30 31 }

mbus30VIF0D		OBJECT-TYPE
			SYNTAX	INTEGER
			ACCESS	read-only
			STATUS	current
	DESCRIPTION ""
			::= { mbus30 32 }

mbus30Value0D		OBJECT-TYPE
			SYNTAX	INTEGER
			ACCESS	read-only
			STATUS	current
	DESCRIPTION ""
			::= { mbus30 33 }

mbus30VIF0E		OBJECT-TYPE
			SYNTAX	INTEGER
			ACCESS	read-only
			STATUS	current
	DESCRIPTION ""
			::= { mbus30 34 }

mbus30Value0E		OBJECT-TYPE
			SYNTAX	INTEGER
			ACCESS	read-only
			STATUS	current
	DESCRIPTION ""
			::= { mbus30 35 }

mbus30VIF0F		OBJECT-TYPE
			SYNTAX	INTEGER
			ACCESS	read-only
			STATUS	current
	DESCRIPTION ""
			::= { mbus30 36 }

mbus30Value0F		OBJECT-TYPE
			SYNTAX	INTEGER
			ACCESS	read-only
			STATUS	current
	DESCRIPTION ""
			::= { mbus30 37 }

mbus30VIF10		OBJECT-TYPE
			SYNTAX	INTEGER
			ACCESS	read-only
			STATUS	current
	DESCRIPTION ""
			::= { mbus30 38 }

mbus30Value10		OBJECT-TYPE
			SYNTAX	INTEGER
			ACCESS	read-only
			STATUS	current
	DESCRIPTION ""
			::= { mbus30 39 }

mbus30VIF11		OBJECT-TYPE
			SYNTAX	INTEGER
			ACCESS	read-only
			STATUS	current
	DESCRIPTION ""
			::= { mbus30 40 }

mbus30Value11		OBJECT-TYPE
			SYNTAX	INTEGER
			ACCESS	read-only
			STATUS	current
	DESCRIPTION ""
			::= { mbus30 41 }

mbus30VIF12		OBJECT-TYPE
			SYNTAX	INTEGER
			ACCESS	read-only
			STATUS	current
	DESCRIPTION ""
			::= { mbus30 42 }

mbus30Value12		OBJECT-TYPE
			SYNTAX	INTEGER
			ACCESS	read-only
			STATUS	current
	DESCRIPTION ""
			::= { mbus30 43 }

mbus30VIF13		OBJECT-TYPE
			SYNTAX	INTEGER
			ACCESS	read-only
			STATUS	current
	DESCRIPTION ""
			::= { mbus30 44 }

mbus30Value13		OBJECT-TYPE
			SYNTAX	INTEGER
			ACCESS	read-only
			STATUS	current
	DESCRIPTION ""
			::= { mbus30 45 }

mbus30VIF14		OBJECT-TYPE
			SYNTAX	INTEGER
			ACCESS	read-only
			STATUS	current
	DESCRIPTION ""
			::= { mbus30 46 }

mbus30Value14		OBJECT-TYPE
			SYNTAX	INTEGER
			ACCESS	read-only
			STATUS	current
	DESCRIPTION ""
			::= { mbus30 47 }

mbus30VIF15		OBJECT-TYPE
			SYNTAX	INTEGER
			ACCESS	read-only
			STATUS	current
	DESCRIPTION ""
			::= { mbus30 48 }

mbus30Value15		OBJECT-TYPE
			SYNTAX	INTEGER
			ACCESS	read-only
			STATUS	current
	DESCRIPTION ""
			::= { mbus30 49 }

mbus30VIF16		OBJECT-TYPE
			SYNTAX	INTEGER
			ACCESS	read-only
			STATUS	current
	DESCRIPTION ""
			::= { mbus30 50 }

mbus30Value16		OBJECT-TYPE
			SYNTAX	INTEGER
			ACCESS	read-only
			STATUS	current
	DESCRIPTION ""
			::= { mbus30 51 }

mbus30VIF17		OBJECT-TYPE
			SYNTAX	INTEGER
			ACCESS	read-only
			STATUS	current
	DESCRIPTION ""
			::= { mbus30 52 }

mbus30Value17		OBJECT-TYPE
			SYNTAX	INTEGER
			ACCESS	read-only
			STATUS	current
	DESCRIPTION ""
			::= { mbus30 53 }

mbus30VIF18		OBJECT-TYPE
			SYNTAX	INTEGER
			ACCESS	read-only
			STATUS	current
	DESCRIPTION ""
			::= { mbus30 54 }

mbus30Value18		OBJECT-TYPE
			SYNTAX	INTEGER
			ACCESS	read-only
			STATUS	current
	DESCRIPTION ""
			::= { mbus30 55 }

mbus30VIF19		OBJECT-TYPE
			SYNTAX	INTEGER
			ACCESS	read-only
			STATUS	current
	DESCRIPTION ""
			::= { mbus30 56 }

mbus30Value19		OBJECT-TYPE
			SYNTAX	INTEGER
			ACCESS	read-only
			STATUS	current
	DESCRIPTION ""
			::= { mbus30 57 }

mbus30VIF1A		OBJECT-TYPE
			SYNTAX	INTEGER
			ACCESS	read-only
			STATUS	current
	DESCRIPTION ""
			::= { mbus30 58 }

mbus30Value1A		OBJECT-TYPE
			SYNTAX	INTEGER
			ACCESS	read-only
			STATUS	current
	DESCRIPTION ""
			::= { mbus30 59 }

mbus30VIF1B		OBJECT-TYPE
			SYNTAX	INTEGER
			ACCESS	read-only
			STATUS	current
	DESCRIPTION ""
			::= { mbus30 60 }

mbus30Value1B		OBJECT-TYPE
			SYNTAX	INTEGER
			ACCESS	read-only
			STATUS	current
	DESCRIPTION ""
			::= { mbus30 61 }

mbus30VIF1C		OBJECT-TYPE
			SYNTAX	INTEGER
			ACCESS	read-only
			STATUS	current
	DESCRIPTION ""
			::= { mbus30 62 }

mbus30Value1C		OBJECT-TYPE
			SYNTAX	INTEGER
			ACCESS	read-only
			STATUS	current
	DESCRIPTION ""
			::= { mbus30 63 }

mbus30VIF1D		OBJECT-TYPE
			SYNTAX	INTEGER
			ACCESS	read-only
			STATUS	current
	DESCRIPTION ""
			::= { mbus30 64 }

mbus30Value1D		OBJECT-TYPE
			SYNTAX	INTEGER
			ACCESS	read-only
			STATUS	current
	DESCRIPTION ""
			::= { mbus30 65 }

mbus30VIF1E		OBJECT-TYPE
			SYNTAX	INTEGER
			ACCESS	read-only
			STATUS	current
	DESCRIPTION ""
			::= { mbus30 66 }

mbus30Value1E		OBJECT-TYPE
			SYNTAX	INTEGER
			ACCESS	read-only
			STATUS	current
	DESCRIPTION ""
			::= { mbus30 67 }

mbus30VIF1F		OBJECT-TYPE
			SYNTAX	INTEGER
			ACCESS	read-only
			STATUS	current
	DESCRIPTION ""
			::= { mbus30 68 }

mbus30Value1F		OBJECT-TYPE
			SYNTAX	INTEGER
			ACCESS	read-only
			STATUS	current
	DESCRIPTION ""
			::= { mbus30 69 }

mbus30VIF20		OBJECT-TYPE
			SYNTAX	INTEGER
			ACCESS	read-only
			STATUS	current
	DESCRIPTION ""
			::= { mbus30 70 }

mbus30Value20		OBJECT-TYPE
			SYNTAX	INTEGER
			ACCESS	read-only
			STATUS	current
	DESCRIPTION ""
			::= { mbus30 71 }

mbus30VIF21		OBJECT-TYPE
			SYNTAX	INTEGER
			ACCESS	read-only
			STATUS	current
	DESCRIPTION ""
			::= { mbus30 72 }

mbus30Value21		OBJECT-TYPE
			SYNTAX	INTEGER
			ACCESS	read-only
			STATUS	current
	DESCRIPTION ""
			::= { mbus30 73 }

mbus30VIF22		OBJECT-TYPE
			SYNTAX	INTEGER
			ACCESS	read-only
			STATUS	current
	DESCRIPTION ""
			::= { mbus30 74 }

mbus30Value22		OBJECT-TYPE
			SYNTAX	INTEGER
			ACCESS	read-only
			STATUS	current
	DESCRIPTION ""
			::= { mbus30 75 }

mbus30VIF23		OBJECT-TYPE
			SYNTAX	INTEGER
			ACCESS	read-only
			STATUS	current
	DESCRIPTION ""
			::= { mbus30 76 }

mbus30Value23		OBJECT-TYPE
			SYNTAX	INTEGER
			ACCESS	read-only
			STATUS	current
	DESCRIPTION ""
			::= { mbus30 77 }

mbus30VIF24		OBJECT-TYPE
			SYNTAX	INTEGER
			ACCESS	read-only
			STATUS	current
	DESCRIPTION ""
			::= { mbus30 78 }

mbus30Value24		OBJECT-TYPE
			SYNTAX	INTEGER
			ACCESS	read-only
			STATUS	current
	DESCRIPTION ""
			::= { mbus30 79 }

mbus30VIF25		OBJECT-TYPE
			SYNTAX	INTEGER
			ACCESS	read-only
			STATUS	current
	DESCRIPTION ""
			::= { mbus30 80 }

mbus30Value25		OBJECT-TYPE
			SYNTAX	INTEGER
			ACCESS	read-only
			STATUS	current
	DESCRIPTION ""
			::= { mbus30 81 }

mbus30VIF26		OBJECT-TYPE
			SYNTAX	INTEGER
			ACCESS	read-only
			STATUS	current
	DESCRIPTION ""
			::= { mbus30 82 }

mbus30Value26		OBJECT-TYPE
			SYNTAX	INTEGER
			ACCESS	read-only
			STATUS	current
	DESCRIPTION ""
			::= { mbus30 83 }

mbus30VIF27		OBJECT-TYPE
			SYNTAX	INTEGER
			ACCESS	read-only
			STATUS	current
	DESCRIPTION ""
			::= { mbus30 84 }

mbus30Value27		OBJECT-TYPE
			SYNTAX	INTEGER
			ACCESS	read-only
			STATUS	current
	DESCRIPTION ""
			::= { mbus30 85 }

mbus30VIF28		OBJECT-TYPE
			SYNTAX	INTEGER
			ACCESS	read-only
			STATUS	current
	DESCRIPTION ""
			::= { mbus30 86 }

mbus30Value28		OBJECT-TYPE
			SYNTAX	INTEGER
			ACCESS	read-only
			STATUS	current
	DESCRIPTION ""
			::= { mbus30 87 }

mbus30VIF29		OBJECT-TYPE
			SYNTAX	INTEGER
			ACCESS	read-only
			STATUS	current
	DESCRIPTION ""
			::= { mbus30 88 }

mbus30Value29		OBJECT-TYPE
			SYNTAX	INTEGER
			ACCESS	read-only
			STATUS	current
	DESCRIPTION ""
			::= { mbus30 89 }

mbus30VIF2A		OBJECT-TYPE
			SYNTAX	INTEGER
			ACCESS	read-only
			STATUS	current
	DESCRIPTION ""
			::= { mbus30 90 }

mbus30Value2A		OBJECT-TYPE
			SYNTAX	INTEGER
			ACCESS	read-only
			STATUS	current
	DESCRIPTION ""
			::= { mbus30 91 }

mbus30VIF2B		OBJECT-TYPE
			SYNTAX	INTEGER
			ACCESS	read-only
			STATUS	current
	DESCRIPTION ""
			::= { mbus30 92 }

mbus30Value2B		OBJECT-TYPE
			SYNTAX	INTEGER
			ACCESS	read-only
			STATUS	current
	DESCRIPTION ""
			::= { mbus30 93 }

mbus30VIF2C		OBJECT-TYPE
			SYNTAX	INTEGER
			ACCESS	read-only
			STATUS	current
	DESCRIPTION ""
			::= { mbus30 94 }

mbus30Value2C		OBJECT-TYPE
			SYNTAX	INTEGER
			ACCESS	read-only
			STATUS	current
	DESCRIPTION ""
			::= { mbus30 95 }

mbus30VIF2D		OBJECT-TYPE
			SYNTAX	INTEGER
			ACCESS	read-only
			STATUS	current
	DESCRIPTION ""
			::= { mbus30 96 }

mbus30Value2D		OBJECT-TYPE
			SYNTAX	INTEGER
			ACCESS	read-only
			STATUS	current
	DESCRIPTION ""
			::= { mbus30 97 }

mbus30VIF2E		OBJECT-TYPE
			SYNTAX	INTEGER
			ACCESS	read-only
			STATUS	current
	DESCRIPTION ""
			::= { mbus30 98 }

mbus30Value2E		OBJECT-TYPE
			SYNTAX	INTEGER
			ACCESS	read-only
			STATUS	current
	DESCRIPTION ""
			::= { mbus30 99 }

mbus30VIF2F		OBJECT-TYPE
			SYNTAX	INTEGER
			ACCESS	read-only
			STATUS	current
	DESCRIPTION ""
			::= { mbus30 100 }

mbus30Value2F		OBJECT-TYPE
			SYNTAX	INTEGER
			ACCESS	read-only
			STATUS	current
	DESCRIPTION ""
			::= { mbus30 101 }

mbus31			OBJECT IDENTIFIER ::= { mbus 49 }

mbus31IdNumber		OBJECT-TYPE
			SYNTAX	Gauge
			ACCESS	read-only
			STATUS	current
	DESCRIPTION ""
			::= { mbus31 1 }

mbus31Manufacturer	OBJECT-TYPE
			SYNTAX	Gauge
			ACCESS	read-only
			STATUS	current
	DESCRIPTION ""
			::= { mbus31 2 }

mbus31Version		OBJECT-TYPE
			SYNTAX	Gauge
			ACCESS	read-only
			STATUS	current
	DESCRIPTION ""
			::= { mbus31 3 }

mbus31Medium		OBJECT-TYPE
			SYNTAX	Gauge
			ACCESS	read-only
			STATUS	current
	DESCRIPTION ""
			::= { mbus31 4 }

mbus31Status		OBJECT-TYPE
			SYNTAX	Gauge
			ACCESS	read-only
			STATUS	current
	DESCRIPTION ""
			::= { mbus31 5 }

mbus31VIF00		OBJECT-TYPE
			SYNTAX	INTEGER
			ACCESS	read-only
			STATUS	current
	DESCRIPTION ""
			::= { mbus31 6 }

mbus31Value00		OBJECT-TYPE
			SYNTAX	INTEGER
			ACCESS	read-only
			STATUS	current
	DESCRIPTION ""
			::= { mbus31 7 }

mbus31VIF01		OBJECT-TYPE
			SYNTAX	INTEGER
			ACCESS	read-only
			STATUS	current
	DESCRIPTION ""
			::= { mbus31 8 }

mbus31Value01		OBJECT-TYPE
			SYNTAX	INTEGER
			ACCESS	read-only
			STATUS	current
	DESCRIPTION ""
			::= { mbus31 9 }

mbus31VIF02		OBJECT-TYPE
			SYNTAX	INTEGER
			ACCESS	read-only
			STATUS	current
	DESCRIPTION ""
			::= { mbus31 10 }

mbus31Value02		OBJECT-TYPE
			SYNTAX	INTEGER
			ACCESS	read-only
			STATUS	current
	DESCRIPTION ""
			::= { mbus31 11 }

mbus31VIF03		OBJECT-TYPE
			SYNTAX	INTEGER
			ACCESS	read-only
			STATUS	current
	DESCRIPTION ""
			::= { mbus31 12 }

mbus31Value03		OBJECT-TYPE
			SYNTAX	INTEGER
			ACCESS	read-only
			STATUS	current
	DESCRIPTION ""
			::= { mbus31 13 }

mbus31VIF04		OBJECT-TYPE
			SYNTAX	INTEGER
			ACCESS	read-only
			STATUS	current
	DESCRIPTION ""
			::= { mbus31 14 }

mbus31Value04		OBJECT-TYPE
			SYNTAX	INTEGER
			ACCESS	read-only
			STATUS	current
	DESCRIPTION ""
			::= { mbus31 15 }

mbus31VIF05		OBJECT-TYPE
			SYNTAX	INTEGER
			ACCESS	read-only
			STATUS	current
	DESCRIPTION ""
			::= { mbus31 16 }

mbus31Value05		OBJECT-TYPE
			SYNTAX	INTEGER
			ACCESS	read-only
			STATUS	current
	DESCRIPTION ""
			::= { mbus31 17 }

mbus31VIF06		OBJECT-TYPE
			SYNTAX	INTEGER
			ACCESS	read-only
			STATUS	current
	DESCRIPTION ""
			::= { mbus31 18 }

mbus31Value06		OBJECT-TYPE
			SYNTAX	INTEGER
			ACCESS	read-only
			STATUS	current
	DESCRIPTION ""
			::= { mbus31 19 }

mbus31VIF07		OBJECT-TYPE
			SYNTAX	INTEGER
			ACCESS	read-only
			STATUS	current
	DESCRIPTION ""
			::= { mbus31 20 }

mbus31Value07		OBJECT-TYPE
			SYNTAX	INTEGER
			ACCESS	read-only
			STATUS	current
	DESCRIPTION ""
			::= { mbus31 21 }

mbus31VIF08		OBJECT-TYPE
			SYNTAX	INTEGER
			ACCESS	read-only
			STATUS	current
	DESCRIPTION ""
			::= { mbus31 22 }

mbus31Value08		OBJECT-TYPE
			SYNTAX	INTEGER
			ACCESS	read-only
			STATUS	current
	DESCRIPTION ""
			::= { mbus31 23 }

mbus31VIF09		OBJECT-TYPE
			SYNTAX	INTEGER
			ACCESS	read-only
			STATUS	current
	DESCRIPTION ""
			::= { mbus31 24 }

mbus31Value09		OBJECT-TYPE
			SYNTAX	INTEGER
			ACCESS	read-only
			STATUS	current
	DESCRIPTION ""
			::= { mbus31 25 }

mbus31VIF0A		OBJECT-TYPE
			SYNTAX	INTEGER
			ACCESS	read-only
			STATUS	current
	DESCRIPTION ""
			::= { mbus31 26 }

mbus31Value0A		OBJECT-TYPE
			SYNTAX	INTEGER
			ACCESS	read-only
			STATUS	current
	DESCRIPTION ""
			::= { mbus31 27 }

mbus31VIF0B		OBJECT-TYPE
			SYNTAX	INTEGER
			ACCESS	read-only
			STATUS	current
	DESCRIPTION ""
			::= { mbus31 28 }

mbus31Value0B		OBJECT-TYPE
			SYNTAX	INTEGER
			ACCESS	read-only
			STATUS	current
	DESCRIPTION ""
			::= { mbus31 29 }

mbus31VIF0C		OBJECT-TYPE
			SYNTAX	INTEGER
			ACCESS	read-only
			STATUS	current
	DESCRIPTION ""
			::= { mbus31 30 }

mbus31Value0C		OBJECT-TYPE
			SYNTAX	INTEGER
			ACCESS	read-only
			STATUS	current
	DESCRIPTION ""
			::= { mbus31 31 }

mbus31VIF0D		OBJECT-TYPE
			SYNTAX	INTEGER
			ACCESS	read-only
			STATUS	current
	DESCRIPTION ""
			::= { mbus31 32 }

mbus31Value0D		OBJECT-TYPE
			SYNTAX	INTEGER
			ACCESS	read-only
			STATUS	current
	DESCRIPTION ""
			::= { mbus31 33 }

mbus31VIF0E		OBJECT-TYPE
			SYNTAX	INTEGER
			ACCESS	read-only
			STATUS	current
	DESCRIPTION ""
			::= { mbus31 34 }

mbus31Value0E		OBJECT-TYPE
			SYNTAX	INTEGER
			ACCESS	read-only
			STATUS	current
	DESCRIPTION ""
			::= { mbus31 35 }

mbus31VIF0F		OBJECT-TYPE
			SYNTAX	INTEGER
			ACCESS	read-only
			STATUS	current
	DESCRIPTION ""
			::= { mbus31 36 }

mbus31Value0F		OBJECT-TYPE
			SYNTAX	INTEGER
			ACCESS	read-only
			STATUS	current
	DESCRIPTION ""
			::= { mbus31 37 }

mbus31VIF10		OBJECT-TYPE
			SYNTAX	INTEGER
			ACCESS	read-only
			STATUS	current
	DESCRIPTION ""
			::= { mbus31 38 }

mbus31Value10		OBJECT-TYPE
			SYNTAX	INTEGER
			ACCESS	read-only
			STATUS	current
	DESCRIPTION ""
			::= { mbus31 39 }

mbus31VIF11		OBJECT-TYPE
			SYNTAX	INTEGER
			ACCESS	read-only
			STATUS	current
	DESCRIPTION ""
			::= { mbus31 40 }

mbus31Value11		OBJECT-TYPE
			SYNTAX	INTEGER
			ACCESS	read-only
			STATUS	current
	DESCRIPTION ""
			::= { mbus31 41 }

mbus31VIF12		OBJECT-TYPE
			SYNTAX	INTEGER
			ACCESS	read-only
			STATUS	current
	DESCRIPTION ""
			::= { mbus31 42 }

mbus31Value12		OBJECT-TYPE
			SYNTAX	INTEGER
			ACCESS	read-only
			STATUS	current
	DESCRIPTION ""
			::= { mbus31 43 }

mbus31VIF13		OBJECT-TYPE
			SYNTAX	INTEGER
			ACCESS	read-only
			STATUS	current
	DESCRIPTION ""
			::= { mbus31 44 }

mbus31Value13		OBJECT-TYPE
			SYNTAX	INTEGER
			ACCESS	read-only
			STATUS	current
	DESCRIPTION ""
			::= { mbus31 45 }

mbus31VIF14		OBJECT-TYPE
			SYNTAX	INTEGER
			ACCESS	read-only
			STATUS	current
	DESCRIPTION ""
			::= { mbus31 46 }

mbus31Value14		OBJECT-TYPE
			SYNTAX	INTEGER
			ACCESS	read-only
			STATUS	current
	DESCRIPTION ""
			::= { mbus31 47 }

mbus31VIF15		OBJECT-TYPE
			SYNTAX	INTEGER
			ACCESS	read-only
			STATUS	current
	DESCRIPTION ""
			::= { mbus31 48 }

mbus31Value15		OBJECT-TYPE
			SYNTAX	INTEGER
			ACCESS	read-only
			STATUS	current
	DESCRIPTION ""
			::= { mbus31 49 }

mbus31VIF16		OBJECT-TYPE
			SYNTAX	INTEGER
			ACCESS	read-only
			STATUS	current
	DESCRIPTION ""
			::= { mbus31 50 }

mbus31Value16		OBJECT-TYPE
			SYNTAX	INTEGER
			ACCESS	read-only
			STATUS	current
	DESCRIPTION ""
			::= { mbus31 51 }

mbus31VIF17		OBJECT-TYPE
			SYNTAX	INTEGER
			ACCESS	read-only
			STATUS	current
	DESCRIPTION ""
			::= { mbus31 52 }

mbus31Value17		OBJECT-TYPE
			SYNTAX	INTEGER
			ACCESS	read-only
			STATUS	current
	DESCRIPTION ""
			::= { mbus31 53 }

mbus31VIF18		OBJECT-TYPE
			SYNTAX	INTEGER
			ACCESS	read-only
			STATUS	current
	DESCRIPTION ""
			::= { mbus31 54 }

mbus31Value18		OBJECT-TYPE
			SYNTAX	INTEGER
			ACCESS	read-only
			STATUS	current
	DESCRIPTION ""
			::= { mbus31 55 }

mbus31VIF19		OBJECT-TYPE
			SYNTAX	INTEGER
			ACCESS	read-only
			STATUS	current
	DESCRIPTION ""
			::= { mbus31 56 }

mbus31Value19		OBJECT-TYPE
			SYNTAX	INTEGER
			ACCESS	read-only
			STATUS	current
	DESCRIPTION ""
			::= { mbus31 57 }

mbus31VIF1A		OBJECT-TYPE
			SYNTAX	INTEGER
			ACCESS	read-only
			STATUS	current
	DESCRIPTION ""
			::= { mbus31 58 }

mbus31Value1A		OBJECT-TYPE
			SYNTAX	INTEGER
			ACCESS	read-only
			STATUS	current
	DESCRIPTION ""
			::= { mbus31 59 }

mbus31VIF1B		OBJECT-TYPE
			SYNTAX	INTEGER
			ACCESS	read-only
			STATUS	current
	DESCRIPTION ""
			::= { mbus31 60 }

mbus31Value1B		OBJECT-TYPE
			SYNTAX	INTEGER
			ACCESS	read-only
			STATUS	current
	DESCRIPTION ""
			::= { mbus31 61 }

mbus31VIF1C		OBJECT-TYPE
			SYNTAX	INTEGER
			ACCESS	read-only
			STATUS	current
	DESCRIPTION ""
			::= { mbus31 62 }

mbus31Value1C		OBJECT-TYPE
			SYNTAX	INTEGER
			ACCESS	read-only
			STATUS	current
	DESCRIPTION ""
			::= { mbus31 63 }

mbus31VIF1D		OBJECT-TYPE
			SYNTAX	INTEGER
			ACCESS	read-only
			STATUS	current
	DESCRIPTION ""
			::= { mbus31 64 }

mbus31Value1D		OBJECT-TYPE
			SYNTAX	INTEGER
			ACCESS	read-only
			STATUS	current
	DESCRIPTION ""
			::= { mbus31 65 }

mbus31VIF1E		OBJECT-TYPE
			SYNTAX	INTEGER
			ACCESS	read-only
			STATUS	current
	DESCRIPTION ""
			::= { mbus31 66 }

mbus31Value1E		OBJECT-TYPE
			SYNTAX	INTEGER
			ACCESS	read-only
			STATUS	current
	DESCRIPTION ""
			::= { mbus31 67 }

mbus31VIF1F		OBJECT-TYPE
			SYNTAX	INTEGER
			ACCESS	read-only
			STATUS	current
	DESCRIPTION ""
			::= { mbus31 68 }

mbus31Value1F		OBJECT-TYPE
			SYNTAX	INTEGER
			ACCESS	read-only
			STATUS	current
	DESCRIPTION ""
			::= { mbus31 69 }

mbus31VIF20		OBJECT-TYPE
			SYNTAX	INTEGER
			ACCESS	read-only
			STATUS	current
	DESCRIPTION ""
			::= { mbus31 70 }

mbus31Value20		OBJECT-TYPE
			SYNTAX	INTEGER
			ACCESS	read-only
			STATUS	current
	DESCRIPTION ""
			::= { mbus31 71 }

mbus31VIF21		OBJECT-TYPE
			SYNTAX	INTEGER
			ACCESS	read-only
			STATUS	current
	DESCRIPTION ""
			::= { mbus31 72 }

mbus31Value21		OBJECT-TYPE
			SYNTAX	INTEGER
			ACCESS	read-only
			STATUS	current
	DESCRIPTION ""
			::= { mbus31 73 }

mbus31VIF22		OBJECT-TYPE
			SYNTAX	INTEGER
			ACCESS	read-only
			STATUS	current
	DESCRIPTION ""
			::= { mbus31 74 }

mbus31Value22		OBJECT-TYPE
			SYNTAX	INTEGER
			ACCESS	read-only
			STATUS	current
	DESCRIPTION ""
			::= { mbus31 75 }

mbus31VIF23		OBJECT-TYPE
			SYNTAX	INTEGER
			ACCESS	read-only
			STATUS	current
	DESCRIPTION ""
			::= { mbus31 76 }

mbus31Value23		OBJECT-TYPE
			SYNTAX	INTEGER
			ACCESS	read-only
			STATUS	current
	DESCRIPTION ""
			::= { mbus31 77 }

mbus31VIF24		OBJECT-TYPE
			SYNTAX	INTEGER
			ACCESS	read-only
			STATUS	current
	DESCRIPTION ""
			::= { mbus31 78 }

mbus31Value24		OBJECT-TYPE
			SYNTAX	INTEGER
			ACCESS	read-only
			STATUS	current
	DESCRIPTION ""
			::= { mbus31 79 }

mbus31VIF25		OBJECT-TYPE
			SYNTAX	INTEGER
			ACCESS	read-only
			STATUS	current
	DESCRIPTION ""
			::= { mbus31 80 }

mbus31Value25		OBJECT-TYPE
			SYNTAX	INTEGER
			ACCESS	read-only
			STATUS	current
	DESCRIPTION ""
			::= { mbus31 81 }

mbus31VIF26		OBJECT-TYPE
			SYNTAX	INTEGER
			ACCESS	read-only
			STATUS	current
	DESCRIPTION ""
			::= { mbus31 82 }

mbus31Value26		OBJECT-TYPE
			SYNTAX	INTEGER
			ACCESS	read-only
			STATUS	current
	DESCRIPTION ""
			::= { mbus31 83 }

mbus31VIF27		OBJECT-TYPE
			SYNTAX	INTEGER
			ACCESS	read-only
			STATUS	current
	DESCRIPTION ""
			::= { mbus31 84 }

mbus31Value27		OBJECT-TYPE
			SYNTAX	INTEGER
			ACCESS	read-only
			STATUS	current
	DESCRIPTION ""
			::= { mbus31 85 }

mbus31VIF28		OBJECT-TYPE
			SYNTAX	INTEGER
			ACCESS	read-only
			STATUS	current
	DESCRIPTION ""
			::= { mbus31 86 }

mbus31Value28		OBJECT-TYPE
			SYNTAX	INTEGER
			ACCESS	read-only
			STATUS	current
	DESCRIPTION ""
			::= { mbus31 87 }

mbus31VIF29		OBJECT-TYPE
			SYNTAX	INTEGER
			ACCESS	read-only
			STATUS	current
	DESCRIPTION ""
			::= { mbus31 88 }

mbus31Value29		OBJECT-TYPE
			SYNTAX	INTEGER
			ACCESS	read-only
			STATUS	current
	DESCRIPTION ""
			::= { mbus31 89 }

mbus31VIF2A		OBJECT-TYPE
			SYNTAX	INTEGER
			ACCESS	read-only
			STATUS	current
	DESCRIPTION ""
			::= { mbus31 90 }

mbus31Value2A		OBJECT-TYPE
			SYNTAX	INTEGER
			ACCESS	read-only
			STATUS	current
	DESCRIPTION ""
			::= { mbus31 91 }

mbus31VIF2B		OBJECT-TYPE
			SYNTAX	INTEGER
			ACCESS	read-only
			STATUS	current
	DESCRIPTION ""
			::= { mbus31 92 }

mbus31Value2B		OBJECT-TYPE
			SYNTAX	INTEGER
			ACCESS	read-only
			STATUS	current
	DESCRIPTION ""
			::= { mbus31 93 }

mbus31VIF2C		OBJECT-TYPE
			SYNTAX	INTEGER
			ACCESS	read-only
			STATUS	current
	DESCRIPTION ""
			::= { mbus31 94 }

mbus31Value2C		OBJECT-TYPE
			SYNTAX	INTEGER
			ACCESS	read-only
			STATUS	current
	DESCRIPTION ""
			::= { mbus31 95 }

mbus31VIF2D		OBJECT-TYPE
			SYNTAX	INTEGER
			ACCESS	read-only
			STATUS	current
	DESCRIPTION ""
			::= { mbus31 96 }

mbus31Value2D		OBJECT-TYPE
			SYNTAX	INTEGER
			ACCESS	read-only
			STATUS	current
	DESCRIPTION ""
			::= { mbus31 97 }

mbus31VIF2E		OBJECT-TYPE
			SYNTAX	INTEGER
			ACCESS	read-only
			STATUS	current
	DESCRIPTION ""
			::= { mbus31 98 }

mbus31Value2E		OBJECT-TYPE
			SYNTAX	INTEGER
			ACCESS	read-only
			STATUS	current
	DESCRIPTION ""
			::= { mbus31 99 }

mbus31VIF2F		OBJECT-TYPE
			SYNTAX	INTEGER
			ACCESS	read-only
			STATUS	current
	DESCRIPTION ""
			::= { mbus31 100 }

mbus31Value2F		OBJECT-TYPE
			SYNTAX	INTEGER
			ACCESS	read-only
			STATUS	current
	DESCRIPTION ""
			::= { mbus31 101 }

mbus32			OBJECT IDENTIFIER ::= { mbus 50 }

mbus32IdNumber		OBJECT-TYPE
			SYNTAX	Gauge
			ACCESS	read-only
			STATUS	current
	DESCRIPTION ""
			::= { mbus32 1 }

mbus32Manufacturer	OBJECT-TYPE
			SYNTAX	Gauge
			ACCESS	read-only
			STATUS	current
	DESCRIPTION ""
			::= { mbus32 2 }

mbus32Version		OBJECT-TYPE
			SYNTAX	Gauge
			ACCESS	read-only
			STATUS	current
	DESCRIPTION ""
			::= { mbus32 3 }

mbus32Medium		OBJECT-TYPE
			SYNTAX	Gauge
			ACCESS	read-only
			STATUS	current
	DESCRIPTION ""
			::= { mbus32 4 }

mbus32Status		OBJECT-TYPE
			SYNTAX	Gauge
			ACCESS	read-only
			STATUS	current
	DESCRIPTION ""
			::= { mbus32 5 }

mbus32VIF00		OBJECT-TYPE
			SYNTAX	INTEGER
			ACCESS	read-only
			STATUS	current
	DESCRIPTION ""
			::= { mbus32 6 }

mbus32Value00		OBJECT-TYPE
			SYNTAX	INTEGER
			ACCESS	read-only
			STATUS	current
	DESCRIPTION ""
			::= { mbus32 7 }

mbus32VIF01		OBJECT-TYPE
			SYNTAX	INTEGER
			ACCESS	read-only
			STATUS	current
	DESCRIPTION ""
			::= { mbus32 8 }

mbus32Value01		OBJECT-TYPE
			SYNTAX	INTEGER
			ACCESS	read-only
			STATUS	current
	DESCRIPTION ""
			::= { mbus32 9 }

mbus32VIF02		OBJECT-TYPE
			SYNTAX	INTEGER
			ACCESS	read-only
			STATUS	current
	DESCRIPTION ""
			::= { mbus32 10 }

mbus32Value02		OBJECT-TYPE
			SYNTAX	INTEGER
			ACCESS	read-only
			STATUS	current
	DESCRIPTION ""
			::= { mbus32 11 }

mbus32VIF03		OBJECT-TYPE
			SYNTAX	INTEGER
			ACCESS	read-only
			STATUS	current
	DESCRIPTION ""
			::= { mbus32 12 }

mbus32Value03		OBJECT-TYPE
			SYNTAX	INTEGER
			ACCESS	read-only
			STATUS	current
	DESCRIPTION ""
			::= { mbus32 13 }

mbus32VIF04		OBJECT-TYPE
			SYNTAX	INTEGER
			ACCESS	read-only
			STATUS	current
	DESCRIPTION ""
			::= { mbus32 14 }

mbus32Value04		OBJECT-TYPE
			SYNTAX	INTEGER
			ACCESS	read-only
			STATUS	current
	DESCRIPTION ""
			::= { mbus32 15 }

mbus32VIF05		OBJECT-TYPE
			SYNTAX	INTEGER
			ACCESS	read-only
			STATUS	current
	DESCRIPTION ""
			::= { mbus32 16 }

mbus32Value05		OBJECT-TYPE
			SYNTAX	INTEGER
			ACCESS	read-only
			STATUS	current
	DESCRIPTION ""
			::= { mbus32 17 }

mbus32VIF06		OBJECT-TYPE
			SYNTAX	INTEGER
			ACCESS	read-only
			STATUS	current
	DESCRIPTION ""
			::= { mbus32 18 }

mbus32Value06		OBJECT-TYPE
			SYNTAX	INTEGER
			ACCESS	read-only
			STATUS	current
	DESCRIPTION ""
			::= { mbus32 19 }

mbus32VIF07		OBJECT-TYPE
			SYNTAX	INTEGER
			ACCESS	read-only
			STATUS	current
	DESCRIPTION ""
			::= { mbus32 20 }

mbus32Value07		OBJECT-TYPE
			SYNTAX	INTEGER
			ACCESS	read-only
			STATUS	current
	DESCRIPTION ""
			::= { mbus32 21 }

mbus32VIF08		OBJECT-TYPE
			SYNTAX	INTEGER
			ACCESS	read-only
			STATUS	current
	DESCRIPTION ""
			::= { mbus32 22 }

mbus32Value08		OBJECT-TYPE
			SYNTAX	INTEGER
			ACCESS	read-only
			STATUS	current
	DESCRIPTION ""
			::= { mbus32 23 }

mbus32VIF09		OBJECT-TYPE
			SYNTAX	INTEGER
			ACCESS	read-only
			STATUS	current
	DESCRIPTION ""
			::= { mbus32 24 }

mbus32Value09		OBJECT-TYPE
			SYNTAX	INTEGER
			ACCESS	read-only
			STATUS	current
	DESCRIPTION ""
			::= { mbus32 25 }

mbus32VIF0A		OBJECT-TYPE
			SYNTAX	INTEGER
			ACCESS	read-only
			STATUS	current
	DESCRIPTION ""
			::= { mbus32 26 }

mbus32Value0A		OBJECT-TYPE
			SYNTAX	INTEGER
			ACCESS	read-only
			STATUS	current
	DESCRIPTION ""
			::= { mbus32 27 }

mbus32VIF0B		OBJECT-TYPE
			SYNTAX	INTEGER
			ACCESS	read-only
			STATUS	current
	DESCRIPTION ""
			::= { mbus32 28 }

mbus32Value0B		OBJECT-TYPE
			SYNTAX	INTEGER
			ACCESS	read-only
			STATUS	current
	DESCRIPTION ""
			::= { mbus32 29 }

mbus32VIF0C		OBJECT-TYPE
			SYNTAX	INTEGER
			ACCESS	read-only
			STATUS	current
	DESCRIPTION ""
			::= { mbus32 30 }

mbus32Value0C		OBJECT-TYPE
			SYNTAX	INTEGER
			ACCESS	read-only
			STATUS	current
	DESCRIPTION ""
			::= { mbus32 31 }

mbus32VIF0D		OBJECT-TYPE
			SYNTAX	INTEGER
			ACCESS	read-only
			STATUS	current
	DESCRIPTION ""
			::= { mbus32 32 }

mbus32Value0D		OBJECT-TYPE
			SYNTAX	INTEGER
			ACCESS	read-only
			STATUS	current
	DESCRIPTION ""
			::= { mbus32 33 }

mbus32VIF0E		OBJECT-TYPE
			SYNTAX	INTEGER
			ACCESS	read-only
			STATUS	current
	DESCRIPTION ""
			::= { mbus32 34 }

mbus32Value0E		OBJECT-TYPE
			SYNTAX	INTEGER
			ACCESS	read-only
			STATUS	current
	DESCRIPTION ""
			::= { mbus32 35 }

mbus32VIF0F		OBJECT-TYPE
			SYNTAX	INTEGER
			ACCESS	read-only
			STATUS	current
	DESCRIPTION ""
			::= { mbus32 36 }

mbus32Value0F		OBJECT-TYPE
			SYNTAX	INTEGER
			ACCESS	read-only
			STATUS	current
	DESCRIPTION ""
			::= { mbus32 37 }

mbus32VIF10		OBJECT-TYPE
			SYNTAX	INTEGER
			ACCESS	read-only
			STATUS	current
	DESCRIPTION ""
			::= { mbus32 38 }

mbus32Value10		OBJECT-TYPE
			SYNTAX	INTEGER
			ACCESS	read-only
			STATUS	current
	DESCRIPTION ""
			::= { mbus32 39 }

mbus32VIF11		OBJECT-TYPE
			SYNTAX	INTEGER
			ACCESS	read-only
			STATUS	current
	DESCRIPTION ""
			::= { mbus32 40 }

mbus32Value11		OBJECT-TYPE
			SYNTAX	INTEGER
			ACCESS	read-only
			STATUS	current
	DESCRIPTION ""
			::= { mbus32 41 }

mbus32VIF12		OBJECT-TYPE
			SYNTAX	INTEGER
			ACCESS	read-only
			STATUS	current
	DESCRIPTION ""
			::= { mbus32 42 }

mbus32Value12		OBJECT-TYPE
			SYNTAX	INTEGER
			ACCESS	read-only
			STATUS	current
	DESCRIPTION ""
			::= { mbus32 43 }

mbus32VIF13		OBJECT-TYPE
			SYNTAX	INTEGER
			ACCESS	read-only
			STATUS	current
	DESCRIPTION ""
			::= { mbus32 44 }

mbus32Value13		OBJECT-TYPE
			SYNTAX	INTEGER
			ACCESS	read-only
			STATUS	current
	DESCRIPTION ""
			::= { mbus32 45 }

mbus32VIF14		OBJECT-TYPE
			SYNTAX	INTEGER
			ACCESS	read-only
			STATUS	current
	DESCRIPTION ""
			::= { mbus32 46 }

mbus32Value14		OBJECT-TYPE
			SYNTAX	INTEGER
			ACCESS	read-only
			STATUS	current
	DESCRIPTION ""
			::= { mbus32 47 }

mbus32VIF15		OBJECT-TYPE
			SYNTAX	INTEGER
			ACCESS	read-only
			STATUS	current
	DESCRIPTION ""
			::= { mbus32 48 }

mbus32Value15		OBJECT-TYPE
			SYNTAX	INTEGER
			ACCESS	read-only
			STATUS	current
	DESCRIPTION ""
			::= { mbus32 49 }

mbus32VIF16		OBJECT-TYPE
			SYNTAX	INTEGER
			ACCESS	read-only
			STATUS	current
	DESCRIPTION ""
			::= { mbus32 50 }

mbus32Value16		OBJECT-TYPE
			SYNTAX	INTEGER
			ACCESS	read-only
			STATUS	current
	DESCRIPTION ""
			::= { mbus32 51 }

mbus32VIF17		OBJECT-TYPE
			SYNTAX	INTEGER
			ACCESS	read-only
			STATUS	current
	DESCRIPTION ""
			::= { mbus32 52 }

mbus32Value17		OBJECT-TYPE
			SYNTAX	INTEGER
			ACCESS	read-only
			STATUS	current
	DESCRIPTION ""
			::= { mbus32 53 }

mbus32VIF18		OBJECT-TYPE
			SYNTAX	INTEGER
			ACCESS	read-only
			STATUS	current
	DESCRIPTION ""
			::= { mbus32 54 }

mbus32Value18		OBJECT-TYPE
			SYNTAX	INTEGER
			ACCESS	read-only
			STATUS	current
	DESCRIPTION ""
			::= { mbus32 55 }

mbus32VIF19		OBJECT-TYPE
			SYNTAX	INTEGER
			ACCESS	read-only
			STATUS	current
	DESCRIPTION ""
			::= { mbus32 56 }

mbus32Value19		OBJECT-TYPE
			SYNTAX	INTEGER
			ACCESS	read-only
			STATUS	current
	DESCRIPTION ""
			::= { mbus32 57 }

mbus32VIF1A		OBJECT-TYPE
			SYNTAX	INTEGER
			ACCESS	read-only
			STATUS	current
	DESCRIPTION ""
			::= { mbus32 58 }

mbus32Value1A		OBJECT-TYPE
			SYNTAX	INTEGER
			ACCESS	read-only
			STATUS	current
	DESCRIPTION ""
			::= { mbus32 59 }

mbus32VIF1B		OBJECT-TYPE
			SYNTAX	INTEGER
			ACCESS	read-only
			STATUS	current
	DESCRIPTION ""
			::= { mbus32 60 }

mbus32Value1B		OBJECT-TYPE
			SYNTAX	INTEGER
			ACCESS	read-only
			STATUS	current
	DESCRIPTION ""
			::= { mbus32 61 }

mbus32VIF1C		OBJECT-TYPE
			SYNTAX	INTEGER
			ACCESS	read-only
			STATUS	current
	DESCRIPTION ""
			::= { mbus32 62 }

mbus32Value1C		OBJECT-TYPE
			SYNTAX	INTEGER
			ACCESS	read-only
			STATUS	current
	DESCRIPTION ""
			::= { mbus32 63 }

mbus32VIF1D		OBJECT-TYPE
			SYNTAX	INTEGER
			ACCESS	read-only
			STATUS	current
	DESCRIPTION ""
			::= { mbus32 64 }

mbus32Value1D		OBJECT-TYPE
			SYNTAX	INTEGER
			ACCESS	read-only
			STATUS	current
	DESCRIPTION ""
			::= { mbus32 65 }

mbus32VIF1E		OBJECT-TYPE
			SYNTAX	INTEGER
			ACCESS	read-only
			STATUS	current
	DESCRIPTION ""
			::= { mbus32 66 }

mbus32Value1E		OBJECT-TYPE
			SYNTAX	INTEGER
			ACCESS	read-only
			STATUS	current
	DESCRIPTION ""
			::= { mbus32 67 }

mbus32VIF1F		OBJECT-TYPE
			SYNTAX	INTEGER
			ACCESS	read-only
			STATUS	current
	DESCRIPTION ""
			::= { mbus32 68 }

mbus32Value1F		OBJECT-TYPE
			SYNTAX	INTEGER
			ACCESS	read-only
			STATUS	current
	DESCRIPTION ""
			::= { mbus32 69 }

mbus32VIF20		OBJECT-TYPE
			SYNTAX	INTEGER
			ACCESS	read-only
			STATUS	current
	DESCRIPTION ""
			::= { mbus32 70 }

mbus32Value20		OBJECT-TYPE
			SYNTAX	INTEGER
			ACCESS	read-only
			STATUS	current
	DESCRIPTION ""
			::= { mbus32 71 }

mbus32VIF21		OBJECT-TYPE
			SYNTAX	INTEGER
			ACCESS	read-only
			STATUS	current
	DESCRIPTION ""
			::= { mbus32 72 }

mbus32Value21		OBJECT-TYPE
			SYNTAX	INTEGER
			ACCESS	read-only
			STATUS	current
	DESCRIPTION ""
			::= { mbus32 73 }

mbus32VIF22		OBJECT-TYPE
			SYNTAX	INTEGER
			ACCESS	read-only
			STATUS	current
	DESCRIPTION ""
			::= { mbus32 74 }

mbus32Value22		OBJECT-TYPE
			SYNTAX	INTEGER
			ACCESS	read-only
			STATUS	current
	DESCRIPTION ""
			::= { mbus32 75 }

mbus32VIF23		OBJECT-TYPE
			SYNTAX	INTEGER
			ACCESS	read-only
			STATUS	current
	DESCRIPTION ""
			::= { mbus32 76 }

mbus32Value23		OBJECT-TYPE
			SYNTAX	INTEGER
			ACCESS	read-only
			STATUS	current
	DESCRIPTION ""
			::= { mbus32 77 }

mbus32VIF24		OBJECT-TYPE
			SYNTAX	INTEGER
			ACCESS	read-only
			STATUS	current
	DESCRIPTION ""
			::= { mbus32 78 }

mbus32Value24		OBJECT-TYPE
			SYNTAX	INTEGER
			ACCESS	read-only
			STATUS	current
	DESCRIPTION ""
			::= { mbus32 79 }

mbus32VIF25		OBJECT-TYPE
			SYNTAX	INTEGER
			ACCESS	read-only
			STATUS	current
	DESCRIPTION ""
			::= { mbus32 80 }

mbus32Value25		OBJECT-TYPE
			SYNTAX	INTEGER
			ACCESS	read-only
			STATUS	current
	DESCRIPTION ""
			::= { mbus32 81 }

mbus32VIF26		OBJECT-TYPE
			SYNTAX	INTEGER
			ACCESS	read-only
			STATUS	current
	DESCRIPTION ""
			::= { mbus32 82 }

mbus32Value26		OBJECT-TYPE
			SYNTAX	INTEGER
			ACCESS	read-only
			STATUS	current
	DESCRIPTION ""
			::= { mbus32 83 }

mbus32VIF27		OBJECT-TYPE
			SYNTAX	INTEGER
			ACCESS	read-only
			STATUS	current
	DESCRIPTION ""
			::= { mbus32 84 }

mbus32Value27		OBJECT-TYPE
			SYNTAX	INTEGER
			ACCESS	read-only
			STATUS	current
	DESCRIPTION ""
			::= { mbus32 85 }

mbus32VIF28		OBJECT-TYPE
			SYNTAX	INTEGER
			ACCESS	read-only
			STATUS	current
	DESCRIPTION ""
			::= { mbus32 86 }

mbus32Value28		OBJECT-TYPE
			SYNTAX	INTEGER
			ACCESS	read-only
			STATUS	current
	DESCRIPTION ""
			::= { mbus32 87 }

mbus32VIF29		OBJECT-TYPE
			SYNTAX	INTEGER
			ACCESS	read-only
			STATUS	current
	DESCRIPTION ""
			::= { mbus32 88 }

mbus32Value29		OBJECT-TYPE
			SYNTAX	INTEGER
			ACCESS	read-only
			STATUS	current
	DESCRIPTION ""
			::= { mbus32 89 }

mbus32VIF2A		OBJECT-TYPE
			SYNTAX	INTEGER
			ACCESS	read-only
			STATUS	current
	DESCRIPTION ""
			::= { mbus32 90 }

mbus32Value2A		OBJECT-TYPE
			SYNTAX	INTEGER
			ACCESS	read-only
			STATUS	current
	DESCRIPTION ""
			::= { mbus32 91 }

mbus32VIF2B		OBJECT-TYPE
			SYNTAX	INTEGER
			ACCESS	read-only
			STATUS	current
	DESCRIPTION ""
			::= { mbus32 92 }

mbus32Value2B		OBJECT-TYPE
			SYNTAX	INTEGER
			ACCESS	read-only
			STATUS	current
	DESCRIPTION ""
			::= { mbus32 93 }

mbus32VIF2C		OBJECT-TYPE
			SYNTAX	INTEGER
			ACCESS	read-only
			STATUS	current
	DESCRIPTION ""
			::= { mbus32 94 }

mbus32Value2C		OBJECT-TYPE
			SYNTAX	INTEGER
			ACCESS	read-only
			STATUS	current
	DESCRIPTION ""
			::= { mbus32 95 }

mbus32VIF2D		OBJECT-TYPE
			SYNTAX	INTEGER
			ACCESS	read-only
			STATUS	current
	DESCRIPTION ""
			::= { mbus32 96 }

mbus32Value2D		OBJECT-TYPE
			SYNTAX	INTEGER
			ACCESS	read-only
			STATUS	current
	DESCRIPTION ""
			::= { mbus32 97 }

mbus32VIF2E		OBJECT-TYPE
			SYNTAX	INTEGER
			ACCESS	read-only
			STATUS	current
	DESCRIPTION ""
			::= { mbus32 98 }

mbus32Value2E		OBJECT-TYPE
			SYNTAX	INTEGER
			ACCESS	read-only
			STATUS	current
	DESCRIPTION ""
			::= { mbus32 99 }

mbus32VIF2F		OBJECT-TYPE
			SYNTAX	INTEGER
			ACCESS	read-only
			STATUS	current
	DESCRIPTION ""
			::= { mbus32 100 }

mbus32Value2F		OBJECT-TYPE
			SYNTAX	INTEGER
			ACCESS	read-only
			STATUS	current
	DESCRIPTION ""
			::= { mbus32 101 }

mbus33			OBJECT IDENTIFIER ::= { mbus 51 }

mbus33IdNumber		OBJECT-TYPE
			SYNTAX	Gauge
			ACCESS	read-only
			STATUS	current
	DESCRIPTION ""
			::= { mbus33 1 }

mbus33Manufacturer	OBJECT-TYPE
			SYNTAX	Gauge
			ACCESS	read-only
			STATUS	current
	DESCRIPTION ""
			::= { mbus33 2 }

mbus33Version		OBJECT-TYPE
			SYNTAX	Gauge
			ACCESS	read-only
			STATUS	current
	DESCRIPTION ""
			::= { mbus33 3 }

mbus33Medium		OBJECT-TYPE
			SYNTAX	Gauge
			ACCESS	read-only
			STATUS	current
	DESCRIPTION ""
			::= { mbus33 4 }

mbus33Status		OBJECT-TYPE
			SYNTAX	Gauge
			ACCESS	read-only
			STATUS	current
	DESCRIPTION ""
			::= { mbus33 5 }

mbus33VIF00		OBJECT-TYPE
			SYNTAX	INTEGER
			ACCESS	read-only
			STATUS	current
	DESCRIPTION ""
			::= { mbus33 6 }

mbus33Value00		OBJECT-TYPE
			SYNTAX	INTEGER
			ACCESS	read-only
			STATUS	current
	DESCRIPTION ""
			::= { mbus33 7 }

mbus33VIF01		OBJECT-TYPE
			SYNTAX	INTEGER
			ACCESS	read-only
			STATUS	current
	DESCRIPTION ""
			::= { mbus33 8 }

mbus33Value01		OBJECT-TYPE
			SYNTAX	INTEGER
			ACCESS	read-only
			STATUS	current
	DESCRIPTION ""
			::= { mbus33 9 }

mbus33VIF02		OBJECT-TYPE
			SYNTAX	INTEGER
			ACCESS	read-only
			STATUS	current
	DESCRIPTION ""
			::= { mbus33 10 }

mbus33Value02		OBJECT-TYPE
			SYNTAX	INTEGER
			ACCESS	read-only
			STATUS	current
	DESCRIPTION ""
			::= { mbus33 11 }

mbus33VIF03		OBJECT-TYPE
			SYNTAX	INTEGER
			ACCESS	read-only
			STATUS	current
	DESCRIPTION ""
			::= { mbus33 12 }

mbus33Value03		OBJECT-TYPE
			SYNTAX	INTEGER
			ACCESS	read-only
			STATUS	current
	DESCRIPTION ""
			::= { mbus33 13 }

mbus33VIF04		OBJECT-TYPE
			SYNTAX	INTEGER
			ACCESS	read-only
			STATUS	current
	DESCRIPTION ""
			::= { mbus33 14 }

mbus33Value04		OBJECT-TYPE
			SYNTAX	INTEGER
			ACCESS	read-only
			STATUS	current
	DESCRIPTION ""
			::= { mbus33 15 }

mbus33VIF05		OBJECT-TYPE
			SYNTAX	INTEGER
			ACCESS	read-only
			STATUS	current
	DESCRIPTION ""
			::= { mbus33 16 }

mbus33Value05		OBJECT-TYPE
			SYNTAX	INTEGER
			ACCESS	read-only
			STATUS	current
	DESCRIPTION ""
			::= { mbus33 17 }

mbus33VIF06		OBJECT-TYPE
			SYNTAX	INTEGER
			ACCESS	read-only
			STATUS	current
	DESCRIPTION ""
			::= { mbus33 18 }

mbus33Value06		OBJECT-TYPE
			SYNTAX	INTEGER
			ACCESS	read-only
			STATUS	current
	DESCRIPTION ""
			::= { mbus33 19 }

mbus33VIF07		OBJECT-TYPE
			SYNTAX	INTEGER
			ACCESS	read-only
			STATUS	current
	DESCRIPTION ""
			::= { mbus33 20 }

mbus33Value07		OBJECT-TYPE
			SYNTAX	INTEGER
			ACCESS	read-only
			STATUS	current
	DESCRIPTION ""
			::= { mbus33 21 }

mbus33VIF08		OBJECT-TYPE
			SYNTAX	INTEGER
			ACCESS	read-only
			STATUS	current
	DESCRIPTION ""
			::= { mbus33 22 }

mbus33Value08		OBJECT-TYPE
			SYNTAX	INTEGER
			ACCESS	read-only
			STATUS	current
	DESCRIPTION ""
			::= { mbus33 23 }

mbus33VIF09		OBJECT-TYPE
			SYNTAX	INTEGER
			ACCESS	read-only
			STATUS	current
	DESCRIPTION ""
			::= { mbus33 24 }

mbus33Value09		OBJECT-TYPE
			SYNTAX	INTEGER
			ACCESS	read-only
			STATUS	current
	DESCRIPTION ""
			::= { mbus33 25 }

mbus33VIF0A		OBJECT-TYPE
			SYNTAX	INTEGER
			ACCESS	read-only
			STATUS	current
	DESCRIPTION ""
			::= { mbus33 26 }

mbus33Value0A		OBJECT-TYPE
			SYNTAX	INTEGER
			ACCESS	read-only
			STATUS	current
	DESCRIPTION ""
			::= { mbus33 27 }

mbus33VIF0B		OBJECT-TYPE
			SYNTAX	INTEGER
			ACCESS	read-only
			STATUS	current
	DESCRIPTION ""
			::= { mbus33 28 }

mbus33Value0B		OBJECT-TYPE
			SYNTAX	INTEGER
			ACCESS	read-only
			STATUS	current
	DESCRIPTION ""
			::= { mbus33 29 }

mbus33VIF0C		OBJECT-TYPE
			SYNTAX	INTEGER
			ACCESS	read-only
			STATUS	current
	DESCRIPTION ""
			::= { mbus33 30 }

mbus33Value0C		OBJECT-TYPE
			SYNTAX	INTEGER
			ACCESS	read-only
			STATUS	current
	DESCRIPTION ""
			::= { mbus33 31 }

mbus33VIF0D		OBJECT-TYPE
			SYNTAX	INTEGER
			ACCESS	read-only
			STATUS	current
	DESCRIPTION ""
			::= { mbus33 32 }

mbus33Value0D		OBJECT-TYPE
			SYNTAX	INTEGER
			ACCESS	read-only
			STATUS	current
	DESCRIPTION ""
			::= { mbus33 33 }

mbus33VIF0E		OBJECT-TYPE
			SYNTAX	INTEGER
			ACCESS	read-only
			STATUS	current
	DESCRIPTION ""
			::= { mbus33 34 }

mbus33Value0E		OBJECT-TYPE
			SYNTAX	INTEGER
			ACCESS	read-only
			STATUS	current
	DESCRIPTION ""
			::= { mbus33 35 }

mbus33VIF0F		OBJECT-TYPE
			SYNTAX	INTEGER
			ACCESS	read-only
			STATUS	current
	DESCRIPTION ""
			::= { mbus33 36 }

mbus33Value0F		OBJECT-TYPE
			SYNTAX	INTEGER
			ACCESS	read-only
			STATUS	current
	DESCRIPTION ""
			::= { mbus33 37 }

mbus33VIF10		OBJECT-TYPE
			SYNTAX	INTEGER
			ACCESS	read-only
			STATUS	current
	DESCRIPTION ""
			::= { mbus33 38 }

mbus33Value10		OBJECT-TYPE
			SYNTAX	INTEGER
			ACCESS	read-only
			STATUS	current
	DESCRIPTION ""
			::= { mbus33 39 }

mbus33VIF11		OBJECT-TYPE
			SYNTAX	INTEGER
			ACCESS	read-only
			STATUS	current
	DESCRIPTION ""
			::= { mbus33 40 }

mbus33Value11		OBJECT-TYPE
			SYNTAX	INTEGER
			ACCESS	read-only
			STATUS	current
	DESCRIPTION ""
			::= { mbus33 41 }

mbus33VIF12		OBJECT-TYPE
			SYNTAX	INTEGER
			ACCESS	read-only
			STATUS	current
	DESCRIPTION ""
			::= { mbus33 42 }

mbus33Value12		OBJECT-TYPE
			SYNTAX	INTEGER
			ACCESS	read-only
			STATUS	current
	DESCRIPTION ""
			::= { mbus33 43 }

mbus33VIF13		OBJECT-TYPE
			SYNTAX	INTEGER
			ACCESS	read-only
			STATUS	current
	DESCRIPTION ""
			::= { mbus33 44 }

mbus33Value13		OBJECT-TYPE
			SYNTAX	INTEGER
			ACCESS	read-only
			STATUS	current
	DESCRIPTION ""
			::= { mbus33 45 }

mbus33VIF14		OBJECT-TYPE
			SYNTAX	INTEGER
			ACCESS	read-only
			STATUS	current
	DESCRIPTION ""
			::= { mbus33 46 }

mbus33Value14		OBJECT-TYPE
			SYNTAX	INTEGER
			ACCESS	read-only
			STATUS	current
	DESCRIPTION ""
			::= { mbus33 47 }

mbus33VIF15		OBJECT-TYPE
			SYNTAX	INTEGER
			ACCESS	read-only
			STATUS	current
	DESCRIPTION ""
			::= { mbus33 48 }

mbus33Value15		OBJECT-TYPE
			SYNTAX	INTEGER
			ACCESS	read-only
			STATUS	current
	DESCRIPTION ""
			::= { mbus33 49 }

mbus33VIF16		OBJECT-TYPE
			SYNTAX	INTEGER
			ACCESS	read-only
			STATUS	current
	DESCRIPTION ""
			::= { mbus33 50 }

mbus33Value16		OBJECT-TYPE
			SYNTAX	INTEGER
			ACCESS	read-only
			STATUS	current
	DESCRIPTION ""
			::= { mbus33 51 }

mbus33VIF17		OBJECT-TYPE
			SYNTAX	INTEGER
			ACCESS	read-only
			STATUS	current
	DESCRIPTION ""
			::= { mbus33 52 }

mbus33Value17		OBJECT-TYPE
			SYNTAX	INTEGER
			ACCESS	read-only
			STATUS	current
	DESCRIPTION ""
			::= { mbus33 53 }

mbus33VIF18		OBJECT-TYPE
			SYNTAX	INTEGER
			ACCESS	read-only
			STATUS	current
	DESCRIPTION ""
			::= { mbus33 54 }

mbus33Value18		OBJECT-TYPE
			SYNTAX	INTEGER
			ACCESS	read-only
			STATUS	current
	DESCRIPTION ""
			::= { mbus33 55 }

mbus33VIF19		OBJECT-TYPE
			SYNTAX	INTEGER
			ACCESS	read-only
			STATUS	current
	DESCRIPTION ""
			::= { mbus33 56 }

mbus33Value19		OBJECT-TYPE
			SYNTAX	INTEGER
			ACCESS	read-only
			STATUS	current
	DESCRIPTION ""
			::= { mbus33 57 }

mbus33VIF1A		OBJECT-TYPE
			SYNTAX	INTEGER
			ACCESS	read-only
			STATUS	current
	DESCRIPTION ""
			::= { mbus33 58 }

mbus33Value1A		OBJECT-TYPE
			SYNTAX	INTEGER
			ACCESS	read-only
			STATUS	current
	DESCRIPTION ""
			::= { mbus33 59 }

mbus33VIF1B		OBJECT-TYPE
			SYNTAX	INTEGER
			ACCESS	read-only
			STATUS	current
	DESCRIPTION ""
			::= { mbus33 60 }

mbus33Value1B		OBJECT-TYPE
			SYNTAX	INTEGER
			ACCESS	read-only
			STATUS	current
	DESCRIPTION ""
			::= { mbus33 61 }

mbus33VIF1C		OBJECT-TYPE
			SYNTAX	INTEGER
			ACCESS	read-only
			STATUS	current
	DESCRIPTION ""
			::= { mbus33 62 }

mbus33Value1C		OBJECT-TYPE
			SYNTAX	INTEGER
			ACCESS	read-only
			STATUS	current
	DESCRIPTION ""
			::= { mbus33 63 }

mbus33VIF1D		OBJECT-TYPE
			SYNTAX	INTEGER
			ACCESS	read-only
			STATUS	current
	DESCRIPTION ""
			::= { mbus33 64 }

mbus33Value1D		OBJECT-TYPE
			SYNTAX	INTEGER
			ACCESS	read-only
			STATUS	current
	DESCRIPTION ""
			::= { mbus33 65 }

mbus33VIF1E		OBJECT-TYPE
			SYNTAX	INTEGER
			ACCESS	read-only
			STATUS	current
	DESCRIPTION ""
			::= { mbus33 66 }

mbus33Value1E		OBJECT-TYPE
			SYNTAX	INTEGER
			ACCESS	read-only
			STATUS	current
	DESCRIPTION ""
			::= { mbus33 67 }

mbus33VIF1F		OBJECT-TYPE
			SYNTAX	INTEGER
			ACCESS	read-only
			STATUS	current
	DESCRIPTION ""
			::= { mbus33 68 }

mbus33Value1F		OBJECT-TYPE
			SYNTAX	INTEGER
			ACCESS	read-only
			STATUS	current
	DESCRIPTION ""
			::= { mbus33 69 }

mbus33VIF20		OBJECT-TYPE
			SYNTAX	INTEGER
			ACCESS	read-only
			STATUS	current
	DESCRIPTION ""
			::= { mbus33 70 }

mbus33Value20		OBJECT-TYPE
			SYNTAX	INTEGER
			ACCESS	read-only
			STATUS	current
	DESCRIPTION ""
			::= { mbus33 71 }

mbus33VIF21		OBJECT-TYPE
			SYNTAX	INTEGER
			ACCESS	read-only
			STATUS	current
	DESCRIPTION ""
			::= { mbus33 72 }

mbus33Value21		OBJECT-TYPE
			SYNTAX	INTEGER
			ACCESS	read-only
			STATUS	current
	DESCRIPTION ""
			::= { mbus33 73 }

mbus33VIF22		OBJECT-TYPE
			SYNTAX	INTEGER
			ACCESS	read-only
			STATUS	current
	DESCRIPTION ""
			::= { mbus33 74 }

mbus33Value22		OBJECT-TYPE
			SYNTAX	INTEGER
			ACCESS	read-only
			STATUS	current
	DESCRIPTION ""
			::= { mbus33 75 }

mbus33VIF23		OBJECT-TYPE
			SYNTAX	INTEGER
			ACCESS	read-only
			STATUS	current
	DESCRIPTION ""
			::= { mbus33 76 }

mbus33Value23		OBJECT-TYPE
			SYNTAX	INTEGER
			ACCESS	read-only
			STATUS	current
	DESCRIPTION ""
			::= { mbus33 77 }

mbus33VIF24		OBJECT-TYPE
			SYNTAX	INTEGER
			ACCESS	read-only
			STATUS	current
	DESCRIPTION ""
			::= { mbus33 78 }

mbus33Value24		OBJECT-TYPE
			SYNTAX	INTEGER
			ACCESS	read-only
			STATUS	current
	DESCRIPTION ""
			::= { mbus33 79 }

mbus33VIF25		OBJECT-TYPE
			SYNTAX	INTEGER
			ACCESS	read-only
			STATUS	current
	DESCRIPTION ""
			::= { mbus33 80 }

mbus33Value25		OBJECT-TYPE
			SYNTAX	INTEGER
			ACCESS	read-only
			STATUS	current
	DESCRIPTION ""
			::= { mbus33 81 }

mbus33VIF26		OBJECT-TYPE
			SYNTAX	INTEGER
			ACCESS	read-only
			STATUS	current
	DESCRIPTION ""
			::= { mbus33 82 }

mbus33Value26		OBJECT-TYPE
			SYNTAX	INTEGER
			ACCESS	read-only
			STATUS	current
	DESCRIPTION ""
			::= { mbus33 83 }

mbus33VIF27		OBJECT-TYPE
			SYNTAX	INTEGER
			ACCESS	read-only
			STATUS	current
	DESCRIPTION ""
			::= { mbus33 84 }

mbus33Value27		OBJECT-TYPE
			SYNTAX	INTEGER
			ACCESS	read-only
			STATUS	current
	DESCRIPTION ""
			::= { mbus33 85 }

mbus33VIF28		OBJECT-TYPE
			SYNTAX	INTEGER
			ACCESS	read-only
			STATUS	current
	DESCRIPTION ""
			::= { mbus33 86 }

mbus33Value28		OBJECT-TYPE
			SYNTAX	INTEGER
			ACCESS	read-only
			STATUS	current
	DESCRIPTION ""
			::= { mbus33 87 }

mbus33VIF29		OBJECT-TYPE
			SYNTAX	INTEGER
			ACCESS	read-only
			STATUS	current
	DESCRIPTION ""
			::= { mbus33 88 }

mbus33Value29		OBJECT-TYPE
			SYNTAX	INTEGER
			ACCESS	read-only
			STATUS	current
	DESCRIPTION ""
			::= { mbus33 89 }

mbus33VIF2A		OBJECT-TYPE
			SYNTAX	INTEGER
			ACCESS	read-only
			STATUS	current
	DESCRIPTION ""
			::= { mbus33 90 }

mbus33Value2A		OBJECT-TYPE
			SYNTAX	INTEGER
			ACCESS	read-only
			STATUS	current
	DESCRIPTION ""
			::= { mbus33 91 }

mbus33VIF2B		OBJECT-TYPE
			SYNTAX	INTEGER
			ACCESS	read-only
			STATUS	current
	DESCRIPTION ""
			::= { mbus33 92 }

mbus33Value2B		OBJECT-TYPE
			SYNTAX	INTEGER
			ACCESS	read-only
			STATUS	current
	DESCRIPTION ""
			::= { mbus33 93 }

mbus33VIF2C		OBJECT-TYPE
			SYNTAX	INTEGER
			ACCESS	read-only
			STATUS	current
	DESCRIPTION ""
			::= { mbus33 94 }

mbus33Value2C		OBJECT-TYPE
			SYNTAX	INTEGER
			ACCESS	read-only
			STATUS	current
	DESCRIPTION ""
			::= { mbus33 95 }

mbus33VIF2D		OBJECT-TYPE
			SYNTAX	INTEGER
			ACCESS	read-only
			STATUS	current
	DESCRIPTION ""
			::= { mbus33 96 }

mbus33Value2D		OBJECT-TYPE
			SYNTAX	INTEGER
			ACCESS	read-only
			STATUS	current
	DESCRIPTION ""
			::= { mbus33 97 }

mbus33VIF2E		OBJECT-TYPE
			SYNTAX	INTEGER
			ACCESS	read-only
			STATUS	current
	DESCRIPTION ""
			::= { mbus33 98 }

mbus33Value2E		OBJECT-TYPE
			SYNTAX	INTEGER
			ACCESS	read-only
			STATUS	current
	DESCRIPTION ""
			::= { mbus33 99 }

mbus33VIF2F		OBJECT-TYPE
			SYNTAX	INTEGER
			ACCESS	read-only
			STATUS	current
	DESCRIPTION ""
			::= { mbus33 100 }

mbus33Value2F		OBJECT-TYPE
			SYNTAX	INTEGER
			ACCESS	read-only
			STATUS	current
	DESCRIPTION ""
			::= { mbus33 101 }

mbus34			OBJECT IDENTIFIER ::= { mbus 52 }

mbus34IdNumber		OBJECT-TYPE
			SYNTAX	Gauge
			ACCESS	read-only
			STATUS	current
	DESCRIPTION ""
			::= { mbus34 1 }

mbus34Manufacturer	OBJECT-TYPE
			SYNTAX	Gauge
			ACCESS	read-only
			STATUS	current
	DESCRIPTION ""
			::= { mbus34 2 }

mbus34Version		OBJECT-TYPE
			SYNTAX	Gauge
			ACCESS	read-only
			STATUS	current
	DESCRIPTION ""
			::= { mbus34 3 }

mbus34Medium		OBJECT-TYPE
			SYNTAX	Gauge
			ACCESS	read-only
			STATUS	current
	DESCRIPTION ""
			::= { mbus34 4 }

mbus34Status		OBJECT-TYPE
			SYNTAX	Gauge
			ACCESS	read-only
			STATUS	current
	DESCRIPTION ""
			::= { mbus34 5 }

mbus34VIF00		OBJECT-TYPE
			SYNTAX	INTEGER
			ACCESS	read-only
			STATUS	current
	DESCRIPTION ""
			::= { mbus34 6 }

mbus34Value00		OBJECT-TYPE
			SYNTAX	INTEGER
			ACCESS	read-only
			STATUS	current
	DESCRIPTION ""
			::= { mbus34 7 }

mbus34VIF01		OBJECT-TYPE
			SYNTAX	INTEGER
			ACCESS	read-only
			STATUS	current
	DESCRIPTION ""
			::= { mbus34 8 }

mbus34Value01		OBJECT-TYPE
			SYNTAX	INTEGER
			ACCESS	read-only
			STATUS	current
	DESCRIPTION ""
			::= { mbus34 9 }

mbus34VIF02		OBJECT-TYPE
			SYNTAX	INTEGER
			ACCESS	read-only
			STATUS	current
	DESCRIPTION ""
			::= { mbus34 10 }

mbus34Value02		OBJECT-TYPE
			SYNTAX	INTEGER
			ACCESS	read-only
			STATUS	current
	DESCRIPTION ""
			::= { mbus34 11 }

mbus34VIF03		OBJECT-TYPE
			SYNTAX	INTEGER
			ACCESS	read-only
			STATUS	current
	DESCRIPTION ""
			::= { mbus34 12 }

mbus34Value03		OBJECT-TYPE
			SYNTAX	INTEGER
			ACCESS	read-only
			STATUS	current
	DESCRIPTION ""
			::= { mbus34 13 }

mbus34VIF04		OBJECT-TYPE
			SYNTAX	INTEGER
			ACCESS	read-only
			STATUS	current
	DESCRIPTION ""
			::= { mbus34 14 }

mbus34Value04		OBJECT-TYPE
			SYNTAX	INTEGER
			ACCESS	read-only
			STATUS	current
	DESCRIPTION ""
			::= { mbus34 15 }

mbus34VIF05		OBJECT-TYPE
			SYNTAX	INTEGER
			ACCESS	read-only
			STATUS	current
	DESCRIPTION ""
			::= { mbus34 16 }

mbus34Value05		OBJECT-TYPE
			SYNTAX	INTEGER
			ACCESS	read-only
			STATUS	current
	DESCRIPTION ""
			::= { mbus34 17 }

mbus34VIF06		OBJECT-TYPE
			SYNTAX	INTEGER
			ACCESS	read-only
			STATUS	current
	DESCRIPTION ""
			::= { mbus34 18 }

mbus34Value06		OBJECT-TYPE
			SYNTAX	INTEGER
			ACCESS	read-only
			STATUS	current
	DESCRIPTION ""
			::= { mbus34 19 }

mbus34VIF07		OBJECT-TYPE
			SYNTAX	INTEGER
			ACCESS	read-only
			STATUS	current
	DESCRIPTION ""
			::= { mbus34 20 }

mbus34Value07		OBJECT-TYPE
			SYNTAX	INTEGER
			ACCESS	read-only
			STATUS	current
	DESCRIPTION ""
			::= { mbus34 21 }

mbus34VIF08		OBJECT-TYPE
			SYNTAX	INTEGER
			ACCESS	read-only
			STATUS	current
	DESCRIPTION ""
			::= { mbus34 22 }

mbus34Value08		OBJECT-TYPE
			SYNTAX	INTEGER
			ACCESS	read-only
			STATUS	current
	DESCRIPTION ""
			::= { mbus34 23 }

mbus34VIF09		OBJECT-TYPE
			SYNTAX	INTEGER
			ACCESS	read-only
			STATUS	current
	DESCRIPTION ""
			::= { mbus34 24 }

mbus34Value09		OBJECT-TYPE
			SYNTAX	INTEGER
			ACCESS	read-only
			STATUS	current
	DESCRIPTION ""
			::= { mbus34 25 }

mbus34VIF0A		OBJECT-TYPE
			SYNTAX	INTEGER
			ACCESS	read-only
			STATUS	current
	DESCRIPTION ""
			::= { mbus34 26 }

mbus34Value0A		OBJECT-TYPE
			SYNTAX	INTEGER
			ACCESS	read-only
			STATUS	current
	DESCRIPTION ""
			::= { mbus34 27 }

mbus34VIF0B		OBJECT-TYPE
			SYNTAX	INTEGER
			ACCESS	read-only
			STATUS	current
	DESCRIPTION ""
			::= { mbus34 28 }

mbus34Value0B		OBJECT-TYPE
			SYNTAX	INTEGER
			ACCESS	read-only
			STATUS	current
	DESCRIPTION ""
			::= { mbus34 29 }

mbus34VIF0C		OBJECT-TYPE
			SYNTAX	INTEGER
			ACCESS	read-only
			STATUS	current
	DESCRIPTION ""
			::= { mbus34 30 }

mbus34Value0C		OBJECT-TYPE
			SYNTAX	INTEGER
			ACCESS	read-only
			STATUS	current
	DESCRIPTION ""
			::= { mbus34 31 }

mbus34VIF0D		OBJECT-TYPE
			SYNTAX	INTEGER
			ACCESS	read-only
			STATUS	current
	DESCRIPTION ""
			::= { mbus34 32 }

mbus34Value0D		OBJECT-TYPE
			SYNTAX	INTEGER
			ACCESS	read-only
			STATUS	current
	DESCRIPTION ""
			::= { mbus34 33 }

mbus34VIF0E		OBJECT-TYPE
			SYNTAX	INTEGER
			ACCESS	read-only
			STATUS	current
	DESCRIPTION ""
			::= { mbus34 34 }

mbus34Value0E		OBJECT-TYPE
			SYNTAX	INTEGER
			ACCESS	read-only
			STATUS	current
	DESCRIPTION ""
			::= { mbus34 35 }

mbus34VIF0F		OBJECT-TYPE
			SYNTAX	INTEGER
			ACCESS	read-only
			STATUS	current
	DESCRIPTION ""
			::= { mbus34 36 }

mbus34Value0F		OBJECT-TYPE
			SYNTAX	INTEGER
			ACCESS	read-only
			STATUS	current
	DESCRIPTION ""
			::= { mbus34 37 }

mbus34VIF10		OBJECT-TYPE
			SYNTAX	INTEGER
			ACCESS	read-only
			STATUS	current
	DESCRIPTION ""
			::= { mbus34 38 }

mbus34Value10		OBJECT-TYPE
			SYNTAX	INTEGER
			ACCESS	read-only
			STATUS	current
	DESCRIPTION ""
			::= { mbus34 39 }

mbus34VIF11		OBJECT-TYPE
			SYNTAX	INTEGER
			ACCESS	read-only
			STATUS	current
	DESCRIPTION ""
			::= { mbus34 40 }

mbus34Value11		OBJECT-TYPE
			SYNTAX	INTEGER
			ACCESS	read-only
			STATUS	current
	DESCRIPTION ""
			::= { mbus34 41 }

mbus34VIF12		OBJECT-TYPE
			SYNTAX	INTEGER
			ACCESS	read-only
			STATUS	current
	DESCRIPTION ""
			::= { mbus34 42 }

mbus34Value12		OBJECT-TYPE
			SYNTAX	INTEGER
			ACCESS	read-only
			STATUS	current
	DESCRIPTION ""
			::= { mbus34 43 }

mbus34VIF13		OBJECT-TYPE
			SYNTAX	INTEGER
			ACCESS	read-only
			STATUS	current
	DESCRIPTION ""
			::= { mbus34 44 }

mbus34Value13		OBJECT-TYPE
			SYNTAX	INTEGER
			ACCESS	read-only
			STATUS	current
	DESCRIPTION ""
			::= { mbus34 45 }

mbus34VIF14		OBJECT-TYPE
			SYNTAX	INTEGER
			ACCESS	read-only
			STATUS	current
	DESCRIPTION ""
			::= { mbus34 46 }

mbus34Value14		OBJECT-TYPE
			SYNTAX	INTEGER
			ACCESS	read-only
			STATUS	current
	DESCRIPTION ""
			::= { mbus34 47 }

mbus34VIF15		OBJECT-TYPE
			SYNTAX	INTEGER
			ACCESS	read-only
			STATUS	current
	DESCRIPTION ""
			::= { mbus34 48 }

mbus34Value15		OBJECT-TYPE
			SYNTAX	INTEGER
			ACCESS	read-only
			STATUS	current
	DESCRIPTION ""
			::= { mbus34 49 }

mbus34VIF16		OBJECT-TYPE
			SYNTAX	INTEGER
			ACCESS	read-only
			STATUS	current
	DESCRIPTION ""
			::= { mbus34 50 }

mbus34Value16		OBJECT-TYPE
			SYNTAX	INTEGER
			ACCESS	read-only
			STATUS	current
	DESCRIPTION ""
			::= { mbus34 51 }

mbus34VIF17		OBJECT-TYPE
			SYNTAX	INTEGER
			ACCESS	read-only
			STATUS	current
	DESCRIPTION ""
			::= { mbus34 52 }

mbus34Value17		OBJECT-TYPE
			SYNTAX	INTEGER
			ACCESS	read-only
			STATUS	current
	DESCRIPTION ""
			::= { mbus34 53 }

mbus34VIF18		OBJECT-TYPE
			SYNTAX	INTEGER
			ACCESS	read-only
			STATUS	current
	DESCRIPTION ""
			::= { mbus34 54 }

mbus34Value18		OBJECT-TYPE
			SYNTAX	INTEGER
			ACCESS	read-only
			STATUS	current
	DESCRIPTION ""
			::= { mbus34 55 }

mbus34VIF19		OBJECT-TYPE
			SYNTAX	INTEGER
			ACCESS	read-only
			STATUS	current
	DESCRIPTION ""
			::= { mbus34 56 }

mbus34Value19		OBJECT-TYPE
			SYNTAX	INTEGER
			ACCESS	read-only
			STATUS	current
	DESCRIPTION ""
			::= { mbus34 57 }

mbus34VIF1A		OBJECT-TYPE
			SYNTAX	INTEGER
			ACCESS	read-only
			STATUS	current
	DESCRIPTION ""
			::= { mbus34 58 }

mbus34Value1A		OBJECT-TYPE
			SYNTAX	INTEGER
			ACCESS	read-only
			STATUS	current
	DESCRIPTION ""
			::= { mbus34 59 }

mbus34VIF1B		OBJECT-TYPE
			SYNTAX	INTEGER
			ACCESS	read-only
			STATUS	current
	DESCRIPTION ""
			::= { mbus34 60 }

mbus34Value1B		OBJECT-TYPE
			SYNTAX	INTEGER
			ACCESS	read-only
			STATUS	current
	DESCRIPTION ""
			::= { mbus34 61 }

mbus34VIF1C		OBJECT-TYPE
			SYNTAX	INTEGER
			ACCESS	read-only
			STATUS	current
	DESCRIPTION ""
			::= { mbus34 62 }

mbus34Value1C		OBJECT-TYPE
			SYNTAX	INTEGER
			ACCESS	read-only
			STATUS	current
	DESCRIPTION ""
			::= { mbus34 63 }

mbus34VIF1D		OBJECT-TYPE
			SYNTAX	INTEGER
			ACCESS	read-only
			STATUS	current
	DESCRIPTION ""
			::= { mbus34 64 }

mbus34Value1D		OBJECT-TYPE
			SYNTAX	INTEGER
			ACCESS	read-only
			STATUS	current
	DESCRIPTION ""
			::= { mbus34 65 }

mbus34VIF1E		OBJECT-TYPE
			SYNTAX	INTEGER
			ACCESS	read-only
			STATUS	current
	DESCRIPTION ""
			::= { mbus34 66 }

mbus34Value1E		OBJECT-TYPE
			SYNTAX	INTEGER
			ACCESS	read-only
			STATUS	current
	DESCRIPTION ""
			::= { mbus34 67 }

mbus34VIF1F		OBJECT-TYPE
			SYNTAX	INTEGER
			ACCESS	read-only
			STATUS	current
	DESCRIPTION ""
			::= { mbus34 68 }

mbus34Value1F		OBJECT-TYPE
			SYNTAX	INTEGER
			ACCESS	read-only
			STATUS	current
	DESCRIPTION ""
			::= { mbus34 69 }

mbus34VIF20		OBJECT-TYPE
			SYNTAX	INTEGER
			ACCESS	read-only
			STATUS	current
	DESCRIPTION ""
			::= { mbus34 70 }

mbus34Value20		OBJECT-TYPE
			SYNTAX	INTEGER
			ACCESS	read-only
			STATUS	current
	DESCRIPTION ""
			::= { mbus34 71 }

mbus34VIF21		OBJECT-TYPE
			SYNTAX	INTEGER
			ACCESS	read-only
			STATUS	current
	DESCRIPTION ""
			::= { mbus34 72 }

mbus34Value21		OBJECT-TYPE
			SYNTAX	INTEGER
			ACCESS	read-only
			STATUS	current
	DESCRIPTION ""
			::= { mbus34 73 }

mbus34VIF22		OBJECT-TYPE
			SYNTAX	INTEGER
			ACCESS	read-only
			STATUS	current
	DESCRIPTION ""
			::= { mbus34 74 }

mbus34Value22		OBJECT-TYPE
			SYNTAX	INTEGER
			ACCESS	read-only
			STATUS	current
	DESCRIPTION ""
			::= { mbus34 75 }

mbus34VIF23		OBJECT-TYPE
			SYNTAX	INTEGER
			ACCESS	read-only
			STATUS	current
	DESCRIPTION ""
			::= { mbus34 76 }

mbus34Value23		OBJECT-TYPE
			SYNTAX	INTEGER
			ACCESS	read-only
			STATUS	current
	DESCRIPTION ""
			::= { mbus34 77 }

mbus34VIF24		OBJECT-TYPE
			SYNTAX	INTEGER
			ACCESS	read-only
			STATUS	current
	DESCRIPTION ""
			::= { mbus34 78 }

mbus34Value24		OBJECT-TYPE
			SYNTAX	INTEGER
			ACCESS	read-only
			STATUS	current
	DESCRIPTION ""
			::= { mbus34 79 }

mbus34VIF25		OBJECT-TYPE
			SYNTAX	INTEGER
			ACCESS	read-only
			STATUS	current
	DESCRIPTION ""
			::= { mbus34 80 }

mbus34Value25		OBJECT-TYPE
			SYNTAX	INTEGER
			ACCESS	read-only
			STATUS	current
	DESCRIPTION ""
			::= { mbus34 81 }

mbus34VIF26		OBJECT-TYPE
			SYNTAX	INTEGER
			ACCESS	read-only
			STATUS	current
	DESCRIPTION ""
			::= { mbus34 82 }

mbus34Value26		OBJECT-TYPE
			SYNTAX	INTEGER
			ACCESS	read-only
			STATUS	current
	DESCRIPTION ""
			::= { mbus34 83 }

mbus34VIF27		OBJECT-TYPE
			SYNTAX	INTEGER
			ACCESS	read-only
			STATUS	current
	DESCRIPTION ""
			::= { mbus34 84 }

mbus34Value27		OBJECT-TYPE
			SYNTAX	INTEGER
			ACCESS	read-only
			STATUS	current
	DESCRIPTION ""
			::= { mbus34 85 }

mbus34VIF28		OBJECT-TYPE
			SYNTAX	INTEGER
			ACCESS	read-only
			STATUS	current
	DESCRIPTION ""
			::= { mbus34 86 }

mbus34Value28		OBJECT-TYPE
			SYNTAX	INTEGER
			ACCESS	read-only
			STATUS	current
	DESCRIPTION ""
			::= { mbus34 87 }

mbus34VIF29		OBJECT-TYPE
			SYNTAX	INTEGER
			ACCESS	read-only
			STATUS	current
	DESCRIPTION ""
			::= { mbus34 88 }

mbus34Value29		OBJECT-TYPE
			SYNTAX	INTEGER
			ACCESS	read-only
			STATUS	current
	DESCRIPTION ""
			::= { mbus34 89 }

mbus34VIF2A		OBJECT-TYPE
			SYNTAX	INTEGER
			ACCESS	read-only
			STATUS	current
	DESCRIPTION ""
			::= { mbus34 90 }

mbus34Value2A		OBJECT-TYPE
			SYNTAX	INTEGER
			ACCESS	read-only
			STATUS	current
	DESCRIPTION ""
			::= { mbus34 91 }

mbus34VIF2B		OBJECT-TYPE
			SYNTAX	INTEGER
			ACCESS	read-only
			STATUS	current
	DESCRIPTION ""
			::= { mbus34 92 }

mbus34Value2B		OBJECT-TYPE
			SYNTAX	INTEGER
			ACCESS	read-only
			STATUS	current
	DESCRIPTION ""
			::= { mbus34 93 }

mbus34VIF2C		OBJECT-TYPE
			SYNTAX	INTEGER
			ACCESS	read-only
			STATUS	current
	DESCRIPTION ""
			::= { mbus34 94 }

mbus34Value2C		OBJECT-TYPE
			SYNTAX	INTEGER
			ACCESS	read-only
			STATUS	current
	DESCRIPTION ""
			::= { mbus34 95 }

mbus34VIF2D		OBJECT-TYPE
			SYNTAX	INTEGER
			ACCESS	read-only
			STATUS	current
	DESCRIPTION ""
			::= { mbus34 96 }

mbus34Value2D		OBJECT-TYPE
			SYNTAX	INTEGER
			ACCESS	read-only
			STATUS	current
	DESCRIPTION ""
			::= { mbus34 97 }

mbus34VIF2E		OBJECT-TYPE
			SYNTAX	INTEGER
			ACCESS	read-only
			STATUS	current
	DESCRIPTION ""
			::= { mbus34 98 }

mbus34Value2E		OBJECT-TYPE
			SYNTAX	INTEGER
			ACCESS	read-only
			STATUS	current
	DESCRIPTION ""
			::= { mbus34 99 }

mbus34VIF2F		OBJECT-TYPE
			SYNTAX	INTEGER
			ACCESS	read-only
			STATUS	current
	DESCRIPTION ""
			::= { mbus34 100 }

mbus34Value2F		OBJECT-TYPE
			SYNTAX	INTEGER
			ACCESS	read-only
			STATUS	current
	DESCRIPTION ""
			::= { mbus34 101 }

mbus35			OBJECT IDENTIFIER ::= { mbus 53 }

mbus35IdNumber		OBJECT-TYPE
			SYNTAX	Gauge
			ACCESS	read-only
			STATUS	current
	DESCRIPTION ""
			::= { mbus35 1 }

mbus35Manufacturer	OBJECT-TYPE
			SYNTAX	Gauge
			ACCESS	read-only
			STATUS	current
	DESCRIPTION ""
			::= { mbus35 2 }

mbus35Version		OBJECT-TYPE
			SYNTAX	Gauge
			ACCESS	read-only
			STATUS	current
	DESCRIPTION ""
			::= { mbus35 3 }

mbus35Medium		OBJECT-TYPE
			SYNTAX	Gauge
			ACCESS	read-only
			STATUS	current
	DESCRIPTION ""
			::= { mbus35 4 }

mbus35Status		OBJECT-TYPE
			SYNTAX	Gauge
			ACCESS	read-only
			STATUS	current
	DESCRIPTION ""
			::= { mbus35 5 }

mbus35VIF00		OBJECT-TYPE
			SYNTAX	INTEGER
			ACCESS	read-only
			STATUS	current
	DESCRIPTION ""
			::= { mbus35 6 }

mbus35Value00		OBJECT-TYPE
			SYNTAX	INTEGER
			ACCESS	read-only
			STATUS	current
	DESCRIPTION ""
			::= { mbus35 7 }

mbus35VIF01		OBJECT-TYPE
			SYNTAX	INTEGER
			ACCESS	read-only
			STATUS	current
	DESCRIPTION ""
			::= { mbus35 8 }

mbus35Value01		OBJECT-TYPE
			SYNTAX	INTEGER
			ACCESS	read-only
			STATUS	current
	DESCRIPTION ""
			::= { mbus35 9 }

mbus35VIF02		OBJECT-TYPE
			SYNTAX	INTEGER
			ACCESS	read-only
			STATUS	current
	DESCRIPTION ""
			::= { mbus35 10 }

mbus35Value02		OBJECT-TYPE
			SYNTAX	INTEGER
			ACCESS	read-only
			STATUS	current
	DESCRIPTION ""
			::= { mbus35 11 }

mbus35VIF03		OBJECT-TYPE
			SYNTAX	INTEGER
			ACCESS	read-only
			STATUS	current
	DESCRIPTION ""
			::= { mbus35 12 }

mbus35Value03		OBJECT-TYPE
			SYNTAX	INTEGER
			ACCESS	read-only
			STATUS	current
	DESCRIPTION ""
			::= { mbus35 13 }

mbus35VIF04		OBJECT-TYPE
			SYNTAX	INTEGER
			ACCESS	read-only
			STATUS	current
	DESCRIPTION ""
			::= { mbus35 14 }

mbus35Value04		OBJECT-TYPE
			SYNTAX	INTEGER
			ACCESS	read-only
			STATUS	current
	DESCRIPTION ""
			::= { mbus35 15 }

mbus35VIF05		OBJECT-TYPE
			SYNTAX	INTEGER
			ACCESS	read-only
			STATUS	current
	DESCRIPTION ""
			::= { mbus35 16 }

mbus35Value05		OBJECT-TYPE
			SYNTAX	INTEGER
			ACCESS	read-only
			STATUS	current
	DESCRIPTION ""
			::= { mbus35 17 }

mbus35VIF06		OBJECT-TYPE
			SYNTAX	INTEGER
			ACCESS	read-only
			STATUS	current
	DESCRIPTION ""
			::= { mbus35 18 }

mbus35Value06		OBJECT-TYPE
			SYNTAX	INTEGER
			ACCESS	read-only
			STATUS	current
	DESCRIPTION ""
			::= { mbus35 19 }

mbus35VIF07		OBJECT-TYPE
			SYNTAX	INTEGER
			ACCESS	read-only
			STATUS	current
	DESCRIPTION ""
			::= { mbus35 20 }

mbus35Value07		OBJECT-TYPE
			SYNTAX	INTEGER
			ACCESS	read-only
			STATUS	current
	DESCRIPTION ""
			::= { mbus35 21 }

mbus35VIF08		OBJECT-TYPE
			SYNTAX	INTEGER
			ACCESS	read-only
			STATUS	current
	DESCRIPTION ""
			::= { mbus35 22 }

mbus35Value08		OBJECT-TYPE
			SYNTAX	INTEGER
			ACCESS	read-only
			STATUS	current
	DESCRIPTION ""
			::= { mbus35 23 }

mbus35VIF09		OBJECT-TYPE
			SYNTAX	INTEGER
			ACCESS	read-only
			STATUS	current
	DESCRIPTION ""
			::= { mbus35 24 }

mbus35Value09		OBJECT-TYPE
			SYNTAX	INTEGER
			ACCESS	read-only
			STATUS	current
	DESCRIPTION ""
			::= { mbus35 25 }

mbus35VIF0A		OBJECT-TYPE
			SYNTAX	INTEGER
			ACCESS	read-only
			STATUS	current
	DESCRIPTION ""
			::= { mbus35 26 }

mbus35Value0A		OBJECT-TYPE
			SYNTAX	INTEGER
			ACCESS	read-only
			STATUS	current
	DESCRIPTION ""
			::= { mbus35 27 }

mbus35VIF0B		OBJECT-TYPE
			SYNTAX	INTEGER
			ACCESS	read-only
			STATUS	current
	DESCRIPTION ""
			::= { mbus35 28 }

mbus35Value0B		OBJECT-TYPE
			SYNTAX	INTEGER
			ACCESS	read-only
			STATUS	current
	DESCRIPTION ""
			::= { mbus35 29 }

mbus35VIF0C		OBJECT-TYPE
			SYNTAX	INTEGER
			ACCESS	read-only
			STATUS	current
	DESCRIPTION ""
			::= { mbus35 30 }

mbus35Value0C		OBJECT-TYPE
			SYNTAX	INTEGER
			ACCESS	read-only
			STATUS	current
	DESCRIPTION ""
			::= { mbus35 31 }

mbus35VIF0D		OBJECT-TYPE
			SYNTAX	INTEGER
			ACCESS	read-only
			STATUS	current
	DESCRIPTION ""
			::= { mbus35 32 }

mbus35Value0D		OBJECT-TYPE
			SYNTAX	INTEGER
			ACCESS	read-only
			STATUS	current
	DESCRIPTION ""
			::= { mbus35 33 }

mbus35VIF0E		OBJECT-TYPE
			SYNTAX	INTEGER
			ACCESS	read-only
			STATUS	current
	DESCRIPTION ""
			::= { mbus35 34 }

mbus35Value0E		OBJECT-TYPE
			SYNTAX	INTEGER
			ACCESS	read-only
			STATUS	current
	DESCRIPTION ""
			::= { mbus35 35 }

mbus35VIF0F		OBJECT-TYPE
			SYNTAX	INTEGER
			ACCESS	read-only
			STATUS	current
	DESCRIPTION ""
			::= { mbus35 36 }

mbus35Value0F		OBJECT-TYPE
			SYNTAX	INTEGER
			ACCESS	read-only
			STATUS	current
	DESCRIPTION ""
			::= { mbus35 37 }

mbus35VIF10		OBJECT-TYPE
			SYNTAX	INTEGER
			ACCESS	read-only
			STATUS	current
	DESCRIPTION ""
			::= { mbus35 38 }

mbus35Value10		OBJECT-TYPE
			SYNTAX	INTEGER
			ACCESS	read-only
			STATUS	current
	DESCRIPTION ""
			::= { mbus35 39 }

mbus35VIF11		OBJECT-TYPE
			SYNTAX	INTEGER
			ACCESS	read-only
			STATUS	current
	DESCRIPTION ""
			::= { mbus35 40 }

mbus35Value11		OBJECT-TYPE
			SYNTAX	INTEGER
			ACCESS	read-only
			STATUS	current
	DESCRIPTION ""
			::= { mbus35 41 }

mbus35VIF12		OBJECT-TYPE
			SYNTAX	INTEGER
			ACCESS	read-only
			STATUS	current
	DESCRIPTION ""
			::= { mbus35 42 }

mbus35Value12		OBJECT-TYPE
			SYNTAX	INTEGER
			ACCESS	read-only
			STATUS	current
	DESCRIPTION ""
			::= { mbus35 43 }

mbus35VIF13		OBJECT-TYPE
			SYNTAX	INTEGER
			ACCESS	read-only
			STATUS	current
	DESCRIPTION ""
			::= { mbus35 44 }

mbus35Value13		OBJECT-TYPE
			SYNTAX	INTEGER
			ACCESS	read-only
			STATUS	current
	DESCRIPTION ""
			::= { mbus35 45 }

mbus35VIF14		OBJECT-TYPE
			SYNTAX	INTEGER
			ACCESS	read-only
			STATUS	current
	DESCRIPTION ""
			::= { mbus35 46 }

mbus35Value14		OBJECT-TYPE
			SYNTAX	INTEGER
			ACCESS	read-only
			STATUS	current
	DESCRIPTION ""
			::= { mbus35 47 }

mbus35VIF15		OBJECT-TYPE
			SYNTAX	INTEGER
			ACCESS	read-only
			STATUS	current
	DESCRIPTION ""
			::= { mbus35 48 }

mbus35Value15		OBJECT-TYPE
			SYNTAX	INTEGER
			ACCESS	read-only
			STATUS	current
	DESCRIPTION ""
			::= { mbus35 49 }

mbus35VIF16		OBJECT-TYPE
			SYNTAX	INTEGER
			ACCESS	read-only
			STATUS	current
	DESCRIPTION ""
			::= { mbus35 50 }

mbus35Value16		OBJECT-TYPE
			SYNTAX	INTEGER
			ACCESS	read-only
			STATUS	current
	DESCRIPTION ""
			::= { mbus35 51 }

mbus35VIF17		OBJECT-TYPE
			SYNTAX	INTEGER
			ACCESS	read-only
			STATUS	current
	DESCRIPTION ""
			::= { mbus35 52 }

mbus35Value17		OBJECT-TYPE
			SYNTAX	INTEGER
			ACCESS	read-only
			STATUS	current
	DESCRIPTION ""
			::= { mbus35 53 }

mbus35VIF18		OBJECT-TYPE
			SYNTAX	INTEGER
			ACCESS	read-only
			STATUS	current
	DESCRIPTION ""
			::= { mbus35 54 }

mbus35Value18		OBJECT-TYPE
			SYNTAX	INTEGER
			ACCESS	read-only
			STATUS	current
	DESCRIPTION ""
			::= { mbus35 55 }

mbus35VIF19		OBJECT-TYPE
			SYNTAX	INTEGER
			ACCESS	read-only
			STATUS	current
	DESCRIPTION ""
			::= { mbus35 56 }

mbus35Value19		OBJECT-TYPE
			SYNTAX	INTEGER
			ACCESS	read-only
			STATUS	current
	DESCRIPTION ""
			::= { mbus35 57 }

mbus35VIF1A		OBJECT-TYPE
			SYNTAX	INTEGER
			ACCESS	read-only
			STATUS	current
	DESCRIPTION ""
			::= { mbus35 58 }

mbus35Value1A		OBJECT-TYPE
			SYNTAX	INTEGER
			ACCESS	read-only
			STATUS	current
	DESCRIPTION ""
			::= { mbus35 59 }

mbus35VIF1B		OBJECT-TYPE
			SYNTAX	INTEGER
			ACCESS	read-only
			STATUS	current
	DESCRIPTION ""
			::= { mbus35 60 }

mbus35Value1B		OBJECT-TYPE
			SYNTAX	INTEGER
			ACCESS	read-only
			STATUS	current
	DESCRIPTION ""
			::= { mbus35 61 }

mbus35VIF1C		OBJECT-TYPE
			SYNTAX	INTEGER
			ACCESS	read-only
			STATUS	current
	DESCRIPTION ""
			::= { mbus35 62 }

mbus35Value1C		OBJECT-TYPE
			SYNTAX	INTEGER
			ACCESS	read-only
			STATUS	current
	DESCRIPTION ""
			::= { mbus35 63 }

mbus35VIF1D		OBJECT-TYPE
			SYNTAX	INTEGER
			ACCESS	read-only
			STATUS	current
	DESCRIPTION ""
			::= { mbus35 64 }

mbus35Value1D		OBJECT-TYPE
			SYNTAX	INTEGER
			ACCESS	read-only
			STATUS	current
	DESCRIPTION ""
			::= { mbus35 65 }

mbus35VIF1E		OBJECT-TYPE
			SYNTAX	INTEGER
			ACCESS	read-only
			STATUS	current
	DESCRIPTION ""
			::= { mbus35 66 }

mbus35Value1E		OBJECT-TYPE
			SYNTAX	INTEGER
			ACCESS	read-only
			STATUS	current
	DESCRIPTION ""
			::= { mbus35 67 }

mbus35VIF1F		OBJECT-TYPE
			SYNTAX	INTEGER
			ACCESS	read-only
			STATUS	current
	DESCRIPTION ""
			::= { mbus35 68 }

mbus35Value1F		OBJECT-TYPE
			SYNTAX	INTEGER
			ACCESS	read-only
			STATUS	current
	DESCRIPTION ""
			::= { mbus35 69 }

mbus35VIF20		OBJECT-TYPE
			SYNTAX	INTEGER
			ACCESS	read-only
			STATUS	current
	DESCRIPTION ""
			::= { mbus35 70 }

mbus35Value20		OBJECT-TYPE
			SYNTAX	INTEGER
			ACCESS	read-only
			STATUS	current
	DESCRIPTION ""
			::= { mbus35 71 }

mbus35VIF21		OBJECT-TYPE
			SYNTAX	INTEGER
			ACCESS	read-only
			STATUS	current
	DESCRIPTION ""
			::= { mbus35 72 }

mbus35Value21		OBJECT-TYPE
			SYNTAX	INTEGER
			ACCESS	read-only
			STATUS	current
	DESCRIPTION ""
			::= { mbus35 73 }

mbus35VIF22		OBJECT-TYPE
			SYNTAX	INTEGER
			ACCESS	read-only
			STATUS	current
	DESCRIPTION ""
			::= { mbus35 74 }

mbus35Value22		OBJECT-TYPE
			SYNTAX	INTEGER
			ACCESS	read-only
			STATUS	current
	DESCRIPTION ""
			::= { mbus35 75 }

mbus35VIF23		OBJECT-TYPE
			SYNTAX	INTEGER
			ACCESS	read-only
			STATUS	current
	DESCRIPTION ""
			::= { mbus35 76 }

mbus35Value23		OBJECT-TYPE
			SYNTAX	INTEGER
			ACCESS	read-only
			STATUS	current
	DESCRIPTION ""
			::= { mbus35 77 }

mbus35VIF24		OBJECT-TYPE
			SYNTAX	INTEGER
			ACCESS	read-only
			STATUS	current
	DESCRIPTION ""
			::= { mbus35 78 }

mbus35Value24		OBJECT-TYPE
			SYNTAX	INTEGER
			ACCESS	read-only
			STATUS	current
	DESCRIPTION ""
			::= { mbus35 79 }

mbus35VIF25		OBJECT-TYPE
			SYNTAX	INTEGER
			ACCESS	read-only
			STATUS	current
	DESCRIPTION ""
			::= { mbus35 80 }

mbus35Value25		OBJECT-TYPE
			SYNTAX	INTEGER
			ACCESS	read-only
			STATUS	current
	DESCRIPTION ""
			::= { mbus35 81 }

mbus35VIF26		OBJECT-TYPE
			SYNTAX	INTEGER
			ACCESS	read-only
			STATUS	current
	DESCRIPTION ""
			::= { mbus35 82 }

mbus35Value26		OBJECT-TYPE
			SYNTAX	INTEGER
			ACCESS	read-only
			STATUS	current
	DESCRIPTION ""
			::= { mbus35 83 }

mbus35VIF27		OBJECT-TYPE
			SYNTAX	INTEGER
			ACCESS	read-only
			STATUS	current
	DESCRIPTION ""
			::= { mbus35 84 }

mbus35Value27		OBJECT-TYPE
			SYNTAX	INTEGER
			ACCESS	read-only
			STATUS	current
	DESCRIPTION ""
			::= { mbus35 85 }

mbus35VIF28		OBJECT-TYPE
			SYNTAX	INTEGER
			ACCESS	read-only
			STATUS	current
	DESCRIPTION ""
			::= { mbus35 86 }

mbus35Value28		OBJECT-TYPE
			SYNTAX	INTEGER
			ACCESS	read-only
			STATUS	current
	DESCRIPTION ""
			::= { mbus35 87 }

mbus35VIF29		OBJECT-TYPE
			SYNTAX	INTEGER
			ACCESS	read-only
			STATUS	current
	DESCRIPTION ""
			::= { mbus35 88 }

mbus35Value29		OBJECT-TYPE
			SYNTAX	INTEGER
			ACCESS	read-only
			STATUS	current
	DESCRIPTION ""
			::= { mbus35 89 }

mbus35VIF2A		OBJECT-TYPE
			SYNTAX	INTEGER
			ACCESS	read-only
			STATUS	current
	DESCRIPTION ""
			::= { mbus35 90 }

mbus35Value2A		OBJECT-TYPE
			SYNTAX	INTEGER
			ACCESS	read-only
			STATUS	current
	DESCRIPTION ""
			::= { mbus35 91 }

mbus35VIF2B		OBJECT-TYPE
			SYNTAX	INTEGER
			ACCESS	read-only
			STATUS	current
	DESCRIPTION ""
			::= { mbus35 92 }

mbus35Value2B		OBJECT-TYPE
			SYNTAX	INTEGER
			ACCESS	read-only
			STATUS	current
	DESCRIPTION ""
			::= { mbus35 93 }

mbus35VIF2C		OBJECT-TYPE
			SYNTAX	INTEGER
			ACCESS	read-only
			STATUS	current
	DESCRIPTION ""
			::= { mbus35 94 }

mbus35Value2C		OBJECT-TYPE
			SYNTAX	INTEGER
			ACCESS	read-only
			STATUS	current
	DESCRIPTION ""
			::= { mbus35 95 }

mbus35VIF2D		OBJECT-TYPE
			SYNTAX	INTEGER
			ACCESS	read-only
			STATUS	current
	DESCRIPTION ""
			::= { mbus35 96 }

mbus35Value2D		OBJECT-TYPE
			SYNTAX	INTEGER
			ACCESS	read-only
			STATUS	current
	DESCRIPTION ""
			::= { mbus35 97 }

mbus35VIF2E		OBJECT-TYPE
			SYNTAX	INTEGER
			ACCESS	read-only
			STATUS	current
	DESCRIPTION ""
			::= { mbus35 98 }

mbus35Value2E		OBJECT-TYPE
			SYNTAX	INTEGER
			ACCESS	read-only
			STATUS	current
	DESCRIPTION ""
			::= { mbus35 99 }

mbus35VIF2F		OBJECT-TYPE
			SYNTAX	INTEGER
			ACCESS	read-only
			STATUS	current
	DESCRIPTION ""
			::= { mbus35 100 }

mbus35Value2F		OBJECT-TYPE
			SYNTAX	INTEGER
			ACCESS	read-only
			STATUS	current
	DESCRIPTION ""
			::= { mbus35 101 }

mbus36			OBJECT IDENTIFIER ::= { mbus 54 }

mbus36IdNumber		OBJECT-TYPE
			SYNTAX	Gauge
			ACCESS	read-only
			STATUS	current
	DESCRIPTION ""
			::= { mbus36 1 }

mbus36Manufacturer	OBJECT-TYPE
			SYNTAX	Gauge
			ACCESS	read-only
			STATUS	current
	DESCRIPTION ""
			::= { mbus36 2 }

mbus36Version		OBJECT-TYPE
			SYNTAX	Gauge
			ACCESS	read-only
			STATUS	current
	DESCRIPTION ""
			::= { mbus36 3 }

mbus36Medium		OBJECT-TYPE
			SYNTAX	Gauge
			ACCESS	read-only
			STATUS	current
	DESCRIPTION ""
			::= { mbus36 4 }

mbus36Status		OBJECT-TYPE
			SYNTAX	Gauge
			ACCESS	read-only
			STATUS	current
	DESCRIPTION ""
			::= { mbus36 5 }

mbus36VIF00		OBJECT-TYPE
			SYNTAX	INTEGER
			ACCESS	read-only
			STATUS	current
	DESCRIPTION ""
			::= { mbus36 6 }

mbus36Value00		OBJECT-TYPE
			SYNTAX	INTEGER
			ACCESS	read-only
			STATUS	current
	DESCRIPTION ""
			::= { mbus36 7 }

mbus36VIF01		OBJECT-TYPE
			SYNTAX	INTEGER
			ACCESS	read-only
			STATUS	current
	DESCRIPTION ""
			::= { mbus36 8 }

mbus36Value01		OBJECT-TYPE
			SYNTAX	INTEGER
			ACCESS	read-only
			STATUS	current
	DESCRIPTION ""
			::= { mbus36 9 }

mbus36VIF02		OBJECT-TYPE
			SYNTAX	INTEGER
			ACCESS	read-only
			STATUS	current
	DESCRIPTION ""
			::= { mbus36 10 }

mbus36Value02		OBJECT-TYPE
			SYNTAX	INTEGER
			ACCESS	read-only
			STATUS	current
	DESCRIPTION ""
			::= { mbus36 11 }

mbus36VIF03		OBJECT-TYPE
			SYNTAX	INTEGER
			ACCESS	read-only
			STATUS	current
	DESCRIPTION ""
			::= { mbus36 12 }

mbus36Value03		OBJECT-TYPE
			SYNTAX	INTEGER
			ACCESS	read-only
			STATUS	current
	DESCRIPTION ""
			::= { mbus36 13 }

mbus36VIF04		OBJECT-TYPE
			SYNTAX	INTEGER
			ACCESS	read-only
			STATUS	current
	DESCRIPTION ""
			::= { mbus36 14 }

mbus36Value04		OBJECT-TYPE
			SYNTAX	INTEGER
			ACCESS	read-only
			STATUS	current
	DESCRIPTION ""
			::= { mbus36 15 }

mbus36VIF05		OBJECT-TYPE
			SYNTAX	INTEGER
			ACCESS	read-only
			STATUS	current
	DESCRIPTION ""
			::= { mbus36 16 }

mbus36Value05		OBJECT-TYPE
			SYNTAX	INTEGER
			ACCESS	read-only
			STATUS	current
	DESCRIPTION ""
			::= { mbus36 17 }

mbus36VIF06		OBJECT-TYPE
			SYNTAX	INTEGER
			ACCESS	read-only
			STATUS	current
	DESCRIPTION ""
			::= { mbus36 18 }

mbus36Value06		OBJECT-TYPE
			SYNTAX	INTEGER
			ACCESS	read-only
			STATUS	current
	DESCRIPTION ""
			::= { mbus36 19 }

mbus36VIF07		OBJECT-TYPE
			SYNTAX	INTEGER
			ACCESS	read-only
			STATUS	current
	DESCRIPTION ""
			::= { mbus36 20 }

mbus36Value07		OBJECT-TYPE
			SYNTAX	INTEGER
			ACCESS	read-only
			STATUS	current
	DESCRIPTION ""
			::= { mbus36 21 }

mbus36VIF08		OBJECT-TYPE
			SYNTAX	INTEGER
			ACCESS	read-only
			STATUS	current
	DESCRIPTION ""
			::= { mbus36 22 }

mbus36Value08		OBJECT-TYPE
			SYNTAX	INTEGER
			ACCESS	read-only
			STATUS	current
	DESCRIPTION ""
			::= { mbus36 23 }

mbus36VIF09		OBJECT-TYPE
			SYNTAX	INTEGER
			ACCESS	read-only
			STATUS	current
	DESCRIPTION ""
			::= { mbus36 24 }

mbus36Value09		OBJECT-TYPE
			SYNTAX	INTEGER
			ACCESS	read-only
			STATUS	current
	DESCRIPTION ""
			::= { mbus36 25 }

mbus36VIF0A		OBJECT-TYPE
			SYNTAX	INTEGER
			ACCESS	read-only
			STATUS	current
	DESCRIPTION ""
			::= { mbus36 26 }

mbus36Value0A		OBJECT-TYPE
			SYNTAX	INTEGER
			ACCESS	read-only
			STATUS	current
	DESCRIPTION ""
			::= { mbus36 27 }

mbus36VIF0B		OBJECT-TYPE
			SYNTAX	INTEGER
			ACCESS	read-only
			STATUS	current
	DESCRIPTION ""
			::= { mbus36 28 }

mbus36Value0B		OBJECT-TYPE
			SYNTAX	INTEGER
			ACCESS	read-only
			STATUS	current
	DESCRIPTION ""
			::= { mbus36 29 }

mbus36VIF0C		OBJECT-TYPE
			SYNTAX	INTEGER
			ACCESS	read-only
			STATUS	current
	DESCRIPTION ""
			::= { mbus36 30 }

mbus36Value0C		OBJECT-TYPE
			SYNTAX	INTEGER
			ACCESS	read-only
			STATUS	current
	DESCRIPTION ""
			::= { mbus36 31 }

mbus36VIF0D		OBJECT-TYPE
			SYNTAX	INTEGER
			ACCESS	read-only
			STATUS	current
	DESCRIPTION ""
			::= { mbus36 32 }

mbus36Value0D		OBJECT-TYPE
			SYNTAX	INTEGER
			ACCESS	read-only
			STATUS	current
	DESCRIPTION ""
			::= { mbus36 33 }

mbus36VIF0E		OBJECT-TYPE
			SYNTAX	INTEGER
			ACCESS	read-only
			STATUS	current
	DESCRIPTION ""
			::= { mbus36 34 }

mbus36Value0E		OBJECT-TYPE
			SYNTAX	INTEGER
			ACCESS	read-only
			STATUS	current
	DESCRIPTION ""
			::= { mbus36 35 }

mbus36VIF0F		OBJECT-TYPE
			SYNTAX	INTEGER
			ACCESS	read-only
			STATUS	current
	DESCRIPTION ""
			::= { mbus36 36 }

mbus36Value0F		OBJECT-TYPE
			SYNTAX	INTEGER
			ACCESS	read-only
			STATUS	current
	DESCRIPTION ""
			::= { mbus36 37 }

mbus36VIF10		OBJECT-TYPE
			SYNTAX	INTEGER
			ACCESS	read-only
			STATUS	current
	DESCRIPTION ""
			::= { mbus36 38 }

mbus36Value10		OBJECT-TYPE
			SYNTAX	INTEGER
			ACCESS	read-only
			STATUS	current
	DESCRIPTION ""
			::= { mbus36 39 }

mbus36VIF11		OBJECT-TYPE
			SYNTAX	INTEGER
			ACCESS	read-only
			STATUS	current
	DESCRIPTION ""
			::= { mbus36 40 }

mbus36Value11		OBJECT-TYPE
			SYNTAX	INTEGER
			ACCESS	read-only
			STATUS	current
	DESCRIPTION ""
			::= { mbus36 41 }

mbus36VIF12		OBJECT-TYPE
			SYNTAX	INTEGER
			ACCESS	read-only
			STATUS	current
	DESCRIPTION ""
			::= { mbus36 42 }

mbus36Value12		OBJECT-TYPE
			SYNTAX	INTEGER
			ACCESS	read-only
			STATUS	current
	DESCRIPTION ""
			::= { mbus36 43 }

mbus36VIF13		OBJECT-TYPE
			SYNTAX	INTEGER
			ACCESS	read-only
			STATUS	current
	DESCRIPTION ""
			::= { mbus36 44 }

mbus36Value13		OBJECT-TYPE
			SYNTAX	INTEGER
			ACCESS	read-only
			STATUS	current
	DESCRIPTION ""
			::= { mbus36 45 }

mbus36VIF14		OBJECT-TYPE
			SYNTAX	INTEGER
			ACCESS	read-only
			STATUS	current
	DESCRIPTION ""
			::= { mbus36 46 }

mbus36Value14		OBJECT-TYPE
			SYNTAX	INTEGER
			ACCESS	read-only
			STATUS	current
	DESCRIPTION ""
			::= { mbus36 47 }

mbus36VIF15		OBJECT-TYPE
			SYNTAX	INTEGER
			ACCESS	read-only
			STATUS	current
	DESCRIPTION ""
			::= { mbus36 48 }

mbus36Value15		OBJECT-TYPE
			SYNTAX	INTEGER
			ACCESS	read-only
			STATUS	current
	DESCRIPTION ""
			::= { mbus36 49 }

mbus36VIF16		OBJECT-TYPE
			SYNTAX	INTEGER
			ACCESS	read-only
			STATUS	current
	DESCRIPTION ""
			::= { mbus36 50 }

mbus36Value16		OBJECT-TYPE
			SYNTAX	INTEGER
			ACCESS	read-only
			STATUS	current
	DESCRIPTION ""
			::= { mbus36 51 }

mbus36VIF17		OBJECT-TYPE
			SYNTAX	INTEGER
			ACCESS	read-only
			STATUS	current
	DESCRIPTION ""
			::= { mbus36 52 }

mbus36Value17		OBJECT-TYPE
			SYNTAX	INTEGER
			ACCESS	read-only
			STATUS	current
	DESCRIPTION ""
			::= { mbus36 53 }

mbus36VIF18		OBJECT-TYPE
			SYNTAX	INTEGER
			ACCESS	read-only
			STATUS	current
	DESCRIPTION ""
			::= { mbus36 54 }

mbus36Value18		OBJECT-TYPE
			SYNTAX	INTEGER
			ACCESS	read-only
			STATUS	current
	DESCRIPTION ""
			::= { mbus36 55 }

mbus36VIF19		OBJECT-TYPE
			SYNTAX	INTEGER
			ACCESS	read-only
			STATUS	current
	DESCRIPTION ""
			::= { mbus36 56 }

mbus36Value19		OBJECT-TYPE
			SYNTAX	INTEGER
			ACCESS	read-only
			STATUS	current
	DESCRIPTION ""
			::= { mbus36 57 }

mbus36VIF1A		OBJECT-TYPE
			SYNTAX	INTEGER
			ACCESS	read-only
			STATUS	current
	DESCRIPTION ""
			::= { mbus36 58 }

mbus36Value1A		OBJECT-TYPE
			SYNTAX	INTEGER
			ACCESS	read-only
			STATUS	current
	DESCRIPTION ""
			::= { mbus36 59 }

mbus36VIF1B		OBJECT-TYPE
			SYNTAX	INTEGER
			ACCESS	read-only
			STATUS	current
	DESCRIPTION ""
			::= { mbus36 60 }

mbus36Value1B		OBJECT-TYPE
			SYNTAX	INTEGER
			ACCESS	read-only
			STATUS	current
	DESCRIPTION ""
			::= { mbus36 61 }

mbus36VIF1C		OBJECT-TYPE
			SYNTAX	INTEGER
			ACCESS	read-only
			STATUS	current
	DESCRIPTION ""
			::= { mbus36 62 }

mbus36Value1C		OBJECT-TYPE
			SYNTAX	INTEGER
			ACCESS	read-only
			STATUS	current
	DESCRIPTION ""
			::= { mbus36 63 }

mbus36VIF1D		OBJECT-TYPE
			SYNTAX	INTEGER
			ACCESS	read-only
			STATUS	current
	DESCRIPTION ""
			::= { mbus36 64 }

mbus36Value1D		OBJECT-TYPE
			SYNTAX	INTEGER
			ACCESS	read-only
			STATUS	current
	DESCRIPTION ""
			::= { mbus36 65 }

mbus36VIF1E		OBJECT-TYPE
			SYNTAX	INTEGER
			ACCESS	read-only
			STATUS	current
	DESCRIPTION ""
			::= { mbus36 66 }

mbus36Value1E		OBJECT-TYPE
			SYNTAX	INTEGER
			ACCESS	read-only
			STATUS	current
	DESCRIPTION ""
			::= { mbus36 67 }

mbus36VIF1F		OBJECT-TYPE
			SYNTAX	INTEGER
			ACCESS	read-only
			STATUS	current
	DESCRIPTION ""
			::= { mbus36 68 }

mbus36Value1F		OBJECT-TYPE
			SYNTAX	INTEGER
			ACCESS	read-only
			STATUS	current
	DESCRIPTION ""
			::= { mbus36 69 }

mbus36VIF20		OBJECT-TYPE
			SYNTAX	INTEGER
			ACCESS	read-only
			STATUS	current
	DESCRIPTION ""
			::= { mbus36 70 }

mbus36Value20		OBJECT-TYPE
			SYNTAX	INTEGER
			ACCESS	read-only
			STATUS	current
	DESCRIPTION ""
			::= { mbus36 71 }

mbus36VIF21		OBJECT-TYPE
			SYNTAX	INTEGER
			ACCESS	read-only
			STATUS	current
	DESCRIPTION ""
			::= { mbus36 72 }

mbus36Value21		OBJECT-TYPE
			SYNTAX	INTEGER
			ACCESS	read-only
			STATUS	current
	DESCRIPTION ""
			::= { mbus36 73 }

mbus36VIF22		OBJECT-TYPE
			SYNTAX	INTEGER
			ACCESS	read-only
			STATUS	current
	DESCRIPTION ""
			::= { mbus36 74 }

mbus36Value22		OBJECT-TYPE
			SYNTAX	INTEGER
			ACCESS	read-only
			STATUS	current
	DESCRIPTION ""
			::= { mbus36 75 }

mbus36VIF23		OBJECT-TYPE
			SYNTAX	INTEGER
			ACCESS	read-only
			STATUS	current
	DESCRIPTION ""
			::= { mbus36 76 }

mbus36Value23		OBJECT-TYPE
			SYNTAX	INTEGER
			ACCESS	read-only
			STATUS	current
	DESCRIPTION ""
			::= { mbus36 77 }

mbus36VIF24		OBJECT-TYPE
			SYNTAX	INTEGER
			ACCESS	read-only
			STATUS	current
	DESCRIPTION ""
			::= { mbus36 78 }

mbus36Value24		OBJECT-TYPE
			SYNTAX	INTEGER
			ACCESS	read-only
			STATUS	current
	DESCRIPTION ""
			::= { mbus36 79 }

mbus36VIF25		OBJECT-TYPE
			SYNTAX	INTEGER
			ACCESS	read-only
			STATUS	current
	DESCRIPTION ""
			::= { mbus36 80 }

mbus36Value25		OBJECT-TYPE
			SYNTAX	INTEGER
			ACCESS	read-only
			STATUS	current
	DESCRIPTION ""
			::= { mbus36 81 }

mbus36VIF26		OBJECT-TYPE
			SYNTAX	INTEGER
			ACCESS	read-only
			STATUS	current
	DESCRIPTION ""
			::= { mbus36 82 }

mbus36Value26		OBJECT-TYPE
			SYNTAX	INTEGER
			ACCESS	read-only
			STATUS	current
	DESCRIPTION ""
			::= { mbus36 83 }

mbus36VIF27		OBJECT-TYPE
			SYNTAX	INTEGER
			ACCESS	read-only
			STATUS	current
	DESCRIPTION ""
			::= { mbus36 84 }

mbus36Value27		OBJECT-TYPE
			SYNTAX	INTEGER
			ACCESS	read-only
			STATUS	current
	DESCRIPTION ""
			::= { mbus36 85 }

mbus36VIF28		OBJECT-TYPE
			SYNTAX	INTEGER
			ACCESS	read-only
			STATUS	current
	DESCRIPTION ""
			::= { mbus36 86 }

mbus36Value28		OBJECT-TYPE
			SYNTAX	INTEGER
			ACCESS	read-only
			STATUS	current
	DESCRIPTION ""
			::= { mbus36 87 }

mbus36VIF29		OBJECT-TYPE
			SYNTAX	INTEGER
			ACCESS	read-only
			STATUS	current
	DESCRIPTION ""
			::= { mbus36 88 }

mbus36Value29		OBJECT-TYPE
			SYNTAX	INTEGER
			ACCESS	read-only
			STATUS	current
	DESCRIPTION ""
			::= { mbus36 89 }

mbus36VIF2A		OBJECT-TYPE
			SYNTAX	INTEGER
			ACCESS	read-only
			STATUS	current
	DESCRIPTION ""
			::= { mbus36 90 }

mbus36Value2A		OBJECT-TYPE
			SYNTAX	INTEGER
			ACCESS	read-only
			STATUS	current
	DESCRIPTION ""
			::= { mbus36 91 }

mbus36VIF2B		OBJECT-TYPE
			SYNTAX	INTEGER
			ACCESS	read-only
			STATUS	current
	DESCRIPTION ""
			::= { mbus36 92 }

mbus36Value2B		OBJECT-TYPE
			SYNTAX	INTEGER
			ACCESS	read-only
			STATUS	current
	DESCRIPTION ""
			::= { mbus36 93 }

mbus36VIF2C		OBJECT-TYPE
			SYNTAX	INTEGER
			ACCESS	read-only
			STATUS	current
	DESCRIPTION ""
			::= { mbus36 94 }

mbus36Value2C		OBJECT-TYPE
			SYNTAX	INTEGER
			ACCESS	read-only
			STATUS	current
	DESCRIPTION ""
			::= { mbus36 95 }

mbus36VIF2D		OBJECT-TYPE
			SYNTAX	INTEGER
			ACCESS	read-only
			STATUS	current
	DESCRIPTION ""
			::= { mbus36 96 }

mbus36Value2D		OBJECT-TYPE
			SYNTAX	INTEGER
			ACCESS	read-only
			STATUS	current
	DESCRIPTION ""
			::= { mbus36 97 }

mbus36VIF2E		OBJECT-TYPE
			SYNTAX	INTEGER
			ACCESS	read-only
			STATUS	current
	DESCRIPTION ""
			::= { mbus36 98 }

mbus36Value2E		OBJECT-TYPE
			SYNTAX	INTEGER
			ACCESS	read-only
			STATUS	current
	DESCRIPTION ""
			::= { mbus36 99 }

mbus36VIF2F		OBJECT-TYPE
			SYNTAX	INTEGER
			ACCESS	read-only
			STATUS	current
	DESCRIPTION ""
			::= { mbus36 100 }

mbus36Value2F		OBJECT-TYPE
			SYNTAX	INTEGER
			ACCESS	read-only
			STATUS	current
	DESCRIPTION ""
			::= { mbus36 101 }

mbus37			OBJECT IDENTIFIER ::= { mbus 55 }

mbus37IdNumber		OBJECT-TYPE
			SYNTAX	Gauge
			ACCESS	read-only
			STATUS	current
	DESCRIPTION ""
			::= { mbus37 1 }

mbus37Manufacturer	OBJECT-TYPE
			SYNTAX	Gauge
			ACCESS	read-only
			STATUS	current
	DESCRIPTION ""
			::= { mbus37 2 }

mbus37Version		OBJECT-TYPE
			SYNTAX	Gauge
			ACCESS	read-only
			STATUS	current
	DESCRIPTION ""
			::= { mbus37 3 }

mbus37Medium		OBJECT-TYPE
			SYNTAX	Gauge
			ACCESS	read-only
			STATUS	current
	DESCRIPTION ""
			::= { mbus37 4 }

mbus37Status		OBJECT-TYPE
			SYNTAX	Gauge
			ACCESS	read-only
			STATUS	current
	DESCRIPTION ""
			::= { mbus37 5 }

mbus37VIF00		OBJECT-TYPE
			SYNTAX	INTEGER
			ACCESS	read-only
			STATUS	current
	DESCRIPTION ""
			::= { mbus37 6 }

mbus37Value00		OBJECT-TYPE
			SYNTAX	INTEGER
			ACCESS	read-only
			STATUS	current
	DESCRIPTION ""
			::= { mbus37 7 }

mbus37VIF01		OBJECT-TYPE
			SYNTAX	INTEGER
			ACCESS	read-only
			STATUS	current
	DESCRIPTION ""
			::= { mbus37 8 }

mbus37Value01		OBJECT-TYPE
			SYNTAX	INTEGER
			ACCESS	read-only
			STATUS	current
	DESCRIPTION ""
			::= { mbus37 9 }

mbus37VIF02		OBJECT-TYPE
			SYNTAX	INTEGER
			ACCESS	read-only
			STATUS	current
	DESCRIPTION ""
			::= { mbus37 10 }

mbus37Value02		OBJECT-TYPE
			SYNTAX	INTEGER
			ACCESS	read-only
			STATUS	current
	DESCRIPTION ""
			::= { mbus37 11 }

mbus37VIF03		OBJECT-TYPE
			SYNTAX	INTEGER
			ACCESS	read-only
			STATUS	current
	DESCRIPTION ""
			::= { mbus37 12 }

mbus37Value03		OBJECT-TYPE
			SYNTAX	INTEGER
			ACCESS	read-only
			STATUS	current
	DESCRIPTION ""
			::= { mbus37 13 }

mbus37VIF04		OBJECT-TYPE
			SYNTAX	INTEGER
			ACCESS	read-only
			STATUS	current
	DESCRIPTION ""
			::= { mbus37 14 }

mbus37Value04		OBJECT-TYPE
			SYNTAX	INTEGER
			ACCESS	read-only
			STATUS	current
	DESCRIPTION ""
			::= { mbus37 15 }

mbus37VIF05		OBJECT-TYPE
			SYNTAX	INTEGER
			ACCESS	read-only
			STATUS	current
	DESCRIPTION ""
			::= { mbus37 16 }

mbus37Value05		OBJECT-TYPE
			SYNTAX	INTEGER
			ACCESS	read-only
			STATUS	current
	DESCRIPTION ""
			::= { mbus37 17 }

mbus37VIF06		OBJECT-TYPE
			SYNTAX	INTEGER
			ACCESS	read-only
			STATUS	current
	DESCRIPTION ""
			::= { mbus37 18 }

mbus37Value06		OBJECT-TYPE
			SYNTAX	INTEGER
			ACCESS	read-only
			STATUS	current
	DESCRIPTION ""
			::= { mbus37 19 }

mbus37VIF07		OBJECT-TYPE
			SYNTAX	INTEGER
			ACCESS	read-only
			STATUS	current
	DESCRIPTION ""
			::= { mbus37 20 }

mbus37Value07		OBJECT-TYPE
			SYNTAX	INTEGER
			ACCESS	read-only
			STATUS	current
	DESCRIPTION ""
			::= { mbus37 21 }

mbus37VIF08		OBJECT-TYPE
			SYNTAX	INTEGER
			ACCESS	read-only
			STATUS	current
	DESCRIPTION ""
			::= { mbus37 22 }

mbus37Value08		OBJECT-TYPE
			SYNTAX	INTEGER
			ACCESS	read-only
			STATUS	current
	DESCRIPTION ""
			::= { mbus37 23 }

mbus37VIF09		OBJECT-TYPE
			SYNTAX	INTEGER
			ACCESS	read-only
			STATUS	current
	DESCRIPTION ""
			::= { mbus37 24 }

mbus37Value09		OBJECT-TYPE
			SYNTAX	INTEGER
			ACCESS	read-only
			STATUS	current
	DESCRIPTION ""
			::= { mbus37 25 }

mbus37VIF0A		OBJECT-TYPE
			SYNTAX	INTEGER
			ACCESS	read-only
			STATUS	current
	DESCRIPTION ""
			::= { mbus37 26 }

mbus37Value0A		OBJECT-TYPE
			SYNTAX	INTEGER
			ACCESS	read-only
			STATUS	current
	DESCRIPTION ""
			::= { mbus37 27 }

mbus37VIF0B		OBJECT-TYPE
			SYNTAX	INTEGER
			ACCESS	read-only
			STATUS	current
	DESCRIPTION ""
			::= { mbus37 28 }

mbus37Value0B		OBJECT-TYPE
			SYNTAX	INTEGER
			ACCESS	read-only
			STATUS	current
	DESCRIPTION ""
			::= { mbus37 29 }

mbus37VIF0C		OBJECT-TYPE
			SYNTAX	INTEGER
			ACCESS	read-only
			STATUS	current
	DESCRIPTION ""
			::= { mbus37 30 }

mbus37Value0C		OBJECT-TYPE
			SYNTAX	INTEGER
			ACCESS	read-only
			STATUS	current
	DESCRIPTION ""
			::= { mbus37 31 }

mbus37VIF0D		OBJECT-TYPE
			SYNTAX	INTEGER
			ACCESS	read-only
			STATUS	current
	DESCRIPTION ""
			::= { mbus37 32 }

mbus37Value0D		OBJECT-TYPE
			SYNTAX	INTEGER
			ACCESS	read-only
			STATUS	current
	DESCRIPTION ""
			::= { mbus37 33 }

mbus37VIF0E		OBJECT-TYPE
			SYNTAX	INTEGER
			ACCESS	read-only
			STATUS	current
	DESCRIPTION ""
			::= { mbus37 34 }

mbus37Value0E		OBJECT-TYPE
			SYNTAX	INTEGER
			ACCESS	read-only
			STATUS	current
	DESCRIPTION ""
			::= { mbus37 35 }

mbus37VIF0F		OBJECT-TYPE
			SYNTAX	INTEGER
			ACCESS	read-only
			STATUS	current
	DESCRIPTION ""
			::= { mbus37 36 }

mbus37Value0F		OBJECT-TYPE
			SYNTAX	INTEGER
			ACCESS	read-only
			STATUS	current
	DESCRIPTION ""
			::= { mbus37 37 }

mbus37VIF10		OBJECT-TYPE
			SYNTAX	INTEGER
			ACCESS	read-only
			STATUS	current
	DESCRIPTION ""
			::= { mbus37 38 }

mbus37Value10		OBJECT-TYPE
			SYNTAX	INTEGER
			ACCESS	read-only
			STATUS	current
	DESCRIPTION ""
			::= { mbus37 39 }

mbus37VIF11		OBJECT-TYPE
			SYNTAX	INTEGER
			ACCESS	read-only
			STATUS	current
	DESCRIPTION ""
			::= { mbus37 40 }

mbus37Value11		OBJECT-TYPE
			SYNTAX	INTEGER
			ACCESS	read-only
			STATUS	current
	DESCRIPTION ""
			::= { mbus37 41 }

mbus37VIF12		OBJECT-TYPE
			SYNTAX	INTEGER
			ACCESS	read-only
			STATUS	current
	DESCRIPTION ""
			::= { mbus37 42 }

mbus37Value12		OBJECT-TYPE
			SYNTAX	INTEGER
			ACCESS	read-only
			STATUS	current
	DESCRIPTION ""
			::= { mbus37 43 }

mbus37VIF13		OBJECT-TYPE
			SYNTAX	INTEGER
			ACCESS	read-only
			STATUS	current
	DESCRIPTION ""
			::= { mbus37 44 }

mbus37Value13		OBJECT-TYPE
			SYNTAX	INTEGER
			ACCESS	read-only
			STATUS	current
	DESCRIPTION ""
			::= { mbus37 45 }

mbus37VIF14		OBJECT-TYPE
			SYNTAX	INTEGER
			ACCESS	read-only
			STATUS	current
	DESCRIPTION ""
			::= { mbus37 46 }

mbus37Value14		OBJECT-TYPE
			SYNTAX	INTEGER
			ACCESS	read-only
			STATUS	current
	DESCRIPTION ""
			::= { mbus37 47 }

mbus37VIF15		OBJECT-TYPE
			SYNTAX	INTEGER
			ACCESS	read-only
			STATUS	current
	DESCRIPTION ""
			::= { mbus37 48 }

mbus37Value15		OBJECT-TYPE
			SYNTAX	INTEGER
			ACCESS	read-only
			STATUS	current
	DESCRIPTION ""
			::= { mbus37 49 }

mbus37VIF16		OBJECT-TYPE
			SYNTAX	INTEGER
			ACCESS	read-only
			STATUS	current
	DESCRIPTION ""
			::= { mbus37 50 }

mbus37Value16		OBJECT-TYPE
			SYNTAX	INTEGER
			ACCESS	read-only
			STATUS	current
	DESCRIPTION ""
			::= { mbus37 51 }

mbus37VIF17		OBJECT-TYPE
			SYNTAX	INTEGER
			ACCESS	read-only
			STATUS	current
	DESCRIPTION ""
			::= { mbus37 52 }

mbus37Value17		OBJECT-TYPE
			SYNTAX	INTEGER
			ACCESS	read-only
			STATUS	current
	DESCRIPTION ""
			::= { mbus37 53 }

mbus37VIF18		OBJECT-TYPE
			SYNTAX	INTEGER
			ACCESS	read-only
			STATUS	current
	DESCRIPTION ""
			::= { mbus37 54 }

mbus37Value18		OBJECT-TYPE
			SYNTAX	INTEGER
			ACCESS	read-only
			STATUS	current
	DESCRIPTION ""
			::= { mbus37 55 }

mbus37VIF19		OBJECT-TYPE
			SYNTAX	INTEGER
			ACCESS	read-only
			STATUS	current
	DESCRIPTION ""
			::= { mbus37 56 }

mbus37Value19		OBJECT-TYPE
			SYNTAX	INTEGER
			ACCESS	read-only
			STATUS	current
	DESCRIPTION ""
			::= { mbus37 57 }

mbus37VIF1A		OBJECT-TYPE
			SYNTAX	INTEGER
			ACCESS	read-only
			STATUS	current
	DESCRIPTION ""
			::= { mbus37 58 }

mbus37Value1A		OBJECT-TYPE
			SYNTAX	INTEGER
			ACCESS	read-only
			STATUS	current
	DESCRIPTION ""
			::= { mbus37 59 }

mbus37VIF1B		OBJECT-TYPE
			SYNTAX	INTEGER
			ACCESS	read-only
			STATUS	current
	DESCRIPTION ""
			::= { mbus37 60 }

mbus37Value1B		OBJECT-TYPE
			SYNTAX	INTEGER
			ACCESS	read-only
			STATUS	current
	DESCRIPTION ""
			::= { mbus37 61 }

mbus37VIF1C		OBJECT-TYPE
			SYNTAX	INTEGER
			ACCESS	read-only
			STATUS	current
	DESCRIPTION ""
			::= { mbus37 62 }

mbus37Value1C		OBJECT-TYPE
			SYNTAX	INTEGER
			ACCESS	read-only
			STATUS	current
	DESCRIPTION ""
			::= { mbus37 63 }

mbus37VIF1D		OBJECT-TYPE
			SYNTAX	INTEGER
			ACCESS	read-only
			STATUS	current
	DESCRIPTION ""
			::= { mbus37 64 }

mbus37Value1D		OBJECT-TYPE
			SYNTAX	INTEGER
			ACCESS	read-only
			STATUS	current
	DESCRIPTION ""
			::= { mbus37 65 }

mbus37VIF1E		OBJECT-TYPE
			SYNTAX	INTEGER
			ACCESS	read-only
			STATUS	current
	DESCRIPTION ""
			::= { mbus37 66 }

mbus37Value1E		OBJECT-TYPE
			SYNTAX	INTEGER
			ACCESS	read-only
			STATUS	current
	DESCRIPTION ""
			::= { mbus37 67 }

mbus37VIF1F		OBJECT-TYPE
			SYNTAX	INTEGER
			ACCESS	read-only
			STATUS	current
	DESCRIPTION ""
			::= { mbus37 68 }

mbus37Value1F		OBJECT-TYPE
			SYNTAX	INTEGER
			ACCESS	read-only
			STATUS	current
	DESCRIPTION ""
			::= { mbus37 69 }

mbus37VIF20		OBJECT-TYPE
			SYNTAX	INTEGER
			ACCESS	read-only
			STATUS	current
	DESCRIPTION ""
			::= { mbus37 70 }

mbus37Value20		OBJECT-TYPE
			SYNTAX	INTEGER
			ACCESS	read-only
			STATUS	current
	DESCRIPTION ""
			::= { mbus37 71 }

mbus37VIF21		OBJECT-TYPE
			SYNTAX	INTEGER
			ACCESS	read-only
			STATUS	current
	DESCRIPTION ""
			::= { mbus37 72 }

mbus37Value21		OBJECT-TYPE
			SYNTAX	INTEGER
			ACCESS	read-only
			STATUS	current
	DESCRIPTION ""
			::= { mbus37 73 }

mbus37VIF22		OBJECT-TYPE
			SYNTAX	INTEGER
			ACCESS	read-only
			STATUS	current
	DESCRIPTION ""
			::= { mbus37 74 }

mbus37Value22		OBJECT-TYPE
			SYNTAX	INTEGER
			ACCESS	read-only
			STATUS	current
	DESCRIPTION ""
			::= { mbus37 75 }

mbus37VIF23		OBJECT-TYPE
			SYNTAX	INTEGER
			ACCESS	read-only
			STATUS	current
	DESCRIPTION ""
			::= { mbus37 76 }

mbus37Value23		OBJECT-TYPE
			SYNTAX	INTEGER
			ACCESS	read-only
			STATUS	current
	DESCRIPTION ""
			::= { mbus37 77 }

mbus37VIF24		OBJECT-TYPE
			SYNTAX	INTEGER
			ACCESS	read-only
			STATUS	current
	DESCRIPTION ""
			::= { mbus37 78 }

mbus37Value24		OBJECT-TYPE
			SYNTAX	INTEGER
			ACCESS	read-only
			STATUS	current
	DESCRIPTION ""
			::= { mbus37 79 }

mbus37VIF25		OBJECT-TYPE
			SYNTAX	INTEGER
			ACCESS	read-only
			STATUS	current
	DESCRIPTION ""
			::= { mbus37 80 }

mbus37Value25		OBJECT-TYPE
			SYNTAX	INTEGER
			ACCESS	read-only
			STATUS	current
	DESCRIPTION ""
			::= { mbus37 81 }

mbus37VIF26		OBJECT-TYPE
			SYNTAX	INTEGER
			ACCESS	read-only
			STATUS	current
	DESCRIPTION ""
			::= { mbus37 82 }

mbus37Value26		OBJECT-TYPE
			SYNTAX	INTEGER
			ACCESS	read-only
			STATUS	current
	DESCRIPTION ""
			::= { mbus37 83 }

mbus37VIF27		OBJECT-TYPE
			SYNTAX	INTEGER
			ACCESS	read-only
			STATUS	current
	DESCRIPTION ""
			::= { mbus37 84 }

mbus37Value27		OBJECT-TYPE
			SYNTAX	INTEGER
			ACCESS	read-only
			STATUS	current
	DESCRIPTION ""
			::= { mbus37 85 }

mbus37VIF28		OBJECT-TYPE
			SYNTAX	INTEGER
			ACCESS	read-only
			STATUS	current
	DESCRIPTION ""
			::= { mbus37 86 }

mbus37Value28		OBJECT-TYPE
			SYNTAX	INTEGER
			ACCESS	read-only
			STATUS	current
	DESCRIPTION ""
			::= { mbus37 87 }

mbus37VIF29		OBJECT-TYPE
			SYNTAX	INTEGER
			ACCESS	read-only
			STATUS	current
	DESCRIPTION ""
			::= { mbus37 88 }

mbus37Value29		OBJECT-TYPE
			SYNTAX	INTEGER
			ACCESS	read-only
			STATUS	current
	DESCRIPTION ""
			::= { mbus37 89 }

mbus37VIF2A		OBJECT-TYPE
			SYNTAX	INTEGER
			ACCESS	read-only
			STATUS	current
	DESCRIPTION ""
			::= { mbus37 90 }

mbus37Value2A		OBJECT-TYPE
			SYNTAX	INTEGER
			ACCESS	read-only
			STATUS	current
	DESCRIPTION ""
			::= { mbus37 91 }

mbus37VIF2B		OBJECT-TYPE
			SYNTAX	INTEGER
			ACCESS	read-only
			STATUS	current
	DESCRIPTION ""
			::= { mbus37 92 }

mbus37Value2B		OBJECT-TYPE
			SYNTAX	INTEGER
			ACCESS	read-only
			STATUS	current
	DESCRIPTION ""
			::= { mbus37 93 }

mbus37VIF2C		OBJECT-TYPE
			SYNTAX	INTEGER
			ACCESS	read-only
			STATUS	current
	DESCRIPTION ""
			::= { mbus37 94 }

mbus37Value2C		OBJECT-TYPE
			SYNTAX	INTEGER
			ACCESS	read-only
			STATUS	current
	DESCRIPTION ""
			::= { mbus37 95 }

mbus37VIF2D		OBJECT-TYPE
			SYNTAX	INTEGER
			ACCESS	read-only
			STATUS	current
	DESCRIPTION ""
			::= { mbus37 96 }

mbus37Value2D		OBJECT-TYPE
			SYNTAX	INTEGER
			ACCESS	read-only
			STATUS	current
	DESCRIPTION ""
			::= { mbus37 97 }

mbus37VIF2E		OBJECT-TYPE
			SYNTAX	INTEGER
			ACCESS	read-only
			STATUS	current
	DESCRIPTION ""
			::= { mbus37 98 }

mbus37Value2E		OBJECT-TYPE
			SYNTAX	INTEGER
			ACCESS	read-only
			STATUS	current
	DESCRIPTION ""
			::= { mbus37 99 }

mbus37VIF2F		OBJECT-TYPE
			SYNTAX	INTEGER
			ACCESS	read-only
			STATUS	current
	DESCRIPTION ""
			::= { mbus37 100 }

mbus37Value2F		OBJECT-TYPE
			SYNTAX	INTEGER
			ACCESS	read-only
			STATUS	current
	DESCRIPTION ""
			::= { mbus37 101 }

mbus38			OBJECT IDENTIFIER ::= { mbus 56 }

mbus38IdNumber		OBJECT-TYPE
			SYNTAX	Gauge
			ACCESS	read-only
			STATUS	current
	DESCRIPTION ""
			::= { mbus38 1 }

mbus38Manufacturer	OBJECT-TYPE
			SYNTAX	Gauge
			ACCESS	read-only
			STATUS	current
	DESCRIPTION ""
			::= { mbus38 2 }

mbus38Version		OBJECT-TYPE
			SYNTAX	Gauge
			ACCESS	read-only
			STATUS	current
	DESCRIPTION ""
			::= { mbus38 3 }

mbus38Medium		OBJECT-TYPE
			SYNTAX	Gauge
			ACCESS	read-only
			STATUS	current
	DESCRIPTION ""
			::= { mbus38 4 }

mbus38Status		OBJECT-TYPE
			SYNTAX	Gauge
			ACCESS	read-only
			STATUS	current
	DESCRIPTION ""
			::= { mbus38 5 }

mbus38VIF00		OBJECT-TYPE
			SYNTAX	INTEGER
			ACCESS	read-only
			STATUS	current
	DESCRIPTION ""
			::= { mbus38 6 }

mbus38Value00		OBJECT-TYPE
			SYNTAX	INTEGER
			ACCESS	read-only
			STATUS	current
	DESCRIPTION ""
			::= { mbus38 7 }

mbus38VIF01		OBJECT-TYPE
			SYNTAX	INTEGER
			ACCESS	read-only
			STATUS	current
	DESCRIPTION ""
			::= { mbus38 8 }

mbus38Value01		OBJECT-TYPE
			SYNTAX	INTEGER
			ACCESS	read-only
			STATUS	current
	DESCRIPTION ""
			::= { mbus38 9 }

mbus38VIF02		OBJECT-TYPE
			SYNTAX	INTEGER
			ACCESS	read-only
			STATUS	current
	DESCRIPTION ""
			::= { mbus38 10 }

mbus38Value02		OBJECT-TYPE
			SYNTAX	INTEGER
			ACCESS	read-only
			STATUS	current
	DESCRIPTION ""
			::= { mbus38 11 }

mbus38VIF03		OBJECT-TYPE
			SYNTAX	INTEGER
			ACCESS	read-only
			STATUS	current
	DESCRIPTION ""
			::= { mbus38 12 }

mbus38Value03		OBJECT-TYPE
			SYNTAX	INTEGER
			ACCESS	read-only
			STATUS	current
	DESCRIPTION ""
			::= { mbus38 13 }

mbus38VIF04		OBJECT-TYPE
			SYNTAX	INTEGER
			ACCESS	read-only
			STATUS	current
	DESCRIPTION ""
			::= { mbus38 14 }

mbus38Value04		OBJECT-TYPE
			SYNTAX	INTEGER
			ACCESS	read-only
			STATUS	current
	DESCRIPTION ""
			::= { mbus38 15 }

mbus38VIF05		OBJECT-TYPE
			SYNTAX	INTEGER
			ACCESS	read-only
			STATUS	current
	DESCRIPTION ""
			::= { mbus38 16 }

mbus38Value05		OBJECT-TYPE
			SYNTAX	INTEGER
			ACCESS	read-only
			STATUS	current
	DESCRIPTION ""
			::= { mbus38 17 }

mbus38VIF06		OBJECT-TYPE
			SYNTAX	INTEGER
			ACCESS	read-only
			STATUS	current
	DESCRIPTION ""
			::= { mbus38 18 }

mbus38Value06		OBJECT-TYPE
			SYNTAX	INTEGER
			ACCESS	read-only
			STATUS	current
	DESCRIPTION ""
			::= { mbus38 19 }

mbus38VIF07		OBJECT-TYPE
			SYNTAX	INTEGER
			ACCESS	read-only
			STATUS	current
	DESCRIPTION ""
			::= { mbus38 20 }

mbus38Value07		OBJECT-TYPE
			SYNTAX	INTEGER
			ACCESS	read-only
			STATUS	current
	DESCRIPTION ""
			::= { mbus38 21 }

mbus38VIF08		OBJECT-TYPE
			SYNTAX	INTEGER
			ACCESS	read-only
			STATUS	current
	DESCRIPTION ""
			::= { mbus38 22 }

mbus38Value08		OBJECT-TYPE
			SYNTAX	INTEGER
			ACCESS	read-only
			STATUS	current
	DESCRIPTION ""
			::= { mbus38 23 }

mbus38VIF09		OBJECT-TYPE
			SYNTAX	INTEGER
			ACCESS	read-only
			STATUS	current
	DESCRIPTION ""
			::= { mbus38 24 }

mbus38Value09		OBJECT-TYPE
			SYNTAX	INTEGER
			ACCESS	read-only
			STATUS	current
	DESCRIPTION ""
			::= { mbus38 25 }

mbus38VIF0A		OBJECT-TYPE
			SYNTAX	INTEGER
			ACCESS	read-only
			STATUS	current
	DESCRIPTION ""
			::= { mbus38 26 }

mbus38Value0A		OBJECT-TYPE
			SYNTAX	INTEGER
			ACCESS	read-only
			STATUS	current
	DESCRIPTION ""
			::= { mbus38 27 }

mbus38VIF0B		OBJECT-TYPE
			SYNTAX	INTEGER
			ACCESS	read-only
			STATUS	current
	DESCRIPTION ""
			::= { mbus38 28 }

mbus38Value0B		OBJECT-TYPE
			SYNTAX	INTEGER
			ACCESS	read-only
			STATUS	current
	DESCRIPTION ""
			::= { mbus38 29 }

mbus38VIF0C		OBJECT-TYPE
			SYNTAX	INTEGER
			ACCESS	read-only
			STATUS	current
	DESCRIPTION ""
			::= { mbus38 30 }

mbus38Value0C		OBJECT-TYPE
			SYNTAX	INTEGER
			ACCESS	read-only
			STATUS	current
	DESCRIPTION ""
			::= { mbus38 31 }

mbus38VIF0D		OBJECT-TYPE
			SYNTAX	INTEGER
			ACCESS	read-only
			STATUS	current
	DESCRIPTION ""
			::= { mbus38 32 }

mbus38Value0D		OBJECT-TYPE
			SYNTAX	INTEGER
			ACCESS	read-only
			STATUS	current
	DESCRIPTION ""
			::= { mbus38 33 }

mbus38VIF0E		OBJECT-TYPE
			SYNTAX	INTEGER
			ACCESS	read-only
			STATUS	current
	DESCRIPTION ""
			::= { mbus38 34 }

mbus38Value0E		OBJECT-TYPE
			SYNTAX	INTEGER
			ACCESS	read-only
			STATUS	current
	DESCRIPTION ""
			::= { mbus38 35 }

mbus38VIF0F		OBJECT-TYPE
			SYNTAX	INTEGER
			ACCESS	read-only
			STATUS	current
	DESCRIPTION ""
			::= { mbus38 36 }

mbus38Value0F		OBJECT-TYPE
			SYNTAX	INTEGER
			ACCESS	read-only
			STATUS	current
	DESCRIPTION ""
			::= { mbus38 37 }

mbus38VIF10		OBJECT-TYPE
			SYNTAX	INTEGER
			ACCESS	read-only
			STATUS	current
	DESCRIPTION ""
			::= { mbus38 38 }

mbus38Value10		OBJECT-TYPE
			SYNTAX	INTEGER
			ACCESS	read-only
			STATUS	current
	DESCRIPTION ""
			::= { mbus38 39 }

mbus38VIF11		OBJECT-TYPE
			SYNTAX	INTEGER
			ACCESS	read-only
			STATUS	current
	DESCRIPTION ""
			::= { mbus38 40 }

mbus38Value11		OBJECT-TYPE
			SYNTAX	INTEGER
			ACCESS	read-only
			STATUS	current
	DESCRIPTION ""
			::= { mbus38 41 }

mbus38VIF12		OBJECT-TYPE
			SYNTAX	INTEGER
			ACCESS	read-only
			STATUS	current
	DESCRIPTION ""
			::= { mbus38 42 }

mbus38Value12		OBJECT-TYPE
			SYNTAX	INTEGER
			ACCESS	read-only
			STATUS	current
	DESCRIPTION ""
			::= { mbus38 43 }

mbus38VIF13		OBJECT-TYPE
			SYNTAX	INTEGER
			ACCESS	read-only
			STATUS	current
	DESCRIPTION ""
			::= { mbus38 44 }

mbus38Value13		OBJECT-TYPE
			SYNTAX	INTEGER
			ACCESS	read-only
			STATUS	current
	DESCRIPTION ""
			::= { mbus38 45 }

mbus38VIF14		OBJECT-TYPE
			SYNTAX	INTEGER
			ACCESS	read-only
			STATUS	current
	DESCRIPTION ""
			::= { mbus38 46 }

mbus38Value14		OBJECT-TYPE
			SYNTAX	INTEGER
			ACCESS	read-only
			STATUS	current
	DESCRIPTION ""
			::= { mbus38 47 }

mbus38VIF15		OBJECT-TYPE
			SYNTAX	INTEGER
			ACCESS	read-only
			STATUS	current
	DESCRIPTION ""
			::= { mbus38 48 }

mbus38Value15		OBJECT-TYPE
			SYNTAX	INTEGER
			ACCESS	read-only
			STATUS	current
	DESCRIPTION ""
			::= { mbus38 49 }

mbus38VIF16		OBJECT-TYPE
			SYNTAX	INTEGER
			ACCESS	read-only
			STATUS	current
	DESCRIPTION ""
			::= { mbus38 50 }

mbus38Value16		OBJECT-TYPE
			SYNTAX	INTEGER
			ACCESS	read-only
			STATUS	current
	DESCRIPTION ""
			::= { mbus38 51 }

mbus38VIF17		OBJECT-TYPE
			SYNTAX	INTEGER
			ACCESS	read-only
			STATUS	current
	DESCRIPTION ""
			::= { mbus38 52 }

mbus38Value17		OBJECT-TYPE
			SYNTAX	INTEGER
			ACCESS	read-only
			STATUS	current
	DESCRIPTION ""
			::= { mbus38 53 }

mbus38VIF18		OBJECT-TYPE
			SYNTAX	INTEGER
			ACCESS	read-only
			STATUS	current
	DESCRIPTION ""
			::= { mbus38 54 }

mbus38Value18		OBJECT-TYPE
			SYNTAX	INTEGER
			ACCESS	read-only
			STATUS	current
	DESCRIPTION ""
			::= { mbus38 55 }

mbus38VIF19		OBJECT-TYPE
			SYNTAX	INTEGER
			ACCESS	read-only
			STATUS	current
	DESCRIPTION ""
			::= { mbus38 56 }

mbus38Value19		OBJECT-TYPE
			SYNTAX	INTEGER
			ACCESS	read-only
			STATUS	current
	DESCRIPTION ""
			::= { mbus38 57 }

mbus38VIF1A		OBJECT-TYPE
			SYNTAX	INTEGER
			ACCESS	read-only
			STATUS	current
	DESCRIPTION ""
			::= { mbus38 58 }

mbus38Value1A		OBJECT-TYPE
			SYNTAX	INTEGER
			ACCESS	read-only
			STATUS	current
	DESCRIPTION ""
			::= { mbus38 59 }

mbus38VIF1B		OBJECT-TYPE
			SYNTAX	INTEGER
			ACCESS	read-only
			STATUS	current
	DESCRIPTION ""
			::= { mbus38 60 }

mbus38Value1B		OBJECT-TYPE
			SYNTAX	INTEGER
			ACCESS	read-only
			STATUS	current
	DESCRIPTION ""
			::= { mbus38 61 }

mbus38VIF1C		OBJECT-TYPE
			SYNTAX	INTEGER
			ACCESS	read-only
			STATUS	current
	DESCRIPTION ""
			::= { mbus38 62 }

mbus38Value1C		OBJECT-TYPE
			SYNTAX	INTEGER
			ACCESS	read-only
			STATUS	current
	DESCRIPTION ""
			::= { mbus38 63 }

mbus38VIF1D		OBJECT-TYPE
			SYNTAX	INTEGER
			ACCESS	read-only
			STATUS	current
	DESCRIPTION ""
			::= { mbus38 64 }

mbus38Value1D		OBJECT-TYPE
			SYNTAX	INTEGER
			ACCESS	read-only
			STATUS	current
	DESCRIPTION ""
			::= { mbus38 65 }

mbus38VIF1E		OBJECT-TYPE
			SYNTAX	INTEGER
			ACCESS	read-only
			STATUS	current
	DESCRIPTION ""
			::= { mbus38 66 }

mbus38Value1E		OBJECT-TYPE
			SYNTAX	INTEGER
			ACCESS	read-only
			STATUS	current
	DESCRIPTION ""
			::= { mbus38 67 }

mbus38VIF1F		OBJECT-TYPE
			SYNTAX	INTEGER
			ACCESS	read-only
			STATUS	current
	DESCRIPTION ""
			::= { mbus38 68 }

mbus38Value1F		OBJECT-TYPE
			SYNTAX	INTEGER
			ACCESS	read-only
			STATUS	current
	DESCRIPTION ""
			::= { mbus38 69 }

mbus38VIF20		OBJECT-TYPE
			SYNTAX	INTEGER
			ACCESS	read-only
			STATUS	current
	DESCRIPTION ""
			::= { mbus38 70 }

mbus38Value20		OBJECT-TYPE
			SYNTAX	INTEGER
			ACCESS	read-only
			STATUS	current
	DESCRIPTION ""
			::= { mbus38 71 }

mbus38VIF21		OBJECT-TYPE
			SYNTAX	INTEGER
			ACCESS	read-only
			STATUS	current
	DESCRIPTION ""
			::= { mbus38 72 }

mbus38Value21		OBJECT-TYPE
			SYNTAX	INTEGER
			ACCESS	read-only
			STATUS	current
	DESCRIPTION ""
			::= { mbus38 73 }

mbus38VIF22		OBJECT-TYPE
			SYNTAX	INTEGER
			ACCESS	read-only
			STATUS	current
	DESCRIPTION ""
			::= { mbus38 74 }

mbus38Value22		OBJECT-TYPE
			SYNTAX	INTEGER
			ACCESS	read-only
			STATUS	current
	DESCRIPTION ""
			::= { mbus38 75 }

mbus38VIF23		OBJECT-TYPE
			SYNTAX	INTEGER
			ACCESS	read-only
			STATUS	current
	DESCRIPTION ""
			::= { mbus38 76 }

mbus38Value23		OBJECT-TYPE
			SYNTAX	INTEGER
			ACCESS	read-only
			STATUS	current
	DESCRIPTION ""
			::= { mbus38 77 }

mbus38VIF24		OBJECT-TYPE
			SYNTAX	INTEGER
			ACCESS	read-only
			STATUS	current
	DESCRIPTION ""
			::= { mbus38 78 }

mbus38Value24		OBJECT-TYPE
			SYNTAX	INTEGER
			ACCESS	read-only
			STATUS	current
	DESCRIPTION ""
			::= { mbus38 79 }

mbus38VIF25		OBJECT-TYPE
			SYNTAX	INTEGER
			ACCESS	read-only
			STATUS	current
	DESCRIPTION ""
			::= { mbus38 80 }

mbus38Value25		OBJECT-TYPE
			SYNTAX	INTEGER
			ACCESS	read-only
			STATUS	current
	DESCRIPTION ""
			::= { mbus38 81 }

mbus38VIF26		OBJECT-TYPE
			SYNTAX	INTEGER
			ACCESS	read-only
			STATUS	current
	DESCRIPTION ""
			::= { mbus38 82 }

mbus38Value26		OBJECT-TYPE
			SYNTAX	INTEGER
			ACCESS	read-only
			STATUS	current
	DESCRIPTION ""
			::= { mbus38 83 }

mbus38VIF27		OBJECT-TYPE
			SYNTAX	INTEGER
			ACCESS	read-only
			STATUS	current
	DESCRIPTION ""
			::= { mbus38 84 }

mbus38Value27		OBJECT-TYPE
			SYNTAX	INTEGER
			ACCESS	read-only
			STATUS	current
	DESCRIPTION ""
			::= { mbus38 85 }

mbus38VIF28		OBJECT-TYPE
			SYNTAX	INTEGER
			ACCESS	read-only
			STATUS	current
	DESCRIPTION ""
			::= { mbus38 86 }

mbus38Value28		OBJECT-TYPE
			SYNTAX	INTEGER
			ACCESS	read-only
			STATUS	current
	DESCRIPTION ""
			::= { mbus38 87 }

mbus38VIF29		OBJECT-TYPE
			SYNTAX	INTEGER
			ACCESS	read-only
			STATUS	current
	DESCRIPTION ""
			::= { mbus38 88 }

mbus38Value29		OBJECT-TYPE
			SYNTAX	INTEGER
			ACCESS	read-only
			STATUS	current
	DESCRIPTION ""
			::= { mbus38 89 }

mbus38VIF2A		OBJECT-TYPE
			SYNTAX	INTEGER
			ACCESS	read-only
			STATUS	current
	DESCRIPTION ""
			::= { mbus38 90 }

mbus38Value2A		OBJECT-TYPE
			SYNTAX	INTEGER
			ACCESS	read-only
			STATUS	current
	DESCRIPTION ""
			::= { mbus38 91 }

mbus38VIF2B		OBJECT-TYPE
			SYNTAX	INTEGER
			ACCESS	read-only
			STATUS	current
	DESCRIPTION ""
			::= { mbus38 92 }

mbus38Value2B		OBJECT-TYPE
			SYNTAX	INTEGER
			ACCESS	read-only
			STATUS	current
	DESCRIPTION ""
			::= { mbus38 93 }

mbus38VIF2C		OBJECT-TYPE
			SYNTAX	INTEGER
			ACCESS	read-only
			STATUS	current
	DESCRIPTION ""
			::= { mbus38 94 }

mbus38Value2C		OBJECT-TYPE
			SYNTAX	INTEGER
			ACCESS	read-only
			STATUS	current
	DESCRIPTION ""
			::= { mbus38 95 }

mbus38VIF2D		OBJECT-TYPE
			SYNTAX	INTEGER
			ACCESS	read-only
			STATUS	current
	DESCRIPTION ""
			::= { mbus38 96 }

mbus38Value2D		OBJECT-TYPE
			SYNTAX	INTEGER
			ACCESS	read-only
			STATUS	current
	DESCRIPTION ""
			::= { mbus38 97 }

mbus38VIF2E		OBJECT-TYPE
			SYNTAX	INTEGER
			ACCESS	read-only
			STATUS	current
	DESCRIPTION ""
			::= { mbus38 98 }

mbus38Value2E		OBJECT-TYPE
			SYNTAX	INTEGER
			ACCESS	read-only
			STATUS	current
	DESCRIPTION ""
			::= { mbus38 99 }

mbus38VIF2F		OBJECT-TYPE
			SYNTAX	INTEGER
			ACCESS	read-only
			STATUS	current
	DESCRIPTION ""
			::= { mbus38 100 }

mbus38Value2F		OBJECT-TYPE
			SYNTAX	INTEGER
			ACCESS	read-only
			STATUS	current
	DESCRIPTION ""
			::= { mbus38 101 }

mbus39			OBJECT IDENTIFIER ::= { mbus 57 }

mbus39IdNumber		OBJECT-TYPE
			SYNTAX	Gauge
			ACCESS	read-only
			STATUS	current
	DESCRIPTION ""
			::= { mbus39 1 }

mbus39Manufacturer	OBJECT-TYPE
			SYNTAX	Gauge
			ACCESS	read-only
			STATUS	current
	DESCRIPTION ""
			::= { mbus39 2 }

mbus39Version		OBJECT-TYPE
			SYNTAX	Gauge
			ACCESS	read-only
			STATUS	current
	DESCRIPTION ""
			::= { mbus39 3 }

mbus39Medium		OBJECT-TYPE
			SYNTAX	Gauge
			ACCESS	read-only
			STATUS	current
	DESCRIPTION ""
			::= { mbus39 4 }

mbus39Status		OBJECT-TYPE
			SYNTAX	Gauge
			ACCESS	read-only
			STATUS	current
	DESCRIPTION ""
			::= { mbus39 5 }

mbus39VIF00		OBJECT-TYPE
			SYNTAX	INTEGER
			ACCESS	read-only
			STATUS	current
	DESCRIPTION ""
			::= { mbus39 6 }

mbus39Value00		OBJECT-TYPE
			SYNTAX	INTEGER
			ACCESS	read-only
			STATUS	current
	DESCRIPTION ""
			::= { mbus39 7 }

mbus39VIF01		OBJECT-TYPE
			SYNTAX	INTEGER
			ACCESS	read-only
			STATUS	current
	DESCRIPTION ""
			::= { mbus39 8 }

mbus39Value01		OBJECT-TYPE
			SYNTAX	INTEGER
			ACCESS	read-only
			STATUS	current
	DESCRIPTION ""
			::= { mbus39 9 }

mbus39VIF02		OBJECT-TYPE
			SYNTAX	INTEGER
			ACCESS	read-only
			STATUS	current
	DESCRIPTION ""
			::= { mbus39 10 }

mbus39Value02		OBJECT-TYPE
			SYNTAX	INTEGER
			ACCESS	read-only
			STATUS	current
	DESCRIPTION ""
			::= { mbus39 11 }

mbus39VIF03		OBJECT-TYPE
			SYNTAX	INTEGER
			ACCESS	read-only
			STATUS	current
	DESCRIPTION ""
			::= { mbus39 12 }

mbus39Value03		OBJECT-TYPE
			SYNTAX	INTEGER
			ACCESS	read-only
			STATUS	current
	DESCRIPTION ""
			::= { mbus39 13 }

mbus39VIF04		OBJECT-TYPE
			SYNTAX	INTEGER
			ACCESS	read-only
			STATUS	current
	DESCRIPTION ""
			::= { mbus39 14 }

mbus39Value04		OBJECT-TYPE
			SYNTAX	INTEGER
			ACCESS	read-only
			STATUS	current
	DESCRIPTION ""
			::= { mbus39 15 }

mbus39VIF05		OBJECT-TYPE
			SYNTAX	INTEGER
			ACCESS	read-only
			STATUS	current
	DESCRIPTION ""
			::= { mbus39 16 }

mbus39Value05		OBJECT-TYPE
			SYNTAX	INTEGER
			ACCESS	read-only
			STATUS	current
	DESCRIPTION ""
			::= { mbus39 17 }

mbus39VIF06		OBJECT-TYPE
			SYNTAX	INTEGER
			ACCESS	read-only
			STATUS	current
	DESCRIPTION ""
			::= { mbus39 18 }

mbus39Value06		OBJECT-TYPE
			SYNTAX	INTEGER
			ACCESS	read-only
			STATUS	current
	DESCRIPTION ""
			::= { mbus39 19 }

mbus39VIF07		OBJECT-TYPE
			SYNTAX	INTEGER
			ACCESS	read-only
			STATUS	current
	DESCRIPTION ""
			::= { mbus39 20 }

mbus39Value07		OBJECT-TYPE
			SYNTAX	INTEGER
			ACCESS	read-only
			STATUS	current
	DESCRIPTION ""
			::= { mbus39 21 }

mbus39VIF08		OBJECT-TYPE
			SYNTAX	INTEGER
			ACCESS	read-only
			STATUS	current
	DESCRIPTION ""
			::= { mbus39 22 }

mbus39Value08		OBJECT-TYPE
			SYNTAX	INTEGER
			ACCESS	read-only
			STATUS	current
	DESCRIPTION ""
			::= { mbus39 23 }

mbus39VIF09		OBJECT-TYPE
			SYNTAX	INTEGER
			ACCESS	read-only
			STATUS	current
	DESCRIPTION ""
			::= { mbus39 24 }

mbus39Value09		OBJECT-TYPE
			SYNTAX	INTEGER
			ACCESS	read-only
			STATUS	current
	DESCRIPTION ""
			::= { mbus39 25 }

mbus39VIF0A		OBJECT-TYPE
			SYNTAX	INTEGER
			ACCESS	read-only
			STATUS	current
	DESCRIPTION ""
			::= { mbus39 26 }

mbus39Value0A		OBJECT-TYPE
			SYNTAX	INTEGER
			ACCESS	read-only
			STATUS	current
	DESCRIPTION ""
			::= { mbus39 27 }

mbus39VIF0B		OBJECT-TYPE
			SYNTAX	INTEGER
			ACCESS	read-only
			STATUS	current
	DESCRIPTION ""
			::= { mbus39 28 }

mbus39Value0B		OBJECT-TYPE
			SYNTAX	INTEGER
			ACCESS	read-only
			STATUS	current
	DESCRIPTION ""
			::= { mbus39 29 }

mbus39VIF0C		OBJECT-TYPE
			SYNTAX	INTEGER
			ACCESS	read-only
			STATUS	current
	DESCRIPTION ""
			::= { mbus39 30 }

mbus39Value0C		OBJECT-TYPE
			SYNTAX	INTEGER
			ACCESS	read-only
			STATUS	current
	DESCRIPTION ""
			::= { mbus39 31 }

mbus39VIF0D		OBJECT-TYPE
			SYNTAX	INTEGER
			ACCESS	read-only
			STATUS	current
	DESCRIPTION ""
			::= { mbus39 32 }

mbus39Value0D		OBJECT-TYPE
			SYNTAX	INTEGER
			ACCESS	read-only
			STATUS	current
	DESCRIPTION ""
			::= { mbus39 33 }

mbus39VIF0E		OBJECT-TYPE
			SYNTAX	INTEGER
			ACCESS	read-only
			STATUS	current
	DESCRIPTION ""
			::= { mbus39 34 }

mbus39Value0E		OBJECT-TYPE
			SYNTAX	INTEGER
			ACCESS	read-only
			STATUS	current
	DESCRIPTION ""
			::= { mbus39 35 }

mbus39VIF0F		OBJECT-TYPE
			SYNTAX	INTEGER
			ACCESS	read-only
			STATUS	current
	DESCRIPTION ""
			::= { mbus39 36 }

mbus39Value0F		OBJECT-TYPE
			SYNTAX	INTEGER
			ACCESS	read-only
			STATUS	current
	DESCRIPTION ""
			::= { mbus39 37 }

mbus39VIF10		OBJECT-TYPE
			SYNTAX	INTEGER
			ACCESS	read-only
			STATUS	current
	DESCRIPTION ""
			::= { mbus39 38 }

mbus39Value10		OBJECT-TYPE
			SYNTAX	INTEGER
			ACCESS	read-only
			STATUS	current
	DESCRIPTION ""
			::= { mbus39 39 }

mbus39VIF11		OBJECT-TYPE
			SYNTAX	INTEGER
			ACCESS	read-only
			STATUS	current
	DESCRIPTION ""
			::= { mbus39 40 }

mbus39Value11		OBJECT-TYPE
			SYNTAX	INTEGER
			ACCESS	read-only
			STATUS	current
	DESCRIPTION ""
			::= { mbus39 41 }

mbus39VIF12		OBJECT-TYPE
			SYNTAX	INTEGER
			ACCESS	read-only
			STATUS	current
	DESCRIPTION ""
			::= { mbus39 42 }

mbus39Value12		OBJECT-TYPE
			SYNTAX	INTEGER
			ACCESS	read-only
			STATUS	current
	DESCRIPTION ""
			::= { mbus39 43 }

mbus39VIF13		OBJECT-TYPE
			SYNTAX	INTEGER
			ACCESS	read-only
			STATUS	current
	DESCRIPTION ""
			::= { mbus39 44 }

mbus39Value13		OBJECT-TYPE
			SYNTAX	INTEGER
			ACCESS	read-only
			STATUS	current
	DESCRIPTION ""
			::= { mbus39 45 }

mbus39VIF14		OBJECT-TYPE
			SYNTAX	INTEGER
			ACCESS	read-only
			STATUS	current
	DESCRIPTION ""
			::= { mbus39 46 }

mbus39Value14		OBJECT-TYPE
			SYNTAX	INTEGER
			ACCESS	read-only
			STATUS	current
	DESCRIPTION ""
			::= { mbus39 47 }

mbus39VIF15		OBJECT-TYPE
			SYNTAX	INTEGER
			ACCESS	read-only
			STATUS	current
	DESCRIPTION ""
			::= { mbus39 48 }

mbus39Value15		OBJECT-TYPE
			SYNTAX	INTEGER
			ACCESS	read-only
			STATUS	current
	DESCRIPTION ""
			::= { mbus39 49 }

mbus39VIF16		OBJECT-TYPE
			SYNTAX	INTEGER
			ACCESS	read-only
			STATUS	current
	DESCRIPTION ""
			::= { mbus39 50 }

mbus39Value16		OBJECT-TYPE
			SYNTAX	INTEGER
			ACCESS	read-only
			STATUS	current
	DESCRIPTION ""
			::= { mbus39 51 }

mbus39VIF17		OBJECT-TYPE
			SYNTAX	INTEGER
			ACCESS	read-only
			STATUS	current
	DESCRIPTION ""
			::= { mbus39 52 }

mbus39Value17		OBJECT-TYPE
			SYNTAX	INTEGER
			ACCESS	read-only
			STATUS	current
	DESCRIPTION ""
			::= { mbus39 53 }

mbus39VIF18		OBJECT-TYPE
			SYNTAX	INTEGER
			ACCESS	read-only
			STATUS	current
	DESCRIPTION ""
			::= { mbus39 54 }

mbus39Value18		OBJECT-TYPE
			SYNTAX	INTEGER
			ACCESS	read-only
			STATUS	current
	DESCRIPTION ""
			::= { mbus39 55 }

mbus39VIF19		OBJECT-TYPE
			SYNTAX	INTEGER
			ACCESS	read-only
			STATUS	current
	DESCRIPTION ""
			::= { mbus39 56 }

mbus39Value19		OBJECT-TYPE
			SYNTAX	INTEGER
			ACCESS	read-only
			STATUS	current
	DESCRIPTION ""
			::= { mbus39 57 }

mbus39VIF1A		OBJECT-TYPE
			SYNTAX	INTEGER
			ACCESS	read-only
			STATUS	current
	DESCRIPTION ""
			::= { mbus39 58 }

mbus39Value1A		OBJECT-TYPE
			SYNTAX	INTEGER
			ACCESS	read-only
			STATUS	current
	DESCRIPTION ""
			::= { mbus39 59 }

mbus39VIF1B		OBJECT-TYPE
			SYNTAX	INTEGER
			ACCESS	read-only
			STATUS	current
	DESCRIPTION ""
			::= { mbus39 60 }

mbus39Value1B		OBJECT-TYPE
			SYNTAX	INTEGER
			ACCESS	read-only
			STATUS	current
	DESCRIPTION ""
			::= { mbus39 61 }

mbus39VIF1C		OBJECT-TYPE
			SYNTAX	INTEGER
			ACCESS	read-only
			STATUS	current
	DESCRIPTION ""
			::= { mbus39 62 }

mbus39Value1C		OBJECT-TYPE
			SYNTAX	INTEGER
			ACCESS	read-only
			STATUS	current
	DESCRIPTION ""
			::= { mbus39 63 }

mbus39VIF1D		OBJECT-TYPE
			SYNTAX	INTEGER
			ACCESS	read-only
			STATUS	current
	DESCRIPTION ""
			::= { mbus39 64 }

mbus39Value1D		OBJECT-TYPE
			SYNTAX	INTEGER
			ACCESS	read-only
			STATUS	current
	DESCRIPTION ""
			::= { mbus39 65 }

mbus39VIF1E		OBJECT-TYPE
			SYNTAX	INTEGER
			ACCESS	read-only
			STATUS	current
	DESCRIPTION ""
			::= { mbus39 66 }

mbus39Value1E		OBJECT-TYPE
			SYNTAX	INTEGER
			ACCESS	read-only
			STATUS	current
	DESCRIPTION ""
			::= { mbus39 67 }

mbus39VIF1F		OBJECT-TYPE
			SYNTAX	INTEGER
			ACCESS	read-only
			STATUS	current
	DESCRIPTION ""
			::= { mbus39 68 }

mbus39Value1F		OBJECT-TYPE
			SYNTAX	INTEGER
			ACCESS	read-only
			STATUS	current
	DESCRIPTION ""
			::= { mbus39 69 }

mbus39VIF20		OBJECT-TYPE
			SYNTAX	INTEGER
			ACCESS	read-only
			STATUS	current
	DESCRIPTION ""
			::= { mbus39 70 }

mbus39Value20		OBJECT-TYPE
			SYNTAX	INTEGER
			ACCESS	read-only
			STATUS	current
	DESCRIPTION ""
			::= { mbus39 71 }

mbus39VIF21		OBJECT-TYPE
			SYNTAX	INTEGER
			ACCESS	read-only
			STATUS	current
	DESCRIPTION ""
			::= { mbus39 72 }

mbus39Value21		OBJECT-TYPE
			SYNTAX	INTEGER
			ACCESS	read-only
			STATUS	current
	DESCRIPTION ""
			::= { mbus39 73 }

mbus39VIF22		OBJECT-TYPE
			SYNTAX	INTEGER
			ACCESS	read-only
			STATUS	current
	DESCRIPTION ""
			::= { mbus39 74 }

mbus39Value22		OBJECT-TYPE
			SYNTAX	INTEGER
			ACCESS	read-only
			STATUS	current
	DESCRIPTION ""
			::= { mbus39 75 }

mbus39VIF23		OBJECT-TYPE
			SYNTAX	INTEGER
			ACCESS	read-only
			STATUS	current
	DESCRIPTION ""
			::= { mbus39 76 }

mbus39Value23		OBJECT-TYPE
			SYNTAX	INTEGER
			ACCESS	read-only
			STATUS	current
	DESCRIPTION ""
			::= { mbus39 77 }

mbus39VIF24		OBJECT-TYPE
			SYNTAX	INTEGER
			ACCESS	read-only
			STATUS	current
	DESCRIPTION ""
			::= { mbus39 78 }

mbus39Value24		OBJECT-TYPE
			SYNTAX	INTEGER
			ACCESS	read-only
			STATUS	current
	DESCRIPTION ""
			::= { mbus39 79 }

mbus39VIF25		OBJECT-TYPE
			SYNTAX	INTEGER
			ACCESS	read-only
			STATUS	current
	DESCRIPTION ""
			::= { mbus39 80 }

mbus39Value25		OBJECT-TYPE
			SYNTAX	INTEGER
			ACCESS	read-only
			STATUS	current
	DESCRIPTION ""
			::= { mbus39 81 }

mbus39VIF26		OBJECT-TYPE
			SYNTAX	INTEGER
			ACCESS	read-only
			STATUS	current
	DESCRIPTION ""
			::= { mbus39 82 }

mbus39Value26		OBJECT-TYPE
			SYNTAX	INTEGER
			ACCESS	read-only
			STATUS	current
	DESCRIPTION ""
			::= { mbus39 83 }

mbus39VIF27		OBJECT-TYPE
			SYNTAX	INTEGER
			ACCESS	read-only
			STATUS	current
	DESCRIPTION ""
			::= { mbus39 84 }

mbus39Value27		OBJECT-TYPE
			SYNTAX	INTEGER
			ACCESS	read-only
			STATUS	current
	DESCRIPTION ""
			::= { mbus39 85 }

mbus39VIF28		OBJECT-TYPE
			SYNTAX	INTEGER
			ACCESS	read-only
			STATUS	current
	DESCRIPTION ""
			::= { mbus39 86 }

mbus39Value28		OBJECT-TYPE
			SYNTAX	INTEGER
			ACCESS	read-only
			STATUS	current
	DESCRIPTION ""
			::= { mbus39 87 }

mbus39VIF29		OBJECT-TYPE
			SYNTAX	INTEGER
			ACCESS	read-only
			STATUS	current
	DESCRIPTION ""
			::= { mbus39 88 }

mbus39Value29		OBJECT-TYPE
			SYNTAX	INTEGER
			ACCESS	read-only
			STATUS	current
	DESCRIPTION ""
			::= { mbus39 89 }

mbus39VIF2A		OBJECT-TYPE
			SYNTAX	INTEGER
			ACCESS	read-only
			STATUS	current
	DESCRIPTION ""
			::= { mbus39 90 }

mbus39Value2A		OBJECT-TYPE
			SYNTAX	INTEGER
			ACCESS	read-only
			STATUS	current
	DESCRIPTION ""
			::= { mbus39 91 }

mbus39VIF2B		OBJECT-TYPE
			SYNTAX	INTEGER
			ACCESS	read-only
			STATUS	current
	DESCRIPTION ""
			::= { mbus39 92 }

mbus39Value2B		OBJECT-TYPE
			SYNTAX	INTEGER
			ACCESS	read-only
			STATUS	current
	DESCRIPTION ""
			::= { mbus39 93 }

mbus39VIF2C		OBJECT-TYPE
			SYNTAX	INTEGER
			ACCESS	read-only
			STATUS	current
	DESCRIPTION ""
			::= { mbus39 94 }

mbus39Value2C		OBJECT-TYPE
			SYNTAX	INTEGER
			ACCESS	read-only
			STATUS	current
	DESCRIPTION ""
			::= { mbus39 95 }

mbus39VIF2D		OBJECT-TYPE
			SYNTAX	INTEGER
			ACCESS	read-only
			STATUS	current
	DESCRIPTION ""
			::= { mbus39 96 }

mbus39Value2D		OBJECT-TYPE
			SYNTAX	INTEGER
			ACCESS	read-only
			STATUS	current
	DESCRIPTION ""
			::= { mbus39 97 }

mbus39VIF2E		OBJECT-TYPE
			SYNTAX	INTEGER
			ACCESS	read-only
			STATUS	current
	DESCRIPTION ""
			::= { mbus39 98 }

mbus39Value2E		OBJECT-TYPE
			SYNTAX	INTEGER
			ACCESS	read-only
			STATUS	current
	DESCRIPTION ""
			::= { mbus39 99 }

mbus39VIF2F		OBJECT-TYPE
			SYNTAX	INTEGER
			ACCESS	read-only
			STATUS	current
	DESCRIPTION ""
			::= { mbus39 100 }

mbus39Value2F		OBJECT-TYPE
			SYNTAX	INTEGER
			ACCESS	read-only
			STATUS	current
	DESCRIPTION ""
			::= { mbus39 101 }

mbus3A			OBJECT IDENTIFIER ::= { mbus 58 }

mbus3AIdNumber		OBJECT-TYPE
			SYNTAX	Gauge
			ACCESS	read-only
			STATUS	current
	DESCRIPTION ""
			::= { mbus3A 1 }

mbus3AManufacturer	OBJECT-TYPE
			SYNTAX	Gauge
			ACCESS	read-only
			STATUS	current
	DESCRIPTION ""
			::= { mbus3A 2 }

mbus3AVersion		OBJECT-TYPE
			SYNTAX	Gauge
			ACCESS	read-only
			STATUS	current
	DESCRIPTION ""
			::= { mbus3A 3 }

mbus3AMedium		OBJECT-TYPE
			SYNTAX	Gauge
			ACCESS	read-only
			STATUS	current
	DESCRIPTION ""
			::= { mbus3A 4 }

mbus3AStatus		OBJECT-TYPE
			SYNTAX	Gauge
			ACCESS	read-only
			STATUS	current
	DESCRIPTION ""
			::= { mbus3A 5 }

mbus3AVIF00		OBJECT-TYPE
			SYNTAX	INTEGER
			ACCESS	read-only
			STATUS	current
	DESCRIPTION ""
			::= { mbus3A 6 }

mbus3AValue00		OBJECT-TYPE
			SYNTAX	INTEGER
			ACCESS	read-only
			STATUS	current
	DESCRIPTION ""
			::= { mbus3A 7 }

mbus3AVIF01		OBJECT-TYPE
			SYNTAX	INTEGER
			ACCESS	read-only
			STATUS	current
	DESCRIPTION ""
			::= { mbus3A 8 }

mbus3AValue01		OBJECT-TYPE
			SYNTAX	INTEGER
			ACCESS	read-only
			STATUS	current
	DESCRIPTION ""
			::= { mbus3A 9 }

mbus3AVIF02		OBJECT-TYPE
			SYNTAX	INTEGER
			ACCESS	read-only
			STATUS	current
	DESCRIPTION ""
			::= { mbus3A 10 }

mbus3AValue02		OBJECT-TYPE
			SYNTAX	INTEGER
			ACCESS	read-only
			STATUS	current
	DESCRIPTION ""
			::= { mbus3A 11 }

mbus3AVIF03		OBJECT-TYPE
			SYNTAX	INTEGER
			ACCESS	read-only
			STATUS	current
	DESCRIPTION ""
			::= { mbus3A 12 }

mbus3AValue03		OBJECT-TYPE
			SYNTAX	INTEGER
			ACCESS	read-only
			STATUS	current
	DESCRIPTION ""
			::= { mbus3A 13 }

mbus3AVIF04		OBJECT-TYPE
			SYNTAX	INTEGER
			ACCESS	read-only
			STATUS	current
	DESCRIPTION ""
			::= { mbus3A 14 }

mbus3AValue04		OBJECT-TYPE
			SYNTAX	INTEGER
			ACCESS	read-only
			STATUS	current
	DESCRIPTION ""
			::= { mbus3A 15 }

mbus3AVIF05		OBJECT-TYPE
			SYNTAX	INTEGER
			ACCESS	read-only
			STATUS	current
	DESCRIPTION ""
			::= { mbus3A 16 }

mbus3AValue05		OBJECT-TYPE
			SYNTAX	INTEGER
			ACCESS	read-only
			STATUS	current
	DESCRIPTION ""
			::= { mbus3A 17 }

mbus3AVIF06		OBJECT-TYPE
			SYNTAX	INTEGER
			ACCESS	read-only
			STATUS	current
	DESCRIPTION ""
			::= { mbus3A 18 }

mbus3AValue06		OBJECT-TYPE
			SYNTAX	INTEGER
			ACCESS	read-only
			STATUS	current
	DESCRIPTION ""
			::= { mbus3A 19 }

mbus3AVIF07		OBJECT-TYPE
			SYNTAX	INTEGER
			ACCESS	read-only
			STATUS	current
	DESCRIPTION ""
			::= { mbus3A 20 }

mbus3AValue07		OBJECT-TYPE
			SYNTAX	INTEGER
			ACCESS	read-only
			STATUS	current
	DESCRIPTION ""
			::= { mbus3A 21 }

mbus3AVIF08		OBJECT-TYPE
			SYNTAX	INTEGER
			ACCESS	read-only
			STATUS	current
	DESCRIPTION ""
			::= { mbus3A 22 }

mbus3AValue08		OBJECT-TYPE
			SYNTAX	INTEGER
			ACCESS	read-only
			STATUS	current
	DESCRIPTION ""
			::= { mbus3A 23 }

mbus3AVIF09		OBJECT-TYPE
			SYNTAX	INTEGER
			ACCESS	read-only
			STATUS	current
	DESCRIPTION ""
			::= { mbus3A 24 }

mbus3AValue09		OBJECT-TYPE
			SYNTAX	INTEGER
			ACCESS	read-only
			STATUS	current
	DESCRIPTION ""
			::= { mbus3A 25 }

mbus3AVIF0A		OBJECT-TYPE
			SYNTAX	INTEGER
			ACCESS	read-only
			STATUS	current
	DESCRIPTION ""
			::= { mbus3A 26 }

mbus3AValue0A		OBJECT-TYPE
			SYNTAX	INTEGER
			ACCESS	read-only
			STATUS	current
	DESCRIPTION ""
			::= { mbus3A 27 }

mbus3AVIF0B		OBJECT-TYPE
			SYNTAX	INTEGER
			ACCESS	read-only
			STATUS	current
	DESCRIPTION ""
			::= { mbus3A 28 }

mbus3AValue0B		OBJECT-TYPE
			SYNTAX	INTEGER
			ACCESS	read-only
			STATUS	current
	DESCRIPTION ""
			::= { mbus3A 29 }

mbus3AVIF0C		OBJECT-TYPE
			SYNTAX	INTEGER
			ACCESS	read-only
			STATUS	current
	DESCRIPTION ""
			::= { mbus3A 30 }

mbus3AValue0C		OBJECT-TYPE
			SYNTAX	INTEGER
			ACCESS	read-only
			STATUS	current
	DESCRIPTION ""
			::= { mbus3A 31 }

mbus3AVIF0D		OBJECT-TYPE
			SYNTAX	INTEGER
			ACCESS	read-only
			STATUS	current
	DESCRIPTION ""
			::= { mbus3A 32 }

mbus3AValue0D		OBJECT-TYPE
			SYNTAX	INTEGER
			ACCESS	read-only
			STATUS	current
	DESCRIPTION ""
			::= { mbus3A 33 }

mbus3AVIF0E		OBJECT-TYPE
			SYNTAX	INTEGER
			ACCESS	read-only
			STATUS	current
	DESCRIPTION ""
			::= { mbus3A 34 }

mbus3AValue0E		OBJECT-TYPE
			SYNTAX	INTEGER
			ACCESS	read-only
			STATUS	current
	DESCRIPTION ""
			::= { mbus3A 35 }

mbus3AVIF0F		OBJECT-TYPE
			SYNTAX	INTEGER
			ACCESS	read-only
			STATUS	current
	DESCRIPTION ""
			::= { mbus3A 36 }

mbus3AValue0F		OBJECT-TYPE
			SYNTAX	INTEGER
			ACCESS	read-only
			STATUS	current
	DESCRIPTION ""
			::= { mbus3A 37 }

mbus3AVIF10		OBJECT-TYPE
			SYNTAX	INTEGER
			ACCESS	read-only
			STATUS	current
	DESCRIPTION ""
			::= { mbus3A 38 }

mbus3AValue10		OBJECT-TYPE
			SYNTAX	INTEGER
			ACCESS	read-only
			STATUS	current
	DESCRIPTION ""
			::= { mbus3A 39 }

mbus3AVIF11		OBJECT-TYPE
			SYNTAX	INTEGER
			ACCESS	read-only
			STATUS	current
	DESCRIPTION ""
			::= { mbus3A 40 }

mbus3AValue11		OBJECT-TYPE
			SYNTAX	INTEGER
			ACCESS	read-only
			STATUS	current
	DESCRIPTION ""
			::= { mbus3A 41 }

mbus3AVIF12		OBJECT-TYPE
			SYNTAX	INTEGER
			ACCESS	read-only
			STATUS	current
	DESCRIPTION ""
			::= { mbus3A 42 }

mbus3AValue12		OBJECT-TYPE
			SYNTAX	INTEGER
			ACCESS	read-only
			STATUS	current
	DESCRIPTION ""
			::= { mbus3A 43 }

mbus3AVIF13		OBJECT-TYPE
			SYNTAX	INTEGER
			ACCESS	read-only
			STATUS	current
	DESCRIPTION ""
			::= { mbus3A 44 }

mbus3AValue13		OBJECT-TYPE
			SYNTAX	INTEGER
			ACCESS	read-only
			STATUS	current
	DESCRIPTION ""
			::= { mbus3A 45 }

mbus3AVIF14		OBJECT-TYPE
			SYNTAX	INTEGER
			ACCESS	read-only
			STATUS	current
	DESCRIPTION ""
			::= { mbus3A 46 }

mbus3AValue14		OBJECT-TYPE
			SYNTAX	INTEGER
			ACCESS	read-only
			STATUS	current
	DESCRIPTION ""
			::= { mbus3A 47 }

mbus3AVIF15		OBJECT-TYPE
			SYNTAX	INTEGER
			ACCESS	read-only
			STATUS	current
	DESCRIPTION ""
			::= { mbus3A 48 }

mbus3AValue15		OBJECT-TYPE
			SYNTAX	INTEGER
			ACCESS	read-only
			STATUS	current
	DESCRIPTION ""
			::= { mbus3A 49 }

mbus3AVIF16		OBJECT-TYPE
			SYNTAX	INTEGER
			ACCESS	read-only
			STATUS	current
	DESCRIPTION ""
			::= { mbus3A 50 }

mbus3AValue16		OBJECT-TYPE
			SYNTAX	INTEGER
			ACCESS	read-only
			STATUS	current
	DESCRIPTION ""
			::= { mbus3A 51 }

mbus3AVIF17		OBJECT-TYPE
			SYNTAX	INTEGER
			ACCESS	read-only
			STATUS	current
	DESCRIPTION ""
			::= { mbus3A 52 }

mbus3AValue17		OBJECT-TYPE
			SYNTAX	INTEGER
			ACCESS	read-only
			STATUS	current
	DESCRIPTION ""
			::= { mbus3A 53 }

mbus3AVIF18		OBJECT-TYPE
			SYNTAX	INTEGER
			ACCESS	read-only
			STATUS	current
	DESCRIPTION ""
			::= { mbus3A 54 }

mbus3AValue18		OBJECT-TYPE
			SYNTAX	INTEGER
			ACCESS	read-only
			STATUS	current
	DESCRIPTION ""
			::= { mbus3A 55 }

mbus3AVIF19		OBJECT-TYPE
			SYNTAX	INTEGER
			ACCESS	read-only
			STATUS	current
	DESCRIPTION ""
			::= { mbus3A 56 }

mbus3AValue19		OBJECT-TYPE
			SYNTAX	INTEGER
			ACCESS	read-only
			STATUS	current
	DESCRIPTION ""
			::= { mbus3A 57 }

mbus3AVIF1A		OBJECT-TYPE
			SYNTAX	INTEGER
			ACCESS	read-only
			STATUS	current
	DESCRIPTION ""
			::= { mbus3A 58 }

mbus3AValue1A		OBJECT-TYPE
			SYNTAX	INTEGER
			ACCESS	read-only
			STATUS	current
	DESCRIPTION ""
			::= { mbus3A 59 }

mbus3AVIF1B		OBJECT-TYPE
			SYNTAX	INTEGER
			ACCESS	read-only
			STATUS	current
	DESCRIPTION ""
			::= { mbus3A 60 }

mbus3AValue1B		OBJECT-TYPE
			SYNTAX	INTEGER
			ACCESS	read-only
			STATUS	current
	DESCRIPTION ""
			::= { mbus3A 61 }

mbus3AVIF1C		OBJECT-TYPE
			SYNTAX	INTEGER
			ACCESS	read-only
			STATUS	current
	DESCRIPTION ""
			::= { mbus3A 62 }

mbus3AValue1C		OBJECT-TYPE
			SYNTAX	INTEGER
			ACCESS	read-only
			STATUS	current
	DESCRIPTION ""
			::= { mbus3A 63 }

mbus3AVIF1D		OBJECT-TYPE
			SYNTAX	INTEGER
			ACCESS	read-only
			STATUS	current
	DESCRIPTION ""
			::= { mbus3A 64 }

mbus3AValue1D		OBJECT-TYPE
			SYNTAX	INTEGER
			ACCESS	read-only
			STATUS	current
	DESCRIPTION ""
			::= { mbus3A 65 }

mbus3AVIF1E		OBJECT-TYPE
			SYNTAX	INTEGER
			ACCESS	read-only
			STATUS	current
	DESCRIPTION ""
			::= { mbus3A 66 }

mbus3AValue1E		OBJECT-TYPE
			SYNTAX	INTEGER
			ACCESS	read-only
			STATUS	current
	DESCRIPTION ""
			::= { mbus3A 67 }

mbus3AVIF1F		OBJECT-TYPE
			SYNTAX	INTEGER
			ACCESS	read-only
			STATUS	current
	DESCRIPTION ""
			::= { mbus3A 68 }

mbus3AValue1F		OBJECT-TYPE
			SYNTAX	INTEGER
			ACCESS	read-only
			STATUS	current
	DESCRIPTION ""
			::= { mbus3A 69 }

mbus3AVIF20		OBJECT-TYPE
			SYNTAX	INTEGER
			ACCESS	read-only
			STATUS	current
	DESCRIPTION ""
			::= { mbus3A 70 }

mbus3AValue20		OBJECT-TYPE
			SYNTAX	INTEGER
			ACCESS	read-only
			STATUS	current
	DESCRIPTION ""
			::= { mbus3A 71 }

mbus3AVIF21		OBJECT-TYPE
			SYNTAX	INTEGER
			ACCESS	read-only
			STATUS	current
	DESCRIPTION ""
			::= { mbus3A 72 }

mbus3AValue21		OBJECT-TYPE
			SYNTAX	INTEGER
			ACCESS	read-only
			STATUS	current
	DESCRIPTION ""
			::= { mbus3A 73 }

mbus3AVIF22		OBJECT-TYPE
			SYNTAX	INTEGER
			ACCESS	read-only
			STATUS	current
	DESCRIPTION ""
			::= { mbus3A 74 }

mbus3AValue22		OBJECT-TYPE
			SYNTAX	INTEGER
			ACCESS	read-only
			STATUS	current
	DESCRIPTION ""
			::= { mbus3A 75 }

mbus3AVIF23		OBJECT-TYPE
			SYNTAX	INTEGER
			ACCESS	read-only
			STATUS	current
	DESCRIPTION ""
			::= { mbus3A 76 }

mbus3AValue23		OBJECT-TYPE
			SYNTAX	INTEGER
			ACCESS	read-only
			STATUS	current
	DESCRIPTION ""
			::= { mbus3A 77 }

mbus3AVIF24		OBJECT-TYPE
			SYNTAX	INTEGER
			ACCESS	read-only
			STATUS	current
	DESCRIPTION ""
			::= { mbus3A 78 }

mbus3AValue24		OBJECT-TYPE
			SYNTAX	INTEGER
			ACCESS	read-only
			STATUS	current
	DESCRIPTION ""
			::= { mbus3A 79 }

mbus3AVIF25		OBJECT-TYPE
			SYNTAX	INTEGER
			ACCESS	read-only
			STATUS	current
	DESCRIPTION ""
			::= { mbus3A 80 }

mbus3AValue25		OBJECT-TYPE
			SYNTAX	INTEGER
			ACCESS	read-only
			STATUS	current
	DESCRIPTION ""
			::= { mbus3A 81 }

mbus3AVIF26		OBJECT-TYPE
			SYNTAX	INTEGER
			ACCESS	read-only
			STATUS	current
	DESCRIPTION ""
			::= { mbus3A 82 }

mbus3AValue26		OBJECT-TYPE
			SYNTAX	INTEGER
			ACCESS	read-only
			STATUS	current
	DESCRIPTION ""
			::= { mbus3A 83 }

mbus3AVIF27		OBJECT-TYPE
			SYNTAX	INTEGER
			ACCESS	read-only
			STATUS	current
	DESCRIPTION ""
			::= { mbus3A 84 }

mbus3AValue27		OBJECT-TYPE
			SYNTAX	INTEGER
			ACCESS	read-only
			STATUS	current
	DESCRIPTION ""
			::= { mbus3A 85 }

mbus3AVIF28		OBJECT-TYPE
			SYNTAX	INTEGER
			ACCESS	read-only
			STATUS	current
	DESCRIPTION ""
			::= { mbus3A 86 }

mbus3AValue28		OBJECT-TYPE
			SYNTAX	INTEGER
			ACCESS	read-only
			STATUS	current
	DESCRIPTION ""
			::= { mbus3A 87 }

mbus3AVIF29		OBJECT-TYPE
			SYNTAX	INTEGER
			ACCESS	read-only
			STATUS	current
	DESCRIPTION ""
			::= { mbus3A 88 }

mbus3AValue29		OBJECT-TYPE
			SYNTAX	INTEGER
			ACCESS	read-only
			STATUS	current
	DESCRIPTION ""
			::= { mbus3A 89 }

mbus3AVIF2A		OBJECT-TYPE
			SYNTAX	INTEGER
			ACCESS	read-only
			STATUS	current
	DESCRIPTION ""
			::= { mbus3A 90 }

mbus3AValue2A		OBJECT-TYPE
			SYNTAX	INTEGER
			ACCESS	read-only
			STATUS	current
	DESCRIPTION ""
			::= { mbus3A 91 }

mbus3AVIF2B		OBJECT-TYPE
			SYNTAX	INTEGER
			ACCESS	read-only
			STATUS	current
	DESCRIPTION ""
			::= { mbus3A 92 }

mbus3AValue2B		OBJECT-TYPE
			SYNTAX	INTEGER
			ACCESS	read-only
			STATUS	current
	DESCRIPTION ""
			::= { mbus3A 93 }

mbus3AVIF2C		OBJECT-TYPE
			SYNTAX	INTEGER
			ACCESS	read-only
			STATUS	current
	DESCRIPTION ""
			::= { mbus3A 94 }

mbus3AValue2C		OBJECT-TYPE
			SYNTAX	INTEGER
			ACCESS	read-only
			STATUS	current
	DESCRIPTION ""
			::= { mbus3A 95 }

mbus3AVIF2D		OBJECT-TYPE
			SYNTAX	INTEGER
			ACCESS	read-only
			STATUS	current
	DESCRIPTION ""
			::= { mbus3A 96 }

mbus3AValue2D		OBJECT-TYPE
			SYNTAX	INTEGER
			ACCESS	read-only
			STATUS	current
	DESCRIPTION ""
			::= { mbus3A 97 }

mbus3AVIF2E		OBJECT-TYPE
			SYNTAX	INTEGER
			ACCESS	read-only
			STATUS	current
	DESCRIPTION ""
			::= { mbus3A 98 }

mbus3AValue2E		OBJECT-TYPE
			SYNTAX	INTEGER
			ACCESS	read-only
			STATUS	current
	DESCRIPTION ""
			::= { mbus3A 99 }

mbus3AVIF2F		OBJECT-TYPE
			SYNTAX	INTEGER
			ACCESS	read-only
			STATUS	current
	DESCRIPTION ""
			::= { mbus3A 100 }

mbus3AValue2F		OBJECT-TYPE
			SYNTAX	INTEGER
			ACCESS	read-only
			STATUS	current
	DESCRIPTION ""
			::= { mbus3A 101 }

mbus3B			OBJECT IDENTIFIER ::= { mbus 59 }

mbus3BIdNumber		OBJECT-TYPE
			SYNTAX	Gauge
			ACCESS	read-only
			STATUS	current
	DESCRIPTION ""
			::= { mbus3B 1 }

mbus3BManufacturer	OBJECT-TYPE
			SYNTAX	Gauge
			ACCESS	read-only
			STATUS	current
	DESCRIPTION ""
			::= { mbus3B 2 }

mbus3BVersion		OBJECT-TYPE
			SYNTAX	Gauge
			ACCESS	read-only
			STATUS	current
	DESCRIPTION ""
			::= { mbus3B 3 }

mbus3BMedium		OBJECT-TYPE
			SYNTAX	Gauge
			ACCESS	read-only
			STATUS	current
	DESCRIPTION ""
			::= { mbus3B 4 }

mbus3BStatus		OBJECT-TYPE
			SYNTAX	Gauge
			ACCESS	read-only
			STATUS	current
	DESCRIPTION ""
			::= { mbus3B 5 }

mbus3BVIF00		OBJECT-TYPE
			SYNTAX	INTEGER
			ACCESS	read-only
			STATUS	current
	DESCRIPTION ""
			::= { mbus3B 6 }

mbus3BValue00		OBJECT-TYPE
			SYNTAX	INTEGER
			ACCESS	read-only
			STATUS	current
	DESCRIPTION ""
			::= { mbus3B 7 }

mbus3BVIF01		OBJECT-TYPE
			SYNTAX	INTEGER
			ACCESS	read-only
			STATUS	current
	DESCRIPTION ""
			::= { mbus3B 8 }

mbus3BValue01		OBJECT-TYPE
			SYNTAX	INTEGER
			ACCESS	read-only
			STATUS	current
	DESCRIPTION ""
			::= { mbus3B 9 }

mbus3BVIF02		OBJECT-TYPE
			SYNTAX	INTEGER
			ACCESS	read-only
			STATUS	current
	DESCRIPTION ""
			::= { mbus3B 10 }

mbus3BValue02		OBJECT-TYPE
			SYNTAX	INTEGER
			ACCESS	read-only
			STATUS	current
	DESCRIPTION ""
			::= { mbus3B 11 }

mbus3BVIF03		OBJECT-TYPE
			SYNTAX	INTEGER
			ACCESS	read-only
			STATUS	current
	DESCRIPTION ""
			::= { mbus3B 12 }

mbus3BValue03		OBJECT-TYPE
			SYNTAX	INTEGER
			ACCESS	read-only
			STATUS	current
	DESCRIPTION ""
			::= { mbus3B 13 }

mbus3BVIF04		OBJECT-TYPE
			SYNTAX	INTEGER
			ACCESS	read-only
			STATUS	current
	DESCRIPTION ""
			::= { mbus3B 14 }

mbus3BValue04		OBJECT-TYPE
			SYNTAX	INTEGER
			ACCESS	read-only
			STATUS	current
	DESCRIPTION ""
			::= { mbus3B 15 }

mbus3BVIF05		OBJECT-TYPE
			SYNTAX	INTEGER
			ACCESS	read-only
			STATUS	current
	DESCRIPTION ""
			::= { mbus3B 16 }

mbus3BValue05		OBJECT-TYPE
			SYNTAX	INTEGER
			ACCESS	read-only
			STATUS	current
	DESCRIPTION ""
			::= { mbus3B 17 }

mbus3BVIF06		OBJECT-TYPE
			SYNTAX	INTEGER
			ACCESS	read-only
			STATUS	current
	DESCRIPTION ""
			::= { mbus3B 18 }

mbus3BValue06		OBJECT-TYPE
			SYNTAX	INTEGER
			ACCESS	read-only
			STATUS	current
	DESCRIPTION ""
			::= { mbus3B 19 }

mbus3BVIF07		OBJECT-TYPE
			SYNTAX	INTEGER
			ACCESS	read-only
			STATUS	current
	DESCRIPTION ""
			::= { mbus3B 20 }

mbus3BValue07		OBJECT-TYPE
			SYNTAX	INTEGER
			ACCESS	read-only
			STATUS	current
	DESCRIPTION ""
			::= { mbus3B 21 }

mbus3BVIF08		OBJECT-TYPE
			SYNTAX	INTEGER
			ACCESS	read-only
			STATUS	current
	DESCRIPTION ""
			::= { mbus3B 22 }

mbus3BValue08		OBJECT-TYPE
			SYNTAX	INTEGER
			ACCESS	read-only
			STATUS	current
	DESCRIPTION ""
			::= { mbus3B 23 }

mbus3BVIF09		OBJECT-TYPE
			SYNTAX	INTEGER
			ACCESS	read-only
			STATUS	current
	DESCRIPTION ""
			::= { mbus3B 24 }

mbus3BValue09		OBJECT-TYPE
			SYNTAX	INTEGER
			ACCESS	read-only
			STATUS	current
	DESCRIPTION ""
			::= { mbus3B 25 }

mbus3BVIF0A		OBJECT-TYPE
			SYNTAX	INTEGER
			ACCESS	read-only
			STATUS	current
	DESCRIPTION ""
			::= { mbus3B 26 }

mbus3BValue0A		OBJECT-TYPE
			SYNTAX	INTEGER
			ACCESS	read-only
			STATUS	current
	DESCRIPTION ""
			::= { mbus3B 27 }

mbus3BVIF0B		OBJECT-TYPE
			SYNTAX	INTEGER
			ACCESS	read-only
			STATUS	current
	DESCRIPTION ""
			::= { mbus3B 28 }

mbus3BValue0B		OBJECT-TYPE
			SYNTAX	INTEGER
			ACCESS	read-only
			STATUS	current
	DESCRIPTION ""
			::= { mbus3B 29 }

mbus3BVIF0C		OBJECT-TYPE
			SYNTAX	INTEGER
			ACCESS	read-only
			STATUS	current
	DESCRIPTION ""
			::= { mbus3B 30 }

mbus3BValue0C		OBJECT-TYPE
			SYNTAX	INTEGER
			ACCESS	read-only
			STATUS	current
	DESCRIPTION ""
			::= { mbus3B 31 }

mbus3BVIF0D		OBJECT-TYPE
			SYNTAX	INTEGER
			ACCESS	read-only
			STATUS	current
	DESCRIPTION ""
			::= { mbus3B 32 }

mbus3BValue0D		OBJECT-TYPE
			SYNTAX	INTEGER
			ACCESS	read-only
			STATUS	current
	DESCRIPTION ""
			::= { mbus3B 33 }

mbus3BVIF0E		OBJECT-TYPE
			SYNTAX	INTEGER
			ACCESS	read-only
			STATUS	current
	DESCRIPTION ""
			::= { mbus3B 34 }

mbus3BValue0E		OBJECT-TYPE
			SYNTAX	INTEGER
			ACCESS	read-only
			STATUS	current
	DESCRIPTION ""
			::= { mbus3B 35 }

mbus3BVIF0F		OBJECT-TYPE
			SYNTAX	INTEGER
			ACCESS	read-only
			STATUS	current
	DESCRIPTION ""
			::= { mbus3B 36 }

mbus3BValue0F		OBJECT-TYPE
			SYNTAX	INTEGER
			ACCESS	read-only
			STATUS	current
	DESCRIPTION ""
			::= { mbus3B 37 }

mbus3BVIF10		OBJECT-TYPE
			SYNTAX	INTEGER
			ACCESS	read-only
			STATUS	current
	DESCRIPTION ""
			::= { mbus3B 38 }

mbus3BValue10		OBJECT-TYPE
			SYNTAX	INTEGER
			ACCESS	read-only
			STATUS	current
	DESCRIPTION ""
			::= { mbus3B 39 }

mbus3BVIF11		OBJECT-TYPE
			SYNTAX	INTEGER
			ACCESS	read-only
			STATUS	current
	DESCRIPTION ""
			::= { mbus3B 40 }

mbus3BValue11		OBJECT-TYPE
			SYNTAX	INTEGER
			ACCESS	read-only
			STATUS	current
	DESCRIPTION ""
			::= { mbus3B 41 }

mbus3BVIF12		OBJECT-TYPE
			SYNTAX	INTEGER
			ACCESS	read-only
			STATUS	current
	DESCRIPTION ""
			::= { mbus3B 42 }

mbus3BValue12		OBJECT-TYPE
			SYNTAX	INTEGER
			ACCESS	read-only
			STATUS	current
	DESCRIPTION ""
			::= { mbus3B 43 }

mbus3BVIF13		OBJECT-TYPE
			SYNTAX	INTEGER
			ACCESS	read-only
			STATUS	current
	DESCRIPTION ""
			::= { mbus3B 44 }

mbus3BValue13		OBJECT-TYPE
			SYNTAX	INTEGER
			ACCESS	read-only
			STATUS	current
	DESCRIPTION ""
			::= { mbus3B 45 }

mbus3BVIF14		OBJECT-TYPE
			SYNTAX	INTEGER
			ACCESS	read-only
			STATUS	current
	DESCRIPTION ""
			::= { mbus3B 46 }

mbus3BValue14		OBJECT-TYPE
			SYNTAX	INTEGER
			ACCESS	read-only
			STATUS	current
	DESCRIPTION ""
			::= { mbus3B 47 }

mbus3BVIF15		OBJECT-TYPE
			SYNTAX	INTEGER
			ACCESS	read-only
			STATUS	current
	DESCRIPTION ""
			::= { mbus3B 48 }

mbus3BValue15		OBJECT-TYPE
			SYNTAX	INTEGER
			ACCESS	read-only
			STATUS	current
	DESCRIPTION ""
			::= { mbus3B 49 }

mbus3BVIF16		OBJECT-TYPE
			SYNTAX	INTEGER
			ACCESS	read-only
			STATUS	current
	DESCRIPTION ""
			::= { mbus3B 50 }

mbus3BValue16		OBJECT-TYPE
			SYNTAX	INTEGER
			ACCESS	read-only
			STATUS	current
	DESCRIPTION ""
			::= { mbus3B 51 }

mbus3BVIF17		OBJECT-TYPE
			SYNTAX	INTEGER
			ACCESS	read-only
			STATUS	current
	DESCRIPTION ""
			::= { mbus3B 52 }

mbus3BValue17		OBJECT-TYPE
			SYNTAX	INTEGER
			ACCESS	read-only
			STATUS	current
	DESCRIPTION ""
			::= { mbus3B 53 }

mbus3BVIF18		OBJECT-TYPE
			SYNTAX	INTEGER
			ACCESS	read-only
			STATUS	current
	DESCRIPTION ""
			::= { mbus3B 54 }

mbus3BValue18		OBJECT-TYPE
			SYNTAX	INTEGER
			ACCESS	read-only
			STATUS	current
	DESCRIPTION ""
			::= { mbus3B 55 }

mbus3BVIF19		OBJECT-TYPE
			SYNTAX	INTEGER
			ACCESS	read-only
			STATUS	current
	DESCRIPTION ""
			::= { mbus3B 56 }

mbus3BValue19		OBJECT-TYPE
			SYNTAX	INTEGER
			ACCESS	read-only
			STATUS	current
	DESCRIPTION ""
			::= { mbus3B 57 }

mbus3BVIF1A		OBJECT-TYPE
			SYNTAX	INTEGER
			ACCESS	read-only
			STATUS	current
	DESCRIPTION ""
			::= { mbus3B 58 }

mbus3BValue1A		OBJECT-TYPE
			SYNTAX	INTEGER
			ACCESS	read-only
			STATUS	current
	DESCRIPTION ""
			::= { mbus3B 59 }

mbus3BVIF1B		OBJECT-TYPE
			SYNTAX	INTEGER
			ACCESS	read-only
			STATUS	current
	DESCRIPTION ""
			::= { mbus3B 60 }

mbus3BValue1B		OBJECT-TYPE
			SYNTAX	INTEGER
			ACCESS	read-only
			STATUS	current
	DESCRIPTION ""
			::= { mbus3B 61 }

mbus3BVIF1C		OBJECT-TYPE
			SYNTAX	INTEGER
			ACCESS	read-only
			STATUS	current
	DESCRIPTION ""
			::= { mbus3B 62 }

mbus3BValue1C		OBJECT-TYPE
			SYNTAX	INTEGER
			ACCESS	read-only
			STATUS	current
	DESCRIPTION ""
			::= { mbus3B 63 }

mbus3BVIF1D		OBJECT-TYPE
			SYNTAX	INTEGER
			ACCESS	read-only
			STATUS	current
	DESCRIPTION ""
			::= { mbus3B 64 }

mbus3BValue1D		OBJECT-TYPE
			SYNTAX	INTEGER
			ACCESS	read-only
			STATUS	current
	DESCRIPTION ""
			::= { mbus3B 65 }

mbus3BVIF1E		OBJECT-TYPE
			SYNTAX	INTEGER
			ACCESS	read-only
			STATUS	current
	DESCRIPTION ""
			::= { mbus3B 66 }

mbus3BValue1E		OBJECT-TYPE
			SYNTAX	INTEGER
			ACCESS	read-only
			STATUS	current
	DESCRIPTION ""
			::= { mbus3B 67 }

mbus3BVIF1F		OBJECT-TYPE
			SYNTAX	INTEGER
			ACCESS	read-only
			STATUS	current
	DESCRIPTION ""
			::= { mbus3B 68 }

mbus3BValue1F		OBJECT-TYPE
			SYNTAX	INTEGER
			ACCESS	read-only
			STATUS	current
	DESCRIPTION ""
			::= { mbus3B 69 }

mbus3BVIF20		OBJECT-TYPE
			SYNTAX	INTEGER
			ACCESS	read-only
			STATUS	current
	DESCRIPTION ""
			::= { mbus3B 70 }

mbus3BValue20		OBJECT-TYPE
			SYNTAX	INTEGER
			ACCESS	read-only
			STATUS	current
	DESCRIPTION ""
			::= { mbus3B 71 }

mbus3BVIF21		OBJECT-TYPE
			SYNTAX	INTEGER
			ACCESS	read-only
			STATUS	current
	DESCRIPTION ""
			::= { mbus3B 72 }

mbus3BValue21		OBJECT-TYPE
			SYNTAX	INTEGER
			ACCESS	read-only
			STATUS	current
	DESCRIPTION ""
			::= { mbus3B 73 }

mbus3BVIF22		OBJECT-TYPE
			SYNTAX	INTEGER
			ACCESS	read-only
			STATUS	current
	DESCRIPTION ""
			::= { mbus3B 74 }

mbus3BValue22		OBJECT-TYPE
			SYNTAX	INTEGER
			ACCESS	read-only
			STATUS	current
	DESCRIPTION ""
			::= { mbus3B 75 }

mbus3BVIF23		OBJECT-TYPE
			SYNTAX	INTEGER
			ACCESS	read-only
			STATUS	current
	DESCRIPTION ""
			::= { mbus3B 76 }

mbus3BValue23		OBJECT-TYPE
			SYNTAX	INTEGER
			ACCESS	read-only
			STATUS	current
	DESCRIPTION ""
			::= { mbus3B 77 }

mbus3BVIF24		OBJECT-TYPE
			SYNTAX	INTEGER
			ACCESS	read-only
			STATUS	current
	DESCRIPTION ""
			::= { mbus3B 78 }

mbus3BValue24		OBJECT-TYPE
			SYNTAX	INTEGER
			ACCESS	read-only
			STATUS	current
	DESCRIPTION ""
			::= { mbus3B 79 }

mbus3BVIF25		OBJECT-TYPE
			SYNTAX	INTEGER
			ACCESS	read-only
			STATUS	current
	DESCRIPTION ""
			::= { mbus3B 80 }

mbus3BValue25		OBJECT-TYPE
			SYNTAX	INTEGER
			ACCESS	read-only
			STATUS	current
	DESCRIPTION ""
			::= { mbus3B 81 }

mbus3BVIF26		OBJECT-TYPE
			SYNTAX	INTEGER
			ACCESS	read-only
			STATUS	current
	DESCRIPTION ""
			::= { mbus3B 82 }

mbus3BValue26		OBJECT-TYPE
			SYNTAX	INTEGER
			ACCESS	read-only
			STATUS	current
	DESCRIPTION ""
			::= { mbus3B 83 }

mbus3BVIF27		OBJECT-TYPE
			SYNTAX	INTEGER
			ACCESS	read-only
			STATUS	current
	DESCRIPTION ""
			::= { mbus3B 84 }

mbus3BValue27		OBJECT-TYPE
			SYNTAX	INTEGER
			ACCESS	read-only
			STATUS	current
	DESCRIPTION ""
			::= { mbus3B 85 }

mbus3BVIF28		OBJECT-TYPE
			SYNTAX	INTEGER
			ACCESS	read-only
			STATUS	current
	DESCRIPTION ""
			::= { mbus3B 86 }

mbus3BValue28		OBJECT-TYPE
			SYNTAX	INTEGER
			ACCESS	read-only
			STATUS	current
	DESCRIPTION ""
			::= { mbus3B 87 }

mbus3BVIF29		OBJECT-TYPE
			SYNTAX	INTEGER
			ACCESS	read-only
			STATUS	current
	DESCRIPTION ""
			::= { mbus3B 88 }

mbus3BValue29		OBJECT-TYPE
			SYNTAX	INTEGER
			ACCESS	read-only
			STATUS	current
	DESCRIPTION ""
			::= { mbus3B 89 }

mbus3BVIF2A		OBJECT-TYPE
			SYNTAX	INTEGER
			ACCESS	read-only
			STATUS	current
	DESCRIPTION ""
			::= { mbus3B 90 }

mbus3BValue2A		OBJECT-TYPE
			SYNTAX	INTEGER
			ACCESS	read-only
			STATUS	current
	DESCRIPTION ""
			::= { mbus3B 91 }

mbus3BVIF2B		OBJECT-TYPE
			SYNTAX	INTEGER
			ACCESS	read-only
			STATUS	current
	DESCRIPTION ""
			::= { mbus3B 92 }

mbus3BValue2B		OBJECT-TYPE
			SYNTAX	INTEGER
			ACCESS	read-only
			STATUS	current
	DESCRIPTION ""
			::= { mbus3B 93 }

mbus3BVIF2C		OBJECT-TYPE
			SYNTAX	INTEGER
			ACCESS	read-only
			STATUS	current
	DESCRIPTION ""
			::= { mbus3B 94 }

mbus3BValue2C		OBJECT-TYPE
			SYNTAX	INTEGER
			ACCESS	read-only
			STATUS	current
	DESCRIPTION ""
			::= { mbus3B 95 }

mbus3BVIF2D		OBJECT-TYPE
			SYNTAX	INTEGER
			ACCESS	read-only
			STATUS	current
	DESCRIPTION ""
			::= { mbus3B 96 }

mbus3BValue2D		OBJECT-TYPE
			SYNTAX	INTEGER
			ACCESS	read-only
			STATUS	current
	DESCRIPTION ""
			::= { mbus3B 97 }

mbus3BVIF2E		OBJECT-TYPE
			SYNTAX	INTEGER
			ACCESS	read-only
			STATUS	current
	DESCRIPTION ""
			::= { mbus3B 98 }

mbus3BValue2E		OBJECT-TYPE
			SYNTAX	INTEGER
			ACCESS	read-only
			STATUS	current
	DESCRIPTION ""
			::= { mbus3B 99 }

mbus3BVIF2F		OBJECT-TYPE
			SYNTAX	INTEGER
			ACCESS	read-only
			STATUS	current
	DESCRIPTION ""
			::= { mbus3B 100 }

mbus3BValue2F		OBJECT-TYPE
			SYNTAX	INTEGER
			ACCESS	read-only
			STATUS	current
	DESCRIPTION ""
			::= { mbus3B 101 }

mbus3C			OBJECT IDENTIFIER ::= { mbus 60 }

mbus3CIdNumber		OBJECT-TYPE
			SYNTAX	Gauge
			ACCESS	read-only
			STATUS	current
	DESCRIPTION ""
			::= { mbus3C 1 }

mbus3CManufacturer	OBJECT-TYPE
			SYNTAX	Gauge
			ACCESS	read-only
			STATUS	current
	DESCRIPTION ""
			::= { mbus3C 2 }

mbus3CVersion		OBJECT-TYPE
			SYNTAX	Gauge
			ACCESS	read-only
			STATUS	current
	DESCRIPTION ""
			::= { mbus3C 3 }

mbus3CMedium		OBJECT-TYPE
			SYNTAX	Gauge
			ACCESS	read-only
			STATUS	current
	DESCRIPTION ""
			::= { mbus3C 4 }

mbus3CStatus		OBJECT-TYPE
			SYNTAX	Gauge
			ACCESS	read-only
			STATUS	current
	DESCRIPTION ""
			::= { mbus3C 5 }

mbus3CVIF00		OBJECT-TYPE
			SYNTAX	INTEGER
			ACCESS	read-only
			STATUS	current
	DESCRIPTION ""
			::= { mbus3C 6 }

mbus3CValue00		OBJECT-TYPE
			SYNTAX	INTEGER
			ACCESS	read-only
			STATUS	current
	DESCRIPTION ""
			::= { mbus3C 7 }

mbus3CVIF01		OBJECT-TYPE
			SYNTAX	INTEGER
			ACCESS	read-only
			STATUS	current
	DESCRIPTION ""
			::= { mbus3C 8 }

mbus3CValue01		OBJECT-TYPE
			SYNTAX	INTEGER
			ACCESS	read-only
			STATUS	current
	DESCRIPTION ""
			::= { mbus3C 9 }

mbus3CVIF02		OBJECT-TYPE
			SYNTAX	INTEGER
			ACCESS	read-only
			STATUS	current
	DESCRIPTION ""
			::= { mbus3C 10 }

mbus3CValue02		OBJECT-TYPE
			SYNTAX	INTEGER
			ACCESS	read-only
			STATUS	current
	DESCRIPTION ""
			::= { mbus3C 11 }

mbus3CVIF03		OBJECT-TYPE
			SYNTAX	INTEGER
			ACCESS	read-only
			STATUS	current
	DESCRIPTION ""
			::= { mbus3C 12 }

mbus3CValue03		OBJECT-TYPE
			SYNTAX	INTEGER
			ACCESS	read-only
			STATUS	current
	DESCRIPTION ""
			::= { mbus3C 13 }

mbus3CVIF04		OBJECT-TYPE
			SYNTAX	INTEGER
			ACCESS	read-only
			STATUS	current
	DESCRIPTION ""
			::= { mbus3C 14 }

mbus3CValue04		OBJECT-TYPE
			SYNTAX	INTEGER
			ACCESS	read-only
			STATUS	current
	DESCRIPTION ""
			::= { mbus3C 15 }

mbus3CVIF05		OBJECT-TYPE
			SYNTAX	INTEGER
			ACCESS	read-only
			STATUS	current
	DESCRIPTION ""
			::= { mbus3C 16 }

mbus3CValue05		OBJECT-TYPE
			SYNTAX	INTEGER
			ACCESS	read-only
			STATUS	current
	DESCRIPTION ""
			::= { mbus3C 17 }

mbus3CVIF06		OBJECT-TYPE
			SYNTAX	INTEGER
			ACCESS	read-only
			STATUS	current
	DESCRIPTION ""
			::= { mbus3C 18 }

mbus3CValue06		OBJECT-TYPE
			SYNTAX	INTEGER
			ACCESS	read-only
			STATUS	current
	DESCRIPTION ""
			::= { mbus3C 19 }

mbus3CVIF07		OBJECT-TYPE
			SYNTAX	INTEGER
			ACCESS	read-only
			STATUS	current
	DESCRIPTION ""
			::= { mbus3C 20 }

mbus3CValue07		OBJECT-TYPE
			SYNTAX	INTEGER
			ACCESS	read-only
			STATUS	current
	DESCRIPTION ""
			::= { mbus3C 21 }

mbus3CVIF08		OBJECT-TYPE
			SYNTAX	INTEGER
			ACCESS	read-only
			STATUS	current
	DESCRIPTION ""
			::= { mbus3C 22 }

mbus3CValue08		OBJECT-TYPE
			SYNTAX	INTEGER
			ACCESS	read-only
			STATUS	current
	DESCRIPTION ""
			::= { mbus3C 23 }

mbus3CVIF09		OBJECT-TYPE
			SYNTAX	INTEGER
			ACCESS	read-only
			STATUS	current
	DESCRIPTION ""
			::= { mbus3C 24 }

mbus3CValue09		OBJECT-TYPE
			SYNTAX	INTEGER
			ACCESS	read-only
			STATUS	current
	DESCRIPTION ""
			::= { mbus3C 25 }

mbus3CVIF0A		OBJECT-TYPE
			SYNTAX	INTEGER
			ACCESS	read-only
			STATUS	current
	DESCRIPTION ""
			::= { mbus3C 26 }

mbus3CValue0A		OBJECT-TYPE
			SYNTAX	INTEGER
			ACCESS	read-only
			STATUS	current
	DESCRIPTION ""
			::= { mbus3C 27 }

mbus3CVIF0B		OBJECT-TYPE
			SYNTAX	INTEGER
			ACCESS	read-only
			STATUS	current
	DESCRIPTION ""
			::= { mbus3C 28 }

mbus3CValue0B		OBJECT-TYPE
			SYNTAX	INTEGER
			ACCESS	read-only
			STATUS	current
	DESCRIPTION ""
			::= { mbus3C 29 }

mbus3CVIF0C		OBJECT-TYPE
			SYNTAX	INTEGER
			ACCESS	read-only
			STATUS	current
	DESCRIPTION ""
			::= { mbus3C 30 }

mbus3CValue0C		OBJECT-TYPE
			SYNTAX	INTEGER
			ACCESS	read-only
			STATUS	current
	DESCRIPTION ""
			::= { mbus3C 31 }

mbus3CVIF0D		OBJECT-TYPE
			SYNTAX	INTEGER
			ACCESS	read-only
			STATUS	current
	DESCRIPTION ""
			::= { mbus3C 32 }

mbus3CValue0D		OBJECT-TYPE
			SYNTAX	INTEGER
			ACCESS	read-only
			STATUS	current
	DESCRIPTION ""
			::= { mbus3C 33 }

mbus3CVIF0E		OBJECT-TYPE
			SYNTAX	INTEGER
			ACCESS	read-only
			STATUS	current
	DESCRIPTION ""
			::= { mbus3C 34 }

mbus3CValue0E		OBJECT-TYPE
			SYNTAX	INTEGER
			ACCESS	read-only
			STATUS	current
	DESCRIPTION ""
			::= { mbus3C 35 }

mbus3CVIF0F		OBJECT-TYPE
			SYNTAX	INTEGER
			ACCESS	read-only
			STATUS	current
	DESCRIPTION ""
			::= { mbus3C 36 }

mbus3CValue0F		OBJECT-TYPE
			SYNTAX	INTEGER
			ACCESS	read-only
			STATUS	current
	DESCRIPTION ""
			::= { mbus3C 37 }

mbus3CVIF10		OBJECT-TYPE
			SYNTAX	INTEGER
			ACCESS	read-only
			STATUS	current
	DESCRIPTION ""
			::= { mbus3C 38 }

mbus3CValue10		OBJECT-TYPE
			SYNTAX	INTEGER
			ACCESS	read-only
			STATUS	current
	DESCRIPTION ""
			::= { mbus3C 39 }

mbus3CVIF11		OBJECT-TYPE
			SYNTAX	INTEGER
			ACCESS	read-only
			STATUS	current
	DESCRIPTION ""
			::= { mbus3C 40 }

mbus3CValue11		OBJECT-TYPE
			SYNTAX	INTEGER
			ACCESS	read-only
			STATUS	current
	DESCRIPTION ""
			::= { mbus3C 41 }

mbus3CVIF12		OBJECT-TYPE
			SYNTAX	INTEGER
			ACCESS	read-only
			STATUS	current
	DESCRIPTION ""
			::= { mbus3C 42 }

mbus3CValue12		OBJECT-TYPE
			SYNTAX	INTEGER
			ACCESS	read-only
			STATUS	current
	DESCRIPTION ""
			::= { mbus3C 43 }

mbus3CVIF13		OBJECT-TYPE
			SYNTAX	INTEGER
			ACCESS	read-only
			STATUS	current
	DESCRIPTION ""
			::= { mbus3C 44 }

mbus3CValue13		OBJECT-TYPE
			SYNTAX	INTEGER
			ACCESS	read-only
			STATUS	current
	DESCRIPTION ""
			::= { mbus3C 45 }

mbus3CVIF14		OBJECT-TYPE
			SYNTAX	INTEGER
			ACCESS	read-only
			STATUS	current
	DESCRIPTION ""
			::= { mbus3C 46 }

mbus3CValue14		OBJECT-TYPE
			SYNTAX	INTEGER
			ACCESS	read-only
			STATUS	current
	DESCRIPTION ""
			::= { mbus3C 47 }

mbus3CVIF15		OBJECT-TYPE
			SYNTAX	INTEGER
			ACCESS	read-only
			STATUS	current
	DESCRIPTION ""
			::= { mbus3C 48 }

mbus3CValue15		OBJECT-TYPE
			SYNTAX	INTEGER
			ACCESS	read-only
			STATUS	current
	DESCRIPTION ""
			::= { mbus3C 49 }

mbus3CVIF16		OBJECT-TYPE
			SYNTAX	INTEGER
			ACCESS	read-only
			STATUS	current
	DESCRIPTION ""
			::= { mbus3C 50 }

mbus3CValue16		OBJECT-TYPE
			SYNTAX	INTEGER
			ACCESS	read-only
			STATUS	current
	DESCRIPTION ""
			::= { mbus3C 51 }

mbus3CVIF17		OBJECT-TYPE
			SYNTAX	INTEGER
			ACCESS	read-only
			STATUS	current
	DESCRIPTION ""
			::= { mbus3C 52 }

mbus3CValue17		OBJECT-TYPE
			SYNTAX	INTEGER
			ACCESS	read-only
			STATUS	current
	DESCRIPTION ""
			::= { mbus3C 53 }

mbus3CVIF18		OBJECT-TYPE
			SYNTAX	INTEGER
			ACCESS	read-only
			STATUS	current
	DESCRIPTION ""
			::= { mbus3C 54 }

mbus3CValue18		OBJECT-TYPE
			SYNTAX	INTEGER
			ACCESS	read-only
			STATUS	current
	DESCRIPTION ""
			::= { mbus3C 55 }

mbus3CVIF19		OBJECT-TYPE
			SYNTAX	INTEGER
			ACCESS	read-only
			STATUS	current
	DESCRIPTION ""
			::= { mbus3C 56 }

mbus3CValue19		OBJECT-TYPE
			SYNTAX	INTEGER
			ACCESS	read-only
			STATUS	current
	DESCRIPTION ""
			::= { mbus3C 57 }

mbus3CVIF1A		OBJECT-TYPE
			SYNTAX	INTEGER
			ACCESS	read-only
			STATUS	current
	DESCRIPTION ""
			::= { mbus3C 58 }

mbus3CValue1A		OBJECT-TYPE
			SYNTAX	INTEGER
			ACCESS	read-only
			STATUS	current
	DESCRIPTION ""
			::= { mbus3C 59 }

mbus3CVIF1B		OBJECT-TYPE
			SYNTAX	INTEGER
			ACCESS	read-only
			STATUS	current
	DESCRIPTION ""
			::= { mbus3C 60 }

mbus3CValue1B		OBJECT-TYPE
			SYNTAX	INTEGER
			ACCESS	read-only
			STATUS	current
	DESCRIPTION ""
			::= { mbus3C 61 }

mbus3CVIF1C		OBJECT-TYPE
			SYNTAX	INTEGER
			ACCESS	read-only
			STATUS	current
	DESCRIPTION ""
			::= { mbus3C 62 }

mbus3CValue1C		OBJECT-TYPE
			SYNTAX	INTEGER
			ACCESS	read-only
			STATUS	current
	DESCRIPTION ""
			::= { mbus3C 63 }

mbus3CVIF1D		OBJECT-TYPE
			SYNTAX	INTEGER
			ACCESS	read-only
			STATUS	current
	DESCRIPTION ""
			::= { mbus3C 64 }

mbus3CValue1D		OBJECT-TYPE
			SYNTAX	INTEGER
			ACCESS	read-only
			STATUS	current
	DESCRIPTION ""
			::= { mbus3C 65 }

mbus3CVIF1E		OBJECT-TYPE
			SYNTAX	INTEGER
			ACCESS	read-only
			STATUS	current
	DESCRIPTION ""
			::= { mbus3C 66 }

mbus3CValue1E		OBJECT-TYPE
			SYNTAX	INTEGER
			ACCESS	read-only
			STATUS	current
	DESCRIPTION ""
			::= { mbus3C 67 }

mbus3CVIF1F		OBJECT-TYPE
			SYNTAX	INTEGER
			ACCESS	read-only
			STATUS	current
	DESCRIPTION ""
			::= { mbus3C 68 }

mbus3CValue1F		OBJECT-TYPE
			SYNTAX	INTEGER
			ACCESS	read-only
			STATUS	current
	DESCRIPTION ""
			::= { mbus3C 69 }

mbus3CVIF20		OBJECT-TYPE
			SYNTAX	INTEGER
			ACCESS	read-only
			STATUS	current
	DESCRIPTION ""
			::= { mbus3C 70 }

mbus3CValue20		OBJECT-TYPE
			SYNTAX	INTEGER
			ACCESS	read-only
			STATUS	current
	DESCRIPTION ""
			::= { mbus3C 71 }

mbus3CVIF21		OBJECT-TYPE
			SYNTAX	INTEGER
			ACCESS	read-only
			STATUS	current
	DESCRIPTION ""
			::= { mbus3C 72 }

mbus3CValue21		OBJECT-TYPE
			SYNTAX	INTEGER
			ACCESS	read-only
			STATUS	current
	DESCRIPTION ""
			::= { mbus3C 73 }

mbus3CVIF22		OBJECT-TYPE
			SYNTAX	INTEGER
			ACCESS	read-only
			STATUS	current
	DESCRIPTION ""
			::= { mbus3C 74 }

mbus3CValue22		OBJECT-TYPE
			SYNTAX	INTEGER
			ACCESS	read-only
			STATUS	current
	DESCRIPTION ""
			::= { mbus3C 75 }

mbus3CVIF23		OBJECT-TYPE
			SYNTAX	INTEGER
			ACCESS	read-only
			STATUS	current
	DESCRIPTION ""
			::= { mbus3C 76 }

mbus3CValue23		OBJECT-TYPE
			SYNTAX	INTEGER
			ACCESS	read-only
			STATUS	current
	DESCRIPTION ""
			::= { mbus3C 77 }

mbus3CVIF24		OBJECT-TYPE
			SYNTAX	INTEGER
			ACCESS	read-only
			STATUS	current
	DESCRIPTION ""
			::= { mbus3C 78 }

mbus3CValue24		OBJECT-TYPE
			SYNTAX	INTEGER
			ACCESS	read-only
			STATUS	current
	DESCRIPTION ""
			::= { mbus3C 79 }

mbus3CVIF25		OBJECT-TYPE
			SYNTAX	INTEGER
			ACCESS	read-only
			STATUS	current
	DESCRIPTION ""
			::= { mbus3C 80 }

mbus3CValue25		OBJECT-TYPE
			SYNTAX	INTEGER
			ACCESS	read-only
			STATUS	current
	DESCRIPTION ""
			::= { mbus3C 81 }

mbus3CVIF26		OBJECT-TYPE
			SYNTAX	INTEGER
			ACCESS	read-only
			STATUS	current
	DESCRIPTION ""
			::= { mbus3C 82 }

mbus3CValue26		OBJECT-TYPE
			SYNTAX	INTEGER
			ACCESS	read-only
			STATUS	current
	DESCRIPTION ""
			::= { mbus3C 83 }

mbus3CVIF27		OBJECT-TYPE
			SYNTAX	INTEGER
			ACCESS	read-only
			STATUS	current
	DESCRIPTION ""
			::= { mbus3C 84 }

mbus3CValue27		OBJECT-TYPE
			SYNTAX	INTEGER
			ACCESS	read-only
			STATUS	current
	DESCRIPTION ""
			::= { mbus3C 85 }

mbus3CVIF28		OBJECT-TYPE
			SYNTAX	INTEGER
			ACCESS	read-only
			STATUS	current
	DESCRIPTION ""
			::= { mbus3C 86 }

mbus3CValue28		OBJECT-TYPE
			SYNTAX	INTEGER
			ACCESS	read-only
			STATUS	current
	DESCRIPTION ""
			::= { mbus3C 87 }

mbus3CVIF29		OBJECT-TYPE
			SYNTAX	INTEGER
			ACCESS	read-only
			STATUS	current
	DESCRIPTION ""
			::= { mbus3C 88 }

mbus3CValue29		OBJECT-TYPE
			SYNTAX	INTEGER
			ACCESS	read-only
			STATUS	current
	DESCRIPTION ""
			::= { mbus3C 89 }

mbus3CVIF2A		OBJECT-TYPE
			SYNTAX	INTEGER
			ACCESS	read-only
			STATUS	current
	DESCRIPTION ""
			::= { mbus3C 90 }

mbus3CValue2A		OBJECT-TYPE
			SYNTAX	INTEGER
			ACCESS	read-only
			STATUS	current
	DESCRIPTION ""
			::= { mbus3C 91 }

mbus3CVIF2B		OBJECT-TYPE
			SYNTAX	INTEGER
			ACCESS	read-only
			STATUS	current
	DESCRIPTION ""
			::= { mbus3C 92 }

mbus3CValue2B		OBJECT-TYPE
			SYNTAX	INTEGER
			ACCESS	read-only
			STATUS	current
	DESCRIPTION ""
			::= { mbus3C 93 }

mbus3CVIF2C		OBJECT-TYPE
			SYNTAX	INTEGER
			ACCESS	read-only
			STATUS	current
	DESCRIPTION ""
			::= { mbus3C 94 }

mbus3CValue2C		OBJECT-TYPE
			SYNTAX	INTEGER
			ACCESS	read-only
			STATUS	current
	DESCRIPTION ""
			::= { mbus3C 95 }

mbus3CVIF2D		OBJECT-TYPE
			SYNTAX	INTEGER
			ACCESS	read-only
			STATUS	current
	DESCRIPTION ""
			::= { mbus3C 96 }

mbus3CValue2D		OBJECT-TYPE
			SYNTAX	INTEGER
			ACCESS	read-only
			STATUS	current
	DESCRIPTION ""
			::= { mbus3C 97 }

mbus3CVIF2E		OBJECT-TYPE
			SYNTAX	INTEGER
			ACCESS	read-only
			STATUS	current
	DESCRIPTION ""
			::= { mbus3C 98 }

mbus3CValue2E		OBJECT-TYPE
			SYNTAX	INTEGER
			ACCESS	read-only
			STATUS	current
	DESCRIPTION ""
			::= { mbus3C 99 }

mbus3CVIF2F		OBJECT-TYPE
			SYNTAX	INTEGER
			ACCESS	read-only
			STATUS	current
	DESCRIPTION ""
			::= { mbus3C 100 }

mbus3CValue2F		OBJECT-TYPE
			SYNTAX	INTEGER
			ACCESS	read-only
			STATUS	current
	DESCRIPTION ""
			::= { mbus3C 101 }

mbus3D			OBJECT IDENTIFIER ::= { mbus 61 }

mbus3DIdNumber		OBJECT-TYPE
			SYNTAX	Gauge
			ACCESS	read-only
			STATUS	current
	DESCRIPTION ""
			::= { mbus3D 1 }

mbus3DManufacturer	OBJECT-TYPE
			SYNTAX	Gauge
			ACCESS	read-only
			STATUS	current
	DESCRIPTION ""
			::= { mbus3D 2 }

mbus3DVersion		OBJECT-TYPE
			SYNTAX	Gauge
			ACCESS	read-only
			STATUS	current
	DESCRIPTION ""
			::= { mbus3D 3 }

mbus3DMedium		OBJECT-TYPE
			SYNTAX	Gauge
			ACCESS	read-only
			STATUS	current
	DESCRIPTION ""
			::= { mbus3D 4 }

mbus3DStatus		OBJECT-TYPE
			SYNTAX	Gauge
			ACCESS	read-only
			STATUS	current
	DESCRIPTION ""
			::= { mbus3D 5 }

mbus3DVIF00		OBJECT-TYPE
			SYNTAX	INTEGER
			ACCESS	read-only
			STATUS	current
	DESCRIPTION ""
			::= { mbus3D 6 }

mbus3DValue00		OBJECT-TYPE
			SYNTAX	INTEGER
			ACCESS	read-only
			STATUS	current
	DESCRIPTION ""
			::= { mbus3D 7 }

mbus3DVIF01		OBJECT-TYPE
			SYNTAX	INTEGER
			ACCESS	read-only
			STATUS	current
	DESCRIPTION ""
			::= { mbus3D 8 }

mbus3DValue01		OBJECT-TYPE
			SYNTAX	INTEGER
			ACCESS	read-only
			STATUS	current
	DESCRIPTION ""
			::= { mbus3D 9 }

mbus3DVIF02		OBJECT-TYPE
			SYNTAX	INTEGER
			ACCESS	read-only
			STATUS	current
	DESCRIPTION ""
			::= { mbus3D 10 }

mbus3DValue02		OBJECT-TYPE
			SYNTAX	INTEGER
			ACCESS	read-only
			STATUS	current
	DESCRIPTION ""
			::= { mbus3D 11 }

mbus3DVIF03		OBJECT-TYPE
			SYNTAX	INTEGER
			ACCESS	read-only
			STATUS	current
	DESCRIPTION ""
			::= { mbus3D 12 }

mbus3DValue03		OBJECT-TYPE
			SYNTAX	INTEGER
			ACCESS	read-only
			STATUS	current
	DESCRIPTION ""
			::= { mbus3D 13 }

mbus3DVIF04		OBJECT-TYPE
			SYNTAX	INTEGER
			ACCESS	read-only
			STATUS	current
	DESCRIPTION ""
			::= { mbus3D 14 }

mbus3DValue04		OBJECT-TYPE
			SYNTAX	INTEGER
			ACCESS	read-only
			STATUS	current
	DESCRIPTION ""
			::= { mbus3D 15 }

mbus3DVIF05		OBJECT-TYPE
			SYNTAX	INTEGER
			ACCESS	read-only
			STATUS	current
	DESCRIPTION ""
			::= { mbus3D 16 }

mbus3DValue05		OBJECT-TYPE
			SYNTAX	INTEGER
			ACCESS	read-only
			STATUS	current
	DESCRIPTION ""
			::= { mbus3D 17 }

mbus3DVIF06		OBJECT-TYPE
			SYNTAX	INTEGER
			ACCESS	read-only
			STATUS	current
	DESCRIPTION ""
			::= { mbus3D 18 }

mbus3DValue06		OBJECT-TYPE
			SYNTAX	INTEGER
			ACCESS	read-only
			STATUS	current
	DESCRIPTION ""
			::= { mbus3D 19 }

mbus3DVIF07		OBJECT-TYPE
			SYNTAX	INTEGER
			ACCESS	read-only
			STATUS	current
	DESCRIPTION ""
			::= { mbus3D 20 }

mbus3DValue07		OBJECT-TYPE
			SYNTAX	INTEGER
			ACCESS	read-only
			STATUS	current
	DESCRIPTION ""
			::= { mbus3D 21 }

mbus3DVIF08		OBJECT-TYPE
			SYNTAX	INTEGER
			ACCESS	read-only
			STATUS	current
	DESCRIPTION ""
			::= { mbus3D 22 }

mbus3DValue08		OBJECT-TYPE
			SYNTAX	INTEGER
			ACCESS	read-only
			STATUS	current
	DESCRIPTION ""
			::= { mbus3D 23 }

mbus3DVIF09		OBJECT-TYPE
			SYNTAX	INTEGER
			ACCESS	read-only
			STATUS	current
	DESCRIPTION ""
			::= { mbus3D 24 }

mbus3DValue09		OBJECT-TYPE
			SYNTAX	INTEGER
			ACCESS	read-only
			STATUS	current
	DESCRIPTION ""
			::= { mbus3D 25 }

mbus3DVIF0A		OBJECT-TYPE
			SYNTAX	INTEGER
			ACCESS	read-only
			STATUS	current
	DESCRIPTION ""
			::= { mbus3D 26 }

mbus3DValue0A		OBJECT-TYPE
			SYNTAX	INTEGER
			ACCESS	read-only
			STATUS	current
	DESCRIPTION ""
			::= { mbus3D 27 }

mbus3DVIF0B		OBJECT-TYPE
			SYNTAX	INTEGER
			ACCESS	read-only
			STATUS	current
	DESCRIPTION ""
			::= { mbus3D 28 }

mbus3DValue0B		OBJECT-TYPE
			SYNTAX	INTEGER
			ACCESS	read-only
			STATUS	current
	DESCRIPTION ""
			::= { mbus3D 29 }

mbus3DVIF0C		OBJECT-TYPE
			SYNTAX	INTEGER
			ACCESS	read-only
			STATUS	current
	DESCRIPTION ""
			::= { mbus3D 30 }

mbus3DValue0C		OBJECT-TYPE
			SYNTAX	INTEGER
			ACCESS	read-only
			STATUS	current
	DESCRIPTION ""
			::= { mbus3D 31 }

mbus3DVIF0D		OBJECT-TYPE
			SYNTAX	INTEGER
			ACCESS	read-only
			STATUS	current
	DESCRIPTION ""
			::= { mbus3D 32 }

mbus3DValue0D		OBJECT-TYPE
			SYNTAX	INTEGER
			ACCESS	read-only
			STATUS	current
	DESCRIPTION ""
			::= { mbus3D 33 }

mbus3DVIF0E		OBJECT-TYPE
			SYNTAX	INTEGER
			ACCESS	read-only
			STATUS	current
	DESCRIPTION ""
			::= { mbus3D 34 }

mbus3DValue0E		OBJECT-TYPE
			SYNTAX	INTEGER
			ACCESS	read-only
			STATUS	current
	DESCRIPTION ""
			::= { mbus3D 35 }

mbus3DVIF0F		OBJECT-TYPE
			SYNTAX	INTEGER
			ACCESS	read-only
			STATUS	current
	DESCRIPTION ""
			::= { mbus3D 36 }

mbus3DValue0F		OBJECT-TYPE
			SYNTAX	INTEGER
			ACCESS	read-only
			STATUS	current
	DESCRIPTION ""
			::= { mbus3D 37 }

mbus3DVIF10		OBJECT-TYPE
			SYNTAX	INTEGER
			ACCESS	read-only
			STATUS	current
	DESCRIPTION ""
			::= { mbus3D 38 }

mbus3DValue10		OBJECT-TYPE
			SYNTAX	INTEGER
			ACCESS	read-only
			STATUS	current
	DESCRIPTION ""
			::= { mbus3D 39 }

mbus3DVIF11		OBJECT-TYPE
			SYNTAX	INTEGER
			ACCESS	read-only
			STATUS	current
	DESCRIPTION ""
			::= { mbus3D 40 }

mbus3DValue11		OBJECT-TYPE
			SYNTAX	INTEGER
			ACCESS	read-only
			STATUS	current
	DESCRIPTION ""
			::= { mbus3D 41 }

mbus3DVIF12		OBJECT-TYPE
			SYNTAX	INTEGER
			ACCESS	read-only
			STATUS	current
	DESCRIPTION ""
			::= { mbus3D 42 }

mbus3DValue12		OBJECT-TYPE
			SYNTAX	INTEGER
			ACCESS	read-only
			STATUS	current
	DESCRIPTION ""
			::= { mbus3D 43 }

mbus3DVIF13		OBJECT-TYPE
			SYNTAX	INTEGER
			ACCESS	read-only
			STATUS	current
	DESCRIPTION ""
			::= { mbus3D 44 }

mbus3DValue13		OBJECT-TYPE
			SYNTAX	INTEGER
			ACCESS	read-only
			STATUS	current
	DESCRIPTION ""
			::= { mbus3D 45 }

mbus3DVIF14		OBJECT-TYPE
			SYNTAX	INTEGER
			ACCESS	read-only
			STATUS	current
	DESCRIPTION ""
			::= { mbus3D 46 }

mbus3DValue14		OBJECT-TYPE
			SYNTAX	INTEGER
			ACCESS	read-only
			STATUS	current
	DESCRIPTION ""
			::= { mbus3D 47 }

mbus3DVIF15		OBJECT-TYPE
			SYNTAX	INTEGER
			ACCESS	read-only
			STATUS	current
	DESCRIPTION ""
			::= { mbus3D 48 }

mbus3DValue15		OBJECT-TYPE
			SYNTAX	INTEGER
			ACCESS	read-only
			STATUS	current
	DESCRIPTION ""
			::= { mbus3D 49 }

mbus3DVIF16		OBJECT-TYPE
			SYNTAX	INTEGER
			ACCESS	read-only
			STATUS	current
	DESCRIPTION ""
			::= { mbus3D 50 }

mbus3DValue16		OBJECT-TYPE
			SYNTAX	INTEGER
			ACCESS	read-only
			STATUS	current
	DESCRIPTION ""
			::= { mbus3D 51 }

mbus3DVIF17		OBJECT-TYPE
			SYNTAX	INTEGER
			ACCESS	read-only
			STATUS	current
	DESCRIPTION ""
			::= { mbus3D 52 }

mbus3DValue17		OBJECT-TYPE
			SYNTAX	INTEGER
			ACCESS	read-only
			STATUS	current
	DESCRIPTION ""
			::= { mbus3D 53 }

mbus3DVIF18		OBJECT-TYPE
			SYNTAX	INTEGER
			ACCESS	read-only
			STATUS	current
	DESCRIPTION ""
			::= { mbus3D 54 }

mbus3DValue18		OBJECT-TYPE
			SYNTAX	INTEGER
			ACCESS	read-only
			STATUS	current
	DESCRIPTION ""
			::= { mbus3D 55 }

mbus3DVIF19		OBJECT-TYPE
			SYNTAX	INTEGER
			ACCESS	read-only
			STATUS	current
	DESCRIPTION ""
			::= { mbus3D 56 }

mbus3DValue19		OBJECT-TYPE
			SYNTAX	INTEGER
			ACCESS	read-only
			STATUS	current
	DESCRIPTION ""
			::= { mbus3D 57 }

mbus3DVIF1A		OBJECT-TYPE
			SYNTAX	INTEGER
			ACCESS	read-only
			STATUS	current
	DESCRIPTION ""
			::= { mbus3D 58 }

mbus3DValue1A		OBJECT-TYPE
			SYNTAX	INTEGER
			ACCESS	read-only
			STATUS	current
	DESCRIPTION ""
			::= { mbus3D 59 }

mbus3DVIF1B		OBJECT-TYPE
			SYNTAX	INTEGER
			ACCESS	read-only
			STATUS	current
	DESCRIPTION ""
			::= { mbus3D 60 }

mbus3DValue1B		OBJECT-TYPE
			SYNTAX	INTEGER
			ACCESS	read-only
			STATUS	current
	DESCRIPTION ""
			::= { mbus3D 61 }

mbus3DVIF1C		OBJECT-TYPE
			SYNTAX	INTEGER
			ACCESS	read-only
			STATUS	current
	DESCRIPTION ""
			::= { mbus3D 62 }

mbus3DValue1C		OBJECT-TYPE
			SYNTAX	INTEGER
			ACCESS	read-only
			STATUS	current
	DESCRIPTION ""
			::= { mbus3D 63 }

mbus3DVIF1D		OBJECT-TYPE
			SYNTAX	INTEGER
			ACCESS	read-only
			STATUS	current
	DESCRIPTION ""
			::= { mbus3D 64 }

mbus3DValue1D		OBJECT-TYPE
			SYNTAX	INTEGER
			ACCESS	read-only
			STATUS	current
	DESCRIPTION ""
			::= { mbus3D 65 }

mbus3DVIF1E		OBJECT-TYPE
			SYNTAX	INTEGER
			ACCESS	read-only
			STATUS	current
	DESCRIPTION ""
			::= { mbus3D 66 }

mbus3DValue1E		OBJECT-TYPE
			SYNTAX	INTEGER
			ACCESS	read-only
			STATUS	current
	DESCRIPTION ""
			::= { mbus3D 67 }

mbus3DVIF1F		OBJECT-TYPE
			SYNTAX	INTEGER
			ACCESS	read-only
			STATUS	current
	DESCRIPTION ""
			::= { mbus3D 68 }

mbus3DValue1F		OBJECT-TYPE
			SYNTAX	INTEGER
			ACCESS	read-only
			STATUS	current
	DESCRIPTION ""
			::= { mbus3D 69 }

mbus3DVIF20		OBJECT-TYPE
			SYNTAX	INTEGER
			ACCESS	read-only
			STATUS	current
	DESCRIPTION ""
			::= { mbus3D 70 }

mbus3DValue20		OBJECT-TYPE
			SYNTAX	INTEGER
			ACCESS	read-only
			STATUS	current
	DESCRIPTION ""
			::= { mbus3D 71 }

mbus3DVIF21		OBJECT-TYPE
			SYNTAX	INTEGER
			ACCESS	read-only
			STATUS	current
	DESCRIPTION ""
			::= { mbus3D 72 }

mbus3DValue21		OBJECT-TYPE
			SYNTAX	INTEGER
			ACCESS	read-only
			STATUS	current
	DESCRIPTION ""
			::= { mbus3D 73 }

mbus3DVIF22		OBJECT-TYPE
			SYNTAX	INTEGER
			ACCESS	read-only
			STATUS	current
	DESCRIPTION ""
			::= { mbus3D 74 }

mbus3DValue22		OBJECT-TYPE
			SYNTAX	INTEGER
			ACCESS	read-only
			STATUS	current
	DESCRIPTION ""
			::= { mbus3D 75 }

mbus3DVIF23		OBJECT-TYPE
			SYNTAX	INTEGER
			ACCESS	read-only
			STATUS	current
	DESCRIPTION ""
			::= { mbus3D 76 }

mbus3DValue23		OBJECT-TYPE
			SYNTAX	INTEGER
			ACCESS	read-only
			STATUS	current
	DESCRIPTION ""
			::= { mbus3D 77 }

mbus3DVIF24		OBJECT-TYPE
			SYNTAX	INTEGER
			ACCESS	read-only
			STATUS	current
	DESCRIPTION ""
			::= { mbus3D 78 }

mbus3DValue24		OBJECT-TYPE
			SYNTAX	INTEGER
			ACCESS	read-only
			STATUS	current
	DESCRIPTION ""
			::= { mbus3D 79 }

mbus3DVIF25		OBJECT-TYPE
			SYNTAX	INTEGER
			ACCESS	read-only
			STATUS	current
	DESCRIPTION ""
			::= { mbus3D 80 }

mbus3DValue25		OBJECT-TYPE
			SYNTAX	INTEGER
			ACCESS	read-only
			STATUS	current
	DESCRIPTION ""
			::= { mbus3D 81 }

mbus3DVIF26		OBJECT-TYPE
			SYNTAX	INTEGER
			ACCESS	read-only
			STATUS	current
	DESCRIPTION ""
			::= { mbus3D 82 }

mbus3DValue26		OBJECT-TYPE
			SYNTAX	INTEGER
			ACCESS	read-only
			STATUS	current
	DESCRIPTION ""
			::= { mbus3D 83 }

mbus3DVIF27		OBJECT-TYPE
			SYNTAX	INTEGER
			ACCESS	read-only
			STATUS	current
	DESCRIPTION ""
			::= { mbus3D 84 }

mbus3DValue27		OBJECT-TYPE
			SYNTAX	INTEGER
			ACCESS	read-only
			STATUS	current
	DESCRIPTION ""
			::= { mbus3D 85 }

mbus3DVIF28		OBJECT-TYPE
			SYNTAX	INTEGER
			ACCESS	read-only
			STATUS	current
	DESCRIPTION ""
			::= { mbus3D 86 }

mbus3DValue28		OBJECT-TYPE
			SYNTAX	INTEGER
			ACCESS	read-only
			STATUS	current
	DESCRIPTION ""
			::= { mbus3D 87 }

mbus3DVIF29		OBJECT-TYPE
			SYNTAX	INTEGER
			ACCESS	read-only
			STATUS	current
	DESCRIPTION ""
			::= { mbus3D 88 }

mbus3DValue29		OBJECT-TYPE
			SYNTAX	INTEGER
			ACCESS	read-only
			STATUS	current
	DESCRIPTION ""
			::= { mbus3D 89 }

mbus3DVIF2A		OBJECT-TYPE
			SYNTAX	INTEGER
			ACCESS	read-only
			STATUS	current
	DESCRIPTION ""
			::= { mbus3D 90 }

mbus3DValue2A		OBJECT-TYPE
			SYNTAX	INTEGER
			ACCESS	read-only
			STATUS	current
	DESCRIPTION ""
			::= { mbus3D 91 }

mbus3DVIF2B		OBJECT-TYPE
			SYNTAX	INTEGER
			ACCESS	read-only
			STATUS	current
	DESCRIPTION ""
			::= { mbus3D 92 }

mbus3DValue2B		OBJECT-TYPE
			SYNTAX	INTEGER
			ACCESS	read-only
			STATUS	current
	DESCRIPTION ""
			::= { mbus3D 93 }

mbus3DVIF2C		OBJECT-TYPE
			SYNTAX	INTEGER
			ACCESS	read-only
			STATUS	current
	DESCRIPTION ""
			::= { mbus3D 94 }

mbus3DValue2C		OBJECT-TYPE
			SYNTAX	INTEGER
			ACCESS	read-only
			STATUS	current
	DESCRIPTION ""
			::= { mbus3D 95 }

mbus3DVIF2D		OBJECT-TYPE
			SYNTAX	INTEGER
			ACCESS	read-only
			STATUS	current
	DESCRIPTION ""
			::= { mbus3D 96 }

mbus3DValue2D		OBJECT-TYPE
			SYNTAX	INTEGER
			ACCESS	read-only
			STATUS	current
	DESCRIPTION ""
			::= { mbus3D 97 }

mbus3DVIF2E		OBJECT-TYPE
			SYNTAX	INTEGER
			ACCESS	read-only
			STATUS	current
	DESCRIPTION ""
			::= { mbus3D 98 }

mbus3DValue2E		OBJECT-TYPE
			SYNTAX	INTEGER
			ACCESS	read-only
			STATUS	current
	DESCRIPTION ""
			::= { mbus3D 99 }

mbus3DVIF2F		OBJECT-TYPE
			SYNTAX	INTEGER
			ACCESS	read-only
			STATUS	current
	DESCRIPTION ""
			::= { mbus3D 100 }

mbus3DValue2F		OBJECT-TYPE
			SYNTAX	INTEGER
			ACCESS	read-only
			STATUS	current
	DESCRIPTION ""
			::= { mbus3D 101 }

mbus3E			OBJECT IDENTIFIER ::= { mbus 62 }

mbus3EIdNumber		OBJECT-TYPE
			SYNTAX	Gauge
			ACCESS	read-only
			STATUS	current
	DESCRIPTION ""
			::= { mbus3E 1 }

mbus3EManufacturer	OBJECT-TYPE
			SYNTAX	Gauge
			ACCESS	read-only
			STATUS	current
	DESCRIPTION ""
			::= { mbus3E 2 }

mbus3EVersion		OBJECT-TYPE
			SYNTAX	Gauge
			ACCESS	read-only
			STATUS	current
	DESCRIPTION ""
			::= { mbus3E 3 }

mbus3EMedium		OBJECT-TYPE
			SYNTAX	Gauge
			ACCESS	read-only
			STATUS	current
	DESCRIPTION ""
			::= { mbus3E 4 }

mbus3EStatus		OBJECT-TYPE
			SYNTAX	Gauge
			ACCESS	read-only
			STATUS	current
	DESCRIPTION ""
			::= { mbus3E 5 }

mbus3EVIF00		OBJECT-TYPE
			SYNTAX	INTEGER
			ACCESS	read-only
			STATUS	current
	DESCRIPTION ""
			::= { mbus3E 6 }

mbus3EValue00		OBJECT-TYPE
			SYNTAX	INTEGER
			ACCESS	read-only
			STATUS	current
	DESCRIPTION ""
			::= { mbus3E 7 }

mbus3EVIF01		OBJECT-TYPE
			SYNTAX	INTEGER
			ACCESS	read-only
			STATUS	current
	DESCRIPTION ""
			::= { mbus3E 8 }

mbus3EValue01		OBJECT-TYPE
			SYNTAX	INTEGER
			ACCESS	read-only
			STATUS	current
	DESCRIPTION ""
			::= { mbus3E 9 }

mbus3EVIF02		OBJECT-TYPE
			SYNTAX	INTEGER
			ACCESS	read-only
			STATUS	current
	DESCRIPTION ""
			::= { mbus3E 10 }

mbus3EValue02		OBJECT-TYPE
			SYNTAX	INTEGER
			ACCESS	read-only
			STATUS	current
	DESCRIPTION ""
			::= { mbus3E 11 }

mbus3EVIF03		OBJECT-TYPE
			SYNTAX	INTEGER
			ACCESS	read-only
			STATUS	current
	DESCRIPTION ""
			::= { mbus3E 12 }

mbus3EValue03		OBJECT-TYPE
			SYNTAX	INTEGER
			ACCESS	read-only
			STATUS	current
	DESCRIPTION ""
			::= { mbus3E 13 }

mbus3EVIF04		OBJECT-TYPE
			SYNTAX	INTEGER
			ACCESS	read-only
			STATUS	current
	DESCRIPTION ""
			::= { mbus3E 14 }

mbus3EValue04		OBJECT-TYPE
			SYNTAX	INTEGER
			ACCESS	read-only
			STATUS	current
	DESCRIPTION ""
			::= { mbus3E 15 }

mbus3EVIF05		OBJECT-TYPE
			SYNTAX	INTEGER
			ACCESS	read-only
			STATUS	current
	DESCRIPTION ""
			::= { mbus3E 16 }

mbus3EValue05		OBJECT-TYPE
			SYNTAX	INTEGER
			ACCESS	read-only
			STATUS	current
	DESCRIPTION ""
			::= { mbus3E 17 }

mbus3EVIF06		OBJECT-TYPE
			SYNTAX	INTEGER
			ACCESS	read-only
			STATUS	current
	DESCRIPTION ""
			::= { mbus3E 18 }

mbus3EValue06		OBJECT-TYPE
			SYNTAX	INTEGER
			ACCESS	read-only
			STATUS	current
	DESCRIPTION ""
			::= { mbus3E 19 }

mbus3EVIF07		OBJECT-TYPE
			SYNTAX	INTEGER
			ACCESS	read-only
			STATUS	current
	DESCRIPTION ""
			::= { mbus3E 20 }

mbus3EValue07		OBJECT-TYPE
			SYNTAX	INTEGER
			ACCESS	read-only
			STATUS	current
	DESCRIPTION ""
			::= { mbus3E 21 }

mbus3EVIF08		OBJECT-TYPE
			SYNTAX	INTEGER
			ACCESS	read-only
			STATUS	current
	DESCRIPTION ""
			::= { mbus3E 22 }

mbus3EValue08		OBJECT-TYPE
			SYNTAX	INTEGER
			ACCESS	read-only
			STATUS	current
	DESCRIPTION ""
			::= { mbus3E 23 }

mbus3EVIF09		OBJECT-TYPE
			SYNTAX	INTEGER
			ACCESS	read-only
			STATUS	current
	DESCRIPTION ""
			::= { mbus3E 24 }

mbus3EValue09		OBJECT-TYPE
			SYNTAX	INTEGER
			ACCESS	read-only
			STATUS	current
	DESCRIPTION ""
			::= { mbus3E 25 }

mbus3EVIF0A		OBJECT-TYPE
			SYNTAX	INTEGER
			ACCESS	read-only
			STATUS	current
	DESCRIPTION ""
			::= { mbus3E 26 }

mbus3EValue0A		OBJECT-TYPE
			SYNTAX	INTEGER
			ACCESS	read-only
			STATUS	current
	DESCRIPTION ""
			::= { mbus3E 27 }

mbus3EVIF0B		OBJECT-TYPE
			SYNTAX	INTEGER
			ACCESS	read-only
			STATUS	current
	DESCRIPTION ""
			::= { mbus3E 28 }

mbus3EValue0B		OBJECT-TYPE
			SYNTAX	INTEGER
			ACCESS	read-only
			STATUS	current
	DESCRIPTION ""
			::= { mbus3E 29 }

mbus3EVIF0C		OBJECT-TYPE
			SYNTAX	INTEGER
			ACCESS	read-only
			STATUS	current
	DESCRIPTION ""
			::= { mbus3E 30 }

mbus3EValue0C		OBJECT-TYPE
			SYNTAX	INTEGER
			ACCESS	read-only
			STATUS	current
	DESCRIPTION ""
			::= { mbus3E 31 }

mbus3EVIF0D		OBJECT-TYPE
			SYNTAX	INTEGER
			ACCESS	read-only
			STATUS	current
	DESCRIPTION ""
			::= { mbus3E 32 }

mbus3EValue0D		OBJECT-TYPE
			SYNTAX	INTEGER
			ACCESS	read-only
			STATUS	current
	DESCRIPTION ""
			::= { mbus3E 33 }

mbus3EVIF0E		OBJECT-TYPE
			SYNTAX	INTEGER
			ACCESS	read-only
			STATUS	current
	DESCRIPTION ""
			::= { mbus3E 34 }

mbus3EValue0E		OBJECT-TYPE
			SYNTAX	INTEGER
			ACCESS	read-only
			STATUS	current
	DESCRIPTION ""
			::= { mbus3E 35 }

mbus3EVIF0F		OBJECT-TYPE
			SYNTAX	INTEGER
			ACCESS	read-only
			STATUS	current
	DESCRIPTION ""
			::= { mbus3E 36 }

mbus3EValue0F		OBJECT-TYPE
			SYNTAX	INTEGER
			ACCESS	read-only
			STATUS	current
	DESCRIPTION ""
			::= { mbus3E 37 }

mbus3EVIF10		OBJECT-TYPE
			SYNTAX	INTEGER
			ACCESS	read-only
			STATUS	current
	DESCRIPTION ""
			::= { mbus3E 38 }

mbus3EValue10		OBJECT-TYPE
			SYNTAX	INTEGER
			ACCESS	read-only
			STATUS	current
	DESCRIPTION ""
			::= { mbus3E 39 }

mbus3EVIF11		OBJECT-TYPE
			SYNTAX	INTEGER
			ACCESS	read-only
			STATUS	current
	DESCRIPTION ""
			::= { mbus3E 40 }

mbus3EValue11		OBJECT-TYPE
			SYNTAX	INTEGER
			ACCESS	read-only
			STATUS	current
	DESCRIPTION ""
			::= { mbus3E 41 }

mbus3EVIF12		OBJECT-TYPE
			SYNTAX	INTEGER
			ACCESS	read-only
			STATUS	current
	DESCRIPTION ""
			::= { mbus3E 42 }

mbus3EValue12		OBJECT-TYPE
			SYNTAX	INTEGER
			ACCESS	read-only
			STATUS	current
	DESCRIPTION ""
			::= { mbus3E 43 }

mbus3EVIF13		OBJECT-TYPE
			SYNTAX	INTEGER
			ACCESS	read-only
			STATUS	current
	DESCRIPTION ""
			::= { mbus3E 44 }

mbus3EValue13		OBJECT-TYPE
			SYNTAX	INTEGER
			ACCESS	read-only
			STATUS	current
	DESCRIPTION ""
			::= { mbus3E 45 }

mbus3EVIF14		OBJECT-TYPE
			SYNTAX	INTEGER
			ACCESS	read-only
			STATUS	current
	DESCRIPTION ""
			::= { mbus3E 46 }

mbus3EValue14		OBJECT-TYPE
			SYNTAX	INTEGER
			ACCESS	read-only
			STATUS	current
	DESCRIPTION ""
			::= { mbus3E 47 }

mbus3EVIF15		OBJECT-TYPE
			SYNTAX	INTEGER
			ACCESS	read-only
			STATUS	current
	DESCRIPTION ""
			::= { mbus3E 48 }

mbus3EValue15		OBJECT-TYPE
			SYNTAX	INTEGER
			ACCESS	read-only
			STATUS	current
	DESCRIPTION ""
			::= { mbus3E 49 }

mbus3EVIF16		OBJECT-TYPE
			SYNTAX	INTEGER
			ACCESS	read-only
			STATUS	current
	DESCRIPTION ""
			::= { mbus3E 50 }

mbus3EValue16		OBJECT-TYPE
			SYNTAX	INTEGER
			ACCESS	read-only
			STATUS	current
	DESCRIPTION ""
			::= { mbus3E 51 }

mbus3EVIF17		OBJECT-TYPE
			SYNTAX	INTEGER
			ACCESS	read-only
			STATUS	current
	DESCRIPTION ""
			::= { mbus3E 52 }

mbus3EValue17		OBJECT-TYPE
			SYNTAX	INTEGER
			ACCESS	read-only
			STATUS	current
	DESCRIPTION ""
			::= { mbus3E 53 }

mbus3EVIF18		OBJECT-TYPE
			SYNTAX	INTEGER
			ACCESS	read-only
			STATUS	current
	DESCRIPTION ""
			::= { mbus3E 54 }

mbus3EValue18		OBJECT-TYPE
			SYNTAX	INTEGER
			ACCESS	read-only
			STATUS	current
	DESCRIPTION ""
			::= { mbus3E 55 }

mbus3EVIF19		OBJECT-TYPE
			SYNTAX	INTEGER
			ACCESS	read-only
			STATUS	current
	DESCRIPTION ""
			::= { mbus3E 56 }

mbus3EValue19		OBJECT-TYPE
			SYNTAX	INTEGER
			ACCESS	read-only
			STATUS	current
	DESCRIPTION ""
			::= { mbus3E 57 }

mbus3EVIF1A		OBJECT-TYPE
			SYNTAX	INTEGER
			ACCESS	read-only
			STATUS	current
	DESCRIPTION ""
			::= { mbus3E 58 }

mbus3EValue1A		OBJECT-TYPE
			SYNTAX	INTEGER
			ACCESS	read-only
			STATUS	current
	DESCRIPTION ""
			::= { mbus3E 59 }

mbus3EVIF1B		OBJECT-TYPE
			SYNTAX	INTEGER
			ACCESS	read-only
			STATUS	current
	DESCRIPTION ""
			::= { mbus3E 60 }

mbus3EValue1B		OBJECT-TYPE
			SYNTAX	INTEGER
			ACCESS	read-only
			STATUS	current
	DESCRIPTION ""
			::= { mbus3E 61 }

mbus3EVIF1C		OBJECT-TYPE
			SYNTAX	INTEGER
			ACCESS	read-only
			STATUS	current
	DESCRIPTION ""
			::= { mbus3E 62 }

mbus3EValue1C		OBJECT-TYPE
			SYNTAX	INTEGER
			ACCESS	read-only
			STATUS	current
	DESCRIPTION ""
			::= { mbus3E 63 }

mbus3EVIF1D		OBJECT-TYPE
			SYNTAX	INTEGER
			ACCESS	read-only
			STATUS	current
	DESCRIPTION ""
			::= { mbus3E 64 }

mbus3EValue1D		OBJECT-TYPE
			SYNTAX	INTEGER
			ACCESS	read-only
			STATUS	current
	DESCRIPTION ""
			::= { mbus3E 65 }

mbus3EVIF1E		OBJECT-TYPE
			SYNTAX	INTEGER
			ACCESS	read-only
			STATUS	current
	DESCRIPTION ""
			::= { mbus3E 66 }

mbus3EValue1E		OBJECT-TYPE
			SYNTAX	INTEGER
			ACCESS	read-only
			STATUS	current
	DESCRIPTION ""
			::= { mbus3E 67 }

mbus3EVIF1F		OBJECT-TYPE
			SYNTAX	INTEGER
			ACCESS	read-only
			STATUS	current
	DESCRIPTION ""
			::= { mbus3E 68 }

mbus3EValue1F		OBJECT-TYPE
			SYNTAX	INTEGER
			ACCESS	read-only
			STATUS	current
	DESCRIPTION ""
			::= { mbus3E 69 }

mbus3EVIF20		OBJECT-TYPE
			SYNTAX	INTEGER
			ACCESS	read-only
			STATUS	current
	DESCRIPTION ""
			::= { mbus3E 70 }

mbus3EValue20		OBJECT-TYPE
			SYNTAX	INTEGER
			ACCESS	read-only
			STATUS	current
	DESCRIPTION ""
			::= { mbus3E 71 }

mbus3EVIF21		OBJECT-TYPE
			SYNTAX	INTEGER
			ACCESS	read-only
			STATUS	current
	DESCRIPTION ""
			::= { mbus3E 72 }

mbus3EValue21		OBJECT-TYPE
			SYNTAX	INTEGER
			ACCESS	read-only
			STATUS	current
	DESCRIPTION ""
			::= { mbus3E 73 }

mbus3EVIF22		OBJECT-TYPE
			SYNTAX	INTEGER
			ACCESS	read-only
			STATUS	current
	DESCRIPTION ""
			::= { mbus3E 74 }

mbus3EValue22		OBJECT-TYPE
			SYNTAX	INTEGER
			ACCESS	read-only
			STATUS	current
	DESCRIPTION ""
			::= { mbus3E 75 }

mbus3EVIF23		OBJECT-TYPE
			SYNTAX	INTEGER
			ACCESS	read-only
			STATUS	current
	DESCRIPTION ""
			::= { mbus3E 76 }

mbus3EValue23		OBJECT-TYPE
			SYNTAX	INTEGER
			ACCESS	read-only
			STATUS	current
	DESCRIPTION ""
			::= { mbus3E 77 }

mbus3EVIF24		OBJECT-TYPE
			SYNTAX	INTEGER
			ACCESS	read-only
			STATUS	current
	DESCRIPTION ""
			::= { mbus3E 78 }

mbus3EValue24		OBJECT-TYPE
			SYNTAX	INTEGER
			ACCESS	read-only
			STATUS	current
	DESCRIPTION ""
			::= { mbus3E 79 }

mbus3EVIF25		OBJECT-TYPE
			SYNTAX	INTEGER
			ACCESS	read-only
			STATUS	current
	DESCRIPTION ""
			::= { mbus3E 80 }

mbus3EValue25		OBJECT-TYPE
			SYNTAX	INTEGER
			ACCESS	read-only
			STATUS	current
	DESCRIPTION ""
			::= { mbus3E 81 }

mbus3EVIF26		OBJECT-TYPE
			SYNTAX	INTEGER
			ACCESS	read-only
			STATUS	current
	DESCRIPTION ""
			::= { mbus3E 82 }

mbus3EValue26		OBJECT-TYPE
			SYNTAX	INTEGER
			ACCESS	read-only
			STATUS	current
	DESCRIPTION ""
			::= { mbus3E 83 }

mbus3EVIF27		OBJECT-TYPE
			SYNTAX	INTEGER
			ACCESS	read-only
			STATUS	current
	DESCRIPTION ""
			::= { mbus3E 84 }

mbus3EValue27		OBJECT-TYPE
			SYNTAX	INTEGER
			ACCESS	read-only
			STATUS	current
	DESCRIPTION ""
			::= { mbus3E 85 }

mbus3EVIF28		OBJECT-TYPE
			SYNTAX	INTEGER
			ACCESS	read-only
			STATUS	current
	DESCRIPTION ""
			::= { mbus3E 86 }

mbus3EValue28		OBJECT-TYPE
			SYNTAX	INTEGER
			ACCESS	read-only
			STATUS	current
	DESCRIPTION ""
			::= { mbus3E 87 }

mbus3EVIF29		OBJECT-TYPE
			SYNTAX	INTEGER
			ACCESS	read-only
			STATUS	current
	DESCRIPTION ""
			::= { mbus3E 88 }

mbus3EValue29		OBJECT-TYPE
			SYNTAX	INTEGER
			ACCESS	read-only
			STATUS	current
	DESCRIPTION ""
			::= { mbus3E 89 }

mbus3EVIF2A		OBJECT-TYPE
			SYNTAX	INTEGER
			ACCESS	read-only
			STATUS	current
	DESCRIPTION ""
			::= { mbus3E 90 }

mbus3EValue2A		OBJECT-TYPE
			SYNTAX	INTEGER
			ACCESS	read-only
			STATUS	current
	DESCRIPTION ""
			::= { mbus3E 91 }

mbus3EVIF2B		OBJECT-TYPE
			SYNTAX	INTEGER
			ACCESS	read-only
			STATUS	current
	DESCRIPTION ""
			::= { mbus3E 92 }

mbus3EValue2B		OBJECT-TYPE
			SYNTAX	INTEGER
			ACCESS	read-only
			STATUS	current
	DESCRIPTION ""
			::= { mbus3E 93 }

mbus3EVIF2C		OBJECT-TYPE
			SYNTAX	INTEGER
			ACCESS	read-only
			STATUS	current
	DESCRIPTION ""
			::= { mbus3E 94 }

mbus3EValue2C		OBJECT-TYPE
			SYNTAX	INTEGER
			ACCESS	read-only
			STATUS	current
	DESCRIPTION ""
			::= { mbus3E 95 }

mbus3EVIF2D		OBJECT-TYPE
			SYNTAX	INTEGER
			ACCESS	read-only
			STATUS	current
	DESCRIPTION ""
			::= { mbus3E 96 }

mbus3EValue2D		OBJECT-TYPE
			SYNTAX	INTEGER
			ACCESS	read-only
			STATUS	current
	DESCRIPTION ""
			::= { mbus3E 97 }

mbus3EVIF2E		OBJECT-TYPE
			SYNTAX	INTEGER
			ACCESS	read-only
			STATUS	current
	DESCRIPTION ""
			::= { mbus3E 98 }

mbus3EValue2E		OBJECT-TYPE
			SYNTAX	INTEGER
			ACCESS	read-only
			STATUS	current
	DESCRIPTION ""
			::= { mbus3E 99 }

mbus3EVIF2F		OBJECT-TYPE
			SYNTAX	INTEGER
			ACCESS	read-only
			STATUS	current
	DESCRIPTION ""
			::= { mbus3E 100 }

mbus3EValue2F		OBJECT-TYPE
			SYNTAX	INTEGER
			ACCESS	read-only
			STATUS	current
	DESCRIPTION ""
			::= { mbus3E 101 }

mbus3F			OBJECT IDENTIFIER ::= { mbus 63 }

mbus3FIdNumber		OBJECT-TYPE
			SYNTAX	Gauge
			ACCESS	read-only
			STATUS	current
	DESCRIPTION ""
			::= { mbus3F 1 }

mbus3FManufacturer	OBJECT-TYPE
			SYNTAX	Gauge
			ACCESS	read-only
			STATUS	current
	DESCRIPTION ""
			::= { mbus3F 2 }

mbus3FVersion		OBJECT-TYPE
			SYNTAX	Gauge
			ACCESS	read-only
			STATUS	current
	DESCRIPTION ""
			::= { mbus3F 3 }

mbus3FMedium		OBJECT-TYPE
			SYNTAX	Gauge
			ACCESS	read-only
			STATUS	current
	DESCRIPTION ""
			::= { mbus3F 4 }

mbus3FStatus		OBJECT-TYPE
			SYNTAX	Gauge
			ACCESS	read-only
			STATUS	current
	DESCRIPTION ""
			::= { mbus3F 5 }

mbus3FVIF00		OBJECT-TYPE
			SYNTAX	INTEGER
			ACCESS	read-only
			STATUS	current
	DESCRIPTION ""
			::= { mbus3F 6 }

mbus3FValue00		OBJECT-TYPE
			SYNTAX	INTEGER
			ACCESS	read-only
			STATUS	current
	DESCRIPTION ""
			::= { mbus3F 7 }

mbus3FVIF01		OBJECT-TYPE
			SYNTAX	INTEGER
			ACCESS	read-only
			STATUS	current
	DESCRIPTION ""
			::= { mbus3F 8 }

mbus3FValue01		OBJECT-TYPE
			SYNTAX	INTEGER
			ACCESS	read-only
			STATUS	current
	DESCRIPTION ""
			::= { mbus3F 9 }

mbus3FVIF02		OBJECT-TYPE
			SYNTAX	INTEGER
			ACCESS	read-only
			STATUS	current
	DESCRIPTION ""
			::= { mbus3F 10 }

mbus3FValue02		OBJECT-TYPE
			SYNTAX	INTEGER
			ACCESS	read-only
			STATUS	current
	DESCRIPTION ""
			::= { mbus3F 11 }

mbus3FVIF03		OBJECT-TYPE
			SYNTAX	INTEGER
			ACCESS	read-only
			STATUS	current
	DESCRIPTION ""
			::= { mbus3F 12 }

mbus3FValue03		OBJECT-TYPE
			SYNTAX	INTEGER
			ACCESS	read-only
			STATUS	current
	DESCRIPTION ""
			::= { mbus3F 13 }

mbus3FVIF04		OBJECT-TYPE
			SYNTAX	INTEGER
			ACCESS	read-only
			STATUS	current
	DESCRIPTION ""
			::= { mbus3F 14 }

mbus3FValue04		OBJECT-TYPE
			SYNTAX	INTEGER
			ACCESS	read-only
			STATUS	current
	DESCRIPTION ""
			::= { mbus3F 15 }

mbus3FVIF05		OBJECT-TYPE
			SYNTAX	INTEGER
			ACCESS	read-only
			STATUS	current
	DESCRIPTION ""
			::= { mbus3F 16 }

mbus3FValue05		OBJECT-TYPE
			SYNTAX	INTEGER
			ACCESS	read-only
			STATUS	current
	DESCRIPTION ""
			::= { mbus3F 17 }

mbus3FVIF06		OBJECT-TYPE
			SYNTAX	INTEGER
			ACCESS	read-only
			STATUS	current
	DESCRIPTION ""
			::= { mbus3F 18 }

mbus3FValue06		OBJECT-TYPE
			SYNTAX	INTEGER
			ACCESS	read-only
			STATUS	current
	DESCRIPTION ""
			::= { mbus3F 19 }

mbus3FVIF07		OBJECT-TYPE
			SYNTAX	INTEGER
			ACCESS	read-only
			STATUS	current
	DESCRIPTION ""
			::= { mbus3F 20 }

mbus3FValue07		OBJECT-TYPE
			SYNTAX	INTEGER
			ACCESS	read-only
			STATUS	current
	DESCRIPTION ""
			::= { mbus3F 21 }

mbus3FVIF08		OBJECT-TYPE
			SYNTAX	INTEGER
			ACCESS	read-only
			STATUS	current
	DESCRIPTION ""
			::= { mbus3F 22 }

mbus3FValue08		OBJECT-TYPE
			SYNTAX	INTEGER
			ACCESS	read-only
			STATUS	current
	DESCRIPTION ""
			::= { mbus3F 23 }

mbus3FVIF09		OBJECT-TYPE
			SYNTAX	INTEGER
			ACCESS	read-only
			STATUS	current
	DESCRIPTION ""
			::= { mbus3F 24 }

mbus3FValue09		OBJECT-TYPE
			SYNTAX	INTEGER
			ACCESS	read-only
			STATUS	current
	DESCRIPTION ""
			::= { mbus3F 25 }

mbus3FVIF0A		OBJECT-TYPE
			SYNTAX	INTEGER
			ACCESS	read-only
			STATUS	current
	DESCRIPTION ""
			::= { mbus3F 26 }

mbus3FValue0A		OBJECT-TYPE
			SYNTAX	INTEGER
			ACCESS	read-only
			STATUS	current
	DESCRIPTION ""
			::= { mbus3F 27 }

mbus3FVIF0B		OBJECT-TYPE
			SYNTAX	INTEGER
			ACCESS	read-only
			STATUS	current
	DESCRIPTION ""
			::= { mbus3F 28 }

mbus3FValue0B		OBJECT-TYPE
			SYNTAX	INTEGER
			ACCESS	read-only
			STATUS	current
	DESCRIPTION ""
			::= { mbus3F 29 }

mbus3FVIF0C		OBJECT-TYPE
			SYNTAX	INTEGER
			ACCESS	read-only
			STATUS	current
	DESCRIPTION ""
			::= { mbus3F 30 }

mbus3FValue0C		OBJECT-TYPE
			SYNTAX	INTEGER
			ACCESS	read-only
			STATUS	current
	DESCRIPTION ""
			::= { mbus3F 31 }

mbus3FVIF0D		OBJECT-TYPE
			SYNTAX	INTEGER
			ACCESS	read-only
			STATUS	current
	DESCRIPTION ""
			::= { mbus3F 32 }

mbus3FValue0D		OBJECT-TYPE
			SYNTAX	INTEGER
			ACCESS	read-only
			STATUS	current
	DESCRIPTION ""
			::= { mbus3F 33 }

mbus3FVIF0E		OBJECT-TYPE
			SYNTAX	INTEGER
			ACCESS	read-only
			STATUS	current
	DESCRIPTION ""
			::= { mbus3F 34 }

mbus3FValue0E		OBJECT-TYPE
			SYNTAX	INTEGER
			ACCESS	read-only
			STATUS	current
	DESCRIPTION ""
			::= { mbus3F 35 }

mbus3FVIF0F		OBJECT-TYPE
			SYNTAX	INTEGER
			ACCESS	read-only
			STATUS	current
	DESCRIPTION ""
			::= { mbus3F 36 }

mbus3FValue0F		OBJECT-TYPE
			SYNTAX	INTEGER
			ACCESS	read-only
			STATUS	current
	DESCRIPTION ""
			::= { mbus3F 37 }

mbus3FVIF10		OBJECT-TYPE
			SYNTAX	INTEGER
			ACCESS	read-only
			STATUS	current
	DESCRIPTION ""
			::= { mbus3F 38 }

mbus3FValue10		OBJECT-TYPE
			SYNTAX	INTEGER
			ACCESS	read-only
			STATUS	current
	DESCRIPTION ""
			::= { mbus3F 39 }

mbus3FVIF11		OBJECT-TYPE
			SYNTAX	INTEGER
			ACCESS	read-only
			STATUS	current
	DESCRIPTION ""
			::= { mbus3F 40 }

mbus3FValue11		OBJECT-TYPE
			SYNTAX	INTEGER
			ACCESS	read-only
			STATUS	current
	DESCRIPTION ""
			::= { mbus3F 41 }

mbus3FVIF12		OBJECT-TYPE
			SYNTAX	INTEGER
			ACCESS	read-only
			STATUS	current
	DESCRIPTION ""
			::= { mbus3F 42 }

mbus3FValue12		OBJECT-TYPE
			SYNTAX	INTEGER
			ACCESS	read-only
			STATUS	current
	DESCRIPTION ""
			::= { mbus3F 43 }

mbus3FVIF13		OBJECT-TYPE
			SYNTAX	INTEGER
			ACCESS	read-only
			STATUS	current
	DESCRIPTION ""
			::= { mbus3F 44 }

mbus3FValue13		OBJECT-TYPE
			SYNTAX	INTEGER
			ACCESS	read-only
			STATUS	current
	DESCRIPTION ""
			::= { mbus3F 45 }

mbus3FVIF14		OBJECT-TYPE
			SYNTAX	INTEGER
			ACCESS	read-only
			STATUS	current
	DESCRIPTION ""
			::= { mbus3F 46 }

mbus3FValue14		OBJECT-TYPE
			SYNTAX	INTEGER
			ACCESS	read-only
			STATUS	current
	DESCRIPTION ""
			::= { mbus3F 47 }

mbus3FVIF15		OBJECT-TYPE
			SYNTAX	INTEGER
			ACCESS	read-only
			STATUS	current
	DESCRIPTION ""
			::= { mbus3F 48 }

mbus3FValue15		OBJECT-TYPE
			SYNTAX	INTEGER
			ACCESS	read-only
			STATUS	current
	DESCRIPTION ""
			::= { mbus3F 49 }

mbus3FVIF16		OBJECT-TYPE
			SYNTAX	INTEGER
			ACCESS	read-only
			STATUS	current
	DESCRIPTION ""
			::= { mbus3F 50 }

mbus3FValue16		OBJECT-TYPE
			SYNTAX	INTEGER
			ACCESS	read-only
			STATUS	current
	DESCRIPTION ""
			::= { mbus3F 51 }

mbus3FVIF17		OBJECT-TYPE
			SYNTAX	INTEGER
			ACCESS	read-only
			STATUS	current
	DESCRIPTION ""
			::= { mbus3F 52 }

mbus3FValue17		OBJECT-TYPE
			SYNTAX	INTEGER
			ACCESS	read-only
			STATUS	current
	DESCRIPTION ""
			::= { mbus3F 53 }

mbus3FVIF18		OBJECT-TYPE
			SYNTAX	INTEGER
			ACCESS	read-only
			STATUS	current
	DESCRIPTION ""
			::= { mbus3F 54 }

mbus3FValue18		OBJECT-TYPE
			SYNTAX	INTEGER
			ACCESS	read-only
			STATUS	current
	DESCRIPTION ""
			::= { mbus3F 55 }

mbus3FVIF19		OBJECT-TYPE
			SYNTAX	INTEGER
			ACCESS	read-only
			STATUS	current
	DESCRIPTION ""
			::= { mbus3F 56 }

mbus3FValue19		OBJECT-TYPE
			SYNTAX	INTEGER
			ACCESS	read-only
			STATUS	current
	DESCRIPTION ""
			::= { mbus3F 57 }

mbus3FVIF1A		OBJECT-TYPE
			SYNTAX	INTEGER
			ACCESS	read-only
			STATUS	current
	DESCRIPTION ""
			::= { mbus3F 58 }

mbus3FValue1A		OBJECT-TYPE
			SYNTAX	INTEGER
			ACCESS	read-only
			STATUS	current
	DESCRIPTION ""
			::= { mbus3F 59 }

mbus3FVIF1B		OBJECT-TYPE
			SYNTAX	INTEGER
			ACCESS	read-only
			STATUS	current
	DESCRIPTION ""
			::= { mbus3F 60 }

mbus3FValue1B		OBJECT-TYPE
			SYNTAX	INTEGER
			ACCESS	read-only
			STATUS	current
	DESCRIPTION ""
			::= { mbus3F 61 }

mbus3FVIF1C		OBJECT-TYPE
			SYNTAX	INTEGER
			ACCESS	read-only
			STATUS	current
	DESCRIPTION ""
			::= { mbus3F 62 }

mbus3FValue1C		OBJECT-TYPE
			SYNTAX	INTEGER
			ACCESS	read-only
			STATUS	current
	DESCRIPTION ""
			::= { mbus3F 63 }

mbus3FVIF1D		OBJECT-TYPE
			SYNTAX	INTEGER
			ACCESS	read-only
			STATUS	current
	DESCRIPTION ""
			::= { mbus3F 64 }

mbus3FValue1D		OBJECT-TYPE
			SYNTAX	INTEGER
			ACCESS	read-only
			STATUS	current
	DESCRIPTION ""
			::= { mbus3F 65 }

mbus3FVIF1E		OBJECT-TYPE
			SYNTAX	INTEGER
			ACCESS	read-only
			STATUS	current
	DESCRIPTION ""
			::= { mbus3F 66 }

mbus3FValue1E		OBJECT-TYPE
			SYNTAX	INTEGER
			ACCESS	read-only
			STATUS	current
	DESCRIPTION ""
			::= { mbus3F 67 }

mbus3FVIF1F		OBJECT-TYPE
			SYNTAX	INTEGER
			ACCESS	read-only
			STATUS	current
	DESCRIPTION ""
			::= { mbus3F 68 }

mbus3FValue1F		OBJECT-TYPE
			SYNTAX	INTEGER
			ACCESS	read-only
			STATUS	current
	DESCRIPTION ""
			::= { mbus3F 69 }

mbus3FVIF20		OBJECT-TYPE
			SYNTAX	INTEGER
			ACCESS	read-only
			STATUS	current
	DESCRIPTION ""
			::= { mbus3F 70 }

mbus3FValue20		OBJECT-TYPE
			SYNTAX	INTEGER
			ACCESS	read-only
			STATUS	current
	DESCRIPTION ""
			::= { mbus3F 71 }

mbus3FVIF21		OBJECT-TYPE
			SYNTAX	INTEGER
			ACCESS	read-only
			STATUS	current
	DESCRIPTION ""
			::= { mbus3F 72 }

mbus3FValue21		OBJECT-TYPE
			SYNTAX	INTEGER
			ACCESS	read-only
			STATUS	current
	DESCRIPTION ""
			::= { mbus3F 73 }

mbus3FVIF22		OBJECT-TYPE
			SYNTAX	INTEGER
			ACCESS	read-only
			STATUS	current
	DESCRIPTION ""
			::= { mbus3F 74 }

mbus3FValue22		OBJECT-TYPE
			SYNTAX	INTEGER
			ACCESS	read-only
			STATUS	current
	DESCRIPTION ""
			::= { mbus3F 75 }

mbus3FVIF23		OBJECT-TYPE
			SYNTAX	INTEGER
			ACCESS	read-only
			STATUS	current
	DESCRIPTION ""
			::= { mbus3F 76 }

mbus3FValue23		OBJECT-TYPE
			SYNTAX	INTEGER
			ACCESS	read-only
			STATUS	current
	DESCRIPTION ""
			::= { mbus3F 77 }

mbus3FVIF24		OBJECT-TYPE
			SYNTAX	INTEGER
			ACCESS	read-only
			STATUS	current
	DESCRIPTION ""
			::= { mbus3F 78 }

mbus3FValue24		OBJECT-TYPE
			SYNTAX	INTEGER
			ACCESS	read-only
			STATUS	current
	DESCRIPTION ""
			::= { mbus3F 79 }

mbus3FVIF25		OBJECT-TYPE
			SYNTAX	INTEGER
			ACCESS	read-only
			STATUS	current
	DESCRIPTION ""
			::= { mbus3F 80 }

mbus3FValue25		OBJECT-TYPE
			SYNTAX	INTEGER
			ACCESS	read-only
			STATUS	current
	DESCRIPTION ""
			::= { mbus3F 81 }

mbus3FVIF26		OBJECT-TYPE
			SYNTAX	INTEGER
			ACCESS	read-only
			STATUS	current
	DESCRIPTION ""
			::= { mbus3F 82 }

mbus3FValue26		OBJECT-TYPE
			SYNTAX	INTEGER
			ACCESS	read-only
			STATUS	current
	DESCRIPTION ""
			::= { mbus3F 83 }

mbus3FVIF27		OBJECT-TYPE
			SYNTAX	INTEGER
			ACCESS	read-only
			STATUS	current
	DESCRIPTION ""
			::= { mbus3F 84 }

mbus3FValue27		OBJECT-TYPE
			SYNTAX	INTEGER
			ACCESS	read-only
			STATUS	current
	DESCRIPTION ""
			::= { mbus3F 85 }

mbus3FVIF28		OBJECT-TYPE
			SYNTAX	INTEGER
			ACCESS	read-only
			STATUS	current
	DESCRIPTION ""
			::= { mbus3F 86 }

mbus3FValue28		OBJECT-TYPE
			SYNTAX	INTEGER
			ACCESS	read-only
			STATUS	current
	DESCRIPTION ""
			::= { mbus3F 87 }

mbus3FVIF29		OBJECT-TYPE
			SYNTAX	INTEGER
			ACCESS	read-only
			STATUS	current
	DESCRIPTION ""
			::= { mbus3F 88 }

mbus3FValue29		OBJECT-TYPE
			SYNTAX	INTEGER
			ACCESS	read-only
			STATUS	current
	DESCRIPTION ""
			::= { mbus3F 89 }

mbus3FVIF2A		OBJECT-TYPE
			SYNTAX	INTEGER
			ACCESS	read-only
			STATUS	current
	DESCRIPTION ""
			::= { mbus3F 90 }

mbus3FValue2A		OBJECT-TYPE
			SYNTAX	INTEGER
			ACCESS	read-only
			STATUS	current
	DESCRIPTION ""
			::= { mbus3F 91 }

mbus3FVIF2B		OBJECT-TYPE
			SYNTAX	INTEGER
			ACCESS	read-only
			STATUS	current
	DESCRIPTION ""
			::= { mbus3F 92 }

mbus3FValue2B		OBJECT-TYPE
			SYNTAX	INTEGER
			ACCESS	read-only
			STATUS	current
	DESCRIPTION ""
			::= { mbus3F 93 }

mbus3FVIF2C		OBJECT-TYPE
			SYNTAX	INTEGER
			ACCESS	read-only
			STATUS	current
	DESCRIPTION ""
			::= { mbus3F 94 }

mbus3FValue2C		OBJECT-TYPE
			SYNTAX	INTEGER
			ACCESS	read-only
			STATUS	current
	DESCRIPTION ""
			::= { mbus3F 95 }

mbus3FVIF2D		OBJECT-TYPE
			SYNTAX	INTEGER
			ACCESS	read-only
			STATUS	current
	DESCRIPTION ""
			::= { mbus3F 96 }

mbus3FValue2D		OBJECT-TYPE
			SYNTAX	INTEGER
			ACCESS	read-only
			STATUS	current
	DESCRIPTION ""
			::= { mbus3F 97 }

mbus3FVIF2E		OBJECT-TYPE
			SYNTAX	INTEGER
			ACCESS	read-only
			STATUS	current
	DESCRIPTION ""
			::= { mbus3F 98 }

mbus3FValue2E		OBJECT-TYPE
			SYNTAX	INTEGER
			ACCESS	read-only
			STATUS	current
	DESCRIPTION ""
			::= { mbus3F 99 }

mbus3FVIF2F		OBJECT-TYPE
			SYNTAX	INTEGER
			ACCESS	read-only
			STATUS	current
	DESCRIPTION ""
			::= { mbus3F 100 }

mbus3FValue2F		OBJECT-TYPE
			SYNTAX	INTEGER
			ACCESS	read-only
			STATUS	current
	DESCRIPTION ""
			::= { mbus3F 101 }

mbus40			OBJECT IDENTIFIER ::= { mbus 64 }

mbus40IdNumber		OBJECT-TYPE
			SYNTAX	Gauge
			ACCESS	read-only
			STATUS	current
	DESCRIPTION ""
			::= { mbus40 1 }

mbus40Manufacturer	OBJECT-TYPE
			SYNTAX	Gauge
			ACCESS	read-only
			STATUS	current
	DESCRIPTION ""
			::= { mbus40 2 }

mbus40Version		OBJECT-TYPE
			SYNTAX	Gauge
			ACCESS	read-only
			STATUS	current
	DESCRIPTION ""
			::= { mbus40 3 }

mbus40Medium		OBJECT-TYPE
			SYNTAX	Gauge
			ACCESS	read-only
			STATUS	current
	DESCRIPTION ""
			::= { mbus40 4 }

mbus40Status		OBJECT-TYPE
			SYNTAX	Gauge
			ACCESS	read-only
			STATUS	current
	DESCRIPTION ""
			::= { mbus40 5 }

mbus40VIF00		OBJECT-TYPE
			SYNTAX	INTEGER
			ACCESS	read-only
			STATUS	current
	DESCRIPTION ""
			::= { mbus40 6 }

mbus40Value00		OBJECT-TYPE
			SYNTAX	INTEGER
			ACCESS	read-only
			STATUS	current
	DESCRIPTION ""
			::= { mbus40 7 }

mbus40VIF01		OBJECT-TYPE
			SYNTAX	INTEGER
			ACCESS	read-only
			STATUS	current
	DESCRIPTION ""
			::= { mbus40 8 }

mbus40Value01		OBJECT-TYPE
			SYNTAX	INTEGER
			ACCESS	read-only
			STATUS	current
	DESCRIPTION ""
			::= { mbus40 9 }

mbus40VIF02		OBJECT-TYPE
			SYNTAX	INTEGER
			ACCESS	read-only
			STATUS	current
	DESCRIPTION ""
			::= { mbus40 10 }

mbus40Value02		OBJECT-TYPE
			SYNTAX	INTEGER
			ACCESS	read-only
			STATUS	current
	DESCRIPTION ""
			::= { mbus40 11 }

mbus40VIF03		OBJECT-TYPE
			SYNTAX	INTEGER
			ACCESS	read-only
			STATUS	current
	DESCRIPTION ""
			::= { mbus40 12 }

mbus40Value03		OBJECT-TYPE
			SYNTAX	INTEGER
			ACCESS	read-only
			STATUS	current
	DESCRIPTION ""
			::= { mbus40 13 }

mbus40VIF04		OBJECT-TYPE
			SYNTAX	INTEGER
			ACCESS	read-only
			STATUS	current
	DESCRIPTION ""
			::= { mbus40 14 }

mbus40Value04		OBJECT-TYPE
			SYNTAX	INTEGER
			ACCESS	read-only
			STATUS	current
	DESCRIPTION ""
			::= { mbus40 15 }

mbus40VIF05		OBJECT-TYPE
			SYNTAX	INTEGER
			ACCESS	read-only
			STATUS	current
	DESCRIPTION ""
			::= { mbus40 16 }

mbus40Value05		OBJECT-TYPE
			SYNTAX	INTEGER
			ACCESS	read-only
			STATUS	current
	DESCRIPTION ""
			::= { mbus40 17 }

mbus40VIF06		OBJECT-TYPE
			SYNTAX	INTEGER
			ACCESS	read-only
			STATUS	current
	DESCRIPTION ""
			::= { mbus40 18 }

mbus40Value06		OBJECT-TYPE
			SYNTAX	INTEGER
			ACCESS	read-only
			STATUS	current
	DESCRIPTION ""
			::= { mbus40 19 }

mbus40VIF07		OBJECT-TYPE
			SYNTAX	INTEGER
			ACCESS	read-only
			STATUS	current
	DESCRIPTION ""
			::= { mbus40 20 }

mbus40Value07		OBJECT-TYPE
			SYNTAX	INTEGER
			ACCESS	read-only
			STATUS	current
	DESCRIPTION ""
			::= { mbus40 21 }

mbus40VIF08		OBJECT-TYPE
			SYNTAX	INTEGER
			ACCESS	read-only
			STATUS	current
	DESCRIPTION ""
			::= { mbus40 22 }

mbus40Value08		OBJECT-TYPE
			SYNTAX	INTEGER
			ACCESS	read-only
			STATUS	current
	DESCRIPTION ""
			::= { mbus40 23 }

mbus40VIF09		OBJECT-TYPE
			SYNTAX	INTEGER
			ACCESS	read-only
			STATUS	current
	DESCRIPTION ""
			::= { mbus40 24 }

mbus40Value09		OBJECT-TYPE
			SYNTAX	INTEGER
			ACCESS	read-only
			STATUS	current
	DESCRIPTION ""
			::= { mbus40 25 }

mbus40VIF0A		OBJECT-TYPE
			SYNTAX	INTEGER
			ACCESS	read-only
			STATUS	current
	DESCRIPTION ""
			::= { mbus40 26 }

mbus40Value0A		OBJECT-TYPE
			SYNTAX	INTEGER
			ACCESS	read-only
			STATUS	current
	DESCRIPTION ""
			::= { mbus40 27 }

mbus40VIF0B		OBJECT-TYPE
			SYNTAX	INTEGER
			ACCESS	read-only
			STATUS	current
	DESCRIPTION ""
			::= { mbus40 28 }

mbus40Value0B		OBJECT-TYPE
			SYNTAX	INTEGER
			ACCESS	read-only
			STATUS	current
	DESCRIPTION ""
			::= { mbus40 29 }

mbus40VIF0C		OBJECT-TYPE
			SYNTAX	INTEGER
			ACCESS	read-only
			STATUS	current
	DESCRIPTION ""
			::= { mbus40 30 }

mbus40Value0C		OBJECT-TYPE
			SYNTAX	INTEGER
			ACCESS	read-only
			STATUS	current
	DESCRIPTION ""
			::= { mbus40 31 }

mbus40VIF0D		OBJECT-TYPE
			SYNTAX	INTEGER
			ACCESS	read-only
			STATUS	current
	DESCRIPTION ""
			::= { mbus40 32 }

mbus40Value0D		OBJECT-TYPE
			SYNTAX	INTEGER
			ACCESS	read-only
			STATUS	current
	DESCRIPTION ""
			::= { mbus40 33 }

mbus40VIF0E		OBJECT-TYPE
			SYNTAX	INTEGER
			ACCESS	read-only
			STATUS	current
	DESCRIPTION ""
			::= { mbus40 34 }

mbus40Value0E		OBJECT-TYPE
			SYNTAX	INTEGER
			ACCESS	read-only
			STATUS	current
	DESCRIPTION ""
			::= { mbus40 35 }

mbus40VIF0F		OBJECT-TYPE
			SYNTAX	INTEGER
			ACCESS	read-only
			STATUS	current
	DESCRIPTION ""
			::= { mbus40 36 }

mbus40Value0F		OBJECT-TYPE
			SYNTAX	INTEGER
			ACCESS	read-only
			STATUS	current
	DESCRIPTION ""
			::= { mbus40 37 }

mbus40VIF10		OBJECT-TYPE
			SYNTAX	INTEGER
			ACCESS	read-only
			STATUS	current
	DESCRIPTION ""
			::= { mbus40 38 }

mbus40Value10		OBJECT-TYPE
			SYNTAX	INTEGER
			ACCESS	read-only
			STATUS	current
	DESCRIPTION ""
			::= { mbus40 39 }

mbus40VIF11		OBJECT-TYPE
			SYNTAX	INTEGER
			ACCESS	read-only
			STATUS	current
	DESCRIPTION ""
			::= { mbus40 40 }

mbus40Value11		OBJECT-TYPE
			SYNTAX	INTEGER
			ACCESS	read-only
			STATUS	current
	DESCRIPTION ""
			::= { mbus40 41 }

mbus40VIF12		OBJECT-TYPE
			SYNTAX	INTEGER
			ACCESS	read-only
			STATUS	current
	DESCRIPTION ""
			::= { mbus40 42 }

mbus40Value12		OBJECT-TYPE
			SYNTAX	INTEGER
			ACCESS	read-only
			STATUS	current
	DESCRIPTION ""
			::= { mbus40 43 }

mbus40VIF13		OBJECT-TYPE
			SYNTAX	INTEGER
			ACCESS	read-only
			STATUS	current
	DESCRIPTION ""
			::= { mbus40 44 }

mbus40Value13		OBJECT-TYPE
			SYNTAX	INTEGER
			ACCESS	read-only
			STATUS	current
	DESCRIPTION ""
			::= { mbus40 45 }

mbus40VIF14		OBJECT-TYPE
			SYNTAX	INTEGER
			ACCESS	read-only
			STATUS	current
	DESCRIPTION ""
			::= { mbus40 46 }

mbus40Value14		OBJECT-TYPE
			SYNTAX	INTEGER
			ACCESS	read-only
			STATUS	current
	DESCRIPTION ""
			::= { mbus40 47 }

mbus40VIF15		OBJECT-TYPE
			SYNTAX	INTEGER
			ACCESS	read-only
			STATUS	current
	DESCRIPTION ""
			::= { mbus40 48 }

mbus40Value15		OBJECT-TYPE
			SYNTAX	INTEGER
			ACCESS	read-only
			STATUS	current
	DESCRIPTION ""
			::= { mbus40 49 }

mbus40VIF16		OBJECT-TYPE
			SYNTAX	INTEGER
			ACCESS	read-only
			STATUS	current
	DESCRIPTION ""
			::= { mbus40 50 }

mbus40Value16		OBJECT-TYPE
			SYNTAX	INTEGER
			ACCESS	read-only
			STATUS	current
	DESCRIPTION ""
			::= { mbus40 51 }

mbus40VIF17		OBJECT-TYPE
			SYNTAX	INTEGER
			ACCESS	read-only
			STATUS	current
	DESCRIPTION ""
			::= { mbus40 52 }

mbus40Value17		OBJECT-TYPE
			SYNTAX	INTEGER
			ACCESS	read-only
			STATUS	current
	DESCRIPTION ""
			::= { mbus40 53 }

mbus40VIF18		OBJECT-TYPE
			SYNTAX	INTEGER
			ACCESS	read-only
			STATUS	current
	DESCRIPTION ""
			::= { mbus40 54 }

mbus40Value18		OBJECT-TYPE
			SYNTAX	INTEGER
			ACCESS	read-only
			STATUS	current
	DESCRIPTION ""
			::= { mbus40 55 }

mbus40VIF19		OBJECT-TYPE
			SYNTAX	INTEGER
			ACCESS	read-only
			STATUS	current
	DESCRIPTION ""
			::= { mbus40 56 }

mbus40Value19		OBJECT-TYPE
			SYNTAX	INTEGER
			ACCESS	read-only
			STATUS	current
	DESCRIPTION ""
			::= { mbus40 57 }

mbus40VIF1A		OBJECT-TYPE
			SYNTAX	INTEGER
			ACCESS	read-only
			STATUS	current
	DESCRIPTION ""
			::= { mbus40 58 }

mbus40Value1A		OBJECT-TYPE
			SYNTAX	INTEGER
			ACCESS	read-only
			STATUS	current
	DESCRIPTION ""
			::= { mbus40 59 }

mbus40VIF1B		OBJECT-TYPE
			SYNTAX	INTEGER
			ACCESS	read-only
			STATUS	current
	DESCRIPTION ""
			::= { mbus40 60 }

mbus40Value1B		OBJECT-TYPE
			SYNTAX	INTEGER
			ACCESS	read-only
			STATUS	current
	DESCRIPTION ""
			::= { mbus40 61 }

mbus40VIF1C		OBJECT-TYPE
			SYNTAX	INTEGER
			ACCESS	read-only
			STATUS	current
	DESCRIPTION ""
			::= { mbus40 62 }

mbus40Value1C		OBJECT-TYPE
			SYNTAX	INTEGER
			ACCESS	read-only
			STATUS	current
	DESCRIPTION ""
			::= { mbus40 63 }

mbus40VIF1D		OBJECT-TYPE
			SYNTAX	INTEGER
			ACCESS	read-only
			STATUS	current
	DESCRIPTION ""
			::= { mbus40 64 }

mbus40Value1D		OBJECT-TYPE
			SYNTAX	INTEGER
			ACCESS	read-only
			STATUS	current
	DESCRIPTION ""
			::= { mbus40 65 }

mbus40VIF1E		OBJECT-TYPE
			SYNTAX	INTEGER
			ACCESS	read-only
			STATUS	current
	DESCRIPTION ""
			::= { mbus40 66 }

mbus40Value1E		OBJECT-TYPE
			SYNTAX	INTEGER
			ACCESS	read-only
			STATUS	current
	DESCRIPTION ""
			::= { mbus40 67 }

mbus40VIF1F		OBJECT-TYPE
			SYNTAX	INTEGER
			ACCESS	read-only
			STATUS	current
	DESCRIPTION ""
			::= { mbus40 68 }

mbus40Value1F		OBJECT-TYPE
			SYNTAX	INTEGER
			ACCESS	read-only
			STATUS	current
	DESCRIPTION ""
			::= { mbus40 69 }

mbus40VIF20		OBJECT-TYPE
			SYNTAX	INTEGER
			ACCESS	read-only
			STATUS	current
	DESCRIPTION ""
			::= { mbus40 70 }

mbus40Value20		OBJECT-TYPE
			SYNTAX	INTEGER
			ACCESS	read-only
			STATUS	current
	DESCRIPTION ""
			::= { mbus40 71 }

mbus40VIF21		OBJECT-TYPE
			SYNTAX	INTEGER
			ACCESS	read-only
			STATUS	current
	DESCRIPTION ""
			::= { mbus40 72 }

mbus40Value21		OBJECT-TYPE
			SYNTAX	INTEGER
			ACCESS	read-only
			STATUS	current
	DESCRIPTION ""
			::= { mbus40 73 }

mbus40VIF22		OBJECT-TYPE
			SYNTAX	INTEGER
			ACCESS	read-only
			STATUS	current
	DESCRIPTION ""
			::= { mbus40 74 }

mbus40Value22		OBJECT-TYPE
			SYNTAX	INTEGER
			ACCESS	read-only
			STATUS	current
	DESCRIPTION ""
			::= { mbus40 75 }

mbus40VIF23		OBJECT-TYPE
			SYNTAX	INTEGER
			ACCESS	read-only
			STATUS	current
	DESCRIPTION ""
			::= { mbus40 76 }

mbus40Value23		OBJECT-TYPE
			SYNTAX	INTEGER
			ACCESS	read-only
			STATUS	current
	DESCRIPTION ""
			::= { mbus40 77 }

mbus40VIF24		OBJECT-TYPE
			SYNTAX	INTEGER
			ACCESS	read-only
			STATUS	current
	DESCRIPTION ""
			::= { mbus40 78 }

mbus40Value24		OBJECT-TYPE
			SYNTAX	INTEGER
			ACCESS	read-only
			STATUS	current
	DESCRIPTION ""
			::= { mbus40 79 }

mbus40VIF25		OBJECT-TYPE
			SYNTAX	INTEGER
			ACCESS	read-only
			STATUS	current
	DESCRIPTION ""
			::= { mbus40 80 }

mbus40Value25		OBJECT-TYPE
			SYNTAX	INTEGER
			ACCESS	read-only
			STATUS	current
	DESCRIPTION ""
			::= { mbus40 81 }

mbus40VIF26		OBJECT-TYPE
			SYNTAX	INTEGER
			ACCESS	read-only
			STATUS	current
	DESCRIPTION ""
			::= { mbus40 82 }

mbus40Value26		OBJECT-TYPE
			SYNTAX	INTEGER
			ACCESS	read-only
			STATUS	current
	DESCRIPTION ""
			::= { mbus40 83 }

mbus40VIF27		OBJECT-TYPE
			SYNTAX	INTEGER
			ACCESS	read-only
			STATUS	current
	DESCRIPTION ""
			::= { mbus40 84 }

mbus40Value27		OBJECT-TYPE
			SYNTAX	INTEGER
			ACCESS	read-only
			STATUS	current
	DESCRIPTION ""
			::= { mbus40 85 }

mbus40VIF28		OBJECT-TYPE
			SYNTAX	INTEGER
			ACCESS	read-only
			STATUS	current
	DESCRIPTION ""
			::= { mbus40 86 }

mbus40Value28		OBJECT-TYPE
			SYNTAX	INTEGER
			ACCESS	read-only
			STATUS	current
	DESCRIPTION ""
			::= { mbus40 87 }

mbus40VIF29		OBJECT-TYPE
			SYNTAX	INTEGER
			ACCESS	read-only
			STATUS	current
	DESCRIPTION ""
			::= { mbus40 88 }

mbus40Value29		OBJECT-TYPE
			SYNTAX	INTEGER
			ACCESS	read-only
			STATUS	current
	DESCRIPTION ""
			::= { mbus40 89 }

mbus40VIF2A		OBJECT-TYPE
			SYNTAX	INTEGER
			ACCESS	read-only
			STATUS	current
	DESCRIPTION ""
			::= { mbus40 90 }

mbus40Value2A		OBJECT-TYPE
			SYNTAX	INTEGER
			ACCESS	read-only
			STATUS	current
	DESCRIPTION ""
			::= { mbus40 91 }

mbus40VIF2B		OBJECT-TYPE
			SYNTAX	INTEGER
			ACCESS	read-only
			STATUS	current
	DESCRIPTION ""
			::= { mbus40 92 }

mbus40Value2B		OBJECT-TYPE
			SYNTAX	INTEGER
			ACCESS	read-only
			STATUS	current
	DESCRIPTION ""
			::= { mbus40 93 }

mbus40VIF2C		OBJECT-TYPE
			SYNTAX	INTEGER
			ACCESS	read-only
			STATUS	current
	DESCRIPTION ""
			::= { mbus40 94 }

mbus40Value2C		OBJECT-TYPE
			SYNTAX	INTEGER
			ACCESS	read-only
			STATUS	current
	DESCRIPTION ""
			::= { mbus40 95 }

mbus40VIF2D		OBJECT-TYPE
			SYNTAX	INTEGER
			ACCESS	read-only
			STATUS	current
	DESCRIPTION ""
			::= { mbus40 96 }

mbus40Value2D		OBJECT-TYPE
			SYNTAX	INTEGER
			ACCESS	read-only
			STATUS	current
	DESCRIPTION ""
			::= { mbus40 97 }

mbus40VIF2E		OBJECT-TYPE
			SYNTAX	INTEGER
			ACCESS	read-only
			STATUS	current
	DESCRIPTION ""
			::= { mbus40 98 }

mbus40Value2E		OBJECT-TYPE
			SYNTAX	INTEGER
			ACCESS	read-only
			STATUS	current
	DESCRIPTION ""
			::= { mbus40 99 }

mbus40VIF2F		OBJECT-TYPE
			SYNTAX	INTEGER
			ACCESS	read-only
			STATUS	current
	DESCRIPTION ""
			::= { mbus40 100 }

mbus40Value2F		OBJECT-TYPE
			SYNTAX	INTEGER
			ACCESS	read-only
			STATUS	current
	DESCRIPTION ""
			::= { mbus40 101 }

mbus41			OBJECT IDENTIFIER ::= { mbus 65 }

mbus41IdNumber		OBJECT-TYPE
			SYNTAX	Gauge
			ACCESS	read-only
			STATUS	current
	DESCRIPTION ""
			::= { mbus41 1 }

mbus41Manufacturer	OBJECT-TYPE
			SYNTAX	Gauge
			ACCESS	read-only
			STATUS	current
	DESCRIPTION ""
			::= { mbus41 2 }

mbus41Version		OBJECT-TYPE
			SYNTAX	Gauge
			ACCESS	read-only
			STATUS	current
	DESCRIPTION ""
			::= { mbus41 3 }

mbus41Medium		OBJECT-TYPE
			SYNTAX	Gauge
			ACCESS	read-only
			STATUS	current
	DESCRIPTION ""
			::= { mbus41 4 }

mbus41Status		OBJECT-TYPE
			SYNTAX	Gauge
			ACCESS	read-only
			STATUS	current
	DESCRIPTION ""
			::= { mbus41 5 }

mbus41VIF00		OBJECT-TYPE
			SYNTAX	INTEGER
			ACCESS	read-only
			STATUS	current
	DESCRIPTION ""
			::= { mbus41 6 }

mbus41Value00		OBJECT-TYPE
			SYNTAX	INTEGER
			ACCESS	read-only
			STATUS	current
	DESCRIPTION ""
			::= { mbus41 7 }

mbus41VIF01		OBJECT-TYPE
			SYNTAX	INTEGER
			ACCESS	read-only
			STATUS	current
	DESCRIPTION ""
			::= { mbus41 8 }

mbus41Value01		OBJECT-TYPE
			SYNTAX	INTEGER
			ACCESS	read-only
			STATUS	current
	DESCRIPTION ""
			::= { mbus41 9 }

mbus41VIF02		OBJECT-TYPE
			SYNTAX	INTEGER
			ACCESS	read-only
			STATUS	current
	DESCRIPTION ""
			::= { mbus41 10 }

mbus41Value02		OBJECT-TYPE
			SYNTAX	INTEGER
			ACCESS	read-only
			STATUS	current
	DESCRIPTION ""
			::= { mbus41 11 }

mbus41VIF03		OBJECT-TYPE
			SYNTAX	INTEGER
			ACCESS	read-only
			STATUS	current
	DESCRIPTION ""
			::= { mbus41 12 }

mbus41Value03		OBJECT-TYPE
			SYNTAX	INTEGER
			ACCESS	read-only
			STATUS	current
	DESCRIPTION ""
			::= { mbus41 13 }

mbus41VIF04		OBJECT-TYPE
			SYNTAX	INTEGER
			ACCESS	read-only
			STATUS	current
	DESCRIPTION ""
			::= { mbus41 14 }

mbus41Value04		OBJECT-TYPE
			SYNTAX	INTEGER
			ACCESS	read-only
			STATUS	current
	DESCRIPTION ""
			::= { mbus41 15 }

mbus41VIF05		OBJECT-TYPE
			SYNTAX	INTEGER
			ACCESS	read-only
			STATUS	current
	DESCRIPTION ""
			::= { mbus41 16 }

mbus41Value05		OBJECT-TYPE
			SYNTAX	INTEGER
			ACCESS	read-only
			STATUS	current
	DESCRIPTION ""
			::= { mbus41 17 }

mbus41VIF06		OBJECT-TYPE
			SYNTAX	INTEGER
			ACCESS	read-only
			STATUS	current
	DESCRIPTION ""
			::= { mbus41 18 }

mbus41Value06		OBJECT-TYPE
			SYNTAX	INTEGER
			ACCESS	read-only
			STATUS	current
	DESCRIPTION ""
			::= { mbus41 19 }

mbus41VIF07		OBJECT-TYPE
			SYNTAX	INTEGER
			ACCESS	read-only
			STATUS	current
	DESCRIPTION ""
			::= { mbus41 20 }

mbus41Value07		OBJECT-TYPE
			SYNTAX	INTEGER
			ACCESS	read-only
			STATUS	current
	DESCRIPTION ""
			::= { mbus41 21 }

mbus41VIF08		OBJECT-TYPE
			SYNTAX	INTEGER
			ACCESS	read-only
			STATUS	current
	DESCRIPTION ""
			::= { mbus41 22 }

mbus41Value08		OBJECT-TYPE
			SYNTAX	INTEGER
			ACCESS	read-only
			STATUS	current
	DESCRIPTION ""
			::= { mbus41 23 }

mbus41VIF09		OBJECT-TYPE
			SYNTAX	INTEGER
			ACCESS	read-only
			STATUS	current
	DESCRIPTION ""
			::= { mbus41 24 }

mbus41Value09		OBJECT-TYPE
			SYNTAX	INTEGER
			ACCESS	read-only
			STATUS	current
	DESCRIPTION ""
			::= { mbus41 25 }

mbus41VIF0A		OBJECT-TYPE
			SYNTAX	INTEGER
			ACCESS	read-only
			STATUS	current
	DESCRIPTION ""
			::= { mbus41 26 }

mbus41Value0A		OBJECT-TYPE
			SYNTAX	INTEGER
			ACCESS	read-only
			STATUS	current
	DESCRIPTION ""
			::= { mbus41 27 }

mbus41VIF0B		OBJECT-TYPE
			SYNTAX	INTEGER
			ACCESS	read-only
			STATUS	current
	DESCRIPTION ""
			::= { mbus41 28 }

mbus41Value0B		OBJECT-TYPE
			SYNTAX	INTEGER
			ACCESS	read-only
			STATUS	current
	DESCRIPTION ""
			::= { mbus41 29 }

mbus41VIF0C		OBJECT-TYPE
			SYNTAX	INTEGER
			ACCESS	read-only
			STATUS	current
	DESCRIPTION ""
			::= { mbus41 30 }

mbus41Value0C		OBJECT-TYPE
			SYNTAX	INTEGER
			ACCESS	read-only
			STATUS	current
	DESCRIPTION ""
			::= { mbus41 31 }

mbus41VIF0D		OBJECT-TYPE
			SYNTAX	INTEGER
			ACCESS	read-only
			STATUS	current
	DESCRIPTION ""
			::= { mbus41 32 }

mbus41Value0D		OBJECT-TYPE
			SYNTAX	INTEGER
			ACCESS	read-only
			STATUS	current
	DESCRIPTION ""
			::= { mbus41 33 }

mbus41VIF0E		OBJECT-TYPE
			SYNTAX	INTEGER
			ACCESS	read-only
			STATUS	current
	DESCRIPTION ""
			::= { mbus41 34 }

mbus41Value0E		OBJECT-TYPE
			SYNTAX	INTEGER
			ACCESS	read-only
			STATUS	current
	DESCRIPTION ""
			::= { mbus41 35 }

mbus41VIF0F		OBJECT-TYPE
			SYNTAX	INTEGER
			ACCESS	read-only
			STATUS	current
	DESCRIPTION ""
			::= { mbus41 36 }

mbus41Value0F		OBJECT-TYPE
			SYNTAX	INTEGER
			ACCESS	read-only
			STATUS	current
	DESCRIPTION ""
			::= { mbus41 37 }

mbus41VIF10		OBJECT-TYPE
			SYNTAX	INTEGER
			ACCESS	read-only
			STATUS	current
	DESCRIPTION ""
			::= { mbus41 38 }

mbus41Value10		OBJECT-TYPE
			SYNTAX	INTEGER
			ACCESS	read-only
			STATUS	current
	DESCRIPTION ""
			::= { mbus41 39 }

mbus41VIF11		OBJECT-TYPE
			SYNTAX	INTEGER
			ACCESS	read-only
			STATUS	current
	DESCRIPTION ""
			::= { mbus41 40 }

mbus41Value11		OBJECT-TYPE
			SYNTAX	INTEGER
			ACCESS	read-only
			STATUS	current
	DESCRIPTION ""
			::= { mbus41 41 }

mbus41VIF12		OBJECT-TYPE
			SYNTAX	INTEGER
			ACCESS	read-only
			STATUS	current
	DESCRIPTION ""
			::= { mbus41 42 }

mbus41Value12		OBJECT-TYPE
			SYNTAX	INTEGER
			ACCESS	read-only
			STATUS	current
	DESCRIPTION ""
			::= { mbus41 43 }

mbus41VIF13		OBJECT-TYPE
			SYNTAX	INTEGER
			ACCESS	read-only
			STATUS	current
	DESCRIPTION ""
			::= { mbus41 44 }

mbus41Value13		OBJECT-TYPE
			SYNTAX	INTEGER
			ACCESS	read-only
			STATUS	current
	DESCRIPTION ""
			::= { mbus41 45 }

mbus41VIF14		OBJECT-TYPE
			SYNTAX	INTEGER
			ACCESS	read-only
			STATUS	current
	DESCRIPTION ""
			::= { mbus41 46 }

mbus41Value14		OBJECT-TYPE
			SYNTAX	INTEGER
			ACCESS	read-only
			STATUS	current
	DESCRIPTION ""
			::= { mbus41 47 }

mbus41VIF15		OBJECT-TYPE
			SYNTAX	INTEGER
			ACCESS	read-only
			STATUS	current
	DESCRIPTION ""
			::= { mbus41 48 }

mbus41Value15		OBJECT-TYPE
			SYNTAX	INTEGER
			ACCESS	read-only
			STATUS	current
	DESCRIPTION ""
			::= { mbus41 49 }

mbus41VIF16		OBJECT-TYPE
			SYNTAX	INTEGER
			ACCESS	read-only
			STATUS	current
	DESCRIPTION ""
			::= { mbus41 50 }

mbus41Value16		OBJECT-TYPE
			SYNTAX	INTEGER
			ACCESS	read-only
			STATUS	current
	DESCRIPTION ""
			::= { mbus41 51 }

mbus41VIF17		OBJECT-TYPE
			SYNTAX	INTEGER
			ACCESS	read-only
			STATUS	current
	DESCRIPTION ""
			::= { mbus41 52 }

mbus41Value17		OBJECT-TYPE
			SYNTAX	INTEGER
			ACCESS	read-only
			STATUS	current
	DESCRIPTION ""
			::= { mbus41 53 }

mbus41VIF18		OBJECT-TYPE
			SYNTAX	INTEGER
			ACCESS	read-only
			STATUS	current
	DESCRIPTION ""
			::= { mbus41 54 }

mbus41Value18		OBJECT-TYPE
			SYNTAX	INTEGER
			ACCESS	read-only
			STATUS	current
	DESCRIPTION ""
			::= { mbus41 55 }

mbus41VIF19		OBJECT-TYPE
			SYNTAX	INTEGER
			ACCESS	read-only
			STATUS	current
	DESCRIPTION ""
			::= { mbus41 56 }

mbus41Value19		OBJECT-TYPE
			SYNTAX	INTEGER
			ACCESS	read-only
			STATUS	current
	DESCRIPTION ""
			::= { mbus41 57 }

mbus41VIF1A		OBJECT-TYPE
			SYNTAX	INTEGER
			ACCESS	read-only
			STATUS	current
	DESCRIPTION ""
			::= { mbus41 58 }

mbus41Value1A		OBJECT-TYPE
			SYNTAX	INTEGER
			ACCESS	read-only
			STATUS	current
	DESCRIPTION ""
			::= { mbus41 59 }

mbus41VIF1B		OBJECT-TYPE
			SYNTAX	INTEGER
			ACCESS	read-only
			STATUS	current
	DESCRIPTION ""
			::= { mbus41 60 }

mbus41Value1B		OBJECT-TYPE
			SYNTAX	INTEGER
			ACCESS	read-only
			STATUS	current
	DESCRIPTION ""
			::= { mbus41 61 }

mbus41VIF1C		OBJECT-TYPE
			SYNTAX	INTEGER
			ACCESS	read-only
			STATUS	current
	DESCRIPTION ""
			::= { mbus41 62 }

mbus41Value1C		OBJECT-TYPE
			SYNTAX	INTEGER
			ACCESS	read-only
			STATUS	current
	DESCRIPTION ""
			::= { mbus41 63 }

mbus41VIF1D		OBJECT-TYPE
			SYNTAX	INTEGER
			ACCESS	read-only
			STATUS	current
	DESCRIPTION ""
			::= { mbus41 64 }

mbus41Value1D		OBJECT-TYPE
			SYNTAX	INTEGER
			ACCESS	read-only
			STATUS	current
	DESCRIPTION ""
			::= { mbus41 65 }

mbus41VIF1E		OBJECT-TYPE
			SYNTAX	INTEGER
			ACCESS	read-only
			STATUS	current
	DESCRIPTION ""
			::= { mbus41 66 }

mbus41Value1E		OBJECT-TYPE
			SYNTAX	INTEGER
			ACCESS	read-only
			STATUS	current
	DESCRIPTION ""
			::= { mbus41 67 }

mbus41VIF1F		OBJECT-TYPE
			SYNTAX	INTEGER
			ACCESS	read-only
			STATUS	current
	DESCRIPTION ""
			::= { mbus41 68 }

mbus41Value1F		OBJECT-TYPE
			SYNTAX	INTEGER
			ACCESS	read-only
			STATUS	current
	DESCRIPTION ""
			::= { mbus41 69 }

mbus41VIF20		OBJECT-TYPE
			SYNTAX	INTEGER
			ACCESS	read-only
			STATUS	current
	DESCRIPTION ""
			::= { mbus41 70 }

mbus41Value20		OBJECT-TYPE
			SYNTAX	INTEGER
			ACCESS	read-only
			STATUS	current
	DESCRIPTION ""
			::= { mbus41 71 }

mbus41VIF21		OBJECT-TYPE
			SYNTAX	INTEGER
			ACCESS	read-only
			STATUS	current
	DESCRIPTION ""
			::= { mbus41 72 }

mbus41Value21		OBJECT-TYPE
			SYNTAX	INTEGER
			ACCESS	read-only
			STATUS	current
	DESCRIPTION ""
			::= { mbus41 73 }

mbus41VIF22		OBJECT-TYPE
			SYNTAX	INTEGER
			ACCESS	read-only
			STATUS	current
	DESCRIPTION ""
			::= { mbus41 74 }

mbus41Value22		OBJECT-TYPE
			SYNTAX	INTEGER
			ACCESS	read-only
			STATUS	current
	DESCRIPTION ""
			::= { mbus41 75 }

mbus41VIF23		OBJECT-TYPE
			SYNTAX	INTEGER
			ACCESS	read-only
			STATUS	current
	DESCRIPTION ""
			::= { mbus41 76 }

mbus41Value23		OBJECT-TYPE
			SYNTAX	INTEGER
			ACCESS	read-only
			STATUS	current
	DESCRIPTION ""
			::= { mbus41 77 }

mbus41VIF24		OBJECT-TYPE
			SYNTAX	INTEGER
			ACCESS	read-only
			STATUS	current
	DESCRIPTION ""
			::= { mbus41 78 }

mbus41Value24		OBJECT-TYPE
			SYNTAX	INTEGER
			ACCESS	read-only
			STATUS	current
	DESCRIPTION ""
			::= { mbus41 79 }

mbus41VIF25		OBJECT-TYPE
			SYNTAX	INTEGER
			ACCESS	read-only
			STATUS	current
	DESCRIPTION ""
			::= { mbus41 80 }

mbus41Value25		OBJECT-TYPE
			SYNTAX	INTEGER
			ACCESS	read-only
			STATUS	current
	DESCRIPTION ""
			::= { mbus41 81 }

mbus41VIF26		OBJECT-TYPE
			SYNTAX	INTEGER
			ACCESS	read-only
			STATUS	current
	DESCRIPTION ""
			::= { mbus41 82 }

mbus41Value26		OBJECT-TYPE
			SYNTAX	INTEGER
			ACCESS	read-only
			STATUS	current
	DESCRIPTION ""
			::= { mbus41 83 }

mbus41VIF27		OBJECT-TYPE
			SYNTAX	INTEGER
			ACCESS	read-only
			STATUS	current
	DESCRIPTION ""
			::= { mbus41 84 }

mbus41Value27		OBJECT-TYPE
			SYNTAX	INTEGER
			ACCESS	read-only
			STATUS	current
	DESCRIPTION ""
			::= { mbus41 85 }

mbus41VIF28		OBJECT-TYPE
			SYNTAX	INTEGER
			ACCESS	read-only
			STATUS	current
	DESCRIPTION ""
			::= { mbus41 86 }

mbus41Value28		OBJECT-TYPE
			SYNTAX	INTEGER
			ACCESS	read-only
			STATUS	current
	DESCRIPTION ""
			::= { mbus41 87 }

mbus41VIF29		OBJECT-TYPE
			SYNTAX	INTEGER
			ACCESS	read-only
			STATUS	current
	DESCRIPTION ""
			::= { mbus41 88 }

mbus41Value29		OBJECT-TYPE
			SYNTAX	INTEGER
			ACCESS	read-only
			STATUS	current
	DESCRIPTION ""
			::= { mbus41 89 }

mbus41VIF2A		OBJECT-TYPE
			SYNTAX	INTEGER
			ACCESS	read-only
			STATUS	current
	DESCRIPTION ""
			::= { mbus41 90 }

mbus41Value2A		OBJECT-TYPE
			SYNTAX	INTEGER
			ACCESS	read-only
			STATUS	current
	DESCRIPTION ""
			::= { mbus41 91 }

mbus41VIF2B		OBJECT-TYPE
			SYNTAX	INTEGER
			ACCESS	read-only
			STATUS	current
	DESCRIPTION ""
			::= { mbus41 92 }

mbus41Value2B		OBJECT-TYPE
			SYNTAX	INTEGER
			ACCESS	read-only
			STATUS	current
	DESCRIPTION ""
			::= { mbus41 93 }

mbus41VIF2C		OBJECT-TYPE
			SYNTAX	INTEGER
			ACCESS	read-only
			STATUS	current
	DESCRIPTION ""
			::= { mbus41 94 }

mbus41Value2C		OBJECT-TYPE
			SYNTAX	INTEGER
			ACCESS	read-only
			STATUS	current
	DESCRIPTION ""
			::= { mbus41 95 }

mbus41VIF2D		OBJECT-TYPE
			SYNTAX	INTEGER
			ACCESS	read-only
			STATUS	current
	DESCRIPTION ""
			::= { mbus41 96 }

mbus41Value2D		OBJECT-TYPE
			SYNTAX	INTEGER
			ACCESS	read-only
			STATUS	current
	DESCRIPTION ""
			::= { mbus41 97 }

mbus41VIF2E		OBJECT-TYPE
			SYNTAX	INTEGER
			ACCESS	read-only
			STATUS	current
	DESCRIPTION ""
			::= { mbus41 98 }

mbus41Value2E		OBJECT-TYPE
			SYNTAX	INTEGER
			ACCESS	read-only
			STATUS	current
	DESCRIPTION ""
			::= { mbus41 99 }

mbus41VIF2F		OBJECT-TYPE
			SYNTAX	INTEGER
			ACCESS	read-only
			STATUS	current
	DESCRIPTION ""
			::= { mbus41 100 }

mbus41Value2F		OBJECT-TYPE
			SYNTAX	INTEGER
			ACCESS	read-only
			STATUS	current
	DESCRIPTION ""
			::= { mbus41 101 }

mbus42			OBJECT IDENTIFIER ::= { mbus 66 }

mbus42IdNumber		OBJECT-TYPE
			SYNTAX	Gauge
			ACCESS	read-only
			STATUS	current
	DESCRIPTION ""
			::= { mbus42 1 }

mbus42Manufacturer	OBJECT-TYPE
			SYNTAX	Gauge
			ACCESS	read-only
			STATUS	current
	DESCRIPTION ""
			::= { mbus42 2 }

mbus42Version		OBJECT-TYPE
			SYNTAX	Gauge
			ACCESS	read-only
			STATUS	current
	DESCRIPTION ""
			::= { mbus42 3 }

mbus42Medium		OBJECT-TYPE
			SYNTAX	Gauge
			ACCESS	read-only
			STATUS	current
	DESCRIPTION ""
			::= { mbus42 4 }

mbus42Status		OBJECT-TYPE
			SYNTAX	Gauge
			ACCESS	read-only
			STATUS	current
	DESCRIPTION ""
			::= { mbus42 5 }

mbus42VIF00		OBJECT-TYPE
			SYNTAX	INTEGER
			ACCESS	read-only
			STATUS	current
	DESCRIPTION ""
			::= { mbus42 6 }

mbus42Value00		OBJECT-TYPE
			SYNTAX	INTEGER
			ACCESS	read-only
			STATUS	current
	DESCRIPTION ""
			::= { mbus42 7 }

mbus42VIF01		OBJECT-TYPE
			SYNTAX	INTEGER
			ACCESS	read-only
			STATUS	current
	DESCRIPTION ""
			::= { mbus42 8 }

mbus42Value01		OBJECT-TYPE
			SYNTAX	INTEGER
			ACCESS	read-only
			STATUS	current
	DESCRIPTION ""
			::= { mbus42 9 }

mbus42VIF02		OBJECT-TYPE
			SYNTAX	INTEGER
			ACCESS	read-only
			STATUS	current
	DESCRIPTION ""
			::= { mbus42 10 }

mbus42Value02		OBJECT-TYPE
			SYNTAX	INTEGER
			ACCESS	read-only
			STATUS	current
	DESCRIPTION ""
			::= { mbus42 11 }

mbus42VIF03		OBJECT-TYPE
			SYNTAX	INTEGER
			ACCESS	read-only
			STATUS	current
	DESCRIPTION ""
			::= { mbus42 12 }

mbus42Value03		OBJECT-TYPE
			SYNTAX	INTEGER
			ACCESS	read-only
			STATUS	current
	DESCRIPTION ""
			::= { mbus42 13 }

mbus42VIF04		OBJECT-TYPE
			SYNTAX	INTEGER
			ACCESS	read-only
			STATUS	current
	DESCRIPTION ""
			::= { mbus42 14 }

mbus42Value04		OBJECT-TYPE
			SYNTAX	INTEGER
			ACCESS	read-only
			STATUS	current
	DESCRIPTION ""
			::= { mbus42 15 }

mbus42VIF05		OBJECT-TYPE
			SYNTAX	INTEGER
			ACCESS	read-only
			STATUS	current
	DESCRIPTION ""
			::= { mbus42 16 }

mbus42Value05		OBJECT-TYPE
			SYNTAX	INTEGER
			ACCESS	read-only
			STATUS	current
	DESCRIPTION ""
			::= { mbus42 17 }

mbus42VIF06		OBJECT-TYPE
			SYNTAX	INTEGER
			ACCESS	read-only
			STATUS	current
	DESCRIPTION ""
			::= { mbus42 18 }

mbus42Value06		OBJECT-TYPE
			SYNTAX	INTEGER
			ACCESS	read-only
			STATUS	current
	DESCRIPTION ""
			::= { mbus42 19 }

mbus42VIF07		OBJECT-TYPE
			SYNTAX	INTEGER
			ACCESS	read-only
			STATUS	current
	DESCRIPTION ""
			::= { mbus42 20 }

mbus42Value07		OBJECT-TYPE
			SYNTAX	INTEGER
			ACCESS	read-only
			STATUS	current
	DESCRIPTION ""
			::= { mbus42 21 }

mbus42VIF08		OBJECT-TYPE
			SYNTAX	INTEGER
			ACCESS	read-only
			STATUS	current
	DESCRIPTION ""
			::= { mbus42 22 }

mbus42Value08		OBJECT-TYPE
			SYNTAX	INTEGER
			ACCESS	read-only
			STATUS	current
	DESCRIPTION ""
			::= { mbus42 23 }

mbus42VIF09		OBJECT-TYPE
			SYNTAX	INTEGER
			ACCESS	read-only
			STATUS	current
	DESCRIPTION ""
			::= { mbus42 24 }

mbus42Value09		OBJECT-TYPE
			SYNTAX	INTEGER
			ACCESS	read-only
			STATUS	current
	DESCRIPTION ""
			::= { mbus42 25 }

mbus42VIF0A		OBJECT-TYPE
			SYNTAX	INTEGER
			ACCESS	read-only
			STATUS	current
	DESCRIPTION ""
			::= { mbus42 26 }

mbus42Value0A		OBJECT-TYPE
			SYNTAX	INTEGER
			ACCESS	read-only
			STATUS	current
	DESCRIPTION ""
			::= { mbus42 27 }

mbus42VIF0B		OBJECT-TYPE
			SYNTAX	INTEGER
			ACCESS	read-only
			STATUS	current
	DESCRIPTION ""
			::= { mbus42 28 }

mbus42Value0B		OBJECT-TYPE
			SYNTAX	INTEGER
			ACCESS	read-only
			STATUS	current
	DESCRIPTION ""
			::= { mbus42 29 }

mbus42VIF0C		OBJECT-TYPE
			SYNTAX	INTEGER
			ACCESS	read-only
			STATUS	current
	DESCRIPTION ""
			::= { mbus42 30 }

mbus42Value0C		OBJECT-TYPE
			SYNTAX	INTEGER
			ACCESS	read-only
			STATUS	current
	DESCRIPTION ""
			::= { mbus42 31 }

mbus42VIF0D		OBJECT-TYPE
			SYNTAX	INTEGER
			ACCESS	read-only
			STATUS	current
	DESCRIPTION ""
			::= { mbus42 32 }

mbus42Value0D		OBJECT-TYPE
			SYNTAX	INTEGER
			ACCESS	read-only
			STATUS	current
	DESCRIPTION ""
			::= { mbus42 33 }

mbus42VIF0E		OBJECT-TYPE
			SYNTAX	INTEGER
			ACCESS	read-only
			STATUS	current
	DESCRIPTION ""
			::= { mbus42 34 }

mbus42Value0E		OBJECT-TYPE
			SYNTAX	INTEGER
			ACCESS	read-only
			STATUS	current
	DESCRIPTION ""
			::= { mbus42 35 }

mbus42VIF0F		OBJECT-TYPE
			SYNTAX	INTEGER
			ACCESS	read-only
			STATUS	current
	DESCRIPTION ""
			::= { mbus42 36 }

mbus42Value0F		OBJECT-TYPE
			SYNTAX	INTEGER
			ACCESS	read-only
			STATUS	current
	DESCRIPTION ""
			::= { mbus42 37 }

mbus42VIF10		OBJECT-TYPE
			SYNTAX	INTEGER
			ACCESS	read-only
			STATUS	current
	DESCRIPTION ""
			::= { mbus42 38 }

mbus42Value10		OBJECT-TYPE
			SYNTAX	INTEGER
			ACCESS	read-only
			STATUS	current
	DESCRIPTION ""
			::= { mbus42 39 }

mbus42VIF11		OBJECT-TYPE
			SYNTAX	INTEGER
			ACCESS	read-only
			STATUS	current
	DESCRIPTION ""
			::= { mbus42 40 }

mbus42Value11		OBJECT-TYPE
			SYNTAX	INTEGER
			ACCESS	read-only
			STATUS	current
	DESCRIPTION ""
			::= { mbus42 41 }

mbus42VIF12		OBJECT-TYPE
			SYNTAX	INTEGER
			ACCESS	read-only
			STATUS	current
	DESCRIPTION ""
			::= { mbus42 42 }

mbus42Value12		OBJECT-TYPE
			SYNTAX	INTEGER
			ACCESS	read-only
			STATUS	current
	DESCRIPTION ""
			::= { mbus42 43 }

mbus42VIF13		OBJECT-TYPE
			SYNTAX	INTEGER
			ACCESS	read-only
			STATUS	current
	DESCRIPTION ""
			::= { mbus42 44 }

mbus42Value13		OBJECT-TYPE
			SYNTAX	INTEGER
			ACCESS	read-only
			STATUS	current
	DESCRIPTION ""
			::= { mbus42 45 }

mbus42VIF14		OBJECT-TYPE
			SYNTAX	INTEGER
			ACCESS	read-only
			STATUS	current
	DESCRIPTION ""
			::= { mbus42 46 }

mbus42Value14		OBJECT-TYPE
			SYNTAX	INTEGER
			ACCESS	read-only
			STATUS	current
	DESCRIPTION ""
			::= { mbus42 47 }

mbus42VIF15		OBJECT-TYPE
			SYNTAX	INTEGER
			ACCESS	read-only
			STATUS	current
	DESCRIPTION ""
			::= { mbus42 48 }

mbus42Value15		OBJECT-TYPE
			SYNTAX	INTEGER
			ACCESS	read-only
			STATUS	current
	DESCRIPTION ""
			::= { mbus42 49 }

mbus42VIF16		OBJECT-TYPE
			SYNTAX	INTEGER
			ACCESS	read-only
			STATUS	current
	DESCRIPTION ""
			::= { mbus42 50 }

mbus42Value16		OBJECT-TYPE
			SYNTAX	INTEGER
			ACCESS	read-only
			STATUS	current
	DESCRIPTION ""
			::= { mbus42 51 }

mbus42VIF17		OBJECT-TYPE
			SYNTAX	INTEGER
			ACCESS	read-only
			STATUS	current
	DESCRIPTION ""
			::= { mbus42 52 }

mbus42Value17		OBJECT-TYPE
			SYNTAX	INTEGER
			ACCESS	read-only
			STATUS	current
	DESCRIPTION ""
			::= { mbus42 53 }

mbus42VIF18		OBJECT-TYPE
			SYNTAX	INTEGER
			ACCESS	read-only
			STATUS	current
	DESCRIPTION ""
			::= { mbus42 54 }

mbus42Value18		OBJECT-TYPE
			SYNTAX	INTEGER
			ACCESS	read-only
			STATUS	current
	DESCRIPTION ""
			::= { mbus42 55 }

mbus42VIF19		OBJECT-TYPE
			SYNTAX	INTEGER
			ACCESS	read-only
			STATUS	current
	DESCRIPTION ""
			::= { mbus42 56 }

mbus42Value19		OBJECT-TYPE
			SYNTAX	INTEGER
			ACCESS	read-only
			STATUS	current
	DESCRIPTION ""
			::= { mbus42 57 }

mbus42VIF1A		OBJECT-TYPE
			SYNTAX	INTEGER
			ACCESS	read-only
			STATUS	current
	DESCRIPTION ""
			::= { mbus42 58 }

mbus42Value1A		OBJECT-TYPE
			SYNTAX	INTEGER
			ACCESS	read-only
			STATUS	current
	DESCRIPTION ""
			::= { mbus42 59 }

mbus42VIF1B		OBJECT-TYPE
			SYNTAX	INTEGER
			ACCESS	read-only
			STATUS	current
	DESCRIPTION ""
			::= { mbus42 60 }

mbus42Value1B		OBJECT-TYPE
			SYNTAX	INTEGER
			ACCESS	read-only
			STATUS	current
	DESCRIPTION ""
			::= { mbus42 61 }

mbus42VIF1C		OBJECT-TYPE
			SYNTAX	INTEGER
			ACCESS	read-only
			STATUS	current
	DESCRIPTION ""
			::= { mbus42 62 }

mbus42Value1C		OBJECT-TYPE
			SYNTAX	INTEGER
			ACCESS	read-only
			STATUS	current
	DESCRIPTION ""
			::= { mbus42 63 }

mbus42VIF1D		OBJECT-TYPE
			SYNTAX	INTEGER
			ACCESS	read-only
			STATUS	current
	DESCRIPTION ""
			::= { mbus42 64 }

mbus42Value1D		OBJECT-TYPE
			SYNTAX	INTEGER
			ACCESS	read-only
			STATUS	current
	DESCRIPTION ""
			::= { mbus42 65 }

mbus42VIF1E		OBJECT-TYPE
			SYNTAX	INTEGER
			ACCESS	read-only
			STATUS	current
	DESCRIPTION ""
			::= { mbus42 66 }

mbus42Value1E		OBJECT-TYPE
			SYNTAX	INTEGER
			ACCESS	read-only
			STATUS	current
	DESCRIPTION ""
			::= { mbus42 67 }

mbus42VIF1F		OBJECT-TYPE
			SYNTAX	INTEGER
			ACCESS	read-only
			STATUS	current
	DESCRIPTION ""
			::= { mbus42 68 }

mbus42Value1F		OBJECT-TYPE
			SYNTAX	INTEGER
			ACCESS	read-only
			STATUS	current
	DESCRIPTION ""
			::= { mbus42 69 }

mbus42VIF20		OBJECT-TYPE
			SYNTAX	INTEGER
			ACCESS	read-only
			STATUS	current
	DESCRIPTION ""
			::= { mbus42 70 }

mbus42Value20		OBJECT-TYPE
			SYNTAX	INTEGER
			ACCESS	read-only
			STATUS	current
	DESCRIPTION ""
			::= { mbus42 71 }

mbus42VIF21		OBJECT-TYPE
			SYNTAX	INTEGER
			ACCESS	read-only
			STATUS	current
	DESCRIPTION ""
			::= { mbus42 72 }

mbus42Value21		OBJECT-TYPE
			SYNTAX	INTEGER
			ACCESS	read-only
			STATUS	current
	DESCRIPTION ""
			::= { mbus42 73 }

mbus42VIF22		OBJECT-TYPE
			SYNTAX	INTEGER
			ACCESS	read-only
			STATUS	current
	DESCRIPTION ""
			::= { mbus42 74 }

mbus42Value22		OBJECT-TYPE
			SYNTAX	INTEGER
			ACCESS	read-only
			STATUS	current
	DESCRIPTION ""
			::= { mbus42 75 }

mbus42VIF23		OBJECT-TYPE
			SYNTAX	INTEGER
			ACCESS	read-only
			STATUS	current
	DESCRIPTION ""
			::= { mbus42 76 }

mbus42Value23		OBJECT-TYPE
			SYNTAX	INTEGER
			ACCESS	read-only
			STATUS	current
	DESCRIPTION ""
			::= { mbus42 77 }

mbus42VIF24		OBJECT-TYPE
			SYNTAX	INTEGER
			ACCESS	read-only
			STATUS	current
	DESCRIPTION ""
			::= { mbus42 78 }

mbus42Value24		OBJECT-TYPE
			SYNTAX	INTEGER
			ACCESS	read-only
			STATUS	current
	DESCRIPTION ""
			::= { mbus42 79 }

mbus42VIF25		OBJECT-TYPE
			SYNTAX	INTEGER
			ACCESS	read-only
			STATUS	current
	DESCRIPTION ""
			::= { mbus42 80 }

mbus42Value25		OBJECT-TYPE
			SYNTAX	INTEGER
			ACCESS	read-only
			STATUS	current
	DESCRIPTION ""
			::= { mbus42 81 }

mbus42VIF26		OBJECT-TYPE
			SYNTAX	INTEGER
			ACCESS	read-only
			STATUS	current
	DESCRIPTION ""
			::= { mbus42 82 }

mbus42Value26		OBJECT-TYPE
			SYNTAX	INTEGER
			ACCESS	read-only
			STATUS	current
	DESCRIPTION ""
			::= { mbus42 83 }

mbus42VIF27		OBJECT-TYPE
			SYNTAX	INTEGER
			ACCESS	read-only
			STATUS	current
	DESCRIPTION ""
			::= { mbus42 84 }

mbus42Value27		OBJECT-TYPE
			SYNTAX	INTEGER
			ACCESS	read-only
			STATUS	current
	DESCRIPTION ""
			::= { mbus42 85 }

mbus42VIF28		OBJECT-TYPE
			SYNTAX	INTEGER
			ACCESS	read-only
			STATUS	current
	DESCRIPTION ""
			::= { mbus42 86 }

mbus42Value28		OBJECT-TYPE
			SYNTAX	INTEGER
			ACCESS	read-only
			STATUS	current
	DESCRIPTION ""
			::= { mbus42 87 }

mbus42VIF29		OBJECT-TYPE
			SYNTAX	INTEGER
			ACCESS	read-only
			STATUS	current
	DESCRIPTION ""
			::= { mbus42 88 }

mbus42Value29		OBJECT-TYPE
			SYNTAX	INTEGER
			ACCESS	read-only
			STATUS	current
	DESCRIPTION ""
			::= { mbus42 89 }

mbus42VIF2A		OBJECT-TYPE
			SYNTAX	INTEGER
			ACCESS	read-only
			STATUS	current
	DESCRIPTION ""
			::= { mbus42 90 }

mbus42Value2A		OBJECT-TYPE
			SYNTAX	INTEGER
			ACCESS	read-only
			STATUS	current
	DESCRIPTION ""
			::= { mbus42 91 }

mbus42VIF2B		OBJECT-TYPE
			SYNTAX	INTEGER
			ACCESS	read-only
			STATUS	current
	DESCRIPTION ""
			::= { mbus42 92 }

mbus42Value2B		OBJECT-TYPE
			SYNTAX	INTEGER
			ACCESS	read-only
			STATUS	current
	DESCRIPTION ""
			::= { mbus42 93 }

mbus42VIF2C		OBJECT-TYPE
			SYNTAX	INTEGER
			ACCESS	read-only
			STATUS	current
	DESCRIPTION ""
			::= { mbus42 94 }

mbus42Value2C		OBJECT-TYPE
			SYNTAX	INTEGER
			ACCESS	read-only
			STATUS	current
	DESCRIPTION ""
			::= { mbus42 95 }

mbus42VIF2D		OBJECT-TYPE
			SYNTAX	INTEGER
			ACCESS	read-only
			STATUS	current
	DESCRIPTION ""
			::= { mbus42 96 }

mbus42Value2D		OBJECT-TYPE
			SYNTAX	INTEGER
			ACCESS	read-only
			STATUS	current
	DESCRIPTION ""
			::= { mbus42 97 }

mbus42VIF2E		OBJECT-TYPE
			SYNTAX	INTEGER
			ACCESS	read-only
			STATUS	current
	DESCRIPTION ""
			::= { mbus42 98 }

mbus42Value2E		OBJECT-TYPE
			SYNTAX	INTEGER
			ACCESS	read-only
			STATUS	current
	DESCRIPTION ""
			::= { mbus42 99 }

mbus42VIF2F		OBJECT-TYPE
			SYNTAX	INTEGER
			ACCESS	read-only
			STATUS	current
	DESCRIPTION ""
			::= { mbus42 100 }

mbus42Value2F		OBJECT-TYPE
			SYNTAX	INTEGER
			ACCESS	read-only
			STATUS	current
	DESCRIPTION ""
			::= { mbus42 101 }

mbus43			OBJECT IDENTIFIER ::= { mbus 67 }

mbus43IdNumber		OBJECT-TYPE
			SYNTAX	Gauge
			ACCESS	read-only
			STATUS	current
	DESCRIPTION ""
			::= { mbus43 1 }

mbus43Manufacturer	OBJECT-TYPE
			SYNTAX	Gauge
			ACCESS	read-only
			STATUS	current
	DESCRIPTION ""
			::= { mbus43 2 }

mbus43Version		OBJECT-TYPE
			SYNTAX	Gauge
			ACCESS	read-only
			STATUS	current
	DESCRIPTION ""
			::= { mbus43 3 }

mbus43Medium		OBJECT-TYPE
			SYNTAX	Gauge
			ACCESS	read-only
			STATUS	current
	DESCRIPTION ""
			::= { mbus43 4 }

mbus43Status		OBJECT-TYPE
			SYNTAX	Gauge
			ACCESS	read-only
			STATUS	current
	DESCRIPTION ""
			::= { mbus43 5 }

mbus43VIF00		OBJECT-TYPE
			SYNTAX	INTEGER
			ACCESS	read-only
			STATUS	current
	DESCRIPTION ""
			::= { mbus43 6 }

mbus43Value00		OBJECT-TYPE
			SYNTAX	INTEGER
			ACCESS	read-only
			STATUS	current
	DESCRIPTION ""
			::= { mbus43 7 }

mbus43VIF01		OBJECT-TYPE
			SYNTAX	INTEGER
			ACCESS	read-only
			STATUS	current
	DESCRIPTION ""
			::= { mbus43 8 }

mbus43Value01		OBJECT-TYPE
			SYNTAX	INTEGER
			ACCESS	read-only
			STATUS	current
	DESCRIPTION ""
			::= { mbus43 9 }

mbus43VIF02		OBJECT-TYPE
			SYNTAX	INTEGER
			ACCESS	read-only
			STATUS	current
	DESCRIPTION ""
			::= { mbus43 10 }

mbus43Value02		OBJECT-TYPE
			SYNTAX	INTEGER
			ACCESS	read-only
			STATUS	current
	DESCRIPTION ""
			::= { mbus43 11 }

mbus43VIF03		OBJECT-TYPE
			SYNTAX	INTEGER
			ACCESS	read-only
			STATUS	current
	DESCRIPTION ""
			::= { mbus43 12 }

mbus43Value03		OBJECT-TYPE
			SYNTAX	INTEGER
			ACCESS	read-only
			STATUS	current
	DESCRIPTION ""
			::= { mbus43 13 }

mbus43VIF04		OBJECT-TYPE
			SYNTAX	INTEGER
			ACCESS	read-only
			STATUS	current
	DESCRIPTION ""
			::= { mbus43 14 }

mbus43Value04		OBJECT-TYPE
			SYNTAX	INTEGER
			ACCESS	read-only
			STATUS	current
	DESCRIPTION ""
			::= { mbus43 15 }

mbus43VIF05		OBJECT-TYPE
			SYNTAX	INTEGER
			ACCESS	read-only
			STATUS	current
	DESCRIPTION ""
			::= { mbus43 16 }

mbus43Value05		OBJECT-TYPE
			SYNTAX	INTEGER
			ACCESS	read-only
			STATUS	current
	DESCRIPTION ""
			::= { mbus43 17 }

mbus43VIF06		OBJECT-TYPE
			SYNTAX	INTEGER
			ACCESS	read-only
			STATUS	current
	DESCRIPTION ""
			::= { mbus43 18 }

mbus43Value06		OBJECT-TYPE
			SYNTAX	INTEGER
			ACCESS	read-only
			STATUS	current
	DESCRIPTION ""
			::= { mbus43 19 }

mbus43VIF07		OBJECT-TYPE
			SYNTAX	INTEGER
			ACCESS	read-only
			STATUS	current
	DESCRIPTION ""
			::= { mbus43 20 }

mbus43Value07		OBJECT-TYPE
			SYNTAX	INTEGER
			ACCESS	read-only
			STATUS	current
	DESCRIPTION ""
			::= { mbus43 21 }

mbus43VIF08		OBJECT-TYPE
			SYNTAX	INTEGER
			ACCESS	read-only
			STATUS	current
	DESCRIPTION ""
			::= { mbus43 22 }

mbus43Value08		OBJECT-TYPE
			SYNTAX	INTEGER
			ACCESS	read-only
			STATUS	current
	DESCRIPTION ""
			::= { mbus43 23 }

mbus43VIF09		OBJECT-TYPE
			SYNTAX	INTEGER
			ACCESS	read-only
			STATUS	current
	DESCRIPTION ""
			::= { mbus43 24 }

mbus43Value09		OBJECT-TYPE
			SYNTAX	INTEGER
			ACCESS	read-only
			STATUS	current
	DESCRIPTION ""
			::= { mbus43 25 }

mbus43VIF0A		OBJECT-TYPE
			SYNTAX	INTEGER
			ACCESS	read-only
			STATUS	current
	DESCRIPTION ""
			::= { mbus43 26 }

mbus43Value0A		OBJECT-TYPE
			SYNTAX	INTEGER
			ACCESS	read-only
			STATUS	current
	DESCRIPTION ""
			::= { mbus43 27 }

mbus43VIF0B		OBJECT-TYPE
			SYNTAX	INTEGER
			ACCESS	read-only
			STATUS	current
	DESCRIPTION ""
			::= { mbus43 28 }

mbus43Value0B		OBJECT-TYPE
			SYNTAX	INTEGER
			ACCESS	read-only
			STATUS	current
	DESCRIPTION ""
			::= { mbus43 29 }

mbus43VIF0C		OBJECT-TYPE
			SYNTAX	INTEGER
			ACCESS	read-only
			STATUS	current
	DESCRIPTION ""
			::= { mbus43 30 }

mbus43Value0C		OBJECT-TYPE
			SYNTAX	INTEGER
			ACCESS	read-only
			STATUS	current
	DESCRIPTION ""
			::= { mbus43 31 }

mbus43VIF0D		OBJECT-TYPE
			SYNTAX	INTEGER
			ACCESS	read-only
			STATUS	current
	DESCRIPTION ""
			::= { mbus43 32 }

mbus43Value0D		OBJECT-TYPE
			SYNTAX	INTEGER
			ACCESS	read-only
			STATUS	current
	DESCRIPTION ""
			::= { mbus43 33 }

mbus43VIF0E		OBJECT-TYPE
			SYNTAX	INTEGER
			ACCESS	read-only
			STATUS	current
	DESCRIPTION ""
			::= { mbus43 34 }

mbus43Value0E		OBJECT-TYPE
			SYNTAX	INTEGER
			ACCESS	read-only
			STATUS	current
	DESCRIPTION ""
			::= { mbus43 35 }

mbus43VIF0F		OBJECT-TYPE
			SYNTAX	INTEGER
			ACCESS	read-only
			STATUS	current
	DESCRIPTION ""
			::= { mbus43 36 }

mbus43Value0F		OBJECT-TYPE
			SYNTAX	INTEGER
			ACCESS	read-only
			STATUS	current
	DESCRIPTION ""
			::= { mbus43 37 }

mbus43VIF10		OBJECT-TYPE
			SYNTAX	INTEGER
			ACCESS	read-only
			STATUS	current
	DESCRIPTION ""
			::= { mbus43 38 }

mbus43Value10		OBJECT-TYPE
			SYNTAX	INTEGER
			ACCESS	read-only
			STATUS	current
	DESCRIPTION ""
			::= { mbus43 39 }

mbus43VIF11		OBJECT-TYPE
			SYNTAX	INTEGER
			ACCESS	read-only
			STATUS	current
	DESCRIPTION ""
			::= { mbus43 40 }

mbus43Value11		OBJECT-TYPE
			SYNTAX	INTEGER
			ACCESS	read-only
			STATUS	current
	DESCRIPTION ""
			::= { mbus43 41 }

mbus43VIF12		OBJECT-TYPE
			SYNTAX	INTEGER
			ACCESS	read-only
			STATUS	current
	DESCRIPTION ""
			::= { mbus43 42 }

mbus43Value12		OBJECT-TYPE
			SYNTAX	INTEGER
			ACCESS	read-only
			STATUS	current
	DESCRIPTION ""
			::= { mbus43 43 }

mbus43VIF13		OBJECT-TYPE
			SYNTAX	INTEGER
			ACCESS	read-only
			STATUS	current
	DESCRIPTION ""
			::= { mbus43 44 }

mbus43Value13		OBJECT-TYPE
			SYNTAX	INTEGER
			ACCESS	read-only
			STATUS	current
	DESCRIPTION ""
			::= { mbus43 45 }

mbus43VIF14		OBJECT-TYPE
			SYNTAX	INTEGER
			ACCESS	read-only
			STATUS	current
	DESCRIPTION ""
			::= { mbus43 46 }

mbus43Value14		OBJECT-TYPE
			SYNTAX	INTEGER
			ACCESS	read-only
			STATUS	current
	DESCRIPTION ""
			::= { mbus43 47 }

mbus43VIF15		OBJECT-TYPE
			SYNTAX	INTEGER
			ACCESS	read-only
			STATUS	current
	DESCRIPTION ""
			::= { mbus43 48 }

mbus43Value15		OBJECT-TYPE
			SYNTAX	INTEGER
			ACCESS	read-only
			STATUS	current
	DESCRIPTION ""
			::= { mbus43 49 }

mbus43VIF16		OBJECT-TYPE
			SYNTAX	INTEGER
			ACCESS	read-only
			STATUS	current
	DESCRIPTION ""
			::= { mbus43 50 }

mbus43Value16		OBJECT-TYPE
			SYNTAX	INTEGER
			ACCESS	read-only
			STATUS	current
	DESCRIPTION ""
			::= { mbus43 51 }

mbus43VIF17		OBJECT-TYPE
			SYNTAX	INTEGER
			ACCESS	read-only
			STATUS	current
	DESCRIPTION ""
			::= { mbus43 52 }

mbus43Value17		OBJECT-TYPE
			SYNTAX	INTEGER
			ACCESS	read-only
			STATUS	current
	DESCRIPTION ""
			::= { mbus43 53 }

mbus43VIF18		OBJECT-TYPE
			SYNTAX	INTEGER
			ACCESS	read-only
			STATUS	current
	DESCRIPTION ""
			::= { mbus43 54 }

mbus43Value18		OBJECT-TYPE
			SYNTAX	INTEGER
			ACCESS	read-only
			STATUS	current
	DESCRIPTION ""
			::= { mbus43 55 }

mbus43VIF19		OBJECT-TYPE
			SYNTAX	INTEGER
			ACCESS	read-only
			STATUS	current
	DESCRIPTION ""
			::= { mbus43 56 }

mbus43Value19		OBJECT-TYPE
			SYNTAX	INTEGER
			ACCESS	read-only
			STATUS	current
	DESCRIPTION ""
			::= { mbus43 57 }

mbus43VIF1A		OBJECT-TYPE
			SYNTAX	INTEGER
			ACCESS	read-only
			STATUS	current
	DESCRIPTION ""
			::= { mbus43 58 }

mbus43Value1A		OBJECT-TYPE
			SYNTAX	INTEGER
			ACCESS	read-only
			STATUS	current
	DESCRIPTION ""
			::= { mbus43 59 }

mbus43VIF1B		OBJECT-TYPE
			SYNTAX	INTEGER
			ACCESS	read-only
			STATUS	current
	DESCRIPTION ""
			::= { mbus43 60 }

mbus43Value1B		OBJECT-TYPE
			SYNTAX	INTEGER
			ACCESS	read-only
			STATUS	current
	DESCRIPTION ""
			::= { mbus43 61 }

mbus43VIF1C		OBJECT-TYPE
			SYNTAX	INTEGER
			ACCESS	read-only
			STATUS	current
	DESCRIPTION ""
			::= { mbus43 62 }

mbus43Value1C		OBJECT-TYPE
			SYNTAX	INTEGER
			ACCESS	read-only
			STATUS	current
	DESCRIPTION ""
			::= { mbus43 63 }

mbus43VIF1D		OBJECT-TYPE
			SYNTAX	INTEGER
			ACCESS	read-only
			STATUS	current
	DESCRIPTION ""
			::= { mbus43 64 }

mbus43Value1D		OBJECT-TYPE
			SYNTAX	INTEGER
			ACCESS	read-only
			STATUS	current
	DESCRIPTION ""
			::= { mbus43 65 }

mbus43VIF1E		OBJECT-TYPE
			SYNTAX	INTEGER
			ACCESS	read-only
			STATUS	current
	DESCRIPTION ""
			::= { mbus43 66 }

mbus43Value1E		OBJECT-TYPE
			SYNTAX	INTEGER
			ACCESS	read-only
			STATUS	current
	DESCRIPTION ""
			::= { mbus43 67 }

mbus43VIF1F		OBJECT-TYPE
			SYNTAX	INTEGER
			ACCESS	read-only
			STATUS	current
	DESCRIPTION ""
			::= { mbus43 68 }

mbus43Value1F		OBJECT-TYPE
			SYNTAX	INTEGER
			ACCESS	read-only
			STATUS	current
	DESCRIPTION ""
			::= { mbus43 69 }

mbus43VIF20		OBJECT-TYPE
			SYNTAX	INTEGER
			ACCESS	read-only
			STATUS	current
	DESCRIPTION ""
			::= { mbus43 70 }

mbus43Value20		OBJECT-TYPE
			SYNTAX	INTEGER
			ACCESS	read-only
			STATUS	current
	DESCRIPTION ""
			::= { mbus43 71 }

mbus43VIF21		OBJECT-TYPE
			SYNTAX	INTEGER
			ACCESS	read-only
			STATUS	current
	DESCRIPTION ""
			::= { mbus43 72 }

mbus43Value21		OBJECT-TYPE
			SYNTAX	INTEGER
			ACCESS	read-only
			STATUS	current
	DESCRIPTION ""
			::= { mbus43 73 }

mbus43VIF22		OBJECT-TYPE
			SYNTAX	INTEGER
			ACCESS	read-only
			STATUS	current
	DESCRIPTION ""
			::= { mbus43 74 }

mbus43Value22		OBJECT-TYPE
			SYNTAX	INTEGER
			ACCESS	read-only
			STATUS	current
	DESCRIPTION ""
			::= { mbus43 75 }

mbus43VIF23		OBJECT-TYPE
			SYNTAX	INTEGER
			ACCESS	read-only
			STATUS	current
	DESCRIPTION ""
			::= { mbus43 76 }

mbus43Value23		OBJECT-TYPE
			SYNTAX	INTEGER
			ACCESS	read-only
			STATUS	current
	DESCRIPTION ""
			::= { mbus43 77 }

mbus43VIF24		OBJECT-TYPE
			SYNTAX	INTEGER
			ACCESS	read-only
			STATUS	current
	DESCRIPTION ""
			::= { mbus43 78 }

mbus43Value24		OBJECT-TYPE
			SYNTAX	INTEGER
			ACCESS	read-only
			STATUS	current
	DESCRIPTION ""
			::= { mbus43 79 }

mbus43VIF25		OBJECT-TYPE
			SYNTAX	INTEGER
			ACCESS	read-only
			STATUS	current
	DESCRIPTION ""
			::= { mbus43 80 }

mbus43Value25		OBJECT-TYPE
			SYNTAX	INTEGER
			ACCESS	read-only
			STATUS	current
	DESCRIPTION ""
			::= { mbus43 81 }

mbus43VIF26		OBJECT-TYPE
			SYNTAX	INTEGER
			ACCESS	read-only
			STATUS	current
	DESCRIPTION ""
			::= { mbus43 82 }

mbus43Value26		OBJECT-TYPE
			SYNTAX	INTEGER
			ACCESS	read-only
			STATUS	current
	DESCRIPTION ""
			::= { mbus43 83 }

mbus43VIF27		OBJECT-TYPE
			SYNTAX	INTEGER
			ACCESS	read-only
			STATUS	current
	DESCRIPTION ""
			::= { mbus43 84 }

mbus43Value27		OBJECT-TYPE
			SYNTAX	INTEGER
			ACCESS	read-only
			STATUS	current
	DESCRIPTION ""
			::= { mbus43 85 }

mbus43VIF28		OBJECT-TYPE
			SYNTAX	INTEGER
			ACCESS	read-only
			STATUS	current
	DESCRIPTION ""
			::= { mbus43 86 }

mbus43Value28		OBJECT-TYPE
			SYNTAX	INTEGER
			ACCESS	read-only
			STATUS	current
	DESCRIPTION ""
			::= { mbus43 87 }

mbus43VIF29		OBJECT-TYPE
			SYNTAX	INTEGER
			ACCESS	read-only
			STATUS	current
	DESCRIPTION ""
			::= { mbus43 88 }

mbus43Value29		OBJECT-TYPE
			SYNTAX	INTEGER
			ACCESS	read-only
			STATUS	current
	DESCRIPTION ""
			::= { mbus43 89 }

mbus43VIF2A		OBJECT-TYPE
			SYNTAX	INTEGER
			ACCESS	read-only
			STATUS	current
	DESCRIPTION ""
			::= { mbus43 90 }

mbus43Value2A		OBJECT-TYPE
			SYNTAX	INTEGER
			ACCESS	read-only
			STATUS	current
	DESCRIPTION ""
			::= { mbus43 91 }

mbus43VIF2B		OBJECT-TYPE
			SYNTAX	INTEGER
			ACCESS	read-only
			STATUS	current
	DESCRIPTION ""
			::= { mbus43 92 }

mbus43Value2B		OBJECT-TYPE
			SYNTAX	INTEGER
			ACCESS	read-only
			STATUS	current
	DESCRIPTION ""
			::= { mbus43 93 }

mbus43VIF2C		OBJECT-TYPE
			SYNTAX	INTEGER
			ACCESS	read-only
			STATUS	current
	DESCRIPTION ""
			::= { mbus43 94 }

mbus43Value2C		OBJECT-TYPE
			SYNTAX	INTEGER
			ACCESS	read-only
			STATUS	current
	DESCRIPTION ""
			::= { mbus43 95 }

mbus43VIF2D		OBJECT-TYPE
			SYNTAX	INTEGER
			ACCESS	read-only
			STATUS	current
	DESCRIPTION ""
			::= { mbus43 96 }

mbus43Value2D		OBJECT-TYPE
			SYNTAX	INTEGER
			ACCESS	read-only
			STATUS	current
	DESCRIPTION ""
			::= { mbus43 97 }

mbus43VIF2E		OBJECT-TYPE
			SYNTAX	INTEGER
			ACCESS	read-only
			STATUS	current
	DESCRIPTION ""
			::= { mbus43 98 }

mbus43Value2E		OBJECT-TYPE
			SYNTAX	INTEGER
			ACCESS	read-only
			STATUS	current
	DESCRIPTION ""
			::= { mbus43 99 }

mbus43VIF2F		OBJECT-TYPE
			SYNTAX	INTEGER
			ACCESS	read-only
			STATUS	current
	DESCRIPTION ""
			::= { mbus43 100 }

mbus43Value2F		OBJECT-TYPE
			SYNTAX	INTEGER
			ACCESS	read-only
			STATUS	current
	DESCRIPTION ""
			::= { mbus43 101 }

mbus44			OBJECT IDENTIFIER ::= { mbus 68 }

mbus44IdNumber		OBJECT-TYPE
			SYNTAX	Gauge
			ACCESS	read-only
			STATUS	current
	DESCRIPTION ""
			::= { mbus44 1 }

mbus44Manufacturer	OBJECT-TYPE
			SYNTAX	Gauge
			ACCESS	read-only
			STATUS	current
	DESCRIPTION ""
			::= { mbus44 2 }

mbus44Version		OBJECT-TYPE
			SYNTAX	Gauge
			ACCESS	read-only
			STATUS	current
	DESCRIPTION ""
			::= { mbus44 3 }

mbus44Medium		OBJECT-TYPE
			SYNTAX	Gauge
			ACCESS	read-only
			STATUS	current
	DESCRIPTION ""
			::= { mbus44 4 }

mbus44Status		OBJECT-TYPE
			SYNTAX	Gauge
			ACCESS	read-only
			STATUS	current
	DESCRIPTION ""
			::= { mbus44 5 }

mbus44VIF00		OBJECT-TYPE
			SYNTAX	INTEGER
			ACCESS	read-only
			STATUS	current
	DESCRIPTION ""
			::= { mbus44 6 }

mbus44Value00		OBJECT-TYPE
			SYNTAX	INTEGER
			ACCESS	read-only
			STATUS	current
	DESCRIPTION ""
			::= { mbus44 7 }

mbus44VIF01		OBJECT-TYPE
			SYNTAX	INTEGER
			ACCESS	read-only
			STATUS	current
	DESCRIPTION ""
			::= { mbus44 8 }

mbus44Value01		OBJECT-TYPE
			SYNTAX	INTEGER
			ACCESS	read-only
			STATUS	current
	DESCRIPTION ""
			::= { mbus44 9 }

mbus44VIF02		OBJECT-TYPE
			SYNTAX	INTEGER
			ACCESS	read-only
			STATUS	current
	DESCRIPTION ""
			::= { mbus44 10 }

mbus44Value02		OBJECT-TYPE
			SYNTAX	INTEGER
			ACCESS	read-only
			STATUS	current
	DESCRIPTION ""
			::= { mbus44 11 }

mbus44VIF03		OBJECT-TYPE
			SYNTAX	INTEGER
			ACCESS	read-only
			STATUS	current
	DESCRIPTION ""
			::= { mbus44 12 }

mbus44Value03		OBJECT-TYPE
			SYNTAX	INTEGER
			ACCESS	read-only
			STATUS	current
	DESCRIPTION ""
			::= { mbus44 13 }

mbus44VIF04		OBJECT-TYPE
			SYNTAX	INTEGER
			ACCESS	read-only
			STATUS	current
	DESCRIPTION ""
			::= { mbus44 14 }

mbus44Value04		OBJECT-TYPE
			SYNTAX	INTEGER
			ACCESS	read-only
			STATUS	current
	DESCRIPTION ""
			::= { mbus44 15 }

mbus44VIF05		OBJECT-TYPE
			SYNTAX	INTEGER
			ACCESS	read-only
			STATUS	current
	DESCRIPTION ""
			::= { mbus44 16 }

mbus44Value05		OBJECT-TYPE
			SYNTAX	INTEGER
			ACCESS	read-only
			STATUS	current
	DESCRIPTION ""
			::= { mbus44 17 }

mbus44VIF06		OBJECT-TYPE
			SYNTAX	INTEGER
			ACCESS	read-only
			STATUS	current
	DESCRIPTION ""
			::= { mbus44 18 }

mbus44Value06		OBJECT-TYPE
			SYNTAX	INTEGER
			ACCESS	read-only
			STATUS	current
	DESCRIPTION ""
			::= { mbus44 19 }

mbus44VIF07		OBJECT-TYPE
			SYNTAX	INTEGER
			ACCESS	read-only
			STATUS	current
	DESCRIPTION ""
			::= { mbus44 20 }

mbus44Value07		OBJECT-TYPE
			SYNTAX	INTEGER
			ACCESS	read-only
			STATUS	current
	DESCRIPTION ""
			::= { mbus44 21 }

mbus44VIF08		OBJECT-TYPE
			SYNTAX	INTEGER
			ACCESS	read-only
			STATUS	current
	DESCRIPTION ""
			::= { mbus44 22 }

mbus44Value08		OBJECT-TYPE
			SYNTAX	INTEGER
			ACCESS	read-only
			STATUS	current
	DESCRIPTION ""
			::= { mbus44 23 }

mbus44VIF09		OBJECT-TYPE
			SYNTAX	INTEGER
			ACCESS	read-only
			STATUS	current
	DESCRIPTION ""
			::= { mbus44 24 }

mbus44Value09		OBJECT-TYPE
			SYNTAX	INTEGER
			ACCESS	read-only
			STATUS	current
	DESCRIPTION ""
			::= { mbus44 25 }

mbus44VIF0A		OBJECT-TYPE
			SYNTAX	INTEGER
			ACCESS	read-only
			STATUS	current
	DESCRIPTION ""
			::= { mbus44 26 }

mbus44Value0A		OBJECT-TYPE
			SYNTAX	INTEGER
			ACCESS	read-only
			STATUS	current
	DESCRIPTION ""
			::= { mbus44 27 }

mbus44VIF0B		OBJECT-TYPE
			SYNTAX	INTEGER
			ACCESS	read-only
			STATUS	current
	DESCRIPTION ""
			::= { mbus44 28 }

mbus44Value0B		OBJECT-TYPE
			SYNTAX	INTEGER
			ACCESS	read-only
			STATUS	current
	DESCRIPTION ""
			::= { mbus44 29 }

mbus44VIF0C		OBJECT-TYPE
			SYNTAX	INTEGER
			ACCESS	read-only
			STATUS	current
	DESCRIPTION ""
			::= { mbus44 30 }

mbus44Value0C		OBJECT-TYPE
			SYNTAX	INTEGER
			ACCESS	read-only
			STATUS	current
	DESCRIPTION ""
			::= { mbus44 31 }

mbus44VIF0D		OBJECT-TYPE
			SYNTAX	INTEGER
			ACCESS	read-only
			STATUS	current
	DESCRIPTION ""
			::= { mbus44 32 }

mbus44Value0D		OBJECT-TYPE
			SYNTAX	INTEGER
			ACCESS	read-only
			STATUS	current
	DESCRIPTION ""
			::= { mbus44 33 }

mbus44VIF0E		OBJECT-TYPE
			SYNTAX	INTEGER
			ACCESS	read-only
			STATUS	current
	DESCRIPTION ""
			::= { mbus44 34 }

mbus44Value0E		OBJECT-TYPE
			SYNTAX	INTEGER
			ACCESS	read-only
			STATUS	current
	DESCRIPTION ""
			::= { mbus44 35 }

mbus44VIF0F		OBJECT-TYPE
			SYNTAX	INTEGER
			ACCESS	read-only
			STATUS	current
	DESCRIPTION ""
			::= { mbus44 36 }

mbus44Value0F		OBJECT-TYPE
			SYNTAX	INTEGER
			ACCESS	read-only
			STATUS	current
	DESCRIPTION ""
			::= { mbus44 37 }

mbus44VIF10		OBJECT-TYPE
			SYNTAX	INTEGER
			ACCESS	read-only
			STATUS	current
	DESCRIPTION ""
			::= { mbus44 38 }

mbus44Value10		OBJECT-TYPE
			SYNTAX	INTEGER
			ACCESS	read-only
			STATUS	current
	DESCRIPTION ""
			::= { mbus44 39 }

mbus44VIF11		OBJECT-TYPE
			SYNTAX	INTEGER
			ACCESS	read-only
			STATUS	current
	DESCRIPTION ""
			::= { mbus44 40 }

mbus44Value11		OBJECT-TYPE
			SYNTAX	INTEGER
			ACCESS	read-only
			STATUS	current
	DESCRIPTION ""
			::= { mbus44 41 }

mbus44VIF12		OBJECT-TYPE
			SYNTAX	INTEGER
			ACCESS	read-only
			STATUS	current
	DESCRIPTION ""
			::= { mbus44 42 }

mbus44Value12		OBJECT-TYPE
			SYNTAX	INTEGER
			ACCESS	read-only
			STATUS	current
	DESCRIPTION ""
			::= { mbus44 43 }

mbus44VIF13		OBJECT-TYPE
			SYNTAX	INTEGER
			ACCESS	read-only
			STATUS	current
	DESCRIPTION ""
			::= { mbus44 44 }

mbus44Value13		OBJECT-TYPE
			SYNTAX	INTEGER
			ACCESS	read-only
			STATUS	current
	DESCRIPTION ""
			::= { mbus44 45 }

mbus44VIF14		OBJECT-TYPE
			SYNTAX	INTEGER
			ACCESS	read-only
			STATUS	current
	DESCRIPTION ""
			::= { mbus44 46 }

mbus44Value14		OBJECT-TYPE
			SYNTAX	INTEGER
			ACCESS	read-only
			STATUS	current
	DESCRIPTION ""
			::= { mbus44 47 }

mbus44VIF15		OBJECT-TYPE
			SYNTAX	INTEGER
			ACCESS	read-only
			STATUS	current
	DESCRIPTION ""
			::= { mbus44 48 }

mbus44Value15		OBJECT-TYPE
			SYNTAX	INTEGER
			ACCESS	read-only
			STATUS	current
	DESCRIPTION ""
			::= { mbus44 49 }

mbus44VIF16		OBJECT-TYPE
			SYNTAX	INTEGER
			ACCESS	read-only
			STATUS	current
	DESCRIPTION ""
			::= { mbus44 50 }

mbus44Value16		OBJECT-TYPE
			SYNTAX	INTEGER
			ACCESS	read-only
			STATUS	current
	DESCRIPTION ""
			::= { mbus44 51 }

mbus44VIF17		OBJECT-TYPE
			SYNTAX	INTEGER
			ACCESS	read-only
			STATUS	current
	DESCRIPTION ""
			::= { mbus44 52 }

mbus44Value17		OBJECT-TYPE
			SYNTAX	INTEGER
			ACCESS	read-only
			STATUS	current
	DESCRIPTION ""
			::= { mbus44 53 }

mbus44VIF18		OBJECT-TYPE
			SYNTAX	INTEGER
			ACCESS	read-only
			STATUS	current
	DESCRIPTION ""
			::= { mbus44 54 }

mbus44Value18		OBJECT-TYPE
			SYNTAX	INTEGER
			ACCESS	read-only
			STATUS	current
	DESCRIPTION ""
			::= { mbus44 55 }

mbus44VIF19		OBJECT-TYPE
			SYNTAX	INTEGER
			ACCESS	read-only
			STATUS	current
	DESCRIPTION ""
			::= { mbus44 56 }

mbus44Value19		OBJECT-TYPE
			SYNTAX	INTEGER
			ACCESS	read-only
			STATUS	current
	DESCRIPTION ""
			::= { mbus44 57 }

mbus44VIF1A		OBJECT-TYPE
			SYNTAX	INTEGER
			ACCESS	read-only
			STATUS	current
	DESCRIPTION ""
			::= { mbus44 58 }

mbus44Value1A		OBJECT-TYPE
			SYNTAX	INTEGER
			ACCESS	read-only
			STATUS	current
	DESCRIPTION ""
			::= { mbus44 59 }

mbus44VIF1B		OBJECT-TYPE
			SYNTAX	INTEGER
			ACCESS	read-only
			STATUS	current
	DESCRIPTION ""
			::= { mbus44 60 }

mbus44Value1B		OBJECT-TYPE
			SYNTAX	INTEGER
			ACCESS	read-only
			STATUS	current
	DESCRIPTION ""
			::= { mbus44 61 }

mbus44VIF1C		OBJECT-TYPE
			SYNTAX	INTEGER
			ACCESS	read-only
			STATUS	current
	DESCRIPTION ""
			::= { mbus44 62 }

mbus44Value1C		OBJECT-TYPE
			SYNTAX	INTEGER
			ACCESS	read-only
			STATUS	current
	DESCRIPTION ""
			::= { mbus44 63 }

mbus44VIF1D		OBJECT-TYPE
			SYNTAX	INTEGER
			ACCESS	read-only
			STATUS	current
	DESCRIPTION ""
			::= { mbus44 64 }

mbus44Value1D		OBJECT-TYPE
			SYNTAX	INTEGER
			ACCESS	read-only
			STATUS	current
	DESCRIPTION ""
			::= { mbus44 65 }

mbus44VIF1E		OBJECT-TYPE
			SYNTAX	INTEGER
			ACCESS	read-only
			STATUS	current
	DESCRIPTION ""
			::= { mbus44 66 }

mbus44Value1E		OBJECT-TYPE
			SYNTAX	INTEGER
			ACCESS	read-only
			STATUS	current
	DESCRIPTION ""
			::= { mbus44 67 }

mbus44VIF1F		OBJECT-TYPE
			SYNTAX	INTEGER
			ACCESS	read-only
			STATUS	current
	DESCRIPTION ""
			::= { mbus44 68 }

mbus44Value1F		OBJECT-TYPE
			SYNTAX	INTEGER
			ACCESS	read-only
			STATUS	current
	DESCRIPTION ""
			::= { mbus44 69 }

mbus44VIF20		OBJECT-TYPE
			SYNTAX	INTEGER
			ACCESS	read-only
			STATUS	current
	DESCRIPTION ""
			::= { mbus44 70 }

mbus44Value20		OBJECT-TYPE
			SYNTAX	INTEGER
			ACCESS	read-only
			STATUS	current
	DESCRIPTION ""
			::= { mbus44 71 }

mbus44VIF21		OBJECT-TYPE
			SYNTAX	INTEGER
			ACCESS	read-only
			STATUS	current
	DESCRIPTION ""
			::= { mbus44 72 }

mbus44Value21		OBJECT-TYPE
			SYNTAX	INTEGER
			ACCESS	read-only
			STATUS	current
	DESCRIPTION ""
			::= { mbus44 73 }

mbus44VIF22		OBJECT-TYPE
			SYNTAX	INTEGER
			ACCESS	read-only
			STATUS	current
	DESCRIPTION ""
			::= { mbus44 74 }

mbus44Value22		OBJECT-TYPE
			SYNTAX	INTEGER
			ACCESS	read-only
			STATUS	current
	DESCRIPTION ""
			::= { mbus44 75 }

mbus44VIF23		OBJECT-TYPE
			SYNTAX	INTEGER
			ACCESS	read-only
			STATUS	current
	DESCRIPTION ""
			::= { mbus44 76 }

mbus44Value23		OBJECT-TYPE
			SYNTAX	INTEGER
			ACCESS	read-only
			STATUS	current
	DESCRIPTION ""
			::= { mbus44 77 }

mbus44VIF24		OBJECT-TYPE
			SYNTAX	INTEGER
			ACCESS	read-only
			STATUS	current
	DESCRIPTION ""
			::= { mbus44 78 }

mbus44Value24		OBJECT-TYPE
			SYNTAX	INTEGER
			ACCESS	read-only
			STATUS	current
	DESCRIPTION ""
			::= { mbus44 79 }

mbus44VIF25		OBJECT-TYPE
			SYNTAX	INTEGER
			ACCESS	read-only
			STATUS	current
	DESCRIPTION ""
			::= { mbus44 80 }

mbus44Value25		OBJECT-TYPE
			SYNTAX	INTEGER
			ACCESS	read-only
			STATUS	current
	DESCRIPTION ""
			::= { mbus44 81 }

mbus44VIF26		OBJECT-TYPE
			SYNTAX	INTEGER
			ACCESS	read-only
			STATUS	current
	DESCRIPTION ""
			::= { mbus44 82 }

mbus44Value26		OBJECT-TYPE
			SYNTAX	INTEGER
			ACCESS	read-only
			STATUS	current
	DESCRIPTION ""
			::= { mbus44 83 }

mbus44VIF27		OBJECT-TYPE
			SYNTAX	INTEGER
			ACCESS	read-only
			STATUS	current
	DESCRIPTION ""
			::= { mbus44 84 }

mbus44Value27		OBJECT-TYPE
			SYNTAX	INTEGER
			ACCESS	read-only
			STATUS	current
	DESCRIPTION ""
			::= { mbus44 85 }

mbus44VIF28		OBJECT-TYPE
			SYNTAX	INTEGER
			ACCESS	read-only
			STATUS	current
	DESCRIPTION ""
			::= { mbus44 86 }

mbus44Value28		OBJECT-TYPE
			SYNTAX	INTEGER
			ACCESS	read-only
			STATUS	current
	DESCRIPTION ""
			::= { mbus44 87 }

mbus44VIF29		OBJECT-TYPE
			SYNTAX	INTEGER
			ACCESS	read-only
			STATUS	current
	DESCRIPTION ""
			::= { mbus44 88 }

mbus44Value29		OBJECT-TYPE
			SYNTAX	INTEGER
			ACCESS	read-only
			STATUS	current
	DESCRIPTION ""
			::= { mbus44 89 }

mbus44VIF2A		OBJECT-TYPE
			SYNTAX	INTEGER
			ACCESS	read-only
			STATUS	current
	DESCRIPTION ""
			::= { mbus44 90 }

mbus44Value2A		OBJECT-TYPE
			SYNTAX	INTEGER
			ACCESS	read-only
			STATUS	current
	DESCRIPTION ""
			::= { mbus44 91 }

mbus44VIF2B		OBJECT-TYPE
			SYNTAX	INTEGER
			ACCESS	read-only
			STATUS	current
	DESCRIPTION ""
			::= { mbus44 92 }

mbus44Value2B		OBJECT-TYPE
			SYNTAX	INTEGER
			ACCESS	read-only
			STATUS	current
	DESCRIPTION ""
			::= { mbus44 93 }

mbus44VIF2C		OBJECT-TYPE
			SYNTAX	INTEGER
			ACCESS	read-only
			STATUS	current
	DESCRIPTION ""
			::= { mbus44 94 }

mbus44Value2C		OBJECT-TYPE
			SYNTAX	INTEGER
			ACCESS	read-only
			STATUS	current
	DESCRIPTION ""
			::= { mbus44 95 }

mbus44VIF2D		OBJECT-TYPE
			SYNTAX	INTEGER
			ACCESS	read-only
			STATUS	current
	DESCRIPTION ""
			::= { mbus44 96 }

mbus44Value2D		OBJECT-TYPE
			SYNTAX	INTEGER
			ACCESS	read-only
			STATUS	current
	DESCRIPTION ""
			::= { mbus44 97 }

mbus44VIF2E		OBJECT-TYPE
			SYNTAX	INTEGER
			ACCESS	read-only
			STATUS	current
	DESCRIPTION ""
			::= { mbus44 98 }

mbus44Value2E		OBJECT-TYPE
			SYNTAX	INTEGER
			ACCESS	read-only
			STATUS	current
	DESCRIPTION ""
			::= { mbus44 99 }

mbus44VIF2F		OBJECT-TYPE
			SYNTAX	INTEGER
			ACCESS	read-only
			STATUS	current
	DESCRIPTION ""
			::= { mbus44 100 }

mbus44Value2F		OBJECT-TYPE
			SYNTAX	INTEGER
			ACCESS	read-only
			STATUS	current
	DESCRIPTION ""
			::= { mbus44 101 }

mbus45			OBJECT IDENTIFIER ::= { mbus 69 }

mbus45IdNumber		OBJECT-TYPE
			SYNTAX	Gauge
			ACCESS	read-only
			STATUS	current
	DESCRIPTION ""
			::= { mbus45 1 }

mbus45Manufacturer	OBJECT-TYPE
			SYNTAX	Gauge
			ACCESS	read-only
			STATUS	current
	DESCRIPTION ""
			::= { mbus45 2 }

mbus45Version		OBJECT-TYPE
			SYNTAX	Gauge
			ACCESS	read-only
			STATUS	current
	DESCRIPTION ""
			::= { mbus45 3 }

mbus45Medium		OBJECT-TYPE
			SYNTAX	Gauge
			ACCESS	read-only
			STATUS	current
	DESCRIPTION ""
			::= { mbus45 4 }

mbus45Status		OBJECT-TYPE
			SYNTAX	Gauge
			ACCESS	read-only
			STATUS	current
	DESCRIPTION ""
			::= { mbus45 5 }

mbus45VIF00		OBJECT-TYPE
			SYNTAX	INTEGER
			ACCESS	read-only
			STATUS	current
	DESCRIPTION ""
			::= { mbus45 6 }

mbus45Value00		OBJECT-TYPE
			SYNTAX	INTEGER
			ACCESS	read-only
			STATUS	current
	DESCRIPTION ""
			::= { mbus45 7 }

mbus45VIF01		OBJECT-TYPE
			SYNTAX	INTEGER
			ACCESS	read-only
			STATUS	current
	DESCRIPTION ""
			::= { mbus45 8 }

mbus45Value01		OBJECT-TYPE
			SYNTAX	INTEGER
			ACCESS	read-only
			STATUS	current
	DESCRIPTION ""
			::= { mbus45 9 }

mbus45VIF02		OBJECT-TYPE
			SYNTAX	INTEGER
			ACCESS	read-only
			STATUS	current
	DESCRIPTION ""
			::= { mbus45 10 }

mbus45Value02		OBJECT-TYPE
			SYNTAX	INTEGER
			ACCESS	read-only
			STATUS	current
	DESCRIPTION ""
			::= { mbus45 11 }

mbus45VIF03		OBJECT-TYPE
			SYNTAX	INTEGER
			ACCESS	read-only
			STATUS	current
	DESCRIPTION ""
			::= { mbus45 12 }

mbus45Value03		OBJECT-TYPE
			SYNTAX	INTEGER
			ACCESS	read-only
			STATUS	current
	DESCRIPTION ""
			::= { mbus45 13 }

mbus45VIF04		OBJECT-TYPE
			SYNTAX	INTEGER
			ACCESS	read-only
			STATUS	current
	DESCRIPTION ""
			::= { mbus45 14 }

mbus45Value04		OBJECT-TYPE
			SYNTAX	INTEGER
			ACCESS	read-only
			STATUS	current
	DESCRIPTION ""
			::= { mbus45 15 }

mbus45VIF05		OBJECT-TYPE
			SYNTAX	INTEGER
			ACCESS	read-only
			STATUS	current
	DESCRIPTION ""
			::= { mbus45 16 }

mbus45Value05		OBJECT-TYPE
			SYNTAX	INTEGER
			ACCESS	read-only
			STATUS	current
	DESCRIPTION ""
			::= { mbus45 17 }

mbus45VIF06		OBJECT-TYPE
			SYNTAX	INTEGER
			ACCESS	read-only
			STATUS	current
	DESCRIPTION ""
			::= { mbus45 18 }

mbus45Value06		OBJECT-TYPE
			SYNTAX	INTEGER
			ACCESS	read-only
			STATUS	current
	DESCRIPTION ""
			::= { mbus45 19 }

mbus45VIF07		OBJECT-TYPE
			SYNTAX	INTEGER
			ACCESS	read-only
			STATUS	current
	DESCRIPTION ""
			::= { mbus45 20 }

mbus45Value07		OBJECT-TYPE
			SYNTAX	INTEGER
			ACCESS	read-only
			STATUS	current
	DESCRIPTION ""
			::= { mbus45 21 }

mbus45VIF08		OBJECT-TYPE
			SYNTAX	INTEGER
			ACCESS	read-only
			STATUS	current
	DESCRIPTION ""
			::= { mbus45 22 }

mbus45Value08		OBJECT-TYPE
			SYNTAX	INTEGER
			ACCESS	read-only
			STATUS	current
	DESCRIPTION ""
			::= { mbus45 23 }

mbus45VIF09		OBJECT-TYPE
			SYNTAX	INTEGER
			ACCESS	read-only
			STATUS	current
	DESCRIPTION ""
			::= { mbus45 24 }

mbus45Value09		OBJECT-TYPE
			SYNTAX	INTEGER
			ACCESS	read-only
			STATUS	current
	DESCRIPTION ""
			::= { mbus45 25 }

mbus45VIF0A		OBJECT-TYPE
			SYNTAX	INTEGER
			ACCESS	read-only
			STATUS	current
	DESCRIPTION ""
			::= { mbus45 26 }

mbus45Value0A		OBJECT-TYPE
			SYNTAX	INTEGER
			ACCESS	read-only
			STATUS	current
	DESCRIPTION ""
			::= { mbus45 27 }

mbus45VIF0B		OBJECT-TYPE
			SYNTAX	INTEGER
			ACCESS	read-only
			STATUS	current
	DESCRIPTION ""
			::= { mbus45 28 }

mbus45Value0B		OBJECT-TYPE
			SYNTAX	INTEGER
			ACCESS	read-only
			STATUS	current
	DESCRIPTION ""
			::= { mbus45 29 }

mbus45VIF0C		OBJECT-TYPE
			SYNTAX	INTEGER
			ACCESS	read-only
			STATUS	current
	DESCRIPTION ""
			::= { mbus45 30 }

mbus45Value0C		OBJECT-TYPE
			SYNTAX	INTEGER
			ACCESS	read-only
			STATUS	current
	DESCRIPTION ""
			::= { mbus45 31 }

mbus45VIF0D		OBJECT-TYPE
			SYNTAX	INTEGER
			ACCESS	read-only
			STATUS	current
	DESCRIPTION ""
			::= { mbus45 32 }

mbus45Value0D		OBJECT-TYPE
			SYNTAX	INTEGER
			ACCESS	read-only
			STATUS	current
	DESCRIPTION ""
			::= { mbus45 33 }

mbus45VIF0E		OBJECT-TYPE
			SYNTAX	INTEGER
			ACCESS	read-only
			STATUS	current
	DESCRIPTION ""
			::= { mbus45 34 }

mbus45Value0E		OBJECT-TYPE
			SYNTAX	INTEGER
			ACCESS	read-only
			STATUS	current
	DESCRIPTION ""
			::= { mbus45 35 }

mbus45VIF0F		OBJECT-TYPE
			SYNTAX	INTEGER
			ACCESS	read-only
			STATUS	current
	DESCRIPTION ""
			::= { mbus45 36 }

mbus45Value0F		OBJECT-TYPE
			SYNTAX	INTEGER
			ACCESS	read-only
			STATUS	current
	DESCRIPTION ""
			::= { mbus45 37 }

mbus45VIF10		OBJECT-TYPE
			SYNTAX	INTEGER
			ACCESS	read-only
			STATUS	current
	DESCRIPTION ""
			::= { mbus45 38 }

mbus45Value10		OBJECT-TYPE
			SYNTAX	INTEGER
			ACCESS	read-only
			STATUS	current
	DESCRIPTION ""
			::= { mbus45 39 }

mbus45VIF11		OBJECT-TYPE
			SYNTAX	INTEGER
			ACCESS	read-only
			STATUS	current
	DESCRIPTION ""
			::= { mbus45 40 }

mbus45Value11		OBJECT-TYPE
			SYNTAX	INTEGER
			ACCESS	read-only
			STATUS	current
	DESCRIPTION ""
			::= { mbus45 41 }

mbus45VIF12		OBJECT-TYPE
			SYNTAX	INTEGER
			ACCESS	read-only
			STATUS	current
	DESCRIPTION ""
			::= { mbus45 42 }

mbus45Value12		OBJECT-TYPE
			SYNTAX	INTEGER
			ACCESS	read-only
			STATUS	current
	DESCRIPTION ""
			::= { mbus45 43 }

mbus45VIF13		OBJECT-TYPE
			SYNTAX	INTEGER
			ACCESS	read-only
			STATUS	current
	DESCRIPTION ""
			::= { mbus45 44 }

mbus45Value13		OBJECT-TYPE
			SYNTAX	INTEGER
			ACCESS	read-only
			STATUS	current
	DESCRIPTION ""
			::= { mbus45 45 }

mbus45VIF14		OBJECT-TYPE
			SYNTAX	INTEGER
			ACCESS	read-only
			STATUS	current
	DESCRIPTION ""
			::= { mbus45 46 }

mbus45Value14		OBJECT-TYPE
			SYNTAX	INTEGER
			ACCESS	read-only
			STATUS	current
	DESCRIPTION ""
			::= { mbus45 47 }

mbus45VIF15		OBJECT-TYPE
			SYNTAX	INTEGER
			ACCESS	read-only
			STATUS	current
	DESCRIPTION ""
			::= { mbus45 48 }

mbus45Value15		OBJECT-TYPE
			SYNTAX	INTEGER
			ACCESS	read-only
			STATUS	current
	DESCRIPTION ""
			::= { mbus45 49 }

mbus45VIF16		OBJECT-TYPE
			SYNTAX	INTEGER
			ACCESS	read-only
			STATUS	current
	DESCRIPTION ""
			::= { mbus45 50 }

mbus45Value16		OBJECT-TYPE
			SYNTAX	INTEGER
			ACCESS	read-only
			STATUS	current
	DESCRIPTION ""
			::= { mbus45 51 }

mbus45VIF17		OBJECT-TYPE
			SYNTAX	INTEGER
			ACCESS	read-only
			STATUS	current
	DESCRIPTION ""
			::= { mbus45 52 }

mbus45Value17		OBJECT-TYPE
			SYNTAX	INTEGER
			ACCESS	read-only
			STATUS	current
	DESCRIPTION ""
			::= { mbus45 53 }

mbus45VIF18		OBJECT-TYPE
			SYNTAX	INTEGER
			ACCESS	read-only
			STATUS	current
	DESCRIPTION ""
			::= { mbus45 54 }

mbus45Value18		OBJECT-TYPE
			SYNTAX	INTEGER
			ACCESS	read-only
			STATUS	current
	DESCRIPTION ""
			::= { mbus45 55 }

mbus45VIF19		OBJECT-TYPE
			SYNTAX	INTEGER
			ACCESS	read-only
			STATUS	current
	DESCRIPTION ""
			::= { mbus45 56 }

mbus45Value19		OBJECT-TYPE
			SYNTAX	INTEGER
			ACCESS	read-only
			STATUS	current
	DESCRIPTION ""
			::= { mbus45 57 }

mbus45VIF1A		OBJECT-TYPE
			SYNTAX	INTEGER
			ACCESS	read-only
			STATUS	current
	DESCRIPTION ""
			::= { mbus45 58 }

mbus45Value1A		OBJECT-TYPE
			SYNTAX	INTEGER
			ACCESS	read-only
			STATUS	current
	DESCRIPTION ""
			::= { mbus45 59 }

mbus45VIF1B		OBJECT-TYPE
			SYNTAX	INTEGER
			ACCESS	read-only
			STATUS	current
	DESCRIPTION ""
			::= { mbus45 60 }

mbus45Value1B		OBJECT-TYPE
			SYNTAX	INTEGER
			ACCESS	read-only
			STATUS	current
	DESCRIPTION ""
			::= { mbus45 61 }

mbus45VIF1C		OBJECT-TYPE
			SYNTAX	INTEGER
			ACCESS	read-only
			STATUS	current
	DESCRIPTION ""
			::= { mbus45 62 }

mbus45Value1C		OBJECT-TYPE
			SYNTAX	INTEGER
			ACCESS	read-only
			STATUS	current
	DESCRIPTION ""
			::= { mbus45 63 }

mbus45VIF1D		OBJECT-TYPE
			SYNTAX	INTEGER
			ACCESS	read-only
			STATUS	current
	DESCRIPTION ""
			::= { mbus45 64 }

mbus45Value1D		OBJECT-TYPE
			SYNTAX	INTEGER
			ACCESS	read-only
			STATUS	current
	DESCRIPTION ""
			::= { mbus45 65 }

mbus45VIF1E		OBJECT-TYPE
			SYNTAX	INTEGER
			ACCESS	read-only
			STATUS	current
	DESCRIPTION ""
			::= { mbus45 66 }

mbus45Value1E		OBJECT-TYPE
			SYNTAX	INTEGER
			ACCESS	read-only
			STATUS	current
	DESCRIPTION ""
			::= { mbus45 67 }

mbus45VIF1F		OBJECT-TYPE
			SYNTAX	INTEGER
			ACCESS	read-only
			STATUS	current
	DESCRIPTION ""
			::= { mbus45 68 }

mbus45Value1F		OBJECT-TYPE
			SYNTAX	INTEGER
			ACCESS	read-only
			STATUS	current
	DESCRIPTION ""
			::= { mbus45 69 }

mbus45VIF20		OBJECT-TYPE
			SYNTAX	INTEGER
			ACCESS	read-only
			STATUS	current
	DESCRIPTION ""
			::= { mbus45 70 }

mbus45Value20		OBJECT-TYPE
			SYNTAX	INTEGER
			ACCESS	read-only
			STATUS	current
	DESCRIPTION ""
			::= { mbus45 71 }

mbus45VIF21		OBJECT-TYPE
			SYNTAX	INTEGER
			ACCESS	read-only
			STATUS	current
	DESCRIPTION ""
			::= { mbus45 72 }

mbus45Value21		OBJECT-TYPE
			SYNTAX	INTEGER
			ACCESS	read-only
			STATUS	current
	DESCRIPTION ""
			::= { mbus45 73 }

mbus45VIF22		OBJECT-TYPE
			SYNTAX	INTEGER
			ACCESS	read-only
			STATUS	current
	DESCRIPTION ""
			::= { mbus45 74 }

mbus45Value22		OBJECT-TYPE
			SYNTAX	INTEGER
			ACCESS	read-only
			STATUS	current
	DESCRIPTION ""
			::= { mbus45 75 }

mbus45VIF23		OBJECT-TYPE
			SYNTAX	INTEGER
			ACCESS	read-only
			STATUS	current
	DESCRIPTION ""
			::= { mbus45 76 }

mbus45Value23		OBJECT-TYPE
			SYNTAX	INTEGER
			ACCESS	read-only
			STATUS	current
	DESCRIPTION ""
			::= { mbus45 77 }

mbus45VIF24		OBJECT-TYPE
			SYNTAX	INTEGER
			ACCESS	read-only
			STATUS	current
	DESCRIPTION ""
			::= { mbus45 78 }

mbus45Value24		OBJECT-TYPE
			SYNTAX	INTEGER
			ACCESS	read-only
			STATUS	current
	DESCRIPTION ""
			::= { mbus45 79 }

mbus45VIF25		OBJECT-TYPE
			SYNTAX	INTEGER
			ACCESS	read-only
			STATUS	current
	DESCRIPTION ""
			::= { mbus45 80 }

mbus45Value25		OBJECT-TYPE
			SYNTAX	INTEGER
			ACCESS	read-only
			STATUS	current
	DESCRIPTION ""
			::= { mbus45 81 }

mbus45VIF26		OBJECT-TYPE
			SYNTAX	INTEGER
			ACCESS	read-only
			STATUS	current
	DESCRIPTION ""
			::= { mbus45 82 }

mbus45Value26		OBJECT-TYPE
			SYNTAX	INTEGER
			ACCESS	read-only
			STATUS	current
	DESCRIPTION ""
			::= { mbus45 83 }

mbus45VIF27		OBJECT-TYPE
			SYNTAX	INTEGER
			ACCESS	read-only
			STATUS	current
	DESCRIPTION ""
			::= { mbus45 84 }

mbus45Value27		OBJECT-TYPE
			SYNTAX	INTEGER
			ACCESS	read-only
			STATUS	current
	DESCRIPTION ""
			::= { mbus45 85 }

mbus45VIF28		OBJECT-TYPE
			SYNTAX	INTEGER
			ACCESS	read-only
			STATUS	current
	DESCRIPTION ""
			::= { mbus45 86 }

mbus45Value28		OBJECT-TYPE
			SYNTAX	INTEGER
			ACCESS	read-only
			STATUS	current
	DESCRIPTION ""
			::= { mbus45 87 }

mbus45VIF29		OBJECT-TYPE
			SYNTAX	INTEGER
			ACCESS	read-only
			STATUS	current
	DESCRIPTION ""
			::= { mbus45 88 }

mbus45Value29		OBJECT-TYPE
			SYNTAX	INTEGER
			ACCESS	read-only
			STATUS	current
	DESCRIPTION ""
			::= { mbus45 89 }

mbus45VIF2A		OBJECT-TYPE
			SYNTAX	INTEGER
			ACCESS	read-only
			STATUS	current
	DESCRIPTION ""
			::= { mbus45 90 }

mbus45Value2A		OBJECT-TYPE
			SYNTAX	INTEGER
			ACCESS	read-only
			STATUS	current
	DESCRIPTION ""
			::= { mbus45 91 }

mbus45VIF2B		OBJECT-TYPE
			SYNTAX	INTEGER
			ACCESS	read-only
			STATUS	current
	DESCRIPTION ""
			::= { mbus45 92 }

mbus45Value2B		OBJECT-TYPE
			SYNTAX	INTEGER
			ACCESS	read-only
			STATUS	current
	DESCRIPTION ""
			::= { mbus45 93 }

mbus45VIF2C		OBJECT-TYPE
			SYNTAX	INTEGER
			ACCESS	read-only
			STATUS	current
	DESCRIPTION ""
			::= { mbus45 94 }

mbus45Value2C		OBJECT-TYPE
			SYNTAX	INTEGER
			ACCESS	read-only
			STATUS	current
	DESCRIPTION ""
			::= { mbus45 95 }

mbus45VIF2D		OBJECT-TYPE
			SYNTAX	INTEGER
			ACCESS	read-only
			STATUS	current
	DESCRIPTION ""
			::= { mbus45 96 }

mbus45Value2D		OBJECT-TYPE
			SYNTAX	INTEGER
			ACCESS	read-only
			STATUS	current
	DESCRIPTION ""
			::= { mbus45 97 }

mbus45VIF2E		OBJECT-TYPE
			SYNTAX	INTEGER
			ACCESS	read-only
			STATUS	current
	DESCRIPTION ""
			::= { mbus45 98 }

mbus45Value2E		OBJECT-TYPE
			SYNTAX	INTEGER
			ACCESS	read-only
			STATUS	current
	DESCRIPTION ""
			::= { mbus45 99 }

mbus45VIF2F		OBJECT-TYPE
			SYNTAX	INTEGER
			ACCESS	read-only
			STATUS	current
	DESCRIPTION ""
			::= { mbus45 100 }

mbus45Value2F		OBJECT-TYPE
			SYNTAX	INTEGER
			ACCESS	read-only
			STATUS	current
	DESCRIPTION ""
			::= { mbus45 101 }

mbus46			OBJECT IDENTIFIER ::= { mbus 70 }

mbus46IdNumber		OBJECT-TYPE
			SYNTAX	Gauge
			ACCESS	read-only
			STATUS	current
	DESCRIPTION ""
			::= { mbus46 1 }

mbus46Manufacturer	OBJECT-TYPE
			SYNTAX	Gauge
			ACCESS	read-only
			STATUS	current
	DESCRIPTION ""
			::= { mbus46 2 }

mbus46Version		OBJECT-TYPE
			SYNTAX	Gauge
			ACCESS	read-only
			STATUS	current
	DESCRIPTION ""
			::= { mbus46 3 }

mbus46Medium		OBJECT-TYPE
			SYNTAX	Gauge
			ACCESS	read-only
			STATUS	current
	DESCRIPTION ""
			::= { mbus46 4 }

mbus46Status		OBJECT-TYPE
			SYNTAX	Gauge
			ACCESS	read-only
			STATUS	current
	DESCRIPTION ""
			::= { mbus46 5 }

mbus46VIF00		OBJECT-TYPE
			SYNTAX	INTEGER
			ACCESS	read-only
			STATUS	current
	DESCRIPTION ""
			::= { mbus46 6 }

mbus46Value00		OBJECT-TYPE
			SYNTAX	INTEGER
			ACCESS	read-only
			STATUS	current
	DESCRIPTION ""
			::= { mbus46 7 }

mbus46VIF01		OBJECT-TYPE
			SYNTAX	INTEGER
			ACCESS	read-only
			STATUS	current
	DESCRIPTION ""
			::= { mbus46 8 }

mbus46Value01		OBJECT-TYPE
			SYNTAX	INTEGER
			ACCESS	read-only
			STATUS	current
	DESCRIPTION ""
			::= { mbus46 9 }

mbus46VIF02		OBJECT-TYPE
			SYNTAX	INTEGER
			ACCESS	read-only
			STATUS	current
	DESCRIPTION ""
			::= { mbus46 10 }

mbus46Value02		OBJECT-TYPE
			SYNTAX	INTEGER
			ACCESS	read-only
			STATUS	current
	DESCRIPTION ""
			::= { mbus46 11 }

mbus46VIF03		OBJECT-TYPE
			SYNTAX	INTEGER
			ACCESS	read-only
			STATUS	current
	DESCRIPTION ""
			::= { mbus46 12 }

mbus46Value03		OBJECT-TYPE
			SYNTAX	INTEGER
			ACCESS	read-only
			STATUS	current
	DESCRIPTION ""
			::= { mbus46 13 }

mbus46VIF04		OBJECT-TYPE
			SYNTAX	INTEGER
			ACCESS	read-only
			STATUS	current
	DESCRIPTION ""
			::= { mbus46 14 }

mbus46Value04		OBJECT-TYPE
			SYNTAX	INTEGER
			ACCESS	read-only
			STATUS	current
	DESCRIPTION ""
			::= { mbus46 15 }

mbus46VIF05		OBJECT-TYPE
			SYNTAX	INTEGER
			ACCESS	read-only
			STATUS	current
	DESCRIPTION ""
			::= { mbus46 16 }

mbus46Value05		OBJECT-TYPE
			SYNTAX	INTEGER
			ACCESS	read-only
			STATUS	current
	DESCRIPTION ""
			::= { mbus46 17 }

mbus46VIF06		OBJECT-TYPE
			SYNTAX	INTEGER
			ACCESS	read-only
			STATUS	current
	DESCRIPTION ""
			::= { mbus46 18 }

mbus46Value06		OBJECT-TYPE
			SYNTAX	INTEGER
			ACCESS	read-only
			STATUS	current
	DESCRIPTION ""
			::= { mbus46 19 }

mbus46VIF07		OBJECT-TYPE
			SYNTAX	INTEGER
			ACCESS	read-only
			STATUS	current
	DESCRIPTION ""
			::= { mbus46 20 }

mbus46Value07		OBJECT-TYPE
			SYNTAX	INTEGER
			ACCESS	read-only
			STATUS	current
	DESCRIPTION ""
			::= { mbus46 21 }

mbus46VIF08		OBJECT-TYPE
			SYNTAX	INTEGER
			ACCESS	read-only
			STATUS	current
	DESCRIPTION ""
			::= { mbus46 22 }

mbus46Value08		OBJECT-TYPE
			SYNTAX	INTEGER
			ACCESS	read-only
			STATUS	current
	DESCRIPTION ""
			::= { mbus46 23 }

mbus46VIF09		OBJECT-TYPE
			SYNTAX	INTEGER
			ACCESS	read-only
			STATUS	current
	DESCRIPTION ""
			::= { mbus46 24 }

mbus46Value09		OBJECT-TYPE
			SYNTAX	INTEGER
			ACCESS	read-only
			STATUS	current
	DESCRIPTION ""
			::= { mbus46 25 }

mbus46VIF0A		OBJECT-TYPE
			SYNTAX	INTEGER
			ACCESS	read-only
			STATUS	current
	DESCRIPTION ""
			::= { mbus46 26 }

mbus46Value0A		OBJECT-TYPE
			SYNTAX	INTEGER
			ACCESS	read-only
			STATUS	current
	DESCRIPTION ""
			::= { mbus46 27 }

mbus46VIF0B		OBJECT-TYPE
			SYNTAX	INTEGER
			ACCESS	read-only
			STATUS	current
	DESCRIPTION ""
			::= { mbus46 28 }

mbus46Value0B		OBJECT-TYPE
			SYNTAX	INTEGER
			ACCESS	read-only
			STATUS	current
	DESCRIPTION ""
			::= { mbus46 29 }

mbus46VIF0C		OBJECT-TYPE
			SYNTAX	INTEGER
			ACCESS	read-only
			STATUS	current
	DESCRIPTION ""
			::= { mbus46 30 }

mbus46Value0C		OBJECT-TYPE
			SYNTAX	INTEGER
			ACCESS	read-only
			STATUS	current
	DESCRIPTION ""
			::= { mbus46 31 }

mbus46VIF0D		OBJECT-TYPE
			SYNTAX	INTEGER
			ACCESS	read-only
			STATUS	current
	DESCRIPTION ""
			::= { mbus46 32 }

mbus46Value0D		OBJECT-TYPE
			SYNTAX	INTEGER
			ACCESS	read-only
			STATUS	current
	DESCRIPTION ""
			::= { mbus46 33 }

mbus46VIF0E		OBJECT-TYPE
			SYNTAX	INTEGER
			ACCESS	read-only
			STATUS	current
	DESCRIPTION ""
			::= { mbus46 34 }

mbus46Value0E		OBJECT-TYPE
			SYNTAX	INTEGER
			ACCESS	read-only
			STATUS	current
	DESCRIPTION ""
			::= { mbus46 35 }

mbus46VIF0F		OBJECT-TYPE
			SYNTAX	INTEGER
			ACCESS	read-only
			STATUS	current
	DESCRIPTION ""
			::= { mbus46 36 }

mbus46Value0F		OBJECT-TYPE
			SYNTAX	INTEGER
			ACCESS	read-only
			STATUS	current
	DESCRIPTION ""
			::= { mbus46 37 }

mbus46VIF10		OBJECT-TYPE
			SYNTAX	INTEGER
			ACCESS	read-only
			STATUS	current
	DESCRIPTION ""
			::= { mbus46 38 }

mbus46Value10		OBJECT-TYPE
			SYNTAX	INTEGER
			ACCESS	read-only
			STATUS	current
	DESCRIPTION ""
			::= { mbus46 39 }

mbus46VIF11		OBJECT-TYPE
			SYNTAX	INTEGER
			ACCESS	read-only
			STATUS	current
	DESCRIPTION ""
			::= { mbus46 40 }

mbus46Value11		OBJECT-TYPE
			SYNTAX	INTEGER
			ACCESS	read-only
			STATUS	current
	DESCRIPTION ""
			::= { mbus46 41 }

mbus46VIF12		OBJECT-TYPE
			SYNTAX	INTEGER
			ACCESS	read-only
			STATUS	current
	DESCRIPTION ""
			::= { mbus46 42 }

mbus46Value12		OBJECT-TYPE
			SYNTAX	INTEGER
			ACCESS	read-only
			STATUS	current
	DESCRIPTION ""
			::= { mbus46 43 }

mbus46VIF13		OBJECT-TYPE
			SYNTAX	INTEGER
			ACCESS	read-only
			STATUS	current
	DESCRIPTION ""
			::= { mbus46 44 }

mbus46Value13		OBJECT-TYPE
			SYNTAX	INTEGER
			ACCESS	read-only
			STATUS	current
	DESCRIPTION ""
			::= { mbus46 45 }

mbus46VIF14		OBJECT-TYPE
			SYNTAX	INTEGER
			ACCESS	read-only
			STATUS	current
	DESCRIPTION ""
			::= { mbus46 46 }

mbus46Value14		OBJECT-TYPE
			SYNTAX	INTEGER
			ACCESS	read-only
			STATUS	current
	DESCRIPTION ""
			::= { mbus46 47 }

mbus46VIF15		OBJECT-TYPE
			SYNTAX	INTEGER
			ACCESS	read-only
			STATUS	current
	DESCRIPTION ""
			::= { mbus46 48 }

mbus46Value15		OBJECT-TYPE
			SYNTAX	INTEGER
			ACCESS	read-only
			STATUS	current
	DESCRIPTION ""
			::= { mbus46 49 }

mbus46VIF16		OBJECT-TYPE
			SYNTAX	INTEGER
			ACCESS	read-only
			STATUS	current
	DESCRIPTION ""
			::= { mbus46 50 }

mbus46Value16		OBJECT-TYPE
			SYNTAX	INTEGER
			ACCESS	read-only
			STATUS	current
	DESCRIPTION ""
			::= { mbus46 51 }

mbus46VIF17		OBJECT-TYPE
			SYNTAX	INTEGER
			ACCESS	read-only
			STATUS	current
	DESCRIPTION ""
			::= { mbus46 52 }

mbus46Value17		OBJECT-TYPE
			SYNTAX	INTEGER
			ACCESS	read-only
			STATUS	current
	DESCRIPTION ""
			::= { mbus46 53 }

mbus46VIF18		OBJECT-TYPE
			SYNTAX	INTEGER
			ACCESS	read-only
			STATUS	current
	DESCRIPTION ""
			::= { mbus46 54 }

mbus46Value18		OBJECT-TYPE
			SYNTAX	INTEGER
			ACCESS	read-only
			STATUS	current
	DESCRIPTION ""
			::= { mbus46 55 }

mbus46VIF19		OBJECT-TYPE
			SYNTAX	INTEGER
			ACCESS	read-only
			STATUS	current
	DESCRIPTION ""
			::= { mbus46 56 }

mbus46Value19		OBJECT-TYPE
			SYNTAX	INTEGER
			ACCESS	read-only
			STATUS	current
	DESCRIPTION ""
			::= { mbus46 57 }

mbus46VIF1A		OBJECT-TYPE
			SYNTAX	INTEGER
			ACCESS	read-only
			STATUS	current
	DESCRIPTION ""
			::= { mbus46 58 }

mbus46Value1A		OBJECT-TYPE
			SYNTAX	INTEGER
			ACCESS	read-only
			STATUS	current
	DESCRIPTION ""
			::= { mbus46 59 }

mbus46VIF1B		OBJECT-TYPE
			SYNTAX	INTEGER
			ACCESS	read-only
			STATUS	current
	DESCRIPTION ""
			::= { mbus46 60 }

mbus46Value1B		OBJECT-TYPE
			SYNTAX	INTEGER
			ACCESS	read-only
			STATUS	current
	DESCRIPTION ""
			::= { mbus46 61 }

mbus46VIF1C		OBJECT-TYPE
			SYNTAX	INTEGER
			ACCESS	read-only
			STATUS	current
	DESCRIPTION ""
			::= { mbus46 62 }

mbus46Value1C		OBJECT-TYPE
			SYNTAX	INTEGER
			ACCESS	read-only
			STATUS	current
	DESCRIPTION ""
			::= { mbus46 63 }

mbus46VIF1D		OBJECT-TYPE
			SYNTAX	INTEGER
			ACCESS	read-only
			STATUS	current
	DESCRIPTION ""
			::= { mbus46 64 }

mbus46Value1D		OBJECT-TYPE
			SYNTAX	INTEGER
			ACCESS	read-only
			STATUS	current
	DESCRIPTION ""
			::= { mbus46 65 }

mbus46VIF1E		OBJECT-TYPE
			SYNTAX	INTEGER
			ACCESS	read-only
			STATUS	current
	DESCRIPTION ""
			::= { mbus46 66 }

mbus46Value1E		OBJECT-TYPE
			SYNTAX	INTEGER
			ACCESS	read-only
			STATUS	current
	DESCRIPTION ""
			::= { mbus46 67 }

mbus46VIF1F		OBJECT-TYPE
			SYNTAX	INTEGER
			ACCESS	read-only
			STATUS	current
	DESCRIPTION ""
			::= { mbus46 68 }

mbus46Value1F		OBJECT-TYPE
			SYNTAX	INTEGER
			ACCESS	read-only
			STATUS	current
	DESCRIPTION ""
			::= { mbus46 69 }

mbus46VIF20		OBJECT-TYPE
			SYNTAX	INTEGER
			ACCESS	read-only
			STATUS	current
	DESCRIPTION ""
			::= { mbus46 70 }

mbus46Value20		OBJECT-TYPE
			SYNTAX	INTEGER
			ACCESS	read-only
			STATUS	current
	DESCRIPTION ""
			::= { mbus46 71 }

mbus46VIF21		OBJECT-TYPE
			SYNTAX	INTEGER
			ACCESS	read-only
			STATUS	current
	DESCRIPTION ""
			::= { mbus46 72 }

mbus46Value21		OBJECT-TYPE
			SYNTAX	INTEGER
			ACCESS	read-only
			STATUS	current
	DESCRIPTION ""
			::= { mbus46 73 }

mbus46VIF22		OBJECT-TYPE
			SYNTAX	INTEGER
			ACCESS	read-only
			STATUS	current
	DESCRIPTION ""
			::= { mbus46 74 }

mbus46Value22		OBJECT-TYPE
			SYNTAX	INTEGER
			ACCESS	read-only
			STATUS	current
	DESCRIPTION ""
			::= { mbus46 75 }

mbus46VIF23		OBJECT-TYPE
			SYNTAX	INTEGER
			ACCESS	read-only
			STATUS	current
	DESCRIPTION ""
			::= { mbus46 76 }

mbus46Value23		OBJECT-TYPE
			SYNTAX	INTEGER
			ACCESS	read-only
			STATUS	current
	DESCRIPTION ""
			::= { mbus46 77 }

mbus46VIF24		OBJECT-TYPE
			SYNTAX	INTEGER
			ACCESS	read-only
			STATUS	current
	DESCRIPTION ""
			::= { mbus46 78 }

mbus46Value24		OBJECT-TYPE
			SYNTAX	INTEGER
			ACCESS	read-only
			STATUS	current
	DESCRIPTION ""
			::= { mbus46 79 }

mbus46VIF25		OBJECT-TYPE
			SYNTAX	INTEGER
			ACCESS	read-only
			STATUS	current
	DESCRIPTION ""
			::= { mbus46 80 }

mbus46Value25		OBJECT-TYPE
			SYNTAX	INTEGER
			ACCESS	read-only
			STATUS	current
	DESCRIPTION ""
			::= { mbus46 81 }

mbus46VIF26		OBJECT-TYPE
			SYNTAX	INTEGER
			ACCESS	read-only
			STATUS	current
	DESCRIPTION ""
			::= { mbus46 82 }

mbus46Value26		OBJECT-TYPE
			SYNTAX	INTEGER
			ACCESS	read-only
			STATUS	current
	DESCRIPTION ""
			::= { mbus46 83 }

mbus46VIF27		OBJECT-TYPE
			SYNTAX	INTEGER
			ACCESS	read-only
			STATUS	current
	DESCRIPTION ""
			::= { mbus46 84 }

mbus46Value27		OBJECT-TYPE
			SYNTAX	INTEGER
			ACCESS	read-only
			STATUS	current
	DESCRIPTION ""
			::= { mbus46 85 }

mbus46VIF28		OBJECT-TYPE
			SYNTAX	INTEGER
			ACCESS	read-only
			STATUS	current
	DESCRIPTION ""
			::= { mbus46 86 }

mbus46Value28		OBJECT-TYPE
			SYNTAX	INTEGER
			ACCESS	read-only
			STATUS	current
	DESCRIPTION ""
			::= { mbus46 87 }

mbus46VIF29		OBJECT-TYPE
			SYNTAX	INTEGER
			ACCESS	read-only
			STATUS	current
	DESCRIPTION ""
			::= { mbus46 88 }

mbus46Value29		OBJECT-TYPE
			SYNTAX	INTEGER
			ACCESS	read-only
			STATUS	current
	DESCRIPTION ""
			::= { mbus46 89 }

mbus46VIF2A		OBJECT-TYPE
			SYNTAX	INTEGER
			ACCESS	read-only
			STATUS	current
	DESCRIPTION ""
			::= { mbus46 90 }

mbus46Value2A		OBJECT-TYPE
			SYNTAX	INTEGER
			ACCESS	read-only
			STATUS	current
	DESCRIPTION ""
			::= { mbus46 91 }

mbus46VIF2B		OBJECT-TYPE
			SYNTAX	INTEGER
			ACCESS	read-only
			STATUS	current
	DESCRIPTION ""
			::= { mbus46 92 }

mbus46Value2B		OBJECT-TYPE
			SYNTAX	INTEGER
			ACCESS	read-only
			STATUS	current
	DESCRIPTION ""
			::= { mbus46 93 }

mbus46VIF2C		OBJECT-TYPE
			SYNTAX	INTEGER
			ACCESS	read-only
			STATUS	current
	DESCRIPTION ""
			::= { mbus46 94 }

mbus46Value2C		OBJECT-TYPE
			SYNTAX	INTEGER
			ACCESS	read-only
			STATUS	current
	DESCRIPTION ""
			::= { mbus46 95 }

mbus46VIF2D		OBJECT-TYPE
			SYNTAX	INTEGER
			ACCESS	read-only
			STATUS	current
	DESCRIPTION ""
			::= { mbus46 96 }

mbus46Value2D		OBJECT-TYPE
			SYNTAX	INTEGER
			ACCESS	read-only
			STATUS	current
	DESCRIPTION ""
			::= { mbus46 97 }

mbus46VIF2E		OBJECT-TYPE
			SYNTAX	INTEGER
			ACCESS	read-only
			STATUS	current
	DESCRIPTION ""
			::= { mbus46 98 }

mbus46Value2E		OBJECT-TYPE
			SYNTAX	INTEGER
			ACCESS	read-only
			STATUS	current
	DESCRIPTION ""
			::= { mbus46 99 }

mbus46VIF2F		OBJECT-TYPE
			SYNTAX	INTEGER
			ACCESS	read-only
			STATUS	current
	DESCRIPTION ""
			::= { mbus46 100 }

mbus46Value2F		OBJECT-TYPE
			SYNTAX	INTEGER
			ACCESS	read-only
			STATUS	current
	DESCRIPTION ""
			::= { mbus46 101 }

mbus47			OBJECT IDENTIFIER ::= { mbus 71 }

mbus47IdNumber		OBJECT-TYPE
			SYNTAX	Gauge
			ACCESS	read-only
			STATUS	current
	DESCRIPTION ""
			::= { mbus47 1 }

mbus47Manufacturer	OBJECT-TYPE
			SYNTAX	Gauge
			ACCESS	read-only
			STATUS	current
	DESCRIPTION ""
			::= { mbus47 2 }

mbus47Version		OBJECT-TYPE
			SYNTAX	Gauge
			ACCESS	read-only
			STATUS	current
	DESCRIPTION ""
			::= { mbus47 3 }

mbus47Medium		OBJECT-TYPE
			SYNTAX	Gauge
			ACCESS	read-only
			STATUS	current
	DESCRIPTION ""
			::= { mbus47 4 }

mbus47Status		OBJECT-TYPE
			SYNTAX	Gauge
			ACCESS	read-only
			STATUS	current
	DESCRIPTION ""
			::= { mbus47 5 }

mbus47VIF00		OBJECT-TYPE
			SYNTAX	INTEGER
			ACCESS	read-only
			STATUS	current
	DESCRIPTION ""
			::= { mbus47 6 }

mbus47Value00		OBJECT-TYPE
			SYNTAX	INTEGER
			ACCESS	read-only
			STATUS	current
	DESCRIPTION ""
			::= { mbus47 7 }

mbus47VIF01		OBJECT-TYPE
			SYNTAX	INTEGER
			ACCESS	read-only
			STATUS	current
	DESCRIPTION ""
			::= { mbus47 8 }

mbus47Value01		OBJECT-TYPE
			SYNTAX	INTEGER
			ACCESS	read-only
			STATUS	current
	DESCRIPTION ""
			::= { mbus47 9 }

mbus47VIF02		OBJECT-TYPE
			SYNTAX	INTEGER
			ACCESS	read-only
			STATUS	current
	DESCRIPTION ""
			::= { mbus47 10 }

mbus47Value02		OBJECT-TYPE
			SYNTAX	INTEGER
			ACCESS	read-only
			STATUS	current
	DESCRIPTION ""
			::= { mbus47 11 }

mbus47VIF03		OBJECT-TYPE
			SYNTAX	INTEGER
			ACCESS	read-only
			STATUS	current
	DESCRIPTION ""
			::= { mbus47 12 }

mbus47Value03		OBJECT-TYPE
			SYNTAX	INTEGER
			ACCESS	read-only
			STATUS	current
	DESCRIPTION ""
			::= { mbus47 13 }

mbus47VIF04		OBJECT-TYPE
			SYNTAX	INTEGER
			ACCESS	read-only
			STATUS	current
	DESCRIPTION ""
			::= { mbus47 14 }

mbus47Value04		OBJECT-TYPE
			SYNTAX	INTEGER
			ACCESS	read-only
			STATUS	current
	DESCRIPTION ""
			::= { mbus47 15 }

mbus47VIF05		OBJECT-TYPE
			SYNTAX	INTEGER
			ACCESS	read-only
			STATUS	current
	DESCRIPTION ""
			::= { mbus47 16 }

mbus47Value05		OBJECT-TYPE
			SYNTAX	INTEGER
			ACCESS	read-only
			STATUS	current
	DESCRIPTION ""
			::= { mbus47 17 }

mbus47VIF06		OBJECT-TYPE
			SYNTAX	INTEGER
			ACCESS	read-only
			STATUS	current
	DESCRIPTION ""
			::= { mbus47 18 }

mbus47Value06		OBJECT-TYPE
			SYNTAX	INTEGER
			ACCESS	read-only
			STATUS	current
	DESCRIPTION ""
			::= { mbus47 19 }

mbus47VIF07		OBJECT-TYPE
			SYNTAX	INTEGER
			ACCESS	read-only
			STATUS	current
	DESCRIPTION ""
			::= { mbus47 20 }

mbus47Value07		OBJECT-TYPE
			SYNTAX	INTEGER
			ACCESS	read-only
			STATUS	current
	DESCRIPTION ""
			::= { mbus47 21 }

mbus47VIF08		OBJECT-TYPE
			SYNTAX	INTEGER
			ACCESS	read-only
			STATUS	current
	DESCRIPTION ""
			::= { mbus47 22 }

mbus47Value08		OBJECT-TYPE
			SYNTAX	INTEGER
			ACCESS	read-only
			STATUS	current
	DESCRIPTION ""
			::= { mbus47 23 }

mbus47VIF09		OBJECT-TYPE
			SYNTAX	INTEGER
			ACCESS	read-only
			STATUS	current
	DESCRIPTION ""
			::= { mbus47 24 }

mbus47Value09		OBJECT-TYPE
			SYNTAX	INTEGER
			ACCESS	read-only
			STATUS	current
	DESCRIPTION ""
			::= { mbus47 25 }

mbus47VIF0A		OBJECT-TYPE
			SYNTAX	INTEGER
			ACCESS	read-only
			STATUS	current
	DESCRIPTION ""
			::= { mbus47 26 }

mbus47Value0A		OBJECT-TYPE
			SYNTAX	INTEGER
			ACCESS	read-only
			STATUS	current
	DESCRIPTION ""
			::= { mbus47 27 }

mbus47VIF0B		OBJECT-TYPE
			SYNTAX	INTEGER
			ACCESS	read-only
			STATUS	current
	DESCRIPTION ""
			::= { mbus47 28 }

mbus47Value0B		OBJECT-TYPE
			SYNTAX	INTEGER
			ACCESS	read-only
			STATUS	current
	DESCRIPTION ""
			::= { mbus47 29 }

mbus47VIF0C		OBJECT-TYPE
			SYNTAX	INTEGER
			ACCESS	read-only
			STATUS	current
	DESCRIPTION ""
			::= { mbus47 30 }

mbus47Value0C		OBJECT-TYPE
			SYNTAX	INTEGER
			ACCESS	read-only
			STATUS	current
	DESCRIPTION ""
			::= { mbus47 31 }

mbus47VIF0D		OBJECT-TYPE
			SYNTAX	INTEGER
			ACCESS	read-only
			STATUS	current
	DESCRIPTION ""
			::= { mbus47 32 }

mbus47Value0D		OBJECT-TYPE
			SYNTAX	INTEGER
			ACCESS	read-only
			STATUS	current
	DESCRIPTION ""
			::= { mbus47 33 }

mbus47VIF0E		OBJECT-TYPE
			SYNTAX	INTEGER
			ACCESS	read-only
			STATUS	current
	DESCRIPTION ""
			::= { mbus47 34 }

mbus47Value0E		OBJECT-TYPE
			SYNTAX	INTEGER
			ACCESS	read-only
			STATUS	current
	DESCRIPTION ""
			::= { mbus47 35 }

mbus47VIF0F		OBJECT-TYPE
			SYNTAX	INTEGER
			ACCESS	read-only
			STATUS	current
	DESCRIPTION ""
			::= { mbus47 36 }

mbus47Value0F		OBJECT-TYPE
			SYNTAX	INTEGER
			ACCESS	read-only
			STATUS	current
	DESCRIPTION ""
			::= { mbus47 37 }

mbus47VIF10		OBJECT-TYPE
			SYNTAX	INTEGER
			ACCESS	read-only
			STATUS	current
	DESCRIPTION ""
			::= { mbus47 38 }

mbus47Value10		OBJECT-TYPE
			SYNTAX	INTEGER
			ACCESS	read-only
			STATUS	current
	DESCRIPTION ""
			::= { mbus47 39 }

mbus47VIF11		OBJECT-TYPE
			SYNTAX	INTEGER
			ACCESS	read-only
			STATUS	current
	DESCRIPTION ""
			::= { mbus47 40 }

mbus47Value11		OBJECT-TYPE
			SYNTAX	INTEGER
			ACCESS	read-only
			STATUS	current
	DESCRIPTION ""
			::= { mbus47 41 }

mbus47VIF12		OBJECT-TYPE
			SYNTAX	INTEGER
			ACCESS	read-only
			STATUS	current
	DESCRIPTION ""
			::= { mbus47 42 }

mbus47Value12		OBJECT-TYPE
			SYNTAX	INTEGER
			ACCESS	read-only
			STATUS	current
	DESCRIPTION ""
			::= { mbus47 43 }

mbus47VIF13		OBJECT-TYPE
			SYNTAX	INTEGER
			ACCESS	read-only
			STATUS	current
	DESCRIPTION ""
			::= { mbus47 44 }

mbus47Value13		OBJECT-TYPE
			SYNTAX	INTEGER
			ACCESS	read-only
			STATUS	current
	DESCRIPTION ""
			::= { mbus47 45 }

mbus47VIF14		OBJECT-TYPE
			SYNTAX	INTEGER
			ACCESS	read-only
			STATUS	current
	DESCRIPTION ""
			::= { mbus47 46 }

mbus47Value14		OBJECT-TYPE
			SYNTAX	INTEGER
			ACCESS	read-only
			STATUS	current
	DESCRIPTION ""
			::= { mbus47 47 }

mbus47VIF15		OBJECT-TYPE
			SYNTAX	INTEGER
			ACCESS	read-only
			STATUS	current
	DESCRIPTION ""
			::= { mbus47 48 }

mbus47Value15		OBJECT-TYPE
			SYNTAX	INTEGER
			ACCESS	read-only
			STATUS	current
	DESCRIPTION ""
			::= { mbus47 49 }

mbus47VIF16		OBJECT-TYPE
			SYNTAX	INTEGER
			ACCESS	read-only
			STATUS	current
	DESCRIPTION ""
			::= { mbus47 50 }

mbus47Value16		OBJECT-TYPE
			SYNTAX	INTEGER
			ACCESS	read-only
			STATUS	current
	DESCRIPTION ""
			::= { mbus47 51 }

mbus47VIF17		OBJECT-TYPE
			SYNTAX	INTEGER
			ACCESS	read-only
			STATUS	current
	DESCRIPTION ""
			::= { mbus47 52 }

mbus47Value17		OBJECT-TYPE
			SYNTAX	INTEGER
			ACCESS	read-only
			STATUS	current
	DESCRIPTION ""
			::= { mbus47 53 }

mbus47VIF18		OBJECT-TYPE
			SYNTAX	INTEGER
			ACCESS	read-only
			STATUS	current
	DESCRIPTION ""
			::= { mbus47 54 }

mbus47Value18		OBJECT-TYPE
			SYNTAX	INTEGER
			ACCESS	read-only
			STATUS	current
	DESCRIPTION ""
			::= { mbus47 55 }

mbus47VIF19		OBJECT-TYPE
			SYNTAX	INTEGER
			ACCESS	read-only
			STATUS	current
	DESCRIPTION ""
			::= { mbus47 56 }

mbus47Value19		OBJECT-TYPE
			SYNTAX	INTEGER
			ACCESS	read-only
			STATUS	current
	DESCRIPTION ""
			::= { mbus47 57 }

mbus47VIF1A		OBJECT-TYPE
			SYNTAX	INTEGER
			ACCESS	read-only
			STATUS	current
	DESCRIPTION ""
			::= { mbus47 58 }

mbus47Value1A		OBJECT-TYPE
			SYNTAX	INTEGER
			ACCESS	read-only
			STATUS	current
	DESCRIPTION ""
			::= { mbus47 59 }

mbus47VIF1B		OBJECT-TYPE
			SYNTAX	INTEGER
			ACCESS	read-only
			STATUS	current
	DESCRIPTION ""
			::= { mbus47 60 }

mbus47Value1B		OBJECT-TYPE
			SYNTAX	INTEGER
			ACCESS	read-only
			STATUS	current
	DESCRIPTION ""
			::= { mbus47 61 }

mbus47VIF1C		OBJECT-TYPE
			SYNTAX	INTEGER
			ACCESS	read-only
			STATUS	current
	DESCRIPTION ""
			::= { mbus47 62 }

mbus47Value1C		OBJECT-TYPE
			SYNTAX	INTEGER
			ACCESS	read-only
			STATUS	current
	DESCRIPTION ""
			::= { mbus47 63 }

mbus47VIF1D		OBJECT-TYPE
			SYNTAX	INTEGER
			ACCESS	read-only
			STATUS	current
	DESCRIPTION ""
			::= { mbus47 64 }

mbus47Value1D		OBJECT-TYPE
			SYNTAX	INTEGER
			ACCESS	read-only
			STATUS	current
	DESCRIPTION ""
			::= { mbus47 65 }

mbus47VIF1E		OBJECT-TYPE
			SYNTAX	INTEGER
			ACCESS	read-only
			STATUS	current
	DESCRIPTION ""
			::= { mbus47 66 }

mbus47Value1E		OBJECT-TYPE
			SYNTAX	INTEGER
			ACCESS	read-only
			STATUS	current
	DESCRIPTION ""
			::= { mbus47 67 }

mbus47VIF1F		OBJECT-TYPE
			SYNTAX	INTEGER
			ACCESS	read-only
			STATUS	current
	DESCRIPTION ""
			::= { mbus47 68 }

mbus47Value1F		OBJECT-TYPE
			SYNTAX	INTEGER
			ACCESS	read-only
			STATUS	current
	DESCRIPTION ""
			::= { mbus47 69 }

mbus47VIF20		OBJECT-TYPE
			SYNTAX	INTEGER
			ACCESS	read-only
			STATUS	current
	DESCRIPTION ""
			::= { mbus47 70 }

mbus47Value20		OBJECT-TYPE
			SYNTAX	INTEGER
			ACCESS	read-only
			STATUS	current
	DESCRIPTION ""
			::= { mbus47 71 }

mbus47VIF21		OBJECT-TYPE
			SYNTAX	INTEGER
			ACCESS	read-only
			STATUS	current
	DESCRIPTION ""
			::= { mbus47 72 }

mbus47Value21		OBJECT-TYPE
			SYNTAX	INTEGER
			ACCESS	read-only
			STATUS	current
	DESCRIPTION ""
			::= { mbus47 73 }

mbus47VIF22		OBJECT-TYPE
			SYNTAX	INTEGER
			ACCESS	read-only
			STATUS	current
	DESCRIPTION ""
			::= { mbus47 74 }

mbus47Value22		OBJECT-TYPE
			SYNTAX	INTEGER
			ACCESS	read-only
			STATUS	current
	DESCRIPTION ""
			::= { mbus47 75 }

mbus47VIF23		OBJECT-TYPE
			SYNTAX	INTEGER
			ACCESS	read-only
			STATUS	current
	DESCRIPTION ""
			::= { mbus47 76 }

mbus47Value23		OBJECT-TYPE
			SYNTAX	INTEGER
			ACCESS	read-only
			STATUS	current
	DESCRIPTION ""
			::= { mbus47 77 }

mbus47VIF24		OBJECT-TYPE
			SYNTAX	INTEGER
			ACCESS	read-only
			STATUS	current
	DESCRIPTION ""
			::= { mbus47 78 }

mbus47Value24		OBJECT-TYPE
			SYNTAX	INTEGER
			ACCESS	read-only
			STATUS	current
	DESCRIPTION ""
			::= { mbus47 79 }

mbus47VIF25		OBJECT-TYPE
			SYNTAX	INTEGER
			ACCESS	read-only
			STATUS	current
	DESCRIPTION ""
			::= { mbus47 80 }

mbus47Value25		OBJECT-TYPE
			SYNTAX	INTEGER
			ACCESS	read-only
			STATUS	current
	DESCRIPTION ""
			::= { mbus47 81 }

mbus47VIF26		OBJECT-TYPE
			SYNTAX	INTEGER
			ACCESS	read-only
			STATUS	current
	DESCRIPTION ""
			::= { mbus47 82 }

mbus47Value26		OBJECT-TYPE
			SYNTAX	INTEGER
			ACCESS	read-only
			STATUS	current
	DESCRIPTION ""
			::= { mbus47 83 }

mbus47VIF27		OBJECT-TYPE
			SYNTAX	INTEGER
			ACCESS	read-only
			STATUS	current
	DESCRIPTION ""
			::= { mbus47 84 }

mbus47Value27		OBJECT-TYPE
			SYNTAX	INTEGER
			ACCESS	read-only
			STATUS	current
	DESCRIPTION ""
			::= { mbus47 85 }

mbus47VIF28		OBJECT-TYPE
			SYNTAX	INTEGER
			ACCESS	read-only
			STATUS	current
	DESCRIPTION ""
			::= { mbus47 86 }

mbus47Value28		OBJECT-TYPE
			SYNTAX	INTEGER
			ACCESS	read-only
			STATUS	current
	DESCRIPTION ""
			::= { mbus47 87 }

mbus47VIF29		OBJECT-TYPE
			SYNTAX	INTEGER
			ACCESS	read-only
			STATUS	current
	DESCRIPTION ""
			::= { mbus47 88 }

mbus47Value29		OBJECT-TYPE
			SYNTAX	INTEGER
			ACCESS	read-only
			STATUS	current
	DESCRIPTION ""
			::= { mbus47 89 }

mbus47VIF2A		OBJECT-TYPE
			SYNTAX	INTEGER
			ACCESS	read-only
			STATUS	current
	DESCRIPTION ""
			::= { mbus47 90 }

mbus47Value2A		OBJECT-TYPE
			SYNTAX	INTEGER
			ACCESS	read-only
			STATUS	current
	DESCRIPTION ""
			::= { mbus47 91 }

mbus47VIF2B		OBJECT-TYPE
			SYNTAX	INTEGER
			ACCESS	read-only
			STATUS	current
	DESCRIPTION ""
			::= { mbus47 92 }

mbus47Value2B		OBJECT-TYPE
			SYNTAX	INTEGER
			ACCESS	read-only
			STATUS	current
	DESCRIPTION ""
			::= { mbus47 93 }

mbus47VIF2C		OBJECT-TYPE
			SYNTAX	INTEGER
			ACCESS	read-only
			STATUS	current
	DESCRIPTION ""
			::= { mbus47 94 }

mbus47Value2C		OBJECT-TYPE
			SYNTAX	INTEGER
			ACCESS	read-only
			STATUS	current
	DESCRIPTION ""
			::= { mbus47 95 }

mbus47VIF2D		OBJECT-TYPE
			SYNTAX	INTEGER
			ACCESS	read-only
			STATUS	current
	DESCRIPTION ""
			::= { mbus47 96 }

mbus47Value2D		OBJECT-TYPE
			SYNTAX	INTEGER
			ACCESS	read-only
			STATUS	current
	DESCRIPTION ""
			::= { mbus47 97 }

mbus47VIF2E		OBJECT-TYPE
			SYNTAX	INTEGER
			ACCESS	read-only
			STATUS	current
	DESCRIPTION ""
			::= { mbus47 98 }

mbus47Value2E		OBJECT-TYPE
			SYNTAX	INTEGER
			ACCESS	read-only
			STATUS	current
	DESCRIPTION ""
			::= { mbus47 99 }

mbus47VIF2F		OBJECT-TYPE
			SYNTAX	INTEGER
			ACCESS	read-only
			STATUS	current
	DESCRIPTION ""
			::= { mbus47 100 }

mbus47Value2F		OBJECT-TYPE
			SYNTAX	INTEGER
			ACCESS	read-only
			STATUS	current
	DESCRIPTION ""
			::= { mbus47 101 }

mbus48			OBJECT IDENTIFIER ::= { mbus 72 }

mbus48IdNumber		OBJECT-TYPE
			SYNTAX	Gauge
			ACCESS	read-only
			STATUS	current
	DESCRIPTION ""
			::= { mbus48 1 }

mbus48Manufacturer	OBJECT-TYPE
			SYNTAX	Gauge
			ACCESS	read-only
			STATUS	current
	DESCRIPTION ""
			::= { mbus48 2 }

mbus48Version		OBJECT-TYPE
			SYNTAX	Gauge
			ACCESS	read-only
			STATUS	current
	DESCRIPTION ""
			::= { mbus48 3 }

mbus48Medium		OBJECT-TYPE
			SYNTAX	Gauge
			ACCESS	read-only
			STATUS	current
	DESCRIPTION ""
			::= { mbus48 4 }

mbus48Status		OBJECT-TYPE
			SYNTAX	Gauge
			ACCESS	read-only
			STATUS	current
	DESCRIPTION ""
			::= { mbus48 5 }

mbus48VIF00		OBJECT-TYPE
			SYNTAX	INTEGER
			ACCESS	read-only
			STATUS	current
	DESCRIPTION ""
			::= { mbus48 6 }

mbus48Value00		OBJECT-TYPE
			SYNTAX	INTEGER
			ACCESS	read-only
			STATUS	current
	DESCRIPTION ""
			::= { mbus48 7 }

mbus48VIF01		OBJECT-TYPE
			SYNTAX	INTEGER
			ACCESS	read-only
			STATUS	current
	DESCRIPTION ""
			::= { mbus48 8 }

mbus48Value01		OBJECT-TYPE
			SYNTAX	INTEGER
			ACCESS	read-only
			STATUS	current
	DESCRIPTION ""
			::= { mbus48 9 }

mbus48VIF02		OBJECT-TYPE
			SYNTAX	INTEGER
			ACCESS	read-only
			STATUS	current
	DESCRIPTION ""
			::= { mbus48 10 }

mbus48Value02		OBJECT-TYPE
			SYNTAX	INTEGER
			ACCESS	read-only
			STATUS	current
	DESCRIPTION ""
			::= { mbus48 11 }

mbus48VIF03		OBJECT-TYPE
			SYNTAX	INTEGER
			ACCESS	read-only
			STATUS	current
	DESCRIPTION ""
			::= { mbus48 12 }

mbus48Value03		OBJECT-TYPE
			SYNTAX	INTEGER
			ACCESS	read-only
			STATUS	current
	DESCRIPTION ""
			::= { mbus48 13 }

mbus48VIF04		OBJECT-TYPE
			SYNTAX	INTEGER
			ACCESS	read-only
			STATUS	current
	DESCRIPTION ""
			::= { mbus48 14 }

mbus48Value04		OBJECT-TYPE
			SYNTAX	INTEGER
			ACCESS	read-only
			STATUS	current
	DESCRIPTION ""
			::= { mbus48 15 }

mbus48VIF05		OBJECT-TYPE
			SYNTAX	INTEGER
			ACCESS	read-only
			STATUS	current
	DESCRIPTION ""
			::= { mbus48 16 }

mbus48Value05		OBJECT-TYPE
			SYNTAX	INTEGER
			ACCESS	read-only
			STATUS	current
	DESCRIPTION ""
			::= { mbus48 17 }

mbus48VIF06		OBJECT-TYPE
			SYNTAX	INTEGER
			ACCESS	read-only
			STATUS	current
	DESCRIPTION ""
			::= { mbus48 18 }

mbus48Value06		OBJECT-TYPE
			SYNTAX	INTEGER
			ACCESS	read-only
			STATUS	current
	DESCRIPTION ""
			::= { mbus48 19 }

mbus48VIF07		OBJECT-TYPE
			SYNTAX	INTEGER
			ACCESS	read-only
			STATUS	current
	DESCRIPTION ""
			::= { mbus48 20 }

mbus48Value07		OBJECT-TYPE
			SYNTAX	INTEGER
			ACCESS	read-only
			STATUS	current
	DESCRIPTION ""
			::= { mbus48 21 }

mbus48VIF08		OBJECT-TYPE
			SYNTAX	INTEGER
			ACCESS	read-only
			STATUS	current
	DESCRIPTION ""
			::= { mbus48 22 }

mbus48Value08		OBJECT-TYPE
			SYNTAX	INTEGER
			ACCESS	read-only
			STATUS	current
	DESCRIPTION ""
			::= { mbus48 23 }

mbus48VIF09		OBJECT-TYPE
			SYNTAX	INTEGER
			ACCESS	read-only
			STATUS	current
	DESCRIPTION ""
			::= { mbus48 24 }

mbus48Value09		OBJECT-TYPE
			SYNTAX	INTEGER
			ACCESS	read-only
			STATUS	current
	DESCRIPTION ""
			::= { mbus48 25 }

mbus48VIF0A		OBJECT-TYPE
			SYNTAX	INTEGER
			ACCESS	read-only
			STATUS	current
	DESCRIPTION ""
			::= { mbus48 26 }

mbus48Value0A		OBJECT-TYPE
			SYNTAX	INTEGER
			ACCESS	read-only
			STATUS	current
	DESCRIPTION ""
			::= { mbus48 27 }

mbus48VIF0B		OBJECT-TYPE
			SYNTAX	INTEGER
			ACCESS	read-only
			STATUS	current
	DESCRIPTION ""
			::= { mbus48 28 }

mbus48Value0B		OBJECT-TYPE
			SYNTAX	INTEGER
			ACCESS	read-only
			STATUS	current
	DESCRIPTION ""
			::= { mbus48 29 }

mbus48VIF0C		OBJECT-TYPE
			SYNTAX	INTEGER
			ACCESS	read-only
			STATUS	current
	DESCRIPTION ""
			::= { mbus48 30 }

mbus48Value0C		OBJECT-TYPE
			SYNTAX	INTEGER
			ACCESS	read-only
			STATUS	current
	DESCRIPTION ""
			::= { mbus48 31 }

mbus48VIF0D		OBJECT-TYPE
			SYNTAX	INTEGER
			ACCESS	read-only
			STATUS	current
	DESCRIPTION ""
			::= { mbus48 32 }

mbus48Value0D		OBJECT-TYPE
			SYNTAX	INTEGER
			ACCESS	read-only
			STATUS	current
	DESCRIPTION ""
			::= { mbus48 33 }

mbus48VIF0E		OBJECT-TYPE
			SYNTAX	INTEGER
			ACCESS	read-only
			STATUS	current
	DESCRIPTION ""
			::= { mbus48 34 }

mbus48Value0E		OBJECT-TYPE
			SYNTAX	INTEGER
			ACCESS	read-only
			STATUS	current
	DESCRIPTION ""
			::= { mbus48 35 }

mbus48VIF0F		OBJECT-TYPE
			SYNTAX	INTEGER
			ACCESS	read-only
			STATUS	current
	DESCRIPTION ""
			::= { mbus48 36 }

mbus48Value0F		OBJECT-TYPE
			SYNTAX	INTEGER
			ACCESS	read-only
			STATUS	current
	DESCRIPTION ""
			::= { mbus48 37 }

mbus48VIF10		OBJECT-TYPE
			SYNTAX	INTEGER
			ACCESS	read-only
			STATUS	current
	DESCRIPTION ""
			::= { mbus48 38 }

mbus48Value10		OBJECT-TYPE
			SYNTAX	INTEGER
			ACCESS	read-only
			STATUS	current
	DESCRIPTION ""
			::= { mbus48 39 }

mbus48VIF11		OBJECT-TYPE
			SYNTAX	INTEGER
			ACCESS	read-only
			STATUS	current
	DESCRIPTION ""
			::= { mbus48 40 }

mbus48Value11		OBJECT-TYPE
			SYNTAX	INTEGER
			ACCESS	read-only
			STATUS	current
	DESCRIPTION ""
			::= { mbus48 41 }

mbus48VIF12		OBJECT-TYPE
			SYNTAX	INTEGER
			ACCESS	read-only
			STATUS	current
	DESCRIPTION ""
			::= { mbus48 42 }

mbus48Value12		OBJECT-TYPE
			SYNTAX	INTEGER
			ACCESS	read-only
			STATUS	current
	DESCRIPTION ""
			::= { mbus48 43 }

mbus48VIF13		OBJECT-TYPE
			SYNTAX	INTEGER
			ACCESS	read-only
			STATUS	current
	DESCRIPTION ""
			::= { mbus48 44 }

mbus48Value13		OBJECT-TYPE
			SYNTAX	INTEGER
			ACCESS	read-only
			STATUS	current
	DESCRIPTION ""
			::= { mbus48 45 }

mbus48VIF14		OBJECT-TYPE
			SYNTAX	INTEGER
			ACCESS	read-only
			STATUS	current
	DESCRIPTION ""
			::= { mbus48 46 }

mbus48Value14		OBJECT-TYPE
			SYNTAX	INTEGER
			ACCESS	read-only
			STATUS	current
	DESCRIPTION ""
			::= { mbus48 47 }

mbus48VIF15		OBJECT-TYPE
			SYNTAX	INTEGER
			ACCESS	read-only
			STATUS	current
	DESCRIPTION ""
			::= { mbus48 48 }

mbus48Value15		OBJECT-TYPE
			SYNTAX	INTEGER
			ACCESS	read-only
			STATUS	current
	DESCRIPTION ""
			::= { mbus48 49 }

mbus48VIF16		OBJECT-TYPE
			SYNTAX	INTEGER
			ACCESS	read-only
			STATUS	current
	DESCRIPTION ""
			::= { mbus48 50 }

mbus48Value16		OBJECT-TYPE
			SYNTAX	INTEGER
			ACCESS	read-only
			STATUS	current
	DESCRIPTION ""
			::= { mbus48 51 }

mbus48VIF17		OBJECT-TYPE
			SYNTAX	INTEGER
			ACCESS	read-only
			STATUS	current
	DESCRIPTION ""
			::= { mbus48 52 }

mbus48Value17		OBJECT-TYPE
			SYNTAX	INTEGER
			ACCESS	read-only
			STATUS	current
	DESCRIPTION ""
			::= { mbus48 53 }

mbus48VIF18		OBJECT-TYPE
			SYNTAX	INTEGER
			ACCESS	read-only
			STATUS	current
	DESCRIPTION ""
			::= { mbus48 54 }

mbus48Value18		OBJECT-TYPE
			SYNTAX	INTEGER
			ACCESS	read-only
			STATUS	current
	DESCRIPTION ""
			::= { mbus48 55 }

mbus48VIF19		OBJECT-TYPE
			SYNTAX	INTEGER
			ACCESS	read-only
			STATUS	current
	DESCRIPTION ""
			::= { mbus48 56 }

mbus48Value19		OBJECT-TYPE
			SYNTAX	INTEGER
			ACCESS	read-only
			STATUS	current
	DESCRIPTION ""
			::= { mbus48 57 }

mbus48VIF1A		OBJECT-TYPE
			SYNTAX	INTEGER
			ACCESS	read-only
			STATUS	current
	DESCRIPTION ""
			::= { mbus48 58 }

mbus48Value1A		OBJECT-TYPE
			SYNTAX	INTEGER
			ACCESS	read-only
			STATUS	current
	DESCRIPTION ""
			::= { mbus48 59 }

mbus48VIF1B		OBJECT-TYPE
			SYNTAX	INTEGER
			ACCESS	read-only
			STATUS	current
	DESCRIPTION ""
			::= { mbus48 60 }

mbus48Value1B		OBJECT-TYPE
			SYNTAX	INTEGER
			ACCESS	read-only
			STATUS	current
	DESCRIPTION ""
			::= { mbus48 61 }

mbus48VIF1C		OBJECT-TYPE
			SYNTAX	INTEGER
			ACCESS	read-only
			STATUS	current
	DESCRIPTION ""
			::= { mbus48 62 }

mbus48Value1C		OBJECT-TYPE
			SYNTAX	INTEGER
			ACCESS	read-only
			STATUS	current
	DESCRIPTION ""
			::= { mbus48 63 }

mbus48VIF1D		OBJECT-TYPE
			SYNTAX	INTEGER
			ACCESS	read-only
			STATUS	current
	DESCRIPTION ""
			::= { mbus48 64 }

mbus48Value1D		OBJECT-TYPE
			SYNTAX	INTEGER
			ACCESS	read-only
			STATUS	current
	DESCRIPTION ""
			::= { mbus48 65 }

mbus48VIF1E		OBJECT-TYPE
			SYNTAX	INTEGER
			ACCESS	read-only
			STATUS	current
	DESCRIPTION ""
			::= { mbus48 66 }

mbus48Value1E		OBJECT-TYPE
			SYNTAX	INTEGER
			ACCESS	read-only
			STATUS	current
	DESCRIPTION ""
			::= { mbus48 67 }

mbus48VIF1F		OBJECT-TYPE
			SYNTAX	INTEGER
			ACCESS	read-only
			STATUS	current
	DESCRIPTION ""
			::= { mbus48 68 }

mbus48Value1F		OBJECT-TYPE
			SYNTAX	INTEGER
			ACCESS	read-only
			STATUS	current
	DESCRIPTION ""
			::= { mbus48 69 }

mbus48VIF20		OBJECT-TYPE
			SYNTAX	INTEGER
			ACCESS	read-only
			STATUS	current
	DESCRIPTION ""
			::= { mbus48 70 }

mbus48Value20		OBJECT-TYPE
			SYNTAX	INTEGER
			ACCESS	read-only
			STATUS	current
	DESCRIPTION ""
			::= { mbus48 71 }

mbus48VIF21		OBJECT-TYPE
			SYNTAX	INTEGER
			ACCESS	read-only
			STATUS	current
	DESCRIPTION ""
			::= { mbus48 72 }

mbus48Value21		OBJECT-TYPE
			SYNTAX	INTEGER
			ACCESS	read-only
			STATUS	current
	DESCRIPTION ""
			::= { mbus48 73 }

mbus48VIF22		OBJECT-TYPE
			SYNTAX	INTEGER
			ACCESS	read-only
			STATUS	current
	DESCRIPTION ""
			::= { mbus48 74 }

mbus48Value22		OBJECT-TYPE
			SYNTAX	INTEGER
			ACCESS	read-only
			STATUS	current
	DESCRIPTION ""
			::= { mbus48 75 }

mbus48VIF23		OBJECT-TYPE
			SYNTAX	INTEGER
			ACCESS	read-only
			STATUS	current
	DESCRIPTION ""
			::= { mbus48 76 }

mbus48Value23		OBJECT-TYPE
			SYNTAX	INTEGER
			ACCESS	read-only
			STATUS	current
	DESCRIPTION ""
			::= { mbus48 77 }

mbus48VIF24		OBJECT-TYPE
			SYNTAX	INTEGER
			ACCESS	read-only
			STATUS	current
	DESCRIPTION ""
			::= { mbus48 78 }

mbus48Value24		OBJECT-TYPE
			SYNTAX	INTEGER
			ACCESS	read-only
			STATUS	current
	DESCRIPTION ""
			::= { mbus48 79 }

mbus48VIF25		OBJECT-TYPE
			SYNTAX	INTEGER
			ACCESS	read-only
			STATUS	current
	DESCRIPTION ""
			::= { mbus48 80 }

mbus48Value25		OBJECT-TYPE
			SYNTAX	INTEGER
			ACCESS	read-only
			STATUS	current
	DESCRIPTION ""
			::= { mbus48 81 }

mbus48VIF26		OBJECT-TYPE
			SYNTAX	INTEGER
			ACCESS	read-only
			STATUS	current
	DESCRIPTION ""
			::= { mbus48 82 }

mbus48Value26		OBJECT-TYPE
			SYNTAX	INTEGER
			ACCESS	read-only
			STATUS	current
	DESCRIPTION ""
			::= { mbus48 83 }

mbus48VIF27		OBJECT-TYPE
			SYNTAX	INTEGER
			ACCESS	read-only
			STATUS	current
	DESCRIPTION ""
			::= { mbus48 84 }

mbus48Value27		OBJECT-TYPE
			SYNTAX	INTEGER
			ACCESS	read-only
			STATUS	current
	DESCRIPTION ""
			::= { mbus48 85 }

mbus48VIF28		OBJECT-TYPE
			SYNTAX	INTEGER
			ACCESS	read-only
			STATUS	current
	DESCRIPTION ""
			::= { mbus48 86 }

mbus48Value28		OBJECT-TYPE
			SYNTAX	INTEGER
			ACCESS	read-only
			STATUS	current
	DESCRIPTION ""
			::= { mbus48 87 }

mbus48VIF29		OBJECT-TYPE
			SYNTAX	INTEGER
			ACCESS	read-only
			STATUS	current
	DESCRIPTION ""
			::= { mbus48 88 }

mbus48Value29		OBJECT-TYPE
			SYNTAX	INTEGER
			ACCESS	read-only
			STATUS	current
	DESCRIPTION ""
			::= { mbus48 89 }

mbus48VIF2A		OBJECT-TYPE
			SYNTAX	INTEGER
			ACCESS	read-only
			STATUS	current
	DESCRIPTION ""
			::= { mbus48 90 }

mbus48Value2A		OBJECT-TYPE
			SYNTAX	INTEGER
			ACCESS	read-only
			STATUS	current
	DESCRIPTION ""
			::= { mbus48 91 }

mbus48VIF2B		OBJECT-TYPE
			SYNTAX	INTEGER
			ACCESS	read-only
			STATUS	current
	DESCRIPTION ""
			::= { mbus48 92 }

mbus48Value2B		OBJECT-TYPE
			SYNTAX	INTEGER
			ACCESS	read-only
			STATUS	current
	DESCRIPTION ""
			::= { mbus48 93 }

mbus48VIF2C		OBJECT-TYPE
			SYNTAX	INTEGER
			ACCESS	read-only
			STATUS	current
	DESCRIPTION ""
			::= { mbus48 94 }

mbus48Value2C		OBJECT-TYPE
			SYNTAX	INTEGER
			ACCESS	read-only
			STATUS	current
	DESCRIPTION ""
			::= { mbus48 95 }

mbus48VIF2D		OBJECT-TYPE
			SYNTAX	INTEGER
			ACCESS	read-only
			STATUS	current
	DESCRIPTION ""
			::= { mbus48 96 }

mbus48Value2D		OBJECT-TYPE
			SYNTAX	INTEGER
			ACCESS	read-only
			STATUS	current
	DESCRIPTION ""
			::= { mbus48 97 }

mbus48VIF2E		OBJECT-TYPE
			SYNTAX	INTEGER
			ACCESS	read-only
			STATUS	current
	DESCRIPTION ""
			::= { mbus48 98 }

mbus48Value2E		OBJECT-TYPE
			SYNTAX	INTEGER
			ACCESS	read-only
			STATUS	current
	DESCRIPTION ""
			::= { mbus48 99 }

mbus48VIF2F		OBJECT-TYPE
			SYNTAX	INTEGER
			ACCESS	read-only
			STATUS	current
	DESCRIPTION ""
			::= { mbus48 100 }

mbus48Value2F		OBJECT-TYPE
			SYNTAX	INTEGER
			ACCESS	read-only
			STATUS	current
	DESCRIPTION ""
			::= { mbus48 101 }

mbus49			OBJECT IDENTIFIER ::= { mbus 73 }

mbus49IdNumber		OBJECT-TYPE
			SYNTAX	Gauge
			ACCESS	read-only
			STATUS	current
	DESCRIPTION ""
			::= { mbus49 1 }

mbus49Manufacturer	OBJECT-TYPE
			SYNTAX	Gauge
			ACCESS	read-only
			STATUS	current
	DESCRIPTION ""
			::= { mbus49 2 }

mbus49Version		OBJECT-TYPE
			SYNTAX	Gauge
			ACCESS	read-only
			STATUS	current
	DESCRIPTION ""
			::= { mbus49 3 }

mbus49Medium		OBJECT-TYPE
			SYNTAX	Gauge
			ACCESS	read-only
			STATUS	current
	DESCRIPTION ""
			::= { mbus49 4 }

mbus49Status		OBJECT-TYPE
			SYNTAX	Gauge
			ACCESS	read-only
			STATUS	current
	DESCRIPTION ""
			::= { mbus49 5 }

mbus49VIF00		OBJECT-TYPE
			SYNTAX	INTEGER
			ACCESS	read-only
			STATUS	current
	DESCRIPTION ""
			::= { mbus49 6 }

mbus49Value00		OBJECT-TYPE
			SYNTAX	INTEGER
			ACCESS	read-only
			STATUS	current
	DESCRIPTION ""
			::= { mbus49 7 }

mbus49VIF01		OBJECT-TYPE
			SYNTAX	INTEGER
			ACCESS	read-only
			STATUS	current
	DESCRIPTION ""
			::= { mbus49 8 }

mbus49Value01		OBJECT-TYPE
			SYNTAX	INTEGER
			ACCESS	read-only
			STATUS	current
	DESCRIPTION ""
			::= { mbus49 9 }

mbus49VIF02		OBJECT-TYPE
			SYNTAX	INTEGER
			ACCESS	read-only
			STATUS	current
	DESCRIPTION ""
			::= { mbus49 10 }

mbus49Value02		OBJECT-TYPE
			SYNTAX	INTEGER
			ACCESS	read-only
			STATUS	current
	DESCRIPTION ""
			::= { mbus49 11 }

mbus49VIF03		OBJECT-TYPE
			SYNTAX	INTEGER
			ACCESS	read-only
			STATUS	current
	DESCRIPTION ""
			::= { mbus49 12 }

mbus49Value03		OBJECT-TYPE
			SYNTAX	INTEGER
			ACCESS	read-only
			STATUS	current
	DESCRIPTION ""
			::= { mbus49 13 }

mbus49VIF04		OBJECT-TYPE
			SYNTAX	INTEGER
			ACCESS	read-only
			STATUS	current
	DESCRIPTION ""
			::= { mbus49 14 }

mbus49Value04		OBJECT-TYPE
			SYNTAX	INTEGER
			ACCESS	read-only
			STATUS	current
	DESCRIPTION ""
			::= { mbus49 15 }

mbus49VIF05		OBJECT-TYPE
			SYNTAX	INTEGER
			ACCESS	read-only
			STATUS	current
	DESCRIPTION ""
			::= { mbus49 16 }

mbus49Value05		OBJECT-TYPE
			SYNTAX	INTEGER
			ACCESS	read-only
			STATUS	current
	DESCRIPTION ""
			::= { mbus49 17 }

mbus49VIF06		OBJECT-TYPE
			SYNTAX	INTEGER
			ACCESS	read-only
			STATUS	current
	DESCRIPTION ""
			::= { mbus49 18 }

mbus49Value06		OBJECT-TYPE
			SYNTAX	INTEGER
			ACCESS	read-only
			STATUS	current
	DESCRIPTION ""
			::= { mbus49 19 }

mbus49VIF07		OBJECT-TYPE
			SYNTAX	INTEGER
			ACCESS	read-only
			STATUS	current
	DESCRIPTION ""
			::= { mbus49 20 }

mbus49Value07		OBJECT-TYPE
			SYNTAX	INTEGER
			ACCESS	read-only
			STATUS	current
	DESCRIPTION ""
			::= { mbus49 21 }

mbus49VIF08		OBJECT-TYPE
			SYNTAX	INTEGER
			ACCESS	read-only
			STATUS	current
	DESCRIPTION ""
			::= { mbus49 22 }

mbus49Value08		OBJECT-TYPE
			SYNTAX	INTEGER
			ACCESS	read-only
			STATUS	current
	DESCRIPTION ""
			::= { mbus49 23 }

mbus49VIF09		OBJECT-TYPE
			SYNTAX	INTEGER
			ACCESS	read-only
			STATUS	current
	DESCRIPTION ""
			::= { mbus49 24 }

mbus49Value09		OBJECT-TYPE
			SYNTAX	INTEGER
			ACCESS	read-only
			STATUS	current
	DESCRIPTION ""
			::= { mbus49 25 }

mbus49VIF0A		OBJECT-TYPE
			SYNTAX	INTEGER
			ACCESS	read-only
			STATUS	current
	DESCRIPTION ""
			::= { mbus49 26 }

mbus49Value0A		OBJECT-TYPE
			SYNTAX	INTEGER
			ACCESS	read-only
			STATUS	current
	DESCRIPTION ""
			::= { mbus49 27 }

mbus49VIF0B		OBJECT-TYPE
			SYNTAX	INTEGER
			ACCESS	read-only
			STATUS	current
	DESCRIPTION ""
			::= { mbus49 28 }

mbus49Value0B		OBJECT-TYPE
			SYNTAX	INTEGER
			ACCESS	read-only
			STATUS	current
	DESCRIPTION ""
			::= { mbus49 29 }

mbus49VIF0C		OBJECT-TYPE
			SYNTAX	INTEGER
			ACCESS	read-only
			STATUS	current
	DESCRIPTION ""
			::= { mbus49 30 }

mbus49Value0C		OBJECT-TYPE
			SYNTAX	INTEGER
			ACCESS	read-only
			STATUS	current
	DESCRIPTION ""
			::= { mbus49 31 }

mbus49VIF0D		OBJECT-TYPE
			SYNTAX	INTEGER
			ACCESS	read-only
			STATUS	current
	DESCRIPTION ""
			::= { mbus49 32 }

mbus49Value0D		OBJECT-TYPE
			SYNTAX	INTEGER
			ACCESS	read-only
			STATUS	current
	DESCRIPTION ""
			::= { mbus49 33 }

mbus49VIF0E		OBJECT-TYPE
			SYNTAX	INTEGER
			ACCESS	read-only
			STATUS	current
	DESCRIPTION ""
			::= { mbus49 34 }

mbus49Value0E		OBJECT-TYPE
			SYNTAX	INTEGER
			ACCESS	read-only
			STATUS	current
	DESCRIPTION ""
			::= { mbus49 35 }

mbus49VIF0F		OBJECT-TYPE
			SYNTAX	INTEGER
			ACCESS	read-only
			STATUS	current
	DESCRIPTION ""
			::= { mbus49 36 }

mbus49Value0F		OBJECT-TYPE
			SYNTAX	INTEGER
			ACCESS	read-only
			STATUS	current
	DESCRIPTION ""
			::= { mbus49 37 }

mbus49VIF10		OBJECT-TYPE
			SYNTAX	INTEGER
			ACCESS	read-only
			STATUS	current
	DESCRIPTION ""
			::= { mbus49 38 }

mbus49Value10		OBJECT-TYPE
			SYNTAX	INTEGER
			ACCESS	read-only
			STATUS	current
	DESCRIPTION ""
			::= { mbus49 39 }

mbus49VIF11		OBJECT-TYPE
			SYNTAX	INTEGER
			ACCESS	read-only
			STATUS	current
	DESCRIPTION ""
			::= { mbus49 40 }

mbus49Value11		OBJECT-TYPE
			SYNTAX	INTEGER
			ACCESS	read-only
			STATUS	current
	DESCRIPTION ""
			::= { mbus49 41 }

mbus49VIF12		OBJECT-TYPE
			SYNTAX	INTEGER
			ACCESS	read-only
			STATUS	current
	DESCRIPTION ""
			::= { mbus49 42 }

mbus49Value12		OBJECT-TYPE
			SYNTAX	INTEGER
			ACCESS	read-only
			STATUS	current
	DESCRIPTION ""
			::= { mbus49 43 }

mbus49VIF13		OBJECT-TYPE
			SYNTAX	INTEGER
			ACCESS	read-only
			STATUS	current
	DESCRIPTION ""
			::= { mbus49 44 }

mbus49Value13		OBJECT-TYPE
			SYNTAX	INTEGER
			ACCESS	read-only
			STATUS	current
	DESCRIPTION ""
			::= { mbus49 45 }

mbus49VIF14		OBJECT-TYPE
			SYNTAX	INTEGER
			ACCESS	read-only
			STATUS	current
	DESCRIPTION ""
			::= { mbus49 46 }

mbus49Value14		OBJECT-TYPE
			SYNTAX	INTEGER
			ACCESS	read-only
			STATUS	current
	DESCRIPTION ""
			::= { mbus49 47 }

mbus49VIF15		OBJECT-TYPE
			SYNTAX	INTEGER
			ACCESS	read-only
			STATUS	current
	DESCRIPTION ""
			::= { mbus49 48 }

mbus49Value15		OBJECT-TYPE
			SYNTAX	INTEGER
			ACCESS	read-only
			STATUS	current
	DESCRIPTION ""
			::= { mbus49 49 }

mbus49VIF16		OBJECT-TYPE
			SYNTAX	INTEGER
			ACCESS	read-only
			STATUS	current
	DESCRIPTION ""
			::= { mbus49 50 }

mbus49Value16		OBJECT-TYPE
			SYNTAX	INTEGER
			ACCESS	read-only
			STATUS	current
	DESCRIPTION ""
			::= { mbus49 51 }

mbus49VIF17		OBJECT-TYPE
			SYNTAX	INTEGER
			ACCESS	read-only
			STATUS	current
	DESCRIPTION ""
			::= { mbus49 52 }

mbus49Value17		OBJECT-TYPE
			SYNTAX	INTEGER
			ACCESS	read-only
			STATUS	current
	DESCRIPTION ""
			::= { mbus49 53 }

mbus49VIF18		OBJECT-TYPE
			SYNTAX	INTEGER
			ACCESS	read-only
			STATUS	current
	DESCRIPTION ""
			::= { mbus49 54 }

mbus49Value18		OBJECT-TYPE
			SYNTAX	INTEGER
			ACCESS	read-only
			STATUS	current
	DESCRIPTION ""
			::= { mbus49 55 }

mbus49VIF19		OBJECT-TYPE
			SYNTAX	INTEGER
			ACCESS	read-only
			STATUS	current
	DESCRIPTION ""
			::= { mbus49 56 }

mbus49Value19		OBJECT-TYPE
			SYNTAX	INTEGER
			ACCESS	read-only
			STATUS	current
	DESCRIPTION ""
			::= { mbus49 57 }

mbus49VIF1A		OBJECT-TYPE
			SYNTAX	INTEGER
			ACCESS	read-only
			STATUS	current
	DESCRIPTION ""
			::= { mbus49 58 }

mbus49Value1A		OBJECT-TYPE
			SYNTAX	INTEGER
			ACCESS	read-only
			STATUS	current
	DESCRIPTION ""
			::= { mbus49 59 }

mbus49VIF1B		OBJECT-TYPE
			SYNTAX	INTEGER
			ACCESS	read-only
			STATUS	current
	DESCRIPTION ""
			::= { mbus49 60 }

mbus49Value1B		OBJECT-TYPE
			SYNTAX	INTEGER
			ACCESS	read-only
			STATUS	current
	DESCRIPTION ""
			::= { mbus49 61 }

mbus49VIF1C		OBJECT-TYPE
			SYNTAX	INTEGER
			ACCESS	read-only
			STATUS	current
	DESCRIPTION ""
			::= { mbus49 62 }

mbus49Value1C		OBJECT-TYPE
			SYNTAX	INTEGER
			ACCESS	read-only
			STATUS	current
	DESCRIPTION ""
			::= { mbus49 63 }

mbus49VIF1D		OBJECT-TYPE
			SYNTAX	INTEGER
			ACCESS	read-only
			STATUS	current
	DESCRIPTION ""
			::= { mbus49 64 }

mbus49Value1D		OBJECT-TYPE
			SYNTAX	INTEGER
			ACCESS	read-only
			STATUS	current
	DESCRIPTION ""
			::= { mbus49 65 }

mbus49VIF1E		OBJECT-TYPE
			SYNTAX	INTEGER
			ACCESS	read-only
			STATUS	current
	DESCRIPTION ""
			::= { mbus49 66 }

mbus49Value1E		OBJECT-TYPE
			SYNTAX	INTEGER
			ACCESS	read-only
			STATUS	current
	DESCRIPTION ""
			::= { mbus49 67 }

mbus49VIF1F		OBJECT-TYPE
			SYNTAX	INTEGER
			ACCESS	read-only
			STATUS	current
	DESCRIPTION ""
			::= { mbus49 68 }

mbus49Value1F		OBJECT-TYPE
			SYNTAX	INTEGER
			ACCESS	read-only
			STATUS	current
	DESCRIPTION ""
			::= { mbus49 69 }

mbus49VIF20		OBJECT-TYPE
			SYNTAX	INTEGER
			ACCESS	read-only
			STATUS	current
	DESCRIPTION ""
			::= { mbus49 70 }

mbus49Value20		OBJECT-TYPE
			SYNTAX	INTEGER
			ACCESS	read-only
			STATUS	current
	DESCRIPTION ""
			::= { mbus49 71 }

mbus49VIF21		OBJECT-TYPE
			SYNTAX	INTEGER
			ACCESS	read-only
			STATUS	current
	DESCRIPTION ""
			::= { mbus49 72 }

mbus49Value21		OBJECT-TYPE
			SYNTAX	INTEGER
			ACCESS	read-only
			STATUS	current
	DESCRIPTION ""
			::= { mbus49 73 }

mbus49VIF22		OBJECT-TYPE
			SYNTAX	INTEGER
			ACCESS	read-only
			STATUS	current
	DESCRIPTION ""
			::= { mbus49 74 }

mbus49Value22		OBJECT-TYPE
			SYNTAX	INTEGER
			ACCESS	read-only
			STATUS	current
	DESCRIPTION ""
			::= { mbus49 75 }

mbus49VIF23		OBJECT-TYPE
			SYNTAX	INTEGER
			ACCESS	read-only
			STATUS	current
	DESCRIPTION ""
			::= { mbus49 76 }

mbus49Value23		OBJECT-TYPE
			SYNTAX	INTEGER
			ACCESS	read-only
			STATUS	current
	DESCRIPTION ""
			::= { mbus49 77 }

mbus49VIF24		OBJECT-TYPE
			SYNTAX	INTEGER
			ACCESS	read-only
			STATUS	current
	DESCRIPTION ""
			::= { mbus49 78 }

mbus49Value24		OBJECT-TYPE
			SYNTAX	INTEGER
			ACCESS	read-only
			STATUS	current
	DESCRIPTION ""
			::= { mbus49 79 }

mbus49VIF25		OBJECT-TYPE
			SYNTAX	INTEGER
			ACCESS	read-only
			STATUS	current
	DESCRIPTION ""
			::= { mbus49 80 }

mbus49Value25		OBJECT-TYPE
			SYNTAX	INTEGER
			ACCESS	read-only
			STATUS	current
	DESCRIPTION ""
			::= { mbus49 81 }

mbus49VIF26		OBJECT-TYPE
			SYNTAX	INTEGER
			ACCESS	read-only
			STATUS	current
	DESCRIPTION ""
			::= { mbus49 82 }

mbus49Value26		OBJECT-TYPE
			SYNTAX	INTEGER
			ACCESS	read-only
			STATUS	current
	DESCRIPTION ""
			::= { mbus49 83 }

mbus49VIF27		OBJECT-TYPE
			SYNTAX	INTEGER
			ACCESS	read-only
			STATUS	current
	DESCRIPTION ""
			::= { mbus49 84 }

mbus49Value27		OBJECT-TYPE
			SYNTAX	INTEGER
			ACCESS	read-only
			STATUS	current
	DESCRIPTION ""
			::= { mbus49 85 }

mbus49VIF28		OBJECT-TYPE
			SYNTAX	INTEGER
			ACCESS	read-only
			STATUS	current
	DESCRIPTION ""
			::= { mbus49 86 }

mbus49Value28		OBJECT-TYPE
			SYNTAX	INTEGER
			ACCESS	read-only
			STATUS	current
	DESCRIPTION ""
			::= { mbus49 87 }

mbus49VIF29		OBJECT-TYPE
			SYNTAX	INTEGER
			ACCESS	read-only
			STATUS	current
	DESCRIPTION ""
			::= { mbus49 88 }

mbus49Value29		OBJECT-TYPE
			SYNTAX	INTEGER
			ACCESS	read-only
			STATUS	current
	DESCRIPTION ""
			::= { mbus49 89 }

mbus49VIF2A		OBJECT-TYPE
			SYNTAX	INTEGER
			ACCESS	read-only
			STATUS	current
	DESCRIPTION ""
			::= { mbus49 90 }

mbus49Value2A		OBJECT-TYPE
			SYNTAX	INTEGER
			ACCESS	read-only
			STATUS	current
	DESCRIPTION ""
			::= { mbus49 91 }

mbus49VIF2B		OBJECT-TYPE
			SYNTAX	INTEGER
			ACCESS	read-only
			STATUS	current
	DESCRIPTION ""
			::= { mbus49 92 }

mbus49Value2B		OBJECT-TYPE
			SYNTAX	INTEGER
			ACCESS	read-only
			STATUS	current
	DESCRIPTION ""
			::= { mbus49 93 }

mbus49VIF2C		OBJECT-TYPE
			SYNTAX	INTEGER
			ACCESS	read-only
			STATUS	current
	DESCRIPTION ""
			::= { mbus49 94 }

mbus49Value2C		OBJECT-TYPE
			SYNTAX	INTEGER
			ACCESS	read-only
			STATUS	current
	DESCRIPTION ""
			::= { mbus49 95 }

mbus49VIF2D		OBJECT-TYPE
			SYNTAX	INTEGER
			ACCESS	read-only
			STATUS	current
	DESCRIPTION ""
			::= { mbus49 96 }

mbus49Value2D		OBJECT-TYPE
			SYNTAX	INTEGER
			ACCESS	read-only
			STATUS	current
	DESCRIPTION ""
			::= { mbus49 97 }

mbus49VIF2E		OBJECT-TYPE
			SYNTAX	INTEGER
			ACCESS	read-only
			STATUS	current
	DESCRIPTION ""
			::= { mbus49 98 }

mbus49Value2E		OBJECT-TYPE
			SYNTAX	INTEGER
			ACCESS	read-only
			STATUS	current
	DESCRIPTION ""
			::= { mbus49 99 }

mbus49VIF2F		OBJECT-TYPE
			SYNTAX	INTEGER
			ACCESS	read-only
			STATUS	current
	DESCRIPTION ""
			::= { mbus49 100 }

mbus49Value2F		OBJECT-TYPE
			SYNTAX	INTEGER
			ACCESS	read-only
			STATUS	current
	DESCRIPTION ""
			::= { mbus49 101 }

mbus4A			OBJECT IDENTIFIER ::= { mbus 74 }

mbus4AIdNumber		OBJECT-TYPE
			SYNTAX	Gauge
			ACCESS	read-only
			STATUS	current
	DESCRIPTION ""
			::= { mbus4A 1 }

mbus4AManufacturer	OBJECT-TYPE
			SYNTAX	Gauge
			ACCESS	read-only
			STATUS	current
	DESCRIPTION ""
			::= { mbus4A 2 }

mbus4AVersion		OBJECT-TYPE
			SYNTAX	Gauge
			ACCESS	read-only
			STATUS	current
	DESCRIPTION ""
			::= { mbus4A 3 }

mbus4AMedium		OBJECT-TYPE
			SYNTAX	Gauge
			ACCESS	read-only
			STATUS	current
	DESCRIPTION ""
			::= { mbus4A 4 }

mbus4AStatus		OBJECT-TYPE
			SYNTAX	Gauge
			ACCESS	read-only
			STATUS	current
	DESCRIPTION ""
			::= { mbus4A 5 }

mbus4AVIF00		OBJECT-TYPE
			SYNTAX	INTEGER
			ACCESS	read-only
			STATUS	current
	DESCRIPTION ""
			::= { mbus4A 6 }

mbus4AValue00		OBJECT-TYPE
			SYNTAX	INTEGER
			ACCESS	read-only
			STATUS	current
	DESCRIPTION ""
			::= { mbus4A 7 }

mbus4AVIF01		OBJECT-TYPE
			SYNTAX	INTEGER
			ACCESS	read-only
			STATUS	current
	DESCRIPTION ""
			::= { mbus4A 8 }

mbus4AValue01		OBJECT-TYPE
			SYNTAX	INTEGER
			ACCESS	read-only
			STATUS	current
	DESCRIPTION ""
			::= { mbus4A 9 }

mbus4AVIF02		OBJECT-TYPE
			SYNTAX	INTEGER
			ACCESS	read-only
			STATUS	current
	DESCRIPTION ""
			::= { mbus4A 10 }

mbus4AValue02		OBJECT-TYPE
			SYNTAX	INTEGER
			ACCESS	read-only
			STATUS	current
	DESCRIPTION ""
			::= { mbus4A 11 }

mbus4AVIF03		OBJECT-TYPE
			SYNTAX	INTEGER
			ACCESS	read-only
			STATUS	current
	DESCRIPTION ""
			::= { mbus4A 12 }

mbus4AValue03		OBJECT-TYPE
			SYNTAX	INTEGER
			ACCESS	read-only
			STATUS	current
	DESCRIPTION ""
			::= { mbus4A 13 }

mbus4AVIF04		OBJECT-TYPE
			SYNTAX	INTEGER
			ACCESS	read-only
			STATUS	current
	DESCRIPTION ""
			::= { mbus4A 14 }

mbus4AValue04		OBJECT-TYPE
			SYNTAX	INTEGER
			ACCESS	read-only
			STATUS	current
	DESCRIPTION ""
			::= { mbus4A 15 }

mbus4AVIF05		OBJECT-TYPE
			SYNTAX	INTEGER
			ACCESS	read-only
			STATUS	current
	DESCRIPTION ""
			::= { mbus4A 16 }

mbus4AValue05		OBJECT-TYPE
			SYNTAX	INTEGER
			ACCESS	read-only
			STATUS	current
	DESCRIPTION ""
			::= { mbus4A 17 }

mbus4AVIF06		OBJECT-TYPE
			SYNTAX	INTEGER
			ACCESS	read-only
			STATUS	current
	DESCRIPTION ""
			::= { mbus4A 18 }

mbus4AValue06		OBJECT-TYPE
			SYNTAX	INTEGER
			ACCESS	read-only
			STATUS	current
	DESCRIPTION ""
			::= { mbus4A 19 }

mbus4AVIF07		OBJECT-TYPE
			SYNTAX	INTEGER
			ACCESS	read-only
			STATUS	current
	DESCRIPTION ""
			::= { mbus4A 20 }

mbus4AValue07		OBJECT-TYPE
			SYNTAX	INTEGER
			ACCESS	read-only
			STATUS	current
	DESCRIPTION ""
			::= { mbus4A 21 }

mbus4AVIF08		OBJECT-TYPE
			SYNTAX	INTEGER
			ACCESS	read-only
			STATUS	current
	DESCRIPTION ""
			::= { mbus4A 22 }

mbus4AValue08		OBJECT-TYPE
			SYNTAX	INTEGER
			ACCESS	read-only
			STATUS	current
	DESCRIPTION ""
			::= { mbus4A 23 }

mbus4AVIF09		OBJECT-TYPE
			SYNTAX	INTEGER
			ACCESS	read-only
			STATUS	current
	DESCRIPTION ""
			::= { mbus4A 24 }

mbus4AValue09		OBJECT-TYPE
			SYNTAX	INTEGER
			ACCESS	read-only
			STATUS	current
	DESCRIPTION ""
			::= { mbus4A 25 }

mbus4AVIF0A		OBJECT-TYPE
			SYNTAX	INTEGER
			ACCESS	read-only
			STATUS	current
	DESCRIPTION ""
			::= { mbus4A 26 }

mbus4AValue0A		OBJECT-TYPE
			SYNTAX	INTEGER
			ACCESS	read-only
			STATUS	current
	DESCRIPTION ""
			::= { mbus4A 27 }

mbus4AVIF0B		OBJECT-TYPE
			SYNTAX	INTEGER
			ACCESS	read-only
			STATUS	current
	DESCRIPTION ""
			::= { mbus4A 28 }

mbus4AValue0B		OBJECT-TYPE
			SYNTAX	INTEGER
			ACCESS	read-only
			STATUS	current
	DESCRIPTION ""
			::= { mbus4A 29 }

mbus4AVIF0C		OBJECT-TYPE
			SYNTAX	INTEGER
			ACCESS	read-only
			STATUS	current
	DESCRIPTION ""
			::= { mbus4A 30 }

mbus4AValue0C		OBJECT-TYPE
			SYNTAX	INTEGER
			ACCESS	read-only
			STATUS	current
	DESCRIPTION ""
			::= { mbus4A 31 }

mbus4AVIF0D		OBJECT-TYPE
			SYNTAX	INTEGER
			ACCESS	read-only
			STATUS	current
	DESCRIPTION ""
			::= { mbus4A 32 }

mbus4AValue0D		OBJECT-TYPE
			SYNTAX	INTEGER
			ACCESS	read-only
			STATUS	current
	DESCRIPTION ""
			::= { mbus4A 33 }

mbus4AVIF0E		OBJECT-TYPE
			SYNTAX	INTEGER
			ACCESS	read-only
			STATUS	current
	DESCRIPTION ""
			::= { mbus4A 34 }

mbus4AValue0E		OBJECT-TYPE
			SYNTAX	INTEGER
			ACCESS	read-only
			STATUS	current
	DESCRIPTION ""
			::= { mbus4A 35 }

mbus4AVIF0F		OBJECT-TYPE
			SYNTAX	INTEGER
			ACCESS	read-only
			STATUS	current
	DESCRIPTION ""
			::= { mbus4A 36 }

mbus4AValue0F		OBJECT-TYPE
			SYNTAX	INTEGER
			ACCESS	read-only
			STATUS	current
	DESCRIPTION ""
			::= { mbus4A 37 }

mbus4AVIF10		OBJECT-TYPE
			SYNTAX	INTEGER
			ACCESS	read-only
			STATUS	current
	DESCRIPTION ""
			::= { mbus4A 38 }

mbus4AValue10		OBJECT-TYPE
			SYNTAX	INTEGER
			ACCESS	read-only
			STATUS	current
	DESCRIPTION ""
			::= { mbus4A 39 }

mbus4AVIF11		OBJECT-TYPE
			SYNTAX	INTEGER
			ACCESS	read-only
			STATUS	current
	DESCRIPTION ""
			::= { mbus4A 40 }

mbus4AValue11		OBJECT-TYPE
			SYNTAX	INTEGER
			ACCESS	read-only
			STATUS	current
	DESCRIPTION ""
			::= { mbus4A 41 }

mbus4AVIF12		OBJECT-TYPE
			SYNTAX	INTEGER
			ACCESS	read-only
			STATUS	current
	DESCRIPTION ""
			::= { mbus4A 42 }

mbus4AValue12		OBJECT-TYPE
			SYNTAX	INTEGER
			ACCESS	read-only
			STATUS	current
	DESCRIPTION ""
			::= { mbus4A 43 }

mbus4AVIF13		OBJECT-TYPE
			SYNTAX	INTEGER
			ACCESS	read-only
			STATUS	current
	DESCRIPTION ""
			::= { mbus4A 44 }

mbus4AValue13		OBJECT-TYPE
			SYNTAX	INTEGER
			ACCESS	read-only
			STATUS	current
	DESCRIPTION ""
			::= { mbus4A 45 }

mbus4AVIF14		OBJECT-TYPE
			SYNTAX	INTEGER
			ACCESS	read-only
			STATUS	current
	DESCRIPTION ""
			::= { mbus4A 46 }

mbus4AValue14		OBJECT-TYPE
			SYNTAX	INTEGER
			ACCESS	read-only
			STATUS	current
	DESCRIPTION ""
			::= { mbus4A 47 }

mbus4AVIF15		OBJECT-TYPE
			SYNTAX	INTEGER
			ACCESS	read-only
			STATUS	current
	DESCRIPTION ""
			::= { mbus4A 48 }

mbus4AValue15		OBJECT-TYPE
			SYNTAX	INTEGER
			ACCESS	read-only
			STATUS	current
	DESCRIPTION ""
			::= { mbus4A 49 }

mbus4AVIF16		OBJECT-TYPE
			SYNTAX	INTEGER
			ACCESS	read-only
			STATUS	current
	DESCRIPTION ""
			::= { mbus4A 50 }

mbus4AValue16		OBJECT-TYPE
			SYNTAX	INTEGER
			ACCESS	read-only
			STATUS	current
	DESCRIPTION ""
			::= { mbus4A 51 }

mbus4AVIF17		OBJECT-TYPE
			SYNTAX	INTEGER
			ACCESS	read-only
			STATUS	current
	DESCRIPTION ""
			::= { mbus4A 52 }

mbus4AValue17		OBJECT-TYPE
			SYNTAX	INTEGER
			ACCESS	read-only
			STATUS	current
	DESCRIPTION ""
			::= { mbus4A 53 }

mbus4AVIF18		OBJECT-TYPE
			SYNTAX	INTEGER
			ACCESS	read-only
			STATUS	current
	DESCRIPTION ""
			::= { mbus4A 54 }

mbus4AValue18		OBJECT-TYPE
			SYNTAX	INTEGER
			ACCESS	read-only
			STATUS	current
	DESCRIPTION ""
			::= { mbus4A 55 }

mbus4AVIF19		OBJECT-TYPE
			SYNTAX	INTEGER
			ACCESS	read-only
			STATUS	current
	DESCRIPTION ""
			::= { mbus4A 56 }

mbus4AValue19		OBJECT-TYPE
			SYNTAX	INTEGER
			ACCESS	read-only
			STATUS	current
	DESCRIPTION ""
			::= { mbus4A 57 }

mbus4AVIF1A		OBJECT-TYPE
			SYNTAX	INTEGER
			ACCESS	read-only
			STATUS	current
	DESCRIPTION ""
			::= { mbus4A 58 }

mbus4AValue1A		OBJECT-TYPE
			SYNTAX	INTEGER
			ACCESS	read-only
			STATUS	current
	DESCRIPTION ""
			::= { mbus4A 59 }

mbus4AVIF1B		OBJECT-TYPE
			SYNTAX	INTEGER
			ACCESS	read-only
			STATUS	current
	DESCRIPTION ""
			::= { mbus4A 60 }

mbus4AValue1B		OBJECT-TYPE
			SYNTAX	INTEGER
			ACCESS	read-only
			STATUS	current
	DESCRIPTION ""
			::= { mbus4A 61 }

mbus4AVIF1C		OBJECT-TYPE
			SYNTAX	INTEGER
			ACCESS	read-only
			STATUS	current
	DESCRIPTION ""
			::= { mbus4A 62 }

mbus4AValue1C		OBJECT-TYPE
			SYNTAX	INTEGER
			ACCESS	read-only
			STATUS	current
	DESCRIPTION ""
			::= { mbus4A 63 }

mbus4AVIF1D		OBJECT-TYPE
			SYNTAX	INTEGER
			ACCESS	read-only
			STATUS	current
	DESCRIPTION ""
			::= { mbus4A 64 }

mbus4AValue1D		OBJECT-TYPE
			SYNTAX	INTEGER
			ACCESS	read-only
			STATUS	current
	DESCRIPTION ""
			::= { mbus4A 65 }

mbus4AVIF1E		OBJECT-TYPE
			SYNTAX	INTEGER
			ACCESS	read-only
			STATUS	current
	DESCRIPTION ""
			::= { mbus4A 66 }

mbus4AValue1E		OBJECT-TYPE
			SYNTAX	INTEGER
			ACCESS	read-only
			STATUS	current
	DESCRIPTION ""
			::= { mbus4A 67 }

mbus4AVIF1F		OBJECT-TYPE
			SYNTAX	INTEGER
			ACCESS	read-only
			STATUS	current
	DESCRIPTION ""
			::= { mbus4A 68 }

mbus4AValue1F		OBJECT-TYPE
			SYNTAX	INTEGER
			ACCESS	read-only
			STATUS	current
	DESCRIPTION ""
			::= { mbus4A 69 }

mbus4AVIF20		OBJECT-TYPE
			SYNTAX	INTEGER
			ACCESS	read-only
			STATUS	current
	DESCRIPTION ""
			::= { mbus4A 70 }

mbus4AValue20		OBJECT-TYPE
			SYNTAX	INTEGER
			ACCESS	read-only
			STATUS	current
	DESCRIPTION ""
			::= { mbus4A 71 }

mbus4AVIF21		OBJECT-TYPE
			SYNTAX	INTEGER
			ACCESS	read-only
			STATUS	current
	DESCRIPTION ""
			::= { mbus4A 72 }

mbus4AValue21		OBJECT-TYPE
			SYNTAX	INTEGER
			ACCESS	read-only
			STATUS	current
	DESCRIPTION ""
			::= { mbus4A 73 }

mbus4AVIF22		OBJECT-TYPE
			SYNTAX	INTEGER
			ACCESS	read-only
			STATUS	current
	DESCRIPTION ""
			::= { mbus4A 74 }

mbus4AValue22		OBJECT-TYPE
			SYNTAX	INTEGER
			ACCESS	read-only
			STATUS	current
	DESCRIPTION ""
			::= { mbus4A 75 }

mbus4AVIF23		OBJECT-TYPE
			SYNTAX	INTEGER
			ACCESS	read-only
			STATUS	current
	DESCRIPTION ""
			::= { mbus4A 76 }

mbus4AValue23		OBJECT-TYPE
			SYNTAX	INTEGER
			ACCESS	read-only
			STATUS	current
	DESCRIPTION ""
			::= { mbus4A 77 }

mbus4AVIF24		OBJECT-TYPE
			SYNTAX	INTEGER
			ACCESS	read-only
			STATUS	current
	DESCRIPTION ""
			::= { mbus4A 78 }

mbus4AValue24		OBJECT-TYPE
			SYNTAX	INTEGER
			ACCESS	read-only
			STATUS	current
	DESCRIPTION ""
			::= { mbus4A 79 }

mbus4AVIF25		OBJECT-TYPE
			SYNTAX	INTEGER
			ACCESS	read-only
			STATUS	current
	DESCRIPTION ""
			::= { mbus4A 80 }

mbus4AValue25		OBJECT-TYPE
			SYNTAX	INTEGER
			ACCESS	read-only
			STATUS	current
	DESCRIPTION ""
			::= { mbus4A 81 }

mbus4AVIF26		OBJECT-TYPE
			SYNTAX	INTEGER
			ACCESS	read-only
			STATUS	current
	DESCRIPTION ""
			::= { mbus4A 82 }

mbus4AValue26		OBJECT-TYPE
			SYNTAX	INTEGER
			ACCESS	read-only
			STATUS	current
	DESCRIPTION ""
			::= { mbus4A 83 }

mbus4AVIF27		OBJECT-TYPE
			SYNTAX	INTEGER
			ACCESS	read-only
			STATUS	current
	DESCRIPTION ""
			::= { mbus4A 84 }

mbus4AValue27		OBJECT-TYPE
			SYNTAX	INTEGER
			ACCESS	read-only
			STATUS	current
	DESCRIPTION ""
			::= { mbus4A 85 }

mbus4AVIF28		OBJECT-TYPE
			SYNTAX	INTEGER
			ACCESS	read-only
			STATUS	current
	DESCRIPTION ""
			::= { mbus4A 86 }

mbus4AValue28		OBJECT-TYPE
			SYNTAX	INTEGER
			ACCESS	read-only
			STATUS	current
	DESCRIPTION ""
			::= { mbus4A 87 }

mbus4AVIF29		OBJECT-TYPE
			SYNTAX	INTEGER
			ACCESS	read-only
			STATUS	current
	DESCRIPTION ""
			::= { mbus4A 88 }

mbus4AValue29		OBJECT-TYPE
			SYNTAX	INTEGER
			ACCESS	read-only
			STATUS	current
	DESCRIPTION ""
			::= { mbus4A 89 }

mbus4AVIF2A		OBJECT-TYPE
			SYNTAX	INTEGER
			ACCESS	read-only
			STATUS	current
	DESCRIPTION ""
			::= { mbus4A 90 }

mbus4AValue2A		OBJECT-TYPE
			SYNTAX	INTEGER
			ACCESS	read-only
			STATUS	current
	DESCRIPTION ""
			::= { mbus4A 91 }

mbus4AVIF2B		OBJECT-TYPE
			SYNTAX	INTEGER
			ACCESS	read-only
			STATUS	current
	DESCRIPTION ""
			::= { mbus4A 92 }

mbus4AValue2B		OBJECT-TYPE
			SYNTAX	INTEGER
			ACCESS	read-only
			STATUS	current
	DESCRIPTION ""
			::= { mbus4A 93 }

mbus4AVIF2C		OBJECT-TYPE
			SYNTAX	INTEGER
			ACCESS	read-only
			STATUS	current
	DESCRIPTION ""
			::= { mbus4A 94 }

mbus4AValue2C		OBJECT-TYPE
			SYNTAX	INTEGER
			ACCESS	read-only
			STATUS	current
	DESCRIPTION ""
			::= { mbus4A 95 }

mbus4AVIF2D		OBJECT-TYPE
			SYNTAX	INTEGER
			ACCESS	read-only
			STATUS	current
	DESCRIPTION ""
			::= { mbus4A 96 }

mbus4AValue2D		OBJECT-TYPE
			SYNTAX	INTEGER
			ACCESS	read-only
			STATUS	current
	DESCRIPTION ""
			::= { mbus4A 97 }

mbus4AVIF2E		OBJECT-TYPE
			SYNTAX	INTEGER
			ACCESS	read-only
			STATUS	current
	DESCRIPTION ""
			::= { mbus4A 98 }

mbus4AValue2E		OBJECT-TYPE
			SYNTAX	INTEGER
			ACCESS	read-only
			STATUS	current
	DESCRIPTION ""
			::= { mbus4A 99 }

mbus4AVIF2F		OBJECT-TYPE
			SYNTAX	INTEGER
			ACCESS	read-only
			STATUS	current
	DESCRIPTION ""
			::= { mbus4A 100 }

mbus4AValue2F		OBJECT-TYPE
			SYNTAX	INTEGER
			ACCESS	read-only
			STATUS	current
	DESCRIPTION ""
			::= { mbus4A 101 }

mbus4B			OBJECT IDENTIFIER ::= { mbus 75 }

mbus4BIdNumber		OBJECT-TYPE
			SYNTAX	Gauge
			ACCESS	read-only
			STATUS	current
	DESCRIPTION ""
			::= { mbus4B 1 }

mbus4BManufacturer	OBJECT-TYPE
			SYNTAX	Gauge
			ACCESS	read-only
			STATUS	current
	DESCRIPTION ""
			::= { mbus4B 2 }

mbus4BVersion		OBJECT-TYPE
			SYNTAX	Gauge
			ACCESS	read-only
			STATUS	current
	DESCRIPTION ""
			::= { mbus4B 3 }

mbus4BMedium		OBJECT-TYPE
			SYNTAX	Gauge
			ACCESS	read-only
			STATUS	current
	DESCRIPTION ""
			::= { mbus4B 4 }

mbus4BStatus		OBJECT-TYPE
			SYNTAX	Gauge
			ACCESS	read-only
			STATUS	current
	DESCRIPTION ""
			::= { mbus4B 5 }

mbus4BVIF00		OBJECT-TYPE
			SYNTAX	INTEGER
			ACCESS	read-only
			STATUS	current
	DESCRIPTION ""
			::= { mbus4B 6 }

mbus4BValue00		OBJECT-TYPE
			SYNTAX	INTEGER
			ACCESS	read-only
			STATUS	current
	DESCRIPTION ""
			::= { mbus4B 7 }

mbus4BVIF01		OBJECT-TYPE
			SYNTAX	INTEGER
			ACCESS	read-only
			STATUS	current
	DESCRIPTION ""
			::= { mbus4B 8 }

mbus4BValue01		OBJECT-TYPE
			SYNTAX	INTEGER
			ACCESS	read-only
			STATUS	current
	DESCRIPTION ""
			::= { mbus4B 9 }

mbus4BVIF02		OBJECT-TYPE
			SYNTAX	INTEGER
			ACCESS	read-only
			STATUS	current
	DESCRIPTION ""
			::= { mbus4B 10 }

mbus4BValue02		OBJECT-TYPE
			SYNTAX	INTEGER
			ACCESS	read-only
			STATUS	current
	DESCRIPTION ""
			::= { mbus4B 11 }

mbus4BVIF03		OBJECT-TYPE
			SYNTAX	INTEGER
			ACCESS	read-only
			STATUS	current
	DESCRIPTION ""
			::= { mbus4B 12 }

mbus4BValue03		OBJECT-TYPE
			SYNTAX	INTEGER
			ACCESS	read-only
			STATUS	current
	DESCRIPTION ""
			::= { mbus4B 13 }

mbus4BVIF04		OBJECT-TYPE
			SYNTAX	INTEGER
			ACCESS	read-only
			STATUS	current
	DESCRIPTION ""
			::= { mbus4B 14 }

mbus4BValue04		OBJECT-TYPE
			SYNTAX	INTEGER
			ACCESS	read-only
			STATUS	current
	DESCRIPTION ""
			::= { mbus4B 15 }

mbus4BVIF05		OBJECT-TYPE
			SYNTAX	INTEGER
			ACCESS	read-only
			STATUS	current
	DESCRIPTION ""
			::= { mbus4B 16 }

mbus4BValue05		OBJECT-TYPE
			SYNTAX	INTEGER
			ACCESS	read-only
			STATUS	current
	DESCRIPTION ""
			::= { mbus4B 17 }

mbus4BVIF06		OBJECT-TYPE
			SYNTAX	INTEGER
			ACCESS	read-only
			STATUS	current
	DESCRIPTION ""
			::= { mbus4B 18 }

mbus4BValue06		OBJECT-TYPE
			SYNTAX	INTEGER
			ACCESS	read-only
			STATUS	current
	DESCRIPTION ""
			::= { mbus4B 19 }

mbus4BVIF07		OBJECT-TYPE
			SYNTAX	INTEGER
			ACCESS	read-only
			STATUS	current
	DESCRIPTION ""
			::= { mbus4B 20 }

mbus4BValue07		OBJECT-TYPE
			SYNTAX	INTEGER
			ACCESS	read-only
			STATUS	current
	DESCRIPTION ""
			::= { mbus4B 21 }

mbus4BVIF08		OBJECT-TYPE
			SYNTAX	INTEGER
			ACCESS	read-only
			STATUS	current
	DESCRIPTION ""
			::= { mbus4B 22 }

mbus4BValue08		OBJECT-TYPE
			SYNTAX	INTEGER
			ACCESS	read-only
			STATUS	current
	DESCRIPTION ""
			::= { mbus4B 23 }

mbus4BVIF09		OBJECT-TYPE
			SYNTAX	INTEGER
			ACCESS	read-only
			STATUS	current
	DESCRIPTION ""
			::= { mbus4B 24 }

mbus4BValue09		OBJECT-TYPE
			SYNTAX	INTEGER
			ACCESS	read-only
			STATUS	current
	DESCRIPTION ""
			::= { mbus4B 25 }

mbus4BVIF0A		OBJECT-TYPE
			SYNTAX	INTEGER
			ACCESS	read-only
			STATUS	current
	DESCRIPTION ""
			::= { mbus4B 26 }

mbus4BValue0A		OBJECT-TYPE
			SYNTAX	INTEGER
			ACCESS	read-only
			STATUS	current
	DESCRIPTION ""
			::= { mbus4B 27 }

mbus4BVIF0B		OBJECT-TYPE
			SYNTAX	INTEGER
			ACCESS	read-only
			STATUS	current
	DESCRIPTION ""
			::= { mbus4B 28 }

mbus4BValue0B		OBJECT-TYPE
			SYNTAX	INTEGER
			ACCESS	read-only
			STATUS	current
	DESCRIPTION ""
			::= { mbus4B 29 }

mbus4BVIF0C		OBJECT-TYPE
			SYNTAX	INTEGER
			ACCESS	read-only
			STATUS	current
	DESCRIPTION ""
			::= { mbus4B 30 }

mbus4BValue0C		OBJECT-TYPE
			SYNTAX	INTEGER
			ACCESS	read-only
			STATUS	current
	DESCRIPTION ""
			::= { mbus4B 31 }

mbus4BVIF0D		OBJECT-TYPE
			SYNTAX	INTEGER
			ACCESS	read-only
			STATUS	current
	DESCRIPTION ""
			::= { mbus4B 32 }

mbus4BValue0D		OBJECT-TYPE
			SYNTAX	INTEGER
			ACCESS	read-only
			STATUS	current
	DESCRIPTION ""
			::= { mbus4B 33 }

mbus4BVIF0E		OBJECT-TYPE
			SYNTAX	INTEGER
			ACCESS	read-only
			STATUS	current
	DESCRIPTION ""
			::= { mbus4B 34 }

mbus4BValue0E		OBJECT-TYPE
			SYNTAX	INTEGER
			ACCESS	read-only
			STATUS	current
	DESCRIPTION ""
			::= { mbus4B 35 }

mbus4BVIF0F		OBJECT-TYPE
			SYNTAX	INTEGER
			ACCESS	read-only
			STATUS	current
	DESCRIPTION ""
			::= { mbus4B 36 }

mbus4BValue0F		OBJECT-TYPE
			SYNTAX	INTEGER
			ACCESS	read-only
			STATUS	current
	DESCRIPTION ""
			::= { mbus4B 37 }

mbus4BVIF10		OBJECT-TYPE
			SYNTAX	INTEGER
			ACCESS	read-only
			STATUS	current
	DESCRIPTION ""
			::= { mbus4B 38 }

mbus4BValue10		OBJECT-TYPE
			SYNTAX	INTEGER
			ACCESS	read-only
			STATUS	current
	DESCRIPTION ""
			::= { mbus4B 39 }

mbus4BVIF11		OBJECT-TYPE
			SYNTAX	INTEGER
			ACCESS	read-only
			STATUS	current
	DESCRIPTION ""
			::= { mbus4B 40 }

mbus4BValue11		OBJECT-TYPE
			SYNTAX	INTEGER
			ACCESS	read-only
			STATUS	current
	DESCRIPTION ""
			::= { mbus4B 41 }

mbus4BVIF12		OBJECT-TYPE
			SYNTAX	INTEGER
			ACCESS	read-only
			STATUS	current
	DESCRIPTION ""
			::= { mbus4B 42 }

mbus4BValue12		OBJECT-TYPE
			SYNTAX	INTEGER
			ACCESS	read-only
			STATUS	current
	DESCRIPTION ""
			::= { mbus4B 43 }

mbus4BVIF13		OBJECT-TYPE
			SYNTAX	INTEGER
			ACCESS	read-only
			STATUS	current
	DESCRIPTION ""
			::= { mbus4B 44 }

mbus4BValue13		OBJECT-TYPE
			SYNTAX	INTEGER
			ACCESS	read-only
			STATUS	current
	DESCRIPTION ""
			::= { mbus4B 45 }

mbus4BVIF14		OBJECT-TYPE
			SYNTAX	INTEGER
			ACCESS	read-only
			STATUS	current
	DESCRIPTION ""
			::= { mbus4B 46 }

mbus4BValue14		OBJECT-TYPE
			SYNTAX	INTEGER
			ACCESS	read-only
			STATUS	current
	DESCRIPTION ""
			::= { mbus4B 47 }

mbus4BVIF15		OBJECT-TYPE
			SYNTAX	INTEGER
			ACCESS	read-only
			STATUS	current
	DESCRIPTION ""
			::= { mbus4B 48 }

mbus4BValue15		OBJECT-TYPE
			SYNTAX	INTEGER
			ACCESS	read-only
			STATUS	current
	DESCRIPTION ""
			::= { mbus4B 49 }

mbus4BVIF16		OBJECT-TYPE
			SYNTAX	INTEGER
			ACCESS	read-only
			STATUS	current
	DESCRIPTION ""
			::= { mbus4B 50 }

mbus4BValue16		OBJECT-TYPE
			SYNTAX	INTEGER
			ACCESS	read-only
			STATUS	current
	DESCRIPTION ""
			::= { mbus4B 51 }

mbus4BVIF17		OBJECT-TYPE
			SYNTAX	INTEGER
			ACCESS	read-only
			STATUS	current
	DESCRIPTION ""
			::= { mbus4B 52 }

mbus4BValue17		OBJECT-TYPE
			SYNTAX	INTEGER
			ACCESS	read-only
			STATUS	current
	DESCRIPTION ""
			::= { mbus4B 53 }

mbus4BVIF18		OBJECT-TYPE
			SYNTAX	INTEGER
			ACCESS	read-only
			STATUS	current
	DESCRIPTION ""
			::= { mbus4B 54 }

mbus4BValue18		OBJECT-TYPE
			SYNTAX	INTEGER
			ACCESS	read-only
			STATUS	current
	DESCRIPTION ""
			::= { mbus4B 55 }

mbus4BVIF19		OBJECT-TYPE
			SYNTAX	INTEGER
			ACCESS	read-only
			STATUS	current
	DESCRIPTION ""
			::= { mbus4B 56 }

mbus4BValue19		OBJECT-TYPE
			SYNTAX	INTEGER
			ACCESS	read-only
			STATUS	current
	DESCRIPTION ""
			::= { mbus4B 57 }

mbus4BVIF1A		OBJECT-TYPE
			SYNTAX	INTEGER
			ACCESS	read-only
			STATUS	current
	DESCRIPTION ""
			::= { mbus4B 58 }

mbus4BValue1A		OBJECT-TYPE
			SYNTAX	INTEGER
			ACCESS	read-only
			STATUS	current
	DESCRIPTION ""
			::= { mbus4B 59 }

mbus4BVIF1B		OBJECT-TYPE
			SYNTAX	INTEGER
			ACCESS	read-only
			STATUS	current
	DESCRIPTION ""
			::= { mbus4B 60 }

mbus4BValue1B		OBJECT-TYPE
			SYNTAX	INTEGER
			ACCESS	read-only
			STATUS	current
	DESCRIPTION ""
			::= { mbus4B 61 }

mbus4BVIF1C		OBJECT-TYPE
			SYNTAX	INTEGER
			ACCESS	read-only
			STATUS	current
	DESCRIPTION ""
			::= { mbus4B 62 }

mbus4BValue1C		OBJECT-TYPE
			SYNTAX	INTEGER
			ACCESS	read-only
			STATUS	current
	DESCRIPTION ""
			::= { mbus4B 63 }

mbus4BVIF1D		OBJECT-TYPE
			SYNTAX	INTEGER
			ACCESS	read-only
			STATUS	current
	DESCRIPTION ""
			::= { mbus4B 64 }

mbus4BValue1D		OBJECT-TYPE
			SYNTAX	INTEGER
			ACCESS	read-only
			STATUS	current
	DESCRIPTION ""
			::= { mbus4B 65 }

mbus4BVIF1E		OBJECT-TYPE
			SYNTAX	INTEGER
			ACCESS	read-only
			STATUS	current
	DESCRIPTION ""
			::= { mbus4B 66 }

mbus4BValue1E		OBJECT-TYPE
			SYNTAX	INTEGER
			ACCESS	read-only
			STATUS	current
	DESCRIPTION ""
			::= { mbus4B 67 }

mbus4BVIF1F		OBJECT-TYPE
			SYNTAX	INTEGER
			ACCESS	read-only
			STATUS	current
	DESCRIPTION ""
			::= { mbus4B 68 }

mbus4BValue1F		OBJECT-TYPE
			SYNTAX	INTEGER
			ACCESS	read-only
			STATUS	current
	DESCRIPTION ""
			::= { mbus4B 69 }

mbus4BVIF20		OBJECT-TYPE
			SYNTAX	INTEGER
			ACCESS	read-only
			STATUS	current
	DESCRIPTION ""
			::= { mbus4B 70 }

mbus4BValue20		OBJECT-TYPE
			SYNTAX	INTEGER
			ACCESS	read-only
			STATUS	current
	DESCRIPTION ""
			::= { mbus4B 71 }

mbus4BVIF21		OBJECT-TYPE
			SYNTAX	INTEGER
			ACCESS	read-only
			STATUS	current
	DESCRIPTION ""
			::= { mbus4B 72 }

mbus4BValue21		OBJECT-TYPE
			SYNTAX	INTEGER
			ACCESS	read-only
			STATUS	current
	DESCRIPTION ""
			::= { mbus4B 73 }

mbus4BVIF22		OBJECT-TYPE
			SYNTAX	INTEGER
			ACCESS	read-only
			STATUS	current
	DESCRIPTION ""
			::= { mbus4B 74 }

mbus4BValue22		OBJECT-TYPE
			SYNTAX	INTEGER
			ACCESS	read-only
			STATUS	current
	DESCRIPTION ""
			::= { mbus4B 75 }

mbus4BVIF23		OBJECT-TYPE
			SYNTAX	INTEGER
			ACCESS	read-only
			STATUS	current
	DESCRIPTION ""
			::= { mbus4B 76 }

mbus4BValue23		OBJECT-TYPE
			SYNTAX	INTEGER
			ACCESS	read-only
			STATUS	current
	DESCRIPTION ""
			::= { mbus4B 77 }

mbus4BVIF24		OBJECT-TYPE
			SYNTAX	INTEGER
			ACCESS	read-only
			STATUS	current
	DESCRIPTION ""
			::= { mbus4B 78 }

mbus4BValue24		OBJECT-TYPE
			SYNTAX	INTEGER
			ACCESS	read-only
			STATUS	current
	DESCRIPTION ""
			::= { mbus4B 79 }

mbus4BVIF25		OBJECT-TYPE
			SYNTAX	INTEGER
			ACCESS	read-only
			STATUS	current
	DESCRIPTION ""
			::= { mbus4B 80 }

mbus4BValue25		OBJECT-TYPE
			SYNTAX	INTEGER
			ACCESS	read-only
			STATUS	current
	DESCRIPTION ""
			::= { mbus4B 81 }

mbus4BVIF26		OBJECT-TYPE
			SYNTAX	INTEGER
			ACCESS	read-only
			STATUS	current
	DESCRIPTION ""
			::= { mbus4B 82 }

mbus4BValue26		OBJECT-TYPE
			SYNTAX	INTEGER
			ACCESS	read-only
			STATUS	current
	DESCRIPTION ""
			::= { mbus4B 83 }

mbus4BVIF27		OBJECT-TYPE
			SYNTAX	INTEGER
			ACCESS	read-only
			STATUS	current
	DESCRIPTION ""
			::= { mbus4B 84 }

mbus4BValue27		OBJECT-TYPE
			SYNTAX	INTEGER
			ACCESS	read-only
			STATUS	current
	DESCRIPTION ""
			::= { mbus4B 85 }

mbus4BVIF28		OBJECT-TYPE
			SYNTAX	INTEGER
			ACCESS	read-only
			STATUS	current
	DESCRIPTION ""
			::= { mbus4B 86 }

mbus4BValue28		OBJECT-TYPE
			SYNTAX	INTEGER
			ACCESS	read-only
			STATUS	current
	DESCRIPTION ""
			::= { mbus4B 87 }

mbus4BVIF29		OBJECT-TYPE
			SYNTAX	INTEGER
			ACCESS	read-only
			STATUS	current
	DESCRIPTION ""
			::= { mbus4B 88 }

mbus4BValue29		OBJECT-TYPE
			SYNTAX	INTEGER
			ACCESS	read-only
			STATUS	current
	DESCRIPTION ""
			::= { mbus4B 89 }

mbus4BVIF2A		OBJECT-TYPE
			SYNTAX	INTEGER
			ACCESS	read-only
			STATUS	current
	DESCRIPTION ""
			::= { mbus4B 90 }

mbus4BValue2A		OBJECT-TYPE
			SYNTAX	INTEGER
			ACCESS	read-only
			STATUS	current
	DESCRIPTION ""
			::= { mbus4B 91 }

mbus4BVIF2B		OBJECT-TYPE
			SYNTAX	INTEGER
			ACCESS	read-only
			STATUS	current
	DESCRIPTION ""
			::= { mbus4B 92 }

mbus4BValue2B		OBJECT-TYPE
			SYNTAX	INTEGER
			ACCESS	read-only
			STATUS	current
	DESCRIPTION ""
			::= { mbus4B 93 }

mbus4BVIF2C		OBJECT-TYPE
			SYNTAX	INTEGER
			ACCESS	read-only
			STATUS	current
	DESCRIPTION ""
			::= { mbus4B 94 }

mbus4BValue2C		OBJECT-TYPE
			SYNTAX	INTEGER
			ACCESS	read-only
			STATUS	current
	DESCRIPTION ""
			::= { mbus4B 95 }

mbus4BVIF2D		OBJECT-TYPE
			SYNTAX	INTEGER
			ACCESS	read-only
			STATUS	current
	DESCRIPTION ""
			::= { mbus4B 96 }

mbus4BValue2D		OBJECT-TYPE
			SYNTAX	INTEGER
			ACCESS	read-only
			STATUS	current
	DESCRIPTION ""
			::= { mbus4B 97 }

mbus4BVIF2E		OBJECT-TYPE
			SYNTAX	INTEGER
			ACCESS	read-only
			STATUS	current
	DESCRIPTION ""
			::= { mbus4B 98 }

mbus4BValue2E		OBJECT-TYPE
			SYNTAX	INTEGER
			ACCESS	read-only
			STATUS	current
	DESCRIPTION ""
			::= { mbus4B 99 }

mbus4BVIF2F		OBJECT-TYPE
			SYNTAX	INTEGER
			ACCESS	read-only
			STATUS	current
	DESCRIPTION ""
			::= { mbus4B 100 }

mbus4BValue2F		OBJECT-TYPE
			SYNTAX	INTEGER
			ACCESS	read-only
			STATUS	current
	DESCRIPTION ""
			::= { mbus4B 101 }

mbus4C			OBJECT IDENTIFIER ::= { mbus 76 }

mbus4CIdNumber		OBJECT-TYPE
			SYNTAX	Gauge
			ACCESS	read-only
			STATUS	current
	DESCRIPTION ""
			::= { mbus4C 1 }

mbus4CManufacturer	OBJECT-TYPE
			SYNTAX	Gauge
			ACCESS	read-only
			STATUS	current
	DESCRIPTION ""
			::= { mbus4C 2 }

mbus4CVersion		OBJECT-TYPE
			SYNTAX	Gauge
			ACCESS	read-only
			STATUS	current
	DESCRIPTION ""
			::= { mbus4C 3 }

mbus4CMedium		OBJECT-TYPE
			SYNTAX	Gauge
			ACCESS	read-only
			STATUS	current
	DESCRIPTION ""
			::= { mbus4C 4 }

mbus4CStatus		OBJECT-TYPE
			SYNTAX	Gauge
			ACCESS	read-only
			STATUS	current
	DESCRIPTION ""
			::= { mbus4C 5 }

mbus4CVIF00		OBJECT-TYPE
			SYNTAX	INTEGER
			ACCESS	read-only
			STATUS	current
	DESCRIPTION ""
			::= { mbus4C 6 }

mbus4CValue00		OBJECT-TYPE
			SYNTAX	INTEGER
			ACCESS	read-only
			STATUS	current
	DESCRIPTION ""
			::= { mbus4C 7 }

mbus4CVIF01		OBJECT-TYPE
			SYNTAX	INTEGER
			ACCESS	read-only
			STATUS	current
	DESCRIPTION ""
			::= { mbus4C 8 }

mbus4CValue01		OBJECT-TYPE
			SYNTAX	INTEGER
			ACCESS	read-only
			STATUS	current
	DESCRIPTION ""
			::= { mbus4C 9 }

mbus4CVIF02		OBJECT-TYPE
			SYNTAX	INTEGER
			ACCESS	read-only
			STATUS	current
	DESCRIPTION ""
			::= { mbus4C 10 }

mbus4CValue02		OBJECT-TYPE
			SYNTAX	INTEGER
			ACCESS	read-only
			STATUS	current
	DESCRIPTION ""
			::= { mbus4C 11 }

mbus4CVIF03		OBJECT-TYPE
			SYNTAX	INTEGER
			ACCESS	read-only
			STATUS	current
	DESCRIPTION ""
			::= { mbus4C 12 }

mbus4CValue03		OBJECT-TYPE
			SYNTAX	INTEGER
			ACCESS	read-only
			STATUS	current
	DESCRIPTION ""
			::= { mbus4C 13 }

mbus4CVIF04		OBJECT-TYPE
			SYNTAX	INTEGER
			ACCESS	read-only
			STATUS	current
	DESCRIPTION ""
			::= { mbus4C 14 }

mbus4CValue04		OBJECT-TYPE
			SYNTAX	INTEGER
			ACCESS	read-only
			STATUS	current
	DESCRIPTION ""
			::= { mbus4C 15 }

mbus4CVIF05		OBJECT-TYPE
			SYNTAX	INTEGER
			ACCESS	read-only
			STATUS	current
	DESCRIPTION ""
			::= { mbus4C 16 }

mbus4CValue05		OBJECT-TYPE
			SYNTAX	INTEGER
			ACCESS	read-only
			STATUS	current
	DESCRIPTION ""
			::= { mbus4C 17 }

mbus4CVIF06		OBJECT-TYPE
			SYNTAX	INTEGER
			ACCESS	read-only
			STATUS	current
	DESCRIPTION ""
			::= { mbus4C 18 }

mbus4CValue06		OBJECT-TYPE
			SYNTAX	INTEGER
			ACCESS	read-only
			STATUS	current
	DESCRIPTION ""
			::= { mbus4C 19 }

mbus4CVIF07		OBJECT-TYPE
			SYNTAX	INTEGER
			ACCESS	read-only
			STATUS	current
	DESCRIPTION ""
			::= { mbus4C 20 }

mbus4CValue07		OBJECT-TYPE
			SYNTAX	INTEGER
			ACCESS	read-only
			STATUS	current
	DESCRIPTION ""
			::= { mbus4C 21 }

mbus4CVIF08		OBJECT-TYPE
			SYNTAX	INTEGER
			ACCESS	read-only
			STATUS	current
	DESCRIPTION ""
			::= { mbus4C 22 }

mbus4CValue08		OBJECT-TYPE
			SYNTAX	INTEGER
			ACCESS	read-only
			STATUS	current
	DESCRIPTION ""
			::= { mbus4C 23 }

mbus4CVIF09		OBJECT-TYPE
			SYNTAX	INTEGER
			ACCESS	read-only
			STATUS	current
	DESCRIPTION ""
			::= { mbus4C 24 }

mbus4CValue09		OBJECT-TYPE
			SYNTAX	INTEGER
			ACCESS	read-only
			STATUS	current
	DESCRIPTION ""
			::= { mbus4C 25 }

mbus4CVIF0A		OBJECT-TYPE
			SYNTAX	INTEGER
			ACCESS	read-only
			STATUS	current
	DESCRIPTION ""
			::= { mbus4C 26 }

mbus4CValue0A		OBJECT-TYPE
			SYNTAX	INTEGER
			ACCESS	read-only
			STATUS	current
	DESCRIPTION ""
			::= { mbus4C 27 }

mbus4CVIF0B		OBJECT-TYPE
			SYNTAX	INTEGER
			ACCESS	read-only
			STATUS	current
	DESCRIPTION ""
			::= { mbus4C 28 }

mbus4CValue0B		OBJECT-TYPE
			SYNTAX	INTEGER
			ACCESS	read-only
			STATUS	current
	DESCRIPTION ""
			::= { mbus4C 29 }

mbus4CVIF0C		OBJECT-TYPE
			SYNTAX	INTEGER
			ACCESS	read-only
			STATUS	current
	DESCRIPTION ""
			::= { mbus4C 30 }

mbus4CValue0C		OBJECT-TYPE
			SYNTAX	INTEGER
			ACCESS	read-only
			STATUS	current
	DESCRIPTION ""
			::= { mbus4C 31 }

mbus4CVIF0D		OBJECT-TYPE
			SYNTAX	INTEGER
			ACCESS	read-only
			STATUS	current
	DESCRIPTION ""
			::= { mbus4C 32 }

mbus4CValue0D		OBJECT-TYPE
			SYNTAX	INTEGER
			ACCESS	read-only
			STATUS	current
	DESCRIPTION ""
			::= { mbus4C 33 }

mbus4CVIF0E		OBJECT-TYPE
			SYNTAX	INTEGER
			ACCESS	read-only
			STATUS	current
	DESCRIPTION ""
			::= { mbus4C 34 }

mbus4CValue0E		OBJECT-TYPE
			SYNTAX	INTEGER
			ACCESS	read-only
			STATUS	current
	DESCRIPTION ""
			::= { mbus4C 35 }

mbus4CVIF0F		OBJECT-TYPE
			SYNTAX	INTEGER
			ACCESS	read-only
			STATUS	current
	DESCRIPTION ""
			::= { mbus4C 36 }

mbus4CValue0F		OBJECT-TYPE
			SYNTAX	INTEGER
			ACCESS	read-only
			STATUS	current
	DESCRIPTION ""
			::= { mbus4C 37 }

mbus4CVIF10		OBJECT-TYPE
			SYNTAX	INTEGER
			ACCESS	read-only
			STATUS	current
	DESCRIPTION ""
			::= { mbus4C 38 }

mbus4CValue10		OBJECT-TYPE
			SYNTAX	INTEGER
			ACCESS	read-only
			STATUS	current
	DESCRIPTION ""
			::= { mbus4C 39 }

mbus4CVIF11		OBJECT-TYPE
			SYNTAX	INTEGER
			ACCESS	read-only
			STATUS	current
	DESCRIPTION ""
			::= { mbus4C 40 }

mbus4CValue11		OBJECT-TYPE
			SYNTAX	INTEGER
			ACCESS	read-only
			STATUS	current
	DESCRIPTION ""
			::= { mbus4C 41 }

mbus4CVIF12		OBJECT-TYPE
			SYNTAX	INTEGER
			ACCESS	read-only
			STATUS	current
	DESCRIPTION ""
			::= { mbus4C 42 }

mbus4CValue12		OBJECT-TYPE
			SYNTAX	INTEGER
			ACCESS	read-only
			STATUS	current
	DESCRIPTION ""
			::= { mbus4C 43 }

mbus4CVIF13		OBJECT-TYPE
			SYNTAX	INTEGER
			ACCESS	read-only
			STATUS	current
	DESCRIPTION ""
			::= { mbus4C 44 }

mbus4CValue13		OBJECT-TYPE
			SYNTAX	INTEGER
			ACCESS	read-only
			STATUS	current
	DESCRIPTION ""
			::= { mbus4C 45 }

mbus4CVIF14		OBJECT-TYPE
			SYNTAX	INTEGER
			ACCESS	read-only
			STATUS	current
	DESCRIPTION ""
			::= { mbus4C 46 }

mbus4CValue14		OBJECT-TYPE
			SYNTAX	INTEGER
			ACCESS	read-only
			STATUS	current
	DESCRIPTION ""
			::= { mbus4C 47 }

mbus4CVIF15		OBJECT-TYPE
			SYNTAX	INTEGER
			ACCESS	read-only
			STATUS	current
	DESCRIPTION ""
			::= { mbus4C 48 }

mbus4CValue15		OBJECT-TYPE
			SYNTAX	INTEGER
			ACCESS	read-only
			STATUS	current
	DESCRIPTION ""
			::= { mbus4C 49 }

mbus4CVIF16		OBJECT-TYPE
			SYNTAX	INTEGER
			ACCESS	read-only
			STATUS	current
	DESCRIPTION ""
			::= { mbus4C 50 }

mbus4CValue16		OBJECT-TYPE
			SYNTAX	INTEGER
			ACCESS	read-only
			STATUS	current
	DESCRIPTION ""
			::= { mbus4C 51 }

mbus4CVIF17		OBJECT-TYPE
			SYNTAX	INTEGER
			ACCESS	read-only
			STATUS	current
	DESCRIPTION ""
			::= { mbus4C 52 }

mbus4CValue17		OBJECT-TYPE
			SYNTAX	INTEGER
			ACCESS	read-only
			STATUS	current
	DESCRIPTION ""
			::= { mbus4C 53 }

mbus4CVIF18		OBJECT-TYPE
			SYNTAX	INTEGER
			ACCESS	read-only
			STATUS	current
	DESCRIPTION ""
			::= { mbus4C 54 }

mbus4CValue18		OBJECT-TYPE
			SYNTAX	INTEGER
			ACCESS	read-only
			STATUS	current
	DESCRIPTION ""
			::= { mbus4C 55 }

mbus4CVIF19		OBJECT-TYPE
			SYNTAX	INTEGER
			ACCESS	read-only
			STATUS	current
	DESCRIPTION ""
			::= { mbus4C 56 }

mbus4CValue19		OBJECT-TYPE
			SYNTAX	INTEGER
			ACCESS	read-only
			STATUS	current
	DESCRIPTION ""
			::= { mbus4C 57 }

mbus4CVIF1A		OBJECT-TYPE
			SYNTAX	INTEGER
			ACCESS	read-only
			STATUS	current
	DESCRIPTION ""
			::= { mbus4C 58 }

mbus4CValue1A		OBJECT-TYPE
			SYNTAX	INTEGER
			ACCESS	read-only
			STATUS	current
	DESCRIPTION ""
			::= { mbus4C 59 }

mbus4CVIF1B		OBJECT-TYPE
			SYNTAX	INTEGER
			ACCESS	read-only
			STATUS	current
	DESCRIPTION ""
			::= { mbus4C 60 }

mbus4CValue1B		OBJECT-TYPE
			SYNTAX	INTEGER
			ACCESS	read-only
			STATUS	current
	DESCRIPTION ""
			::= { mbus4C 61 }

mbus4CVIF1C		OBJECT-TYPE
			SYNTAX	INTEGER
			ACCESS	read-only
			STATUS	current
	DESCRIPTION ""
			::= { mbus4C 62 }

mbus4CValue1C		OBJECT-TYPE
			SYNTAX	INTEGER
			ACCESS	read-only
			STATUS	current
	DESCRIPTION ""
			::= { mbus4C 63 }

mbus4CVIF1D		OBJECT-TYPE
			SYNTAX	INTEGER
			ACCESS	read-only
			STATUS	current
	DESCRIPTION ""
			::= { mbus4C 64 }

mbus4CValue1D		OBJECT-TYPE
			SYNTAX	INTEGER
			ACCESS	read-only
			STATUS	current
	DESCRIPTION ""
			::= { mbus4C 65 }

mbus4CVIF1E		OBJECT-TYPE
			SYNTAX	INTEGER
			ACCESS	read-only
			STATUS	current
	DESCRIPTION ""
			::= { mbus4C 66 }

mbus4CValue1E		OBJECT-TYPE
			SYNTAX	INTEGER
			ACCESS	read-only
			STATUS	current
	DESCRIPTION ""
			::= { mbus4C 67 }

mbus4CVIF1F		OBJECT-TYPE
			SYNTAX	INTEGER
			ACCESS	read-only
			STATUS	current
	DESCRIPTION ""
			::= { mbus4C 68 }

mbus4CValue1F		OBJECT-TYPE
			SYNTAX	INTEGER
			ACCESS	read-only
			STATUS	current
	DESCRIPTION ""
			::= { mbus4C 69 }

mbus4CVIF20		OBJECT-TYPE
			SYNTAX	INTEGER
			ACCESS	read-only
			STATUS	current
	DESCRIPTION ""
			::= { mbus4C 70 }

mbus4CValue20		OBJECT-TYPE
			SYNTAX	INTEGER
			ACCESS	read-only
			STATUS	current
	DESCRIPTION ""
			::= { mbus4C 71 }

mbus4CVIF21		OBJECT-TYPE
			SYNTAX	INTEGER
			ACCESS	read-only
			STATUS	current
	DESCRIPTION ""
			::= { mbus4C 72 }

mbus4CValue21		OBJECT-TYPE
			SYNTAX	INTEGER
			ACCESS	read-only
			STATUS	current
	DESCRIPTION ""
			::= { mbus4C 73 }

mbus4CVIF22		OBJECT-TYPE
			SYNTAX	INTEGER
			ACCESS	read-only
			STATUS	current
	DESCRIPTION ""
			::= { mbus4C 74 }

mbus4CValue22		OBJECT-TYPE
			SYNTAX	INTEGER
			ACCESS	read-only
			STATUS	current
	DESCRIPTION ""
			::= { mbus4C 75 }

mbus4CVIF23		OBJECT-TYPE
			SYNTAX	INTEGER
			ACCESS	read-only
			STATUS	current
	DESCRIPTION ""
			::= { mbus4C 76 }

mbus4CValue23		OBJECT-TYPE
			SYNTAX	INTEGER
			ACCESS	read-only
			STATUS	current
	DESCRIPTION ""
			::= { mbus4C 77 }

mbus4CVIF24		OBJECT-TYPE
			SYNTAX	INTEGER
			ACCESS	read-only
			STATUS	current
	DESCRIPTION ""
			::= { mbus4C 78 }

mbus4CValue24		OBJECT-TYPE
			SYNTAX	INTEGER
			ACCESS	read-only
			STATUS	current
	DESCRIPTION ""
			::= { mbus4C 79 }

mbus4CVIF25		OBJECT-TYPE
			SYNTAX	INTEGER
			ACCESS	read-only
			STATUS	current
	DESCRIPTION ""
			::= { mbus4C 80 }

mbus4CValue25		OBJECT-TYPE
			SYNTAX	INTEGER
			ACCESS	read-only
			STATUS	current
	DESCRIPTION ""
			::= { mbus4C 81 }

mbus4CVIF26		OBJECT-TYPE
			SYNTAX	INTEGER
			ACCESS	read-only
			STATUS	current
	DESCRIPTION ""
			::= { mbus4C 82 }

mbus4CValue26		OBJECT-TYPE
			SYNTAX	INTEGER
			ACCESS	read-only
			STATUS	current
	DESCRIPTION ""
			::= { mbus4C 83 }

mbus4CVIF27		OBJECT-TYPE
			SYNTAX	INTEGER
			ACCESS	read-only
			STATUS	current
	DESCRIPTION ""
			::= { mbus4C 84 }

mbus4CValue27		OBJECT-TYPE
			SYNTAX	INTEGER
			ACCESS	read-only
			STATUS	current
	DESCRIPTION ""
			::= { mbus4C 85 }

mbus4CVIF28		OBJECT-TYPE
			SYNTAX	INTEGER
			ACCESS	read-only
			STATUS	current
	DESCRIPTION ""
			::= { mbus4C 86 }

mbus4CValue28		OBJECT-TYPE
			SYNTAX	INTEGER
			ACCESS	read-only
			STATUS	current
	DESCRIPTION ""
			::= { mbus4C 87 }

mbus4CVIF29		OBJECT-TYPE
			SYNTAX	INTEGER
			ACCESS	read-only
			STATUS	current
	DESCRIPTION ""
			::= { mbus4C 88 }

mbus4CValue29		OBJECT-TYPE
			SYNTAX	INTEGER
			ACCESS	read-only
			STATUS	current
	DESCRIPTION ""
			::= { mbus4C 89 }

mbus4CVIF2A		OBJECT-TYPE
			SYNTAX	INTEGER
			ACCESS	read-only
			STATUS	current
	DESCRIPTION ""
			::= { mbus4C 90 }

mbus4CValue2A		OBJECT-TYPE
			SYNTAX	INTEGER
			ACCESS	read-only
			STATUS	current
	DESCRIPTION ""
			::= { mbus4C 91 }

mbus4CVIF2B		OBJECT-TYPE
			SYNTAX	INTEGER
			ACCESS	read-only
			STATUS	current
	DESCRIPTION ""
			::= { mbus4C 92 }

mbus4CValue2B		OBJECT-TYPE
			SYNTAX	INTEGER
			ACCESS	read-only
			STATUS	current
	DESCRIPTION ""
			::= { mbus4C 93 }

mbus4CVIF2C		OBJECT-TYPE
			SYNTAX	INTEGER
			ACCESS	read-only
			STATUS	current
	DESCRIPTION ""
			::= { mbus4C 94 }

mbus4CValue2C		OBJECT-TYPE
			SYNTAX	INTEGER
			ACCESS	read-only
			STATUS	current
	DESCRIPTION ""
			::= { mbus4C 95 }

mbus4CVIF2D		OBJECT-TYPE
			SYNTAX	INTEGER
			ACCESS	read-only
			STATUS	current
	DESCRIPTION ""
			::= { mbus4C 96 }

mbus4CValue2D		OBJECT-TYPE
			SYNTAX	INTEGER
			ACCESS	read-only
			STATUS	current
	DESCRIPTION ""
			::= { mbus4C 97 }

mbus4CVIF2E		OBJECT-TYPE
			SYNTAX	INTEGER
			ACCESS	read-only
			STATUS	current
	DESCRIPTION ""
			::= { mbus4C 98 }

mbus4CValue2E		OBJECT-TYPE
			SYNTAX	INTEGER
			ACCESS	read-only
			STATUS	current
	DESCRIPTION ""
			::= { mbus4C 99 }

mbus4CVIF2F		OBJECT-TYPE
			SYNTAX	INTEGER
			ACCESS	read-only
			STATUS	current
	DESCRIPTION ""
			::= { mbus4C 100 }

mbus4CValue2F		OBJECT-TYPE
			SYNTAX	INTEGER
			ACCESS	read-only
			STATUS	current
	DESCRIPTION ""
			::= { mbus4C 101 }

mbus4D			OBJECT IDENTIFIER ::= { mbus 77 }

mbus4DIdNumber		OBJECT-TYPE
			SYNTAX	Gauge
			ACCESS	read-only
			STATUS	current
	DESCRIPTION ""
			::= { mbus4D 1 }

mbus4DManufacturer	OBJECT-TYPE
			SYNTAX	Gauge
			ACCESS	read-only
			STATUS	current
	DESCRIPTION ""
			::= { mbus4D 2 }

mbus4DVersion		OBJECT-TYPE
			SYNTAX	Gauge
			ACCESS	read-only
			STATUS	current
	DESCRIPTION ""
			::= { mbus4D 3 }

mbus4DMedium		OBJECT-TYPE
			SYNTAX	Gauge
			ACCESS	read-only
			STATUS	current
	DESCRIPTION ""
			::= { mbus4D 4 }

mbus4DStatus		OBJECT-TYPE
			SYNTAX	Gauge
			ACCESS	read-only
			STATUS	current
	DESCRIPTION ""
			::= { mbus4D 5 }

mbus4DVIF00		OBJECT-TYPE
			SYNTAX	INTEGER
			ACCESS	read-only
			STATUS	current
	DESCRIPTION ""
			::= { mbus4D 6 }

mbus4DValue00		OBJECT-TYPE
			SYNTAX	INTEGER
			ACCESS	read-only
			STATUS	current
	DESCRIPTION ""
			::= { mbus4D 7 }

mbus4DVIF01		OBJECT-TYPE
			SYNTAX	INTEGER
			ACCESS	read-only
			STATUS	current
	DESCRIPTION ""
			::= { mbus4D 8 }

mbus4DValue01		OBJECT-TYPE
			SYNTAX	INTEGER
			ACCESS	read-only
			STATUS	current
	DESCRIPTION ""
			::= { mbus4D 9 }

mbus4DVIF02		OBJECT-TYPE
			SYNTAX	INTEGER
			ACCESS	read-only
			STATUS	current
	DESCRIPTION ""
			::= { mbus4D 10 }

mbus4DValue02		OBJECT-TYPE
			SYNTAX	INTEGER
			ACCESS	read-only
			STATUS	current
	DESCRIPTION ""
			::= { mbus4D 11 }

mbus4DVIF03		OBJECT-TYPE
			SYNTAX	INTEGER
			ACCESS	read-only
			STATUS	current
	DESCRIPTION ""
			::= { mbus4D 12 }

mbus4DValue03		OBJECT-TYPE
			SYNTAX	INTEGER
			ACCESS	read-only
			STATUS	current
	DESCRIPTION ""
			::= { mbus4D 13 }

mbus4DVIF04		OBJECT-TYPE
			SYNTAX	INTEGER
			ACCESS	read-only
			STATUS	current
	DESCRIPTION ""
			::= { mbus4D 14 }

mbus4DValue04		OBJECT-TYPE
			SYNTAX	INTEGER
			ACCESS	read-only
			STATUS	current
	DESCRIPTION ""
			::= { mbus4D 15 }

mbus4DVIF05		OBJECT-TYPE
			SYNTAX	INTEGER
			ACCESS	read-only
			STATUS	current
	DESCRIPTION ""
			::= { mbus4D 16 }

mbus4DValue05		OBJECT-TYPE
			SYNTAX	INTEGER
			ACCESS	read-only
			STATUS	current
	DESCRIPTION ""
			::= { mbus4D 17 }

mbus4DVIF06		OBJECT-TYPE
			SYNTAX	INTEGER
			ACCESS	read-only
			STATUS	current
	DESCRIPTION ""
			::= { mbus4D 18 }

mbus4DValue06		OBJECT-TYPE
			SYNTAX	INTEGER
			ACCESS	read-only
			STATUS	current
	DESCRIPTION ""
			::= { mbus4D 19 }

mbus4DVIF07		OBJECT-TYPE
			SYNTAX	INTEGER
			ACCESS	read-only
			STATUS	current
	DESCRIPTION ""
			::= { mbus4D 20 }

mbus4DValue07		OBJECT-TYPE
			SYNTAX	INTEGER
			ACCESS	read-only
			STATUS	current
	DESCRIPTION ""
			::= { mbus4D 21 }

mbus4DVIF08		OBJECT-TYPE
			SYNTAX	INTEGER
			ACCESS	read-only
			STATUS	current
	DESCRIPTION ""
			::= { mbus4D 22 }

mbus4DValue08		OBJECT-TYPE
			SYNTAX	INTEGER
			ACCESS	read-only
			STATUS	current
	DESCRIPTION ""
			::= { mbus4D 23 }

mbus4DVIF09		OBJECT-TYPE
			SYNTAX	INTEGER
			ACCESS	read-only
			STATUS	current
	DESCRIPTION ""
			::= { mbus4D 24 }

mbus4DValue09		OBJECT-TYPE
			SYNTAX	INTEGER
			ACCESS	read-only
			STATUS	current
	DESCRIPTION ""
			::= { mbus4D 25 }

mbus4DVIF0A		OBJECT-TYPE
			SYNTAX	INTEGER
			ACCESS	read-only
			STATUS	current
	DESCRIPTION ""
			::= { mbus4D 26 }

mbus4DValue0A		OBJECT-TYPE
			SYNTAX	INTEGER
			ACCESS	read-only
			STATUS	current
	DESCRIPTION ""
			::= { mbus4D 27 }

mbus4DVIF0B		OBJECT-TYPE
			SYNTAX	INTEGER
			ACCESS	read-only
			STATUS	current
	DESCRIPTION ""
			::= { mbus4D 28 }

mbus4DValue0B		OBJECT-TYPE
			SYNTAX	INTEGER
			ACCESS	read-only
			STATUS	current
	DESCRIPTION ""
			::= { mbus4D 29 }

mbus4DVIF0C		OBJECT-TYPE
			SYNTAX	INTEGER
			ACCESS	read-only
			STATUS	current
	DESCRIPTION ""
			::= { mbus4D 30 }

mbus4DValue0C		OBJECT-TYPE
			SYNTAX	INTEGER
			ACCESS	read-only
			STATUS	current
	DESCRIPTION ""
			::= { mbus4D 31 }

mbus4DVIF0D		OBJECT-TYPE
			SYNTAX	INTEGER
			ACCESS	read-only
			STATUS	current
	DESCRIPTION ""
			::= { mbus4D 32 }

mbus4DValue0D		OBJECT-TYPE
			SYNTAX	INTEGER
			ACCESS	read-only
			STATUS	current
	DESCRIPTION ""
			::= { mbus4D 33 }

mbus4DVIF0E		OBJECT-TYPE
			SYNTAX	INTEGER
			ACCESS	read-only
			STATUS	current
	DESCRIPTION ""
			::= { mbus4D 34 }

mbus4DValue0E		OBJECT-TYPE
			SYNTAX	INTEGER
			ACCESS	read-only
			STATUS	current
	DESCRIPTION ""
			::= { mbus4D 35 }

mbus4DVIF0F		OBJECT-TYPE
			SYNTAX	INTEGER
			ACCESS	read-only
			STATUS	current
	DESCRIPTION ""
			::= { mbus4D 36 }

mbus4DValue0F		OBJECT-TYPE
			SYNTAX	INTEGER
			ACCESS	read-only
			STATUS	current
	DESCRIPTION ""
			::= { mbus4D 37 }

mbus4DVIF10		OBJECT-TYPE
			SYNTAX	INTEGER
			ACCESS	read-only
			STATUS	current
	DESCRIPTION ""
			::= { mbus4D 38 }

mbus4DValue10		OBJECT-TYPE
			SYNTAX	INTEGER
			ACCESS	read-only
			STATUS	current
	DESCRIPTION ""
			::= { mbus4D 39 }

mbus4DVIF11		OBJECT-TYPE
			SYNTAX	INTEGER
			ACCESS	read-only
			STATUS	current
	DESCRIPTION ""
			::= { mbus4D 40 }

mbus4DValue11		OBJECT-TYPE
			SYNTAX	INTEGER
			ACCESS	read-only
			STATUS	current
	DESCRIPTION ""
			::= { mbus4D 41 }

mbus4DVIF12		OBJECT-TYPE
			SYNTAX	INTEGER
			ACCESS	read-only
			STATUS	current
	DESCRIPTION ""
			::= { mbus4D 42 }

mbus4DValue12		OBJECT-TYPE
			SYNTAX	INTEGER
			ACCESS	read-only
			STATUS	current
	DESCRIPTION ""
			::= { mbus4D 43 }

mbus4DVIF13		OBJECT-TYPE
			SYNTAX	INTEGER
			ACCESS	read-only
			STATUS	current
	DESCRIPTION ""
			::= { mbus4D 44 }

mbus4DValue13		OBJECT-TYPE
			SYNTAX	INTEGER
			ACCESS	read-only
			STATUS	current
	DESCRIPTION ""
			::= { mbus4D 45 }

mbus4DVIF14		OBJECT-TYPE
			SYNTAX	INTEGER
			ACCESS	read-only
			STATUS	current
	DESCRIPTION ""
			::= { mbus4D 46 }

mbus4DValue14		OBJECT-TYPE
			SYNTAX	INTEGER
			ACCESS	read-only
			STATUS	current
	DESCRIPTION ""
			::= { mbus4D 47 }

mbus4DVIF15		OBJECT-TYPE
			SYNTAX	INTEGER
			ACCESS	read-only
			STATUS	current
	DESCRIPTION ""
			::= { mbus4D 48 }

mbus4DValue15		OBJECT-TYPE
			SYNTAX	INTEGER
			ACCESS	read-only
			STATUS	current
	DESCRIPTION ""
			::= { mbus4D 49 }

mbus4DVIF16		OBJECT-TYPE
			SYNTAX	INTEGER
			ACCESS	read-only
			STATUS	current
	DESCRIPTION ""
			::= { mbus4D 50 }

mbus4DValue16		OBJECT-TYPE
			SYNTAX	INTEGER
			ACCESS	read-only
			STATUS	current
	DESCRIPTION ""
			::= { mbus4D 51 }

mbus4DVIF17		OBJECT-TYPE
			SYNTAX	INTEGER
			ACCESS	read-only
			STATUS	current
	DESCRIPTION ""
			::= { mbus4D 52 }

mbus4DValue17		OBJECT-TYPE
			SYNTAX	INTEGER
			ACCESS	read-only
			STATUS	current
	DESCRIPTION ""
			::= { mbus4D 53 }

mbus4DVIF18		OBJECT-TYPE
			SYNTAX	INTEGER
			ACCESS	read-only
			STATUS	current
	DESCRIPTION ""
			::= { mbus4D 54 }

mbus4DValue18		OBJECT-TYPE
			SYNTAX	INTEGER
			ACCESS	read-only
			STATUS	current
	DESCRIPTION ""
			::= { mbus4D 55 }

mbus4DVIF19		OBJECT-TYPE
			SYNTAX	INTEGER
			ACCESS	read-only
			STATUS	current
	DESCRIPTION ""
			::= { mbus4D 56 }

mbus4DValue19		OBJECT-TYPE
			SYNTAX	INTEGER
			ACCESS	read-only
			STATUS	current
	DESCRIPTION ""
			::= { mbus4D 57 }

mbus4DVIF1A		OBJECT-TYPE
			SYNTAX	INTEGER
			ACCESS	read-only
			STATUS	current
	DESCRIPTION ""
			::= { mbus4D 58 }

mbus4DValue1A		OBJECT-TYPE
			SYNTAX	INTEGER
			ACCESS	read-only
			STATUS	current
	DESCRIPTION ""
			::= { mbus4D 59 }

mbus4DVIF1B		OBJECT-TYPE
			SYNTAX	INTEGER
			ACCESS	read-only
			STATUS	current
	DESCRIPTION ""
			::= { mbus4D 60 }

mbus4DValue1B		OBJECT-TYPE
			SYNTAX	INTEGER
			ACCESS	read-only
			STATUS	current
	DESCRIPTION ""
			::= { mbus4D 61 }

mbus4DVIF1C		OBJECT-TYPE
			SYNTAX	INTEGER
			ACCESS	read-only
			STATUS	current
	DESCRIPTION ""
			::= { mbus4D 62 }

mbus4DValue1C		OBJECT-TYPE
			SYNTAX	INTEGER
			ACCESS	read-only
			STATUS	current
	DESCRIPTION ""
			::= { mbus4D 63 }

mbus4DVIF1D		OBJECT-TYPE
			SYNTAX	INTEGER
			ACCESS	read-only
			STATUS	current
	DESCRIPTION ""
			::= { mbus4D 64 }

mbus4DValue1D		OBJECT-TYPE
			SYNTAX	INTEGER
			ACCESS	read-only
			STATUS	current
	DESCRIPTION ""
			::= { mbus4D 65 }

mbus4DVIF1E		OBJECT-TYPE
			SYNTAX	INTEGER
			ACCESS	read-only
			STATUS	current
	DESCRIPTION ""
			::= { mbus4D 66 }

mbus4DValue1E		OBJECT-TYPE
			SYNTAX	INTEGER
			ACCESS	read-only
			STATUS	current
	DESCRIPTION ""
			::= { mbus4D 67 }

mbus4DVIF1F		OBJECT-TYPE
			SYNTAX	INTEGER
			ACCESS	read-only
			STATUS	current
	DESCRIPTION ""
			::= { mbus4D 68 }

mbus4DValue1F		OBJECT-TYPE
			SYNTAX	INTEGER
			ACCESS	read-only
			STATUS	current
	DESCRIPTION ""
			::= { mbus4D 69 }

mbus4DVIF20		OBJECT-TYPE
			SYNTAX	INTEGER
			ACCESS	read-only
			STATUS	current
	DESCRIPTION ""
			::= { mbus4D 70 }

mbus4DValue20		OBJECT-TYPE
			SYNTAX	INTEGER
			ACCESS	read-only
			STATUS	current
	DESCRIPTION ""
			::= { mbus4D 71 }

mbus4DVIF21		OBJECT-TYPE
			SYNTAX	INTEGER
			ACCESS	read-only
			STATUS	current
	DESCRIPTION ""
			::= { mbus4D 72 }

mbus4DValue21		OBJECT-TYPE
			SYNTAX	INTEGER
			ACCESS	read-only
			STATUS	current
	DESCRIPTION ""
			::= { mbus4D 73 }

mbus4DVIF22		OBJECT-TYPE
			SYNTAX	INTEGER
			ACCESS	read-only
			STATUS	current
	DESCRIPTION ""
			::= { mbus4D 74 }

mbus4DValue22		OBJECT-TYPE
			SYNTAX	INTEGER
			ACCESS	read-only
			STATUS	current
	DESCRIPTION ""
			::= { mbus4D 75 }

mbus4DVIF23		OBJECT-TYPE
			SYNTAX	INTEGER
			ACCESS	read-only
			STATUS	current
	DESCRIPTION ""
			::= { mbus4D 76 }

mbus4DValue23		OBJECT-TYPE
			SYNTAX	INTEGER
			ACCESS	read-only
			STATUS	current
	DESCRIPTION ""
			::= { mbus4D 77 }

mbus4DVIF24		OBJECT-TYPE
			SYNTAX	INTEGER
			ACCESS	read-only
			STATUS	current
	DESCRIPTION ""
			::= { mbus4D 78 }

mbus4DValue24		OBJECT-TYPE
			SYNTAX	INTEGER
			ACCESS	read-only
			STATUS	current
	DESCRIPTION ""
			::= { mbus4D 79 }

mbus4DVIF25		OBJECT-TYPE
			SYNTAX	INTEGER
			ACCESS	read-only
			STATUS	current
	DESCRIPTION ""
			::= { mbus4D 80 }

mbus4DValue25		OBJECT-TYPE
			SYNTAX	INTEGER
			ACCESS	read-only
			STATUS	current
	DESCRIPTION ""
			::= { mbus4D 81 }

mbus4DVIF26		OBJECT-TYPE
			SYNTAX	INTEGER
			ACCESS	read-only
			STATUS	current
	DESCRIPTION ""
			::= { mbus4D 82 }

mbus4DValue26		OBJECT-TYPE
			SYNTAX	INTEGER
			ACCESS	read-only
			STATUS	current
	DESCRIPTION ""
			::= { mbus4D 83 }

mbus4DVIF27		OBJECT-TYPE
			SYNTAX	INTEGER
			ACCESS	read-only
			STATUS	current
	DESCRIPTION ""
			::= { mbus4D 84 }

mbus4DValue27		OBJECT-TYPE
			SYNTAX	INTEGER
			ACCESS	read-only
			STATUS	current
	DESCRIPTION ""
			::= { mbus4D 85 }

mbus4DVIF28		OBJECT-TYPE
			SYNTAX	INTEGER
			ACCESS	read-only
			STATUS	current
	DESCRIPTION ""
			::= { mbus4D 86 }

mbus4DValue28		OBJECT-TYPE
			SYNTAX	INTEGER
			ACCESS	read-only
			STATUS	current
	DESCRIPTION ""
			::= { mbus4D 87 }

mbus4DVIF29		OBJECT-TYPE
			SYNTAX	INTEGER
			ACCESS	read-only
			STATUS	current
	DESCRIPTION ""
			::= { mbus4D 88 }

mbus4DValue29		OBJECT-TYPE
			SYNTAX	INTEGER
			ACCESS	read-only
			STATUS	current
	DESCRIPTION ""
			::= { mbus4D 89 }

mbus4DVIF2A		OBJECT-TYPE
			SYNTAX	INTEGER
			ACCESS	read-only
			STATUS	current
	DESCRIPTION ""
			::= { mbus4D 90 }

mbus4DValue2A		OBJECT-TYPE
			SYNTAX	INTEGER
			ACCESS	read-only
			STATUS	current
	DESCRIPTION ""
			::= { mbus4D 91 }

mbus4DVIF2B		OBJECT-TYPE
			SYNTAX	INTEGER
			ACCESS	read-only
			STATUS	current
	DESCRIPTION ""
			::= { mbus4D 92 }

mbus4DValue2B		OBJECT-TYPE
			SYNTAX	INTEGER
			ACCESS	read-only
			STATUS	current
	DESCRIPTION ""
			::= { mbus4D 93 }

mbus4DVIF2C		OBJECT-TYPE
			SYNTAX	INTEGER
			ACCESS	read-only
			STATUS	current
	DESCRIPTION ""
			::= { mbus4D 94 }

mbus4DValue2C		OBJECT-TYPE
			SYNTAX	INTEGER
			ACCESS	read-only
			STATUS	current
	DESCRIPTION ""
			::= { mbus4D 95 }

mbus4DVIF2D		OBJECT-TYPE
			SYNTAX	INTEGER
			ACCESS	read-only
			STATUS	current
	DESCRIPTION ""
			::= { mbus4D 96 }

mbus4DValue2D		OBJECT-TYPE
			SYNTAX	INTEGER
			ACCESS	read-only
			STATUS	current
	DESCRIPTION ""
			::= { mbus4D 97 }

mbus4DVIF2E		OBJECT-TYPE
			SYNTAX	INTEGER
			ACCESS	read-only
			STATUS	current
	DESCRIPTION ""
			::= { mbus4D 98 }

mbus4DValue2E		OBJECT-TYPE
			SYNTAX	INTEGER
			ACCESS	read-only
			STATUS	current
	DESCRIPTION ""
			::= { mbus4D 99 }

mbus4DVIF2F		OBJECT-TYPE
			SYNTAX	INTEGER
			ACCESS	read-only
			STATUS	current
	DESCRIPTION ""
			::= { mbus4D 100 }

mbus4DValue2F		OBJECT-TYPE
			SYNTAX	INTEGER
			ACCESS	read-only
			STATUS	current
	DESCRIPTION ""
			::= { mbus4D 101 }

mbus4E			OBJECT IDENTIFIER ::= { mbus 78 }

mbus4EIdNumber		OBJECT-TYPE
			SYNTAX	Gauge
			ACCESS	read-only
			STATUS	current
	DESCRIPTION ""
			::= { mbus4E 1 }

mbus4EManufacturer	OBJECT-TYPE
			SYNTAX	Gauge
			ACCESS	read-only
			STATUS	current
	DESCRIPTION ""
			::= { mbus4E 2 }

mbus4EVersion		OBJECT-TYPE
			SYNTAX	Gauge
			ACCESS	read-only
			STATUS	current
	DESCRIPTION ""
			::= { mbus4E 3 }

mbus4EMedium		OBJECT-TYPE
			SYNTAX	Gauge
			ACCESS	read-only
			STATUS	current
	DESCRIPTION ""
			::= { mbus4E 4 }

mbus4EStatus		OBJECT-TYPE
			SYNTAX	Gauge
			ACCESS	read-only
			STATUS	current
	DESCRIPTION ""
			::= { mbus4E 5 }

mbus4EVIF00		OBJECT-TYPE
			SYNTAX	INTEGER
			ACCESS	read-only
			STATUS	current
	DESCRIPTION ""
			::= { mbus4E 6 }

mbus4EValue00		OBJECT-TYPE
			SYNTAX	INTEGER
			ACCESS	read-only
			STATUS	current
	DESCRIPTION ""
			::= { mbus4E 7 }

mbus4EVIF01		OBJECT-TYPE
			SYNTAX	INTEGER
			ACCESS	read-only
			STATUS	current
	DESCRIPTION ""
			::= { mbus4E 8 }

mbus4EValue01		OBJECT-TYPE
			SYNTAX	INTEGER
			ACCESS	read-only
			STATUS	current
	DESCRIPTION ""
			::= { mbus4E 9 }

mbus4EVIF02		OBJECT-TYPE
			SYNTAX	INTEGER
			ACCESS	read-only
			STATUS	current
	DESCRIPTION ""
			::= { mbus4E 10 }

mbus4EValue02		OBJECT-TYPE
			SYNTAX	INTEGER
			ACCESS	read-only
			STATUS	current
	DESCRIPTION ""
			::= { mbus4E 11 }

mbus4EVIF03		OBJECT-TYPE
			SYNTAX	INTEGER
			ACCESS	read-only
			STATUS	current
	DESCRIPTION ""
			::= { mbus4E 12 }

mbus4EValue03		OBJECT-TYPE
			SYNTAX	INTEGER
			ACCESS	read-only
			STATUS	current
	DESCRIPTION ""
			::= { mbus4E 13 }

mbus4EVIF04		OBJECT-TYPE
			SYNTAX	INTEGER
			ACCESS	read-only
			STATUS	current
	DESCRIPTION ""
			::= { mbus4E 14 }

mbus4EValue04		OBJECT-TYPE
			SYNTAX	INTEGER
			ACCESS	read-only
			STATUS	current
	DESCRIPTION ""
			::= { mbus4E 15 }

mbus4EVIF05		OBJECT-TYPE
			SYNTAX	INTEGER
			ACCESS	read-only
			STATUS	current
	DESCRIPTION ""
			::= { mbus4E 16 }

mbus4EValue05		OBJECT-TYPE
			SYNTAX	INTEGER
			ACCESS	read-only
			STATUS	current
	DESCRIPTION ""
			::= { mbus4E 17 }

mbus4EVIF06		OBJECT-TYPE
			SYNTAX	INTEGER
			ACCESS	read-only
			STATUS	current
	DESCRIPTION ""
			::= { mbus4E 18 }

mbus4EValue06		OBJECT-TYPE
			SYNTAX	INTEGER
			ACCESS	read-only
			STATUS	current
	DESCRIPTION ""
			::= { mbus4E 19 }

mbus4EVIF07		OBJECT-TYPE
			SYNTAX	INTEGER
			ACCESS	read-only
			STATUS	current
	DESCRIPTION ""
			::= { mbus4E 20 }

mbus4EValue07		OBJECT-TYPE
			SYNTAX	INTEGER
			ACCESS	read-only
			STATUS	current
	DESCRIPTION ""
			::= { mbus4E 21 }

mbus4EVIF08		OBJECT-TYPE
			SYNTAX	INTEGER
			ACCESS	read-only
			STATUS	current
	DESCRIPTION ""
			::= { mbus4E 22 }

mbus4EValue08		OBJECT-TYPE
			SYNTAX	INTEGER
			ACCESS	read-only
			STATUS	current
	DESCRIPTION ""
			::= { mbus4E 23 }

mbus4EVIF09		OBJECT-TYPE
			SYNTAX	INTEGER
			ACCESS	read-only
			STATUS	current
	DESCRIPTION ""
			::= { mbus4E 24 }

mbus4EValue09		OBJECT-TYPE
			SYNTAX	INTEGER
			ACCESS	read-only
			STATUS	current
	DESCRIPTION ""
			::= { mbus4E 25 }

mbus4EVIF0A		OBJECT-TYPE
			SYNTAX	INTEGER
			ACCESS	read-only
			STATUS	current
	DESCRIPTION ""
			::= { mbus4E 26 }

mbus4EValue0A		OBJECT-TYPE
			SYNTAX	INTEGER
			ACCESS	read-only
			STATUS	current
	DESCRIPTION ""
			::= { mbus4E 27 }

mbus4EVIF0B		OBJECT-TYPE
			SYNTAX	INTEGER
			ACCESS	read-only
			STATUS	current
	DESCRIPTION ""
			::= { mbus4E 28 }

mbus4EValue0B		OBJECT-TYPE
			SYNTAX	INTEGER
			ACCESS	read-only
			STATUS	current
	DESCRIPTION ""
			::= { mbus4E 29 }

mbus4EVIF0C		OBJECT-TYPE
			SYNTAX	INTEGER
			ACCESS	read-only
			STATUS	current
	DESCRIPTION ""
			::= { mbus4E 30 }

mbus4EValue0C		OBJECT-TYPE
			SYNTAX	INTEGER
			ACCESS	read-only
			STATUS	current
	DESCRIPTION ""
			::= { mbus4E 31 }

mbus4EVIF0D		OBJECT-TYPE
			SYNTAX	INTEGER
			ACCESS	read-only
			STATUS	current
	DESCRIPTION ""
			::= { mbus4E 32 }

mbus4EValue0D		OBJECT-TYPE
			SYNTAX	INTEGER
			ACCESS	read-only
			STATUS	current
	DESCRIPTION ""
			::= { mbus4E 33 }

mbus4EVIF0E		OBJECT-TYPE
			SYNTAX	INTEGER
			ACCESS	read-only
			STATUS	current
	DESCRIPTION ""
			::= { mbus4E 34 }

mbus4EValue0E		OBJECT-TYPE
			SYNTAX	INTEGER
			ACCESS	read-only
			STATUS	current
	DESCRIPTION ""
			::= { mbus4E 35 }

mbus4EVIF0F		OBJECT-TYPE
			SYNTAX	INTEGER
			ACCESS	read-only
			STATUS	current
	DESCRIPTION ""
			::= { mbus4E 36 }

mbus4EValue0F		OBJECT-TYPE
			SYNTAX	INTEGER
			ACCESS	read-only
			STATUS	current
	DESCRIPTION ""
			::= { mbus4E 37 }

mbus4EVIF10		OBJECT-TYPE
			SYNTAX	INTEGER
			ACCESS	read-only
			STATUS	current
	DESCRIPTION ""
			::= { mbus4E 38 }

mbus4EValue10		OBJECT-TYPE
			SYNTAX	INTEGER
			ACCESS	read-only
			STATUS	current
	DESCRIPTION ""
			::= { mbus4E 39 }

mbus4EVIF11		OBJECT-TYPE
			SYNTAX	INTEGER
			ACCESS	read-only
			STATUS	current
	DESCRIPTION ""
			::= { mbus4E 40 }

mbus4EValue11		OBJECT-TYPE
			SYNTAX	INTEGER
			ACCESS	read-only
			STATUS	current
	DESCRIPTION ""
			::= { mbus4E 41 }

mbus4EVIF12		OBJECT-TYPE
			SYNTAX	INTEGER
			ACCESS	read-only
			STATUS	current
	DESCRIPTION ""
			::= { mbus4E 42 }

mbus4EValue12		OBJECT-TYPE
			SYNTAX	INTEGER
			ACCESS	read-only
			STATUS	current
	DESCRIPTION ""
			::= { mbus4E 43 }

mbus4EVIF13		OBJECT-TYPE
			SYNTAX	INTEGER
			ACCESS	read-only
			STATUS	current
	DESCRIPTION ""
			::= { mbus4E 44 }

mbus4EValue13		OBJECT-TYPE
			SYNTAX	INTEGER
			ACCESS	read-only
			STATUS	current
	DESCRIPTION ""
			::= { mbus4E 45 }

mbus4EVIF14		OBJECT-TYPE
			SYNTAX	INTEGER
			ACCESS	read-only
			STATUS	current
	DESCRIPTION ""
			::= { mbus4E 46 }

mbus4EValue14		OBJECT-TYPE
			SYNTAX	INTEGER
			ACCESS	read-only
			STATUS	current
	DESCRIPTION ""
			::= { mbus4E 47 }

mbus4EVIF15		OBJECT-TYPE
			SYNTAX	INTEGER
			ACCESS	read-only
			STATUS	current
	DESCRIPTION ""
			::= { mbus4E 48 }

mbus4EValue15		OBJECT-TYPE
			SYNTAX	INTEGER
			ACCESS	read-only
			STATUS	current
	DESCRIPTION ""
			::= { mbus4E 49 }

mbus4EVIF16		OBJECT-TYPE
			SYNTAX	INTEGER
			ACCESS	read-only
			STATUS	current
	DESCRIPTION ""
			::= { mbus4E 50 }

mbus4EValue16		OBJECT-TYPE
			SYNTAX	INTEGER
			ACCESS	read-only
			STATUS	current
	DESCRIPTION ""
			::= { mbus4E 51 }

mbus4EVIF17		OBJECT-TYPE
			SYNTAX	INTEGER
			ACCESS	read-only
			STATUS	current
	DESCRIPTION ""
			::= { mbus4E 52 }

mbus4EValue17		OBJECT-TYPE
			SYNTAX	INTEGER
			ACCESS	read-only
			STATUS	current
	DESCRIPTION ""
			::= { mbus4E 53 }

mbus4EVIF18		OBJECT-TYPE
			SYNTAX	INTEGER
			ACCESS	read-only
			STATUS	current
	DESCRIPTION ""
			::= { mbus4E 54 }

mbus4EValue18		OBJECT-TYPE
			SYNTAX	INTEGER
			ACCESS	read-only
			STATUS	current
	DESCRIPTION ""
			::= { mbus4E 55 }

mbus4EVIF19		OBJECT-TYPE
			SYNTAX	INTEGER
			ACCESS	read-only
			STATUS	current
	DESCRIPTION ""
			::= { mbus4E 56 }

mbus4EValue19		OBJECT-TYPE
			SYNTAX	INTEGER
			ACCESS	read-only
			STATUS	current
	DESCRIPTION ""
			::= { mbus4E 57 }

mbus4EVIF1A		OBJECT-TYPE
			SYNTAX	INTEGER
			ACCESS	read-only
			STATUS	current
	DESCRIPTION ""
			::= { mbus4E 58 }

mbus4EValue1A		OBJECT-TYPE
			SYNTAX	INTEGER
			ACCESS	read-only
			STATUS	current
	DESCRIPTION ""
			::= { mbus4E 59 }

mbus4EVIF1B		OBJECT-TYPE
			SYNTAX	INTEGER
			ACCESS	read-only
			STATUS	current
	DESCRIPTION ""
			::= { mbus4E 60 }

mbus4EValue1B		OBJECT-TYPE
			SYNTAX	INTEGER
			ACCESS	read-only
			STATUS	current
	DESCRIPTION ""
			::= { mbus4E 61 }

mbus4EVIF1C		OBJECT-TYPE
			SYNTAX	INTEGER
			ACCESS	read-only
			STATUS	current
	DESCRIPTION ""
			::= { mbus4E 62 }

mbus4EValue1C		OBJECT-TYPE
			SYNTAX	INTEGER
			ACCESS	read-only
			STATUS	current
	DESCRIPTION ""
			::= { mbus4E 63 }

mbus4EVIF1D		OBJECT-TYPE
			SYNTAX	INTEGER
			ACCESS	read-only
			STATUS	current
	DESCRIPTION ""
			::= { mbus4E 64 }

mbus4EValue1D		OBJECT-TYPE
			SYNTAX	INTEGER
			ACCESS	read-only
			STATUS	current
	DESCRIPTION ""
			::= { mbus4E 65 }

mbus4EVIF1E		OBJECT-TYPE
			SYNTAX	INTEGER
			ACCESS	read-only
			STATUS	current
	DESCRIPTION ""
			::= { mbus4E 66 }

mbus4EValue1E		OBJECT-TYPE
			SYNTAX	INTEGER
			ACCESS	read-only
			STATUS	current
	DESCRIPTION ""
			::= { mbus4E 67 }

mbus4EVIF1F		OBJECT-TYPE
			SYNTAX	INTEGER
			ACCESS	read-only
			STATUS	current
	DESCRIPTION ""
			::= { mbus4E 68 }

mbus4EValue1F		OBJECT-TYPE
			SYNTAX	INTEGER
			ACCESS	read-only
			STATUS	current
	DESCRIPTION ""
			::= { mbus4E 69 }

mbus4EVIF20		OBJECT-TYPE
			SYNTAX	INTEGER
			ACCESS	read-only
			STATUS	current
	DESCRIPTION ""
			::= { mbus4E 70 }

mbus4EValue20		OBJECT-TYPE
			SYNTAX	INTEGER
			ACCESS	read-only
			STATUS	current
	DESCRIPTION ""
			::= { mbus4E 71 }

mbus4EVIF21		OBJECT-TYPE
			SYNTAX	INTEGER
			ACCESS	read-only
			STATUS	current
	DESCRIPTION ""
			::= { mbus4E 72 }

mbus4EValue21		OBJECT-TYPE
			SYNTAX	INTEGER
			ACCESS	read-only
			STATUS	current
	DESCRIPTION ""
			::= { mbus4E 73 }

mbus4EVIF22		OBJECT-TYPE
			SYNTAX	INTEGER
			ACCESS	read-only
			STATUS	current
	DESCRIPTION ""
			::= { mbus4E 74 }

mbus4EValue22		OBJECT-TYPE
			SYNTAX	INTEGER
			ACCESS	read-only
			STATUS	current
	DESCRIPTION ""
			::= { mbus4E 75 }

mbus4EVIF23		OBJECT-TYPE
			SYNTAX	INTEGER
			ACCESS	read-only
			STATUS	current
	DESCRIPTION ""
			::= { mbus4E 76 }

mbus4EValue23		OBJECT-TYPE
			SYNTAX	INTEGER
			ACCESS	read-only
			STATUS	current
	DESCRIPTION ""
			::= { mbus4E 77 }

mbus4EVIF24		OBJECT-TYPE
			SYNTAX	INTEGER
			ACCESS	read-only
			STATUS	current
	DESCRIPTION ""
			::= { mbus4E 78 }

mbus4EValue24		OBJECT-TYPE
			SYNTAX	INTEGER
			ACCESS	read-only
			STATUS	current
	DESCRIPTION ""
			::= { mbus4E 79 }

mbus4EVIF25		OBJECT-TYPE
			SYNTAX	INTEGER
			ACCESS	read-only
			STATUS	current
	DESCRIPTION ""
			::= { mbus4E 80 }

mbus4EValue25		OBJECT-TYPE
			SYNTAX	INTEGER
			ACCESS	read-only
			STATUS	current
	DESCRIPTION ""
			::= { mbus4E 81 }

mbus4EVIF26		OBJECT-TYPE
			SYNTAX	INTEGER
			ACCESS	read-only
			STATUS	current
	DESCRIPTION ""
			::= { mbus4E 82 }

mbus4EValue26		OBJECT-TYPE
			SYNTAX	INTEGER
			ACCESS	read-only
			STATUS	current
	DESCRIPTION ""
			::= { mbus4E 83 }

mbus4EVIF27		OBJECT-TYPE
			SYNTAX	INTEGER
			ACCESS	read-only
			STATUS	current
	DESCRIPTION ""
			::= { mbus4E 84 }

mbus4EValue27		OBJECT-TYPE
			SYNTAX	INTEGER
			ACCESS	read-only
			STATUS	current
	DESCRIPTION ""
			::= { mbus4E 85 }

mbus4EVIF28		OBJECT-TYPE
			SYNTAX	INTEGER
			ACCESS	read-only
			STATUS	current
	DESCRIPTION ""
			::= { mbus4E 86 }

mbus4EValue28		OBJECT-TYPE
			SYNTAX	INTEGER
			ACCESS	read-only
			STATUS	current
	DESCRIPTION ""
			::= { mbus4E 87 }

mbus4EVIF29		OBJECT-TYPE
			SYNTAX	INTEGER
			ACCESS	read-only
			STATUS	current
	DESCRIPTION ""
			::= { mbus4E 88 }

mbus4EValue29		OBJECT-TYPE
			SYNTAX	INTEGER
			ACCESS	read-only
			STATUS	current
	DESCRIPTION ""
			::= { mbus4E 89 }

mbus4EVIF2A		OBJECT-TYPE
			SYNTAX	INTEGER
			ACCESS	read-only
			STATUS	current
	DESCRIPTION ""
			::= { mbus4E 90 }

mbus4EValue2A		OBJECT-TYPE
			SYNTAX	INTEGER
			ACCESS	read-only
			STATUS	current
	DESCRIPTION ""
			::= { mbus4E 91 }

mbus4EVIF2B		OBJECT-TYPE
			SYNTAX	INTEGER
			ACCESS	read-only
			STATUS	current
	DESCRIPTION ""
			::= { mbus4E 92 }

mbus4EValue2B		OBJECT-TYPE
			SYNTAX	INTEGER
			ACCESS	read-only
			STATUS	current
	DESCRIPTION ""
			::= { mbus4E 93 }

mbus4EVIF2C		OBJECT-TYPE
			SYNTAX	INTEGER
			ACCESS	read-only
			STATUS	current
	DESCRIPTION ""
			::= { mbus4E 94 }

mbus4EValue2C		OBJECT-TYPE
			SYNTAX	INTEGER
			ACCESS	read-only
			STATUS	current
	DESCRIPTION ""
			::= { mbus4E 95 }

mbus4EVIF2D		OBJECT-TYPE
			SYNTAX	INTEGER
			ACCESS	read-only
			STATUS	current
	DESCRIPTION ""
			::= { mbus4E 96 }

mbus4EValue2D		OBJECT-TYPE
			SYNTAX	INTEGER
			ACCESS	read-only
			STATUS	current
	DESCRIPTION ""
			::= { mbus4E 97 }

mbus4EVIF2E		OBJECT-TYPE
			SYNTAX	INTEGER
			ACCESS	read-only
			STATUS	current
	DESCRIPTION ""
			::= { mbus4E 98 }

mbus4EValue2E		OBJECT-TYPE
			SYNTAX	INTEGER
			ACCESS	read-only
			STATUS	current
	DESCRIPTION ""
			::= { mbus4E 99 }

mbus4EVIF2F		OBJECT-TYPE
			SYNTAX	INTEGER
			ACCESS	read-only
			STATUS	current
	DESCRIPTION ""
			::= { mbus4E 100 }

mbus4EValue2F		OBJECT-TYPE
			SYNTAX	INTEGER
			ACCESS	read-only
			STATUS	current
	DESCRIPTION ""
			::= { mbus4E 101 }

mbus4F			OBJECT IDENTIFIER ::= { mbus 79 }

mbus4FIdNumber		OBJECT-TYPE
			SYNTAX	Gauge
			ACCESS	read-only
			STATUS	current
	DESCRIPTION ""
			::= { mbus4F 1 }

mbus4FManufacturer	OBJECT-TYPE
			SYNTAX	Gauge
			ACCESS	read-only
			STATUS	current
	DESCRIPTION ""
			::= { mbus4F 2 }

mbus4FVersion		OBJECT-TYPE
			SYNTAX	Gauge
			ACCESS	read-only
			STATUS	current
	DESCRIPTION ""
			::= { mbus4F 3 }

mbus4FMedium		OBJECT-TYPE
			SYNTAX	Gauge
			ACCESS	read-only
			STATUS	current
	DESCRIPTION ""
			::= { mbus4F 4 }

mbus4FStatus		OBJECT-TYPE
			SYNTAX	Gauge
			ACCESS	read-only
			STATUS	current
	DESCRIPTION ""
			::= { mbus4F 5 }

mbus4FVIF00		OBJECT-TYPE
			SYNTAX	INTEGER
			ACCESS	read-only
			STATUS	current
	DESCRIPTION ""
			::= { mbus4F 6 }

mbus4FValue00		OBJECT-TYPE
			SYNTAX	INTEGER
			ACCESS	read-only
			STATUS	current
	DESCRIPTION ""
			::= { mbus4F 7 }

mbus4FVIF01		OBJECT-TYPE
			SYNTAX	INTEGER
			ACCESS	read-only
			STATUS	current
	DESCRIPTION ""
			::= { mbus4F 8 }

mbus4FValue01		OBJECT-TYPE
			SYNTAX	INTEGER
			ACCESS	read-only
			STATUS	current
	DESCRIPTION ""
			::= { mbus4F 9 }

mbus4FVIF02		OBJECT-TYPE
			SYNTAX	INTEGER
			ACCESS	read-only
			STATUS	current
	DESCRIPTION ""
			::= { mbus4F 10 }

mbus4FValue02		OBJECT-TYPE
			SYNTAX	INTEGER
			ACCESS	read-only
			STATUS	current
	DESCRIPTION ""
			::= { mbus4F 11 }

mbus4FVIF03		OBJECT-TYPE
			SYNTAX	INTEGER
			ACCESS	read-only
			STATUS	current
	DESCRIPTION ""
			::= { mbus4F 12 }

mbus4FValue03		OBJECT-TYPE
			SYNTAX	INTEGER
			ACCESS	read-only
			STATUS	current
	DESCRIPTION ""
			::= { mbus4F 13 }

mbus4FVIF04		OBJECT-TYPE
			SYNTAX	INTEGER
			ACCESS	read-only
			STATUS	current
	DESCRIPTION ""
			::= { mbus4F 14 }

mbus4FValue04		OBJECT-TYPE
			SYNTAX	INTEGER
			ACCESS	read-only
			STATUS	current
	DESCRIPTION ""
			::= { mbus4F 15 }

mbus4FVIF05		OBJECT-TYPE
			SYNTAX	INTEGER
			ACCESS	read-only
			STATUS	current
	DESCRIPTION ""
			::= { mbus4F 16 }

mbus4FValue05		OBJECT-TYPE
			SYNTAX	INTEGER
			ACCESS	read-only
			STATUS	current
	DESCRIPTION ""
			::= { mbus4F 17 }

mbus4FVIF06		OBJECT-TYPE
			SYNTAX	INTEGER
			ACCESS	read-only
			STATUS	current
	DESCRIPTION ""
			::= { mbus4F 18 }

mbus4FValue06		OBJECT-TYPE
			SYNTAX	INTEGER
			ACCESS	read-only
			STATUS	current
	DESCRIPTION ""
			::= { mbus4F 19 }

mbus4FVIF07		OBJECT-TYPE
			SYNTAX	INTEGER
			ACCESS	read-only
			STATUS	current
	DESCRIPTION ""
			::= { mbus4F 20 }

mbus4FValue07		OBJECT-TYPE
			SYNTAX	INTEGER
			ACCESS	read-only
			STATUS	current
	DESCRIPTION ""
			::= { mbus4F 21 }

mbus4FVIF08		OBJECT-TYPE
			SYNTAX	INTEGER
			ACCESS	read-only
			STATUS	current
	DESCRIPTION ""
			::= { mbus4F 22 }

mbus4FValue08		OBJECT-TYPE
			SYNTAX	INTEGER
			ACCESS	read-only
			STATUS	current
	DESCRIPTION ""
			::= { mbus4F 23 }

mbus4FVIF09		OBJECT-TYPE
			SYNTAX	INTEGER
			ACCESS	read-only
			STATUS	current
	DESCRIPTION ""
			::= { mbus4F 24 }

mbus4FValue09		OBJECT-TYPE
			SYNTAX	INTEGER
			ACCESS	read-only
			STATUS	current
	DESCRIPTION ""
			::= { mbus4F 25 }

mbus4FVIF0A		OBJECT-TYPE
			SYNTAX	INTEGER
			ACCESS	read-only
			STATUS	current
	DESCRIPTION ""
			::= { mbus4F 26 }

mbus4FValue0A		OBJECT-TYPE
			SYNTAX	INTEGER
			ACCESS	read-only
			STATUS	current
	DESCRIPTION ""
			::= { mbus4F 27 }

mbus4FVIF0B		OBJECT-TYPE
			SYNTAX	INTEGER
			ACCESS	read-only
			STATUS	current
	DESCRIPTION ""
			::= { mbus4F 28 }

mbus4FValue0B		OBJECT-TYPE
			SYNTAX	INTEGER
			ACCESS	read-only
			STATUS	current
	DESCRIPTION ""
			::= { mbus4F 29 }

mbus4FVIF0C		OBJECT-TYPE
			SYNTAX	INTEGER
			ACCESS	read-only
			STATUS	current
	DESCRIPTION ""
			::= { mbus4F 30 }

mbus4FValue0C		OBJECT-TYPE
			SYNTAX	INTEGER
			ACCESS	read-only
			STATUS	current
	DESCRIPTION ""
			::= { mbus4F 31 }

mbus4FVIF0D		OBJECT-TYPE
			SYNTAX	INTEGER
			ACCESS	read-only
			STATUS	current
	DESCRIPTION ""
			::= { mbus4F 32 }

mbus4FValue0D		OBJECT-TYPE
			SYNTAX	INTEGER
			ACCESS	read-only
			STATUS	current
	DESCRIPTION ""
			::= { mbus4F 33 }

mbus4FVIF0E		OBJECT-TYPE
			SYNTAX	INTEGER
			ACCESS	read-only
			STATUS	current
	DESCRIPTION ""
			::= { mbus4F 34 }

mbus4FValue0E		OBJECT-TYPE
			SYNTAX	INTEGER
			ACCESS	read-only
			STATUS	current
	DESCRIPTION ""
			::= { mbus4F 35 }

mbus4FVIF0F		OBJECT-TYPE
			SYNTAX	INTEGER
			ACCESS	read-only
			STATUS	current
	DESCRIPTION ""
			::= { mbus4F 36 }

mbus4FValue0F		OBJECT-TYPE
			SYNTAX	INTEGER
			ACCESS	read-only
			STATUS	current
	DESCRIPTION ""
			::= { mbus4F 37 }

mbus4FVIF10		OBJECT-TYPE
			SYNTAX	INTEGER
			ACCESS	read-only
			STATUS	current
	DESCRIPTION ""
			::= { mbus4F 38 }

mbus4FValue10		OBJECT-TYPE
			SYNTAX	INTEGER
			ACCESS	read-only
			STATUS	current
	DESCRIPTION ""
			::= { mbus4F 39 }

mbus4FVIF11		OBJECT-TYPE
			SYNTAX	INTEGER
			ACCESS	read-only
			STATUS	current
	DESCRIPTION ""
			::= { mbus4F 40 }

mbus4FValue11		OBJECT-TYPE
			SYNTAX	INTEGER
			ACCESS	read-only
			STATUS	current
	DESCRIPTION ""
			::= { mbus4F 41 }

mbus4FVIF12		OBJECT-TYPE
			SYNTAX	INTEGER
			ACCESS	read-only
			STATUS	current
	DESCRIPTION ""
			::= { mbus4F 42 }

mbus4FValue12		OBJECT-TYPE
			SYNTAX	INTEGER
			ACCESS	read-only
			STATUS	current
	DESCRIPTION ""
			::= { mbus4F 43 }

mbus4FVIF13		OBJECT-TYPE
			SYNTAX	INTEGER
			ACCESS	read-only
			STATUS	current
	DESCRIPTION ""
			::= { mbus4F 44 }

mbus4FValue13		OBJECT-TYPE
			SYNTAX	INTEGER
			ACCESS	read-only
			STATUS	current
	DESCRIPTION ""
			::= { mbus4F 45 }

mbus4FVIF14		OBJECT-TYPE
			SYNTAX	INTEGER
			ACCESS	read-only
			STATUS	current
	DESCRIPTION ""
			::= { mbus4F 46 }

mbus4FValue14		OBJECT-TYPE
			SYNTAX	INTEGER
			ACCESS	read-only
			STATUS	current
	DESCRIPTION ""
			::= { mbus4F 47 }

mbus4FVIF15		OBJECT-TYPE
			SYNTAX	INTEGER
			ACCESS	read-only
			STATUS	current
	DESCRIPTION ""
			::= { mbus4F 48 }

mbus4FValue15		OBJECT-TYPE
			SYNTAX	INTEGER
			ACCESS	read-only
			STATUS	current
	DESCRIPTION ""
			::= { mbus4F 49 }

mbus4FVIF16		OBJECT-TYPE
			SYNTAX	INTEGER
			ACCESS	read-only
			STATUS	current
	DESCRIPTION ""
			::= { mbus4F 50 }

mbus4FValue16		OBJECT-TYPE
			SYNTAX	INTEGER
			ACCESS	read-only
			STATUS	current
	DESCRIPTION ""
			::= { mbus4F 51 }

mbus4FVIF17		OBJECT-TYPE
			SYNTAX	INTEGER
			ACCESS	read-only
			STATUS	current
	DESCRIPTION ""
			::= { mbus4F 52 }

mbus4FValue17		OBJECT-TYPE
			SYNTAX	INTEGER
			ACCESS	read-only
			STATUS	current
	DESCRIPTION ""
			::= { mbus4F 53 }

mbus4FVIF18		OBJECT-TYPE
			SYNTAX	INTEGER
			ACCESS	read-only
			STATUS	current
	DESCRIPTION ""
			::= { mbus4F 54 }

mbus4FValue18		OBJECT-TYPE
			SYNTAX	INTEGER
			ACCESS	read-only
			STATUS	current
	DESCRIPTION ""
			::= { mbus4F 55 }

mbus4FVIF19		OBJECT-TYPE
			SYNTAX	INTEGER
			ACCESS	read-only
			STATUS	current
	DESCRIPTION ""
			::= { mbus4F 56 }

mbus4FValue19		OBJECT-TYPE
			SYNTAX	INTEGER
			ACCESS	read-only
			STATUS	current
	DESCRIPTION ""
			::= { mbus4F 57 }

mbus4FVIF1A		OBJECT-TYPE
			SYNTAX	INTEGER
			ACCESS	read-only
			STATUS	current
	DESCRIPTION ""
			::= { mbus4F 58 }

mbus4FValue1A		OBJECT-TYPE
			SYNTAX	INTEGER
			ACCESS	read-only
			STATUS	current
	DESCRIPTION ""
			::= { mbus4F 59 }

mbus4FVIF1B		OBJECT-TYPE
			SYNTAX	INTEGER
			ACCESS	read-only
			STATUS	current
	DESCRIPTION ""
			::= { mbus4F 60 }

mbus4FValue1B		OBJECT-TYPE
			SYNTAX	INTEGER
			ACCESS	read-only
			STATUS	current
	DESCRIPTION ""
			::= { mbus4F 61 }

mbus4FVIF1C		OBJECT-TYPE
			SYNTAX	INTEGER
			ACCESS	read-only
			STATUS	current
	DESCRIPTION ""
			::= { mbus4F 62 }

mbus4FValue1C		OBJECT-TYPE
			SYNTAX	INTEGER
			ACCESS	read-only
			STATUS	current
	DESCRIPTION ""
			::= { mbus4F 63 }

mbus4FVIF1D		OBJECT-TYPE
			SYNTAX	INTEGER
			ACCESS	read-only
			STATUS	current
	DESCRIPTION ""
			::= { mbus4F 64 }

mbus4FValue1D		OBJECT-TYPE
			SYNTAX	INTEGER
			ACCESS	read-only
			STATUS	current
	DESCRIPTION ""
			::= { mbus4F 65 }

mbus4FVIF1E		OBJECT-TYPE
			SYNTAX	INTEGER
			ACCESS	read-only
			STATUS	current
	DESCRIPTION ""
			::= { mbus4F 66 }

mbus4FValue1E		OBJECT-TYPE
			SYNTAX	INTEGER
			ACCESS	read-only
			STATUS	current
	DESCRIPTION ""
			::= { mbus4F 67 }

mbus4FVIF1F		OBJECT-TYPE
			SYNTAX	INTEGER
			ACCESS	read-only
			STATUS	current
	DESCRIPTION ""
			::= { mbus4F 68 }

mbus4FValue1F		OBJECT-TYPE
			SYNTAX	INTEGER
			ACCESS	read-only
			STATUS	current
	DESCRIPTION ""
			::= { mbus4F 69 }

mbus4FVIF20		OBJECT-TYPE
			SYNTAX	INTEGER
			ACCESS	read-only
			STATUS	current
	DESCRIPTION ""
			::= { mbus4F 70 }

mbus4FValue20		OBJECT-TYPE
			SYNTAX	INTEGER
			ACCESS	read-only
			STATUS	current
	DESCRIPTION ""
			::= { mbus4F 71 }

mbus4FVIF21		OBJECT-TYPE
			SYNTAX	INTEGER
			ACCESS	read-only
			STATUS	current
	DESCRIPTION ""
			::= { mbus4F 72 }

mbus4FValue21		OBJECT-TYPE
			SYNTAX	INTEGER
			ACCESS	read-only
			STATUS	current
	DESCRIPTION ""
			::= { mbus4F 73 }

mbus4FVIF22		OBJECT-TYPE
			SYNTAX	INTEGER
			ACCESS	read-only
			STATUS	current
	DESCRIPTION ""
			::= { mbus4F 74 }

mbus4FValue22		OBJECT-TYPE
			SYNTAX	INTEGER
			ACCESS	read-only
			STATUS	current
	DESCRIPTION ""
			::= { mbus4F 75 }

mbus4FVIF23		OBJECT-TYPE
			SYNTAX	INTEGER
			ACCESS	read-only
			STATUS	current
	DESCRIPTION ""
			::= { mbus4F 76 }

mbus4FValue23		OBJECT-TYPE
			SYNTAX	INTEGER
			ACCESS	read-only
			STATUS	current
	DESCRIPTION ""
			::= { mbus4F 77 }

mbus4FVIF24		OBJECT-TYPE
			SYNTAX	INTEGER
			ACCESS	read-only
			STATUS	current
	DESCRIPTION ""
			::= { mbus4F 78 }

mbus4FValue24		OBJECT-TYPE
			SYNTAX	INTEGER
			ACCESS	read-only
			STATUS	current
	DESCRIPTION ""
			::= { mbus4F 79 }

mbus4FVIF25		OBJECT-TYPE
			SYNTAX	INTEGER
			ACCESS	read-only
			STATUS	current
	DESCRIPTION ""
			::= { mbus4F 80 }

mbus4FValue25		OBJECT-TYPE
			SYNTAX	INTEGER
			ACCESS	read-only
			STATUS	current
	DESCRIPTION ""
			::= { mbus4F 81 }

mbus4FVIF26		OBJECT-TYPE
			SYNTAX	INTEGER
			ACCESS	read-only
			STATUS	current
	DESCRIPTION ""
			::= { mbus4F 82 }

mbus4FValue26		OBJECT-TYPE
			SYNTAX	INTEGER
			ACCESS	read-only
			STATUS	current
	DESCRIPTION ""
			::= { mbus4F 83 }

mbus4FVIF27		OBJECT-TYPE
			SYNTAX	INTEGER
			ACCESS	read-only
			STATUS	current
	DESCRIPTION ""
			::= { mbus4F 84 }

mbus4FValue27		OBJECT-TYPE
			SYNTAX	INTEGER
			ACCESS	read-only
			STATUS	current
	DESCRIPTION ""
			::= { mbus4F 85 }

mbus4FVIF28		OBJECT-TYPE
			SYNTAX	INTEGER
			ACCESS	read-only
			STATUS	current
	DESCRIPTION ""
			::= { mbus4F 86 }

mbus4FValue28		OBJECT-TYPE
			SYNTAX	INTEGER
			ACCESS	read-only
			STATUS	current
	DESCRIPTION ""
			::= { mbus4F 87 }

mbus4FVIF29		OBJECT-TYPE
			SYNTAX	INTEGER
			ACCESS	read-only
			STATUS	current
	DESCRIPTION ""
			::= { mbus4F 88 }

mbus4FValue29		OBJECT-TYPE
			SYNTAX	INTEGER
			ACCESS	read-only
			STATUS	current
	DESCRIPTION ""
			::= { mbus4F 89 }

mbus4FVIF2A		OBJECT-TYPE
			SYNTAX	INTEGER
			ACCESS	read-only
			STATUS	current
	DESCRIPTION ""
			::= { mbus4F 90 }

mbus4FValue2A		OBJECT-TYPE
			SYNTAX	INTEGER
			ACCESS	read-only
			STATUS	current
	DESCRIPTION ""
			::= { mbus4F 91 }

mbus4FVIF2B		OBJECT-TYPE
			SYNTAX	INTEGER
			ACCESS	read-only
			STATUS	current
	DESCRIPTION ""
			::= { mbus4F 92 }

mbus4FValue2B		OBJECT-TYPE
			SYNTAX	INTEGER
			ACCESS	read-only
			STATUS	current
	DESCRIPTION ""
			::= { mbus4F 93 }

mbus4FVIF2C		OBJECT-TYPE
			SYNTAX	INTEGER
			ACCESS	read-only
			STATUS	current
	DESCRIPTION ""
			::= { mbus4F 94 }

mbus4FValue2C		OBJECT-TYPE
			SYNTAX	INTEGER
			ACCESS	read-only
			STATUS	current
	DESCRIPTION ""
			::= { mbus4F 95 }

mbus4FVIF2D		OBJECT-TYPE
			SYNTAX	INTEGER
			ACCESS	read-only
			STATUS	current
	DESCRIPTION ""
			::= { mbus4F 96 }

mbus4FValue2D		OBJECT-TYPE
			SYNTAX	INTEGER
			ACCESS	read-only
			STATUS	current
	DESCRIPTION ""
			::= { mbus4F 97 }

mbus4FVIF2E		OBJECT-TYPE
			SYNTAX	INTEGER
			ACCESS	read-only
			STATUS	current
	DESCRIPTION ""
			::= { mbus4F 98 }

mbus4FValue2E		OBJECT-TYPE
			SYNTAX	INTEGER
			ACCESS	read-only
			STATUS	current
	DESCRIPTION ""
			::= { mbus4F 99 }

mbus4FVIF2F		OBJECT-TYPE
			SYNTAX	INTEGER
			ACCESS	read-only
			STATUS	current
	DESCRIPTION ""
			::= { mbus4F 100 }

mbus4FValue2F		OBJECT-TYPE
			SYNTAX	INTEGER
			ACCESS	read-only
			STATUS	current
	DESCRIPTION ""
			::= { mbus4F 101 }

mbus50			OBJECT IDENTIFIER ::= { mbus 80 }

mbus50IdNumber		OBJECT-TYPE
			SYNTAX	Gauge
			ACCESS	read-only
			STATUS	current
	DESCRIPTION ""
			::= { mbus50 1 }

mbus50Manufacturer	OBJECT-TYPE
			SYNTAX	Gauge
			ACCESS	read-only
			STATUS	current
	DESCRIPTION ""
			::= { mbus50 2 }

mbus50Version		OBJECT-TYPE
			SYNTAX	Gauge
			ACCESS	read-only
			STATUS	current
	DESCRIPTION ""
			::= { mbus50 3 }

mbus50Medium		OBJECT-TYPE
			SYNTAX	Gauge
			ACCESS	read-only
			STATUS	current
	DESCRIPTION ""
			::= { mbus50 4 }

mbus50Status		OBJECT-TYPE
			SYNTAX	Gauge
			ACCESS	read-only
			STATUS	current
	DESCRIPTION ""
			::= { mbus50 5 }

mbus50VIF00		OBJECT-TYPE
			SYNTAX	INTEGER
			ACCESS	read-only
			STATUS	current
	DESCRIPTION ""
			::= { mbus50 6 }

mbus50Value00		OBJECT-TYPE
			SYNTAX	INTEGER
			ACCESS	read-only
			STATUS	current
	DESCRIPTION ""
			::= { mbus50 7 }

mbus50VIF01		OBJECT-TYPE
			SYNTAX	INTEGER
			ACCESS	read-only
			STATUS	current
	DESCRIPTION ""
			::= { mbus50 8 }

mbus50Value01		OBJECT-TYPE
			SYNTAX	INTEGER
			ACCESS	read-only
			STATUS	current
	DESCRIPTION ""
			::= { mbus50 9 }

mbus50VIF02		OBJECT-TYPE
			SYNTAX	INTEGER
			ACCESS	read-only
			STATUS	current
	DESCRIPTION ""
			::= { mbus50 10 }

mbus50Value02		OBJECT-TYPE
			SYNTAX	INTEGER
			ACCESS	read-only
			STATUS	current
	DESCRIPTION ""
			::= { mbus50 11 }

mbus50VIF03		OBJECT-TYPE
			SYNTAX	INTEGER
			ACCESS	read-only
			STATUS	current
	DESCRIPTION ""
			::= { mbus50 12 }

mbus50Value03		OBJECT-TYPE
			SYNTAX	INTEGER
			ACCESS	read-only
			STATUS	current
	DESCRIPTION ""
			::= { mbus50 13 }

mbus50VIF04		OBJECT-TYPE
			SYNTAX	INTEGER
			ACCESS	read-only
			STATUS	current
	DESCRIPTION ""
			::= { mbus50 14 }

mbus50Value04		OBJECT-TYPE
			SYNTAX	INTEGER
			ACCESS	read-only
			STATUS	current
	DESCRIPTION ""
			::= { mbus50 15 }

mbus50VIF05		OBJECT-TYPE
			SYNTAX	INTEGER
			ACCESS	read-only
			STATUS	current
	DESCRIPTION ""
			::= { mbus50 16 }

mbus50Value05		OBJECT-TYPE
			SYNTAX	INTEGER
			ACCESS	read-only
			STATUS	current
	DESCRIPTION ""
			::= { mbus50 17 }

mbus50VIF06		OBJECT-TYPE
			SYNTAX	INTEGER
			ACCESS	read-only
			STATUS	current
	DESCRIPTION ""
			::= { mbus50 18 }

mbus50Value06		OBJECT-TYPE
			SYNTAX	INTEGER
			ACCESS	read-only
			STATUS	current
	DESCRIPTION ""
			::= { mbus50 19 }

mbus50VIF07		OBJECT-TYPE
			SYNTAX	INTEGER
			ACCESS	read-only
			STATUS	current
	DESCRIPTION ""
			::= { mbus50 20 }

mbus50Value07		OBJECT-TYPE
			SYNTAX	INTEGER
			ACCESS	read-only
			STATUS	current
	DESCRIPTION ""
			::= { mbus50 21 }

mbus50VIF08		OBJECT-TYPE
			SYNTAX	INTEGER
			ACCESS	read-only
			STATUS	current
	DESCRIPTION ""
			::= { mbus50 22 }

mbus50Value08		OBJECT-TYPE
			SYNTAX	INTEGER
			ACCESS	read-only
			STATUS	current
	DESCRIPTION ""
			::= { mbus50 23 }

mbus50VIF09		OBJECT-TYPE
			SYNTAX	INTEGER
			ACCESS	read-only
			STATUS	current
	DESCRIPTION ""
			::= { mbus50 24 }

mbus50Value09		OBJECT-TYPE
			SYNTAX	INTEGER
			ACCESS	read-only
			STATUS	current
	DESCRIPTION ""
			::= { mbus50 25 }

mbus50VIF0A		OBJECT-TYPE
			SYNTAX	INTEGER
			ACCESS	read-only
			STATUS	current
	DESCRIPTION ""
			::= { mbus50 26 }

mbus50Value0A		OBJECT-TYPE
			SYNTAX	INTEGER
			ACCESS	read-only
			STATUS	current
	DESCRIPTION ""
			::= { mbus50 27 }

mbus50VIF0B		OBJECT-TYPE
			SYNTAX	INTEGER
			ACCESS	read-only
			STATUS	current
	DESCRIPTION ""
			::= { mbus50 28 }

mbus50Value0B		OBJECT-TYPE
			SYNTAX	INTEGER
			ACCESS	read-only
			STATUS	current
	DESCRIPTION ""
			::= { mbus50 29 }

mbus50VIF0C		OBJECT-TYPE
			SYNTAX	INTEGER
			ACCESS	read-only
			STATUS	current
	DESCRIPTION ""
			::= { mbus50 30 }

mbus50Value0C		OBJECT-TYPE
			SYNTAX	INTEGER
			ACCESS	read-only
			STATUS	current
	DESCRIPTION ""
			::= { mbus50 31 }

mbus50VIF0D		OBJECT-TYPE
			SYNTAX	INTEGER
			ACCESS	read-only
			STATUS	current
	DESCRIPTION ""
			::= { mbus50 32 }

mbus50Value0D		OBJECT-TYPE
			SYNTAX	INTEGER
			ACCESS	read-only
			STATUS	current
	DESCRIPTION ""
			::= { mbus50 33 }

mbus50VIF0E		OBJECT-TYPE
			SYNTAX	INTEGER
			ACCESS	read-only
			STATUS	current
	DESCRIPTION ""
			::= { mbus50 34 }

mbus50Value0E		OBJECT-TYPE
			SYNTAX	INTEGER
			ACCESS	read-only
			STATUS	current
	DESCRIPTION ""
			::= { mbus50 35 }

mbus50VIF0F		OBJECT-TYPE
			SYNTAX	INTEGER
			ACCESS	read-only
			STATUS	current
	DESCRIPTION ""
			::= { mbus50 36 }

mbus50Value0F		OBJECT-TYPE
			SYNTAX	INTEGER
			ACCESS	read-only
			STATUS	current
	DESCRIPTION ""
			::= { mbus50 37 }

mbus50VIF10		OBJECT-TYPE
			SYNTAX	INTEGER
			ACCESS	read-only
			STATUS	current
	DESCRIPTION ""
			::= { mbus50 38 }

mbus50Value10		OBJECT-TYPE
			SYNTAX	INTEGER
			ACCESS	read-only
			STATUS	current
	DESCRIPTION ""
			::= { mbus50 39 }

mbus50VIF11		OBJECT-TYPE
			SYNTAX	INTEGER
			ACCESS	read-only
			STATUS	current
	DESCRIPTION ""
			::= { mbus50 40 }

mbus50Value11		OBJECT-TYPE
			SYNTAX	INTEGER
			ACCESS	read-only
			STATUS	current
	DESCRIPTION ""
			::= { mbus50 41 }

mbus50VIF12		OBJECT-TYPE
			SYNTAX	INTEGER
			ACCESS	read-only
			STATUS	current
	DESCRIPTION ""
			::= { mbus50 42 }

mbus50Value12		OBJECT-TYPE
			SYNTAX	INTEGER
			ACCESS	read-only
			STATUS	current
	DESCRIPTION ""
			::= { mbus50 43 }

mbus50VIF13		OBJECT-TYPE
			SYNTAX	INTEGER
			ACCESS	read-only
			STATUS	current
	DESCRIPTION ""
			::= { mbus50 44 }

mbus50Value13		OBJECT-TYPE
			SYNTAX	INTEGER
			ACCESS	read-only
			STATUS	current
	DESCRIPTION ""
			::= { mbus50 45 }

mbus50VIF14		OBJECT-TYPE
			SYNTAX	INTEGER
			ACCESS	read-only
			STATUS	current
	DESCRIPTION ""
			::= { mbus50 46 }

mbus50Value14		OBJECT-TYPE
			SYNTAX	INTEGER
			ACCESS	read-only
			STATUS	current
	DESCRIPTION ""
			::= { mbus50 47 }

mbus50VIF15		OBJECT-TYPE
			SYNTAX	INTEGER
			ACCESS	read-only
			STATUS	current
	DESCRIPTION ""
			::= { mbus50 48 }

mbus50Value15		OBJECT-TYPE
			SYNTAX	INTEGER
			ACCESS	read-only
			STATUS	current
	DESCRIPTION ""
			::= { mbus50 49 }

mbus50VIF16		OBJECT-TYPE
			SYNTAX	INTEGER
			ACCESS	read-only
			STATUS	current
	DESCRIPTION ""
			::= { mbus50 50 }

mbus50Value16		OBJECT-TYPE
			SYNTAX	INTEGER
			ACCESS	read-only
			STATUS	current
	DESCRIPTION ""
			::= { mbus50 51 }

mbus50VIF17		OBJECT-TYPE
			SYNTAX	INTEGER
			ACCESS	read-only
			STATUS	current
	DESCRIPTION ""
			::= { mbus50 52 }

mbus50Value17		OBJECT-TYPE
			SYNTAX	INTEGER
			ACCESS	read-only
			STATUS	current
	DESCRIPTION ""
			::= { mbus50 53 }

mbus50VIF18		OBJECT-TYPE
			SYNTAX	INTEGER
			ACCESS	read-only
			STATUS	current
	DESCRIPTION ""
			::= { mbus50 54 }

mbus50Value18		OBJECT-TYPE
			SYNTAX	INTEGER
			ACCESS	read-only
			STATUS	current
	DESCRIPTION ""
			::= { mbus50 55 }

mbus50VIF19		OBJECT-TYPE
			SYNTAX	INTEGER
			ACCESS	read-only
			STATUS	current
	DESCRIPTION ""
			::= { mbus50 56 }

mbus50Value19		OBJECT-TYPE
			SYNTAX	INTEGER
			ACCESS	read-only
			STATUS	current
	DESCRIPTION ""
			::= { mbus50 57 }

mbus50VIF1A		OBJECT-TYPE
			SYNTAX	INTEGER
			ACCESS	read-only
			STATUS	current
	DESCRIPTION ""
			::= { mbus50 58 }

mbus50Value1A		OBJECT-TYPE
			SYNTAX	INTEGER
			ACCESS	read-only
			STATUS	current
	DESCRIPTION ""
			::= { mbus50 59 }

mbus50VIF1B		OBJECT-TYPE
			SYNTAX	INTEGER
			ACCESS	read-only
			STATUS	current
	DESCRIPTION ""
			::= { mbus50 60 }

mbus50Value1B		OBJECT-TYPE
			SYNTAX	INTEGER
			ACCESS	read-only
			STATUS	current
	DESCRIPTION ""
			::= { mbus50 61 }

mbus50VIF1C		OBJECT-TYPE
			SYNTAX	INTEGER
			ACCESS	read-only
			STATUS	current
	DESCRIPTION ""
			::= { mbus50 62 }

mbus50Value1C		OBJECT-TYPE
			SYNTAX	INTEGER
			ACCESS	read-only
			STATUS	current
	DESCRIPTION ""
			::= { mbus50 63 }

mbus50VIF1D		OBJECT-TYPE
			SYNTAX	INTEGER
			ACCESS	read-only
			STATUS	current
	DESCRIPTION ""
			::= { mbus50 64 }

mbus50Value1D		OBJECT-TYPE
			SYNTAX	INTEGER
			ACCESS	read-only
			STATUS	current
	DESCRIPTION ""
			::= { mbus50 65 }

mbus50VIF1E		OBJECT-TYPE
			SYNTAX	INTEGER
			ACCESS	read-only
			STATUS	current
	DESCRIPTION ""
			::= { mbus50 66 }

mbus50Value1E		OBJECT-TYPE
			SYNTAX	INTEGER
			ACCESS	read-only
			STATUS	current
	DESCRIPTION ""
			::= { mbus50 67 }

mbus50VIF1F		OBJECT-TYPE
			SYNTAX	INTEGER
			ACCESS	read-only
			STATUS	current
	DESCRIPTION ""
			::= { mbus50 68 }

mbus50Value1F		OBJECT-TYPE
			SYNTAX	INTEGER
			ACCESS	read-only
			STATUS	current
	DESCRIPTION ""
			::= { mbus50 69 }

mbus50VIF20		OBJECT-TYPE
			SYNTAX	INTEGER
			ACCESS	read-only
			STATUS	current
	DESCRIPTION ""
			::= { mbus50 70 }

mbus50Value20		OBJECT-TYPE
			SYNTAX	INTEGER
			ACCESS	read-only
			STATUS	current
	DESCRIPTION ""
			::= { mbus50 71 }

mbus50VIF21		OBJECT-TYPE
			SYNTAX	INTEGER
			ACCESS	read-only
			STATUS	current
	DESCRIPTION ""
			::= { mbus50 72 }

mbus50Value21		OBJECT-TYPE
			SYNTAX	INTEGER
			ACCESS	read-only
			STATUS	current
	DESCRIPTION ""
			::= { mbus50 73 }

mbus50VIF22		OBJECT-TYPE
			SYNTAX	INTEGER
			ACCESS	read-only
			STATUS	current
	DESCRIPTION ""
			::= { mbus50 74 }

mbus50Value22		OBJECT-TYPE
			SYNTAX	INTEGER
			ACCESS	read-only
			STATUS	current
	DESCRIPTION ""
			::= { mbus50 75 }

mbus50VIF23		OBJECT-TYPE
			SYNTAX	INTEGER
			ACCESS	read-only
			STATUS	current
	DESCRIPTION ""
			::= { mbus50 76 }

mbus50Value23		OBJECT-TYPE
			SYNTAX	INTEGER
			ACCESS	read-only
			STATUS	current
	DESCRIPTION ""
			::= { mbus50 77 }

mbus50VIF24		OBJECT-TYPE
			SYNTAX	INTEGER
			ACCESS	read-only
			STATUS	current
	DESCRIPTION ""
			::= { mbus50 78 }

mbus50Value24		OBJECT-TYPE
			SYNTAX	INTEGER
			ACCESS	read-only
			STATUS	current
	DESCRIPTION ""
			::= { mbus50 79 }

mbus50VIF25		OBJECT-TYPE
			SYNTAX	INTEGER
			ACCESS	read-only
			STATUS	current
	DESCRIPTION ""
			::= { mbus50 80 }

mbus50Value25		OBJECT-TYPE
			SYNTAX	INTEGER
			ACCESS	read-only
			STATUS	current
	DESCRIPTION ""
			::= { mbus50 81 }

mbus50VIF26		OBJECT-TYPE
			SYNTAX	INTEGER
			ACCESS	read-only
			STATUS	current
	DESCRIPTION ""
			::= { mbus50 82 }

mbus50Value26		OBJECT-TYPE
			SYNTAX	INTEGER
			ACCESS	read-only
			STATUS	current
	DESCRIPTION ""
			::= { mbus50 83 }

mbus50VIF27		OBJECT-TYPE
			SYNTAX	INTEGER
			ACCESS	read-only
			STATUS	current
	DESCRIPTION ""
			::= { mbus50 84 }

mbus50Value27		OBJECT-TYPE
			SYNTAX	INTEGER
			ACCESS	read-only
			STATUS	current
	DESCRIPTION ""
			::= { mbus50 85 }

mbus50VIF28		OBJECT-TYPE
			SYNTAX	INTEGER
			ACCESS	read-only
			STATUS	current
	DESCRIPTION ""
			::= { mbus50 86 }

mbus50Value28		OBJECT-TYPE
			SYNTAX	INTEGER
			ACCESS	read-only
			STATUS	current
	DESCRIPTION ""
			::= { mbus50 87 }

mbus50VIF29		OBJECT-TYPE
			SYNTAX	INTEGER
			ACCESS	read-only
			STATUS	current
	DESCRIPTION ""
			::= { mbus50 88 }

mbus50Value29		OBJECT-TYPE
			SYNTAX	INTEGER
			ACCESS	read-only
			STATUS	current
	DESCRIPTION ""
			::= { mbus50 89 }

mbus50VIF2A		OBJECT-TYPE
			SYNTAX	INTEGER
			ACCESS	read-only
			STATUS	current
	DESCRIPTION ""
			::= { mbus50 90 }

mbus50Value2A		OBJECT-TYPE
			SYNTAX	INTEGER
			ACCESS	read-only
			STATUS	current
	DESCRIPTION ""
			::= { mbus50 91 }

mbus50VIF2B		OBJECT-TYPE
			SYNTAX	INTEGER
			ACCESS	read-only
			STATUS	current
	DESCRIPTION ""
			::= { mbus50 92 }

mbus50Value2B		OBJECT-TYPE
			SYNTAX	INTEGER
			ACCESS	read-only
			STATUS	current
	DESCRIPTION ""
			::= { mbus50 93 }

mbus50VIF2C		OBJECT-TYPE
			SYNTAX	INTEGER
			ACCESS	read-only
			STATUS	current
	DESCRIPTION ""
			::= { mbus50 94 }

mbus50Value2C		OBJECT-TYPE
			SYNTAX	INTEGER
			ACCESS	read-only
			STATUS	current
	DESCRIPTION ""
			::= { mbus50 95 }

mbus50VIF2D		OBJECT-TYPE
			SYNTAX	INTEGER
			ACCESS	read-only
			STATUS	current
	DESCRIPTION ""
			::= { mbus50 96 }

mbus50Value2D		OBJECT-TYPE
			SYNTAX	INTEGER
			ACCESS	read-only
			STATUS	current
	DESCRIPTION ""
			::= { mbus50 97 }

mbus50VIF2E		OBJECT-TYPE
			SYNTAX	INTEGER
			ACCESS	read-only
			STATUS	current
	DESCRIPTION ""
			::= { mbus50 98 }

mbus50Value2E		OBJECT-TYPE
			SYNTAX	INTEGER
			ACCESS	read-only
			STATUS	current
	DESCRIPTION ""
			::= { mbus50 99 }

mbus50VIF2F		OBJECT-TYPE
			SYNTAX	INTEGER
			ACCESS	read-only
			STATUS	current
	DESCRIPTION ""
			::= { mbus50 100 }

mbus50Value2F		OBJECT-TYPE
			SYNTAX	INTEGER
			ACCESS	read-only
			STATUS	current
	DESCRIPTION ""
			::= { mbus50 101 }

mbus51			OBJECT IDENTIFIER ::= { mbus 81 }

mbus51IdNumber		OBJECT-TYPE
			SYNTAX	Gauge
			ACCESS	read-only
			STATUS	current
	DESCRIPTION ""
			::= { mbus51 1 }

mbus51Manufacturer	OBJECT-TYPE
			SYNTAX	Gauge
			ACCESS	read-only
			STATUS	current
	DESCRIPTION ""
			::= { mbus51 2 }

mbus51Version		OBJECT-TYPE
			SYNTAX	Gauge
			ACCESS	read-only
			STATUS	current
	DESCRIPTION ""
			::= { mbus51 3 }

mbus51Medium		OBJECT-TYPE
			SYNTAX	Gauge
			ACCESS	read-only
			STATUS	current
	DESCRIPTION ""
			::= { mbus51 4 }

mbus51Status		OBJECT-TYPE
			SYNTAX	Gauge
			ACCESS	read-only
			STATUS	current
	DESCRIPTION ""
			::= { mbus51 5 }

mbus51VIF00		OBJECT-TYPE
			SYNTAX	INTEGER
			ACCESS	read-only
			STATUS	current
	DESCRIPTION ""
			::= { mbus51 6 }

mbus51Value00		OBJECT-TYPE
			SYNTAX	INTEGER
			ACCESS	read-only
			STATUS	current
	DESCRIPTION ""
			::= { mbus51 7 }

mbus51VIF01		OBJECT-TYPE
			SYNTAX	INTEGER
			ACCESS	read-only
			STATUS	current
	DESCRIPTION ""
			::= { mbus51 8 }

mbus51Value01		OBJECT-TYPE
			SYNTAX	INTEGER
			ACCESS	read-only
			STATUS	current
	DESCRIPTION ""
			::= { mbus51 9 }

mbus51VIF02		OBJECT-TYPE
			SYNTAX	INTEGER
			ACCESS	read-only
			STATUS	current
	DESCRIPTION ""
			::= { mbus51 10 }

mbus51Value02		OBJECT-TYPE
			SYNTAX	INTEGER
			ACCESS	read-only
			STATUS	current
	DESCRIPTION ""
			::= { mbus51 11 }

mbus51VIF03		OBJECT-TYPE
			SYNTAX	INTEGER
			ACCESS	read-only
			STATUS	current
	DESCRIPTION ""
			::= { mbus51 12 }

mbus51Value03		OBJECT-TYPE
			SYNTAX	INTEGER
			ACCESS	read-only
			STATUS	current
	DESCRIPTION ""
			::= { mbus51 13 }

mbus51VIF04		OBJECT-TYPE
			SYNTAX	INTEGER
			ACCESS	read-only
			STATUS	current
	DESCRIPTION ""
			::= { mbus51 14 }

mbus51Value04		OBJECT-TYPE
			SYNTAX	INTEGER
			ACCESS	read-only
			STATUS	current
	DESCRIPTION ""
			::= { mbus51 15 }

mbus51VIF05		OBJECT-TYPE
			SYNTAX	INTEGER
			ACCESS	read-only
			STATUS	current
	DESCRIPTION ""
			::= { mbus51 16 }

mbus51Value05		OBJECT-TYPE
			SYNTAX	INTEGER
			ACCESS	read-only
			STATUS	current
	DESCRIPTION ""
			::= { mbus51 17 }

mbus51VIF06		OBJECT-TYPE
			SYNTAX	INTEGER
			ACCESS	read-only
			STATUS	current
	DESCRIPTION ""
			::= { mbus51 18 }

mbus51Value06		OBJECT-TYPE
			SYNTAX	INTEGER
			ACCESS	read-only
			STATUS	current
	DESCRIPTION ""
			::= { mbus51 19 }

mbus51VIF07		OBJECT-TYPE
			SYNTAX	INTEGER
			ACCESS	read-only
			STATUS	current
	DESCRIPTION ""
			::= { mbus51 20 }

mbus51Value07		OBJECT-TYPE
			SYNTAX	INTEGER
			ACCESS	read-only
			STATUS	current
	DESCRIPTION ""
			::= { mbus51 21 }

mbus51VIF08		OBJECT-TYPE
			SYNTAX	INTEGER
			ACCESS	read-only
			STATUS	current
	DESCRIPTION ""
			::= { mbus51 22 }

mbus51Value08		OBJECT-TYPE
			SYNTAX	INTEGER
			ACCESS	read-only
			STATUS	current
	DESCRIPTION ""
			::= { mbus51 23 }

mbus51VIF09		OBJECT-TYPE
			SYNTAX	INTEGER
			ACCESS	read-only
			STATUS	current
	DESCRIPTION ""
			::= { mbus51 24 }

mbus51Value09		OBJECT-TYPE
			SYNTAX	INTEGER
			ACCESS	read-only
			STATUS	current
	DESCRIPTION ""
			::= { mbus51 25 }

mbus51VIF0A		OBJECT-TYPE
			SYNTAX	INTEGER
			ACCESS	read-only
			STATUS	current
	DESCRIPTION ""
			::= { mbus51 26 }

mbus51Value0A		OBJECT-TYPE
			SYNTAX	INTEGER
			ACCESS	read-only
			STATUS	current
	DESCRIPTION ""
			::= { mbus51 27 }

mbus51VIF0B		OBJECT-TYPE
			SYNTAX	INTEGER
			ACCESS	read-only
			STATUS	current
	DESCRIPTION ""
			::= { mbus51 28 }

mbus51Value0B		OBJECT-TYPE
			SYNTAX	INTEGER
			ACCESS	read-only
			STATUS	current
	DESCRIPTION ""
			::= { mbus51 29 }

mbus51VIF0C		OBJECT-TYPE
			SYNTAX	INTEGER
			ACCESS	read-only
			STATUS	current
	DESCRIPTION ""
			::= { mbus51 30 }

mbus51Value0C		OBJECT-TYPE
			SYNTAX	INTEGER
			ACCESS	read-only
			STATUS	current
	DESCRIPTION ""
			::= { mbus51 31 }

mbus51VIF0D		OBJECT-TYPE
			SYNTAX	INTEGER
			ACCESS	read-only
			STATUS	current
	DESCRIPTION ""
			::= { mbus51 32 }

mbus51Value0D		OBJECT-TYPE
			SYNTAX	INTEGER
			ACCESS	read-only
			STATUS	current
	DESCRIPTION ""
			::= { mbus51 33 }

mbus51VIF0E		OBJECT-TYPE
			SYNTAX	INTEGER
			ACCESS	read-only
			STATUS	current
	DESCRIPTION ""
			::= { mbus51 34 }

mbus51Value0E		OBJECT-TYPE
			SYNTAX	INTEGER
			ACCESS	read-only
			STATUS	current
	DESCRIPTION ""
			::= { mbus51 35 }

mbus51VIF0F		OBJECT-TYPE
			SYNTAX	INTEGER
			ACCESS	read-only
			STATUS	current
	DESCRIPTION ""
			::= { mbus51 36 }

mbus51Value0F		OBJECT-TYPE
			SYNTAX	INTEGER
			ACCESS	read-only
			STATUS	current
	DESCRIPTION ""
			::= { mbus51 37 }

mbus51VIF10		OBJECT-TYPE
			SYNTAX	INTEGER
			ACCESS	read-only
			STATUS	current
	DESCRIPTION ""
			::= { mbus51 38 }

mbus51Value10		OBJECT-TYPE
			SYNTAX	INTEGER
			ACCESS	read-only
			STATUS	current
	DESCRIPTION ""
			::= { mbus51 39 }

mbus51VIF11		OBJECT-TYPE
			SYNTAX	INTEGER
			ACCESS	read-only
			STATUS	current
	DESCRIPTION ""
			::= { mbus51 40 }

mbus51Value11		OBJECT-TYPE
			SYNTAX	INTEGER
			ACCESS	read-only
			STATUS	current
	DESCRIPTION ""
			::= { mbus51 41 }

mbus51VIF12		OBJECT-TYPE
			SYNTAX	INTEGER
			ACCESS	read-only
			STATUS	current
	DESCRIPTION ""
			::= { mbus51 42 }

mbus51Value12		OBJECT-TYPE
			SYNTAX	INTEGER
			ACCESS	read-only
			STATUS	current
	DESCRIPTION ""
			::= { mbus51 43 }

mbus51VIF13		OBJECT-TYPE
			SYNTAX	INTEGER
			ACCESS	read-only
			STATUS	current
	DESCRIPTION ""
			::= { mbus51 44 }

mbus51Value13		OBJECT-TYPE
			SYNTAX	INTEGER
			ACCESS	read-only
			STATUS	current
	DESCRIPTION ""
			::= { mbus51 45 }

mbus51VIF14		OBJECT-TYPE
			SYNTAX	INTEGER
			ACCESS	read-only
			STATUS	current
	DESCRIPTION ""
			::= { mbus51 46 }

mbus51Value14		OBJECT-TYPE
			SYNTAX	INTEGER
			ACCESS	read-only
			STATUS	current
	DESCRIPTION ""
			::= { mbus51 47 }

mbus51VIF15		OBJECT-TYPE
			SYNTAX	INTEGER
			ACCESS	read-only
			STATUS	current
	DESCRIPTION ""
			::= { mbus51 48 }

mbus51Value15		OBJECT-TYPE
			SYNTAX	INTEGER
			ACCESS	read-only
			STATUS	current
	DESCRIPTION ""
			::= { mbus51 49 }

mbus51VIF16		OBJECT-TYPE
			SYNTAX	INTEGER
			ACCESS	read-only
			STATUS	current
	DESCRIPTION ""
			::= { mbus51 50 }

mbus51Value16		OBJECT-TYPE
			SYNTAX	INTEGER
			ACCESS	read-only
			STATUS	current
	DESCRIPTION ""
			::= { mbus51 51 }

mbus51VIF17		OBJECT-TYPE
			SYNTAX	INTEGER
			ACCESS	read-only
			STATUS	current
	DESCRIPTION ""
			::= { mbus51 52 }

mbus51Value17		OBJECT-TYPE
			SYNTAX	INTEGER
			ACCESS	read-only
			STATUS	current
	DESCRIPTION ""
			::= { mbus51 53 }

mbus51VIF18		OBJECT-TYPE
			SYNTAX	INTEGER
			ACCESS	read-only
			STATUS	current
	DESCRIPTION ""
			::= { mbus51 54 }

mbus51Value18		OBJECT-TYPE
			SYNTAX	INTEGER
			ACCESS	read-only
			STATUS	current
	DESCRIPTION ""
			::= { mbus51 55 }

mbus51VIF19		OBJECT-TYPE
			SYNTAX	INTEGER
			ACCESS	read-only
			STATUS	current
	DESCRIPTION ""
			::= { mbus51 56 }

mbus51Value19		OBJECT-TYPE
			SYNTAX	INTEGER
			ACCESS	read-only
			STATUS	current
	DESCRIPTION ""
			::= { mbus51 57 }

mbus51VIF1A		OBJECT-TYPE
			SYNTAX	INTEGER
			ACCESS	read-only
			STATUS	current
	DESCRIPTION ""
			::= { mbus51 58 }

mbus51Value1A		OBJECT-TYPE
			SYNTAX	INTEGER
			ACCESS	read-only
			STATUS	current
	DESCRIPTION ""
			::= { mbus51 59 }

mbus51VIF1B		OBJECT-TYPE
			SYNTAX	INTEGER
			ACCESS	read-only
			STATUS	current
	DESCRIPTION ""
			::= { mbus51 60 }

mbus51Value1B		OBJECT-TYPE
			SYNTAX	INTEGER
			ACCESS	read-only
			STATUS	current
	DESCRIPTION ""
			::= { mbus51 61 }

mbus51VIF1C		OBJECT-TYPE
			SYNTAX	INTEGER
			ACCESS	read-only
			STATUS	current
	DESCRIPTION ""
			::= { mbus51 62 }

mbus51Value1C		OBJECT-TYPE
			SYNTAX	INTEGER
			ACCESS	read-only
			STATUS	current
	DESCRIPTION ""
			::= { mbus51 63 }

mbus51VIF1D		OBJECT-TYPE
			SYNTAX	INTEGER
			ACCESS	read-only
			STATUS	current
	DESCRIPTION ""
			::= { mbus51 64 }

mbus51Value1D		OBJECT-TYPE
			SYNTAX	INTEGER
			ACCESS	read-only
			STATUS	current
	DESCRIPTION ""
			::= { mbus51 65 }

mbus51VIF1E		OBJECT-TYPE
			SYNTAX	INTEGER
			ACCESS	read-only
			STATUS	current
	DESCRIPTION ""
			::= { mbus51 66 }

mbus51Value1E		OBJECT-TYPE
			SYNTAX	INTEGER
			ACCESS	read-only
			STATUS	current
	DESCRIPTION ""
			::= { mbus51 67 }

mbus51VIF1F		OBJECT-TYPE
			SYNTAX	INTEGER
			ACCESS	read-only
			STATUS	current
	DESCRIPTION ""
			::= { mbus51 68 }

mbus51Value1F		OBJECT-TYPE
			SYNTAX	INTEGER
			ACCESS	read-only
			STATUS	current
	DESCRIPTION ""
			::= { mbus51 69 }

mbus51VIF20		OBJECT-TYPE
			SYNTAX	INTEGER
			ACCESS	read-only
			STATUS	current
	DESCRIPTION ""
			::= { mbus51 70 }

mbus51Value20		OBJECT-TYPE
			SYNTAX	INTEGER
			ACCESS	read-only
			STATUS	current
	DESCRIPTION ""
			::= { mbus51 71 }

mbus51VIF21		OBJECT-TYPE
			SYNTAX	INTEGER
			ACCESS	read-only
			STATUS	current
	DESCRIPTION ""
			::= { mbus51 72 }

mbus51Value21		OBJECT-TYPE
			SYNTAX	INTEGER
			ACCESS	read-only
			STATUS	current
	DESCRIPTION ""
			::= { mbus51 73 }

mbus51VIF22		OBJECT-TYPE
			SYNTAX	INTEGER
			ACCESS	read-only
			STATUS	current
	DESCRIPTION ""
			::= { mbus51 74 }

mbus51Value22		OBJECT-TYPE
			SYNTAX	INTEGER
			ACCESS	read-only
			STATUS	current
	DESCRIPTION ""
			::= { mbus51 75 }

mbus51VIF23		OBJECT-TYPE
			SYNTAX	INTEGER
			ACCESS	read-only
			STATUS	current
	DESCRIPTION ""
			::= { mbus51 76 }

mbus51Value23		OBJECT-TYPE
			SYNTAX	INTEGER
			ACCESS	read-only
			STATUS	current
	DESCRIPTION ""
			::= { mbus51 77 }

mbus51VIF24		OBJECT-TYPE
			SYNTAX	INTEGER
			ACCESS	read-only
			STATUS	current
	DESCRIPTION ""
			::= { mbus51 78 }

mbus51Value24		OBJECT-TYPE
			SYNTAX	INTEGER
			ACCESS	read-only
			STATUS	current
	DESCRIPTION ""
			::= { mbus51 79 }

mbus51VIF25		OBJECT-TYPE
			SYNTAX	INTEGER
			ACCESS	read-only
			STATUS	current
	DESCRIPTION ""
			::= { mbus51 80 }

mbus51Value25		OBJECT-TYPE
			SYNTAX	INTEGER
			ACCESS	read-only
			STATUS	current
	DESCRIPTION ""
			::= { mbus51 81 }

mbus51VIF26		OBJECT-TYPE
			SYNTAX	INTEGER
			ACCESS	read-only
			STATUS	current
	DESCRIPTION ""
			::= { mbus51 82 }

mbus51Value26		OBJECT-TYPE
			SYNTAX	INTEGER
			ACCESS	read-only
			STATUS	current
	DESCRIPTION ""
			::= { mbus51 83 }

mbus51VIF27		OBJECT-TYPE
			SYNTAX	INTEGER
			ACCESS	read-only
			STATUS	current
	DESCRIPTION ""
			::= { mbus51 84 }

mbus51Value27		OBJECT-TYPE
			SYNTAX	INTEGER
			ACCESS	read-only
			STATUS	current
	DESCRIPTION ""
			::= { mbus51 85 }

mbus51VIF28		OBJECT-TYPE
			SYNTAX	INTEGER
			ACCESS	read-only
			STATUS	current
	DESCRIPTION ""
			::= { mbus51 86 }

mbus51Value28		OBJECT-TYPE
			SYNTAX	INTEGER
			ACCESS	read-only
			STATUS	current
	DESCRIPTION ""
			::= { mbus51 87 }

mbus51VIF29		OBJECT-TYPE
			SYNTAX	INTEGER
			ACCESS	read-only
			STATUS	current
	DESCRIPTION ""
			::= { mbus51 88 }

mbus51Value29		OBJECT-TYPE
			SYNTAX	INTEGER
			ACCESS	read-only
			STATUS	current
	DESCRIPTION ""
			::= { mbus51 89 }

mbus51VIF2A		OBJECT-TYPE
			SYNTAX	INTEGER
			ACCESS	read-only
			STATUS	current
	DESCRIPTION ""
			::= { mbus51 90 }

mbus51Value2A		OBJECT-TYPE
			SYNTAX	INTEGER
			ACCESS	read-only
			STATUS	current
	DESCRIPTION ""
			::= { mbus51 91 }

mbus51VIF2B		OBJECT-TYPE
			SYNTAX	INTEGER
			ACCESS	read-only
			STATUS	current
	DESCRIPTION ""
			::= { mbus51 92 }

mbus51Value2B		OBJECT-TYPE
			SYNTAX	INTEGER
			ACCESS	read-only
			STATUS	current
	DESCRIPTION ""
			::= { mbus51 93 }

mbus51VIF2C		OBJECT-TYPE
			SYNTAX	INTEGER
			ACCESS	read-only
			STATUS	current
	DESCRIPTION ""
			::= { mbus51 94 }

mbus51Value2C		OBJECT-TYPE
			SYNTAX	INTEGER
			ACCESS	read-only
			STATUS	current
	DESCRIPTION ""
			::= { mbus51 95 }

mbus51VIF2D		OBJECT-TYPE
			SYNTAX	INTEGER
			ACCESS	read-only
			STATUS	current
	DESCRIPTION ""
			::= { mbus51 96 }

mbus51Value2D		OBJECT-TYPE
			SYNTAX	INTEGER
			ACCESS	read-only
			STATUS	current
	DESCRIPTION ""
			::= { mbus51 97 }

mbus51VIF2E		OBJECT-TYPE
			SYNTAX	INTEGER
			ACCESS	read-only
			STATUS	current
	DESCRIPTION ""
			::= { mbus51 98 }

mbus51Value2E		OBJECT-TYPE
			SYNTAX	INTEGER
			ACCESS	read-only
			STATUS	current
	DESCRIPTION ""
			::= { mbus51 99 }

mbus51VIF2F		OBJECT-TYPE
			SYNTAX	INTEGER
			ACCESS	read-only
			STATUS	current
	DESCRIPTION ""
			::= { mbus51 100 }

mbus51Value2F		OBJECT-TYPE
			SYNTAX	INTEGER
			ACCESS	read-only
			STATUS	current
	DESCRIPTION ""
			::= { mbus51 101 }

mbus52			OBJECT IDENTIFIER ::= { mbus 82 }

mbus52IdNumber		OBJECT-TYPE
			SYNTAX	Gauge
			ACCESS	read-only
			STATUS	current
	DESCRIPTION ""
			::= { mbus52 1 }

mbus52Manufacturer	OBJECT-TYPE
			SYNTAX	Gauge
			ACCESS	read-only
			STATUS	current
	DESCRIPTION ""
			::= { mbus52 2 }

mbus52Version		OBJECT-TYPE
			SYNTAX	Gauge
			ACCESS	read-only
			STATUS	current
	DESCRIPTION ""
			::= { mbus52 3 }

mbus52Medium		OBJECT-TYPE
			SYNTAX	Gauge
			ACCESS	read-only
			STATUS	current
	DESCRIPTION ""
			::= { mbus52 4 }

mbus52Status		OBJECT-TYPE
			SYNTAX	Gauge
			ACCESS	read-only
			STATUS	current
	DESCRIPTION ""
			::= { mbus52 5 }

mbus52VIF00		OBJECT-TYPE
			SYNTAX	INTEGER
			ACCESS	read-only
			STATUS	current
	DESCRIPTION ""
			::= { mbus52 6 }

mbus52Value00		OBJECT-TYPE
			SYNTAX	INTEGER
			ACCESS	read-only
			STATUS	current
	DESCRIPTION ""
			::= { mbus52 7 }

mbus52VIF01		OBJECT-TYPE
			SYNTAX	INTEGER
			ACCESS	read-only
			STATUS	current
	DESCRIPTION ""
			::= { mbus52 8 }

mbus52Value01		OBJECT-TYPE
			SYNTAX	INTEGER
			ACCESS	read-only
			STATUS	current
	DESCRIPTION ""
			::= { mbus52 9 }

mbus52VIF02		OBJECT-TYPE
			SYNTAX	INTEGER
			ACCESS	read-only
			STATUS	current
	DESCRIPTION ""
			::= { mbus52 10 }

mbus52Value02		OBJECT-TYPE
			SYNTAX	INTEGER
			ACCESS	read-only
			STATUS	current
	DESCRIPTION ""
			::= { mbus52 11 }

mbus52VIF03		OBJECT-TYPE
			SYNTAX	INTEGER
			ACCESS	read-only
			STATUS	current
	DESCRIPTION ""
			::= { mbus52 12 }

mbus52Value03		OBJECT-TYPE
			SYNTAX	INTEGER
			ACCESS	read-only
			STATUS	current
	DESCRIPTION ""
			::= { mbus52 13 }

mbus52VIF04		OBJECT-TYPE
			SYNTAX	INTEGER
			ACCESS	read-only
			STATUS	current
	DESCRIPTION ""
			::= { mbus52 14 }

mbus52Value04		OBJECT-TYPE
			SYNTAX	INTEGER
			ACCESS	read-only
			STATUS	current
	DESCRIPTION ""
			::= { mbus52 15 }

mbus52VIF05		OBJECT-TYPE
			SYNTAX	INTEGER
			ACCESS	read-only
			STATUS	current
	DESCRIPTION ""
			::= { mbus52 16 }

mbus52Value05		OBJECT-TYPE
			SYNTAX	INTEGER
			ACCESS	read-only
			STATUS	current
	DESCRIPTION ""
			::= { mbus52 17 }

mbus52VIF06		OBJECT-TYPE
			SYNTAX	INTEGER
			ACCESS	read-only
			STATUS	current
	DESCRIPTION ""
			::= { mbus52 18 }

mbus52Value06		OBJECT-TYPE
			SYNTAX	INTEGER
			ACCESS	read-only
			STATUS	current
	DESCRIPTION ""
			::= { mbus52 19 }

mbus52VIF07		OBJECT-TYPE
			SYNTAX	INTEGER
			ACCESS	read-only
			STATUS	current
	DESCRIPTION ""
			::= { mbus52 20 }

mbus52Value07		OBJECT-TYPE
			SYNTAX	INTEGER
			ACCESS	read-only
			STATUS	current
	DESCRIPTION ""
			::= { mbus52 21 }

mbus52VIF08		OBJECT-TYPE
			SYNTAX	INTEGER
			ACCESS	read-only
			STATUS	current
	DESCRIPTION ""
			::= { mbus52 22 }

mbus52Value08		OBJECT-TYPE
			SYNTAX	INTEGER
			ACCESS	read-only
			STATUS	current
	DESCRIPTION ""
			::= { mbus52 23 }

mbus52VIF09		OBJECT-TYPE
			SYNTAX	INTEGER
			ACCESS	read-only
			STATUS	current
	DESCRIPTION ""
			::= { mbus52 24 }

mbus52Value09		OBJECT-TYPE
			SYNTAX	INTEGER
			ACCESS	read-only
			STATUS	current
	DESCRIPTION ""
			::= { mbus52 25 }

mbus52VIF0A		OBJECT-TYPE
			SYNTAX	INTEGER
			ACCESS	read-only
			STATUS	current
	DESCRIPTION ""
			::= { mbus52 26 }

mbus52Value0A		OBJECT-TYPE
			SYNTAX	INTEGER
			ACCESS	read-only
			STATUS	current
	DESCRIPTION ""
			::= { mbus52 27 }

mbus52VIF0B		OBJECT-TYPE
			SYNTAX	INTEGER
			ACCESS	read-only
			STATUS	current
	DESCRIPTION ""
			::= { mbus52 28 }

mbus52Value0B		OBJECT-TYPE
			SYNTAX	INTEGER
			ACCESS	read-only
			STATUS	current
	DESCRIPTION ""
			::= { mbus52 29 }

mbus52VIF0C		OBJECT-TYPE
			SYNTAX	INTEGER
			ACCESS	read-only
			STATUS	current
	DESCRIPTION ""
			::= { mbus52 30 }

mbus52Value0C		OBJECT-TYPE
			SYNTAX	INTEGER
			ACCESS	read-only
			STATUS	current
	DESCRIPTION ""
			::= { mbus52 31 }

mbus52VIF0D		OBJECT-TYPE
			SYNTAX	INTEGER
			ACCESS	read-only
			STATUS	current
	DESCRIPTION ""
			::= { mbus52 32 }

mbus52Value0D		OBJECT-TYPE
			SYNTAX	INTEGER
			ACCESS	read-only
			STATUS	current
	DESCRIPTION ""
			::= { mbus52 33 }

mbus52VIF0E		OBJECT-TYPE
			SYNTAX	INTEGER
			ACCESS	read-only
			STATUS	current
	DESCRIPTION ""
			::= { mbus52 34 }

mbus52Value0E		OBJECT-TYPE
			SYNTAX	INTEGER
			ACCESS	read-only
			STATUS	current
	DESCRIPTION ""
			::= { mbus52 35 }

mbus52VIF0F		OBJECT-TYPE
			SYNTAX	INTEGER
			ACCESS	read-only
			STATUS	current
	DESCRIPTION ""
			::= { mbus52 36 }

mbus52Value0F		OBJECT-TYPE
			SYNTAX	INTEGER
			ACCESS	read-only
			STATUS	current
	DESCRIPTION ""
			::= { mbus52 37 }

mbus52VIF10		OBJECT-TYPE
			SYNTAX	INTEGER
			ACCESS	read-only
			STATUS	current
	DESCRIPTION ""
			::= { mbus52 38 }

mbus52Value10		OBJECT-TYPE
			SYNTAX	INTEGER
			ACCESS	read-only
			STATUS	current
	DESCRIPTION ""
			::= { mbus52 39 }

mbus52VIF11		OBJECT-TYPE
			SYNTAX	INTEGER
			ACCESS	read-only
			STATUS	current
	DESCRIPTION ""
			::= { mbus52 40 }

mbus52Value11		OBJECT-TYPE
			SYNTAX	INTEGER
			ACCESS	read-only
			STATUS	current
	DESCRIPTION ""
			::= { mbus52 41 }

mbus52VIF12		OBJECT-TYPE
			SYNTAX	INTEGER
			ACCESS	read-only
			STATUS	current
	DESCRIPTION ""
			::= { mbus52 42 }

mbus52Value12		OBJECT-TYPE
			SYNTAX	INTEGER
			ACCESS	read-only
			STATUS	current
	DESCRIPTION ""
			::= { mbus52 43 }

mbus52VIF13		OBJECT-TYPE
			SYNTAX	INTEGER
			ACCESS	read-only
			STATUS	current
	DESCRIPTION ""
			::= { mbus52 44 }

mbus52Value13		OBJECT-TYPE
			SYNTAX	INTEGER
			ACCESS	read-only
			STATUS	current
	DESCRIPTION ""
			::= { mbus52 45 }

mbus52VIF14		OBJECT-TYPE
			SYNTAX	INTEGER
			ACCESS	read-only
			STATUS	current
	DESCRIPTION ""
			::= { mbus52 46 }

mbus52Value14		OBJECT-TYPE
			SYNTAX	INTEGER
			ACCESS	read-only
			STATUS	current
	DESCRIPTION ""
			::= { mbus52 47 }

mbus52VIF15		OBJECT-TYPE
			SYNTAX	INTEGER
			ACCESS	read-only
			STATUS	current
	DESCRIPTION ""
			::= { mbus52 48 }

mbus52Value15		OBJECT-TYPE
			SYNTAX	INTEGER
			ACCESS	read-only
			STATUS	current
	DESCRIPTION ""
			::= { mbus52 49 }

mbus52VIF16		OBJECT-TYPE
			SYNTAX	INTEGER
			ACCESS	read-only
			STATUS	current
	DESCRIPTION ""
			::= { mbus52 50 }

mbus52Value16		OBJECT-TYPE
			SYNTAX	INTEGER
			ACCESS	read-only
			STATUS	current
	DESCRIPTION ""
			::= { mbus52 51 }

mbus52VIF17		OBJECT-TYPE
			SYNTAX	INTEGER
			ACCESS	read-only
			STATUS	current
	DESCRIPTION ""
			::= { mbus52 52 }

mbus52Value17		OBJECT-TYPE
			SYNTAX	INTEGER
			ACCESS	read-only
			STATUS	current
	DESCRIPTION ""
			::= { mbus52 53 }

mbus52VIF18		OBJECT-TYPE
			SYNTAX	INTEGER
			ACCESS	read-only
			STATUS	current
	DESCRIPTION ""
			::= { mbus52 54 }

mbus52Value18		OBJECT-TYPE
			SYNTAX	INTEGER
			ACCESS	read-only
			STATUS	current
	DESCRIPTION ""
			::= { mbus52 55 }

mbus52VIF19		OBJECT-TYPE
			SYNTAX	INTEGER
			ACCESS	read-only
			STATUS	current
	DESCRIPTION ""
			::= { mbus52 56 }

mbus52Value19		OBJECT-TYPE
			SYNTAX	INTEGER
			ACCESS	read-only
			STATUS	current
	DESCRIPTION ""
			::= { mbus52 57 }

mbus52VIF1A		OBJECT-TYPE
			SYNTAX	INTEGER
			ACCESS	read-only
			STATUS	current
	DESCRIPTION ""
			::= { mbus52 58 }

mbus52Value1A		OBJECT-TYPE
			SYNTAX	INTEGER
			ACCESS	read-only
			STATUS	current
	DESCRIPTION ""
			::= { mbus52 59 }

mbus52VIF1B		OBJECT-TYPE
			SYNTAX	INTEGER
			ACCESS	read-only
			STATUS	current
	DESCRIPTION ""
			::= { mbus52 60 }

mbus52Value1B		OBJECT-TYPE
			SYNTAX	INTEGER
			ACCESS	read-only
			STATUS	current
	DESCRIPTION ""
			::= { mbus52 61 }

mbus52VIF1C		OBJECT-TYPE
			SYNTAX	INTEGER
			ACCESS	read-only
			STATUS	current
	DESCRIPTION ""
			::= { mbus52 62 }

mbus52Value1C		OBJECT-TYPE
			SYNTAX	INTEGER
			ACCESS	read-only
			STATUS	current
	DESCRIPTION ""
			::= { mbus52 63 }

mbus52VIF1D		OBJECT-TYPE
			SYNTAX	INTEGER
			ACCESS	read-only
			STATUS	current
	DESCRIPTION ""
			::= { mbus52 64 }

mbus52Value1D		OBJECT-TYPE
			SYNTAX	INTEGER
			ACCESS	read-only
			STATUS	current
	DESCRIPTION ""
			::= { mbus52 65 }

mbus52VIF1E		OBJECT-TYPE
			SYNTAX	INTEGER
			ACCESS	read-only
			STATUS	current
	DESCRIPTION ""
			::= { mbus52 66 }

mbus52Value1E		OBJECT-TYPE
			SYNTAX	INTEGER
			ACCESS	read-only
			STATUS	current
	DESCRIPTION ""
			::= { mbus52 67 }

mbus52VIF1F		OBJECT-TYPE
			SYNTAX	INTEGER
			ACCESS	read-only
			STATUS	current
	DESCRIPTION ""
			::= { mbus52 68 }

mbus52Value1F		OBJECT-TYPE
			SYNTAX	INTEGER
			ACCESS	read-only
			STATUS	current
	DESCRIPTION ""
			::= { mbus52 69 }

mbus52VIF20		OBJECT-TYPE
			SYNTAX	INTEGER
			ACCESS	read-only
			STATUS	current
	DESCRIPTION ""
			::= { mbus52 70 }

mbus52Value20		OBJECT-TYPE
			SYNTAX	INTEGER
			ACCESS	read-only
			STATUS	current
	DESCRIPTION ""
			::= { mbus52 71 }

mbus52VIF21		OBJECT-TYPE
			SYNTAX	INTEGER
			ACCESS	read-only
			STATUS	current
	DESCRIPTION ""
			::= { mbus52 72 }

mbus52Value21		OBJECT-TYPE
			SYNTAX	INTEGER
			ACCESS	read-only
			STATUS	current
	DESCRIPTION ""
			::= { mbus52 73 }

mbus52VIF22		OBJECT-TYPE
			SYNTAX	INTEGER
			ACCESS	read-only
			STATUS	current
	DESCRIPTION ""
			::= { mbus52 74 }

mbus52Value22		OBJECT-TYPE
			SYNTAX	INTEGER
			ACCESS	read-only
			STATUS	current
	DESCRIPTION ""
			::= { mbus52 75 }

mbus52VIF23		OBJECT-TYPE
			SYNTAX	INTEGER
			ACCESS	read-only
			STATUS	current
	DESCRIPTION ""
			::= { mbus52 76 }

mbus52Value23		OBJECT-TYPE
			SYNTAX	INTEGER
			ACCESS	read-only
			STATUS	current
	DESCRIPTION ""
			::= { mbus52 77 }

mbus52VIF24		OBJECT-TYPE
			SYNTAX	INTEGER
			ACCESS	read-only
			STATUS	current
	DESCRIPTION ""
			::= { mbus52 78 }

mbus52Value24		OBJECT-TYPE
			SYNTAX	INTEGER
			ACCESS	read-only
			STATUS	current
	DESCRIPTION ""
			::= { mbus52 79 }

mbus52VIF25		OBJECT-TYPE
			SYNTAX	INTEGER
			ACCESS	read-only
			STATUS	current
	DESCRIPTION ""
			::= { mbus52 80 }

mbus52Value25		OBJECT-TYPE
			SYNTAX	INTEGER
			ACCESS	read-only
			STATUS	current
	DESCRIPTION ""
			::= { mbus52 81 }

mbus52VIF26		OBJECT-TYPE
			SYNTAX	INTEGER
			ACCESS	read-only
			STATUS	current
	DESCRIPTION ""
			::= { mbus52 82 }

mbus52Value26		OBJECT-TYPE
			SYNTAX	INTEGER
			ACCESS	read-only
			STATUS	current
	DESCRIPTION ""
			::= { mbus52 83 }

mbus52VIF27		OBJECT-TYPE
			SYNTAX	INTEGER
			ACCESS	read-only
			STATUS	current
	DESCRIPTION ""
			::= { mbus52 84 }

mbus52Value27		OBJECT-TYPE
			SYNTAX	INTEGER
			ACCESS	read-only
			STATUS	current
	DESCRIPTION ""
			::= { mbus52 85 }

mbus52VIF28		OBJECT-TYPE
			SYNTAX	INTEGER
			ACCESS	read-only
			STATUS	current
	DESCRIPTION ""
			::= { mbus52 86 }

mbus52Value28		OBJECT-TYPE
			SYNTAX	INTEGER
			ACCESS	read-only
			STATUS	current
	DESCRIPTION ""
			::= { mbus52 87 }

mbus52VIF29		OBJECT-TYPE
			SYNTAX	INTEGER
			ACCESS	read-only
			STATUS	current
	DESCRIPTION ""
			::= { mbus52 88 }

mbus52Value29		OBJECT-TYPE
			SYNTAX	INTEGER
			ACCESS	read-only
			STATUS	current
	DESCRIPTION ""
			::= { mbus52 89 }

mbus52VIF2A		OBJECT-TYPE
			SYNTAX	INTEGER
			ACCESS	read-only
			STATUS	current
	DESCRIPTION ""
			::= { mbus52 90 }

mbus52Value2A		OBJECT-TYPE
			SYNTAX	INTEGER
			ACCESS	read-only
			STATUS	current
	DESCRIPTION ""
			::= { mbus52 91 }

mbus52VIF2B		OBJECT-TYPE
			SYNTAX	INTEGER
			ACCESS	read-only
			STATUS	current
	DESCRIPTION ""
			::= { mbus52 92 }

mbus52Value2B		OBJECT-TYPE
			SYNTAX	INTEGER
			ACCESS	read-only
			STATUS	current
	DESCRIPTION ""
			::= { mbus52 93 }

mbus52VIF2C		OBJECT-TYPE
			SYNTAX	INTEGER
			ACCESS	read-only
			STATUS	current
	DESCRIPTION ""
			::= { mbus52 94 }

mbus52Value2C		OBJECT-TYPE
			SYNTAX	INTEGER
			ACCESS	read-only
			STATUS	current
	DESCRIPTION ""
			::= { mbus52 95 }

mbus52VIF2D		OBJECT-TYPE
			SYNTAX	INTEGER
			ACCESS	read-only
			STATUS	current
	DESCRIPTION ""
			::= { mbus52 96 }

mbus52Value2D		OBJECT-TYPE
			SYNTAX	INTEGER
			ACCESS	read-only
			STATUS	current
	DESCRIPTION ""
			::= { mbus52 97 }

mbus52VIF2E		OBJECT-TYPE
			SYNTAX	INTEGER
			ACCESS	read-only
			STATUS	current
	DESCRIPTION ""
			::= { mbus52 98 }

mbus52Value2E		OBJECT-TYPE
			SYNTAX	INTEGER
			ACCESS	read-only
			STATUS	current
	DESCRIPTION ""
			::= { mbus52 99 }

mbus52VIF2F		OBJECT-TYPE
			SYNTAX	INTEGER
			ACCESS	read-only
			STATUS	current
	DESCRIPTION ""
			::= { mbus52 100 }

mbus52Value2F		OBJECT-TYPE
			SYNTAX	INTEGER
			ACCESS	read-only
			STATUS	current
	DESCRIPTION ""
			::= { mbus52 101 }

mbus53			OBJECT IDENTIFIER ::= { mbus 83 }

mbus53IdNumber		OBJECT-TYPE
			SYNTAX	Gauge
			ACCESS	read-only
			STATUS	current
	DESCRIPTION ""
			::= { mbus53 1 }

mbus53Manufacturer	OBJECT-TYPE
			SYNTAX	Gauge
			ACCESS	read-only
			STATUS	current
	DESCRIPTION ""
			::= { mbus53 2 }

mbus53Version		OBJECT-TYPE
			SYNTAX	Gauge
			ACCESS	read-only
			STATUS	current
	DESCRIPTION ""
			::= { mbus53 3 }

mbus53Medium		OBJECT-TYPE
			SYNTAX	Gauge
			ACCESS	read-only
			STATUS	current
	DESCRIPTION ""
			::= { mbus53 4 }

mbus53Status		OBJECT-TYPE
			SYNTAX	Gauge
			ACCESS	read-only
			STATUS	current
	DESCRIPTION ""
			::= { mbus53 5 }

mbus53VIF00		OBJECT-TYPE
			SYNTAX	INTEGER
			ACCESS	read-only
			STATUS	current
	DESCRIPTION ""
			::= { mbus53 6 }

mbus53Value00		OBJECT-TYPE
			SYNTAX	INTEGER
			ACCESS	read-only
			STATUS	current
	DESCRIPTION ""
			::= { mbus53 7 }

mbus53VIF01		OBJECT-TYPE
			SYNTAX	INTEGER
			ACCESS	read-only
			STATUS	current
	DESCRIPTION ""
			::= { mbus53 8 }

mbus53Value01		OBJECT-TYPE
			SYNTAX	INTEGER
			ACCESS	read-only
			STATUS	current
	DESCRIPTION ""
			::= { mbus53 9 }

mbus53VIF02		OBJECT-TYPE
			SYNTAX	INTEGER
			ACCESS	read-only
			STATUS	current
	DESCRIPTION ""
			::= { mbus53 10 }

mbus53Value02		OBJECT-TYPE
			SYNTAX	INTEGER
			ACCESS	read-only
			STATUS	current
	DESCRIPTION ""
			::= { mbus53 11 }

mbus53VIF03		OBJECT-TYPE
			SYNTAX	INTEGER
			ACCESS	read-only
			STATUS	current
	DESCRIPTION ""
			::= { mbus53 12 }

mbus53Value03		OBJECT-TYPE
			SYNTAX	INTEGER
			ACCESS	read-only
			STATUS	current
	DESCRIPTION ""
			::= { mbus53 13 }

mbus53VIF04		OBJECT-TYPE
			SYNTAX	INTEGER
			ACCESS	read-only
			STATUS	current
	DESCRIPTION ""
			::= { mbus53 14 }

mbus53Value04		OBJECT-TYPE
			SYNTAX	INTEGER
			ACCESS	read-only
			STATUS	current
	DESCRIPTION ""
			::= { mbus53 15 }

mbus53VIF05		OBJECT-TYPE
			SYNTAX	INTEGER
			ACCESS	read-only
			STATUS	current
	DESCRIPTION ""
			::= { mbus53 16 }

mbus53Value05		OBJECT-TYPE
			SYNTAX	INTEGER
			ACCESS	read-only
			STATUS	current
	DESCRIPTION ""
			::= { mbus53 17 }

mbus53VIF06		OBJECT-TYPE
			SYNTAX	INTEGER
			ACCESS	read-only
			STATUS	current
	DESCRIPTION ""
			::= { mbus53 18 }

mbus53Value06		OBJECT-TYPE
			SYNTAX	INTEGER
			ACCESS	read-only
			STATUS	current
	DESCRIPTION ""
			::= { mbus53 19 }

mbus53VIF07		OBJECT-TYPE
			SYNTAX	INTEGER
			ACCESS	read-only
			STATUS	current
	DESCRIPTION ""
			::= { mbus53 20 }

mbus53Value07		OBJECT-TYPE
			SYNTAX	INTEGER
			ACCESS	read-only
			STATUS	current
	DESCRIPTION ""
			::= { mbus53 21 }

mbus53VIF08		OBJECT-TYPE
			SYNTAX	INTEGER
			ACCESS	read-only
			STATUS	current
	DESCRIPTION ""
			::= { mbus53 22 }

mbus53Value08		OBJECT-TYPE
			SYNTAX	INTEGER
			ACCESS	read-only
			STATUS	current
	DESCRIPTION ""
			::= { mbus53 23 }

mbus53VIF09		OBJECT-TYPE
			SYNTAX	INTEGER
			ACCESS	read-only
			STATUS	current
	DESCRIPTION ""
			::= { mbus53 24 }

mbus53Value09		OBJECT-TYPE
			SYNTAX	INTEGER
			ACCESS	read-only
			STATUS	current
	DESCRIPTION ""
			::= { mbus53 25 }

mbus53VIF0A		OBJECT-TYPE
			SYNTAX	INTEGER
			ACCESS	read-only
			STATUS	current
	DESCRIPTION ""
			::= { mbus53 26 }

mbus53Value0A		OBJECT-TYPE
			SYNTAX	INTEGER
			ACCESS	read-only
			STATUS	current
	DESCRIPTION ""
			::= { mbus53 27 }

mbus53VIF0B		OBJECT-TYPE
			SYNTAX	INTEGER
			ACCESS	read-only
			STATUS	current
	DESCRIPTION ""
			::= { mbus53 28 }

mbus53Value0B		OBJECT-TYPE
			SYNTAX	INTEGER
			ACCESS	read-only
			STATUS	current
	DESCRIPTION ""
			::= { mbus53 29 }

mbus53VIF0C		OBJECT-TYPE
			SYNTAX	INTEGER
			ACCESS	read-only
			STATUS	current
	DESCRIPTION ""
			::= { mbus53 30 }

mbus53Value0C		OBJECT-TYPE
			SYNTAX	INTEGER
			ACCESS	read-only
			STATUS	current
	DESCRIPTION ""
			::= { mbus53 31 }

mbus53VIF0D		OBJECT-TYPE
			SYNTAX	INTEGER
			ACCESS	read-only
			STATUS	current
	DESCRIPTION ""
			::= { mbus53 32 }

mbus53Value0D		OBJECT-TYPE
			SYNTAX	INTEGER
			ACCESS	read-only
			STATUS	current
	DESCRIPTION ""
			::= { mbus53 33 }

mbus53VIF0E		OBJECT-TYPE
			SYNTAX	INTEGER
			ACCESS	read-only
			STATUS	current
	DESCRIPTION ""
			::= { mbus53 34 }

mbus53Value0E		OBJECT-TYPE
			SYNTAX	INTEGER
			ACCESS	read-only
			STATUS	current
	DESCRIPTION ""
			::= { mbus53 35 }

mbus53VIF0F		OBJECT-TYPE
			SYNTAX	INTEGER
			ACCESS	read-only
			STATUS	current
	DESCRIPTION ""
			::= { mbus53 36 }

mbus53Value0F		OBJECT-TYPE
			SYNTAX	INTEGER
			ACCESS	read-only
			STATUS	current
	DESCRIPTION ""
			::= { mbus53 37 }

mbus53VIF10		OBJECT-TYPE
			SYNTAX	INTEGER
			ACCESS	read-only
			STATUS	current
	DESCRIPTION ""
			::= { mbus53 38 }

mbus53Value10		OBJECT-TYPE
			SYNTAX	INTEGER
			ACCESS	read-only
			STATUS	current
	DESCRIPTION ""
			::= { mbus53 39 }

mbus53VIF11		OBJECT-TYPE
			SYNTAX	INTEGER
			ACCESS	read-only
			STATUS	current
	DESCRIPTION ""
			::= { mbus53 40 }

mbus53Value11		OBJECT-TYPE
			SYNTAX	INTEGER
			ACCESS	read-only
			STATUS	current
	DESCRIPTION ""
			::= { mbus53 41 }

mbus53VIF12		OBJECT-TYPE
			SYNTAX	INTEGER
			ACCESS	read-only
			STATUS	current
	DESCRIPTION ""
			::= { mbus53 42 }

mbus53Value12		OBJECT-TYPE
			SYNTAX	INTEGER
			ACCESS	read-only
			STATUS	current
	DESCRIPTION ""
			::= { mbus53 43 }

mbus53VIF13		OBJECT-TYPE
			SYNTAX	INTEGER
			ACCESS	read-only
			STATUS	current
	DESCRIPTION ""
			::= { mbus53 44 }

mbus53Value13		OBJECT-TYPE
			SYNTAX	INTEGER
			ACCESS	read-only
			STATUS	current
	DESCRIPTION ""
			::= { mbus53 45 }

mbus53VIF14		OBJECT-TYPE
			SYNTAX	INTEGER
			ACCESS	read-only
			STATUS	current
	DESCRIPTION ""
			::= { mbus53 46 }

mbus53Value14		OBJECT-TYPE
			SYNTAX	INTEGER
			ACCESS	read-only
			STATUS	current
	DESCRIPTION ""
			::= { mbus53 47 }

mbus53VIF15		OBJECT-TYPE
			SYNTAX	INTEGER
			ACCESS	read-only
			STATUS	current
	DESCRIPTION ""
			::= { mbus53 48 }

mbus53Value15		OBJECT-TYPE
			SYNTAX	INTEGER
			ACCESS	read-only
			STATUS	current
	DESCRIPTION ""
			::= { mbus53 49 }

mbus53VIF16		OBJECT-TYPE
			SYNTAX	INTEGER
			ACCESS	read-only
			STATUS	current
	DESCRIPTION ""
			::= { mbus53 50 }

mbus53Value16		OBJECT-TYPE
			SYNTAX	INTEGER
			ACCESS	read-only
			STATUS	current
	DESCRIPTION ""
			::= { mbus53 51 }

mbus53VIF17		OBJECT-TYPE
			SYNTAX	INTEGER
			ACCESS	read-only
			STATUS	current
	DESCRIPTION ""
			::= { mbus53 52 }

mbus53Value17		OBJECT-TYPE
			SYNTAX	INTEGER
			ACCESS	read-only
			STATUS	current
	DESCRIPTION ""
			::= { mbus53 53 }

mbus53VIF18		OBJECT-TYPE
			SYNTAX	INTEGER
			ACCESS	read-only
			STATUS	current
	DESCRIPTION ""
			::= { mbus53 54 }

mbus53Value18		OBJECT-TYPE
			SYNTAX	INTEGER
			ACCESS	read-only
			STATUS	current
	DESCRIPTION ""
			::= { mbus53 55 }

mbus53VIF19		OBJECT-TYPE
			SYNTAX	INTEGER
			ACCESS	read-only
			STATUS	current
	DESCRIPTION ""
			::= { mbus53 56 }

mbus53Value19		OBJECT-TYPE
			SYNTAX	INTEGER
			ACCESS	read-only
			STATUS	current
	DESCRIPTION ""
			::= { mbus53 57 }

mbus53VIF1A		OBJECT-TYPE
			SYNTAX	INTEGER
			ACCESS	read-only
			STATUS	current
	DESCRIPTION ""
			::= { mbus53 58 }

mbus53Value1A		OBJECT-TYPE
			SYNTAX	INTEGER
			ACCESS	read-only
			STATUS	current
	DESCRIPTION ""
			::= { mbus53 59 }

mbus53VIF1B		OBJECT-TYPE
			SYNTAX	INTEGER
			ACCESS	read-only
			STATUS	current
	DESCRIPTION ""
			::= { mbus53 60 }

mbus53Value1B		OBJECT-TYPE
			SYNTAX	INTEGER
			ACCESS	read-only
			STATUS	current
	DESCRIPTION ""
			::= { mbus53 61 }

mbus53VIF1C		OBJECT-TYPE
			SYNTAX	INTEGER
			ACCESS	read-only
			STATUS	current
	DESCRIPTION ""
			::= { mbus53 62 }

mbus53Value1C		OBJECT-TYPE
			SYNTAX	INTEGER
			ACCESS	read-only
			STATUS	current
	DESCRIPTION ""
			::= { mbus53 63 }

mbus53VIF1D		OBJECT-TYPE
			SYNTAX	INTEGER
			ACCESS	read-only
			STATUS	current
	DESCRIPTION ""
			::= { mbus53 64 }

mbus53Value1D		OBJECT-TYPE
			SYNTAX	INTEGER
			ACCESS	read-only
			STATUS	current
	DESCRIPTION ""
			::= { mbus53 65 }

mbus53VIF1E		OBJECT-TYPE
			SYNTAX	INTEGER
			ACCESS	read-only
			STATUS	current
	DESCRIPTION ""
			::= { mbus53 66 }

mbus53Value1E		OBJECT-TYPE
			SYNTAX	INTEGER
			ACCESS	read-only
			STATUS	current
	DESCRIPTION ""
			::= { mbus53 67 }

mbus53VIF1F		OBJECT-TYPE
			SYNTAX	INTEGER
			ACCESS	read-only
			STATUS	current
	DESCRIPTION ""
			::= { mbus53 68 }

mbus53Value1F		OBJECT-TYPE
			SYNTAX	INTEGER
			ACCESS	read-only
			STATUS	current
	DESCRIPTION ""
			::= { mbus53 69 }

mbus53VIF20		OBJECT-TYPE
			SYNTAX	INTEGER
			ACCESS	read-only
			STATUS	current
	DESCRIPTION ""
			::= { mbus53 70 }

mbus53Value20		OBJECT-TYPE
			SYNTAX	INTEGER
			ACCESS	read-only
			STATUS	current
	DESCRIPTION ""
			::= { mbus53 71 }

mbus53VIF21		OBJECT-TYPE
			SYNTAX	INTEGER
			ACCESS	read-only
			STATUS	current
	DESCRIPTION ""
			::= { mbus53 72 }

mbus53Value21		OBJECT-TYPE
			SYNTAX	INTEGER
			ACCESS	read-only
			STATUS	current
	DESCRIPTION ""
			::= { mbus53 73 }

mbus53VIF22		OBJECT-TYPE
			SYNTAX	INTEGER
			ACCESS	read-only
			STATUS	current
	DESCRIPTION ""
			::= { mbus53 74 }

mbus53Value22		OBJECT-TYPE
			SYNTAX	INTEGER
			ACCESS	read-only
			STATUS	current
	DESCRIPTION ""
			::= { mbus53 75 }

mbus53VIF23		OBJECT-TYPE
			SYNTAX	INTEGER
			ACCESS	read-only
			STATUS	current
	DESCRIPTION ""
			::= { mbus53 76 }

mbus53Value23		OBJECT-TYPE
			SYNTAX	INTEGER
			ACCESS	read-only
			STATUS	current
	DESCRIPTION ""
			::= { mbus53 77 }

mbus53VIF24		OBJECT-TYPE
			SYNTAX	INTEGER
			ACCESS	read-only
			STATUS	current
	DESCRIPTION ""
			::= { mbus53 78 }

mbus53Value24		OBJECT-TYPE
			SYNTAX	INTEGER
			ACCESS	read-only
			STATUS	current
	DESCRIPTION ""
			::= { mbus53 79 }

mbus53VIF25		OBJECT-TYPE
			SYNTAX	INTEGER
			ACCESS	read-only
			STATUS	current
	DESCRIPTION ""
			::= { mbus53 80 }

mbus53Value25		OBJECT-TYPE
			SYNTAX	INTEGER
			ACCESS	read-only
			STATUS	current
	DESCRIPTION ""
			::= { mbus53 81 }

mbus53VIF26		OBJECT-TYPE
			SYNTAX	INTEGER
			ACCESS	read-only
			STATUS	current
	DESCRIPTION ""
			::= { mbus53 82 }

mbus53Value26		OBJECT-TYPE
			SYNTAX	INTEGER
			ACCESS	read-only
			STATUS	current
	DESCRIPTION ""
			::= { mbus53 83 }

mbus53VIF27		OBJECT-TYPE
			SYNTAX	INTEGER
			ACCESS	read-only
			STATUS	current
	DESCRIPTION ""
			::= { mbus53 84 }

mbus53Value27		OBJECT-TYPE
			SYNTAX	INTEGER
			ACCESS	read-only
			STATUS	current
	DESCRIPTION ""
			::= { mbus53 85 }

mbus53VIF28		OBJECT-TYPE
			SYNTAX	INTEGER
			ACCESS	read-only
			STATUS	current
	DESCRIPTION ""
			::= { mbus53 86 }

mbus53Value28		OBJECT-TYPE
			SYNTAX	INTEGER
			ACCESS	read-only
			STATUS	current
	DESCRIPTION ""
			::= { mbus53 87 }

mbus53VIF29		OBJECT-TYPE
			SYNTAX	INTEGER
			ACCESS	read-only
			STATUS	current
	DESCRIPTION ""
			::= { mbus53 88 }

mbus53Value29		OBJECT-TYPE
			SYNTAX	INTEGER
			ACCESS	read-only
			STATUS	current
	DESCRIPTION ""
			::= { mbus53 89 }

mbus53VIF2A		OBJECT-TYPE
			SYNTAX	INTEGER
			ACCESS	read-only
			STATUS	current
	DESCRIPTION ""
			::= { mbus53 90 }

mbus53Value2A		OBJECT-TYPE
			SYNTAX	INTEGER
			ACCESS	read-only
			STATUS	current
	DESCRIPTION ""
			::= { mbus53 91 }

mbus53VIF2B		OBJECT-TYPE
			SYNTAX	INTEGER
			ACCESS	read-only
			STATUS	current
	DESCRIPTION ""
			::= { mbus53 92 }

mbus53Value2B		OBJECT-TYPE
			SYNTAX	INTEGER
			ACCESS	read-only
			STATUS	current
	DESCRIPTION ""
			::= { mbus53 93 }

mbus53VIF2C		OBJECT-TYPE
			SYNTAX	INTEGER
			ACCESS	read-only
			STATUS	current
	DESCRIPTION ""
			::= { mbus53 94 }

mbus53Value2C		OBJECT-TYPE
			SYNTAX	INTEGER
			ACCESS	read-only
			STATUS	current
	DESCRIPTION ""
			::= { mbus53 95 }

mbus53VIF2D		OBJECT-TYPE
			SYNTAX	INTEGER
			ACCESS	read-only
			STATUS	current
	DESCRIPTION ""
			::= { mbus53 96 }

mbus53Value2D		OBJECT-TYPE
			SYNTAX	INTEGER
			ACCESS	read-only
			STATUS	current
	DESCRIPTION ""
			::= { mbus53 97 }

mbus53VIF2E		OBJECT-TYPE
			SYNTAX	INTEGER
			ACCESS	read-only
			STATUS	current
	DESCRIPTION ""
			::= { mbus53 98 }

mbus53Value2E		OBJECT-TYPE
			SYNTAX	INTEGER
			ACCESS	read-only
			STATUS	current
	DESCRIPTION ""
			::= { mbus53 99 }

mbus53VIF2F		OBJECT-TYPE
			SYNTAX	INTEGER
			ACCESS	read-only
			STATUS	current
	DESCRIPTION ""
			::= { mbus53 100 }

mbus53Value2F		OBJECT-TYPE
			SYNTAX	INTEGER
			ACCESS	read-only
			STATUS	current
	DESCRIPTION ""
			::= { mbus53 101 }

mbus54			OBJECT IDENTIFIER ::= { mbus 84 }

mbus54IdNumber		OBJECT-TYPE
			SYNTAX	Gauge
			ACCESS	read-only
			STATUS	current
	DESCRIPTION ""
			::= { mbus54 1 }

mbus54Manufacturer	OBJECT-TYPE
			SYNTAX	Gauge
			ACCESS	read-only
			STATUS	current
	DESCRIPTION ""
			::= { mbus54 2 }

mbus54Version		OBJECT-TYPE
			SYNTAX	Gauge
			ACCESS	read-only
			STATUS	current
	DESCRIPTION ""
			::= { mbus54 3 }

mbus54Medium		OBJECT-TYPE
			SYNTAX	Gauge
			ACCESS	read-only
			STATUS	current
	DESCRIPTION ""
			::= { mbus54 4 }

mbus54Status		OBJECT-TYPE
			SYNTAX	Gauge
			ACCESS	read-only
			STATUS	current
	DESCRIPTION ""
			::= { mbus54 5 }

mbus54VIF00		OBJECT-TYPE
			SYNTAX	INTEGER
			ACCESS	read-only
			STATUS	current
	DESCRIPTION ""
			::= { mbus54 6 }

mbus54Value00		OBJECT-TYPE
			SYNTAX	INTEGER
			ACCESS	read-only
			STATUS	current
	DESCRIPTION ""
			::= { mbus54 7 }

mbus54VIF01		OBJECT-TYPE
			SYNTAX	INTEGER
			ACCESS	read-only
			STATUS	current
	DESCRIPTION ""
			::= { mbus54 8 }

mbus54Value01		OBJECT-TYPE
			SYNTAX	INTEGER
			ACCESS	read-only
			STATUS	current
	DESCRIPTION ""
			::= { mbus54 9 }

mbus54VIF02		OBJECT-TYPE
			SYNTAX	INTEGER
			ACCESS	read-only
			STATUS	current
	DESCRIPTION ""
			::= { mbus54 10 }

mbus54Value02		OBJECT-TYPE
			SYNTAX	INTEGER
			ACCESS	read-only
			STATUS	current
	DESCRIPTION ""
			::= { mbus54 11 }

mbus54VIF03		OBJECT-TYPE
			SYNTAX	INTEGER
			ACCESS	read-only
			STATUS	current
	DESCRIPTION ""
			::= { mbus54 12 }

mbus54Value03		OBJECT-TYPE
			SYNTAX	INTEGER
			ACCESS	read-only
			STATUS	current
	DESCRIPTION ""
			::= { mbus54 13 }

mbus54VIF04		OBJECT-TYPE
			SYNTAX	INTEGER
			ACCESS	read-only
			STATUS	current
	DESCRIPTION ""
			::= { mbus54 14 }

mbus54Value04		OBJECT-TYPE
			SYNTAX	INTEGER
			ACCESS	read-only
			STATUS	current
	DESCRIPTION ""
			::= { mbus54 15 }

mbus54VIF05		OBJECT-TYPE
			SYNTAX	INTEGER
			ACCESS	read-only
			STATUS	current
	DESCRIPTION ""
			::= { mbus54 16 }

mbus54Value05		OBJECT-TYPE
			SYNTAX	INTEGER
			ACCESS	read-only
			STATUS	current
	DESCRIPTION ""
			::= { mbus54 17 }

mbus54VIF06		OBJECT-TYPE
			SYNTAX	INTEGER
			ACCESS	read-only
			STATUS	current
	DESCRIPTION ""
			::= { mbus54 18 }

mbus54Value06		OBJECT-TYPE
			SYNTAX	INTEGER
			ACCESS	read-only
			STATUS	current
	DESCRIPTION ""
			::= { mbus54 19 }

mbus54VIF07		OBJECT-TYPE
			SYNTAX	INTEGER
			ACCESS	read-only
			STATUS	current
	DESCRIPTION ""
			::= { mbus54 20 }

mbus54Value07		OBJECT-TYPE
			SYNTAX	INTEGER
			ACCESS	read-only
			STATUS	current
	DESCRIPTION ""
			::= { mbus54 21 }

mbus54VIF08		OBJECT-TYPE
			SYNTAX	INTEGER
			ACCESS	read-only
			STATUS	current
	DESCRIPTION ""
			::= { mbus54 22 }

mbus54Value08		OBJECT-TYPE
			SYNTAX	INTEGER
			ACCESS	read-only
			STATUS	current
	DESCRIPTION ""
			::= { mbus54 23 }

mbus54VIF09		OBJECT-TYPE
			SYNTAX	INTEGER
			ACCESS	read-only
			STATUS	current
	DESCRIPTION ""
			::= { mbus54 24 }

mbus54Value09		OBJECT-TYPE
			SYNTAX	INTEGER
			ACCESS	read-only
			STATUS	current
	DESCRIPTION ""
			::= { mbus54 25 }

mbus54VIF0A		OBJECT-TYPE
			SYNTAX	INTEGER
			ACCESS	read-only
			STATUS	current
	DESCRIPTION ""
			::= { mbus54 26 }

mbus54Value0A		OBJECT-TYPE
			SYNTAX	INTEGER
			ACCESS	read-only
			STATUS	current
	DESCRIPTION ""
			::= { mbus54 27 }

mbus54VIF0B		OBJECT-TYPE
			SYNTAX	INTEGER
			ACCESS	read-only
			STATUS	current
	DESCRIPTION ""
			::= { mbus54 28 }

mbus54Value0B		OBJECT-TYPE
			SYNTAX	INTEGER
			ACCESS	read-only
			STATUS	current
	DESCRIPTION ""
			::= { mbus54 29 }

mbus54VIF0C		OBJECT-TYPE
			SYNTAX	INTEGER
			ACCESS	read-only
			STATUS	current
	DESCRIPTION ""
			::= { mbus54 30 }

mbus54Value0C		OBJECT-TYPE
			SYNTAX	INTEGER
			ACCESS	read-only
			STATUS	current
	DESCRIPTION ""
			::= { mbus54 31 }

mbus54VIF0D		OBJECT-TYPE
			SYNTAX	INTEGER
			ACCESS	read-only
			STATUS	current
	DESCRIPTION ""
			::= { mbus54 32 }

mbus54Value0D		OBJECT-TYPE
			SYNTAX	INTEGER
			ACCESS	read-only
			STATUS	current
	DESCRIPTION ""
			::= { mbus54 33 }

mbus54VIF0E		OBJECT-TYPE
			SYNTAX	INTEGER
			ACCESS	read-only
			STATUS	current
	DESCRIPTION ""
			::= { mbus54 34 }

mbus54Value0E		OBJECT-TYPE
			SYNTAX	INTEGER
			ACCESS	read-only
			STATUS	current
	DESCRIPTION ""
			::= { mbus54 35 }

mbus54VIF0F		OBJECT-TYPE
			SYNTAX	INTEGER
			ACCESS	read-only
			STATUS	current
	DESCRIPTION ""
			::= { mbus54 36 }

mbus54Value0F		OBJECT-TYPE
			SYNTAX	INTEGER
			ACCESS	read-only
			STATUS	current
	DESCRIPTION ""
			::= { mbus54 37 }

mbus54VIF10		OBJECT-TYPE
			SYNTAX	INTEGER
			ACCESS	read-only
			STATUS	current
	DESCRIPTION ""
			::= { mbus54 38 }

mbus54Value10		OBJECT-TYPE
			SYNTAX	INTEGER
			ACCESS	read-only
			STATUS	current
	DESCRIPTION ""
			::= { mbus54 39 }

mbus54VIF11		OBJECT-TYPE
			SYNTAX	INTEGER
			ACCESS	read-only
			STATUS	current
	DESCRIPTION ""
			::= { mbus54 40 }

mbus54Value11		OBJECT-TYPE
			SYNTAX	INTEGER
			ACCESS	read-only
			STATUS	current
	DESCRIPTION ""
			::= { mbus54 41 }

mbus54VIF12		OBJECT-TYPE
			SYNTAX	INTEGER
			ACCESS	read-only
			STATUS	current
	DESCRIPTION ""
			::= { mbus54 42 }

mbus54Value12		OBJECT-TYPE
			SYNTAX	INTEGER
			ACCESS	read-only
			STATUS	current
	DESCRIPTION ""
			::= { mbus54 43 }

mbus54VIF13		OBJECT-TYPE
			SYNTAX	INTEGER
			ACCESS	read-only
			STATUS	current
	DESCRIPTION ""
			::= { mbus54 44 }

mbus54Value13		OBJECT-TYPE
			SYNTAX	INTEGER
			ACCESS	read-only
			STATUS	current
	DESCRIPTION ""
			::= { mbus54 45 }

mbus54VIF14		OBJECT-TYPE
			SYNTAX	INTEGER
			ACCESS	read-only
			STATUS	current
	DESCRIPTION ""
			::= { mbus54 46 }

mbus54Value14		OBJECT-TYPE
			SYNTAX	INTEGER
			ACCESS	read-only
			STATUS	current
	DESCRIPTION ""
			::= { mbus54 47 }

mbus54VIF15		OBJECT-TYPE
			SYNTAX	INTEGER
			ACCESS	read-only
			STATUS	current
	DESCRIPTION ""
			::= { mbus54 48 }

mbus54Value15		OBJECT-TYPE
			SYNTAX	INTEGER
			ACCESS	read-only
			STATUS	current
	DESCRIPTION ""
			::= { mbus54 49 }

mbus54VIF16		OBJECT-TYPE
			SYNTAX	INTEGER
			ACCESS	read-only
			STATUS	current
	DESCRIPTION ""
			::= { mbus54 50 }

mbus54Value16		OBJECT-TYPE
			SYNTAX	INTEGER
			ACCESS	read-only
			STATUS	current
	DESCRIPTION ""
			::= { mbus54 51 }

mbus54VIF17		OBJECT-TYPE
			SYNTAX	INTEGER
			ACCESS	read-only
			STATUS	current
	DESCRIPTION ""
			::= { mbus54 52 }

mbus54Value17		OBJECT-TYPE
			SYNTAX	INTEGER
			ACCESS	read-only
			STATUS	current
	DESCRIPTION ""
			::= { mbus54 53 }

mbus54VIF18		OBJECT-TYPE
			SYNTAX	INTEGER
			ACCESS	read-only
			STATUS	current
	DESCRIPTION ""
			::= { mbus54 54 }

mbus54Value18		OBJECT-TYPE
			SYNTAX	INTEGER
			ACCESS	read-only
			STATUS	current
	DESCRIPTION ""
			::= { mbus54 55 }

mbus54VIF19		OBJECT-TYPE
			SYNTAX	INTEGER
			ACCESS	read-only
			STATUS	current
	DESCRIPTION ""
			::= { mbus54 56 }

mbus54Value19		OBJECT-TYPE
			SYNTAX	INTEGER
			ACCESS	read-only
			STATUS	current
	DESCRIPTION ""
			::= { mbus54 57 }

mbus54VIF1A		OBJECT-TYPE
			SYNTAX	INTEGER
			ACCESS	read-only
			STATUS	current
	DESCRIPTION ""
			::= { mbus54 58 }

mbus54Value1A		OBJECT-TYPE
			SYNTAX	INTEGER
			ACCESS	read-only
			STATUS	current
	DESCRIPTION ""
			::= { mbus54 59 }

mbus54VIF1B		OBJECT-TYPE
			SYNTAX	INTEGER
			ACCESS	read-only
			STATUS	current
	DESCRIPTION ""
			::= { mbus54 60 }

mbus54Value1B		OBJECT-TYPE
			SYNTAX	INTEGER
			ACCESS	read-only
			STATUS	current
	DESCRIPTION ""
			::= { mbus54 61 }

mbus54VIF1C		OBJECT-TYPE
			SYNTAX	INTEGER
			ACCESS	read-only
			STATUS	current
	DESCRIPTION ""
			::= { mbus54 62 }

mbus54Value1C		OBJECT-TYPE
			SYNTAX	INTEGER
			ACCESS	read-only
			STATUS	current
	DESCRIPTION ""
			::= { mbus54 63 }

mbus54VIF1D		OBJECT-TYPE
			SYNTAX	INTEGER
			ACCESS	read-only
			STATUS	current
	DESCRIPTION ""
			::= { mbus54 64 }

mbus54Value1D		OBJECT-TYPE
			SYNTAX	INTEGER
			ACCESS	read-only
			STATUS	current
	DESCRIPTION ""
			::= { mbus54 65 }

mbus54VIF1E		OBJECT-TYPE
			SYNTAX	INTEGER
			ACCESS	read-only
			STATUS	current
	DESCRIPTION ""
			::= { mbus54 66 }

mbus54Value1E		OBJECT-TYPE
			SYNTAX	INTEGER
			ACCESS	read-only
			STATUS	current
	DESCRIPTION ""
			::= { mbus54 67 }

mbus54VIF1F		OBJECT-TYPE
			SYNTAX	INTEGER
			ACCESS	read-only
			STATUS	current
	DESCRIPTION ""
			::= { mbus54 68 }

mbus54Value1F		OBJECT-TYPE
			SYNTAX	INTEGER
			ACCESS	read-only
			STATUS	current
	DESCRIPTION ""
			::= { mbus54 69 }

mbus54VIF20		OBJECT-TYPE
			SYNTAX	INTEGER
			ACCESS	read-only
			STATUS	current
	DESCRIPTION ""
			::= { mbus54 70 }

mbus54Value20		OBJECT-TYPE
			SYNTAX	INTEGER
			ACCESS	read-only
			STATUS	current
	DESCRIPTION ""
			::= { mbus54 71 }

mbus54VIF21		OBJECT-TYPE
			SYNTAX	INTEGER
			ACCESS	read-only
			STATUS	current
	DESCRIPTION ""
			::= { mbus54 72 }

mbus54Value21		OBJECT-TYPE
			SYNTAX	INTEGER
			ACCESS	read-only
			STATUS	current
	DESCRIPTION ""
			::= { mbus54 73 }

mbus54VIF22		OBJECT-TYPE
			SYNTAX	INTEGER
			ACCESS	read-only
			STATUS	current
	DESCRIPTION ""
			::= { mbus54 74 }

mbus54Value22		OBJECT-TYPE
			SYNTAX	INTEGER
			ACCESS	read-only
			STATUS	current
	DESCRIPTION ""
			::= { mbus54 75 }

mbus54VIF23		OBJECT-TYPE
			SYNTAX	INTEGER
			ACCESS	read-only
			STATUS	current
	DESCRIPTION ""
			::= { mbus54 76 }

mbus54Value23		OBJECT-TYPE
			SYNTAX	INTEGER
			ACCESS	read-only
			STATUS	current
	DESCRIPTION ""
			::= { mbus54 77 }

mbus54VIF24		OBJECT-TYPE
			SYNTAX	INTEGER
			ACCESS	read-only
			STATUS	current
	DESCRIPTION ""
			::= { mbus54 78 }

mbus54Value24		OBJECT-TYPE
			SYNTAX	INTEGER
			ACCESS	read-only
			STATUS	current
	DESCRIPTION ""
			::= { mbus54 79 }

mbus54VIF25		OBJECT-TYPE
			SYNTAX	INTEGER
			ACCESS	read-only
			STATUS	current
	DESCRIPTION ""
			::= { mbus54 80 }

mbus54Value25		OBJECT-TYPE
			SYNTAX	INTEGER
			ACCESS	read-only
			STATUS	current
	DESCRIPTION ""
			::= { mbus54 81 }

mbus54VIF26		OBJECT-TYPE
			SYNTAX	INTEGER
			ACCESS	read-only
			STATUS	current
	DESCRIPTION ""
			::= { mbus54 82 }

mbus54Value26		OBJECT-TYPE
			SYNTAX	INTEGER
			ACCESS	read-only
			STATUS	current
	DESCRIPTION ""
			::= { mbus54 83 }

mbus54VIF27		OBJECT-TYPE
			SYNTAX	INTEGER
			ACCESS	read-only
			STATUS	current
	DESCRIPTION ""
			::= { mbus54 84 }

mbus54Value27		OBJECT-TYPE
			SYNTAX	INTEGER
			ACCESS	read-only
			STATUS	current
	DESCRIPTION ""
			::= { mbus54 85 }

mbus54VIF28		OBJECT-TYPE
			SYNTAX	INTEGER
			ACCESS	read-only
			STATUS	current
	DESCRIPTION ""
			::= { mbus54 86 }

mbus54Value28		OBJECT-TYPE
			SYNTAX	INTEGER
			ACCESS	read-only
			STATUS	current
	DESCRIPTION ""
			::= { mbus54 87 }

mbus54VIF29		OBJECT-TYPE
			SYNTAX	INTEGER
			ACCESS	read-only
			STATUS	current
	DESCRIPTION ""
			::= { mbus54 88 }

mbus54Value29		OBJECT-TYPE
			SYNTAX	INTEGER
			ACCESS	read-only
			STATUS	current
	DESCRIPTION ""
			::= { mbus54 89 }

mbus54VIF2A		OBJECT-TYPE
			SYNTAX	INTEGER
			ACCESS	read-only
			STATUS	current
	DESCRIPTION ""
			::= { mbus54 90 }

mbus54Value2A		OBJECT-TYPE
			SYNTAX	INTEGER
			ACCESS	read-only
			STATUS	current
	DESCRIPTION ""
			::= { mbus54 91 }

mbus54VIF2B		OBJECT-TYPE
			SYNTAX	INTEGER
			ACCESS	read-only
			STATUS	current
	DESCRIPTION ""
			::= { mbus54 92 }

mbus54Value2B		OBJECT-TYPE
			SYNTAX	INTEGER
			ACCESS	read-only
			STATUS	current
	DESCRIPTION ""
			::= { mbus54 93 }

mbus54VIF2C		OBJECT-TYPE
			SYNTAX	INTEGER
			ACCESS	read-only
			STATUS	current
	DESCRIPTION ""
			::= { mbus54 94 }

mbus54Value2C		OBJECT-TYPE
			SYNTAX	INTEGER
			ACCESS	read-only
			STATUS	current
	DESCRIPTION ""
			::= { mbus54 95 }

mbus54VIF2D		OBJECT-TYPE
			SYNTAX	INTEGER
			ACCESS	read-only
			STATUS	current
	DESCRIPTION ""
			::= { mbus54 96 }

mbus54Value2D		OBJECT-TYPE
			SYNTAX	INTEGER
			ACCESS	read-only
			STATUS	current
	DESCRIPTION ""
			::= { mbus54 97 }

mbus54VIF2E		OBJECT-TYPE
			SYNTAX	INTEGER
			ACCESS	read-only
			STATUS	current
	DESCRIPTION ""
			::= { mbus54 98 }

mbus54Value2E		OBJECT-TYPE
			SYNTAX	INTEGER
			ACCESS	read-only
			STATUS	current
	DESCRIPTION ""
			::= { mbus54 99 }

mbus54VIF2F		OBJECT-TYPE
			SYNTAX	INTEGER
			ACCESS	read-only
			STATUS	current
	DESCRIPTION ""
			::= { mbus54 100 }

mbus54Value2F		OBJECT-TYPE
			SYNTAX	INTEGER
			ACCESS	read-only
			STATUS	current
	DESCRIPTION ""
			::= { mbus54 101 }

mbus55			OBJECT IDENTIFIER ::= { mbus 85 }

mbus55IdNumber		OBJECT-TYPE
			SYNTAX	Gauge
			ACCESS	read-only
			STATUS	current
	DESCRIPTION ""
			::= { mbus55 1 }

mbus55Manufacturer	OBJECT-TYPE
			SYNTAX	Gauge
			ACCESS	read-only
			STATUS	current
	DESCRIPTION ""
			::= { mbus55 2 }

mbus55Version		OBJECT-TYPE
			SYNTAX	Gauge
			ACCESS	read-only
			STATUS	current
	DESCRIPTION ""
			::= { mbus55 3 }

mbus55Medium		OBJECT-TYPE
			SYNTAX	Gauge
			ACCESS	read-only
			STATUS	current
	DESCRIPTION ""
			::= { mbus55 4 }

mbus55Status		OBJECT-TYPE
			SYNTAX	Gauge
			ACCESS	read-only
			STATUS	current
	DESCRIPTION ""
			::= { mbus55 5 }

mbus55VIF00		OBJECT-TYPE
			SYNTAX	INTEGER
			ACCESS	read-only
			STATUS	current
	DESCRIPTION ""
			::= { mbus55 6 }

mbus55Value00		OBJECT-TYPE
			SYNTAX	INTEGER
			ACCESS	read-only
			STATUS	current
	DESCRIPTION ""
			::= { mbus55 7 }

mbus55VIF01		OBJECT-TYPE
			SYNTAX	INTEGER
			ACCESS	read-only
			STATUS	current
	DESCRIPTION ""
			::= { mbus55 8 }

mbus55Value01		OBJECT-TYPE
			SYNTAX	INTEGER
			ACCESS	read-only
			STATUS	current
	DESCRIPTION ""
			::= { mbus55 9 }

mbus55VIF02		OBJECT-TYPE
			SYNTAX	INTEGER
			ACCESS	read-only
			STATUS	current
	DESCRIPTION ""
			::= { mbus55 10 }

mbus55Value02		OBJECT-TYPE
			SYNTAX	INTEGER
			ACCESS	read-only
			STATUS	current
	DESCRIPTION ""
			::= { mbus55 11 }

mbus55VIF03		OBJECT-TYPE
			SYNTAX	INTEGER
			ACCESS	read-only
			STATUS	current
	DESCRIPTION ""
			::= { mbus55 12 }

mbus55Value03		OBJECT-TYPE
			SYNTAX	INTEGER
			ACCESS	read-only
			STATUS	current
	DESCRIPTION ""
			::= { mbus55 13 }

mbus55VIF04		OBJECT-TYPE
			SYNTAX	INTEGER
			ACCESS	read-only
			STATUS	current
	DESCRIPTION ""
			::= { mbus55 14 }

mbus55Value04		OBJECT-TYPE
			SYNTAX	INTEGER
			ACCESS	read-only
			STATUS	current
	DESCRIPTION ""
			::= { mbus55 15 }

mbus55VIF05		OBJECT-TYPE
			SYNTAX	INTEGER
			ACCESS	read-only
			STATUS	current
	DESCRIPTION ""
			::= { mbus55 16 }

mbus55Value05		OBJECT-TYPE
			SYNTAX	INTEGER
			ACCESS	read-only
			STATUS	current
	DESCRIPTION ""
			::= { mbus55 17 }

mbus55VIF06		OBJECT-TYPE
			SYNTAX	INTEGER
			ACCESS	read-only
			STATUS	current
	DESCRIPTION ""
			::= { mbus55 18 }

mbus55Value06		OBJECT-TYPE
			SYNTAX	INTEGER
			ACCESS	read-only
			STATUS	current
	DESCRIPTION ""
			::= { mbus55 19 }

mbus55VIF07		OBJECT-TYPE
			SYNTAX	INTEGER
			ACCESS	read-only
			STATUS	current
	DESCRIPTION ""
			::= { mbus55 20 }

mbus55Value07		OBJECT-TYPE
			SYNTAX	INTEGER
			ACCESS	read-only
			STATUS	current
	DESCRIPTION ""
			::= { mbus55 21 }

mbus55VIF08		OBJECT-TYPE
			SYNTAX	INTEGER
			ACCESS	read-only
			STATUS	current
	DESCRIPTION ""
			::= { mbus55 22 }

mbus55Value08		OBJECT-TYPE
			SYNTAX	INTEGER
			ACCESS	read-only
			STATUS	current
	DESCRIPTION ""
			::= { mbus55 23 }

mbus55VIF09		OBJECT-TYPE
			SYNTAX	INTEGER
			ACCESS	read-only
			STATUS	current
	DESCRIPTION ""
			::= { mbus55 24 }

mbus55Value09		OBJECT-TYPE
			SYNTAX	INTEGER
			ACCESS	read-only
			STATUS	current
	DESCRIPTION ""
			::= { mbus55 25 }

mbus55VIF0A		OBJECT-TYPE
			SYNTAX	INTEGER
			ACCESS	read-only
			STATUS	current
	DESCRIPTION ""
			::= { mbus55 26 }

mbus55Value0A		OBJECT-TYPE
			SYNTAX	INTEGER
			ACCESS	read-only
			STATUS	current
	DESCRIPTION ""
			::= { mbus55 27 }

mbus55VIF0B		OBJECT-TYPE
			SYNTAX	INTEGER
			ACCESS	read-only
			STATUS	current
	DESCRIPTION ""
			::= { mbus55 28 }

mbus55Value0B		OBJECT-TYPE
			SYNTAX	INTEGER
			ACCESS	read-only
			STATUS	current
	DESCRIPTION ""
			::= { mbus55 29 }

mbus55VIF0C		OBJECT-TYPE
			SYNTAX	INTEGER
			ACCESS	read-only
			STATUS	current
	DESCRIPTION ""
			::= { mbus55 30 }

mbus55Value0C		OBJECT-TYPE
			SYNTAX	INTEGER
			ACCESS	read-only
			STATUS	current
	DESCRIPTION ""
			::= { mbus55 31 }

mbus55VIF0D		OBJECT-TYPE
			SYNTAX	INTEGER
			ACCESS	read-only
			STATUS	current
	DESCRIPTION ""
			::= { mbus55 32 }

mbus55Value0D		OBJECT-TYPE
			SYNTAX	INTEGER
			ACCESS	read-only
			STATUS	current
	DESCRIPTION ""
			::= { mbus55 33 }

mbus55VIF0E		OBJECT-TYPE
			SYNTAX	INTEGER
			ACCESS	read-only
			STATUS	current
	DESCRIPTION ""
			::= { mbus55 34 }

mbus55Value0E		OBJECT-TYPE
			SYNTAX	INTEGER
			ACCESS	read-only
			STATUS	current
	DESCRIPTION ""
			::= { mbus55 35 }

mbus55VIF0F		OBJECT-TYPE
			SYNTAX	INTEGER
			ACCESS	read-only
			STATUS	current
	DESCRIPTION ""
			::= { mbus55 36 }

mbus55Value0F		OBJECT-TYPE
			SYNTAX	INTEGER
			ACCESS	read-only
			STATUS	current
	DESCRIPTION ""
			::= { mbus55 37 }

mbus55VIF10		OBJECT-TYPE
			SYNTAX	INTEGER
			ACCESS	read-only
			STATUS	current
	DESCRIPTION ""
			::= { mbus55 38 }

mbus55Value10		OBJECT-TYPE
			SYNTAX	INTEGER
			ACCESS	read-only
			STATUS	current
	DESCRIPTION ""
			::= { mbus55 39 }

mbus55VIF11		OBJECT-TYPE
			SYNTAX	INTEGER
			ACCESS	read-only
			STATUS	current
	DESCRIPTION ""
			::= { mbus55 40 }

mbus55Value11		OBJECT-TYPE
			SYNTAX	INTEGER
			ACCESS	read-only
			STATUS	current
	DESCRIPTION ""
			::= { mbus55 41 }

mbus55VIF12		OBJECT-TYPE
			SYNTAX	INTEGER
			ACCESS	read-only
			STATUS	current
	DESCRIPTION ""
			::= { mbus55 42 }

mbus55Value12		OBJECT-TYPE
			SYNTAX	INTEGER
			ACCESS	read-only
			STATUS	current
	DESCRIPTION ""
			::= { mbus55 43 }

mbus55VIF13		OBJECT-TYPE
			SYNTAX	INTEGER
			ACCESS	read-only
			STATUS	current
	DESCRIPTION ""
			::= { mbus55 44 }

mbus55Value13		OBJECT-TYPE
			SYNTAX	INTEGER
			ACCESS	read-only
			STATUS	current
	DESCRIPTION ""
			::= { mbus55 45 }

mbus55VIF14		OBJECT-TYPE
			SYNTAX	INTEGER
			ACCESS	read-only
			STATUS	current
	DESCRIPTION ""
			::= { mbus55 46 }

mbus55Value14		OBJECT-TYPE
			SYNTAX	INTEGER
			ACCESS	read-only
			STATUS	current
	DESCRIPTION ""
			::= { mbus55 47 }

mbus55VIF15		OBJECT-TYPE
			SYNTAX	INTEGER
			ACCESS	read-only
			STATUS	current
	DESCRIPTION ""
			::= { mbus55 48 }

mbus55Value15		OBJECT-TYPE
			SYNTAX	INTEGER
			ACCESS	read-only
			STATUS	current
	DESCRIPTION ""
			::= { mbus55 49 }

mbus55VIF16		OBJECT-TYPE
			SYNTAX	INTEGER
			ACCESS	read-only
			STATUS	current
	DESCRIPTION ""
			::= { mbus55 50 }

mbus55Value16		OBJECT-TYPE
			SYNTAX	INTEGER
			ACCESS	read-only
			STATUS	current
	DESCRIPTION ""
			::= { mbus55 51 }

mbus55VIF17		OBJECT-TYPE
			SYNTAX	INTEGER
			ACCESS	read-only
			STATUS	current
	DESCRIPTION ""
			::= { mbus55 52 }

mbus55Value17		OBJECT-TYPE
			SYNTAX	INTEGER
			ACCESS	read-only
			STATUS	current
	DESCRIPTION ""
			::= { mbus55 53 }

mbus55VIF18		OBJECT-TYPE
			SYNTAX	INTEGER
			ACCESS	read-only
			STATUS	current
	DESCRIPTION ""
			::= { mbus55 54 }

mbus55Value18		OBJECT-TYPE
			SYNTAX	INTEGER
			ACCESS	read-only
			STATUS	current
	DESCRIPTION ""
			::= { mbus55 55 }

mbus55VIF19		OBJECT-TYPE
			SYNTAX	INTEGER
			ACCESS	read-only
			STATUS	current
	DESCRIPTION ""
			::= { mbus55 56 }

mbus55Value19		OBJECT-TYPE
			SYNTAX	INTEGER
			ACCESS	read-only
			STATUS	current
	DESCRIPTION ""
			::= { mbus55 57 }

mbus55VIF1A		OBJECT-TYPE
			SYNTAX	INTEGER
			ACCESS	read-only
			STATUS	current
	DESCRIPTION ""
			::= { mbus55 58 }

mbus55Value1A		OBJECT-TYPE
			SYNTAX	INTEGER
			ACCESS	read-only
			STATUS	current
	DESCRIPTION ""
			::= { mbus55 59 }

mbus55VIF1B		OBJECT-TYPE
			SYNTAX	INTEGER
			ACCESS	read-only
			STATUS	current
	DESCRIPTION ""
			::= { mbus55 60 }

mbus55Value1B		OBJECT-TYPE
			SYNTAX	INTEGER
			ACCESS	read-only
			STATUS	current
	DESCRIPTION ""
			::= { mbus55 61 }

mbus55VIF1C		OBJECT-TYPE
			SYNTAX	INTEGER
			ACCESS	read-only
			STATUS	current
	DESCRIPTION ""
			::= { mbus55 62 }

mbus55Value1C		OBJECT-TYPE
			SYNTAX	INTEGER
			ACCESS	read-only
			STATUS	current
	DESCRIPTION ""
			::= { mbus55 63 }

mbus55VIF1D		OBJECT-TYPE
			SYNTAX	INTEGER
			ACCESS	read-only
			STATUS	current
	DESCRIPTION ""
			::= { mbus55 64 }

mbus55Value1D		OBJECT-TYPE
			SYNTAX	INTEGER
			ACCESS	read-only
			STATUS	current
	DESCRIPTION ""
			::= { mbus55 65 }

mbus55VIF1E		OBJECT-TYPE
			SYNTAX	INTEGER
			ACCESS	read-only
			STATUS	current
	DESCRIPTION ""
			::= { mbus55 66 }

mbus55Value1E		OBJECT-TYPE
			SYNTAX	INTEGER
			ACCESS	read-only
			STATUS	current
	DESCRIPTION ""
			::= { mbus55 67 }

mbus55VIF1F		OBJECT-TYPE
			SYNTAX	INTEGER
			ACCESS	read-only
			STATUS	current
	DESCRIPTION ""
			::= { mbus55 68 }

mbus55Value1F		OBJECT-TYPE
			SYNTAX	INTEGER
			ACCESS	read-only
			STATUS	current
	DESCRIPTION ""
			::= { mbus55 69 }

mbus55VIF20		OBJECT-TYPE
			SYNTAX	INTEGER
			ACCESS	read-only
			STATUS	current
	DESCRIPTION ""
			::= { mbus55 70 }

mbus55Value20		OBJECT-TYPE
			SYNTAX	INTEGER
			ACCESS	read-only
			STATUS	current
	DESCRIPTION ""
			::= { mbus55 71 }

mbus55VIF21		OBJECT-TYPE
			SYNTAX	INTEGER
			ACCESS	read-only
			STATUS	current
	DESCRIPTION ""
			::= { mbus55 72 }

mbus55Value21		OBJECT-TYPE
			SYNTAX	INTEGER
			ACCESS	read-only
			STATUS	current
	DESCRIPTION ""
			::= { mbus55 73 }

mbus55VIF22		OBJECT-TYPE
			SYNTAX	INTEGER
			ACCESS	read-only
			STATUS	current
	DESCRIPTION ""
			::= { mbus55 74 }

mbus55Value22		OBJECT-TYPE
			SYNTAX	INTEGER
			ACCESS	read-only
			STATUS	current
	DESCRIPTION ""
			::= { mbus55 75 }

mbus55VIF23		OBJECT-TYPE
			SYNTAX	INTEGER
			ACCESS	read-only
			STATUS	current
	DESCRIPTION ""
			::= { mbus55 76 }

mbus55Value23		OBJECT-TYPE
			SYNTAX	INTEGER
			ACCESS	read-only
			STATUS	current
	DESCRIPTION ""
			::= { mbus55 77 }

mbus55VIF24		OBJECT-TYPE
			SYNTAX	INTEGER
			ACCESS	read-only
			STATUS	current
	DESCRIPTION ""
			::= { mbus55 78 }

mbus55Value24		OBJECT-TYPE
			SYNTAX	INTEGER
			ACCESS	read-only
			STATUS	current
	DESCRIPTION ""
			::= { mbus55 79 }

mbus55VIF25		OBJECT-TYPE
			SYNTAX	INTEGER
			ACCESS	read-only
			STATUS	current
	DESCRIPTION ""
			::= { mbus55 80 }

mbus55Value25		OBJECT-TYPE
			SYNTAX	INTEGER
			ACCESS	read-only
			STATUS	current
	DESCRIPTION ""
			::= { mbus55 81 }

mbus55VIF26		OBJECT-TYPE
			SYNTAX	INTEGER
			ACCESS	read-only
			STATUS	current
	DESCRIPTION ""
			::= { mbus55 82 }

mbus55Value26		OBJECT-TYPE
			SYNTAX	INTEGER
			ACCESS	read-only
			STATUS	current
	DESCRIPTION ""
			::= { mbus55 83 }

mbus55VIF27		OBJECT-TYPE
			SYNTAX	INTEGER
			ACCESS	read-only
			STATUS	current
	DESCRIPTION ""
			::= { mbus55 84 }

mbus55Value27		OBJECT-TYPE
			SYNTAX	INTEGER
			ACCESS	read-only
			STATUS	current
	DESCRIPTION ""
			::= { mbus55 85 }

mbus55VIF28		OBJECT-TYPE
			SYNTAX	INTEGER
			ACCESS	read-only
			STATUS	current
	DESCRIPTION ""
			::= { mbus55 86 }

mbus55Value28		OBJECT-TYPE
			SYNTAX	INTEGER
			ACCESS	read-only
			STATUS	current
	DESCRIPTION ""
			::= { mbus55 87 }

mbus55VIF29		OBJECT-TYPE
			SYNTAX	INTEGER
			ACCESS	read-only
			STATUS	current
	DESCRIPTION ""
			::= { mbus55 88 }

mbus55Value29		OBJECT-TYPE
			SYNTAX	INTEGER
			ACCESS	read-only
			STATUS	current
	DESCRIPTION ""
			::= { mbus55 89 }

mbus55VIF2A		OBJECT-TYPE
			SYNTAX	INTEGER
			ACCESS	read-only
			STATUS	current
	DESCRIPTION ""
			::= { mbus55 90 }

mbus55Value2A		OBJECT-TYPE
			SYNTAX	INTEGER
			ACCESS	read-only
			STATUS	current
	DESCRIPTION ""
			::= { mbus55 91 }

mbus55VIF2B		OBJECT-TYPE
			SYNTAX	INTEGER
			ACCESS	read-only
			STATUS	current
	DESCRIPTION ""
			::= { mbus55 92 }

mbus55Value2B		OBJECT-TYPE
			SYNTAX	INTEGER
			ACCESS	read-only
			STATUS	current
	DESCRIPTION ""
			::= { mbus55 93 }

mbus55VIF2C		OBJECT-TYPE
			SYNTAX	INTEGER
			ACCESS	read-only
			STATUS	current
	DESCRIPTION ""
			::= { mbus55 94 }

mbus55Value2C		OBJECT-TYPE
			SYNTAX	INTEGER
			ACCESS	read-only
			STATUS	current
	DESCRIPTION ""
			::= { mbus55 95 }

mbus55VIF2D		OBJECT-TYPE
			SYNTAX	INTEGER
			ACCESS	read-only
			STATUS	current
	DESCRIPTION ""
			::= { mbus55 96 }

mbus55Value2D		OBJECT-TYPE
			SYNTAX	INTEGER
			ACCESS	read-only
			STATUS	current
	DESCRIPTION ""
			::= { mbus55 97 }

mbus55VIF2E		OBJECT-TYPE
			SYNTAX	INTEGER
			ACCESS	read-only
			STATUS	current
	DESCRIPTION ""
			::= { mbus55 98 }

mbus55Value2E		OBJECT-TYPE
			SYNTAX	INTEGER
			ACCESS	read-only
			STATUS	current
	DESCRIPTION ""
			::= { mbus55 99 }

mbus55VIF2F		OBJECT-TYPE
			SYNTAX	INTEGER
			ACCESS	read-only
			STATUS	current
	DESCRIPTION ""
			::= { mbus55 100 }

mbus55Value2F		OBJECT-TYPE
			SYNTAX	INTEGER
			ACCESS	read-only
			STATUS	current
	DESCRIPTION ""
			::= { mbus55 101 }

mbus56			OBJECT IDENTIFIER ::= { mbus 86 }

mbus56IdNumber		OBJECT-TYPE
			SYNTAX	Gauge
			ACCESS	read-only
			STATUS	current
	DESCRIPTION ""
			::= { mbus56 1 }

mbus56Manufacturer	OBJECT-TYPE
			SYNTAX	Gauge
			ACCESS	read-only
			STATUS	current
	DESCRIPTION ""
			::= { mbus56 2 }

mbus56Version		OBJECT-TYPE
			SYNTAX	Gauge
			ACCESS	read-only
			STATUS	current
	DESCRIPTION ""
			::= { mbus56 3 }

mbus56Medium		OBJECT-TYPE
			SYNTAX	Gauge
			ACCESS	read-only
			STATUS	current
	DESCRIPTION ""
			::= { mbus56 4 }

mbus56Status		OBJECT-TYPE
			SYNTAX	Gauge
			ACCESS	read-only
			STATUS	current
	DESCRIPTION ""
			::= { mbus56 5 }

mbus56VIF00		OBJECT-TYPE
			SYNTAX	INTEGER
			ACCESS	read-only
			STATUS	current
	DESCRIPTION ""
			::= { mbus56 6 }

mbus56Value00		OBJECT-TYPE
			SYNTAX	INTEGER
			ACCESS	read-only
			STATUS	current
	DESCRIPTION ""
			::= { mbus56 7 }

mbus56VIF01		OBJECT-TYPE
			SYNTAX	INTEGER
			ACCESS	read-only
			STATUS	current
	DESCRIPTION ""
			::= { mbus56 8 }

mbus56Value01		OBJECT-TYPE
			SYNTAX	INTEGER
			ACCESS	read-only
			STATUS	current
	DESCRIPTION ""
			::= { mbus56 9 }

mbus56VIF02		OBJECT-TYPE
			SYNTAX	INTEGER
			ACCESS	read-only
			STATUS	current
	DESCRIPTION ""
			::= { mbus56 10 }

mbus56Value02		OBJECT-TYPE
			SYNTAX	INTEGER
			ACCESS	read-only
			STATUS	current
	DESCRIPTION ""
			::= { mbus56 11 }

mbus56VIF03		OBJECT-TYPE
			SYNTAX	INTEGER
			ACCESS	read-only
			STATUS	current
	DESCRIPTION ""
			::= { mbus56 12 }

mbus56Value03		OBJECT-TYPE
			SYNTAX	INTEGER
			ACCESS	read-only
			STATUS	current
	DESCRIPTION ""
			::= { mbus56 13 }

mbus56VIF04		OBJECT-TYPE
			SYNTAX	INTEGER
			ACCESS	read-only
			STATUS	current
	DESCRIPTION ""
			::= { mbus56 14 }

mbus56Value04		OBJECT-TYPE
			SYNTAX	INTEGER
			ACCESS	read-only
			STATUS	current
	DESCRIPTION ""
			::= { mbus56 15 }

mbus56VIF05		OBJECT-TYPE
			SYNTAX	INTEGER
			ACCESS	read-only
			STATUS	current
	DESCRIPTION ""
			::= { mbus56 16 }

mbus56Value05		OBJECT-TYPE
			SYNTAX	INTEGER
			ACCESS	read-only
			STATUS	current
	DESCRIPTION ""
			::= { mbus56 17 }

mbus56VIF06		OBJECT-TYPE
			SYNTAX	INTEGER
			ACCESS	read-only
			STATUS	current
	DESCRIPTION ""
			::= { mbus56 18 }

mbus56Value06		OBJECT-TYPE
			SYNTAX	INTEGER
			ACCESS	read-only
			STATUS	current
	DESCRIPTION ""
			::= { mbus56 19 }

mbus56VIF07		OBJECT-TYPE
			SYNTAX	INTEGER
			ACCESS	read-only
			STATUS	current
	DESCRIPTION ""
			::= { mbus56 20 }

mbus56Value07		OBJECT-TYPE
			SYNTAX	INTEGER
			ACCESS	read-only
			STATUS	current
	DESCRIPTION ""
			::= { mbus56 21 }

mbus56VIF08		OBJECT-TYPE
			SYNTAX	INTEGER
			ACCESS	read-only
			STATUS	current
	DESCRIPTION ""
			::= { mbus56 22 }

mbus56Value08		OBJECT-TYPE
			SYNTAX	INTEGER
			ACCESS	read-only
			STATUS	current
	DESCRIPTION ""
			::= { mbus56 23 }

mbus56VIF09		OBJECT-TYPE
			SYNTAX	INTEGER
			ACCESS	read-only
			STATUS	current
	DESCRIPTION ""
			::= { mbus56 24 }

mbus56Value09		OBJECT-TYPE
			SYNTAX	INTEGER
			ACCESS	read-only
			STATUS	current
	DESCRIPTION ""
			::= { mbus56 25 }

mbus56VIF0A		OBJECT-TYPE
			SYNTAX	INTEGER
			ACCESS	read-only
			STATUS	current
	DESCRIPTION ""
			::= { mbus56 26 }

mbus56Value0A		OBJECT-TYPE
			SYNTAX	INTEGER
			ACCESS	read-only
			STATUS	current
	DESCRIPTION ""
			::= { mbus56 27 }

mbus56VIF0B		OBJECT-TYPE
			SYNTAX	INTEGER
			ACCESS	read-only
			STATUS	current
	DESCRIPTION ""
			::= { mbus56 28 }

mbus56Value0B		OBJECT-TYPE
			SYNTAX	INTEGER
			ACCESS	read-only
			STATUS	current
	DESCRIPTION ""
			::= { mbus56 29 }

mbus56VIF0C		OBJECT-TYPE
			SYNTAX	INTEGER
			ACCESS	read-only
			STATUS	current
	DESCRIPTION ""
			::= { mbus56 30 }

mbus56Value0C		OBJECT-TYPE
			SYNTAX	INTEGER
			ACCESS	read-only
			STATUS	current
	DESCRIPTION ""
			::= { mbus56 31 }

mbus56VIF0D		OBJECT-TYPE
			SYNTAX	INTEGER
			ACCESS	read-only
			STATUS	current
	DESCRIPTION ""
			::= { mbus56 32 }

mbus56Value0D		OBJECT-TYPE
			SYNTAX	INTEGER
			ACCESS	read-only
			STATUS	current
	DESCRIPTION ""
			::= { mbus56 33 }

mbus56VIF0E		OBJECT-TYPE
			SYNTAX	INTEGER
			ACCESS	read-only
			STATUS	current
	DESCRIPTION ""
			::= { mbus56 34 }

mbus56Value0E		OBJECT-TYPE
			SYNTAX	INTEGER
			ACCESS	read-only
			STATUS	current
	DESCRIPTION ""
			::= { mbus56 35 }

mbus56VIF0F		OBJECT-TYPE
			SYNTAX	INTEGER
			ACCESS	read-only
			STATUS	current
	DESCRIPTION ""
			::= { mbus56 36 }

mbus56Value0F		OBJECT-TYPE
			SYNTAX	INTEGER
			ACCESS	read-only
			STATUS	current
	DESCRIPTION ""
			::= { mbus56 37 }

mbus56VIF10		OBJECT-TYPE
			SYNTAX	INTEGER
			ACCESS	read-only
			STATUS	current
	DESCRIPTION ""
			::= { mbus56 38 }

mbus56Value10		OBJECT-TYPE
			SYNTAX	INTEGER
			ACCESS	read-only
			STATUS	current
	DESCRIPTION ""
			::= { mbus56 39 }

mbus56VIF11		OBJECT-TYPE
			SYNTAX	INTEGER
			ACCESS	read-only
			STATUS	current
	DESCRIPTION ""
			::= { mbus56 40 }

mbus56Value11		OBJECT-TYPE
			SYNTAX	INTEGER
			ACCESS	read-only
			STATUS	current
	DESCRIPTION ""
			::= { mbus56 41 }

mbus56VIF12		OBJECT-TYPE
			SYNTAX	INTEGER
			ACCESS	read-only
			STATUS	current
	DESCRIPTION ""
			::= { mbus56 42 }

mbus56Value12		OBJECT-TYPE
			SYNTAX	INTEGER
			ACCESS	read-only
			STATUS	current
	DESCRIPTION ""
			::= { mbus56 43 }

mbus56VIF13		OBJECT-TYPE
			SYNTAX	INTEGER
			ACCESS	read-only
			STATUS	current
	DESCRIPTION ""
			::= { mbus56 44 }

mbus56Value13		OBJECT-TYPE
			SYNTAX	INTEGER
			ACCESS	read-only
			STATUS	current
	DESCRIPTION ""
			::= { mbus56 45 }

mbus56VIF14		OBJECT-TYPE
			SYNTAX	INTEGER
			ACCESS	read-only
			STATUS	current
	DESCRIPTION ""
			::= { mbus56 46 }

mbus56Value14		OBJECT-TYPE
			SYNTAX	INTEGER
			ACCESS	read-only
			STATUS	current
	DESCRIPTION ""
			::= { mbus56 47 }

mbus56VIF15		OBJECT-TYPE
			SYNTAX	INTEGER
			ACCESS	read-only
			STATUS	current
	DESCRIPTION ""
			::= { mbus56 48 }

mbus56Value15		OBJECT-TYPE
			SYNTAX	INTEGER
			ACCESS	read-only
			STATUS	current
	DESCRIPTION ""
			::= { mbus56 49 }

mbus56VIF16		OBJECT-TYPE
			SYNTAX	INTEGER
			ACCESS	read-only
			STATUS	current
	DESCRIPTION ""
			::= { mbus56 50 }

mbus56Value16		OBJECT-TYPE
			SYNTAX	INTEGER
			ACCESS	read-only
			STATUS	current
	DESCRIPTION ""
			::= { mbus56 51 }

mbus56VIF17		OBJECT-TYPE
			SYNTAX	INTEGER
			ACCESS	read-only
			STATUS	current
	DESCRIPTION ""
			::= { mbus56 52 }

mbus56Value17		OBJECT-TYPE
			SYNTAX	INTEGER
			ACCESS	read-only
			STATUS	current
	DESCRIPTION ""
			::= { mbus56 53 }

mbus56VIF18		OBJECT-TYPE
			SYNTAX	INTEGER
			ACCESS	read-only
			STATUS	current
	DESCRIPTION ""
			::= { mbus56 54 }

mbus56Value18		OBJECT-TYPE
			SYNTAX	INTEGER
			ACCESS	read-only
			STATUS	current
	DESCRIPTION ""
			::= { mbus56 55 }

mbus56VIF19		OBJECT-TYPE
			SYNTAX	INTEGER
			ACCESS	read-only
			STATUS	current
	DESCRIPTION ""
			::= { mbus56 56 }

mbus56Value19		OBJECT-TYPE
			SYNTAX	INTEGER
			ACCESS	read-only
			STATUS	current
	DESCRIPTION ""
			::= { mbus56 57 }

mbus56VIF1A		OBJECT-TYPE
			SYNTAX	INTEGER
			ACCESS	read-only
			STATUS	current
	DESCRIPTION ""
			::= { mbus56 58 }

mbus56Value1A		OBJECT-TYPE
			SYNTAX	INTEGER
			ACCESS	read-only
			STATUS	current
	DESCRIPTION ""
			::= { mbus56 59 }

mbus56VIF1B		OBJECT-TYPE
			SYNTAX	INTEGER
			ACCESS	read-only
			STATUS	current
	DESCRIPTION ""
			::= { mbus56 60 }

mbus56Value1B		OBJECT-TYPE
			SYNTAX	INTEGER
			ACCESS	read-only
			STATUS	current
	DESCRIPTION ""
			::= { mbus56 61 }

mbus56VIF1C		OBJECT-TYPE
			SYNTAX	INTEGER
			ACCESS	read-only
			STATUS	current
	DESCRIPTION ""
			::= { mbus56 62 }

mbus56Value1C		OBJECT-TYPE
			SYNTAX	INTEGER
			ACCESS	read-only
			STATUS	current
	DESCRIPTION ""
			::= { mbus56 63 }

mbus56VIF1D		OBJECT-TYPE
			SYNTAX	INTEGER
			ACCESS	read-only
			STATUS	current
	DESCRIPTION ""
			::= { mbus56 64 }

mbus56Value1D		OBJECT-TYPE
			SYNTAX	INTEGER
			ACCESS	read-only
			STATUS	current
	DESCRIPTION ""
			::= { mbus56 65 }

mbus56VIF1E		OBJECT-TYPE
			SYNTAX	INTEGER
			ACCESS	read-only
			STATUS	current
	DESCRIPTION ""
			::= { mbus56 66 }

mbus56Value1E		OBJECT-TYPE
			SYNTAX	INTEGER
			ACCESS	read-only
			STATUS	current
	DESCRIPTION ""
			::= { mbus56 67 }

mbus56VIF1F		OBJECT-TYPE
			SYNTAX	INTEGER
			ACCESS	read-only
			STATUS	current
	DESCRIPTION ""
			::= { mbus56 68 }

mbus56Value1F		OBJECT-TYPE
			SYNTAX	INTEGER
			ACCESS	read-only
			STATUS	current
	DESCRIPTION ""
			::= { mbus56 69 }

mbus56VIF20		OBJECT-TYPE
			SYNTAX	INTEGER
			ACCESS	read-only
			STATUS	current
	DESCRIPTION ""
			::= { mbus56 70 }

mbus56Value20		OBJECT-TYPE
			SYNTAX	INTEGER
			ACCESS	read-only
			STATUS	current
	DESCRIPTION ""
			::= { mbus56 71 }

mbus56VIF21		OBJECT-TYPE
			SYNTAX	INTEGER
			ACCESS	read-only
			STATUS	current
	DESCRIPTION ""
			::= { mbus56 72 }

mbus56Value21		OBJECT-TYPE
			SYNTAX	INTEGER
			ACCESS	read-only
			STATUS	current
	DESCRIPTION ""
			::= { mbus56 73 }

mbus56VIF22		OBJECT-TYPE
			SYNTAX	INTEGER
			ACCESS	read-only
			STATUS	current
	DESCRIPTION ""
			::= { mbus56 74 }

mbus56Value22		OBJECT-TYPE
			SYNTAX	INTEGER
			ACCESS	read-only
			STATUS	current
	DESCRIPTION ""
			::= { mbus56 75 }

mbus56VIF23		OBJECT-TYPE
			SYNTAX	INTEGER
			ACCESS	read-only
			STATUS	current
	DESCRIPTION ""
			::= { mbus56 76 }

mbus56Value23		OBJECT-TYPE
			SYNTAX	INTEGER
			ACCESS	read-only
			STATUS	current
	DESCRIPTION ""
			::= { mbus56 77 }

mbus56VIF24		OBJECT-TYPE
			SYNTAX	INTEGER
			ACCESS	read-only
			STATUS	current
	DESCRIPTION ""
			::= { mbus56 78 }

mbus56Value24		OBJECT-TYPE
			SYNTAX	INTEGER
			ACCESS	read-only
			STATUS	current
	DESCRIPTION ""
			::= { mbus56 79 }

mbus56VIF25		OBJECT-TYPE
			SYNTAX	INTEGER
			ACCESS	read-only
			STATUS	current
	DESCRIPTION ""
			::= { mbus56 80 }

mbus56Value25		OBJECT-TYPE
			SYNTAX	INTEGER
			ACCESS	read-only
			STATUS	current
	DESCRIPTION ""
			::= { mbus56 81 }

mbus56VIF26		OBJECT-TYPE
			SYNTAX	INTEGER
			ACCESS	read-only
			STATUS	current
	DESCRIPTION ""
			::= { mbus56 82 }

mbus56Value26		OBJECT-TYPE
			SYNTAX	INTEGER
			ACCESS	read-only
			STATUS	current
	DESCRIPTION ""
			::= { mbus56 83 }

mbus56VIF27		OBJECT-TYPE
			SYNTAX	INTEGER
			ACCESS	read-only
			STATUS	current
	DESCRIPTION ""
			::= { mbus56 84 }

mbus56Value27		OBJECT-TYPE
			SYNTAX	INTEGER
			ACCESS	read-only
			STATUS	current
	DESCRIPTION ""
			::= { mbus56 85 }

mbus56VIF28		OBJECT-TYPE
			SYNTAX	INTEGER
			ACCESS	read-only
			STATUS	current
	DESCRIPTION ""
			::= { mbus56 86 }

mbus56Value28		OBJECT-TYPE
			SYNTAX	INTEGER
			ACCESS	read-only
			STATUS	current
	DESCRIPTION ""
			::= { mbus56 87 }

mbus56VIF29		OBJECT-TYPE
			SYNTAX	INTEGER
			ACCESS	read-only
			STATUS	current
	DESCRIPTION ""
			::= { mbus56 88 }

mbus56Value29		OBJECT-TYPE
			SYNTAX	INTEGER
			ACCESS	read-only
			STATUS	current
	DESCRIPTION ""
			::= { mbus56 89 }

mbus56VIF2A		OBJECT-TYPE
			SYNTAX	INTEGER
			ACCESS	read-only
			STATUS	current
	DESCRIPTION ""
			::= { mbus56 90 }

mbus56Value2A		OBJECT-TYPE
			SYNTAX	INTEGER
			ACCESS	read-only
			STATUS	current
	DESCRIPTION ""
			::= { mbus56 91 }

mbus56VIF2B		OBJECT-TYPE
			SYNTAX	INTEGER
			ACCESS	read-only
			STATUS	current
	DESCRIPTION ""
			::= { mbus56 92 }

mbus56Value2B		OBJECT-TYPE
			SYNTAX	INTEGER
			ACCESS	read-only
			STATUS	current
	DESCRIPTION ""
			::= { mbus56 93 }

mbus56VIF2C		OBJECT-TYPE
			SYNTAX	INTEGER
			ACCESS	read-only
			STATUS	current
	DESCRIPTION ""
			::= { mbus56 94 }

mbus56Value2C		OBJECT-TYPE
			SYNTAX	INTEGER
			ACCESS	read-only
			STATUS	current
	DESCRIPTION ""
			::= { mbus56 95 }

mbus56VIF2D		OBJECT-TYPE
			SYNTAX	INTEGER
			ACCESS	read-only
			STATUS	current
	DESCRIPTION ""
			::= { mbus56 96 }

mbus56Value2D		OBJECT-TYPE
			SYNTAX	INTEGER
			ACCESS	read-only
			STATUS	current
	DESCRIPTION ""
			::= { mbus56 97 }

mbus56VIF2E		OBJECT-TYPE
			SYNTAX	INTEGER
			ACCESS	read-only
			STATUS	current
	DESCRIPTION ""
			::= { mbus56 98 }

mbus56Value2E		OBJECT-TYPE
			SYNTAX	INTEGER
			ACCESS	read-only
			STATUS	current
	DESCRIPTION ""
			::= { mbus56 99 }

mbus56VIF2F		OBJECT-TYPE
			SYNTAX	INTEGER
			ACCESS	read-only
			STATUS	current
	DESCRIPTION ""
			::= { mbus56 100 }

mbus56Value2F		OBJECT-TYPE
			SYNTAX	INTEGER
			ACCESS	read-only
			STATUS	current
	DESCRIPTION ""
			::= { mbus56 101 }

mbus57			OBJECT IDENTIFIER ::= { mbus 87 }

mbus57IdNumber		OBJECT-TYPE
			SYNTAX	Gauge
			ACCESS	read-only
			STATUS	current
	DESCRIPTION ""
			::= { mbus57 1 }

mbus57Manufacturer	OBJECT-TYPE
			SYNTAX	Gauge
			ACCESS	read-only
			STATUS	current
	DESCRIPTION ""
			::= { mbus57 2 }

mbus57Version		OBJECT-TYPE
			SYNTAX	Gauge
			ACCESS	read-only
			STATUS	current
	DESCRIPTION ""
			::= { mbus57 3 }

mbus57Medium		OBJECT-TYPE
			SYNTAX	Gauge
			ACCESS	read-only
			STATUS	current
	DESCRIPTION ""
			::= { mbus57 4 }

mbus57Status		OBJECT-TYPE
			SYNTAX	Gauge
			ACCESS	read-only
			STATUS	current
	DESCRIPTION ""
			::= { mbus57 5 }

mbus57VIF00		OBJECT-TYPE
			SYNTAX	INTEGER
			ACCESS	read-only
			STATUS	current
	DESCRIPTION ""
			::= { mbus57 6 }

mbus57Value00		OBJECT-TYPE
			SYNTAX	INTEGER
			ACCESS	read-only
			STATUS	current
	DESCRIPTION ""
			::= { mbus57 7 }

mbus57VIF01		OBJECT-TYPE
			SYNTAX	INTEGER
			ACCESS	read-only
			STATUS	current
	DESCRIPTION ""
			::= { mbus57 8 }

mbus57Value01		OBJECT-TYPE
			SYNTAX	INTEGER
			ACCESS	read-only
			STATUS	current
	DESCRIPTION ""
			::= { mbus57 9 }

mbus57VIF02		OBJECT-TYPE
			SYNTAX	INTEGER
			ACCESS	read-only
			STATUS	current
	DESCRIPTION ""
			::= { mbus57 10 }

mbus57Value02		OBJECT-TYPE
			SYNTAX	INTEGER
			ACCESS	read-only
			STATUS	current
	DESCRIPTION ""
			::= { mbus57 11 }

mbus57VIF03		OBJECT-TYPE
			SYNTAX	INTEGER
			ACCESS	read-only
			STATUS	current
	DESCRIPTION ""
			::= { mbus57 12 }

mbus57Value03		OBJECT-TYPE
			SYNTAX	INTEGER
			ACCESS	read-only
			STATUS	current
	DESCRIPTION ""
			::= { mbus57 13 }

mbus57VIF04		OBJECT-TYPE
			SYNTAX	INTEGER
			ACCESS	read-only
			STATUS	current
	DESCRIPTION ""
			::= { mbus57 14 }

mbus57Value04		OBJECT-TYPE
			SYNTAX	INTEGER
			ACCESS	read-only
			STATUS	current
	DESCRIPTION ""
			::= { mbus57 15 }

mbus57VIF05		OBJECT-TYPE
			SYNTAX	INTEGER
			ACCESS	read-only
			STATUS	current
	DESCRIPTION ""
			::= { mbus57 16 }

mbus57Value05		OBJECT-TYPE
			SYNTAX	INTEGER
			ACCESS	read-only
			STATUS	current
	DESCRIPTION ""
			::= { mbus57 17 }

mbus57VIF06		OBJECT-TYPE
			SYNTAX	INTEGER
			ACCESS	read-only
			STATUS	current
	DESCRIPTION ""
			::= { mbus57 18 }

mbus57Value06		OBJECT-TYPE
			SYNTAX	INTEGER
			ACCESS	read-only
			STATUS	current
	DESCRIPTION ""
			::= { mbus57 19 }

mbus57VIF07		OBJECT-TYPE
			SYNTAX	INTEGER
			ACCESS	read-only
			STATUS	current
	DESCRIPTION ""
			::= { mbus57 20 }

mbus57Value07		OBJECT-TYPE
			SYNTAX	INTEGER
			ACCESS	read-only
			STATUS	current
	DESCRIPTION ""
			::= { mbus57 21 }

mbus57VIF08		OBJECT-TYPE
			SYNTAX	INTEGER
			ACCESS	read-only
			STATUS	current
	DESCRIPTION ""
			::= { mbus57 22 }

mbus57Value08		OBJECT-TYPE
			SYNTAX	INTEGER
			ACCESS	read-only
			STATUS	current
	DESCRIPTION ""
			::= { mbus57 23 }

mbus57VIF09		OBJECT-TYPE
			SYNTAX	INTEGER
			ACCESS	read-only
			STATUS	current
	DESCRIPTION ""
			::= { mbus57 24 }

mbus57Value09		OBJECT-TYPE
			SYNTAX	INTEGER
			ACCESS	read-only
			STATUS	current
	DESCRIPTION ""
			::= { mbus57 25 }

mbus57VIF0A		OBJECT-TYPE
			SYNTAX	INTEGER
			ACCESS	read-only
			STATUS	current
	DESCRIPTION ""
			::= { mbus57 26 }

mbus57Value0A		OBJECT-TYPE
			SYNTAX	INTEGER
			ACCESS	read-only
			STATUS	current
	DESCRIPTION ""
			::= { mbus57 27 }

mbus57VIF0B		OBJECT-TYPE
			SYNTAX	INTEGER
			ACCESS	read-only
			STATUS	current
	DESCRIPTION ""
			::= { mbus57 28 }

mbus57Value0B		OBJECT-TYPE
			SYNTAX	INTEGER
			ACCESS	read-only
			STATUS	current
	DESCRIPTION ""
			::= { mbus57 29 }

mbus57VIF0C		OBJECT-TYPE
			SYNTAX	INTEGER
			ACCESS	read-only
			STATUS	current
	DESCRIPTION ""
			::= { mbus57 30 }

mbus57Value0C		OBJECT-TYPE
			SYNTAX	INTEGER
			ACCESS	read-only
			STATUS	current
	DESCRIPTION ""
			::= { mbus57 31 }

mbus57VIF0D		OBJECT-TYPE
			SYNTAX	INTEGER
			ACCESS	read-only
			STATUS	current
	DESCRIPTION ""
			::= { mbus57 32 }

mbus57Value0D		OBJECT-TYPE
			SYNTAX	INTEGER
			ACCESS	read-only
			STATUS	current
	DESCRIPTION ""
			::= { mbus57 33 }

mbus57VIF0E		OBJECT-TYPE
			SYNTAX	INTEGER
			ACCESS	read-only
			STATUS	current
	DESCRIPTION ""
			::= { mbus57 34 }

mbus57Value0E		OBJECT-TYPE
			SYNTAX	INTEGER
			ACCESS	read-only
			STATUS	current
	DESCRIPTION ""
			::= { mbus57 35 }

mbus57VIF0F		OBJECT-TYPE
			SYNTAX	INTEGER
			ACCESS	read-only
			STATUS	current
	DESCRIPTION ""
			::= { mbus57 36 }

mbus57Value0F		OBJECT-TYPE
			SYNTAX	INTEGER
			ACCESS	read-only
			STATUS	current
	DESCRIPTION ""
			::= { mbus57 37 }

mbus57VIF10		OBJECT-TYPE
			SYNTAX	INTEGER
			ACCESS	read-only
			STATUS	current
	DESCRIPTION ""
			::= { mbus57 38 }

mbus57Value10		OBJECT-TYPE
			SYNTAX	INTEGER
			ACCESS	read-only
			STATUS	current
	DESCRIPTION ""
			::= { mbus57 39 }

mbus57VIF11		OBJECT-TYPE
			SYNTAX	INTEGER
			ACCESS	read-only
			STATUS	current
	DESCRIPTION ""
			::= { mbus57 40 }

mbus57Value11		OBJECT-TYPE
			SYNTAX	INTEGER
			ACCESS	read-only
			STATUS	current
	DESCRIPTION ""
			::= { mbus57 41 }

mbus57VIF12		OBJECT-TYPE
			SYNTAX	INTEGER
			ACCESS	read-only
			STATUS	current
	DESCRIPTION ""
			::= { mbus57 42 }

mbus57Value12		OBJECT-TYPE
			SYNTAX	INTEGER
			ACCESS	read-only
			STATUS	current
	DESCRIPTION ""
			::= { mbus57 43 }

mbus57VIF13		OBJECT-TYPE
			SYNTAX	INTEGER
			ACCESS	read-only
			STATUS	current
	DESCRIPTION ""
			::= { mbus57 44 }

mbus57Value13		OBJECT-TYPE
			SYNTAX	INTEGER
			ACCESS	read-only
			STATUS	current
	DESCRIPTION ""
			::= { mbus57 45 }

mbus57VIF14		OBJECT-TYPE
			SYNTAX	INTEGER
			ACCESS	read-only
			STATUS	current
	DESCRIPTION ""
			::= { mbus57 46 }

mbus57Value14		OBJECT-TYPE
			SYNTAX	INTEGER
			ACCESS	read-only
			STATUS	current
	DESCRIPTION ""
			::= { mbus57 47 }

mbus57VIF15		OBJECT-TYPE
			SYNTAX	INTEGER
			ACCESS	read-only
			STATUS	current
	DESCRIPTION ""
			::= { mbus57 48 }

mbus57Value15		OBJECT-TYPE
			SYNTAX	INTEGER
			ACCESS	read-only
			STATUS	current
	DESCRIPTION ""
			::= { mbus57 49 }

mbus57VIF16		OBJECT-TYPE
			SYNTAX	INTEGER
			ACCESS	read-only
			STATUS	current
	DESCRIPTION ""
			::= { mbus57 50 }

mbus57Value16		OBJECT-TYPE
			SYNTAX	INTEGER
			ACCESS	read-only
			STATUS	current
	DESCRIPTION ""
			::= { mbus57 51 }

mbus57VIF17		OBJECT-TYPE
			SYNTAX	INTEGER
			ACCESS	read-only
			STATUS	current
	DESCRIPTION ""
			::= { mbus57 52 }

mbus57Value17		OBJECT-TYPE
			SYNTAX	INTEGER
			ACCESS	read-only
			STATUS	current
	DESCRIPTION ""
			::= { mbus57 53 }

mbus57VIF18		OBJECT-TYPE
			SYNTAX	INTEGER
			ACCESS	read-only
			STATUS	current
	DESCRIPTION ""
			::= { mbus57 54 }

mbus57Value18		OBJECT-TYPE
			SYNTAX	INTEGER
			ACCESS	read-only
			STATUS	current
	DESCRIPTION ""
			::= { mbus57 55 }

mbus57VIF19		OBJECT-TYPE
			SYNTAX	INTEGER
			ACCESS	read-only
			STATUS	current
	DESCRIPTION ""
			::= { mbus57 56 }

mbus57Value19		OBJECT-TYPE
			SYNTAX	INTEGER
			ACCESS	read-only
			STATUS	current
	DESCRIPTION ""
			::= { mbus57 57 }

mbus57VIF1A		OBJECT-TYPE
			SYNTAX	INTEGER
			ACCESS	read-only
			STATUS	current
	DESCRIPTION ""
			::= { mbus57 58 }

mbus57Value1A		OBJECT-TYPE
			SYNTAX	INTEGER
			ACCESS	read-only
			STATUS	current
	DESCRIPTION ""
			::= { mbus57 59 }

mbus57VIF1B		OBJECT-TYPE
			SYNTAX	INTEGER
			ACCESS	read-only
			STATUS	current
	DESCRIPTION ""
			::= { mbus57 60 }

mbus57Value1B		OBJECT-TYPE
			SYNTAX	INTEGER
			ACCESS	read-only
			STATUS	current
	DESCRIPTION ""
			::= { mbus57 61 }

mbus57VIF1C		OBJECT-TYPE
			SYNTAX	INTEGER
			ACCESS	read-only
			STATUS	current
	DESCRIPTION ""
			::= { mbus57 62 }

mbus57Value1C		OBJECT-TYPE
			SYNTAX	INTEGER
			ACCESS	read-only
			STATUS	current
	DESCRIPTION ""
			::= { mbus57 63 }

mbus57VIF1D		OBJECT-TYPE
			SYNTAX	INTEGER
			ACCESS	read-only
			STATUS	current
	DESCRIPTION ""
			::= { mbus57 64 }

mbus57Value1D		OBJECT-TYPE
			SYNTAX	INTEGER
			ACCESS	read-only
			STATUS	current
	DESCRIPTION ""
			::= { mbus57 65 }

mbus57VIF1E		OBJECT-TYPE
			SYNTAX	INTEGER
			ACCESS	read-only
			STATUS	current
	DESCRIPTION ""
			::= { mbus57 66 }

mbus57Value1E		OBJECT-TYPE
			SYNTAX	INTEGER
			ACCESS	read-only
			STATUS	current
	DESCRIPTION ""
			::= { mbus57 67 }

mbus57VIF1F		OBJECT-TYPE
			SYNTAX	INTEGER
			ACCESS	read-only
			STATUS	current
	DESCRIPTION ""
			::= { mbus57 68 }

mbus57Value1F		OBJECT-TYPE
			SYNTAX	INTEGER
			ACCESS	read-only
			STATUS	current
	DESCRIPTION ""
			::= { mbus57 69 }

mbus57VIF20		OBJECT-TYPE
			SYNTAX	INTEGER
			ACCESS	read-only
			STATUS	current
	DESCRIPTION ""
			::= { mbus57 70 }

mbus57Value20		OBJECT-TYPE
			SYNTAX	INTEGER
			ACCESS	read-only
			STATUS	current
	DESCRIPTION ""
			::= { mbus57 71 }

mbus57VIF21		OBJECT-TYPE
			SYNTAX	INTEGER
			ACCESS	read-only
			STATUS	current
	DESCRIPTION ""
			::= { mbus57 72 }

mbus57Value21		OBJECT-TYPE
			SYNTAX	INTEGER
			ACCESS	read-only
			STATUS	current
	DESCRIPTION ""
			::= { mbus57 73 }

mbus57VIF22		OBJECT-TYPE
			SYNTAX	INTEGER
			ACCESS	read-only
			STATUS	current
	DESCRIPTION ""
			::= { mbus57 74 }

mbus57Value22		OBJECT-TYPE
			SYNTAX	INTEGER
			ACCESS	read-only
			STATUS	current
	DESCRIPTION ""
			::= { mbus57 75 }

mbus57VIF23		OBJECT-TYPE
			SYNTAX	INTEGER
			ACCESS	read-only
			STATUS	current
	DESCRIPTION ""
			::= { mbus57 76 }

mbus57Value23		OBJECT-TYPE
			SYNTAX	INTEGER
			ACCESS	read-only
			STATUS	current
	DESCRIPTION ""
			::= { mbus57 77 }

mbus57VIF24		OBJECT-TYPE
			SYNTAX	INTEGER
			ACCESS	read-only
			STATUS	current
	DESCRIPTION ""
			::= { mbus57 78 }

mbus57Value24		OBJECT-TYPE
			SYNTAX	INTEGER
			ACCESS	read-only
			STATUS	current
	DESCRIPTION ""
			::= { mbus57 79 }

mbus57VIF25		OBJECT-TYPE
			SYNTAX	INTEGER
			ACCESS	read-only
			STATUS	current
	DESCRIPTION ""
			::= { mbus57 80 }

mbus57Value25		OBJECT-TYPE
			SYNTAX	INTEGER
			ACCESS	read-only
			STATUS	current
	DESCRIPTION ""
			::= { mbus57 81 }

mbus57VIF26		OBJECT-TYPE
			SYNTAX	INTEGER
			ACCESS	read-only
			STATUS	current
	DESCRIPTION ""
			::= { mbus57 82 }

mbus57Value26		OBJECT-TYPE
			SYNTAX	INTEGER
			ACCESS	read-only
			STATUS	current
	DESCRIPTION ""
			::= { mbus57 83 }

mbus57VIF27		OBJECT-TYPE
			SYNTAX	INTEGER
			ACCESS	read-only
			STATUS	current
	DESCRIPTION ""
			::= { mbus57 84 }

mbus57Value27		OBJECT-TYPE
			SYNTAX	INTEGER
			ACCESS	read-only
			STATUS	current
	DESCRIPTION ""
			::= { mbus57 85 }

mbus57VIF28		OBJECT-TYPE
			SYNTAX	INTEGER
			ACCESS	read-only
			STATUS	current
	DESCRIPTION ""
			::= { mbus57 86 }

mbus57Value28		OBJECT-TYPE
			SYNTAX	INTEGER
			ACCESS	read-only
			STATUS	current
	DESCRIPTION ""
			::= { mbus57 87 }

mbus57VIF29		OBJECT-TYPE
			SYNTAX	INTEGER
			ACCESS	read-only
			STATUS	current
	DESCRIPTION ""
			::= { mbus57 88 }

mbus57Value29		OBJECT-TYPE
			SYNTAX	INTEGER
			ACCESS	read-only
			STATUS	current
	DESCRIPTION ""
			::= { mbus57 89 }

mbus57VIF2A		OBJECT-TYPE
			SYNTAX	INTEGER
			ACCESS	read-only
			STATUS	current
	DESCRIPTION ""
			::= { mbus57 90 }

mbus57Value2A		OBJECT-TYPE
			SYNTAX	INTEGER
			ACCESS	read-only
			STATUS	current
	DESCRIPTION ""
			::= { mbus57 91 }

mbus57VIF2B		OBJECT-TYPE
			SYNTAX	INTEGER
			ACCESS	read-only
			STATUS	current
	DESCRIPTION ""
			::= { mbus57 92 }

mbus57Value2B		OBJECT-TYPE
			SYNTAX	INTEGER
			ACCESS	read-only
			STATUS	current
	DESCRIPTION ""
			::= { mbus57 93 }

mbus57VIF2C		OBJECT-TYPE
			SYNTAX	INTEGER
			ACCESS	read-only
			STATUS	current
	DESCRIPTION ""
			::= { mbus57 94 }

mbus57Value2C		OBJECT-TYPE
			SYNTAX	INTEGER
			ACCESS	read-only
			STATUS	current
	DESCRIPTION ""
			::= { mbus57 95 }

mbus57VIF2D		OBJECT-TYPE
			SYNTAX	INTEGER
			ACCESS	read-only
			STATUS	current
	DESCRIPTION ""
			::= { mbus57 96 }

mbus57Value2D		OBJECT-TYPE
			SYNTAX	INTEGER
			ACCESS	read-only
			STATUS	current
	DESCRIPTION ""
			::= { mbus57 97 }

mbus57VIF2E		OBJECT-TYPE
			SYNTAX	INTEGER
			ACCESS	read-only
			STATUS	current
	DESCRIPTION ""
			::= { mbus57 98 }

mbus57Value2E		OBJECT-TYPE
			SYNTAX	INTEGER
			ACCESS	read-only
			STATUS	current
	DESCRIPTION ""
			::= { mbus57 99 }

mbus57VIF2F		OBJECT-TYPE
			SYNTAX	INTEGER
			ACCESS	read-only
			STATUS	current
	DESCRIPTION ""
			::= { mbus57 100 }

mbus57Value2F		OBJECT-TYPE
			SYNTAX	INTEGER
			ACCESS	read-only
			STATUS	current
	DESCRIPTION ""
			::= { mbus57 101 }

mbus58			OBJECT IDENTIFIER ::= { mbus 88 }

mbus58IdNumber		OBJECT-TYPE
			SYNTAX	Gauge
			ACCESS	read-only
			STATUS	current
	DESCRIPTION ""
			::= { mbus58 1 }

mbus58Manufacturer	OBJECT-TYPE
			SYNTAX	Gauge
			ACCESS	read-only
			STATUS	current
	DESCRIPTION ""
			::= { mbus58 2 }

mbus58Version		OBJECT-TYPE
			SYNTAX	Gauge
			ACCESS	read-only
			STATUS	current
	DESCRIPTION ""
			::= { mbus58 3 }

mbus58Medium		OBJECT-TYPE
			SYNTAX	Gauge
			ACCESS	read-only
			STATUS	current
	DESCRIPTION ""
			::= { mbus58 4 }

mbus58Status		OBJECT-TYPE
			SYNTAX	Gauge
			ACCESS	read-only
			STATUS	current
	DESCRIPTION ""
			::= { mbus58 5 }

mbus58VIF00		OBJECT-TYPE
			SYNTAX	INTEGER
			ACCESS	read-only
			STATUS	current
	DESCRIPTION ""
			::= { mbus58 6 }

mbus58Value00		OBJECT-TYPE
			SYNTAX	INTEGER
			ACCESS	read-only
			STATUS	current
	DESCRIPTION ""
			::= { mbus58 7 }

mbus58VIF01		OBJECT-TYPE
			SYNTAX	INTEGER
			ACCESS	read-only
			STATUS	current
	DESCRIPTION ""
			::= { mbus58 8 }

mbus58Value01		OBJECT-TYPE
			SYNTAX	INTEGER
			ACCESS	read-only
			STATUS	current
	DESCRIPTION ""
			::= { mbus58 9 }

mbus58VIF02		OBJECT-TYPE
			SYNTAX	INTEGER
			ACCESS	read-only
			STATUS	current
	DESCRIPTION ""
			::= { mbus58 10 }

mbus58Value02		OBJECT-TYPE
			SYNTAX	INTEGER
			ACCESS	read-only
			STATUS	current
	DESCRIPTION ""
			::= { mbus58 11 }

mbus58VIF03		OBJECT-TYPE
			SYNTAX	INTEGER
			ACCESS	read-only
			STATUS	current
	DESCRIPTION ""
			::= { mbus58 12 }

mbus58Value03		OBJECT-TYPE
			SYNTAX	INTEGER
			ACCESS	read-only
			STATUS	current
	DESCRIPTION ""
			::= { mbus58 13 }

mbus58VIF04		OBJECT-TYPE
			SYNTAX	INTEGER
			ACCESS	read-only
			STATUS	current
	DESCRIPTION ""
			::= { mbus58 14 }

mbus58Value04		OBJECT-TYPE
			SYNTAX	INTEGER
			ACCESS	read-only
			STATUS	current
	DESCRIPTION ""
			::= { mbus58 15 }

mbus58VIF05		OBJECT-TYPE
			SYNTAX	INTEGER
			ACCESS	read-only
			STATUS	current
	DESCRIPTION ""
			::= { mbus58 16 }

mbus58Value05		OBJECT-TYPE
			SYNTAX	INTEGER
			ACCESS	read-only
			STATUS	current
	DESCRIPTION ""
			::= { mbus58 17 }

mbus58VIF06		OBJECT-TYPE
			SYNTAX	INTEGER
			ACCESS	read-only
			STATUS	current
	DESCRIPTION ""
			::= { mbus58 18 }

mbus58Value06		OBJECT-TYPE
			SYNTAX	INTEGER
			ACCESS	read-only
			STATUS	current
	DESCRIPTION ""
			::= { mbus58 19 }

mbus58VIF07		OBJECT-TYPE
			SYNTAX	INTEGER
			ACCESS	read-only
			STATUS	current
	DESCRIPTION ""
			::= { mbus58 20 }

mbus58Value07		OBJECT-TYPE
			SYNTAX	INTEGER
			ACCESS	read-only
			STATUS	current
	DESCRIPTION ""
			::= { mbus58 21 }

mbus58VIF08		OBJECT-TYPE
			SYNTAX	INTEGER
			ACCESS	read-only
			STATUS	current
	DESCRIPTION ""
			::= { mbus58 22 }

mbus58Value08		OBJECT-TYPE
			SYNTAX	INTEGER
			ACCESS	read-only
			STATUS	current
	DESCRIPTION ""
			::= { mbus58 23 }

mbus58VIF09		OBJECT-TYPE
			SYNTAX	INTEGER
			ACCESS	read-only
			STATUS	current
	DESCRIPTION ""
			::= { mbus58 24 }

mbus58Value09		OBJECT-TYPE
			SYNTAX	INTEGER
			ACCESS	read-only
			STATUS	current
	DESCRIPTION ""
			::= { mbus58 25 }

mbus58VIF0A		OBJECT-TYPE
			SYNTAX	INTEGER
			ACCESS	read-only
			STATUS	current
	DESCRIPTION ""
			::= { mbus58 26 }

mbus58Value0A		OBJECT-TYPE
			SYNTAX	INTEGER
			ACCESS	read-only
			STATUS	current
	DESCRIPTION ""
			::= { mbus58 27 }

mbus58VIF0B		OBJECT-TYPE
			SYNTAX	INTEGER
			ACCESS	read-only
			STATUS	current
	DESCRIPTION ""
			::= { mbus58 28 }

mbus58Value0B		OBJECT-TYPE
			SYNTAX	INTEGER
			ACCESS	read-only
			STATUS	current
	DESCRIPTION ""
			::= { mbus58 29 }

mbus58VIF0C		OBJECT-TYPE
			SYNTAX	INTEGER
			ACCESS	read-only
			STATUS	current
	DESCRIPTION ""
			::= { mbus58 30 }

mbus58Value0C		OBJECT-TYPE
			SYNTAX	INTEGER
			ACCESS	read-only
			STATUS	current
	DESCRIPTION ""
			::= { mbus58 31 }

mbus58VIF0D		OBJECT-TYPE
			SYNTAX	INTEGER
			ACCESS	read-only
			STATUS	current
	DESCRIPTION ""
			::= { mbus58 32 }

mbus58Value0D		OBJECT-TYPE
			SYNTAX	INTEGER
			ACCESS	read-only
			STATUS	current
	DESCRIPTION ""
			::= { mbus58 33 }

mbus58VIF0E		OBJECT-TYPE
			SYNTAX	INTEGER
			ACCESS	read-only
			STATUS	current
	DESCRIPTION ""
			::= { mbus58 34 }

mbus58Value0E		OBJECT-TYPE
			SYNTAX	INTEGER
			ACCESS	read-only
			STATUS	current
	DESCRIPTION ""
			::= { mbus58 35 }

mbus58VIF0F		OBJECT-TYPE
			SYNTAX	INTEGER
			ACCESS	read-only
			STATUS	current
	DESCRIPTION ""
			::= { mbus58 36 }

mbus58Value0F		OBJECT-TYPE
			SYNTAX	INTEGER
			ACCESS	read-only
			STATUS	current
	DESCRIPTION ""
			::= { mbus58 37 }

mbus58VIF10		OBJECT-TYPE
			SYNTAX	INTEGER
			ACCESS	read-only
			STATUS	current
	DESCRIPTION ""
			::= { mbus58 38 }

mbus58Value10		OBJECT-TYPE
			SYNTAX	INTEGER
			ACCESS	read-only
			STATUS	current
	DESCRIPTION ""
			::= { mbus58 39 }

mbus58VIF11		OBJECT-TYPE
			SYNTAX	INTEGER
			ACCESS	read-only
			STATUS	current
	DESCRIPTION ""
			::= { mbus58 40 }

mbus58Value11		OBJECT-TYPE
			SYNTAX	INTEGER
			ACCESS	read-only
			STATUS	current
	DESCRIPTION ""
			::= { mbus58 41 }

mbus58VIF12		OBJECT-TYPE
			SYNTAX	INTEGER
			ACCESS	read-only
			STATUS	current
	DESCRIPTION ""
			::= { mbus58 42 }

mbus58Value12		OBJECT-TYPE
			SYNTAX	INTEGER
			ACCESS	read-only
			STATUS	current
	DESCRIPTION ""
			::= { mbus58 43 }

mbus58VIF13		OBJECT-TYPE
			SYNTAX	INTEGER
			ACCESS	read-only
			STATUS	current
	DESCRIPTION ""
			::= { mbus58 44 }

mbus58Value13		OBJECT-TYPE
			SYNTAX	INTEGER
			ACCESS	read-only
			STATUS	current
	DESCRIPTION ""
			::= { mbus58 45 }

mbus58VIF14		OBJECT-TYPE
			SYNTAX	INTEGER
			ACCESS	read-only
			STATUS	current
	DESCRIPTION ""
			::= { mbus58 46 }

mbus58Value14		OBJECT-TYPE
			SYNTAX	INTEGER
			ACCESS	read-only
			STATUS	current
	DESCRIPTION ""
			::= { mbus58 47 }

mbus58VIF15		OBJECT-TYPE
			SYNTAX	INTEGER
			ACCESS	read-only
			STATUS	current
	DESCRIPTION ""
			::= { mbus58 48 }

mbus58Value15		OBJECT-TYPE
			SYNTAX	INTEGER
			ACCESS	read-only
			STATUS	current
	DESCRIPTION ""
			::= { mbus58 49 }

mbus58VIF16		OBJECT-TYPE
			SYNTAX	INTEGER
			ACCESS	read-only
			STATUS	current
	DESCRIPTION ""
			::= { mbus58 50 }

mbus58Value16		OBJECT-TYPE
			SYNTAX	INTEGER
			ACCESS	read-only
			STATUS	current
	DESCRIPTION ""
			::= { mbus58 51 }

mbus58VIF17		OBJECT-TYPE
			SYNTAX	INTEGER
			ACCESS	read-only
			STATUS	current
	DESCRIPTION ""
			::= { mbus58 52 }

mbus58Value17		OBJECT-TYPE
			SYNTAX	INTEGER
			ACCESS	read-only
			STATUS	current
	DESCRIPTION ""
			::= { mbus58 53 }

mbus58VIF18		OBJECT-TYPE
			SYNTAX	INTEGER
			ACCESS	read-only
			STATUS	current
	DESCRIPTION ""
			::= { mbus58 54 }

mbus58Value18		OBJECT-TYPE
			SYNTAX	INTEGER
			ACCESS	read-only
			STATUS	current
	DESCRIPTION ""
			::= { mbus58 55 }

mbus58VIF19		OBJECT-TYPE
			SYNTAX	INTEGER
			ACCESS	read-only
			STATUS	current
	DESCRIPTION ""
			::= { mbus58 56 }

mbus58Value19		OBJECT-TYPE
			SYNTAX	INTEGER
			ACCESS	read-only
			STATUS	current
	DESCRIPTION ""
			::= { mbus58 57 }

mbus58VIF1A		OBJECT-TYPE
			SYNTAX	INTEGER
			ACCESS	read-only
			STATUS	current
	DESCRIPTION ""
			::= { mbus58 58 }

mbus58Value1A		OBJECT-TYPE
			SYNTAX	INTEGER
			ACCESS	read-only
			STATUS	current
	DESCRIPTION ""
			::= { mbus58 59 }

mbus58VIF1B		OBJECT-TYPE
			SYNTAX	INTEGER
			ACCESS	read-only
			STATUS	current
	DESCRIPTION ""
			::= { mbus58 60 }

mbus58Value1B		OBJECT-TYPE
			SYNTAX	INTEGER
			ACCESS	read-only
			STATUS	current
	DESCRIPTION ""
			::= { mbus58 61 }

mbus58VIF1C		OBJECT-TYPE
			SYNTAX	INTEGER
			ACCESS	read-only
			STATUS	current
	DESCRIPTION ""
			::= { mbus58 62 }

mbus58Value1C		OBJECT-TYPE
			SYNTAX	INTEGER
			ACCESS	read-only
			STATUS	current
	DESCRIPTION ""
			::= { mbus58 63 }

mbus58VIF1D		OBJECT-TYPE
			SYNTAX	INTEGER
			ACCESS	read-only
			STATUS	current
	DESCRIPTION ""
			::= { mbus58 64 }

mbus58Value1D		OBJECT-TYPE
			SYNTAX	INTEGER
			ACCESS	read-only
			STATUS	current
	DESCRIPTION ""
			::= { mbus58 65 }

mbus58VIF1E		OBJECT-TYPE
			SYNTAX	INTEGER
			ACCESS	read-only
			STATUS	current
	DESCRIPTION ""
			::= { mbus58 66 }

mbus58Value1E		OBJECT-TYPE
			SYNTAX	INTEGER
			ACCESS	read-only
			STATUS	current
	DESCRIPTION ""
			::= { mbus58 67 }

mbus58VIF1F		OBJECT-TYPE
			SYNTAX	INTEGER
			ACCESS	read-only
			STATUS	current
	DESCRIPTION ""
			::= { mbus58 68 }

mbus58Value1F		OBJECT-TYPE
			SYNTAX	INTEGER
			ACCESS	read-only
			STATUS	current
	DESCRIPTION ""
			::= { mbus58 69 }

mbus58VIF20		OBJECT-TYPE
			SYNTAX	INTEGER
			ACCESS	read-only
			STATUS	current
	DESCRIPTION ""
			::= { mbus58 70 }

mbus58Value20		OBJECT-TYPE
			SYNTAX	INTEGER
			ACCESS	read-only
			STATUS	current
	DESCRIPTION ""
			::= { mbus58 71 }

mbus58VIF21		OBJECT-TYPE
			SYNTAX	INTEGER
			ACCESS	read-only
			STATUS	current
	DESCRIPTION ""
			::= { mbus58 72 }

mbus58Value21		OBJECT-TYPE
			SYNTAX	INTEGER
			ACCESS	read-only
			STATUS	current
	DESCRIPTION ""
			::= { mbus58 73 }

mbus58VIF22		OBJECT-TYPE
			SYNTAX	INTEGER
			ACCESS	read-only
			STATUS	current
	DESCRIPTION ""
			::= { mbus58 74 }

mbus58Value22		OBJECT-TYPE
			SYNTAX	INTEGER
			ACCESS	read-only
			STATUS	current
	DESCRIPTION ""
			::= { mbus58 75 }

mbus58VIF23		OBJECT-TYPE
			SYNTAX	INTEGER
			ACCESS	read-only
			STATUS	current
	DESCRIPTION ""
			::= { mbus58 76 }

mbus58Value23		OBJECT-TYPE
			SYNTAX	INTEGER
			ACCESS	read-only
			STATUS	current
	DESCRIPTION ""
			::= { mbus58 77 }

mbus58VIF24		OBJECT-TYPE
			SYNTAX	INTEGER
			ACCESS	read-only
			STATUS	current
	DESCRIPTION ""
			::= { mbus58 78 }

mbus58Value24		OBJECT-TYPE
			SYNTAX	INTEGER
			ACCESS	read-only
			STATUS	current
	DESCRIPTION ""
			::= { mbus58 79 }

mbus58VIF25		OBJECT-TYPE
			SYNTAX	INTEGER
			ACCESS	read-only
			STATUS	current
	DESCRIPTION ""
			::= { mbus58 80 }

mbus58Value25		OBJECT-TYPE
			SYNTAX	INTEGER
			ACCESS	read-only
			STATUS	current
	DESCRIPTION ""
			::= { mbus58 81 }

mbus58VIF26		OBJECT-TYPE
			SYNTAX	INTEGER
			ACCESS	read-only
			STATUS	current
	DESCRIPTION ""
			::= { mbus58 82 }

mbus58Value26		OBJECT-TYPE
			SYNTAX	INTEGER
			ACCESS	read-only
			STATUS	current
	DESCRIPTION ""
			::= { mbus58 83 }

mbus58VIF27		OBJECT-TYPE
			SYNTAX	INTEGER
			ACCESS	read-only
			STATUS	current
	DESCRIPTION ""
			::= { mbus58 84 }

mbus58Value27		OBJECT-TYPE
			SYNTAX	INTEGER
			ACCESS	read-only
			STATUS	current
	DESCRIPTION ""
			::= { mbus58 85 }

mbus58VIF28		OBJECT-TYPE
			SYNTAX	INTEGER
			ACCESS	read-only
			STATUS	current
	DESCRIPTION ""
			::= { mbus58 86 }

mbus58Value28		OBJECT-TYPE
			SYNTAX	INTEGER
			ACCESS	read-only
			STATUS	current
	DESCRIPTION ""
			::= { mbus58 87 }

mbus58VIF29		OBJECT-TYPE
			SYNTAX	INTEGER
			ACCESS	read-only
			STATUS	current
	DESCRIPTION ""
			::= { mbus58 88 }

mbus58Value29		OBJECT-TYPE
			SYNTAX	INTEGER
			ACCESS	read-only
			STATUS	current
	DESCRIPTION ""
			::= { mbus58 89 }

mbus58VIF2A		OBJECT-TYPE
			SYNTAX	INTEGER
			ACCESS	read-only
			STATUS	current
	DESCRIPTION ""
			::= { mbus58 90 }

mbus58Value2A		OBJECT-TYPE
			SYNTAX	INTEGER
			ACCESS	read-only
			STATUS	current
	DESCRIPTION ""
			::= { mbus58 91 }

mbus58VIF2B		OBJECT-TYPE
			SYNTAX	INTEGER
			ACCESS	read-only
			STATUS	current
	DESCRIPTION ""
			::= { mbus58 92 }

mbus58Value2B		OBJECT-TYPE
			SYNTAX	INTEGER
			ACCESS	read-only
			STATUS	current
	DESCRIPTION ""
			::= { mbus58 93 }

mbus58VIF2C		OBJECT-TYPE
			SYNTAX	INTEGER
			ACCESS	read-only
			STATUS	current
	DESCRIPTION ""
			::= { mbus58 94 }

mbus58Value2C		OBJECT-TYPE
			SYNTAX	INTEGER
			ACCESS	read-only
			STATUS	current
	DESCRIPTION ""
			::= { mbus58 95 }

mbus58VIF2D		OBJECT-TYPE
			SYNTAX	INTEGER
			ACCESS	read-only
			STATUS	current
	DESCRIPTION ""
			::= { mbus58 96 }

mbus58Value2D		OBJECT-TYPE
			SYNTAX	INTEGER
			ACCESS	read-only
			STATUS	current
	DESCRIPTION ""
			::= { mbus58 97 }

mbus58VIF2E		OBJECT-TYPE
			SYNTAX	INTEGER
			ACCESS	read-only
			STATUS	current
	DESCRIPTION ""
			::= { mbus58 98 }

mbus58Value2E		OBJECT-TYPE
			SYNTAX	INTEGER
			ACCESS	read-only
			STATUS	current
	DESCRIPTION ""
			::= { mbus58 99 }

mbus58VIF2F		OBJECT-TYPE
			SYNTAX	INTEGER
			ACCESS	read-only
			STATUS	current
	DESCRIPTION ""
			::= { mbus58 100 }

mbus58Value2F		OBJECT-TYPE
			SYNTAX	INTEGER
			ACCESS	read-only
			STATUS	current
	DESCRIPTION ""
			::= { mbus58 101 }

mbus59			OBJECT IDENTIFIER ::= { mbus 89 }

mbus59IdNumber		OBJECT-TYPE
			SYNTAX	Gauge
			ACCESS	read-only
			STATUS	current
	DESCRIPTION ""
			::= { mbus59 1 }

mbus59Manufacturer	OBJECT-TYPE
			SYNTAX	Gauge
			ACCESS	read-only
			STATUS	current
	DESCRIPTION ""
			::= { mbus59 2 }

mbus59Version		OBJECT-TYPE
			SYNTAX	Gauge
			ACCESS	read-only
			STATUS	current
	DESCRIPTION ""
			::= { mbus59 3 }

mbus59Medium		OBJECT-TYPE
			SYNTAX	Gauge
			ACCESS	read-only
			STATUS	current
	DESCRIPTION ""
			::= { mbus59 4 }

mbus59Status		OBJECT-TYPE
			SYNTAX	Gauge
			ACCESS	read-only
			STATUS	current
	DESCRIPTION ""
			::= { mbus59 5 }

mbus59VIF00		OBJECT-TYPE
			SYNTAX	INTEGER
			ACCESS	read-only
			STATUS	current
	DESCRIPTION ""
			::= { mbus59 6 }

mbus59Value00		OBJECT-TYPE
			SYNTAX	INTEGER
			ACCESS	read-only
			STATUS	current
	DESCRIPTION ""
			::= { mbus59 7 }

mbus59VIF01		OBJECT-TYPE
			SYNTAX	INTEGER
			ACCESS	read-only
			STATUS	current
	DESCRIPTION ""
			::= { mbus59 8 }

mbus59Value01		OBJECT-TYPE
			SYNTAX	INTEGER
			ACCESS	read-only
			STATUS	current
	DESCRIPTION ""
			::= { mbus59 9 }

mbus59VIF02		OBJECT-TYPE
			SYNTAX	INTEGER
			ACCESS	read-only
			STATUS	current
	DESCRIPTION ""
			::= { mbus59 10 }

mbus59Value02		OBJECT-TYPE
			SYNTAX	INTEGER
			ACCESS	read-only
			STATUS	current
	DESCRIPTION ""
			::= { mbus59 11 }

mbus59VIF03		OBJECT-TYPE
			SYNTAX	INTEGER
			ACCESS	read-only
			STATUS	current
	DESCRIPTION ""
			::= { mbus59 12 }

mbus59Value03		OBJECT-TYPE
			SYNTAX	INTEGER
			ACCESS	read-only
			STATUS	current
	DESCRIPTION ""
			::= { mbus59 13 }

mbus59VIF04		OBJECT-TYPE
			SYNTAX	INTEGER
			ACCESS	read-only
			STATUS	current
	DESCRIPTION ""
			::= { mbus59 14 }

mbus59Value04		OBJECT-TYPE
			SYNTAX	INTEGER
			ACCESS	read-only
			STATUS	current
	DESCRIPTION ""
			::= { mbus59 15 }

mbus59VIF05		OBJECT-TYPE
			SYNTAX	INTEGER
			ACCESS	read-only
			STATUS	current
	DESCRIPTION ""
			::= { mbus59 16 }

mbus59Value05		OBJECT-TYPE
			SYNTAX	INTEGER
			ACCESS	read-only
			STATUS	current
	DESCRIPTION ""
			::= { mbus59 17 }

mbus59VIF06		OBJECT-TYPE
			SYNTAX	INTEGER
			ACCESS	read-only
			STATUS	current
	DESCRIPTION ""
			::= { mbus59 18 }

mbus59Value06		OBJECT-TYPE
			SYNTAX	INTEGER
			ACCESS	read-only
			STATUS	current
	DESCRIPTION ""
			::= { mbus59 19 }

mbus59VIF07		OBJECT-TYPE
			SYNTAX	INTEGER
			ACCESS	read-only
			STATUS	current
	DESCRIPTION ""
			::= { mbus59 20 }

mbus59Value07		OBJECT-TYPE
			SYNTAX	INTEGER
			ACCESS	read-only
			STATUS	current
	DESCRIPTION ""
			::= { mbus59 21 }

mbus59VIF08		OBJECT-TYPE
			SYNTAX	INTEGER
			ACCESS	read-only
			STATUS	current
	DESCRIPTION ""
			::= { mbus59 22 }

mbus59Value08		OBJECT-TYPE
			SYNTAX	INTEGER
			ACCESS	read-only
			STATUS	current
	DESCRIPTION ""
			::= { mbus59 23 }

mbus59VIF09		OBJECT-TYPE
			SYNTAX	INTEGER
			ACCESS	read-only
			STATUS	current
	DESCRIPTION ""
			::= { mbus59 24 }

mbus59Value09		OBJECT-TYPE
			SYNTAX	INTEGER
			ACCESS	read-only
			STATUS	current
	DESCRIPTION ""
			::= { mbus59 25 }

mbus59VIF0A		OBJECT-TYPE
			SYNTAX	INTEGER
			ACCESS	read-only
			STATUS	current
	DESCRIPTION ""
			::= { mbus59 26 }

mbus59Value0A		OBJECT-TYPE
			SYNTAX	INTEGER
			ACCESS	read-only
			STATUS	current
	DESCRIPTION ""
			::= { mbus59 27 }

mbus59VIF0B		OBJECT-TYPE
			SYNTAX	INTEGER
			ACCESS	read-only
			STATUS	current
	DESCRIPTION ""
			::= { mbus59 28 }

mbus59Value0B		OBJECT-TYPE
			SYNTAX	INTEGER
			ACCESS	read-only
			STATUS	current
	DESCRIPTION ""
			::= { mbus59 29 }

mbus59VIF0C		OBJECT-TYPE
			SYNTAX	INTEGER
			ACCESS	read-only
			STATUS	current
	DESCRIPTION ""
			::= { mbus59 30 }

mbus59Value0C		OBJECT-TYPE
			SYNTAX	INTEGER
			ACCESS	read-only
			STATUS	current
	DESCRIPTION ""
			::= { mbus59 31 }

mbus59VIF0D		OBJECT-TYPE
			SYNTAX	INTEGER
			ACCESS	read-only
			STATUS	current
	DESCRIPTION ""
			::= { mbus59 32 }

mbus59Value0D		OBJECT-TYPE
			SYNTAX	INTEGER
			ACCESS	read-only
			STATUS	current
	DESCRIPTION ""
			::= { mbus59 33 }

mbus59VIF0E		OBJECT-TYPE
			SYNTAX	INTEGER
			ACCESS	read-only
			STATUS	current
	DESCRIPTION ""
			::= { mbus59 34 }

mbus59Value0E		OBJECT-TYPE
			SYNTAX	INTEGER
			ACCESS	read-only
			STATUS	current
	DESCRIPTION ""
			::= { mbus59 35 }

mbus59VIF0F		OBJECT-TYPE
			SYNTAX	INTEGER
			ACCESS	read-only
			STATUS	current
	DESCRIPTION ""
			::= { mbus59 36 }

mbus59Value0F		OBJECT-TYPE
			SYNTAX	INTEGER
			ACCESS	read-only
			STATUS	current
	DESCRIPTION ""
			::= { mbus59 37 }

mbus59VIF10		OBJECT-TYPE
			SYNTAX	INTEGER
			ACCESS	read-only
			STATUS	current
	DESCRIPTION ""
			::= { mbus59 38 }

mbus59Value10		OBJECT-TYPE
			SYNTAX	INTEGER
			ACCESS	read-only
			STATUS	current
	DESCRIPTION ""
			::= { mbus59 39 }

mbus59VIF11		OBJECT-TYPE
			SYNTAX	INTEGER
			ACCESS	read-only
			STATUS	current
	DESCRIPTION ""
			::= { mbus59 40 }

mbus59Value11		OBJECT-TYPE
			SYNTAX	INTEGER
			ACCESS	read-only
			STATUS	current
	DESCRIPTION ""
			::= { mbus59 41 }

mbus59VIF12		OBJECT-TYPE
			SYNTAX	INTEGER
			ACCESS	read-only
			STATUS	current
	DESCRIPTION ""
			::= { mbus59 42 }

mbus59Value12		OBJECT-TYPE
			SYNTAX	INTEGER
			ACCESS	read-only
			STATUS	current
	DESCRIPTION ""
			::= { mbus59 43 }

mbus59VIF13		OBJECT-TYPE
			SYNTAX	INTEGER
			ACCESS	read-only
			STATUS	current
	DESCRIPTION ""
			::= { mbus59 44 }

mbus59Value13		OBJECT-TYPE
			SYNTAX	INTEGER
			ACCESS	read-only
			STATUS	current
	DESCRIPTION ""
			::= { mbus59 45 }

mbus59VIF14		OBJECT-TYPE
			SYNTAX	INTEGER
			ACCESS	read-only
			STATUS	current
	DESCRIPTION ""
			::= { mbus59 46 }

mbus59Value14		OBJECT-TYPE
			SYNTAX	INTEGER
			ACCESS	read-only
			STATUS	current
	DESCRIPTION ""
			::= { mbus59 47 }

mbus59VIF15		OBJECT-TYPE
			SYNTAX	INTEGER
			ACCESS	read-only
			STATUS	current
	DESCRIPTION ""
			::= { mbus59 48 }

mbus59Value15		OBJECT-TYPE
			SYNTAX	INTEGER
			ACCESS	read-only
			STATUS	current
	DESCRIPTION ""
			::= { mbus59 49 }

mbus59VIF16		OBJECT-TYPE
			SYNTAX	INTEGER
			ACCESS	read-only
			STATUS	current
	DESCRIPTION ""
			::= { mbus59 50 }

mbus59Value16		OBJECT-TYPE
			SYNTAX	INTEGER
			ACCESS	read-only
			STATUS	current
	DESCRIPTION ""
			::= { mbus59 51 }

mbus59VIF17		OBJECT-TYPE
			SYNTAX	INTEGER
			ACCESS	read-only
			STATUS	current
	DESCRIPTION ""
			::= { mbus59 52 }

mbus59Value17		OBJECT-TYPE
			SYNTAX	INTEGER
			ACCESS	read-only
			STATUS	current
	DESCRIPTION ""
			::= { mbus59 53 }

mbus59VIF18		OBJECT-TYPE
			SYNTAX	INTEGER
			ACCESS	read-only
			STATUS	current
	DESCRIPTION ""
			::= { mbus59 54 }

mbus59Value18		OBJECT-TYPE
			SYNTAX	INTEGER
			ACCESS	read-only
			STATUS	current
	DESCRIPTION ""
			::= { mbus59 55 }

mbus59VIF19		OBJECT-TYPE
			SYNTAX	INTEGER
			ACCESS	read-only
			STATUS	current
	DESCRIPTION ""
			::= { mbus59 56 }

mbus59Value19		OBJECT-TYPE
			SYNTAX	INTEGER
			ACCESS	read-only
			STATUS	current
	DESCRIPTION ""
			::= { mbus59 57 }

mbus59VIF1A		OBJECT-TYPE
			SYNTAX	INTEGER
			ACCESS	read-only
			STATUS	current
	DESCRIPTION ""
			::= { mbus59 58 }

mbus59Value1A		OBJECT-TYPE
			SYNTAX	INTEGER
			ACCESS	read-only
			STATUS	current
	DESCRIPTION ""
			::= { mbus59 59 }

mbus59VIF1B		OBJECT-TYPE
			SYNTAX	INTEGER
			ACCESS	read-only
			STATUS	current
	DESCRIPTION ""
			::= { mbus59 60 }

mbus59Value1B		OBJECT-TYPE
			SYNTAX	INTEGER
			ACCESS	read-only
			STATUS	current
	DESCRIPTION ""
			::= { mbus59 61 }

mbus59VIF1C		OBJECT-TYPE
			SYNTAX	INTEGER
			ACCESS	read-only
			STATUS	current
	DESCRIPTION ""
			::= { mbus59 62 }

mbus59Value1C		OBJECT-TYPE
			SYNTAX	INTEGER
			ACCESS	read-only
			STATUS	current
	DESCRIPTION ""
			::= { mbus59 63 }

mbus59VIF1D		OBJECT-TYPE
			SYNTAX	INTEGER
			ACCESS	read-only
			STATUS	current
	DESCRIPTION ""
			::= { mbus59 64 }

mbus59Value1D		OBJECT-TYPE
			SYNTAX	INTEGER
			ACCESS	read-only
			STATUS	current
	DESCRIPTION ""
			::= { mbus59 65 }

mbus59VIF1E		OBJECT-TYPE
			SYNTAX	INTEGER
			ACCESS	read-only
			STATUS	current
	DESCRIPTION ""
			::= { mbus59 66 }

mbus59Value1E		OBJECT-TYPE
			SYNTAX	INTEGER
			ACCESS	read-only
			STATUS	current
	DESCRIPTION ""
			::= { mbus59 67 }

mbus59VIF1F		OBJECT-TYPE
			SYNTAX	INTEGER
			ACCESS	read-only
			STATUS	current
	DESCRIPTION ""
			::= { mbus59 68 }

mbus59Value1F		OBJECT-TYPE
			SYNTAX	INTEGER
			ACCESS	read-only
			STATUS	current
	DESCRIPTION ""
			::= { mbus59 69 }

mbus59VIF20		OBJECT-TYPE
			SYNTAX	INTEGER
			ACCESS	read-only
			STATUS	current
	DESCRIPTION ""
			::= { mbus59 70 }

mbus59Value20		OBJECT-TYPE
			SYNTAX	INTEGER
			ACCESS	read-only
			STATUS	current
	DESCRIPTION ""
			::= { mbus59 71 }

mbus59VIF21		OBJECT-TYPE
			SYNTAX	INTEGER
			ACCESS	read-only
			STATUS	current
	DESCRIPTION ""
			::= { mbus59 72 }

mbus59Value21		OBJECT-TYPE
			SYNTAX	INTEGER
			ACCESS	read-only
			STATUS	current
	DESCRIPTION ""
			::= { mbus59 73 }

mbus59VIF22		OBJECT-TYPE
			SYNTAX	INTEGER
			ACCESS	read-only
			STATUS	current
	DESCRIPTION ""
			::= { mbus59 74 }

mbus59Value22		OBJECT-TYPE
			SYNTAX	INTEGER
			ACCESS	read-only
			STATUS	current
	DESCRIPTION ""
			::= { mbus59 75 }

mbus59VIF23		OBJECT-TYPE
			SYNTAX	INTEGER
			ACCESS	read-only
			STATUS	current
	DESCRIPTION ""
			::= { mbus59 76 }

mbus59Value23		OBJECT-TYPE
			SYNTAX	INTEGER
			ACCESS	read-only
			STATUS	current
	DESCRIPTION ""
			::= { mbus59 77 }

mbus59VIF24		OBJECT-TYPE
			SYNTAX	INTEGER
			ACCESS	read-only
			STATUS	current
	DESCRIPTION ""
			::= { mbus59 78 }

mbus59Value24		OBJECT-TYPE
			SYNTAX	INTEGER
			ACCESS	read-only
			STATUS	current
	DESCRIPTION ""
			::= { mbus59 79 }

mbus59VIF25		OBJECT-TYPE
			SYNTAX	INTEGER
			ACCESS	read-only
			STATUS	current
	DESCRIPTION ""
			::= { mbus59 80 }

mbus59Value25		OBJECT-TYPE
			SYNTAX	INTEGER
			ACCESS	read-only
			STATUS	current
	DESCRIPTION ""
			::= { mbus59 81 }

mbus59VIF26		OBJECT-TYPE
			SYNTAX	INTEGER
			ACCESS	read-only
			STATUS	current
	DESCRIPTION ""
			::= { mbus59 82 }

mbus59Value26		OBJECT-TYPE
			SYNTAX	INTEGER
			ACCESS	read-only
			STATUS	current
	DESCRIPTION ""
			::= { mbus59 83 }

mbus59VIF27		OBJECT-TYPE
			SYNTAX	INTEGER
			ACCESS	read-only
			STATUS	current
	DESCRIPTION ""
			::= { mbus59 84 }

mbus59Value27		OBJECT-TYPE
			SYNTAX	INTEGER
			ACCESS	read-only
			STATUS	current
	DESCRIPTION ""
			::= { mbus59 85 }

mbus59VIF28		OBJECT-TYPE
			SYNTAX	INTEGER
			ACCESS	read-only
			STATUS	current
	DESCRIPTION ""
			::= { mbus59 86 }

mbus59Value28		OBJECT-TYPE
			SYNTAX	INTEGER
			ACCESS	read-only
			STATUS	current
	DESCRIPTION ""
			::= { mbus59 87 }

mbus59VIF29		OBJECT-TYPE
			SYNTAX	INTEGER
			ACCESS	read-only
			STATUS	current
	DESCRIPTION ""
			::= { mbus59 88 }

mbus59Value29		OBJECT-TYPE
			SYNTAX	INTEGER
			ACCESS	read-only
			STATUS	current
	DESCRIPTION ""
			::= { mbus59 89 }

mbus59VIF2A		OBJECT-TYPE
			SYNTAX	INTEGER
			ACCESS	read-only
			STATUS	current
	DESCRIPTION ""
			::= { mbus59 90 }

mbus59Value2A		OBJECT-TYPE
			SYNTAX	INTEGER
			ACCESS	read-only
			STATUS	current
	DESCRIPTION ""
			::= { mbus59 91 }

mbus59VIF2B		OBJECT-TYPE
			SYNTAX	INTEGER
			ACCESS	read-only
			STATUS	current
	DESCRIPTION ""
			::= { mbus59 92 }

mbus59Value2B		OBJECT-TYPE
			SYNTAX	INTEGER
			ACCESS	read-only
			STATUS	current
	DESCRIPTION ""
			::= { mbus59 93 }

mbus59VIF2C		OBJECT-TYPE
			SYNTAX	INTEGER
			ACCESS	read-only
			STATUS	current
	DESCRIPTION ""
			::= { mbus59 94 }

mbus59Value2C		OBJECT-TYPE
			SYNTAX	INTEGER
			ACCESS	read-only
			STATUS	current
	DESCRIPTION ""
			::= { mbus59 95 }

mbus59VIF2D		OBJECT-TYPE
			SYNTAX	INTEGER
			ACCESS	read-only
			STATUS	current
	DESCRIPTION ""
			::= { mbus59 96 }

mbus59Value2D		OBJECT-TYPE
			SYNTAX	INTEGER
			ACCESS	read-only
			STATUS	current
	DESCRIPTION ""
			::= { mbus59 97 }

mbus59VIF2E		OBJECT-TYPE
			SYNTAX	INTEGER
			ACCESS	read-only
			STATUS	current
	DESCRIPTION ""
			::= { mbus59 98 }

mbus59Value2E		OBJECT-TYPE
			SYNTAX	INTEGER
			ACCESS	read-only
			STATUS	current
	DESCRIPTION ""
			::= { mbus59 99 }

mbus59VIF2F		OBJECT-TYPE
			SYNTAX	INTEGER
			ACCESS	read-only
			STATUS	current
	DESCRIPTION ""
			::= { mbus59 100 }

mbus59Value2F		OBJECT-TYPE
			SYNTAX	INTEGER
			ACCESS	read-only
			STATUS	current
	DESCRIPTION ""
			::= { mbus59 101 }

mbus5A			OBJECT IDENTIFIER ::= { mbus 90 }

mbus5AIdNumber		OBJECT-TYPE
			SYNTAX	Gauge
			ACCESS	read-only
			STATUS	current
	DESCRIPTION ""
			::= { mbus5A 1 }

mbus5AManufacturer	OBJECT-TYPE
			SYNTAX	Gauge
			ACCESS	read-only
			STATUS	current
	DESCRIPTION ""
			::= { mbus5A 2 }

mbus5AVersion		OBJECT-TYPE
			SYNTAX	Gauge
			ACCESS	read-only
			STATUS	current
	DESCRIPTION ""
			::= { mbus5A 3 }

mbus5AMedium		OBJECT-TYPE
			SYNTAX	Gauge
			ACCESS	read-only
			STATUS	current
	DESCRIPTION ""
			::= { mbus5A 4 }

mbus5AStatus		OBJECT-TYPE
			SYNTAX	Gauge
			ACCESS	read-only
			STATUS	current
	DESCRIPTION ""
			::= { mbus5A 5 }

mbus5AVIF00		OBJECT-TYPE
			SYNTAX	INTEGER
			ACCESS	read-only
			STATUS	current
	DESCRIPTION ""
			::= { mbus5A 6 }

mbus5AValue00		OBJECT-TYPE
			SYNTAX	INTEGER
			ACCESS	read-only
			STATUS	current
	DESCRIPTION ""
			::= { mbus5A 7 }

mbus5AVIF01		OBJECT-TYPE
			SYNTAX	INTEGER
			ACCESS	read-only
			STATUS	current
	DESCRIPTION ""
			::= { mbus5A 8 }

mbus5AValue01		OBJECT-TYPE
			SYNTAX	INTEGER
			ACCESS	read-only
			STATUS	current
	DESCRIPTION ""
			::= { mbus5A 9 }

mbus5AVIF02		OBJECT-TYPE
			SYNTAX	INTEGER
			ACCESS	read-only
			STATUS	current
	DESCRIPTION ""
			::= { mbus5A 10 }

mbus5AValue02		OBJECT-TYPE
			SYNTAX	INTEGER
			ACCESS	read-only
			STATUS	current
	DESCRIPTION ""
			::= { mbus5A 11 }

mbus5AVIF03		OBJECT-TYPE
			SYNTAX	INTEGER
			ACCESS	read-only
			STATUS	current
	DESCRIPTION ""
			::= { mbus5A 12 }

mbus5AValue03		OBJECT-TYPE
			SYNTAX	INTEGER
			ACCESS	read-only
			STATUS	current
	DESCRIPTION ""
			::= { mbus5A 13 }

mbus5AVIF04		OBJECT-TYPE
			SYNTAX	INTEGER
			ACCESS	read-only
			STATUS	current
	DESCRIPTION ""
			::= { mbus5A 14 }

mbus5AValue04		OBJECT-TYPE
			SYNTAX	INTEGER
			ACCESS	read-only
			STATUS	current
	DESCRIPTION ""
			::= { mbus5A 15 }

mbus5AVIF05		OBJECT-TYPE
			SYNTAX	INTEGER
			ACCESS	read-only
			STATUS	current
	DESCRIPTION ""
			::= { mbus5A 16 }

mbus5AValue05		OBJECT-TYPE
			SYNTAX	INTEGER
			ACCESS	read-only
			STATUS	current
	DESCRIPTION ""
			::= { mbus5A 17 }

mbus5AVIF06		OBJECT-TYPE
			SYNTAX	INTEGER
			ACCESS	read-only
			STATUS	current
	DESCRIPTION ""
			::= { mbus5A 18 }

mbus5AValue06		OBJECT-TYPE
			SYNTAX	INTEGER
			ACCESS	read-only
			STATUS	current
	DESCRIPTION ""
			::= { mbus5A 19 }

mbus5AVIF07		OBJECT-TYPE
			SYNTAX	INTEGER
			ACCESS	read-only
			STATUS	current
	DESCRIPTION ""
			::= { mbus5A 20 }

mbus5AValue07		OBJECT-TYPE
			SYNTAX	INTEGER
			ACCESS	read-only
			STATUS	current
	DESCRIPTION ""
			::= { mbus5A 21 }

mbus5AVIF08		OBJECT-TYPE
			SYNTAX	INTEGER
			ACCESS	read-only
			STATUS	current
	DESCRIPTION ""
			::= { mbus5A 22 }

mbus5AValue08		OBJECT-TYPE
			SYNTAX	INTEGER
			ACCESS	read-only
			STATUS	current
	DESCRIPTION ""
			::= { mbus5A 23 }

mbus5AVIF09		OBJECT-TYPE
			SYNTAX	INTEGER
			ACCESS	read-only
			STATUS	current
	DESCRIPTION ""
			::= { mbus5A 24 }

mbus5AValue09		OBJECT-TYPE
			SYNTAX	INTEGER
			ACCESS	read-only
			STATUS	current
	DESCRIPTION ""
			::= { mbus5A 25 }

mbus5AVIF0A		OBJECT-TYPE
			SYNTAX	INTEGER
			ACCESS	read-only
			STATUS	current
	DESCRIPTION ""
			::= { mbus5A 26 }

mbus5AValue0A		OBJECT-TYPE
			SYNTAX	INTEGER
			ACCESS	read-only
			STATUS	current
	DESCRIPTION ""
			::= { mbus5A 27 }

mbus5AVIF0B		OBJECT-TYPE
			SYNTAX	INTEGER
			ACCESS	read-only
			STATUS	current
	DESCRIPTION ""
			::= { mbus5A 28 }

mbus5AValue0B		OBJECT-TYPE
			SYNTAX	INTEGER
			ACCESS	read-only
			STATUS	current
	DESCRIPTION ""
			::= { mbus5A 29 }

mbus5AVIF0C		OBJECT-TYPE
			SYNTAX	INTEGER
			ACCESS	read-only
			STATUS	current
	DESCRIPTION ""
			::= { mbus5A 30 }

mbus5AValue0C		OBJECT-TYPE
			SYNTAX	INTEGER
			ACCESS	read-only
			STATUS	current
	DESCRIPTION ""
			::= { mbus5A 31 }

mbus5AVIF0D		OBJECT-TYPE
			SYNTAX	INTEGER
			ACCESS	read-only
			STATUS	current
	DESCRIPTION ""
			::= { mbus5A 32 }

mbus5AValue0D		OBJECT-TYPE
			SYNTAX	INTEGER
			ACCESS	read-only
			STATUS	current
	DESCRIPTION ""
			::= { mbus5A 33 }

mbus5AVIF0E		OBJECT-TYPE
			SYNTAX	INTEGER
			ACCESS	read-only
			STATUS	current
	DESCRIPTION ""
			::= { mbus5A 34 }

mbus5AValue0E		OBJECT-TYPE
			SYNTAX	INTEGER
			ACCESS	read-only
			STATUS	current
	DESCRIPTION ""
			::= { mbus5A 35 }

mbus5AVIF0F		OBJECT-TYPE
			SYNTAX	INTEGER
			ACCESS	read-only
			STATUS	current
	DESCRIPTION ""
			::= { mbus5A 36 }

mbus5AValue0F		OBJECT-TYPE
			SYNTAX	INTEGER
			ACCESS	read-only
			STATUS	current
	DESCRIPTION ""
			::= { mbus5A 37 }

mbus5AVIF10		OBJECT-TYPE
			SYNTAX	INTEGER
			ACCESS	read-only
			STATUS	current
	DESCRIPTION ""
			::= { mbus5A 38 }

mbus5AValue10		OBJECT-TYPE
			SYNTAX	INTEGER
			ACCESS	read-only
			STATUS	current
	DESCRIPTION ""
			::= { mbus5A 39 }

mbus5AVIF11		OBJECT-TYPE
			SYNTAX	INTEGER
			ACCESS	read-only
			STATUS	current
	DESCRIPTION ""
			::= { mbus5A 40 }

mbus5AValue11		OBJECT-TYPE
			SYNTAX	INTEGER
			ACCESS	read-only
			STATUS	current
	DESCRIPTION ""
			::= { mbus5A 41 }

mbus5AVIF12		OBJECT-TYPE
			SYNTAX	INTEGER
			ACCESS	read-only
			STATUS	current
	DESCRIPTION ""
			::= { mbus5A 42 }

mbus5AValue12		OBJECT-TYPE
			SYNTAX	INTEGER
			ACCESS	read-only
			STATUS	current
	DESCRIPTION ""
			::= { mbus5A 43 }

mbus5AVIF13		OBJECT-TYPE
			SYNTAX	INTEGER
			ACCESS	read-only
			STATUS	current
	DESCRIPTION ""
			::= { mbus5A 44 }

mbus5AValue13		OBJECT-TYPE
			SYNTAX	INTEGER
			ACCESS	read-only
			STATUS	current
	DESCRIPTION ""
			::= { mbus5A 45 }

mbus5AVIF14		OBJECT-TYPE
			SYNTAX	INTEGER
			ACCESS	read-only
			STATUS	current
	DESCRIPTION ""
			::= { mbus5A 46 }

mbus5AValue14		OBJECT-TYPE
			SYNTAX	INTEGER
			ACCESS	read-only
			STATUS	current
	DESCRIPTION ""
			::= { mbus5A 47 }

mbus5AVIF15		OBJECT-TYPE
			SYNTAX	INTEGER
			ACCESS	read-only
			STATUS	current
	DESCRIPTION ""
			::= { mbus5A 48 }

mbus5AValue15		OBJECT-TYPE
			SYNTAX	INTEGER
			ACCESS	read-only
			STATUS	current
	DESCRIPTION ""
			::= { mbus5A 49 }

mbus5AVIF16		OBJECT-TYPE
			SYNTAX	INTEGER
			ACCESS	read-only
			STATUS	current
	DESCRIPTION ""
			::= { mbus5A 50 }

mbus5AValue16		OBJECT-TYPE
			SYNTAX	INTEGER
			ACCESS	read-only
			STATUS	current
	DESCRIPTION ""
			::= { mbus5A 51 }

mbus5AVIF17		OBJECT-TYPE
			SYNTAX	INTEGER
			ACCESS	read-only
			STATUS	current
	DESCRIPTION ""
			::= { mbus5A 52 }

mbus5AValue17		OBJECT-TYPE
			SYNTAX	INTEGER
			ACCESS	read-only
			STATUS	current
	DESCRIPTION ""
			::= { mbus5A 53 }

mbus5AVIF18		OBJECT-TYPE
			SYNTAX	INTEGER
			ACCESS	read-only
			STATUS	current
	DESCRIPTION ""
			::= { mbus5A 54 }

mbus5AValue18		OBJECT-TYPE
			SYNTAX	INTEGER
			ACCESS	read-only
			STATUS	current
	DESCRIPTION ""
			::= { mbus5A 55 }

mbus5AVIF19		OBJECT-TYPE
			SYNTAX	INTEGER
			ACCESS	read-only
			STATUS	current
	DESCRIPTION ""
			::= { mbus5A 56 }

mbus5AValue19		OBJECT-TYPE
			SYNTAX	INTEGER
			ACCESS	read-only
			STATUS	current
	DESCRIPTION ""
			::= { mbus5A 57 }

mbus5AVIF1A		OBJECT-TYPE
			SYNTAX	INTEGER
			ACCESS	read-only
			STATUS	current
	DESCRIPTION ""
			::= { mbus5A 58 }

mbus5AValue1A		OBJECT-TYPE
			SYNTAX	INTEGER
			ACCESS	read-only
			STATUS	current
	DESCRIPTION ""
			::= { mbus5A 59 }

mbus5AVIF1B		OBJECT-TYPE
			SYNTAX	INTEGER
			ACCESS	read-only
			STATUS	current
	DESCRIPTION ""
			::= { mbus5A 60 }

mbus5AValue1B		OBJECT-TYPE
			SYNTAX	INTEGER
			ACCESS	read-only
			STATUS	current
	DESCRIPTION ""
			::= { mbus5A 61 }

mbus5AVIF1C		OBJECT-TYPE
			SYNTAX	INTEGER
			ACCESS	read-only
			STATUS	current
	DESCRIPTION ""
			::= { mbus5A 62 }

mbus5AValue1C		OBJECT-TYPE
			SYNTAX	INTEGER
			ACCESS	read-only
			STATUS	current
	DESCRIPTION ""
			::= { mbus5A 63 }

mbus5AVIF1D		OBJECT-TYPE
			SYNTAX	INTEGER
			ACCESS	read-only
			STATUS	current
	DESCRIPTION ""
			::= { mbus5A 64 }

mbus5AValue1D		OBJECT-TYPE
			SYNTAX	INTEGER
			ACCESS	read-only
			STATUS	current
	DESCRIPTION ""
			::= { mbus5A 65 }

mbus5AVIF1E		OBJECT-TYPE
			SYNTAX	INTEGER
			ACCESS	read-only
			STATUS	current
	DESCRIPTION ""
			::= { mbus5A 66 }

mbus5AValue1E		OBJECT-TYPE
			SYNTAX	INTEGER
			ACCESS	read-only
			STATUS	current
	DESCRIPTION ""
			::= { mbus5A 67 }

mbus5AVIF1F		OBJECT-TYPE
			SYNTAX	INTEGER
			ACCESS	read-only
			STATUS	current
	DESCRIPTION ""
			::= { mbus5A 68 }

mbus5AValue1F		OBJECT-TYPE
			SYNTAX	INTEGER
			ACCESS	read-only
			STATUS	current
	DESCRIPTION ""
			::= { mbus5A 69 }

mbus5AVIF20		OBJECT-TYPE
			SYNTAX	INTEGER
			ACCESS	read-only
			STATUS	current
	DESCRIPTION ""
			::= { mbus5A 70 }

mbus5AValue20		OBJECT-TYPE
			SYNTAX	INTEGER
			ACCESS	read-only
			STATUS	current
	DESCRIPTION ""
			::= { mbus5A 71 }

mbus5AVIF21		OBJECT-TYPE
			SYNTAX	INTEGER
			ACCESS	read-only
			STATUS	current
	DESCRIPTION ""
			::= { mbus5A 72 }

mbus5AValue21		OBJECT-TYPE
			SYNTAX	INTEGER
			ACCESS	read-only
			STATUS	current
	DESCRIPTION ""
			::= { mbus5A 73 }

mbus5AVIF22		OBJECT-TYPE
			SYNTAX	INTEGER
			ACCESS	read-only
			STATUS	current
	DESCRIPTION ""
			::= { mbus5A 74 }

mbus5AValue22		OBJECT-TYPE
			SYNTAX	INTEGER
			ACCESS	read-only
			STATUS	current
	DESCRIPTION ""
			::= { mbus5A 75 }

mbus5AVIF23		OBJECT-TYPE
			SYNTAX	INTEGER
			ACCESS	read-only
			STATUS	current
	DESCRIPTION ""
			::= { mbus5A 76 }

mbus5AValue23		OBJECT-TYPE
			SYNTAX	INTEGER
			ACCESS	read-only
			STATUS	current
	DESCRIPTION ""
			::= { mbus5A 77 }

mbus5AVIF24		OBJECT-TYPE
			SYNTAX	INTEGER
			ACCESS	read-only
			STATUS	current
	DESCRIPTION ""
			::= { mbus5A 78 }

mbus5AValue24		OBJECT-TYPE
			SYNTAX	INTEGER
			ACCESS	read-only
			STATUS	current
	DESCRIPTION ""
			::= { mbus5A 79 }

mbus5AVIF25		OBJECT-TYPE
			SYNTAX	INTEGER
			ACCESS	read-only
			STATUS	current
	DESCRIPTION ""
			::= { mbus5A 80 }

mbus5AValue25		OBJECT-TYPE
			SYNTAX	INTEGER
			ACCESS	read-only
			STATUS	current
	DESCRIPTION ""
			::= { mbus5A 81 }

mbus5AVIF26		OBJECT-TYPE
			SYNTAX	INTEGER
			ACCESS	read-only
			STATUS	current
	DESCRIPTION ""
			::= { mbus5A 82 }

mbus5AValue26		OBJECT-TYPE
			SYNTAX	INTEGER
			ACCESS	read-only
			STATUS	current
	DESCRIPTION ""
			::= { mbus5A 83 }

mbus5AVIF27		OBJECT-TYPE
			SYNTAX	INTEGER
			ACCESS	read-only
			STATUS	current
	DESCRIPTION ""
			::= { mbus5A 84 }

mbus5AValue27		OBJECT-TYPE
			SYNTAX	INTEGER
			ACCESS	read-only
			STATUS	current
	DESCRIPTION ""
			::= { mbus5A 85 }

mbus5AVIF28		OBJECT-TYPE
			SYNTAX	INTEGER
			ACCESS	read-only
			STATUS	current
	DESCRIPTION ""
			::= { mbus5A 86 }

mbus5AValue28		OBJECT-TYPE
			SYNTAX	INTEGER
			ACCESS	read-only
			STATUS	current
	DESCRIPTION ""
			::= { mbus5A 87 }

mbus5AVIF29		OBJECT-TYPE
			SYNTAX	INTEGER
			ACCESS	read-only
			STATUS	current
	DESCRIPTION ""
			::= { mbus5A 88 }

mbus5AValue29		OBJECT-TYPE
			SYNTAX	INTEGER
			ACCESS	read-only
			STATUS	current
	DESCRIPTION ""
			::= { mbus5A 89 }

mbus5AVIF2A		OBJECT-TYPE
			SYNTAX	INTEGER
			ACCESS	read-only
			STATUS	current
	DESCRIPTION ""
			::= { mbus5A 90 }

mbus5AValue2A		OBJECT-TYPE
			SYNTAX	INTEGER
			ACCESS	read-only
			STATUS	current
	DESCRIPTION ""
			::= { mbus5A 91 }

mbus5AVIF2B		OBJECT-TYPE
			SYNTAX	INTEGER
			ACCESS	read-only
			STATUS	current
	DESCRIPTION ""
			::= { mbus5A 92 }

mbus5AValue2B		OBJECT-TYPE
			SYNTAX	INTEGER
			ACCESS	read-only
			STATUS	current
	DESCRIPTION ""
			::= { mbus5A 93 }

mbus5AVIF2C		OBJECT-TYPE
			SYNTAX	INTEGER
			ACCESS	read-only
			STATUS	current
	DESCRIPTION ""
			::= { mbus5A 94 }

mbus5AValue2C		OBJECT-TYPE
			SYNTAX	INTEGER
			ACCESS	read-only
			STATUS	current
	DESCRIPTION ""
			::= { mbus5A 95 }

mbus5AVIF2D		OBJECT-TYPE
			SYNTAX	INTEGER
			ACCESS	read-only
			STATUS	current
	DESCRIPTION ""
			::= { mbus5A 96 }

mbus5AValue2D		OBJECT-TYPE
			SYNTAX	INTEGER
			ACCESS	read-only
			STATUS	current
	DESCRIPTION ""
			::= { mbus5A 97 }

mbus5AVIF2E		OBJECT-TYPE
			SYNTAX	INTEGER
			ACCESS	read-only
			STATUS	current
	DESCRIPTION ""
			::= { mbus5A 98 }

mbus5AValue2E		OBJECT-TYPE
			SYNTAX	INTEGER
			ACCESS	read-only
			STATUS	current
	DESCRIPTION ""
			::= { mbus5A 99 }

mbus5AVIF2F		OBJECT-TYPE
			SYNTAX	INTEGER
			ACCESS	read-only
			STATUS	current
	DESCRIPTION ""
			::= { mbus5A 100 }

mbus5AValue2F		OBJECT-TYPE
			SYNTAX	INTEGER
			ACCESS	read-only
			STATUS	current
	DESCRIPTION ""
			::= { mbus5A 101 }

mbus5B			OBJECT IDENTIFIER ::= { mbus 91 }

mbus5BIdNumber		OBJECT-TYPE
			SYNTAX	Gauge
			ACCESS	read-only
			STATUS	current
	DESCRIPTION ""
			::= { mbus5B 1 }

mbus5BManufacturer	OBJECT-TYPE
			SYNTAX	Gauge
			ACCESS	read-only
			STATUS	current
	DESCRIPTION ""
			::= { mbus5B 2 }

mbus5BVersion		OBJECT-TYPE
			SYNTAX	Gauge
			ACCESS	read-only
			STATUS	current
	DESCRIPTION ""
			::= { mbus5B 3 }

mbus5BMedium		OBJECT-TYPE
			SYNTAX	Gauge
			ACCESS	read-only
			STATUS	current
	DESCRIPTION ""
			::= { mbus5B 4 }

mbus5BStatus		OBJECT-TYPE
			SYNTAX	Gauge
			ACCESS	read-only
			STATUS	current
	DESCRIPTION ""
			::= { mbus5B 5 }

mbus5BVIF00		OBJECT-TYPE
			SYNTAX	INTEGER
			ACCESS	read-only
			STATUS	current
	DESCRIPTION ""
			::= { mbus5B 6 }

mbus5BValue00		OBJECT-TYPE
			SYNTAX	INTEGER
			ACCESS	read-only
			STATUS	current
	DESCRIPTION ""
			::= { mbus5B 7 }

mbus5BVIF01		OBJECT-TYPE
			SYNTAX	INTEGER
			ACCESS	read-only
			STATUS	current
	DESCRIPTION ""
			::= { mbus5B 8 }

mbus5BValue01		OBJECT-TYPE
			SYNTAX	INTEGER
			ACCESS	read-only
			STATUS	current
	DESCRIPTION ""
			::= { mbus5B 9 }

mbus5BVIF02		OBJECT-TYPE
			SYNTAX	INTEGER
			ACCESS	read-only
			STATUS	current
	DESCRIPTION ""
			::= { mbus5B 10 }

mbus5BValue02		OBJECT-TYPE
			SYNTAX	INTEGER
			ACCESS	read-only
			STATUS	current
	DESCRIPTION ""
			::= { mbus5B 11 }

mbus5BVIF03		OBJECT-TYPE
			SYNTAX	INTEGER
			ACCESS	read-only
			STATUS	current
	DESCRIPTION ""
			::= { mbus5B 12 }

mbus5BValue03		OBJECT-TYPE
			SYNTAX	INTEGER
			ACCESS	read-only
			STATUS	current
	DESCRIPTION ""
			::= { mbus5B 13 }

mbus5BVIF04		OBJECT-TYPE
			SYNTAX	INTEGER
			ACCESS	read-only
			STATUS	current
	DESCRIPTION ""
			::= { mbus5B 14 }

mbus5BValue04		OBJECT-TYPE
			SYNTAX	INTEGER
			ACCESS	read-only
			STATUS	current
	DESCRIPTION ""
			::= { mbus5B 15 }

mbus5BVIF05		OBJECT-TYPE
			SYNTAX	INTEGER
			ACCESS	read-only
			STATUS	current
	DESCRIPTION ""
			::= { mbus5B 16 }

mbus5BValue05		OBJECT-TYPE
			SYNTAX	INTEGER
			ACCESS	read-only
			STATUS	current
	DESCRIPTION ""
			::= { mbus5B 17 }

mbus5BVIF06		OBJECT-TYPE
			SYNTAX	INTEGER
			ACCESS	read-only
			STATUS	current
	DESCRIPTION ""
			::= { mbus5B 18 }

mbus5BValue06		OBJECT-TYPE
			SYNTAX	INTEGER
			ACCESS	read-only
			STATUS	current
	DESCRIPTION ""
			::= { mbus5B 19 }

mbus5BVIF07		OBJECT-TYPE
			SYNTAX	INTEGER
			ACCESS	read-only
			STATUS	current
	DESCRIPTION ""
			::= { mbus5B 20 }

mbus5BValue07		OBJECT-TYPE
			SYNTAX	INTEGER
			ACCESS	read-only
			STATUS	current
	DESCRIPTION ""
			::= { mbus5B 21 }

mbus5BVIF08		OBJECT-TYPE
			SYNTAX	INTEGER
			ACCESS	read-only
			STATUS	current
	DESCRIPTION ""
			::= { mbus5B 22 }

mbus5BValue08		OBJECT-TYPE
			SYNTAX	INTEGER
			ACCESS	read-only
			STATUS	current
	DESCRIPTION ""
			::= { mbus5B 23 }

mbus5BVIF09		OBJECT-TYPE
			SYNTAX	INTEGER
			ACCESS	read-only
			STATUS	current
	DESCRIPTION ""
			::= { mbus5B 24 }

mbus5BValue09		OBJECT-TYPE
			SYNTAX	INTEGER
			ACCESS	read-only
			STATUS	current
	DESCRIPTION ""
			::= { mbus5B 25 }

mbus5BVIF0A		OBJECT-TYPE
			SYNTAX	INTEGER
			ACCESS	read-only
			STATUS	current
	DESCRIPTION ""
			::= { mbus5B 26 }

mbus5BValue0A		OBJECT-TYPE
			SYNTAX	INTEGER
			ACCESS	read-only
			STATUS	current
	DESCRIPTION ""
			::= { mbus5B 27 }

mbus5BVIF0B		OBJECT-TYPE
			SYNTAX	INTEGER
			ACCESS	read-only
			STATUS	current
	DESCRIPTION ""
			::= { mbus5B 28 }

mbus5BValue0B		OBJECT-TYPE
			SYNTAX	INTEGER
			ACCESS	read-only
			STATUS	current
	DESCRIPTION ""
			::= { mbus5B 29 }

mbus5BVIF0C		OBJECT-TYPE
			SYNTAX	INTEGER
			ACCESS	read-only
			STATUS	current
	DESCRIPTION ""
			::= { mbus5B 30 }

mbus5BValue0C		OBJECT-TYPE
			SYNTAX	INTEGER
			ACCESS	read-only
			STATUS	current
	DESCRIPTION ""
			::= { mbus5B 31 }

mbus5BVIF0D		OBJECT-TYPE
			SYNTAX	INTEGER
			ACCESS	read-only
			STATUS	current
	DESCRIPTION ""
			::= { mbus5B 32 }

mbus5BValue0D		OBJECT-TYPE
			SYNTAX	INTEGER
			ACCESS	read-only
			STATUS	current
	DESCRIPTION ""
			::= { mbus5B 33 }

mbus5BVIF0E		OBJECT-TYPE
			SYNTAX	INTEGER
			ACCESS	read-only
			STATUS	current
	DESCRIPTION ""
			::= { mbus5B 34 }

mbus5BValue0E		OBJECT-TYPE
			SYNTAX	INTEGER
			ACCESS	read-only
			STATUS	current
	DESCRIPTION ""
			::= { mbus5B 35 }

mbus5BVIF0F		OBJECT-TYPE
			SYNTAX	INTEGER
			ACCESS	read-only
			STATUS	current
	DESCRIPTION ""
			::= { mbus5B 36 }

mbus5BValue0F		OBJECT-TYPE
			SYNTAX	INTEGER
			ACCESS	read-only
			STATUS	current
	DESCRIPTION ""
			::= { mbus5B 37 }

mbus5BVIF10		OBJECT-TYPE
			SYNTAX	INTEGER
			ACCESS	read-only
			STATUS	current
	DESCRIPTION ""
			::= { mbus5B 38 }

mbus5BValue10		OBJECT-TYPE
			SYNTAX	INTEGER
			ACCESS	read-only
			STATUS	current
	DESCRIPTION ""
			::= { mbus5B 39 }

mbus5BVIF11		OBJECT-TYPE
			SYNTAX	INTEGER
			ACCESS	read-only
			STATUS	current
	DESCRIPTION ""
			::= { mbus5B 40 }

mbus5BValue11		OBJECT-TYPE
			SYNTAX	INTEGER
			ACCESS	read-only
			STATUS	current
	DESCRIPTION ""
			::= { mbus5B 41 }

mbus5BVIF12		OBJECT-TYPE
			SYNTAX	INTEGER
			ACCESS	read-only
			STATUS	current
	DESCRIPTION ""
			::= { mbus5B 42 }

mbus5BValue12		OBJECT-TYPE
			SYNTAX	INTEGER
			ACCESS	read-only
			STATUS	current
	DESCRIPTION ""
			::= { mbus5B 43 }

mbus5BVIF13		OBJECT-TYPE
			SYNTAX	INTEGER
			ACCESS	read-only
			STATUS	current
	DESCRIPTION ""
			::= { mbus5B 44 }

mbus5BValue13		OBJECT-TYPE
			SYNTAX	INTEGER
			ACCESS	read-only
			STATUS	current
	DESCRIPTION ""
			::= { mbus5B 45 }

mbus5BVIF14		OBJECT-TYPE
			SYNTAX	INTEGER
			ACCESS	read-only
			STATUS	current
	DESCRIPTION ""
			::= { mbus5B 46 }

mbus5BValue14		OBJECT-TYPE
			SYNTAX	INTEGER
			ACCESS	read-only
			STATUS	current
	DESCRIPTION ""
			::= { mbus5B 47 }

mbus5BVIF15		OBJECT-TYPE
			SYNTAX	INTEGER
			ACCESS	read-only
			STATUS	current
	DESCRIPTION ""
			::= { mbus5B 48 }

mbus5BValue15		OBJECT-TYPE
			SYNTAX	INTEGER
			ACCESS	read-only
			STATUS	current
	DESCRIPTION ""
			::= { mbus5B 49 }

mbus5BVIF16		OBJECT-TYPE
			SYNTAX	INTEGER
			ACCESS	read-only
			STATUS	current
	DESCRIPTION ""
			::= { mbus5B 50 }

mbus5BValue16		OBJECT-TYPE
			SYNTAX	INTEGER
			ACCESS	read-only
			STATUS	current
	DESCRIPTION ""
			::= { mbus5B 51 }

mbus5BVIF17		OBJECT-TYPE
			SYNTAX	INTEGER
			ACCESS	read-only
			STATUS	current
	DESCRIPTION ""
			::= { mbus5B 52 }

mbus5BValue17		OBJECT-TYPE
			SYNTAX	INTEGER
			ACCESS	read-only
			STATUS	current
	DESCRIPTION ""
			::= { mbus5B 53 }

mbus5BVIF18		OBJECT-TYPE
			SYNTAX	INTEGER
			ACCESS	read-only
			STATUS	current
	DESCRIPTION ""
			::= { mbus5B 54 }

mbus5BValue18		OBJECT-TYPE
			SYNTAX	INTEGER
			ACCESS	read-only
			STATUS	current
	DESCRIPTION ""
			::= { mbus5B 55 }

mbus5BVIF19		OBJECT-TYPE
			SYNTAX	INTEGER
			ACCESS	read-only
			STATUS	current
	DESCRIPTION ""
			::= { mbus5B 56 }

mbus5BValue19		OBJECT-TYPE
			SYNTAX	INTEGER
			ACCESS	read-only
			STATUS	current
	DESCRIPTION ""
			::= { mbus5B 57 }

mbus5BVIF1A		OBJECT-TYPE
			SYNTAX	INTEGER
			ACCESS	read-only
			STATUS	current
	DESCRIPTION ""
			::= { mbus5B 58 }

mbus5BValue1A		OBJECT-TYPE
			SYNTAX	INTEGER
			ACCESS	read-only
			STATUS	current
	DESCRIPTION ""
			::= { mbus5B 59 }

mbus5BVIF1B		OBJECT-TYPE
			SYNTAX	INTEGER
			ACCESS	read-only
			STATUS	current
	DESCRIPTION ""
			::= { mbus5B 60 }

mbus5BValue1B		OBJECT-TYPE
			SYNTAX	INTEGER
			ACCESS	read-only
			STATUS	current
	DESCRIPTION ""
			::= { mbus5B 61 }

mbus5BVIF1C		OBJECT-TYPE
			SYNTAX	INTEGER
			ACCESS	read-only
			STATUS	current
	DESCRIPTION ""
			::= { mbus5B 62 }

mbus5BValue1C		OBJECT-TYPE
			SYNTAX	INTEGER
			ACCESS	read-only
			STATUS	current
	DESCRIPTION ""
			::= { mbus5B 63 }

mbus5BVIF1D		OBJECT-TYPE
			SYNTAX	INTEGER
			ACCESS	read-only
			STATUS	current
	DESCRIPTION ""
			::= { mbus5B 64 }

mbus5BValue1D		OBJECT-TYPE
			SYNTAX	INTEGER
			ACCESS	read-only
			STATUS	current
	DESCRIPTION ""
			::= { mbus5B 65 }

mbus5BVIF1E		OBJECT-TYPE
			SYNTAX	INTEGER
			ACCESS	read-only
			STATUS	current
	DESCRIPTION ""
			::= { mbus5B 66 }

mbus5BValue1E		OBJECT-TYPE
			SYNTAX	INTEGER
			ACCESS	read-only
			STATUS	current
	DESCRIPTION ""
			::= { mbus5B 67 }

mbus5BVIF1F		OBJECT-TYPE
			SYNTAX	INTEGER
			ACCESS	read-only
			STATUS	current
	DESCRIPTION ""
			::= { mbus5B 68 }

mbus5BValue1F		OBJECT-TYPE
			SYNTAX	INTEGER
			ACCESS	read-only
			STATUS	current
	DESCRIPTION ""
			::= { mbus5B 69 }

mbus5BVIF20		OBJECT-TYPE
			SYNTAX	INTEGER
			ACCESS	read-only
			STATUS	current
	DESCRIPTION ""
			::= { mbus5B 70 }

mbus5BValue20		OBJECT-TYPE
			SYNTAX	INTEGER
			ACCESS	read-only
			STATUS	current
	DESCRIPTION ""
			::= { mbus5B 71 }

mbus5BVIF21		OBJECT-TYPE
			SYNTAX	INTEGER
			ACCESS	read-only
			STATUS	current
	DESCRIPTION ""
			::= { mbus5B 72 }

mbus5BValue21		OBJECT-TYPE
			SYNTAX	INTEGER
			ACCESS	read-only
			STATUS	current
	DESCRIPTION ""
			::= { mbus5B 73 }

mbus5BVIF22		OBJECT-TYPE
			SYNTAX	INTEGER
			ACCESS	read-only
			STATUS	current
	DESCRIPTION ""
			::= { mbus5B 74 }

mbus5BValue22		OBJECT-TYPE
			SYNTAX	INTEGER
			ACCESS	read-only
			STATUS	current
	DESCRIPTION ""
			::= { mbus5B 75 }

mbus5BVIF23		OBJECT-TYPE
			SYNTAX	INTEGER
			ACCESS	read-only
			STATUS	current
	DESCRIPTION ""
			::= { mbus5B 76 }

mbus5BValue23		OBJECT-TYPE
			SYNTAX	INTEGER
			ACCESS	read-only
			STATUS	current
	DESCRIPTION ""
			::= { mbus5B 77 }

mbus5BVIF24		OBJECT-TYPE
			SYNTAX	INTEGER
			ACCESS	read-only
			STATUS	current
	DESCRIPTION ""
			::= { mbus5B 78 }

mbus5BValue24		OBJECT-TYPE
			SYNTAX	INTEGER
			ACCESS	read-only
			STATUS	current
	DESCRIPTION ""
			::= { mbus5B 79 }

mbus5BVIF25		OBJECT-TYPE
			SYNTAX	INTEGER
			ACCESS	read-only
			STATUS	current
	DESCRIPTION ""
			::= { mbus5B 80 }

mbus5BValue25		OBJECT-TYPE
			SYNTAX	INTEGER
			ACCESS	read-only
			STATUS	current
	DESCRIPTION ""
			::= { mbus5B 81 }

mbus5BVIF26		OBJECT-TYPE
			SYNTAX	INTEGER
			ACCESS	read-only
			STATUS	current
	DESCRIPTION ""
			::= { mbus5B 82 }

mbus5BValue26		OBJECT-TYPE
			SYNTAX	INTEGER
			ACCESS	read-only
			STATUS	current
	DESCRIPTION ""
			::= { mbus5B 83 }

mbus5BVIF27		OBJECT-TYPE
			SYNTAX	INTEGER
			ACCESS	read-only
			STATUS	current
	DESCRIPTION ""
			::= { mbus5B 84 }

mbus5BValue27		OBJECT-TYPE
			SYNTAX	INTEGER
			ACCESS	read-only
			STATUS	current
	DESCRIPTION ""
			::= { mbus5B 85 }

mbus5BVIF28		OBJECT-TYPE
			SYNTAX	INTEGER
			ACCESS	read-only
			STATUS	current
	DESCRIPTION ""
			::= { mbus5B 86 }

mbus5BValue28		OBJECT-TYPE
			SYNTAX	INTEGER
			ACCESS	read-only
			STATUS	current
	DESCRIPTION ""
			::= { mbus5B 87 }

mbus5BVIF29		OBJECT-TYPE
			SYNTAX	INTEGER
			ACCESS	read-only
			STATUS	current
	DESCRIPTION ""
			::= { mbus5B 88 }

mbus5BValue29		OBJECT-TYPE
			SYNTAX	INTEGER
			ACCESS	read-only
			STATUS	current
	DESCRIPTION ""
			::= { mbus5B 89 }

mbus5BVIF2A		OBJECT-TYPE
			SYNTAX	INTEGER
			ACCESS	read-only
			STATUS	current
	DESCRIPTION ""
			::= { mbus5B 90 }

mbus5BValue2A		OBJECT-TYPE
			SYNTAX	INTEGER
			ACCESS	read-only
			STATUS	current
	DESCRIPTION ""
			::= { mbus5B 91 }

mbus5BVIF2B		OBJECT-TYPE
			SYNTAX	INTEGER
			ACCESS	read-only
			STATUS	current
	DESCRIPTION ""
			::= { mbus5B 92 }

mbus5BValue2B		OBJECT-TYPE
			SYNTAX	INTEGER
			ACCESS	read-only
			STATUS	current
	DESCRIPTION ""
			::= { mbus5B 93 }

mbus5BVIF2C		OBJECT-TYPE
			SYNTAX	INTEGER
			ACCESS	read-only
			STATUS	current
	DESCRIPTION ""
			::= { mbus5B 94 }

mbus5BValue2C		OBJECT-TYPE
			SYNTAX	INTEGER
			ACCESS	read-only
			STATUS	current
	DESCRIPTION ""
			::= { mbus5B 95 }

mbus5BVIF2D		OBJECT-TYPE
			SYNTAX	INTEGER
			ACCESS	read-only
			STATUS	current
	DESCRIPTION ""
			::= { mbus5B 96 }

mbus5BValue2D		OBJECT-TYPE
			SYNTAX	INTEGER
			ACCESS	read-only
			STATUS	current
	DESCRIPTION ""
			::= { mbus5B 97 }

mbus5BVIF2E		OBJECT-TYPE
			SYNTAX	INTEGER
			ACCESS	read-only
			STATUS	current
	DESCRIPTION ""
			::= { mbus5B 98 }

mbus5BValue2E		OBJECT-TYPE
			SYNTAX	INTEGER
			ACCESS	read-only
			STATUS	current
	DESCRIPTION ""
			::= { mbus5B 99 }

mbus5BVIF2F		OBJECT-TYPE
			SYNTAX	INTEGER
			ACCESS	read-only
			STATUS	current
	DESCRIPTION ""
			::= { mbus5B 100 }

mbus5BValue2F		OBJECT-TYPE
			SYNTAX	INTEGER
			ACCESS	read-only
			STATUS	current
	DESCRIPTION ""
			::= { mbus5B 101 }

mbus5C			OBJECT IDENTIFIER ::= { mbus 92 }

mbus5CIdNumber		OBJECT-TYPE
			SYNTAX	Gauge
			ACCESS	read-only
			STATUS	current
	DESCRIPTION ""
			::= { mbus5C 1 }

mbus5CManufacturer	OBJECT-TYPE
			SYNTAX	Gauge
			ACCESS	read-only
			STATUS	current
	DESCRIPTION ""
			::= { mbus5C 2 }

mbus5CVersion		OBJECT-TYPE
			SYNTAX	Gauge
			ACCESS	read-only
			STATUS	current
	DESCRIPTION ""
			::= { mbus5C 3 }

mbus5CMedium		OBJECT-TYPE
			SYNTAX	Gauge
			ACCESS	read-only
			STATUS	current
	DESCRIPTION ""
			::= { mbus5C 4 }

mbus5CStatus		OBJECT-TYPE
			SYNTAX	Gauge
			ACCESS	read-only
			STATUS	current
	DESCRIPTION ""
			::= { mbus5C 5 }

mbus5CVIF00		OBJECT-TYPE
			SYNTAX	INTEGER
			ACCESS	read-only
			STATUS	current
	DESCRIPTION ""
			::= { mbus5C 6 }

mbus5CValue00		OBJECT-TYPE
			SYNTAX	INTEGER
			ACCESS	read-only
			STATUS	current
	DESCRIPTION ""
			::= { mbus5C 7 }

mbus5CVIF01		OBJECT-TYPE
			SYNTAX	INTEGER
			ACCESS	read-only
			STATUS	current
	DESCRIPTION ""
			::= { mbus5C 8 }

mbus5CValue01		OBJECT-TYPE
			SYNTAX	INTEGER
			ACCESS	read-only
			STATUS	current
	DESCRIPTION ""
			::= { mbus5C 9 }

mbus5CVIF02		OBJECT-TYPE
			SYNTAX	INTEGER
			ACCESS	read-only
			STATUS	current
	DESCRIPTION ""
			::= { mbus5C 10 }

mbus5CValue02		OBJECT-TYPE
			SYNTAX	INTEGER
			ACCESS	read-only
			STATUS	current
	DESCRIPTION ""
			::= { mbus5C 11 }

mbus5CVIF03		OBJECT-TYPE
			SYNTAX	INTEGER
			ACCESS	read-only
			STATUS	current
	DESCRIPTION ""
			::= { mbus5C 12 }

mbus5CValue03		OBJECT-TYPE
			SYNTAX	INTEGER
			ACCESS	read-only
			STATUS	current
	DESCRIPTION ""
			::= { mbus5C 13 }

mbus5CVIF04		OBJECT-TYPE
			SYNTAX	INTEGER
			ACCESS	read-only
			STATUS	current
	DESCRIPTION ""
			::= { mbus5C 14 }

mbus5CValue04		OBJECT-TYPE
			SYNTAX	INTEGER
			ACCESS	read-only
			STATUS	current
	DESCRIPTION ""
			::= { mbus5C 15 }

mbus5CVIF05		OBJECT-TYPE
			SYNTAX	INTEGER
			ACCESS	read-only
			STATUS	current
	DESCRIPTION ""
			::= { mbus5C 16 }

mbus5CValue05		OBJECT-TYPE
			SYNTAX	INTEGER
			ACCESS	read-only
			STATUS	current
	DESCRIPTION ""
			::= { mbus5C 17 }

mbus5CVIF06		OBJECT-TYPE
			SYNTAX	INTEGER
			ACCESS	read-only
			STATUS	current
	DESCRIPTION ""
			::= { mbus5C 18 }

mbus5CValue06		OBJECT-TYPE
			SYNTAX	INTEGER
			ACCESS	read-only
			STATUS	current
	DESCRIPTION ""
			::= { mbus5C 19 }

mbus5CVIF07		OBJECT-TYPE
			SYNTAX	INTEGER
			ACCESS	read-only
			STATUS	current
	DESCRIPTION ""
			::= { mbus5C 20 }

mbus5CValue07		OBJECT-TYPE
			SYNTAX	INTEGER
			ACCESS	read-only
			STATUS	current
	DESCRIPTION ""
			::= { mbus5C 21 }

mbus5CVIF08		OBJECT-TYPE
			SYNTAX	INTEGER
			ACCESS	read-only
			STATUS	current
	DESCRIPTION ""
			::= { mbus5C 22 }

mbus5CValue08		OBJECT-TYPE
			SYNTAX	INTEGER
			ACCESS	read-only
			STATUS	current
	DESCRIPTION ""
			::= { mbus5C 23 }

mbus5CVIF09		OBJECT-TYPE
			SYNTAX	INTEGER
			ACCESS	read-only
			STATUS	current
	DESCRIPTION ""
			::= { mbus5C 24 }

mbus5CValue09		OBJECT-TYPE
			SYNTAX	INTEGER
			ACCESS	read-only
			STATUS	current
	DESCRIPTION ""
			::= { mbus5C 25 }

mbus5CVIF0A		OBJECT-TYPE
			SYNTAX	INTEGER
			ACCESS	read-only
			STATUS	current
	DESCRIPTION ""
			::= { mbus5C 26 }

mbus5CValue0A		OBJECT-TYPE
			SYNTAX	INTEGER
			ACCESS	read-only
			STATUS	current
	DESCRIPTION ""
			::= { mbus5C 27 }

mbus5CVIF0B		OBJECT-TYPE
			SYNTAX	INTEGER
			ACCESS	read-only
			STATUS	current
	DESCRIPTION ""
			::= { mbus5C 28 }

mbus5CValue0B		OBJECT-TYPE
			SYNTAX	INTEGER
			ACCESS	read-only
			STATUS	current
	DESCRIPTION ""
			::= { mbus5C 29 }

mbus5CVIF0C		OBJECT-TYPE
			SYNTAX	INTEGER
			ACCESS	read-only
			STATUS	current
	DESCRIPTION ""
			::= { mbus5C 30 }

mbus5CValue0C		OBJECT-TYPE
			SYNTAX	INTEGER
			ACCESS	read-only
			STATUS	current
	DESCRIPTION ""
			::= { mbus5C 31 }

mbus5CVIF0D		OBJECT-TYPE
			SYNTAX	INTEGER
			ACCESS	read-only
			STATUS	current
	DESCRIPTION ""
			::= { mbus5C 32 }

mbus5CValue0D		OBJECT-TYPE
			SYNTAX	INTEGER
			ACCESS	read-only
			STATUS	current
	DESCRIPTION ""
			::= { mbus5C 33 }

mbus5CVIF0E		OBJECT-TYPE
			SYNTAX	INTEGER
			ACCESS	read-only
			STATUS	current
	DESCRIPTION ""
			::= { mbus5C 34 }

mbus5CValue0E		OBJECT-TYPE
			SYNTAX	INTEGER
			ACCESS	read-only
			STATUS	current
	DESCRIPTION ""
			::= { mbus5C 35 }

mbus5CVIF0F		OBJECT-TYPE
			SYNTAX	INTEGER
			ACCESS	read-only
			STATUS	current
	DESCRIPTION ""
			::= { mbus5C 36 }

mbus5CValue0F		OBJECT-TYPE
			SYNTAX	INTEGER
			ACCESS	read-only
			STATUS	current
	DESCRIPTION ""
			::= { mbus5C 37 }

mbus5CVIF10		OBJECT-TYPE
			SYNTAX	INTEGER
			ACCESS	read-only
			STATUS	current
	DESCRIPTION ""
			::= { mbus5C 38 }

mbus5CValue10		OBJECT-TYPE
			SYNTAX	INTEGER
			ACCESS	read-only
			STATUS	current
	DESCRIPTION ""
			::= { mbus5C 39 }

mbus5CVIF11		OBJECT-TYPE
			SYNTAX	INTEGER
			ACCESS	read-only
			STATUS	current
	DESCRIPTION ""
			::= { mbus5C 40 }

mbus5CValue11		OBJECT-TYPE
			SYNTAX	INTEGER
			ACCESS	read-only
			STATUS	current
	DESCRIPTION ""
			::= { mbus5C 41 }

mbus5CVIF12		OBJECT-TYPE
			SYNTAX	INTEGER
			ACCESS	read-only
			STATUS	current
	DESCRIPTION ""
			::= { mbus5C 42 }

mbus5CValue12		OBJECT-TYPE
			SYNTAX	INTEGER
			ACCESS	read-only
			STATUS	current
	DESCRIPTION ""
			::= { mbus5C 43 }

mbus5CVIF13		OBJECT-TYPE
			SYNTAX	INTEGER
			ACCESS	read-only
			STATUS	current
	DESCRIPTION ""
			::= { mbus5C 44 }

mbus5CValue13		OBJECT-TYPE
			SYNTAX	INTEGER
			ACCESS	read-only
			STATUS	current
	DESCRIPTION ""
			::= { mbus5C 45 }

mbus5CVIF14		OBJECT-TYPE
			SYNTAX	INTEGER
			ACCESS	read-only
			STATUS	current
	DESCRIPTION ""
			::= { mbus5C 46 }

mbus5CValue14		OBJECT-TYPE
			SYNTAX	INTEGER
			ACCESS	read-only
			STATUS	current
	DESCRIPTION ""
			::= { mbus5C 47 }

mbus5CVIF15		OBJECT-TYPE
			SYNTAX	INTEGER
			ACCESS	read-only
			STATUS	current
	DESCRIPTION ""
			::= { mbus5C 48 }

mbus5CValue15		OBJECT-TYPE
			SYNTAX	INTEGER
			ACCESS	read-only
			STATUS	current
	DESCRIPTION ""
			::= { mbus5C 49 }

mbus5CVIF16		OBJECT-TYPE
			SYNTAX	INTEGER
			ACCESS	read-only
			STATUS	current
	DESCRIPTION ""
			::= { mbus5C 50 }

mbus5CValue16		OBJECT-TYPE
			SYNTAX	INTEGER
			ACCESS	read-only
			STATUS	current
	DESCRIPTION ""
			::= { mbus5C 51 }

mbus5CVIF17		OBJECT-TYPE
			SYNTAX	INTEGER
			ACCESS	read-only
			STATUS	current
	DESCRIPTION ""
			::= { mbus5C 52 }

mbus5CValue17		OBJECT-TYPE
			SYNTAX	INTEGER
			ACCESS	read-only
			STATUS	current
	DESCRIPTION ""
			::= { mbus5C 53 }

mbus5CVIF18		OBJECT-TYPE
			SYNTAX	INTEGER
			ACCESS	read-only
			STATUS	current
	DESCRIPTION ""
			::= { mbus5C 54 }

mbus5CValue18		OBJECT-TYPE
			SYNTAX	INTEGER
			ACCESS	read-only
			STATUS	current
	DESCRIPTION ""
			::= { mbus5C 55 }

mbus5CVIF19		OBJECT-TYPE
			SYNTAX	INTEGER
			ACCESS	read-only
			STATUS	current
	DESCRIPTION ""
			::= { mbus5C 56 }

mbus5CValue19		OBJECT-TYPE
			SYNTAX	INTEGER
			ACCESS	read-only
			STATUS	current
	DESCRIPTION ""
			::= { mbus5C 57 }

mbus5CVIF1A		OBJECT-TYPE
			SYNTAX	INTEGER
			ACCESS	read-only
			STATUS	current
	DESCRIPTION ""
			::= { mbus5C 58 }

mbus5CValue1A		OBJECT-TYPE
			SYNTAX	INTEGER
			ACCESS	read-only
			STATUS	current
	DESCRIPTION ""
			::= { mbus5C 59 }

mbus5CVIF1B		OBJECT-TYPE
			SYNTAX	INTEGER
			ACCESS	read-only
			STATUS	current
	DESCRIPTION ""
			::= { mbus5C 60 }

mbus5CValue1B		OBJECT-TYPE
			SYNTAX	INTEGER
			ACCESS	read-only
			STATUS	current
	DESCRIPTION ""
			::= { mbus5C 61 }

mbus5CVIF1C		OBJECT-TYPE
			SYNTAX	INTEGER
			ACCESS	read-only
			STATUS	current
	DESCRIPTION ""
			::= { mbus5C 62 }

mbus5CValue1C		OBJECT-TYPE
			SYNTAX	INTEGER
			ACCESS	read-only
			STATUS	current
	DESCRIPTION ""
			::= { mbus5C 63 }

mbus5CVIF1D		OBJECT-TYPE
			SYNTAX	INTEGER
			ACCESS	read-only
			STATUS	current
	DESCRIPTION ""
			::= { mbus5C 64 }

mbus5CValue1D		OBJECT-TYPE
			SYNTAX	INTEGER
			ACCESS	read-only
			STATUS	current
	DESCRIPTION ""
			::= { mbus5C 65 }

mbus5CVIF1E		OBJECT-TYPE
			SYNTAX	INTEGER
			ACCESS	read-only
			STATUS	current
	DESCRIPTION ""
			::= { mbus5C 66 }

mbus5CValue1E		OBJECT-TYPE
			SYNTAX	INTEGER
			ACCESS	read-only
			STATUS	current
	DESCRIPTION ""
			::= { mbus5C 67 }

mbus5CVIF1F		OBJECT-TYPE
			SYNTAX	INTEGER
			ACCESS	read-only
			STATUS	current
	DESCRIPTION ""
			::= { mbus5C 68 }

mbus5CValue1F		OBJECT-TYPE
			SYNTAX	INTEGER
			ACCESS	read-only
			STATUS	current
	DESCRIPTION ""
			::= { mbus5C 69 }

mbus5CVIF20		OBJECT-TYPE
			SYNTAX	INTEGER
			ACCESS	read-only
			STATUS	current
	DESCRIPTION ""
			::= { mbus5C 70 }

mbus5CValue20		OBJECT-TYPE
			SYNTAX	INTEGER
			ACCESS	read-only
			STATUS	current
	DESCRIPTION ""
			::= { mbus5C 71 }

mbus5CVIF21		OBJECT-TYPE
			SYNTAX	INTEGER
			ACCESS	read-only
			STATUS	current
	DESCRIPTION ""
			::= { mbus5C 72 }

mbus5CValue21		OBJECT-TYPE
			SYNTAX	INTEGER
			ACCESS	read-only
			STATUS	current
	DESCRIPTION ""
			::= { mbus5C 73 }

mbus5CVIF22		OBJECT-TYPE
			SYNTAX	INTEGER
			ACCESS	read-only
			STATUS	current
	DESCRIPTION ""
			::= { mbus5C 74 }

mbus5CValue22		OBJECT-TYPE
			SYNTAX	INTEGER
			ACCESS	read-only
			STATUS	current
	DESCRIPTION ""
			::= { mbus5C 75 }

mbus5CVIF23		OBJECT-TYPE
			SYNTAX	INTEGER
			ACCESS	read-only
			STATUS	current
	DESCRIPTION ""
			::= { mbus5C 76 }

mbus5CValue23		OBJECT-TYPE
			SYNTAX	INTEGER
			ACCESS	read-only
			STATUS	current
	DESCRIPTION ""
			::= { mbus5C 77 }

mbus5CVIF24		OBJECT-TYPE
			SYNTAX	INTEGER
			ACCESS	read-only
			STATUS	current
	DESCRIPTION ""
			::= { mbus5C 78 }

mbus5CValue24		OBJECT-TYPE
			SYNTAX	INTEGER
			ACCESS	read-only
			STATUS	current
	DESCRIPTION ""
			::= { mbus5C 79 }

mbus5CVIF25		OBJECT-TYPE
			SYNTAX	INTEGER
			ACCESS	read-only
			STATUS	current
	DESCRIPTION ""
			::= { mbus5C 80 }

mbus5CValue25		OBJECT-TYPE
			SYNTAX	INTEGER
			ACCESS	read-only
			STATUS	current
	DESCRIPTION ""
			::= { mbus5C 81 }

mbus5CVIF26		OBJECT-TYPE
			SYNTAX	INTEGER
			ACCESS	read-only
			STATUS	current
	DESCRIPTION ""
			::= { mbus5C 82 }

mbus5CValue26		OBJECT-TYPE
			SYNTAX	INTEGER
			ACCESS	read-only
			STATUS	current
	DESCRIPTION ""
			::= { mbus5C 83 }

mbus5CVIF27		OBJECT-TYPE
			SYNTAX	INTEGER
			ACCESS	read-only
			STATUS	current
	DESCRIPTION ""
			::= { mbus5C 84 }

mbus5CValue27		OBJECT-TYPE
			SYNTAX	INTEGER
			ACCESS	read-only
			STATUS	current
	DESCRIPTION ""
			::= { mbus5C 85 }

mbus5CVIF28		OBJECT-TYPE
			SYNTAX	INTEGER
			ACCESS	read-only
			STATUS	current
	DESCRIPTION ""
			::= { mbus5C 86 }

mbus5CValue28		OBJECT-TYPE
			SYNTAX	INTEGER
			ACCESS	read-only
			STATUS	current
	DESCRIPTION ""
			::= { mbus5C 87 }

mbus5CVIF29		OBJECT-TYPE
			SYNTAX	INTEGER
			ACCESS	read-only
			STATUS	current
	DESCRIPTION ""
			::= { mbus5C 88 }

mbus5CValue29		OBJECT-TYPE
			SYNTAX	INTEGER
			ACCESS	read-only
			STATUS	current
	DESCRIPTION ""
			::= { mbus5C 89 }

mbus5CVIF2A		OBJECT-TYPE
			SYNTAX	INTEGER
			ACCESS	read-only
			STATUS	current
	DESCRIPTION ""
			::= { mbus5C 90 }

mbus5CValue2A		OBJECT-TYPE
			SYNTAX	INTEGER
			ACCESS	read-only
			STATUS	current
	DESCRIPTION ""
			::= { mbus5C 91 }

mbus5CVIF2B		OBJECT-TYPE
			SYNTAX	INTEGER
			ACCESS	read-only
			STATUS	current
	DESCRIPTION ""
			::= { mbus5C 92 }

mbus5CValue2B		OBJECT-TYPE
			SYNTAX	INTEGER
			ACCESS	read-only
			STATUS	current
	DESCRIPTION ""
			::= { mbus5C 93 }

mbus5CVIF2C		OBJECT-TYPE
			SYNTAX	INTEGER
			ACCESS	read-only
			STATUS	current
	DESCRIPTION ""
			::= { mbus5C 94 }

mbus5CValue2C		OBJECT-TYPE
			SYNTAX	INTEGER
			ACCESS	read-only
			STATUS	current
	DESCRIPTION ""
			::= { mbus5C 95 }

mbus5CVIF2D		OBJECT-TYPE
			SYNTAX	INTEGER
			ACCESS	read-only
			STATUS	current
	DESCRIPTION ""
			::= { mbus5C 96 }

mbus5CValue2D		OBJECT-TYPE
			SYNTAX	INTEGER
			ACCESS	read-only
			STATUS	current
	DESCRIPTION ""
			::= { mbus5C 97 }

mbus5CVIF2E		OBJECT-TYPE
			SYNTAX	INTEGER
			ACCESS	read-only
			STATUS	current
	DESCRIPTION ""
			::= { mbus5C 98 }

mbus5CValue2E		OBJECT-TYPE
			SYNTAX	INTEGER
			ACCESS	read-only
			STATUS	current
	DESCRIPTION ""
			::= { mbus5C 99 }

mbus5CVIF2F		OBJECT-TYPE
			SYNTAX	INTEGER
			ACCESS	read-only
			STATUS	current
	DESCRIPTION ""
			::= { mbus5C 100 }

mbus5CValue2F		OBJECT-TYPE
			SYNTAX	INTEGER
			ACCESS	read-only
			STATUS	current
	DESCRIPTION ""
			::= { mbus5C 101 }

mbus5D			OBJECT IDENTIFIER ::= { mbus 93 }

mbus5DIdNumber		OBJECT-TYPE
			SYNTAX	Gauge
			ACCESS	read-only
			STATUS	current
	DESCRIPTION ""
			::= { mbus5D 1 }

mbus5DManufacturer	OBJECT-TYPE
			SYNTAX	Gauge
			ACCESS	read-only
			STATUS	current
	DESCRIPTION ""
			::= { mbus5D 2 }

mbus5DVersion		OBJECT-TYPE
			SYNTAX	Gauge
			ACCESS	read-only
			STATUS	current
	DESCRIPTION ""
			::= { mbus5D 3 }

mbus5DMedium		OBJECT-TYPE
			SYNTAX	Gauge
			ACCESS	read-only
			STATUS	current
	DESCRIPTION ""
			::= { mbus5D 4 }

mbus5DStatus		OBJECT-TYPE
			SYNTAX	Gauge
			ACCESS	read-only
			STATUS	current
	DESCRIPTION ""
			::= { mbus5D 5 }

mbus5DVIF00		OBJECT-TYPE
			SYNTAX	INTEGER
			ACCESS	read-only
			STATUS	current
	DESCRIPTION ""
			::= { mbus5D 6 }

mbus5DValue00		OBJECT-TYPE
			SYNTAX	INTEGER
			ACCESS	read-only
			STATUS	current
	DESCRIPTION ""
			::= { mbus5D 7 }

mbus5DVIF01		OBJECT-TYPE
			SYNTAX	INTEGER
			ACCESS	read-only
			STATUS	current
	DESCRIPTION ""
			::= { mbus5D 8 }

mbus5DValue01		OBJECT-TYPE
			SYNTAX	INTEGER
			ACCESS	read-only
			STATUS	current
	DESCRIPTION ""
			::= { mbus5D 9 }

mbus5DVIF02		OBJECT-TYPE
			SYNTAX	INTEGER
			ACCESS	read-only
			STATUS	current
	DESCRIPTION ""
			::= { mbus5D 10 }

mbus5DValue02		OBJECT-TYPE
			SYNTAX	INTEGER
			ACCESS	read-only
			STATUS	current
	DESCRIPTION ""
			::= { mbus5D 11 }

mbus5DVIF03		OBJECT-TYPE
			SYNTAX	INTEGER
			ACCESS	read-only
			STATUS	current
	DESCRIPTION ""
			::= { mbus5D 12 }

mbus5DValue03		OBJECT-TYPE
			SYNTAX	INTEGER
			ACCESS	read-only
			STATUS	current
	DESCRIPTION ""
			::= { mbus5D 13 }

mbus5DVIF04		OBJECT-TYPE
			SYNTAX	INTEGER
			ACCESS	read-only
			STATUS	current
	DESCRIPTION ""
			::= { mbus5D 14 }

mbus5DValue04		OBJECT-TYPE
			SYNTAX	INTEGER
			ACCESS	read-only
			STATUS	current
	DESCRIPTION ""
			::= { mbus5D 15 }

mbus5DVIF05		OBJECT-TYPE
			SYNTAX	INTEGER
			ACCESS	read-only
			STATUS	current
	DESCRIPTION ""
			::= { mbus5D 16 }

mbus5DValue05		OBJECT-TYPE
			SYNTAX	INTEGER
			ACCESS	read-only
			STATUS	current
	DESCRIPTION ""
			::= { mbus5D 17 }

mbus5DVIF06		OBJECT-TYPE
			SYNTAX	INTEGER
			ACCESS	read-only
			STATUS	current
	DESCRIPTION ""
			::= { mbus5D 18 }

mbus5DValue06		OBJECT-TYPE
			SYNTAX	INTEGER
			ACCESS	read-only
			STATUS	current
	DESCRIPTION ""
			::= { mbus5D 19 }

mbus5DVIF07		OBJECT-TYPE
			SYNTAX	INTEGER
			ACCESS	read-only
			STATUS	current
	DESCRIPTION ""
			::= { mbus5D 20 }

mbus5DValue07		OBJECT-TYPE
			SYNTAX	INTEGER
			ACCESS	read-only
			STATUS	current
	DESCRIPTION ""
			::= { mbus5D 21 }

mbus5DVIF08		OBJECT-TYPE
			SYNTAX	INTEGER
			ACCESS	read-only
			STATUS	current
	DESCRIPTION ""
			::= { mbus5D 22 }

mbus5DValue08		OBJECT-TYPE
			SYNTAX	INTEGER
			ACCESS	read-only
			STATUS	current
	DESCRIPTION ""
			::= { mbus5D 23 }

mbus5DVIF09		OBJECT-TYPE
			SYNTAX	INTEGER
			ACCESS	read-only
			STATUS	current
	DESCRIPTION ""
			::= { mbus5D 24 }

mbus5DValue09		OBJECT-TYPE
			SYNTAX	INTEGER
			ACCESS	read-only
			STATUS	current
	DESCRIPTION ""
			::= { mbus5D 25 }

mbus5DVIF0A		OBJECT-TYPE
			SYNTAX	INTEGER
			ACCESS	read-only
			STATUS	current
	DESCRIPTION ""
			::= { mbus5D 26 }

mbus5DValue0A		OBJECT-TYPE
			SYNTAX	INTEGER
			ACCESS	read-only
			STATUS	current
	DESCRIPTION ""
			::= { mbus5D 27 }

mbus5DVIF0B		OBJECT-TYPE
			SYNTAX	INTEGER
			ACCESS	read-only
			STATUS	current
	DESCRIPTION ""
			::= { mbus5D 28 }

mbus5DValue0B		OBJECT-TYPE
			SYNTAX	INTEGER
			ACCESS	read-only
			STATUS	current
	DESCRIPTION ""
			::= { mbus5D 29 }

mbus5DVIF0C		OBJECT-TYPE
			SYNTAX	INTEGER
			ACCESS	read-only
			STATUS	current
	DESCRIPTION ""
			::= { mbus5D 30 }

mbus5DValue0C		OBJECT-TYPE
			SYNTAX	INTEGER
			ACCESS	read-only
			STATUS	current
	DESCRIPTION ""
			::= { mbus5D 31 }

mbus5DVIF0D		OBJECT-TYPE
			SYNTAX	INTEGER
			ACCESS	read-only
			STATUS	current
	DESCRIPTION ""
			::= { mbus5D 32 }

mbus5DValue0D		OBJECT-TYPE
			SYNTAX	INTEGER
			ACCESS	read-only
			STATUS	current
	DESCRIPTION ""
			::= { mbus5D 33 }

mbus5DVIF0E		OBJECT-TYPE
			SYNTAX	INTEGER
			ACCESS	read-only
			STATUS	current
	DESCRIPTION ""
			::= { mbus5D 34 }

mbus5DValue0E		OBJECT-TYPE
			SYNTAX	INTEGER
			ACCESS	read-only
			STATUS	current
	DESCRIPTION ""
			::= { mbus5D 35 }

mbus5DVIF0F		OBJECT-TYPE
			SYNTAX	INTEGER
			ACCESS	read-only
			STATUS	current
	DESCRIPTION ""
			::= { mbus5D 36 }

mbus5DValue0F		OBJECT-TYPE
			SYNTAX	INTEGER
			ACCESS	read-only
			STATUS	current
	DESCRIPTION ""
			::= { mbus5D 37 }

mbus5DVIF10		OBJECT-TYPE
			SYNTAX	INTEGER
			ACCESS	read-only
			STATUS	current
	DESCRIPTION ""
			::= { mbus5D 38 }

mbus5DValue10		OBJECT-TYPE
			SYNTAX	INTEGER
			ACCESS	read-only
			STATUS	current
	DESCRIPTION ""
			::= { mbus5D 39 }

mbus5DVIF11		OBJECT-TYPE
			SYNTAX	INTEGER
			ACCESS	read-only
			STATUS	current
	DESCRIPTION ""
			::= { mbus5D 40 }

mbus5DValue11		OBJECT-TYPE
			SYNTAX	INTEGER
			ACCESS	read-only
			STATUS	current
	DESCRIPTION ""
			::= { mbus5D 41 }

mbus5DVIF12		OBJECT-TYPE
			SYNTAX	INTEGER
			ACCESS	read-only
			STATUS	current
	DESCRIPTION ""
			::= { mbus5D 42 }

mbus5DValue12		OBJECT-TYPE
			SYNTAX	INTEGER
			ACCESS	read-only
			STATUS	current
	DESCRIPTION ""
			::= { mbus5D 43 }

mbus5DVIF13		OBJECT-TYPE
			SYNTAX	INTEGER
			ACCESS	read-only
			STATUS	current
	DESCRIPTION ""
			::= { mbus5D 44 }

mbus5DValue13		OBJECT-TYPE
			SYNTAX	INTEGER
			ACCESS	read-only
			STATUS	current
	DESCRIPTION ""
			::= { mbus5D 45 }

mbus5DVIF14		OBJECT-TYPE
			SYNTAX	INTEGER
			ACCESS	read-only
			STATUS	current
	DESCRIPTION ""
			::= { mbus5D 46 }

mbus5DValue14		OBJECT-TYPE
			SYNTAX	INTEGER
			ACCESS	read-only
			STATUS	current
	DESCRIPTION ""
			::= { mbus5D 47 }

mbus5DVIF15		OBJECT-TYPE
			SYNTAX	INTEGER
			ACCESS	read-only
			STATUS	current
	DESCRIPTION ""
			::= { mbus5D 48 }

mbus5DValue15		OBJECT-TYPE
			SYNTAX	INTEGER
			ACCESS	read-only
			STATUS	current
	DESCRIPTION ""
			::= { mbus5D 49 }

mbus5DVIF16		OBJECT-TYPE
			SYNTAX	INTEGER
			ACCESS	read-only
			STATUS	current
	DESCRIPTION ""
			::= { mbus5D 50 }

mbus5DValue16		OBJECT-TYPE
			SYNTAX	INTEGER
			ACCESS	read-only
			STATUS	current
	DESCRIPTION ""
			::= { mbus5D 51 }

mbus5DVIF17		OBJECT-TYPE
			SYNTAX	INTEGER
			ACCESS	read-only
			STATUS	current
	DESCRIPTION ""
			::= { mbus5D 52 }

mbus5DValue17		OBJECT-TYPE
			SYNTAX	INTEGER
			ACCESS	read-only
			STATUS	current
	DESCRIPTION ""
			::= { mbus5D 53 }

mbus5DVIF18		OBJECT-TYPE
			SYNTAX	INTEGER
			ACCESS	read-only
			STATUS	current
	DESCRIPTION ""
			::= { mbus5D 54 }

mbus5DValue18		OBJECT-TYPE
			SYNTAX	INTEGER
			ACCESS	read-only
			STATUS	current
	DESCRIPTION ""
			::= { mbus5D 55 }

mbus5DVIF19		OBJECT-TYPE
			SYNTAX	INTEGER
			ACCESS	read-only
			STATUS	current
	DESCRIPTION ""
			::= { mbus5D 56 }

mbus5DValue19		OBJECT-TYPE
			SYNTAX	INTEGER
			ACCESS	read-only
			STATUS	current
	DESCRIPTION ""
			::= { mbus5D 57 }

mbus5DVIF1A		OBJECT-TYPE
			SYNTAX	INTEGER
			ACCESS	read-only
			STATUS	current
	DESCRIPTION ""
			::= { mbus5D 58 }

mbus5DValue1A		OBJECT-TYPE
			SYNTAX	INTEGER
			ACCESS	read-only
			STATUS	current
	DESCRIPTION ""
			::= { mbus5D 59 }

mbus5DVIF1B		OBJECT-TYPE
			SYNTAX	INTEGER
			ACCESS	read-only
			STATUS	current
	DESCRIPTION ""
			::= { mbus5D 60 }

mbus5DValue1B		OBJECT-TYPE
			SYNTAX	INTEGER
			ACCESS	read-only
			STATUS	current
	DESCRIPTION ""
			::= { mbus5D 61 }

mbus5DVIF1C		OBJECT-TYPE
			SYNTAX	INTEGER
			ACCESS	read-only
			STATUS	current
	DESCRIPTION ""
			::= { mbus5D 62 }

mbus5DValue1C		OBJECT-TYPE
			SYNTAX	INTEGER
			ACCESS	read-only
			STATUS	current
	DESCRIPTION ""
			::= { mbus5D 63 }

mbus5DVIF1D		OBJECT-TYPE
			SYNTAX	INTEGER
			ACCESS	read-only
			STATUS	current
	DESCRIPTION ""
			::= { mbus5D 64 }

mbus5DValue1D		OBJECT-TYPE
			SYNTAX	INTEGER
			ACCESS	read-only
			STATUS	current
	DESCRIPTION ""
			::= { mbus5D 65 }

mbus5DVIF1E		OBJECT-TYPE
			SYNTAX	INTEGER
			ACCESS	read-only
			STATUS	current
	DESCRIPTION ""
			::= { mbus5D 66 }

mbus5DValue1E		OBJECT-TYPE
			SYNTAX	INTEGER
			ACCESS	read-only
			STATUS	current
	DESCRIPTION ""
			::= { mbus5D 67 }

mbus5DVIF1F		OBJECT-TYPE
			SYNTAX	INTEGER
			ACCESS	read-only
			STATUS	current
	DESCRIPTION ""
			::= { mbus5D 68 }

mbus5DValue1F		OBJECT-TYPE
			SYNTAX	INTEGER
			ACCESS	read-only
			STATUS	current
	DESCRIPTION ""
			::= { mbus5D 69 }

mbus5DVIF20		OBJECT-TYPE
			SYNTAX	INTEGER
			ACCESS	read-only
			STATUS	current
	DESCRIPTION ""
			::= { mbus5D 70 }

mbus5DValue20		OBJECT-TYPE
			SYNTAX	INTEGER
			ACCESS	read-only
			STATUS	current
	DESCRIPTION ""
			::= { mbus5D 71 }

mbus5DVIF21		OBJECT-TYPE
			SYNTAX	INTEGER
			ACCESS	read-only
			STATUS	current
	DESCRIPTION ""
			::= { mbus5D 72 }

mbus5DValue21		OBJECT-TYPE
			SYNTAX	INTEGER
			ACCESS	read-only
			STATUS	current
	DESCRIPTION ""
			::= { mbus5D 73 }

mbus5DVIF22		OBJECT-TYPE
			SYNTAX	INTEGER
			ACCESS	read-only
			STATUS	current
	DESCRIPTION ""
			::= { mbus5D 74 }

mbus5DValue22		OBJECT-TYPE
			SYNTAX	INTEGER
			ACCESS	read-only
			STATUS	current
	DESCRIPTION ""
			::= { mbus5D 75 }

mbus5DVIF23		OBJECT-TYPE
			SYNTAX	INTEGER
			ACCESS	read-only
			STATUS	current
	DESCRIPTION ""
			::= { mbus5D 76 }

mbus5DValue23		OBJECT-TYPE
			SYNTAX	INTEGER
			ACCESS	read-only
			STATUS	current
	DESCRIPTION ""
			::= { mbus5D 77 }

mbus5DVIF24		OBJECT-TYPE
			SYNTAX	INTEGER
			ACCESS	read-only
			STATUS	current
	DESCRIPTION ""
			::= { mbus5D 78 }

mbus5DValue24		OBJECT-TYPE
			SYNTAX	INTEGER
			ACCESS	read-only
			STATUS	current
	DESCRIPTION ""
			::= { mbus5D 79 }

mbus5DVIF25		OBJECT-TYPE
			SYNTAX	INTEGER
			ACCESS	read-only
			STATUS	current
	DESCRIPTION ""
			::= { mbus5D 80 }

mbus5DValue25		OBJECT-TYPE
			SYNTAX	INTEGER
			ACCESS	read-only
			STATUS	current
	DESCRIPTION ""
			::= { mbus5D 81 }

mbus5DVIF26		OBJECT-TYPE
			SYNTAX	INTEGER
			ACCESS	read-only
			STATUS	current
	DESCRIPTION ""
			::= { mbus5D 82 }

mbus5DValue26		OBJECT-TYPE
			SYNTAX	INTEGER
			ACCESS	read-only
			STATUS	current
	DESCRIPTION ""
			::= { mbus5D 83 }

mbus5DVIF27		OBJECT-TYPE
			SYNTAX	INTEGER
			ACCESS	read-only
			STATUS	current
	DESCRIPTION ""
			::= { mbus5D 84 }

mbus5DValue27		OBJECT-TYPE
			SYNTAX	INTEGER
			ACCESS	read-only
			STATUS	current
	DESCRIPTION ""
			::= { mbus5D 85 }

mbus5DVIF28		OBJECT-TYPE
			SYNTAX	INTEGER
			ACCESS	read-only
			STATUS	current
	DESCRIPTION ""
			::= { mbus5D 86 }

mbus5DValue28		OBJECT-TYPE
			SYNTAX	INTEGER
			ACCESS	read-only
			STATUS	current
	DESCRIPTION ""
			::= { mbus5D 87 }

mbus5DVIF29		OBJECT-TYPE
			SYNTAX	INTEGER
			ACCESS	read-only
			STATUS	current
	DESCRIPTION ""
			::= { mbus5D 88 }

mbus5DValue29		OBJECT-TYPE
			SYNTAX	INTEGER
			ACCESS	read-only
			STATUS	current
	DESCRIPTION ""
			::= { mbus5D 89 }

mbus5DVIF2A		OBJECT-TYPE
			SYNTAX	INTEGER
			ACCESS	read-only
			STATUS	current
	DESCRIPTION ""
			::= { mbus5D 90 }

mbus5DValue2A		OBJECT-TYPE
			SYNTAX	INTEGER
			ACCESS	read-only
			STATUS	current
	DESCRIPTION ""
			::= { mbus5D 91 }

mbus5DVIF2B		OBJECT-TYPE
			SYNTAX	INTEGER
			ACCESS	read-only
			STATUS	current
	DESCRIPTION ""
			::= { mbus5D 92 }

mbus5DValue2B		OBJECT-TYPE
			SYNTAX	INTEGER
			ACCESS	read-only
			STATUS	current
	DESCRIPTION ""
			::= { mbus5D 93 }

mbus5DVIF2C		OBJECT-TYPE
			SYNTAX	INTEGER
			ACCESS	read-only
			STATUS	current
	DESCRIPTION ""
			::= { mbus5D 94 }

mbus5DValue2C		OBJECT-TYPE
			SYNTAX	INTEGER
			ACCESS	read-only
			STATUS	current
	DESCRIPTION ""
			::= { mbus5D 95 }

mbus5DVIF2D		OBJECT-TYPE
			SYNTAX	INTEGER
			ACCESS	read-only
			STATUS	current
	DESCRIPTION ""
			::= { mbus5D 96 }

mbus5DValue2D		OBJECT-TYPE
			SYNTAX	INTEGER
			ACCESS	read-only
			STATUS	current
	DESCRIPTION ""
			::= { mbus5D 97 }

mbus5DVIF2E		OBJECT-TYPE
			SYNTAX	INTEGER
			ACCESS	read-only
			STATUS	current
	DESCRIPTION ""
			::= { mbus5D 98 }

mbus5DValue2E		OBJECT-TYPE
			SYNTAX	INTEGER
			ACCESS	read-only
			STATUS	current
	DESCRIPTION ""
			::= { mbus5D 99 }

mbus5DVIF2F		OBJECT-TYPE
			SYNTAX	INTEGER
			ACCESS	read-only
			STATUS	current
	DESCRIPTION ""
			::= { mbus5D 100 }

mbus5DValue2F		OBJECT-TYPE
			SYNTAX	INTEGER
			ACCESS	read-only
			STATUS	current
	DESCRIPTION ""
			::= { mbus5D 101 }

mbus5E			OBJECT IDENTIFIER ::= { mbus 94 }

mbus5EIdNumber		OBJECT-TYPE
			SYNTAX	Gauge
			ACCESS	read-only
			STATUS	current
	DESCRIPTION ""
			::= { mbus5E 1 }

mbus5EManufacturer	OBJECT-TYPE
			SYNTAX	Gauge
			ACCESS	read-only
			STATUS	current
	DESCRIPTION ""
			::= { mbus5E 2 }

mbus5EVersion		OBJECT-TYPE
			SYNTAX	Gauge
			ACCESS	read-only
			STATUS	current
	DESCRIPTION ""
			::= { mbus5E 3 }

mbus5EMedium		OBJECT-TYPE
			SYNTAX	Gauge
			ACCESS	read-only
			STATUS	current
	DESCRIPTION ""
			::= { mbus5E 4 }

mbus5EStatus		OBJECT-TYPE
			SYNTAX	Gauge
			ACCESS	read-only
			STATUS	current
	DESCRIPTION ""
			::= { mbus5E 5 }

mbus5EVIF00		OBJECT-TYPE
			SYNTAX	INTEGER
			ACCESS	read-only
			STATUS	current
	DESCRIPTION ""
			::= { mbus5E 6 }

mbus5EValue00		OBJECT-TYPE
			SYNTAX	INTEGER
			ACCESS	read-only
			STATUS	current
	DESCRIPTION ""
			::= { mbus5E 7 }

mbus5EVIF01		OBJECT-TYPE
			SYNTAX	INTEGER
			ACCESS	read-only
			STATUS	current
	DESCRIPTION ""
			::= { mbus5E 8 }

mbus5EValue01		OBJECT-TYPE
			SYNTAX	INTEGER
			ACCESS	read-only
			STATUS	current
	DESCRIPTION ""
			::= { mbus5E 9 }

mbus5EVIF02		OBJECT-TYPE
			SYNTAX	INTEGER
			ACCESS	read-only
			STATUS	current
	DESCRIPTION ""
			::= { mbus5E 10 }

mbus5EValue02		OBJECT-TYPE
			SYNTAX	INTEGER
			ACCESS	read-only
			STATUS	current
	DESCRIPTION ""
			::= { mbus5E 11 }

mbus5EVIF03		OBJECT-TYPE
			SYNTAX	INTEGER
			ACCESS	read-only
			STATUS	current
	DESCRIPTION ""
			::= { mbus5E 12 }

mbus5EValue03		OBJECT-TYPE
			SYNTAX	INTEGER
			ACCESS	read-only
			STATUS	current
	DESCRIPTION ""
			::= { mbus5E 13 }

mbus5EVIF04		OBJECT-TYPE
			SYNTAX	INTEGER
			ACCESS	read-only
			STATUS	current
	DESCRIPTION ""
			::= { mbus5E 14 }

mbus5EValue04		OBJECT-TYPE
			SYNTAX	INTEGER
			ACCESS	read-only
			STATUS	current
	DESCRIPTION ""
			::= { mbus5E 15 }

mbus5EVIF05		OBJECT-TYPE
			SYNTAX	INTEGER
			ACCESS	read-only
			STATUS	current
	DESCRIPTION ""
			::= { mbus5E 16 }

mbus5EValue05		OBJECT-TYPE
			SYNTAX	INTEGER
			ACCESS	read-only
			STATUS	current
	DESCRIPTION ""
			::= { mbus5E 17 }

mbus5EVIF06		OBJECT-TYPE
			SYNTAX	INTEGER
			ACCESS	read-only
			STATUS	current
	DESCRIPTION ""
			::= { mbus5E 18 }

mbus5EValue06		OBJECT-TYPE
			SYNTAX	INTEGER
			ACCESS	read-only
			STATUS	current
	DESCRIPTION ""
			::= { mbus5E 19 }

mbus5EVIF07		OBJECT-TYPE
			SYNTAX	INTEGER
			ACCESS	read-only
			STATUS	current
	DESCRIPTION ""
			::= { mbus5E 20 }

mbus5EValue07		OBJECT-TYPE
			SYNTAX	INTEGER
			ACCESS	read-only
			STATUS	current
	DESCRIPTION ""
			::= { mbus5E 21 }

mbus5EVIF08		OBJECT-TYPE
			SYNTAX	INTEGER
			ACCESS	read-only
			STATUS	current
	DESCRIPTION ""
			::= { mbus5E 22 }

mbus5EValue08		OBJECT-TYPE
			SYNTAX	INTEGER
			ACCESS	read-only
			STATUS	current
	DESCRIPTION ""
			::= { mbus5E 23 }

mbus5EVIF09		OBJECT-TYPE
			SYNTAX	INTEGER
			ACCESS	read-only
			STATUS	current
	DESCRIPTION ""
			::= { mbus5E 24 }

mbus5EValue09		OBJECT-TYPE
			SYNTAX	INTEGER
			ACCESS	read-only
			STATUS	current
	DESCRIPTION ""
			::= { mbus5E 25 }

mbus5EVIF0A		OBJECT-TYPE
			SYNTAX	INTEGER
			ACCESS	read-only
			STATUS	current
	DESCRIPTION ""
			::= { mbus5E 26 }

mbus5EValue0A		OBJECT-TYPE
			SYNTAX	INTEGER
			ACCESS	read-only
			STATUS	current
	DESCRIPTION ""
			::= { mbus5E 27 }

mbus5EVIF0B		OBJECT-TYPE
			SYNTAX	INTEGER
			ACCESS	read-only
			STATUS	current
	DESCRIPTION ""
			::= { mbus5E 28 }

mbus5EValue0B		OBJECT-TYPE
			SYNTAX	INTEGER
			ACCESS	read-only
			STATUS	current
	DESCRIPTION ""
			::= { mbus5E 29 }

mbus5EVIF0C		OBJECT-TYPE
			SYNTAX	INTEGER
			ACCESS	read-only
			STATUS	current
	DESCRIPTION ""
			::= { mbus5E 30 }

mbus5EValue0C		OBJECT-TYPE
			SYNTAX	INTEGER
			ACCESS	read-only
			STATUS	current
	DESCRIPTION ""
			::= { mbus5E 31 }

mbus5EVIF0D		OBJECT-TYPE
			SYNTAX	INTEGER
			ACCESS	read-only
			STATUS	current
	DESCRIPTION ""
			::= { mbus5E 32 }

mbus5EValue0D		OBJECT-TYPE
			SYNTAX	INTEGER
			ACCESS	read-only
			STATUS	current
	DESCRIPTION ""
			::= { mbus5E 33 }

mbus5EVIF0E		OBJECT-TYPE
			SYNTAX	INTEGER
			ACCESS	read-only
			STATUS	current
	DESCRIPTION ""
			::= { mbus5E 34 }

mbus5EValue0E		OBJECT-TYPE
			SYNTAX	INTEGER
			ACCESS	read-only
			STATUS	current
	DESCRIPTION ""
			::= { mbus5E 35 }

mbus5EVIF0F		OBJECT-TYPE
			SYNTAX	INTEGER
			ACCESS	read-only
			STATUS	current
	DESCRIPTION ""
			::= { mbus5E 36 }

mbus5EValue0F		OBJECT-TYPE
			SYNTAX	INTEGER
			ACCESS	read-only
			STATUS	current
	DESCRIPTION ""
			::= { mbus5E 37 }

mbus5EVIF10		OBJECT-TYPE
			SYNTAX	INTEGER
			ACCESS	read-only
			STATUS	current
	DESCRIPTION ""
			::= { mbus5E 38 }

mbus5EValue10		OBJECT-TYPE
			SYNTAX	INTEGER
			ACCESS	read-only
			STATUS	current
	DESCRIPTION ""
			::= { mbus5E 39 }

mbus5EVIF11		OBJECT-TYPE
			SYNTAX	INTEGER
			ACCESS	read-only
			STATUS	current
	DESCRIPTION ""
			::= { mbus5E 40 }

mbus5EValue11		OBJECT-TYPE
			SYNTAX	INTEGER
			ACCESS	read-only
			STATUS	current
	DESCRIPTION ""
			::= { mbus5E 41 }

mbus5EVIF12		OBJECT-TYPE
			SYNTAX	INTEGER
			ACCESS	read-only
			STATUS	current
	DESCRIPTION ""
			::= { mbus5E 42 }

mbus5EValue12		OBJECT-TYPE
			SYNTAX	INTEGER
			ACCESS	read-only
			STATUS	current
	DESCRIPTION ""
			::= { mbus5E 43 }

mbus5EVIF13		OBJECT-TYPE
			SYNTAX	INTEGER
			ACCESS	read-only
			STATUS	current
	DESCRIPTION ""
			::= { mbus5E 44 }

mbus5EValue13		OBJECT-TYPE
			SYNTAX	INTEGER
			ACCESS	read-only
			STATUS	current
	DESCRIPTION ""
			::= { mbus5E 45 }

mbus5EVIF14		OBJECT-TYPE
			SYNTAX	INTEGER
			ACCESS	read-only
			STATUS	current
	DESCRIPTION ""
			::= { mbus5E 46 }

mbus5EValue14		OBJECT-TYPE
			SYNTAX	INTEGER
			ACCESS	read-only
			STATUS	current
	DESCRIPTION ""
			::= { mbus5E 47 }

mbus5EVIF15		OBJECT-TYPE
			SYNTAX	INTEGER
			ACCESS	read-only
			STATUS	current
	DESCRIPTION ""
			::= { mbus5E 48 }

mbus5EValue15		OBJECT-TYPE
			SYNTAX	INTEGER
			ACCESS	read-only
			STATUS	current
	DESCRIPTION ""
			::= { mbus5E 49 }

mbus5EVIF16		OBJECT-TYPE
			SYNTAX	INTEGER
			ACCESS	read-only
			STATUS	current
	DESCRIPTION ""
			::= { mbus5E 50 }

mbus5EValue16		OBJECT-TYPE
			SYNTAX	INTEGER
			ACCESS	read-only
			STATUS	current
	DESCRIPTION ""
			::= { mbus5E 51 }

mbus5EVIF17		OBJECT-TYPE
			SYNTAX	INTEGER
			ACCESS	read-only
			STATUS	current
	DESCRIPTION ""
			::= { mbus5E 52 }

mbus5EValue17		OBJECT-TYPE
			SYNTAX	INTEGER
			ACCESS	read-only
			STATUS	current
	DESCRIPTION ""
			::= { mbus5E 53 }

mbus5EVIF18		OBJECT-TYPE
			SYNTAX	INTEGER
			ACCESS	read-only
			STATUS	current
	DESCRIPTION ""
			::= { mbus5E 54 }

mbus5EValue18		OBJECT-TYPE
			SYNTAX	INTEGER
			ACCESS	read-only
			STATUS	current
	DESCRIPTION ""
			::= { mbus5E 55 }

mbus5EVIF19		OBJECT-TYPE
			SYNTAX	INTEGER
			ACCESS	read-only
			STATUS	current
	DESCRIPTION ""
			::= { mbus5E 56 }

mbus5EValue19		OBJECT-TYPE
			SYNTAX	INTEGER
			ACCESS	read-only
			STATUS	current
	DESCRIPTION ""
			::= { mbus5E 57 }

mbus5EVIF1A		OBJECT-TYPE
			SYNTAX	INTEGER
			ACCESS	read-only
			STATUS	current
	DESCRIPTION ""
			::= { mbus5E 58 }

mbus5EValue1A		OBJECT-TYPE
			SYNTAX	INTEGER
			ACCESS	read-only
			STATUS	current
	DESCRIPTION ""
			::= { mbus5E 59 }

mbus5EVIF1B		OBJECT-TYPE
			SYNTAX	INTEGER
			ACCESS	read-only
			STATUS	current
	DESCRIPTION ""
			::= { mbus5E 60 }

mbus5EValue1B		OBJECT-TYPE
			SYNTAX	INTEGER
			ACCESS	read-only
			STATUS	current
	DESCRIPTION ""
			::= { mbus5E 61 }

mbus5EVIF1C		OBJECT-TYPE
			SYNTAX	INTEGER
			ACCESS	read-only
			STATUS	current
	DESCRIPTION ""
			::= { mbus5E 62 }

mbus5EValue1C		OBJECT-TYPE
			SYNTAX	INTEGER
			ACCESS	read-only
			STATUS	current
	DESCRIPTION ""
			::= { mbus5E 63 }

mbus5EVIF1D		OBJECT-TYPE
			SYNTAX	INTEGER
			ACCESS	read-only
			STATUS	current
	DESCRIPTION ""
			::= { mbus5E 64 }

mbus5EValue1D		OBJECT-TYPE
			SYNTAX	INTEGER
			ACCESS	read-only
			STATUS	current
	DESCRIPTION ""
			::= { mbus5E 65 }

mbus5EVIF1E		OBJECT-TYPE
			SYNTAX	INTEGER
			ACCESS	read-only
			STATUS	current
	DESCRIPTION ""
			::= { mbus5E 66 }

mbus5EValue1E		OBJECT-TYPE
			SYNTAX	INTEGER
			ACCESS	read-only
			STATUS	current
	DESCRIPTION ""
			::= { mbus5E 67 }

mbus5EVIF1F		OBJECT-TYPE
			SYNTAX	INTEGER
			ACCESS	read-only
			STATUS	current
	DESCRIPTION ""
			::= { mbus5E 68 }

mbus5EValue1F		OBJECT-TYPE
			SYNTAX	INTEGER
			ACCESS	read-only
			STATUS	current
	DESCRIPTION ""
			::= { mbus5E 69 }

mbus5EVIF20		OBJECT-TYPE
			SYNTAX	INTEGER
			ACCESS	read-only
			STATUS	current
	DESCRIPTION ""
			::= { mbus5E 70 }

mbus5EValue20		OBJECT-TYPE
			SYNTAX	INTEGER
			ACCESS	read-only
			STATUS	current
	DESCRIPTION ""
			::= { mbus5E 71 }

mbus5EVIF21		OBJECT-TYPE
			SYNTAX	INTEGER
			ACCESS	read-only
			STATUS	current
	DESCRIPTION ""
			::= { mbus5E 72 }

mbus5EValue21		OBJECT-TYPE
			SYNTAX	INTEGER
			ACCESS	read-only
			STATUS	current
	DESCRIPTION ""
			::= { mbus5E 73 }

mbus5EVIF22		OBJECT-TYPE
			SYNTAX	INTEGER
			ACCESS	read-only
			STATUS	current
	DESCRIPTION ""
			::= { mbus5E 74 }

mbus5EValue22		OBJECT-TYPE
			SYNTAX	INTEGER
			ACCESS	read-only
			STATUS	current
	DESCRIPTION ""
			::= { mbus5E 75 }

mbus5EVIF23		OBJECT-TYPE
			SYNTAX	INTEGER
			ACCESS	read-only
			STATUS	current
	DESCRIPTION ""
			::= { mbus5E 76 }

mbus5EValue23		OBJECT-TYPE
			SYNTAX	INTEGER
			ACCESS	read-only
			STATUS	current
	DESCRIPTION ""
			::= { mbus5E 77 }

mbus5EVIF24		OBJECT-TYPE
			SYNTAX	INTEGER
			ACCESS	read-only
			STATUS	current
	DESCRIPTION ""
			::= { mbus5E 78 }

mbus5EValue24		OBJECT-TYPE
			SYNTAX	INTEGER
			ACCESS	read-only
			STATUS	current
	DESCRIPTION ""
			::= { mbus5E 79 }

mbus5EVIF25		OBJECT-TYPE
			SYNTAX	INTEGER
			ACCESS	read-only
			STATUS	current
	DESCRIPTION ""
			::= { mbus5E 80 }

mbus5EValue25		OBJECT-TYPE
			SYNTAX	INTEGER
			ACCESS	read-only
			STATUS	current
	DESCRIPTION ""
			::= { mbus5E 81 }

mbus5EVIF26		OBJECT-TYPE
			SYNTAX	INTEGER
			ACCESS	read-only
			STATUS	current
	DESCRIPTION ""
			::= { mbus5E 82 }

mbus5EValue26		OBJECT-TYPE
			SYNTAX	INTEGER
			ACCESS	read-only
			STATUS	current
	DESCRIPTION ""
			::= { mbus5E 83 }

mbus5EVIF27		OBJECT-TYPE
			SYNTAX	INTEGER
			ACCESS	read-only
			STATUS	current
	DESCRIPTION ""
			::= { mbus5E 84 }

mbus5EValue27		OBJECT-TYPE
			SYNTAX	INTEGER
			ACCESS	read-only
			STATUS	current
	DESCRIPTION ""
			::= { mbus5E 85 }

mbus5EVIF28		OBJECT-TYPE
			SYNTAX	INTEGER
			ACCESS	read-only
			STATUS	current
	DESCRIPTION ""
			::= { mbus5E 86 }

mbus5EValue28		OBJECT-TYPE
			SYNTAX	INTEGER
			ACCESS	read-only
			STATUS	current
	DESCRIPTION ""
			::= { mbus5E 87 }

mbus5EVIF29		OBJECT-TYPE
			SYNTAX	INTEGER
			ACCESS	read-only
			STATUS	current
	DESCRIPTION ""
			::= { mbus5E 88 }

mbus5EValue29		OBJECT-TYPE
			SYNTAX	INTEGER
			ACCESS	read-only
			STATUS	current
	DESCRIPTION ""
			::= { mbus5E 89 }

mbus5EVIF2A		OBJECT-TYPE
			SYNTAX	INTEGER
			ACCESS	read-only
			STATUS	current
	DESCRIPTION ""
			::= { mbus5E 90 }

mbus5EValue2A		OBJECT-TYPE
			SYNTAX	INTEGER
			ACCESS	read-only
			STATUS	current
	DESCRIPTION ""
			::= { mbus5E 91 }

mbus5EVIF2B		OBJECT-TYPE
			SYNTAX	INTEGER
			ACCESS	read-only
			STATUS	current
	DESCRIPTION ""
			::= { mbus5E 92 }

mbus5EValue2B		OBJECT-TYPE
			SYNTAX	INTEGER
			ACCESS	read-only
			STATUS	current
	DESCRIPTION ""
			::= { mbus5E 93 }

mbus5EVIF2C		OBJECT-TYPE
			SYNTAX	INTEGER
			ACCESS	read-only
			STATUS	current
	DESCRIPTION ""
			::= { mbus5E 94 }

mbus5EValue2C		OBJECT-TYPE
			SYNTAX	INTEGER
			ACCESS	read-only
			STATUS	current
	DESCRIPTION ""
			::= { mbus5E 95 }

mbus5EVIF2D		OBJECT-TYPE
			SYNTAX	INTEGER
			ACCESS	read-only
			STATUS	current
	DESCRIPTION ""
			::= { mbus5E 96 }

mbus5EValue2D		OBJECT-TYPE
			SYNTAX	INTEGER
			ACCESS	read-only
			STATUS	current
	DESCRIPTION ""
			::= { mbus5E 97 }

mbus5EVIF2E		OBJECT-TYPE
			SYNTAX	INTEGER
			ACCESS	read-only
			STATUS	current
	DESCRIPTION ""
			::= { mbus5E 98 }

mbus5EValue2E		OBJECT-TYPE
			SYNTAX	INTEGER
			ACCESS	read-only
			STATUS	current
	DESCRIPTION ""
			::= { mbus5E 99 }

mbus5EVIF2F		OBJECT-TYPE
			SYNTAX	INTEGER
			ACCESS	read-only
			STATUS	current
	DESCRIPTION ""
			::= { mbus5E 100 }

mbus5EValue2F		OBJECT-TYPE
			SYNTAX	INTEGER
			ACCESS	read-only
			STATUS	current
	DESCRIPTION ""
			::= { mbus5E 101 }

mbus5F			OBJECT IDENTIFIER ::= { mbus 95 }

mbus5FIdNumber		OBJECT-TYPE
			SYNTAX	Gauge
			ACCESS	read-only
			STATUS	current
	DESCRIPTION ""
			::= { mbus5F 1 }

mbus5FManufacturer	OBJECT-TYPE
			SYNTAX	Gauge
			ACCESS	read-only
			STATUS	current
	DESCRIPTION ""
			::= { mbus5F 2 }

mbus5FVersion		OBJECT-TYPE
			SYNTAX	Gauge
			ACCESS	read-only
			STATUS	current
	DESCRIPTION ""
			::= { mbus5F 3 }

mbus5FMedium		OBJECT-TYPE
			SYNTAX	Gauge
			ACCESS	read-only
			STATUS	current
	DESCRIPTION ""
			::= { mbus5F 4 }

mbus5FStatus		OBJECT-TYPE
			SYNTAX	Gauge
			ACCESS	read-only
			STATUS	current
	DESCRIPTION ""
			::= { mbus5F 5 }

mbus5FVIF00		OBJECT-TYPE
			SYNTAX	INTEGER
			ACCESS	read-only
			STATUS	current
	DESCRIPTION ""
			::= { mbus5F 6 }

mbus5FValue00		OBJECT-TYPE
			SYNTAX	INTEGER
			ACCESS	read-only
			STATUS	current
	DESCRIPTION ""
			::= { mbus5F 7 }

mbus5FVIF01		OBJECT-TYPE
			SYNTAX	INTEGER
			ACCESS	read-only
			STATUS	current
	DESCRIPTION ""
			::= { mbus5F 8 }

mbus5FValue01		OBJECT-TYPE
			SYNTAX	INTEGER
			ACCESS	read-only
			STATUS	current
	DESCRIPTION ""
			::= { mbus5F 9 }

mbus5FVIF02		OBJECT-TYPE
			SYNTAX	INTEGER
			ACCESS	read-only
			STATUS	current
	DESCRIPTION ""
			::= { mbus5F 10 }

mbus5FValue02		OBJECT-TYPE
			SYNTAX	INTEGER
			ACCESS	read-only
			STATUS	current
	DESCRIPTION ""
			::= { mbus5F 11 }

mbus5FVIF03		OBJECT-TYPE
			SYNTAX	INTEGER
			ACCESS	read-only
			STATUS	current
	DESCRIPTION ""
			::= { mbus5F 12 }

mbus5FValue03		OBJECT-TYPE
			SYNTAX	INTEGER
			ACCESS	read-only
			STATUS	current
	DESCRIPTION ""
			::= { mbus5F 13 }

mbus5FVIF04		OBJECT-TYPE
			SYNTAX	INTEGER
			ACCESS	read-only
			STATUS	current
	DESCRIPTION ""
			::= { mbus5F 14 }

mbus5FValue04		OBJECT-TYPE
			SYNTAX	INTEGER
			ACCESS	read-only
			STATUS	current
	DESCRIPTION ""
			::= { mbus5F 15 }

mbus5FVIF05		OBJECT-TYPE
			SYNTAX	INTEGER
			ACCESS	read-only
			STATUS	current
	DESCRIPTION ""
			::= { mbus5F 16 }

mbus5FValue05		OBJECT-TYPE
			SYNTAX	INTEGER
			ACCESS	read-only
			STATUS	current
	DESCRIPTION ""
			::= { mbus5F 17 }

mbus5FVIF06		OBJECT-TYPE
			SYNTAX	INTEGER
			ACCESS	read-only
			STATUS	current
	DESCRIPTION ""
			::= { mbus5F 18 }

mbus5FValue06		OBJECT-TYPE
			SYNTAX	INTEGER
			ACCESS	read-only
			STATUS	current
	DESCRIPTION ""
			::= { mbus5F 19 }

mbus5FVIF07		OBJECT-TYPE
			SYNTAX	INTEGER
			ACCESS	read-only
			STATUS	current
	DESCRIPTION ""
			::= { mbus5F 20 }

mbus5FValue07		OBJECT-TYPE
			SYNTAX	INTEGER
			ACCESS	read-only
			STATUS	current
	DESCRIPTION ""
			::= { mbus5F 21 }

mbus5FVIF08		OBJECT-TYPE
			SYNTAX	INTEGER
			ACCESS	read-only
			STATUS	current
	DESCRIPTION ""
			::= { mbus5F 22 }

mbus5FValue08		OBJECT-TYPE
			SYNTAX	INTEGER
			ACCESS	read-only
			STATUS	current
	DESCRIPTION ""
			::= { mbus5F 23 }

mbus5FVIF09		OBJECT-TYPE
			SYNTAX	INTEGER
			ACCESS	read-only
			STATUS	current
	DESCRIPTION ""
			::= { mbus5F 24 }

mbus5FValue09		OBJECT-TYPE
			SYNTAX	INTEGER
			ACCESS	read-only
			STATUS	current
	DESCRIPTION ""
			::= { mbus5F 25 }

mbus5FVIF0A		OBJECT-TYPE
			SYNTAX	INTEGER
			ACCESS	read-only
			STATUS	current
	DESCRIPTION ""
			::= { mbus5F 26 }

mbus5FValue0A		OBJECT-TYPE
			SYNTAX	INTEGER
			ACCESS	read-only
			STATUS	current
	DESCRIPTION ""
			::= { mbus5F 27 }

mbus5FVIF0B		OBJECT-TYPE
			SYNTAX	INTEGER
			ACCESS	read-only
			STATUS	current
	DESCRIPTION ""
			::= { mbus5F 28 }

mbus5FValue0B		OBJECT-TYPE
			SYNTAX	INTEGER
			ACCESS	read-only
			STATUS	current
	DESCRIPTION ""
			::= { mbus5F 29 }

mbus5FVIF0C		OBJECT-TYPE
			SYNTAX	INTEGER
			ACCESS	read-only
			STATUS	current
	DESCRIPTION ""
			::= { mbus5F 30 }

mbus5FValue0C		OBJECT-TYPE
			SYNTAX	INTEGER
			ACCESS	read-only
			STATUS	current
	DESCRIPTION ""
			::= { mbus5F 31 }

mbus5FVIF0D		OBJECT-TYPE
			SYNTAX	INTEGER
			ACCESS	read-only
			STATUS	current
	DESCRIPTION ""
			::= { mbus5F 32 }

mbus5FValue0D		OBJECT-TYPE
			SYNTAX	INTEGER
			ACCESS	read-only
			STATUS	current
	DESCRIPTION ""
			::= { mbus5F 33 }

mbus5FVIF0E		OBJECT-TYPE
			SYNTAX	INTEGER
			ACCESS	read-only
			STATUS	current
	DESCRIPTION ""
			::= { mbus5F 34 }

mbus5FValue0E		OBJECT-TYPE
			SYNTAX	INTEGER
			ACCESS	read-only
			STATUS	current
	DESCRIPTION ""
			::= { mbus5F 35 }

mbus5FVIF0F		OBJECT-TYPE
			SYNTAX	INTEGER
			ACCESS	read-only
			STATUS	current
	DESCRIPTION ""
			::= { mbus5F 36 }

mbus5FValue0F		OBJECT-TYPE
			SYNTAX	INTEGER
			ACCESS	read-only
			STATUS	current
	DESCRIPTION ""
			::= { mbus5F 37 }

mbus5FVIF10		OBJECT-TYPE
			SYNTAX	INTEGER
			ACCESS	read-only
			STATUS	current
	DESCRIPTION ""
			::= { mbus5F 38 }

mbus5FValue10		OBJECT-TYPE
			SYNTAX	INTEGER
			ACCESS	read-only
			STATUS	current
	DESCRIPTION ""
			::= { mbus5F 39 }

mbus5FVIF11		OBJECT-TYPE
			SYNTAX	INTEGER
			ACCESS	read-only
			STATUS	current
	DESCRIPTION ""
			::= { mbus5F 40 }

mbus5FValue11		OBJECT-TYPE
			SYNTAX	INTEGER
			ACCESS	read-only
			STATUS	current
	DESCRIPTION ""
			::= { mbus5F 41 }

mbus5FVIF12		OBJECT-TYPE
			SYNTAX	INTEGER
			ACCESS	read-only
			STATUS	current
	DESCRIPTION ""
			::= { mbus5F 42 }

mbus5FValue12		OBJECT-TYPE
			SYNTAX	INTEGER
			ACCESS	read-only
			STATUS	current
	DESCRIPTION ""
			::= { mbus5F 43 }

mbus5FVIF13		OBJECT-TYPE
			SYNTAX	INTEGER
			ACCESS	read-only
			STATUS	current
	DESCRIPTION ""
			::= { mbus5F 44 }

mbus5FValue13		OBJECT-TYPE
			SYNTAX	INTEGER
			ACCESS	read-only
			STATUS	current
	DESCRIPTION ""
			::= { mbus5F 45 }

mbus5FVIF14		OBJECT-TYPE
			SYNTAX	INTEGER
			ACCESS	read-only
			STATUS	current
	DESCRIPTION ""
			::= { mbus5F 46 }

mbus5FValue14		OBJECT-TYPE
			SYNTAX	INTEGER
			ACCESS	read-only
			STATUS	current
	DESCRIPTION ""
			::= { mbus5F 47 }

mbus5FVIF15		OBJECT-TYPE
			SYNTAX	INTEGER
			ACCESS	read-only
			STATUS	current
	DESCRIPTION ""
			::= { mbus5F 48 }

mbus5FValue15		OBJECT-TYPE
			SYNTAX	INTEGER
			ACCESS	read-only
			STATUS	current
	DESCRIPTION ""
			::= { mbus5F 49 }

mbus5FVIF16		OBJECT-TYPE
			SYNTAX	INTEGER
			ACCESS	read-only
			STATUS	current
	DESCRIPTION ""
			::= { mbus5F 50 }

mbus5FValue16		OBJECT-TYPE
			SYNTAX	INTEGER
			ACCESS	read-only
			STATUS	current
	DESCRIPTION ""
			::= { mbus5F 51 }

mbus5FVIF17		OBJECT-TYPE
			SYNTAX	INTEGER
			ACCESS	read-only
			STATUS	current
	DESCRIPTION ""
			::= { mbus5F 52 }

mbus5FValue17		OBJECT-TYPE
			SYNTAX	INTEGER
			ACCESS	read-only
			STATUS	current
	DESCRIPTION ""
			::= { mbus5F 53 }

mbus5FVIF18		OBJECT-TYPE
			SYNTAX	INTEGER
			ACCESS	read-only
			STATUS	current
	DESCRIPTION ""
			::= { mbus5F 54 }

mbus5FValue18		OBJECT-TYPE
			SYNTAX	INTEGER
			ACCESS	read-only
			STATUS	current
	DESCRIPTION ""
			::= { mbus5F 55 }

mbus5FVIF19		OBJECT-TYPE
			SYNTAX	INTEGER
			ACCESS	read-only
			STATUS	current
	DESCRIPTION ""
			::= { mbus5F 56 }

mbus5FValue19		OBJECT-TYPE
			SYNTAX	INTEGER
			ACCESS	read-only
			STATUS	current
	DESCRIPTION ""
			::= { mbus5F 57 }

mbus5FVIF1A		OBJECT-TYPE
			SYNTAX	INTEGER
			ACCESS	read-only
			STATUS	current
	DESCRIPTION ""
			::= { mbus5F 58 }

mbus5FValue1A		OBJECT-TYPE
			SYNTAX	INTEGER
			ACCESS	read-only
			STATUS	current
	DESCRIPTION ""
			::= { mbus5F 59 }

mbus5FVIF1B		OBJECT-TYPE
			SYNTAX	INTEGER
			ACCESS	read-only
			STATUS	current
	DESCRIPTION ""
			::= { mbus5F 60 }

mbus5FValue1B		OBJECT-TYPE
			SYNTAX	INTEGER
			ACCESS	read-only
			STATUS	current
	DESCRIPTION ""
			::= { mbus5F 61 }

mbus5FVIF1C		OBJECT-TYPE
			SYNTAX	INTEGER
			ACCESS	read-only
			STATUS	current
	DESCRIPTION ""
			::= { mbus5F 62 }

mbus5FValue1C		OBJECT-TYPE
			SYNTAX	INTEGER
			ACCESS	read-only
			STATUS	current
	DESCRIPTION ""
			::= { mbus5F 63 }

mbus5FVIF1D		OBJECT-TYPE
			SYNTAX	INTEGER
			ACCESS	read-only
			STATUS	current
	DESCRIPTION ""
			::= { mbus5F 64 }

mbus5FValue1D		OBJECT-TYPE
			SYNTAX	INTEGER
			ACCESS	read-only
			STATUS	current
	DESCRIPTION ""
			::= { mbus5F 65 }

mbus5FVIF1E		OBJECT-TYPE
			SYNTAX	INTEGER
			ACCESS	read-only
			STATUS	current
	DESCRIPTION ""
			::= { mbus5F 66 }

mbus5FValue1E		OBJECT-TYPE
			SYNTAX	INTEGER
			ACCESS	read-only
			STATUS	current
	DESCRIPTION ""
			::= { mbus5F 67 }

mbus5FVIF1F		OBJECT-TYPE
			SYNTAX	INTEGER
			ACCESS	read-only
			STATUS	current
	DESCRIPTION ""
			::= { mbus5F 68 }

mbus5FValue1F		OBJECT-TYPE
			SYNTAX	INTEGER
			ACCESS	read-only
			STATUS	current
	DESCRIPTION ""
			::= { mbus5F 69 }

mbus5FVIF20		OBJECT-TYPE
			SYNTAX	INTEGER
			ACCESS	read-only
			STATUS	current
	DESCRIPTION ""
			::= { mbus5F 70 }

mbus5FValue20		OBJECT-TYPE
			SYNTAX	INTEGER
			ACCESS	read-only
			STATUS	current
	DESCRIPTION ""
			::= { mbus5F 71 }

mbus5FVIF21		OBJECT-TYPE
			SYNTAX	INTEGER
			ACCESS	read-only
			STATUS	current
	DESCRIPTION ""
			::= { mbus5F 72 }

mbus5FValue21		OBJECT-TYPE
			SYNTAX	INTEGER
			ACCESS	read-only
			STATUS	current
	DESCRIPTION ""
			::= { mbus5F 73 }

mbus5FVIF22		OBJECT-TYPE
			SYNTAX	INTEGER
			ACCESS	read-only
			STATUS	current
	DESCRIPTION ""
			::= { mbus5F 74 }

mbus5FValue22		OBJECT-TYPE
			SYNTAX	INTEGER
			ACCESS	read-only
			STATUS	current
	DESCRIPTION ""
			::= { mbus5F 75 }

mbus5FVIF23		OBJECT-TYPE
			SYNTAX	INTEGER
			ACCESS	read-only
			STATUS	current
	DESCRIPTION ""
			::= { mbus5F 76 }

mbus5FValue23		OBJECT-TYPE
			SYNTAX	INTEGER
			ACCESS	read-only
			STATUS	current
	DESCRIPTION ""
			::= { mbus5F 77 }

mbus5FVIF24		OBJECT-TYPE
			SYNTAX	INTEGER
			ACCESS	read-only
			STATUS	current
	DESCRIPTION ""
			::= { mbus5F 78 }

mbus5FValue24		OBJECT-TYPE
			SYNTAX	INTEGER
			ACCESS	read-only
			STATUS	current
	DESCRIPTION ""
			::= { mbus5F 79 }

mbus5FVIF25		OBJECT-TYPE
			SYNTAX	INTEGER
			ACCESS	read-only
			STATUS	current
	DESCRIPTION ""
			::= { mbus5F 80 }

mbus5FValue25		OBJECT-TYPE
			SYNTAX	INTEGER
			ACCESS	read-only
			STATUS	current
	DESCRIPTION ""
			::= { mbus5F 81 }

mbus5FVIF26		OBJECT-TYPE
			SYNTAX	INTEGER
			ACCESS	read-only
			STATUS	current
	DESCRIPTION ""
			::= { mbus5F 82 }

mbus5FValue26		OBJECT-TYPE
			SYNTAX	INTEGER
			ACCESS	read-only
			STATUS	current
	DESCRIPTION ""
			::= { mbus5F 83 }

mbus5FVIF27		OBJECT-TYPE
			SYNTAX	INTEGER
			ACCESS	read-only
			STATUS	current
	DESCRIPTION ""
			::= { mbus5F 84 }

mbus5FValue27		OBJECT-TYPE
			SYNTAX	INTEGER
			ACCESS	read-only
			STATUS	current
	DESCRIPTION ""
			::= { mbus5F 85 }

mbus5FVIF28		OBJECT-TYPE
			SYNTAX	INTEGER
			ACCESS	read-only
			STATUS	current
	DESCRIPTION ""
			::= { mbus5F 86 }

mbus5FValue28		OBJECT-TYPE
			SYNTAX	INTEGER
			ACCESS	read-only
			STATUS	current
	DESCRIPTION ""
			::= { mbus5F 87 }

mbus5FVIF29		OBJECT-TYPE
			SYNTAX	INTEGER
			ACCESS	read-only
			STATUS	current
	DESCRIPTION ""
			::= { mbus5F 88 }

mbus5FValue29		OBJECT-TYPE
			SYNTAX	INTEGER
			ACCESS	read-only
			STATUS	current
	DESCRIPTION ""
			::= { mbus5F 89 }

mbus5FVIF2A		OBJECT-TYPE
			SYNTAX	INTEGER
			ACCESS	read-only
			STATUS	current
	DESCRIPTION ""
			::= { mbus5F 90 }

mbus5FValue2A		OBJECT-TYPE
			SYNTAX	INTEGER
			ACCESS	read-only
			STATUS	current
	DESCRIPTION ""
			::= { mbus5F 91 }

mbus5FVIF2B		OBJECT-TYPE
			SYNTAX	INTEGER
			ACCESS	read-only
			STATUS	current
	DESCRIPTION ""
			::= { mbus5F 92 }

mbus5FValue2B		OBJECT-TYPE
			SYNTAX	INTEGER
			ACCESS	read-only
			STATUS	current
	DESCRIPTION ""
			::= { mbus5F 93 }

mbus5FVIF2C		OBJECT-TYPE
			SYNTAX	INTEGER
			ACCESS	read-only
			STATUS	current
	DESCRIPTION ""
			::= { mbus5F 94 }

mbus5FValue2C		OBJECT-TYPE
			SYNTAX	INTEGER
			ACCESS	read-only
			STATUS	current
	DESCRIPTION ""
			::= { mbus5F 95 }

mbus5FVIF2D		OBJECT-TYPE
			SYNTAX	INTEGER
			ACCESS	read-only
			STATUS	current
	DESCRIPTION ""
			::= { mbus5F 96 }

mbus5FValue2D		OBJECT-TYPE
			SYNTAX	INTEGER
			ACCESS	read-only
			STATUS	current
	DESCRIPTION ""
			::= { mbus5F 97 }

mbus5FVIF2E		OBJECT-TYPE
			SYNTAX	INTEGER
			ACCESS	read-only
			STATUS	current
	DESCRIPTION ""
			::= { mbus5F 98 }

mbus5FValue2E		OBJECT-TYPE
			SYNTAX	INTEGER
			ACCESS	read-only
			STATUS	current
	DESCRIPTION ""
			::= { mbus5F 99 }

mbus5FVIF2F		OBJECT-TYPE
			SYNTAX	INTEGER
			ACCESS	read-only
			STATUS	current
	DESCRIPTION ""
			::= { mbus5F 100 }

mbus5FValue2F		OBJECT-TYPE
			SYNTAX	INTEGER
			ACCESS	read-only
			STATUS	current
	DESCRIPTION ""
			::= { mbus5F 101 }

mbus60			OBJECT IDENTIFIER ::= { mbus 96 }

mbus60IdNumber		OBJECT-TYPE
			SYNTAX	Gauge
			ACCESS	read-only
			STATUS	current
	DESCRIPTION ""
			::= { mbus60 1 }

mbus60Manufacturer	OBJECT-TYPE
			SYNTAX	Gauge
			ACCESS	read-only
			STATUS	current
	DESCRIPTION ""
			::= { mbus60 2 }

mbus60Version		OBJECT-TYPE
			SYNTAX	Gauge
			ACCESS	read-only
			STATUS	current
	DESCRIPTION ""
			::= { mbus60 3 }

mbus60Medium		OBJECT-TYPE
			SYNTAX	Gauge
			ACCESS	read-only
			STATUS	current
	DESCRIPTION ""
			::= { mbus60 4 }

mbus60Status		OBJECT-TYPE
			SYNTAX	Gauge
			ACCESS	read-only
			STATUS	current
	DESCRIPTION ""
			::= { mbus60 5 }

mbus60VIF00		OBJECT-TYPE
			SYNTAX	INTEGER
			ACCESS	read-only
			STATUS	current
	DESCRIPTION ""
			::= { mbus60 6 }

mbus60Value00		OBJECT-TYPE
			SYNTAX	INTEGER
			ACCESS	read-only
			STATUS	current
	DESCRIPTION ""
			::= { mbus60 7 }

mbus60VIF01		OBJECT-TYPE
			SYNTAX	INTEGER
			ACCESS	read-only
			STATUS	current
	DESCRIPTION ""
			::= { mbus60 8 }

mbus60Value01		OBJECT-TYPE
			SYNTAX	INTEGER
			ACCESS	read-only
			STATUS	current
	DESCRIPTION ""
			::= { mbus60 9 }

mbus60VIF02		OBJECT-TYPE
			SYNTAX	INTEGER
			ACCESS	read-only
			STATUS	current
	DESCRIPTION ""
			::= { mbus60 10 }

mbus60Value02		OBJECT-TYPE
			SYNTAX	INTEGER
			ACCESS	read-only
			STATUS	current
	DESCRIPTION ""
			::= { mbus60 11 }

mbus60VIF03		OBJECT-TYPE
			SYNTAX	INTEGER
			ACCESS	read-only
			STATUS	current
	DESCRIPTION ""
			::= { mbus60 12 }

mbus60Value03		OBJECT-TYPE
			SYNTAX	INTEGER
			ACCESS	read-only
			STATUS	current
	DESCRIPTION ""
			::= { mbus60 13 }

mbus60VIF04		OBJECT-TYPE
			SYNTAX	INTEGER
			ACCESS	read-only
			STATUS	current
	DESCRIPTION ""
			::= { mbus60 14 }

mbus60Value04		OBJECT-TYPE
			SYNTAX	INTEGER
			ACCESS	read-only
			STATUS	current
	DESCRIPTION ""
			::= { mbus60 15 }

mbus60VIF05		OBJECT-TYPE
			SYNTAX	INTEGER
			ACCESS	read-only
			STATUS	current
	DESCRIPTION ""
			::= { mbus60 16 }

mbus60Value05		OBJECT-TYPE
			SYNTAX	INTEGER
			ACCESS	read-only
			STATUS	current
	DESCRIPTION ""
			::= { mbus60 17 }

mbus60VIF06		OBJECT-TYPE
			SYNTAX	INTEGER
			ACCESS	read-only
			STATUS	current
	DESCRIPTION ""
			::= { mbus60 18 }

mbus60Value06		OBJECT-TYPE
			SYNTAX	INTEGER
			ACCESS	read-only
			STATUS	current
	DESCRIPTION ""
			::= { mbus60 19 }

mbus60VIF07		OBJECT-TYPE
			SYNTAX	INTEGER
			ACCESS	read-only
			STATUS	current
	DESCRIPTION ""
			::= { mbus60 20 }

mbus60Value07		OBJECT-TYPE
			SYNTAX	INTEGER
			ACCESS	read-only
			STATUS	current
	DESCRIPTION ""
			::= { mbus60 21 }

mbus60VIF08		OBJECT-TYPE
			SYNTAX	INTEGER
			ACCESS	read-only
			STATUS	current
	DESCRIPTION ""
			::= { mbus60 22 }

mbus60Value08		OBJECT-TYPE
			SYNTAX	INTEGER
			ACCESS	read-only
			STATUS	current
	DESCRIPTION ""
			::= { mbus60 23 }

mbus60VIF09		OBJECT-TYPE
			SYNTAX	INTEGER
			ACCESS	read-only
			STATUS	current
	DESCRIPTION ""
			::= { mbus60 24 }

mbus60Value09		OBJECT-TYPE
			SYNTAX	INTEGER
			ACCESS	read-only
			STATUS	current
	DESCRIPTION ""
			::= { mbus60 25 }

mbus60VIF0A		OBJECT-TYPE
			SYNTAX	INTEGER
			ACCESS	read-only
			STATUS	current
	DESCRIPTION ""
			::= { mbus60 26 }

mbus60Value0A		OBJECT-TYPE
			SYNTAX	INTEGER
			ACCESS	read-only
			STATUS	current
	DESCRIPTION ""
			::= { mbus60 27 }

mbus60VIF0B		OBJECT-TYPE
			SYNTAX	INTEGER
			ACCESS	read-only
			STATUS	current
	DESCRIPTION ""
			::= { mbus60 28 }

mbus60Value0B		OBJECT-TYPE
			SYNTAX	INTEGER
			ACCESS	read-only
			STATUS	current
	DESCRIPTION ""
			::= { mbus60 29 }

mbus60VIF0C		OBJECT-TYPE
			SYNTAX	INTEGER
			ACCESS	read-only
			STATUS	current
	DESCRIPTION ""
			::= { mbus60 30 }

mbus60Value0C		OBJECT-TYPE
			SYNTAX	INTEGER
			ACCESS	read-only
			STATUS	current
	DESCRIPTION ""
			::= { mbus60 31 }

mbus60VIF0D		OBJECT-TYPE
			SYNTAX	INTEGER
			ACCESS	read-only
			STATUS	current
	DESCRIPTION ""
			::= { mbus60 32 }

mbus60Value0D		OBJECT-TYPE
			SYNTAX	INTEGER
			ACCESS	read-only
			STATUS	current
	DESCRIPTION ""
			::= { mbus60 33 }

mbus60VIF0E		OBJECT-TYPE
			SYNTAX	INTEGER
			ACCESS	read-only
			STATUS	current
	DESCRIPTION ""
			::= { mbus60 34 }

mbus60Value0E		OBJECT-TYPE
			SYNTAX	INTEGER
			ACCESS	read-only
			STATUS	current
	DESCRIPTION ""
			::= { mbus60 35 }

mbus60VIF0F		OBJECT-TYPE
			SYNTAX	INTEGER
			ACCESS	read-only
			STATUS	current
	DESCRIPTION ""
			::= { mbus60 36 }

mbus60Value0F		OBJECT-TYPE
			SYNTAX	INTEGER
			ACCESS	read-only
			STATUS	current
	DESCRIPTION ""
			::= { mbus60 37 }

mbus60VIF10		OBJECT-TYPE
			SYNTAX	INTEGER
			ACCESS	read-only
			STATUS	current
	DESCRIPTION ""
			::= { mbus60 38 }

mbus60Value10		OBJECT-TYPE
			SYNTAX	INTEGER
			ACCESS	read-only
			STATUS	current
	DESCRIPTION ""
			::= { mbus60 39 }

mbus60VIF11		OBJECT-TYPE
			SYNTAX	INTEGER
			ACCESS	read-only
			STATUS	current
	DESCRIPTION ""
			::= { mbus60 40 }

mbus60Value11		OBJECT-TYPE
			SYNTAX	INTEGER
			ACCESS	read-only
			STATUS	current
	DESCRIPTION ""
			::= { mbus60 41 }

mbus60VIF12		OBJECT-TYPE
			SYNTAX	INTEGER
			ACCESS	read-only
			STATUS	current
	DESCRIPTION ""
			::= { mbus60 42 }

mbus60Value12		OBJECT-TYPE
			SYNTAX	INTEGER
			ACCESS	read-only
			STATUS	current
	DESCRIPTION ""
			::= { mbus60 43 }

mbus60VIF13		OBJECT-TYPE
			SYNTAX	INTEGER
			ACCESS	read-only
			STATUS	current
	DESCRIPTION ""
			::= { mbus60 44 }

mbus60Value13		OBJECT-TYPE
			SYNTAX	INTEGER
			ACCESS	read-only
			STATUS	current
	DESCRIPTION ""
			::= { mbus60 45 }

mbus60VIF14		OBJECT-TYPE
			SYNTAX	INTEGER
			ACCESS	read-only
			STATUS	current
	DESCRIPTION ""
			::= { mbus60 46 }

mbus60Value14		OBJECT-TYPE
			SYNTAX	INTEGER
			ACCESS	read-only
			STATUS	current
	DESCRIPTION ""
			::= { mbus60 47 }

mbus60VIF15		OBJECT-TYPE
			SYNTAX	INTEGER
			ACCESS	read-only
			STATUS	current
	DESCRIPTION ""
			::= { mbus60 48 }

mbus60Value15		OBJECT-TYPE
			SYNTAX	INTEGER
			ACCESS	read-only
			STATUS	current
	DESCRIPTION ""
			::= { mbus60 49 }

mbus60VIF16		OBJECT-TYPE
			SYNTAX	INTEGER
			ACCESS	read-only
			STATUS	current
	DESCRIPTION ""
			::= { mbus60 50 }

mbus60Value16		OBJECT-TYPE
			SYNTAX	INTEGER
			ACCESS	read-only
			STATUS	current
	DESCRIPTION ""
			::= { mbus60 51 }

mbus60VIF17		OBJECT-TYPE
			SYNTAX	INTEGER
			ACCESS	read-only
			STATUS	current
	DESCRIPTION ""
			::= { mbus60 52 }

mbus60Value17		OBJECT-TYPE
			SYNTAX	INTEGER
			ACCESS	read-only
			STATUS	current
	DESCRIPTION ""
			::= { mbus60 53 }

mbus60VIF18		OBJECT-TYPE
			SYNTAX	INTEGER
			ACCESS	read-only
			STATUS	current
	DESCRIPTION ""
			::= { mbus60 54 }

mbus60Value18		OBJECT-TYPE
			SYNTAX	INTEGER
			ACCESS	read-only
			STATUS	current
	DESCRIPTION ""
			::= { mbus60 55 }

mbus60VIF19		OBJECT-TYPE
			SYNTAX	INTEGER
			ACCESS	read-only
			STATUS	current
	DESCRIPTION ""
			::= { mbus60 56 }

mbus60Value19		OBJECT-TYPE
			SYNTAX	INTEGER
			ACCESS	read-only
			STATUS	current
	DESCRIPTION ""
			::= { mbus60 57 }

mbus60VIF1A		OBJECT-TYPE
			SYNTAX	INTEGER
			ACCESS	read-only
			STATUS	current
	DESCRIPTION ""
			::= { mbus60 58 }

mbus60Value1A		OBJECT-TYPE
			SYNTAX	INTEGER
			ACCESS	read-only
			STATUS	current
	DESCRIPTION ""
			::= { mbus60 59 }

mbus60VIF1B		OBJECT-TYPE
			SYNTAX	INTEGER
			ACCESS	read-only
			STATUS	current
	DESCRIPTION ""
			::= { mbus60 60 }

mbus60Value1B		OBJECT-TYPE
			SYNTAX	INTEGER
			ACCESS	read-only
			STATUS	current
	DESCRIPTION ""
			::= { mbus60 61 }

mbus60VIF1C		OBJECT-TYPE
			SYNTAX	INTEGER
			ACCESS	read-only
			STATUS	current
	DESCRIPTION ""
			::= { mbus60 62 }

mbus60Value1C		OBJECT-TYPE
			SYNTAX	INTEGER
			ACCESS	read-only
			STATUS	current
	DESCRIPTION ""
			::= { mbus60 63 }

mbus60VIF1D		OBJECT-TYPE
			SYNTAX	INTEGER
			ACCESS	read-only
			STATUS	current
	DESCRIPTION ""
			::= { mbus60 64 }

mbus60Value1D		OBJECT-TYPE
			SYNTAX	INTEGER
			ACCESS	read-only
			STATUS	current
	DESCRIPTION ""
			::= { mbus60 65 }

mbus60VIF1E		OBJECT-TYPE
			SYNTAX	INTEGER
			ACCESS	read-only
			STATUS	current
	DESCRIPTION ""
			::= { mbus60 66 }

mbus60Value1E		OBJECT-TYPE
			SYNTAX	INTEGER
			ACCESS	read-only
			STATUS	current
	DESCRIPTION ""
			::= { mbus60 67 }

mbus60VIF1F		OBJECT-TYPE
			SYNTAX	INTEGER
			ACCESS	read-only
			STATUS	current
	DESCRIPTION ""
			::= { mbus60 68 }

mbus60Value1F		OBJECT-TYPE
			SYNTAX	INTEGER
			ACCESS	read-only
			STATUS	current
	DESCRIPTION ""
			::= { mbus60 69 }

mbus60VIF20		OBJECT-TYPE
			SYNTAX	INTEGER
			ACCESS	read-only
			STATUS	current
	DESCRIPTION ""
			::= { mbus60 70 }

mbus60Value20		OBJECT-TYPE
			SYNTAX	INTEGER
			ACCESS	read-only
			STATUS	current
	DESCRIPTION ""
			::= { mbus60 71 }

mbus60VIF21		OBJECT-TYPE
			SYNTAX	INTEGER
			ACCESS	read-only
			STATUS	current
	DESCRIPTION ""
			::= { mbus60 72 }

mbus60Value21		OBJECT-TYPE
			SYNTAX	INTEGER
			ACCESS	read-only
			STATUS	current
	DESCRIPTION ""
			::= { mbus60 73 }

mbus60VIF22		OBJECT-TYPE
			SYNTAX	INTEGER
			ACCESS	read-only
			STATUS	current
	DESCRIPTION ""
			::= { mbus60 74 }

mbus60Value22		OBJECT-TYPE
			SYNTAX	INTEGER
			ACCESS	read-only
			STATUS	current
	DESCRIPTION ""
			::= { mbus60 75 }

mbus60VIF23		OBJECT-TYPE
			SYNTAX	INTEGER
			ACCESS	read-only
			STATUS	current
	DESCRIPTION ""
			::= { mbus60 76 }

mbus60Value23		OBJECT-TYPE
			SYNTAX	INTEGER
			ACCESS	read-only
			STATUS	current
	DESCRIPTION ""
			::= { mbus60 77 }

mbus60VIF24		OBJECT-TYPE
			SYNTAX	INTEGER
			ACCESS	read-only
			STATUS	current
	DESCRIPTION ""
			::= { mbus60 78 }

mbus60Value24		OBJECT-TYPE
			SYNTAX	INTEGER
			ACCESS	read-only
			STATUS	current
	DESCRIPTION ""
			::= { mbus60 79 }

mbus60VIF25		OBJECT-TYPE
			SYNTAX	INTEGER
			ACCESS	read-only
			STATUS	current
	DESCRIPTION ""
			::= { mbus60 80 }

mbus60Value25		OBJECT-TYPE
			SYNTAX	INTEGER
			ACCESS	read-only
			STATUS	current
	DESCRIPTION ""
			::= { mbus60 81 }

mbus60VIF26		OBJECT-TYPE
			SYNTAX	INTEGER
			ACCESS	read-only
			STATUS	current
	DESCRIPTION ""
			::= { mbus60 82 }

mbus60Value26		OBJECT-TYPE
			SYNTAX	INTEGER
			ACCESS	read-only
			STATUS	current
	DESCRIPTION ""
			::= { mbus60 83 }

mbus60VIF27		OBJECT-TYPE
			SYNTAX	INTEGER
			ACCESS	read-only
			STATUS	current
	DESCRIPTION ""
			::= { mbus60 84 }

mbus60Value27		OBJECT-TYPE
			SYNTAX	INTEGER
			ACCESS	read-only
			STATUS	current
	DESCRIPTION ""
			::= { mbus60 85 }

mbus60VIF28		OBJECT-TYPE
			SYNTAX	INTEGER
			ACCESS	read-only
			STATUS	current
	DESCRIPTION ""
			::= { mbus60 86 }

mbus60Value28		OBJECT-TYPE
			SYNTAX	INTEGER
			ACCESS	read-only
			STATUS	current
	DESCRIPTION ""
			::= { mbus60 87 }

mbus60VIF29		OBJECT-TYPE
			SYNTAX	INTEGER
			ACCESS	read-only
			STATUS	current
	DESCRIPTION ""
			::= { mbus60 88 }

mbus60Value29		OBJECT-TYPE
			SYNTAX	INTEGER
			ACCESS	read-only
			STATUS	current
	DESCRIPTION ""
			::= { mbus60 89 }

mbus60VIF2A		OBJECT-TYPE
			SYNTAX	INTEGER
			ACCESS	read-only
			STATUS	current
	DESCRIPTION ""
			::= { mbus60 90 }

mbus60Value2A		OBJECT-TYPE
			SYNTAX	INTEGER
			ACCESS	read-only
			STATUS	current
	DESCRIPTION ""
			::= { mbus60 91 }

mbus60VIF2B		OBJECT-TYPE
			SYNTAX	INTEGER
			ACCESS	read-only
			STATUS	current
	DESCRIPTION ""
			::= { mbus60 92 }

mbus60Value2B		OBJECT-TYPE
			SYNTAX	INTEGER
			ACCESS	read-only
			STATUS	current
	DESCRIPTION ""
			::= { mbus60 93 }

mbus60VIF2C		OBJECT-TYPE
			SYNTAX	INTEGER
			ACCESS	read-only
			STATUS	current
	DESCRIPTION ""
			::= { mbus60 94 }

mbus60Value2C		OBJECT-TYPE
			SYNTAX	INTEGER
			ACCESS	read-only
			STATUS	current
	DESCRIPTION ""
			::= { mbus60 95 }

mbus60VIF2D		OBJECT-TYPE
			SYNTAX	INTEGER
			ACCESS	read-only
			STATUS	current
	DESCRIPTION ""
			::= { mbus60 96 }

mbus60Value2D		OBJECT-TYPE
			SYNTAX	INTEGER
			ACCESS	read-only
			STATUS	current
	DESCRIPTION ""
			::= { mbus60 97 }

mbus60VIF2E		OBJECT-TYPE
			SYNTAX	INTEGER
			ACCESS	read-only
			STATUS	current
	DESCRIPTION ""
			::= { mbus60 98 }

mbus60Value2E		OBJECT-TYPE
			SYNTAX	INTEGER
			ACCESS	read-only
			STATUS	current
	DESCRIPTION ""
			::= { mbus60 99 }

mbus60VIF2F		OBJECT-TYPE
			SYNTAX	INTEGER
			ACCESS	read-only
			STATUS	current
	DESCRIPTION ""
			::= { mbus60 100 }

mbus60Value2F		OBJECT-TYPE
			SYNTAX	INTEGER
			ACCESS	read-only
			STATUS	current
	DESCRIPTION ""
			::= { mbus60 101 }

mbus61			OBJECT IDENTIFIER ::= { mbus 97 }

mbus61IdNumber		OBJECT-TYPE
			SYNTAX	Gauge
			ACCESS	read-only
			STATUS	current
	DESCRIPTION ""
			::= { mbus61 1 }

mbus61Manufacturer	OBJECT-TYPE
			SYNTAX	Gauge
			ACCESS	read-only
			STATUS	current
	DESCRIPTION ""
			::= { mbus61 2 }

mbus61Version		OBJECT-TYPE
			SYNTAX	Gauge
			ACCESS	read-only
			STATUS	current
	DESCRIPTION ""
			::= { mbus61 3 }

mbus61Medium		OBJECT-TYPE
			SYNTAX	Gauge
			ACCESS	read-only
			STATUS	current
	DESCRIPTION ""
			::= { mbus61 4 }

mbus61Status		OBJECT-TYPE
			SYNTAX	Gauge
			ACCESS	read-only
			STATUS	current
	DESCRIPTION ""
			::= { mbus61 5 }

mbus61VIF00		OBJECT-TYPE
			SYNTAX	INTEGER
			ACCESS	read-only
			STATUS	current
	DESCRIPTION ""
			::= { mbus61 6 }

mbus61Value00		OBJECT-TYPE
			SYNTAX	INTEGER
			ACCESS	read-only
			STATUS	current
	DESCRIPTION ""
			::= { mbus61 7 }

mbus61VIF01		OBJECT-TYPE
			SYNTAX	INTEGER
			ACCESS	read-only
			STATUS	current
	DESCRIPTION ""
			::= { mbus61 8 }

mbus61Value01		OBJECT-TYPE
			SYNTAX	INTEGER
			ACCESS	read-only
			STATUS	current
	DESCRIPTION ""
			::= { mbus61 9 }

mbus61VIF02		OBJECT-TYPE
			SYNTAX	INTEGER
			ACCESS	read-only
			STATUS	current
	DESCRIPTION ""
			::= { mbus61 10 }

mbus61Value02		OBJECT-TYPE
			SYNTAX	INTEGER
			ACCESS	read-only
			STATUS	current
	DESCRIPTION ""
			::= { mbus61 11 }

mbus61VIF03		OBJECT-TYPE
			SYNTAX	INTEGER
			ACCESS	read-only
			STATUS	current
	DESCRIPTION ""
			::= { mbus61 12 }

mbus61Value03		OBJECT-TYPE
			SYNTAX	INTEGER
			ACCESS	read-only
			STATUS	current
	DESCRIPTION ""
			::= { mbus61 13 }

mbus61VIF04		OBJECT-TYPE
			SYNTAX	INTEGER
			ACCESS	read-only
			STATUS	current
	DESCRIPTION ""
			::= { mbus61 14 }

mbus61Value04		OBJECT-TYPE
			SYNTAX	INTEGER
			ACCESS	read-only
			STATUS	current
	DESCRIPTION ""
			::= { mbus61 15 }

mbus61VIF05		OBJECT-TYPE
			SYNTAX	INTEGER
			ACCESS	read-only
			STATUS	current
	DESCRIPTION ""
			::= { mbus61 16 }

mbus61Value05		OBJECT-TYPE
			SYNTAX	INTEGER
			ACCESS	read-only
			STATUS	current
	DESCRIPTION ""
			::= { mbus61 17 }

mbus61VIF06		OBJECT-TYPE
			SYNTAX	INTEGER
			ACCESS	read-only
			STATUS	current
	DESCRIPTION ""
			::= { mbus61 18 }

mbus61Value06		OBJECT-TYPE
			SYNTAX	INTEGER
			ACCESS	read-only
			STATUS	current
	DESCRIPTION ""
			::= { mbus61 19 }

mbus61VIF07		OBJECT-TYPE
			SYNTAX	INTEGER
			ACCESS	read-only
			STATUS	current
	DESCRIPTION ""
			::= { mbus61 20 }

mbus61Value07		OBJECT-TYPE
			SYNTAX	INTEGER
			ACCESS	read-only
			STATUS	current
	DESCRIPTION ""
			::= { mbus61 21 }

mbus61VIF08		OBJECT-TYPE
			SYNTAX	INTEGER
			ACCESS	read-only
			STATUS	current
	DESCRIPTION ""
			::= { mbus61 22 }

mbus61Value08		OBJECT-TYPE
			SYNTAX	INTEGER
			ACCESS	read-only
			STATUS	current
	DESCRIPTION ""
			::= { mbus61 23 }

mbus61VIF09		OBJECT-TYPE
			SYNTAX	INTEGER
			ACCESS	read-only
			STATUS	current
	DESCRIPTION ""
			::= { mbus61 24 }

mbus61Value09		OBJECT-TYPE
			SYNTAX	INTEGER
			ACCESS	read-only
			STATUS	current
	DESCRIPTION ""
			::= { mbus61 25 }

mbus61VIF0A		OBJECT-TYPE
			SYNTAX	INTEGER
			ACCESS	read-only
			STATUS	current
	DESCRIPTION ""
			::= { mbus61 26 }

mbus61Value0A		OBJECT-TYPE
			SYNTAX	INTEGER
			ACCESS	read-only
			STATUS	current
	DESCRIPTION ""
			::= { mbus61 27 }

mbus61VIF0B		OBJECT-TYPE
			SYNTAX	INTEGER
			ACCESS	read-only
			STATUS	current
	DESCRIPTION ""
			::= { mbus61 28 }

mbus61Value0B		OBJECT-TYPE
			SYNTAX	INTEGER
			ACCESS	read-only
			STATUS	current
	DESCRIPTION ""
			::= { mbus61 29 }

mbus61VIF0C		OBJECT-TYPE
			SYNTAX	INTEGER
			ACCESS	read-only
			STATUS	current
	DESCRIPTION ""
			::= { mbus61 30 }

mbus61Value0C		OBJECT-TYPE
			SYNTAX	INTEGER
			ACCESS	read-only
			STATUS	current
	DESCRIPTION ""
			::= { mbus61 31 }

mbus61VIF0D		OBJECT-TYPE
			SYNTAX	INTEGER
			ACCESS	read-only
			STATUS	current
	DESCRIPTION ""
			::= { mbus61 32 }

mbus61Value0D		OBJECT-TYPE
			SYNTAX	INTEGER
			ACCESS	read-only
			STATUS	current
	DESCRIPTION ""
			::= { mbus61 33 }

mbus61VIF0E		OBJECT-TYPE
			SYNTAX	INTEGER
			ACCESS	read-only
			STATUS	current
	DESCRIPTION ""
			::= { mbus61 34 }

mbus61Value0E		OBJECT-TYPE
			SYNTAX	INTEGER
			ACCESS	read-only
			STATUS	current
	DESCRIPTION ""
			::= { mbus61 35 }

mbus61VIF0F		OBJECT-TYPE
			SYNTAX	INTEGER
			ACCESS	read-only
			STATUS	current
	DESCRIPTION ""
			::= { mbus61 36 }

mbus61Value0F		OBJECT-TYPE
			SYNTAX	INTEGER
			ACCESS	read-only
			STATUS	current
	DESCRIPTION ""
			::= { mbus61 37 }

mbus61VIF10		OBJECT-TYPE
			SYNTAX	INTEGER
			ACCESS	read-only
			STATUS	current
	DESCRIPTION ""
			::= { mbus61 38 }

mbus61Value10		OBJECT-TYPE
			SYNTAX	INTEGER
			ACCESS	read-only
			STATUS	current
	DESCRIPTION ""
			::= { mbus61 39 }

mbus61VIF11		OBJECT-TYPE
			SYNTAX	INTEGER
			ACCESS	read-only
			STATUS	current
	DESCRIPTION ""
			::= { mbus61 40 }

mbus61Value11		OBJECT-TYPE
			SYNTAX	INTEGER
			ACCESS	read-only
			STATUS	current
	DESCRIPTION ""
			::= { mbus61 41 }

mbus61VIF12		OBJECT-TYPE
			SYNTAX	INTEGER
			ACCESS	read-only
			STATUS	current
	DESCRIPTION ""
			::= { mbus61 42 }

mbus61Value12		OBJECT-TYPE
			SYNTAX	INTEGER
			ACCESS	read-only
			STATUS	current
	DESCRIPTION ""
			::= { mbus61 43 }

mbus61VIF13		OBJECT-TYPE
			SYNTAX	INTEGER
			ACCESS	read-only
			STATUS	current
	DESCRIPTION ""
			::= { mbus61 44 }

mbus61Value13		OBJECT-TYPE
			SYNTAX	INTEGER
			ACCESS	read-only
			STATUS	current
	DESCRIPTION ""
			::= { mbus61 45 }

mbus61VIF14		OBJECT-TYPE
			SYNTAX	INTEGER
			ACCESS	read-only
			STATUS	current
	DESCRIPTION ""
			::= { mbus61 46 }

mbus61Value14		OBJECT-TYPE
			SYNTAX	INTEGER
			ACCESS	read-only
			STATUS	current
	DESCRIPTION ""
			::= { mbus61 47 }

mbus61VIF15		OBJECT-TYPE
			SYNTAX	INTEGER
			ACCESS	read-only
			STATUS	current
	DESCRIPTION ""
			::= { mbus61 48 }

mbus61Value15		OBJECT-TYPE
			SYNTAX	INTEGER
			ACCESS	read-only
			STATUS	current
	DESCRIPTION ""
			::= { mbus61 49 }

mbus61VIF16		OBJECT-TYPE
			SYNTAX	INTEGER
			ACCESS	read-only
			STATUS	current
	DESCRIPTION ""
			::= { mbus61 50 }

mbus61Value16		OBJECT-TYPE
			SYNTAX	INTEGER
			ACCESS	read-only
			STATUS	current
	DESCRIPTION ""
			::= { mbus61 51 }

mbus61VIF17		OBJECT-TYPE
			SYNTAX	INTEGER
			ACCESS	read-only
			STATUS	current
	DESCRIPTION ""
			::= { mbus61 52 }

mbus61Value17		OBJECT-TYPE
			SYNTAX	INTEGER
			ACCESS	read-only
			STATUS	current
	DESCRIPTION ""
			::= { mbus61 53 }

mbus61VIF18		OBJECT-TYPE
			SYNTAX	INTEGER
			ACCESS	read-only
			STATUS	current
	DESCRIPTION ""
			::= { mbus61 54 }

mbus61Value18		OBJECT-TYPE
			SYNTAX	INTEGER
			ACCESS	read-only
			STATUS	current
	DESCRIPTION ""
			::= { mbus61 55 }

mbus61VIF19		OBJECT-TYPE
			SYNTAX	INTEGER
			ACCESS	read-only
			STATUS	current
	DESCRIPTION ""
			::= { mbus61 56 }

mbus61Value19		OBJECT-TYPE
			SYNTAX	INTEGER
			ACCESS	read-only
			STATUS	current
	DESCRIPTION ""
			::= { mbus61 57 }

mbus61VIF1A		OBJECT-TYPE
			SYNTAX	INTEGER
			ACCESS	read-only
			STATUS	current
	DESCRIPTION ""
			::= { mbus61 58 }

mbus61Value1A		OBJECT-TYPE
			SYNTAX	INTEGER
			ACCESS	read-only
			STATUS	current
	DESCRIPTION ""
			::= { mbus61 59 }

mbus61VIF1B		OBJECT-TYPE
			SYNTAX	INTEGER
			ACCESS	read-only
			STATUS	current
	DESCRIPTION ""
			::= { mbus61 60 }

mbus61Value1B		OBJECT-TYPE
			SYNTAX	INTEGER
			ACCESS	read-only
			STATUS	current
	DESCRIPTION ""
			::= { mbus61 61 }

mbus61VIF1C		OBJECT-TYPE
			SYNTAX	INTEGER
			ACCESS	read-only
			STATUS	current
	DESCRIPTION ""
			::= { mbus61 62 }

mbus61Value1C		OBJECT-TYPE
			SYNTAX	INTEGER
			ACCESS	read-only
			STATUS	current
	DESCRIPTION ""
			::= { mbus61 63 }

mbus61VIF1D		OBJECT-TYPE
			SYNTAX	INTEGER
			ACCESS	read-only
			STATUS	current
	DESCRIPTION ""
			::= { mbus61 64 }

mbus61Value1D		OBJECT-TYPE
			SYNTAX	INTEGER
			ACCESS	read-only
			STATUS	current
	DESCRIPTION ""
			::= { mbus61 65 }

mbus61VIF1E		OBJECT-TYPE
			SYNTAX	INTEGER
			ACCESS	read-only
			STATUS	current
	DESCRIPTION ""
			::= { mbus61 66 }

mbus61Value1E		OBJECT-TYPE
			SYNTAX	INTEGER
			ACCESS	read-only
			STATUS	current
	DESCRIPTION ""
			::= { mbus61 67 }

mbus61VIF1F		OBJECT-TYPE
			SYNTAX	INTEGER
			ACCESS	read-only
			STATUS	current
	DESCRIPTION ""
			::= { mbus61 68 }

mbus61Value1F		OBJECT-TYPE
			SYNTAX	INTEGER
			ACCESS	read-only
			STATUS	current
	DESCRIPTION ""
			::= { mbus61 69 }

mbus61VIF20		OBJECT-TYPE
			SYNTAX	INTEGER
			ACCESS	read-only
			STATUS	current
	DESCRIPTION ""
			::= { mbus61 70 }

mbus61Value20		OBJECT-TYPE
			SYNTAX	INTEGER
			ACCESS	read-only
			STATUS	current
	DESCRIPTION ""
			::= { mbus61 71 }

mbus61VIF21		OBJECT-TYPE
			SYNTAX	INTEGER
			ACCESS	read-only
			STATUS	current
	DESCRIPTION ""
			::= { mbus61 72 }

mbus61Value21		OBJECT-TYPE
			SYNTAX	INTEGER
			ACCESS	read-only
			STATUS	current
	DESCRIPTION ""
			::= { mbus61 73 }

mbus61VIF22		OBJECT-TYPE
			SYNTAX	INTEGER
			ACCESS	read-only
			STATUS	current
	DESCRIPTION ""
			::= { mbus61 74 }

mbus61Value22		OBJECT-TYPE
			SYNTAX	INTEGER
			ACCESS	read-only
			STATUS	current
	DESCRIPTION ""
			::= { mbus61 75 }

mbus61VIF23		OBJECT-TYPE
			SYNTAX	INTEGER
			ACCESS	read-only
			STATUS	current
	DESCRIPTION ""
			::= { mbus61 76 }

mbus61Value23		OBJECT-TYPE
			SYNTAX	INTEGER
			ACCESS	read-only
			STATUS	current
	DESCRIPTION ""
			::= { mbus61 77 }

mbus61VIF24		OBJECT-TYPE
			SYNTAX	INTEGER
			ACCESS	read-only
			STATUS	current
	DESCRIPTION ""
			::= { mbus61 78 }

mbus61Value24		OBJECT-TYPE
			SYNTAX	INTEGER
			ACCESS	read-only
			STATUS	current
	DESCRIPTION ""
			::= { mbus61 79 }

mbus61VIF25		OBJECT-TYPE
			SYNTAX	INTEGER
			ACCESS	read-only
			STATUS	current
	DESCRIPTION ""
			::= { mbus61 80 }

mbus61Value25		OBJECT-TYPE
			SYNTAX	INTEGER
			ACCESS	read-only
			STATUS	current
	DESCRIPTION ""
			::= { mbus61 81 }

mbus61VIF26		OBJECT-TYPE
			SYNTAX	INTEGER
			ACCESS	read-only
			STATUS	current
	DESCRIPTION ""
			::= { mbus61 82 }

mbus61Value26		OBJECT-TYPE
			SYNTAX	INTEGER
			ACCESS	read-only
			STATUS	current
	DESCRIPTION ""
			::= { mbus61 83 }

mbus61VIF27		OBJECT-TYPE
			SYNTAX	INTEGER
			ACCESS	read-only
			STATUS	current
	DESCRIPTION ""
			::= { mbus61 84 }

mbus61Value27		OBJECT-TYPE
			SYNTAX	INTEGER
			ACCESS	read-only
			STATUS	current
	DESCRIPTION ""
			::= { mbus61 85 }

mbus61VIF28		OBJECT-TYPE
			SYNTAX	INTEGER
			ACCESS	read-only
			STATUS	current
	DESCRIPTION ""
			::= { mbus61 86 }

mbus61Value28		OBJECT-TYPE
			SYNTAX	INTEGER
			ACCESS	read-only
			STATUS	current
	DESCRIPTION ""
			::= { mbus61 87 }

mbus61VIF29		OBJECT-TYPE
			SYNTAX	INTEGER
			ACCESS	read-only
			STATUS	current
	DESCRIPTION ""
			::= { mbus61 88 }

mbus61Value29		OBJECT-TYPE
			SYNTAX	INTEGER
			ACCESS	read-only
			STATUS	current
	DESCRIPTION ""
			::= { mbus61 89 }

mbus61VIF2A		OBJECT-TYPE
			SYNTAX	INTEGER
			ACCESS	read-only
			STATUS	current
	DESCRIPTION ""
			::= { mbus61 90 }

mbus61Value2A		OBJECT-TYPE
			SYNTAX	INTEGER
			ACCESS	read-only
			STATUS	current
	DESCRIPTION ""
			::= { mbus61 91 }

mbus61VIF2B		OBJECT-TYPE
			SYNTAX	INTEGER
			ACCESS	read-only
			STATUS	current
	DESCRIPTION ""
			::= { mbus61 92 }

mbus61Value2B		OBJECT-TYPE
			SYNTAX	INTEGER
			ACCESS	read-only
			STATUS	current
	DESCRIPTION ""
			::= { mbus61 93 }

mbus61VIF2C		OBJECT-TYPE
			SYNTAX	INTEGER
			ACCESS	read-only
			STATUS	current
	DESCRIPTION ""
			::= { mbus61 94 }

mbus61Value2C		OBJECT-TYPE
			SYNTAX	INTEGER
			ACCESS	read-only
			STATUS	current
	DESCRIPTION ""
			::= { mbus61 95 }

mbus61VIF2D		OBJECT-TYPE
			SYNTAX	INTEGER
			ACCESS	read-only
			STATUS	current
	DESCRIPTION ""
			::= { mbus61 96 }

mbus61Value2D		OBJECT-TYPE
			SYNTAX	INTEGER
			ACCESS	read-only
			STATUS	current
	DESCRIPTION ""
			::= { mbus61 97 }

mbus61VIF2E		OBJECT-TYPE
			SYNTAX	INTEGER
			ACCESS	read-only
			STATUS	current
	DESCRIPTION ""
			::= { mbus61 98 }

mbus61Value2E		OBJECT-TYPE
			SYNTAX	INTEGER
			ACCESS	read-only
			STATUS	current
	DESCRIPTION ""
			::= { mbus61 99 }

mbus61VIF2F		OBJECT-TYPE
			SYNTAX	INTEGER
			ACCESS	read-only
			STATUS	current
	DESCRIPTION ""
			::= { mbus61 100 }

mbus61Value2F		OBJECT-TYPE
			SYNTAX	INTEGER
			ACCESS	read-only
			STATUS	current
	DESCRIPTION ""
			::= { mbus61 101 }

mbus62			OBJECT IDENTIFIER ::= { mbus 98 }

mbus62IdNumber		OBJECT-TYPE
			SYNTAX	Gauge
			ACCESS	read-only
			STATUS	current
	DESCRIPTION ""
			::= { mbus62 1 }

mbus62Manufacturer	OBJECT-TYPE
			SYNTAX	Gauge
			ACCESS	read-only
			STATUS	current
	DESCRIPTION ""
			::= { mbus62 2 }

mbus62Version		OBJECT-TYPE
			SYNTAX	Gauge
			ACCESS	read-only
			STATUS	current
	DESCRIPTION ""
			::= { mbus62 3 }

mbus62Medium		OBJECT-TYPE
			SYNTAX	Gauge
			ACCESS	read-only
			STATUS	current
	DESCRIPTION ""
			::= { mbus62 4 }

mbus62Status		OBJECT-TYPE
			SYNTAX	Gauge
			ACCESS	read-only
			STATUS	current
	DESCRIPTION ""
			::= { mbus62 5 }

mbus62VIF00		OBJECT-TYPE
			SYNTAX	INTEGER
			ACCESS	read-only
			STATUS	current
	DESCRIPTION ""
			::= { mbus62 6 }

mbus62Value00		OBJECT-TYPE
			SYNTAX	INTEGER
			ACCESS	read-only
			STATUS	current
	DESCRIPTION ""
			::= { mbus62 7 }

mbus62VIF01		OBJECT-TYPE
			SYNTAX	INTEGER
			ACCESS	read-only
			STATUS	current
	DESCRIPTION ""
			::= { mbus62 8 }

mbus62Value01		OBJECT-TYPE
			SYNTAX	INTEGER
			ACCESS	read-only
			STATUS	current
	DESCRIPTION ""
			::= { mbus62 9 }

mbus62VIF02		OBJECT-TYPE
			SYNTAX	INTEGER
			ACCESS	read-only
			STATUS	current
	DESCRIPTION ""
			::= { mbus62 10 }

mbus62Value02		OBJECT-TYPE
			SYNTAX	INTEGER
			ACCESS	read-only
			STATUS	current
	DESCRIPTION ""
			::= { mbus62 11 }

mbus62VIF03		OBJECT-TYPE
			SYNTAX	INTEGER
			ACCESS	read-only
			STATUS	current
	DESCRIPTION ""
			::= { mbus62 12 }

mbus62Value03		OBJECT-TYPE
			SYNTAX	INTEGER
			ACCESS	read-only
			STATUS	current
	DESCRIPTION ""
			::= { mbus62 13 }

mbus62VIF04		OBJECT-TYPE
			SYNTAX	INTEGER
			ACCESS	read-only
			STATUS	current
	DESCRIPTION ""
			::= { mbus62 14 }

mbus62Value04		OBJECT-TYPE
			SYNTAX	INTEGER
			ACCESS	read-only
			STATUS	current
	DESCRIPTION ""
			::= { mbus62 15 }

mbus62VIF05		OBJECT-TYPE
			SYNTAX	INTEGER
			ACCESS	read-only
			STATUS	current
	DESCRIPTION ""
			::= { mbus62 16 }

mbus62Value05		OBJECT-TYPE
			SYNTAX	INTEGER
			ACCESS	read-only
			STATUS	current
	DESCRIPTION ""
			::= { mbus62 17 }

mbus62VIF06		OBJECT-TYPE
			SYNTAX	INTEGER
			ACCESS	read-only
			STATUS	current
	DESCRIPTION ""
			::= { mbus62 18 }

mbus62Value06		OBJECT-TYPE
			SYNTAX	INTEGER
			ACCESS	read-only
			STATUS	current
	DESCRIPTION ""
			::= { mbus62 19 }

mbus62VIF07		OBJECT-TYPE
			SYNTAX	INTEGER
			ACCESS	read-only
			STATUS	current
	DESCRIPTION ""
			::= { mbus62 20 }

mbus62Value07		OBJECT-TYPE
			SYNTAX	INTEGER
			ACCESS	read-only
			STATUS	current
	DESCRIPTION ""
			::= { mbus62 21 }

mbus62VIF08		OBJECT-TYPE
			SYNTAX	INTEGER
			ACCESS	read-only
			STATUS	current
	DESCRIPTION ""
			::= { mbus62 22 }

mbus62Value08		OBJECT-TYPE
			SYNTAX	INTEGER
			ACCESS	read-only
			STATUS	current
	DESCRIPTION ""
			::= { mbus62 23 }

mbus62VIF09		OBJECT-TYPE
			SYNTAX	INTEGER
			ACCESS	read-only
			STATUS	current
	DESCRIPTION ""
			::= { mbus62 24 }

mbus62Value09		OBJECT-TYPE
			SYNTAX	INTEGER
			ACCESS	read-only
			STATUS	current
	DESCRIPTION ""
			::= { mbus62 25 }

mbus62VIF0A		OBJECT-TYPE
			SYNTAX	INTEGER
			ACCESS	read-only
			STATUS	current
	DESCRIPTION ""
			::= { mbus62 26 }

mbus62Value0A		OBJECT-TYPE
			SYNTAX	INTEGER
			ACCESS	read-only
			STATUS	current
	DESCRIPTION ""
			::= { mbus62 27 }

mbus62VIF0B		OBJECT-TYPE
			SYNTAX	INTEGER
			ACCESS	read-only
			STATUS	current
	DESCRIPTION ""
			::= { mbus62 28 }

mbus62Value0B		OBJECT-TYPE
			SYNTAX	INTEGER
			ACCESS	read-only
			STATUS	current
	DESCRIPTION ""
			::= { mbus62 29 }

mbus62VIF0C		OBJECT-TYPE
			SYNTAX	INTEGER
			ACCESS	read-only
			STATUS	current
	DESCRIPTION ""
			::= { mbus62 30 }

mbus62Value0C		OBJECT-TYPE
			SYNTAX	INTEGER
			ACCESS	read-only
			STATUS	current
	DESCRIPTION ""
			::= { mbus62 31 }

mbus62VIF0D		OBJECT-TYPE
			SYNTAX	INTEGER
			ACCESS	read-only
			STATUS	current
	DESCRIPTION ""
			::= { mbus62 32 }

mbus62Value0D		OBJECT-TYPE
			SYNTAX	INTEGER
			ACCESS	read-only
			STATUS	current
	DESCRIPTION ""
			::= { mbus62 33 }

mbus62VIF0E		OBJECT-TYPE
			SYNTAX	INTEGER
			ACCESS	read-only
			STATUS	current
	DESCRIPTION ""
			::= { mbus62 34 }

mbus62Value0E		OBJECT-TYPE
			SYNTAX	INTEGER
			ACCESS	read-only
			STATUS	current
	DESCRIPTION ""
			::= { mbus62 35 }

mbus62VIF0F		OBJECT-TYPE
			SYNTAX	INTEGER
			ACCESS	read-only
			STATUS	current
	DESCRIPTION ""
			::= { mbus62 36 }

mbus62Value0F		OBJECT-TYPE
			SYNTAX	INTEGER
			ACCESS	read-only
			STATUS	current
	DESCRIPTION ""
			::= { mbus62 37 }

mbus62VIF10		OBJECT-TYPE
			SYNTAX	INTEGER
			ACCESS	read-only
			STATUS	current
	DESCRIPTION ""
			::= { mbus62 38 }

mbus62Value10		OBJECT-TYPE
			SYNTAX	INTEGER
			ACCESS	read-only
			STATUS	current
	DESCRIPTION ""
			::= { mbus62 39 }

mbus62VIF11		OBJECT-TYPE
			SYNTAX	INTEGER
			ACCESS	read-only
			STATUS	current
	DESCRIPTION ""
			::= { mbus62 40 }

mbus62Value11		OBJECT-TYPE
			SYNTAX	INTEGER
			ACCESS	read-only
			STATUS	current
	DESCRIPTION ""
			::= { mbus62 41 }

mbus62VIF12		OBJECT-TYPE
			SYNTAX	INTEGER
			ACCESS	read-only
			STATUS	current
	DESCRIPTION ""
			::= { mbus62 42 }

mbus62Value12		OBJECT-TYPE
			SYNTAX	INTEGER
			ACCESS	read-only
			STATUS	current
	DESCRIPTION ""
			::= { mbus62 43 }

mbus62VIF13		OBJECT-TYPE
			SYNTAX	INTEGER
			ACCESS	read-only
			STATUS	current
	DESCRIPTION ""
			::= { mbus62 44 }

mbus62Value13		OBJECT-TYPE
			SYNTAX	INTEGER
			ACCESS	read-only
			STATUS	current
	DESCRIPTION ""
			::= { mbus62 45 }

mbus62VIF14		OBJECT-TYPE
			SYNTAX	INTEGER
			ACCESS	read-only
			STATUS	current
	DESCRIPTION ""
			::= { mbus62 46 }

mbus62Value14		OBJECT-TYPE
			SYNTAX	INTEGER
			ACCESS	read-only
			STATUS	current
	DESCRIPTION ""
			::= { mbus62 47 }

mbus62VIF15		OBJECT-TYPE
			SYNTAX	INTEGER
			ACCESS	read-only
			STATUS	current
	DESCRIPTION ""
			::= { mbus62 48 }

mbus62Value15		OBJECT-TYPE
			SYNTAX	INTEGER
			ACCESS	read-only
			STATUS	current
	DESCRIPTION ""
			::= { mbus62 49 }

mbus62VIF16		OBJECT-TYPE
			SYNTAX	INTEGER
			ACCESS	read-only
			STATUS	current
	DESCRIPTION ""
			::= { mbus62 50 }

mbus62Value16		OBJECT-TYPE
			SYNTAX	INTEGER
			ACCESS	read-only
			STATUS	current
	DESCRIPTION ""
			::= { mbus62 51 }

mbus62VIF17		OBJECT-TYPE
			SYNTAX	INTEGER
			ACCESS	read-only
			STATUS	current
	DESCRIPTION ""
			::= { mbus62 52 }

mbus62Value17		OBJECT-TYPE
			SYNTAX	INTEGER
			ACCESS	read-only
			STATUS	current
	DESCRIPTION ""
			::= { mbus62 53 }

mbus62VIF18		OBJECT-TYPE
			SYNTAX	INTEGER
			ACCESS	read-only
			STATUS	current
	DESCRIPTION ""
			::= { mbus62 54 }

mbus62Value18		OBJECT-TYPE
			SYNTAX	INTEGER
			ACCESS	read-only
			STATUS	current
	DESCRIPTION ""
			::= { mbus62 55 }

mbus62VIF19		OBJECT-TYPE
			SYNTAX	INTEGER
			ACCESS	read-only
			STATUS	current
	DESCRIPTION ""
			::= { mbus62 56 }

mbus62Value19		OBJECT-TYPE
			SYNTAX	INTEGER
			ACCESS	read-only
			STATUS	current
	DESCRIPTION ""
			::= { mbus62 57 }

mbus62VIF1A		OBJECT-TYPE
			SYNTAX	INTEGER
			ACCESS	read-only
			STATUS	current
	DESCRIPTION ""
			::= { mbus62 58 }

mbus62Value1A		OBJECT-TYPE
			SYNTAX	INTEGER
			ACCESS	read-only
			STATUS	current
	DESCRIPTION ""
			::= { mbus62 59 }

mbus62VIF1B		OBJECT-TYPE
			SYNTAX	INTEGER
			ACCESS	read-only
			STATUS	current
	DESCRIPTION ""
			::= { mbus62 60 }

mbus62Value1B		OBJECT-TYPE
			SYNTAX	INTEGER
			ACCESS	read-only
			STATUS	current
	DESCRIPTION ""
			::= { mbus62 61 }

mbus62VIF1C		OBJECT-TYPE
			SYNTAX	INTEGER
			ACCESS	read-only
			STATUS	current
	DESCRIPTION ""
			::= { mbus62 62 }

mbus62Value1C		OBJECT-TYPE
			SYNTAX	INTEGER
			ACCESS	read-only
			STATUS	current
	DESCRIPTION ""
			::= { mbus62 63 }

mbus62VIF1D		OBJECT-TYPE
			SYNTAX	INTEGER
			ACCESS	read-only
			STATUS	current
	DESCRIPTION ""
			::= { mbus62 64 }

mbus62Value1D		OBJECT-TYPE
			SYNTAX	INTEGER
			ACCESS	read-only
			STATUS	current
	DESCRIPTION ""
			::= { mbus62 65 }

mbus62VIF1E		OBJECT-TYPE
			SYNTAX	INTEGER
			ACCESS	read-only
			STATUS	current
	DESCRIPTION ""
			::= { mbus62 66 }

mbus62Value1E		OBJECT-TYPE
			SYNTAX	INTEGER
			ACCESS	read-only
			STATUS	current
	DESCRIPTION ""
			::= { mbus62 67 }

mbus62VIF1F		OBJECT-TYPE
			SYNTAX	INTEGER
			ACCESS	read-only
			STATUS	current
	DESCRIPTION ""
			::= { mbus62 68 }

mbus62Value1F		OBJECT-TYPE
			SYNTAX	INTEGER
			ACCESS	read-only
			STATUS	current
	DESCRIPTION ""
			::= { mbus62 69 }

mbus62VIF20		OBJECT-TYPE
			SYNTAX	INTEGER
			ACCESS	read-only
			STATUS	current
	DESCRIPTION ""
			::= { mbus62 70 }

mbus62Value20		OBJECT-TYPE
			SYNTAX	INTEGER
			ACCESS	read-only
			STATUS	current
	DESCRIPTION ""
			::= { mbus62 71 }

mbus62VIF21		OBJECT-TYPE
			SYNTAX	INTEGER
			ACCESS	read-only
			STATUS	current
	DESCRIPTION ""
			::= { mbus62 72 }

mbus62Value21		OBJECT-TYPE
			SYNTAX	INTEGER
			ACCESS	read-only
			STATUS	current
	DESCRIPTION ""
			::= { mbus62 73 }

mbus62VIF22		OBJECT-TYPE
			SYNTAX	INTEGER
			ACCESS	read-only
			STATUS	current
	DESCRIPTION ""
			::= { mbus62 74 }

mbus62Value22		OBJECT-TYPE
			SYNTAX	INTEGER
			ACCESS	read-only
			STATUS	current
	DESCRIPTION ""
			::= { mbus62 75 }

mbus62VIF23		OBJECT-TYPE
			SYNTAX	INTEGER
			ACCESS	read-only
			STATUS	current
	DESCRIPTION ""
			::= { mbus62 76 }

mbus62Value23		OBJECT-TYPE
			SYNTAX	INTEGER
			ACCESS	read-only
			STATUS	current
	DESCRIPTION ""
			::= { mbus62 77 }

mbus62VIF24		OBJECT-TYPE
			SYNTAX	INTEGER
			ACCESS	read-only
			STATUS	current
	DESCRIPTION ""
			::= { mbus62 78 }

mbus62Value24		OBJECT-TYPE
			SYNTAX	INTEGER
			ACCESS	read-only
			STATUS	current
	DESCRIPTION ""
			::= { mbus62 79 }

mbus62VIF25		OBJECT-TYPE
			SYNTAX	INTEGER
			ACCESS	read-only
			STATUS	current
	DESCRIPTION ""
			::= { mbus62 80 }

mbus62Value25		OBJECT-TYPE
			SYNTAX	INTEGER
			ACCESS	read-only
			STATUS	current
	DESCRIPTION ""
			::= { mbus62 81 }

mbus62VIF26		OBJECT-TYPE
			SYNTAX	INTEGER
			ACCESS	read-only
			STATUS	current
	DESCRIPTION ""
			::= { mbus62 82 }

mbus62Value26		OBJECT-TYPE
			SYNTAX	INTEGER
			ACCESS	read-only
			STATUS	current
	DESCRIPTION ""
			::= { mbus62 83 }

mbus62VIF27		OBJECT-TYPE
			SYNTAX	INTEGER
			ACCESS	read-only
			STATUS	current
	DESCRIPTION ""
			::= { mbus62 84 }

mbus62Value27		OBJECT-TYPE
			SYNTAX	INTEGER
			ACCESS	read-only
			STATUS	current
	DESCRIPTION ""
			::= { mbus62 85 }

mbus62VIF28		OBJECT-TYPE
			SYNTAX	INTEGER
			ACCESS	read-only
			STATUS	current
	DESCRIPTION ""
			::= { mbus62 86 }

mbus62Value28		OBJECT-TYPE
			SYNTAX	INTEGER
			ACCESS	read-only
			STATUS	current
	DESCRIPTION ""
			::= { mbus62 87 }

mbus62VIF29		OBJECT-TYPE
			SYNTAX	INTEGER
			ACCESS	read-only
			STATUS	current
	DESCRIPTION ""
			::= { mbus62 88 }

mbus62Value29		OBJECT-TYPE
			SYNTAX	INTEGER
			ACCESS	read-only
			STATUS	current
	DESCRIPTION ""
			::= { mbus62 89 }

mbus62VIF2A		OBJECT-TYPE
			SYNTAX	INTEGER
			ACCESS	read-only
			STATUS	current
	DESCRIPTION ""
			::= { mbus62 90 }

mbus62Value2A		OBJECT-TYPE
			SYNTAX	INTEGER
			ACCESS	read-only
			STATUS	current
	DESCRIPTION ""
			::= { mbus62 91 }

mbus62VIF2B		OBJECT-TYPE
			SYNTAX	INTEGER
			ACCESS	read-only
			STATUS	current
	DESCRIPTION ""
			::= { mbus62 92 }

mbus62Value2B		OBJECT-TYPE
			SYNTAX	INTEGER
			ACCESS	read-only
			STATUS	current
	DESCRIPTION ""
			::= { mbus62 93 }

mbus62VIF2C		OBJECT-TYPE
			SYNTAX	INTEGER
			ACCESS	read-only
			STATUS	current
	DESCRIPTION ""
			::= { mbus62 94 }

mbus62Value2C		OBJECT-TYPE
			SYNTAX	INTEGER
			ACCESS	read-only
			STATUS	current
	DESCRIPTION ""
			::= { mbus62 95 }

mbus62VIF2D		OBJECT-TYPE
			SYNTAX	INTEGER
			ACCESS	read-only
			STATUS	current
	DESCRIPTION ""
			::= { mbus62 96 }

mbus62Value2D		OBJECT-TYPE
			SYNTAX	INTEGER
			ACCESS	read-only
			STATUS	current
	DESCRIPTION ""
			::= { mbus62 97 }

mbus62VIF2E		OBJECT-TYPE
			SYNTAX	INTEGER
			ACCESS	read-only
			STATUS	current
	DESCRIPTION ""
			::= { mbus62 98 }

mbus62Value2E		OBJECT-TYPE
			SYNTAX	INTEGER
			ACCESS	read-only
			STATUS	current
	DESCRIPTION ""
			::= { mbus62 99 }

mbus62VIF2F		OBJECT-TYPE
			SYNTAX	INTEGER
			ACCESS	read-only
			STATUS	current
	DESCRIPTION ""
			::= { mbus62 100 }

mbus62Value2F		OBJECT-TYPE
			SYNTAX	INTEGER
			ACCESS	read-only
			STATUS	current
	DESCRIPTION ""
			::= { mbus62 101 }

mbus63			OBJECT IDENTIFIER ::= { mbus 99 }

mbus63IdNumber		OBJECT-TYPE
			SYNTAX	Gauge
			ACCESS	read-only
			STATUS	current
	DESCRIPTION ""
			::= { mbus63 1 }

mbus63Manufacturer	OBJECT-TYPE
			SYNTAX	Gauge
			ACCESS	read-only
			STATUS	current
	DESCRIPTION ""
			::= { mbus63 2 }

mbus63Version		OBJECT-TYPE
			SYNTAX	Gauge
			ACCESS	read-only
			STATUS	current
	DESCRIPTION ""
			::= { mbus63 3 }

mbus63Medium		OBJECT-TYPE
			SYNTAX	Gauge
			ACCESS	read-only
			STATUS	current
	DESCRIPTION ""
			::= { mbus63 4 }

mbus63Status		OBJECT-TYPE
			SYNTAX	Gauge
			ACCESS	read-only
			STATUS	current
	DESCRIPTION ""
			::= { mbus63 5 }

mbus63VIF00		OBJECT-TYPE
			SYNTAX	INTEGER
			ACCESS	read-only
			STATUS	current
	DESCRIPTION ""
			::= { mbus63 6 }

mbus63Value00		OBJECT-TYPE
			SYNTAX	INTEGER
			ACCESS	read-only
			STATUS	current
	DESCRIPTION ""
			::= { mbus63 7 }

mbus63VIF01		OBJECT-TYPE
			SYNTAX	INTEGER
			ACCESS	read-only
			STATUS	current
	DESCRIPTION ""
			::= { mbus63 8 }

mbus63Value01		OBJECT-TYPE
			SYNTAX	INTEGER
			ACCESS	read-only
			STATUS	current
	DESCRIPTION ""
			::= { mbus63 9 }

mbus63VIF02		OBJECT-TYPE
			SYNTAX	INTEGER
			ACCESS	read-only
			STATUS	current
	DESCRIPTION ""
			::= { mbus63 10 }

mbus63Value02		OBJECT-TYPE
			SYNTAX	INTEGER
			ACCESS	read-only
			STATUS	current
	DESCRIPTION ""
			::= { mbus63 11 }

mbus63VIF03		OBJECT-TYPE
			SYNTAX	INTEGER
			ACCESS	read-only
			STATUS	current
	DESCRIPTION ""
			::= { mbus63 12 }

mbus63Value03		OBJECT-TYPE
			SYNTAX	INTEGER
			ACCESS	read-only
			STATUS	current
	DESCRIPTION ""
			::= { mbus63 13 }

mbus63VIF04		OBJECT-TYPE
			SYNTAX	INTEGER
			ACCESS	read-only
			STATUS	current
	DESCRIPTION ""
			::= { mbus63 14 }

mbus63Value04		OBJECT-TYPE
			SYNTAX	INTEGER
			ACCESS	read-only
			STATUS	current
	DESCRIPTION ""
			::= { mbus63 15 }

mbus63VIF05		OBJECT-TYPE
			SYNTAX	INTEGER
			ACCESS	read-only
			STATUS	current
	DESCRIPTION ""
			::= { mbus63 16 }

mbus63Value05		OBJECT-TYPE
			SYNTAX	INTEGER
			ACCESS	read-only
			STATUS	current
	DESCRIPTION ""
			::= { mbus63 17 }

mbus63VIF06		OBJECT-TYPE
			SYNTAX	INTEGER
			ACCESS	read-only
			STATUS	current
	DESCRIPTION ""
			::= { mbus63 18 }

mbus63Value06		OBJECT-TYPE
			SYNTAX	INTEGER
			ACCESS	read-only
			STATUS	current
	DESCRIPTION ""
			::= { mbus63 19 }

mbus63VIF07		OBJECT-TYPE
			SYNTAX	INTEGER
			ACCESS	read-only
			STATUS	current
	DESCRIPTION ""
			::= { mbus63 20 }

mbus63Value07		OBJECT-TYPE
			SYNTAX	INTEGER
			ACCESS	read-only
			STATUS	current
	DESCRIPTION ""
			::= { mbus63 21 }

mbus63VIF08		OBJECT-TYPE
			SYNTAX	INTEGER
			ACCESS	read-only
			STATUS	current
	DESCRIPTION ""
			::= { mbus63 22 }

mbus63Value08		OBJECT-TYPE
			SYNTAX	INTEGER
			ACCESS	read-only
			STATUS	current
	DESCRIPTION ""
			::= { mbus63 23 }

mbus63VIF09		OBJECT-TYPE
			SYNTAX	INTEGER
			ACCESS	read-only
			STATUS	current
	DESCRIPTION ""
			::= { mbus63 24 }

mbus63Value09		OBJECT-TYPE
			SYNTAX	INTEGER
			ACCESS	read-only
			STATUS	current
	DESCRIPTION ""
			::= { mbus63 25 }

mbus63VIF0A		OBJECT-TYPE
			SYNTAX	INTEGER
			ACCESS	read-only
			STATUS	current
	DESCRIPTION ""
			::= { mbus63 26 }

mbus63Value0A		OBJECT-TYPE
			SYNTAX	INTEGER
			ACCESS	read-only
			STATUS	current
	DESCRIPTION ""
			::= { mbus63 27 }

mbus63VIF0B		OBJECT-TYPE
			SYNTAX	INTEGER
			ACCESS	read-only
			STATUS	current
	DESCRIPTION ""
			::= { mbus63 28 }

mbus63Value0B		OBJECT-TYPE
			SYNTAX	INTEGER
			ACCESS	read-only
			STATUS	current
	DESCRIPTION ""
			::= { mbus63 29 }

mbus63VIF0C		OBJECT-TYPE
			SYNTAX	INTEGER
			ACCESS	read-only
			STATUS	current
	DESCRIPTION ""
			::= { mbus63 30 }

mbus63Value0C		OBJECT-TYPE
			SYNTAX	INTEGER
			ACCESS	read-only
			STATUS	current
	DESCRIPTION ""
			::= { mbus63 31 }

mbus63VIF0D		OBJECT-TYPE
			SYNTAX	INTEGER
			ACCESS	read-only
			STATUS	current
	DESCRIPTION ""
			::= { mbus63 32 }

mbus63Value0D		OBJECT-TYPE
			SYNTAX	INTEGER
			ACCESS	read-only
			STATUS	current
	DESCRIPTION ""
			::= { mbus63 33 }

mbus63VIF0E		OBJECT-TYPE
			SYNTAX	INTEGER
			ACCESS	read-only
			STATUS	current
	DESCRIPTION ""
			::= { mbus63 34 }

mbus63Value0E		OBJECT-TYPE
			SYNTAX	INTEGER
			ACCESS	read-only
			STATUS	current
	DESCRIPTION ""
			::= { mbus63 35 }

mbus63VIF0F		OBJECT-TYPE
			SYNTAX	INTEGER
			ACCESS	read-only
			STATUS	current
	DESCRIPTION ""
			::= { mbus63 36 }

mbus63Value0F		OBJECT-TYPE
			SYNTAX	INTEGER
			ACCESS	read-only
			STATUS	current
	DESCRIPTION ""
			::= { mbus63 37 }

mbus63VIF10		OBJECT-TYPE
			SYNTAX	INTEGER
			ACCESS	read-only
			STATUS	current
	DESCRIPTION ""
			::= { mbus63 38 }

mbus63Value10		OBJECT-TYPE
			SYNTAX	INTEGER
			ACCESS	read-only
			STATUS	current
	DESCRIPTION ""
			::= { mbus63 39 }

mbus63VIF11		OBJECT-TYPE
			SYNTAX	INTEGER
			ACCESS	read-only
			STATUS	current
	DESCRIPTION ""
			::= { mbus63 40 }

mbus63Value11		OBJECT-TYPE
			SYNTAX	INTEGER
			ACCESS	read-only
			STATUS	current
	DESCRIPTION ""
			::= { mbus63 41 }

mbus63VIF12		OBJECT-TYPE
			SYNTAX	INTEGER
			ACCESS	read-only
			STATUS	current
	DESCRIPTION ""
			::= { mbus63 42 }

mbus63Value12		OBJECT-TYPE
			SYNTAX	INTEGER
			ACCESS	read-only
			STATUS	current
	DESCRIPTION ""
			::= { mbus63 43 }

mbus63VIF13		OBJECT-TYPE
			SYNTAX	INTEGER
			ACCESS	read-only
			STATUS	current
	DESCRIPTION ""
			::= { mbus63 44 }

mbus63Value13		OBJECT-TYPE
			SYNTAX	INTEGER
			ACCESS	read-only
			STATUS	current
	DESCRIPTION ""
			::= { mbus63 45 }

mbus63VIF14		OBJECT-TYPE
			SYNTAX	INTEGER
			ACCESS	read-only
			STATUS	current
	DESCRIPTION ""
			::= { mbus63 46 }

mbus63Value14		OBJECT-TYPE
			SYNTAX	INTEGER
			ACCESS	read-only
			STATUS	current
	DESCRIPTION ""
			::= { mbus63 47 }

mbus63VIF15		OBJECT-TYPE
			SYNTAX	INTEGER
			ACCESS	read-only
			STATUS	current
	DESCRIPTION ""
			::= { mbus63 48 }

mbus63Value15		OBJECT-TYPE
			SYNTAX	INTEGER
			ACCESS	read-only
			STATUS	current
	DESCRIPTION ""
			::= { mbus63 49 }

mbus63VIF16		OBJECT-TYPE
			SYNTAX	INTEGER
			ACCESS	read-only
			STATUS	current
	DESCRIPTION ""
			::= { mbus63 50 }

mbus63Value16		OBJECT-TYPE
			SYNTAX	INTEGER
			ACCESS	read-only
			STATUS	current
	DESCRIPTION ""
			::= { mbus63 51 }

mbus63VIF17		OBJECT-TYPE
			SYNTAX	INTEGER
			ACCESS	read-only
			STATUS	current
	DESCRIPTION ""
			::= { mbus63 52 }

mbus63Value17		OBJECT-TYPE
			SYNTAX	INTEGER
			ACCESS	read-only
			STATUS	current
	DESCRIPTION ""
			::= { mbus63 53 }

mbus63VIF18		OBJECT-TYPE
			SYNTAX	INTEGER
			ACCESS	read-only
			STATUS	current
	DESCRIPTION ""
			::= { mbus63 54 }

mbus63Value18		OBJECT-TYPE
			SYNTAX	INTEGER
			ACCESS	read-only
			STATUS	current
	DESCRIPTION ""
			::= { mbus63 55 }

mbus63VIF19		OBJECT-TYPE
			SYNTAX	INTEGER
			ACCESS	read-only
			STATUS	current
	DESCRIPTION ""
			::= { mbus63 56 }

mbus63Value19		OBJECT-TYPE
			SYNTAX	INTEGER
			ACCESS	read-only
			STATUS	current
	DESCRIPTION ""
			::= { mbus63 57 }

mbus63VIF1A		OBJECT-TYPE
			SYNTAX	INTEGER
			ACCESS	read-only
			STATUS	current
	DESCRIPTION ""
			::= { mbus63 58 }

mbus63Value1A		OBJECT-TYPE
			SYNTAX	INTEGER
			ACCESS	read-only
			STATUS	current
	DESCRIPTION ""
			::= { mbus63 59 }

mbus63VIF1B		OBJECT-TYPE
			SYNTAX	INTEGER
			ACCESS	read-only
			STATUS	current
	DESCRIPTION ""
			::= { mbus63 60 }

mbus63Value1B		OBJECT-TYPE
			SYNTAX	INTEGER
			ACCESS	read-only
			STATUS	current
	DESCRIPTION ""
			::= { mbus63 61 }

mbus63VIF1C		OBJECT-TYPE
			SYNTAX	INTEGER
			ACCESS	read-only
			STATUS	current
	DESCRIPTION ""
			::= { mbus63 62 }

mbus63Value1C		OBJECT-TYPE
			SYNTAX	INTEGER
			ACCESS	read-only
			STATUS	current
	DESCRIPTION ""
			::= { mbus63 63 }

mbus63VIF1D		OBJECT-TYPE
			SYNTAX	INTEGER
			ACCESS	read-only
			STATUS	current
	DESCRIPTION ""
			::= { mbus63 64 }

mbus63Value1D		OBJECT-TYPE
			SYNTAX	INTEGER
			ACCESS	read-only
			STATUS	current
	DESCRIPTION ""
			::= { mbus63 65 }

mbus63VIF1E		OBJECT-TYPE
			SYNTAX	INTEGER
			ACCESS	read-only
			STATUS	current
	DESCRIPTION ""
			::= { mbus63 66 }

mbus63Value1E		OBJECT-TYPE
			SYNTAX	INTEGER
			ACCESS	read-only
			STATUS	current
	DESCRIPTION ""
			::= { mbus63 67 }

mbus63VIF1F		OBJECT-TYPE
			SYNTAX	INTEGER
			ACCESS	read-only
			STATUS	current
	DESCRIPTION ""
			::= { mbus63 68 }

mbus63Value1F		OBJECT-TYPE
			SYNTAX	INTEGER
			ACCESS	read-only
			STATUS	current
	DESCRIPTION ""
			::= { mbus63 69 }

mbus63VIF20		OBJECT-TYPE
			SYNTAX	INTEGER
			ACCESS	read-only
			STATUS	current
	DESCRIPTION ""
			::= { mbus63 70 }

mbus63Value20		OBJECT-TYPE
			SYNTAX	INTEGER
			ACCESS	read-only
			STATUS	current
	DESCRIPTION ""
			::= { mbus63 71 }

mbus63VIF21		OBJECT-TYPE
			SYNTAX	INTEGER
			ACCESS	read-only
			STATUS	current
	DESCRIPTION ""
			::= { mbus63 72 }

mbus63Value21		OBJECT-TYPE
			SYNTAX	INTEGER
			ACCESS	read-only
			STATUS	current
	DESCRIPTION ""
			::= { mbus63 73 }

mbus63VIF22		OBJECT-TYPE
			SYNTAX	INTEGER
			ACCESS	read-only
			STATUS	current
	DESCRIPTION ""
			::= { mbus63 74 }

mbus63Value22		OBJECT-TYPE
			SYNTAX	INTEGER
			ACCESS	read-only
			STATUS	current
	DESCRIPTION ""
			::= { mbus63 75 }

mbus63VIF23		OBJECT-TYPE
			SYNTAX	INTEGER
			ACCESS	read-only
			STATUS	current
	DESCRIPTION ""
			::= { mbus63 76 }

mbus63Value23		OBJECT-TYPE
			SYNTAX	INTEGER
			ACCESS	read-only
			STATUS	current
	DESCRIPTION ""
			::= { mbus63 77 }

mbus63VIF24		OBJECT-TYPE
			SYNTAX	INTEGER
			ACCESS	read-only
			STATUS	current
	DESCRIPTION ""
			::= { mbus63 78 }

mbus63Value24		OBJECT-TYPE
			SYNTAX	INTEGER
			ACCESS	read-only
			STATUS	current
	DESCRIPTION ""
			::= { mbus63 79 }

mbus63VIF25		OBJECT-TYPE
			SYNTAX	INTEGER
			ACCESS	read-only
			STATUS	current
	DESCRIPTION ""
			::= { mbus63 80 }

mbus63Value25		OBJECT-TYPE
			SYNTAX	INTEGER
			ACCESS	read-only
			STATUS	current
	DESCRIPTION ""
			::= { mbus63 81 }

mbus63VIF26		OBJECT-TYPE
			SYNTAX	INTEGER
			ACCESS	read-only
			STATUS	current
	DESCRIPTION ""
			::= { mbus63 82 }

mbus63Value26		OBJECT-TYPE
			SYNTAX	INTEGER
			ACCESS	read-only
			STATUS	current
	DESCRIPTION ""
			::= { mbus63 83 }

mbus63VIF27		OBJECT-TYPE
			SYNTAX	INTEGER
			ACCESS	read-only
			STATUS	current
	DESCRIPTION ""
			::= { mbus63 84 }

mbus63Value27		OBJECT-TYPE
			SYNTAX	INTEGER
			ACCESS	read-only
			STATUS	current
	DESCRIPTION ""
			::= { mbus63 85 }

mbus63VIF28		OBJECT-TYPE
			SYNTAX	INTEGER
			ACCESS	read-only
			STATUS	current
	DESCRIPTION ""
			::= { mbus63 86 }

mbus63Value28		OBJECT-TYPE
			SYNTAX	INTEGER
			ACCESS	read-only
			STATUS	current
	DESCRIPTION ""
			::= { mbus63 87 }

mbus63VIF29		OBJECT-TYPE
			SYNTAX	INTEGER
			ACCESS	read-only
			STATUS	current
	DESCRIPTION ""
			::= { mbus63 88 }

mbus63Value29		OBJECT-TYPE
			SYNTAX	INTEGER
			ACCESS	read-only
			STATUS	current
	DESCRIPTION ""
			::= { mbus63 89 }

mbus63VIF2A		OBJECT-TYPE
			SYNTAX	INTEGER
			ACCESS	read-only
			STATUS	current
	DESCRIPTION ""
			::= { mbus63 90 }

mbus63Value2A		OBJECT-TYPE
			SYNTAX	INTEGER
			ACCESS	read-only
			STATUS	current
	DESCRIPTION ""
			::= { mbus63 91 }

mbus63VIF2B		OBJECT-TYPE
			SYNTAX	INTEGER
			ACCESS	read-only
			STATUS	current
	DESCRIPTION ""
			::= { mbus63 92 }

mbus63Value2B		OBJECT-TYPE
			SYNTAX	INTEGER
			ACCESS	read-only
			STATUS	current
	DESCRIPTION ""
			::= { mbus63 93 }

mbus63VIF2C		OBJECT-TYPE
			SYNTAX	INTEGER
			ACCESS	read-only
			STATUS	current
	DESCRIPTION ""
			::= { mbus63 94 }

mbus63Value2C		OBJECT-TYPE
			SYNTAX	INTEGER
			ACCESS	read-only
			STATUS	current
	DESCRIPTION ""
			::= { mbus63 95 }

mbus63VIF2D		OBJECT-TYPE
			SYNTAX	INTEGER
			ACCESS	read-only
			STATUS	current
	DESCRIPTION ""
			::= { mbus63 96 }

mbus63Value2D		OBJECT-TYPE
			SYNTAX	INTEGER
			ACCESS	read-only
			STATUS	current
	DESCRIPTION ""
			::= { mbus63 97 }

mbus63VIF2E		OBJECT-TYPE
			SYNTAX	INTEGER
			ACCESS	read-only
			STATUS	current
	DESCRIPTION ""
			::= { mbus63 98 }

mbus63Value2E		OBJECT-TYPE
			SYNTAX	INTEGER
			ACCESS	read-only
			STATUS	current
	DESCRIPTION ""
			::= { mbus63 99 }

mbus63VIF2F		OBJECT-TYPE
			SYNTAX	INTEGER
			ACCESS	read-only
			STATUS	current
	DESCRIPTION ""
			::= { mbus63 100 }

mbus63Value2F		OBJECT-TYPE
			SYNTAX	INTEGER
			ACCESS	read-only
			STATUS	current
	DESCRIPTION ""
			::= { mbus63 101 }

mbus64			OBJECT IDENTIFIER ::= { mbus 100 }

mbus64IdNumber		OBJECT-TYPE
			SYNTAX	Gauge
			ACCESS	read-only
			STATUS	current
	DESCRIPTION ""
			::= { mbus64 1 }

mbus64Manufacturer	OBJECT-TYPE
			SYNTAX	Gauge
			ACCESS	read-only
			STATUS	current
	DESCRIPTION ""
			::= { mbus64 2 }

mbus64Version		OBJECT-TYPE
			SYNTAX	Gauge
			ACCESS	read-only
			STATUS	current
	DESCRIPTION ""
			::= { mbus64 3 }

mbus64Medium		OBJECT-TYPE
			SYNTAX	Gauge
			ACCESS	read-only
			STATUS	current
	DESCRIPTION ""
			::= { mbus64 4 }

mbus64Status		OBJECT-TYPE
			SYNTAX	Gauge
			ACCESS	read-only
			STATUS	current
	DESCRIPTION ""
			::= { mbus64 5 }

mbus64VIF00		OBJECT-TYPE
			SYNTAX	INTEGER
			ACCESS	read-only
			STATUS	current
	DESCRIPTION ""
			::= { mbus64 6 }

mbus64Value00		OBJECT-TYPE
			SYNTAX	INTEGER
			ACCESS	read-only
			STATUS	current
	DESCRIPTION ""
			::= { mbus64 7 }

mbus64VIF01		OBJECT-TYPE
			SYNTAX	INTEGER
			ACCESS	read-only
			STATUS	current
	DESCRIPTION ""
			::= { mbus64 8 }

mbus64Value01		OBJECT-TYPE
			SYNTAX	INTEGER
			ACCESS	read-only
			STATUS	current
	DESCRIPTION ""
			::= { mbus64 9 }

mbus64VIF02		OBJECT-TYPE
			SYNTAX	INTEGER
			ACCESS	read-only
			STATUS	current
	DESCRIPTION ""
			::= { mbus64 10 }

mbus64Value02		OBJECT-TYPE
			SYNTAX	INTEGER
			ACCESS	read-only
			STATUS	current
	DESCRIPTION ""
			::= { mbus64 11 }

mbus64VIF03		OBJECT-TYPE
			SYNTAX	INTEGER
			ACCESS	read-only
			STATUS	current
	DESCRIPTION ""
			::= { mbus64 12 }

mbus64Value03		OBJECT-TYPE
			SYNTAX	INTEGER
			ACCESS	read-only
			STATUS	current
	DESCRIPTION ""
			::= { mbus64 13 }

mbus64VIF04		OBJECT-TYPE
			SYNTAX	INTEGER
			ACCESS	read-only
			STATUS	current
	DESCRIPTION ""
			::= { mbus64 14 }

mbus64Value04		OBJECT-TYPE
			SYNTAX	INTEGER
			ACCESS	read-only
			STATUS	current
	DESCRIPTION ""
			::= { mbus64 15 }

mbus64VIF05		OBJECT-TYPE
			SYNTAX	INTEGER
			ACCESS	read-only
			STATUS	current
	DESCRIPTION ""
			::= { mbus64 16 }

mbus64Value05		OBJECT-TYPE
			SYNTAX	INTEGER
			ACCESS	read-only
			STATUS	current
	DESCRIPTION ""
			::= { mbus64 17 }

mbus64VIF06		OBJECT-TYPE
			SYNTAX	INTEGER
			ACCESS	read-only
			STATUS	current
	DESCRIPTION ""
			::= { mbus64 18 }

mbus64Value06		OBJECT-TYPE
			SYNTAX	INTEGER
			ACCESS	read-only
			STATUS	current
	DESCRIPTION ""
			::= { mbus64 19 }

mbus64VIF07		OBJECT-TYPE
			SYNTAX	INTEGER
			ACCESS	read-only
			STATUS	current
	DESCRIPTION ""
			::= { mbus64 20 }

mbus64Value07		OBJECT-TYPE
			SYNTAX	INTEGER
			ACCESS	read-only
			STATUS	current
	DESCRIPTION ""
			::= { mbus64 21 }

mbus64VIF08		OBJECT-TYPE
			SYNTAX	INTEGER
			ACCESS	read-only
			STATUS	current
	DESCRIPTION ""
			::= { mbus64 22 }

mbus64Value08		OBJECT-TYPE
			SYNTAX	INTEGER
			ACCESS	read-only
			STATUS	current
	DESCRIPTION ""
			::= { mbus64 23 }

mbus64VIF09		OBJECT-TYPE
			SYNTAX	INTEGER
			ACCESS	read-only
			STATUS	current
	DESCRIPTION ""
			::= { mbus64 24 }

mbus64Value09		OBJECT-TYPE
			SYNTAX	INTEGER
			ACCESS	read-only
			STATUS	current
	DESCRIPTION ""
			::= { mbus64 25 }

mbus64VIF0A		OBJECT-TYPE
			SYNTAX	INTEGER
			ACCESS	read-only
			STATUS	current
	DESCRIPTION ""
			::= { mbus64 26 }

mbus64Value0A		OBJECT-TYPE
			SYNTAX	INTEGER
			ACCESS	read-only
			STATUS	current
	DESCRIPTION ""
			::= { mbus64 27 }

mbus64VIF0B		OBJECT-TYPE
			SYNTAX	INTEGER
			ACCESS	read-only
			STATUS	current
	DESCRIPTION ""
			::= { mbus64 28 }

mbus64Value0B		OBJECT-TYPE
			SYNTAX	INTEGER
			ACCESS	read-only
			STATUS	current
	DESCRIPTION ""
			::= { mbus64 29 }

mbus64VIF0C		OBJECT-TYPE
			SYNTAX	INTEGER
			ACCESS	read-only
			STATUS	current
	DESCRIPTION ""
			::= { mbus64 30 }

mbus64Value0C		OBJECT-TYPE
			SYNTAX	INTEGER
			ACCESS	read-only
			STATUS	current
	DESCRIPTION ""
			::= { mbus64 31 }

mbus64VIF0D		OBJECT-TYPE
			SYNTAX	INTEGER
			ACCESS	read-only
			STATUS	current
	DESCRIPTION ""
			::= { mbus64 32 }

mbus64Value0D		OBJECT-TYPE
			SYNTAX	INTEGER
			ACCESS	read-only
			STATUS	current
	DESCRIPTION ""
			::= { mbus64 33 }

mbus64VIF0E		OBJECT-TYPE
			SYNTAX	INTEGER
			ACCESS	read-only
			STATUS	current
	DESCRIPTION ""
			::= { mbus64 34 }

mbus64Value0E		OBJECT-TYPE
			SYNTAX	INTEGER
			ACCESS	read-only
			STATUS	current
	DESCRIPTION ""
			::= { mbus64 35 }

mbus64VIF0F		OBJECT-TYPE
			SYNTAX	INTEGER
			ACCESS	read-only
			STATUS	current
	DESCRIPTION ""
			::= { mbus64 36 }

mbus64Value0F		OBJECT-TYPE
			SYNTAX	INTEGER
			ACCESS	read-only
			STATUS	current
	DESCRIPTION ""
			::= { mbus64 37 }

mbus64VIF10		OBJECT-TYPE
			SYNTAX	INTEGER
			ACCESS	read-only
			STATUS	current
	DESCRIPTION ""
			::= { mbus64 38 }

mbus64Value10		OBJECT-TYPE
			SYNTAX	INTEGER
			ACCESS	read-only
			STATUS	current
	DESCRIPTION ""
			::= { mbus64 39 }

mbus64VIF11		OBJECT-TYPE
			SYNTAX	INTEGER
			ACCESS	read-only
			STATUS	current
	DESCRIPTION ""
			::= { mbus64 40 }

mbus64Value11		OBJECT-TYPE
			SYNTAX	INTEGER
			ACCESS	read-only
			STATUS	current
	DESCRIPTION ""
			::= { mbus64 41 }

mbus64VIF12		OBJECT-TYPE
			SYNTAX	INTEGER
			ACCESS	read-only
			STATUS	current
	DESCRIPTION ""
			::= { mbus64 42 }

mbus64Value12		OBJECT-TYPE
			SYNTAX	INTEGER
			ACCESS	read-only
			STATUS	current
	DESCRIPTION ""
			::= { mbus64 43 }

mbus64VIF13		OBJECT-TYPE
			SYNTAX	INTEGER
			ACCESS	read-only
			STATUS	current
	DESCRIPTION ""
			::= { mbus64 44 }

mbus64Value13		OBJECT-TYPE
			SYNTAX	INTEGER
			ACCESS	read-only
			STATUS	current
	DESCRIPTION ""
			::= { mbus64 45 }

mbus64VIF14		OBJECT-TYPE
			SYNTAX	INTEGER
			ACCESS	read-only
			STATUS	current
	DESCRIPTION ""
			::= { mbus64 46 }

mbus64Value14		OBJECT-TYPE
			SYNTAX	INTEGER
			ACCESS	read-only
			STATUS	current
	DESCRIPTION ""
			::= { mbus64 47 }

mbus64VIF15		OBJECT-TYPE
			SYNTAX	INTEGER
			ACCESS	read-only
			STATUS	current
	DESCRIPTION ""
			::= { mbus64 48 }

mbus64Value15		OBJECT-TYPE
			SYNTAX	INTEGER
			ACCESS	read-only
			STATUS	current
	DESCRIPTION ""
			::= { mbus64 49 }

mbus64VIF16		OBJECT-TYPE
			SYNTAX	INTEGER
			ACCESS	read-only
			STATUS	current
	DESCRIPTION ""
			::= { mbus64 50 }

mbus64Value16		OBJECT-TYPE
			SYNTAX	INTEGER
			ACCESS	read-only
			STATUS	current
	DESCRIPTION ""
			::= { mbus64 51 }

mbus64VIF17		OBJECT-TYPE
			SYNTAX	INTEGER
			ACCESS	read-only
			STATUS	current
	DESCRIPTION ""
			::= { mbus64 52 }

mbus64Value17		OBJECT-TYPE
			SYNTAX	INTEGER
			ACCESS	read-only
			STATUS	current
	DESCRIPTION ""
			::= { mbus64 53 }

mbus64VIF18		OBJECT-TYPE
			SYNTAX	INTEGER
			ACCESS	read-only
			STATUS	current
	DESCRIPTION ""
			::= { mbus64 54 }

mbus64Value18		OBJECT-TYPE
			SYNTAX	INTEGER
			ACCESS	read-only
			STATUS	current
	DESCRIPTION ""
			::= { mbus64 55 }

mbus64VIF19		OBJECT-TYPE
			SYNTAX	INTEGER
			ACCESS	read-only
			STATUS	current
	DESCRIPTION ""
			::= { mbus64 56 }

mbus64Value19		OBJECT-TYPE
			SYNTAX	INTEGER
			ACCESS	read-only
			STATUS	current
	DESCRIPTION ""
			::= { mbus64 57 }

mbus64VIF1A		OBJECT-TYPE
			SYNTAX	INTEGER
			ACCESS	read-only
			STATUS	current
	DESCRIPTION ""
			::= { mbus64 58 }

mbus64Value1A		OBJECT-TYPE
			SYNTAX	INTEGER
			ACCESS	read-only
			STATUS	current
	DESCRIPTION ""
			::= { mbus64 59 }

mbus64VIF1B		OBJECT-TYPE
			SYNTAX	INTEGER
			ACCESS	read-only
			STATUS	current
	DESCRIPTION ""
			::= { mbus64 60 }

mbus64Value1B		OBJECT-TYPE
			SYNTAX	INTEGER
			ACCESS	read-only
			STATUS	current
	DESCRIPTION ""
			::= { mbus64 61 }

mbus64VIF1C		OBJECT-TYPE
			SYNTAX	INTEGER
			ACCESS	read-only
			STATUS	current
	DESCRIPTION ""
			::= { mbus64 62 }

mbus64Value1C		OBJECT-TYPE
			SYNTAX	INTEGER
			ACCESS	read-only
			STATUS	current
	DESCRIPTION ""
			::= { mbus64 63 }

mbus64VIF1D		OBJECT-TYPE
			SYNTAX	INTEGER
			ACCESS	read-only
			STATUS	current
	DESCRIPTION ""
			::= { mbus64 64 }

mbus64Value1D		OBJECT-TYPE
			SYNTAX	INTEGER
			ACCESS	read-only
			STATUS	current
	DESCRIPTION ""
			::= { mbus64 65 }

mbus64VIF1E		OBJECT-TYPE
			SYNTAX	INTEGER
			ACCESS	read-only
			STATUS	current
	DESCRIPTION ""
			::= { mbus64 66 }

mbus64Value1E		OBJECT-TYPE
			SYNTAX	INTEGER
			ACCESS	read-only
			STATUS	current
	DESCRIPTION ""
			::= { mbus64 67 }

mbus64VIF1F		OBJECT-TYPE
			SYNTAX	INTEGER
			ACCESS	read-only
			STATUS	current
	DESCRIPTION ""
			::= { mbus64 68 }

mbus64Value1F		OBJECT-TYPE
			SYNTAX	INTEGER
			ACCESS	read-only
			STATUS	current
	DESCRIPTION ""
			::= { mbus64 69 }

mbus64VIF20		OBJECT-TYPE
			SYNTAX	INTEGER
			ACCESS	read-only
			STATUS	current
	DESCRIPTION ""
			::= { mbus64 70 }

mbus64Value20		OBJECT-TYPE
			SYNTAX	INTEGER
			ACCESS	read-only
			STATUS	current
	DESCRIPTION ""
			::= { mbus64 71 }

mbus64VIF21		OBJECT-TYPE
			SYNTAX	INTEGER
			ACCESS	read-only
			STATUS	current
	DESCRIPTION ""
			::= { mbus64 72 }

mbus64Value21		OBJECT-TYPE
			SYNTAX	INTEGER
			ACCESS	read-only
			STATUS	current
	DESCRIPTION ""
			::= { mbus64 73 }

mbus64VIF22		OBJECT-TYPE
			SYNTAX	INTEGER
			ACCESS	read-only
			STATUS	current
	DESCRIPTION ""
			::= { mbus64 74 }

mbus64Value22		OBJECT-TYPE
			SYNTAX	INTEGER
			ACCESS	read-only
			STATUS	current
	DESCRIPTION ""
			::= { mbus64 75 }

mbus64VIF23		OBJECT-TYPE
			SYNTAX	INTEGER
			ACCESS	read-only
			STATUS	current
	DESCRIPTION ""
			::= { mbus64 76 }

mbus64Value23		OBJECT-TYPE
			SYNTAX	INTEGER
			ACCESS	read-only
			STATUS	current
	DESCRIPTION ""
			::= { mbus64 77 }

mbus64VIF24		OBJECT-TYPE
			SYNTAX	INTEGER
			ACCESS	read-only
			STATUS	current
	DESCRIPTION ""
			::= { mbus64 78 }

mbus64Value24		OBJECT-TYPE
			SYNTAX	INTEGER
			ACCESS	read-only
			STATUS	current
	DESCRIPTION ""
			::= { mbus64 79 }

mbus64VIF25		OBJECT-TYPE
			SYNTAX	INTEGER
			ACCESS	read-only
			STATUS	current
	DESCRIPTION ""
			::= { mbus64 80 }

mbus64Value25		OBJECT-TYPE
			SYNTAX	INTEGER
			ACCESS	read-only
			STATUS	current
	DESCRIPTION ""
			::= { mbus64 81 }

mbus64VIF26		OBJECT-TYPE
			SYNTAX	INTEGER
			ACCESS	read-only
			STATUS	current
	DESCRIPTION ""
			::= { mbus64 82 }

mbus64Value26		OBJECT-TYPE
			SYNTAX	INTEGER
			ACCESS	read-only
			STATUS	current
	DESCRIPTION ""
			::= { mbus64 83 }

mbus64VIF27		OBJECT-TYPE
			SYNTAX	INTEGER
			ACCESS	read-only
			STATUS	current
	DESCRIPTION ""
			::= { mbus64 84 }

mbus64Value27		OBJECT-TYPE
			SYNTAX	INTEGER
			ACCESS	read-only
			STATUS	current
	DESCRIPTION ""
			::= { mbus64 85 }

mbus64VIF28		OBJECT-TYPE
			SYNTAX	INTEGER
			ACCESS	read-only
			STATUS	current
	DESCRIPTION ""
			::= { mbus64 86 }

mbus64Value28		OBJECT-TYPE
			SYNTAX	INTEGER
			ACCESS	read-only
			STATUS	current
	DESCRIPTION ""
			::= { mbus64 87 }

mbus64VIF29		OBJECT-TYPE
			SYNTAX	INTEGER
			ACCESS	read-only
			STATUS	current
	DESCRIPTION ""
			::= { mbus64 88 }

mbus64Value29		OBJECT-TYPE
			SYNTAX	INTEGER
			ACCESS	read-only
			STATUS	current
	DESCRIPTION ""
			::= { mbus64 89 }

mbus64VIF2A		OBJECT-TYPE
			SYNTAX	INTEGER
			ACCESS	read-only
			STATUS	current
	DESCRIPTION ""
			::= { mbus64 90 }

mbus64Value2A		OBJECT-TYPE
			SYNTAX	INTEGER
			ACCESS	read-only
			STATUS	current
	DESCRIPTION ""
			::= { mbus64 91 }

mbus64VIF2B		OBJECT-TYPE
			SYNTAX	INTEGER
			ACCESS	read-only
			STATUS	current
	DESCRIPTION ""
			::= { mbus64 92 }

mbus64Value2B		OBJECT-TYPE
			SYNTAX	INTEGER
			ACCESS	read-only
			STATUS	current
	DESCRIPTION ""
			::= { mbus64 93 }

mbus64VIF2C		OBJECT-TYPE
			SYNTAX	INTEGER
			ACCESS	read-only
			STATUS	current
	DESCRIPTION ""
			::= { mbus64 94 }

mbus64Value2C		OBJECT-TYPE
			SYNTAX	INTEGER
			ACCESS	read-only
			STATUS	current
	DESCRIPTION ""
			::= { mbus64 95 }

mbus64VIF2D		OBJECT-TYPE
			SYNTAX	INTEGER
			ACCESS	read-only
			STATUS	current
	DESCRIPTION ""
			::= { mbus64 96 }

mbus64Value2D		OBJECT-TYPE
			SYNTAX	INTEGER
			ACCESS	read-only
			STATUS	current
	DESCRIPTION ""
			::= { mbus64 97 }

mbus64VIF2E		OBJECT-TYPE
			SYNTAX	INTEGER
			ACCESS	read-only
			STATUS	current
	DESCRIPTION ""
			::= { mbus64 98 }

mbus64Value2E		OBJECT-TYPE
			SYNTAX	INTEGER
			ACCESS	read-only
			STATUS	current
	DESCRIPTION ""
			::= { mbus64 99 }

mbus64VIF2F		OBJECT-TYPE
			SYNTAX	INTEGER
			ACCESS	read-only
			STATUS	current
	DESCRIPTION ""
			::= { mbus64 100 }

mbus64Value2F		OBJECT-TYPE
			SYNTAX	INTEGER
			ACCESS	read-only
			STATUS	current
	DESCRIPTION ""
			::= { mbus64 101 }

mbus65			OBJECT IDENTIFIER ::= { mbus 101 }

mbus65IdNumber		OBJECT-TYPE
			SYNTAX	Gauge
			ACCESS	read-only
			STATUS	current
	DESCRIPTION ""
			::= { mbus65 1 }

mbus65Manufacturer	OBJECT-TYPE
			SYNTAX	Gauge
			ACCESS	read-only
			STATUS	current
	DESCRIPTION ""
			::= { mbus65 2 }

mbus65Version		OBJECT-TYPE
			SYNTAX	Gauge
			ACCESS	read-only
			STATUS	current
	DESCRIPTION ""
			::= { mbus65 3 }

mbus65Medium		OBJECT-TYPE
			SYNTAX	Gauge
			ACCESS	read-only
			STATUS	current
	DESCRIPTION ""
			::= { mbus65 4 }

mbus65Status		OBJECT-TYPE
			SYNTAX	Gauge
			ACCESS	read-only
			STATUS	current
	DESCRIPTION ""
			::= { mbus65 5 }

mbus65VIF00		OBJECT-TYPE
			SYNTAX	INTEGER
			ACCESS	read-only
			STATUS	current
	DESCRIPTION ""
			::= { mbus65 6 }

mbus65Value00		OBJECT-TYPE
			SYNTAX	INTEGER
			ACCESS	read-only
			STATUS	current
	DESCRIPTION ""
			::= { mbus65 7 }

mbus65VIF01		OBJECT-TYPE
			SYNTAX	INTEGER
			ACCESS	read-only
			STATUS	current
	DESCRIPTION ""
			::= { mbus65 8 }

mbus65Value01		OBJECT-TYPE
			SYNTAX	INTEGER
			ACCESS	read-only
			STATUS	current
	DESCRIPTION ""
			::= { mbus65 9 }

mbus65VIF02		OBJECT-TYPE
			SYNTAX	INTEGER
			ACCESS	read-only
			STATUS	current
	DESCRIPTION ""
			::= { mbus65 10 }

mbus65Value02		OBJECT-TYPE
			SYNTAX	INTEGER
			ACCESS	read-only
			STATUS	current
	DESCRIPTION ""
			::= { mbus65 11 }

mbus65VIF03		OBJECT-TYPE
			SYNTAX	INTEGER
			ACCESS	read-only
			STATUS	current
	DESCRIPTION ""
			::= { mbus65 12 }

mbus65Value03		OBJECT-TYPE
			SYNTAX	INTEGER
			ACCESS	read-only
			STATUS	current
	DESCRIPTION ""
			::= { mbus65 13 }

mbus65VIF04		OBJECT-TYPE
			SYNTAX	INTEGER
			ACCESS	read-only
			STATUS	current
	DESCRIPTION ""
			::= { mbus65 14 }

mbus65Value04		OBJECT-TYPE
			SYNTAX	INTEGER
			ACCESS	read-only
			STATUS	current
	DESCRIPTION ""
			::= { mbus65 15 }

mbus65VIF05		OBJECT-TYPE
			SYNTAX	INTEGER
			ACCESS	read-only
			STATUS	current
	DESCRIPTION ""
			::= { mbus65 16 }

mbus65Value05		OBJECT-TYPE
			SYNTAX	INTEGER
			ACCESS	read-only
			STATUS	current
	DESCRIPTION ""
			::= { mbus65 17 }

mbus65VIF06		OBJECT-TYPE
			SYNTAX	INTEGER
			ACCESS	read-only
			STATUS	current
	DESCRIPTION ""
			::= { mbus65 18 }

mbus65Value06		OBJECT-TYPE
			SYNTAX	INTEGER
			ACCESS	read-only
			STATUS	current
	DESCRIPTION ""
			::= { mbus65 19 }

mbus65VIF07		OBJECT-TYPE
			SYNTAX	INTEGER
			ACCESS	read-only
			STATUS	current
	DESCRIPTION ""
			::= { mbus65 20 }

mbus65Value07		OBJECT-TYPE
			SYNTAX	INTEGER
			ACCESS	read-only
			STATUS	current
	DESCRIPTION ""
			::= { mbus65 21 }

mbus65VIF08		OBJECT-TYPE
			SYNTAX	INTEGER
			ACCESS	read-only
			STATUS	current
	DESCRIPTION ""
			::= { mbus65 22 }

mbus65Value08		OBJECT-TYPE
			SYNTAX	INTEGER
			ACCESS	read-only
			STATUS	current
	DESCRIPTION ""
			::= { mbus65 23 }

mbus65VIF09		OBJECT-TYPE
			SYNTAX	INTEGER
			ACCESS	read-only
			STATUS	current
	DESCRIPTION ""
			::= { mbus65 24 }

mbus65Value09		OBJECT-TYPE
			SYNTAX	INTEGER
			ACCESS	read-only
			STATUS	current
	DESCRIPTION ""
			::= { mbus65 25 }

mbus65VIF0A		OBJECT-TYPE
			SYNTAX	INTEGER
			ACCESS	read-only
			STATUS	current
	DESCRIPTION ""
			::= { mbus65 26 }

mbus65Value0A		OBJECT-TYPE
			SYNTAX	INTEGER
			ACCESS	read-only
			STATUS	current
	DESCRIPTION ""
			::= { mbus65 27 }

mbus65VIF0B		OBJECT-TYPE
			SYNTAX	INTEGER
			ACCESS	read-only
			STATUS	current
	DESCRIPTION ""
			::= { mbus65 28 }

mbus65Value0B		OBJECT-TYPE
			SYNTAX	INTEGER
			ACCESS	read-only
			STATUS	current
	DESCRIPTION ""
			::= { mbus65 29 }

mbus65VIF0C		OBJECT-TYPE
			SYNTAX	INTEGER
			ACCESS	read-only
			STATUS	current
	DESCRIPTION ""
			::= { mbus65 30 }

mbus65Value0C		OBJECT-TYPE
			SYNTAX	INTEGER
			ACCESS	read-only
			STATUS	current
	DESCRIPTION ""
			::= { mbus65 31 }

mbus65VIF0D		OBJECT-TYPE
			SYNTAX	INTEGER
			ACCESS	read-only
			STATUS	current
	DESCRIPTION ""
			::= { mbus65 32 }

mbus65Value0D		OBJECT-TYPE
			SYNTAX	INTEGER
			ACCESS	read-only
			STATUS	current
	DESCRIPTION ""
			::= { mbus65 33 }

mbus65VIF0E		OBJECT-TYPE
			SYNTAX	INTEGER
			ACCESS	read-only
			STATUS	current
	DESCRIPTION ""
			::= { mbus65 34 }

mbus65Value0E		OBJECT-TYPE
			SYNTAX	INTEGER
			ACCESS	read-only
			STATUS	current
	DESCRIPTION ""
			::= { mbus65 35 }

mbus65VIF0F		OBJECT-TYPE
			SYNTAX	INTEGER
			ACCESS	read-only
			STATUS	current
	DESCRIPTION ""
			::= { mbus65 36 }

mbus65Value0F		OBJECT-TYPE
			SYNTAX	INTEGER
			ACCESS	read-only
			STATUS	current
	DESCRIPTION ""
			::= { mbus65 37 }

mbus65VIF10		OBJECT-TYPE
			SYNTAX	INTEGER
			ACCESS	read-only
			STATUS	current
	DESCRIPTION ""
			::= { mbus65 38 }

mbus65Value10		OBJECT-TYPE
			SYNTAX	INTEGER
			ACCESS	read-only
			STATUS	current
	DESCRIPTION ""
			::= { mbus65 39 }

mbus65VIF11		OBJECT-TYPE
			SYNTAX	INTEGER
			ACCESS	read-only
			STATUS	current
	DESCRIPTION ""
			::= { mbus65 40 }

mbus65Value11		OBJECT-TYPE
			SYNTAX	INTEGER
			ACCESS	read-only
			STATUS	current
	DESCRIPTION ""
			::= { mbus65 41 }

mbus65VIF12		OBJECT-TYPE
			SYNTAX	INTEGER
			ACCESS	read-only
			STATUS	current
	DESCRIPTION ""
			::= { mbus65 42 }

mbus65Value12		OBJECT-TYPE
			SYNTAX	INTEGER
			ACCESS	read-only
			STATUS	current
	DESCRIPTION ""
			::= { mbus65 43 }

mbus65VIF13		OBJECT-TYPE
			SYNTAX	INTEGER
			ACCESS	read-only
			STATUS	current
	DESCRIPTION ""
			::= { mbus65 44 }

mbus65Value13		OBJECT-TYPE
			SYNTAX	INTEGER
			ACCESS	read-only
			STATUS	current
	DESCRIPTION ""
			::= { mbus65 45 }

mbus65VIF14		OBJECT-TYPE
			SYNTAX	INTEGER
			ACCESS	read-only
			STATUS	current
	DESCRIPTION ""
			::= { mbus65 46 }

mbus65Value14		OBJECT-TYPE
			SYNTAX	INTEGER
			ACCESS	read-only
			STATUS	current
	DESCRIPTION ""
			::= { mbus65 47 }

mbus65VIF15		OBJECT-TYPE
			SYNTAX	INTEGER
			ACCESS	read-only
			STATUS	current
	DESCRIPTION ""
			::= { mbus65 48 }

mbus65Value15		OBJECT-TYPE
			SYNTAX	INTEGER
			ACCESS	read-only
			STATUS	current
	DESCRIPTION ""
			::= { mbus65 49 }

mbus65VIF16		OBJECT-TYPE
			SYNTAX	INTEGER
			ACCESS	read-only
			STATUS	current
	DESCRIPTION ""
			::= { mbus65 50 }

mbus65Value16		OBJECT-TYPE
			SYNTAX	INTEGER
			ACCESS	read-only
			STATUS	current
	DESCRIPTION ""
			::= { mbus65 51 }

mbus65VIF17		OBJECT-TYPE
			SYNTAX	INTEGER
			ACCESS	read-only
			STATUS	current
	DESCRIPTION ""
			::= { mbus65 52 }

mbus65Value17		OBJECT-TYPE
			SYNTAX	INTEGER
			ACCESS	read-only
			STATUS	current
	DESCRIPTION ""
			::= { mbus65 53 }

mbus65VIF18		OBJECT-TYPE
			SYNTAX	INTEGER
			ACCESS	read-only
			STATUS	current
	DESCRIPTION ""
			::= { mbus65 54 }

mbus65Value18		OBJECT-TYPE
			SYNTAX	INTEGER
			ACCESS	read-only
			STATUS	current
	DESCRIPTION ""
			::= { mbus65 55 }

mbus65VIF19		OBJECT-TYPE
			SYNTAX	INTEGER
			ACCESS	read-only
			STATUS	current
	DESCRIPTION ""
			::= { mbus65 56 }

mbus65Value19		OBJECT-TYPE
			SYNTAX	INTEGER
			ACCESS	read-only
			STATUS	current
	DESCRIPTION ""
			::= { mbus65 57 }

mbus65VIF1A		OBJECT-TYPE
			SYNTAX	INTEGER
			ACCESS	read-only
			STATUS	current
	DESCRIPTION ""
			::= { mbus65 58 }

mbus65Value1A		OBJECT-TYPE
			SYNTAX	INTEGER
			ACCESS	read-only
			STATUS	current
	DESCRIPTION ""
			::= { mbus65 59 }

mbus65VIF1B		OBJECT-TYPE
			SYNTAX	INTEGER
			ACCESS	read-only
			STATUS	current
	DESCRIPTION ""
			::= { mbus65 60 }

mbus65Value1B		OBJECT-TYPE
			SYNTAX	INTEGER
			ACCESS	read-only
			STATUS	current
	DESCRIPTION ""
			::= { mbus65 61 }

mbus65VIF1C		OBJECT-TYPE
			SYNTAX	INTEGER
			ACCESS	read-only
			STATUS	current
	DESCRIPTION ""
			::= { mbus65 62 }

mbus65Value1C		OBJECT-TYPE
			SYNTAX	INTEGER
			ACCESS	read-only
			STATUS	current
	DESCRIPTION ""
			::= { mbus65 63 }

mbus65VIF1D		OBJECT-TYPE
			SYNTAX	INTEGER
			ACCESS	read-only
			STATUS	current
	DESCRIPTION ""
			::= { mbus65 64 }

mbus65Value1D		OBJECT-TYPE
			SYNTAX	INTEGER
			ACCESS	read-only
			STATUS	current
	DESCRIPTION ""
			::= { mbus65 65 }

mbus65VIF1E		OBJECT-TYPE
			SYNTAX	INTEGER
			ACCESS	read-only
			STATUS	current
	DESCRIPTION ""
			::= { mbus65 66 }

mbus65Value1E		OBJECT-TYPE
			SYNTAX	INTEGER
			ACCESS	read-only
			STATUS	current
	DESCRIPTION ""
			::= { mbus65 67 }

mbus65VIF1F		OBJECT-TYPE
			SYNTAX	INTEGER
			ACCESS	read-only
			STATUS	current
	DESCRIPTION ""
			::= { mbus65 68 }

mbus65Value1F		OBJECT-TYPE
			SYNTAX	INTEGER
			ACCESS	read-only
			STATUS	current
	DESCRIPTION ""
			::= { mbus65 69 }

mbus65VIF20		OBJECT-TYPE
			SYNTAX	INTEGER
			ACCESS	read-only
			STATUS	current
	DESCRIPTION ""
			::= { mbus65 70 }

mbus65Value20		OBJECT-TYPE
			SYNTAX	INTEGER
			ACCESS	read-only
			STATUS	current
	DESCRIPTION ""
			::= { mbus65 71 }

mbus65VIF21		OBJECT-TYPE
			SYNTAX	INTEGER
			ACCESS	read-only
			STATUS	current
	DESCRIPTION ""
			::= { mbus65 72 }

mbus65Value21		OBJECT-TYPE
			SYNTAX	INTEGER
			ACCESS	read-only
			STATUS	current
	DESCRIPTION ""
			::= { mbus65 73 }

mbus65VIF22		OBJECT-TYPE
			SYNTAX	INTEGER
			ACCESS	read-only
			STATUS	current
	DESCRIPTION ""
			::= { mbus65 74 }

mbus65Value22		OBJECT-TYPE
			SYNTAX	INTEGER
			ACCESS	read-only
			STATUS	current
	DESCRIPTION ""
			::= { mbus65 75 }

mbus65VIF23		OBJECT-TYPE
			SYNTAX	INTEGER
			ACCESS	read-only
			STATUS	current
	DESCRIPTION ""
			::= { mbus65 76 }

mbus65Value23		OBJECT-TYPE
			SYNTAX	INTEGER
			ACCESS	read-only
			STATUS	current
	DESCRIPTION ""
			::= { mbus65 77 }

mbus65VIF24		OBJECT-TYPE
			SYNTAX	INTEGER
			ACCESS	read-only
			STATUS	current
	DESCRIPTION ""
			::= { mbus65 78 }

mbus65Value24		OBJECT-TYPE
			SYNTAX	INTEGER
			ACCESS	read-only
			STATUS	current
	DESCRIPTION ""
			::= { mbus65 79 }

mbus65VIF25		OBJECT-TYPE
			SYNTAX	INTEGER
			ACCESS	read-only
			STATUS	current
	DESCRIPTION ""
			::= { mbus65 80 }

mbus65Value25		OBJECT-TYPE
			SYNTAX	INTEGER
			ACCESS	read-only
			STATUS	current
	DESCRIPTION ""
			::= { mbus65 81 }

mbus65VIF26		OBJECT-TYPE
			SYNTAX	INTEGER
			ACCESS	read-only
			STATUS	current
	DESCRIPTION ""
			::= { mbus65 82 }

mbus65Value26		OBJECT-TYPE
			SYNTAX	INTEGER
			ACCESS	read-only
			STATUS	current
	DESCRIPTION ""
			::= { mbus65 83 }

mbus65VIF27		OBJECT-TYPE
			SYNTAX	INTEGER
			ACCESS	read-only
			STATUS	current
	DESCRIPTION ""
			::= { mbus65 84 }

mbus65Value27		OBJECT-TYPE
			SYNTAX	INTEGER
			ACCESS	read-only
			STATUS	current
	DESCRIPTION ""
			::= { mbus65 85 }

mbus65VIF28		OBJECT-TYPE
			SYNTAX	INTEGER
			ACCESS	read-only
			STATUS	current
	DESCRIPTION ""
			::= { mbus65 86 }

mbus65Value28		OBJECT-TYPE
			SYNTAX	INTEGER
			ACCESS	read-only
			STATUS	current
	DESCRIPTION ""
			::= { mbus65 87 }

mbus65VIF29		OBJECT-TYPE
			SYNTAX	INTEGER
			ACCESS	read-only
			STATUS	current
	DESCRIPTION ""
			::= { mbus65 88 }

mbus65Value29		OBJECT-TYPE
			SYNTAX	INTEGER
			ACCESS	read-only
			STATUS	current
	DESCRIPTION ""
			::= { mbus65 89 }

mbus65VIF2A		OBJECT-TYPE
			SYNTAX	INTEGER
			ACCESS	read-only
			STATUS	current
	DESCRIPTION ""
			::= { mbus65 90 }

mbus65Value2A		OBJECT-TYPE
			SYNTAX	INTEGER
			ACCESS	read-only
			STATUS	current
	DESCRIPTION ""
			::= { mbus65 91 }

mbus65VIF2B		OBJECT-TYPE
			SYNTAX	INTEGER
			ACCESS	read-only
			STATUS	current
	DESCRIPTION ""
			::= { mbus65 92 }

mbus65Value2B		OBJECT-TYPE
			SYNTAX	INTEGER
			ACCESS	read-only
			STATUS	current
	DESCRIPTION ""
			::= { mbus65 93 }

mbus65VIF2C		OBJECT-TYPE
			SYNTAX	INTEGER
			ACCESS	read-only
			STATUS	current
	DESCRIPTION ""
			::= { mbus65 94 }

mbus65Value2C		OBJECT-TYPE
			SYNTAX	INTEGER
			ACCESS	read-only
			STATUS	current
	DESCRIPTION ""
			::= { mbus65 95 }

mbus65VIF2D		OBJECT-TYPE
			SYNTAX	INTEGER
			ACCESS	read-only
			STATUS	current
	DESCRIPTION ""
			::= { mbus65 96 }

mbus65Value2D		OBJECT-TYPE
			SYNTAX	INTEGER
			ACCESS	read-only
			STATUS	current
	DESCRIPTION ""
			::= { mbus65 97 }

mbus65VIF2E		OBJECT-TYPE
			SYNTAX	INTEGER
			ACCESS	read-only
			STATUS	current
	DESCRIPTION ""
			::= { mbus65 98 }

mbus65Value2E		OBJECT-TYPE
			SYNTAX	INTEGER
			ACCESS	read-only
			STATUS	current
	DESCRIPTION ""
			::= { mbus65 99 }

mbus65VIF2F		OBJECT-TYPE
			SYNTAX	INTEGER
			ACCESS	read-only
			STATUS	current
	DESCRIPTION ""
			::= { mbus65 100 }

mbus65Value2F		OBJECT-TYPE
			SYNTAX	INTEGER
			ACCESS	read-only
			STATUS	current
	DESCRIPTION ""
			::= { mbus65 101 }

mbus66			OBJECT IDENTIFIER ::= { mbus 102 }

mbus66IdNumber		OBJECT-TYPE
			SYNTAX	Gauge
			ACCESS	read-only
			STATUS	current
	DESCRIPTION ""
			::= { mbus66 1 }

mbus66Manufacturer	OBJECT-TYPE
			SYNTAX	Gauge
			ACCESS	read-only
			STATUS	current
	DESCRIPTION ""
			::= { mbus66 2 }

mbus66Version		OBJECT-TYPE
			SYNTAX	Gauge
			ACCESS	read-only
			STATUS	current
	DESCRIPTION ""
			::= { mbus66 3 }

mbus66Medium		OBJECT-TYPE
			SYNTAX	Gauge
			ACCESS	read-only
			STATUS	current
	DESCRIPTION ""
			::= { mbus66 4 }

mbus66Status		OBJECT-TYPE
			SYNTAX	Gauge
			ACCESS	read-only
			STATUS	current
	DESCRIPTION ""
			::= { mbus66 5 }

mbus66VIF00		OBJECT-TYPE
			SYNTAX	INTEGER
			ACCESS	read-only
			STATUS	current
	DESCRIPTION ""
			::= { mbus66 6 }

mbus66Value00		OBJECT-TYPE
			SYNTAX	INTEGER
			ACCESS	read-only
			STATUS	current
	DESCRIPTION ""
			::= { mbus66 7 }

mbus66VIF01		OBJECT-TYPE
			SYNTAX	INTEGER
			ACCESS	read-only
			STATUS	current
	DESCRIPTION ""
			::= { mbus66 8 }

mbus66Value01		OBJECT-TYPE
			SYNTAX	INTEGER
			ACCESS	read-only
			STATUS	current
	DESCRIPTION ""
			::= { mbus66 9 }

mbus66VIF02		OBJECT-TYPE
			SYNTAX	INTEGER
			ACCESS	read-only
			STATUS	current
	DESCRIPTION ""
			::= { mbus66 10 }

mbus66Value02		OBJECT-TYPE
			SYNTAX	INTEGER
			ACCESS	read-only
			STATUS	current
	DESCRIPTION ""
			::= { mbus66 11 }

mbus66VIF03		OBJECT-TYPE
			SYNTAX	INTEGER
			ACCESS	read-only
			STATUS	current
	DESCRIPTION ""
			::= { mbus66 12 }

mbus66Value03		OBJECT-TYPE
			SYNTAX	INTEGER
			ACCESS	read-only
			STATUS	current
	DESCRIPTION ""
			::= { mbus66 13 }

mbus66VIF04		OBJECT-TYPE
			SYNTAX	INTEGER
			ACCESS	read-only
			STATUS	current
	DESCRIPTION ""
			::= { mbus66 14 }

mbus66Value04		OBJECT-TYPE
			SYNTAX	INTEGER
			ACCESS	read-only
			STATUS	current
	DESCRIPTION ""
			::= { mbus66 15 }

mbus66VIF05		OBJECT-TYPE
			SYNTAX	INTEGER
			ACCESS	read-only
			STATUS	current
	DESCRIPTION ""
			::= { mbus66 16 }

mbus66Value05		OBJECT-TYPE
			SYNTAX	INTEGER
			ACCESS	read-only
			STATUS	current
	DESCRIPTION ""
			::= { mbus66 17 }

mbus66VIF06		OBJECT-TYPE
			SYNTAX	INTEGER
			ACCESS	read-only
			STATUS	current
	DESCRIPTION ""
			::= { mbus66 18 }

mbus66Value06		OBJECT-TYPE
			SYNTAX	INTEGER
			ACCESS	read-only
			STATUS	current
	DESCRIPTION ""
			::= { mbus66 19 }

mbus66VIF07		OBJECT-TYPE
			SYNTAX	INTEGER
			ACCESS	read-only
			STATUS	current
	DESCRIPTION ""
			::= { mbus66 20 }

mbus66Value07		OBJECT-TYPE
			SYNTAX	INTEGER
			ACCESS	read-only
			STATUS	current
	DESCRIPTION ""
			::= { mbus66 21 }

mbus66VIF08		OBJECT-TYPE
			SYNTAX	INTEGER
			ACCESS	read-only
			STATUS	current
	DESCRIPTION ""
			::= { mbus66 22 }

mbus66Value08		OBJECT-TYPE
			SYNTAX	INTEGER
			ACCESS	read-only
			STATUS	current
	DESCRIPTION ""
			::= { mbus66 23 }

mbus66VIF09		OBJECT-TYPE
			SYNTAX	INTEGER
			ACCESS	read-only
			STATUS	current
	DESCRIPTION ""
			::= { mbus66 24 }

mbus66Value09		OBJECT-TYPE
			SYNTAX	INTEGER
			ACCESS	read-only
			STATUS	current
	DESCRIPTION ""
			::= { mbus66 25 }

mbus66VIF0A		OBJECT-TYPE
			SYNTAX	INTEGER
			ACCESS	read-only
			STATUS	current
	DESCRIPTION ""
			::= { mbus66 26 }

mbus66Value0A		OBJECT-TYPE
			SYNTAX	INTEGER
			ACCESS	read-only
			STATUS	current
	DESCRIPTION ""
			::= { mbus66 27 }

mbus66VIF0B		OBJECT-TYPE
			SYNTAX	INTEGER
			ACCESS	read-only
			STATUS	current
	DESCRIPTION ""
			::= { mbus66 28 }

mbus66Value0B		OBJECT-TYPE
			SYNTAX	INTEGER
			ACCESS	read-only
			STATUS	current
	DESCRIPTION ""
			::= { mbus66 29 }

mbus66VIF0C		OBJECT-TYPE
			SYNTAX	INTEGER
			ACCESS	read-only
			STATUS	current
	DESCRIPTION ""
			::= { mbus66 30 }

mbus66Value0C		OBJECT-TYPE
			SYNTAX	INTEGER
			ACCESS	read-only
			STATUS	current
	DESCRIPTION ""
			::= { mbus66 31 }

mbus66VIF0D		OBJECT-TYPE
			SYNTAX	INTEGER
			ACCESS	read-only
			STATUS	current
	DESCRIPTION ""
			::= { mbus66 32 }

mbus66Value0D		OBJECT-TYPE
			SYNTAX	INTEGER
			ACCESS	read-only
			STATUS	current
	DESCRIPTION ""
			::= { mbus66 33 }

mbus66VIF0E		OBJECT-TYPE
			SYNTAX	INTEGER
			ACCESS	read-only
			STATUS	current
	DESCRIPTION ""
			::= { mbus66 34 }

mbus66Value0E		OBJECT-TYPE
			SYNTAX	INTEGER
			ACCESS	read-only
			STATUS	current
	DESCRIPTION ""
			::= { mbus66 35 }

mbus66VIF0F		OBJECT-TYPE
			SYNTAX	INTEGER
			ACCESS	read-only
			STATUS	current
	DESCRIPTION ""
			::= { mbus66 36 }

mbus66Value0F		OBJECT-TYPE
			SYNTAX	INTEGER
			ACCESS	read-only
			STATUS	current
	DESCRIPTION ""
			::= { mbus66 37 }

mbus66VIF10		OBJECT-TYPE
			SYNTAX	INTEGER
			ACCESS	read-only
			STATUS	current
	DESCRIPTION ""
			::= { mbus66 38 }

mbus66Value10		OBJECT-TYPE
			SYNTAX	INTEGER
			ACCESS	read-only
			STATUS	current
	DESCRIPTION ""
			::= { mbus66 39 }

mbus66VIF11		OBJECT-TYPE
			SYNTAX	INTEGER
			ACCESS	read-only
			STATUS	current
	DESCRIPTION ""
			::= { mbus66 40 }

mbus66Value11		OBJECT-TYPE
			SYNTAX	INTEGER
			ACCESS	read-only
			STATUS	current
	DESCRIPTION ""
			::= { mbus66 41 }

mbus66VIF12		OBJECT-TYPE
			SYNTAX	INTEGER
			ACCESS	read-only
			STATUS	current
	DESCRIPTION ""
			::= { mbus66 42 }

mbus66Value12		OBJECT-TYPE
			SYNTAX	INTEGER
			ACCESS	read-only
			STATUS	current
	DESCRIPTION ""
			::= { mbus66 43 }

mbus66VIF13		OBJECT-TYPE
			SYNTAX	INTEGER
			ACCESS	read-only
			STATUS	current
	DESCRIPTION ""
			::= { mbus66 44 }

mbus66Value13		OBJECT-TYPE
			SYNTAX	INTEGER
			ACCESS	read-only
			STATUS	current
	DESCRIPTION ""
			::= { mbus66 45 }

mbus66VIF14		OBJECT-TYPE
			SYNTAX	INTEGER
			ACCESS	read-only
			STATUS	current
	DESCRIPTION ""
			::= { mbus66 46 }

mbus66Value14		OBJECT-TYPE
			SYNTAX	INTEGER
			ACCESS	read-only
			STATUS	current
	DESCRIPTION ""
			::= { mbus66 47 }

mbus66VIF15		OBJECT-TYPE
			SYNTAX	INTEGER
			ACCESS	read-only
			STATUS	current
	DESCRIPTION ""
			::= { mbus66 48 }

mbus66Value15		OBJECT-TYPE
			SYNTAX	INTEGER
			ACCESS	read-only
			STATUS	current
	DESCRIPTION ""
			::= { mbus66 49 }

mbus66VIF16		OBJECT-TYPE
			SYNTAX	INTEGER
			ACCESS	read-only
			STATUS	current
	DESCRIPTION ""
			::= { mbus66 50 }

mbus66Value16		OBJECT-TYPE
			SYNTAX	INTEGER
			ACCESS	read-only
			STATUS	current
	DESCRIPTION ""
			::= { mbus66 51 }

mbus66VIF17		OBJECT-TYPE
			SYNTAX	INTEGER
			ACCESS	read-only
			STATUS	current
	DESCRIPTION ""
			::= { mbus66 52 }

mbus66Value17		OBJECT-TYPE
			SYNTAX	INTEGER
			ACCESS	read-only
			STATUS	current
	DESCRIPTION ""
			::= { mbus66 53 }

mbus66VIF18		OBJECT-TYPE
			SYNTAX	INTEGER
			ACCESS	read-only
			STATUS	current
	DESCRIPTION ""
			::= { mbus66 54 }

mbus66Value18		OBJECT-TYPE
			SYNTAX	INTEGER
			ACCESS	read-only
			STATUS	current
	DESCRIPTION ""
			::= { mbus66 55 }

mbus66VIF19		OBJECT-TYPE
			SYNTAX	INTEGER
			ACCESS	read-only
			STATUS	current
	DESCRIPTION ""
			::= { mbus66 56 }

mbus66Value19		OBJECT-TYPE
			SYNTAX	INTEGER
			ACCESS	read-only
			STATUS	current
	DESCRIPTION ""
			::= { mbus66 57 }

mbus66VIF1A		OBJECT-TYPE
			SYNTAX	INTEGER
			ACCESS	read-only
			STATUS	current
	DESCRIPTION ""
			::= { mbus66 58 }

mbus66Value1A		OBJECT-TYPE
			SYNTAX	INTEGER
			ACCESS	read-only
			STATUS	current
	DESCRIPTION ""
			::= { mbus66 59 }

mbus66VIF1B		OBJECT-TYPE
			SYNTAX	INTEGER
			ACCESS	read-only
			STATUS	current
	DESCRIPTION ""
			::= { mbus66 60 }

mbus66Value1B		OBJECT-TYPE
			SYNTAX	INTEGER
			ACCESS	read-only
			STATUS	current
	DESCRIPTION ""
			::= { mbus66 61 }

mbus66VIF1C		OBJECT-TYPE
			SYNTAX	INTEGER
			ACCESS	read-only
			STATUS	current
	DESCRIPTION ""
			::= { mbus66 62 }

mbus66Value1C		OBJECT-TYPE
			SYNTAX	INTEGER
			ACCESS	read-only
			STATUS	current
	DESCRIPTION ""
			::= { mbus66 63 }

mbus66VIF1D		OBJECT-TYPE
			SYNTAX	INTEGER
			ACCESS	read-only
			STATUS	current
	DESCRIPTION ""
			::= { mbus66 64 }

mbus66Value1D		OBJECT-TYPE
			SYNTAX	INTEGER
			ACCESS	read-only
			STATUS	current
	DESCRIPTION ""
			::= { mbus66 65 }

mbus66VIF1E		OBJECT-TYPE
			SYNTAX	INTEGER
			ACCESS	read-only
			STATUS	current
	DESCRIPTION ""
			::= { mbus66 66 }

mbus66Value1E		OBJECT-TYPE
			SYNTAX	INTEGER
			ACCESS	read-only
			STATUS	current
	DESCRIPTION ""
			::= { mbus66 67 }

mbus66VIF1F		OBJECT-TYPE
			SYNTAX	INTEGER
			ACCESS	read-only
			STATUS	current
	DESCRIPTION ""
			::= { mbus66 68 }

mbus66Value1F		OBJECT-TYPE
			SYNTAX	INTEGER
			ACCESS	read-only
			STATUS	current
	DESCRIPTION ""
			::= { mbus66 69 }

mbus66VIF20		OBJECT-TYPE
			SYNTAX	INTEGER
			ACCESS	read-only
			STATUS	current
	DESCRIPTION ""
			::= { mbus66 70 }

mbus66Value20		OBJECT-TYPE
			SYNTAX	INTEGER
			ACCESS	read-only
			STATUS	current
	DESCRIPTION ""
			::= { mbus66 71 }

mbus66VIF21		OBJECT-TYPE
			SYNTAX	INTEGER
			ACCESS	read-only
			STATUS	current
	DESCRIPTION ""
			::= { mbus66 72 }

mbus66Value21		OBJECT-TYPE
			SYNTAX	INTEGER
			ACCESS	read-only
			STATUS	current
	DESCRIPTION ""
			::= { mbus66 73 }

mbus66VIF22		OBJECT-TYPE
			SYNTAX	INTEGER
			ACCESS	read-only
			STATUS	current
	DESCRIPTION ""
			::= { mbus66 74 }

mbus66Value22		OBJECT-TYPE
			SYNTAX	INTEGER
			ACCESS	read-only
			STATUS	current
	DESCRIPTION ""
			::= { mbus66 75 }

mbus66VIF23		OBJECT-TYPE
			SYNTAX	INTEGER
			ACCESS	read-only
			STATUS	current
	DESCRIPTION ""
			::= { mbus66 76 }

mbus66Value23		OBJECT-TYPE
			SYNTAX	INTEGER
			ACCESS	read-only
			STATUS	current
	DESCRIPTION ""
			::= { mbus66 77 }

mbus66VIF24		OBJECT-TYPE
			SYNTAX	INTEGER
			ACCESS	read-only
			STATUS	current
	DESCRIPTION ""
			::= { mbus66 78 }

mbus66Value24		OBJECT-TYPE
			SYNTAX	INTEGER
			ACCESS	read-only
			STATUS	current
	DESCRIPTION ""
			::= { mbus66 79 }

mbus66VIF25		OBJECT-TYPE
			SYNTAX	INTEGER
			ACCESS	read-only
			STATUS	current
	DESCRIPTION ""
			::= { mbus66 80 }

mbus66Value25		OBJECT-TYPE
			SYNTAX	INTEGER
			ACCESS	read-only
			STATUS	current
	DESCRIPTION ""
			::= { mbus66 81 }

mbus66VIF26		OBJECT-TYPE
			SYNTAX	INTEGER
			ACCESS	read-only
			STATUS	current
	DESCRIPTION ""
			::= { mbus66 82 }

mbus66Value26		OBJECT-TYPE
			SYNTAX	INTEGER
			ACCESS	read-only
			STATUS	current
	DESCRIPTION ""
			::= { mbus66 83 }

mbus66VIF27		OBJECT-TYPE
			SYNTAX	INTEGER
			ACCESS	read-only
			STATUS	current
	DESCRIPTION ""
			::= { mbus66 84 }

mbus66Value27		OBJECT-TYPE
			SYNTAX	INTEGER
			ACCESS	read-only
			STATUS	current
	DESCRIPTION ""
			::= { mbus66 85 }

mbus66VIF28		OBJECT-TYPE
			SYNTAX	INTEGER
			ACCESS	read-only
			STATUS	current
	DESCRIPTION ""
			::= { mbus66 86 }

mbus66Value28		OBJECT-TYPE
			SYNTAX	INTEGER
			ACCESS	read-only
			STATUS	current
	DESCRIPTION ""
			::= { mbus66 87 }

mbus66VIF29		OBJECT-TYPE
			SYNTAX	INTEGER
			ACCESS	read-only
			STATUS	current
	DESCRIPTION ""
			::= { mbus66 88 }

mbus66Value29		OBJECT-TYPE
			SYNTAX	INTEGER
			ACCESS	read-only
			STATUS	current
	DESCRIPTION ""
			::= { mbus66 89 }

mbus66VIF2A		OBJECT-TYPE
			SYNTAX	INTEGER
			ACCESS	read-only
			STATUS	current
	DESCRIPTION ""
			::= { mbus66 90 }

mbus66Value2A		OBJECT-TYPE
			SYNTAX	INTEGER
			ACCESS	read-only
			STATUS	current
	DESCRIPTION ""
			::= { mbus66 91 }

mbus66VIF2B		OBJECT-TYPE
			SYNTAX	INTEGER
			ACCESS	read-only
			STATUS	current
	DESCRIPTION ""
			::= { mbus66 92 }

mbus66Value2B		OBJECT-TYPE
			SYNTAX	INTEGER
			ACCESS	read-only
			STATUS	current
	DESCRIPTION ""
			::= { mbus66 93 }

mbus66VIF2C		OBJECT-TYPE
			SYNTAX	INTEGER
			ACCESS	read-only
			STATUS	current
	DESCRIPTION ""
			::= { mbus66 94 }

mbus66Value2C		OBJECT-TYPE
			SYNTAX	INTEGER
			ACCESS	read-only
			STATUS	current
	DESCRIPTION ""
			::= { mbus66 95 }

mbus66VIF2D		OBJECT-TYPE
			SYNTAX	INTEGER
			ACCESS	read-only
			STATUS	current
	DESCRIPTION ""
			::= { mbus66 96 }

mbus66Value2D		OBJECT-TYPE
			SYNTAX	INTEGER
			ACCESS	read-only
			STATUS	current
	DESCRIPTION ""
			::= { mbus66 97 }

mbus66VIF2E		OBJECT-TYPE
			SYNTAX	INTEGER
			ACCESS	read-only
			STATUS	current
	DESCRIPTION ""
			::= { mbus66 98 }

mbus66Value2E		OBJECT-TYPE
			SYNTAX	INTEGER
			ACCESS	read-only
			STATUS	current
	DESCRIPTION ""
			::= { mbus66 99 }

mbus66VIF2F		OBJECT-TYPE
			SYNTAX	INTEGER
			ACCESS	read-only
			STATUS	current
	DESCRIPTION ""
			::= { mbus66 100 }

mbus66Value2F		OBJECT-TYPE
			SYNTAX	INTEGER
			ACCESS	read-only
			STATUS	current
	DESCRIPTION ""
			::= { mbus66 101 }

mbus67			OBJECT IDENTIFIER ::= { mbus 103 }

mbus67IdNumber		OBJECT-TYPE
			SYNTAX	Gauge
			ACCESS	read-only
			STATUS	current
	DESCRIPTION ""
			::= { mbus67 1 }

mbus67Manufacturer	OBJECT-TYPE
			SYNTAX	Gauge
			ACCESS	read-only
			STATUS	current
	DESCRIPTION ""
			::= { mbus67 2 }

mbus67Version		OBJECT-TYPE
			SYNTAX	Gauge
			ACCESS	read-only
			STATUS	current
	DESCRIPTION ""
			::= { mbus67 3 }

mbus67Medium		OBJECT-TYPE
			SYNTAX	Gauge
			ACCESS	read-only
			STATUS	current
	DESCRIPTION ""
			::= { mbus67 4 }

mbus67Status		OBJECT-TYPE
			SYNTAX	Gauge
			ACCESS	read-only
			STATUS	current
	DESCRIPTION ""
			::= { mbus67 5 }

mbus67VIF00		OBJECT-TYPE
			SYNTAX	INTEGER
			ACCESS	read-only
			STATUS	current
	DESCRIPTION ""
			::= { mbus67 6 }

mbus67Value00		OBJECT-TYPE
			SYNTAX	INTEGER
			ACCESS	read-only
			STATUS	current
	DESCRIPTION ""
			::= { mbus67 7 }

mbus67VIF01		OBJECT-TYPE
			SYNTAX	INTEGER
			ACCESS	read-only
			STATUS	current
	DESCRIPTION ""
			::= { mbus67 8 }

mbus67Value01		OBJECT-TYPE
			SYNTAX	INTEGER
			ACCESS	read-only
			STATUS	current
	DESCRIPTION ""
			::= { mbus67 9 }

mbus67VIF02		OBJECT-TYPE
			SYNTAX	INTEGER
			ACCESS	read-only
			STATUS	current
	DESCRIPTION ""
			::= { mbus67 10 }

mbus67Value02		OBJECT-TYPE
			SYNTAX	INTEGER
			ACCESS	read-only
			STATUS	current
	DESCRIPTION ""
			::= { mbus67 11 }

mbus67VIF03		OBJECT-TYPE
			SYNTAX	INTEGER
			ACCESS	read-only
			STATUS	current
	DESCRIPTION ""
			::= { mbus67 12 }

mbus67Value03		OBJECT-TYPE
			SYNTAX	INTEGER
			ACCESS	read-only
			STATUS	current
	DESCRIPTION ""
			::= { mbus67 13 }

mbus67VIF04		OBJECT-TYPE
			SYNTAX	INTEGER
			ACCESS	read-only
			STATUS	current
	DESCRIPTION ""
			::= { mbus67 14 }

mbus67Value04		OBJECT-TYPE
			SYNTAX	INTEGER
			ACCESS	read-only
			STATUS	current
	DESCRIPTION ""
			::= { mbus67 15 }

mbus67VIF05		OBJECT-TYPE
			SYNTAX	INTEGER
			ACCESS	read-only
			STATUS	current
	DESCRIPTION ""
			::= { mbus67 16 }

mbus67Value05		OBJECT-TYPE
			SYNTAX	INTEGER
			ACCESS	read-only
			STATUS	current
	DESCRIPTION ""
			::= { mbus67 17 }

mbus67VIF06		OBJECT-TYPE
			SYNTAX	INTEGER
			ACCESS	read-only
			STATUS	current
	DESCRIPTION ""
			::= { mbus67 18 }

mbus67Value06		OBJECT-TYPE
			SYNTAX	INTEGER
			ACCESS	read-only
			STATUS	current
	DESCRIPTION ""
			::= { mbus67 19 }

mbus67VIF07		OBJECT-TYPE
			SYNTAX	INTEGER
			ACCESS	read-only
			STATUS	current
	DESCRIPTION ""
			::= { mbus67 20 }

mbus67Value07		OBJECT-TYPE
			SYNTAX	INTEGER
			ACCESS	read-only
			STATUS	current
	DESCRIPTION ""
			::= { mbus67 21 }

mbus67VIF08		OBJECT-TYPE
			SYNTAX	INTEGER
			ACCESS	read-only
			STATUS	current
	DESCRIPTION ""
			::= { mbus67 22 }

mbus67Value08		OBJECT-TYPE
			SYNTAX	INTEGER
			ACCESS	read-only
			STATUS	current
	DESCRIPTION ""
			::= { mbus67 23 }

mbus67VIF09		OBJECT-TYPE
			SYNTAX	INTEGER
			ACCESS	read-only
			STATUS	current
	DESCRIPTION ""
			::= { mbus67 24 }

mbus67Value09		OBJECT-TYPE
			SYNTAX	INTEGER
			ACCESS	read-only
			STATUS	current
	DESCRIPTION ""
			::= { mbus67 25 }

mbus67VIF0A		OBJECT-TYPE
			SYNTAX	INTEGER
			ACCESS	read-only
			STATUS	current
	DESCRIPTION ""
			::= { mbus67 26 }

mbus67Value0A		OBJECT-TYPE
			SYNTAX	INTEGER
			ACCESS	read-only
			STATUS	current
	DESCRIPTION ""
			::= { mbus67 27 }

mbus67VIF0B		OBJECT-TYPE
			SYNTAX	INTEGER
			ACCESS	read-only
			STATUS	current
	DESCRIPTION ""
			::= { mbus67 28 }

mbus67Value0B		OBJECT-TYPE
			SYNTAX	INTEGER
			ACCESS	read-only
			STATUS	current
	DESCRIPTION ""
			::= { mbus67 29 }

mbus67VIF0C		OBJECT-TYPE
			SYNTAX	INTEGER
			ACCESS	read-only
			STATUS	current
	DESCRIPTION ""
			::= { mbus67 30 }

mbus67Value0C		OBJECT-TYPE
			SYNTAX	INTEGER
			ACCESS	read-only
			STATUS	current
	DESCRIPTION ""
			::= { mbus67 31 }

mbus67VIF0D		OBJECT-TYPE
			SYNTAX	INTEGER
			ACCESS	read-only
			STATUS	current
	DESCRIPTION ""
			::= { mbus67 32 }

mbus67Value0D		OBJECT-TYPE
			SYNTAX	INTEGER
			ACCESS	read-only
			STATUS	current
	DESCRIPTION ""
			::= { mbus67 33 }

mbus67VIF0E		OBJECT-TYPE
			SYNTAX	INTEGER
			ACCESS	read-only
			STATUS	current
	DESCRIPTION ""
			::= { mbus67 34 }

mbus67Value0E		OBJECT-TYPE
			SYNTAX	INTEGER
			ACCESS	read-only
			STATUS	current
	DESCRIPTION ""
			::= { mbus67 35 }

mbus67VIF0F		OBJECT-TYPE
			SYNTAX	INTEGER
			ACCESS	read-only
			STATUS	current
	DESCRIPTION ""
			::= { mbus67 36 }

mbus67Value0F		OBJECT-TYPE
			SYNTAX	INTEGER
			ACCESS	read-only
			STATUS	current
	DESCRIPTION ""
			::= { mbus67 37 }

mbus67VIF10		OBJECT-TYPE
			SYNTAX	INTEGER
			ACCESS	read-only
			STATUS	current
	DESCRIPTION ""
			::= { mbus67 38 }

mbus67Value10		OBJECT-TYPE
			SYNTAX	INTEGER
			ACCESS	read-only
			STATUS	current
	DESCRIPTION ""
			::= { mbus67 39 }

mbus67VIF11		OBJECT-TYPE
			SYNTAX	INTEGER
			ACCESS	read-only
			STATUS	current
	DESCRIPTION ""
			::= { mbus67 40 }

mbus67Value11		OBJECT-TYPE
			SYNTAX	INTEGER
			ACCESS	read-only
			STATUS	current
	DESCRIPTION ""
			::= { mbus67 41 }

mbus67VIF12		OBJECT-TYPE
			SYNTAX	INTEGER
			ACCESS	read-only
			STATUS	current
	DESCRIPTION ""
			::= { mbus67 42 }

mbus67Value12		OBJECT-TYPE
			SYNTAX	INTEGER
			ACCESS	read-only
			STATUS	current
	DESCRIPTION ""
			::= { mbus67 43 }

mbus67VIF13		OBJECT-TYPE
			SYNTAX	INTEGER
			ACCESS	read-only
			STATUS	current
	DESCRIPTION ""
			::= { mbus67 44 }

mbus67Value13		OBJECT-TYPE
			SYNTAX	INTEGER
			ACCESS	read-only
			STATUS	current
	DESCRIPTION ""
			::= { mbus67 45 }

mbus67VIF14		OBJECT-TYPE
			SYNTAX	INTEGER
			ACCESS	read-only
			STATUS	current
	DESCRIPTION ""
			::= { mbus67 46 }

mbus67Value14		OBJECT-TYPE
			SYNTAX	INTEGER
			ACCESS	read-only
			STATUS	current
	DESCRIPTION ""
			::= { mbus67 47 }

mbus67VIF15		OBJECT-TYPE
			SYNTAX	INTEGER
			ACCESS	read-only
			STATUS	current
	DESCRIPTION ""
			::= { mbus67 48 }

mbus67Value15		OBJECT-TYPE
			SYNTAX	INTEGER
			ACCESS	read-only
			STATUS	current
	DESCRIPTION ""
			::= { mbus67 49 }

mbus67VIF16		OBJECT-TYPE
			SYNTAX	INTEGER
			ACCESS	read-only
			STATUS	current
	DESCRIPTION ""
			::= { mbus67 50 }

mbus67Value16		OBJECT-TYPE
			SYNTAX	INTEGER
			ACCESS	read-only
			STATUS	current
	DESCRIPTION ""
			::= { mbus67 51 }

mbus67VIF17		OBJECT-TYPE
			SYNTAX	INTEGER
			ACCESS	read-only
			STATUS	current
	DESCRIPTION ""
			::= { mbus67 52 }

mbus67Value17		OBJECT-TYPE
			SYNTAX	INTEGER
			ACCESS	read-only
			STATUS	current
	DESCRIPTION ""
			::= { mbus67 53 }

mbus67VIF18		OBJECT-TYPE
			SYNTAX	INTEGER
			ACCESS	read-only
			STATUS	current
	DESCRIPTION ""
			::= { mbus67 54 }

mbus67Value18		OBJECT-TYPE
			SYNTAX	INTEGER
			ACCESS	read-only
			STATUS	current
	DESCRIPTION ""
			::= { mbus67 55 }

mbus67VIF19		OBJECT-TYPE
			SYNTAX	INTEGER
			ACCESS	read-only
			STATUS	current
	DESCRIPTION ""
			::= { mbus67 56 }

mbus67Value19		OBJECT-TYPE
			SYNTAX	INTEGER
			ACCESS	read-only
			STATUS	current
	DESCRIPTION ""
			::= { mbus67 57 }

mbus67VIF1A		OBJECT-TYPE
			SYNTAX	INTEGER
			ACCESS	read-only
			STATUS	current
	DESCRIPTION ""
			::= { mbus67 58 }

mbus67Value1A		OBJECT-TYPE
			SYNTAX	INTEGER
			ACCESS	read-only
			STATUS	current
	DESCRIPTION ""
			::= { mbus67 59 }

mbus67VIF1B		OBJECT-TYPE
			SYNTAX	INTEGER
			ACCESS	read-only
			STATUS	current
	DESCRIPTION ""
			::= { mbus67 60 }

mbus67Value1B		OBJECT-TYPE
			SYNTAX	INTEGER
			ACCESS	read-only
			STATUS	current
	DESCRIPTION ""
			::= { mbus67 61 }

mbus67VIF1C		OBJECT-TYPE
			SYNTAX	INTEGER
			ACCESS	read-only
			STATUS	current
	DESCRIPTION ""
			::= { mbus67 62 }

mbus67Value1C		OBJECT-TYPE
			SYNTAX	INTEGER
			ACCESS	read-only
			STATUS	current
	DESCRIPTION ""
			::= { mbus67 63 }

mbus67VIF1D		OBJECT-TYPE
			SYNTAX	INTEGER
			ACCESS	read-only
			STATUS	current
	DESCRIPTION ""
			::= { mbus67 64 }

mbus67Value1D		OBJECT-TYPE
			SYNTAX	INTEGER
			ACCESS	read-only
			STATUS	current
	DESCRIPTION ""
			::= { mbus67 65 }

mbus67VIF1E		OBJECT-TYPE
			SYNTAX	INTEGER
			ACCESS	read-only
			STATUS	current
	DESCRIPTION ""
			::= { mbus67 66 }

mbus67Value1E		OBJECT-TYPE
			SYNTAX	INTEGER
			ACCESS	read-only
			STATUS	current
	DESCRIPTION ""
			::= { mbus67 67 }

mbus67VIF1F		OBJECT-TYPE
			SYNTAX	INTEGER
			ACCESS	read-only
			STATUS	current
	DESCRIPTION ""
			::= { mbus67 68 }

mbus67Value1F		OBJECT-TYPE
			SYNTAX	INTEGER
			ACCESS	read-only
			STATUS	current
	DESCRIPTION ""
			::= { mbus67 69 }

mbus67VIF20		OBJECT-TYPE
			SYNTAX	INTEGER
			ACCESS	read-only
			STATUS	current
	DESCRIPTION ""
			::= { mbus67 70 }

mbus67Value20		OBJECT-TYPE
			SYNTAX	INTEGER
			ACCESS	read-only
			STATUS	current
	DESCRIPTION ""
			::= { mbus67 71 }

mbus67VIF21		OBJECT-TYPE
			SYNTAX	INTEGER
			ACCESS	read-only
			STATUS	current
	DESCRIPTION ""
			::= { mbus67 72 }

mbus67Value21		OBJECT-TYPE
			SYNTAX	INTEGER
			ACCESS	read-only
			STATUS	current
	DESCRIPTION ""
			::= { mbus67 73 }

mbus67VIF22		OBJECT-TYPE
			SYNTAX	INTEGER
			ACCESS	read-only
			STATUS	current
	DESCRIPTION ""
			::= { mbus67 74 }

mbus67Value22		OBJECT-TYPE
			SYNTAX	INTEGER
			ACCESS	read-only
			STATUS	current
	DESCRIPTION ""
			::= { mbus67 75 }

mbus67VIF23		OBJECT-TYPE
			SYNTAX	INTEGER
			ACCESS	read-only
			STATUS	current
	DESCRIPTION ""
			::= { mbus67 76 }

mbus67Value23		OBJECT-TYPE
			SYNTAX	INTEGER
			ACCESS	read-only
			STATUS	current
	DESCRIPTION ""
			::= { mbus67 77 }

mbus67VIF24		OBJECT-TYPE
			SYNTAX	INTEGER
			ACCESS	read-only
			STATUS	current
	DESCRIPTION ""
			::= { mbus67 78 }

mbus67Value24		OBJECT-TYPE
			SYNTAX	INTEGER
			ACCESS	read-only
			STATUS	current
	DESCRIPTION ""
			::= { mbus67 79 }

mbus67VIF25		OBJECT-TYPE
			SYNTAX	INTEGER
			ACCESS	read-only
			STATUS	current
	DESCRIPTION ""
			::= { mbus67 80 }

mbus67Value25		OBJECT-TYPE
			SYNTAX	INTEGER
			ACCESS	read-only
			STATUS	current
	DESCRIPTION ""
			::= { mbus67 81 }

mbus67VIF26		OBJECT-TYPE
			SYNTAX	INTEGER
			ACCESS	read-only
			STATUS	current
	DESCRIPTION ""
			::= { mbus67 82 }

mbus67Value26		OBJECT-TYPE
			SYNTAX	INTEGER
			ACCESS	read-only
			STATUS	current
	DESCRIPTION ""
			::= { mbus67 83 }

mbus67VIF27		OBJECT-TYPE
			SYNTAX	INTEGER
			ACCESS	read-only
			STATUS	current
	DESCRIPTION ""
			::= { mbus67 84 }

mbus67Value27		OBJECT-TYPE
			SYNTAX	INTEGER
			ACCESS	read-only
			STATUS	current
	DESCRIPTION ""
			::= { mbus67 85 }

mbus67VIF28		OBJECT-TYPE
			SYNTAX	INTEGER
			ACCESS	read-only
			STATUS	current
	DESCRIPTION ""
			::= { mbus67 86 }

mbus67Value28		OBJECT-TYPE
			SYNTAX	INTEGER
			ACCESS	read-only
			STATUS	current
	DESCRIPTION ""
			::= { mbus67 87 }

mbus67VIF29		OBJECT-TYPE
			SYNTAX	INTEGER
			ACCESS	read-only
			STATUS	current
	DESCRIPTION ""
			::= { mbus67 88 }

mbus67Value29		OBJECT-TYPE
			SYNTAX	INTEGER
			ACCESS	read-only
			STATUS	current
	DESCRIPTION ""
			::= { mbus67 89 }

mbus67VIF2A		OBJECT-TYPE
			SYNTAX	INTEGER
			ACCESS	read-only
			STATUS	current
	DESCRIPTION ""
			::= { mbus67 90 }

mbus67Value2A		OBJECT-TYPE
			SYNTAX	INTEGER
			ACCESS	read-only
			STATUS	current
	DESCRIPTION ""
			::= { mbus67 91 }

mbus67VIF2B		OBJECT-TYPE
			SYNTAX	INTEGER
			ACCESS	read-only
			STATUS	current
	DESCRIPTION ""
			::= { mbus67 92 }

mbus67Value2B		OBJECT-TYPE
			SYNTAX	INTEGER
			ACCESS	read-only
			STATUS	current
	DESCRIPTION ""
			::= { mbus67 93 }

mbus67VIF2C		OBJECT-TYPE
			SYNTAX	INTEGER
			ACCESS	read-only
			STATUS	current
	DESCRIPTION ""
			::= { mbus67 94 }

mbus67Value2C		OBJECT-TYPE
			SYNTAX	INTEGER
			ACCESS	read-only
			STATUS	current
	DESCRIPTION ""
			::= { mbus67 95 }

mbus67VIF2D		OBJECT-TYPE
			SYNTAX	INTEGER
			ACCESS	read-only
			STATUS	current
	DESCRIPTION ""
			::= { mbus67 96 }

mbus67Value2D		OBJECT-TYPE
			SYNTAX	INTEGER
			ACCESS	read-only
			STATUS	current
	DESCRIPTION ""
			::= { mbus67 97 }

mbus67VIF2E		OBJECT-TYPE
			SYNTAX	INTEGER
			ACCESS	read-only
			STATUS	current
	DESCRIPTION ""
			::= { mbus67 98 }

mbus67Value2E		OBJECT-TYPE
			SYNTAX	INTEGER
			ACCESS	read-only
			STATUS	current
	DESCRIPTION ""
			::= { mbus67 99 }

mbus67VIF2F		OBJECT-TYPE
			SYNTAX	INTEGER
			ACCESS	read-only
			STATUS	current
	DESCRIPTION ""
			::= { mbus67 100 }

mbus67Value2F		OBJECT-TYPE
			SYNTAX	INTEGER
			ACCESS	read-only
			STATUS	current
	DESCRIPTION ""
			::= { mbus67 101 }

mbus68			OBJECT IDENTIFIER ::= { mbus 104 }

mbus68IdNumber		OBJECT-TYPE
			SYNTAX	Gauge
			ACCESS	read-only
			STATUS	current
	DESCRIPTION ""
			::= { mbus68 1 }

mbus68Manufacturer	OBJECT-TYPE
			SYNTAX	Gauge
			ACCESS	read-only
			STATUS	current
	DESCRIPTION ""
			::= { mbus68 2 }

mbus68Version		OBJECT-TYPE
			SYNTAX	Gauge
			ACCESS	read-only
			STATUS	current
	DESCRIPTION ""
			::= { mbus68 3 }

mbus68Medium		OBJECT-TYPE
			SYNTAX	Gauge
			ACCESS	read-only
			STATUS	current
	DESCRIPTION ""
			::= { mbus68 4 }

mbus68Status		OBJECT-TYPE
			SYNTAX	Gauge
			ACCESS	read-only
			STATUS	current
	DESCRIPTION ""
			::= { mbus68 5 }

mbus68VIF00		OBJECT-TYPE
			SYNTAX	INTEGER
			ACCESS	read-only
			STATUS	current
	DESCRIPTION ""
			::= { mbus68 6 }

mbus68Value00		OBJECT-TYPE
			SYNTAX	INTEGER
			ACCESS	read-only
			STATUS	current
	DESCRIPTION ""
			::= { mbus68 7 }

mbus68VIF01		OBJECT-TYPE
			SYNTAX	INTEGER
			ACCESS	read-only
			STATUS	current
	DESCRIPTION ""
			::= { mbus68 8 }

mbus68Value01		OBJECT-TYPE
			SYNTAX	INTEGER
			ACCESS	read-only
			STATUS	current
	DESCRIPTION ""
			::= { mbus68 9 }

mbus68VIF02		OBJECT-TYPE
			SYNTAX	INTEGER
			ACCESS	read-only
			STATUS	current
	DESCRIPTION ""
			::= { mbus68 10 }

mbus68Value02		OBJECT-TYPE
			SYNTAX	INTEGER
			ACCESS	read-only
			STATUS	current
	DESCRIPTION ""
			::= { mbus68 11 }

mbus68VIF03		OBJECT-TYPE
			SYNTAX	INTEGER
			ACCESS	read-only
			STATUS	current
	DESCRIPTION ""
			::= { mbus68 12 }

mbus68Value03		OBJECT-TYPE
			SYNTAX	INTEGER
			ACCESS	read-only
			STATUS	current
	DESCRIPTION ""
			::= { mbus68 13 }

mbus68VIF04		OBJECT-TYPE
			SYNTAX	INTEGER
			ACCESS	read-only
			STATUS	current
	DESCRIPTION ""
			::= { mbus68 14 }

mbus68Value04		OBJECT-TYPE
			SYNTAX	INTEGER
			ACCESS	read-only
			STATUS	current
	DESCRIPTION ""
			::= { mbus68 15 }

mbus68VIF05		OBJECT-TYPE
			SYNTAX	INTEGER
			ACCESS	read-only
			STATUS	current
	DESCRIPTION ""
			::= { mbus68 16 }

mbus68Value05		OBJECT-TYPE
			SYNTAX	INTEGER
			ACCESS	read-only
			STATUS	current
	DESCRIPTION ""
			::= { mbus68 17 }

mbus68VIF06		OBJECT-TYPE
			SYNTAX	INTEGER
			ACCESS	read-only
			STATUS	current
	DESCRIPTION ""
			::= { mbus68 18 }

mbus68Value06		OBJECT-TYPE
			SYNTAX	INTEGER
			ACCESS	read-only
			STATUS	current
	DESCRIPTION ""
			::= { mbus68 19 }

mbus68VIF07		OBJECT-TYPE
			SYNTAX	INTEGER
			ACCESS	read-only
			STATUS	current
	DESCRIPTION ""
			::= { mbus68 20 }

mbus68Value07		OBJECT-TYPE
			SYNTAX	INTEGER
			ACCESS	read-only
			STATUS	current
	DESCRIPTION ""
			::= { mbus68 21 }

mbus68VIF08		OBJECT-TYPE
			SYNTAX	INTEGER
			ACCESS	read-only
			STATUS	current
	DESCRIPTION ""
			::= { mbus68 22 }

mbus68Value08		OBJECT-TYPE
			SYNTAX	INTEGER
			ACCESS	read-only
			STATUS	current
	DESCRIPTION ""
			::= { mbus68 23 }

mbus68VIF09		OBJECT-TYPE
			SYNTAX	INTEGER
			ACCESS	read-only
			STATUS	current
	DESCRIPTION ""
			::= { mbus68 24 }

mbus68Value09		OBJECT-TYPE
			SYNTAX	INTEGER
			ACCESS	read-only
			STATUS	current
	DESCRIPTION ""
			::= { mbus68 25 }

mbus68VIF0A		OBJECT-TYPE
			SYNTAX	INTEGER
			ACCESS	read-only
			STATUS	current
	DESCRIPTION ""
			::= { mbus68 26 }

mbus68Value0A		OBJECT-TYPE
			SYNTAX	INTEGER
			ACCESS	read-only
			STATUS	current
	DESCRIPTION ""
			::= { mbus68 27 }

mbus68VIF0B		OBJECT-TYPE
			SYNTAX	INTEGER
			ACCESS	read-only
			STATUS	current
	DESCRIPTION ""
			::= { mbus68 28 }

mbus68Value0B		OBJECT-TYPE
			SYNTAX	INTEGER
			ACCESS	read-only
			STATUS	current
	DESCRIPTION ""
			::= { mbus68 29 }

mbus68VIF0C		OBJECT-TYPE
			SYNTAX	INTEGER
			ACCESS	read-only
			STATUS	current
	DESCRIPTION ""
			::= { mbus68 30 }

mbus68Value0C		OBJECT-TYPE
			SYNTAX	INTEGER
			ACCESS	read-only
			STATUS	current
	DESCRIPTION ""
			::= { mbus68 31 }

mbus68VIF0D		OBJECT-TYPE
			SYNTAX	INTEGER
			ACCESS	read-only
			STATUS	current
	DESCRIPTION ""
			::= { mbus68 32 }

mbus68Value0D		OBJECT-TYPE
			SYNTAX	INTEGER
			ACCESS	read-only
			STATUS	current
	DESCRIPTION ""
			::= { mbus68 33 }

mbus68VIF0E		OBJECT-TYPE
			SYNTAX	INTEGER
			ACCESS	read-only
			STATUS	current
	DESCRIPTION ""
			::= { mbus68 34 }

mbus68Value0E		OBJECT-TYPE
			SYNTAX	INTEGER
			ACCESS	read-only
			STATUS	current
	DESCRIPTION ""
			::= { mbus68 35 }

mbus68VIF0F		OBJECT-TYPE
			SYNTAX	INTEGER
			ACCESS	read-only
			STATUS	current
	DESCRIPTION ""
			::= { mbus68 36 }

mbus68Value0F		OBJECT-TYPE
			SYNTAX	INTEGER
			ACCESS	read-only
			STATUS	current
	DESCRIPTION ""
			::= { mbus68 37 }

mbus68VIF10		OBJECT-TYPE
			SYNTAX	INTEGER
			ACCESS	read-only
			STATUS	current
	DESCRIPTION ""
			::= { mbus68 38 }

mbus68Value10		OBJECT-TYPE
			SYNTAX	INTEGER
			ACCESS	read-only
			STATUS	current
	DESCRIPTION ""
			::= { mbus68 39 }

mbus68VIF11		OBJECT-TYPE
			SYNTAX	INTEGER
			ACCESS	read-only
			STATUS	current
	DESCRIPTION ""
			::= { mbus68 40 }

mbus68Value11		OBJECT-TYPE
			SYNTAX	INTEGER
			ACCESS	read-only
			STATUS	current
	DESCRIPTION ""
			::= { mbus68 41 }

mbus68VIF12		OBJECT-TYPE
			SYNTAX	INTEGER
			ACCESS	read-only
			STATUS	current
	DESCRIPTION ""
			::= { mbus68 42 }

mbus68Value12		OBJECT-TYPE
			SYNTAX	INTEGER
			ACCESS	read-only
			STATUS	current
	DESCRIPTION ""
			::= { mbus68 43 }

mbus68VIF13		OBJECT-TYPE
			SYNTAX	INTEGER
			ACCESS	read-only
			STATUS	current
	DESCRIPTION ""
			::= { mbus68 44 }

mbus68Value13		OBJECT-TYPE
			SYNTAX	INTEGER
			ACCESS	read-only
			STATUS	current
	DESCRIPTION ""
			::= { mbus68 45 }

mbus68VIF14		OBJECT-TYPE
			SYNTAX	INTEGER
			ACCESS	read-only
			STATUS	current
	DESCRIPTION ""
			::= { mbus68 46 }

mbus68Value14		OBJECT-TYPE
			SYNTAX	INTEGER
			ACCESS	read-only
			STATUS	current
	DESCRIPTION ""
			::= { mbus68 47 }

mbus68VIF15		OBJECT-TYPE
			SYNTAX	INTEGER
			ACCESS	read-only
			STATUS	current
	DESCRIPTION ""
			::= { mbus68 48 }

mbus68Value15		OBJECT-TYPE
			SYNTAX	INTEGER
			ACCESS	read-only
			STATUS	current
	DESCRIPTION ""
			::= { mbus68 49 }

mbus68VIF16		OBJECT-TYPE
			SYNTAX	INTEGER
			ACCESS	read-only
			STATUS	current
	DESCRIPTION ""
			::= { mbus68 50 }

mbus68Value16		OBJECT-TYPE
			SYNTAX	INTEGER
			ACCESS	read-only
			STATUS	current
	DESCRIPTION ""
			::= { mbus68 51 }

mbus68VIF17		OBJECT-TYPE
			SYNTAX	INTEGER
			ACCESS	read-only
			STATUS	current
	DESCRIPTION ""
			::= { mbus68 52 }

mbus68Value17		OBJECT-TYPE
			SYNTAX	INTEGER
			ACCESS	read-only
			STATUS	current
	DESCRIPTION ""
			::= { mbus68 53 }

mbus68VIF18		OBJECT-TYPE
			SYNTAX	INTEGER
			ACCESS	read-only
			STATUS	current
	DESCRIPTION ""
			::= { mbus68 54 }

mbus68Value18		OBJECT-TYPE
			SYNTAX	INTEGER
			ACCESS	read-only
			STATUS	current
	DESCRIPTION ""
			::= { mbus68 55 }

mbus68VIF19		OBJECT-TYPE
			SYNTAX	INTEGER
			ACCESS	read-only
			STATUS	current
	DESCRIPTION ""
			::= { mbus68 56 }

mbus68Value19		OBJECT-TYPE
			SYNTAX	INTEGER
			ACCESS	read-only
			STATUS	current
	DESCRIPTION ""
			::= { mbus68 57 }

mbus68VIF1A		OBJECT-TYPE
			SYNTAX	INTEGER
			ACCESS	read-only
			STATUS	current
	DESCRIPTION ""
			::= { mbus68 58 }

mbus68Value1A		OBJECT-TYPE
			SYNTAX	INTEGER
			ACCESS	read-only
			STATUS	current
	DESCRIPTION ""
			::= { mbus68 59 }

mbus68VIF1B		OBJECT-TYPE
			SYNTAX	INTEGER
			ACCESS	read-only
			STATUS	current
	DESCRIPTION ""
			::= { mbus68 60 }

mbus68Value1B		OBJECT-TYPE
			SYNTAX	INTEGER
			ACCESS	read-only
			STATUS	current
	DESCRIPTION ""
			::= { mbus68 61 }

mbus68VIF1C		OBJECT-TYPE
			SYNTAX	INTEGER
			ACCESS	read-only
			STATUS	current
	DESCRIPTION ""
			::= { mbus68 62 }

mbus68Value1C		OBJECT-TYPE
			SYNTAX	INTEGER
			ACCESS	read-only
			STATUS	current
	DESCRIPTION ""
			::= { mbus68 63 }

mbus68VIF1D		OBJECT-TYPE
			SYNTAX	INTEGER
			ACCESS	read-only
			STATUS	current
	DESCRIPTION ""
			::= { mbus68 64 }

mbus68Value1D		OBJECT-TYPE
			SYNTAX	INTEGER
			ACCESS	read-only
			STATUS	current
	DESCRIPTION ""
			::= { mbus68 65 }

mbus68VIF1E		OBJECT-TYPE
			SYNTAX	INTEGER
			ACCESS	read-only
			STATUS	current
	DESCRIPTION ""
			::= { mbus68 66 }

mbus68Value1E		OBJECT-TYPE
			SYNTAX	INTEGER
			ACCESS	read-only
			STATUS	current
	DESCRIPTION ""
			::= { mbus68 67 }

mbus68VIF1F		OBJECT-TYPE
			SYNTAX	INTEGER
			ACCESS	read-only
			STATUS	current
	DESCRIPTION ""
			::= { mbus68 68 }

mbus68Value1F		OBJECT-TYPE
			SYNTAX	INTEGER
			ACCESS	read-only
			STATUS	current
	DESCRIPTION ""
			::= { mbus68 69 }

mbus68VIF20		OBJECT-TYPE
			SYNTAX	INTEGER
			ACCESS	read-only
			STATUS	current
	DESCRIPTION ""
			::= { mbus68 70 }

mbus68Value20		OBJECT-TYPE
			SYNTAX	INTEGER
			ACCESS	read-only
			STATUS	current
	DESCRIPTION ""
			::= { mbus68 71 }

mbus68VIF21		OBJECT-TYPE
			SYNTAX	INTEGER
			ACCESS	read-only
			STATUS	current
	DESCRIPTION ""
			::= { mbus68 72 }

mbus68Value21		OBJECT-TYPE
			SYNTAX	INTEGER
			ACCESS	read-only
			STATUS	current
	DESCRIPTION ""
			::= { mbus68 73 }

mbus68VIF22		OBJECT-TYPE
			SYNTAX	INTEGER
			ACCESS	read-only
			STATUS	current
	DESCRIPTION ""
			::= { mbus68 74 }

mbus68Value22		OBJECT-TYPE
			SYNTAX	INTEGER
			ACCESS	read-only
			STATUS	current
	DESCRIPTION ""
			::= { mbus68 75 }

mbus68VIF23		OBJECT-TYPE
			SYNTAX	INTEGER
			ACCESS	read-only
			STATUS	current
	DESCRIPTION ""
			::= { mbus68 76 }

mbus68Value23		OBJECT-TYPE
			SYNTAX	INTEGER
			ACCESS	read-only
			STATUS	current
	DESCRIPTION ""
			::= { mbus68 77 }

mbus68VIF24		OBJECT-TYPE
			SYNTAX	INTEGER
			ACCESS	read-only
			STATUS	current
	DESCRIPTION ""
			::= { mbus68 78 }

mbus68Value24		OBJECT-TYPE
			SYNTAX	INTEGER
			ACCESS	read-only
			STATUS	current
	DESCRIPTION ""
			::= { mbus68 79 }

mbus68VIF25		OBJECT-TYPE
			SYNTAX	INTEGER
			ACCESS	read-only
			STATUS	current
	DESCRIPTION ""
			::= { mbus68 80 }

mbus68Value25		OBJECT-TYPE
			SYNTAX	INTEGER
			ACCESS	read-only
			STATUS	current
	DESCRIPTION ""
			::= { mbus68 81 }

mbus68VIF26		OBJECT-TYPE
			SYNTAX	INTEGER
			ACCESS	read-only
			STATUS	current
	DESCRIPTION ""
			::= { mbus68 82 }

mbus68Value26		OBJECT-TYPE
			SYNTAX	INTEGER
			ACCESS	read-only
			STATUS	current
	DESCRIPTION ""
			::= { mbus68 83 }

mbus68VIF27		OBJECT-TYPE
			SYNTAX	INTEGER
			ACCESS	read-only
			STATUS	current
	DESCRIPTION ""
			::= { mbus68 84 }

mbus68Value27		OBJECT-TYPE
			SYNTAX	INTEGER
			ACCESS	read-only
			STATUS	current
	DESCRIPTION ""
			::= { mbus68 85 }

mbus68VIF28		OBJECT-TYPE
			SYNTAX	INTEGER
			ACCESS	read-only
			STATUS	current
	DESCRIPTION ""
			::= { mbus68 86 }

mbus68Value28		OBJECT-TYPE
			SYNTAX	INTEGER
			ACCESS	read-only
			STATUS	current
	DESCRIPTION ""
			::= { mbus68 87 }

mbus68VIF29		OBJECT-TYPE
			SYNTAX	INTEGER
			ACCESS	read-only
			STATUS	current
	DESCRIPTION ""
			::= { mbus68 88 }

mbus68Value29		OBJECT-TYPE
			SYNTAX	INTEGER
			ACCESS	read-only
			STATUS	current
	DESCRIPTION ""
			::= { mbus68 89 }

mbus68VIF2A		OBJECT-TYPE
			SYNTAX	INTEGER
			ACCESS	read-only
			STATUS	current
	DESCRIPTION ""
			::= { mbus68 90 }

mbus68Value2A		OBJECT-TYPE
			SYNTAX	INTEGER
			ACCESS	read-only
			STATUS	current
	DESCRIPTION ""
			::= { mbus68 91 }

mbus68VIF2B		OBJECT-TYPE
			SYNTAX	INTEGER
			ACCESS	read-only
			STATUS	current
	DESCRIPTION ""
			::= { mbus68 92 }

mbus68Value2B		OBJECT-TYPE
			SYNTAX	INTEGER
			ACCESS	read-only
			STATUS	current
	DESCRIPTION ""
			::= { mbus68 93 }

mbus68VIF2C		OBJECT-TYPE
			SYNTAX	INTEGER
			ACCESS	read-only
			STATUS	current
	DESCRIPTION ""
			::= { mbus68 94 }

mbus68Value2C		OBJECT-TYPE
			SYNTAX	INTEGER
			ACCESS	read-only
			STATUS	current
	DESCRIPTION ""
			::= { mbus68 95 }

mbus68VIF2D		OBJECT-TYPE
			SYNTAX	INTEGER
			ACCESS	read-only
			STATUS	current
	DESCRIPTION ""
			::= { mbus68 96 }

mbus68Value2D		OBJECT-TYPE
			SYNTAX	INTEGER
			ACCESS	read-only
			STATUS	current
	DESCRIPTION ""
			::= { mbus68 97 }

mbus68VIF2E		OBJECT-TYPE
			SYNTAX	INTEGER
			ACCESS	read-only
			STATUS	current
	DESCRIPTION ""
			::= { mbus68 98 }

mbus68Value2E		OBJECT-TYPE
			SYNTAX	INTEGER
			ACCESS	read-only
			STATUS	current
	DESCRIPTION ""
			::= { mbus68 99 }

mbus68VIF2F		OBJECT-TYPE
			SYNTAX	INTEGER
			ACCESS	read-only
			STATUS	current
	DESCRIPTION ""
			::= { mbus68 100 }

mbus68Value2F		OBJECT-TYPE
			SYNTAX	INTEGER
			ACCESS	read-only
			STATUS	current
	DESCRIPTION ""
			::= { mbus68 101 }

mbus69			OBJECT IDENTIFIER ::= { mbus 105 }

mbus69IdNumber		OBJECT-TYPE
			SYNTAX	Gauge
			ACCESS	read-only
			STATUS	current
	DESCRIPTION ""
			::= { mbus69 1 }

mbus69Manufacturer	OBJECT-TYPE
			SYNTAX	Gauge
			ACCESS	read-only
			STATUS	current
	DESCRIPTION ""
			::= { mbus69 2 }

mbus69Version		OBJECT-TYPE
			SYNTAX	Gauge
			ACCESS	read-only
			STATUS	current
	DESCRIPTION ""
			::= { mbus69 3 }

mbus69Medium		OBJECT-TYPE
			SYNTAX	Gauge
			ACCESS	read-only
			STATUS	current
	DESCRIPTION ""
			::= { mbus69 4 }

mbus69Status		OBJECT-TYPE
			SYNTAX	Gauge
			ACCESS	read-only
			STATUS	current
	DESCRIPTION ""
			::= { mbus69 5 }

mbus69VIF00		OBJECT-TYPE
			SYNTAX	INTEGER
			ACCESS	read-only
			STATUS	current
	DESCRIPTION ""
			::= { mbus69 6 }

mbus69Value00		OBJECT-TYPE
			SYNTAX	INTEGER
			ACCESS	read-only
			STATUS	current
	DESCRIPTION ""
			::= { mbus69 7 }

mbus69VIF01		OBJECT-TYPE
			SYNTAX	INTEGER
			ACCESS	read-only
			STATUS	current
	DESCRIPTION ""
			::= { mbus69 8 }

mbus69Value01		OBJECT-TYPE
			SYNTAX	INTEGER
			ACCESS	read-only
			STATUS	current
	DESCRIPTION ""
			::= { mbus69 9 }

mbus69VIF02		OBJECT-TYPE
			SYNTAX	INTEGER
			ACCESS	read-only
			STATUS	current
	DESCRIPTION ""
			::= { mbus69 10 }

mbus69Value02		OBJECT-TYPE
			SYNTAX	INTEGER
			ACCESS	read-only
			STATUS	current
	DESCRIPTION ""
			::= { mbus69 11 }

mbus69VIF03		OBJECT-TYPE
			SYNTAX	INTEGER
			ACCESS	read-only
			STATUS	current
	DESCRIPTION ""
			::= { mbus69 12 }

mbus69Value03		OBJECT-TYPE
			SYNTAX	INTEGER
			ACCESS	read-only
			STATUS	current
	DESCRIPTION ""
			::= { mbus69 13 }

mbus69VIF04		OBJECT-TYPE
			SYNTAX	INTEGER
			ACCESS	read-only
			STATUS	current
	DESCRIPTION ""
			::= { mbus69 14 }

mbus69Value04		OBJECT-TYPE
			SYNTAX	INTEGER
			ACCESS	read-only
			STATUS	current
	DESCRIPTION ""
			::= { mbus69 15 }

mbus69VIF05		OBJECT-TYPE
			SYNTAX	INTEGER
			ACCESS	read-only
			STATUS	current
	DESCRIPTION ""
			::= { mbus69 16 }

mbus69Value05		OBJECT-TYPE
			SYNTAX	INTEGER
			ACCESS	read-only
			STATUS	current
	DESCRIPTION ""
			::= { mbus69 17 }

mbus69VIF06		OBJECT-TYPE
			SYNTAX	INTEGER
			ACCESS	read-only
			STATUS	current
	DESCRIPTION ""
			::= { mbus69 18 }

mbus69Value06		OBJECT-TYPE
			SYNTAX	INTEGER
			ACCESS	read-only
			STATUS	current
	DESCRIPTION ""
			::= { mbus69 19 }

mbus69VIF07		OBJECT-TYPE
			SYNTAX	INTEGER
			ACCESS	read-only
			STATUS	current
	DESCRIPTION ""
			::= { mbus69 20 }

mbus69Value07		OBJECT-TYPE
			SYNTAX	INTEGER
			ACCESS	read-only
			STATUS	current
	DESCRIPTION ""
			::= { mbus69 21 }

mbus69VIF08		OBJECT-TYPE
			SYNTAX	INTEGER
			ACCESS	read-only
			STATUS	current
	DESCRIPTION ""
			::= { mbus69 22 }

mbus69Value08		OBJECT-TYPE
			SYNTAX	INTEGER
			ACCESS	read-only
			STATUS	current
	DESCRIPTION ""
			::= { mbus69 23 }

mbus69VIF09		OBJECT-TYPE
			SYNTAX	INTEGER
			ACCESS	read-only
			STATUS	current
	DESCRIPTION ""
			::= { mbus69 24 }

mbus69Value09		OBJECT-TYPE
			SYNTAX	INTEGER
			ACCESS	read-only
			STATUS	current
	DESCRIPTION ""
			::= { mbus69 25 }

mbus69VIF0A		OBJECT-TYPE
			SYNTAX	INTEGER
			ACCESS	read-only
			STATUS	current
	DESCRIPTION ""
			::= { mbus69 26 }

mbus69Value0A		OBJECT-TYPE
			SYNTAX	INTEGER
			ACCESS	read-only
			STATUS	current
	DESCRIPTION ""
			::= { mbus69 27 }

mbus69VIF0B		OBJECT-TYPE
			SYNTAX	INTEGER
			ACCESS	read-only
			STATUS	current
	DESCRIPTION ""
			::= { mbus69 28 }

mbus69Value0B		OBJECT-TYPE
			SYNTAX	INTEGER
			ACCESS	read-only
			STATUS	current
	DESCRIPTION ""
			::= { mbus69 29 }

mbus69VIF0C		OBJECT-TYPE
			SYNTAX	INTEGER
			ACCESS	read-only
			STATUS	current
	DESCRIPTION ""
			::= { mbus69 30 }

mbus69Value0C		OBJECT-TYPE
			SYNTAX	INTEGER
			ACCESS	read-only
			STATUS	current
	DESCRIPTION ""
			::= { mbus69 31 }

mbus69VIF0D		OBJECT-TYPE
			SYNTAX	INTEGER
			ACCESS	read-only
			STATUS	current
	DESCRIPTION ""
			::= { mbus69 32 }

mbus69Value0D		OBJECT-TYPE
			SYNTAX	INTEGER
			ACCESS	read-only
			STATUS	current
	DESCRIPTION ""
			::= { mbus69 33 }

mbus69VIF0E		OBJECT-TYPE
			SYNTAX	INTEGER
			ACCESS	read-only
			STATUS	current
	DESCRIPTION ""
			::= { mbus69 34 }

mbus69Value0E		OBJECT-TYPE
			SYNTAX	INTEGER
			ACCESS	read-only
			STATUS	current
	DESCRIPTION ""
			::= { mbus69 35 }

mbus69VIF0F		OBJECT-TYPE
			SYNTAX	INTEGER
			ACCESS	read-only
			STATUS	current
	DESCRIPTION ""
			::= { mbus69 36 }

mbus69Value0F		OBJECT-TYPE
			SYNTAX	INTEGER
			ACCESS	read-only
			STATUS	current
	DESCRIPTION ""
			::= { mbus69 37 }

mbus69VIF10		OBJECT-TYPE
			SYNTAX	INTEGER
			ACCESS	read-only
			STATUS	current
	DESCRIPTION ""
			::= { mbus69 38 }

mbus69Value10		OBJECT-TYPE
			SYNTAX	INTEGER
			ACCESS	read-only
			STATUS	current
	DESCRIPTION ""
			::= { mbus69 39 }

mbus69VIF11		OBJECT-TYPE
			SYNTAX	INTEGER
			ACCESS	read-only
			STATUS	current
	DESCRIPTION ""
			::= { mbus69 40 }

mbus69Value11		OBJECT-TYPE
			SYNTAX	INTEGER
			ACCESS	read-only
			STATUS	current
	DESCRIPTION ""
			::= { mbus69 41 }

mbus69VIF12		OBJECT-TYPE
			SYNTAX	INTEGER
			ACCESS	read-only
			STATUS	current
	DESCRIPTION ""
			::= { mbus69 42 }

mbus69Value12		OBJECT-TYPE
			SYNTAX	INTEGER
			ACCESS	read-only
			STATUS	current
	DESCRIPTION ""
			::= { mbus69 43 }

mbus69VIF13		OBJECT-TYPE
			SYNTAX	INTEGER
			ACCESS	read-only
			STATUS	current
	DESCRIPTION ""
			::= { mbus69 44 }

mbus69Value13		OBJECT-TYPE
			SYNTAX	INTEGER
			ACCESS	read-only
			STATUS	current
	DESCRIPTION ""
			::= { mbus69 45 }

mbus69VIF14		OBJECT-TYPE
			SYNTAX	INTEGER
			ACCESS	read-only
			STATUS	current
	DESCRIPTION ""
			::= { mbus69 46 }

mbus69Value14		OBJECT-TYPE
			SYNTAX	INTEGER
			ACCESS	read-only
			STATUS	current
	DESCRIPTION ""
			::= { mbus69 47 }

mbus69VIF15		OBJECT-TYPE
			SYNTAX	INTEGER
			ACCESS	read-only
			STATUS	current
	DESCRIPTION ""
			::= { mbus69 48 }

mbus69Value15		OBJECT-TYPE
			SYNTAX	INTEGER
			ACCESS	read-only
			STATUS	current
	DESCRIPTION ""
			::= { mbus69 49 }

mbus69VIF16		OBJECT-TYPE
			SYNTAX	INTEGER
			ACCESS	read-only
			STATUS	current
	DESCRIPTION ""
			::= { mbus69 50 }

mbus69Value16		OBJECT-TYPE
			SYNTAX	INTEGER
			ACCESS	read-only
			STATUS	current
	DESCRIPTION ""
			::= { mbus69 51 }

mbus69VIF17		OBJECT-TYPE
			SYNTAX	INTEGER
			ACCESS	read-only
			STATUS	current
	DESCRIPTION ""
			::= { mbus69 52 }

mbus69Value17		OBJECT-TYPE
			SYNTAX	INTEGER
			ACCESS	read-only
			STATUS	current
	DESCRIPTION ""
			::= { mbus69 53 }

mbus69VIF18		OBJECT-TYPE
			SYNTAX	INTEGER
			ACCESS	read-only
			STATUS	current
	DESCRIPTION ""
			::= { mbus69 54 }

mbus69Value18		OBJECT-TYPE
			SYNTAX	INTEGER
			ACCESS	read-only
			STATUS	current
	DESCRIPTION ""
			::= { mbus69 55 }

mbus69VIF19		OBJECT-TYPE
			SYNTAX	INTEGER
			ACCESS	read-only
			STATUS	current
	DESCRIPTION ""
			::= { mbus69 56 }

mbus69Value19		OBJECT-TYPE
			SYNTAX	INTEGER
			ACCESS	read-only
			STATUS	current
	DESCRIPTION ""
			::= { mbus69 57 }

mbus69VIF1A		OBJECT-TYPE
			SYNTAX	INTEGER
			ACCESS	read-only
			STATUS	current
	DESCRIPTION ""
			::= { mbus69 58 }

mbus69Value1A		OBJECT-TYPE
			SYNTAX	INTEGER
			ACCESS	read-only
			STATUS	current
	DESCRIPTION ""
			::= { mbus69 59 }

mbus69VIF1B		OBJECT-TYPE
			SYNTAX	INTEGER
			ACCESS	read-only
			STATUS	current
	DESCRIPTION ""
			::= { mbus69 60 }

mbus69Value1B		OBJECT-TYPE
			SYNTAX	INTEGER
			ACCESS	read-only
			STATUS	current
	DESCRIPTION ""
			::= { mbus69 61 }

mbus69VIF1C		OBJECT-TYPE
			SYNTAX	INTEGER
			ACCESS	read-only
			STATUS	current
	DESCRIPTION ""
			::= { mbus69 62 }

mbus69Value1C		OBJECT-TYPE
			SYNTAX	INTEGER
			ACCESS	read-only
			STATUS	current
	DESCRIPTION ""
			::= { mbus69 63 }

mbus69VIF1D		OBJECT-TYPE
			SYNTAX	INTEGER
			ACCESS	read-only
			STATUS	current
	DESCRIPTION ""
			::= { mbus69 64 }

mbus69Value1D		OBJECT-TYPE
			SYNTAX	INTEGER
			ACCESS	read-only
			STATUS	current
	DESCRIPTION ""
			::= { mbus69 65 }

mbus69VIF1E		OBJECT-TYPE
			SYNTAX	INTEGER
			ACCESS	read-only
			STATUS	current
	DESCRIPTION ""
			::= { mbus69 66 }

mbus69Value1E		OBJECT-TYPE
			SYNTAX	INTEGER
			ACCESS	read-only
			STATUS	current
	DESCRIPTION ""
			::= { mbus69 67 }

mbus69VIF1F		OBJECT-TYPE
			SYNTAX	INTEGER
			ACCESS	read-only
			STATUS	current
	DESCRIPTION ""
			::= { mbus69 68 }

mbus69Value1F		OBJECT-TYPE
			SYNTAX	INTEGER
			ACCESS	read-only
			STATUS	current
	DESCRIPTION ""
			::= { mbus69 69 }

mbus69VIF20		OBJECT-TYPE
			SYNTAX	INTEGER
			ACCESS	read-only
			STATUS	current
	DESCRIPTION ""
			::= { mbus69 70 }

mbus69Value20		OBJECT-TYPE
			SYNTAX	INTEGER
			ACCESS	read-only
			STATUS	current
	DESCRIPTION ""
			::= { mbus69 71 }

mbus69VIF21		OBJECT-TYPE
			SYNTAX	INTEGER
			ACCESS	read-only
			STATUS	current
	DESCRIPTION ""
			::= { mbus69 72 }

mbus69Value21		OBJECT-TYPE
			SYNTAX	INTEGER
			ACCESS	read-only
			STATUS	current
	DESCRIPTION ""
			::= { mbus69 73 }

mbus69VIF22		OBJECT-TYPE
			SYNTAX	INTEGER
			ACCESS	read-only
			STATUS	current
	DESCRIPTION ""
			::= { mbus69 74 }

mbus69Value22		OBJECT-TYPE
			SYNTAX	INTEGER
			ACCESS	read-only
			STATUS	current
	DESCRIPTION ""
			::= { mbus69 75 }

mbus69VIF23		OBJECT-TYPE
			SYNTAX	INTEGER
			ACCESS	read-only
			STATUS	current
	DESCRIPTION ""
			::= { mbus69 76 }

mbus69Value23		OBJECT-TYPE
			SYNTAX	INTEGER
			ACCESS	read-only
			STATUS	current
	DESCRIPTION ""
			::= { mbus69 77 }

mbus69VIF24		OBJECT-TYPE
			SYNTAX	INTEGER
			ACCESS	read-only
			STATUS	current
	DESCRIPTION ""
			::= { mbus69 78 }

mbus69Value24		OBJECT-TYPE
			SYNTAX	INTEGER
			ACCESS	read-only
			STATUS	current
	DESCRIPTION ""
			::= { mbus69 79 }

mbus69VIF25		OBJECT-TYPE
			SYNTAX	INTEGER
			ACCESS	read-only
			STATUS	current
	DESCRIPTION ""
			::= { mbus69 80 }

mbus69Value25		OBJECT-TYPE
			SYNTAX	INTEGER
			ACCESS	read-only
			STATUS	current
	DESCRIPTION ""
			::= { mbus69 81 }

mbus69VIF26		OBJECT-TYPE
			SYNTAX	INTEGER
			ACCESS	read-only
			STATUS	current
	DESCRIPTION ""
			::= { mbus69 82 }

mbus69Value26		OBJECT-TYPE
			SYNTAX	INTEGER
			ACCESS	read-only
			STATUS	current
	DESCRIPTION ""
			::= { mbus69 83 }

mbus69VIF27		OBJECT-TYPE
			SYNTAX	INTEGER
			ACCESS	read-only
			STATUS	current
	DESCRIPTION ""
			::= { mbus69 84 }

mbus69Value27		OBJECT-TYPE
			SYNTAX	INTEGER
			ACCESS	read-only
			STATUS	current
	DESCRIPTION ""
			::= { mbus69 85 }

mbus69VIF28		OBJECT-TYPE
			SYNTAX	INTEGER
			ACCESS	read-only
			STATUS	current
	DESCRIPTION ""
			::= { mbus69 86 }

mbus69Value28		OBJECT-TYPE
			SYNTAX	INTEGER
			ACCESS	read-only
			STATUS	current
	DESCRIPTION ""
			::= { mbus69 87 }

mbus69VIF29		OBJECT-TYPE
			SYNTAX	INTEGER
			ACCESS	read-only
			STATUS	current
	DESCRIPTION ""
			::= { mbus69 88 }

mbus69Value29		OBJECT-TYPE
			SYNTAX	INTEGER
			ACCESS	read-only
			STATUS	current
	DESCRIPTION ""
			::= { mbus69 89 }

mbus69VIF2A		OBJECT-TYPE
			SYNTAX	INTEGER
			ACCESS	read-only
			STATUS	current
	DESCRIPTION ""
			::= { mbus69 90 }

mbus69Value2A		OBJECT-TYPE
			SYNTAX	INTEGER
			ACCESS	read-only
			STATUS	current
	DESCRIPTION ""
			::= { mbus69 91 }

mbus69VIF2B		OBJECT-TYPE
			SYNTAX	INTEGER
			ACCESS	read-only
			STATUS	current
	DESCRIPTION ""
			::= { mbus69 92 }

mbus69Value2B		OBJECT-TYPE
			SYNTAX	INTEGER
			ACCESS	read-only
			STATUS	current
	DESCRIPTION ""
			::= { mbus69 93 }

mbus69VIF2C		OBJECT-TYPE
			SYNTAX	INTEGER
			ACCESS	read-only
			STATUS	current
	DESCRIPTION ""
			::= { mbus69 94 }

mbus69Value2C		OBJECT-TYPE
			SYNTAX	INTEGER
			ACCESS	read-only
			STATUS	current
	DESCRIPTION ""
			::= { mbus69 95 }

mbus69VIF2D		OBJECT-TYPE
			SYNTAX	INTEGER
			ACCESS	read-only
			STATUS	current
	DESCRIPTION ""
			::= { mbus69 96 }

mbus69Value2D		OBJECT-TYPE
			SYNTAX	INTEGER
			ACCESS	read-only
			STATUS	current
	DESCRIPTION ""
			::= { mbus69 97 }

mbus69VIF2E		OBJECT-TYPE
			SYNTAX	INTEGER
			ACCESS	read-only
			STATUS	current
	DESCRIPTION ""
			::= { mbus69 98 }

mbus69Value2E		OBJECT-TYPE
			SYNTAX	INTEGER
			ACCESS	read-only
			STATUS	current
	DESCRIPTION ""
			::= { mbus69 99 }

mbus69VIF2F		OBJECT-TYPE
			SYNTAX	INTEGER
			ACCESS	read-only
			STATUS	current
	DESCRIPTION ""
			::= { mbus69 100 }

mbus69Value2F		OBJECT-TYPE
			SYNTAX	INTEGER
			ACCESS	read-only
			STATUS	current
	DESCRIPTION ""
			::= { mbus69 101 }

mbus6A			OBJECT IDENTIFIER ::= { mbus 106 }

mbus6AIdNumber		OBJECT-TYPE
			SYNTAX	Gauge
			ACCESS	read-only
			STATUS	current
	DESCRIPTION ""
			::= { mbus6A 1 }

mbus6AManufacturer	OBJECT-TYPE
			SYNTAX	Gauge
			ACCESS	read-only
			STATUS	current
	DESCRIPTION ""
			::= { mbus6A 2 }

mbus6AVersion		OBJECT-TYPE
			SYNTAX	Gauge
			ACCESS	read-only
			STATUS	current
	DESCRIPTION ""
			::= { mbus6A 3 }

mbus6AMedium		OBJECT-TYPE
			SYNTAX	Gauge
			ACCESS	read-only
			STATUS	current
	DESCRIPTION ""
			::= { mbus6A 4 }

mbus6AStatus		OBJECT-TYPE
			SYNTAX	Gauge
			ACCESS	read-only
			STATUS	current
	DESCRIPTION ""
			::= { mbus6A 5 }

mbus6AVIF00		OBJECT-TYPE
			SYNTAX	INTEGER
			ACCESS	read-only
			STATUS	current
	DESCRIPTION ""
			::= { mbus6A 6 }

mbus6AValue00		OBJECT-TYPE
			SYNTAX	INTEGER
			ACCESS	read-only
			STATUS	current
	DESCRIPTION ""
			::= { mbus6A 7 }

mbus6AVIF01		OBJECT-TYPE
			SYNTAX	INTEGER
			ACCESS	read-only
			STATUS	current
	DESCRIPTION ""
			::= { mbus6A 8 }

mbus6AValue01		OBJECT-TYPE
			SYNTAX	INTEGER
			ACCESS	read-only
			STATUS	current
	DESCRIPTION ""
			::= { mbus6A 9 }

mbus6AVIF02		OBJECT-TYPE
			SYNTAX	INTEGER
			ACCESS	read-only
			STATUS	current
	DESCRIPTION ""
			::= { mbus6A 10 }

mbus6AValue02		OBJECT-TYPE
			SYNTAX	INTEGER
			ACCESS	read-only
			STATUS	current
	DESCRIPTION ""
			::= { mbus6A 11 }

mbus6AVIF03		OBJECT-TYPE
			SYNTAX	INTEGER
			ACCESS	read-only
			STATUS	current
	DESCRIPTION ""
			::= { mbus6A 12 }

mbus6AValue03		OBJECT-TYPE
			SYNTAX	INTEGER
			ACCESS	read-only
			STATUS	current
	DESCRIPTION ""
			::= { mbus6A 13 }

mbus6AVIF04		OBJECT-TYPE
			SYNTAX	INTEGER
			ACCESS	read-only
			STATUS	current
	DESCRIPTION ""
			::= { mbus6A 14 }

mbus6AValue04		OBJECT-TYPE
			SYNTAX	INTEGER
			ACCESS	read-only
			STATUS	current
	DESCRIPTION ""
			::= { mbus6A 15 }

mbus6AVIF05		OBJECT-TYPE
			SYNTAX	INTEGER
			ACCESS	read-only
			STATUS	current
	DESCRIPTION ""
			::= { mbus6A 16 }

mbus6AValue05		OBJECT-TYPE
			SYNTAX	INTEGER
			ACCESS	read-only
			STATUS	current
	DESCRIPTION ""
			::= { mbus6A 17 }

mbus6AVIF06		OBJECT-TYPE
			SYNTAX	INTEGER
			ACCESS	read-only
			STATUS	current
	DESCRIPTION ""
			::= { mbus6A 18 }

mbus6AValue06		OBJECT-TYPE
			SYNTAX	INTEGER
			ACCESS	read-only
			STATUS	current
	DESCRIPTION ""
			::= { mbus6A 19 }

mbus6AVIF07		OBJECT-TYPE
			SYNTAX	INTEGER
			ACCESS	read-only
			STATUS	current
	DESCRIPTION ""
			::= { mbus6A 20 }

mbus6AValue07		OBJECT-TYPE
			SYNTAX	INTEGER
			ACCESS	read-only
			STATUS	current
	DESCRIPTION ""
			::= { mbus6A 21 }

mbus6AVIF08		OBJECT-TYPE
			SYNTAX	INTEGER
			ACCESS	read-only
			STATUS	current
	DESCRIPTION ""
			::= { mbus6A 22 }

mbus6AValue08		OBJECT-TYPE
			SYNTAX	INTEGER
			ACCESS	read-only
			STATUS	current
	DESCRIPTION ""
			::= { mbus6A 23 }

mbus6AVIF09		OBJECT-TYPE
			SYNTAX	INTEGER
			ACCESS	read-only
			STATUS	current
	DESCRIPTION ""
			::= { mbus6A 24 }

mbus6AValue09		OBJECT-TYPE
			SYNTAX	INTEGER
			ACCESS	read-only
			STATUS	current
	DESCRIPTION ""
			::= { mbus6A 25 }

mbus6AVIF0A		OBJECT-TYPE
			SYNTAX	INTEGER
			ACCESS	read-only
			STATUS	current
	DESCRIPTION ""
			::= { mbus6A 26 }

mbus6AValue0A		OBJECT-TYPE
			SYNTAX	INTEGER
			ACCESS	read-only
			STATUS	current
	DESCRIPTION ""
			::= { mbus6A 27 }

mbus6AVIF0B		OBJECT-TYPE
			SYNTAX	INTEGER
			ACCESS	read-only
			STATUS	current
	DESCRIPTION ""
			::= { mbus6A 28 }

mbus6AValue0B		OBJECT-TYPE
			SYNTAX	INTEGER
			ACCESS	read-only
			STATUS	current
	DESCRIPTION ""
			::= { mbus6A 29 }

mbus6AVIF0C		OBJECT-TYPE
			SYNTAX	INTEGER
			ACCESS	read-only
			STATUS	current
	DESCRIPTION ""
			::= { mbus6A 30 }

mbus6AValue0C		OBJECT-TYPE
			SYNTAX	INTEGER
			ACCESS	read-only
			STATUS	current
	DESCRIPTION ""
			::= { mbus6A 31 }

mbus6AVIF0D		OBJECT-TYPE
			SYNTAX	INTEGER
			ACCESS	read-only
			STATUS	current
	DESCRIPTION ""
			::= { mbus6A 32 }

mbus6AValue0D		OBJECT-TYPE
			SYNTAX	INTEGER
			ACCESS	read-only
			STATUS	current
	DESCRIPTION ""
			::= { mbus6A 33 }

mbus6AVIF0E		OBJECT-TYPE
			SYNTAX	INTEGER
			ACCESS	read-only
			STATUS	current
	DESCRIPTION ""
			::= { mbus6A 34 }

mbus6AValue0E		OBJECT-TYPE
			SYNTAX	INTEGER
			ACCESS	read-only
			STATUS	current
	DESCRIPTION ""
			::= { mbus6A 35 }

mbus6AVIF0F		OBJECT-TYPE
			SYNTAX	INTEGER
			ACCESS	read-only
			STATUS	current
	DESCRIPTION ""
			::= { mbus6A 36 }

mbus6AValue0F		OBJECT-TYPE
			SYNTAX	INTEGER
			ACCESS	read-only
			STATUS	current
	DESCRIPTION ""
			::= { mbus6A 37 }

mbus6AVIF10		OBJECT-TYPE
			SYNTAX	INTEGER
			ACCESS	read-only
			STATUS	current
	DESCRIPTION ""
			::= { mbus6A 38 }

mbus6AValue10		OBJECT-TYPE
			SYNTAX	INTEGER
			ACCESS	read-only
			STATUS	current
	DESCRIPTION ""
			::= { mbus6A 39 }

mbus6AVIF11		OBJECT-TYPE
			SYNTAX	INTEGER
			ACCESS	read-only
			STATUS	current
	DESCRIPTION ""
			::= { mbus6A 40 }

mbus6AValue11		OBJECT-TYPE
			SYNTAX	INTEGER
			ACCESS	read-only
			STATUS	current
	DESCRIPTION ""
			::= { mbus6A 41 }

mbus6AVIF12		OBJECT-TYPE
			SYNTAX	INTEGER
			ACCESS	read-only
			STATUS	current
	DESCRIPTION ""
			::= { mbus6A 42 }

mbus6AValue12		OBJECT-TYPE
			SYNTAX	INTEGER
			ACCESS	read-only
			STATUS	current
	DESCRIPTION ""
			::= { mbus6A 43 }

mbus6AVIF13		OBJECT-TYPE
			SYNTAX	INTEGER
			ACCESS	read-only
			STATUS	current
	DESCRIPTION ""
			::= { mbus6A 44 }

mbus6AValue13		OBJECT-TYPE
			SYNTAX	INTEGER
			ACCESS	read-only
			STATUS	current
	DESCRIPTION ""
			::= { mbus6A 45 }

mbus6AVIF14		OBJECT-TYPE
			SYNTAX	INTEGER
			ACCESS	read-only
			STATUS	current
	DESCRIPTION ""
			::= { mbus6A 46 }

mbus6AValue14		OBJECT-TYPE
			SYNTAX	INTEGER
			ACCESS	read-only
			STATUS	current
	DESCRIPTION ""
			::= { mbus6A 47 }

mbus6AVIF15		OBJECT-TYPE
			SYNTAX	INTEGER
			ACCESS	read-only
			STATUS	current
	DESCRIPTION ""
			::= { mbus6A 48 }

mbus6AValue15		OBJECT-TYPE
			SYNTAX	INTEGER
			ACCESS	read-only
			STATUS	current
	DESCRIPTION ""
			::= { mbus6A 49 }

mbus6AVIF16		OBJECT-TYPE
			SYNTAX	INTEGER
			ACCESS	read-only
			STATUS	current
	DESCRIPTION ""
			::= { mbus6A 50 }

mbus6AValue16		OBJECT-TYPE
			SYNTAX	INTEGER
			ACCESS	read-only
			STATUS	current
	DESCRIPTION ""
			::= { mbus6A 51 }

mbus6AVIF17		OBJECT-TYPE
			SYNTAX	INTEGER
			ACCESS	read-only
			STATUS	current
	DESCRIPTION ""
			::= { mbus6A 52 }

mbus6AValue17		OBJECT-TYPE
			SYNTAX	INTEGER
			ACCESS	read-only
			STATUS	current
	DESCRIPTION ""
			::= { mbus6A 53 }

mbus6AVIF18		OBJECT-TYPE
			SYNTAX	INTEGER
			ACCESS	read-only
			STATUS	current
	DESCRIPTION ""
			::= { mbus6A 54 }

mbus6AValue18		OBJECT-TYPE
			SYNTAX	INTEGER
			ACCESS	read-only
			STATUS	current
	DESCRIPTION ""
			::= { mbus6A 55 }

mbus6AVIF19		OBJECT-TYPE
			SYNTAX	INTEGER
			ACCESS	read-only
			STATUS	current
	DESCRIPTION ""
			::= { mbus6A 56 }

mbus6AValue19		OBJECT-TYPE
			SYNTAX	INTEGER
			ACCESS	read-only
			STATUS	current
	DESCRIPTION ""
			::= { mbus6A 57 }

mbus6AVIF1A		OBJECT-TYPE
			SYNTAX	INTEGER
			ACCESS	read-only
			STATUS	current
	DESCRIPTION ""
			::= { mbus6A 58 }

mbus6AValue1A		OBJECT-TYPE
			SYNTAX	INTEGER
			ACCESS	read-only
			STATUS	current
	DESCRIPTION ""
			::= { mbus6A 59 }

mbus6AVIF1B		OBJECT-TYPE
			SYNTAX	INTEGER
			ACCESS	read-only
			STATUS	current
	DESCRIPTION ""
			::= { mbus6A 60 }

mbus6AValue1B		OBJECT-TYPE
			SYNTAX	INTEGER
			ACCESS	read-only
			STATUS	current
	DESCRIPTION ""
			::= { mbus6A 61 }

mbus6AVIF1C		OBJECT-TYPE
			SYNTAX	INTEGER
			ACCESS	read-only
			STATUS	current
	DESCRIPTION ""
			::= { mbus6A 62 }

mbus6AValue1C		OBJECT-TYPE
			SYNTAX	INTEGER
			ACCESS	read-only
			STATUS	current
	DESCRIPTION ""
			::= { mbus6A 63 }

mbus6AVIF1D		OBJECT-TYPE
			SYNTAX	INTEGER
			ACCESS	read-only
			STATUS	current
	DESCRIPTION ""
			::= { mbus6A 64 }

mbus6AValue1D		OBJECT-TYPE
			SYNTAX	INTEGER
			ACCESS	read-only
			STATUS	current
	DESCRIPTION ""
			::= { mbus6A 65 }

mbus6AVIF1E		OBJECT-TYPE
			SYNTAX	INTEGER
			ACCESS	read-only
			STATUS	current
	DESCRIPTION ""
			::= { mbus6A 66 }

mbus6AValue1E		OBJECT-TYPE
			SYNTAX	INTEGER
			ACCESS	read-only
			STATUS	current
	DESCRIPTION ""
			::= { mbus6A 67 }

mbus6AVIF1F		OBJECT-TYPE
			SYNTAX	INTEGER
			ACCESS	read-only
			STATUS	current
	DESCRIPTION ""
			::= { mbus6A 68 }

mbus6AValue1F		OBJECT-TYPE
			SYNTAX	INTEGER
			ACCESS	read-only
			STATUS	current
	DESCRIPTION ""
			::= { mbus6A 69 }

mbus6AVIF20		OBJECT-TYPE
			SYNTAX	INTEGER
			ACCESS	read-only
			STATUS	current
	DESCRIPTION ""
			::= { mbus6A 70 }

mbus6AValue20		OBJECT-TYPE
			SYNTAX	INTEGER
			ACCESS	read-only
			STATUS	current
	DESCRIPTION ""
			::= { mbus6A 71 }

mbus6AVIF21		OBJECT-TYPE
			SYNTAX	INTEGER
			ACCESS	read-only
			STATUS	current
	DESCRIPTION ""
			::= { mbus6A 72 }

mbus6AValue21		OBJECT-TYPE
			SYNTAX	INTEGER
			ACCESS	read-only
			STATUS	current
	DESCRIPTION ""
			::= { mbus6A 73 }

mbus6AVIF22		OBJECT-TYPE
			SYNTAX	INTEGER
			ACCESS	read-only
			STATUS	current
	DESCRIPTION ""
			::= { mbus6A 74 }

mbus6AValue22		OBJECT-TYPE
			SYNTAX	INTEGER
			ACCESS	read-only
			STATUS	current
	DESCRIPTION ""
			::= { mbus6A 75 }

mbus6AVIF23		OBJECT-TYPE
			SYNTAX	INTEGER
			ACCESS	read-only
			STATUS	current
	DESCRIPTION ""
			::= { mbus6A 76 }

mbus6AValue23		OBJECT-TYPE
			SYNTAX	INTEGER
			ACCESS	read-only
			STATUS	current
	DESCRIPTION ""
			::= { mbus6A 77 }

mbus6AVIF24		OBJECT-TYPE
			SYNTAX	INTEGER
			ACCESS	read-only
			STATUS	current
	DESCRIPTION ""
			::= { mbus6A 78 }

mbus6AValue24		OBJECT-TYPE
			SYNTAX	INTEGER
			ACCESS	read-only
			STATUS	current
	DESCRIPTION ""
			::= { mbus6A 79 }

mbus6AVIF25		OBJECT-TYPE
			SYNTAX	INTEGER
			ACCESS	read-only
			STATUS	current
	DESCRIPTION ""
			::= { mbus6A 80 }

mbus6AValue25		OBJECT-TYPE
			SYNTAX	INTEGER
			ACCESS	read-only
			STATUS	current
	DESCRIPTION ""
			::= { mbus6A 81 }

mbus6AVIF26		OBJECT-TYPE
			SYNTAX	INTEGER
			ACCESS	read-only
			STATUS	current
	DESCRIPTION ""
			::= { mbus6A 82 }

mbus6AValue26		OBJECT-TYPE
			SYNTAX	INTEGER
			ACCESS	read-only
			STATUS	current
	DESCRIPTION ""
			::= { mbus6A 83 }

mbus6AVIF27		OBJECT-TYPE
			SYNTAX	INTEGER
			ACCESS	read-only
			STATUS	current
	DESCRIPTION ""
			::= { mbus6A 84 }

mbus6AValue27		OBJECT-TYPE
			SYNTAX	INTEGER
			ACCESS	read-only
			STATUS	current
	DESCRIPTION ""
			::= { mbus6A 85 }

mbus6AVIF28		OBJECT-TYPE
			SYNTAX	INTEGER
			ACCESS	read-only
			STATUS	current
	DESCRIPTION ""
			::= { mbus6A 86 }

mbus6AValue28		OBJECT-TYPE
			SYNTAX	INTEGER
			ACCESS	read-only
			STATUS	current
	DESCRIPTION ""
			::= { mbus6A 87 }

mbus6AVIF29		OBJECT-TYPE
			SYNTAX	INTEGER
			ACCESS	read-only
			STATUS	current
	DESCRIPTION ""
			::= { mbus6A 88 }

mbus6AValue29		OBJECT-TYPE
			SYNTAX	INTEGER
			ACCESS	read-only
			STATUS	current
	DESCRIPTION ""
			::= { mbus6A 89 }

mbus6AVIF2A		OBJECT-TYPE
			SYNTAX	INTEGER
			ACCESS	read-only
			STATUS	current
	DESCRIPTION ""
			::= { mbus6A 90 }

mbus6AValue2A		OBJECT-TYPE
			SYNTAX	INTEGER
			ACCESS	read-only
			STATUS	current
	DESCRIPTION ""
			::= { mbus6A 91 }

mbus6AVIF2B		OBJECT-TYPE
			SYNTAX	INTEGER
			ACCESS	read-only
			STATUS	current
	DESCRIPTION ""
			::= { mbus6A 92 }

mbus6AValue2B		OBJECT-TYPE
			SYNTAX	INTEGER
			ACCESS	read-only
			STATUS	current
	DESCRIPTION ""
			::= { mbus6A 93 }

mbus6AVIF2C		OBJECT-TYPE
			SYNTAX	INTEGER
			ACCESS	read-only
			STATUS	current
	DESCRIPTION ""
			::= { mbus6A 94 }

mbus6AValue2C		OBJECT-TYPE
			SYNTAX	INTEGER
			ACCESS	read-only
			STATUS	current
	DESCRIPTION ""
			::= { mbus6A 95 }

mbus6AVIF2D		OBJECT-TYPE
			SYNTAX	INTEGER
			ACCESS	read-only
			STATUS	current
	DESCRIPTION ""
			::= { mbus6A 96 }

mbus6AValue2D		OBJECT-TYPE
			SYNTAX	INTEGER
			ACCESS	read-only
			STATUS	current
	DESCRIPTION ""
			::= { mbus6A 97 }

mbus6AVIF2E		OBJECT-TYPE
			SYNTAX	INTEGER
			ACCESS	read-only
			STATUS	current
	DESCRIPTION ""
			::= { mbus6A 98 }

mbus6AValue2E		OBJECT-TYPE
			SYNTAX	INTEGER
			ACCESS	read-only
			STATUS	current
	DESCRIPTION ""
			::= { mbus6A 99 }

mbus6AVIF2F		OBJECT-TYPE
			SYNTAX	INTEGER
			ACCESS	read-only
			STATUS	current
	DESCRIPTION ""
			::= { mbus6A 100 }

mbus6AValue2F		OBJECT-TYPE
			SYNTAX	INTEGER
			ACCESS	read-only
			STATUS	current
	DESCRIPTION ""
			::= { mbus6A 101 }

mbus6B			OBJECT IDENTIFIER ::= { mbus 107 }

mbus6BIdNumber		OBJECT-TYPE
			SYNTAX	Gauge
			ACCESS	read-only
			STATUS	current
	DESCRIPTION ""
			::= { mbus6B 1 }

mbus6BManufacturer	OBJECT-TYPE
			SYNTAX	Gauge
			ACCESS	read-only
			STATUS	current
	DESCRIPTION ""
			::= { mbus6B 2 }

mbus6BVersion		OBJECT-TYPE
			SYNTAX	Gauge
			ACCESS	read-only
			STATUS	current
	DESCRIPTION ""
			::= { mbus6B 3 }

mbus6BMedium		OBJECT-TYPE
			SYNTAX	Gauge
			ACCESS	read-only
			STATUS	current
	DESCRIPTION ""
			::= { mbus6B 4 }

mbus6BStatus		OBJECT-TYPE
			SYNTAX	Gauge
			ACCESS	read-only
			STATUS	current
	DESCRIPTION ""
			::= { mbus6B 5 }

mbus6BVIF00		OBJECT-TYPE
			SYNTAX	INTEGER
			ACCESS	read-only
			STATUS	current
	DESCRIPTION ""
			::= { mbus6B 6 }

mbus6BValue00		OBJECT-TYPE
			SYNTAX	INTEGER
			ACCESS	read-only
			STATUS	current
	DESCRIPTION ""
			::= { mbus6B 7 }

mbus6BVIF01		OBJECT-TYPE
			SYNTAX	INTEGER
			ACCESS	read-only
			STATUS	current
	DESCRIPTION ""
			::= { mbus6B 8 }

mbus6BValue01		OBJECT-TYPE
			SYNTAX	INTEGER
			ACCESS	read-only
			STATUS	current
	DESCRIPTION ""
			::= { mbus6B 9 }

mbus6BVIF02		OBJECT-TYPE
			SYNTAX	INTEGER
			ACCESS	read-only
			STATUS	current
	DESCRIPTION ""
			::= { mbus6B 10 }

mbus6BValue02		OBJECT-TYPE
			SYNTAX	INTEGER
			ACCESS	read-only
			STATUS	current
	DESCRIPTION ""
			::= { mbus6B 11 }

mbus6BVIF03		OBJECT-TYPE
			SYNTAX	INTEGER
			ACCESS	read-only
			STATUS	current
	DESCRIPTION ""
			::= { mbus6B 12 }

mbus6BValue03		OBJECT-TYPE
			SYNTAX	INTEGER
			ACCESS	read-only
			STATUS	current
	DESCRIPTION ""
			::= { mbus6B 13 }

mbus6BVIF04		OBJECT-TYPE
			SYNTAX	INTEGER
			ACCESS	read-only
			STATUS	current
	DESCRIPTION ""
			::= { mbus6B 14 }

mbus6BValue04		OBJECT-TYPE
			SYNTAX	INTEGER
			ACCESS	read-only
			STATUS	current
	DESCRIPTION ""
			::= { mbus6B 15 }

mbus6BVIF05		OBJECT-TYPE
			SYNTAX	INTEGER
			ACCESS	read-only
			STATUS	current
	DESCRIPTION ""
			::= { mbus6B 16 }

mbus6BValue05		OBJECT-TYPE
			SYNTAX	INTEGER
			ACCESS	read-only
			STATUS	current
	DESCRIPTION ""
			::= { mbus6B 17 }

mbus6BVIF06		OBJECT-TYPE
			SYNTAX	INTEGER
			ACCESS	read-only
			STATUS	current
	DESCRIPTION ""
			::= { mbus6B 18 }

mbus6BValue06		OBJECT-TYPE
			SYNTAX	INTEGER
			ACCESS	read-only
			STATUS	current
	DESCRIPTION ""
			::= { mbus6B 19 }

mbus6BVIF07		OBJECT-TYPE
			SYNTAX	INTEGER
			ACCESS	read-only
			STATUS	current
	DESCRIPTION ""
			::= { mbus6B 20 }

mbus6BValue07		OBJECT-TYPE
			SYNTAX	INTEGER
			ACCESS	read-only
			STATUS	current
	DESCRIPTION ""
			::= { mbus6B 21 }

mbus6BVIF08		OBJECT-TYPE
			SYNTAX	INTEGER
			ACCESS	read-only
			STATUS	current
	DESCRIPTION ""
			::= { mbus6B 22 }

mbus6BValue08		OBJECT-TYPE
			SYNTAX	INTEGER
			ACCESS	read-only
			STATUS	current
	DESCRIPTION ""
			::= { mbus6B 23 }

mbus6BVIF09		OBJECT-TYPE
			SYNTAX	INTEGER
			ACCESS	read-only
			STATUS	current
	DESCRIPTION ""
			::= { mbus6B 24 }

mbus6BValue09		OBJECT-TYPE
			SYNTAX	INTEGER
			ACCESS	read-only
			STATUS	current
	DESCRIPTION ""
			::= { mbus6B 25 }

mbus6BVIF0A		OBJECT-TYPE
			SYNTAX	INTEGER
			ACCESS	read-only
			STATUS	current
	DESCRIPTION ""
			::= { mbus6B 26 }

mbus6BValue0A		OBJECT-TYPE
			SYNTAX	INTEGER
			ACCESS	read-only
			STATUS	current
	DESCRIPTION ""
			::= { mbus6B 27 }

mbus6BVIF0B		OBJECT-TYPE
			SYNTAX	INTEGER
			ACCESS	read-only
			STATUS	current
	DESCRIPTION ""
			::= { mbus6B 28 }

mbus6BValue0B		OBJECT-TYPE
			SYNTAX	INTEGER
			ACCESS	read-only
			STATUS	current
	DESCRIPTION ""
			::= { mbus6B 29 }

mbus6BVIF0C		OBJECT-TYPE
			SYNTAX	INTEGER
			ACCESS	read-only
			STATUS	current
	DESCRIPTION ""
			::= { mbus6B 30 }

mbus6BValue0C		OBJECT-TYPE
			SYNTAX	INTEGER
			ACCESS	read-only
			STATUS	current
	DESCRIPTION ""
			::= { mbus6B 31 }

mbus6BVIF0D		OBJECT-TYPE
			SYNTAX	INTEGER
			ACCESS	read-only
			STATUS	current
	DESCRIPTION ""
			::= { mbus6B 32 }

mbus6BValue0D		OBJECT-TYPE
			SYNTAX	INTEGER
			ACCESS	read-only
			STATUS	current
	DESCRIPTION ""
			::= { mbus6B 33 }

mbus6BVIF0E		OBJECT-TYPE
			SYNTAX	INTEGER
			ACCESS	read-only
			STATUS	current
	DESCRIPTION ""
			::= { mbus6B 34 }

mbus6BValue0E		OBJECT-TYPE
			SYNTAX	INTEGER
			ACCESS	read-only
			STATUS	current
	DESCRIPTION ""
			::= { mbus6B 35 }

mbus6BVIF0F		OBJECT-TYPE
			SYNTAX	INTEGER
			ACCESS	read-only
			STATUS	current
	DESCRIPTION ""
			::= { mbus6B 36 }

mbus6BValue0F		OBJECT-TYPE
			SYNTAX	INTEGER
			ACCESS	read-only
			STATUS	current
	DESCRIPTION ""
			::= { mbus6B 37 }

mbus6BVIF10		OBJECT-TYPE
			SYNTAX	INTEGER
			ACCESS	read-only
			STATUS	current
	DESCRIPTION ""
			::= { mbus6B 38 }

mbus6BValue10		OBJECT-TYPE
			SYNTAX	INTEGER
			ACCESS	read-only
			STATUS	current
	DESCRIPTION ""
			::= { mbus6B 39 }

mbus6BVIF11		OBJECT-TYPE
			SYNTAX	INTEGER
			ACCESS	read-only
			STATUS	current
	DESCRIPTION ""
			::= { mbus6B 40 }

mbus6BValue11		OBJECT-TYPE
			SYNTAX	INTEGER
			ACCESS	read-only
			STATUS	current
	DESCRIPTION ""
			::= { mbus6B 41 }

mbus6BVIF12		OBJECT-TYPE
			SYNTAX	INTEGER
			ACCESS	read-only
			STATUS	current
	DESCRIPTION ""
			::= { mbus6B 42 }

mbus6BValue12		OBJECT-TYPE
			SYNTAX	INTEGER
			ACCESS	read-only
			STATUS	current
	DESCRIPTION ""
			::= { mbus6B 43 }

mbus6BVIF13		OBJECT-TYPE
			SYNTAX	INTEGER
			ACCESS	read-only
			STATUS	current
	DESCRIPTION ""
			::= { mbus6B 44 }

mbus6BValue13		OBJECT-TYPE
			SYNTAX	INTEGER
			ACCESS	read-only
			STATUS	current
	DESCRIPTION ""
			::= { mbus6B 45 }

mbus6BVIF14		OBJECT-TYPE
			SYNTAX	INTEGER
			ACCESS	read-only
			STATUS	current
	DESCRIPTION ""
			::= { mbus6B 46 }

mbus6BValue14		OBJECT-TYPE
			SYNTAX	INTEGER
			ACCESS	read-only
			STATUS	current
	DESCRIPTION ""
			::= { mbus6B 47 }

mbus6BVIF15		OBJECT-TYPE
			SYNTAX	INTEGER
			ACCESS	read-only
			STATUS	current
	DESCRIPTION ""
			::= { mbus6B 48 }

mbus6BValue15		OBJECT-TYPE
			SYNTAX	INTEGER
			ACCESS	read-only
			STATUS	current
	DESCRIPTION ""
			::= { mbus6B 49 }

mbus6BVIF16		OBJECT-TYPE
			SYNTAX	INTEGER
			ACCESS	read-only
			STATUS	current
	DESCRIPTION ""
			::= { mbus6B 50 }

mbus6BValue16		OBJECT-TYPE
			SYNTAX	INTEGER
			ACCESS	read-only
			STATUS	current
	DESCRIPTION ""
			::= { mbus6B 51 }

mbus6BVIF17		OBJECT-TYPE
			SYNTAX	INTEGER
			ACCESS	read-only
			STATUS	current
	DESCRIPTION ""
			::= { mbus6B 52 }

mbus6BValue17		OBJECT-TYPE
			SYNTAX	INTEGER
			ACCESS	read-only
			STATUS	current
	DESCRIPTION ""
			::= { mbus6B 53 }

mbus6BVIF18		OBJECT-TYPE
			SYNTAX	INTEGER
			ACCESS	read-only
			STATUS	current
	DESCRIPTION ""
			::= { mbus6B 54 }

mbus6BValue18		OBJECT-TYPE
			SYNTAX	INTEGER
			ACCESS	read-only
			STATUS	current
	DESCRIPTION ""
			::= { mbus6B 55 }

mbus6BVIF19		OBJECT-TYPE
			SYNTAX	INTEGER
			ACCESS	read-only
			STATUS	current
	DESCRIPTION ""
			::= { mbus6B 56 }

mbus6BValue19		OBJECT-TYPE
			SYNTAX	INTEGER
			ACCESS	read-only
			STATUS	current
	DESCRIPTION ""
			::= { mbus6B 57 }

mbus6BVIF1A		OBJECT-TYPE
			SYNTAX	INTEGER
			ACCESS	read-only
			STATUS	current
	DESCRIPTION ""
			::= { mbus6B 58 }

mbus6BValue1A		OBJECT-TYPE
			SYNTAX	INTEGER
			ACCESS	read-only
			STATUS	current
	DESCRIPTION ""
			::= { mbus6B 59 }

mbus6BVIF1B		OBJECT-TYPE
			SYNTAX	INTEGER
			ACCESS	read-only
			STATUS	current
	DESCRIPTION ""
			::= { mbus6B 60 }

mbus6BValue1B		OBJECT-TYPE
			SYNTAX	INTEGER
			ACCESS	read-only
			STATUS	current
	DESCRIPTION ""
			::= { mbus6B 61 }

mbus6BVIF1C		OBJECT-TYPE
			SYNTAX	INTEGER
			ACCESS	read-only
			STATUS	current
	DESCRIPTION ""
			::= { mbus6B 62 }

mbus6BValue1C		OBJECT-TYPE
			SYNTAX	INTEGER
			ACCESS	read-only
			STATUS	current
	DESCRIPTION ""
			::= { mbus6B 63 }

mbus6BVIF1D		OBJECT-TYPE
			SYNTAX	INTEGER
			ACCESS	read-only
			STATUS	current
	DESCRIPTION ""
			::= { mbus6B 64 }

mbus6BValue1D		OBJECT-TYPE
			SYNTAX	INTEGER
			ACCESS	read-only
			STATUS	current
	DESCRIPTION ""
			::= { mbus6B 65 }

mbus6BVIF1E		OBJECT-TYPE
			SYNTAX	INTEGER
			ACCESS	read-only
			STATUS	current
	DESCRIPTION ""
			::= { mbus6B 66 }

mbus6BValue1E		OBJECT-TYPE
			SYNTAX	INTEGER
			ACCESS	read-only
			STATUS	current
	DESCRIPTION ""
			::= { mbus6B 67 }

mbus6BVIF1F		OBJECT-TYPE
			SYNTAX	INTEGER
			ACCESS	read-only
			STATUS	current
	DESCRIPTION ""
			::= { mbus6B 68 }

mbus6BValue1F		OBJECT-TYPE
			SYNTAX	INTEGER
			ACCESS	read-only
			STATUS	current
	DESCRIPTION ""
			::= { mbus6B 69 }

mbus6BVIF20		OBJECT-TYPE
			SYNTAX	INTEGER
			ACCESS	read-only
			STATUS	current
	DESCRIPTION ""
			::= { mbus6B 70 }

mbus6BValue20		OBJECT-TYPE
			SYNTAX	INTEGER
			ACCESS	read-only
			STATUS	current
	DESCRIPTION ""
			::= { mbus6B 71 }

mbus6BVIF21		OBJECT-TYPE
			SYNTAX	INTEGER
			ACCESS	read-only
			STATUS	current
	DESCRIPTION ""
			::= { mbus6B 72 }

mbus6BValue21		OBJECT-TYPE
			SYNTAX	INTEGER
			ACCESS	read-only
			STATUS	current
	DESCRIPTION ""
			::= { mbus6B 73 }

mbus6BVIF22		OBJECT-TYPE
			SYNTAX	INTEGER
			ACCESS	read-only
			STATUS	current
	DESCRIPTION ""
			::= { mbus6B 74 }

mbus6BValue22		OBJECT-TYPE
			SYNTAX	INTEGER
			ACCESS	read-only
			STATUS	current
	DESCRIPTION ""
			::= { mbus6B 75 }

mbus6BVIF23		OBJECT-TYPE
			SYNTAX	INTEGER
			ACCESS	read-only
			STATUS	current
	DESCRIPTION ""
			::= { mbus6B 76 }

mbus6BValue23		OBJECT-TYPE
			SYNTAX	INTEGER
			ACCESS	read-only
			STATUS	current
	DESCRIPTION ""
			::= { mbus6B 77 }

mbus6BVIF24		OBJECT-TYPE
			SYNTAX	INTEGER
			ACCESS	read-only
			STATUS	current
	DESCRIPTION ""
			::= { mbus6B 78 }

mbus6BValue24		OBJECT-TYPE
			SYNTAX	INTEGER
			ACCESS	read-only
			STATUS	current
	DESCRIPTION ""
			::= { mbus6B 79 }

mbus6BVIF25		OBJECT-TYPE
			SYNTAX	INTEGER
			ACCESS	read-only
			STATUS	current
	DESCRIPTION ""
			::= { mbus6B 80 }

mbus6BValue25		OBJECT-TYPE
			SYNTAX	INTEGER
			ACCESS	read-only
			STATUS	current
	DESCRIPTION ""
			::= { mbus6B 81 }

mbus6BVIF26		OBJECT-TYPE
			SYNTAX	INTEGER
			ACCESS	read-only
			STATUS	current
	DESCRIPTION ""
			::= { mbus6B 82 }

mbus6BValue26		OBJECT-TYPE
			SYNTAX	INTEGER
			ACCESS	read-only
			STATUS	current
	DESCRIPTION ""
			::= { mbus6B 83 }

mbus6BVIF27		OBJECT-TYPE
			SYNTAX	INTEGER
			ACCESS	read-only
			STATUS	current
	DESCRIPTION ""
			::= { mbus6B 84 }

mbus6BValue27		OBJECT-TYPE
			SYNTAX	INTEGER
			ACCESS	read-only
			STATUS	current
	DESCRIPTION ""
			::= { mbus6B 85 }

mbus6BVIF28		OBJECT-TYPE
			SYNTAX	INTEGER
			ACCESS	read-only
			STATUS	current
	DESCRIPTION ""
			::= { mbus6B 86 }

mbus6BValue28		OBJECT-TYPE
			SYNTAX	INTEGER
			ACCESS	read-only
			STATUS	current
	DESCRIPTION ""
			::= { mbus6B 87 }

mbus6BVIF29		OBJECT-TYPE
			SYNTAX	INTEGER
			ACCESS	read-only
			STATUS	current
	DESCRIPTION ""
			::= { mbus6B 88 }

mbus6BValue29		OBJECT-TYPE
			SYNTAX	INTEGER
			ACCESS	read-only
			STATUS	current
	DESCRIPTION ""
			::= { mbus6B 89 }

mbus6BVIF2A		OBJECT-TYPE
			SYNTAX	INTEGER
			ACCESS	read-only
			STATUS	current
	DESCRIPTION ""
			::= { mbus6B 90 }

mbus6BValue2A		OBJECT-TYPE
			SYNTAX	INTEGER
			ACCESS	read-only
			STATUS	current
	DESCRIPTION ""
			::= { mbus6B 91 }

mbus6BVIF2B		OBJECT-TYPE
			SYNTAX	INTEGER
			ACCESS	read-only
			STATUS	current
	DESCRIPTION ""
			::= { mbus6B 92 }

mbus6BValue2B		OBJECT-TYPE
			SYNTAX	INTEGER
			ACCESS	read-only
			STATUS	current
	DESCRIPTION ""
			::= { mbus6B 93 }

mbus6BVIF2C		OBJECT-TYPE
			SYNTAX	INTEGER
			ACCESS	read-only
			STATUS	current
	DESCRIPTION ""
			::= { mbus6B 94 }

mbus6BValue2C		OBJECT-TYPE
			SYNTAX	INTEGER
			ACCESS	read-only
			STATUS	current
	DESCRIPTION ""
			::= { mbus6B 95 }

mbus6BVIF2D		OBJECT-TYPE
			SYNTAX	INTEGER
			ACCESS	read-only
			STATUS	current
	DESCRIPTION ""
			::= { mbus6B 96 }

mbus6BValue2D		OBJECT-TYPE
			SYNTAX	INTEGER
			ACCESS	read-only
			STATUS	current
	DESCRIPTION ""
			::= { mbus6B 97 }

mbus6BVIF2E		OBJECT-TYPE
			SYNTAX	INTEGER
			ACCESS	read-only
			STATUS	current
	DESCRIPTION ""
			::= { mbus6B 98 }

mbus6BValue2E		OBJECT-TYPE
			SYNTAX	INTEGER
			ACCESS	read-only
			STATUS	current
	DESCRIPTION ""
			::= { mbus6B 99 }

mbus6BVIF2F		OBJECT-TYPE
			SYNTAX	INTEGER
			ACCESS	read-only
			STATUS	current
	DESCRIPTION ""
			::= { mbus6B 100 }

mbus6BValue2F		OBJECT-TYPE
			SYNTAX	INTEGER
			ACCESS	read-only
			STATUS	current
	DESCRIPTION ""
			::= { mbus6B 101 }

mbus6C			OBJECT IDENTIFIER ::= { mbus 108 }

mbus6CIdNumber		OBJECT-TYPE
			SYNTAX	Gauge
			ACCESS	read-only
			STATUS	current
	DESCRIPTION ""
			::= { mbus6C 1 }

mbus6CManufacturer	OBJECT-TYPE
			SYNTAX	Gauge
			ACCESS	read-only
			STATUS	current
	DESCRIPTION ""
			::= { mbus6C 2 }

mbus6CVersion		OBJECT-TYPE
			SYNTAX	Gauge
			ACCESS	read-only
			STATUS	current
	DESCRIPTION ""
			::= { mbus6C 3 }

mbus6CMedium		OBJECT-TYPE
			SYNTAX	Gauge
			ACCESS	read-only
			STATUS	current
	DESCRIPTION ""
			::= { mbus6C 4 }

mbus6CStatus		OBJECT-TYPE
			SYNTAX	Gauge
			ACCESS	read-only
			STATUS	current
	DESCRIPTION ""
			::= { mbus6C 5 }

mbus6CVIF00		OBJECT-TYPE
			SYNTAX	INTEGER
			ACCESS	read-only
			STATUS	current
	DESCRIPTION ""
			::= { mbus6C 6 }

mbus6CValue00		OBJECT-TYPE
			SYNTAX	INTEGER
			ACCESS	read-only
			STATUS	current
	DESCRIPTION ""
			::= { mbus6C 7 }

mbus6CVIF01		OBJECT-TYPE
			SYNTAX	INTEGER
			ACCESS	read-only
			STATUS	current
	DESCRIPTION ""
			::= { mbus6C 8 }

mbus6CValue01		OBJECT-TYPE
			SYNTAX	INTEGER
			ACCESS	read-only
			STATUS	current
	DESCRIPTION ""
			::= { mbus6C 9 }

mbus6CVIF02		OBJECT-TYPE
			SYNTAX	INTEGER
			ACCESS	read-only
			STATUS	current
	DESCRIPTION ""
			::= { mbus6C 10 }

mbus6CValue02		OBJECT-TYPE
			SYNTAX	INTEGER
			ACCESS	read-only
			STATUS	current
	DESCRIPTION ""
			::= { mbus6C 11 }

mbus6CVIF03		OBJECT-TYPE
			SYNTAX	INTEGER
			ACCESS	read-only
			STATUS	current
	DESCRIPTION ""
			::= { mbus6C 12 }

mbus6CValue03		OBJECT-TYPE
			SYNTAX	INTEGER
			ACCESS	read-only
			STATUS	current
	DESCRIPTION ""
			::= { mbus6C 13 }

mbus6CVIF04		OBJECT-TYPE
			SYNTAX	INTEGER
			ACCESS	read-only
			STATUS	current
	DESCRIPTION ""
			::= { mbus6C 14 }

mbus6CValue04		OBJECT-TYPE
			SYNTAX	INTEGER
			ACCESS	read-only
			STATUS	current
	DESCRIPTION ""
			::= { mbus6C 15 }

mbus6CVIF05		OBJECT-TYPE
			SYNTAX	INTEGER
			ACCESS	read-only
			STATUS	current
	DESCRIPTION ""
			::= { mbus6C 16 }

mbus6CValue05		OBJECT-TYPE
			SYNTAX	INTEGER
			ACCESS	read-only
			STATUS	current
	DESCRIPTION ""
			::= { mbus6C 17 }

mbus6CVIF06		OBJECT-TYPE
			SYNTAX	INTEGER
			ACCESS	read-only
			STATUS	current
	DESCRIPTION ""
			::= { mbus6C 18 }

mbus6CValue06		OBJECT-TYPE
			SYNTAX	INTEGER
			ACCESS	read-only
			STATUS	current
	DESCRIPTION ""
			::= { mbus6C 19 }

mbus6CVIF07		OBJECT-TYPE
			SYNTAX	INTEGER
			ACCESS	read-only
			STATUS	current
	DESCRIPTION ""
			::= { mbus6C 20 }

mbus6CValue07		OBJECT-TYPE
			SYNTAX	INTEGER
			ACCESS	read-only
			STATUS	current
	DESCRIPTION ""
			::= { mbus6C 21 }

mbus6CVIF08		OBJECT-TYPE
			SYNTAX	INTEGER
			ACCESS	read-only
			STATUS	current
	DESCRIPTION ""
			::= { mbus6C 22 }

mbus6CValue08		OBJECT-TYPE
			SYNTAX	INTEGER
			ACCESS	read-only
			STATUS	current
	DESCRIPTION ""
			::= { mbus6C 23 }

mbus6CVIF09		OBJECT-TYPE
			SYNTAX	INTEGER
			ACCESS	read-only
			STATUS	current
	DESCRIPTION ""
			::= { mbus6C 24 }

mbus6CValue09		OBJECT-TYPE
			SYNTAX	INTEGER
			ACCESS	read-only
			STATUS	current
	DESCRIPTION ""
			::= { mbus6C 25 }

mbus6CVIF0A		OBJECT-TYPE
			SYNTAX	INTEGER
			ACCESS	read-only
			STATUS	current
	DESCRIPTION ""
			::= { mbus6C 26 }

mbus6CValue0A		OBJECT-TYPE
			SYNTAX	INTEGER
			ACCESS	read-only
			STATUS	current
	DESCRIPTION ""
			::= { mbus6C 27 }

mbus6CVIF0B		OBJECT-TYPE
			SYNTAX	INTEGER
			ACCESS	read-only
			STATUS	current
	DESCRIPTION ""
			::= { mbus6C 28 }

mbus6CValue0B		OBJECT-TYPE
			SYNTAX	INTEGER
			ACCESS	read-only
			STATUS	current
	DESCRIPTION ""
			::= { mbus6C 29 }

mbus6CVIF0C		OBJECT-TYPE
			SYNTAX	INTEGER
			ACCESS	read-only
			STATUS	current
	DESCRIPTION ""
			::= { mbus6C 30 }

mbus6CValue0C		OBJECT-TYPE
			SYNTAX	INTEGER
			ACCESS	read-only
			STATUS	current
	DESCRIPTION ""
			::= { mbus6C 31 }

mbus6CVIF0D		OBJECT-TYPE
			SYNTAX	INTEGER
			ACCESS	read-only
			STATUS	current
	DESCRIPTION ""
			::= { mbus6C 32 }

mbus6CValue0D		OBJECT-TYPE
			SYNTAX	INTEGER
			ACCESS	read-only
			STATUS	current
	DESCRIPTION ""
			::= { mbus6C 33 }

mbus6CVIF0E		OBJECT-TYPE
			SYNTAX	INTEGER
			ACCESS	read-only
			STATUS	current
	DESCRIPTION ""
			::= { mbus6C 34 }

mbus6CValue0E		OBJECT-TYPE
			SYNTAX	INTEGER
			ACCESS	read-only
			STATUS	current
	DESCRIPTION ""
			::= { mbus6C 35 }

mbus6CVIF0F		OBJECT-TYPE
			SYNTAX	INTEGER
			ACCESS	read-only
			STATUS	current
	DESCRIPTION ""
			::= { mbus6C 36 }

mbus6CValue0F		OBJECT-TYPE
			SYNTAX	INTEGER
			ACCESS	read-only
			STATUS	current
	DESCRIPTION ""
			::= { mbus6C 37 }

mbus6CVIF10		OBJECT-TYPE
			SYNTAX	INTEGER
			ACCESS	read-only
			STATUS	current
	DESCRIPTION ""
			::= { mbus6C 38 }

mbus6CValue10		OBJECT-TYPE
			SYNTAX	INTEGER
			ACCESS	read-only
			STATUS	current
	DESCRIPTION ""
			::= { mbus6C 39 }

mbus6CVIF11		OBJECT-TYPE
			SYNTAX	INTEGER
			ACCESS	read-only
			STATUS	current
	DESCRIPTION ""
			::= { mbus6C 40 }

mbus6CValue11		OBJECT-TYPE
			SYNTAX	INTEGER
			ACCESS	read-only
			STATUS	current
	DESCRIPTION ""
			::= { mbus6C 41 }

mbus6CVIF12		OBJECT-TYPE
			SYNTAX	INTEGER
			ACCESS	read-only
			STATUS	current
	DESCRIPTION ""
			::= { mbus6C 42 }

mbus6CValue12		OBJECT-TYPE
			SYNTAX	INTEGER
			ACCESS	read-only
			STATUS	current
	DESCRIPTION ""
			::= { mbus6C 43 }

mbus6CVIF13		OBJECT-TYPE
			SYNTAX	INTEGER
			ACCESS	read-only
			STATUS	current
	DESCRIPTION ""
			::= { mbus6C 44 }

mbus6CValue13		OBJECT-TYPE
			SYNTAX	INTEGER
			ACCESS	read-only
			STATUS	current
	DESCRIPTION ""
			::= { mbus6C 45 }

mbus6CVIF14		OBJECT-TYPE
			SYNTAX	INTEGER
			ACCESS	read-only
			STATUS	current
	DESCRIPTION ""
			::= { mbus6C 46 }

mbus6CValue14		OBJECT-TYPE
			SYNTAX	INTEGER
			ACCESS	read-only
			STATUS	current
	DESCRIPTION ""
			::= { mbus6C 47 }

mbus6CVIF15		OBJECT-TYPE
			SYNTAX	INTEGER
			ACCESS	read-only
			STATUS	current
	DESCRIPTION ""
			::= { mbus6C 48 }

mbus6CValue15		OBJECT-TYPE
			SYNTAX	INTEGER
			ACCESS	read-only
			STATUS	current
	DESCRIPTION ""
			::= { mbus6C 49 }

mbus6CVIF16		OBJECT-TYPE
			SYNTAX	INTEGER
			ACCESS	read-only
			STATUS	current
	DESCRIPTION ""
			::= { mbus6C 50 }

mbus6CValue16		OBJECT-TYPE
			SYNTAX	INTEGER
			ACCESS	read-only
			STATUS	current
	DESCRIPTION ""
			::= { mbus6C 51 }

mbus6CVIF17		OBJECT-TYPE
			SYNTAX	INTEGER
			ACCESS	read-only
			STATUS	current
	DESCRIPTION ""
			::= { mbus6C 52 }

mbus6CValue17		OBJECT-TYPE
			SYNTAX	INTEGER
			ACCESS	read-only
			STATUS	current
	DESCRIPTION ""
			::= { mbus6C 53 }

mbus6CVIF18		OBJECT-TYPE
			SYNTAX	INTEGER
			ACCESS	read-only
			STATUS	current
	DESCRIPTION ""
			::= { mbus6C 54 }

mbus6CValue18		OBJECT-TYPE
			SYNTAX	INTEGER
			ACCESS	read-only
			STATUS	current
	DESCRIPTION ""
			::= { mbus6C 55 }

mbus6CVIF19		OBJECT-TYPE
			SYNTAX	INTEGER
			ACCESS	read-only
			STATUS	current
	DESCRIPTION ""
			::= { mbus6C 56 }

mbus6CValue19		OBJECT-TYPE
			SYNTAX	INTEGER
			ACCESS	read-only
			STATUS	current
	DESCRIPTION ""
			::= { mbus6C 57 }

mbus6CVIF1A		OBJECT-TYPE
			SYNTAX	INTEGER
			ACCESS	read-only
			STATUS	current
	DESCRIPTION ""
			::= { mbus6C 58 }

mbus6CValue1A		OBJECT-TYPE
			SYNTAX	INTEGER
			ACCESS	read-only
			STATUS	current
	DESCRIPTION ""
			::= { mbus6C 59 }

mbus6CVIF1B		OBJECT-TYPE
			SYNTAX	INTEGER
			ACCESS	read-only
			STATUS	current
	DESCRIPTION ""
			::= { mbus6C 60 }

mbus6CValue1B		OBJECT-TYPE
			SYNTAX	INTEGER
			ACCESS	read-only
			STATUS	current
	DESCRIPTION ""
			::= { mbus6C 61 }

mbus6CVIF1C		OBJECT-TYPE
			SYNTAX	INTEGER
			ACCESS	read-only
			STATUS	current
	DESCRIPTION ""
			::= { mbus6C 62 }

mbus6CValue1C		OBJECT-TYPE
			SYNTAX	INTEGER
			ACCESS	read-only
			STATUS	current
	DESCRIPTION ""
			::= { mbus6C 63 }

mbus6CVIF1D		OBJECT-TYPE
			SYNTAX	INTEGER
			ACCESS	read-only
			STATUS	current
	DESCRIPTION ""
			::= { mbus6C 64 }

mbus6CValue1D		OBJECT-TYPE
			SYNTAX	INTEGER
			ACCESS	read-only
			STATUS	current
	DESCRIPTION ""
			::= { mbus6C 65 }

mbus6CVIF1E		OBJECT-TYPE
			SYNTAX	INTEGER
			ACCESS	read-only
			STATUS	current
	DESCRIPTION ""
			::= { mbus6C 66 }

mbus6CValue1E		OBJECT-TYPE
			SYNTAX	INTEGER
			ACCESS	read-only
			STATUS	current
	DESCRIPTION ""
			::= { mbus6C 67 }

mbus6CVIF1F		OBJECT-TYPE
			SYNTAX	INTEGER
			ACCESS	read-only
			STATUS	current
	DESCRIPTION ""
			::= { mbus6C 68 }

mbus6CValue1F		OBJECT-TYPE
			SYNTAX	INTEGER
			ACCESS	read-only
			STATUS	current
	DESCRIPTION ""
			::= { mbus6C 69 }

mbus6CVIF20		OBJECT-TYPE
			SYNTAX	INTEGER
			ACCESS	read-only
			STATUS	current
	DESCRIPTION ""
			::= { mbus6C 70 }

mbus6CValue20		OBJECT-TYPE
			SYNTAX	INTEGER
			ACCESS	read-only
			STATUS	current
	DESCRIPTION ""
			::= { mbus6C 71 }

mbus6CVIF21		OBJECT-TYPE
			SYNTAX	INTEGER
			ACCESS	read-only
			STATUS	current
	DESCRIPTION ""
			::= { mbus6C 72 }

mbus6CValue21		OBJECT-TYPE
			SYNTAX	INTEGER
			ACCESS	read-only
			STATUS	current
	DESCRIPTION ""
			::= { mbus6C 73 }

mbus6CVIF22		OBJECT-TYPE
			SYNTAX	INTEGER
			ACCESS	read-only
			STATUS	current
	DESCRIPTION ""
			::= { mbus6C 74 }

mbus6CValue22		OBJECT-TYPE
			SYNTAX	INTEGER
			ACCESS	read-only
			STATUS	current
	DESCRIPTION ""
			::= { mbus6C 75 }

mbus6CVIF23		OBJECT-TYPE
			SYNTAX	INTEGER
			ACCESS	read-only
			STATUS	current
	DESCRIPTION ""
			::= { mbus6C 76 }

mbus6CValue23		OBJECT-TYPE
			SYNTAX	INTEGER
			ACCESS	read-only
			STATUS	current
	DESCRIPTION ""
			::= { mbus6C 77 }

mbus6CVIF24		OBJECT-TYPE
			SYNTAX	INTEGER
			ACCESS	read-only
			STATUS	current
	DESCRIPTION ""
			::= { mbus6C 78 }

mbus6CValue24		OBJECT-TYPE
			SYNTAX	INTEGER
			ACCESS	read-only
			STATUS	current
	DESCRIPTION ""
			::= { mbus6C 79 }

mbus6CVIF25		OBJECT-TYPE
			SYNTAX	INTEGER
			ACCESS	read-only
			STATUS	current
	DESCRIPTION ""
			::= { mbus6C 80 }

mbus6CValue25		OBJECT-TYPE
			SYNTAX	INTEGER
			ACCESS	read-only
			STATUS	current
	DESCRIPTION ""
			::= { mbus6C 81 }

mbus6CVIF26		OBJECT-TYPE
			SYNTAX	INTEGER
			ACCESS	read-only
			STATUS	current
	DESCRIPTION ""
			::= { mbus6C 82 }

mbus6CValue26		OBJECT-TYPE
			SYNTAX	INTEGER
			ACCESS	read-only
			STATUS	current
	DESCRIPTION ""
			::= { mbus6C 83 }

mbus6CVIF27		OBJECT-TYPE
			SYNTAX	INTEGER
			ACCESS	read-only
			STATUS	current
	DESCRIPTION ""
			::= { mbus6C 84 }

mbus6CValue27		OBJECT-TYPE
			SYNTAX	INTEGER
			ACCESS	read-only
			STATUS	current
	DESCRIPTION ""
			::= { mbus6C 85 }

mbus6CVIF28		OBJECT-TYPE
			SYNTAX	INTEGER
			ACCESS	read-only
			STATUS	current
	DESCRIPTION ""
			::= { mbus6C 86 }

mbus6CValue28		OBJECT-TYPE
			SYNTAX	INTEGER
			ACCESS	read-only
			STATUS	current
	DESCRIPTION ""
			::= { mbus6C 87 }

mbus6CVIF29		OBJECT-TYPE
			SYNTAX	INTEGER
			ACCESS	read-only
			STATUS	current
	DESCRIPTION ""
			::= { mbus6C 88 }

mbus6CValue29		OBJECT-TYPE
			SYNTAX	INTEGER
			ACCESS	read-only
			STATUS	current
	DESCRIPTION ""
			::= { mbus6C 89 }

mbus6CVIF2A		OBJECT-TYPE
			SYNTAX	INTEGER
			ACCESS	read-only
			STATUS	current
	DESCRIPTION ""
			::= { mbus6C 90 }

mbus6CValue2A		OBJECT-TYPE
			SYNTAX	INTEGER
			ACCESS	read-only
			STATUS	current
	DESCRIPTION ""
			::= { mbus6C 91 }

mbus6CVIF2B		OBJECT-TYPE
			SYNTAX	INTEGER
			ACCESS	read-only
			STATUS	current
	DESCRIPTION ""
			::= { mbus6C 92 }

mbus6CValue2B		OBJECT-TYPE
			SYNTAX	INTEGER
			ACCESS	read-only
			STATUS	current
	DESCRIPTION ""
			::= { mbus6C 93 }

mbus6CVIF2C		OBJECT-TYPE
			SYNTAX	INTEGER
			ACCESS	read-only
			STATUS	current
	DESCRIPTION ""
			::= { mbus6C 94 }

mbus6CValue2C		OBJECT-TYPE
			SYNTAX	INTEGER
			ACCESS	read-only
			STATUS	current
	DESCRIPTION ""
			::= { mbus6C 95 }

mbus6CVIF2D		OBJECT-TYPE
			SYNTAX	INTEGER
			ACCESS	read-only
			STATUS	current
	DESCRIPTION ""
			::= { mbus6C 96 }

mbus6CValue2D		OBJECT-TYPE
			SYNTAX	INTEGER
			ACCESS	read-only
			STATUS	current
	DESCRIPTION ""
			::= { mbus6C 97 }

mbus6CVIF2E		OBJECT-TYPE
			SYNTAX	INTEGER
			ACCESS	read-only
			STATUS	current
	DESCRIPTION ""
			::= { mbus6C 98 }

mbus6CValue2E		OBJECT-TYPE
			SYNTAX	INTEGER
			ACCESS	read-only
			STATUS	current
	DESCRIPTION ""
			::= { mbus6C 99 }

mbus6CVIF2F		OBJECT-TYPE
			SYNTAX	INTEGER
			ACCESS	read-only
			STATUS	current
	DESCRIPTION ""
			::= { mbus6C 100 }

mbus6CValue2F		OBJECT-TYPE
			SYNTAX	INTEGER
			ACCESS	read-only
			STATUS	current
	DESCRIPTION ""
			::= { mbus6C 101 }

mbus6D			OBJECT IDENTIFIER ::= { mbus 109 }

mbus6DIdNumber		OBJECT-TYPE
			SYNTAX	Gauge
			ACCESS	read-only
			STATUS	current
	DESCRIPTION ""
			::= { mbus6D 1 }

mbus6DManufacturer	OBJECT-TYPE
			SYNTAX	Gauge
			ACCESS	read-only
			STATUS	current
	DESCRIPTION ""
			::= { mbus6D 2 }

mbus6DVersion		OBJECT-TYPE
			SYNTAX	Gauge
			ACCESS	read-only
			STATUS	current
	DESCRIPTION ""
			::= { mbus6D 3 }

mbus6DMedium		OBJECT-TYPE
			SYNTAX	Gauge
			ACCESS	read-only
			STATUS	current
	DESCRIPTION ""
			::= { mbus6D 4 }

mbus6DStatus		OBJECT-TYPE
			SYNTAX	Gauge
			ACCESS	read-only
			STATUS	current
	DESCRIPTION ""
			::= { mbus6D 5 }

mbus6DVIF00		OBJECT-TYPE
			SYNTAX	INTEGER
			ACCESS	read-only
			STATUS	current
	DESCRIPTION ""
			::= { mbus6D 6 }

mbus6DValue00		OBJECT-TYPE
			SYNTAX	INTEGER
			ACCESS	read-only
			STATUS	current
	DESCRIPTION ""
			::= { mbus6D 7 }

mbus6DVIF01		OBJECT-TYPE
			SYNTAX	INTEGER
			ACCESS	read-only
			STATUS	current
	DESCRIPTION ""
			::= { mbus6D 8 }

mbus6DValue01		OBJECT-TYPE
			SYNTAX	INTEGER
			ACCESS	read-only
			STATUS	current
	DESCRIPTION ""
			::= { mbus6D 9 }

mbus6DVIF02		OBJECT-TYPE
			SYNTAX	INTEGER
			ACCESS	read-only
			STATUS	current
	DESCRIPTION ""
			::= { mbus6D 10 }

mbus6DValue02		OBJECT-TYPE
			SYNTAX	INTEGER
			ACCESS	read-only
			STATUS	current
	DESCRIPTION ""
			::= { mbus6D 11 }

mbus6DVIF03		OBJECT-TYPE
			SYNTAX	INTEGER
			ACCESS	read-only
			STATUS	current
	DESCRIPTION ""
			::= { mbus6D 12 }

mbus6DValue03		OBJECT-TYPE
			SYNTAX	INTEGER
			ACCESS	read-only
			STATUS	current
	DESCRIPTION ""
			::= { mbus6D 13 }

mbus6DVIF04		OBJECT-TYPE
			SYNTAX	INTEGER
			ACCESS	read-only
			STATUS	current
	DESCRIPTION ""
			::= { mbus6D 14 }

mbus6DValue04		OBJECT-TYPE
			SYNTAX	INTEGER
			ACCESS	read-only
			STATUS	current
	DESCRIPTION ""
			::= { mbus6D 15 }

mbus6DVIF05		OBJECT-TYPE
			SYNTAX	INTEGER
			ACCESS	read-only
			STATUS	current
	DESCRIPTION ""
			::= { mbus6D 16 }

mbus6DValue05		OBJECT-TYPE
			SYNTAX	INTEGER
			ACCESS	read-only
			STATUS	current
	DESCRIPTION ""
			::= { mbus6D 17 }

mbus6DVIF06		OBJECT-TYPE
			SYNTAX	INTEGER
			ACCESS	read-only
			STATUS	current
	DESCRIPTION ""
			::= { mbus6D 18 }

mbus6DValue06		OBJECT-TYPE
			SYNTAX	INTEGER
			ACCESS	read-only
			STATUS	current
	DESCRIPTION ""
			::= { mbus6D 19 }

mbus6DVIF07		OBJECT-TYPE
			SYNTAX	INTEGER
			ACCESS	read-only
			STATUS	current
	DESCRIPTION ""
			::= { mbus6D 20 }

mbus6DValue07		OBJECT-TYPE
			SYNTAX	INTEGER
			ACCESS	read-only
			STATUS	current
	DESCRIPTION ""
			::= { mbus6D 21 }

mbus6DVIF08		OBJECT-TYPE
			SYNTAX	INTEGER
			ACCESS	read-only
			STATUS	current
	DESCRIPTION ""
			::= { mbus6D 22 }

mbus6DValue08		OBJECT-TYPE
			SYNTAX	INTEGER
			ACCESS	read-only
			STATUS	current
	DESCRIPTION ""
			::= { mbus6D 23 }

mbus6DVIF09		OBJECT-TYPE
			SYNTAX	INTEGER
			ACCESS	read-only
			STATUS	current
	DESCRIPTION ""
			::= { mbus6D 24 }

mbus6DValue09		OBJECT-TYPE
			SYNTAX	INTEGER
			ACCESS	read-only
			STATUS	current
	DESCRIPTION ""
			::= { mbus6D 25 }

mbus6DVIF0A		OBJECT-TYPE
			SYNTAX	INTEGER
			ACCESS	read-only
			STATUS	current
	DESCRIPTION ""
			::= { mbus6D 26 }

mbus6DValue0A		OBJECT-TYPE
			SYNTAX	INTEGER
			ACCESS	read-only
			STATUS	current
	DESCRIPTION ""
			::= { mbus6D 27 }

mbus6DVIF0B		OBJECT-TYPE
			SYNTAX	INTEGER
			ACCESS	read-only
			STATUS	current
	DESCRIPTION ""
			::= { mbus6D 28 }

mbus6DValue0B		OBJECT-TYPE
			SYNTAX	INTEGER
			ACCESS	read-only
			STATUS	current
	DESCRIPTION ""
			::= { mbus6D 29 }

mbus6DVIF0C		OBJECT-TYPE
			SYNTAX	INTEGER
			ACCESS	read-only
			STATUS	current
	DESCRIPTION ""
			::= { mbus6D 30 }

mbus6DValue0C		OBJECT-TYPE
			SYNTAX	INTEGER
			ACCESS	read-only
			STATUS	current
	DESCRIPTION ""
			::= { mbus6D 31 }

mbus6DVIF0D		OBJECT-TYPE
			SYNTAX	INTEGER
			ACCESS	read-only
			STATUS	current
	DESCRIPTION ""
			::= { mbus6D 32 }

mbus6DValue0D		OBJECT-TYPE
			SYNTAX	INTEGER
			ACCESS	read-only
			STATUS	current
	DESCRIPTION ""
			::= { mbus6D 33 }

mbus6DVIF0E		OBJECT-TYPE
			SYNTAX	INTEGER
			ACCESS	read-only
			STATUS	current
	DESCRIPTION ""
			::= { mbus6D 34 }

mbus6DValue0E		OBJECT-TYPE
			SYNTAX	INTEGER
			ACCESS	read-only
			STATUS	current
	DESCRIPTION ""
			::= { mbus6D 35 }

mbus6DVIF0F		OBJECT-TYPE
			SYNTAX	INTEGER
			ACCESS	read-only
			STATUS	current
	DESCRIPTION ""
			::= { mbus6D 36 }

mbus6DValue0F		OBJECT-TYPE
			SYNTAX	INTEGER
			ACCESS	read-only
			STATUS	current
	DESCRIPTION ""
			::= { mbus6D 37 }

mbus6DVIF10		OBJECT-TYPE
			SYNTAX	INTEGER
			ACCESS	read-only
			STATUS	current
	DESCRIPTION ""
			::= { mbus6D 38 }

mbus6DValue10		OBJECT-TYPE
			SYNTAX	INTEGER
			ACCESS	read-only
			STATUS	current
	DESCRIPTION ""
			::= { mbus6D 39 }

mbus6DVIF11		OBJECT-TYPE
			SYNTAX	INTEGER
			ACCESS	read-only
			STATUS	current
	DESCRIPTION ""
			::= { mbus6D 40 }

mbus6DValue11		OBJECT-TYPE
			SYNTAX	INTEGER
			ACCESS	read-only
			STATUS	current
	DESCRIPTION ""
			::= { mbus6D 41 }

mbus6DVIF12		OBJECT-TYPE
			SYNTAX	INTEGER
			ACCESS	read-only
			STATUS	current
	DESCRIPTION ""
			::= { mbus6D 42 }

mbus6DValue12		OBJECT-TYPE
			SYNTAX	INTEGER
			ACCESS	read-only
			STATUS	current
	DESCRIPTION ""
			::= { mbus6D 43 }

mbus6DVIF13		OBJECT-TYPE
			SYNTAX	INTEGER
			ACCESS	read-only
			STATUS	current
	DESCRIPTION ""
			::= { mbus6D 44 }

mbus6DValue13		OBJECT-TYPE
			SYNTAX	INTEGER
			ACCESS	read-only
			STATUS	current
	DESCRIPTION ""
			::= { mbus6D 45 }

mbus6DVIF14		OBJECT-TYPE
			SYNTAX	INTEGER
			ACCESS	read-only
			STATUS	current
	DESCRIPTION ""
			::= { mbus6D 46 }

mbus6DValue14		OBJECT-TYPE
			SYNTAX	INTEGER
			ACCESS	read-only
			STATUS	current
	DESCRIPTION ""
			::= { mbus6D 47 }

mbus6DVIF15		OBJECT-TYPE
			SYNTAX	INTEGER
			ACCESS	read-only
			STATUS	current
	DESCRIPTION ""
			::= { mbus6D 48 }

mbus6DValue15		OBJECT-TYPE
			SYNTAX	INTEGER
			ACCESS	read-only
			STATUS	current
	DESCRIPTION ""
			::= { mbus6D 49 }

mbus6DVIF16		OBJECT-TYPE
			SYNTAX	INTEGER
			ACCESS	read-only
			STATUS	current
	DESCRIPTION ""
			::= { mbus6D 50 }

mbus6DValue16		OBJECT-TYPE
			SYNTAX	INTEGER
			ACCESS	read-only
			STATUS	current
	DESCRIPTION ""
			::= { mbus6D 51 }

mbus6DVIF17		OBJECT-TYPE
			SYNTAX	INTEGER
			ACCESS	read-only
			STATUS	current
	DESCRIPTION ""
			::= { mbus6D 52 }

mbus6DValue17		OBJECT-TYPE
			SYNTAX	INTEGER
			ACCESS	read-only
			STATUS	current
	DESCRIPTION ""
			::= { mbus6D 53 }

mbus6DVIF18		OBJECT-TYPE
			SYNTAX	INTEGER
			ACCESS	read-only
			STATUS	current
	DESCRIPTION ""
			::= { mbus6D 54 }

mbus6DValue18		OBJECT-TYPE
			SYNTAX	INTEGER
			ACCESS	read-only
			STATUS	current
	DESCRIPTION ""
			::= { mbus6D 55 }

mbus6DVIF19		OBJECT-TYPE
			SYNTAX	INTEGER
			ACCESS	read-only
			STATUS	current
	DESCRIPTION ""
			::= { mbus6D 56 }

mbus6DValue19		OBJECT-TYPE
			SYNTAX	INTEGER
			ACCESS	read-only
			STATUS	current
	DESCRIPTION ""
			::= { mbus6D 57 }

mbus6DVIF1A		OBJECT-TYPE
			SYNTAX	INTEGER
			ACCESS	read-only
			STATUS	current
	DESCRIPTION ""
			::= { mbus6D 58 }

mbus6DValue1A		OBJECT-TYPE
			SYNTAX	INTEGER
			ACCESS	read-only
			STATUS	current
	DESCRIPTION ""
			::= { mbus6D 59 }

mbus6DVIF1B		OBJECT-TYPE
			SYNTAX	INTEGER
			ACCESS	read-only
			STATUS	current
	DESCRIPTION ""
			::= { mbus6D 60 }

mbus6DValue1B		OBJECT-TYPE
			SYNTAX	INTEGER
			ACCESS	read-only
			STATUS	current
	DESCRIPTION ""
			::= { mbus6D 61 }

mbus6DVIF1C		OBJECT-TYPE
			SYNTAX	INTEGER
			ACCESS	read-only
			STATUS	current
	DESCRIPTION ""
			::= { mbus6D 62 }

mbus6DValue1C		OBJECT-TYPE
			SYNTAX	INTEGER
			ACCESS	read-only
			STATUS	current
	DESCRIPTION ""
			::= { mbus6D 63 }

mbus6DVIF1D		OBJECT-TYPE
			SYNTAX	INTEGER
			ACCESS	read-only
			STATUS	current
	DESCRIPTION ""
			::= { mbus6D 64 }

mbus6DValue1D		OBJECT-TYPE
			SYNTAX	INTEGER
			ACCESS	read-only
			STATUS	current
	DESCRIPTION ""
			::= { mbus6D 65 }

mbus6DVIF1E		OBJECT-TYPE
			SYNTAX	INTEGER
			ACCESS	read-only
			STATUS	current
	DESCRIPTION ""
			::= { mbus6D 66 }

mbus6DValue1E		OBJECT-TYPE
			SYNTAX	INTEGER
			ACCESS	read-only
			STATUS	current
	DESCRIPTION ""
			::= { mbus6D 67 }

mbus6DVIF1F		OBJECT-TYPE
			SYNTAX	INTEGER
			ACCESS	read-only
			STATUS	current
	DESCRIPTION ""
			::= { mbus6D 68 }

mbus6DValue1F		OBJECT-TYPE
			SYNTAX	INTEGER
			ACCESS	read-only
			STATUS	current
	DESCRIPTION ""
			::= { mbus6D 69 }

mbus6DVIF20		OBJECT-TYPE
			SYNTAX	INTEGER
			ACCESS	read-only
			STATUS	current
	DESCRIPTION ""
			::= { mbus6D 70 }

mbus6DValue20		OBJECT-TYPE
			SYNTAX	INTEGER
			ACCESS	read-only
			STATUS	current
	DESCRIPTION ""
			::= { mbus6D 71 }

mbus6DVIF21		OBJECT-TYPE
			SYNTAX	INTEGER
			ACCESS	read-only
			STATUS	current
	DESCRIPTION ""
			::= { mbus6D 72 }

mbus6DValue21		OBJECT-TYPE
			SYNTAX	INTEGER
			ACCESS	read-only
			STATUS	current
	DESCRIPTION ""
			::= { mbus6D 73 }

mbus6DVIF22		OBJECT-TYPE
			SYNTAX	INTEGER
			ACCESS	read-only
			STATUS	current
	DESCRIPTION ""
			::= { mbus6D 74 }

mbus6DValue22		OBJECT-TYPE
			SYNTAX	INTEGER
			ACCESS	read-only
			STATUS	current
	DESCRIPTION ""
			::= { mbus6D 75 }

mbus6DVIF23		OBJECT-TYPE
			SYNTAX	INTEGER
			ACCESS	read-only
			STATUS	current
	DESCRIPTION ""
			::= { mbus6D 76 }

mbus6DValue23		OBJECT-TYPE
			SYNTAX	INTEGER
			ACCESS	read-only
			STATUS	current
	DESCRIPTION ""
			::= { mbus6D 77 }

mbus6DVIF24		OBJECT-TYPE
			SYNTAX	INTEGER
			ACCESS	read-only
			STATUS	current
	DESCRIPTION ""
			::= { mbus6D 78 }

mbus6DValue24		OBJECT-TYPE
			SYNTAX	INTEGER
			ACCESS	read-only
			STATUS	current
	DESCRIPTION ""
			::= { mbus6D 79 }

mbus6DVIF25		OBJECT-TYPE
			SYNTAX	INTEGER
			ACCESS	read-only
			STATUS	current
	DESCRIPTION ""
			::= { mbus6D 80 }

mbus6DValue25		OBJECT-TYPE
			SYNTAX	INTEGER
			ACCESS	read-only
			STATUS	current
	DESCRIPTION ""
			::= { mbus6D 81 }

mbus6DVIF26		OBJECT-TYPE
			SYNTAX	INTEGER
			ACCESS	read-only
			STATUS	current
	DESCRIPTION ""
			::= { mbus6D 82 }

mbus6DValue26		OBJECT-TYPE
			SYNTAX	INTEGER
			ACCESS	read-only
			STATUS	current
	DESCRIPTION ""
			::= { mbus6D 83 }

mbus6DVIF27		OBJECT-TYPE
			SYNTAX	INTEGER
			ACCESS	read-only
			STATUS	current
	DESCRIPTION ""
			::= { mbus6D 84 }

mbus6DValue27		OBJECT-TYPE
			SYNTAX	INTEGER
			ACCESS	read-only
			STATUS	current
	DESCRIPTION ""
			::= { mbus6D 85 }

mbus6DVIF28		OBJECT-TYPE
			SYNTAX	INTEGER
			ACCESS	read-only
			STATUS	current
	DESCRIPTION ""
			::= { mbus6D 86 }

mbus6DValue28		OBJECT-TYPE
			SYNTAX	INTEGER
			ACCESS	read-only
			STATUS	current
	DESCRIPTION ""
			::= { mbus6D 87 }

mbus6DVIF29		OBJECT-TYPE
			SYNTAX	INTEGER
			ACCESS	read-only
			STATUS	current
	DESCRIPTION ""
			::= { mbus6D 88 }

mbus6DValue29		OBJECT-TYPE
			SYNTAX	INTEGER
			ACCESS	read-only
			STATUS	current
	DESCRIPTION ""
			::= { mbus6D 89 }

mbus6DVIF2A		OBJECT-TYPE
			SYNTAX	INTEGER
			ACCESS	read-only
			STATUS	current
	DESCRIPTION ""
			::= { mbus6D 90 }

mbus6DValue2A		OBJECT-TYPE
			SYNTAX	INTEGER
			ACCESS	read-only
			STATUS	current
	DESCRIPTION ""
			::= { mbus6D 91 }

mbus6DVIF2B		OBJECT-TYPE
			SYNTAX	INTEGER
			ACCESS	read-only
			STATUS	current
	DESCRIPTION ""
			::= { mbus6D 92 }

mbus6DValue2B		OBJECT-TYPE
			SYNTAX	INTEGER
			ACCESS	read-only
			STATUS	current
	DESCRIPTION ""
			::= { mbus6D 93 }

mbus6DVIF2C		OBJECT-TYPE
			SYNTAX	INTEGER
			ACCESS	read-only
			STATUS	current
	DESCRIPTION ""
			::= { mbus6D 94 }

mbus6DValue2C		OBJECT-TYPE
			SYNTAX	INTEGER
			ACCESS	read-only
			STATUS	current
	DESCRIPTION ""
			::= { mbus6D 95 }

mbus6DVIF2D		OBJECT-TYPE
			SYNTAX	INTEGER
			ACCESS	read-only
			STATUS	current
	DESCRIPTION ""
			::= { mbus6D 96 }

mbus6DValue2D		OBJECT-TYPE
			SYNTAX	INTEGER
			ACCESS	read-only
			STATUS	current
	DESCRIPTION ""
			::= { mbus6D 97 }

mbus6DVIF2E		OBJECT-TYPE
			SYNTAX	INTEGER
			ACCESS	read-only
			STATUS	current
	DESCRIPTION ""
			::= { mbus6D 98 }

mbus6DValue2E		OBJECT-TYPE
			SYNTAX	INTEGER
			ACCESS	read-only
			STATUS	current
	DESCRIPTION ""
			::= { mbus6D 99 }

mbus6DVIF2F		OBJECT-TYPE
			SYNTAX	INTEGER
			ACCESS	read-only
			STATUS	current
	DESCRIPTION ""
			::= { mbus6D 100 }

mbus6DValue2F		OBJECT-TYPE
			SYNTAX	INTEGER
			ACCESS	read-only
			STATUS	current
	DESCRIPTION ""
			::= { mbus6D 101 }

mbus6E			OBJECT IDENTIFIER ::= { mbus 110 }

mbus6EIdNumber		OBJECT-TYPE
			SYNTAX	Gauge
			ACCESS	read-only
			STATUS	current
	DESCRIPTION ""
			::= { mbus6E 1 }

mbus6EManufacturer	OBJECT-TYPE
			SYNTAX	Gauge
			ACCESS	read-only
			STATUS	current
	DESCRIPTION ""
			::= { mbus6E 2 }

mbus6EVersion		OBJECT-TYPE
			SYNTAX	Gauge
			ACCESS	read-only
			STATUS	current
	DESCRIPTION ""
			::= { mbus6E 3 }

mbus6EMedium		OBJECT-TYPE
			SYNTAX	Gauge
			ACCESS	read-only
			STATUS	current
	DESCRIPTION ""
			::= { mbus6E 4 }

mbus6EStatus		OBJECT-TYPE
			SYNTAX	Gauge
			ACCESS	read-only
			STATUS	current
	DESCRIPTION ""
			::= { mbus6E 5 }

mbus6EVIF00		OBJECT-TYPE
			SYNTAX	INTEGER
			ACCESS	read-only
			STATUS	current
	DESCRIPTION ""
			::= { mbus6E 6 }

mbus6EValue00		OBJECT-TYPE
			SYNTAX	INTEGER
			ACCESS	read-only
			STATUS	current
	DESCRIPTION ""
			::= { mbus6E 7 }

mbus6EVIF01		OBJECT-TYPE
			SYNTAX	INTEGER
			ACCESS	read-only
			STATUS	current
	DESCRIPTION ""
			::= { mbus6E 8 }

mbus6EValue01		OBJECT-TYPE
			SYNTAX	INTEGER
			ACCESS	read-only
			STATUS	current
	DESCRIPTION ""
			::= { mbus6E 9 }

mbus6EVIF02		OBJECT-TYPE
			SYNTAX	INTEGER
			ACCESS	read-only
			STATUS	current
	DESCRIPTION ""
			::= { mbus6E 10 }

mbus6EValue02		OBJECT-TYPE
			SYNTAX	INTEGER
			ACCESS	read-only
			STATUS	current
	DESCRIPTION ""
			::= { mbus6E 11 }

mbus6EVIF03		OBJECT-TYPE
			SYNTAX	INTEGER
			ACCESS	read-only
			STATUS	current
	DESCRIPTION ""
			::= { mbus6E 12 }

mbus6EValue03		OBJECT-TYPE
			SYNTAX	INTEGER
			ACCESS	read-only
			STATUS	current
	DESCRIPTION ""
			::= { mbus6E 13 }

mbus6EVIF04		OBJECT-TYPE
			SYNTAX	INTEGER
			ACCESS	read-only
			STATUS	current
	DESCRIPTION ""
			::= { mbus6E 14 }

mbus6EValue04		OBJECT-TYPE
			SYNTAX	INTEGER
			ACCESS	read-only
			STATUS	current
	DESCRIPTION ""
			::= { mbus6E 15 }

mbus6EVIF05		OBJECT-TYPE
			SYNTAX	INTEGER
			ACCESS	read-only
			STATUS	current
	DESCRIPTION ""
			::= { mbus6E 16 }

mbus6EValue05		OBJECT-TYPE
			SYNTAX	INTEGER
			ACCESS	read-only
			STATUS	current
	DESCRIPTION ""
			::= { mbus6E 17 }

mbus6EVIF06		OBJECT-TYPE
			SYNTAX	INTEGER
			ACCESS	read-only
			STATUS	current
	DESCRIPTION ""
			::= { mbus6E 18 }

mbus6EValue06		OBJECT-TYPE
			SYNTAX	INTEGER
			ACCESS	read-only
			STATUS	current
	DESCRIPTION ""
			::= { mbus6E 19 }

mbus6EVIF07		OBJECT-TYPE
			SYNTAX	INTEGER
			ACCESS	read-only
			STATUS	current
	DESCRIPTION ""
			::= { mbus6E 20 }

mbus6EValue07		OBJECT-TYPE
			SYNTAX	INTEGER
			ACCESS	read-only
			STATUS	current
	DESCRIPTION ""
			::= { mbus6E 21 }

mbus6EVIF08		OBJECT-TYPE
			SYNTAX	INTEGER
			ACCESS	read-only
			STATUS	current
	DESCRIPTION ""
			::= { mbus6E 22 }

mbus6EValue08		OBJECT-TYPE
			SYNTAX	INTEGER
			ACCESS	read-only
			STATUS	current
	DESCRIPTION ""
			::= { mbus6E 23 }

mbus6EVIF09		OBJECT-TYPE
			SYNTAX	INTEGER
			ACCESS	read-only
			STATUS	current
	DESCRIPTION ""
			::= { mbus6E 24 }

mbus6EValue09		OBJECT-TYPE
			SYNTAX	INTEGER
			ACCESS	read-only
			STATUS	current
	DESCRIPTION ""
			::= { mbus6E 25 }

mbus6EVIF0A		OBJECT-TYPE
			SYNTAX	INTEGER
			ACCESS	read-only
			STATUS	current
	DESCRIPTION ""
			::= { mbus6E 26 }

mbus6EValue0A		OBJECT-TYPE
			SYNTAX	INTEGER
			ACCESS	read-only
			STATUS	current
	DESCRIPTION ""
			::= { mbus6E 27 }

mbus6EVIF0B		OBJECT-TYPE
			SYNTAX	INTEGER
			ACCESS	read-only
			STATUS	current
	DESCRIPTION ""
			::= { mbus6E 28 }

mbus6EValue0B		OBJECT-TYPE
			SYNTAX	INTEGER
			ACCESS	read-only
			STATUS	current
	DESCRIPTION ""
			::= { mbus6E 29 }

mbus6EVIF0C		OBJECT-TYPE
			SYNTAX	INTEGER
			ACCESS	read-only
			STATUS	current
	DESCRIPTION ""
			::= { mbus6E 30 }

mbus6EValue0C		OBJECT-TYPE
			SYNTAX	INTEGER
			ACCESS	read-only
			STATUS	current
	DESCRIPTION ""
			::= { mbus6E 31 }

mbus6EVIF0D		OBJECT-TYPE
			SYNTAX	INTEGER
			ACCESS	read-only
			STATUS	current
	DESCRIPTION ""
			::= { mbus6E 32 }

mbus6EValue0D		OBJECT-TYPE
			SYNTAX	INTEGER
			ACCESS	read-only
			STATUS	current
	DESCRIPTION ""
			::= { mbus6E 33 }

mbus6EVIF0E		OBJECT-TYPE
			SYNTAX	INTEGER
			ACCESS	read-only
			STATUS	current
	DESCRIPTION ""
			::= { mbus6E 34 }

mbus6EValue0E		OBJECT-TYPE
			SYNTAX	INTEGER
			ACCESS	read-only
			STATUS	current
	DESCRIPTION ""
			::= { mbus6E 35 }

mbus6EVIF0F		OBJECT-TYPE
			SYNTAX	INTEGER
			ACCESS	read-only
			STATUS	current
	DESCRIPTION ""
			::= { mbus6E 36 }

mbus6EValue0F		OBJECT-TYPE
			SYNTAX	INTEGER
			ACCESS	read-only
			STATUS	current
	DESCRIPTION ""
			::= { mbus6E 37 }

mbus6EVIF10		OBJECT-TYPE
			SYNTAX	INTEGER
			ACCESS	read-only
			STATUS	current
	DESCRIPTION ""
			::= { mbus6E 38 }

mbus6EValue10		OBJECT-TYPE
			SYNTAX	INTEGER
			ACCESS	read-only
			STATUS	current
	DESCRIPTION ""
			::= { mbus6E 39 }

mbus6EVIF11		OBJECT-TYPE
			SYNTAX	INTEGER
			ACCESS	read-only
			STATUS	current
	DESCRIPTION ""
			::= { mbus6E 40 }

mbus6EValue11		OBJECT-TYPE
			SYNTAX	INTEGER
			ACCESS	read-only
			STATUS	current
	DESCRIPTION ""
			::= { mbus6E 41 }

mbus6EVIF12		OBJECT-TYPE
			SYNTAX	INTEGER
			ACCESS	read-only
			STATUS	current
	DESCRIPTION ""
			::= { mbus6E 42 }

mbus6EValue12		OBJECT-TYPE
			SYNTAX	INTEGER
			ACCESS	read-only
			STATUS	current
	DESCRIPTION ""
			::= { mbus6E 43 }

mbus6EVIF13		OBJECT-TYPE
			SYNTAX	INTEGER
			ACCESS	read-only
			STATUS	current
	DESCRIPTION ""
			::= { mbus6E 44 }

mbus6EValue13		OBJECT-TYPE
			SYNTAX	INTEGER
			ACCESS	read-only
			STATUS	current
	DESCRIPTION ""
			::= { mbus6E 45 }

mbus6EVIF14		OBJECT-TYPE
			SYNTAX	INTEGER
			ACCESS	read-only
			STATUS	current
	DESCRIPTION ""
			::= { mbus6E 46 }

mbus6EValue14		OBJECT-TYPE
			SYNTAX	INTEGER
			ACCESS	read-only
			STATUS	current
	DESCRIPTION ""
			::= { mbus6E 47 }

mbus6EVIF15		OBJECT-TYPE
			SYNTAX	INTEGER
			ACCESS	read-only
			STATUS	current
	DESCRIPTION ""
			::= { mbus6E 48 }

mbus6EValue15		OBJECT-TYPE
			SYNTAX	INTEGER
			ACCESS	read-only
			STATUS	current
	DESCRIPTION ""
			::= { mbus6E 49 }

mbus6EVIF16		OBJECT-TYPE
			SYNTAX	INTEGER
			ACCESS	read-only
			STATUS	current
	DESCRIPTION ""
			::= { mbus6E 50 }

mbus6EValue16		OBJECT-TYPE
			SYNTAX	INTEGER
			ACCESS	read-only
			STATUS	current
	DESCRIPTION ""
			::= { mbus6E 51 }

mbus6EVIF17		OBJECT-TYPE
			SYNTAX	INTEGER
			ACCESS	read-only
			STATUS	current
	DESCRIPTION ""
			::= { mbus6E 52 }

mbus6EValue17		OBJECT-TYPE
			SYNTAX	INTEGER
			ACCESS	read-only
			STATUS	current
	DESCRIPTION ""
			::= { mbus6E 53 }

mbus6EVIF18		OBJECT-TYPE
			SYNTAX	INTEGER
			ACCESS	read-only
			STATUS	current
	DESCRIPTION ""
			::= { mbus6E 54 }

mbus6EValue18		OBJECT-TYPE
			SYNTAX	INTEGER
			ACCESS	read-only
			STATUS	current
	DESCRIPTION ""
			::= { mbus6E 55 }

mbus6EVIF19		OBJECT-TYPE
			SYNTAX	INTEGER
			ACCESS	read-only
			STATUS	current
	DESCRIPTION ""
			::= { mbus6E 56 }

mbus6EValue19		OBJECT-TYPE
			SYNTAX	INTEGER
			ACCESS	read-only
			STATUS	current
	DESCRIPTION ""
			::= { mbus6E 57 }

mbus6EVIF1A		OBJECT-TYPE
			SYNTAX	INTEGER
			ACCESS	read-only
			STATUS	current
	DESCRIPTION ""
			::= { mbus6E 58 }

mbus6EValue1A		OBJECT-TYPE
			SYNTAX	INTEGER
			ACCESS	read-only
			STATUS	current
	DESCRIPTION ""
			::= { mbus6E 59 }

mbus6EVIF1B		OBJECT-TYPE
			SYNTAX	INTEGER
			ACCESS	read-only
			STATUS	current
	DESCRIPTION ""
			::= { mbus6E 60 }

mbus6EValue1B		OBJECT-TYPE
			SYNTAX	INTEGER
			ACCESS	read-only
			STATUS	current
	DESCRIPTION ""
			::= { mbus6E 61 }

mbus6EVIF1C		OBJECT-TYPE
			SYNTAX	INTEGER
			ACCESS	read-only
			STATUS	current
	DESCRIPTION ""
			::= { mbus6E 62 }

mbus6EValue1C		OBJECT-TYPE
			SYNTAX	INTEGER
			ACCESS	read-only
			STATUS	current
	DESCRIPTION ""
			::= { mbus6E 63 }

mbus6EVIF1D		OBJECT-TYPE
			SYNTAX	INTEGER
			ACCESS	read-only
			STATUS	current
	DESCRIPTION ""
			::= { mbus6E 64 }

mbus6EValue1D		OBJECT-TYPE
			SYNTAX	INTEGER
			ACCESS	read-only
			STATUS	current
	DESCRIPTION ""
			::= { mbus6E 65 }

mbus6EVIF1E		OBJECT-TYPE
			SYNTAX	INTEGER
			ACCESS	read-only
			STATUS	current
	DESCRIPTION ""
			::= { mbus6E 66 }

mbus6EValue1E		OBJECT-TYPE
			SYNTAX	INTEGER
			ACCESS	read-only
			STATUS	current
	DESCRIPTION ""
			::= { mbus6E 67 }

mbus6EVIF1F		OBJECT-TYPE
			SYNTAX	INTEGER
			ACCESS	read-only
			STATUS	current
	DESCRIPTION ""
			::= { mbus6E 68 }

mbus6EValue1F		OBJECT-TYPE
			SYNTAX	INTEGER
			ACCESS	read-only
			STATUS	current
	DESCRIPTION ""
			::= { mbus6E 69 }

mbus6EVIF20		OBJECT-TYPE
			SYNTAX	INTEGER
			ACCESS	read-only
			STATUS	current
	DESCRIPTION ""
			::= { mbus6E 70 }

mbus6EValue20		OBJECT-TYPE
			SYNTAX	INTEGER
			ACCESS	read-only
			STATUS	current
	DESCRIPTION ""
			::= { mbus6E 71 }

mbus6EVIF21		OBJECT-TYPE
			SYNTAX	INTEGER
			ACCESS	read-only
			STATUS	current
	DESCRIPTION ""
			::= { mbus6E 72 }

mbus6EValue21		OBJECT-TYPE
			SYNTAX	INTEGER
			ACCESS	read-only
			STATUS	current
	DESCRIPTION ""
			::= { mbus6E 73 }

mbus6EVIF22		OBJECT-TYPE
			SYNTAX	INTEGER
			ACCESS	read-only
			STATUS	current
	DESCRIPTION ""
			::= { mbus6E 74 }

mbus6EValue22		OBJECT-TYPE
			SYNTAX	INTEGER
			ACCESS	read-only
			STATUS	current
	DESCRIPTION ""
			::= { mbus6E 75 }

mbus6EVIF23		OBJECT-TYPE
			SYNTAX	INTEGER
			ACCESS	read-only
			STATUS	current
	DESCRIPTION ""
			::= { mbus6E 76 }

mbus6EValue23		OBJECT-TYPE
			SYNTAX	INTEGER
			ACCESS	read-only
			STATUS	current
	DESCRIPTION ""
			::= { mbus6E 77 }

mbus6EVIF24		OBJECT-TYPE
			SYNTAX	INTEGER
			ACCESS	read-only
			STATUS	current
	DESCRIPTION ""
			::= { mbus6E 78 }

mbus6EValue24		OBJECT-TYPE
			SYNTAX	INTEGER
			ACCESS	read-only
			STATUS	current
	DESCRIPTION ""
			::= { mbus6E 79 }

mbus6EVIF25		OBJECT-TYPE
			SYNTAX	INTEGER
			ACCESS	read-only
			STATUS	current
	DESCRIPTION ""
			::= { mbus6E 80 }

mbus6EValue25		OBJECT-TYPE
			SYNTAX	INTEGER
			ACCESS	read-only
			STATUS	current
	DESCRIPTION ""
			::= { mbus6E 81 }

mbus6EVIF26		OBJECT-TYPE
			SYNTAX	INTEGER
			ACCESS	read-only
			STATUS	current
	DESCRIPTION ""
			::= { mbus6E 82 }

mbus6EValue26		OBJECT-TYPE
			SYNTAX	INTEGER
			ACCESS	read-only
			STATUS	current
	DESCRIPTION ""
			::= { mbus6E 83 }

mbus6EVIF27		OBJECT-TYPE
			SYNTAX	INTEGER
			ACCESS	read-only
			STATUS	current
	DESCRIPTION ""
			::= { mbus6E 84 }

mbus6EValue27		OBJECT-TYPE
			SYNTAX	INTEGER
			ACCESS	read-only
			STATUS	current
	DESCRIPTION ""
			::= { mbus6E 85 }

mbus6EVIF28		OBJECT-TYPE
			SYNTAX	INTEGER
			ACCESS	read-only
			STATUS	current
	DESCRIPTION ""
			::= { mbus6E 86 }

mbus6EValue28		OBJECT-TYPE
			SYNTAX	INTEGER
			ACCESS	read-only
			STATUS	current
	DESCRIPTION ""
			::= { mbus6E 87 }

mbus6EVIF29		OBJECT-TYPE
			SYNTAX	INTEGER
			ACCESS	read-only
			STATUS	current
	DESCRIPTION ""
			::= { mbus6E 88 }

mbus6EValue29		OBJECT-TYPE
			SYNTAX	INTEGER
			ACCESS	read-only
			STATUS	current
	DESCRIPTION ""
			::= { mbus6E 89 }

mbus6EVIF2A		OBJECT-TYPE
			SYNTAX	INTEGER
			ACCESS	read-only
			STATUS	current
	DESCRIPTION ""
			::= { mbus6E 90 }

mbus6EValue2A		OBJECT-TYPE
			SYNTAX	INTEGER
			ACCESS	read-only
			STATUS	current
	DESCRIPTION ""
			::= { mbus6E 91 }

mbus6EVIF2B		OBJECT-TYPE
			SYNTAX	INTEGER
			ACCESS	read-only
			STATUS	current
	DESCRIPTION ""
			::= { mbus6E 92 }

mbus6EValue2B		OBJECT-TYPE
			SYNTAX	INTEGER
			ACCESS	read-only
			STATUS	current
	DESCRIPTION ""
			::= { mbus6E 93 }

mbus6EVIF2C		OBJECT-TYPE
			SYNTAX	INTEGER
			ACCESS	read-only
			STATUS	current
	DESCRIPTION ""
			::= { mbus6E 94 }

mbus6EValue2C		OBJECT-TYPE
			SYNTAX	INTEGER
			ACCESS	read-only
			STATUS	current
	DESCRIPTION ""
			::= { mbus6E 95 }

mbus6EVIF2D		OBJECT-TYPE
			SYNTAX	INTEGER
			ACCESS	read-only
			STATUS	current
	DESCRIPTION ""
			::= { mbus6E 96 }

mbus6EValue2D		OBJECT-TYPE
			SYNTAX	INTEGER
			ACCESS	read-only
			STATUS	current
	DESCRIPTION ""
			::= { mbus6E 97 }

mbus6EVIF2E		OBJECT-TYPE
			SYNTAX	INTEGER
			ACCESS	read-only
			STATUS	current
	DESCRIPTION ""
			::= { mbus6E 98 }

mbus6EValue2E		OBJECT-TYPE
			SYNTAX	INTEGER
			ACCESS	read-only
			STATUS	current
	DESCRIPTION ""
			::= { mbus6E 99 }

mbus6EVIF2F		OBJECT-TYPE
			SYNTAX	INTEGER
			ACCESS	read-only
			STATUS	current
	DESCRIPTION ""
			::= { mbus6E 100 }

mbus6EValue2F		OBJECT-TYPE
			SYNTAX	INTEGER
			ACCESS	read-only
			STATUS	current
	DESCRIPTION ""
			::= { mbus6E 101 }

mbus6F			OBJECT IDENTIFIER ::= { mbus 111 }

mbus6FIdNumber		OBJECT-TYPE
			SYNTAX	Gauge
			ACCESS	read-only
			STATUS	current
	DESCRIPTION ""
			::= { mbus6F 1 }

mbus6FManufacturer	OBJECT-TYPE
			SYNTAX	Gauge
			ACCESS	read-only
			STATUS	current
	DESCRIPTION ""
			::= { mbus6F 2 }

mbus6FVersion		OBJECT-TYPE
			SYNTAX	Gauge
			ACCESS	read-only
			STATUS	current
	DESCRIPTION ""
			::= { mbus6F 3 }

mbus6FMedium		OBJECT-TYPE
			SYNTAX	Gauge
			ACCESS	read-only
			STATUS	current
	DESCRIPTION ""
			::= { mbus6F 4 }

mbus6FStatus		OBJECT-TYPE
			SYNTAX	Gauge
			ACCESS	read-only
			STATUS	current
	DESCRIPTION ""
			::= { mbus6F 5 }

mbus6FVIF00		OBJECT-TYPE
			SYNTAX	INTEGER
			ACCESS	read-only
			STATUS	current
	DESCRIPTION ""
			::= { mbus6F 6 }

mbus6FValue00		OBJECT-TYPE
			SYNTAX	INTEGER
			ACCESS	read-only
			STATUS	current
	DESCRIPTION ""
			::= { mbus6F 7 }

mbus6FVIF01		OBJECT-TYPE
			SYNTAX	INTEGER
			ACCESS	read-only
			STATUS	current
	DESCRIPTION ""
			::= { mbus6F 8 }

mbus6FValue01		OBJECT-TYPE
			SYNTAX	INTEGER
			ACCESS	read-only
			STATUS	current
	DESCRIPTION ""
			::= { mbus6F 9 }

mbus6FVIF02		OBJECT-TYPE
			SYNTAX	INTEGER
			ACCESS	read-only
			STATUS	current
	DESCRIPTION ""
			::= { mbus6F 10 }

mbus6FValue02		OBJECT-TYPE
			SYNTAX	INTEGER
			ACCESS	read-only
			STATUS	current
	DESCRIPTION ""
			::= { mbus6F 11 }

mbus6FVIF03		OBJECT-TYPE
			SYNTAX	INTEGER
			ACCESS	read-only
			STATUS	current
	DESCRIPTION ""
			::= { mbus6F 12 }

mbus6FValue03		OBJECT-TYPE
			SYNTAX	INTEGER
			ACCESS	read-only
			STATUS	current
	DESCRIPTION ""
			::= { mbus6F 13 }

mbus6FVIF04		OBJECT-TYPE
			SYNTAX	INTEGER
			ACCESS	read-only
			STATUS	current
	DESCRIPTION ""
			::= { mbus6F 14 }

mbus6FValue04		OBJECT-TYPE
			SYNTAX	INTEGER
			ACCESS	read-only
			STATUS	current
	DESCRIPTION ""
			::= { mbus6F 15 }

mbus6FVIF05		OBJECT-TYPE
			SYNTAX	INTEGER
			ACCESS	read-only
			STATUS	current
	DESCRIPTION ""
			::= { mbus6F 16 }

mbus6FValue05		OBJECT-TYPE
			SYNTAX	INTEGER
			ACCESS	read-only
			STATUS	current
	DESCRIPTION ""
			::= { mbus6F 17 }

mbus6FVIF06		OBJECT-TYPE
			SYNTAX	INTEGER
			ACCESS	read-only
			STATUS	current
	DESCRIPTION ""
			::= { mbus6F 18 }

mbus6FValue06		OBJECT-TYPE
			SYNTAX	INTEGER
			ACCESS	read-only
			STATUS	current
	DESCRIPTION ""
			::= { mbus6F 19 }

mbus6FVIF07		OBJECT-TYPE
			SYNTAX	INTEGER
			ACCESS	read-only
			STATUS	current
	DESCRIPTION ""
			::= { mbus6F 20 }

mbus6FValue07		OBJECT-TYPE
			SYNTAX	INTEGER
			ACCESS	read-only
			STATUS	current
	DESCRIPTION ""
			::= { mbus6F 21 }

mbus6FVIF08		OBJECT-TYPE
			SYNTAX	INTEGER
			ACCESS	read-only
			STATUS	current
	DESCRIPTION ""
			::= { mbus6F 22 }

mbus6FValue08		OBJECT-TYPE
			SYNTAX	INTEGER
			ACCESS	read-only
			STATUS	current
	DESCRIPTION ""
			::= { mbus6F 23 }

mbus6FVIF09		OBJECT-TYPE
			SYNTAX	INTEGER
			ACCESS	read-only
			STATUS	current
	DESCRIPTION ""
			::= { mbus6F 24 }

mbus6FValue09		OBJECT-TYPE
			SYNTAX	INTEGER
			ACCESS	read-only
			STATUS	current
	DESCRIPTION ""
			::= { mbus6F 25 }

mbus6FVIF0A		OBJECT-TYPE
			SYNTAX	INTEGER
			ACCESS	read-only
			STATUS	current
	DESCRIPTION ""
			::= { mbus6F 26 }

mbus6FValue0A		OBJECT-TYPE
			SYNTAX	INTEGER
			ACCESS	read-only
			STATUS	current
	DESCRIPTION ""
			::= { mbus6F 27 }

mbus6FVIF0B		OBJECT-TYPE
			SYNTAX	INTEGER
			ACCESS	read-only
			STATUS	current
	DESCRIPTION ""
			::= { mbus6F 28 }

mbus6FValue0B		OBJECT-TYPE
			SYNTAX	INTEGER
			ACCESS	read-only
			STATUS	current
	DESCRIPTION ""
			::= { mbus6F 29 }

mbus6FVIF0C		OBJECT-TYPE
			SYNTAX	INTEGER
			ACCESS	read-only
			STATUS	current
	DESCRIPTION ""
			::= { mbus6F 30 }

mbus6FValue0C		OBJECT-TYPE
			SYNTAX	INTEGER
			ACCESS	read-only
			STATUS	current
	DESCRIPTION ""
			::= { mbus6F 31 }

mbus6FVIF0D		OBJECT-TYPE
			SYNTAX	INTEGER
			ACCESS	read-only
			STATUS	current
	DESCRIPTION ""
			::= { mbus6F 32 }

mbus6FValue0D		OBJECT-TYPE
			SYNTAX	INTEGER
			ACCESS	read-only
			STATUS	current
	DESCRIPTION ""
			::= { mbus6F 33 }

mbus6FVIF0E		OBJECT-TYPE
			SYNTAX	INTEGER
			ACCESS	read-only
			STATUS	current
	DESCRIPTION ""
			::= { mbus6F 34 }

mbus6FValue0E		OBJECT-TYPE
			SYNTAX	INTEGER
			ACCESS	read-only
			STATUS	current
	DESCRIPTION ""
			::= { mbus6F 35 }

mbus6FVIF0F		OBJECT-TYPE
			SYNTAX	INTEGER
			ACCESS	read-only
			STATUS	current
	DESCRIPTION ""
			::= { mbus6F 36 }

mbus6FValue0F		OBJECT-TYPE
			SYNTAX	INTEGER
			ACCESS	read-only
			STATUS	current
	DESCRIPTION ""
			::= { mbus6F 37 }

mbus6FVIF10		OBJECT-TYPE
			SYNTAX	INTEGER
			ACCESS	read-only
			STATUS	current
	DESCRIPTION ""
			::= { mbus6F 38 }

mbus6FValue10		OBJECT-TYPE
			SYNTAX	INTEGER
			ACCESS	read-only
			STATUS	current
	DESCRIPTION ""
			::= { mbus6F 39 }

mbus6FVIF11		OBJECT-TYPE
			SYNTAX	INTEGER
			ACCESS	read-only
			STATUS	current
	DESCRIPTION ""
			::= { mbus6F 40 }

mbus6FValue11		OBJECT-TYPE
			SYNTAX	INTEGER
			ACCESS	read-only
			STATUS	current
	DESCRIPTION ""
			::= { mbus6F 41 }

mbus6FVIF12		OBJECT-TYPE
			SYNTAX	INTEGER
			ACCESS	read-only
			STATUS	current
	DESCRIPTION ""
			::= { mbus6F 42 }

mbus6FValue12		OBJECT-TYPE
			SYNTAX	INTEGER
			ACCESS	read-only
			STATUS	current
	DESCRIPTION ""
			::= { mbus6F 43 }

mbus6FVIF13		OBJECT-TYPE
			SYNTAX	INTEGER
			ACCESS	read-only
			STATUS	current
	DESCRIPTION ""
			::= { mbus6F 44 }

mbus6FValue13		OBJECT-TYPE
			SYNTAX	INTEGER
			ACCESS	read-only
			STATUS	current
	DESCRIPTION ""
			::= { mbus6F 45 }

mbus6FVIF14		OBJECT-TYPE
			SYNTAX	INTEGER
			ACCESS	read-only
			STATUS	current
	DESCRIPTION ""
			::= { mbus6F 46 }

mbus6FValue14		OBJECT-TYPE
			SYNTAX	INTEGER
			ACCESS	read-only
			STATUS	current
	DESCRIPTION ""
			::= { mbus6F 47 }

mbus6FVIF15		OBJECT-TYPE
			SYNTAX	INTEGER
			ACCESS	read-only
			STATUS	current
	DESCRIPTION ""
			::= { mbus6F 48 }

mbus6FValue15		OBJECT-TYPE
			SYNTAX	INTEGER
			ACCESS	read-only
			STATUS	current
	DESCRIPTION ""
			::= { mbus6F 49 }

mbus6FVIF16		OBJECT-TYPE
			SYNTAX	INTEGER
			ACCESS	read-only
			STATUS	current
	DESCRIPTION ""
			::= { mbus6F 50 }

mbus6FValue16		OBJECT-TYPE
			SYNTAX	INTEGER
			ACCESS	read-only
			STATUS	current
	DESCRIPTION ""
			::= { mbus6F 51 }

mbus6FVIF17		OBJECT-TYPE
			SYNTAX	INTEGER
			ACCESS	read-only
			STATUS	current
	DESCRIPTION ""
			::= { mbus6F 52 }

mbus6FValue17		OBJECT-TYPE
			SYNTAX	INTEGER
			ACCESS	read-only
			STATUS	current
	DESCRIPTION ""
			::= { mbus6F 53 }

mbus6FVIF18		OBJECT-TYPE
			SYNTAX	INTEGER
			ACCESS	read-only
			STATUS	current
	DESCRIPTION ""
			::= { mbus6F 54 }

mbus6FValue18		OBJECT-TYPE
			SYNTAX	INTEGER
			ACCESS	read-only
			STATUS	current
	DESCRIPTION ""
			::= { mbus6F 55 }

mbus6FVIF19		OBJECT-TYPE
			SYNTAX	INTEGER
			ACCESS	read-only
			STATUS	current
	DESCRIPTION ""
			::= { mbus6F 56 }

mbus6FValue19		OBJECT-TYPE
			SYNTAX	INTEGER
			ACCESS	read-only
			STATUS	current
	DESCRIPTION ""
			::= { mbus6F 57 }

mbus6FVIF1A		OBJECT-TYPE
			SYNTAX	INTEGER
			ACCESS	read-only
			STATUS	current
	DESCRIPTION ""
			::= { mbus6F 58 }

mbus6FValue1A		OBJECT-TYPE
			SYNTAX	INTEGER
			ACCESS	read-only
			STATUS	current
	DESCRIPTION ""
			::= { mbus6F 59 }

mbus6FVIF1B		OBJECT-TYPE
			SYNTAX	INTEGER
			ACCESS	read-only
			STATUS	current
	DESCRIPTION ""
			::= { mbus6F 60 }

mbus6FValue1B		OBJECT-TYPE
			SYNTAX	INTEGER
			ACCESS	read-only
			STATUS	current
	DESCRIPTION ""
			::= { mbus6F 61 }

mbus6FVIF1C		OBJECT-TYPE
			SYNTAX	INTEGER
			ACCESS	read-only
			STATUS	current
	DESCRIPTION ""
			::= { mbus6F 62 }

mbus6FValue1C		OBJECT-TYPE
			SYNTAX	INTEGER
			ACCESS	read-only
			STATUS	current
	DESCRIPTION ""
			::= { mbus6F 63 }

mbus6FVIF1D		OBJECT-TYPE
			SYNTAX	INTEGER
			ACCESS	read-only
			STATUS	current
	DESCRIPTION ""
			::= { mbus6F 64 }

mbus6FValue1D		OBJECT-TYPE
			SYNTAX	INTEGER
			ACCESS	read-only
			STATUS	current
	DESCRIPTION ""
			::= { mbus6F 65 }

mbus6FVIF1E		OBJECT-TYPE
			SYNTAX	INTEGER
			ACCESS	read-only
			STATUS	current
	DESCRIPTION ""
			::= { mbus6F 66 }

mbus6FValue1E		OBJECT-TYPE
			SYNTAX	INTEGER
			ACCESS	read-only
			STATUS	current
	DESCRIPTION ""
			::= { mbus6F 67 }

mbus6FVIF1F		OBJECT-TYPE
			SYNTAX	INTEGER
			ACCESS	read-only
			STATUS	current
	DESCRIPTION ""
			::= { mbus6F 68 }

mbus6FValue1F		OBJECT-TYPE
			SYNTAX	INTEGER
			ACCESS	read-only
			STATUS	current
	DESCRIPTION ""
			::= { mbus6F 69 }

mbus6FVIF20		OBJECT-TYPE
			SYNTAX	INTEGER
			ACCESS	read-only
			STATUS	current
	DESCRIPTION ""
			::= { mbus6F 70 }

mbus6FValue20		OBJECT-TYPE
			SYNTAX	INTEGER
			ACCESS	read-only
			STATUS	current
	DESCRIPTION ""
			::= { mbus6F 71 }

mbus6FVIF21		OBJECT-TYPE
			SYNTAX	INTEGER
			ACCESS	read-only
			STATUS	current
	DESCRIPTION ""
			::= { mbus6F 72 }

mbus6FValue21		OBJECT-TYPE
			SYNTAX	INTEGER
			ACCESS	read-only
			STATUS	current
	DESCRIPTION ""
			::= { mbus6F 73 }

mbus6FVIF22		OBJECT-TYPE
			SYNTAX	INTEGER
			ACCESS	read-only
			STATUS	current
	DESCRIPTION ""
			::= { mbus6F 74 }

mbus6FValue22		OBJECT-TYPE
			SYNTAX	INTEGER
			ACCESS	read-only
			STATUS	current
	DESCRIPTION ""
			::= { mbus6F 75 }

mbus6FVIF23		OBJECT-TYPE
			SYNTAX	INTEGER
			ACCESS	read-only
			STATUS	current
	DESCRIPTION ""
			::= { mbus6F 76 }

mbus6FValue23		OBJECT-TYPE
			SYNTAX	INTEGER
			ACCESS	read-only
			STATUS	current
	DESCRIPTION ""
			::= { mbus6F 77 }

mbus6FVIF24		OBJECT-TYPE
			SYNTAX	INTEGER
			ACCESS	read-only
			STATUS	current
	DESCRIPTION ""
			::= { mbus6F 78 }

mbus6FValue24		OBJECT-TYPE
			SYNTAX	INTEGER
			ACCESS	read-only
			STATUS	current
	DESCRIPTION ""
			::= { mbus6F 79 }

mbus6FVIF25		OBJECT-TYPE
			SYNTAX	INTEGER
			ACCESS	read-only
			STATUS	current
	DESCRIPTION ""
			::= { mbus6F 80 }

mbus6FValue25		OBJECT-TYPE
			SYNTAX	INTEGER
			ACCESS	read-only
			STATUS	current
	DESCRIPTION ""
			::= { mbus6F 81 }

mbus6FVIF26		OBJECT-TYPE
			SYNTAX	INTEGER
			ACCESS	read-only
			STATUS	current
	DESCRIPTION ""
			::= { mbus6F 82 }

mbus6FValue26		OBJECT-TYPE
			SYNTAX	INTEGER
			ACCESS	read-only
			STATUS	current
	DESCRIPTION ""
			::= { mbus6F 83 }

mbus6FVIF27		OBJECT-TYPE
			SYNTAX	INTEGER
			ACCESS	read-only
			STATUS	current
	DESCRIPTION ""
			::= { mbus6F 84 }

mbus6FValue27		OBJECT-TYPE
			SYNTAX	INTEGER
			ACCESS	read-only
			STATUS	current
	DESCRIPTION ""
			::= { mbus6F 85 }

mbus6FVIF28		OBJECT-TYPE
			SYNTAX	INTEGER
			ACCESS	read-only
			STATUS	current
	DESCRIPTION ""
			::= { mbus6F 86 }

mbus6FValue28		OBJECT-TYPE
			SYNTAX	INTEGER
			ACCESS	read-only
			STATUS	current
	DESCRIPTION ""
			::= { mbus6F 87 }

mbus6FVIF29		OBJECT-TYPE
			SYNTAX	INTEGER
			ACCESS	read-only
			STATUS	current
	DESCRIPTION ""
			::= { mbus6F 88 }

mbus6FValue29		OBJECT-TYPE
			SYNTAX	INTEGER
			ACCESS	read-only
			STATUS	current
	DESCRIPTION ""
			::= { mbus6F 89 }

mbus6FVIF2A		OBJECT-TYPE
			SYNTAX	INTEGER
			ACCESS	read-only
			STATUS	current
	DESCRIPTION ""
			::= { mbus6F 90 }

mbus6FValue2A		OBJECT-TYPE
			SYNTAX	INTEGER
			ACCESS	read-only
			STATUS	current
	DESCRIPTION ""
			::= { mbus6F 91 }

mbus6FVIF2B		OBJECT-TYPE
			SYNTAX	INTEGER
			ACCESS	read-only
			STATUS	current
	DESCRIPTION ""
			::= { mbus6F 92 }

mbus6FValue2B		OBJECT-TYPE
			SYNTAX	INTEGER
			ACCESS	read-only
			STATUS	current
	DESCRIPTION ""
			::= { mbus6F 93 }

mbus6FVIF2C		OBJECT-TYPE
			SYNTAX	INTEGER
			ACCESS	read-only
			STATUS	current
	DESCRIPTION ""
			::= { mbus6F 94 }

mbus6FValue2C		OBJECT-TYPE
			SYNTAX	INTEGER
			ACCESS	read-only
			STATUS	current
	DESCRIPTION ""
			::= { mbus6F 95 }

mbus6FVIF2D		OBJECT-TYPE
			SYNTAX	INTEGER
			ACCESS	read-only
			STATUS	current
	DESCRIPTION ""
			::= { mbus6F 96 }

mbus6FValue2D		OBJECT-TYPE
			SYNTAX	INTEGER
			ACCESS	read-only
			STATUS	current
	DESCRIPTION ""
			::= { mbus6F 97 }

mbus6FVIF2E		OBJECT-TYPE
			SYNTAX	INTEGER
			ACCESS	read-only
			STATUS	current
	DESCRIPTION ""
			::= { mbus6F 98 }

mbus6FValue2E		OBJECT-TYPE
			SYNTAX	INTEGER
			ACCESS	read-only
			STATUS	current
	DESCRIPTION ""
			::= { mbus6F 99 }

mbus6FVIF2F		OBJECT-TYPE
			SYNTAX	INTEGER
			ACCESS	read-only
			STATUS	current
	DESCRIPTION ""
			::= { mbus6F 100 }

mbus6FValue2F		OBJECT-TYPE
			SYNTAX	INTEGER
			ACCESS	read-only
			STATUS	current
	DESCRIPTION ""
			::= { mbus6F 101 }

mbus70			OBJECT IDENTIFIER ::= { mbus 112 }

mbus70IdNumber		OBJECT-TYPE
			SYNTAX	Gauge
			ACCESS	read-only
			STATUS	current
	DESCRIPTION ""
			::= { mbus70 1 }

mbus70Manufacturer	OBJECT-TYPE
			SYNTAX	Gauge
			ACCESS	read-only
			STATUS	current
	DESCRIPTION ""
			::= { mbus70 2 }

mbus70Version		OBJECT-TYPE
			SYNTAX	Gauge
			ACCESS	read-only
			STATUS	current
	DESCRIPTION ""
			::= { mbus70 3 }

mbus70Medium		OBJECT-TYPE
			SYNTAX	Gauge
			ACCESS	read-only
			STATUS	current
	DESCRIPTION ""
			::= { mbus70 4 }

mbus70Status		OBJECT-TYPE
			SYNTAX	Gauge
			ACCESS	read-only
			STATUS	current
	DESCRIPTION ""
			::= { mbus70 5 }

mbus70VIF00		OBJECT-TYPE
			SYNTAX	INTEGER
			ACCESS	read-only
			STATUS	current
	DESCRIPTION ""
			::= { mbus70 6 }

mbus70Value00		OBJECT-TYPE
			SYNTAX	INTEGER
			ACCESS	read-only
			STATUS	current
	DESCRIPTION ""
			::= { mbus70 7 }

mbus70VIF01		OBJECT-TYPE
			SYNTAX	INTEGER
			ACCESS	read-only
			STATUS	current
	DESCRIPTION ""
			::= { mbus70 8 }

mbus70Value01		OBJECT-TYPE
			SYNTAX	INTEGER
			ACCESS	read-only
			STATUS	current
	DESCRIPTION ""
			::= { mbus70 9 }

mbus70VIF02		OBJECT-TYPE
			SYNTAX	INTEGER
			ACCESS	read-only
			STATUS	current
	DESCRIPTION ""
			::= { mbus70 10 }

mbus70Value02		OBJECT-TYPE
			SYNTAX	INTEGER
			ACCESS	read-only
			STATUS	current
	DESCRIPTION ""
			::= { mbus70 11 }

mbus70VIF03		OBJECT-TYPE
			SYNTAX	INTEGER
			ACCESS	read-only
			STATUS	current
	DESCRIPTION ""
			::= { mbus70 12 }

mbus70Value03		OBJECT-TYPE
			SYNTAX	INTEGER
			ACCESS	read-only
			STATUS	current
	DESCRIPTION ""
			::= { mbus70 13 }

mbus70VIF04		OBJECT-TYPE
			SYNTAX	INTEGER
			ACCESS	read-only
			STATUS	current
	DESCRIPTION ""
			::= { mbus70 14 }

mbus70Value04		OBJECT-TYPE
			SYNTAX	INTEGER
			ACCESS	read-only
			STATUS	current
	DESCRIPTION ""
			::= { mbus70 15 }

mbus70VIF05		OBJECT-TYPE
			SYNTAX	INTEGER
			ACCESS	read-only
			STATUS	current
	DESCRIPTION ""
			::= { mbus70 16 }

mbus70Value05		OBJECT-TYPE
			SYNTAX	INTEGER
			ACCESS	read-only
			STATUS	current
	DESCRIPTION ""
			::= { mbus70 17 }

mbus70VIF06		OBJECT-TYPE
			SYNTAX	INTEGER
			ACCESS	read-only
			STATUS	current
	DESCRIPTION ""
			::= { mbus70 18 }

mbus70Value06		OBJECT-TYPE
			SYNTAX	INTEGER
			ACCESS	read-only
			STATUS	current
	DESCRIPTION ""
			::= { mbus70 19 }

mbus70VIF07		OBJECT-TYPE
			SYNTAX	INTEGER
			ACCESS	read-only
			STATUS	current
	DESCRIPTION ""
			::= { mbus70 20 }

mbus70Value07		OBJECT-TYPE
			SYNTAX	INTEGER
			ACCESS	read-only
			STATUS	current
	DESCRIPTION ""
			::= { mbus70 21 }

mbus70VIF08		OBJECT-TYPE
			SYNTAX	INTEGER
			ACCESS	read-only
			STATUS	current
	DESCRIPTION ""
			::= { mbus70 22 }

mbus70Value08		OBJECT-TYPE
			SYNTAX	INTEGER
			ACCESS	read-only
			STATUS	current
	DESCRIPTION ""
			::= { mbus70 23 }

mbus70VIF09		OBJECT-TYPE
			SYNTAX	INTEGER
			ACCESS	read-only
			STATUS	current
	DESCRIPTION ""
			::= { mbus70 24 }

mbus70Value09		OBJECT-TYPE
			SYNTAX	INTEGER
			ACCESS	read-only
			STATUS	current
	DESCRIPTION ""
			::= { mbus70 25 }

mbus70VIF0A		OBJECT-TYPE
			SYNTAX	INTEGER
			ACCESS	read-only
			STATUS	current
	DESCRIPTION ""
			::= { mbus70 26 }

mbus70Value0A		OBJECT-TYPE
			SYNTAX	INTEGER
			ACCESS	read-only
			STATUS	current
	DESCRIPTION ""
			::= { mbus70 27 }

mbus70VIF0B		OBJECT-TYPE
			SYNTAX	INTEGER
			ACCESS	read-only
			STATUS	current
	DESCRIPTION ""
			::= { mbus70 28 }

mbus70Value0B		OBJECT-TYPE
			SYNTAX	INTEGER
			ACCESS	read-only
			STATUS	current
	DESCRIPTION ""
			::= { mbus70 29 }

mbus70VIF0C		OBJECT-TYPE
			SYNTAX	INTEGER
			ACCESS	read-only
			STATUS	current
	DESCRIPTION ""
			::= { mbus70 30 }

mbus70Value0C		OBJECT-TYPE
			SYNTAX	INTEGER
			ACCESS	read-only
			STATUS	current
	DESCRIPTION ""
			::= { mbus70 31 }

mbus70VIF0D		OBJECT-TYPE
			SYNTAX	INTEGER
			ACCESS	read-only
			STATUS	current
	DESCRIPTION ""
			::= { mbus70 32 }

mbus70Value0D		OBJECT-TYPE
			SYNTAX	INTEGER
			ACCESS	read-only
			STATUS	current
	DESCRIPTION ""
			::= { mbus70 33 }

mbus70VIF0E		OBJECT-TYPE
			SYNTAX	INTEGER
			ACCESS	read-only
			STATUS	current
	DESCRIPTION ""
			::= { mbus70 34 }

mbus70Value0E		OBJECT-TYPE
			SYNTAX	INTEGER
			ACCESS	read-only
			STATUS	current
	DESCRIPTION ""
			::= { mbus70 35 }

mbus70VIF0F		OBJECT-TYPE
			SYNTAX	INTEGER
			ACCESS	read-only
			STATUS	current
	DESCRIPTION ""
			::= { mbus70 36 }

mbus70Value0F		OBJECT-TYPE
			SYNTAX	INTEGER
			ACCESS	read-only
			STATUS	current
	DESCRIPTION ""
			::= { mbus70 37 }

mbus70VIF10		OBJECT-TYPE
			SYNTAX	INTEGER
			ACCESS	read-only
			STATUS	current
	DESCRIPTION ""
			::= { mbus70 38 }

mbus70Value10		OBJECT-TYPE
			SYNTAX	INTEGER
			ACCESS	read-only
			STATUS	current
	DESCRIPTION ""
			::= { mbus70 39 }

mbus70VIF11		OBJECT-TYPE
			SYNTAX	INTEGER
			ACCESS	read-only
			STATUS	current
	DESCRIPTION ""
			::= { mbus70 40 }

mbus70Value11		OBJECT-TYPE
			SYNTAX	INTEGER
			ACCESS	read-only
			STATUS	current
	DESCRIPTION ""
			::= { mbus70 41 }

mbus70VIF12		OBJECT-TYPE
			SYNTAX	INTEGER
			ACCESS	read-only
			STATUS	current
	DESCRIPTION ""
			::= { mbus70 42 }

mbus70Value12		OBJECT-TYPE
			SYNTAX	INTEGER
			ACCESS	read-only
			STATUS	current
	DESCRIPTION ""
			::= { mbus70 43 }

mbus70VIF13		OBJECT-TYPE
			SYNTAX	INTEGER
			ACCESS	read-only
			STATUS	current
	DESCRIPTION ""
			::= { mbus70 44 }

mbus70Value13		OBJECT-TYPE
			SYNTAX	INTEGER
			ACCESS	read-only
			STATUS	current
	DESCRIPTION ""
			::= { mbus70 45 }

mbus70VIF14		OBJECT-TYPE
			SYNTAX	INTEGER
			ACCESS	read-only
			STATUS	current
	DESCRIPTION ""
			::= { mbus70 46 }

mbus70Value14		OBJECT-TYPE
			SYNTAX	INTEGER
			ACCESS	read-only
			STATUS	current
	DESCRIPTION ""
			::= { mbus70 47 }

mbus70VIF15		OBJECT-TYPE
			SYNTAX	INTEGER
			ACCESS	read-only
			STATUS	current
	DESCRIPTION ""
			::= { mbus70 48 }

mbus70Value15		OBJECT-TYPE
			SYNTAX	INTEGER
			ACCESS	read-only
			STATUS	current
	DESCRIPTION ""
			::= { mbus70 49 }

mbus70VIF16		OBJECT-TYPE
			SYNTAX	INTEGER
			ACCESS	read-only
			STATUS	current
	DESCRIPTION ""
			::= { mbus70 50 }

mbus70Value16		OBJECT-TYPE
			SYNTAX	INTEGER
			ACCESS	read-only
			STATUS	current
	DESCRIPTION ""
			::= { mbus70 51 }

mbus70VIF17		OBJECT-TYPE
			SYNTAX	INTEGER
			ACCESS	read-only
			STATUS	current
	DESCRIPTION ""
			::= { mbus70 52 }

mbus70Value17		OBJECT-TYPE
			SYNTAX	INTEGER
			ACCESS	read-only
			STATUS	current
	DESCRIPTION ""
			::= { mbus70 53 }

mbus70VIF18		OBJECT-TYPE
			SYNTAX	INTEGER
			ACCESS	read-only
			STATUS	current
	DESCRIPTION ""
			::= { mbus70 54 }

mbus70Value18		OBJECT-TYPE
			SYNTAX	INTEGER
			ACCESS	read-only
			STATUS	current
	DESCRIPTION ""
			::= { mbus70 55 }

mbus70VIF19		OBJECT-TYPE
			SYNTAX	INTEGER
			ACCESS	read-only
			STATUS	current
	DESCRIPTION ""
			::= { mbus70 56 }

mbus70Value19		OBJECT-TYPE
			SYNTAX	INTEGER
			ACCESS	read-only
			STATUS	current
	DESCRIPTION ""
			::= { mbus70 57 }

mbus70VIF1A		OBJECT-TYPE
			SYNTAX	INTEGER
			ACCESS	read-only
			STATUS	current
	DESCRIPTION ""
			::= { mbus70 58 }

mbus70Value1A		OBJECT-TYPE
			SYNTAX	INTEGER
			ACCESS	read-only
			STATUS	current
	DESCRIPTION ""
			::= { mbus70 59 }

mbus70VIF1B		OBJECT-TYPE
			SYNTAX	INTEGER
			ACCESS	read-only
			STATUS	current
	DESCRIPTION ""
			::= { mbus70 60 }

mbus70Value1B		OBJECT-TYPE
			SYNTAX	INTEGER
			ACCESS	read-only
			STATUS	current
	DESCRIPTION ""
			::= { mbus70 61 }

mbus70VIF1C		OBJECT-TYPE
			SYNTAX	INTEGER
			ACCESS	read-only
			STATUS	current
	DESCRIPTION ""
			::= { mbus70 62 }

mbus70Value1C		OBJECT-TYPE
			SYNTAX	INTEGER
			ACCESS	read-only
			STATUS	current
	DESCRIPTION ""
			::= { mbus70 63 }

mbus70VIF1D		OBJECT-TYPE
			SYNTAX	INTEGER
			ACCESS	read-only
			STATUS	current
	DESCRIPTION ""
			::= { mbus70 64 }

mbus70Value1D		OBJECT-TYPE
			SYNTAX	INTEGER
			ACCESS	read-only
			STATUS	current
	DESCRIPTION ""
			::= { mbus70 65 }

mbus70VIF1E		OBJECT-TYPE
			SYNTAX	INTEGER
			ACCESS	read-only
			STATUS	current
	DESCRIPTION ""
			::= { mbus70 66 }

mbus70Value1E		OBJECT-TYPE
			SYNTAX	INTEGER
			ACCESS	read-only
			STATUS	current
	DESCRIPTION ""
			::= { mbus70 67 }

mbus70VIF1F		OBJECT-TYPE
			SYNTAX	INTEGER
			ACCESS	read-only
			STATUS	current
	DESCRIPTION ""
			::= { mbus70 68 }

mbus70Value1F		OBJECT-TYPE
			SYNTAX	INTEGER
			ACCESS	read-only
			STATUS	current
	DESCRIPTION ""
			::= { mbus70 69 }

mbus70VIF20		OBJECT-TYPE
			SYNTAX	INTEGER
			ACCESS	read-only
			STATUS	current
	DESCRIPTION ""
			::= { mbus70 70 }

mbus70Value20		OBJECT-TYPE
			SYNTAX	INTEGER
			ACCESS	read-only
			STATUS	current
	DESCRIPTION ""
			::= { mbus70 71 }

mbus70VIF21		OBJECT-TYPE
			SYNTAX	INTEGER
			ACCESS	read-only
			STATUS	current
	DESCRIPTION ""
			::= { mbus70 72 }

mbus70Value21		OBJECT-TYPE
			SYNTAX	INTEGER
			ACCESS	read-only
			STATUS	current
	DESCRIPTION ""
			::= { mbus70 73 }

mbus70VIF22		OBJECT-TYPE
			SYNTAX	INTEGER
			ACCESS	read-only
			STATUS	current
	DESCRIPTION ""
			::= { mbus70 74 }

mbus70Value22		OBJECT-TYPE
			SYNTAX	INTEGER
			ACCESS	read-only
			STATUS	current
	DESCRIPTION ""
			::= { mbus70 75 }

mbus70VIF23		OBJECT-TYPE
			SYNTAX	INTEGER
			ACCESS	read-only
			STATUS	current
	DESCRIPTION ""
			::= { mbus70 76 }

mbus70Value23		OBJECT-TYPE
			SYNTAX	INTEGER
			ACCESS	read-only
			STATUS	current
	DESCRIPTION ""
			::= { mbus70 77 }

mbus70VIF24		OBJECT-TYPE
			SYNTAX	INTEGER
			ACCESS	read-only
			STATUS	current
	DESCRIPTION ""
			::= { mbus70 78 }

mbus70Value24		OBJECT-TYPE
			SYNTAX	INTEGER
			ACCESS	read-only
			STATUS	current
	DESCRIPTION ""
			::= { mbus70 79 }

mbus70VIF25		OBJECT-TYPE
			SYNTAX	INTEGER
			ACCESS	read-only
			STATUS	current
	DESCRIPTION ""
			::= { mbus70 80 }

mbus70Value25		OBJECT-TYPE
			SYNTAX	INTEGER
			ACCESS	read-only
			STATUS	current
	DESCRIPTION ""
			::= { mbus70 81 }

mbus70VIF26		OBJECT-TYPE
			SYNTAX	INTEGER
			ACCESS	read-only
			STATUS	current
	DESCRIPTION ""
			::= { mbus70 82 }

mbus70Value26		OBJECT-TYPE
			SYNTAX	INTEGER
			ACCESS	read-only
			STATUS	current
	DESCRIPTION ""
			::= { mbus70 83 }

mbus70VIF27		OBJECT-TYPE
			SYNTAX	INTEGER
			ACCESS	read-only
			STATUS	current
	DESCRIPTION ""
			::= { mbus70 84 }

mbus70Value27		OBJECT-TYPE
			SYNTAX	INTEGER
			ACCESS	read-only
			STATUS	current
	DESCRIPTION ""
			::= { mbus70 85 }

mbus70VIF28		OBJECT-TYPE
			SYNTAX	INTEGER
			ACCESS	read-only
			STATUS	current
	DESCRIPTION ""
			::= { mbus70 86 }

mbus70Value28		OBJECT-TYPE
			SYNTAX	INTEGER
			ACCESS	read-only
			STATUS	current
	DESCRIPTION ""
			::= { mbus70 87 }

mbus70VIF29		OBJECT-TYPE
			SYNTAX	INTEGER
			ACCESS	read-only
			STATUS	current
	DESCRIPTION ""
			::= { mbus70 88 }

mbus70Value29		OBJECT-TYPE
			SYNTAX	INTEGER
			ACCESS	read-only
			STATUS	current
	DESCRIPTION ""
			::= { mbus70 89 }

mbus70VIF2A		OBJECT-TYPE
			SYNTAX	INTEGER
			ACCESS	read-only
			STATUS	current
	DESCRIPTION ""
			::= { mbus70 90 }

mbus70Value2A		OBJECT-TYPE
			SYNTAX	INTEGER
			ACCESS	read-only
			STATUS	current
	DESCRIPTION ""
			::= { mbus70 91 }

mbus70VIF2B		OBJECT-TYPE
			SYNTAX	INTEGER
			ACCESS	read-only
			STATUS	current
	DESCRIPTION ""
			::= { mbus70 92 }

mbus70Value2B		OBJECT-TYPE
			SYNTAX	INTEGER
			ACCESS	read-only
			STATUS	current
	DESCRIPTION ""
			::= { mbus70 93 }

mbus70VIF2C		OBJECT-TYPE
			SYNTAX	INTEGER
			ACCESS	read-only
			STATUS	current
	DESCRIPTION ""
			::= { mbus70 94 }

mbus70Value2C		OBJECT-TYPE
			SYNTAX	INTEGER
			ACCESS	read-only
			STATUS	current
	DESCRIPTION ""
			::= { mbus70 95 }

mbus70VIF2D		OBJECT-TYPE
			SYNTAX	INTEGER
			ACCESS	read-only
			STATUS	current
	DESCRIPTION ""
			::= { mbus70 96 }

mbus70Value2D		OBJECT-TYPE
			SYNTAX	INTEGER
			ACCESS	read-only
			STATUS	current
	DESCRIPTION ""
			::= { mbus70 97 }

mbus70VIF2E		OBJECT-TYPE
			SYNTAX	INTEGER
			ACCESS	read-only
			STATUS	current
	DESCRIPTION ""
			::= { mbus70 98 }

mbus70Value2E		OBJECT-TYPE
			SYNTAX	INTEGER
			ACCESS	read-only
			STATUS	current
	DESCRIPTION ""
			::= { mbus70 99 }

mbus70VIF2F		OBJECT-TYPE
			SYNTAX	INTEGER
			ACCESS	read-only
			STATUS	current
	DESCRIPTION ""
			::= { mbus70 100 }

mbus70Value2F		OBJECT-TYPE
			SYNTAX	INTEGER
			ACCESS	read-only
			STATUS	current
	DESCRIPTION ""
			::= { mbus70 101 }

mbus71			OBJECT IDENTIFIER ::= { mbus 113 }

mbus71IdNumber		OBJECT-TYPE
			SYNTAX	Gauge
			ACCESS	read-only
			STATUS	current
	DESCRIPTION ""
			::= { mbus71 1 }

mbus71Manufacturer	OBJECT-TYPE
			SYNTAX	Gauge
			ACCESS	read-only
			STATUS	current
	DESCRIPTION ""
			::= { mbus71 2 }

mbus71Version		OBJECT-TYPE
			SYNTAX	Gauge
			ACCESS	read-only
			STATUS	current
	DESCRIPTION ""
			::= { mbus71 3 }

mbus71Medium		OBJECT-TYPE
			SYNTAX	Gauge
			ACCESS	read-only
			STATUS	current
	DESCRIPTION ""
			::= { mbus71 4 }

mbus71Status		OBJECT-TYPE
			SYNTAX	Gauge
			ACCESS	read-only
			STATUS	current
	DESCRIPTION ""
			::= { mbus71 5 }

mbus71VIF00		OBJECT-TYPE
			SYNTAX	INTEGER
			ACCESS	read-only
			STATUS	current
	DESCRIPTION ""
			::= { mbus71 6 }

mbus71Value00		OBJECT-TYPE
			SYNTAX	INTEGER
			ACCESS	read-only
			STATUS	current
	DESCRIPTION ""
			::= { mbus71 7 }

mbus71VIF01		OBJECT-TYPE
			SYNTAX	INTEGER
			ACCESS	read-only
			STATUS	current
	DESCRIPTION ""
			::= { mbus71 8 }

mbus71Value01		OBJECT-TYPE
			SYNTAX	INTEGER
			ACCESS	read-only
			STATUS	current
	DESCRIPTION ""
			::= { mbus71 9 }

mbus71VIF02		OBJECT-TYPE
			SYNTAX	INTEGER
			ACCESS	read-only
			STATUS	current
	DESCRIPTION ""
			::= { mbus71 10 }

mbus71Value02		OBJECT-TYPE
			SYNTAX	INTEGER
			ACCESS	read-only
			STATUS	current
	DESCRIPTION ""
			::= { mbus71 11 }

mbus71VIF03		OBJECT-TYPE
			SYNTAX	INTEGER
			ACCESS	read-only
			STATUS	current
	DESCRIPTION ""
			::= { mbus71 12 }

mbus71Value03		OBJECT-TYPE
			SYNTAX	INTEGER
			ACCESS	read-only
			STATUS	current
	DESCRIPTION ""
			::= { mbus71 13 }

mbus71VIF04		OBJECT-TYPE
			SYNTAX	INTEGER
			ACCESS	read-only
			STATUS	current
	DESCRIPTION ""
			::= { mbus71 14 }

mbus71Value04		OBJECT-TYPE
			SYNTAX	INTEGER
			ACCESS	read-only
			STATUS	current
	DESCRIPTION ""
			::= { mbus71 15 }

mbus71VIF05		OBJECT-TYPE
			SYNTAX	INTEGER
			ACCESS	read-only
			STATUS	current
	DESCRIPTION ""
			::= { mbus71 16 }

mbus71Value05		OBJECT-TYPE
			SYNTAX	INTEGER
			ACCESS	read-only
			STATUS	current
	DESCRIPTION ""
			::= { mbus71 17 }

mbus71VIF06		OBJECT-TYPE
			SYNTAX	INTEGER
			ACCESS	read-only
			STATUS	current
	DESCRIPTION ""
			::= { mbus71 18 }

mbus71Value06		OBJECT-TYPE
			SYNTAX	INTEGER
			ACCESS	read-only
			STATUS	current
	DESCRIPTION ""
			::= { mbus71 19 }

mbus71VIF07		OBJECT-TYPE
			SYNTAX	INTEGER
			ACCESS	read-only
			STATUS	current
	DESCRIPTION ""
			::= { mbus71 20 }

mbus71Value07		OBJECT-TYPE
			SYNTAX	INTEGER
			ACCESS	read-only
			STATUS	current
	DESCRIPTION ""
			::= { mbus71 21 }

mbus71VIF08		OBJECT-TYPE
			SYNTAX	INTEGER
			ACCESS	read-only
			STATUS	current
	DESCRIPTION ""
			::= { mbus71 22 }

mbus71Value08		OBJECT-TYPE
			SYNTAX	INTEGER
			ACCESS	read-only
			STATUS	current
	DESCRIPTION ""
			::= { mbus71 23 }

mbus71VIF09		OBJECT-TYPE
			SYNTAX	INTEGER
			ACCESS	read-only
			STATUS	current
	DESCRIPTION ""
			::= { mbus71 24 }

mbus71Value09		OBJECT-TYPE
			SYNTAX	INTEGER
			ACCESS	read-only
			STATUS	current
	DESCRIPTION ""
			::= { mbus71 25 }

mbus71VIF0A		OBJECT-TYPE
			SYNTAX	INTEGER
			ACCESS	read-only
			STATUS	current
	DESCRIPTION ""
			::= { mbus71 26 }

mbus71Value0A		OBJECT-TYPE
			SYNTAX	INTEGER
			ACCESS	read-only
			STATUS	current
	DESCRIPTION ""
			::= { mbus71 27 }

mbus71VIF0B		OBJECT-TYPE
			SYNTAX	INTEGER
			ACCESS	read-only
			STATUS	current
	DESCRIPTION ""
			::= { mbus71 28 }

mbus71Value0B		OBJECT-TYPE
			SYNTAX	INTEGER
			ACCESS	read-only
			STATUS	current
	DESCRIPTION ""
			::= { mbus71 29 }

mbus71VIF0C		OBJECT-TYPE
			SYNTAX	INTEGER
			ACCESS	read-only
			STATUS	current
	DESCRIPTION ""
			::= { mbus71 30 }

mbus71Value0C		OBJECT-TYPE
			SYNTAX	INTEGER
			ACCESS	read-only
			STATUS	current
	DESCRIPTION ""
			::= { mbus71 31 }

mbus71VIF0D		OBJECT-TYPE
			SYNTAX	INTEGER
			ACCESS	read-only
			STATUS	current
	DESCRIPTION ""
			::= { mbus71 32 }

mbus71Value0D		OBJECT-TYPE
			SYNTAX	INTEGER
			ACCESS	read-only
			STATUS	current
	DESCRIPTION ""
			::= { mbus71 33 }

mbus71VIF0E		OBJECT-TYPE
			SYNTAX	INTEGER
			ACCESS	read-only
			STATUS	current
	DESCRIPTION ""
			::= { mbus71 34 }

mbus71Value0E		OBJECT-TYPE
			SYNTAX	INTEGER
			ACCESS	read-only
			STATUS	current
	DESCRIPTION ""
			::= { mbus71 35 }

mbus71VIF0F		OBJECT-TYPE
			SYNTAX	INTEGER
			ACCESS	read-only
			STATUS	current
	DESCRIPTION ""
			::= { mbus71 36 }

mbus71Value0F		OBJECT-TYPE
			SYNTAX	INTEGER
			ACCESS	read-only
			STATUS	current
	DESCRIPTION ""
			::= { mbus71 37 }

mbus71VIF10		OBJECT-TYPE
			SYNTAX	INTEGER
			ACCESS	read-only
			STATUS	current
	DESCRIPTION ""
			::= { mbus71 38 }

mbus71Value10		OBJECT-TYPE
			SYNTAX	INTEGER
			ACCESS	read-only
			STATUS	current
	DESCRIPTION ""
			::= { mbus71 39 }

mbus71VIF11		OBJECT-TYPE
			SYNTAX	INTEGER
			ACCESS	read-only
			STATUS	current
	DESCRIPTION ""
			::= { mbus71 40 }

mbus71Value11		OBJECT-TYPE
			SYNTAX	INTEGER
			ACCESS	read-only
			STATUS	current
	DESCRIPTION ""
			::= { mbus71 41 }

mbus71VIF12		OBJECT-TYPE
			SYNTAX	INTEGER
			ACCESS	read-only
			STATUS	current
	DESCRIPTION ""
			::= { mbus71 42 }

mbus71Value12		OBJECT-TYPE
			SYNTAX	INTEGER
			ACCESS	read-only
			STATUS	current
	DESCRIPTION ""
			::= { mbus71 43 }

mbus71VIF13		OBJECT-TYPE
			SYNTAX	INTEGER
			ACCESS	read-only
			STATUS	current
	DESCRIPTION ""
			::= { mbus71 44 }

mbus71Value13		OBJECT-TYPE
			SYNTAX	INTEGER
			ACCESS	read-only
			STATUS	current
	DESCRIPTION ""
			::= { mbus71 45 }

mbus71VIF14		OBJECT-TYPE
			SYNTAX	INTEGER
			ACCESS	read-only
			STATUS	current
	DESCRIPTION ""
			::= { mbus71 46 }

mbus71Value14		OBJECT-TYPE
			SYNTAX	INTEGER
			ACCESS	read-only
			STATUS	current
	DESCRIPTION ""
			::= { mbus71 47 }

mbus71VIF15		OBJECT-TYPE
			SYNTAX	INTEGER
			ACCESS	read-only
			STATUS	current
	DESCRIPTION ""
			::= { mbus71 48 }

mbus71Value15		OBJECT-TYPE
			SYNTAX	INTEGER
			ACCESS	read-only
			STATUS	current
	DESCRIPTION ""
			::= { mbus71 49 }

mbus71VIF16		OBJECT-TYPE
			SYNTAX	INTEGER
			ACCESS	read-only
			STATUS	current
	DESCRIPTION ""
			::= { mbus71 50 }

mbus71Value16		OBJECT-TYPE
			SYNTAX	INTEGER
			ACCESS	read-only
			STATUS	current
	DESCRIPTION ""
			::= { mbus71 51 }

mbus71VIF17		OBJECT-TYPE
			SYNTAX	INTEGER
			ACCESS	read-only
			STATUS	current
	DESCRIPTION ""
			::= { mbus71 52 }

mbus71Value17		OBJECT-TYPE
			SYNTAX	INTEGER
			ACCESS	read-only
			STATUS	current
	DESCRIPTION ""
			::= { mbus71 53 }

mbus71VIF18		OBJECT-TYPE
			SYNTAX	INTEGER
			ACCESS	read-only
			STATUS	current
	DESCRIPTION ""
			::= { mbus71 54 }

mbus71Value18		OBJECT-TYPE
			SYNTAX	INTEGER
			ACCESS	read-only
			STATUS	current
	DESCRIPTION ""
			::= { mbus71 55 }

mbus71VIF19		OBJECT-TYPE
			SYNTAX	INTEGER
			ACCESS	read-only
			STATUS	current
	DESCRIPTION ""
			::= { mbus71 56 }

mbus71Value19		OBJECT-TYPE
			SYNTAX	INTEGER
			ACCESS	read-only
			STATUS	current
	DESCRIPTION ""
			::= { mbus71 57 }

mbus71VIF1A		OBJECT-TYPE
			SYNTAX	INTEGER
			ACCESS	read-only
			STATUS	current
	DESCRIPTION ""
			::= { mbus71 58 }

mbus71Value1A		OBJECT-TYPE
			SYNTAX	INTEGER
			ACCESS	read-only
			STATUS	current
	DESCRIPTION ""
			::= { mbus71 59 }

mbus71VIF1B		OBJECT-TYPE
			SYNTAX	INTEGER
			ACCESS	read-only
			STATUS	current
	DESCRIPTION ""
			::= { mbus71 60 }

mbus71Value1B		OBJECT-TYPE
			SYNTAX	INTEGER
			ACCESS	read-only
			STATUS	current
	DESCRIPTION ""
			::= { mbus71 61 }

mbus71VIF1C		OBJECT-TYPE
			SYNTAX	INTEGER
			ACCESS	read-only
			STATUS	current
	DESCRIPTION ""
			::= { mbus71 62 }

mbus71Value1C		OBJECT-TYPE
			SYNTAX	INTEGER
			ACCESS	read-only
			STATUS	current
	DESCRIPTION ""
			::= { mbus71 63 }

mbus71VIF1D		OBJECT-TYPE
			SYNTAX	INTEGER
			ACCESS	read-only
			STATUS	current
	DESCRIPTION ""
			::= { mbus71 64 }

mbus71Value1D		OBJECT-TYPE
			SYNTAX	INTEGER
			ACCESS	read-only
			STATUS	current
	DESCRIPTION ""
			::= { mbus71 65 }

mbus71VIF1E		OBJECT-TYPE
			SYNTAX	INTEGER
			ACCESS	read-only
			STATUS	current
	DESCRIPTION ""
			::= { mbus71 66 }

mbus71Value1E		OBJECT-TYPE
			SYNTAX	INTEGER
			ACCESS	read-only
			STATUS	current
	DESCRIPTION ""
			::= { mbus71 67 }

mbus71VIF1F		OBJECT-TYPE
			SYNTAX	INTEGER
			ACCESS	read-only
			STATUS	current
	DESCRIPTION ""
			::= { mbus71 68 }

mbus71Value1F		OBJECT-TYPE
			SYNTAX	INTEGER
			ACCESS	read-only
			STATUS	current
	DESCRIPTION ""
			::= { mbus71 69 }

mbus71VIF20		OBJECT-TYPE
			SYNTAX	INTEGER
			ACCESS	read-only
			STATUS	current
	DESCRIPTION ""
			::= { mbus71 70 }

mbus71Value20		OBJECT-TYPE
			SYNTAX	INTEGER
			ACCESS	read-only
			STATUS	current
	DESCRIPTION ""
			::= { mbus71 71 }

mbus71VIF21		OBJECT-TYPE
			SYNTAX	INTEGER
			ACCESS	read-only
			STATUS	current
	DESCRIPTION ""
			::= { mbus71 72 }

mbus71Value21		OBJECT-TYPE
			SYNTAX	INTEGER
			ACCESS	read-only
			STATUS	current
	DESCRIPTION ""
			::= { mbus71 73 }

mbus71VIF22		OBJECT-TYPE
			SYNTAX	INTEGER
			ACCESS	read-only
			STATUS	current
	DESCRIPTION ""
			::= { mbus71 74 }

mbus71Value22		OBJECT-TYPE
			SYNTAX	INTEGER
			ACCESS	read-only
			STATUS	current
	DESCRIPTION ""
			::= { mbus71 75 }

mbus71VIF23		OBJECT-TYPE
			SYNTAX	INTEGER
			ACCESS	read-only
			STATUS	current
	DESCRIPTION ""
			::= { mbus71 76 }

mbus71Value23		OBJECT-TYPE
			SYNTAX	INTEGER
			ACCESS	read-only
			STATUS	current
	DESCRIPTION ""
			::= { mbus71 77 }

mbus71VIF24		OBJECT-TYPE
			SYNTAX	INTEGER
			ACCESS	read-only
			STATUS	current
	DESCRIPTION ""
			::= { mbus71 78 }

mbus71Value24		OBJECT-TYPE
			SYNTAX	INTEGER
			ACCESS	read-only
			STATUS	current
	DESCRIPTION ""
			::= { mbus71 79 }

mbus71VIF25		OBJECT-TYPE
			SYNTAX	INTEGER
			ACCESS	read-only
			STATUS	current
	DESCRIPTION ""
			::= { mbus71 80 }

mbus71Value25		OBJECT-TYPE
			SYNTAX	INTEGER
			ACCESS	read-only
			STATUS	current
	DESCRIPTION ""
			::= { mbus71 81 }

mbus71VIF26		OBJECT-TYPE
			SYNTAX	INTEGER
			ACCESS	read-only
			STATUS	current
	DESCRIPTION ""
			::= { mbus71 82 }

mbus71Value26		OBJECT-TYPE
			SYNTAX	INTEGER
			ACCESS	read-only
			STATUS	current
	DESCRIPTION ""
			::= { mbus71 83 }

mbus71VIF27		OBJECT-TYPE
			SYNTAX	INTEGER
			ACCESS	read-only
			STATUS	current
	DESCRIPTION ""
			::= { mbus71 84 }

mbus71Value27		OBJECT-TYPE
			SYNTAX	INTEGER
			ACCESS	read-only
			STATUS	current
	DESCRIPTION ""
			::= { mbus71 85 }

mbus71VIF28		OBJECT-TYPE
			SYNTAX	INTEGER
			ACCESS	read-only
			STATUS	current
	DESCRIPTION ""
			::= { mbus71 86 }

mbus71Value28		OBJECT-TYPE
			SYNTAX	INTEGER
			ACCESS	read-only
			STATUS	current
	DESCRIPTION ""
			::= { mbus71 87 }

mbus71VIF29		OBJECT-TYPE
			SYNTAX	INTEGER
			ACCESS	read-only
			STATUS	current
	DESCRIPTION ""
			::= { mbus71 88 }

mbus71Value29		OBJECT-TYPE
			SYNTAX	INTEGER
			ACCESS	read-only
			STATUS	current
	DESCRIPTION ""
			::= { mbus71 89 }

mbus71VIF2A		OBJECT-TYPE
			SYNTAX	INTEGER
			ACCESS	read-only
			STATUS	current
	DESCRIPTION ""
			::= { mbus71 90 }

mbus71Value2A		OBJECT-TYPE
			SYNTAX	INTEGER
			ACCESS	read-only
			STATUS	current
	DESCRIPTION ""
			::= { mbus71 91 }

mbus71VIF2B		OBJECT-TYPE
			SYNTAX	INTEGER
			ACCESS	read-only
			STATUS	current
	DESCRIPTION ""
			::= { mbus71 92 }

mbus71Value2B		OBJECT-TYPE
			SYNTAX	INTEGER
			ACCESS	read-only
			STATUS	current
	DESCRIPTION ""
			::= { mbus71 93 }

mbus71VIF2C		OBJECT-TYPE
			SYNTAX	INTEGER
			ACCESS	read-only
			STATUS	current
	DESCRIPTION ""
			::= { mbus71 94 }

mbus71Value2C		OBJECT-TYPE
			SYNTAX	INTEGER
			ACCESS	read-only
			STATUS	current
	DESCRIPTION ""
			::= { mbus71 95 }

mbus71VIF2D		OBJECT-TYPE
			SYNTAX	INTEGER
			ACCESS	read-only
			STATUS	current
	DESCRIPTION ""
			::= { mbus71 96 }

mbus71Value2D		OBJECT-TYPE
			SYNTAX	INTEGER
			ACCESS	read-only
			STATUS	current
	DESCRIPTION ""
			::= { mbus71 97 }

mbus71VIF2E		OBJECT-TYPE
			SYNTAX	INTEGER
			ACCESS	read-only
			STATUS	current
	DESCRIPTION ""
			::= { mbus71 98 }

mbus71Value2E		OBJECT-TYPE
			SYNTAX	INTEGER
			ACCESS	read-only
			STATUS	current
	DESCRIPTION ""
			::= { mbus71 99 }

mbus71VIF2F		OBJECT-TYPE
			SYNTAX	INTEGER
			ACCESS	read-only
			STATUS	current
	DESCRIPTION ""
			::= { mbus71 100 }

mbus71Value2F		OBJECT-TYPE
			SYNTAX	INTEGER
			ACCESS	read-only
			STATUS	current
	DESCRIPTION ""
			::= { mbus71 101 }

mbus72			OBJECT IDENTIFIER ::= { mbus 114 }

mbus72IdNumber		OBJECT-TYPE
			SYNTAX	Gauge
			ACCESS	read-only
			STATUS	current
	DESCRIPTION ""
			::= { mbus72 1 }

mbus72Manufacturer	OBJECT-TYPE
			SYNTAX	Gauge
			ACCESS	read-only
			STATUS	current
	DESCRIPTION ""
			::= { mbus72 2 }

mbus72Version		OBJECT-TYPE
			SYNTAX	Gauge
			ACCESS	read-only
			STATUS	current
	DESCRIPTION ""
			::= { mbus72 3 }

mbus72Medium		OBJECT-TYPE
			SYNTAX	Gauge
			ACCESS	read-only
			STATUS	current
	DESCRIPTION ""
			::= { mbus72 4 }

mbus72Status		OBJECT-TYPE
			SYNTAX	Gauge
			ACCESS	read-only
			STATUS	current
	DESCRIPTION ""
			::= { mbus72 5 }

mbus72VIF00		OBJECT-TYPE
			SYNTAX	INTEGER
			ACCESS	read-only
			STATUS	current
	DESCRIPTION ""
			::= { mbus72 6 }

mbus72Value00		OBJECT-TYPE
			SYNTAX	INTEGER
			ACCESS	read-only
			STATUS	current
	DESCRIPTION ""
			::= { mbus72 7 }

mbus72VIF01		OBJECT-TYPE
			SYNTAX	INTEGER
			ACCESS	read-only
			STATUS	current
	DESCRIPTION ""
			::= { mbus72 8 }

mbus72Value01		OBJECT-TYPE
			SYNTAX	INTEGER
			ACCESS	read-only
			STATUS	current
	DESCRIPTION ""
			::= { mbus72 9 }

mbus72VIF02		OBJECT-TYPE
			SYNTAX	INTEGER
			ACCESS	read-only
			STATUS	current
	DESCRIPTION ""
			::= { mbus72 10 }

mbus72Value02		OBJECT-TYPE
			SYNTAX	INTEGER
			ACCESS	read-only
			STATUS	current
	DESCRIPTION ""
			::= { mbus72 11 }

mbus72VIF03		OBJECT-TYPE
			SYNTAX	INTEGER
			ACCESS	read-only
			STATUS	current
	DESCRIPTION ""
			::= { mbus72 12 }

mbus72Value03		OBJECT-TYPE
			SYNTAX	INTEGER
			ACCESS	read-only
			STATUS	current
	DESCRIPTION ""
			::= { mbus72 13 }

mbus72VIF04		OBJECT-TYPE
			SYNTAX	INTEGER
			ACCESS	read-only
			STATUS	current
	DESCRIPTION ""
			::= { mbus72 14 }

mbus72Value04		OBJECT-TYPE
			SYNTAX	INTEGER
			ACCESS	read-only
			STATUS	current
	DESCRIPTION ""
			::= { mbus72 15 }

mbus72VIF05		OBJECT-TYPE
			SYNTAX	INTEGER
			ACCESS	read-only
			STATUS	current
	DESCRIPTION ""
			::= { mbus72 16 }

mbus72Value05		OBJECT-TYPE
			SYNTAX	INTEGER
			ACCESS	read-only
			STATUS	current
	DESCRIPTION ""
			::= { mbus72 17 }

mbus72VIF06		OBJECT-TYPE
			SYNTAX	INTEGER
			ACCESS	read-only
			STATUS	current
	DESCRIPTION ""
			::= { mbus72 18 }

mbus72Value06		OBJECT-TYPE
			SYNTAX	INTEGER
			ACCESS	read-only
			STATUS	current
	DESCRIPTION ""
			::= { mbus72 19 }

mbus72VIF07		OBJECT-TYPE
			SYNTAX	INTEGER
			ACCESS	read-only
			STATUS	current
	DESCRIPTION ""
			::= { mbus72 20 }

mbus72Value07		OBJECT-TYPE
			SYNTAX	INTEGER
			ACCESS	read-only
			STATUS	current
	DESCRIPTION ""
			::= { mbus72 21 }

mbus72VIF08		OBJECT-TYPE
			SYNTAX	INTEGER
			ACCESS	read-only
			STATUS	current
	DESCRIPTION ""
			::= { mbus72 22 }

mbus72Value08		OBJECT-TYPE
			SYNTAX	INTEGER
			ACCESS	read-only
			STATUS	current
	DESCRIPTION ""
			::= { mbus72 23 }

mbus72VIF09		OBJECT-TYPE
			SYNTAX	INTEGER
			ACCESS	read-only
			STATUS	current
	DESCRIPTION ""
			::= { mbus72 24 }

mbus72Value09		OBJECT-TYPE
			SYNTAX	INTEGER
			ACCESS	read-only
			STATUS	current
	DESCRIPTION ""
			::= { mbus72 25 }

mbus72VIF0A		OBJECT-TYPE
			SYNTAX	INTEGER
			ACCESS	read-only
			STATUS	current
	DESCRIPTION ""
			::= { mbus72 26 }

mbus72Value0A		OBJECT-TYPE
			SYNTAX	INTEGER
			ACCESS	read-only
			STATUS	current
	DESCRIPTION ""
			::= { mbus72 27 }

mbus72VIF0B		OBJECT-TYPE
			SYNTAX	INTEGER
			ACCESS	read-only
			STATUS	current
	DESCRIPTION ""
			::= { mbus72 28 }

mbus72Value0B		OBJECT-TYPE
			SYNTAX	INTEGER
			ACCESS	read-only
			STATUS	current
	DESCRIPTION ""
			::= { mbus72 29 }

mbus72VIF0C		OBJECT-TYPE
			SYNTAX	INTEGER
			ACCESS	read-only
			STATUS	current
	DESCRIPTION ""
			::= { mbus72 30 }

mbus72Value0C		OBJECT-TYPE
			SYNTAX	INTEGER
			ACCESS	read-only
			STATUS	current
	DESCRIPTION ""
			::= { mbus72 31 }

mbus72VIF0D		OBJECT-TYPE
			SYNTAX	INTEGER
			ACCESS	read-only
			STATUS	current
	DESCRIPTION ""
			::= { mbus72 32 }

mbus72Value0D		OBJECT-TYPE
			SYNTAX	INTEGER
			ACCESS	read-only
			STATUS	current
	DESCRIPTION ""
			::= { mbus72 33 }

mbus72VIF0E		OBJECT-TYPE
			SYNTAX	INTEGER
			ACCESS	read-only
			STATUS	current
	DESCRIPTION ""
			::= { mbus72 34 }

mbus72Value0E		OBJECT-TYPE
			SYNTAX	INTEGER
			ACCESS	read-only
			STATUS	current
	DESCRIPTION ""
			::= { mbus72 35 }

mbus72VIF0F		OBJECT-TYPE
			SYNTAX	INTEGER
			ACCESS	read-only
			STATUS	current
	DESCRIPTION ""
			::= { mbus72 36 }

mbus72Value0F		OBJECT-TYPE
			SYNTAX	INTEGER
			ACCESS	read-only
			STATUS	current
	DESCRIPTION ""
			::= { mbus72 37 }

mbus72VIF10		OBJECT-TYPE
			SYNTAX	INTEGER
			ACCESS	read-only
			STATUS	current
	DESCRIPTION ""
			::= { mbus72 38 }

mbus72Value10		OBJECT-TYPE
			SYNTAX	INTEGER
			ACCESS	read-only
			STATUS	current
	DESCRIPTION ""
			::= { mbus72 39 }

mbus72VIF11		OBJECT-TYPE
			SYNTAX	INTEGER
			ACCESS	read-only
			STATUS	current
	DESCRIPTION ""
			::= { mbus72 40 }

mbus72Value11		OBJECT-TYPE
			SYNTAX	INTEGER
			ACCESS	read-only
			STATUS	current
	DESCRIPTION ""
			::= { mbus72 41 }

mbus72VIF12		OBJECT-TYPE
			SYNTAX	INTEGER
			ACCESS	read-only
			STATUS	current
	DESCRIPTION ""
			::= { mbus72 42 }

mbus72Value12		OBJECT-TYPE
			SYNTAX	INTEGER
			ACCESS	read-only
			STATUS	current
	DESCRIPTION ""
			::= { mbus72 43 }

mbus72VIF13		OBJECT-TYPE
			SYNTAX	INTEGER
			ACCESS	read-only
			STATUS	current
	DESCRIPTION ""
			::= { mbus72 44 }

mbus72Value13		OBJECT-TYPE
			SYNTAX	INTEGER
			ACCESS	read-only
			STATUS	current
	DESCRIPTION ""
			::= { mbus72 45 }

mbus72VIF14		OBJECT-TYPE
			SYNTAX	INTEGER
			ACCESS	read-only
			STATUS	current
	DESCRIPTION ""
			::= { mbus72 46 }

mbus72Value14		OBJECT-TYPE
			SYNTAX	INTEGER
			ACCESS	read-only
			STATUS	current
	DESCRIPTION ""
			::= { mbus72 47 }

mbus72VIF15		OBJECT-TYPE
			SYNTAX	INTEGER
			ACCESS	read-only
			STATUS	current
	DESCRIPTION ""
			::= { mbus72 48 }

mbus72Value15		OBJECT-TYPE
			SYNTAX	INTEGER
			ACCESS	read-only
			STATUS	current
	DESCRIPTION ""
			::= { mbus72 49 }

mbus72VIF16		OBJECT-TYPE
			SYNTAX	INTEGER
			ACCESS	read-only
			STATUS	current
	DESCRIPTION ""
			::= { mbus72 50 }

mbus72Value16		OBJECT-TYPE
			SYNTAX	INTEGER
			ACCESS	read-only
			STATUS	current
	DESCRIPTION ""
			::= { mbus72 51 }

mbus72VIF17		OBJECT-TYPE
			SYNTAX	INTEGER
			ACCESS	read-only
			STATUS	current
	DESCRIPTION ""
			::= { mbus72 52 }

mbus72Value17		OBJECT-TYPE
			SYNTAX	INTEGER
			ACCESS	read-only
			STATUS	current
	DESCRIPTION ""
			::= { mbus72 53 }

mbus72VIF18		OBJECT-TYPE
			SYNTAX	INTEGER
			ACCESS	read-only
			STATUS	current
	DESCRIPTION ""
			::= { mbus72 54 }

mbus72Value18		OBJECT-TYPE
			SYNTAX	INTEGER
			ACCESS	read-only
			STATUS	current
	DESCRIPTION ""
			::= { mbus72 55 }

mbus72VIF19		OBJECT-TYPE
			SYNTAX	INTEGER
			ACCESS	read-only
			STATUS	current
	DESCRIPTION ""
			::= { mbus72 56 }

mbus72Value19		OBJECT-TYPE
			SYNTAX	INTEGER
			ACCESS	read-only
			STATUS	current
	DESCRIPTION ""
			::= { mbus72 57 }

mbus72VIF1A		OBJECT-TYPE
			SYNTAX	INTEGER
			ACCESS	read-only
			STATUS	current
	DESCRIPTION ""
			::= { mbus72 58 }

mbus72Value1A		OBJECT-TYPE
			SYNTAX	INTEGER
			ACCESS	read-only
			STATUS	current
	DESCRIPTION ""
			::= { mbus72 59 }

mbus72VIF1B		OBJECT-TYPE
			SYNTAX	INTEGER
			ACCESS	read-only
			STATUS	current
	DESCRIPTION ""
			::= { mbus72 60 }

mbus72Value1B		OBJECT-TYPE
			SYNTAX	INTEGER
			ACCESS	read-only
			STATUS	current
	DESCRIPTION ""
			::= { mbus72 61 }

mbus72VIF1C		OBJECT-TYPE
			SYNTAX	INTEGER
			ACCESS	read-only
			STATUS	current
	DESCRIPTION ""
			::= { mbus72 62 }

mbus72Value1C		OBJECT-TYPE
			SYNTAX	INTEGER
			ACCESS	read-only
			STATUS	current
	DESCRIPTION ""
			::= { mbus72 63 }

mbus72VIF1D		OBJECT-TYPE
			SYNTAX	INTEGER
			ACCESS	read-only
			STATUS	current
	DESCRIPTION ""
			::= { mbus72 64 }

mbus72Value1D		OBJECT-TYPE
			SYNTAX	INTEGER
			ACCESS	read-only
			STATUS	current
	DESCRIPTION ""
			::= { mbus72 65 }

mbus72VIF1E		OBJECT-TYPE
			SYNTAX	INTEGER
			ACCESS	read-only
			STATUS	current
	DESCRIPTION ""
			::= { mbus72 66 }

mbus72Value1E		OBJECT-TYPE
			SYNTAX	INTEGER
			ACCESS	read-only
			STATUS	current
	DESCRIPTION ""
			::= { mbus72 67 }

mbus72VIF1F		OBJECT-TYPE
			SYNTAX	INTEGER
			ACCESS	read-only
			STATUS	current
	DESCRIPTION ""
			::= { mbus72 68 }

mbus72Value1F		OBJECT-TYPE
			SYNTAX	INTEGER
			ACCESS	read-only
			STATUS	current
	DESCRIPTION ""
			::= { mbus72 69 }

mbus72VIF20		OBJECT-TYPE
			SYNTAX	INTEGER
			ACCESS	read-only
			STATUS	current
	DESCRIPTION ""
			::= { mbus72 70 }

mbus72Value20		OBJECT-TYPE
			SYNTAX	INTEGER
			ACCESS	read-only
			STATUS	current
	DESCRIPTION ""
			::= { mbus72 71 }

mbus72VIF21		OBJECT-TYPE
			SYNTAX	INTEGER
			ACCESS	read-only
			STATUS	current
	DESCRIPTION ""
			::= { mbus72 72 }

mbus72Value21		OBJECT-TYPE
			SYNTAX	INTEGER
			ACCESS	read-only
			STATUS	current
	DESCRIPTION ""
			::= { mbus72 73 }

mbus72VIF22		OBJECT-TYPE
			SYNTAX	INTEGER
			ACCESS	read-only
			STATUS	current
	DESCRIPTION ""
			::= { mbus72 74 }

mbus72Value22		OBJECT-TYPE
			SYNTAX	INTEGER
			ACCESS	read-only
			STATUS	current
	DESCRIPTION ""
			::= { mbus72 75 }

mbus72VIF23		OBJECT-TYPE
			SYNTAX	INTEGER
			ACCESS	read-only
			STATUS	current
	DESCRIPTION ""
			::= { mbus72 76 }

mbus72Value23		OBJECT-TYPE
			SYNTAX	INTEGER
			ACCESS	read-only
			STATUS	current
	DESCRIPTION ""
			::= { mbus72 77 }

mbus72VIF24		OBJECT-TYPE
			SYNTAX	INTEGER
			ACCESS	read-only
			STATUS	current
	DESCRIPTION ""
			::= { mbus72 78 }

mbus72Value24		OBJECT-TYPE
			SYNTAX	INTEGER
			ACCESS	read-only
			STATUS	current
	DESCRIPTION ""
			::= { mbus72 79 }

mbus72VIF25		OBJECT-TYPE
			SYNTAX	INTEGER
			ACCESS	read-only
			STATUS	current
	DESCRIPTION ""
			::= { mbus72 80 }

mbus72Value25		OBJECT-TYPE
			SYNTAX	INTEGER
			ACCESS	read-only
			STATUS	current
	DESCRIPTION ""
			::= { mbus72 81 }

mbus72VIF26		OBJECT-TYPE
			SYNTAX	INTEGER
			ACCESS	read-only
			STATUS	current
	DESCRIPTION ""
			::= { mbus72 82 }

mbus72Value26		OBJECT-TYPE
			SYNTAX	INTEGER
			ACCESS	read-only
			STATUS	current
	DESCRIPTION ""
			::= { mbus72 83 }

mbus72VIF27		OBJECT-TYPE
			SYNTAX	INTEGER
			ACCESS	read-only
			STATUS	current
	DESCRIPTION ""
			::= { mbus72 84 }

mbus72Value27		OBJECT-TYPE
			SYNTAX	INTEGER
			ACCESS	read-only
			STATUS	current
	DESCRIPTION ""
			::= { mbus72 85 }

mbus72VIF28		OBJECT-TYPE
			SYNTAX	INTEGER
			ACCESS	read-only
			STATUS	current
	DESCRIPTION ""
			::= { mbus72 86 }

mbus72Value28		OBJECT-TYPE
			SYNTAX	INTEGER
			ACCESS	read-only
			STATUS	current
	DESCRIPTION ""
			::= { mbus72 87 }

mbus72VIF29		OBJECT-TYPE
			SYNTAX	INTEGER
			ACCESS	read-only
			STATUS	current
	DESCRIPTION ""
			::= { mbus72 88 }

mbus72Value29		OBJECT-TYPE
			SYNTAX	INTEGER
			ACCESS	read-only
			STATUS	current
	DESCRIPTION ""
			::= { mbus72 89 }

mbus72VIF2A		OBJECT-TYPE
			SYNTAX	INTEGER
			ACCESS	read-only
			STATUS	current
	DESCRIPTION ""
			::= { mbus72 90 }

mbus72Value2A		OBJECT-TYPE
			SYNTAX	INTEGER
			ACCESS	read-only
			STATUS	current
	DESCRIPTION ""
			::= { mbus72 91 }

mbus72VIF2B		OBJECT-TYPE
			SYNTAX	INTEGER
			ACCESS	read-only
			STATUS	current
	DESCRIPTION ""
			::= { mbus72 92 }

mbus72Value2B		OBJECT-TYPE
			SYNTAX	INTEGER
			ACCESS	read-only
			STATUS	current
	DESCRIPTION ""
			::= { mbus72 93 }

mbus72VIF2C		OBJECT-TYPE
			SYNTAX	INTEGER
			ACCESS	read-only
			STATUS	current
	DESCRIPTION ""
			::= { mbus72 94 }

mbus72Value2C		OBJECT-TYPE
			SYNTAX	INTEGER
			ACCESS	read-only
			STATUS	current
	DESCRIPTION ""
			::= { mbus72 95 }

mbus72VIF2D		OBJECT-TYPE
			SYNTAX	INTEGER
			ACCESS	read-only
			STATUS	current
	DESCRIPTION ""
			::= { mbus72 96 }

mbus72Value2D		OBJECT-TYPE
			SYNTAX	INTEGER
			ACCESS	read-only
			STATUS	current
	DESCRIPTION ""
			::= { mbus72 97 }

mbus72VIF2E		OBJECT-TYPE
			SYNTAX	INTEGER
			ACCESS	read-only
			STATUS	current
	DESCRIPTION ""
			::= { mbus72 98 }

mbus72Value2E		OBJECT-TYPE
			SYNTAX	INTEGER
			ACCESS	read-only
			STATUS	current
	DESCRIPTION ""
			::= { mbus72 99 }

mbus72VIF2F		OBJECT-TYPE
			SYNTAX	INTEGER
			ACCESS	read-only
			STATUS	current
	DESCRIPTION ""
			::= { mbus72 100 }

mbus72Value2F		OBJECT-TYPE
			SYNTAX	INTEGER
			ACCESS	read-only
			STATUS	current
	DESCRIPTION ""
			::= { mbus72 101 }

mbus73			OBJECT IDENTIFIER ::= { mbus 115 }

mbus73IdNumber		OBJECT-TYPE
			SYNTAX	Gauge
			ACCESS	read-only
			STATUS	current
	DESCRIPTION ""
			::= { mbus73 1 }

mbus73Manufacturer	OBJECT-TYPE
			SYNTAX	Gauge
			ACCESS	read-only
			STATUS	current
	DESCRIPTION ""
			::= { mbus73 2 }

mbus73Version		OBJECT-TYPE
			SYNTAX	Gauge
			ACCESS	read-only
			STATUS	current
	DESCRIPTION ""
			::= { mbus73 3 }

mbus73Medium		OBJECT-TYPE
			SYNTAX	Gauge
			ACCESS	read-only
			STATUS	current
	DESCRIPTION ""
			::= { mbus73 4 }

mbus73Status		OBJECT-TYPE
			SYNTAX	Gauge
			ACCESS	read-only
			STATUS	current
	DESCRIPTION ""
			::= { mbus73 5 }

mbus73VIF00		OBJECT-TYPE
			SYNTAX	INTEGER
			ACCESS	read-only
			STATUS	current
	DESCRIPTION ""
			::= { mbus73 6 }

mbus73Value00		OBJECT-TYPE
			SYNTAX	INTEGER
			ACCESS	read-only
			STATUS	current
	DESCRIPTION ""
			::= { mbus73 7 }

mbus73VIF01		OBJECT-TYPE
			SYNTAX	INTEGER
			ACCESS	read-only
			STATUS	current
	DESCRIPTION ""
			::= { mbus73 8 }

mbus73Value01		OBJECT-TYPE
			SYNTAX	INTEGER
			ACCESS	read-only
			STATUS	current
	DESCRIPTION ""
			::= { mbus73 9 }

mbus73VIF02		OBJECT-TYPE
			SYNTAX	INTEGER
			ACCESS	read-only
			STATUS	current
	DESCRIPTION ""
			::= { mbus73 10 }

mbus73Value02		OBJECT-TYPE
			SYNTAX	INTEGER
			ACCESS	read-only
			STATUS	current
	DESCRIPTION ""
			::= { mbus73 11 }

mbus73VIF03		OBJECT-TYPE
			SYNTAX	INTEGER
			ACCESS	read-only
			STATUS	current
	DESCRIPTION ""
			::= { mbus73 12 }

mbus73Value03		OBJECT-TYPE
			SYNTAX	INTEGER
			ACCESS	read-only
			STATUS	current
	DESCRIPTION ""
			::= { mbus73 13 }

mbus73VIF04		OBJECT-TYPE
			SYNTAX	INTEGER
			ACCESS	read-only
			STATUS	current
	DESCRIPTION ""
			::= { mbus73 14 }

mbus73Value04		OBJECT-TYPE
			SYNTAX	INTEGER
			ACCESS	read-only
			STATUS	current
	DESCRIPTION ""
			::= { mbus73 15 }

mbus73VIF05		OBJECT-TYPE
			SYNTAX	INTEGER
			ACCESS	read-only
			STATUS	current
	DESCRIPTION ""
			::= { mbus73 16 }

mbus73Value05		OBJECT-TYPE
			SYNTAX	INTEGER
			ACCESS	read-only
			STATUS	current
	DESCRIPTION ""
			::= { mbus73 17 }

mbus73VIF06		OBJECT-TYPE
			SYNTAX	INTEGER
			ACCESS	read-only
			STATUS	current
	DESCRIPTION ""
			::= { mbus73 18 }

mbus73Value06		OBJECT-TYPE
			SYNTAX	INTEGER
			ACCESS	read-only
			STATUS	current
	DESCRIPTION ""
			::= { mbus73 19 }

mbus73VIF07		OBJECT-TYPE
			SYNTAX	INTEGER
			ACCESS	read-only
			STATUS	current
	DESCRIPTION ""
			::= { mbus73 20 }

mbus73Value07		OBJECT-TYPE
			SYNTAX	INTEGER
			ACCESS	read-only
			STATUS	current
	DESCRIPTION ""
			::= { mbus73 21 }

mbus73VIF08		OBJECT-TYPE
			SYNTAX	INTEGER
			ACCESS	read-only
			STATUS	current
	DESCRIPTION ""
			::= { mbus73 22 }

mbus73Value08		OBJECT-TYPE
			SYNTAX	INTEGER
			ACCESS	read-only
			STATUS	current
	DESCRIPTION ""
			::= { mbus73 23 }

mbus73VIF09		OBJECT-TYPE
			SYNTAX	INTEGER
			ACCESS	read-only
			STATUS	current
	DESCRIPTION ""
			::= { mbus73 24 }

mbus73Value09		OBJECT-TYPE
			SYNTAX	INTEGER
			ACCESS	read-only
			STATUS	current
	DESCRIPTION ""
			::= { mbus73 25 }

mbus73VIF0A		OBJECT-TYPE
			SYNTAX	INTEGER
			ACCESS	read-only
			STATUS	current
	DESCRIPTION ""
			::= { mbus73 26 }

mbus73Value0A		OBJECT-TYPE
			SYNTAX	INTEGER
			ACCESS	read-only
			STATUS	current
	DESCRIPTION ""
			::= { mbus73 27 }

mbus73VIF0B		OBJECT-TYPE
			SYNTAX	INTEGER
			ACCESS	read-only
			STATUS	current
	DESCRIPTION ""
			::= { mbus73 28 }

mbus73Value0B		OBJECT-TYPE
			SYNTAX	INTEGER
			ACCESS	read-only
			STATUS	current
	DESCRIPTION ""
			::= { mbus73 29 }

mbus73VIF0C		OBJECT-TYPE
			SYNTAX	INTEGER
			ACCESS	read-only
			STATUS	current
	DESCRIPTION ""
			::= { mbus73 30 }

mbus73Value0C		OBJECT-TYPE
			SYNTAX	INTEGER
			ACCESS	read-only
			STATUS	current
	DESCRIPTION ""
			::= { mbus73 31 }

mbus73VIF0D		OBJECT-TYPE
			SYNTAX	INTEGER
			ACCESS	read-only
			STATUS	current
	DESCRIPTION ""
			::= { mbus73 32 }

mbus73Value0D		OBJECT-TYPE
			SYNTAX	INTEGER
			ACCESS	read-only
			STATUS	current
	DESCRIPTION ""
			::= { mbus73 33 }

mbus73VIF0E		OBJECT-TYPE
			SYNTAX	INTEGER
			ACCESS	read-only
			STATUS	current
	DESCRIPTION ""
			::= { mbus73 34 }

mbus73Value0E		OBJECT-TYPE
			SYNTAX	INTEGER
			ACCESS	read-only
			STATUS	current
	DESCRIPTION ""
			::= { mbus73 35 }

mbus73VIF0F		OBJECT-TYPE
			SYNTAX	INTEGER
			ACCESS	read-only
			STATUS	current
	DESCRIPTION ""
			::= { mbus73 36 }

mbus73Value0F		OBJECT-TYPE
			SYNTAX	INTEGER
			ACCESS	read-only
			STATUS	current
	DESCRIPTION ""
			::= { mbus73 37 }

mbus73VIF10		OBJECT-TYPE
			SYNTAX	INTEGER
			ACCESS	read-only
			STATUS	current
	DESCRIPTION ""
			::= { mbus73 38 }

mbus73Value10		OBJECT-TYPE
			SYNTAX	INTEGER
			ACCESS	read-only
			STATUS	current
	DESCRIPTION ""
			::= { mbus73 39 }

mbus73VIF11		OBJECT-TYPE
			SYNTAX	INTEGER
			ACCESS	read-only
			STATUS	current
	DESCRIPTION ""
			::= { mbus73 40 }

mbus73Value11		OBJECT-TYPE
			SYNTAX	INTEGER
			ACCESS	read-only
			STATUS	current
	DESCRIPTION ""
			::= { mbus73 41 }

mbus73VIF12		OBJECT-TYPE
			SYNTAX	INTEGER
			ACCESS	read-only
			STATUS	current
	DESCRIPTION ""
			::= { mbus73 42 }

mbus73Value12		OBJECT-TYPE
			SYNTAX	INTEGER
			ACCESS	read-only
			STATUS	current
	DESCRIPTION ""
			::= { mbus73 43 }

mbus73VIF13		OBJECT-TYPE
			SYNTAX	INTEGER
			ACCESS	read-only
			STATUS	current
	DESCRIPTION ""
			::= { mbus73 44 }

mbus73Value13		OBJECT-TYPE
			SYNTAX	INTEGER
			ACCESS	read-only
			STATUS	current
	DESCRIPTION ""
			::= { mbus73 45 }

mbus73VIF14		OBJECT-TYPE
			SYNTAX	INTEGER
			ACCESS	read-only
			STATUS	current
	DESCRIPTION ""
			::= { mbus73 46 }

mbus73Value14		OBJECT-TYPE
			SYNTAX	INTEGER
			ACCESS	read-only
			STATUS	current
	DESCRIPTION ""
			::= { mbus73 47 }

mbus73VIF15		OBJECT-TYPE
			SYNTAX	INTEGER
			ACCESS	read-only
			STATUS	current
	DESCRIPTION ""
			::= { mbus73 48 }

mbus73Value15		OBJECT-TYPE
			SYNTAX	INTEGER
			ACCESS	read-only
			STATUS	current
	DESCRIPTION ""
			::= { mbus73 49 }

mbus73VIF16		OBJECT-TYPE
			SYNTAX	INTEGER
			ACCESS	read-only
			STATUS	current
	DESCRIPTION ""
			::= { mbus73 50 }

mbus73Value16		OBJECT-TYPE
			SYNTAX	INTEGER
			ACCESS	read-only
			STATUS	current
	DESCRIPTION ""
			::= { mbus73 51 }

mbus73VIF17		OBJECT-TYPE
			SYNTAX	INTEGER
			ACCESS	read-only
			STATUS	current
	DESCRIPTION ""
			::= { mbus73 52 }

mbus73Value17		OBJECT-TYPE
			SYNTAX	INTEGER
			ACCESS	read-only
			STATUS	current
	DESCRIPTION ""
			::= { mbus73 53 }

mbus73VIF18		OBJECT-TYPE
			SYNTAX	INTEGER
			ACCESS	read-only
			STATUS	current
	DESCRIPTION ""
			::= { mbus73 54 }

mbus73Value18		OBJECT-TYPE
			SYNTAX	INTEGER
			ACCESS	read-only
			STATUS	current
	DESCRIPTION ""
			::= { mbus73 55 }

mbus73VIF19		OBJECT-TYPE
			SYNTAX	INTEGER
			ACCESS	read-only
			STATUS	current
	DESCRIPTION ""
			::= { mbus73 56 }

mbus73Value19		OBJECT-TYPE
			SYNTAX	INTEGER
			ACCESS	read-only
			STATUS	current
	DESCRIPTION ""
			::= { mbus73 57 }

mbus73VIF1A		OBJECT-TYPE
			SYNTAX	INTEGER
			ACCESS	read-only
			STATUS	current
	DESCRIPTION ""
			::= { mbus73 58 }

mbus73Value1A		OBJECT-TYPE
			SYNTAX	INTEGER
			ACCESS	read-only
			STATUS	current
	DESCRIPTION ""
			::= { mbus73 59 }

mbus73VIF1B		OBJECT-TYPE
			SYNTAX	INTEGER
			ACCESS	read-only
			STATUS	current
	DESCRIPTION ""
			::= { mbus73 60 }

mbus73Value1B		OBJECT-TYPE
			SYNTAX	INTEGER
			ACCESS	read-only
			STATUS	current
	DESCRIPTION ""
			::= { mbus73 61 }

mbus73VIF1C		OBJECT-TYPE
			SYNTAX	INTEGER
			ACCESS	read-only
			STATUS	current
	DESCRIPTION ""
			::= { mbus73 62 }

mbus73Value1C		OBJECT-TYPE
			SYNTAX	INTEGER
			ACCESS	read-only
			STATUS	current
	DESCRIPTION ""
			::= { mbus73 63 }

mbus73VIF1D		OBJECT-TYPE
			SYNTAX	INTEGER
			ACCESS	read-only
			STATUS	current
	DESCRIPTION ""
			::= { mbus73 64 }

mbus73Value1D		OBJECT-TYPE
			SYNTAX	INTEGER
			ACCESS	read-only
			STATUS	current
	DESCRIPTION ""
			::= { mbus73 65 }

mbus73VIF1E		OBJECT-TYPE
			SYNTAX	INTEGER
			ACCESS	read-only
			STATUS	current
	DESCRIPTION ""
			::= { mbus73 66 }

mbus73Value1E		OBJECT-TYPE
			SYNTAX	INTEGER
			ACCESS	read-only
			STATUS	current
	DESCRIPTION ""
			::= { mbus73 67 }

mbus73VIF1F		OBJECT-TYPE
			SYNTAX	INTEGER
			ACCESS	read-only
			STATUS	current
	DESCRIPTION ""
			::= { mbus73 68 }

mbus73Value1F		OBJECT-TYPE
			SYNTAX	INTEGER
			ACCESS	read-only
			STATUS	current
	DESCRIPTION ""
			::= { mbus73 69 }

mbus73VIF20		OBJECT-TYPE
			SYNTAX	INTEGER
			ACCESS	read-only
			STATUS	current
	DESCRIPTION ""
			::= { mbus73 70 }

mbus73Value20		OBJECT-TYPE
			SYNTAX	INTEGER
			ACCESS	read-only
			STATUS	current
	DESCRIPTION ""
			::= { mbus73 71 }

mbus73VIF21		OBJECT-TYPE
			SYNTAX	INTEGER
			ACCESS	read-only
			STATUS	current
	DESCRIPTION ""
			::= { mbus73 72 }

mbus73Value21		OBJECT-TYPE
			SYNTAX	INTEGER
			ACCESS	read-only
			STATUS	current
	DESCRIPTION ""
			::= { mbus73 73 }

mbus73VIF22		OBJECT-TYPE
			SYNTAX	INTEGER
			ACCESS	read-only
			STATUS	current
	DESCRIPTION ""
			::= { mbus73 74 }

mbus73Value22		OBJECT-TYPE
			SYNTAX	INTEGER
			ACCESS	read-only
			STATUS	current
	DESCRIPTION ""
			::= { mbus73 75 }

mbus73VIF23		OBJECT-TYPE
			SYNTAX	INTEGER
			ACCESS	read-only
			STATUS	current
	DESCRIPTION ""
			::= { mbus73 76 }

mbus73Value23		OBJECT-TYPE
			SYNTAX	INTEGER
			ACCESS	read-only
			STATUS	current
	DESCRIPTION ""
			::= { mbus73 77 }

mbus73VIF24		OBJECT-TYPE
			SYNTAX	INTEGER
			ACCESS	read-only
			STATUS	current
	DESCRIPTION ""
			::= { mbus73 78 }

mbus73Value24		OBJECT-TYPE
			SYNTAX	INTEGER
			ACCESS	read-only
			STATUS	current
	DESCRIPTION ""
			::= { mbus73 79 }

mbus73VIF25		OBJECT-TYPE
			SYNTAX	INTEGER
			ACCESS	read-only
			STATUS	current
	DESCRIPTION ""
			::= { mbus73 80 }

mbus73Value25		OBJECT-TYPE
			SYNTAX	INTEGER
			ACCESS	read-only
			STATUS	current
	DESCRIPTION ""
			::= { mbus73 81 }

mbus73VIF26		OBJECT-TYPE
			SYNTAX	INTEGER
			ACCESS	read-only
			STATUS	current
	DESCRIPTION ""
			::= { mbus73 82 }

mbus73Value26		OBJECT-TYPE
			SYNTAX	INTEGER
			ACCESS	read-only
			STATUS	current
	DESCRIPTION ""
			::= { mbus73 83 }

mbus73VIF27		OBJECT-TYPE
			SYNTAX	INTEGER
			ACCESS	read-only
			STATUS	current
	DESCRIPTION ""
			::= { mbus73 84 }

mbus73Value27		OBJECT-TYPE
			SYNTAX	INTEGER
			ACCESS	read-only
			STATUS	current
	DESCRIPTION ""
			::= { mbus73 85 }

mbus73VIF28		OBJECT-TYPE
			SYNTAX	INTEGER
			ACCESS	read-only
			STATUS	current
	DESCRIPTION ""
			::= { mbus73 86 }

mbus73Value28		OBJECT-TYPE
			SYNTAX	INTEGER
			ACCESS	read-only
			STATUS	current
	DESCRIPTION ""
			::= { mbus73 87 }

mbus73VIF29		OBJECT-TYPE
			SYNTAX	INTEGER
			ACCESS	read-only
			STATUS	current
	DESCRIPTION ""
			::= { mbus73 88 }

mbus73Value29		OBJECT-TYPE
			SYNTAX	INTEGER
			ACCESS	read-only
			STATUS	current
	DESCRIPTION ""
			::= { mbus73 89 }

mbus73VIF2A		OBJECT-TYPE
			SYNTAX	INTEGER
			ACCESS	read-only
			STATUS	current
	DESCRIPTION ""
			::= { mbus73 90 }

mbus73Value2A		OBJECT-TYPE
			SYNTAX	INTEGER
			ACCESS	read-only
			STATUS	current
	DESCRIPTION ""
			::= { mbus73 91 }

mbus73VIF2B		OBJECT-TYPE
			SYNTAX	INTEGER
			ACCESS	read-only
			STATUS	current
	DESCRIPTION ""
			::= { mbus73 92 }

mbus73Value2B		OBJECT-TYPE
			SYNTAX	INTEGER
			ACCESS	read-only
			STATUS	current
	DESCRIPTION ""
			::= { mbus73 93 }

mbus73VIF2C		OBJECT-TYPE
			SYNTAX	INTEGER
			ACCESS	read-only
			STATUS	current
	DESCRIPTION ""
			::= { mbus73 94 }

mbus73Value2C		OBJECT-TYPE
			SYNTAX	INTEGER
			ACCESS	read-only
			STATUS	current
	DESCRIPTION ""
			::= { mbus73 95 }

mbus73VIF2D		OBJECT-TYPE
			SYNTAX	INTEGER
			ACCESS	read-only
			STATUS	current
	DESCRIPTION ""
			::= { mbus73 96 }

mbus73Value2D		OBJECT-TYPE
			SYNTAX	INTEGER
			ACCESS	read-only
			STATUS	current
	DESCRIPTION ""
			::= { mbus73 97 }

mbus73VIF2E		OBJECT-TYPE
			SYNTAX	INTEGER
			ACCESS	read-only
			STATUS	current
	DESCRIPTION ""
			::= { mbus73 98 }

mbus73Value2E		OBJECT-TYPE
			SYNTAX	INTEGER
			ACCESS	read-only
			STATUS	current
	DESCRIPTION ""
			::= { mbus73 99 }

mbus73VIF2F		OBJECT-TYPE
			SYNTAX	INTEGER
			ACCESS	read-only
			STATUS	current
	DESCRIPTION ""
			::= { mbus73 100 }

mbus73Value2F		OBJECT-TYPE
			SYNTAX	INTEGER
			ACCESS	read-only
			STATUS	current
	DESCRIPTION ""
			::= { mbus73 101 }

mbus74			OBJECT IDENTIFIER ::= { mbus 116 }

mbus74IdNumber		OBJECT-TYPE
			SYNTAX	Gauge
			ACCESS	read-only
			STATUS	current
	DESCRIPTION ""
			::= { mbus74 1 }

mbus74Manufacturer	OBJECT-TYPE
			SYNTAX	Gauge
			ACCESS	read-only
			STATUS	current
	DESCRIPTION ""
			::= { mbus74 2 }

mbus74Version		OBJECT-TYPE
			SYNTAX	Gauge
			ACCESS	read-only
			STATUS	current
	DESCRIPTION ""
			::= { mbus74 3 }

mbus74Medium		OBJECT-TYPE
			SYNTAX	Gauge
			ACCESS	read-only
			STATUS	current
	DESCRIPTION ""
			::= { mbus74 4 }

mbus74Status		OBJECT-TYPE
			SYNTAX	Gauge
			ACCESS	read-only
			STATUS	current
	DESCRIPTION ""
			::= { mbus74 5 }

mbus74VIF00		OBJECT-TYPE
			SYNTAX	INTEGER
			ACCESS	read-only
			STATUS	current
	DESCRIPTION ""
			::= { mbus74 6 }

mbus74Value00		OBJECT-TYPE
			SYNTAX	INTEGER
			ACCESS	read-only
			STATUS	current
	DESCRIPTION ""
			::= { mbus74 7 }

mbus74VIF01		OBJECT-TYPE
			SYNTAX	INTEGER
			ACCESS	read-only
			STATUS	current
	DESCRIPTION ""
			::= { mbus74 8 }

mbus74Value01		OBJECT-TYPE
			SYNTAX	INTEGER
			ACCESS	read-only
			STATUS	current
	DESCRIPTION ""
			::= { mbus74 9 }

mbus74VIF02		OBJECT-TYPE
			SYNTAX	INTEGER
			ACCESS	read-only
			STATUS	current
	DESCRIPTION ""
			::= { mbus74 10 }

mbus74Value02		OBJECT-TYPE
			SYNTAX	INTEGER
			ACCESS	read-only
			STATUS	current
	DESCRIPTION ""
			::= { mbus74 11 }

mbus74VIF03		OBJECT-TYPE
			SYNTAX	INTEGER
			ACCESS	read-only
			STATUS	current
	DESCRIPTION ""
			::= { mbus74 12 }

mbus74Value03		OBJECT-TYPE
			SYNTAX	INTEGER
			ACCESS	read-only
			STATUS	current
	DESCRIPTION ""
			::= { mbus74 13 }

mbus74VIF04		OBJECT-TYPE
			SYNTAX	INTEGER
			ACCESS	read-only
			STATUS	current
	DESCRIPTION ""
			::= { mbus74 14 }

mbus74Value04		OBJECT-TYPE
			SYNTAX	INTEGER
			ACCESS	read-only
			STATUS	current
	DESCRIPTION ""
			::= { mbus74 15 }

mbus74VIF05		OBJECT-TYPE
			SYNTAX	INTEGER
			ACCESS	read-only
			STATUS	current
	DESCRIPTION ""
			::= { mbus74 16 }

mbus74Value05		OBJECT-TYPE
			SYNTAX	INTEGER
			ACCESS	read-only
			STATUS	current
	DESCRIPTION ""
			::= { mbus74 17 }

mbus74VIF06		OBJECT-TYPE
			SYNTAX	INTEGER
			ACCESS	read-only
			STATUS	current
	DESCRIPTION ""
			::= { mbus74 18 }

mbus74Value06		OBJECT-TYPE
			SYNTAX	INTEGER
			ACCESS	read-only
			STATUS	current
	DESCRIPTION ""
			::= { mbus74 19 }

mbus74VIF07		OBJECT-TYPE
			SYNTAX	INTEGER
			ACCESS	read-only
			STATUS	current
	DESCRIPTION ""
			::= { mbus74 20 }

mbus74Value07		OBJECT-TYPE
			SYNTAX	INTEGER
			ACCESS	read-only
			STATUS	current
	DESCRIPTION ""
			::= { mbus74 21 }

mbus74VIF08		OBJECT-TYPE
			SYNTAX	INTEGER
			ACCESS	read-only
			STATUS	current
	DESCRIPTION ""
			::= { mbus74 22 }

mbus74Value08		OBJECT-TYPE
			SYNTAX	INTEGER
			ACCESS	read-only
			STATUS	current
	DESCRIPTION ""
			::= { mbus74 23 }

mbus74VIF09		OBJECT-TYPE
			SYNTAX	INTEGER
			ACCESS	read-only
			STATUS	current
	DESCRIPTION ""
			::= { mbus74 24 }

mbus74Value09		OBJECT-TYPE
			SYNTAX	INTEGER
			ACCESS	read-only
			STATUS	current
	DESCRIPTION ""
			::= { mbus74 25 }

mbus74VIF0A		OBJECT-TYPE
			SYNTAX	INTEGER
			ACCESS	read-only
			STATUS	current
	DESCRIPTION ""
			::= { mbus74 26 }

mbus74Value0A		OBJECT-TYPE
			SYNTAX	INTEGER
			ACCESS	read-only
			STATUS	current
	DESCRIPTION ""
			::= { mbus74 27 }

mbus74VIF0B		OBJECT-TYPE
			SYNTAX	INTEGER
			ACCESS	read-only
			STATUS	current
	DESCRIPTION ""
			::= { mbus74 28 }

mbus74Value0B		OBJECT-TYPE
			SYNTAX	INTEGER
			ACCESS	read-only
			STATUS	current
	DESCRIPTION ""
			::= { mbus74 29 }

mbus74VIF0C		OBJECT-TYPE
			SYNTAX	INTEGER
			ACCESS	read-only
			STATUS	current
	DESCRIPTION ""
			::= { mbus74 30 }

mbus74Value0C		OBJECT-TYPE
			SYNTAX	INTEGER
			ACCESS	read-only
			STATUS	current
	DESCRIPTION ""
			::= { mbus74 31 }

mbus74VIF0D		OBJECT-TYPE
			SYNTAX	INTEGER
			ACCESS	read-only
			STATUS	current
	DESCRIPTION ""
			::= { mbus74 32 }

mbus74Value0D		OBJECT-TYPE
			SYNTAX	INTEGER
			ACCESS	read-only
			STATUS	current
	DESCRIPTION ""
			::= { mbus74 33 }

mbus74VIF0E		OBJECT-TYPE
			SYNTAX	INTEGER
			ACCESS	read-only
			STATUS	current
	DESCRIPTION ""
			::= { mbus74 34 }

mbus74Value0E		OBJECT-TYPE
			SYNTAX	INTEGER
			ACCESS	read-only
			STATUS	current
	DESCRIPTION ""
			::= { mbus74 35 }

mbus74VIF0F		OBJECT-TYPE
			SYNTAX	INTEGER
			ACCESS	read-only
			STATUS	current
	DESCRIPTION ""
			::= { mbus74 36 }

mbus74Value0F		OBJECT-TYPE
			SYNTAX	INTEGER
			ACCESS	read-only
			STATUS	current
	DESCRIPTION ""
			::= { mbus74 37 }

mbus74VIF10		OBJECT-TYPE
			SYNTAX	INTEGER
			ACCESS	read-only
			STATUS	current
	DESCRIPTION ""
			::= { mbus74 38 }

mbus74Value10		OBJECT-TYPE
			SYNTAX	INTEGER
			ACCESS	read-only
			STATUS	current
	DESCRIPTION ""
			::= { mbus74 39 }

mbus74VIF11		OBJECT-TYPE
			SYNTAX	INTEGER
			ACCESS	read-only
			STATUS	current
	DESCRIPTION ""
			::= { mbus74 40 }

mbus74Value11		OBJECT-TYPE
			SYNTAX	INTEGER
			ACCESS	read-only
			STATUS	current
	DESCRIPTION ""
			::= { mbus74 41 }

mbus74VIF12		OBJECT-TYPE
			SYNTAX	INTEGER
			ACCESS	read-only
			STATUS	current
	DESCRIPTION ""
			::= { mbus74 42 }

mbus74Value12		OBJECT-TYPE
			SYNTAX	INTEGER
			ACCESS	read-only
			STATUS	current
	DESCRIPTION ""
			::= { mbus74 43 }

mbus74VIF13		OBJECT-TYPE
			SYNTAX	INTEGER
			ACCESS	read-only
			STATUS	current
	DESCRIPTION ""
			::= { mbus74 44 }

mbus74Value13		OBJECT-TYPE
			SYNTAX	INTEGER
			ACCESS	read-only
			STATUS	current
	DESCRIPTION ""
			::= { mbus74 45 }

mbus74VIF14		OBJECT-TYPE
			SYNTAX	INTEGER
			ACCESS	read-only
			STATUS	current
	DESCRIPTION ""
			::= { mbus74 46 }

mbus74Value14		OBJECT-TYPE
			SYNTAX	INTEGER
			ACCESS	read-only
			STATUS	current
	DESCRIPTION ""
			::= { mbus74 47 }

mbus74VIF15		OBJECT-TYPE
			SYNTAX	INTEGER
			ACCESS	read-only
			STATUS	current
	DESCRIPTION ""
			::= { mbus74 48 }

mbus74Value15		OBJECT-TYPE
			SYNTAX	INTEGER
			ACCESS	read-only
			STATUS	current
	DESCRIPTION ""
			::= { mbus74 49 }

mbus74VIF16		OBJECT-TYPE
			SYNTAX	INTEGER
			ACCESS	read-only
			STATUS	current
	DESCRIPTION ""
			::= { mbus74 50 }

mbus74Value16		OBJECT-TYPE
			SYNTAX	INTEGER
			ACCESS	read-only
			STATUS	current
	DESCRIPTION ""
			::= { mbus74 51 }

mbus74VIF17		OBJECT-TYPE
			SYNTAX	INTEGER
			ACCESS	read-only
			STATUS	current
	DESCRIPTION ""
			::= { mbus74 52 }

mbus74Value17		OBJECT-TYPE
			SYNTAX	INTEGER
			ACCESS	read-only
			STATUS	current
	DESCRIPTION ""
			::= { mbus74 53 }

mbus74VIF18		OBJECT-TYPE
			SYNTAX	INTEGER
			ACCESS	read-only
			STATUS	current
	DESCRIPTION ""
			::= { mbus74 54 }

mbus74Value18		OBJECT-TYPE
			SYNTAX	INTEGER
			ACCESS	read-only
			STATUS	current
	DESCRIPTION ""
			::= { mbus74 55 }

mbus74VIF19		OBJECT-TYPE
			SYNTAX	INTEGER
			ACCESS	read-only
			STATUS	current
	DESCRIPTION ""
			::= { mbus74 56 }

mbus74Value19		OBJECT-TYPE
			SYNTAX	INTEGER
			ACCESS	read-only
			STATUS	current
	DESCRIPTION ""
			::= { mbus74 57 }

mbus74VIF1A		OBJECT-TYPE
			SYNTAX	INTEGER
			ACCESS	read-only
			STATUS	current
	DESCRIPTION ""
			::= { mbus74 58 }

mbus74Value1A		OBJECT-TYPE
			SYNTAX	INTEGER
			ACCESS	read-only
			STATUS	current
	DESCRIPTION ""
			::= { mbus74 59 }

mbus74VIF1B		OBJECT-TYPE
			SYNTAX	INTEGER
			ACCESS	read-only
			STATUS	current
	DESCRIPTION ""
			::= { mbus74 60 }

mbus74Value1B		OBJECT-TYPE
			SYNTAX	INTEGER
			ACCESS	read-only
			STATUS	current
	DESCRIPTION ""
			::= { mbus74 61 }

mbus74VIF1C		OBJECT-TYPE
			SYNTAX	INTEGER
			ACCESS	read-only
			STATUS	current
	DESCRIPTION ""
			::= { mbus74 62 }

mbus74Value1C		OBJECT-TYPE
			SYNTAX	INTEGER
			ACCESS	read-only
			STATUS	current
	DESCRIPTION ""
			::= { mbus74 63 }

mbus74VIF1D		OBJECT-TYPE
			SYNTAX	INTEGER
			ACCESS	read-only
			STATUS	current
	DESCRIPTION ""
			::= { mbus74 64 }

mbus74Value1D		OBJECT-TYPE
			SYNTAX	INTEGER
			ACCESS	read-only
			STATUS	current
	DESCRIPTION ""
			::= { mbus74 65 }

mbus74VIF1E		OBJECT-TYPE
			SYNTAX	INTEGER
			ACCESS	read-only
			STATUS	current
	DESCRIPTION ""
			::= { mbus74 66 }

mbus74Value1E		OBJECT-TYPE
			SYNTAX	INTEGER
			ACCESS	read-only
			STATUS	current
	DESCRIPTION ""
			::= { mbus74 67 }

mbus74VIF1F		OBJECT-TYPE
			SYNTAX	INTEGER
			ACCESS	read-only
			STATUS	current
	DESCRIPTION ""
			::= { mbus74 68 }

mbus74Value1F		OBJECT-TYPE
			SYNTAX	INTEGER
			ACCESS	read-only
			STATUS	current
	DESCRIPTION ""
			::= { mbus74 69 }

mbus74VIF20		OBJECT-TYPE
			SYNTAX	INTEGER
			ACCESS	read-only
			STATUS	current
	DESCRIPTION ""
			::= { mbus74 70 }

mbus74Value20		OBJECT-TYPE
			SYNTAX	INTEGER
			ACCESS	read-only
			STATUS	current
	DESCRIPTION ""
			::= { mbus74 71 }

mbus74VIF21		OBJECT-TYPE
			SYNTAX	INTEGER
			ACCESS	read-only
			STATUS	current
	DESCRIPTION ""
			::= { mbus74 72 }

mbus74Value21		OBJECT-TYPE
			SYNTAX	INTEGER
			ACCESS	read-only
			STATUS	current
	DESCRIPTION ""
			::= { mbus74 73 }

mbus74VIF22		OBJECT-TYPE
			SYNTAX	INTEGER
			ACCESS	read-only
			STATUS	current
	DESCRIPTION ""
			::= { mbus74 74 }

mbus74Value22		OBJECT-TYPE
			SYNTAX	INTEGER
			ACCESS	read-only
			STATUS	current
	DESCRIPTION ""
			::= { mbus74 75 }

mbus74VIF23		OBJECT-TYPE
			SYNTAX	INTEGER
			ACCESS	read-only
			STATUS	current
	DESCRIPTION ""
			::= { mbus74 76 }

mbus74Value23		OBJECT-TYPE
			SYNTAX	INTEGER
			ACCESS	read-only
			STATUS	current
	DESCRIPTION ""
			::= { mbus74 77 }

mbus74VIF24		OBJECT-TYPE
			SYNTAX	INTEGER
			ACCESS	read-only
			STATUS	current
	DESCRIPTION ""
			::= { mbus74 78 }

mbus74Value24		OBJECT-TYPE
			SYNTAX	INTEGER
			ACCESS	read-only
			STATUS	current
	DESCRIPTION ""
			::= { mbus74 79 }

mbus74VIF25		OBJECT-TYPE
			SYNTAX	INTEGER
			ACCESS	read-only
			STATUS	current
	DESCRIPTION ""
			::= { mbus74 80 }

mbus74Value25		OBJECT-TYPE
			SYNTAX	INTEGER
			ACCESS	read-only
			STATUS	current
	DESCRIPTION ""
			::= { mbus74 81 }

mbus74VIF26		OBJECT-TYPE
			SYNTAX	INTEGER
			ACCESS	read-only
			STATUS	current
	DESCRIPTION ""
			::= { mbus74 82 }

mbus74Value26		OBJECT-TYPE
			SYNTAX	INTEGER
			ACCESS	read-only
			STATUS	current
	DESCRIPTION ""
			::= { mbus74 83 }

mbus74VIF27		OBJECT-TYPE
			SYNTAX	INTEGER
			ACCESS	read-only
			STATUS	current
	DESCRIPTION ""
			::= { mbus74 84 }

mbus74Value27		OBJECT-TYPE
			SYNTAX	INTEGER
			ACCESS	read-only
			STATUS	current
	DESCRIPTION ""
			::= { mbus74 85 }

mbus74VIF28		OBJECT-TYPE
			SYNTAX	INTEGER
			ACCESS	read-only
			STATUS	current
	DESCRIPTION ""
			::= { mbus74 86 }

mbus74Value28		OBJECT-TYPE
			SYNTAX	INTEGER
			ACCESS	read-only
			STATUS	current
	DESCRIPTION ""
			::= { mbus74 87 }

mbus74VIF29		OBJECT-TYPE
			SYNTAX	INTEGER
			ACCESS	read-only
			STATUS	current
	DESCRIPTION ""
			::= { mbus74 88 }

mbus74Value29		OBJECT-TYPE
			SYNTAX	INTEGER
			ACCESS	read-only
			STATUS	current
	DESCRIPTION ""
			::= { mbus74 89 }

mbus74VIF2A		OBJECT-TYPE
			SYNTAX	INTEGER
			ACCESS	read-only
			STATUS	current
	DESCRIPTION ""
			::= { mbus74 90 }

mbus74Value2A		OBJECT-TYPE
			SYNTAX	INTEGER
			ACCESS	read-only
			STATUS	current
	DESCRIPTION ""
			::= { mbus74 91 }

mbus74VIF2B		OBJECT-TYPE
			SYNTAX	INTEGER
			ACCESS	read-only
			STATUS	current
	DESCRIPTION ""
			::= { mbus74 92 }

mbus74Value2B		OBJECT-TYPE
			SYNTAX	INTEGER
			ACCESS	read-only
			STATUS	current
	DESCRIPTION ""
			::= { mbus74 93 }

mbus74VIF2C		OBJECT-TYPE
			SYNTAX	INTEGER
			ACCESS	read-only
			STATUS	current
	DESCRIPTION ""
			::= { mbus74 94 }

mbus74Value2C		OBJECT-TYPE
			SYNTAX	INTEGER
			ACCESS	read-only
			STATUS	current
	DESCRIPTION ""
			::= { mbus74 95 }

mbus74VIF2D		OBJECT-TYPE
			SYNTAX	INTEGER
			ACCESS	read-only
			STATUS	current
	DESCRIPTION ""
			::= { mbus74 96 }

mbus74Value2D		OBJECT-TYPE
			SYNTAX	INTEGER
			ACCESS	read-only
			STATUS	current
	DESCRIPTION ""
			::= { mbus74 97 }

mbus74VIF2E		OBJECT-TYPE
			SYNTAX	INTEGER
			ACCESS	read-only
			STATUS	current
	DESCRIPTION ""
			::= { mbus74 98 }

mbus74Value2E		OBJECT-TYPE
			SYNTAX	INTEGER
			ACCESS	read-only
			STATUS	current
	DESCRIPTION ""
			::= { mbus74 99 }

mbus74VIF2F		OBJECT-TYPE
			SYNTAX	INTEGER
			ACCESS	read-only
			STATUS	current
	DESCRIPTION ""
			::= { mbus74 100 }

mbus74Value2F		OBJECT-TYPE
			SYNTAX	INTEGER
			ACCESS	read-only
			STATUS	current
	DESCRIPTION ""
			::= { mbus74 101 }

mbus75			OBJECT IDENTIFIER ::= { mbus 117 }

mbus75IdNumber		OBJECT-TYPE
			SYNTAX	Gauge
			ACCESS	read-only
			STATUS	current
	DESCRIPTION ""
			::= { mbus75 1 }

mbus75Manufacturer	OBJECT-TYPE
			SYNTAX	Gauge
			ACCESS	read-only
			STATUS	current
	DESCRIPTION ""
			::= { mbus75 2 }

mbus75Version		OBJECT-TYPE
			SYNTAX	Gauge
			ACCESS	read-only
			STATUS	current
	DESCRIPTION ""
			::= { mbus75 3 }

mbus75Medium		OBJECT-TYPE
			SYNTAX	Gauge
			ACCESS	read-only
			STATUS	current
	DESCRIPTION ""
			::= { mbus75 4 }

mbus75Status		OBJECT-TYPE
			SYNTAX	Gauge
			ACCESS	read-only
			STATUS	current
	DESCRIPTION ""
			::= { mbus75 5 }

mbus75VIF00		OBJECT-TYPE
			SYNTAX	INTEGER
			ACCESS	read-only
			STATUS	current
	DESCRIPTION ""
			::= { mbus75 6 }

mbus75Value00		OBJECT-TYPE
			SYNTAX	INTEGER
			ACCESS	read-only
			STATUS	current
	DESCRIPTION ""
			::= { mbus75 7 }

mbus75VIF01		OBJECT-TYPE
			SYNTAX	INTEGER
			ACCESS	read-only
			STATUS	current
	DESCRIPTION ""
			::= { mbus75 8 }

mbus75Value01		OBJECT-TYPE
			SYNTAX	INTEGER
			ACCESS	read-only
			STATUS	current
	DESCRIPTION ""
			::= { mbus75 9 }

mbus75VIF02		OBJECT-TYPE
			SYNTAX	INTEGER
			ACCESS	read-only
			STATUS	current
	DESCRIPTION ""
			::= { mbus75 10 }

mbus75Value02		OBJECT-TYPE
			SYNTAX	INTEGER
			ACCESS	read-only
			STATUS	current
	DESCRIPTION ""
			::= { mbus75 11 }

mbus75VIF03		OBJECT-TYPE
			SYNTAX	INTEGER
			ACCESS	read-only
			STATUS	current
	DESCRIPTION ""
			::= { mbus75 12 }

mbus75Value03		OBJECT-TYPE
			SYNTAX	INTEGER
			ACCESS	read-only
			STATUS	current
	DESCRIPTION ""
			::= { mbus75 13 }

mbus75VIF04		OBJECT-TYPE
			SYNTAX	INTEGER
			ACCESS	read-only
			STATUS	current
	DESCRIPTION ""
			::= { mbus75 14 }

mbus75Value04		OBJECT-TYPE
			SYNTAX	INTEGER
			ACCESS	read-only
			STATUS	current
	DESCRIPTION ""
			::= { mbus75 15 }

mbus75VIF05		OBJECT-TYPE
			SYNTAX	INTEGER
			ACCESS	read-only
			STATUS	current
	DESCRIPTION ""
			::= { mbus75 16 }

mbus75Value05		OBJECT-TYPE
			SYNTAX	INTEGER
			ACCESS	read-only
			STATUS	current
	DESCRIPTION ""
			::= { mbus75 17 }

mbus75VIF06		OBJECT-TYPE
			SYNTAX	INTEGER
			ACCESS	read-only
			STATUS	current
	DESCRIPTION ""
			::= { mbus75 18 }

mbus75Value06		OBJECT-TYPE
			SYNTAX	INTEGER
			ACCESS	read-only
			STATUS	current
	DESCRIPTION ""
			::= { mbus75 19 }

mbus75VIF07		OBJECT-TYPE
			SYNTAX	INTEGER
			ACCESS	read-only
			STATUS	current
	DESCRIPTION ""
			::= { mbus75 20 }

mbus75Value07		OBJECT-TYPE
			SYNTAX	INTEGER
			ACCESS	read-only
			STATUS	current
	DESCRIPTION ""
			::= { mbus75 21 }

mbus75VIF08		OBJECT-TYPE
			SYNTAX	INTEGER
			ACCESS	read-only
			STATUS	current
	DESCRIPTION ""
			::= { mbus75 22 }

mbus75Value08		OBJECT-TYPE
			SYNTAX	INTEGER
			ACCESS	read-only
			STATUS	current
	DESCRIPTION ""
			::= { mbus75 23 }

mbus75VIF09		OBJECT-TYPE
			SYNTAX	INTEGER
			ACCESS	read-only
			STATUS	current
	DESCRIPTION ""
			::= { mbus75 24 }

mbus75Value09		OBJECT-TYPE
			SYNTAX	INTEGER
			ACCESS	read-only
			STATUS	current
	DESCRIPTION ""
			::= { mbus75 25 }

mbus75VIF0A		OBJECT-TYPE
			SYNTAX	INTEGER
			ACCESS	read-only
			STATUS	current
	DESCRIPTION ""
			::= { mbus75 26 }

mbus75Value0A		OBJECT-TYPE
			SYNTAX	INTEGER
			ACCESS	read-only
			STATUS	current
	DESCRIPTION ""
			::= { mbus75 27 }

mbus75VIF0B		OBJECT-TYPE
			SYNTAX	INTEGER
			ACCESS	read-only
			STATUS	current
	DESCRIPTION ""
			::= { mbus75 28 }

mbus75Value0B		OBJECT-TYPE
			SYNTAX	INTEGER
			ACCESS	read-only
			STATUS	current
	DESCRIPTION ""
			::= { mbus75 29 }

mbus75VIF0C		OBJECT-TYPE
			SYNTAX	INTEGER
			ACCESS	read-only
			STATUS	current
	DESCRIPTION ""
			::= { mbus75 30 }

mbus75Value0C		OBJECT-TYPE
			SYNTAX	INTEGER
			ACCESS	read-only
			STATUS	current
	DESCRIPTION ""
			::= { mbus75 31 }

mbus75VIF0D		OBJECT-TYPE
			SYNTAX	INTEGER
			ACCESS	read-only
			STATUS	current
	DESCRIPTION ""
			::= { mbus75 32 }

mbus75Value0D		OBJECT-TYPE
			SYNTAX	INTEGER
			ACCESS	read-only
			STATUS	current
	DESCRIPTION ""
			::= { mbus75 33 }

mbus75VIF0E		OBJECT-TYPE
			SYNTAX	INTEGER
			ACCESS	read-only
			STATUS	current
	DESCRIPTION ""
			::= { mbus75 34 }

mbus75Value0E		OBJECT-TYPE
			SYNTAX	INTEGER
			ACCESS	read-only
			STATUS	current
	DESCRIPTION ""
			::= { mbus75 35 }

mbus75VIF0F		OBJECT-TYPE
			SYNTAX	INTEGER
			ACCESS	read-only
			STATUS	current
	DESCRIPTION ""
			::= { mbus75 36 }

mbus75Value0F		OBJECT-TYPE
			SYNTAX	INTEGER
			ACCESS	read-only
			STATUS	current
	DESCRIPTION ""
			::= { mbus75 37 }

mbus75VIF10		OBJECT-TYPE
			SYNTAX	INTEGER
			ACCESS	read-only
			STATUS	current
	DESCRIPTION ""
			::= { mbus75 38 }

mbus75Value10		OBJECT-TYPE
			SYNTAX	INTEGER
			ACCESS	read-only
			STATUS	current
	DESCRIPTION ""
			::= { mbus75 39 }

mbus75VIF11		OBJECT-TYPE
			SYNTAX	INTEGER
			ACCESS	read-only
			STATUS	current
	DESCRIPTION ""
			::= { mbus75 40 }

mbus75Value11		OBJECT-TYPE
			SYNTAX	INTEGER
			ACCESS	read-only
			STATUS	current
	DESCRIPTION ""
			::= { mbus75 41 }

mbus75VIF12		OBJECT-TYPE
			SYNTAX	INTEGER
			ACCESS	read-only
			STATUS	current
	DESCRIPTION ""
			::= { mbus75 42 }

mbus75Value12		OBJECT-TYPE
			SYNTAX	INTEGER
			ACCESS	read-only
			STATUS	current
	DESCRIPTION ""
			::= { mbus75 43 }

mbus75VIF13		OBJECT-TYPE
			SYNTAX	INTEGER
			ACCESS	read-only
			STATUS	current
	DESCRIPTION ""
			::= { mbus75 44 }

mbus75Value13		OBJECT-TYPE
			SYNTAX	INTEGER
			ACCESS	read-only
			STATUS	current
	DESCRIPTION ""
			::= { mbus75 45 }

mbus75VIF14		OBJECT-TYPE
			SYNTAX	INTEGER
			ACCESS	read-only
			STATUS	current
	DESCRIPTION ""
			::= { mbus75 46 }

mbus75Value14		OBJECT-TYPE
			SYNTAX	INTEGER
			ACCESS	read-only
			STATUS	current
	DESCRIPTION ""
			::= { mbus75 47 }

mbus75VIF15		OBJECT-TYPE
			SYNTAX	INTEGER
			ACCESS	read-only
			STATUS	current
	DESCRIPTION ""
			::= { mbus75 48 }

mbus75Value15		OBJECT-TYPE
			SYNTAX	INTEGER
			ACCESS	read-only
			STATUS	current
	DESCRIPTION ""
			::= { mbus75 49 }

mbus75VIF16		OBJECT-TYPE
			SYNTAX	INTEGER
			ACCESS	read-only
			STATUS	current
	DESCRIPTION ""
			::= { mbus75 50 }

mbus75Value16		OBJECT-TYPE
			SYNTAX	INTEGER
			ACCESS	read-only
			STATUS	current
	DESCRIPTION ""
			::= { mbus75 51 }

mbus75VIF17		OBJECT-TYPE
			SYNTAX	INTEGER
			ACCESS	read-only
			STATUS	current
	DESCRIPTION ""
			::= { mbus75 52 }

mbus75Value17		OBJECT-TYPE
			SYNTAX	INTEGER
			ACCESS	read-only
			STATUS	current
	DESCRIPTION ""
			::= { mbus75 53 }

mbus75VIF18		OBJECT-TYPE
			SYNTAX	INTEGER
			ACCESS	read-only
			STATUS	current
	DESCRIPTION ""
			::= { mbus75 54 }

mbus75Value18		OBJECT-TYPE
			SYNTAX	INTEGER
			ACCESS	read-only
			STATUS	current
	DESCRIPTION ""
			::= { mbus75 55 }

mbus75VIF19		OBJECT-TYPE
			SYNTAX	INTEGER
			ACCESS	read-only
			STATUS	current
	DESCRIPTION ""
			::= { mbus75 56 }

mbus75Value19		OBJECT-TYPE
			SYNTAX	INTEGER
			ACCESS	read-only
			STATUS	current
	DESCRIPTION ""
			::= { mbus75 57 }

mbus75VIF1A		OBJECT-TYPE
			SYNTAX	INTEGER
			ACCESS	read-only
			STATUS	current
	DESCRIPTION ""
			::= { mbus75 58 }

mbus75Value1A		OBJECT-TYPE
			SYNTAX	INTEGER
			ACCESS	read-only
			STATUS	current
	DESCRIPTION ""
			::= { mbus75 59 }

mbus75VIF1B		OBJECT-TYPE
			SYNTAX	INTEGER
			ACCESS	read-only
			STATUS	current
	DESCRIPTION ""
			::= { mbus75 60 }

mbus75Value1B		OBJECT-TYPE
			SYNTAX	INTEGER
			ACCESS	read-only
			STATUS	current
	DESCRIPTION ""
			::= { mbus75 61 }

mbus75VIF1C		OBJECT-TYPE
			SYNTAX	INTEGER
			ACCESS	read-only
			STATUS	current
	DESCRIPTION ""
			::= { mbus75 62 }

mbus75Value1C		OBJECT-TYPE
			SYNTAX	INTEGER
			ACCESS	read-only
			STATUS	current
	DESCRIPTION ""
			::= { mbus75 63 }

mbus75VIF1D		OBJECT-TYPE
			SYNTAX	INTEGER
			ACCESS	read-only
			STATUS	current
	DESCRIPTION ""
			::= { mbus75 64 }

mbus75Value1D		OBJECT-TYPE
			SYNTAX	INTEGER
			ACCESS	read-only
			STATUS	current
	DESCRIPTION ""
			::= { mbus75 65 }

mbus75VIF1E		OBJECT-TYPE
			SYNTAX	INTEGER
			ACCESS	read-only
			STATUS	current
	DESCRIPTION ""
			::= { mbus75 66 }

mbus75Value1E		OBJECT-TYPE
			SYNTAX	INTEGER
			ACCESS	read-only
			STATUS	current
	DESCRIPTION ""
			::= { mbus75 67 }

mbus75VIF1F		OBJECT-TYPE
			SYNTAX	INTEGER
			ACCESS	read-only
			STATUS	current
	DESCRIPTION ""
			::= { mbus75 68 }

mbus75Value1F		OBJECT-TYPE
			SYNTAX	INTEGER
			ACCESS	read-only
			STATUS	current
	DESCRIPTION ""
			::= { mbus75 69 }

mbus75VIF20		OBJECT-TYPE
			SYNTAX	INTEGER
			ACCESS	read-only
			STATUS	current
	DESCRIPTION ""
			::= { mbus75 70 }

mbus75Value20		OBJECT-TYPE
			SYNTAX	INTEGER
			ACCESS	read-only
			STATUS	current
	DESCRIPTION ""
			::= { mbus75 71 }

mbus75VIF21		OBJECT-TYPE
			SYNTAX	INTEGER
			ACCESS	read-only
			STATUS	current
	DESCRIPTION ""
			::= { mbus75 72 }

mbus75Value21		OBJECT-TYPE
			SYNTAX	INTEGER
			ACCESS	read-only
			STATUS	current
	DESCRIPTION ""
			::= { mbus75 73 }

mbus75VIF22		OBJECT-TYPE
			SYNTAX	INTEGER
			ACCESS	read-only
			STATUS	current
	DESCRIPTION ""
			::= { mbus75 74 }

mbus75Value22		OBJECT-TYPE
			SYNTAX	INTEGER
			ACCESS	read-only
			STATUS	current
	DESCRIPTION ""
			::= { mbus75 75 }

mbus75VIF23		OBJECT-TYPE
			SYNTAX	INTEGER
			ACCESS	read-only
			STATUS	current
	DESCRIPTION ""
			::= { mbus75 76 }

mbus75Value23		OBJECT-TYPE
			SYNTAX	INTEGER
			ACCESS	read-only
			STATUS	current
	DESCRIPTION ""
			::= { mbus75 77 }

mbus75VIF24		OBJECT-TYPE
			SYNTAX	INTEGER
			ACCESS	read-only
			STATUS	current
	DESCRIPTION ""
			::= { mbus75 78 }

mbus75Value24		OBJECT-TYPE
			SYNTAX	INTEGER
			ACCESS	read-only
			STATUS	current
	DESCRIPTION ""
			::= { mbus75 79 }

mbus75VIF25		OBJECT-TYPE
			SYNTAX	INTEGER
			ACCESS	read-only
			STATUS	current
	DESCRIPTION ""
			::= { mbus75 80 }

mbus75Value25		OBJECT-TYPE
			SYNTAX	INTEGER
			ACCESS	read-only
			STATUS	current
	DESCRIPTION ""
			::= { mbus75 81 }

mbus75VIF26		OBJECT-TYPE
			SYNTAX	INTEGER
			ACCESS	read-only
			STATUS	current
	DESCRIPTION ""
			::= { mbus75 82 }

mbus75Value26		OBJECT-TYPE
			SYNTAX	INTEGER
			ACCESS	read-only
			STATUS	current
	DESCRIPTION ""
			::= { mbus75 83 }

mbus75VIF27		OBJECT-TYPE
			SYNTAX	INTEGER
			ACCESS	read-only
			STATUS	current
	DESCRIPTION ""
			::= { mbus75 84 }

mbus75Value27		OBJECT-TYPE
			SYNTAX	INTEGER
			ACCESS	read-only
			STATUS	current
	DESCRIPTION ""
			::= { mbus75 85 }

mbus75VIF28		OBJECT-TYPE
			SYNTAX	INTEGER
			ACCESS	read-only
			STATUS	current
	DESCRIPTION ""
			::= { mbus75 86 }

mbus75Value28		OBJECT-TYPE
			SYNTAX	INTEGER
			ACCESS	read-only
			STATUS	current
	DESCRIPTION ""
			::= { mbus75 87 }

mbus75VIF29		OBJECT-TYPE
			SYNTAX	INTEGER
			ACCESS	read-only
			STATUS	current
	DESCRIPTION ""
			::= { mbus75 88 }

mbus75Value29		OBJECT-TYPE
			SYNTAX	INTEGER
			ACCESS	read-only
			STATUS	current
	DESCRIPTION ""
			::= { mbus75 89 }

mbus75VIF2A		OBJECT-TYPE
			SYNTAX	INTEGER
			ACCESS	read-only
			STATUS	current
	DESCRIPTION ""
			::= { mbus75 90 }

mbus75Value2A		OBJECT-TYPE
			SYNTAX	INTEGER
			ACCESS	read-only
			STATUS	current
	DESCRIPTION ""
			::= { mbus75 91 }

mbus75VIF2B		OBJECT-TYPE
			SYNTAX	INTEGER
			ACCESS	read-only
			STATUS	current
	DESCRIPTION ""
			::= { mbus75 92 }

mbus75Value2B		OBJECT-TYPE
			SYNTAX	INTEGER
			ACCESS	read-only
			STATUS	current
	DESCRIPTION ""
			::= { mbus75 93 }

mbus75VIF2C		OBJECT-TYPE
			SYNTAX	INTEGER
			ACCESS	read-only
			STATUS	current
	DESCRIPTION ""
			::= { mbus75 94 }

mbus75Value2C		OBJECT-TYPE
			SYNTAX	INTEGER
			ACCESS	read-only
			STATUS	current
	DESCRIPTION ""
			::= { mbus75 95 }

mbus75VIF2D		OBJECT-TYPE
			SYNTAX	INTEGER
			ACCESS	read-only
			STATUS	current
	DESCRIPTION ""
			::= { mbus75 96 }

mbus75Value2D		OBJECT-TYPE
			SYNTAX	INTEGER
			ACCESS	read-only
			STATUS	current
	DESCRIPTION ""
			::= { mbus75 97 }

mbus75VIF2E		OBJECT-TYPE
			SYNTAX	INTEGER
			ACCESS	read-only
			STATUS	current
	DESCRIPTION ""
			::= { mbus75 98 }

mbus75Value2E		OBJECT-TYPE
			SYNTAX	INTEGER
			ACCESS	read-only
			STATUS	current
	DESCRIPTION ""
			::= { mbus75 99 }

mbus75VIF2F		OBJECT-TYPE
			SYNTAX	INTEGER
			ACCESS	read-only
			STATUS	current
	DESCRIPTION ""
			::= { mbus75 100 }

mbus75Value2F		OBJECT-TYPE
			SYNTAX	INTEGER
			ACCESS	read-only
			STATUS	current
	DESCRIPTION ""
			::= { mbus75 101 }

mbus76			OBJECT IDENTIFIER ::= { mbus 118 }

mbus76IdNumber		OBJECT-TYPE
			SYNTAX	Gauge
			ACCESS	read-only
			STATUS	current
	DESCRIPTION ""
			::= { mbus76 1 }

mbus76Manufacturer	OBJECT-TYPE
			SYNTAX	Gauge
			ACCESS	read-only
			STATUS	current
	DESCRIPTION ""
			::= { mbus76 2 }

mbus76Version		OBJECT-TYPE
			SYNTAX	Gauge
			ACCESS	read-only
			STATUS	current
	DESCRIPTION ""
			::= { mbus76 3 }

mbus76Medium		OBJECT-TYPE
			SYNTAX	Gauge
			ACCESS	read-only
			STATUS	current
	DESCRIPTION ""
			::= { mbus76 4 }

mbus76Status		OBJECT-TYPE
			SYNTAX	Gauge
			ACCESS	read-only
			STATUS	current
	DESCRIPTION ""
			::= { mbus76 5 }

mbus76VIF00		OBJECT-TYPE
			SYNTAX	INTEGER
			ACCESS	read-only
			STATUS	current
	DESCRIPTION ""
			::= { mbus76 6 }

mbus76Value00		OBJECT-TYPE
			SYNTAX	INTEGER
			ACCESS	read-only
			STATUS	current
	DESCRIPTION ""
			::= { mbus76 7 }

mbus76VIF01		OBJECT-TYPE
			SYNTAX	INTEGER
			ACCESS	read-only
			STATUS	current
	DESCRIPTION ""
			::= { mbus76 8 }

mbus76Value01		OBJECT-TYPE
			SYNTAX	INTEGER
			ACCESS	read-only
			STATUS	current
	DESCRIPTION ""
			::= { mbus76 9 }

mbus76VIF02		OBJECT-TYPE
			SYNTAX	INTEGER
			ACCESS	read-only
			STATUS	current
	DESCRIPTION ""
			::= { mbus76 10 }

mbus76Value02		OBJECT-TYPE
			SYNTAX	INTEGER
			ACCESS	read-only
			STATUS	current
	DESCRIPTION ""
			::= { mbus76 11 }

mbus76VIF03		OBJECT-TYPE
			SYNTAX	INTEGER
			ACCESS	read-only
			STATUS	current
	DESCRIPTION ""
			::= { mbus76 12 }

mbus76Value03		OBJECT-TYPE
			SYNTAX	INTEGER
			ACCESS	read-only
			STATUS	current
	DESCRIPTION ""
			::= { mbus76 13 }

mbus76VIF04		OBJECT-TYPE
			SYNTAX	INTEGER
			ACCESS	read-only
			STATUS	current
	DESCRIPTION ""
			::= { mbus76 14 }

mbus76Value04		OBJECT-TYPE
			SYNTAX	INTEGER
			ACCESS	read-only
			STATUS	current
	DESCRIPTION ""
			::= { mbus76 15 }

mbus76VIF05		OBJECT-TYPE
			SYNTAX	INTEGER
			ACCESS	read-only
			STATUS	current
	DESCRIPTION ""
			::= { mbus76 16 }

mbus76Value05		OBJECT-TYPE
			SYNTAX	INTEGER
			ACCESS	read-only
			STATUS	current
	DESCRIPTION ""
			::= { mbus76 17 }

mbus76VIF06		OBJECT-TYPE
			SYNTAX	INTEGER
			ACCESS	read-only
			STATUS	current
	DESCRIPTION ""
			::= { mbus76 18 }

mbus76Value06		OBJECT-TYPE
			SYNTAX	INTEGER
			ACCESS	read-only
			STATUS	current
	DESCRIPTION ""
			::= { mbus76 19 }

mbus76VIF07		OBJECT-TYPE
			SYNTAX	INTEGER
			ACCESS	read-only
			STATUS	current
	DESCRIPTION ""
			::= { mbus76 20 }

mbus76Value07		OBJECT-TYPE
			SYNTAX	INTEGER
			ACCESS	read-only
			STATUS	current
	DESCRIPTION ""
			::= { mbus76 21 }

mbus76VIF08		OBJECT-TYPE
			SYNTAX	INTEGER
			ACCESS	read-only
			STATUS	current
	DESCRIPTION ""
			::= { mbus76 22 }

mbus76Value08		OBJECT-TYPE
			SYNTAX	INTEGER
			ACCESS	read-only
			STATUS	current
	DESCRIPTION ""
			::= { mbus76 23 }

mbus76VIF09		OBJECT-TYPE
			SYNTAX	INTEGER
			ACCESS	read-only
			STATUS	current
	DESCRIPTION ""
			::= { mbus76 24 }

mbus76Value09		OBJECT-TYPE
			SYNTAX	INTEGER
			ACCESS	read-only
			STATUS	current
	DESCRIPTION ""
			::= { mbus76 25 }

mbus76VIF0A		OBJECT-TYPE
			SYNTAX	INTEGER
			ACCESS	read-only
			STATUS	current
	DESCRIPTION ""
			::= { mbus76 26 }

mbus76Value0A		OBJECT-TYPE
			SYNTAX	INTEGER
			ACCESS	read-only
			STATUS	current
	DESCRIPTION ""
			::= { mbus76 27 }

mbus76VIF0B		OBJECT-TYPE
			SYNTAX	INTEGER
			ACCESS	read-only
			STATUS	current
	DESCRIPTION ""
			::= { mbus76 28 }

mbus76Value0B		OBJECT-TYPE
			SYNTAX	INTEGER
			ACCESS	read-only
			STATUS	current
	DESCRIPTION ""
			::= { mbus76 29 }

mbus76VIF0C		OBJECT-TYPE
			SYNTAX	INTEGER
			ACCESS	read-only
			STATUS	current
	DESCRIPTION ""
			::= { mbus76 30 }

mbus76Value0C		OBJECT-TYPE
			SYNTAX	INTEGER
			ACCESS	read-only
			STATUS	current
	DESCRIPTION ""
			::= { mbus76 31 }

mbus76VIF0D		OBJECT-TYPE
			SYNTAX	INTEGER
			ACCESS	read-only
			STATUS	current
	DESCRIPTION ""
			::= { mbus76 32 }

mbus76Value0D		OBJECT-TYPE
			SYNTAX	INTEGER
			ACCESS	read-only
			STATUS	current
	DESCRIPTION ""
			::= { mbus76 33 }

mbus76VIF0E		OBJECT-TYPE
			SYNTAX	INTEGER
			ACCESS	read-only
			STATUS	current
	DESCRIPTION ""
			::= { mbus76 34 }

mbus76Value0E		OBJECT-TYPE
			SYNTAX	INTEGER
			ACCESS	read-only
			STATUS	current
	DESCRIPTION ""
			::= { mbus76 35 }

mbus76VIF0F		OBJECT-TYPE
			SYNTAX	INTEGER
			ACCESS	read-only
			STATUS	current
	DESCRIPTION ""
			::= { mbus76 36 }

mbus76Value0F		OBJECT-TYPE
			SYNTAX	INTEGER
			ACCESS	read-only
			STATUS	current
	DESCRIPTION ""
			::= { mbus76 37 }

mbus76VIF10		OBJECT-TYPE
			SYNTAX	INTEGER
			ACCESS	read-only
			STATUS	current
	DESCRIPTION ""
			::= { mbus76 38 }

mbus76Value10		OBJECT-TYPE
			SYNTAX	INTEGER
			ACCESS	read-only
			STATUS	current
	DESCRIPTION ""
			::= { mbus76 39 }

mbus76VIF11		OBJECT-TYPE
			SYNTAX	INTEGER
			ACCESS	read-only
			STATUS	current
	DESCRIPTION ""
			::= { mbus76 40 }

mbus76Value11		OBJECT-TYPE
			SYNTAX	INTEGER
			ACCESS	read-only
			STATUS	current
	DESCRIPTION ""
			::= { mbus76 41 }

mbus76VIF12		OBJECT-TYPE
			SYNTAX	INTEGER
			ACCESS	read-only
			STATUS	current
	DESCRIPTION ""
			::= { mbus76 42 }

mbus76Value12		OBJECT-TYPE
			SYNTAX	INTEGER
			ACCESS	read-only
			STATUS	current
	DESCRIPTION ""
			::= { mbus76 43 }

mbus76VIF13		OBJECT-TYPE
			SYNTAX	INTEGER
			ACCESS	read-only
			STATUS	current
	DESCRIPTION ""
			::= { mbus76 44 }

mbus76Value13		OBJECT-TYPE
			SYNTAX	INTEGER
			ACCESS	read-only
			STATUS	current
	DESCRIPTION ""
			::= { mbus76 45 }

mbus76VIF14		OBJECT-TYPE
			SYNTAX	INTEGER
			ACCESS	read-only
			STATUS	current
	DESCRIPTION ""
			::= { mbus76 46 }

mbus76Value14		OBJECT-TYPE
			SYNTAX	INTEGER
			ACCESS	read-only
			STATUS	current
	DESCRIPTION ""
			::= { mbus76 47 }

mbus76VIF15		OBJECT-TYPE
			SYNTAX	INTEGER
			ACCESS	read-only
			STATUS	current
	DESCRIPTION ""
			::= { mbus76 48 }

mbus76Value15		OBJECT-TYPE
			SYNTAX	INTEGER
			ACCESS	read-only
			STATUS	current
	DESCRIPTION ""
			::= { mbus76 49 }

mbus76VIF16		OBJECT-TYPE
			SYNTAX	INTEGER
			ACCESS	read-only
			STATUS	current
	DESCRIPTION ""
			::= { mbus76 50 }

mbus76Value16		OBJECT-TYPE
			SYNTAX	INTEGER
			ACCESS	read-only
			STATUS	current
	DESCRIPTION ""
			::= { mbus76 51 }

mbus76VIF17		OBJECT-TYPE
			SYNTAX	INTEGER
			ACCESS	read-only
			STATUS	current
	DESCRIPTION ""
			::= { mbus76 52 }

mbus76Value17		OBJECT-TYPE
			SYNTAX	INTEGER
			ACCESS	read-only
			STATUS	current
	DESCRIPTION ""
			::= { mbus76 53 }

mbus76VIF18		OBJECT-TYPE
			SYNTAX	INTEGER
			ACCESS	read-only
			STATUS	current
	DESCRIPTION ""
			::= { mbus76 54 }

mbus76Value18		OBJECT-TYPE
			SYNTAX	INTEGER
			ACCESS	read-only
			STATUS	current
	DESCRIPTION ""
			::= { mbus76 55 }

mbus76VIF19		OBJECT-TYPE
			SYNTAX	INTEGER
			ACCESS	read-only
			STATUS	current
	DESCRIPTION ""
			::= { mbus76 56 }

mbus76Value19		OBJECT-TYPE
			SYNTAX	INTEGER
			ACCESS	read-only
			STATUS	current
	DESCRIPTION ""
			::= { mbus76 57 }

mbus76VIF1A		OBJECT-TYPE
			SYNTAX	INTEGER
			ACCESS	read-only
			STATUS	current
	DESCRIPTION ""
			::= { mbus76 58 }

mbus76Value1A		OBJECT-TYPE
			SYNTAX	INTEGER
			ACCESS	read-only
			STATUS	current
	DESCRIPTION ""
			::= { mbus76 59 }

mbus76VIF1B		OBJECT-TYPE
			SYNTAX	INTEGER
			ACCESS	read-only
			STATUS	current
	DESCRIPTION ""
			::= { mbus76 60 }

mbus76Value1B		OBJECT-TYPE
			SYNTAX	INTEGER
			ACCESS	read-only
			STATUS	current
	DESCRIPTION ""
			::= { mbus76 61 }

mbus76VIF1C		OBJECT-TYPE
			SYNTAX	INTEGER
			ACCESS	read-only
			STATUS	current
	DESCRIPTION ""
			::= { mbus76 62 }

mbus76Value1C		OBJECT-TYPE
			SYNTAX	INTEGER
			ACCESS	read-only
			STATUS	current
	DESCRIPTION ""
			::= { mbus76 63 }

mbus76VIF1D		OBJECT-TYPE
			SYNTAX	INTEGER
			ACCESS	read-only
			STATUS	current
	DESCRIPTION ""
			::= { mbus76 64 }

mbus76Value1D		OBJECT-TYPE
			SYNTAX	INTEGER
			ACCESS	read-only
			STATUS	current
	DESCRIPTION ""
			::= { mbus76 65 }

mbus76VIF1E		OBJECT-TYPE
			SYNTAX	INTEGER
			ACCESS	read-only
			STATUS	current
	DESCRIPTION ""
			::= { mbus76 66 }

mbus76Value1E		OBJECT-TYPE
			SYNTAX	INTEGER
			ACCESS	read-only
			STATUS	current
	DESCRIPTION ""
			::= { mbus76 67 }

mbus76VIF1F		OBJECT-TYPE
			SYNTAX	INTEGER
			ACCESS	read-only
			STATUS	current
	DESCRIPTION ""
			::= { mbus76 68 }

mbus76Value1F		OBJECT-TYPE
			SYNTAX	INTEGER
			ACCESS	read-only
			STATUS	current
	DESCRIPTION ""
			::= { mbus76 69 }

mbus76VIF20		OBJECT-TYPE
			SYNTAX	INTEGER
			ACCESS	read-only
			STATUS	current
	DESCRIPTION ""
			::= { mbus76 70 }

mbus76Value20		OBJECT-TYPE
			SYNTAX	INTEGER
			ACCESS	read-only
			STATUS	current
	DESCRIPTION ""
			::= { mbus76 71 }

mbus76VIF21		OBJECT-TYPE
			SYNTAX	INTEGER
			ACCESS	read-only
			STATUS	current
	DESCRIPTION ""
			::= { mbus76 72 }

mbus76Value21		OBJECT-TYPE
			SYNTAX	INTEGER
			ACCESS	read-only
			STATUS	current
	DESCRIPTION ""
			::= { mbus76 73 }

mbus76VIF22		OBJECT-TYPE
			SYNTAX	INTEGER
			ACCESS	read-only
			STATUS	current
	DESCRIPTION ""
			::= { mbus76 74 }

mbus76Value22		OBJECT-TYPE
			SYNTAX	INTEGER
			ACCESS	read-only
			STATUS	current
	DESCRIPTION ""
			::= { mbus76 75 }

mbus76VIF23		OBJECT-TYPE
			SYNTAX	INTEGER
			ACCESS	read-only
			STATUS	current
	DESCRIPTION ""
			::= { mbus76 76 }

mbus76Value23		OBJECT-TYPE
			SYNTAX	INTEGER
			ACCESS	read-only
			STATUS	current
	DESCRIPTION ""
			::= { mbus76 77 }

mbus76VIF24		OBJECT-TYPE
			SYNTAX	INTEGER
			ACCESS	read-only
			STATUS	current
	DESCRIPTION ""
			::= { mbus76 78 }

mbus76Value24		OBJECT-TYPE
			SYNTAX	INTEGER
			ACCESS	read-only
			STATUS	current
	DESCRIPTION ""
			::= { mbus76 79 }

mbus76VIF25		OBJECT-TYPE
			SYNTAX	INTEGER
			ACCESS	read-only
			STATUS	current
	DESCRIPTION ""
			::= { mbus76 80 }

mbus76Value25		OBJECT-TYPE
			SYNTAX	INTEGER
			ACCESS	read-only
			STATUS	current
	DESCRIPTION ""
			::= { mbus76 81 }

mbus76VIF26		OBJECT-TYPE
			SYNTAX	INTEGER
			ACCESS	read-only
			STATUS	current
	DESCRIPTION ""
			::= { mbus76 82 }

mbus76Value26		OBJECT-TYPE
			SYNTAX	INTEGER
			ACCESS	read-only
			STATUS	current
	DESCRIPTION ""
			::= { mbus76 83 }

mbus76VIF27		OBJECT-TYPE
			SYNTAX	INTEGER
			ACCESS	read-only
			STATUS	current
	DESCRIPTION ""
			::= { mbus76 84 }

mbus76Value27		OBJECT-TYPE
			SYNTAX	INTEGER
			ACCESS	read-only
			STATUS	current
	DESCRIPTION ""
			::= { mbus76 85 }

mbus76VIF28		OBJECT-TYPE
			SYNTAX	INTEGER
			ACCESS	read-only
			STATUS	current
	DESCRIPTION ""
			::= { mbus76 86 }

mbus76Value28		OBJECT-TYPE
			SYNTAX	INTEGER
			ACCESS	read-only
			STATUS	current
	DESCRIPTION ""
			::= { mbus76 87 }

mbus76VIF29		OBJECT-TYPE
			SYNTAX	INTEGER
			ACCESS	read-only
			STATUS	current
	DESCRIPTION ""
			::= { mbus76 88 }

mbus76Value29		OBJECT-TYPE
			SYNTAX	INTEGER
			ACCESS	read-only
			STATUS	current
	DESCRIPTION ""
			::= { mbus76 89 }

mbus76VIF2A		OBJECT-TYPE
			SYNTAX	INTEGER
			ACCESS	read-only
			STATUS	current
	DESCRIPTION ""
			::= { mbus76 90 }

mbus76Value2A		OBJECT-TYPE
			SYNTAX	INTEGER
			ACCESS	read-only
			STATUS	current
	DESCRIPTION ""
			::= { mbus76 91 }

mbus76VIF2B		OBJECT-TYPE
			SYNTAX	INTEGER
			ACCESS	read-only
			STATUS	current
	DESCRIPTION ""
			::= { mbus76 92 }

mbus76Value2B		OBJECT-TYPE
			SYNTAX	INTEGER
			ACCESS	read-only
			STATUS	current
	DESCRIPTION ""
			::= { mbus76 93 }

mbus76VIF2C		OBJECT-TYPE
			SYNTAX	INTEGER
			ACCESS	read-only
			STATUS	current
	DESCRIPTION ""
			::= { mbus76 94 }

mbus76Value2C		OBJECT-TYPE
			SYNTAX	INTEGER
			ACCESS	read-only
			STATUS	current
	DESCRIPTION ""
			::= { mbus76 95 }

mbus76VIF2D		OBJECT-TYPE
			SYNTAX	INTEGER
			ACCESS	read-only
			STATUS	current
	DESCRIPTION ""
			::= { mbus76 96 }

mbus76Value2D		OBJECT-TYPE
			SYNTAX	INTEGER
			ACCESS	read-only
			STATUS	current
	DESCRIPTION ""
			::= { mbus76 97 }

mbus76VIF2E		OBJECT-TYPE
			SYNTAX	INTEGER
			ACCESS	read-only
			STATUS	current
	DESCRIPTION ""
			::= { mbus76 98 }

mbus76Value2E		OBJECT-TYPE
			SYNTAX	INTEGER
			ACCESS	read-only
			STATUS	current
	DESCRIPTION ""
			::= { mbus76 99 }

mbus76VIF2F		OBJECT-TYPE
			SYNTAX	INTEGER
			ACCESS	read-only
			STATUS	current
	DESCRIPTION ""
			::= { mbus76 100 }

mbus76Value2F		OBJECT-TYPE
			SYNTAX	INTEGER
			ACCESS	read-only
			STATUS	current
	DESCRIPTION ""
			::= { mbus76 101 }

mbus77			OBJECT IDENTIFIER ::= { mbus 119 }

mbus77IdNumber		OBJECT-TYPE
			SYNTAX	Gauge
			ACCESS	read-only
			STATUS	current
	DESCRIPTION ""
			::= { mbus77 1 }

mbus77Manufacturer	OBJECT-TYPE
			SYNTAX	Gauge
			ACCESS	read-only
			STATUS	current
	DESCRIPTION ""
			::= { mbus77 2 }

mbus77Version		OBJECT-TYPE
			SYNTAX	Gauge
			ACCESS	read-only
			STATUS	current
	DESCRIPTION ""
			::= { mbus77 3 }

mbus77Medium		OBJECT-TYPE
			SYNTAX	Gauge
			ACCESS	read-only
			STATUS	current
	DESCRIPTION ""
			::= { mbus77 4 }

mbus77Status		OBJECT-TYPE
			SYNTAX	Gauge
			ACCESS	read-only
			STATUS	current
	DESCRIPTION ""
			::= { mbus77 5 }

mbus77VIF00		OBJECT-TYPE
			SYNTAX	INTEGER
			ACCESS	read-only
			STATUS	current
	DESCRIPTION ""
			::= { mbus77 6 }

mbus77Value00		OBJECT-TYPE
			SYNTAX	INTEGER
			ACCESS	read-only
			STATUS	current
	DESCRIPTION ""
			::= { mbus77 7 }

mbus77VIF01		OBJECT-TYPE
			SYNTAX	INTEGER
			ACCESS	read-only
			STATUS	current
	DESCRIPTION ""
			::= { mbus77 8 }

mbus77Value01		OBJECT-TYPE
			SYNTAX	INTEGER
			ACCESS	read-only
			STATUS	current
	DESCRIPTION ""
			::= { mbus77 9 }

mbus77VIF02		OBJECT-TYPE
			SYNTAX	INTEGER
			ACCESS	read-only
			STATUS	current
	DESCRIPTION ""
			::= { mbus77 10 }

mbus77Value02		OBJECT-TYPE
			SYNTAX	INTEGER
			ACCESS	read-only
			STATUS	current
	DESCRIPTION ""
			::= { mbus77 11 }

mbus77VIF03		OBJECT-TYPE
			SYNTAX	INTEGER
			ACCESS	read-only
			STATUS	current
	DESCRIPTION ""
			::= { mbus77 12 }

mbus77Value03		OBJECT-TYPE
			SYNTAX	INTEGER
			ACCESS	read-only
			STATUS	current
	DESCRIPTION ""
			::= { mbus77 13 }

mbus77VIF04		OBJECT-TYPE
			SYNTAX	INTEGER
			ACCESS	read-only
			STATUS	current
	DESCRIPTION ""
			::= { mbus77 14 }

mbus77Value04		OBJECT-TYPE
			SYNTAX	INTEGER
			ACCESS	read-only
			STATUS	current
	DESCRIPTION ""
			::= { mbus77 15 }

mbus77VIF05		OBJECT-TYPE
			SYNTAX	INTEGER
			ACCESS	read-only
			STATUS	current
	DESCRIPTION ""
			::= { mbus77 16 }

mbus77Value05		OBJECT-TYPE
			SYNTAX	INTEGER
			ACCESS	read-only
			STATUS	current
	DESCRIPTION ""
			::= { mbus77 17 }

mbus77VIF06		OBJECT-TYPE
			SYNTAX	INTEGER
			ACCESS	read-only
			STATUS	current
	DESCRIPTION ""
			::= { mbus77 18 }

mbus77Value06		OBJECT-TYPE
			SYNTAX	INTEGER
			ACCESS	read-only
			STATUS	current
	DESCRIPTION ""
			::= { mbus77 19 }

mbus77VIF07		OBJECT-TYPE
			SYNTAX	INTEGER
			ACCESS	read-only
			STATUS	current
	DESCRIPTION ""
			::= { mbus77 20 }

mbus77Value07		OBJECT-TYPE
			SYNTAX	INTEGER
			ACCESS	read-only
			STATUS	current
	DESCRIPTION ""
			::= { mbus77 21 }

mbus77VIF08		OBJECT-TYPE
			SYNTAX	INTEGER
			ACCESS	read-only
			STATUS	current
	DESCRIPTION ""
			::= { mbus77 22 }

mbus77Value08		OBJECT-TYPE
			SYNTAX	INTEGER
			ACCESS	read-only
			STATUS	current
	DESCRIPTION ""
			::= { mbus77 23 }

mbus77VIF09		OBJECT-TYPE
			SYNTAX	INTEGER
			ACCESS	read-only
			STATUS	current
	DESCRIPTION ""
			::= { mbus77 24 }

mbus77Value09		OBJECT-TYPE
			SYNTAX	INTEGER
			ACCESS	read-only
			STATUS	current
	DESCRIPTION ""
			::= { mbus77 25 }

mbus77VIF0A		OBJECT-TYPE
			SYNTAX	INTEGER
			ACCESS	read-only
			STATUS	current
	DESCRIPTION ""
			::= { mbus77 26 }

mbus77Value0A		OBJECT-TYPE
			SYNTAX	INTEGER
			ACCESS	read-only
			STATUS	current
	DESCRIPTION ""
			::= { mbus77 27 }

mbus77VIF0B		OBJECT-TYPE
			SYNTAX	INTEGER
			ACCESS	read-only
			STATUS	current
	DESCRIPTION ""
			::= { mbus77 28 }

mbus77Value0B		OBJECT-TYPE
			SYNTAX	INTEGER
			ACCESS	read-only
			STATUS	current
	DESCRIPTION ""
			::= { mbus77 29 }

mbus77VIF0C		OBJECT-TYPE
			SYNTAX	INTEGER
			ACCESS	read-only
			STATUS	current
	DESCRIPTION ""
			::= { mbus77 30 }

mbus77Value0C		OBJECT-TYPE
			SYNTAX	INTEGER
			ACCESS	read-only
			STATUS	current
	DESCRIPTION ""
			::= { mbus77 31 }

mbus77VIF0D		OBJECT-TYPE
			SYNTAX	INTEGER
			ACCESS	read-only
			STATUS	current
	DESCRIPTION ""
			::= { mbus77 32 }

mbus77Value0D		OBJECT-TYPE
			SYNTAX	INTEGER
			ACCESS	read-only
			STATUS	current
	DESCRIPTION ""
			::= { mbus77 33 }

mbus77VIF0E		OBJECT-TYPE
			SYNTAX	INTEGER
			ACCESS	read-only
			STATUS	current
	DESCRIPTION ""
			::= { mbus77 34 }

mbus77Value0E		OBJECT-TYPE
			SYNTAX	INTEGER
			ACCESS	read-only
			STATUS	current
	DESCRIPTION ""
			::= { mbus77 35 }

mbus77VIF0F		OBJECT-TYPE
			SYNTAX	INTEGER
			ACCESS	read-only
			STATUS	current
	DESCRIPTION ""
			::= { mbus77 36 }

mbus77Value0F		OBJECT-TYPE
			SYNTAX	INTEGER
			ACCESS	read-only
			STATUS	current
	DESCRIPTION ""
			::= { mbus77 37 }

mbus77VIF10		OBJECT-TYPE
			SYNTAX	INTEGER
			ACCESS	read-only
			STATUS	current
	DESCRIPTION ""
			::= { mbus77 38 }

mbus77Value10		OBJECT-TYPE
			SYNTAX	INTEGER
			ACCESS	read-only
			STATUS	current
	DESCRIPTION ""
			::= { mbus77 39 }

mbus77VIF11		OBJECT-TYPE
			SYNTAX	INTEGER
			ACCESS	read-only
			STATUS	current
	DESCRIPTION ""
			::= { mbus77 40 }

mbus77Value11		OBJECT-TYPE
			SYNTAX	INTEGER
			ACCESS	read-only
			STATUS	current
	DESCRIPTION ""
			::= { mbus77 41 }

mbus77VIF12		OBJECT-TYPE
			SYNTAX	INTEGER
			ACCESS	read-only
			STATUS	current
	DESCRIPTION ""
			::= { mbus77 42 }

mbus77Value12		OBJECT-TYPE
			SYNTAX	INTEGER
			ACCESS	read-only
			STATUS	current
	DESCRIPTION ""
			::= { mbus77 43 }

mbus77VIF13		OBJECT-TYPE
			SYNTAX	INTEGER
			ACCESS	read-only
			STATUS	current
	DESCRIPTION ""
			::= { mbus77 44 }

mbus77Value13		OBJECT-TYPE
			SYNTAX	INTEGER
			ACCESS	read-only
			STATUS	current
	DESCRIPTION ""
			::= { mbus77 45 }

mbus77VIF14		OBJECT-TYPE
			SYNTAX	INTEGER
			ACCESS	read-only
			STATUS	current
	DESCRIPTION ""
			::= { mbus77 46 }

mbus77Value14		OBJECT-TYPE
			SYNTAX	INTEGER
			ACCESS	read-only
			STATUS	current
	DESCRIPTION ""
			::= { mbus77 47 }

mbus77VIF15		OBJECT-TYPE
			SYNTAX	INTEGER
			ACCESS	read-only
			STATUS	current
	DESCRIPTION ""
			::= { mbus77 48 }

mbus77Value15		OBJECT-TYPE
			SYNTAX	INTEGER
			ACCESS	read-only
			STATUS	current
	DESCRIPTION ""
			::= { mbus77 49 }

mbus77VIF16		OBJECT-TYPE
			SYNTAX	INTEGER
			ACCESS	read-only
			STATUS	current
	DESCRIPTION ""
			::= { mbus77 50 }

mbus77Value16		OBJECT-TYPE
			SYNTAX	INTEGER
			ACCESS	read-only
			STATUS	current
	DESCRIPTION ""
			::= { mbus77 51 }

mbus77VIF17		OBJECT-TYPE
			SYNTAX	INTEGER
			ACCESS	read-only
			STATUS	current
	DESCRIPTION ""
			::= { mbus77 52 }

mbus77Value17		OBJECT-TYPE
			SYNTAX	INTEGER
			ACCESS	read-only
			STATUS	current
	DESCRIPTION ""
			::= { mbus77 53 }

mbus77VIF18		OBJECT-TYPE
			SYNTAX	INTEGER
			ACCESS	read-only
			STATUS	current
	DESCRIPTION ""
			::= { mbus77 54 }

mbus77Value18		OBJECT-TYPE
			SYNTAX	INTEGER
			ACCESS	read-only
			STATUS	current
	DESCRIPTION ""
			::= { mbus77 55 }

mbus77VIF19		OBJECT-TYPE
			SYNTAX	INTEGER
			ACCESS	read-only
			STATUS	current
	DESCRIPTION ""
			::= { mbus77 56 }

mbus77Value19		OBJECT-TYPE
			SYNTAX	INTEGER
			ACCESS	read-only
			STATUS	current
	DESCRIPTION ""
			::= { mbus77 57 }

mbus77VIF1A		OBJECT-TYPE
			SYNTAX	INTEGER
			ACCESS	read-only
			STATUS	current
	DESCRIPTION ""
			::= { mbus77 58 }

mbus77Value1A		OBJECT-TYPE
			SYNTAX	INTEGER
			ACCESS	read-only
			STATUS	current
	DESCRIPTION ""
			::= { mbus77 59 }

mbus77VIF1B		OBJECT-TYPE
			SYNTAX	INTEGER
			ACCESS	read-only
			STATUS	current
	DESCRIPTION ""
			::= { mbus77 60 }

mbus77Value1B		OBJECT-TYPE
			SYNTAX	INTEGER
			ACCESS	read-only
			STATUS	current
	DESCRIPTION ""
			::= { mbus77 61 }

mbus77VIF1C		OBJECT-TYPE
			SYNTAX	INTEGER
			ACCESS	read-only
			STATUS	current
	DESCRIPTION ""
			::= { mbus77 62 }

mbus77Value1C		OBJECT-TYPE
			SYNTAX	INTEGER
			ACCESS	read-only
			STATUS	current
	DESCRIPTION ""
			::= { mbus77 63 }

mbus77VIF1D		OBJECT-TYPE
			SYNTAX	INTEGER
			ACCESS	read-only
			STATUS	current
	DESCRIPTION ""
			::= { mbus77 64 }

mbus77Value1D		OBJECT-TYPE
			SYNTAX	INTEGER
			ACCESS	read-only
			STATUS	current
	DESCRIPTION ""
			::= { mbus77 65 }

mbus77VIF1E		OBJECT-TYPE
			SYNTAX	INTEGER
			ACCESS	read-only
			STATUS	current
	DESCRIPTION ""
			::= { mbus77 66 }

mbus77Value1E		OBJECT-TYPE
			SYNTAX	INTEGER
			ACCESS	read-only
			STATUS	current
	DESCRIPTION ""
			::= { mbus77 67 }

mbus77VIF1F		OBJECT-TYPE
			SYNTAX	INTEGER
			ACCESS	read-only
			STATUS	current
	DESCRIPTION ""
			::= { mbus77 68 }

mbus77Value1F		OBJECT-TYPE
			SYNTAX	INTEGER
			ACCESS	read-only
			STATUS	current
	DESCRIPTION ""
			::= { mbus77 69 }

mbus77VIF20		OBJECT-TYPE
			SYNTAX	INTEGER
			ACCESS	read-only
			STATUS	current
	DESCRIPTION ""
			::= { mbus77 70 }

mbus77Value20		OBJECT-TYPE
			SYNTAX	INTEGER
			ACCESS	read-only
			STATUS	current
	DESCRIPTION ""
			::= { mbus77 71 }

mbus77VIF21		OBJECT-TYPE
			SYNTAX	INTEGER
			ACCESS	read-only
			STATUS	current
	DESCRIPTION ""
			::= { mbus77 72 }

mbus77Value21		OBJECT-TYPE
			SYNTAX	INTEGER
			ACCESS	read-only
			STATUS	current
	DESCRIPTION ""
			::= { mbus77 73 }

mbus77VIF22		OBJECT-TYPE
			SYNTAX	INTEGER
			ACCESS	read-only
			STATUS	current
	DESCRIPTION ""
			::= { mbus77 74 }

mbus77Value22		OBJECT-TYPE
			SYNTAX	INTEGER
			ACCESS	read-only
			STATUS	current
	DESCRIPTION ""
			::= { mbus77 75 }

mbus77VIF23		OBJECT-TYPE
			SYNTAX	INTEGER
			ACCESS	read-only
			STATUS	current
	DESCRIPTION ""
			::= { mbus77 76 }

mbus77Value23		OBJECT-TYPE
			SYNTAX	INTEGER
			ACCESS	read-only
			STATUS	current
	DESCRIPTION ""
			::= { mbus77 77 }

mbus77VIF24		OBJECT-TYPE
			SYNTAX	INTEGER
			ACCESS	read-only
			STATUS	current
	DESCRIPTION ""
			::= { mbus77 78 }

mbus77Value24		OBJECT-TYPE
			SYNTAX	INTEGER
			ACCESS	read-only
			STATUS	current
	DESCRIPTION ""
			::= { mbus77 79 }

mbus77VIF25		OBJECT-TYPE
			SYNTAX	INTEGER
			ACCESS	read-only
			STATUS	current
	DESCRIPTION ""
			::= { mbus77 80 }

mbus77Value25		OBJECT-TYPE
			SYNTAX	INTEGER
			ACCESS	read-only
			STATUS	current
	DESCRIPTION ""
			::= { mbus77 81 }

mbus77VIF26		OBJECT-TYPE
			SYNTAX	INTEGER
			ACCESS	read-only
			STATUS	current
	DESCRIPTION ""
			::= { mbus77 82 }

mbus77Value26		OBJECT-TYPE
			SYNTAX	INTEGER
			ACCESS	read-only
			STATUS	current
	DESCRIPTION ""
			::= { mbus77 83 }

mbus77VIF27		OBJECT-TYPE
			SYNTAX	INTEGER
			ACCESS	read-only
			STATUS	current
	DESCRIPTION ""
			::= { mbus77 84 }

mbus77Value27		OBJECT-TYPE
			SYNTAX	INTEGER
			ACCESS	read-only
			STATUS	current
	DESCRIPTION ""
			::= { mbus77 85 }

mbus77VIF28		OBJECT-TYPE
			SYNTAX	INTEGER
			ACCESS	read-only
			STATUS	current
	DESCRIPTION ""
			::= { mbus77 86 }

mbus77Value28		OBJECT-TYPE
			SYNTAX	INTEGER
			ACCESS	read-only
			STATUS	current
	DESCRIPTION ""
			::= { mbus77 87 }

mbus77VIF29		OBJECT-TYPE
			SYNTAX	INTEGER
			ACCESS	read-only
			STATUS	current
	DESCRIPTION ""
			::= { mbus77 88 }

mbus77Value29		OBJECT-TYPE
			SYNTAX	INTEGER
			ACCESS	read-only
			STATUS	current
	DESCRIPTION ""
			::= { mbus77 89 }

mbus77VIF2A		OBJECT-TYPE
			SYNTAX	INTEGER
			ACCESS	read-only
			STATUS	current
	DESCRIPTION ""
			::= { mbus77 90 }

mbus77Value2A		OBJECT-TYPE
			SYNTAX	INTEGER
			ACCESS	read-only
			STATUS	current
	DESCRIPTION ""
			::= { mbus77 91 }

mbus77VIF2B		OBJECT-TYPE
			SYNTAX	INTEGER
			ACCESS	read-only
			STATUS	current
	DESCRIPTION ""
			::= { mbus77 92 }

mbus77Value2B		OBJECT-TYPE
			SYNTAX	INTEGER
			ACCESS	read-only
			STATUS	current
	DESCRIPTION ""
			::= { mbus77 93 }

mbus77VIF2C		OBJECT-TYPE
			SYNTAX	INTEGER
			ACCESS	read-only
			STATUS	current
	DESCRIPTION ""
			::= { mbus77 94 }

mbus77Value2C		OBJECT-TYPE
			SYNTAX	INTEGER
			ACCESS	read-only
			STATUS	current
	DESCRIPTION ""
			::= { mbus77 95 }

mbus77VIF2D		OBJECT-TYPE
			SYNTAX	INTEGER
			ACCESS	read-only
			STATUS	current
	DESCRIPTION ""
			::= { mbus77 96 }

mbus77Value2D		OBJECT-TYPE
			SYNTAX	INTEGER
			ACCESS	read-only
			STATUS	current
	DESCRIPTION ""
			::= { mbus77 97 }

mbus77VIF2E		OBJECT-TYPE
			SYNTAX	INTEGER
			ACCESS	read-only
			STATUS	current
	DESCRIPTION ""
			::= { mbus77 98 }

mbus77Value2E		OBJECT-TYPE
			SYNTAX	INTEGER
			ACCESS	read-only
			STATUS	current
	DESCRIPTION ""
			::= { mbus77 99 }

mbus77VIF2F		OBJECT-TYPE
			SYNTAX	INTEGER
			ACCESS	read-only
			STATUS	current
	DESCRIPTION ""
			::= { mbus77 100 }

mbus77Value2F		OBJECT-TYPE
			SYNTAX	INTEGER
			ACCESS	read-only
			STATUS	current
	DESCRIPTION ""
			::= { mbus77 101 }

mbus78			OBJECT IDENTIFIER ::= { mbus 120 }

mbus78IdNumber		OBJECT-TYPE
			SYNTAX	Gauge
			ACCESS	read-only
			STATUS	current
	DESCRIPTION ""
			::= { mbus78 1 }

mbus78Manufacturer	OBJECT-TYPE
			SYNTAX	Gauge
			ACCESS	read-only
			STATUS	current
	DESCRIPTION ""
			::= { mbus78 2 }

mbus78Version		OBJECT-TYPE
			SYNTAX	Gauge
			ACCESS	read-only
			STATUS	current
	DESCRIPTION ""
			::= { mbus78 3 }

mbus78Medium		OBJECT-TYPE
			SYNTAX	Gauge
			ACCESS	read-only
			STATUS	current
	DESCRIPTION ""
			::= { mbus78 4 }

mbus78Status		OBJECT-TYPE
			SYNTAX	Gauge
			ACCESS	read-only
			STATUS	current
	DESCRIPTION ""
			::= { mbus78 5 }

mbus78VIF00		OBJECT-TYPE
			SYNTAX	INTEGER
			ACCESS	read-only
			STATUS	current
	DESCRIPTION ""
			::= { mbus78 6 }

mbus78Value00		OBJECT-TYPE
			SYNTAX	INTEGER
			ACCESS	read-only
			STATUS	current
	DESCRIPTION ""
			::= { mbus78 7 }

mbus78VIF01		OBJECT-TYPE
			SYNTAX	INTEGER
			ACCESS	read-only
			STATUS	current
	DESCRIPTION ""
			::= { mbus78 8 }

mbus78Value01		OBJECT-TYPE
			SYNTAX	INTEGER
			ACCESS	read-only
			STATUS	current
	DESCRIPTION ""
			::= { mbus78 9 }

mbus78VIF02		OBJECT-TYPE
			SYNTAX	INTEGER
			ACCESS	read-only
			STATUS	current
	DESCRIPTION ""
			::= { mbus78 10 }

mbus78Value02		OBJECT-TYPE
			SYNTAX	INTEGER
			ACCESS	read-only
			STATUS	current
	DESCRIPTION ""
			::= { mbus78 11 }

mbus78VIF03		OBJECT-TYPE
			SYNTAX	INTEGER
			ACCESS	read-only
			STATUS	current
	DESCRIPTION ""
			::= { mbus78 12 }

mbus78Value03		OBJECT-TYPE
			SYNTAX	INTEGER
			ACCESS	read-only
			STATUS	current
	DESCRIPTION ""
			::= { mbus78 13 }

mbus78VIF04		OBJECT-TYPE
			SYNTAX	INTEGER
			ACCESS	read-only
			STATUS	current
	DESCRIPTION ""
			::= { mbus78 14 }

mbus78Value04		OBJECT-TYPE
			SYNTAX	INTEGER
			ACCESS	read-only
			STATUS	current
	DESCRIPTION ""
			::= { mbus78 15 }

mbus78VIF05		OBJECT-TYPE
			SYNTAX	INTEGER
			ACCESS	read-only
			STATUS	current
	DESCRIPTION ""
			::= { mbus78 16 }

mbus78Value05		OBJECT-TYPE
			SYNTAX	INTEGER
			ACCESS	read-only
			STATUS	current
	DESCRIPTION ""
			::= { mbus78 17 }

mbus78VIF06		OBJECT-TYPE
			SYNTAX	INTEGER
			ACCESS	read-only
			STATUS	current
	DESCRIPTION ""
			::= { mbus78 18 }

mbus78Value06		OBJECT-TYPE
			SYNTAX	INTEGER
			ACCESS	read-only
			STATUS	current
	DESCRIPTION ""
			::= { mbus78 19 }

mbus78VIF07		OBJECT-TYPE
			SYNTAX	INTEGER
			ACCESS	read-only
			STATUS	current
	DESCRIPTION ""
			::= { mbus78 20 }

mbus78Value07		OBJECT-TYPE
			SYNTAX	INTEGER
			ACCESS	read-only
			STATUS	current
	DESCRIPTION ""
			::= { mbus78 21 }

mbus78VIF08		OBJECT-TYPE
			SYNTAX	INTEGER
			ACCESS	read-only
			STATUS	current
	DESCRIPTION ""
			::= { mbus78 22 }

mbus78Value08		OBJECT-TYPE
			SYNTAX	INTEGER
			ACCESS	read-only
			STATUS	current
	DESCRIPTION ""
			::= { mbus78 23 }

mbus78VIF09		OBJECT-TYPE
			SYNTAX	INTEGER
			ACCESS	read-only
			STATUS	current
	DESCRIPTION ""
			::= { mbus78 24 }

mbus78Value09		OBJECT-TYPE
			SYNTAX	INTEGER
			ACCESS	read-only
			STATUS	current
	DESCRIPTION ""
			::= { mbus78 25 }

mbus78VIF0A		OBJECT-TYPE
			SYNTAX	INTEGER
			ACCESS	read-only
			STATUS	current
	DESCRIPTION ""
			::= { mbus78 26 }

mbus78Value0A		OBJECT-TYPE
			SYNTAX	INTEGER
			ACCESS	read-only
			STATUS	current
	DESCRIPTION ""
			::= { mbus78 27 }

mbus78VIF0B		OBJECT-TYPE
			SYNTAX	INTEGER
			ACCESS	read-only
			STATUS	current
	DESCRIPTION ""
			::= { mbus78 28 }

mbus78Value0B		OBJECT-TYPE
			SYNTAX	INTEGER
			ACCESS	read-only
			STATUS	current
	DESCRIPTION ""
			::= { mbus78 29 }

mbus78VIF0C		OBJECT-TYPE
			SYNTAX	INTEGER
			ACCESS	read-only
			STATUS	current
	DESCRIPTION ""
			::= { mbus78 30 }

mbus78Value0C		OBJECT-TYPE
			SYNTAX	INTEGER
			ACCESS	read-only
			STATUS	current
	DESCRIPTION ""
			::= { mbus78 31 }

mbus78VIF0D		OBJECT-TYPE
			SYNTAX	INTEGER
			ACCESS	read-only
			STATUS	current
	DESCRIPTION ""
			::= { mbus78 32 }

mbus78Value0D		OBJECT-TYPE
			SYNTAX	INTEGER
			ACCESS	read-only
			STATUS	current
	DESCRIPTION ""
			::= { mbus78 33 }

mbus78VIF0E		OBJECT-TYPE
			SYNTAX	INTEGER
			ACCESS	read-only
			STATUS	current
	DESCRIPTION ""
			::= { mbus78 34 }

mbus78Value0E		OBJECT-TYPE
			SYNTAX	INTEGER
			ACCESS	read-only
			STATUS	current
	DESCRIPTION ""
			::= { mbus78 35 }

mbus78VIF0F		OBJECT-TYPE
			SYNTAX	INTEGER
			ACCESS	read-only
			STATUS	current
	DESCRIPTION ""
			::= { mbus78 36 }

mbus78Value0F		OBJECT-TYPE
			SYNTAX	INTEGER
			ACCESS	read-only
			STATUS	current
	DESCRIPTION ""
			::= { mbus78 37 }

mbus78VIF10		OBJECT-TYPE
			SYNTAX	INTEGER
			ACCESS	read-only
			STATUS	current
	DESCRIPTION ""
			::= { mbus78 38 }

mbus78Value10		OBJECT-TYPE
			SYNTAX	INTEGER
			ACCESS	read-only
			STATUS	current
	DESCRIPTION ""
			::= { mbus78 39 }

mbus78VIF11		OBJECT-TYPE
			SYNTAX	INTEGER
			ACCESS	read-only
			STATUS	current
	DESCRIPTION ""
			::= { mbus78 40 }

mbus78Value11		OBJECT-TYPE
			SYNTAX	INTEGER
			ACCESS	read-only
			STATUS	current
	DESCRIPTION ""
			::= { mbus78 41 }

mbus78VIF12		OBJECT-TYPE
			SYNTAX	INTEGER
			ACCESS	read-only
			STATUS	current
	DESCRIPTION ""
			::= { mbus78 42 }

mbus78Value12		OBJECT-TYPE
			SYNTAX	INTEGER
			ACCESS	read-only
			STATUS	current
	DESCRIPTION ""
			::= { mbus78 43 }

mbus78VIF13		OBJECT-TYPE
			SYNTAX	INTEGER
			ACCESS	read-only
			STATUS	current
	DESCRIPTION ""
			::= { mbus78 44 }

mbus78Value13		OBJECT-TYPE
			SYNTAX	INTEGER
			ACCESS	read-only
			STATUS	current
	DESCRIPTION ""
			::= { mbus78 45 }

mbus78VIF14		OBJECT-TYPE
			SYNTAX	INTEGER
			ACCESS	read-only
			STATUS	current
	DESCRIPTION ""
			::= { mbus78 46 }

mbus78Value14		OBJECT-TYPE
			SYNTAX	INTEGER
			ACCESS	read-only
			STATUS	current
	DESCRIPTION ""
			::= { mbus78 47 }

mbus78VIF15		OBJECT-TYPE
			SYNTAX	INTEGER
			ACCESS	read-only
			STATUS	current
	DESCRIPTION ""
			::= { mbus78 48 }

mbus78Value15		OBJECT-TYPE
			SYNTAX	INTEGER
			ACCESS	read-only
			STATUS	current
	DESCRIPTION ""
			::= { mbus78 49 }

mbus78VIF16		OBJECT-TYPE
			SYNTAX	INTEGER
			ACCESS	read-only
			STATUS	current
	DESCRIPTION ""
			::= { mbus78 50 }

mbus78Value16		OBJECT-TYPE
			SYNTAX	INTEGER
			ACCESS	read-only
			STATUS	current
	DESCRIPTION ""
			::= { mbus78 51 }

mbus78VIF17		OBJECT-TYPE
			SYNTAX	INTEGER
			ACCESS	read-only
			STATUS	current
	DESCRIPTION ""
			::= { mbus78 52 }

mbus78Value17		OBJECT-TYPE
			SYNTAX	INTEGER
			ACCESS	read-only
			STATUS	current
	DESCRIPTION ""
			::= { mbus78 53 }

mbus78VIF18		OBJECT-TYPE
			SYNTAX	INTEGER
			ACCESS	read-only
			STATUS	current
	DESCRIPTION ""
			::= { mbus78 54 }

mbus78Value18		OBJECT-TYPE
			SYNTAX	INTEGER
			ACCESS	read-only
			STATUS	current
	DESCRIPTION ""
			::= { mbus78 55 }

mbus78VIF19		OBJECT-TYPE
			SYNTAX	INTEGER
			ACCESS	read-only
			STATUS	current
	DESCRIPTION ""
			::= { mbus78 56 }

mbus78Value19		OBJECT-TYPE
			SYNTAX	INTEGER
			ACCESS	read-only
			STATUS	current
	DESCRIPTION ""
			::= { mbus78 57 }

mbus78VIF1A		OBJECT-TYPE
			SYNTAX	INTEGER
			ACCESS	read-only
			STATUS	current
	DESCRIPTION ""
			::= { mbus78 58 }

mbus78Value1A		OBJECT-TYPE
			SYNTAX	INTEGER
			ACCESS	read-only
			STATUS	current
	DESCRIPTION ""
			::= { mbus78 59 }

mbus78VIF1B		OBJECT-TYPE
			SYNTAX	INTEGER
			ACCESS	read-only
			STATUS	current
	DESCRIPTION ""
			::= { mbus78 60 }

mbus78Value1B		OBJECT-TYPE
			SYNTAX	INTEGER
			ACCESS	read-only
			STATUS	current
	DESCRIPTION ""
			::= { mbus78 61 }

mbus78VIF1C		OBJECT-TYPE
			SYNTAX	INTEGER
			ACCESS	read-only
			STATUS	current
	DESCRIPTION ""
			::= { mbus78 62 }

mbus78Value1C		OBJECT-TYPE
			SYNTAX	INTEGER
			ACCESS	read-only
			STATUS	current
	DESCRIPTION ""
			::= { mbus78 63 }

mbus78VIF1D		OBJECT-TYPE
			SYNTAX	INTEGER
			ACCESS	read-only
			STATUS	current
	DESCRIPTION ""
			::= { mbus78 64 }

mbus78Value1D		OBJECT-TYPE
			SYNTAX	INTEGER
			ACCESS	read-only
			STATUS	current
	DESCRIPTION ""
			::= { mbus78 65 }

mbus78VIF1E		OBJECT-TYPE
			SYNTAX	INTEGER
			ACCESS	read-only
			STATUS	current
	DESCRIPTION ""
			::= { mbus78 66 }

mbus78Value1E		OBJECT-TYPE
			SYNTAX	INTEGER
			ACCESS	read-only
			STATUS	current
	DESCRIPTION ""
			::= { mbus78 67 }

mbus78VIF1F		OBJECT-TYPE
			SYNTAX	INTEGER
			ACCESS	read-only
			STATUS	current
	DESCRIPTION ""
			::= { mbus78 68 }

mbus78Value1F		OBJECT-TYPE
			SYNTAX	INTEGER
			ACCESS	read-only
			STATUS	current
	DESCRIPTION ""
			::= { mbus78 69 }

mbus78VIF20		OBJECT-TYPE
			SYNTAX	INTEGER
			ACCESS	read-only
			STATUS	current
	DESCRIPTION ""
			::= { mbus78 70 }

mbus78Value20		OBJECT-TYPE
			SYNTAX	INTEGER
			ACCESS	read-only
			STATUS	current
	DESCRIPTION ""
			::= { mbus78 71 }

mbus78VIF21		OBJECT-TYPE
			SYNTAX	INTEGER
			ACCESS	read-only
			STATUS	current
	DESCRIPTION ""
			::= { mbus78 72 }

mbus78Value21		OBJECT-TYPE
			SYNTAX	INTEGER
			ACCESS	read-only
			STATUS	current
	DESCRIPTION ""
			::= { mbus78 73 }

mbus78VIF22		OBJECT-TYPE
			SYNTAX	INTEGER
			ACCESS	read-only
			STATUS	current
	DESCRIPTION ""
			::= { mbus78 74 }

mbus78Value22		OBJECT-TYPE
			SYNTAX	INTEGER
			ACCESS	read-only
			STATUS	current
	DESCRIPTION ""
			::= { mbus78 75 }

mbus78VIF23		OBJECT-TYPE
			SYNTAX	INTEGER
			ACCESS	read-only
			STATUS	current
	DESCRIPTION ""
			::= { mbus78 76 }

mbus78Value23		OBJECT-TYPE
			SYNTAX	INTEGER
			ACCESS	read-only
			STATUS	current
	DESCRIPTION ""
			::= { mbus78 77 }

mbus78VIF24		OBJECT-TYPE
			SYNTAX	INTEGER
			ACCESS	read-only
			STATUS	current
	DESCRIPTION ""
			::= { mbus78 78 }

mbus78Value24		OBJECT-TYPE
			SYNTAX	INTEGER
			ACCESS	read-only
			STATUS	current
	DESCRIPTION ""
			::= { mbus78 79 }

mbus78VIF25		OBJECT-TYPE
			SYNTAX	INTEGER
			ACCESS	read-only
			STATUS	current
	DESCRIPTION ""
			::= { mbus78 80 }

mbus78Value25		OBJECT-TYPE
			SYNTAX	INTEGER
			ACCESS	read-only
			STATUS	current
	DESCRIPTION ""
			::= { mbus78 81 }

mbus78VIF26		OBJECT-TYPE
			SYNTAX	INTEGER
			ACCESS	read-only
			STATUS	current
	DESCRIPTION ""
			::= { mbus78 82 }

mbus78Value26		OBJECT-TYPE
			SYNTAX	INTEGER
			ACCESS	read-only
			STATUS	current
	DESCRIPTION ""
			::= { mbus78 83 }

mbus78VIF27		OBJECT-TYPE
			SYNTAX	INTEGER
			ACCESS	read-only
			STATUS	current
	DESCRIPTION ""
			::= { mbus78 84 }

mbus78Value27		OBJECT-TYPE
			SYNTAX	INTEGER
			ACCESS	read-only
			STATUS	current
	DESCRIPTION ""
			::= { mbus78 85 }

mbus78VIF28		OBJECT-TYPE
			SYNTAX	INTEGER
			ACCESS	read-only
			STATUS	current
	DESCRIPTION ""
			::= { mbus78 86 }

mbus78Value28		OBJECT-TYPE
			SYNTAX	INTEGER
			ACCESS	read-only
			STATUS	current
	DESCRIPTION ""
			::= { mbus78 87 }

mbus78VIF29		OBJECT-TYPE
			SYNTAX	INTEGER
			ACCESS	read-only
			STATUS	current
	DESCRIPTION ""
			::= { mbus78 88 }

mbus78Value29		OBJECT-TYPE
			SYNTAX	INTEGER
			ACCESS	read-only
			STATUS	current
	DESCRIPTION ""
			::= { mbus78 89 }

mbus78VIF2A		OBJECT-TYPE
			SYNTAX	INTEGER
			ACCESS	read-only
			STATUS	current
	DESCRIPTION ""
			::= { mbus78 90 }

mbus78Value2A		OBJECT-TYPE
			SYNTAX	INTEGER
			ACCESS	read-only
			STATUS	current
	DESCRIPTION ""
			::= { mbus78 91 }

mbus78VIF2B		OBJECT-TYPE
			SYNTAX	INTEGER
			ACCESS	read-only
			STATUS	current
	DESCRIPTION ""
			::= { mbus78 92 }

mbus78Value2B		OBJECT-TYPE
			SYNTAX	INTEGER
			ACCESS	read-only
			STATUS	current
	DESCRIPTION ""
			::= { mbus78 93 }

mbus78VIF2C		OBJECT-TYPE
			SYNTAX	INTEGER
			ACCESS	read-only
			STATUS	current
	DESCRIPTION ""
			::= { mbus78 94 }

mbus78Value2C		OBJECT-TYPE
			SYNTAX	INTEGER
			ACCESS	read-only
			STATUS	current
	DESCRIPTION ""
			::= { mbus78 95 }

mbus78VIF2D		OBJECT-TYPE
			SYNTAX	INTEGER
			ACCESS	read-only
			STATUS	current
	DESCRIPTION ""
			::= { mbus78 96 }

mbus78Value2D		OBJECT-TYPE
			SYNTAX	INTEGER
			ACCESS	read-only
			STATUS	current
	DESCRIPTION ""
			::= { mbus78 97 }

mbus78VIF2E		OBJECT-TYPE
			SYNTAX	INTEGER
			ACCESS	read-only
			STATUS	current
	DESCRIPTION ""
			::= { mbus78 98 }

mbus78Value2E		OBJECT-TYPE
			SYNTAX	INTEGER
			ACCESS	read-only
			STATUS	current
	DESCRIPTION ""
			::= { mbus78 99 }

mbus78VIF2F		OBJECT-TYPE
			SYNTAX	INTEGER
			ACCESS	read-only
			STATUS	current
	DESCRIPTION ""
			::= { mbus78 100 }

mbus78Value2F		OBJECT-TYPE
			SYNTAX	INTEGER
			ACCESS	read-only
			STATUS	current
	DESCRIPTION ""
			::= { mbus78 101 }

mbus79			OBJECT IDENTIFIER ::= { mbus 121 }

mbus79IdNumber		OBJECT-TYPE
			SYNTAX	Gauge
			ACCESS	read-only
			STATUS	current
	DESCRIPTION ""
			::= { mbus79 1 }

mbus79Manufacturer	OBJECT-TYPE
			SYNTAX	Gauge
			ACCESS	read-only
			STATUS	current
	DESCRIPTION ""
			::= { mbus79 2 }

mbus79Version		OBJECT-TYPE
			SYNTAX	Gauge
			ACCESS	read-only
			STATUS	current
	DESCRIPTION ""
			::= { mbus79 3 }

mbus79Medium		OBJECT-TYPE
			SYNTAX	Gauge
			ACCESS	read-only
			STATUS	current
	DESCRIPTION ""
			::= { mbus79 4 }

mbus79Status		OBJECT-TYPE
			SYNTAX	Gauge
			ACCESS	read-only
			STATUS	current
	DESCRIPTION ""
			::= { mbus79 5 }

mbus79VIF00		OBJECT-TYPE
			SYNTAX	INTEGER
			ACCESS	read-only
			STATUS	current
	DESCRIPTION ""
			::= { mbus79 6 }

mbus79Value00		OBJECT-TYPE
			SYNTAX	INTEGER
			ACCESS	read-only
			STATUS	current
	DESCRIPTION ""
			::= { mbus79 7 }

mbus79VIF01		OBJECT-TYPE
			SYNTAX	INTEGER
			ACCESS	read-only
			STATUS	current
	DESCRIPTION ""
			::= { mbus79 8 }

mbus79Value01		OBJECT-TYPE
			SYNTAX	INTEGER
			ACCESS	read-only
			STATUS	current
	DESCRIPTION ""
			::= { mbus79 9 }

mbus79VIF02		OBJECT-TYPE
			SYNTAX	INTEGER
			ACCESS	read-only
			STATUS	current
	DESCRIPTION ""
			::= { mbus79 10 }

mbus79Value02		OBJECT-TYPE
			SYNTAX	INTEGER
			ACCESS	read-only
			STATUS	current
	DESCRIPTION ""
			::= { mbus79 11 }

mbus79VIF03		OBJECT-TYPE
			SYNTAX	INTEGER
			ACCESS	read-only
			STATUS	current
	DESCRIPTION ""
			::= { mbus79 12 }

mbus79Value03		OBJECT-TYPE
			SYNTAX	INTEGER
			ACCESS	read-only
			STATUS	current
	DESCRIPTION ""
			::= { mbus79 13 }

mbus79VIF04		OBJECT-TYPE
			SYNTAX	INTEGER
			ACCESS	read-only
			STATUS	current
	DESCRIPTION ""
			::= { mbus79 14 }

mbus79Value04		OBJECT-TYPE
			SYNTAX	INTEGER
			ACCESS	read-only
			STATUS	current
	DESCRIPTION ""
			::= { mbus79 15 }

mbus79VIF05		OBJECT-TYPE
			SYNTAX	INTEGER
			ACCESS	read-only
			STATUS	current
	DESCRIPTION ""
			::= { mbus79 16 }

mbus79Value05		OBJECT-TYPE
			SYNTAX	INTEGER
			ACCESS	read-only
			STATUS	current
	DESCRIPTION ""
			::= { mbus79 17 }

mbus79VIF06		OBJECT-TYPE
			SYNTAX	INTEGER
			ACCESS	read-only
			STATUS	current
	DESCRIPTION ""
			::= { mbus79 18 }

mbus79Value06		OBJECT-TYPE
			SYNTAX	INTEGER
			ACCESS	read-only
			STATUS	current
	DESCRIPTION ""
			::= { mbus79 19 }

mbus79VIF07		OBJECT-TYPE
			SYNTAX	INTEGER
			ACCESS	read-only
			STATUS	current
	DESCRIPTION ""
			::= { mbus79 20 }

mbus79Value07		OBJECT-TYPE
			SYNTAX	INTEGER
			ACCESS	read-only
			STATUS	current
	DESCRIPTION ""
			::= { mbus79 21 }

mbus79VIF08		OBJECT-TYPE
			SYNTAX	INTEGER
			ACCESS	read-only
			STATUS	current
	DESCRIPTION ""
			::= { mbus79 22 }

mbus79Value08		OBJECT-TYPE
			SYNTAX	INTEGER
			ACCESS	read-only
			STATUS	current
	DESCRIPTION ""
			::= { mbus79 23 }

mbus79VIF09		OBJECT-TYPE
			SYNTAX	INTEGER
			ACCESS	read-only
			STATUS	current
	DESCRIPTION ""
			::= { mbus79 24 }

mbus79Value09		OBJECT-TYPE
			SYNTAX	INTEGER
			ACCESS	read-only
			STATUS	current
	DESCRIPTION ""
			::= { mbus79 25 }

mbus79VIF0A		OBJECT-TYPE
			SYNTAX	INTEGER
			ACCESS	read-only
			STATUS	current
	DESCRIPTION ""
			::= { mbus79 26 }

mbus79Value0A		OBJECT-TYPE
			SYNTAX	INTEGER
			ACCESS	read-only
			STATUS	current
	DESCRIPTION ""
			::= { mbus79 27 }

mbus79VIF0B		OBJECT-TYPE
			SYNTAX	INTEGER
			ACCESS	read-only
			STATUS	current
	DESCRIPTION ""
			::= { mbus79 28 }

mbus79Value0B		OBJECT-TYPE
			SYNTAX	INTEGER
			ACCESS	read-only
			STATUS	current
	DESCRIPTION ""
			::= { mbus79 29 }

mbus79VIF0C		OBJECT-TYPE
			SYNTAX	INTEGER
			ACCESS	read-only
			STATUS	current
	DESCRIPTION ""
			::= { mbus79 30 }

mbus79Value0C		OBJECT-TYPE
			SYNTAX	INTEGER
			ACCESS	read-only
			STATUS	current
	DESCRIPTION ""
			::= { mbus79 31 }

mbus79VIF0D		OBJECT-TYPE
			SYNTAX	INTEGER
			ACCESS	read-only
			STATUS	current
	DESCRIPTION ""
			::= { mbus79 32 }

mbus79Value0D		OBJECT-TYPE
			SYNTAX	INTEGER
			ACCESS	read-only
			STATUS	current
	DESCRIPTION ""
			::= { mbus79 33 }

mbus79VIF0E		OBJECT-TYPE
			SYNTAX	INTEGER
			ACCESS	read-only
			STATUS	current
	DESCRIPTION ""
			::= { mbus79 34 }

mbus79Value0E		OBJECT-TYPE
			SYNTAX	INTEGER
			ACCESS	read-only
			STATUS	current
	DESCRIPTION ""
			::= { mbus79 35 }

mbus79VIF0F		OBJECT-TYPE
			SYNTAX	INTEGER
			ACCESS	read-only
			STATUS	current
	DESCRIPTION ""
			::= { mbus79 36 }

mbus79Value0F		OBJECT-TYPE
			SYNTAX	INTEGER
			ACCESS	read-only
			STATUS	current
	DESCRIPTION ""
			::= { mbus79 37 }

mbus79VIF10		OBJECT-TYPE
			SYNTAX	INTEGER
			ACCESS	read-only
			STATUS	current
	DESCRIPTION ""
			::= { mbus79 38 }

mbus79Value10		OBJECT-TYPE
			SYNTAX	INTEGER
			ACCESS	read-only
			STATUS	current
	DESCRIPTION ""
			::= { mbus79 39 }

mbus79VIF11		OBJECT-TYPE
			SYNTAX	INTEGER
			ACCESS	read-only
			STATUS	current
	DESCRIPTION ""
			::= { mbus79 40 }

mbus79Value11		OBJECT-TYPE
			SYNTAX	INTEGER
			ACCESS	read-only
			STATUS	current
	DESCRIPTION ""
			::= { mbus79 41 }

mbus79VIF12		OBJECT-TYPE
			SYNTAX	INTEGER
			ACCESS	read-only
			STATUS	current
	DESCRIPTION ""
			::= { mbus79 42 }

mbus79Value12		OBJECT-TYPE
			SYNTAX	INTEGER
			ACCESS	read-only
			STATUS	current
	DESCRIPTION ""
			::= { mbus79 43 }

mbus79VIF13		OBJECT-TYPE
			SYNTAX	INTEGER
			ACCESS	read-only
			STATUS	current
	DESCRIPTION ""
			::= { mbus79 44 }

mbus79Value13		OBJECT-TYPE
			SYNTAX	INTEGER
			ACCESS	read-only
			STATUS	current
	DESCRIPTION ""
			::= { mbus79 45 }

mbus79VIF14		OBJECT-TYPE
			SYNTAX	INTEGER
			ACCESS	read-only
			STATUS	current
	DESCRIPTION ""
			::= { mbus79 46 }

mbus79Value14		OBJECT-TYPE
			SYNTAX	INTEGER
			ACCESS	read-only
			STATUS	current
	DESCRIPTION ""
			::= { mbus79 47 }

mbus79VIF15		OBJECT-TYPE
			SYNTAX	INTEGER
			ACCESS	read-only
			STATUS	current
	DESCRIPTION ""
			::= { mbus79 48 }

mbus79Value15		OBJECT-TYPE
			SYNTAX	INTEGER
			ACCESS	read-only
			STATUS	current
	DESCRIPTION ""
			::= { mbus79 49 }

mbus79VIF16		OBJECT-TYPE
			SYNTAX	INTEGER
			ACCESS	read-only
			STATUS	current
	DESCRIPTION ""
			::= { mbus79 50 }

mbus79Value16		OBJECT-TYPE
			SYNTAX	INTEGER
			ACCESS	read-only
			STATUS	current
	DESCRIPTION ""
			::= { mbus79 51 }

mbus79VIF17		OBJECT-TYPE
			SYNTAX	INTEGER
			ACCESS	read-only
			STATUS	current
	DESCRIPTION ""
			::= { mbus79 52 }

mbus79Value17		OBJECT-TYPE
			SYNTAX	INTEGER
			ACCESS	read-only
			STATUS	current
	DESCRIPTION ""
			::= { mbus79 53 }

mbus79VIF18		OBJECT-TYPE
			SYNTAX	INTEGER
			ACCESS	read-only
			STATUS	current
	DESCRIPTION ""
			::= { mbus79 54 }

mbus79Value18		OBJECT-TYPE
			SYNTAX	INTEGER
			ACCESS	read-only
			STATUS	current
	DESCRIPTION ""
			::= { mbus79 55 }

mbus79VIF19		OBJECT-TYPE
			SYNTAX	INTEGER
			ACCESS	read-only
			STATUS	current
	DESCRIPTION ""
			::= { mbus79 56 }

mbus79Value19		OBJECT-TYPE
			SYNTAX	INTEGER
			ACCESS	read-only
			STATUS	current
	DESCRIPTION ""
			::= { mbus79 57 }

mbus79VIF1A		OBJECT-TYPE
			SYNTAX	INTEGER
			ACCESS	read-only
			STATUS	current
	DESCRIPTION ""
			::= { mbus79 58 }

mbus79Value1A		OBJECT-TYPE
			SYNTAX	INTEGER
			ACCESS	read-only
			STATUS	current
	DESCRIPTION ""
			::= { mbus79 59 }

mbus79VIF1B		OBJECT-TYPE
			SYNTAX	INTEGER
			ACCESS	read-only
			STATUS	current
	DESCRIPTION ""
			::= { mbus79 60 }

mbus79Value1B		OBJECT-TYPE
			SYNTAX	INTEGER
			ACCESS	read-only
			STATUS	current
	DESCRIPTION ""
			::= { mbus79 61 }

mbus79VIF1C		OBJECT-TYPE
			SYNTAX	INTEGER
			ACCESS	read-only
			STATUS	current
	DESCRIPTION ""
			::= { mbus79 62 }

mbus79Value1C		OBJECT-TYPE
			SYNTAX	INTEGER
			ACCESS	read-only
			STATUS	current
	DESCRIPTION ""
			::= { mbus79 63 }

mbus79VIF1D		OBJECT-TYPE
			SYNTAX	INTEGER
			ACCESS	read-only
			STATUS	current
	DESCRIPTION ""
			::= { mbus79 64 }

mbus79Value1D		OBJECT-TYPE
			SYNTAX	INTEGER
			ACCESS	read-only
			STATUS	current
	DESCRIPTION ""
			::= { mbus79 65 }

mbus79VIF1E		OBJECT-TYPE
			SYNTAX	INTEGER
			ACCESS	read-only
			STATUS	current
	DESCRIPTION ""
			::= { mbus79 66 }

mbus79Value1E		OBJECT-TYPE
			SYNTAX	INTEGER
			ACCESS	read-only
			STATUS	current
	DESCRIPTION ""
			::= { mbus79 67 }

mbus79VIF1F		OBJECT-TYPE
			SYNTAX	INTEGER
			ACCESS	read-only
			STATUS	current
	DESCRIPTION ""
			::= { mbus79 68 }

mbus79Value1F		OBJECT-TYPE
			SYNTAX	INTEGER
			ACCESS	read-only
			STATUS	current
	DESCRIPTION ""
			::= { mbus79 69 }

mbus79VIF20		OBJECT-TYPE
			SYNTAX	INTEGER
			ACCESS	read-only
			STATUS	current
	DESCRIPTION ""
			::= { mbus79 70 }

mbus79Value20		OBJECT-TYPE
			SYNTAX	INTEGER
			ACCESS	read-only
			STATUS	current
	DESCRIPTION ""
			::= { mbus79 71 }

mbus79VIF21		OBJECT-TYPE
			SYNTAX	INTEGER
			ACCESS	read-only
			STATUS	current
	DESCRIPTION ""
			::= { mbus79 72 }

mbus79Value21		OBJECT-TYPE
			SYNTAX	INTEGER
			ACCESS	read-only
			STATUS	current
	DESCRIPTION ""
			::= { mbus79 73 }

mbus79VIF22		OBJECT-TYPE
			SYNTAX	INTEGER
			ACCESS	read-only
			STATUS	current
	DESCRIPTION ""
			::= { mbus79 74 }

mbus79Value22		OBJECT-TYPE
			SYNTAX	INTEGER
			ACCESS	read-only
			STATUS	current
	DESCRIPTION ""
			::= { mbus79 75 }

mbus79VIF23		OBJECT-TYPE
			SYNTAX	INTEGER
			ACCESS	read-only
			STATUS	current
	DESCRIPTION ""
			::= { mbus79 76 }

mbus79Value23		OBJECT-TYPE
			SYNTAX	INTEGER
			ACCESS	read-only
			STATUS	current
	DESCRIPTION ""
			::= { mbus79 77 }

mbus79VIF24		OBJECT-TYPE
			SYNTAX	INTEGER
			ACCESS	read-only
			STATUS	current
	DESCRIPTION ""
			::= { mbus79 78 }

mbus79Value24		OBJECT-TYPE
			SYNTAX	INTEGER
			ACCESS	read-only
			STATUS	current
	DESCRIPTION ""
			::= { mbus79 79 }

mbus79VIF25		OBJECT-TYPE
			SYNTAX	INTEGER
			ACCESS	read-only
			STATUS	current
	DESCRIPTION ""
			::= { mbus79 80 }

mbus79Value25		OBJECT-TYPE
			SYNTAX	INTEGER
			ACCESS	read-only
			STATUS	current
	DESCRIPTION ""
			::= { mbus79 81 }

mbus79VIF26		OBJECT-TYPE
			SYNTAX	INTEGER
			ACCESS	read-only
			STATUS	current
	DESCRIPTION ""
			::= { mbus79 82 }

mbus79Value26		OBJECT-TYPE
			SYNTAX	INTEGER
			ACCESS	read-only
			STATUS	current
	DESCRIPTION ""
			::= { mbus79 83 }

mbus79VIF27		OBJECT-TYPE
			SYNTAX	INTEGER
			ACCESS	read-only
			STATUS	current
	DESCRIPTION ""
			::= { mbus79 84 }

mbus79Value27		OBJECT-TYPE
			SYNTAX	INTEGER
			ACCESS	read-only
			STATUS	current
	DESCRIPTION ""
			::= { mbus79 85 }

mbus79VIF28		OBJECT-TYPE
			SYNTAX	INTEGER
			ACCESS	read-only
			STATUS	current
	DESCRIPTION ""
			::= { mbus79 86 }

mbus79Value28		OBJECT-TYPE
			SYNTAX	INTEGER
			ACCESS	read-only
			STATUS	current
	DESCRIPTION ""
			::= { mbus79 87 }

mbus79VIF29		OBJECT-TYPE
			SYNTAX	INTEGER
			ACCESS	read-only
			STATUS	current
	DESCRIPTION ""
			::= { mbus79 88 }

mbus79Value29		OBJECT-TYPE
			SYNTAX	INTEGER
			ACCESS	read-only
			STATUS	current
	DESCRIPTION ""
			::= { mbus79 89 }

mbus79VIF2A		OBJECT-TYPE
			SYNTAX	INTEGER
			ACCESS	read-only
			STATUS	current
	DESCRIPTION ""
			::= { mbus79 90 }

mbus79Value2A		OBJECT-TYPE
			SYNTAX	INTEGER
			ACCESS	read-only
			STATUS	current
	DESCRIPTION ""
			::= { mbus79 91 }

mbus79VIF2B		OBJECT-TYPE
			SYNTAX	INTEGER
			ACCESS	read-only
			STATUS	current
	DESCRIPTION ""
			::= { mbus79 92 }

mbus79Value2B		OBJECT-TYPE
			SYNTAX	INTEGER
			ACCESS	read-only
			STATUS	current
	DESCRIPTION ""
			::= { mbus79 93 }

mbus79VIF2C		OBJECT-TYPE
			SYNTAX	INTEGER
			ACCESS	read-only
			STATUS	current
	DESCRIPTION ""
			::= { mbus79 94 }

mbus79Value2C		OBJECT-TYPE
			SYNTAX	INTEGER
			ACCESS	read-only
			STATUS	current
	DESCRIPTION ""
			::= { mbus79 95 }

mbus79VIF2D		OBJECT-TYPE
			SYNTAX	INTEGER
			ACCESS	read-only
			STATUS	current
	DESCRIPTION ""
			::= { mbus79 96 }

mbus79Value2D		OBJECT-TYPE
			SYNTAX	INTEGER
			ACCESS	read-only
			STATUS	current
	DESCRIPTION ""
			::= { mbus79 97 }

mbus79VIF2E		OBJECT-TYPE
			SYNTAX	INTEGER
			ACCESS	read-only
			STATUS	current
	DESCRIPTION ""
			::= { mbus79 98 }

mbus79Value2E		OBJECT-TYPE
			SYNTAX	INTEGER
			ACCESS	read-only
			STATUS	current
	DESCRIPTION ""
			::= { mbus79 99 }

mbus79VIF2F		OBJECT-TYPE
			SYNTAX	INTEGER
			ACCESS	read-only
			STATUS	current
	DESCRIPTION ""
			::= { mbus79 100 }

mbus79Value2F		OBJECT-TYPE
			SYNTAX	INTEGER
			ACCESS	read-only
			STATUS	current
	DESCRIPTION ""
			::= { mbus79 101 }

mbus7A			OBJECT IDENTIFIER ::= { mbus 122 }

mbus7AIdNumber		OBJECT-TYPE
			SYNTAX	Gauge
			ACCESS	read-only
			STATUS	current
	DESCRIPTION ""
			::= { mbus7A 1 }

mbus7AManufacturer	OBJECT-TYPE
			SYNTAX	Gauge
			ACCESS	read-only
			STATUS	current
	DESCRIPTION ""
			::= { mbus7A 2 }

mbus7AVersion		OBJECT-TYPE
			SYNTAX	Gauge
			ACCESS	read-only
			STATUS	current
	DESCRIPTION ""
			::= { mbus7A 3 }

mbus7AMedium		OBJECT-TYPE
			SYNTAX	Gauge
			ACCESS	read-only
			STATUS	current
	DESCRIPTION ""
			::= { mbus7A 4 }

mbus7AStatus		OBJECT-TYPE
			SYNTAX	Gauge
			ACCESS	read-only
			STATUS	current
	DESCRIPTION ""
			::= { mbus7A 5 }

mbus7AVIF00		OBJECT-TYPE
			SYNTAX	INTEGER
			ACCESS	read-only
			STATUS	current
	DESCRIPTION ""
			::= { mbus7A 6 }

mbus7AValue00		OBJECT-TYPE
			SYNTAX	INTEGER
			ACCESS	read-only
			STATUS	current
	DESCRIPTION ""
			::= { mbus7A 7 }

mbus7AVIF01		OBJECT-TYPE
			SYNTAX	INTEGER
			ACCESS	read-only
			STATUS	current
	DESCRIPTION ""
			::= { mbus7A 8 }

mbus7AValue01		OBJECT-TYPE
			SYNTAX	INTEGER
			ACCESS	read-only
			STATUS	current
	DESCRIPTION ""
			::= { mbus7A 9 }

mbus7AVIF02		OBJECT-TYPE
			SYNTAX	INTEGER
			ACCESS	read-only
			STATUS	current
	DESCRIPTION ""
			::= { mbus7A 10 }

mbus7AValue02		OBJECT-TYPE
			SYNTAX	INTEGER
			ACCESS	read-only
			STATUS	current
	DESCRIPTION ""
			::= { mbus7A 11 }

mbus7AVIF03		OBJECT-TYPE
			SYNTAX	INTEGER
			ACCESS	read-only
			STATUS	current
	DESCRIPTION ""
			::= { mbus7A 12 }

mbus7AValue03		OBJECT-TYPE
			SYNTAX	INTEGER
			ACCESS	read-only
			STATUS	current
	DESCRIPTION ""
			::= { mbus7A 13 }

mbus7AVIF04		OBJECT-TYPE
			SYNTAX	INTEGER
			ACCESS	read-only
			STATUS	current
	DESCRIPTION ""
			::= { mbus7A 14 }

mbus7AValue04		OBJECT-TYPE
			SYNTAX	INTEGER
			ACCESS	read-only
			STATUS	current
	DESCRIPTION ""
			::= { mbus7A 15 }

mbus7AVIF05		OBJECT-TYPE
			SYNTAX	INTEGER
			ACCESS	read-only
			STATUS	current
	DESCRIPTION ""
			::= { mbus7A 16 }

mbus7AValue05		OBJECT-TYPE
			SYNTAX	INTEGER
			ACCESS	read-only
			STATUS	current
	DESCRIPTION ""
			::= { mbus7A 17 }

mbus7AVIF06		OBJECT-TYPE
			SYNTAX	INTEGER
			ACCESS	read-only
			STATUS	current
	DESCRIPTION ""
			::= { mbus7A 18 }

mbus7AValue06		OBJECT-TYPE
			SYNTAX	INTEGER
			ACCESS	read-only
			STATUS	current
	DESCRIPTION ""
			::= { mbus7A 19 }

mbus7AVIF07		OBJECT-TYPE
			SYNTAX	INTEGER
			ACCESS	read-only
			STATUS	current
	DESCRIPTION ""
			::= { mbus7A 20 }

mbus7AValue07		OBJECT-TYPE
			SYNTAX	INTEGER
			ACCESS	read-only
			STATUS	current
	DESCRIPTION ""
			::= { mbus7A 21 }

mbus7AVIF08		OBJECT-TYPE
			SYNTAX	INTEGER
			ACCESS	read-only
			STATUS	current
	DESCRIPTION ""
			::= { mbus7A 22 }

mbus7AValue08		OBJECT-TYPE
			SYNTAX	INTEGER
			ACCESS	read-only
			STATUS	current
	DESCRIPTION ""
			::= { mbus7A 23 }

mbus7AVIF09		OBJECT-TYPE
			SYNTAX	INTEGER
			ACCESS	read-only
			STATUS	current
	DESCRIPTION ""
			::= { mbus7A 24 }

mbus7AValue09		OBJECT-TYPE
			SYNTAX	INTEGER
			ACCESS	read-only
			STATUS	current
	DESCRIPTION ""
			::= { mbus7A 25 }

mbus7AVIF0A		OBJECT-TYPE
			SYNTAX	INTEGER
			ACCESS	read-only
			STATUS	current
	DESCRIPTION ""
			::= { mbus7A 26 }

mbus7AValue0A		OBJECT-TYPE
			SYNTAX	INTEGER
			ACCESS	read-only
			STATUS	current
	DESCRIPTION ""
			::= { mbus7A 27 }

mbus7AVIF0B		OBJECT-TYPE
			SYNTAX	INTEGER
			ACCESS	read-only
			STATUS	current
	DESCRIPTION ""
			::= { mbus7A 28 }

mbus7AValue0B		OBJECT-TYPE
			SYNTAX	INTEGER
			ACCESS	read-only
			STATUS	current
	DESCRIPTION ""
			::= { mbus7A 29 }

mbus7AVIF0C		OBJECT-TYPE
			SYNTAX	INTEGER
			ACCESS	read-only
			STATUS	current
	DESCRIPTION ""
			::= { mbus7A 30 }

mbus7AValue0C		OBJECT-TYPE
			SYNTAX	INTEGER
			ACCESS	read-only
			STATUS	current
	DESCRIPTION ""
			::= { mbus7A 31 }

mbus7AVIF0D		OBJECT-TYPE
			SYNTAX	INTEGER
			ACCESS	read-only
			STATUS	current
	DESCRIPTION ""
			::= { mbus7A 32 }

mbus7AValue0D		OBJECT-TYPE
			SYNTAX	INTEGER
			ACCESS	read-only
			STATUS	current
	DESCRIPTION ""
			::= { mbus7A 33 }

mbus7AVIF0E		OBJECT-TYPE
			SYNTAX	INTEGER
			ACCESS	read-only
			STATUS	current
	DESCRIPTION ""
			::= { mbus7A 34 }

mbus7AValue0E		OBJECT-TYPE
			SYNTAX	INTEGER
			ACCESS	read-only
			STATUS	current
	DESCRIPTION ""
			::= { mbus7A 35 }

mbus7AVIF0F		OBJECT-TYPE
			SYNTAX	INTEGER
			ACCESS	read-only
			STATUS	current
	DESCRIPTION ""
			::= { mbus7A 36 }

mbus7AValue0F		OBJECT-TYPE
			SYNTAX	INTEGER
			ACCESS	read-only
			STATUS	current
	DESCRIPTION ""
			::= { mbus7A 37 }

mbus7AVIF10		OBJECT-TYPE
			SYNTAX	INTEGER
			ACCESS	read-only
			STATUS	current
	DESCRIPTION ""
			::= { mbus7A 38 }

mbus7AValue10		OBJECT-TYPE
			SYNTAX	INTEGER
			ACCESS	read-only
			STATUS	current
	DESCRIPTION ""
			::= { mbus7A 39 }

mbus7AVIF11		OBJECT-TYPE
			SYNTAX	INTEGER
			ACCESS	read-only
			STATUS	current
	DESCRIPTION ""
			::= { mbus7A 40 }

mbus7AValue11		OBJECT-TYPE
			SYNTAX	INTEGER
			ACCESS	read-only
			STATUS	current
	DESCRIPTION ""
			::= { mbus7A 41 }

mbus7AVIF12		OBJECT-TYPE
			SYNTAX	INTEGER
			ACCESS	read-only
			STATUS	current
	DESCRIPTION ""
			::= { mbus7A 42 }

mbus7AValue12		OBJECT-TYPE
			SYNTAX	INTEGER
			ACCESS	read-only
			STATUS	current
	DESCRIPTION ""
			::= { mbus7A 43 }

mbus7AVIF13		OBJECT-TYPE
			SYNTAX	INTEGER
			ACCESS	read-only
			STATUS	current
	DESCRIPTION ""
			::= { mbus7A 44 }

mbus7AValue13		OBJECT-TYPE
			SYNTAX	INTEGER
			ACCESS	read-only
			STATUS	current
	DESCRIPTION ""
			::= { mbus7A 45 }

mbus7AVIF14		OBJECT-TYPE
			SYNTAX	INTEGER
			ACCESS	read-only
			STATUS	current
	DESCRIPTION ""
			::= { mbus7A 46 }

mbus7AValue14		OBJECT-TYPE
			SYNTAX	INTEGER
			ACCESS	read-only
			STATUS	current
	DESCRIPTION ""
			::= { mbus7A 47 }

mbus7AVIF15		OBJECT-TYPE
			SYNTAX	INTEGER
			ACCESS	read-only
			STATUS	current
	DESCRIPTION ""
			::= { mbus7A 48 }

mbus7AValue15		OBJECT-TYPE
			SYNTAX	INTEGER
			ACCESS	read-only
			STATUS	current
	DESCRIPTION ""
			::= { mbus7A 49 }

mbus7AVIF16		OBJECT-TYPE
			SYNTAX	INTEGER
			ACCESS	read-only
			STATUS	current
	DESCRIPTION ""
			::= { mbus7A 50 }

mbus7AValue16		OBJECT-TYPE
			SYNTAX	INTEGER
			ACCESS	read-only
			STATUS	current
	DESCRIPTION ""
			::= { mbus7A 51 }

mbus7AVIF17		OBJECT-TYPE
			SYNTAX	INTEGER
			ACCESS	read-only
			STATUS	current
	DESCRIPTION ""
			::= { mbus7A 52 }

mbus7AValue17		OBJECT-TYPE
			SYNTAX	INTEGER
			ACCESS	read-only
			STATUS	current
	DESCRIPTION ""
			::= { mbus7A 53 }

mbus7AVIF18		OBJECT-TYPE
			SYNTAX	INTEGER
			ACCESS	read-only
			STATUS	current
	DESCRIPTION ""
			::= { mbus7A 54 }

mbus7AValue18		OBJECT-TYPE
			SYNTAX	INTEGER
			ACCESS	read-only
			STATUS	current
	DESCRIPTION ""
			::= { mbus7A 55 }

mbus7AVIF19		OBJECT-TYPE
			SYNTAX	INTEGER
			ACCESS	read-only
			STATUS	current
	DESCRIPTION ""
			::= { mbus7A 56 }

mbus7AValue19		OBJECT-TYPE
			SYNTAX	INTEGER
			ACCESS	read-only
			STATUS	current
	DESCRIPTION ""
			::= { mbus7A 57 }

mbus7AVIF1A		OBJECT-TYPE
			SYNTAX	INTEGER
			ACCESS	read-only
			STATUS	current
	DESCRIPTION ""
			::= { mbus7A 58 }

mbus7AValue1A		OBJECT-TYPE
			SYNTAX	INTEGER
			ACCESS	read-only
			STATUS	current
	DESCRIPTION ""
			::= { mbus7A 59 }

mbus7AVIF1B		OBJECT-TYPE
			SYNTAX	INTEGER
			ACCESS	read-only
			STATUS	current
	DESCRIPTION ""
			::= { mbus7A 60 }

mbus7AValue1B		OBJECT-TYPE
			SYNTAX	INTEGER
			ACCESS	read-only
			STATUS	current
	DESCRIPTION ""
			::= { mbus7A 61 }

mbus7AVIF1C		OBJECT-TYPE
			SYNTAX	INTEGER
			ACCESS	read-only
			STATUS	current
	DESCRIPTION ""
			::= { mbus7A 62 }

mbus7AValue1C		OBJECT-TYPE
			SYNTAX	INTEGER
			ACCESS	read-only
			STATUS	current
	DESCRIPTION ""
			::= { mbus7A 63 }

mbus7AVIF1D		OBJECT-TYPE
			SYNTAX	INTEGER
			ACCESS	read-only
			STATUS	current
	DESCRIPTION ""
			::= { mbus7A 64 }

mbus7AValue1D		OBJECT-TYPE
			SYNTAX	INTEGER
			ACCESS	read-only
			STATUS	current
	DESCRIPTION ""
			::= { mbus7A 65 }

mbus7AVIF1E		OBJECT-TYPE
			SYNTAX	INTEGER
			ACCESS	read-only
			STATUS	current
	DESCRIPTION ""
			::= { mbus7A 66 }

mbus7AValue1E		OBJECT-TYPE
			SYNTAX	INTEGER
			ACCESS	read-only
			STATUS	current
	DESCRIPTION ""
			::= { mbus7A 67 }

mbus7AVIF1F		OBJECT-TYPE
			SYNTAX	INTEGER
			ACCESS	read-only
			STATUS	current
	DESCRIPTION ""
			::= { mbus7A 68 }

mbus7AValue1F		OBJECT-TYPE
			SYNTAX	INTEGER
			ACCESS	read-only
			STATUS	current
	DESCRIPTION ""
			::= { mbus7A 69 }

mbus7AVIF20		OBJECT-TYPE
			SYNTAX	INTEGER
			ACCESS	read-only
			STATUS	current
	DESCRIPTION ""
			::= { mbus7A 70 }

mbus7AValue20		OBJECT-TYPE
			SYNTAX	INTEGER
			ACCESS	read-only
			STATUS	current
	DESCRIPTION ""
			::= { mbus7A 71 }

mbus7AVIF21		OBJECT-TYPE
			SYNTAX	INTEGER
			ACCESS	read-only
			STATUS	current
	DESCRIPTION ""
			::= { mbus7A 72 }

mbus7AValue21		OBJECT-TYPE
			SYNTAX	INTEGER
			ACCESS	read-only
			STATUS	current
	DESCRIPTION ""
			::= { mbus7A 73 }

mbus7AVIF22		OBJECT-TYPE
			SYNTAX	INTEGER
			ACCESS	read-only
			STATUS	current
	DESCRIPTION ""
			::= { mbus7A 74 }

mbus7AValue22		OBJECT-TYPE
			SYNTAX	INTEGER
			ACCESS	read-only
			STATUS	current
	DESCRIPTION ""
			::= { mbus7A 75 }

mbus7AVIF23		OBJECT-TYPE
			SYNTAX	INTEGER
			ACCESS	read-only
			STATUS	current
	DESCRIPTION ""
			::= { mbus7A 76 }

mbus7AValue23		OBJECT-TYPE
			SYNTAX	INTEGER
			ACCESS	read-only
			STATUS	current
	DESCRIPTION ""
			::= { mbus7A 77 }

mbus7AVIF24		OBJECT-TYPE
			SYNTAX	INTEGER
			ACCESS	read-only
			STATUS	current
	DESCRIPTION ""
			::= { mbus7A 78 }

mbus7AValue24		OBJECT-TYPE
			SYNTAX	INTEGER
			ACCESS	read-only
			STATUS	current
	DESCRIPTION ""
			::= { mbus7A 79 }

mbus7AVIF25		OBJECT-TYPE
			SYNTAX	INTEGER
			ACCESS	read-only
			STATUS	current
	DESCRIPTION ""
			::= { mbus7A 80 }

mbus7AValue25		OBJECT-TYPE
			SYNTAX	INTEGER
			ACCESS	read-only
			STATUS	current
	DESCRIPTION ""
			::= { mbus7A 81 }

mbus7AVIF26		OBJECT-TYPE
			SYNTAX	INTEGER
			ACCESS	read-only
			STATUS	current
	DESCRIPTION ""
			::= { mbus7A 82 }

mbus7AValue26		OBJECT-TYPE
			SYNTAX	INTEGER
			ACCESS	read-only
			STATUS	current
	DESCRIPTION ""
			::= { mbus7A 83 }

mbus7AVIF27		OBJECT-TYPE
			SYNTAX	INTEGER
			ACCESS	read-only
			STATUS	current
	DESCRIPTION ""
			::= { mbus7A 84 }

mbus7AValue27		OBJECT-TYPE
			SYNTAX	INTEGER
			ACCESS	read-only
			STATUS	current
	DESCRIPTION ""
			::= { mbus7A 85 }

mbus7AVIF28		OBJECT-TYPE
			SYNTAX	INTEGER
			ACCESS	read-only
			STATUS	current
	DESCRIPTION ""
			::= { mbus7A 86 }

mbus7AValue28		OBJECT-TYPE
			SYNTAX	INTEGER
			ACCESS	read-only
			STATUS	current
	DESCRIPTION ""
			::= { mbus7A 87 }

mbus7AVIF29		OBJECT-TYPE
			SYNTAX	INTEGER
			ACCESS	read-only
			STATUS	current
	DESCRIPTION ""
			::= { mbus7A 88 }

mbus7AValue29		OBJECT-TYPE
			SYNTAX	INTEGER
			ACCESS	read-only
			STATUS	current
	DESCRIPTION ""
			::= { mbus7A 89 }

mbus7AVIF2A		OBJECT-TYPE
			SYNTAX	INTEGER
			ACCESS	read-only
			STATUS	current
	DESCRIPTION ""
			::= { mbus7A 90 }

mbus7AValue2A		OBJECT-TYPE
			SYNTAX	INTEGER
			ACCESS	read-only
			STATUS	current
	DESCRIPTION ""
			::= { mbus7A 91 }

mbus7AVIF2B		OBJECT-TYPE
			SYNTAX	INTEGER
			ACCESS	read-only
			STATUS	current
	DESCRIPTION ""
			::= { mbus7A 92 }

mbus7AValue2B		OBJECT-TYPE
			SYNTAX	INTEGER
			ACCESS	read-only
			STATUS	current
	DESCRIPTION ""
			::= { mbus7A 93 }

mbus7AVIF2C		OBJECT-TYPE
			SYNTAX	INTEGER
			ACCESS	read-only
			STATUS	current
	DESCRIPTION ""
			::= { mbus7A 94 }

mbus7AValue2C		OBJECT-TYPE
			SYNTAX	INTEGER
			ACCESS	read-only
			STATUS	current
	DESCRIPTION ""
			::= { mbus7A 95 }

mbus7AVIF2D		OBJECT-TYPE
			SYNTAX	INTEGER
			ACCESS	read-only
			STATUS	current
	DESCRIPTION ""
			::= { mbus7A 96 }

mbus7AValue2D		OBJECT-TYPE
			SYNTAX	INTEGER
			ACCESS	read-only
			STATUS	current
	DESCRIPTION ""
			::= { mbus7A 97 }

mbus7AVIF2E		OBJECT-TYPE
			SYNTAX	INTEGER
			ACCESS	read-only
			STATUS	current
	DESCRIPTION ""
			::= { mbus7A 98 }

mbus7AValue2E		OBJECT-TYPE
			SYNTAX	INTEGER
			ACCESS	read-only
			STATUS	current
	DESCRIPTION ""
			::= { mbus7A 99 }

mbus7AVIF2F		OBJECT-TYPE
			SYNTAX	INTEGER
			ACCESS	read-only
			STATUS	current
	DESCRIPTION ""
			::= { mbus7A 100 }

mbus7AValue2F		OBJECT-TYPE
			SYNTAX	INTEGER
			ACCESS	read-only
			STATUS	current
	DESCRIPTION ""
			::= { mbus7A 101 }

mbus7B			OBJECT IDENTIFIER ::= { mbus 123 }

mbus7BIdNumber		OBJECT-TYPE
			SYNTAX	Gauge
			ACCESS	read-only
			STATUS	current
	DESCRIPTION ""
			::= { mbus7B 1 }

mbus7BManufacturer	OBJECT-TYPE
			SYNTAX	Gauge
			ACCESS	read-only
			STATUS	current
	DESCRIPTION ""
			::= { mbus7B 2 }

mbus7BVersion		OBJECT-TYPE
			SYNTAX	Gauge
			ACCESS	read-only
			STATUS	current
	DESCRIPTION ""
			::= { mbus7B 3 }

mbus7BMedium		OBJECT-TYPE
			SYNTAX	Gauge
			ACCESS	read-only
			STATUS	current
	DESCRIPTION ""
			::= { mbus7B 4 }

mbus7BStatus		OBJECT-TYPE
			SYNTAX	Gauge
			ACCESS	read-only
			STATUS	current
	DESCRIPTION ""
			::= { mbus7B 5 }

mbus7BVIF00		OBJECT-TYPE
			SYNTAX	INTEGER
			ACCESS	read-only
			STATUS	current
	DESCRIPTION ""
			::= { mbus7B 6 }

mbus7BValue00		OBJECT-TYPE
			SYNTAX	INTEGER
			ACCESS	read-only
			STATUS	current
	DESCRIPTION ""
			::= { mbus7B 7 }

mbus7BVIF01		OBJECT-TYPE
			SYNTAX	INTEGER
			ACCESS	read-only
			STATUS	current
	DESCRIPTION ""
			::= { mbus7B 8 }

mbus7BValue01		OBJECT-TYPE
			SYNTAX	INTEGER
			ACCESS	read-only
			STATUS	current
	DESCRIPTION ""
			::= { mbus7B 9 }

mbus7BVIF02		OBJECT-TYPE
			SYNTAX	INTEGER
			ACCESS	read-only
			STATUS	current
	DESCRIPTION ""
			::= { mbus7B 10 }

mbus7BValue02		OBJECT-TYPE
			SYNTAX	INTEGER
			ACCESS	read-only
			STATUS	current
	DESCRIPTION ""
			::= { mbus7B 11 }

mbus7BVIF03		OBJECT-TYPE
			SYNTAX	INTEGER
			ACCESS	read-only
			STATUS	current
	DESCRIPTION ""
			::= { mbus7B 12 }

mbus7BValue03		OBJECT-TYPE
			SYNTAX	INTEGER
			ACCESS	read-only
			STATUS	current
	DESCRIPTION ""
			::= { mbus7B 13 }

mbus7BVIF04		OBJECT-TYPE
			SYNTAX	INTEGER
			ACCESS	read-only
			STATUS	current
	DESCRIPTION ""
			::= { mbus7B 14 }

mbus7BValue04		OBJECT-TYPE
			SYNTAX	INTEGER
			ACCESS	read-only
			STATUS	current
	DESCRIPTION ""
			::= { mbus7B 15 }

mbus7BVIF05		OBJECT-TYPE
			SYNTAX	INTEGER
			ACCESS	read-only
			STATUS	current
	DESCRIPTION ""
			::= { mbus7B 16 }

mbus7BValue05		OBJECT-TYPE
			SYNTAX	INTEGER
			ACCESS	read-only
			STATUS	current
	DESCRIPTION ""
			::= { mbus7B 17 }

mbus7BVIF06		OBJECT-TYPE
			SYNTAX	INTEGER
			ACCESS	read-only
			STATUS	current
	DESCRIPTION ""
			::= { mbus7B 18 }

mbus7BValue06		OBJECT-TYPE
			SYNTAX	INTEGER
			ACCESS	read-only
			STATUS	current
	DESCRIPTION ""
			::= { mbus7B 19 }

mbus7BVIF07		OBJECT-TYPE
			SYNTAX	INTEGER
			ACCESS	read-only
			STATUS	current
	DESCRIPTION ""
			::= { mbus7B 20 }

mbus7BValue07		OBJECT-TYPE
			SYNTAX	INTEGER
			ACCESS	read-only
			STATUS	current
	DESCRIPTION ""
			::= { mbus7B 21 }

mbus7BVIF08		OBJECT-TYPE
			SYNTAX	INTEGER
			ACCESS	read-only
			STATUS	current
	DESCRIPTION ""
			::= { mbus7B 22 }

mbus7BValue08		OBJECT-TYPE
			SYNTAX	INTEGER
			ACCESS	read-only
			STATUS	current
	DESCRIPTION ""
			::= { mbus7B 23 }

mbus7BVIF09		OBJECT-TYPE
			SYNTAX	INTEGER
			ACCESS	read-only
			STATUS	current
	DESCRIPTION ""
			::= { mbus7B 24 }

mbus7BValue09		OBJECT-TYPE
			SYNTAX	INTEGER
			ACCESS	read-only
			STATUS	current
	DESCRIPTION ""
			::= { mbus7B 25 }

mbus7BVIF0A		OBJECT-TYPE
			SYNTAX	INTEGER
			ACCESS	read-only
			STATUS	current
	DESCRIPTION ""
			::= { mbus7B 26 }

mbus7BValue0A		OBJECT-TYPE
			SYNTAX	INTEGER
			ACCESS	read-only
			STATUS	current
	DESCRIPTION ""
			::= { mbus7B 27 }

mbus7BVIF0B		OBJECT-TYPE
			SYNTAX	INTEGER
			ACCESS	read-only
			STATUS	current
	DESCRIPTION ""
			::= { mbus7B 28 }

mbus7BValue0B		OBJECT-TYPE
			SYNTAX	INTEGER
			ACCESS	read-only
			STATUS	current
	DESCRIPTION ""
			::= { mbus7B 29 }

mbus7BVIF0C		OBJECT-TYPE
			SYNTAX	INTEGER
			ACCESS	read-only
			STATUS	current
	DESCRIPTION ""
			::= { mbus7B 30 }

mbus7BValue0C		OBJECT-TYPE
			SYNTAX	INTEGER
			ACCESS	read-only
			STATUS	current
	DESCRIPTION ""
			::= { mbus7B 31 }

mbus7BVIF0D		OBJECT-TYPE
			SYNTAX	INTEGER
			ACCESS	read-only
			STATUS	current
	DESCRIPTION ""
			::= { mbus7B 32 }

mbus7BValue0D		OBJECT-TYPE
			SYNTAX	INTEGER
			ACCESS	read-only
			STATUS	current
	DESCRIPTION ""
			::= { mbus7B 33 }

mbus7BVIF0E		OBJECT-TYPE
			SYNTAX	INTEGER
			ACCESS	read-only
			STATUS	current
	DESCRIPTION ""
			::= { mbus7B 34 }

mbus7BValue0E		OBJECT-TYPE
			SYNTAX	INTEGER
			ACCESS	read-only
			STATUS	current
	DESCRIPTION ""
			::= { mbus7B 35 }

mbus7BVIF0F		OBJECT-TYPE
			SYNTAX	INTEGER
			ACCESS	read-only
			STATUS	current
	DESCRIPTION ""
			::= { mbus7B 36 }

mbus7BValue0F		OBJECT-TYPE
			SYNTAX	INTEGER
			ACCESS	read-only
			STATUS	current
	DESCRIPTION ""
			::= { mbus7B 37 }

mbus7BVIF10		OBJECT-TYPE
			SYNTAX	INTEGER
			ACCESS	read-only
			STATUS	current
	DESCRIPTION ""
			::= { mbus7B 38 }

mbus7BValue10		OBJECT-TYPE
			SYNTAX	INTEGER
			ACCESS	read-only
			STATUS	current
	DESCRIPTION ""
			::= { mbus7B 39 }

mbus7BVIF11		OBJECT-TYPE
			SYNTAX	INTEGER
			ACCESS	read-only
			STATUS	current
	DESCRIPTION ""
			::= { mbus7B 40 }

mbus7BValue11		OBJECT-TYPE
			SYNTAX	INTEGER
			ACCESS	read-only
			STATUS	current
	DESCRIPTION ""
			::= { mbus7B 41 }

mbus7BVIF12		OBJECT-TYPE
			SYNTAX	INTEGER
			ACCESS	read-only
			STATUS	current
	DESCRIPTION ""
			::= { mbus7B 42 }

mbus7BValue12		OBJECT-TYPE
			SYNTAX	INTEGER
			ACCESS	read-only
			STATUS	current
	DESCRIPTION ""
			::= { mbus7B 43 }

mbus7BVIF13		OBJECT-TYPE
			SYNTAX	INTEGER
			ACCESS	read-only
			STATUS	current
	DESCRIPTION ""
			::= { mbus7B 44 }

mbus7BValue13		OBJECT-TYPE
			SYNTAX	INTEGER
			ACCESS	read-only
			STATUS	current
	DESCRIPTION ""
			::= { mbus7B 45 }

mbus7BVIF14		OBJECT-TYPE
			SYNTAX	INTEGER
			ACCESS	read-only
			STATUS	current
	DESCRIPTION ""
			::= { mbus7B 46 }

mbus7BValue14		OBJECT-TYPE
			SYNTAX	INTEGER
			ACCESS	read-only
			STATUS	current
	DESCRIPTION ""
			::= { mbus7B 47 }

mbus7BVIF15		OBJECT-TYPE
			SYNTAX	INTEGER
			ACCESS	read-only
			STATUS	current
	DESCRIPTION ""
			::= { mbus7B 48 }

mbus7BValue15		OBJECT-TYPE
			SYNTAX	INTEGER
			ACCESS	read-only
			STATUS	current
	DESCRIPTION ""
			::= { mbus7B 49 }

mbus7BVIF16		OBJECT-TYPE
			SYNTAX	INTEGER
			ACCESS	read-only
			STATUS	current
	DESCRIPTION ""
			::= { mbus7B 50 }

mbus7BValue16		OBJECT-TYPE
			SYNTAX	INTEGER
			ACCESS	read-only
			STATUS	current
	DESCRIPTION ""
			::= { mbus7B 51 }

mbus7BVIF17		OBJECT-TYPE
			SYNTAX	INTEGER
			ACCESS	read-only
			STATUS	current
	DESCRIPTION ""
			::= { mbus7B 52 }

mbus7BValue17		OBJECT-TYPE
			SYNTAX	INTEGER
			ACCESS	read-only
			STATUS	current
	DESCRIPTION ""
			::= { mbus7B 53 }

mbus7BVIF18		OBJECT-TYPE
			SYNTAX	INTEGER
			ACCESS	read-only
			STATUS	current
	DESCRIPTION ""
			::= { mbus7B 54 }

mbus7BValue18		OBJECT-TYPE
			SYNTAX	INTEGER
			ACCESS	read-only
			STATUS	current
	DESCRIPTION ""
			::= { mbus7B 55 }

mbus7BVIF19		OBJECT-TYPE
			SYNTAX	INTEGER
			ACCESS	read-only
			STATUS	current
	DESCRIPTION ""
			::= { mbus7B 56 }

mbus7BValue19		OBJECT-TYPE
			SYNTAX	INTEGER
			ACCESS	read-only
			STATUS	current
	DESCRIPTION ""
			::= { mbus7B 57 }

mbus7BVIF1A		OBJECT-TYPE
			SYNTAX	INTEGER
			ACCESS	read-only
			STATUS	current
	DESCRIPTION ""
			::= { mbus7B 58 }

mbus7BValue1A		OBJECT-TYPE
			SYNTAX	INTEGER
			ACCESS	read-only
			STATUS	current
	DESCRIPTION ""
			::= { mbus7B 59 }

mbus7BVIF1B		OBJECT-TYPE
			SYNTAX	INTEGER
			ACCESS	read-only
			STATUS	current
	DESCRIPTION ""
			::= { mbus7B 60 }

mbus7BValue1B		OBJECT-TYPE
			SYNTAX	INTEGER
			ACCESS	read-only
			STATUS	current
	DESCRIPTION ""
			::= { mbus7B 61 }

mbus7BVIF1C		OBJECT-TYPE
			SYNTAX	INTEGER
			ACCESS	read-only
			STATUS	current
	DESCRIPTION ""
			::= { mbus7B 62 }

mbus7BValue1C		OBJECT-TYPE
			SYNTAX	INTEGER
			ACCESS	read-only
			STATUS	current
	DESCRIPTION ""
			::= { mbus7B 63 }

mbus7BVIF1D		OBJECT-TYPE
			SYNTAX	INTEGER
			ACCESS	read-only
			STATUS	current
	DESCRIPTION ""
			::= { mbus7B 64 }

mbus7BValue1D		OBJECT-TYPE
			SYNTAX	INTEGER
			ACCESS	read-only
			STATUS	current
	DESCRIPTION ""
			::= { mbus7B 65 }

mbus7BVIF1E		OBJECT-TYPE
			SYNTAX	INTEGER
			ACCESS	read-only
			STATUS	current
	DESCRIPTION ""
			::= { mbus7B 66 }

mbus7BValue1E		OBJECT-TYPE
			SYNTAX	INTEGER
			ACCESS	read-only
			STATUS	current
	DESCRIPTION ""
			::= { mbus7B 67 }

mbus7BVIF1F		OBJECT-TYPE
			SYNTAX	INTEGER
			ACCESS	read-only
			STATUS	current
	DESCRIPTION ""
			::= { mbus7B 68 }

mbus7BValue1F		OBJECT-TYPE
			SYNTAX	INTEGER
			ACCESS	read-only
			STATUS	current
	DESCRIPTION ""
			::= { mbus7B 69 }

mbus7BVIF20		OBJECT-TYPE
			SYNTAX	INTEGER
			ACCESS	read-only
			STATUS	current
	DESCRIPTION ""
			::= { mbus7B 70 }

mbus7BValue20		OBJECT-TYPE
			SYNTAX	INTEGER
			ACCESS	read-only
			STATUS	current
	DESCRIPTION ""
			::= { mbus7B 71 }

mbus7BVIF21		OBJECT-TYPE
			SYNTAX	INTEGER
			ACCESS	read-only
			STATUS	current
	DESCRIPTION ""
			::= { mbus7B 72 }

mbus7BValue21		OBJECT-TYPE
			SYNTAX	INTEGER
			ACCESS	read-only
			STATUS	current
	DESCRIPTION ""
			::= { mbus7B 73 }

mbus7BVIF22		OBJECT-TYPE
			SYNTAX	INTEGER
			ACCESS	read-only
			STATUS	current
	DESCRIPTION ""
			::= { mbus7B 74 }

mbus7BValue22		OBJECT-TYPE
			SYNTAX	INTEGER
			ACCESS	read-only
			STATUS	current
	DESCRIPTION ""
			::= { mbus7B 75 }

mbus7BVIF23		OBJECT-TYPE
			SYNTAX	INTEGER
			ACCESS	read-only
			STATUS	current
	DESCRIPTION ""
			::= { mbus7B 76 }

mbus7BValue23		OBJECT-TYPE
			SYNTAX	INTEGER
			ACCESS	read-only
			STATUS	current
	DESCRIPTION ""
			::= { mbus7B 77 }

mbus7BVIF24		OBJECT-TYPE
			SYNTAX	INTEGER
			ACCESS	read-only
			STATUS	current
	DESCRIPTION ""
			::= { mbus7B 78 }

mbus7BValue24		OBJECT-TYPE
			SYNTAX	INTEGER
			ACCESS	read-only
			STATUS	current
	DESCRIPTION ""
			::= { mbus7B 79 }

mbus7BVIF25		OBJECT-TYPE
			SYNTAX	INTEGER
			ACCESS	read-only
			STATUS	current
	DESCRIPTION ""
			::= { mbus7B 80 }

mbus7BValue25		OBJECT-TYPE
			SYNTAX	INTEGER
			ACCESS	read-only
			STATUS	current
	DESCRIPTION ""
			::= { mbus7B 81 }

mbus7BVIF26		OBJECT-TYPE
			SYNTAX	INTEGER
			ACCESS	read-only
			STATUS	current
	DESCRIPTION ""
			::= { mbus7B 82 }

mbus7BValue26		OBJECT-TYPE
			SYNTAX	INTEGER
			ACCESS	read-only
			STATUS	current
	DESCRIPTION ""
			::= { mbus7B 83 }

mbus7BVIF27		OBJECT-TYPE
			SYNTAX	INTEGER
			ACCESS	read-only
			STATUS	current
	DESCRIPTION ""
			::= { mbus7B 84 }

mbus7BValue27		OBJECT-TYPE
			SYNTAX	INTEGER
			ACCESS	read-only
			STATUS	current
	DESCRIPTION ""
			::= { mbus7B 85 }

mbus7BVIF28		OBJECT-TYPE
			SYNTAX	INTEGER
			ACCESS	read-only
			STATUS	current
	DESCRIPTION ""
			::= { mbus7B 86 }

mbus7BValue28		OBJECT-TYPE
			SYNTAX	INTEGER
			ACCESS	read-only
			STATUS	current
	DESCRIPTION ""
			::= { mbus7B 87 }

mbus7BVIF29		OBJECT-TYPE
			SYNTAX	INTEGER
			ACCESS	read-only
			STATUS	current
	DESCRIPTION ""
			::= { mbus7B 88 }

mbus7BValue29		OBJECT-TYPE
			SYNTAX	INTEGER
			ACCESS	read-only
			STATUS	current
	DESCRIPTION ""
			::= { mbus7B 89 }

mbus7BVIF2A		OBJECT-TYPE
			SYNTAX	INTEGER
			ACCESS	read-only
			STATUS	current
	DESCRIPTION ""
			::= { mbus7B 90 }

mbus7BValue2A		OBJECT-TYPE
			SYNTAX	INTEGER
			ACCESS	read-only
			STATUS	current
	DESCRIPTION ""
			::= { mbus7B 91 }

mbus7BVIF2B		OBJECT-TYPE
			SYNTAX	INTEGER
			ACCESS	read-only
			STATUS	current
	DESCRIPTION ""
			::= { mbus7B 92 }

mbus7BValue2B		OBJECT-TYPE
			SYNTAX	INTEGER
			ACCESS	read-only
			STATUS	current
	DESCRIPTION ""
			::= { mbus7B 93 }

mbus7BVIF2C		OBJECT-TYPE
			SYNTAX	INTEGER
			ACCESS	read-only
			STATUS	current
	DESCRIPTION ""
			::= { mbus7B 94 }

mbus7BValue2C		OBJECT-TYPE
			SYNTAX	INTEGER
			ACCESS	read-only
			STATUS	current
	DESCRIPTION ""
			::= { mbus7B 95 }

mbus7BVIF2D		OBJECT-TYPE
			SYNTAX	INTEGER
			ACCESS	read-only
			STATUS	current
	DESCRIPTION ""
			::= { mbus7B 96 }

mbus7BValue2D		OBJECT-TYPE
			SYNTAX	INTEGER
			ACCESS	read-only
			STATUS	current
	DESCRIPTION ""
			::= { mbus7B 97 }

mbus7BVIF2E		OBJECT-TYPE
			SYNTAX	INTEGER
			ACCESS	read-only
			STATUS	current
	DESCRIPTION ""
			::= { mbus7B 98 }

mbus7BValue2E		OBJECT-TYPE
			SYNTAX	INTEGER
			ACCESS	read-only
			STATUS	current
	DESCRIPTION ""
			::= { mbus7B 99 }

mbus7BVIF2F		OBJECT-TYPE
			SYNTAX	INTEGER
			ACCESS	read-only
			STATUS	current
	DESCRIPTION ""
			::= { mbus7B 100 }

mbus7BValue2F		OBJECT-TYPE
			SYNTAX	INTEGER
			ACCESS	read-only
			STATUS	current
	DESCRIPTION ""
			::= { mbus7B 101 }

mbus7C			OBJECT IDENTIFIER ::= { mbus 124 }

mbus7CIdNumber		OBJECT-TYPE
			SYNTAX	Gauge
			ACCESS	read-only
			STATUS	current
	DESCRIPTION ""
			::= { mbus7C 1 }

mbus7CManufacturer	OBJECT-TYPE
			SYNTAX	Gauge
			ACCESS	read-only
			STATUS	current
	DESCRIPTION ""
			::= { mbus7C 2 }

mbus7CVersion		OBJECT-TYPE
			SYNTAX	Gauge
			ACCESS	read-only
			STATUS	current
	DESCRIPTION ""
			::= { mbus7C 3 }

mbus7CMedium		OBJECT-TYPE
			SYNTAX	Gauge
			ACCESS	read-only
			STATUS	current
	DESCRIPTION ""
			::= { mbus7C 4 }

mbus7CStatus		OBJECT-TYPE
			SYNTAX	Gauge
			ACCESS	read-only
			STATUS	current
	DESCRIPTION ""
			::= { mbus7C 5 }

mbus7CVIF00		OBJECT-TYPE
			SYNTAX	INTEGER
			ACCESS	read-only
			STATUS	current
	DESCRIPTION ""
			::= { mbus7C 6 }

mbus7CValue00		OBJECT-TYPE
			SYNTAX	INTEGER
			ACCESS	read-only
			STATUS	current
	DESCRIPTION ""
			::= { mbus7C 7 }

mbus7CVIF01		OBJECT-TYPE
			SYNTAX	INTEGER
			ACCESS	read-only
			STATUS	current
	DESCRIPTION ""
			::= { mbus7C 8 }

mbus7CValue01		OBJECT-TYPE
			SYNTAX	INTEGER
			ACCESS	read-only
			STATUS	current
	DESCRIPTION ""
			::= { mbus7C 9 }

mbus7CVIF02		OBJECT-TYPE
			SYNTAX	INTEGER
			ACCESS	read-only
			STATUS	current
	DESCRIPTION ""
			::= { mbus7C 10 }

mbus7CValue02		OBJECT-TYPE
			SYNTAX	INTEGER
			ACCESS	read-only
			STATUS	current
	DESCRIPTION ""
			::= { mbus7C 11 }

mbus7CVIF03		OBJECT-TYPE
			SYNTAX	INTEGER
			ACCESS	read-only
			STATUS	current
	DESCRIPTION ""
			::= { mbus7C 12 }

mbus7CValue03		OBJECT-TYPE
			SYNTAX	INTEGER
			ACCESS	read-only
			STATUS	current
	DESCRIPTION ""
			::= { mbus7C 13 }

mbus7CVIF04		OBJECT-TYPE
			SYNTAX	INTEGER
			ACCESS	read-only
			STATUS	current
	DESCRIPTION ""
			::= { mbus7C 14 }

mbus7CValue04		OBJECT-TYPE
			SYNTAX	INTEGER
			ACCESS	read-only
			STATUS	current
	DESCRIPTION ""
			::= { mbus7C 15 }

mbus7CVIF05		OBJECT-TYPE
			SYNTAX	INTEGER
			ACCESS	read-only
			STATUS	current
	DESCRIPTION ""
			::= { mbus7C 16 }

mbus7CValue05		OBJECT-TYPE
			SYNTAX	INTEGER
			ACCESS	read-only
			STATUS	current
	DESCRIPTION ""
			::= { mbus7C 17 }

mbus7CVIF06		OBJECT-TYPE
			SYNTAX	INTEGER
			ACCESS	read-only
			STATUS	current
	DESCRIPTION ""
			::= { mbus7C 18 }

mbus7CValue06		OBJECT-TYPE
			SYNTAX	INTEGER
			ACCESS	read-only
			STATUS	current
	DESCRIPTION ""
			::= { mbus7C 19 }

mbus7CVIF07		OBJECT-TYPE
			SYNTAX	INTEGER
			ACCESS	read-only
			STATUS	current
	DESCRIPTION ""
			::= { mbus7C 20 }

mbus7CValue07		OBJECT-TYPE
			SYNTAX	INTEGER
			ACCESS	read-only
			STATUS	current
	DESCRIPTION ""
			::= { mbus7C 21 }

mbus7CVIF08		OBJECT-TYPE
			SYNTAX	INTEGER
			ACCESS	read-only
			STATUS	current
	DESCRIPTION ""
			::= { mbus7C 22 }

mbus7CValue08		OBJECT-TYPE
			SYNTAX	INTEGER
			ACCESS	read-only
			STATUS	current
	DESCRIPTION ""
			::= { mbus7C 23 }

mbus7CVIF09		OBJECT-TYPE
			SYNTAX	INTEGER
			ACCESS	read-only
			STATUS	current
	DESCRIPTION ""
			::= { mbus7C 24 }

mbus7CValue09		OBJECT-TYPE
			SYNTAX	INTEGER
			ACCESS	read-only
			STATUS	current
	DESCRIPTION ""
			::= { mbus7C 25 }

mbus7CVIF0A		OBJECT-TYPE
			SYNTAX	INTEGER
			ACCESS	read-only
			STATUS	current
	DESCRIPTION ""
			::= { mbus7C 26 }

mbus7CValue0A		OBJECT-TYPE
			SYNTAX	INTEGER
			ACCESS	read-only
			STATUS	current
	DESCRIPTION ""
			::= { mbus7C 27 }

mbus7CVIF0B		OBJECT-TYPE
			SYNTAX	INTEGER
			ACCESS	read-only
			STATUS	current
	DESCRIPTION ""
			::= { mbus7C 28 }

mbus7CValue0B		OBJECT-TYPE
			SYNTAX	INTEGER
			ACCESS	read-only
			STATUS	current
	DESCRIPTION ""
			::= { mbus7C 29 }

mbus7CVIF0C		OBJECT-TYPE
			SYNTAX	INTEGER
			ACCESS	read-only
			STATUS	current
	DESCRIPTION ""
			::= { mbus7C 30 }

mbus7CValue0C		OBJECT-TYPE
			SYNTAX	INTEGER
			ACCESS	read-only
			STATUS	current
	DESCRIPTION ""
			::= { mbus7C 31 }

mbus7CVIF0D		OBJECT-TYPE
			SYNTAX	INTEGER
			ACCESS	read-only
			STATUS	current
	DESCRIPTION ""
			::= { mbus7C 32 }

mbus7CValue0D		OBJECT-TYPE
			SYNTAX	INTEGER
			ACCESS	read-only
			STATUS	current
	DESCRIPTION ""
			::= { mbus7C 33 }

mbus7CVIF0E		OBJECT-TYPE
			SYNTAX	INTEGER
			ACCESS	read-only
			STATUS	current
	DESCRIPTION ""
			::= { mbus7C 34 }

mbus7CValue0E		OBJECT-TYPE
			SYNTAX	INTEGER
			ACCESS	read-only
			STATUS	current
	DESCRIPTION ""
			::= { mbus7C 35 }

mbus7CVIF0F		OBJECT-TYPE
			SYNTAX	INTEGER
			ACCESS	read-only
			STATUS	current
	DESCRIPTION ""
			::= { mbus7C 36 }

mbus7CValue0F		OBJECT-TYPE
			SYNTAX	INTEGER
			ACCESS	read-only
			STATUS	current
	DESCRIPTION ""
			::= { mbus7C 37 }

mbus7CVIF10		OBJECT-TYPE
			SYNTAX	INTEGER
			ACCESS	read-only
			STATUS	current
	DESCRIPTION ""
			::= { mbus7C 38 }

mbus7CValue10		OBJECT-TYPE
			SYNTAX	INTEGER
			ACCESS	read-only
			STATUS	current
	DESCRIPTION ""
			::= { mbus7C 39 }

mbus7CVIF11		OBJECT-TYPE
			SYNTAX	INTEGER
			ACCESS	read-only
			STATUS	current
	DESCRIPTION ""
			::= { mbus7C 40 }

mbus7CValue11		OBJECT-TYPE
			SYNTAX	INTEGER
			ACCESS	read-only
			STATUS	current
	DESCRIPTION ""
			::= { mbus7C 41 }

mbus7CVIF12		OBJECT-TYPE
			SYNTAX	INTEGER
			ACCESS	read-only
			STATUS	current
	DESCRIPTION ""
			::= { mbus7C 42 }

mbus7CValue12		OBJECT-TYPE
			SYNTAX	INTEGER
			ACCESS	read-only
			STATUS	current
	DESCRIPTION ""
			::= { mbus7C 43 }

mbus7CVIF13		OBJECT-TYPE
			SYNTAX	INTEGER
			ACCESS	read-only
			STATUS	current
	DESCRIPTION ""
			::= { mbus7C 44 }

mbus7CValue13		OBJECT-TYPE
			SYNTAX	INTEGER
			ACCESS	read-only
			STATUS	current
	DESCRIPTION ""
			::= { mbus7C 45 }

mbus7CVIF14		OBJECT-TYPE
			SYNTAX	INTEGER
			ACCESS	read-only
			STATUS	current
	DESCRIPTION ""
			::= { mbus7C 46 }

mbus7CValue14		OBJECT-TYPE
			SYNTAX	INTEGER
			ACCESS	read-only
			STATUS	current
	DESCRIPTION ""
			::= { mbus7C 47 }

mbus7CVIF15		OBJECT-TYPE
			SYNTAX	INTEGER
			ACCESS	read-only
			STATUS	current
	DESCRIPTION ""
			::= { mbus7C 48 }

mbus7CValue15		OBJECT-TYPE
			SYNTAX	INTEGER
			ACCESS	read-only
			STATUS	current
	DESCRIPTION ""
			::= { mbus7C 49 }

mbus7CVIF16		OBJECT-TYPE
			SYNTAX	INTEGER
			ACCESS	read-only
			STATUS	current
	DESCRIPTION ""
			::= { mbus7C 50 }

mbus7CValue16		OBJECT-TYPE
			SYNTAX	INTEGER
			ACCESS	read-only
			STATUS	current
	DESCRIPTION ""
			::= { mbus7C 51 }

mbus7CVIF17		OBJECT-TYPE
			SYNTAX	INTEGER
			ACCESS	read-only
			STATUS	current
	DESCRIPTION ""
			::= { mbus7C 52 }

mbus7CValue17		OBJECT-TYPE
			SYNTAX	INTEGER
			ACCESS	read-only
			STATUS	current
	DESCRIPTION ""
			::= { mbus7C 53 }

mbus7CVIF18		OBJECT-TYPE
			SYNTAX	INTEGER
			ACCESS	read-only
			STATUS	current
	DESCRIPTION ""
			::= { mbus7C 54 }

mbus7CValue18		OBJECT-TYPE
			SYNTAX	INTEGER
			ACCESS	read-only
			STATUS	current
	DESCRIPTION ""
			::= { mbus7C 55 }

mbus7CVIF19		OBJECT-TYPE
			SYNTAX	INTEGER
			ACCESS	read-only
			STATUS	current
	DESCRIPTION ""
			::= { mbus7C 56 }

mbus7CValue19		OBJECT-TYPE
			SYNTAX	INTEGER
			ACCESS	read-only
			STATUS	current
	DESCRIPTION ""
			::= { mbus7C 57 }

mbus7CVIF1A		OBJECT-TYPE
			SYNTAX	INTEGER
			ACCESS	read-only
			STATUS	current
	DESCRIPTION ""
			::= { mbus7C 58 }

mbus7CValue1A		OBJECT-TYPE
			SYNTAX	INTEGER
			ACCESS	read-only
			STATUS	current
	DESCRIPTION ""
			::= { mbus7C 59 }

mbus7CVIF1B		OBJECT-TYPE
			SYNTAX	INTEGER
			ACCESS	read-only
			STATUS	current
	DESCRIPTION ""
			::= { mbus7C 60 }

mbus7CValue1B		OBJECT-TYPE
			SYNTAX	INTEGER
			ACCESS	read-only
			STATUS	current
	DESCRIPTION ""
			::= { mbus7C 61 }

mbus7CVIF1C		OBJECT-TYPE
			SYNTAX	INTEGER
			ACCESS	read-only
			STATUS	current
	DESCRIPTION ""
			::= { mbus7C 62 }

mbus7CValue1C		OBJECT-TYPE
			SYNTAX	INTEGER
			ACCESS	read-only
			STATUS	current
	DESCRIPTION ""
			::= { mbus7C 63 }

mbus7CVIF1D		OBJECT-TYPE
			SYNTAX	INTEGER
			ACCESS	read-only
			STATUS	current
	DESCRIPTION ""
			::= { mbus7C 64 }

mbus7CValue1D		OBJECT-TYPE
			SYNTAX	INTEGER
			ACCESS	read-only
			STATUS	current
	DESCRIPTION ""
			::= { mbus7C 65 }

mbus7CVIF1E		OBJECT-TYPE
			SYNTAX	INTEGER
			ACCESS	read-only
			STATUS	current
	DESCRIPTION ""
			::= { mbus7C 66 }

mbus7CValue1E		OBJECT-TYPE
			SYNTAX	INTEGER
			ACCESS	read-only
			STATUS	current
	DESCRIPTION ""
			::= { mbus7C 67 }

mbus7CVIF1F		OBJECT-TYPE
			SYNTAX	INTEGER
			ACCESS	read-only
			STATUS	current
	DESCRIPTION ""
			::= { mbus7C 68 }

mbus7CValue1F		OBJECT-TYPE
			SYNTAX	INTEGER
			ACCESS	read-only
			STATUS	current
	DESCRIPTION ""
			::= { mbus7C 69 }

mbus7CVIF20		OBJECT-TYPE
			SYNTAX	INTEGER
			ACCESS	read-only
			STATUS	current
	DESCRIPTION ""
			::= { mbus7C 70 }

mbus7CValue20		OBJECT-TYPE
			SYNTAX	INTEGER
			ACCESS	read-only
			STATUS	current
	DESCRIPTION ""
			::= { mbus7C 71 }

mbus7CVIF21		OBJECT-TYPE
			SYNTAX	INTEGER
			ACCESS	read-only
			STATUS	current
	DESCRIPTION ""
			::= { mbus7C 72 }

mbus7CValue21		OBJECT-TYPE
			SYNTAX	INTEGER
			ACCESS	read-only
			STATUS	current
	DESCRIPTION ""
			::= { mbus7C 73 }

mbus7CVIF22		OBJECT-TYPE
			SYNTAX	INTEGER
			ACCESS	read-only
			STATUS	current
	DESCRIPTION ""
			::= { mbus7C 74 }

mbus7CValue22		OBJECT-TYPE
			SYNTAX	INTEGER
			ACCESS	read-only
			STATUS	current
	DESCRIPTION ""
			::= { mbus7C 75 }

mbus7CVIF23		OBJECT-TYPE
			SYNTAX	INTEGER
			ACCESS	read-only
			STATUS	current
	DESCRIPTION ""
			::= { mbus7C 76 }

mbus7CValue23		OBJECT-TYPE
			SYNTAX	INTEGER
			ACCESS	read-only
			STATUS	current
	DESCRIPTION ""
			::= { mbus7C 77 }

mbus7CVIF24		OBJECT-TYPE
			SYNTAX	INTEGER
			ACCESS	read-only
			STATUS	current
	DESCRIPTION ""
			::= { mbus7C 78 }

mbus7CValue24		OBJECT-TYPE
			SYNTAX	INTEGER
			ACCESS	read-only
			STATUS	current
	DESCRIPTION ""
			::= { mbus7C 79 }

mbus7CVIF25		OBJECT-TYPE
			SYNTAX	INTEGER
			ACCESS	read-only
			STATUS	current
	DESCRIPTION ""
			::= { mbus7C 80 }

mbus7CValue25		OBJECT-TYPE
			SYNTAX	INTEGER
			ACCESS	read-only
			STATUS	current
	DESCRIPTION ""
			::= { mbus7C 81 }

mbus7CVIF26		OBJECT-TYPE
			SYNTAX	INTEGER
			ACCESS	read-only
			STATUS	current
	DESCRIPTION ""
			::= { mbus7C 82 }

mbus7CValue26		OBJECT-TYPE
			SYNTAX	INTEGER
			ACCESS	read-only
			STATUS	current
	DESCRIPTION ""
			::= { mbus7C 83 }

mbus7CVIF27		OBJECT-TYPE
			SYNTAX	INTEGER
			ACCESS	read-only
			STATUS	current
	DESCRIPTION ""
			::= { mbus7C 84 }

mbus7CValue27		OBJECT-TYPE
			SYNTAX	INTEGER
			ACCESS	read-only
			STATUS	current
	DESCRIPTION ""
			::= { mbus7C 85 }

mbus7CVIF28		OBJECT-TYPE
			SYNTAX	INTEGER
			ACCESS	read-only
			STATUS	current
	DESCRIPTION ""
			::= { mbus7C 86 }

mbus7CValue28		OBJECT-TYPE
			SYNTAX	INTEGER
			ACCESS	read-only
			STATUS	current
	DESCRIPTION ""
			::= { mbus7C 87 }

mbus7CVIF29		OBJECT-TYPE
			SYNTAX	INTEGER
			ACCESS	read-only
			STATUS	current
	DESCRIPTION ""
			::= { mbus7C 88 }

mbus7CValue29		OBJECT-TYPE
			SYNTAX	INTEGER
			ACCESS	read-only
			STATUS	current
	DESCRIPTION ""
			::= { mbus7C 89 }

mbus7CVIF2A		OBJECT-TYPE
			SYNTAX	INTEGER
			ACCESS	read-only
			STATUS	current
	DESCRIPTION ""
			::= { mbus7C 90 }

mbus7CValue2A		OBJECT-TYPE
			SYNTAX	INTEGER
			ACCESS	read-only
			STATUS	current
	DESCRIPTION ""
			::= { mbus7C 91 }

mbus7CVIF2B		OBJECT-TYPE
			SYNTAX	INTEGER
			ACCESS	read-only
			STATUS	current
	DESCRIPTION ""
			::= { mbus7C 92 }

mbus7CValue2B		OBJECT-TYPE
			SYNTAX	INTEGER
			ACCESS	read-only
			STATUS	current
	DESCRIPTION ""
			::= { mbus7C 93 }

mbus7CVIF2C		OBJECT-TYPE
			SYNTAX	INTEGER
			ACCESS	read-only
			STATUS	current
	DESCRIPTION ""
			::= { mbus7C 94 }

mbus7CValue2C		OBJECT-TYPE
			SYNTAX	INTEGER
			ACCESS	read-only
			STATUS	current
	DESCRIPTION ""
			::= { mbus7C 95 }

mbus7CVIF2D		OBJECT-TYPE
			SYNTAX	INTEGER
			ACCESS	read-only
			STATUS	current
	DESCRIPTION ""
			::= { mbus7C 96 }

mbus7CValue2D		OBJECT-TYPE
			SYNTAX	INTEGER
			ACCESS	read-only
			STATUS	current
	DESCRIPTION ""
			::= { mbus7C 97 }

mbus7CVIF2E		OBJECT-TYPE
			SYNTAX	INTEGER
			ACCESS	read-only
			STATUS	current
	DESCRIPTION ""
			::= { mbus7C 98 }

mbus7CValue2E		OBJECT-TYPE
			SYNTAX	INTEGER
			ACCESS	read-only
			STATUS	current
	DESCRIPTION ""
			::= { mbus7C 99 }

mbus7CVIF2F		OBJECT-TYPE
			SYNTAX	INTEGER
			ACCESS	read-only
			STATUS	current
	DESCRIPTION ""
			::= { mbus7C 100 }

mbus7CValue2F		OBJECT-TYPE
			SYNTAX	INTEGER
			ACCESS	read-only
			STATUS	current
	DESCRIPTION ""
			::= { mbus7C 101 }

mbus7D			OBJECT IDENTIFIER ::= { mbus 125 }

mbus7DIdNumber		OBJECT-TYPE
			SYNTAX	Gauge
			ACCESS	read-only
			STATUS	current
	DESCRIPTION ""
			::= { mbus7D 1 }

mbus7DManufacturer	OBJECT-TYPE
			SYNTAX	Gauge
			ACCESS	read-only
			STATUS	current
	DESCRIPTION ""
			::= { mbus7D 2 }

mbus7DVersion		OBJECT-TYPE
			SYNTAX	Gauge
			ACCESS	read-only
			STATUS	current
	DESCRIPTION ""
			::= { mbus7D 3 }

mbus7DMedium		OBJECT-TYPE
			SYNTAX	Gauge
			ACCESS	read-only
			STATUS	current
	DESCRIPTION ""
			::= { mbus7D 4 }

mbus7DStatus		OBJECT-TYPE
			SYNTAX	Gauge
			ACCESS	read-only
			STATUS	current
	DESCRIPTION ""
			::= { mbus7D 5 }

mbus7DVIF00		OBJECT-TYPE
			SYNTAX	INTEGER
			ACCESS	read-only
			STATUS	current
	DESCRIPTION ""
			::= { mbus7D 6 }

mbus7DValue00		OBJECT-TYPE
			SYNTAX	INTEGER
			ACCESS	read-only
			STATUS	current
	DESCRIPTION ""
			::= { mbus7D 7 }

mbus7DVIF01		OBJECT-TYPE
			SYNTAX	INTEGER
			ACCESS	read-only
			STATUS	current
	DESCRIPTION ""
			::= { mbus7D 8 }

mbus7DValue01		OBJECT-TYPE
			SYNTAX	INTEGER
			ACCESS	read-only
			STATUS	current
	DESCRIPTION ""
			::= { mbus7D 9 }

mbus7DVIF02		OBJECT-TYPE
			SYNTAX	INTEGER
			ACCESS	read-only
			STATUS	current
	DESCRIPTION ""
			::= { mbus7D 10 }

mbus7DValue02		OBJECT-TYPE
			SYNTAX	INTEGER
			ACCESS	read-only
			STATUS	current
	DESCRIPTION ""
			::= { mbus7D 11 }

mbus7DVIF03		OBJECT-TYPE
			SYNTAX	INTEGER
			ACCESS	read-only
			STATUS	current
	DESCRIPTION ""
			::= { mbus7D 12 }

mbus7DValue03		OBJECT-TYPE
			SYNTAX	INTEGER
			ACCESS	read-only
			STATUS	current
	DESCRIPTION ""
			::= { mbus7D 13 }

mbus7DVIF04		OBJECT-TYPE
			SYNTAX	INTEGER
			ACCESS	read-only
			STATUS	current
	DESCRIPTION ""
			::= { mbus7D 14 }

mbus7DValue04		OBJECT-TYPE
			SYNTAX	INTEGER
			ACCESS	read-only
			STATUS	current
	DESCRIPTION ""
			::= { mbus7D 15 }

mbus7DVIF05		OBJECT-TYPE
			SYNTAX	INTEGER
			ACCESS	read-only
			STATUS	current
	DESCRIPTION ""
			::= { mbus7D 16 }

mbus7DValue05		OBJECT-TYPE
			SYNTAX	INTEGER
			ACCESS	read-only
			STATUS	current
	DESCRIPTION ""
			::= { mbus7D 17 }

mbus7DVIF06		OBJECT-TYPE
			SYNTAX	INTEGER
			ACCESS	read-only
			STATUS	current
	DESCRIPTION ""
			::= { mbus7D 18 }

mbus7DValue06		OBJECT-TYPE
			SYNTAX	INTEGER
			ACCESS	read-only
			STATUS	current
	DESCRIPTION ""
			::= { mbus7D 19 }

mbus7DVIF07		OBJECT-TYPE
			SYNTAX	INTEGER
			ACCESS	read-only
			STATUS	current
	DESCRIPTION ""
			::= { mbus7D 20 }

mbus7DValue07		OBJECT-TYPE
			SYNTAX	INTEGER
			ACCESS	read-only
			STATUS	current
	DESCRIPTION ""
			::= { mbus7D 21 }

mbus7DVIF08		OBJECT-TYPE
			SYNTAX	INTEGER
			ACCESS	read-only
			STATUS	current
	DESCRIPTION ""
			::= { mbus7D 22 }

mbus7DValue08		OBJECT-TYPE
			SYNTAX	INTEGER
			ACCESS	read-only
			STATUS	current
	DESCRIPTION ""
			::= { mbus7D 23 }

mbus7DVIF09		OBJECT-TYPE
			SYNTAX	INTEGER
			ACCESS	read-only
			STATUS	current
	DESCRIPTION ""
			::= { mbus7D 24 }

mbus7DValue09		OBJECT-TYPE
			SYNTAX	INTEGER
			ACCESS	read-only
			STATUS	current
	DESCRIPTION ""
			::= { mbus7D 25 }

mbus7DVIF0A		OBJECT-TYPE
			SYNTAX	INTEGER
			ACCESS	read-only
			STATUS	current
	DESCRIPTION ""
			::= { mbus7D 26 }

mbus7DValue0A		OBJECT-TYPE
			SYNTAX	INTEGER
			ACCESS	read-only
			STATUS	current
	DESCRIPTION ""
			::= { mbus7D 27 }

mbus7DVIF0B		OBJECT-TYPE
			SYNTAX	INTEGER
			ACCESS	read-only
			STATUS	current
	DESCRIPTION ""
			::= { mbus7D 28 }

mbus7DValue0B		OBJECT-TYPE
			SYNTAX	INTEGER
			ACCESS	read-only
			STATUS	current
	DESCRIPTION ""
			::= { mbus7D 29 }

mbus7DVIF0C		OBJECT-TYPE
			SYNTAX	INTEGER
			ACCESS	read-only
			STATUS	current
	DESCRIPTION ""
			::= { mbus7D 30 }

mbus7DValue0C		OBJECT-TYPE
			SYNTAX	INTEGER
			ACCESS	read-only
			STATUS	current
	DESCRIPTION ""
			::= { mbus7D 31 }

mbus7DVIF0D		OBJECT-TYPE
			SYNTAX	INTEGER
			ACCESS	read-only
			STATUS	current
	DESCRIPTION ""
			::= { mbus7D 32 }

mbus7DValue0D		OBJECT-TYPE
			SYNTAX	INTEGER
			ACCESS	read-only
			STATUS	current
	DESCRIPTION ""
			::= { mbus7D 33 }

mbus7DVIF0E		OBJECT-TYPE
			SYNTAX	INTEGER
			ACCESS	read-only
			STATUS	current
	DESCRIPTION ""
			::= { mbus7D 34 }

mbus7DValue0E		OBJECT-TYPE
			SYNTAX	INTEGER
			ACCESS	read-only
			STATUS	current
	DESCRIPTION ""
			::= { mbus7D 35 }

mbus7DVIF0F		OBJECT-TYPE
			SYNTAX	INTEGER
			ACCESS	read-only
			STATUS	current
	DESCRIPTION ""
			::= { mbus7D 36 }

mbus7DValue0F		OBJECT-TYPE
			SYNTAX	INTEGER
			ACCESS	read-only
			STATUS	current
	DESCRIPTION ""
			::= { mbus7D 37 }

mbus7DVIF10		OBJECT-TYPE
			SYNTAX	INTEGER
			ACCESS	read-only
			STATUS	current
	DESCRIPTION ""
			::= { mbus7D 38 }

mbus7DValue10		OBJECT-TYPE
			SYNTAX	INTEGER
			ACCESS	read-only
			STATUS	current
	DESCRIPTION ""
			::= { mbus7D 39 }

mbus7DVIF11		OBJECT-TYPE
			SYNTAX	INTEGER
			ACCESS	read-only
			STATUS	current
	DESCRIPTION ""
			::= { mbus7D 40 }

mbus7DValue11		OBJECT-TYPE
			SYNTAX	INTEGER
			ACCESS	read-only
			STATUS	current
	DESCRIPTION ""
			::= { mbus7D 41 }

mbus7DVIF12		OBJECT-TYPE
			SYNTAX	INTEGER
			ACCESS	read-only
			STATUS	current
	DESCRIPTION ""
			::= { mbus7D 42 }

mbus7DValue12		OBJECT-TYPE
			SYNTAX	INTEGER
			ACCESS	read-only
			STATUS	current
	DESCRIPTION ""
			::= { mbus7D 43 }

mbus7DVIF13		OBJECT-TYPE
			SYNTAX	INTEGER
			ACCESS	read-only
			STATUS	current
	DESCRIPTION ""
			::= { mbus7D 44 }

mbus7DValue13		OBJECT-TYPE
			SYNTAX	INTEGER
			ACCESS	read-only
			STATUS	current
	DESCRIPTION ""
			::= { mbus7D 45 }

mbus7DVIF14		OBJECT-TYPE
			SYNTAX	INTEGER
			ACCESS	read-only
			STATUS	current
	DESCRIPTION ""
			::= { mbus7D 46 }

mbus7DValue14		OBJECT-TYPE
			SYNTAX	INTEGER
			ACCESS	read-only
			STATUS	current
	DESCRIPTION ""
			::= { mbus7D 47 }

mbus7DVIF15		OBJECT-TYPE
			SYNTAX	INTEGER
			ACCESS	read-only
			STATUS	current
	DESCRIPTION ""
			::= { mbus7D 48 }

mbus7DValue15		OBJECT-TYPE
			SYNTAX	INTEGER
			ACCESS	read-only
			STATUS	current
	DESCRIPTION ""
			::= { mbus7D 49 }

mbus7DVIF16		OBJECT-TYPE
			SYNTAX	INTEGER
			ACCESS	read-only
			STATUS	current
	DESCRIPTION ""
			::= { mbus7D 50 }

mbus7DValue16		OBJECT-TYPE
			SYNTAX	INTEGER
			ACCESS	read-only
			STATUS	current
	DESCRIPTION ""
			::= { mbus7D 51 }

mbus7DVIF17		OBJECT-TYPE
			SYNTAX	INTEGER
			ACCESS	read-only
			STATUS	current
	DESCRIPTION ""
			::= { mbus7D 52 }

mbus7DValue17		OBJECT-TYPE
			SYNTAX	INTEGER
			ACCESS	read-only
			STATUS	current
	DESCRIPTION ""
			::= { mbus7D 53 }

mbus7DVIF18		OBJECT-TYPE
			SYNTAX	INTEGER
			ACCESS	read-only
			STATUS	current
	DESCRIPTION ""
			::= { mbus7D 54 }

mbus7DValue18		OBJECT-TYPE
			SYNTAX	INTEGER
			ACCESS	read-only
			STATUS	current
	DESCRIPTION ""
			::= { mbus7D 55 }

mbus7DVIF19		OBJECT-TYPE
			SYNTAX	INTEGER
			ACCESS	read-only
			STATUS	current
	DESCRIPTION ""
			::= { mbus7D 56 }

mbus7DValue19		OBJECT-TYPE
			SYNTAX	INTEGER
			ACCESS	read-only
			STATUS	current
	DESCRIPTION ""
			::= { mbus7D 57 }

mbus7DVIF1A		OBJECT-TYPE
			SYNTAX	INTEGER
			ACCESS	read-only
			STATUS	current
	DESCRIPTION ""
			::= { mbus7D 58 }

mbus7DValue1A		OBJECT-TYPE
			SYNTAX	INTEGER
			ACCESS	read-only
			STATUS	current
	DESCRIPTION ""
			::= { mbus7D 59 }

mbus7DVIF1B		OBJECT-TYPE
			SYNTAX	INTEGER
			ACCESS	read-only
			STATUS	current
	DESCRIPTION ""
			::= { mbus7D 60 }

mbus7DValue1B		OBJECT-TYPE
			SYNTAX	INTEGER
			ACCESS	read-only
			STATUS	current
	DESCRIPTION ""
			::= { mbus7D 61 }

mbus7DVIF1C		OBJECT-TYPE
			SYNTAX	INTEGER
			ACCESS	read-only
			STATUS	current
	DESCRIPTION ""
			::= { mbus7D 62 }

mbus7DValue1C		OBJECT-TYPE
			SYNTAX	INTEGER
			ACCESS	read-only
			STATUS	current
	DESCRIPTION ""
			::= { mbus7D 63 }

mbus7DVIF1D		OBJECT-TYPE
			SYNTAX	INTEGER
			ACCESS	read-only
			STATUS	current
	DESCRIPTION ""
			::= { mbus7D 64 }

mbus7DValue1D		OBJECT-TYPE
			SYNTAX	INTEGER
			ACCESS	read-only
			STATUS	current
	DESCRIPTION ""
			::= { mbus7D 65 }

mbus7DVIF1E		OBJECT-TYPE
			SYNTAX	INTEGER
			ACCESS	read-only
			STATUS	current
	DESCRIPTION ""
			::= { mbus7D 66 }

mbus7DValue1E		OBJECT-TYPE
			SYNTAX	INTEGER
			ACCESS	read-only
			STATUS	current
	DESCRIPTION ""
			::= { mbus7D 67 }

mbus7DVIF1F		OBJECT-TYPE
			SYNTAX	INTEGER
			ACCESS	read-only
			STATUS	current
	DESCRIPTION ""
			::= { mbus7D 68 }

mbus7DValue1F		OBJECT-TYPE
			SYNTAX	INTEGER
			ACCESS	read-only
			STATUS	current
	DESCRIPTION ""
			::= { mbus7D 69 }

mbus7DVIF20		OBJECT-TYPE
			SYNTAX	INTEGER
			ACCESS	read-only
			STATUS	current
	DESCRIPTION ""
			::= { mbus7D 70 }

mbus7DValue20		OBJECT-TYPE
			SYNTAX	INTEGER
			ACCESS	read-only
			STATUS	current
	DESCRIPTION ""
			::= { mbus7D 71 }

mbus7DVIF21		OBJECT-TYPE
			SYNTAX	INTEGER
			ACCESS	read-only
			STATUS	current
	DESCRIPTION ""
			::= { mbus7D 72 }

mbus7DValue21		OBJECT-TYPE
			SYNTAX	INTEGER
			ACCESS	read-only
			STATUS	current
	DESCRIPTION ""
			::= { mbus7D 73 }

mbus7DVIF22		OBJECT-TYPE
			SYNTAX	INTEGER
			ACCESS	read-only
			STATUS	current
	DESCRIPTION ""
			::= { mbus7D 74 }

mbus7DValue22		OBJECT-TYPE
			SYNTAX	INTEGER
			ACCESS	read-only
			STATUS	current
	DESCRIPTION ""
			::= { mbus7D 75 }

mbus7DVIF23		OBJECT-TYPE
			SYNTAX	INTEGER
			ACCESS	read-only
			STATUS	current
	DESCRIPTION ""
			::= { mbus7D 76 }

mbus7DValue23		OBJECT-TYPE
			SYNTAX	INTEGER
			ACCESS	read-only
			STATUS	current
	DESCRIPTION ""
			::= { mbus7D 77 }

mbus7DVIF24		OBJECT-TYPE
			SYNTAX	INTEGER
			ACCESS	read-only
			STATUS	current
	DESCRIPTION ""
			::= { mbus7D 78 }

mbus7DValue24		OBJECT-TYPE
			SYNTAX	INTEGER
			ACCESS	read-only
			STATUS	current
	DESCRIPTION ""
			::= { mbus7D 79 }

mbus7DVIF25		OBJECT-TYPE
			SYNTAX	INTEGER
			ACCESS	read-only
			STATUS	current
	DESCRIPTION ""
			::= { mbus7D 80 }

mbus7DValue25		OBJECT-TYPE
			SYNTAX	INTEGER
			ACCESS	read-only
			STATUS	current
	DESCRIPTION ""
			::= { mbus7D 81 }

mbus7DVIF26		OBJECT-TYPE
			SYNTAX	INTEGER
			ACCESS	read-only
			STATUS	current
	DESCRIPTION ""
			::= { mbus7D 82 }

mbus7DValue26		OBJECT-TYPE
			SYNTAX	INTEGER
			ACCESS	read-only
			STATUS	current
	DESCRIPTION ""
			::= { mbus7D 83 }

mbus7DVIF27		OBJECT-TYPE
			SYNTAX	INTEGER
			ACCESS	read-only
			STATUS	current
	DESCRIPTION ""
			::= { mbus7D 84 }

mbus7DValue27		OBJECT-TYPE
			SYNTAX	INTEGER
			ACCESS	read-only
			STATUS	current
	DESCRIPTION ""
			::= { mbus7D 85 }

mbus7DVIF28		OBJECT-TYPE
			SYNTAX	INTEGER
			ACCESS	read-only
			STATUS	current
	DESCRIPTION ""
			::= { mbus7D 86 }

mbus7DValue28		OBJECT-TYPE
			SYNTAX	INTEGER
			ACCESS	read-only
			STATUS	current
	DESCRIPTION ""
			::= { mbus7D 87 }

mbus7DVIF29		OBJECT-TYPE
			SYNTAX	INTEGER
			ACCESS	read-only
			STATUS	current
	DESCRIPTION ""
			::= { mbus7D 88 }

mbus7DValue29		OBJECT-TYPE
			SYNTAX	INTEGER
			ACCESS	read-only
			STATUS	current
	DESCRIPTION ""
			::= { mbus7D 89 }

mbus7DVIF2A		OBJECT-TYPE
			SYNTAX	INTEGER
			ACCESS	read-only
			STATUS	current
	DESCRIPTION ""
			::= { mbus7D 90 }

mbus7DValue2A		OBJECT-TYPE
			SYNTAX	INTEGER
			ACCESS	read-only
			STATUS	current
	DESCRIPTION ""
			::= { mbus7D 91 }

mbus7DVIF2B		OBJECT-TYPE
			SYNTAX	INTEGER
			ACCESS	read-only
			STATUS	current
	DESCRIPTION ""
			::= { mbus7D 92 }

mbus7DValue2B		OBJECT-TYPE
			SYNTAX	INTEGER
			ACCESS	read-only
			STATUS	current
	DESCRIPTION ""
			::= { mbus7D 93 }

mbus7DVIF2C		OBJECT-TYPE
			SYNTAX	INTEGER
			ACCESS	read-only
			STATUS	current
	DESCRIPTION ""
			::= { mbus7D 94 }

mbus7DValue2C		OBJECT-TYPE
			SYNTAX	INTEGER
			ACCESS	read-only
			STATUS	current
	DESCRIPTION ""
			::= { mbus7D 95 }

mbus7DVIF2D		OBJECT-TYPE
			SYNTAX	INTEGER
			ACCESS	read-only
			STATUS	current
	DESCRIPTION ""
			::= { mbus7D 96 }

mbus7DValue2D		OBJECT-TYPE
			SYNTAX	INTEGER
			ACCESS	read-only
			STATUS	current
	DESCRIPTION ""
			::= { mbus7D 97 }

mbus7DVIF2E		OBJECT-TYPE
			SYNTAX	INTEGER
			ACCESS	read-only
			STATUS	current
	DESCRIPTION ""
			::= { mbus7D 98 }

mbus7DValue2E		OBJECT-TYPE
			SYNTAX	INTEGER
			ACCESS	read-only
			STATUS	current
	DESCRIPTION ""
			::= { mbus7D 99 }

mbus7DVIF2F		OBJECT-TYPE
			SYNTAX	INTEGER
			ACCESS	read-only
			STATUS	current
	DESCRIPTION ""
			::= { mbus7D 100 }

mbus7DValue2F		OBJECT-TYPE
			SYNTAX	INTEGER
			ACCESS	read-only
			STATUS	current
	DESCRIPTION ""
			::= { mbus7D 101 }

mbus7E			OBJECT IDENTIFIER ::= { mbus 126 }

mbus7EIdNumber		OBJECT-TYPE
			SYNTAX	Gauge
			ACCESS	read-only
			STATUS	current
	DESCRIPTION ""
			::= { mbus7E 1 }

mbus7EManufacturer	OBJECT-TYPE
			SYNTAX	Gauge
			ACCESS	read-only
			STATUS	current
	DESCRIPTION ""
			::= { mbus7E 2 }

mbus7EVersion		OBJECT-TYPE
			SYNTAX	Gauge
			ACCESS	read-only
			STATUS	current
	DESCRIPTION ""
			::= { mbus7E 3 }

mbus7EMedium		OBJECT-TYPE
			SYNTAX	Gauge
			ACCESS	read-only
			STATUS	current
	DESCRIPTION ""
			::= { mbus7E 4 }

mbus7EStatus		OBJECT-TYPE
			SYNTAX	Gauge
			ACCESS	read-only
			STATUS	current
	DESCRIPTION ""
			::= { mbus7E 5 }

mbus7EVIF00		OBJECT-TYPE
			SYNTAX	INTEGER
			ACCESS	read-only
			STATUS	current
	DESCRIPTION ""
			::= { mbus7E 6 }

mbus7EValue00		OBJECT-TYPE
			SYNTAX	INTEGER
			ACCESS	read-only
			STATUS	current
	DESCRIPTION ""
			::= { mbus7E 7 }

mbus7EVIF01		OBJECT-TYPE
			SYNTAX	INTEGER
			ACCESS	read-only
			STATUS	current
	DESCRIPTION ""
			::= { mbus7E 8 }

mbus7EValue01		OBJECT-TYPE
			SYNTAX	INTEGER
			ACCESS	read-only
			STATUS	current
	DESCRIPTION ""
			::= { mbus7E 9 }

mbus7EVIF02		OBJECT-TYPE
			SYNTAX	INTEGER
			ACCESS	read-only
			STATUS	current
	DESCRIPTION ""
			::= { mbus7E 10 }

mbus7EValue02		OBJECT-TYPE
			SYNTAX	INTEGER
			ACCESS	read-only
			STATUS	current
	DESCRIPTION ""
			::= { mbus7E 11 }

mbus7EVIF03		OBJECT-TYPE
			SYNTAX	INTEGER
			ACCESS	read-only
			STATUS	current
	DESCRIPTION ""
			::= { mbus7E 12 }

mbus7EValue03		OBJECT-TYPE
			SYNTAX	INTEGER
			ACCESS	read-only
			STATUS	current
	DESCRIPTION ""
			::= { mbus7E 13 }

mbus7EVIF04		OBJECT-TYPE
			SYNTAX	INTEGER
			ACCESS	read-only
			STATUS	current
	DESCRIPTION ""
			::= { mbus7E 14 }

mbus7EValue04		OBJECT-TYPE
			SYNTAX	INTEGER
			ACCESS	read-only
			STATUS	current
	DESCRIPTION ""
			::= { mbus7E 15 }

mbus7EVIF05		OBJECT-TYPE
			SYNTAX	INTEGER
			ACCESS	read-only
			STATUS	current
	DESCRIPTION ""
			::= { mbus7E 16 }

mbus7EValue05		OBJECT-TYPE
			SYNTAX	INTEGER
			ACCESS	read-only
			STATUS	current
	DESCRIPTION ""
			::= { mbus7E 17 }

mbus7EVIF06		OBJECT-TYPE
			SYNTAX	INTEGER
			ACCESS	read-only
			STATUS	current
	DESCRIPTION ""
			::= { mbus7E 18 }

mbus7EValue06		OBJECT-TYPE
			SYNTAX	INTEGER
			ACCESS	read-only
			STATUS	current
	DESCRIPTION ""
			::= { mbus7E 19 }

mbus7EVIF07		OBJECT-TYPE
			SYNTAX	INTEGER
			ACCESS	read-only
			STATUS	current
	DESCRIPTION ""
			::= { mbus7E 20 }

mbus7EValue07		OBJECT-TYPE
			SYNTAX	INTEGER
			ACCESS	read-only
			STATUS	current
	DESCRIPTION ""
			::= { mbus7E 21 }

mbus7EVIF08		OBJECT-TYPE
			SYNTAX	INTEGER
			ACCESS	read-only
			STATUS	current
	DESCRIPTION ""
			::= { mbus7E 22 }

mbus7EValue08		OBJECT-TYPE
			SYNTAX	INTEGER
			ACCESS	read-only
			STATUS	current
	DESCRIPTION ""
			::= { mbus7E 23 }

mbus7EVIF09		OBJECT-TYPE
			SYNTAX	INTEGER
			ACCESS	read-only
			STATUS	current
	DESCRIPTION ""
			::= { mbus7E 24 }

mbus7EValue09		OBJECT-TYPE
			SYNTAX	INTEGER
			ACCESS	read-only
			STATUS	current
	DESCRIPTION ""
			::= { mbus7E 25 }

mbus7EVIF0A		OBJECT-TYPE
			SYNTAX	INTEGER
			ACCESS	read-only
			STATUS	current
	DESCRIPTION ""
			::= { mbus7E 26 }

mbus7EValue0A		OBJECT-TYPE
			SYNTAX	INTEGER
			ACCESS	read-only
			STATUS	current
	DESCRIPTION ""
			::= { mbus7E 27 }

mbus7EVIF0B		OBJECT-TYPE
			SYNTAX	INTEGER
			ACCESS	read-only
			STATUS	current
	DESCRIPTION ""
			::= { mbus7E 28 }

mbus7EValue0B		OBJECT-TYPE
			SYNTAX	INTEGER
			ACCESS	read-only
			STATUS	current
	DESCRIPTION ""
			::= { mbus7E 29 }

mbus7EVIF0C		OBJECT-TYPE
			SYNTAX	INTEGER
			ACCESS	read-only
			STATUS	current
	DESCRIPTION ""
			::= { mbus7E 30 }

mbus7EValue0C		OBJECT-TYPE
			SYNTAX	INTEGER
			ACCESS	read-only
			STATUS	current
	DESCRIPTION ""
			::= { mbus7E 31 }

mbus7EVIF0D		OBJECT-TYPE
			SYNTAX	INTEGER
			ACCESS	read-only
			STATUS	current
	DESCRIPTION ""
			::= { mbus7E 32 }

mbus7EValue0D		OBJECT-TYPE
			SYNTAX	INTEGER
			ACCESS	read-only
			STATUS	current
	DESCRIPTION ""
			::= { mbus7E 33 }

mbus7EVIF0E		OBJECT-TYPE
			SYNTAX	INTEGER
			ACCESS	read-only
			STATUS	current
	DESCRIPTION ""
			::= { mbus7E 34 }

mbus7EValue0E		OBJECT-TYPE
			SYNTAX	INTEGER
			ACCESS	read-only
			STATUS	current
	DESCRIPTION ""
			::= { mbus7E 35 }

mbus7EVIF0F		OBJECT-TYPE
			SYNTAX	INTEGER
			ACCESS	read-only
			STATUS	current
	DESCRIPTION ""
			::= { mbus7E 36 }

mbus7EValue0F		OBJECT-TYPE
			SYNTAX	INTEGER
			ACCESS	read-only
			STATUS	current
	DESCRIPTION ""
			::= { mbus7E 37 }

mbus7EVIF10		OBJECT-TYPE
			SYNTAX	INTEGER
			ACCESS	read-only
			STATUS	current
	DESCRIPTION ""
			::= { mbus7E 38 }

mbus7EValue10		OBJECT-TYPE
			SYNTAX	INTEGER
			ACCESS	read-only
			STATUS	current
	DESCRIPTION ""
			::= { mbus7E 39 }

mbus7EVIF11		OBJECT-TYPE
			SYNTAX	INTEGER
			ACCESS	read-only
			STATUS	current
	DESCRIPTION ""
			::= { mbus7E 40 }

mbus7EValue11		OBJECT-TYPE
			SYNTAX	INTEGER
			ACCESS	read-only
			STATUS	current
	DESCRIPTION ""
			::= { mbus7E 41 }

mbus7EVIF12		OBJECT-TYPE
			SYNTAX	INTEGER
			ACCESS	read-only
			STATUS	current
	DESCRIPTION ""
			::= { mbus7E 42 }

mbus7EValue12		OBJECT-TYPE
			SYNTAX	INTEGER
			ACCESS	read-only
			STATUS	current
	DESCRIPTION ""
			::= { mbus7E 43 }

mbus7EVIF13		OBJECT-TYPE
			SYNTAX	INTEGER
			ACCESS	read-only
			STATUS	current
	DESCRIPTION ""
			::= { mbus7E 44 }

mbus7EValue13		OBJECT-TYPE
			SYNTAX	INTEGER
			ACCESS	read-only
			STATUS	current
	DESCRIPTION ""
			::= { mbus7E 45 }

mbus7EVIF14		OBJECT-TYPE
			SYNTAX	INTEGER
			ACCESS	read-only
			STATUS	current
	DESCRIPTION ""
			::= { mbus7E 46 }

mbus7EValue14		OBJECT-TYPE
			SYNTAX	INTEGER
			ACCESS	read-only
			STATUS	current
	DESCRIPTION ""
			::= { mbus7E 47 }

mbus7EVIF15		OBJECT-TYPE
			SYNTAX	INTEGER
			ACCESS	read-only
			STATUS	current
	DESCRIPTION ""
			::= { mbus7E 48 }

mbus7EValue15		OBJECT-TYPE
			SYNTAX	INTEGER
			ACCESS	read-only
			STATUS	current
	DESCRIPTION ""
			::= { mbus7E 49 }

mbus7EVIF16		OBJECT-TYPE
			SYNTAX	INTEGER
			ACCESS	read-only
			STATUS	current
	DESCRIPTION ""
			::= { mbus7E 50 }

mbus7EValue16		OBJECT-TYPE
			SYNTAX	INTEGER
			ACCESS	read-only
			STATUS	current
	DESCRIPTION ""
			::= { mbus7E 51 }

mbus7EVIF17		OBJECT-TYPE
			SYNTAX	INTEGER
			ACCESS	read-only
			STATUS	current
	DESCRIPTION ""
			::= { mbus7E 52 }

mbus7EValue17		OBJECT-TYPE
			SYNTAX	INTEGER
			ACCESS	read-only
			STATUS	current
	DESCRIPTION ""
			::= { mbus7E 53 }

mbus7EVIF18		OBJECT-TYPE
			SYNTAX	INTEGER
			ACCESS	read-only
			STATUS	current
	DESCRIPTION ""
			::= { mbus7E 54 }

mbus7EValue18		OBJECT-TYPE
			SYNTAX	INTEGER
			ACCESS	read-only
			STATUS	current
	DESCRIPTION ""
			::= { mbus7E 55 }

mbus7EVIF19		OBJECT-TYPE
			SYNTAX	INTEGER
			ACCESS	read-only
			STATUS	current
	DESCRIPTION ""
			::= { mbus7E 56 }

mbus7EValue19		OBJECT-TYPE
			SYNTAX	INTEGER
			ACCESS	read-only
			STATUS	current
	DESCRIPTION ""
			::= { mbus7E 57 }

mbus7EVIF1A		OBJECT-TYPE
			SYNTAX	INTEGER
			ACCESS	read-only
			STATUS	current
	DESCRIPTION ""
			::= { mbus7E 58 }

mbus7EValue1A		OBJECT-TYPE
			SYNTAX	INTEGER
			ACCESS	read-only
			STATUS	current
	DESCRIPTION ""
			::= { mbus7E 59 }

mbus7EVIF1B		OBJECT-TYPE
			SYNTAX	INTEGER
			ACCESS	read-only
			STATUS	current
	DESCRIPTION ""
			::= { mbus7E 60 }

mbus7EValue1B		OBJECT-TYPE
			SYNTAX	INTEGER
			ACCESS	read-only
			STATUS	current
	DESCRIPTION ""
			::= { mbus7E 61 }

mbus7EVIF1C		OBJECT-TYPE
			SYNTAX	INTEGER
			ACCESS	read-only
			STATUS	current
	DESCRIPTION ""
			::= { mbus7E 62 }

mbus7EValue1C		OBJECT-TYPE
			SYNTAX	INTEGER
			ACCESS	read-only
			STATUS	current
	DESCRIPTION ""
			::= { mbus7E 63 }

mbus7EVIF1D		OBJECT-TYPE
			SYNTAX	INTEGER
			ACCESS	read-only
			STATUS	current
	DESCRIPTION ""
			::= { mbus7E 64 }

mbus7EValue1D		OBJECT-TYPE
			SYNTAX	INTEGER
			ACCESS	read-only
			STATUS	current
	DESCRIPTION ""
			::= { mbus7E 65 }

mbus7EVIF1E		OBJECT-TYPE
			SYNTAX	INTEGER
			ACCESS	read-only
			STATUS	current
	DESCRIPTION ""
			::= { mbus7E 66 }

mbus7EValue1E		OBJECT-TYPE
			SYNTAX	INTEGER
			ACCESS	read-only
			STATUS	current
	DESCRIPTION ""
			::= { mbus7E 67 }

mbus7EVIF1F		OBJECT-TYPE
			SYNTAX	INTEGER
			ACCESS	read-only
			STATUS	current
	DESCRIPTION ""
			::= { mbus7E 68 }

mbus7EValue1F		OBJECT-TYPE
			SYNTAX	INTEGER
			ACCESS	read-only
			STATUS	current
	DESCRIPTION ""
			::= { mbus7E 69 }

mbus7EVIF20		OBJECT-TYPE
			SYNTAX	INTEGER
			ACCESS	read-only
			STATUS	current
	DESCRIPTION ""
			::= { mbus7E 70 }

mbus7EValue20		OBJECT-TYPE
			SYNTAX	INTEGER
			ACCESS	read-only
			STATUS	current
	DESCRIPTION ""
			::= { mbus7E 71 }

mbus7EVIF21		OBJECT-TYPE
			SYNTAX	INTEGER
			ACCESS	read-only
			STATUS	current
	DESCRIPTION ""
			::= { mbus7E 72 }

mbus7EValue21		OBJECT-TYPE
			SYNTAX	INTEGER
			ACCESS	read-only
			STATUS	current
	DESCRIPTION ""
			::= { mbus7E 73 }

mbus7EVIF22		OBJECT-TYPE
			SYNTAX	INTEGER
			ACCESS	read-only
			STATUS	current
	DESCRIPTION ""
			::= { mbus7E 74 }

mbus7EValue22		OBJECT-TYPE
			SYNTAX	INTEGER
			ACCESS	read-only
			STATUS	current
	DESCRIPTION ""
			::= { mbus7E 75 }

mbus7EVIF23		OBJECT-TYPE
			SYNTAX	INTEGER
			ACCESS	read-only
			STATUS	current
	DESCRIPTION ""
			::= { mbus7E 76 }

mbus7EValue23		OBJECT-TYPE
			SYNTAX	INTEGER
			ACCESS	read-only
			STATUS	current
	DESCRIPTION ""
			::= { mbus7E 77 }

mbus7EVIF24		OBJECT-TYPE
			SYNTAX	INTEGER
			ACCESS	read-only
			STATUS	current
	DESCRIPTION ""
			::= { mbus7E 78 }

mbus7EValue24		OBJECT-TYPE
			SYNTAX	INTEGER
			ACCESS	read-only
			STATUS	current
	DESCRIPTION ""
			::= { mbus7E 79 }

mbus7EVIF25		OBJECT-TYPE
			SYNTAX	INTEGER
			ACCESS	read-only
			STATUS	current
	DESCRIPTION ""
			::= { mbus7E 80 }

mbus7EValue25		OBJECT-TYPE
			SYNTAX	INTEGER
			ACCESS	read-only
			STATUS	current
	DESCRIPTION ""
			::= { mbus7E 81 }

mbus7EVIF26		OBJECT-TYPE
			SYNTAX	INTEGER
			ACCESS	read-only
			STATUS	current
	DESCRIPTION ""
			::= { mbus7E 82 }

mbus7EValue26		OBJECT-TYPE
			SYNTAX	INTEGER
			ACCESS	read-only
			STATUS	current
	DESCRIPTION ""
			::= { mbus7E 83 }

mbus7EVIF27		OBJECT-TYPE
			SYNTAX	INTEGER
			ACCESS	read-only
			STATUS	current
	DESCRIPTION ""
			::= { mbus7E 84 }

mbus7EValue27		OBJECT-TYPE
			SYNTAX	INTEGER
			ACCESS	read-only
			STATUS	current
	DESCRIPTION ""
			::= { mbus7E 85 }

mbus7EVIF28		OBJECT-TYPE
			SYNTAX	INTEGER
			ACCESS	read-only
			STATUS	current
	DESCRIPTION ""
			::= { mbus7E 86 }

mbus7EValue28		OBJECT-TYPE
			SYNTAX	INTEGER
			ACCESS	read-only
			STATUS	current
	DESCRIPTION ""
			::= { mbus7E 87 }

mbus7EVIF29		OBJECT-TYPE
			SYNTAX	INTEGER
			ACCESS	read-only
			STATUS	current
	DESCRIPTION ""
			::= { mbus7E 88 }

mbus7EValue29		OBJECT-TYPE
			SYNTAX	INTEGER
			ACCESS	read-only
			STATUS	current
	DESCRIPTION ""
			::= { mbus7E 89 }

mbus7EVIF2A		OBJECT-TYPE
			SYNTAX	INTEGER
			ACCESS	read-only
			STATUS	current
	DESCRIPTION ""
			::= { mbus7E 90 }

mbus7EValue2A		OBJECT-TYPE
			SYNTAX	INTEGER
			ACCESS	read-only
			STATUS	current
	DESCRIPTION ""
			::= { mbus7E 91 }

mbus7EVIF2B		OBJECT-TYPE
			SYNTAX	INTEGER
			ACCESS	read-only
			STATUS	current
	DESCRIPTION ""
			::= { mbus7E 92 }

mbus7EValue2B		OBJECT-TYPE
			SYNTAX	INTEGER
			ACCESS	read-only
			STATUS	current
	DESCRIPTION ""
			::= { mbus7E 93 }

mbus7EVIF2C		OBJECT-TYPE
			SYNTAX	INTEGER
			ACCESS	read-only
			STATUS	current
	DESCRIPTION ""
			::= { mbus7E 94 }

mbus7EValue2C		OBJECT-TYPE
			SYNTAX	INTEGER
			ACCESS	read-only
			STATUS	current
	DESCRIPTION ""
			::= { mbus7E 95 }

mbus7EVIF2D		OBJECT-TYPE
			SYNTAX	INTEGER
			ACCESS	read-only
			STATUS	current
	DESCRIPTION ""
			::= { mbus7E 96 }

mbus7EValue2D		OBJECT-TYPE
			SYNTAX	INTEGER
			ACCESS	read-only
			STATUS	current
	DESCRIPTION ""
			::= { mbus7E 97 }

mbus7EVIF2E		OBJECT-TYPE
			SYNTAX	INTEGER
			ACCESS	read-only
			STATUS	current
	DESCRIPTION ""
			::= { mbus7E 98 }

mbus7EValue2E		OBJECT-TYPE
			SYNTAX	INTEGER
			ACCESS	read-only
			STATUS	current
	DESCRIPTION ""
			::= { mbus7E 99 }

mbus7EVIF2F		OBJECT-TYPE
			SYNTAX	INTEGER
			ACCESS	read-only
			STATUS	current
	DESCRIPTION ""
			::= { mbus7E 100 }

mbus7EValue2F		OBJECT-TYPE
			SYNTAX	INTEGER
			ACCESS	read-only
			STATUS	current
	DESCRIPTION ""
			::= { mbus7E 101 }

mbus7F			OBJECT IDENTIFIER ::= { mbus 127 }

mbus7FIdNumber		OBJECT-TYPE
			SYNTAX	Gauge
			ACCESS	read-only
			STATUS	current
	DESCRIPTION ""
			::= { mbus7F 1 }

mbus7FManufacturer	OBJECT-TYPE
			SYNTAX	Gauge
			ACCESS	read-only
			STATUS	current
	DESCRIPTION ""
			::= { mbus7F 2 }

mbus7FVersion		OBJECT-TYPE
			SYNTAX	Gauge
			ACCESS	read-only
			STATUS	current
	DESCRIPTION ""
			::= { mbus7F 3 }

mbus7FMedium		OBJECT-TYPE
			SYNTAX	Gauge
			ACCESS	read-only
			STATUS	current
	DESCRIPTION ""
			::= { mbus7F 4 }

mbus7FStatus		OBJECT-TYPE
			SYNTAX	Gauge
			ACCESS	read-only
			STATUS	current
	DESCRIPTION ""
			::= { mbus7F 5 }

mbus7FVIF00		OBJECT-TYPE
			SYNTAX	INTEGER
			ACCESS	read-only
			STATUS	current
	DESCRIPTION ""
			::= { mbus7F 6 }

mbus7FValue00		OBJECT-TYPE
			SYNTAX	INTEGER
			ACCESS	read-only
			STATUS	current
	DESCRIPTION ""
			::= { mbus7F 7 }

mbus7FVIF01		OBJECT-TYPE
			SYNTAX	INTEGER
			ACCESS	read-only
			STATUS	current
	DESCRIPTION ""
			::= { mbus7F 8 }

mbus7FValue01		OBJECT-TYPE
			SYNTAX	INTEGER
			ACCESS	read-only
			STATUS	current
	DESCRIPTION ""
			::= { mbus7F 9 }

mbus7FVIF02		OBJECT-TYPE
			SYNTAX	INTEGER
			ACCESS	read-only
			STATUS	current
	DESCRIPTION ""
			::= { mbus7F 10 }

mbus7FValue02		OBJECT-TYPE
			SYNTAX	INTEGER
			ACCESS	read-only
			STATUS	current
	DESCRIPTION ""
			::= { mbus7F 11 }

mbus7FVIF03		OBJECT-TYPE
			SYNTAX	INTEGER
			ACCESS	read-only
			STATUS	current
	DESCRIPTION ""
			::= { mbus7F 12 }

mbus7FValue03		OBJECT-TYPE
			SYNTAX	INTEGER
			ACCESS	read-only
			STATUS	current
	DESCRIPTION ""
			::= { mbus7F 13 }

mbus7FVIF04		OBJECT-TYPE
			SYNTAX	INTEGER
			ACCESS	read-only
			STATUS	current
	DESCRIPTION ""
			::= { mbus7F 14 }

mbus7FValue04		OBJECT-TYPE
			SYNTAX	INTEGER
			ACCESS	read-only
			STATUS	current
	DESCRIPTION ""
			::= { mbus7F 15 }

mbus7FVIF05		OBJECT-TYPE
			SYNTAX	INTEGER
			ACCESS	read-only
			STATUS	current
	DESCRIPTION ""
			::= { mbus7F 16 }

mbus7FValue05		OBJECT-TYPE
			SYNTAX	INTEGER
			ACCESS	read-only
			STATUS	current
	DESCRIPTION ""
			::= { mbus7F 17 }

mbus7FVIF06		OBJECT-TYPE
			SYNTAX	INTEGER
			ACCESS	read-only
			STATUS	current
	DESCRIPTION ""
			::= { mbus7F 18 }

mbus7FValue06		OBJECT-TYPE
			SYNTAX	INTEGER
			ACCESS	read-only
			STATUS	current
	DESCRIPTION ""
			::= { mbus7F 19 }

mbus7FVIF07		OBJECT-TYPE
			SYNTAX	INTEGER
			ACCESS	read-only
			STATUS	current
	DESCRIPTION ""
			::= { mbus7F 20 }

mbus7FValue07		OBJECT-TYPE
			SYNTAX	INTEGER
			ACCESS	read-only
			STATUS	current
	DESCRIPTION ""
			::= { mbus7F 21 }

mbus7FVIF08		OBJECT-TYPE
			SYNTAX	INTEGER
			ACCESS	read-only
			STATUS	current
	DESCRIPTION ""
			::= { mbus7F 22 }

mbus7FValue08		OBJECT-TYPE
			SYNTAX	INTEGER
			ACCESS	read-only
			STATUS	current
	DESCRIPTION ""
			::= { mbus7F 23 }

mbus7FVIF09		OBJECT-TYPE
			SYNTAX	INTEGER
			ACCESS	read-only
			STATUS	current
	DESCRIPTION ""
			::= { mbus7F 24 }

mbus7FValue09		OBJECT-TYPE
			SYNTAX	INTEGER
			ACCESS	read-only
			STATUS	current
	DESCRIPTION ""
			::= { mbus7F 25 }

mbus7FVIF0A		OBJECT-TYPE
			SYNTAX	INTEGER
			ACCESS	read-only
			STATUS	current
	DESCRIPTION ""
			::= { mbus7F 26 }

mbus7FValue0A		OBJECT-TYPE
			SYNTAX	INTEGER
			ACCESS	read-only
			STATUS	current
	DESCRIPTION ""
			::= { mbus7F 27 }

mbus7FVIF0B		OBJECT-TYPE
			SYNTAX	INTEGER
			ACCESS	read-only
			STATUS	current
	DESCRIPTION ""
			::= { mbus7F 28 }

mbus7FValue0B		OBJECT-TYPE
			SYNTAX	INTEGER
			ACCESS	read-only
			STATUS	current
	DESCRIPTION ""
			::= { mbus7F 29 }

mbus7FVIF0C		OBJECT-TYPE
			SYNTAX	INTEGER
			ACCESS	read-only
			STATUS	current
	DESCRIPTION ""
			::= { mbus7F 30 }

mbus7FValue0C		OBJECT-TYPE
			SYNTAX	INTEGER
			ACCESS	read-only
			STATUS	current
	DESCRIPTION ""
			::= { mbus7F 31 }

mbus7FVIF0D		OBJECT-TYPE
			SYNTAX	INTEGER
			ACCESS	read-only
			STATUS	current
	DESCRIPTION ""
			::= { mbus7F 32 }

mbus7FValue0D		OBJECT-TYPE
			SYNTAX	INTEGER
			ACCESS	read-only
			STATUS	current
	DESCRIPTION ""
			::= { mbus7F 33 }

mbus7FVIF0E		OBJECT-TYPE
			SYNTAX	INTEGER
			ACCESS	read-only
			STATUS	current
	DESCRIPTION ""
			::= { mbus7F 34 }

mbus7FValue0E		OBJECT-TYPE
			SYNTAX	INTEGER
			ACCESS	read-only
			STATUS	current
	DESCRIPTION ""
			::= { mbus7F 35 }

mbus7FVIF0F		OBJECT-TYPE
			SYNTAX	INTEGER
			ACCESS	read-only
			STATUS	current
	DESCRIPTION ""
			::= { mbus7F 36 }

mbus7FValue0F		OBJECT-TYPE
			SYNTAX	INTEGER
			ACCESS	read-only
			STATUS	current
	DESCRIPTION ""
			::= { mbus7F 37 }

mbus7FVIF10		OBJECT-TYPE
			SYNTAX	INTEGER
			ACCESS	read-only
			STATUS	current
	DESCRIPTION ""
			::= { mbus7F 38 }

mbus7FValue10		OBJECT-TYPE
			SYNTAX	INTEGER
			ACCESS	read-only
			STATUS	current
	DESCRIPTION ""
			::= { mbus7F 39 }

mbus7FVIF11		OBJECT-TYPE
			SYNTAX	INTEGER
			ACCESS	read-only
			STATUS	current
	DESCRIPTION ""
			::= { mbus7F 40 }

mbus7FValue11		OBJECT-TYPE
			SYNTAX	INTEGER
			ACCESS	read-only
			STATUS	current
	DESCRIPTION ""
			::= { mbus7F 41 }

mbus7FVIF12		OBJECT-TYPE
			SYNTAX	INTEGER
			ACCESS	read-only
			STATUS	current
	DESCRIPTION ""
			::= { mbus7F 42 }

mbus7FValue12		OBJECT-TYPE
			SYNTAX	INTEGER
			ACCESS	read-only
			STATUS	current
	DESCRIPTION ""
			::= { mbus7F 43 }

mbus7FVIF13		OBJECT-TYPE
			SYNTAX	INTEGER
			ACCESS	read-only
			STATUS	current
	DESCRIPTION ""
			::= { mbus7F 44 }

mbus7FValue13		OBJECT-TYPE
			SYNTAX	INTEGER
			ACCESS	read-only
			STATUS	current
	DESCRIPTION ""
			::= { mbus7F 45 }

mbus7FVIF14		OBJECT-TYPE
			SYNTAX	INTEGER
			ACCESS	read-only
			STATUS	current
	DESCRIPTION ""
			::= { mbus7F 46 }

mbus7FValue14		OBJECT-TYPE
			SYNTAX	INTEGER
			ACCESS	read-only
			STATUS	current
	DESCRIPTION ""
			::= { mbus7F 47 }

mbus7FVIF15		OBJECT-TYPE
			SYNTAX	INTEGER
			ACCESS	read-only
			STATUS	current
	DESCRIPTION ""
			::= { mbus7F 48 }

mbus7FValue15		OBJECT-TYPE
			SYNTAX	INTEGER
			ACCESS	read-only
			STATUS	current
	DESCRIPTION ""
			::= { mbus7F 49 }

mbus7FVIF16		OBJECT-TYPE
			SYNTAX	INTEGER
			ACCESS	read-only
			STATUS	current
	DESCRIPTION ""
			::= { mbus7F 50 }

mbus7FValue16		OBJECT-TYPE
			SYNTAX	INTEGER
			ACCESS	read-only
			STATUS	current
	DESCRIPTION ""
			::= { mbus7F 51 }

mbus7FVIF17		OBJECT-TYPE
			SYNTAX	INTEGER
			ACCESS	read-only
			STATUS	current
	DESCRIPTION ""
			::= { mbus7F 52 }

mbus7FValue17		OBJECT-TYPE
			SYNTAX	INTEGER
			ACCESS	read-only
			STATUS	current
	DESCRIPTION ""
			::= { mbus7F 53 }

mbus7FVIF18		OBJECT-TYPE
			SYNTAX	INTEGER
			ACCESS	read-only
			STATUS	current
	DESCRIPTION ""
			::= { mbus7F 54 }

mbus7FValue18		OBJECT-TYPE
			SYNTAX	INTEGER
			ACCESS	read-only
			STATUS	current
	DESCRIPTION ""
			::= { mbus7F 55 }

mbus7FVIF19		OBJECT-TYPE
			SYNTAX	INTEGER
			ACCESS	read-only
			STATUS	current
	DESCRIPTION ""
			::= { mbus7F 56 }

mbus7FValue19		OBJECT-TYPE
			SYNTAX	INTEGER
			ACCESS	read-only
			STATUS	current
	DESCRIPTION ""
			::= { mbus7F 57 }

mbus7FVIF1A		OBJECT-TYPE
			SYNTAX	INTEGER
			ACCESS	read-only
			STATUS	current
	DESCRIPTION ""
			::= { mbus7F 58 }

mbus7FValue1A		OBJECT-TYPE
			SYNTAX	INTEGER
			ACCESS	read-only
			STATUS	current
	DESCRIPTION ""
			::= { mbus7F 59 }

mbus7FVIF1B		OBJECT-TYPE
			SYNTAX	INTEGER
			ACCESS	read-only
			STATUS	current
	DESCRIPTION ""
			::= { mbus7F 60 }

mbus7FValue1B		OBJECT-TYPE
			SYNTAX	INTEGER
			ACCESS	read-only
			STATUS	current
	DESCRIPTION ""
			::= { mbus7F 61 }

mbus7FVIF1C		OBJECT-TYPE
			SYNTAX	INTEGER
			ACCESS	read-only
			STATUS	current
	DESCRIPTION ""
			::= { mbus7F 62 }

mbus7FValue1C		OBJECT-TYPE
			SYNTAX	INTEGER
			ACCESS	read-only
			STATUS	current
	DESCRIPTION ""
			::= { mbus7F 63 }

mbus7FVIF1D		OBJECT-TYPE
			SYNTAX	INTEGER
			ACCESS	read-only
			STATUS	current
	DESCRIPTION ""
			::= { mbus7F 64 }

mbus7FValue1D		OBJECT-TYPE
			SYNTAX	INTEGER
			ACCESS	read-only
			STATUS	current
	DESCRIPTION ""
			::= { mbus7F 65 }

mbus7FVIF1E		OBJECT-TYPE
			SYNTAX	INTEGER
			ACCESS	read-only
			STATUS	current
	DESCRIPTION ""
			::= { mbus7F 66 }

mbus7FValue1E		OBJECT-TYPE
			SYNTAX	INTEGER
			ACCESS	read-only
			STATUS	current
	DESCRIPTION ""
			::= { mbus7F 67 }

mbus7FVIF1F		OBJECT-TYPE
			SYNTAX	INTEGER
			ACCESS	read-only
			STATUS	current
	DESCRIPTION ""
			::= { mbus7F 68 }

mbus7FValue1F		OBJECT-TYPE
			SYNTAX	INTEGER
			ACCESS	read-only
			STATUS	current
	DESCRIPTION ""
			::= { mbus7F 69 }

mbus7FVIF20		OBJECT-TYPE
			SYNTAX	INTEGER
			ACCESS	read-only
			STATUS	current
	DESCRIPTION ""
			::= { mbus7F 70 }

mbus7FValue20		OBJECT-TYPE
			SYNTAX	INTEGER
			ACCESS	read-only
			STATUS	current
	DESCRIPTION ""
			::= { mbus7F 71 }

mbus7FVIF21		OBJECT-TYPE
			SYNTAX	INTEGER
			ACCESS	read-only
			STATUS	current
	DESCRIPTION ""
			::= { mbus7F 72 }

mbus7FValue21		OBJECT-TYPE
			SYNTAX	INTEGER
			ACCESS	read-only
			STATUS	current
	DESCRIPTION ""
			::= { mbus7F 73 }

mbus7FVIF22		OBJECT-TYPE
			SYNTAX	INTEGER
			ACCESS	read-only
			STATUS	current
	DESCRIPTION ""
			::= { mbus7F 74 }

mbus7FValue22		OBJECT-TYPE
			SYNTAX	INTEGER
			ACCESS	read-only
			STATUS	current
	DESCRIPTION ""
			::= { mbus7F 75 }

mbus7FVIF23		OBJECT-TYPE
			SYNTAX	INTEGER
			ACCESS	read-only
			STATUS	current
	DESCRIPTION ""
			::= { mbus7F 76 }

mbus7FValue23		OBJECT-TYPE
			SYNTAX	INTEGER
			ACCESS	read-only
			STATUS	current
	DESCRIPTION ""
			::= { mbus7F 77 }

mbus7FVIF24		OBJECT-TYPE
			SYNTAX	INTEGER
			ACCESS	read-only
			STATUS	current
	DESCRIPTION ""
			::= { mbus7F 78 }

mbus7FValue24		OBJECT-TYPE
			SYNTAX	INTEGER
			ACCESS	read-only
			STATUS	current
	DESCRIPTION ""
			::= { mbus7F 79 }

mbus7FVIF25		OBJECT-TYPE
			SYNTAX	INTEGER
			ACCESS	read-only
			STATUS	current
	DESCRIPTION ""
			::= { mbus7F 80 }

mbus7FValue25		OBJECT-TYPE
			SYNTAX	INTEGER
			ACCESS	read-only
			STATUS	current
	DESCRIPTION ""
			::= { mbus7F 81 }

mbus7FVIF26		OBJECT-TYPE
			SYNTAX	INTEGER
			ACCESS	read-only
			STATUS	current
	DESCRIPTION ""
			::= { mbus7F 82 }

mbus7FValue26		OBJECT-TYPE
			SYNTAX	INTEGER
			ACCESS	read-only
			STATUS	current
	DESCRIPTION ""
			::= { mbus7F 83 }

mbus7FVIF27		OBJECT-TYPE
			SYNTAX	INTEGER
			ACCESS	read-only
			STATUS	current
	DESCRIPTION ""
			::= { mbus7F 84 }

mbus7FValue27		OBJECT-TYPE
			SYNTAX	INTEGER
			ACCESS	read-only
			STATUS	current
	DESCRIPTION ""
			::= { mbus7F 85 }

mbus7FVIF28		OBJECT-TYPE
			SYNTAX	INTEGER
			ACCESS	read-only
			STATUS	current
	DESCRIPTION ""
			::= { mbus7F 86 }

mbus7FValue28		OBJECT-TYPE
			SYNTAX	INTEGER
			ACCESS	read-only
			STATUS	current
	DESCRIPTION ""
			::= { mbus7F 87 }

mbus7FVIF29		OBJECT-TYPE
			SYNTAX	INTEGER
			ACCESS	read-only
			STATUS	current
	DESCRIPTION ""
			::= { mbus7F 88 }

mbus7FValue29		OBJECT-TYPE
			SYNTAX	INTEGER
			ACCESS	read-only
			STATUS	current
	DESCRIPTION ""
			::= { mbus7F 89 }

mbus7FVIF2A		OBJECT-TYPE
			SYNTAX	INTEGER
			ACCESS	read-only
			STATUS	current
	DESCRIPTION ""
			::= { mbus7F 90 }

mbus7FValue2A		OBJECT-TYPE
			SYNTAX	INTEGER
			ACCESS	read-only
			STATUS	current
	DESCRIPTION ""
			::= { mbus7F 91 }

mbus7FVIF2B		OBJECT-TYPE
			SYNTAX	INTEGER
			ACCESS	read-only
			STATUS	current
	DESCRIPTION ""
			::= { mbus7F 92 }

mbus7FValue2B		OBJECT-TYPE
			SYNTAX	INTEGER
			ACCESS	read-only
			STATUS	current
	DESCRIPTION ""
			::= { mbus7F 93 }

mbus7FVIF2C		OBJECT-TYPE
			SYNTAX	INTEGER
			ACCESS	read-only
			STATUS	current
	DESCRIPTION ""
			::= { mbus7F 94 }

mbus7FValue2C		OBJECT-TYPE
			SYNTAX	INTEGER
			ACCESS	read-only
			STATUS	current
	DESCRIPTION ""
			::= { mbus7F 95 }

mbus7FVIF2D		OBJECT-TYPE
			SYNTAX	INTEGER
			ACCESS	read-only
			STATUS	current
	DESCRIPTION ""
			::= { mbus7F 96 }

mbus7FValue2D		OBJECT-TYPE
			SYNTAX	INTEGER
			ACCESS	read-only
			STATUS	current
	DESCRIPTION ""
			::= { mbus7F 97 }

mbus7FVIF2E		OBJECT-TYPE
			SYNTAX	INTEGER
			ACCESS	read-only
			STATUS	current
	DESCRIPTION ""
			::= { mbus7F 98 }

mbus7FValue2E		OBJECT-TYPE
			SYNTAX	INTEGER
			ACCESS	read-only
			STATUS	current
	DESCRIPTION ""
			::= { mbus7F 99 }

mbus7FVIF2F		OBJECT-TYPE
			SYNTAX	INTEGER
			ACCESS	read-only
			STATUS	current
	DESCRIPTION ""
			::= { mbus7F 100 }

mbus7FValue2F		OBJECT-TYPE
			SYNTAX	INTEGER
			ACCESS	read-only
			STATUS	current
	DESCRIPTION ""
			::= { mbus7F 101 }

mbus80			OBJECT IDENTIFIER ::= { mbus 128 }

mbus80IdNumber		OBJECT-TYPE
			SYNTAX	Gauge
			ACCESS	read-only
			STATUS	current
	DESCRIPTION ""
			::= { mbus80 1 }

mbus80Manufacturer	OBJECT-TYPE
			SYNTAX	Gauge
			ACCESS	read-only
			STATUS	current
	DESCRIPTION ""
			::= { mbus80 2 }

mbus80Version		OBJECT-TYPE
			SYNTAX	Gauge
			ACCESS	read-only
			STATUS	current
	DESCRIPTION ""
			::= { mbus80 3 }

mbus80Medium		OBJECT-TYPE
			SYNTAX	Gauge
			ACCESS	read-only
			STATUS	current
	DESCRIPTION ""
			::= { mbus80 4 }

mbus80Status		OBJECT-TYPE
			SYNTAX	Gauge
			ACCESS	read-only
			STATUS	current
	DESCRIPTION ""
			::= { mbus80 5 }

mbus80VIF00		OBJECT-TYPE
			SYNTAX	INTEGER
			ACCESS	read-only
			STATUS	current
	DESCRIPTION ""
			::= { mbus80 6 }

mbus80Value00		OBJECT-TYPE
			SYNTAX	INTEGER
			ACCESS	read-only
			STATUS	current
	DESCRIPTION ""
			::= { mbus80 7 }

mbus80VIF01		OBJECT-TYPE
			SYNTAX	INTEGER
			ACCESS	read-only
			STATUS	current
	DESCRIPTION ""
			::= { mbus80 8 }

mbus80Value01		OBJECT-TYPE
			SYNTAX	INTEGER
			ACCESS	read-only
			STATUS	current
	DESCRIPTION ""
			::= { mbus80 9 }

mbus80VIF02		OBJECT-TYPE
			SYNTAX	INTEGER
			ACCESS	read-only
			STATUS	current
	DESCRIPTION ""
			::= { mbus80 10 }

mbus80Value02		OBJECT-TYPE
			SYNTAX	INTEGER
			ACCESS	read-only
			STATUS	current
	DESCRIPTION ""
			::= { mbus80 11 }

mbus80VIF03		OBJECT-TYPE
			SYNTAX	INTEGER
			ACCESS	read-only
			STATUS	current
	DESCRIPTION ""
			::= { mbus80 12 }

mbus80Value03		OBJECT-TYPE
			SYNTAX	INTEGER
			ACCESS	read-only
			STATUS	current
	DESCRIPTION ""
			::= { mbus80 13 }

mbus80VIF04		OBJECT-TYPE
			SYNTAX	INTEGER
			ACCESS	read-only
			STATUS	current
	DESCRIPTION ""
			::= { mbus80 14 }

mbus80Value04		OBJECT-TYPE
			SYNTAX	INTEGER
			ACCESS	read-only
			STATUS	current
	DESCRIPTION ""
			::= { mbus80 15 }

mbus80VIF05		OBJECT-TYPE
			SYNTAX	INTEGER
			ACCESS	read-only
			STATUS	current
	DESCRIPTION ""
			::= { mbus80 16 }

mbus80Value05		OBJECT-TYPE
			SYNTAX	INTEGER
			ACCESS	read-only
			STATUS	current
	DESCRIPTION ""
			::= { mbus80 17 }

mbus80VIF06		OBJECT-TYPE
			SYNTAX	INTEGER
			ACCESS	read-only
			STATUS	current
	DESCRIPTION ""
			::= { mbus80 18 }

mbus80Value06		OBJECT-TYPE
			SYNTAX	INTEGER
			ACCESS	read-only
			STATUS	current
	DESCRIPTION ""
			::= { mbus80 19 }

mbus80VIF07		OBJECT-TYPE
			SYNTAX	INTEGER
			ACCESS	read-only
			STATUS	current
	DESCRIPTION ""
			::= { mbus80 20 }

mbus80Value07		OBJECT-TYPE
			SYNTAX	INTEGER
			ACCESS	read-only
			STATUS	current
	DESCRIPTION ""
			::= { mbus80 21 }

mbus80VIF08		OBJECT-TYPE
			SYNTAX	INTEGER
			ACCESS	read-only
			STATUS	current
	DESCRIPTION ""
			::= { mbus80 22 }

mbus80Value08		OBJECT-TYPE
			SYNTAX	INTEGER
			ACCESS	read-only
			STATUS	current
	DESCRIPTION ""
			::= { mbus80 23 }

mbus80VIF09		OBJECT-TYPE
			SYNTAX	INTEGER
			ACCESS	read-only
			STATUS	current
	DESCRIPTION ""
			::= { mbus80 24 }

mbus80Value09		OBJECT-TYPE
			SYNTAX	INTEGER
			ACCESS	read-only
			STATUS	current
	DESCRIPTION ""
			::= { mbus80 25 }

mbus80VIF0A		OBJECT-TYPE
			SYNTAX	INTEGER
			ACCESS	read-only
			STATUS	current
	DESCRIPTION ""
			::= { mbus80 26 }

mbus80Value0A		OBJECT-TYPE
			SYNTAX	INTEGER
			ACCESS	read-only
			STATUS	current
	DESCRIPTION ""
			::= { mbus80 27 }

mbus80VIF0B		OBJECT-TYPE
			SYNTAX	INTEGER
			ACCESS	read-only
			STATUS	current
	DESCRIPTION ""
			::= { mbus80 28 }

mbus80Value0B		OBJECT-TYPE
			SYNTAX	INTEGER
			ACCESS	read-only
			STATUS	current
	DESCRIPTION ""
			::= { mbus80 29 }

mbus80VIF0C		OBJECT-TYPE
			SYNTAX	INTEGER
			ACCESS	read-only
			STATUS	current
	DESCRIPTION ""
			::= { mbus80 30 }

mbus80Value0C		OBJECT-TYPE
			SYNTAX	INTEGER
			ACCESS	read-only
			STATUS	current
	DESCRIPTION ""
			::= { mbus80 31 }

mbus80VIF0D		OBJECT-TYPE
			SYNTAX	INTEGER
			ACCESS	read-only
			STATUS	current
	DESCRIPTION ""
			::= { mbus80 32 }

mbus80Value0D		OBJECT-TYPE
			SYNTAX	INTEGER
			ACCESS	read-only
			STATUS	current
	DESCRIPTION ""
			::= { mbus80 33 }

mbus80VIF0E		OBJECT-TYPE
			SYNTAX	INTEGER
			ACCESS	read-only
			STATUS	current
	DESCRIPTION ""
			::= { mbus80 34 }

mbus80Value0E		OBJECT-TYPE
			SYNTAX	INTEGER
			ACCESS	read-only
			STATUS	current
	DESCRIPTION ""
			::= { mbus80 35 }

mbus80VIF0F		OBJECT-TYPE
			SYNTAX	INTEGER
			ACCESS	read-only
			STATUS	current
	DESCRIPTION ""
			::= { mbus80 36 }

mbus80Value0F		OBJECT-TYPE
			SYNTAX	INTEGER
			ACCESS	read-only
			STATUS	current
	DESCRIPTION ""
			::= { mbus80 37 }

mbus80VIF10		OBJECT-TYPE
			SYNTAX	INTEGER
			ACCESS	read-only
			STATUS	current
	DESCRIPTION ""
			::= { mbus80 38 }

mbus80Value10		OBJECT-TYPE
			SYNTAX	INTEGER
			ACCESS	read-only
			STATUS	current
	DESCRIPTION ""
			::= { mbus80 39 }

mbus80VIF11		OBJECT-TYPE
			SYNTAX	INTEGER
			ACCESS	read-only
			STATUS	current
	DESCRIPTION ""
			::= { mbus80 40 }

mbus80Value11		OBJECT-TYPE
			SYNTAX	INTEGER
			ACCESS	read-only
			STATUS	current
	DESCRIPTION ""
			::= { mbus80 41 }

mbus80VIF12		OBJECT-TYPE
			SYNTAX	INTEGER
			ACCESS	read-only
			STATUS	current
	DESCRIPTION ""
			::= { mbus80 42 }

mbus80Value12		OBJECT-TYPE
			SYNTAX	INTEGER
			ACCESS	read-only
			STATUS	current
	DESCRIPTION ""
			::= { mbus80 43 }

mbus80VIF13		OBJECT-TYPE
			SYNTAX	INTEGER
			ACCESS	read-only
			STATUS	current
	DESCRIPTION ""
			::= { mbus80 44 }

mbus80Value13		OBJECT-TYPE
			SYNTAX	INTEGER
			ACCESS	read-only
			STATUS	current
	DESCRIPTION ""
			::= { mbus80 45 }

mbus80VIF14		OBJECT-TYPE
			SYNTAX	INTEGER
			ACCESS	read-only
			STATUS	current
	DESCRIPTION ""
			::= { mbus80 46 }

mbus80Value14		OBJECT-TYPE
			SYNTAX	INTEGER
			ACCESS	read-only
			STATUS	current
	DESCRIPTION ""
			::= { mbus80 47 }

mbus80VIF15		OBJECT-TYPE
			SYNTAX	INTEGER
			ACCESS	read-only
			STATUS	current
	DESCRIPTION ""
			::= { mbus80 48 }

mbus80Value15		OBJECT-TYPE
			SYNTAX	INTEGER
			ACCESS	read-only
			STATUS	current
	DESCRIPTION ""
			::= { mbus80 49 }

mbus80VIF16		OBJECT-TYPE
			SYNTAX	INTEGER
			ACCESS	read-only
			STATUS	current
	DESCRIPTION ""
			::= { mbus80 50 }

mbus80Value16		OBJECT-TYPE
			SYNTAX	INTEGER
			ACCESS	read-only
			STATUS	current
	DESCRIPTION ""
			::= { mbus80 51 }

mbus80VIF17		OBJECT-TYPE
			SYNTAX	INTEGER
			ACCESS	read-only
			STATUS	current
	DESCRIPTION ""
			::= { mbus80 52 }

mbus80Value17		OBJECT-TYPE
			SYNTAX	INTEGER
			ACCESS	read-only
			STATUS	current
	DESCRIPTION ""
			::= { mbus80 53 }

mbus80VIF18		OBJECT-TYPE
			SYNTAX	INTEGER
			ACCESS	read-only
			STATUS	current
	DESCRIPTION ""
			::= { mbus80 54 }

mbus80Value18		OBJECT-TYPE
			SYNTAX	INTEGER
			ACCESS	read-only
			STATUS	current
	DESCRIPTION ""
			::= { mbus80 55 }

mbus80VIF19		OBJECT-TYPE
			SYNTAX	INTEGER
			ACCESS	read-only
			STATUS	current
	DESCRIPTION ""
			::= { mbus80 56 }

mbus80Value19		OBJECT-TYPE
			SYNTAX	INTEGER
			ACCESS	read-only
			STATUS	current
	DESCRIPTION ""
			::= { mbus80 57 }

mbus80VIF1A		OBJECT-TYPE
			SYNTAX	INTEGER
			ACCESS	read-only
			STATUS	current
	DESCRIPTION ""
			::= { mbus80 58 }

mbus80Value1A		OBJECT-TYPE
			SYNTAX	INTEGER
			ACCESS	read-only
			STATUS	current
	DESCRIPTION ""
			::= { mbus80 59 }

mbus80VIF1B		OBJECT-TYPE
			SYNTAX	INTEGER
			ACCESS	read-only
			STATUS	current
	DESCRIPTION ""
			::= { mbus80 60 }

mbus80Value1B		OBJECT-TYPE
			SYNTAX	INTEGER
			ACCESS	read-only
			STATUS	current
	DESCRIPTION ""
			::= { mbus80 61 }

mbus80VIF1C		OBJECT-TYPE
			SYNTAX	INTEGER
			ACCESS	read-only
			STATUS	current
	DESCRIPTION ""
			::= { mbus80 62 }

mbus80Value1C		OBJECT-TYPE
			SYNTAX	INTEGER
			ACCESS	read-only
			STATUS	current
	DESCRIPTION ""
			::= { mbus80 63 }

mbus80VIF1D		OBJECT-TYPE
			SYNTAX	INTEGER
			ACCESS	read-only
			STATUS	current
	DESCRIPTION ""
			::= { mbus80 64 }

mbus80Value1D		OBJECT-TYPE
			SYNTAX	INTEGER
			ACCESS	read-only
			STATUS	current
	DESCRIPTION ""
			::= { mbus80 65 }

mbus80VIF1E		OBJECT-TYPE
			SYNTAX	INTEGER
			ACCESS	read-only
			STATUS	current
	DESCRIPTION ""
			::= { mbus80 66 }

mbus80Value1E		OBJECT-TYPE
			SYNTAX	INTEGER
			ACCESS	read-only
			STATUS	current
	DESCRIPTION ""
			::= { mbus80 67 }

mbus80VIF1F		OBJECT-TYPE
			SYNTAX	INTEGER
			ACCESS	read-only
			STATUS	current
	DESCRIPTION ""
			::= { mbus80 68 }

mbus80Value1F		OBJECT-TYPE
			SYNTAX	INTEGER
			ACCESS	read-only
			STATUS	current
	DESCRIPTION ""
			::= { mbus80 69 }

mbus80VIF20		OBJECT-TYPE
			SYNTAX	INTEGER
			ACCESS	read-only
			STATUS	current
	DESCRIPTION ""
			::= { mbus80 70 }

mbus80Value20		OBJECT-TYPE
			SYNTAX	INTEGER
			ACCESS	read-only
			STATUS	current
	DESCRIPTION ""
			::= { mbus80 71 }

mbus80VIF21		OBJECT-TYPE
			SYNTAX	INTEGER
			ACCESS	read-only
			STATUS	current
	DESCRIPTION ""
			::= { mbus80 72 }

mbus80Value21		OBJECT-TYPE
			SYNTAX	INTEGER
			ACCESS	read-only
			STATUS	current
	DESCRIPTION ""
			::= { mbus80 73 }

mbus80VIF22		OBJECT-TYPE
			SYNTAX	INTEGER
			ACCESS	read-only
			STATUS	current
	DESCRIPTION ""
			::= { mbus80 74 }

mbus80Value22		OBJECT-TYPE
			SYNTAX	INTEGER
			ACCESS	read-only
			STATUS	current
	DESCRIPTION ""
			::= { mbus80 75 }

mbus80VIF23		OBJECT-TYPE
			SYNTAX	INTEGER
			ACCESS	read-only
			STATUS	current
	DESCRIPTION ""
			::= { mbus80 76 }

mbus80Value23		OBJECT-TYPE
			SYNTAX	INTEGER
			ACCESS	read-only
			STATUS	current
	DESCRIPTION ""
			::= { mbus80 77 }

mbus80VIF24		OBJECT-TYPE
			SYNTAX	INTEGER
			ACCESS	read-only
			STATUS	current
	DESCRIPTION ""
			::= { mbus80 78 }

mbus80Value24		OBJECT-TYPE
			SYNTAX	INTEGER
			ACCESS	read-only
			STATUS	current
	DESCRIPTION ""
			::= { mbus80 79 }

mbus80VIF25		OBJECT-TYPE
			SYNTAX	INTEGER
			ACCESS	read-only
			STATUS	current
	DESCRIPTION ""
			::= { mbus80 80 }

mbus80Value25		OBJECT-TYPE
			SYNTAX	INTEGER
			ACCESS	read-only
			STATUS	current
	DESCRIPTION ""
			::= { mbus80 81 }

mbus80VIF26		OBJECT-TYPE
			SYNTAX	INTEGER
			ACCESS	read-only
			STATUS	current
	DESCRIPTION ""
			::= { mbus80 82 }

mbus80Value26		OBJECT-TYPE
			SYNTAX	INTEGER
			ACCESS	read-only
			STATUS	current
	DESCRIPTION ""
			::= { mbus80 83 }

mbus80VIF27		OBJECT-TYPE
			SYNTAX	INTEGER
			ACCESS	read-only
			STATUS	current
	DESCRIPTION ""
			::= { mbus80 84 }

mbus80Value27		OBJECT-TYPE
			SYNTAX	INTEGER
			ACCESS	read-only
			STATUS	current
	DESCRIPTION ""
			::= { mbus80 85 }

mbus80VIF28		OBJECT-TYPE
			SYNTAX	INTEGER
			ACCESS	read-only
			STATUS	current
	DESCRIPTION ""
			::= { mbus80 86 }

mbus80Value28		OBJECT-TYPE
			SYNTAX	INTEGER
			ACCESS	read-only
			STATUS	current
	DESCRIPTION ""
			::= { mbus80 87 }

mbus80VIF29		OBJECT-TYPE
			SYNTAX	INTEGER
			ACCESS	read-only
			STATUS	current
	DESCRIPTION ""
			::= { mbus80 88 }

mbus80Value29		OBJECT-TYPE
			SYNTAX	INTEGER
			ACCESS	read-only
			STATUS	current
	DESCRIPTION ""
			::= { mbus80 89 }

mbus80VIF2A		OBJECT-TYPE
			SYNTAX	INTEGER
			ACCESS	read-only
			STATUS	current
	DESCRIPTION ""
			::= { mbus80 90 }

mbus80Value2A		OBJECT-TYPE
			SYNTAX	INTEGER
			ACCESS	read-only
			STATUS	current
	DESCRIPTION ""
			::= { mbus80 91 }

mbus80VIF2B		OBJECT-TYPE
			SYNTAX	INTEGER
			ACCESS	read-only
			STATUS	current
	DESCRIPTION ""
			::= { mbus80 92 }

mbus80Value2B		OBJECT-TYPE
			SYNTAX	INTEGER
			ACCESS	read-only
			STATUS	current
	DESCRIPTION ""
			::= { mbus80 93 }

mbus80VIF2C		OBJECT-TYPE
			SYNTAX	INTEGER
			ACCESS	read-only
			STATUS	current
	DESCRIPTION ""
			::= { mbus80 94 }

mbus80Value2C		OBJECT-TYPE
			SYNTAX	INTEGER
			ACCESS	read-only
			STATUS	current
	DESCRIPTION ""
			::= { mbus80 95 }

mbus80VIF2D		OBJECT-TYPE
			SYNTAX	INTEGER
			ACCESS	read-only
			STATUS	current
	DESCRIPTION ""
			::= { mbus80 96 }

mbus80Value2D		OBJECT-TYPE
			SYNTAX	INTEGER
			ACCESS	read-only
			STATUS	current
	DESCRIPTION ""
			::= { mbus80 97 }

mbus80VIF2E		OBJECT-TYPE
			SYNTAX	INTEGER
			ACCESS	read-only
			STATUS	current
	DESCRIPTION ""
			::= { mbus80 98 }

mbus80Value2E		OBJECT-TYPE
			SYNTAX	INTEGER
			ACCESS	read-only
			STATUS	current
	DESCRIPTION ""
			::= { mbus80 99 }

mbus80VIF2F		OBJECT-TYPE
			SYNTAX	INTEGER
			ACCESS	read-only
			STATUS	current
	DESCRIPTION ""
			::= { mbus80 100 }

mbus80Value2F		OBJECT-TYPE
			SYNTAX	INTEGER
			ACCESS	read-only
			STATUS	current
	DESCRIPTION ""
			::= { mbus80 101 }

mbus81			OBJECT IDENTIFIER ::= { mbus 129 }

mbus81IdNumber		OBJECT-TYPE
			SYNTAX	Gauge
			ACCESS	read-only
			STATUS	current
	DESCRIPTION ""
			::= { mbus81 1 }

mbus81Manufacturer	OBJECT-TYPE
			SYNTAX	Gauge
			ACCESS	read-only
			STATUS	current
	DESCRIPTION ""
			::= { mbus81 2 }

mbus81Version		OBJECT-TYPE
			SYNTAX	Gauge
			ACCESS	read-only
			STATUS	current
	DESCRIPTION ""
			::= { mbus81 3 }

mbus81Medium		OBJECT-TYPE
			SYNTAX	Gauge
			ACCESS	read-only
			STATUS	current
	DESCRIPTION ""
			::= { mbus81 4 }

mbus81Status		OBJECT-TYPE
			SYNTAX	Gauge
			ACCESS	read-only
			STATUS	current
	DESCRIPTION ""
			::= { mbus81 5 }

mbus81VIF00		OBJECT-TYPE
			SYNTAX	INTEGER
			ACCESS	read-only
			STATUS	current
	DESCRIPTION ""
			::= { mbus81 6 }

mbus81Value00		OBJECT-TYPE
			SYNTAX	INTEGER
			ACCESS	read-only
			STATUS	current
	DESCRIPTION ""
			::= { mbus81 7 }

mbus81VIF01		OBJECT-TYPE
			SYNTAX	INTEGER
			ACCESS	read-only
			STATUS	current
	DESCRIPTION ""
			::= { mbus81 8 }

mbus81Value01		OBJECT-TYPE
			SYNTAX	INTEGER
			ACCESS	read-only
			STATUS	current
	DESCRIPTION ""
			::= { mbus81 9 }

mbus81VIF02		OBJECT-TYPE
			SYNTAX	INTEGER
			ACCESS	read-only
			STATUS	current
	DESCRIPTION ""
			::= { mbus81 10 }

mbus81Value02		OBJECT-TYPE
			SYNTAX	INTEGER
			ACCESS	read-only
			STATUS	current
	DESCRIPTION ""
			::= { mbus81 11 }

mbus81VIF03		OBJECT-TYPE
			SYNTAX	INTEGER
			ACCESS	read-only
			STATUS	current
	DESCRIPTION ""
			::= { mbus81 12 }

mbus81Value03		OBJECT-TYPE
			SYNTAX	INTEGER
			ACCESS	read-only
			STATUS	current
	DESCRIPTION ""
			::= { mbus81 13 }

mbus81VIF04		OBJECT-TYPE
			SYNTAX	INTEGER
			ACCESS	read-only
			STATUS	current
	DESCRIPTION ""
			::= { mbus81 14 }

mbus81Value04		OBJECT-TYPE
			SYNTAX	INTEGER
			ACCESS	read-only
			STATUS	current
	DESCRIPTION ""
			::= { mbus81 15 }

mbus81VIF05		OBJECT-TYPE
			SYNTAX	INTEGER
			ACCESS	read-only
			STATUS	current
	DESCRIPTION ""
			::= { mbus81 16 }

mbus81Value05		OBJECT-TYPE
			SYNTAX	INTEGER
			ACCESS	read-only
			STATUS	current
	DESCRIPTION ""
			::= { mbus81 17 }

mbus81VIF06		OBJECT-TYPE
			SYNTAX	INTEGER
			ACCESS	read-only
			STATUS	current
	DESCRIPTION ""
			::= { mbus81 18 }

mbus81Value06		OBJECT-TYPE
			SYNTAX	INTEGER
			ACCESS	read-only
			STATUS	current
	DESCRIPTION ""
			::= { mbus81 19 }

mbus81VIF07		OBJECT-TYPE
			SYNTAX	INTEGER
			ACCESS	read-only
			STATUS	current
	DESCRIPTION ""
			::= { mbus81 20 }

mbus81Value07		OBJECT-TYPE
			SYNTAX	INTEGER
			ACCESS	read-only
			STATUS	current
	DESCRIPTION ""
			::= { mbus81 21 }

mbus81VIF08		OBJECT-TYPE
			SYNTAX	INTEGER
			ACCESS	read-only
			STATUS	current
	DESCRIPTION ""
			::= { mbus81 22 }

mbus81Value08		OBJECT-TYPE
			SYNTAX	INTEGER
			ACCESS	read-only
			STATUS	current
	DESCRIPTION ""
			::= { mbus81 23 }

mbus81VIF09		OBJECT-TYPE
			SYNTAX	INTEGER
			ACCESS	read-only
			STATUS	current
	DESCRIPTION ""
			::= { mbus81 24 }

mbus81Value09		OBJECT-TYPE
			SYNTAX	INTEGER
			ACCESS	read-only
			STATUS	current
	DESCRIPTION ""
			::= { mbus81 25 }

mbus81VIF0A		OBJECT-TYPE
			SYNTAX	INTEGER
			ACCESS	read-only
			STATUS	current
	DESCRIPTION ""
			::= { mbus81 26 }

mbus81Value0A		OBJECT-TYPE
			SYNTAX	INTEGER
			ACCESS	read-only
			STATUS	current
	DESCRIPTION ""
			::= { mbus81 27 }

mbus81VIF0B		OBJECT-TYPE
			SYNTAX	INTEGER
			ACCESS	read-only
			STATUS	current
	DESCRIPTION ""
			::= { mbus81 28 }

mbus81Value0B		OBJECT-TYPE
			SYNTAX	INTEGER
			ACCESS	read-only
			STATUS	current
	DESCRIPTION ""
			::= { mbus81 29 }

mbus81VIF0C		OBJECT-TYPE
			SYNTAX	INTEGER
			ACCESS	read-only
			STATUS	current
	DESCRIPTION ""
			::= { mbus81 30 }

mbus81Value0C		OBJECT-TYPE
			SYNTAX	INTEGER
			ACCESS	read-only
			STATUS	current
	DESCRIPTION ""
			::= { mbus81 31 }

mbus81VIF0D		OBJECT-TYPE
			SYNTAX	INTEGER
			ACCESS	read-only
			STATUS	current
	DESCRIPTION ""
			::= { mbus81 32 }

mbus81Value0D		OBJECT-TYPE
			SYNTAX	INTEGER
			ACCESS	read-only
			STATUS	current
	DESCRIPTION ""
			::= { mbus81 33 }

mbus81VIF0E		OBJECT-TYPE
			SYNTAX	INTEGER
			ACCESS	read-only
			STATUS	current
	DESCRIPTION ""
			::= { mbus81 34 }

mbus81Value0E		OBJECT-TYPE
			SYNTAX	INTEGER
			ACCESS	read-only
			STATUS	current
	DESCRIPTION ""
			::= { mbus81 35 }

mbus81VIF0F		OBJECT-TYPE
			SYNTAX	INTEGER
			ACCESS	read-only
			STATUS	current
	DESCRIPTION ""
			::= { mbus81 36 }

mbus81Value0F		OBJECT-TYPE
			SYNTAX	INTEGER
			ACCESS	read-only
			STATUS	current
	DESCRIPTION ""
			::= { mbus81 37 }

mbus81VIF10		OBJECT-TYPE
			SYNTAX	INTEGER
			ACCESS	read-only
			STATUS	current
	DESCRIPTION ""
			::= { mbus81 38 }

mbus81Value10		OBJECT-TYPE
			SYNTAX	INTEGER
			ACCESS	read-only
			STATUS	current
	DESCRIPTION ""
			::= { mbus81 39 }

mbus81VIF11		OBJECT-TYPE
			SYNTAX	INTEGER
			ACCESS	read-only
			STATUS	current
	DESCRIPTION ""
			::= { mbus81 40 }

mbus81Value11		OBJECT-TYPE
			SYNTAX	INTEGER
			ACCESS	read-only
			STATUS	current
	DESCRIPTION ""
			::= { mbus81 41 }

mbus81VIF12		OBJECT-TYPE
			SYNTAX	INTEGER
			ACCESS	read-only
			STATUS	current
	DESCRIPTION ""
			::= { mbus81 42 }

mbus81Value12		OBJECT-TYPE
			SYNTAX	INTEGER
			ACCESS	read-only
			STATUS	current
	DESCRIPTION ""
			::= { mbus81 43 }

mbus81VIF13		OBJECT-TYPE
			SYNTAX	INTEGER
			ACCESS	read-only
			STATUS	current
	DESCRIPTION ""
			::= { mbus81 44 }

mbus81Value13		OBJECT-TYPE
			SYNTAX	INTEGER
			ACCESS	read-only
			STATUS	current
	DESCRIPTION ""
			::= { mbus81 45 }

mbus81VIF14		OBJECT-TYPE
			SYNTAX	INTEGER
			ACCESS	read-only
			STATUS	current
	DESCRIPTION ""
			::= { mbus81 46 }

mbus81Value14		OBJECT-TYPE
			SYNTAX	INTEGER
			ACCESS	read-only
			STATUS	current
	DESCRIPTION ""
			::= { mbus81 47 }

mbus81VIF15		OBJECT-TYPE
			SYNTAX	INTEGER
			ACCESS	read-only
			STATUS	current
	DESCRIPTION ""
			::= { mbus81 48 }

mbus81Value15		OBJECT-TYPE
			SYNTAX	INTEGER
			ACCESS	read-only
			STATUS	current
	DESCRIPTION ""
			::= { mbus81 49 }

mbus81VIF16		OBJECT-TYPE
			SYNTAX	INTEGER
			ACCESS	read-only
			STATUS	current
	DESCRIPTION ""
			::= { mbus81 50 }

mbus81Value16		OBJECT-TYPE
			SYNTAX	INTEGER
			ACCESS	read-only
			STATUS	current
	DESCRIPTION ""
			::= { mbus81 51 }

mbus81VIF17		OBJECT-TYPE
			SYNTAX	INTEGER
			ACCESS	read-only
			STATUS	current
	DESCRIPTION ""
			::= { mbus81 52 }

mbus81Value17		OBJECT-TYPE
			SYNTAX	INTEGER
			ACCESS	read-only
			STATUS	current
	DESCRIPTION ""
			::= { mbus81 53 }

mbus81VIF18		OBJECT-TYPE
			SYNTAX	INTEGER
			ACCESS	read-only
			STATUS	current
	DESCRIPTION ""
			::= { mbus81 54 }

mbus81Value18		OBJECT-TYPE
			SYNTAX	INTEGER
			ACCESS	read-only
			STATUS	current
	DESCRIPTION ""
			::= { mbus81 55 }

mbus81VIF19		OBJECT-TYPE
			SYNTAX	INTEGER
			ACCESS	read-only
			STATUS	current
	DESCRIPTION ""
			::= { mbus81 56 }

mbus81Value19		OBJECT-TYPE
			SYNTAX	INTEGER
			ACCESS	read-only
			STATUS	current
	DESCRIPTION ""
			::= { mbus81 57 }

mbus81VIF1A		OBJECT-TYPE
			SYNTAX	INTEGER
			ACCESS	read-only
			STATUS	current
	DESCRIPTION ""
			::= { mbus81 58 }

mbus81Value1A		OBJECT-TYPE
			SYNTAX	INTEGER
			ACCESS	read-only
			STATUS	current
	DESCRIPTION ""
			::= { mbus81 59 }

mbus81VIF1B		OBJECT-TYPE
			SYNTAX	INTEGER
			ACCESS	read-only
			STATUS	current
	DESCRIPTION ""
			::= { mbus81 60 }

mbus81Value1B		OBJECT-TYPE
			SYNTAX	INTEGER
			ACCESS	read-only
			STATUS	current
	DESCRIPTION ""
			::= { mbus81 61 }

mbus81VIF1C		OBJECT-TYPE
			SYNTAX	INTEGER
			ACCESS	read-only
			STATUS	current
	DESCRIPTION ""
			::= { mbus81 62 }

mbus81Value1C		OBJECT-TYPE
			SYNTAX	INTEGER
			ACCESS	read-only
			STATUS	current
	DESCRIPTION ""
			::= { mbus81 63 }

mbus81VIF1D		OBJECT-TYPE
			SYNTAX	INTEGER
			ACCESS	read-only
			STATUS	current
	DESCRIPTION ""
			::= { mbus81 64 }

mbus81Value1D		OBJECT-TYPE
			SYNTAX	INTEGER
			ACCESS	read-only
			STATUS	current
	DESCRIPTION ""
			::= { mbus81 65 }

mbus81VIF1E		OBJECT-TYPE
			SYNTAX	INTEGER
			ACCESS	read-only
			STATUS	current
	DESCRIPTION ""
			::= { mbus81 66 }

mbus81Value1E		OBJECT-TYPE
			SYNTAX	INTEGER
			ACCESS	read-only
			STATUS	current
	DESCRIPTION ""
			::= { mbus81 67 }

mbus81VIF1F		OBJECT-TYPE
			SYNTAX	INTEGER
			ACCESS	read-only
			STATUS	current
	DESCRIPTION ""
			::= { mbus81 68 }

mbus81Value1F		OBJECT-TYPE
			SYNTAX	INTEGER
			ACCESS	read-only
			STATUS	current
	DESCRIPTION ""
			::= { mbus81 69 }

mbus81VIF20		OBJECT-TYPE
			SYNTAX	INTEGER
			ACCESS	read-only
			STATUS	current
	DESCRIPTION ""
			::= { mbus81 70 }

mbus81Value20		OBJECT-TYPE
			SYNTAX	INTEGER
			ACCESS	read-only
			STATUS	current
	DESCRIPTION ""
			::= { mbus81 71 }

mbus81VIF21		OBJECT-TYPE
			SYNTAX	INTEGER
			ACCESS	read-only
			STATUS	current
	DESCRIPTION ""
			::= { mbus81 72 }

mbus81Value21		OBJECT-TYPE
			SYNTAX	INTEGER
			ACCESS	read-only
			STATUS	current
	DESCRIPTION ""
			::= { mbus81 73 }

mbus81VIF22		OBJECT-TYPE
			SYNTAX	INTEGER
			ACCESS	read-only
			STATUS	current
	DESCRIPTION ""
			::= { mbus81 74 }

mbus81Value22		OBJECT-TYPE
			SYNTAX	INTEGER
			ACCESS	read-only
			STATUS	current
	DESCRIPTION ""
			::= { mbus81 75 }

mbus81VIF23		OBJECT-TYPE
			SYNTAX	INTEGER
			ACCESS	read-only
			STATUS	current
	DESCRIPTION ""
			::= { mbus81 76 }

mbus81Value23		OBJECT-TYPE
			SYNTAX	INTEGER
			ACCESS	read-only
			STATUS	current
	DESCRIPTION ""
			::= { mbus81 77 }

mbus81VIF24		OBJECT-TYPE
			SYNTAX	INTEGER
			ACCESS	read-only
			STATUS	current
	DESCRIPTION ""
			::= { mbus81 78 }

mbus81Value24		OBJECT-TYPE
			SYNTAX	INTEGER
			ACCESS	read-only
			STATUS	current
	DESCRIPTION ""
			::= { mbus81 79 }

mbus81VIF25		OBJECT-TYPE
			SYNTAX	INTEGER
			ACCESS	read-only
			STATUS	current
	DESCRIPTION ""
			::= { mbus81 80 }

mbus81Value25		OBJECT-TYPE
			SYNTAX	INTEGER
			ACCESS	read-only
			STATUS	current
	DESCRIPTION ""
			::= { mbus81 81 }

mbus81VIF26		OBJECT-TYPE
			SYNTAX	INTEGER
			ACCESS	read-only
			STATUS	current
	DESCRIPTION ""
			::= { mbus81 82 }

mbus81Value26		OBJECT-TYPE
			SYNTAX	INTEGER
			ACCESS	read-only
			STATUS	current
	DESCRIPTION ""
			::= { mbus81 83 }

mbus81VIF27		OBJECT-TYPE
			SYNTAX	INTEGER
			ACCESS	read-only
			STATUS	current
	DESCRIPTION ""
			::= { mbus81 84 }

mbus81Value27		OBJECT-TYPE
			SYNTAX	INTEGER
			ACCESS	read-only
			STATUS	current
	DESCRIPTION ""
			::= { mbus81 85 }

mbus81VIF28		OBJECT-TYPE
			SYNTAX	INTEGER
			ACCESS	read-only
			STATUS	current
	DESCRIPTION ""
			::= { mbus81 86 }

mbus81Value28		OBJECT-TYPE
			SYNTAX	INTEGER
			ACCESS	read-only
			STATUS	current
	DESCRIPTION ""
			::= { mbus81 87 }

mbus81VIF29		OBJECT-TYPE
			SYNTAX	INTEGER
			ACCESS	read-only
			STATUS	current
	DESCRIPTION ""
			::= { mbus81 88 }

mbus81Value29		OBJECT-TYPE
			SYNTAX	INTEGER
			ACCESS	read-only
			STATUS	current
	DESCRIPTION ""
			::= { mbus81 89 }

mbus81VIF2A		OBJECT-TYPE
			SYNTAX	INTEGER
			ACCESS	read-only
			STATUS	current
	DESCRIPTION ""
			::= { mbus81 90 }

mbus81Value2A		OBJECT-TYPE
			SYNTAX	INTEGER
			ACCESS	read-only
			STATUS	current
	DESCRIPTION ""
			::= { mbus81 91 }

mbus81VIF2B		OBJECT-TYPE
			SYNTAX	INTEGER
			ACCESS	read-only
			STATUS	current
	DESCRIPTION ""
			::= { mbus81 92 }

mbus81Value2B		OBJECT-TYPE
			SYNTAX	INTEGER
			ACCESS	read-only
			STATUS	current
	DESCRIPTION ""
			::= { mbus81 93 }

mbus81VIF2C		OBJECT-TYPE
			SYNTAX	INTEGER
			ACCESS	read-only
			STATUS	current
	DESCRIPTION ""
			::= { mbus81 94 }

mbus81Value2C		OBJECT-TYPE
			SYNTAX	INTEGER
			ACCESS	read-only
			STATUS	current
	DESCRIPTION ""
			::= { mbus81 95 }

mbus81VIF2D		OBJECT-TYPE
			SYNTAX	INTEGER
			ACCESS	read-only
			STATUS	current
	DESCRIPTION ""
			::= { mbus81 96 }

mbus81Value2D		OBJECT-TYPE
			SYNTAX	INTEGER
			ACCESS	read-only
			STATUS	current
	DESCRIPTION ""
			::= { mbus81 97 }

mbus81VIF2E		OBJECT-TYPE
			SYNTAX	INTEGER
			ACCESS	read-only
			STATUS	current
	DESCRIPTION ""
			::= { mbus81 98 }

mbus81Value2E		OBJECT-TYPE
			SYNTAX	INTEGER
			ACCESS	read-only
			STATUS	current
	DESCRIPTION ""
			::= { mbus81 99 }

mbus81VIF2F		OBJECT-TYPE
			SYNTAX	INTEGER
			ACCESS	read-only
			STATUS	current
	DESCRIPTION ""
			::= { mbus81 100 }

mbus81Value2F		OBJECT-TYPE
			SYNTAX	INTEGER
			ACCESS	read-only
			STATUS	current
	DESCRIPTION ""
			::= { mbus81 101 }

mbus82			OBJECT IDENTIFIER ::= { mbus 130 }

mbus82IdNumber		OBJECT-TYPE
			SYNTAX	Gauge
			ACCESS	read-only
			STATUS	current
	DESCRIPTION ""
			::= { mbus82 1 }

mbus82Manufacturer	OBJECT-TYPE
			SYNTAX	Gauge
			ACCESS	read-only
			STATUS	current
	DESCRIPTION ""
			::= { mbus82 2 }

mbus82Version		OBJECT-TYPE
			SYNTAX	Gauge
			ACCESS	read-only
			STATUS	current
	DESCRIPTION ""
			::= { mbus82 3 }

mbus82Medium		OBJECT-TYPE
			SYNTAX	Gauge
			ACCESS	read-only
			STATUS	current
	DESCRIPTION ""
			::= { mbus82 4 }

mbus82Status		OBJECT-TYPE
			SYNTAX	Gauge
			ACCESS	read-only
			STATUS	current
	DESCRIPTION ""
			::= { mbus82 5 }

mbus82VIF00		OBJECT-TYPE
			SYNTAX	INTEGER
			ACCESS	read-only
			STATUS	current
	DESCRIPTION ""
			::= { mbus82 6 }

mbus82Value00		OBJECT-TYPE
			SYNTAX	INTEGER
			ACCESS	read-only
			STATUS	current
	DESCRIPTION ""
			::= { mbus82 7 }

mbus82VIF01		OBJECT-TYPE
			SYNTAX	INTEGER
			ACCESS	read-only
			STATUS	current
	DESCRIPTION ""
			::= { mbus82 8 }

mbus82Value01		OBJECT-TYPE
			SYNTAX	INTEGER
			ACCESS	read-only
			STATUS	current
	DESCRIPTION ""
			::= { mbus82 9 }

mbus82VIF02		OBJECT-TYPE
			SYNTAX	INTEGER
			ACCESS	read-only
			STATUS	current
	DESCRIPTION ""
			::= { mbus82 10 }

mbus82Value02		OBJECT-TYPE
			SYNTAX	INTEGER
			ACCESS	read-only
			STATUS	current
	DESCRIPTION ""
			::= { mbus82 11 }

mbus82VIF03		OBJECT-TYPE
			SYNTAX	INTEGER
			ACCESS	read-only
			STATUS	current
	DESCRIPTION ""
			::= { mbus82 12 }

mbus82Value03		OBJECT-TYPE
			SYNTAX	INTEGER
			ACCESS	read-only
			STATUS	current
	DESCRIPTION ""
			::= { mbus82 13 }

mbus82VIF04		OBJECT-TYPE
			SYNTAX	INTEGER
			ACCESS	read-only
			STATUS	current
	DESCRIPTION ""
			::= { mbus82 14 }

mbus82Value04		OBJECT-TYPE
			SYNTAX	INTEGER
			ACCESS	read-only
			STATUS	current
	DESCRIPTION ""
			::= { mbus82 15 }

mbus82VIF05		OBJECT-TYPE
			SYNTAX	INTEGER
			ACCESS	read-only
			STATUS	current
	DESCRIPTION ""
			::= { mbus82 16 }

mbus82Value05		OBJECT-TYPE
			SYNTAX	INTEGER
			ACCESS	read-only
			STATUS	current
	DESCRIPTION ""
			::= { mbus82 17 }

mbus82VIF06		OBJECT-TYPE
			SYNTAX	INTEGER
			ACCESS	read-only
			STATUS	current
	DESCRIPTION ""
			::= { mbus82 18 }

mbus82Value06		OBJECT-TYPE
			SYNTAX	INTEGER
			ACCESS	read-only
			STATUS	current
	DESCRIPTION ""
			::= { mbus82 19 }

mbus82VIF07		OBJECT-TYPE
			SYNTAX	INTEGER
			ACCESS	read-only
			STATUS	current
	DESCRIPTION ""
			::= { mbus82 20 }

mbus82Value07		OBJECT-TYPE
			SYNTAX	INTEGER
			ACCESS	read-only
			STATUS	current
	DESCRIPTION ""
			::= { mbus82 21 }

mbus82VIF08		OBJECT-TYPE
			SYNTAX	INTEGER
			ACCESS	read-only
			STATUS	current
	DESCRIPTION ""
			::= { mbus82 22 }

mbus82Value08		OBJECT-TYPE
			SYNTAX	INTEGER
			ACCESS	read-only
			STATUS	current
	DESCRIPTION ""
			::= { mbus82 23 }

mbus82VIF09		OBJECT-TYPE
			SYNTAX	INTEGER
			ACCESS	read-only
			STATUS	current
	DESCRIPTION ""
			::= { mbus82 24 }

mbus82Value09		OBJECT-TYPE
			SYNTAX	INTEGER
			ACCESS	read-only
			STATUS	current
	DESCRIPTION ""
			::= { mbus82 25 }

mbus82VIF0A		OBJECT-TYPE
			SYNTAX	INTEGER
			ACCESS	read-only
			STATUS	current
	DESCRIPTION ""
			::= { mbus82 26 }

mbus82Value0A		OBJECT-TYPE
			SYNTAX	INTEGER
			ACCESS	read-only
			STATUS	current
	DESCRIPTION ""
			::= { mbus82 27 }

mbus82VIF0B		OBJECT-TYPE
			SYNTAX	INTEGER
			ACCESS	read-only
			STATUS	current
	DESCRIPTION ""
			::= { mbus82 28 }

mbus82Value0B		OBJECT-TYPE
			SYNTAX	INTEGER
			ACCESS	read-only
			STATUS	current
	DESCRIPTION ""
			::= { mbus82 29 }

mbus82VIF0C		OBJECT-TYPE
			SYNTAX	INTEGER
			ACCESS	read-only
			STATUS	current
	DESCRIPTION ""
			::= { mbus82 30 }

mbus82Value0C		OBJECT-TYPE
			SYNTAX	INTEGER
			ACCESS	read-only
			STATUS	current
	DESCRIPTION ""
			::= { mbus82 31 }

mbus82VIF0D		OBJECT-TYPE
			SYNTAX	INTEGER
			ACCESS	read-only
			STATUS	current
	DESCRIPTION ""
			::= { mbus82 32 }

mbus82Value0D		OBJECT-TYPE
			SYNTAX	INTEGER
			ACCESS	read-only
			STATUS	current
	DESCRIPTION ""
			::= { mbus82 33 }

mbus82VIF0E		OBJECT-TYPE
			SYNTAX	INTEGER
			ACCESS	read-only
			STATUS	current
	DESCRIPTION ""
			::= { mbus82 34 }

mbus82Value0E		OBJECT-TYPE
			SYNTAX	INTEGER
			ACCESS	read-only
			STATUS	current
	DESCRIPTION ""
			::= { mbus82 35 }

mbus82VIF0F		OBJECT-TYPE
			SYNTAX	INTEGER
			ACCESS	read-only
			STATUS	current
	DESCRIPTION ""
			::= { mbus82 36 }

mbus82Value0F		OBJECT-TYPE
			SYNTAX	INTEGER
			ACCESS	read-only
			STATUS	current
	DESCRIPTION ""
			::= { mbus82 37 }

mbus82VIF10		OBJECT-TYPE
			SYNTAX	INTEGER
			ACCESS	read-only
			STATUS	current
	DESCRIPTION ""
			::= { mbus82 38 }

mbus82Value10		OBJECT-TYPE
			SYNTAX	INTEGER
			ACCESS	read-only
			STATUS	current
	DESCRIPTION ""
			::= { mbus82 39 }

mbus82VIF11		OBJECT-TYPE
			SYNTAX	INTEGER
			ACCESS	read-only
			STATUS	current
	DESCRIPTION ""
			::= { mbus82 40 }

mbus82Value11		OBJECT-TYPE
			SYNTAX	INTEGER
			ACCESS	read-only
			STATUS	current
	DESCRIPTION ""
			::= { mbus82 41 }

mbus82VIF12		OBJECT-TYPE
			SYNTAX	INTEGER
			ACCESS	read-only
			STATUS	current
	DESCRIPTION ""
			::= { mbus82 42 }

mbus82Value12		OBJECT-TYPE
			SYNTAX	INTEGER
			ACCESS	read-only
			STATUS	current
	DESCRIPTION ""
			::= { mbus82 43 }

mbus82VIF13		OBJECT-TYPE
			SYNTAX	INTEGER
			ACCESS	read-only
			STATUS	current
	DESCRIPTION ""
			::= { mbus82 44 }

mbus82Value13		OBJECT-TYPE
			SYNTAX	INTEGER
			ACCESS	read-only
			STATUS	current
	DESCRIPTION ""
			::= { mbus82 45 }

mbus82VIF14		OBJECT-TYPE
			SYNTAX	INTEGER
			ACCESS	read-only
			STATUS	current
	DESCRIPTION ""
			::= { mbus82 46 }

mbus82Value14		OBJECT-TYPE
			SYNTAX	INTEGER
			ACCESS	read-only
			STATUS	current
	DESCRIPTION ""
			::= { mbus82 47 }

mbus82VIF15		OBJECT-TYPE
			SYNTAX	INTEGER
			ACCESS	read-only
			STATUS	current
	DESCRIPTION ""
			::= { mbus82 48 }

mbus82Value15		OBJECT-TYPE
			SYNTAX	INTEGER
			ACCESS	read-only
			STATUS	current
	DESCRIPTION ""
			::= { mbus82 49 }

mbus82VIF16		OBJECT-TYPE
			SYNTAX	INTEGER
			ACCESS	read-only
			STATUS	current
	DESCRIPTION ""
			::= { mbus82 50 }

mbus82Value16		OBJECT-TYPE
			SYNTAX	INTEGER
			ACCESS	read-only
			STATUS	current
	DESCRIPTION ""
			::= { mbus82 51 }

mbus82VIF17		OBJECT-TYPE
			SYNTAX	INTEGER
			ACCESS	read-only
			STATUS	current
	DESCRIPTION ""
			::= { mbus82 52 }

mbus82Value17		OBJECT-TYPE
			SYNTAX	INTEGER
			ACCESS	read-only
			STATUS	current
	DESCRIPTION ""
			::= { mbus82 53 }

mbus82VIF18		OBJECT-TYPE
			SYNTAX	INTEGER
			ACCESS	read-only
			STATUS	current
	DESCRIPTION ""
			::= { mbus82 54 }

mbus82Value18		OBJECT-TYPE
			SYNTAX	INTEGER
			ACCESS	read-only
			STATUS	current
	DESCRIPTION ""
			::= { mbus82 55 }

mbus82VIF19		OBJECT-TYPE
			SYNTAX	INTEGER
			ACCESS	read-only
			STATUS	current
	DESCRIPTION ""
			::= { mbus82 56 }

mbus82Value19		OBJECT-TYPE
			SYNTAX	INTEGER
			ACCESS	read-only
			STATUS	current
	DESCRIPTION ""
			::= { mbus82 57 }

mbus82VIF1A		OBJECT-TYPE
			SYNTAX	INTEGER
			ACCESS	read-only
			STATUS	current
	DESCRIPTION ""
			::= { mbus82 58 }

mbus82Value1A		OBJECT-TYPE
			SYNTAX	INTEGER
			ACCESS	read-only
			STATUS	current
	DESCRIPTION ""
			::= { mbus82 59 }

mbus82VIF1B		OBJECT-TYPE
			SYNTAX	INTEGER
			ACCESS	read-only
			STATUS	current
	DESCRIPTION ""
			::= { mbus82 60 }

mbus82Value1B		OBJECT-TYPE
			SYNTAX	INTEGER
			ACCESS	read-only
			STATUS	current
	DESCRIPTION ""
			::= { mbus82 61 }

mbus82VIF1C		OBJECT-TYPE
			SYNTAX	INTEGER
			ACCESS	read-only
			STATUS	current
	DESCRIPTION ""
			::= { mbus82 62 }

mbus82Value1C		OBJECT-TYPE
			SYNTAX	INTEGER
			ACCESS	read-only
			STATUS	current
	DESCRIPTION ""
			::= { mbus82 63 }

mbus82VIF1D		OBJECT-TYPE
			SYNTAX	INTEGER
			ACCESS	read-only
			STATUS	current
	DESCRIPTION ""
			::= { mbus82 64 }

mbus82Value1D		OBJECT-TYPE
			SYNTAX	INTEGER
			ACCESS	read-only
			STATUS	current
	DESCRIPTION ""
			::= { mbus82 65 }

mbus82VIF1E		OBJECT-TYPE
			SYNTAX	INTEGER
			ACCESS	read-only
			STATUS	current
	DESCRIPTION ""
			::= { mbus82 66 }

mbus82Value1E		OBJECT-TYPE
			SYNTAX	INTEGER
			ACCESS	read-only
			STATUS	current
	DESCRIPTION ""
			::= { mbus82 67 }

mbus82VIF1F		OBJECT-TYPE
			SYNTAX	INTEGER
			ACCESS	read-only
			STATUS	current
	DESCRIPTION ""
			::= { mbus82 68 }

mbus82Value1F		OBJECT-TYPE
			SYNTAX	INTEGER
			ACCESS	read-only
			STATUS	current
	DESCRIPTION ""
			::= { mbus82 69 }

mbus82VIF20		OBJECT-TYPE
			SYNTAX	INTEGER
			ACCESS	read-only
			STATUS	current
	DESCRIPTION ""
			::= { mbus82 70 }

mbus82Value20		OBJECT-TYPE
			SYNTAX	INTEGER
			ACCESS	read-only
			STATUS	current
	DESCRIPTION ""
			::= { mbus82 71 }

mbus82VIF21		OBJECT-TYPE
			SYNTAX	INTEGER
			ACCESS	read-only
			STATUS	current
	DESCRIPTION ""
			::= { mbus82 72 }

mbus82Value21		OBJECT-TYPE
			SYNTAX	INTEGER
			ACCESS	read-only
			STATUS	current
	DESCRIPTION ""
			::= { mbus82 73 }

mbus82VIF22		OBJECT-TYPE
			SYNTAX	INTEGER
			ACCESS	read-only
			STATUS	current
	DESCRIPTION ""
			::= { mbus82 74 }

mbus82Value22		OBJECT-TYPE
			SYNTAX	INTEGER
			ACCESS	read-only
			STATUS	current
	DESCRIPTION ""
			::= { mbus82 75 }

mbus82VIF23		OBJECT-TYPE
			SYNTAX	INTEGER
			ACCESS	read-only
			STATUS	current
	DESCRIPTION ""
			::= { mbus82 76 }

mbus82Value23		OBJECT-TYPE
			SYNTAX	INTEGER
			ACCESS	read-only
			STATUS	current
	DESCRIPTION ""
			::= { mbus82 77 }

mbus82VIF24		OBJECT-TYPE
			SYNTAX	INTEGER
			ACCESS	read-only
			STATUS	current
	DESCRIPTION ""
			::= { mbus82 78 }

mbus82Value24		OBJECT-TYPE
			SYNTAX	INTEGER
			ACCESS	read-only
			STATUS	current
	DESCRIPTION ""
			::= { mbus82 79 }

mbus82VIF25		OBJECT-TYPE
			SYNTAX	INTEGER
			ACCESS	read-only
			STATUS	current
	DESCRIPTION ""
			::= { mbus82 80 }

mbus82Value25		OBJECT-TYPE
			SYNTAX	INTEGER
			ACCESS	read-only
			STATUS	current
	DESCRIPTION ""
			::= { mbus82 81 }

mbus82VIF26		OBJECT-TYPE
			SYNTAX	INTEGER
			ACCESS	read-only
			STATUS	current
	DESCRIPTION ""
			::= { mbus82 82 }

mbus82Value26		OBJECT-TYPE
			SYNTAX	INTEGER
			ACCESS	read-only
			STATUS	current
	DESCRIPTION ""
			::= { mbus82 83 }

mbus82VIF27		OBJECT-TYPE
			SYNTAX	INTEGER
			ACCESS	read-only
			STATUS	current
	DESCRIPTION ""
			::= { mbus82 84 }

mbus82Value27		OBJECT-TYPE
			SYNTAX	INTEGER
			ACCESS	read-only
			STATUS	current
	DESCRIPTION ""
			::= { mbus82 85 }

mbus82VIF28		OBJECT-TYPE
			SYNTAX	INTEGER
			ACCESS	read-only
			STATUS	current
	DESCRIPTION ""
			::= { mbus82 86 }

mbus82Value28		OBJECT-TYPE
			SYNTAX	INTEGER
			ACCESS	read-only
			STATUS	current
	DESCRIPTION ""
			::= { mbus82 87 }

mbus82VIF29		OBJECT-TYPE
			SYNTAX	INTEGER
			ACCESS	read-only
			STATUS	current
	DESCRIPTION ""
			::= { mbus82 88 }

mbus82Value29		OBJECT-TYPE
			SYNTAX	INTEGER
			ACCESS	read-only
			STATUS	current
	DESCRIPTION ""
			::= { mbus82 89 }

mbus82VIF2A		OBJECT-TYPE
			SYNTAX	INTEGER
			ACCESS	read-only
			STATUS	current
	DESCRIPTION ""
			::= { mbus82 90 }

mbus82Value2A		OBJECT-TYPE
			SYNTAX	INTEGER
			ACCESS	read-only
			STATUS	current
	DESCRIPTION ""
			::= { mbus82 91 }

mbus82VIF2B		OBJECT-TYPE
			SYNTAX	INTEGER
			ACCESS	read-only
			STATUS	current
	DESCRIPTION ""
			::= { mbus82 92 }

mbus82Value2B		OBJECT-TYPE
			SYNTAX	INTEGER
			ACCESS	read-only
			STATUS	current
	DESCRIPTION ""
			::= { mbus82 93 }

mbus82VIF2C		OBJECT-TYPE
			SYNTAX	INTEGER
			ACCESS	read-only
			STATUS	current
	DESCRIPTION ""
			::= { mbus82 94 }

mbus82Value2C		OBJECT-TYPE
			SYNTAX	INTEGER
			ACCESS	read-only
			STATUS	current
	DESCRIPTION ""
			::= { mbus82 95 }

mbus82VIF2D		OBJECT-TYPE
			SYNTAX	INTEGER
			ACCESS	read-only
			STATUS	current
	DESCRIPTION ""
			::= { mbus82 96 }

mbus82Value2D		OBJECT-TYPE
			SYNTAX	INTEGER
			ACCESS	read-only
			STATUS	current
	DESCRIPTION ""
			::= { mbus82 97 }

mbus82VIF2E		OBJECT-TYPE
			SYNTAX	INTEGER
			ACCESS	read-only
			STATUS	current
	DESCRIPTION ""
			::= { mbus82 98 }

mbus82Value2E		OBJECT-TYPE
			SYNTAX	INTEGER
			ACCESS	read-only
			STATUS	current
	DESCRIPTION ""
			::= { mbus82 99 }

mbus82VIF2F		OBJECT-TYPE
			SYNTAX	INTEGER
			ACCESS	read-only
			STATUS	current
	DESCRIPTION ""
			::= { mbus82 100 }

mbus82Value2F		OBJECT-TYPE
			SYNTAX	INTEGER
			ACCESS	read-only
			STATUS	current
	DESCRIPTION ""
			::= { mbus82 101 }

mbus83			OBJECT IDENTIFIER ::= { mbus 131 }

mbus83IdNumber		OBJECT-TYPE
			SYNTAX	Gauge
			ACCESS	read-only
			STATUS	current
	DESCRIPTION ""
			::= { mbus83 1 }

mbus83Manufacturer	OBJECT-TYPE
			SYNTAX	Gauge
			ACCESS	read-only
			STATUS	current
	DESCRIPTION ""
			::= { mbus83 2 }

mbus83Version		OBJECT-TYPE
			SYNTAX	Gauge
			ACCESS	read-only
			STATUS	current
	DESCRIPTION ""
			::= { mbus83 3 }

mbus83Medium		OBJECT-TYPE
			SYNTAX	Gauge
			ACCESS	read-only
			STATUS	current
	DESCRIPTION ""
			::= { mbus83 4 }

mbus83Status		OBJECT-TYPE
			SYNTAX	Gauge
			ACCESS	read-only
			STATUS	current
	DESCRIPTION ""
			::= { mbus83 5 }

mbus83VIF00		OBJECT-TYPE
			SYNTAX	INTEGER
			ACCESS	read-only
			STATUS	current
	DESCRIPTION ""
			::= { mbus83 6 }

mbus83Value00		OBJECT-TYPE
			SYNTAX	INTEGER
			ACCESS	read-only
			STATUS	current
	DESCRIPTION ""
			::= { mbus83 7 }

mbus83VIF01		OBJECT-TYPE
			SYNTAX	INTEGER
			ACCESS	read-only
			STATUS	current
	DESCRIPTION ""
			::= { mbus83 8 }

mbus83Value01		OBJECT-TYPE
			SYNTAX	INTEGER
			ACCESS	read-only
			STATUS	current
	DESCRIPTION ""
			::= { mbus83 9 }

mbus83VIF02		OBJECT-TYPE
			SYNTAX	INTEGER
			ACCESS	read-only
			STATUS	current
	DESCRIPTION ""
			::= { mbus83 10 }

mbus83Value02		OBJECT-TYPE
			SYNTAX	INTEGER
			ACCESS	read-only
			STATUS	current
	DESCRIPTION ""
			::= { mbus83 11 }

mbus83VIF03		OBJECT-TYPE
			SYNTAX	INTEGER
			ACCESS	read-only
			STATUS	current
	DESCRIPTION ""
			::= { mbus83 12 }

mbus83Value03		OBJECT-TYPE
			SYNTAX	INTEGER
			ACCESS	read-only
			STATUS	current
	DESCRIPTION ""
			::= { mbus83 13 }

mbus83VIF04		OBJECT-TYPE
			SYNTAX	INTEGER
			ACCESS	read-only
			STATUS	current
	DESCRIPTION ""
			::= { mbus83 14 }

mbus83Value04		OBJECT-TYPE
			SYNTAX	INTEGER
			ACCESS	read-only
			STATUS	current
	DESCRIPTION ""
			::= { mbus83 15 }

mbus83VIF05		OBJECT-TYPE
			SYNTAX	INTEGER
			ACCESS	read-only
			STATUS	current
	DESCRIPTION ""
			::= { mbus83 16 }

mbus83Value05		OBJECT-TYPE
			SYNTAX	INTEGER
			ACCESS	read-only
			STATUS	current
	DESCRIPTION ""
			::= { mbus83 17 }

mbus83VIF06		OBJECT-TYPE
			SYNTAX	INTEGER
			ACCESS	read-only
			STATUS	current
	DESCRIPTION ""
			::= { mbus83 18 }

mbus83Value06		OBJECT-TYPE
			SYNTAX	INTEGER
			ACCESS	read-only
			STATUS	current
	DESCRIPTION ""
			::= { mbus83 19 }

mbus83VIF07		OBJECT-TYPE
			SYNTAX	INTEGER
			ACCESS	read-only
			STATUS	current
	DESCRIPTION ""
			::= { mbus83 20 }

mbus83Value07		OBJECT-TYPE
			SYNTAX	INTEGER
			ACCESS	read-only
			STATUS	current
	DESCRIPTION ""
			::= { mbus83 21 }

mbus83VIF08		OBJECT-TYPE
			SYNTAX	INTEGER
			ACCESS	read-only
			STATUS	current
	DESCRIPTION ""
			::= { mbus83 22 }

mbus83Value08		OBJECT-TYPE
			SYNTAX	INTEGER
			ACCESS	read-only
			STATUS	current
	DESCRIPTION ""
			::= { mbus83 23 }

mbus83VIF09		OBJECT-TYPE
			SYNTAX	INTEGER
			ACCESS	read-only
			STATUS	current
	DESCRIPTION ""
			::= { mbus83 24 }

mbus83Value09		OBJECT-TYPE
			SYNTAX	INTEGER
			ACCESS	read-only
			STATUS	current
	DESCRIPTION ""
			::= { mbus83 25 }

mbus83VIF0A		OBJECT-TYPE
			SYNTAX	INTEGER
			ACCESS	read-only
			STATUS	current
	DESCRIPTION ""
			::= { mbus83 26 }

mbus83Value0A		OBJECT-TYPE
			SYNTAX	INTEGER
			ACCESS	read-only
			STATUS	current
	DESCRIPTION ""
			::= { mbus83 27 }

mbus83VIF0B		OBJECT-TYPE
			SYNTAX	INTEGER
			ACCESS	read-only
			STATUS	current
	DESCRIPTION ""
			::= { mbus83 28 }

mbus83Value0B		OBJECT-TYPE
			SYNTAX	INTEGER
			ACCESS	read-only
			STATUS	current
	DESCRIPTION ""
			::= { mbus83 29 }

mbus83VIF0C		OBJECT-TYPE
			SYNTAX	INTEGER
			ACCESS	read-only
			STATUS	current
	DESCRIPTION ""
			::= { mbus83 30 }

mbus83Value0C		OBJECT-TYPE
			SYNTAX	INTEGER
			ACCESS	read-only
			STATUS	current
	DESCRIPTION ""
			::= { mbus83 31 }

mbus83VIF0D		OBJECT-TYPE
			SYNTAX	INTEGER
			ACCESS	read-only
			STATUS	current
	DESCRIPTION ""
			::= { mbus83 32 }

mbus83Value0D		OBJECT-TYPE
			SYNTAX	INTEGER
			ACCESS	read-only
			STATUS	current
	DESCRIPTION ""
			::= { mbus83 33 }

mbus83VIF0E		OBJECT-TYPE
			SYNTAX	INTEGER
			ACCESS	read-only
			STATUS	current
	DESCRIPTION ""
			::= { mbus83 34 }

mbus83Value0E		OBJECT-TYPE
			SYNTAX	INTEGER
			ACCESS	read-only
			STATUS	current
	DESCRIPTION ""
			::= { mbus83 35 }

mbus83VIF0F		OBJECT-TYPE
			SYNTAX	INTEGER
			ACCESS	read-only
			STATUS	current
	DESCRIPTION ""
			::= { mbus83 36 }

mbus83Value0F		OBJECT-TYPE
			SYNTAX	INTEGER
			ACCESS	read-only
			STATUS	current
	DESCRIPTION ""
			::= { mbus83 37 }

mbus83VIF10		OBJECT-TYPE
			SYNTAX	INTEGER
			ACCESS	read-only
			STATUS	current
	DESCRIPTION ""
			::= { mbus83 38 }

mbus83Value10		OBJECT-TYPE
			SYNTAX	INTEGER
			ACCESS	read-only
			STATUS	current
	DESCRIPTION ""
			::= { mbus83 39 }

mbus83VIF11		OBJECT-TYPE
			SYNTAX	INTEGER
			ACCESS	read-only
			STATUS	current
	DESCRIPTION ""
			::= { mbus83 40 }

mbus83Value11		OBJECT-TYPE
			SYNTAX	INTEGER
			ACCESS	read-only
			STATUS	current
	DESCRIPTION ""
			::= { mbus83 41 }

mbus83VIF12		OBJECT-TYPE
			SYNTAX	INTEGER
			ACCESS	read-only
			STATUS	current
	DESCRIPTION ""
			::= { mbus83 42 }

mbus83Value12		OBJECT-TYPE
			SYNTAX	INTEGER
			ACCESS	read-only
			STATUS	current
	DESCRIPTION ""
			::= { mbus83 43 }

mbus83VIF13		OBJECT-TYPE
			SYNTAX	INTEGER
			ACCESS	read-only
			STATUS	current
	DESCRIPTION ""
			::= { mbus83 44 }

mbus83Value13		OBJECT-TYPE
			SYNTAX	INTEGER
			ACCESS	read-only
			STATUS	current
	DESCRIPTION ""
			::= { mbus83 45 }

mbus83VIF14		OBJECT-TYPE
			SYNTAX	INTEGER
			ACCESS	read-only
			STATUS	current
	DESCRIPTION ""
			::= { mbus83 46 }

mbus83Value14		OBJECT-TYPE
			SYNTAX	INTEGER
			ACCESS	read-only
			STATUS	current
	DESCRIPTION ""
			::= { mbus83 47 }

mbus83VIF15		OBJECT-TYPE
			SYNTAX	INTEGER
			ACCESS	read-only
			STATUS	current
	DESCRIPTION ""
			::= { mbus83 48 }

mbus83Value15		OBJECT-TYPE
			SYNTAX	INTEGER
			ACCESS	read-only
			STATUS	current
	DESCRIPTION ""
			::= { mbus83 49 }

mbus83VIF16		OBJECT-TYPE
			SYNTAX	INTEGER
			ACCESS	read-only
			STATUS	current
	DESCRIPTION ""
			::= { mbus83 50 }

mbus83Value16		OBJECT-TYPE
			SYNTAX	INTEGER
			ACCESS	read-only
			STATUS	current
	DESCRIPTION ""
			::= { mbus83 51 }

mbus83VIF17		OBJECT-TYPE
			SYNTAX	INTEGER
			ACCESS	read-only
			STATUS	current
	DESCRIPTION ""
			::= { mbus83 52 }

mbus83Value17		OBJECT-TYPE
			SYNTAX	INTEGER
			ACCESS	read-only
			STATUS	current
	DESCRIPTION ""
			::= { mbus83 53 }

mbus83VIF18		OBJECT-TYPE
			SYNTAX	INTEGER
			ACCESS	read-only
			STATUS	current
	DESCRIPTION ""
			::= { mbus83 54 }

mbus83Value18		OBJECT-TYPE
			SYNTAX	INTEGER
			ACCESS	read-only
			STATUS	current
	DESCRIPTION ""
			::= { mbus83 55 }

mbus83VIF19		OBJECT-TYPE
			SYNTAX	INTEGER
			ACCESS	read-only
			STATUS	current
	DESCRIPTION ""
			::= { mbus83 56 }

mbus83Value19		OBJECT-TYPE
			SYNTAX	INTEGER
			ACCESS	read-only
			STATUS	current
	DESCRIPTION ""
			::= { mbus83 57 }

mbus83VIF1A		OBJECT-TYPE
			SYNTAX	INTEGER
			ACCESS	read-only
			STATUS	current
	DESCRIPTION ""
			::= { mbus83 58 }

mbus83Value1A		OBJECT-TYPE
			SYNTAX	INTEGER
			ACCESS	read-only
			STATUS	current
	DESCRIPTION ""
			::= { mbus83 59 }

mbus83VIF1B		OBJECT-TYPE
			SYNTAX	INTEGER
			ACCESS	read-only
			STATUS	current
	DESCRIPTION ""
			::= { mbus83 60 }

mbus83Value1B		OBJECT-TYPE
			SYNTAX	INTEGER
			ACCESS	read-only
			STATUS	current
	DESCRIPTION ""
			::= { mbus83 61 }

mbus83VIF1C		OBJECT-TYPE
			SYNTAX	INTEGER
			ACCESS	read-only
			STATUS	current
	DESCRIPTION ""
			::= { mbus83 62 }

mbus83Value1C		OBJECT-TYPE
			SYNTAX	INTEGER
			ACCESS	read-only
			STATUS	current
	DESCRIPTION ""
			::= { mbus83 63 }

mbus83VIF1D		OBJECT-TYPE
			SYNTAX	INTEGER
			ACCESS	read-only
			STATUS	current
	DESCRIPTION ""
			::= { mbus83 64 }

mbus83Value1D		OBJECT-TYPE
			SYNTAX	INTEGER
			ACCESS	read-only
			STATUS	current
	DESCRIPTION ""
			::= { mbus83 65 }

mbus83VIF1E		OBJECT-TYPE
			SYNTAX	INTEGER
			ACCESS	read-only
			STATUS	current
	DESCRIPTION ""
			::= { mbus83 66 }

mbus83Value1E		OBJECT-TYPE
			SYNTAX	INTEGER
			ACCESS	read-only
			STATUS	current
	DESCRIPTION ""
			::= { mbus83 67 }

mbus83VIF1F		OBJECT-TYPE
			SYNTAX	INTEGER
			ACCESS	read-only
			STATUS	current
	DESCRIPTION ""
			::= { mbus83 68 }

mbus83Value1F		OBJECT-TYPE
			SYNTAX	INTEGER
			ACCESS	read-only
			STATUS	current
	DESCRIPTION ""
			::= { mbus83 69 }

mbus83VIF20		OBJECT-TYPE
			SYNTAX	INTEGER
			ACCESS	read-only
			STATUS	current
	DESCRIPTION ""
			::= { mbus83 70 }

mbus83Value20		OBJECT-TYPE
			SYNTAX	INTEGER
			ACCESS	read-only
			STATUS	current
	DESCRIPTION ""
			::= { mbus83 71 }

mbus83VIF21		OBJECT-TYPE
			SYNTAX	INTEGER
			ACCESS	read-only
			STATUS	current
	DESCRIPTION ""
			::= { mbus83 72 }

mbus83Value21		OBJECT-TYPE
			SYNTAX	INTEGER
			ACCESS	read-only
			STATUS	current
	DESCRIPTION ""
			::= { mbus83 73 }

mbus83VIF22		OBJECT-TYPE
			SYNTAX	INTEGER
			ACCESS	read-only
			STATUS	current
	DESCRIPTION ""
			::= { mbus83 74 }

mbus83Value22		OBJECT-TYPE
			SYNTAX	INTEGER
			ACCESS	read-only
			STATUS	current
	DESCRIPTION ""
			::= { mbus83 75 }

mbus83VIF23		OBJECT-TYPE
			SYNTAX	INTEGER
			ACCESS	read-only
			STATUS	current
	DESCRIPTION ""
			::= { mbus83 76 }

mbus83Value23		OBJECT-TYPE
			SYNTAX	INTEGER
			ACCESS	read-only
			STATUS	current
	DESCRIPTION ""
			::= { mbus83 77 }

mbus83VIF24		OBJECT-TYPE
			SYNTAX	INTEGER
			ACCESS	read-only
			STATUS	current
	DESCRIPTION ""
			::= { mbus83 78 }

mbus83Value24		OBJECT-TYPE
			SYNTAX	INTEGER
			ACCESS	read-only
			STATUS	current
	DESCRIPTION ""
			::= { mbus83 79 }

mbus83VIF25		OBJECT-TYPE
			SYNTAX	INTEGER
			ACCESS	read-only
			STATUS	current
	DESCRIPTION ""
			::= { mbus83 80 }

mbus83Value25		OBJECT-TYPE
			SYNTAX	INTEGER
			ACCESS	read-only
			STATUS	current
	DESCRIPTION ""
			::= { mbus83 81 }

mbus83VIF26		OBJECT-TYPE
			SYNTAX	INTEGER
			ACCESS	read-only
			STATUS	current
	DESCRIPTION ""
			::= { mbus83 82 }

mbus83Value26		OBJECT-TYPE
			SYNTAX	INTEGER
			ACCESS	read-only
			STATUS	current
	DESCRIPTION ""
			::= { mbus83 83 }

mbus83VIF27		OBJECT-TYPE
			SYNTAX	INTEGER
			ACCESS	read-only
			STATUS	current
	DESCRIPTION ""
			::= { mbus83 84 }

mbus83Value27		OBJECT-TYPE
			SYNTAX	INTEGER
			ACCESS	read-only
			STATUS	current
	DESCRIPTION ""
			::= { mbus83 85 }

mbus83VIF28		OBJECT-TYPE
			SYNTAX	INTEGER
			ACCESS	read-only
			STATUS	current
	DESCRIPTION ""
			::= { mbus83 86 }

mbus83Value28		OBJECT-TYPE
			SYNTAX	INTEGER
			ACCESS	read-only
			STATUS	current
	DESCRIPTION ""
			::= { mbus83 87 }

mbus83VIF29		OBJECT-TYPE
			SYNTAX	INTEGER
			ACCESS	read-only
			STATUS	current
	DESCRIPTION ""
			::= { mbus83 88 }

mbus83Value29		OBJECT-TYPE
			SYNTAX	INTEGER
			ACCESS	read-only
			STATUS	current
	DESCRIPTION ""
			::= { mbus83 89 }

mbus83VIF2A		OBJECT-TYPE
			SYNTAX	INTEGER
			ACCESS	read-only
			STATUS	current
	DESCRIPTION ""
			::= { mbus83 90 }

mbus83Value2A		OBJECT-TYPE
			SYNTAX	INTEGER
			ACCESS	read-only
			STATUS	current
	DESCRIPTION ""
			::= { mbus83 91 }

mbus83VIF2B		OBJECT-TYPE
			SYNTAX	INTEGER
			ACCESS	read-only
			STATUS	current
	DESCRIPTION ""
			::= { mbus83 92 }

mbus83Value2B		OBJECT-TYPE
			SYNTAX	INTEGER
			ACCESS	read-only
			STATUS	current
	DESCRIPTION ""
			::= { mbus83 93 }

mbus83VIF2C		OBJECT-TYPE
			SYNTAX	INTEGER
			ACCESS	read-only
			STATUS	current
	DESCRIPTION ""
			::= { mbus83 94 }

mbus83Value2C		OBJECT-TYPE
			SYNTAX	INTEGER
			ACCESS	read-only
			STATUS	current
	DESCRIPTION ""
			::= { mbus83 95 }

mbus83VIF2D		OBJECT-TYPE
			SYNTAX	INTEGER
			ACCESS	read-only
			STATUS	current
	DESCRIPTION ""
			::= { mbus83 96 }

mbus83Value2D		OBJECT-TYPE
			SYNTAX	INTEGER
			ACCESS	read-only
			STATUS	current
	DESCRIPTION ""
			::= { mbus83 97 }

mbus83VIF2E		OBJECT-TYPE
			SYNTAX	INTEGER
			ACCESS	read-only
			STATUS	current
	DESCRIPTION ""
			::= { mbus83 98 }

mbus83Value2E		OBJECT-TYPE
			SYNTAX	INTEGER
			ACCESS	read-only
			STATUS	current
	DESCRIPTION ""
			::= { mbus83 99 }

mbus83VIF2F		OBJECT-TYPE
			SYNTAX	INTEGER
			ACCESS	read-only
			STATUS	current
	DESCRIPTION ""
			::= { mbus83 100 }

mbus83Value2F		OBJECT-TYPE
			SYNTAX	INTEGER
			ACCESS	read-only
			STATUS	current
	DESCRIPTION ""
			::= { mbus83 101 }

mbus84			OBJECT IDENTIFIER ::= { mbus 132 }

mbus84IdNumber		OBJECT-TYPE
			SYNTAX	Gauge
			ACCESS	read-only
			STATUS	current
	DESCRIPTION ""
			::= { mbus84 1 }

mbus84Manufacturer	OBJECT-TYPE
			SYNTAX	Gauge
			ACCESS	read-only
			STATUS	current
	DESCRIPTION ""
			::= { mbus84 2 }

mbus84Version		OBJECT-TYPE
			SYNTAX	Gauge
			ACCESS	read-only
			STATUS	current
	DESCRIPTION ""
			::= { mbus84 3 }

mbus84Medium		OBJECT-TYPE
			SYNTAX	Gauge
			ACCESS	read-only
			STATUS	current
	DESCRIPTION ""
			::= { mbus84 4 }

mbus84Status		OBJECT-TYPE
			SYNTAX	Gauge
			ACCESS	read-only
			STATUS	current
	DESCRIPTION ""
			::= { mbus84 5 }

mbus84VIF00		OBJECT-TYPE
			SYNTAX	INTEGER
			ACCESS	read-only
			STATUS	current
	DESCRIPTION ""
			::= { mbus84 6 }

mbus84Value00		OBJECT-TYPE
			SYNTAX	INTEGER
			ACCESS	read-only
			STATUS	current
	DESCRIPTION ""
			::= { mbus84 7 }

mbus84VIF01		OBJECT-TYPE
			SYNTAX	INTEGER
			ACCESS	read-only
			STATUS	current
	DESCRIPTION ""
			::= { mbus84 8 }

mbus84Value01		OBJECT-TYPE
			SYNTAX	INTEGER
			ACCESS	read-only
			STATUS	current
	DESCRIPTION ""
			::= { mbus84 9 }

mbus84VIF02		OBJECT-TYPE
			SYNTAX	INTEGER
			ACCESS	read-only
			STATUS	current
	DESCRIPTION ""
			::= { mbus84 10 }

mbus84Value02		OBJECT-TYPE
			SYNTAX	INTEGER
			ACCESS	read-only
			STATUS	current
	DESCRIPTION ""
			::= { mbus84 11 }

mbus84VIF03		OBJECT-TYPE
			SYNTAX	INTEGER
			ACCESS	read-only
			STATUS	current
	DESCRIPTION ""
			::= { mbus84 12 }

mbus84Value03		OBJECT-TYPE
			SYNTAX	INTEGER
			ACCESS	read-only
			STATUS	current
	DESCRIPTION ""
			::= { mbus84 13 }

mbus84VIF04		OBJECT-TYPE
			SYNTAX	INTEGER
			ACCESS	read-only
			STATUS	current
	DESCRIPTION ""
			::= { mbus84 14 }

mbus84Value04		OBJECT-TYPE
			SYNTAX	INTEGER
			ACCESS	read-only
			STATUS	current
	DESCRIPTION ""
			::= { mbus84 15 }

mbus84VIF05		OBJECT-TYPE
			SYNTAX	INTEGER
			ACCESS	read-only
			STATUS	current
	DESCRIPTION ""
			::= { mbus84 16 }

mbus84Value05		OBJECT-TYPE
			SYNTAX	INTEGER
			ACCESS	read-only
			STATUS	current
	DESCRIPTION ""
			::= { mbus84 17 }

mbus84VIF06		OBJECT-TYPE
			SYNTAX	INTEGER
			ACCESS	read-only
			STATUS	current
	DESCRIPTION ""
			::= { mbus84 18 }

mbus84Value06		OBJECT-TYPE
			SYNTAX	INTEGER
			ACCESS	read-only
			STATUS	current
	DESCRIPTION ""
			::= { mbus84 19 }

mbus84VIF07		OBJECT-TYPE
			SYNTAX	INTEGER
			ACCESS	read-only
			STATUS	current
	DESCRIPTION ""
			::= { mbus84 20 }

mbus84Value07		OBJECT-TYPE
			SYNTAX	INTEGER
			ACCESS	read-only
			STATUS	current
	DESCRIPTION ""
			::= { mbus84 21 }

mbus84VIF08		OBJECT-TYPE
			SYNTAX	INTEGER
			ACCESS	read-only
			STATUS	current
	DESCRIPTION ""
			::= { mbus84 22 }

mbus84Value08		OBJECT-TYPE
			SYNTAX	INTEGER
			ACCESS	read-only
			STATUS	current
	DESCRIPTION ""
			::= { mbus84 23 }

mbus84VIF09		OBJECT-TYPE
			SYNTAX	INTEGER
			ACCESS	read-only
			STATUS	current
	DESCRIPTION ""
			::= { mbus84 24 }

mbus84Value09		OBJECT-TYPE
			SYNTAX	INTEGER
			ACCESS	read-only
			STATUS	current
	DESCRIPTION ""
			::= { mbus84 25 }

mbus84VIF0A		OBJECT-TYPE
			SYNTAX	INTEGER
			ACCESS	read-only
			STATUS	current
	DESCRIPTION ""
			::= { mbus84 26 }

mbus84Value0A		OBJECT-TYPE
			SYNTAX	INTEGER
			ACCESS	read-only
			STATUS	current
	DESCRIPTION ""
			::= { mbus84 27 }

mbus84VIF0B		OBJECT-TYPE
			SYNTAX	INTEGER
			ACCESS	read-only
			STATUS	current
	DESCRIPTION ""
			::= { mbus84 28 }

mbus84Value0B		OBJECT-TYPE
			SYNTAX	INTEGER
			ACCESS	read-only
			STATUS	current
	DESCRIPTION ""
			::= { mbus84 29 }

mbus84VIF0C		OBJECT-TYPE
			SYNTAX	INTEGER
			ACCESS	read-only
			STATUS	current
	DESCRIPTION ""
			::= { mbus84 30 }

mbus84Value0C		OBJECT-TYPE
			SYNTAX	INTEGER
			ACCESS	read-only
			STATUS	current
	DESCRIPTION ""
			::= { mbus84 31 }

mbus84VIF0D		OBJECT-TYPE
			SYNTAX	INTEGER
			ACCESS	read-only
			STATUS	current
	DESCRIPTION ""
			::= { mbus84 32 }

mbus84Value0D		OBJECT-TYPE
			SYNTAX	INTEGER
			ACCESS	read-only
			STATUS	current
	DESCRIPTION ""
			::= { mbus84 33 }

mbus84VIF0E		OBJECT-TYPE
			SYNTAX	INTEGER
			ACCESS	read-only
			STATUS	current
	DESCRIPTION ""
			::= { mbus84 34 }

mbus84Value0E		OBJECT-TYPE
			SYNTAX	INTEGER
			ACCESS	read-only
			STATUS	current
	DESCRIPTION ""
			::= { mbus84 35 }

mbus84VIF0F		OBJECT-TYPE
			SYNTAX	INTEGER
			ACCESS	read-only
			STATUS	current
	DESCRIPTION ""
			::= { mbus84 36 }

mbus84Value0F		OBJECT-TYPE
			SYNTAX	INTEGER
			ACCESS	read-only
			STATUS	current
	DESCRIPTION ""
			::= { mbus84 37 }

mbus84VIF10		OBJECT-TYPE
			SYNTAX	INTEGER
			ACCESS	read-only
			STATUS	current
	DESCRIPTION ""
			::= { mbus84 38 }

mbus84Value10		OBJECT-TYPE
			SYNTAX	INTEGER
			ACCESS	read-only
			STATUS	current
	DESCRIPTION ""
			::= { mbus84 39 }

mbus84VIF11		OBJECT-TYPE
			SYNTAX	INTEGER
			ACCESS	read-only
			STATUS	current
	DESCRIPTION ""
			::= { mbus84 40 }

mbus84Value11		OBJECT-TYPE
			SYNTAX	INTEGER
			ACCESS	read-only
			STATUS	current
	DESCRIPTION ""
			::= { mbus84 41 }

mbus84VIF12		OBJECT-TYPE
			SYNTAX	INTEGER
			ACCESS	read-only
			STATUS	current
	DESCRIPTION ""
			::= { mbus84 42 }

mbus84Value12		OBJECT-TYPE
			SYNTAX	INTEGER
			ACCESS	read-only
			STATUS	current
	DESCRIPTION ""
			::= { mbus84 43 }

mbus84VIF13		OBJECT-TYPE
			SYNTAX	INTEGER
			ACCESS	read-only
			STATUS	current
	DESCRIPTION ""
			::= { mbus84 44 }

mbus84Value13		OBJECT-TYPE
			SYNTAX	INTEGER
			ACCESS	read-only
			STATUS	current
	DESCRIPTION ""
			::= { mbus84 45 }

mbus84VIF14		OBJECT-TYPE
			SYNTAX	INTEGER
			ACCESS	read-only
			STATUS	current
	DESCRIPTION ""
			::= { mbus84 46 }

mbus84Value14		OBJECT-TYPE
			SYNTAX	INTEGER
			ACCESS	read-only
			STATUS	current
	DESCRIPTION ""
			::= { mbus84 47 }

mbus84VIF15		OBJECT-TYPE
			SYNTAX	INTEGER
			ACCESS	read-only
			STATUS	current
	DESCRIPTION ""
			::= { mbus84 48 }

mbus84Value15		OBJECT-TYPE
			SYNTAX	INTEGER
			ACCESS	read-only
			STATUS	current
	DESCRIPTION ""
			::= { mbus84 49 }

mbus84VIF16		OBJECT-TYPE
			SYNTAX	INTEGER
			ACCESS	read-only
			STATUS	current
	DESCRIPTION ""
			::= { mbus84 50 }

mbus84Value16		OBJECT-TYPE
			SYNTAX	INTEGER
			ACCESS	read-only
			STATUS	current
	DESCRIPTION ""
			::= { mbus84 51 }

mbus84VIF17		OBJECT-TYPE
			SYNTAX	INTEGER
			ACCESS	read-only
			STATUS	current
	DESCRIPTION ""
			::= { mbus84 52 }

mbus84Value17		OBJECT-TYPE
			SYNTAX	INTEGER
			ACCESS	read-only
			STATUS	current
	DESCRIPTION ""
			::= { mbus84 53 }

mbus84VIF18		OBJECT-TYPE
			SYNTAX	INTEGER
			ACCESS	read-only
			STATUS	current
	DESCRIPTION ""
			::= { mbus84 54 }

mbus84Value18		OBJECT-TYPE
			SYNTAX	INTEGER
			ACCESS	read-only
			STATUS	current
	DESCRIPTION ""
			::= { mbus84 55 }

mbus84VIF19		OBJECT-TYPE
			SYNTAX	INTEGER
			ACCESS	read-only
			STATUS	current
	DESCRIPTION ""
			::= { mbus84 56 }

mbus84Value19		OBJECT-TYPE
			SYNTAX	INTEGER
			ACCESS	read-only
			STATUS	current
	DESCRIPTION ""
			::= { mbus84 57 }

mbus84VIF1A		OBJECT-TYPE
			SYNTAX	INTEGER
			ACCESS	read-only
			STATUS	current
	DESCRIPTION ""
			::= { mbus84 58 }

mbus84Value1A		OBJECT-TYPE
			SYNTAX	INTEGER
			ACCESS	read-only
			STATUS	current
	DESCRIPTION ""
			::= { mbus84 59 }

mbus84VIF1B		OBJECT-TYPE
			SYNTAX	INTEGER
			ACCESS	read-only
			STATUS	current
	DESCRIPTION ""
			::= { mbus84 60 }

mbus84Value1B		OBJECT-TYPE
			SYNTAX	INTEGER
			ACCESS	read-only
			STATUS	current
	DESCRIPTION ""
			::= { mbus84 61 }

mbus84VIF1C		OBJECT-TYPE
			SYNTAX	INTEGER
			ACCESS	read-only
			STATUS	current
	DESCRIPTION ""
			::= { mbus84 62 }

mbus84Value1C		OBJECT-TYPE
			SYNTAX	INTEGER
			ACCESS	read-only
			STATUS	current
	DESCRIPTION ""
			::= { mbus84 63 }

mbus84VIF1D		OBJECT-TYPE
			SYNTAX	INTEGER
			ACCESS	read-only
			STATUS	current
	DESCRIPTION ""
			::= { mbus84 64 }

mbus84Value1D		OBJECT-TYPE
			SYNTAX	INTEGER
			ACCESS	read-only
			STATUS	current
	DESCRIPTION ""
			::= { mbus84 65 }

mbus84VIF1E		OBJECT-TYPE
			SYNTAX	INTEGER
			ACCESS	read-only
			STATUS	current
	DESCRIPTION ""
			::= { mbus84 66 }

mbus84Value1E		OBJECT-TYPE
			SYNTAX	INTEGER
			ACCESS	read-only
			STATUS	current
	DESCRIPTION ""
			::= { mbus84 67 }

mbus84VIF1F		OBJECT-TYPE
			SYNTAX	INTEGER
			ACCESS	read-only
			STATUS	current
	DESCRIPTION ""
			::= { mbus84 68 }

mbus84Value1F		OBJECT-TYPE
			SYNTAX	INTEGER
			ACCESS	read-only
			STATUS	current
	DESCRIPTION ""
			::= { mbus84 69 }

mbus84VIF20		OBJECT-TYPE
			SYNTAX	INTEGER
			ACCESS	read-only
			STATUS	current
	DESCRIPTION ""
			::= { mbus84 70 }

mbus84Value20		OBJECT-TYPE
			SYNTAX	INTEGER
			ACCESS	read-only
			STATUS	current
	DESCRIPTION ""
			::= { mbus84 71 }

mbus84VIF21		OBJECT-TYPE
			SYNTAX	INTEGER
			ACCESS	read-only
			STATUS	current
	DESCRIPTION ""
			::= { mbus84 72 }

mbus84Value21		OBJECT-TYPE
			SYNTAX	INTEGER
			ACCESS	read-only
			STATUS	current
	DESCRIPTION ""
			::= { mbus84 73 }

mbus84VIF22		OBJECT-TYPE
			SYNTAX	INTEGER
			ACCESS	read-only
			STATUS	current
	DESCRIPTION ""
			::= { mbus84 74 }

mbus84Value22		OBJECT-TYPE
			SYNTAX	INTEGER
			ACCESS	read-only
			STATUS	current
	DESCRIPTION ""
			::= { mbus84 75 }

mbus84VIF23		OBJECT-TYPE
			SYNTAX	INTEGER
			ACCESS	read-only
			STATUS	current
	DESCRIPTION ""
			::= { mbus84 76 }

mbus84Value23		OBJECT-TYPE
			SYNTAX	INTEGER
			ACCESS	read-only
			STATUS	current
	DESCRIPTION ""
			::= { mbus84 77 }

mbus84VIF24		OBJECT-TYPE
			SYNTAX	INTEGER
			ACCESS	read-only
			STATUS	current
	DESCRIPTION ""
			::= { mbus84 78 }

mbus84Value24		OBJECT-TYPE
			SYNTAX	INTEGER
			ACCESS	read-only
			STATUS	current
	DESCRIPTION ""
			::= { mbus84 79 }

mbus84VIF25		OBJECT-TYPE
			SYNTAX	INTEGER
			ACCESS	read-only
			STATUS	current
	DESCRIPTION ""
			::= { mbus84 80 }

mbus84Value25		OBJECT-TYPE
			SYNTAX	INTEGER
			ACCESS	read-only
			STATUS	current
	DESCRIPTION ""
			::= { mbus84 81 }

mbus84VIF26		OBJECT-TYPE
			SYNTAX	INTEGER
			ACCESS	read-only
			STATUS	current
	DESCRIPTION ""
			::= { mbus84 82 }

mbus84Value26		OBJECT-TYPE
			SYNTAX	INTEGER
			ACCESS	read-only
			STATUS	current
	DESCRIPTION ""
			::= { mbus84 83 }

mbus84VIF27		OBJECT-TYPE
			SYNTAX	INTEGER
			ACCESS	read-only
			STATUS	current
	DESCRIPTION ""
			::= { mbus84 84 }

mbus84Value27		OBJECT-TYPE
			SYNTAX	INTEGER
			ACCESS	read-only
			STATUS	current
	DESCRIPTION ""
			::= { mbus84 85 }

mbus84VIF28		OBJECT-TYPE
			SYNTAX	INTEGER
			ACCESS	read-only
			STATUS	current
	DESCRIPTION ""
			::= { mbus84 86 }

mbus84Value28		OBJECT-TYPE
			SYNTAX	INTEGER
			ACCESS	read-only
			STATUS	current
	DESCRIPTION ""
			::= { mbus84 87 }

mbus84VIF29		OBJECT-TYPE
			SYNTAX	INTEGER
			ACCESS	read-only
			STATUS	current
	DESCRIPTION ""
			::= { mbus84 88 }

mbus84Value29		OBJECT-TYPE
			SYNTAX	INTEGER
			ACCESS	read-only
			STATUS	current
	DESCRIPTION ""
			::= { mbus84 89 }

mbus84VIF2A		OBJECT-TYPE
			SYNTAX	INTEGER
			ACCESS	read-only
			STATUS	current
	DESCRIPTION ""
			::= { mbus84 90 }

mbus84Value2A		OBJECT-TYPE
			SYNTAX	INTEGER
			ACCESS	read-only
			STATUS	current
	DESCRIPTION ""
			::= { mbus84 91 }

mbus84VIF2B		OBJECT-TYPE
			SYNTAX	INTEGER
			ACCESS	read-only
			STATUS	current
	DESCRIPTION ""
			::= { mbus84 92 }

mbus84Value2B		OBJECT-TYPE
			SYNTAX	INTEGER
			ACCESS	read-only
			STATUS	current
	DESCRIPTION ""
			::= { mbus84 93 }

mbus84VIF2C		OBJECT-TYPE
			SYNTAX	INTEGER
			ACCESS	read-only
			STATUS	current
	DESCRIPTION ""
			::= { mbus84 94 }

mbus84Value2C		OBJECT-TYPE
			SYNTAX	INTEGER
			ACCESS	read-only
			STATUS	current
	DESCRIPTION ""
			::= { mbus84 95 }

mbus84VIF2D		OBJECT-TYPE
			SYNTAX	INTEGER
			ACCESS	read-only
			STATUS	current
	DESCRIPTION ""
			::= { mbus84 96 }

mbus84Value2D		OBJECT-TYPE
			SYNTAX	INTEGER
			ACCESS	read-only
			STATUS	current
	DESCRIPTION ""
			::= { mbus84 97 }

mbus84VIF2E		OBJECT-TYPE
			SYNTAX	INTEGER
			ACCESS	read-only
			STATUS	current
	DESCRIPTION ""
			::= { mbus84 98 }

mbus84Value2E		OBJECT-TYPE
			SYNTAX	INTEGER
			ACCESS	read-only
			STATUS	current
	DESCRIPTION ""
			::= { mbus84 99 }

mbus84VIF2F		OBJECT-TYPE
			SYNTAX	INTEGER
			ACCESS	read-only
			STATUS	current
	DESCRIPTION ""
			::= { mbus84 100 }

mbus84Value2F		OBJECT-TYPE
			SYNTAX	INTEGER
			ACCESS	read-only
			STATUS	current
	DESCRIPTION ""
			::= { mbus84 101 }

mbus85			OBJECT IDENTIFIER ::= { mbus 133 }

mbus85IdNumber		OBJECT-TYPE
			SYNTAX	Gauge
			ACCESS	read-only
			STATUS	current
	DESCRIPTION ""
			::= { mbus85 1 }

mbus85Manufacturer	OBJECT-TYPE
			SYNTAX	Gauge
			ACCESS	read-only
			STATUS	current
	DESCRIPTION ""
			::= { mbus85 2 }

mbus85Version		OBJECT-TYPE
			SYNTAX	Gauge
			ACCESS	read-only
			STATUS	current
	DESCRIPTION ""
			::= { mbus85 3 }

mbus85Medium		OBJECT-TYPE
			SYNTAX	Gauge
			ACCESS	read-only
			STATUS	current
	DESCRIPTION ""
			::= { mbus85 4 }

mbus85Status		OBJECT-TYPE
			SYNTAX	Gauge
			ACCESS	read-only
			STATUS	current
	DESCRIPTION ""
			::= { mbus85 5 }

mbus85VIF00		OBJECT-TYPE
			SYNTAX	INTEGER
			ACCESS	read-only
			STATUS	current
	DESCRIPTION ""
			::= { mbus85 6 }

mbus85Value00		OBJECT-TYPE
			SYNTAX	INTEGER
			ACCESS	read-only
			STATUS	current
	DESCRIPTION ""
			::= { mbus85 7 }

mbus85VIF01		OBJECT-TYPE
			SYNTAX	INTEGER
			ACCESS	read-only
			STATUS	current
	DESCRIPTION ""
			::= { mbus85 8 }

mbus85Value01		OBJECT-TYPE
			SYNTAX	INTEGER
			ACCESS	read-only
			STATUS	current
	DESCRIPTION ""
			::= { mbus85 9 }

mbus85VIF02		OBJECT-TYPE
			SYNTAX	INTEGER
			ACCESS	read-only
			STATUS	current
	DESCRIPTION ""
			::= { mbus85 10 }

mbus85Value02		OBJECT-TYPE
			SYNTAX	INTEGER
			ACCESS	read-only
			STATUS	current
	DESCRIPTION ""
			::= { mbus85 11 }

mbus85VIF03		OBJECT-TYPE
			SYNTAX	INTEGER
			ACCESS	read-only
			STATUS	current
	DESCRIPTION ""
			::= { mbus85 12 }

mbus85Value03		OBJECT-TYPE
			SYNTAX	INTEGER
			ACCESS	read-only
			STATUS	current
	DESCRIPTION ""
			::= { mbus85 13 }

mbus85VIF04		OBJECT-TYPE
			SYNTAX	INTEGER
			ACCESS	read-only
			STATUS	current
	DESCRIPTION ""
			::= { mbus85 14 }

mbus85Value04		OBJECT-TYPE
			SYNTAX	INTEGER
			ACCESS	read-only
			STATUS	current
	DESCRIPTION ""
			::= { mbus85 15 }

mbus85VIF05		OBJECT-TYPE
			SYNTAX	INTEGER
			ACCESS	read-only
			STATUS	current
	DESCRIPTION ""
			::= { mbus85 16 }

mbus85Value05		OBJECT-TYPE
			SYNTAX	INTEGER
			ACCESS	read-only
			STATUS	current
	DESCRIPTION ""
			::= { mbus85 17 }

mbus85VIF06		OBJECT-TYPE
			SYNTAX	INTEGER
			ACCESS	read-only
			STATUS	current
	DESCRIPTION ""
			::= { mbus85 18 }

mbus85Value06		OBJECT-TYPE
			SYNTAX	INTEGER
			ACCESS	read-only
			STATUS	current
	DESCRIPTION ""
			::= { mbus85 19 }

mbus85VIF07		OBJECT-TYPE
			SYNTAX	INTEGER
			ACCESS	read-only
			STATUS	current
	DESCRIPTION ""
			::= { mbus85 20 }

mbus85Value07		OBJECT-TYPE
			SYNTAX	INTEGER
			ACCESS	read-only
			STATUS	current
	DESCRIPTION ""
			::= { mbus85 21 }

mbus85VIF08		OBJECT-TYPE
			SYNTAX	INTEGER
			ACCESS	read-only
			STATUS	current
	DESCRIPTION ""
			::= { mbus85 22 }

mbus85Value08		OBJECT-TYPE
			SYNTAX	INTEGER
			ACCESS	read-only
			STATUS	current
	DESCRIPTION ""
			::= { mbus85 23 }

mbus85VIF09		OBJECT-TYPE
			SYNTAX	INTEGER
			ACCESS	read-only
			STATUS	current
	DESCRIPTION ""
			::= { mbus85 24 }

mbus85Value09		OBJECT-TYPE
			SYNTAX	INTEGER
			ACCESS	read-only
			STATUS	current
	DESCRIPTION ""
			::= { mbus85 25 }

mbus85VIF0A		OBJECT-TYPE
			SYNTAX	INTEGER
			ACCESS	read-only
			STATUS	current
	DESCRIPTION ""
			::= { mbus85 26 }

mbus85Value0A		OBJECT-TYPE
			SYNTAX	INTEGER
			ACCESS	read-only
			STATUS	current
	DESCRIPTION ""
			::= { mbus85 27 }

mbus85VIF0B		OBJECT-TYPE
			SYNTAX	INTEGER
			ACCESS	read-only
			STATUS	current
	DESCRIPTION ""
			::= { mbus85 28 }

mbus85Value0B		OBJECT-TYPE
			SYNTAX	INTEGER
			ACCESS	read-only
			STATUS	current
	DESCRIPTION ""
			::= { mbus85 29 }

mbus85VIF0C		OBJECT-TYPE
			SYNTAX	INTEGER
			ACCESS	read-only
			STATUS	current
	DESCRIPTION ""
			::= { mbus85 30 }

mbus85Value0C		OBJECT-TYPE
			SYNTAX	INTEGER
			ACCESS	read-only
			STATUS	current
	DESCRIPTION ""
			::= { mbus85 31 }

mbus85VIF0D		OBJECT-TYPE
			SYNTAX	INTEGER
			ACCESS	read-only
			STATUS	current
	DESCRIPTION ""
			::= { mbus85 32 }

mbus85Value0D		OBJECT-TYPE
			SYNTAX	INTEGER
			ACCESS	read-only
			STATUS	current
	DESCRIPTION ""
			::= { mbus85 33 }

mbus85VIF0E		OBJECT-TYPE
			SYNTAX	INTEGER
			ACCESS	read-only
			STATUS	current
	DESCRIPTION ""
			::= { mbus85 34 }

mbus85Value0E		OBJECT-TYPE
			SYNTAX	INTEGER
			ACCESS	read-only
			STATUS	current
	DESCRIPTION ""
			::= { mbus85 35 }

mbus85VIF0F		OBJECT-TYPE
			SYNTAX	INTEGER
			ACCESS	read-only
			STATUS	current
	DESCRIPTION ""
			::= { mbus85 36 }

mbus85Value0F		OBJECT-TYPE
			SYNTAX	INTEGER
			ACCESS	read-only
			STATUS	current
	DESCRIPTION ""
			::= { mbus85 37 }

mbus85VIF10		OBJECT-TYPE
			SYNTAX	INTEGER
			ACCESS	read-only
			STATUS	current
	DESCRIPTION ""
			::= { mbus85 38 }

mbus85Value10		OBJECT-TYPE
			SYNTAX	INTEGER
			ACCESS	read-only
			STATUS	current
	DESCRIPTION ""
			::= { mbus85 39 }

mbus85VIF11		OBJECT-TYPE
			SYNTAX	INTEGER
			ACCESS	read-only
			STATUS	current
	DESCRIPTION ""
			::= { mbus85 40 }

mbus85Value11		OBJECT-TYPE
			SYNTAX	INTEGER
			ACCESS	read-only
			STATUS	current
	DESCRIPTION ""
			::= { mbus85 41 }

mbus85VIF12		OBJECT-TYPE
			SYNTAX	INTEGER
			ACCESS	read-only
			STATUS	current
	DESCRIPTION ""
			::= { mbus85 42 }

mbus85Value12		OBJECT-TYPE
			SYNTAX	INTEGER
			ACCESS	read-only
			STATUS	current
	DESCRIPTION ""
			::= { mbus85 43 }

mbus85VIF13		OBJECT-TYPE
			SYNTAX	INTEGER
			ACCESS	read-only
			STATUS	current
	DESCRIPTION ""
			::= { mbus85 44 }

mbus85Value13		OBJECT-TYPE
			SYNTAX	INTEGER
			ACCESS	read-only
			STATUS	current
	DESCRIPTION ""
			::= { mbus85 45 }

mbus85VIF14		OBJECT-TYPE
			SYNTAX	INTEGER
			ACCESS	read-only
			STATUS	current
	DESCRIPTION ""
			::= { mbus85 46 }

mbus85Value14		OBJECT-TYPE
			SYNTAX	INTEGER
			ACCESS	read-only
			STATUS	current
	DESCRIPTION ""
			::= { mbus85 47 }

mbus85VIF15		OBJECT-TYPE
			SYNTAX	INTEGER
			ACCESS	read-only
			STATUS	current
	DESCRIPTION ""
			::= { mbus85 48 }

mbus85Value15		OBJECT-TYPE
			SYNTAX	INTEGER
			ACCESS	read-only
			STATUS	current
	DESCRIPTION ""
			::= { mbus85 49 }

mbus85VIF16		OBJECT-TYPE
			SYNTAX	INTEGER
			ACCESS	read-only
			STATUS	current
	DESCRIPTION ""
			::= { mbus85 50 }

mbus85Value16		OBJECT-TYPE
			SYNTAX	INTEGER
			ACCESS	read-only
			STATUS	current
	DESCRIPTION ""
			::= { mbus85 51 }

mbus85VIF17		OBJECT-TYPE
			SYNTAX	INTEGER
			ACCESS	read-only
			STATUS	current
	DESCRIPTION ""
			::= { mbus85 52 }

mbus85Value17		OBJECT-TYPE
			SYNTAX	INTEGER
			ACCESS	read-only
			STATUS	current
	DESCRIPTION ""
			::= { mbus85 53 }

mbus85VIF18		OBJECT-TYPE
			SYNTAX	INTEGER
			ACCESS	read-only
			STATUS	current
	DESCRIPTION ""
			::= { mbus85 54 }

mbus85Value18		OBJECT-TYPE
			SYNTAX	INTEGER
			ACCESS	read-only
			STATUS	current
	DESCRIPTION ""
			::= { mbus85 55 }

mbus85VIF19		OBJECT-TYPE
			SYNTAX	INTEGER
			ACCESS	read-only
			STATUS	current
	DESCRIPTION ""
			::= { mbus85 56 }

mbus85Value19		OBJECT-TYPE
			SYNTAX	INTEGER
			ACCESS	read-only
			STATUS	current
	DESCRIPTION ""
			::= { mbus85 57 }

mbus85VIF1A		OBJECT-TYPE
			SYNTAX	INTEGER
			ACCESS	read-only
			STATUS	current
	DESCRIPTION ""
			::= { mbus85 58 }

mbus85Value1A		OBJECT-TYPE
			SYNTAX	INTEGER
			ACCESS	read-only
			STATUS	current
	DESCRIPTION ""
			::= { mbus85 59 }

mbus85VIF1B		OBJECT-TYPE
			SYNTAX	INTEGER
			ACCESS	read-only
			STATUS	current
	DESCRIPTION ""
			::= { mbus85 60 }

mbus85Value1B		OBJECT-TYPE
			SYNTAX	INTEGER
			ACCESS	read-only
			STATUS	current
	DESCRIPTION ""
			::= { mbus85 61 }

mbus85VIF1C		OBJECT-TYPE
			SYNTAX	INTEGER
			ACCESS	read-only
			STATUS	current
	DESCRIPTION ""
			::= { mbus85 62 }

mbus85Value1C		OBJECT-TYPE
			SYNTAX	INTEGER
			ACCESS	read-only
			STATUS	current
	DESCRIPTION ""
			::= { mbus85 63 }

mbus85VIF1D		OBJECT-TYPE
			SYNTAX	INTEGER
			ACCESS	read-only
			STATUS	current
	DESCRIPTION ""
			::= { mbus85 64 }

mbus85Value1D		OBJECT-TYPE
			SYNTAX	INTEGER
			ACCESS	read-only
			STATUS	current
	DESCRIPTION ""
			::= { mbus85 65 }

mbus85VIF1E		OBJECT-TYPE
			SYNTAX	INTEGER
			ACCESS	read-only
			STATUS	current
	DESCRIPTION ""
			::= { mbus85 66 }

mbus85Value1E		OBJECT-TYPE
			SYNTAX	INTEGER
			ACCESS	read-only
			STATUS	current
	DESCRIPTION ""
			::= { mbus85 67 }

mbus85VIF1F		OBJECT-TYPE
			SYNTAX	INTEGER
			ACCESS	read-only
			STATUS	current
	DESCRIPTION ""
			::= { mbus85 68 }

mbus85Value1F		OBJECT-TYPE
			SYNTAX	INTEGER
			ACCESS	read-only
			STATUS	current
	DESCRIPTION ""
			::= { mbus85 69 }

mbus85VIF20		OBJECT-TYPE
			SYNTAX	INTEGER
			ACCESS	read-only
			STATUS	current
	DESCRIPTION ""
			::= { mbus85 70 }

mbus85Value20		OBJECT-TYPE
			SYNTAX	INTEGER
			ACCESS	read-only
			STATUS	current
	DESCRIPTION ""
			::= { mbus85 71 }

mbus85VIF21		OBJECT-TYPE
			SYNTAX	INTEGER
			ACCESS	read-only
			STATUS	current
	DESCRIPTION ""
			::= { mbus85 72 }

mbus85Value21		OBJECT-TYPE
			SYNTAX	INTEGER
			ACCESS	read-only
			STATUS	current
	DESCRIPTION ""
			::= { mbus85 73 }

mbus85VIF22		OBJECT-TYPE
			SYNTAX	INTEGER
			ACCESS	read-only
			STATUS	current
	DESCRIPTION ""
			::= { mbus85 74 }

mbus85Value22		OBJECT-TYPE
			SYNTAX	INTEGER
			ACCESS	read-only
			STATUS	current
	DESCRIPTION ""
			::= { mbus85 75 }

mbus85VIF23		OBJECT-TYPE
			SYNTAX	INTEGER
			ACCESS	read-only
			STATUS	current
	DESCRIPTION ""
			::= { mbus85 76 }

mbus85Value23		OBJECT-TYPE
			SYNTAX	INTEGER
			ACCESS	read-only
			STATUS	current
	DESCRIPTION ""
			::= { mbus85 77 }

mbus85VIF24		OBJECT-TYPE
			SYNTAX	INTEGER
			ACCESS	read-only
			STATUS	current
	DESCRIPTION ""
			::= { mbus85 78 }

mbus85Value24		OBJECT-TYPE
			SYNTAX	INTEGER
			ACCESS	read-only
			STATUS	current
	DESCRIPTION ""
			::= { mbus85 79 }

mbus85VIF25		OBJECT-TYPE
			SYNTAX	INTEGER
			ACCESS	read-only
			STATUS	current
	DESCRIPTION ""
			::= { mbus85 80 }

mbus85Value25		OBJECT-TYPE
			SYNTAX	INTEGER
			ACCESS	read-only
			STATUS	current
	DESCRIPTION ""
			::= { mbus85 81 }

mbus85VIF26		OBJECT-TYPE
			SYNTAX	INTEGER
			ACCESS	read-only
			STATUS	current
	DESCRIPTION ""
			::= { mbus85 82 }

mbus85Value26		OBJECT-TYPE
			SYNTAX	INTEGER
			ACCESS	read-only
			STATUS	current
	DESCRIPTION ""
			::= { mbus85 83 }

mbus85VIF27		OBJECT-TYPE
			SYNTAX	INTEGER
			ACCESS	read-only
			STATUS	current
	DESCRIPTION ""
			::= { mbus85 84 }

mbus85Value27		OBJECT-TYPE
			SYNTAX	INTEGER
			ACCESS	read-only
			STATUS	current
	DESCRIPTION ""
			::= { mbus85 85 }

mbus85VIF28		OBJECT-TYPE
			SYNTAX	INTEGER
			ACCESS	read-only
			STATUS	current
	DESCRIPTION ""
			::= { mbus85 86 }

mbus85Value28		OBJECT-TYPE
			SYNTAX	INTEGER
			ACCESS	read-only
			STATUS	current
	DESCRIPTION ""
			::= { mbus85 87 }

mbus85VIF29		OBJECT-TYPE
			SYNTAX	INTEGER
			ACCESS	read-only
			STATUS	current
	DESCRIPTION ""
			::= { mbus85 88 }

mbus85Value29		OBJECT-TYPE
			SYNTAX	INTEGER
			ACCESS	read-only
			STATUS	current
	DESCRIPTION ""
			::= { mbus85 89 }

mbus85VIF2A		OBJECT-TYPE
			SYNTAX	INTEGER
			ACCESS	read-only
			STATUS	current
	DESCRIPTION ""
			::= { mbus85 90 }

mbus85Value2A		OBJECT-TYPE
			SYNTAX	INTEGER
			ACCESS	read-only
			STATUS	current
	DESCRIPTION ""
			::= { mbus85 91 }

mbus85VIF2B		OBJECT-TYPE
			SYNTAX	INTEGER
			ACCESS	read-only
			STATUS	current
	DESCRIPTION ""
			::= { mbus85 92 }

mbus85Value2B		OBJECT-TYPE
			SYNTAX	INTEGER
			ACCESS	read-only
			STATUS	current
	DESCRIPTION ""
			::= { mbus85 93 }

mbus85VIF2C		OBJECT-TYPE
			SYNTAX	INTEGER
			ACCESS	read-only
			STATUS	current
	DESCRIPTION ""
			::= { mbus85 94 }

mbus85Value2C		OBJECT-TYPE
			SYNTAX	INTEGER
			ACCESS	read-only
			STATUS	current
	DESCRIPTION ""
			::= { mbus85 95 }

mbus85VIF2D		OBJECT-TYPE
			SYNTAX	INTEGER
			ACCESS	read-only
			STATUS	current
	DESCRIPTION ""
			::= { mbus85 96 }

mbus85Value2D		OBJECT-TYPE
			SYNTAX	INTEGER
			ACCESS	read-only
			STATUS	current
	DESCRIPTION ""
			::= { mbus85 97 }

mbus85VIF2E		OBJECT-TYPE
			SYNTAX	INTEGER
			ACCESS	read-only
			STATUS	current
	DESCRIPTION ""
			::= { mbus85 98 }

mbus85Value2E		OBJECT-TYPE
			SYNTAX	INTEGER
			ACCESS	read-only
			STATUS	current
	DESCRIPTION ""
			::= { mbus85 99 }

mbus85VIF2F		OBJECT-TYPE
			SYNTAX	INTEGER
			ACCESS	read-only
			STATUS	current
	DESCRIPTION ""
			::= { mbus85 100 }

mbus85Value2F		OBJECT-TYPE
			SYNTAX	INTEGER
			ACCESS	read-only
			STATUS	current
	DESCRIPTION ""
			::= { mbus85 101 }

mbus86			OBJECT IDENTIFIER ::= { mbus 134 }

mbus86IdNumber		OBJECT-TYPE
			SYNTAX	Gauge
			ACCESS	read-only
			STATUS	current
	DESCRIPTION ""
			::= { mbus86 1 }

mbus86Manufacturer	OBJECT-TYPE
			SYNTAX	Gauge
			ACCESS	read-only
			STATUS	current
	DESCRIPTION ""
			::= { mbus86 2 }

mbus86Version		OBJECT-TYPE
			SYNTAX	Gauge
			ACCESS	read-only
			STATUS	current
	DESCRIPTION ""
			::= { mbus86 3 }

mbus86Medium		OBJECT-TYPE
			SYNTAX	Gauge
			ACCESS	read-only
			STATUS	current
	DESCRIPTION ""
			::= { mbus86 4 }

mbus86Status		OBJECT-TYPE
			SYNTAX	Gauge
			ACCESS	read-only
			STATUS	current
	DESCRIPTION ""
			::= { mbus86 5 }

mbus86VIF00		OBJECT-TYPE
			SYNTAX	INTEGER
			ACCESS	read-only
			STATUS	current
	DESCRIPTION ""
			::= { mbus86 6 }

mbus86Value00		OBJECT-TYPE
			SYNTAX	INTEGER
			ACCESS	read-only
			STATUS	current
	DESCRIPTION ""
			::= { mbus86 7 }

mbus86VIF01		OBJECT-TYPE
			SYNTAX	INTEGER
			ACCESS	read-only
			STATUS	current
	DESCRIPTION ""
			::= { mbus86 8 }

mbus86Value01		OBJECT-TYPE
			SYNTAX	INTEGER
			ACCESS	read-only
			STATUS	current
	DESCRIPTION ""
			::= { mbus86 9 }

mbus86VIF02		OBJECT-TYPE
			SYNTAX	INTEGER
			ACCESS	read-only
			STATUS	current
	DESCRIPTION ""
			::= { mbus86 10 }

mbus86Value02		OBJECT-TYPE
			SYNTAX	INTEGER
			ACCESS	read-only
			STATUS	current
	DESCRIPTION ""
			::= { mbus86 11 }

mbus86VIF03		OBJECT-TYPE
			SYNTAX	INTEGER
			ACCESS	read-only
			STATUS	current
	DESCRIPTION ""
			::= { mbus86 12 }

mbus86Value03		OBJECT-TYPE
			SYNTAX	INTEGER
			ACCESS	read-only
			STATUS	current
	DESCRIPTION ""
			::= { mbus86 13 }

mbus86VIF04		OBJECT-TYPE
			SYNTAX	INTEGER
			ACCESS	read-only
			STATUS	current
	DESCRIPTION ""
			::= { mbus86 14 }

mbus86Value04		OBJECT-TYPE
			SYNTAX	INTEGER
			ACCESS	read-only
			STATUS	current
	DESCRIPTION ""
			::= { mbus86 15 }

mbus86VIF05		OBJECT-TYPE
			SYNTAX	INTEGER
			ACCESS	read-only
			STATUS	current
	DESCRIPTION ""
			::= { mbus86 16 }

mbus86Value05		OBJECT-TYPE
			SYNTAX	INTEGER
			ACCESS	read-only
			STATUS	current
	DESCRIPTION ""
			::= { mbus86 17 }

mbus86VIF06		OBJECT-TYPE
			SYNTAX	INTEGER
			ACCESS	read-only
			STATUS	current
	DESCRIPTION ""
			::= { mbus86 18 }

mbus86Value06		OBJECT-TYPE
			SYNTAX	INTEGER
			ACCESS	read-only
			STATUS	current
	DESCRIPTION ""
			::= { mbus86 19 }

mbus86VIF07		OBJECT-TYPE
			SYNTAX	INTEGER
			ACCESS	read-only
			STATUS	current
	DESCRIPTION ""
			::= { mbus86 20 }

mbus86Value07		OBJECT-TYPE
			SYNTAX	INTEGER
			ACCESS	read-only
			STATUS	current
	DESCRIPTION ""
			::= { mbus86 21 }

mbus86VIF08		OBJECT-TYPE
			SYNTAX	INTEGER
			ACCESS	read-only
			STATUS	current
	DESCRIPTION ""
			::= { mbus86 22 }

mbus86Value08		OBJECT-TYPE
			SYNTAX	INTEGER
			ACCESS	read-only
			STATUS	current
	DESCRIPTION ""
			::= { mbus86 23 }

mbus86VIF09		OBJECT-TYPE
			SYNTAX	INTEGER
			ACCESS	read-only
			STATUS	current
	DESCRIPTION ""
			::= { mbus86 24 }

mbus86Value09		OBJECT-TYPE
			SYNTAX	INTEGER
			ACCESS	read-only
			STATUS	current
	DESCRIPTION ""
			::= { mbus86 25 }

mbus86VIF0A		OBJECT-TYPE
			SYNTAX	INTEGER
			ACCESS	read-only
			STATUS	current
	DESCRIPTION ""
			::= { mbus86 26 }

mbus86Value0A		OBJECT-TYPE
			SYNTAX	INTEGER
			ACCESS	read-only
			STATUS	current
	DESCRIPTION ""
			::= { mbus86 27 }

mbus86VIF0B		OBJECT-TYPE
			SYNTAX	INTEGER
			ACCESS	read-only
			STATUS	current
	DESCRIPTION ""
			::= { mbus86 28 }

mbus86Value0B		OBJECT-TYPE
			SYNTAX	INTEGER
			ACCESS	read-only
			STATUS	current
	DESCRIPTION ""
			::= { mbus86 29 }

mbus86VIF0C		OBJECT-TYPE
			SYNTAX	INTEGER
			ACCESS	read-only
			STATUS	current
	DESCRIPTION ""
			::= { mbus86 30 }

mbus86Value0C		OBJECT-TYPE
			SYNTAX	INTEGER
			ACCESS	read-only
			STATUS	current
	DESCRIPTION ""
			::= { mbus86 31 }

mbus86VIF0D		OBJECT-TYPE
			SYNTAX	INTEGER
			ACCESS	read-only
			STATUS	current
	DESCRIPTION ""
			::= { mbus86 32 }

mbus86Value0D		OBJECT-TYPE
			SYNTAX	INTEGER
			ACCESS	read-only
			STATUS	current
	DESCRIPTION ""
			::= { mbus86 33 }

mbus86VIF0E		OBJECT-TYPE
			SYNTAX	INTEGER
			ACCESS	read-only
			STATUS	current
	DESCRIPTION ""
			::= { mbus86 34 }

mbus86Value0E		OBJECT-TYPE
			SYNTAX	INTEGER
			ACCESS	read-only
			STATUS	current
	DESCRIPTION ""
			::= { mbus86 35 }

mbus86VIF0F		OBJECT-TYPE
			SYNTAX	INTEGER
			ACCESS	read-only
			STATUS	current
	DESCRIPTION ""
			::= { mbus86 36 }

mbus86Value0F		OBJECT-TYPE
			SYNTAX	INTEGER
			ACCESS	read-only
			STATUS	current
	DESCRIPTION ""
			::= { mbus86 37 }

mbus86VIF10		OBJECT-TYPE
			SYNTAX	INTEGER
			ACCESS	read-only
			STATUS	current
	DESCRIPTION ""
			::= { mbus86 38 }

mbus86Value10		OBJECT-TYPE
			SYNTAX	INTEGER
			ACCESS	read-only
			STATUS	current
	DESCRIPTION ""
			::= { mbus86 39 }

mbus86VIF11		OBJECT-TYPE
			SYNTAX	INTEGER
			ACCESS	read-only
			STATUS	current
	DESCRIPTION ""
			::= { mbus86 40 }

mbus86Value11		OBJECT-TYPE
			SYNTAX	INTEGER
			ACCESS	read-only
			STATUS	current
	DESCRIPTION ""
			::= { mbus86 41 }

mbus86VIF12		OBJECT-TYPE
			SYNTAX	INTEGER
			ACCESS	read-only
			STATUS	current
	DESCRIPTION ""
			::= { mbus86 42 }

mbus86Value12		OBJECT-TYPE
			SYNTAX	INTEGER
			ACCESS	read-only
			STATUS	current
	DESCRIPTION ""
			::= { mbus86 43 }

mbus86VIF13		OBJECT-TYPE
			SYNTAX	INTEGER
			ACCESS	read-only
			STATUS	current
	DESCRIPTION ""
			::= { mbus86 44 }

mbus86Value13		OBJECT-TYPE
			SYNTAX	INTEGER
			ACCESS	read-only
			STATUS	current
	DESCRIPTION ""
			::= { mbus86 45 }

mbus86VIF14		OBJECT-TYPE
			SYNTAX	INTEGER
			ACCESS	read-only
			STATUS	current
	DESCRIPTION ""
			::= { mbus86 46 }

mbus86Value14		OBJECT-TYPE
			SYNTAX	INTEGER
			ACCESS	read-only
			STATUS	current
	DESCRIPTION ""
			::= { mbus86 47 }

mbus86VIF15		OBJECT-TYPE
			SYNTAX	INTEGER
			ACCESS	read-only
			STATUS	current
	DESCRIPTION ""
			::= { mbus86 48 }

mbus86Value15		OBJECT-TYPE
			SYNTAX	INTEGER
			ACCESS	read-only
			STATUS	current
	DESCRIPTION ""
			::= { mbus86 49 }

mbus86VIF16		OBJECT-TYPE
			SYNTAX	INTEGER
			ACCESS	read-only
			STATUS	current
	DESCRIPTION ""
			::= { mbus86 50 }

mbus86Value16		OBJECT-TYPE
			SYNTAX	INTEGER
			ACCESS	read-only
			STATUS	current
	DESCRIPTION ""
			::= { mbus86 51 }

mbus86VIF17		OBJECT-TYPE
			SYNTAX	INTEGER
			ACCESS	read-only
			STATUS	current
	DESCRIPTION ""
			::= { mbus86 52 }

mbus86Value17		OBJECT-TYPE
			SYNTAX	INTEGER
			ACCESS	read-only
			STATUS	current
	DESCRIPTION ""
			::= { mbus86 53 }

mbus86VIF18		OBJECT-TYPE
			SYNTAX	INTEGER
			ACCESS	read-only
			STATUS	current
	DESCRIPTION ""
			::= { mbus86 54 }

mbus86Value18		OBJECT-TYPE
			SYNTAX	INTEGER
			ACCESS	read-only
			STATUS	current
	DESCRIPTION ""
			::= { mbus86 55 }

mbus86VIF19		OBJECT-TYPE
			SYNTAX	INTEGER
			ACCESS	read-only
			STATUS	current
	DESCRIPTION ""
			::= { mbus86 56 }

mbus86Value19		OBJECT-TYPE
			SYNTAX	INTEGER
			ACCESS	read-only
			STATUS	current
	DESCRIPTION ""
			::= { mbus86 57 }

mbus86VIF1A		OBJECT-TYPE
			SYNTAX	INTEGER
			ACCESS	read-only
			STATUS	current
	DESCRIPTION ""
			::= { mbus86 58 }

mbus86Value1A		OBJECT-TYPE
			SYNTAX	INTEGER
			ACCESS	read-only
			STATUS	current
	DESCRIPTION ""
			::= { mbus86 59 }

mbus86VIF1B		OBJECT-TYPE
			SYNTAX	INTEGER
			ACCESS	read-only
			STATUS	current
	DESCRIPTION ""
			::= { mbus86 60 }

mbus86Value1B		OBJECT-TYPE
			SYNTAX	INTEGER
			ACCESS	read-only
			STATUS	current
	DESCRIPTION ""
			::= { mbus86 61 }

mbus86VIF1C		OBJECT-TYPE
			SYNTAX	INTEGER
			ACCESS	read-only
			STATUS	current
	DESCRIPTION ""
			::= { mbus86 62 }

mbus86Value1C		OBJECT-TYPE
			SYNTAX	INTEGER
			ACCESS	read-only
			STATUS	current
	DESCRIPTION ""
			::= { mbus86 63 }

mbus86VIF1D		OBJECT-TYPE
			SYNTAX	INTEGER
			ACCESS	read-only
			STATUS	current
	DESCRIPTION ""
			::= { mbus86 64 }

mbus86Value1D		OBJECT-TYPE
			SYNTAX	INTEGER
			ACCESS	read-only
			STATUS	current
	DESCRIPTION ""
			::= { mbus86 65 }

mbus86VIF1E		OBJECT-TYPE
			SYNTAX	INTEGER
			ACCESS	read-only
			STATUS	current
	DESCRIPTION ""
			::= { mbus86 66 }

mbus86Value1E		OBJECT-TYPE
			SYNTAX	INTEGER
			ACCESS	read-only
			STATUS	current
	DESCRIPTION ""
			::= { mbus86 67 }

mbus86VIF1F		OBJECT-TYPE
			SYNTAX	INTEGER
			ACCESS	read-only
			STATUS	current
	DESCRIPTION ""
			::= { mbus86 68 }

mbus86Value1F		OBJECT-TYPE
			SYNTAX	INTEGER
			ACCESS	read-only
			STATUS	current
	DESCRIPTION ""
			::= { mbus86 69 }

mbus86VIF20		OBJECT-TYPE
			SYNTAX	INTEGER
			ACCESS	read-only
			STATUS	current
	DESCRIPTION ""
			::= { mbus86 70 }

mbus86Value20		OBJECT-TYPE
			SYNTAX	INTEGER
			ACCESS	read-only
			STATUS	current
	DESCRIPTION ""
			::= { mbus86 71 }

mbus86VIF21		OBJECT-TYPE
			SYNTAX	INTEGER
			ACCESS	read-only
			STATUS	current
	DESCRIPTION ""
			::= { mbus86 72 }

mbus86Value21		OBJECT-TYPE
			SYNTAX	INTEGER
			ACCESS	read-only
			STATUS	current
	DESCRIPTION ""
			::= { mbus86 73 }

mbus86VIF22		OBJECT-TYPE
			SYNTAX	INTEGER
			ACCESS	read-only
			STATUS	current
	DESCRIPTION ""
			::= { mbus86 74 }

mbus86Value22		OBJECT-TYPE
			SYNTAX	INTEGER
			ACCESS	read-only
			STATUS	current
	DESCRIPTION ""
			::= { mbus86 75 }

mbus86VIF23		OBJECT-TYPE
			SYNTAX	INTEGER
			ACCESS	read-only
			STATUS	current
	DESCRIPTION ""
			::= { mbus86 76 }

mbus86Value23		OBJECT-TYPE
			SYNTAX	INTEGER
			ACCESS	read-only
			STATUS	current
	DESCRIPTION ""
			::= { mbus86 77 }

mbus86VIF24		OBJECT-TYPE
			SYNTAX	INTEGER
			ACCESS	read-only
			STATUS	current
	DESCRIPTION ""
			::= { mbus86 78 }

mbus86Value24		OBJECT-TYPE
			SYNTAX	INTEGER
			ACCESS	read-only
			STATUS	current
	DESCRIPTION ""
			::= { mbus86 79 }

mbus86VIF25		OBJECT-TYPE
			SYNTAX	INTEGER
			ACCESS	read-only
			STATUS	current
	DESCRIPTION ""
			::= { mbus86 80 }

mbus86Value25		OBJECT-TYPE
			SYNTAX	INTEGER
			ACCESS	read-only
			STATUS	current
	DESCRIPTION ""
			::= { mbus86 81 }

mbus86VIF26		OBJECT-TYPE
			SYNTAX	INTEGER
			ACCESS	read-only
			STATUS	current
	DESCRIPTION ""
			::= { mbus86 82 }

mbus86Value26		OBJECT-TYPE
			SYNTAX	INTEGER
			ACCESS	read-only
			STATUS	current
	DESCRIPTION ""
			::= { mbus86 83 }

mbus86VIF27		OBJECT-TYPE
			SYNTAX	INTEGER
			ACCESS	read-only
			STATUS	current
	DESCRIPTION ""
			::= { mbus86 84 }

mbus86Value27		OBJECT-TYPE
			SYNTAX	INTEGER
			ACCESS	read-only
			STATUS	current
	DESCRIPTION ""
			::= { mbus86 85 }

mbus86VIF28		OBJECT-TYPE
			SYNTAX	INTEGER
			ACCESS	read-only
			STATUS	current
	DESCRIPTION ""
			::= { mbus86 86 }

mbus86Value28		OBJECT-TYPE
			SYNTAX	INTEGER
			ACCESS	read-only
			STATUS	current
	DESCRIPTION ""
			::= { mbus86 87 }

mbus86VIF29		OBJECT-TYPE
			SYNTAX	INTEGER
			ACCESS	read-only
			STATUS	current
	DESCRIPTION ""
			::= { mbus86 88 }

mbus86Value29		OBJECT-TYPE
			SYNTAX	INTEGER
			ACCESS	read-only
			STATUS	current
	DESCRIPTION ""
			::= { mbus86 89 }

mbus86VIF2A		OBJECT-TYPE
			SYNTAX	INTEGER
			ACCESS	read-only
			STATUS	current
	DESCRIPTION ""
			::= { mbus86 90 }

mbus86Value2A		OBJECT-TYPE
			SYNTAX	INTEGER
			ACCESS	read-only
			STATUS	current
	DESCRIPTION ""
			::= { mbus86 91 }

mbus86VIF2B		OBJECT-TYPE
			SYNTAX	INTEGER
			ACCESS	read-only
			STATUS	current
	DESCRIPTION ""
			::= { mbus86 92 }

mbus86Value2B		OBJECT-TYPE
			SYNTAX	INTEGER
			ACCESS	read-only
			STATUS	current
	DESCRIPTION ""
			::= { mbus86 93 }

mbus86VIF2C		OBJECT-TYPE
			SYNTAX	INTEGER
			ACCESS	read-only
			STATUS	current
	DESCRIPTION ""
			::= { mbus86 94 }

mbus86Value2C		OBJECT-TYPE
			SYNTAX	INTEGER
			ACCESS	read-only
			STATUS	current
	DESCRIPTION ""
			::= { mbus86 95 }

mbus86VIF2D		OBJECT-TYPE
			SYNTAX	INTEGER
			ACCESS	read-only
			STATUS	current
	DESCRIPTION ""
			::= { mbus86 96 }

mbus86Value2D		OBJECT-TYPE
			SYNTAX	INTEGER
			ACCESS	read-only
			STATUS	current
	DESCRIPTION ""
			::= { mbus86 97 }

mbus86VIF2E		OBJECT-TYPE
			SYNTAX	INTEGER
			ACCESS	read-only
			STATUS	current
	DESCRIPTION ""
			::= { mbus86 98 }

mbus86Value2E		OBJECT-TYPE
			SYNTAX	INTEGER
			ACCESS	read-only
			STATUS	current
	DESCRIPTION ""
			::= { mbus86 99 }

mbus86VIF2F		OBJECT-TYPE
			SYNTAX	INTEGER
			ACCESS	read-only
			STATUS	current
	DESCRIPTION ""
			::= { mbus86 100 }

mbus86Value2F		OBJECT-TYPE
			SYNTAX	INTEGER
			ACCESS	read-only
			STATUS	current
	DESCRIPTION ""
			::= { mbus86 101 }

mbus87			OBJECT IDENTIFIER ::= { mbus 135 }

mbus87IdNumber		OBJECT-TYPE
			SYNTAX	Gauge
			ACCESS	read-only
			STATUS	current
	DESCRIPTION ""
			::= { mbus87 1 }

mbus87Manufacturer	OBJECT-TYPE
			SYNTAX	Gauge
			ACCESS	read-only
			STATUS	current
	DESCRIPTION ""
			::= { mbus87 2 }

mbus87Version		OBJECT-TYPE
			SYNTAX	Gauge
			ACCESS	read-only
			STATUS	current
	DESCRIPTION ""
			::= { mbus87 3 }

mbus87Medium		OBJECT-TYPE
			SYNTAX	Gauge
			ACCESS	read-only
			STATUS	current
	DESCRIPTION ""
			::= { mbus87 4 }

mbus87Status		OBJECT-TYPE
			SYNTAX	Gauge
			ACCESS	read-only
			STATUS	current
	DESCRIPTION ""
			::= { mbus87 5 }

mbus87VIF00		OBJECT-TYPE
			SYNTAX	INTEGER
			ACCESS	read-only
			STATUS	current
	DESCRIPTION ""
			::= { mbus87 6 }

mbus87Value00		OBJECT-TYPE
			SYNTAX	INTEGER
			ACCESS	read-only
			STATUS	current
	DESCRIPTION ""
			::= { mbus87 7 }

mbus87VIF01		OBJECT-TYPE
			SYNTAX	INTEGER
			ACCESS	read-only
			STATUS	current
	DESCRIPTION ""
			::= { mbus87 8 }

mbus87Value01		OBJECT-TYPE
			SYNTAX	INTEGER
			ACCESS	read-only
			STATUS	current
	DESCRIPTION ""
			::= { mbus87 9 }

mbus87VIF02		OBJECT-TYPE
			SYNTAX	INTEGER
			ACCESS	read-only
			STATUS	current
	DESCRIPTION ""
			::= { mbus87 10 }

mbus87Value02		OBJECT-TYPE
			SYNTAX	INTEGER
			ACCESS	read-only
			STATUS	current
	DESCRIPTION ""
			::= { mbus87 11 }

mbus87VIF03		OBJECT-TYPE
			SYNTAX	INTEGER
			ACCESS	read-only
			STATUS	current
	DESCRIPTION ""
			::= { mbus87 12 }

mbus87Value03		OBJECT-TYPE
			SYNTAX	INTEGER
			ACCESS	read-only
			STATUS	current
	DESCRIPTION ""
			::= { mbus87 13 }

mbus87VIF04		OBJECT-TYPE
			SYNTAX	INTEGER
			ACCESS	read-only
			STATUS	current
	DESCRIPTION ""
			::= { mbus87 14 }

mbus87Value04		OBJECT-TYPE
			SYNTAX	INTEGER
			ACCESS	read-only
			STATUS	current
	DESCRIPTION ""
			::= { mbus87 15 }

mbus87VIF05		OBJECT-TYPE
			SYNTAX	INTEGER
			ACCESS	read-only
			STATUS	current
	DESCRIPTION ""
			::= { mbus87 16 }

mbus87Value05		OBJECT-TYPE
			SYNTAX	INTEGER
			ACCESS	read-only
			STATUS	current
	DESCRIPTION ""
			::= { mbus87 17 }

mbus87VIF06		OBJECT-TYPE
			SYNTAX	INTEGER
			ACCESS	read-only
			STATUS	current
	DESCRIPTION ""
			::= { mbus87 18 }

mbus87Value06		OBJECT-TYPE
			SYNTAX	INTEGER
			ACCESS	read-only
			STATUS	current
	DESCRIPTION ""
			::= { mbus87 19 }

mbus87VIF07		OBJECT-TYPE
			SYNTAX	INTEGER
			ACCESS	read-only
			STATUS	current
	DESCRIPTION ""
			::= { mbus87 20 }

mbus87Value07		OBJECT-TYPE
			SYNTAX	INTEGER
			ACCESS	read-only
			STATUS	current
	DESCRIPTION ""
			::= { mbus87 21 }

mbus87VIF08		OBJECT-TYPE
			SYNTAX	INTEGER
			ACCESS	read-only
			STATUS	current
	DESCRIPTION ""
			::= { mbus87 22 }

mbus87Value08		OBJECT-TYPE
			SYNTAX	INTEGER
			ACCESS	read-only
			STATUS	current
	DESCRIPTION ""
			::= { mbus87 23 }

mbus87VIF09		OBJECT-TYPE
			SYNTAX	INTEGER
			ACCESS	read-only
			STATUS	current
	DESCRIPTION ""
			::= { mbus87 24 }

mbus87Value09		OBJECT-TYPE
			SYNTAX	INTEGER
			ACCESS	read-only
			STATUS	current
	DESCRIPTION ""
			::= { mbus87 25 }

mbus87VIF0A		OBJECT-TYPE
			SYNTAX	INTEGER
			ACCESS	read-only
			STATUS	current
	DESCRIPTION ""
			::= { mbus87 26 }

mbus87Value0A		OBJECT-TYPE
			SYNTAX	INTEGER
			ACCESS	read-only
			STATUS	current
	DESCRIPTION ""
			::= { mbus87 27 }

mbus87VIF0B		OBJECT-TYPE
			SYNTAX	INTEGER
			ACCESS	read-only
			STATUS	current
	DESCRIPTION ""
			::= { mbus87 28 }

mbus87Value0B		OBJECT-TYPE
			SYNTAX	INTEGER
			ACCESS	read-only
			STATUS	current
	DESCRIPTION ""
			::= { mbus87 29 }

mbus87VIF0C		OBJECT-TYPE
			SYNTAX	INTEGER
			ACCESS	read-only
			STATUS	current
	DESCRIPTION ""
			::= { mbus87 30 }

mbus87Value0C		OBJECT-TYPE
			SYNTAX	INTEGER
			ACCESS	read-only
			STATUS	current
	DESCRIPTION ""
			::= { mbus87 31 }

mbus87VIF0D		OBJECT-TYPE
			SYNTAX	INTEGER
			ACCESS	read-only
			STATUS	current
	DESCRIPTION ""
			::= { mbus87 32 }

mbus87Value0D		OBJECT-TYPE
			SYNTAX	INTEGER
			ACCESS	read-only
			STATUS	current
	DESCRIPTION ""
			::= { mbus87 33 }

mbus87VIF0E		OBJECT-TYPE
			SYNTAX	INTEGER
			ACCESS	read-only
			STATUS	current
	DESCRIPTION ""
			::= { mbus87 34 }

mbus87Value0E		OBJECT-TYPE
			SYNTAX	INTEGER
			ACCESS	read-only
			STATUS	current
	DESCRIPTION ""
			::= { mbus87 35 }

mbus87VIF0F		OBJECT-TYPE
			SYNTAX	INTEGER
			ACCESS	read-only
			STATUS	current
	DESCRIPTION ""
			::= { mbus87 36 }

mbus87Value0F		OBJECT-TYPE
			SYNTAX	INTEGER
			ACCESS	read-only
			STATUS	current
	DESCRIPTION ""
			::= { mbus87 37 }

mbus87VIF10		OBJECT-TYPE
			SYNTAX	INTEGER
			ACCESS	read-only
			STATUS	current
	DESCRIPTION ""
			::= { mbus87 38 }

mbus87Value10		OBJECT-TYPE
			SYNTAX	INTEGER
			ACCESS	read-only
			STATUS	current
	DESCRIPTION ""
			::= { mbus87 39 }

mbus87VIF11		OBJECT-TYPE
			SYNTAX	INTEGER
			ACCESS	read-only
			STATUS	current
	DESCRIPTION ""
			::= { mbus87 40 }

mbus87Value11		OBJECT-TYPE
			SYNTAX	INTEGER
			ACCESS	read-only
			STATUS	current
	DESCRIPTION ""
			::= { mbus87 41 }

mbus87VIF12		OBJECT-TYPE
			SYNTAX	INTEGER
			ACCESS	read-only
			STATUS	current
	DESCRIPTION ""
			::= { mbus87 42 }

mbus87Value12		OBJECT-TYPE
			SYNTAX	INTEGER
			ACCESS	read-only
			STATUS	current
	DESCRIPTION ""
			::= { mbus87 43 }

mbus87VIF13		OBJECT-TYPE
			SYNTAX	INTEGER
			ACCESS	read-only
			STATUS	current
	DESCRIPTION ""
			::= { mbus87 44 }

mbus87Value13		OBJECT-TYPE
			SYNTAX	INTEGER
			ACCESS	read-only
			STATUS	current
	DESCRIPTION ""
			::= { mbus87 45 }

mbus87VIF14		OBJECT-TYPE
			SYNTAX	INTEGER
			ACCESS	read-only
			STATUS	current
	DESCRIPTION ""
			::= { mbus87 46 }

mbus87Value14		OBJECT-TYPE
			SYNTAX	INTEGER
			ACCESS	read-only
			STATUS	current
	DESCRIPTION ""
			::= { mbus87 47 }

mbus87VIF15		OBJECT-TYPE
			SYNTAX	INTEGER
			ACCESS	read-only
			STATUS	current
	DESCRIPTION ""
			::= { mbus87 48 }

mbus87Value15		OBJECT-TYPE
			SYNTAX	INTEGER
			ACCESS	read-only
			STATUS	current
	DESCRIPTION ""
			::= { mbus87 49 }

mbus87VIF16		OBJECT-TYPE
			SYNTAX	INTEGER
			ACCESS	read-only
			STATUS	current
	DESCRIPTION ""
			::= { mbus87 50 }

mbus87Value16		OBJECT-TYPE
			SYNTAX	INTEGER
			ACCESS	read-only
			STATUS	current
	DESCRIPTION ""
			::= { mbus87 51 }

mbus87VIF17		OBJECT-TYPE
			SYNTAX	INTEGER
			ACCESS	read-only
			STATUS	current
	DESCRIPTION ""
			::= { mbus87 52 }

mbus87Value17		OBJECT-TYPE
			SYNTAX	INTEGER
			ACCESS	read-only
			STATUS	current
	DESCRIPTION ""
			::= { mbus87 53 }

mbus87VIF18		OBJECT-TYPE
			SYNTAX	INTEGER
			ACCESS	read-only
			STATUS	current
	DESCRIPTION ""
			::= { mbus87 54 }

mbus87Value18		OBJECT-TYPE
			SYNTAX	INTEGER
			ACCESS	read-only
			STATUS	current
	DESCRIPTION ""
			::= { mbus87 55 }

mbus87VIF19		OBJECT-TYPE
			SYNTAX	INTEGER
			ACCESS	read-only
			STATUS	current
	DESCRIPTION ""
			::= { mbus87 56 }

mbus87Value19		OBJECT-TYPE
			SYNTAX	INTEGER
			ACCESS	read-only
			STATUS	current
	DESCRIPTION ""
			::= { mbus87 57 }

mbus87VIF1A		OBJECT-TYPE
			SYNTAX	INTEGER
			ACCESS	read-only
			STATUS	current
	DESCRIPTION ""
			::= { mbus87 58 }

mbus87Value1A		OBJECT-TYPE
			SYNTAX	INTEGER
			ACCESS	read-only
			STATUS	current
	DESCRIPTION ""
			::= { mbus87 59 }

mbus87VIF1B		OBJECT-TYPE
			SYNTAX	INTEGER
			ACCESS	read-only
			STATUS	current
	DESCRIPTION ""
			::= { mbus87 60 }

mbus87Value1B		OBJECT-TYPE
			SYNTAX	INTEGER
			ACCESS	read-only
			STATUS	current
	DESCRIPTION ""
			::= { mbus87 61 }

mbus87VIF1C		OBJECT-TYPE
			SYNTAX	INTEGER
			ACCESS	read-only
			STATUS	current
	DESCRIPTION ""
			::= { mbus87 62 }

mbus87Value1C		OBJECT-TYPE
			SYNTAX	INTEGER
			ACCESS	read-only
			STATUS	current
	DESCRIPTION ""
			::= { mbus87 63 }

mbus87VIF1D		OBJECT-TYPE
			SYNTAX	INTEGER
			ACCESS	read-only
			STATUS	current
	DESCRIPTION ""
			::= { mbus87 64 }

mbus87Value1D		OBJECT-TYPE
			SYNTAX	INTEGER
			ACCESS	read-only
			STATUS	current
	DESCRIPTION ""
			::= { mbus87 65 }

mbus87VIF1E		OBJECT-TYPE
			SYNTAX	INTEGER
			ACCESS	read-only
			STATUS	current
	DESCRIPTION ""
			::= { mbus87 66 }

mbus87Value1E		OBJECT-TYPE
			SYNTAX	INTEGER
			ACCESS	read-only
			STATUS	current
	DESCRIPTION ""
			::= { mbus87 67 }

mbus87VIF1F		OBJECT-TYPE
			SYNTAX	INTEGER
			ACCESS	read-only
			STATUS	current
	DESCRIPTION ""
			::= { mbus87 68 }

mbus87Value1F		OBJECT-TYPE
			SYNTAX	INTEGER
			ACCESS	read-only
			STATUS	current
	DESCRIPTION ""
			::= { mbus87 69 }

mbus87VIF20		OBJECT-TYPE
			SYNTAX	INTEGER
			ACCESS	read-only
			STATUS	current
	DESCRIPTION ""
			::= { mbus87 70 }

mbus87Value20		OBJECT-TYPE
			SYNTAX	INTEGER
			ACCESS	read-only
			STATUS	current
	DESCRIPTION ""
			::= { mbus87 71 }

mbus87VIF21		OBJECT-TYPE
			SYNTAX	INTEGER
			ACCESS	read-only
			STATUS	current
	DESCRIPTION ""
			::= { mbus87 72 }

mbus87Value21		OBJECT-TYPE
			SYNTAX	INTEGER
			ACCESS	read-only
			STATUS	current
	DESCRIPTION ""
			::= { mbus87 73 }

mbus87VIF22		OBJECT-TYPE
			SYNTAX	INTEGER
			ACCESS	read-only
			STATUS	current
	DESCRIPTION ""
			::= { mbus87 74 }

mbus87Value22		OBJECT-TYPE
			SYNTAX	INTEGER
			ACCESS	read-only
			STATUS	current
	DESCRIPTION ""
			::= { mbus87 75 }

mbus87VIF23		OBJECT-TYPE
			SYNTAX	INTEGER
			ACCESS	read-only
			STATUS	current
	DESCRIPTION ""
			::= { mbus87 76 }

mbus87Value23		OBJECT-TYPE
			SYNTAX	INTEGER
			ACCESS	read-only
			STATUS	current
	DESCRIPTION ""
			::= { mbus87 77 }

mbus87VIF24		OBJECT-TYPE
			SYNTAX	INTEGER
			ACCESS	read-only
			STATUS	current
	DESCRIPTION ""
			::= { mbus87 78 }

mbus87Value24		OBJECT-TYPE
			SYNTAX	INTEGER
			ACCESS	read-only
			STATUS	current
	DESCRIPTION ""
			::= { mbus87 79 }

mbus87VIF25		OBJECT-TYPE
			SYNTAX	INTEGER
			ACCESS	read-only
			STATUS	current
	DESCRIPTION ""
			::= { mbus87 80 }

mbus87Value25		OBJECT-TYPE
			SYNTAX	INTEGER
			ACCESS	read-only
			STATUS	current
	DESCRIPTION ""
			::= { mbus87 81 }

mbus87VIF26		OBJECT-TYPE
			SYNTAX	INTEGER
			ACCESS	read-only
			STATUS	current
	DESCRIPTION ""
			::= { mbus87 82 }

mbus87Value26		OBJECT-TYPE
			SYNTAX	INTEGER
			ACCESS	read-only
			STATUS	current
	DESCRIPTION ""
			::= { mbus87 83 }

mbus87VIF27		OBJECT-TYPE
			SYNTAX	INTEGER
			ACCESS	read-only
			STATUS	current
	DESCRIPTION ""
			::= { mbus87 84 }

mbus87Value27		OBJECT-TYPE
			SYNTAX	INTEGER
			ACCESS	read-only
			STATUS	current
	DESCRIPTION ""
			::= { mbus87 85 }

mbus87VIF28		OBJECT-TYPE
			SYNTAX	INTEGER
			ACCESS	read-only
			STATUS	current
	DESCRIPTION ""
			::= { mbus87 86 }

mbus87Value28		OBJECT-TYPE
			SYNTAX	INTEGER
			ACCESS	read-only
			STATUS	current
	DESCRIPTION ""
			::= { mbus87 87 }

mbus87VIF29		OBJECT-TYPE
			SYNTAX	INTEGER
			ACCESS	read-only
			STATUS	current
	DESCRIPTION ""
			::= { mbus87 88 }

mbus87Value29		OBJECT-TYPE
			SYNTAX	INTEGER
			ACCESS	read-only
			STATUS	current
	DESCRIPTION ""
			::= { mbus87 89 }

mbus87VIF2A		OBJECT-TYPE
			SYNTAX	INTEGER
			ACCESS	read-only
			STATUS	current
	DESCRIPTION ""
			::= { mbus87 90 }

mbus87Value2A		OBJECT-TYPE
			SYNTAX	INTEGER
			ACCESS	read-only
			STATUS	current
	DESCRIPTION ""
			::= { mbus87 91 }

mbus87VIF2B		OBJECT-TYPE
			SYNTAX	INTEGER
			ACCESS	read-only
			STATUS	current
	DESCRIPTION ""
			::= { mbus87 92 }

mbus87Value2B		OBJECT-TYPE
			SYNTAX	INTEGER
			ACCESS	read-only
			STATUS	current
	DESCRIPTION ""
			::= { mbus87 93 }

mbus87VIF2C		OBJECT-TYPE
			SYNTAX	INTEGER
			ACCESS	read-only
			STATUS	current
	DESCRIPTION ""
			::= { mbus87 94 }

mbus87Value2C		OBJECT-TYPE
			SYNTAX	INTEGER
			ACCESS	read-only
			STATUS	current
	DESCRIPTION ""
			::= { mbus87 95 }

mbus87VIF2D		OBJECT-TYPE
			SYNTAX	INTEGER
			ACCESS	read-only
			STATUS	current
	DESCRIPTION ""
			::= { mbus87 96 }

mbus87Value2D		OBJECT-TYPE
			SYNTAX	INTEGER
			ACCESS	read-only
			STATUS	current
	DESCRIPTION ""
			::= { mbus87 97 }

mbus87VIF2E		OBJECT-TYPE
			SYNTAX	INTEGER
			ACCESS	read-only
			STATUS	current
	DESCRIPTION ""
			::= { mbus87 98 }

mbus87Value2E		OBJECT-TYPE
			SYNTAX	INTEGER
			ACCESS	read-only
			STATUS	current
	DESCRIPTION ""
			::= { mbus87 99 }

mbus87VIF2F		OBJECT-TYPE
			SYNTAX	INTEGER
			ACCESS	read-only
			STATUS	current
	DESCRIPTION ""
			::= { mbus87 100 }

mbus87Value2F		OBJECT-TYPE
			SYNTAX	INTEGER
			ACCESS	read-only
			STATUS	current
	DESCRIPTION ""
			::= { mbus87 101 }

mbus88			OBJECT IDENTIFIER ::= { mbus 136 }

mbus88IdNumber		OBJECT-TYPE
			SYNTAX	Gauge
			ACCESS	read-only
			STATUS	current
	DESCRIPTION ""
			::= { mbus88 1 }

mbus88Manufacturer	OBJECT-TYPE
			SYNTAX	Gauge
			ACCESS	read-only
			STATUS	current
	DESCRIPTION ""
			::= { mbus88 2 }

mbus88Version		OBJECT-TYPE
			SYNTAX	Gauge
			ACCESS	read-only
			STATUS	current
	DESCRIPTION ""
			::= { mbus88 3 }

mbus88Medium		OBJECT-TYPE
			SYNTAX	Gauge
			ACCESS	read-only
			STATUS	current
	DESCRIPTION ""
			::= { mbus88 4 }

mbus88Status		OBJECT-TYPE
			SYNTAX	Gauge
			ACCESS	read-only
			STATUS	current
	DESCRIPTION ""
			::= { mbus88 5 }

mbus88VIF00		OBJECT-TYPE
			SYNTAX	INTEGER
			ACCESS	read-only
			STATUS	current
	DESCRIPTION ""
			::= { mbus88 6 }

mbus88Value00		OBJECT-TYPE
			SYNTAX	INTEGER
			ACCESS	read-only
			STATUS	current
	DESCRIPTION ""
			::= { mbus88 7 }

mbus88VIF01		OBJECT-TYPE
			SYNTAX	INTEGER
			ACCESS	read-only
			STATUS	current
	DESCRIPTION ""
			::= { mbus88 8 }

mbus88Value01		OBJECT-TYPE
			SYNTAX	INTEGER
			ACCESS	read-only
			STATUS	current
	DESCRIPTION ""
			::= { mbus88 9 }

mbus88VIF02		OBJECT-TYPE
			SYNTAX	INTEGER
			ACCESS	read-only
			STATUS	current
	DESCRIPTION ""
			::= { mbus88 10 }

mbus88Value02		OBJECT-TYPE
			SYNTAX	INTEGER
			ACCESS	read-only
			STATUS	current
	DESCRIPTION ""
			::= { mbus88 11 }

mbus88VIF03		OBJECT-TYPE
			SYNTAX	INTEGER
			ACCESS	read-only
			STATUS	current
	DESCRIPTION ""
			::= { mbus88 12 }

mbus88Value03		OBJECT-TYPE
			SYNTAX	INTEGER
			ACCESS	read-only
			STATUS	current
	DESCRIPTION ""
			::= { mbus88 13 }

mbus88VIF04		OBJECT-TYPE
			SYNTAX	INTEGER
			ACCESS	read-only
			STATUS	current
	DESCRIPTION ""
			::= { mbus88 14 }

mbus88Value04		OBJECT-TYPE
			SYNTAX	INTEGER
			ACCESS	read-only
			STATUS	current
	DESCRIPTION ""
			::= { mbus88 15 }

mbus88VIF05		OBJECT-TYPE
			SYNTAX	INTEGER
			ACCESS	read-only
			STATUS	current
	DESCRIPTION ""
			::= { mbus88 16 }

mbus88Value05		OBJECT-TYPE
			SYNTAX	INTEGER
			ACCESS	read-only
			STATUS	current
	DESCRIPTION ""
			::= { mbus88 17 }

mbus88VIF06		OBJECT-TYPE
			SYNTAX	INTEGER
			ACCESS	read-only
			STATUS	current
	DESCRIPTION ""
			::= { mbus88 18 }

mbus88Value06		OBJECT-TYPE
			SYNTAX	INTEGER
			ACCESS	read-only
			STATUS	current
	DESCRIPTION ""
			::= { mbus88 19 }

mbus88VIF07		OBJECT-TYPE
			SYNTAX	INTEGER
			ACCESS	read-only
			STATUS	current
	DESCRIPTION ""
			::= { mbus88 20 }

mbus88Value07		OBJECT-TYPE
			SYNTAX	INTEGER
			ACCESS	read-only
			STATUS	current
	DESCRIPTION ""
			::= { mbus88 21 }

mbus88VIF08		OBJECT-TYPE
			SYNTAX	INTEGER
			ACCESS	read-only
			STATUS	current
	DESCRIPTION ""
			::= { mbus88 22 }

mbus88Value08		OBJECT-TYPE
			SYNTAX	INTEGER
			ACCESS	read-only
			STATUS	current
	DESCRIPTION ""
			::= { mbus88 23 }

mbus88VIF09		OBJECT-TYPE
			SYNTAX	INTEGER
			ACCESS	read-only
			STATUS	current
	DESCRIPTION ""
			::= { mbus88 24 }

mbus88Value09		OBJECT-TYPE
			SYNTAX	INTEGER
			ACCESS	read-only
			STATUS	current
	DESCRIPTION ""
			::= { mbus88 25 }

mbus88VIF0A		OBJECT-TYPE
			SYNTAX	INTEGER
			ACCESS	read-only
			STATUS	current
	DESCRIPTION ""
			::= { mbus88 26 }

mbus88Value0A		OBJECT-TYPE
			SYNTAX	INTEGER
			ACCESS	read-only
			STATUS	current
	DESCRIPTION ""
			::= { mbus88 27 }

mbus88VIF0B		OBJECT-TYPE
			SYNTAX	INTEGER
			ACCESS	read-only
			STATUS	current
	DESCRIPTION ""
			::= { mbus88 28 }

mbus88Value0B		OBJECT-TYPE
			SYNTAX	INTEGER
			ACCESS	read-only
			STATUS	current
	DESCRIPTION ""
			::= { mbus88 29 }

mbus88VIF0C		OBJECT-TYPE
			SYNTAX	INTEGER
			ACCESS	read-only
			STATUS	current
	DESCRIPTION ""
			::= { mbus88 30 }

mbus88Value0C		OBJECT-TYPE
			SYNTAX	INTEGER
			ACCESS	read-only
			STATUS	current
	DESCRIPTION ""
			::= { mbus88 31 }

mbus88VIF0D		OBJECT-TYPE
			SYNTAX	INTEGER
			ACCESS	read-only
			STATUS	current
	DESCRIPTION ""
			::= { mbus88 32 }

mbus88Value0D		OBJECT-TYPE
			SYNTAX	INTEGER
			ACCESS	read-only
			STATUS	current
	DESCRIPTION ""
			::= { mbus88 33 }

mbus88VIF0E		OBJECT-TYPE
			SYNTAX	INTEGER
			ACCESS	read-only
			STATUS	current
	DESCRIPTION ""
			::= { mbus88 34 }

mbus88Value0E		OBJECT-TYPE
			SYNTAX	INTEGER
			ACCESS	read-only
			STATUS	current
	DESCRIPTION ""
			::= { mbus88 35 }

mbus88VIF0F		OBJECT-TYPE
			SYNTAX	INTEGER
			ACCESS	read-only
			STATUS	current
	DESCRIPTION ""
			::= { mbus88 36 }

mbus88Value0F		OBJECT-TYPE
			SYNTAX	INTEGER
			ACCESS	read-only
			STATUS	current
	DESCRIPTION ""
			::= { mbus88 37 }

mbus88VIF10		OBJECT-TYPE
			SYNTAX	INTEGER
			ACCESS	read-only
			STATUS	current
	DESCRIPTION ""
			::= { mbus88 38 }

mbus88Value10		OBJECT-TYPE
			SYNTAX	INTEGER
			ACCESS	read-only
			STATUS	current
	DESCRIPTION ""
			::= { mbus88 39 }

mbus88VIF11		OBJECT-TYPE
			SYNTAX	INTEGER
			ACCESS	read-only
			STATUS	current
	DESCRIPTION ""
			::= { mbus88 40 }

mbus88Value11		OBJECT-TYPE
			SYNTAX	INTEGER
			ACCESS	read-only
			STATUS	current
	DESCRIPTION ""
			::= { mbus88 41 }

mbus88VIF12		OBJECT-TYPE
			SYNTAX	INTEGER
			ACCESS	read-only
			STATUS	current
	DESCRIPTION ""
			::= { mbus88 42 }

mbus88Value12		OBJECT-TYPE
			SYNTAX	INTEGER
			ACCESS	read-only
			STATUS	current
	DESCRIPTION ""
			::= { mbus88 43 }

mbus88VIF13		OBJECT-TYPE
			SYNTAX	INTEGER
			ACCESS	read-only
			STATUS	current
	DESCRIPTION ""
			::= { mbus88 44 }

mbus88Value13		OBJECT-TYPE
			SYNTAX	INTEGER
			ACCESS	read-only
			STATUS	current
	DESCRIPTION ""
			::= { mbus88 45 }

mbus88VIF14		OBJECT-TYPE
			SYNTAX	INTEGER
			ACCESS	read-only
			STATUS	current
	DESCRIPTION ""
			::= { mbus88 46 }

mbus88Value14		OBJECT-TYPE
			SYNTAX	INTEGER
			ACCESS	read-only
			STATUS	current
	DESCRIPTION ""
			::= { mbus88 47 }

mbus88VIF15		OBJECT-TYPE
			SYNTAX	INTEGER
			ACCESS	read-only
			STATUS	current
	DESCRIPTION ""
			::= { mbus88 48 }

mbus88Value15		OBJECT-TYPE
			SYNTAX	INTEGER
			ACCESS	read-only
			STATUS	current
	DESCRIPTION ""
			::= { mbus88 49 }

mbus88VIF16		OBJECT-TYPE
			SYNTAX	INTEGER
			ACCESS	read-only
			STATUS	current
	DESCRIPTION ""
			::= { mbus88 50 }

mbus88Value16		OBJECT-TYPE
			SYNTAX	INTEGER
			ACCESS	read-only
			STATUS	current
	DESCRIPTION ""
			::= { mbus88 51 }

mbus88VIF17		OBJECT-TYPE
			SYNTAX	INTEGER
			ACCESS	read-only
			STATUS	current
	DESCRIPTION ""
			::= { mbus88 52 }

mbus88Value17		OBJECT-TYPE
			SYNTAX	INTEGER
			ACCESS	read-only
			STATUS	current
	DESCRIPTION ""
			::= { mbus88 53 }

mbus88VIF18		OBJECT-TYPE
			SYNTAX	INTEGER
			ACCESS	read-only
			STATUS	current
	DESCRIPTION ""
			::= { mbus88 54 }

mbus88Value18		OBJECT-TYPE
			SYNTAX	INTEGER
			ACCESS	read-only
			STATUS	current
	DESCRIPTION ""
			::= { mbus88 55 }

mbus88VIF19		OBJECT-TYPE
			SYNTAX	INTEGER
			ACCESS	read-only
			STATUS	current
	DESCRIPTION ""
			::= { mbus88 56 }

mbus88Value19		OBJECT-TYPE
			SYNTAX	INTEGER
			ACCESS	read-only
			STATUS	current
	DESCRIPTION ""
			::= { mbus88 57 }

mbus88VIF1A		OBJECT-TYPE
			SYNTAX	INTEGER
			ACCESS	read-only
			STATUS	current
	DESCRIPTION ""
			::= { mbus88 58 }

mbus88Value1A		OBJECT-TYPE
			SYNTAX	INTEGER
			ACCESS	read-only
			STATUS	current
	DESCRIPTION ""
			::= { mbus88 59 }

mbus88VIF1B		OBJECT-TYPE
			SYNTAX	INTEGER
			ACCESS	read-only
			STATUS	current
	DESCRIPTION ""
			::= { mbus88 60 }

mbus88Value1B		OBJECT-TYPE
			SYNTAX	INTEGER
			ACCESS	read-only
			STATUS	current
	DESCRIPTION ""
			::= { mbus88 61 }

mbus88VIF1C		OBJECT-TYPE
			SYNTAX	INTEGER
			ACCESS	read-only
			STATUS	current
	DESCRIPTION ""
			::= { mbus88 62 }

mbus88Value1C		OBJECT-TYPE
			SYNTAX	INTEGER
			ACCESS	read-only
			STATUS	current
	DESCRIPTION ""
			::= { mbus88 63 }

mbus88VIF1D		OBJECT-TYPE
			SYNTAX	INTEGER
			ACCESS	read-only
			STATUS	current
	DESCRIPTION ""
			::= { mbus88 64 }

mbus88Value1D		OBJECT-TYPE
			SYNTAX	INTEGER
			ACCESS	read-only
			STATUS	current
	DESCRIPTION ""
			::= { mbus88 65 }

mbus88VIF1E		OBJECT-TYPE
			SYNTAX	INTEGER
			ACCESS	read-only
			STATUS	current
	DESCRIPTION ""
			::= { mbus88 66 }

mbus88Value1E		OBJECT-TYPE
			SYNTAX	INTEGER
			ACCESS	read-only
			STATUS	current
	DESCRIPTION ""
			::= { mbus88 67 }

mbus88VIF1F		OBJECT-TYPE
			SYNTAX	INTEGER
			ACCESS	read-only
			STATUS	current
	DESCRIPTION ""
			::= { mbus88 68 }

mbus88Value1F		OBJECT-TYPE
			SYNTAX	INTEGER
			ACCESS	read-only
			STATUS	current
	DESCRIPTION ""
			::= { mbus88 69 }

mbus88VIF20		OBJECT-TYPE
			SYNTAX	INTEGER
			ACCESS	read-only
			STATUS	current
	DESCRIPTION ""
			::= { mbus88 70 }

mbus88Value20		OBJECT-TYPE
			SYNTAX	INTEGER
			ACCESS	read-only
			STATUS	current
	DESCRIPTION ""
			::= { mbus88 71 }

mbus88VIF21		OBJECT-TYPE
			SYNTAX	INTEGER
			ACCESS	read-only
			STATUS	current
	DESCRIPTION ""
			::= { mbus88 72 }

mbus88Value21		OBJECT-TYPE
			SYNTAX	INTEGER
			ACCESS	read-only
			STATUS	current
	DESCRIPTION ""
			::= { mbus88 73 }

mbus88VIF22		OBJECT-TYPE
			SYNTAX	INTEGER
			ACCESS	read-only
			STATUS	current
	DESCRIPTION ""
			::= { mbus88 74 }

mbus88Value22		OBJECT-TYPE
			SYNTAX	INTEGER
			ACCESS	read-only
			STATUS	current
	DESCRIPTION ""
			::= { mbus88 75 }

mbus88VIF23		OBJECT-TYPE
			SYNTAX	INTEGER
			ACCESS	read-only
			STATUS	current
	DESCRIPTION ""
			::= { mbus88 76 }

mbus88Value23		OBJECT-TYPE
			SYNTAX	INTEGER
			ACCESS	read-only
			STATUS	current
	DESCRIPTION ""
			::= { mbus88 77 }

mbus88VIF24		OBJECT-TYPE
			SYNTAX	INTEGER
			ACCESS	read-only
			STATUS	current
	DESCRIPTION ""
			::= { mbus88 78 }

mbus88Value24		OBJECT-TYPE
			SYNTAX	INTEGER
			ACCESS	read-only
			STATUS	current
	DESCRIPTION ""
			::= { mbus88 79 }

mbus88VIF25		OBJECT-TYPE
			SYNTAX	INTEGER
			ACCESS	read-only
			STATUS	current
	DESCRIPTION ""
			::= { mbus88 80 }

mbus88Value25		OBJECT-TYPE
			SYNTAX	INTEGER
			ACCESS	read-only
			STATUS	current
	DESCRIPTION ""
			::= { mbus88 81 }

mbus88VIF26		OBJECT-TYPE
			SYNTAX	INTEGER
			ACCESS	read-only
			STATUS	current
	DESCRIPTION ""
			::= { mbus88 82 }

mbus88Value26		OBJECT-TYPE
			SYNTAX	INTEGER
			ACCESS	read-only
			STATUS	current
	DESCRIPTION ""
			::= { mbus88 83 }

mbus88VIF27		OBJECT-TYPE
			SYNTAX	INTEGER
			ACCESS	read-only
			STATUS	current
	DESCRIPTION ""
			::= { mbus88 84 }

mbus88Value27		OBJECT-TYPE
			SYNTAX	INTEGER
			ACCESS	read-only
			STATUS	current
	DESCRIPTION ""
			::= { mbus88 85 }

mbus88VIF28		OBJECT-TYPE
			SYNTAX	INTEGER
			ACCESS	read-only
			STATUS	current
	DESCRIPTION ""
			::= { mbus88 86 }

mbus88Value28		OBJECT-TYPE
			SYNTAX	INTEGER
			ACCESS	read-only
			STATUS	current
	DESCRIPTION ""
			::= { mbus88 87 }

mbus88VIF29		OBJECT-TYPE
			SYNTAX	INTEGER
			ACCESS	read-only
			STATUS	current
	DESCRIPTION ""
			::= { mbus88 88 }

mbus88Value29		OBJECT-TYPE
			SYNTAX	INTEGER
			ACCESS	read-only
			STATUS	current
	DESCRIPTION ""
			::= { mbus88 89 }

mbus88VIF2A		OBJECT-TYPE
			SYNTAX	INTEGER
			ACCESS	read-only
			STATUS	current
	DESCRIPTION ""
			::= { mbus88 90 }

mbus88Value2A		OBJECT-TYPE
			SYNTAX	INTEGER
			ACCESS	read-only
			STATUS	current
	DESCRIPTION ""
			::= { mbus88 91 }

mbus88VIF2B		OBJECT-TYPE
			SYNTAX	INTEGER
			ACCESS	read-only
			STATUS	current
	DESCRIPTION ""
			::= { mbus88 92 }

mbus88Value2B		OBJECT-TYPE
			SYNTAX	INTEGER
			ACCESS	read-only
			STATUS	current
	DESCRIPTION ""
			::= { mbus88 93 }

mbus88VIF2C		OBJECT-TYPE
			SYNTAX	INTEGER
			ACCESS	read-only
			STATUS	current
	DESCRIPTION ""
			::= { mbus88 94 }

mbus88Value2C		OBJECT-TYPE
			SYNTAX	INTEGER
			ACCESS	read-only
			STATUS	current
	DESCRIPTION ""
			::= { mbus88 95 }

mbus88VIF2D		OBJECT-TYPE
			SYNTAX	INTEGER
			ACCESS	read-only
			STATUS	current
	DESCRIPTION ""
			::= { mbus88 96 }

mbus88Value2D		OBJECT-TYPE
			SYNTAX	INTEGER
			ACCESS	read-only
			STATUS	current
	DESCRIPTION ""
			::= { mbus88 97 }

mbus88VIF2E		OBJECT-TYPE
			SYNTAX	INTEGER
			ACCESS	read-only
			STATUS	current
	DESCRIPTION ""
			::= { mbus88 98 }

mbus88Value2E		OBJECT-TYPE
			SYNTAX	INTEGER
			ACCESS	read-only
			STATUS	current
	DESCRIPTION ""
			::= { mbus88 99 }

mbus88VIF2F		OBJECT-TYPE
			SYNTAX	INTEGER
			ACCESS	read-only
			STATUS	current
	DESCRIPTION ""
			::= { mbus88 100 }

mbus88Value2F		OBJECT-TYPE
			SYNTAX	INTEGER
			ACCESS	read-only
			STATUS	current
	DESCRIPTION ""
			::= { mbus88 101 }

mbus89			OBJECT IDENTIFIER ::= { mbus 137 }

mbus89IdNumber		OBJECT-TYPE
			SYNTAX	Gauge
			ACCESS	read-only
			STATUS	current
	DESCRIPTION ""
			::= { mbus89 1 }

mbus89Manufacturer	OBJECT-TYPE
			SYNTAX	Gauge
			ACCESS	read-only
			STATUS	current
	DESCRIPTION ""
			::= { mbus89 2 }

mbus89Version		OBJECT-TYPE
			SYNTAX	Gauge
			ACCESS	read-only
			STATUS	current
	DESCRIPTION ""
			::= { mbus89 3 }

mbus89Medium		OBJECT-TYPE
			SYNTAX	Gauge
			ACCESS	read-only
			STATUS	current
	DESCRIPTION ""
			::= { mbus89 4 }

mbus89Status		OBJECT-TYPE
			SYNTAX	Gauge
			ACCESS	read-only
			STATUS	current
	DESCRIPTION ""
			::= { mbus89 5 }

mbus89VIF00		OBJECT-TYPE
			SYNTAX	INTEGER
			ACCESS	read-only
			STATUS	current
	DESCRIPTION ""
			::= { mbus89 6 }

mbus89Value00		OBJECT-TYPE
			SYNTAX	INTEGER
			ACCESS	read-only
			STATUS	current
	DESCRIPTION ""
			::= { mbus89 7 }

mbus89VIF01		OBJECT-TYPE
			SYNTAX	INTEGER
			ACCESS	read-only
			STATUS	current
	DESCRIPTION ""
			::= { mbus89 8 }

mbus89Value01		OBJECT-TYPE
			SYNTAX	INTEGER
			ACCESS	read-only
			STATUS	current
	DESCRIPTION ""
			::= { mbus89 9 }

mbus89VIF02		OBJECT-TYPE
			SYNTAX	INTEGER
			ACCESS	read-only
			STATUS	current
	DESCRIPTION ""
			::= { mbus89 10 }

mbus89Value02		OBJECT-TYPE
			SYNTAX	INTEGER
			ACCESS	read-only
			STATUS	current
	DESCRIPTION ""
			::= { mbus89 11 }

mbus89VIF03		OBJECT-TYPE
			SYNTAX	INTEGER
			ACCESS	read-only
			STATUS	current
	DESCRIPTION ""
			::= { mbus89 12 }

mbus89Value03		OBJECT-TYPE
			SYNTAX	INTEGER
			ACCESS	read-only
			STATUS	current
	DESCRIPTION ""
			::= { mbus89 13 }

mbus89VIF04		OBJECT-TYPE
			SYNTAX	INTEGER
			ACCESS	read-only
			STATUS	current
	DESCRIPTION ""
			::= { mbus89 14 }

mbus89Value04		OBJECT-TYPE
			SYNTAX	INTEGER
			ACCESS	read-only
			STATUS	current
	DESCRIPTION ""
			::= { mbus89 15 }

mbus89VIF05		OBJECT-TYPE
			SYNTAX	INTEGER
			ACCESS	read-only
			STATUS	current
	DESCRIPTION ""
			::= { mbus89 16 }

mbus89Value05		OBJECT-TYPE
			SYNTAX	INTEGER
			ACCESS	read-only
			STATUS	current
	DESCRIPTION ""
			::= { mbus89 17 }

mbus89VIF06		OBJECT-TYPE
			SYNTAX	INTEGER
			ACCESS	read-only
			STATUS	current
	DESCRIPTION ""
			::= { mbus89 18 }

mbus89Value06		OBJECT-TYPE
			SYNTAX	INTEGER
			ACCESS	read-only
			STATUS	current
	DESCRIPTION ""
			::= { mbus89 19 }

mbus89VIF07		OBJECT-TYPE
			SYNTAX	INTEGER
			ACCESS	read-only
			STATUS	current
	DESCRIPTION ""
			::= { mbus89 20 }

mbus89Value07		OBJECT-TYPE
			SYNTAX	INTEGER
			ACCESS	read-only
			STATUS	current
	DESCRIPTION ""
			::= { mbus89 21 }

mbus89VIF08		OBJECT-TYPE
			SYNTAX	INTEGER
			ACCESS	read-only
			STATUS	current
	DESCRIPTION ""
			::= { mbus89 22 }

mbus89Value08		OBJECT-TYPE
			SYNTAX	INTEGER
			ACCESS	read-only
			STATUS	current
	DESCRIPTION ""
			::= { mbus89 23 }

mbus89VIF09		OBJECT-TYPE
			SYNTAX	INTEGER
			ACCESS	read-only
			STATUS	current
	DESCRIPTION ""
			::= { mbus89 24 }

mbus89Value09		OBJECT-TYPE
			SYNTAX	INTEGER
			ACCESS	read-only
			STATUS	current
	DESCRIPTION ""
			::= { mbus89 25 }

mbus89VIF0A		OBJECT-TYPE
			SYNTAX	INTEGER
			ACCESS	read-only
			STATUS	current
	DESCRIPTION ""
			::= { mbus89 26 }

mbus89Value0A		OBJECT-TYPE
			SYNTAX	INTEGER
			ACCESS	read-only
			STATUS	current
	DESCRIPTION ""
			::= { mbus89 27 }

mbus89VIF0B		OBJECT-TYPE
			SYNTAX	INTEGER
			ACCESS	read-only
			STATUS	current
	DESCRIPTION ""
			::= { mbus89 28 }

mbus89Value0B		OBJECT-TYPE
			SYNTAX	INTEGER
			ACCESS	read-only
			STATUS	current
	DESCRIPTION ""
			::= { mbus89 29 }

mbus89VIF0C		OBJECT-TYPE
			SYNTAX	INTEGER
			ACCESS	read-only
			STATUS	current
	DESCRIPTION ""
			::= { mbus89 30 }

mbus89Value0C		OBJECT-TYPE
			SYNTAX	INTEGER
			ACCESS	read-only
			STATUS	current
	DESCRIPTION ""
			::= { mbus89 31 }

mbus89VIF0D		OBJECT-TYPE
			SYNTAX	INTEGER
			ACCESS	read-only
			STATUS	current
	DESCRIPTION ""
			::= { mbus89 32 }

mbus89Value0D		OBJECT-TYPE
			SYNTAX	INTEGER
			ACCESS	read-only
			STATUS	current
	DESCRIPTION ""
			::= { mbus89 33 }

mbus89VIF0E		OBJECT-TYPE
			SYNTAX	INTEGER
			ACCESS	read-only
			STATUS	current
	DESCRIPTION ""
			::= { mbus89 34 }

mbus89Value0E		OBJECT-TYPE
			SYNTAX	INTEGER
			ACCESS	read-only
			STATUS	current
	DESCRIPTION ""
			::= { mbus89 35 }

mbus89VIF0F		OBJECT-TYPE
			SYNTAX	INTEGER
			ACCESS	read-only
			STATUS	current
	DESCRIPTION ""
			::= { mbus89 36 }

mbus89Value0F		OBJECT-TYPE
			SYNTAX	INTEGER
			ACCESS	read-only
			STATUS	current
	DESCRIPTION ""
			::= { mbus89 37 }

mbus89VIF10		OBJECT-TYPE
			SYNTAX	INTEGER
			ACCESS	read-only
			STATUS	current
	DESCRIPTION ""
			::= { mbus89 38 }

mbus89Value10		OBJECT-TYPE
			SYNTAX	INTEGER
			ACCESS	read-only
			STATUS	current
	DESCRIPTION ""
			::= { mbus89 39 }

mbus89VIF11		OBJECT-TYPE
			SYNTAX	INTEGER
			ACCESS	read-only
			STATUS	current
	DESCRIPTION ""
			::= { mbus89 40 }

mbus89Value11		OBJECT-TYPE
			SYNTAX	INTEGER
			ACCESS	read-only
			STATUS	current
	DESCRIPTION ""
			::= { mbus89 41 }

mbus89VIF12		OBJECT-TYPE
			SYNTAX	INTEGER
			ACCESS	read-only
			STATUS	current
	DESCRIPTION ""
			::= { mbus89 42 }

mbus89Value12		OBJECT-TYPE
			SYNTAX	INTEGER
			ACCESS	read-only
			STATUS	current
	DESCRIPTION ""
			::= { mbus89 43 }

mbus89VIF13		OBJECT-TYPE
			SYNTAX	INTEGER
			ACCESS	read-only
			STATUS	current
	DESCRIPTION ""
			::= { mbus89 44 }

mbus89Value13		OBJECT-TYPE
			SYNTAX	INTEGER
			ACCESS	read-only
			STATUS	current
	DESCRIPTION ""
			::= { mbus89 45 }

mbus89VIF14		OBJECT-TYPE
			SYNTAX	INTEGER
			ACCESS	read-only
			STATUS	current
	DESCRIPTION ""
			::= { mbus89 46 }

mbus89Value14		OBJECT-TYPE
			SYNTAX	INTEGER
			ACCESS	read-only
			STATUS	current
	DESCRIPTION ""
			::= { mbus89 47 }

mbus89VIF15		OBJECT-TYPE
			SYNTAX	INTEGER
			ACCESS	read-only
			STATUS	current
	DESCRIPTION ""
			::= { mbus89 48 }

mbus89Value15		OBJECT-TYPE
			SYNTAX	INTEGER
			ACCESS	read-only
			STATUS	current
	DESCRIPTION ""
			::= { mbus89 49 }

mbus89VIF16		OBJECT-TYPE
			SYNTAX	INTEGER
			ACCESS	read-only
			STATUS	current
	DESCRIPTION ""
			::= { mbus89 50 }

mbus89Value16		OBJECT-TYPE
			SYNTAX	INTEGER
			ACCESS	read-only
			STATUS	current
	DESCRIPTION ""
			::= { mbus89 51 }

mbus89VIF17		OBJECT-TYPE
			SYNTAX	INTEGER
			ACCESS	read-only
			STATUS	current
	DESCRIPTION ""
			::= { mbus89 52 }

mbus89Value17		OBJECT-TYPE
			SYNTAX	INTEGER
			ACCESS	read-only
			STATUS	current
	DESCRIPTION ""
			::= { mbus89 53 }

mbus89VIF18		OBJECT-TYPE
			SYNTAX	INTEGER
			ACCESS	read-only
			STATUS	current
	DESCRIPTION ""
			::= { mbus89 54 }

mbus89Value18		OBJECT-TYPE
			SYNTAX	INTEGER
			ACCESS	read-only
			STATUS	current
	DESCRIPTION ""
			::= { mbus89 55 }

mbus89VIF19		OBJECT-TYPE
			SYNTAX	INTEGER
			ACCESS	read-only
			STATUS	current
	DESCRIPTION ""
			::= { mbus89 56 }

mbus89Value19		OBJECT-TYPE
			SYNTAX	INTEGER
			ACCESS	read-only
			STATUS	current
	DESCRIPTION ""
			::= { mbus89 57 }

mbus89VIF1A		OBJECT-TYPE
			SYNTAX	INTEGER
			ACCESS	read-only
			STATUS	current
	DESCRIPTION ""
			::= { mbus89 58 }

mbus89Value1A		OBJECT-TYPE
			SYNTAX	INTEGER
			ACCESS	read-only
			STATUS	current
	DESCRIPTION ""
			::= { mbus89 59 }

mbus89VIF1B		OBJECT-TYPE
			SYNTAX	INTEGER
			ACCESS	read-only
			STATUS	current
	DESCRIPTION ""
			::= { mbus89 60 }

mbus89Value1B		OBJECT-TYPE
			SYNTAX	INTEGER
			ACCESS	read-only
			STATUS	current
	DESCRIPTION ""
			::= { mbus89 61 }

mbus89VIF1C		OBJECT-TYPE
			SYNTAX	INTEGER
			ACCESS	read-only
			STATUS	current
	DESCRIPTION ""
			::= { mbus89 62 }

mbus89Value1C		OBJECT-TYPE
			SYNTAX	INTEGER
			ACCESS	read-only
			STATUS	current
	DESCRIPTION ""
			::= { mbus89 63 }

mbus89VIF1D		OBJECT-TYPE
			SYNTAX	INTEGER
			ACCESS	read-only
			STATUS	current
	DESCRIPTION ""
			::= { mbus89 64 }

mbus89Value1D		OBJECT-TYPE
			SYNTAX	INTEGER
			ACCESS	read-only
			STATUS	current
	DESCRIPTION ""
			::= { mbus89 65 }

mbus89VIF1E		OBJECT-TYPE
			SYNTAX	INTEGER
			ACCESS	read-only
			STATUS	current
	DESCRIPTION ""
			::= { mbus89 66 }

mbus89Value1E		OBJECT-TYPE
			SYNTAX	INTEGER
			ACCESS	read-only
			STATUS	current
	DESCRIPTION ""
			::= { mbus89 67 }

mbus89VIF1F		OBJECT-TYPE
			SYNTAX	INTEGER
			ACCESS	read-only
			STATUS	current
	DESCRIPTION ""
			::= { mbus89 68 }

mbus89Value1F		OBJECT-TYPE
			SYNTAX	INTEGER
			ACCESS	read-only
			STATUS	current
	DESCRIPTION ""
			::= { mbus89 69 }

mbus89VIF20		OBJECT-TYPE
			SYNTAX	INTEGER
			ACCESS	read-only
			STATUS	current
	DESCRIPTION ""
			::= { mbus89 70 }

mbus89Value20		OBJECT-TYPE
			SYNTAX	INTEGER
			ACCESS	read-only
			STATUS	current
	DESCRIPTION ""
			::= { mbus89 71 }

mbus89VIF21		OBJECT-TYPE
			SYNTAX	INTEGER
			ACCESS	read-only
			STATUS	current
	DESCRIPTION ""
			::= { mbus89 72 }

mbus89Value21		OBJECT-TYPE
			SYNTAX	INTEGER
			ACCESS	read-only
			STATUS	current
	DESCRIPTION ""
			::= { mbus89 73 }

mbus89VIF22		OBJECT-TYPE
			SYNTAX	INTEGER
			ACCESS	read-only
			STATUS	current
	DESCRIPTION ""
			::= { mbus89 74 }

mbus89Value22		OBJECT-TYPE
			SYNTAX	INTEGER
			ACCESS	read-only
			STATUS	current
	DESCRIPTION ""
			::= { mbus89 75 }

mbus89VIF23		OBJECT-TYPE
			SYNTAX	INTEGER
			ACCESS	read-only
			STATUS	current
	DESCRIPTION ""
			::= { mbus89 76 }

mbus89Value23		OBJECT-TYPE
			SYNTAX	INTEGER
			ACCESS	read-only
			STATUS	current
	DESCRIPTION ""
			::= { mbus89 77 }

mbus89VIF24		OBJECT-TYPE
			SYNTAX	INTEGER
			ACCESS	read-only
			STATUS	current
	DESCRIPTION ""
			::= { mbus89 78 }

mbus89Value24		OBJECT-TYPE
			SYNTAX	INTEGER
			ACCESS	read-only
			STATUS	current
	DESCRIPTION ""
			::= { mbus89 79 }

mbus89VIF25		OBJECT-TYPE
			SYNTAX	INTEGER
			ACCESS	read-only
			STATUS	current
	DESCRIPTION ""
			::= { mbus89 80 }

mbus89Value25		OBJECT-TYPE
			SYNTAX	INTEGER
			ACCESS	read-only
			STATUS	current
	DESCRIPTION ""
			::= { mbus89 81 }

mbus89VIF26		OBJECT-TYPE
			SYNTAX	INTEGER
			ACCESS	read-only
			STATUS	current
	DESCRIPTION ""
			::= { mbus89 82 }

mbus89Value26		OBJECT-TYPE
			SYNTAX	INTEGER
			ACCESS	read-only
			STATUS	current
	DESCRIPTION ""
			::= { mbus89 83 }

mbus89VIF27		OBJECT-TYPE
			SYNTAX	INTEGER
			ACCESS	read-only
			STATUS	current
	DESCRIPTION ""
			::= { mbus89 84 }

mbus89Value27		OBJECT-TYPE
			SYNTAX	INTEGER
			ACCESS	read-only
			STATUS	current
	DESCRIPTION ""
			::= { mbus89 85 }

mbus89VIF28		OBJECT-TYPE
			SYNTAX	INTEGER
			ACCESS	read-only
			STATUS	current
	DESCRIPTION ""
			::= { mbus89 86 }

mbus89Value28		OBJECT-TYPE
			SYNTAX	INTEGER
			ACCESS	read-only
			STATUS	current
	DESCRIPTION ""
			::= { mbus89 87 }

mbus89VIF29		OBJECT-TYPE
			SYNTAX	INTEGER
			ACCESS	read-only
			STATUS	current
	DESCRIPTION ""
			::= { mbus89 88 }

mbus89Value29		OBJECT-TYPE
			SYNTAX	INTEGER
			ACCESS	read-only
			STATUS	current
	DESCRIPTION ""
			::= { mbus89 89 }

mbus89VIF2A		OBJECT-TYPE
			SYNTAX	INTEGER
			ACCESS	read-only
			STATUS	current
	DESCRIPTION ""
			::= { mbus89 90 }

mbus89Value2A		OBJECT-TYPE
			SYNTAX	INTEGER
			ACCESS	read-only
			STATUS	current
	DESCRIPTION ""
			::= { mbus89 91 }

mbus89VIF2B		OBJECT-TYPE
			SYNTAX	INTEGER
			ACCESS	read-only
			STATUS	current
	DESCRIPTION ""
			::= { mbus89 92 }

mbus89Value2B		OBJECT-TYPE
			SYNTAX	INTEGER
			ACCESS	read-only
			STATUS	current
	DESCRIPTION ""
			::= { mbus89 93 }

mbus89VIF2C		OBJECT-TYPE
			SYNTAX	INTEGER
			ACCESS	read-only
			STATUS	current
	DESCRIPTION ""
			::= { mbus89 94 }

mbus89Value2C		OBJECT-TYPE
			SYNTAX	INTEGER
			ACCESS	read-only
			STATUS	current
	DESCRIPTION ""
			::= { mbus89 95 }

mbus89VIF2D		OBJECT-TYPE
			SYNTAX	INTEGER
			ACCESS	read-only
			STATUS	current
	DESCRIPTION ""
			::= { mbus89 96 }

mbus89Value2D		OBJECT-TYPE
			SYNTAX	INTEGER
			ACCESS	read-only
			STATUS	current
	DESCRIPTION ""
			::= { mbus89 97 }

mbus89VIF2E		OBJECT-TYPE
			SYNTAX	INTEGER
			ACCESS	read-only
			STATUS	current
	DESCRIPTION ""
			::= { mbus89 98 }

mbus89Value2E		OBJECT-TYPE
			SYNTAX	INTEGER
			ACCESS	read-only
			STATUS	current
	DESCRIPTION ""
			::= { mbus89 99 }

mbus89VIF2F		OBJECT-TYPE
			SYNTAX	INTEGER
			ACCESS	read-only
			STATUS	current
	DESCRIPTION ""
			::= { mbus89 100 }

mbus89Value2F		OBJECT-TYPE
			SYNTAX	INTEGER
			ACCESS	read-only
			STATUS	current
	DESCRIPTION ""
			::= { mbus89 101 }

mbus8A			OBJECT IDENTIFIER ::= { mbus 138 }

mbus8AIdNumber		OBJECT-TYPE
			SYNTAX	Gauge
			ACCESS	read-only
			STATUS	current
	DESCRIPTION ""
			::= { mbus8A 1 }

mbus8AManufacturer	OBJECT-TYPE
			SYNTAX	Gauge
			ACCESS	read-only
			STATUS	current
	DESCRIPTION ""
			::= { mbus8A 2 }

mbus8AVersion		OBJECT-TYPE
			SYNTAX	Gauge
			ACCESS	read-only
			STATUS	current
	DESCRIPTION ""
			::= { mbus8A 3 }

mbus8AMedium		OBJECT-TYPE
			SYNTAX	Gauge
			ACCESS	read-only
			STATUS	current
	DESCRIPTION ""
			::= { mbus8A 4 }

mbus8AStatus		OBJECT-TYPE
			SYNTAX	Gauge
			ACCESS	read-only
			STATUS	current
	DESCRIPTION ""
			::= { mbus8A 5 }

mbus8AVIF00		OBJECT-TYPE
			SYNTAX	INTEGER
			ACCESS	read-only
			STATUS	current
	DESCRIPTION ""
			::= { mbus8A 6 }

mbus8AValue00		OBJECT-TYPE
			SYNTAX	INTEGER
			ACCESS	read-only
			STATUS	current
	DESCRIPTION ""
			::= { mbus8A 7 }

mbus8AVIF01		OBJECT-TYPE
			SYNTAX	INTEGER
			ACCESS	read-only
			STATUS	current
	DESCRIPTION ""
			::= { mbus8A 8 }

mbus8AValue01		OBJECT-TYPE
			SYNTAX	INTEGER
			ACCESS	read-only
			STATUS	current
	DESCRIPTION ""
			::= { mbus8A 9 }

mbus8AVIF02		OBJECT-TYPE
			SYNTAX	INTEGER
			ACCESS	read-only
			STATUS	current
	DESCRIPTION ""
			::= { mbus8A 10 }

mbus8AValue02		OBJECT-TYPE
			SYNTAX	INTEGER
			ACCESS	read-only
			STATUS	current
	DESCRIPTION ""
			::= { mbus8A 11 }

mbus8AVIF03		OBJECT-TYPE
			SYNTAX	INTEGER
			ACCESS	read-only
			STATUS	current
	DESCRIPTION ""
			::= { mbus8A 12 }

mbus8AValue03		OBJECT-TYPE
			SYNTAX	INTEGER
			ACCESS	read-only
			STATUS	current
	DESCRIPTION ""
			::= { mbus8A 13 }

mbus8AVIF04		OBJECT-TYPE
			SYNTAX	INTEGER
			ACCESS	read-only
			STATUS	current
	DESCRIPTION ""
			::= { mbus8A 14 }

mbus8AValue04		OBJECT-TYPE
			SYNTAX	INTEGER
			ACCESS	read-only
			STATUS	current
	DESCRIPTION ""
			::= { mbus8A 15 }

mbus8AVIF05		OBJECT-TYPE
			SYNTAX	INTEGER
			ACCESS	read-only
			STATUS	current
	DESCRIPTION ""
			::= { mbus8A 16 }

mbus8AValue05		OBJECT-TYPE
			SYNTAX	INTEGER
			ACCESS	read-only
			STATUS	current
	DESCRIPTION ""
			::= { mbus8A 17 }

mbus8AVIF06		OBJECT-TYPE
			SYNTAX	INTEGER
			ACCESS	read-only
			STATUS	current
	DESCRIPTION ""
			::= { mbus8A 18 }

mbus8AValue06		OBJECT-TYPE
			SYNTAX	INTEGER
			ACCESS	read-only
			STATUS	current
	DESCRIPTION ""
			::= { mbus8A 19 }

mbus8AVIF07		OBJECT-TYPE
			SYNTAX	INTEGER
			ACCESS	read-only
			STATUS	current
	DESCRIPTION ""
			::= { mbus8A 20 }

mbus8AValue07		OBJECT-TYPE
			SYNTAX	INTEGER
			ACCESS	read-only
			STATUS	current
	DESCRIPTION ""
			::= { mbus8A 21 }

mbus8AVIF08		OBJECT-TYPE
			SYNTAX	INTEGER
			ACCESS	read-only
			STATUS	current
	DESCRIPTION ""
			::= { mbus8A 22 }

mbus8AValue08		OBJECT-TYPE
			SYNTAX	INTEGER
			ACCESS	read-only
			STATUS	current
	DESCRIPTION ""
			::= { mbus8A 23 }

mbus8AVIF09		OBJECT-TYPE
			SYNTAX	INTEGER
			ACCESS	read-only
			STATUS	current
	DESCRIPTION ""
			::= { mbus8A 24 }

mbus8AValue09		OBJECT-TYPE
			SYNTAX	INTEGER
			ACCESS	read-only
			STATUS	current
	DESCRIPTION ""
			::= { mbus8A 25 }

mbus8AVIF0A		OBJECT-TYPE
			SYNTAX	INTEGER
			ACCESS	read-only
			STATUS	current
	DESCRIPTION ""
			::= { mbus8A 26 }

mbus8AValue0A		OBJECT-TYPE
			SYNTAX	INTEGER
			ACCESS	read-only
			STATUS	current
	DESCRIPTION ""
			::= { mbus8A 27 }

mbus8AVIF0B		OBJECT-TYPE
			SYNTAX	INTEGER
			ACCESS	read-only
			STATUS	current
	DESCRIPTION ""
			::= { mbus8A 28 }

mbus8AValue0B		OBJECT-TYPE
			SYNTAX	INTEGER
			ACCESS	read-only
			STATUS	current
	DESCRIPTION ""
			::= { mbus8A 29 }

mbus8AVIF0C		OBJECT-TYPE
			SYNTAX	INTEGER
			ACCESS	read-only
			STATUS	current
	DESCRIPTION ""
			::= { mbus8A 30 }

mbus8AValue0C		OBJECT-TYPE
			SYNTAX	INTEGER
			ACCESS	read-only
			STATUS	current
	DESCRIPTION ""
			::= { mbus8A 31 }

mbus8AVIF0D		OBJECT-TYPE
			SYNTAX	INTEGER
			ACCESS	read-only
			STATUS	current
	DESCRIPTION ""
			::= { mbus8A 32 }

mbus8AValue0D		OBJECT-TYPE
			SYNTAX	INTEGER
			ACCESS	read-only
			STATUS	current
	DESCRIPTION ""
			::= { mbus8A 33 }

mbus8AVIF0E		OBJECT-TYPE
			SYNTAX	INTEGER
			ACCESS	read-only
			STATUS	current
	DESCRIPTION ""
			::= { mbus8A 34 }

mbus8AValue0E		OBJECT-TYPE
			SYNTAX	INTEGER
			ACCESS	read-only
			STATUS	current
	DESCRIPTION ""
			::= { mbus8A 35 }

mbus8AVIF0F		OBJECT-TYPE
			SYNTAX	INTEGER
			ACCESS	read-only
			STATUS	current
	DESCRIPTION ""
			::= { mbus8A 36 }

mbus8AValue0F		OBJECT-TYPE
			SYNTAX	INTEGER
			ACCESS	read-only
			STATUS	current
	DESCRIPTION ""
			::= { mbus8A 37 }

mbus8AVIF10		OBJECT-TYPE
			SYNTAX	INTEGER
			ACCESS	read-only
			STATUS	current
	DESCRIPTION ""
			::= { mbus8A 38 }

mbus8AValue10		OBJECT-TYPE
			SYNTAX	INTEGER
			ACCESS	read-only
			STATUS	current
	DESCRIPTION ""
			::= { mbus8A 39 }

mbus8AVIF11		OBJECT-TYPE
			SYNTAX	INTEGER
			ACCESS	read-only
			STATUS	current
	DESCRIPTION ""
			::= { mbus8A 40 }

mbus8AValue11		OBJECT-TYPE
			SYNTAX	INTEGER
			ACCESS	read-only
			STATUS	current
	DESCRIPTION ""
			::= { mbus8A 41 }

mbus8AVIF12		OBJECT-TYPE
			SYNTAX	INTEGER
			ACCESS	read-only
			STATUS	current
	DESCRIPTION ""
			::= { mbus8A 42 }

mbus8AValue12		OBJECT-TYPE
			SYNTAX	INTEGER
			ACCESS	read-only
			STATUS	current
	DESCRIPTION ""
			::= { mbus8A 43 }

mbus8AVIF13		OBJECT-TYPE
			SYNTAX	INTEGER
			ACCESS	read-only
			STATUS	current
	DESCRIPTION ""
			::= { mbus8A 44 }

mbus8AValue13		OBJECT-TYPE
			SYNTAX	INTEGER
			ACCESS	read-only
			STATUS	current
	DESCRIPTION ""
			::= { mbus8A 45 }

mbus8AVIF14		OBJECT-TYPE
			SYNTAX	INTEGER
			ACCESS	read-only
			STATUS	current
	DESCRIPTION ""
			::= { mbus8A 46 }

mbus8AValue14		OBJECT-TYPE
			SYNTAX	INTEGER
			ACCESS	read-only
			STATUS	current
	DESCRIPTION ""
			::= { mbus8A 47 }

mbus8AVIF15		OBJECT-TYPE
			SYNTAX	INTEGER
			ACCESS	read-only
			STATUS	current
	DESCRIPTION ""
			::= { mbus8A 48 }

mbus8AValue15		OBJECT-TYPE
			SYNTAX	INTEGER
			ACCESS	read-only
			STATUS	current
	DESCRIPTION ""
			::= { mbus8A 49 }

mbus8AVIF16		OBJECT-TYPE
			SYNTAX	INTEGER
			ACCESS	read-only
			STATUS	current
	DESCRIPTION ""
			::= { mbus8A 50 }

mbus8AValue16		OBJECT-TYPE
			SYNTAX	INTEGER
			ACCESS	read-only
			STATUS	current
	DESCRIPTION ""
			::= { mbus8A 51 }

mbus8AVIF17		OBJECT-TYPE
			SYNTAX	INTEGER
			ACCESS	read-only
			STATUS	current
	DESCRIPTION ""
			::= { mbus8A 52 }

mbus8AValue17		OBJECT-TYPE
			SYNTAX	INTEGER
			ACCESS	read-only
			STATUS	current
	DESCRIPTION ""
			::= { mbus8A 53 }

mbus8AVIF18		OBJECT-TYPE
			SYNTAX	INTEGER
			ACCESS	read-only
			STATUS	current
	DESCRIPTION ""
			::= { mbus8A 54 }

mbus8AValue18		OBJECT-TYPE
			SYNTAX	INTEGER
			ACCESS	read-only
			STATUS	current
	DESCRIPTION ""
			::= { mbus8A 55 }

mbus8AVIF19		OBJECT-TYPE
			SYNTAX	INTEGER
			ACCESS	read-only
			STATUS	current
	DESCRIPTION ""
			::= { mbus8A 56 }

mbus8AValue19		OBJECT-TYPE
			SYNTAX	INTEGER
			ACCESS	read-only
			STATUS	current
	DESCRIPTION ""
			::= { mbus8A 57 }

mbus8AVIF1A		OBJECT-TYPE
			SYNTAX	INTEGER
			ACCESS	read-only
			STATUS	current
	DESCRIPTION ""
			::= { mbus8A 58 }

mbus8AValue1A		OBJECT-TYPE
			SYNTAX	INTEGER
			ACCESS	read-only
			STATUS	current
	DESCRIPTION ""
			::= { mbus8A 59 }

mbus8AVIF1B		OBJECT-TYPE
			SYNTAX	INTEGER
			ACCESS	read-only
			STATUS	current
	DESCRIPTION ""
			::= { mbus8A 60 }

mbus8AValue1B		OBJECT-TYPE
			SYNTAX	INTEGER
			ACCESS	read-only
			STATUS	current
	DESCRIPTION ""
			::= { mbus8A 61 }

mbus8AVIF1C		OBJECT-TYPE
			SYNTAX	INTEGER
			ACCESS	read-only
			STATUS	current
	DESCRIPTION ""
			::= { mbus8A 62 }

mbus8AValue1C		OBJECT-TYPE
			SYNTAX	INTEGER
			ACCESS	read-only
			STATUS	current
	DESCRIPTION ""
			::= { mbus8A 63 }

mbus8AVIF1D		OBJECT-TYPE
			SYNTAX	INTEGER
			ACCESS	read-only
			STATUS	current
	DESCRIPTION ""
			::= { mbus8A 64 }

mbus8AValue1D		OBJECT-TYPE
			SYNTAX	INTEGER
			ACCESS	read-only
			STATUS	current
	DESCRIPTION ""
			::= { mbus8A 65 }

mbus8AVIF1E		OBJECT-TYPE
			SYNTAX	INTEGER
			ACCESS	read-only
			STATUS	current
	DESCRIPTION ""
			::= { mbus8A 66 }

mbus8AValue1E		OBJECT-TYPE
			SYNTAX	INTEGER
			ACCESS	read-only
			STATUS	current
	DESCRIPTION ""
			::= { mbus8A 67 }

mbus8AVIF1F		OBJECT-TYPE
			SYNTAX	INTEGER
			ACCESS	read-only
			STATUS	current
	DESCRIPTION ""
			::= { mbus8A 68 }

mbus8AValue1F		OBJECT-TYPE
			SYNTAX	INTEGER
			ACCESS	read-only
			STATUS	current
	DESCRIPTION ""
			::= { mbus8A 69 }

mbus8AVIF20		OBJECT-TYPE
			SYNTAX	INTEGER
			ACCESS	read-only
			STATUS	current
	DESCRIPTION ""
			::= { mbus8A 70 }

mbus8AValue20		OBJECT-TYPE
			SYNTAX	INTEGER
			ACCESS	read-only
			STATUS	current
	DESCRIPTION ""
			::= { mbus8A 71 }

mbus8AVIF21		OBJECT-TYPE
			SYNTAX	INTEGER
			ACCESS	read-only
			STATUS	current
	DESCRIPTION ""
			::= { mbus8A 72 }

mbus8AValue21		OBJECT-TYPE
			SYNTAX	INTEGER
			ACCESS	read-only
			STATUS	current
	DESCRIPTION ""
			::= { mbus8A 73 }

mbus8AVIF22		OBJECT-TYPE
			SYNTAX	INTEGER
			ACCESS	read-only
			STATUS	current
	DESCRIPTION ""
			::= { mbus8A 74 }

mbus8AValue22		OBJECT-TYPE
			SYNTAX	INTEGER
			ACCESS	read-only
			STATUS	current
	DESCRIPTION ""
			::= { mbus8A 75 }

mbus8AVIF23		OBJECT-TYPE
			SYNTAX	INTEGER
			ACCESS	read-only
			STATUS	current
	DESCRIPTION ""
			::= { mbus8A 76 }

mbus8AValue23		OBJECT-TYPE
			SYNTAX	INTEGER
			ACCESS	read-only
			STATUS	current
	DESCRIPTION ""
			::= { mbus8A 77 }

mbus8AVIF24		OBJECT-TYPE
			SYNTAX	INTEGER
			ACCESS	read-only
			STATUS	current
	DESCRIPTION ""
			::= { mbus8A 78 }

mbus8AValue24		OBJECT-TYPE
			SYNTAX	INTEGER
			ACCESS	read-only
			STATUS	current
	DESCRIPTION ""
			::= { mbus8A 79 }

mbus8AVIF25		OBJECT-TYPE
			SYNTAX	INTEGER
			ACCESS	read-only
			STATUS	current
	DESCRIPTION ""
			::= { mbus8A 80 }

mbus8AValue25		OBJECT-TYPE
			SYNTAX	INTEGER
			ACCESS	read-only
			STATUS	current
	DESCRIPTION ""
			::= { mbus8A 81 }

mbus8AVIF26		OBJECT-TYPE
			SYNTAX	INTEGER
			ACCESS	read-only
			STATUS	current
	DESCRIPTION ""
			::= { mbus8A 82 }

mbus8AValue26		OBJECT-TYPE
			SYNTAX	INTEGER
			ACCESS	read-only
			STATUS	current
	DESCRIPTION ""
			::= { mbus8A 83 }

mbus8AVIF27		OBJECT-TYPE
			SYNTAX	INTEGER
			ACCESS	read-only
			STATUS	current
	DESCRIPTION ""
			::= { mbus8A 84 }

mbus8AValue27		OBJECT-TYPE
			SYNTAX	INTEGER
			ACCESS	read-only
			STATUS	current
	DESCRIPTION ""
			::= { mbus8A 85 }

mbus8AVIF28		OBJECT-TYPE
			SYNTAX	INTEGER
			ACCESS	read-only
			STATUS	current
	DESCRIPTION ""
			::= { mbus8A 86 }

mbus8AValue28		OBJECT-TYPE
			SYNTAX	INTEGER
			ACCESS	read-only
			STATUS	current
	DESCRIPTION ""
			::= { mbus8A 87 }

mbus8AVIF29		OBJECT-TYPE
			SYNTAX	INTEGER
			ACCESS	read-only
			STATUS	current
	DESCRIPTION ""
			::= { mbus8A 88 }

mbus8AValue29		OBJECT-TYPE
			SYNTAX	INTEGER
			ACCESS	read-only
			STATUS	current
	DESCRIPTION ""
			::= { mbus8A 89 }

mbus8AVIF2A		OBJECT-TYPE
			SYNTAX	INTEGER
			ACCESS	read-only
			STATUS	current
	DESCRIPTION ""
			::= { mbus8A 90 }

mbus8AValue2A		OBJECT-TYPE
			SYNTAX	INTEGER
			ACCESS	read-only
			STATUS	current
	DESCRIPTION ""
			::= { mbus8A 91 }

mbus8AVIF2B		OBJECT-TYPE
			SYNTAX	INTEGER
			ACCESS	read-only
			STATUS	current
	DESCRIPTION ""
			::= { mbus8A 92 }

mbus8AValue2B		OBJECT-TYPE
			SYNTAX	INTEGER
			ACCESS	read-only
			STATUS	current
	DESCRIPTION ""
			::= { mbus8A 93 }

mbus8AVIF2C		OBJECT-TYPE
			SYNTAX	INTEGER
			ACCESS	read-only
			STATUS	current
	DESCRIPTION ""
			::= { mbus8A 94 }

mbus8AValue2C		OBJECT-TYPE
			SYNTAX	INTEGER
			ACCESS	read-only
			STATUS	current
	DESCRIPTION ""
			::= { mbus8A 95 }

mbus8AVIF2D		OBJECT-TYPE
			SYNTAX	INTEGER
			ACCESS	read-only
			STATUS	current
	DESCRIPTION ""
			::= { mbus8A 96 }

mbus8AValue2D		OBJECT-TYPE
			SYNTAX	INTEGER
			ACCESS	read-only
			STATUS	current
	DESCRIPTION ""
			::= { mbus8A 97 }

mbus8AVIF2E		OBJECT-TYPE
			SYNTAX	INTEGER
			ACCESS	read-only
			STATUS	current
	DESCRIPTION ""
			::= { mbus8A 98 }

mbus8AValue2E		OBJECT-TYPE
			SYNTAX	INTEGER
			ACCESS	read-only
			STATUS	current
	DESCRIPTION ""
			::= { mbus8A 99 }

mbus8AVIF2F		OBJECT-TYPE
			SYNTAX	INTEGER
			ACCESS	read-only
			STATUS	current
	DESCRIPTION ""
			::= { mbus8A 100 }

mbus8AValue2F		OBJECT-TYPE
			SYNTAX	INTEGER
			ACCESS	read-only
			STATUS	current
	DESCRIPTION ""
			::= { mbus8A 101 }

mbus8B			OBJECT IDENTIFIER ::= { mbus 139 }

mbus8BIdNumber		OBJECT-TYPE
			SYNTAX	Gauge
			ACCESS	read-only
			STATUS	current
	DESCRIPTION ""
			::= { mbus8B 1 }

mbus8BManufacturer	OBJECT-TYPE
			SYNTAX	Gauge
			ACCESS	read-only
			STATUS	current
	DESCRIPTION ""
			::= { mbus8B 2 }

mbus8BVersion		OBJECT-TYPE
			SYNTAX	Gauge
			ACCESS	read-only
			STATUS	current
	DESCRIPTION ""
			::= { mbus8B 3 }

mbus8BMedium		OBJECT-TYPE
			SYNTAX	Gauge
			ACCESS	read-only
			STATUS	current
	DESCRIPTION ""
			::= { mbus8B 4 }

mbus8BStatus		OBJECT-TYPE
			SYNTAX	Gauge
			ACCESS	read-only
			STATUS	current
	DESCRIPTION ""
			::= { mbus8B 5 }

mbus8BVIF00		OBJECT-TYPE
			SYNTAX	INTEGER
			ACCESS	read-only
			STATUS	current
	DESCRIPTION ""
			::= { mbus8B 6 }

mbus8BValue00		OBJECT-TYPE
			SYNTAX	INTEGER
			ACCESS	read-only
			STATUS	current
	DESCRIPTION ""
			::= { mbus8B 7 }

mbus8BVIF01		OBJECT-TYPE
			SYNTAX	INTEGER
			ACCESS	read-only
			STATUS	current
	DESCRIPTION ""
			::= { mbus8B 8 }

mbus8BValue01		OBJECT-TYPE
			SYNTAX	INTEGER
			ACCESS	read-only
			STATUS	current
	DESCRIPTION ""
			::= { mbus8B 9 }

mbus8BVIF02		OBJECT-TYPE
			SYNTAX	INTEGER
			ACCESS	read-only
			STATUS	current
	DESCRIPTION ""
			::= { mbus8B 10 }

mbus8BValue02		OBJECT-TYPE
			SYNTAX	INTEGER
			ACCESS	read-only
			STATUS	current
	DESCRIPTION ""
			::= { mbus8B 11 }

mbus8BVIF03		OBJECT-TYPE
			SYNTAX	INTEGER
			ACCESS	read-only
			STATUS	current
	DESCRIPTION ""
			::= { mbus8B 12 }

mbus8BValue03		OBJECT-TYPE
			SYNTAX	INTEGER
			ACCESS	read-only
			STATUS	current
	DESCRIPTION ""
			::= { mbus8B 13 }

mbus8BVIF04		OBJECT-TYPE
			SYNTAX	INTEGER
			ACCESS	read-only
			STATUS	current
	DESCRIPTION ""
			::= { mbus8B 14 }

mbus8BValue04		OBJECT-TYPE
			SYNTAX	INTEGER
			ACCESS	read-only
			STATUS	current
	DESCRIPTION ""
			::= { mbus8B 15 }

mbus8BVIF05		OBJECT-TYPE
			SYNTAX	INTEGER
			ACCESS	read-only
			STATUS	current
	DESCRIPTION ""
			::= { mbus8B 16 }

mbus8BValue05		OBJECT-TYPE
			SYNTAX	INTEGER
			ACCESS	read-only
			STATUS	current
	DESCRIPTION ""
			::= { mbus8B 17 }

mbus8BVIF06		OBJECT-TYPE
			SYNTAX	INTEGER
			ACCESS	read-only
			STATUS	current
	DESCRIPTION ""
			::= { mbus8B 18 }

mbus8BValue06		OBJECT-TYPE
			SYNTAX	INTEGER
			ACCESS	read-only
			STATUS	current
	DESCRIPTION ""
			::= { mbus8B 19 }

mbus8BVIF07		OBJECT-TYPE
			SYNTAX	INTEGER
			ACCESS	read-only
			STATUS	current
	DESCRIPTION ""
			::= { mbus8B 20 }

mbus8BValue07		OBJECT-TYPE
			SYNTAX	INTEGER
			ACCESS	read-only
			STATUS	current
	DESCRIPTION ""
			::= { mbus8B 21 }

mbus8BVIF08		OBJECT-TYPE
			SYNTAX	INTEGER
			ACCESS	read-only
			STATUS	current
	DESCRIPTION ""
			::= { mbus8B 22 }

mbus8BValue08		OBJECT-TYPE
			SYNTAX	INTEGER
			ACCESS	read-only
			STATUS	current
	DESCRIPTION ""
			::= { mbus8B 23 }

mbus8BVIF09		OBJECT-TYPE
			SYNTAX	INTEGER
			ACCESS	read-only
			STATUS	current
	DESCRIPTION ""
			::= { mbus8B 24 }

mbus8BValue09		OBJECT-TYPE
			SYNTAX	INTEGER
			ACCESS	read-only
			STATUS	current
	DESCRIPTION ""
			::= { mbus8B 25 }

mbus8BVIF0A		OBJECT-TYPE
			SYNTAX	INTEGER
			ACCESS	read-only
			STATUS	current
	DESCRIPTION ""
			::= { mbus8B 26 }

mbus8BValue0A		OBJECT-TYPE
			SYNTAX	INTEGER
			ACCESS	read-only
			STATUS	current
	DESCRIPTION ""
			::= { mbus8B 27 }

mbus8BVIF0B		OBJECT-TYPE
			SYNTAX	INTEGER
			ACCESS	read-only
			STATUS	current
	DESCRIPTION ""
			::= { mbus8B 28 }

mbus8BValue0B		OBJECT-TYPE
			SYNTAX	INTEGER
			ACCESS	read-only
			STATUS	current
	DESCRIPTION ""
			::= { mbus8B 29 }

mbus8BVIF0C		OBJECT-TYPE
			SYNTAX	INTEGER
			ACCESS	read-only
			STATUS	current
	DESCRIPTION ""
			::= { mbus8B 30 }

mbus8BValue0C		OBJECT-TYPE
			SYNTAX	INTEGER
			ACCESS	read-only
			STATUS	current
	DESCRIPTION ""
			::= { mbus8B 31 }

mbus8BVIF0D		OBJECT-TYPE
			SYNTAX	INTEGER
			ACCESS	read-only
			STATUS	current
	DESCRIPTION ""
			::= { mbus8B 32 }

mbus8BValue0D		OBJECT-TYPE
			SYNTAX	INTEGER
			ACCESS	read-only
			STATUS	current
	DESCRIPTION ""
			::= { mbus8B 33 }

mbus8BVIF0E		OBJECT-TYPE
			SYNTAX	INTEGER
			ACCESS	read-only
			STATUS	current
	DESCRIPTION ""
			::= { mbus8B 34 }

mbus8BValue0E		OBJECT-TYPE
			SYNTAX	INTEGER
			ACCESS	read-only
			STATUS	current
	DESCRIPTION ""
			::= { mbus8B 35 }

mbus8BVIF0F		OBJECT-TYPE
			SYNTAX	INTEGER
			ACCESS	read-only
			STATUS	current
	DESCRIPTION ""
			::= { mbus8B 36 }

mbus8BValue0F		OBJECT-TYPE
			SYNTAX	INTEGER
			ACCESS	read-only
			STATUS	current
	DESCRIPTION ""
			::= { mbus8B 37 }

mbus8BVIF10		OBJECT-TYPE
			SYNTAX	INTEGER
			ACCESS	read-only
			STATUS	current
	DESCRIPTION ""
			::= { mbus8B 38 }

mbus8BValue10		OBJECT-TYPE
			SYNTAX	INTEGER
			ACCESS	read-only
			STATUS	current
	DESCRIPTION ""
			::= { mbus8B 39 }

mbus8BVIF11		OBJECT-TYPE
			SYNTAX	INTEGER
			ACCESS	read-only
			STATUS	current
	DESCRIPTION ""
			::= { mbus8B 40 }

mbus8BValue11		OBJECT-TYPE
			SYNTAX	INTEGER
			ACCESS	read-only
			STATUS	current
	DESCRIPTION ""
			::= { mbus8B 41 }

mbus8BVIF12		OBJECT-TYPE
			SYNTAX	INTEGER
			ACCESS	read-only
			STATUS	current
	DESCRIPTION ""
			::= { mbus8B 42 }

mbus8BValue12		OBJECT-TYPE
			SYNTAX	INTEGER
			ACCESS	read-only
			STATUS	current
	DESCRIPTION ""
			::= { mbus8B 43 }

mbus8BVIF13		OBJECT-TYPE
			SYNTAX	INTEGER
			ACCESS	read-only
			STATUS	current
	DESCRIPTION ""
			::= { mbus8B 44 }

mbus8BValue13		OBJECT-TYPE
			SYNTAX	INTEGER
			ACCESS	read-only
			STATUS	current
	DESCRIPTION ""
			::= { mbus8B 45 }

mbus8BVIF14		OBJECT-TYPE
			SYNTAX	INTEGER
			ACCESS	read-only
			STATUS	current
	DESCRIPTION ""
			::= { mbus8B 46 }

mbus8BValue14		OBJECT-TYPE
			SYNTAX	INTEGER
			ACCESS	read-only
			STATUS	current
	DESCRIPTION ""
			::= { mbus8B 47 }

mbus8BVIF15		OBJECT-TYPE
			SYNTAX	INTEGER
			ACCESS	read-only
			STATUS	current
	DESCRIPTION ""
			::= { mbus8B 48 }

mbus8BValue15		OBJECT-TYPE
			SYNTAX	INTEGER
			ACCESS	read-only
			STATUS	current
	DESCRIPTION ""
			::= { mbus8B 49 }

mbus8BVIF16		OBJECT-TYPE
			SYNTAX	INTEGER
			ACCESS	read-only
			STATUS	current
	DESCRIPTION ""
			::= { mbus8B 50 }

mbus8BValue16		OBJECT-TYPE
			SYNTAX	INTEGER
			ACCESS	read-only
			STATUS	current
	DESCRIPTION ""
			::= { mbus8B 51 }

mbus8BVIF17		OBJECT-TYPE
			SYNTAX	INTEGER
			ACCESS	read-only
			STATUS	current
	DESCRIPTION ""
			::= { mbus8B 52 }

mbus8BValue17		OBJECT-TYPE
			SYNTAX	INTEGER
			ACCESS	read-only
			STATUS	current
	DESCRIPTION ""
			::= { mbus8B 53 }

mbus8BVIF18		OBJECT-TYPE
			SYNTAX	INTEGER
			ACCESS	read-only
			STATUS	current
	DESCRIPTION ""
			::= { mbus8B 54 }

mbus8BValue18		OBJECT-TYPE
			SYNTAX	INTEGER
			ACCESS	read-only
			STATUS	current
	DESCRIPTION ""
			::= { mbus8B 55 }

mbus8BVIF19		OBJECT-TYPE
			SYNTAX	INTEGER
			ACCESS	read-only
			STATUS	current
	DESCRIPTION ""
			::= { mbus8B 56 }

mbus8BValue19		OBJECT-TYPE
			SYNTAX	INTEGER
			ACCESS	read-only
			STATUS	current
	DESCRIPTION ""
			::= { mbus8B 57 }

mbus8BVIF1A		OBJECT-TYPE
			SYNTAX	INTEGER
			ACCESS	read-only
			STATUS	current
	DESCRIPTION ""
			::= { mbus8B 58 }

mbus8BValue1A		OBJECT-TYPE
			SYNTAX	INTEGER
			ACCESS	read-only
			STATUS	current
	DESCRIPTION ""
			::= { mbus8B 59 }

mbus8BVIF1B		OBJECT-TYPE
			SYNTAX	INTEGER
			ACCESS	read-only
			STATUS	current
	DESCRIPTION ""
			::= { mbus8B 60 }

mbus8BValue1B		OBJECT-TYPE
			SYNTAX	INTEGER
			ACCESS	read-only
			STATUS	current
	DESCRIPTION ""
			::= { mbus8B 61 }

mbus8BVIF1C		OBJECT-TYPE
			SYNTAX	INTEGER
			ACCESS	read-only
			STATUS	current
	DESCRIPTION ""
			::= { mbus8B 62 }

mbus8BValue1C		OBJECT-TYPE
			SYNTAX	INTEGER
			ACCESS	read-only
			STATUS	current
	DESCRIPTION ""
			::= { mbus8B 63 }

mbus8BVIF1D		OBJECT-TYPE
			SYNTAX	INTEGER
			ACCESS	read-only
			STATUS	current
	DESCRIPTION ""
			::= { mbus8B 64 }

mbus8BValue1D		OBJECT-TYPE
			SYNTAX	INTEGER
			ACCESS	read-only
			STATUS	current
	DESCRIPTION ""
			::= { mbus8B 65 }

mbus8BVIF1E		OBJECT-TYPE
			SYNTAX	INTEGER
			ACCESS	read-only
			STATUS	current
	DESCRIPTION ""
			::= { mbus8B 66 }

mbus8BValue1E		OBJECT-TYPE
			SYNTAX	INTEGER
			ACCESS	read-only
			STATUS	current
	DESCRIPTION ""
			::= { mbus8B 67 }

mbus8BVIF1F		OBJECT-TYPE
			SYNTAX	INTEGER
			ACCESS	read-only
			STATUS	current
	DESCRIPTION ""
			::= { mbus8B 68 }

mbus8BValue1F		OBJECT-TYPE
			SYNTAX	INTEGER
			ACCESS	read-only
			STATUS	current
	DESCRIPTION ""
			::= { mbus8B 69 }

mbus8BVIF20		OBJECT-TYPE
			SYNTAX	INTEGER
			ACCESS	read-only
			STATUS	current
	DESCRIPTION ""
			::= { mbus8B 70 }

mbus8BValue20		OBJECT-TYPE
			SYNTAX	INTEGER
			ACCESS	read-only
			STATUS	current
	DESCRIPTION ""
			::= { mbus8B 71 }

mbus8BVIF21		OBJECT-TYPE
			SYNTAX	INTEGER
			ACCESS	read-only
			STATUS	current
	DESCRIPTION ""
			::= { mbus8B 72 }

mbus8BValue21		OBJECT-TYPE
			SYNTAX	INTEGER
			ACCESS	read-only
			STATUS	current
	DESCRIPTION ""
			::= { mbus8B 73 }

mbus8BVIF22		OBJECT-TYPE
			SYNTAX	INTEGER
			ACCESS	read-only
			STATUS	current
	DESCRIPTION ""
			::= { mbus8B 74 }

mbus8BValue22		OBJECT-TYPE
			SYNTAX	INTEGER
			ACCESS	read-only
			STATUS	current
	DESCRIPTION ""
			::= { mbus8B 75 }

mbus8BVIF23		OBJECT-TYPE
			SYNTAX	INTEGER
			ACCESS	read-only
			STATUS	current
	DESCRIPTION ""
			::= { mbus8B 76 }

mbus8BValue23		OBJECT-TYPE
			SYNTAX	INTEGER
			ACCESS	read-only
			STATUS	current
	DESCRIPTION ""
			::= { mbus8B 77 }

mbus8BVIF24		OBJECT-TYPE
			SYNTAX	INTEGER
			ACCESS	read-only
			STATUS	current
	DESCRIPTION ""
			::= { mbus8B 78 }

mbus8BValue24		OBJECT-TYPE
			SYNTAX	INTEGER
			ACCESS	read-only
			STATUS	current
	DESCRIPTION ""
			::= { mbus8B 79 }

mbus8BVIF25		OBJECT-TYPE
			SYNTAX	INTEGER
			ACCESS	read-only
			STATUS	current
	DESCRIPTION ""
			::= { mbus8B 80 }

mbus8BValue25		OBJECT-TYPE
			SYNTAX	INTEGER
			ACCESS	read-only
			STATUS	current
	DESCRIPTION ""
			::= { mbus8B 81 }

mbus8BVIF26		OBJECT-TYPE
			SYNTAX	INTEGER
			ACCESS	read-only
			STATUS	current
	DESCRIPTION ""
			::= { mbus8B 82 }

mbus8BValue26		OBJECT-TYPE
			SYNTAX	INTEGER
			ACCESS	read-only
			STATUS	current
	DESCRIPTION ""
			::= { mbus8B 83 }

mbus8BVIF27		OBJECT-TYPE
			SYNTAX	INTEGER
			ACCESS	read-only
			STATUS	current
	DESCRIPTION ""
			::= { mbus8B 84 }

mbus8BValue27		OBJECT-TYPE
			SYNTAX	INTEGER
			ACCESS	read-only
			STATUS	current
	DESCRIPTION ""
			::= { mbus8B 85 }

mbus8BVIF28		OBJECT-TYPE
			SYNTAX	INTEGER
			ACCESS	read-only
			STATUS	current
	DESCRIPTION ""
			::= { mbus8B 86 }

mbus8BValue28		OBJECT-TYPE
			SYNTAX	INTEGER
			ACCESS	read-only
			STATUS	current
	DESCRIPTION ""
			::= { mbus8B 87 }

mbus8BVIF29		OBJECT-TYPE
			SYNTAX	INTEGER
			ACCESS	read-only
			STATUS	current
	DESCRIPTION ""
			::= { mbus8B 88 }

mbus8BValue29		OBJECT-TYPE
			SYNTAX	INTEGER
			ACCESS	read-only
			STATUS	current
	DESCRIPTION ""
			::= { mbus8B 89 }

mbus8BVIF2A		OBJECT-TYPE
			SYNTAX	INTEGER
			ACCESS	read-only
			STATUS	current
	DESCRIPTION ""
			::= { mbus8B 90 }

mbus8BValue2A		OBJECT-TYPE
			SYNTAX	INTEGER
			ACCESS	read-only
			STATUS	current
	DESCRIPTION ""
			::= { mbus8B 91 }

mbus8BVIF2B		OBJECT-TYPE
			SYNTAX	INTEGER
			ACCESS	read-only
			STATUS	current
	DESCRIPTION ""
			::= { mbus8B 92 }

mbus8BValue2B		OBJECT-TYPE
			SYNTAX	INTEGER
			ACCESS	read-only
			STATUS	current
	DESCRIPTION ""
			::= { mbus8B 93 }

mbus8BVIF2C		OBJECT-TYPE
			SYNTAX	INTEGER
			ACCESS	read-only
			STATUS	current
	DESCRIPTION ""
			::= { mbus8B 94 }

mbus8BValue2C		OBJECT-TYPE
			SYNTAX	INTEGER
			ACCESS	read-only
			STATUS	current
	DESCRIPTION ""
			::= { mbus8B 95 }

mbus8BVIF2D		OBJECT-TYPE
			SYNTAX	INTEGER
			ACCESS	read-only
			STATUS	current
	DESCRIPTION ""
			::= { mbus8B 96 }

mbus8BValue2D		OBJECT-TYPE
			SYNTAX	INTEGER
			ACCESS	read-only
			STATUS	current
	DESCRIPTION ""
			::= { mbus8B 97 }

mbus8BVIF2E		OBJECT-TYPE
			SYNTAX	INTEGER
			ACCESS	read-only
			STATUS	current
	DESCRIPTION ""
			::= { mbus8B 98 }

mbus8BValue2E		OBJECT-TYPE
			SYNTAX	INTEGER
			ACCESS	read-only
			STATUS	current
	DESCRIPTION ""
			::= { mbus8B 99 }

mbus8BVIF2F		OBJECT-TYPE
			SYNTAX	INTEGER
			ACCESS	read-only
			STATUS	current
	DESCRIPTION ""
			::= { mbus8B 100 }

mbus8BValue2F		OBJECT-TYPE
			SYNTAX	INTEGER
			ACCESS	read-only
			STATUS	current
	DESCRIPTION ""
			::= { mbus8B 101 }

mbus8C			OBJECT IDENTIFIER ::= { mbus 140 }

mbus8CIdNumber		OBJECT-TYPE
			SYNTAX	Gauge
			ACCESS	read-only
			STATUS	current
	DESCRIPTION ""
			::= { mbus8C 1 }

mbus8CManufacturer	OBJECT-TYPE
			SYNTAX	Gauge
			ACCESS	read-only
			STATUS	current
	DESCRIPTION ""
			::= { mbus8C 2 }

mbus8CVersion		OBJECT-TYPE
			SYNTAX	Gauge
			ACCESS	read-only
			STATUS	current
	DESCRIPTION ""
			::= { mbus8C 3 }

mbus8CMedium		OBJECT-TYPE
			SYNTAX	Gauge
			ACCESS	read-only
			STATUS	current
	DESCRIPTION ""
			::= { mbus8C 4 }

mbus8CStatus		OBJECT-TYPE
			SYNTAX	Gauge
			ACCESS	read-only
			STATUS	current
	DESCRIPTION ""
			::= { mbus8C 5 }

mbus8CVIF00		OBJECT-TYPE
			SYNTAX	INTEGER
			ACCESS	read-only
			STATUS	current
	DESCRIPTION ""
			::= { mbus8C 6 }

mbus8CValue00		OBJECT-TYPE
			SYNTAX	INTEGER
			ACCESS	read-only
			STATUS	current
	DESCRIPTION ""
			::= { mbus8C 7 }

mbus8CVIF01		OBJECT-TYPE
			SYNTAX	INTEGER
			ACCESS	read-only
			STATUS	current
	DESCRIPTION ""
			::= { mbus8C 8 }

mbus8CValue01		OBJECT-TYPE
			SYNTAX	INTEGER
			ACCESS	read-only
			STATUS	current
	DESCRIPTION ""
			::= { mbus8C 9 }

mbus8CVIF02		OBJECT-TYPE
			SYNTAX	INTEGER
			ACCESS	read-only
			STATUS	current
	DESCRIPTION ""
			::= { mbus8C 10 }

mbus8CValue02		OBJECT-TYPE
			SYNTAX	INTEGER
			ACCESS	read-only
			STATUS	current
	DESCRIPTION ""
			::= { mbus8C 11 }

mbus8CVIF03		OBJECT-TYPE
			SYNTAX	INTEGER
			ACCESS	read-only
			STATUS	current
	DESCRIPTION ""
			::= { mbus8C 12 }

mbus8CValue03		OBJECT-TYPE
			SYNTAX	INTEGER
			ACCESS	read-only
			STATUS	current
	DESCRIPTION ""
			::= { mbus8C 13 }

mbus8CVIF04		OBJECT-TYPE
			SYNTAX	INTEGER
			ACCESS	read-only
			STATUS	current
	DESCRIPTION ""
			::= { mbus8C 14 }

mbus8CValue04		OBJECT-TYPE
			SYNTAX	INTEGER
			ACCESS	read-only
			STATUS	current
	DESCRIPTION ""
			::= { mbus8C 15 }

mbus8CVIF05		OBJECT-TYPE
			SYNTAX	INTEGER
			ACCESS	read-only
			STATUS	current
	DESCRIPTION ""
			::= { mbus8C 16 }

mbus8CValue05		OBJECT-TYPE
			SYNTAX	INTEGER
			ACCESS	read-only
			STATUS	current
	DESCRIPTION ""
			::= { mbus8C 17 }

mbus8CVIF06		OBJECT-TYPE
			SYNTAX	INTEGER
			ACCESS	read-only
			STATUS	current
	DESCRIPTION ""
			::= { mbus8C 18 }

mbus8CValue06		OBJECT-TYPE
			SYNTAX	INTEGER
			ACCESS	read-only
			STATUS	current
	DESCRIPTION ""
			::= { mbus8C 19 }

mbus8CVIF07		OBJECT-TYPE
			SYNTAX	INTEGER
			ACCESS	read-only
			STATUS	current
	DESCRIPTION ""
			::= { mbus8C 20 }

mbus8CValue07		OBJECT-TYPE
			SYNTAX	INTEGER
			ACCESS	read-only
			STATUS	current
	DESCRIPTION ""
			::= { mbus8C 21 }

mbus8CVIF08		OBJECT-TYPE
			SYNTAX	INTEGER
			ACCESS	read-only
			STATUS	current
	DESCRIPTION ""
			::= { mbus8C 22 }

mbus8CValue08		OBJECT-TYPE
			SYNTAX	INTEGER
			ACCESS	read-only
			STATUS	current
	DESCRIPTION ""
			::= { mbus8C 23 }

mbus8CVIF09		OBJECT-TYPE
			SYNTAX	INTEGER
			ACCESS	read-only
			STATUS	current
	DESCRIPTION ""
			::= { mbus8C 24 }

mbus8CValue09		OBJECT-TYPE
			SYNTAX	INTEGER
			ACCESS	read-only
			STATUS	current
	DESCRIPTION ""
			::= { mbus8C 25 }

mbus8CVIF0A		OBJECT-TYPE
			SYNTAX	INTEGER
			ACCESS	read-only
			STATUS	current
	DESCRIPTION ""
			::= { mbus8C 26 }

mbus8CValue0A		OBJECT-TYPE
			SYNTAX	INTEGER
			ACCESS	read-only
			STATUS	current
	DESCRIPTION ""
			::= { mbus8C 27 }

mbus8CVIF0B		OBJECT-TYPE
			SYNTAX	INTEGER
			ACCESS	read-only
			STATUS	current
	DESCRIPTION ""
			::= { mbus8C 28 }

mbus8CValue0B		OBJECT-TYPE
			SYNTAX	INTEGER
			ACCESS	read-only
			STATUS	current
	DESCRIPTION ""
			::= { mbus8C 29 }

mbus8CVIF0C		OBJECT-TYPE
			SYNTAX	INTEGER
			ACCESS	read-only
			STATUS	current
	DESCRIPTION ""
			::= { mbus8C 30 }

mbus8CValue0C		OBJECT-TYPE
			SYNTAX	INTEGER
			ACCESS	read-only
			STATUS	current
	DESCRIPTION ""
			::= { mbus8C 31 }

mbus8CVIF0D		OBJECT-TYPE
			SYNTAX	INTEGER
			ACCESS	read-only
			STATUS	current
	DESCRIPTION ""
			::= { mbus8C 32 }

mbus8CValue0D		OBJECT-TYPE
			SYNTAX	INTEGER
			ACCESS	read-only
			STATUS	current
	DESCRIPTION ""
			::= { mbus8C 33 }

mbus8CVIF0E		OBJECT-TYPE
			SYNTAX	INTEGER
			ACCESS	read-only
			STATUS	current
	DESCRIPTION ""
			::= { mbus8C 34 }

mbus8CValue0E		OBJECT-TYPE
			SYNTAX	INTEGER
			ACCESS	read-only
			STATUS	current
	DESCRIPTION ""
			::= { mbus8C 35 }

mbus8CVIF0F		OBJECT-TYPE
			SYNTAX	INTEGER
			ACCESS	read-only
			STATUS	current
	DESCRIPTION ""
			::= { mbus8C 36 }

mbus8CValue0F		OBJECT-TYPE
			SYNTAX	INTEGER
			ACCESS	read-only
			STATUS	current
	DESCRIPTION ""
			::= { mbus8C 37 }

mbus8CVIF10		OBJECT-TYPE
			SYNTAX	INTEGER
			ACCESS	read-only
			STATUS	current
	DESCRIPTION ""
			::= { mbus8C 38 }

mbus8CValue10		OBJECT-TYPE
			SYNTAX	INTEGER
			ACCESS	read-only
			STATUS	current
	DESCRIPTION ""
			::= { mbus8C 39 }

mbus8CVIF11		OBJECT-TYPE
			SYNTAX	INTEGER
			ACCESS	read-only
			STATUS	current
	DESCRIPTION ""
			::= { mbus8C 40 }

mbus8CValue11		OBJECT-TYPE
			SYNTAX	INTEGER
			ACCESS	read-only
			STATUS	current
	DESCRIPTION ""
			::= { mbus8C 41 }

mbus8CVIF12		OBJECT-TYPE
			SYNTAX	INTEGER
			ACCESS	read-only
			STATUS	current
	DESCRIPTION ""
			::= { mbus8C 42 }

mbus8CValue12		OBJECT-TYPE
			SYNTAX	INTEGER
			ACCESS	read-only
			STATUS	current
	DESCRIPTION ""
			::= { mbus8C 43 }

mbus8CVIF13		OBJECT-TYPE
			SYNTAX	INTEGER
			ACCESS	read-only
			STATUS	current
	DESCRIPTION ""
			::= { mbus8C 44 }

mbus8CValue13		OBJECT-TYPE
			SYNTAX	INTEGER
			ACCESS	read-only
			STATUS	current
	DESCRIPTION ""
			::= { mbus8C 45 }

mbus8CVIF14		OBJECT-TYPE
			SYNTAX	INTEGER
			ACCESS	read-only
			STATUS	current
	DESCRIPTION ""
			::= { mbus8C 46 }

mbus8CValue14		OBJECT-TYPE
			SYNTAX	INTEGER
			ACCESS	read-only
			STATUS	current
	DESCRIPTION ""
			::= { mbus8C 47 }

mbus8CVIF15		OBJECT-TYPE
			SYNTAX	INTEGER
			ACCESS	read-only
			STATUS	current
	DESCRIPTION ""
			::= { mbus8C 48 }

mbus8CValue15		OBJECT-TYPE
			SYNTAX	INTEGER
			ACCESS	read-only
			STATUS	current
	DESCRIPTION ""
			::= { mbus8C 49 }

mbus8CVIF16		OBJECT-TYPE
			SYNTAX	INTEGER
			ACCESS	read-only
			STATUS	current
	DESCRIPTION ""
			::= { mbus8C 50 }

mbus8CValue16		OBJECT-TYPE
			SYNTAX	INTEGER
			ACCESS	read-only
			STATUS	current
	DESCRIPTION ""
			::= { mbus8C 51 }

mbus8CVIF17		OBJECT-TYPE
			SYNTAX	INTEGER
			ACCESS	read-only
			STATUS	current
	DESCRIPTION ""
			::= { mbus8C 52 }

mbus8CValue17		OBJECT-TYPE
			SYNTAX	INTEGER
			ACCESS	read-only
			STATUS	current
	DESCRIPTION ""
			::= { mbus8C 53 }

mbus8CVIF18		OBJECT-TYPE
			SYNTAX	INTEGER
			ACCESS	read-only
			STATUS	current
	DESCRIPTION ""
			::= { mbus8C 54 }

mbus8CValue18		OBJECT-TYPE
			SYNTAX	INTEGER
			ACCESS	read-only
			STATUS	current
	DESCRIPTION ""
			::= { mbus8C 55 }

mbus8CVIF19		OBJECT-TYPE
			SYNTAX	INTEGER
			ACCESS	read-only
			STATUS	current
	DESCRIPTION ""
			::= { mbus8C 56 }

mbus8CValue19		OBJECT-TYPE
			SYNTAX	INTEGER
			ACCESS	read-only
			STATUS	current
	DESCRIPTION ""
			::= { mbus8C 57 }

mbus8CVIF1A		OBJECT-TYPE
			SYNTAX	INTEGER
			ACCESS	read-only
			STATUS	current
	DESCRIPTION ""
			::= { mbus8C 58 }

mbus8CValue1A		OBJECT-TYPE
			SYNTAX	INTEGER
			ACCESS	read-only
			STATUS	current
	DESCRIPTION ""
			::= { mbus8C 59 }

mbus8CVIF1B		OBJECT-TYPE
			SYNTAX	INTEGER
			ACCESS	read-only
			STATUS	current
	DESCRIPTION ""
			::= { mbus8C 60 }

mbus8CValue1B		OBJECT-TYPE
			SYNTAX	INTEGER
			ACCESS	read-only
			STATUS	current
	DESCRIPTION ""
			::= { mbus8C 61 }

mbus8CVIF1C		OBJECT-TYPE
			SYNTAX	INTEGER
			ACCESS	read-only
			STATUS	current
	DESCRIPTION ""
			::= { mbus8C 62 }

mbus8CValue1C		OBJECT-TYPE
			SYNTAX	INTEGER
			ACCESS	read-only
			STATUS	current
	DESCRIPTION ""
			::= { mbus8C 63 }

mbus8CVIF1D		OBJECT-TYPE
			SYNTAX	INTEGER
			ACCESS	read-only
			STATUS	current
	DESCRIPTION ""
			::= { mbus8C 64 }

mbus8CValue1D		OBJECT-TYPE
			SYNTAX	INTEGER
			ACCESS	read-only
			STATUS	current
	DESCRIPTION ""
			::= { mbus8C 65 }

mbus8CVIF1E		OBJECT-TYPE
			SYNTAX	INTEGER
			ACCESS	read-only
			STATUS	current
	DESCRIPTION ""
			::= { mbus8C 66 }

mbus8CValue1E		OBJECT-TYPE
			SYNTAX	INTEGER
			ACCESS	read-only
			STATUS	current
	DESCRIPTION ""
			::= { mbus8C 67 }

mbus8CVIF1F		OBJECT-TYPE
			SYNTAX	INTEGER
			ACCESS	read-only
			STATUS	current
	DESCRIPTION ""
			::= { mbus8C 68 }

mbus8CValue1F		OBJECT-TYPE
			SYNTAX	INTEGER
			ACCESS	read-only
			STATUS	current
	DESCRIPTION ""
			::= { mbus8C 69 }

mbus8CVIF20		OBJECT-TYPE
			SYNTAX	INTEGER
			ACCESS	read-only
			STATUS	current
	DESCRIPTION ""
			::= { mbus8C 70 }

mbus8CValue20		OBJECT-TYPE
			SYNTAX	INTEGER
			ACCESS	read-only
			STATUS	current
	DESCRIPTION ""
			::= { mbus8C 71 }

mbus8CVIF21		OBJECT-TYPE
			SYNTAX	INTEGER
			ACCESS	read-only
			STATUS	current
	DESCRIPTION ""
			::= { mbus8C 72 }

mbus8CValue21		OBJECT-TYPE
			SYNTAX	INTEGER
			ACCESS	read-only
			STATUS	current
	DESCRIPTION ""
			::= { mbus8C 73 }

mbus8CVIF22		OBJECT-TYPE
			SYNTAX	INTEGER
			ACCESS	read-only
			STATUS	current
	DESCRIPTION ""
			::= { mbus8C 74 }

mbus8CValue22		OBJECT-TYPE
			SYNTAX	INTEGER
			ACCESS	read-only
			STATUS	current
	DESCRIPTION ""
			::= { mbus8C 75 }

mbus8CVIF23		OBJECT-TYPE
			SYNTAX	INTEGER
			ACCESS	read-only
			STATUS	current
	DESCRIPTION ""
			::= { mbus8C 76 }

mbus8CValue23		OBJECT-TYPE
			SYNTAX	INTEGER
			ACCESS	read-only
			STATUS	current
	DESCRIPTION ""
			::= { mbus8C 77 }

mbus8CVIF24		OBJECT-TYPE
			SYNTAX	INTEGER
			ACCESS	read-only
			STATUS	current
	DESCRIPTION ""
			::= { mbus8C 78 }

mbus8CValue24		OBJECT-TYPE
			SYNTAX	INTEGER
			ACCESS	read-only
			STATUS	current
	DESCRIPTION ""
			::= { mbus8C 79 }

mbus8CVIF25		OBJECT-TYPE
			SYNTAX	INTEGER
			ACCESS	read-only
			STATUS	current
	DESCRIPTION ""
			::= { mbus8C 80 }

mbus8CValue25		OBJECT-TYPE
			SYNTAX	INTEGER
			ACCESS	read-only
			STATUS	current
	DESCRIPTION ""
			::= { mbus8C 81 }

mbus8CVIF26		OBJECT-TYPE
			SYNTAX	INTEGER
			ACCESS	read-only
			STATUS	current
	DESCRIPTION ""
			::= { mbus8C 82 }

mbus8CValue26		OBJECT-TYPE
			SYNTAX	INTEGER
			ACCESS	read-only
			STATUS	current
	DESCRIPTION ""
			::= { mbus8C 83 }

mbus8CVIF27		OBJECT-TYPE
			SYNTAX	INTEGER
			ACCESS	read-only
			STATUS	current
	DESCRIPTION ""
			::= { mbus8C 84 }

mbus8CValue27		OBJECT-TYPE
			SYNTAX	INTEGER
			ACCESS	read-only
			STATUS	current
	DESCRIPTION ""
			::= { mbus8C 85 }

mbus8CVIF28		OBJECT-TYPE
			SYNTAX	INTEGER
			ACCESS	read-only
			STATUS	current
	DESCRIPTION ""
			::= { mbus8C 86 }

mbus8CValue28		OBJECT-TYPE
			SYNTAX	INTEGER
			ACCESS	read-only
			STATUS	current
	DESCRIPTION ""
			::= { mbus8C 87 }

mbus8CVIF29		OBJECT-TYPE
			SYNTAX	INTEGER
			ACCESS	read-only
			STATUS	current
	DESCRIPTION ""
			::= { mbus8C 88 }

mbus8CValue29		OBJECT-TYPE
			SYNTAX	INTEGER
			ACCESS	read-only
			STATUS	current
	DESCRIPTION ""
			::= { mbus8C 89 }

mbus8CVIF2A		OBJECT-TYPE
			SYNTAX	INTEGER
			ACCESS	read-only
			STATUS	current
	DESCRIPTION ""
			::= { mbus8C 90 }

mbus8CValue2A		OBJECT-TYPE
			SYNTAX	INTEGER
			ACCESS	read-only
			STATUS	current
	DESCRIPTION ""
			::= { mbus8C 91 }

mbus8CVIF2B		OBJECT-TYPE
			SYNTAX	INTEGER
			ACCESS	read-only
			STATUS	current
	DESCRIPTION ""
			::= { mbus8C 92 }

mbus8CValue2B		OBJECT-TYPE
			SYNTAX	INTEGER
			ACCESS	read-only
			STATUS	current
	DESCRIPTION ""
			::= { mbus8C 93 }

mbus8CVIF2C		OBJECT-TYPE
			SYNTAX	INTEGER
			ACCESS	read-only
			STATUS	current
	DESCRIPTION ""
			::= { mbus8C 94 }

mbus8CValue2C		OBJECT-TYPE
			SYNTAX	INTEGER
			ACCESS	read-only
			STATUS	current
	DESCRIPTION ""
			::= { mbus8C 95 }

mbus8CVIF2D		OBJECT-TYPE
			SYNTAX	INTEGER
			ACCESS	read-only
			STATUS	current
	DESCRIPTION ""
			::= { mbus8C 96 }

mbus8CValue2D		OBJECT-TYPE
			SYNTAX	INTEGER
			ACCESS	read-only
			STATUS	current
	DESCRIPTION ""
			::= { mbus8C 97 }

mbus8CVIF2E		OBJECT-TYPE
			SYNTAX	INTEGER
			ACCESS	read-only
			STATUS	current
	DESCRIPTION ""
			::= { mbus8C 98 }

mbus8CValue2E		OBJECT-TYPE
			SYNTAX	INTEGER
			ACCESS	read-only
			STATUS	current
	DESCRIPTION ""
			::= { mbus8C 99 }

mbus8CVIF2F		OBJECT-TYPE
			SYNTAX	INTEGER
			ACCESS	read-only
			STATUS	current
	DESCRIPTION ""
			::= { mbus8C 100 }

mbus8CValue2F		OBJECT-TYPE
			SYNTAX	INTEGER
			ACCESS	read-only
			STATUS	current
	DESCRIPTION ""
			::= { mbus8C 101 }

mbus8D			OBJECT IDENTIFIER ::= { mbus 141 }

mbus8DIdNumber		OBJECT-TYPE
			SYNTAX	Gauge
			ACCESS	read-only
			STATUS	current
	DESCRIPTION ""
			::= { mbus8D 1 }

mbus8DManufacturer	OBJECT-TYPE
			SYNTAX	Gauge
			ACCESS	read-only
			STATUS	current
	DESCRIPTION ""
			::= { mbus8D 2 }

mbus8DVersion		OBJECT-TYPE
			SYNTAX	Gauge
			ACCESS	read-only
			STATUS	current
	DESCRIPTION ""
			::= { mbus8D 3 }

mbus8DMedium		OBJECT-TYPE
			SYNTAX	Gauge
			ACCESS	read-only
			STATUS	current
	DESCRIPTION ""
			::= { mbus8D 4 }

mbus8DStatus		OBJECT-TYPE
			SYNTAX	Gauge
			ACCESS	read-only
			STATUS	current
	DESCRIPTION ""
			::= { mbus8D 5 }

mbus8DVIF00		OBJECT-TYPE
			SYNTAX	INTEGER
			ACCESS	read-only
			STATUS	current
	DESCRIPTION ""
			::= { mbus8D 6 }

mbus8DValue00		OBJECT-TYPE
			SYNTAX	INTEGER
			ACCESS	read-only
			STATUS	current
	DESCRIPTION ""
			::= { mbus8D 7 }

mbus8DVIF01		OBJECT-TYPE
			SYNTAX	INTEGER
			ACCESS	read-only
			STATUS	current
	DESCRIPTION ""
			::= { mbus8D 8 }

mbus8DValue01		OBJECT-TYPE
			SYNTAX	INTEGER
			ACCESS	read-only
			STATUS	current
	DESCRIPTION ""
			::= { mbus8D 9 }

mbus8DVIF02		OBJECT-TYPE
			SYNTAX	INTEGER
			ACCESS	read-only
			STATUS	current
	DESCRIPTION ""
			::= { mbus8D 10 }

mbus8DValue02		OBJECT-TYPE
			SYNTAX	INTEGER
			ACCESS	read-only
			STATUS	current
	DESCRIPTION ""
			::= { mbus8D 11 }

mbus8DVIF03		OBJECT-TYPE
			SYNTAX	INTEGER
			ACCESS	read-only
			STATUS	current
	DESCRIPTION ""
			::= { mbus8D 12 }

mbus8DValue03		OBJECT-TYPE
			SYNTAX	INTEGER
			ACCESS	read-only
			STATUS	current
	DESCRIPTION ""
			::= { mbus8D 13 }

mbus8DVIF04		OBJECT-TYPE
			SYNTAX	INTEGER
			ACCESS	read-only
			STATUS	current
	DESCRIPTION ""
			::= { mbus8D 14 }

mbus8DValue04		OBJECT-TYPE
			SYNTAX	INTEGER
			ACCESS	read-only
			STATUS	current
	DESCRIPTION ""
			::= { mbus8D 15 }

mbus8DVIF05		OBJECT-TYPE
			SYNTAX	INTEGER
			ACCESS	read-only
			STATUS	current
	DESCRIPTION ""
			::= { mbus8D 16 }

mbus8DValue05		OBJECT-TYPE
			SYNTAX	INTEGER
			ACCESS	read-only
			STATUS	current
	DESCRIPTION ""
			::= { mbus8D 17 }

mbus8DVIF06		OBJECT-TYPE
			SYNTAX	INTEGER
			ACCESS	read-only
			STATUS	current
	DESCRIPTION ""
			::= { mbus8D 18 }

mbus8DValue06		OBJECT-TYPE
			SYNTAX	INTEGER
			ACCESS	read-only
			STATUS	current
	DESCRIPTION ""
			::= { mbus8D 19 }

mbus8DVIF07		OBJECT-TYPE
			SYNTAX	INTEGER
			ACCESS	read-only
			STATUS	current
	DESCRIPTION ""
			::= { mbus8D 20 }

mbus8DValue07		OBJECT-TYPE
			SYNTAX	INTEGER
			ACCESS	read-only
			STATUS	current
	DESCRIPTION ""
			::= { mbus8D 21 }

mbus8DVIF08		OBJECT-TYPE
			SYNTAX	INTEGER
			ACCESS	read-only
			STATUS	current
	DESCRIPTION ""
			::= { mbus8D 22 }

mbus8DValue08		OBJECT-TYPE
			SYNTAX	INTEGER
			ACCESS	read-only
			STATUS	current
	DESCRIPTION ""
			::= { mbus8D 23 }

mbus8DVIF09		OBJECT-TYPE
			SYNTAX	INTEGER
			ACCESS	read-only
			STATUS	current
	DESCRIPTION ""
			::= { mbus8D 24 }

mbus8DValue09		OBJECT-TYPE
			SYNTAX	INTEGER
			ACCESS	read-only
			STATUS	current
	DESCRIPTION ""
			::= { mbus8D 25 }

mbus8DVIF0A		OBJECT-TYPE
			SYNTAX	INTEGER
			ACCESS	read-only
			STATUS	current
	DESCRIPTION ""
			::= { mbus8D 26 }

mbus8DValue0A		OBJECT-TYPE
			SYNTAX	INTEGER
			ACCESS	read-only
			STATUS	current
	DESCRIPTION ""
			::= { mbus8D 27 }

mbus8DVIF0B		OBJECT-TYPE
			SYNTAX	INTEGER
			ACCESS	read-only
			STATUS	current
	DESCRIPTION ""
			::= { mbus8D 28 }

mbus8DValue0B		OBJECT-TYPE
			SYNTAX	INTEGER
			ACCESS	read-only
			STATUS	current
	DESCRIPTION ""
			::= { mbus8D 29 }

mbus8DVIF0C		OBJECT-TYPE
			SYNTAX	INTEGER
			ACCESS	read-only
			STATUS	current
	DESCRIPTION ""
			::= { mbus8D 30 }

mbus8DValue0C		OBJECT-TYPE
			SYNTAX	INTEGER
			ACCESS	read-only
			STATUS	current
	DESCRIPTION ""
			::= { mbus8D 31 }

mbus8DVIF0D		OBJECT-TYPE
			SYNTAX	INTEGER
			ACCESS	read-only
			STATUS	current
	DESCRIPTION ""
			::= { mbus8D 32 }

mbus8DValue0D		OBJECT-TYPE
			SYNTAX	INTEGER
			ACCESS	read-only
			STATUS	current
	DESCRIPTION ""
			::= { mbus8D 33 }

mbus8DVIF0E		OBJECT-TYPE
			SYNTAX	INTEGER
			ACCESS	read-only
			STATUS	current
	DESCRIPTION ""
			::= { mbus8D 34 }

mbus8DValue0E		OBJECT-TYPE
			SYNTAX	INTEGER
			ACCESS	read-only
			STATUS	current
	DESCRIPTION ""
			::= { mbus8D 35 }

mbus8DVIF0F		OBJECT-TYPE
			SYNTAX	INTEGER
			ACCESS	read-only
			STATUS	current
	DESCRIPTION ""
			::= { mbus8D 36 }

mbus8DValue0F		OBJECT-TYPE
			SYNTAX	INTEGER
			ACCESS	read-only
			STATUS	current
	DESCRIPTION ""
			::= { mbus8D 37 }

mbus8DVIF10		OBJECT-TYPE
			SYNTAX	INTEGER
			ACCESS	read-only
			STATUS	current
	DESCRIPTION ""
			::= { mbus8D 38 }

mbus8DValue10		OBJECT-TYPE
			SYNTAX	INTEGER
			ACCESS	read-only
			STATUS	current
	DESCRIPTION ""
			::= { mbus8D 39 }

mbus8DVIF11		OBJECT-TYPE
			SYNTAX	INTEGER
			ACCESS	read-only
			STATUS	current
	DESCRIPTION ""
			::= { mbus8D 40 }

mbus8DValue11		OBJECT-TYPE
			SYNTAX	INTEGER
			ACCESS	read-only
			STATUS	current
	DESCRIPTION ""
			::= { mbus8D 41 }

mbus8DVIF12		OBJECT-TYPE
			SYNTAX	INTEGER
			ACCESS	read-only
			STATUS	current
	DESCRIPTION ""
			::= { mbus8D 42 }

mbus8DValue12		OBJECT-TYPE
			SYNTAX	INTEGER
			ACCESS	read-only
			STATUS	current
	DESCRIPTION ""
			::= { mbus8D 43 }

mbus8DVIF13		OBJECT-TYPE
			SYNTAX	INTEGER
			ACCESS	read-only
			STATUS	current
	DESCRIPTION ""
			::= { mbus8D 44 }

mbus8DValue13		OBJECT-TYPE
			SYNTAX	INTEGER
			ACCESS	read-only
			STATUS	current
	DESCRIPTION ""
			::= { mbus8D 45 }

mbus8DVIF14		OBJECT-TYPE
			SYNTAX	INTEGER
			ACCESS	read-only
			STATUS	current
	DESCRIPTION ""
			::= { mbus8D 46 }

mbus8DValue14		OBJECT-TYPE
			SYNTAX	INTEGER
			ACCESS	read-only
			STATUS	current
	DESCRIPTION ""
			::= { mbus8D 47 }

mbus8DVIF15		OBJECT-TYPE
			SYNTAX	INTEGER
			ACCESS	read-only
			STATUS	current
	DESCRIPTION ""
			::= { mbus8D 48 }

mbus8DValue15		OBJECT-TYPE
			SYNTAX	INTEGER
			ACCESS	read-only
			STATUS	current
	DESCRIPTION ""
			::= { mbus8D 49 }

mbus8DVIF16		OBJECT-TYPE
			SYNTAX	INTEGER
			ACCESS	read-only
			STATUS	current
	DESCRIPTION ""
			::= { mbus8D 50 }

mbus8DValue16		OBJECT-TYPE
			SYNTAX	INTEGER
			ACCESS	read-only
			STATUS	current
	DESCRIPTION ""
			::= { mbus8D 51 }

mbus8DVIF17		OBJECT-TYPE
			SYNTAX	INTEGER
			ACCESS	read-only
			STATUS	current
	DESCRIPTION ""
			::= { mbus8D 52 }

mbus8DValue17		OBJECT-TYPE
			SYNTAX	INTEGER
			ACCESS	read-only
			STATUS	current
	DESCRIPTION ""
			::= { mbus8D 53 }

mbus8DVIF18		OBJECT-TYPE
			SYNTAX	INTEGER
			ACCESS	read-only
			STATUS	current
	DESCRIPTION ""
			::= { mbus8D 54 }

mbus8DValue18		OBJECT-TYPE
			SYNTAX	INTEGER
			ACCESS	read-only
			STATUS	current
	DESCRIPTION ""
			::= { mbus8D 55 }

mbus8DVIF19		OBJECT-TYPE
			SYNTAX	INTEGER
			ACCESS	read-only
			STATUS	current
	DESCRIPTION ""
			::= { mbus8D 56 }

mbus8DValue19		OBJECT-TYPE
			SYNTAX	INTEGER
			ACCESS	read-only
			STATUS	current
	DESCRIPTION ""
			::= { mbus8D 57 }

mbus8DVIF1A		OBJECT-TYPE
			SYNTAX	INTEGER
			ACCESS	read-only
			STATUS	current
	DESCRIPTION ""
			::= { mbus8D 58 }

mbus8DValue1A		OBJECT-TYPE
			SYNTAX	INTEGER
			ACCESS	read-only
			STATUS	current
	DESCRIPTION ""
			::= { mbus8D 59 }

mbus8DVIF1B		OBJECT-TYPE
			SYNTAX	INTEGER
			ACCESS	read-only
			STATUS	current
	DESCRIPTION ""
			::= { mbus8D 60 }

mbus8DValue1B		OBJECT-TYPE
			SYNTAX	INTEGER
			ACCESS	read-only
			STATUS	current
	DESCRIPTION ""
			::= { mbus8D 61 }

mbus8DVIF1C		OBJECT-TYPE
			SYNTAX	INTEGER
			ACCESS	read-only
			STATUS	current
	DESCRIPTION ""
			::= { mbus8D 62 }

mbus8DValue1C		OBJECT-TYPE
			SYNTAX	INTEGER
			ACCESS	read-only
			STATUS	current
	DESCRIPTION ""
			::= { mbus8D 63 }

mbus8DVIF1D		OBJECT-TYPE
			SYNTAX	INTEGER
			ACCESS	read-only
			STATUS	current
	DESCRIPTION ""
			::= { mbus8D 64 }

mbus8DValue1D		OBJECT-TYPE
			SYNTAX	INTEGER
			ACCESS	read-only
			STATUS	current
	DESCRIPTION ""
			::= { mbus8D 65 }

mbus8DVIF1E		OBJECT-TYPE
			SYNTAX	INTEGER
			ACCESS	read-only
			STATUS	current
	DESCRIPTION ""
			::= { mbus8D 66 }

mbus8DValue1E		OBJECT-TYPE
			SYNTAX	INTEGER
			ACCESS	read-only
			STATUS	current
	DESCRIPTION ""
			::= { mbus8D 67 }

mbus8DVIF1F		OBJECT-TYPE
			SYNTAX	INTEGER
			ACCESS	read-only
			STATUS	current
	DESCRIPTION ""
			::= { mbus8D 68 }

mbus8DValue1F		OBJECT-TYPE
			SYNTAX	INTEGER
			ACCESS	read-only
			STATUS	current
	DESCRIPTION ""
			::= { mbus8D 69 }

mbus8DVIF20		OBJECT-TYPE
			SYNTAX	INTEGER
			ACCESS	read-only
			STATUS	current
	DESCRIPTION ""
			::= { mbus8D 70 }

mbus8DValue20		OBJECT-TYPE
			SYNTAX	INTEGER
			ACCESS	read-only
			STATUS	current
	DESCRIPTION ""
			::= { mbus8D 71 }

mbus8DVIF21		OBJECT-TYPE
			SYNTAX	INTEGER
			ACCESS	read-only
			STATUS	current
	DESCRIPTION ""
			::= { mbus8D 72 }

mbus8DValue21		OBJECT-TYPE
			SYNTAX	INTEGER
			ACCESS	read-only
			STATUS	current
	DESCRIPTION ""
			::= { mbus8D 73 }

mbus8DVIF22		OBJECT-TYPE
			SYNTAX	INTEGER
			ACCESS	read-only
			STATUS	current
	DESCRIPTION ""
			::= { mbus8D 74 }

mbus8DValue22		OBJECT-TYPE
			SYNTAX	INTEGER
			ACCESS	read-only
			STATUS	current
	DESCRIPTION ""
			::= { mbus8D 75 }

mbus8DVIF23		OBJECT-TYPE
			SYNTAX	INTEGER
			ACCESS	read-only
			STATUS	current
	DESCRIPTION ""
			::= { mbus8D 76 }

mbus8DValue23		OBJECT-TYPE
			SYNTAX	INTEGER
			ACCESS	read-only
			STATUS	current
	DESCRIPTION ""
			::= { mbus8D 77 }

mbus8DVIF24		OBJECT-TYPE
			SYNTAX	INTEGER
			ACCESS	read-only
			STATUS	current
	DESCRIPTION ""
			::= { mbus8D 78 }

mbus8DValue24		OBJECT-TYPE
			SYNTAX	INTEGER
			ACCESS	read-only
			STATUS	current
	DESCRIPTION ""
			::= { mbus8D 79 }

mbus8DVIF25		OBJECT-TYPE
			SYNTAX	INTEGER
			ACCESS	read-only
			STATUS	current
	DESCRIPTION ""
			::= { mbus8D 80 }

mbus8DValue25		OBJECT-TYPE
			SYNTAX	INTEGER
			ACCESS	read-only
			STATUS	current
	DESCRIPTION ""
			::= { mbus8D 81 }

mbus8DVIF26		OBJECT-TYPE
			SYNTAX	INTEGER
			ACCESS	read-only
			STATUS	current
	DESCRIPTION ""
			::= { mbus8D 82 }

mbus8DValue26		OBJECT-TYPE
			SYNTAX	INTEGER
			ACCESS	read-only
			STATUS	current
	DESCRIPTION ""
			::= { mbus8D 83 }

mbus8DVIF27		OBJECT-TYPE
			SYNTAX	INTEGER
			ACCESS	read-only
			STATUS	current
	DESCRIPTION ""
			::= { mbus8D 84 }

mbus8DValue27		OBJECT-TYPE
			SYNTAX	INTEGER
			ACCESS	read-only
			STATUS	current
	DESCRIPTION ""
			::= { mbus8D 85 }

mbus8DVIF28		OBJECT-TYPE
			SYNTAX	INTEGER
			ACCESS	read-only
			STATUS	current
	DESCRIPTION ""
			::= { mbus8D 86 }

mbus8DValue28		OBJECT-TYPE
			SYNTAX	INTEGER
			ACCESS	read-only
			STATUS	current
	DESCRIPTION ""
			::= { mbus8D 87 }

mbus8DVIF29		OBJECT-TYPE
			SYNTAX	INTEGER
			ACCESS	read-only
			STATUS	current
	DESCRIPTION ""
			::= { mbus8D 88 }

mbus8DValue29		OBJECT-TYPE
			SYNTAX	INTEGER
			ACCESS	read-only
			STATUS	current
	DESCRIPTION ""
			::= { mbus8D 89 }

mbus8DVIF2A		OBJECT-TYPE
			SYNTAX	INTEGER
			ACCESS	read-only
			STATUS	current
	DESCRIPTION ""
			::= { mbus8D 90 }

mbus8DValue2A		OBJECT-TYPE
			SYNTAX	INTEGER
			ACCESS	read-only
			STATUS	current
	DESCRIPTION ""
			::= { mbus8D 91 }

mbus8DVIF2B		OBJECT-TYPE
			SYNTAX	INTEGER
			ACCESS	read-only
			STATUS	current
	DESCRIPTION ""
			::= { mbus8D 92 }

mbus8DValue2B		OBJECT-TYPE
			SYNTAX	INTEGER
			ACCESS	read-only
			STATUS	current
	DESCRIPTION ""
			::= { mbus8D 93 }

mbus8DVIF2C		OBJECT-TYPE
			SYNTAX	INTEGER
			ACCESS	read-only
			STATUS	current
	DESCRIPTION ""
			::= { mbus8D 94 }

mbus8DValue2C		OBJECT-TYPE
			SYNTAX	INTEGER
			ACCESS	read-only
			STATUS	current
	DESCRIPTION ""
			::= { mbus8D 95 }

mbus8DVIF2D		OBJECT-TYPE
			SYNTAX	INTEGER
			ACCESS	read-only
			STATUS	current
	DESCRIPTION ""
			::= { mbus8D 96 }

mbus8DValue2D		OBJECT-TYPE
			SYNTAX	INTEGER
			ACCESS	read-only
			STATUS	current
	DESCRIPTION ""
			::= { mbus8D 97 }

mbus8DVIF2E		OBJECT-TYPE
			SYNTAX	INTEGER
			ACCESS	read-only
			STATUS	current
	DESCRIPTION ""
			::= { mbus8D 98 }

mbus8DValue2E		OBJECT-TYPE
			SYNTAX	INTEGER
			ACCESS	read-only
			STATUS	current
	DESCRIPTION ""
			::= { mbus8D 99 }

mbus8DVIF2F		OBJECT-TYPE
			SYNTAX	INTEGER
			ACCESS	read-only
			STATUS	current
	DESCRIPTION ""
			::= { mbus8D 100 }

mbus8DValue2F		OBJECT-TYPE
			SYNTAX	INTEGER
			ACCESS	read-only
			STATUS	current
	DESCRIPTION ""
			::= { mbus8D 101 }

mbus8E			OBJECT IDENTIFIER ::= { mbus 142 }

mbus8EIdNumber		OBJECT-TYPE
			SYNTAX	Gauge
			ACCESS	read-only
			STATUS	current
	DESCRIPTION ""
			::= { mbus8E 1 }

mbus8EManufacturer	OBJECT-TYPE
			SYNTAX	Gauge
			ACCESS	read-only
			STATUS	current
	DESCRIPTION ""
			::= { mbus8E 2 }

mbus8EVersion		OBJECT-TYPE
			SYNTAX	Gauge
			ACCESS	read-only
			STATUS	current
	DESCRIPTION ""
			::= { mbus8E 3 }

mbus8EMedium		OBJECT-TYPE
			SYNTAX	Gauge
			ACCESS	read-only
			STATUS	current
	DESCRIPTION ""
			::= { mbus8E 4 }

mbus8EStatus		OBJECT-TYPE
			SYNTAX	Gauge
			ACCESS	read-only
			STATUS	current
	DESCRIPTION ""
			::= { mbus8E 5 }

mbus8EVIF00		OBJECT-TYPE
			SYNTAX	INTEGER
			ACCESS	read-only
			STATUS	current
	DESCRIPTION ""
			::= { mbus8E 6 }

mbus8EValue00		OBJECT-TYPE
			SYNTAX	INTEGER
			ACCESS	read-only
			STATUS	current
	DESCRIPTION ""
			::= { mbus8E 7 }

mbus8EVIF01		OBJECT-TYPE
			SYNTAX	INTEGER
			ACCESS	read-only
			STATUS	current
	DESCRIPTION ""
			::= { mbus8E 8 }

mbus8EValue01		OBJECT-TYPE
			SYNTAX	INTEGER
			ACCESS	read-only
			STATUS	current
	DESCRIPTION ""
			::= { mbus8E 9 }

mbus8EVIF02		OBJECT-TYPE
			SYNTAX	INTEGER
			ACCESS	read-only
			STATUS	current
	DESCRIPTION ""
			::= { mbus8E 10 }

mbus8EValue02		OBJECT-TYPE
			SYNTAX	INTEGER
			ACCESS	read-only
			STATUS	current
	DESCRIPTION ""
			::= { mbus8E 11 }

mbus8EVIF03		OBJECT-TYPE
			SYNTAX	INTEGER
			ACCESS	read-only
			STATUS	current
	DESCRIPTION ""
			::= { mbus8E 12 }

mbus8EValue03		OBJECT-TYPE
			SYNTAX	INTEGER
			ACCESS	read-only
			STATUS	current
	DESCRIPTION ""
			::= { mbus8E 13 }

mbus8EVIF04		OBJECT-TYPE
			SYNTAX	INTEGER
			ACCESS	read-only
			STATUS	current
	DESCRIPTION ""
			::= { mbus8E 14 }

mbus8EValue04		OBJECT-TYPE
			SYNTAX	INTEGER
			ACCESS	read-only
			STATUS	current
	DESCRIPTION ""
			::= { mbus8E 15 }

mbus8EVIF05		OBJECT-TYPE
			SYNTAX	INTEGER
			ACCESS	read-only
			STATUS	current
	DESCRIPTION ""
			::= { mbus8E 16 }

mbus8EValue05		OBJECT-TYPE
			SYNTAX	INTEGER
			ACCESS	read-only
			STATUS	current
	DESCRIPTION ""
			::= { mbus8E 17 }

mbus8EVIF06		OBJECT-TYPE
			SYNTAX	INTEGER
			ACCESS	read-only
			STATUS	current
	DESCRIPTION ""
			::= { mbus8E 18 }

mbus8EValue06		OBJECT-TYPE
			SYNTAX	INTEGER
			ACCESS	read-only
			STATUS	current
	DESCRIPTION ""
			::= { mbus8E 19 }

mbus8EVIF07		OBJECT-TYPE
			SYNTAX	INTEGER
			ACCESS	read-only
			STATUS	current
	DESCRIPTION ""
			::= { mbus8E 20 }

mbus8EValue07		OBJECT-TYPE
			SYNTAX	INTEGER
			ACCESS	read-only
			STATUS	current
	DESCRIPTION ""
			::= { mbus8E 21 }

mbus8EVIF08		OBJECT-TYPE
			SYNTAX	INTEGER
			ACCESS	read-only
			STATUS	current
	DESCRIPTION ""
			::= { mbus8E 22 }

mbus8EValue08		OBJECT-TYPE
			SYNTAX	INTEGER
			ACCESS	read-only
			STATUS	current
	DESCRIPTION ""
			::= { mbus8E 23 }

mbus8EVIF09		OBJECT-TYPE
			SYNTAX	INTEGER
			ACCESS	read-only
			STATUS	current
	DESCRIPTION ""
			::= { mbus8E 24 }

mbus8EValue09		OBJECT-TYPE
			SYNTAX	INTEGER
			ACCESS	read-only
			STATUS	current
	DESCRIPTION ""
			::= { mbus8E 25 }

mbus8EVIF0A		OBJECT-TYPE
			SYNTAX	INTEGER
			ACCESS	read-only
			STATUS	current
	DESCRIPTION ""
			::= { mbus8E 26 }

mbus8EValue0A		OBJECT-TYPE
			SYNTAX	INTEGER
			ACCESS	read-only
			STATUS	current
	DESCRIPTION ""
			::= { mbus8E 27 }

mbus8EVIF0B		OBJECT-TYPE
			SYNTAX	INTEGER
			ACCESS	read-only
			STATUS	current
	DESCRIPTION ""
			::= { mbus8E 28 }

mbus8EValue0B		OBJECT-TYPE
			SYNTAX	INTEGER
			ACCESS	read-only
			STATUS	current
	DESCRIPTION ""
			::= { mbus8E 29 }

mbus8EVIF0C		OBJECT-TYPE
			SYNTAX	INTEGER
			ACCESS	read-only
			STATUS	current
	DESCRIPTION ""
			::= { mbus8E 30 }

mbus8EValue0C		OBJECT-TYPE
			SYNTAX	INTEGER
			ACCESS	read-only
			STATUS	current
	DESCRIPTION ""
			::= { mbus8E 31 }

mbus8EVIF0D		OBJECT-TYPE
			SYNTAX	INTEGER
			ACCESS	read-only
			STATUS	current
	DESCRIPTION ""
			::= { mbus8E 32 }

mbus8EValue0D		OBJECT-TYPE
			SYNTAX	INTEGER
			ACCESS	read-only
			STATUS	current
	DESCRIPTION ""
			::= { mbus8E 33 }

mbus8EVIF0E		OBJECT-TYPE
			SYNTAX	INTEGER
			ACCESS	read-only
			STATUS	current
	DESCRIPTION ""
			::= { mbus8E 34 }

mbus8EValue0E		OBJECT-TYPE
			SYNTAX	INTEGER
			ACCESS	read-only
			STATUS	current
	DESCRIPTION ""
			::= { mbus8E 35 }

mbus8EVIF0F		OBJECT-TYPE
			SYNTAX	INTEGER
			ACCESS	read-only
			STATUS	current
	DESCRIPTION ""
			::= { mbus8E 36 }

mbus8EValue0F		OBJECT-TYPE
			SYNTAX	INTEGER
			ACCESS	read-only
			STATUS	current
	DESCRIPTION ""
			::= { mbus8E 37 }

mbus8EVIF10		OBJECT-TYPE
			SYNTAX	INTEGER
			ACCESS	read-only
			STATUS	current
	DESCRIPTION ""
			::= { mbus8E 38 }

mbus8EValue10		OBJECT-TYPE
			SYNTAX	INTEGER
			ACCESS	read-only
			STATUS	current
	DESCRIPTION ""
			::= { mbus8E 39 }

mbus8EVIF11		OBJECT-TYPE
			SYNTAX	INTEGER
			ACCESS	read-only
			STATUS	current
	DESCRIPTION ""
			::= { mbus8E 40 }

mbus8EValue11		OBJECT-TYPE
			SYNTAX	INTEGER
			ACCESS	read-only
			STATUS	current
	DESCRIPTION ""
			::= { mbus8E 41 }

mbus8EVIF12		OBJECT-TYPE
			SYNTAX	INTEGER
			ACCESS	read-only
			STATUS	current
	DESCRIPTION ""
			::= { mbus8E 42 }

mbus8EValue12		OBJECT-TYPE
			SYNTAX	INTEGER
			ACCESS	read-only
			STATUS	current
	DESCRIPTION ""
			::= { mbus8E 43 }

mbus8EVIF13		OBJECT-TYPE
			SYNTAX	INTEGER
			ACCESS	read-only
			STATUS	current
	DESCRIPTION ""
			::= { mbus8E 44 }

mbus8EValue13		OBJECT-TYPE
			SYNTAX	INTEGER
			ACCESS	read-only
			STATUS	current
	DESCRIPTION ""
			::= { mbus8E 45 }

mbus8EVIF14		OBJECT-TYPE
			SYNTAX	INTEGER
			ACCESS	read-only
			STATUS	current
	DESCRIPTION ""
			::= { mbus8E 46 }

mbus8EValue14		OBJECT-TYPE
			SYNTAX	INTEGER
			ACCESS	read-only
			STATUS	current
	DESCRIPTION ""
			::= { mbus8E 47 }

mbus8EVIF15		OBJECT-TYPE
			SYNTAX	INTEGER
			ACCESS	read-only
			STATUS	current
	DESCRIPTION ""
			::= { mbus8E 48 }

mbus8EValue15		OBJECT-TYPE
			SYNTAX	INTEGER
			ACCESS	read-only
			STATUS	current
	DESCRIPTION ""
			::= { mbus8E 49 }

mbus8EVIF16		OBJECT-TYPE
			SYNTAX	INTEGER
			ACCESS	read-only
			STATUS	current
	DESCRIPTION ""
			::= { mbus8E 50 }

mbus8EValue16		OBJECT-TYPE
			SYNTAX	INTEGER
			ACCESS	read-only
			STATUS	current
	DESCRIPTION ""
			::= { mbus8E 51 }

mbus8EVIF17		OBJECT-TYPE
			SYNTAX	INTEGER
			ACCESS	read-only
			STATUS	current
	DESCRIPTION ""
			::= { mbus8E 52 }

mbus8EValue17		OBJECT-TYPE
			SYNTAX	INTEGER
			ACCESS	read-only
			STATUS	current
	DESCRIPTION ""
			::= { mbus8E 53 }

mbus8EVIF18		OBJECT-TYPE
			SYNTAX	INTEGER
			ACCESS	read-only
			STATUS	current
	DESCRIPTION ""
			::= { mbus8E 54 }

mbus8EValue18		OBJECT-TYPE
			SYNTAX	INTEGER
			ACCESS	read-only
			STATUS	current
	DESCRIPTION ""
			::= { mbus8E 55 }

mbus8EVIF19		OBJECT-TYPE
			SYNTAX	INTEGER
			ACCESS	read-only
			STATUS	current
	DESCRIPTION ""
			::= { mbus8E 56 }

mbus8EValue19		OBJECT-TYPE
			SYNTAX	INTEGER
			ACCESS	read-only
			STATUS	current
	DESCRIPTION ""
			::= { mbus8E 57 }

mbus8EVIF1A		OBJECT-TYPE
			SYNTAX	INTEGER
			ACCESS	read-only
			STATUS	current
	DESCRIPTION ""
			::= { mbus8E 58 }

mbus8EValue1A		OBJECT-TYPE
			SYNTAX	INTEGER
			ACCESS	read-only
			STATUS	current
	DESCRIPTION ""
			::= { mbus8E 59 }

mbus8EVIF1B		OBJECT-TYPE
			SYNTAX	INTEGER
			ACCESS	read-only
			STATUS	current
	DESCRIPTION ""
			::= { mbus8E 60 }

mbus8EValue1B		OBJECT-TYPE
			SYNTAX	INTEGER
			ACCESS	read-only
			STATUS	current
	DESCRIPTION ""
			::= { mbus8E 61 }

mbus8EVIF1C		OBJECT-TYPE
			SYNTAX	INTEGER
			ACCESS	read-only
			STATUS	current
	DESCRIPTION ""
			::= { mbus8E 62 }

mbus8EValue1C		OBJECT-TYPE
			SYNTAX	INTEGER
			ACCESS	read-only
			STATUS	current
	DESCRIPTION ""
			::= { mbus8E 63 }

mbus8EVIF1D		OBJECT-TYPE
			SYNTAX	INTEGER
			ACCESS	read-only
			STATUS	current
	DESCRIPTION ""
			::= { mbus8E 64 }

mbus8EValue1D		OBJECT-TYPE
			SYNTAX	INTEGER
			ACCESS	read-only
			STATUS	current
	DESCRIPTION ""
			::= { mbus8E 65 }

mbus8EVIF1E		OBJECT-TYPE
			SYNTAX	INTEGER
			ACCESS	read-only
			STATUS	current
	DESCRIPTION ""
			::= { mbus8E 66 }

mbus8EValue1E		OBJECT-TYPE
			SYNTAX	INTEGER
			ACCESS	read-only
			STATUS	current
	DESCRIPTION ""
			::= { mbus8E 67 }

mbus8EVIF1F		OBJECT-TYPE
			SYNTAX	INTEGER
			ACCESS	read-only
			STATUS	current
	DESCRIPTION ""
			::= { mbus8E 68 }

mbus8EValue1F		OBJECT-TYPE
			SYNTAX	INTEGER
			ACCESS	read-only
			STATUS	current
	DESCRIPTION ""
			::= { mbus8E 69 }

mbus8EVIF20		OBJECT-TYPE
			SYNTAX	INTEGER
			ACCESS	read-only
			STATUS	current
	DESCRIPTION ""
			::= { mbus8E 70 }

mbus8EValue20		OBJECT-TYPE
			SYNTAX	INTEGER
			ACCESS	read-only
			STATUS	current
	DESCRIPTION ""
			::= { mbus8E 71 }

mbus8EVIF21		OBJECT-TYPE
			SYNTAX	INTEGER
			ACCESS	read-only
			STATUS	current
	DESCRIPTION ""
			::= { mbus8E 72 }

mbus8EValue21		OBJECT-TYPE
			SYNTAX	INTEGER
			ACCESS	read-only
			STATUS	current
	DESCRIPTION ""
			::= { mbus8E 73 }

mbus8EVIF22		OBJECT-TYPE
			SYNTAX	INTEGER
			ACCESS	read-only
			STATUS	current
	DESCRIPTION ""
			::= { mbus8E 74 }

mbus8EValue22		OBJECT-TYPE
			SYNTAX	INTEGER
			ACCESS	read-only
			STATUS	current
	DESCRIPTION ""
			::= { mbus8E 75 }

mbus8EVIF23		OBJECT-TYPE
			SYNTAX	INTEGER
			ACCESS	read-only
			STATUS	current
	DESCRIPTION ""
			::= { mbus8E 76 }

mbus8EValue23		OBJECT-TYPE
			SYNTAX	INTEGER
			ACCESS	read-only
			STATUS	current
	DESCRIPTION ""
			::= { mbus8E 77 }

mbus8EVIF24		OBJECT-TYPE
			SYNTAX	INTEGER
			ACCESS	read-only
			STATUS	current
	DESCRIPTION ""
			::= { mbus8E 78 }

mbus8EValue24		OBJECT-TYPE
			SYNTAX	INTEGER
			ACCESS	read-only
			STATUS	current
	DESCRIPTION ""
			::= { mbus8E 79 }

mbus8EVIF25		OBJECT-TYPE
			SYNTAX	INTEGER
			ACCESS	read-only
			STATUS	current
	DESCRIPTION ""
			::= { mbus8E 80 }

mbus8EValue25		OBJECT-TYPE
			SYNTAX	INTEGER
			ACCESS	read-only
			STATUS	current
	DESCRIPTION ""
			::= { mbus8E 81 }

mbus8EVIF26		OBJECT-TYPE
			SYNTAX	INTEGER
			ACCESS	read-only
			STATUS	current
	DESCRIPTION ""
			::= { mbus8E 82 }

mbus8EValue26		OBJECT-TYPE
			SYNTAX	INTEGER
			ACCESS	read-only
			STATUS	current
	DESCRIPTION ""
			::= { mbus8E 83 }

mbus8EVIF27		OBJECT-TYPE
			SYNTAX	INTEGER
			ACCESS	read-only
			STATUS	current
	DESCRIPTION ""
			::= { mbus8E 84 }

mbus8EValue27		OBJECT-TYPE
			SYNTAX	INTEGER
			ACCESS	read-only
			STATUS	current
	DESCRIPTION ""
			::= { mbus8E 85 }

mbus8EVIF28		OBJECT-TYPE
			SYNTAX	INTEGER
			ACCESS	read-only
			STATUS	current
	DESCRIPTION ""
			::= { mbus8E 86 }

mbus8EValue28		OBJECT-TYPE
			SYNTAX	INTEGER
			ACCESS	read-only
			STATUS	current
	DESCRIPTION ""
			::= { mbus8E 87 }

mbus8EVIF29		OBJECT-TYPE
			SYNTAX	INTEGER
			ACCESS	read-only
			STATUS	current
	DESCRIPTION ""
			::= { mbus8E 88 }

mbus8EValue29		OBJECT-TYPE
			SYNTAX	INTEGER
			ACCESS	read-only
			STATUS	current
	DESCRIPTION ""
			::= { mbus8E 89 }

mbus8EVIF2A		OBJECT-TYPE
			SYNTAX	INTEGER
			ACCESS	read-only
			STATUS	current
	DESCRIPTION ""
			::= { mbus8E 90 }

mbus8EValue2A		OBJECT-TYPE
			SYNTAX	INTEGER
			ACCESS	read-only
			STATUS	current
	DESCRIPTION ""
			::= { mbus8E 91 }

mbus8EVIF2B		OBJECT-TYPE
			SYNTAX	INTEGER
			ACCESS	read-only
			STATUS	current
	DESCRIPTION ""
			::= { mbus8E 92 }

mbus8EValue2B		OBJECT-TYPE
			SYNTAX	INTEGER
			ACCESS	read-only
			STATUS	current
	DESCRIPTION ""
			::= { mbus8E 93 }

mbus8EVIF2C		OBJECT-TYPE
			SYNTAX	INTEGER
			ACCESS	read-only
			STATUS	current
	DESCRIPTION ""
			::= { mbus8E 94 }

mbus8EValue2C		OBJECT-TYPE
			SYNTAX	INTEGER
			ACCESS	read-only
			STATUS	current
	DESCRIPTION ""
			::= { mbus8E 95 }

mbus8EVIF2D		OBJECT-TYPE
			SYNTAX	INTEGER
			ACCESS	read-only
			STATUS	current
	DESCRIPTION ""
			::= { mbus8E 96 }

mbus8EValue2D		OBJECT-TYPE
			SYNTAX	INTEGER
			ACCESS	read-only
			STATUS	current
	DESCRIPTION ""
			::= { mbus8E 97 }

mbus8EVIF2E		OBJECT-TYPE
			SYNTAX	INTEGER
			ACCESS	read-only
			STATUS	current
	DESCRIPTION ""
			::= { mbus8E 98 }

mbus8EValue2E		OBJECT-TYPE
			SYNTAX	INTEGER
			ACCESS	read-only
			STATUS	current
	DESCRIPTION ""
			::= { mbus8E 99 }

mbus8EVIF2F		OBJECT-TYPE
			SYNTAX	INTEGER
			ACCESS	read-only
			STATUS	current
	DESCRIPTION ""
			::= { mbus8E 100 }

mbus8EValue2F		OBJECT-TYPE
			SYNTAX	INTEGER
			ACCESS	read-only
			STATUS	current
	DESCRIPTION ""
			::= { mbus8E 101 }

mbus8F			OBJECT IDENTIFIER ::= { mbus 143 }

mbus8FIdNumber		OBJECT-TYPE
			SYNTAX	Gauge
			ACCESS	read-only
			STATUS	current
	DESCRIPTION ""
			::= { mbus8F 1 }

mbus8FManufacturer	OBJECT-TYPE
			SYNTAX	Gauge
			ACCESS	read-only
			STATUS	current
	DESCRIPTION ""
			::= { mbus8F 2 }

mbus8FVersion		OBJECT-TYPE
			SYNTAX	Gauge
			ACCESS	read-only
			STATUS	current
	DESCRIPTION ""
			::= { mbus8F 3 }

mbus8FMedium		OBJECT-TYPE
			SYNTAX	Gauge
			ACCESS	read-only
			STATUS	current
	DESCRIPTION ""
			::= { mbus8F 4 }

mbus8FStatus		OBJECT-TYPE
			SYNTAX	Gauge
			ACCESS	read-only
			STATUS	current
	DESCRIPTION ""
			::= { mbus8F 5 }

mbus8FVIF00		OBJECT-TYPE
			SYNTAX	INTEGER
			ACCESS	read-only
			STATUS	current
	DESCRIPTION ""
			::= { mbus8F 6 }

mbus8FValue00		OBJECT-TYPE
			SYNTAX	INTEGER
			ACCESS	read-only
			STATUS	current
	DESCRIPTION ""
			::= { mbus8F 7 }

mbus8FVIF01		OBJECT-TYPE
			SYNTAX	INTEGER
			ACCESS	read-only
			STATUS	current
	DESCRIPTION ""
			::= { mbus8F 8 }

mbus8FValue01		OBJECT-TYPE
			SYNTAX	INTEGER
			ACCESS	read-only
			STATUS	current
	DESCRIPTION ""
			::= { mbus8F 9 }

mbus8FVIF02		OBJECT-TYPE
			SYNTAX	INTEGER
			ACCESS	read-only
			STATUS	current
	DESCRIPTION ""
			::= { mbus8F 10 }

mbus8FValue02		OBJECT-TYPE
			SYNTAX	INTEGER
			ACCESS	read-only
			STATUS	current
	DESCRIPTION ""
			::= { mbus8F 11 }

mbus8FVIF03		OBJECT-TYPE
			SYNTAX	INTEGER
			ACCESS	read-only
			STATUS	current
	DESCRIPTION ""
			::= { mbus8F 12 }

mbus8FValue03		OBJECT-TYPE
			SYNTAX	INTEGER
			ACCESS	read-only
			STATUS	current
	DESCRIPTION ""
			::= { mbus8F 13 }

mbus8FVIF04		OBJECT-TYPE
			SYNTAX	INTEGER
			ACCESS	read-only
			STATUS	current
	DESCRIPTION ""
			::= { mbus8F 14 }

mbus8FValue04		OBJECT-TYPE
			SYNTAX	INTEGER
			ACCESS	read-only
			STATUS	current
	DESCRIPTION ""
			::= { mbus8F 15 }

mbus8FVIF05		OBJECT-TYPE
			SYNTAX	INTEGER
			ACCESS	read-only
			STATUS	current
	DESCRIPTION ""
			::= { mbus8F 16 }

mbus8FValue05		OBJECT-TYPE
			SYNTAX	INTEGER
			ACCESS	read-only
			STATUS	current
	DESCRIPTION ""
			::= { mbus8F 17 }

mbus8FVIF06		OBJECT-TYPE
			SYNTAX	INTEGER
			ACCESS	read-only
			STATUS	current
	DESCRIPTION ""
			::= { mbus8F 18 }

mbus8FValue06		OBJECT-TYPE
			SYNTAX	INTEGER
			ACCESS	read-only
			STATUS	current
	DESCRIPTION ""
			::= { mbus8F 19 }

mbus8FVIF07		OBJECT-TYPE
			SYNTAX	INTEGER
			ACCESS	read-only
			STATUS	current
	DESCRIPTION ""
			::= { mbus8F 20 }

mbus8FValue07		OBJECT-TYPE
			SYNTAX	INTEGER
			ACCESS	read-only
			STATUS	current
	DESCRIPTION ""
			::= { mbus8F 21 }

mbus8FVIF08		OBJECT-TYPE
			SYNTAX	INTEGER
			ACCESS	read-only
			STATUS	current
	DESCRIPTION ""
			::= { mbus8F 22 }

mbus8FValue08		OBJECT-TYPE
			SYNTAX	INTEGER
			ACCESS	read-only
			STATUS	current
	DESCRIPTION ""
			::= { mbus8F 23 }

mbus8FVIF09		OBJECT-TYPE
			SYNTAX	INTEGER
			ACCESS	read-only
			STATUS	current
	DESCRIPTION ""
			::= { mbus8F 24 }

mbus8FValue09		OBJECT-TYPE
			SYNTAX	INTEGER
			ACCESS	read-only
			STATUS	current
	DESCRIPTION ""
			::= { mbus8F 25 }

mbus8FVIF0A		OBJECT-TYPE
			SYNTAX	INTEGER
			ACCESS	read-only
			STATUS	current
	DESCRIPTION ""
			::= { mbus8F 26 }

mbus8FValue0A		OBJECT-TYPE
			SYNTAX	INTEGER
			ACCESS	read-only
			STATUS	current
	DESCRIPTION ""
			::= { mbus8F 27 }

mbus8FVIF0B		OBJECT-TYPE
			SYNTAX	INTEGER
			ACCESS	read-only
			STATUS	current
	DESCRIPTION ""
			::= { mbus8F 28 }

mbus8FValue0B		OBJECT-TYPE
			SYNTAX	INTEGER
			ACCESS	read-only
			STATUS	current
	DESCRIPTION ""
			::= { mbus8F 29 }

mbus8FVIF0C		OBJECT-TYPE
			SYNTAX	INTEGER
			ACCESS	read-only
			STATUS	current
	DESCRIPTION ""
			::= { mbus8F 30 }

mbus8FValue0C		OBJECT-TYPE
			SYNTAX	INTEGER
			ACCESS	read-only
			STATUS	current
	DESCRIPTION ""
			::= { mbus8F 31 }

mbus8FVIF0D		OBJECT-TYPE
			SYNTAX	INTEGER
			ACCESS	read-only
			STATUS	current
	DESCRIPTION ""
			::= { mbus8F 32 }

mbus8FValue0D		OBJECT-TYPE
			SYNTAX	INTEGER
			ACCESS	read-only
			STATUS	current
	DESCRIPTION ""
			::= { mbus8F 33 }

mbus8FVIF0E		OBJECT-TYPE
			SYNTAX	INTEGER
			ACCESS	read-only
			STATUS	current
	DESCRIPTION ""
			::= { mbus8F 34 }

mbus8FValue0E		OBJECT-TYPE
			SYNTAX	INTEGER
			ACCESS	read-only
			STATUS	current
	DESCRIPTION ""
			::= { mbus8F 35 }

mbus8FVIF0F		OBJECT-TYPE
			SYNTAX	INTEGER
			ACCESS	read-only
			STATUS	current
	DESCRIPTION ""
			::= { mbus8F 36 }

mbus8FValue0F		OBJECT-TYPE
			SYNTAX	INTEGER
			ACCESS	read-only
			STATUS	current
	DESCRIPTION ""
			::= { mbus8F 37 }

mbus8FVIF10		OBJECT-TYPE
			SYNTAX	INTEGER
			ACCESS	read-only
			STATUS	current
	DESCRIPTION ""
			::= { mbus8F 38 }

mbus8FValue10		OBJECT-TYPE
			SYNTAX	INTEGER
			ACCESS	read-only
			STATUS	current
	DESCRIPTION ""
			::= { mbus8F 39 }

mbus8FVIF11		OBJECT-TYPE
			SYNTAX	INTEGER
			ACCESS	read-only
			STATUS	current
	DESCRIPTION ""
			::= { mbus8F 40 }

mbus8FValue11		OBJECT-TYPE
			SYNTAX	INTEGER
			ACCESS	read-only
			STATUS	current
	DESCRIPTION ""
			::= { mbus8F 41 }

mbus8FVIF12		OBJECT-TYPE
			SYNTAX	INTEGER
			ACCESS	read-only
			STATUS	current
	DESCRIPTION ""
			::= { mbus8F 42 }

mbus8FValue12		OBJECT-TYPE
			SYNTAX	INTEGER
			ACCESS	read-only
			STATUS	current
	DESCRIPTION ""
			::= { mbus8F 43 }

mbus8FVIF13		OBJECT-TYPE
			SYNTAX	INTEGER
			ACCESS	read-only
			STATUS	current
	DESCRIPTION ""
			::= { mbus8F 44 }

mbus8FValue13		OBJECT-TYPE
			SYNTAX	INTEGER
			ACCESS	read-only
			STATUS	current
	DESCRIPTION ""
			::= { mbus8F 45 }

mbus8FVIF14		OBJECT-TYPE
			SYNTAX	INTEGER
			ACCESS	read-only
			STATUS	current
	DESCRIPTION ""
			::= { mbus8F 46 }

mbus8FValue14		OBJECT-TYPE
			SYNTAX	INTEGER
			ACCESS	read-only
			STATUS	current
	DESCRIPTION ""
			::= { mbus8F 47 }

mbus8FVIF15		OBJECT-TYPE
			SYNTAX	INTEGER
			ACCESS	read-only
			STATUS	current
	DESCRIPTION ""
			::= { mbus8F 48 }

mbus8FValue15		OBJECT-TYPE
			SYNTAX	INTEGER
			ACCESS	read-only
			STATUS	current
	DESCRIPTION ""
			::= { mbus8F 49 }

mbus8FVIF16		OBJECT-TYPE
			SYNTAX	INTEGER
			ACCESS	read-only
			STATUS	current
	DESCRIPTION ""
			::= { mbus8F 50 }

mbus8FValue16		OBJECT-TYPE
			SYNTAX	INTEGER
			ACCESS	read-only
			STATUS	current
	DESCRIPTION ""
			::= { mbus8F 51 }

mbus8FVIF17		OBJECT-TYPE
			SYNTAX	INTEGER
			ACCESS	read-only
			STATUS	current
	DESCRIPTION ""
			::= { mbus8F 52 }

mbus8FValue17		OBJECT-TYPE
			SYNTAX	INTEGER
			ACCESS	read-only
			STATUS	current
	DESCRIPTION ""
			::= { mbus8F 53 }

mbus8FVIF18		OBJECT-TYPE
			SYNTAX	INTEGER
			ACCESS	read-only
			STATUS	current
	DESCRIPTION ""
			::= { mbus8F 54 }

mbus8FValue18		OBJECT-TYPE
			SYNTAX	INTEGER
			ACCESS	read-only
			STATUS	current
	DESCRIPTION ""
			::= { mbus8F 55 }

mbus8FVIF19		OBJECT-TYPE
			SYNTAX	INTEGER
			ACCESS	read-only
			STATUS	current
	DESCRIPTION ""
			::= { mbus8F 56 }

mbus8FValue19		OBJECT-TYPE
			SYNTAX	INTEGER
			ACCESS	read-only
			STATUS	current
	DESCRIPTION ""
			::= { mbus8F 57 }

mbus8FVIF1A		OBJECT-TYPE
			SYNTAX	INTEGER
			ACCESS	read-only
			STATUS	current
	DESCRIPTION ""
			::= { mbus8F 58 }

mbus8FValue1A		OBJECT-TYPE
			SYNTAX	INTEGER
			ACCESS	read-only
			STATUS	current
	DESCRIPTION ""
			::= { mbus8F 59 }

mbus8FVIF1B		OBJECT-TYPE
			SYNTAX	INTEGER
			ACCESS	read-only
			STATUS	current
	DESCRIPTION ""
			::= { mbus8F 60 }

mbus8FValue1B		OBJECT-TYPE
			SYNTAX	INTEGER
			ACCESS	read-only
			STATUS	current
	DESCRIPTION ""
			::= { mbus8F 61 }

mbus8FVIF1C		OBJECT-TYPE
			SYNTAX	INTEGER
			ACCESS	read-only
			STATUS	current
	DESCRIPTION ""
			::= { mbus8F 62 }

mbus8FValue1C		OBJECT-TYPE
			SYNTAX	INTEGER
			ACCESS	read-only
			STATUS	current
	DESCRIPTION ""
			::= { mbus8F 63 }

mbus8FVIF1D		OBJECT-TYPE
			SYNTAX	INTEGER
			ACCESS	read-only
			STATUS	current
	DESCRIPTION ""
			::= { mbus8F 64 }

mbus8FValue1D		OBJECT-TYPE
			SYNTAX	INTEGER
			ACCESS	read-only
			STATUS	current
	DESCRIPTION ""
			::= { mbus8F 65 }

mbus8FVIF1E		OBJECT-TYPE
			SYNTAX	INTEGER
			ACCESS	read-only
			STATUS	current
	DESCRIPTION ""
			::= { mbus8F 66 }

mbus8FValue1E		OBJECT-TYPE
			SYNTAX	INTEGER
			ACCESS	read-only
			STATUS	current
	DESCRIPTION ""
			::= { mbus8F 67 }

mbus8FVIF1F		OBJECT-TYPE
			SYNTAX	INTEGER
			ACCESS	read-only
			STATUS	current
	DESCRIPTION ""
			::= { mbus8F 68 }

mbus8FValue1F		OBJECT-TYPE
			SYNTAX	INTEGER
			ACCESS	read-only
			STATUS	current
	DESCRIPTION ""
			::= { mbus8F 69 }

mbus8FVIF20		OBJECT-TYPE
			SYNTAX	INTEGER
			ACCESS	read-only
			STATUS	current
	DESCRIPTION ""
			::= { mbus8F 70 }

mbus8FValue20		OBJECT-TYPE
			SYNTAX	INTEGER
			ACCESS	read-only
			STATUS	current
	DESCRIPTION ""
			::= { mbus8F 71 }

mbus8FVIF21		OBJECT-TYPE
			SYNTAX	INTEGER
			ACCESS	read-only
			STATUS	current
	DESCRIPTION ""
			::= { mbus8F 72 }

mbus8FValue21		OBJECT-TYPE
			SYNTAX	INTEGER
			ACCESS	read-only
			STATUS	current
	DESCRIPTION ""
			::= { mbus8F 73 }

mbus8FVIF22		OBJECT-TYPE
			SYNTAX	INTEGER
			ACCESS	read-only
			STATUS	current
	DESCRIPTION ""
			::= { mbus8F 74 }

mbus8FValue22		OBJECT-TYPE
			SYNTAX	INTEGER
			ACCESS	read-only
			STATUS	current
	DESCRIPTION ""
			::= { mbus8F 75 }

mbus8FVIF23		OBJECT-TYPE
			SYNTAX	INTEGER
			ACCESS	read-only
			STATUS	current
	DESCRIPTION ""
			::= { mbus8F 76 }

mbus8FValue23		OBJECT-TYPE
			SYNTAX	INTEGER
			ACCESS	read-only
			STATUS	current
	DESCRIPTION ""
			::= { mbus8F 77 }

mbus8FVIF24		OBJECT-TYPE
			SYNTAX	INTEGER
			ACCESS	read-only
			STATUS	current
	DESCRIPTION ""
			::= { mbus8F 78 }

mbus8FValue24		OBJECT-TYPE
			SYNTAX	INTEGER
			ACCESS	read-only
			STATUS	current
	DESCRIPTION ""
			::= { mbus8F 79 }

mbus8FVIF25		OBJECT-TYPE
			SYNTAX	INTEGER
			ACCESS	read-only
			STATUS	current
	DESCRIPTION ""
			::= { mbus8F 80 }

mbus8FValue25		OBJECT-TYPE
			SYNTAX	INTEGER
			ACCESS	read-only
			STATUS	current
	DESCRIPTION ""
			::= { mbus8F 81 }

mbus8FVIF26		OBJECT-TYPE
			SYNTAX	INTEGER
			ACCESS	read-only
			STATUS	current
	DESCRIPTION ""
			::= { mbus8F 82 }

mbus8FValue26		OBJECT-TYPE
			SYNTAX	INTEGER
			ACCESS	read-only
			STATUS	current
	DESCRIPTION ""
			::= { mbus8F 83 }

mbus8FVIF27		OBJECT-TYPE
			SYNTAX	INTEGER
			ACCESS	read-only
			STATUS	current
	DESCRIPTION ""
			::= { mbus8F 84 }

mbus8FValue27		OBJECT-TYPE
			SYNTAX	INTEGER
			ACCESS	read-only
			STATUS	current
	DESCRIPTION ""
			::= { mbus8F 85 }

mbus8FVIF28		OBJECT-TYPE
			SYNTAX	INTEGER
			ACCESS	read-only
			STATUS	current
	DESCRIPTION ""
			::= { mbus8F 86 }

mbus8FValue28		OBJECT-TYPE
			SYNTAX	INTEGER
			ACCESS	read-only
			STATUS	current
	DESCRIPTION ""
			::= { mbus8F 87 }

mbus8FVIF29		OBJECT-TYPE
			SYNTAX	INTEGER
			ACCESS	read-only
			STATUS	current
	DESCRIPTION ""
			::= { mbus8F 88 }

mbus8FValue29		OBJECT-TYPE
			SYNTAX	INTEGER
			ACCESS	read-only
			STATUS	current
	DESCRIPTION ""
			::= { mbus8F 89 }

mbus8FVIF2A		OBJECT-TYPE
			SYNTAX	INTEGER
			ACCESS	read-only
			STATUS	current
	DESCRIPTION ""
			::= { mbus8F 90 }

mbus8FValue2A		OBJECT-TYPE
			SYNTAX	INTEGER
			ACCESS	read-only
			STATUS	current
	DESCRIPTION ""
			::= { mbus8F 91 }

mbus8FVIF2B		OBJECT-TYPE
			SYNTAX	INTEGER
			ACCESS	read-only
			STATUS	current
	DESCRIPTION ""
			::= { mbus8F 92 }

mbus8FValue2B		OBJECT-TYPE
			SYNTAX	INTEGER
			ACCESS	read-only
			STATUS	current
	DESCRIPTION ""
			::= { mbus8F 93 }

mbus8FVIF2C		OBJECT-TYPE
			SYNTAX	INTEGER
			ACCESS	read-only
			STATUS	current
	DESCRIPTION ""
			::= { mbus8F 94 }

mbus8FValue2C		OBJECT-TYPE
			SYNTAX	INTEGER
			ACCESS	read-only
			STATUS	current
	DESCRIPTION ""
			::= { mbus8F 95 }

mbus8FVIF2D		OBJECT-TYPE
			SYNTAX	INTEGER
			ACCESS	read-only
			STATUS	current
	DESCRIPTION ""
			::= { mbus8F 96 }

mbus8FValue2D		OBJECT-TYPE
			SYNTAX	INTEGER
			ACCESS	read-only
			STATUS	current
	DESCRIPTION ""
			::= { mbus8F 97 }

mbus8FVIF2E		OBJECT-TYPE
			SYNTAX	INTEGER
			ACCESS	read-only
			STATUS	current
	DESCRIPTION ""
			::= { mbus8F 98 }

mbus8FValue2E		OBJECT-TYPE
			SYNTAX	INTEGER
			ACCESS	read-only
			STATUS	current
	DESCRIPTION ""
			::= { mbus8F 99 }

mbus8FVIF2F		OBJECT-TYPE
			SYNTAX	INTEGER
			ACCESS	read-only
			STATUS	current
	DESCRIPTION ""
			::= { mbus8F 100 }

mbus8FValue2F		OBJECT-TYPE
			SYNTAX	INTEGER
			ACCESS	read-only
			STATUS	current
	DESCRIPTION ""
			::= { mbus8F 101 }

mbus90			OBJECT IDENTIFIER ::= { mbus 144 }

mbus90IdNumber		OBJECT-TYPE
			SYNTAX	Gauge
			ACCESS	read-only
			STATUS	current
	DESCRIPTION ""
			::= { mbus90 1 }

mbus90Manufacturer	OBJECT-TYPE
			SYNTAX	Gauge
			ACCESS	read-only
			STATUS	current
	DESCRIPTION ""
			::= { mbus90 2 }

mbus90Version		OBJECT-TYPE
			SYNTAX	Gauge
			ACCESS	read-only
			STATUS	current
	DESCRIPTION ""
			::= { mbus90 3 }

mbus90Medium		OBJECT-TYPE
			SYNTAX	Gauge
			ACCESS	read-only
			STATUS	current
	DESCRIPTION ""
			::= { mbus90 4 }

mbus90Status		OBJECT-TYPE
			SYNTAX	Gauge
			ACCESS	read-only
			STATUS	current
	DESCRIPTION ""
			::= { mbus90 5 }

mbus90VIF00		OBJECT-TYPE
			SYNTAX	INTEGER
			ACCESS	read-only
			STATUS	current
	DESCRIPTION ""
			::= { mbus90 6 }

mbus90Value00		OBJECT-TYPE
			SYNTAX	INTEGER
			ACCESS	read-only
			STATUS	current
	DESCRIPTION ""
			::= { mbus90 7 }

mbus90VIF01		OBJECT-TYPE
			SYNTAX	INTEGER
			ACCESS	read-only
			STATUS	current
	DESCRIPTION ""
			::= { mbus90 8 }

mbus90Value01		OBJECT-TYPE
			SYNTAX	INTEGER
			ACCESS	read-only
			STATUS	current
	DESCRIPTION ""
			::= { mbus90 9 }

mbus90VIF02		OBJECT-TYPE
			SYNTAX	INTEGER
			ACCESS	read-only
			STATUS	current
	DESCRIPTION ""
			::= { mbus90 10 }

mbus90Value02		OBJECT-TYPE
			SYNTAX	INTEGER
			ACCESS	read-only
			STATUS	current
	DESCRIPTION ""
			::= { mbus90 11 }

mbus90VIF03		OBJECT-TYPE
			SYNTAX	INTEGER
			ACCESS	read-only
			STATUS	current
	DESCRIPTION ""
			::= { mbus90 12 }

mbus90Value03		OBJECT-TYPE
			SYNTAX	INTEGER
			ACCESS	read-only
			STATUS	current
	DESCRIPTION ""
			::= { mbus90 13 }

mbus90VIF04		OBJECT-TYPE
			SYNTAX	INTEGER
			ACCESS	read-only
			STATUS	current
	DESCRIPTION ""
			::= { mbus90 14 }

mbus90Value04		OBJECT-TYPE
			SYNTAX	INTEGER
			ACCESS	read-only
			STATUS	current
	DESCRIPTION ""
			::= { mbus90 15 }

mbus90VIF05		OBJECT-TYPE
			SYNTAX	INTEGER
			ACCESS	read-only
			STATUS	current
	DESCRIPTION ""
			::= { mbus90 16 }

mbus90Value05		OBJECT-TYPE
			SYNTAX	INTEGER
			ACCESS	read-only
			STATUS	current
	DESCRIPTION ""
			::= { mbus90 17 }

mbus90VIF06		OBJECT-TYPE
			SYNTAX	INTEGER
			ACCESS	read-only
			STATUS	current
	DESCRIPTION ""
			::= { mbus90 18 }

mbus90Value06		OBJECT-TYPE
			SYNTAX	INTEGER
			ACCESS	read-only
			STATUS	current
	DESCRIPTION ""
			::= { mbus90 19 }

mbus90VIF07		OBJECT-TYPE
			SYNTAX	INTEGER
			ACCESS	read-only
			STATUS	current
	DESCRIPTION ""
			::= { mbus90 20 }

mbus90Value07		OBJECT-TYPE
			SYNTAX	INTEGER
			ACCESS	read-only
			STATUS	current
	DESCRIPTION ""
			::= { mbus90 21 }

mbus90VIF08		OBJECT-TYPE
			SYNTAX	INTEGER
			ACCESS	read-only
			STATUS	current
	DESCRIPTION ""
			::= { mbus90 22 }

mbus90Value08		OBJECT-TYPE
			SYNTAX	INTEGER
			ACCESS	read-only
			STATUS	current
	DESCRIPTION ""
			::= { mbus90 23 }

mbus90VIF09		OBJECT-TYPE
			SYNTAX	INTEGER
			ACCESS	read-only
			STATUS	current
	DESCRIPTION ""
			::= { mbus90 24 }

mbus90Value09		OBJECT-TYPE
			SYNTAX	INTEGER
			ACCESS	read-only
			STATUS	current
	DESCRIPTION ""
			::= { mbus90 25 }

mbus90VIF0A		OBJECT-TYPE
			SYNTAX	INTEGER
			ACCESS	read-only
			STATUS	current
	DESCRIPTION ""
			::= { mbus90 26 }

mbus90Value0A		OBJECT-TYPE
			SYNTAX	INTEGER
			ACCESS	read-only
			STATUS	current
	DESCRIPTION ""
			::= { mbus90 27 }

mbus90VIF0B		OBJECT-TYPE
			SYNTAX	INTEGER
			ACCESS	read-only
			STATUS	current
	DESCRIPTION ""
			::= { mbus90 28 }

mbus90Value0B		OBJECT-TYPE
			SYNTAX	INTEGER
			ACCESS	read-only
			STATUS	current
	DESCRIPTION ""
			::= { mbus90 29 }

mbus90VIF0C		OBJECT-TYPE
			SYNTAX	INTEGER
			ACCESS	read-only
			STATUS	current
	DESCRIPTION ""
			::= { mbus90 30 }

mbus90Value0C		OBJECT-TYPE
			SYNTAX	INTEGER
			ACCESS	read-only
			STATUS	current
	DESCRIPTION ""
			::= { mbus90 31 }

mbus90VIF0D		OBJECT-TYPE
			SYNTAX	INTEGER
			ACCESS	read-only
			STATUS	current
	DESCRIPTION ""
			::= { mbus90 32 }

mbus90Value0D		OBJECT-TYPE
			SYNTAX	INTEGER
			ACCESS	read-only
			STATUS	current
	DESCRIPTION ""
			::= { mbus90 33 }

mbus90VIF0E		OBJECT-TYPE
			SYNTAX	INTEGER
			ACCESS	read-only
			STATUS	current
	DESCRIPTION ""
			::= { mbus90 34 }

mbus90Value0E		OBJECT-TYPE
			SYNTAX	INTEGER
			ACCESS	read-only
			STATUS	current
	DESCRIPTION ""
			::= { mbus90 35 }

mbus90VIF0F		OBJECT-TYPE
			SYNTAX	INTEGER
			ACCESS	read-only
			STATUS	current
	DESCRIPTION ""
			::= { mbus90 36 }

mbus90Value0F		OBJECT-TYPE
			SYNTAX	INTEGER
			ACCESS	read-only
			STATUS	current
	DESCRIPTION ""
			::= { mbus90 37 }

mbus90VIF10		OBJECT-TYPE
			SYNTAX	INTEGER
			ACCESS	read-only
			STATUS	current
	DESCRIPTION ""
			::= { mbus90 38 }

mbus90Value10		OBJECT-TYPE
			SYNTAX	INTEGER
			ACCESS	read-only
			STATUS	current
	DESCRIPTION ""
			::= { mbus90 39 }

mbus90VIF11		OBJECT-TYPE
			SYNTAX	INTEGER
			ACCESS	read-only
			STATUS	current
	DESCRIPTION ""
			::= { mbus90 40 }

mbus90Value11		OBJECT-TYPE
			SYNTAX	INTEGER
			ACCESS	read-only
			STATUS	current
	DESCRIPTION ""
			::= { mbus90 41 }

mbus90VIF12		OBJECT-TYPE
			SYNTAX	INTEGER
			ACCESS	read-only
			STATUS	current
	DESCRIPTION ""
			::= { mbus90 42 }

mbus90Value12		OBJECT-TYPE
			SYNTAX	INTEGER
			ACCESS	read-only
			STATUS	current
	DESCRIPTION ""
			::= { mbus90 43 }

mbus90VIF13		OBJECT-TYPE
			SYNTAX	INTEGER
			ACCESS	read-only
			STATUS	current
	DESCRIPTION ""
			::= { mbus90 44 }

mbus90Value13		OBJECT-TYPE
			SYNTAX	INTEGER
			ACCESS	read-only
			STATUS	current
	DESCRIPTION ""
			::= { mbus90 45 }

mbus90VIF14		OBJECT-TYPE
			SYNTAX	INTEGER
			ACCESS	read-only
			STATUS	current
	DESCRIPTION ""
			::= { mbus90 46 }

mbus90Value14		OBJECT-TYPE
			SYNTAX	INTEGER
			ACCESS	read-only
			STATUS	current
	DESCRIPTION ""
			::= { mbus90 47 }

mbus90VIF15		OBJECT-TYPE
			SYNTAX	INTEGER
			ACCESS	read-only
			STATUS	current
	DESCRIPTION ""
			::= { mbus90 48 }

mbus90Value15		OBJECT-TYPE
			SYNTAX	INTEGER
			ACCESS	read-only
			STATUS	current
	DESCRIPTION ""
			::= { mbus90 49 }

mbus90VIF16		OBJECT-TYPE
			SYNTAX	INTEGER
			ACCESS	read-only
			STATUS	current
	DESCRIPTION ""
			::= { mbus90 50 }

mbus90Value16		OBJECT-TYPE
			SYNTAX	INTEGER
			ACCESS	read-only
			STATUS	current
	DESCRIPTION ""
			::= { mbus90 51 }

mbus90VIF17		OBJECT-TYPE
			SYNTAX	INTEGER
			ACCESS	read-only
			STATUS	current
	DESCRIPTION ""
			::= { mbus90 52 }

mbus90Value17		OBJECT-TYPE
			SYNTAX	INTEGER
			ACCESS	read-only
			STATUS	current
	DESCRIPTION ""
			::= { mbus90 53 }

mbus90VIF18		OBJECT-TYPE
			SYNTAX	INTEGER
			ACCESS	read-only
			STATUS	current
	DESCRIPTION ""
			::= { mbus90 54 }

mbus90Value18		OBJECT-TYPE
			SYNTAX	INTEGER
			ACCESS	read-only
			STATUS	current
	DESCRIPTION ""
			::= { mbus90 55 }

mbus90VIF19		OBJECT-TYPE
			SYNTAX	INTEGER
			ACCESS	read-only
			STATUS	current
	DESCRIPTION ""
			::= { mbus90 56 }

mbus90Value19		OBJECT-TYPE
			SYNTAX	INTEGER
			ACCESS	read-only
			STATUS	current
	DESCRIPTION ""
			::= { mbus90 57 }

mbus90VIF1A		OBJECT-TYPE
			SYNTAX	INTEGER
			ACCESS	read-only
			STATUS	current
	DESCRIPTION ""
			::= { mbus90 58 }

mbus90Value1A		OBJECT-TYPE
			SYNTAX	INTEGER
			ACCESS	read-only
			STATUS	current
	DESCRIPTION ""
			::= { mbus90 59 }

mbus90VIF1B		OBJECT-TYPE
			SYNTAX	INTEGER
			ACCESS	read-only
			STATUS	current
	DESCRIPTION ""
			::= { mbus90 60 }

mbus90Value1B		OBJECT-TYPE
			SYNTAX	INTEGER
			ACCESS	read-only
			STATUS	current
	DESCRIPTION ""
			::= { mbus90 61 }

mbus90VIF1C		OBJECT-TYPE
			SYNTAX	INTEGER
			ACCESS	read-only
			STATUS	current
	DESCRIPTION ""
			::= { mbus90 62 }

mbus90Value1C		OBJECT-TYPE
			SYNTAX	INTEGER
			ACCESS	read-only
			STATUS	current
	DESCRIPTION ""
			::= { mbus90 63 }

mbus90VIF1D		OBJECT-TYPE
			SYNTAX	INTEGER
			ACCESS	read-only
			STATUS	current
	DESCRIPTION ""
			::= { mbus90 64 }

mbus90Value1D		OBJECT-TYPE
			SYNTAX	INTEGER
			ACCESS	read-only
			STATUS	current
	DESCRIPTION ""
			::= { mbus90 65 }

mbus90VIF1E		OBJECT-TYPE
			SYNTAX	INTEGER
			ACCESS	read-only
			STATUS	current
	DESCRIPTION ""
			::= { mbus90 66 }

mbus90Value1E		OBJECT-TYPE
			SYNTAX	INTEGER
			ACCESS	read-only
			STATUS	current
	DESCRIPTION ""
			::= { mbus90 67 }

mbus90VIF1F		OBJECT-TYPE
			SYNTAX	INTEGER
			ACCESS	read-only
			STATUS	current
	DESCRIPTION ""
			::= { mbus90 68 }

mbus90Value1F		OBJECT-TYPE
			SYNTAX	INTEGER
			ACCESS	read-only
			STATUS	current
	DESCRIPTION ""
			::= { mbus90 69 }

mbus90VIF20		OBJECT-TYPE
			SYNTAX	INTEGER
			ACCESS	read-only
			STATUS	current
	DESCRIPTION ""
			::= { mbus90 70 }

mbus90Value20		OBJECT-TYPE
			SYNTAX	INTEGER
			ACCESS	read-only
			STATUS	current
	DESCRIPTION ""
			::= { mbus90 71 }

mbus90VIF21		OBJECT-TYPE
			SYNTAX	INTEGER
			ACCESS	read-only
			STATUS	current
	DESCRIPTION ""
			::= { mbus90 72 }

mbus90Value21		OBJECT-TYPE
			SYNTAX	INTEGER
			ACCESS	read-only
			STATUS	current
	DESCRIPTION ""
			::= { mbus90 73 }

mbus90VIF22		OBJECT-TYPE
			SYNTAX	INTEGER
			ACCESS	read-only
			STATUS	current
	DESCRIPTION ""
			::= { mbus90 74 }

mbus90Value22		OBJECT-TYPE
			SYNTAX	INTEGER
			ACCESS	read-only
			STATUS	current
	DESCRIPTION ""
			::= { mbus90 75 }

mbus90VIF23		OBJECT-TYPE
			SYNTAX	INTEGER
			ACCESS	read-only
			STATUS	current
	DESCRIPTION ""
			::= { mbus90 76 }

mbus90Value23		OBJECT-TYPE
			SYNTAX	INTEGER
			ACCESS	read-only
			STATUS	current
	DESCRIPTION ""
			::= { mbus90 77 }

mbus90VIF24		OBJECT-TYPE
			SYNTAX	INTEGER
			ACCESS	read-only
			STATUS	current
	DESCRIPTION ""
			::= { mbus90 78 }

mbus90Value24		OBJECT-TYPE
			SYNTAX	INTEGER
			ACCESS	read-only
			STATUS	current
	DESCRIPTION ""
			::= { mbus90 79 }

mbus90VIF25		OBJECT-TYPE
			SYNTAX	INTEGER
			ACCESS	read-only
			STATUS	current
	DESCRIPTION ""
			::= { mbus90 80 }

mbus90Value25		OBJECT-TYPE
			SYNTAX	INTEGER
			ACCESS	read-only
			STATUS	current
	DESCRIPTION ""
			::= { mbus90 81 }

mbus90VIF26		OBJECT-TYPE
			SYNTAX	INTEGER
			ACCESS	read-only
			STATUS	current
	DESCRIPTION ""
			::= { mbus90 82 }

mbus90Value26		OBJECT-TYPE
			SYNTAX	INTEGER
			ACCESS	read-only
			STATUS	current
	DESCRIPTION ""
			::= { mbus90 83 }

mbus90VIF27		OBJECT-TYPE
			SYNTAX	INTEGER
			ACCESS	read-only
			STATUS	current
	DESCRIPTION ""
			::= { mbus90 84 }

mbus90Value27		OBJECT-TYPE
			SYNTAX	INTEGER
			ACCESS	read-only
			STATUS	current
	DESCRIPTION ""
			::= { mbus90 85 }

mbus90VIF28		OBJECT-TYPE
			SYNTAX	INTEGER
			ACCESS	read-only
			STATUS	current
	DESCRIPTION ""
			::= { mbus90 86 }

mbus90Value28		OBJECT-TYPE
			SYNTAX	INTEGER
			ACCESS	read-only
			STATUS	current
	DESCRIPTION ""
			::= { mbus90 87 }

mbus90VIF29		OBJECT-TYPE
			SYNTAX	INTEGER
			ACCESS	read-only
			STATUS	current
	DESCRIPTION ""
			::= { mbus90 88 }

mbus90Value29		OBJECT-TYPE
			SYNTAX	INTEGER
			ACCESS	read-only
			STATUS	current
	DESCRIPTION ""
			::= { mbus90 89 }

mbus90VIF2A		OBJECT-TYPE
			SYNTAX	INTEGER
			ACCESS	read-only
			STATUS	current
	DESCRIPTION ""
			::= { mbus90 90 }

mbus90Value2A		OBJECT-TYPE
			SYNTAX	INTEGER
			ACCESS	read-only
			STATUS	current
	DESCRIPTION ""
			::= { mbus90 91 }

mbus90VIF2B		OBJECT-TYPE
			SYNTAX	INTEGER
			ACCESS	read-only
			STATUS	current
	DESCRIPTION ""
			::= { mbus90 92 }

mbus90Value2B		OBJECT-TYPE
			SYNTAX	INTEGER
			ACCESS	read-only
			STATUS	current
	DESCRIPTION ""
			::= { mbus90 93 }

mbus90VIF2C		OBJECT-TYPE
			SYNTAX	INTEGER
			ACCESS	read-only
			STATUS	current
	DESCRIPTION ""
			::= { mbus90 94 }

mbus90Value2C		OBJECT-TYPE
			SYNTAX	INTEGER
			ACCESS	read-only
			STATUS	current
	DESCRIPTION ""
			::= { mbus90 95 }

mbus90VIF2D		OBJECT-TYPE
			SYNTAX	INTEGER
			ACCESS	read-only
			STATUS	current
	DESCRIPTION ""
			::= { mbus90 96 }

mbus90Value2D		OBJECT-TYPE
			SYNTAX	INTEGER
			ACCESS	read-only
			STATUS	current
	DESCRIPTION ""
			::= { mbus90 97 }

mbus90VIF2E		OBJECT-TYPE
			SYNTAX	INTEGER
			ACCESS	read-only
			STATUS	current
	DESCRIPTION ""
			::= { mbus90 98 }

mbus90Value2E		OBJECT-TYPE
			SYNTAX	INTEGER
			ACCESS	read-only
			STATUS	current
	DESCRIPTION ""
			::= { mbus90 99 }

mbus90VIF2F		OBJECT-TYPE
			SYNTAX	INTEGER
			ACCESS	read-only
			STATUS	current
	DESCRIPTION ""
			::= { mbus90 100 }

mbus90Value2F		OBJECT-TYPE
			SYNTAX	INTEGER
			ACCESS	read-only
			STATUS	current
	DESCRIPTION ""
			::= { mbus90 101 }

mbus91			OBJECT IDENTIFIER ::= { mbus 145 }

mbus91IdNumber		OBJECT-TYPE
			SYNTAX	Gauge
			ACCESS	read-only
			STATUS	current
	DESCRIPTION ""
			::= { mbus91 1 }

mbus91Manufacturer	OBJECT-TYPE
			SYNTAX	Gauge
			ACCESS	read-only
			STATUS	current
	DESCRIPTION ""
			::= { mbus91 2 }

mbus91Version		OBJECT-TYPE
			SYNTAX	Gauge
			ACCESS	read-only
			STATUS	current
	DESCRIPTION ""
			::= { mbus91 3 }

mbus91Medium		OBJECT-TYPE
			SYNTAX	Gauge
			ACCESS	read-only
			STATUS	current
	DESCRIPTION ""
			::= { mbus91 4 }

mbus91Status		OBJECT-TYPE
			SYNTAX	Gauge
			ACCESS	read-only
			STATUS	current
	DESCRIPTION ""
			::= { mbus91 5 }

mbus91VIF00		OBJECT-TYPE
			SYNTAX	INTEGER
			ACCESS	read-only
			STATUS	current
	DESCRIPTION ""
			::= { mbus91 6 }

mbus91Value00		OBJECT-TYPE
			SYNTAX	INTEGER
			ACCESS	read-only
			STATUS	current
	DESCRIPTION ""
			::= { mbus91 7 }

mbus91VIF01		OBJECT-TYPE
			SYNTAX	INTEGER
			ACCESS	read-only
			STATUS	current
	DESCRIPTION ""
			::= { mbus91 8 }

mbus91Value01		OBJECT-TYPE
			SYNTAX	INTEGER
			ACCESS	read-only
			STATUS	current
	DESCRIPTION ""
			::= { mbus91 9 }

mbus91VIF02		OBJECT-TYPE
			SYNTAX	INTEGER
			ACCESS	read-only
			STATUS	current
	DESCRIPTION ""
			::= { mbus91 10 }

mbus91Value02		OBJECT-TYPE
			SYNTAX	INTEGER
			ACCESS	read-only
			STATUS	current
	DESCRIPTION ""
			::= { mbus91 11 }

mbus91VIF03		OBJECT-TYPE
			SYNTAX	INTEGER
			ACCESS	read-only
			STATUS	current
	DESCRIPTION ""
			::= { mbus91 12 }

mbus91Value03		OBJECT-TYPE
			SYNTAX	INTEGER
			ACCESS	read-only
			STATUS	current
	DESCRIPTION ""
			::= { mbus91 13 }

mbus91VIF04		OBJECT-TYPE
			SYNTAX	INTEGER
			ACCESS	read-only
			STATUS	current
	DESCRIPTION ""
			::= { mbus91 14 }

mbus91Value04		OBJECT-TYPE
			SYNTAX	INTEGER
			ACCESS	read-only
			STATUS	current
	DESCRIPTION ""
			::= { mbus91 15 }

mbus91VIF05		OBJECT-TYPE
			SYNTAX	INTEGER
			ACCESS	read-only
			STATUS	current
	DESCRIPTION ""
			::= { mbus91 16 }

mbus91Value05		OBJECT-TYPE
			SYNTAX	INTEGER
			ACCESS	read-only
			STATUS	current
	DESCRIPTION ""
			::= { mbus91 17 }

mbus91VIF06		OBJECT-TYPE
			SYNTAX	INTEGER
			ACCESS	read-only
			STATUS	current
	DESCRIPTION ""
			::= { mbus91 18 }

mbus91Value06		OBJECT-TYPE
			SYNTAX	INTEGER
			ACCESS	read-only
			STATUS	current
	DESCRIPTION ""
			::= { mbus91 19 }

mbus91VIF07		OBJECT-TYPE
			SYNTAX	INTEGER
			ACCESS	read-only
			STATUS	current
	DESCRIPTION ""
			::= { mbus91 20 }

mbus91Value07		OBJECT-TYPE
			SYNTAX	INTEGER
			ACCESS	read-only
			STATUS	current
	DESCRIPTION ""
			::= { mbus91 21 }

mbus91VIF08		OBJECT-TYPE
			SYNTAX	INTEGER
			ACCESS	read-only
			STATUS	current
	DESCRIPTION ""
			::= { mbus91 22 }

mbus91Value08		OBJECT-TYPE
			SYNTAX	INTEGER
			ACCESS	read-only
			STATUS	current
	DESCRIPTION ""
			::= { mbus91 23 }

mbus91VIF09		OBJECT-TYPE
			SYNTAX	INTEGER
			ACCESS	read-only
			STATUS	current
	DESCRIPTION ""
			::= { mbus91 24 }

mbus91Value09		OBJECT-TYPE
			SYNTAX	INTEGER
			ACCESS	read-only
			STATUS	current
	DESCRIPTION ""
			::= { mbus91 25 }

mbus91VIF0A		OBJECT-TYPE
			SYNTAX	INTEGER
			ACCESS	read-only
			STATUS	current
	DESCRIPTION ""
			::= { mbus91 26 }

mbus91Value0A		OBJECT-TYPE
			SYNTAX	INTEGER
			ACCESS	read-only
			STATUS	current
	DESCRIPTION ""
			::= { mbus91 27 }

mbus91VIF0B		OBJECT-TYPE
			SYNTAX	INTEGER
			ACCESS	read-only
			STATUS	current
	DESCRIPTION ""
			::= { mbus91 28 }

mbus91Value0B		OBJECT-TYPE
			SYNTAX	INTEGER
			ACCESS	read-only
			STATUS	current
	DESCRIPTION ""
			::= { mbus91 29 }

mbus91VIF0C		OBJECT-TYPE
			SYNTAX	INTEGER
			ACCESS	read-only
			STATUS	current
	DESCRIPTION ""
			::= { mbus91 30 }

mbus91Value0C		OBJECT-TYPE
			SYNTAX	INTEGER
			ACCESS	read-only
			STATUS	current
	DESCRIPTION ""
			::= { mbus91 31 }

mbus91VIF0D		OBJECT-TYPE
			SYNTAX	INTEGER
			ACCESS	read-only
			STATUS	current
	DESCRIPTION ""
			::= { mbus91 32 }

mbus91Value0D		OBJECT-TYPE
			SYNTAX	INTEGER
			ACCESS	read-only
			STATUS	current
	DESCRIPTION ""
			::= { mbus91 33 }

mbus91VIF0E		OBJECT-TYPE
			SYNTAX	INTEGER
			ACCESS	read-only
			STATUS	current
	DESCRIPTION ""
			::= { mbus91 34 }

mbus91Value0E		OBJECT-TYPE
			SYNTAX	INTEGER
			ACCESS	read-only
			STATUS	current
	DESCRIPTION ""
			::= { mbus91 35 }

mbus91VIF0F		OBJECT-TYPE
			SYNTAX	INTEGER
			ACCESS	read-only
			STATUS	current
	DESCRIPTION ""
			::= { mbus91 36 }

mbus91Value0F		OBJECT-TYPE
			SYNTAX	INTEGER
			ACCESS	read-only
			STATUS	current
	DESCRIPTION ""
			::= { mbus91 37 }

mbus91VIF10		OBJECT-TYPE
			SYNTAX	INTEGER
			ACCESS	read-only
			STATUS	current
	DESCRIPTION ""
			::= { mbus91 38 }

mbus91Value10		OBJECT-TYPE
			SYNTAX	INTEGER
			ACCESS	read-only
			STATUS	current
	DESCRIPTION ""
			::= { mbus91 39 }

mbus91VIF11		OBJECT-TYPE
			SYNTAX	INTEGER
			ACCESS	read-only
			STATUS	current
	DESCRIPTION ""
			::= { mbus91 40 }

mbus91Value11		OBJECT-TYPE
			SYNTAX	INTEGER
			ACCESS	read-only
			STATUS	current
	DESCRIPTION ""
			::= { mbus91 41 }

mbus91VIF12		OBJECT-TYPE
			SYNTAX	INTEGER
			ACCESS	read-only
			STATUS	current
	DESCRIPTION ""
			::= { mbus91 42 }

mbus91Value12		OBJECT-TYPE
			SYNTAX	INTEGER
			ACCESS	read-only
			STATUS	current
	DESCRIPTION ""
			::= { mbus91 43 }

mbus91VIF13		OBJECT-TYPE
			SYNTAX	INTEGER
			ACCESS	read-only
			STATUS	current
	DESCRIPTION ""
			::= { mbus91 44 }

mbus91Value13		OBJECT-TYPE
			SYNTAX	INTEGER
			ACCESS	read-only
			STATUS	current
	DESCRIPTION ""
			::= { mbus91 45 }

mbus91VIF14		OBJECT-TYPE
			SYNTAX	INTEGER
			ACCESS	read-only
			STATUS	current
	DESCRIPTION ""
			::= { mbus91 46 }

mbus91Value14		OBJECT-TYPE
			SYNTAX	INTEGER
			ACCESS	read-only
			STATUS	current
	DESCRIPTION ""
			::= { mbus91 47 }

mbus91VIF15		OBJECT-TYPE
			SYNTAX	INTEGER
			ACCESS	read-only
			STATUS	current
	DESCRIPTION ""
			::= { mbus91 48 }

mbus91Value15		OBJECT-TYPE
			SYNTAX	INTEGER
			ACCESS	read-only
			STATUS	current
	DESCRIPTION ""
			::= { mbus91 49 }

mbus91VIF16		OBJECT-TYPE
			SYNTAX	INTEGER
			ACCESS	read-only
			STATUS	current
	DESCRIPTION ""
			::= { mbus91 50 }

mbus91Value16		OBJECT-TYPE
			SYNTAX	INTEGER
			ACCESS	read-only
			STATUS	current
	DESCRIPTION ""
			::= { mbus91 51 }

mbus91VIF17		OBJECT-TYPE
			SYNTAX	INTEGER
			ACCESS	read-only
			STATUS	current
	DESCRIPTION ""
			::= { mbus91 52 }

mbus91Value17		OBJECT-TYPE
			SYNTAX	INTEGER
			ACCESS	read-only
			STATUS	current
	DESCRIPTION ""
			::= { mbus91 53 }

mbus91VIF18		OBJECT-TYPE
			SYNTAX	INTEGER
			ACCESS	read-only
			STATUS	current
	DESCRIPTION ""
			::= { mbus91 54 }

mbus91Value18		OBJECT-TYPE
			SYNTAX	INTEGER
			ACCESS	read-only
			STATUS	current
	DESCRIPTION ""
			::= { mbus91 55 }

mbus91VIF19		OBJECT-TYPE
			SYNTAX	INTEGER
			ACCESS	read-only
			STATUS	current
	DESCRIPTION ""
			::= { mbus91 56 }

mbus91Value19		OBJECT-TYPE
			SYNTAX	INTEGER
			ACCESS	read-only
			STATUS	current
	DESCRIPTION ""
			::= { mbus91 57 }

mbus91VIF1A		OBJECT-TYPE
			SYNTAX	INTEGER
			ACCESS	read-only
			STATUS	current
	DESCRIPTION ""
			::= { mbus91 58 }

mbus91Value1A		OBJECT-TYPE
			SYNTAX	INTEGER
			ACCESS	read-only
			STATUS	current
	DESCRIPTION ""
			::= { mbus91 59 }

mbus91VIF1B		OBJECT-TYPE
			SYNTAX	INTEGER
			ACCESS	read-only
			STATUS	current
	DESCRIPTION ""
			::= { mbus91 60 }

mbus91Value1B		OBJECT-TYPE
			SYNTAX	INTEGER
			ACCESS	read-only
			STATUS	current
	DESCRIPTION ""
			::= { mbus91 61 }

mbus91VIF1C		OBJECT-TYPE
			SYNTAX	INTEGER
			ACCESS	read-only
			STATUS	current
	DESCRIPTION ""
			::= { mbus91 62 }

mbus91Value1C		OBJECT-TYPE
			SYNTAX	INTEGER
			ACCESS	read-only
			STATUS	current
	DESCRIPTION ""
			::= { mbus91 63 }

mbus91VIF1D		OBJECT-TYPE
			SYNTAX	INTEGER
			ACCESS	read-only
			STATUS	current
	DESCRIPTION ""
			::= { mbus91 64 }

mbus91Value1D		OBJECT-TYPE
			SYNTAX	INTEGER
			ACCESS	read-only
			STATUS	current
	DESCRIPTION ""
			::= { mbus91 65 }

mbus91VIF1E		OBJECT-TYPE
			SYNTAX	INTEGER
			ACCESS	read-only
			STATUS	current
	DESCRIPTION ""
			::= { mbus91 66 }

mbus91Value1E		OBJECT-TYPE
			SYNTAX	INTEGER
			ACCESS	read-only
			STATUS	current
	DESCRIPTION ""
			::= { mbus91 67 }

mbus91VIF1F		OBJECT-TYPE
			SYNTAX	INTEGER
			ACCESS	read-only
			STATUS	current
	DESCRIPTION ""
			::= { mbus91 68 }

mbus91Value1F		OBJECT-TYPE
			SYNTAX	INTEGER
			ACCESS	read-only
			STATUS	current
	DESCRIPTION ""
			::= { mbus91 69 }

mbus91VIF20		OBJECT-TYPE
			SYNTAX	INTEGER
			ACCESS	read-only
			STATUS	current
	DESCRIPTION ""
			::= { mbus91 70 }

mbus91Value20		OBJECT-TYPE
			SYNTAX	INTEGER
			ACCESS	read-only
			STATUS	current
	DESCRIPTION ""
			::= { mbus91 71 }

mbus91VIF21		OBJECT-TYPE
			SYNTAX	INTEGER
			ACCESS	read-only
			STATUS	current
	DESCRIPTION ""
			::= { mbus91 72 }

mbus91Value21		OBJECT-TYPE
			SYNTAX	INTEGER
			ACCESS	read-only
			STATUS	current
	DESCRIPTION ""
			::= { mbus91 73 }

mbus91VIF22		OBJECT-TYPE
			SYNTAX	INTEGER
			ACCESS	read-only
			STATUS	current
	DESCRIPTION ""
			::= { mbus91 74 }

mbus91Value22		OBJECT-TYPE
			SYNTAX	INTEGER
			ACCESS	read-only
			STATUS	current
	DESCRIPTION ""
			::= { mbus91 75 }

mbus91VIF23		OBJECT-TYPE
			SYNTAX	INTEGER
			ACCESS	read-only
			STATUS	current
	DESCRIPTION ""
			::= { mbus91 76 }

mbus91Value23		OBJECT-TYPE
			SYNTAX	INTEGER
			ACCESS	read-only
			STATUS	current
	DESCRIPTION ""
			::= { mbus91 77 }

mbus91VIF24		OBJECT-TYPE
			SYNTAX	INTEGER
			ACCESS	read-only
			STATUS	current
	DESCRIPTION ""
			::= { mbus91 78 }

mbus91Value24		OBJECT-TYPE
			SYNTAX	INTEGER
			ACCESS	read-only
			STATUS	current
	DESCRIPTION ""
			::= { mbus91 79 }

mbus91VIF25		OBJECT-TYPE
			SYNTAX	INTEGER
			ACCESS	read-only
			STATUS	current
	DESCRIPTION ""
			::= { mbus91 80 }

mbus91Value25		OBJECT-TYPE
			SYNTAX	INTEGER
			ACCESS	read-only
			STATUS	current
	DESCRIPTION ""
			::= { mbus91 81 }

mbus91VIF26		OBJECT-TYPE
			SYNTAX	INTEGER
			ACCESS	read-only
			STATUS	current
	DESCRIPTION ""
			::= { mbus91 82 }

mbus91Value26		OBJECT-TYPE
			SYNTAX	INTEGER
			ACCESS	read-only
			STATUS	current
	DESCRIPTION ""
			::= { mbus91 83 }

mbus91VIF27		OBJECT-TYPE
			SYNTAX	INTEGER
			ACCESS	read-only
			STATUS	current
	DESCRIPTION ""
			::= { mbus91 84 }

mbus91Value27		OBJECT-TYPE
			SYNTAX	INTEGER
			ACCESS	read-only
			STATUS	current
	DESCRIPTION ""
			::= { mbus91 85 }

mbus91VIF28		OBJECT-TYPE
			SYNTAX	INTEGER
			ACCESS	read-only
			STATUS	current
	DESCRIPTION ""
			::= { mbus91 86 }

mbus91Value28		OBJECT-TYPE
			SYNTAX	INTEGER
			ACCESS	read-only
			STATUS	current
	DESCRIPTION ""
			::= { mbus91 87 }

mbus91VIF29		OBJECT-TYPE
			SYNTAX	INTEGER
			ACCESS	read-only
			STATUS	current
	DESCRIPTION ""
			::= { mbus91 88 }

mbus91Value29		OBJECT-TYPE
			SYNTAX	INTEGER
			ACCESS	read-only
			STATUS	current
	DESCRIPTION ""
			::= { mbus91 89 }

mbus91VIF2A		OBJECT-TYPE
			SYNTAX	INTEGER
			ACCESS	read-only
			STATUS	current
	DESCRIPTION ""
			::= { mbus91 90 }

mbus91Value2A		OBJECT-TYPE
			SYNTAX	INTEGER
			ACCESS	read-only
			STATUS	current
	DESCRIPTION ""
			::= { mbus91 91 }

mbus91VIF2B		OBJECT-TYPE
			SYNTAX	INTEGER
			ACCESS	read-only
			STATUS	current
	DESCRIPTION ""
			::= { mbus91 92 }

mbus91Value2B		OBJECT-TYPE
			SYNTAX	INTEGER
			ACCESS	read-only
			STATUS	current
	DESCRIPTION ""
			::= { mbus91 93 }

mbus91VIF2C		OBJECT-TYPE
			SYNTAX	INTEGER
			ACCESS	read-only
			STATUS	current
	DESCRIPTION ""
			::= { mbus91 94 }

mbus91Value2C		OBJECT-TYPE
			SYNTAX	INTEGER
			ACCESS	read-only
			STATUS	current
	DESCRIPTION ""
			::= { mbus91 95 }

mbus91VIF2D		OBJECT-TYPE
			SYNTAX	INTEGER
			ACCESS	read-only
			STATUS	current
	DESCRIPTION ""
			::= { mbus91 96 }

mbus91Value2D		OBJECT-TYPE
			SYNTAX	INTEGER
			ACCESS	read-only
			STATUS	current
	DESCRIPTION ""
			::= { mbus91 97 }

mbus91VIF2E		OBJECT-TYPE
			SYNTAX	INTEGER
			ACCESS	read-only
			STATUS	current
	DESCRIPTION ""
			::= { mbus91 98 }

mbus91Value2E		OBJECT-TYPE
			SYNTAX	INTEGER
			ACCESS	read-only
			STATUS	current
	DESCRIPTION ""
			::= { mbus91 99 }

mbus91VIF2F		OBJECT-TYPE
			SYNTAX	INTEGER
			ACCESS	read-only
			STATUS	current
	DESCRIPTION ""
			::= { mbus91 100 }

mbus91Value2F		OBJECT-TYPE
			SYNTAX	INTEGER
			ACCESS	read-only
			STATUS	current
	DESCRIPTION ""
			::= { mbus91 101 }

mbus92			OBJECT IDENTIFIER ::= { mbus 146 }

mbus92IdNumber		OBJECT-TYPE
			SYNTAX	Gauge
			ACCESS	read-only
			STATUS	current
	DESCRIPTION ""
			::= { mbus92 1 }

mbus92Manufacturer	OBJECT-TYPE
			SYNTAX	Gauge
			ACCESS	read-only
			STATUS	current
	DESCRIPTION ""
			::= { mbus92 2 }

mbus92Version		OBJECT-TYPE
			SYNTAX	Gauge
			ACCESS	read-only
			STATUS	current
	DESCRIPTION ""
			::= { mbus92 3 }

mbus92Medium		OBJECT-TYPE
			SYNTAX	Gauge
			ACCESS	read-only
			STATUS	current
	DESCRIPTION ""
			::= { mbus92 4 }

mbus92Status		OBJECT-TYPE
			SYNTAX	Gauge
			ACCESS	read-only
			STATUS	current
	DESCRIPTION ""
			::= { mbus92 5 }

mbus92VIF00		OBJECT-TYPE
			SYNTAX	INTEGER
			ACCESS	read-only
			STATUS	current
	DESCRIPTION ""
			::= { mbus92 6 }

mbus92Value00		OBJECT-TYPE
			SYNTAX	INTEGER
			ACCESS	read-only
			STATUS	current
	DESCRIPTION ""
			::= { mbus92 7 }

mbus92VIF01		OBJECT-TYPE
			SYNTAX	INTEGER
			ACCESS	read-only
			STATUS	current
	DESCRIPTION ""
			::= { mbus92 8 }

mbus92Value01		OBJECT-TYPE
			SYNTAX	INTEGER
			ACCESS	read-only
			STATUS	current
	DESCRIPTION ""
			::= { mbus92 9 }

mbus92VIF02		OBJECT-TYPE
			SYNTAX	INTEGER
			ACCESS	read-only
			STATUS	current
	DESCRIPTION ""
			::= { mbus92 10 }

mbus92Value02		OBJECT-TYPE
			SYNTAX	INTEGER
			ACCESS	read-only
			STATUS	current
	DESCRIPTION ""
			::= { mbus92 11 }

mbus92VIF03		OBJECT-TYPE
			SYNTAX	INTEGER
			ACCESS	read-only
			STATUS	current
	DESCRIPTION ""
			::= { mbus92 12 }

mbus92Value03		OBJECT-TYPE
			SYNTAX	INTEGER
			ACCESS	read-only
			STATUS	current
	DESCRIPTION ""
			::= { mbus92 13 }

mbus92VIF04		OBJECT-TYPE
			SYNTAX	INTEGER
			ACCESS	read-only
			STATUS	current
	DESCRIPTION ""
			::= { mbus92 14 }

mbus92Value04		OBJECT-TYPE
			SYNTAX	INTEGER
			ACCESS	read-only
			STATUS	current
	DESCRIPTION ""
			::= { mbus92 15 }

mbus92VIF05		OBJECT-TYPE
			SYNTAX	INTEGER
			ACCESS	read-only
			STATUS	current
	DESCRIPTION ""
			::= { mbus92 16 }

mbus92Value05		OBJECT-TYPE
			SYNTAX	INTEGER
			ACCESS	read-only
			STATUS	current
	DESCRIPTION ""
			::= { mbus92 17 }

mbus92VIF06		OBJECT-TYPE
			SYNTAX	INTEGER
			ACCESS	read-only
			STATUS	current
	DESCRIPTION ""
			::= { mbus92 18 }

mbus92Value06		OBJECT-TYPE
			SYNTAX	INTEGER
			ACCESS	read-only
			STATUS	current
	DESCRIPTION ""
			::= { mbus92 19 }

mbus92VIF07		OBJECT-TYPE
			SYNTAX	INTEGER
			ACCESS	read-only
			STATUS	current
	DESCRIPTION ""
			::= { mbus92 20 }

mbus92Value07		OBJECT-TYPE
			SYNTAX	INTEGER
			ACCESS	read-only
			STATUS	current
	DESCRIPTION ""
			::= { mbus92 21 }

mbus92VIF08		OBJECT-TYPE
			SYNTAX	INTEGER
			ACCESS	read-only
			STATUS	current
	DESCRIPTION ""
			::= { mbus92 22 }

mbus92Value08		OBJECT-TYPE
			SYNTAX	INTEGER
			ACCESS	read-only
			STATUS	current
	DESCRIPTION ""
			::= { mbus92 23 }

mbus92VIF09		OBJECT-TYPE
			SYNTAX	INTEGER
			ACCESS	read-only
			STATUS	current
	DESCRIPTION ""
			::= { mbus92 24 }

mbus92Value09		OBJECT-TYPE
			SYNTAX	INTEGER
			ACCESS	read-only
			STATUS	current
	DESCRIPTION ""
			::= { mbus92 25 }

mbus92VIF0A		OBJECT-TYPE
			SYNTAX	INTEGER
			ACCESS	read-only
			STATUS	current
	DESCRIPTION ""
			::= { mbus92 26 }

mbus92Value0A		OBJECT-TYPE
			SYNTAX	INTEGER
			ACCESS	read-only
			STATUS	current
	DESCRIPTION ""
			::= { mbus92 27 }

mbus92VIF0B		OBJECT-TYPE
			SYNTAX	INTEGER
			ACCESS	read-only
			STATUS	current
	DESCRIPTION ""
			::= { mbus92 28 }

mbus92Value0B		OBJECT-TYPE
			SYNTAX	INTEGER
			ACCESS	read-only
			STATUS	current
	DESCRIPTION ""
			::= { mbus92 29 }

mbus92VIF0C		OBJECT-TYPE
			SYNTAX	INTEGER
			ACCESS	read-only
			STATUS	current
	DESCRIPTION ""
			::= { mbus92 30 }

mbus92Value0C		OBJECT-TYPE
			SYNTAX	INTEGER
			ACCESS	read-only
			STATUS	current
	DESCRIPTION ""
			::= { mbus92 31 }

mbus92VIF0D		OBJECT-TYPE
			SYNTAX	INTEGER
			ACCESS	read-only
			STATUS	current
	DESCRIPTION ""
			::= { mbus92 32 }

mbus92Value0D		OBJECT-TYPE
			SYNTAX	INTEGER
			ACCESS	read-only
			STATUS	current
	DESCRIPTION ""
			::= { mbus92 33 }

mbus92VIF0E		OBJECT-TYPE
			SYNTAX	INTEGER
			ACCESS	read-only
			STATUS	current
	DESCRIPTION ""
			::= { mbus92 34 }

mbus92Value0E		OBJECT-TYPE
			SYNTAX	INTEGER
			ACCESS	read-only
			STATUS	current
	DESCRIPTION ""
			::= { mbus92 35 }

mbus92VIF0F		OBJECT-TYPE
			SYNTAX	INTEGER
			ACCESS	read-only
			STATUS	current
	DESCRIPTION ""
			::= { mbus92 36 }

mbus92Value0F		OBJECT-TYPE
			SYNTAX	INTEGER
			ACCESS	read-only
			STATUS	current
	DESCRIPTION ""
			::= { mbus92 37 }

mbus92VIF10		OBJECT-TYPE
			SYNTAX	INTEGER
			ACCESS	read-only
			STATUS	current
	DESCRIPTION ""
			::= { mbus92 38 }

mbus92Value10		OBJECT-TYPE
			SYNTAX	INTEGER
			ACCESS	read-only
			STATUS	current
	DESCRIPTION ""
			::= { mbus92 39 }

mbus92VIF11		OBJECT-TYPE
			SYNTAX	INTEGER
			ACCESS	read-only
			STATUS	current
	DESCRIPTION ""
			::= { mbus92 40 }

mbus92Value11		OBJECT-TYPE
			SYNTAX	INTEGER
			ACCESS	read-only
			STATUS	current
	DESCRIPTION ""
			::= { mbus92 41 }

mbus92VIF12		OBJECT-TYPE
			SYNTAX	INTEGER
			ACCESS	read-only
			STATUS	current
	DESCRIPTION ""
			::= { mbus92 42 }

mbus92Value12		OBJECT-TYPE
			SYNTAX	INTEGER
			ACCESS	read-only
			STATUS	current
	DESCRIPTION ""
			::= { mbus92 43 }

mbus92VIF13		OBJECT-TYPE
			SYNTAX	INTEGER
			ACCESS	read-only
			STATUS	current
	DESCRIPTION ""
			::= { mbus92 44 }

mbus92Value13		OBJECT-TYPE
			SYNTAX	INTEGER
			ACCESS	read-only
			STATUS	current
	DESCRIPTION ""
			::= { mbus92 45 }

mbus92VIF14		OBJECT-TYPE
			SYNTAX	INTEGER
			ACCESS	read-only
			STATUS	current
	DESCRIPTION ""
			::= { mbus92 46 }

mbus92Value14		OBJECT-TYPE
			SYNTAX	INTEGER
			ACCESS	read-only
			STATUS	current
	DESCRIPTION ""
			::= { mbus92 47 }

mbus92VIF15		OBJECT-TYPE
			SYNTAX	INTEGER
			ACCESS	read-only
			STATUS	current
	DESCRIPTION ""
			::= { mbus92 48 }

mbus92Value15		OBJECT-TYPE
			SYNTAX	INTEGER
			ACCESS	read-only
			STATUS	current
	DESCRIPTION ""
			::= { mbus92 49 }

mbus92VIF16		OBJECT-TYPE
			SYNTAX	INTEGER
			ACCESS	read-only
			STATUS	current
	DESCRIPTION ""
			::= { mbus92 50 }

mbus92Value16		OBJECT-TYPE
			SYNTAX	INTEGER
			ACCESS	read-only
			STATUS	current
	DESCRIPTION ""
			::= { mbus92 51 }

mbus92VIF17		OBJECT-TYPE
			SYNTAX	INTEGER
			ACCESS	read-only
			STATUS	current
	DESCRIPTION ""
			::= { mbus92 52 }

mbus92Value17		OBJECT-TYPE
			SYNTAX	INTEGER
			ACCESS	read-only
			STATUS	current
	DESCRIPTION ""
			::= { mbus92 53 }

mbus92VIF18		OBJECT-TYPE
			SYNTAX	INTEGER
			ACCESS	read-only
			STATUS	current
	DESCRIPTION ""
			::= { mbus92 54 }

mbus92Value18		OBJECT-TYPE
			SYNTAX	INTEGER
			ACCESS	read-only
			STATUS	current
	DESCRIPTION ""
			::= { mbus92 55 }

mbus92VIF19		OBJECT-TYPE
			SYNTAX	INTEGER
			ACCESS	read-only
			STATUS	current
	DESCRIPTION ""
			::= { mbus92 56 }

mbus92Value19		OBJECT-TYPE
			SYNTAX	INTEGER
			ACCESS	read-only
			STATUS	current
	DESCRIPTION ""
			::= { mbus92 57 }

mbus92VIF1A		OBJECT-TYPE
			SYNTAX	INTEGER
			ACCESS	read-only
			STATUS	current
	DESCRIPTION ""
			::= { mbus92 58 }

mbus92Value1A		OBJECT-TYPE
			SYNTAX	INTEGER
			ACCESS	read-only
			STATUS	current
	DESCRIPTION ""
			::= { mbus92 59 }

mbus92VIF1B		OBJECT-TYPE
			SYNTAX	INTEGER
			ACCESS	read-only
			STATUS	current
	DESCRIPTION ""
			::= { mbus92 60 }

mbus92Value1B		OBJECT-TYPE
			SYNTAX	INTEGER
			ACCESS	read-only
			STATUS	current
	DESCRIPTION ""
			::= { mbus92 61 }

mbus92VIF1C		OBJECT-TYPE
			SYNTAX	INTEGER
			ACCESS	read-only
			STATUS	current
	DESCRIPTION ""
			::= { mbus92 62 }

mbus92Value1C		OBJECT-TYPE
			SYNTAX	INTEGER
			ACCESS	read-only
			STATUS	current
	DESCRIPTION ""
			::= { mbus92 63 }

mbus92VIF1D		OBJECT-TYPE
			SYNTAX	INTEGER
			ACCESS	read-only
			STATUS	current
	DESCRIPTION ""
			::= { mbus92 64 }

mbus92Value1D		OBJECT-TYPE
			SYNTAX	INTEGER
			ACCESS	read-only
			STATUS	current
	DESCRIPTION ""
			::= { mbus92 65 }

mbus92VIF1E		OBJECT-TYPE
			SYNTAX	INTEGER
			ACCESS	read-only
			STATUS	current
	DESCRIPTION ""
			::= { mbus92 66 }

mbus92Value1E		OBJECT-TYPE
			SYNTAX	INTEGER
			ACCESS	read-only
			STATUS	current
	DESCRIPTION ""
			::= { mbus92 67 }

mbus92VIF1F		OBJECT-TYPE
			SYNTAX	INTEGER
			ACCESS	read-only
			STATUS	current
	DESCRIPTION ""
			::= { mbus92 68 }

mbus92Value1F		OBJECT-TYPE
			SYNTAX	INTEGER
			ACCESS	read-only
			STATUS	current
	DESCRIPTION ""
			::= { mbus92 69 }

mbus92VIF20		OBJECT-TYPE
			SYNTAX	INTEGER
			ACCESS	read-only
			STATUS	current
	DESCRIPTION ""
			::= { mbus92 70 }

mbus92Value20		OBJECT-TYPE
			SYNTAX	INTEGER
			ACCESS	read-only
			STATUS	current
	DESCRIPTION ""
			::= { mbus92 71 }

mbus92VIF21		OBJECT-TYPE
			SYNTAX	INTEGER
			ACCESS	read-only
			STATUS	current
	DESCRIPTION ""
			::= { mbus92 72 }

mbus92Value21		OBJECT-TYPE
			SYNTAX	INTEGER
			ACCESS	read-only
			STATUS	current
	DESCRIPTION ""
			::= { mbus92 73 }

mbus92VIF22		OBJECT-TYPE
			SYNTAX	INTEGER
			ACCESS	read-only
			STATUS	current
	DESCRIPTION ""
			::= { mbus92 74 }

mbus92Value22		OBJECT-TYPE
			SYNTAX	INTEGER
			ACCESS	read-only
			STATUS	current
	DESCRIPTION ""
			::= { mbus92 75 }

mbus92VIF23		OBJECT-TYPE
			SYNTAX	INTEGER
			ACCESS	read-only
			STATUS	current
	DESCRIPTION ""
			::= { mbus92 76 }

mbus92Value23		OBJECT-TYPE
			SYNTAX	INTEGER
			ACCESS	read-only
			STATUS	current
	DESCRIPTION ""
			::= { mbus92 77 }

mbus92VIF24		OBJECT-TYPE
			SYNTAX	INTEGER
			ACCESS	read-only
			STATUS	current
	DESCRIPTION ""
			::= { mbus92 78 }

mbus92Value24		OBJECT-TYPE
			SYNTAX	INTEGER
			ACCESS	read-only
			STATUS	current
	DESCRIPTION ""
			::= { mbus92 79 }

mbus92VIF25		OBJECT-TYPE
			SYNTAX	INTEGER
			ACCESS	read-only
			STATUS	current
	DESCRIPTION ""
			::= { mbus92 80 }

mbus92Value25		OBJECT-TYPE
			SYNTAX	INTEGER
			ACCESS	read-only
			STATUS	current
	DESCRIPTION ""
			::= { mbus92 81 }

mbus92VIF26		OBJECT-TYPE
			SYNTAX	INTEGER
			ACCESS	read-only
			STATUS	current
	DESCRIPTION ""
			::= { mbus92 82 }

mbus92Value26		OBJECT-TYPE
			SYNTAX	INTEGER
			ACCESS	read-only
			STATUS	current
	DESCRIPTION ""
			::= { mbus92 83 }

mbus92VIF27		OBJECT-TYPE
			SYNTAX	INTEGER
			ACCESS	read-only
			STATUS	current
	DESCRIPTION ""
			::= { mbus92 84 }

mbus92Value27		OBJECT-TYPE
			SYNTAX	INTEGER
			ACCESS	read-only
			STATUS	current
	DESCRIPTION ""
			::= { mbus92 85 }

mbus92VIF28		OBJECT-TYPE
			SYNTAX	INTEGER
			ACCESS	read-only
			STATUS	current
	DESCRIPTION ""
			::= { mbus92 86 }

mbus92Value28		OBJECT-TYPE
			SYNTAX	INTEGER
			ACCESS	read-only
			STATUS	current
	DESCRIPTION ""
			::= { mbus92 87 }

mbus92VIF29		OBJECT-TYPE
			SYNTAX	INTEGER
			ACCESS	read-only
			STATUS	current
	DESCRIPTION ""
			::= { mbus92 88 }

mbus92Value29		OBJECT-TYPE
			SYNTAX	INTEGER
			ACCESS	read-only
			STATUS	current
	DESCRIPTION ""
			::= { mbus92 89 }

mbus92VIF2A		OBJECT-TYPE
			SYNTAX	INTEGER
			ACCESS	read-only
			STATUS	current
	DESCRIPTION ""
			::= { mbus92 90 }

mbus92Value2A		OBJECT-TYPE
			SYNTAX	INTEGER
			ACCESS	read-only
			STATUS	current
	DESCRIPTION ""
			::= { mbus92 91 }

mbus92VIF2B		OBJECT-TYPE
			SYNTAX	INTEGER
			ACCESS	read-only
			STATUS	current
	DESCRIPTION ""
			::= { mbus92 92 }

mbus92Value2B		OBJECT-TYPE
			SYNTAX	INTEGER
			ACCESS	read-only
			STATUS	current
	DESCRIPTION ""
			::= { mbus92 93 }

mbus92VIF2C		OBJECT-TYPE
			SYNTAX	INTEGER
			ACCESS	read-only
			STATUS	current
	DESCRIPTION ""
			::= { mbus92 94 }

mbus92Value2C		OBJECT-TYPE
			SYNTAX	INTEGER
			ACCESS	read-only
			STATUS	current
	DESCRIPTION ""
			::= { mbus92 95 }

mbus92VIF2D		OBJECT-TYPE
			SYNTAX	INTEGER
			ACCESS	read-only
			STATUS	current
	DESCRIPTION ""
			::= { mbus92 96 }

mbus92Value2D		OBJECT-TYPE
			SYNTAX	INTEGER
			ACCESS	read-only
			STATUS	current
	DESCRIPTION ""
			::= { mbus92 97 }

mbus92VIF2E		OBJECT-TYPE
			SYNTAX	INTEGER
			ACCESS	read-only
			STATUS	current
	DESCRIPTION ""
			::= { mbus92 98 }

mbus92Value2E		OBJECT-TYPE
			SYNTAX	INTEGER
			ACCESS	read-only
			STATUS	current
	DESCRIPTION ""
			::= { mbus92 99 }

mbus92VIF2F		OBJECT-TYPE
			SYNTAX	INTEGER
			ACCESS	read-only
			STATUS	current
	DESCRIPTION ""
			::= { mbus92 100 }

mbus92Value2F		OBJECT-TYPE
			SYNTAX	INTEGER
			ACCESS	read-only
			STATUS	current
	DESCRIPTION ""
			::= { mbus92 101 }

mbus93			OBJECT IDENTIFIER ::= { mbus 147 }

mbus93IdNumber		OBJECT-TYPE
			SYNTAX	Gauge
			ACCESS	read-only
			STATUS	current
	DESCRIPTION ""
			::= { mbus93 1 }

mbus93Manufacturer	OBJECT-TYPE
			SYNTAX	Gauge
			ACCESS	read-only
			STATUS	current
	DESCRIPTION ""
			::= { mbus93 2 }

mbus93Version		OBJECT-TYPE
			SYNTAX	Gauge
			ACCESS	read-only
			STATUS	current
	DESCRIPTION ""
			::= { mbus93 3 }

mbus93Medium		OBJECT-TYPE
			SYNTAX	Gauge
			ACCESS	read-only
			STATUS	current
	DESCRIPTION ""
			::= { mbus93 4 }

mbus93Status		OBJECT-TYPE
			SYNTAX	Gauge
			ACCESS	read-only
			STATUS	current
	DESCRIPTION ""
			::= { mbus93 5 }

mbus93VIF00		OBJECT-TYPE
			SYNTAX	INTEGER
			ACCESS	read-only
			STATUS	current
	DESCRIPTION ""
			::= { mbus93 6 }

mbus93Value00		OBJECT-TYPE
			SYNTAX	INTEGER
			ACCESS	read-only
			STATUS	current
	DESCRIPTION ""
			::= { mbus93 7 }

mbus93VIF01		OBJECT-TYPE
			SYNTAX	INTEGER
			ACCESS	read-only
			STATUS	current
	DESCRIPTION ""
			::= { mbus93 8 }

mbus93Value01		OBJECT-TYPE
			SYNTAX	INTEGER
			ACCESS	read-only
			STATUS	current
	DESCRIPTION ""
			::= { mbus93 9 }

mbus93VIF02		OBJECT-TYPE
			SYNTAX	INTEGER
			ACCESS	read-only
			STATUS	current
	DESCRIPTION ""
			::= { mbus93 10 }

mbus93Value02		OBJECT-TYPE
			SYNTAX	INTEGER
			ACCESS	read-only
			STATUS	current
	DESCRIPTION ""
			::= { mbus93 11 }

mbus93VIF03		OBJECT-TYPE
			SYNTAX	INTEGER
			ACCESS	read-only
			STATUS	current
	DESCRIPTION ""
			::= { mbus93 12 }

mbus93Value03		OBJECT-TYPE
			SYNTAX	INTEGER
			ACCESS	read-only
			STATUS	current
	DESCRIPTION ""
			::= { mbus93 13 }

mbus93VIF04		OBJECT-TYPE
			SYNTAX	INTEGER
			ACCESS	read-only
			STATUS	current
	DESCRIPTION ""
			::= { mbus93 14 }

mbus93Value04		OBJECT-TYPE
			SYNTAX	INTEGER
			ACCESS	read-only
			STATUS	current
	DESCRIPTION ""
			::= { mbus93 15 }

mbus93VIF05		OBJECT-TYPE
			SYNTAX	INTEGER
			ACCESS	read-only
			STATUS	current
	DESCRIPTION ""
			::= { mbus93 16 }

mbus93Value05		OBJECT-TYPE
			SYNTAX	INTEGER
			ACCESS	read-only
			STATUS	current
	DESCRIPTION ""
			::= { mbus93 17 }

mbus93VIF06		OBJECT-TYPE
			SYNTAX	INTEGER
			ACCESS	read-only
			STATUS	current
	DESCRIPTION ""
			::= { mbus93 18 }

mbus93Value06		OBJECT-TYPE
			SYNTAX	INTEGER
			ACCESS	read-only
			STATUS	current
	DESCRIPTION ""
			::= { mbus93 19 }

mbus93VIF07		OBJECT-TYPE
			SYNTAX	INTEGER
			ACCESS	read-only
			STATUS	current
	DESCRIPTION ""
			::= { mbus93 20 }

mbus93Value07		OBJECT-TYPE
			SYNTAX	INTEGER
			ACCESS	read-only
			STATUS	current
	DESCRIPTION ""
			::= { mbus93 21 }

mbus93VIF08		OBJECT-TYPE
			SYNTAX	INTEGER
			ACCESS	read-only
			STATUS	current
	DESCRIPTION ""
			::= { mbus93 22 }

mbus93Value08		OBJECT-TYPE
			SYNTAX	INTEGER
			ACCESS	read-only
			STATUS	current
	DESCRIPTION ""
			::= { mbus93 23 }

mbus93VIF09		OBJECT-TYPE
			SYNTAX	INTEGER
			ACCESS	read-only
			STATUS	current
	DESCRIPTION ""
			::= { mbus93 24 }

mbus93Value09		OBJECT-TYPE
			SYNTAX	INTEGER
			ACCESS	read-only
			STATUS	current
	DESCRIPTION ""
			::= { mbus93 25 }

mbus93VIF0A		OBJECT-TYPE
			SYNTAX	INTEGER
			ACCESS	read-only
			STATUS	current
	DESCRIPTION ""
			::= { mbus93 26 }

mbus93Value0A		OBJECT-TYPE
			SYNTAX	INTEGER
			ACCESS	read-only
			STATUS	current
	DESCRIPTION ""
			::= { mbus93 27 }

mbus93VIF0B		OBJECT-TYPE
			SYNTAX	INTEGER
			ACCESS	read-only
			STATUS	current
	DESCRIPTION ""
			::= { mbus93 28 }

mbus93Value0B		OBJECT-TYPE
			SYNTAX	INTEGER
			ACCESS	read-only
			STATUS	current
	DESCRIPTION ""
			::= { mbus93 29 }

mbus93VIF0C		OBJECT-TYPE
			SYNTAX	INTEGER
			ACCESS	read-only
			STATUS	current
	DESCRIPTION ""
			::= { mbus93 30 }

mbus93Value0C		OBJECT-TYPE
			SYNTAX	INTEGER
			ACCESS	read-only
			STATUS	current
	DESCRIPTION ""
			::= { mbus93 31 }

mbus93VIF0D		OBJECT-TYPE
			SYNTAX	INTEGER
			ACCESS	read-only
			STATUS	current
	DESCRIPTION ""
			::= { mbus93 32 }

mbus93Value0D		OBJECT-TYPE
			SYNTAX	INTEGER
			ACCESS	read-only
			STATUS	current
	DESCRIPTION ""
			::= { mbus93 33 }

mbus93VIF0E		OBJECT-TYPE
			SYNTAX	INTEGER
			ACCESS	read-only
			STATUS	current
	DESCRIPTION ""
			::= { mbus93 34 }

mbus93Value0E		OBJECT-TYPE
			SYNTAX	INTEGER
			ACCESS	read-only
			STATUS	current
	DESCRIPTION ""
			::= { mbus93 35 }

mbus93VIF0F		OBJECT-TYPE
			SYNTAX	INTEGER
			ACCESS	read-only
			STATUS	current
	DESCRIPTION ""
			::= { mbus93 36 }

mbus93Value0F		OBJECT-TYPE
			SYNTAX	INTEGER
			ACCESS	read-only
			STATUS	current
	DESCRIPTION ""
			::= { mbus93 37 }

mbus93VIF10		OBJECT-TYPE
			SYNTAX	INTEGER
			ACCESS	read-only
			STATUS	current
	DESCRIPTION ""
			::= { mbus93 38 }

mbus93Value10		OBJECT-TYPE
			SYNTAX	INTEGER
			ACCESS	read-only
			STATUS	current
	DESCRIPTION ""
			::= { mbus93 39 }

mbus93VIF11		OBJECT-TYPE
			SYNTAX	INTEGER
			ACCESS	read-only
			STATUS	current
	DESCRIPTION ""
			::= { mbus93 40 }

mbus93Value11		OBJECT-TYPE
			SYNTAX	INTEGER
			ACCESS	read-only
			STATUS	current
	DESCRIPTION ""
			::= { mbus93 41 }

mbus93VIF12		OBJECT-TYPE
			SYNTAX	INTEGER
			ACCESS	read-only
			STATUS	current
	DESCRIPTION ""
			::= { mbus93 42 }

mbus93Value12		OBJECT-TYPE
			SYNTAX	INTEGER
			ACCESS	read-only
			STATUS	current
	DESCRIPTION ""
			::= { mbus93 43 }

mbus93VIF13		OBJECT-TYPE
			SYNTAX	INTEGER
			ACCESS	read-only
			STATUS	current
	DESCRIPTION ""
			::= { mbus93 44 }

mbus93Value13		OBJECT-TYPE
			SYNTAX	INTEGER
			ACCESS	read-only
			STATUS	current
	DESCRIPTION ""
			::= { mbus93 45 }

mbus93VIF14		OBJECT-TYPE
			SYNTAX	INTEGER
			ACCESS	read-only
			STATUS	current
	DESCRIPTION ""
			::= { mbus93 46 }

mbus93Value14		OBJECT-TYPE
			SYNTAX	INTEGER
			ACCESS	read-only
			STATUS	current
	DESCRIPTION ""
			::= { mbus93 47 }

mbus93VIF15		OBJECT-TYPE
			SYNTAX	INTEGER
			ACCESS	read-only
			STATUS	current
	DESCRIPTION ""
			::= { mbus93 48 }

mbus93Value15		OBJECT-TYPE
			SYNTAX	INTEGER
			ACCESS	read-only
			STATUS	current
	DESCRIPTION ""
			::= { mbus93 49 }

mbus93VIF16		OBJECT-TYPE
			SYNTAX	INTEGER
			ACCESS	read-only
			STATUS	current
	DESCRIPTION ""
			::= { mbus93 50 }

mbus93Value16		OBJECT-TYPE
			SYNTAX	INTEGER
			ACCESS	read-only
			STATUS	current
	DESCRIPTION ""
			::= { mbus93 51 }

mbus93VIF17		OBJECT-TYPE
			SYNTAX	INTEGER
			ACCESS	read-only
			STATUS	current
	DESCRIPTION ""
			::= { mbus93 52 }

mbus93Value17		OBJECT-TYPE
			SYNTAX	INTEGER
			ACCESS	read-only
			STATUS	current
	DESCRIPTION ""
			::= { mbus93 53 }

mbus93VIF18		OBJECT-TYPE
			SYNTAX	INTEGER
			ACCESS	read-only
			STATUS	current
	DESCRIPTION ""
			::= { mbus93 54 }

mbus93Value18		OBJECT-TYPE
			SYNTAX	INTEGER
			ACCESS	read-only
			STATUS	current
	DESCRIPTION ""
			::= { mbus93 55 }

mbus93VIF19		OBJECT-TYPE
			SYNTAX	INTEGER
			ACCESS	read-only
			STATUS	current
	DESCRIPTION ""
			::= { mbus93 56 }

mbus93Value19		OBJECT-TYPE
			SYNTAX	INTEGER
			ACCESS	read-only
			STATUS	current
	DESCRIPTION ""
			::= { mbus93 57 }

mbus93VIF1A		OBJECT-TYPE
			SYNTAX	INTEGER
			ACCESS	read-only
			STATUS	current
	DESCRIPTION ""
			::= { mbus93 58 }

mbus93Value1A		OBJECT-TYPE
			SYNTAX	INTEGER
			ACCESS	read-only
			STATUS	current
	DESCRIPTION ""
			::= { mbus93 59 }

mbus93VIF1B		OBJECT-TYPE
			SYNTAX	INTEGER
			ACCESS	read-only
			STATUS	current
	DESCRIPTION ""
			::= { mbus93 60 }

mbus93Value1B		OBJECT-TYPE
			SYNTAX	INTEGER
			ACCESS	read-only
			STATUS	current
	DESCRIPTION ""
			::= { mbus93 61 }

mbus93VIF1C		OBJECT-TYPE
			SYNTAX	INTEGER
			ACCESS	read-only
			STATUS	current
	DESCRIPTION ""
			::= { mbus93 62 }

mbus93Value1C		OBJECT-TYPE
			SYNTAX	INTEGER
			ACCESS	read-only
			STATUS	current
	DESCRIPTION ""
			::= { mbus93 63 }

mbus93VIF1D		OBJECT-TYPE
			SYNTAX	INTEGER
			ACCESS	read-only
			STATUS	current
	DESCRIPTION ""
			::= { mbus93 64 }

mbus93Value1D		OBJECT-TYPE
			SYNTAX	INTEGER
			ACCESS	read-only
			STATUS	current
	DESCRIPTION ""
			::= { mbus93 65 }

mbus93VIF1E		OBJECT-TYPE
			SYNTAX	INTEGER
			ACCESS	read-only
			STATUS	current
	DESCRIPTION ""
			::= { mbus93 66 }

mbus93Value1E		OBJECT-TYPE
			SYNTAX	INTEGER
			ACCESS	read-only
			STATUS	current
	DESCRIPTION ""
			::= { mbus93 67 }

mbus93VIF1F		OBJECT-TYPE
			SYNTAX	INTEGER
			ACCESS	read-only
			STATUS	current
	DESCRIPTION ""
			::= { mbus93 68 }

mbus93Value1F		OBJECT-TYPE
			SYNTAX	INTEGER
			ACCESS	read-only
			STATUS	current
	DESCRIPTION ""
			::= { mbus93 69 }

mbus93VIF20		OBJECT-TYPE
			SYNTAX	INTEGER
			ACCESS	read-only
			STATUS	current
	DESCRIPTION ""
			::= { mbus93 70 }

mbus93Value20		OBJECT-TYPE
			SYNTAX	INTEGER
			ACCESS	read-only
			STATUS	current
	DESCRIPTION ""
			::= { mbus93 71 }

mbus93VIF21		OBJECT-TYPE
			SYNTAX	INTEGER
			ACCESS	read-only
			STATUS	current
	DESCRIPTION ""
			::= { mbus93 72 }

mbus93Value21		OBJECT-TYPE
			SYNTAX	INTEGER
			ACCESS	read-only
			STATUS	current
	DESCRIPTION ""
			::= { mbus93 73 }

mbus93VIF22		OBJECT-TYPE
			SYNTAX	INTEGER
			ACCESS	read-only
			STATUS	current
	DESCRIPTION ""
			::= { mbus93 74 }

mbus93Value22		OBJECT-TYPE
			SYNTAX	INTEGER
			ACCESS	read-only
			STATUS	current
	DESCRIPTION ""
			::= { mbus93 75 }

mbus93VIF23		OBJECT-TYPE
			SYNTAX	INTEGER
			ACCESS	read-only
			STATUS	current
	DESCRIPTION ""
			::= { mbus93 76 }

mbus93Value23		OBJECT-TYPE
			SYNTAX	INTEGER
			ACCESS	read-only
			STATUS	current
	DESCRIPTION ""
			::= { mbus93 77 }

mbus93VIF24		OBJECT-TYPE
			SYNTAX	INTEGER
			ACCESS	read-only
			STATUS	current
	DESCRIPTION ""
			::= { mbus93 78 }

mbus93Value24		OBJECT-TYPE
			SYNTAX	INTEGER
			ACCESS	read-only
			STATUS	current
	DESCRIPTION ""
			::= { mbus93 79 }

mbus93VIF25		OBJECT-TYPE
			SYNTAX	INTEGER
			ACCESS	read-only
			STATUS	current
	DESCRIPTION ""
			::= { mbus93 80 }

mbus93Value25		OBJECT-TYPE
			SYNTAX	INTEGER
			ACCESS	read-only
			STATUS	current
	DESCRIPTION ""
			::= { mbus93 81 }

mbus93VIF26		OBJECT-TYPE
			SYNTAX	INTEGER
			ACCESS	read-only
			STATUS	current
	DESCRIPTION ""
			::= { mbus93 82 }

mbus93Value26		OBJECT-TYPE
			SYNTAX	INTEGER
			ACCESS	read-only
			STATUS	current
	DESCRIPTION ""
			::= { mbus93 83 }

mbus93VIF27		OBJECT-TYPE
			SYNTAX	INTEGER
			ACCESS	read-only
			STATUS	current
	DESCRIPTION ""
			::= { mbus93 84 }

mbus93Value27		OBJECT-TYPE
			SYNTAX	INTEGER
			ACCESS	read-only
			STATUS	current
	DESCRIPTION ""
			::= { mbus93 85 }

mbus93VIF28		OBJECT-TYPE
			SYNTAX	INTEGER
			ACCESS	read-only
			STATUS	current
	DESCRIPTION ""
			::= { mbus93 86 }

mbus93Value28		OBJECT-TYPE
			SYNTAX	INTEGER
			ACCESS	read-only
			STATUS	current
	DESCRIPTION ""
			::= { mbus93 87 }

mbus93VIF29		OBJECT-TYPE
			SYNTAX	INTEGER
			ACCESS	read-only
			STATUS	current
	DESCRIPTION ""
			::= { mbus93 88 }

mbus93Value29		OBJECT-TYPE
			SYNTAX	INTEGER
			ACCESS	read-only
			STATUS	current
	DESCRIPTION ""
			::= { mbus93 89 }

mbus93VIF2A		OBJECT-TYPE
			SYNTAX	INTEGER
			ACCESS	read-only
			STATUS	current
	DESCRIPTION ""
			::= { mbus93 90 }

mbus93Value2A		OBJECT-TYPE
			SYNTAX	INTEGER
			ACCESS	read-only
			STATUS	current
	DESCRIPTION ""
			::= { mbus93 91 }

mbus93VIF2B		OBJECT-TYPE
			SYNTAX	INTEGER
			ACCESS	read-only
			STATUS	current
	DESCRIPTION ""
			::= { mbus93 92 }

mbus93Value2B		OBJECT-TYPE
			SYNTAX	INTEGER
			ACCESS	read-only
			STATUS	current
	DESCRIPTION ""
			::= { mbus93 93 }

mbus93VIF2C		OBJECT-TYPE
			SYNTAX	INTEGER
			ACCESS	read-only
			STATUS	current
	DESCRIPTION ""
			::= { mbus93 94 }

mbus93Value2C		OBJECT-TYPE
			SYNTAX	INTEGER
			ACCESS	read-only
			STATUS	current
	DESCRIPTION ""
			::= { mbus93 95 }

mbus93VIF2D		OBJECT-TYPE
			SYNTAX	INTEGER
			ACCESS	read-only
			STATUS	current
	DESCRIPTION ""
			::= { mbus93 96 }

mbus93Value2D		OBJECT-TYPE
			SYNTAX	INTEGER
			ACCESS	read-only
			STATUS	current
	DESCRIPTION ""
			::= { mbus93 97 }

mbus93VIF2E		OBJECT-TYPE
			SYNTAX	INTEGER
			ACCESS	read-only
			STATUS	current
	DESCRIPTION ""
			::= { mbus93 98 }

mbus93Value2E		OBJECT-TYPE
			SYNTAX	INTEGER
			ACCESS	read-only
			STATUS	current
	DESCRIPTION ""
			::= { mbus93 99 }

mbus93VIF2F		OBJECT-TYPE
			SYNTAX	INTEGER
			ACCESS	read-only
			STATUS	current
	DESCRIPTION ""
			::= { mbus93 100 }

mbus93Value2F		OBJECT-TYPE
			SYNTAX	INTEGER
			ACCESS	read-only
			STATUS	current
	DESCRIPTION ""
			::= { mbus93 101 }

mbus94			OBJECT IDENTIFIER ::= { mbus 148 }

mbus94IdNumber		OBJECT-TYPE
			SYNTAX	Gauge
			ACCESS	read-only
			STATUS	current
	DESCRIPTION ""
			::= { mbus94 1 }

mbus94Manufacturer	OBJECT-TYPE
			SYNTAX	Gauge
			ACCESS	read-only
			STATUS	current
	DESCRIPTION ""
			::= { mbus94 2 }

mbus94Version		OBJECT-TYPE
			SYNTAX	Gauge
			ACCESS	read-only
			STATUS	current
	DESCRIPTION ""
			::= { mbus94 3 }

mbus94Medium		OBJECT-TYPE
			SYNTAX	Gauge
			ACCESS	read-only
			STATUS	current
	DESCRIPTION ""
			::= { mbus94 4 }

mbus94Status		OBJECT-TYPE
			SYNTAX	Gauge
			ACCESS	read-only
			STATUS	current
	DESCRIPTION ""
			::= { mbus94 5 }

mbus94VIF00		OBJECT-TYPE
			SYNTAX	INTEGER
			ACCESS	read-only
			STATUS	current
	DESCRIPTION ""
			::= { mbus94 6 }

mbus94Value00		OBJECT-TYPE
			SYNTAX	INTEGER
			ACCESS	read-only
			STATUS	current
	DESCRIPTION ""
			::= { mbus94 7 }

mbus94VIF01		OBJECT-TYPE
			SYNTAX	INTEGER
			ACCESS	read-only
			STATUS	current
	DESCRIPTION ""
			::= { mbus94 8 }

mbus94Value01		OBJECT-TYPE
			SYNTAX	INTEGER
			ACCESS	read-only
			STATUS	current
	DESCRIPTION ""
			::= { mbus94 9 }

mbus94VIF02		OBJECT-TYPE
			SYNTAX	INTEGER
			ACCESS	read-only
			STATUS	current
	DESCRIPTION ""
			::= { mbus94 10 }

mbus94Value02		OBJECT-TYPE
			SYNTAX	INTEGER
			ACCESS	read-only
			STATUS	current
	DESCRIPTION ""
			::= { mbus94 11 }

mbus94VIF03		OBJECT-TYPE
			SYNTAX	INTEGER
			ACCESS	read-only
			STATUS	current
	DESCRIPTION ""
			::= { mbus94 12 }

mbus94Value03		OBJECT-TYPE
			SYNTAX	INTEGER
			ACCESS	read-only
			STATUS	current
	DESCRIPTION ""
			::= { mbus94 13 }

mbus94VIF04		OBJECT-TYPE
			SYNTAX	INTEGER
			ACCESS	read-only
			STATUS	current
	DESCRIPTION ""
			::= { mbus94 14 }

mbus94Value04		OBJECT-TYPE
			SYNTAX	INTEGER
			ACCESS	read-only
			STATUS	current
	DESCRIPTION ""
			::= { mbus94 15 }

mbus94VIF05		OBJECT-TYPE
			SYNTAX	INTEGER
			ACCESS	read-only
			STATUS	current
	DESCRIPTION ""
			::= { mbus94 16 }

mbus94Value05		OBJECT-TYPE
			SYNTAX	INTEGER
			ACCESS	read-only
			STATUS	current
	DESCRIPTION ""
			::= { mbus94 17 }

mbus94VIF06		OBJECT-TYPE
			SYNTAX	INTEGER
			ACCESS	read-only
			STATUS	current
	DESCRIPTION ""
			::= { mbus94 18 }

mbus94Value06		OBJECT-TYPE
			SYNTAX	INTEGER
			ACCESS	read-only
			STATUS	current
	DESCRIPTION ""
			::= { mbus94 19 }

mbus94VIF07		OBJECT-TYPE
			SYNTAX	INTEGER
			ACCESS	read-only
			STATUS	current
	DESCRIPTION ""
			::= { mbus94 20 }

mbus94Value07		OBJECT-TYPE
			SYNTAX	INTEGER
			ACCESS	read-only
			STATUS	current
	DESCRIPTION ""
			::= { mbus94 21 }

mbus94VIF08		OBJECT-TYPE
			SYNTAX	INTEGER
			ACCESS	read-only
			STATUS	current
	DESCRIPTION ""
			::= { mbus94 22 }

mbus94Value08		OBJECT-TYPE
			SYNTAX	INTEGER
			ACCESS	read-only
			STATUS	current
	DESCRIPTION ""
			::= { mbus94 23 }

mbus94VIF09		OBJECT-TYPE
			SYNTAX	INTEGER
			ACCESS	read-only
			STATUS	current
	DESCRIPTION ""
			::= { mbus94 24 }

mbus94Value09		OBJECT-TYPE
			SYNTAX	INTEGER
			ACCESS	read-only
			STATUS	current
	DESCRIPTION ""
			::= { mbus94 25 }

mbus94VIF0A		OBJECT-TYPE
			SYNTAX	INTEGER
			ACCESS	read-only
			STATUS	current
	DESCRIPTION ""
			::= { mbus94 26 }

mbus94Value0A		OBJECT-TYPE
			SYNTAX	INTEGER
			ACCESS	read-only
			STATUS	current
	DESCRIPTION ""
			::= { mbus94 27 }

mbus94VIF0B		OBJECT-TYPE
			SYNTAX	INTEGER
			ACCESS	read-only
			STATUS	current
	DESCRIPTION ""
			::= { mbus94 28 }

mbus94Value0B		OBJECT-TYPE
			SYNTAX	INTEGER
			ACCESS	read-only
			STATUS	current
	DESCRIPTION ""
			::= { mbus94 29 }

mbus94VIF0C		OBJECT-TYPE
			SYNTAX	INTEGER
			ACCESS	read-only
			STATUS	current
	DESCRIPTION ""
			::= { mbus94 30 }

mbus94Value0C		OBJECT-TYPE
			SYNTAX	INTEGER
			ACCESS	read-only
			STATUS	current
	DESCRIPTION ""
			::= { mbus94 31 }

mbus94VIF0D		OBJECT-TYPE
			SYNTAX	INTEGER
			ACCESS	read-only
			STATUS	current
	DESCRIPTION ""
			::= { mbus94 32 }

mbus94Value0D		OBJECT-TYPE
			SYNTAX	INTEGER
			ACCESS	read-only
			STATUS	current
	DESCRIPTION ""
			::= { mbus94 33 }

mbus94VIF0E		OBJECT-TYPE
			SYNTAX	INTEGER
			ACCESS	read-only
			STATUS	current
	DESCRIPTION ""
			::= { mbus94 34 }

mbus94Value0E		OBJECT-TYPE
			SYNTAX	INTEGER
			ACCESS	read-only
			STATUS	current
	DESCRIPTION ""
			::= { mbus94 35 }

mbus94VIF0F		OBJECT-TYPE
			SYNTAX	INTEGER
			ACCESS	read-only
			STATUS	current
	DESCRIPTION ""
			::= { mbus94 36 }

mbus94Value0F		OBJECT-TYPE
			SYNTAX	INTEGER
			ACCESS	read-only
			STATUS	current
	DESCRIPTION ""
			::= { mbus94 37 }

mbus94VIF10		OBJECT-TYPE
			SYNTAX	INTEGER
			ACCESS	read-only
			STATUS	current
	DESCRIPTION ""
			::= { mbus94 38 }

mbus94Value10		OBJECT-TYPE
			SYNTAX	INTEGER
			ACCESS	read-only
			STATUS	current
	DESCRIPTION ""
			::= { mbus94 39 }

mbus94VIF11		OBJECT-TYPE
			SYNTAX	INTEGER
			ACCESS	read-only
			STATUS	current
	DESCRIPTION ""
			::= { mbus94 40 }

mbus94Value11		OBJECT-TYPE
			SYNTAX	INTEGER
			ACCESS	read-only
			STATUS	current
	DESCRIPTION ""
			::= { mbus94 41 }

mbus94VIF12		OBJECT-TYPE
			SYNTAX	INTEGER
			ACCESS	read-only
			STATUS	current
	DESCRIPTION ""
			::= { mbus94 42 }

mbus94Value12		OBJECT-TYPE
			SYNTAX	INTEGER
			ACCESS	read-only
			STATUS	current
	DESCRIPTION ""
			::= { mbus94 43 }

mbus94VIF13		OBJECT-TYPE
			SYNTAX	INTEGER
			ACCESS	read-only
			STATUS	current
	DESCRIPTION ""
			::= { mbus94 44 }

mbus94Value13		OBJECT-TYPE
			SYNTAX	INTEGER
			ACCESS	read-only
			STATUS	current
	DESCRIPTION ""
			::= { mbus94 45 }

mbus94VIF14		OBJECT-TYPE
			SYNTAX	INTEGER
			ACCESS	read-only
			STATUS	current
	DESCRIPTION ""
			::= { mbus94 46 }

mbus94Value14		OBJECT-TYPE
			SYNTAX	INTEGER
			ACCESS	read-only
			STATUS	current
	DESCRIPTION ""
			::= { mbus94 47 }

mbus94VIF15		OBJECT-TYPE
			SYNTAX	INTEGER
			ACCESS	read-only
			STATUS	current
	DESCRIPTION ""
			::= { mbus94 48 }

mbus94Value15		OBJECT-TYPE
			SYNTAX	INTEGER
			ACCESS	read-only
			STATUS	current
	DESCRIPTION ""
			::= { mbus94 49 }

mbus94VIF16		OBJECT-TYPE
			SYNTAX	INTEGER
			ACCESS	read-only
			STATUS	current
	DESCRIPTION ""
			::= { mbus94 50 }

mbus94Value16		OBJECT-TYPE
			SYNTAX	INTEGER
			ACCESS	read-only
			STATUS	current
	DESCRIPTION ""
			::= { mbus94 51 }

mbus94VIF17		OBJECT-TYPE
			SYNTAX	INTEGER
			ACCESS	read-only
			STATUS	current
	DESCRIPTION ""
			::= { mbus94 52 }

mbus94Value17		OBJECT-TYPE
			SYNTAX	INTEGER
			ACCESS	read-only
			STATUS	current
	DESCRIPTION ""
			::= { mbus94 53 }

mbus94VIF18		OBJECT-TYPE
			SYNTAX	INTEGER
			ACCESS	read-only
			STATUS	current
	DESCRIPTION ""
			::= { mbus94 54 }

mbus94Value18		OBJECT-TYPE
			SYNTAX	INTEGER
			ACCESS	read-only
			STATUS	current
	DESCRIPTION ""
			::= { mbus94 55 }

mbus94VIF19		OBJECT-TYPE
			SYNTAX	INTEGER
			ACCESS	read-only
			STATUS	current
	DESCRIPTION ""
			::= { mbus94 56 }

mbus94Value19		OBJECT-TYPE
			SYNTAX	INTEGER
			ACCESS	read-only
			STATUS	current
	DESCRIPTION ""
			::= { mbus94 57 }

mbus94VIF1A		OBJECT-TYPE
			SYNTAX	INTEGER
			ACCESS	read-only
			STATUS	current
	DESCRIPTION ""
			::= { mbus94 58 }

mbus94Value1A		OBJECT-TYPE
			SYNTAX	INTEGER
			ACCESS	read-only
			STATUS	current
	DESCRIPTION ""
			::= { mbus94 59 }

mbus94VIF1B		OBJECT-TYPE
			SYNTAX	INTEGER
			ACCESS	read-only
			STATUS	current
	DESCRIPTION ""
			::= { mbus94 60 }

mbus94Value1B		OBJECT-TYPE
			SYNTAX	INTEGER
			ACCESS	read-only
			STATUS	current
	DESCRIPTION ""
			::= { mbus94 61 }

mbus94VIF1C		OBJECT-TYPE
			SYNTAX	INTEGER
			ACCESS	read-only
			STATUS	current
	DESCRIPTION ""
			::= { mbus94 62 }

mbus94Value1C		OBJECT-TYPE
			SYNTAX	INTEGER
			ACCESS	read-only
			STATUS	current
	DESCRIPTION ""
			::= { mbus94 63 }

mbus94VIF1D		OBJECT-TYPE
			SYNTAX	INTEGER
			ACCESS	read-only
			STATUS	current
	DESCRIPTION ""
			::= { mbus94 64 }

mbus94Value1D		OBJECT-TYPE
			SYNTAX	INTEGER
			ACCESS	read-only
			STATUS	current
	DESCRIPTION ""
			::= { mbus94 65 }

mbus94VIF1E		OBJECT-TYPE
			SYNTAX	INTEGER
			ACCESS	read-only
			STATUS	current
	DESCRIPTION ""
			::= { mbus94 66 }

mbus94Value1E		OBJECT-TYPE
			SYNTAX	INTEGER
			ACCESS	read-only
			STATUS	current
	DESCRIPTION ""
			::= { mbus94 67 }

mbus94VIF1F		OBJECT-TYPE
			SYNTAX	INTEGER
			ACCESS	read-only
			STATUS	current
	DESCRIPTION ""
			::= { mbus94 68 }

mbus94Value1F		OBJECT-TYPE
			SYNTAX	INTEGER
			ACCESS	read-only
			STATUS	current
	DESCRIPTION ""
			::= { mbus94 69 }

mbus94VIF20		OBJECT-TYPE
			SYNTAX	INTEGER
			ACCESS	read-only
			STATUS	current
	DESCRIPTION ""
			::= { mbus94 70 }

mbus94Value20		OBJECT-TYPE
			SYNTAX	INTEGER
			ACCESS	read-only
			STATUS	current
	DESCRIPTION ""
			::= { mbus94 71 }

mbus94VIF21		OBJECT-TYPE
			SYNTAX	INTEGER
			ACCESS	read-only
			STATUS	current
	DESCRIPTION ""
			::= { mbus94 72 }

mbus94Value21		OBJECT-TYPE
			SYNTAX	INTEGER
			ACCESS	read-only
			STATUS	current
	DESCRIPTION ""
			::= { mbus94 73 }

mbus94VIF22		OBJECT-TYPE
			SYNTAX	INTEGER
			ACCESS	read-only
			STATUS	current
	DESCRIPTION ""
			::= { mbus94 74 }

mbus94Value22		OBJECT-TYPE
			SYNTAX	INTEGER
			ACCESS	read-only
			STATUS	current
	DESCRIPTION ""
			::= { mbus94 75 }

mbus94VIF23		OBJECT-TYPE
			SYNTAX	INTEGER
			ACCESS	read-only
			STATUS	current
	DESCRIPTION ""
			::= { mbus94 76 }

mbus94Value23		OBJECT-TYPE
			SYNTAX	INTEGER
			ACCESS	read-only
			STATUS	current
	DESCRIPTION ""
			::= { mbus94 77 }

mbus94VIF24		OBJECT-TYPE
			SYNTAX	INTEGER
			ACCESS	read-only
			STATUS	current
	DESCRIPTION ""
			::= { mbus94 78 }

mbus94Value24		OBJECT-TYPE
			SYNTAX	INTEGER
			ACCESS	read-only
			STATUS	current
	DESCRIPTION ""
			::= { mbus94 79 }

mbus94VIF25		OBJECT-TYPE
			SYNTAX	INTEGER
			ACCESS	read-only
			STATUS	current
	DESCRIPTION ""
			::= { mbus94 80 }

mbus94Value25		OBJECT-TYPE
			SYNTAX	INTEGER
			ACCESS	read-only
			STATUS	current
	DESCRIPTION ""
			::= { mbus94 81 }

mbus94VIF26		OBJECT-TYPE
			SYNTAX	INTEGER
			ACCESS	read-only
			STATUS	current
	DESCRIPTION ""
			::= { mbus94 82 }

mbus94Value26		OBJECT-TYPE
			SYNTAX	INTEGER
			ACCESS	read-only
			STATUS	current
	DESCRIPTION ""
			::= { mbus94 83 }

mbus94VIF27		OBJECT-TYPE
			SYNTAX	INTEGER
			ACCESS	read-only
			STATUS	current
	DESCRIPTION ""
			::= { mbus94 84 }

mbus94Value27		OBJECT-TYPE
			SYNTAX	INTEGER
			ACCESS	read-only
			STATUS	current
	DESCRIPTION ""
			::= { mbus94 85 }

mbus94VIF28		OBJECT-TYPE
			SYNTAX	INTEGER
			ACCESS	read-only
			STATUS	current
	DESCRIPTION ""
			::= { mbus94 86 }

mbus94Value28		OBJECT-TYPE
			SYNTAX	INTEGER
			ACCESS	read-only
			STATUS	current
	DESCRIPTION ""
			::= { mbus94 87 }

mbus94VIF29		OBJECT-TYPE
			SYNTAX	INTEGER
			ACCESS	read-only
			STATUS	current
	DESCRIPTION ""
			::= { mbus94 88 }

mbus94Value29		OBJECT-TYPE
			SYNTAX	INTEGER
			ACCESS	read-only
			STATUS	current
	DESCRIPTION ""
			::= { mbus94 89 }

mbus94VIF2A		OBJECT-TYPE
			SYNTAX	INTEGER
			ACCESS	read-only
			STATUS	current
	DESCRIPTION ""
			::= { mbus94 90 }

mbus94Value2A		OBJECT-TYPE
			SYNTAX	INTEGER
			ACCESS	read-only
			STATUS	current
	DESCRIPTION ""
			::= { mbus94 91 }

mbus94VIF2B		OBJECT-TYPE
			SYNTAX	INTEGER
			ACCESS	read-only
			STATUS	current
	DESCRIPTION ""
			::= { mbus94 92 }

mbus94Value2B		OBJECT-TYPE
			SYNTAX	INTEGER
			ACCESS	read-only
			STATUS	current
	DESCRIPTION ""
			::= { mbus94 93 }

mbus94VIF2C		OBJECT-TYPE
			SYNTAX	INTEGER
			ACCESS	read-only
			STATUS	current
	DESCRIPTION ""
			::= { mbus94 94 }

mbus94Value2C		OBJECT-TYPE
			SYNTAX	INTEGER
			ACCESS	read-only
			STATUS	current
	DESCRIPTION ""
			::= { mbus94 95 }

mbus94VIF2D		OBJECT-TYPE
			SYNTAX	INTEGER
			ACCESS	read-only
			STATUS	current
	DESCRIPTION ""
			::= { mbus94 96 }

mbus94Value2D		OBJECT-TYPE
			SYNTAX	INTEGER
			ACCESS	read-only
			STATUS	current
	DESCRIPTION ""
			::= { mbus94 97 }

mbus94VIF2E		OBJECT-TYPE
			SYNTAX	INTEGER
			ACCESS	read-only
			STATUS	current
	DESCRIPTION ""
			::= { mbus94 98 }

mbus94Value2E		OBJECT-TYPE
			SYNTAX	INTEGER
			ACCESS	read-only
			STATUS	current
	DESCRIPTION ""
			::= { mbus94 99 }

mbus94VIF2F		OBJECT-TYPE
			SYNTAX	INTEGER
			ACCESS	read-only
			STATUS	current
	DESCRIPTION ""
			::= { mbus94 100 }

mbus94Value2F		OBJECT-TYPE
			SYNTAX	INTEGER
			ACCESS	read-only
			STATUS	current
	DESCRIPTION ""
			::= { mbus94 101 }

mbus95			OBJECT IDENTIFIER ::= { mbus 149 }

mbus95IdNumber		OBJECT-TYPE
			SYNTAX	Gauge
			ACCESS	read-only
			STATUS	current
	DESCRIPTION ""
			::= { mbus95 1 }

mbus95Manufacturer	OBJECT-TYPE
			SYNTAX	Gauge
			ACCESS	read-only
			STATUS	current
	DESCRIPTION ""
			::= { mbus95 2 }

mbus95Version		OBJECT-TYPE
			SYNTAX	Gauge
			ACCESS	read-only
			STATUS	current
	DESCRIPTION ""
			::= { mbus95 3 }

mbus95Medium		OBJECT-TYPE
			SYNTAX	Gauge
			ACCESS	read-only
			STATUS	current
	DESCRIPTION ""
			::= { mbus95 4 }

mbus95Status		OBJECT-TYPE
			SYNTAX	Gauge
			ACCESS	read-only
			STATUS	current
	DESCRIPTION ""
			::= { mbus95 5 }

mbus95VIF00		OBJECT-TYPE
			SYNTAX	INTEGER
			ACCESS	read-only
			STATUS	current
	DESCRIPTION ""
			::= { mbus95 6 }

mbus95Value00		OBJECT-TYPE
			SYNTAX	INTEGER
			ACCESS	read-only
			STATUS	current
	DESCRIPTION ""
			::= { mbus95 7 }

mbus95VIF01		OBJECT-TYPE
			SYNTAX	INTEGER
			ACCESS	read-only
			STATUS	current
	DESCRIPTION ""
			::= { mbus95 8 }

mbus95Value01		OBJECT-TYPE
			SYNTAX	INTEGER
			ACCESS	read-only
			STATUS	current
	DESCRIPTION ""
			::= { mbus95 9 }

mbus95VIF02		OBJECT-TYPE
			SYNTAX	INTEGER
			ACCESS	read-only
			STATUS	current
	DESCRIPTION ""
			::= { mbus95 10 }

mbus95Value02		OBJECT-TYPE
			SYNTAX	INTEGER
			ACCESS	read-only
			STATUS	current
	DESCRIPTION ""
			::= { mbus95 11 }

mbus95VIF03		OBJECT-TYPE
			SYNTAX	INTEGER
			ACCESS	read-only
			STATUS	current
	DESCRIPTION ""
			::= { mbus95 12 }

mbus95Value03		OBJECT-TYPE
			SYNTAX	INTEGER
			ACCESS	read-only
			STATUS	current
	DESCRIPTION ""
			::= { mbus95 13 }

mbus95VIF04		OBJECT-TYPE
			SYNTAX	INTEGER
			ACCESS	read-only
			STATUS	current
	DESCRIPTION ""
			::= { mbus95 14 }

mbus95Value04		OBJECT-TYPE
			SYNTAX	INTEGER
			ACCESS	read-only
			STATUS	current
	DESCRIPTION ""
			::= { mbus95 15 }

mbus95VIF05		OBJECT-TYPE
			SYNTAX	INTEGER
			ACCESS	read-only
			STATUS	current
	DESCRIPTION ""
			::= { mbus95 16 }

mbus95Value05		OBJECT-TYPE
			SYNTAX	INTEGER
			ACCESS	read-only
			STATUS	current
	DESCRIPTION ""
			::= { mbus95 17 }

mbus95VIF06		OBJECT-TYPE
			SYNTAX	INTEGER
			ACCESS	read-only
			STATUS	current
	DESCRIPTION ""
			::= { mbus95 18 }

mbus95Value06		OBJECT-TYPE
			SYNTAX	INTEGER
			ACCESS	read-only
			STATUS	current
	DESCRIPTION ""
			::= { mbus95 19 }

mbus95VIF07		OBJECT-TYPE
			SYNTAX	INTEGER
			ACCESS	read-only
			STATUS	current
	DESCRIPTION ""
			::= { mbus95 20 }

mbus95Value07		OBJECT-TYPE
			SYNTAX	INTEGER
			ACCESS	read-only
			STATUS	current
	DESCRIPTION ""
			::= { mbus95 21 }

mbus95VIF08		OBJECT-TYPE
			SYNTAX	INTEGER
			ACCESS	read-only
			STATUS	current
	DESCRIPTION ""
			::= { mbus95 22 }

mbus95Value08		OBJECT-TYPE
			SYNTAX	INTEGER
			ACCESS	read-only
			STATUS	current
	DESCRIPTION ""
			::= { mbus95 23 }

mbus95VIF09		OBJECT-TYPE
			SYNTAX	INTEGER
			ACCESS	read-only
			STATUS	current
	DESCRIPTION ""
			::= { mbus95 24 }

mbus95Value09		OBJECT-TYPE
			SYNTAX	INTEGER
			ACCESS	read-only
			STATUS	current
	DESCRIPTION ""
			::= { mbus95 25 }

mbus95VIF0A		OBJECT-TYPE
			SYNTAX	INTEGER
			ACCESS	read-only
			STATUS	current
	DESCRIPTION ""
			::= { mbus95 26 }

mbus95Value0A		OBJECT-TYPE
			SYNTAX	INTEGER
			ACCESS	read-only
			STATUS	current
	DESCRIPTION ""
			::= { mbus95 27 }

mbus95VIF0B		OBJECT-TYPE
			SYNTAX	INTEGER
			ACCESS	read-only
			STATUS	current
	DESCRIPTION ""
			::= { mbus95 28 }

mbus95Value0B		OBJECT-TYPE
			SYNTAX	INTEGER
			ACCESS	read-only
			STATUS	current
	DESCRIPTION ""
			::= { mbus95 29 }

mbus95VIF0C		OBJECT-TYPE
			SYNTAX	INTEGER
			ACCESS	read-only
			STATUS	current
	DESCRIPTION ""
			::= { mbus95 30 }

mbus95Value0C		OBJECT-TYPE
			SYNTAX	INTEGER
			ACCESS	read-only
			STATUS	current
	DESCRIPTION ""
			::= { mbus95 31 }

mbus95VIF0D		OBJECT-TYPE
			SYNTAX	INTEGER
			ACCESS	read-only
			STATUS	current
	DESCRIPTION ""
			::= { mbus95 32 }

mbus95Value0D		OBJECT-TYPE
			SYNTAX	INTEGER
			ACCESS	read-only
			STATUS	current
	DESCRIPTION ""
			::= { mbus95 33 }

mbus95VIF0E		OBJECT-TYPE
			SYNTAX	INTEGER
			ACCESS	read-only
			STATUS	current
	DESCRIPTION ""
			::= { mbus95 34 }

mbus95Value0E		OBJECT-TYPE
			SYNTAX	INTEGER
			ACCESS	read-only
			STATUS	current
	DESCRIPTION ""
			::= { mbus95 35 }

mbus95VIF0F		OBJECT-TYPE
			SYNTAX	INTEGER
			ACCESS	read-only
			STATUS	current
	DESCRIPTION ""
			::= { mbus95 36 }

mbus95Value0F		OBJECT-TYPE
			SYNTAX	INTEGER
			ACCESS	read-only
			STATUS	current
	DESCRIPTION ""
			::= { mbus95 37 }

mbus95VIF10		OBJECT-TYPE
			SYNTAX	INTEGER
			ACCESS	read-only
			STATUS	current
	DESCRIPTION ""
			::= { mbus95 38 }

mbus95Value10		OBJECT-TYPE
			SYNTAX	INTEGER
			ACCESS	read-only
			STATUS	current
	DESCRIPTION ""
			::= { mbus95 39 }

mbus95VIF11		OBJECT-TYPE
			SYNTAX	INTEGER
			ACCESS	read-only
			STATUS	current
	DESCRIPTION ""
			::= { mbus95 40 }

mbus95Value11		OBJECT-TYPE
			SYNTAX	INTEGER
			ACCESS	read-only
			STATUS	current
	DESCRIPTION ""
			::= { mbus95 41 }

mbus95VIF12		OBJECT-TYPE
			SYNTAX	INTEGER
			ACCESS	read-only
			STATUS	current
	DESCRIPTION ""
			::= { mbus95 42 }

mbus95Value12		OBJECT-TYPE
			SYNTAX	INTEGER
			ACCESS	read-only
			STATUS	current
	DESCRIPTION ""
			::= { mbus95 43 }

mbus95VIF13		OBJECT-TYPE
			SYNTAX	INTEGER
			ACCESS	read-only
			STATUS	current
	DESCRIPTION ""
			::= { mbus95 44 }

mbus95Value13		OBJECT-TYPE
			SYNTAX	INTEGER
			ACCESS	read-only
			STATUS	current
	DESCRIPTION ""
			::= { mbus95 45 }

mbus95VIF14		OBJECT-TYPE
			SYNTAX	INTEGER
			ACCESS	read-only
			STATUS	current
	DESCRIPTION ""
			::= { mbus95 46 }

mbus95Value14		OBJECT-TYPE
			SYNTAX	INTEGER
			ACCESS	read-only
			STATUS	current
	DESCRIPTION ""
			::= { mbus95 47 }

mbus95VIF15		OBJECT-TYPE
			SYNTAX	INTEGER
			ACCESS	read-only
			STATUS	current
	DESCRIPTION ""
			::= { mbus95 48 }

mbus95Value15		OBJECT-TYPE
			SYNTAX	INTEGER
			ACCESS	read-only
			STATUS	current
	DESCRIPTION ""
			::= { mbus95 49 }

mbus95VIF16		OBJECT-TYPE
			SYNTAX	INTEGER
			ACCESS	read-only
			STATUS	current
	DESCRIPTION ""
			::= { mbus95 50 }

mbus95Value16		OBJECT-TYPE
			SYNTAX	INTEGER
			ACCESS	read-only
			STATUS	current
	DESCRIPTION ""
			::= { mbus95 51 }

mbus95VIF17		OBJECT-TYPE
			SYNTAX	INTEGER
			ACCESS	read-only
			STATUS	current
	DESCRIPTION ""
			::= { mbus95 52 }

mbus95Value17		OBJECT-TYPE
			SYNTAX	INTEGER
			ACCESS	read-only
			STATUS	current
	DESCRIPTION ""
			::= { mbus95 53 }

mbus95VIF18		OBJECT-TYPE
			SYNTAX	INTEGER
			ACCESS	read-only
			STATUS	current
	DESCRIPTION ""
			::= { mbus95 54 }

mbus95Value18		OBJECT-TYPE
			SYNTAX	INTEGER
			ACCESS	read-only
			STATUS	current
	DESCRIPTION ""
			::= { mbus95 55 }

mbus95VIF19		OBJECT-TYPE
			SYNTAX	INTEGER
			ACCESS	read-only
			STATUS	current
	DESCRIPTION ""
			::= { mbus95 56 }

mbus95Value19		OBJECT-TYPE
			SYNTAX	INTEGER
			ACCESS	read-only
			STATUS	current
	DESCRIPTION ""
			::= { mbus95 57 }

mbus95VIF1A		OBJECT-TYPE
			SYNTAX	INTEGER
			ACCESS	read-only
			STATUS	current
	DESCRIPTION ""
			::= { mbus95 58 }

mbus95Value1A		OBJECT-TYPE
			SYNTAX	INTEGER
			ACCESS	read-only
			STATUS	current
	DESCRIPTION ""
			::= { mbus95 59 }

mbus95VIF1B		OBJECT-TYPE
			SYNTAX	INTEGER
			ACCESS	read-only
			STATUS	current
	DESCRIPTION ""
			::= { mbus95 60 }

mbus95Value1B		OBJECT-TYPE
			SYNTAX	INTEGER
			ACCESS	read-only
			STATUS	current
	DESCRIPTION ""
			::= { mbus95 61 }

mbus95VIF1C		OBJECT-TYPE
			SYNTAX	INTEGER
			ACCESS	read-only
			STATUS	current
	DESCRIPTION ""
			::= { mbus95 62 }

mbus95Value1C		OBJECT-TYPE
			SYNTAX	INTEGER
			ACCESS	read-only
			STATUS	current
	DESCRIPTION ""
			::= { mbus95 63 }

mbus95VIF1D		OBJECT-TYPE
			SYNTAX	INTEGER
			ACCESS	read-only
			STATUS	current
	DESCRIPTION ""
			::= { mbus95 64 }

mbus95Value1D		OBJECT-TYPE
			SYNTAX	INTEGER
			ACCESS	read-only
			STATUS	current
	DESCRIPTION ""
			::= { mbus95 65 }

mbus95VIF1E		OBJECT-TYPE
			SYNTAX	INTEGER
			ACCESS	read-only
			STATUS	current
	DESCRIPTION ""
			::= { mbus95 66 }

mbus95Value1E		OBJECT-TYPE
			SYNTAX	INTEGER
			ACCESS	read-only
			STATUS	current
	DESCRIPTION ""
			::= { mbus95 67 }

mbus95VIF1F		OBJECT-TYPE
			SYNTAX	INTEGER
			ACCESS	read-only
			STATUS	current
	DESCRIPTION ""
			::= { mbus95 68 }

mbus95Value1F		OBJECT-TYPE
			SYNTAX	INTEGER
			ACCESS	read-only
			STATUS	current
	DESCRIPTION ""
			::= { mbus95 69 }

mbus95VIF20		OBJECT-TYPE
			SYNTAX	INTEGER
			ACCESS	read-only
			STATUS	current
	DESCRIPTION ""
			::= { mbus95 70 }

mbus95Value20		OBJECT-TYPE
			SYNTAX	INTEGER
			ACCESS	read-only
			STATUS	current
	DESCRIPTION ""
			::= { mbus95 71 }

mbus95VIF21		OBJECT-TYPE
			SYNTAX	INTEGER
			ACCESS	read-only
			STATUS	current
	DESCRIPTION ""
			::= { mbus95 72 }

mbus95Value21		OBJECT-TYPE
			SYNTAX	INTEGER
			ACCESS	read-only
			STATUS	current
	DESCRIPTION ""
			::= { mbus95 73 }

mbus95VIF22		OBJECT-TYPE
			SYNTAX	INTEGER
			ACCESS	read-only
			STATUS	current
	DESCRIPTION ""
			::= { mbus95 74 }

mbus95Value22		OBJECT-TYPE
			SYNTAX	INTEGER
			ACCESS	read-only
			STATUS	current
	DESCRIPTION ""
			::= { mbus95 75 }

mbus95VIF23		OBJECT-TYPE
			SYNTAX	INTEGER
			ACCESS	read-only
			STATUS	current
	DESCRIPTION ""
			::= { mbus95 76 }

mbus95Value23		OBJECT-TYPE
			SYNTAX	INTEGER
			ACCESS	read-only
			STATUS	current
	DESCRIPTION ""
			::= { mbus95 77 }

mbus95VIF24		OBJECT-TYPE
			SYNTAX	INTEGER
			ACCESS	read-only
			STATUS	current
	DESCRIPTION ""
			::= { mbus95 78 }

mbus95Value24		OBJECT-TYPE
			SYNTAX	INTEGER
			ACCESS	read-only
			STATUS	current
	DESCRIPTION ""
			::= { mbus95 79 }

mbus95VIF25		OBJECT-TYPE
			SYNTAX	INTEGER
			ACCESS	read-only
			STATUS	current
	DESCRIPTION ""
			::= { mbus95 80 }

mbus95Value25		OBJECT-TYPE
			SYNTAX	INTEGER
			ACCESS	read-only
			STATUS	current
	DESCRIPTION ""
			::= { mbus95 81 }

mbus95VIF26		OBJECT-TYPE
			SYNTAX	INTEGER
			ACCESS	read-only
			STATUS	current
	DESCRIPTION ""
			::= { mbus95 82 }

mbus95Value26		OBJECT-TYPE
			SYNTAX	INTEGER
			ACCESS	read-only
			STATUS	current
	DESCRIPTION ""
			::= { mbus95 83 }

mbus95VIF27		OBJECT-TYPE
			SYNTAX	INTEGER
			ACCESS	read-only
			STATUS	current
	DESCRIPTION ""
			::= { mbus95 84 }

mbus95Value27		OBJECT-TYPE
			SYNTAX	INTEGER
			ACCESS	read-only
			STATUS	current
	DESCRIPTION ""
			::= { mbus95 85 }

mbus95VIF28		OBJECT-TYPE
			SYNTAX	INTEGER
			ACCESS	read-only
			STATUS	current
	DESCRIPTION ""
			::= { mbus95 86 }

mbus95Value28		OBJECT-TYPE
			SYNTAX	INTEGER
			ACCESS	read-only
			STATUS	current
	DESCRIPTION ""
			::= { mbus95 87 }

mbus95VIF29		OBJECT-TYPE
			SYNTAX	INTEGER
			ACCESS	read-only
			STATUS	current
	DESCRIPTION ""
			::= { mbus95 88 }

mbus95Value29		OBJECT-TYPE
			SYNTAX	INTEGER
			ACCESS	read-only
			STATUS	current
	DESCRIPTION ""
			::= { mbus95 89 }

mbus95VIF2A		OBJECT-TYPE
			SYNTAX	INTEGER
			ACCESS	read-only
			STATUS	current
	DESCRIPTION ""
			::= { mbus95 90 }

mbus95Value2A		OBJECT-TYPE
			SYNTAX	INTEGER
			ACCESS	read-only
			STATUS	current
	DESCRIPTION ""
			::= { mbus95 91 }

mbus95VIF2B		OBJECT-TYPE
			SYNTAX	INTEGER
			ACCESS	read-only
			STATUS	current
	DESCRIPTION ""
			::= { mbus95 92 }

mbus95Value2B		OBJECT-TYPE
			SYNTAX	INTEGER
			ACCESS	read-only
			STATUS	current
	DESCRIPTION ""
			::= { mbus95 93 }

mbus95VIF2C		OBJECT-TYPE
			SYNTAX	INTEGER
			ACCESS	read-only
			STATUS	current
	DESCRIPTION ""
			::= { mbus95 94 }

mbus95Value2C		OBJECT-TYPE
			SYNTAX	INTEGER
			ACCESS	read-only
			STATUS	current
	DESCRIPTION ""
			::= { mbus95 95 }

mbus95VIF2D		OBJECT-TYPE
			SYNTAX	INTEGER
			ACCESS	read-only
			STATUS	current
	DESCRIPTION ""
			::= { mbus95 96 }

mbus95Value2D		OBJECT-TYPE
			SYNTAX	INTEGER
			ACCESS	read-only
			STATUS	current
	DESCRIPTION ""
			::= { mbus95 97 }

mbus95VIF2E		OBJECT-TYPE
			SYNTAX	INTEGER
			ACCESS	read-only
			STATUS	current
	DESCRIPTION ""
			::= { mbus95 98 }

mbus95Value2E		OBJECT-TYPE
			SYNTAX	INTEGER
			ACCESS	read-only
			STATUS	current
	DESCRIPTION ""
			::= { mbus95 99 }

mbus95VIF2F		OBJECT-TYPE
			SYNTAX	INTEGER
			ACCESS	read-only
			STATUS	current
	DESCRIPTION ""
			::= { mbus95 100 }

mbus95Value2F		OBJECT-TYPE
			SYNTAX	INTEGER
			ACCESS	read-only
			STATUS	current
	DESCRIPTION ""
			::= { mbus95 101 }

mbus96			OBJECT IDENTIFIER ::= { mbus 150 }

mbus96IdNumber		OBJECT-TYPE
			SYNTAX	Gauge
			ACCESS	read-only
			STATUS	current
	DESCRIPTION ""
			::= { mbus96 1 }

mbus96Manufacturer	OBJECT-TYPE
			SYNTAX	Gauge
			ACCESS	read-only
			STATUS	current
	DESCRIPTION ""
			::= { mbus96 2 }

mbus96Version		OBJECT-TYPE
			SYNTAX	Gauge
			ACCESS	read-only
			STATUS	current
	DESCRIPTION ""
			::= { mbus96 3 }

mbus96Medium		OBJECT-TYPE
			SYNTAX	Gauge
			ACCESS	read-only
			STATUS	current
	DESCRIPTION ""
			::= { mbus96 4 }

mbus96Status		OBJECT-TYPE
			SYNTAX	Gauge
			ACCESS	read-only
			STATUS	current
	DESCRIPTION ""
			::= { mbus96 5 }

mbus96VIF00		OBJECT-TYPE
			SYNTAX	INTEGER
			ACCESS	read-only
			STATUS	current
	DESCRIPTION ""
			::= { mbus96 6 }

mbus96Value00		OBJECT-TYPE
			SYNTAX	INTEGER
			ACCESS	read-only
			STATUS	current
	DESCRIPTION ""
			::= { mbus96 7 }

mbus96VIF01		OBJECT-TYPE
			SYNTAX	INTEGER
			ACCESS	read-only
			STATUS	current
	DESCRIPTION ""
			::= { mbus96 8 }

mbus96Value01		OBJECT-TYPE
			SYNTAX	INTEGER
			ACCESS	read-only
			STATUS	current
	DESCRIPTION ""
			::= { mbus96 9 }

mbus96VIF02		OBJECT-TYPE
			SYNTAX	INTEGER
			ACCESS	read-only
			STATUS	current
	DESCRIPTION ""
			::= { mbus96 10 }

mbus96Value02		OBJECT-TYPE
			SYNTAX	INTEGER
			ACCESS	read-only
			STATUS	current
	DESCRIPTION ""
			::= { mbus96 11 }

mbus96VIF03		OBJECT-TYPE
			SYNTAX	INTEGER
			ACCESS	read-only
			STATUS	current
	DESCRIPTION ""
			::= { mbus96 12 }

mbus96Value03		OBJECT-TYPE
			SYNTAX	INTEGER
			ACCESS	read-only
			STATUS	current
	DESCRIPTION ""
			::= { mbus96 13 }

mbus96VIF04		OBJECT-TYPE
			SYNTAX	INTEGER
			ACCESS	read-only
			STATUS	current
	DESCRIPTION ""
			::= { mbus96 14 }

mbus96Value04		OBJECT-TYPE
			SYNTAX	INTEGER
			ACCESS	read-only
			STATUS	current
	DESCRIPTION ""
			::= { mbus96 15 }

mbus96VIF05		OBJECT-TYPE
			SYNTAX	INTEGER
			ACCESS	read-only
			STATUS	current
	DESCRIPTION ""
			::= { mbus96 16 }

mbus96Value05		OBJECT-TYPE
			SYNTAX	INTEGER
			ACCESS	read-only
			STATUS	current
	DESCRIPTION ""
			::= { mbus96 17 }

mbus96VIF06		OBJECT-TYPE
			SYNTAX	INTEGER
			ACCESS	read-only
			STATUS	current
	DESCRIPTION ""
			::= { mbus96 18 }

mbus96Value06		OBJECT-TYPE
			SYNTAX	INTEGER
			ACCESS	read-only
			STATUS	current
	DESCRIPTION ""
			::= { mbus96 19 }

mbus96VIF07		OBJECT-TYPE
			SYNTAX	INTEGER
			ACCESS	read-only
			STATUS	current
	DESCRIPTION ""
			::= { mbus96 20 }

mbus96Value07		OBJECT-TYPE
			SYNTAX	INTEGER
			ACCESS	read-only
			STATUS	current
	DESCRIPTION ""
			::= { mbus96 21 }

mbus96VIF08		OBJECT-TYPE
			SYNTAX	INTEGER
			ACCESS	read-only
			STATUS	current
	DESCRIPTION ""
			::= { mbus96 22 }

mbus96Value08		OBJECT-TYPE
			SYNTAX	INTEGER
			ACCESS	read-only
			STATUS	current
	DESCRIPTION ""
			::= { mbus96 23 }

mbus96VIF09		OBJECT-TYPE
			SYNTAX	INTEGER
			ACCESS	read-only
			STATUS	current
	DESCRIPTION ""
			::= { mbus96 24 }

mbus96Value09		OBJECT-TYPE
			SYNTAX	INTEGER
			ACCESS	read-only
			STATUS	current
	DESCRIPTION ""
			::= { mbus96 25 }

mbus96VIF0A		OBJECT-TYPE
			SYNTAX	INTEGER
			ACCESS	read-only
			STATUS	current
	DESCRIPTION ""
			::= { mbus96 26 }

mbus96Value0A		OBJECT-TYPE
			SYNTAX	INTEGER
			ACCESS	read-only
			STATUS	current
	DESCRIPTION ""
			::= { mbus96 27 }

mbus96VIF0B		OBJECT-TYPE
			SYNTAX	INTEGER
			ACCESS	read-only
			STATUS	current
	DESCRIPTION ""
			::= { mbus96 28 }

mbus96Value0B		OBJECT-TYPE
			SYNTAX	INTEGER
			ACCESS	read-only
			STATUS	current
	DESCRIPTION ""
			::= { mbus96 29 }

mbus96VIF0C		OBJECT-TYPE
			SYNTAX	INTEGER
			ACCESS	read-only
			STATUS	current
	DESCRIPTION ""
			::= { mbus96 30 }

mbus96Value0C		OBJECT-TYPE
			SYNTAX	INTEGER
			ACCESS	read-only
			STATUS	current
	DESCRIPTION ""
			::= { mbus96 31 }

mbus96VIF0D		OBJECT-TYPE
			SYNTAX	INTEGER
			ACCESS	read-only
			STATUS	current
	DESCRIPTION ""
			::= { mbus96 32 }

mbus96Value0D		OBJECT-TYPE
			SYNTAX	INTEGER
			ACCESS	read-only
			STATUS	current
	DESCRIPTION ""
			::= { mbus96 33 }

mbus96VIF0E		OBJECT-TYPE
			SYNTAX	INTEGER
			ACCESS	read-only
			STATUS	current
	DESCRIPTION ""
			::= { mbus96 34 }

mbus96Value0E		OBJECT-TYPE
			SYNTAX	INTEGER
			ACCESS	read-only
			STATUS	current
	DESCRIPTION ""
			::= { mbus96 35 }

mbus96VIF0F		OBJECT-TYPE
			SYNTAX	INTEGER
			ACCESS	read-only
			STATUS	current
	DESCRIPTION ""
			::= { mbus96 36 }

mbus96Value0F		OBJECT-TYPE
			SYNTAX	INTEGER
			ACCESS	read-only
			STATUS	current
	DESCRIPTION ""
			::= { mbus96 37 }

mbus96VIF10		OBJECT-TYPE
			SYNTAX	INTEGER
			ACCESS	read-only
			STATUS	current
	DESCRIPTION ""
			::= { mbus96 38 }

mbus96Value10		OBJECT-TYPE
			SYNTAX	INTEGER
			ACCESS	read-only
			STATUS	current
	DESCRIPTION ""
			::= { mbus96 39 }

mbus96VIF11		OBJECT-TYPE
			SYNTAX	INTEGER
			ACCESS	read-only
			STATUS	current
	DESCRIPTION ""
			::= { mbus96 40 }

mbus96Value11		OBJECT-TYPE
			SYNTAX	INTEGER
			ACCESS	read-only
			STATUS	current
	DESCRIPTION ""
			::= { mbus96 41 }

mbus96VIF12		OBJECT-TYPE
			SYNTAX	INTEGER
			ACCESS	read-only
			STATUS	current
	DESCRIPTION ""
			::= { mbus96 42 }

mbus96Value12		OBJECT-TYPE
			SYNTAX	INTEGER
			ACCESS	read-only
			STATUS	current
	DESCRIPTION ""
			::= { mbus96 43 }

mbus96VIF13		OBJECT-TYPE
			SYNTAX	INTEGER
			ACCESS	read-only
			STATUS	current
	DESCRIPTION ""
			::= { mbus96 44 }

mbus96Value13		OBJECT-TYPE
			SYNTAX	INTEGER
			ACCESS	read-only
			STATUS	current
	DESCRIPTION ""
			::= { mbus96 45 }

mbus96VIF14		OBJECT-TYPE
			SYNTAX	INTEGER
			ACCESS	read-only
			STATUS	current
	DESCRIPTION ""
			::= { mbus96 46 }

mbus96Value14		OBJECT-TYPE
			SYNTAX	INTEGER
			ACCESS	read-only
			STATUS	current
	DESCRIPTION ""
			::= { mbus96 47 }

mbus96VIF15		OBJECT-TYPE
			SYNTAX	INTEGER
			ACCESS	read-only
			STATUS	current
	DESCRIPTION ""
			::= { mbus96 48 }

mbus96Value15		OBJECT-TYPE
			SYNTAX	INTEGER
			ACCESS	read-only
			STATUS	current
	DESCRIPTION ""
			::= { mbus96 49 }

mbus96VIF16		OBJECT-TYPE
			SYNTAX	INTEGER
			ACCESS	read-only
			STATUS	current
	DESCRIPTION ""
			::= { mbus96 50 }

mbus96Value16		OBJECT-TYPE
			SYNTAX	INTEGER
			ACCESS	read-only
			STATUS	current
	DESCRIPTION ""
			::= { mbus96 51 }

mbus96VIF17		OBJECT-TYPE
			SYNTAX	INTEGER
			ACCESS	read-only
			STATUS	current
	DESCRIPTION ""
			::= { mbus96 52 }

mbus96Value17		OBJECT-TYPE
			SYNTAX	INTEGER
			ACCESS	read-only
			STATUS	current
	DESCRIPTION ""
			::= { mbus96 53 }

mbus96VIF18		OBJECT-TYPE
			SYNTAX	INTEGER
			ACCESS	read-only
			STATUS	current
	DESCRIPTION ""
			::= { mbus96 54 }

mbus96Value18		OBJECT-TYPE
			SYNTAX	INTEGER
			ACCESS	read-only
			STATUS	current
	DESCRIPTION ""
			::= { mbus96 55 }

mbus96VIF19		OBJECT-TYPE
			SYNTAX	INTEGER
			ACCESS	read-only
			STATUS	current
	DESCRIPTION ""
			::= { mbus96 56 }

mbus96Value19		OBJECT-TYPE
			SYNTAX	INTEGER
			ACCESS	read-only
			STATUS	current
	DESCRIPTION ""
			::= { mbus96 57 }

mbus96VIF1A		OBJECT-TYPE
			SYNTAX	INTEGER
			ACCESS	read-only
			STATUS	current
	DESCRIPTION ""
			::= { mbus96 58 }

mbus96Value1A		OBJECT-TYPE
			SYNTAX	INTEGER
			ACCESS	read-only
			STATUS	current
	DESCRIPTION ""
			::= { mbus96 59 }

mbus96VIF1B		OBJECT-TYPE
			SYNTAX	INTEGER
			ACCESS	read-only
			STATUS	current
	DESCRIPTION ""
			::= { mbus96 60 }

mbus96Value1B		OBJECT-TYPE
			SYNTAX	INTEGER
			ACCESS	read-only
			STATUS	current
	DESCRIPTION ""
			::= { mbus96 61 }

mbus96VIF1C		OBJECT-TYPE
			SYNTAX	INTEGER
			ACCESS	read-only
			STATUS	current
	DESCRIPTION ""
			::= { mbus96 62 }

mbus96Value1C		OBJECT-TYPE
			SYNTAX	INTEGER
			ACCESS	read-only
			STATUS	current
	DESCRIPTION ""
			::= { mbus96 63 }

mbus96VIF1D		OBJECT-TYPE
			SYNTAX	INTEGER
			ACCESS	read-only
			STATUS	current
	DESCRIPTION ""
			::= { mbus96 64 }

mbus96Value1D		OBJECT-TYPE
			SYNTAX	INTEGER
			ACCESS	read-only
			STATUS	current
	DESCRIPTION ""
			::= { mbus96 65 }

mbus96VIF1E		OBJECT-TYPE
			SYNTAX	INTEGER
			ACCESS	read-only
			STATUS	current
	DESCRIPTION ""
			::= { mbus96 66 }

mbus96Value1E		OBJECT-TYPE
			SYNTAX	INTEGER
			ACCESS	read-only
			STATUS	current
	DESCRIPTION ""
			::= { mbus96 67 }

mbus96VIF1F		OBJECT-TYPE
			SYNTAX	INTEGER
			ACCESS	read-only
			STATUS	current
	DESCRIPTION ""
			::= { mbus96 68 }

mbus96Value1F		OBJECT-TYPE
			SYNTAX	INTEGER
			ACCESS	read-only
			STATUS	current
	DESCRIPTION ""
			::= { mbus96 69 }

mbus96VIF20		OBJECT-TYPE
			SYNTAX	INTEGER
			ACCESS	read-only
			STATUS	current
	DESCRIPTION ""
			::= { mbus96 70 }

mbus96Value20		OBJECT-TYPE
			SYNTAX	INTEGER
			ACCESS	read-only
			STATUS	current
	DESCRIPTION ""
			::= { mbus96 71 }

mbus96VIF21		OBJECT-TYPE
			SYNTAX	INTEGER
			ACCESS	read-only
			STATUS	current
	DESCRIPTION ""
			::= { mbus96 72 }

mbus96Value21		OBJECT-TYPE
			SYNTAX	INTEGER
			ACCESS	read-only
			STATUS	current
	DESCRIPTION ""
			::= { mbus96 73 }

mbus96VIF22		OBJECT-TYPE
			SYNTAX	INTEGER
			ACCESS	read-only
			STATUS	current
	DESCRIPTION ""
			::= { mbus96 74 }

mbus96Value22		OBJECT-TYPE
			SYNTAX	INTEGER
			ACCESS	read-only
			STATUS	current
	DESCRIPTION ""
			::= { mbus96 75 }

mbus96VIF23		OBJECT-TYPE
			SYNTAX	INTEGER
			ACCESS	read-only
			STATUS	current
	DESCRIPTION ""
			::= { mbus96 76 }

mbus96Value23		OBJECT-TYPE
			SYNTAX	INTEGER
			ACCESS	read-only
			STATUS	current
	DESCRIPTION ""
			::= { mbus96 77 }

mbus96VIF24		OBJECT-TYPE
			SYNTAX	INTEGER
			ACCESS	read-only
			STATUS	current
	DESCRIPTION ""
			::= { mbus96 78 }

mbus96Value24		OBJECT-TYPE
			SYNTAX	INTEGER
			ACCESS	read-only
			STATUS	current
	DESCRIPTION ""
			::= { mbus96 79 }

mbus96VIF25		OBJECT-TYPE
			SYNTAX	INTEGER
			ACCESS	read-only
			STATUS	current
	DESCRIPTION ""
			::= { mbus96 80 }

mbus96Value25		OBJECT-TYPE
			SYNTAX	INTEGER
			ACCESS	read-only
			STATUS	current
	DESCRIPTION ""
			::= { mbus96 81 }

mbus96VIF26		OBJECT-TYPE
			SYNTAX	INTEGER
			ACCESS	read-only
			STATUS	current
	DESCRIPTION ""
			::= { mbus96 82 }

mbus96Value26		OBJECT-TYPE
			SYNTAX	INTEGER
			ACCESS	read-only
			STATUS	current
	DESCRIPTION ""
			::= { mbus96 83 }

mbus96VIF27		OBJECT-TYPE
			SYNTAX	INTEGER
			ACCESS	read-only
			STATUS	current
	DESCRIPTION ""
			::= { mbus96 84 }

mbus96Value27		OBJECT-TYPE
			SYNTAX	INTEGER
			ACCESS	read-only
			STATUS	current
	DESCRIPTION ""
			::= { mbus96 85 }

mbus96VIF28		OBJECT-TYPE
			SYNTAX	INTEGER
			ACCESS	read-only
			STATUS	current
	DESCRIPTION ""
			::= { mbus96 86 }

mbus96Value28		OBJECT-TYPE
			SYNTAX	INTEGER
			ACCESS	read-only
			STATUS	current
	DESCRIPTION ""
			::= { mbus96 87 }

mbus96VIF29		OBJECT-TYPE
			SYNTAX	INTEGER
			ACCESS	read-only
			STATUS	current
	DESCRIPTION ""
			::= { mbus96 88 }

mbus96Value29		OBJECT-TYPE
			SYNTAX	INTEGER
			ACCESS	read-only
			STATUS	current
	DESCRIPTION ""
			::= { mbus96 89 }

mbus96VIF2A		OBJECT-TYPE
			SYNTAX	INTEGER
			ACCESS	read-only
			STATUS	current
	DESCRIPTION ""
			::= { mbus96 90 }

mbus96Value2A		OBJECT-TYPE
			SYNTAX	INTEGER
			ACCESS	read-only
			STATUS	current
	DESCRIPTION ""
			::= { mbus96 91 }

mbus96VIF2B		OBJECT-TYPE
			SYNTAX	INTEGER
			ACCESS	read-only
			STATUS	current
	DESCRIPTION ""
			::= { mbus96 92 }

mbus96Value2B		OBJECT-TYPE
			SYNTAX	INTEGER
			ACCESS	read-only
			STATUS	current
	DESCRIPTION ""
			::= { mbus96 93 }

mbus96VIF2C		OBJECT-TYPE
			SYNTAX	INTEGER
			ACCESS	read-only
			STATUS	current
	DESCRIPTION ""
			::= { mbus96 94 }

mbus96Value2C		OBJECT-TYPE
			SYNTAX	INTEGER
			ACCESS	read-only
			STATUS	current
	DESCRIPTION ""
			::= { mbus96 95 }

mbus96VIF2D		OBJECT-TYPE
			SYNTAX	INTEGER
			ACCESS	read-only
			STATUS	current
	DESCRIPTION ""
			::= { mbus96 96 }

mbus96Value2D		OBJECT-TYPE
			SYNTAX	INTEGER
			ACCESS	read-only
			STATUS	current
	DESCRIPTION ""
			::= { mbus96 97 }

mbus96VIF2E		OBJECT-TYPE
			SYNTAX	INTEGER
			ACCESS	read-only
			STATUS	current
	DESCRIPTION ""
			::= { mbus96 98 }

mbus96Value2E		OBJECT-TYPE
			SYNTAX	INTEGER
			ACCESS	read-only
			STATUS	current
	DESCRIPTION ""
			::= { mbus96 99 }

mbus96VIF2F		OBJECT-TYPE
			SYNTAX	INTEGER
			ACCESS	read-only
			STATUS	current
	DESCRIPTION ""
			::= { mbus96 100 }

mbus96Value2F		OBJECT-TYPE
			SYNTAX	INTEGER
			ACCESS	read-only
			STATUS	current
	DESCRIPTION ""
			::= { mbus96 101 }

mbus97			OBJECT IDENTIFIER ::= { mbus 151 }

mbus97IdNumber		OBJECT-TYPE
			SYNTAX	Gauge
			ACCESS	read-only
			STATUS	current
	DESCRIPTION ""
			::= { mbus97 1 }

mbus97Manufacturer	OBJECT-TYPE
			SYNTAX	Gauge
			ACCESS	read-only
			STATUS	current
	DESCRIPTION ""
			::= { mbus97 2 }

mbus97Version		OBJECT-TYPE
			SYNTAX	Gauge
			ACCESS	read-only
			STATUS	current
	DESCRIPTION ""
			::= { mbus97 3 }

mbus97Medium		OBJECT-TYPE
			SYNTAX	Gauge
			ACCESS	read-only
			STATUS	current
	DESCRIPTION ""
			::= { mbus97 4 }

mbus97Status		OBJECT-TYPE
			SYNTAX	Gauge
			ACCESS	read-only
			STATUS	current
	DESCRIPTION ""
			::= { mbus97 5 }

mbus97VIF00		OBJECT-TYPE
			SYNTAX	INTEGER
			ACCESS	read-only
			STATUS	current
	DESCRIPTION ""
			::= { mbus97 6 }

mbus97Value00		OBJECT-TYPE
			SYNTAX	INTEGER
			ACCESS	read-only
			STATUS	current
	DESCRIPTION ""
			::= { mbus97 7 }

mbus97VIF01		OBJECT-TYPE
			SYNTAX	INTEGER
			ACCESS	read-only
			STATUS	current
	DESCRIPTION ""
			::= { mbus97 8 }

mbus97Value01		OBJECT-TYPE
			SYNTAX	INTEGER
			ACCESS	read-only
			STATUS	current
	DESCRIPTION ""
			::= { mbus97 9 }

mbus97VIF02		OBJECT-TYPE
			SYNTAX	INTEGER
			ACCESS	read-only
			STATUS	current
	DESCRIPTION ""
			::= { mbus97 10 }

mbus97Value02		OBJECT-TYPE
			SYNTAX	INTEGER
			ACCESS	read-only
			STATUS	current
	DESCRIPTION ""
			::= { mbus97 11 }

mbus97VIF03		OBJECT-TYPE
			SYNTAX	INTEGER
			ACCESS	read-only
			STATUS	current
	DESCRIPTION ""
			::= { mbus97 12 }

mbus97Value03		OBJECT-TYPE
			SYNTAX	INTEGER
			ACCESS	read-only
			STATUS	current
	DESCRIPTION ""
			::= { mbus97 13 }

mbus97VIF04		OBJECT-TYPE
			SYNTAX	INTEGER
			ACCESS	read-only
			STATUS	current
	DESCRIPTION ""
			::= { mbus97 14 }

mbus97Value04		OBJECT-TYPE
			SYNTAX	INTEGER
			ACCESS	read-only
			STATUS	current
	DESCRIPTION ""
			::= { mbus97 15 }

mbus97VIF05		OBJECT-TYPE
			SYNTAX	INTEGER
			ACCESS	read-only
			STATUS	current
	DESCRIPTION ""
			::= { mbus97 16 }

mbus97Value05		OBJECT-TYPE
			SYNTAX	INTEGER
			ACCESS	read-only
			STATUS	current
	DESCRIPTION ""
			::= { mbus97 17 }

mbus97VIF06		OBJECT-TYPE
			SYNTAX	INTEGER
			ACCESS	read-only
			STATUS	current
	DESCRIPTION ""
			::= { mbus97 18 }

mbus97Value06		OBJECT-TYPE
			SYNTAX	INTEGER
			ACCESS	read-only
			STATUS	current
	DESCRIPTION ""
			::= { mbus97 19 }

mbus97VIF07		OBJECT-TYPE
			SYNTAX	INTEGER
			ACCESS	read-only
			STATUS	current
	DESCRIPTION ""
			::= { mbus97 20 }

mbus97Value07		OBJECT-TYPE
			SYNTAX	INTEGER
			ACCESS	read-only
			STATUS	current
	DESCRIPTION ""
			::= { mbus97 21 }

mbus97VIF08		OBJECT-TYPE
			SYNTAX	INTEGER
			ACCESS	read-only
			STATUS	current
	DESCRIPTION ""
			::= { mbus97 22 }

mbus97Value08		OBJECT-TYPE
			SYNTAX	INTEGER
			ACCESS	read-only
			STATUS	current
	DESCRIPTION ""
			::= { mbus97 23 }

mbus97VIF09		OBJECT-TYPE
			SYNTAX	INTEGER
			ACCESS	read-only
			STATUS	current
	DESCRIPTION ""
			::= { mbus97 24 }

mbus97Value09		OBJECT-TYPE
			SYNTAX	INTEGER
			ACCESS	read-only
			STATUS	current
	DESCRIPTION ""
			::= { mbus97 25 }

mbus97VIF0A		OBJECT-TYPE
			SYNTAX	INTEGER
			ACCESS	read-only
			STATUS	current
	DESCRIPTION ""
			::= { mbus97 26 }

mbus97Value0A		OBJECT-TYPE
			SYNTAX	INTEGER
			ACCESS	read-only
			STATUS	current
	DESCRIPTION ""
			::= { mbus97 27 }

mbus97VIF0B		OBJECT-TYPE
			SYNTAX	INTEGER
			ACCESS	read-only
			STATUS	current
	DESCRIPTION ""
			::= { mbus97 28 }

mbus97Value0B		OBJECT-TYPE
			SYNTAX	INTEGER
			ACCESS	read-only
			STATUS	current
	DESCRIPTION ""
			::= { mbus97 29 }

mbus97VIF0C		OBJECT-TYPE
			SYNTAX	INTEGER
			ACCESS	read-only
			STATUS	current
	DESCRIPTION ""
			::= { mbus97 30 }

mbus97Value0C		OBJECT-TYPE
			SYNTAX	INTEGER
			ACCESS	read-only
			STATUS	current
	DESCRIPTION ""
			::= { mbus97 31 }

mbus97VIF0D		OBJECT-TYPE
			SYNTAX	INTEGER
			ACCESS	read-only
			STATUS	current
	DESCRIPTION ""
			::= { mbus97 32 }

mbus97Value0D		OBJECT-TYPE
			SYNTAX	INTEGER
			ACCESS	read-only
			STATUS	current
	DESCRIPTION ""
			::= { mbus97 33 }

mbus97VIF0E		OBJECT-TYPE
			SYNTAX	INTEGER
			ACCESS	read-only
			STATUS	current
	DESCRIPTION ""
			::= { mbus97 34 }

mbus97Value0E		OBJECT-TYPE
			SYNTAX	INTEGER
			ACCESS	read-only
			STATUS	current
	DESCRIPTION ""
			::= { mbus97 35 }

mbus97VIF0F		OBJECT-TYPE
			SYNTAX	INTEGER
			ACCESS	read-only
			STATUS	current
	DESCRIPTION ""
			::= { mbus97 36 }

mbus97Value0F		OBJECT-TYPE
			SYNTAX	INTEGER
			ACCESS	read-only
			STATUS	current
	DESCRIPTION ""
			::= { mbus97 37 }

mbus97VIF10		OBJECT-TYPE
			SYNTAX	INTEGER
			ACCESS	read-only
			STATUS	current
	DESCRIPTION ""
			::= { mbus97 38 }

mbus97Value10		OBJECT-TYPE
			SYNTAX	INTEGER
			ACCESS	read-only
			STATUS	current
	DESCRIPTION ""
			::= { mbus97 39 }

mbus97VIF11		OBJECT-TYPE
			SYNTAX	INTEGER
			ACCESS	read-only
			STATUS	current
	DESCRIPTION ""
			::= { mbus97 40 }

mbus97Value11		OBJECT-TYPE
			SYNTAX	INTEGER
			ACCESS	read-only
			STATUS	current
	DESCRIPTION ""
			::= { mbus97 41 }

mbus97VIF12		OBJECT-TYPE
			SYNTAX	INTEGER
			ACCESS	read-only
			STATUS	current
	DESCRIPTION ""
			::= { mbus97 42 }

mbus97Value12		OBJECT-TYPE
			SYNTAX	INTEGER
			ACCESS	read-only
			STATUS	current
	DESCRIPTION ""
			::= { mbus97 43 }

mbus97VIF13		OBJECT-TYPE
			SYNTAX	INTEGER
			ACCESS	read-only
			STATUS	current
	DESCRIPTION ""
			::= { mbus97 44 }

mbus97Value13		OBJECT-TYPE
			SYNTAX	INTEGER
			ACCESS	read-only
			STATUS	current
	DESCRIPTION ""
			::= { mbus97 45 }

mbus97VIF14		OBJECT-TYPE
			SYNTAX	INTEGER
			ACCESS	read-only
			STATUS	current
	DESCRIPTION ""
			::= { mbus97 46 }

mbus97Value14		OBJECT-TYPE
			SYNTAX	INTEGER
			ACCESS	read-only
			STATUS	current
	DESCRIPTION ""
			::= { mbus97 47 }

mbus97VIF15		OBJECT-TYPE
			SYNTAX	INTEGER
			ACCESS	read-only
			STATUS	current
	DESCRIPTION ""
			::= { mbus97 48 }

mbus97Value15		OBJECT-TYPE
			SYNTAX	INTEGER
			ACCESS	read-only
			STATUS	current
	DESCRIPTION ""
			::= { mbus97 49 }

mbus97VIF16		OBJECT-TYPE
			SYNTAX	INTEGER
			ACCESS	read-only
			STATUS	current
	DESCRIPTION ""
			::= { mbus97 50 }

mbus97Value16		OBJECT-TYPE
			SYNTAX	INTEGER
			ACCESS	read-only
			STATUS	current
	DESCRIPTION ""
			::= { mbus97 51 }

mbus97VIF17		OBJECT-TYPE
			SYNTAX	INTEGER
			ACCESS	read-only
			STATUS	current
	DESCRIPTION ""
			::= { mbus97 52 }

mbus97Value17		OBJECT-TYPE
			SYNTAX	INTEGER
			ACCESS	read-only
			STATUS	current
	DESCRIPTION ""
			::= { mbus97 53 }

mbus97VIF18		OBJECT-TYPE
			SYNTAX	INTEGER
			ACCESS	read-only
			STATUS	current
	DESCRIPTION ""
			::= { mbus97 54 }

mbus97Value18		OBJECT-TYPE
			SYNTAX	INTEGER
			ACCESS	read-only
			STATUS	current
	DESCRIPTION ""
			::= { mbus97 55 }

mbus97VIF19		OBJECT-TYPE
			SYNTAX	INTEGER
			ACCESS	read-only
			STATUS	current
	DESCRIPTION ""
			::= { mbus97 56 }

mbus97Value19		OBJECT-TYPE
			SYNTAX	INTEGER
			ACCESS	read-only
			STATUS	current
	DESCRIPTION ""
			::= { mbus97 57 }

mbus97VIF1A		OBJECT-TYPE
			SYNTAX	INTEGER
			ACCESS	read-only
			STATUS	current
	DESCRIPTION ""
			::= { mbus97 58 }

mbus97Value1A		OBJECT-TYPE
			SYNTAX	INTEGER
			ACCESS	read-only
			STATUS	current
	DESCRIPTION ""
			::= { mbus97 59 }

mbus97VIF1B		OBJECT-TYPE
			SYNTAX	INTEGER
			ACCESS	read-only
			STATUS	current
	DESCRIPTION ""
			::= { mbus97 60 }

mbus97Value1B		OBJECT-TYPE
			SYNTAX	INTEGER
			ACCESS	read-only
			STATUS	current
	DESCRIPTION ""
			::= { mbus97 61 }

mbus97VIF1C		OBJECT-TYPE
			SYNTAX	INTEGER
			ACCESS	read-only
			STATUS	current
	DESCRIPTION ""
			::= { mbus97 62 }

mbus97Value1C		OBJECT-TYPE
			SYNTAX	INTEGER
			ACCESS	read-only
			STATUS	current
	DESCRIPTION ""
			::= { mbus97 63 }

mbus97VIF1D		OBJECT-TYPE
			SYNTAX	INTEGER
			ACCESS	read-only
			STATUS	current
	DESCRIPTION ""
			::= { mbus97 64 }

mbus97Value1D		OBJECT-TYPE
			SYNTAX	INTEGER
			ACCESS	read-only
			STATUS	current
	DESCRIPTION ""
			::= { mbus97 65 }

mbus97VIF1E		OBJECT-TYPE
			SYNTAX	INTEGER
			ACCESS	read-only
			STATUS	current
	DESCRIPTION ""
			::= { mbus97 66 }

mbus97Value1E		OBJECT-TYPE
			SYNTAX	INTEGER
			ACCESS	read-only
			STATUS	current
	DESCRIPTION ""
			::= { mbus97 67 }

mbus97VIF1F		OBJECT-TYPE
			SYNTAX	INTEGER
			ACCESS	read-only
			STATUS	current
	DESCRIPTION ""
			::= { mbus97 68 }

mbus97Value1F		OBJECT-TYPE
			SYNTAX	INTEGER
			ACCESS	read-only
			STATUS	current
	DESCRIPTION ""
			::= { mbus97 69 }

mbus97VIF20		OBJECT-TYPE
			SYNTAX	INTEGER
			ACCESS	read-only
			STATUS	current
	DESCRIPTION ""
			::= { mbus97 70 }

mbus97Value20		OBJECT-TYPE
			SYNTAX	INTEGER
			ACCESS	read-only
			STATUS	current
	DESCRIPTION ""
			::= { mbus97 71 }

mbus97VIF21		OBJECT-TYPE
			SYNTAX	INTEGER
			ACCESS	read-only
			STATUS	current
	DESCRIPTION ""
			::= { mbus97 72 }

mbus97Value21		OBJECT-TYPE
			SYNTAX	INTEGER
			ACCESS	read-only
			STATUS	current
	DESCRIPTION ""
			::= { mbus97 73 }

mbus97VIF22		OBJECT-TYPE
			SYNTAX	INTEGER
			ACCESS	read-only
			STATUS	current
	DESCRIPTION ""
			::= { mbus97 74 }

mbus97Value22		OBJECT-TYPE
			SYNTAX	INTEGER
			ACCESS	read-only
			STATUS	current
	DESCRIPTION ""
			::= { mbus97 75 }

mbus97VIF23		OBJECT-TYPE
			SYNTAX	INTEGER
			ACCESS	read-only
			STATUS	current
	DESCRIPTION ""
			::= { mbus97 76 }

mbus97Value23		OBJECT-TYPE
			SYNTAX	INTEGER
			ACCESS	read-only
			STATUS	current
	DESCRIPTION ""
			::= { mbus97 77 }

mbus97VIF24		OBJECT-TYPE
			SYNTAX	INTEGER
			ACCESS	read-only
			STATUS	current
	DESCRIPTION ""
			::= { mbus97 78 }

mbus97Value24		OBJECT-TYPE
			SYNTAX	INTEGER
			ACCESS	read-only
			STATUS	current
	DESCRIPTION ""
			::= { mbus97 79 }

mbus97VIF25		OBJECT-TYPE
			SYNTAX	INTEGER
			ACCESS	read-only
			STATUS	current
	DESCRIPTION ""
			::= { mbus97 80 }

mbus97Value25		OBJECT-TYPE
			SYNTAX	INTEGER
			ACCESS	read-only
			STATUS	current
	DESCRIPTION ""
			::= { mbus97 81 }

mbus97VIF26		OBJECT-TYPE
			SYNTAX	INTEGER
			ACCESS	read-only
			STATUS	current
	DESCRIPTION ""
			::= { mbus97 82 }

mbus97Value26		OBJECT-TYPE
			SYNTAX	INTEGER
			ACCESS	read-only
			STATUS	current
	DESCRIPTION ""
			::= { mbus97 83 }

mbus97VIF27		OBJECT-TYPE
			SYNTAX	INTEGER
			ACCESS	read-only
			STATUS	current
	DESCRIPTION ""
			::= { mbus97 84 }

mbus97Value27		OBJECT-TYPE
			SYNTAX	INTEGER
			ACCESS	read-only
			STATUS	current
	DESCRIPTION ""
			::= { mbus97 85 }

mbus97VIF28		OBJECT-TYPE
			SYNTAX	INTEGER
			ACCESS	read-only
			STATUS	current
	DESCRIPTION ""
			::= { mbus97 86 }

mbus97Value28		OBJECT-TYPE
			SYNTAX	INTEGER
			ACCESS	read-only
			STATUS	current
	DESCRIPTION ""
			::= { mbus97 87 }

mbus97VIF29		OBJECT-TYPE
			SYNTAX	INTEGER
			ACCESS	read-only
			STATUS	current
	DESCRIPTION ""
			::= { mbus97 88 }

mbus97Value29		OBJECT-TYPE
			SYNTAX	INTEGER
			ACCESS	read-only
			STATUS	current
	DESCRIPTION ""
			::= { mbus97 89 }

mbus97VIF2A		OBJECT-TYPE
			SYNTAX	INTEGER
			ACCESS	read-only
			STATUS	current
	DESCRIPTION ""
			::= { mbus97 90 }

mbus97Value2A		OBJECT-TYPE
			SYNTAX	INTEGER
			ACCESS	read-only
			STATUS	current
	DESCRIPTION ""
			::= { mbus97 91 }

mbus97VIF2B		OBJECT-TYPE
			SYNTAX	INTEGER
			ACCESS	read-only
			STATUS	current
	DESCRIPTION ""
			::= { mbus97 92 }

mbus97Value2B		OBJECT-TYPE
			SYNTAX	INTEGER
			ACCESS	read-only
			STATUS	current
	DESCRIPTION ""
			::= { mbus97 93 }

mbus97VIF2C		OBJECT-TYPE
			SYNTAX	INTEGER
			ACCESS	read-only
			STATUS	current
	DESCRIPTION ""
			::= { mbus97 94 }

mbus97Value2C		OBJECT-TYPE
			SYNTAX	INTEGER
			ACCESS	read-only
			STATUS	current
	DESCRIPTION ""
			::= { mbus97 95 }

mbus97VIF2D		OBJECT-TYPE
			SYNTAX	INTEGER
			ACCESS	read-only
			STATUS	current
	DESCRIPTION ""
			::= { mbus97 96 }

mbus97Value2D		OBJECT-TYPE
			SYNTAX	INTEGER
			ACCESS	read-only
			STATUS	current
	DESCRIPTION ""
			::= { mbus97 97 }

mbus97VIF2E		OBJECT-TYPE
			SYNTAX	INTEGER
			ACCESS	read-only
			STATUS	current
	DESCRIPTION ""
			::= { mbus97 98 }

mbus97Value2E		OBJECT-TYPE
			SYNTAX	INTEGER
			ACCESS	read-only
			STATUS	current
	DESCRIPTION ""
			::= { mbus97 99 }

mbus97VIF2F		OBJECT-TYPE
			SYNTAX	INTEGER
			ACCESS	read-only
			STATUS	current
	DESCRIPTION ""
			::= { mbus97 100 }

mbus97Value2F		OBJECT-TYPE
			SYNTAX	INTEGER
			ACCESS	read-only
			STATUS	current
	DESCRIPTION ""
			::= { mbus97 101 }

mbus98			OBJECT IDENTIFIER ::= { mbus 152 }

mbus98IdNumber		OBJECT-TYPE
			SYNTAX	Gauge
			ACCESS	read-only
			STATUS	current
	DESCRIPTION ""
			::= { mbus98 1 }

mbus98Manufacturer	OBJECT-TYPE
			SYNTAX	Gauge
			ACCESS	read-only
			STATUS	current
	DESCRIPTION ""
			::= { mbus98 2 }

mbus98Version		OBJECT-TYPE
			SYNTAX	Gauge
			ACCESS	read-only
			STATUS	current
	DESCRIPTION ""
			::= { mbus98 3 }

mbus98Medium		OBJECT-TYPE
			SYNTAX	Gauge
			ACCESS	read-only
			STATUS	current
	DESCRIPTION ""
			::= { mbus98 4 }

mbus98Status		OBJECT-TYPE
			SYNTAX	Gauge
			ACCESS	read-only
			STATUS	current
	DESCRIPTION ""
			::= { mbus98 5 }

mbus98VIF00		OBJECT-TYPE
			SYNTAX	INTEGER
			ACCESS	read-only
			STATUS	current
	DESCRIPTION ""
			::= { mbus98 6 }

mbus98Value00		OBJECT-TYPE
			SYNTAX	INTEGER
			ACCESS	read-only
			STATUS	current
	DESCRIPTION ""
			::= { mbus98 7 }

mbus98VIF01		OBJECT-TYPE
			SYNTAX	INTEGER
			ACCESS	read-only
			STATUS	current
	DESCRIPTION ""
			::= { mbus98 8 }

mbus98Value01		OBJECT-TYPE
			SYNTAX	INTEGER
			ACCESS	read-only
			STATUS	current
	DESCRIPTION ""
			::= { mbus98 9 }

mbus98VIF02		OBJECT-TYPE
			SYNTAX	INTEGER
			ACCESS	read-only
			STATUS	current
	DESCRIPTION ""
			::= { mbus98 10 }

mbus98Value02		OBJECT-TYPE
			SYNTAX	INTEGER
			ACCESS	read-only
			STATUS	current
	DESCRIPTION ""
			::= { mbus98 11 }

mbus98VIF03		OBJECT-TYPE
			SYNTAX	INTEGER
			ACCESS	read-only
			STATUS	current
	DESCRIPTION ""
			::= { mbus98 12 }

mbus98Value03		OBJECT-TYPE
			SYNTAX	INTEGER
			ACCESS	read-only
			STATUS	current
	DESCRIPTION ""
			::= { mbus98 13 }

mbus98VIF04		OBJECT-TYPE
			SYNTAX	INTEGER
			ACCESS	read-only
			STATUS	current
	DESCRIPTION ""
			::= { mbus98 14 }

mbus98Value04		OBJECT-TYPE
			SYNTAX	INTEGER
			ACCESS	read-only
			STATUS	current
	DESCRIPTION ""
			::= { mbus98 15 }

mbus98VIF05		OBJECT-TYPE
			SYNTAX	INTEGER
			ACCESS	read-only
			STATUS	current
	DESCRIPTION ""
			::= { mbus98 16 }

mbus98Value05		OBJECT-TYPE
			SYNTAX	INTEGER
			ACCESS	read-only
			STATUS	current
	DESCRIPTION ""
			::= { mbus98 17 }

mbus98VIF06		OBJECT-TYPE
			SYNTAX	INTEGER
			ACCESS	read-only
			STATUS	current
	DESCRIPTION ""
			::= { mbus98 18 }

mbus98Value06		OBJECT-TYPE
			SYNTAX	INTEGER
			ACCESS	read-only
			STATUS	current
	DESCRIPTION ""
			::= { mbus98 19 }

mbus98VIF07		OBJECT-TYPE
			SYNTAX	INTEGER
			ACCESS	read-only
			STATUS	current
	DESCRIPTION ""
			::= { mbus98 20 }

mbus98Value07		OBJECT-TYPE
			SYNTAX	INTEGER
			ACCESS	read-only
			STATUS	current
	DESCRIPTION ""
			::= { mbus98 21 }

mbus98VIF08		OBJECT-TYPE
			SYNTAX	INTEGER
			ACCESS	read-only
			STATUS	current
	DESCRIPTION ""
			::= { mbus98 22 }

mbus98Value08		OBJECT-TYPE
			SYNTAX	INTEGER
			ACCESS	read-only
			STATUS	current
	DESCRIPTION ""
			::= { mbus98 23 }

mbus98VIF09		OBJECT-TYPE
			SYNTAX	INTEGER
			ACCESS	read-only
			STATUS	current
	DESCRIPTION ""
			::= { mbus98 24 }

mbus98Value09		OBJECT-TYPE
			SYNTAX	INTEGER
			ACCESS	read-only
			STATUS	current
	DESCRIPTION ""
			::= { mbus98 25 }

mbus98VIF0A		OBJECT-TYPE
			SYNTAX	INTEGER
			ACCESS	read-only
			STATUS	current
	DESCRIPTION ""
			::= { mbus98 26 }

mbus98Value0A		OBJECT-TYPE
			SYNTAX	INTEGER
			ACCESS	read-only
			STATUS	current
	DESCRIPTION ""
			::= { mbus98 27 }

mbus98VIF0B		OBJECT-TYPE
			SYNTAX	INTEGER
			ACCESS	read-only
			STATUS	current
	DESCRIPTION ""
			::= { mbus98 28 }

mbus98Value0B		OBJECT-TYPE
			SYNTAX	INTEGER
			ACCESS	read-only
			STATUS	current
	DESCRIPTION ""
			::= { mbus98 29 }

mbus98VIF0C		OBJECT-TYPE
			SYNTAX	INTEGER
			ACCESS	read-only
			STATUS	current
	DESCRIPTION ""
			::= { mbus98 30 }

mbus98Value0C		OBJECT-TYPE
			SYNTAX	INTEGER
			ACCESS	read-only
			STATUS	current
	DESCRIPTION ""
			::= { mbus98 31 }

mbus98VIF0D		OBJECT-TYPE
			SYNTAX	INTEGER
			ACCESS	read-only
			STATUS	current
	DESCRIPTION ""
			::= { mbus98 32 }

mbus98Value0D		OBJECT-TYPE
			SYNTAX	INTEGER
			ACCESS	read-only
			STATUS	current
	DESCRIPTION ""
			::= { mbus98 33 }

mbus98VIF0E		OBJECT-TYPE
			SYNTAX	INTEGER
			ACCESS	read-only
			STATUS	current
	DESCRIPTION ""
			::= { mbus98 34 }

mbus98Value0E		OBJECT-TYPE
			SYNTAX	INTEGER
			ACCESS	read-only
			STATUS	current
	DESCRIPTION ""
			::= { mbus98 35 }

mbus98VIF0F		OBJECT-TYPE
			SYNTAX	INTEGER
			ACCESS	read-only
			STATUS	current
	DESCRIPTION ""
			::= { mbus98 36 }

mbus98Value0F		OBJECT-TYPE
			SYNTAX	INTEGER
			ACCESS	read-only
			STATUS	current
	DESCRIPTION ""
			::= { mbus98 37 }

mbus98VIF10		OBJECT-TYPE
			SYNTAX	INTEGER
			ACCESS	read-only
			STATUS	current
	DESCRIPTION ""
			::= { mbus98 38 }

mbus98Value10		OBJECT-TYPE
			SYNTAX	INTEGER
			ACCESS	read-only
			STATUS	current
	DESCRIPTION ""
			::= { mbus98 39 }

mbus98VIF11		OBJECT-TYPE
			SYNTAX	INTEGER
			ACCESS	read-only
			STATUS	current
	DESCRIPTION ""
			::= { mbus98 40 }

mbus98Value11		OBJECT-TYPE
			SYNTAX	INTEGER
			ACCESS	read-only
			STATUS	current
	DESCRIPTION ""
			::= { mbus98 41 }

mbus98VIF12		OBJECT-TYPE
			SYNTAX	INTEGER
			ACCESS	read-only
			STATUS	current
	DESCRIPTION ""
			::= { mbus98 42 }

mbus98Value12		OBJECT-TYPE
			SYNTAX	INTEGER
			ACCESS	read-only
			STATUS	current
	DESCRIPTION ""
			::= { mbus98 43 }

mbus98VIF13		OBJECT-TYPE
			SYNTAX	INTEGER
			ACCESS	read-only
			STATUS	current
	DESCRIPTION ""
			::= { mbus98 44 }

mbus98Value13		OBJECT-TYPE
			SYNTAX	INTEGER
			ACCESS	read-only
			STATUS	current
	DESCRIPTION ""
			::= { mbus98 45 }

mbus98VIF14		OBJECT-TYPE
			SYNTAX	INTEGER
			ACCESS	read-only
			STATUS	current
	DESCRIPTION ""
			::= { mbus98 46 }

mbus98Value14		OBJECT-TYPE
			SYNTAX	INTEGER
			ACCESS	read-only
			STATUS	current
	DESCRIPTION ""
			::= { mbus98 47 }

mbus98VIF15		OBJECT-TYPE
			SYNTAX	INTEGER
			ACCESS	read-only
			STATUS	current
	DESCRIPTION ""
			::= { mbus98 48 }

mbus98Value15		OBJECT-TYPE
			SYNTAX	INTEGER
			ACCESS	read-only
			STATUS	current
	DESCRIPTION ""
			::= { mbus98 49 }

mbus98VIF16		OBJECT-TYPE
			SYNTAX	INTEGER
			ACCESS	read-only
			STATUS	current
	DESCRIPTION ""
			::= { mbus98 50 }

mbus98Value16		OBJECT-TYPE
			SYNTAX	INTEGER
			ACCESS	read-only
			STATUS	current
	DESCRIPTION ""
			::= { mbus98 51 }

mbus98VIF17		OBJECT-TYPE
			SYNTAX	INTEGER
			ACCESS	read-only
			STATUS	current
	DESCRIPTION ""
			::= { mbus98 52 }

mbus98Value17		OBJECT-TYPE
			SYNTAX	INTEGER
			ACCESS	read-only
			STATUS	current
	DESCRIPTION ""
			::= { mbus98 53 }

mbus98VIF18		OBJECT-TYPE
			SYNTAX	INTEGER
			ACCESS	read-only
			STATUS	current
	DESCRIPTION ""
			::= { mbus98 54 }

mbus98Value18		OBJECT-TYPE
			SYNTAX	INTEGER
			ACCESS	read-only
			STATUS	current
	DESCRIPTION ""
			::= { mbus98 55 }

mbus98VIF19		OBJECT-TYPE
			SYNTAX	INTEGER
			ACCESS	read-only
			STATUS	current
	DESCRIPTION ""
			::= { mbus98 56 }

mbus98Value19		OBJECT-TYPE
			SYNTAX	INTEGER
			ACCESS	read-only
			STATUS	current
	DESCRIPTION ""
			::= { mbus98 57 }

mbus98VIF1A		OBJECT-TYPE
			SYNTAX	INTEGER
			ACCESS	read-only
			STATUS	current
	DESCRIPTION ""
			::= { mbus98 58 }

mbus98Value1A		OBJECT-TYPE
			SYNTAX	INTEGER
			ACCESS	read-only
			STATUS	current
	DESCRIPTION ""
			::= { mbus98 59 }

mbus98VIF1B		OBJECT-TYPE
			SYNTAX	INTEGER
			ACCESS	read-only
			STATUS	current
	DESCRIPTION ""
			::= { mbus98 60 }

mbus98Value1B		OBJECT-TYPE
			SYNTAX	INTEGER
			ACCESS	read-only
			STATUS	current
	DESCRIPTION ""
			::= { mbus98 61 }

mbus98VIF1C		OBJECT-TYPE
			SYNTAX	INTEGER
			ACCESS	read-only
			STATUS	current
	DESCRIPTION ""
			::= { mbus98 62 }

mbus98Value1C		OBJECT-TYPE
			SYNTAX	INTEGER
			ACCESS	read-only
			STATUS	current
	DESCRIPTION ""
			::= { mbus98 63 }

mbus98VIF1D		OBJECT-TYPE
			SYNTAX	INTEGER
			ACCESS	read-only
			STATUS	current
	DESCRIPTION ""
			::= { mbus98 64 }

mbus98Value1D		OBJECT-TYPE
			SYNTAX	INTEGER
			ACCESS	read-only
			STATUS	current
	DESCRIPTION ""
			::= { mbus98 65 }

mbus98VIF1E		OBJECT-TYPE
			SYNTAX	INTEGER
			ACCESS	read-only
			STATUS	current
	DESCRIPTION ""
			::= { mbus98 66 }

mbus98Value1E		OBJECT-TYPE
			SYNTAX	INTEGER
			ACCESS	read-only
			STATUS	current
	DESCRIPTION ""
			::= { mbus98 67 }

mbus98VIF1F		OBJECT-TYPE
			SYNTAX	INTEGER
			ACCESS	read-only
			STATUS	current
	DESCRIPTION ""
			::= { mbus98 68 }

mbus98Value1F		OBJECT-TYPE
			SYNTAX	INTEGER
			ACCESS	read-only
			STATUS	current
	DESCRIPTION ""
			::= { mbus98 69 }

mbus98VIF20		OBJECT-TYPE
			SYNTAX	INTEGER
			ACCESS	read-only
			STATUS	current
	DESCRIPTION ""
			::= { mbus98 70 }

mbus98Value20		OBJECT-TYPE
			SYNTAX	INTEGER
			ACCESS	read-only
			STATUS	current
	DESCRIPTION ""
			::= { mbus98 71 }

mbus98VIF21		OBJECT-TYPE
			SYNTAX	INTEGER
			ACCESS	read-only
			STATUS	current
	DESCRIPTION ""
			::= { mbus98 72 }

mbus98Value21		OBJECT-TYPE
			SYNTAX	INTEGER
			ACCESS	read-only
			STATUS	current
	DESCRIPTION ""
			::= { mbus98 73 }

mbus98VIF22		OBJECT-TYPE
			SYNTAX	INTEGER
			ACCESS	read-only
			STATUS	current
	DESCRIPTION ""
			::= { mbus98 74 }

mbus98Value22		OBJECT-TYPE
			SYNTAX	INTEGER
			ACCESS	read-only
			STATUS	current
	DESCRIPTION ""
			::= { mbus98 75 }

mbus98VIF23		OBJECT-TYPE
			SYNTAX	INTEGER
			ACCESS	read-only
			STATUS	current
	DESCRIPTION ""
			::= { mbus98 76 }

mbus98Value23		OBJECT-TYPE
			SYNTAX	INTEGER
			ACCESS	read-only
			STATUS	current
	DESCRIPTION ""
			::= { mbus98 77 }

mbus98VIF24		OBJECT-TYPE
			SYNTAX	INTEGER
			ACCESS	read-only
			STATUS	current
	DESCRIPTION ""
			::= { mbus98 78 }

mbus98Value24		OBJECT-TYPE
			SYNTAX	INTEGER
			ACCESS	read-only
			STATUS	current
	DESCRIPTION ""
			::= { mbus98 79 }

mbus98VIF25		OBJECT-TYPE
			SYNTAX	INTEGER
			ACCESS	read-only
			STATUS	current
	DESCRIPTION ""
			::= { mbus98 80 }

mbus98Value25		OBJECT-TYPE
			SYNTAX	INTEGER
			ACCESS	read-only
			STATUS	current
	DESCRIPTION ""
			::= { mbus98 81 }

mbus98VIF26		OBJECT-TYPE
			SYNTAX	INTEGER
			ACCESS	read-only
			STATUS	current
	DESCRIPTION ""
			::= { mbus98 82 }

mbus98Value26		OBJECT-TYPE
			SYNTAX	INTEGER
			ACCESS	read-only
			STATUS	current
	DESCRIPTION ""
			::= { mbus98 83 }

mbus98VIF27		OBJECT-TYPE
			SYNTAX	INTEGER
			ACCESS	read-only
			STATUS	current
	DESCRIPTION ""
			::= { mbus98 84 }

mbus98Value27		OBJECT-TYPE
			SYNTAX	INTEGER
			ACCESS	read-only
			STATUS	current
	DESCRIPTION ""
			::= { mbus98 85 }

mbus98VIF28		OBJECT-TYPE
			SYNTAX	INTEGER
			ACCESS	read-only
			STATUS	current
	DESCRIPTION ""
			::= { mbus98 86 }

mbus98Value28		OBJECT-TYPE
			SYNTAX	INTEGER
			ACCESS	read-only
			STATUS	current
	DESCRIPTION ""
			::= { mbus98 87 }

mbus98VIF29		OBJECT-TYPE
			SYNTAX	INTEGER
			ACCESS	read-only
			STATUS	current
	DESCRIPTION ""
			::= { mbus98 88 }

mbus98Value29		OBJECT-TYPE
			SYNTAX	INTEGER
			ACCESS	read-only
			STATUS	current
	DESCRIPTION ""
			::= { mbus98 89 }

mbus98VIF2A		OBJECT-TYPE
			SYNTAX	INTEGER
			ACCESS	read-only
			STATUS	current
	DESCRIPTION ""
			::= { mbus98 90 }

mbus98Value2A		OBJECT-TYPE
			SYNTAX	INTEGER
			ACCESS	read-only
			STATUS	current
	DESCRIPTION ""
			::= { mbus98 91 }

mbus98VIF2B		OBJECT-TYPE
			SYNTAX	INTEGER
			ACCESS	read-only
			STATUS	current
	DESCRIPTION ""
			::= { mbus98 92 }

mbus98Value2B		OBJECT-TYPE
			SYNTAX	INTEGER
			ACCESS	read-only
			STATUS	current
	DESCRIPTION ""
			::= { mbus98 93 }

mbus98VIF2C		OBJECT-TYPE
			SYNTAX	INTEGER
			ACCESS	read-only
			STATUS	current
	DESCRIPTION ""
			::= { mbus98 94 }

mbus98Value2C		OBJECT-TYPE
			SYNTAX	INTEGER
			ACCESS	read-only
			STATUS	current
	DESCRIPTION ""
			::= { mbus98 95 }

mbus98VIF2D		OBJECT-TYPE
			SYNTAX	INTEGER
			ACCESS	read-only
			STATUS	current
	DESCRIPTION ""
			::= { mbus98 96 }

mbus98Value2D		OBJECT-TYPE
			SYNTAX	INTEGER
			ACCESS	read-only
			STATUS	current
	DESCRIPTION ""
			::= { mbus98 97 }

mbus98VIF2E		OBJECT-TYPE
			SYNTAX	INTEGER
			ACCESS	read-only
			STATUS	current
	DESCRIPTION ""
			::= { mbus98 98 }

mbus98Value2E		OBJECT-TYPE
			SYNTAX	INTEGER
			ACCESS	read-only
			STATUS	current
	DESCRIPTION ""
			::= { mbus98 99 }

mbus98VIF2F		OBJECT-TYPE
			SYNTAX	INTEGER
			ACCESS	read-only
			STATUS	current
	DESCRIPTION ""
			::= { mbus98 100 }

mbus98Value2F		OBJECT-TYPE
			SYNTAX	INTEGER
			ACCESS	read-only
			STATUS	current
	DESCRIPTION ""
			::= { mbus98 101 }

mbus99			OBJECT IDENTIFIER ::= { mbus 153 }

mbus99IdNumber		OBJECT-TYPE
			SYNTAX	Gauge
			ACCESS	read-only
			STATUS	current
	DESCRIPTION ""
			::= { mbus99 1 }

mbus99Manufacturer	OBJECT-TYPE
			SYNTAX	Gauge
			ACCESS	read-only
			STATUS	current
	DESCRIPTION ""
			::= { mbus99 2 }

mbus99Version		OBJECT-TYPE
			SYNTAX	Gauge
			ACCESS	read-only
			STATUS	current
	DESCRIPTION ""
			::= { mbus99 3 }

mbus99Medium		OBJECT-TYPE
			SYNTAX	Gauge
			ACCESS	read-only
			STATUS	current
	DESCRIPTION ""
			::= { mbus99 4 }

mbus99Status		OBJECT-TYPE
			SYNTAX	Gauge
			ACCESS	read-only
			STATUS	current
	DESCRIPTION ""
			::= { mbus99 5 }

mbus99VIF00		OBJECT-TYPE
			SYNTAX	INTEGER
			ACCESS	read-only
			STATUS	current
	DESCRIPTION ""
			::= { mbus99 6 }

mbus99Value00		OBJECT-TYPE
			SYNTAX	INTEGER
			ACCESS	read-only
			STATUS	current
	DESCRIPTION ""
			::= { mbus99 7 }

mbus99VIF01		OBJECT-TYPE
			SYNTAX	INTEGER
			ACCESS	read-only
			STATUS	current
	DESCRIPTION ""
			::= { mbus99 8 }

mbus99Value01		OBJECT-TYPE
			SYNTAX	INTEGER
			ACCESS	read-only
			STATUS	current
	DESCRIPTION ""
			::= { mbus99 9 }

mbus99VIF02		OBJECT-TYPE
			SYNTAX	INTEGER
			ACCESS	read-only
			STATUS	current
	DESCRIPTION ""
			::= { mbus99 10 }

mbus99Value02		OBJECT-TYPE
			SYNTAX	INTEGER
			ACCESS	read-only
			STATUS	current
	DESCRIPTION ""
			::= { mbus99 11 }

mbus99VIF03		OBJECT-TYPE
			SYNTAX	INTEGER
			ACCESS	read-only
			STATUS	current
	DESCRIPTION ""
			::= { mbus99 12 }

mbus99Value03		OBJECT-TYPE
			SYNTAX	INTEGER
			ACCESS	read-only
			STATUS	current
	DESCRIPTION ""
			::= { mbus99 13 }

mbus99VIF04		OBJECT-TYPE
			SYNTAX	INTEGER
			ACCESS	read-only
			STATUS	current
	DESCRIPTION ""
			::= { mbus99 14 }

mbus99Value04		OBJECT-TYPE
			SYNTAX	INTEGER
			ACCESS	read-only
			STATUS	current
	DESCRIPTION ""
			::= { mbus99 15 }

mbus99VIF05		OBJECT-TYPE
			SYNTAX	INTEGER
			ACCESS	read-only
			STATUS	current
	DESCRIPTION ""
			::= { mbus99 16 }

mbus99Value05		OBJECT-TYPE
			SYNTAX	INTEGER
			ACCESS	read-only
			STATUS	current
	DESCRIPTION ""
			::= { mbus99 17 }

mbus99VIF06		OBJECT-TYPE
			SYNTAX	INTEGER
			ACCESS	read-only
			STATUS	current
	DESCRIPTION ""
			::= { mbus99 18 }

mbus99Value06		OBJECT-TYPE
			SYNTAX	INTEGER
			ACCESS	read-only
			STATUS	current
	DESCRIPTION ""
			::= { mbus99 19 }

mbus99VIF07		OBJECT-TYPE
			SYNTAX	INTEGER
			ACCESS	read-only
			STATUS	current
	DESCRIPTION ""
			::= { mbus99 20 }

mbus99Value07		OBJECT-TYPE
			SYNTAX	INTEGER
			ACCESS	read-only
			STATUS	current
	DESCRIPTION ""
			::= { mbus99 21 }

mbus99VIF08		OBJECT-TYPE
			SYNTAX	INTEGER
			ACCESS	read-only
			STATUS	current
	DESCRIPTION ""
			::= { mbus99 22 }

mbus99Value08		OBJECT-TYPE
			SYNTAX	INTEGER
			ACCESS	read-only
			STATUS	current
	DESCRIPTION ""
			::= { mbus99 23 }

mbus99VIF09		OBJECT-TYPE
			SYNTAX	INTEGER
			ACCESS	read-only
			STATUS	current
	DESCRIPTION ""
			::= { mbus99 24 }

mbus99Value09		OBJECT-TYPE
			SYNTAX	INTEGER
			ACCESS	read-only
			STATUS	current
	DESCRIPTION ""
			::= { mbus99 25 }

mbus99VIF0A		OBJECT-TYPE
			SYNTAX	INTEGER
			ACCESS	read-only
			STATUS	current
	DESCRIPTION ""
			::= { mbus99 26 }

mbus99Value0A		OBJECT-TYPE
			SYNTAX	INTEGER
			ACCESS	read-only
			STATUS	current
	DESCRIPTION ""
			::= { mbus99 27 }

mbus99VIF0B		OBJECT-TYPE
			SYNTAX	INTEGER
			ACCESS	read-only
			STATUS	current
	DESCRIPTION ""
			::= { mbus99 28 }

mbus99Value0B		OBJECT-TYPE
			SYNTAX	INTEGER
			ACCESS	read-only
			STATUS	current
	DESCRIPTION ""
			::= { mbus99 29 }

mbus99VIF0C		OBJECT-TYPE
			SYNTAX	INTEGER
			ACCESS	read-only
			STATUS	current
	DESCRIPTION ""
			::= { mbus99 30 }

mbus99Value0C		OBJECT-TYPE
			SYNTAX	INTEGER
			ACCESS	read-only
			STATUS	current
	DESCRIPTION ""
			::= { mbus99 31 }

mbus99VIF0D		OBJECT-TYPE
			SYNTAX	INTEGER
			ACCESS	read-only
			STATUS	current
	DESCRIPTION ""
			::= { mbus99 32 }

mbus99Value0D		OBJECT-TYPE
			SYNTAX	INTEGER
			ACCESS	read-only
			STATUS	current
	DESCRIPTION ""
			::= { mbus99 33 }

mbus99VIF0E		OBJECT-TYPE
			SYNTAX	INTEGER
			ACCESS	read-only
			STATUS	current
	DESCRIPTION ""
			::= { mbus99 34 }

mbus99Value0E		OBJECT-TYPE
			SYNTAX	INTEGER
			ACCESS	read-only
			STATUS	current
	DESCRIPTION ""
			::= { mbus99 35 }

mbus99VIF0F		OBJECT-TYPE
			SYNTAX	INTEGER
			ACCESS	read-only
			STATUS	current
	DESCRIPTION ""
			::= { mbus99 36 }

mbus99Value0F		OBJECT-TYPE
			SYNTAX	INTEGER
			ACCESS	read-only
			STATUS	current
	DESCRIPTION ""
			::= { mbus99 37 }

mbus99VIF10		OBJECT-TYPE
			SYNTAX	INTEGER
			ACCESS	read-only
			STATUS	current
	DESCRIPTION ""
			::= { mbus99 38 }

mbus99Value10		OBJECT-TYPE
			SYNTAX	INTEGER
			ACCESS	read-only
			STATUS	current
	DESCRIPTION ""
			::= { mbus99 39 }

mbus99VIF11		OBJECT-TYPE
			SYNTAX	INTEGER
			ACCESS	read-only
			STATUS	current
	DESCRIPTION ""
			::= { mbus99 40 }

mbus99Value11		OBJECT-TYPE
			SYNTAX	INTEGER
			ACCESS	read-only
			STATUS	current
	DESCRIPTION ""
			::= { mbus99 41 }

mbus99VIF12		OBJECT-TYPE
			SYNTAX	INTEGER
			ACCESS	read-only
			STATUS	current
	DESCRIPTION ""
			::= { mbus99 42 }

mbus99Value12		OBJECT-TYPE
			SYNTAX	INTEGER
			ACCESS	read-only
			STATUS	current
	DESCRIPTION ""
			::= { mbus99 43 }

mbus99VIF13		OBJECT-TYPE
			SYNTAX	INTEGER
			ACCESS	read-only
			STATUS	current
	DESCRIPTION ""
			::= { mbus99 44 }

mbus99Value13		OBJECT-TYPE
			SYNTAX	INTEGER
			ACCESS	read-only
			STATUS	current
	DESCRIPTION ""
			::= { mbus99 45 }

mbus99VIF14		OBJECT-TYPE
			SYNTAX	INTEGER
			ACCESS	read-only
			STATUS	current
	DESCRIPTION ""
			::= { mbus99 46 }

mbus99Value14		OBJECT-TYPE
			SYNTAX	INTEGER
			ACCESS	read-only
			STATUS	current
	DESCRIPTION ""
			::= { mbus99 47 }

mbus99VIF15		OBJECT-TYPE
			SYNTAX	INTEGER
			ACCESS	read-only
			STATUS	current
	DESCRIPTION ""
			::= { mbus99 48 }

mbus99Value15		OBJECT-TYPE
			SYNTAX	INTEGER
			ACCESS	read-only
			STATUS	current
	DESCRIPTION ""
			::= { mbus99 49 }

mbus99VIF16		OBJECT-TYPE
			SYNTAX	INTEGER
			ACCESS	read-only
			STATUS	current
	DESCRIPTION ""
			::= { mbus99 50 }

mbus99Value16		OBJECT-TYPE
			SYNTAX	INTEGER
			ACCESS	read-only
			STATUS	current
	DESCRIPTION ""
			::= { mbus99 51 }

mbus99VIF17		OBJECT-TYPE
			SYNTAX	INTEGER
			ACCESS	read-only
			STATUS	current
	DESCRIPTION ""
			::= { mbus99 52 }

mbus99Value17		OBJECT-TYPE
			SYNTAX	INTEGER
			ACCESS	read-only
			STATUS	current
	DESCRIPTION ""
			::= { mbus99 53 }

mbus99VIF18		OBJECT-TYPE
			SYNTAX	INTEGER
			ACCESS	read-only
			STATUS	current
	DESCRIPTION ""
			::= { mbus99 54 }

mbus99Value18		OBJECT-TYPE
			SYNTAX	INTEGER
			ACCESS	read-only
			STATUS	current
	DESCRIPTION ""
			::= { mbus99 55 }

mbus99VIF19		OBJECT-TYPE
			SYNTAX	INTEGER
			ACCESS	read-only
			STATUS	current
	DESCRIPTION ""
			::= { mbus99 56 }

mbus99Value19		OBJECT-TYPE
			SYNTAX	INTEGER
			ACCESS	read-only
			STATUS	current
	DESCRIPTION ""
			::= { mbus99 57 }

mbus99VIF1A		OBJECT-TYPE
			SYNTAX	INTEGER
			ACCESS	read-only
			STATUS	current
	DESCRIPTION ""
			::= { mbus99 58 }

mbus99Value1A		OBJECT-TYPE
			SYNTAX	INTEGER
			ACCESS	read-only
			STATUS	current
	DESCRIPTION ""
			::= { mbus99 59 }

mbus99VIF1B		OBJECT-TYPE
			SYNTAX	INTEGER
			ACCESS	read-only
			STATUS	current
	DESCRIPTION ""
			::= { mbus99 60 }

mbus99Value1B		OBJECT-TYPE
			SYNTAX	INTEGER
			ACCESS	read-only
			STATUS	current
	DESCRIPTION ""
			::= { mbus99 61 }

mbus99VIF1C		OBJECT-TYPE
			SYNTAX	INTEGER
			ACCESS	read-only
			STATUS	current
	DESCRIPTION ""
			::= { mbus99 62 }

mbus99Value1C		OBJECT-TYPE
			SYNTAX	INTEGER
			ACCESS	read-only
			STATUS	current
	DESCRIPTION ""
			::= { mbus99 63 }

mbus99VIF1D		OBJECT-TYPE
			SYNTAX	INTEGER
			ACCESS	read-only
			STATUS	current
	DESCRIPTION ""
			::= { mbus99 64 }

mbus99Value1D		OBJECT-TYPE
			SYNTAX	INTEGER
			ACCESS	read-only
			STATUS	current
	DESCRIPTION ""
			::= { mbus99 65 }

mbus99VIF1E		OBJECT-TYPE
			SYNTAX	INTEGER
			ACCESS	read-only
			STATUS	current
	DESCRIPTION ""
			::= { mbus99 66 }

mbus99Value1E		OBJECT-TYPE
			SYNTAX	INTEGER
			ACCESS	read-only
			STATUS	current
	DESCRIPTION ""
			::= { mbus99 67 }

mbus99VIF1F		OBJECT-TYPE
			SYNTAX	INTEGER
			ACCESS	read-only
			STATUS	current
	DESCRIPTION ""
			::= { mbus99 68 }

mbus99Value1F		OBJECT-TYPE
			SYNTAX	INTEGER
			ACCESS	read-only
			STATUS	current
	DESCRIPTION ""
			::= { mbus99 69 }

mbus99VIF20		OBJECT-TYPE
			SYNTAX	INTEGER
			ACCESS	read-only
			STATUS	current
	DESCRIPTION ""
			::= { mbus99 70 }

mbus99Value20		OBJECT-TYPE
			SYNTAX	INTEGER
			ACCESS	read-only
			STATUS	current
	DESCRIPTION ""
			::= { mbus99 71 }

mbus99VIF21		OBJECT-TYPE
			SYNTAX	INTEGER
			ACCESS	read-only
			STATUS	current
	DESCRIPTION ""
			::= { mbus99 72 }

mbus99Value21		OBJECT-TYPE
			SYNTAX	INTEGER
			ACCESS	read-only
			STATUS	current
	DESCRIPTION ""
			::= { mbus99 73 }

mbus99VIF22		OBJECT-TYPE
			SYNTAX	INTEGER
			ACCESS	read-only
			STATUS	current
	DESCRIPTION ""
			::= { mbus99 74 }

mbus99Value22		OBJECT-TYPE
			SYNTAX	INTEGER
			ACCESS	read-only
			STATUS	current
	DESCRIPTION ""
			::= { mbus99 75 }

mbus99VIF23		OBJECT-TYPE
			SYNTAX	INTEGER
			ACCESS	read-only
			STATUS	current
	DESCRIPTION ""
			::= { mbus99 76 }

mbus99Value23		OBJECT-TYPE
			SYNTAX	INTEGER
			ACCESS	read-only
			STATUS	current
	DESCRIPTION ""
			::= { mbus99 77 }

mbus99VIF24		OBJECT-TYPE
			SYNTAX	INTEGER
			ACCESS	read-only
			STATUS	current
	DESCRIPTION ""
			::= { mbus99 78 }

mbus99Value24		OBJECT-TYPE
			SYNTAX	INTEGER
			ACCESS	read-only
			STATUS	current
	DESCRIPTION ""
			::= { mbus99 79 }

mbus99VIF25		OBJECT-TYPE
			SYNTAX	INTEGER
			ACCESS	read-only
			STATUS	current
	DESCRIPTION ""
			::= { mbus99 80 }

mbus99Value25		OBJECT-TYPE
			SYNTAX	INTEGER
			ACCESS	read-only
			STATUS	current
	DESCRIPTION ""
			::= { mbus99 81 }

mbus99VIF26		OBJECT-TYPE
			SYNTAX	INTEGER
			ACCESS	read-only
			STATUS	current
	DESCRIPTION ""
			::= { mbus99 82 }

mbus99Value26		OBJECT-TYPE
			SYNTAX	INTEGER
			ACCESS	read-only
			STATUS	current
	DESCRIPTION ""
			::= { mbus99 83 }

mbus99VIF27		OBJECT-TYPE
			SYNTAX	INTEGER
			ACCESS	read-only
			STATUS	current
	DESCRIPTION ""
			::= { mbus99 84 }

mbus99Value27		OBJECT-TYPE
			SYNTAX	INTEGER
			ACCESS	read-only
			STATUS	current
	DESCRIPTION ""
			::= { mbus99 85 }

mbus99VIF28		OBJECT-TYPE
			SYNTAX	INTEGER
			ACCESS	read-only
			STATUS	current
	DESCRIPTION ""
			::= { mbus99 86 }

mbus99Value28		OBJECT-TYPE
			SYNTAX	INTEGER
			ACCESS	read-only
			STATUS	current
	DESCRIPTION ""
			::= { mbus99 87 }

mbus99VIF29		OBJECT-TYPE
			SYNTAX	INTEGER
			ACCESS	read-only
			STATUS	current
	DESCRIPTION ""
			::= { mbus99 88 }

mbus99Value29		OBJECT-TYPE
			SYNTAX	INTEGER
			ACCESS	read-only
			STATUS	current
	DESCRIPTION ""
			::= { mbus99 89 }

mbus99VIF2A		OBJECT-TYPE
			SYNTAX	INTEGER
			ACCESS	read-only
			STATUS	current
	DESCRIPTION ""
			::= { mbus99 90 }

mbus99Value2A		OBJECT-TYPE
			SYNTAX	INTEGER
			ACCESS	read-only
			STATUS	current
	DESCRIPTION ""
			::= { mbus99 91 }

mbus99VIF2B		OBJECT-TYPE
			SYNTAX	INTEGER
			ACCESS	read-only
			STATUS	current
	DESCRIPTION ""
			::= { mbus99 92 }

mbus99Value2B		OBJECT-TYPE
			SYNTAX	INTEGER
			ACCESS	read-only
			STATUS	current
	DESCRIPTION ""
			::= { mbus99 93 }

mbus99VIF2C		OBJECT-TYPE
			SYNTAX	INTEGER
			ACCESS	read-only
			STATUS	current
	DESCRIPTION ""
			::= { mbus99 94 }

mbus99Value2C		OBJECT-TYPE
			SYNTAX	INTEGER
			ACCESS	read-only
			STATUS	current
	DESCRIPTION ""
			::= { mbus99 95 }

mbus99VIF2D		OBJECT-TYPE
			SYNTAX	INTEGER
			ACCESS	read-only
			STATUS	current
	DESCRIPTION ""
			::= { mbus99 96 }

mbus99Value2D		OBJECT-TYPE
			SYNTAX	INTEGER
			ACCESS	read-only
			STATUS	current
	DESCRIPTION ""
			::= { mbus99 97 }

mbus99VIF2E		OBJECT-TYPE
			SYNTAX	INTEGER
			ACCESS	read-only
			STATUS	current
	DESCRIPTION ""
			::= { mbus99 98 }

mbus99Value2E		OBJECT-TYPE
			SYNTAX	INTEGER
			ACCESS	read-only
			STATUS	current
	DESCRIPTION ""
			::= { mbus99 99 }

mbus99VIF2F		OBJECT-TYPE
			SYNTAX	INTEGER
			ACCESS	read-only
			STATUS	current
	DESCRIPTION ""
			::= { mbus99 100 }

mbus99Value2F		OBJECT-TYPE
			SYNTAX	INTEGER
			ACCESS	read-only
			STATUS	current
	DESCRIPTION ""
			::= { mbus99 101 }

mbus9A			OBJECT IDENTIFIER ::= { mbus 154 }

mbus9AIdNumber		OBJECT-TYPE
			SYNTAX	Gauge
			ACCESS	read-only
			STATUS	current
	DESCRIPTION ""
			::= { mbus9A 1 }

mbus9AManufacturer	OBJECT-TYPE
			SYNTAX	Gauge
			ACCESS	read-only
			STATUS	current
	DESCRIPTION ""
			::= { mbus9A 2 }

mbus9AVersion		OBJECT-TYPE
			SYNTAX	Gauge
			ACCESS	read-only
			STATUS	current
	DESCRIPTION ""
			::= { mbus9A 3 }

mbus9AMedium		OBJECT-TYPE
			SYNTAX	Gauge
			ACCESS	read-only
			STATUS	current
	DESCRIPTION ""
			::= { mbus9A 4 }

mbus9AStatus		OBJECT-TYPE
			SYNTAX	Gauge
			ACCESS	read-only
			STATUS	current
	DESCRIPTION ""
			::= { mbus9A 5 }

mbus9AVIF00		OBJECT-TYPE
			SYNTAX	INTEGER
			ACCESS	read-only
			STATUS	current
	DESCRIPTION ""
			::= { mbus9A 6 }

mbus9AValue00		OBJECT-TYPE
			SYNTAX	INTEGER
			ACCESS	read-only
			STATUS	current
	DESCRIPTION ""
			::= { mbus9A 7 }

mbus9AVIF01		OBJECT-TYPE
			SYNTAX	INTEGER
			ACCESS	read-only
			STATUS	current
	DESCRIPTION ""
			::= { mbus9A 8 }

mbus9AValue01		OBJECT-TYPE
			SYNTAX	INTEGER
			ACCESS	read-only
			STATUS	current
	DESCRIPTION ""
			::= { mbus9A 9 }

mbus9AVIF02		OBJECT-TYPE
			SYNTAX	INTEGER
			ACCESS	read-only
			STATUS	current
	DESCRIPTION ""
			::= { mbus9A 10 }

mbus9AValue02		OBJECT-TYPE
			SYNTAX	INTEGER
			ACCESS	read-only
			STATUS	current
	DESCRIPTION ""
			::= { mbus9A 11 }

mbus9AVIF03		OBJECT-TYPE
			SYNTAX	INTEGER
			ACCESS	read-only
			STATUS	current
	DESCRIPTION ""
			::= { mbus9A 12 }

mbus9AValue03		OBJECT-TYPE
			SYNTAX	INTEGER
			ACCESS	read-only
			STATUS	current
	DESCRIPTION ""
			::= { mbus9A 13 }

mbus9AVIF04		OBJECT-TYPE
			SYNTAX	INTEGER
			ACCESS	read-only
			STATUS	current
	DESCRIPTION ""
			::= { mbus9A 14 }

mbus9AValue04		OBJECT-TYPE
			SYNTAX	INTEGER
			ACCESS	read-only
			STATUS	current
	DESCRIPTION ""
			::= { mbus9A 15 }

mbus9AVIF05		OBJECT-TYPE
			SYNTAX	INTEGER
			ACCESS	read-only
			STATUS	current
	DESCRIPTION ""
			::= { mbus9A 16 }

mbus9AValue05		OBJECT-TYPE
			SYNTAX	INTEGER
			ACCESS	read-only
			STATUS	current
	DESCRIPTION ""
			::= { mbus9A 17 }

mbus9AVIF06		OBJECT-TYPE
			SYNTAX	INTEGER
			ACCESS	read-only
			STATUS	current
	DESCRIPTION ""
			::= { mbus9A 18 }

mbus9AValue06		OBJECT-TYPE
			SYNTAX	INTEGER
			ACCESS	read-only
			STATUS	current
	DESCRIPTION ""
			::= { mbus9A 19 }

mbus9AVIF07		OBJECT-TYPE
			SYNTAX	INTEGER
			ACCESS	read-only
			STATUS	current
	DESCRIPTION ""
			::= { mbus9A 20 }

mbus9AValue07		OBJECT-TYPE
			SYNTAX	INTEGER
			ACCESS	read-only
			STATUS	current
	DESCRIPTION ""
			::= { mbus9A 21 }

mbus9AVIF08		OBJECT-TYPE
			SYNTAX	INTEGER
			ACCESS	read-only
			STATUS	current
	DESCRIPTION ""
			::= { mbus9A 22 }

mbus9AValue08		OBJECT-TYPE
			SYNTAX	INTEGER
			ACCESS	read-only
			STATUS	current
	DESCRIPTION ""
			::= { mbus9A 23 }

mbus9AVIF09		OBJECT-TYPE
			SYNTAX	INTEGER
			ACCESS	read-only
			STATUS	current
	DESCRIPTION ""
			::= { mbus9A 24 }

mbus9AValue09		OBJECT-TYPE
			SYNTAX	INTEGER
			ACCESS	read-only
			STATUS	current
	DESCRIPTION ""
			::= { mbus9A 25 }

mbus9AVIF0A		OBJECT-TYPE
			SYNTAX	INTEGER
			ACCESS	read-only
			STATUS	current
	DESCRIPTION ""
			::= { mbus9A 26 }

mbus9AValue0A		OBJECT-TYPE
			SYNTAX	INTEGER
			ACCESS	read-only
			STATUS	current
	DESCRIPTION ""
			::= { mbus9A 27 }

mbus9AVIF0B		OBJECT-TYPE
			SYNTAX	INTEGER
			ACCESS	read-only
			STATUS	current
	DESCRIPTION ""
			::= { mbus9A 28 }

mbus9AValue0B		OBJECT-TYPE
			SYNTAX	INTEGER
			ACCESS	read-only
			STATUS	current
	DESCRIPTION ""
			::= { mbus9A 29 }

mbus9AVIF0C		OBJECT-TYPE
			SYNTAX	INTEGER
			ACCESS	read-only
			STATUS	current
	DESCRIPTION ""
			::= { mbus9A 30 }

mbus9AValue0C		OBJECT-TYPE
			SYNTAX	INTEGER
			ACCESS	read-only
			STATUS	current
	DESCRIPTION ""
			::= { mbus9A 31 }

mbus9AVIF0D		OBJECT-TYPE
			SYNTAX	INTEGER
			ACCESS	read-only
			STATUS	current
	DESCRIPTION ""
			::= { mbus9A 32 }

mbus9AValue0D		OBJECT-TYPE
			SYNTAX	INTEGER
			ACCESS	read-only
			STATUS	current
	DESCRIPTION ""
			::= { mbus9A 33 }

mbus9AVIF0E		OBJECT-TYPE
			SYNTAX	INTEGER
			ACCESS	read-only
			STATUS	current
	DESCRIPTION ""
			::= { mbus9A 34 }

mbus9AValue0E		OBJECT-TYPE
			SYNTAX	INTEGER
			ACCESS	read-only
			STATUS	current
	DESCRIPTION ""
			::= { mbus9A 35 }

mbus9AVIF0F		OBJECT-TYPE
			SYNTAX	INTEGER
			ACCESS	read-only
			STATUS	current
	DESCRIPTION ""
			::= { mbus9A 36 }

mbus9AValue0F		OBJECT-TYPE
			SYNTAX	INTEGER
			ACCESS	read-only
			STATUS	current
	DESCRIPTION ""
			::= { mbus9A 37 }

mbus9AVIF10		OBJECT-TYPE
			SYNTAX	INTEGER
			ACCESS	read-only
			STATUS	current
	DESCRIPTION ""
			::= { mbus9A 38 }

mbus9AValue10		OBJECT-TYPE
			SYNTAX	INTEGER
			ACCESS	read-only
			STATUS	current
	DESCRIPTION ""
			::= { mbus9A 39 }

mbus9AVIF11		OBJECT-TYPE
			SYNTAX	INTEGER
			ACCESS	read-only
			STATUS	current
	DESCRIPTION ""
			::= { mbus9A 40 }

mbus9AValue11		OBJECT-TYPE
			SYNTAX	INTEGER
			ACCESS	read-only
			STATUS	current
	DESCRIPTION ""
			::= { mbus9A 41 }

mbus9AVIF12		OBJECT-TYPE
			SYNTAX	INTEGER
			ACCESS	read-only
			STATUS	current
	DESCRIPTION ""
			::= { mbus9A 42 }

mbus9AValue12		OBJECT-TYPE
			SYNTAX	INTEGER
			ACCESS	read-only
			STATUS	current
	DESCRIPTION ""
			::= { mbus9A 43 }

mbus9AVIF13		OBJECT-TYPE
			SYNTAX	INTEGER
			ACCESS	read-only
			STATUS	current
	DESCRIPTION ""
			::= { mbus9A 44 }

mbus9AValue13		OBJECT-TYPE
			SYNTAX	INTEGER
			ACCESS	read-only
			STATUS	current
	DESCRIPTION ""
			::= { mbus9A 45 }

mbus9AVIF14		OBJECT-TYPE
			SYNTAX	INTEGER
			ACCESS	read-only
			STATUS	current
	DESCRIPTION ""
			::= { mbus9A 46 }

mbus9AValue14		OBJECT-TYPE
			SYNTAX	INTEGER
			ACCESS	read-only
			STATUS	current
	DESCRIPTION ""
			::= { mbus9A 47 }

mbus9AVIF15		OBJECT-TYPE
			SYNTAX	INTEGER
			ACCESS	read-only
			STATUS	current
	DESCRIPTION ""
			::= { mbus9A 48 }

mbus9AValue15		OBJECT-TYPE
			SYNTAX	INTEGER
			ACCESS	read-only
			STATUS	current
	DESCRIPTION ""
			::= { mbus9A 49 }

mbus9AVIF16		OBJECT-TYPE
			SYNTAX	INTEGER
			ACCESS	read-only
			STATUS	current
	DESCRIPTION ""
			::= { mbus9A 50 }

mbus9AValue16		OBJECT-TYPE
			SYNTAX	INTEGER
			ACCESS	read-only
			STATUS	current
	DESCRIPTION ""
			::= { mbus9A 51 }

mbus9AVIF17		OBJECT-TYPE
			SYNTAX	INTEGER
			ACCESS	read-only
			STATUS	current
	DESCRIPTION ""
			::= { mbus9A 52 }

mbus9AValue17		OBJECT-TYPE
			SYNTAX	INTEGER
			ACCESS	read-only
			STATUS	current
	DESCRIPTION ""
			::= { mbus9A 53 }

mbus9AVIF18		OBJECT-TYPE
			SYNTAX	INTEGER
			ACCESS	read-only
			STATUS	current
	DESCRIPTION ""
			::= { mbus9A 54 }

mbus9AValue18		OBJECT-TYPE
			SYNTAX	INTEGER
			ACCESS	read-only
			STATUS	current
	DESCRIPTION ""
			::= { mbus9A 55 }

mbus9AVIF19		OBJECT-TYPE
			SYNTAX	INTEGER
			ACCESS	read-only
			STATUS	current
	DESCRIPTION ""
			::= { mbus9A 56 }

mbus9AValue19		OBJECT-TYPE
			SYNTAX	INTEGER
			ACCESS	read-only
			STATUS	current
	DESCRIPTION ""
			::= { mbus9A 57 }

mbus9AVIF1A		OBJECT-TYPE
			SYNTAX	INTEGER
			ACCESS	read-only
			STATUS	current
	DESCRIPTION ""
			::= { mbus9A 58 }

mbus9AValue1A		OBJECT-TYPE
			SYNTAX	INTEGER
			ACCESS	read-only
			STATUS	current
	DESCRIPTION ""
			::= { mbus9A 59 }

mbus9AVIF1B		OBJECT-TYPE
			SYNTAX	INTEGER
			ACCESS	read-only
			STATUS	current
	DESCRIPTION ""
			::= { mbus9A 60 }

mbus9AValue1B		OBJECT-TYPE
			SYNTAX	INTEGER
			ACCESS	read-only
			STATUS	current
	DESCRIPTION ""
			::= { mbus9A 61 }

mbus9AVIF1C		OBJECT-TYPE
			SYNTAX	INTEGER
			ACCESS	read-only
			STATUS	current
	DESCRIPTION ""
			::= { mbus9A 62 }

mbus9AValue1C		OBJECT-TYPE
			SYNTAX	INTEGER
			ACCESS	read-only
			STATUS	current
	DESCRIPTION ""
			::= { mbus9A 63 }

mbus9AVIF1D		OBJECT-TYPE
			SYNTAX	INTEGER
			ACCESS	read-only
			STATUS	current
	DESCRIPTION ""
			::= { mbus9A 64 }

mbus9AValue1D		OBJECT-TYPE
			SYNTAX	INTEGER
			ACCESS	read-only
			STATUS	current
	DESCRIPTION ""
			::= { mbus9A 65 }

mbus9AVIF1E		OBJECT-TYPE
			SYNTAX	INTEGER
			ACCESS	read-only
			STATUS	current
	DESCRIPTION ""
			::= { mbus9A 66 }

mbus9AValue1E		OBJECT-TYPE
			SYNTAX	INTEGER
			ACCESS	read-only
			STATUS	current
	DESCRIPTION ""
			::= { mbus9A 67 }

mbus9AVIF1F		OBJECT-TYPE
			SYNTAX	INTEGER
			ACCESS	read-only
			STATUS	current
	DESCRIPTION ""
			::= { mbus9A 68 }

mbus9AValue1F		OBJECT-TYPE
			SYNTAX	INTEGER
			ACCESS	read-only
			STATUS	current
	DESCRIPTION ""
			::= { mbus9A 69 }

mbus9AVIF20		OBJECT-TYPE
			SYNTAX	INTEGER
			ACCESS	read-only
			STATUS	current
	DESCRIPTION ""
			::= { mbus9A 70 }

mbus9AValue20		OBJECT-TYPE
			SYNTAX	INTEGER
			ACCESS	read-only
			STATUS	current
	DESCRIPTION ""
			::= { mbus9A 71 }

mbus9AVIF21		OBJECT-TYPE
			SYNTAX	INTEGER
			ACCESS	read-only
			STATUS	current
	DESCRIPTION ""
			::= { mbus9A 72 }

mbus9AValue21		OBJECT-TYPE
			SYNTAX	INTEGER
			ACCESS	read-only
			STATUS	current
	DESCRIPTION ""
			::= { mbus9A 73 }

mbus9AVIF22		OBJECT-TYPE
			SYNTAX	INTEGER
			ACCESS	read-only
			STATUS	current
	DESCRIPTION ""
			::= { mbus9A 74 }

mbus9AValue22		OBJECT-TYPE
			SYNTAX	INTEGER
			ACCESS	read-only
			STATUS	current
	DESCRIPTION ""
			::= { mbus9A 75 }

mbus9AVIF23		OBJECT-TYPE
			SYNTAX	INTEGER
			ACCESS	read-only
			STATUS	current
	DESCRIPTION ""
			::= { mbus9A 76 }

mbus9AValue23		OBJECT-TYPE
			SYNTAX	INTEGER
			ACCESS	read-only
			STATUS	current
	DESCRIPTION ""
			::= { mbus9A 77 }

mbus9AVIF24		OBJECT-TYPE
			SYNTAX	INTEGER
			ACCESS	read-only
			STATUS	current
	DESCRIPTION ""
			::= { mbus9A 78 }

mbus9AValue24		OBJECT-TYPE
			SYNTAX	INTEGER
			ACCESS	read-only
			STATUS	current
	DESCRIPTION ""
			::= { mbus9A 79 }

mbus9AVIF25		OBJECT-TYPE
			SYNTAX	INTEGER
			ACCESS	read-only
			STATUS	current
	DESCRIPTION ""
			::= { mbus9A 80 }

mbus9AValue25		OBJECT-TYPE
			SYNTAX	INTEGER
			ACCESS	read-only
			STATUS	current
	DESCRIPTION ""
			::= { mbus9A 81 }

mbus9AVIF26		OBJECT-TYPE
			SYNTAX	INTEGER
			ACCESS	read-only
			STATUS	current
	DESCRIPTION ""
			::= { mbus9A 82 }

mbus9AValue26		OBJECT-TYPE
			SYNTAX	INTEGER
			ACCESS	read-only
			STATUS	current
	DESCRIPTION ""
			::= { mbus9A 83 }

mbus9AVIF27		OBJECT-TYPE
			SYNTAX	INTEGER
			ACCESS	read-only
			STATUS	current
	DESCRIPTION ""
			::= { mbus9A 84 }

mbus9AValue27		OBJECT-TYPE
			SYNTAX	INTEGER
			ACCESS	read-only
			STATUS	current
	DESCRIPTION ""
			::= { mbus9A 85 }

mbus9AVIF28		OBJECT-TYPE
			SYNTAX	INTEGER
			ACCESS	read-only
			STATUS	current
	DESCRIPTION ""
			::= { mbus9A 86 }

mbus9AValue28		OBJECT-TYPE
			SYNTAX	INTEGER
			ACCESS	read-only
			STATUS	current
	DESCRIPTION ""
			::= { mbus9A 87 }

mbus9AVIF29		OBJECT-TYPE
			SYNTAX	INTEGER
			ACCESS	read-only
			STATUS	current
	DESCRIPTION ""
			::= { mbus9A 88 }

mbus9AValue29		OBJECT-TYPE
			SYNTAX	INTEGER
			ACCESS	read-only
			STATUS	current
	DESCRIPTION ""
			::= { mbus9A 89 }

mbus9AVIF2A		OBJECT-TYPE
			SYNTAX	INTEGER
			ACCESS	read-only
			STATUS	current
	DESCRIPTION ""
			::= { mbus9A 90 }

mbus9AValue2A		OBJECT-TYPE
			SYNTAX	INTEGER
			ACCESS	read-only
			STATUS	current
	DESCRIPTION ""
			::= { mbus9A 91 }

mbus9AVIF2B		OBJECT-TYPE
			SYNTAX	INTEGER
			ACCESS	read-only
			STATUS	current
	DESCRIPTION ""
			::= { mbus9A 92 }

mbus9AValue2B		OBJECT-TYPE
			SYNTAX	INTEGER
			ACCESS	read-only
			STATUS	current
	DESCRIPTION ""
			::= { mbus9A 93 }

mbus9AVIF2C		OBJECT-TYPE
			SYNTAX	INTEGER
			ACCESS	read-only
			STATUS	current
	DESCRIPTION ""
			::= { mbus9A 94 }

mbus9AValue2C		OBJECT-TYPE
			SYNTAX	INTEGER
			ACCESS	read-only
			STATUS	current
	DESCRIPTION ""
			::= { mbus9A 95 }

mbus9AVIF2D		OBJECT-TYPE
			SYNTAX	INTEGER
			ACCESS	read-only
			STATUS	current
	DESCRIPTION ""
			::= { mbus9A 96 }

mbus9AValue2D		OBJECT-TYPE
			SYNTAX	INTEGER
			ACCESS	read-only
			STATUS	current
	DESCRIPTION ""
			::= { mbus9A 97 }

mbus9AVIF2E		OBJECT-TYPE
			SYNTAX	INTEGER
			ACCESS	read-only
			STATUS	current
	DESCRIPTION ""
			::= { mbus9A 98 }

mbus9AValue2E		OBJECT-TYPE
			SYNTAX	INTEGER
			ACCESS	read-only
			STATUS	current
	DESCRIPTION ""
			::= { mbus9A 99 }

mbus9AVIF2F		OBJECT-TYPE
			SYNTAX	INTEGER
			ACCESS	read-only
			STATUS	current
	DESCRIPTION ""
			::= { mbus9A 100 }

mbus9AValue2F		OBJECT-TYPE
			SYNTAX	INTEGER
			ACCESS	read-only
			STATUS	current
	DESCRIPTION ""
			::= { mbus9A 101 }

mbus9B			OBJECT IDENTIFIER ::= { mbus 155 }

mbus9BIdNumber		OBJECT-TYPE
			SYNTAX	Gauge
			ACCESS	read-only
			STATUS	current
	DESCRIPTION ""
			::= { mbus9B 1 }

mbus9BManufacturer	OBJECT-TYPE
			SYNTAX	Gauge
			ACCESS	read-only
			STATUS	current
	DESCRIPTION ""
			::= { mbus9B 2 }

mbus9BVersion		OBJECT-TYPE
			SYNTAX	Gauge
			ACCESS	read-only
			STATUS	current
	DESCRIPTION ""
			::= { mbus9B 3 }

mbus9BMedium		OBJECT-TYPE
			SYNTAX	Gauge
			ACCESS	read-only
			STATUS	current
	DESCRIPTION ""
			::= { mbus9B 4 }

mbus9BStatus		OBJECT-TYPE
			SYNTAX	Gauge
			ACCESS	read-only
			STATUS	current
	DESCRIPTION ""
			::= { mbus9B 5 }

mbus9BVIF00		OBJECT-TYPE
			SYNTAX	INTEGER
			ACCESS	read-only
			STATUS	current
	DESCRIPTION ""
			::= { mbus9B 6 }

mbus9BValue00		OBJECT-TYPE
			SYNTAX	INTEGER
			ACCESS	read-only
			STATUS	current
	DESCRIPTION ""
			::= { mbus9B 7 }

mbus9BVIF01		OBJECT-TYPE
			SYNTAX	INTEGER
			ACCESS	read-only
			STATUS	current
	DESCRIPTION ""
			::= { mbus9B 8 }

mbus9BValue01		OBJECT-TYPE
			SYNTAX	INTEGER
			ACCESS	read-only
			STATUS	current
	DESCRIPTION ""
			::= { mbus9B 9 }

mbus9BVIF02		OBJECT-TYPE
			SYNTAX	INTEGER
			ACCESS	read-only
			STATUS	current
	DESCRIPTION ""
			::= { mbus9B 10 }

mbus9BValue02		OBJECT-TYPE
			SYNTAX	INTEGER
			ACCESS	read-only
			STATUS	current
	DESCRIPTION ""
			::= { mbus9B 11 }

mbus9BVIF03		OBJECT-TYPE
			SYNTAX	INTEGER
			ACCESS	read-only
			STATUS	current
	DESCRIPTION ""
			::= { mbus9B 12 }

mbus9BValue03		OBJECT-TYPE
			SYNTAX	INTEGER
			ACCESS	read-only
			STATUS	current
	DESCRIPTION ""
			::= { mbus9B 13 }

mbus9BVIF04		OBJECT-TYPE
			SYNTAX	INTEGER
			ACCESS	read-only
			STATUS	current
	DESCRIPTION ""
			::= { mbus9B 14 }

mbus9BValue04		OBJECT-TYPE
			SYNTAX	INTEGER
			ACCESS	read-only
			STATUS	current
	DESCRIPTION ""
			::= { mbus9B 15 }

mbus9BVIF05		OBJECT-TYPE
			SYNTAX	INTEGER
			ACCESS	read-only
			STATUS	current
	DESCRIPTION ""
			::= { mbus9B 16 }

mbus9BValue05		OBJECT-TYPE
			SYNTAX	INTEGER
			ACCESS	read-only
			STATUS	current
	DESCRIPTION ""
			::= { mbus9B 17 }

mbus9BVIF06		OBJECT-TYPE
			SYNTAX	INTEGER
			ACCESS	read-only
			STATUS	current
	DESCRIPTION ""
			::= { mbus9B 18 }

mbus9BValue06		OBJECT-TYPE
			SYNTAX	INTEGER
			ACCESS	read-only
			STATUS	current
	DESCRIPTION ""
			::= { mbus9B 19 }

mbus9BVIF07		OBJECT-TYPE
			SYNTAX	INTEGER
			ACCESS	read-only
			STATUS	current
	DESCRIPTION ""
			::= { mbus9B 20 }

mbus9BValue07		OBJECT-TYPE
			SYNTAX	INTEGER
			ACCESS	read-only
			STATUS	current
	DESCRIPTION ""
			::= { mbus9B 21 }

mbus9BVIF08		OBJECT-TYPE
			SYNTAX	INTEGER
			ACCESS	read-only
			STATUS	current
	DESCRIPTION ""
			::= { mbus9B 22 }

mbus9BValue08		OBJECT-TYPE
			SYNTAX	INTEGER
			ACCESS	read-only
			STATUS	current
	DESCRIPTION ""
			::= { mbus9B 23 }

mbus9BVIF09		OBJECT-TYPE
			SYNTAX	INTEGER
			ACCESS	read-only
			STATUS	current
	DESCRIPTION ""
			::= { mbus9B 24 }

mbus9BValue09		OBJECT-TYPE
			SYNTAX	INTEGER
			ACCESS	read-only
			STATUS	current
	DESCRIPTION ""
			::= { mbus9B 25 }

mbus9BVIF0A		OBJECT-TYPE
			SYNTAX	INTEGER
			ACCESS	read-only
			STATUS	current
	DESCRIPTION ""
			::= { mbus9B 26 }

mbus9BValue0A		OBJECT-TYPE
			SYNTAX	INTEGER
			ACCESS	read-only
			STATUS	current
	DESCRIPTION ""
			::= { mbus9B 27 }

mbus9BVIF0B		OBJECT-TYPE
			SYNTAX	INTEGER
			ACCESS	read-only
			STATUS	current
	DESCRIPTION ""
			::= { mbus9B 28 }

mbus9BValue0B		OBJECT-TYPE
			SYNTAX	INTEGER
			ACCESS	read-only
			STATUS	current
	DESCRIPTION ""
			::= { mbus9B 29 }

mbus9BVIF0C		OBJECT-TYPE
			SYNTAX	INTEGER
			ACCESS	read-only
			STATUS	current
	DESCRIPTION ""
			::= { mbus9B 30 }

mbus9BValue0C		OBJECT-TYPE
			SYNTAX	INTEGER
			ACCESS	read-only
			STATUS	current
	DESCRIPTION ""
			::= { mbus9B 31 }

mbus9BVIF0D		OBJECT-TYPE
			SYNTAX	INTEGER
			ACCESS	read-only
			STATUS	current
	DESCRIPTION ""
			::= { mbus9B 32 }

mbus9BValue0D		OBJECT-TYPE
			SYNTAX	INTEGER
			ACCESS	read-only
			STATUS	current
	DESCRIPTION ""
			::= { mbus9B 33 }

mbus9BVIF0E		OBJECT-TYPE
			SYNTAX	INTEGER
			ACCESS	read-only
			STATUS	current
	DESCRIPTION ""
			::= { mbus9B 34 }

mbus9BValue0E		OBJECT-TYPE
			SYNTAX	INTEGER
			ACCESS	read-only
			STATUS	current
	DESCRIPTION ""
			::= { mbus9B 35 }

mbus9BVIF0F		OBJECT-TYPE
			SYNTAX	INTEGER
			ACCESS	read-only
			STATUS	current
	DESCRIPTION ""
			::= { mbus9B 36 }

mbus9BValue0F		OBJECT-TYPE
			SYNTAX	INTEGER
			ACCESS	read-only
			STATUS	current
	DESCRIPTION ""
			::= { mbus9B 37 }

mbus9BVIF10		OBJECT-TYPE
			SYNTAX	INTEGER
			ACCESS	read-only
			STATUS	current
	DESCRIPTION ""
			::= { mbus9B 38 }

mbus9BValue10		OBJECT-TYPE
			SYNTAX	INTEGER
			ACCESS	read-only
			STATUS	current
	DESCRIPTION ""
			::= { mbus9B 39 }

mbus9BVIF11		OBJECT-TYPE
			SYNTAX	INTEGER
			ACCESS	read-only
			STATUS	current
	DESCRIPTION ""
			::= { mbus9B 40 }

mbus9BValue11		OBJECT-TYPE
			SYNTAX	INTEGER
			ACCESS	read-only
			STATUS	current
	DESCRIPTION ""
			::= { mbus9B 41 }

mbus9BVIF12		OBJECT-TYPE
			SYNTAX	INTEGER
			ACCESS	read-only
			STATUS	current
	DESCRIPTION ""
			::= { mbus9B 42 }

mbus9BValue12		OBJECT-TYPE
			SYNTAX	INTEGER
			ACCESS	read-only
			STATUS	current
	DESCRIPTION ""
			::= { mbus9B 43 }

mbus9BVIF13		OBJECT-TYPE
			SYNTAX	INTEGER
			ACCESS	read-only
			STATUS	current
	DESCRIPTION ""
			::= { mbus9B 44 }

mbus9BValue13		OBJECT-TYPE
			SYNTAX	INTEGER
			ACCESS	read-only
			STATUS	current
	DESCRIPTION ""
			::= { mbus9B 45 }

mbus9BVIF14		OBJECT-TYPE
			SYNTAX	INTEGER
			ACCESS	read-only
			STATUS	current
	DESCRIPTION ""
			::= { mbus9B 46 }

mbus9BValue14		OBJECT-TYPE
			SYNTAX	INTEGER
			ACCESS	read-only
			STATUS	current
	DESCRIPTION ""
			::= { mbus9B 47 }

mbus9BVIF15		OBJECT-TYPE
			SYNTAX	INTEGER
			ACCESS	read-only
			STATUS	current
	DESCRIPTION ""
			::= { mbus9B 48 }

mbus9BValue15		OBJECT-TYPE
			SYNTAX	INTEGER
			ACCESS	read-only
			STATUS	current
	DESCRIPTION ""
			::= { mbus9B 49 }

mbus9BVIF16		OBJECT-TYPE
			SYNTAX	INTEGER
			ACCESS	read-only
			STATUS	current
	DESCRIPTION ""
			::= { mbus9B 50 }

mbus9BValue16		OBJECT-TYPE
			SYNTAX	INTEGER
			ACCESS	read-only
			STATUS	current
	DESCRIPTION ""
			::= { mbus9B 51 }

mbus9BVIF17		OBJECT-TYPE
			SYNTAX	INTEGER
			ACCESS	read-only
			STATUS	current
	DESCRIPTION ""
			::= { mbus9B 52 }

mbus9BValue17		OBJECT-TYPE
			SYNTAX	INTEGER
			ACCESS	read-only
			STATUS	current
	DESCRIPTION ""
			::= { mbus9B 53 }

mbus9BVIF18		OBJECT-TYPE
			SYNTAX	INTEGER
			ACCESS	read-only
			STATUS	current
	DESCRIPTION ""
			::= { mbus9B 54 }

mbus9BValue18		OBJECT-TYPE
			SYNTAX	INTEGER
			ACCESS	read-only
			STATUS	current
	DESCRIPTION ""
			::= { mbus9B 55 }

mbus9BVIF19		OBJECT-TYPE
			SYNTAX	INTEGER
			ACCESS	read-only
			STATUS	current
	DESCRIPTION ""
			::= { mbus9B 56 }

mbus9BValue19		OBJECT-TYPE
			SYNTAX	INTEGER
			ACCESS	read-only
			STATUS	current
	DESCRIPTION ""
			::= { mbus9B 57 }

mbus9BVIF1A		OBJECT-TYPE
			SYNTAX	INTEGER
			ACCESS	read-only
			STATUS	current
	DESCRIPTION ""
			::= { mbus9B 58 }

mbus9BValue1A		OBJECT-TYPE
			SYNTAX	INTEGER
			ACCESS	read-only
			STATUS	current
	DESCRIPTION ""
			::= { mbus9B 59 }

mbus9BVIF1B		OBJECT-TYPE
			SYNTAX	INTEGER
			ACCESS	read-only
			STATUS	current
	DESCRIPTION ""
			::= { mbus9B 60 }

mbus9BValue1B		OBJECT-TYPE
			SYNTAX	INTEGER
			ACCESS	read-only
			STATUS	current
	DESCRIPTION ""
			::= { mbus9B 61 }

mbus9BVIF1C		OBJECT-TYPE
			SYNTAX	INTEGER
			ACCESS	read-only
			STATUS	current
	DESCRIPTION ""
			::= { mbus9B 62 }

mbus9BValue1C		OBJECT-TYPE
			SYNTAX	INTEGER
			ACCESS	read-only
			STATUS	current
	DESCRIPTION ""
			::= { mbus9B 63 }

mbus9BVIF1D		OBJECT-TYPE
			SYNTAX	INTEGER
			ACCESS	read-only
			STATUS	current
	DESCRIPTION ""
			::= { mbus9B 64 }

mbus9BValue1D		OBJECT-TYPE
			SYNTAX	INTEGER
			ACCESS	read-only
			STATUS	current
	DESCRIPTION ""
			::= { mbus9B 65 }

mbus9BVIF1E		OBJECT-TYPE
			SYNTAX	INTEGER
			ACCESS	read-only
			STATUS	current
	DESCRIPTION ""
			::= { mbus9B 66 }

mbus9BValue1E		OBJECT-TYPE
			SYNTAX	INTEGER
			ACCESS	read-only
			STATUS	current
	DESCRIPTION ""
			::= { mbus9B 67 }

mbus9BVIF1F		OBJECT-TYPE
			SYNTAX	INTEGER
			ACCESS	read-only
			STATUS	current
	DESCRIPTION ""
			::= { mbus9B 68 }

mbus9BValue1F		OBJECT-TYPE
			SYNTAX	INTEGER
			ACCESS	read-only
			STATUS	current
	DESCRIPTION ""
			::= { mbus9B 69 }

mbus9BVIF20		OBJECT-TYPE
			SYNTAX	INTEGER
			ACCESS	read-only
			STATUS	current
	DESCRIPTION ""
			::= { mbus9B 70 }

mbus9BValue20		OBJECT-TYPE
			SYNTAX	INTEGER
			ACCESS	read-only
			STATUS	current
	DESCRIPTION ""
			::= { mbus9B 71 }

mbus9BVIF21		OBJECT-TYPE
			SYNTAX	INTEGER
			ACCESS	read-only
			STATUS	current
	DESCRIPTION ""
			::= { mbus9B 72 }

mbus9BValue21		OBJECT-TYPE
			SYNTAX	INTEGER
			ACCESS	read-only
			STATUS	current
	DESCRIPTION ""
			::= { mbus9B 73 }

mbus9BVIF22		OBJECT-TYPE
			SYNTAX	INTEGER
			ACCESS	read-only
			STATUS	current
	DESCRIPTION ""
			::= { mbus9B 74 }

mbus9BValue22		OBJECT-TYPE
			SYNTAX	INTEGER
			ACCESS	read-only
			STATUS	current
	DESCRIPTION ""
			::= { mbus9B 75 }

mbus9BVIF23		OBJECT-TYPE
			SYNTAX	INTEGER
			ACCESS	read-only
			STATUS	current
	DESCRIPTION ""
			::= { mbus9B 76 }

mbus9BValue23		OBJECT-TYPE
			SYNTAX	INTEGER
			ACCESS	read-only
			STATUS	current
	DESCRIPTION ""
			::= { mbus9B 77 }

mbus9BVIF24		OBJECT-TYPE
			SYNTAX	INTEGER
			ACCESS	read-only
			STATUS	current
	DESCRIPTION ""
			::= { mbus9B 78 }

mbus9BValue24		OBJECT-TYPE
			SYNTAX	INTEGER
			ACCESS	read-only
			STATUS	current
	DESCRIPTION ""
			::= { mbus9B 79 }

mbus9BVIF25		OBJECT-TYPE
			SYNTAX	INTEGER
			ACCESS	read-only
			STATUS	current
	DESCRIPTION ""
			::= { mbus9B 80 }

mbus9BValue25		OBJECT-TYPE
			SYNTAX	INTEGER
			ACCESS	read-only
			STATUS	current
	DESCRIPTION ""
			::= { mbus9B 81 }

mbus9BVIF26		OBJECT-TYPE
			SYNTAX	INTEGER
			ACCESS	read-only
			STATUS	current
	DESCRIPTION ""
			::= { mbus9B 82 }

mbus9BValue26		OBJECT-TYPE
			SYNTAX	INTEGER
			ACCESS	read-only
			STATUS	current
	DESCRIPTION ""
			::= { mbus9B 83 }

mbus9BVIF27		OBJECT-TYPE
			SYNTAX	INTEGER
			ACCESS	read-only
			STATUS	current
	DESCRIPTION ""
			::= { mbus9B 84 }

mbus9BValue27		OBJECT-TYPE
			SYNTAX	INTEGER
			ACCESS	read-only
			STATUS	current
	DESCRIPTION ""
			::= { mbus9B 85 }

mbus9BVIF28		OBJECT-TYPE
			SYNTAX	INTEGER
			ACCESS	read-only
			STATUS	current
	DESCRIPTION ""
			::= { mbus9B 86 }

mbus9BValue28		OBJECT-TYPE
			SYNTAX	INTEGER
			ACCESS	read-only
			STATUS	current
	DESCRIPTION ""
			::= { mbus9B 87 }

mbus9BVIF29		OBJECT-TYPE
			SYNTAX	INTEGER
			ACCESS	read-only
			STATUS	current
	DESCRIPTION ""
			::= { mbus9B 88 }

mbus9BValue29		OBJECT-TYPE
			SYNTAX	INTEGER
			ACCESS	read-only
			STATUS	current
	DESCRIPTION ""
			::= { mbus9B 89 }

mbus9BVIF2A		OBJECT-TYPE
			SYNTAX	INTEGER
			ACCESS	read-only
			STATUS	current
	DESCRIPTION ""
			::= { mbus9B 90 }

mbus9BValue2A		OBJECT-TYPE
			SYNTAX	INTEGER
			ACCESS	read-only
			STATUS	current
	DESCRIPTION ""
			::= { mbus9B 91 }

mbus9BVIF2B		OBJECT-TYPE
			SYNTAX	INTEGER
			ACCESS	read-only
			STATUS	current
	DESCRIPTION ""
			::= { mbus9B 92 }

mbus9BValue2B		OBJECT-TYPE
			SYNTAX	INTEGER
			ACCESS	read-only
			STATUS	current
	DESCRIPTION ""
			::= { mbus9B 93 }

mbus9BVIF2C		OBJECT-TYPE
			SYNTAX	INTEGER
			ACCESS	read-only
			STATUS	current
	DESCRIPTION ""
			::= { mbus9B 94 }

mbus9BValue2C		OBJECT-TYPE
			SYNTAX	INTEGER
			ACCESS	read-only
			STATUS	current
	DESCRIPTION ""
			::= { mbus9B 95 }

mbus9BVIF2D		OBJECT-TYPE
			SYNTAX	INTEGER
			ACCESS	read-only
			STATUS	current
	DESCRIPTION ""
			::= { mbus9B 96 }

mbus9BValue2D		OBJECT-TYPE
			SYNTAX	INTEGER
			ACCESS	read-only
			STATUS	current
	DESCRIPTION ""
			::= { mbus9B 97 }

mbus9BVIF2E		OBJECT-TYPE
			SYNTAX	INTEGER
			ACCESS	read-only
			STATUS	current
	DESCRIPTION ""
			::= { mbus9B 98 }

mbus9BValue2E		OBJECT-TYPE
			SYNTAX	INTEGER
			ACCESS	read-only
			STATUS	current
	DESCRIPTION ""
			::= { mbus9B 99 }

mbus9BVIF2F		OBJECT-TYPE
			SYNTAX	INTEGER
			ACCESS	read-only
			STATUS	current
	DESCRIPTION ""
			::= { mbus9B 100 }

mbus9BValue2F		OBJECT-TYPE
			SYNTAX	INTEGER
			ACCESS	read-only
			STATUS	current
	DESCRIPTION ""
			::= { mbus9B 101 }

mbus9C			OBJECT IDENTIFIER ::= { mbus 156 }

mbus9CIdNumber		OBJECT-TYPE
			SYNTAX	Gauge
			ACCESS	read-only
			STATUS	current
	DESCRIPTION ""
			::= { mbus9C 1 }

mbus9CManufacturer	OBJECT-TYPE
			SYNTAX	Gauge
			ACCESS	read-only
			STATUS	current
	DESCRIPTION ""
			::= { mbus9C 2 }

mbus9CVersion		OBJECT-TYPE
			SYNTAX	Gauge
			ACCESS	read-only
			STATUS	current
	DESCRIPTION ""
			::= { mbus9C 3 }

mbus9CMedium		OBJECT-TYPE
			SYNTAX	Gauge
			ACCESS	read-only
			STATUS	current
	DESCRIPTION ""
			::= { mbus9C 4 }

mbus9CStatus		OBJECT-TYPE
			SYNTAX	Gauge
			ACCESS	read-only
			STATUS	current
	DESCRIPTION ""
			::= { mbus9C 5 }

mbus9CVIF00		OBJECT-TYPE
			SYNTAX	INTEGER
			ACCESS	read-only
			STATUS	current
	DESCRIPTION ""
			::= { mbus9C 6 }

mbus9CValue00		OBJECT-TYPE
			SYNTAX	INTEGER
			ACCESS	read-only
			STATUS	current
	DESCRIPTION ""
			::= { mbus9C 7 }

mbus9CVIF01		OBJECT-TYPE
			SYNTAX	INTEGER
			ACCESS	read-only
			STATUS	current
	DESCRIPTION ""
			::= { mbus9C 8 }

mbus9CValue01		OBJECT-TYPE
			SYNTAX	INTEGER
			ACCESS	read-only
			STATUS	current
	DESCRIPTION ""
			::= { mbus9C 9 }

mbus9CVIF02		OBJECT-TYPE
			SYNTAX	INTEGER
			ACCESS	read-only
			STATUS	current
	DESCRIPTION ""
			::= { mbus9C 10 }

mbus9CValue02		OBJECT-TYPE
			SYNTAX	INTEGER
			ACCESS	read-only
			STATUS	current
	DESCRIPTION ""
			::= { mbus9C 11 }

mbus9CVIF03		OBJECT-TYPE
			SYNTAX	INTEGER
			ACCESS	read-only
			STATUS	current
	DESCRIPTION ""
			::= { mbus9C 12 }

mbus9CValue03		OBJECT-TYPE
			SYNTAX	INTEGER
			ACCESS	read-only
			STATUS	current
	DESCRIPTION ""
			::= { mbus9C 13 }

mbus9CVIF04		OBJECT-TYPE
			SYNTAX	INTEGER
			ACCESS	read-only
			STATUS	current
	DESCRIPTION ""
			::= { mbus9C 14 }

mbus9CValue04		OBJECT-TYPE
			SYNTAX	INTEGER
			ACCESS	read-only
			STATUS	current
	DESCRIPTION ""
			::= { mbus9C 15 }

mbus9CVIF05		OBJECT-TYPE
			SYNTAX	INTEGER
			ACCESS	read-only
			STATUS	current
	DESCRIPTION ""
			::= { mbus9C 16 }

mbus9CValue05		OBJECT-TYPE
			SYNTAX	INTEGER
			ACCESS	read-only
			STATUS	current
	DESCRIPTION ""
			::= { mbus9C 17 }

mbus9CVIF06		OBJECT-TYPE
			SYNTAX	INTEGER
			ACCESS	read-only
			STATUS	current
	DESCRIPTION ""
			::= { mbus9C 18 }

mbus9CValue06		OBJECT-TYPE
			SYNTAX	INTEGER
			ACCESS	read-only
			STATUS	current
	DESCRIPTION ""
			::= { mbus9C 19 }

mbus9CVIF07		OBJECT-TYPE
			SYNTAX	INTEGER
			ACCESS	read-only
			STATUS	current
	DESCRIPTION ""
			::= { mbus9C 20 }

mbus9CValue07		OBJECT-TYPE
			SYNTAX	INTEGER
			ACCESS	read-only
			STATUS	current
	DESCRIPTION ""
			::= { mbus9C 21 }

mbus9CVIF08		OBJECT-TYPE
			SYNTAX	INTEGER
			ACCESS	read-only
			STATUS	current
	DESCRIPTION ""
			::= { mbus9C 22 }

mbus9CValue08		OBJECT-TYPE
			SYNTAX	INTEGER
			ACCESS	read-only
			STATUS	current
	DESCRIPTION ""
			::= { mbus9C 23 }

mbus9CVIF09		OBJECT-TYPE
			SYNTAX	INTEGER
			ACCESS	read-only
			STATUS	current
	DESCRIPTION ""
			::= { mbus9C 24 }

mbus9CValue09		OBJECT-TYPE
			SYNTAX	INTEGER
			ACCESS	read-only
			STATUS	current
	DESCRIPTION ""
			::= { mbus9C 25 }

mbus9CVIF0A		OBJECT-TYPE
			SYNTAX	INTEGER
			ACCESS	read-only
			STATUS	current
	DESCRIPTION ""
			::= { mbus9C 26 }

mbus9CValue0A		OBJECT-TYPE
			SYNTAX	INTEGER
			ACCESS	read-only
			STATUS	current
	DESCRIPTION ""
			::= { mbus9C 27 }

mbus9CVIF0B		OBJECT-TYPE
			SYNTAX	INTEGER
			ACCESS	read-only
			STATUS	current
	DESCRIPTION ""
			::= { mbus9C 28 }

mbus9CValue0B		OBJECT-TYPE
			SYNTAX	INTEGER
			ACCESS	read-only
			STATUS	current
	DESCRIPTION ""
			::= { mbus9C 29 }

mbus9CVIF0C		OBJECT-TYPE
			SYNTAX	INTEGER
			ACCESS	read-only
			STATUS	current
	DESCRIPTION ""
			::= { mbus9C 30 }

mbus9CValue0C		OBJECT-TYPE
			SYNTAX	INTEGER
			ACCESS	read-only
			STATUS	current
	DESCRIPTION ""
			::= { mbus9C 31 }

mbus9CVIF0D		OBJECT-TYPE
			SYNTAX	INTEGER
			ACCESS	read-only
			STATUS	current
	DESCRIPTION ""
			::= { mbus9C 32 }

mbus9CValue0D		OBJECT-TYPE
			SYNTAX	INTEGER
			ACCESS	read-only
			STATUS	current
	DESCRIPTION ""
			::= { mbus9C 33 }

mbus9CVIF0E		OBJECT-TYPE
			SYNTAX	INTEGER
			ACCESS	read-only
			STATUS	current
	DESCRIPTION ""
			::= { mbus9C 34 }

mbus9CValue0E		OBJECT-TYPE
			SYNTAX	INTEGER
			ACCESS	read-only
			STATUS	current
	DESCRIPTION ""
			::= { mbus9C 35 }

mbus9CVIF0F		OBJECT-TYPE
			SYNTAX	INTEGER
			ACCESS	read-only
			STATUS	current
	DESCRIPTION ""
			::= { mbus9C 36 }

mbus9CValue0F		OBJECT-TYPE
			SYNTAX	INTEGER
			ACCESS	read-only
			STATUS	current
	DESCRIPTION ""
			::= { mbus9C 37 }

mbus9CVIF10		OBJECT-TYPE
			SYNTAX	INTEGER
			ACCESS	read-only
			STATUS	current
	DESCRIPTION ""
			::= { mbus9C 38 }

mbus9CValue10		OBJECT-TYPE
			SYNTAX	INTEGER
			ACCESS	read-only
			STATUS	current
	DESCRIPTION ""
			::= { mbus9C 39 }

mbus9CVIF11		OBJECT-TYPE
			SYNTAX	INTEGER
			ACCESS	read-only
			STATUS	current
	DESCRIPTION ""
			::= { mbus9C 40 }

mbus9CValue11		OBJECT-TYPE
			SYNTAX	INTEGER
			ACCESS	read-only
			STATUS	current
	DESCRIPTION ""
			::= { mbus9C 41 }

mbus9CVIF12		OBJECT-TYPE
			SYNTAX	INTEGER
			ACCESS	read-only
			STATUS	current
	DESCRIPTION ""
			::= { mbus9C 42 }

mbus9CValue12		OBJECT-TYPE
			SYNTAX	INTEGER
			ACCESS	read-only
			STATUS	current
	DESCRIPTION ""
			::= { mbus9C 43 }

mbus9CVIF13		OBJECT-TYPE
			SYNTAX	INTEGER
			ACCESS	read-only
			STATUS	current
	DESCRIPTION ""
			::= { mbus9C 44 }

mbus9CValue13		OBJECT-TYPE
			SYNTAX	INTEGER
			ACCESS	read-only
			STATUS	current
	DESCRIPTION ""
			::= { mbus9C 45 }

mbus9CVIF14		OBJECT-TYPE
			SYNTAX	INTEGER
			ACCESS	read-only
			STATUS	current
	DESCRIPTION ""
			::= { mbus9C 46 }

mbus9CValue14		OBJECT-TYPE
			SYNTAX	INTEGER
			ACCESS	read-only
			STATUS	current
	DESCRIPTION ""
			::= { mbus9C 47 }

mbus9CVIF15		OBJECT-TYPE
			SYNTAX	INTEGER
			ACCESS	read-only
			STATUS	current
	DESCRIPTION ""
			::= { mbus9C 48 }

mbus9CValue15		OBJECT-TYPE
			SYNTAX	INTEGER
			ACCESS	read-only
			STATUS	current
	DESCRIPTION ""
			::= { mbus9C 49 }

mbus9CVIF16		OBJECT-TYPE
			SYNTAX	INTEGER
			ACCESS	read-only
			STATUS	current
	DESCRIPTION ""
			::= { mbus9C 50 }

mbus9CValue16		OBJECT-TYPE
			SYNTAX	INTEGER
			ACCESS	read-only
			STATUS	current
	DESCRIPTION ""
			::= { mbus9C 51 }

mbus9CVIF17		OBJECT-TYPE
			SYNTAX	INTEGER
			ACCESS	read-only
			STATUS	current
	DESCRIPTION ""
			::= { mbus9C 52 }

mbus9CValue17		OBJECT-TYPE
			SYNTAX	INTEGER
			ACCESS	read-only
			STATUS	current
	DESCRIPTION ""
			::= { mbus9C 53 }

mbus9CVIF18		OBJECT-TYPE
			SYNTAX	INTEGER
			ACCESS	read-only
			STATUS	current
	DESCRIPTION ""
			::= { mbus9C 54 }

mbus9CValue18		OBJECT-TYPE
			SYNTAX	INTEGER
			ACCESS	read-only
			STATUS	current
	DESCRIPTION ""
			::= { mbus9C 55 }

mbus9CVIF19		OBJECT-TYPE
			SYNTAX	INTEGER
			ACCESS	read-only
			STATUS	current
	DESCRIPTION ""
			::= { mbus9C 56 }

mbus9CValue19		OBJECT-TYPE
			SYNTAX	INTEGER
			ACCESS	read-only
			STATUS	current
	DESCRIPTION ""
			::= { mbus9C 57 }

mbus9CVIF1A		OBJECT-TYPE
			SYNTAX	INTEGER
			ACCESS	read-only
			STATUS	current
	DESCRIPTION ""
			::= { mbus9C 58 }

mbus9CValue1A		OBJECT-TYPE
			SYNTAX	INTEGER
			ACCESS	read-only
			STATUS	current
	DESCRIPTION ""
			::= { mbus9C 59 }

mbus9CVIF1B		OBJECT-TYPE
			SYNTAX	INTEGER
			ACCESS	read-only
			STATUS	current
	DESCRIPTION ""
			::= { mbus9C 60 }

mbus9CValue1B		OBJECT-TYPE
			SYNTAX	INTEGER
			ACCESS	read-only
			STATUS	current
	DESCRIPTION ""
			::= { mbus9C 61 }

mbus9CVIF1C		OBJECT-TYPE
			SYNTAX	INTEGER
			ACCESS	read-only
			STATUS	current
	DESCRIPTION ""
			::= { mbus9C 62 }

mbus9CValue1C		OBJECT-TYPE
			SYNTAX	INTEGER
			ACCESS	read-only
			STATUS	current
	DESCRIPTION ""
			::= { mbus9C 63 }

mbus9CVIF1D		OBJECT-TYPE
			SYNTAX	INTEGER
			ACCESS	read-only
			STATUS	current
	DESCRIPTION ""
			::= { mbus9C 64 }

mbus9CValue1D		OBJECT-TYPE
			SYNTAX	INTEGER
			ACCESS	read-only
			STATUS	current
	DESCRIPTION ""
			::= { mbus9C 65 }

mbus9CVIF1E		OBJECT-TYPE
			SYNTAX	INTEGER
			ACCESS	read-only
			STATUS	current
	DESCRIPTION ""
			::= { mbus9C 66 }

mbus9CValue1E		OBJECT-TYPE
			SYNTAX	INTEGER
			ACCESS	read-only
			STATUS	current
	DESCRIPTION ""
			::= { mbus9C 67 }

mbus9CVIF1F		OBJECT-TYPE
			SYNTAX	INTEGER
			ACCESS	read-only
			STATUS	current
	DESCRIPTION ""
			::= { mbus9C 68 }

mbus9CValue1F		OBJECT-TYPE
			SYNTAX	INTEGER
			ACCESS	read-only
			STATUS	current
	DESCRIPTION ""
			::= { mbus9C 69 }

mbus9CVIF20		OBJECT-TYPE
			SYNTAX	INTEGER
			ACCESS	read-only
			STATUS	current
	DESCRIPTION ""
			::= { mbus9C 70 }

mbus9CValue20		OBJECT-TYPE
			SYNTAX	INTEGER
			ACCESS	read-only
			STATUS	current
	DESCRIPTION ""
			::= { mbus9C 71 }

mbus9CVIF21		OBJECT-TYPE
			SYNTAX	INTEGER
			ACCESS	read-only
			STATUS	current
	DESCRIPTION ""
			::= { mbus9C 72 }

mbus9CValue21		OBJECT-TYPE
			SYNTAX	INTEGER
			ACCESS	read-only
			STATUS	current
	DESCRIPTION ""
			::= { mbus9C 73 }

mbus9CVIF22		OBJECT-TYPE
			SYNTAX	INTEGER
			ACCESS	read-only
			STATUS	current
	DESCRIPTION ""
			::= { mbus9C 74 }

mbus9CValue22		OBJECT-TYPE
			SYNTAX	INTEGER
			ACCESS	read-only
			STATUS	current
	DESCRIPTION ""
			::= { mbus9C 75 }

mbus9CVIF23		OBJECT-TYPE
			SYNTAX	INTEGER
			ACCESS	read-only
			STATUS	current
	DESCRIPTION ""
			::= { mbus9C 76 }

mbus9CValue23		OBJECT-TYPE
			SYNTAX	INTEGER
			ACCESS	read-only
			STATUS	current
	DESCRIPTION ""
			::= { mbus9C 77 }

mbus9CVIF24		OBJECT-TYPE
			SYNTAX	INTEGER
			ACCESS	read-only
			STATUS	current
	DESCRIPTION ""
			::= { mbus9C 78 }

mbus9CValue24		OBJECT-TYPE
			SYNTAX	INTEGER
			ACCESS	read-only
			STATUS	current
	DESCRIPTION ""
			::= { mbus9C 79 }

mbus9CVIF25		OBJECT-TYPE
			SYNTAX	INTEGER
			ACCESS	read-only
			STATUS	current
	DESCRIPTION ""
			::= { mbus9C 80 }

mbus9CValue25		OBJECT-TYPE
			SYNTAX	INTEGER
			ACCESS	read-only
			STATUS	current
	DESCRIPTION ""
			::= { mbus9C 81 }

mbus9CVIF26		OBJECT-TYPE
			SYNTAX	INTEGER
			ACCESS	read-only
			STATUS	current
	DESCRIPTION ""
			::= { mbus9C 82 }

mbus9CValue26		OBJECT-TYPE
			SYNTAX	INTEGER
			ACCESS	read-only
			STATUS	current
	DESCRIPTION ""
			::= { mbus9C 83 }

mbus9CVIF27		OBJECT-TYPE
			SYNTAX	INTEGER
			ACCESS	read-only
			STATUS	current
	DESCRIPTION ""
			::= { mbus9C 84 }

mbus9CValue27		OBJECT-TYPE
			SYNTAX	INTEGER
			ACCESS	read-only
			STATUS	current
	DESCRIPTION ""
			::= { mbus9C 85 }

mbus9CVIF28		OBJECT-TYPE
			SYNTAX	INTEGER
			ACCESS	read-only
			STATUS	current
	DESCRIPTION ""
			::= { mbus9C 86 }

mbus9CValue28		OBJECT-TYPE
			SYNTAX	INTEGER
			ACCESS	read-only
			STATUS	current
	DESCRIPTION ""
			::= { mbus9C 87 }

mbus9CVIF29		OBJECT-TYPE
			SYNTAX	INTEGER
			ACCESS	read-only
			STATUS	current
	DESCRIPTION ""
			::= { mbus9C 88 }

mbus9CValue29		OBJECT-TYPE
			SYNTAX	INTEGER
			ACCESS	read-only
			STATUS	current
	DESCRIPTION ""
			::= { mbus9C 89 }

mbus9CVIF2A		OBJECT-TYPE
			SYNTAX	INTEGER
			ACCESS	read-only
			STATUS	current
	DESCRIPTION ""
			::= { mbus9C 90 }

mbus9CValue2A		OBJECT-TYPE
			SYNTAX	INTEGER
			ACCESS	read-only
			STATUS	current
	DESCRIPTION ""
			::= { mbus9C 91 }

mbus9CVIF2B		OBJECT-TYPE
			SYNTAX	INTEGER
			ACCESS	read-only
			STATUS	current
	DESCRIPTION ""
			::= { mbus9C 92 }

mbus9CValue2B		OBJECT-TYPE
			SYNTAX	INTEGER
			ACCESS	read-only
			STATUS	current
	DESCRIPTION ""
			::= { mbus9C 93 }

mbus9CVIF2C		OBJECT-TYPE
			SYNTAX	INTEGER
			ACCESS	read-only
			STATUS	current
	DESCRIPTION ""
			::= { mbus9C 94 }

mbus9CValue2C		OBJECT-TYPE
			SYNTAX	INTEGER
			ACCESS	read-only
			STATUS	current
	DESCRIPTION ""
			::= { mbus9C 95 }

mbus9CVIF2D		OBJECT-TYPE
			SYNTAX	INTEGER
			ACCESS	read-only
			STATUS	current
	DESCRIPTION ""
			::= { mbus9C 96 }

mbus9CValue2D		OBJECT-TYPE
			SYNTAX	INTEGER
			ACCESS	read-only
			STATUS	current
	DESCRIPTION ""
			::= { mbus9C 97 }

mbus9CVIF2E		OBJECT-TYPE
			SYNTAX	INTEGER
			ACCESS	read-only
			STATUS	current
	DESCRIPTION ""
			::= { mbus9C 98 }

mbus9CValue2E		OBJECT-TYPE
			SYNTAX	INTEGER
			ACCESS	read-only
			STATUS	current
	DESCRIPTION ""
			::= { mbus9C 99 }

mbus9CVIF2F		OBJECT-TYPE
			SYNTAX	INTEGER
			ACCESS	read-only
			STATUS	current
	DESCRIPTION ""
			::= { mbus9C 100 }

mbus9CValue2F		OBJECT-TYPE
			SYNTAX	INTEGER
			ACCESS	read-only
			STATUS	current
	DESCRIPTION ""
			::= { mbus9C 101 }

mbus9D			OBJECT IDENTIFIER ::= { mbus 157 }

mbus9DIdNumber		OBJECT-TYPE
			SYNTAX	Gauge
			ACCESS	read-only
			STATUS	current
	DESCRIPTION ""
			::= { mbus9D 1 }

mbus9DManufacturer	OBJECT-TYPE
			SYNTAX	Gauge
			ACCESS	read-only
			STATUS	current
	DESCRIPTION ""
			::= { mbus9D 2 }

mbus9DVersion		OBJECT-TYPE
			SYNTAX	Gauge
			ACCESS	read-only
			STATUS	current
	DESCRIPTION ""
			::= { mbus9D 3 }

mbus9DMedium		OBJECT-TYPE
			SYNTAX	Gauge
			ACCESS	read-only
			STATUS	current
	DESCRIPTION ""
			::= { mbus9D 4 }

mbus9DStatus		OBJECT-TYPE
			SYNTAX	Gauge
			ACCESS	read-only
			STATUS	current
	DESCRIPTION ""
			::= { mbus9D 5 }

mbus9DVIF00		OBJECT-TYPE
			SYNTAX	INTEGER
			ACCESS	read-only
			STATUS	current
	DESCRIPTION ""
			::= { mbus9D 6 }

mbus9DValue00		OBJECT-TYPE
			SYNTAX	INTEGER
			ACCESS	read-only
			STATUS	current
	DESCRIPTION ""
			::= { mbus9D 7 }

mbus9DVIF01		OBJECT-TYPE
			SYNTAX	INTEGER
			ACCESS	read-only
			STATUS	current
	DESCRIPTION ""
			::= { mbus9D 8 }

mbus9DValue01		OBJECT-TYPE
			SYNTAX	INTEGER
			ACCESS	read-only
			STATUS	current
	DESCRIPTION ""
			::= { mbus9D 9 }

mbus9DVIF02		OBJECT-TYPE
			SYNTAX	INTEGER
			ACCESS	read-only
			STATUS	current
	DESCRIPTION ""
			::= { mbus9D 10 }

mbus9DValue02		OBJECT-TYPE
			SYNTAX	INTEGER
			ACCESS	read-only
			STATUS	current
	DESCRIPTION ""
			::= { mbus9D 11 }

mbus9DVIF03		OBJECT-TYPE
			SYNTAX	INTEGER
			ACCESS	read-only
			STATUS	current
	DESCRIPTION ""
			::= { mbus9D 12 }

mbus9DValue03		OBJECT-TYPE
			SYNTAX	INTEGER
			ACCESS	read-only
			STATUS	current
	DESCRIPTION ""
			::= { mbus9D 13 }

mbus9DVIF04		OBJECT-TYPE
			SYNTAX	INTEGER
			ACCESS	read-only
			STATUS	current
	DESCRIPTION ""
			::= { mbus9D 14 }

mbus9DValue04		OBJECT-TYPE
			SYNTAX	INTEGER
			ACCESS	read-only
			STATUS	current
	DESCRIPTION ""
			::= { mbus9D 15 }

mbus9DVIF05		OBJECT-TYPE
			SYNTAX	INTEGER
			ACCESS	read-only
			STATUS	current
	DESCRIPTION ""
			::= { mbus9D 16 }

mbus9DValue05		OBJECT-TYPE
			SYNTAX	INTEGER
			ACCESS	read-only
			STATUS	current
	DESCRIPTION ""
			::= { mbus9D 17 }

mbus9DVIF06		OBJECT-TYPE
			SYNTAX	INTEGER
			ACCESS	read-only
			STATUS	current
	DESCRIPTION ""
			::= { mbus9D 18 }

mbus9DValue06		OBJECT-TYPE
			SYNTAX	INTEGER
			ACCESS	read-only
			STATUS	current
	DESCRIPTION ""
			::= { mbus9D 19 }

mbus9DVIF07		OBJECT-TYPE
			SYNTAX	INTEGER
			ACCESS	read-only
			STATUS	current
	DESCRIPTION ""
			::= { mbus9D 20 }

mbus9DValue07		OBJECT-TYPE
			SYNTAX	INTEGER
			ACCESS	read-only
			STATUS	current
	DESCRIPTION ""
			::= { mbus9D 21 }

mbus9DVIF08		OBJECT-TYPE
			SYNTAX	INTEGER
			ACCESS	read-only
			STATUS	current
	DESCRIPTION ""
			::= { mbus9D 22 }

mbus9DValue08		OBJECT-TYPE
			SYNTAX	INTEGER
			ACCESS	read-only
			STATUS	current
	DESCRIPTION ""
			::= { mbus9D 23 }

mbus9DVIF09		OBJECT-TYPE
			SYNTAX	INTEGER
			ACCESS	read-only
			STATUS	current
	DESCRIPTION ""
			::= { mbus9D 24 }

mbus9DValue09		OBJECT-TYPE
			SYNTAX	INTEGER
			ACCESS	read-only
			STATUS	current
	DESCRIPTION ""
			::= { mbus9D 25 }

mbus9DVIF0A		OBJECT-TYPE
			SYNTAX	INTEGER
			ACCESS	read-only
			STATUS	current
	DESCRIPTION ""
			::= { mbus9D 26 }

mbus9DValue0A		OBJECT-TYPE
			SYNTAX	INTEGER
			ACCESS	read-only
			STATUS	current
	DESCRIPTION ""
			::= { mbus9D 27 }

mbus9DVIF0B		OBJECT-TYPE
			SYNTAX	INTEGER
			ACCESS	read-only
			STATUS	current
	DESCRIPTION ""
			::= { mbus9D 28 }

mbus9DValue0B		OBJECT-TYPE
			SYNTAX	INTEGER
			ACCESS	read-only
			STATUS	current
	DESCRIPTION ""
			::= { mbus9D 29 }

mbus9DVIF0C		OBJECT-TYPE
			SYNTAX	INTEGER
			ACCESS	read-only
			STATUS	current
	DESCRIPTION ""
			::= { mbus9D 30 }

mbus9DValue0C		OBJECT-TYPE
			SYNTAX	INTEGER
			ACCESS	read-only
			STATUS	current
	DESCRIPTION ""
			::= { mbus9D 31 }

mbus9DVIF0D		OBJECT-TYPE
			SYNTAX	INTEGER
			ACCESS	read-only
			STATUS	current
	DESCRIPTION ""
			::= { mbus9D 32 }

mbus9DValue0D		OBJECT-TYPE
			SYNTAX	INTEGER
			ACCESS	read-only
			STATUS	current
	DESCRIPTION ""
			::= { mbus9D 33 }

mbus9DVIF0E		OBJECT-TYPE
			SYNTAX	INTEGER
			ACCESS	read-only
			STATUS	current
	DESCRIPTION ""
			::= { mbus9D 34 }

mbus9DValue0E		OBJECT-TYPE
			SYNTAX	INTEGER
			ACCESS	read-only
			STATUS	current
	DESCRIPTION ""
			::= { mbus9D 35 }

mbus9DVIF0F		OBJECT-TYPE
			SYNTAX	INTEGER
			ACCESS	read-only
			STATUS	current
	DESCRIPTION ""
			::= { mbus9D 36 }

mbus9DValue0F		OBJECT-TYPE
			SYNTAX	INTEGER
			ACCESS	read-only
			STATUS	current
	DESCRIPTION ""
			::= { mbus9D 37 }

mbus9DVIF10		OBJECT-TYPE
			SYNTAX	INTEGER
			ACCESS	read-only
			STATUS	current
	DESCRIPTION ""
			::= { mbus9D 38 }

mbus9DValue10		OBJECT-TYPE
			SYNTAX	INTEGER
			ACCESS	read-only
			STATUS	current
	DESCRIPTION ""
			::= { mbus9D 39 }

mbus9DVIF11		OBJECT-TYPE
			SYNTAX	INTEGER
			ACCESS	read-only
			STATUS	current
	DESCRIPTION ""
			::= { mbus9D 40 }

mbus9DValue11		OBJECT-TYPE
			SYNTAX	INTEGER
			ACCESS	read-only
			STATUS	current
	DESCRIPTION ""
			::= { mbus9D 41 }

mbus9DVIF12		OBJECT-TYPE
			SYNTAX	INTEGER
			ACCESS	read-only
			STATUS	current
	DESCRIPTION ""
			::= { mbus9D 42 }

mbus9DValue12		OBJECT-TYPE
			SYNTAX	INTEGER
			ACCESS	read-only
			STATUS	current
	DESCRIPTION ""
			::= { mbus9D 43 }

mbus9DVIF13		OBJECT-TYPE
			SYNTAX	INTEGER
			ACCESS	read-only
			STATUS	current
	DESCRIPTION ""
			::= { mbus9D 44 }

mbus9DValue13		OBJECT-TYPE
			SYNTAX	INTEGER
			ACCESS	read-only
			STATUS	current
	DESCRIPTION ""
			::= { mbus9D 45 }

mbus9DVIF14		OBJECT-TYPE
			SYNTAX	INTEGER
			ACCESS	read-only
			STATUS	current
	DESCRIPTION ""
			::= { mbus9D 46 }

mbus9DValue14		OBJECT-TYPE
			SYNTAX	INTEGER
			ACCESS	read-only
			STATUS	current
	DESCRIPTION ""
			::= { mbus9D 47 }

mbus9DVIF15		OBJECT-TYPE
			SYNTAX	INTEGER
			ACCESS	read-only
			STATUS	current
	DESCRIPTION ""
			::= { mbus9D 48 }

mbus9DValue15		OBJECT-TYPE
			SYNTAX	INTEGER
			ACCESS	read-only
			STATUS	current
	DESCRIPTION ""
			::= { mbus9D 49 }

mbus9DVIF16		OBJECT-TYPE
			SYNTAX	INTEGER
			ACCESS	read-only
			STATUS	current
	DESCRIPTION ""
			::= { mbus9D 50 }

mbus9DValue16		OBJECT-TYPE
			SYNTAX	INTEGER
			ACCESS	read-only
			STATUS	current
	DESCRIPTION ""
			::= { mbus9D 51 }

mbus9DVIF17		OBJECT-TYPE
			SYNTAX	INTEGER
			ACCESS	read-only
			STATUS	current
	DESCRIPTION ""
			::= { mbus9D 52 }

mbus9DValue17		OBJECT-TYPE
			SYNTAX	INTEGER
			ACCESS	read-only
			STATUS	current
	DESCRIPTION ""
			::= { mbus9D 53 }

mbus9DVIF18		OBJECT-TYPE
			SYNTAX	INTEGER
			ACCESS	read-only
			STATUS	current
	DESCRIPTION ""
			::= { mbus9D 54 }

mbus9DValue18		OBJECT-TYPE
			SYNTAX	INTEGER
			ACCESS	read-only
			STATUS	current
	DESCRIPTION ""
			::= { mbus9D 55 }

mbus9DVIF19		OBJECT-TYPE
			SYNTAX	INTEGER
			ACCESS	read-only
			STATUS	current
	DESCRIPTION ""
			::= { mbus9D 56 }

mbus9DValue19		OBJECT-TYPE
			SYNTAX	INTEGER
			ACCESS	read-only
			STATUS	current
	DESCRIPTION ""
			::= { mbus9D 57 }

mbus9DVIF1A		OBJECT-TYPE
			SYNTAX	INTEGER
			ACCESS	read-only
			STATUS	current
	DESCRIPTION ""
			::= { mbus9D 58 }

mbus9DValue1A		OBJECT-TYPE
			SYNTAX	INTEGER
			ACCESS	read-only
			STATUS	current
	DESCRIPTION ""
			::= { mbus9D 59 }

mbus9DVIF1B		OBJECT-TYPE
			SYNTAX	INTEGER
			ACCESS	read-only
			STATUS	current
	DESCRIPTION ""
			::= { mbus9D 60 }

mbus9DValue1B		OBJECT-TYPE
			SYNTAX	INTEGER
			ACCESS	read-only
			STATUS	current
	DESCRIPTION ""
			::= { mbus9D 61 }

mbus9DVIF1C		OBJECT-TYPE
			SYNTAX	INTEGER
			ACCESS	read-only
			STATUS	current
	DESCRIPTION ""
			::= { mbus9D 62 }

mbus9DValue1C		OBJECT-TYPE
			SYNTAX	INTEGER
			ACCESS	read-only
			STATUS	current
	DESCRIPTION ""
			::= { mbus9D 63 }

mbus9DVIF1D		OBJECT-TYPE
			SYNTAX	INTEGER
			ACCESS	read-only
			STATUS	current
	DESCRIPTION ""
			::= { mbus9D 64 }

mbus9DValue1D		OBJECT-TYPE
			SYNTAX	INTEGER
			ACCESS	read-only
			STATUS	current
	DESCRIPTION ""
			::= { mbus9D 65 }

mbus9DVIF1E		OBJECT-TYPE
			SYNTAX	INTEGER
			ACCESS	read-only
			STATUS	current
	DESCRIPTION ""
			::= { mbus9D 66 }

mbus9DValue1E		OBJECT-TYPE
			SYNTAX	INTEGER
			ACCESS	read-only
			STATUS	current
	DESCRIPTION ""
			::= { mbus9D 67 }

mbus9DVIF1F		OBJECT-TYPE
			SYNTAX	INTEGER
			ACCESS	read-only
			STATUS	current
	DESCRIPTION ""
			::= { mbus9D 68 }

mbus9DValue1F		OBJECT-TYPE
			SYNTAX	INTEGER
			ACCESS	read-only
			STATUS	current
	DESCRIPTION ""
			::= { mbus9D 69 }

mbus9DVIF20		OBJECT-TYPE
			SYNTAX	INTEGER
			ACCESS	read-only
			STATUS	current
	DESCRIPTION ""
			::= { mbus9D 70 }

mbus9DValue20		OBJECT-TYPE
			SYNTAX	INTEGER
			ACCESS	read-only
			STATUS	current
	DESCRIPTION ""
			::= { mbus9D 71 }

mbus9DVIF21		OBJECT-TYPE
			SYNTAX	INTEGER
			ACCESS	read-only
			STATUS	current
	DESCRIPTION ""
			::= { mbus9D 72 }

mbus9DValue21		OBJECT-TYPE
			SYNTAX	INTEGER
			ACCESS	read-only
			STATUS	current
	DESCRIPTION ""
			::= { mbus9D 73 }

mbus9DVIF22		OBJECT-TYPE
			SYNTAX	INTEGER
			ACCESS	read-only
			STATUS	current
	DESCRIPTION ""
			::= { mbus9D 74 }

mbus9DValue22		OBJECT-TYPE
			SYNTAX	INTEGER
			ACCESS	read-only
			STATUS	current
	DESCRIPTION ""
			::= { mbus9D 75 }

mbus9DVIF23		OBJECT-TYPE
			SYNTAX	INTEGER
			ACCESS	read-only
			STATUS	current
	DESCRIPTION ""
			::= { mbus9D 76 }

mbus9DValue23		OBJECT-TYPE
			SYNTAX	INTEGER
			ACCESS	read-only
			STATUS	current
	DESCRIPTION ""
			::= { mbus9D 77 }

mbus9DVIF24		OBJECT-TYPE
			SYNTAX	INTEGER
			ACCESS	read-only
			STATUS	current
	DESCRIPTION ""
			::= { mbus9D 78 }

mbus9DValue24		OBJECT-TYPE
			SYNTAX	INTEGER
			ACCESS	read-only
			STATUS	current
	DESCRIPTION ""
			::= { mbus9D 79 }

mbus9DVIF25		OBJECT-TYPE
			SYNTAX	INTEGER
			ACCESS	read-only
			STATUS	current
	DESCRIPTION ""
			::= { mbus9D 80 }

mbus9DValue25		OBJECT-TYPE
			SYNTAX	INTEGER
			ACCESS	read-only
			STATUS	current
	DESCRIPTION ""
			::= { mbus9D 81 }

mbus9DVIF26		OBJECT-TYPE
			SYNTAX	INTEGER
			ACCESS	read-only
			STATUS	current
	DESCRIPTION ""
			::= { mbus9D 82 }

mbus9DValue26		OBJECT-TYPE
			SYNTAX	INTEGER
			ACCESS	read-only
			STATUS	current
	DESCRIPTION ""
			::= { mbus9D 83 }

mbus9DVIF27		OBJECT-TYPE
			SYNTAX	INTEGER
			ACCESS	read-only
			STATUS	current
	DESCRIPTION ""
			::= { mbus9D 84 }

mbus9DValue27		OBJECT-TYPE
			SYNTAX	INTEGER
			ACCESS	read-only
			STATUS	current
	DESCRIPTION ""
			::= { mbus9D 85 }

mbus9DVIF28		OBJECT-TYPE
			SYNTAX	INTEGER
			ACCESS	read-only
			STATUS	current
	DESCRIPTION ""
			::= { mbus9D 86 }

mbus9DValue28		OBJECT-TYPE
			SYNTAX	INTEGER
			ACCESS	read-only
			STATUS	current
	DESCRIPTION ""
			::= { mbus9D 87 }

mbus9DVIF29		OBJECT-TYPE
			SYNTAX	INTEGER
			ACCESS	read-only
			STATUS	current
	DESCRIPTION ""
			::= { mbus9D 88 }

mbus9DValue29		OBJECT-TYPE
			SYNTAX	INTEGER
			ACCESS	read-only
			STATUS	current
	DESCRIPTION ""
			::= { mbus9D 89 }

mbus9DVIF2A		OBJECT-TYPE
			SYNTAX	INTEGER
			ACCESS	read-only
			STATUS	current
	DESCRIPTION ""
			::= { mbus9D 90 }

mbus9DValue2A		OBJECT-TYPE
			SYNTAX	INTEGER
			ACCESS	read-only
			STATUS	current
	DESCRIPTION ""
			::= { mbus9D 91 }

mbus9DVIF2B		OBJECT-TYPE
			SYNTAX	INTEGER
			ACCESS	read-only
			STATUS	current
	DESCRIPTION ""
			::= { mbus9D 92 }

mbus9DValue2B		OBJECT-TYPE
			SYNTAX	INTEGER
			ACCESS	read-only
			STATUS	current
	DESCRIPTION ""
			::= { mbus9D 93 }

mbus9DVIF2C		OBJECT-TYPE
			SYNTAX	INTEGER
			ACCESS	read-only
			STATUS	current
	DESCRIPTION ""
			::= { mbus9D 94 }

mbus9DValue2C		OBJECT-TYPE
			SYNTAX	INTEGER
			ACCESS	read-only
			STATUS	current
	DESCRIPTION ""
			::= { mbus9D 95 }

mbus9DVIF2D		OBJECT-TYPE
			SYNTAX	INTEGER
			ACCESS	read-only
			STATUS	current
	DESCRIPTION ""
			::= { mbus9D 96 }

mbus9DValue2D		OBJECT-TYPE
			SYNTAX	INTEGER
			ACCESS	read-only
			STATUS	current
	DESCRIPTION ""
			::= { mbus9D 97 }

mbus9DVIF2E		OBJECT-TYPE
			SYNTAX	INTEGER
			ACCESS	read-only
			STATUS	current
	DESCRIPTION ""
			::= { mbus9D 98 }

mbus9DValue2E		OBJECT-TYPE
			SYNTAX	INTEGER
			ACCESS	read-only
			STATUS	current
	DESCRIPTION ""
			::= { mbus9D 99 }

mbus9DVIF2F		OBJECT-TYPE
			SYNTAX	INTEGER
			ACCESS	read-only
			STATUS	current
	DESCRIPTION ""
			::= { mbus9D 100 }

mbus9DValue2F		OBJECT-TYPE
			SYNTAX	INTEGER
			ACCESS	read-only
			STATUS	current
	DESCRIPTION ""
			::= { mbus9D 101 }

mbus9E			OBJECT IDENTIFIER ::= { mbus 158 }

mbus9EIdNumber		OBJECT-TYPE
			SYNTAX	Gauge
			ACCESS	read-only
			STATUS	current
	DESCRIPTION ""
			::= { mbus9E 1 }

mbus9EManufacturer	OBJECT-TYPE
			SYNTAX	Gauge
			ACCESS	read-only
			STATUS	current
	DESCRIPTION ""
			::= { mbus9E 2 }

mbus9EVersion		OBJECT-TYPE
			SYNTAX	Gauge
			ACCESS	read-only
			STATUS	current
	DESCRIPTION ""
			::= { mbus9E 3 }

mbus9EMedium		OBJECT-TYPE
			SYNTAX	Gauge
			ACCESS	read-only
			STATUS	current
	DESCRIPTION ""
			::= { mbus9E 4 }

mbus9EStatus		OBJECT-TYPE
			SYNTAX	Gauge
			ACCESS	read-only
			STATUS	current
	DESCRIPTION ""
			::= { mbus9E 5 }

mbus9EVIF00		OBJECT-TYPE
			SYNTAX	INTEGER
			ACCESS	read-only
			STATUS	current
	DESCRIPTION ""
			::= { mbus9E 6 }

mbus9EValue00		OBJECT-TYPE
			SYNTAX	INTEGER
			ACCESS	read-only
			STATUS	current
	DESCRIPTION ""
			::= { mbus9E 7 }

mbus9EVIF01		OBJECT-TYPE
			SYNTAX	INTEGER
			ACCESS	read-only
			STATUS	current
	DESCRIPTION ""
			::= { mbus9E 8 }

mbus9EValue01		OBJECT-TYPE
			SYNTAX	INTEGER
			ACCESS	read-only
			STATUS	current
	DESCRIPTION ""
			::= { mbus9E 9 }

mbus9EVIF02		OBJECT-TYPE
			SYNTAX	INTEGER
			ACCESS	read-only
			STATUS	current
	DESCRIPTION ""
			::= { mbus9E 10 }

mbus9EValue02		OBJECT-TYPE
			SYNTAX	INTEGER
			ACCESS	read-only
			STATUS	current
	DESCRIPTION ""
			::= { mbus9E 11 }

mbus9EVIF03		OBJECT-TYPE
			SYNTAX	INTEGER
			ACCESS	read-only
			STATUS	current
	DESCRIPTION ""
			::= { mbus9E 12 }

mbus9EValue03		OBJECT-TYPE
			SYNTAX	INTEGER
			ACCESS	read-only
			STATUS	current
	DESCRIPTION ""
			::= { mbus9E 13 }

mbus9EVIF04		OBJECT-TYPE
			SYNTAX	INTEGER
			ACCESS	read-only
			STATUS	current
	DESCRIPTION ""
			::= { mbus9E 14 }

mbus9EValue04		OBJECT-TYPE
			SYNTAX	INTEGER
			ACCESS	read-only
			STATUS	current
	DESCRIPTION ""
			::= { mbus9E 15 }

mbus9EVIF05		OBJECT-TYPE
			SYNTAX	INTEGER
			ACCESS	read-only
			STATUS	current
	DESCRIPTION ""
			::= { mbus9E 16 }

mbus9EValue05		OBJECT-TYPE
			SYNTAX	INTEGER
			ACCESS	read-only
			STATUS	current
	DESCRIPTION ""
			::= { mbus9E 17 }

mbus9EVIF06		OBJECT-TYPE
			SYNTAX	INTEGER
			ACCESS	read-only
			STATUS	current
	DESCRIPTION ""
			::= { mbus9E 18 }

mbus9EValue06		OBJECT-TYPE
			SYNTAX	INTEGER
			ACCESS	read-only
			STATUS	current
	DESCRIPTION ""
			::= { mbus9E 19 }

mbus9EVIF07		OBJECT-TYPE
			SYNTAX	INTEGER
			ACCESS	read-only
			STATUS	current
	DESCRIPTION ""
			::= { mbus9E 20 }

mbus9EValue07		OBJECT-TYPE
			SYNTAX	INTEGER
			ACCESS	read-only
			STATUS	current
	DESCRIPTION ""
			::= { mbus9E 21 }

mbus9EVIF08		OBJECT-TYPE
			SYNTAX	INTEGER
			ACCESS	read-only
			STATUS	current
	DESCRIPTION ""
			::= { mbus9E 22 }

mbus9EValue08		OBJECT-TYPE
			SYNTAX	INTEGER
			ACCESS	read-only
			STATUS	current
	DESCRIPTION ""
			::= { mbus9E 23 }

mbus9EVIF09		OBJECT-TYPE
			SYNTAX	INTEGER
			ACCESS	read-only
			STATUS	current
	DESCRIPTION ""
			::= { mbus9E 24 }

mbus9EValue09		OBJECT-TYPE
			SYNTAX	INTEGER
			ACCESS	read-only
			STATUS	current
	DESCRIPTION ""
			::= { mbus9E 25 }

mbus9EVIF0A		OBJECT-TYPE
			SYNTAX	INTEGER
			ACCESS	read-only
			STATUS	current
	DESCRIPTION ""
			::= { mbus9E 26 }

mbus9EValue0A		OBJECT-TYPE
			SYNTAX	INTEGER
			ACCESS	read-only
			STATUS	current
	DESCRIPTION ""
			::= { mbus9E 27 }

mbus9EVIF0B		OBJECT-TYPE
			SYNTAX	INTEGER
			ACCESS	read-only
			STATUS	current
	DESCRIPTION ""
			::= { mbus9E 28 }

mbus9EValue0B		OBJECT-TYPE
			SYNTAX	INTEGER
			ACCESS	read-only
			STATUS	current
	DESCRIPTION ""
			::= { mbus9E 29 }

mbus9EVIF0C		OBJECT-TYPE
			SYNTAX	INTEGER
			ACCESS	read-only
			STATUS	current
	DESCRIPTION ""
			::= { mbus9E 30 }

mbus9EValue0C		OBJECT-TYPE
			SYNTAX	INTEGER
			ACCESS	read-only
			STATUS	current
	DESCRIPTION ""
			::= { mbus9E 31 }

mbus9EVIF0D		OBJECT-TYPE
			SYNTAX	INTEGER
			ACCESS	read-only
			STATUS	current
	DESCRIPTION ""
			::= { mbus9E 32 }

mbus9EValue0D		OBJECT-TYPE
			SYNTAX	INTEGER
			ACCESS	read-only
			STATUS	current
	DESCRIPTION ""
			::= { mbus9E 33 }

mbus9EVIF0E		OBJECT-TYPE
			SYNTAX	INTEGER
			ACCESS	read-only
			STATUS	current
	DESCRIPTION ""
			::= { mbus9E 34 }

mbus9EValue0E		OBJECT-TYPE
			SYNTAX	INTEGER
			ACCESS	read-only
			STATUS	current
	DESCRIPTION ""
			::= { mbus9E 35 }

mbus9EVIF0F		OBJECT-TYPE
			SYNTAX	INTEGER
			ACCESS	read-only
			STATUS	current
	DESCRIPTION ""
			::= { mbus9E 36 }

mbus9EValue0F		OBJECT-TYPE
			SYNTAX	INTEGER
			ACCESS	read-only
			STATUS	current
	DESCRIPTION ""
			::= { mbus9E 37 }

mbus9EVIF10		OBJECT-TYPE
			SYNTAX	INTEGER
			ACCESS	read-only
			STATUS	current
	DESCRIPTION ""
			::= { mbus9E 38 }

mbus9EValue10		OBJECT-TYPE
			SYNTAX	INTEGER
			ACCESS	read-only
			STATUS	current
	DESCRIPTION ""
			::= { mbus9E 39 }

mbus9EVIF11		OBJECT-TYPE
			SYNTAX	INTEGER
			ACCESS	read-only
			STATUS	current
	DESCRIPTION ""
			::= { mbus9E 40 }

mbus9EValue11		OBJECT-TYPE
			SYNTAX	INTEGER
			ACCESS	read-only
			STATUS	current
	DESCRIPTION ""
			::= { mbus9E 41 }

mbus9EVIF12		OBJECT-TYPE
			SYNTAX	INTEGER
			ACCESS	read-only
			STATUS	current
	DESCRIPTION ""
			::= { mbus9E 42 }

mbus9EValue12		OBJECT-TYPE
			SYNTAX	INTEGER
			ACCESS	read-only
			STATUS	current
	DESCRIPTION ""
			::= { mbus9E 43 }

mbus9EVIF13		OBJECT-TYPE
			SYNTAX	INTEGER
			ACCESS	read-only
			STATUS	current
	DESCRIPTION ""
			::= { mbus9E 44 }

mbus9EValue13		OBJECT-TYPE
			SYNTAX	INTEGER
			ACCESS	read-only
			STATUS	current
	DESCRIPTION ""
			::= { mbus9E 45 }

mbus9EVIF14		OBJECT-TYPE
			SYNTAX	INTEGER
			ACCESS	read-only
			STATUS	current
	DESCRIPTION ""
			::= { mbus9E 46 }

mbus9EValue14		OBJECT-TYPE
			SYNTAX	INTEGER
			ACCESS	read-only
			STATUS	current
	DESCRIPTION ""
			::= { mbus9E 47 }

mbus9EVIF15		OBJECT-TYPE
			SYNTAX	INTEGER
			ACCESS	read-only
			STATUS	current
	DESCRIPTION ""
			::= { mbus9E 48 }

mbus9EValue15		OBJECT-TYPE
			SYNTAX	INTEGER
			ACCESS	read-only
			STATUS	current
	DESCRIPTION ""
			::= { mbus9E 49 }

mbus9EVIF16		OBJECT-TYPE
			SYNTAX	INTEGER
			ACCESS	read-only
			STATUS	current
	DESCRIPTION ""
			::= { mbus9E 50 }

mbus9EValue16		OBJECT-TYPE
			SYNTAX	INTEGER
			ACCESS	read-only
			STATUS	current
	DESCRIPTION ""
			::= { mbus9E 51 }

mbus9EVIF17		OBJECT-TYPE
			SYNTAX	INTEGER
			ACCESS	read-only
			STATUS	current
	DESCRIPTION ""
			::= { mbus9E 52 }

mbus9EValue17		OBJECT-TYPE
			SYNTAX	INTEGER
			ACCESS	read-only
			STATUS	current
	DESCRIPTION ""
			::= { mbus9E 53 }

mbus9EVIF18		OBJECT-TYPE
			SYNTAX	INTEGER
			ACCESS	read-only
			STATUS	current
	DESCRIPTION ""
			::= { mbus9E 54 }

mbus9EValue18		OBJECT-TYPE
			SYNTAX	INTEGER
			ACCESS	read-only
			STATUS	current
	DESCRIPTION ""
			::= { mbus9E 55 }

mbus9EVIF19		OBJECT-TYPE
			SYNTAX	INTEGER
			ACCESS	read-only
			STATUS	current
	DESCRIPTION ""
			::= { mbus9E 56 }

mbus9EValue19		OBJECT-TYPE
			SYNTAX	INTEGER
			ACCESS	read-only
			STATUS	current
	DESCRIPTION ""
			::= { mbus9E 57 }

mbus9EVIF1A		OBJECT-TYPE
			SYNTAX	INTEGER
			ACCESS	read-only
			STATUS	current
	DESCRIPTION ""
			::= { mbus9E 58 }

mbus9EValue1A		OBJECT-TYPE
			SYNTAX	INTEGER
			ACCESS	read-only
			STATUS	current
	DESCRIPTION ""
			::= { mbus9E 59 }

mbus9EVIF1B		OBJECT-TYPE
			SYNTAX	INTEGER
			ACCESS	read-only
			STATUS	current
	DESCRIPTION ""
			::= { mbus9E 60 }

mbus9EValue1B		OBJECT-TYPE
			SYNTAX	INTEGER
			ACCESS	read-only
			STATUS	current
	DESCRIPTION ""
			::= { mbus9E 61 }

mbus9EVIF1C		OBJECT-TYPE
			SYNTAX	INTEGER
			ACCESS	read-only
			STATUS	current
	DESCRIPTION ""
			::= { mbus9E 62 }

mbus9EValue1C		OBJECT-TYPE
			SYNTAX	INTEGER
			ACCESS	read-only
			STATUS	current
	DESCRIPTION ""
			::= { mbus9E 63 }

mbus9EVIF1D		OBJECT-TYPE
			SYNTAX	INTEGER
			ACCESS	read-only
			STATUS	current
	DESCRIPTION ""
			::= { mbus9E 64 }

mbus9EValue1D		OBJECT-TYPE
			SYNTAX	INTEGER
			ACCESS	read-only
			STATUS	current
	DESCRIPTION ""
			::= { mbus9E 65 }

mbus9EVIF1E		OBJECT-TYPE
			SYNTAX	INTEGER
			ACCESS	read-only
			STATUS	current
	DESCRIPTION ""
			::= { mbus9E 66 }

mbus9EValue1E		OBJECT-TYPE
			SYNTAX	INTEGER
			ACCESS	read-only
			STATUS	current
	DESCRIPTION ""
			::= { mbus9E 67 }

mbus9EVIF1F		OBJECT-TYPE
			SYNTAX	INTEGER
			ACCESS	read-only
			STATUS	current
	DESCRIPTION ""
			::= { mbus9E 68 }

mbus9EValue1F		OBJECT-TYPE
			SYNTAX	INTEGER
			ACCESS	read-only
			STATUS	current
	DESCRIPTION ""
			::= { mbus9E 69 }

mbus9EVIF20		OBJECT-TYPE
			SYNTAX	INTEGER
			ACCESS	read-only
			STATUS	current
	DESCRIPTION ""
			::= { mbus9E 70 }

mbus9EValue20		OBJECT-TYPE
			SYNTAX	INTEGER
			ACCESS	read-only
			STATUS	current
	DESCRIPTION ""
			::= { mbus9E 71 }

mbus9EVIF21		OBJECT-TYPE
			SYNTAX	INTEGER
			ACCESS	read-only
			STATUS	current
	DESCRIPTION ""
			::= { mbus9E 72 }

mbus9EValue21		OBJECT-TYPE
			SYNTAX	INTEGER
			ACCESS	read-only
			STATUS	current
	DESCRIPTION ""
			::= { mbus9E 73 }

mbus9EVIF22		OBJECT-TYPE
			SYNTAX	INTEGER
			ACCESS	read-only
			STATUS	current
	DESCRIPTION ""
			::= { mbus9E 74 }

mbus9EValue22		OBJECT-TYPE
			SYNTAX	INTEGER
			ACCESS	read-only
			STATUS	current
	DESCRIPTION ""
			::= { mbus9E 75 }

mbus9EVIF23		OBJECT-TYPE
			SYNTAX	INTEGER
			ACCESS	read-only
			STATUS	current
	DESCRIPTION ""
			::= { mbus9E 76 }

mbus9EValue23		OBJECT-TYPE
			SYNTAX	INTEGER
			ACCESS	read-only
			STATUS	current
	DESCRIPTION ""
			::= { mbus9E 77 }

mbus9EVIF24		OBJECT-TYPE
			SYNTAX	INTEGER
			ACCESS	read-only
			STATUS	current
	DESCRIPTION ""
			::= { mbus9E 78 }

mbus9EValue24		OBJECT-TYPE
			SYNTAX	INTEGER
			ACCESS	read-only
			STATUS	current
	DESCRIPTION ""
			::= { mbus9E 79 }

mbus9EVIF25		OBJECT-TYPE
			SYNTAX	INTEGER
			ACCESS	read-only
			STATUS	current
	DESCRIPTION ""
			::= { mbus9E 80 }

mbus9EValue25		OBJECT-TYPE
			SYNTAX	INTEGER
			ACCESS	read-only
			STATUS	current
	DESCRIPTION ""
			::= { mbus9E 81 }

mbus9EVIF26		OBJECT-TYPE
			SYNTAX	INTEGER
			ACCESS	read-only
			STATUS	current
	DESCRIPTION ""
			::= { mbus9E 82 }

mbus9EValue26		OBJECT-TYPE
			SYNTAX	INTEGER
			ACCESS	read-only
			STATUS	current
	DESCRIPTION ""
			::= { mbus9E 83 }

mbus9EVIF27		OBJECT-TYPE
			SYNTAX	INTEGER
			ACCESS	read-only
			STATUS	current
	DESCRIPTION ""
			::= { mbus9E 84 }

mbus9EValue27		OBJECT-TYPE
			SYNTAX	INTEGER
			ACCESS	read-only
			STATUS	current
	DESCRIPTION ""
			::= { mbus9E 85 }

mbus9EVIF28		OBJECT-TYPE
			SYNTAX	INTEGER
			ACCESS	read-only
			STATUS	current
	DESCRIPTION ""
			::= { mbus9E 86 }

mbus9EValue28		OBJECT-TYPE
			SYNTAX	INTEGER
			ACCESS	read-only
			STATUS	current
	DESCRIPTION ""
			::= { mbus9E 87 }

mbus9EVIF29		OBJECT-TYPE
			SYNTAX	INTEGER
			ACCESS	read-only
			STATUS	current
	DESCRIPTION ""
			::= { mbus9E 88 }

mbus9EValue29		OBJECT-TYPE
			SYNTAX	INTEGER
			ACCESS	read-only
			STATUS	current
	DESCRIPTION ""
			::= { mbus9E 89 }

mbus9EVIF2A		OBJECT-TYPE
			SYNTAX	INTEGER
			ACCESS	read-only
			STATUS	current
	DESCRIPTION ""
			::= { mbus9E 90 }

mbus9EValue2A		OBJECT-TYPE
			SYNTAX	INTEGER
			ACCESS	read-only
			STATUS	current
	DESCRIPTION ""
			::= { mbus9E 91 }

mbus9EVIF2B		OBJECT-TYPE
			SYNTAX	INTEGER
			ACCESS	read-only
			STATUS	current
	DESCRIPTION ""
			::= { mbus9E 92 }

mbus9EValue2B		OBJECT-TYPE
			SYNTAX	INTEGER
			ACCESS	read-only
			STATUS	current
	DESCRIPTION ""
			::= { mbus9E 93 }

mbus9EVIF2C		OBJECT-TYPE
			SYNTAX	INTEGER
			ACCESS	read-only
			STATUS	current
	DESCRIPTION ""
			::= { mbus9E 94 }

mbus9EValue2C		OBJECT-TYPE
			SYNTAX	INTEGER
			ACCESS	read-only
			STATUS	current
	DESCRIPTION ""
			::= { mbus9E 95 }

mbus9EVIF2D		OBJECT-TYPE
			SYNTAX	INTEGER
			ACCESS	read-only
			STATUS	current
	DESCRIPTION ""
			::= { mbus9E 96 }

mbus9EValue2D		OBJECT-TYPE
			SYNTAX	INTEGER
			ACCESS	read-only
			STATUS	current
	DESCRIPTION ""
			::= { mbus9E 97 }

mbus9EVIF2E		OBJECT-TYPE
			SYNTAX	INTEGER
			ACCESS	read-only
			STATUS	current
	DESCRIPTION ""
			::= { mbus9E 98 }

mbus9EValue2E		OBJECT-TYPE
			SYNTAX	INTEGER
			ACCESS	read-only
			STATUS	current
	DESCRIPTION ""
			::= { mbus9E 99 }

mbus9EVIF2F		OBJECT-TYPE
			SYNTAX	INTEGER
			ACCESS	read-only
			STATUS	current
	DESCRIPTION ""
			::= { mbus9E 100 }

mbus9EValue2F		OBJECT-TYPE
			SYNTAX	INTEGER
			ACCESS	read-only
			STATUS	current
	DESCRIPTION ""
			::= { mbus9E 101 }

mbus9F			OBJECT IDENTIFIER ::= { mbus 159 }

mbus9FIdNumber		OBJECT-TYPE
			SYNTAX	Gauge
			ACCESS	read-only
			STATUS	current
	DESCRIPTION ""
			::= { mbus9F 1 }

mbus9FManufacturer	OBJECT-TYPE
			SYNTAX	Gauge
			ACCESS	read-only
			STATUS	current
	DESCRIPTION ""
			::= { mbus9F 2 }

mbus9FVersion		OBJECT-TYPE
			SYNTAX	Gauge
			ACCESS	read-only
			STATUS	current
	DESCRIPTION ""
			::= { mbus9F 3 }

mbus9FMedium		OBJECT-TYPE
			SYNTAX	Gauge
			ACCESS	read-only
			STATUS	current
	DESCRIPTION ""
			::= { mbus9F 4 }

mbus9FStatus		OBJECT-TYPE
			SYNTAX	Gauge
			ACCESS	read-only
			STATUS	current
	DESCRIPTION ""
			::= { mbus9F 5 }

mbus9FVIF00		OBJECT-TYPE
			SYNTAX	INTEGER
			ACCESS	read-only
			STATUS	current
	DESCRIPTION ""
			::= { mbus9F 6 }

mbus9FValue00		OBJECT-TYPE
			SYNTAX	INTEGER
			ACCESS	read-only
			STATUS	current
	DESCRIPTION ""
			::= { mbus9F 7 }

mbus9FVIF01		OBJECT-TYPE
			SYNTAX	INTEGER
			ACCESS	read-only
			STATUS	current
	DESCRIPTION ""
			::= { mbus9F 8 }

mbus9FValue01		OBJECT-TYPE
			SYNTAX	INTEGER
			ACCESS	read-only
			STATUS	current
	DESCRIPTION ""
			::= { mbus9F 9 }

mbus9FVIF02		OBJECT-TYPE
			SYNTAX	INTEGER
			ACCESS	read-only
			STATUS	current
	DESCRIPTION ""
			::= { mbus9F 10 }

mbus9FValue02		OBJECT-TYPE
			SYNTAX	INTEGER
			ACCESS	read-only
			STATUS	current
	DESCRIPTION ""
			::= { mbus9F 11 }

mbus9FVIF03		OBJECT-TYPE
			SYNTAX	INTEGER
			ACCESS	read-only
			STATUS	current
	DESCRIPTION ""
			::= { mbus9F 12 }

mbus9FValue03		OBJECT-TYPE
			SYNTAX	INTEGER
			ACCESS	read-only
			STATUS	current
	DESCRIPTION ""
			::= { mbus9F 13 }

mbus9FVIF04		OBJECT-TYPE
			SYNTAX	INTEGER
			ACCESS	read-only
			STATUS	current
	DESCRIPTION ""
			::= { mbus9F 14 }

mbus9FValue04		OBJECT-TYPE
			SYNTAX	INTEGER
			ACCESS	read-only
			STATUS	current
	DESCRIPTION ""
			::= { mbus9F 15 }

mbus9FVIF05		OBJECT-TYPE
			SYNTAX	INTEGER
			ACCESS	read-only
			STATUS	current
	DESCRIPTION ""
			::= { mbus9F 16 }

mbus9FValue05		OBJECT-TYPE
			SYNTAX	INTEGER
			ACCESS	read-only
			STATUS	current
	DESCRIPTION ""
			::= { mbus9F 17 }

mbus9FVIF06		OBJECT-TYPE
			SYNTAX	INTEGER
			ACCESS	read-only
			STATUS	current
	DESCRIPTION ""
			::= { mbus9F 18 }

mbus9FValue06		OBJECT-TYPE
			SYNTAX	INTEGER
			ACCESS	read-only
			STATUS	current
	DESCRIPTION ""
			::= { mbus9F 19 }

mbus9FVIF07		OBJECT-TYPE
			SYNTAX	INTEGER
			ACCESS	read-only
			STATUS	current
	DESCRIPTION ""
			::= { mbus9F 20 }

mbus9FValue07		OBJECT-TYPE
			SYNTAX	INTEGER
			ACCESS	read-only
			STATUS	current
	DESCRIPTION ""
			::= { mbus9F 21 }

mbus9FVIF08		OBJECT-TYPE
			SYNTAX	INTEGER
			ACCESS	read-only
			STATUS	current
	DESCRIPTION ""
			::= { mbus9F 22 }

mbus9FValue08		OBJECT-TYPE
			SYNTAX	INTEGER
			ACCESS	read-only
			STATUS	current
	DESCRIPTION ""
			::= { mbus9F 23 }

mbus9FVIF09		OBJECT-TYPE
			SYNTAX	INTEGER
			ACCESS	read-only
			STATUS	current
	DESCRIPTION ""
			::= { mbus9F 24 }

mbus9FValue09		OBJECT-TYPE
			SYNTAX	INTEGER
			ACCESS	read-only
			STATUS	current
	DESCRIPTION ""
			::= { mbus9F 25 }

mbus9FVIF0A		OBJECT-TYPE
			SYNTAX	INTEGER
			ACCESS	read-only
			STATUS	current
	DESCRIPTION ""
			::= { mbus9F 26 }

mbus9FValue0A		OBJECT-TYPE
			SYNTAX	INTEGER
			ACCESS	read-only
			STATUS	current
	DESCRIPTION ""
			::= { mbus9F 27 }

mbus9FVIF0B		OBJECT-TYPE
			SYNTAX	INTEGER
			ACCESS	read-only
			STATUS	current
	DESCRIPTION ""
			::= { mbus9F 28 }

mbus9FValue0B		OBJECT-TYPE
			SYNTAX	INTEGER
			ACCESS	read-only
			STATUS	current
	DESCRIPTION ""
			::= { mbus9F 29 }

mbus9FVIF0C		OBJECT-TYPE
			SYNTAX	INTEGER
			ACCESS	read-only
			STATUS	current
	DESCRIPTION ""
			::= { mbus9F 30 }

mbus9FValue0C		OBJECT-TYPE
			SYNTAX	INTEGER
			ACCESS	read-only
			STATUS	current
	DESCRIPTION ""
			::= { mbus9F 31 }

mbus9FVIF0D		OBJECT-TYPE
			SYNTAX	INTEGER
			ACCESS	read-only
			STATUS	current
	DESCRIPTION ""
			::= { mbus9F 32 }

mbus9FValue0D		OBJECT-TYPE
			SYNTAX	INTEGER
			ACCESS	read-only
			STATUS	current
	DESCRIPTION ""
			::= { mbus9F 33 }

mbus9FVIF0E		OBJECT-TYPE
			SYNTAX	INTEGER
			ACCESS	read-only
			STATUS	current
	DESCRIPTION ""
			::= { mbus9F 34 }

mbus9FValue0E		OBJECT-TYPE
			SYNTAX	INTEGER
			ACCESS	read-only
			STATUS	current
	DESCRIPTION ""
			::= { mbus9F 35 }

mbus9FVIF0F		OBJECT-TYPE
			SYNTAX	INTEGER
			ACCESS	read-only
			STATUS	current
	DESCRIPTION ""
			::= { mbus9F 36 }

mbus9FValue0F		OBJECT-TYPE
			SYNTAX	INTEGER
			ACCESS	read-only
			STATUS	current
	DESCRIPTION ""
			::= { mbus9F 37 }

mbus9FVIF10		OBJECT-TYPE
			SYNTAX	INTEGER
			ACCESS	read-only
			STATUS	current
	DESCRIPTION ""
			::= { mbus9F 38 }

mbus9FValue10		OBJECT-TYPE
			SYNTAX	INTEGER
			ACCESS	read-only
			STATUS	current
	DESCRIPTION ""
			::= { mbus9F 39 }

mbus9FVIF11		OBJECT-TYPE
			SYNTAX	INTEGER
			ACCESS	read-only
			STATUS	current
	DESCRIPTION ""
			::= { mbus9F 40 }

mbus9FValue11		OBJECT-TYPE
			SYNTAX	INTEGER
			ACCESS	read-only
			STATUS	current
	DESCRIPTION ""
			::= { mbus9F 41 }

mbus9FVIF12		OBJECT-TYPE
			SYNTAX	INTEGER
			ACCESS	read-only
			STATUS	current
	DESCRIPTION ""
			::= { mbus9F 42 }

mbus9FValue12		OBJECT-TYPE
			SYNTAX	INTEGER
			ACCESS	read-only
			STATUS	current
	DESCRIPTION ""
			::= { mbus9F 43 }

mbus9FVIF13		OBJECT-TYPE
			SYNTAX	INTEGER
			ACCESS	read-only
			STATUS	current
	DESCRIPTION ""
			::= { mbus9F 44 }

mbus9FValue13		OBJECT-TYPE
			SYNTAX	INTEGER
			ACCESS	read-only
			STATUS	current
	DESCRIPTION ""
			::= { mbus9F 45 }

mbus9FVIF14		OBJECT-TYPE
			SYNTAX	INTEGER
			ACCESS	read-only
			STATUS	current
	DESCRIPTION ""
			::= { mbus9F 46 }

mbus9FValue14		OBJECT-TYPE
			SYNTAX	INTEGER
			ACCESS	read-only
			STATUS	current
	DESCRIPTION ""
			::= { mbus9F 47 }

mbus9FVIF15		OBJECT-TYPE
			SYNTAX	INTEGER
			ACCESS	read-only
			STATUS	current
	DESCRIPTION ""
			::= { mbus9F 48 }

mbus9FValue15		OBJECT-TYPE
			SYNTAX	INTEGER
			ACCESS	read-only
			STATUS	current
	DESCRIPTION ""
			::= { mbus9F 49 }

mbus9FVIF16		OBJECT-TYPE
			SYNTAX	INTEGER
			ACCESS	read-only
			STATUS	current
	DESCRIPTION ""
			::= { mbus9F 50 }

mbus9FValue16		OBJECT-TYPE
			SYNTAX	INTEGER
			ACCESS	read-only
			STATUS	current
	DESCRIPTION ""
			::= { mbus9F 51 }

mbus9FVIF17		OBJECT-TYPE
			SYNTAX	INTEGER
			ACCESS	read-only
			STATUS	current
	DESCRIPTION ""
			::= { mbus9F 52 }

mbus9FValue17		OBJECT-TYPE
			SYNTAX	INTEGER
			ACCESS	read-only
			STATUS	current
	DESCRIPTION ""
			::= { mbus9F 53 }

mbus9FVIF18		OBJECT-TYPE
			SYNTAX	INTEGER
			ACCESS	read-only
			STATUS	current
	DESCRIPTION ""
			::= { mbus9F 54 }

mbus9FValue18		OBJECT-TYPE
			SYNTAX	INTEGER
			ACCESS	read-only
			STATUS	current
	DESCRIPTION ""
			::= { mbus9F 55 }

mbus9FVIF19		OBJECT-TYPE
			SYNTAX	INTEGER
			ACCESS	read-only
			STATUS	current
	DESCRIPTION ""
			::= { mbus9F 56 }

mbus9FValue19		OBJECT-TYPE
			SYNTAX	INTEGER
			ACCESS	read-only
			STATUS	current
	DESCRIPTION ""
			::= { mbus9F 57 }

mbus9FVIF1A		OBJECT-TYPE
			SYNTAX	INTEGER
			ACCESS	read-only
			STATUS	current
	DESCRIPTION ""
			::= { mbus9F 58 }

mbus9FValue1A		OBJECT-TYPE
			SYNTAX	INTEGER
			ACCESS	read-only
			STATUS	current
	DESCRIPTION ""
			::= { mbus9F 59 }

mbus9FVIF1B		OBJECT-TYPE
			SYNTAX	INTEGER
			ACCESS	read-only
			STATUS	current
	DESCRIPTION ""
			::= { mbus9F 60 }

mbus9FValue1B		OBJECT-TYPE
			SYNTAX	INTEGER
			ACCESS	read-only
			STATUS	current
	DESCRIPTION ""
			::= { mbus9F 61 }

mbus9FVIF1C		OBJECT-TYPE
			SYNTAX	INTEGER
			ACCESS	read-only
			STATUS	current
	DESCRIPTION ""
			::= { mbus9F 62 }

mbus9FValue1C		OBJECT-TYPE
			SYNTAX	INTEGER
			ACCESS	read-only
			STATUS	current
	DESCRIPTION ""
			::= { mbus9F 63 }

mbus9FVIF1D		OBJECT-TYPE
			SYNTAX	INTEGER
			ACCESS	read-only
			STATUS	current
	DESCRIPTION ""
			::= { mbus9F 64 }

mbus9FValue1D		OBJECT-TYPE
			SYNTAX	INTEGER
			ACCESS	read-only
			STATUS	current
	DESCRIPTION ""
			::= { mbus9F 65 }

mbus9FVIF1E		OBJECT-TYPE
			SYNTAX	INTEGER
			ACCESS	read-only
			STATUS	current
	DESCRIPTION ""
			::= { mbus9F 66 }

mbus9FValue1E		OBJECT-TYPE
			SYNTAX	INTEGER
			ACCESS	read-only
			STATUS	current
	DESCRIPTION ""
			::= { mbus9F 67 }

mbus9FVIF1F		OBJECT-TYPE
			SYNTAX	INTEGER
			ACCESS	read-only
			STATUS	current
	DESCRIPTION ""
			::= { mbus9F 68 }

mbus9FValue1F		OBJECT-TYPE
			SYNTAX	INTEGER
			ACCESS	read-only
			STATUS	current
	DESCRIPTION ""
			::= { mbus9F 69 }

mbus9FVIF20		OBJECT-TYPE
			SYNTAX	INTEGER
			ACCESS	read-only
			STATUS	current
	DESCRIPTION ""
			::= { mbus9F 70 }

mbus9FValue20		OBJECT-TYPE
			SYNTAX	INTEGER
			ACCESS	read-only
			STATUS	current
	DESCRIPTION ""
			::= { mbus9F 71 }

mbus9FVIF21		OBJECT-TYPE
			SYNTAX	INTEGER
			ACCESS	read-only
			STATUS	current
	DESCRIPTION ""
			::= { mbus9F 72 }

mbus9FValue21		OBJECT-TYPE
			SYNTAX	INTEGER
			ACCESS	read-only
			STATUS	current
	DESCRIPTION ""
			::= { mbus9F 73 }

mbus9FVIF22		OBJECT-TYPE
			SYNTAX	INTEGER
			ACCESS	read-only
			STATUS	current
	DESCRIPTION ""
			::= { mbus9F 74 }

mbus9FValue22		OBJECT-TYPE
			SYNTAX	INTEGER
			ACCESS	read-only
			STATUS	current
	DESCRIPTION ""
			::= { mbus9F 75 }

mbus9FVIF23		OBJECT-TYPE
			SYNTAX	INTEGER
			ACCESS	read-only
			STATUS	current
	DESCRIPTION ""
			::= { mbus9F 76 }

mbus9FValue23		OBJECT-TYPE
			SYNTAX	INTEGER
			ACCESS	read-only
			STATUS	current
	DESCRIPTION ""
			::= { mbus9F 77 }

mbus9FVIF24		OBJECT-TYPE
			SYNTAX	INTEGER
			ACCESS	read-only
			STATUS	current
	DESCRIPTION ""
			::= { mbus9F 78 }

mbus9FValue24		OBJECT-TYPE
			SYNTAX	INTEGER
			ACCESS	read-only
			STATUS	current
	DESCRIPTION ""
			::= { mbus9F 79 }

mbus9FVIF25		OBJECT-TYPE
			SYNTAX	INTEGER
			ACCESS	read-only
			STATUS	current
	DESCRIPTION ""
			::= { mbus9F 80 }

mbus9FValue25		OBJECT-TYPE
			SYNTAX	INTEGER
			ACCESS	read-only
			STATUS	current
	DESCRIPTION ""
			::= { mbus9F 81 }

mbus9FVIF26		OBJECT-TYPE
			SYNTAX	INTEGER
			ACCESS	read-only
			STATUS	current
	DESCRIPTION ""
			::= { mbus9F 82 }

mbus9FValue26		OBJECT-TYPE
			SYNTAX	INTEGER
			ACCESS	read-only
			STATUS	current
	DESCRIPTION ""
			::= { mbus9F 83 }

mbus9FVIF27		OBJECT-TYPE
			SYNTAX	INTEGER
			ACCESS	read-only
			STATUS	current
	DESCRIPTION ""
			::= { mbus9F 84 }

mbus9FValue27		OBJECT-TYPE
			SYNTAX	INTEGER
			ACCESS	read-only
			STATUS	current
	DESCRIPTION ""
			::= { mbus9F 85 }

mbus9FVIF28		OBJECT-TYPE
			SYNTAX	INTEGER
			ACCESS	read-only
			STATUS	current
	DESCRIPTION ""
			::= { mbus9F 86 }

mbus9FValue28		OBJECT-TYPE
			SYNTAX	INTEGER
			ACCESS	read-only
			STATUS	current
	DESCRIPTION ""
			::= { mbus9F 87 }

mbus9FVIF29		OBJECT-TYPE
			SYNTAX	INTEGER
			ACCESS	read-only
			STATUS	current
	DESCRIPTION ""
			::= { mbus9F 88 }

mbus9FValue29		OBJECT-TYPE
			SYNTAX	INTEGER
			ACCESS	read-only
			STATUS	current
	DESCRIPTION ""
			::= { mbus9F 89 }

mbus9FVIF2A		OBJECT-TYPE
			SYNTAX	INTEGER
			ACCESS	read-only
			STATUS	current
	DESCRIPTION ""
			::= { mbus9F 90 }

mbus9FValue2A		OBJECT-TYPE
			SYNTAX	INTEGER
			ACCESS	read-only
			STATUS	current
	DESCRIPTION ""
			::= { mbus9F 91 }

mbus9FVIF2B		OBJECT-TYPE
			SYNTAX	INTEGER
			ACCESS	read-only
			STATUS	current
	DESCRIPTION ""
			::= { mbus9F 92 }

mbus9FValue2B		OBJECT-TYPE
			SYNTAX	INTEGER
			ACCESS	read-only
			STATUS	current
	DESCRIPTION ""
			::= { mbus9F 93 }

mbus9FVIF2C		OBJECT-TYPE
			SYNTAX	INTEGER
			ACCESS	read-only
			STATUS	current
	DESCRIPTION ""
			::= { mbus9F 94 }

mbus9FValue2C		OBJECT-TYPE
			SYNTAX	INTEGER
			ACCESS	read-only
			STATUS	current
	DESCRIPTION ""
			::= { mbus9F 95 }

mbus9FVIF2D		OBJECT-TYPE
			SYNTAX	INTEGER
			ACCESS	read-only
			STATUS	current
	DESCRIPTION ""
			::= { mbus9F 96 }

mbus9FValue2D		OBJECT-TYPE
			SYNTAX	INTEGER
			ACCESS	read-only
			STATUS	current
	DESCRIPTION ""
			::= { mbus9F 97 }

mbus9FVIF2E		OBJECT-TYPE
			SYNTAX	INTEGER
			ACCESS	read-only
			STATUS	current
	DESCRIPTION ""
			::= { mbus9F 98 }

mbus9FValue2E		OBJECT-TYPE
			SYNTAX	INTEGER
			ACCESS	read-only
			STATUS	current
	DESCRIPTION ""
			::= { mbus9F 99 }

mbus9FVIF2F		OBJECT-TYPE
			SYNTAX	INTEGER
			ACCESS	read-only
			STATUS	current
	DESCRIPTION ""
			::= { mbus9F 100 }

mbus9FValue2F		OBJECT-TYPE
			SYNTAX	INTEGER
			ACCESS	read-only
			STATUS	current
	DESCRIPTION ""
			::= { mbus9F 101 }

mbusA0			OBJECT IDENTIFIER ::= { mbus 160 }

mbusA0IdNumber		OBJECT-TYPE
			SYNTAX	Gauge
			ACCESS	read-only
			STATUS	current
	DESCRIPTION ""
			::= { mbusA0 1 }

mbusA0Manufacturer	OBJECT-TYPE
			SYNTAX	Gauge
			ACCESS	read-only
			STATUS	current
	DESCRIPTION ""
			::= { mbusA0 2 }

mbusA0Version		OBJECT-TYPE
			SYNTAX	Gauge
			ACCESS	read-only
			STATUS	current
	DESCRIPTION ""
			::= { mbusA0 3 }

mbusA0Medium		OBJECT-TYPE
			SYNTAX	Gauge
			ACCESS	read-only
			STATUS	current
	DESCRIPTION ""
			::= { mbusA0 4 }

mbusA0Status		OBJECT-TYPE
			SYNTAX	Gauge
			ACCESS	read-only
			STATUS	current
	DESCRIPTION ""
			::= { mbusA0 5 }

mbusA0VIF00		OBJECT-TYPE
			SYNTAX	INTEGER
			ACCESS	read-only
			STATUS	current
	DESCRIPTION ""
			::= { mbusA0 6 }

mbusA0Value00		OBJECT-TYPE
			SYNTAX	INTEGER
			ACCESS	read-only
			STATUS	current
	DESCRIPTION ""
			::= { mbusA0 7 }

mbusA0VIF01		OBJECT-TYPE
			SYNTAX	INTEGER
			ACCESS	read-only
			STATUS	current
	DESCRIPTION ""
			::= { mbusA0 8 }

mbusA0Value01		OBJECT-TYPE
			SYNTAX	INTEGER
			ACCESS	read-only
			STATUS	current
	DESCRIPTION ""
			::= { mbusA0 9 }

mbusA0VIF02		OBJECT-TYPE
			SYNTAX	INTEGER
			ACCESS	read-only
			STATUS	current
	DESCRIPTION ""
			::= { mbusA0 10 }

mbusA0Value02		OBJECT-TYPE
			SYNTAX	INTEGER
			ACCESS	read-only
			STATUS	current
	DESCRIPTION ""
			::= { mbusA0 11 }

mbusA0VIF03		OBJECT-TYPE
			SYNTAX	INTEGER
			ACCESS	read-only
			STATUS	current
	DESCRIPTION ""
			::= { mbusA0 12 }

mbusA0Value03		OBJECT-TYPE
			SYNTAX	INTEGER
			ACCESS	read-only
			STATUS	current
	DESCRIPTION ""
			::= { mbusA0 13 }

mbusA0VIF04		OBJECT-TYPE
			SYNTAX	INTEGER
			ACCESS	read-only
			STATUS	current
	DESCRIPTION ""
			::= { mbusA0 14 }

mbusA0Value04		OBJECT-TYPE
			SYNTAX	INTEGER
			ACCESS	read-only
			STATUS	current
	DESCRIPTION ""
			::= { mbusA0 15 }

mbusA0VIF05		OBJECT-TYPE
			SYNTAX	INTEGER
			ACCESS	read-only
			STATUS	current
	DESCRIPTION ""
			::= { mbusA0 16 }

mbusA0Value05		OBJECT-TYPE
			SYNTAX	INTEGER
			ACCESS	read-only
			STATUS	current
	DESCRIPTION ""
			::= { mbusA0 17 }

mbusA0VIF06		OBJECT-TYPE
			SYNTAX	INTEGER
			ACCESS	read-only
			STATUS	current
	DESCRIPTION ""
			::= { mbusA0 18 }

mbusA0Value06		OBJECT-TYPE
			SYNTAX	INTEGER
			ACCESS	read-only
			STATUS	current
	DESCRIPTION ""
			::= { mbusA0 19 }

mbusA0VIF07		OBJECT-TYPE
			SYNTAX	INTEGER
			ACCESS	read-only
			STATUS	current
	DESCRIPTION ""
			::= { mbusA0 20 }

mbusA0Value07		OBJECT-TYPE
			SYNTAX	INTEGER
			ACCESS	read-only
			STATUS	current
	DESCRIPTION ""
			::= { mbusA0 21 }

mbusA0VIF08		OBJECT-TYPE
			SYNTAX	INTEGER
			ACCESS	read-only
			STATUS	current
	DESCRIPTION ""
			::= { mbusA0 22 }

mbusA0Value08		OBJECT-TYPE
			SYNTAX	INTEGER
			ACCESS	read-only
			STATUS	current
	DESCRIPTION ""
			::= { mbusA0 23 }

mbusA0VIF09		OBJECT-TYPE
			SYNTAX	INTEGER
			ACCESS	read-only
			STATUS	current
	DESCRIPTION ""
			::= { mbusA0 24 }

mbusA0Value09		OBJECT-TYPE
			SYNTAX	INTEGER
			ACCESS	read-only
			STATUS	current
	DESCRIPTION ""
			::= { mbusA0 25 }

mbusA0VIF0A		OBJECT-TYPE
			SYNTAX	INTEGER
			ACCESS	read-only
			STATUS	current
	DESCRIPTION ""
			::= { mbusA0 26 }

mbusA0Value0A		OBJECT-TYPE
			SYNTAX	INTEGER
			ACCESS	read-only
			STATUS	current
	DESCRIPTION ""
			::= { mbusA0 27 }

mbusA0VIF0B		OBJECT-TYPE
			SYNTAX	INTEGER
			ACCESS	read-only
			STATUS	current
	DESCRIPTION ""
			::= { mbusA0 28 }

mbusA0Value0B		OBJECT-TYPE
			SYNTAX	INTEGER
			ACCESS	read-only
			STATUS	current
	DESCRIPTION ""
			::= { mbusA0 29 }

mbusA0VIF0C		OBJECT-TYPE
			SYNTAX	INTEGER
			ACCESS	read-only
			STATUS	current
	DESCRIPTION ""
			::= { mbusA0 30 }

mbusA0Value0C		OBJECT-TYPE
			SYNTAX	INTEGER
			ACCESS	read-only
			STATUS	current
	DESCRIPTION ""
			::= { mbusA0 31 }

mbusA0VIF0D		OBJECT-TYPE
			SYNTAX	INTEGER
			ACCESS	read-only
			STATUS	current
	DESCRIPTION ""
			::= { mbusA0 32 }

mbusA0Value0D		OBJECT-TYPE
			SYNTAX	INTEGER
			ACCESS	read-only
			STATUS	current
	DESCRIPTION ""
			::= { mbusA0 33 }

mbusA0VIF0E		OBJECT-TYPE
			SYNTAX	INTEGER
			ACCESS	read-only
			STATUS	current
	DESCRIPTION ""
			::= { mbusA0 34 }

mbusA0Value0E		OBJECT-TYPE
			SYNTAX	INTEGER
			ACCESS	read-only
			STATUS	current
	DESCRIPTION ""
			::= { mbusA0 35 }

mbusA0VIF0F		OBJECT-TYPE
			SYNTAX	INTEGER
			ACCESS	read-only
			STATUS	current
	DESCRIPTION ""
			::= { mbusA0 36 }

mbusA0Value0F		OBJECT-TYPE
			SYNTAX	INTEGER
			ACCESS	read-only
			STATUS	current
	DESCRIPTION ""
			::= { mbusA0 37 }

mbusA0VIF10		OBJECT-TYPE
			SYNTAX	INTEGER
			ACCESS	read-only
			STATUS	current
	DESCRIPTION ""
			::= { mbusA0 38 }

mbusA0Value10		OBJECT-TYPE
			SYNTAX	INTEGER
			ACCESS	read-only
			STATUS	current
	DESCRIPTION ""
			::= { mbusA0 39 }

mbusA0VIF11		OBJECT-TYPE
			SYNTAX	INTEGER
			ACCESS	read-only
			STATUS	current
	DESCRIPTION ""
			::= { mbusA0 40 }

mbusA0Value11		OBJECT-TYPE
			SYNTAX	INTEGER
			ACCESS	read-only
			STATUS	current
	DESCRIPTION ""
			::= { mbusA0 41 }

mbusA0VIF12		OBJECT-TYPE
			SYNTAX	INTEGER
			ACCESS	read-only
			STATUS	current
	DESCRIPTION ""
			::= { mbusA0 42 }

mbusA0Value12		OBJECT-TYPE
			SYNTAX	INTEGER
			ACCESS	read-only
			STATUS	current
	DESCRIPTION ""
			::= { mbusA0 43 }

mbusA0VIF13		OBJECT-TYPE
			SYNTAX	INTEGER
			ACCESS	read-only
			STATUS	current
	DESCRIPTION ""
			::= { mbusA0 44 }

mbusA0Value13		OBJECT-TYPE
			SYNTAX	INTEGER
			ACCESS	read-only
			STATUS	current
	DESCRIPTION ""
			::= { mbusA0 45 }

mbusA0VIF14		OBJECT-TYPE
			SYNTAX	INTEGER
			ACCESS	read-only
			STATUS	current
	DESCRIPTION ""
			::= { mbusA0 46 }

mbusA0Value14		OBJECT-TYPE
			SYNTAX	INTEGER
			ACCESS	read-only
			STATUS	current
	DESCRIPTION ""
			::= { mbusA0 47 }

mbusA0VIF15		OBJECT-TYPE
			SYNTAX	INTEGER
			ACCESS	read-only
			STATUS	current
	DESCRIPTION ""
			::= { mbusA0 48 }

mbusA0Value15		OBJECT-TYPE
			SYNTAX	INTEGER
			ACCESS	read-only
			STATUS	current
	DESCRIPTION ""
			::= { mbusA0 49 }

mbusA0VIF16		OBJECT-TYPE
			SYNTAX	INTEGER
			ACCESS	read-only
			STATUS	current
	DESCRIPTION ""
			::= { mbusA0 50 }

mbusA0Value16		OBJECT-TYPE
			SYNTAX	INTEGER
			ACCESS	read-only
			STATUS	current
	DESCRIPTION ""
			::= { mbusA0 51 }

mbusA0VIF17		OBJECT-TYPE
			SYNTAX	INTEGER
			ACCESS	read-only
			STATUS	current
	DESCRIPTION ""
			::= { mbusA0 52 }

mbusA0Value17		OBJECT-TYPE
			SYNTAX	INTEGER
			ACCESS	read-only
			STATUS	current
	DESCRIPTION ""
			::= { mbusA0 53 }

mbusA0VIF18		OBJECT-TYPE
			SYNTAX	INTEGER
			ACCESS	read-only
			STATUS	current
	DESCRIPTION ""
			::= { mbusA0 54 }

mbusA0Value18		OBJECT-TYPE
			SYNTAX	INTEGER
			ACCESS	read-only
			STATUS	current
	DESCRIPTION ""
			::= { mbusA0 55 }

mbusA0VIF19		OBJECT-TYPE
			SYNTAX	INTEGER
			ACCESS	read-only
			STATUS	current
	DESCRIPTION ""
			::= { mbusA0 56 }

mbusA0Value19		OBJECT-TYPE
			SYNTAX	INTEGER
			ACCESS	read-only
			STATUS	current
	DESCRIPTION ""
			::= { mbusA0 57 }

mbusA0VIF1A		OBJECT-TYPE
			SYNTAX	INTEGER
			ACCESS	read-only
			STATUS	current
	DESCRIPTION ""
			::= { mbusA0 58 }

mbusA0Value1A		OBJECT-TYPE
			SYNTAX	INTEGER
			ACCESS	read-only
			STATUS	current
	DESCRIPTION ""
			::= { mbusA0 59 }

mbusA0VIF1B		OBJECT-TYPE
			SYNTAX	INTEGER
			ACCESS	read-only
			STATUS	current
	DESCRIPTION ""
			::= { mbusA0 60 }

mbusA0Value1B		OBJECT-TYPE
			SYNTAX	INTEGER
			ACCESS	read-only
			STATUS	current
	DESCRIPTION ""
			::= { mbusA0 61 }

mbusA0VIF1C		OBJECT-TYPE
			SYNTAX	INTEGER
			ACCESS	read-only
			STATUS	current
	DESCRIPTION ""
			::= { mbusA0 62 }

mbusA0Value1C		OBJECT-TYPE
			SYNTAX	INTEGER
			ACCESS	read-only
			STATUS	current
	DESCRIPTION ""
			::= { mbusA0 63 }

mbusA0VIF1D		OBJECT-TYPE
			SYNTAX	INTEGER
			ACCESS	read-only
			STATUS	current
	DESCRIPTION ""
			::= { mbusA0 64 }

mbusA0Value1D		OBJECT-TYPE
			SYNTAX	INTEGER
			ACCESS	read-only
			STATUS	current
	DESCRIPTION ""
			::= { mbusA0 65 }

mbusA0VIF1E		OBJECT-TYPE
			SYNTAX	INTEGER
			ACCESS	read-only
			STATUS	current
	DESCRIPTION ""
			::= { mbusA0 66 }

mbusA0Value1E		OBJECT-TYPE
			SYNTAX	INTEGER
			ACCESS	read-only
			STATUS	current
	DESCRIPTION ""
			::= { mbusA0 67 }

mbusA0VIF1F		OBJECT-TYPE
			SYNTAX	INTEGER
			ACCESS	read-only
			STATUS	current
	DESCRIPTION ""
			::= { mbusA0 68 }

mbusA0Value1F		OBJECT-TYPE
			SYNTAX	INTEGER
			ACCESS	read-only
			STATUS	current
	DESCRIPTION ""
			::= { mbusA0 69 }

mbusA0VIF20		OBJECT-TYPE
			SYNTAX	INTEGER
			ACCESS	read-only
			STATUS	current
	DESCRIPTION ""
			::= { mbusA0 70 }

mbusA0Value20		OBJECT-TYPE
			SYNTAX	INTEGER
			ACCESS	read-only
			STATUS	current
	DESCRIPTION ""
			::= { mbusA0 71 }

mbusA0VIF21		OBJECT-TYPE
			SYNTAX	INTEGER
			ACCESS	read-only
			STATUS	current
	DESCRIPTION ""
			::= { mbusA0 72 }

mbusA0Value21		OBJECT-TYPE
			SYNTAX	INTEGER
			ACCESS	read-only
			STATUS	current
	DESCRIPTION ""
			::= { mbusA0 73 }

mbusA0VIF22		OBJECT-TYPE
			SYNTAX	INTEGER
			ACCESS	read-only
			STATUS	current
	DESCRIPTION ""
			::= { mbusA0 74 }

mbusA0Value22		OBJECT-TYPE
			SYNTAX	INTEGER
			ACCESS	read-only
			STATUS	current
	DESCRIPTION ""
			::= { mbusA0 75 }

mbusA0VIF23		OBJECT-TYPE
			SYNTAX	INTEGER
			ACCESS	read-only
			STATUS	current
	DESCRIPTION ""
			::= { mbusA0 76 }

mbusA0Value23		OBJECT-TYPE
			SYNTAX	INTEGER
			ACCESS	read-only
			STATUS	current
	DESCRIPTION ""
			::= { mbusA0 77 }

mbusA0VIF24		OBJECT-TYPE
			SYNTAX	INTEGER
			ACCESS	read-only
			STATUS	current
	DESCRIPTION ""
			::= { mbusA0 78 }

mbusA0Value24		OBJECT-TYPE
			SYNTAX	INTEGER
			ACCESS	read-only
			STATUS	current
	DESCRIPTION ""
			::= { mbusA0 79 }

mbusA0VIF25		OBJECT-TYPE
			SYNTAX	INTEGER
			ACCESS	read-only
			STATUS	current
	DESCRIPTION ""
			::= { mbusA0 80 }

mbusA0Value25		OBJECT-TYPE
			SYNTAX	INTEGER
			ACCESS	read-only
			STATUS	current
	DESCRIPTION ""
			::= { mbusA0 81 }

mbusA0VIF26		OBJECT-TYPE
			SYNTAX	INTEGER
			ACCESS	read-only
			STATUS	current
	DESCRIPTION ""
			::= { mbusA0 82 }

mbusA0Value26		OBJECT-TYPE
			SYNTAX	INTEGER
			ACCESS	read-only
			STATUS	current
	DESCRIPTION ""
			::= { mbusA0 83 }

mbusA0VIF27		OBJECT-TYPE
			SYNTAX	INTEGER
			ACCESS	read-only
			STATUS	current
	DESCRIPTION ""
			::= { mbusA0 84 }

mbusA0Value27		OBJECT-TYPE
			SYNTAX	INTEGER
			ACCESS	read-only
			STATUS	current
	DESCRIPTION ""
			::= { mbusA0 85 }

mbusA0VIF28		OBJECT-TYPE
			SYNTAX	INTEGER
			ACCESS	read-only
			STATUS	current
	DESCRIPTION ""
			::= { mbusA0 86 }

mbusA0Value28		OBJECT-TYPE
			SYNTAX	INTEGER
			ACCESS	read-only
			STATUS	current
	DESCRIPTION ""
			::= { mbusA0 87 }

mbusA0VIF29		OBJECT-TYPE
			SYNTAX	INTEGER
			ACCESS	read-only
			STATUS	current
	DESCRIPTION ""
			::= { mbusA0 88 }

mbusA0Value29		OBJECT-TYPE
			SYNTAX	INTEGER
			ACCESS	read-only
			STATUS	current
	DESCRIPTION ""
			::= { mbusA0 89 }

mbusA0VIF2A		OBJECT-TYPE
			SYNTAX	INTEGER
			ACCESS	read-only
			STATUS	current
	DESCRIPTION ""
			::= { mbusA0 90 }

mbusA0Value2A		OBJECT-TYPE
			SYNTAX	INTEGER
			ACCESS	read-only
			STATUS	current
	DESCRIPTION ""
			::= { mbusA0 91 }

mbusA0VIF2B		OBJECT-TYPE
			SYNTAX	INTEGER
			ACCESS	read-only
			STATUS	current
	DESCRIPTION ""
			::= { mbusA0 92 }

mbusA0Value2B		OBJECT-TYPE
			SYNTAX	INTEGER
			ACCESS	read-only
			STATUS	current
	DESCRIPTION ""
			::= { mbusA0 93 }

mbusA0VIF2C		OBJECT-TYPE
			SYNTAX	INTEGER
			ACCESS	read-only
			STATUS	current
	DESCRIPTION ""
			::= { mbusA0 94 }

mbusA0Value2C		OBJECT-TYPE
			SYNTAX	INTEGER
			ACCESS	read-only
			STATUS	current
	DESCRIPTION ""
			::= { mbusA0 95 }

mbusA0VIF2D		OBJECT-TYPE
			SYNTAX	INTEGER
			ACCESS	read-only
			STATUS	current
	DESCRIPTION ""
			::= { mbusA0 96 }

mbusA0Value2D		OBJECT-TYPE
			SYNTAX	INTEGER
			ACCESS	read-only
			STATUS	current
	DESCRIPTION ""
			::= { mbusA0 97 }

mbusA0VIF2E		OBJECT-TYPE
			SYNTAX	INTEGER
			ACCESS	read-only
			STATUS	current
	DESCRIPTION ""
			::= { mbusA0 98 }

mbusA0Value2E		OBJECT-TYPE
			SYNTAX	INTEGER
			ACCESS	read-only
			STATUS	current
	DESCRIPTION ""
			::= { mbusA0 99 }

mbusA0VIF2F		OBJECT-TYPE
			SYNTAX	INTEGER
			ACCESS	read-only
			STATUS	current
	DESCRIPTION ""
			::= { mbusA0 100 }

mbusA0Value2F		OBJECT-TYPE
			SYNTAX	INTEGER
			ACCESS	read-only
			STATUS	current
	DESCRIPTION ""
			::= { mbusA0 101 }

mbusA1			OBJECT IDENTIFIER ::= { mbus 161 }

mbusA1IdNumber		OBJECT-TYPE
			SYNTAX	Gauge
			ACCESS	read-only
			STATUS	current
	DESCRIPTION ""
			::= { mbusA1 1 }

mbusA1Manufacturer	OBJECT-TYPE
			SYNTAX	Gauge
			ACCESS	read-only
			STATUS	current
	DESCRIPTION ""
			::= { mbusA1 2 }

mbusA1Version		OBJECT-TYPE
			SYNTAX	Gauge
			ACCESS	read-only
			STATUS	current
	DESCRIPTION ""
			::= { mbusA1 3 }

mbusA1Medium		OBJECT-TYPE
			SYNTAX	Gauge
			ACCESS	read-only
			STATUS	current
	DESCRIPTION ""
			::= { mbusA1 4 }

mbusA1Status		OBJECT-TYPE
			SYNTAX	Gauge
			ACCESS	read-only
			STATUS	current
	DESCRIPTION ""
			::= { mbusA1 5 }

mbusA1VIF00		OBJECT-TYPE
			SYNTAX	INTEGER
			ACCESS	read-only
			STATUS	current
	DESCRIPTION ""
			::= { mbusA1 6 }

mbusA1Value00		OBJECT-TYPE
			SYNTAX	INTEGER
			ACCESS	read-only
			STATUS	current
	DESCRIPTION ""
			::= { mbusA1 7 }

mbusA1VIF01		OBJECT-TYPE
			SYNTAX	INTEGER
			ACCESS	read-only
			STATUS	current
	DESCRIPTION ""
			::= { mbusA1 8 }

mbusA1Value01		OBJECT-TYPE
			SYNTAX	INTEGER
			ACCESS	read-only
			STATUS	current
	DESCRIPTION ""
			::= { mbusA1 9 }

mbusA1VIF02		OBJECT-TYPE
			SYNTAX	INTEGER
			ACCESS	read-only
			STATUS	current
	DESCRIPTION ""
			::= { mbusA1 10 }

mbusA1Value02		OBJECT-TYPE
			SYNTAX	INTEGER
			ACCESS	read-only
			STATUS	current
	DESCRIPTION ""
			::= { mbusA1 11 }

mbusA1VIF03		OBJECT-TYPE
			SYNTAX	INTEGER
			ACCESS	read-only
			STATUS	current
	DESCRIPTION ""
			::= { mbusA1 12 }

mbusA1Value03		OBJECT-TYPE
			SYNTAX	INTEGER
			ACCESS	read-only
			STATUS	current
	DESCRIPTION ""
			::= { mbusA1 13 }

mbusA1VIF04		OBJECT-TYPE
			SYNTAX	INTEGER
			ACCESS	read-only
			STATUS	current
	DESCRIPTION ""
			::= { mbusA1 14 }

mbusA1Value04		OBJECT-TYPE
			SYNTAX	INTEGER
			ACCESS	read-only
			STATUS	current
	DESCRIPTION ""
			::= { mbusA1 15 }

mbusA1VIF05		OBJECT-TYPE
			SYNTAX	INTEGER
			ACCESS	read-only
			STATUS	current
	DESCRIPTION ""
			::= { mbusA1 16 }

mbusA1Value05		OBJECT-TYPE
			SYNTAX	INTEGER
			ACCESS	read-only
			STATUS	current
	DESCRIPTION ""
			::= { mbusA1 17 }

mbusA1VIF06		OBJECT-TYPE
			SYNTAX	INTEGER
			ACCESS	read-only
			STATUS	current
	DESCRIPTION ""
			::= { mbusA1 18 }

mbusA1Value06		OBJECT-TYPE
			SYNTAX	INTEGER
			ACCESS	read-only
			STATUS	current
	DESCRIPTION ""
			::= { mbusA1 19 }

mbusA1VIF07		OBJECT-TYPE
			SYNTAX	INTEGER
			ACCESS	read-only
			STATUS	current
	DESCRIPTION ""
			::= { mbusA1 20 }

mbusA1Value07		OBJECT-TYPE
			SYNTAX	INTEGER
			ACCESS	read-only
			STATUS	current
	DESCRIPTION ""
			::= { mbusA1 21 }

mbusA1VIF08		OBJECT-TYPE
			SYNTAX	INTEGER
			ACCESS	read-only
			STATUS	current
	DESCRIPTION ""
			::= { mbusA1 22 }

mbusA1Value08		OBJECT-TYPE
			SYNTAX	INTEGER
			ACCESS	read-only
			STATUS	current
	DESCRIPTION ""
			::= { mbusA1 23 }

mbusA1VIF09		OBJECT-TYPE
			SYNTAX	INTEGER
			ACCESS	read-only
			STATUS	current
	DESCRIPTION ""
			::= { mbusA1 24 }

mbusA1Value09		OBJECT-TYPE
			SYNTAX	INTEGER
			ACCESS	read-only
			STATUS	current
	DESCRIPTION ""
			::= { mbusA1 25 }

mbusA1VIF0A		OBJECT-TYPE
			SYNTAX	INTEGER
			ACCESS	read-only
			STATUS	current
	DESCRIPTION ""
			::= { mbusA1 26 }

mbusA1Value0A		OBJECT-TYPE
			SYNTAX	INTEGER
			ACCESS	read-only
			STATUS	current
	DESCRIPTION ""
			::= { mbusA1 27 }

mbusA1VIF0B		OBJECT-TYPE
			SYNTAX	INTEGER
			ACCESS	read-only
			STATUS	current
	DESCRIPTION ""
			::= { mbusA1 28 }

mbusA1Value0B		OBJECT-TYPE
			SYNTAX	INTEGER
			ACCESS	read-only
			STATUS	current
	DESCRIPTION ""
			::= { mbusA1 29 }

mbusA1VIF0C		OBJECT-TYPE
			SYNTAX	INTEGER
			ACCESS	read-only
			STATUS	current
	DESCRIPTION ""
			::= { mbusA1 30 }

mbusA1Value0C		OBJECT-TYPE
			SYNTAX	INTEGER
			ACCESS	read-only
			STATUS	current
	DESCRIPTION ""
			::= { mbusA1 31 }

mbusA1VIF0D		OBJECT-TYPE
			SYNTAX	INTEGER
			ACCESS	read-only
			STATUS	current
	DESCRIPTION ""
			::= { mbusA1 32 }

mbusA1Value0D		OBJECT-TYPE
			SYNTAX	INTEGER
			ACCESS	read-only
			STATUS	current
	DESCRIPTION ""
			::= { mbusA1 33 }

mbusA1VIF0E		OBJECT-TYPE
			SYNTAX	INTEGER
			ACCESS	read-only
			STATUS	current
	DESCRIPTION ""
			::= { mbusA1 34 }

mbusA1Value0E		OBJECT-TYPE
			SYNTAX	INTEGER
			ACCESS	read-only
			STATUS	current
	DESCRIPTION ""
			::= { mbusA1 35 }

mbusA1VIF0F		OBJECT-TYPE
			SYNTAX	INTEGER
			ACCESS	read-only
			STATUS	current
	DESCRIPTION ""
			::= { mbusA1 36 }

mbusA1Value0F		OBJECT-TYPE
			SYNTAX	INTEGER
			ACCESS	read-only
			STATUS	current
	DESCRIPTION ""
			::= { mbusA1 37 }

mbusA1VIF10		OBJECT-TYPE
			SYNTAX	INTEGER
			ACCESS	read-only
			STATUS	current
	DESCRIPTION ""
			::= { mbusA1 38 }

mbusA1Value10		OBJECT-TYPE
			SYNTAX	INTEGER
			ACCESS	read-only
			STATUS	current
	DESCRIPTION ""
			::= { mbusA1 39 }

mbusA1VIF11		OBJECT-TYPE
			SYNTAX	INTEGER
			ACCESS	read-only
			STATUS	current
	DESCRIPTION ""
			::= { mbusA1 40 }

mbusA1Value11		OBJECT-TYPE
			SYNTAX	INTEGER
			ACCESS	read-only
			STATUS	current
	DESCRIPTION ""
			::= { mbusA1 41 }

mbusA1VIF12		OBJECT-TYPE
			SYNTAX	INTEGER
			ACCESS	read-only
			STATUS	current
	DESCRIPTION ""
			::= { mbusA1 42 }

mbusA1Value12		OBJECT-TYPE
			SYNTAX	INTEGER
			ACCESS	read-only
			STATUS	current
	DESCRIPTION ""
			::= { mbusA1 43 }

mbusA1VIF13		OBJECT-TYPE
			SYNTAX	INTEGER
			ACCESS	read-only
			STATUS	current
	DESCRIPTION ""
			::= { mbusA1 44 }

mbusA1Value13		OBJECT-TYPE
			SYNTAX	INTEGER
			ACCESS	read-only
			STATUS	current
	DESCRIPTION ""
			::= { mbusA1 45 }

mbusA1VIF14		OBJECT-TYPE
			SYNTAX	INTEGER
			ACCESS	read-only
			STATUS	current
	DESCRIPTION ""
			::= { mbusA1 46 }

mbusA1Value14		OBJECT-TYPE
			SYNTAX	INTEGER
			ACCESS	read-only
			STATUS	current
	DESCRIPTION ""
			::= { mbusA1 47 }

mbusA1VIF15		OBJECT-TYPE
			SYNTAX	INTEGER
			ACCESS	read-only
			STATUS	current
	DESCRIPTION ""
			::= { mbusA1 48 }

mbusA1Value15		OBJECT-TYPE
			SYNTAX	INTEGER
			ACCESS	read-only
			STATUS	current
	DESCRIPTION ""
			::= { mbusA1 49 }

mbusA1VIF16		OBJECT-TYPE
			SYNTAX	INTEGER
			ACCESS	read-only
			STATUS	current
	DESCRIPTION ""
			::= { mbusA1 50 }

mbusA1Value16		OBJECT-TYPE
			SYNTAX	INTEGER
			ACCESS	read-only
			STATUS	current
	DESCRIPTION ""
			::= { mbusA1 51 }

mbusA1VIF17		OBJECT-TYPE
			SYNTAX	INTEGER
			ACCESS	read-only
			STATUS	current
	DESCRIPTION ""
			::= { mbusA1 52 }

mbusA1Value17		OBJECT-TYPE
			SYNTAX	INTEGER
			ACCESS	read-only
			STATUS	current
	DESCRIPTION ""
			::= { mbusA1 53 }

mbusA1VIF18		OBJECT-TYPE
			SYNTAX	INTEGER
			ACCESS	read-only
			STATUS	current
	DESCRIPTION ""
			::= { mbusA1 54 }

mbusA1Value18		OBJECT-TYPE
			SYNTAX	INTEGER
			ACCESS	read-only
			STATUS	current
	DESCRIPTION ""
			::= { mbusA1 55 }

mbusA1VIF19		OBJECT-TYPE
			SYNTAX	INTEGER
			ACCESS	read-only
			STATUS	current
	DESCRIPTION ""
			::= { mbusA1 56 }

mbusA1Value19		OBJECT-TYPE
			SYNTAX	INTEGER
			ACCESS	read-only
			STATUS	current
	DESCRIPTION ""
			::= { mbusA1 57 }

mbusA1VIF1A		OBJECT-TYPE
			SYNTAX	INTEGER
			ACCESS	read-only
			STATUS	current
	DESCRIPTION ""
			::= { mbusA1 58 }

mbusA1Value1A		OBJECT-TYPE
			SYNTAX	INTEGER
			ACCESS	read-only
			STATUS	current
	DESCRIPTION ""
			::= { mbusA1 59 }

mbusA1VIF1B		OBJECT-TYPE
			SYNTAX	INTEGER
			ACCESS	read-only
			STATUS	current
	DESCRIPTION ""
			::= { mbusA1 60 }

mbusA1Value1B		OBJECT-TYPE
			SYNTAX	INTEGER
			ACCESS	read-only
			STATUS	current
	DESCRIPTION ""
			::= { mbusA1 61 }

mbusA1VIF1C		OBJECT-TYPE
			SYNTAX	INTEGER
			ACCESS	read-only
			STATUS	current
	DESCRIPTION ""
			::= { mbusA1 62 }

mbusA1Value1C		OBJECT-TYPE
			SYNTAX	INTEGER
			ACCESS	read-only
			STATUS	current
	DESCRIPTION ""
			::= { mbusA1 63 }

mbusA1VIF1D		OBJECT-TYPE
			SYNTAX	INTEGER
			ACCESS	read-only
			STATUS	current
	DESCRIPTION ""
			::= { mbusA1 64 }

mbusA1Value1D		OBJECT-TYPE
			SYNTAX	INTEGER
			ACCESS	read-only
			STATUS	current
	DESCRIPTION ""
			::= { mbusA1 65 }

mbusA1VIF1E		OBJECT-TYPE
			SYNTAX	INTEGER
			ACCESS	read-only
			STATUS	current
	DESCRIPTION ""
			::= { mbusA1 66 }

mbusA1Value1E		OBJECT-TYPE
			SYNTAX	INTEGER
			ACCESS	read-only
			STATUS	current
	DESCRIPTION ""
			::= { mbusA1 67 }

mbusA1VIF1F		OBJECT-TYPE
			SYNTAX	INTEGER
			ACCESS	read-only
			STATUS	current
	DESCRIPTION ""
			::= { mbusA1 68 }

mbusA1Value1F		OBJECT-TYPE
			SYNTAX	INTEGER
			ACCESS	read-only
			STATUS	current
	DESCRIPTION ""
			::= { mbusA1 69 }

mbusA1VIF20		OBJECT-TYPE
			SYNTAX	INTEGER
			ACCESS	read-only
			STATUS	current
	DESCRIPTION ""
			::= { mbusA1 70 }

mbusA1Value20		OBJECT-TYPE
			SYNTAX	INTEGER
			ACCESS	read-only
			STATUS	current
	DESCRIPTION ""
			::= { mbusA1 71 }

mbusA1VIF21		OBJECT-TYPE
			SYNTAX	INTEGER
			ACCESS	read-only
			STATUS	current
	DESCRIPTION ""
			::= { mbusA1 72 }

mbusA1Value21		OBJECT-TYPE
			SYNTAX	INTEGER
			ACCESS	read-only
			STATUS	current
	DESCRIPTION ""
			::= { mbusA1 73 }

mbusA1VIF22		OBJECT-TYPE
			SYNTAX	INTEGER
			ACCESS	read-only
			STATUS	current
	DESCRIPTION ""
			::= { mbusA1 74 }

mbusA1Value22		OBJECT-TYPE
			SYNTAX	INTEGER
			ACCESS	read-only
			STATUS	current
	DESCRIPTION ""
			::= { mbusA1 75 }

mbusA1VIF23		OBJECT-TYPE
			SYNTAX	INTEGER
			ACCESS	read-only
			STATUS	current
	DESCRIPTION ""
			::= { mbusA1 76 }

mbusA1Value23		OBJECT-TYPE
			SYNTAX	INTEGER
			ACCESS	read-only
			STATUS	current
	DESCRIPTION ""
			::= { mbusA1 77 }

mbusA1VIF24		OBJECT-TYPE
			SYNTAX	INTEGER
			ACCESS	read-only
			STATUS	current
	DESCRIPTION ""
			::= { mbusA1 78 }

mbusA1Value24		OBJECT-TYPE
			SYNTAX	INTEGER
			ACCESS	read-only
			STATUS	current
	DESCRIPTION ""
			::= { mbusA1 79 }

mbusA1VIF25		OBJECT-TYPE
			SYNTAX	INTEGER
			ACCESS	read-only
			STATUS	current
	DESCRIPTION ""
			::= { mbusA1 80 }

mbusA1Value25		OBJECT-TYPE
			SYNTAX	INTEGER
			ACCESS	read-only
			STATUS	current
	DESCRIPTION ""
			::= { mbusA1 81 }

mbusA1VIF26		OBJECT-TYPE
			SYNTAX	INTEGER
			ACCESS	read-only
			STATUS	current
	DESCRIPTION ""
			::= { mbusA1 82 }

mbusA1Value26		OBJECT-TYPE
			SYNTAX	INTEGER
			ACCESS	read-only
			STATUS	current
	DESCRIPTION ""
			::= { mbusA1 83 }

mbusA1VIF27		OBJECT-TYPE
			SYNTAX	INTEGER
			ACCESS	read-only
			STATUS	current
	DESCRIPTION ""
			::= { mbusA1 84 }

mbusA1Value27		OBJECT-TYPE
			SYNTAX	INTEGER
			ACCESS	read-only
			STATUS	current
	DESCRIPTION ""
			::= { mbusA1 85 }

mbusA1VIF28		OBJECT-TYPE
			SYNTAX	INTEGER
			ACCESS	read-only
			STATUS	current
	DESCRIPTION ""
			::= { mbusA1 86 }

mbusA1Value28		OBJECT-TYPE
			SYNTAX	INTEGER
			ACCESS	read-only
			STATUS	current
	DESCRIPTION ""
			::= { mbusA1 87 }

mbusA1VIF29		OBJECT-TYPE
			SYNTAX	INTEGER
			ACCESS	read-only
			STATUS	current
	DESCRIPTION ""
			::= { mbusA1 88 }

mbusA1Value29		OBJECT-TYPE
			SYNTAX	INTEGER
			ACCESS	read-only
			STATUS	current
	DESCRIPTION ""
			::= { mbusA1 89 }

mbusA1VIF2A		OBJECT-TYPE
			SYNTAX	INTEGER
			ACCESS	read-only
			STATUS	current
	DESCRIPTION ""
			::= { mbusA1 90 }

mbusA1Value2A		OBJECT-TYPE
			SYNTAX	INTEGER
			ACCESS	read-only
			STATUS	current
	DESCRIPTION ""
			::= { mbusA1 91 }

mbusA1VIF2B		OBJECT-TYPE
			SYNTAX	INTEGER
			ACCESS	read-only
			STATUS	current
	DESCRIPTION ""
			::= { mbusA1 92 }

mbusA1Value2B		OBJECT-TYPE
			SYNTAX	INTEGER
			ACCESS	read-only
			STATUS	current
	DESCRIPTION ""
			::= { mbusA1 93 }

mbusA1VIF2C		OBJECT-TYPE
			SYNTAX	INTEGER
			ACCESS	read-only
			STATUS	current
	DESCRIPTION ""
			::= { mbusA1 94 }

mbusA1Value2C		OBJECT-TYPE
			SYNTAX	INTEGER
			ACCESS	read-only
			STATUS	current
	DESCRIPTION ""
			::= { mbusA1 95 }

mbusA1VIF2D		OBJECT-TYPE
			SYNTAX	INTEGER
			ACCESS	read-only
			STATUS	current
	DESCRIPTION ""
			::= { mbusA1 96 }

mbusA1Value2D		OBJECT-TYPE
			SYNTAX	INTEGER
			ACCESS	read-only
			STATUS	current
	DESCRIPTION ""
			::= { mbusA1 97 }

mbusA1VIF2E		OBJECT-TYPE
			SYNTAX	INTEGER
			ACCESS	read-only
			STATUS	current
	DESCRIPTION ""
			::= { mbusA1 98 }

mbusA1Value2E		OBJECT-TYPE
			SYNTAX	INTEGER
			ACCESS	read-only
			STATUS	current
	DESCRIPTION ""
			::= { mbusA1 99 }

mbusA1VIF2F		OBJECT-TYPE
			SYNTAX	INTEGER
			ACCESS	read-only
			STATUS	current
	DESCRIPTION ""
			::= { mbusA1 100 }

mbusA1Value2F		OBJECT-TYPE
			SYNTAX	INTEGER
			ACCESS	read-only
			STATUS	current
	DESCRIPTION ""
			::= { mbusA1 101 }

mbusA2			OBJECT IDENTIFIER ::= { mbus 162 }

mbusA2IdNumber		OBJECT-TYPE
			SYNTAX	Gauge
			ACCESS	read-only
			STATUS	current
	DESCRIPTION ""
			::= { mbusA2 1 }

mbusA2Manufacturer	OBJECT-TYPE
			SYNTAX	Gauge
			ACCESS	read-only
			STATUS	current
	DESCRIPTION ""
			::= { mbusA2 2 }

mbusA2Version		OBJECT-TYPE
			SYNTAX	Gauge
			ACCESS	read-only
			STATUS	current
	DESCRIPTION ""
			::= { mbusA2 3 }

mbusA2Medium		OBJECT-TYPE
			SYNTAX	Gauge
			ACCESS	read-only
			STATUS	current
	DESCRIPTION ""
			::= { mbusA2 4 }

mbusA2Status		OBJECT-TYPE
			SYNTAX	Gauge
			ACCESS	read-only
			STATUS	current
	DESCRIPTION ""
			::= { mbusA2 5 }

mbusA2VIF00		OBJECT-TYPE
			SYNTAX	INTEGER
			ACCESS	read-only
			STATUS	current
	DESCRIPTION ""
			::= { mbusA2 6 }

mbusA2Value00		OBJECT-TYPE
			SYNTAX	INTEGER
			ACCESS	read-only
			STATUS	current
	DESCRIPTION ""
			::= { mbusA2 7 }

mbusA2VIF01		OBJECT-TYPE
			SYNTAX	INTEGER
			ACCESS	read-only
			STATUS	current
	DESCRIPTION ""
			::= { mbusA2 8 }

mbusA2Value01		OBJECT-TYPE
			SYNTAX	INTEGER
			ACCESS	read-only
			STATUS	current
	DESCRIPTION ""
			::= { mbusA2 9 }

mbusA2VIF02		OBJECT-TYPE
			SYNTAX	INTEGER
			ACCESS	read-only
			STATUS	current
	DESCRIPTION ""
			::= { mbusA2 10 }

mbusA2Value02		OBJECT-TYPE
			SYNTAX	INTEGER
			ACCESS	read-only
			STATUS	current
	DESCRIPTION ""
			::= { mbusA2 11 }

mbusA2VIF03		OBJECT-TYPE
			SYNTAX	INTEGER
			ACCESS	read-only
			STATUS	current
	DESCRIPTION ""
			::= { mbusA2 12 }

mbusA2Value03		OBJECT-TYPE
			SYNTAX	INTEGER
			ACCESS	read-only
			STATUS	current
	DESCRIPTION ""
			::= { mbusA2 13 }

mbusA2VIF04		OBJECT-TYPE
			SYNTAX	INTEGER
			ACCESS	read-only
			STATUS	current
	DESCRIPTION ""
			::= { mbusA2 14 }

mbusA2Value04		OBJECT-TYPE
			SYNTAX	INTEGER
			ACCESS	read-only
			STATUS	current
	DESCRIPTION ""
			::= { mbusA2 15 }

mbusA2VIF05		OBJECT-TYPE
			SYNTAX	INTEGER
			ACCESS	read-only
			STATUS	current
	DESCRIPTION ""
			::= { mbusA2 16 }

mbusA2Value05		OBJECT-TYPE
			SYNTAX	INTEGER
			ACCESS	read-only
			STATUS	current
	DESCRIPTION ""
			::= { mbusA2 17 }

mbusA2VIF06		OBJECT-TYPE
			SYNTAX	INTEGER
			ACCESS	read-only
			STATUS	current
	DESCRIPTION ""
			::= { mbusA2 18 }

mbusA2Value06		OBJECT-TYPE
			SYNTAX	INTEGER
			ACCESS	read-only
			STATUS	current
	DESCRIPTION ""
			::= { mbusA2 19 }

mbusA2VIF07		OBJECT-TYPE
			SYNTAX	INTEGER
			ACCESS	read-only
			STATUS	current
	DESCRIPTION ""
			::= { mbusA2 20 }

mbusA2Value07		OBJECT-TYPE
			SYNTAX	INTEGER
			ACCESS	read-only
			STATUS	current
	DESCRIPTION ""
			::= { mbusA2 21 }

mbusA2VIF08		OBJECT-TYPE
			SYNTAX	INTEGER
			ACCESS	read-only
			STATUS	current
	DESCRIPTION ""
			::= { mbusA2 22 }

mbusA2Value08		OBJECT-TYPE
			SYNTAX	INTEGER
			ACCESS	read-only
			STATUS	current
	DESCRIPTION ""
			::= { mbusA2 23 }

mbusA2VIF09		OBJECT-TYPE
			SYNTAX	INTEGER
			ACCESS	read-only
			STATUS	current
	DESCRIPTION ""
			::= { mbusA2 24 }

mbusA2Value09		OBJECT-TYPE
			SYNTAX	INTEGER
			ACCESS	read-only
			STATUS	current
	DESCRIPTION ""
			::= { mbusA2 25 }

mbusA2VIF0A		OBJECT-TYPE
			SYNTAX	INTEGER
			ACCESS	read-only
			STATUS	current
	DESCRIPTION ""
			::= { mbusA2 26 }

mbusA2Value0A		OBJECT-TYPE
			SYNTAX	INTEGER
			ACCESS	read-only
			STATUS	current
	DESCRIPTION ""
			::= { mbusA2 27 }

mbusA2VIF0B		OBJECT-TYPE
			SYNTAX	INTEGER
			ACCESS	read-only
			STATUS	current
	DESCRIPTION ""
			::= { mbusA2 28 }

mbusA2Value0B		OBJECT-TYPE
			SYNTAX	INTEGER
			ACCESS	read-only
			STATUS	current
	DESCRIPTION ""
			::= { mbusA2 29 }

mbusA2VIF0C		OBJECT-TYPE
			SYNTAX	INTEGER
			ACCESS	read-only
			STATUS	current
	DESCRIPTION ""
			::= { mbusA2 30 }

mbusA2Value0C		OBJECT-TYPE
			SYNTAX	INTEGER
			ACCESS	read-only
			STATUS	current
	DESCRIPTION ""
			::= { mbusA2 31 }

mbusA2VIF0D		OBJECT-TYPE
			SYNTAX	INTEGER
			ACCESS	read-only
			STATUS	current
	DESCRIPTION ""
			::= { mbusA2 32 }

mbusA2Value0D		OBJECT-TYPE
			SYNTAX	INTEGER
			ACCESS	read-only
			STATUS	current
	DESCRIPTION ""
			::= { mbusA2 33 }

mbusA2VIF0E		OBJECT-TYPE
			SYNTAX	INTEGER
			ACCESS	read-only
			STATUS	current
	DESCRIPTION ""
			::= { mbusA2 34 }

mbusA2Value0E		OBJECT-TYPE
			SYNTAX	INTEGER
			ACCESS	read-only
			STATUS	current
	DESCRIPTION ""
			::= { mbusA2 35 }

mbusA2VIF0F		OBJECT-TYPE
			SYNTAX	INTEGER
			ACCESS	read-only
			STATUS	current
	DESCRIPTION ""
			::= { mbusA2 36 }

mbusA2Value0F		OBJECT-TYPE
			SYNTAX	INTEGER
			ACCESS	read-only
			STATUS	current
	DESCRIPTION ""
			::= { mbusA2 37 }

mbusA2VIF10		OBJECT-TYPE
			SYNTAX	INTEGER
			ACCESS	read-only
			STATUS	current
	DESCRIPTION ""
			::= { mbusA2 38 }

mbusA2Value10		OBJECT-TYPE
			SYNTAX	INTEGER
			ACCESS	read-only
			STATUS	current
	DESCRIPTION ""
			::= { mbusA2 39 }

mbusA2VIF11		OBJECT-TYPE
			SYNTAX	INTEGER
			ACCESS	read-only
			STATUS	current
	DESCRIPTION ""
			::= { mbusA2 40 }

mbusA2Value11		OBJECT-TYPE
			SYNTAX	INTEGER
			ACCESS	read-only
			STATUS	current
	DESCRIPTION ""
			::= { mbusA2 41 }

mbusA2VIF12		OBJECT-TYPE
			SYNTAX	INTEGER
			ACCESS	read-only
			STATUS	current
	DESCRIPTION ""
			::= { mbusA2 42 }

mbusA2Value12		OBJECT-TYPE
			SYNTAX	INTEGER
			ACCESS	read-only
			STATUS	current
	DESCRIPTION ""
			::= { mbusA2 43 }

mbusA2VIF13		OBJECT-TYPE
			SYNTAX	INTEGER
			ACCESS	read-only
			STATUS	current
	DESCRIPTION ""
			::= { mbusA2 44 }

mbusA2Value13		OBJECT-TYPE
			SYNTAX	INTEGER
			ACCESS	read-only
			STATUS	current
	DESCRIPTION ""
			::= { mbusA2 45 }

mbusA2VIF14		OBJECT-TYPE
			SYNTAX	INTEGER
			ACCESS	read-only
			STATUS	current
	DESCRIPTION ""
			::= { mbusA2 46 }

mbusA2Value14		OBJECT-TYPE
			SYNTAX	INTEGER
			ACCESS	read-only
			STATUS	current
	DESCRIPTION ""
			::= { mbusA2 47 }

mbusA2VIF15		OBJECT-TYPE
			SYNTAX	INTEGER
			ACCESS	read-only
			STATUS	current
	DESCRIPTION ""
			::= { mbusA2 48 }

mbusA2Value15		OBJECT-TYPE
			SYNTAX	INTEGER
			ACCESS	read-only
			STATUS	current
	DESCRIPTION ""
			::= { mbusA2 49 }

mbusA2VIF16		OBJECT-TYPE
			SYNTAX	INTEGER
			ACCESS	read-only
			STATUS	current
	DESCRIPTION ""
			::= { mbusA2 50 }

mbusA2Value16		OBJECT-TYPE
			SYNTAX	INTEGER
			ACCESS	read-only
			STATUS	current
	DESCRIPTION ""
			::= { mbusA2 51 }

mbusA2VIF17		OBJECT-TYPE
			SYNTAX	INTEGER
			ACCESS	read-only
			STATUS	current
	DESCRIPTION ""
			::= { mbusA2 52 }

mbusA2Value17		OBJECT-TYPE
			SYNTAX	INTEGER
			ACCESS	read-only
			STATUS	current
	DESCRIPTION ""
			::= { mbusA2 53 }

mbusA2VIF18		OBJECT-TYPE
			SYNTAX	INTEGER
			ACCESS	read-only
			STATUS	current
	DESCRIPTION ""
			::= { mbusA2 54 }

mbusA2Value18		OBJECT-TYPE
			SYNTAX	INTEGER
			ACCESS	read-only
			STATUS	current
	DESCRIPTION ""
			::= { mbusA2 55 }

mbusA2VIF19		OBJECT-TYPE
			SYNTAX	INTEGER
			ACCESS	read-only
			STATUS	current
	DESCRIPTION ""
			::= { mbusA2 56 }

mbusA2Value19		OBJECT-TYPE
			SYNTAX	INTEGER
			ACCESS	read-only
			STATUS	current
	DESCRIPTION ""
			::= { mbusA2 57 }

mbusA2VIF1A		OBJECT-TYPE
			SYNTAX	INTEGER
			ACCESS	read-only
			STATUS	current
	DESCRIPTION ""
			::= { mbusA2 58 }

mbusA2Value1A		OBJECT-TYPE
			SYNTAX	INTEGER
			ACCESS	read-only
			STATUS	current
	DESCRIPTION ""
			::= { mbusA2 59 }

mbusA2VIF1B		OBJECT-TYPE
			SYNTAX	INTEGER
			ACCESS	read-only
			STATUS	current
	DESCRIPTION ""
			::= { mbusA2 60 }

mbusA2Value1B		OBJECT-TYPE
			SYNTAX	INTEGER
			ACCESS	read-only
			STATUS	current
	DESCRIPTION ""
			::= { mbusA2 61 }

mbusA2VIF1C		OBJECT-TYPE
			SYNTAX	INTEGER
			ACCESS	read-only
			STATUS	current
	DESCRIPTION ""
			::= { mbusA2 62 }

mbusA2Value1C		OBJECT-TYPE
			SYNTAX	INTEGER
			ACCESS	read-only
			STATUS	current
	DESCRIPTION ""
			::= { mbusA2 63 }

mbusA2VIF1D		OBJECT-TYPE
			SYNTAX	INTEGER
			ACCESS	read-only
			STATUS	current
	DESCRIPTION ""
			::= { mbusA2 64 }

mbusA2Value1D		OBJECT-TYPE
			SYNTAX	INTEGER
			ACCESS	read-only
			STATUS	current
	DESCRIPTION ""
			::= { mbusA2 65 }

mbusA2VIF1E		OBJECT-TYPE
			SYNTAX	INTEGER
			ACCESS	read-only
			STATUS	current
	DESCRIPTION ""
			::= { mbusA2 66 }

mbusA2Value1E		OBJECT-TYPE
			SYNTAX	INTEGER
			ACCESS	read-only
			STATUS	current
	DESCRIPTION ""
			::= { mbusA2 67 }

mbusA2VIF1F		OBJECT-TYPE
			SYNTAX	INTEGER
			ACCESS	read-only
			STATUS	current
	DESCRIPTION ""
			::= { mbusA2 68 }

mbusA2Value1F		OBJECT-TYPE
			SYNTAX	INTEGER
			ACCESS	read-only
			STATUS	current
	DESCRIPTION ""
			::= { mbusA2 69 }

mbusA2VIF20		OBJECT-TYPE
			SYNTAX	INTEGER
			ACCESS	read-only
			STATUS	current
	DESCRIPTION ""
			::= { mbusA2 70 }

mbusA2Value20		OBJECT-TYPE
			SYNTAX	INTEGER
			ACCESS	read-only
			STATUS	current
	DESCRIPTION ""
			::= { mbusA2 71 }

mbusA2VIF21		OBJECT-TYPE
			SYNTAX	INTEGER
			ACCESS	read-only
			STATUS	current
	DESCRIPTION ""
			::= { mbusA2 72 }

mbusA2Value21		OBJECT-TYPE
			SYNTAX	INTEGER
			ACCESS	read-only
			STATUS	current
	DESCRIPTION ""
			::= { mbusA2 73 }

mbusA2VIF22		OBJECT-TYPE
			SYNTAX	INTEGER
			ACCESS	read-only
			STATUS	current
	DESCRIPTION ""
			::= { mbusA2 74 }

mbusA2Value22		OBJECT-TYPE
			SYNTAX	INTEGER
			ACCESS	read-only
			STATUS	current
	DESCRIPTION ""
			::= { mbusA2 75 }

mbusA2VIF23		OBJECT-TYPE
			SYNTAX	INTEGER
			ACCESS	read-only
			STATUS	current
	DESCRIPTION ""
			::= { mbusA2 76 }

mbusA2Value23		OBJECT-TYPE
			SYNTAX	INTEGER
			ACCESS	read-only
			STATUS	current
	DESCRIPTION ""
			::= { mbusA2 77 }

mbusA2VIF24		OBJECT-TYPE
			SYNTAX	INTEGER
			ACCESS	read-only
			STATUS	current
	DESCRIPTION ""
			::= { mbusA2 78 }

mbusA2Value24		OBJECT-TYPE
			SYNTAX	INTEGER
			ACCESS	read-only
			STATUS	current
	DESCRIPTION ""
			::= { mbusA2 79 }

mbusA2VIF25		OBJECT-TYPE
			SYNTAX	INTEGER
			ACCESS	read-only
			STATUS	current
	DESCRIPTION ""
			::= { mbusA2 80 }

mbusA2Value25		OBJECT-TYPE
			SYNTAX	INTEGER
			ACCESS	read-only
			STATUS	current
	DESCRIPTION ""
			::= { mbusA2 81 }

mbusA2VIF26		OBJECT-TYPE
			SYNTAX	INTEGER
			ACCESS	read-only
			STATUS	current
	DESCRIPTION ""
			::= { mbusA2 82 }

mbusA2Value26		OBJECT-TYPE
			SYNTAX	INTEGER
			ACCESS	read-only
			STATUS	current
	DESCRIPTION ""
			::= { mbusA2 83 }

mbusA2VIF27		OBJECT-TYPE
			SYNTAX	INTEGER
			ACCESS	read-only
			STATUS	current
	DESCRIPTION ""
			::= { mbusA2 84 }

mbusA2Value27		OBJECT-TYPE
			SYNTAX	INTEGER
			ACCESS	read-only
			STATUS	current
	DESCRIPTION ""
			::= { mbusA2 85 }

mbusA2VIF28		OBJECT-TYPE
			SYNTAX	INTEGER
			ACCESS	read-only
			STATUS	current
	DESCRIPTION ""
			::= { mbusA2 86 }

mbusA2Value28		OBJECT-TYPE
			SYNTAX	INTEGER
			ACCESS	read-only
			STATUS	current
	DESCRIPTION ""
			::= { mbusA2 87 }

mbusA2VIF29		OBJECT-TYPE
			SYNTAX	INTEGER
			ACCESS	read-only
			STATUS	current
	DESCRIPTION ""
			::= { mbusA2 88 }

mbusA2Value29		OBJECT-TYPE
			SYNTAX	INTEGER
			ACCESS	read-only
			STATUS	current
	DESCRIPTION ""
			::= { mbusA2 89 }

mbusA2VIF2A		OBJECT-TYPE
			SYNTAX	INTEGER
			ACCESS	read-only
			STATUS	current
	DESCRIPTION ""
			::= { mbusA2 90 }

mbusA2Value2A		OBJECT-TYPE
			SYNTAX	INTEGER
			ACCESS	read-only
			STATUS	current
	DESCRIPTION ""
			::= { mbusA2 91 }

mbusA2VIF2B		OBJECT-TYPE
			SYNTAX	INTEGER
			ACCESS	read-only
			STATUS	current
	DESCRIPTION ""
			::= { mbusA2 92 }

mbusA2Value2B		OBJECT-TYPE
			SYNTAX	INTEGER
			ACCESS	read-only
			STATUS	current
	DESCRIPTION ""
			::= { mbusA2 93 }

mbusA2VIF2C		OBJECT-TYPE
			SYNTAX	INTEGER
			ACCESS	read-only
			STATUS	current
	DESCRIPTION ""
			::= { mbusA2 94 }

mbusA2Value2C		OBJECT-TYPE
			SYNTAX	INTEGER
			ACCESS	read-only
			STATUS	current
	DESCRIPTION ""
			::= { mbusA2 95 }

mbusA2VIF2D		OBJECT-TYPE
			SYNTAX	INTEGER
			ACCESS	read-only
			STATUS	current
	DESCRIPTION ""
			::= { mbusA2 96 }

mbusA2Value2D		OBJECT-TYPE
			SYNTAX	INTEGER
			ACCESS	read-only
			STATUS	current
	DESCRIPTION ""
			::= { mbusA2 97 }

mbusA2VIF2E		OBJECT-TYPE
			SYNTAX	INTEGER
			ACCESS	read-only
			STATUS	current
	DESCRIPTION ""
			::= { mbusA2 98 }

mbusA2Value2E		OBJECT-TYPE
			SYNTAX	INTEGER
			ACCESS	read-only
			STATUS	current
	DESCRIPTION ""
			::= { mbusA2 99 }

mbusA2VIF2F		OBJECT-TYPE
			SYNTAX	INTEGER
			ACCESS	read-only
			STATUS	current
	DESCRIPTION ""
			::= { mbusA2 100 }

mbusA2Value2F		OBJECT-TYPE
			SYNTAX	INTEGER
			ACCESS	read-only
			STATUS	current
	DESCRIPTION ""
			::= { mbusA2 101 }

mbusA3			OBJECT IDENTIFIER ::= { mbus 163 }

mbusA3IdNumber		OBJECT-TYPE
			SYNTAX	Gauge
			ACCESS	read-only
			STATUS	current
	DESCRIPTION ""
			::= { mbusA3 1 }

mbusA3Manufacturer	OBJECT-TYPE
			SYNTAX	Gauge
			ACCESS	read-only
			STATUS	current
	DESCRIPTION ""
			::= { mbusA3 2 }

mbusA3Version		OBJECT-TYPE
			SYNTAX	Gauge
			ACCESS	read-only
			STATUS	current
	DESCRIPTION ""
			::= { mbusA3 3 }

mbusA3Medium		OBJECT-TYPE
			SYNTAX	Gauge
			ACCESS	read-only
			STATUS	current
	DESCRIPTION ""
			::= { mbusA3 4 }

mbusA3Status		OBJECT-TYPE
			SYNTAX	Gauge
			ACCESS	read-only
			STATUS	current
	DESCRIPTION ""
			::= { mbusA3 5 }

mbusA3VIF00		OBJECT-TYPE
			SYNTAX	INTEGER
			ACCESS	read-only
			STATUS	current
	DESCRIPTION ""
			::= { mbusA3 6 }

mbusA3Value00		OBJECT-TYPE
			SYNTAX	INTEGER
			ACCESS	read-only
			STATUS	current
	DESCRIPTION ""
			::= { mbusA3 7 }

mbusA3VIF01		OBJECT-TYPE
			SYNTAX	INTEGER
			ACCESS	read-only
			STATUS	current
	DESCRIPTION ""
			::= { mbusA3 8 }

mbusA3Value01		OBJECT-TYPE
			SYNTAX	INTEGER
			ACCESS	read-only
			STATUS	current
	DESCRIPTION ""
			::= { mbusA3 9 }

mbusA3VIF02		OBJECT-TYPE
			SYNTAX	INTEGER
			ACCESS	read-only
			STATUS	current
	DESCRIPTION ""
			::= { mbusA3 10 }

mbusA3Value02		OBJECT-TYPE
			SYNTAX	INTEGER
			ACCESS	read-only
			STATUS	current
	DESCRIPTION ""
			::= { mbusA3 11 }

mbusA3VIF03		OBJECT-TYPE
			SYNTAX	INTEGER
			ACCESS	read-only
			STATUS	current
	DESCRIPTION ""
			::= { mbusA3 12 }

mbusA3Value03		OBJECT-TYPE
			SYNTAX	INTEGER
			ACCESS	read-only
			STATUS	current
	DESCRIPTION ""
			::= { mbusA3 13 }

mbusA3VIF04		OBJECT-TYPE
			SYNTAX	INTEGER
			ACCESS	read-only
			STATUS	current
	DESCRIPTION ""
			::= { mbusA3 14 }

mbusA3Value04		OBJECT-TYPE
			SYNTAX	INTEGER
			ACCESS	read-only
			STATUS	current
	DESCRIPTION ""
			::= { mbusA3 15 }

mbusA3VIF05		OBJECT-TYPE
			SYNTAX	INTEGER
			ACCESS	read-only
			STATUS	current
	DESCRIPTION ""
			::= { mbusA3 16 }

mbusA3Value05		OBJECT-TYPE
			SYNTAX	INTEGER
			ACCESS	read-only
			STATUS	current
	DESCRIPTION ""
			::= { mbusA3 17 }

mbusA3VIF06		OBJECT-TYPE
			SYNTAX	INTEGER
			ACCESS	read-only
			STATUS	current
	DESCRIPTION ""
			::= { mbusA3 18 }

mbusA3Value06		OBJECT-TYPE
			SYNTAX	INTEGER
			ACCESS	read-only
			STATUS	current
	DESCRIPTION ""
			::= { mbusA3 19 }

mbusA3VIF07		OBJECT-TYPE
			SYNTAX	INTEGER
			ACCESS	read-only
			STATUS	current
	DESCRIPTION ""
			::= { mbusA3 20 }

mbusA3Value07		OBJECT-TYPE
			SYNTAX	INTEGER
			ACCESS	read-only
			STATUS	current
	DESCRIPTION ""
			::= { mbusA3 21 }

mbusA3VIF08		OBJECT-TYPE
			SYNTAX	INTEGER
			ACCESS	read-only
			STATUS	current
	DESCRIPTION ""
			::= { mbusA3 22 }

mbusA3Value08		OBJECT-TYPE
			SYNTAX	INTEGER
			ACCESS	read-only
			STATUS	current
	DESCRIPTION ""
			::= { mbusA3 23 }

mbusA3VIF09		OBJECT-TYPE
			SYNTAX	INTEGER
			ACCESS	read-only
			STATUS	current
	DESCRIPTION ""
			::= { mbusA3 24 }

mbusA3Value09		OBJECT-TYPE
			SYNTAX	INTEGER
			ACCESS	read-only
			STATUS	current
	DESCRIPTION ""
			::= { mbusA3 25 }

mbusA3VIF0A		OBJECT-TYPE
			SYNTAX	INTEGER
			ACCESS	read-only
			STATUS	current
	DESCRIPTION ""
			::= { mbusA3 26 }

mbusA3Value0A		OBJECT-TYPE
			SYNTAX	INTEGER
			ACCESS	read-only
			STATUS	current
	DESCRIPTION ""
			::= { mbusA3 27 }

mbusA3VIF0B		OBJECT-TYPE
			SYNTAX	INTEGER
			ACCESS	read-only
			STATUS	current
	DESCRIPTION ""
			::= { mbusA3 28 }

mbusA3Value0B		OBJECT-TYPE
			SYNTAX	INTEGER
			ACCESS	read-only
			STATUS	current
	DESCRIPTION ""
			::= { mbusA3 29 }

mbusA3VIF0C		OBJECT-TYPE
			SYNTAX	INTEGER
			ACCESS	read-only
			STATUS	current
	DESCRIPTION ""
			::= { mbusA3 30 }

mbusA3Value0C		OBJECT-TYPE
			SYNTAX	INTEGER
			ACCESS	read-only
			STATUS	current
	DESCRIPTION ""
			::= { mbusA3 31 }

mbusA3VIF0D		OBJECT-TYPE
			SYNTAX	INTEGER
			ACCESS	read-only
			STATUS	current
	DESCRIPTION ""
			::= { mbusA3 32 }

mbusA3Value0D		OBJECT-TYPE
			SYNTAX	INTEGER
			ACCESS	read-only
			STATUS	current
	DESCRIPTION ""
			::= { mbusA3 33 }

mbusA3VIF0E		OBJECT-TYPE
			SYNTAX	INTEGER
			ACCESS	read-only
			STATUS	current
	DESCRIPTION ""
			::= { mbusA3 34 }

mbusA3Value0E		OBJECT-TYPE
			SYNTAX	INTEGER
			ACCESS	read-only
			STATUS	current
	DESCRIPTION ""
			::= { mbusA3 35 }

mbusA3VIF0F		OBJECT-TYPE
			SYNTAX	INTEGER
			ACCESS	read-only
			STATUS	current
	DESCRIPTION ""
			::= { mbusA3 36 }

mbusA3Value0F		OBJECT-TYPE
			SYNTAX	INTEGER
			ACCESS	read-only
			STATUS	current
	DESCRIPTION ""
			::= { mbusA3 37 }

mbusA3VIF10		OBJECT-TYPE
			SYNTAX	INTEGER
			ACCESS	read-only
			STATUS	current
	DESCRIPTION ""
			::= { mbusA3 38 }

mbusA3Value10		OBJECT-TYPE
			SYNTAX	INTEGER
			ACCESS	read-only
			STATUS	current
	DESCRIPTION ""
			::= { mbusA3 39 }

mbusA3VIF11		OBJECT-TYPE
			SYNTAX	INTEGER
			ACCESS	read-only
			STATUS	current
	DESCRIPTION ""
			::= { mbusA3 40 }

mbusA3Value11		OBJECT-TYPE
			SYNTAX	INTEGER
			ACCESS	read-only
			STATUS	current
	DESCRIPTION ""
			::= { mbusA3 41 }

mbusA3VIF12		OBJECT-TYPE
			SYNTAX	INTEGER
			ACCESS	read-only
			STATUS	current
	DESCRIPTION ""
			::= { mbusA3 42 }

mbusA3Value12		OBJECT-TYPE
			SYNTAX	INTEGER
			ACCESS	read-only
			STATUS	current
	DESCRIPTION ""
			::= { mbusA3 43 }

mbusA3VIF13		OBJECT-TYPE
			SYNTAX	INTEGER
			ACCESS	read-only
			STATUS	current
	DESCRIPTION ""
			::= { mbusA3 44 }

mbusA3Value13		OBJECT-TYPE
			SYNTAX	INTEGER
			ACCESS	read-only
			STATUS	current
	DESCRIPTION ""
			::= { mbusA3 45 }

mbusA3VIF14		OBJECT-TYPE
			SYNTAX	INTEGER
			ACCESS	read-only
			STATUS	current
	DESCRIPTION ""
			::= { mbusA3 46 }

mbusA3Value14		OBJECT-TYPE
			SYNTAX	INTEGER
			ACCESS	read-only
			STATUS	current
	DESCRIPTION ""
			::= { mbusA3 47 }

mbusA3VIF15		OBJECT-TYPE
			SYNTAX	INTEGER
			ACCESS	read-only
			STATUS	current
	DESCRIPTION ""
			::= { mbusA3 48 }

mbusA3Value15		OBJECT-TYPE
			SYNTAX	INTEGER
			ACCESS	read-only
			STATUS	current
	DESCRIPTION ""
			::= { mbusA3 49 }

mbusA3VIF16		OBJECT-TYPE
			SYNTAX	INTEGER
			ACCESS	read-only
			STATUS	current
	DESCRIPTION ""
			::= { mbusA3 50 }

mbusA3Value16		OBJECT-TYPE
			SYNTAX	INTEGER
			ACCESS	read-only
			STATUS	current
	DESCRIPTION ""
			::= { mbusA3 51 }

mbusA3VIF17		OBJECT-TYPE
			SYNTAX	INTEGER
			ACCESS	read-only
			STATUS	current
	DESCRIPTION ""
			::= { mbusA3 52 }

mbusA3Value17		OBJECT-TYPE
			SYNTAX	INTEGER
			ACCESS	read-only
			STATUS	current
	DESCRIPTION ""
			::= { mbusA3 53 }

mbusA3VIF18		OBJECT-TYPE
			SYNTAX	INTEGER
			ACCESS	read-only
			STATUS	current
	DESCRIPTION ""
			::= { mbusA3 54 }

mbusA3Value18		OBJECT-TYPE
			SYNTAX	INTEGER
			ACCESS	read-only
			STATUS	current
	DESCRIPTION ""
			::= { mbusA3 55 }

mbusA3VIF19		OBJECT-TYPE
			SYNTAX	INTEGER
			ACCESS	read-only
			STATUS	current
	DESCRIPTION ""
			::= { mbusA3 56 }

mbusA3Value19		OBJECT-TYPE
			SYNTAX	INTEGER
			ACCESS	read-only
			STATUS	current
	DESCRIPTION ""
			::= { mbusA3 57 }

mbusA3VIF1A		OBJECT-TYPE
			SYNTAX	INTEGER
			ACCESS	read-only
			STATUS	current
	DESCRIPTION ""
			::= { mbusA3 58 }

mbusA3Value1A		OBJECT-TYPE
			SYNTAX	INTEGER
			ACCESS	read-only
			STATUS	current
	DESCRIPTION ""
			::= { mbusA3 59 }

mbusA3VIF1B		OBJECT-TYPE
			SYNTAX	INTEGER
			ACCESS	read-only
			STATUS	current
	DESCRIPTION ""
			::= { mbusA3 60 }

mbusA3Value1B		OBJECT-TYPE
			SYNTAX	INTEGER
			ACCESS	read-only
			STATUS	current
	DESCRIPTION ""
			::= { mbusA3 61 }

mbusA3VIF1C		OBJECT-TYPE
			SYNTAX	INTEGER
			ACCESS	read-only
			STATUS	current
	DESCRIPTION ""
			::= { mbusA3 62 }

mbusA3Value1C		OBJECT-TYPE
			SYNTAX	INTEGER
			ACCESS	read-only
			STATUS	current
	DESCRIPTION ""
			::= { mbusA3 63 }

mbusA3VIF1D		OBJECT-TYPE
			SYNTAX	INTEGER
			ACCESS	read-only
			STATUS	current
	DESCRIPTION ""
			::= { mbusA3 64 }

mbusA3Value1D		OBJECT-TYPE
			SYNTAX	INTEGER
			ACCESS	read-only
			STATUS	current
	DESCRIPTION ""
			::= { mbusA3 65 }

mbusA3VIF1E		OBJECT-TYPE
			SYNTAX	INTEGER
			ACCESS	read-only
			STATUS	current
	DESCRIPTION ""
			::= { mbusA3 66 }

mbusA3Value1E		OBJECT-TYPE
			SYNTAX	INTEGER
			ACCESS	read-only
			STATUS	current
	DESCRIPTION ""
			::= { mbusA3 67 }

mbusA3VIF1F		OBJECT-TYPE
			SYNTAX	INTEGER
			ACCESS	read-only
			STATUS	current
	DESCRIPTION ""
			::= { mbusA3 68 }

mbusA3Value1F		OBJECT-TYPE
			SYNTAX	INTEGER
			ACCESS	read-only
			STATUS	current
	DESCRIPTION ""
			::= { mbusA3 69 }

mbusA3VIF20		OBJECT-TYPE
			SYNTAX	INTEGER
			ACCESS	read-only
			STATUS	current
	DESCRIPTION ""
			::= { mbusA3 70 }

mbusA3Value20		OBJECT-TYPE
			SYNTAX	INTEGER
			ACCESS	read-only
			STATUS	current
	DESCRIPTION ""
			::= { mbusA3 71 }

mbusA3VIF21		OBJECT-TYPE
			SYNTAX	INTEGER
			ACCESS	read-only
			STATUS	current
	DESCRIPTION ""
			::= { mbusA3 72 }

mbusA3Value21		OBJECT-TYPE
			SYNTAX	INTEGER
			ACCESS	read-only
			STATUS	current
	DESCRIPTION ""
			::= { mbusA3 73 }

mbusA3VIF22		OBJECT-TYPE
			SYNTAX	INTEGER
			ACCESS	read-only
			STATUS	current
	DESCRIPTION ""
			::= { mbusA3 74 }

mbusA3Value22		OBJECT-TYPE
			SYNTAX	INTEGER
			ACCESS	read-only
			STATUS	current
	DESCRIPTION ""
			::= { mbusA3 75 }

mbusA3VIF23		OBJECT-TYPE
			SYNTAX	INTEGER
			ACCESS	read-only
			STATUS	current
	DESCRIPTION ""
			::= { mbusA3 76 }

mbusA3Value23		OBJECT-TYPE
			SYNTAX	INTEGER
			ACCESS	read-only
			STATUS	current
	DESCRIPTION ""
			::= { mbusA3 77 }

mbusA3VIF24		OBJECT-TYPE
			SYNTAX	INTEGER
			ACCESS	read-only
			STATUS	current
	DESCRIPTION ""
			::= { mbusA3 78 }

mbusA3Value24		OBJECT-TYPE
			SYNTAX	INTEGER
			ACCESS	read-only
			STATUS	current
	DESCRIPTION ""
			::= { mbusA3 79 }

mbusA3VIF25		OBJECT-TYPE
			SYNTAX	INTEGER
			ACCESS	read-only
			STATUS	current
	DESCRIPTION ""
			::= { mbusA3 80 }

mbusA3Value25		OBJECT-TYPE
			SYNTAX	INTEGER
			ACCESS	read-only
			STATUS	current
	DESCRIPTION ""
			::= { mbusA3 81 }

mbusA3VIF26		OBJECT-TYPE
			SYNTAX	INTEGER
			ACCESS	read-only
			STATUS	current
	DESCRIPTION ""
			::= { mbusA3 82 }

mbusA3Value26		OBJECT-TYPE
			SYNTAX	INTEGER
			ACCESS	read-only
			STATUS	current
	DESCRIPTION ""
			::= { mbusA3 83 }

mbusA3VIF27		OBJECT-TYPE
			SYNTAX	INTEGER
			ACCESS	read-only
			STATUS	current
	DESCRIPTION ""
			::= { mbusA3 84 }

mbusA3Value27		OBJECT-TYPE
			SYNTAX	INTEGER
			ACCESS	read-only
			STATUS	current
	DESCRIPTION ""
			::= { mbusA3 85 }

mbusA3VIF28		OBJECT-TYPE
			SYNTAX	INTEGER
			ACCESS	read-only
			STATUS	current
	DESCRIPTION ""
			::= { mbusA3 86 }

mbusA3Value28		OBJECT-TYPE
			SYNTAX	INTEGER
			ACCESS	read-only
			STATUS	current
	DESCRIPTION ""
			::= { mbusA3 87 }

mbusA3VIF29		OBJECT-TYPE
			SYNTAX	INTEGER
			ACCESS	read-only
			STATUS	current
	DESCRIPTION ""
			::= { mbusA3 88 }

mbusA3Value29		OBJECT-TYPE
			SYNTAX	INTEGER
			ACCESS	read-only
			STATUS	current
	DESCRIPTION ""
			::= { mbusA3 89 }

mbusA3VIF2A		OBJECT-TYPE
			SYNTAX	INTEGER
			ACCESS	read-only
			STATUS	current
	DESCRIPTION ""
			::= { mbusA3 90 }

mbusA3Value2A		OBJECT-TYPE
			SYNTAX	INTEGER
			ACCESS	read-only
			STATUS	current
	DESCRIPTION ""
			::= { mbusA3 91 }

mbusA3VIF2B		OBJECT-TYPE
			SYNTAX	INTEGER
			ACCESS	read-only
			STATUS	current
	DESCRIPTION ""
			::= { mbusA3 92 }

mbusA3Value2B		OBJECT-TYPE
			SYNTAX	INTEGER
			ACCESS	read-only
			STATUS	current
	DESCRIPTION ""
			::= { mbusA3 93 }

mbusA3VIF2C		OBJECT-TYPE
			SYNTAX	INTEGER
			ACCESS	read-only
			STATUS	current
	DESCRIPTION ""
			::= { mbusA3 94 }

mbusA3Value2C		OBJECT-TYPE
			SYNTAX	INTEGER
			ACCESS	read-only
			STATUS	current
	DESCRIPTION ""
			::= { mbusA3 95 }

mbusA3VIF2D		OBJECT-TYPE
			SYNTAX	INTEGER
			ACCESS	read-only
			STATUS	current
	DESCRIPTION ""
			::= { mbusA3 96 }

mbusA3Value2D		OBJECT-TYPE
			SYNTAX	INTEGER
			ACCESS	read-only
			STATUS	current
	DESCRIPTION ""
			::= { mbusA3 97 }

mbusA3VIF2E		OBJECT-TYPE
			SYNTAX	INTEGER
			ACCESS	read-only
			STATUS	current
	DESCRIPTION ""
			::= { mbusA3 98 }

mbusA3Value2E		OBJECT-TYPE
			SYNTAX	INTEGER
			ACCESS	read-only
			STATUS	current
	DESCRIPTION ""
			::= { mbusA3 99 }

mbusA3VIF2F		OBJECT-TYPE
			SYNTAX	INTEGER
			ACCESS	read-only
			STATUS	current
	DESCRIPTION ""
			::= { mbusA3 100 }

mbusA3Value2F		OBJECT-TYPE
			SYNTAX	INTEGER
			ACCESS	read-only
			STATUS	current
	DESCRIPTION ""
			::= { mbusA3 101 }

mbusA4			OBJECT IDENTIFIER ::= { mbus 164 }

mbusA4IdNumber		OBJECT-TYPE
			SYNTAX	Gauge
			ACCESS	read-only
			STATUS	current
	DESCRIPTION ""
			::= { mbusA4 1 }

mbusA4Manufacturer	OBJECT-TYPE
			SYNTAX	Gauge
			ACCESS	read-only
			STATUS	current
	DESCRIPTION ""
			::= { mbusA4 2 }

mbusA4Version		OBJECT-TYPE
			SYNTAX	Gauge
			ACCESS	read-only
			STATUS	current
	DESCRIPTION ""
			::= { mbusA4 3 }

mbusA4Medium		OBJECT-TYPE
			SYNTAX	Gauge
			ACCESS	read-only
			STATUS	current
	DESCRIPTION ""
			::= { mbusA4 4 }

mbusA4Status		OBJECT-TYPE
			SYNTAX	Gauge
			ACCESS	read-only
			STATUS	current
	DESCRIPTION ""
			::= { mbusA4 5 }

mbusA4VIF00		OBJECT-TYPE
			SYNTAX	INTEGER
			ACCESS	read-only
			STATUS	current
	DESCRIPTION ""
			::= { mbusA4 6 }

mbusA4Value00		OBJECT-TYPE
			SYNTAX	INTEGER
			ACCESS	read-only
			STATUS	current
	DESCRIPTION ""
			::= { mbusA4 7 }

mbusA4VIF01		OBJECT-TYPE
			SYNTAX	INTEGER
			ACCESS	read-only
			STATUS	current
	DESCRIPTION ""
			::= { mbusA4 8 }

mbusA4Value01		OBJECT-TYPE
			SYNTAX	INTEGER
			ACCESS	read-only
			STATUS	current
	DESCRIPTION ""
			::= { mbusA4 9 }

mbusA4VIF02		OBJECT-TYPE
			SYNTAX	INTEGER
			ACCESS	read-only
			STATUS	current
	DESCRIPTION ""
			::= { mbusA4 10 }

mbusA4Value02		OBJECT-TYPE
			SYNTAX	INTEGER
			ACCESS	read-only
			STATUS	current
	DESCRIPTION ""
			::= { mbusA4 11 }

mbusA4VIF03		OBJECT-TYPE
			SYNTAX	INTEGER
			ACCESS	read-only
			STATUS	current
	DESCRIPTION ""
			::= { mbusA4 12 }

mbusA4Value03		OBJECT-TYPE
			SYNTAX	INTEGER
			ACCESS	read-only
			STATUS	current
	DESCRIPTION ""
			::= { mbusA4 13 }

mbusA4VIF04		OBJECT-TYPE
			SYNTAX	INTEGER
			ACCESS	read-only
			STATUS	current
	DESCRIPTION ""
			::= { mbusA4 14 }

mbusA4Value04		OBJECT-TYPE
			SYNTAX	INTEGER
			ACCESS	read-only
			STATUS	current
	DESCRIPTION ""
			::= { mbusA4 15 }

mbusA4VIF05		OBJECT-TYPE
			SYNTAX	INTEGER
			ACCESS	read-only
			STATUS	current
	DESCRIPTION ""
			::= { mbusA4 16 }

mbusA4Value05		OBJECT-TYPE
			SYNTAX	INTEGER
			ACCESS	read-only
			STATUS	current
	DESCRIPTION ""
			::= { mbusA4 17 }

mbusA4VIF06		OBJECT-TYPE
			SYNTAX	INTEGER
			ACCESS	read-only
			STATUS	current
	DESCRIPTION ""
			::= { mbusA4 18 }

mbusA4Value06		OBJECT-TYPE
			SYNTAX	INTEGER
			ACCESS	read-only
			STATUS	current
	DESCRIPTION ""
			::= { mbusA4 19 }

mbusA4VIF07		OBJECT-TYPE
			SYNTAX	INTEGER
			ACCESS	read-only
			STATUS	current
	DESCRIPTION ""
			::= { mbusA4 20 }

mbusA4Value07		OBJECT-TYPE
			SYNTAX	INTEGER
			ACCESS	read-only
			STATUS	current
	DESCRIPTION ""
			::= { mbusA4 21 }

mbusA4VIF08		OBJECT-TYPE
			SYNTAX	INTEGER
			ACCESS	read-only
			STATUS	current
	DESCRIPTION ""
			::= { mbusA4 22 }

mbusA4Value08		OBJECT-TYPE
			SYNTAX	INTEGER
			ACCESS	read-only
			STATUS	current
	DESCRIPTION ""
			::= { mbusA4 23 }

mbusA4VIF09		OBJECT-TYPE
			SYNTAX	INTEGER
			ACCESS	read-only
			STATUS	current
	DESCRIPTION ""
			::= { mbusA4 24 }

mbusA4Value09		OBJECT-TYPE
			SYNTAX	INTEGER
			ACCESS	read-only
			STATUS	current
	DESCRIPTION ""
			::= { mbusA4 25 }

mbusA4VIF0A		OBJECT-TYPE
			SYNTAX	INTEGER
			ACCESS	read-only
			STATUS	current
	DESCRIPTION ""
			::= { mbusA4 26 }

mbusA4Value0A		OBJECT-TYPE
			SYNTAX	INTEGER
			ACCESS	read-only
			STATUS	current
	DESCRIPTION ""
			::= { mbusA4 27 }

mbusA4VIF0B		OBJECT-TYPE
			SYNTAX	INTEGER
			ACCESS	read-only
			STATUS	current
	DESCRIPTION ""
			::= { mbusA4 28 }

mbusA4Value0B		OBJECT-TYPE
			SYNTAX	INTEGER
			ACCESS	read-only
			STATUS	current
	DESCRIPTION ""
			::= { mbusA4 29 }

mbusA4VIF0C		OBJECT-TYPE
			SYNTAX	INTEGER
			ACCESS	read-only
			STATUS	current
	DESCRIPTION ""
			::= { mbusA4 30 }

mbusA4Value0C		OBJECT-TYPE
			SYNTAX	INTEGER
			ACCESS	read-only
			STATUS	current
	DESCRIPTION ""
			::= { mbusA4 31 }

mbusA4VIF0D		OBJECT-TYPE
			SYNTAX	INTEGER
			ACCESS	read-only
			STATUS	current
	DESCRIPTION ""
			::= { mbusA4 32 }

mbusA4Value0D		OBJECT-TYPE
			SYNTAX	INTEGER
			ACCESS	read-only
			STATUS	current
	DESCRIPTION ""
			::= { mbusA4 33 }

mbusA4VIF0E		OBJECT-TYPE
			SYNTAX	INTEGER
			ACCESS	read-only
			STATUS	current
	DESCRIPTION ""
			::= { mbusA4 34 }

mbusA4Value0E		OBJECT-TYPE
			SYNTAX	INTEGER
			ACCESS	read-only
			STATUS	current
	DESCRIPTION ""
			::= { mbusA4 35 }

mbusA4VIF0F		OBJECT-TYPE
			SYNTAX	INTEGER
			ACCESS	read-only
			STATUS	current
	DESCRIPTION ""
			::= { mbusA4 36 }

mbusA4Value0F		OBJECT-TYPE
			SYNTAX	INTEGER
			ACCESS	read-only
			STATUS	current
	DESCRIPTION ""
			::= { mbusA4 37 }

mbusA4VIF10		OBJECT-TYPE
			SYNTAX	INTEGER
			ACCESS	read-only
			STATUS	current
	DESCRIPTION ""
			::= { mbusA4 38 }

mbusA4Value10		OBJECT-TYPE
			SYNTAX	INTEGER
			ACCESS	read-only
			STATUS	current
	DESCRIPTION ""
			::= { mbusA4 39 }

mbusA4VIF11		OBJECT-TYPE
			SYNTAX	INTEGER
			ACCESS	read-only
			STATUS	current
	DESCRIPTION ""
			::= { mbusA4 40 }

mbusA4Value11		OBJECT-TYPE
			SYNTAX	INTEGER
			ACCESS	read-only
			STATUS	current
	DESCRIPTION ""
			::= { mbusA4 41 }

mbusA4VIF12		OBJECT-TYPE
			SYNTAX	INTEGER
			ACCESS	read-only
			STATUS	current
	DESCRIPTION ""
			::= { mbusA4 42 }

mbusA4Value12		OBJECT-TYPE
			SYNTAX	INTEGER
			ACCESS	read-only
			STATUS	current
	DESCRIPTION ""
			::= { mbusA4 43 }

mbusA4VIF13		OBJECT-TYPE
			SYNTAX	INTEGER
			ACCESS	read-only
			STATUS	current
	DESCRIPTION ""
			::= { mbusA4 44 }

mbusA4Value13		OBJECT-TYPE
			SYNTAX	INTEGER
			ACCESS	read-only
			STATUS	current
	DESCRIPTION ""
			::= { mbusA4 45 }

mbusA4VIF14		OBJECT-TYPE
			SYNTAX	INTEGER
			ACCESS	read-only
			STATUS	current
	DESCRIPTION ""
			::= { mbusA4 46 }

mbusA4Value14		OBJECT-TYPE
			SYNTAX	INTEGER
			ACCESS	read-only
			STATUS	current
	DESCRIPTION ""
			::= { mbusA4 47 }

mbusA4VIF15		OBJECT-TYPE
			SYNTAX	INTEGER
			ACCESS	read-only
			STATUS	current
	DESCRIPTION ""
			::= { mbusA4 48 }

mbusA4Value15		OBJECT-TYPE
			SYNTAX	INTEGER
			ACCESS	read-only
			STATUS	current
	DESCRIPTION ""
			::= { mbusA4 49 }

mbusA4VIF16		OBJECT-TYPE
			SYNTAX	INTEGER
			ACCESS	read-only
			STATUS	current
	DESCRIPTION ""
			::= { mbusA4 50 }

mbusA4Value16		OBJECT-TYPE
			SYNTAX	INTEGER
			ACCESS	read-only
			STATUS	current
	DESCRIPTION ""
			::= { mbusA4 51 }

mbusA4VIF17		OBJECT-TYPE
			SYNTAX	INTEGER
			ACCESS	read-only
			STATUS	current
	DESCRIPTION ""
			::= { mbusA4 52 }

mbusA4Value17		OBJECT-TYPE
			SYNTAX	INTEGER
			ACCESS	read-only
			STATUS	current
	DESCRIPTION ""
			::= { mbusA4 53 }

mbusA4VIF18		OBJECT-TYPE
			SYNTAX	INTEGER
			ACCESS	read-only
			STATUS	current
	DESCRIPTION ""
			::= { mbusA4 54 }

mbusA4Value18		OBJECT-TYPE
			SYNTAX	INTEGER
			ACCESS	read-only
			STATUS	current
	DESCRIPTION ""
			::= { mbusA4 55 }

mbusA4VIF19		OBJECT-TYPE
			SYNTAX	INTEGER
			ACCESS	read-only
			STATUS	current
	DESCRIPTION ""
			::= { mbusA4 56 }

mbusA4Value19		OBJECT-TYPE
			SYNTAX	INTEGER
			ACCESS	read-only
			STATUS	current
	DESCRIPTION ""
			::= { mbusA4 57 }

mbusA4VIF1A		OBJECT-TYPE
			SYNTAX	INTEGER
			ACCESS	read-only
			STATUS	current
	DESCRIPTION ""
			::= { mbusA4 58 }

mbusA4Value1A		OBJECT-TYPE
			SYNTAX	INTEGER
			ACCESS	read-only
			STATUS	current
	DESCRIPTION ""
			::= { mbusA4 59 }

mbusA4VIF1B		OBJECT-TYPE
			SYNTAX	INTEGER
			ACCESS	read-only
			STATUS	current
	DESCRIPTION ""
			::= { mbusA4 60 }

mbusA4Value1B		OBJECT-TYPE
			SYNTAX	INTEGER
			ACCESS	read-only
			STATUS	current
	DESCRIPTION ""
			::= { mbusA4 61 }

mbusA4VIF1C		OBJECT-TYPE
			SYNTAX	INTEGER
			ACCESS	read-only
			STATUS	current
	DESCRIPTION ""
			::= { mbusA4 62 }

mbusA4Value1C		OBJECT-TYPE
			SYNTAX	INTEGER
			ACCESS	read-only
			STATUS	current
	DESCRIPTION ""
			::= { mbusA4 63 }

mbusA4VIF1D		OBJECT-TYPE
			SYNTAX	INTEGER
			ACCESS	read-only
			STATUS	current
	DESCRIPTION ""
			::= { mbusA4 64 }

mbusA4Value1D		OBJECT-TYPE
			SYNTAX	INTEGER
			ACCESS	read-only
			STATUS	current
	DESCRIPTION ""
			::= { mbusA4 65 }

mbusA4VIF1E		OBJECT-TYPE
			SYNTAX	INTEGER
			ACCESS	read-only
			STATUS	current
	DESCRIPTION ""
			::= { mbusA4 66 }

mbusA4Value1E		OBJECT-TYPE
			SYNTAX	INTEGER
			ACCESS	read-only
			STATUS	current
	DESCRIPTION ""
			::= { mbusA4 67 }

mbusA4VIF1F		OBJECT-TYPE
			SYNTAX	INTEGER
			ACCESS	read-only
			STATUS	current
	DESCRIPTION ""
			::= { mbusA4 68 }

mbusA4Value1F		OBJECT-TYPE
			SYNTAX	INTEGER
			ACCESS	read-only
			STATUS	current
	DESCRIPTION ""
			::= { mbusA4 69 }

mbusA4VIF20		OBJECT-TYPE
			SYNTAX	INTEGER
			ACCESS	read-only
			STATUS	current
	DESCRIPTION ""
			::= { mbusA4 70 }

mbusA4Value20		OBJECT-TYPE
			SYNTAX	INTEGER
			ACCESS	read-only
			STATUS	current
	DESCRIPTION ""
			::= { mbusA4 71 }

mbusA4VIF21		OBJECT-TYPE
			SYNTAX	INTEGER
			ACCESS	read-only
			STATUS	current
	DESCRIPTION ""
			::= { mbusA4 72 }

mbusA4Value21		OBJECT-TYPE
			SYNTAX	INTEGER
			ACCESS	read-only
			STATUS	current
	DESCRIPTION ""
			::= { mbusA4 73 }

mbusA4VIF22		OBJECT-TYPE
			SYNTAX	INTEGER
			ACCESS	read-only
			STATUS	current
	DESCRIPTION ""
			::= { mbusA4 74 }

mbusA4Value22		OBJECT-TYPE
			SYNTAX	INTEGER
			ACCESS	read-only
			STATUS	current
	DESCRIPTION ""
			::= { mbusA4 75 }

mbusA4VIF23		OBJECT-TYPE
			SYNTAX	INTEGER
			ACCESS	read-only
			STATUS	current
	DESCRIPTION ""
			::= { mbusA4 76 }

mbusA4Value23		OBJECT-TYPE
			SYNTAX	INTEGER
			ACCESS	read-only
			STATUS	current
	DESCRIPTION ""
			::= { mbusA4 77 }

mbusA4VIF24		OBJECT-TYPE
			SYNTAX	INTEGER
			ACCESS	read-only
			STATUS	current
	DESCRIPTION ""
			::= { mbusA4 78 }

mbusA4Value24		OBJECT-TYPE
			SYNTAX	INTEGER
			ACCESS	read-only
			STATUS	current
	DESCRIPTION ""
			::= { mbusA4 79 }

mbusA4VIF25		OBJECT-TYPE
			SYNTAX	INTEGER
			ACCESS	read-only
			STATUS	current
	DESCRIPTION ""
			::= { mbusA4 80 }

mbusA4Value25		OBJECT-TYPE
			SYNTAX	INTEGER
			ACCESS	read-only
			STATUS	current
	DESCRIPTION ""
			::= { mbusA4 81 }

mbusA4VIF26		OBJECT-TYPE
			SYNTAX	INTEGER
			ACCESS	read-only
			STATUS	current
	DESCRIPTION ""
			::= { mbusA4 82 }

mbusA4Value26		OBJECT-TYPE
			SYNTAX	INTEGER
			ACCESS	read-only
			STATUS	current
	DESCRIPTION ""
			::= { mbusA4 83 }

mbusA4VIF27		OBJECT-TYPE
			SYNTAX	INTEGER
			ACCESS	read-only
			STATUS	current
	DESCRIPTION ""
			::= { mbusA4 84 }

mbusA4Value27		OBJECT-TYPE
			SYNTAX	INTEGER
			ACCESS	read-only
			STATUS	current
	DESCRIPTION ""
			::= { mbusA4 85 }

mbusA4VIF28		OBJECT-TYPE
			SYNTAX	INTEGER
			ACCESS	read-only
			STATUS	current
	DESCRIPTION ""
			::= { mbusA4 86 }

mbusA4Value28		OBJECT-TYPE
			SYNTAX	INTEGER
			ACCESS	read-only
			STATUS	current
	DESCRIPTION ""
			::= { mbusA4 87 }

mbusA4VIF29		OBJECT-TYPE
			SYNTAX	INTEGER
			ACCESS	read-only
			STATUS	current
	DESCRIPTION ""
			::= { mbusA4 88 }

mbusA4Value29		OBJECT-TYPE
			SYNTAX	INTEGER
			ACCESS	read-only
			STATUS	current
	DESCRIPTION ""
			::= { mbusA4 89 }

mbusA4VIF2A		OBJECT-TYPE
			SYNTAX	INTEGER
			ACCESS	read-only
			STATUS	current
	DESCRIPTION ""
			::= { mbusA4 90 }

mbusA4Value2A		OBJECT-TYPE
			SYNTAX	INTEGER
			ACCESS	read-only
			STATUS	current
	DESCRIPTION ""
			::= { mbusA4 91 }

mbusA4VIF2B		OBJECT-TYPE
			SYNTAX	INTEGER
			ACCESS	read-only
			STATUS	current
	DESCRIPTION ""
			::= { mbusA4 92 }

mbusA4Value2B		OBJECT-TYPE
			SYNTAX	INTEGER
			ACCESS	read-only
			STATUS	current
	DESCRIPTION ""
			::= { mbusA4 93 }

mbusA4VIF2C		OBJECT-TYPE
			SYNTAX	INTEGER
			ACCESS	read-only
			STATUS	current
	DESCRIPTION ""
			::= { mbusA4 94 }

mbusA4Value2C		OBJECT-TYPE
			SYNTAX	INTEGER
			ACCESS	read-only
			STATUS	current
	DESCRIPTION ""
			::= { mbusA4 95 }

mbusA4VIF2D		OBJECT-TYPE
			SYNTAX	INTEGER
			ACCESS	read-only
			STATUS	current
	DESCRIPTION ""
			::= { mbusA4 96 }

mbusA4Value2D		OBJECT-TYPE
			SYNTAX	INTEGER
			ACCESS	read-only
			STATUS	current
	DESCRIPTION ""
			::= { mbusA4 97 }

mbusA4VIF2E		OBJECT-TYPE
			SYNTAX	INTEGER
			ACCESS	read-only
			STATUS	current
	DESCRIPTION ""
			::= { mbusA4 98 }

mbusA4Value2E		OBJECT-TYPE
			SYNTAX	INTEGER
			ACCESS	read-only
			STATUS	current
	DESCRIPTION ""
			::= { mbusA4 99 }

mbusA4VIF2F		OBJECT-TYPE
			SYNTAX	INTEGER
			ACCESS	read-only
			STATUS	current
	DESCRIPTION ""
			::= { mbusA4 100 }

mbusA4Value2F		OBJECT-TYPE
			SYNTAX	INTEGER
			ACCESS	read-only
			STATUS	current
	DESCRIPTION ""
			::= { mbusA4 101 }

mbusA5			OBJECT IDENTIFIER ::= { mbus 165 }

mbusA5IdNumber		OBJECT-TYPE
			SYNTAX	Gauge
			ACCESS	read-only
			STATUS	current
	DESCRIPTION ""
			::= { mbusA5 1 }

mbusA5Manufacturer	OBJECT-TYPE
			SYNTAX	Gauge
			ACCESS	read-only
			STATUS	current
	DESCRIPTION ""
			::= { mbusA5 2 }

mbusA5Version		OBJECT-TYPE
			SYNTAX	Gauge
			ACCESS	read-only
			STATUS	current
	DESCRIPTION ""
			::= { mbusA5 3 }

mbusA5Medium		OBJECT-TYPE
			SYNTAX	Gauge
			ACCESS	read-only
			STATUS	current
	DESCRIPTION ""
			::= { mbusA5 4 }

mbusA5Status		OBJECT-TYPE
			SYNTAX	Gauge
			ACCESS	read-only
			STATUS	current
	DESCRIPTION ""
			::= { mbusA5 5 }

mbusA5VIF00		OBJECT-TYPE
			SYNTAX	INTEGER
			ACCESS	read-only
			STATUS	current
	DESCRIPTION ""
			::= { mbusA5 6 }

mbusA5Value00		OBJECT-TYPE
			SYNTAX	INTEGER
			ACCESS	read-only
			STATUS	current
	DESCRIPTION ""
			::= { mbusA5 7 }

mbusA5VIF01		OBJECT-TYPE
			SYNTAX	INTEGER
			ACCESS	read-only
			STATUS	current
	DESCRIPTION ""
			::= { mbusA5 8 }

mbusA5Value01		OBJECT-TYPE
			SYNTAX	INTEGER
			ACCESS	read-only
			STATUS	current
	DESCRIPTION ""
			::= { mbusA5 9 }

mbusA5VIF02		OBJECT-TYPE
			SYNTAX	INTEGER
			ACCESS	read-only
			STATUS	current
	DESCRIPTION ""
			::= { mbusA5 10 }

mbusA5Value02		OBJECT-TYPE
			SYNTAX	INTEGER
			ACCESS	read-only
			STATUS	current
	DESCRIPTION ""
			::= { mbusA5 11 }

mbusA5VIF03		OBJECT-TYPE
			SYNTAX	INTEGER
			ACCESS	read-only
			STATUS	current
	DESCRIPTION ""
			::= { mbusA5 12 }

mbusA5Value03		OBJECT-TYPE
			SYNTAX	INTEGER
			ACCESS	read-only
			STATUS	current
	DESCRIPTION ""
			::= { mbusA5 13 }

mbusA5VIF04		OBJECT-TYPE
			SYNTAX	INTEGER
			ACCESS	read-only
			STATUS	current
	DESCRIPTION ""
			::= { mbusA5 14 }

mbusA5Value04		OBJECT-TYPE
			SYNTAX	INTEGER
			ACCESS	read-only
			STATUS	current
	DESCRIPTION ""
			::= { mbusA5 15 }

mbusA5VIF05		OBJECT-TYPE
			SYNTAX	INTEGER
			ACCESS	read-only
			STATUS	current
	DESCRIPTION ""
			::= { mbusA5 16 }

mbusA5Value05		OBJECT-TYPE
			SYNTAX	INTEGER
			ACCESS	read-only
			STATUS	current
	DESCRIPTION ""
			::= { mbusA5 17 }

mbusA5VIF06		OBJECT-TYPE
			SYNTAX	INTEGER
			ACCESS	read-only
			STATUS	current
	DESCRIPTION ""
			::= { mbusA5 18 }

mbusA5Value06		OBJECT-TYPE
			SYNTAX	INTEGER
			ACCESS	read-only
			STATUS	current
	DESCRIPTION ""
			::= { mbusA5 19 }

mbusA5VIF07		OBJECT-TYPE
			SYNTAX	INTEGER
			ACCESS	read-only
			STATUS	current
	DESCRIPTION ""
			::= { mbusA5 20 }

mbusA5Value07		OBJECT-TYPE
			SYNTAX	INTEGER
			ACCESS	read-only
			STATUS	current
	DESCRIPTION ""
			::= { mbusA5 21 }

mbusA5VIF08		OBJECT-TYPE
			SYNTAX	INTEGER
			ACCESS	read-only
			STATUS	current
	DESCRIPTION ""
			::= { mbusA5 22 }

mbusA5Value08		OBJECT-TYPE
			SYNTAX	INTEGER
			ACCESS	read-only
			STATUS	current
	DESCRIPTION ""
			::= { mbusA5 23 }

mbusA5VIF09		OBJECT-TYPE
			SYNTAX	INTEGER
			ACCESS	read-only
			STATUS	current
	DESCRIPTION ""
			::= { mbusA5 24 }

mbusA5Value09		OBJECT-TYPE
			SYNTAX	INTEGER
			ACCESS	read-only
			STATUS	current
	DESCRIPTION ""
			::= { mbusA5 25 }

mbusA5VIF0A		OBJECT-TYPE
			SYNTAX	INTEGER
			ACCESS	read-only
			STATUS	current
	DESCRIPTION ""
			::= { mbusA5 26 }

mbusA5Value0A		OBJECT-TYPE
			SYNTAX	INTEGER
			ACCESS	read-only
			STATUS	current
	DESCRIPTION ""
			::= { mbusA5 27 }

mbusA5VIF0B		OBJECT-TYPE
			SYNTAX	INTEGER
			ACCESS	read-only
			STATUS	current
	DESCRIPTION ""
			::= { mbusA5 28 }

mbusA5Value0B		OBJECT-TYPE
			SYNTAX	INTEGER
			ACCESS	read-only
			STATUS	current
	DESCRIPTION ""
			::= { mbusA5 29 }

mbusA5VIF0C		OBJECT-TYPE
			SYNTAX	INTEGER
			ACCESS	read-only
			STATUS	current
	DESCRIPTION ""
			::= { mbusA5 30 }

mbusA5Value0C		OBJECT-TYPE
			SYNTAX	INTEGER
			ACCESS	read-only
			STATUS	current
	DESCRIPTION ""
			::= { mbusA5 31 }

mbusA5VIF0D		OBJECT-TYPE
			SYNTAX	INTEGER
			ACCESS	read-only
			STATUS	current
	DESCRIPTION ""
			::= { mbusA5 32 }

mbusA5Value0D		OBJECT-TYPE
			SYNTAX	INTEGER
			ACCESS	read-only
			STATUS	current
	DESCRIPTION ""
			::= { mbusA5 33 }

mbusA5VIF0E		OBJECT-TYPE
			SYNTAX	INTEGER
			ACCESS	read-only
			STATUS	current
	DESCRIPTION ""
			::= { mbusA5 34 }

mbusA5Value0E		OBJECT-TYPE
			SYNTAX	INTEGER
			ACCESS	read-only
			STATUS	current
	DESCRIPTION ""
			::= { mbusA5 35 }

mbusA5VIF0F		OBJECT-TYPE
			SYNTAX	INTEGER
			ACCESS	read-only
			STATUS	current
	DESCRIPTION ""
			::= { mbusA5 36 }

mbusA5Value0F		OBJECT-TYPE
			SYNTAX	INTEGER
			ACCESS	read-only
			STATUS	current
	DESCRIPTION ""
			::= { mbusA5 37 }

mbusA5VIF10		OBJECT-TYPE
			SYNTAX	INTEGER
			ACCESS	read-only
			STATUS	current
	DESCRIPTION ""
			::= { mbusA5 38 }

mbusA5Value10		OBJECT-TYPE
			SYNTAX	INTEGER
			ACCESS	read-only
			STATUS	current
	DESCRIPTION ""
			::= { mbusA5 39 }

mbusA5VIF11		OBJECT-TYPE
			SYNTAX	INTEGER
			ACCESS	read-only
			STATUS	current
	DESCRIPTION ""
			::= { mbusA5 40 }

mbusA5Value11		OBJECT-TYPE
			SYNTAX	INTEGER
			ACCESS	read-only
			STATUS	current
	DESCRIPTION ""
			::= { mbusA5 41 }

mbusA5VIF12		OBJECT-TYPE
			SYNTAX	INTEGER
			ACCESS	read-only
			STATUS	current
	DESCRIPTION ""
			::= { mbusA5 42 }

mbusA5Value12		OBJECT-TYPE
			SYNTAX	INTEGER
			ACCESS	read-only
			STATUS	current
	DESCRIPTION ""
			::= { mbusA5 43 }

mbusA5VIF13		OBJECT-TYPE
			SYNTAX	INTEGER
			ACCESS	read-only
			STATUS	current
	DESCRIPTION ""
			::= { mbusA5 44 }

mbusA5Value13		OBJECT-TYPE
			SYNTAX	INTEGER
			ACCESS	read-only
			STATUS	current
	DESCRIPTION ""
			::= { mbusA5 45 }

mbusA5VIF14		OBJECT-TYPE
			SYNTAX	INTEGER
			ACCESS	read-only
			STATUS	current
	DESCRIPTION ""
			::= { mbusA5 46 }

mbusA5Value14		OBJECT-TYPE
			SYNTAX	INTEGER
			ACCESS	read-only
			STATUS	current
	DESCRIPTION ""
			::= { mbusA5 47 }

mbusA5VIF15		OBJECT-TYPE
			SYNTAX	INTEGER
			ACCESS	read-only
			STATUS	current
	DESCRIPTION ""
			::= { mbusA5 48 }

mbusA5Value15		OBJECT-TYPE
			SYNTAX	INTEGER
			ACCESS	read-only
			STATUS	current
	DESCRIPTION ""
			::= { mbusA5 49 }

mbusA5VIF16		OBJECT-TYPE
			SYNTAX	INTEGER
			ACCESS	read-only
			STATUS	current
	DESCRIPTION ""
			::= { mbusA5 50 }

mbusA5Value16		OBJECT-TYPE
			SYNTAX	INTEGER
			ACCESS	read-only
			STATUS	current
	DESCRIPTION ""
			::= { mbusA5 51 }

mbusA5VIF17		OBJECT-TYPE
			SYNTAX	INTEGER
			ACCESS	read-only
			STATUS	current
	DESCRIPTION ""
			::= { mbusA5 52 }

mbusA5Value17		OBJECT-TYPE
			SYNTAX	INTEGER
			ACCESS	read-only
			STATUS	current
	DESCRIPTION ""
			::= { mbusA5 53 }

mbusA5VIF18		OBJECT-TYPE
			SYNTAX	INTEGER
			ACCESS	read-only
			STATUS	current
	DESCRIPTION ""
			::= { mbusA5 54 }

mbusA5Value18		OBJECT-TYPE
			SYNTAX	INTEGER
			ACCESS	read-only
			STATUS	current
	DESCRIPTION ""
			::= { mbusA5 55 }

mbusA5VIF19		OBJECT-TYPE
			SYNTAX	INTEGER
			ACCESS	read-only
			STATUS	current
	DESCRIPTION ""
			::= { mbusA5 56 }

mbusA5Value19		OBJECT-TYPE
			SYNTAX	INTEGER
			ACCESS	read-only
			STATUS	current
	DESCRIPTION ""
			::= { mbusA5 57 }

mbusA5VIF1A		OBJECT-TYPE
			SYNTAX	INTEGER
			ACCESS	read-only
			STATUS	current
	DESCRIPTION ""
			::= { mbusA5 58 }

mbusA5Value1A		OBJECT-TYPE
			SYNTAX	INTEGER
			ACCESS	read-only
			STATUS	current
	DESCRIPTION ""
			::= { mbusA5 59 }

mbusA5VIF1B		OBJECT-TYPE
			SYNTAX	INTEGER
			ACCESS	read-only
			STATUS	current
	DESCRIPTION ""
			::= { mbusA5 60 }

mbusA5Value1B		OBJECT-TYPE
			SYNTAX	INTEGER
			ACCESS	read-only
			STATUS	current
	DESCRIPTION ""
			::= { mbusA5 61 }

mbusA5VIF1C		OBJECT-TYPE
			SYNTAX	INTEGER
			ACCESS	read-only
			STATUS	current
	DESCRIPTION ""
			::= { mbusA5 62 }

mbusA5Value1C		OBJECT-TYPE
			SYNTAX	INTEGER
			ACCESS	read-only
			STATUS	current
	DESCRIPTION ""
			::= { mbusA5 63 }

mbusA5VIF1D		OBJECT-TYPE
			SYNTAX	INTEGER
			ACCESS	read-only
			STATUS	current
	DESCRIPTION ""
			::= { mbusA5 64 }

mbusA5Value1D		OBJECT-TYPE
			SYNTAX	INTEGER
			ACCESS	read-only
			STATUS	current
	DESCRIPTION ""
			::= { mbusA5 65 }

mbusA5VIF1E		OBJECT-TYPE
			SYNTAX	INTEGER
			ACCESS	read-only
			STATUS	current
	DESCRIPTION ""
			::= { mbusA5 66 }

mbusA5Value1E		OBJECT-TYPE
			SYNTAX	INTEGER
			ACCESS	read-only
			STATUS	current
	DESCRIPTION ""
			::= { mbusA5 67 }

mbusA5VIF1F		OBJECT-TYPE
			SYNTAX	INTEGER
			ACCESS	read-only
			STATUS	current
	DESCRIPTION ""
			::= { mbusA5 68 }

mbusA5Value1F		OBJECT-TYPE
			SYNTAX	INTEGER
			ACCESS	read-only
			STATUS	current
	DESCRIPTION ""
			::= { mbusA5 69 }

mbusA5VIF20		OBJECT-TYPE
			SYNTAX	INTEGER
			ACCESS	read-only
			STATUS	current
	DESCRIPTION ""
			::= { mbusA5 70 }

mbusA5Value20		OBJECT-TYPE
			SYNTAX	INTEGER
			ACCESS	read-only
			STATUS	current
	DESCRIPTION ""
			::= { mbusA5 71 }

mbusA5VIF21		OBJECT-TYPE
			SYNTAX	INTEGER
			ACCESS	read-only
			STATUS	current
	DESCRIPTION ""
			::= { mbusA5 72 }

mbusA5Value21		OBJECT-TYPE
			SYNTAX	INTEGER
			ACCESS	read-only
			STATUS	current
	DESCRIPTION ""
			::= { mbusA5 73 }

mbusA5VIF22		OBJECT-TYPE
			SYNTAX	INTEGER
			ACCESS	read-only
			STATUS	current
	DESCRIPTION ""
			::= { mbusA5 74 }

mbusA5Value22		OBJECT-TYPE
			SYNTAX	INTEGER
			ACCESS	read-only
			STATUS	current
	DESCRIPTION ""
			::= { mbusA5 75 }

mbusA5VIF23		OBJECT-TYPE
			SYNTAX	INTEGER
			ACCESS	read-only
			STATUS	current
	DESCRIPTION ""
			::= { mbusA5 76 }

mbusA5Value23		OBJECT-TYPE
			SYNTAX	INTEGER
			ACCESS	read-only
			STATUS	current
	DESCRIPTION ""
			::= { mbusA5 77 }

mbusA5VIF24		OBJECT-TYPE
			SYNTAX	INTEGER
			ACCESS	read-only
			STATUS	current
	DESCRIPTION ""
			::= { mbusA5 78 }

mbusA5Value24		OBJECT-TYPE
			SYNTAX	INTEGER
			ACCESS	read-only
			STATUS	current
	DESCRIPTION ""
			::= { mbusA5 79 }

mbusA5VIF25		OBJECT-TYPE
			SYNTAX	INTEGER
			ACCESS	read-only
			STATUS	current
	DESCRIPTION ""
			::= { mbusA5 80 }

mbusA5Value25		OBJECT-TYPE
			SYNTAX	INTEGER
			ACCESS	read-only
			STATUS	current
	DESCRIPTION ""
			::= { mbusA5 81 }

mbusA5VIF26		OBJECT-TYPE
			SYNTAX	INTEGER
			ACCESS	read-only
			STATUS	current
	DESCRIPTION ""
			::= { mbusA5 82 }

mbusA5Value26		OBJECT-TYPE
			SYNTAX	INTEGER
			ACCESS	read-only
			STATUS	current
	DESCRIPTION ""
			::= { mbusA5 83 }

mbusA5VIF27		OBJECT-TYPE
			SYNTAX	INTEGER
			ACCESS	read-only
			STATUS	current
	DESCRIPTION ""
			::= { mbusA5 84 }

mbusA5Value27		OBJECT-TYPE
			SYNTAX	INTEGER
			ACCESS	read-only
			STATUS	current
	DESCRIPTION ""
			::= { mbusA5 85 }

mbusA5VIF28		OBJECT-TYPE
			SYNTAX	INTEGER
			ACCESS	read-only
			STATUS	current
	DESCRIPTION ""
			::= { mbusA5 86 }

mbusA5Value28		OBJECT-TYPE
			SYNTAX	INTEGER
			ACCESS	read-only
			STATUS	current
	DESCRIPTION ""
			::= { mbusA5 87 }

mbusA5VIF29		OBJECT-TYPE
			SYNTAX	INTEGER
			ACCESS	read-only
			STATUS	current
	DESCRIPTION ""
			::= { mbusA5 88 }

mbusA5Value29		OBJECT-TYPE
			SYNTAX	INTEGER
			ACCESS	read-only
			STATUS	current
	DESCRIPTION ""
			::= { mbusA5 89 }

mbusA5VIF2A		OBJECT-TYPE
			SYNTAX	INTEGER
			ACCESS	read-only
			STATUS	current
	DESCRIPTION ""
			::= { mbusA5 90 }

mbusA5Value2A		OBJECT-TYPE
			SYNTAX	INTEGER
			ACCESS	read-only
			STATUS	current
	DESCRIPTION ""
			::= { mbusA5 91 }

mbusA5VIF2B		OBJECT-TYPE
			SYNTAX	INTEGER
			ACCESS	read-only
			STATUS	current
	DESCRIPTION ""
			::= { mbusA5 92 }

mbusA5Value2B		OBJECT-TYPE
			SYNTAX	INTEGER
			ACCESS	read-only
			STATUS	current
	DESCRIPTION ""
			::= { mbusA5 93 }

mbusA5VIF2C		OBJECT-TYPE
			SYNTAX	INTEGER
			ACCESS	read-only
			STATUS	current
	DESCRIPTION ""
			::= { mbusA5 94 }

mbusA5Value2C		OBJECT-TYPE
			SYNTAX	INTEGER
			ACCESS	read-only
			STATUS	current
	DESCRIPTION ""
			::= { mbusA5 95 }

mbusA5VIF2D		OBJECT-TYPE
			SYNTAX	INTEGER
			ACCESS	read-only
			STATUS	current
	DESCRIPTION ""
			::= { mbusA5 96 }

mbusA5Value2D		OBJECT-TYPE
			SYNTAX	INTEGER
			ACCESS	read-only
			STATUS	current
	DESCRIPTION ""
			::= { mbusA5 97 }

mbusA5VIF2E		OBJECT-TYPE
			SYNTAX	INTEGER
			ACCESS	read-only
			STATUS	current
	DESCRIPTION ""
			::= { mbusA5 98 }

mbusA5Value2E		OBJECT-TYPE
			SYNTAX	INTEGER
			ACCESS	read-only
			STATUS	current
	DESCRIPTION ""
			::= { mbusA5 99 }

mbusA5VIF2F		OBJECT-TYPE
			SYNTAX	INTEGER
			ACCESS	read-only
			STATUS	current
	DESCRIPTION ""
			::= { mbusA5 100 }

mbusA5Value2F		OBJECT-TYPE
			SYNTAX	INTEGER
			ACCESS	read-only
			STATUS	current
	DESCRIPTION ""
			::= { mbusA5 101 }

mbusA6			OBJECT IDENTIFIER ::= { mbus 166 }

mbusA6IdNumber		OBJECT-TYPE
			SYNTAX	Gauge
			ACCESS	read-only
			STATUS	current
	DESCRIPTION ""
			::= { mbusA6 1 }

mbusA6Manufacturer	OBJECT-TYPE
			SYNTAX	Gauge
			ACCESS	read-only
			STATUS	current
	DESCRIPTION ""
			::= { mbusA6 2 }

mbusA6Version		OBJECT-TYPE
			SYNTAX	Gauge
			ACCESS	read-only
			STATUS	current
	DESCRIPTION ""
			::= { mbusA6 3 }

mbusA6Medium		OBJECT-TYPE
			SYNTAX	Gauge
			ACCESS	read-only
			STATUS	current
	DESCRIPTION ""
			::= { mbusA6 4 }

mbusA6Status		OBJECT-TYPE
			SYNTAX	Gauge
			ACCESS	read-only
			STATUS	current
	DESCRIPTION ""
			::= { mbusA6 5 }

mbusA6VIF00		OBJECT-TYPE
			SYNTAX	INTEGER
			ACCESS	read-only
			STATUS	current
	DESCRIPTION ""
			::= { mbusA6 6 }

mbusA6Value00		OBJECT-TYPE
			SYNTAX	INTEGER
			ACCESS	read-only
			STATUS	current
	DESCRIPTION ""
			::= { mbusA6 7 }

mbusA6VIF01		OBJECT-TYPE
			SYNTAX	INTEGER
			ACCESS	read-only
			STATUS	current
	DESCRIPTION ""
			::= { mbusA6 8 }

mbusA6Value01		OBJECT-TYPE
			SYNTAX	INTEGER
			ACCESS	read-only
			STATUS	current
	DESCRIPTION ""
			::= { mbusA6 9 }

mbusA6VIF02		OBJECT-TYPE
			SYNTAX	INTEGER
			ACCESS	read-only
			STATUS	current
	DESCRIPTION ""
			::= { mbusA6 10 }

mbusA6Value02		OBJECT-TYPE
			SYNTAX	INTEGER
			ACCESS	read-only
			STATUS	current
	DESCRIPTION ""
			::= { mbusA6 11 }

mbusA6VIF03		OBJECT-TYPE
			SYNTAX	INTEGER
			ACCESS	read-only
			STATUS	current
	DESCRIPTION ""
			::= { mbusA6 12 }

mbusA6Value03		OBJECT-TYPE
			SYNTAX	INTEGER
			ACCESS	read-only
			STATUS	current
	DESCRIPTION ""
			::= { mbusA6 13 }

mbusA6VIF04		OBJECT-TYPE
			SYNTAX	INTEGER
			ACCESS	read-only
			STATUS	current
	DESCRIPTION ""
			::= { mbusA6 14 }

mbusA6Value04		OBJECT-TYPE
			SYNTAX	INTEGER
			ACCESS	read-only
			STATUS	current
	DESCRIPTION ""
			::= { mbusA6 15 }

mbusA6VIF05		OBJECT-TYPE
			SYNTAX	INTEGER
			ACCESS	read-only
			STATUS	current
	DESCRIPTION ""
			::= { mbusA6 16 }

mbusA6Value05		OBJECT-TYPE
			SYNTAX	INTEGER
			ACCESS	read-only
			STATUS	current
	DESCRIPTION ""
			::= { mbusA6 17 }

mbusA6VIF06		OBJECT-TYPE
			SYNTAX	INTEGER
			ACCESS	read-only
			STATUS	current
	DESCRIPTION ""
			::= { mbusA6 18 }

mbusA6Value06		OBJECT-TYPE
			SYNTAX	INTEGER
			ACCESS	read-only
			STATUS	current
	DESCRIPTION ""
			::= { mbusA6 19 }

mbusA6VIF07		OBJECT-TYPE
			SYNTAX	INTEGER
			ACCESS	read-only
			STATUS	current
	DESCRIPTION ""
			::= { mbusA6 20 }

mbusA6Value07		OBJECT-TYPE
			SYNTAX	INTEGER
			ACCESS	read-only
			STATUS	current
	DESCRIPTION ""
			::= { mbusA6 21 }

mbusA6VIF08		OBJECT-TYPE
			SYNTAX	INTEGER
			ACCESS	read-only
			STATUS	current
	DESCRIPTION ""
			::= { mbusA6 22 }

mbusA6Value08		OBJECT-TYPE
			SYNTAX	INTEGER
			ACCESS	read-only
			STATUS	current
	DESCRIPTION ""
			::= { mbusA6 23 }

mbusA6VIF09		OBJECT-TYPE
			SYNTAX	INTEGER
			ACCESS	read-only
			STATUS	current
	DESCRIPTION ""
			::= { mbusA6 24 }

mbusA6Value09		OBJECT-TYPE
			SYNTAX	INTEGER
			ACCESS	read-only
			STATUS	current
	DESCRIPTION ""
			::= { mbusA6 25 }

mbusA6VIF0A		OBJECT-TYPE
			SYNTAX	INTEGER
			ACCESS	read-only
			STATUS	current
	DESCRIPTION ""
			::= { mbusA6 26 }

mbusA6Value0A		OBJECT-TYPE
			SYNTAX	INTEGER
			ACCESS	read-only
			STATUS	current
	DESCRIPTION ""
			::= { mbusA6 27 }

mbusA6VIF0B		OBJECT-TYPE
			SYNTAX	INTEGER
			ACCESS	read-only
			STATUS	current
	DESCRIPTION ""
			::= { mbusA6 28 }

mbusA6Value0B		OBJECT-TYPE
			SYNTAX	INTEGER
			ACCESS	read-only
			STATUS	current
	DESCRIPTION ""
			::= { mbusA6 29 }

mbusA6VIF0C		OBJECT-TYPE
			SYNTAX	INTEGER
			ACCESS	read-only
			STATUS	current
	DESCRIPTION ""
			::= { mbusA6 30 }

mbusA6Value0C		OBJECT-TYPE
			SYNTAX	INTEGER
			ACCESS	read-only
			STATUS	current
	DESCRIPTION ""
			::= { mbusA6 31 }

mbusA6VIF0D		OBJECT-TYPE
			SYNTAX	INTEGER
			ACCESS	read-only
			STATUS	current
	DESCRIPTION ""
			::= { mbusA6 32 }

mbusA6Value0D		OBJECT-TYPE
			SYNTAX	INTEGER
			ACCESS	read-only
			STATUS	current
	DESCRIPTION ""
			::= { mbusA6 33 }

mbusA6VIF0E		OBJECT-TYPE
			SYNTAX	INTEGER
			ACCESS	read-only
			STATUS	current
	DESCRIPTION ""
			::= { mbusA6 34 }

mbusA6Value0E		OBJECT-TYPE
			SYNTAX	INTEGER
			ACCESS	read-only
			STATUS	current
	DESCRIPTION ""
			::= { mbusA6 35 }

mbusA6VIF0F		OBJECT-TYPE
			SYNTAX	INTEGER
			ACCESS	read-only
			STATUS	current
	DESCRIPTION ""
			::= { mbusA6 36 }

mbusA6Value0F		OBJECT-TYPE
			SYNTAX	INTEGER
			ACCESS	read-only
			STATUS	current
	DESCRIPTION ""
			::= { mbusA6 37 }

mbusA6VIF10		OBJECT-TYPE
			SYNTAX	INTEGER
			ACCESS	read-only
			STATUS	current
	DESCRIPTION ""
			::= { mbusA6 38 }

mbusA6Value10		OBJECT-TYPE
			SYNTAX	INTEGER
			ACCESS	read-only
			STATUS	current
	DESCRIPTION ""
			::= { mbusA6 39 }

mbusA6VIF11		OBJECT-TYPE
			SYNTAX	INTEGER
			ACCESS	read-only
			STATUS	current
	DESCRIPTION ""
			::= { mbusA6 40 }

mbusA6Value11		OBJECT-TYPE
			SYNTAX	INTEGER
			ACCESS	read-only
			STATUS	current
	DESCRIPTION ""
			::= { mbusA6 41 }

mbusA6VIF12		OBJECT-TYPE
			SYNTAX	INTEGER
			ACCESS	read-only
			STATUS	current
	DESCRIPTION ""
			::= { mbusA6 42 }

mbusA6Value12		OBJECT-TYPE
			SYNTAX	INTEGER
			ACCESS	read-only
			STATUS	current
	DESCRIPTION ""
			::= { mbusA6 43 }

mbusA6VIF13		OBJECT-TYPE
			SYNTAX	INTEGER
			ACCESS	read-only
			STATUS	current
	DESCRIPTION ""
			::= { mbusA6 44 }

mbusA6Value13		OBJECT-TYPE
			SYNTAX	INTEGER
			ACCESS	read-only
			STATUS	current
	DESCRIPTION ""
			::= { mbusA6 45 }

mbusA6VIF14		OBJECT-TYPE
			SYNTAX	INTEGER
			ACCESS	read-only
			STATUS	current
	DESCRIPTION ""
			::= { mbusA6 46 }

mbusA6Value14		OBJECT-TYPE
			SYNTAX	INTEGER
			ACCESS	read-only
			STATUS	current
	DESCRIPTION ""
			::= { mbusA6 47 }

mbusA6VIF15		OBJECT-TYPE
			SYNTAX	INTEGER
			ACCESS	read-only
			STATUS	current
	DESCRIPTION ""
			::= { mbusA6 48 }

mbusA6Value15		OBJECT-TYPE
			SYNTAX	INTEGER
			ACCESS	read-only
			STATUS	current
	DESCRIPTION ""
			::= { mbusA6 49 }

mbusA6VIF16		OBJECT-TYPE
			SYNTAX	INTEGER
			ACCESS	read-only
			STATUS	current
	DESCRIPTION ""
			::= { mbusA6 50 }

mbusA6Value16		OBJECT-TYPE
			SYNTAX	INTEGER
			ACCESS	read-only
			STATUS	current
	DESCRIPTION ""
			::= { mbusA6 51 }

mbusA6VIF17		OBJECT-TYPE
			SYNTAX	INTEGER
			ACCESS	read-only
			STATUS	current
	DESCRIPTION ""
			::= { mbusA6 52 }

mbusA6Value17		OBJECT-TYPE
			SYNTAX	INTEGER
			ACCESS	read-only
			STATUS	current
	DESCRIPTION ""
			::= { mbusA6 53 }

mbusA6VIF18		OBJECT-TYPE
			SYNTAX	INTEGER
			ACCESS	read-only
			STATUS	current
	DESCRIPTION ""
			::= { mbusA6 54 }

mbusA6Value18		OBJECT-TYPE
			SYNTAX	INTEGER
			ACCESS	read-only
			STATUS	current
	DESCRIPTION ""
			::= { mbusA6 55 }

mbusA6VIF19		OBJECT-TYPE
			SYNTAX	INTEGER
			ACCESS	read-only
			STATUS	current
	DESCRIPTION ""
			::= { mbusA6 56 }

mbusA6Value19		OBJECT-TYPE
			SYNTAX	INTEGER
			ACCESS	read-only
			STATUS	current
	DESCRIPTION ""
			::= { mbusA6 57 }

mbusA6VIF1A		OBJECT-TYPE
			SYNTAX	INTEGER
			ACCESS	read-only
			STATUS	current
	DESCRIPTION ""
			::= { mbusA6 58 }

mbusA6Value1A		OBJECT-TYPE
			SYNTAX	INTEGER
			ACCESS	read-only
			STATUS	current
	DESCRIPTION ""
			::= { mbusA6 59 }

mbusA6VIF1B		OBJECT-TYPE
			SYNTAX	INTEGER
			ACCESS	read-only
			STATUS	current
	DESCRIPTION ""
			::= { mbusA6 60 }

mbusA6Value1B		OBJECT-TYPE
			SYNTAX	INTEGER
			ACCESS	read-only
			STATUS	current
	DESCRIPTION ""
			::= { mbusA6 61 }

mbusA6VIF1C		OBJECT-TYPE
			SYNTAX	INTEGER
			ACCESS	read-only
			STATUS	current
	DESCRIPTION ""
			::= { mbusA6 62 }

mbusA6Value1C		OBJECT-TYPE
			SYNTAX	INTEGER
			ACCESS	read-only
			STATUS	current
	DESCRIPTION ""
			::= { mbusA6 63 }

mbusA6VIF1D		OBJECT-TYPE
			SYNTAX	INTEGER
			ACCESS	read-only
			STATUS	current
	DESCRIPTION ""
			::= { mbusA6 64 }

mbusA6Value1D		OBJECT-TYPE
			SYNTAX	INTEGER
			ACCESS	read-only
			STATUS	current
	DESCRIPTION ""
			::= { mbusA6 65 }

mbusA6VIF1E		OBJECT-TYPE
			SYNTAX	INTEGER
			ACCESS	read-only
			STATUS	current
	DESCRIPTION ""
			::= { mbusA6 66 }

mbusA6Value1E		OBJECT-TYPE
			SYNTAX	INTEGER
			ACCESS	read-only
			STATUS	current
	DESCRIPTION ""
			::= { mbusA6 67 }

mbusA6VIF1F		OBJECT-TYPE
			SYNTAX	INTEGER
			ACCESS	read-only
			STATUS	current
	DESCRIPTION ""
			::= { mbusA6 68 }

mbusA6Value1F		OBJECT-TYPE
			SYNTAX	INTEGER
			ACCESS	read-only
			STATUS	current
	DESCRIPTION ""
			::= { mbusA6 69 }

mbusA6VIF20		OBJECT-TYPE
			SYNTAX	INTEGER
			ACCESS	read-only
			STATUS	current
	DESCRIPTION ""
			::= { mbusA6 70 }

mbusA6Value20		OBJECT-TYPE
			SYNTAX	INTEGER
			ACCESS	read-only
			STATUS	current
	DESCRIPTION ""
			::= { mbusA6 71 }

mbusA6VIF21		OBJECT-TYPE
			SYNTAX	INTEGER
			ACCESS	read-only
			STATUS	current
	DESCRIPTION ""
			::= { mbusA6 72 }

mbusA6Value21		OBJECT-TYPE
			SYNTAX	INTEGER
			ACCESS	read-only
			STATUS	current
	DESCRIPTION ""
			::= { mbusA6 73 }

mbusA6VIF22		OBJECT-TYPE
			SYNTAX	INTEGER
			ACCESS	read-only
			STATUS	current
	DESCRIPTION ""
			::= { mbusA6 74 }

mbusA6Value22		OBJECT-TYPE
			SYNTAX	INTEGER
			ACCESS	read-only
			STATUS	current
	DESCRIPTION ""
			::= { mbusA6 75 }

mbusA6VIF23		OBJECT-TYPE
			SYNTAX	INTEGER
			ACCESS	read-only
			STATUS	current
	DESCRIPTION ""
			::= { mbusA6 76 }

mbusA6Value23		OBJECT-TYPE
			SYNTAX	INTEGER
			ACCESS	read-only
			STATUS	current
	DESCRIPTION ""
			::= { mbusA6 77 }

mbusA6VIF24		OBJECT-TYPE
			SYNTAX	INTEGER
			ACCESS	read-only
			STATUS	current
	DESCRIPTION ""
			::= { mbusA6 78 }

mbusA6Value24		OBJECT-TYPE
			SYNTAX	INTEGER
			ACCESS	read-only
			STATUS	current
	DESCRIPTION ""
			::= { mbusA6 79 }

mbusA6VIF25		OBJECT-TYPE
			SYNTAX	INTEGER
			ACCESS	read-only
			STATUS	current
	DESCRIPTION ""
			::= { mbusA6 80 }

mbusA6Value25		OBJECT-TYPE
			SYNTAX	INTEGER
			ACCESS	read-only
			STATUS	current
	DESCRIPTION ""
			::= { mbusA6 81 }

mbusA6VIF26		OBJECT-TYPE
			SYNTAX	INTEGER
			ACCESS	read-only
			STATUS	current
	DESCRIPTION ""
			::= { mbusA6 82 }

mbusA6Value26		OBJECT-TYPE
			SYNTAX	INTEGER
			ACCESS	read-only
			STATUS	current
	DESCRIPTION ""
			::= { mbusA6 83 }

mbusA6VIF27		OBJECT-TYPE
			SYNTAX	INTEGER
			ACCESS	read-only
			STATUS	current
	DESCRIPTION ""
			::= { mbusA6 84 }

mbusA6Value27		OBJECT-TYPE
			SYNTAX	INTEGER
			ACCESS	read-only
			STATUS	current
	DESCRIPTION ""
			::= { mbusA6 85 }

mbusA6VIF28		OBJECT-TYPE
			SYNTAX	INTEGER
			ACCESS	read-only
			STATUS	current
	DESCRIPTION ""
			::= { mbusA6 86 }

mbusA6Value28		OBJECT-TYPE
			SYNTAX	INTEGER
			ACCESS	read-only
			STATUS	current
	DESCRIPTION ""
			::= { mbusA6 87 }

mbusA6VIF29		OBJECT-TYPE
			SYNTAX	INTEGER
			ACCESS	read-only
			STATUS	current
	DESCRIPTION ""
			::= { mbusA6 88 }

mbusA6Value29		OBJECT-TYPE
			SYNTAX	INTEGER
			ACCESS	read-only
			STATUS	current
	DESCRIPTION ""
			::= { mbusA6 89 }

mbusA6VIF2A		OBJECT-TYPE
			SYNTAX	INTEGER
			ACCESS	read-only
			STATUS	current
	DESCRIPTION ""
			::= { mbusA6 90 }

mbusA6Value2A		OBJECT-TYPE
			SYNTAX	INTEGER
			ACCESS	read-only
			STATUS	current
	DESCRIPTION ""
			::= { mbusA6 91 }

mbusA6VIF2B		OBJECT-TYPE
			SYNTAX	INTEGER
			ACCESS	read-only
			STATUS	current
	DESCRIPTION ""
			::= { mbusA6 92 }

mbusA6Value2B		OBJECT-TYPE
			SYNTAX	INTEGER
			ACCESS	read-only
			STATUS	current
	DESCRIPTION ""
			::= { mbusA6 93 }

mbusA6VIF2C		OBJECT-TYPE
			SYNTAX	INTEGER
			ACCESS	read-only
			STATUS	current
	DESCRIPTION ""
			::= { mbusA6 94 }

mbusA6Value2C		OBJECT-TYPE
			SYNTAX	INTEGER
			ACCESS	read-only
			STATUS	current
	DESCRIPTION ""
			::= { mbusA6 95 }

mbusA6VIF2D		OBJECT-TYPE
			SYNTAX	INTEGER
			ACCESS	read-only
			STATUS	current
	DESCRIPTION ""
			::= { mbusA6 96 }

mbusA6Value2D		OBJECT-TYPE
			SYNTAX	INTEGER
			ACCESS	read-only
			STATUS	current
	DESCRIPTION ""
			::= { mbusA6 97 }

mbusA6VIF2E		OBJECT-TYPE
			SYNTAX	INTEGER
			ACCESS	read-only
			STATUS	current
	DESCRIPTION ""
			::= { mbusA6 98 }

mbusA6Value2E		OBJECT-TYPE
			SYNTAX	INTEGER
			ACCESS	read-only
			STATUS	current
	DESCRIPTION ""
			::= { mbusA6 99 }

mbusA6VIF2F		OBJECT-TYPE
			SYNTAX	INTEGER
			ACCESS	read-only
			STATUS	current
	DESCRIPTION ""
			::= { mbusA6 100 }

mbusA6Value2F		OBJECT-TYPE
			SYNTAX	INTEGER
			ACCESS	read-only
			STATUS	current
	DESCRIPTION ""
			::= { mbusA6 101 }

mbusA7			OBJECT IDENTIFIER ::= { mbus 167 }

mbusA7IdNumber		OBJECT-TYPE
			SYNTAX	Gauge
			ACCESS	read-only
			STATUS	current
	DESCRIPTION ""
			::= { mbusA7 1 }

mbusA7Manufacturer	OBJECT-TYPE
			SYNTAX	Gauge
			ACCESS	read-only
			STATUS	current
	DESCRIPTION ""
			::= { mbusA7 2 }

mbusA7Version		OBJECT-TYPE
			SYNTAX	Gauge
			ACCESS	read-only
			STATUS	current
	DESCRIPTION ""
			::= { mbusA7 3 }

mbusA7Medium		OBJECT-TYPE
			SYNTAX	Gauge
			ACCESS	read-only
			STATUS	current
	DESCRIPTION ""
			::= { mbusA7 4 }

mbusA7Status		OBJECT-TYPE
			SYNTAX	Gauge
			ACCESS	read-only
			STATUS	current
	DESCRIPTION ""
			::= { mbusA7 5 }

mbusA7VIF00		OBJECT-TYPE
			SYNTAX	INTEGER
			ACCESS	read-only
			STATUS	current
	DESCRIPTION ""
			::= { mbusA7 6 }

mbusA7Value00		OBJECT-TYPE
			SYNTAX	INTEGER
			ACCESS	read-only
			STATUS	current
	DESCRIPTION ""
			::= { mbusA7 7 }

mbusA7VIF01		OBJECT-TYPE
			SYNTAX	INTEGER
			ACCESS	read-only
			STATUS	current
	DESCRIPTION ""
			::= { mbusA7 8 }

mbusA7Value01		OBJECT-TYPE
			SYNTAX	INTEGER
			ACCESS	read-only
			STATUS	current
	DESCRIPTION ""
			::= { mbusA7 9 }

mbusA7VIF02		OBJECT-TYPE
			SYNTAX	INTEGER
			ACCESS	read-only
			STATUS	current
	DESCRIPTION ""
			::= { mbusA7 10 }

mbusA7Value02		OBJECT-TYPE
			SYNTAX	INTEGER
			ACCESS	read-only
			STATUS	current
	DESCRIPTION ""
			::= { mbusA7 11 }

mbusA7VIF03		OBJECT-TYPE
			SYNTAX	INTEGER
			ACCESS	read-only
			STATUS	current
	DESCRIPTION ""
			::= { mbusA7 12 }

mbusA7Value03		OBJECT-TYPE
			SYNTAX	INTEGER
			ACCESS	read-only
			STATUS	current
	DESCRIPTION ""
			::= { mbusA7 13 }

mbusA7VIF04		OBJECT-TYPE
			SYNTAX	INTEGER
			ACCESS	read-only
			STATUS	current
	DESCRIPTION ""
			::= { mbusA7 14 }

mbusA7Value04		OBJECT-TYPE
			SYNTAX	INTEGER
			ACCESS	read-only
			STATUS	current
	DESCRIPTION ""
			::= { mbusA7 15 }

mbusA7VIF05		OBJECT-TYPE
			SYNTAX	INTEGER
			ACCESS	read-only
			STATUS	current
	DESCRIPTION ""
			::= { mbusA7 16 }

mbusA7Value05		OBJECT-TYPE
			SYNTAX	INTEGER
			ACCESS	read-only
			STATUS	current
	DESCRIPTION ""
			::= { mbusA7 17 }

mbusA7VIF06		OBJECT-TYPE
			SYNTAX	INTEGER
			ACCESS	read-only
			STATUS	current
	DESCRIPTION ""
			::= { mbusA7 18 }

mbusA7Value06		OBJECT-TYPE
			SYNTAX	INTEGER
			ACCESS	read-only
			STATUS	current
	DESCRIPTION ""
			::= { mbusA7 19 }

mbusA7VIF07		OBJECT-TYPE
			SYNTAX	INTEGER
			ACCESS	read-only
			STATUS	current
	DESCRIPTION ""
			::= { mbusA7 20 }

mbusA7Value07		OBJECT-TYPE
			SYNTAX	INTEGER
			ACCESS	read-only
			STATUS	current
	DESCRIPTION ""
			::= { mbusA7 21 }

mbusA7VIF08		OBJECT-TYPE
			SYNTAX	INTEGER
			ACCESS	read-only
			STATUS	current
	DESCRIPTION ""
			::= { mbusA7 22 }

mbusA7Value08		OBJECT-TYPE
			SYNTAX	INTEGER
			ACCESS	read-only
			STATUS	current
	DESCRIPTION ""
			::= { mbusA7 23 }

mbusA7VIF09		OBJECT-TYPE
			SYNTAX	INTEGER
			ACCESS	read-only
			STATUS	current
	DESCRIPTION ""
			::= { mbusA7 24 }

mbusA7Value09		OBJECT-TYPE
			SYNTAX	INTEGER
			ACCESS	read-only
			STATUS	current
	DESCRIPTION ""
			::= { mbusA7 25 }

mbusA7VIF0A		OBJECT-TYPE
			SYNTAX	INTEGER
			ACCESS	read-only
			STATUS	current
	DESCRIPTION ""
			::= { mbusA7 26 }

mbusA7Value0A		OBJECT-TYPE
			SYNTAX	INTEGER
			ACCESS	read-only
			STATUS	current
	DESCRIPTION ""
			::= { mbusA7 27 }

mbusA7VIF0B		OBJECT-TYPE
			SYNTAX	INTEGER
			ACCESS	read-only
			STATUS	current
	DESCRIPTION ""
			::= { mbusA7 28 }

mbusA7Value0B		OBJECT-TYPE
			SYNTAX	INTEGER
			ACCESS	read-only
			STATUS	current
	DESCRIPTION ""
			::= { mbusA7 29 }

mbusA7VIF0C		OBJECT-TYPE
			SYNTAX	INTEGER
			ACCESS	read-only
			STATUS	current
	DESCRIPTION ""
			::= { mbusA7 30 }

mbusA7Value0C		OBJECT-TYPE
			SYNTAX	INTEGER
			ACCESS	read-only
			STATUS	current
	DESCRIPTION ""
			::= { mbusA7 31 }

mbusA7VIF0D		OBJECT-TYPE
			SYNTAX	INTEGER
			ACCESS	read-only
			STATUS	current
	DESCRIPTION ""
			::= { mbusA7 32 }

mbusA7Value0D		OBJECT-TYPE
			SYNTAX	INTEGER
			ACCESS	read-only
			STATUS	current
	DESCRIPTION ""
			::= { mbusA7 33 }

mbusA7VIF0E		OBJECT-TYPE
			SYNTAX	INTEGER
			ACCESS	read-only
			STATUS	current
	DESCRIPTION ""
			::= { mbusA7 34 }

mbusA7Value0E		OBJECT-TYPE
			SYNTAX	INTEGER
			ACCESS	read-only
			STATUS	current
	DESCRIPTION ""
			::= { mbusA7 35 }

mbusA7VIF0F		OBJECT-TYPE
			SYNTAX	INTEGER
			ACCESS	read-only
			STATUS	current
	DESCRIPTION ""
			::= { mbusA7 36 }

mbusA7Value0F		OBJECT-TYPE
			SYNTAX	INTEGER
			ACCESS	read-only
			STATUS	current
	DESCRIPTION ""
			::= { mbusA7 37 }

mbusA7VIF10		OBJECT-TYPE
			SYNTAX	INTEGER
			ACCESS	read-only
			STATUS	current
	DESCRIPTION ""
			::= { mbusA7 38 }

mbusA7Value10		OBJECT-TYPE
			SYNTAX	INTEGER
			ACCESS	read-only
			STATUS	current
	DESCRIPTION ""
			::= { mbusA7 39 }

mbusA7VIF11		OBJECT-TYPE
			SYNTAX	INTEGER
			ACCESS	read-only
			STATUS	current
	DESCRIPTION ""
			::= { mbusA7 40 }

mbusA7Value11		OBJECT-TYPE
			SYNTAX	INTEGER
			ACCESS	read-only
			STATUS	current
	DESCRIPTION ""
			::= { mbusA7 41 }

mbusA7VIF12		OBJECT-TYPE
			SYNTAX	INTEGER
			ACCESS	read-only
			STATUS	current
	DESCRIPTION ""
			::= { mbusA7 42 }

mbusA7Value12		OBJECT-TYPE
			SYNTAX	INTEGER
			ACCESS	read-only
			STATUS	current
	DESCRIPTION ""
			::= { mbusA7 43 }

mbusA7VIF13		OBJECT-TYPE
			SYNTAX	INTEGER
			ACCESS	read-only
			STATUS	current
	DESCRIPTION ""
			::= { mbusA7 44 }

mbusA7Value13		OBJECT-TYPE
			SYNTAX	INTEGER
			ACCESS	read-only
			STATUS	current
	DESCRIPTION ""
			::= { mbusA7 45 }

mbusA7VIF14		OBJECT-TYPE
			SYNTAX	INTEGER
			ACCESS	read-only
			STATUS	current
	DESCRIPTION ""
			::= { mbusA7 46 }

mbusA7Value14		OBJECT-TYPE
			SYNTAX	INTEGER
			ACCESS	read-only
			STATUS	current
	DESCRIPTION ""
			::= { mbusA7 47 }

mbusA7VIF15		OBJECT-TYPE
			SYNTAX	INTEGER
			ACCESS	read-only
			STATUS	current
	DESCRIPTION ""
			::= { mbusA7 48 }

mbusA7Value15		OBJECT-TYPE
			SYNTAX	INTEGER
			ACCESS	read-only
			STATUS	current
	DESCRIPTION ""
			::= { mbusA7 49 }

mbusA7VIF16		OBJECT-TYPE
			SYNTAX	INTEGER
			ACCESS	read-only
			STATUS	current
	DESCRIPTION ""
			::= { mbusA7 50 }

mbusA7Value16		OBJECT-TYPE
			SYNTAX	INTEGER
			ACCESS	read-only
			STATUS	current
	DESCRIPTION ""
			::= { mbusA7 51 }

mbusA7VIF17		OBJECT-TYPE
			SYNTAX	INTEGER
			ACCESS	read-only
			STATUS	current
	DESCRIPTION ""
			::= { mbusA7 52 }

mbusA7Value17		OBJECT-TYPE
			SYNTAX	INTEGER
			ACCESS	read-only
			STATUS	current
	DESCRIPTION ""
			::= { mbusA7 53 }

mbusA7VIF18		OBJECT-TYPE
			SYNTAX	INTEGER
			ACCESS	read-only
			STATUS	current
	DESCRIPTION ""
			::= { mbusA7 54 }

mbusA7Value18		OBJECT-TYPE
			SYNTAX	INTEGER
			ACCESS	read-only
			STATUS	current
	DESCRIPTION ""
			::= { mbusA7 55 }

mbusA7VIF19		OBJECT-TYPE
			SYNTAX	INTEGER
			ACCESS	read-only
			STATUS	current
	DESCRIPTION ""
			::= { mbusA7 56 }

mbusA7Value19		OBJECT-TYPE
			SYNTAX	INTEGER
			ACCESS	read-only
			STATUS	current
	DESCRIPTION ""
			::= { mbusA7 57 }

mbusA7VIF1A		OBJECT-TYPE
			SYNTAX	INTEGER
			ACCESS	read-only
			STATUS	current
	DESCRIPTION ""
			::= { mbusA7 58 }

mbusA7Value1A		OBJECT-TYPE
			SYNTAX	INTEGER
			ACCESS	read-only
			STATUS	current
	DESCRIPTION ""
			::= { mbusA7 59 }

mbusA7VIF1B		OBJECT-TYPE
			SYNTAX	INTEGER
			ACCESS	read-only
			STATUS	current
	DESCRIPTION ""
			::= { mbusA7 60 }

mbusA7Value1B		OBJECT-TYPE
			SYNTAX	INTEGER
			ACCESS	read-only
			STATUS	current
	DESCRIPTION ""
			::= { mbusA7 61 }

mbusA7VIF1C		OBJECT-TYPE
			SYNTAX	INTEGER
			ACCESS	read-only
			STATUS	current
	DESCRIPTION ""
			::= { mbusA7 62 }

mbusA7Value1C		OBJECT-TYPE
			SYNTAX	INTEGER
			ACCESS	read-only
			STATUS	current
	DESCRIPTION ""
			::= { mbusA7 63 }

mbusA7VIF1D		OBJECT-TYPE
			SYNTAX	INTEGER
			ACCESS	read-only
			STATUS	current
	DESCRIPTION ""
			::= { mbusA7 64 }

mbusA7Value1D		OBJECT-TYPE
			SYNTAX	INTEGER
			ACCESS	read-only
			STATUS	current
	DESCRIPTION ""
			::= { mbusA7 65 }

mbusA7VIF1E		OBJECT-TYPE
			SYNTAX	INTEGER
			ACCESS	read-only
			STATUS	current
	DESCRIPTION ""
			::= { mbusA7 66 }

mbusA7Value1E		OBJECT-TYPE
			SYNTAX	INTEGER
			ACCESS	read-only
			STATUS	current
	DESCRIPTION ""
			::= { mbusA7 67 }

mbusA7VIF1F		OBJECT-TYPE
			SYNTAX	INTEGER
			ACCESS	read-only
			STATUS	current
	DESCRIPTION ""
			::= { mbusA7 68 }

mbusA7Value1F		OBJECT-TYPE
			SYNTAX	INTEGER
			ACCESS	read-only
			STATUS	current
	DESCRIPTION ""
			::= { mbusA7 69 }

mbusA7VIF20		OBJECT-TYPE
			SYNTAX	INTEGER
			ACCESS	read-only
			STATUS	current
	DESCRIPTION ""
			::= { mbusA7 70 }

mbusA7Value20		OBJECT-TYPE
			SYNTAX	INTEGER
			ACCESS	read-only
			STATUS	current
	DESCRIPTION ""
			::= { mbusA7 71 }

mbusA7VIF21		OBJECT-TYPE
			SYNTAX	INTEGER
			ACCESS	read-only
			STATUS	current
	DESCRIPTION ""
			::= { mbusA7 72 }

mbusA7Value21		OBJECT-TYPE
			SYNTAX	INTEGER
			ACCESS	read-only
			STATUS	current
	DESCRIPTION ""
			::= { mbusA7 73 }

mbusA7VIF22		OBJECT-TYPE
			SYNTAX	INTEGER
			ACCESS	read-only
			STATUS	current
	DESCRIPTION ""
			::= { mbusA7 74 }

mbusA7Value22		OBJECT-TYPE
			SYNTAX	INTEGER
			ACCESS	read-only
			STATUS	current
	DESCRIPTION ""
			::= { mbusA7 75 }

mbusA7VIF23		OBJECT-TYPE
			SYNTAX	INTEGER
			ACCESS	read-only
			STATUS	current
	DESCRIPTION ""
			::= { mbusA7 76 }

mbusA7Value23		OBJECT-TYPE
			SYNTAX	INTEGER
			ACCESS	read-only
			STATUS	current
	DESCRIPTION ""
			::= { mbusA7 77 }

mbusA7VIF24		OBJECT-TYPE
			SYNTAX	INTEGER
			ACCESS	read-only
			STATUS	current
	DESCRIPTION ""
			::= { mbusA7 78 }

mbusA7Value24		OBJECT-TYPE
			SYNTAX	INTEGER
			ACCESS	read-only
			STATUS	current
	DESCRIPTION ""
			::= { mbusA7 79 }

mbusA7VIF25		OBJECT-TYPE
			SYNTAX	INTEGER
			ACCESS	read-only
			STATUS	current
	DESCRIPTION ""
			::= { mbusA7 80 }

mbusA7Value25		OBJECT-TYPE
			SYNTAX	INTEGER
			ACCESS	read-only
			STATUS	current
	DESCRIPTION ""
			::= { mbusA7 81 }

mbusA7VIF26		OBJECT-TYPE
			SYNTAX	INTEGER
			ACCESS	read-only
			STATUS	current
	DESCRIPTION ""
			::= { mbusA7 82 }

mbusA7Value26		OBJECT-TYPE
			SYNTAX	INTEGER
			ACCESS	read-only
			STATUS	current
	DESCRIPTION ""
			::= { mbusA7 83 }

mbusA7VIF27		OBJECT-TYPE
			SYNTAX	INTEGER
			ACCESS	read-only
			STATUS	current
	DESCRIPTION ""
			::= { mbusA7 84 }

mbusA7Value27		OBJECT-TYPE
			SYNTAX	INTEGER
			ACCESS	read-only
			STATUS	current
	DESCRIPTION ""
			::= { mbusA7 85 }

mbusA7VIF28		OBJECT-TYPE
			SYNTAX	INTEGER
			ACCESS	read-only
			STATUS	current
	DESCRIPTION ""
			::= { mbusA7 86 }

mbusA7Value28		OBJECT-TYPE
			SYNTAX	INTEGER
			ACCESS	read-only
			STATUS	current
	DESCRIPTION ""
			::= { mbusA7 87 }

mbusA7VIF29		OBJECT-TYPE
			SYNTAX	INTEGER
			ACCESS	read-only
			STATUS	current
	DESCRIPTION ""
			::= { mbusA7 88 }

mbusA7Value29		OBJECT-TYPE
			SYNTAX	INTEGER
			ACCESS	read-only
			STATUS	current
	DESCRIPTION ""
			::= { mbusA7 89 }

mbusA7VIF2A		OBJECT-TYPE
			SYNTAX	INTEGER
			ACCESS	read-only
			STATUS	current
	DESCRIPTION ""
			::= { mbusA7 90 }

mbusA7Value2A		OBJECT-TYPE
			SYNTAX	INTEGER
			ACCESS	read-only
			STATUS	current
	DESCRIPTION ""
			::= { mbusA7 91 }

mbusA7VIF2B		OBJECT-TYPE
			SYNTAX	INTEGER
			ACCESS	read-only
			STATUS	current
	DESCRIPTION ""
			::= { mbusA7 92 }

mbusA7Value2B		OBJECT-TYPE
			SYNTAX	INTEGER
			ACCESS	read-only
			STATUS	current
	DESCRIPTION ""
			::= { mbusA7 93 }

mbusA7VIF2C		OBJECT-TYPE
			SYNTAX	INTEGER
			ACCESS	read-only
			STATUS	current
	DESCRIPTION ""
			::= { mbusA7 94 }

mbusA7Value2C		OBJECT-TYPE
			SYNTAX	INTEGER
			ACCESS	read-only
			STATUS	current
	DESCRIPTION ""
			::= { mbusA7 95 }

mbusA7VIF2D		OBJECT-TYPE
			SYNTAX	INTEGER
			ACCESS	read-only
			STATUS	current
	DESCRIPTION ""
			::= { mbusA7 96 }

mbusA7Value2D		OBJECT-TYPE
			SYNTAX	INTEGER
			ACCESS	read-only
			STATUS	current
	DESCRIPTION ""
			::= { mbusA7 97 }

mbusA7VIF2E		OBJECT-TYPE
			SYNTAX	INTEGER
			ACCESS	read-only
			STATUS	current
	DESCRIPTION ""
			::= { mbusA7 98 }

mbusA7Value2E		OBJECT-TYPE
			SYNTAX	INTEGER
			ACCESS	read-only
			STATUS	current
	DESCRIPTION ""
			::= { mbusA7 99 }

mbusA7VIF2F		OBJECT-TYPE
			SYNTAX	INTEGER
			ACCESS	read-only
			STATUS	current
	DESCRIPTION ""
			::= { mbusA7 100 }

mbusA7Value2F		OBJECT-TYPE
			SYNTAX	INTEGER
			ACCESS	read-only
			STATUS	current
	DESCRIPTION ""
			::= { mbusA7 101 }

mbusA8			OBJECT IDENTIFIER ::= { mbus 168 }

mbusA8IdNumber		OBJECT-TYPE
			SYNTAX	Gauge
			ACCESS	read-only
			STATUS	current
	DESCRIPTION ""
			::= { mbusA8 1 }

mbusA8Manufacturer	OBJECT-TYPE
			SYNTAX	Gauge
			ACCESS	read-only
			STATUS	current
	DESCRIPTION ""
			::= { mbusA8 2 }

mbusA8Version		OBJECT-TYPE
			SYNTAX	Gauge
			ACCESS	read-only
			STATUS	current
	DESCRIPTION ""
			::= { mbusA8 3 }

mbusA8Medium		OBJECT-TYPE
			SYNTAX	Gauge
			ACCESS	read-only
			STATUS	current
	DESCRIPTION ""
			::= { mbusA8 4 }

mbusA8Status		OBJECT-TYPE
			SYNTAX	Gauge
			ACCESS	read-only
			STATUS	current
	DESCRIPTION ""
			::= { mbusA8 5 }

mbusA8VIF00		OBJECT-TYPE
			SYNTAX	INTEGER
			ACCESS	read-only
			STATUS	current
	DESCRIPTION ""
			::= { mbusA8 6 }

mbusA8Value00		OBJECT-TYPE
			SYNTAX	INTEGER
			ACCESS	read-only
			STATUS	current
	DESCRIPTION ""
			::= { mbusA8 7 }

mbusA8VIF01		OBJECT-TYPE
			SYNTAX	INTEGER
			ACCESS	read-only
			STATUS	current
	DESCRIPTION ""
			::= { mbusA8 8 }

mbusA8Value01		OBJECT-TYPE
			SYNTAX	INTEGER
			ACCESS	read-only
			STATUS	current
	DESCRIPTION ""
			::= { mbusA8 9 }

mbusA8VIF02		OBJECT-TYPE
			SYNTAX	INTEGER
			ACCESS	read-only
			STATUS	current
	DESCRIPTION ""
			::= { mbusA8 10 }

mbusA8Value02		OBJECT-TYPE
			SYNTAX	INTEGER
			ACCESS	read-only
			STATUS	current
	DESCRIPTION ""
			::= { mbusA8 11 }

mbusA8VIF03		OBJECT-TYPE
			SYNTAX	INTEGER
			ACCESS	read-only
			STATUS	current
	DESCRIPTION ""
			::= { mbusA8 12 }

mbusA8Value03		OBJECT-TYPE
			SYNTAX	INTEGER
			ACCESS	read-only
			STATUS	current
	DESCRIPTION ""
			::= { mbusA8 13 }

mbusA8VIF04		OBJECT-TYPE
			SYNTAX	INTEGER
			ACCESS	read-only
			STATUS	current
	DESCRIPTION ""
			::= { mbusA8 14 }

mbusA8Value04		OBJECT-TYPE
			SYNTAX	INTEGER
			ACCESS	read-only
			STATUS	current
	DESCRIPTION ""
			::= { mbusA8 15 }

mbusA8VIF05		OBJECT-TYPE
			SYNTAX	INTEGER
			ACCESS	read-only
			STATUS	current
	DESCRIPTION ""
			::= { mbusA8 16 }

mbusA8Value05		OBJECT-TYPE
			SYNTAX	INTEGER
			ACCESS	read-only
			STATUS	current
	DESCRIPTION ""
			::= { mbusA8 17 }

mbusA8VIF06		OBJECT-TYPE
			SYNTAX	INTEGER
			ACCESS	read-only
			STATUS	current
	DESCRIPTION ""
			::= { mbusA8 18 }

mbusA8Value06		OBJECT-TYPE
			SYNTAX	INTEGER
			ACCESS	read-only
			STATUS	current
	DESCRIPTION ""
			::= { mbusA8 19 }

mbusA8VIF07		OBJECT-TYPE
			SYNTAX	INTEGER
			ACCESS	read-only
			STATUS	current
	DESCRIPTION ""
			::= { mbusA8 20 }

mbusA8Value07		OBJECT-TYPE
			SYNTAX	INTEGER
			ACCESS	read-only
			STATUS	current
	DESCRIPTION ""
			::= { mbusA8 21 }

mbusA8VIF08		OBJECT-TYPE
			SYNTAX	INTEGER
			ACCESS	read-only
			STATUS	current
	DESCRIPTION ""
			::= { mbusA8 22 }

mbusA8Value08		OBJECT-TYPE
			SYNTAX	INTEGER
			ACCESS	read-only
			STATUS	current
	DESCRIPTION ""
			::= { mbusA8 23 }

mbusA8VIF09		OBJECT-TYPE
			SYNTAX	INTEGER
			ACCESS	read-only
			STATUS	current
	DESCRIPTION ""
			::= { mbusA8 24 }

mbusA8Value09		OBJECT-TYPE
			SYNTAX	INTEGER
			ACCESS	read-only
			STATUS	current
	DESCRIPTION ""
			::= { mbusA8 25 }

mbusA8VIF0A		OBJECT-TYPE
			SYNTAX	INTEGER
			ACCESS	read-only
			STATUS	current
	DESCRIPTION ""
			::= { mbusA8 26 }

mbusA8Value0A		OBJECT-TYPE
			SYNTAX	INTEGER
			ACCESS	read-only
			STATUS	current
	DESCRIPTION ""
			::= { mbusA8 27 }

mbusA8VIF0B		OBJECT-TYPE
			SYNTAX	INTEGER
			ACCESS	read-only
			STATUS	current
	DESCRIPTION ""
			::= { mbusA8 28 }

mbusA8Value0B		OBJECT-TYPE
			SYNTAX	INTEGER
			ACCESS	read-only
			STATUS	current
	DESCRIPTION ""
			::= { mbusA8 29 }

mbusA8VIF0C		OBJECT-TYPE
			SYNTAX	INTEGER
			ACCESS	read-only
			STATUS	current
	DESCRIPTION ""
			::= { mbusA8 30 }

mbusA8Value0C		OBJECT-TYPE
			SYNTAX	INTEGER
			ACCESS	read-only
			STATUS	current
	DESCRIPTION ""
			::= { mbusA8 31 }

mbusA8VIF0D		OBJECT-TYPE
			SYNTAX	INTEGER
			ACCESS	read-only
			STATUS	current
	DESCRIPTION ""
			::= { mbusA8 32 }

mbusA8Value0D		OBJECT-TYPE
			SYNTAX	INTEGER
			ACCESS	read-only
			STATUS	current
	DESCRIPTION ""
			::= { mbusA8 33 }

mbusA8VIF0E		OBJECT-TYPE
			SYNTAX	INTEGER
			ACCESS	read-only
			STATUS	current
	DESCRIPTION ""
			::= { mbusA8 34 }

mbusA8Value0E		OBJECT-TYPE
			SYNTAX	INTEGER
			ACCESS	read-only
			STATUS	current
	DESCRIPTION ""
			::= { mbusA8 35 }

mbusA8VIF0F		OBJECT-TYPE
			SYNTAX	INTEGER
			ACCESS	read-only
			STATUS	current
	DESCRIPTION ""
			::= { mbusA8 36 }

mbusA8Value0F		OBJECT-TYPE
			SYNTAX	INTEGER
			ACCESS	read-only
			STATUS	current
	DESCRIPTION ""
			::= { mbusA8 37 }

mbusA8VIF10		OBJECT-TYPE
			SYNTAX	INTEGER
			ACCESS	read-only
			STATUS	current
	DESCRIPTION ""
			::= { mbusA8 38 }

mbusA8Value10		OBJECT-TYPE
			SYNTAX	INTEGER
			ACCESS	read-only
			STATUS	current
	DESCRIPTION ""
			::= { mbusA8 39 }

mbusA8VIF11		OBJECT-TYPE
			SYNTAX	INTEGER
			ACCESS	read-only
			STATUS	current
	DESCRIPTION ""
			::= { mbusA8 40 }

mbusA8Value11		OBJECT-TYPE
			SYNTAX	INTEGER
			ACCESS	read-only
			STATUS	current
	DESCRIPTION ""
			::= { mbusA8 41 }

mbusA8VIF12		OBJECT-TYPE
			SYNTAX	INTEGER
			ACCESS	read-only
			STATUS	current
	DESCRIPTION ""
			::= { mbusA8 42 }

mbusA8Value12		OBJECT-TYPE
			SYNTAX	INTEGER
			ACCESS	read-only
			STATUS	current
	DESCRIPTION ""
			::= { mbusA8 43 }

mbusA8VIF13		OBJECT-TYPE
			SYNTAX	INTEGER
			ACCESS	read-only
			STATUS	current
	DESCRIPTION ""
			::= { mbusA8 44 }

mbusA8Value13		OBJECT-TYPE
			SYNTAX	INTEGER
			ACCESS	read-only
			STATUS	current
	DESCRIPTION ""
			::= { mbusA8 45 }

mbusA8VIF14		OBJECT-TYPE
			SYNTAX	INTEGER
			ACCESS	read-only
			STATUS	current
	DESCRIPTION ""
			::= { mbusA8 46 }

mbusA8Value14		OBJECT-TYPE
			SYNTAX	INTEGER
			ACCESS	read-only
			STATUS	current
	DESCRIPTION ""
			::= { mbusA8 47 }

mbusA8VIF15		OBJECT-TYPE
			SYNTAX	INTEGER
			ACCESS	read-only
			STATUS	current
	DESCRIPTION ""
			::= { mbusA8 48 }

mbusA8Value15		OBJECT-TYPE
			SYNTAX	INTEGER
			ACCESS	read-only
			STATUS	current
	DESCRIPTION ""
			::= { mbusA8 49 }

mbusA8VIF16		OBJECT-TYPE
			SYNTAX	INTEGER
			ACCESS	read-only
			STATUS	current
	DESCRIPTION ""
			::= { mbusA8 50 }

mbusA8Value16		OBJECT-TYPE
			SYNTAX	INTEGER
			ACCESS	read-only
			STATUS	current
	DESCRIPTION ""
			::= { mbusA8 51 }

mbusA8VIF17		OBJECT-TYPE
			SYNTAX	INTEGER
			ACCESS	read-only
			STATUS	current
	DESCRIPTION ""
			::= { mbusA8 52 }

mbusA8Value17		OBJECT-TYPE
			SYNTAX	INTEGER
			ACCESS	read-only
			STATUS	current
	DESCRIPTION ""
			::= { mbusA8 53 }

mbusA8VIF18		OBJECT-TYPE
			SYNTAX	INTEGER
			ACCESS	read-only
			STATUS	current
	DESCRIPTION ""
			::= { mbusA8 54 }

mbusA8Value18		OBJECT-TYPE
			SYNTAX	INTEGER
			ACCESS	read-only
			STATUS	current
	DESCRIPTION ""
			::= { mbusA8 55 }

mbusA8VIF19		OBJECT-TYPE
			SYNTAX	INTEGER
			ACCESS	read-only
			STATUS	current
	DESCRIPTION ""
			::= { mbusA8 56 }

mbusA8Value19		OBJECT-TYPE
			SYNTAX	INTEGER
			ACCESS	read-only
			STATUS	current
	DESCRIPTION ""
			::= { mbusA8 57 }

mbusA8VIF1A		OBJECT-TYPE
			SYNTAX	INTEGER
			ACCESS	read-only
			STATUS	current
	DESCRIPTION ""
			::= { mbusA8 58 }

mbusA8Value1A		OBJECT-TYPE
			SYNTAX	INTEGER
			ACCESS	read-only
			STATUS	current
	DESCRIPTION ""
			::= { mbusA8 59 }

mbusA8VIF1B		OBJECT-TYPE
			SYNTAX	INTEGER
			ACCESS	read-only
			STATUS	current
	DESCRIPTION ""
			::= { mbusA8 60 }

mbusA8Value1B		OBJECT-TYPE
			SYNTAX	INTEGER
			ACCESS	read-only
			STATUS	current
	DESCRIPTION ""
			::= { mbusA8 61 }

mbusA8VIF1C		OBJECT-TYPE
			SYNTAX	INTEGER
			ACCESS	read-only
			STATUS	current
	DESCRIPTION ""
			::= { mbusA8 62 }

mbusA8Value1C		OBJECT-TYPE
			SYNTAX	INTEGER
			ACCESS	read-only
			STATUS	current
	DESCRIPTION ""
			::= { mbusA8 63 }

mbusA8VIF1D		OBJECT-TYPE
			SYNTAX	INTEGER
			ACCESS	read-only
			STATUS	current
	DESCRIPTION ""
			::= { mbusA8 64 }

mbusA8Value1D		OBJECT-TYPE
			SYNTAX	INTEGER
			ACCESS	read-only
			STATUS	current
	DESCRIPTION ""
			::= { mbusA8 65 }

mbusA8VIF1E		OBJECT-TYPE
			SYNTAX	INTEGER
			ACCESS	read-only
			STATUS	current
	DESCRIPTION ""
			::= { mbusA8 66 }

mbusA8Value1E		OBJECT-TYPE
			SYNTAX	INTEGER
			ACCESS	read-only
			STATUS	current
	DESCRIPTION ""
			::= { mbusA8 67 }

mbusA8VIF1F		OBJECT-TYPE
			SYNTAX	INTEGER
			ACCESS	read-only
			STATUS	current
	DESCRIPTION ""
			::= { mbusA8 68 }

mbusA8Value1F		OBJECT-TYPE
			SYNTAX	INTEGER
			ACCESS	read-only
			STATUS	current
	DESCRIPTION ""
			::= { mbusA8 69 }

mbusA8VIF20		OBJECT-TYPE
			SYNTAX	INTEGER
			ACCESS	read-only
			STATUS	current
	DESCRIPTION ""
			::= { mbusA8 70 }

mbusA8Value20		OBJECT-TYPE
			SYNTAX	INTEGER
			ACCESS	read-only
			STATUS	current
	DESCRIPTION ""
			::= { mbusA8 71 }

mbusA8VIF21		OBJECT-TYPE
			SYNTAX	INTEGER
			ACCESS	read-only
			STATUS	current
	DESCRIPTION ""
			::= { mbusA8 72 }

mbusA8Value21		OBJECT-TYPE
			SYNTAX	INTEGER
			ACCESS	read-only
			STATUS	current
	DESCRIPTION ""
			::= { mbusA8 73 }

mbusA8VIF22		OBJECT-TYPE
			SYNTAX	INTEGER
			ACCESS	read-only
			STATUS	current
	DESCRIPTION ""
			::= { mbusA8 74 }

mbusA8Value22		OBJECT-TYPE
			SYNTAX	INTEGER
			ACCESS	read-only
			STATUS	current
	DESCRIPTION ""
			::= { mbusA8 75 }

mbusA8VIF23		OBJECT-TYPE
			SYNTAX	INTEGER
			ACCESS	read-only
			STATUS	current
	DESCRIPTION ""
			::= { mbusA8 76 }

mbusA8Value23		OBJECT-TYPE
			SYNTAX	INTEGER
			ACCESS	read-only
			STATUS	current
	DESCRIPTION ""
			::= { mbusA8 77 }

mbusA8VIF24		OBJECT-TYPE
			SYNTAX	INTEGER
			ACCESS	read-only
			STATUS	current
	DESCRIPTION ""
			::= { mbusA8 78 }

mbusA8Value24		OBJECT-TYPE
			SYNTAX	INTEGER
			ACCESS	read-only
			STATUS	current
	DESCRIPTION ""
			::= { mbusA8 79 }

mbusA8VIF25		OBJECT-TYPE
			SYNTAX	INTEGER
			ACCESS	read-only
			STATUS	current
	DESCRIPTION ""
			::= { mbusA8 80 }

mbusA8Value25		OBJECT-TYPE
			SYNTAX	INTEGER
			ACCESS	read-only
			STATUS	current
	DESCRIPTION ""
			::= { mbusA8 81 }

mbusA8VIF26		OBJECT-TYPE
			SYNTAX	INTEGER
			ACCESS	read-only
			STATUS	current
	DESCRIPTION ""
			::= { mbusA8 82 }

mbusA8Value26		OBJECT-TYPE
			SYNTAX	INTEGER
			ACCESS	read-only
			STATUS	current
	DESCRIPTION ""
			::= { mbusA8 83 }

mbusA8VIF27		OBJECT-TYPE
			SYNTAX	INTEGER
			ACCESS	read-only
			STATUS	current
	DESCRIPTION ""
			::= { mbusA8 84 }

mbusA8Value27		OBJECT-TYPE
			SYNTAX	INTEGER
			ACCESS	read-only
			STATUS	current
	DESCRIPTION ""
			::= { mbusA8 85 }

mbusA8VIF28		OBJECT-TYPE
			SYNTAX	INTEGER
			ACCESS	read-only
			STATUS	current
	DESCRIPTION ""
			::= { mbusA8 86 }

mbusA8Value28		OBJECT-TYPE
			SYNTAX	INTEGER
			ACCESS	read-only
			STATUS	current
	DESCRIPTION ""
			::= { mbusA8 87 }

mbusA8VIF29		OBJECT-TYPE
			SYNTAX	INTEGER
			ACCESS	read-only
			STATUS	current
	DESCRIPTION ""
			::= { mbusA8 88 }

mbusA8Value29		OBJECT-TYPE
			SYNTAX	INTEGER
			ACCESS	read-only
			STATUS	current
	DESCRIPTION ""
			::= { mbusA8 89 }

mbusA8VIF2A		OBJECT-TYPE
			SYNTAX	INTEGER
			ACCESS	read-only
			STATUS	current
	DESCRIPTION ""
			::= { mbusA8 90 }

mbusA8Value2A		OBJECT-TYPE
			SYNTAX	INTEGER
			ACCESS	read-only
			STATUS	current
	DESCRIPTION ""
			::= { mbusA8 91 }

mbusA8VIF2B		OBJECT-TYPE
			SYNTAX	INTEGER
			ACCESS	read-only
			STATUS	current
	DESCRIPTION ""
			::= { mbusA8 92 }

mbusA8Value2B		OBJECT-TYPE
			SYNTAX	INTEGER
			ACCESS	read-only
			STATUS	current
	DESCRIPTION ""
			::= { mbusA8 93 }

mbusA8VIF2C		OBJECT-TYPE
			SYNTAX	INTEGER
			ACCESS	read-only
			STATUS	current
	DESCRIPTION ""
			::= { mbusA8 94 }

mbusA8Value2C		OBJECT-TYPE
			SYNTAX	INTEGER
			ACCESS	read-only
			STATUS	current
	DESCRIPTION ""
			::= { mbusA8 95 }

mbusA8VIF2D		OBJECT-TYPE
			SYNTAX	INTEGER
			ACCESS	read-only
			STATUS	current
	DESCRIPTION ""
			::= { mbusA8 96 }

mbusA8Value2D		OBJECT-TYPE
			SYNTAX	INTEGER
			ACCESS	read-only
			STATUS	current
	DESCRIPTION ""
			::= { mbusA8 97 }

mbusA8VIF2E		OBJECT-TYPE
			SYNTAX	INTEGER
			ACCESS	read-only
			STATUS	current
	DESCRIPTION ""
			::= { mbusA8 98 }

mbusA8Value2E		OBJECT-TYPE
			SYNTAX	INTEGER
			ACCESS	read-only
			STATUS	current
	DESCRIPTION ""
			::= { mbusA8 99 }

mbusA8VIF2F		OBJECT-TYPE
			SYNTAX	INTEGER
			ACCESS	read-only
			STATUS	current
	DESCRIPTION ""
			::= { mbusA8 100 }

mbusA8Value2F		OBJECT-TYPE
			SYNTAX	INTEGER
			ACCESS	read-only
			STATUS	current
	DESCRIPTION ""
			::= { mbusA8 101 }

mbusA9			OBJECT IDENTIFIER ::= { mbus 169 }

mbusA9IdNumber		OBJECT-TYPE
			SYNTAX	Gauge
			ACCESS	read-only
			STATUS	current
	DESCRIPTION ""
			::= { mbusA9 1 }

mbusA9Manufacturer	OBJECT-TYPE
			SYNTAX	Gauge
			ACCESS	read-only
			STATUS	current
	DESCRIPTION ""
			::= { mbusA9 2 }

mbusA9Version		OBJECT-TYPE
			SYNTAX	Gauge
			ACCESS	read-only
			STATUS	current
	DESCRIPTION ""
			::= { mbusA9 3 }

mbusA9Medium		OBJECT-TYPE
			SYNTAX	Gauge
			ACCESS	read-only
			STATUS	current
	DESCRIPTION ""
			::= { mbusA9 4 }

mbusA9Status		OBJECT-TYPE
			SYNTAX	Gauge
			ACCESS	read-only
			STATUS	current
	DESCRIPTION ""
			::= { mbusA9 5 }

mbusA9VIF00		OBJECT-TYPE
			SYNTAX	INTEGER
			ACCESS	read-only
			STATUS	current
	DESCRIPTION ""
			::= { mbusA9 6 }

mbusA9Value00		OBJECT-TYPE
			SYNTAX	INTEGER
			ACCESS	read-only
			STATUS	current
	DESCRIPTION ""
			::= { mbusA9 7 }

mbusA9VIF01		OBJECT-TYPE
			SYNTAX	INTEGER
			ACCESS	read-only
			STATUS	current
	DESCRIPTION ""
			::= { mbusA9 8 }

mbusA9Value01		OBJECT-TYPE
			SYNTAX	INTEGER
			ACCESS	read-only
			STATUS	current
	DESCRIPTION ""
			::= { mbusA9 9 }

mbusA9VIF02		OBJECT-TYPE
			SYNTAX	INTEGER
			ACCESS	read-only
			STATUS	current
	DESCRIPTION ""
			::= { mbusA9 10 }

mbusA9Value02		OBJECT-TYPE
			SYNTAX	INTEGER
			ACCESS	read-only
			STATUS	current
	DESCRIPTION ""
			::= { mbusA9 11 }

mbusA9VIF03		OBJECT-TYPE
			SYNTAX	INTEGER
			ACCESS	read-only
			STATUS	current
	DESCRIPTION ""
			::= { mbusA9 12 }

mbusA9Value03		OBJECT-TYPE
			SYNTAX	INTEGER
			ACCESS	read-only
			STATUS	current
	DESCRIPTION ""
			::= { mbusA9 13 }

mbusA9VIF04		OBJECT-TYPE
			SYNTAX	INTEGER
			ACCESS	read-only
			STATUS	current
	DESCRIPTION ""
			::= { mbusA9 14 }

mbusA9Value04		OBJECT-TYPE
			SYNTAX	INTEGER
			ACCESS	read-only
			STATUS	current
	DESCRIPTION ""
			::= { mbusA9 15 }

mbusA9VIF05		OBJECT-TYPE
			SYNTAX	INTEGER
			ACCESS	read-only
			STATUS	current
	DESCRIPTION ""
			::= { mbusA9 16 }

mbusA9Value05		OBJECT-TYPE
			SYNTAX	INTEGER
			ACCESS	read-only
			STATUS	current
	DESCRIPTION ""
			::= { mbusA9 17 }

mbusA9VIF06		OBJECT-TYPE
			SYNTAX	INTEGER
			ACCESS	read-only
			STATUS	current
	DESCRIPTION ""
			::= { mbusA9 18 }

mbusA9Value06		OBJECT-TYPE
			SYNTAX	INTEGER
			ACCESS	read-only
			STATUS	current
	DESCRIPTION ""
			::= { mbusA9 19 }

mbusA9VIF07		OBJECT-TYPE
			SYNTAX	INTEGER
			ACCESS	read-only
			STATUS	current
	DESCRIPTION ""
			::= { mbusA9 20 }

mbusA9Value07		OBJECT-TYPE
			SYNTAX	INTEGER
			ACCESS	read-only
			STATUS	current
	DESCRIPTION ""
			::= { mbusA9 21 }

mbusA9VIF08		OBJECT-TYPE
			SYNTAX	INTEGER
			ACCESS	read-only
			STATUS	current
	DESCRIPTION ""
			::= { mbusA9 22 }

mbusA9Value08		OBJECT-TYPE
			SYNTAX	INTEGER
			ACCESS	read-only
			STATUS	current
	DESCRIPTION ""
			::= { mbusA9 23 }

mbusA9VIF09		OBJECT-TYPE
			SYNTAX	INTEGER
			ACCESS	read-only
			STATUS	current
	DESCRIPTION ""
			::= { mbusA9 24 }

mbusA9Value09		OBJECT-TYPE
			SYNTAX	INTEGER
			ACCESS	read-only
			STATUS	current
	DESCRIPTION ""
			::= { mbusA9 25 }

mbusA9VIF0A		OBJECT-TYPE
			SYNTAX	INTEGER
			ACCESS	read-only
			STATUS	current
	DESCRIPTION ""
			::= { mbusA9 26 }

mbusA9Value0A		OBJECT-TYPE
			SYNTAX	INTEGER
			ACCESS	read-only
			STATUS	current
	DESCRIPTION ""
			::= { mbusA9 27 }

mbusA9VIF0B		OBJECT-TYPE
			SYNTAX	INTEGER
			ACCESS	read-only
			STATUS	current
	DESCRIPTION ""
			::= { mbusA9 28 }

mbusA9Value0B		OBJECT-TYPE
			SYNTAX	INTEGER
			ACCESS	read-only
			STATUS	current
	DESCRIPTION ""
			::= { mbusA9 29 }

mbusA9VIF0C		OBJECT-TYPE
			SYNTAX	INTEGER
			ACCESS	read-only
			STATUS	current
	DESCRIPTION ""
			::= { mbusA9 30 }

mbusA9Value0C		OBJECT-TYPE
			SYNTAX	INTEGER
			ACCESS	read-only
			STATUS	current
	DESCRIPTION ""
			::= { mbusA9 31 }

mbusA9VIF0D		OBJECT-TYPE
			SYNTAX	INTEGER
			ACCESS	read-only
			STATUS	current
	DESCRIPTION ""
			::= { mbusA9 32 }

mbusA9Value0D		OBJECT-TYPE
			SYNTAX	INTEGER
			ACCESS	read-only
			STATUS	current
	DESCRIPTION ""
			::= { mbusA9 33 }

mbusA9VIF0E		OBJECT-TYPE
			SYNTAX	INTEGER
			ACCESS	read-only
			STATUS	current
	DESCRIPTION ""
			::= { mbusA9 34 }

mbusA9Value0E		OBJECT-TYPE
			SYNTAX	INTEGER
			ACCESS	read-only
			STATUS	current
	DESCRIPTION ""
			::= { mbusA9 35 }

mbusA9VIF0F		OBJECT-TYPE
			SYNTAX	INTEGER
			ACCESS	read-only
			STATUS	current
	DESCRIPTION ""
			::= { mbusA9 36 }

mbusA9Value0F		OBJECT-TYPE
			SYNTAX	INTEGER
			ACCESS	read-only
			STATUS	current
	DESCRIPTION ""
			::= { mbusA9 37 }

mbusA9VIF10		OBJECT-TYPE
			SYNTAX	INTEGER
			ACCESS	read-only
			STATUS	current
	DESCRIPTION ""
			::= { mbusA9 38 }

mbusA9Value10		OBJECT-TYPE
			SYNTAX	INTEGER
			ACCESS	read-only
			STATUS	current
	DESCRIPTION ""
			::= { mbusA9 39 }

mbusA9VIF11		OBJECT-TYPE
			SYNTAX	INTEGER
			ACCESS	read-only
			STATUS	current
	DESCRIPTION ""
			::= { mbusA9 40 }

mbusA9Value11		OBJECT-TYPE
			SYNTAX	INTEGER
			ACCESS	read-only
			STATUS	current
	DESCRIPTION ""
			::= { mbusA9 41 }

mbusA9VIF12		OBJECT-TYPE
			SYNTAX	INTEGER
			ACCESS	read-only
			STATUS	current
	DESCRIPTION ""
			::= { mbusA9 42 }

mbusA9Value12		OBJECT-TYPE
			SYNTAX	INTEGER
			ACCESS	read-only
			STATUS	current
	DESCRIPTION ""
			::= { mbusA9 43 }

mbusA9VIF13		OBJECT-TYPE
			SYNTAX	INTEGER
			ACCESS	read-only
			STATUS	current
	DESCRIPTION ""
			::= { mbusA9 44 }

mbusA9Value13		OBJECT-TYPE
			SYNTAX	INTEGER
			ACCESS	read-only
			STATUS	current
	DESCRIPTION ""
			::= { mbusA9 45 }

mbusA9VIF14		OBJECT-TYPE
			SYNTAX	INTEGER
			ACCESS	read-only
			STATUS	current
	DESCRIPTION ""
			::= { mbusA9 46 }

mbusA9Value14		OBJECT-TYPE
			SYNTAX	INTEGER
			ACCESS	read-only
			STATUS	current
	DESCRIPTION ""
			::= { mbusA9 47 }

mbusA9VIF15		OBJECT-TYPE
			SYNTAX	INTEGER
			ACCESS	read-only
			STATUS	current
	DESCRIPTION ""
			::= { mbusA9 48 }

mbusA9Value15		OBJECT-TYPE
			SYNTAX	INTEGER
			ACCESS	read-only
			STATUS	current
	DESCRIPTION ""
			::= { mbusA9 49 }

mbusA9VIF16		OBJECT-TYPE
			SYNTAX	INTEGER
			ACCESS	read-only
			STATUS	current
	DESCRIPTION ""
			::= { mbusA9 50 }

mbusA9Value16		OBJECT-TYPE
			SYNTAX	INTEGER
			ACCESS	read-only
			STATUS	current
	DESCRIPTION ""
			::= { mbusA9 51 }

mbusA9VIF17		OBJECT-TYPE
			SYNTAX	INTEGER
			ACCESS	read-only
			STATUS	current
	DESCRIPTION ""
			::= { mbusA9 52 }

mbusA9Value17		OBJECT-TYPE
			SYNTAX	INTEGER
			ACCESS	read-only
			STATUS	current
	DESCRIPTION ""
			::= { mbusA9 53 }

mbusA9VIF18		OBJECT-TYPE
			SYNTAX	INTEGER
			ACCESS	read-only
			STATUS	current
	DESCRIPTION ""
			::= { mbusA9 54 }

mbusA9Value18		OBJECT-TYPE
			SYNTAX	INTEGER
			ACCESS	read-only
			STATUS	current
	DESCRIPTION ""
			::= { mbusA9 55 }

mbusA9VIF19		OBJECT-TYPE
			SYNTAX	INTEGER
			ACCESS	read-only
			STATUS	current
	DESCRIPTION ""
			::= { mbusA9 56 }

mbusA9Value19		OBJECT-TYPE
			SYNTAX	INTEGER
			ACCESS	read-only
			STATUS	current
	DESCRIPTION ""
			::= { mbusA9 57 }

mbusA9VIF1A		OBJECT-TYPE
			SYNTAX	INTEGER
			ACCESS	read-only
			STATUS	current
	DESCRIPTION ""
			::= { mbusA9 58 }

mbusA9Value1A		OBJECT-TYPE
			SYNTAX	INTEGER
			ACCESS	read-only
			STATUS	current
	DESCRIPTION ""
			::= { mbusA9 59 }

mbusA9VIF1B		OBJECT-TYPE
			SYNTAX	INTEGER
			ACCESS	read-only
			STATUS	current
	DESCRIPTION ""
			::= { mbusA9 60 }

mbusA9Value1B		OBJECT-TYPE
			SYNTAX	INTEGER
			ACCESS	read-only
			STATUS	current
	DESCRIPTION ""
			::= { mbusA9 61 }

mbusA9VIF1C		OBJECT-TYPE
			SYNTAX	INTEGER
			ACCESS	read-only
			STATUS	current
	DESCRIPTION ""
			::= { mbusA9 62 }

mbusA9Value1C		OBJECT-TYPE
			SYNTAX	INTEGER
			ACCESS	read-only
			STATUS	current
	DESCRIPTION ""
			::= { mbusA9 63 }

mbusA9VIF1D		OBJECT-TYPE
			SYNTAX	INTEGER
			ACCESS	read-only
			STATUS	current
	DESCRIPTION ""
			::= { mbusA9 64 }

mbusA9Value1D		OBJECT-TYPE
			SYNTAX	INTEGER
			ACCESS	read-only
			STATUS	current
	DESCRIPTION ""
			::= { mbusA9 65 }

mbusA9VIF1E		OBJECT-TYPE
			SYNTAX	INTEGER
			ACCESS	read-only
			STATUS	current
	DESCRIPTION ""
			::= { mbusA9 66 }

mbusA9Value1E		OBJECT-TYPE
			SYNTAX	INTEGER
			ACCESS	read-only
			STATUS	current
	DESCRIPTION ""
			::= { mbusA9 67 }

mbusA9VIF1F		OBJECT-TYPE
			SYNTAX	INTEGER
			ACCESS	read-only
			STATUS	current
	DESCRIPTION ""
			::= { mbusA9 68 }

mbusA9Value1F		OBJECT-TYPE
			SYNTAX	INTEGER
			ACCESS	read-only
			STATUS	current
	DESCRIPTION ""
			::= { mbusA9 69 }

mbusA9VIF20		OBJECT-TYPE
			SYNTAX	INTEGER
			ACCESS	read-only
			STATUS	current
	DESCRIPTION ""
			::= { mbusA9 70 }

mbusA9Value20		OBJECT-TYPE
			SYNTAX	INTEGER
			ACCESS	read-only
			STATUS	current
	DESCRIPTION ""
			::= { mbusA9 71 }

mbusA9VIF21		OBJECT-TYPE
			SYNTAX	INTEGER
			ACCESS	read-only
			STATUS	current
	DESCRIPTION ""
			::= { mbusA9 72 }

mbusA9Value21		OBJECT-TYPE
			SYNTAX	INTEGER
			ACCESS	read-only
			STATUS	current
	DESCRIPTION ""
			::= { mbusA9 73 }

mbusA9VIF22		OBJECT-TYPE
			SYNTAX	INTEGER
			ACCESS	read-only
			STATUS	current
	DESCRIPTION ""
			::= { mbusA9 74 }

mbusA9Value22		OBJECT-TYPE
			SYNTAX	INTEGER
			ACCESS	read-only
			STATUS	current
	DESCRIPTION ""
			::= { mbusA9 75 }

mbusA9VIF23		OBJECT-TYPE
			SYNTAX	INTEGER
			ACCESS	read-only
			STATUS	current
	DESCRIPTION ""
			::= { mbusA9 76 }

mbusA9Value23		OBJECT-TYPE
			SYNTAX	INTEGER
			ACCESS	read-only
			STATUS	current
	DESCRIPTION ""
			::= { mbusA9 77 }

mbusA9VIF24		OBJECT-TYPE
			SYNTAX	INTEGER
			ACCESS	read-only
			STATUS	current
	DESCRIPTION ""
			::= { mbusA9 78 }

mbusA9Value24		OBJECT-TYPE
			SYNTAX	INTEGER
			ACCESS	read-only
			STATUS	current
	DESCRIPTION ""
			::= { mbusA9 79 }

mbusA9VIF25		OBJECT-TYPE
			SYNTAX	INTEGER
			ACCESS	read-only
			STATUS	current
	DESCRIPTION ""
			::= { mbusA9 80 }

mbusA9Value25		OBJECT-TYPE
			SYNTAX	INTEGER
			ACCESS	read-only
			STATUS	current
	DESCRIPTION ""
			::= { mbusA9 81 }

mbusA9VIF26		OBJECT-TYPE
			SYNTAX	INTEGER
			ACCESS	read-only
			STATUS	current
	DESCRIPTION ""
			::= { mbusA9 82 }

mbusA9Value26		OBJECT-TYPE
			SYNTAX	INTEGER
			ACCESS	read-only
			STATUS	current
	DESCRIPTION ""
			::= { mbusA9 83 }

mbusA9VIF27		OBJECT-TYPE
			SYNTAX	INTEGER
			ACCESS	read-only
			STATUS	current
	DESCRIPTION ""
			::= { mbusA9 84 }

mbusA9Value27		OBJECT-TYPE
			SYNTAX	INTEGER
			ACCESS	read-only
			STATUS	current
	DESCRIPTION ""
			::= { mbusA9 85 }

mbusA9VIF28		OBJECT-TYPE
			SYNTAX	INTEGER
			ACCESS	read-only
			STATUS	current
	DESCRIPTION ""
			::= { mbusA9 86 }

mbusA9Value28		OBJECT-TYPE
			SYNTAX	INTEGER
			ACCESS	read-only
			STATUS	current
	DESCRIPTION ""
			::= { mbusA9 87 }

mbusA9VIF29		OBJECT-TYPE
			SYNTAX	INTEGER
			ACCESS	read-only
			STATUS	current
	DESCRIPTION ""
			::= { mbusA9 88 }

mbusA9Value29		OBJECT-TYPE
			SYNTAX	INTEGER
			ACCESS	read-only
			STATUS	current
	DESCRIPTION ""
			::= { mbusA9 89 }

mbusA9VIF2A		OBJECT-TYPE
			SYNTAX	INTEGER
			ACCESS	read-only
			STATUS	current
	DESCRIPTION ""
			::= { mbusA9 90 }

mbusA9Value2A		OBJECT-TYPE
			SYNTAX	INTEGER
			ACCESS	read-only
			STATUS	current
	DESCRIPTION ""
			::= { mbusA9 91 }

mbusA9VIF2B		OBJECT-TYPE
			SYNTAX	INTEGER
			ACCESS	read-only
			STATUS	current
	DESCRIPTION ""
			::= { mbusA9 92 }

mbusA9Value2B		OBJECT-TYPE
			SYNTAX	INTEGER
			ACCESS	read-only
			STATUS	current
	DESCRIPTION ""
			::= { mbusA9 93 }

mbusA9VIF2C		OBJECT-TYPE
			SYNTAX	INTEGER
			ACCESS	read-only
			STATUS	current
	DESCRIPTION ""
			::= { mbusA9 94 }

mbusA9Value2C		OBJECT-TYPE
			SYNTAX	INTEGER
			ACCESS	read-only
			STATUS	current
	DESCRIPTION ""
			::= { mbusA9 95 }

mbusA9VIF2D		OBJECT-TYPE
			SYNTAX	INTEGER
			ACCESS	read-only
			STATUS	current
	DESCRIPTION ""
			::= { mbusA9 96 }

mbusA9Value2D		OBJECT-TYPE
			SYNTAX	INTEGER
			ACCESS	read-only
			STATUS	current
	DESCRIPTION ""
			::= { mbusA9 97 }

mbusA9VIF2E		OBJECT-TYPE
			SYNTAX	INTEGER
			ACCESS	read-only
			STATUS	current
	DESCRIPTION ""
			::= { mbusA9 98 }

mbusA9Value2E		OBJECT-TYPE
			SYNTAX	INTEGER
			ACCESS	read-only
			STATUS	current
	DESCRIPTION ""
			::= { mbusA9 99 }

mbusA9VIF2F		OBJECT-TYPE
			SYNTAX	INTEGER
			ACCESS	read-only
			STATUS	current
	DESCRIPTION ""
			::= { mbusA9 100 }

mbusA9Value2F		OBJECT-TYPE
			SYNTAX	INTEGER
			ACCESS	read-only
			STATUS	current
	DESCRIPTION ""
			::= { mbusA9 101 }

mbusAA			OBJECT IDENTIFIER ::= { mbus 170 }

mbusAAIdNumber		OBJECT-TYPE
			SYNTAX	Gauge
			ACCESS	read-only
			STATUS	current
	DESCRIPTION ""
			::= { mbusAA 1 }

mbusAAManufacturer	OBJECT-TYPE
			SYNTAX	Gauge
			ACCESS	read-only
			STATUS	current
	DESCRIPTION ""
			::= { mbusAA 2 }

mbusAAVersion		OBJECT-TYPE
			SYNTAX	Gauge
			ACCESS	read-only
			STATUS	current
	DESCRIPTION ""
			::= { mbusAA 3 }

mbusAAMedium		OBJECT-TYPE
			SYNTAX	Gauge
			ACCESS	read-only
			STATUS	current
	DESCRIPTION ""
			::= { mbusAA 4 }

mbusAAStatus		OBJECT-TYPE
			SYNTAX	Gauge
			ACCESS	read-only
			STATUS	current
	DESCRIPTION ""
			::= { mbusAA 5 }

mbusAAVIF00		OBJECT-TYPE
			SYNTAX	INTEGER
			ACCESS	read-only
			STATUS	current
	DESCRIPTION ""
			::= { mbusAA 6 }

mbusAAValue00		OBJECT-TYPE
			SYNTAX	INTEGER
			ACCESS	read-only
			STATUS	current
	DESCRIPTION ""
			::= { mbusAA 7 }

mbusAAVIF01		OBJECT-TYPE
			SYNTAX	INTEGER
			ACCESS	read-only
			STATUS	current
	DESCRIPTION ""
			::= { mbusAA 8 }

mbusAAValue01		OBJECT-TYPE
			SYNTAX	INTEGER
			ACCESS	read-only
			STATUS	current
	DESCRIPTION ""
			::= { mbusAA 9 }

mbusAAVIF02		OBJECT-TYPE
			SYNTAX	INTEGER
			ACCESS	read-only
			STATUS	current
	DESCRIPTION ""
			::= { mbusAA 10 }

mbusAAValue02		OBJECT-TYPE
			SYNTAX	INTEGER
			ACCESS	read-only
			STATUS	current
	DESCRIPTION ""
			::= { mbusAA 11 }

mbusAAVIF03		OBJECT-TYPE
			SYNTAX	INTEGER
			ACCESS	read-only
			STATUS	current
	DESCRIPTION ""
			::= { mbusAA 12 }

mbusAAValue03		OBJECT-TYPE
			SYNTAX	INTEGER
			ACCESS	read-only
			STATUS	current
	DESCRIPTION ""
			::= { mbusAA 13 }

mbusAAVIF04		OBJECT-TYPE
			SYNTAX	INTEGER
			ACCESS	read-only
			STATUS	current
	DESCRIPTION ""
			::= { mbusAA 14 }

mbusAAValue04		OBJECT-TYPE
			SYNTAX	INTEGER
			ACCESS	read-only
			STATUS	current
	DESCRIPTION ""
			::= { mbusAA 15 }

mbusAAVIF05		OBJECT-TYPE
			SYNTAX	INTEGER
			ACCESS	read-only
			STATUS	current
	DESCRIPTION ""
			::= { mbusAA 16 }

mbusAAValue05		OBJECT-TYPE
			SYNTAX	INTEGER
			ACCESS	read-only
			STATUS	current
	DESCRIPTION ""
			::= { mbusAA 17 }

mbusAAVIF06		OBJECT-TYPE
			SYNTAX	INTEGER
			ACCESS	read-only
			STATUS	current
	DESCRIPTION ""
			::= { mbusAA 18 }

mbusAAValue06		OBJECT-TYPE
			SYNTAX	INTEGER
			ACCESS	read-only
			STATUS	current
	DESCRIPTION ""
			::= { mbusAA 19 }

mbusAAVIF07		OBJECT-TYPE
			SYNTAX	INTEGER
			ACCESS	read-only
			STATUS	current
	DESCRIPTION ""
			::= { mbusAA 20 }

mbusAAValue07		OBJECT-TYPE
			SYNTAX	INTEGER
			ACCESS	read-only
			STATUS	current
	DESCRIPTION ""
			::= { mbusAA 21 }

mbusAAVIF08		OBJECT-TYPE
			SYNTAX	INTEGER
			ACCESS	read-only
			STATUS	current
	DESCRIPTION ""
			::= { mbusAA 22 }

mbusAAValue08		OBJECT-TYPE
			SYNTAX	INTEGER
			ACCESS	read-only
			STATUS	current
	DESCRIPTION ""
			::= { mbusAA 23 }

mbusAAVIF09		OBJECT-TYPE
			SYNTAX	INTEGER
			ACCESS	read-only
			STATUS	current
	DESCRIPTION ""
			::= { mbusAA 24 }

mbusAAValue09		OBJECT-TYPE
			SYNTAX	INTEGER
			ACCESS	read-only
			STATUS	current
	DESCRIPTION ""
			::= { mbusAA 25 }

mbusAAVIF0A		OBJECT-TYPE
			SYNTAX	INTEGER
			ACCESS	read-only
			STATUS	current
	DESCRIPTION ""
			::= { mbusAA 26 }

mbusAAValue0A		OBJECT-TYPE
			SYNTAX	INTEGER
			ACCESS	read-only
			STATUS	current
	DESCRIPTION ""
			::= { mbusAA 27 }

mbusAAVIF0B		OBJECT-TYPE
			SYNTAX	INTEGER
			ACCESS	read-only
			STATUS	current
	DESCRIPTION ""
			::= { mbusAA 28 }

mbusAAValue0B		OBJECT-TYPE
			SYNTAX	INTEGER
			ACCESS	read-only
			STATUS	current
	DESCRIPTION ""
			::= { mbusAA 29 }

mbusAAVIF0C		OBJECT-TYPE
			SYNTAX	INTEGER
			ACCESS	read-only
			STATUS	current
	DESCRIPTION ""
			::= { mbusAA 30 }

mbusAAValue0C		OBJECT-TYPE
			SYNTAX	INTEGER
			ACCESS	read-only
			STATUS	current
	DESCRIPTION ""
			::= { mbusAA 31 }

mbusAAVIF0D		OBJECT-TYPE
			SYNTAX	INTEGER
			ACCESS	read-only
			STATUS	current
	DESCRIPTION ""
			::= { mbusAA 32 }

mbusAAValue0D		OBJECT-TYPE
			SYNTAX	INTEGER
			ACCESS	read-only
			STATUS	current
	DESCRIPTION ""
			::= { mbusAA 33 }

mbusAAVIF0E		OBJECT-TYPE
			SYNTAX	INTEGER
			ACCESS	read-only
			STATUS	current
	DESCRIPTION ""
			::= { mbusAA 34 }

mbusAAValue0E		OBJECT-TYPE
			SYNTAX	INTEGER
			ACCESS	read-only
			STATUS	current
	DESCRIPTION ""
			::= { mbusAA 35 }

mbusAAVIF0F		OBJECT-TYPE
			SYNTAX	INTEGER
			ACCESS	read-only
			STATUS	current
	DESCRIPTION ""
			::= { mbusAA 36 }

mbusAAValue0F		OBJECT-TYPE
			SYNTAX	INTEGER
			ACCESS	read-only
			STATUS	current
	DESCRIPTION ""
			::= { mbusAA 37 }

mbusAAVIF10		OBJECT-TYPE
			SYNTAX	INTEGER
			ACCESS	read-only
			STATUS	current
	DESCRIPTION ""
			::= { mbusAA 38 }

mbusAAValue10		OBJECT-TYPE
			SYNTAX	INTEGER
			ACCESS	read-only
			STATUS	current
	DESCRIPTION ""
			::= { mbusAA 39 }

mbusAAVIF11		OBJECT-TYPE
			SYNTAX	INTEGER
			ACCESS	read-only
			STATUS	current
	DESCRIPTION ""
			::= { mbusAA 40 }

mbusAAValue11		OBJECT-TYPE
			SYNTAX	INTEGER
			ACCESS	read-only
			STATUS	current
	DESCRIPTION ""
			::= { mbusAA 41 }

mbusAAVIF12		OBJECT-TYPE
			SYNTAX	INTEGER
			ACCESS	read-only
			STATUS	current
	DESCRIPTION ""
			::= { mbusAA 42 }

mbusAAValue12		OBJECT-TYPE
			SYNTAX	INTEGER
			ACCESS	read-only
			STATUS	current
	DESCRIPTION ""
			::= { mbusAA 43 }

mbusAAVIF13		OBJECT-TYPE
			SYNTAX	INTEGER
			ACCESS	read-only
			STATUS	current
	DESCRIPTION ""
			::= { mbusAA 44 }

mbusAAValue13		OBJECT-TYPE
			SYNTAX	INTEGER
			ACCESS	read-only
			STATUS	current
	DESCRIPTION ""
			::= { mbusAA 45 }

mbusAAVIF14		OBJECT-TYPE
			SYNTAX	INTEGER
			ACCESS	read-only
			STATUS	current
	DESCRIPTION ""
			::= { mbusAA 46 }

mbusAAValue14		OBJECT-TYPE
			SYNTAX	INTEGER
			ACCESS	read-only
			STATUS	current
	DESCRIPTION ""
			::= { mbusAA 47 }

mbusAAVIF15		OBJECT-TYPE
			SYNTAX	INTEGER
			ACCESS	read-only
			STATUS	current
	DESCRIPTION ""
			::= { mbusAA 48 }

mbusAAValue15		OBJECT-TYPE
			SYNTAX	INTEGER
			ACCESS	read-only
			STATUS	current
	DESCRIPTION ""
			::= { mbusAA 49 }

mbusAAVIF16		OBJECT-TYPE
			SYNTAX	INTEGER
			ACCESS	read-only
			STATUS	current
	DESCRIPTION ""
			::= { mbusAA 50 }

mbusAAValue16		OBJECT-TYPE
			SYNTAX	INTEGER
			ACCESS	read-only
			STATUS	current
	DESCRIPTION ""
			::= { mbusAA 51 }

mbusAAVIF17		OBJECT-TYPE
			SYNTAX	INTEGER
			ACCESS	read-only
			STATUS	current
	DESCRIPTION ""
			::= { mbusAA 52 }

mbusAAValue17		OBJECT-TYPE
			SYNTAX	INTEGER
			ACCESS	read-only
			STATUS	current
	DESCRIPTION ""
			::= { mbusAA 53 }

mbusAAVIF18		OBJECT-TYPE
			SYNTAX	INTEGER
			ACCESS	read-only
			STATUS	current
	DESCRIPTION ""
			::= { mbusAA 54 }

mbusAAValue18		OBJECT-TYPE
			SYNTAX	INTEGER
			ACCESS	read-only
			STATUS	current
	DESCRIPTION ""
			::= { mbusAA 55 }

mbusAAVIF19		OBJECT-TYPE
			SYNTAX	INTEGER
			ACCESS	read-only
			STATUS	current
	DESCRIPTION ""
			::= { mbusAA 56 }

mbusAAValue19		OBJECT-TYPE
			SYNTAX	INTEGER
			ACCESS	read-only
			STATUS	current
	DESCRIPTION ""
			::= { mbusAA 57 }

mbusAAVIF1A		OBJECT-TYPE
			SYNTAX	INTEGER
			ACCESS	read-only
			STATUS	current
	DESCRIPTION ""
			::= { mbusAA 58 }

mbusAAValue1A		OBJECT-TYPE
			SYNTAX	INTEGER
			ACCESS	read-only
			STATUS	current
	DESCRIPTION ""
			::= { mbusAA 59 }

mbusAAVIF1B		OBJECT-TYPE
			SYNTAX	INTEGER
			ACCESS	read-only
			STATUS	current
	DESCRIPTION ""
			::= { mbusAA 60 }

mbusAAValue1B		OBJECT-TYPE
			SYNTAX	INTEGER
			ACCESS	read-only
			STATUS	current
	DESCRIPTION ""
			::= { mbusAA 61 }

mbusAAVIF1C		OBJECT-TYPE
			SYNTAX	INTEGER
			ACCESS	read-only
			STATUS	current
	DESCRIPTION ""
			::= { mbusAA 62 }

mbusAAValue1C		OBJECT-TYPE
			SYNTAX	INTEGER
			ACCESS	read-only
			STATUS	current
	DESCRIPTION ""
			::= { mbusAA 63 }

mbusAAVIF1D		OBJECT-TYPE
			SYNTAX	INTEGER
			ACCESS	read-only
			STATUS	current
	DESCRIPTION ""
			::= { mbusAA 64 }

mbusAAValue1D		OBJECT-TYPE
			SYNTAX	INTEGER
			ACCESS	read-only
			STATUS	current
	DESCRIPTION ""
			::= { mbusAA 65 }

mbusAAVIF1E		OBJECT-TYPE
			SYNTAX	INTEGER
			ACCESS	read-only
			STATUS	current
	DESCRIPTION ""
			::= { mbusAA 66 }

mbusAAValue1E		OBJECT-TYPE
			SYNTAX	INTEGER
			ACCESS	read-only
			STATUS	current
	DESCRIPTION ""
			::= { mbusAA 67 }

mbusAAVIF1F		OBJECT-TYPE
			SYNTAX	INTEGER
			ACCESS	read-only
			STATUS	current
	DESCRIPTION ""
			::= { mbusAA 68 }

mbusAAValue1F		OBJECT-TYPE
			SYNTAX	INTEGER
			ACCESS	read-only
			STATUS	current
	DESCRIPTION ""
			::= { mbusAA 69 }

mbusAAVIF20		OBJECT-TYPE
			SYNTAX	INTEGER
			ACCESS	read-only
			STATUS	current
	DESCRIPTION ""
			::= { mbusAA 70 }

mbusAAValue20		OBJECT-TYPE
			SYNTAX	INTEGER
			ACCESS	read-only
			STATUS	current
	DESCRIPTION ""
			::= { mbusAA 71 }

mbusAAVIF21		OBJECT-TYPE
			SYNTAX	INTEGER
			ACCESS	read-only
			STATUS	current
	DESCRIPTION ""
			::= { mbusAA 72 }

mbusAAValue21		OBJECT-TYPE
			SYNTAX	INTEGER
			ACCESS	read-only
			STATUS	current
	DESCRIPTION ""
			::= { mbusAA 73 }

mbusAAVIF22		OBJECT-TYPE
			SYNTAX	INTEGER
			ACCESS	read-only
			STATUS	current
	DESCRIPTION ""
			::= { mbusAA 74 }

mbusAAValue22		OBJECT-TYPE
			SYNTAX	INTEGER
			ACCESS	read-only
			STATUS	current
	DESCRIPTION ""
			::= { mbusAA 75 }

mbusAAVIF23		OBJECT-TYPE
			SYNTAX	INTEGER
			ACCESS	read-only
			STATUS	current
	DESCRIPTION ""
			::= { mbusAA 76 }

mbusAAValue23		OBJECT-TYPE
			SYNTAX	INTEGER
			ACCESS	read-only
			STATUS	current
	DESCRIPTION ""
			::= { mbusAA 77 }

mbusAAVIF24		OBJECT-TYPE
			SYNTAX	INTEGER
			ACCESS	read-only
			STATUS	current
	DESCRIPTION ""
			::= { mbusAA 78 }

mbusAAValue24		OBJECT-TYPE
			SYNTAX	INTEGER
			ACCESS	read-only
			STATUS	current
	DESCRIPTION ""
			::= { mbusAA 79 }

mbusAAVIF25		OBJECT-TYPE
			SYNTAX	INTEGER
			ACCESS	read-only
			STATUS	current
	DESCRIPTION ""
			::= { mbusAA 80 }

mbusAAValue25		OBJECT-TYPE
			SYNTAX	INTEGER
			ACCESS	read-only
			STATUS	current
	DESCRIPTION ""
			::= { mbusAA 81 }

mbusAAVIF26		OBJECT-TYPE
			SYNTAX	INTEGER
			ACCESS	read-only
			STATUS	current
	DESCRIPTION ""
			::= { mbusAA 82 }

mbusAAValue26		OBJECT-TYPE
			SYNTAX	INTEGER
			ACCESS	read-only
			STATUS	current
	DESCRIPTION ""
			::= { mbusAA 83 }

mbusAAVIF27		OBJECT-TYPE
			SYNTAX	INTEGER
			ACCESS	read-only
			STATUS	current
	DESCRIPTION ""
			::= { mbusAA 84 }

mbusAAValue27		OBJECT-TYPE
			SYNTAX	INTEGER
			ACCESS	read-only
			STATUS	current
	DESCRIPTION ""
			::= { mbusAA 85 }

mbusAAVIF28		OBJECT-TYPE
			SYNTAX	INTEGER
			ACCESS	read-only
			STATUS	current
	DESCRIPTION ""
			::= { mbusAA 86 }

mbusAAValue28		OBJECT-TYPE
			SYNTAX	INTEGER
			ACCESS	read-only
			STATUS	current
	DESCRIPTION ""
			::= { mbusAA 87 }

mbusAAVIF29		OBJECT-TYPE
			SYNTAX	INTEGER
			ACCESS	read-only
			STATUS	current
	DESCRIPTION ""
			::= { mbusAA 88 }

mbusAAValue29		OBJECT-TYPE
			SYNTAX	INTEGER
			ACCESS	read-only
			STATUS	current
	DESCRIPTION ""
			::= { mbusAA 89 }

mbusAAVIF2A		OBJECT-TYPE
			SYNTAX	INTEGER
			ACCESS	read-only
			STATUS	current
	DESCRIPTION ""
			::= { mbusAA 90 }

mbusAAValue2A		OBJECT-TYPE
			SYNTAX	INTEGER
			ACCESS	read-only
			STATUS	current
	DESCRIPTION ""
			::= { mbusAA 91 }

mbusAAVIF2B		OBJECT-TYPE
			SYNTAX	INTEGER
			ACCESS	read-only
			STATUS	current
	DESCRIPTION ""
			::= { mbusAA 92 }

mbusAAValue2B		OBJECT-TYPE
			SYNTAX	INTEGER
			ACCESS	read-only
			STATUS	current
	DESCRIPTION ""
			::= { mbusAA 93 }

mbusAAVIF2C		OBJECT-TYPE
			SYNTAX	INTEGER
			ACCESS	read-only
			STATUS	current
	DESCRIPTION ""
			::= { mbusAA 94 }

mbusAAValue2C		OBJECT-TYPE
			SYNTAX	INTEGER
			ACCESS	read-only
			STATUS	current
	DESCRIPTION ""
			::= { mbusAA 95 }

mbusAAVIF2D		OBJECT-TYPE
			SYNTAX	INTEGER
			ACCESS	read-only
			STATUS	current
	DESCRIPTION ""
			::= { mbusAA 96 }

mbusAAValue2D		OBJECT-TYPE
			SYNTAX	INTEGER
			ACCESS	read-only
			STATUS	current
	DESCRIPTION ""
			::= { mbusAA 97 }

mbusAAVIF2E		OBJECT-TYPE
			SYNTAX	INTEGER
			ACCESS	read-only
			STATUS	current
	DESCRIPTION ""
			::= { mbusAA 98 }

mbusAAValue2E		OBJECT-TYPE
			SYNTAX	INTEGER
			ACCESS	read-only
			STATUS	current
	DESCRIPTION ""
			::= { mbusAA 99 }

mbusAAVIF2F		OBJECT-TYPE
			SYNTAX	INTEGER
			ACCESS	read-only
			STATUS	current
	DESCRIPTION ""
			::= { mbusAA 100 }

mbusAAValue2F		OBJECT-TYPE
			SYNTAX	INTEGER
			ACCESS	read-only
			STATUS	current
	DESCRIPTION ""
			::= { mbusAA 101 }

mbusAB			OBJECT IDENTIFIER ::= { mbus 171 }

mbusABIdNumber		OBJECT-TYPE
			SYNTAX	Gauge
			ACCESS	read-only
			STATUS	current
	DESCRIPTION ""
			::= { mbusAB 1 }

mbusABManufacturer	OBJECT-TYPE
			SYNTAX	Gauge
			ACCESS	read-only
			STATUS	current
	DESCRIPTION ""
			::= { mbusAB 2 }

mbusABVersion		OBJECT-TYPE
			SYNTAX	Gauge
			ACCESS	read-only
			STATUS	current
	DESCRIPTION ""
			::= { mbusAB 3 }

mbusABMedium		OBJECT-TYPE
			SYNTAX	Gauge
			ACCESS	read-only
			STATUS	current
	DESCRIPTION ""
			::= { mbusAB 4 }

mbusABStatus		OBJECT-TYPE
			SYNTAX	Gauge
			ACCESS	read-only
			STATUS	current
	DESCRIPTION ""
			::= { mbusAB 5 }

mbusABVIF00		OBJECT-TYPE
			SYNTAX	INTEGER
			ACCESS	read-only
			STATUS	current
	DESCRIPTION ""
			::= { mbusAB 6 }

mbusABValue00		OBJECT-TYPE
			SYNTAX	INTEGER
			ACCESS	read-only
			STATUS	current
	DESCRIPTION ""
			::= { mbusAB 7 }

mbusABVIF01		OBJECT-TYPE
			SYNTAX	INTEGER
			ACCESS	read-only
			STATUS	current
	DESCRIPTION ""
			::= { mbusAB 8 }

mbusABValue01		OBJECT-TYPE
			SYNTAX	INTEGER
			ACCESS	read-only
			STATUS	current
	DESCRIPTION ""
			::= { mbusAB 9 }

mbusABVIF02		OBJECT-TYPE
			SYNTAX	INTEGER
			ACCESS	read-only
			STATUS	current
	DESCRIPTION ""
			::= { mbusAB 10 }

mbusABValue02		OBJECT-TYPE
			SYNTAX	INTEGER
			ACCESS	read-only
			STATUS	current
	DESCRIPTION ""
			::= { mbusAB 11 }

mbusABVIF03		OBJECT-TYPE
			SYNTAX	INTEGER
			ACCESS	read-only
			STATUS	current
	DESCRIPTION ""
			::= { mbusAB 12 }

mbusABValue03		OBJECT-TYPE
			SYNTAX	INTEGER
			ACCESS	read-only
			STATUS	current
	DESCRIPTION ""
			::= { mbusAB 13 }

mbusABVIF04		OBJECT-TYPE
			SYNTAX	INTEGER
			ACCESS	read-only
			STATUS	current
	DESCRIPTION ""
			::= { mbusAB 14 }

mbusABValue04		OBJECT-TYPE
			SYNTAX	INTEGER
			ACCESS	read-only
			STATUS	current
	DESCRIPTION ""
			::= { mbusAB 15 }

mbusABVIF05		OBJECT-TYPE
			SYNTAX	INTEGER
			ACCESS	read-only
			STATUS	current
	DESCRIPTION ""
			::= { mbusAB 16 }

mbusABValue05		OBJECT-TYPE
			SYNTAX	INTEGER
			ACCESS	read-only
			STATUS	current
	DESCRIPTION ""
			::= { mbusAB 17 }

mbusABVIF06		OBJECT-TYPE
			SYNTAX	INTEGER
			ACCESS	read-only
			STATUS	current
	DESCRIPTION ""
			::= { mbusAB 18 }

mbusABValue06		OBJECT-TYPE
			SYNTAX	INTEGER
			ACCESS	read-only
			STATUS	current
	DESCRIPTION ""
			::= { mbusAB 19 }

mbusABVIF07		OBJECT-TYPE
			SYNTAX	INTEGER
			ACCESS	read-only
			STATUS	current
	DESCRIPTION ""
			::= { mbusAB 20 }

mbusABValue07		OBJECT-TYPE
			SYNTAX	INTEGER
			ACCESS	read-only
			STATUS	current
	DESCRIPTION ""
			::= { mbusAB 21 }

mbusABVIF08		OBJECT-TYPE
			SYNTAX	INTEGER
			ACCESS	read-only
			STATUS	current
	DESCRIPTION ""
			::= { mbusAB 22 }

mbusABValue08		OBJECT-TYPE
			SYNTAX	INTEGER
			ACCESS	read-only
			STATUS	current
	DESCRIPTION ""
			::= { mbusAB 23 }

mbusABVIF09		OBJECT-TYPE
			SYNTAX	INTEGER
			ACCESS	read-only
			STATUS	current
	DESCRIPTION ""
			::= { mbusAB 24 }

mbusABValue09		OBJECT-TYPE
			SYNTAX	INTEGER
			ACCESS	read-only
			STATUS	current
	DESCRIPTION ""
			::= { mbusAB 25 }

mbusABVIF0A		OBJECT-TYPE
			SYNTAX	INTEGER
			ACCESS	read-only
			STATUS	current
	DESCRIPTION ""
			::= { mbusAB 26 }

mbusABValue0A		OBJECT-TYPE
			SYNTAX	INTEGER
			ACCESS	read-only
			STATUS	current
	DESCRIPTION ""
			::= { mbusAB 27 }

mbusABVIF0B		OBJECT-TYPE
			SYNTAX	INTEGER
			ACCESS	read-only
			STATUS	current
	DESCRIPTION ""
			::= { mbusAB 28 }

mbusABValue0B		OBJECT-TYPE
			SYNTAX	INTEGER
			ACCESS	read-only
			STATUS	current
	DESCRIPTION ""
			::= { mbusAB 29 }

mbusABVIF0C		OBJECT-TYPE
			SYNTAX	INTEGER
			ACCESS	read-only
			STATUS	current
	DESCRIPTION ""
			::= { mbusAB 30 }

mbusABValue0C		OBJECT-TYPE
			SYNTAX	INTEGER
			ACCESS	read-only
			STATUS	current
	DESCRIPTION ""
			::= { mbusAB 31 }

mbusABVIF0D		OBJECT-TYPE
			SYNTAX	INTEGER
			ACCESS	read-only
			STATUS	current
	DESCRIPTION ""
			::= { mbusAB 32 }

mbusABValue0D		OBJECT-TYPE
			SYNTAX	INTEGER
			ACCESS	read-only
			STATUS	current
	DESCRIPTION ""
			::= { mbusAB 33 }

mbusABVIF0E		OBJECT-TYPE
			SYNTAX	INTEGER
			ACCESS	read-only
			STATUS	current
	DESCRIPTION ""
			::= { mbusAB 34 }

mbusABValue0E		OBJECT-TYPE
			SYNTAX	INTEGER
			ACCESS	read-only
			STATUS	current
	DESCRIPTION ""
			::= { mbusAB 35 }

mbusABVIF0F		OBJECT-TYPE
			SYNTAX	INTEGER
			ACCESS	read-only
			STATUS	current
	DESCRIPTION ""
			::= { mbusAB 36 }

mbusABValue0F		OBJECT-TYPE
			SYNTAX	INTEGER
			ACCESS	read-only
			STATUS	current
	DESCRIPTION ""
			::= { mbusAB 37 }

mbusABVIF10		OBJECT-TYPE
			SYNTAX	INTEGER
			ACCESS	read-only
			STATUS	current
	DESCRIPTION ""
			::= { mbusAB 38 }

mbusABValue10		OBJECT-TYPE
			SYNTAX	INTEGER
			ACCESS	read-only
			STATUS	current
	DESCRIPTION ""
			::= { mbusAB 39 }

mbusABVIF11		OBJECT-TYPE
			SYNTAX	INTEGER
			ACCESS	read-only
			STATUS	current
	DESCRIPTION ""
			::= { mbusAB 40 }

mbusABValue11		OBJECT-TYPE
			SYNTAX	INTEGER
			ACCESS	read-only
			STATUS	current
	DESCRIPTION ""
			::= { mbusAB 41 }

mbusABVIF12		OBJECT-TYPE
			SYNTAX	INTEGER
			ACCESS	read-only
			STATUS	current
	DESCRIPTION ""
			::= { mbusAB 42 }

mbusABValue12		OBJECT-TYPE
			SYNTAX	INTEGER
			ACCESS	read-only
			STATUS	current
	DESCRIPTION ""
			::= { mbusAB 43 }

mbusABVIF13		OBJECT-TYPE
			SYNTAX	INTEGER
			ACCESS	read-only
			STATUS	current
	DESCRIPTION ""
			::= { mbusAB 44 }

mbusABValue13		OBJECT-TYPE
			SYNTAX	INTEGER
			ACCESS	read-only
			STATUS	current
	DESCRIPTION ""
			::= { mbusAB 45 }

mbusABVIF14		OBJECT-TYPE
			SYNTAX	INTEGER
			ACCESS	read-only
			STATUS	current
	DESCRIPTION ""
			::= { mbusAB 46 }

mbusABValue14		OBJECT-TYPE
			SYNTAX	INTEGER
			ACCESS	read-only
			STATUS	current
	DESCRIPTION ""
			::= { mbusAB 47 }

mbusABVIF15		OBJECT-TYPE
			SYNTAX	INTEGER
			ACCESS	read-only
			STATUS	current
	DESCRIPTION ""
			::= { mbusAB 48 }

mbusABValue15		OBJECT-TYPE
			SYNTAX	INTEGER
			ACCESS	read-only
			STATUS	current
	DESCRIPTION ""
			::= { mbusAB 49 }

mbusABVIF16		OBJECT-TYPE
			SYNTAX	INTEGER
			ACCESS	read-only
			STATUS	current
	DESCRIPTION ""
			::= { mbusAB 50 }

mbusABValue16		OBJECT-TYPE
			SYNTAX	INTEGER
			ACCESS	read-only
			STATUS	current
	DESCRIPTION ""
			::= { mbusAB 51 }

mbusABVIF17		OBJECT-TYPE
			SYNTAX	INTEGER
			ACCESS	read-only
			STATUS	current
	DESCRIPTION ""
			::= { mbusAB 52 }

mbusABValue17		OBJECT-TYPE
			SYNTAX	INTEGER
			ACCESS	read-only
			STATUS	current
	DESCRIPTION ""
			::= { mbusAB 53 }

mbusABVIF18		OBJECT-TYPE
			SYNTAX	INTEGER
			ACCESS	read-only
			STATUS	current
	DESCRIPTION ""
			::= { mbusAB 54 }

mbusABValue18		OBJECT-TYPE
			SYNTAX	INTEGER
			ACCESS	read-only
			STATUS	current
	DESCRIPTION ""
			::= { mbusAB 55 }

mbusABVIF19		OBJECT-TYPE
			SYNTAX	INTEGER
			ACCESS	read-only
			STATUS	current
	DESCRIPTION ""
			::= { mbusAB 56 }

mbusABValue19		OBJECT-TYPE
			SYNTAX	INTEGER
			ACCESS	read-only
			STATUS	current
	DESCRIPTION ""
			::= { mbusAB 57 }

mbusABVIF1A		OBJECT-TYPE
			SYNTAX	INTEGER
			ACCESS	read-only
			STATUS	current
	DESCRIPTION ""
			::= { mbusAB 58 }

mbusABValue1A		OBJECT-TYPE
			SYNTAX	INTEGER
			ACCESS	read-only
			STATUS	current
	DESCRIPTION ""
			::= { mbusAB 59 }

mbusABVIF1B		OBJECT-TYPE
			SYNTAX	INTEGER
			ACCESS	read-only
			STATUS	current
	DESCRIPTION ""
			::= { mbusAB 60 }

mbusABValue1B		OBJECT-TYPE
			SYNTAX	INTEGER
			ACCESS	read-only
			STATUS	current
	DESCRIPTION ""
			::= { mbusAB 61 }

mbusABVIF1C		OBJECT-TYPE
			SYNTAX	INTEGER
			ACCESS	read-only
			STATUS	current
	DESCRIPTION ""
			::= { mbusAB 62 }

mbusABValue1C		OBJECT-TYPE
			SYNTAX	INTEGER
			ACCESS	read-only
			STATUS	current
	DESCRIPTION ""
			::= { mbusAB 63 }

mbusABVIF1D		OBJECT-TYPE
			SYNTAX	INTEGER
			ACCESS	read-only
			STATUS	current
	DESCRIPTION ""
			::= { mbusAB 64 }

mbusABValue1D		OBJECT-TYPE
			SYNTAX	INTEGER
			ACCESS	read-only
			STATUS	current
	DESCRIPTION ""
			::= { mbusAB 65 }

mbusABVIF1E		OBJECT-TYPE
			SYNTAX	INTEGER
			ACCESS	read-only
			STATUS	current
	DESCRIPTION ""
			::= { mbusAB 66 }

mbusABValue1E		OBJECT-TYPE
			SYNTAX	INTEGER
			ACCESS	read-only
			STATUS	current
	DESCRIPTION ""
			::= { mbusAB 67 }

mbusABVIF1F		OBJECT-TYPE
			SYNTAX	INTEGER
			ACCESS	read-only
			STATUS	current
	DESCRIPTION ""
			::= { mbusAB 68 }

mbusABValue1F		OBJECT-TYPE
			SYNTAX	INTEGER
			ACCESS	read-only
			STATUS	current
	DESCRIPTION ""
			::= { mbusAB 69 }

mbusABVIF20		OBJECT-TYPE
			SYNTAX	INTEGER
			ACCESS	read-only
			STATUS	current
	DESCRIPTION ""
			::= { mbusAB 70 }

mbusABValue20		OBJECT-TYPE
			SYNTAX	INTEGER
			ACCESS	read-only
			STATUS	current
	DESCRIPTION ""
			::= { mbusAB 71 }

mbusABVIF21		OBJECT-TYPE
			SYNTAX	INTEGER
			ACCESS	read-only
			STATUS	current
	DESCRIPTION ""
			::= { mbusAB 72 }

mbusABValue21		OBJECT-TYPE
			SYNTAX	INTEGER
			ACCESS	read-only
			STATUS	current
	DESCRIPTION ""
			::= { mbusAB 73 }

mbusABVIF22		OBJECT-TYPE
			SYNTAX	INTEGER
			ACCESS	read-only
			STATUS	current
	DESCRIPTION ""
			::= { mbusAB 74 }

mbusABValue22		OBJECT-TYPE
			SYNTAX	INTEGER
			ACCESS	read-only
			STATUS	current
	DESCRIPTION ""
			::= { mbusAB 75 }

mbusABVIF23		OBJECT-TYPE
			SYNTAX	INTEGER
			ACCESS	read-only
			STATUS	current
	DESCRIPTION ""
			::= { mbusAB 76 }

mbusABValue23		OBJECT-TYPE
			SYNTAX	INTEGER
			ACCESS	read-only
			STATUS	current
	DESCRIPTION ""
			::= { mbusAB 77 }

mbusABVIF24		OBJECT-TYPE
			SYNTAX	INTEGER
			ACCESS	read-only
			STATUS	current
	DESCRIPTION ""
			::= { mbusAB 78 }

mbusABValue24		OBJECT-TYPE
			SYNTAX	INTEGER
			ACCESS	read-only
			STATUS	current
	DESCRIPTION ""
			::= { mbusAB 79 }

mbusABVIF25		OBJECT-TYPE
			SYNTAX	INTEGER
			ACCESS	read-only
			STATUS	current
	DESCRIPTION ""
			::= { mbusAB 80 }

mbusABValue25		OBJECT-TYPE
			SYNTAX	INTEGER
			ACCESS	read-only
			STATUS	current
	DESCRIPTION ""
			::= { mbusAB 81 }

mbusABVIF26		OBJECT-TYPE
			SYNTAX	INTEGER
			ACCESS	read-only
			STATUS	current
	DESCRIPTION ""
			::= { mbusAB 82 }

mbusABValue26		OBJECT-TYPE
			SYNTAX	INTEGER
			ACCESS	read-only
			STATUS	current
	DESCRIPTION ""
			::= { mbusAB 83 }

mbusABVIF27		OBJECT-TYPE
			SYNTAX	INTEGER
			ACCESS	read-only
			STATUS	current
	DESCRIPTION ""
			::= { mbusAB 84 }

mbusABValue27		OBJECT-TYPE
			SYNTAX	INTEGER
			ACCESS	read-only
			STATUS	current
	DESCRIPTION ""
			::= { mbusAB 85 }

mbusABVIF28		OBJECT-TYPE
			SYNTAX	INTEGER
			ACCESS	read-only
			STATUS	current
	DESCRIPTION ""
			::= { mbusAB 86 }

mbusABValue28		OBJECT-TYPE
			SYNTAX	INTEGER
			ACCESS	read-only
			STATUS	current
	DESCRIPTION ""
			::= { mbusAB 87 }

mbusABVIF29		OBJECT-TYPE
			SYNTAX	INTEGER
			ACCESS	read-only
			STATUS	current
	DESCRIPTION ""
			::= { mbusAB 88 }

mbusABValue29		OBJECT-TYPE
			SYNTAX	INTEGER
			ACCESS	read-only
			STATUS	current
	DESCRIPTION ""
			::= { mbusAB 89 }

mbusABVIF2A		OBJECT-TYPE
			SYNTAX	INTEGER
			ACCESS	read-only
			STATUS	current
	DESCRIPTION ""
			::= { mbusAB 90 }

mbusABValue2A		OBJECT-TYPE
			SYNTAX	INTEGER
			ACCESS	read-only
			STATUS	current
	DESCRIPTION ""
			::= { mbusAB 91 }

mbusABVIF2B		OBJECT-TYPE
			SYNTAX	INTEGER
			ACCESS	read-only
			STATUS	current
	DESCRIPTION ""
			::= { mbusAB 92 }

mbusABValue2B		OBJECT-TYPE
			SYNTAX	INTEGER
			ACCESS	read-only
			STATUS	current
	DESCRIPTION ""
			::= { mbusAB 93 }

mbusABVIF2C		OBJECT-TYPE
			SYNTAX	INTEGER
			ACCESS	read-only
			STATUS	current
	DESCRIPTION ""
			::= { mbusAB 94 }

mbusABValue2C		OBJECT-TYPE
			SYNTAX	INTEGER
			ACCESS	read-only
			STATUS	current
	DESCRIPTION ""
			::= { mbusAB 95 }

mbusABVIF2D		OBJECT-TYPE
			SYNTAX	INTEGER
			ACCESS	read-only
			STATUS	current
	DESCRIPTION ""
			::= { mbusAB 96 }

mbusABValue2D		OBJECT-TYPE
			SYNTAX	INTEGER
			ACCESS	read-only
			STATUS	current
	DESCRIPTION ""
			::= { mbusAB 97 }

mbusABVIF2E		OBJECT-TYPE
			SYNTAX	INTEGER
			ACCESS	read-only
			STATUS	current
	DESCRIPTION ""
			::= { mbusAB 98 }

mbusABValue2E		OBJECT-TYPE
			SYNTAX	INTEGER
			ACCESS	read-only
			STATUS	current
	DESCRIPTION ""
			::= { mbusAB 99 }

mbusABVIF2F		OBJECT-TYPE
			SYNTAX	INTEGER
			ACCESS	read-only
			STATUS	current
	DESCRIPTION ""
			::= { mbusAB 100 }

mbusABValue2F		OBJECT-TYPE
			SYNTAX	INTEGER
			ACCESS	read-only
			STATUS	current
	DESCRIPTION ""
			::= { mbusAB 101 }

mbusAC			OBJECT IDENTIFIER ::= { mbus 172 }

mbusACIdNumber		OBJECT-TYPE
			SYNTAX	Gauge
			ACCESS	read-only
			STATUS	current
	DESCRIPTION ""
			::= { mbusAC 1 }

mbusACManufacturer	OBJECT-TYPE
			SYNTAX	Gauge
			ACCESS	read-only
			STATUS	current
	DESCRIPTION ""
			::= { mbusAC 2 }

mbusACVersion		OBJECT-TYPE
			SYNTAX	Gauge
			ACCESS	read-only
			STATUS	current
	DESCRIPTION ""
			::= { mbusAC 3 }

mbusACMedium		OBJECT-TYPE
			SYNTAX	Gauge
			ACCESS	read-only
			STATUS	current
	DESCRIPTION ""
			::= { mbusAC 4 }

mbusACStatus		OBJECT-TYPE
			SYNTAX	Gauge
			ACCESS	read-only
			STATUS	current
	DESCRIPTION ""
			::= { mbusAC 5 }

mbusACVIF00		OBJECT-TYPE
			SYNTAX	INTEGER
			ACCESS	read-only
			STATUS	current
	DESCRIPTION ""
			::= { mbusAC 6 }

mbusACValue00		OBJECT-TYPE
			SYNTAX	INTEGER
			ACCESS	read-only
			STATUS	current
	DESCRIPTION ""
			::= { mbusAC 7 }

mbusACVIF01		OBJECT-TYPE
			SYNTAX	INTEGER
			ACCESS	read-only
			STATUS	current
	DESCRIPTION ""
			::= { mbusAC 8 }

mbusACValue01		OBJECT-TYPE
			SYNTAX	INTEGER
			ACCESS	read-only
			STATUS	current
	DESCRIPTION ""
			::= { mbusAC 9 }

mbusACVIF02		OBJECT-TYPE
			SYNTAX	INTEGER
			ACCESS	read-only
			STATUS	current
	DESCRIPTION ""
			::= { mbusAC 10 }

mbusACValue02		OBJECT-TYPE
			SYNTAX	INTEGER
			ACCESS	read-only
			STATUS	current
	DESCRIPTION ""
			::= { mbusAC 11 }

mbusACVIF03		OBJECT-TYPE
			SYNTAX	INTEGER
			ACCESS	read-only
			STATUS	current
	DESCRIPTION ""
			::= { mbusAC 12 }

mbusACValue03		OBJECT-TYPE
			SYNTAX	INTEGER
			ACCESS	read-only
			STATUS	current
	DESCRIPTION ""
			::= { mbusAC 13 }

mbusACVIF04		OBJECT-TYPE
			SYNTAX	INTEGER
			ACCESS	read-only
			STATUS	current
	DESCRIPTION ""
			::= { mbusAC 14 }

mbusACValue04		OBJECT-TYPE
			SYNTAX	INTEGER
			ACCESS	read-only
			STATUS	current
	DESCRIPTION ""
			::= { mbusAC 15 }

mbusACVIF05		OBJECT-TYPE
			SYNTAX	INTEGER
			ACCESS	read-only
			STATUS	current
	DESCRIPTION ""
			::= { mbusAC 16 }

mbusACValue05		OBJECT-TYPE
			SYNTAX	INTEGER
			ACCESS	read-only
			STATUS	current
	DESCRIPTION ""
			::= { mbusAC 17 }

mbusACVIF06		OBJECT-TYPE
			SYNTAX	INTEGER
			ACCESS	read-only
			STATUS	current
	DESCRIPTION ""
			::= { mbusAC 18 }

mbusACValue06		OBJECT-TYPE
			SYNTAX	INTEGER
			ACCESS	read-only
			STATUS	current
	DESCRIPTION ""
			::= { mbusAC 19 }

mbusACVIF07		OBJECT-TYPE
			SYNTAX	INTEGER
			ACCESS	read-only
			STATUS	current
	DESCRIPTION ""
			::= { mbusAC 20 }

mbusACValue07		OBJECT-TYPE
			SYNTAX	INTEGER
			ACCESS	read-only
			STATUS	current
	DESCRIPTION ""
			::= { mbusAC 21 }

mbusACVIF08		OBJECT-TYPE
			SYNTAX	INTEGER
			ACCESS	read-only
			STATUS	current
	DESCRIPTION ""
			::= { mbusAC 22 }

mbusACValue08		OBJECT-TYPE
			SYNTAX	INTEGER
			ACCESS	read-only
			STATUS	current
	DESCRIPTION ""
			::= { mbusAC 23 }

mbusACVIF09		OBJECT-TYPE
			SYNTAX	INTEGER
			ACCESS	read-only
			STATUS	current
	DESCRIPTION ""
			::= { mbusAC 24 }

mbusACValue09		OBJECT-TYPE
			SYNTAX	INTEGER
			ACCESS	read-only
			STATUS	current
	DESCRIPTION ""
			::= { mbusAC 25 }

mbusACVIF0A		OBJECT-TYPE
			SYNTAX	INTEGER
			ACCESS	read-only
			STATUS	current
	DESCRIPTION ""
			::= { mbusAC 26 }

mbusACValue0A		OBJECT-TYPE
			SYNTAX	INTEGER
			ACCESS	read-only
			STATUS	current
	DESCRIPTION ""
			::= { mbusAC 27 }

mbusACVIF0B		OBJECT-TYPE
			SYNTAX	INTEGER
			ACCESS	read-only
			STATUS	current
	DESCRIPTION ""
			::= { mbusAC 28 }

mbusACValue0B		OBJECT-TYPE
			SYNTAX	INTEGER
			ACCESS	read-only
			STATUS	current
	DESCRIPTION ""
			::= { mbusAC 29 }

mbusACVIF0C		OBJECT-TYPE
			SYNTAX	INTEGER
			ACCESS	read-only
			STATUS	current
	DESCRIPTION ""
			::= { mbusAC 30 }

mbusACValue0C		OBJECT-TYPE
			SYNTAX	INTEGER
			ACCESS	read-only
			STATUS	current
	DESCRIPTION ""
			::= { mbusAC 31 }

mbusACVIF0D		OBJECT-TYPE
			SYNTAX	INTEGER
			ACCESS	read-only
			STATUS	current
	DESCRIPTION ""
			::= { mbusAC 32 }

mbusACValue0D		OBJECT-TYPE
			SYNTAX	INTEGER
			ACCESS	read-only
			STATUS	current
	DESCRIPTION ""
			::= { mbusAC 33 }

mbusACVIF0E		OBJECT-TYPE
			SYNTAX	INTEGER
			ACCESS	read-only
			STATUS	current
	DESCRIPTION ""
			::= { mbusAC 34 }

mbusACValue0E		OBJECT-TYPE
			SYNTAX	INTEGER
			ACCESS	read-only
			STATUS	current
	DESCRIPTION ""
			::= { mbusAC 35 }

mbusACVIF0F		OBJECT-TYPE
			SYNTAX	INTEGER
			ACCESS	read-only
			STATUS	current
	DESCRIPTION ""
			::= { mbusAC 36 }

mbusACValue0F		OBJECT-TYPE
			SYNTAX	INTEGER
			ACCESS	read-only
			STATUS	current
	DESCRIPTION ""
			::= { mbusAC 37 }

mbusACVIF10		OBJECT-TYPE
			SYNTAX	INTEGER
			ACCESS	read-only
			STATUS	current
	DESCRIPTION ""
			::= { mbusAC 38 }

mbusACValue10		OBJECT-TYPE
			SYNTAX	INTEGER
			ACCESS	read-only
			STATUS	current
	DESCRIPTION ""
			::= { mbusAC 39 }

mbusACVIF11		OBJECT-TYPE
			SYNTAX	INTEGER
			ACCESS	read-only
			STATUS	current
	DESCRIPTION ""
			::= { mbusAC 40 }

mbusACValue11		OBJECT-TYPE
			SYNTAX	INTEGER
			ACCESS	read-only
			STATUS	current
	DESCRIPTION ""
			::= { mbusAC 41 }

mbusACVIF12		OBJECT-TYPE
			SYNTAX	INTEGER
			ACCESS	read-only
			STATUS	current
	DESCRIPTION ""
			::= { mbusAC 42 }

mbusACValue12		OBJECT-TYPE
			SYNTAX	INTEGER
			ACCESS	read-only
			STATUS	current
	DESCRIPTION ""
			::= { mbusAC 43 }

mbusACVIF13		OBJECT-TYPE
			SYNTAX	INTEGER
			ACCESS	read-only
			STATUS	current
	DESCRIPTION ""
			::= { mbusAC 44 }

mbusACValue13		OBJECT-TYPE
			SYNTAX	INTEGER
			ACCESS	read-only
			STATUS	current
	DESCRIPTION ""
			::= { mbusAC 45 }

mbusACVIF14		OBJECT-TYPE
			SYNTAX	INTEGER
			ACCESS	read-only
			STATUS	current
	DESCRIPTION ""
			::= { mbusAC 46 }

mbusACValue14		OBJECT-TYPE
			SYNTAX	INTEGER
			ACCESS	read-only
			STATUS	current
	DESCRIPTION ""
			::= { mbusAC 47 }

mbusACVIF15		OBJECT-TYPE
			SYNTAX	INTEGER
			ACCESS	read-only
			STATUS	current
	DESCRIPTION ""
			::= { mbusAC 48 }

mbusACValue15		OBJECT-TYPE
			SYNTAX	INTEGER
			ACCESS	read-only
			STATUS	current
	DESCRIPTION ""
			::= { mbusAC 49 }

mbusACVIF16		OBJECT-TYPE
			SYNTAX	INTEGER
			ACCESS	read-only
			STATUS	current
	DESCRIPTION ""
			::= { mbusAC 50 }

mbusACValue16		OBJECT-TYPE
			SYNTAX	INTEGER
			ACCESS	read-only
			STATUS	current
	DESCRIPTION ""
			::= { mbusAC 51 }

mbusACVIF17		OBJECT-TYPE
			SYNTAX	INTEGER
			ACCESS	read-only
			STATUS	current
	DESCRIPTION ""
			::= { mbusAC 52 }

mbusACValue17		OBJECT-TYPE
			SYNTAX	INTEGER
			ACCESS	read-only
			STATUS	current
	DESCRIPTION ""
			::= { mbusAC 53 }

mbusACVIF18		OBJECT-TYPE
			SYNTAX	INTEGER
			ACCESS	read-only
			STATUS	current
	DESCRIPTION ""
			::= { mbusAC 54 }

mbusACValue18		OBJECT-TYPE
			SYNTAX	INTEGER
			ACCESS	read-only
			STATUS	current
	DESCRIPTION ""
			::= { mbusAC 55 }

mbusACVIF19		OBJECT-TYPE
			SYNTAX	INTEGER
			ACCESS	read-only
			STATUS	current
	DESCRIPTION ""
			::= { mbusAC 56 }

mbusACValue19		OBJECT-TYPE
			SYNTAX	INTEGER
			ACCESS	read-only
			STATUS	current
	DESCRIPTION ""
			::= { mbusAC 57 }

mbusACVIF1A		OBJECT-TYPE
			SYNTAX	INTEGER
			ACCESS	read-only
			STATUS	current
	DESCRIPTION ""
			::= { mbusAC 58 }

mbusACValue1A		OBJECT-TYPE
			SYNTAX	INTEGER
			ACCESS	read-only
			STATUS	current
	DESCRIPTION ""
			::= { mbusAC 59 }

mbusACVIF1B		OBJECT-TYPE
			SYNTAX	INTEGER
			ACCESS	read-only
			STATUS	current
	DESCRIPTION ""
			::= { mbusAC 60 }

mbusACValue1B		OBJECT-TYPE
			SYNTAX	INTEGER
			ACCESS	read-only
			STATUS	current
	DESCRIPTION ""
			::= { mbusAC 61 }

mbusACVIF1C		OBJECT-TYPE
			SYNTAX	INTEGER
			ACCESS	read-only
			STATUS	current
	DESCRIPTION ""
			::= { mbusAC 62 }

mbusACValue1C		OBJECT-TYPE
			SYNTAX	INTEGER
			ACCESS	read-only
			STATUS	current
	DESCRIPTION ""
			::= { mbusAC 63 }

mbusACVIF1D		OBJECT-TYPE
			SYNTAX	INTEGER
			ACCESS	read-only
			STATUS	current
	DESCRIPTION ""
			::= { mbusAC 64 }

mbusACValue1D		OBJECT-TYPE
			SYNTAX	INTEGER
			ACCESS	read-only
			STATUS	current
	DESCRIPTION ""
			::= { mbusAC 65 }

mbusACVIF1E		OBJECT-TYPE
			SYNTAX	INTEGER
			ACCESS	read-only
			STATUS	current
	DESCRIPTION ""
			::= { mbusAC 66 }

mbusACValue1E		OBJECT-TYPE
			SYNTAX	INTEGER
			ACCESS	read-only
			STATUS	current
	DESCRIPTION ""
			::= { mbusAC 67 }

mbusACVIF1F		OBJECT-TYPE
			SYNTAX	INTEGER
			ACCESS	read-only
			STATUS	current
	DESCRIPTION ""
			::= { mbusAC 68 }

mbusACValue1F		OBJECT-TYPE
			SYNTAX	INTEGER
			ACCESS	read-only
			STATUS	current
	DESCRIPTION ""
			::= { mbusAC 69 }

mbusACVIF20		OBJECT-TYPE
			SYNTAX	INTEGER
			ACCESS	read-only
			STATUS	current
	DESCRIPTION ""
			::= { mbusAC 70 }

mbusACValue20		OBJECT-TYPE
			SYNTAX	INTEGER
			ACCESS	read-only
			STATUS	current
	DESCRIPTION ""
			::= { mbusAC 71 }

mbusACVIF21		OBJECT-TYPE
			SYNTAX	INTEGER
			ACCESS	read-only
			STATUS	current
	DESCRIPTION ""
			::= { mbusAC 72 }

mbusACValue21		OBJECT-TYPE
			SYNTAX	INTEGER
			ACCESS	read-only
			STATUS	current
	DESCRIPTION ""
			::= { mbusAC 73 }

mbusACVIF22		OBJECT-TYPE
			SYNTAX	INTEGER
			ACCESS	read-only
			STATUS	current
	DESCRIPTION ""
			::= { mbusAC 74 }

mbusACValue22		OBJECT-TYPE
			SYNTAX	INTEGER
			ACCESS	read-only
			STATUS	current
	DESCRIPTION ""
			::= { mbusAC 75 }

mbusACVIF23		OBJECT-TYPE
			SYNTAX	INTEGER
			ACCESS	read-only
			STATUS	current
	DESCRIPTION ""
			::= { mbusAC 76 }

mbusACValue23		OBJECT-TYPE
			SYNTAX	INTEGER
			ACCESS	read-only
			STATUS	current
	DESCRIPTION ""
			::= { mbusAC 77 }

mbusACVIF24		OBJECT-TYPE
			SYNTAX	INTEGER
			ACCESS	read-only
			STATUS	current
	DESCRIPTION ""
			::= { mbusAC 78 }

mbusACValue24		OBJECT-TYPE
			SYNTAX	INTEGER
			ACCESS	read-only
			STATUS	current
	DESCRIPTION ""
			::= { mbusAC 79 }

mbusACVIF25		OBJECT-TYPE
			SYNTAX	INTEGER
			ACCESS	read-only
			STATUS	current
	DESCRIPTION ""
			::= { mbusAC 80 }

mbusACValue25		OBJECT-TYPE
			SYNTAX	INTEGER
			ACCESS	read-only
			STATUS	current
	DESCRIPTION ""
			::= { mbusAC 81 }

mbusACVIF26		OBJECT-TYPE
			SYNTAX	INTEGER
			ACCESS	read-only
			STATUS	current
	DESCRIPTION ""
			::= { mbusAC 82 }

mbusACValue26		OBJECT-TYPE
			SYNTAX	INTEGER
			ACCESS	read-only
			STATUS	current
	DESCRIPTION ""
			::= { mbusAC 83 }

mbusACVIF27		OBJECT-TYPE
			SYNTAX	INTEGER
			ACCESS	read-only
			STATUS	current
	DESCRIPTION ""
			::= { mbusAC 84 }

mbusACValue27		OBJECT-TYPE
			SYNTAX	INTEGER
			ACCESS	read-only
			STATUS	current
	DESCRIPTION ""
			::= { mbusAC 85 }

mbusACVIF28		OBJECT-TYPE
			SYNTAX	INTEGER
			ACCESS	read-only
			STATUS	current
	DESCRIPTION ""
			::= { mbusAC 86 }

mbusACValue28		OBJECT-TYPE
			SYNTAX	INTEGER
			ACCESS	read-only
			STATUS	current
	DESCRIPTION ""
			::= { mbusAC 87 }

mbusACVIF29		OBJECT-TYPE
			SYNTAX	INTEGER
			ACCESS	read-only
			STATUS	current
	DESCRIPTION ""
			::= { mbusAC 88 }

mbusACValue29		OBJECT-TYPE
			SYNTAX	INTEGER
			ACCESS	read-only
			STATUS	current
	DESCRIPTION ""
			::= { mbusAC 89 }

mbusACVIF2A		OBJECT-TYPE
			SYNTAX	INTEGER
			ACCESS	read-only
			STATUS	current
	DESCRIPTION ""
			::= { mbusAC 90 }

mbusACValue2A		OBJECT-TYPE
			SYNTAX	INTEGER
			ACCESS	read-only
			STATUS	current
	DESCRIPTION ""
			::= { mbusAC 91 }

mbusACVIF2B		OBJECT-TYPE
			SYNTAX	INTEGER
			ACCESS	read-only
			STATUS	current
	DESCRIPTION ""
			::= { mbusAC 92 }

mbusACValue2B		OBJECT-TYPE
			SYNTAX	INTEGER
			ACCESS	read-only
			STATUS	current
	DESCRIPTION ""
			::= { mbusAC 93 }

mbusACVIF2C		OBJECT-TYPE
			SYNTAX	INTEGER
			ACCESS	read-only
			STATUS	current
	DESCRIPTION ""
			::= { mbusAC 94 }

mbusACValue2C		OBJECT-TYPE
			SYNTAX	INTEGER
			ACCESS	read-only
			STATUS	current
	DESCRIPTION ""
			::= { mbusAC 95 }

mbusACVIF2D		OBJECT-TYPE
			SYNTAX	INTEGER
			ACCESS	read-only
			STATUS	current
	DESCRIPTION ""
			::= { mbusAC 96 }

mbusACValue2D		OBJECT-TYPE
			SYNTAX	INTEGER
			ACCESS	read-only
			STATUS	current
	DESCRIPTION ""
			::= { mbusAC 97 }

mbusACVIF2E		OBJECT-TYPE
			SYNTAX	INTEGER
			ACCESS	read-only
			STATUS	current
	DESCRIPTION ""
			::= { mbusAC 98 }

mbusACValue2E		OBJECT-TYPE
			SYNTAX	INTEGER
			ACCESS	read-only
			STATUS	current
	DESCRIPTION ""
			::= { mbusAC 99 }

mbusACVIF2F		OBJECT-TYPE
			SYNTAX	INTEGER
			ACCESS	read-only
			STATUS	current
	DESCRIPTION ""
			::= { mbusAC 100 }

mbusACValue2F		OBJECT-TYPE
			SYNTAX	INTEGER
			ACCESS	read-only
			STATUS	current
	DESCRIPTION ""
			::= { mbusAC 101 }

mbusAD			OBJECT IDENTIFIER ::= { mbus 173 }

mbusADIdNumber		OBJECT-TYPE
			SYNTAX	Gauge
			ACCESS	read-only
			STATUS	current
	DESCRIPTION ""
			::= { mbusAD 1 }

mbusADManufacturer	OBJECT-TYPE
			SYNTAX	Gauge
			ACCESS	read-only
			STATUS	current
	DESCRIPTION ""
			::= { mbusAD 2 }

mbusADVersion		OBJECT-TYPE
			SYNTAX	Gauge
			ACCESS	read-only
			STATUS	current
	DESCRIPTION ""
			::= { mbusAD 3 }

mbusADMedium		OBJECT-TYPE
			SYNTAX	Gauge
			ACCESS	read-only
			STATUS	current
	DESCRIPTION ""
			::= { mbusAD 4 }

mbusADStatus		OBJECT-TYPE
			SYNTAX	Gauge
			ACCESS	read-only
			STATUS	current
	DESCRIPTION ""
			::= { mbusAD 5 }

mbusADVIF00		OBJECT-TYPE
			SYNTAX	INTEGER
			ACCESS	read-only
			STATUS	current
	DESCRIPTION ""
			::= { mbusAD 6 }

mbusADValue00		OBJECT-TYPE
			SYNTAX	INTEGER
			ACCESS	read-only
			STATUS	current
	DESCRIPTION ""
			::= { mbusAD 7 }

mbusADVIF01		OBJECT-TYPE
			SYNTAX	INTEGER
			ACCESS	read-only
			STATUS	current
	DESCRIPTION ""
			::= { mbusAD 8 }

mbusADValue01		OBJECT-TYPE
			SYNTAX	INTEGER
			ACCESS	read-only
			STATUS	current
	DESCRIPTION ""
			::= { mbusAD 9 }

mbusADVIF02		OBJECT-TYPE
			SYNTAX	INTEGER
			ACCESS	read-only
			STATUS	current
	DESCRIPTION ""
			::= { mbusAD 10 }

mbusADValue02		OBJECT-TYPE
			SYNTAX	INTEGER
			ACCESS	read-only
			STATUS	current
	DESCRIPTION ""
			::= { mbusAD 11 }

mbusADVIF03		OBJECT-TYPE
			SYNTAX	INTEGER
			ACCESS	read-only
			STATUS	current
	DESCRIPTION ""
			::= { mbusAD 12 }

mbusADValue03		OBJECT-TYPE
			SYNTAX	INTEGER
			ACCESS	read-only
			STATUS	current
	DESCRIPTION ""
			::= { mbusAD 13 }

mbusADVIF04		OBJECT-TYPE
			SYNTAX	INTEGER
			ACCESS	read-only
			STATUS	current
	DESCRIPTION ""
			::= { mbusAD 14 }

mbusADValue04		OBJECT-TYPE
			SYNTAX	INTEGER
			ACCESS	read-only
			STATUS	current
	DESCRIPTION ""
			::= { mbusAD 15 }

mbusADVIF05		OBJECT-TYPE
			SYNTAX	INTEGER
			ACCESS	read-only
			STATUS	current
	DESCRIPTION ""
			::= { mbusAD 16 }

mbusADValue05		OBJECT-TYPE
			SYNTAX	INTEGER
			ACCESS	read-only
			STATUS	current
	DESCRIPTION ""
			::= { mbusAD 17 }

mbusADVIF06		OBJECT-TYPE
			SYNTAX	INTEGER
			ACCESS	read-only
			STATUS	current
	DESCRIPTION ""
			::= { mbusAD 18 }

mbusADValue06		OBJECT-TYPE
			SYNTAX	INTEGER
			ACCESS	read-only
			STATUS	current
	DESCRIPTION ""
			::= { mbusAD 19 }

mbusADVIF07		OBJECT-TYPE
			SYNTAX	INTEGER
			ACCESS	read-only
			STATUS	current
	DESCRIPTION ""
			::= { mbusAD 20 }

mbusADValue07		OBJECT-TYPE
			SYNTAX	INTEGER
			ACCESS	read-only
			STATUS	current
	DESCRIPTION ""
			::= { mbusAD 21 }

mbusADVIF08		OBJECT-TYPE
			SYNTAX	INTEGER
			ACCESS	read-only
			STATUS	current
	DESCRIPTION ""
			::= { mbusAD 22 }

mbusADValue08		OBJECT-TYPE
			SYNTAX	INTEGER
			ACCESS	read-only
			STATUS	current
	DESCRIPTION ""
			::= { mbusAD 23 }

mbusADVIF09		OBJECT-TYPE
			SYNTAX	INTEGER
			ACCESS	read-only
			STATUS	current
	DESCRIPTION ""
			::= { mbusAD 24 }

mbusADValue09		OBJECT-TYPE
			SYNTAX	INTEGER
			ACCESS	read-only
			STATUS	current
	DESCRIPTION ""
			::= { mbusAD 25 }

mbusADVIF0A		OBJECT-TYPE
			SYNTAX	INTEGER
			ACCESS	read-only
			STATUS	current
	DESCRIPTION ""
			::= { mbusAD 26 }

mbusADValue0A		OBJECT-TYPE
			SYNTAX	INTEGER
			ACCESS	read-only
			STATUS	current
	DESCRIPTION ""
			::= { mbusAD 27 }

mbusADVIF0B		OBJECT-TYPE
			SYNTAX	INTEGER
			ACCESS	read-only
			STATUS	current
	DESCRIPTION ""
			::= { mbusAD 28 }

mbusADValue0B		OBJECT-TYPE
			SYNTAX	INTEGER
			ACCESS	read-only
			STATUS	current
	DESCRIPTION ""
			::= { mbusAD 29 }

mbusADVIF0C		OBJECT-TYPE
			SYNTAX	INTEGER
			ACCESS	read-only
			STATUS	current
	DESCRIPTION ""
			::= { mbusAD 30 }

mbusADValue0C		OBJECT-TYPE
			SYNTAX	INTEGER
			ACCESS	read-only
			STATUS	current
	DESCRIPTION ""
			::= { mbusAD 31 }

mbusADVIF0D		OBJECT-TYPE
			SYNTAX	INTEGER
			ACCESS	read-only
			STATUS	current
	DESCRIPTION ""
			::= { mbusAD 32 }

mbusADValue0D		OBJECT-TYPE
			SYNTAX	INTEGER
			ACCESS	read-only
			STATUS	current
	DESCRIPTION ""
			::= { mbusAD 33 }

mbusADVIF0E		OBJECT-TYPE
			SYNTAX	INTEGER
			ACCESS	read-only
			STATUS	current
	DESCRIPTION ""
			::= { mbusAD 34 }

mbusADValue0E		OBJECT-TYPE
			SYNTAX	INTEGER
			ACCESS	read-only
			STATUS	current
	DESCRIPTION ""
			::= { mbusAD 35 }

mbusADVIF0F		OBJECT-TYPE
			SYNTAX	INTEGER
			ACCESS	read-only
			STATUS	current
	DESCRIPTION ""
			::= { mbusAD 36 }

mbusADValue0F		OBJECT-TYPE
			SYNTAX	INTEGER
			ACCESS	read-only
			STATUS	current
	DESCRIPTION ""
			::= { mbusAD 37 }

mbusADVIF10		OBJECT-TYPE
			SYNTAX	INTEGER
			ACCESS	read-only
			STATUS	current
	DESCRIPTION ""
			::= { mbusAD 38 }

mbusADValue10		OBJECT-TYPE
			SYNTAX	INTEGER
			ACCESS	read-only
			STATUS	current
	DESCRIPTION ""
			::= { mbusAD 39 }

mbusADVIF11		OBJECT-TYPE
			SYNTAX	INTEGER
			ACCESS	read-only
			STATUS	current
	DESCRIPTION ""
			::= { mbusAD 40 }

mbusADValue11		OBJECT-TYPE
			SYNTAX	INTEGER
			ACCESS	read-only
			STATUS	current
	DESCRIPTION ""
			::= { mbusAD 41 }

mbusADVIF12		OBJECT-TYPE
			SYNTAX	INTEGER
			ACCESS	read-only
			STATUS	current
	DESCRIPTION ""
			::= { mbusAD 42 }

mbusADValue12		OBJECT-TYPE
			SYNTAX	INTEGER
			ACCESS	read-only
			STATUS	current
	DESCRIPTION ""
			::= { mbusAD 43 }

mbusADVIF13		OBJECT-TYPE
			SYNTAX	INTEGER
			ACCESS	read-only
			STATUS	current
	DESCRIPTION ""
			::= { mbusAD 44 }

mbusADValue13		OBJECT-TYPE
			SYNTAX	INTEGER
			ACCESS	read-only
			STATUS	current
	DESCRIPTION ""
			::= { mbusAD 45 }

mbusADVIF14		OBJECT-TYPE
			SYNTAX	INTEGER
			ACCESS	read-only
			STATUS	current
	DESCRIPTION ""
			::= { mbusAD 46 }

mbusADValue14		OBJECT-TYPE
			SYNTAX	INTEGER
			ACCESS	read-only
			STATUS	current
	DESCRIPTION ""
			::= { mbusAD 47 }

mbusADVIF15		OBJECT-TYPE
			SYNTAX	INTEGER
			ACCESS	read-only
			STATUS	current
	DESCRIPTION ""
			::= { mbusAD 48 }

mbusADValue15		OBJECT-TYPE
			SYNTAX	INTEGER
			ACCESS	read-only
			STATUS	current
	DESCRIPTION ""
			::= { mbusAD 49 }

mbusADVIF16		OBJECT-TYPE
			SYNTAX	INTEGER
			ACCESS	read-only
			STATUS	current
	DESCRIPTION ""
			::= { mbusAD 50 }

mbusADValue16		OBJECT-TYPE
			SYNTAX	INTEGER
			ACCESS	read-only
			STATUS	current
	DESCRIPTION ""
			::= { mbusAD 51 }

mbusADVIF17		OBJECT-TYPE
			SYNTAX	INTEGER
			ACCESS	read-only
			STATUS	current
	DESCRIPTION ""
			::= { mbusAD 52 }

mbusADValue17		OBJECT-TYPE
			SYNTAX	INTEGER
			ACCESS	read-only
			STATUS	current
	DESCRIPTION ""
			::= { mbusAD 53 }

mbusADVIF18		OBJECT-TYPE
			SYNTAX	INTEGER
			ACCESS	read-only
			STATUS	current
	DESCRIPTION ""
			::= { mbusAD 54 }

mbusADValue18		OBJECT-TYPE
			SYNTAX	INTEGER
			ACCESS	read-only
			STATUS	current
	DESCRIPTION ""
			::= { mbusAD 55 }

mbusADVIF19		OBJECT-TYPE
			SYNTAX	INTEGER
			ACCESS	read-only
			STATUS	current
	DESCRIPTION ""
			::= { mbusAD 56 }

mbusADValue19		OBJECT-TYPE
			SYNTAX	INTEGER
			ACCESS	read-only
			STATUS	current
	DESCRIPTION ""
			::= { mbusAD 57 }

mbusADVIF1A		OBJECT-TYPE
			SYNTAX	INTEGER
			ACCESS	read-only
			STATUS	current
	DESCRIPTION ""
			::= { mbusAD 58 }

mbusADValue1A		OBJECT-TYPE
			SYNTAX	INTEGER
			ACCESS	read-only
			STATUS	current
	DESCRIPTION ""
			::= { mbusAD 59 }

mbusADVIF1B		OBJECT-TYPE
			SYNTAX	INTEGER
			ACCESS	read-only
			STATUS	current
	DESCRIPTION ""
			::= { mbusAD 60 }

mbusADValue1B		OBJECT-TYPE
			SYNTAX	INTEGER
			ACCESS	read-only
			STATUS	current
	DESCRIPTION ""
			::= { mbusAD 61 }

mbusADVIF1C		OBJECT-TYPE
			SYNTAX	INTEGER
			ACCESS	read-only
			STATUS	current
	DESCRIPTION ""
			::= { mbusAD 62 }

mbusADValue1C		OBJECT-TYPE
			SYNTAX	INTEGER
			ACCESS	read-only
			STATUS	current
	DESCRIPTION ""
			::= { mbusAD 63 }

mbusADVIF1D		OBJECT-TYPE
			SYNTAX	INTEGER
			ACCESS	read-only
			STATUS	current
	DESCRIPTION ""
			::= { mbusAD 64 }

mbusADValue1D		OBJECT-TYPE
			SYNTAX	INTEGER
			ACCESS	read-only
			STATUS	current
	DESCRIPTION ""
			::= { mbusAD 65 }

mbusADVIF1E		OBJECT-TYPE
			SYNTAX	INTEGER
			ACCESS	read-only
			STATUS	current
	DESCRIPTION ""
			::= { mbusAD 66 }

mbusADValue1E		OBJECT-TYPE
			SYNTAX	INTEGER
			ACCESS	read-only
			STATUS	current
	DESCRIPTION ""
			::= { mbusAD 67 }

mbusADVIF1F		OBJECT-TYPE
			SYNTAX	INTEGER
			ACCESS	read-only
			STATUS	current
	DESCRIPTION ""
			::= { mbusAD 68 }

mbusADValue1F		OBJECT-TYPE
			SYNTAX	INTEGER
			ACCESS	read-only
			STATUS	current
	DESCRIPTION ""
			::= { mbusAD 69 }

mbusADVIF20		OBJECT-TYPE
			SYNTAX	INTEGER
			ACCESS	read-only
			STATUS	current
	DESCRIPTION ""
			::= { mbusAD 70 }

mbusADValue20		OBJECT-TYPE
			SYNTAX	INTEGER
			ACCESS	read-only
			STATUS	current
	DESCRIPTION ""
			::= { mbusAD 71 }

mbusADVIF21		OBJECT-TYPE
			SYNTAX	INTEGER
			ACCESS	read-only
			STATUS	current
	DESCRIPTION ""
			::= { mbusAD 72 }

mbusADValue21		OBJECT-TYPE
			SYNTAX	INTEGER
			ACCESS	read-only
			STATUS	current
	DESCRIPTION ""
			::= { mbusAD 73 }

mbusADVIF22		OBJECT-TYPE
			SYNTAX	INTEGER
			ACCESS	read-only
			STATUS	current
	DESCRIPTION ""
			::= { mbusAD 74 }

mbusADValue22		OBJECT-TYPE
			SYNTAX	INTEGER
			ACCESS	read-only
			STATUS	current
	DESCRIPTION ""
			::= { mbusAD 75 }

mbusADVIF23		OBJECT-TYPE
			SYNTAX	INTEGER
			ACCESS	read-only
			STATUS	current
	DESCRIPTION ""
			::= { mbusAD 76 }

mbusADValue23		OBJECT-TYPE
			SYNTAX	INTEGER
			ACCESS	read-only
			STATUS	current
	DESCRIPTION ""
			::= { mbusAD 77 }

mbusADVIF24		OBJECT-TYPE
			SYNTAX	INTEGER
			ACCESS	read-only
			STATUS	current
	DESCRIPTION ""
			::= { mbusAD 78 }

mbusADValue24		OBJECT-TYPE
			SYNTAX	INTEGER
			ACCESS	read-only
			STATUS	current
	DESCRIPTION ""
			::= { mbusAD 79 }

mbusADVIF25		OBJECT-TYPE
			SYNTAX	INTEGER
			ACCESS	read-only
			STATUS	current
	DESCRIPTION ""
			::= { mbusAD 80 }

mbusADValue25		OBJECT-TYPE
			SYNTAX	INTEGER
			ACCESS	read-only
			STATUS	current
	DESCRIPTION ""
			::= { mbusAD 81 }

mbusADVIF26		OBJECT-TYPE
			SYNTAX	INTEGER
			ACCESS	read-only
			STATUS	current
	DESCRIPTION ""
			::= { mbusAD 82 }

mbusADValue26		OBJECT-TYPE
			SYNTAX	INTEGER
			ACCESS	read-only
			STATUS	current
	DESCRIPTION ""
			::= { mbusAD 83 }

mbusADVIF27		OBJECT-TYPE
			SYNTAX	INTEGER
			ACCESS	read-only
			STATUS	current
	DESCRIPTION ""
			::= { mbusAD 84 }

mbusADValue27		OBJECT-TYPE
			SYNTAX	INTEGER
			ACCESS	read-only
			STATUS	current
	DESCRIPTION ""
			::= { mbusAD 85 }

mbusADVIF28		OBJECT-TYPE
			SYNTAX	INTEGER
			ACCESS	read-only
			STATUS	current
	DESCRIPTION ""
			::= { mbusAD 86 }

mbusADValue28		OBJECT-TYPE
			SYNTAX	INTEGER
			ACCESS	read-only
			STATUS	current
	DESCRIPTION ""
			::= { mbusAD 87 }

mbusADVIF29		OBJECT-TYPE
			SYNTAX	INTEGER
			ACCESS	read-only
			STATUS	current
	DESCRIPTION ""
			::= { mbusAD 88 }

mbusADValue29		OBJECT-TYPE
			SYNTAX	INTEGER
			ACCESS	read-only
			STATUS	current
	DESCRIPTION ""
			::= { mbusAD 89 }

mbusADVIF2A		OBJECT-TYPE
			SYNTAX	INTEGER
			ACCESS	read-only
			STATUS	current
	DESCRIPTION ""
			::= { mbusAD 90 }

mbusADValue2A		OBJECT-TYPE
			SYNTAX	INTEGER
			ACCESS	read-only
			STATUS	current
	DESCRIPTION ""
			::= { mbusAD 91 }

mbusADVIF2B		OBJECT-TYPE
			SYNTAX	INTEGER
			ACCESS	read-only
			STATUS	current
	DESCRIPTION ""
			::= { mbusAD 92 }

mbusADValue2B		OBJECT-TYPE
			SYNTAX	INTEGER
			ACCESS	read-only
			STATUS	current
	DESCRIPTION ""
			::= { mbusAD 93 }

mbusADVIF2C		OBJECT-TYPE
			SYNTAX	INTEGER
			ACCESS	read-only
			STATUS	current
	DESCRIPTION ""
			::= { mbusAD 94 }

mbusADValue2C		OBJECT-TYPE
			SYNTAX	INTEGER
			ACCESS	read-only
			STATUS	current
	DESCRIPTION ""
			::= { mbusAD 95 }

mbusADVIF2D		OBJECT-TYPE
			SYNTAX	INTEGER
			ACCESS	read-only
			STATUS	current
	DESCRIPTION ""
			::= { mbusAD 96 }

mbusADValue2D		OBJECT-TYPE
			SYNTAX	INTEGER
			ACCESS	read-only
			STATUS	current
	DESCRIPTION ""
			::= { mbusAD 97 }

mbusADVIF2E		OBJECT-TYPE
			SYNTAX	INTEGER
			ACCESS	read-only
			STATUS	current
	DESCRIPTION ""
			::= { mbusAD 98 }

mbusADValue2E		OBJECT-TYPE
			SYNTAX	INTEGER
			ACCESS	read-only
			STATUS	current
	DESCRIPTION ""
			::= { mbusAD 99 }

mbusADVIF2F		OBJECT-TYPE
			SYNTAX	INTEGER
			ACCESS	read-only
			STATUS	current
	DESCRIPTION ""
			::= { mbusAD 100 }

mbusADValue2F		OBJECT-TYPE
			SYNTAX	INTEGER
			ACCESS	read-only
			STATUS	current
	DESCRIPTION ""
			::= { mbusAD 101 }

mbusAE			OBJECT IDENTIFIER ::= { mbus 174 }

mbusAEIdNumber		OBJECT-TYPE
			SYNTAX	Gauge
			ACCESS	read-only
			STATUS	current
	DESCRIPTION ""
			::= { mbusAE 1 }

mbusAEManufacturer	OBJECT-TYPE
			SYNTAX	Gauge
			ACCESS	read-only
			STATUS	current
	DESCRIPTION ""
			::= { mbusAE 2 }

mbusAEVersion		OBJECT-TYPE
			SYNTAX	Gauge
			ACCESS	read-only
			STATUS	current
	DESCRIPTION ""
			::= { mbusAE 3 }

mbusAEMedium		OBJECT-TYPE
			SYNTAX	Gauge
			ACCESS	read-only
			STATUS	current
	DESCRIPTION ""
			::= { mbusAE 4 }

mbusAEStatus		OBJECT-TYPE
			SYNTAX	Gauge
			ACCESS	read-only
			STATUS	current
	DESCRIPTION ""
			::= { mbusAE 5 }

mbusAEVIF00		OBJECT-TYPE
			SYNTAX	INTEGER
			ACCESS	read-only
			STATUS	current
	DESCRIPTION ""
			::= { mbusAE 6 }

mbusAEValue00		OBJECT-TYPE
			SYNTAX	INTEGER
			ACCESS	read-only
			STATUS	current
	DESCRIPTION ""
			::= { mbusAE 7 }

mbusAEVIF01		OBJECT-TYPE
			SYNTAX	INTEGER
			ACCESS	read-only
			STATUS	current
	DESCRIPTION ""
			::= { mbusAE 8 }

mbusAEValue01		OBJECT-TYPE
			SYNTAX	INTEGER
			ACCESS	read-only
			STATUS	current
	DESCRIPTION ""
			::= { mbusAE 9 }

mbusAEVIF02		OBJECT-TYPE
			SYNTAX	INTEGER
			ACCESS	read-only
			STATUS	current
	DESCRIPTION ""
			::= { mbusAE 10 }

mbusAEValue02		OBJECT-TYPE
			SYNTAX	INTEGER
			ACCESS	read-only
			STATUS	current
	DESCRIPTION ""
			::= { mbusAE 11 }

mbusAEVIF03		OBJECT-TYPE
			SYNTAX	INTEGER
			ACCESS	read-only
			STATUS	current
	DESCRIPTION ""
			::= { mbusAE 12 }

mbusAEValue03		OBJECT-TYPE
			SYNTAX	INTEGER
			ACCESS	read-only
			STATUS	current
	DESCRIPTION ""
			::= { mbusAE 13 }

mbusAEVIF04		OBJECT-TYPE
			SYNTAX	INTEGER
			ACCESS	read-only
			STATUS	current
	DESCRIPTION ""
			::= { mbusAE 14 }

mbusAEValue04		OBJECT-TYPE
			SYNTAX	INTEGER
			ACCESS	read-only
			STATUS	current
	DESCRIPTION ""
			::= { mbusAE 15 }

mbusAEVIF05		OBJECT-TYPE
			SYNTAX	INTEGER
			ACCESS	read-only
			STATUS	current
	DESCRIPTION ""
			::= { mbusAE 16 }

mbusAEValue05		OBJECT-TYPE
			SYNTAX	INTEGER
			ACCESS	read-only
			STATUS	current
	DESCRIPTION ""
			::= { mbusAE 17 }

mbusAEVIF06		OBJECT-TYPE
			SYNTAX	INTEGER
			ACCESS	read-only
			STATUS	current
	DESCRIPTION ""
			::= { mbusAE 18 }

mbusAEValue06		OBJECT-TYPE
			SYNTAX	INTEGER
			ACCESS	read-only
			STATUS	current
	DESCRIPTION ""
			::= { mbusAE 19 }

mbusAEVIF07		OBJECT-TYPE
			SYNTAX	INTEGER
			ACCESS	read-only
			STATUS	current
	DESCRIPTION ""
			::= { mbusAE 20 }

mbusAEValue07		OBJECT-TYPE
			SYNTAX	INTEGER
			ACCESS	read-only
			STATUS	current
	DESCRIPTION ""
			::= { mbusAE 21 }

mbusAEVIF08		OBJECT-TYPE
			SYNTAX	INTEGER
			ACCESS	read-only
			STATUS	current
	DESCRIPTION ""
			::= { mbusAE 22 }

mbusAEValue08		OBJECT-TYPE
			SYNTAX	INTEGER
			ACCESS	read-only
			STATUS	current
	DESCRIPTION ""
			::= { mbusAE 23 }

mbusAEVIF09		OBJECT-TYPE
			SYNTAX	INTEGER
			ACCESS	read-only
			STATUS	current
	DESCRIPTION ""
			::= { mbusAE 24 }

mbusAEValue09		OBJECT-TYPE
			SYNTAX	INTEGER
			ACCESS	read-only
			STATUS	current
	DESCRIPTION ""
			::= { mbusAE 25 }

mbusAEVIF0A		OBJECT-TYPE
			SYNTAX	INTEGER
			ACCESS	read-only
			STATUS	current
	DESCRIPTION ""
			::= { mbusAE 26 }

mbusAEValue0A		OBJECT-TYPE
			SYNTAX	INTEGER
			ACCESS	read-only
			STATUS	current
	DESCRIPTION ""
			::= { mbusAE 27 }

mbusAEVIF0B		OBJECT-TYPE
			SYNTAX	INTEGER
			ACCESS	read-only
			STATUS	current
	DESCRIPTION ""
			::= { mbusAE 28 }

mbusAEValue0B		OBJECT-TYPE
			SYNTAX	INTEGER
			ACCESS	read-only
			STATUS	current
	DESCRIPTION ""
			::= { mbusAE 29 }

mbusAEVIF0C		OBJECT-TYPE
			SYNTAX	INTEGER
			ACCESS	read-only
			STATUS	current
	DESCRIPTION ""
			::= { mbusAE 30 }

mbusAEValue0C		OBJECT-TYPE
			SYNTAX	INTEGER
			ACCESS	read-only
			STATUS	current
	DESCRIPTION ""
			::= { mbusAE 31 }

mbusAEVIF0D		OBJECT-TYPE
			SYNTAX	INTEGER
			ACCESS	read-only
			STATUS	current
	DESCRIPTION ""
			::= { mbusAE 32 }

mbusAEValue0D		OBJECT-TYPE
			SYNTAX	INTEGER
			ACCESS	read-only
			STATUS	current
	DESCRIPTION ""
			::= { mbusAE 33 }

mbusAEVIF0E		OBJECT-TYPE
			SYNTAX	INTEGER
			ACCESS	read-only
			STATUS	current
	DESCRIPTION ""
			::= { mbusAE 34 }

mbusAEValue0E		OBJECT-TYPE
			SYNTAX	INTEGER
			ACCESS	read-only
			STATUS	current
	DESCRIPTION ""
			::= { mbusAE 35 }

mbusAEVIF0F		OBJECT-TYPE
			SYNTAX	INTEGER
			ACCESS	read-only
			STATUS	current
	DESCRIPTION ""
			::= { mbusAE 36 }

mbusAEValue0F		OBJECT-TYPE
			SYNTAX	INTEGER
			ACCESS	read-only
			STATUS	current
	DESCRIPTION ""
			::= { mbusAE 37 }

mbusAEVIF10		OBJECT-TYPE
			SYNTAX	INTEGER
			ACCESS	read-only
			STATUS	current
	DESCRIPTION ""
			::= { mbusAE 38 }

mbusAEValue10		OBJECT-TYPE
			SYNTAX	INTEGER
			ACCESS	read-only
			STATUS	current
	DESCRIPTION ""
			::= { mbusAE 39 }

mbusAEVIF11		OBJECT-TYPE
			SYNTAX	INTEGER
			ACCESS	read-only
			STATUS	current
	DESCRIPTION ""
			::= { mbusAE 40 }

mbusAEValue11		OBJECT-TYPE
			SYNTAX	INTEGER
			ACCESS	read-only
			STATUS	current
	DESCRIPTION ""
			::= { mbusAE 41 }

mbusAEVIF12		OBJECT-TYPE
			SYNTAX	INTEGER
			ACCESS	read-only
			STATUS	current
	DESCRIPTION ""
			::= { mbusAE 42 }

mbusAEValue12		OBJECT-TYPE
			SYNTAX	INTEGER
			ACCESS	read-only
			STATUS	current
	DESCRIPTION ""
			::= { mbusAE 43 }

mbusAEVIF13		OBJECT-TYPE
			SYNTAX	INTEGER
			ACCESS	read-only
			STATUS	current
	DESCRIPTION ""
			::= { mbusAE 44 }

mbusAEValue13		OBJECT-TYPE
			SYNTAX	INTEGER
			ACCESS	read-only
			STATUS	current
	DESCRIPTION ""
			::= { mbusAE 45 }

mbusAEVIF14		OBJECT-TYPE
			SYNTAX	INTEGER
			ACCESS	read-only
			STATUS	current
	DESCRIPTION ""
			::= { mbusAE 46 }

mbusAEValue14		OBJECT-TYPE
			SYNTAX	INTEGER
			ACCESS	read-only
			STATUS	current
	DESCRIPTION ""
			::= { mbusAE 47 }

mbusAEVIF15		OBJECT-TYPE
			SYNTAX	INTEGER
			ACCESS	read-only
			STATUS	current
	DESCRIPTION ""
			::= { mbusAE 48 }

mbusAEValue15		OBJECT-TYPE
			SYNTAX	INTEGER
			ACCESS	read-only
			STATUS	current
	DESCRIPTION ""
			::= { mbusAE 49 }

mbusAEVIF16		OBJECT-TYPE
			SYNTAX	INTEGER
			ACCESS	read-only
			STATUS	current
	DESCRIPTION ""
			::= { mbusAE 50 }

mbusAEValue16		OBJECT-TYPE
			SYNTAX	INTEGER
			ACCESS	read-only
			STATUS	current
	DESCRIPTION ""
			::= { mbusAE 51 }

mbusAEVIF17		OBJECT-TYPE
			SYNTAX	INTEGER
			ACCESS	read-only
			STATUS	current
	DESCRIPTION ""
			::= { mbusAE 52 }

mbusAEValue17		OBJECT-TYPE
			SYNTAX	INTEGER
			ACCESS	read-only
			STATUS	current
	DESCRIPTION ""
			::= { mbusAE 53 }

mbusAEVIF18		OBJECT-TYPE
			SYNTAX	INTEGER
			ACCESS	read-only
			STATUS	current
	DESCRIPTION ""
			::= { mbusAE 54 }

mbusAEValue18		OBJECT-TYPE
			SYNTAX	INTEGER
			ACCESS	read-only
			STATUS	current
	DESCRIPTION ""
			::= { mbusAE 55 }

mbusAEVIF19		OBJECT-TYPE
			SYNTAX	INTEGER
			ACCESS	read-only
			STATUS	current
	DESCRIPTION ""
			::= { mbusAE 56 }

mbusAEValue19		OBJECT-TYPE
			SYNTAX	INTEGER
			ACCESS	read-only
			STATUS	current
	DESCRIPTION ""
			::= { mbusAE 57 }

mbusAEVIF1A		OBJECT-TYPE
			SYNTAX	INTEGER
			ACCESS	read-only
			STATUS	current
	DESCRIPTION ""
			::= { mbusAE 58 }

mbusAEValue1A		OBJECT-TYPE
			SYNTAX	INTEGER
			ACCESS	read-only
			STATUS	current
	DESCRIPTION ""
			::= { mbusAE 59 }

mbusAEVIF1B		OBJECT-TYPE
			SYNTAX	INTEGER
			ACCESS	read-only
			STATUS	current
	DESCRIPTION ""
			::= { mbusAE 60 }

mbusAEValue1B		OBJECT-TYPE
			SYNTAX	INTEGER
			ACCESS	read-only
			STATUS	current
	DESCRIPTION ""
			::= { mbusAE 61 }

mbusAEVIF1C		OBJECT-TYPE
			SYNTAX	INTEGER
			ACCESS	read-only
			STATUS	current
	DESCRIPTION ""
			::= { mbusAE 62 }

mbusAEValue1C		OBJECT-TYPE
			SYNTAX	INTEGER
			ACCESS	read-only
			STATUS	current
	DESCRIPTION ""
			::= { mbusAE 63 }

mbusAEVIF1D		OBJECT-TYPE
			SYNTAX	INTEGER
			ACCESS	read-only
			STATUS	current
	DESCRIPTION ""
			::= { mbusAE 64 }

mbusAEValue1D		OBJECT-TYPE
			SYNTAX	INTEGER
			ACCESS	read-only
			STATUS	current
	DESCRIPTION ""
			::= { mbusAE 65 }

mbusAEVIF1E		OBJECT-TYPE
			SYNTAX	INTEGER
			ACCESS	read-only
			STATUS	current
	DESCRIPTION ""
			::= { mbusAE 66 }

mbusAEValue1E		OBJECT-TYPE
			SYNTAX	INTEGER
			ACCESS	read-only
			STATUS	current
	DESCRIPTION ""
			::= { mbusAE 67 }

mbusAEVIF1F		OBJECT-TYPE
			SYNTAX	INTEGER
			ACCESS	read-only
			STATUS	current
	DESCRIPTION ""
			::= { mbusAE 68 }

mbusAEValue1F		OBJECT-TYPE
			SYNTAX	INTEGER
			ACCESS	read-only
			STATUS	current
	DESCRIPTION ""
			::= { mbusAE 69 }

mbusAEVIF20		OBJECT-TYPE
			SYNTAX	INTEGER
			ACCESS	read-only
			STATUS	current
	DESCRIPTION ""
			::= { mbusAE 70 }

mbusAEValue20		OBJECT-TYPE
			SYNTAX	INTEGER
			ACCESS	read-only
			STATUS	current
	DESCRIPTION ""
			::= { mbusAE 71 }

mbusAEVIF21		OBJECT-TYPE
			SYNTAX	INTEGER
			ACCESS	read-only
			STATUS	current
	DESCRIPTION ""
			::= { mbusAE 72 }

mbusAEValue21		OBJECT-TYPE
			SYNTAX	INTEGER
			ACCESS	read-only
			STATUS	current
	DESCRIPTION ""
			::= { mbusAE 73 }

mbusAEVIF22		OBJECT-TYPE
			SYNTAX	INTEGER
			ACCESS	read-only
			STATUS	current
	DESCRIPTION ""
			::= { mbusAE 74 }

mbusAEValue22		OBJECT-TYPE
			SYNTAX	INTEGER
			ACCESS	read-only
			STATUS	current
	DESCRIPTION ""
			::= { mbusAE 75 }

mbusAEVIF23		OBJECT-TYPE
			SYNTAX	INTEGER
			ACCESS	read-only
			STATUS	current
	DESCRIPTION ""
			::= { mbusAE 76 }

mbusAEValue23		OBJECT-TYPE
			SYNTAX	INTEGER
			ACCESS	read-only
			STATUS	current
	DESCRIPTION ""
			::= { mbusAE 77 }

mbusAEVIF24		OBJECT-TYPE
			SYNTAX	INTEGER
			ACCESS	read-only
			STATUS	current
	DESCRIPTION ""
			::= { mbusAE 78 }

mbusAEValue24		OBJECT-TYPE
			SYNTAX	INTEGER
			ACCESS	read-only
			STATUS	current
	DESCRIPTION ""
			::= { mbusAE 79 }

mbusAEVIF25		OBJECT-TYPE
			SYNTAX	INTEGER
			ACCESS	read-only
			STATUS	current
	DESCRIPTION ""
			::= { mbusAE 80 }

mbusAEValue25		OBJECT-TYPE
			SYNTAX	INTEGER
			ACCESS	read-only
			STATUS	current
	DESCRIPTION ""
			::= { mbusAE 81 }

mbusAEVIF26		OBJECT-TYPE
			SYNTAX	INTEGER
			ACCESS	read-only
			STATUS	current
	DESCRIPTION ""
			::= { mbusAE 82 }

mbusAEValue26		OBJECT-TYPE
			SYNTAX	INTEGER
			ACCESS	read-only
			STATUS	current
	DESCRIPTION ""
			::= { mbusAE 83 }

mbusAEVIF27		OBJECT-TYPE
			SYNTAX	INTEGER
			ACCESS	read-only
			STATUS	current
	DESCRIPTION ""
			::= { mbusAE 84 }

mbusAEValue27		OBJECT-TYPE
			SYNTAX	INTEGER
			ACCESS	read-only
			STATUS	current
	DESCRIPTION ""
			::= { mbusAE 85 }

mbusAEVIF28		OBJECT-TYPE
			SYNTAX	INTEGER
			ACCESS	read-only
			STATUS	current
	DESCRIPTION ""
			::= { mbusAE 86 }

mbusAEValue28		OBJECT-TYPE
			SYNTAX	INTEGER
			ACCESS	read-only
			STATUS	current
	DESCRIPTION ""
			::= { mbusAE 87 }

mbusAEVIF29		OBJECT-TYPE
			SYNTAX	INTEGER
			ACCESS	read-only
			STATUS	current
	DESCRIPTION ""
			::= { mbusAE 88 }

mbusAEValue29		OBJECT-TYPE
			SYNTAX	INTEGER
			ACCESS	read-only
			STATUS	current
	DESCRIPTION ""
			::= { mbusAE 89 }

mbusAEVIF2A		OBJECT-TYPE
			SYNTAX	INTEGER
			ACCESS	read-only
			STATUS	current
	DESCRIPTION ""
			::= { mbusAE 90 }

mbusAEValue2A		OBJECT-TYPE
			SYNTAX	INTEGER
			ACCESS	read-only
			STATUS	current
	DESCRIPTION ""
			::= { mbusAE 91 }

mbusAEVIF2B		OBJECT-TYPE
			SYNTAX	INTEGER
			ACCESS	read-only
			STATUS	current
	DESCRIPTION ""
			::= { mbusAE 92 }

mbusAEValue2B		OBJECT-TYPE
			SYNTAX	INTEGER
			ACCESS	read-only
			STATUS	current
	DESCRIPTION ""
			::= { mbusAE 93 }

mbusAEVIF2C		OBJECT-TYPE
			SYNTAX	INTEGER
			ACCESS	read-only
			STATUS	current
	DESCRIPTION ""
			::= { mbusAE 94 }

mbusAEValue2C		OBJECT-TYPE
			SYNTAX	INTEGER
			ACCESS	read-only
			STATUS	current
	DESCRIPTION ""
			::= { mbusAE 95 }

mbusAEVIF2D		OBJECT-TYPE
			SYNTAX	INTEGER
			ACCESS	read-only
			STATUS	current
	DESCRIPTION ""
			::= { mbusAE 96 }

mbusAEValue2D		OBJECT-TYPE
			SYNTAX	INTEGER
			ACCESS	read-only
			STATUS	current
	DESCRIPTION ""
			::= { mbusAE 97 }

mbusAEVIF2E		OBJECT-TYPE
			SYNTAX	INTEGER
			ACCESS	read-only
			STATUS	current
	DESCRIPTION ""
			::= { mbusAE 98 }

mbusAEValue2E		OBJECT-TYPE
			SYNTAX	INTEGER
			ACCESS	read-only
			STATUS	current
	DESCRIPTION ""
			::= { mbusAE 99 }

mbusAEVIF2F		OBJECT-TYPE
			SYNTAX	INTEGER
			ACCESS	read-only
			STATUS	current
	DESCRIPTION ""
			::= { mbusAE 100 }

mbusAEValue2F		OBJECT-TYPE
			SYNTAX	INTEGER
			ACCESS	read-only
			STATUS	current
	DESCRIPTION ""
			::= { mbusAE 101 }

mbusAF			OBJECT IDENTIFIER ::= { mbus 175 }

mbusAFIdNumber		OBJECT-TYPE
			SYNTAX	Gauge
			ACCESS	read-only
			STATUS	current
	DESCRIPTION ""
			::= { mbusAF 1 }

mbusAFManufacturer	OBJECT-TYPE
			SYNTAX	Gauge
			ACCESS	read-only
			STATUS	current
	DESCRIPTION ""
			::= { mbusAF 2 }

mbusAFVersion		OBJECT-TYPE
			SYNTAX	Gauge
			ACCESS	read-only
			STATUS	current
	DESCRIPTION ""
			::= { mbusAF 3 }

mbusAFMedium		OBJECT-TYPE
			SYNTAX	Gauge
			ACCESS	read-only
			STATUS	current
	DESCRIPTION ""
			::= { mbusAF 4 }

mbusAFStatus		OBJECT-TYPE
			SYNTAX	Gauge
			ACCESS	read-only
			STATUS	current
	DESCRIPTION ""
			::= { mbusAF 5 }

mbusAFVIF00		OBJECT-TYPE
			SYNTAX	INTEGER
			ACCESS	read-only
			STATUS	current
	DESCRIPTION ""
			::= { mbusAF 6 }

mbusAFValue00		OBJECT-TYPE
			SYNTAX	INTEGER
			ACCESS	read-only
			STATUS	current
	DESCRIPTION ""
			::= { mbusAF 7 }

mbusAFVIF01		OBJECT-TYPE
			SYNTAX	INTEGER
			ACCESS	read-only
			STATUS	current
	DESCRIPTION ""
			::= { mbusAF 8 }

mbusAFValue01		OBJECT-TYPE
			SYNTAX	INTEGER
			ACCESS	read-only
			STATUS	current
	DESCRIPTION ""
			::= { mbusAF 9 }

mbusAFVIF02		OBJECT-TYPE
			SYNTAX	INTEGER
			ACCESS	read-only
			STATUS	current
	DESCRIPTION ""
			::= { mbusAF 10 }

mbusAFValue02		OBJECT-TYPE
			SYNTAX	INTEGER
			ACCESS	read-only
			STATUS	current
	DESCRIPTION ""
			::= { mbusAF 11 }

mbusAFVIF03		OBJECT-TYPE
			SYNTAX	INTEGER
			ACCESS	read-only
			STATUS	current
	DESCRIPTION ""
			::= { mbusAF 12 }

mbusAFValue03		OBJECT-TYPE
			SYNTAX	INTEGER
			ACCESS	read-only
			STATUS	current
	DESCRIPTION ""
			::= { mbusAF 13 }

mbusAFVIF04		OBJECT-TYPE
			SYNTAX	INTEGER
			ACCESS	read-only
			STATUS	current
	DESCRIPTION ""
			::= { mbusAF 14 }

mbusAFValue04		OBJECT-TYPE
			SYNTAX	INTEGER
			ACCESS	read-only
			STATUS	current
	DESCRIPTION ""
			::= { mbusAF 15 }

mbusAFVIF05		OBJECT-TYPE
			SYNTAX	INTEGER
			ACCESS	read-only
			STATUS	current
	DESCRIPTION ""
			::= { mbusAF 16 }

mbusAFValue05		OBJECT-TYPE
			SYNTAX	INTEGER
			ACCESS	read-only
			STATUS	current
	DESCRIPTION ""
			::= { mbusAF 17 }

mbusAFVIF06		OBJECT-TYPE
			SYNTAX	INTEGER
			ACCESS	read-only
			STATUS	current
	DESCRIPTION ""
			::= { mbusAF 18 }

mbusAFValue06		OBJECT-TYPE
			SYNTAX	INTEGER
			ACCESS	read-only
			STATUS	current
	DESCRIPTION ""
			::= { mbusAF 19 }

mbusAFVIF07		OBJECT-TYPE
			SYNTAX	INTEGER
			ACCESS	read-only
			STATUS	current
	DESCRIPTION ""
			::= { mbusAF 20 }

mbusAFValue07		OBJECT-TYPE
			SYNTAX	INTEGER
			ACCESS	read-only
			STATUS	current
	DESCRIPTION ""
			::= { mbusAF 21 }

mbusAFVIF08		OBJECT-TYPE
			SYNTAX	INTEGER
			ACCESS	read-only
			STATUS	current
	DESCRIPTION ""
			::= { mbusAF 22 }

mbusAFValue08		OBJECT-TYPE
			SYNTAX	INTEGER
			ACCESS	read-only
			STATUS	current
	DESCRIPTION ""
			::= { mbusAF 23 }

mbusAFVIF09		OBJECT-TYPE
			SYNTAX	INTEGER
			ACCESS	read-only
			STATUS	current
	DESCRIPTION ""
			::= { mbusAF 24 }

mbusAFValue09		OBJECT-TYPE
			SYNTAX	INTEGER
			ACCESS	read-only
			STATUS	current
	DESCRIPTION ""
			::= { mbusAF 25 }

mbusAFVIF0A		OBJECT-TYPE
			SYNTAX	INTEGER
			ACCESS	read-only
			STATUS	current
	DESCRIPTION ""
			::= { mbusAF 26 }

mbusAFValue0A		OBJECT-TYPE
			SYNTAX	INTEGER
			ACCESS	read-only
			STATUS	current
	DESCRIPTION ""
			::= { mbusAF 27 }

mbusAFVIF0B		OBJECT-TYPE
			SYNTAX	INTEGER
			ACCESS	read-only
			STATUS	current
	DESCRIPTION ""
			::= { mbusAF 28 }

mbusAFValue0B		OBJECT-TYPE
			SYNTAX	INTEGER
			ACCESS	read-only
			STATUS	current
	DESCRIPTION ""
			::= { mbusAF 29 }

mbusAFVIF0C		OBJECT-TYPE
			SYNTAX	INTEGER
			ACCESS	read-only
			STATUS	current
	DESCRIPTION ""
			::= { mbusAF 30 }

mbusAFValue0C		OBJECT-TYPE
			SYNTAX	INTEGER
			ACCESS	read-only
			STATUS	current
	DESCRIPTION ""
			::= { mbusAF 31 }

mbusAFVIF0D		OBJECT-TYPE
			SYNTAX	INTEGER
			ACCESS	read-only
			STATUS	current
	DESCRIPTION ""
			::= { mbusAF 32 }

mbusAFValue0D		OBJECT-TYPE
			SYNTAX	INTEGER
			ACCESS	read-only
			STATUS	current
	DESCRIPTION ""
			::= { mbusAF 33 }

mbusAFVIF0E		OBJECT-TYPE
			SYNTAX	INTEGER
			ACCESS	read-only
			STATUS	current
	DESCRIPTION ""
			::= { mbusAF 34 }

mbusAFValue0E		OBJECT-TYPE
			SYNTAX	INTEGER
			ACCESS	read-only
			STATUS	current
	DESCRIPTION ""
			::= { mbusAF 35 }

mbusAFVIF0F		OBJECT-TYPE
			SYNTAX	INTEGER
			ACCESS	read-only
			STATUS	current
	DESCRIPTION ""
			::= { mbusAF 36 }

mbusAFValue0F		OBJECT-TYPE
			SYNTAX	INTEGER
			ACCESS	read-only
			STATUS	current
	DESCRIPTION ""
			::= { mbusAF 37 }

mbusAFVIF10		OBJECT-TYPE
			SYNTAX	INTEGER
			ACCESS	read-only
			STATUS	current
	DESCRIPTION ""
			::= { mbusAF 38 }

mbusAFValue10		OBJECT-TYPE
			SYNTAX	INTEGER
			ACCESS	read-only
			STATUS	current
	DESCRIPTION ""
			::= { mbusAF 39 }

mbusAFVIF11		OBJECT-TYPE
			SYNTAX	INTEGER
			ACCESS	read-only
			STATUS	current
	DESCRIPTION ""
			::= { mbusAF 40 }

mbusAFValue11		OBJECT-TYPE
			SYNTAX	INTEGER
			ACCESS	read-only
			STATUS	current
	DESCRIPTION ""
			::= { mbusAF 41 }

mbusAFVIF12		OBJECT-TYPE
			SYNTAX	INTEGER
			ACCESS	read-only
			STATUS	current
	DESCRIPTION ""
			::= { mbusAF 42 }

mbusAFValue12		OBJECT-TYPE
			SYNTAX	INTEGER
			ACCESS	read-only
			STATUS	current
	DESCRIPTION ""
			::= { mbusAF 43 }

mbusAFVIF13		OBJECT-TYPE
			SYNTAX	INTEGER
			ACCESS	read-only
			STATUS	current
	DESCRIPTION ""
			::= { mbusAF 44 }

mbusAFValue13		OBJECT-TYPE
			SYNTAX	INTEGER
			ACCESS	read-only
			STATUS	current
	DESCRIPTION ""
			::= { mbusAF 45 }

mbusAFVIF14		OBJECT-TYPE
			SYNTAX	INTEGER
			ACCESS	read-only
			STATUS	current
	DESCRIPTION ""
			::= { mbusAF 46 }

mbusAFValue14		OBJECT-TYPE
			SYNTAX	INTEGER
			ACCESS	read-only
			STATUS	current
	DESCRIPTION ""
			::= { mbusAF 47 }

mbusAFVIF15		OBJECT-TYPE
			SYNTAX	INTEGER
			ACCESS	read-only
			STATUS	current
	DESCRIPTION ""
			::= { mbusAF 48 }

mbusAFValue15		OBJECT-TYPE
			SYNTAX	INTEGER
			ACCESS	read-only
			STATUS	current
	DESCRIPTION ""
			::= { mbusAF 49 }

mbusAFVIF16		OBJECT-TYPE
			SYNTAX	INTEGER
			ACCESS	read-only
			STATUS	current
	DESCRIPTION ""
			::= { mbusAF 50 }

mbusAFValue16		OBJECT-TYPE
			SYNTAX	INTEGER
			ACCESS	read-only
			STATUS	current
	DESCRIPTION ""
			::= { mbusAF 51 }

mbusAFVIF17		OBJECT-TYPE
			SYNTAX	INTEGER
			ACCESS	read-only
			STATUS	current
	DESCRIPTION ""
			::= { mbusAF 52 }

mbusAFValue17		OBJECT-TYPE
			SYNTAX	INTEGER
			ACCESS	read-only
			STATUS	current
	DESCRIPTION ""
			::= { mbusAF 53 }

mbusAFVIF18		OBJECT-TYPE
			SYNTAX	INTEGER
			ACCESS	read-only
			STATUS	current
	DESCRIPTION ""
			::= { mbusAF 54 }

mbusAFValue18		OBJECT-TYPE
			SYNTAX	INTEGER
			ACCESS	read-only
			STATUS	current
	DESCRIPTION ""
			::= { mbusAF 55 }

mbusAFVIF19		OBJECT-TYPE
			SYNTAX	INTEGER
			ACCESS	read-only
			STATUS	current
	DESCRIPTION ""
			::= { mbusAF 56 }

mbusAFValue19		OBJECT-TYPE
			SYNTAX	INTEGER
			ACCESS	read-only
			STATUS	current
	DESCRIPTION ""
			::= { mbusAF 57 }

mbusAFVIF1A		OBJECT-TYPE
			SYNTAX	INTEGER
			ACCESS	read-only
			STATUS	current
	DESCRIPTION ""
			::= { mbusAF 58 }

mbusAFValue1A		OBJECT-TYPE
			SYNTAX	INTEGER
			ACCESS	read-only
			STATUS	current
	DESCRIPTION ""
			::= { mbusAF 59 }

mbusAFVIF1B		OBJECT-TYPE
			SYNTAX	INTEGER
			ACCESS	read-only
			STATUS	current
	DESCRIPTION ""
			::= { mbusAF 60 }

mbusAFValue1B		OBJECT-TYPE
			SYNTAX	INTEGER
			ACCESS	read-only
			STATUS	current
	DESCRIPTION ""
			::= { mbusAF 61 }

mbusAFVIF1C		OBJECT-TYPE
			SYNTAX	INTEGER
			ACCESS	read-only
			STATUS	current
	DESCRIPTION ""
			::= { mbusAF 62 }

mbusAFValue1C		OBJECT-TYPE
			SYNTAX	INTEGER
			ACCESS	read-only
			STATUS	current
	DESCRIPTION ""
			::= { mbusAF 63 }

mbusAFVIF1D		OBJECT-TYPE
			SYNTAX	INTEGER
			ACCESS	read-only
			STATUS	current
	DESCRIPTION ""
			::= { mbusAF 64 }

mbusAFValue1D		OBJECT-TYPE
			SYNTAX	INTEGER
			ACCESS	read-only
			STATUS	current
	DESCRIPTION ""
			::= { mbusAF 65 }

mbusAFVIF1E		OBJECT-TYPE
			SYNTAX	INTEGER
			ACCESS	read-only
			STATUS	current
	DESCRIPTION ""
			::= { mbusAF 66 }

mbusAFValue1E		OBJECT-TYPE
			SYNTAX	INTEGER
			ACCESS	read-only
			STATUS	current
	DESCRIPTION ""
			::= { mbusAF 67 }

mbusAFVIF1F		OBJECT-TYPE
			SYNTAX	INTEGER
			ACCESS	read-only
			STATUS	current
	DESCRIPTION ""
			::= { mbusAF 68 }

mbusAFValue1F		OBJECT-TYPE
			SYNTAX	INTEGER
			ACCESS	read-only
			STATUS	current
	DESCRIPTION ""
			::= { mbusAF 69 }

mbusAFVIF20		OBJECT-TYPE
			SYNTAX	INTEGER
			ACCESS	read-only
			STATUS	current
	DESCRIPTION ""
			::= { mbusAF 70 }

mbusAFValue20		OBJECT-TYPE
			SYNTAX	INTEGER
			ACCESS	read-only
			STATUS	current
	DESCRIPTION ""
			::= { mbusAF 71 }

mbusAFVIF21		OBJECT-TYPE
			SYNTAX	INTEGER
			ACCESS	read-only
			STATUS	current
	DESCRIPTION ""
			::= { mbusAF 72 }

mbusAFValue21		OBJECT-TYPE
			SYNTAX	INTEGER
			ACCESS	read-only
			STATUS	current
	DESCRIPTION ""
			::= { mbusAF 73 }

mbusAFVIF22		OBJECT-TYPE
			SYNTAX	INTEGER
			ACCESS	read-only
			STATUS	current
	DESCRIPTION ""
			::= { mbusAF 74 }

mbusAFValue22		OBJECT-TYPE
			SYNTAX	INTEGER
			ACCESS	read-only
			STATUS	current
	DESCRIPTION ""
			::= { mbusAF 75 }

mbusAFVIF23		OBJECT-TYPE
			SYNTAX	INTEGER
			ACCESS	read-only
			STATUS	current
	DESCRIPTION ""
			::= { mbusAF 76 }

mbusAFValue23		OBJECT-TYPE
			SYNTAX	INTEGER
			ACCESS	read-only
			STATUS	current
	DESCRIPTION ""
			::= { mbusAF 77 }

mbusAFVIF24		OBJECT-TYPE
			SYNTAX	INTEGER
			ACCESS	read-only
			STATUS	current
	DESCRIPTION ""
			::= { mbusAF 78 }

mbusAFValue24		OBJECT-TYPE
			SYNTAX	INTEGER
			ACCESS	read-only
			STATUS	current
	DESCRIPTION ""
			::= { mbusAF 79 }

mbusAFVIF25		OBJECT-TYPE
			SYNTAX	INTEGER
			ACCESS	read-only
			STATUS	current
	DESCRIPTION ""
			::= { mbusAF 80 }

mbusAFValue25		OBJECT-TYPE
			SYNTAX	INTEGER
			ACCESS	read-only
			STATUS	current
	DESCRIPTION ""
			::= { mbusAF 81 }

mbusAFVIF26		OBJECT-TYPE
			SYNTAX	INTEGER
			ACCESS	read-only
			STATUS	current
	DESCRIPTION ""
			::= { mbusAF 82 }

mbusAFValue26		OBJECT-TYPE
			SYNTAX	INTEGER
			ACCESS	read-only
			STATUS	current
	DESCRIPTION ""
			::= { mbusAF 83 }

mbusAFVIF27		OBJECT-TYPE
			SYNTAX	INTEGER
			ACCESS	read-only
			STATUS	current
	DESCRIPTION ""
			::= { mbusAF 84 }

mbusAFValue27		OBJECT-TYPE
			SYNTAX	INTEGER
			ACCESS	read-only
			STATUS	current
	DESCRIPTION ""
			::= { mbusAF 85 }

mbusAFVIF28		OBJECT-TYPE
			SYNTAX	INTEGER
			ACCESS	read-only
			STATUS	current
	DESCRIPTION ""
			::= { mbusAF 86 }

mbusAFValue28		OBJECT-TYPE
			SYNTAX	INTEGER
			ACCESS	read-only
			STATUS	current
	DESCRIPTION ""
			::= { mbusAF 87 }

mbusAFVIF29		OBJECT-TYPE
			SYNTAX	INTEGER
			ACCESS	read-only
			STATUS	current
	DESCRIPTION ""
			::= { mbusAF 88 }

mbusAFValue29		OBJECT-TYPE
			SYNTAX	INTEGER
			ACCESS	read-only
			STATUS	current
	DESCRIPTION ""
			::= { mbusAF 89 }

mbusAFVIF2A		OBJECT-TYPE
			SYNTAX	INTEGER
			ACCESS	read-only
			STATUS	current
	DESCRIPTION ""
			::= { mbusAF 90 }

mbusAFValue2A		OBJECT-TYPE
			SYNTAX	INTEGER
			ACCESS	read-only
			STATUS	current
	DESCRIPTION ""
			::= { mbusAF 91 }

mbusAFVIF2B		OBJECT-TYPE
			SYNTAX	INTEGER
			ACCESS	read-only
			STATUS	current
	DESCRIPTION ""
			::= { mbusAF 92 }

mbusAFValue2B		OBJECT-TYPE
			SYNTAX	INTEGER
			ACCESS	read-only
			STATUS	current
	DESCRIPTION ""
			::= { mbusAF 93 }

mbusAFVIF2C		OBJECT-TYPE
			SYNTAX	INTEGER
			ACCESS	read-only
			STATUS	current
	DESCRIPTION ""
			::= { mbusAF 94 }

mbusAFValue2C		OBJECT-TYPE
			SYNTAX	INTEGER
			ACCESS	read-only
			STATUS	current
	DESCRIPTION ""
			::= { mbusAF 95 }

mbusAFVIF2D		OBJECT-TYPE
			SYNTAX	INTEGER
			ACCESS	read-only
			STATUS	current
	DESCRIPTION ""
			::= { mbusAF 96 }

mbusAFValue2D		OBJECT-TYPE
			SYNTAX	INTEGER
			ACCESS	read-only
			STATUS	current
	DESCRIPTION ""
			::= { mbusAF 97 }

mbusAFVIF2E		OBJECT-TYPE
			SYNTAX	INTEGER
			ACCESS	read-only
			STATUS	current
	DESCRIPTION ""
			::= { mbusAF 98 }

mbusAFValue2E		OBJECT-TYPE
			SYNTAX	INTEGER
			ACCESS	read-only
			STATUS	current
	DESCRIPTION ""
			::= { mbusAF 99 }

mbusAFVIF2F		OBJECT-TYPE
			SYNTAX	INTEGER
			ACCESS	read-only
			STATUS	current
	DESCRIPTION ""
			::= { mbusAF 100 }

mbusAFValue2F		OBJECT-TYPE
			SYNTAX	INTEGER
			ACCESS	read-only
			STATUS	current
	DESCRIPTION ""
			::= { mbusAF 101 }

mbusB0			OBJECT IDENTIFIER ::= { mbus 176 }

mbusB0IdNumber		OBJECT-TYPE
			SYNTAX	Gauge
			ACCESS	read-only
			STATUS	current
	DESCRIPTION ""
			::= { mbusB0 1 }

mbusB0Manufacturer	OBJECT-TYPE
			SYNTAX	Gauge
			ACCESS	read-only
			STATUS	current
	DESCRIPTION ""
			::= { mbusB0 2 }

mbusB0Version		OBJECT-TYPE
			SYNTAX	Gauge
			ACCESS	read-only
			STATUS	current
	DESCRIPTION ""
			::= { mbusB0 3 }

mbusB0Medium		OBJECT-TYPE
			SYNTAX	Gauge
			ACCESS	read-only
			STATUS	current
	DESCRIPTION ""
			::= { mbusB0 4 }

mbusB0Status		OBJECT-TYPE
			SYNTAX	Gauge
			ACCESS	read-only
			STATUS	current
	DESCRIPTION ""
			::= { mbusB0 5 }

mbusB0VIF00		OBJECT-TYPE
			SYNTAX	INTEGER
			ACCESS	read-only
			STATUS	current
	DESCRIPTION ""
			::= { mbusB0 6 }

mbusB0Value00		OBJECT-TYPE
			SYNTAX	INTEGER
			ACCESS	read-only
			STATUS	current
	DESCRIPTION ""
			::= { mbusB0 7 }

mbusB0VIF01		OBJECT-TYPE
			SYNTAX	INTEGER
			ACCESS	read-only
			STATUS	current
	DESCRIPTION ""
			::= { mbusB0 8 }

mbusB0Value01		OBJECT-TYPE
			SYNTAX	INTEGER
			ACCESS	read-only
			STATUS	current
	DESCRIPTION ""
			::= { mbusB0 9 }

mbusB0VIF02		OBJECT-TYPE
			SYNTAX	INTEGER
			ACCESS	read-only
			STATUS	current
	DESCRIPTION ""
			::= { mbusB0 10 }

mbusB0Value02		OBJECT-TYPE
			SYNTAX	INTEGER
			ACCESS	read-only
			STATUS	current
	DESCRIPTION ""
			::= { mbusB0 11 }

mbusB0VIF03		OBJECT-TYPE
			SYNTAX	INTEGER
			ACCESS	read-only
			STATUS	current
	DESCRIPTION ""
			::= { mbusB0 12 }

mbusB0Value03		OBJECT-TYPE
			SYNTAX	INTEGER
			ACCESS	read-only
			STATUS	current
	DESCRIPTION ""
			::= { mbusB0 13 }

mbusB0VIF04		OBJECT-TYPE
			SYNTAX	INTEGER
			ACCESS	read-only
			STATUS	current
	DESCRIPTION ""
			::= { mbusB0 14 }

mbusB0Value04		OBJECT-TYPE
			SYNTAX	INTEGER
			ACCESS	read-only
			STATUS	current
	DESCRIPTION ""
			::= { mbusB0 15 }

mbusB0VIF05		OBJECT-TYPE
			SYNTAX	INTEGER
			ACCESS	read-only
			STATUS	current
	DESCRIPTION ""
			::= { mbusB0 16 }

mbusB0Value05		OBJECT-TYPE
			SYNTAX	INTEGER
			ACCESS	read-only
			STATUS	current
	DESCRIPTION ""
			::= { mbusB0 17 }

mbusB0VIF06		OBJECT-TYPE
			SYNTAX	INTEGER
			ACCESS	read-only
			STATUS	current
	DESCRIPTION ""
			::= { mbusB0 18 }

mbusB0Value06		OBJECT-TYPE
			SYNTAX	INTEGER
			ACCESS	read-only
			STATUS	current
	DESCRIPTION ""
			::= { mbusB0 19 }

mbusB0VIF07		OBJECT-TYPE
			SYNTAX	INTEGER
			ACCESS	read-only
			STATUS	current
	DESCRIPTION ""
			::= { mbusB0 20 }

mbusB0Value07		OBJECT-TYPE
			SYNTAX	INTEGER
			ACCESS	read-only
			STATUS	current
	DESCRIPTION ""
			::= { mbusB0 21 }

mbusB0VIF08		OBJECT-TYPE
			SYNTAX	INTEGER
			ACCESS	read-only
			STATUS	current
	DESCRIPTION ""
			::= { mbusB0 22 }

mbusB0Value08		OBJECT-TYPE
			SYNTAX	INTEGER
			ACCESS	read-only
			STATUS	current
	DESCRIPTION ""
			::= { mbusB0 23 }

mbusB0VIF09		OBJECT-TYPE
			SYNTAX	INTEGER
			ACCESS	read-only
			STATUS	current
	DESCRIPTION ""
			::= { mbusB0 24 }

mbusB0Value09		OBJECT-TYPE
			SYNTAX	INTEGER
			ACCESS	read-only
			STATUS	current
	DESCRIPTION ""
			::= { mbusB0 25 }

mbusB0VIF0A		OBJECT-TYPE
			SYNTAX	INTEGER
			ACCESS	read-only
			STATUS	current
	DESCRIPTION ""
			::= { mbusB0 26 }

mbusB0Value0A		OBJECT-TYPE
			SYNTAX	INTEGER
			ACCESS	read-only
			STATUS	current
	DESCRIPTION ""
			::= { mbusB0 27 }

mbusB0VIF0B		OBJECT-TYPE
			SYNTAX	INTEGER
			ACCESS	read-only
			STATUS	current
	DESCRIPTION ""
			::= { mbusB0 28 }

mbusB0Value0B		OBJECT-TYPE
			SYNTAX	INTEGER
			ACCESS	read-only
			STATUS	current
	DESCRIPTION ""
			::= { mbusB0 29 }

mbusB0VIF0C		OBJECT-TYPE
			SYNTAX	INTEGER
			ACCESS	read-only
			STATUS	current
	DESCRIPTION ""
			::= { mbusB0 30 }

mbusB0Value0C		OBJECT-TYPE
			SYNTAX	INTEGER
			ACCESS	read-only
			STATUS	current
	DESCRIPTION ""
			::= { mbusB0 31 }

mbusB0VIF0D		OBJECT-TYPE
			SYNTAX	INTEGER
			ACCESS	read-only
			STATUS	current
	DESCRIPTION ""
			::= { mbusB0 32 }

mbusB0Value0D		OBJECT-TYPE
			SYNTAX	INTEGER
			ACCESS	read-only
			STATUS	current
	DESCRIPTION ""
			::= { mbusB0 33 }

mbusB0VIF0E		OBJECT-TYPE
			SYNTAX	INTEGER
			ACCESS	read-only
			STATUS	current
	DESCRIPTION ""
			::= { mbusB0 34 }

mbusB0Value0E		OBJECT-TYPE
			SYNTAX	INTEGER
			ACCESS	read-only
			STATUS	current
	DESCRIPTION ""
			::= { mbusB0 35 }

mbusB0VIF0F		OBJECT-TYPE
			SYNTAX	INTEGER
			ACCESS	read-only
			STATUS	current
	DESCRIPTION ""
			::= { mbusB0 36 }

mbusB0Value0F		OBJECT-TYPE
			SYNTAX	INTEGER
			ACCESS	read-only
			STATUS	current
	DESCRIPTION ""
			::= { mbusB0 37 }

mbusB0VIF10		OBJECT-TYPE
			SYNTAX	INTEGER
			ACCESS	read-only
			STATUS	current
	DESCRIPTION ""
			::= { mbusB0 38 }

mbusB0Value10		OBJECT-TYPE
			SYNTAX	INTEGER
			ACCESS	read-only
			STATUS	current
	DESCRIPTION ""
			::= { mbusB0 39 }

mbusB0VIF11		OBJECT-TYPE
			SYNTAX	INTEGER
			ACCESS	read-only
			STATUS	current
	DESCRIPTION ""
			::= { mbusB0 40 }

mbusB0Value11		OBJECT-TYPE
			SYNTAX	INTEGER
			ACCESS	read-only
			STATUS	current
	DESCRIPTION ""
			::= { mbusB0 41 }

mbusB0VIF12		OBJECT-TYPE
			SYNTAX	INTEGER
			ACCESS	read-only
			STATUS	current
	DESCRIPTION ""
			::= { mbusB0 42 }

mbusB0Value12		OBJECT-TYPE
			SYNTAX	INTEGER
			ACCESS	read-only
			STATUS	current
	DESCRIPTION ""
			::= { mbusB0 43 }

mbusB0VIF13		OBJECT-TYPE
			SYNTAX	INTEGER
			ACCESS	read-only
			STATUS	current
	DESCRIPTION ""
			::= { mbusB0 44 }

mbusB0Value13		OBJECT-TYPE
			SYNTAX	INTEGER
			ACCESS	read-only
			STATUS	current
	DESCRIPTION ""
			::= { mbusB0 45 }

mbusB0VIF14		OBJECT-TYPE
			SYNTAX	INTEGER
			ACCESS	read-only
			STATUS	current
	DESCRIPTION ""
			::= { mbusB0 46 }

mbusB0Value14		OBJECT-TYPE
			SYNTAX	INTEGER
			ACCESS	read-only
			STATUS	current
	DESCRIPTION ""
			::= { mbusB0 47 }

mbusB0VIF15		OBJECT-TYPE
			SYNTAX	INTEGER
			ACCESS	read-only
			STATUS	current
	DESCRIPTION ""
			::= { mbusB0 48 }

mbusB0Value15		OBJECT-TYPE
			SYNTAX	INTEGER
			ACCESS	read-only
			STATUS	current
	DESCRIPTION ""
			::= { mbusB0 49 }

mbusB0VIF16		OBJECT-TYPE
			SYNTAX	INTEGER
			ACCESS	read-only
			STATUS	current
	DESCRIPTION ""
			::= { mbusB0 50 }

mbusB0Value16		OBJECT-TYPE
			SYNTAX	INTEGER
			ACCESS	read-only
			STATUS	current
	DESCRIPTION ""
			::= { mbusB0 51 }

mbusB0VIF17		OBJECT-TYPE
			SYNTAX	INTEGER
			ACCESS	read-only
			STATUS	current
	DESCRIPTION ""
			::= { mbusB0 52 }

mbusB0Value17		OBJECT-TYPE
			SYNTAX	INTEGER
			ACCESS	read-only
			STATUS	current
	DESCRIPTION ""
			::= { mbusB0 53 }

mbusB0VIF18		OBJECT-TYPE
			SYNTAX	INTEGER
			ACCESS	read-only
			STATUS	current
	DESCRIPTION ""
			::= { mbusB0 54 }

mbusB0Value18		OBJECT-TYPE
			SYNTAX	INTEGER
			ACCESS	read-only
			STATUS	current
	DESCRIPTION ""
			::= { mbusB0 55 }

mbusB0VIF19		OBJECT-TYPE
			SYNTAX	INTEGER
			ACCESS	read-only
			STATUS	current
	DESCRIPTION ""
			::= { mbusB0 56 }

mbusB0Value19		OBJECT-TYPE
			SYNTAX	INTEGER
			ACCESS	read-only
			STATUS	current
	DESCRIPTION ""
			::= { mbusB0 57 }

mbusB0VIF1A		OBJECT-TYPE
			SYNTAX	INTEGER
			ACCESS	read-only
			STATUS	current
	DESCRIPTION ""
			::= { mbusB0 58 }

mbusB0Value1A		OBJECT-TYPE
			SYNTAX	INTEGER
			ACCESS	read-only
			STATUS	current
	DESCRIPTION ""
			::= { mbusB0 59 }

mbusB0VIF1B		OBJECT-TYPE
			SYNTAX	INTEGER
			ACCESS	read-only
			STATUS	current
	DESCRIPTION ""
			::= { mbusB0 60 }

mbusB0Value1B		OBJECT-TYPE
			SYNTAX	INTEGER
			ACCESS	read-only
			STATUS	current
	DESCRIPTION ""
			::= { mbusB0 61 }

mbusB0VIF1C		OBJECT-TYPE
			SYNTAX	INTEGER
			ACCESS	read-only
			STATUS	current
	DESCRIPTION ""
			::= { mbusB0 62 }

mbusB0Value1C		OBJECT-TYPE
			SYNTAX	INTEGER
			ACCESS	read-only
			STATUS	current
	DESCRIPTION ""
			::= { mbusB0 63 }

mbusB0VIF1D		OBJECT-TYPE
			SYNTAX	INTEGER
			ACCESS	read-only
			STATUS	current
	DESCRIPTION ""
			::= { mbusB0 64 }

mbusB0Value1D		OBJECT-TYPE
			SYNTAX	INTEGER
			ACCESS	read-only
			STATUS	current
	DESCRIPTION ""
			::= { mbusB0 65 }

mbusB0VIF1E		OBJECT-TYPE
			SYNTAX	INTEGER
			ACCESS	read-only
			STATUS	current
	DESCRIPTION ""
			::= { mbusB0 66 }

mbusB0Value1E		OBJECT-TYPE
			SYNTAX	INTEGER
			ACCESS	read-only
			STATUS	current
	DESCRIPTION ""
			::= { mbusB0 67 }

mbusB0VIF1F		OBJECT-TYPE
			SYNTAX	INTEGER
			ACCESS	read-only
			STATUS	current
	DESCRIPTION ""
			::= { mbusB0 68 }

mbusB0Value1F		OBJECT-TYPE
			SYNTAX	INTEGER
			ACCESS	read-only
			STATUS	current
	DESCRIPTION ""
			::= { mbusB0 69 }

mbusB0VIF20		OBJECT-TYPE
			SYNTAX	INTEGER
			ACCESS	read-only
			STATUS	current
	DESCRIPTION ""
			::= { mbusB0 70 }

mbusB0Value20		OBJECT-TYPE
			SYNTAX	INTEGER
			ACCESS	read-only
			STATUS	current
	DESCRIPTION ""
			::= { mbusB0 71 }

mbusB0VIF21		OBJECT-TYPE
			SYNTAX	INTEGER
			ACCESS	read-only
			STATUS	current
	DESCRIPTION ""
			::= { mbusB0 72 }

mbusB0Value21		OBJECT-TYPE
			SYNTAX	INTEGER
			ACCESS	read-only
			STATUS	current
	DESCRIPTION ""
			::= { mbusB0 73 }

mbusB0VIF22		OBJECT-TYPE
			SYNTAX	INTEGER
			ACCESS	read-only
			STATUS	current
	DESCRIPTION ""
			::= { mbusB0 74 }

mbusB0Value22		OBJECT-TYPE
			SYNTAX	INTEGER
			ACCESS	read-only
			STATUS	current
	DESCRIPTION ""
			::= { mbusB0 75 }

mbusB0VIF23		OBJECT-TYPE
			SYNTAX	INTEGER
			ACCESS	read-only
			STATUS	current
	DESCRIPTION ""
			::= { mbusB0 76 }

mbusB0Value23		OBJECT-TYPE
			SYNTAX	INTEGER
			ACCESS	read-only
			STATUS	current
	DESCRIPTION ""
			::= { mbusB0 77 }

mbusB0VIF24		OBJECT-TYPE
			SYNTAX	INTEGER
			ACCESS	read-only
			STATUS	current
	DESCRIPTION ""
			::= { mbusB0 78 }

mbusB0Value24		OBJECT-TYPE
			SYNTAX	INTEGER
			ACCESS	read-only
			STATUS	current
	DESCRIPTION ""
			::= { mbusB0 79 }

mbusB0VIF25		OBJECT-TYPE
			SYNTAX	INTEGER
			ACCESS	read-only
			STATUS	current
	DESCRIPTION ""
			::= { mbusB0 80 }

mbusB0Value25		OBJECT-TYPE
			SYNTAX	INTEGER
			ACCESS	read-only
			STATUS	current
	DESCRIPTION ""
			::= { mbusB0 81 }

mbusB0VIF26		OBJECT-TYPE
			SYNTAX	INTEGER
			ACCESS	read-only
			STATUS	current
	DESCRIPTION ""
			::= { mbusB0 82 }

mbusB0Value26		OBJECT-TYPE
			SYNTAX	INTEGER
			ACCESS	read-only
			STATUS	current
	DESCRIPTION ""
			::= { mbusB0 83 }

mbusB0VIF27		OBJECT-TYPE
			SYNTAX	INTEGER
			ACCESS	read-only
			STATUS	current
	DESCRIPTION ""
			::= { mbusB0 84 }

mbusB0Value27		OBJECT-TYPE
			SYNTAX	INTEGER
			ACCESS	read-only
			STATUS	current
	DESCRIPTION ""
			::= { mbusB0 85 }

mbusB0VIF28		OBJECT-TYPE
			SYNTAX	INTEGER
			ACCESS	read-only
			STATUS	current
	DESCRIPTION ""
			::= { mbusB0 86 }

mbusB0Value28		OBJECT-TYPE
			SYNTAX	INTEGER
			ACCESS	read-only
			STATUS	current
	DESCRIPTION ""
			::= { mbusB0 87 }

mbusB0VIF29		OBJECT-TYPE
			SYNTAX	INTEGER
			ACCESS	read-only
			STATUS	current
	DESCRIPTION ""
			::= { mbusB0 88 }

mbusB0Value29		OBJECT-TYPE
			SYNTAX	INTEGER
			ACCESS	read-only
			STATUS	current
	DESCRIPTION ""
			::= { mbusB0 89 }

mbusB0VIF2A		OBJECT-TYPE
			SYNTAX	INTEGER
			ACCESS	read-only
			STATUS	current
	DESCRIPTION ""
			::= { mbusB0 90 }

mbusB0Value2A		OBJECT-TYPE
			SYNTAX	INTEGER
			ACCESS	read-only
			STATUS	current
	DESCRIPTION ""
			::= { mbusB0 91 }

mbusB0VIF2B		OBJECT-TYPE
			SYNTAX	INTEGER
			ACCESS	read-only
			STATUS	current
	DESCRIPTION ""
			::= { mbusB0 92 }

mbusB0Value2B		OBJECT-TYPE
			SYNTAX	INTEGER
			ACCESS	read-only
			STATUS	current
	DESCRIPTION ""
			::= { mbusB0 93 }

mbusB0VIF2C		OBJECT-TYPE
			SYNTAX	INTEGER
			ACCESS	read-only
			STATUS	current
	DESCRIPTION ""
			::= { mbusB0 94 }

mbusB0Value2C		OBJECT-TYPE
			SYNTAX	INTEGER
			ACCESS	read-only
			STATUS	current
	DESCRIPTION ""
			::= { mbusB0 95 }

mbusB0VIF2D		OBJECT-TYPE
			SYNTAX	INTEGER
			ACCESS	read-only
			STATUS	current
	DESCRIPTION ""
			::= { mbusB0 96 }

mbusB0Value2D		OBJECT-TYPE
			SYNTAX	INTEGER
			ACCESS	read-only
			STATUS	current
	DESCRIPTION ""
			::= { mbusB0 97 }

mbusB0VIF2E		OBJECT-TYPE
			SYNTAX	INTEGER
			ACCESS	read-only
			STATUS	current
	DESCRIPTION ""
			::= { mbusB0 98 }

mbusB0Value2E		OBJECT-TYPE
			SYNTAX	INTEGER
			ACCESS	read-only
			STATUS	current
	DESCRIPTION ""
			::= { mbusB0 99 }

mbusB0VIF2F		OBJECT-TYPE
			SYNTAX	INTEGER
			ACCESS	read-only
			STATUS	current
	DESCRIPTION ""
			::= { mbusB0 100 }

mbusB0Value2F		OBJECT-TYPE
			SYNTAX	INTEGER
			ACCESS	read-only
			STATUS	current
	DESCRIPTION ""
			::= { mbusB0 101 }

mbusB1			OBJECT IDENTIFIER ::= { mbus 177 }

mbusB1IdNumber		OBJECT-TYPE
			SYNTAX	Gauge
			ACCESS	read-only
			STATUS	current
	DESCRIPTION ""
			::= { mbusB1 1 }

mbusB1Manufacturer	OBJECT-TYPE
			SYNTAX	Gauge
			ACCESS	read-only
			STATUS	current
	DESCRIPTION ""
			::= { mbusB1 2 }

mbusB1Version		OBJECT-TYPE
			SYNTAX	Gauge
			ACCESS	read-only
			STATUS	current
	DESCRIPTION ""
			::= { mbusB1 3 }

mbusB1Medium		OBJECT-TYPE
			SYNTAX	Gauge
			ACCESS	read-only
			STATUS	current
	DESCRIPTION ""
			::= { mbusB1 4 }

mbusB1Status		OBJECT-TYPE
			SYNTAX	Gauge
			ACCESS	read-only
			STATUS	current
	DESCRIPTION ""
			::= { mbusB1 5 }

mbusB1VIF00		OBJECT-TYPE
			SYNTAX	INTEGER
			ACCESS	read-only
			STATUS	current
	DESCRIPTION ""
			::= { mbusB1 6 }

mbusB1Value00		OBJECT-TYPE
			SYNTAX	INTEGER
			ACCESS	read-only
			STATUS	current
	DESCRIPTION ""
			::= { mbusB1 7 }

mbusB1VIF01		OBJECT-TYPE
			SYNTAX	INTEGER
			ACCESS	read-only
			STATUS	current
	DESCRIPTION ""
			::= { mbusB1 8 }

mbusB1Value01		OBJECT-TYPE
			SYNTAX	INTEGER
			ACCESS	read-only
			STATUS	current
	DESCRIPTION ""
			::= { mbusB1 9 }

mbusB1VIF02		OBJECT-TYPE
			SYNTAX	INTEGER
			ACCESS	read-only
			STATUS	current
	DESCRIPTION ""
			::= { mbusB1 10 }

mbusB1Value02		OBJECT-TYPE
			SYNTAX	INTEGER
			ACCESS	read-only
			STATUS	current
	DESCRIPTION ""
			::= { mbusB1 11 }

mbusB1VIF03		OBJECT-TYPE
			SYNTAX	INTEGER
			ACCESS	read-only
			STATUS	current
	DESCRIPTION ""
			::= { mbusB1 12 }

mbusB1Value03		OBJECT-TYPE
			SYNTAX	INTEGER
			ACCESS	read-only
			STATUS	current
	DESCRIPTION ""
			::= { mbusB1 13 }

mbusB1VIF04		OBJECT-TYPE
			SYNTAX	INTEGER
			ACCESS	read-only
			STATUS	current
	DESCRIPTION ""
			::= { mbusB1 14 }

mbusB1Value04		OBJECT-TYPE
			SYNTAX	INTEGER
			ACCESS	read-only
			STATUS	current
	DESCRIPTION ""
			::= { mbusB1 15 }

mbusB1VIF05		OBJECT-TYPE
			SYNTAX	INTEGER
			ACCESS	read-only
			STATUS	current
	DESCRIPTION ""
			::= { mbusB1 16 }

mbusB1Value05		OBJECT-TYPE
			SYNTAX	INTEGER
			ACCESS	read-only
			STATUS	current
	DESCRIPTION ""
			::= { mbusB1 17 }

mbusB1VIF06		OBJECT-TYPE
			SYNTAX	INTEGER
			ACCESS	read-only
			STATUS	current
	DESCRIPTION ""
			::= { mbusB1 18 }

mbusB1Value06		OBJECT-TYPE
			SYNTAX	INTEGER
			ACCESS	read-only
			STATUS	current
	DESCRIPTION ""
			::= { mbusB1 19 }

mbusB1VIF07		OBJECT-TYPE
			SYNTAX	INTEGER
			ACCESS	read-only
			STATUS	current
	DESCRIPTION ""
			::= { mbusB1 20 }

mbusB1Value07		OBJECT-TYPE
			SYNTAX	INTEGER
			ACCESS	read-only
			STATUS	current
	DESCRIPTION ""
			::= { mbusB1 21 }

mbusB1VIF08		OBJECT-TYPE
			SYNTAX	INTEGER
			ACCESS	read-only
			STATUS	current
	DESCRIPTION ""
			::= { mbusB1 22 }

mbusB1Value08		OBJECT-TYPE
			SYNTAX	INTEGER
			ACCESS	read-only
			STATUS	current
	DESCRIPTION ""
			::= { mbusB1 23 }

mbusB1VIF09		OBJECT-TYPE
			SYNTAX	INTEGER
			ACCESS	read-only
			STATUS	current
	DESCRIPTION ""
			::= { mbusB1 24 }

mbusB1Value09		OBJECT-TYPE
			SYNTAX	INTEGER
			ACCESS	read-only
			STATUS	current
	DESCRIPTION ""
			::= { mbusB1 25 }

mbusB1VIF0A		OBJECT-TYPE
			SYNTAX	INTEGER
			ACCESS	read-only
			STATUS	current
	DESCRIPTION ""
			::= { mbusB1 26 }

mbusB1Value0A		OBJECT-TYPE
			SYNTAX	INTEGER
			ACCESS	read-only
			STATUS	current
	DESCRIPTION ""
			::= { mbusB1 27 }

mbusB1VIF0B		OBJECT-TYPE
			SYNTAX	INTEGER
			ACCESS	read-only
			STATUS	current
	DESCRIPTION ""
			::= { mbusB1 28 }

mbusB1Value0B		OBJECT-TYPE
			SYNTAX	INTEGER
			ACCESS	read-only
			STATUS	current
	DESCRIPTION ""
			::= { mbusB1 29 }

mbusB1VIF0C		OBJECT-TYPE
			SYNTAX	INTEGER
			ACCESS	read-only
			STATUS	current
	DESCRIPTION ""
			::= { mbusB1 30 }

mbusB1Value0C		OBJECT-TYPE
			SYNTAX	INTEGER
			ACCESS	read-only
			STATUS	current
	DESCRIPTION ""
			::= { mbusB1 31 }

mbusB1VIF0D		OBJECT-TYPE
			SYNTAX	INTEGER
			ACCESS	read-only
			STATUS	current
	DESCRIPTION ""
			::= { mbusB1 32 }

mbusB1Value0D		OBJECT-TYPE
			SYNTAX	INTEGER
			ACCESS	read-only
			STATUS	current
	DESCRIPTION ""
			::= { mbusB1 33 }

mbusB1VIF0E		OBJECT-TYPE
			SYNTAX	INTEGER
			ACCESS	read-only
			STATUS	current
	DESCRIPTION ""
			::= { mbusB1 34 }

mbusB1Value0E		OBJECT-TYPE
			SYNTAX	INTEGER
			ACCESS	read-only
			STATUS	current
	DESCRIPTION ""
			::= { mbusB1 35 }

mbusB1VIF0F		OBJECT-TYPE
			SYNTAX	INTEGER
			ACCESS	read-only
			STATUS	current
	DESCRIPTION ""
			::= { mbusB1 36 }

mbusB1Value0F		OBJECT-TYPE
			SYNTAX	INTEGER
			ACCESS	read-only
			STATUS	current
	DESCRIPTION ""
			::= { mbusB1 37 }

mbusB1VIF10		OBJECT-TYPE
			SYNTAX	INTEGER
			ACCESS	read-only
			STATUS	current
	DESCRIPTION ""
			::= { mbusB1 38 }

mbusB1Value10		OBJECT-TYPE
			SYNTAX	INTEGER
			ACCESS	read-only
			STATUS	current
	DESCRIPTION ""
			::= { mbusB1 39 }

mbusB1VIF11		OBJECT-TYPE
			SYNTAX	INTEGER
			ACCESS	read-only
			STATUS	current
	DESCRIPTION ""
			::= { mbusB1 40 }

mbusB1Value11		OBJECT-TYPE
			SYNTAX	INTEGER
			ACCESS	read-only
			STATUS	current
	DESCRIPTION ""
			::= { mbusB1 41 }

mbusB1VIF12		OBJECT-TYPE
			SYNTAX	INTEGER
			ACCESS	read-only
			STATUS	current
	DESCRIPTION ""
			::= { mbusB1 42 }

mbusB1Value12		OBJECT-TYPE
			SYNTAX	INTEGER
			ACCESS	read-only
			STATUS	current
	DESCRIPTION ""
			::= { mbusB1 43 }

mbusB1VIF13		OBJECT-TYPE
			SYNTAX	INTEGER
			ACCESS	read-only
			STATUS	current
	DESCRIPTION ""
			::= { mbusB1 44 }

mbusB1Value13		OBJECT-TYPE
			SYNTAX	INTEGER
			ACCESS	read-only
			STATUS	current
	DESCRIPTION ""
			::= { mbusB1 45 }

mbusB1VIF14		OBJECT-TYPE
			SYNTAX	INTEGER
			ACCESS	read-only
			STATUS	current
	DESCRIPTION ""
			::= { mbusB1 46 }

mbusB1Value14		OBJECT-TYPE
			SYNTAX	INTEGER
			ACCESS	read-only
			STATUS	current
	DESCRIPTION ""
			::= { mbusB1 47 }

mbusB1VIF15		OBJECT-TYPE
			SYNTAX	INTEGER
			ACCESS	read-only
			STATUS	current
	DESCRIPTION ""
			::= { mbusB1 48 }

mbusB1Value15		OBJECT-TYPE
			SYNTAX	INTEGER
			ACCESS	read-only
			STATUS	current
	DESCRIPTION ""
			::= { mbusB1 49 }

mbusB1VIF16		OBJECT-TYPE
			SYNTAX	INTEGER
			ACCESS	read-only
			STATUS	current
	DESCRIPTION ""
			::= { mbusB1 50 }

mbusB1Value16		OBJECT-TYPE
			SYNTAX	INTEGER
			ACCESS	read-only
			STATUS	current
	DESCRIPTION ""
			::= { mbusB1 51 }

mbusB1VIF17		OBJECT-TYPE
			SYNTAX	INTEGER
			ACCESS	read-only
			STATUS	current
	DESCRIPTION ""
			::= { mbusB1 52 }

mbusB1Value17		OBJECT-TYPE
			SYNTAX	INTEGER
			ACCESS	read-only
			STATUS	current
	DESCRIPTION ""
			::= { mbusB1 53 }

mbusB1VIF18		OBJECT-TYPE
			SYNTAX	INTEGER
			ACCESS	read-only
			STATUS	current
	DESCRIPTION ""
			::= { mbusB1 54 }

mbusB1Value18		OBJECT-TYPE
			SYNTAX	INTEGER
			ACCESS	read-only
			STATUS	current
	DESCRIPTION ""
			::= { mbusB1 55 }

mbusB1VIF19		OBJECT-TYPE
			SYNTAX	INTEGER
			ACCESS	read-only
			STATUS	current
	DESCRIPTION ""
			::= { mbusB1 56 }

mbusB1Value19		OBJECT-TYPE
			SYNTAX	INTEGER
			ACCESS	read-only
			STATUS	current
	DESCRIPTION ""
			::= { mbusB1 57 }

mbusB1VIF1A		OBJECT-TYPE
			SYNTAX	INTEGER
			ACCESS	read-only
			STATUS	current
	DESCRIPTION ""
			::= { mbusB1 58 }

mbusB1Value1A		OBJECT-TYPE
			SYNTAX	INTEGER
			ACCESS	read-only
			STATUS	current
	DESCRIPTION ""
			::= { mbusB1 59 }

mbusB1VIF1B		OBJECT-TYPE
			SYNTAX	INTEGER
			ACCESS	read-only
			STATUS	current
	DESCRIPTION ""
			::= { mbusB1 60 }

mbusB1Value1B		OBJECT-TYPE
			SYNTAX	INTEGER
			ACCESS	read-only
			STATUS	current
	DESCRIPTION ""
			::= { mbusB1 61 }

mbusB1VIF1C		OBJECT-TYPE
			SYNTAX	INTEGER
			ACCESS	read-only
			STATUS	current
	DESCRIPTION ""
			::= { mbusB1 62 }

mbusB1Value1C		OBJECT-TYPE
			SYNTAX	INTEGER
			ACCESS	read-only
			STATUS	current
	DESCRIPTION ""
			::= { mbusB1 63 }

mbusB1VIF1D		OBJECT-TYPE
			SYNTAX	INTEGER
			ACCESS	read-only
			STATUS	current
	DESCRIPTION ""
			::= { mbusB1 64 }

mbusB1Value1D		OBJECT-TYPE
			SYNTAX	INTEGER
			ACCESS	read-only
			STATUS	current
	DESCRIPTION ""
			::= { mbusB1 65 }

mbusB1VIF1E		OBJECT-TYPE
			SYNTAX	INTEGER
			ACCESS	read-only
			STATUS	current
	DESCRIPTION ""
			::= { mbusB1 66 }

mbusB1Value1E		OBJECT-TYPE
			SYNTAX	INTEGER
			ACCESS	read-only
			STATUS	current
	DESCRIPTION ""
			::= { mbusB1 67 }

mbusB1VIF1F		OBJECT-TYPE
			SYNTAX	INTEGER
			ACCESS	read-only
			STATUS	current
	DESCRIPTION ""
			::= { mbusB1 68 }

mbusB1Value1F		OBJECT-TYPE
			SYNTAX	INTEGER
			ACCESS	read-only
			STATUS	current
	DESCRIPTION ""
			::= { mbusB1 69 }

mbusB1VIF20		OBJECT-TYPE
			SYNTAX	INTEGER
			ACCESS	read-only
			STATUS	current
	DESCRIPTION ""
			::= { mbusB1 70 }

mbusB1Value20		OBJECT-TYPE
			SYNTAX	INTEGER
			ACCESS	read-only
			STATUS	current
	DESCRIPTION ""
			::= { mbusB1 71 }

mbusB1VIF21		OBJECT-TYPE
			SYNTAX	INTEGER
			ACCESS	read-only
			STATUS	current
	DESCRIPTION ""
			::= { mbusB1 72 }

mbusB1Value21		OBJECT-TYPE
			SYNTAX	INTEGER
			ACCESS	read-only
			STATUS	current
	DESCRIPTION ""
			::= { mbusB1 73 }

mbusB1VIF22		OBJECT-TYPE
			SYNTAX	INTEGER
			ACCESS	read-only
			STATUS	current
	DESCRIPTION ""
			::= { mbusB1 74 }

mbusB1Value22		OBJECT-TYPE
			SYNTAX	INTEGER
			ACCESS	read-only
			STATUS	current
	DESCRIPTION ""
			::= { mbusB1 75 }

mbusB1VIF23		OBJECT-TYPE
			SYNTAX	INTEGER
			ACCESS	read-only
			STATUS	current
	DESCRIPTION ""
			::= { mbusB1 76 }

mbusB1Value23		OBJECT-TYPE
			SYNTAX	INTEGER
			ACCESS	read-only
			STATUS	current
	DESCRIPTION ""
			::= { mbusB1 77 }

mbusB1VIF24		OBJECT-TYPE
			SYNTAX	INTEGER
			ACCESS	read-only
			STATUS	current
	DESCRIPTION ""
			::= { mbusB1 78 }

mbusB1Value24		OBJECT-TYPE
			SYNTAX	INTEGER
			ACCESS	read-only
			STATUS	current
	DESCRIPTION ""
			::= { mbusB1 79 }

mbusB1VIF25		OBJECT-TYPE
			SYNTAX	INTEGER
			ACCESS	read-only
			STATUS	current
	DESCRIPTION ""
			::= { mbusB1 80 }

mbusB1Value25		OBJECT-TYPE
			SYNTAX	INTEGER
			ACCESS	read-only
			STATUS	current
	DESCRIPTION ""
			::= { mbusB1 81 }

mbusB1VIF26		OBJECT-TYPE
			SYNTAX	INTEGER
			ACCESS	read-only
			STATUS	current
	DESCRIPTION ""
			::= { mbusB1 82 }

mbusB1Value26		OBJECT-TYPE
			SYNTAX	INTEGER
			ACCESS	read-only
			STATUS	current
	DESCRIPTION ""
			::= { mbusB1 83 }

mbusB1VIF27		OBJECT-TYPE
			SYNTAX	INTEGER
			ACCESS	read-only
			STATUS	current
	DESCRIPTION ""
			::= { mbusB1 84 }

mbusB1Value27		OBJECT-TYPE
			SYNTAX	INTEGER
			ACCESS	read-only
			STATUS	current
	DESCRIPTION ""
			::= { mbusB1 85 }

mbusB1VIF28		OBJECT-TYPE
			SYNTAX	INTEGER
			ACCESS	read-only
			STATUS	current
	DESCRIPTION ""
			::= { mbusB1 86 }

mbusB1Value28		OBJECT-TYPE
			SYNTAX	INTEGER
			ACCESS	read-only
			STATUS	current
	DESCRIPTION ""
			::= { mbusB1 87 }

mbusB1VIF29		OBJECT-TYPE
			SYNTAX	INTEGER
			ACCESS	read-only
			STATUS	current
	DESCRIPTION ""
			::= { mbusB1 88 }

mbusB1Value29		OBJECT-TYPE
			SYNTAX	INTEGER
			ACCESS	read-only
			STATUS	current
	DESCRIPTION ""
			::= { mbusB1 89 }

mbusB1VIF2A		OBJECT-TYPE
			SYNTAX	INTEGER
			ACCESS	read-only
			STATUS	current
	DESCRIPTION ""
			::= { mbusB1 90 }

mbusB1Value2A		OBJECT-TYPE
			SYNTAX	INTEGER
			ACCESS	read-only
			STATUS	current
	DESCRIPTION ""
			::= { mbusB1 91 }

mbusB1VIF2B		OBJECT-TYPE
			SYNTAX	INTEGER
			ACCESS	read-only
			STATUS	current
	DESCRIPTION ""
			::= { mbusB1 92 }

mbusB1Value2B		OBJECT-TYPE
			SYNTAX	INTEGER
			ACCESS	read-only
			STATUS	current
	DESCRIPTION ""
			::= { mbusB1 93 }

mbusB1VIF2C		OBJECT-TYPE
			SYNTAX	INTEGER
			ACCESS	read-only
			STATUS	current
	DESCRIPTION ""
			::= { mbusB1 94 }

mbusB1Value2C		OBJECT-TYPE
			SYNTAX	INTEGER
			ACCESS	read-only
			STATUS	current
	DESCRIPTION ""
			::= { mbusB1 95 }

mbusB1VIF2D		OBJECT-TYPE
			SYNTAX	INTEGER
			ACCESS	read-only
			STATUS	current
	DESCRIPTION ""
			::= { mbusB1 96 }

mbusB1Value2D		OBJECT-TYPE
			SYNTAX	INTEGER
			ACCESS	read-only
			STATUS	current
	DESCRIPTION ""
			::= { mbusB1 97 }

mbusB1VIF2E		OBJECT-TYPE
			SYNTAX	INTEGER
			ACCESS	read-only
			STATUS	current
	DESCRIPTION ""
			::= { mbusB1 98 }

mbusB1Value2E		OBJECT-TYPE
			SYNTAX	INTEGER
			ACCESS	read-only
			STATUS	current
	DESCRIPTION ""
			::= { mbusB1 99 }

mbusB1VIF2F		OBJECT-TYPE
			SYNTAX	INTEGER
			ACCESS	read-only
			STATUS	current
	DESCRIPTION ""
			::= { mbusB1 100 }

mbusB1Value2F		OBJECT-TYPE
			SYNTAX	INTEGER
			ACCESS	read-only
			STATUS	current
	DESCRIPTION ""
			::= { mbusB1 101 }

mbusB2			OBJECT IDENTIFIER ::= { mbus 178 }

mbusB2IdNumber		OBJECT-TYPE
			SYNTAX	Gauge
			ACCESS	read-only
			STATUS	current
	DESCRIPTION ""
			::= { mbusB2 1 }

mbusB2Manufacturer	OBJECT-TYPE
			SYNTAX	Gauge
			ACCESS	read-only
			STATUS	current
	DESCRIPTION ""
			::= { mbusB2 2 }

mbusB2Version		OBJECT-TYPE
			SYNTAX	Gauge
			ACCESS	read-only
			STATUS	current
	DESCRIPTION ""
			::= { mbusB2 3 }

mbusB2Medium		OBJECT-TYPE
			SYNTAX	Gauge
			ACCESS	read-only
			STATUS	current
	DESCRIPTION ""
			::= { mbusB2 4 }

mbusB2Status		OBJECT-TYPE
			SYNTAX	Gauge
			ACCESS	read-only
			STATUS	current
	DESCRIPTION ""
			::= { mbusB2 5 }

mbusB2VIF00		OBJECT-TYPE
			SYNTAX	INTEGER
			ACCESS	read-only
			STATUS	current
	DESCRIPTION ""
			::= { mbusB2 6 }

mbusB2Value00		OBJECT-TYPE
			SYNTAX	INTEGER
			ACCESS	read-only
			STATUS	current
	DESCRIPTION ""
			::= { mbusB2 7 }

mbusB2VIF01		OBJECT-TYPE
			SYNTAX	INTEGER
			ACCESS	read-only
			STATUS	current
	DESCRIPTION ""
			::= { mbusB2 8 }

mbusB2Value01		OBJECT-TYPE
			SYNTAX	INTEGER
			ACCESS	read-only
			STATUS	current
	DESCRIPTION ""
			::= { mbusB2 9 }

mbusB2VIF02		OBJECT-TYPE
			SYNTAX	INTEGER
			ACCESS	read-only
			STATUS	current
	DESCRIPTION ""
			::= { mbusB2 10 }

mbusB2Value02		OBJECT-TYPE
			SYNTAX	INTEGER
			ACCESS	read-only
			STATUS	current
	DESCRIPTION ""
			::= { mbusB2 11 }

mbusB2VIF03		OBJECT-TYPE
			SYNTAX	INTEGER
			ACCESS	read-only
			STATUS	current
	DESCRIPTION ""
			::= { mbusB2 12 }

mbusB2Value03		OBJECT-TYPE
			SYNTAX	INTEGER
			ACCESS	read-only
			STATUS	current
	DESCRIPTION ""
			::= { mbusB2 13 }

mbusB2VIF04		OBJECT-TYPE
			SYNTAX	INTEGER
			ACCESS	read-only
			STATUS	current
	DESCRIPTION ""
			::= { mbusB2 14 }

mbusB2Value04		OBJECT-TYPE
			SYNTAX	INTEGER
			ACCESS	read-only
			STATUS	current
	DESCRIPTION ""
			::= { mbusB2 15 }

mbusB2VIF05		OBJECT-TYPE
			SYNTAX	INTEGER
			ACCESS	read-only
			STATUS	current
	DESCRIPTION ""
			::= { mbusB2 16 }

mbusB2Value05		OBJECT-TYPE
			SYNTAX	INTEGER
			ACCESS	read-only
			STATUS	current
	DESCRIPTION ""
			::= { mbusB2 17 }

mbusB2VIF06		OBJECT-TYPE
			SYNTAX	INTEGER
			ACCESS	read-only
			STATUS	current
	DESCRIPTION ""
			::= { mbusB2 18 }

mbusB2Value06		OBJECT-TYPE
			SYNTAX	INTEGER
			ACCESS	read-only
			STATUS	current
	DESCRIPTION ""
			::= { mbusB2 19 }

mbusB2VIF07		OBJECT-TYPE
			SYNTAX	INTEGER
			ACCESS	read-only
			STATUS	current
	DESCRIPTION ""
			::= { mbusB2 20 }

mbusB2Value07		OBJECT-TYPE
			SYNTAX	INTEGER
			ACCESS	read-only
			STATUS	current
	DESCRIPTION ""
			::= { mbusB2 21 }

mbusB2VIF08		OBJECT-TYPE
			SYNTAX	INTEGER
			ACCESS	read-only
			STATUS	current
	DESCRIPTION ""
			::= { mbusB2 22 }

mbusB2Value08		OBJECT-TYPE
			SYNTAX	INTEGER
			ACCESS	read-only
			STATUS	current
	DESCRIPTION ""
			::= { mbusB2 23 }

mbusB2VIF09		OBJECT-TYPE
			SYNTAX	INTEGER
			ACCESS	read-only
			STATUS	current
	DESCRIPTION ""
			::= { mbusB2 24 }

mbusB2Value09		OBJECT-TYPE
			SYNTAX	INTEGER
			ACCESS	read-only
			STATUS	current
	DESCRIPTION ""
			::= { mbusB2 25 }

mbusB2VIF0A		OBJECT-TYPE
			SYNTAX	INTEGER
			ACCESS	read-only
			STATUS	current
	DESCRIPTION ""
			::= { mbusB2 26 }

mbusB2Value0A		OBJECT-TYPE
			SYNTAX	INTEGER
			ACCESS	read-only
			STATUS	current
	DESCRIPTION ""
			::= { mbusB2 27 }

mbusB2VIF0B		OBJECT-TYPE
			SYNTAX	INTEGER
			ACCESS	read-only
			STATUS	current
	DESCRIPTION ""
			::= { mbusB2 28 }

mbusB2Value0B		OBJECT-TYPE
			SYNTAX	INTEGER
			ACCESS	read-only
			STATUS	current
	DESCRIPTION ""
			::= { mbusB2 29 }

mbusB2VIF0C		OBJECT-TYPE
			SYNTAX	INTEGER
			ACCESS	read-only
			STATUS	current
	DESCRIPTION ""
			::= { mbusB2 30 }

mbusB2Value0C		OBJECT-TYPE
			SYNTAX	INTEGER
			ACCESS	read-only
			STATUS	current
	DESCRIPTION ""
			::= { mbusB2 31 }

mbusB2VIF0D		OBJECT-TYPE
			SYNTAX	INTEGER
			ACCESS	read-only
			STATUS	current
	DESCRIPTION ""
			::= { mbusB2 32 }

mbusB2Value0D		OBJECT-TYPE
			SYNTAX	INTEGER
			ACCESS	read-only
			STATUS	current
	DESCRIPTION ""
			::= { mbusB2 33 }

mbusB2VIF0E		OBJECT-TYPE
			SYNTAX	INTEGER
			ACCESS	read-only
			STATUS	current
	DESCRIPTION ""
			::= { mbusB2 34 }

mbusB2Value0E		OBJECT-TYPE
			SYNTAX	INTEGER
			ACCESS	read-only
			STATUS	current
	DESCRIPTION ""
			::= { mbusB2 35 }

mbusB2VIF0F		OBJECT-TYPE
			SYNTAX	INTEGER
			ACCESS	read-only
			STATUS	current
	DESCRIPTION ""
			::= { mbusB2 36 }

mbusB2Value0F		OBJECT-TYPE
			SYNTAX	INTEGER
			ACCESS	read-only
			STATUS	current
	DESCRIPTION ""
			::= { mbusB2 37 }

mbusB2VIF10		OBJECT-TYPE
			SYNTAX	INTEGER
			ACCESS	read-only
			STATUS	current
	DESCRIPTION ""
			::= { mbusB2 38 }

mbusB2Value10		OBJECT-TYPE
			SYNTAX	INTEGER
			ACCESS	read-only
			STATUS	current
	DESCRIPTION ""
			::= { mbusB2 39 }

mbusB2VIF11		OBJECT-TYPE
			SYNTAX	INTEGER
			ACCESS	read-only
			STATUS	current
	DESCRIPTION ""
			::= { mbusB2 40 }

mbusB2Value11		OBJECT-TYPE
			SYNTAX	INTEGER
			ACCESS	read-only
			STATUS	current
	DESCRIPTION ""
			::= { mbusB2 41 }

mbusB2VIF12		OBJECT-TYPE
			SYNTAX	INTEGER
			ACCESS	read-only
			STATUS	current
	DESCRIPTION ""
			::= { mbusB2 42 }

mbusB2Value12		OBJECT-TYPE
			SYNTAX	INTEGER
			ACCESS	read-only
			STATUS	current
	DESCRIPTION ""
			::= { mbusB2 43 }

mbusB2VIF13		OBJECT-TYPE
			SYNTAX	INTEGER
			ACCESS	read-only
			STATUS	current
	DESCRIPTION ""
			::= { mbusB2 44 }

mbusB2Value13		OBJECT-TYPE
			SYNTAX	INTEGER
			ACCESS	read-only
			STATUS	current
	DESCRIPTION ""
			::= { mbusB2 45 }

mbusB2VIF14		OBJECT-TYPE
			SYNTAX	INTEGER
			ACCESS	read-only
			STATUS	current
	DESCRIPTION ""
			::= { mbusB2 46 }

mbusB2Value14		OBJECT-TYPE
			SYNTAX	INTEGER
			ACCESS	read-only
			STATUS	current
	DESCRIPTION ""
			::= { mbusB2 47 }

mbusB2VIF15		OBJECT-TYPE
			SYNTAX	INTEGER
			ACCESS	read-only
			STATUS	current
	DESCRIPTION ""
			::= { mbusB2 48 }

mbusB2Value15		OBJECT-TYPE
			SYNTAX	INTEGER
			ACCESS	read-only
			STATUS	current
	DESCRIPTION ""
			::= { mbusB2 49 }

mbusB2VIF16		OBJECT-TYPE
			SYNTAX	INTEGER
			ACCESS	read-only
			STATUS	current
	DESCRIPTION ""
			::= { mbusB2 50 }

mbusB2Value16		OBJECT-TYPE
			SYNTAX	INTEGER
			ACCESS	read-only
			STATUS	current
	DESCRIPTION ""
			::= { mbusB2 51 }

mbusB2VIF17		OBJECT-TYPE
			SYNTAX	INTEGER
			ACCESS	read-only
			STATUS	current
	DESCRIPTION ""
			::= { mbusB2 52 }

mbusB2Value17		OBJECT-TYPE
			SYNTAX	INTEGER
			ACCESS	read-only
			STATUS	current
	DESCRIPTION ""
			::= { mbusB2 53 }

mbusB2VIF18		OBJECT-TYPE
			SYNTAX	INTEGER
			ACCESS	read-only
			STATUS	current
	DESCRIPTION ""
			::= { mbusB2 54 }

mbusB2Value18		OBJECT-TYPE
			SYNTAX	INTEGER
			ACCESS	read-only
			STATUS	current
	DESCRIPTION ""
			::= { mbusB2 55 }

mbusB2VIF19		OBJECT-TYPE
			SYNTAX	INTEGER
			ACCESS	read-only
			STATUS	current
	DESCRIPTION ""
			::= { mbusB2 56 }

mbusB2Value19		OBJECT-TYPE
			SYNTAX	INTEGER
			ACCESS	read-only
			STATUS	current
	DESCRIPTION ""
			::= { mbusB2 57 }

mbusB2VIF1A		OBJECT-TYPE
			SYNTAX	INTEGER
			ACCESS	read-only
			STATUS	current
	DESCRIPTION ""
			::= { mbusB2 58 }

mbusB2Value1A		OBJECT-TYPE
			SYNTAX	INTEGER
			ACCESS	read-only
			STATUS	current
	DESCRIPTION ""
			::= { mbusB2 59 }

mbusB2VIF1B		OBJECT-TYPE
			SYNTAX	INTEGER
			ACCESS	read-only
			STATUS	current
	DESCRIPTION ""
			::= { mbusB2 60 }

mbusB2Value1B		OBJECT-TYPE
			SYNTAX	INTEGER
			ACCESS	read-only
			STATUS	current
	DESCRIPTION ""
			::= { mbusB2 61 }

mbusB2VIF1C		OBJECT-TYPE
			SYNTAX	INTEGER
			ACCESS	read-only
			STATUS	current
	DESCRIPTION ""
			::= { mbusB2 62 }

mbusB2Value1C		OBJECT-TYPE
			SYNTAX	INTEGER
			ACCESS	read-only
			STATUS	current
	DESCRIPTION ""
			::= { mbusB2 63 }

mbusB2VIF1D		OBJECT-TYPE
			SYNTAX	INTEGER
			ACCESS	read-only
			STATUS	current
	DESCRIPTION ""
			::= { mbusB2 64 }

mbusB2Value1D		OBJECT-TYPE
			SYNTAX	INTEGER
			ACCESS	read-only
			STATUS	current
	DESCRIPTION ""
			::= { mbusB2 65 }

mbusB2VIF1E		OBJECT-TYPE
			SYNTAX	INTEGER
			ACCESS	read-only
			STATUS	current
	DESCRIPTION ""
			::= { mbusB2 66 }

mbusB2Value1E		OBJECT-TYPE
			SYNTAX	INTEGER
			ACCESS	read-only
			STATUS	current
	DESCRIPTION ""
			::= { mbusB2 67 }

mbusB2VIF1F		OBJECT-TYPE
			SYNTAX	INTEGER
			ACCESS	read-only
			STATUS	current
	DESCRIPTION ""
			::= { mbusB2 68 }

mbusB2Value1F		OBJECT-TYPE
			SYNTAX	INTEGER
			ACCESS	read-only
			STATUS	current
	DESCRIPTION ""
			::= { mbusB2 69 }

mbusB2VIF20		OBJECT-TYPE
			SYNTAX	INTEGER
			ACCESS	read-only
			STATUS	current
	DESCRIPTION ""
			::= { mbusB2 70 }

mbusB2Value20		OBJECT-TYPE
			SYNTAX	INTEGER
			ACCESS	read-only
			STATUS	current
	DESCRIPTION ""
			::= { mbusB2 71 }

mbusB2VIF21		OBJECT-TYPE
			SYNTAX	INTEGER
			ACCESS	read-only
			STATUS	current
	DESCRIPTION ""
			::= { mbusB2 72 }

mbusB2Value21		OBJECT-TYPE
			SYNTAX	INTEGER
			ACCESS	read-only
			STATUS	current
	DESCRIPTION ""
			::= { mbusB2 73 }

mbusB2VIF22		OBJECT-TYPE
			SYNTAX	INTEGER
			ACCESS	read-only
			STATUS	current
	DESCRIPTION ""
			::= { mbusB2 74 }

mbusB2Value22		OBJECT-TYPE
			SYNTAX	INTEGER
			ACCESS	read-only
			STATUS	current
	DESCRIPTION ""
			::= { mbusB2 75 }

mbusB2VIF23		OBJECT-TYPE
			SYNTAX	INTEGER
			ACCESS	read-only
			STATUS	current
	DESCRIPTION ""
			::= { mbusB2 76 }

mbusB2Value23		OBJECT-TYPE
			SYNTAX	INTEGER
			ACCESS	read-only
			STATUS	current
	DESCRIPTION ""
			::= { mbusB2 77 }

mbusB2VIF24		OBJECT-TYPE
			SYNTAX	INTEGER
			ACCESS	read-only
			STATUS	current
	DESCRIPTION ""
			::= { mbusB2 78 }

mbusB2Value24		OBJECT-TYPE
			SYNTAX	INTEGER
			ACCESS	read-only
			STATUS	current
	DESCRIPTION ""
			::= { mbusB2 79 }

mbusB2VIF25		OBJECT-TYPE
			SYNTAX	INTEGER
			ACCESS	read-only
			STATUS	current
	DESCRIPTION ""
			::= { mbusB2 80 }

mbusB2Value25		OBJECT-TYPE
			SYNTAX	INTEGER
			ACCESS	read-only
			STATUS	current
	DESCRIPTION ""
			::= { mbusB2 81 }

mbusB2VIF26		OBJECT-TYPE
			SYNTAX	INTEGER
			ACCESS	read-only
			STATUS	current
	DESCRIPTION ""
			::= { mbusB2 82 }

mbusB2Value26		OBJECT-TYPE
			SYNTAX	INTEGER
			ACCESS	read-only
			STATUS	current
	DESCRIPTION ""
			::= { mbusB2 83 }

mbusB2VIF27		OBJECT-TYPE
			SYNTAX	INTEGER
			ACCESS	read-only
			STATUS	current
	DESCRIPTION ""
			::= { mbusB2 84 }

mbusB2Value27		OBJECT-TYPE
			SYNTAX	INTEGER
			ACCESS	read-only
			STATUS	current
	DESCRIPTION ""
			::= { mbusB2 85 }

mbusB2VIF28		OBJECT-TYPE
			SYNTAX	INTEGER
			ACCESS	read-only
			STATUS	current
	DESCRIPTION ""
			::= { mbusB2 86 }

mbusB2Value28		OBJECT-TYPE
			SYNTAX	INTEGER
			ACCESS	read-only
			STATUS	current
	DESCRIPTION ""
			::= { mbusB2 87 }

mbusB2VIF29		OBJECT-TYPE
			SYNTAX	INTEGER
			ACCESS	read-only
			STATUS	current
	DESCRIPTION ""
			::= { mbusB2 88 }

mbusB2Value29		OBJECT-TYPE
			SYNTAX	INTEGER
			ACCESS	read-only
			STATUS	current
	DESCRIPTION ""
			::= { mbusB2 89 }

mbusB2VIF2A		OBJECT-TYPE
			SYNTAX	INTEGER
			ACCESS	read-only
			STATUS	current
	DESCRIPTION ""
			::= { mbusB2 90 }

mbusB2Value2A		OBJECT-TYPE
			SYNTAX	INTEGER
			ACCESS	read-only
			STATUS	current
	DESCRIPTION ""
			::= { mbusB2 91 }

mbusB2VIF2B		OBJECT-TYPE
			SYNTAX	INTEGER
			ACCESS	read-only
			STATUS	current
	DESCRIPTION ""
			::= { mbusB2 92 }

mbusB2Value2B		OBJECT-TYPE
			SYNTAX	INTEGER
			ACCESS	read-only
			STATUS	current
	DESCRIPTION ""
			::= { mbusB2 93 }

mbusB2VIF2C		OBJECT-TYPE
			SYNTAX	INTEGER
			ACCESS	read-only
			STATUS	current
	DESCRIPTION ""
			::= { mbusB2 94 }

mbusB2Value2C		OBJECT-TYPE
			SYNTAX	INTEGER
			ACCESS	read-only
			STATUS	current
	DESCRIPTION ""
			::= { mbusB2 95 }

mbusB2VIF2D		OBJECT-TYPE
			SYNTAX	INTEGER
			ACCESS	read-only
			STATUS	current
	DESCRIPTION ""
			::= { mbusB2 96 }

mbusB2Value2D		OBJECT-TYPE
			SYNTAX	INTEGER
			ACCESS	read-only
			STATUS	current
	DESCRIPTION ""
			::= { mbusB2 97 }

mbusB2VIF2E		OBJECT-TYPE
			SYNTAX	INTEGER
			ACCESS	read-only
			STATUS	current
	DESCRIPTION ""
			::= { mbusB2 98 }

mbusB2Value2E		OBJECT-TYPE
			SYNTAX	INTEGER
			ACCESS	read-only
			STATUS	current
	DESCRIPTION ""
			::= { mbusB2 99 }

mbusB2VIF2F		OBJECT-TYPE
			SYNTAX	INTEGER
			ACCESS	read-only
			STATUS	current
	DESCRIPTION ""
			::= { mbusB2 100 }

mbusB2Value2F		OBJECT-TYPE
			SYNTAX	INTEGER
			ACCESS	read-only
			STATUS	current
	DESCRIPTION ""
			::= { mbusB2 101 }

mbusB3			OBJECT IDENTIFIER ::= { mbus 179 }

mbusB3IdNumber		OBJECT-TYPE
			SYNTAX	Gauge
			ACCESS	read-only
			STATUS	current
	DESCRIPTION ""
			::= { mbusB3 1 }

mbusB3Manufacturer	OBJECT-TYPE
			SYNTAX	Gauge
			ACCESS	read-only
			STATUS	current
	DESCRIPTION ""
			::= { mbusB3 2 }

mbusB3Version		OBJECT-TYPE
			SYNTAX	Gauge
			ACCESS	read-only
			STATUS	current
	DESCRIPTION ""
			::= { mbusB3 3 }

mbusB3Medium		OBJECT-TYPE
			SYNTAX	Gauge
			ACCESS	read-only
			STATUS	current
	DESCRIPTION ""
			::= { mbusB3 4 }

mbusB3Status		OBJECT-TYPE
			SYNTAX	Gauge
			ACCESS	read-only
			STATUS	current
	DESCRIPTION ""
			::= { mbusB3 5 }

mbusB3VIF00		OBJECT-TYPE
			SYNTAX	INTEGER
			ACCESS	read-only
			STATUS	current
	DESCRIPTION ""
			::= { mbusB3 6 }

mbusB3Value00		OBJECT-TYPE
			SYNTAX	INTEGER
			ACCESS	read-only
			STATUS	current
	DESCRIPTION ""
			::= { mbusB3 7 }

mbusB3VIF01		OBJECT-TYPE
			SYNTAX	INTEGER
			ACCESS	read-only
			STATUS	current
	DESCRIPTION ""
			::= { mbusB3 8 }

mbusB3Value01		OBJECT-TYPE
			SYNTAX	INTEGER
			ACCESS	read-only
			STATUS	current
	DESCRIPTION ""
			::= { mbusB3 9 }

mbusB3VIF02		OBJECT-TYPE
			SYNTAX	INTEGER
			ACCESS	read-only
			STATUS	current
	DESCRIPTION ""
			::= { mbusB3 10 }

mbusB3Value02		OBJECT-TYPE
			SYNTAX	INTEGER
			ACCESS	read-only
			STATUS	current
	DESCRIPTION ""
			::= { mbusB3 11 }

mbusB3VIF03		OBJECT-TYPE
			SYNTAX	INTEGER
			ACCESS	read-only
			STATUS	current
	DESCRIPTION ""
			::= { mbusB3 12 }

mbusB3Value03		OBJECT-TYPE
			SYNTAX	INTEGER
			ACCESS	read-only
			STATUS	current
	DESCRIPTION ""
			::= { mbusB3 13 }

mbusB3VIF04		OBJECT-TYPE
			SYNTAX	INTEGER
			ACCESS	read-only
			STATUS	current
	DESCRIPTION ""
			::= { mbusB3 14 }

mbusB3Value04		OBJECT-TYPE
			SYNTAX	INTEGER
			ACCESS	read-only
			STATUS	current
	DESCRIPTION ""
			::= { mbusB3 15 }

mbusB3VIF05		OBJECT-TYPE
			SYNTAX	INTEGER
			ACCESS	read-only
			STATUS	current
	DESCRIPTION ""
			::= { mbusB3 16 }

mbusB3Value05		OBJECT-TYPE
			SYNTAX	INTEGER
			ACCESS	read-only
			STATUS	current
	DESCRIPTION ""
			::= { mbusB3 17 }

mbusB3VIF06		OBJECT-TYPE
			SYNTAX	INTEGER
			ACCESS	read-only
			STATUS	current
	DESCRIPTION ""
			::= { mbusB3 18 }

mbusB3Value06		OBJECT-TYPE
			SYNTAX	INTEGER
			ACCESS	read-only
			STATUS	current
	DESCRIPTION ""
			::= { mbusB3 19 }

mbusB3VIF07		OBJECT-TYPE
			SYNTAX	INTEGER
			ACCESS	read-only
			STATUS	current
	DESCRIPTION ""
			::= { mbusB3 20 }

mbusB3Value07		OBJECT-TYPE
			SYNTAX	INTEGER
			ACCESS	read-only
			STATUS	current
	DESCRIPTION ""
			::= { mbusB3 21 }

mbusB3VIF08		OBJECT-TYPE
			SYNTAX	INTEGER
			ACCESS	read-only
			STATUS	current
	DESCRIPTION ""
			::= { mbusB3 22 }

mbusB3Value08		OBJECT-TYPE
			SYNTAX	INTEGER
			ACCESS	read-only
			STATUS	current
	DESCRIPTION ""
			::= { mbusB3 23 }

mbusB3VIF09		OBJECT-TYPE
			SYNTAX	INTEGER
			ACCESS	read-only
			STATUS	current
	DESCRIPTION ""
			::= { mbusB3 24 }

mbusB3Value09		OBJECT-TYPE
			SYNTAX	INTEGER
			ACCESS	read-only
			STATUS	current
	DESCRIPTION ""
			::= { mbusB3 25 }

mbusB3VIF0A		OBJECT-TYPE
			SYNTAX	INTEGER
			ACCESS	read-only
			STATUS	current
	DESCRIPTION ""
			::= { mbusB3 26 }

mbusB3Value0A		OBJECT-TYPE
			SYNTAX	INTEGER
			ACCESS	read-only
			STATUS	current
	DESCRIPTION ""
			::= { mbusB3 27 }

mbusB3VIF0B		OBJECT-TYPE
			SYNTAX	INTEGER
			ACCESS	read-only
			STATUS	current
	DESCRIPTION ""
			::= { mbusB3 28 }

mbusB3Value0B		OBJECT-TYPE
			SYNTAX	INTEGER
			ACCESS	read-only
			STATUS	current
	DESCRIPTION ""
			::= { mbusB3 29 }

mbusB3VIF0C		OBJECT-TYPE
			SYNTAX	INTEGER
			ACCESS	read-only
			STATUS	current
	DESCRIPTION ""
			::= { mbusB3 30 }

mbusB3Value0C		OBJECT-TYPE
			SYNTAX	INTEGER
			ACCESS	read-only
			STATUS	current
	DESCRIPTION ""
			::= { mbusB3 31 }

mbusB3VIF0D		OBJECT-TYPE
			SYNTAX	INTEGER
			ACCESS	read-only
			STATUS	current
	DESCRIPTION ""
			::= { mbusB3 32 }

mbusB3Value0D		OBJECT-TYPE
			SYNTAX	INTEGER
			ACCESS	read-only
			STATUS	current
	DESCRIPTION ""
			::= { mbusB3 33 }

mbusB3VIF0E		OBJECT-TYPE
			SYNTAX	INTEGER
			ACCESS	read-only
			STATUS	current
	DESCRIPTION ""
			::= { mbusB3 34 }

mbusB3Value0E		OBJECT-TYPE
			SYNTAX	INTEGER
			ACCESS	read-only
			STATUS	current
	DESCRIPTION ""
			::= { mbusB3 35 }

mbusB3VIF0F		OBJECT-TYPE
			SYNTAX	INTEGER
			ACCESS	read-only
			STATUS	current
	DESCRIPTION ""
			::= { mbusB3 36 }

mbusB3Value0F		OBJECT-TYPE
			SYNTAX	INTEGER
			ACCESS	read-only
			STATUS	current
	DESCRIPTION ""
			::= { mbusB3 37 }

mbusB3VIF10		OBJECT-TYPE
			SYNTAX	INTEGER
			ACCESS	read-only
			STATUS	current
	DESCRIPTION ""
			::= { mbusB3 38 }

mbusB3Value10		OBJECT-TYPE
			SYNTAX	INTEGER
			ACCESS	read-only
			STATUS	current
	DESCRIPTION ""
			::= { mbusB3 39 }

mbusB3VIF11		OBJECT-TYPE
			SYNTAX	INTEGER
			ACCESS	read-only
			STATUS	current
	DESCRIPTION ""
			::= { mbusB3 40 }

mbusB3Value11		OBJECT-TYPE
			SYNTAX	INTEGER
			ACCESS	read-only
			STATUS	current
	DESCRIPTION ""
			::= { mbusB3 41 }

mbusB3VIF12		OBJECT-TYPE
			SYNTAX	INTEGER
			ACCESS	read-only
			STATUS	current
	DESCRIPTION ""
			::= { mbusB3 42 }

mbusB3Value12		OBJECT-TYPE
			SYNTAX	INTEGER
			ACCESS	read-only
			STATUS	current
	DESCRIPTION ""
			::= { mbusB3 43 }

mbusB3VIF13		OBJECT-TYPE
			SYNTAX	INTEGER
			ACCESS	read-only
			STATUS	current
	DESCRIPTION ""
			::= { mbusB3 44 }

mbusB3Value13		OBJECT-TYPE
			SYNTAX	INTEGER
			ACCESS	read-only
			STATUS	current
	DESCRIPTION ""
			::= { mbusB3 45 }

mbusB3VIF14		OBJECT-TYPE
			SYNTAX	INTEGER
			ACCESS	read-only
			STATUS	current
	DESCRIPTION ""
			::= { mbusB3 46 }

mbusB3Value14		OBJECT-TYPE
			SYNTAX	INTEGER
			ACCESS	read-only
			STATUS	current
	DESCRIPTION ""
			::= { mbusB3 47 }

mbusB3VIF15		OBJECT-TYPE
			SYNTAX	INTEGER
			ACCESS	read-only
			STATUS	current
	DESCRIPTION ""
			::= { mbusB3 48 }

mbusB3Value15		OBJECT-TYPE
			SYNTAX	INTEGER
			ACCESS	read-only
			STATUS	current
	DESCRIPTION ""
			::= { mbusB3 49 }

mbusB3VIF16		OBJECT-TYPE
			SYNTAX	INTEGER
			ACCESS	read-only
			STATUS	current
	DESCRIPTION ""
			::= { mbusB3 50 }

mbusB3Value16		OBJECT-TYPE
			SYNTAX	INTEGER
			ACCESS	read-only
			STATUS	current
	DESCRIPTION ""
			::= { mbusB3 51 }

mbusB3VIF17		OBJECT-TYPE
			SYNTAX	INTEGER
			ACCESS	read-only
			STATUS	current
	DESCRIPTION ""
			::= { mbusB3 52 }

mbusB3Value17		OBJECT-TYPE
			SYNTAX	INTEGER
			ACCESS	read-only
			STATUS	current
	DESCRIPTION ""
			::= { mbusB3 53 }

mbusB3VIF18		OBJECT-TYPE
			SYNTAX	INTEGER
			ACCESS	read-only
			STATUS	current
	DESCRIPTION ""
			::= { mbusB3 54 }

mbusB3Value18		OBJECT-TYPE
			SYNTAX	INTEGER
			ACCESS	read-only
			STATUS	current
	DESCRIPTION ""
			::= { mbusB3 55 }

mbusB3VIF19		OBJECT-TYPE
			SYNTAX	INTEGER
			ACCESS	read-only
			STATUS	current
	DESCRIPTION ""
			::= { mbusB3 56 }

mbusB3Value19		OBJECT-TYPE
			SYNTAX	INTEGER
			ACCESS	read-only
			STATUS	current
	DESCRIPTION ""
			::= { mbusB3 57 }

mbusB3VIF1A		OBJECT-TYPE
			SYNTAX	INTEGER
			ACCESS	read-only
			STATUS	current
	DESCRIPTION ""
			::= { mbusB3 58 }

mbusB3Value1A		OBJECT-TYPE
			SYNTAX	INTEGER
			ACCESS	read-only
			STATUS	current
	DESCRIPTION ""
			::= { mbusB3 59 }

mbusB3VIF1B		OBJECT-TYPE
			SYNTAX	INTEGER
			ACCESS	read-only
			STATUS	current
	DESCRIPTION ""
			::= { mbusB3 60 }

mbusB3Value1B		OBJECT-TYPE
			SYNTAX	INTEGER
			ACCESS	read-only
			STATUS	current
	DESCRIPTION ""
			::= { mbusB3 61 }

mbusB3VIF1C		OBJECT-TYPE
			SYNTAX	INTEGER
			ACCESS	read-only
			STATUS	current
	DESCRIPTION ""
			::= { mbusB3 62 }

mbusB3Value1C		OBJECT-TYPE
			SYNTAX	INTEGER
			ACCESS	read-only
			STATUS	current
	DESCRIPTION ""
			::= { mbusB3 63 }

mbusB3VIF1D		OBJECT-TYPE
			SYNTAX	INTEGER
			ACCESS	read-only
			STATUS	current
	DESCRIPTION ""
			::= { mbusB3 64 }

mbusB3Value1D		OBJECT-TYPE
			SYNTAX	INTEGER
			ACCESS	read-only
			STATUS	current
	DESCRIPTION ""
			::= { mbusB3 65 }

mbusB3VIF1E		OBJECT-TYPE
			SYNTAX	INTEGER
			ACCESS	read-only
			STATUS	current
	DESCRIPTION ""
			::= { mbusB3 66 }

mbusB3Value1E		OBJECT-TYPE
			SYNTAX	INTEGER
			ACCESS	read-only
			STATUS	current
	DESCRIPTION ""
			::= { mbusB3 67 }

mbusB3VIF1F		OBJECT-TYPE
			SYNTAX	INTEGER
			ACCESS	read-only
			STATUS	current
	DESCRIPTION ""
			::= { mbusB3 68 }

mbusB3Value1F		OBJECT-TYPE
			SYNTAX	INTEGER
			ACCESS	read-only
			STATUS	current
	DESCRIPTION ""
			::= { mbusB3 69 }

mbusB3VIF20		OBJECT-TYPE
			SYNTAX	INTEGER
			ACCESS	read-only
			STATUS	current
	DESCRIPTION ""
			::= { mbusB3 70 }

mbusB3Value20		OBJECT-TYPE
			SYNTAX	INTEGER
			ACCESS	read-only
			STATUS	current
	DESCRIPTION ""
			::= { mbusB3 71 }

mbusB3VIF21		OBJECT-TYPE
			SYNTAX	INTEGER
			ACCESS	read-only
			STATUS	current
	DESCRIPTION ""
			::= { mbusB3 72 }

mbusB3Value21		OBJECT-TYPE
			SYNTAX	INTEGER
			ACCESS	read-only
			STATUS	current
	DESCRIPTION ""
			::= { mbusB3 73 }

mbusB3VIF22		OBJECT-TYPE
			SYNTAX	INTEGER
			ACCESS	read-only
			STATUS	current
	DESCRIPTION ""
			::= { mbusB3 74 }

mbusB3Value22		OBJECT-TYPE
			SYNTAX	INTEGER
			ACCESS	read-only
			STATUS	current
	DESCRIPTION ""
			::= { mbusB3 75 }

mbusB3VIF23		OBJECT-TYPE
			SYNTAX	INTEGER
			ACCESS	read-only
			STATUS	current
	DESCRIPTION ""
			::= { mbusB3 76 }

mbusB3Value23		OBJECT-TYPE
			SYNTAX	INTEGER
			ACCESS	read-only
			STATUS	current
	DESCRIPTION ""
			::= { mbusB3 77 }

mbusB3VIF24		OBJECT-TYPE
			SYNTAX	INTEGER
			ACCESS	read-only
			STATUS	current
	DESCRIPTION ""
			::= { mbusB3 78 }

mbusB3Value24		OBJECT-TYPE
			SYNTAX	INTEGER
			ACCESS	read-only
			STATUS	current
	DESCRIPTION ""
			::= { mbusB3 79 }

mbusB3VIF25		OBJECT-TYPE
			SYNTAX	INTEGER
			ACCESS	read-only
			STATUS	current
	DESCRIPTION ""
			::= { mbusB3 80 }

mbusB3Value25		OBJECT-TYPE
			SYNTAX	INTEGER
			ACCESS	read-only
			STATUS	current
	DESCRIPTION ""
			::= { mbusB3 81 }

mbusB3VIF26		OBJECT-TYPE
			SYNTAX	INTEGER
			ACCESS	read-only
			STATUS	current
	DESCRIPTION ""
			::= { mbusB3 82 }

mbusB3Value26		OBJECT-TYPE
			SYNTAX	INTEGER
			ACCESS	read-only
			STATUS	current
	DESCRIPTION ""
			::= { mbusB3 83 }

mbusB3VIF27		OBJECT-TYPE
			SYNTAX	INTEGER
			ACCESS	read-only
			STATUS	current
	DESCRIPTION ""
			::= { mbusB3 84 }

mbusB3Value27		OBJECT-TYPE
			SYNTAX	INTEGER
			ACCESS	read-only
			STATUS	current
	DESCRIPTION ""
			::= { mbusB3 85 }

mbusB3VIF28		OBJECT-TYPE
			SYNTAX	INTEGER
			ACCESS	read-only
			STATUS	current
	DESCRIPTION ""
			::= { mbusB3 86 }

mbusB3Value28		OBJECT-TYPE
			SYNTAX	INTEGER
			ACCESS	read-only
			STATUS	current
	DESCRIPTION ""
			::= { mbusB3 87 }

mbusB3VIF29		OBJECT-TYPE
			SYNTAX	INTEGER
			ACCESS	read-only
			STATUS	current
	DESCRIPTION ""
			::= { mbusB3 88 }

mbusB3Value29		OBJECT-TYPE
			SYNTAX	INTEGER
			ACCESS	read-only
			STATUS	current
	DESCRIPTION ""
			::= { mbusB3 89 }

mbusB3VIF2A		OBJECT-TYPE
			SYNTAX	INTEGER
			ACCESS	read-only
			STATUS	current
	DESCRIPTION ""
			::= { mbusB3 90 }

mbusB3Value2A		OBJECT-TYPE
			SYNTAX	INTEGER
			ACCESS	read-only
			STATUS	current
	DESCRIPTION ""
			::= { mbusB3 91 }

mbusB3VIF2B		OBJECT-TYPE
			SYNTAX	INTEGER
			ACCESS	read-only
			STATUS	current
	DESCRIPTION ""
			::= { mbusB3 92 }

mbusB3Value2B		OBJECT-TYPE
			SYNTAX	INTEGER
			ACCESS	read-only
			STATUS	current
	DESCRIPTION ""
			::= { mbusB3 93 }

mbusB3VIF2C		OBJECT-TYPE
			SYNTAX	INTEGER
			ACCESS	read-only
			STATUS	current
	DESCRIPTION ""
			::= { mbusB3 94 }

mbusB3Value2C		OBJECT-TYPE
			SYNTAX	INTEGER
			ACCESS	read-only
			STATUS	current
	DESCRIPTION ""
			::= { mbusB3 95 }

mbusB3VIF2D		OBJECT-TYPE
			SYNTAX	INTEGER
			ACCESS	read-only
			STATUS	current
	DESCRIPTION ""
			::= { mbusB3 96 }

mbusB3Value2D		OBJECT-TYPE
			SYNTAX	INTEGER
			ACCESS	read-only
			STATUS	current
	DESCRIPTION ""
			::= { mbusB3 97 }

mbusB3VIF2E		OBJECT-TYPE
			SYNTAX	INTEGER
			ACCESS	read-only
			STATUS	current
	DESCRIPTION ""
			::= { mbusB3 98 }

mbusB3Value2E		OBJECT-TYPE
			SYNTAX	INTEGER
			ACCESS	read-only
			STATUS	current
	DESCRIPTION ""
			::= { mbusB3 99 }

mbusB3VIF2F		OBJECT-TYPE
			SYNTAX	INTEGER
			ACCESS	read-only
			STATUS	current
	DESCRIPTION ""
			::= { mbusB3 100 }

mbusB3Value2F		OBJECT-TYPE
			SYNTAX	INTEGER
			ACCESS	read-only
			STATUS	current
	DESCRIPTION ""
			::= { mbusB3 101 }

mbusB4			OBJECT IDENTIFIER ::= { mbus 180 }

mbusB4IdNumber		OBJECT-TYPE
			SYNTAX	Gauge
			ACCESS	read-only
			STATUS	current
	DESCRIPTION ""
			::= { mbusB4 1 }

mbusB4Manufacturer	OBJECT-TYPE
			SYNTAX	Gauge
			ACCESS	read-only
			STATUS	current
	DESCRIPTION ""
			::= { mbusB4 2 }

mbusB4Version		OBJECT-TYPE
			SYNTAX	Gauge
			ACCESS	read-only
			STATUS	current
	DESCRIPTION ""
			::= { mbusB4 3 }

mbusB4Medium		OBJECT-TYPE
			SYNTAX	Gauge
			ACCESS	read-only
			STATUS	current
	DESCRIPTION ""
			::= { mbusB4 4 }

mbusB4Status		OBJECT-TYPE
			SYNTAX	Gauge
			ACCESS	read-only
			STATUS	current
	DESCRIPTION ""
			::= { mbusB4 5 }

mbusB4VIF00		OBJECT-TYPE
			SYNTAX	INTEGER
			ACCESS	read-only
			STATUS	current
	DESCRIPTION ""
			::= { mbusB4 6 }

mbusB4Value00		OBJECT-TYPE
			SYNTAX	INTEGER
			ACCESS	read-only
			STATUS	current
	DESCRIPTION ""
			::= { mbusB4 7 }

mbusB4VIF01		OBJECT-TYPE
			SYNTAX	INTEGER
			ACCESS	read-only
			STATUS	current
	DESCRIPTION ""
			::= { mbusB4 8 }

mbusB4Value01		OBJECT-TYPE
			SYNTAX	INTEGER
			ACCESS	read-only
			STATUS	current
	DESCRIPTION ""
			::= { mbusB4 9 }

mbusB4VIF02		OBJECT-TYPE
			SYNTAX	INTEGER
			ACCESS	read-only
			STATUS	current
	DESCRIPTION ""
			::= { mbusB4 10 }

mbusB4Value02		OBJECT-TYPE
			SYNTAX	INTEGER
			ACCESS	read-only
			STATUS	current
	DESCRIPTION ""
			::= { mbusB4 11 }

mbusB4VIF03		OBJECT-TYPE
			SYNTAX	INTEGER
			ACCESS	read-only
			STATUS	current
	DESCRIPTION ""
			::= { mbusB4 12 }

mbusB4Value03		OBJECT-TYPE
			SYNTAX	INTEGER
			ACCESS	read-only
			STATUS	current
	DESCRIPTION ""
			::= { mbusB4 13 }

mbusB4VIF04		OBJECT-TYPE
			SYNTAX	INTEGER
			ACCESS	read-only
			STATUS	current
	DESCRIPTION ""
			::= { mbusB4 14 }

mbusB4Value04		OBJECT-TYPE
			SYNTAX	INTEGER
			ACCESS	read-only
			STATUS	current
	DESCRIPTION ""
			::= { mbusB4 15 }

mbusB4VIF05		OBJECT-TYPE
			SYNTAX	INTEGER
			ACCESS	read-only
			STATUS	current
	DESCRIPTION ""
			::= { mbusB4 16 }

mbusB4Value05		OBJECT-TYPE
			SYNTAX	INTEGER
			ACCESS	read-only
			STATUS	current
	DESCRIPTION ""
			::= { mbusB4 17 }

mbusB4VIF06		OBJECT-TYPE
			SYNTAX	INTEGER
			ACCESS	read-only
			STATUS	current
	DESCRIPTION ""
			::= { mbusB4 18 }

mbusB4Value06		OBJECT-TYPE
			SYNTAX	INTEGER
			ACCESS	read-only
			STATUS	current
	DESCRIPTION ""
			::= { mbusB4 19 }

mbusB4VIF07		OBJECT-TYPE
			SYNTAX	INTEGER
			ACCESS	read-only
			STATUS	current
	DESCRIPTION ""
			::= { mbusB4 20 }

mbusB4Value07		OBJECT-TYPE
			SYNTAX	INTEGER
			ACCESS	read-only
			STATUS	current
	DESCRIPTION ""
			::= { mbusB4 21 }

mbusB4VIF08		OBJECT-TYPE
			SYNTAX	INTEGER
			ACCESS	read-only
			STATUS	current
	DESCRIPTION ""
			::= { mbusB4 22 }

mbusB4Value08		OBJECT-TYPE
			SYNTAX	INTEGER
			ACCESS	read-only
			STATUS	current
	DESCRIPTION ""
			::= { mbusB4 23 }

mbusB4VIF09		OBJECT-TYPE
			SYNTAX	INTEGER
			ACCESS	read-only
			STATUS	current
	DESCRIPTION ""
			::= { mbusB4 24 }

mbusB4Value09		OBJECT-TYPE
			SYNTAX	INTEGER
			ACCESS	read-only
			STATUS	current
	DESCRIPTION ""
			::= { mbusB4 25 }

mbusB4VIF0A		OBJECT-TYPE
			SYNTAX	INTEGER
			ACCESS	read-only
			STATUS	current
	DESCRIPTION ""
			::= { mbusB4 26 }

mbusB4Value0A		OBJECT-TYPE
			SYNTAX	INTEGER
			ACCESS	read-only
			STATUS	current
	DESCRIPTION ""
			::= { mbusB4 27 }

mbusB4VIF0B		OBJECT-TYPE
			SYNTAX	INTEGER
			ACCESS	read-only
			STATUS	current
	DESCRIPTION ""
			::= { mbusB4 28 }

mbusB4Value0B		OBJECT-TYPE
			SYNTAX	INTEGER
			ACCESS	read-only
			STATUS	current
	DESCRIPTION ""
			::= { mbusB4 29 }

mbusB4VIF0C		OBJECT-TYPE
			SYNTAX	INTEGER
			ACCESS	read-only
			STATUS	current
	DESCRIPTION ""
			::= { mbusB4 30 }

mbusB4Value0C		OBJECT-TYPE
			SYNTAX	INTEGER
			ACCESS	read-only
			STATUS	current
	DESCRIPTION ""
			::= { mbusB4 31 }

mbusB4VIF0D		OBJECT-TYPE
			SYNTAX	INTEGER
			ACCESS	read-only
			STATUS	current
	DESCRIPTION ""
			::= { mbusB4 32 }

mbusB4Value0D		OBJECT-TYPE
			SYNTAX	INTEGER
			ACCESS	read-only
			STATUS	current
	DESCRIPTION ""
			::= { mbusB4 33 }

mbusB4VIF0E		OBJECT-TYPE
			SYNTAX	INTEGER
			ACCESS	read-only
			STATUS	current
	DESCRIPTION ""
			::= { mbusB4 34 }

mbusB4Value0E		OBJECT-TYPE
			SYNTAX	INTEGER
			ACCESS	read-only
			STATUS	current
	DESCRIPTION ""
			::= { mbusB4 35 }

mbusB4VIF0F		OBJECT-TYPE
			SYNTAX	INTEGER
			ACCESS	read-only
			STATUS	current
	DESCRIPTION ""
			::= { mbusB4 36 }

mbusB4Value0F		OBJECT-TYPE
			SYNTAX	INTEGER
			ACCESS	read-only
			STATUS	current
	DESCRIPTION ""
			::= { mbusB4 37 }

mbusB4VIF10		OBJECT-TYPE
			SYNTAX	INTEGER
			ACCESS	read-only
			STATUS	current
	DESCRIPTION ""
			::= { mbusB4 38 }

mbusB4Value10		OBJECT-TYPE
			SYNTAX	INTEGER
			ACCESS	read-only
			STATUS	current
	DESCRIPTION ""
			::= { mbusB4 39 }

mbusB4VIF11		OBJECT-TYPE
			SYNTAX	INTEGER
			ACCESS	read-only
			STATUS	current
	DESCRIPTION ""
			::= { mbusB4 40 }

mbusB4Value11		OBJECT-TYPE
			SYNTAX	INTEGER
			ACCESS	read-only
			STATUS	current
	DESCRIPTION ""
			::= { mbusB4 41 }

mbusB4VIF12		OBJECT-TYPE
			SYNTAX	INTEGER
			ACCESS	read-only
			STATUS	current
	DESCRIPTION ""
			::= { mbusB4 42 }

mbusB4Value12		OBJECT-TYPE
			SYNTAX	INTEGER
			ACCESS	read-only
			STATUS	current
	DESCRIPTION ""
			::= { mbusB4 43 }

mbusB4VIF13		OBJECT-TYPE
			SYNTAX	INTEGER
			ACCESS	read-only
			STATUS	current
	DESCRIPTION ""
			::= { mbusB4 44 }

mbusB4Value13		OBJECT-TYPE
			SYNTAX	INTEGER
			ACCESS	read-only
			STATUS	current
	DESCRIPTION ""
			::= { mbusB4 45 }

mbusB4VIF14		OBJECT-TYPE
			SYNTAX	INTEGER
			ACCESS	read-only
			STATUS	current
	DESCRIPTION ""
			::= { mbusB4 46 }

mbusB4Value14		OBJECT-TYPE
			SYNTAX	INTEGER
			ACCESS	read-only
			STATUS	current
	DESCRIPTION ""
			::= { mbusB4 47 }

mbusB4VIF15		OBJECT-TYPE
			SYNTAX	INTEGER
			ACCESS	read-only
			STATUS	current
	DESCRIPTION ""
			::= { mbusB4 48 }

mbusB4Value15		OBJECT-TYPE
			SYNTAX	INTEGER
			ACCESS	read-only
			STATUS	current
	DESCRIPTION ""
			::= { mbusB4 49 }

mbusB4VIF16		OBJECT-TYPE
			SYNTAX	INTEGER
			ACCESS	read-only
			STATUS	current
	DESCRIPTION ""
			::= { mbusB4 50 }

mbusB4Value16		OBJECT-TYPE
			SYNTAX	INTEGER
			ACCESS	read-only
			STATUS	current
	DESCRIPTION ""
			::= { mbusB4 51 }

mbusB4VIF17		OBJECT-TYPE
			SYNTAX	INTEGER
			ACCESS	read-only
			STATUS	current
	DESCRIPTION ""
			::= { mbusB4 52 }

mbusB4Value17		OBJECT-TYPE
			SYNTAX	INTEGER
			ACCESS	read-only
			STATUS	current
	DESCRIPTION ""
			::= { mbusB4 53 }

mbusB4VIF18		OBJECT-TYPE
			SYNTAX	INTEGER
			ACCESS	read-only
			STATUS	current
	DESCRIPTION ""
			::= { mbusB4 54 }

mbusB4Value18		OBJECT-TYPE
			SYNTAX	INTEGER
			ACCESS	read-only
			STATUS	current
	DESCRIPTION ""
			::= { mbusB4 55 }

mbusB4VIF19		OBJECT-TYPE
			SYNTAX	INTEGER
			ACCESS	read-only
			STATUS	current
	DESCRIPTION ""
			::= { mbusB4 56 }

mbusB4Value19		OBJECT-TYPE
			SYNTAX	INTEGER
			ACCESS	read-only
			STATUS	current
	DESCRIPTION ""
			::= { mbusB4 57 }

mbusB4VIF1A		OBJECT-TYPE
			SYNTAX	INTEGER
			ACCESS	read-only
			STATUS	current
	DESCRIPTION ""
			::= { mbusB4 58 }

mbusB4Value1A		OBJECT-TYPE
			SYNTAX	INTEGER
			ACCESS	read-only
			STATUS	current
	DESCRIPTION ""
			::= { mbusB4 59 }

mbusB4VIF1B		OBJECT-TYPE
			SYNTAX	INTEGER
			ACCESS	read-only
			STATUS	current
	DESCRIPTION ""
			::= { mbusB4 60 }

mbusB4Value1B		OBJECT-TYPE
			SYNTAX	INTEGER
			ACCESS	read-only
			STATUS	current
	DESCRIPTION ""
			::= { mbusB4 61 }

mbusB4VIF1C		OBJECT-TYPE
			SYNTAX	INTEGER
			ACCESS	read-only
			STATUS	current
	DESCRIPTION ""
			::= { mbusB4 62 }

mbusB4Value1C		OBJECT-TYPE
			SYNTAX	INTEGER
			ACCESS	read-only
			STATUS	current
	DESCRIPTION ""
			::= { mbusB4 63 }

mbusB4VIF1D		OBJECT-TYPE
			SYNTAX	INTEGER
			ACCESS	read-only
			STATUS	current
	DESCRIPTION ""
			::= { mbusB4 64 }

mbusB4Value1D		OBJECT-TYPE
			SYNTAX	INTEGER
			ACCESS	read-only
			STATUS	current
	DESCRIPTION ""
			::= { mbusB4 65 }

mbusB4VIF1E		OBJECT-TYPE
			SYNTAX	INTEGER
			ACCESS	read-only
			STATUS	current
	DESCRIPTION ""
			::= { mbusB4 66 }

mbusB4Value1E		OBJECT-TYPE
			SYNTAX	INTEGER
			ACCESS	read-only
			STATUS	current
	DESCRIPTION ""
			::= { mbusB4 67 }

mbusB4VIF1F		OBJECT-TYPE
			SYNTAX	INTEGER
			ACCESS	read-only
			STATUS	current
	DESCRIPTION ""
			::= { mbusB4 68 }

mbusB4Value1F		OBJECT-TYPE
			SYNTAX	INTEGER
			ACCESS	read-only
			STATUS	current
	DESCRIPTION ""
			::= { mbusB4 69 }

mbusB4VIF20		OBJECT-TYPE
			SYNTAX	INTEGER
			ACCESS	read-only
			STATUS	current
	DESCRIPTION ""
			::= { mbusB4 70 }

mbusB4Value20		OBJECT-TYPE
			SYNTAX	INTEGER
			ACCESS	read-only
			STATUS	current
	DESCRIPTION ""
			::= { mbusB4 71 }

mbusB4VIF21		OBJECT-TYPE
			SYNTAX	INTEGER
			ACCESS	read-only
			STATUS	current
	DESCRIPTION ""
			::= { mbusB4 72 }

mbusB4Value21		OBJECT-TYPE
			SYNTAX	INTEGER
			ACCESS	read-only
			STATUS	current
	DESCRIPTION ""
			::= { mbusB4 73 }

mbusB4VIF22		OBJECT-TYPE
			SYNTAX	INTEGER
			ACCESS	read-only
			STATUS	current
	DESCRIPTION ""
			::= { mbusB4 74 }

mbusB4Value22		OBJECT-TYPE
			SYNTAX	INTEGER
			ACCESS	read-only
			STATUS	current
	DESCRIPTION ""
			::= { mbusB4 75 }

mbusB4VIF23		OBJECT-TYPE
			SYNTAX	INTEGER
			ACCESS	read-only
			STATUS	current
	DESCRIPTION ""
			::= { mbusB4 76 }

mbusB4Value23		OBJECT-TYPE
			SYNTAX	INTEGER
			ACCESS	read-only
			STATUS	current
	DESCRIPTION ""
			::= { mbusB4 77 }

mbusB4VIF24		OBJECT-TYPE
			SYNTAX	INTEGER
			ACCESS	read-only
			STATUS	current
	DESCRIPTION ""
			::= { mbusB4 78 }

mbusB4Value24		OBJECT-TYPE
			SYNTAX	INTEGER
			ACCESS	read-only
			STATUS	current
	DESCRIPTION ""
			::= { mbusB4 79 }

mbusB4VIF25		OBJECT-TYPE
			SYNTAX	INTEGER
			ACCESS	read-only
			STATUS	current
	DESCRIPTION ""
			::= { mbusB4 80 }

mbusB4Value25		OBJECT-TYPE
			SYNTAX	INTEGER
			ACCESS	read-only
			STATUS	current
	DESCRIPTION ""
			::= { mbusB4 81 }

mbusB4VIF26		OBJECT-TYPE
			SYNTAX	INTEGER
			ACCESS	read-only
			STATUS	current
	DESCRIPTION ""
			::= { mbusB4 82 }

mbusB4Value26		OBJECT-TYPE
			SYNTAX	INTEGER
			ACCESS	read-only
			STATUS	current
	DESCRIPTION ""
			::= { mbusB4 83 }

mbusB4VIF27		OBJECT-TYPE
			SYNTAX	INTEGER
			ACCESS	read-only
			STATUS	current
	DESCRIPTION ""
			::= { mbusB4 84 }

mbusB4Value27		OBJECT-TYPE
			SYNTAX	INTEGER
			ACCESS	read-only
			STATUS	current
	DESCRIPTION ""
			::= { mbusB4 85 }

mbusB4VIF28		OBJECT-TYPE
			SYNTAX	INTEGER
			ACCESS	read-only
			STATUS	current
	DESCRIPTION ""
			::= { mbusB4 86 }

mbusB4Value28		OBJECT-TYPE
			SYNTAX	INTEGER
			ACCESS	read-only
			STATUS	current
	DESCRIPTION ""
			::= { mbusB4 87 }

mbusB4VIF29		OBJECT-TYPE
			SYNTAX	INTEGER
			ACCESS	read-only
			STATUS	current
	DESCRIPTION ""
			::= { mbusB4 88 }

mbusB4Value29		OBJECT-TYPE
			SYNTAX	INTEGER
			ACCESS	read-only
			STATUS	current
	DESCRIPTION ""
			::= { mbusB4 89 }

mbusB4VIF2A		OBJECT-TYPE
			SYNTAX	INTEGER
			ACCESS	read-only
			STATUS	current
	DESCRIPTION ""
			::= { mbusB4 90 }

mbusB4Value2A		OBJECT-TYPE
			SYNTAX	INTEGER
			ACCESS	read-only
			STATUS	current
	DESCRIPTION ""
			::= { mbusB4 91 }

mbusB4VIF2B		OBJECT-TYPE
			SYNTAX	INTEGER
			ACCESS	read-only
			STATUS	current
	DESCRIPTION ""
			::= { mbusB4 92 }

mbusB4Value2B		OBJECT-TYPE
			SYNTAX	INTEGER
			ACCESS	read-only
			STATUS	current
	DESCRIPTION ""
			::= { mbusB4 93 }

mbusB4VIF2C		OBJECT-TYPE
			SYNTAX	INTEGER
			ACCESS	read-only
			STATUS	current
	DESCRIPTION ""
			::= { mbusB4 94 }

mbusB4Value2C		OBJECT-TYPE
			SYNTAX	INTEGER
			ACCESS	read-only
			STATUS	current
	DESCRIPTION ""
			::= { mbusB4 95 }

mbusB4VIF2D		OBJECT-TYPE
			SYNTAX	INTEGER
			ACCESS	read-only
			STATUS	current
	DESCRIPTION ""
			::= { mbusB4 96 }

mbusB4Value2D		OBJECT-TYPE
			SYNTAX	INTEGER
			ACCESS	read-only
			STATUS	current
	DESCRIPTION ""
			::= { mbusB4 97 }

mbusB4VIF2E		OBJECT-TYPE
			SYNTAX	INTEGER
			ACCESS	read-only
			STATUS	current
	DESCRIPTION ""
			::= { mbusB4 98 }

mbusB4Value2E		OBJECT-TYPE
			SYNTAX	INTEGER
			ACCESS	read-only
			STATUS	current
	DESCRIPTION ""
			::= { mbusB4 99 }

mbusB4VIF2F		OBJECT-TYPE
			SYNTAX	INTEGER
			ACCESS	read-only
			STATUS	current
	DESCRIPTION ""
			::= { mbusB4 100 }

mbusB4Value2F		OBJECT-TYPE
			SYNTAX	INTEGER
			ACCESS	read-only
			STATUS	current
	DESCRIPTION ""
			::= { mbusB4 101 }

mbusB5			OBJECT IDENTIFIER ::= { mbus 181 }

mbusB5IdNumber		OBJECT-TYPE
			SYNTAX	Gauge
			ACCESS	read-only
			STATUS	current
	DESCRIPTION ""
			::= { mbusB5 1 }

mbusB5Manufacturer	OBJECT-TYPE
			SYNTAX	Gauge
			ACCESS	read-only
			STATUS	current
	DESCRIPTION ""
			::= { mbusB5 2 }

mbusB5Version		OBJECT-TYPE
			SYNTAX	Gauge
			ACCESS	read-only
			STATUS	current
	DESCRIPTION ""
			::= { mbusB5 3 }

mbusB5Medium		OBJECT-TYPE
			SYNTAX	Gauge
			ACCESS	read-only
			STATUS	current
	DESCRIPTION ""
			::= { mbusB5 4 }

mbusB5Status		OBJECT-TYPE
			SYNTAX	Gauge
			ACCESS	read-only
			STATUS	current
	DESCRIPTION ""
			::= { mbusB5 5 }

mbusB5VIF00		OBJECT-TYPE
			SYNTAX	INTEGER
			ACCESS	read-only
			STATUS	current
	DESCRIPTION ""
			::= { mbusB5 6 }

mbusB5Value00		OBJECT-TYPE
			SYNTAX	INTEGER
			ACCESS	read-only
			STATUS	current
	DESCRIPTION ""
			::= { mbusB5 7 }

mbusB5VIF01		OBJECT-TYPE
			SYNTAX	INTEGER
			ACCESS	read-only
			STATUS	current
	DESCRIPTION ""
			::= { mbusB5 8 }

mbusB5Value01		OBJECT-TYPE
			SYNTAX	INTEGER
			ACCESS	read-only
			STATUS	current
	DESCRIPTION ""
			::= { mbusB5 9 }

mbusB5VIF02		OBJECT-TYPE
			SYNTAX	INTEGER
			ACCESS	read-only
			STATUS	current
	DESCRIPTION ""
			::= { mbusB5 10 }

mbusB5Value02		OBJECT-TYPE
			SYNTAX	INTEGER
			ACCESS	read-only
			STATUS	current
	DESCRIPTION ""
			::= { mbusB5 11 }

mbusB5VIF03		OBJECT-TYPE
			SYNTAX	INTEGER
			ACCESS	read-only
			STATUS	current
	DESCRIPTION ""
			::= { mbusB5 12 }

mbusB5Value03		OBJECT-TYPE
			SYNTAX	INTEGER
			ACCESS	read-only
			STATUS	current
	DESCRIPTION ""
			::= { mbusB5 13 }

mbusB5VIF04		OBJECT-TYPE
			SYNTAX	INTEGER
			ACCESS	read-only
			STATUS	current
	DESCRIPTION ""
			::= { mbusB5 14 }

mbusB5Value04		OBJECT-TYPE
			SYNTAX	INTEGER
			ACCESS	read-only
			STATUS	current
	DESCRIPTION ""
			::= { mbusB5 15 }

mbusB5VIF05		OBJECT-TYPE
			SYNTAX	INTEGER
			ACCESS	read-only
			STATUS	current
	DESCRIPTION ""
			::= { mbusB5 16 }

mbusB5Value05		OBJECT-TYPE
			SYNTAX	INTEGER
			ACCESS	read-only
			STATUS	current
	DESCRIPTION ""
			::= { mbusB5 17 }

mbusB5VIF06		OBJECT-TYPE
			SYNTAX	INTEGER
			ACCESS	read-only
			STATUS	current
	DESCRIPTION ""
			::= { mbusB5 18 }

mbusB5Value06		OBJECT-TYPE
			SYNTAX	INTEGER
			ACCESS	read-only
			STATUS	current
	DESCRIPTION ""
			::= { mbusB5 19 }

mbusB5VIF07		OBJECT-TYPE
			SYNTAX	INTEGER
			ACCESS	read-only
			STATUS	current
	DESCRIPTION ""
			::= { mbusB5 20 }

mbusB5Value07		OBJECT-TYPE
			SYNTAX	INTEGER
			ACCESS	read-only
			STATUS	current
	DESCRIPTION ""
			::= { mbusB5 21 }

mbusB5VIF08		OBJECT-TYPE
			SYNTAX	INTEGER
			ACCESS	read-only
			STATUS	current
	DESCRIPTION ""
			::= { mbusB5 22 }

mbusB5Value08		OBJECT-TYPE
			SYNTAX	INTEGER
			ACCESS	read-only
			STATUS	current
	DESCRIPTION ""
			::= { mbusB5 23 }

mbusB5VIF09		OBJECT-TYPE
			SYNTAX	INTEGER
			ACCESS	read-only
			STATUS	current
	DESCRIPTION ""
			::= { mbusB5 24 }

mbusB5Value09		OBJECT-TYPE
			SYNTAX	INTEGER
			ACCESS	read-only
			STATUS	current
	DESCRIPTION ""
			::= { mbusB5 25 }

mbusB5VIF0A		OBJECT-TYPE
			SYNTAX	INTEGER
			ACCESS	read-only
			STATUS	current
	DESCRIPTION ""
			::= { mbusB5 26 }

mbusB5Value0A		OBJECT-TYPE
			SYNTAX	INTEGER
			ACCESS	read-only
			STATUS	current
	DESCRIPTION ""
			::= { mbusB5 27 }

mbusB5VIF0B		OBJECT-TYPE
			SYNTAX	INTEGER
			ACCESS	read-only
			STATUS	current
	DESCRIPTION ""
			::= { mbusB5 28 }

mbusB5Value0B		OBJECT-TYPE
			SYNTAX	INTEGER
			ACCESS	read-only
			STATUS	current
	DESCRIPTION ""
			::= { mbusB5 29 }

mbusB5VIF0C		OBJECT-TYPE
			SYNTAX	INTEGER
			ACCESS	read-only
			STATUS	current
	DESCRIPTION ""
			::= { mbusB5 30 }

mbusB5Value0C		OBJECT-TYPE
			SYNTAX	INTEGER
			ACCESS	read-only
			STATUS	current
	DESCRIPTION ""
			::= { mbusB5 31 }

mbusB5VIF0D		OBJECT-TYPE
			SYNTAX	INTEGER
			ACCESS	read-only
			STATUS	current
	DESCRIPTION ""
			::= { mbusB5 32 }

mbusB5Value0D		OBJECT-TYPE
			SYNTAX	INTEGER
			ACCESS	read-only
			STATUS	current
	DESCRIPTION ""
			::= { mbusB5 33 }

mbusB5VIF0E		OBJECT-TYPE
			SYNTAX	INTEGER
			ACCESS	read-only
			STATUS	current
	DESCRIPTION ""
			::= { mbusB5 34 }

mbusB5Value0E		OBJECT-TYPE
			SYNTAX	INTEGER
			ACCESS	read-only
			STATUS	current
	DESCRIPTION ""
			::= { mbusB5 35 }

mbusB5VIF0F		OBJECT-TYPE
			SYNTAX	INTEGER
			ACCESS	read-only
			STATUS	current
	DESCRIPTION ""
			::= { mbusB5 36 }

mbusB5Value0F		OBJECT-TYPE
			SYNTAX	INTEGER
			ACCESS	read-only
			STATUS	current
	DESCRIPTION ""
			::= { mbusB5 37 }

mbusB5VIF10		OBJECT-TYPE
			SYNTAX	INTEGER
			ACCESS	read-only
			STATUS	current
	DESCRIPTION ""
			::= { mbusB5 38 }

mbusB5Value10		OBJECT-TYPE
			SYNTAX	INTEGER
			ACCESS	read-only
			STATUS	current
	DESCRIPTION ""
			::= { mbusB5 39 }

mbusB5VIF11		OBJECT-TYPE
			SYNTAX	INTEGER
			ACCESS	read-only
			STATUS	current
	DESCRIPTION ""
			::= { mbusB5 40 }

mbusB5Value11		OBJECT-TYPE
			SYNTAX	INTEGER
			ACCESS	read-only
			STATUS	current
	DESCRIPTION ""
			::= { mbusB5 41 }

mbusB5VIF12		OBJECT-TYPE
			SYNTAX	INTEGER
			ACCESS	read-only
			STATUS	current
	DESCRIPTION ""
			::= { mbusB5 42 }

mbusB5Value12		OBJECT-TYPE
			SYNTAX	INTEGER
			ACCESS	read-only
			STATUS	current
	DESCRIPTION ""
			::= { mbusB5 43 }

mbusB5VIF13		OBJECT-TYPE
			SYNTAX	INTEGER
			ACCESS	read-only
			STATUS	current
	DESCRIPTION ""
			::= { mbusB5 44 }

mbusB5Value13		OBJECT-TYPE
			SYNTAX	INTEGER
			ACCESS	read-only
			STATUS	current
	DESCRIPTION ""
			::= { mbusB5 45 }

mbusB5VIF14		OBJECT-TYPE
			SYNTAX	INTEGER
			ACCESS	read-only
			STATUS	current
	DESCRIPTION ""
			::= { mbusB5 46 }

mbusB5Value14		OBJECT-TYPE
			SYNTAX	INTEGER
			ACCESS	read-only
			STATUS	current
	DESCRIPTION ""
			::= { mbusB5 47 }

mbusB5VIF15		OBJECT-TYPE
			SYNTAX	INTEGER
			ACCESS	read-only
			STATUS	current
	DESCRIPTION ""
			::= { mbusB5 48 }

mbusB5Value15		OBJECT-TYPE
			SYNTAX	INTEGER
			ACCESS	read-only
			STATUS	current
	DESCRIPTION ""
			::= { mbusB5 49 }

mbusB5VIF16		OBJECT-TYPE
			SYNTAX	INTEGER
			ACCESS	read-only
			STATUS	current
	DESCRIPTION ""
			::= { mbusB5 50 }

mbusB5Value16		OBJECT-TYPE
			SYNTAX	INTEGER
			ACCESS	read-only
			STATUS	current
	DESCRIPTION ""
			::= { mbusB5 51 }

mbusB5VIF17		OBJECT-TYPE
			SYNTAX	INTEGER
			ACCESS	read-only
			STATUS	current
	DESCRIPTION ""
			::= { mbusB5 52 }

mbusB5Value17		OBJECT-TYPE
			SYNTAX	INTEGER
			ACCESS	read-only
			STATUS	current
	DESCRIPTION ""
			::= { mbusB5 53 }

mbusB5VIF18		OBJECT-TYPE
			SYNTAX	INTEGER
			ACCESS	read-only
			STATUS	current
	DESCRIPTION ""
			::= { mbusB5 54 }

mbusB5Value18		OBJECT-TYPE
			SYNTAX	INTEGER
			ACCESS	read-only
			STATUS	current
	DESCRIPTION ""
			::= { mbusB5 55 }

mbusB5VIF19		OBJECT-TYPE
			SYNTAX	INTEGER
			ACCESS	read-only
			STATUS	current
	DESCRIPTION ""
			::= { mbusB5 56 }

mbusB5Value19		OBJECT-TYPE
			SYNTAX	INTEGER
			ACCESS	read-only
			STATUS	current
	DESCRIPTION ""
			::= { mbusB5 57 }

mbusB5VIF1A		OBJECT-TYPE
			SYNTAX	INTEGER
			ACCESS	read-only
			STATUS	current
	DESCRIPTION ""
			::= { mbusB5 58 }

mbusB5Value1A		OBJECT-TYPE
			SYNTAX	INTEGER
			ACCESS	read-only
			STATUS	current
	DESCRIPTION ""
			::= { mbusB5 59 }

mbusB5VIF1B		OBJECT-TYPE
			SYNTAX	INTEGER
			ACCESS	read-only
			STATUS	current
	DESCRIPTION ""
			::= { mbusB5 60 }

mbusB5Value1B		OBJECT-TYPE
			SYNTAX	INTEGER
			ACCESS	read-only
			STATUS	current
	DESCRIPTION ""
			::= { mbusB5 61 }

mbusB5VIF1C		OBJECT-TYPE
			SYNTAX	INTEGER
			ACCESS	read-only
			STATUS	current
	DESCRIPTION ""
			::= { mbusB5 62 }

mbusB5Value1C		OBJECT-TYPE
			SYNTAX	INTEGER
			ACCESS	read-only
			STATUS	current
	DESCRIPTION ""
			::= { mbusB5 63 }

mbusB5VIF1D		OBJECT-TYPE
			SYNTAX	INTEGER
			ACCESS	read-only
			STATUS	current
	DESCRIPTION ""
			::= { mbusB5 64 }

mbusB5Value1D		OBJECT-TYPE
			SYNTAX	INTEGER
			ACCESS	read-only
			STATUS	current
	DESCRIPTION ""
			::= { mbusB5 65 }

mbusB5VIF1E		OBJECT-TYPE
			SYNTAX	INTEGER
			ACCESS	read-only
			STATUS	current
	DESCRIPTION ""
			::= { mbusB5 66 }

mbusB5Value1E		OBJECT-TYPE
			SYNTAX	INTEGER
			ACCESS	read-only
			STATUS	current
	DESCRIPTION ""
			::= { mbusB5 67 }

mbusB5VIF1F		OBJECT-TYPE
			SYNTAX	INTEGER
			ACCESS	read-only
			STATUS	current
	DESCRIPTION ""
			::= { mbusB5 68 }

mbusB5Value1F		OBJECT-TYPE
			SYNTAX	INTEGER
			ACCESS	read-only
			STATUS	current
	DESCRIPTION ""
			::= { mbusB5 69 }

mbusB5VIF20		OBJECT-TYPE
			SYNTAX	INTEGER
			ACCESS	read-only
			STATUS	current
	DESCRIPTION ""
			::= { mbusB5 70 }

mbusB5Value20		OBJECT-TYPE
			SYNTAX	INTEGER
			ACCESS	read-only
			STATUS	current
	DESCRIPTION ""
			::= { mbusB5 71 }

mbusB5VIF21		OBJECT-TYPE
			SYNTAX	INTEGER
			ACCESS	read-only
			STATUS	current
	DESCRIPTION ""
			::= { mbusB5 72 }

mbusB5Value21		OBJECT-TYPE
			SYNTAX	INTEGER
			ACCESS	read-only
			STATUS	current
	DESCRIPTION ""
			::= { mbusB5 73 }

mbusB5VIF22		OBJECT-TYPE
			SYNTAX	INTEGER
			ACCESS	read-only
			STATUS	current
	DESCRIPTION ""
			::= { mbusB5 74 }

mbusB5Value22		OBJECT-TYPE
			SYNTAX	INTEGER
			ACCESS	read-only
			STATUS	current
	DESCRIPTION ""
			::= { mbusB5 75 }

mbusB5VIF23		OBJECT-TYPE
			SYNTAX	INTEGER
			ACCESS	read-only
			STATUS	current
	DESCRIPTION ""
			::= { mbusB5 76 }

mbusB5Value23		OBJECT-TYPE
			SYNTAX	INTEGER
			ACCESS	read-only
			STATUS	current
	DESCRIPTION ""
			::= { mbusB5 77 }

mbusB5VIF24		OBJECT-TYPE
			SYNTAX	INTEGER
			ACCESS	read-only
			STATUS	current
	DESCRIPTION ""
			::= { mbusB5 78 }

mbusB5Value24		OBJECT-TYPE
			SYNTAX	INTEGER
			ACCESS	read-only
			STATUS	current
	DESCRIPTION ""
			::= { mbusB5 79 }

mbusB5VIF25		OBJECT-TYPE
			SYNTAX	INTEGER
			ACCESS	read-only
			STATUS	current
	DESCRIPTION ""
			::= { mbusB5 80 }

mbusB5Value25		OBJECT-TYPE
			SYNTAX	INTEGER
			ACCESS	read-only
			STATUS	current
	DESCRIPTION ""
			::= { mbusB5 81 }

mbusB5VIF26		OBJECT-TYPE
			SYNTAX	INTEGER
			ACCESS	read-only
			STATUS	current
	DESCRIPTION ""
			::= { mbusB5 82 }

mbusB5Value26		OBJECT-TYPE
			SYNTAX	INTEGER
			ACCESS	read-only
			STATUS	current
	DESCRIPTION ""
			::= { mbusB5 83 }

mbusB5VIF27		OBJECT-TYPE
			SYNTAX	INTEGER
			ACCESS	read-only
			STATUS	current
	DESCRIPTION ""
			::= { mbusB5 84 }

mbusB5Value27		OBJECT-TYPE
			SYNTAX	INTEGER
			ACCESS	read-only
			STATUS	current
	DESCRIPTION ""
			::= { mbusB5 85 }

mbusB5VIF28		OBJECT-TYPE
			SYNTAX	INTEGER
			ACCESS	read-only
			STATUS	current
	DESCRIPTION ""
			::= { mbusB5 86 }

mbusB5Value28		OBJECT-TYPE
			SYNTAX	INTEGER
			ACCESS	read-only
			STATUS	current
	DESCRIPTION ""
			::= { mbusB5 87 }

mbusB5VIF29		OBJECT-TYPE
			SYNTAX	INTEGER
			ACCESS	read-only
			STATUS	current
	DESCRIPTION ""
			::= { mbusB5 88 }

mbusB5Value29		OBJECT-TYPE
			SYNTAX	INTEGER
			ACCESS	read-only
			STATUS	current
	DESCRIPTION ""
			::= { mbusB5 89 }

mbusB5VIF2A		OBJECT-TYPE
			SYNTAX	INTEGER
			ACCESS	read-only
			STATUS	current
	DESCRIPTION ""
			::= { mbusB5 90 }

mbusB5Value2A		OBJECT-TYPE
			SYNTAX	INTEGER
			ACCESS	read-only
			STATUS	current
	DESCRIPTION ""
			::= { mbusB5 91 }

mbusB5VIF2B		OBJECT-TYPE
			SYNTAX	INTEGER
			ACCESS	read-only
			STATUS	current
	DESCRIPTION ""
			::= { mbusB5 92 }

mbusB5Value2B		OBJECT-TYPE
			SYNTAX	INTEGER
			ACCESS	read-only
			STATUS	current
	DESCRIPTION ""
			::= { mbusB5 93 }

mbusB5VIF2C		OBJECT-TYPE
			SYNTAX	INTEGER
			ACCESS	read-only
			STATUS	current
	DESCRIPTION ""
			::= { mbusB5 94 }

mbusB5Value2C		OBJECT-TYPE
			SYNTAX	INTEGER
			ACCESS	read-only
			STATUS	current
	DESCRIPTION ""
			::= { mbusB5 95 }

mbusB5VIF2D		OBJECT-TYPE
			SYNTAX	INTEGER
			ACCESS	read-only
			STATUS	current
	DESCRIPTION ""
			::= { mbusB5 96 }

mbusB5Value2D		OBJECT-TYPE
			SYNTAX	INTEGER
			ACCESS	read-only
			STATUS	current
	DESCRIPTION ""
			::= { mbusB5 97 }

mbusB5VIF2E		OBJECT-TYPE
			SYNTAX	INTEGER
			ACCESS	read-only
			STATUS	current
	DESCRIPTION ""
			::= { mbusB5 98 }

mbusB5Value2E		OBJECT-TYPE
			SYNTAX	INTEGER
			ACCESS	read-only
			STATUS	current
	DESCRIPTION ""
			::= { mbusB5 99 }

mbusB5VIF2F		OBJECT-TYPE
			SYNTAX	INTEGER
			ACCESS	read-only
			STATUS	current
	DESCRIPTION ""
			::= { mbusB5 100 }

mbusB5Value2F		OBJECT-TYPE
			SYNTAX	INTEGER
			ACCESS	read-only
			STATUS	current
	DESCRIPTION ""
			::= { mbusB5 101 }

mbusB6			OBJECT IDENTIFIER ::= { mbus 182 }

mbusB6IdNumber		OBJECT-TYPE
			SYNTAX	Gauge
			ACCESS	read-only
			STATUS	current
	DESCRIPTION ""
			::= { mbusB6 1 }

mbusB6Manufacturer	OBJECT-TYPE
			SYNTAX	Gauge
			ACCESS	read-only
			STATUS	current
	DESCRIPTION ""
			::= { mbusB6 2 }

mbusB6Version		OBJECT-TYPE
			SYNTAX	Gauge
			ACCESS	read-only
			STATUS	current
	DESCRIPTION ""
			::= { mbusB6 3 }

mbusB6Medium		OBJECT-TYPE
			SYNTAX	Gauge
			ACCESS	read-only
			STATUS	current
	DESCRIPTION ""
			::= { mbusB6 4 }

mbusB6Status		OBJECT-TYPE
			SYNTAX	Gauge
			ACCESS	read-only
			STATUS	current
	DESCRIPTION ""
			::= { mbusB6 5 }

mbusB6VIF00		OBJECT-TYPE
			SYNTAX	INTEGER
			ACCESS	read-only
			STATUS	current
	DESCRIPTION ""
			::= { mbusB6 6 }

mbusB6Value00		OBJECT-TYPE
			SYNTAX	INTEGER
			ACCESS	read-only
			STATUS	current
	DESCRIPTION ""
			::= { mbusB6 7 }

mbusB6VIF01		OBJECT-TYPE
			SYNTAX	INTEGER
			ACCESS	read-only
			STATUS	current
	DESCRIPTION ""
			::= { mbusB6 8 }

mbusB6Value01		OBJECT-TYPE
			SYNTAX	INTEGER
			ACCESS	read-only
			STATUS	current
	DESCRIPTION ""
			::= { mbusB6 9 }

mbusB6VIF02		OBJECT-TYPE
			SYNTAX	INTEGER
			ACCESS	read-only
			STATUS	current
	DESCRIPTION ""
			::= { mbusB6 10 }

mbusB6Value02		OBJECT-TYPE
			SYNTAX	INTEGER
			ACCESS	read-only
			STATUS	current
	DESCRIPTION ""
			::= { mbusB6 11 }

mbusB6VIF03		OBJECT-TYPE
			SYNTAX	INTEGER
			ACCESS	read-only
			STATUS	current
	DESCRIPTION ""
			::= { mbusB6 12 }

mbusB6Value03		OBJECT-TYPE
			SYNTAX	INTEGER
			ACCESS	read-only
			STATUS	current
	DESCRIPTION ""
			::= { mbusB6 13 }

mbusB6VIF04		OBJECT-TYPE
			SYNTAX	INTEGER
			ACCESS	read-only
			STATUS	current
	DESCRIPTION ""
			::= { mbusB6 14 }

mbusB6Value04		OBJECT-TYPE
			SYNTAX	INTEGER
			ACCESS	read-only
			STATUS	current
	DESCRIPTION ""
			::= { mbusB6 15 }

mbusB6VIF05		OBJECT-TYPE
			SYNTAX	INTEGER
			ACCESS	read-only
			STATUS	current
	DESCRIPTION ""
			::= { mbusB6 16 }

mbusB6Value05		OBJECT-TYPE
			SYNTAX	INTEGER
			ACCESS	read-only
			STATUS	current
	DESCRIPTION ""
			::= { mbusB6 17 }

mbusB6VIF06		OBJECT-TYPE
			SYNTAX	INTEGER
			ACCESS	read-only
			STATUS	current
	DESCRIPTION ""
			::= { mbusB6 18 }

mbusB6Value06		OBJECT-TYPE
			SYNTAX	INTEGER
			ACCESS	read-only
			STATUS	current
	DESCRIPTION ""
			::= { mbusB6 19 }

mbusB6VIF07		OBJECT-TYPE
			SYNTAX	INTEGER
			ACCESS	read-only
			STATUS	current
	DESCRIPTION ""
			::= { mbusB6 20 }

mbusB6Value07		OBJECT-TYPE
			SYNTAX	INTEGER
			ACCESS	read-only
			STATUS	current
	DESCRIPTION ""
			::= { mbusB6 21 }

mbusB6VIF08		OBJECT-TYPE
			SYNTAX	INTEGER
			ACCESS	read-only
			STATUS	current
	DESCRIPTION ""
			::= { mbusB6 22 }

mbusB6Value08		OBJECT-TYPE
			SYNTAX	INTEGER
			ACCESS	read-only
			STATUS	current
	DESCRIPTION ""
			::= { mbusB6 23 }

mbusB6VIF09		OBJECT-TYPE
			SYNTAX	INTEGER
			ACCESS	read-only
			STATUS	current
	DESCRIPTION ""
			::= { mbusB6 24 }

mbusB6Value09		OBJECT-TYPE
			SYNTAX	INTEGER
			ACCESS	read-only
			STATUS	current
	DESCRIPTION ""
			::= { mbusB6 25 }

mbusB6VIF0A		OBJECT-TYPE
			SYNTAX	INTEGER
			ACCESS	read-only
			STATUS	current
	DESCRIPTION ""
			::= { mbusB6 26 }

mbusB6Value0A		OBJECT-TYPE
			SYNTAX	INTEGER
			ACCESS	read-only
			STATUS	current
	DESCRIPTION ""
			::= { mbusB6 27 }

mbusB6VIF0B		OBJECT-TYPE
			SYNTAX	INTEGER
			ACCESS	read-only
			STATUS	current
	DESCRIPTION ""
			::= { mbusB6 28 }

mbusB6Value0B		OBJECT-TYPE
			SYNTAX	INTEGER
			ACCESS	read-only
			STATUS	current
	DESCRIPTION ""
			::= { mbusB6 29 }

mbusB6VIF0C		OBJECT-TYPE
			SYNTAX	INTEGER
			ACCESS	read-only
			STATUS	current
	DESCRIPTION ""
			::= { mbusB6 30 }

mbusB6Value0C		OBJECT-TYPE
			SYNTAX	INTEGER
			ACCESS	read-only
			STATUS	current
	DESCRIPTION ""
			::= { mbusB6 31 }

mbusB6VIF0D		OBJECT-TYPE
			SYNTAX	INTEGER
			ACCESS	read-only
			STATUS	current
	DESCRIPTION ""
			::= { mbusB6 32 }

mbusB6Value0D		OBJECT-TYPE
			SYNTAX	INTEGER
			ACCESS	read-only
			STATUS	current
	DESCRIPTION ""
			::= { mbusB6 33 }

mbusB6VIF0E		OBJECT-TYPE
			SYNTAX	INTEGER
			ACCESS	read-only
			STATUS	current
	DESCRIPTION ""
			::= { mbusB6 34 }

mbusB6Value0E		OBJECT-TYPE
			SYNTAX	INTEGER
			ACCESS	read-only
			STATUS	current
	DESCRIPTION ""
			::= { mbusB6 35 }

mbusB6VIF0F		OBJECT-TYPE
			SYNTAX	INTEGER
			ACCESS	read-only
			STATUS	current
	DESCRIPTION ""
			::= { mbusB6 36 }

mbusB6Value0F		OBJECT-TYPE
			SYNTAX	INTEGER
			ACCESS	read-only
			STATUS	current
	DESCRIPTION ""
			::= { mbusB6 37 }

mbusB6VIF10		OBJECT-TYPE
			SYNTAX	INTEGER
			ACCESS	read-only
			STATUS	current
	DESCRIPTION ""
			::= { mbusB6 38 }

mbusB6Value10		OBJECT-TYPE
			SYNTAX	INTEGER
			ACCESS	read-only
			STATUS	current
	DESCRIPTION ""
			::= { mbusB6 39 }

mbusB6VIF11		OBJECT-TYPE
			SYNTAX	INTEGER
			ACCESS	read-only
			STATUS	current
	DESCRIPTION ""
			::= { mbusB6 40 }

mbusB6Value11		OBJECT-TYPE
			SYNTAX	INTEGER
			ACCESS	read-only
			STATUS	current
	DESCRIPTION ""
			::= { mbusB6 41 }

mbusB6VIF12		OBJECT-TYPE
			SYNTAX	INTEGER
			ACCESS	read-only
			STATUS	current
	DESCRIPTION ""
			::= { mbusB6 42 }

mbusB6Value12		OBJECT-TYPE
			SYNTAX	INTEGER
			ACCESS	read-only
			STATUS	current
	DESCRIPTION ""
			::= { mbusB6 43 }

mbusB6VIF13		OBJECT-TYPE
			SYNTAX	INTEGER
			ACCESS	read-only
			STATUS	current
	DESCRIPTION ""
			::= { mbusB6 44 }

mbusB6Value13		OBJECT-TYPE
			SYNTAX	INTEGER
			ACCESS	read-only
			STATUS	current
	DESCRIPTION ""
			::= { mbusB6 45 }

mbusB6VIF14		OBJECT-TYPE
			SYNTAX	INTEGER
			ACCESS	read-only
			STATUS	current
	DESCRIPTION ""
			::= { mbusB6 46 }

mbusB6Value14		OBJECT-TYPE
			SYNTAX	INTEGER
			ACCESS	read-only
			STATUS	current
	DESCRIPTION ""
			::= { mbusB6 47 }

mbusB6VIF15		OBJECT-TYPE
			SYNTAX	INTEGER
			ACCESS	read-only
			STATUS	current
	DESCRIPTION ""
			::= { mbusB6 48 }

mbusB6Value15		OBJECT-TYPE
			SYNTAX	INTEGER
			ACCESS	read-only
			STATUS	current
	DESCRIPTION ""
			::= { mbusB6 49 }

mbusB6VIF16		OBJECT-TYPE
			SYNTAX	INTEGER
			ACCESS	read-only
			STATUS	current
	DESCRIPTION ""
			::= { mbusB6 50 }

mbusB6Value16		OBJECT-TYPE
			SYNTAX	INTEGER
			ACCESS	read-only
			STATUS	current
	DESCRIPTION ""
			::= { mbusB6 51 }

mbusB6VIF17		OBJECT-TYPE
			SYNTAX	INTEGER
			ACCESS	read-only
			STATUS	current
	DESCRIPTION ""
			::= { mbusB6 52 }

mbusB6Value17		OBJECT-TYPE
			SYNTAX	INTEGER
			ACCESS	read-only
			STATUS	current
	DESCRIPTION ""
			::= { mbusB6 53 }

mbusB6VIF18		OBJECT-TYPE
			SYNTAX	INTEGER
			ACCESS	read-only
			STATUS	current
	DESCRIPTION ""
			::= { mbusB6 54 }

mbusB6Value18		OBJECT-TYPE
			SYNTAX	INTEGER
			ACCESS	read-only
			STATUS	current
	DESCRIPTION ""
			::= { mbusB6 55 }

mbusB6VIF19		OBJECT-TYPE
			SYNTAX	INTEGER
			ACCESS	read-only
			STATUS	current
	DESCRIPTION ""
			::= { mbusB6 56 }

mbusB6Value19		OBJECT-TYPE
			SYNTAX	INTEGER
			ACCESS	read-only
			STATUS	current
	DESCRIPTION ""
			::= { mbusB6 57 }

mbusB6VIF1A		OBJECT-TYPE
			SYNTAX	INTEGER
			ACCESS	read-only
			STATUS	current
	DESCRIPTION ""
			::= { mbusB6 58 }

mbusB6Value1A		OBJECT-TYPE
			SYNTAX	INTEGER
			ACCESS	read-only
			STATUS	current
	DESCRIPTION ""
			::= { mbusB6 59 }

mbusB6VIF1B		OBJECT-TYPE
			SYNTAX	INTEGER
			ACCESS	read-only
			STATUS	current
	DESCRIPTION ""
			::= { mbusB6 60 }

mbusB6Value1B		OBJECT-TYPE
			SYNTAX	INTEGER
			ACCESS	read-only
			STATUS	current
	DESCRIPTION ""
			::= { mbusB6 61 }

mbusB6VIF1C		OBJECT-TYPE
			SYNTAX	INTEGER
			ACCESS	read-only
			STATUS	current
	DESCRIPTION ""
			::= { mbusB6 62 }

mbusB6Value1C		OBJECT-TYPE
			SYNTAX	INTEGER
			ACCESS	read-only
			STATUS	current
	DESCRIPTION ""
			::= { mbusB6 63 }

mbusB6VIF1D		OBJECT-TYPE
			SYNTAX	INTEGER
			ACCESS	read-only
			STATUS	current
	DESCRIPTION ""
			::= { mbusB6 64 }

mbusB6Value1D		OBJECT-TYPE
			SYNTAX	INTEGER
			ACCESS	read-only
			STATUS	current
	DESCRIPTION ""
			::= { mbusB6 65 }

mbusB6VIF1E		OBJECT-TYPE
			SYNTAX	INTEGER
			ACCESS	read-only
			STATUS	current
	DESCRIPTION ""
			::= { mbusB6 66 }

mbusB6Value1E		OBJECT-TYPE
			SYNTAX	INTEGER
			ACCESS	read-only
			STATUS	current
	DESCRIPTION ""
			::= { mbusB6 67 }

mbusB6VIF1F		OBJECT-TYPE
			SYNTAX	INTEGER
			ACCESS	read-only
			STATUS	current
	DESCRIPTION ""
			::= { mbusB6 68 }

mbusB6Value1F		OBJECT-TYPE
			SYNTAX	INTEGER
			ACCESS	read-only
			STATUS	current
	DESCRIPTION ""
			::= { mbusB6 69 }

mbusB6VIF20		OBJECT-TYPE
			SYNTAX	INTEGER
			ACCESS	read-only
			STATUS	current
	DESCRIPTION ""
			::= { mbusB6 70 }

mbusB6Value20		OBJECT-TYPE
			SYNTAX	INTEGER
			ACCESS	read-only
			STATUS	current
	DESCRIPTION ""
			::= { mbusB6 71 }

mbusB6VIF21		OBJECT-TYPE
			SYNTAX	INTEGER
			ACCESS	read-only
			STATUS	current
	DESCRIPTION ""
			::= { mbusB6 72 }

mbusB6Value21		OBJECT-TYPE
			SYNTAX	INTEGER
			ACCESS	read-only
			STATUS	current
	DESCRIPTION ""
			::= { mbusB6 73 }

mbusB6VIF22		OBJECT-TYPE
			SYNTAX	INTEGER
			ACCESS	read-only
			STATUS	current
	DESCRIPTION ""
			::= { mbusB6 74 }

mbusB6Value22		OBJECT-TYPE
			SYNTAX	INTEGER
			ACCESS	read-only
			STATUS	current
	DESCRIPTION ""
			::= { mbusB6 75 }

mbusB6VIF23		OBJECT-TYPE
			SYNTAX	INTEGER
			ACCESS	read-only
			STATUS	current
	DESCRIPTION ""
			::= { mbusB6 76 }

mbusB6Value23		OBJECT-TYPE
			SYNTAX	INTEGER
			ACCESS	read-only
			STATUS	current
	DESCRIPTION ""
			::= { mbusB6 77 }

mbusB6VIF24		OBJECT-TYPE
			SYNTAX	INTEGER
			ACCESS	read-only
			STATUS	current
	DESCRIPTION ""
			::= { mbusB6 78 }

mbusB6Value24		OBJECT-TYPE
			SYNTAX	INTEGER
			ACCESS	read-only
			STATUS	current
	DESCRIPTION ""
			::= { mbusB6 79 }

mbusB6VIF25		OBJECT-TYPE
			SYNTAX	INTEGER
			ACCESS	read-only
			STATUS	current
	DESCRIPTION ""
			::= { mbusB6 80 }

mbusB6Value25		OBJECT-TYPE
			SYNTAX	INTEGER
			ACCESS	read-only
			STATUS	current
	DESCRIPTION ""
			::= { mbusB6 81 }

mbusB6VIF26		OBJECT-TYPE
			SYNTAX	INTEGER
			ACCESS	read-only
			STATUS	current
	DESCRIPTION ""
			::= { mbusB6 82 }

mbusB6Value26		OBJECT-TYPE
			SYNTAX	INTEGER
			ACCESS	read-only
			STATUS	current
	DESCRIPTION ""
			::= { mbusB6 83 }

mbusB6VIF27		OBJECT-TYPE
			SYNTAX	INTEGER
			ACCESS	read-only
			STATUS	current
	DESCRIPTION ""
			::= { mbusB6 84 }

mbusB6Value27		OBJECT-TYPE
			SYNTAX	INTEGER
			ACCESS	read-only
			STATUS	current
	DESCRIPTION ""
			::= { mbusB6 85 }

mbusB6VIF28		OBJECT-TYPE
			SYNTAX	INTEGER
			ACCESS	read-only
			STATUS	current
	DESCRIPTION ""
			::= { mbusB6 86 }

mbusB6Value28		OBJECT-TYPE
			SYNTAX	INTEGER
			ACCESS	read-only
			STATUS	current
	DESCRIPTION ""
			::= { mbusB6 87 }

mbusB6VIF29		OBJECT-TYPE
			SYNTAX	INTEGER
			ACCESS	read-only
			STATUS	current
	DESCRIPTION ""
			::= { mbusB6 88 }

mbusB6Value29		OBJECT-TYPE
			SYNTAX	INTEGER
			ACCESS	read-only
			STATUS	current
	DESCRIPTION ""
			::= { mbusB6 89 }

mbusB6VIF2A		OBJECT-TYPE
			SYNTAX	INTEGER
			ACCESS	read-only
			STATUS	current
	DESCRIPTION ""
			::= { mbusB6 90 }

mbusB6Value2A		OBJECT-TYPE
			SYNTAX	INTEGER
			ACCESS	read-only
			STATUS	current
	DESCRIPTION ""
			::= { mbusB6 91 }

mbusB6VIF2B		OBJECT-TYPE
			SYNTAX	INTEGER
			ACCESS	read-only
			STATUS	current
	DESCRIPTION ""
			::= { mbusB6 92 }

mbusB6Value2B		OBJECT-TYPE
			SYNTAX	INTEGER
			ACCESS	read-only
			STATUS	current
	DESCRIPTION ""
			::= { mbusB6 93 }

mbusB6VIF2C		OBJECT-TYPE
			SYNTAX	INTEGER
			ACCESS	read-only
			STATUS	current
	DESCRIPTION ""
			::= { mbusB6 94 }

mbusB6Value2C		OBJECT-TYPE
			SYNTAX	INTEGER
			ACCESS	read-only
			STATUS	current
	DESCRIPTION ""
			::= { mbusB6 95 }

mbusB6VIF2D		OBJECT-TYPE
			SYNTAX	INTEGER
			ACCESS	read-only
			STATUS	current
	DESCRIPTION ""
			::= { mbusB6 96 }

mbusB6Value2D		OBJECT-TYPE
			SYNTAX	INTEGER
			ACCESS	read-only
			STATUS	current
	DESCRIPTION ""
			::= { mbusB6 97 }

mbusB6VIF2E		OBJECT-TYPE
			SYNTAX	INTEGER
			ACCESS	read-only
			STATUS	current
	DESCRIPTION ""
			::= { mbusB6 98 }

mbusB6Value2E		OBJECT-TYPE
			SYNTAX	INTEGER
			ACCESS	read-only
			STATUS	current
	DESCRIPTION ""
			::= { mbusB6 99 }

mbusB6VIF2F		OBJECT-TYPE
			SYNTAX	INTEGER
			ACCESS	read-only
			STATUS	current
	DESCRIPTION ""
			::= { mbusB6 100 }

mbusB6Value2F		OBJECT-TYPE
			SYNTAX	INTEGER
			ACCESS	read-only
			STATUS	current
	DESCRIPTION ""
			::= { mbusB6 101 }

mbusB7			OBJECT IDENTIFIER ::= { mbus 183 }

mbusB7IdNumber		OBJECT-TYPE
			SYNTAX	Gauge
			ACCESS	read-only
			STATUS	current
	DESCRIPTION ""
			::= { mbusB7 1 }

mbusB7Manufacturer	OBJECT-TYPE
			SYNTAX	Gauge
			ACCESS	read-only
			STATUS	current
	DESCRIPTION ""
			::= { mbusB7 2 }

mbusB7Version		OBJECT-TYPE
			SYNTAX	Gauge
			ACCESS	read-only
			STATUS	current
	DESCRIPTION ""
			::= { mbusB7 3 }

mbusB7Medium		OBJECT-TYPE
			SYNTAX	Gauge
			ACCESS	read-only
			STATUS	current
	DESCRIPTION ""
			::= { mbusB7 4 }

mbusB7Status		OBJECT-TYPE
			SYNTAX	Gauge
			ACCESS	read-only
			STATUS	current
	DESCRIPTION ""
			::= { mbusB7 5 }

mbusB7VIF00		OBJECT-TYPE
			SYNTAX	INTEGER
			ACCESS	read-only
			STATUS	current
	DESCRIPTION ""
			::= { mbusB7 6 }

mbusB7Value00		OBJECT-TYPE
			SYNTAX	INTEGER
			ACCESS	read-only
			STATUS	current
	DESCRIPTION ""
			::= { mbusB7 7 }

mbusB7VIF01		OBJECT-TYPE
			SYNTAX	INTEGER
			ACCESS	read-only
			STATUS	current
	DESCRIPTION ""
			::= { mbusB7 8 }

mbusB7Value01		OBJECT-TYPE
			SYNTAX	INTEGER
			ACCESS	read-only
			STATUS	current
	DESCRIPTION ""
			::= { mbusB7 9 }

mbusB7VIF02		OBJECT-TYPE
			SYNTAX	INTEGER
			ACCESS	read-only
			STATUS	current
	DESCRIPTION ""
			::= { mbusB7 10 }

mbusB7Value02		OBJECT-TYPE
			SYNTAX	INTEGER
			ACCESS	read-only
			STATUS	current
	DESCRIPTION ""
			::= { mbusB7 11 }

mbusB7VIF03		OBJECT-TYPE
			SYNTAX	INTEGER
			ACCESS	read-only
			STATUS	current
	DESCRIPTION ""
			::= { mbusB7 12 }

mbusB7Value03		OBJECT-TYPE
			SYNTAX	INTEGER
			ACCESS	read-only
			STATUS	current
	DESCRIPTION ""
			::= { mbusB7 13 }

mbusB7VIF04		OBJECT-TYPE
			SYNTAX	INTEGER
			ACCESS	read-only
			STATUS	current
	DESCRIPTION ""
			::= { mbusB7 14 }

mbusB7Value04		OBJECT-TYPE
			SYNTAX	INTEGER
			ACCESS	read-only
			STATUS	current
	DESCRIPTION ""
			::= { mbusB7 15 }

mbusB7VIF05		OBJECT-TYPE
			SYNTAX	INTEGER
			ACCESS	read-only
			STATUS	current
	DESCRIPTION ""
			::= { mbusB7 16 }

mbusB7Value05		OBJECT-TYPE
			SYNTAX	INTEGER
			ACCESS	read-only
			STATUS	current
	DESCRIPTION ""
			::= { mbusB7 17 }

mbusB7VIF06		OBJECT-TYPE
			SYNTAX	INTEGER
			ACCESS	read-only
			STATUS	current
	DESCRIPTION ""
			::= { mbusB7 18 }

mbusB7Value06		OBJECT-TYPE
			SYNTAX	INTEGER
			ACCESS	read-only
			STATUS	current
	DESCRIPTION ""
			::= { mbusB7 19 }

mbusB7VIF07		OBJECT-TYPE
			SYNTAX	INTEGER
			ACCESS	read-only
			STATUS	current
	DESCRIPTION ""
			::= { mbusB7 20 }

mbusB7Value07		OBJECT-TYPE
			SYNTAX	INTEGER
			ACCESS	read-only
			STATUS	current
	DESCRIPTION ""
			::= { mbusB7 21 }

mbusB7VIF08		OBJECT-TYPE
			SYNTAX	INTEGER
			ACCESS	read-only
			STATUS	current
	DESCRIPTION ""
			::= { mbusB7 22 }

mbusB7Value08		OBJECT-TYPE
			SYNTAX	INTEGER
			ACCESS	read-only
			STATUS	current
	DESCRIPTION ""
			::= { mbusB7 23 }

mbusB7VIF09		OBJECT-TYPE
			SYNTAX	INTEGER
			ACCESS	read-only
			STATUS	current
	DESCRIPTION ""
			::= { mbusB7 24 }

mbusB7Value09		OBJECT-TYPE
			SYNTAX	INTEGER
			ACCESS	read-only
			STATUS	current
	DESCRIPTION ""
			::= { mbusB7 25 }

mbusB7VIF0A		OBJECT-TYPE
			SYNTAX	INTEGER
			ACCESS	read-only
			STATUS	current
	DESCRIPTION ""
			::= { mbusB7 26 }

mbusB7Value0A		OBJECT-TYPE
			SYNTAX	INTEGER
			ACCESS	read-only
			STATUS	current
	DESCRIPTION ""
			::= { mbusB7 27 }

mbusB7VIF0B		OBJECT-TYPE
			SYNTAX	INTEGER
			ACCESS	read-only
			STATUS	current
	DESCRIPTION ""
			::= { mbusB7 28 }

mbusB7Value0B		OBJECT-TYPE
			SYNTAX	INTEGER
			ACCESS	read-only
			STATUS	current
	DESCRIPTION ""
			::= { mbusB7 29 }

mbusB7VIF0C		OBJECT-TYPE
			SYNTAX	INTEGER
			ACCESS	read-only
			STATUS	current
	DESCRIPTION ""
			::= { mbusB7 30 }

mbusB7Value0C		OBJECT-TYPE
			SYNTAX	INTEGER
			ACCESS	read-only
			STATUS	current
	DESCRIPTION ""
			::= { mbusB7 31 }

mbusB7VIF0D		OBJECT-TYPE
			SYNTAX	INTEGER
			ACCESS	read-only
			STATUS	current
	DESCRIPTION ""
			::= { mbusB7 32 }

mbusB7Value0D		OBJECT-TYPE
			SYNTAX	INTEGER
			ACCESS	read-only
			STATUS	current
	DESCRIPTION ""
			::= { mbusB7 33 }

mbusB7VIF0E		OBJECT-TYPE
			SYNTAX	INTEGER
			ACCESS	read-only
			STATUS	current
	DESCRIPTION ""
			::= { mbusB7 34 }

mbusB7Value0E		OBJECT-TYPE
			SYNTAX	INTEGER
			ACCESS	read-only
			STATUS	current
	DESCRIPTION ""
			::= { mbusB7 35 }

mbusB7VIF0F		OBJECT-TYPE
			SYNTAX	INTEGER
			ACCESS	read-only
			STATUS	current
	DESCRIPTION ""
			::= { mbusB7 36 }

mbusB7Value0F		OBJECT-TYPE
			SYNTAX	INTEGER
			ACCESS	read-only
			STATUS	current
	DESCRIPTION ""
			::= { mbusB7 37 }

mbusB7VIF10		OBJECT-TYPE
			SYNTAX	INTEGER
			ACCESS	read-only
			STATUS	current
	DESCRIPTION ""
			::= { mbusB7 38 }

mbusB7Value10		OBJECT-TYPE
			SYNTAX	INTEGER
			ACCESS	read-only
			STATUS	current
	DESCRIPTION ""
			::= { mbusB7 39 }

mbusB7VIF11		OBJECT-TYPE
			SYNTAX	INTEGER
			ACCESS	read-only
			STATUS	current
	DESCRIPTION ""
			::= { mbusB7 40 }

mbusB7Value11		OBJECT-TYPE
			SYNTAX	INTEGER
			ACCESS	read-only
			STATUS	current
	DESCRIPTION ""
			::= { mbusB7 41 }

mbusB7VIF12		OBJECT-TYPE
			SYNTAX	INTEGER
			ACCESS	read-only
			STATUS	current
	DESCRIPTION ""
			::= { mbusB7 42 }

mbusB7Value12		OBJECT-TYPE
			SYNTAX	INTEGER
			ACCESS	read-only
			STATUS	current
	DESCRIPTION ""
			::= { mbusB7 43 }

mbusB7VIF13		OBJECT-TYPE
			SYNTAX	INTEGER
			ACCESS	read-only
			STATUS	current
	DESCRIPTION ""
			::= { mbusB7 44 }

mbusB7Value13		OBJECT-TYPE
			SYNTAX	INTEGER
			ACCESS	read-only
			STATUS	current
	DESCRIPTION ""
			::= { mbusB7 45 }

mbusB7VIF14		OBJECT-TYPE
			SYNTAX	INTEGER
			ACCESS	read-only
			STATUS	current
	DESCRIPTION ""
			::= { mbusB7 46 }

mbusB7Value14		OBJECT-TYPE
			SYNTAX	INTEGER
			ACCESS	read-only
			STATUS	current
	DESCRIPTION ""
			::= { mbusB7 47 }

mbusB7VIF15		OBJECT-TYPE
			SYNTAX	INTEGER
			ACCESS	read-only
			STATUS	current
	DESCRIPTION ""
			::= { mbusB7 48 }

mbusB7Value15		OBJECT-TYPE
			SYNTAX	INTEGER
			ACCESS	read-only
			STATUS	current
	DESCRIPTION ""
			::= { mbusB7 49 }

mbusB7VIF16		OBJECT-TYPE
			SYNTAX	INTEGER
			ACCESS	read-only
			STATUS	current
	DESCRIPTION ""
			::= { mbusB7 50 }

mbusB7Value16		OBJECT-TYPE
			SYNTAX	INTEGER
			ACCESS	read-only
			STATUS	current
	DESCRIPTION ""
			::= { mbusB7 51 }

mbusB7VIF17		OBJECT-TYPE
			SYNTAX	INTEGER
			ACCESS	read-only
			STATUS	current
	DESCRIPTION ""
			::= { mbusB7 52 }

mbusB7Value17		OBJECT-TYPE
			SYNTAX	INTEGER
			ACCESS	read-only
			STATUS	current
	DESCRIPTION ""
			::= { mbusB7 53 }

mbusB7VIF18		OBJECT-TYPE
			SYNTAX	INTEGER
			ACCESS	read-only
			STATUS	current
	DESCRIPTION ""
			::= { mbusB7 54 }

mbusB7Value18		OBJECT-TYPE
			SYNTAX	INTEGER
			ACCESS	read-only
			STATUS	current
	DESCRIPTION ""
			::= { mbusB7 55 }

mbusB7VIF19		OBJECT-TYPE
			SYNTAX	INTEGER
			ACCESS	read-only
			STATUS	current
	DESCRIPTION ""
			::= { mbusB7 56 }

mbusB7Value19		OBJECT-TYPE
			SYNTAX	INTEGER
			ACCESS	read-only
			STATUS	current
	DESCRIPTION ""
			::= { mbusB7 57 }

mbusB7VIF1A		OBJECT-TYPE
			SYNTAX	INTEGER
			ACCESS	read-only
			STATUS	current
	DESCRIPTION ""
			::= { mbusB7 58 }

mbusB7Value1A		OBJECT-TYPE
			SYNTAX	INTEGER
			ACCESS	read-only
			STATUS	current
	DESCRIPTION ""
			::= { mbusB7 59 }

mbusB7VIF1B		OBJECT-TYPE
			SYNTAX	INTEGER
			ACCESS	read-only
			STATUS	current
	DESCRIPTION ""
			::= { mbusB7 60 }

mbusB7Value1B		OBJECT-TYPE
			SYNTAX	INTEGER
			ACCESS	read-only
			STATUS	current
	DESCRIPTION ""
			::= { mbusB7 61 }

mbusB7VIF1C		OBJECT-TYPE
			SYNTAX	INTEGER
			ACCESS	read-only
			STATUS	current
	DESCRIPTION ""
			::= { mbusB7 62 }

mbusB7Value1C		OBJECT-TYPE
			SYNTAX	INTEGER
			ACCESS	read-only
			STATUS	current
	DESCRIPTION ""
			::= { mbusB7 63 }

mbusB7VIF1D		OBJECT-TYPE
			SYNTAX	INTEGER
			ACCESS	read-only
			STATUS	current
	DESCRIPTION ""
			::= { mbusB7 64 }

mbusB7Value1D		OBJECT-TYPE
			SYNTAX	INTEGER
			ACCESS	read-only
			STATUS	current
	DESCRIPTION ""
			::= { mbusB7 65 }

mbusB7VIF1E		OBJECT-TYPE
			SYNTAX	INTEGER
			ACCESS	read-only
			STATUS	current
	DESCRIPTION ""
			::= { mbusB7 66 }

mbusB7Value1E		OBJECT-TYPE
			SYNTAX	INTEGER
			ACCESS	read-only
			STATUS	current
	DESCRIPTION ""
			::= { mbusB7 67 }

mbusB7VIF1F		OBJECT-TYPE
			SYNTAX	INTEGER
			ACCESS	read-only
			STATUS	current
	DESCRIPTION ""
			::= { mbusB7 68 }

mbusB7Value1F		OBJECT-TYPE
			SYNTAX	INTEGER
			ACCESS	read-only
			STATUS	current
	DESCRIPTION ""
			::= { mbusB7 69 }

mbusB7VIF20		OBJECT-TYPE
			SYNTAX	INTEGER
			ACCESS	read-only
			STATUS	current
	DESCRIPTION ""
			::= { mbusB7 70 }

mbusB7Value20		OBJECT-TYPE
			SYNTAX	INTEGER
			ACCESS	read-only
			STATUS	current
	DESCRIPTION ""
			::= { mbusB7 71 }

mbusB7VIF21		OBJECT-TYPE
			SYNTAX	INTEGER
			ACCESS	read-only
			STATUS	current
	DESCRIPTION ""
			::= { mbusB7 72 }

mbusB7Value21		OBJECT-TYPE
			SYNTAX	INTEGER
			ACCESS	read-only
			STATUS	current
	DESCRIPTION ""
			::= { mbusB7 73 }

mbusB7VIF22		OBJECT-TYPE
			SYNTAX	INTEGER
			ACCESS	read-only
			STATUS	current
	DESCRIPTION ""
			::= { mbusB7 74 }

mbusB7Value22		OBJECT-TYPE
			SYNTAX	INTEGER
			ACCESS	read-only
			STATUS	current
	DESCRIPTION ""
			::= { mbusB7 75 }

mbusB7VIF23		OBJECT-TYPE
			SYNTAX	INTEGER
			ACCESS	read-only
			STATUS	current
	DESCRIPTION ""
			::= { mbusB7 76 }

mbusB7Value23		OBJECT-TYPE
			SYNTAX	INTEGER
			ACCESS	read-only
			STATUS	current
	DESCRIPTION ""
			::= { mbusB7 77 }

mbusB7VIF24		OBJECT-TYPE
			SYNTAX	INTEGER
			ACCESS	read-only
			STATUS	current
	DESCRIPTION ""
			::= { mbusB7 78 }

mbusB7Value24		OBJECT-TYPE
			SYNTAX	INTEGER
			ACCESS	read-only
			STATUS	current
	DESCRIPTION ""
			::= { mbusB7 79 }

mbusB7VIF25		OBJECT-TYPE
			SYNTAX	INTEGER
			ACCESS	read-only
			STATUS	current
	DESCRIPTION ""
			::= { mbusB7 80 }

mbusB7Value25		OBJECT-TYPE
			SYNTAX	INTEGER
			ACCESS	read-only
			STATUS	current
	DESCRIPTION ""
			::= { mbusB7 81 }

mbusB7VIF26		OBJECT-TYPE
			SYNTAX	INTEGER
			ACCESS	read-only
			STATUS	current
	DESCRIPTION ""
			::= { mbusB7 82 }

mbusB7Value26		OBJECT-TYPE
			SYNTAX	INTEGER
			ACCESS	read-only
			STATUS	current
	DESCRIPTION ""
			::= { mbusB7 83 }

mbusB7VIF27		OBJECT-TYPE
			SYNTAX	INTEGER
			ACCESS	read-only
			STATUS	current
	DESCRIPTION ""
			::= { mbusB7 84 }

mbusB7Value27		OBJECT-TYPE
			SYNTAX	INTEGER
			ACCESS	read-only
			STATUS	current
	DESCRIPTION ""
			::= { mbusB7 85 }

mbusB7VIF28		OBJECT-TYPE
			SYNTAX	INTEGER
			ACCESS	read-only
			STATUS	current
	DESCRIPTION ""
			::= { mbusB7 86 }

mbusB7Value28		OBJECT-TYPE
			SYNTAX	INTEGER
			ACCESS	read-only
			STATUS	current
	DESCRIPTION ""
			::= { mbusB7 87 }

mbusB7VIF29		OBJECT-TYPE
			SYNTAX	INTEGER
			ACCESS	read-only
			STATUS	current
	DESCRIPTION ""
			::= { mbusB7 88 }

mbusB7Value29		OBJECT-TYPE
			SYNTAX	INTEGER
			ACCESS	read-only
			STATUS	current
	DESCRIPTION ""
			::= { mbusB7 89 }

mbusB7VIF2A		OBJECT-TYPE
			SYNTAX	INTEGER
			ACCESS	read-only
			STATUS	current
	DESCRIPTION ""
			::= { mbusB7 90 }

mbusB7Value2A		OBJECT-TYPE
			SYNTAX	INTEGER
			ACCESS	read-only
			STATUS	current
	DESCRIPTION ""
			::= { mbusB7 91 }

mbusB7VIF2B		OBJECT-TYPE
			SYNTAX	INTEGER
			ACCESS	read-only
			STATUS	current
	DESCRIPTION ""
			::= { mbusB7 92 }

mbusB7Value2B		OBJECT-TYPE
			SYNTAX	INTEGER
			ACCESS	read-only
			STATUS	current
	DESCRIPTION ""
			::= { mbusB7 93 }

mbusB7VIF2C		OBJECT-TYPE
			SYNTAX	INTEGER
			ACCESS	read-only
			STATUS	current
	DESCRIPTION ""
			::= { mbusB7 94 }

mbusB7Value2C		OBJECT-TYPE
			SYNTAX	INTEGER
			ACCESS	read-only
			STATUS	current
	DESCRIPTION ""
			::= { mbusB7 95 }

mbusB7VIF2D		OBJECT-TYPE
			SYNTAX	INTEGER
			ACCESS	read-only
			STATUS	current
	DESCRIPTION ""
			::= { mbusB7 96 }

mbusB7Value2D		OBJECT-TYPE
			SYNTAX	INTEGER
			ACCESS	read-only
			STATUS	current
	DESCRIPTION ""
			::= { mbusB7 97 }

mbusB7VIF2E		OBJECT-TYPE
			SYNTAX	INTEGER
			ACCESS	read-only
			STATUS	current
	DESCRIPTION ""
			::= { mbusB7 98 }

mbusB7Value2E		OBJECT-TYPE
			SYNTAX	INTEGER
			ACCESS	read-only
			STATUS	current
	DESCRIPTION ""
			::= { mbusB7 99 }

mbusB7VIF2F		OBJECT-TYPE
			SYNTAX	INTEGER
			ACCESS	read-only
			STATUS	current
	DESCRIPTION ""
			::= { mbusB7 100 }

mbusB7Value2F		OBJECT-TYPE
			SYNTAX	INTEGER
			ACCESS	read-only
			STATUS	current
	DESCRIPTION ""
			::= { mbusB7 101 }

mbusB8			OBJECT IDENTIFIER ::= { mbus 184 }

mbusB8IdNumber		OBJECT-TYPE
			SYNTAX	Gauge
			ACCESS	read-only
			STATUS	current
	DESCRIPTION ""
			::= { mbusB8 1 }

mbusB8Manufacturer	OBJECT-TYPE
			SYNTAX	Gauge
			ACCESS	read-only
			STATUS	current
	DESCRIPTION ""
			::= { mbusB8 2 }

mbusB8Version		OBJECT-TYPE
			SYNTAX	Gauge
			ACCESS	read-only
			STATUS	current
	DESCRIPTION ""
			::= { mbusB8 3 }

mbusB8Medium		OBJECT-TYPE
			SYNTAX	Gauge
			ACCESS	read-only
			STATUS	current
	DESCRIPTION ""
			::= { mbusB8 4 }

mbusB8Status		OBJECT-TYPE
			SYNTAX	Gauge
			ACCESS	read-only
			STATUS	current
	DESCRIPTION ""
			::= { mbusB8 5 }

mbusB8VIF00		OBJECT-TYPE
			SYNTAX	INTEGER
			ACCESS	read-only
			STATUS	current
	DESCRIPTION ""
			::= { mbusB8 6 }

mbusB8Value00		OBJECT-TYPE
			SYNTAX	INTEGER
			ACCESS	read-only
			STATUS	current
	DESCRIPTION ""
			::= { mbusB8 7 }

mbusB8VIF01		OBJECT-TYPE
			SYNTAX	INTEGER
			ACCESS	read-only
			STATUS	current
	DESCRIPTION ""
			::= { mbusB8 8 }

mbusB8Value01		OBJECT-TYPE
			SYNTAX	INTEGER
			ACCESS	read-only
			STATUS	current
	DESCRIPTION ""
			::= { mbusB8 9 }

mbusB8VIF02		OBJECT-TYPE
			SYNTAX	INTEGER
			ACCESS	read-only
			STATUS	current
	DESCRIPTION ""
			::= { mbusB8 10 }

mbusB8Value02		OBJECT-TYPE
			SYNTAX	INTEGER
			ACCESS	read-only
			STATUS	current
	DESCRIPTION ""
			::= { mbusB8 11 }

mbusB8VIF03		OBJECT-TYPE
			SYNTAX	INTEGER
			ACCESS	read-only
			STATUS	current
	DESCRIPTION ""
			::= { mbusB8 12 }

mbusB8Value03		OBJECT-TYPE
			SYNTAX	INTEGER
			ACCESS	read-only
			STATUS	current
	DESCRIPTION ""
			::= { mbusB8 13 }

mbusB8VIF04		OBJECT-TYPE
			SYNTAX	INTEGER
			ACCESS	read-only
			STATUS	current
	DESCRIPTION ""
			::= { mbusB8 14 }

mbusB8Value04		OBJECT-TYPE
			SYNTAX	INTEGER
			ACCESS	read-only
			STATUS	current
	DESCRIPTION ""
			::= { mbusB8 15 }

mbusB8VIF05		OBJECT-TYPE
			SYNTAX	INTEGER
			ACCESS	read-only
			STATUS	current
	DESCRIPTION ""
			::= { mbusB8 16 }

mbusB8Value05		OBJECT-TYPE
			SYNTAX	INTEGER
			ACCESS	read-only
			STATUS	current
	DESCRIPTION ""
			::= { mbusB8 17 }

mbusB8VIF06		OBJECT-TYPE
			SYNTAX	INTEGER
			ACCESS	read-only
			STATUS	current
	DESCRIPTION ""
			::= { mbusB8 18 }

mbusB8Value06		OBJECT-TYPE
			SYNTAX	INTEGER
			ACCESS	read-only
			STATUS	current
	DESCRIPTION ""
			::= { mbusB8 19 }

mbusB8VIF07		OBJECT-TYPE
			SYNTAX	INTEGER
			ACCESS	read-only
			STATUS	current
	DESCRIPTION ""
			::= { mbusB8 20 }

mbusB8Value07		OBJECT-TYPE
			SYNTAX	INTEGER
			ACCESS	read-only
			STATUS	current
	DESCRIPTION ""
			::= { mbusB8 21 }

mbusB8VIF08		OBJECT-TYPE
			SYNTAX	INTEGER
			ACCESS	read-only
			STATUS	current
	DESCRIPTION ""
			::= { mbusB8 22 }

mbusB8Value08		OBJECT-TYPE
			SYNTAX	INTEGER
			ACCESS	read-only
			STATUS	current
	DESCRIPTION ""
			::= { mbusB8 23 }

mbusB8VIF09		OBJECT-TYPE
			SYNTAX	INTEGER
			ACCESS	read-only
			STATUS	current
	DESCRIPTION ""
			::= { mbusB8 24 }

mbusB8Value09		OBJECT-TYPE
			SYNTAX	INTEGER
			ACCESS	read-only
			STATUS	current
	DESCRIPTION ""
			::= { mbusB8 25 }

mbusB8VIF0A		OBJECT-TYPE
			SYNTAX	INTEGER
			ACCESS	read-only
			STATUS	current
	DESCRIPTION ""
			::= { mbusB8 26 }

mbusB8Value0A		OBJECT-TYPE
			SYNTAX	INTEGER
			ACCESS	read-only
			STATUS	current
	DESCRIPTION ""
			::= { mbusB8 27 }

mbusB8VIF0B		OBJECT-TYPE
			SYNTAX	INTEGER
			ACCESS	read-only
			STATUS	current
	DESCRIPTION ""
			::= { mbusB8 28 }

mbusB8Value0B		OBJECT-TYPE
			SYNTAX	INTEGER
			ACCESS	read-only
			STATUS	current
	DESCRIPTION ""
			::= { mbusB8 29 }

mbusB8VIF0C		OBJECT-TYPE
			SYNTAX	INTEGER
			ACCESS	read-only
			STATUS	current
	DESCRIPTION ""
			::= { mbusB8 30 }

mbusB8Value0C		OBJECT-TYPE
			SYNTAX	INTEGER
			ACCESS	read-only
			STATUS	current
	DESCRIPTION ""
			::= { mbusB8 31 }

mbusB8VIF0D		OBJECT-TYPE
			SYNTAX	INTEGER
			ACCESS	read-only
			STATUS	current
	DESCRIPTION ""
			::= { mbusB8 32 }

mbusB8Value0D		OBJECT-TYPE
			SYNTAX	INTEGER
			ACCESS	read-only
			STATUS	current
	DESCRIPTION ""
			::= { mbusB8 33 }

mbusB8VIF0E		OBJECT-TYPE
			SYNTAX	INTEGER
			ACCESS	read-only
			STATUS	current
	DESCRIPTION ""
			::= { mbusB8 34 }

mbusB8Value0E		OBJECT-TYPE
			SYNTAX	INTEGER
			ACCESS	read-only
			STATUS	current
	DESCRIPTION ""
			::= { mbusB8 35 }

mbusB8VIF0F		OBJECT-TYPE
			SYNTAX	INTEGER
			ACCESS	read-only
			STATUS	current
	DESCRIPTION ""
			::= { mbusB8 36 }

mbusB8Value0F		OBJECT-TYPE
			SYNTAX	INTEGER
			ACCESS	read-only
			STATUS	current
	DESCRIPTION ""
			::= { mbusB8 37 }

mbusB8VIF10		OBJECT-TYPE
			SYNTAX	INTEGER
			ACCESS	read-only
			STATUS	current
	DESCRIPTION ""
			::= { mbusB8 38 }

mbusB8Value10		OBJECT-TYPE
			SYNTAX	INTEGER
			ACCESS	read-only
			STATUS	current
	DESCRIPTION ""
			::= { mbusB8 39 }

mbusB8VIF11		OBJECT-TYPE
			SYNTAX	INTEGER
			ACCESS	read-only
			STATUS	current
	DESCRIPTION ""
			::= { mbusB8 40 }

mbusB8Value11		OBJECT-TYPE
			SYNTAX	INTEGER
			ACCESS	read-only
			STATUS	current
	DESCRIPTION ""
			::= { mbusB8 41 }

mbusB8VIF12		OBJECT-TYPE
			SYNTAX	INTEGER
			ACCESS	read-only
			STATUS	current
	DESCRIPTION ""
			::= { mbusB8 42 }

mbusB8Value12		OBJECT-TYPE
			SYNTAX	INTEGER
			ACCESS	read-only
			STATUS	current
	DESCRIPTION ""
			::= { mbusB8 43 }

mbusB8VIF13		OBJECT-TYPE
			SYNTAX	INTEGER
			ACCESS	read-only
			STATUS	current
	DESCRIPTION ""
			::= { mbusB8 44 }

mbusB8Value13		OBJECT-TYPE
			SYNTAX	INTEGER
			ACCESS	read-only
			STATUS	current
	DESCRIPTION ""
			::= { mbusB8 45 }

mbusB8VIF14		OBJECT-TYPE
			SYNTAX	INTEGER
			ACCESS	read-only
			STATUS	current
	DESCRIPTION ""
			::= { mbusB8 46 }

mbusB8Value14		OBJECT-TYPE
			SYNTAX	INTEGER
			ACCESS	read-only
			STATUS	current
	DESCRIPTION ""
			::= { mbusB8 47 }

mbusB8VIF15		OBJECT-TYPE
			SYNTAX	INTEGER
			ACCESS	read-only
			STATUS	current
	DESCRIPTION ""
			::= { mbusB8 48 }

mbusB8Value15		OBJECT-TYPE
			SYNTAX	INTEGER
			ACCESS	read-only
			STATUS	current
	DESCRIPTION ""
			::= { mbusB8 49 }

mbusB8VIF16		OBJECT-TYPE
			SYNTAX	INTEGER
			ACCESS	read-only
			STATUS	current
	DESCRIPTION ""
			::= { mbusB8 50 }

mbusB8Value16		OBJECT-TYPE
			SYNTAX	INTEGER
			ACCESS	read-only
			STATUS	current
	DESCRIPTION ""
			::= { mbusB8 51 }

mbusB8VIF17		OBJECT-TYPE
			SYNTAX	INTEGER
			ACCESS	read-only
			STATUS	current
	DESCRIPTION ""
			::= { mbusB8 52 }

mbusB8Value17		OBJECT-TYPE
			SYNTAX	INTEGER
			ACCESS	read-only
			STATUS	current
	DESCRIPTION ""
			::= { mbusB8 53 }

mbusB8VIF18		OBJECT-TYPE
			SYNTAX	INTEGER
			ACCESS	read-only
			STATUS	current
	DESCRIPTION ""
			::= { mbusB8 54 }

mbusB8Value18		OBJECT-TYPE
			SYNTAX	INTEGER
			ACCESS	read-only
			STATUS	current
	DESCRIPTION ""
			::= { mbusB8 55 }

mbusB8VIF19		OBJECT-TYPE
			SYNTAX	INTEGER
			ACCESS	read-only
			STATUS	current
	DESCRIPTION ""
			::= { mbusB8 56 }

mbusB8Value19		OBJECT-TYPE
			SYNTAX	INTEGER
			ACCESS	read-only
			STATUS	current
	DESCRIPTION ""
			::= { mbusB8 57 }

mbusB8VIF1A		OBJECT-TYPE
			SYNTAX	INTEGER
			ACCESS	read-only
			STATUS	current
	DESCRIPTION ""
			::= { mbusB8 58 }

mbusB8Value1A		OBJECT-TYPE
			SYNTAX	INTEGER
			ACCESS	read-only
			STATUS	current
	DESCRIPTION ""
			::= { mbusB8 59 }

mbusB8VIF1B		OBJECT-TYPE
			SYNTAX	INTEGER
			ACCESS	read-only
			STATUS	current
	DESCRIPTION ""
			::= { mbusB8 60 }

mbusB8Value1B		OBJECT-TYPE
			SYNTAX	INTEGER
			ACCESS	read-only
			STATUS	current
	DESCRIPTION ""
			::= { mbusB8 61 }

mbusB8VIF1C		OBJECT-TYPE
			SYNTAX	INTEGER
			ACCESS	read-only
			STATUS	current
	DESCRIPTION ""
			::= { mbusB8 62 }

mbusB8Value1C		OBJECT-TYPE
			SYNTAX	INTEGER
			ACCESS	read-only
			STATUS	current
	DESCRIPTION ""
			::= { mbusB8 63 }

mbusB8VIF1D		OBJECT-TYPE
			SYNTAX	INTEGER
			ACCESS	read-only
			STATUS	current
	DESCRIPTION ""
			::= { mbusB8 64 }

mbusB8Value1D		OBJECT-TYPE
			SYNTAX	INTEGER
			ACCESS	read-only
			STATUS	current
	DESCRIPTION ""
			::= { mbusB8 65 }

mbusB8VIF1E		OBJECT-TYPE
			SYNTAX	INTEGER
			ACCESS	read-only
			STATUS	current
	DESCRIPTION ""
			::= { mbusB8 66 }

mbusB8Value1E		OBJECT-TYPE
			SYNTAX	INTEGER
			ACCESS	read-only
			STATUS	current
	DESCRIPTION ""
			::= { mbusB8 67 }

mbusB8VIF1F		OBJECT-TYPE
			SYNTAX	INTEGER
			ACCESS	read-only
			STATUS	current
	DESCRIPTION ""
			::= { mbusB8 68 }

mbusB8Value1F		OBJECT-TYPE
			SYNTAX	INTEGER
			ACCESS	read-only
			STATUS	current
	DESCRIPTION ""
			::= { mbusB8 69 }

mbusB8VIF20		OBJECT-TYPE
			SYNTAX	INTEGER
			ACCESS	read-only
			STATUS	current
	DESCRIPTION ""
			::= { mbusB8 70 }

mbusB8Value20		OBJECT-TYPE
			SYNTAX	INTEGER
			ACCESS	read-only
			STATUS	current
	DESCRIPTION ""
			::= { mbusB8 71 }

mbusB8VIF21		OBJECT-TYPE
			SYNTAX	INTEGER
			ACCESS	read-only
			STATUS	current
	DESCRIPTION ""
			::= { mbusB8 72 }

mbusB8Value21		OBJECT-TYPE
			SYNTAX	INTEGER
			ACCESS	read-only
			STATUS	current
	DESCRIPTION ""
			::= { mbusB8 73 }

mbusB8VIF22		OBJECT-TYPE
			SYNTAX	INTEGER
			ACCESS	read-only
			STATUS	current
	DESCRIPTION ""
			::= { mbusB8 74 }

mbusB8Value22		OBJECT-TYPE
			SYNTAX	INTEGER
			ACCESS	read-only
			STATUS	current
	DESCRIPTION ""
			::= { mbusB8 75 }

mbusB8VIF23		OBJECT-TYPE
			SYNTAX	INTEGER
			ACCESS	read-only
			STATUS	current
	DESCRIPTION ""
			::= { mbusB8 76 }

mbusB8Value23		OBJECT-TYPE
			SYNTAX	INTEGER
			ACCESS	read-only
			STATUS	current
	DESCRIPTION ""
			::= { mbusB8 77 }

mbusB8VIF24		OBJECT-TYPE
			SYNTAX	INTEGER
			ACCESS	read-only
			STATUS	current
	DESCRIPTION ""
			::= { mbusB8 78 }

mbusB8Value24		OBJECT-TYPE
			SYNTAX	INTEGER
			ACCESS	read-only
			STATUS	current
	DESCRIPTION ""
			::= { mbusB8 79 }

mbusB8VIF25		OBJECT-TYPE
			SYNTAX	INTEGER
			ACCESS	read-only
			STATUS	current
	DESCRIPTION ""
			::= { mbusB8 80 }

mbusB8Value25		OBJECT-TYPE
			SYNTAX	INTEGER
			ACCESS	read-only
			STATUS	current
	DESCRIPTION ""
			::= { mbusB8 81 }

mbusB8VIF26		OBJECT-TYPE
			SYNTAX	INTEGER
			ACCESS	read-only
			STATUS	current
	DESCRIPTION ""
			::= { mbusB8 82 }

mbusB8Value26		OBJECT-TYPE
			SYNTAX	INTEGER
			ACCESS	read-only
			STATUS	current
	DESCRIPTION ""
			::= { mbusB8 83 }

mbusB8VIF27		OBJECT-TYPE
			SYNTAX	INTEGER
			ACCESS	read-only
			STATUS	current
	DESCRIPTION ""
			::= { mbusB8 84 }

mbusB8Value27		OBJECT-TYPE
			SYNTAX	INTEGER
			ACCESS	read-only
			STATUS	current
	DESCRIPTION ""
			::= { mbusB8 85 }

mbusB8VIF28		OBJECT-TYPE
			SYNTAX	INTEGER
			ACCESS	read-only
			STATUS	current
	DESCRIPTION ""
			::= { mbusB8 86 }

mbusB8Value28		OBJECT-TYPE
			SYNTAX	INTEGER
			ACCESS	read-only
			STATUS	current
	DESCRIPTION ""
			::= { mbusB8 87 }

mbusB8VIF29		OBJECT-TYPE
			SYNTAX	INTEGER
			ACCESS	read-only
			STATUS	current
	DESCRIPTION ""
			::= { mbusB8 88 }

mbusB8Value29		OBJECT-TYPE
			SYNTAX	INTEGER
			ACCESS	read-only
			STATUS	current
	DESCRIPTION ""
			::= { mbusB8 89 }

mbusB8VIF2A		OBJECT-TYPE
			SYNTAX	INTEGER
			ACCESS	read-only
			STATUS	current
	DESCRIPTION ""
			::= { mbusB8 90 }

mbusB8Value2A		OBJECT-TYPE
			SYNTAX	INTEGER
			ACCESS	read-only
			STATUS	current
	DESCRIPTION ""
			::= { mbusB8 91 }

mbusB8VIF2B		OBJECT-TYPE
			SYNTAX	INTEGER
			ACCESS	read-only
			STATUS	current
	DESCRIPTION ""
			::= { mbusB8 92 }

mbusB8Value2B		OBJECT-TYPE
			SYNTAX	INTEGER
			ACCESS	read-only
			STATUS	current
	DESCRIPTION ""
			::= { mbusB8 93 }

mbusB8VIF2C		OBJECT-TYPE
			SYNTAX	INTEGER
			ACCESS	read-only
			STATUS	current
	DESCRIPTION ""
			::= { mbusB8 94 }

mbusB8Value2C		OBJECT-TYPE
			SYNTAX	INTEGER
			ACCESS	read-only
			STATUS	current
	DESCRIPTION ""
			::= { mbusB8 95 }

mbusB8VIF2D		OBJECT-TYPE
			SYNTAX	INTEGER
			ACCESS	read-only
			STATUS	current
	DESCRIPTION ""
			::= { mbusB8 96 }

mbusB8Value2D		OBJECT-TYPE
			SYNTAX	INTEGER
			ACCESS	read-only
			STATUS	current
	DESCRIPTION ""
			::= { mbusB8 97 }

mbusB8VIF2E		OBJECT-TYPE
			SYNTAX	INTEGER
			ACCESS	read-only
			STATUS	current
	DESCRIPTION ""
			::= { mbusB8 98 }

mbusB8Value2E		OBJECT-TYPE
			SYNTAX	INTEGER
			ACCESS	read-only
			STATUS	current
	DESCRIPTION ""
			::= { mbusB8 99 }

mbusB8VIF2F		OBJECT-TYPE
			SYNTAX	INTEGER
			ACCESS	read-only
			STATUS	current
	DESCRIPTION ""
			::= { mbusB8 100 }

mbusB8Value2F		OBJECT-TYPE
			SYNTAX	INTEGER
			ACCESS	read-only
			STATUS	current
	DESCRIPTION ""
			::= { mbusB8 101 }

mbusB9			OBJECT IDENTIFIER ::= { mbus 185 }

mbusB9IdNumber		OBJECT-TYPE
			SYNTAX	Gauge
			ACCESS	read-only
			STATUS	current
	DESCRIPTION ""
			::= { mbusB9 1 }

mbusB9Manufacturer	OBJECT-TYPE
			SYNTAX	Gauge
			ACCESS	read-only
			STATUS	current
	DESCRIPTION ""
			::= { mbusB9 2 }

mbusB9Version		OBJECT-TYPE
			SYNTAX	Gauge
			ACCESS	read-only
			STATUS	current
	DESCRIPTION ""
			::= { mbusB9 3 }

mbusB9Medium		OBJECT-TYPE
			SYNTAX	Gauge
			ACCESS	read-only
			STATUS	current
	DESCRIPTION ""
			::= { mbusB9 4 }

mbusB9Status		OBJECT-TYPE
			SYNTAX	Gauge
			ACCESS	read-only
			STATUS	current
	DESCRIPTION ""
			::= { mbusB9 5 }

mbusB9VIF00		OBJECT-TYPE
			SYNTAX	INTEGER
			ACCESS	read-only
			STATUS	current
	DESCRIPTION ""
			::= { mbusB9 6 }

mbusB9Value00		OBJECT-TYPE
			SYNTAX	INTEGER
			ACCESS	read-only
			STATUS	current
	DESCRIPTION ""
			::= { mbusB9 7 }

mbusB9VIF01		OBJECT-TYPE
			SYNTAX	INTEGER
			ACCESS	read-only
			STATUS	current
	DESCRIPTION ""
			::= { mbusB9 8 }

mbusB9Value01		OBJECT-TYPE
			SYNTAX	INTEGER
			ACCESS	read-only
			STATUS	current
	DESCRIPTION ""
			::= { mbusB9 9 }

mbusB9VIF02		OBJECT-TYPE
			SYNTAX	INTEGER
			ACCESS	read-only
			STATUS	current
	DESCRIPTION ""
			::= { mbusB9 10 }

mbusB9Value02		OBJECT-TYPE
			SYNTAX	INTEGER
			ACCESS	read-only
			STATUS	current
	DESCRIPTION ""
			::= { mbusB9 11 }

mbusB9VIF03		OBJECT-TYPE
			SYNTAX	INTEGER
			ACCESS	read-only
			STATUS	current
	DESCRIPTION ""
			::= { mbusB9 12 }

mbusB9Value03		OBJECT-TYPE
			SYNTAX	INTEGER
			ACCESS	read-only
			STATUS	current
	DESCRIPTION ""
			::= { mbusB9 13 }

mbusB9VIF04		OBJECT-TYPE
			SYNTAX	INTEGER
			ACCESS	read-only
			STATUS	current
	DESCRIPTION ""
			::= { mbusB9 14 }

mbusB9Value04		OBJECT-TYPE
			SYNTAX	INTEGER
			ACCESS	read-only
			STATUS	current
	DESCRIPTION ""
			::= { mbusB9 15 }

mbusB9VIF05		OBJECT-TYPE
			SYNTAX	INTEGER
			ACCESS	read-only
			STATUS	current
	DESCRIPTION ""
			::= { mbusB9 16 }

mbusB9Value05		OBJECT-TYPE
			SYNTAX	INTEGER
			ACCESS	read-only
			STATUS	current
	DESCRIPTION ""
			::= { mbusB9 17 }

mbusB9VIF06		OBJECT-TYPE
			SYNTAX	INTEGER
			ACCESS	read-only
			STATUS	current
	DESCRIPTION ""
			::= { mbusB9 18 }

mbusB9Value06		OBJECT-TYPE
			SYNTAX	INTEGER
			ACCESS	read-only
			STATUS	current
	DESCRIPTION ""
			::= { mbusB9 19 }

mbusB9VIF07		OBJECT-TYPE
			SYNTAX	INTEGER
			ACCESS	read-only
			STATUS	current
	DESCRIPTION ""
			::= { mbusB9 20 }

mbusB9Value07		OBJECT-TYPE
			SYNTAX	INTEGER
			ACCESS	read-only
			STATUS	current
	DESCRIPTION ""
			::= { mbusB9 21 }

mbusB9VIF08		OBJECT-TYPE
			SYNTAX	INTEGER
			ACCESS	read-only
			STATUS	current
	DESCRIPTION ""
			::= { mbusB9 22 }

mbusB9Value08		OBJECT-TYPE
			SYNTAX	INTEGER
			ACCESS	read-only
			STATUS	current
	DESCRIPTION ""
			::= { mbusB9 23 }

mbusB9VIF09		OBJECT-TYPE
			SYNTAX	INTEGER
			ACCESS	read-only
			STATUS	current
	DESCRIPTION ""
			::= { mbusB9 24 }

mbusB9Value09		OBJECT-TYPE
			SYNTAX	INTEGER
			ACCESS	read-only
			STATUS	current
	DESCRIPTION ""
			::= { mbusB9 25 }

mbusB9VIF0A		OBJECT-TYPE
			SYNTAX	INTEGER
			ACCESS	read-only
			STATUS	current
	DESCRIPTION ""
			::= { mbusB9 26 }

mbusB9Value0A		OBJECT-TYPE
			SYNTAX	INTEGER
			ACCESS	read-only
			STATUS	current
	DESCRIPTION ""
			::= { mbusB9 27 }

mbusB9VIF0B		OBJECT-TYPE
			SYNTAX	INTEGER
			ACCESS	read-only
			STATUS	current
	DESCRIPTION ""
			::= { mbusB9 28 }

mbusB9Value0B		OBJECT-TYPE
			SYNTAX	INTEGER
			ACCESS	read-only
			STATUS	current
	DESCRIPTION ""
			::= { mbusB9 29 }

mbusB9VIF0C		OBJECT-TYPE
			SYNTAX	INTEGER
			ACCESS	read-only
			STATUS	current
	DESCRIPTION ""
			::= { mbusB9 30 }

mbusB9Value0C		OBJECT-TYPE
			SYNTAX	INTEGER
			ACCESS	read-only
			STATUS	current
	DESCRIPTION ""
			::= { mbusB9 31 }

mbusB9VIF0D		OBJECT-TYPE
			SYNTAX	INTEGER
			ACCESS	read-only
			STATUS	current
	DESCRIPTION ""
			::= { mbusB9 32 }

mbusB9Value0D		OBJECT-TYPE
			SYNTAX	INTEGER
			ACCESS	read-only
			STATUS	current
	DESCRIPTION ""
			::= { mbusB9 33 }

mbusB9VIF0E		OBJECT-TYPE
			SYNTAX	INTEGER
			ACCESS	read-only
			STATUS	current
	DESCRIPTION ""
			::= { mbusB9 34 }

mbusB9Value0E		OBJECT-TYPE
			SYNTAX	INTEGER
			ACCESS	read-only
			STATUS	current
	DESCRIPTION ""
			::= { mbusB9 35 }

mbusB9VIF0F		OBJECT-TYPE
			SYNTAX	INTEGER
			ACCESS	read-only
			STATUS	current
	DESCRIPTION ""
			::= { mbusB9 36 }

mbusB9Value0F		OBJECT-TYPE
			SYNTAX	INTEGER
			ACCESS	read-only
			STATUS	current
	DESCRIPTION ""
			::= { mbusB9 37 }

mbusB9VIF10		OBJECT-TYPE
			SYNTAX	INTEGER
			ACCESS	read-only
			STATUS	current
	DESCRIPTION ""
			::= { mbusB9 38 }

mbusB9Value10		OBJECT-TYPE
			SYNTAX	INTEGER
			ACCESS	read-only
			STATUS	current
	DESCRIPTION ""
			::= { mbusB9 39 }

mbusB9VIF11		OBJECT-TYPE
			SYNTAX	INTEGER
			ACCESS	read-only
			STATUS	current
	DESCRIPTION ""
			::= { mbusB9 40 }

mbusB9Value11		OBJECT-TYPE
			SYNTAX	INTEGER
			ACCESS	read-only
			STATUS	current
	DESCRIPTION ""
			::= { mbusB9 41 }

mbusB9VIF12		OBJECT-TYPE
			SYNTAX	INTEGER
			ACCESS	read-only
			STATUS	current
	DESCRIPTION ""
			::= { mbusB9 42 }

mbusB9Value12		OBJECT-TYPE
			SYNTAX	INTEGER
			ACCESS	read-only
			STATUS	current
	DESCRIPTION ""
			::= { mbusB9 43 }

mbusB9VIF13		OBJECT-TYPE
			SYNTAX	INTEGER
			ACCESS	read-only
			STATUS	current
	DESCRIPTION ""
			::= { mbusB9 44 }

mbusB9Value13		OBJECT-TYPE
			SYNTAX	INTEGER
			ACCESS	read-only
			STATUS	current
	DESCRIPTION ""
			::= { mbusB9 45 }

mbusB9VIF14		OBJECT-TYPE
			SYNTAX	INTEGER
			ACCESS	read-only
			STATUS	current
	DESCRIPTION ""
			::= { mbusB9 46 }

mbusB9Value14		OBJECT-TYPE
			SYNTAX	INTEGER
			ACCESS	read-only
			STATUS	current
	DESCRIPTION ""
			::= { mbusB9 47 }

mbusB9VIF15		OBJECT-TYPE
			SYNTAX	INTEGER
			ACCESS	read-only
			STATUS	current
	DESCRIPTION ""
			::= { mbusB9 48 }

mbusB9Value15		OBJECT-TYPE
			SYNTAX	INTEGER
			ACCESS	read-only
			STATUS	current
	DESCRIPTION ""
			::= { mbusB9 49 }

mbusB9VIF16		OBJECT-TYPE
			SYNTAX	INTEGER
			ACCESS	read-only
			STATUS	current
	DESCRIPTION ""
			::= { mbusB9 50 }

mbusB9Value16		OBJECT-TYPE
			SYNTAX	INTEGER
			ACCESS	read-only
			STATUS	current
	DESCRIPTION ""
			::= { mbusB9 51 }

mbusB9VIF17		OBJECT-TYPE
			SYNTAX	INTEGER
			ACCESS	read-only
			STATUS	current
	DESCRIPTION ""
			::= { mbusB9 52 }

mbusB9Value17		OBJECT-TYPE
			SYNTAX	INTEGER
			ACCESS	read-only
			STATUS	current
	DESCRIPTION ""
			::= { mbusB9 53 }

mbusB9VIF18		OBJECT-TYPE
			SYNTAX	INTEGER
			ACCESS	read-only
			STATUS	current
	DESCRIPTION ""
			::= { mbusB9 54 }

mbusB9Value18		OBJECT-TYPE
			SYNTAX	INTEGER
			ACCESS	read-only
			STATUS	current
	DESCRIPTION ""
			::= { mbusB9 55 }

mbusB9VIF19		OBJECT-TYPE
			SYNTAX	INTEGER
			ACCESS	read-only
			STATUS	current
	DESCRIPTION ""
			::= { mbusB9 56 }

mbusB9Value19		OBJECT-TYPE
			SYNTAX	INTEGER
			ACCESS	read-only
			STATUS	current
	DESCRIPTION ""
			::= { mbusB9 57 }

mbusB9VIF1A		OBJECT-TYPE
			SYNTAX	INTEGER
			ACCESS	read-only
			STATUS	current
	DESCRIPTION ""
			::= { mbusB9 58 }

mbusB9Value1A		OBJECT-TYPE
			SYNTAX	INTEGER
			ACCESS	read-only
			STATUS	current
	DESCRIPTION ""
			::= { mbusB9 59 }

mbusB9VIF1B		OBJECT-TYPE
			SYNTAX	INTEGER
			ACCESS	read-only
			STATUS	current
	DESCRIPTION ""
			::= { mbusB9 60 }

mbusB9Value1B		OBJECT-TYPE
			SYNTAX	INTEGER
			ACCESS	read-only
			STATUS	current
	DESCRIPTION ""
			::= { mbusB9 61 }

mbusB9VIF1C		OBJECT-TYPE
			SYNTAX	INTEGER
			ACCESS	read-only
			STATUS	current
	DESCRIPTION ""
			::= { mbusB9 62 }

mbusB9Value1C		OBJECT-TYPE
			SYNTAX	INTEGER
			ACCESS	read-only
			STATUS	current
	DESCRIPTION ""
			::= { mbusB9 63 }

mbusB9VIF1D		OBJECT-TYPE
			SYNTAX	INTEGER
			ACCESS	read-only
			STATUS	current
	DESCRIPTION ""
			::= { mbusB9 64 }

mbusB9Value1D		OBJECT-TYPE
			SYNTAX	INTEGER
			ACCESS	read-only
			STATUS	current
	DESCRIPTION ""
			::= { mbusB9 65 }

mbusB9VIF1E		OBJECT-TYPE
			SYNTAX	INTEGER
			ACCESS	read-only
			STATUS	current
	DESCRIPTION ""
			::= { mbusB9 66 }

mbusB9Value1E		OBJECT-TYPE
			SYNTAX	INTEGER
			ACCESS	read-only
			STATUS	current
	DESCRIPTION ""
			::= { mbusB9 67 }

mbusB9VIF1F		OBJECT-TYPE
			SYNTAX	INTEGER
			ACCESS	read-only
			STATUS	current
	DESCRIPTION ""
			::= { mbusB9 68 }

mbusB9Value1F		OBJECT-TYPE
			SYNTAX	INTEGER
			ACCESS	read-only
			STATUS	current
	DESCRIPTION ""
			::= { mbusB9 69 }

mbusB9VIF20		OBJECT-TYPE
			SYNTAX	INTEGER
			ACCESS	read-only
			STATUS	current
	DESCRIPTION ""
			::= { mbusB9 70 }

mbusB9Value20		OBJECT-TYPE
			SYNTAX	INTEGER
			ACCESS	read-only
			STATUS	current
	DESCRIPTION ""
			::= { mbusB9 71 }

mbusB9VIF21		OBJECT-TYPE
			SYNTAX	INTEGER
			ACCESS	read-only
			STATUS	current
	DESCRIPTION ""
			::= { mbusB9 72 }

mbusB9Value21		OBJECT-TYPE
			SYNTAX	INTEGER
			ACCESS	read-only
			STATUS	current
	DESCRIPTION ""
			::= { mbusB9 73 }

mbusB9VIF22		OBJECT-TYPE
			SYNTAX	INTEGER
			ACCESS	read-only
			STATUS	current
	DESCRIPTION ""
			::= { mbusB9 74 }

mbusB9Value22		OBJECT-TYPE
			SYNTAX	INTEGER
			ACCESS	read-only
			STATUS	current
	DESCRIPTION ""
			::= { mbusB9 75 }

mbusB9VIF23		OBJECT-TYPE
			SYNTAX	INTEGER
			ACCESS	read-only
			STATUS	current
	DESCRIPTION ""
			::= { mbusB9 76 }

mbusB9Value23		OBJECT-TYPE
			SYNTAX	INTEGER
			ACCESS	read-only
			STATUS	current
	DESCRIPTION ""
			::= { mbusB9 77 }

mbusB9VIF24		OBJECT-TYPE
			SYNTAX	INTEGER
			ACCESS	read-only
			STATUS	current
	DESCRIPTION ""
			::= { mbusB9 78 }

mbusB9Value24		OBJECT-TYPE
			SYNTAX	INTEGER
			ACCESS	read-only
			STATUS	current
	DESCRIPTION ""
			::= { mbusB9 79 }

mbusB9VIF25		OBJECT-TYPE
			SYNTAX	INTEGER
			ACCESS	read-only
			STATUS	current
	DESCRIPTION ""
			::= { mbusB9 80 }

mbusB9Value25		OBJECT-TYPE
			SYNTAX	INTEGER
			ACCESS	read-only
			STATUS	current
	DESCRIPTION ""
			::= { mbusB9 81 }

mbusB9VIF26		OBJECT-TYPE
			SYNTAX	INTEGER
			ACCESS	read-only
			STATUS	current
	DESCRIPTION ""
			::= { mbusB9 82 }

mbusB9Value26		OBJECT-TYPE
			SYNTAX	INTEGER
			ACCESS	read-only
			STATUS	current
	DESCRIPTION ""
			::= { mbusB9 83 }

mbusB9VIF27		OBJECT-TYPE
			SYNTAX	INTEGER
			ACCESS	read-only
			STATUS	current
	DESCRIPTION ""
			::= { mbusB9 84 }

mbusB9Value27		OBJECT-TYPE
			SYNTAX	INTEGER
			ACCESS	read-only
			STATUS	current
	DESCRIPTION ""
			::= { mbusB9 85 }

mbusB9VIF28		OBJECT-TYPE
			SYNTAX	INTEGER
			ACCESS	read-only
			STATUS	current
	DESCRIPTION ""
			::= { mbusB9 86 }

mbusB9Value28		OBJECT-TYPE
			SYNTAX	INTEGER
			ACCESS	read-only
			STATUS	current
	DESCRIPTION ""
			::= { mbusB9 87 }

mbusB9VIF29		OBJECT-TYPE
			SYNTAX	INTEGER
			ACCESS	read-only
			STATUS	current
	DESCRIPTION ""
			::= { mbusB9 88 }

mbusB9Value29		OBJECT-TYPE
			SYNTAX	INTEGER
			ACCESS	read-only
			STATUS	current
	DESCRIPTION ""
			::= { mbusB9 89 }

mbusB9VIF2A		OBJECT-TYPE
			SYNTAX	INTEGER
			ACCESS	read-only
			STATUS	current
	DESCRIPTION ""
			::= { mbusB9 90 }

mbusB9Value2A		OBJECT-TYPE
			SYNTAX	INTEGER
			ACCESS	read-only
			STATUS	current
	DESCRIPTION ""
			::= { mbusB9 91 }

mbusB9VIF2B		OBJECT-TYPE
			SYNTAX	INTEGER
			ACCESS	read-only
			STATUS	current
	DESCRIPTION ""
			::= { mbusB9 92 }

mbusB9Value2B		OBJECT-TYPE
			SYNTAX	INTEGER
			ACCESS	read-only
			STATUS	current
	DESCRIPTION ""
			::= { mbusB9 93 }

mbusB9VIF2C		OBJECT-TYPE
			SYNTAX	INTEGER
			ACCESS	read-only
			STATUS	current
	DESCRIPTION ""
			::= { mbusB9 94 }

mbusB9Value2C		OBJECT-TYPE
			SYNTAX	INTEGER
			ACCESS	read-only
			STATUS	current
	DESCRIPTION ""
			::= { mbusB9 95 }

mbusB9VIF2D		OBJECT-TYPE
			SYNTAX	INTEGER
			ACCESS	read-only
			STATUS	current
	DESCRIPTION ""
			::= { mbusB9 96 }

mbusB9Value2D		OBJECT-TYPE
			SYNTAX	INTEGER
			ACCESS	read-only
			STATUS	current
	DESCRIPTION ""
			::= { mbusB9 97 }

mbusB9VIF2E		OBJECT-TYPE
			SYNTAX	INTEGER
			ACCESS	read-only
			STATUS	current
	DESCRIPTION ""
			::= { mbusB9 98 }

mbusB9Value2E		OBJECT-TYPE
			SYNTAX	INTEGER
			ACCESS	read-only
			STATUS	current
	DESCRIPTION ""
			::= { mbusB9 99 }

mbusB9VIF2F		OBJECT-TYPE
			SYNTAX	INTEGER
			ACCESS	read-only
			STATUS	current
	DESCRIPTION ""
			::= { mbusB9 100 }

mbusB9Value2F		OBJECT-TYPE
			SYNTAX	INTEGER
			ACCESS	read-only
			STATUS	current
	DESCRIPTION ""
			::= { mbusB9 101 }

mbusBA			OBJECT IDENTIFIER ::= { mbus 186 }

mbusBAIdNumber		OBJECT-TYPE
			SYNTAX	Gauge
			ACCESS	read-only
			STATUS	current
	DESCRIPTION ""
			::= { mbusBA 1 }

mbusBAManufacturer	OBJECT-TYPE
			SYNTAX	Gauge
			ACCESS	read-only
			STATUS	current
	DESCRIPTION ""
			::= { mbusBA 2 }

mbusBAVersion		OBJECT-TYPE
			SYNTAX	Gauge
			ACCESS	read-only
			STATUS	current
	DESCRIPTION ""
			::= { mbusBA 3 }

mbusBAMedium		OBJECT-TYPE
			SYNTAX	Gauge
			ACCESS	read-only
			STATUS	current
	DESCRIPTION ""
			::= { mbusBA 4 }

mbusBAStatus		OBJECT-TYPE
			SYNTAX	Gauge
			ACCESS	read-only
			STATUS	current
	DESCRIPTION ""
			::= { mbusBA 5 }

mbusBAVIF00		OBJECT-TYPE
			SYNTAX	INTEGER
			ACCESS	read-only
			STATUS	current
	DESCRIPTION ""
			::= { mbusBA 6 }

mbusBAValue00		OBJECT-TYPE
			SYNTAX	INTEGER
			ACCESS	read-only
			STATUS	current
	DESCRIPTION ""
			::= { mbusBA 7 }

mbusBAVIF01		OBJECT-TYPE
			SYNTAX	INTEGER
			ACCESS	read-only
			STATUS	current
	DESCRIPTION ""
			::= { mbusBA 8 }

mbusBAValue01		OBJECT-TYPE
			SYNTAX	INTEGER
			ACCESS	read-only
			STATUS	current
	DESCRIPTION ""
			::= { mbusBA 9 }

mbusBAVIF02		OBJECT-TYPE
			SYNTAX	INTEGER
			ACCESS	read-only
			STATUS	current
	DESCRIPTION ""
			::= { mbusBA 10 }

mbusBAValue02		OBJECT-TYPE
			SYNTAX	INTEGER
			ACCESS	read-only
			STATUS	current
	DESCRIPTION ""
			::= { mbusBA 11 }

mbusBAVIF03		OBJECT-TYPE
			SYNTAX	INTEGER
			ACCESS	read-only
			STATUS	current
	DESCRIPTION ""
			::= { mbusBA 12 }

mbusBAValue03		OBJECT-TYPE
			SYNTAX	INTEGER
			ACCESS	read-only
			STATUS	current
	DESCRIPTION ""
			::= { mbusBA 13 }

mbusBAVIF04		OBJECT-TYPE
			SYNTAX	INTEGER
			ACCESS	read-only
			STATUS	current
	DESCRIPTION ""
			::= { mbusBA 14 }

mbusBAValue04		OBJECT-TYPE
			SYNTAX	INTEGER
			ACCESS	read-only
			STATUS	current
	DESCRIPTION ""
			::= { mbusBA 15 }

mbusBAVIF05		OBJECT-TYPE
			SYNTAX	INTEGER
			ACCESS	read-only
			STATUS	current
	DESCRIPTION ""
			::= { mbusBA 16 }

mbusBAValue05		OBJECT-TYPE
			SYNTAX	INTEGER
			ACCESS	read-only
			STATUS	current
	DESCRIPTION ""
			::= { mbusBA 17 }

mbusBAVIF06		OBJECT-TYPE
			SYNTAX	INTEGER
			ACCESS	read-only
			STATUS	current
	DESCRIPTION ""
			::= { mbusBA 18 }

mbusBAValue06		OBJECT-TYPE
			SYNTAX	INTEGER
			ACCESS	read-only
			STATUS	current
	DESCRIPTION ""
			::= { mbusBA 19 }

mbusBAVIF07		OBJECT-TYPE
			SYNTAX	INTEGER
			ACCESS	read-only
			STATUS	current
	DESCRIPTION ""
			::= { mbusBA 20 }

mbusBAValue07		OBJECT-TYPE
			SYNTAX	INTEGER
			ACCESS	read-only
			STATUS	current
	DESCRIPTION ""
			::= { mbusBA 21 }

mbusBAVIF08		OBJECT-TYPE
			SYNTAX	INTEGER
			ACCESS	read-only
			STATUS	current
	DESCRIPTION ""
			::= { mbusBA 22 }

mbusBAValue08		OBJECT-TYPE
			SYNTAX	INTEGER
			ACCESS	read-only
			STATUS	current
	DESCRIPTION ""
			::= { mbusBA 23 }

mbusBAVIF09		OBJECT-TYPE
			SYNTAX	INTEGER
			ACCESS	read-only
			STATUS	current
	DESCRIPTION ""
			::= { mbusBA 24 }

mbusBAValue09		OBJECT-TYPE
			SYNTAX	INTEGER
			ACCESS	read-only
			STATUS	current
	DESCRIPTION ""
			::= { mbusBA 25 }

mbusBAVIF0A		OBJECT-TYPE
			SYNTAX	INTEGER
			ACCESS	read-only
			STATUS	current
	DESCRIPTION ""
			::= { mbusBA 26 }

mbusBAValue0A		OBJECT-TYPE
			SYNTAX	INTEGER
			ACCESS	read-only
			STATUS	current
	DESCRIPTION ""
			::= { mbusBA 27 }

mbusBAVIF0B		OBJECT-TYPE
			SYNTAX	INTEGER
			ACCESS	read-only
			STATUS	current
	DESCRIPTION ""
			::= { mbusBA 28 }

mbusBAValue0B		OBJECT-TYPE
			SYNTAX	INTEGER
			ACCESS	read-only
			STATUS	current
	DESCRIPTION ""
			::= { mbusBA 29 }

mbusBAVIF0C		OBJECT-TYPE
			SYNTAX	INTEGER
			ACCESS	read-only
			STATUS	current
	DESCRIPTION ""
			::= { mbusBA 30 }

mbusBAValue0C		OBJECT-TYPE
			SYNTAX	INTEGER
			ACCESS	read-only
			STATUS	current
	DESCRIPTION ""
			::= { mbusBA 31 }

mbusBAVIF0D		OBJECT-TYPE
			SYNTAX	INTEGER
			ACCESS	read-only
			STATUS	current
	DESCRIPTION ""
			::= { mbusBA 32 }

mbusBAValue0D		OBJECT-TYPE
			SYNTAX	INTEGER
			ACCESS	read-only
			STATUS	current
	DESCRIPTION ""
			::= { mbusBA 33 }

mbusBAVIF0E		OBJECT-TYPE
			SYNTAX	INTEGER
			ACCESS	read-only
			STATUS	current
	DESCRIPTION ""
			::= { mbusBA 34 }

mbusBAValue0E		OBJECT-TYPE
			SYNTAX	INTEGER
			ACCESS	read-only
			STATUS	current
	DESCRIPTION ""
			::= { mbusBA 35 }

mbusBAVIF0F		OBJECT-TYPE
			SYNTAX	INTEGER
			ACCESS	read-only
			STATUS	current
	DESCRIPTION ""
			::= { mbusBA 36 }

mbusBAValue0F		OBJECT-TYPE
			SYNTAX	INTEGER
			ACCESS	read-only
			STATUS	current
	DESCRIPTION ""
			::= { mbusBA 37 }

mbusBAVIF10		OBJECT-TYPE
			SYNTAX	INTEGER
			ACCESS	read-only
			STATUS	current
	DESCRIPTION ""
			::= { mbusBA 38 }

mbusBAValue10		OBJECT-TYPE
			SYNTAX	INTEGER
			ACCESS	read-only
			STATUS	current
	DESCRIPTION ""
			::= { mbusBA 39 }

mbusBAVIF11		OBJECT-TYPE
			SYNTAX	INTEGER
			ACCESS	read-only
			STATUS	current
	DESCRIPTION ""
			::= { mbusBA 40 }

mbusBAValue11		OBJECT-TYPE
			SYNTAX	INTEGER
			ACCESS	read-only
			STATUS	current
	DESCRIPTION ""
			::= { mbusBA 41 }

mbusBAVIF12		OBJECT-TYPE
			SYNTAX	INTEGER
			ACCESS	read-only
			STATUS	current
	DESCRIPTION ""
			::= { mbusBA 42 }

mbusBAValue12		OBJECT-TYPE
			SYNTAX	INTEGER
			ACCESS	read-only
			STATUS	current
	DESCRIPTION ""
			::= { mbusBA 43 }

mbusBAVIF13		OBJECT-TYPE
			SYNTAX	INTEGER
			ACCESS	read-only
			STATUS	current
	DESCRIPTION ""
			::= { mbusBA 44 }

mbusBAValue13		OBJECT-TYPE
			SYNTAX	INTEGER
			ACCESS	read-only
			STATUS	current
	DESCRIPTION ""
			::= { mbusBA 45 }

mbusBAVIF14		OBJECT-TYPE
			SYNTAX	INTEGER
			ACCESS	read-only
			STATUS	current
	DESCRIPTION ""
			::= { mbusBA 46 }

mbusBAValue14		OBJECT-TYPE
			SYNTAX	INTEGER
			ACCESS	read-only
			STATUS	current
	DESCRIPTION ""
			::= { mbusBA 47 }

mbusBAVIF15		OBJECT-TYPE
			SYNTAX	INTEGER
			ACCESS	read-only
			STATUS	current
	DESCRIPTION ""
			::= { mbusBA 48 }

mbusBAValue15		OBJECT-TYPE
			SYNTAX	INTEGER
			ACCESS	read-only
			STATUS	current
	DESCRIPTION ""
			::= { mbusBA 49 }

mbusBAVIF16		OBJECT-TYPE
			SYNTAX	INTEGER
			ACCESS	read-only
			STATUS	current
	DESCRIPTION ""
			::= { mbusBA 50 }

mbusBAValue16		OBJECT-TYPE
			SYNTAX	INTEGER
			ACCESS	read-only
			STATUS	current
	DESCRIPTION ""
			::= { mbusBA 51 }

mbusBAVIF17		OBJECT-TYPE
			SYNTAX	INTEGER
			ACCESS	read-only
			STATUS	current
	DESCRIPTION ""
			::= { mbusBA 52 }

mbusBAValue17		OBJECT-TYPE
			SYNTAX	INTEGER
			ACCESS	read-only
			STATUS	current
	DESCRIPTION ""
			::= { mbusBA 53 }

mbusBAVIF18		OBJECT-TYPE
			SYNTAX	INTEGER
			ACCESS	read-only
			STATUS	current
	DESCRIPTION ""
			::= { mbusBA 54 }

mbusBAValue18		OBJECT-TYPE
			SYNTAX	INTEGER
			ACCESS	read-only
			STATUS	current
	DESCRIPTION ""
			::= { mbusBA 55 }

mbusBAVIF19		OBJECT-TYPE
			SYNTAX	INTEGER
			ACCESS	read-only
			STATUS	current
	DESCRIPTION ""
			::= { mbusBA 56 }

mbusBAValue19		OBJECT-TYPE
			SYNTAX	INTEGER
			ACCESS	read-only
			STATUS	current
	DESCRIPTION ""
			::= { mbusBA 57 }

mbusBAVIF1A		OBJECT-TYPE
			SYNTAX	INTEGER
			ACCESS	read-only
			STATUS	current
	DESCRIPTION ""
			::= { mbusBA 58 }

mbusBAValue1A		OBJECT-TYPE
			SYNTAX	INTEGER
			ACCESS	read-only
			STATUS	current
	DESCRIPTION ""
			::= { mbusBA 59 }

mbusBAVIF1B		OBJECT-TYPE
			SYNTAX	INTEGER
			ACCESS	read-only
			STATUS	current
	DESCRIPTION ""
			::= { mbusBA 60 }

mbusBAValue1B		OBJECT-TYPE
			SYNTAX	INTEGER
			ACCESS	read-only
			STATUS	current
	DESCRIPTION ""
			::= { mbusBA 61 }

mbusBAVIF1C		OBJECT-TYPE
			SYNTAX	INTEGER
			ACCESS	read-only
			STATUS	current
	DESCRIPTION ""
			::= { mbusBA 62 }

mbusBAValue1C		OBJECT-TYPE
			SYNTAX	INTEGER
			ACCESS	read-only
			STATUS	current
	DESCRIPTION ""
			::= { mbusBA 63 }

mbusBAVIF1D		OBJECT-TYPE
			SYNTAX	INTEGER
			ACCESS	read-only
			STATUS	current
	DESCRIPTION ""
			::= { mbusBA 64 }

mbusBAValue1D		OBJECT-TYPE
			SYNTAX	INTEGER
			ACCESS	read-only
			STATUS	current
	DESCRIPTION ""
			::= { mbusBA 65 }

mbusBAVIF1E		OBJECT-TYPE
			SYNTAX	INTEGER
			ACCESS	read-only
			STATUS	current
	DESCRIPTION ""
			::= { mbusBA 66 }

mbusBAValue1E		OBJECT-TYPE
			SYNTAX	INTEGER
			ACCESS	read-only
			STATUS	current
	DESCRIPTION ""
			::= { mbusBA 67 }

mbusBAVIF1F		OBJECT-TYPE
			SYNTAX	INTEGER
			ACCESS	read-only
			STATUS	current
	DESCRIPTION ""
			::= { mbusBA 68 }

mbusBAValue1F		OBJECT-TYPE
			SYNTAX	INTEGER
			ACCESS	read-only
			STATUS	current
	DESCRIPTION ""
			::= { mbusBA 69 }

mbusBAVIF20		OBJECT-TYPE
			SYNTAX	INTEGER
			ACCESS	read-only
			STATUS	current
	DESCRIPTION ""
			::= { mbusBA 70 }

mbusBAValue20		OBJECT-TYPE
			SYNTAX	INTEGER
			ACCESS	read-only
			STATUS	current
	DESCRIPTION ""
			::= { mbusBA 71 }

mbusBAVIF21		OBJECT-TYPE
			SYNTAX	INTEGER
			ACCESS	read-only
			STATUS	current
	DESCRIPTION ""
			::= { mbusBA 72 }

mbusBAValue21		OBJECT-TYPE
			SYNTAX	INTEGER
			ACCESS	read-only
			STATUS	current
	DESCRIPTION ""
			::= { mbusBA 73 }

mbusBAVIF22		OBJECT-TYPE
			SYNTAX	INTEGER
			ACCESS	read-only
			STATUS	current
	DESCRIPTION ""
			::= { mbusBA 74 }

mbusBAValue22		OBJECT-TYPE
			SYNTAX	INTEGER
			ACCESS	read-only
			STATUS	current
	DESCRIPTION ""
			::= { mbusBA 75 }

mbusBAVIF23		OBJECT-TYPE
			SYNTAX	INTEGER
			ACCESS	read-only
			STATUS	current
	DESCRIPTION ""
			::= { mbusBA 76 }

mbusBAValue23		OBJECT-TYPE
			SYNTAX	INTEGER
			ACCESS	read-only
			STATUS	current
	DESCRIPTION ""
			::= { mbusBA 77 }

mbusBAVIF24		OBJECT-TYPE
			SYNTAX	INTEGER
			ACCESS	read-only
			STATUS	current
	DESCRIPTION ""
			::= { mbusBA 78 }

mbusBAValue24		OBJECT-TYPE
			SYNTAX	INTEGER
			ACCESS	read-only
			STATUS	current
	DESCRIPTION ""
			::= { mbusBA 79 }

mbusBAVIF25		OBJECT-TYPE
			SYNTAX	INTEGER
			ACCESS	read-only
			STATUS	current
	DESCRIPTION ""
			::= { mbusBA 80 }

mbusBAValue25		OBJECT-TYPE
			SYNTAX	INTEGER
			ACCESS	read-only
			STATUS	current
	DESCRIPTION ""
			::= { mbusBA 81 }

mbusBAVIF26		OBJECT-TYPE
			SYNTAX	INTEGER
			ACCESS	read-only
			STATUS	current
	DESCRIPTION ""
			::= { mbusBA 82 }

mbusBAValue26		OBJECT-TYPE
			SYNTAX	INTEGER
			ACCESS	read-only
			STATUS	current
	DESCRIPTION ""
			::= { mbusBA 83 }

mbusBAVIF27		OBJECT-TYPE
			SYNTAX	INTEGER
			ACCESS	read-only
			STATUS	current
	DESCRIPTION ""
			::= { mbusBA 84 }

mbusBAValue27		OBJECT-TYPE
			SYNTAX	INTEGER
			ACCESS	read-only
			STATUS	current
	DESCRIPTION ""
			::= { mbusBA 85 }

mbusBAVIF28		OBJECT-TYPE
			SYNTAX	INTEGER
			ACCESS	read-only
			STATUS	current
	DESCRIPTION ""
			::= { mbusBA 86 }

mbusBAValue28		OBJECT-TYPE
			SYNTAX	INTEGER
			ACCESS	read-only
			STATUS	current
	DESCRIPTION ""
			::= { mbusBA 87 }

mbusBAVIF29		OBJECT-TYPE
			SYNTAX	INTEGER
			ACCESS	read-only
			STATUS	current
	DESCRIPTION ""
			::= { mbusBA 88 }

mbusBAValue29		OBJECT-TYPE
			SYNTAX	INTEGER
			ACCESS	read-only
			STATUS	current
	DESCRIPTION ""
			::= { mbusBA 89 }

mbusBAVIF2A		OBJECT-TYPE
			SYNTAX	INTEGER
			ACCESS	read-only
			STATUS	current
	DESCRIPTION ""
			::= { mbusBA 90 }

mbusBAValue2A		OBJECT-TYPE
			SYNTAX	INTEGER
			ACCESS	read-only
			STATUS	current
	DESCRIPTION ""
			::= { mbusBA 91 }

mbusBAVIF2B		OBJECT-TYPE
			SYNTAX	INTEGER
			ACCESS	read-only
			STATUS	current
	DESCRIPTION ""
			::= { mbusBA 92 }

mbusBAValue2B		OBJECT-TYPE
			SYNTAX	INTEGER
			ACCESS	read-only
			STATUS	current
	DESCRIPTION ""
			::= { mbusBA 93 }

mbusBAVIF2C		OBJECT-TYPE
			SYNTAX	INTEGER
			ACCESS	read-only
			STATUS	current
	DESCRIPTION ""
			::= { mbusBA 94 }

mbusBAValue2C		OBJECT-TYPE
			SYNTAX	INTEGER
			ACCESS	read-only
			STATUS	current
	DESCRIPTION ""
			::= { mbusBA 95 }

mbusBAVIF2D		OBJECT-TYPE
			SYNTAX	INTEGER
			ACCESS	read-only
			STATUS	current
	DESCRIPTION ""
			::= { mbusBA 96 }

mbusBAValue2D		OBJECT-TYPE
			SYNTAX	INTEGER
			ACCESS	read-only
			STATUS	current
	DESCRIPTION ""
			::= { mbusBA 97 }

mbusBAVIF2E		OBJECT-TYPE
			SYNTAX	INTEGER
			ACCESS	read-only
			STATUS	current
	DESCRIPTION ""
			::= { mbusBA 98 }

mbusBAValue2E		OBJECT-TYPE
			SYNTAX	INTEGER
			ACCESS	read-only
			STATUS	current
	DESCRIPTION ""
			::= { mbusBA 99 }

mbusBAVIF2F		OBJECT-TYPE
			SYNTAX	INTEGER
			ACCESS	read-only
			STATUS	current
	DESCRIPTION ""
			::= { mbusBA 100 }

mbusBAValue2F		OBJECT-TYPE
			SYNTAX	INTEGER
			ACCESS	read-only
			STATUS	current
	DESCRIPTION ""
			::= { mbusBA 101 }

mbusBB			OBJECT IDENTIFIER ::= { mbus 187 }

mbusBBIdNumber		OBJECT-TYPE
			SYNTAX	Gauge
			ACCESS	read-only
			STATUS	current
	DESCRIPTION ""
			::= { mbusBB 1 }

mbusBBManufacturer	OBJECT-TYPE
			SYNTAX	Gauge
			ACCESS	read-only
			STATUS	current
	DESCRIPTION ""
			::= { mbusBB 2 }

mbusBBVersion		OBJECT-TYPE
			SYNTAX	Gauge
			ACCESS	read-only
			STATUS	current
	DESCRIPTION ""
			::= { mbusBB 3 }

mbusBBMedium		OBJECT-TYPE
			SYNTAX	Gauge
			ACCESS	read-only
			STATUS	current
	DESCRIPTION ""
			::= { mbusBB 4 }

mbusBBStatus		OBJECT-TYPE
			SYNTAX	Gauge
			ACCESS	read-only
			STATUS	current
	DESCRIPTION ""
			::= { mbusBB 5 }

mbusBBVIF00		OBJECT-TYPE
			SYNTAX	INTEGER
			ACCESS	read-only
			STATUS	current
	DESCRIPTION ""
			::= { mbusBB 6 }

mbusBBValue00		OBJECT-TYPE
			SYNTAX	INTEGER
			ACCESS	read-only
			STATUS	current
	DESCRIPTION ""
			::= { mbusBB 7 }

mbusBBVIF01		OBJECT-TYPE
			SYNTAX	INTEGER
			ACCESS	read-only
			STATUS	current
	DESCRIPTION ""
			::= { mbusBB 8 }

mbusBBValue01		OBJECT-TYPE
			SYNTAX	INTEGER
			ACCESS	read-only
			STATUS	current
	DESCRIPTION ""
			::= { mbusBB 9 }

mbusBBVIF02		OBJECT-TYPE
			SYNTAX	INTEGER
			ACCESS	read-only
			STATUS	current
	DESCRIPTION ""
			::= { mbusBB 10 }

mbusBBValue02		OBJECT-TYPE
			SYNTAX	INTEGER
			ACCESS	read-only
			STATUS	current
	DESCRIPTION ""
			::= { mbusBB 11 }

mbusBBVIF03		OBJECT-TYPE
			SYNTAX	INTEGER
			ACCESS	read-only
			STATUS	current
	DESCRIPTION ""
			::= { mbusBB 12 }

mbusBBValue03		OBJECT-TYPE
			SYNTAX	INTEGER
			ACCESS	read-only
			STATUS	current
	DESCRIPTION ""
			::= { mbusBB 13 }

mbusBBVIF04		OBJECT-TYPE
			SYNTAX	INTEGER
			ACCESS	read-only
			STATUS	current
	DESCRIPTION ""
			::= { mbusBB 14 }

mbusBBValue04		OBJECT-TYPE
			SYNTAX	INTEGER
			ACCESS	read-only
			STATUS	current
	DESCRIPTION ""
			::= { mbusBB 15 }

mbusBBVIF05		OBJECT-TYPE
			SYNTAX	INTEGER
			ACCESS	read-only
			STATUS	current
	DESCRIPTION ""
			::= { mbusBB 16 }

mbusBBValue05		OBJECT-TYPE
			SYNTAX	INTEGER
			ACCESS	read-only
			STATUS	current
	DESCRIPTION ""
			::= { mbusBB 17 }

mbusBBVIF06		OBJECT-TYPE
			SYNTAX	INTEGER
			ACCESS	read-only
			STATUS	current
	DESCRIPTION ""
			::= { mbusBB 18 }

mbusBBValue06		OBJECT-TYPE
			SYNTAX	INTEGER
			ACCESS	read-only
			STATUS	current
	DESCRIPTION ""
			::= { mbusBB 19 }

mbusBBVIF07		OBJECT-TYPE
			SYNTAX	INTEGER
			ACCESS	read-only
			STATUS	current
	DESCRIPTION ""
			::= { mbusBB 20 }

mbusBBValue07		OBJECT-TYPE
			SYNTAX	INTEGER
			ACCESS	read-only
			STATUS	current
	DESCRIPTION ""
			::= { mbusBB 21 }

mbusBBVIF08		OBJECT-TYPE
			SYNTAX	INTEGER
			ACCESS	read-only
			STATUS	current
	DESCRIPTION ""
			::= { mbusBB 22 }

mbusBBValue08		OBJECT-TYPE
			SYNTAX	INTEGER
			ACCESS	read-only
			STATUS	current
	DESCRIPTION ""
			::= { mbusBB 23 }

mbusBBVIF09		OBJECT-TYPE
			SYNTAX	INTEGER
			ACCESS	read-only
			STATUS	current
	DESCRIPTION ""
			::= { mbusBB 24 }

mbusBBValue09		OBJECT-TYPE
			SYNTAX	INTEGER
			ACCESS	read-only
			STATUS	current
	DESCRIPTION ""
			::= { mbusBB 25 }

mbusBBVIF0A		OBJECT-TYPE
			SYNTAX	INTEGER
			ACCESS	read-only
			STATUS	current
	DESCRIPTION ""
			::= { mbusBB 26 }

mbusBBValue0A		OBJECT-TYPE
			SYNTAX	INTEGER
			ACCESS	read-only
			STATUS	current
	DESCRIPTION ""
			::= { mbusBB 27 }

mbusBBVIF0B		OBJECT-TYPE
			SYNTAX	INTEGER
			ACCESS	read-only
			STATUS	current
	DESCRIPTION ""
			::= { mbusBB 28 }

mbusBBValue0B		OBJECT-TYPE
			SYNTAX	INTEGER
			ACCESS	read-only
			STATUS	current
	DESCRIPTION ""
			::= { mbusBB 29 }

mbusBBVIF0C		OBJECT-TYPE
			SYNTAX	INTEGER
			ACCESS	read-only
			STATUS	current
	DESCRIPTION ""
			::= { mbusBB 30 }

mbusBBValue0C		OBJECT-TYPE
			SYNTAX	INTEGER
			ACCESS	read-only
			STATUS	current
	DESCRIPTION ""
			::= { mbusBB 31 }

mbusBBVIF0D		OBJECT-TYPE
			SYNTAX	INTEGER
			ACCESS	read-only
			STATUS	current
	DESCRIPTION ""
			::= { mbusBB 32 }

mbusBBValue0D		OBJECT-TYPE
			SYNTAX	INTEGER
			ACCESS	read-only
			STATUS	current
	DESCRIPTION ""
			::= { mbusBB 33 }

mbusBBVIF0E		OBJECT-TYPE
			SYNTAX	INTEGER
			ACCESS	read-only
			STATUS	current
	DESCRIPTION ""
			::= { mbusBB 34 }

mbusBBValue0E		OBJECT-TYPE
			SYNTAX	INTEGER
			ACCESS	read-only
			STATUS	current
	DESCRIPTION ""
			::= { mbusBB 35 }

mbusBBVIF0F		OBJECT-TYPE
			SYNTAX	INTEGER
			ACCESS	read-only
			STATUS	current
	DESCRIPTION ""
			::= { mbusBB 36 }

mbusBBValue0F		OBJECT-TYPE
			SYNTAX	INTEGER
			ACCESS	read-only
			STATUS	current
	DESCRIPTION ""
			::= { mbusBB 37 }

mbusBBVIF10		OBJECT-TYPE
			SYNTAX	INTEGER
			ACCESS	read-only
			STATUS	current
	DESCRIPTION ""
			::= { mbusBB 38 }

mbusBBValue10		OBJECT-TYPE
			SYNTAX	INTEGER
			ACCESS	read-only
			STATUS	current
	DESCRIPTION ""
			::= { mbusBB 39 }

mbusBBVIF11		OBJECT-TYPE
			SYNTAX	INTEGER
			ACCESS	read-only
			STATUS	current
	DESCRIPTION ""
			::= { mbusBB 40 }

mbusBBValue11		OBJECT-TYPE
			SYNTAX	INTEGER
			ACCESS	read-only
			STATUS	current
	DESCRIPTION ""
			::= { mbusBB 41 }

mbusBBVIF12		OBJECT-TYPE
			SYNTAX	INTEGER
			ACCESS	read-only
			STATUS	current
	DESCRIPTION ""
			::= { mbusBB 42 }

mbusBBValue12		OBJECT-TYPE
			SYNTAX	INTEGER
			ACCESS	read-only
			STATUS	current
	DESCRIPTION ""
			::= { mbusBB 43 }

mbusBBVIF13		OBJECT-TYPE
			SYNTAX	INTEGER
			ACCESS	read-only
			STATUS	current
	DESCRIPTION ""
			::= { mbusBB 44 }

mbusBBValue13		OBJECT-TYPE
			SYNTAX	INTEGER
			ACCESS	read-only
			STATUS	current
	DESCRIPTION ""
			::= { mbusBB 45 }

mbusBBVIF14		OBJECT-TYPE
			SYNTAX	INTEGER
			ACCESS	read-only
			STATUS	current
	DESCRIPTION ""
			::= { mbusBB 46 }

mbusBBValue14		OBJECT-TYPE
			SYNTAX	INTEGER
			ACCESS	read-only
			STATUS	current
	DESCRIPTION ""
			::= { mbusBB 47 }

mbusBBVIF15		OBJECT-TYPE
			SYNTAX	INTEGER
			ACCESS	read-only
			STATUS	current
	DESCRIPTION ""
			::= { mbusBB 48 }

mbusBBValue15		OBJECT-TYPE
			SYNTAX	INTEGER
			ACCESS	read-only
			STATUS	current
	DESCRIPTION ""
			::= { mbusBB 49 }

mbusBBVIF16		OBJECT-TYPE
			SYNTAX	INTEGER
			ACCESS	read-only
			STATUS	current
	DESCRIPTION ""
			::= { mbusBB 50 }

mbusBBValue16		OBJECT-TYPE
			SYNTAX	INTEGER
			ACCESS	read-only
			STATUS	current
	DESCRIPTION ""
			::= { mbusBB 51 }

mbusBBVIF17		OBJECT-TYPE
			SYNTAX	INTEGER
			ACCESS	read-only
			STATUS	current
	DESCRIPTION ""
			::= { mbusBB 52 }

mbusBBValue17		OBJECT-TYPE
			SYNTAX	INTEGER
			ACCESS	read-only
			STATUS	current
	DESCRIPTION ""
			::= { mbusBB 53 }

mbusBBVIF18		OBJECT-TYPE
			SYNTAX	INTEGER
			ACCESS	read-only
			STATUS	current
	DESCRIPTION ""
			::= { mbusBB 54 }

mbusBBValue18		OBJECT-TYPE
			SYNTAX	INTEGER
			ACCESS	read-only
			STATUS	current
	DESCRIPTION ""
			::= { mbusBB 55 }

mbusBBVIF19		OBJECT-TYPE
			SYNTAX	INTEGER
			ACCESS	read-only
			STATUS	current
	DESCRIPTION ""
			::= { mbusBB 56 }

mbusBBValue19		OBJECT-TYPE
			SYNTAX	INTEGER
			ACCESS	read-only
			STATUS	current
	DESCRIPTION ""
			::= { mbusBB 57 }

mbusBBVIF1A		OBJECT-TYPE
			SYNTAX	INTEGER
			ACCESS	read-only
			STATUS	current
	DESCRIPTION ""
			::= { mbusBB 58 }

mbusBBValue1A		OBJECT-TYPE
			SYNTAX	INTEGER
			ACCESS	read-only
			STATUS	current
	DESCRIPTION ""
			::= { mbusBB 59 }

mbusBBVIF1B		OBJECT-TYPE
			SYNTAX	INTEGER
			ACCESS	read-only
			STATUS	current
	DESCRIPTION ""
			::= { mbusBB 60 }

mbusBBValue1B		OBJECT-TYPE
			SYNTAX	INTEGER
			ACCESS	read-only
			STATUS	current
	DESCRIPTION ""
			::= { mbusBB 61 }

mbusBBVIF1C		OBJECT-TYPE
			SYNTAX	INTEGER
			ACCESS	read-only
			STATUS	current
	DESCRIPTION ""
			::= { mbusBB 62 }

mbusBBValue1C		OBJECT-TYPE
			SYNTAX	INTEGER
			ACCESS	read-only
			STATUS	current
	DESCRIPTION ""
			::= { mbusBB 63 }

mbusBBVIF1D		OBJECT-TYPE
			SYNTAX	INTEGER
			ACCESS	read-only
			STATUS	current
	DESCRIPTION ""
			::= { mbusBB 64 }

mbusBBValue1D		OBJECT-TYPE
			SYNTAX	INTEGER
			ACCESS	read-only
			STATUS	current
	DESCRIPTION ""
			::= { mbusBB 65 }

mbusBBVIF1E		OBJECT-TYPE
			SYNTAX	INTEGER
			ACCESS	read-only
			STATUS	current
	DESCRIPTION ""
			::= { mbusBB 66 }

mbusBBValue1E		OBJECT-TYPE
			SYNTAX	INTEGER
			ACCESS	read-only
			STATUS	current
	DESCRIPTION ""
			::= { mbusBB 67 }

mbusBBVIF1F		OBJECT-TYPE
			SYNTAX	INTEGER
			ACCESS	read-only
			STATUS	current
	DESCRIPTION ""
			::= { mbusBB 68 }

mbusBBValue1F		OBJECT-TYPE
			SYNTAX	INTEGER
			ACCESS	read-only
			STATUS	current
	DESCRIPTION ""
			::= { mbusBB 69 }

mbusBBVIF20		OBJECT-TYPE
			SYNTAX	INTEGER
			ACCESS	read-only
			STATUS	current
	DESCRIPTION ""
			::= { mbusBB 70 }

mbusBBValue20		OBJECT-TYPE
			SYNTAX	INTEGER
			ACCESS	read-only
			STATUS	current
	DESCRIPTION ""
			::= { mbusBB 71 }

mbusBBVIF21		OBJECT-TYPE
			SYNTAX	INTEGER
			ACCESS	read-only
			STATUS	current
	DESCRIPTION ""
			::= { mbusBB 72 }

mbusBBValue21		OBJECT-TYPE
			SYNTAX	INTEGER
			ACCESS	read-only
			STATUS	current
	DESCRIPTION ""
			::= { mbusBB 73 }

mbusBBVIF22		OBJECT-TYPE
			SYNTAX	INTEGER
			ACCESS	read-only
			STATUS	current
	DESCRIPTION ""
			::= { mbusBB 74 }

mbusBBValue22		OBJECT-TYPE
			SYNTAX	INTEGER
			ACCESS	read-only
			STATUS	current
	DESCRIPTION ""
			::= { mbusBB 75 }

mbusBBVIF23		OBJECT-TYPE
			SYNTAX	INTEGER
			ACCESS	read-only
			STATUS	current
	DESCRIPTION ""
			::= { mbusBB 76 }

mbusBBValue23		OBJECT-TYPE
			SYNTAX	INTEGER
			ACCESS	read-only
			STATUS	current
	DESCRIPTION ""
			::= { mbusBB 77 }

mbusBBVIF24		OBJECT-TYPE
			SYNTAX	INTEGER
			ACCESS	read-only
			STATUS	current
	DESCRIPTION ""
			::= { mbusBB 78 }

mbusBBValue24		OBJECT-TYPE
			SYNTAX	INTEGER
			ACCESS	read-only
			STATUS	current
	DESCRIPTION ""
			::= { mbusBB 79 }

mbusBBVIF25		OBJECT-TYPE
			SYNTAX	INTEGER
			ACCESS	read-only
			STATUS	current
	DESCRIPTION ""
			::= { mbusBB 80 }

mbusBBValue25		OBJECT-TYPE
			SYNTAX	INTEGER
			ACCESS	read-only
			STATUS	current
	DESCRIPTION ""
			::= { mbusBB 81 }

mbusBBVIF26		OBJECT-TYPE
			SYNTAX	INTEGER
			ACCESS	read-only
			STATUS	current
	DESCRIPTION ""
			::= { mbusBB 82 }

mbusBBValue26		OBJECT-TYPE
			SYNTAX	INTEGER
			ACCESS	read-only
			STATUS	current
	DESCRIPTION ""
			::= { mbusBB 83 }

mbusBBVIF27		OBJECT-TYPE
			SYNTAX	INTEGER
			ACCESS	read-only
			STATUS	current
	DESCRIPTION ""
			::= { mbusBB 84 }

mbusBBValue27		OBJECT-TYPE
			SYNTAX	INTEGER
			ACCESS	read-only
			STATUS	current
	DESCRIPTION ""
			::= { mbusBB 85 }

mbusBBVIF28		OBJECT-TYPE
			SYNTAX	INTEGER
			ACCESS	read-only
			STATUS	current
	DESCRIPTION ""
			::= { mbusBB 86 }

mbusBBValue28		OBJECT-TYPE
			SYNTAX	INTEGER
			ACCESS	read-only
			STATUS	current
	DESCRIPTION ""
			::= { mbusBB 87 }

mbusBBVIF29		OBJECT-TYPE
			SYNTAX	INTEGER
			ACCESS	read-only
			STATUS	current
	DESCRIPTION ""
			::= { mbusBB 88 }

mbusBBValue29		OBJECT-TYPE
			SYNTAX	INTEGER
			ACCESS	read-only
			STATUS	current
	DESCRIPTION ""
			::= { mbusBB 89 }

mbusBBVIF2A		OBJECT-TYPE
			SYNTAX	INTEGER
			ACCESS	read-only
			STATUS	current
	DESCRIPTION ""
			::= { mbusBB 90 }

mbusBBValue2A		OBJECT-TYPE
			SYNTAX	INTEGER
			ACCESS	read-only
			STATUS	current
	DESCRIPTION ""
			::= { mbusBB 91 }

mbusBBVIF2B		OBJECT-TYPE
			SYNTAX	INTEGER
			ACCESS	read-only
			STATUS	current
	DESCRIPTION ""
			::= { mbusBB 92 }

mbusBBValue2B		OBJECT-TYPE
			SYNTAX	INTEGER
			ACCESS	read-only
			STATUS	current
	DESCRIPTION ""
			::= { mbusBB 93 }

mbusBBVIF2C		OBJECT-TYPE
			SYNTAX	INTEGER
			ACCESS	read-only
			STATUS	current
	DESCRIPTION ""
			::= { mbusBB 94 }

mbusBBValue2C		OBJECT-TYPE
			SYNTAX	INTEGER
			ACCESS	read-only
			STATUS	current
	DESCRIPTION ""
			::= { mbusBB 95 }

mbusBBVIF2D		OBJECT-TYPE
			SYNTAX	INTEGER
			ACCESS	read-only
			STATUS	current
	DESCRIPTION ""
			::= { mbusBB 96 }

mbusBBValue2D		OBJECT-TYPE
			SYNTAX	INTEGER
			ACCESS	read-only
			STATUS	current
	DESCRIPTION ""
			::= { mbusBB 97 }

mbusBBVIF2E		OBJECT-TYPE
			SYNTAX	INTEGER
			ACCESS	read-only
			STATUS	current
	DESCRIPTION ""
			::= { mbusBB 98 }

mbusBBValue2E		OBJECT-TYPE
			SYNTAX	INTEGER
			ACCESS	read-only
			STATUS	current
	DESCRIPTION ""
			::= { mbusBB 99 }

mbusBBVIF2F		OBJECT-TYPE
			SYNTAX	INTEGER
			ACCESS	read-only
			STATUS	current
	DESCRIPTION ""
			::= { mbusBB 100 }

mbusBBValue2F		OBJECT-TYPE
			SYNTAX	INTEGER
			ACCESS	read-only
			STATUS	current
	DESCRIPTION ""
			::= { mbusBB 101 }

mbusBC			OBJECT IDENTIFIER ::= { mbus 188 }

mbusBCIdNumber		OBJECT-TYPE
			SYNTAX	Gauge
			ACCESS	read-only
			STATUS	current
	DESCRIPTION ""
			::= { mbusBC 1 }

mbusBCManufacturer	OBJECT-TYPE
			SYNTAX	Gauge
			ACCESS	read-only
			STATUS	current
	DESCRIPTION ""
			::= { mbusBC 2 }

mbusBCVersion		OBJECT-TYPE
			SYNTAX	Gauge
			ACCESS	read-only
			STATUS	current
	DESCRIPTION ""
			::= { mbusBC 3 }

mbusBCMedium		OBJECT-TYPE
			SYNTAX	Gauge
			ACCESS	read-only
			STATUS	current
	DESCRIPTION ""
			::= { mbusBC 4 }

mbusBCStatus		OBJECT-TYPE
			SYNTAX	Gauge
			ACCESS	read-only
			STATUS	current
	DESCRIPTION ""
			::= { mbusBC 5 }

mbusBCVIF00		OBJECT-TYPE
			SYNTAX	INTEGER
			ACCESS	read-only
			STATUS	current
	DESCRIPTION ""
			::= { mbusBC 6 }

mbusBCValue00		OBJECT-TYPE
			SYNTAX	INTEGER
			ACCESS	read-only
			STATUS	current
	DESCRIPTION ""
			::= { mbusBC 7 }

mbusBCVIF01		OBJECT-TYPE
			SYNTAX	INTEGER
			ACCESS	read-only
			STATUS	current
	DESCRIPTION ""
			::= { mbusBC 8 }

mbusBCValue01		OBJECT-TYPE
			SYNTAX	INTEGER
			ACCESS	read-only
			STATUS	current
	DESCRIPTION ""
			::= { mbusBC 9 }

mbusBCVIF02		OBJECT-TYPE
			SYNTAX	INTEGER
			ACCESS	read-only
			STATUS	current
	DESCRIPTION ""
			::= { mbusBC 10 }

mbusBCValue02		OBJECT-TYPE
			SYNTAX	INTEGER
			ACCESS	read-only
			STATUS	current
	DESCRIPTION ""
			::= { mbusBC 11 }

mbusBCVIF03		OBJECT-TYPE
			SYNTAX	INTEGER
			ACCESS	read-only
			STATUS	current
	DESCRIPTION ""
			::= { mbusBC 12 }

mbusBCValue03		OBJECT-TYPE
			SYNTAX	INTEGER
			ACCESS	read-only
			STATUS	current
	DESCRIPTION ""
			::= { mbusBC 13 }

mbusBCVIF04		OBJECT-TYPE
			SYNTAX	INTEGER
			ACCESS	read-only
			STATUS	current
	DESCRIPTION ""
			::= { mbusBC 14 }

mbusBCValue04		OBJECT-TYPE
			SYNTAX	INTEGER
			ACCESS	read-only
			STATUS	current
	DESCRIPTION ""
			::= { mbusBC 15 }

mbusBCVIF05		OBJECT-TYPE
			SYNTAX	INTEGER
			ACCESS	read-only
			STATUS	current
	DESCRIPTION ""
			::= { mbusBC 16 }

mbusBCValue05		OBJECT-TYPE
			SYNTAX	INTEGER
			ACCESS	read-only
			STATUS	current
	DESCRIPTION ""
			::= { mbusBC 17 }

mbusBCVIF06		OBJECT-TYPE
			SYNTAX	INTEGER
			ACCESS	read-only
			STATUS	current
	DESCRIPTION ""
			::= { mbusBC 18 }

mbusBCValue06		OBJECT-TYPE
			SYNTAX	INTEGER
			ACCESS	read-only
			STATUS	current
	DESCRIPTION ""
			::= { mbusBC 19 }

mbusBCVIF07		OBJECT-TYPE
			SYNTAX	INTEGER
			ACCESS	read-only
			STATUS	current
	DESCRIPTION ""
			::= { mbusBC 20 }

mbusBCValue07		OBJECT-TYPE
			SYNTAX	INTEGER
			ACCESS	read-only
			STATUS	current
	DESCRIPTION ""
			::= { mbusBC 21 }

mbusBCVIF08		OBJECT-TYPE
			SYNTAX	INTEGER
			ACCESS	read-only
			STATUS	current
	DESCRIPTION ""
			::= { mbusBC 22 }

mbusBCValue08		OBJECT-TYPE
			SYNTAX	INTEGER
			ACCESS	read-only
			STATUS	current
	DESCRIPTION ""
			::= { mbusBC 23 }

mbusBCVIF09		OBJECT-TYPE
			SYNTAX	INTEGER
			ACCESS	read-only
			STATUS	current
	DESCRIPTION ""
			::= { mbusBC 24 }

mbusBCValue09		OBJECT-TYPE
			SYNTAX	INTEGER
			ACCESS	read-only
			STATUS	current
	DESCRIPTION ""
			::= { mbusBC 25 }

mbusBCVIF0A		OBJECT-TYPE
			SYNTAX	INTEGER
			ACCESS	read-only
			STATUS	current
	DESCRIPTION ""
			::= { mbusBC 26 }

mbusBCValue0A		OBJECT-TYPE
			SYNTAX	INTEGER
			ACCESS	read-only
			STATUS	current
	DESCRIPTION ""
			::= { mbusBC 27 }

mbusBCVIF0B		OBJECT-TYPE
			SYNTAX	INTEGER
			ACCESS	read-only
			STATUS	current
	DESCRIPTION ""
			::= { mbusBC 28 }

mbusBCValue0B		OBJECT-TYPE
			SYNTAX	INTEGER
			ACCESS	read-only
			STATUS	current
	DESCRIPTION ""
			::= { mbusBC 29 }

mbusBCVIF0C		OBJECT-TYPE
			SYNTAX	INTEGER
			ACCESS	read-only
			STATUS	current
	DESCRIPTION ""
			::= { mbusBC 30 }

mbusBCValue0C		OBJECT-TYPE
			SYNTAX	INTEGER
			ACCESS	read-only
			STATUS	current
	DESCRIPTION ""
			::= { mbusBC 31 }

mbusBCVIF0D		OBJECT-TYPE
			SYNTAX	INTEGER
			ACCESS	read-only
			STATUS	current
	DESCRIPTION ""
			::= { mbusBC 32 }

mbusBCValue0D		OBJECT-TYPE
			SYNTAX	INTEGER
			ACCESS	read-only
			STATUS	current
	DESCRIPTION ""
			::= { mbusBC 33 }

mbusBCVIF0E		OBJECT-TYPE
			SYNTAX	INTEGER
			ACCESS	read-only
			STATUS	current
	DESCRIPTION ""
			::= { mbusBC 34 }

mbusBCValue0E		OBJECT-TYPE
			SYNTAX	INTEGER
			ACCESS	read-only
			STATUS	current
	DESCRIPTION ""
			::= { mbusBC 35 }

mbusBCVIF0F		OBJECT-TYPE
			SYNTAX	INTEGER
			ACCESS	read-only
			STATUS	current
	DESCRIPTION ""
			::= { mbusBC 36 }

mbusBCValue0F		OBJECT-TYPE
			SYNTAX	INTEGER
			ACCESS	read-only
			STATUS	current
	DESCRIPTION ""
			::= { mbusBC 37 }

mbusBCVIF10		OBJECT-TYPE
			SYNTAX	INTEGER
			ACCESS	read-only
			STATUS	current
	DESCRIPTION ""
			::= { mbusBC 38 }

mbusBCValue10		OBJECT-TYPE
			SYNTAX	INTEGER
			ACCESS	read-only
			STATUS	current
	DESCRIPTION ""
			::= { mbusBC 39 }

mbusBCVIF11		OBJECT-TYPE
			SYNTAX	INTEGER
			ACCESS	read-only
			STATUS	current
	DESCRIPTION ""
			::= { mbusBC 40 }

mbusBCValue11		OBJECT-TYPE
			SYNTAX	INTEGER
			ACCESS	read-only
			STATUS	current
	DESCRIPTION ""
			::= { mbusBC 41 }

mbusBCVIF12		OBJECT-TYPE
			SYNTAX	INTEGER
			ACCESS	read-only
			STATUS	current
	DESCRIPTION ""
			::= { mbusBC 42 }

mbusBCValue12		OBJECT-TYPE
			SYNTAX	INTEGER
			ACCESS	read-only
			STATUS	current
	DESCRIPTION ""
			::= { mbusBC 43 }

mbusBCVIF13		OBJECT-TYPE
			SYNTAX	INTEGER
			ACCESS	read-only
			STATUS	current
	DESCRIPTION ""
			::= { mbusBC 44 }

mbusBCValue13		OBJECT-TYPE
			SYNTAX	INTEGER
			ACCESS	read-only
			STATUS	current
	DESCRIPTION ""
			::= { mbusBC 45 }

mbusBCVIF14		OBJECT-TYPE
			SYNTAX	INTEGER
			ACCESS	read-only
			STATUS	current
	DESCRIPTION ""
			::= { mbusBC 46 }

mbusBCValue14		OBJECT-TYPE
			SYNTAX	INTEGER
			ACCESS	read-only
			STATUS	current
	DESCRIPTION ""
			::= { mbusBC 47 }

mbusBCVIF15		OBJECT-TYPE
			SYNTAX	INTEGER
			ACCESS	read-only
			STATUS	current
	DESCRIPTION ""
			::= { mbusBC 48 }

mbusBCValue15		OBJECT-TYPE
			SYNTAX	INTEGER
			ACCESS	read-only
			STATUS	current
	DESCRIPTION ""
			::= { mbusBC 49 }

mbusBCVIF16		OBJECT-TYPE
			SYNTAX	INTEGER
			ACCESS	read-only
			STATUS	current
	DESCRIPTION ""
			::= { mbusBC 50 }

mbusBCValue16		OBJECT-TYPE
			SYNTAX	INTEGER
			ACCESS	read-only
			STATUS	current
	DESCRIPTION ""
			::= { mbusBC 51 }

mbusBCVIF17		OBJECT-TYPE
			SYNTAX	INTEGER
			ACCESS	read-only
			STATUS	current
	DESCRIPTION ""
			::= { mbusBC 52 }

mbusBCValue17		OBJECT-TYPE
			SYNTAX	INTEGER
			ACCESS	read-only
			STATUS	current
	DESCRIPTION ""
			::= { mbusBC 53 }

mbusBCVIF18		OBJECT-TYPE
			SYNTAX	INTEGER
			ACCESS	read-only
			STATUS	current
	DESCRIPTION ""
			::= { mbusBC 54 }

mbusBCValue18		OBJECT-TYPE
			SYNTAX	INTEGER
			ACCESS	read-only
			STATUS	current
	DESCRIPTION ""
			::= { mbusBC 55 }

mbusBCVIF19		OBJECT-TYPE
			SYNTAX	INTEGER
			ACCESS	read-only
			STATUS	current
	DESCRIPTION ""
			::= { mbusBC 56 }

mbusBCValue19		OBJECT-TYPE
			SYNTAX	INTEGER
			ACCESS	read-only
			STATUS	current
	DESCRIPTION ""
			::= { mbusBC 57 }

mbusBCVIF1A		OBJECT-TYPE
			SYNTAX	INTEGER
			ACCESS	read-only
			STATUS	current
	DESCRIPTION ""
			::= { mbusBC 58 }

mbusBCValue1A		OBJECT-TYPE
			SYNTAX	INTEGER
			ACCESS	read-only
			STATUS	current
	DESCRIPTION ""
			::= { mbusBC 59 }

mbusBCVIF1B		OBJECT-TYPE
			SYNTAX	INTEGER
			ACCESS	read-only
			STATUS	current
	DESCRIPTION ""
			::= { mbusBC 60 }

mbusBCValue1B		OBJECT-TYPE
			SYNTAX	INTEGER
			ACCESS	read-only
			STATUS	current
	DESCRIPTION ""
			::= { mbusBC 61 }

mbusBCVIF1C		OBJECT-TYPE
			SYNTAX	INTEGER
			ACCESS	read-only
			STATUS	current
	DESCRIPTION ""
			::= { mbusBC 62 }

mbusBCValue1C		OBJECT-TYPE
			SYNTAX	INTEGER
			ACCESS	read-only
			STATUS	current
	DESCRIPTION ""
			::= { mbusBC 63 }

mbusBCVIF1D		OBJECT-TYPE
			SYNTAX	INTEGER
			ACCESS	read-only
			STATUS	current
	DESCRIPTION ""
			::= { mbusBC 64 }

mbusBCValue1D		OBJECT-TYPE
			SYNTAX	INTEGER
			ACCESS	read-only
			STATUS	current
	DESCRIPTION ""
			::= { mbusBC 65 }

mbusBCVIF1E		OBJECT-TYPE
			SYNTAX	INTEGER
			ACCESS	read-only
			STATUS	current
	DESCRIPTION ""
			::= { mbusBC 66 }

mbusBCValue1E		OBJECT-TYPE
			SYNTAX	INTEGER
			ACCESS	read-only
			STATUS	current
	DESCRIPTION ""
			::= { mbusBC 67 }

mbusBCVIF1F		OBJECT-TYPE
			SYNTAX	INTEGER
			ACCESS	read-only
			STATUS	current
	DESCRIPTION ""
			::= { mbusBC 68 }

mbusBCValue1F		OBJECT-TYPE
			SYNTAX	INTEGER
			ACCESS	read-only
			STATUS	current
	DESCRIPTION ""
			::= { mbusBC 69 }

mbusBCVIF20		OBJECT-TYPE
			SYNTAX	INTEGER
			ACCESS	read-only
			STATUS	current
	DESCRIPTION ""
			::= { mbusBC 70 }

mbusBCValue20		OBJECT-TYPE
			SYNTAX	INTEGER
			ACCESS	read-only
			STATUS	current
	DESCRIPTION ""
			::= { mbusBC 71 }

mbusBCVIF21		OBJECT-TYPE
			SYNTAX	INTEGER
			ACCESS	read-only
			STATUS	current
	DESCRIPTION ""
			::= { mbusBC 72 }

mbusBCValue21		OBJECT-TYPE
			SYNTAX	INTEGER
			ACCESS	read-only
			STATUS	current
	DESCRIPTION ""
			::= { mbusBC 73 }

mbusBCVIF22		OBJECT-TYPE
			SYNTAX	INTEGER
			ACCESS	read-only
			STATUS	current
	DESCRIPTION ""
			::= { mbusBC 74 }

mbusBCValue22		OBJECT-TYPE
			SYNTAX	INTEGER
			ACCESS	read-only
			STATUS	current
	DESCRIPTION ""
			::= { mbusBC 75 }

mbusBCVIF23		OBJECT-TYPE
			SYNTAX	INTEGER
			ACCESS	read-only
			STATUS	current
	DESCRIPTION ""
			::= { mbusBC 76 }

mbusBCValue23		OBJECT-TYPE
			SYNTAX	INTEGER
			ACCESS	read-only
			STATUS	current
	DESCRIPTION ""
			::= { mbusBC 77 }

mbusBCVIF24		OBJECT-TYPE
			SYNTAX	INTEGER
			ACCESS	read-only
			STATUS	current
	DESCRIPTION ""
			::= { mbusBC 78 }

mbusBCValue24		OBJECT-TYPE
			SYNTAX	INTEGER
			ACCESS	read-only
			STATUS	current
	DESCRIPTION ""
			::= { mbusBC 79 }

mbusBCVIF25		OBJECT-TYPE
			SYNTAX	INTEGER
			ACCESS	read-only
			STATUS	current
	DESCRIPTION ""
			::= { mbusBC 80 }

mbusBCValue25		OBJECT-TYPE
			SYNTAX	INTEGER
			ACCESS	read-only
			STATUS	current
	DESCRIPTION ""
			::= { mbusBC 81 }

mbusBCVIF26		OBJECT-TYPE
			SYNTAX	INTEGER
			ACCESS	read-only
			STATUS	current
	DESCRIPTION ""
			::= { mbusBC 82 }

mbusBCValue26		OBJECT-TYPE
			SYNTAX	INTEGER
			ACCESS	read-only
			STATUS	current
	DESCRIPTION ""
			::= { mbusBC 83 }

mbusBCVIF27		OBJECT-TYPE
			SYNTAX	INTEGER
			ACCESS	read-only
			STATUS	current
	DESCRIPTION ""
			::= { mbusBC 84 }

mbusBCValue27		OBJECT-TYPE
			SYNTAX	INTEGER
			ACCESS	read-only
			STATUS	current
	DESCRIPTION ""
			::= { mbusBC 85 }

mbusBCVIF28		OBJECT-TYPE
			SYNTAX	INTEGER
			ACCESS	read-only
			STATUS	current
	DESCRIPTION ""
			::= { mbusBC 86 }

mbusBCValue28		OBJECT-TYPE
			SYNTAX	INTEGER
			ACCESS	read-only
			STATUS	current
	DESCRIPTION ""
			::= { mbusBC 87 }

mbusBCVIF29		OBJECT-TYPE
			SYNTAX	INTEGER
			ACCESS	read-only
			STATUS	current
	DESCRIPTION ""
			::= { mbusBC 88 }

mbusBCValue29		OBJECT-TYPE
			SYNTAX	INTEGER
			ACCESS	read-only
			STATUS	current
	DESCRIPTION ""
			::= { mbusBC 89 }

mbusBCVIF2A		OBJECT-TYPE
			SYNTAX	INTEGER
			ACCESS	read-only
			STATUS	current
	DESCRIPTION ""
			::= { mbusBC 90 }

mbusBCValue2A		OBJECT-TYPE
			SYNTAX	INTEGER
			ACCESS	read-only
			STATUS	current
	DESCRIPTION ""
			::= { mbusBC 91 }

mbusBCVIF2B		OBJECT-TYPE
			SYNTAX	INTEGER
			ACCESS	read-only
			STATUS	current
	DESCRIPTION ""
			::= { mbusBC 92 }

mbusBCValue2B		OBJECT-TYPE
			SYNTAX	INTEGER
			ACCESS	read-only
			STATUS	current
	DESCRIPTION ""
			::= { mbusBC 93 }

mbusBCVIF2C		OBJECT-TYPE
			SYNTAX	INTEGER
			ACCESS	read-only
			STATUS	current
	DESCRIPTION ""
			::= { mbusBC 94 }

mbusBCValue2C		OBJECT-TYPE
			SYNTAX	INTEGER
			ACCESS	read-only
			STATUS	current
	DESCRIPTION ""
			::= { mbusBC 95 }

mbusBCVIF2D		OBJECT-TYPE
			SYNTAX	INTEGER
			ACCESS	read-only
			STATUS	current
	DESCRIPTION ""
			::= { mbusBC 96 }

mbusBCValue2D		OBJECT-TYPE
			SYNTAX	INTEGER
			ACCESS	read-only
			STATUS	current
	DESCRIPTION ""
			::= { mbusBC 97 }

mbusBCVIF2E		OBJECT-TYPE
			SYNTAX	INTEGER
			ACCESS	read-only
			STATUS	current
	DESCRIPTION ""
			::= { mbusBC 98 }

mbusBCValue2E		OBJECT-TYPE
			SYNTAX	INTEGER
			ACCESS	read-only
			STATUS	current
	DESCRIPTION ""
			::= { mbusBC 99 }

mbusBCVIF2F		OBJECT-TYPE
			SYNTAX	INTEGER
			ACCESS	read-only
			STATUS	current
	DESCRIPTION ""
			::= { mbusBC 100 }

mbusBCValue2F		OBJECT-TYPE
			SYNTAX	INTEGER
			ACCESS	read-only
			STATUS	current
	DESCRIPTION ""
			::= { mbusBC 101 }

mbusBD			OBJECT IDENTIFIER ::= { mbus 189 }

mbusBDIdNumber		OBJECT-TYPE
			SYNTAX	Gauge
			ACCESS	read-only
			STATUS	current
	DESCRIPTION ""
			::= { mbusBD 1 }

mbusBDManufacturer	OBJECT-TYPE
			SYNTAX	Gauge
			ACCESS	read-only
			STATUS	current
	DESCRIPTION ""
			::= { mbusBD 2 }

mbusBDVersion		OBJECT-TYPE
			SYNTAX	Gauge
			ACCESS	read-only
			STATUS	current
	DESCRIPTION ""
			::= { mbusBD 3 }

mbusBDMedium		OBJECT-TYPE
			SYNTAX	Gauge
			ACCESS	read-only
			STATUS	current
	DESCRIPTION ""
			::= { mbusBD 4 }

mbusBDStatus		OBJECT-TYPE
			SYNTAX	Gauge
			ACCESS	read-only
			STATUS	current
	DESCRIPTION ""
			::= { mbusBD 5 }

mbusBDVIF00		OBJECT-TYPE
			SYNTAX	INTEGER
			ACCESS	read-only
			STATUS	current
	DESCRIPTION ""
			::= { mbusBD 6 }

mbusBDValue00		OBJECT-TYPE
			SYNTAX	INTEGER
			ACCESS	read-only
			STATUS	current
	DESCRIPTION ""
			::= { mbusBD 7 }

mbusBDVIF01		OBJECT-TYPE
			SYNTAX	INTEGER
			ACCESS	read-only
			STATUS	current
	DESCRIPTION ""
			::= { mbusBD 8 }

mbusBDValue01		OBJECT-TYPE
			SYNTAX	INTEGER
			ACCESS	read-only
			STATUS	current
	DESCRIPTION ""
			::= { mbusBD 9 }

mbusBDVIF02		OBJECT-TYPE
			SYNTAX	INTEGER
			ACCESS	read-only
			STATUS	current
	DESCRIPTION ""
			::= { mbusBD 10 }

mbusBDValue02		OBJECT-TYPE
			SYNTAX	INTEGER
			ACCESS	read-only
			STATUS	current
	DESCRIPTION ""
			::= { mbusBD 11 }

mbusBDVIF03		OBJECT-TYPE
			SYNTAX	INTEGER
			ACCESS	read-only
			STATUS	current
	DESCRIPTION ""
			::= { mbusBD 12 }

mbusBDValue03		OBJECT-TYPE
			SYNTAX	INTEGER
			ACCESS	read-only
			STATUS	current
	DESCRIPTION ""
			::= { mbusBD 13 }

mbusBDVIF04		OBJECT-TYPE
			SYNTAX	INTEGER
			ACCESS	read-only
			STATUS	current
	DESCRIPTION ""
			::= { mbusBD 14 }

mbusBDValue04		OBJECT-TYPE
			SYNTAX	INTEGER
			ACCESS	read-only
			STATUS	current
	DESCRIPTION ""
			::= { mbusBD 15 }

mbusBDVIF05		OBJECT-TYPE
			SYNTAX	INTEGER
			ACCESS	read-only
			STATUS	current
	DESCRIPTION ""
			::= { mbusBD 16 }

mbusBDValue05		OBJECT-TYPE
			SYNTAX	INTEGER
			ACCESS	read-only
			STATUS	current
	DESCRIPTION ""
			::= { mbusBD 17 }

mbusBDVIF06		OBJECT-TYPE
			SYNTAX	INTEGER
			ACCESS	read-only
			STATUS	current
	DESCRIPTION ""
			::= { mbusBD 18 }

mbusBDValue06		OBJECT-TYPE
			SYNTAX	INTEGER
			ACCESS	read-only
			STATUS	current
	DESCRIPTION ""
			::= { mbusBD 19 }

mbusBDVIF07		OBJECT-TYPE
			SYNTAX	INTEGER
			ACCESS	read-only
			STATUS	current
	DESCRIPTION ""
			::= { mbusBD 20 }

mbusBDValue07		OBJECT-TYPE
			SYNTAX	INTEGER
			ACCESS	read-only
			STATUS	current
	DESCRIPTION ""
			::= { mbusBD 21 }

mbusBDVIF08		OBJECT-TYPE
			SYNTAX	INTEGER
			ACCESS	read-only
			STATUS	current
	DESCRIPTION ""
			::= { mbusBD 22 }

mbusBDValue08		OBJECT-TYPE
			SYNTAX	INTEGER
			ACCESS	read-only
			STATUS	current
	DESCRIPTION ""
			::= { mbusBD 23 }

mbusBDVIF09		OBJECT-TYPE
			SYNTAX	INTEGER
			ACCESS	read-only
			STATUS	current
	DESCRIPTION ""
			::= { mbusBD 24 }

mbusBDValue09		OBJECT-TYPE
			SYNTAX	INTEGER
			ACCESS	read-only
			STATUS	current
	DESCRIPTION ""
			::= { mbusBD 25 }

mbusBDVIF0A		OBJECT-TYPE
			SYNTAX	INTEGER
			ACCESS	read-only
			STATUS	current
	DESCRIPTION ""
			::= { mbusBD 26 }

mbusBDValue0A		OBJECT-TYPE
			SYNTAX	INTEGER
			ACCESS	read-only
			STATUS	current
	DESCRIPTION ""
			::= { mbusBD 27 }

mbusBDVIF0B		OBJECT-TYPE
			SYNTAX	INTEGER
			ACCESS	read-only
			STATUS	current
	DESCRIPTION ""
			::= { mbusBD 28 }

mbusBDValue0B		OBJECT-TYPE
			SYNTAX	INTEGER
			ACCESS	read-only
			STATUS	current
	DESCRIPTION ""
			::= { mbusBD 29 }

mbusBDVIF0C		OBJECT-TYPE
			SYNTAX	INTEGER
			ACCESS	read-only
			STATUS	current
	DESCRIPTION ""
			::= { mbusBD 30 }

mbusBDValue0C		OBJECT-TYPE
			SYNTAX	INTEGER
			ACCESS	read-only
			STATUS	current
	DESCRIPTION ""
			::= { mbusBD 31 }

mbusBDVIF0D		OBJECT-TYPE
			SYNTAX	INTEGER
			ACCESS	read-only
			STATUS	current
	DESCRIPTION ""
			::= { mbusBD 32 }

mbusBDValue0D		OBJECT-TYPE
			SYNTAX	INTEGER
			ACCESS	read-only
			STATUS	current
	DESCRIPTION ""
			::= { mbusBD 33 }

mbusBDVIF0E		OBJECT-TYPE
			SYNTAX	INTEGER
			ACCESS	read-only
			STATUS	current
	DESCRIPTION ""
			::= { mbusBD 34 }

mbusBDValue0E		OBJECT-TYPE
			SYNTAX	INTEGER
			ACCESS	read-only
			STATUS	current
	DESCRIPTION ""
			::= { mbusBD 35 }

mbusBDVIF0F		OBJECT-TYPE
			SYNTAX	INTEGER
			ACCESS	read-only
			STATUS	current
	DESCRIPTION ""
			::= { mbusBD 36 }

mbusBDValue0F		OBJECT-TYPE
			SYNTAX	INTEGER
			ACCESS	read-only
			STATUS	current
	DESCRIPTION ""
			::= { mbusBD 37 }

mbusBDVIF10		OBJECT-TYPE
			SYNTAX	INTEGER
			ACCESS	read-only
			STATUS	current
	DESCRIPTION ""
			::= { mbusBD 38 }

mbusBDValue10		OBJECT-TYPE
			SYNTAX	INTEGER
			ACCESS	read-only
			STATUS	current
	DESCRIPTION ""
			::= { mbusBD 39 }

mbusBDVIF11		OBJECT-TYPE
			SYNTAX	INTEGER
			ACCESS	read-only
			STATUS	current
	DESCRIPTION ""
			::= { mbusBD 40 }

mbusBDValue11		OBJECT-TYPE
			SYNTAX	INTEGER
			ACCESS	read-only
			STATUS	current
	DESCRIPTION ""
			::= { mbusBD 41 }

mbusBDVIF12		OBJECT-TYPE
			SYNTAX	INTEGER
			ACCESS	read-only
			STATUS	current
	DESCRIPTION ""
			::= { mbusBD 42 }

mbusBDValue12		OBJECT-TYPE
			SYNTAX	INTEGER
			ACCESS	read-only
			STATUS	current
	DESCRIPTION ""
			::= { mbusBD 43 }

mbusBDVIF13		OBJECT-TYPE
			SYNTAX	INTEGER
			ACCESS	read-only
			STATUS	current
	DESCRIPTION ""
			::= { mbusBD 44 }

mbusBDValue13		OBJECT-TYPE
			SYNTAX	INTEGER
			ACCESS	read-only
			STATUS	current
	DESCRIPTION ""
			::= { mbusBD 45 }

mbusBDVIF14		OBJECT-TYPE
			SYNTAX	INTEGER
			ACCESS	read-only
			STATUS	current
	DESCRIPTION ""
			::= { mbusBD 46 }

mbusBDValue14		OBJECT-TYPE
			SYNTAX	INTEGER
			ACCESS	read-only
			STATUS	current
	DESCRIPTION ""
			::= { mbusBD 47 }

mbusBDVIF15		OBJECT-TYPE
			SYNTAX	INTEGER
			ACCESS	read-only
			STATUS	current
	DESCRIPTION ""
			::= { mbusBD 48 }

mbusBDValue15		OBJECT-TYPE
			SYNTAX	INTEGER
			ACCESS	read-only
			STATUS	current
	DESCRIPTION ""
			::= { mbusBD 49 }

mbusBDVIF16		OBJECT-TYPE
			SYNTAX	INTEGER
			ACCESS	read-only
			STATUS	current
	DESCRIPTION ""
			::= { mbusBD 50 }

mbusBDValue16		OBJECT-TYPE
			SYNTAX	INTEGER
			ACCESS	read-only
			STATUS	current
	DESCRIPTION ""
			::= { mbusBD 51 }

mbusBDVIF17		OBJECT-TYPE
			SYNTAX	INTEGER
			ACCESS	read-only
			STATUS	current
	DESCRIPTION ""
			::= { mbusBD 52 }

mbusBDValue17		OBJECT-TYPE
			SYNTAX	INTEGER
			ACCESS	read-only
			STATUS	current
	DESCRIPTION ""
			::= { mbusBD 53 }

mbusBDVIF18		OBJECT-TYPE
			SYNTAX	INTEGER
			ACCESS	read-only
			STATUS	current
	DESCRIPTION ""
			::= { mbusBD 54 }

mbusBDValue18		OBJECT-TYPE
			SYNTAX	INTEGER
			ACCESS	read-only
			STATUS	current
	DESCRIPTION ""
			::= { mbusBD 55 }

mbusBDVIF19		OBJECT-TYPE
			SYNTAX	INTEGER
			ACCESS	read-only
			STATUS	current
	DESCRIPTION ""
			::= { mbusBD 56 }

mbusBDValue19		OBJECT-TYPE
			SYNTAX	INTEGER
			ACCESS	read-only
			STATUS	current
	DESCRIPTION ""
			::= { mbusBD 57 }

mbusBDVIF1A		OBJECT-TYPE
			SYNTAX	INTEGER
			ACCESS	read-only
			STATUS	current
	DESCRIPTION ""
			::= { mbusBD 58 }

mbusBDValue1A		OBJECT-TYPE
			SYNTAX	INTEGER
			ACCESS	read-only
			STATUS	current
	DESCRIPTION ""
			::= { mbusBD 59 }

mbusBDVIF1B		OBJECT-TYPE
			SYNTAX	INTEGER
			ACCESS	read-only
			STATUS	current
	DESCRIPTION ""
			::= { mbusBD 60 }

mbusBDValue1B		OBJECT-TYPE
			SYNTAX	INTEGER
			ACCESS	read-only
			STATUS	current
	DESCRIPTION ""
			::= { mbusBD 61 }

mbusBDVIF1C		OBJECT-TYPE
			SYNTAX	INTEGER
			ACCESS	read-only
			STATUS	current
	DESCRIPTION ""
			::= { mbusBD 62 }

mbusBDValue1C		OBJECT-TYPE
			SYNTAX	INTEGER
			ACCESS	read-only
			STATUS	current
	DESCRIPTION ""
			::= { mbusBD 63 }

mbusBDVIF1D		OBJECT-TYPE
			SYNTAX	INTEGER
			ACCESS	read-only
			STATUS	current
	DESCRIPTION ""
			::= { mbusBD 64 }

mbusBDValue1D		OBJECT-TYPE
			SYNTAX	INTEGER
			ACCESS	read-only
			STATUS	current
	DESCRIPTION ""
			::= { mbusBD 65 }

mbusBDVIF1E		OBJECT-TYPE
			SYNTAX	INTEGER
			ACCESS	read-only
			STATUS	current
	DESCRIPTION ""
			::= { mbusBD 66 }

mbusBDValue1E		OBJECT-TYPE
			SYNTAX	INTEGER
			ACCESS	read-only
			STATUS	current
	DESCRIPTION ""
			::= { mbusBD 67 }

mbusBDVIF1F		OBJECT-TYPE
			SYNTAX	INTEGER
			ACCESS	read-only
			STATUS	current
	DESCRIPTION ""
			::= { mbusBD 68 }

mbusBDValue1F		OBJECT-TYPE
			SYNTAX	INTEGER
			ACCESS	read-only
			STATUS	current
	DESCRIPTION ""
			::= { mbusBD 69 }

mbusBDVIF20		OBJECT-TYPE
			SYNTAX	INTEGER
			ACCESS	read-only
			STATUS	current
	DESCRIPTION ""
			::= { mbusBD 70 }

mbusBDValue20		OBJECT-TYPE
			SYNTAX	INTEGER
			ACCESS	read-only
			STATUS	current
	DESCRIPTION ""
			::= { mbusBD 71 }

mbusBDVIF21		OBJECT-TYPE
			SYNTAX	INTEGER
			ACCESS	read-only
			STATUS	current
	DESCRIPTION ""
			::= { mbusBD 72 }

mbusBDValue21		OBJECT-TYPE
			SYNTAX	INTEGER
			ACCESS	read-only
			STATUS	current
	DESCRIPTION ""
			::= { mbusBD 73 }

mbusBDVIF22		OBJECT-TYPE
			SYNTAX	INTEGER
			ACCESS	read-only
			STATUS	current
	DESCRIPTION ""
			::= { mbusBD 74 }

mbusBDValue22		OBJECT-TYPE
			SYNTAX	INTEGER
			ACCESS	read-only
			STATUS	current
	DESCRIPTION ""
			::= { mbusBD 75 }

mbusBDVIF23		OBJECT-TYPE
			SYNTAX	INTEGER
			ACCESS	read-only
			STATUS	current
	DESCRIPTION ""
			::= { mbusBD 76 }

mbusBDValue23		OBJECT-TYPE
			SYNTAX	INTEGER
			ACCESS	read-only
			STATUS	current
	DESCRIPTION ""
			::= { mbusBD 77 }

mbusBDVIF24		OBJECT-TYPE
			SYNTAX	INTEGER
			ACCESS	read-only
			STATUS	current
	DESCRIPTION ""
			::= { mbusBD 78 }

mbusBDValue24		OBJECT-TYPE
			SYNTAX	INTEGER
			ACCESS	read-only
			STATUS	current
	DESCRIPTION ""
			::= { mbusBD 79 }

mbusBDVIF25		OBJECT-TYPE
			SYNTAX	INTEGER
			ACCESS	read-only
			STATUS	current
	DESCRIPTION ""
			::= { mbusBD 80 }

mbusBDValue25		OBJECT-TYPE
			SYNTAX	INTEGER
			ACCESS	read-only
			STATUS	current
	DESCRIPTION ""
			::= { mbusBD 81 }

mbusBDVIF26		OBJECT-TYPE
			SYNTAX	INTEGER
			ACCESS	read-only
			STATUS	current
	DESCRIPTION ""
			::= { mbusBD 82 }

mbusBDValue26		OBJECT-TYPE
			SYNTAX	INTEGER
			ACCESS	read-only
			STATUS	current
	DESCRIPTION ""
			::= { mbusBD 83 }

mbusBDVIF27		OBJECT-TYPE
			SYNTAX	INTEGER
			ACCESS	read-only
			STATUS	current
	DESCRIPTION ""
			::= { mbusBD 84 }

mbusBDValue27		OBJECT-TYPE
			SYNTAX	INTEGER
			ACCESS	read-only
			STATUS	current
	DESCRIPTION ""
			::= { mbusBD 85 }

mbusBDVIF28		OBJECT-TYPE
			SYNTAX	INTEGER
			ACCESS	read-only
			STATUS	current
	DESCRIPTION ""
			::= { mbusBD 86 }

mbusBDValue28		OBJECT-TYPE
			SYNTAX	INTEGER
			ACCESS	read-only
			STATUS	current
	DESCRIPTION ""
			::= { mbusBD 87 }

mbusBDVIF29		OBJECT-TYPE
			SYNTAX	INTEGER
			ACCESS	read-only
			STATUS	current
	DESCRIPTION ""
			::= { mbusBD 88 }

mbusBDValue29		OBJECT-TYPE
			SYNTAX	INTEGER
			ACCESS	read-only
			STATUS	current
	DESCRIPTION ""
			::= { mbusBD 89 }

mbusBDVIF2A		OBJECT-TYPE
			SYNTAX	INTEGER
			ACCESS	read-only
			STATUS	current
	DESCRIPTION ""
			::= { mbusBD 90 }

mbusBDValue2A		OBJECT-TYPE
			SYNTAX	INTEGER
			ACCESS	read-only
			STATUS	current
	DESCRIPTION ""
			::= { mbusBD 91 }

mbusBDVIF2B		OBJECT-TYPE
			SYNTAX	INTEGER
			ACCESS	read-only
			STATUS	current
	DESCRIPTION ""
			::= { mbusBD 92 }

mbusBDValue2B		OBJECT-TYPE
			SYNTAX	INTEGER
			ACCESS	read-only
			STATUS	current
	DESCRIPTION ""
			::= { mbusBD 93 }

mbusBDVIF2C		OBJECT-TYPE
			SYNTAX	INTEGER
			ACCESS	read-only
			STATUS	current
	DESCRIPTION ""
			::= { mbusBD 94 }

mbusBDValue2C		OBJECT-TYPE
			SYNTAX	INTEGER
			ACCESS	read-only
			STATUS	current
	DESCRIPTION ""
			::= { mbusBD 95 }

mbusBDVIF2D		OBJECT-TYPE
			SYNTAX	INTEGER
			ACCESS	read-only
			STATUS	current
	DESCRIPTION ""
			::= { mbusBD 96 }

mbusBDValue2D		OBJECT-TYPE
			SYNTAX	INTEGER
			ACCESS	read-only
			STATUS	current
	DESCRIPTION ""
			::= { mbusBD 97 }

mbusBDVIF2E		OBJECT-TYPE
			SYNTAX	INTEGER
			ACCESS	read-only
			STATUS	current
	DESCRIPTION ""
			::= { mbusBD 98 }

mbusBDValue2E		OBJECT-TYPE
			SYNTAX	INTEGER
			ACCESS	read-only
			STATUS	current
	DESCRIPTION ""
			::= { mbusBD 99 }

mbusBDVIF2F		OBJECT-TYPE
			SYNTAX	INTEGER
			ACCESS	read-only
			STATUS	current
	DESCRIPTION ""
			::= { mbusBD 100 }

mbusBDValue2F		OBJECT-TYPE
			SYNTAX	INTEGER
			ACCESS	read-only
			STATUS	current
	DESCRIPTION ""
			::= { mbusBD 101 }

mbusBE			OBJECT IDENTIFIER ::= { mbus 190 }

mbusBEIdNumber		OBJECT-TYPE
			SYNTAX	Gauge
			ACCESS	read-only
			STATUS	current
	DESCRIPTION ""
			::= { mbusBE 1 }

mbusBEManufacturer	OBJECT-TYPE
			SYNTAX	Gauge
			ACCESS	read-only
			STATUS	current
	DESCRIPTION ""
			::= { mbusBE 2 }

mbusBEVersion		OBJECT-TYPE
			SYNTAX	Gauge
			ACCESS	read-only
			STATUS	current
	DESCRIPTION ""
			::= { mbusBE 3 }

mbusBEMedium		OBJECT-TYPE
			SYNTAX	Gauge
			ACCESS	read-only
			STATUS	current
	DESCRIPTION ""
			::= { mbusBE 4 }

mbusBEStatus		OBJECT-TYPE
			SYNTAX	Gauge
			ACCESS	read-only
			STATUS	current
	DESCRIPTION ""
			::= { mbusBE 5 }

mbusBEVIF00		OBJECT-TYPE
			SYNTAX	INTEGER
			ACCESS	read-only
			STATUS	current
	DESCRIPTION ""
			::= { mbusBE 6 }

mbusBEValue00		OBJECT-TYPE
			SYNTAX	INTEGER
			ACCESS	read-only
			STATUS	current
	DESCRIPTION ""
			::= { mbusBE 7 }

mbusBEVIF01		OBJECT-TYPE
			SYNTAX	INTEGER
			ACCESS	read-only
			STATUS	current
	DESCRIPTION ""
			::= { mbusBE 8 }

mbusBEValue01		OBJECT-TYPE
			SYNTAX	INTEGER
			ACCESS	read-only
			STATUS	current
	DESCRIPTION ""
			::= { mbusBE 9 }

mbusBEVIF02		OBJECT-TYPE
			SYNTAX	INTEGER
			ACCESS	read-only
			STATUS	current
	DESCRIPTION ""
			::= { mbusBE 10 }

mbusBEValue02		OBJECT-TYPE
			SYNTAX	INTEGER
			ACCESS	read-only
			STATUS	current
	DESCRIPTION ""
			::= { mbusBE 11 }

mbusBEVIF03		OBJECT-TYPE
			SYNTAX	INTEGER
			ACCESS	read-only
			STATUS	current
	DESCRIPTION ""
			::= { mbusBE 12 }

mbusBEValue03		OBJECT-TYPE
			SYNTAX	INTEGER
			ACCESS	read-only
			STATUS	current
	DESCRIPTION ""
			::= { mbusBE 13 }

mbusBEVIF04		OBJECT-TYPE
			SYNTAX	INTEGER
			ACCESS	read-only
			STATUS	current
	DESCRIPTION ""
			::= { mbusBE 14 }

mbusBEValue04		OBJECT-TYPE
			SYNTAX	INTEGER
			ACCESS	read-only
			STATUS	current
	DESCRIPTION ""
			::= { mbusBE 15 }

mbusBEVIF05		OBJECT-TYPE
			SYNTAX	INTEGER
			ACCESS	read-only
			STATUS	current
	DESCRIPTION ""
			::= { mbusBE 16 }

mbusBEValue05		OBJECT-TYPE
			SYNTAX	INTEGER
			ACCESS	read-only
			STATUS	current
	DESCRIPTION ""
			::= { mbusBE 17 }

mbusBEVIF06		OBJECT-TYPE
			SYNTAX	INTEGER
			ACCESS	read-only
			STATUS	current
	DESCRIPTION ""
			::= { mbusBE 18 }

mbusBEValue06		OBJECT-TYPE
			SYNTAX	INTEGER
			ACCESS	read-only
			STATUS	current
	DESCRIPTION ""
			::= { mbusBE 19 }

mbusBEVIF07		OBJECT-TYPE
			SYNTAX	INTEGER
			ACCESS	read-only
			STATUS	current
	DESCRIPTION ""
			::= { mbusBE 20 }

mbusBEValue07		OBJECT-TYPE
			SYNTAX	INTEGER
			ACCESS	read-only
			STATUS	current
	DESCRIPTION ""
			::= { mbusBE 21 }

mbusBEVIF08		OBJECT-TYPE
			SYNTAX	INTEGER
			ACCESS	read-only
			STATUS	current
	DESCRIPTION ""
			::= { mbusBE 22 }

mbusBEValue08		OBJECT-TYPE
			SYNTAX	INTEGER
			ACCESS	read-only
			STATUS	current
	DESCRIPTION ""
			::= { mbusBE 23 }

mbusBEVIF09		OBJECT-TYPE
			SYNTAX	INTEGER
			ACCESS	read-only
			STATUS	current
	DESCRIPTION ""
			::= { mbusBE 24 }

mbusBEValue09		OBJECT-TYPE
			SYNTAX	INTEGER
			ACCESS	read-only
			STATUS	current
	DESCRIPTION ""
			::= { mbusBE 25 }

mbusBEVIF0A		OBJECT-TYPE
			SYNTAX	INTEGER
			ACCESS	read-only
			STATUS	current
	DESCRIPTION ""
			::= { mbusBE 26 }

mbusBEValue0A		OBJECT-TYPE
			SYNTAX	INTEGER
			ACCESS	read-only
			STATUS	current
	DESCRIPTION ""
			::= { mbusBE 27 }

mbusBEVIF0B		OBJECT-TYPE
			SYNTAX	INTEGER
			ACCESS	read-only
			STATUS	current
	DESCRIPTION ""
			::= { mbusBE 28 }

mbusBEValue0B		OBJECT-TYPE
			SYNTAX	INTEGER
			ACCESS	read-only
			STATUS	current
	DESCRIPTION ""
			::= { mbusBE 29 }

mbusBEVIF0C		OBJECT-TYPE
			SYNTAX	INTEGER
			ACCESS	read-only
			STATUS	current
	DESCRIPTION ""
			::= { mbusBE 30 }

mbusBEValue0C		OBJECT-TYPE
			SYNTAX	INTEGER
			ACCESS	read-only
			STATUS	current
	DESCRIPTION ""
			::= { mbusBE 31 }

mbusBEVIF0D		OBJECT-TYPE
			SYNTAX	INTEGER
			ACCESS	read-only
			STATUS	current
	DESCRIPTION ""
			::= { mbusBE 32 }

mbusBEValue0D		OBJECT-TYPE
			SYNTAX	INTEGER
			ACCESS	read-only
			STATUS	current
	DESCRIPTION ""
			::= { mbusBE 33 }

mbusBEVIF0E		OBJECT-TYPE
			SYNTAX	INTEGER
			ACCESS	read-only
			STATUS	current
	DESCRIPTION ""
			::= { mbusBE 34 }

mbusBEValue0E		OBJECT-TYPE
			SYNTAX	INTEGER
			ACCESS	read-only
			STATUS	current
	DESCRIPTION ""
			::= { mbusBE 35 }

mbusBEVIF0F		OBJECT-TYPE
			SYNTAX	INTEGER
			ACCESS	read-only
			STATUS	current
	DESCRIPTION ""
			::= { mbusBE 36 }

mbusBEValue0F		OBJECT-TYPE
			SYNTAX	INTEGER
			ACCESS	read-only
			STATUS	current
	DESCRIPTION ""
			::= { mbusBE 37 }

mbusBEVIF10		OBJECT-TYPE
			SYNTAX	INTEGER
			ACCESS	read-only
			STATUS	current
	DESCRIPTION ""
			::= { mbusBE 38 }

mbusBEValue10		OBJECT-TYPE
			SYNTAX	INTEGER
			ACCESS	read-only
			STATUS	current
	DESCRIPTION ""
			::= { mbusBE 39 }

mbusBEVIF11		OBJECT-TYPE
			SYNTAX	INTEGER
			ACCESS	read-only
			STATUS	current
	DESCRIPTION ""
			::= { mbusBE 40 }

mbusBEValue11		OBJECT-TYPE
			SYNTAX	INTEGER
			ACCESS	read-only
			STATUS	current
	DESCRIPTION ""
			::= { mbusBE 41 }

mbusBEVIF12		OBJECT-TYPE
			SYNTAX	INTEGER
			ACCESS	read-only
			STATUS	current
	DESCRIPTION ""
			::= { mbusBE 42 }

mbusBEValue12		OBJECT-TYPE
			SYNTAX	INTEGER
			ACCESS	read-only
			STATUS	current
	DESCRIPTION ""
			::= { mbusBE 43 }

mbusBEVIF13		OBJECT-TYPE
			SYNTAX	INTEGER
			ACCESS	read-only
			STATUS	current
	DESCRIPTION ""
			::= { mbusBE 44 }

mbusBEValue13		OBJECT-TYPE
			SYNTAX	INTEGER
			ACCESS	read-only
			STATUS	current
	DESCRIPTION ""
			::= { mbusBE 45 }

mbusBEVIF14		OBJECT-TYPE
			SYNTAX	INTEGER
			ACCESS	read-only
			STATUS	current
	DESCRIPTION ""
			::= { mbusBE 46 }

mbusBEValue14		OBJECT-TYPE
			SYNTAX	INTEGER
			ACCESS	read-only
			STATUS	current
	DESCRIPTION ""
			::= { mbusBE 47 }

mbusBEVIF15		OBJECT-TYPE
			SYNTAX	INTEGER
			ACCESS	read-only
			STATUS	current
	DESCRIPTION ""
			::= { mbusBE 48 }

mbusBEValue15		OBJECT-TYPE
			SYNTAX	INTEGER
			ACCESS	read-only
			STATUS	current
	DESCRIPTION ""
			::= { mbusBE 49 }

mbusBEVIF16		OBJECT-TYPE
			SYNTAX	INTEGER
			ACCESS	read-only
			STATUS	current
	DESCRIPTION ""
			::= { mbusBE 50 }

mbusBEValue16		OBJECT-TYPE
			SYNTAX	INTEGER
			ACCESS	read-only
			STATUS	current
	DESCRIPTION ""
			::= { mbusBE 51 }

mbusBEVIF17		OBJECT-TYPE
			SYNTAX	INTEGER
			ACCESS	read-only
			STATUS	current
	DESCRIPTION ""
			::= { mbusBE 52 }

mbusBEValue17		OBJECT-TYPE
			SYNTAX	INTEGER
			ACCESS	read-only
			STATUS	current
	DESCRIPTION ""
			::= { mbusBE 53 }

mbusBEVIF18		OBJECT-TYPE
			SYNTAX	INTEGER
			ACCESS	read-only
			STATUS	current
	DESCRIPTION ""
			::= { mbusBE 54 }

mbusBEValue18		OBJECT-TYPE
			SYNTAX	INTEGER
			ACCESS	read-only
			STATUS	current
	DESCRIPTION ""
			::= { mbusBE 55 }

mbusBEVIF19		OBJECT-TYPE
			SYNTAX	INTEGER
			ACCESS	read-only
			STATUS	current
	DESCRIPTION ""
			::= { mbusBE 56 }

mbusBEValue19		OBJECT-TYPE
			SYNTAX	INTEGER
			ACCESS	read-only
			STATUS	current
	DESCRIPTION ""
			::= { mbusBE 57 }

mbusBEVIF1A		OBJECT-TYPE
			SYNTAX	INTEGER
			ACCESS	read-only
			STATUS	current
	DESCRIPTION ""
			::= { mbusBE 58 }

mbusBEValue1A		OBJECT-TYPE
			SYNTAX	INTEGER
			ACCESS	read-only
			STATUS	current
	DESCRIPTION ""
			::= { mbusBE 59 }

mbusBEVIF1B		OBJECT-TYPE
			SYNTAX	INTEGER
			ACCESS	read-only
			STATUS	current
	DESCRIPTION ""
			::= { mbusBE 60 }

mbusBEValue1B		OBJECT-TYPE
			SYNTAX	INTEGER
			ACCESS	read-only
			STATUS	current
	DESCRIPTION ""
			::= { mbusBE 61 }

mbusBEVIF1C		OBJECT-TYPE
			SYNTAX	INTEGER
			ACCESS	read-only
			STATUS	current
	DESCRIPTION ""
			::= { mbusBE 62 }

mbusBEValue1C		OBJECT-TYPE
			SYNTAX	INTEGER
			ACCESS	read-only
			STATUS	current
	DESCRIPTION ""
			::= { mbusBE 63 }

mbusBEVIF1D		OBJECT-TYPE
			SYNTAX	INTEGER
			ACCESS	read-only
			STATUS	current
	DESCRIPTION ""
			::= { mbusBE 64 }

mbusBEValue1D		OBJECT-TYPE
			SYNTAX	INTEGER
			ACCESS	read-only
			STATUS	current
	DESCRIPTION ""
			::= { mbusBE 65 }

mbusBEVIF1E		OBJECT-TYPE
			SYNTAX	INTEGER
			ACCESS	read-only
			STATUS	current
	DESCRIPTION ""
			::= { mbusBE 66 }

mbusBEValue1E		OBJECT-TYPE
			SYNTAX	INTEGER
			ACCESS	read-only
			STATUS	current
	DESCRIPTION ""
			::= { mbusBE 67 }

mbusBEVIF1F		OBJECT-TYPE
			SYNTAX	INTEGER
			ACCESS	read-only
			STATUS	current
	DESCRIPTION ""
			::= { mbusBE 68 }

mbusBEValue1F		OBJECT-TYPE
			SYNTAX	INTEGER
			ACCESS	read-only
			STATUS	current
	DESCRIPTION ""
			::= { mbusBE 69 }

mbusBEVIF20		OBJECT-TYPE
			SYNTAX	INTEGER
			ACCESS	read-only
			STATUS	current
	DESCRIPTION ""
			::= { mbusBE 70 }

mbusBEValue20		OBJECT-TYPE
			SYNTAX	INTEGER
			ACCESS	read-only
			STATUS	current
	DESCRIPTION ""
			::= { mbusBE 71 }

mbusBEVIF21		OBJECT-TYPE
			SYNTAX	INTEGER
			ACCESS	read-only
			STATUS	current
	DESCRIPTION ""
			::= { mbusBE 72 }

mbusBEValue21		OBJECT-TYPE
			SYNTAX	INTEGER
			ACCESS	read-only
			STATUS	current
	DESCRIPTION ""
			::= { mbusBE 73 }

mbusBEVIF22		OBJECT-TYPE
			SYNTAX	INTEGER
			ACCESS	read-only
			STATUS	current
	DESCRIPTION ""
			::= { mbusBE 74 }

mbusBEValue22		OBJECT-TYPE
			SYNTAX	INTEGER
			ACCESS	read-only
			STATUS	current
	DESCRIPTION ""
			::= { mbusBE 75 }

mbusBEVIF23		OBJECT-TYPE
			SYNTAX	INTEGER
			ACCESS	read-only
			STATUS	current
	DESCRIPTION ""
			::= { mbusBE 76 }

mbusBEValue23		OBJECT-TYPE
			SYNTAX	INTEGER
			ACCESS	read-only
			STATUS	current
	DESCRIPTION ""
			::= { mbusBE 77 }

mbusBEVIF24		OBJECT-TYPE
			SYNTAX	INTEGER
			ACCESS	read-only
			STATUS	current
	DESCRIPTION ""
			::= { mbusBE 78 }

mbusBEValue24		OBJECT-TYPE
			SYNTAX	INTEGER
			ACCESS	read-only
			STATUS	current
	DESCRIPTION ""
			::= { mbusBE 79 }

mbusBEVIF25		OBJECT-TYPE
			SYNTAX	INTEGER
			ACCESS	read-only
			STATUS	current
	DESCRIPTION ""
			::= { mbusBE 80 }

mbusBEValue25		OBJECT-TYPE
			SYNTAX	INTEGER
			ACCESS	read-only
			STATUS	current
	DESCRIPTION ""
			::= { mbusBE 81 }

mbusBEVIF26		OBJECT-TYPE
			SYNTAX	INTEGER
			ACCESS	read-only
			STATUS	current
	DESCRIPTION ""
			::= { mbusBE 82 }

mbusBEValue26		OBJECT-TYPE
			SYNTAX	INTEGER
			ACCESS	read-only
			STATUS	current
	DESCRIPTION ""
			::= { mbusBE 83 }

mbusBEVIF27		OBJECT-TYPE
			SYNTAX	INTEGER
			ACCESS	read-only
			STATUS	current
	DESCRIPTION ""
			::= { mbusBE 84 }

mbusBEValue27		OBJECT-TYPE
			SYNTAX	INTEGER
			ACCESS	read-only
			STATUS	current
	DESCRIPTION ""
			::= { mbusBE 85 }

mbusBEVIF28		OBJECT-TYPE
			SYNTAX	INTEGER
			ACCESS	read-only
			STATUS	current
	DESCRIPTION ""
			::= { mbusBE 86 }

mbusBEValue28		OBJECT-TYPE
			SYNTAX	INTEGER
			ACCESS	read-only
			STATUS	current
	DESCRIPTION ""
			::= { mbusBE 87 }

mbusBEVIF29		OBJECT-TYPE
			SYNTAX	INTEGER
			ACCESS	read-only
			STATUS	current
	DESCRIPTION ""
			::= { mbusBE 88 }

mbusBEValue29		OBJECT-TYPE
			SYNTAX	INTEGER
			ACCESS	read-only
			STATUS	current
	DESCRIPTION ""
			::= { mbusBE 89 }

mbusBEVIF2A		OBJECT-TYPE
			SYNTAX	INTEGER
			ACCESS	read-only
			STATUS	current
	DESCRIPTION ""
			::= { mbusBE 90 }

mbusBEValue2A		OBJECT-TYPE
			SYNTAX	INTEGER
			ACCESS	read-only
			STATUS	current
	DESCRIPTION ""
			::= { mbusBE 91 }

mbusBEVIF2B		OBJECT-TYPE
			SYNTAX	INTEGER
			ACCESS	read-only
			STATUS	current
	DESCRIPTION ""
			::= { mbusBE 92 }

mbusBEValue2B		OBJECT-TYPE
			SYNTAX	INTEGER
			ACCESS	read-only
			STATUS	current
	DESCRIPTION ""
			::= { mbusBE 93 }

mbusBEVIF2C		OBJECT-TYPE
			SYNTAX	INTEGER
			ACCESS	read-only
			STATUS	current
	DESCRIPTION ""
			::= { mbusBE 94 }

mbusBEValue2C		OBJECT-TYPE
			SYNTAX	INTEGER
			ACCESS	read-only
			STATUS	current
	DESCRIPTION ""
			::= { mbusBE 95 }

mbusBEVIF2D		OBJECT-TYPE
			SYNTAX	INTEGER
			ACCESS	read-only
			STATUS	current
	DESCRIPTION ""
			::= { mbusBE 96 }

mbusBEValue2D		OBJECT-TYPE
			SYNTAX	INTEGER
			ACCESS	read-only
			STATUS	current
	DESCRIPTION ""
			::= { mbusBE 97 }

mbusBEVIF2E		OBJECT-TYPE
			SYNTAX	INTEGER
			ACCESS	read-only
			STATUS	current
	DESCRIPTION ""
			::= { mbusBE 98 }

mbusBEValue2E		OBJECT-TYPE
			SYNTAX	INTEGER
			ACCESS	read-only
			STATUS	current
	DESCRIPTION ""
			::= { mbusBE 99 }

mbusBEVIF2F		OBJECT-TYPE
			SYNTAX	INTEGER
			ACCESS	read-only
			STATUS	current
	DESCRIPTION ""
			::= { mbusBE 100 }

mbusBEValue2F		OBJECT-TYPE
			SYNTAX	INTEGER
			ACCESS	read-only
			STATUS	current
	DESCRIPTION ""
			::= { mbusBE 101 }

mbusBF			OBJECT IDENTIFIER ::= { mbus 191 }

mbusBFIdNumber		OBJECT-TYPE
			SYNTAX	Gauge
			ACCESS	read-only
			STATUS	current
	DESCRIPTION ""
			::= { mbusBF 1 }

mbusBFManufacturer	OBJECT-TYPE
			SYNTAX	Gauge
			ACCESS	read-only
			STATUS	current
	DESCRIPTION ""
			::= { mbusBF 2 }

mbusBFVersion		OBJECT-TYPE
			SYNTAX	Gauge
			ACCESS	read-only
			STATUS	current
	DESCRIPTION ""
			::= { mbusBF 3 }

mbusBFMedium		OBJECT-TYPE
			SYNTAX	Gauge
			ACCESS	read-only
			STATUS	current
	DESCRIPTION ""
			::= { mbusBF 4 }

mbusBFStatus		OBJECT-TYPE
			SYNTAX	Gauge
			ACCESS	read-only
			STATUS	current
	DESCRIPTION ""
			::= { mbusBF 5 }

mbusBFVIF00		OBJECT-TYPE
			SYNTAX	INTEGER
			ACCESS	read-only
			STATUS	current
	DESCRIPTION ""
			::= { mbusBF 6 }

mbusBFValue00		OBJECT-TYPE
			SYNTAX	INTEGER
			ACCESS	read-only
			STATUS	current
	DESCRIPTION ""
			::= { mbusBF 7 }

mbusBFVIF01		OBJECT-TYPE
			SYNTAX	INTEGER
			ACCESS	read-only
			STATUS	current
	DESCRIPTION ""
			::= { mbusBF 8 }

mbusBFValue01		OBJECT-TYPE
			SYNTAX	INTEGER
			ACCESS	read-only
			STATUS	current
	DESCRIPTION ""
			::= { mbusBF 9 }

mbusBFVIF02		OBJECT-TYPE
			SYNTAX	INTEGER
			ACCESS	read-only
			STATUS	current
	DESCRIPTION ""
			::= { mbusBF 10 }

mbusBFValue02		OBJECT-TYPE
			SYNTAX	INTEGER
			ACCESS	read-only
			STATUS	current
	DESCRIPTION ""
			::= { mbusBF 11 }

mbusBFVIF03		OBJECT-TYPE
			SYNTAX	INTEGER
			ACCESS	read-only
			STATUS	current
	DESCRIPTION ""
			::= { mbusBF 12 }

mbusBFValue03		OBJECT-TYPE
			SYNTAX	INTEGER
			ACCESS	read-only
			STATUS	current
	DESCRIPTION ""
			::= { mbusBF 13 }

mbusBFVIF04		OBJECT-TYPE
			SYNTAX	INTEGER
			ACCESS	read-only
			STATUS	current
	DESCRIPTION ""
			::= { mbusBF 14 }

mbusBFValue04		OBJECT-TYPE
			SYNTAX	INTEGER
			ACCESS	read-only
			STATUS	current
	DESCRIPTION ""
			::= { mbusBF 15 }

mbusBFVIF05		OBJECT-TYPE
			SYNTAX	INTEGER
			ACCESS	read-only
			STATUS	current
	DESCRIPTION ""
			::= { mbusBF 16 }

mbusBFValue05		OBJECT-TYPE
			SYNTAX	INTEGER
			ACCESS	read-only
			STATUS	current
	DESCRIPTION ""
			::= { mbusBF 17 }

mbusBFVIF06		OBJECT-TYPE
			SYNTAX	INTEGER
			ACCESS	read-only
			STATUS	current
	DESCRIPTION ""
			::= { mbusBF 18 }

mbusBFValue06		OBJECT-TYPE
			SYNTAX	INTEGER
			ACCESS	read-only
			STATUS	current
	DESCRIPTION ""
			::= { mbusBF 19 }

mbusBFVIF07		OBJECT-TYPE
			SYNTAX	INTEGER
			ACCESS	read-only
			STATUS	current
	DESCRIPTION ""
			::= { mbusBF 20 }

mbusBFValue07		OBJECT-TYPE
			SYNTAX	INTEGER
			ACCESS	read-only
			STATUS	current
	DESCRIPTION ""
			::= { mbusBF 21 }

mbusBFVIF08		OBJECT-TYPE
			SYNTAX	INTEGER
			ACCESS	read-only
			STATUS	current
	DESCRIPTION ""
			::= { mbusBF 22 }

mbusBFValue08		OBJECT-TYPE
			SYNTAX	INTEGER
			ACCESS	read-only
			STATUS	current
	DESCRIPTION ""
			::= { mbusBF 23 }

mbusBFVIF09		OBJECT-TYPE
			SYNTAX	INTEGER
			ACCESS	read-only
			STATUS	current
	DESCRIPTION ""
			::= { mbusBF 24 }

mbusBFValue09		OBJECT-TYPE
			SYNTAX	INTEGER
			ACCESS	read-only
			STATUS	current
	DESCRIPTION ""
			::= { mbusBF 25 }

mbusBFVIF0A		OBJECT-TYPE
			SYNTAX	INTEGER
			ACCESS	read-only
			STATUS	current
	DESCRIPTION ""
			::= { mbusBF 26 }

mbusBFValue0A		OBJECT-TYPE
			SYNTAX	INTEGER
			ACCESS	read-only
			STATUS	current
	DESCRIPTION ""
			::= { mbusBF 27 }

mbusBFVIF0B		OBJECT-TYPE
			SYNTAX	INTEGER
			ACCESS	read-only
			STATUS	current
	DESCRIPTION ""
			::= { mbusBF 28 }

mbusBFValue0B		OBJECT-TYPE
			SYNTAX	INTEGER
			ACCESS	read-only
			STATUS	current
	DESCRIPTION ""
			::= { mbusBF 29 }

mbusBFVIF0C		OBJECT-TYPE
			SYNTAX	INTEGER
			ACCESS	read-only
			STATUS	current
	DESCRIPTION ""
			::= { mbusBF 30 }

mbusBFValue0C		OBJECT-TYPE
			SYNTAX	INTEGER
			ACCESS	read-only
			STATUS	current
	DESCRIPTION ""
			::= { mbusBF 31 }

mbusBFVIF0D		OBJECT-TYPE
			SYNTAX	INTEGER
			ACCESS	read-only
			STATUS	current
	DESCRIPTION ""
			::= { mbusBF 32 }

mbusBFValue0D		OBJECT-TYPE
			SYNTAX	INTEGER
			ACCESS	read-only
			STATUS	current
	DESCRIPTION ""
			::= { mbusBF 33 }

mbusBFVIF0E		OBJECT-TYPE
			SYNTAX	INTEGER
			ACCESS	read-only
			STATUS	current
	DESCRIPTION ""
			::= { mbusBF 34 }

mbusBFValue0E		OBJECT-TYPE
			SYNTAX	INTEGER
			ACCESS	read-only
			STATUS	current
	DESCRIPTION ""
			::= { mbusBF 35 }

mbusBFVIF0F		OBJECT-TYPE
			SYNTAX	INTEGER
			ACCESS	read-only
			STATUS	current
	DESCRIPTION ""
			::= { mbusBF 36 }

mbusBFValue0F		OBJECT-TYPE
			SYNTAX	INTEGER
			ACCESS	read-only
			STATUS	current
	DESCRIPTION ""
			::= { mbusBF 37 }

mbusBFVIF10		OBJECT-TYPE
			SYNTAX	INTEGER
			ACCESS	read-only
			STATUS	current
	DESCRIPTION ""
			::= { mbusBF 38 }

mbusBFValue10		OBJECT-TYPE
			SYNTAX	INTEGER
			ACCESS	read-only
			STATUS	current
	DESCRIPTION ""
			::= { mbusBF 39 }

mbusBFVIF11		OBJECT-TYPE
			SYNTAX	INTEGER
			ACCESS	read-only
			STATUS	current
	DESCRIPTION ""
			::= { mbusBF 40 }

mbusBFValue11		OBJECT-TYPE
			SYNTAX	INTEGER
			ACCESS	read-only
			STATUS	current
	DESCRIPTION ""
			::= { mbusBF 41 }

mbusBFVIF12		OBJECT-TYPE
			SYNTAX	INTEGER
			ACCESS	read-only
			STATUS	current
	DESCRIPTION ""
			::= { mbusBF 42 }

mbusBFValue12		OBJECT-TYPE
			SYNTAX	INTEGER
			ACCESS	read-only
			STATUS	current
	DESCRIPTION ""
			::= { mbusBF 43 }

mbusBFVIF13		OBJECT-TYPE
			SYNTAX	INTEGER
			ACCESS	read-only
			STATUS	current
	DESCRIPTION ""
			::= { mbusBF 44 }

mbusBFValue13		OBJECT-TYPE
			SYNTAX	INTEGER
			ACCESS	read-only
			STATUS	current
	DESCRIPTION ""
			::= { mbusBF 45 }

mbusBFVIF14		OBJECT-TYPE
			SYNTAX	INTEGER
			ACCESS	read-only
			STATUS	current
	DESCRIPTION ""
			::= { mbusBF 46 }

mbusBFValue14		OBJECT-TYPE
			SYNTAX	INTEGER
			ACCESS	read-only
			STATUS	current
	DESCRIPTION ""
			::= { mbusBF 47 }

mbusBFVIF15		OBJECT-TYPE
			SYNTAX	INTEGER
			ACCESS	read-only
			STATUS	current
	DESCRIPTION ""
			::= { mbusBF 48 }

mbusBFValue15		OBJECT-TYPE
			SYNTAX	INTEGER
			ACCESS	read-only
			STATUS	current
	DESCRIPTION ""
			::= { mbusBF 49 }

mbusBFVIF16		OBJECT-TYPE
			SYNTAX	INTEGER
			ACCESS	read-only
			STATUS	current
	DESCRIPTION ""
			::= { mbusBF 50 }

mbusBFValue16		OBJECT-TYPE
			SYNTAX	INTEGER
			ACCESS	read-only
			STATUS	current
	DESCRIPTION ""
			::= { mbusBF 51 }

mbusBFVIF17		OBJECT-TYPE
			SYNTAX	INTEGER
			ACCESS	read-only
			STATUS	current
	DESCRIPTION ""
			::= { mbusBF 52 }

mbusBFValue17		OBJECT-TYPE
			SYNTAX	INTEGER
			ACCESS	read-only
			STATUS	current
	DESCRIPTION ""
			::= { mbusBF 53 }

mbusBFVIF18		OBJECT-TYPE
			SYNTAX	INTEGER
			ACCESS	read-only
			STATUS	current
	DESCRIPTION ""
			::= { mbusBF 54 }

mbusBFValue18		OBJECT-TYPE
			SYNTAX	INTEGER
			ACCESS	read-only
			STATUS	current
	DESCRIPTION ""
			::= { mbusBF 55 }

mbusBFVIF19		OBJECT-TYPE
			SYNTAX	INTEGER
			ACCESS	read-only
			STATUS	current
	DESCRIPTION ""
			::= { mbusBF 56 }

mbusBFValue19		OBJECT-TYPE
			SYNTAX	INTEGER
			ACCESS	read-only
			STATUS	current
	DESCRIPTION ""
			::= { mbusBF 57 }

mbusBFVIF1A		OBJECT-TYPE
			SYNTAX	INTEGER
			ACCESS	read-only
			STATUS	current
	DESCRIPTION ""
			::= { mbusBF 58 }

mbusBFValue1A		OBJECT-TYPE
			SYNTAX	INTEGER
			ACCESS	read-only
			STATUS	current
	DESCRIPTION ""
			::= { mbusBF 59 }

mbusBFVIF1B		OBJECT-TYPE
			SYNTAX	INTEGER
			ACCESS	read-only
			STATUS	current
	DESCRIPTION ""
			::= { mbusBF 60 }

mbusBFValue1B		OBJECT-TYPE
			SYNTAX	INTEGER
			ACCESS	read-only
			STATUS	current
	DESCRIPTION ""
			::= { mbusBF 61 }

mbusBFVIF1C		OBJECT-TYPE
			SYNTAX	INTEGER
			ACCESS	read-only
			STATUS	current
	DESCRIPTION ""
			::= { mbusBF 62 }

mbusBFValue1C		OBJECT-TYPE
			SYNTAX	INTEGER
			ACCESS	read-only
			STATUS	current
	DESCRIPTION ""
			::= { mbusBF 63 }

mbusBFVIF1D		OBJECT-TYPE
			SYNTAX	INTEGER
			ACCESS	read-only
			STATUS	current
	DESCRIPTION ""
			::= { mbusBF 64 }

mbusBFValue1D		OBJECT-TYPE
			SYNTAX	INTEGER
			ACCESS	read-only
			STATUS	current
	DESCRIPTION ""
			::= { mbusBF 65 }

mbusBFVIF1E		OBJECT-TYPE
			SYNTAX	INTEGER
			ACCESS	read-only
			STATUS	current
	DESCRIPTION ""
			::= { mbusBF 66 }

mbusBFValue1E		OBJECT-TYPE
			SYNTAX	INTEGER
			ACCESS	read-only
			STATUS	current
	DESCRIPTION ""
			::= { mbusBF 67 }

mbusBFVIF1F		OBJECT-TYPE
			SYNTAX	INTEGER
			ACCESS	read-only
			STATUS	current
	DESCRIPTION ""
			::= { mbusBF 68 }

mbusBFValue1F		OBJECT-TYPE
			SYNTAX	INTEGER
			ACCESS	read-only
			STATUS	current
	DESCRIPTION ""
			::= { mbusBF 69 }

mbusBFVIF20		OBJECT-TYPE
			SYNTAX	INTEGER
			ACCESS	read-only
			STATUS	current
	DESCRIPTION ""
			::= { mbusBF 70 }

mbusBFValue20		OBJECT-TYPE
			SYNTAX	INTEGER
			ACCESS	read-only
			STATUS	current
	DESCRIPTION ""
			::= { mbusBF 71 }

mbusBFVIF21		OBJECT-TYPE
			SYNTAX	INTEGER
			ACCESS	read-only
			STATUS	current
	DESCRIPTION ""
			::= { mbusBF 72 }

mbusBFValue21		OBJECT-TYPE
			SYNTAX	INTEGER
			ACCESS	read-only
			STATUS	current
	DESCRIPTION ""
			::= { mbusBF 73 }

mbusBFVIF22		OBJECT-TYPE
			SYNTAX	INTEGER
			ACCESS	read-only
			STATUS	current
	DESCRIPTION ""
			::= { mbusBF 74 }

mbusBFValue22		OBJECT-TYPE
			SYNTAX	INTEGER
			ACCESS	read-only
			STATUS	current
	DESCRIPTION ""
			::= { mbusBF 75 }

mbusBFVIF23		OBJECT-TYPE
			SYNTAX	INTEGER
			ACCESS	read-only
			STATUS	current
	DESCRIPTION ""
			::= { mbusBF 76 }

mbusBFValue23		OBJECT-TYPE
			SYNTAX	INTEGER
			ACCESS	read-only
			STATUS	current
	DESCRIPTION ""
			::= { mbusBF 77 }

mbusBFVIF24		OBJECT-TYPE
			SYNTAX	INTEGER
			ACCESS	read-only
			STATUS	current
	DESCRIPTION ""
			::= { mbusBF 78 }

mbusBFValue24		OBJECT-TYPE
			SYNTAX	INTEGER
			ACCESS	read-only
			STATUS	current
	DESCRIPTION ""
			::= { mbusBF 79 }

mbusBFVIF25		OBJECT-TYPE
			SYNTAX	INTEGER
			ACCESS	read-only
			STATUS	current
	DESCRIPTION ""
			::= { mbusBF 80 }

mbusBFValue25		OBJECT-TYPE
			SYNTAX	INTEGER
			ACCESS	read-only
			STATUS	current
	DESCRIPTION ""
			::= { mbusBF 81 }

mbusBFVIF26		OBJECT-TYPE
			SYNTAX	INTEGER
			ACCESS	read-only
			STATUS	current
	DESCRIPTION ""
			::= { mbusBF 82 }

mbusBFValue26		OBJECT-TYPE
			SYNTAX	INTEGER
			ACCESS	read-only
			STATUS	current
	DESCRIPTION ""
			::= { mbusBF 83 }

mbusBFVIF27		OBJECT-TYPE
			SYNTAX	INTEGER
			ACCESS	read-only
			STATUS	current
	DESCRIPTION ""
			::= { mbusBF 84 }

mbusBFValue27		OBJECT-TYPE
			SYNTAX	INTEGER
			ACCESS	read-only
			STATUS	current
	DESCRIPTION ""
			::= { mbusBF 85 }

mbusBFVIF28		OBJECT-TYPE
			SYNTAX	INTEGER
			ACCESS	read-only
			STATUS	current
	DESCRIPTION ""
			::= { mbusBF 86 }

mbusBFValue28		OBJECT-TYPE
			SYNTAX	INTEGER
			ACCESS	read-only
			STATUS	current
	DESCRIPTION ""
			::= { mbusBF 87 }

mbusBFVIF29		OBJECT-TYPE
			SYNTAX	INTEGER
			ACCESS	read-only
			STATUS	current
	DESCRIPTION ""
			::= { mbusBF 88 }

mbusBFValue29		OBJECT-TYPE
			SYNTAX	INTEGER
			ACCESS	read-only
			STATUS	current
	DESCRIPTION ""
			::= { mbusBF 89 }

mbusBFVIF2A		OBJECT-TYPE
			SYNTAX	INTEGER
			ACCESS	read-only
			STATUS	current
	DESCRIPTION ""
			::= { mbusBF 90 }

mbusBFValue2A		OBJECT-TYPE
			SYNTAX	INTEGER
			ACCESS	read-only
			STATUS	current
	DESCRIPTION ""
			::= { mbusBF 91 }

mbusBFVIF2B		OBJECT-TYPE
			SYNTAX	INTEGER
			ACCESS	read-only
			STATUS	current
	DESCRIPTION ""
			::= { mbusBF 92 }

mbusBFValue2B		OBJECT-TYPE
			SYNTAX	INTEGER
			ACCESS	read-only
			STATUS	current
	DESCRIPTION ""
			::= { mbusBF 93 }

mbusBFVIF2C		OBJECT-TYPE
			SYNTAX	INTEGER
			ACCESS	read-only
			STATUS	current
	DESCRIPTION ""
			::= { mbusBF 94 }

mbusBFValue2C		OBJECT-TYPE
			SYNTAX	INTEGER
			ACCESS	read-only
			STATUS	current
	DESCRIPTION ""
			::= { mbusBF 95 }

mbusBFVIF2D		OBJECT-TYPE
			SYNTAX	INTEGER
			ACCESS	read-only
			STATUS	current
	DESCRIPTION ""
			::= { mbusBF 96 }

mbusBFValue2D		OBJECT-TYPE
			SYNTAX	INTEGER
			ACCESS	read-only
			STATUS	current
	DESCRIPTION ""
			::= { mbusBF 97 }

mbusBFVIF2E		OBJECT-TYPE
			SYNTAX	INTEGER
			ACCESS	read-only
			STATUS	current
	DESCRIPTION ""
			::= { mbusBF 98 }

mbusBFValue2E		OBJECT-TYPE
			SYNTAX	INTEGER
			ACCESS	read-only
			STATUS	current
	DESCRIPTION ""
			::= { mbusBF 99 }

mbusBFVIF2F		OBJECT-TYPE
			SYNTAX	INTEGER
			ACCESS	read-only
			STATUS	current
	DESCRIPTION ""
			::= { mbusBF 100 }

mbusBFValue2F		OBJECT-TYPE
			SYNTAX	INTEGER
			ACCESS	read-only
			STATUS	current
	DESCRIPTION ""
			::= { mbusBF 101 }

mbusC0			OBJECT IDENTIFIER ::= { mbus 192 }

mbusC0IdNumber		OBJECT-TYPE
			SYNTAX	Gauge
			ACCESS	read-only
			STATUS	current
	DESCRIPTION ""
			::= { mbusC0 1 }

mbusC0Manufacturer	OBJECT-TYPE
			SYNTAX	Gauge
			ACCESS	read-only
			STATUS	current
	DESCRIPTION ""
			::= { mbusC0 2 }

mbusC0Version		OBJECT-TYPE
			SYNTAX	Gauge
			ACCESS	read-only
			STATUS	current
	DESCRIPTION ""
			::= { mbusC0 3 }

mbusC0Medium		OBJECT-TYPE
			SYNTAX	Gauge
			ACCESS	read-only
			STATUS	current
	DESCRIPTION ""
			::= { mbusC0 4 }

mbusC0Status		OBJECT-TYPE
			SYNTAX	Gauge
			ACCESS	read-only
			STATUS	current
	DESCRIPTION ""
			::= { mbusC0 5 }

mbusC0VIF00		OBJECT-TYPE
			SYNTAX	INTEGER
			ACCESS	read-only
			STATUS	current
	DESCRIPTION ""
			::= { mbusC0 6 }

mbusC0Value00		OBJECT-TYPE
			SYNTAX	INTEGER
			ACCESS	read-only
			STATUS	current
	DESCRIPTION ""
			::= { mbusC0 7 }

mbusC0VIF01		OBJECT-TYPE
			SYNTAX	INTEGER
			ACCESS	read-only
			STATUS	current
	DESCRIPTION ""
			::= { mbusC0 8 }

mbusC0Value01		OBJECT-TYPE
			SYNTAX	INTEGER
			ACCESS	read-only
			STATUS	current
	DESCRIPTION ""
			::= { mbusC0 9 }

mbusC0VIF02		OBJECT-TYPE
			SYNTAX	INTEGER
			ACCESS	read-only
			STATUS	current
	DESCRIPTION ""
			::= { mbusC0 10 }

mbusC0Value02		OBJECT-TYPE
			SYNTAX	INTEGER
			ACCESS	read-only
			STATUS	current
	DESCRIPTION ""
			::= { mbusC0 11 }

mbusC0VIF03		OBJECT-TYPE
			SYNTAX	INTEGER
			ACCESS	read-only
			STATUS	current
	DESCRIPTION ""
			::= { mbusC0 12 }

mbusC0Value03		OBJECT-TYPE
			SYNTAX	INTEGER
			ACCESS	read-only
			STATUS	current
	DESCRIPTION ""
			::= { mbusC0 13 }

mbusC0VIF04		OBJECT-TYPE
			SYNTAX	INTEGER
			ACCESS	read-only
			STATUS	current
	DESCRIPTION ""
			::= { mbusC0 14 }

mbusC0Value04		OBJECT-TYPE
			SYNTAX	INTEGER
			ACCESS	read-only
			STATUS	current
	DESCRIPTION ""
			::= { mbusC0 15 }

mbusC0VIF05		OBJECT-TYPE
			SYNTAX	INTEGER
			ACCESS	read-only
			STATUS	current
	DESCRIPTION ""
			::= { mbusC0 16 }

mbusC0Value05		OBJECT-TYPE
			SYNTAX	INTEGER
			ACCESS	read-only
			STATUS	current
	DESCRIPTION ""
			::= { mbusC0 17 }

mbusC0VIF06		OBJECT-TYPE
			SYNTAX	INTEGER
			ACCESS	read-only
			STATUS	current
	DESCRIPTION ""
			::= { mbusC0 18 }

mbusC0Value06		OBJECT-TYPE
			SYNTAX	INTEGER
			ACCESS	read-only
			STATUS	current
	DESCRIPTION ""
			::= { mbusC0 19 }

mbusC0VIF07		OBJECT-TYPE
			SYNTAX	INTEGER
			ACCESS	read-only
			STATUS	current
	DESCRIPTION ""
			::= { mbusC0 20 }

mbusC0Value07		OBJECT-TYPE
			SYNTAX	INTEGER
			ACCESS	read-only
			STATUS	current
	DESCRIPTION ""
			::= { mbusC0 21 }

mbusC0VIF08		OBJECT-TYPE
			SYNTAX	INTEGER
			ACCESS	read-only
			STATUS	current
	DESCRIPTION ""
			::= { mbusC0 22 }

mbusC0Value08		OBJECT-TYPE
			SYNTAX	INTEGER
			ACCESS	read-only
			STATUS	current
	DESCRIPTION ""
			::= { mbusC0 23 }

mbusC0VIF09		OBJECT-TYPE
			SYNTAX	INTEGER
			ACCESS	read-only
			STATUS	current
	DESCRIPTION ""
			::= { mbusC0 24 }

mbusC0Value09		OBJECT-TYPE
			SYNTAX	INTEGER
			ACCESS	read-only
			STATUS	current
	DESCRIPTION ""
			::= { mbusC0 25 }

mbusC0VIF0A		OBJECT-TYPE
			SYNTAX	INTEGER
			ACCESS	read-only
			STATUS	current
	DESCRIPTION ""
			::= { mbusC0 26 }

mbusC0Value0A		OBJECT-TYPE
			SYNTAX	INTEGER
			ACCESS	read-only
			STATUS	current
	DESCRIPTION ""
			::= { mbusC0 27 }

mbusC0VIF0B		OBJECT-TYPE
			SYNTAX	INTEGER
			ACCESS	read-only
			STATUS	current
	DESCRIPTION ""
			::= { mbusC0 28 }

mbusC0Value0B		OBJECT-TYPE
			SYNTAX	INTEGER
			ACCESS	read-only
			STATUS	current
	DESCRIPTION ""
			::= { mbusC0 29 }

mbusC0VIF0C		OBJECT-TYPE
			SYNTAX	INTEGER
			ACCESS	read-only
			STATUS	current
	DESCRIPTION ""
			::= { mbusC0 30 }

mbusC0Value0C		OBJECT-TYPE
			SYNTAX	INTEGER
			ACCESS	read-only
			STATUS	current
	DESCRIPTION ""
			::= { mbusC0 31 }

mbusC0VIF0D		OBJECT-TYPE
			SYNTAX	INTEGER
			ACCESS	read-only
			STATUS	current
	DESCRIPTION ""
			::= { mbusC0 32 }

mbusC0Value0D		OBJECT-TYPE
			SYNTAX	INTEGER
			ACCESS	read-only
			STATUS	current
	DESCRIPTION ""
			::= { mbusC0 33 }

mbusC0VIF0E		OBJECT-TYPE
			SYNTAX	INTEGER
			ACCESS	read-only
			STATUS	current
	DESCRIPTION ""
			::= { mbusC0 34 }

mbusC0Value0E		OBJECT-TYPE
			SYNTAX	INTEGER
			ACCESS	read-only
			STATUS	current
	DESCRIPTION ""
			::= { mbusC0 35 }

mbusC0VIF0F		OBJECT-TYPE
			SYNTAX	INTEGER
			ACCESS	read-only
			STATUS	current
	DESCRIPTION ""
			::= { mbusC0 36 }

mbusC0Value0F		OBJECT-TYPE
			SYNTAX	INTEGER
			ACCESS	read-only
			STATUS	current
	DESCRIPTION ""
			::= { mbusC0 37 }

mbusC0VIF10		OBJECT-TYPE
			SYNTAX	INTEGER
			ACCESS	read-only
			STATUS	current
	DESCRIPTION ""
			::= { mbusC0 38 }

mbusC0Value10		OBJECT-TYPE
			SYNTAX	INTEGER
			ACCESS	read-only
			STATUS	current
	DESCRIPTION ""
			::= { mbusC0 39 }

mbusC0VIF11		OBJECT-TYPE
			SYNTAX	INTEGER
			ACCESS	read-only
			STATUS	current
	DESCRIPTION ""
			::= { mbusC0 40 }

mbusC0Value11		OBJECT-TYPE
			SYNTAX	INTEGER
			ACCESS	read-only
			STATUS	current
	DESCRIPTION ""
			::= { mbusC0 41 }

mbusC0VIF12		OBJECT-TYPE
			SYNTAX	INTEGER
			ACCESS	read-only
			STATUS	current
	DESCRIPTION ""
			::= { mbusC0 42 }

mbusC0Value12		OBJECT-TYPE
			SYNTAX	INTEGER
			ACCESS	read-only
			STATUS	current
	DESCRIPTION ""
			::= { mbusC0 43 }

mbusC0VIF13		OBJECT-TYPE
			SYNTAX	INTEGER
			ACCESS	read-only
			STATUS	current
	DESCRIPTION ""
			::= { mbusC0 44 }

mbusC0Value13		OBJECT-TYPE
			SYNTAX	INTEGER
			ACCESS	read-only
			STATUS	current
	DESCRIPTION ""
			::= { mbusC0 45 }

mbusC0VIF14		OBJECT-TYPE
			SYNTAX	INTEGER
			ACCESS	read-only
			STATUS	current
	DESCRIPTION ""
			::= { mbusC0 46 }

mbusC0Value14		OBJECT-TYPE
			SYNTAX	INTEGER
			ACCESS	read-only
			STATUS	current
	DESCRIPTION ""
			::= { mbusC0 47 }

mbusC0VIF15		OBJECT-TYPE
			SYNTAX	INTEGER
			ACCESS	read-only
			STATUS	current
	DESCRIPTION ""
			::= { mbusC0 48 }

mbusC0Value15		OBJECT-TYPE
			SYNTAX	INTEGER
			ACCESS	read-only
			STATUS	current
	DESCRIPTION ""
			::= { mbusC0 49 }

mbusC0VIF16		OBJECT-TYPE
			SYNTAX	INTEGER
			ACCESS	read-only
			STATUS	current
	DESCRIPTION ""
			::= { mbusC0 50 }

mbusC0Value16		OBJECT-TYPE
			SYNTAX	INTEGER
			ACCESS	read-only
			STATUS	current
	DESCRIPTION ""
			::= { mbusC0 51 }

mbusC0VIF17		OBJECT-TYPE
			SYNTAX	INTEGER
			ACCESS	read-only
			STATUS	current
	DESCRIPTION ""
			::= { mbusC0 52 }

mbusC0Value17		OBJECT-TYPE
			SYNTAX	INTEGER
			ACCESS	read-only
			STATUS	current
	DESCRIPTION ""
			::= { mbusC0 53 }

mbusC0VIF18		OBJECT-TYPE
			SYNTAX	INTEGER
			ACCESS	read-only
			STATUS	current
	DESCRIPTION ""
			::= { mbusC0 54 }

mbusC0Value18		OBJECT-TYPE
			SYNTAX	INTEGER
			ACCESS	read-only
			STATUS	current
	DESCRIPTION ""
			::= { mbusC0 55 }

mbusC0VIF19		OBJECT-TYPE
			SYNTAX	INTEGER
			ACCESS	read-only
			STATUS	current
	DESCRIPTION ""
			::= { mbusC0 56 }

mbusC0Value19		OBJECT-TYPE
			SYNTAX	INTEGER
			ACCESS	read-only
			STATUS	current
	DESCRIPTION ""
			::= { mbusC0 57 }

mbusC0VIF1A		OBJECT-TYPE
			SYNTAX	INTEGER
			ACCESS	read-only
			STATUS	current
	DESCRIPTION ""
			::= { mbusC0 58 }

mbusC0Value1A		OBJECT-TYPE
			SYNTAX	INTEGER
			ACCESS	read-only
			STATUS	current
	DESCRIPTION ""
			::= { mbusC0 59 }

mbusC0VIF1B		OBJECT-TYPE
			SYNTAX	INTEGER
			ACCESS	read-only
			STATUS	current
	DESCRIPTION ""
			::= { mbusC0 60 }

mbusC0Value1B		OBJECT-TYPE
			SYNTAX	INTEGER
			ACCESS	read-only
			STATUS	current
	DESCRIPTION ""
			::= { mbusC0 61 }

mbusC0VIF1C		OBJECT-TYPE
			SYNTAX	INTEGER
			ACCESS	read-only
			STATUS	current
	DESCRIPTION ""
			::= { mbusC0 62 }

mbusC0Value1C		OBJECT-TYPE
			SYNTAX	INTEGER
			ACCESS	read-only
			STATUS	current
	DESCRIPTION ""
			::= { mbusC0 63 }

mbusC0VIF1D		OBJECT-TYPE
			SYNTAX	INTEGER
			ACCESS	read-only
			STATUS	current
	DESCRIPTION ""
			::= { mbusC0 64 }

mbusC0Value1D		OBJECT-TYPE
			SYNTAX	INTEGER
			ACCESS	read-only
			STATUS	current
	DESCRIPTION ""
			::= { mbusC0 65 }

mbusC0VIF1E		OBJECT-TYPE
			SYNTAX	INTEGER
			ACCESS	read-only
			STATUS	current
	DESCRIPTION ""
			::= { mbusC0 66 }

mbusC0Value1E		OBJECT-TYPE
			SYNTAX	INTEGER
			ACCESS	read-only
			STATUS	current
	DESCRIPTION ""
			::= { mbusC0 67 }

mbusC0VIF1F		OBJECT-TYPE
			SYNTAX	INTEGER
			ACCESS	read-only
			STATUS	current
	DESCRIPTION ""
			::= { mbusC0 68 }

mbusC0Value1F		OBJECT-TYPE
			SYNTAX	INTEGER
			ACCESS	read-only
			STATUS	current
	DESCRIPTION ""
			::= { mbusC0 69 }

mbusC0VIF20		OBJECT-TYPE
			SYNTAX	INTEGER
			ACCESS	read-only
			STATUS	current
	DESCRIPTION ""
			::= { mbusC0 70 }

mbusC0Value20		OBJECT-TYPE
			SYNTAX	INTEGER
			ACCESS	read-only
			STATUS	current
	DESCRIPTION ""
			::= { mbusC0 71 }

mbusC0VIF21		OBJECT-TYPE
			SYNTAX	INTEGER
			ACCESS	read-only
			STATUS	current
	DESCRIPTION ""
			::= { mbusC0 72 }

mbusC0Value21		OBJECT-TYPE
			SYNTAX	INTEGER
			ACCESS	read-only
			STATUS	current
	DESCRIPTION ""
			::= { mbusC0 73 }

mbusC0VIF22		OBJECT-TYPE
			SYNTAX	INTEGER
			ACCESS	read-only
			STATUS	current
	DESCRIPTION ""
			::= { mbusC0 74 }

mbusC0Value22		OBJECT-TYPE
			SYNTAX	INTEGER
			ACCESS	read-only
			STATUS	current
	DESCRIPTION ""
			::= { mbusC0 75 }

mbusC0VIF23		OBJECT-TYPE
			SYNTAX	INTEGER
			ACCESS	read-only
			STATUS	current
	DESCRIPTION ""
			::= { mbusC0 76 }

mbusC0Value23		OBJECT-TYPE
			SYNTAX	INTEGER
			ACCESS	read-only
			STATUS	current
	DESCRIPTION ""
			::= { mbusC0 77 }

mbusC0VIF24		OBJECT-TYPE
			SYNTAX	INTEGER
			ACCESS	read-only
			STATUS	current
	DESCRIPTION ""
			::= { mbusC0 78 }

mbusC0Value24		OBJECT-TYPE
			SYNTAX	INTEGER
			ACCESS	read-only
			STATUS	current
	DESCRIPTION ""
			::= { mbusC0 79 }

mbusC0VIF25		OBJECT-TYPE
			SYNTAX	INTEGER
			ACCESS	read-only
			STATUS	current
	DESCRIPTION ""
			::= { mbusC0 80 }

mbusC0Value25		OBJECT-TYPE
			SYNTAX	INTEGER
			ACCESS	read-only
			STATUS	current
	DESCRIPTION ""
			::= { mbusC0 81 }

mbusC0VIF26		OBJECT-TYPE
			SYNTAX	INTEGER
			ACCESS	read-only
			STATUS	current
	DESCRIPTION ""
			::= { mbusC0 82 }

mbusC0Value26		OBJECT-TYPE
			SYNTAX	INTEGER
			ACCESS	read-only
			STATUS	current
	DESCRIPTION ""
			::= { mbusC0 83 }

mbusC0VIF27		OBJECT-TYPE
			SYNTAX	INTEGER
			ACCESS	read-only
			STATUS	current
	DESCRIPTION ""
			::= { mbusC0 84 }

mbusC0Value27		OBJECT-TYPE
			SYNTAX	INTEGER
			ACCESS	read-only
			STATUS	current
	DESCRIPTION ""
			::= { mbusC0 85 }

mbusC0VIF28		OBJECT-TYPE
			SYNTAX	INTEGER
			ACCESS	read-only
			STATUS	current
	DESCRIPTION ""
			::= { mbusC0 86 }

mbusC0Value28		OBJECT-TYPE
			SYNTAX	INTEGER
			ACCESS	read-only
			STATUS	current
	DESCRIPTION ""
			::= { mbusC0 87 }

mbusC0VIF29		OBJECT-TYPE
			SYNTAX	INTEGER
			ACCESS	read-only
			STATUS	current
	DESCRIPTION ""
			::= { mbusC0 88 }

mbusC0Value29		OBJECT-TYPE
			SYNTAX	INTEGER
			ACCESS	read-only
			STATUS	current
	DESCRIPTION ""
			::= { mbusC0 89 }

mbusC0VIF2A		OBJECT-TYPE
			SYNTAX	INTEGER
			ACCESS	read-only
			STATUS	current
	DESCRIPTION ""
			::= { mbusC0 90 }

mbusC0Value2A		OBJECT-TYPE
			SYNTAX	INTEGER
			ACCESS	read-only
			STATUS	current
	DESCRIPTION ""
			::= { mbusC0 91 }

mbusC0VIF2B		OBJECT-TYPE
			SYNTAX	INTEGER
			ACCESS	read-only
			STATUS	current
	DESCRIPTION ""
			::= { mbusC0 92 }

mbusC0Value2B		OBJECT-TYPE
			SYNTAX	INTEGER
			ACCESS	read-only
			STATUS	current
	DESCRIPTION ""
			::= { mbusC0 93 }

mbusC0VIF2C		OBJECT-TYPE
			SYNTAX	INTEGER
			ACCESS	read-only
			STATUS	current
	DESCRIPTION ""
			::= { mbusC0 94 }

mbusC0Value2C		OBJECT-TYPE
			SYNTAX	INTEGER
			ACCESS	read-only
			STATUS	current
	DESCRIPTION ""
			::= { mbusC0 95 }

mbusC0VIF2D		OBJECT-TYPE
			SYNTAX	INTEGER
			ACCESS	read-only
			STATUS	current
	DESCRIPTION ""
			::= { mbusC0 96 }

mbusC0Value2D		OBJECT-TYPE
			SYNTAX	INTEGER
			ACCESS	read-only
			STATUS	current
	DESCRIPTION ""
			::= { mbusC0 97 }

mbusC0VIF2E		OBJECT-TYPE
			SYNTAX	INTEGER
			ACCESS	read-only
			STATUS	current
	DESCRIPTION ""
			::= { mbusC0 98 }

mbusC0Value2E		OBJECT-TYPE
			SYNTAX	INTEGER
			ACCESS	read-only
			STATUS	current
	DESCRIPTION ""
			::= { mbusC0 99 }

mbusC0VIF2F		OBJECT-TYPE
			SYNTAX	INTEGER
			ACCESS	read-only
			STATUS	current
	DESCRIPTION ""
			::= { mbusC0 100 }

mbusC0Value2F		OBJECT-TYPE
			SYNTAX	INTEGER
			ACCESS	read-only
			STATUS	current
	DESCRIPTION ""
			::= { mbusC0 101 }

mbusC1			OBJECT IDENTIFIER ::= { mbus 193 }

mbusC1IdNumber		OBJECT-TYPE
			SYNTAX	Gauge
			ACCESS	read-only
			STATUS	current
	DESCRIPTION ""
			::= { mbusC1 1 }

mbusC1Manufacturer	OBJECT-TYPE
			SYNTAX	Gauge
			ACCESS	read-only
			STATUS	current
	DESCRIPTION ""
			::= { mbusC1 2 }

mbusC1Version		OBJECT-TYPE
			SYNTAX	Gauge
			ACCESS	read-only
			STATUS	current
	DESCRIPTION ""
			::= { mbusC1 3 }

mbusC1Medium		OBJECT-TYPE
			SYNTAX	Gauge
			ACCESS	read-only
			STATUS	current
	DESCRIPTION ""
			::= { mbusC1 4 }

mbusC1Status		OBJECT-TYPE
			SYNTAX	Gauge
			ACCESS	read-only
			STATUS	current
	DESCRIPTION ""
			::= { mbusC1 5 }

mbusC1VIF00		OBJECT-TYPE
			SYNTAX	INTEGER
			ACCESS	read-only
			STATUS	current
	DESCRIPTION ""
			::= { mbusC1 6 }

mbusC1Value00		OBJECT-TYPE
			SYNTAX	INTEGER
			ACCESS	read-only
			STATUS	current
	DESCRIPTION ""
			::= { mbusC1 7 }

mbusC1VIF01		OBJECT-TYPE
			SYNTAX	INTEGER
			ACCESS	read-only
			STATUS	current
	DESCRIPTION ""
			::= { mbusC1 8 }

mbusC1Value01		OBJECT-TYPE
			SYNTAX	INTEGER
			ACCESS	read-only
			STATUS	current
	DESCRIPTION ""
			::= { mbusC1 9 }

mbusC1VIF02		OBJECT-TYPE
			SYNTAX	INTEGER
			ACCESS	read-only
			STATUS	current
	DESCRIPTION ""
			::= { mbusC1 10 }

mbusC1Value02		OBJECT-TYPE
			SYNTAX	INTEGER
			ACCESS	read-only
			STATUS	current
	DESCRIPTION ""
			::= { mbusC1 11 }

mbusC1VIF03		OBJECT-TYPE
			SYNTAX	INTEGER
			ACCESS	read-only
			STATUS	current
	DESCRIPTION ""
			::= { mbusC1 12 }

mbusC1Value03		OBJECT-TYPE
			SYNTAX	INTEGER
			ACCESS	read-only
			STATUS	current
	DESCRIPTION ""
			::= { mbusC1 13 }

mbusC1VIF04		OBJECT-TYPE
			SYNTAX	INTEGER
			ACCESS	read-only
			STATUS	current
	DESCRIPTION ""
			::= { mbusC1 14 }

mbusC1Value04		OBJECT-TYPE
			SYNTAX	INTEGER
			ACCESS	read-only
			STATUS	current
	DESCRIPTION ""
			::= { mbusC1 15 }

mbusC1VIF05		OBJECT-TYPE
			SYNTAX	INTEGER
			ACCESS	read-only
			STATUS	current
	DESCRIPTION ""
			::= { mbusC1 16 }

mbusC1Value05		OBJECT-TYPE
			SYNTAX	INTEGER
			ACCESS	read-only
			STATUS	current
	DESCRIPTION ""
			::= { mbusC1 17 }

mbusC1VIF06		OBJECT-TYPE
			SYNTAX	INTEGER
			ACCESS	read-only
			STATUS	current
	DESCRIPTION ""
			::= { mbusC1 18 }

mbusC1Value06		OBJECT-TYPE
			SYNTAX	INTEGER
			ACCESS	read-only
			STATUS	current
	DESCRIPTION ""
			::= { mbusC1 19 }

mbusC1VIF07		OBJECT-TYPE
			SYNTAX	INTEGER
			ACCESS	read-only
			STATUS	current
	DESCRIPTION ""
			::= { mbusC1 20 }

mbusC1Value07		OBJECT-TYPE
			SYNTAX	INTEGER
			ACCESS	read-only
			STATUS	current
	DESCRIPTION ""
			::= { mbusC1 21 }

mbusC1VIF08		OBJECT-TYPE
			SYNTAX	INTEGER
			ACCESS	read-only
			STATUS	current
	DESCRIPTION ""
			::= { mbusC1 22 }

mbusC1Value08		OBJECT-TYPE
			SYNTAX	INTEGER
			ACCESS	read-only
			STATUS	current
	DESCRIPTION ""
			::= { mbusC1 23 }

mbusC1VIF09		OBJECT-TYPE
			SYNTAX	INTEGER
			ACCESS	read-only
			STATUS	current
	DESCRIPTION ""
			::= { mbusC1 24 }

mbusC1Value09		OBJECT-TYPE
			SYNTAX	INTEGER
			ACCESS	read-only
			STATUS	current
	DESCRIPTION ""
			::= { mbusC1 25 }

mbusC1VIF0A		OBJECT-TYPE
			SYNTAX	INTEGER
			ACCESS	read-only
			STATUS	current
	DESCRIPTION ""
			::= { mbusC1 26 }

mbusC1Value0A		OBJECT-TYPE
			SYNTAX	INTEGER
			ACCESS	read-only
			STATUS	current
	DESCRIPTION ""
			::= { mbusC1 27 }

mbusC1VIF0B		OBJECT-TYPE
			SYNTAX	INTEGER
			ACCESS	read-only
			STATUS	current
	DESCRIPTION ""
			::= { mbusC1 28 }

mbusC1Value0B		OBJECT-TYPE
			SYNTAX	INTEGER
			ACCESS	read-only
			STATUS	current
	DESCRIPTION ""
			::= { mbusC1 29 }

mbusC1VIF0C		OBJECT-TYPE
			SYNTAX	INTEGER
			ACCESS	read-only
			STATUS	current
	DESCRIPTION ""
			::= { mbusC1 30 }

mbusC1Value0C		OBJECT-TYPE
			SYNTAX	INTEGER
			ACCESS	read-only
			STATUS	current
	DESCRIPTION ""
			::= { mbusC1 31 }

mbusC1VIF0D		OBJECT-TYPE
			SYNTAX	INTEGER
			ACCESS	read-only
			STATUS	current
	DESCRIPTION ""
			::= { mbusC1 32 }

mbusC1Value0D		OBJECT-TYPE
			SYNTAX	INTEGER
			ACCESS	read-only
			STATUS	current
	DESCRIPTION ""
			::= { mbusC1 33 }

mbusC1VIF0E		OBJECT-TYPE
			SYNTAX	INTEGER
			ACCESS	read-only
			STATUS	current
	DESCRIPTION ""
			::= { mbusC1 34 }

mbusC1Value0E		OBJECT-TYPE
			SYNTAX	INTEGER
			ACCESS	read-only
			STATUS	current
	DESCRIPTION ""
			::= { mbusC1 35 }

mbusC1VIF0F		OBJECT-TYPE
			SYNTAX	INTEGER
			ACCESS	read-only
			STATUS	current
	DESCRIPTION ""
			::= { mbusC1 36 }

mbusC1Value0F		OBJECT-TYPE
			SYNTAX	INTEGER
			ACCESS	read-only
			STATUS	current
	DESCRIPTION ""
			::= { mbusC1 37 }

mbusC1VIF10		OBJECT-TYPE
			SYNTAX	INTEGER
			ACCESS	read-only
			STATUS	current
	DESCRIPTION ""
			::= { mbusC1 38 }

mbusC1Value10		OBJECT-TYPE
			SYNTAX	INTEGER
			ACCESS	read-only
			STATUS	current
	DESCRIPTION ""
			::= { mbusC1 39 }

mbusC1VIF11		OBJECT-TYPE
			SYNTAX	INTEGER
			ACCESS	read-only
			STATUS	current
	DESCRIPTION ""
			::= { mbusC1 40 }

mbusC1Value11		OBJECT-TYPE
			SYNTAX	INTEGER
			ACCESS	read-only
			STATUS	current
	DESCRIPTION ""
			::= { mbusC1 41 }

mbusC1VIF12		OBJECT-TYPE
			SYNTAX	INTEGER
			ACCESS	read-only
			STATUS	current
	DESCRIPTION ""
			::= { mbusC1 42 }

mbusC1Value12		OBJECT-TYPE
			SYNTAX	INTEGER
			ACCESS	read-only
			STATUS	current
	DESCRIPTION ""
			::= { mbusC1 43 }

mbusC1VIF13		OBJECT-TYPE
			SYNTAX	INTEGER
			ACCESS	read-only
			STATUS	current
	DESCRIPTION ""
			::= { mbusC1 44 }

mbusC1Value13		OBJECT-TYPE
			SYNTAX	INTEGER
			ACCESS	read-only
			STATUS	current
	DESCRIPTION ""
			::= { mbusC1 45 }

mbusC1VIF14		OBJECT-TYPE
			SYNTAX	INTEGER
			ACCESS	read-only
			STATUS	current
	DESCRIPTION ""
			::= { mbusC1 46 }

mbusC1Value14		OBJECT-TYPE
			SYNTAX	INTEGER
			ACCESS	read-only
			STATUS	current
	DESCRIPTION ""
			::= { mbusC1 47 }

mbusC1VIF15		OBJECT-TYPE
			SYNTAX	INTEGER
			ACCESS	read-only
			STATUS	current
	DESCRIPTION ""
			::= { mbusC1 48 }

mbusC1Value15		OBJECT-TYPE
			SYNTAX	INTEGER
			ACCESS	read-only
			STATUS	current
	DESCRIPTION ""
			::= { mbusC1 49 }

mbusC1VIF16		OBJECT-TYPE
			SYNTAX	INTEGER
			ACCESS	read-only
			STATUS	current
	DESCRIPTION ""
			::= { mbusC1 50 }

mbusC1Value16		OBJECT-TYPE
			SYNTAX	INTEGER
			ACCESS	read-only
			STATUS	current
	DESCRIPTION ""
			::= { mbusC1 51 }

mbusC1VIF17		OBJECT-TYPE
			SYNTAX	INTEGER
			ACCESS	read-only
			STATUS	current
	DESCRIPTION ""
			::= { mbusC1 52 }

mbusC1Value17		OBJECT-TYPE
			SYNTAX	INTEGER
			ACCESS	read-only
			STATUS	current
	DESCRIPTION ""
			::= { mbusC1 53 }

mbusC1VIF18		OBJECT-TYPE
			SYNTAX	INTEGER
			ACCESS	read-only
			STATUS	current
	DESCRIPTION ""
			::= { mbusC1 54 }

mbusC1Value18		OBJECT-TYPE
			SYNTAX	INTEGER
			ACCESS	read-only
			STATUS	current
	DESCRIPTION ""
			::= { mbusC1 55 }

mbusC1VIF19		OBJECT-TYPE
			SYNTAX	INTEGER
			ACCESS	read-only
			STATUS	current
	DESCRIPTION ""
			::= { mbusC1 56 }

mbusC1Value19		OBJECT-TYPE
			SYNTAX	INTEGER
			ACCESS	read-only
			STATUS	current
	DESCRIPTION ""
			::= { mbusC1 57 }

mbusC1VIF1A		OBJECT-TYPE
			SYNTAX	INTEGER
			ACCESS	read-only
			STATUS	current
	DESCRIPTION ""
			::= { mbusC1 58 }

mbusC1Value1A		OBJECT-TYPE
			SYNTAX	INTEGER
			ACCESS	read-only
			STATUS	current
	DESCRIPTION ""
			::= { mbusC1 59 }

mbusC1VIF1B		OBJECT-TYPE
			SYNTAX	INTEGER
			ACCESS	read-only
			STATUS	current
	DESCRIPTION ""
			::= { mbusC1 60 }

mbusC1Value1B		OBJECT-TYPE
			SYNTAX	INTEGER
			ACCESS	read-only
			STATUS	current
	DESCRIPTION ""
			::= { mbusC1 61 }

mbusC1VIF1C		OBJECT-TYPE
			SYNTAX	INTEGER
			ACCESS	read-only
			STATUS	current
	DESCRIPTION ""
			::= { mbusC1 62 }

mbusC1Value1C		OBJECT-TYPE
			SYNTAX	INTEGER
			ACCESS	read-only
			STATUS	current
	DESCRIPTION ""
			::= { mbusC1 63 }

mbusC1VIF1D		OBJECT-TYPE
			SYNTAX	INTEGER
			ACCESS	read-only
			STATUS	current
	DESCRIPTION ""
			::= { mbusC1 64 }

mbusC1Value1D		OBJECT-TYPE
			SYNTAX	INTEGER
			ACCESS	read-only
			STATUS	current
	DESCRIPTION ""
			::= { mbusC1 65 }

mbusC1VIF1E		OBJECT-TYPE
			SYNTAX	INTEGER
			ACCESS	read-only
			STATUS	current
	DESCRIPTION ""
			::= { mbusC1 66 }

mbusC1Value1E		OBJECT-TYPE
			SYNTAX	INTEGER
			ACCESS	read-only
			STATUS	current
	DESCRIPTION ""
			::= { mbusC1 67 }

mbusC1VIF1F		OBJECT-TYPE
			SYNTAX	INTEGER
			ACCESS	read-only
			STATUS	current
	DESCRIPTION ""
			::= { mbusC1 68 }

mbusC1Value1F		OBJECT-TYPE
			SYNTAX	INTEGER
			ACCESS	read-only
			STATUS	current
	DESCRIPTION ""
			::= { mbusC1 69 }

mbusC1VIF20		OBJECT-TYPE
			SYNTAX	INTEGER
			ACCESS	read-only
			STATUS	current
	DESCRIPTION ""
			::= { mbusC1 70 }

mbusC1Value20		OBJECT-TYPE
			SYNTAX	INTEGER
			ACCESS	read-only
			STATUS	current
	DESCRIPTION ""
			::= { mbusC1 71 }

mbusC1VIF21		OBJECT-TYPE
			SYNTAX	INTEGER
			ACCESS	read-only
			STATUS	current
	DESCRIPTION ""
			::= { mbusC1 72 }

mbusC1Value21		OBJECT-TYPE
			SYNTAX	INTEGER
			ACCESS	read-only
			STATUS	current
	DESCRIPTION ""
			::= { mbusC1 73 }

mbusC1VIF22		OBJECT-TYPE
			SYNTAX	INTEGER
			ACCESS	read-only
			STATUS	current
	DESCRIPTION ""
			::= { mbusC1 74 }

mbusC1Value22		OBJECT-TYPE
			SYNTAX	INTEGER
			ACCESS	read-only
			STATUS	current
	DESCRIPTION ""
			::= { mbusC1 75 }

mbusC1VIF23		OBJECT-TYPE
			SYNTAX	INTEGER
			ACCESS	read-only
			STATUS	current
	DESCRIPTION ""
			::= { mbusC1 76 }

mbusC1Value23		OBJECT-TYPE
			SYNTAX	INTEGER
			ACCESS	read-only
			STATUS	current
	DESCRIPTION ""
			::= { mbusC1 77 }

mbusC1VIF24		OBJECT-TYPE
			SYNTAX	INTEGER
			ACCESS	read-only
			STATUS	current
	DESCRIPTION ""
			::= { mbusC1 78 }

mbusC1Value24		OBJECT-TYPE
			SYNTAX	INTEGER
			ACCESS	read-only
			STATUS	current
	DESCRIPTION ""
			::= { mbusC1 79 }

mbusC1VIF25		OBJECT-TYPE
			SYNTAX	INTEGER
			ACCESS	read-only
			STATUS	current
	DESCRIPTION ""
			::= { mbusC1 80 }

mbusC1Value25		OBJECT-TYPE
			SYNTAX	INTEGER
			ACCESS	read-only
			STATUS	current
	DESCRIPTION ""
			::= { mbusC1 81 }

mbusC1VIF26		OBJECT-TYPE
			SYNTAX	INTEGER
			ACCESS	read-only
			STATUS	current
	DESCRIPTION ""
			::= { mbusC1 82 }

mbusC1Value26		OBJECT-TYPE
			SYNTAX	INTEGER
			ACCESS	read-only
			STATUS	current
	DESCRIPTION ""
			::= { mbusC1 83 }

mbusC1VIF27		OBJECT-TYPE
			SYNTAX	INTEGER
			ACCESS	read-only
			STATUS	current
	DESCRIPTION ""
			::= { mbusC1 84 }

mbusC1Value27		OBJECT-TYPE
			SYNTAX	INTEGER
			ACCESS	read-only
			STATUS	current
	DESCRIPTION ""
			::= { mbusC1 85 }

mbusC1VIF28		OBJECT-TYPE
			SYNTAX	INTEGER
			ACCESS	read-only
			STATUS	current
	DESCRIPTION ""
			::= { mbusC1 86 }

mbusC1Value28		OBJECT-TYPE
			SYNTAX	INTEGER
			ACCESS	read-only
			STATUS	current
	DESCRIPTION ""
			::= { mbusC1 87 }

mbusC1VIF29		OBJECT-TYPE
			SYNTAX	INTEGER
			ACCESS	read-only
			STATUS	current
	DESCRIPTION ""
			::= { mbusC1 88 }

mbusC1Value29		OBJECT-TYPE
			SYNTAX	INTEGER
			ACCESS	read-only
			STATUS	current
	DESCRIPTION ""
			::= { mbusC1 89 }

mbusC1VIF2A		OBJECT-TYPE
			SYNTAX	INTEGER
			ACCESS	read-only
			STATUS	current
	DESCRIPTION ""
			::= { mbusC1 90 }

mbusC1Value2A		OBJECT-TYPE
			SYNTAX	INTEGER
			ACCESS	read-only
			STATUS	current
	DESCRIPTION ""
			::= { mbusC1 91 }

mbusC1VIF2B		OBJECT-TYPE
			SYNTAX	INTEGER
			ACCESS	read-only
			STATUS	current
	DESCRIPTION ""
			::= { mbusC1 92 }

mbusC1Value2B		OBJECT-TYPE
			SYNTAX	INTEGER
			ACCESS	read-only
			STATUS	current
	DESCRIPTION ""
			::= { mbusC1 93 }

mbusC1VIF2C		OBJECT-TYPE
			SYNTAX	INTEGER
			ACCESS	read-only
			STATUS	current
	DESCRIPTION ""
			::= { mbusC1 94 }

mbusC1Value2C		OBJECT-TYPE
			SYNTAX	INTEGER
			ACCESS	read-only
			STATUS	current
	DESCRIPTION ""
			::= { mbusC1 95 }

mbusC1VIF2D		OBJECT-TYPE
			SYNTAX	INTEGER
			ACCESS	read-only
			STATUS	current
	DESCRIPTION ""
			::= { mbusC1 96 }

mbusC1Value2D		OBJECT-TYPE
			SYNTAX	INTEGER
			ACCESS	read-only
			STATUS	current
	DESCRIPTION ""
			::= { mbusC1 97 }

mbusC1VIF2E		OBJECT-TYPE
			SYNTAX	INTEGER
			ACCESS	read-only
			STATUS	current
	DESCRIPTION ""
			::= { mbusC1 98 }

mbusC1Value2E		OBJECT-TYPE
			SYNTAX	INTEGER
			ACCESS	read-only
			STATUS	current
	DESCRIPTION ""
			::= { mbusC1 99 }

mbusC1VIF2F		OBJECT-TYPE
			SYNTAX	INTEGER
			ACCESS	read-only
			STATUS	current
	DESCRIPTION ""
			::= { mbusC1 100 }

mbusC1Value2F		OBJECT-TYPE
			SYNTAX	INTEGER
			ACCESS	read-only
			STATUS	current
	DESCRIPTION ""
			::= { mbusC1 101 }

mbusC2			OBJECT IDENTIFIER ::= { mbus 194 }

mbusC2IdNumber		OBJECT-TYPE
			SYNTAX	Gauge
			ACCESS	read-only
			STATUS	current
	DESCRIPTION ""
			::= { mbusC2 1 }

mbusC2Manufacturer	OBJECT-TYPE
			SYNTAX	Gauge
			ACCESS	read-only
			STATUS	current
	DESCRIPTION ""
			::= { mbusC2 2 }

mbusC2Version		OBJECT-TYPE
			SYNTAX	Gauge
			ACCESS	read-only
			STATUS	current
	DESCRIPTION ""
			::= { mbusC2 3 }

mbusC2Medium		OBJECT-TYPE
			SYNTAX	Gauge
			ACCESS	read-only
			STATUS	current
	DESCRIPTION ""
			::= { mbusC2 4 }

mbusC2Status		OBJECT-TYPE
			SYNTAX	Gauge
			ACCESS	read-only
			STATUS	current
	DESCRIPTION ""
			::= { mbusC2 5 }

mbusC2VIF00		OBJECT-TYPE
			SYNTAX	INTEGER
			ACCESS	read-only
			STATUS	current
	DESCRIPTION ""
			::= { mbusC2 6 }

mbusC2Value00		OBJECT-TYPE
			SYNTAX	INTEGER
			ACCESS	read-only
			STATUS	current
	DESCRIPTION ""
			::= { mbusC2 7 }

mbusC2VIF01		OBJECT-TYPE
			SYNTAX	INTEGER
			ACCESS	read-only
			STATUS	current
	DESCRIPTION ""
			::= { mbusC2 8 }

mbusC2Value01		OBJECT-TYPE
			SYNTAX	INTEGER
			ACCESS	read-only
			STATUS	current
	DESCRIPTION ""
			::= { mbusC2 9 }

mbusC2VIF02		OBJECT-TYPE
			SYNTAX	INTEGER
			ACCESS	read-only
			STATUS	current
	DESCRIPTION ""
			::= { mbusC2 10 }

mbusC2Value02		OBJECT-TYPE
			SYNTAX	INTEGER
			ACCESS	read-only
			STATUS	current
	DESCRIPTION ""
			::= { mbusC2 11 }

mbusC2VIF03		OBJECT-TYPE
			SYNTAX	INTEGER
			ACCESS	read-only
			STATUS	current
	DESCRIPTION ""
			::= { mbusC2 12 }

mbusC2Value03		OBJECT-TYPE
			SYNTAX	INTEGER
			ACCESS	read-only
			STATUS	current
	DESCRIPTION ""
			::= { mbusC2 13 }

mbusC2VIF04		OBJECT-TYPE
			SYNTAX	INTEGER
			ACCESS	read-only
			STATUS	current
	DESCRIPTION ""
			::= { mbusC2 14 }

mbusC2Value04		OBJECT-TYPE
			SYNTAX	INTEGER
			ACCESS	read-only
			STATUS	current
	DESCRIPTION ""
			::= { mbusC2 15 }

mbusC2VIF05		OBJECT-TYPE
			SYNTAX	INTEGER
			ACCESS	read-only
			STATUS	current
	DESCRIPTION ""
			::= { mbusC2 16 }

mbusC2Value05		OBJECT-TYPE
			SYNTAX	INTEGER
			ACCESS	read-only
			STATUS	current
	DESCRIPTION ""
			::= { mbusC2 17 }

mbusC2VIF06		OBJECT-TYPE
			SYNTAX	INTEGER
			ACCESS	read-only
			STATUS	current
	DESCRIPTION ""
			::= { mbusC2 18 }

mbusC2Value06		OBJECT-TYPE
			SYNTAX	INTEGER
			ACCESS	read-only
			STATUS	current
	DESCRIPTION ""
			::= { mbusC2 19 }

mbusC2VIF07		OBJECT-TYPE
			SYNTAX	INTEGER
			ACCESS	read-only
			STATUS	current
	DESCRIPTION ""
			::= { mbusC2 20 }

mbusC2Value07		OBJECT-TYPE
			SYNTAX	INTEGER
			ACCESS	read-only
			STATUS	current
	DESCRIPTION ""
			::= { mbusC2 21 }

mbusC2VIF08		OBJECT-TYPE
			SYNTAX	INTEGER
			ACCESS	read-only
			STATUS	current
	DESCRIPTION ""
			::= { mbusC2 22 }

mbusC2Value08		OBJECT-TYPE
			SYNTAX	INTEGER
			ACCESS	read-only
			STATUS	current
	DESCRIPTION ""
			::= { mbusC2 23 }

mbusC2VIF09		OBJECT-TYPE
			SYNTAX	INTEGER
			ACCESS	read-only
			STATUS	current
	DESCRIPTION ""
			::= { mbusC2 24 }

mbusC2Value09		OBJECT-TYPE
			SYNTAX	INTEGER
			ACCESS	read-only
			STATUS	current
	DESCRIPTION ""
			::= { mbusC2 25 }

mbusC2VIF0A		OBJECT-TYPE
			SYNTAX	INTEGER
			ACCESS	read-only
			STATUS	current
	DESCRIPTION ""
			::= { mbusC2 26 }

mbusC2Value0A		OBJECT-TYPE
			SYNTAX	INTEGER
			ACCESS	read-only
			STATUS	current
	DESCRIPTION ""
			::= { mbusC2 27 }

mbusC2VIF0B		OBJECT-TYPE
			SYNTAX	INTEGER
			ACCESS	read-only
			STATUS	current
	DESCRIPTION ""
			::= { mbusC2 28 }

mbusC2Value0B		OBJECT-TYPE
			SYNTAX	INTEGER
			ACCESS	read-only
			STATUS	current
	DESCRIPTION ""
			::= { mbusC2 29 }

mbusC2VIF0C		OBJECT-TYPE
			SYNTAX	INTEGER
			ACCESS	read-only
			STATUS	current
	DESCRIPTION ""
			::= { mbusC2 30 }

mbusC2Value0C		OBJECT-TYPE
			SYNTAX	INTEGER
			ACCESS	read-only
			STATUS	current
	DESCRIPTION ""
			::= { mbusC2 31 }

mbusC2VIF0D		OBJECT-TYPE
			SYNTAX	INTEGER
			ACCESS	read-only
			STATUS	current
	DESCRIPTION ""
			::= { mbusC2 32 }

mbusC2Value0D		OBJECT-TYPE
			SYNTAX	INTEGER
			ACCESS	read-only
			STATUS	current
	DESCRIPTION ""
			::= { mbusC2 33 }

mbusC2VIF0E		OBJECT-TYPE
			SYNTAX	INTEGER
			ACCESS	read-only
			STATUS	current
	DESCRIPTION ""
			::= { mbusC2 34 }

mbusC2Value0E		OBJECT-TYPE
			SYNTAX	INTEGER
			ACCESS	read-only
			STATUS	current
	DESCRIPTION ""
			::= { mbusC2 35 }

mbusC2VIF0F		OBJECT-TYPE
			SYNTAX	INTEGER
			ACCESS	read-only
			STATUS	current
	DESCRIPTION ""
			::= { mbusC2 36 }

mbusC2Value0F		OBJECT-TYPE
			SYNTAX	INTEGER
			ACCESS	read-only
			STATUS	current
	DESCRIPTION ""
			::= { mbusC2 37 }

mbusC2VIF10		OBJECT-TYPE
			SYNTAX	INTEGER
			ACCESS	read-only
			STATUS	current
	DESCRIPTION ""
			::= { mbusC2 38 }

mbusC2Value10		OBJECT-TYPE
			SYNTAX	INTEGER
			ACCESS	read-only
			STATUS	current
	DESCRIPTION ""
			::= { mbusC2 39 }

mbusC2VIF11		OBJECT-TYPE
			SYNTAX	INTEGER
			ACCESS	read-only
			STATUS	current
	DESCRIPTION ""
			::= { mbusC2 40 }

mbusC2Value11		OBJECT-TYPE
			SYNTAX	INTEGER
			ACCESS	read-only
			STATUS	current
	DESCRIPTION ""
			::= { mbusC2 41 }

mbusC2VIF12		OBJECT-TYPE
			SYNTAX	INTEGER
			ACCESS	read-only
			STATUS	current
	DESCRIPTION ""
			::= { mbusC2 42 }

mbusC2Value12		OBJECT-TYPE
			SYNTAX	INTEGER
			ACCESS	read-only
			STATUS	current
	DESCRIPTION ""
			::= { mbusC2 43 }

mbusC2VIF13		OBJECT-TYPE
			SYNTAX	INTEGER
			ACCESS	read-only
			STATUS	current
	DESCRIPTION ""
			::= { mbusC2 44 }

mbusC2Value13		OBJECT-TYPE
			SYNTAX	INTEGER
			ACCESS	read-only
			STATUS	current
	DESCRIPTION ""
			::= { mbusC2 45 }

mbusC2VIF14		OBJECT-TYPE
			SYNTAX	INTEGER
			ACCESS	read-only
			STATUS	current
	DESCRIPTION ""
			::= { mbusC2 46 }

mbusC2Value14		OBJECT-TYPE
			SYNTAX	INTEGER
			ACCESS	read-only
			STATUS	current
	DESCRIPTION ""
			::= { mbusC2 47 }

mbusC2VIF15		OBJECT-TYPE
			SYNTAX	INTEGER
			ACCESS	read-only
			STATUS	current
	DESCRIPTION ""
			::= { mbusC2 48 }

mbusC2Value15		OBJECT-TYPE
			SYNTAX	INTEGER
			ACCESS	read-only
			STATUS	current
	DESCRIPTION ""
			::= { mbusC2 49 }

mbusC2VIF16		OBJECT-TYPE
			SYNTAX	INTEGER
			ACCESS	read-only
			STATUS	current
	DESCRIPTION ""
			::= { mbusC2 50 }

mbusC2Value16		OBJECT-TYPE
			SYNTAX	INTEGER
			ACCESS	read-only
			STATUS	current
	DESCRIPTION ""
			::= { mbusC2 51 }

mbusC2VIF17		OBJECT-TYPE
			SYNTAX	INTEGER
			ACCESS	read-only
			STATUS	current
	DESCRIPTION ""
			::= { mbusC2 52 }

mbusC2Value17		OBJECT-TYPE
			SYNTAX	INTEGER
			ACCESS	read-only
			STATUS	current
	DESCRIPTION ""
			::= { mbusC2 53 }

mbusC2VIF18		OBJECT-TYPE
			SYNTAX	INTEGER
			ACCESS	read-only
			STATUS	current
	DESCRIPTION ""
			::= { mbusC2 54 }

mbusC2Value18		OBJECT-TYPE
			SYNTAX	INTEGER
			ACCESS	read-only
			STATUS	current
	DESCRIPTION ""
			::= { mbusC2 55 }

mbusC2VIF19		OBJECT-TYPE
			SYNTAX	INTEGER
			ACCESS	read-only
			STATUS	current
	DESCRIPTION ""
			::= { mbusC2 56 }

mbusC2Value19		OBJECT-TYPE
			SYNTAX	INTEGER
			ACCESS	read-only
			STATUS	current
	DESCRIPTION ""
			::= { mbusC2 57 }

mbusC2VIF1A		OBJECT-TYPE
			SYNTAX	INTEGER
			ACCESS	read-only
			STATUS	current
	DESCRIPTION ""
			::= { mbusC2 58 }

mbusC2Value1A		OBJECT-TYPE
			SYNTAX	INTEGER
			ACCESS	read-only
			STATUS	current
	DESCRIPTION ""
			::= { mbusC2 59 }

mbusC2VIF1B		OBJECT-TYPE
			SYNTAX	INTEGER
			ACCESS	read-only
			STATUS	current
	DESCRIPTION ""
			::= { mbusC2 60 }

mbusC2Value1B		OBJECT-TYPE
			SYNTAX	INTEGER
			ACCESS	read-only
			STATUS	current
	DESCRIPTION ""
			::= { mbusC2 61 }

mbusC2VIF1C		OBJECT-TYPE
			SYNTAX	INTEGER
			ACCESS	read-only
			STATUS	current
	DESCRIPTION ""
			::= { mbusC2 62 }

mbusC2Value1C		OBJECT-TYPE
			SYNTAX	INTEGER
			ACCESS	read-only
			STATUS	current
	DESCRIPTION ""
			::= { mbusC2 63 }

mbusC2VIF1D		OBJECT-TYPE
			SYNTAX	INTEGER
			ACCESS	read-only
			STATUS	current
	DESCRIPTION ""
			::= { mbusC2 64 }

mbusC2Value1D		OBJECT-TYPE
			SYNTAX	INTEGER
			ACCESS	read-only
			STATUS	current
	DESCRIPTION ""
			::= { mbusC2 65 }

mbusC2VIF1E		OBJECT-TYPE
			SYNTAX	INTEGER
			ACCESS	read-only
			STATUS	current
	DESCRIPTION ""
			::= { mbusC2 66 }

mbusC2Value1E		OBJECT-TYPE
			SYNTAX	INTEGER
			ACCESS	read-only
			STATUS	current
	DESCRIPTION ""
			::= { mbusC2 67 }

mbusC2VIF1F		OBJECT-TYPE
			SYNTAX	INTEGER
			ACCESS	read-only
			STATUS	current
	DESCRIPTION ""
			::= { mbusC2 68 }

mbusC2Value1F		OBJECT-TYPE
			SYNTAX	INTEGER
			ACCESS	read-only
			STATUS	current
	DESCRIPTION ""
			::= { mbusC2 69 }

mbusC2VIF20		OBJECT-TYPE
			SYNTAX	INTEGER
			ACCESS	read-only
			STATUS	current
	DESCRIPTION ""
			::= { mbusC2 70 }

mbusC2Value20		OBJECT-TYPE
			SYNTAX	INTEGER
			ACCESS	read-only
			STATUS	current
	DESCRIPTION ""
			::= { mbusC2 71 }

mbusC2VIF21		OBJECT-TYPE
			SYNTAX	INTEGER
			ACCESS	read-only
			STATUS	current
	DESCRIPTION ""
			::= { mbusC2 72 }

mbusC2Value21		OBJECT-TYPE
			SYNTAX	INTEGER
			ACCESS	read-only
			STATUS	current
	DESCRIPTION ""
			::= { mbusC2 73 }

mbusC2VIF22		OBJECT-TYPE
			SYNTAX	INTEGER
			ACCESS	read-only
			STATUS	current
	DESCRIPTION ""
			::= { mbusC2 74 }

mbusC2Value22		OBJECT-TYPE
			SYNTAX	INTEGER
			ACCESS	read-only
			STATUS	current
	DESCRIPTION ""
			::= { mbusC2 75 }

mbusC2VIF23		OBJECT-TYPE
			SYNTAX	INTEGER
			ACCESS	read-only
			STATUS	current
	DESCRIPTION ""
			::= { mbusC2 76 }

mbusC2Value23		OBJECT-TYPE
			SYNTAX	INTEGER
			ACCESS	read-only
			STATUS	current
	DESCRIPTION ""
			::= { mbusC2 77 }

mbusC2VIF24		OBJECT-TYPE
			SYNTAX	INTEGER
			ACCESS	read-only
			STATUS	current
	DESCRIPTION ""
			::= { mbusC2 78 }

mbusC2Value24		OBJECT-TYPE
			SYNTAX	INTEGER
			ACCESS	read-only
			STATUS	current
	DESCRIPTION ""
			::= { mbusC2 79 }

mbusC2VIF25		OBJECT-TYPE
			SYNTAX	INTEGER
			ACCESS	read-only
			STATUS	current
	DESCRIPTION ""
			::= { mbusC2 80 }

mbusC2Value25		OBJECT-TYPE
			SYNTAX	INTEGER
			ACCESS	read-only
			STATUS	current
	DESCRIPTION ""
			::= { mbusC2 81 }

mbusC2VIF26		OBJECT-TYPE
			SYNTAX	INTEGER
			ACCESS	read-only
			STATUS	current
	DESCRIPTION ""
			::= { mbusC2 82 }

mbusC2Value26		OBJECT-TYPE
			SYNTAX	INTEGER
			ACCESS	read-only
			STATUS	current
	DESCRIPTION ""
			::= { mbusC2 83 }

mbusC2VIF27		OBJECT-TYPE
			SYNTAX	INTEGER
			ACCESS	read-only
			STATUS	current
	DESCRIPTION ""
			::= { mbusC2 84 }

mbusC2Value27		OBJECT-TYPE
			SYNTAX	INTEGER
			ACCESS	read-only
			STATUS	current
	DESCRIPTION ""
			::= { mbusC2 85 }

mbusC2VIF28		OBJECT-TYPE
			SYNTAX	INTEGER
			ACCESS	read-only
			STATUS	current
	DESCRIPTION ""
			::= { mbusC2 86 }

mbusC2Value28		OBJECT-TYPE
			SYNTAX	INTEGER
			ACCESS	read-only
			STATUS	current
	DESCRIPTION ""
			::= { mbusC2 87 }

mbusC2VIF29		OBJECT-TYPE
			SYNTAX	INTEGER
			ACCESS	read-only
			STATUS	current
	DESCRIPTION ""
			::= { mbusC2 88 }

mbusC2Value29		OBJECT-TYPE
			SYNTAX	INTEGER
			ACCESS	read-only
			STATUS	current
	DESCRIPTION ""
			::= { mbusC2 89 }

mbusC2VIF2A		OBJECT-TYPE
			SYNTAX	INTEGER
			ACCESS	read-only
			STATUS	current
	DESCRIPTION ""
			::= { mbusC2 90 }

mbusC2Value2A		OBJECT-TYPE
			SYNTAX	INTEGER
			ACCESS	read-only
			STATUS	current
	DESCRIPTION ""
			::= { mbusC2 91 }

mbusC2VIF2B		OBJECT-TYPE
			SYNTAX	INTEGER
			ACCESS	read-only
			STATUS	current
	DESCRIPTION ""
			::= { mbusC2 92 }

mbusC2Value2B		OBJECT-TYPE
			SYNTAX	INTEGER
			ACCESS	read-only
			STATUS	current
	DESCRIPTION ""
			::= { mbusC2 93 }

mbusC2VIF2C		OBJECT-TYPE
			SYNTAX	INTEGER
			ACCESS	read-only
			STATUS	current
	DESCRIPTION ""
			::= { mbusC2 94 }

mbusC2Value2C		OBJECT-TYPE
			SYNTAX	INTEGER
			ACCESS	read-only
			STATUS	current
	DESCRIPTION ""
			::= { mbusC2 95 }

mbusC2VIF2D		OBJECT-TYPE
			SYNTAX	INTEGER
			ACCESS	read-only
			STATUS	current
	DESCRIPTION ""
			::= { mbusC2 96 }

mbusC2Value2D		OBJECT-TYPE
			SYNTAX	INTEGER
			ACCESS	read-only
			STATUS	current
	DESCRIPTION ""
			::= { mbusC2 97 }

mbusC2VIF2E		OBJECT-TYPE
			SYNTAX	INTEGER
			ACCESS	read-only
			STATUS	current
	DESCRIPTION ""
			::= { mbusC2 98 }

mbusC2Value2E		OBJECT-TYPE
			SYNTAX	INTEGER
			ACCESS	read-only
			STATUS	current
	DESCRIPTION ""
			::= { mbusC2 99 }

mbusC2VIF2F		OBJECT-TYPE
			SYNTAX	INTEGER
			ACCESS	read-only
			STATUS	current
	DESCRIPTION ""
			::= { mbusC2 100 }

mbusC2Value2F		OBJECT-TYPE
			SYNTAX	INTEGER
			ACCESS	read-only
			STATUS	current
	DESCRIPTION ""
			::= { mbusC2 101 }

mbusC3			OBJECT IDENTIFIER ::= { mbus 195 }

mbusC3IdNumber		OBJECT-TYPE
			SYNTAX	Gauge
			ACCESS	read-only
			STATUS	current
	DESCRIPTION ""
			::= { mbusC3 1 }

mbusC3Manufacturer	OBJECT-TYPE
			SYNTAX	Gauge
			ACCESS	read-only
			STATUS	current
	DESCRIPTION ""
			::= { mbusC3 2 }

mbusC3Version		OBJECT-TYPE
			SYNTAX	Gauge
			ACCESS	read-only
			STATUS	current
	DESCRIPTION ""
			::= { mbusC3 3 }

mbusC3Medium		OBJECT-TYPE
			SYNTAX	Gauge
			ACCESS	read-only
			STATUS	current
	DESCRIPTION ""
			::= { mbusC3 4 }

mbusC3Status		OBJECT-TYPE
			SYNTAX	Gauge
			ACCESS	read-only
			STATUS	current
	DESCRIPTION ""
			::= { mbusC3 5 }

mbusC3VIF00		OBJECT-TYPE
			SYNTAX	INTEGER
			ACCESS	read-only
			STATUS	current
	DESCRIPTION ""
			::= { mbusC3 6 }

mbusC3Value00		OBJECT-TYPE
			SYNTAX	INTEGER
			ACCESS	read-only
			STATUS	current
	DESCRIPTION ""
			::= { mbusC3 7 }

mbusC3VIF01		OBJECT-TYPE
			SYNTAX	INTEGER
			ACCESS	read-only
			STATUS	current
	DESCRIPTION ""
			::= { mbusC3 8 }

mbusC3Value01		OBJECT-TYPE
			SYNTAX	INTEGER
			ACCESS	read-only
			STATUS	current
	DESCRIPTION ""
			::= { mbusC3 9 }

mbusC3VIF02		OBJECT-TYPE
			SYNTAX	INTEGER
			ACCESS	read-only
			STATUS	current
	DESCRIPTION ""
			::= { mbusC3 10 }

mbusC3Value02		OBJECT-TYPE
			SYNTAX	INTEGER
			ACCESS	read-only
			STATUS	current
	DESCRIPTION ""
			::= { mbusC3 11 }

mbusC3VIF03		OBJECT-TYPE
			SYNTAX	INTEGER
			ACCESS	read-only
			STATUS	current
	DESCRIPTION ""
			::= { mbusC3 12 }

mbusC3Value03		OBJECT-TYPE
			SYNTAX	INTEGER
			ACCESS	read-only
			STATUS	current
	DESCRIPTION ""
			::= { mbusC3 13 }

mbusC3VIF04		OBJECT-TYPE
			SYNTAX	INTEGER
			ACCESS	read-only
			STATUS	current
	DESCRIPTION ""
			::= { mbusC3 14 }

mbusC3Value04		OBJECT-TYPE
			SYNTAX	INTEGER
			ACCESS	read-only
			STATUS	current
	DESCRIPTION ""
			::= { mbusC3 15 }

mbusC3VIF05		OBJECT-TYPE
			SYNTAX	INTEGER
			ACCESS	read-only
			STATUS	current
	DESCRIPTION ""
			::= { mbusC3 16 }

mbusC3Value05		OBJECT-TYPE
			SYNTAX	INTEGER
			ACCESS	read-only
			STATUS	current
	DESCRIPTION ""
			::= { mbusC3 17 }

mbusC3VIF06		OBJECT-TYPE
			SYNTAX	INTEGER
			ACCESS	read-only
			STATUS	current
	DESCRIPTION ""
			::= { mbusC3 18 }

mbusC3Value06		OBJECT-TYPE
			SYNTAX	INTEGER
			ACCESS	read-only
			STATUS	current
	DESCRIPTION ""
			::= { mbusC3 19 }

mbusC3VIF07		OBJECT-TYPE
			SYNTAX	INTEGER
			ACCESS	read-only
			STATUS	current
	DESCRIPTION ""
			::= { mbusC3 20 }

mbusC3Value07		OBJECT-TYPE
			SYNTAX	INTEGER
			ACCESS	read-only
			STATUS	current
	DESCRIPTION ""
			::= { mbusC3 21 }

mbusC3VIF08		OBJECT-TYPE
			SYNTAX	INTEGER
			ACCESS	read-only
			STATUS	current
	DESCRIPTION ""
			::= { mbusC3 22 }

mbusC3Value08		OBJECT-TYPE
			SYNTAX	INTEGER
			ACCESS	read-only
			STATUS	current
	DESCRIPTION ""
			::= { mbusC3 23 }

mbusC3VIF09		OBJECT-TYPE
			SYNTAX	INTEGER
			ACCESS	read-only
			STATUS	current
	DESCRIPTION ""
			::= { mbusC3 24 }

mbusC3Value09		OBJECT-TYPE
			SYNTAX	INTEGER
			ACCESS	read-only
			STATUS	current
	DESCRIPTION ""
			::= { mbusC3 25 }

mbusC3VIF0A		OBJECT-TYPE
			SYNTAX	INTEGER
			ACCESS	read-only
			STATUS	current
	DESCRIPTION ""
			::= { mbusC3 26 }

mbusC3Value0A		OBJECT-TYPE
			SYNTAX	INTEGER
			ACCESS	read-only
			STATUS	current
	DESCRIPTION ""
			::= { mbusC3 27 }

mbusC3VIF0B		OBJECT-TYPE
			SYNTAX	INTEGER
			ACCESS	read-only
			STATUS	current
	DESCRIPTION ""
			::= { mbusC3 28 }

mbusC3Value0B		OBJECT-TYPE
			SYNTAX	INTEGER
			ACCESS	read-only
			STATUS	current
	DESCRIPTION ""
			::= { mbusC3 29 }

mbusC3VIF0C		OBJECT-TYPE
			SYNTAX	INTEGER
			ACCESS	read-only
			STATUS	current
	DESCRIPTION ""
			::= { mbusC3 30 }

mbusC3Value0C		OBJECT-TYPE
			SYNTAX	INTEGER
			ACCESS	read-only
			STATUS	current
	DESCRIPTION ""
			::= { mbusC3 31 }

mbusC3VIF0D		OBJECT-TYPE
			SYNTAX	INTEGER
			ACCESS	read-only
			STATUS	current
	DESCRIPTION ""
			::= { mbusC3 32 }

mbusC3Value0D		OBJECT-TYPE
			SYNTAX	INTEGER
			ACCESS	read-only
			STATUS	current
	DESCRIPTION ""
			::= { mbusC3 33 }

mbusC3VIF0E		OBJECT-TYPE
			SYNTAX	INTEGER
			ACCESS	read-only
			STATUS	current
	DESCRIPTION ""
			::= { mbusC3 34 }

mbusC3Value0E		OBJECT-TYPE
			SYNTAX	INTEGER
			ACCESS	read-only
			STATUS	current
	DESCRIPTION ""
			::= { mbusC3 35 }

mbusC3VIF0F		OBJECT-TYPE
			SYNTAX	INTEGER
			ACCESS	read-only
			STATUS	current
	DESCRIPTION ""
			::= { mbusC3 36 }

mbusC3Value0F		OBJECT-TYPE
			SYNTAX	INTEGER
			ACCESS	read-only
			STATUS	current
	DESCRIPTION ""
			::= { mbusC3 37 }

mbusC3VIF10		OBJECT-TYPE
			SYNTAX	INTEGER
			ACCESS	read-only
			STATUS	current
	DESCRIPTION ""
			::= { mbusC3 38 }

mbusC3Value10		OBJECT-TYPE
			SYNTAX	INTEGER
			ACCESS	read-only
			STATUS	current
	DESCRIPTION ""
			::= { mbusC3 39 }

mbusC3VIF11		OBJECT-TYPE
			SYNTAX	INTEGER
			ACCESS	read-only
			STATUS	current
	DESCRIPTION ""
			::= { mbusC3 40 }

mbusC3Value11		OBJECT-TYPE
			SYNTAX	INTEGER
			ACCESS	read-only
			STATUS	current
	DESCRIPTION ""
			::= { mbusC3 41 }

mbusC3VIF12		OBJECT-TYPE
			SYNTAX	INTEGER
			ACCESS	read-only
			STATUS	current
	DESCRIPTION ""
			::= { mbusC3 42 }

mbusC3Value12		OBJECT-TYPE
			SYNTAX	INTEGER
			ACCESS	read-only
			STATUS	current
	DESCRIPTION ""
			::= { mbusC3 43 }

mbusC3VIF13		OBJECT-TYPE
			SYNTAX	INTEGER
			ACCESS	read-only
			STATUS	current
	DESCRIPTION ""
			::= { mbusC3 44 }

mbusC3Value13		OBJECT-TYPE
			SYNTAX	INTEGER
			ACCESS	read-only
			STATUS	current
	DESCRIPTION ""
			::= { mbusC3 45 }

mbusC3VIF14		OBJECT-TYPE
			SYNTAX	INTEGER
			ACCESS	read-only
			STATUS	current
	DESCRIPTION ""
			::= { mbusC3 46 }

mbusC3Value14		OBJECT-TYPE
			SYNTAX	INTEGER
			ACCESS	read-only
			STATUS	current
	DESCRIPTION ""
			::= { mbusC3 47 }

mbusC3VIF15		OBJECT-TYPE
			SYNTAX	INTEGER
			ACCESS	read-only
			STATUS	current
	DESCRIPTION ""
			::= { mbusC3 48 }

mbusC3Value15		OBJECT-TYPE
			SYNTAX	INTEGER
			ACCESS	read-only
			STATUS	current
	DESCRIPTION ""
			::= { mbusC3 49 }

mbusC3VIF16		OBJECT-TYPE
			SYNTAX	INTEGER
			ACCESS	read-only
			STATUS	current
	DESCRIPTION ""
			::= { mbusC3 50 }

mbusC3Value16		OBJECT-TYPE
			SYNTAX	INTEGER
			ACCESS	read-only
			STATUS	current
	DESCRIPTION ""
			::= { mbusC3 51 }

mbusC3VIF17		OBJECT-TYPE
			SYNTAX	INTEGER
			ACCESS	read-only
			STATUS	current
	DESCRIPTION ""
			::= { mbusC3 52 }

mbusC3Value17		OBJECT-TYPE
			SYNTAX	INTEGER
			ACCESS	read-only
			STATUS	current
	DESCRIPTION ""
			::= { mbusC3 53 }

mbusC3VIF18		OBJECT-TYPE
			SYNTAX	INTEGER
			ACCESS	read-only
			STATUS	current
	DESCRIPTION ""
			::= { mbusC3 54 }

mbusC3Value18		OBJECT-TYPE
			SYNTAX	INTEGER
			ACCESS	read-only
			STATUS	current
	DESCRIPTION ""
			::= { mbusC3 55 }

mbusC3VIF19		OBJECT-TYPE
			SYNTAX	INTEGER
			ACCESS	read-only
			STATUS	current
	DESCRIPTION ""
			::= { mbusC3 56 }

mbusC3Value19		OBJECT-TYPE
			SYNTAX	INTEGER
			ACCESS	read-only
			STATUS	current
	DESCRIPTION ""
			::= { mbusC3 57 }

mbusC3VIF1A		OBJECT-TYPE
			SYNTAX	INTEGER
			ACCESS	read-only
			STATUS	current
	DESCRIPTION ""
			::= { mbusC3 58 }

mbusC3Value1A		OBJECT-TYPE
			SYNTAX	INTEGER
			ACCESS	read-only
			STATUS	current
	DESCRIPTION ""
			::= { mbusC3 59 }

mbusC3VIF1B		OBJECT-TYPE
			SYNTAX	INTEGER
			ACCESS	read-only
			STATUS	current
	DESCRIPTION ""
			::= { mbusC3 60 }

mbusC3Value1B		OBJECT-TYPE
			SYNTAX	INTEGER
			ACCESS	read-only
			STATUS	current
	DESCRIPTION ""
			::= { mbusC3 61 }

mbusC3VIF1C		OBJECT-TYPE
			SYNTAX	INTEGER
			ACCESS	read-only
			STATUS	current
	DESCRIPTION ""
			::= { mbusC3 62 }

mbusC3Value1C		OBJECT-TYPE
			SYNTAX	INTEGER
			ACCESS	read-only
			STATUS	current
	DESCRIPTION ""
			::= { mbusC3 63 }

mbusC3VIF1D		OBJECT-TYPE
			SYNTAX	INTEGER
			ACCESS	read-only
			STATUS	current
	DESCRIPTION ""
			::= { mbusC3 64 }

mbusC3Value1D		OBJECT-TYPE
			SYNTAX	INTEGER
			ACCESS	read-only
			STATUS	current
	DESCRIPTION ""
			::= { mbusC3 65 }

mbusC3VIF1E		OBJECT-TYPE
			SYNTAX	INTEGER
			ACCESS	read-only
			STATUS	current
	DESCRIPTION ""
			::= { mbusC3 66 }

mbusC3Value1E		OBJECT-TYPE
			SYNTAX	INTEGER
			ACCESS	read-only
			STATUS	current
	DESCRIPTION ""
			::= { mbusC3 67 }

mbusC3VIF1F		OBJECT-TYPE
			SYNTAX	INTEGER
			ACCESS	read-only
			STATUS	current
	DESCRIPTION ""
			::= { mbusC3 68 }

mbusC3Value1F		OBJECT-TYPE
			SYNTAX	INTEGER
			ACCESS	read-only
			STATUS	current
	DESCRIPTION ""
			::= { mbusC3 69 }

mbusC3VIF20		OBJECT-TYPE
			SYNTAX	INTEGER
			ACCESS	read-only
			STATUS	current
	DESCRIPTION ""
			::= { mbusC3 70 }

mbusC3Value20		OBJECT-TYPE
			SYNTAX	INTEGER
			ACCESS	read-only
			STATUS	current
	DESCRIPTION ""
			::= { mbusC3 71 }

mbusC3VIF21		OBJECT-TYPE
			SYNTAX	INTEGER
			ACCESS	read-only
			STATUS	current
	DESCRIPTION ""
			::= { mbusC3 72 }

mbusC3Value21		OBJECT-TYPE
			SYNTAX	INTEGER
			ACCESS	read-only
			STATUS	current
	DESCRIPTION ""
			::= { mbusC3 73 }

mbusC3VIF22		OBJECT-TYPE
			SYNTAX	INTEGER
			ACCESS	read-only
			STATUS	current
	DESCRIPTION ""
			::= { mbusC3 74 }

mbusC3Value22		OBJECT-TYPE
			SYNTAX	INTEGER
			ACCESS	read-only
			STATUS	current
	DESCRIPTION ""
			::= { mbusC3 75 }

mbusC3VIF23		OBJECT-TYPE
			SYNTAX	INTEGER
			ACCESS	read-only
			STATUS	current
	DESCRIPTION ""
			::= { mbusC3 76 }

mbusC3Value23		OBJECT-TYPE
			SYNTAX	INTEGER
			ACCESS	read-only
			STATUS	current
	DESCRIPTION ""
			::= { mbusC3 77 }

mbusC3VIF24		OBJECT-TYPE
			SYNTAX	INTEGER
			ACCESS	read-only
			STATUS	current
	DESCRIPTION ""
			::= { mbusC3 78 }

mbusC3Value24		OBJECT-TYPE
			SYNTAX	INTEGER
			ACCESS	read-only
			STATUS	current
	DESCRIPTION ""
			::= { mbusC3 79 }

mbusC3VIF25		OBJECT-TYPE
			SYNTAX	INTEGER
			ACCESS	read-only
			STATUS	current
	DESCRIPTION ""
			::= { mbusC3 80 }

mbusC3Value25		OBJECT-TYPE
			SYNTAX	INTEGER
			ACCESS	read-only
			STATUS	current
	DESCRIPTION ""
			::= { mbusC3 81 }

mbusC3VIF26		OBJECT-TYPE
			SYNTAX	INTEGER
			ACCESS	read-only
			STATUS	current
	DESCRIPTION ""
			::= { mbusC3 82 }

mbusC3Value26		OBJECT-TYPE
			SYNTAX	INTEGER
			ACCESS	read-only
			STATUS	current
	DESCRIPTION ""
			::= { mbusC3 83 }

mbusC3VIF27		OBJECT-TYPE
			SYNTAX	INTEGER
			ACCESS	read-only
			STATUS	current
	DESCRIPTION ""
			::= { mbusC3 84 }

mbusC3Value27		OBJECT-TYPE
			SYNTAX	INTEGER
			ACCESS	read-only
			STATUS	current
	DESCRIPTION ""
			::= { mbusC3 85 }

mbusC3VIF28		OBJECT-TYPE
			SYNTAX	INTEGER
			ACCESS	read-only
			STATUS	current
	DESCRIPTION ""
			::= { mbusC3 86 }

mbusC3Value28		OBJECT-TYPE
			SYNTAX	INTEGER
			ACCESS	read-only
			STATUS	current
	DESCRIPTION ""
			::= { mbusC3 87 }

mbusC3VIF29		OBJECT-TYPE
			SYNTAX	INTEGER
			ACCESS	read-only
			STATUS	current
	DESCRIPTION ""
			::= { mbusC3 88 }

mbusC3Value29		OBJECT-TYPE
			SYNTAX	INTEGER
			ACCESS	read-only
			STATUS	current
	DESCRIPTION ""
			::= { mbusC3 89 }

mbusC3VIF2A		OBJECT-TYPE
			SYNTAX	INTEGER
			ACCESS	read-only
			STATUS	current
	DESCRIPTION ""
			::= { mbusC3 90 }

mbusC3Value2A		OBJECT-TYPE
			SYNTAX	INTEGER
			ACCESS	read-only
			STATUS	current
	DESCRIPTION ""
			::= { mbusC3 91 }

mbusC3VIF2B		OBJECT-TYPE
			SYNTAX	INTEGER
			ACCESS	read-only
			STATUS	current
	DESCRIPTION ""
			::= { mbusC3 92 }

mbusC3Value2B		OBJECT-TYPE
			SYNTAX	INTEGER
			ACCESS	read-only
			STATUS	current
	DESCRIPTION ""
			::= { mbusC3 93 }

mbusC3VIF2C		OBJECT-TYPE
			SYNTAX	INTEGER
			ACCESS	read-only
			STATUS	current
	DESCRIPTION ""
			::= { mbusC3 94 }

mbusC3Value2C		OBJECT-TYPE
			SYNTAX	INTEGER
			ACCESS	read-only
			STATUS	current
	DESCRIPTION ""
			::= { mbusC3 95 }

mbusC3VIF2D		OBJECT-TYPE
			SYNTAX	INTEGER
			ACCESS	read-only
			STATUS	current
	DESCRIPTION ""
			::= { mbusC3 96 }

mbusC3Value2D		OBJECT-TYPE
			SYNTAX	INTEGER
			ACCESS	read-only
			STATUS	current
	DESCRIPTION ""
			::= { mbusC3 97 }

mbusC3VIF2E		OBJECT-TYPE
			SYNTAX	INTEGER
			ACCESS	read-only
			STATUS	current
	DESCRIPTION ""
			::= { mbusC3 98 }

mbusC3Value2E		OBJECT-TYPE
			SYNTAX	INTEGER
			ACCESS	read-only
			STATUS	current
	DESCRIPTION ""
			::= { mbusC3 99 }

mbusC3VIF2F		OBJECT-TYPE
			SYNTAX	INTEGER
			ACCESS	read-only
			STATUS	current
	DESCRIPTION ""
			::= { mbusC3 100 }

mbusC3Value2F		OBJECT-TYPE
			SYNTAX	INTEGER
			ACCESS	read-only
			STATUS	current
	DESCRIPTION ""
			::= { mbusC3 101 }

mbusC4			OBJECT IDENTIFIER ::= { mbus 196 }

mbusC4IdNumber		OBJECT-TYPE
			SYNTAX	Gauge
			ACCESS	read-only
			STATUS	current
	DESCRIPTION ""
			::= { mbusC4 1 }

mbusC4Manufacturer	OBJECT-TYPE
			SYNTAX	Gauge
			ACCESS	read-only
			STATUS	current
	DESCRIPTION ""
			::= { mbusC4 2 }

mbusC4Version		OBJECT-TYPE
			SYNTAX	Gauge
			ACCESS	read-only
			STATUS	current
	DESCRIPTION ""
			::= { mbusC4 3 }

mbusC4Medium		OBJECT-TYPE
			SYNTAX	Gauge
			ACCESS	read-only
			STATUS	current
	DESCRIPTION ""
			::= { mbusC4 4 }

mbusC4Status		OBJECT-TYPE
			SYNTAX	Gauge
			ACCESS	read-only
			STATUS	current
	DESCRIPTION ""
			::= { mbusC4 5 }

mbusC4VIF00		OBJECT-TYPE
			SYNTAX	INTEGER
			ACCESS	read-only
			STATUS	current
	DESCRIPTION ""
			::= { mbusC4 6 }

mbusC4Value00		OBJECT-TYPE
			SYNTAX	INTEGER
			ACCESS	read-only
			STATUS	current
	DESCRIPTION ""
			::= { mbusC4 7 }

mbusC4VIF01		OBJECT-TYPE
			SYNTAX	INTEGER
			ACCESS	read-only
			STATUS	current
	DESCRIPTION ""
			::= { mbusC4 8 }

mbusC4Value01		OBJECT-TYPE
			SYNTAX	INTEGER
			ACCESS	read-only
			STATUS	current
	DESCRIPTION ""
			::= { mbusC4 9 }

mbusC4VIF02		OBJECT-TYPE
			SYNTAX	INTEGER
			ACCESS	read-only
			STATUS	current
	DESCRIPTION ""
			::= { mbusC4 10 }

mbusC4Value02		OBJECT-TYPE
			SYNTAX	INTEGER
			ACCESS	read-only
			STATUS	current
	DESCRIPTION ""
			::= { mbusC4 11 }

mbusC4VIF03		OBJECT-TYPE
			SYNTAX	INTEGER
			ACCESS	read-only
			STATUS	current
	DESCRIPTION ""
			::= { mbusC4 12 }

mbusC4Value03		OBJECT-TYPE
			SYNTAX	INTEGER
			ACCESS	read-only
			STATUS	current
	DESCRIPTION ""
			::= { mbusC4 13 }

mbusC4VIF04		OBJECT-TYPE
			SYNTAX	INTEGER
			ACCESS	read-only
			STATUS	current
	DESCRIPTION ""
			::= { mbusC4 14 }

mbusC4Value04		OBJECT-TYPE
			SYNTAX	INTEGER
			ACCESS	read-only
			STATUS	current
	DESCRIPTION ""
			::= { mbusC4 15 }

mbusC4VIF05		OBJECT-TYPE
			SYNTAX	INTEGER
			ACCESS	read-only
			STATUS	current
	DESCRIPTION ""
			::= { mbusC4 16 }

mbusC4Value05		OBJECT-TYPE
			SYNTAX	INTEGER
			ACCESS	read-only
			STATUS	current
	DESCRIPTION ""
			::= { mbusC4 17 }

mbusC4VIF06		OBJECT-TYPE
			SYNTAX	INTEGER
			ACCESS	read-only
			STATUS	current
	DESCRIPTION ""
			::= { mbusC4 18 }

mbusC4Value06		OBJECT-TYPE
			SYNTAX	INTEGER
			ACCESS	read-only
			STATUS	current
	DESCRIPTION ""
			::= { mbusC4 19 }

mbusC4VIF07		OBJECT-TYPE
			SYNTAX	INTEGER
			ACCESS	read-only
			STATUS	current
	DESCRIPTION ""
			::= { mbusC4 20 }

mbusC4Value07		OBJECT-TYPE
			SYNTAX	INTEGER
			ACCESS	read-only
			STATUS	current
	DESCRIPTION ""
			::= { mbusC4 21 }

mbusC4VIF08		OBJECT-TYPE
			SYNTAX	INTEGER
			ACCESS	read-only
			STATUS	current
	DESCRIPTION ""
			::= { mbusC4 22 }

mbusC4Value08		OBJECT-TYPE
			SYNTAX	INTEGER
			ACCESS	read-only
			STATUS	current
	DESCRIPTION ""
			::= { mbusC4 23 }

mbusC4VIF09		OBJECT-TYPE
			SYNTAX	INTEGER
			ACCESS	read-only
			STATUS	current
	DESCRIPTION ""
			::= { mbusC4 24 }

mbusC4Value09		OBJECT-TYPE
			SYNTAX	INTEGER
			ACCESS	read-only
			STATUS	current
	DESCRIPTION ""
			::= { mbusC4 25 }

mbusC4VIF0A		OBJECT-TYPE
			SYNTAX	INTEGER
			ACCESS	read-only
			STATUS	current
	DESCRIPTION ""
			::= { mbusC4 26 }

mbusC4Value0A		OBJECT-TYPE
			SYNTAX	INTEGER
			ACCESS	read-only
			STATUS	current
	DESCRIPTION ""
			::= { mbusC4 27 }

mbusC4VIF0B		OBJECT-TYPE
			SYNTAX	INTEGER
			ACCESS	read-only
			STATUS	current
	DESCRIPTION ""
			::= { mbusC4 28 }

mbusC4Value0B		OBJECT-TYPE
			SYNTAX	INTEGER
			ACCESS	read-only
			STATUS	current
	DESCRIPTION ""
			::= { mbusC4 29 }

mbusC4VIF0C		OBJECT-TYPE
			SYNTAX	INTEGER
			ACCESS	read-only
			STATUS	current
	DESCRIPTION ""
			::= { mbusC4 30 }

mbusC4Value0C		OBJECT-TYPE
			SYNTAX	INTEGER
			ACCESS	read-only
			STATUS	current
	DESCRIPTION ""
			::= { mbusC4 31 }

mbusC4VIF0D		OBJECT-TYPE
			SYNTAX	INTEGER
			ACCESS	read-only
			STATUS	current
	DESCRIPTION ""
			::= { mbusC4 32 }

mbusC4Value0D		OBJECT-TYPE
			SYNTAX	INTEGER
			ACCESS	read-only
			STATUS	current
	DESCRIPTION ""
			::= { mbusC4 33 }

mbusC4VIF0E		OBJECT-TYPE
			SYNTAX	INTEGER
			ACCESS	read-only
			STATUS	current
	DESCRIPTION ""
			::= { mbusC4 34 }

mbusC4Value0E		OBJECT-TYPE
			SYNTAX	INTEGER
			ACCESS	read-only
			STATUS	current
	DESCRIPTION ""
			::= { mbusC4 35 }

mbusC4VIF0F		OBJECT-TYPE
			SYNTAX	INTEGER
			ACCESS	read-only
			STATUS	current
	DESCRIPTION ""
			::= { mbusC4 36 }

mbusC4Value0F		OBJECT-TYPE
			SYNTAX	INTEGER
			ACCESS	read-only
			STATUS	current
	DESCRIPTION ""
			::= { mbusC4 37 }

mbusC4VIF10		OBJECT-TYPE
			SYNTAX	INTEGER
			ACCESS	read-only
			STATUS	current
	DESCRIPTION ""
			::= { mbusC4 38 }

mbusC4Value10		OBJECT-TYPE
			SYNTAX	INTEGER
			ACCESS	read-only
			STATUS	current
	DESCRIPTION ""
			::= { mbusC4 39 }

mbusC4VIF11		OBJECT-TYPE
			SYNTAX	INTEGER
			ACCESS	read-only
			STATUS	current
	DESCRIPTION ""
			::= { mbusC4 40 }

mbusC4Value11		OBJECT-TYPE
			SYNTAX	INTEGER
			ACCESS	read-only
			STATUS	current
	DESCRIPTION ""
			::= { mbusC4 41 }

mbusC4VIF12		OBJECT-TYPE
			SYNTAX	INTEGER
			ACCESS	read-only
			STATUS	current
	DESCRIPTION ""
			::= { mbusC4 42 }

mbusC4Value12		OBJECT-TYPE
			SYNTAX	INTEGER
			ACCESS	read-only
			STATUS	current
	DESCRIPTION ""
			::= { mbusC4 43 }

mbusC4VIF13		OBJECT-TYPE
			SYNTAX	INTEGER
			ACCESS	read-only
			STATUS	current
	DESCRIPTION ""
			::= { mbusC4 44 }

mbusC4Value13		OBJECT-TYPE
			SYNTAX	INTEGER
			ACCESS	read-only
			STATUS	current
	DESCRIPTION ""
			::= { mbusC4 45 }

mbusC4VIF14		OBJECT-TYPE
			SYNTAX	INTEGER
			ACCESS	read-only
			STATUS	current
	DESCRIPTION ""
			::= { mbusC4 46 }

mbusC4Value14		OBJECT-TYPE
			SYNTAX	INTEGER
			ACCESS	read-only
			STATUS	current
	DESCRIPTION ""
			::= { mbusC4 47 }

mbusC4VIF15		OBJECT-TYPE
			SYNTAX	INTEGER
			ACCESS	read-only
			STATUS	current
	DESCRIPTION ""
			::= { mbusC4 48 }

mbusC4Value15		OBJECT-TYPE
			SYNTAX	INTEGER
			ACCESS	read-only
			STATUS	current
	DESCRIPTION ""
			::= { mbusC4 49 }

mbusC4VIF16		OBJECT-TYPE
			SYNTAX	INTEGER
			ACCESS	read-only
			STATUS	current
	DESCRIPTION ""
			::= { mbusC4 50 }

mbusC4Value16		OBJECT-TYPE
			SYNTAX	INTEGER
			ACCESS	read-only
			STATUS	current
	DESCRIPTION ""
			::= { mbusC4 51 }

mbusC4VIF17		OBJECT-TYPE
			SYNTAX	INTEGER
			ACCESS	read-only
			STATUS	current
	DESCRIPTION ""
			::= { mbusC4 52 }

mbusC4Value17		OBJECT-TYPE
			SYNTAX	INTEGER
			ACCESS	read-only
			STATUS	current
	DESCRIPTION ""
			::= { mbusC4 53 }

mbusC4VIF18		OBJECT-TYPE
			SYNTAX	INTEGER
			ACCESS	read-only
			STATUS	current
	DESCRIPTION ""
			::= { mbusC4 54 }

mbusC4Value18		OBJECT-TYPE
			SYNTAX	INTEGER
			ACCESS	read-only
			STATUS	current
	DESCRIPTION ""
			::= { mbusC4 55 }

mbusC4VIF19		OBJECT-TYPE
			SYNTAX	INTEGER
			ACCESS	read-only
			STATUS	current
	DESCRIPTION ""
			::= { mbusC4 56 }

mbusC4Value19		OBJECT-TYPE
			SYNTAX	INTEGER
			ACCESS	read-only
			STATUS	current
	DESCRIPTION ""
			::= { mbusC4 57 }

mbusC4VIF1A		OBJECT-TYPE
			SYNTAX	INTEGER
			ACCESS	read-only
			STATUS	current
	DESCRIPTION ""
			::= { mbusC4 58 }

mbusC4Value1A		OBJECT-TYPE
			SYNTAX	INTEGER
			ACCESS	read-only
			STATUS	current
	DESCRIPTION ""
			::= { mbusC4 59 }

mbusC4VIF1B		OBJECT-TYPE
			SYNTAX	INTEGER
			ACCESS	read-only
			STATUS	current
	DESCRIPTION ""
			::= { mbusC4 60 }

mbusC4Value1B		OBJECT-TYPE
			SYNTAX	INTEGER
			ACCESS	read-only
			STATUS	current
	DESCRIPTION ""
			::= { mbusC4 61 }

mbusC4VIF1C		OBJECT-TYPE
			SYNTAX	INTEGER
			ACCESS	read-only
			STATUS	current
	DESCRIPTION ""
			::= { mbusC4 62 }

mbusC4Value1C		OBJECT-TYPE
			SYNTAX	INTEGER
			ACCESS	read-only
			STATUS	current
	DESCRIPTION ""
			::= { mbusC4 63 }

mbusC4VIF1D		OBJECT-TYPE
			SYNTAX	INTEGER
			ACCESS	read-only
			STATUS	current
	DESCRIPTION ""
			::= { mbusC4 64 }

mbusC4Value1D		OBJECT-TYPE
			SYNTAX	INTEGER
			ACCESS	read-only
			STATUS	current
	DESCRIPTION ""
			::= { mbusC4 65 }

mbusC4VIF1E		OBJECT-TYPE
			SYNTAX	INTEGER
			ACCESS	read-only
			STATUS	current
	DESCRIPTION ""
			::= { mbusC4 66 }

mbusC4Value1E		OBJECT-TYPE
			SYNTAX	INTEGER
			ACCESS	read-only
			STATUS	current
	DESCRIPTION ""
			::= { mbusC4 67 }

mbusC4VIF1F		OBJECT-TYPE
			SYNTAX	INTEGER
			ACCESS	read-only
			STATUS	current
	DESCRIPTION ""
			::= { mbusC4 68 }

mbusC4Value1F		OBJECT-TYPE
			SYNTAX	INTEGER
			ACCESS	read-only
			STATUS	current
	DESCRIPTION ""
			::= { mbusC4 69 }

mbusC4VIF20		OBJECT-TYPE
			SYNTAX	INTEGER
			ACCESS	read-only
			STATUS	current
	DESCRIPTION ""
			::= { mbusC4 70 }

mbusC4Value20		OBJECT-TYPE
			SYNTAX	INTEGER
			ACCESS	read-only
			STATUS	current
	DESCRIPTION ""
			::= { mbusC4 71 }

mbusC4VIF21		OBJECT-TYPE
			SYNTAX	INTEGER
			ACCESS	read-only
			STATUS	current
	DESCRIPTION ""
			::= { mbusC4 72 }

mbusC4Value21		OBJECT-TYPE
			SYNTAX	INTEGER
			ACCESS	read-only
			STATUS	current
	DESCRIPTION ""
			::= { mbusC4 73 }

mbusC4VIF22		OBJECT-TYPE
			SYNTAX	INTEGER
			ACCESS	read-only
			STATUS	current
	DESCRIPTION ""
			::= { mbusC4 74 }

mbusC4Value22		OBJECT-TYPE
			SYNTAX	INTEGER
			ACCESS	read-only
			STATUS	current
	DESCRIPTION ""
			::= { mbusC4 75 }

mbusC4VIF23		OBJECT-TYPE
			SYNTAX	INTEGER
			ACCESS	read-only
			STATUS	current
	DESCRIPTION ""
			::= { mbusC4 76 }

mbusC4Value23		OBJECT-TYPE
			SYNTAX	INTEGER
			ACCESS	read-only
			STATUS	current
	DESCRIPTION ""
			::= { mbusC4 77 }

mbusC4VIF24		OBJECT-TYPE
			SYNTAX	INTEGER
			ACCESS	read-only
			STATUS	current
	DESCRIPTION ""
			::= { mbusC4 78 }

mbusC4Value24		OBJECT-TYPE
			SYNTAX	INTEGER
			ACCESS	read-only
			STATUS	current
	DESCRIPTION ""
			::= { mbusC4 79 }

mbusC4VIF25		OBJECT-TYPE
			SYNTAX	INTEGER
			ACCESS	read-only
			STATUS	current
	DESCRIPTION ""
			::= { mbusC4 80 }

mbusC4Value25		OBJECT-TYPE
			SYNTAX	INTEGER
			ACCESS	read-only
			STATUS	current
	DESCRIPTION ""
			::= { mbusC4 81 }

mbusC4VIF26		OBJECT-TYPE
			SYNTAX	INTEGER
			ACCESS	read-only
			STATUS	current
	DESCRIPTION ""
			::= { mbusC4 82 }

mbusC4Value26		OBJECT-TYPE
			SYNTAX	INTEGER
			ACCESS	read-only
			STATUS	current
	DESCRIPTION ""
			::= { mbusC4 83 }

mbusC4VIF27		OBJECT-TYPE
			SYNTAX	INTEGER
			ACCESS	read-only
			STATUS	current
	DESCRIPTION ""
			::= { mbusC4 84 }

mbusC4Value27		OBJECT-TYPE
			SYNTAX	INTEGER
			ACCESS	read-only
			STATUS	current
	DESCRIPTION ""
			::= { mbusC4 85 }

mbusC4VIF28		OBJECT-TYPE
			SYNTAX	INTEGER
			ACCESS	read-only
			STATUS	current
	DESCRIPTION ""
			::= { mbusC4 86 }

mbusC4Value28		OBJECT-TYPE
			SYNTAX	INTEGER
			ACCESS	read-only
			STATUS	current
	DESCRIPTION ""
			::= { mbusC4 87 }

mbusC4VIF29		OBJECT-TYPE
			SYNTAX	INTEGER
			ACCESS	read-only
			STATUS	current
	DESCRIPTION ""
			::= { mbusC4 88 }

mbusC4Value29		OBJECT-TYPE
			SYNTAX	INTEGER
			ACCESS	read-only
			STATUS	current
	DESCRIPTION ""
			::= { mbusC4 89 }

mbusC4VIF2A		OBJECT-TYPE
			SYNTAX	INTEGER
			ACCESS	read-only
			STATUS	current
	DESCRIPTION ""
			::= { mbusC4 90 }

mbusC4Value2A		OBJECT-TYPE
			SYNTAX	INTEGER
			ACCESS	read-only
			STATUS	current
	DESCRIPTION ""
			::= { mbusC4 91 }

mbusC4VIF2B		OBJECT-TYPE
			SYNTAX	INTEGER
			ACCESS	read-only
			STATUS	current
	DESCRIPTION ""
			::= { mbusC4 92 }

mbusC4Value2B		OBJECT-TYPE
			SYNTAX	INTEGER
			ACCESS	read-only
			STATUS	current
	DESCRIPTION ""
			::= { mbusC4 93 }

mbusC4VIF2C		OBJECT-TYPE
			SYNTAX	INTEGER
			ACCESS	read-only
			STATUS	current
	DESCRIPTION ""
			::= { mbusC4 94 }

mbusC4Value2C		OBJECT-TYPE
			SYNTAX	INTEGER
			ACCESS	read-only
			STATUS	current
	DESCRIPTION ""
			::= { mbusC4 95 }

mbusC4VIF2D		OBJECT-TYPE
			SYNTAX	INTEGER
			ACCESS	read-only
			STATUS	current
	DESCRIPTION ""
			::= { mbusC4 96 }

mbusC4Value2D		OBJECT-TYPE
			SYNTAX	INTEGER
			ACCESS	read-only
			STATUS	current
	DESCRIPTION ""
			::= { mbusC4 97 }

mbusC4VIF2E		OBJECT-TYPE
			SYNTAX	INTEGER
			ACCESS	read-only
			STATUS	current
	DESCRIPTION ""
			::= { mbusC4 98 }

mbusC4Value2E		OBJECT-TYPE
			SYNTAX	INTEGER
			ACCESS	read-only
			STATUS	current
	DESCRIPTION ""
			::= { mbusC4 99 }

mbusC4VIF2F		OBJECT-TYPE
			SYNTAX	INTEGER
			ACCESS	read-only
			STATUS	current
	DESCRIPTION ""
			::= { mbusC4 100 }

mbusC4Value2F		OBJECT-TYPE
			SYNTAX	INTEGER
			ACCESS	read-only
			STATUS	current
	DESCRIPTION ""
			::= { mbusC4 101 }

mbusC5			OBJECT IDENTIFIER ::= { mbus 197 }

mbusC5IdNumber		OBJECT-TYPE
			SYNTAX	Gauge
			ACCESS	read-only
			STATUS	current
	DESCRIPTION ""
			::= { mbusC5 1 }

mbusC5Manufacturer	OBJECT-TYPE
			SYNTAX	Gauge
			ACCESS	read-only
			STATUS	current
	DESCRIPTION ""
			::= { mbusC5 2 }

mbusC5Version		OBJECT-TYPE
			SYNTAX	Gauge
			ACCESS	read-only
			STATUS	current
	DESCRIPTION ""
			::= { mbusC5 3 }

mbusC5Medium		OBJECT-TYPE
			SYNTAX	Gauge
			ACCESS	read-only
			STATUS	current
	DESCRIPTION ""
			::= { mbusC5 4 }

mbusC5Status		OBJECT-TYPE
			SYNTAX	Gauge
			ACCESS	read-only
			STATUS	current
	DESCRIPTION ""
			::= { mbusC5 5 }

mbusC5VIF00		OBJECT-TYPE
			SYNTAX	INTEGER
			ACCESS	read-only
			STATUS	current
	DESCRIPTION ""
			::= { mbusC5 6 }

mbusC5Value00		OBJECT-TYPE
			SYNTAX	INTEGER
			ACCESS	read-only
			STATUS	current
	DESCRIPTION ""
			::= { mbusC5 7 }

mbusC5VIF01		OBJECT-TYPE
			SYNTAX	INTEGER
			ACCESS	read-only
			STATUS	current
	DESCRIPTION ""
			::= { mbusC5 8 }

mbusC5Value01		OBJECT-TYPE
			SYNTAX	INTEGER
			ACCESS	read-only
			STATUS	current
	DESCRIPTION ""
			::= { mbusC5 9 }

mbusC5VIF02		OBJECT-TYPE
			SYNTAX	INTEGER
			ACCESS	read-only
			STATUS	current
	DESCRIPTION ""
			::= { mbusC5 10 }

mbusC5Value02		OBJECT-TYPE
			SYNTAX	INTEGER
			ACCESS	read-only
			STATUS	current
	DESCRIPTION ""
			::= { mbusC5 11 }

mbusC5VIF03		OBJECT-TYPE
			SYNTAX	INTEGER
			ACCESS	read-only
			STATUS	current
	DESCRIPTION ""
			::= { mbusC5 12 }

mbusC5Value03		OBJECT-TYPE
			SYNTAX	INTEGER
			ACCESS	read-only
			STATUS	current
	DESCRIPTION ""
			::= { mbusC5 13 }

mbusC5VIF04		OBJECT-TYPE
			SYNTAX	INTEGER
			ACCESS	read-only
			STATUS	current
	DESCRIPTION ""
			::= { mbusC5 14 }

mbusC5Value04		OBJECT-TYPE
			SYNTAX	INTEGER
			ACCESS	read-only
			STATUS	current
	DESCRIPTION ""
			::= { mbusC5 15 }

mbusC5VIF05		OBJECT-TYPE
			SYNTAX	INTEGER
			ACCESS	read-only
			STATUS	current
	DESCRIPTION ""
			::= { mbusC5 16 }

mbusC5Value05		OBJECT-TYPE
			SYNTAX	INTEGER
			ACCESS	read-only
			STATUS	current
	DESCRIPTION ""
			::= { mbusC5 17 }

mbusC5VIF06		OBJECT-TYPE
			SYNTAX	INTEGER
			ACCESS	read-only
			STATUS	current
	DESCRIPTION ""
			::= { mbusC5 18 }

mbusC5Value06		OBJECT-TYPE
			SYNTAX	INTEGER
			ACCESS	read-only
			STATUS	current
	DESCRIPTION ""
			::= { mbusC5 19 }

mbusC5VIF07		OBJECT-TYPE
			SYNTAX	INTEGER
			ACCESS	read-only
			STATUS	current
	DESCRIPTION ""
			::= { mbusC5 20 }

mbusC5Value07		OBJECT-TYPE
			SYNTAX	INTEGER
			ACCESS	read-only
			STATUS	current
	DESCRIPTION ""
			::= { mbusC5 21 }

mbusC5VIF08		OBJECT-TYPE
			SYNTAX	INTEGER
			ACCESS	read-only
			STATUS	current
	DESCRIPTION ""
			::= { mbusC5 22 }

mbusC5Value08		OBJECT-TYPE
			SYNTAX	INTEGER
			ACCESS	read-only
			STATUS	current
	DESCRIPTION ""
			::= { mbusC5 23 }

mbusC5VIF09		OBJECT-TYPE
			SYNTAX	INTEGER
			ACCESS	read-only
			STATUS	current
	DESCRIPTION ""
			::= { mbusC5 24 }

mbusC5Value09		OBJECT-TYPE
			SYNTAX	INTEGER
			ACCESS	read-only
			STATUS	current
	DESCRIPTION ""
			::= { mbusC5 25 }

mbusC5VIF0A		OBJECT-TYPE
			SYNTAX	INTEGER
			ACCESS	read-only
			STATUS	current
	DESCRIPTION ""
			::= { mbusC5 26 }

mbusC5Value0A		OBJECT-TYPE
			SYNTAX	INTEGER
			ACCESS	read-only
			STATUS	current
	DESCRIPTION ""
			::= { mbusC5 27 }

mbusC5VIF0B		OBJECT-TYPE
			SYNTAX	INTEGER
			ACCESS	read-only
			STATUS	current
	DESCRIPTION ""
			::= { mbusC5 28 }

mbusC5Value0B		OBJECT-TYPE
			SYNTAX	INTEGER
			ACCESS	read-only
			STATUS	current
	DESCRIPTION ""
			::= { mbusC5 29 }

mbusC5VIF0C		OBJECT-TYPE
			SYNTAX	INTEGER
			ACCESS	read-only
			STATUS	current
	DESCRIPTION ""
			::= { mbusC5 30 }

mbusC5Value0C		OBJECT-TYPE
			SYNTAX	INTEGER
			ACCESS	read-only
			STATUS	current
	DESCRIPTION ""
			::= { mbusC5 31 }

mbusC5VIF0D		OBJECT-TYPE
			SYNTAX	INTEGER
			ACCESS	read-only
			STATUS	current
	DESCRIPTION ""
			::= { mbusC5 32 }

mbusC5Value0D		OBJECT-TYPE
			SYNTAX	INTEGER
			ACCESS	read-only
			STATUS	current
	DESCRIPTION ""
			::= { mbusC5 33 }

mbusC5VIF0E		OBJECT-TYPE
			SYNTAX	INTEGER
			ACCESS	read-only
			STATUS	current
	DESCRIPTION ""
			::= { mbusC5 34 }

mbusC5Value0E		OBJECT-TYPE
			SYNTAX	INTEGER
			ACCESS	read-only
			STATUS	current
	DESCRIPTION ""
			::= { mbusC5 35 }

mbusC5VIF0F		OBJECT-TYPE
			SYNTAX	INTEGER
			ACCESS	read-only
			STATUS	current
	DESCRIPTION ""
			::= { mbusC5 36 }

mbusC5Value0F		OBJECT-TYPE
			SYNTAX	INTEGER
			ACCESS	read-only
			STATUS	current
	DESCRIPTION ""
			::= { mbusC5 37 }

mbusC5VIF10		OBJECT-TYPE
			SYNTAX	INTEGER
			ACCESS	read-only
			STATUS	current
	DESCRIPTION ""
			::= { mbusC5 38 }

mbusC5Value10		OBJECT-TYPE
			SYNTAX	INTEGER
			ACCESS	read-only
			STATUS	current
	DESCRIPTION ""
			::= { mbusC5 39 }

mbusC5VIF11		OBJECT-TYPE
			SYNTAX	INTEGER
			ACCESS	read-only
			STATUS	current
	DESCRIPTION ""
			::= { mbusC5 40 }

mbusC5Value11		OBJECT-TYPE
			SYNTAX	INTEGER
			ACCESS	read-only
			STATUS	current
	DESCRIPTION ""
			::= { mbusC5 41 }

mbusC5VIF12		OBJECT-TYPE
			SYNTAX	INTEGER
			ACCESS	read-only
			STATUS	current
	DESCRIPTION ""
			::= { mbusC5 42 }

mbusC5Value12		OBJECT-TYPE
			SYNTAX	INTEGER
			ACCESS	read-only
			STATUS	current
	DESCRIPTION ""
			::= { mbusC5 43 }

mbusC5VIF13		OBJECT-TYPE
			SYNTAX	INTEGER
			ACCESS	read-only
			STATUS	current
	DESCRIPTION ""
			::= { mbusC5 44 }

mbusC5Value13		OBJECT-TYPE
			SYNTAX	INTEGER
			ACCESS	read-only
			STATUS	current
	DESCRIPTION ""
			::= { mbusC5 45 }

mbusC5VIF14		OBJECT-TYPE
			SYNTAX	INTEGER
			ACCESS	read-only
			STATUS	current
	DESCRIPTION ""
			::= { mbusC5 46 }

mbusC5Value14		OBJECT-TYPE
			SYNTAX	INTEGER
			ACCESS	read-only
			STATUS	current
	DESCRIPTION ""
			::= { mbusC5 47 }

mbusC5VIF15		OBJECT-TYPE
			SYNTAX	INTEGER
			ACCESS	read-only
			STATUS	current
	DESCRIPTION ""
			::= { mbusC5 48 }

mbusC5Value15		OBJECT-TYPE
			SYNTAX	INTEGER
			ACCESS	read-only
			STATUS	current
	DESCRIPTION ""
			::= { mbusC5 49 }

mbusC5VIF16		OBJECT-TYPE
			SYNTAX	INTEGER
			ACCESS	read-only
			STATUS	current
	DESCRIPTION ""
			::= { mbusC5 50 }

mbusC5Value16		OBJECT-TYPE
			SYNTAX	INTEGER
			ACCESS	read-only
			STATUS	current
	DESCRIPTION ""
			::= { mbusC5 51 }

mbusC5VIF17		OBJECT-TYPE
			SYNTAX	INTEGER
			ACCESS	read-only
			STATUS	current
	DESCRIPTION ""
			::= { mbusC5 52 }

mbusC5Value17		OBJECT-TYPE
			SYNTAX	INTEGER
			ACCESS	read-only
			STATUS	current
	DESCRIPTION ""
			::= { mbusC5 53 }

mbusC5VIF18		OBJECT-TYPE
			SYNTAX	INTEGER
			ACCESS	read-only
			STATUS	current
	DESCRIPTION ""
			::= { mbusC5 54 }

mbusC5Value18		OBJECT-TYPE
			SYNTAX	INTEGER
			ACCESS	read-only
			STATUS	current
	DESCRIPTION ""
			::= { mbusC5 55 }

mbusC5VIF19		OBJECT-TYPE
			SYNTAX	INTEGER
			ACCESS	read-only
			STATUS	current
	DESCRIPTION ""
			::= { mbusC5 56 }

mbusC5Value19		OBJECT-TYPE
			SYNTAX	INTEGER
			ACCESS	read-only
			STATUS	current
	DESCRIPTION ""
			::= { mbusC5 57 }

mbusC5VIF1A		OBJECT-TYPE
			SYNTAX	INTEGER
			ACCESS	read-only
			STATUS	current
	DESCRIPTION ""
			::= { mbusC5 58 }

mbusC5Value1A		OBJECT-TYPE
			SYNTAX	INTEGER
			ACCESS	read-only
			STATUS	current
	DESCRIPTION ""
			::= { mbusC5 59 }

mbusC5VIF1B		OBJECT-TYPE
			SYNTAX	INTEGER
			ACCESS	read-only
			STATUS	current
	DESCRIPTION ""
			::= { mbusC5 60 }

mbusC5Value1B		OBJECT-TYPE
			SYNTAX	INTEGER
			ACCESS	read-only
			STATUS	current
	DESCRIPTION ""
			::= { mbusC5 61 }

mbusC5VIF1C		OBJECT-TYPE
			SYNTAX	INTEGER
			ACCESS	read-only
			STATUS	current
	DESCRIPTION ""
			::= { mbusC5 62 }

mbusC5Value1C		OBJECT-TYPE
			SYNTAX	INTEGER
			ACCESS	read-only
			STATUS	current
	DESCRIPTION ""
			::= { mbusC5 63 }

mbusC5VIF1D		OBJECT-TYPE
			SYNTAX	INTEGER
			ACCESS	read-only
			STATUS	current
	DESCRIPTION ""
			::= { mbusC5 64 }

mbusC5Value1D		OBJECT-TYPE
			SYNTAX	INTEGER
			ACCESS	read-only
			STATUS	current
	DESCRIPTION ""
			::= { mbusC5 65 }

mbusC5VIF1E		OBJECT-TYPE
			SYNTAX	INTEGER
			ACCESS	read-only
			STATUS	current
	DESCRIPTION ""
			::= { mbusC5 66 }

mbusC5Value1E		OBJECT-TYPE
			SYNTAX	INTEGER
			ACCESS	read-only
			STATUS	current
	DESCRIPTION ""
			::= { mbusC5 67 }

mbusC5VIF1F		OBJECT-TYPE
			SYNTAX	INTEGER
			ACCESS	read-only
			STATUS	current
	DESCRIPTION ""
			::= { mbusC5 68 }

mbusC5Value1F		OBJECT-TYPE
			SYNTAX	INTEGER
			ACCESS	read-only
			STATUS	current
	DESCRIPTION ""
			::= { mbusC5 69 }

mbusC5VIF20		OBJECT-TYPE
			SYNTAX	INTEGER
			ACCESS	read-only
			STATUS	current
	DESCRIPTION ""
			::= { mbusC5 70 }

mbusC5Value20		OBJECT-TYPE
			SYNTAX	INTEGER
			ACCESS	read-only
			STATUS	current
	DESCRIPTION ""
			::= { mbusC5 71 }

mbusC5VIF21		OBJECT-TYPE
			SYNTAX	INTEGER
			ACCESS	read-only
			STATUS	current
	DESCRIPTION ""
			::= { mbusC5 72 }

mbusC5Value21		OBJECT-TYPE
			SYNTAX	INTEGER
			ACCESS	read-only
			STATUS	current
	DESCRIPTION ""
			::= { mbusC5 73 }

mbusC5VIF22		OBJECT-TYPE
			SYNTAX	INTEGER
			ACCESS	read-only
			STATUS	current
	DESCRIPTION ""
			::= { mbusC5 74 }

mbusC5Value22		OBJECT-TYPE
			SYNTAX	INTEGER
			ACCESS	read-only
			STATUS	current
	DESCRIPTION ""
			::= { mbusC5 75 }

mbusC5VIF23		OBJECT-TYPE
			SYNTAX	INTEGER
			ACCESS	read-only
			STATUS	current
	DESCRIPTION ""
			::= { mbusC5 76 }

mbusC5Value23		OBJECT-TYPE
			SYNTAX	INTEGER
			ACCESS	read-only
			STATUS	current
	DESCRIPTION ""
			::= { mbusC5 77 }

mbusC5VIF24		OBJECT-TYPE
			SYNTAX	INTEGER
			ACCESS	read-only
			STATUS	current
	DESCRIPTION ""
			::= { mbusC5 78 }

mbusC5Value24		OBJECT-TYPE
			SYNTAX	INTEGER
			ACCESS	read-only
			STATUS	current
	DESCRIPTION ""
			::= { mbusC5 79 }

mbusC5VIF25		OBJECT-TYPE
			SYNTAX	INTEGER
			ACCESS	read-only
			STATUS	current
	DESCRIPTION ""
			::= { mbusC5 80 }

mbusC5Value25		OBJECT-TYPE
			SYNTAX	INTEGER
			ACCESS	read-only
			STATUS	current
	DESCRIPTION ""
			::= { mbusC5 81 }

mbusC5VIF26		OBJECT-TYPE
			SYNTAX	INTEGER
			ACCESS	read-only
			STATUS	current
	DESCRIPTION ""
			::= { mbusC5 82 }

mbusC5Value26		OBJECT-TYPE
			SYNTAX	INTEGER
			ACCESS	read-only
			STATUS	current
	DESCRIPTION ""
			::= { mbusC5 83 }

mbusC5VIF27		OBJECT-TYPE
			SYNTAX	INTEGER
			ACCESS	read-only
			STATUS	current
	DESCRIPTION ""
			::= { mbusC5 84 }

mbusC5Value27		OBJECT-TYPE
			SYNTAX	INTEGER
			ACCESS	read-only
			STATUS	current
	DESCRIPTION ""
			::= { mbusC5 85 }

mbusC5VIF28		OBJECT-TYPE
			SYNTAX	INTEGER
			ACCESS	read-only
			STATUS	current
	DESCRIPTION ""
			::= { mbusC5 86 }

mbusC5Value28		OBJECT-TYPE
			SYNTAX	INTEGER
			ACCESS	read-only
			STATUS	current
	DESCRIPTION ""
			::= { mbusC5 87 }

mbusC5VIF29		OBJECT-TYPE
			SYNTAX	INTEGER
			ACCESS	read-only
			STATUS	current
	DESCRIPTION ""
			::= { mbusC5 88 }

mbusC5Value29		OBJECT-TYPE
			SYNTAX	INTEGER
			ACCESS	read-only
			STATUS	current
	DESCRIPTION ""
			::= { mbusC5 89 }

mbusC5VIF2A		OBJECT-TYPE
			SYNTAX	INTEGER
			ACCESS	read-only
			STATUS	current
	DESCRIPTION ""
			::= { mbusC5 90 }

mbusC5Value2A		OBJECT-TYPE
			SYNTAX	INTEGER
			ACCESS	read-only
			STATUS	current
	DESCRIPTION ""
			::= { mbusC5 91 }

mbusC5VIF2B		OBJECT-TYPE
			SYNTAX	INTEGER
			ACCESS	read-only
			STATUS	current
	DESCRIPTION ""
			::= { mbusC5 92 }

mbusC5Value2B		OBJECT-TYPE
			SYNTAX	INTEGER
			ACCESS	read-only
			STATUS	current
	DESCRIPTION ""
			::= { mbusC5 93 }

mbusC5VIF2C		OBJECT-TYPE
			SYNTAX	INTEGER
			ACCESS	read-only
			STATUS	current
	DESCRIPTION ""
			::= { mbusC5 94 }

mbusC5Value2C		OBJECT-TYPE
			SYNTAX	INTEGER
			ACCESS	read-only
			STATUS	current
	DESCRIPTION ""
			::= { mbusC5 95 }

mbusC5VIF2D		OBJECT-TYPE
			SYNTAX	INTEGER
			ACCESS	read-only
			STATUS	current
	DESCRIPTION ""
			::= { mbusC5 96 }

mbusC5Value2D		OBJECT-TYPE
			SYNTAX	INTEGER
			ACCESS	read-only
			STATUS	current
	DESCRIPTION ""
			::= { mbusC5 97 }

mbusC5VIF2E		OBJECT-TYPE
			SYNTAX	INTEGER
			ACCESS	read-only
			STATUS	current
	DESCRIPTION ""
			::= { mbusC5 98 }

mbusC5Value2E		OBJECT-TYPE
			SYNTAX	INTEGER
			ACCESS	read-only
			STATUS	current
	DESCRIPTION ""
			::= { mbusC5 99 }

mbusC5VIF2F		OBJECT-TYPE
			SYNTAX	INTEGER
			ACCESS	read-only
			STATUS	current
	DESCRIPTION ""
			::= { mbusC5 100 }

mbusC5Value2F		OBJECT-TYPE
			SYNTAX	INTEGER
			ACCESS	read-only
			STATUS	current
	DESCRIPTION ""
			::= { mbusC5 101 }

mbusC6			OBJECT IDENTIFIER ::= { mbus 198 }

mbusC6IdNumber		OBJECT-TYPE
			SYNTAX	Gauge
			ACCESS	read-only
			STATUS	current
	DESCRIPTION ""
			::= { mbusC6 1 }

mbusC6Manufacturer	OBJECT-TYPE
			SYNTAX	Gauge
			ACCESS	read-only
			STATUS	current
	DESCRIPTION ""
			::= { mbusC6 2 }

mbusC6Version		OBJECT-TYPE
			SYNTAX	Gauge
			ACCESS	read-only
			STATUS	current
	DESCRIPTION ""
			::= { mbusC6 3 }

mbusC6Medium		OBJECT-TYPE
			SYNTAX	Gauge
			ACCESS	read-only
			STATUS	current
	DESCRIPTION ""
			::= { mbusC6 4 }

mbusC6Status		OBJECT-TYPE
			SYNTAX	Gauge
			ACCESS	read-only
			STATUS	current
	DESCRIPTION ""
			::= { mbusC6 5 }

mbusC6VIF00		OBJECT-TYPE
			SYNTAX	INTEGER
			ACCESS	read-only
			STATUS	current
	DESCRIPTION ""
			::= { mbusC6 6 }

mbusC6Value00		OBJECT-TYPE
			SYNTAX	INTEGER
			ACCESS	read-only
			STATUS	current
	DESCRIPTION ""
			::= { mbusC6 7 }

mbusC6VIF01		OBJECT-TYPE
			SYNTAX	INTEGER
			ACCESS	read-only
			STATUS	current
	DESCRIPTION ""
			::= { mbusC6 8 }

mbusC6Value01		OBJECT-TYPE
			SYNTAX	INTEGER
			ACCESS	read-only
			STATUS	current
	DESCRIPTION ""
			::= { mbusC6 9 }

mbusC6VIF02		OBJECT-TYPE
			SYNTAX	INTEGER
			ACCESS	read-only
			STATUS	current
	DESCRIPTION ""
			::= { mbusC6 10 }

mbusC6Value02		OBJECT-TYPE
			SYNTAX	INTEGER
			ACCESS	read-only
			STATUS	current
	DESCRIPTION ""
			::= { mbusC6 11 }

mbusC6VIF03		OBJECT-TYPE
			SYNTAX	INTEGER
			ACCESS	read-only
			STATUS	current
	DESCRIPTION ""
			::= { mbusC6 12 }

mbusC6Value03		OBJECT-TYPE
			SYNTAX	INTEGER
			ACCESS	read-only
			STATUS	current
	DESCRIPTION ""
			::= { mbusC6 13 }

mbusC6VIF04		OBJECT-TYPE
			SYNTAX	INTEGER
			ACCESS	read-only
			STATUS	current
	DESCRIPTION ""
			::= { mbusC6 14 }

mbusC6Value04		OBJECT-TYPE
			SYNTAX	INTEGER
			ACCESS	read-only
			STATUS	current
	DESCRIPTION ""
			::= { mbusC6 15 }

mbusC6VIF05		OBJECT-TYPE
			SYNTAX	INTEGER
			ACCESS	read-only
			STATUS	current
	DESCRIPTION ""
			::= { mbusC6 16 }

mbusC6Value05		OBJECT-TYPE
			SYNTAX	INTEGER
			ACCESS	read-only
			STATUS	current
	DESCRIPTION ""
			::= { mbusC6 17 }

mbusC6VIF06		OBJECT-TYPE
			SYNTAX	INTEGER
			ACCESS	read-only
			STATUS	current
	DESCRIPTION ""
			::= { mbusC6 18 }

mbusC6Value06		OBJECT-TYPE
			SYNTAX	INTEGER
			ACCESS	read-only
			STATUS	current
	DESCRIPTION ""
			::= { mbusC6 19 }

mbusC6VIF07		OBJECT-TYPE
			SYNTAX	INTEGER
			ACCESS	read-only
			STATUS	current
	DESCRIPTION ""
			::= { mbusC6 20 }

mbusC6Value07		OBJECT-TYPE
			SYNTAX	INTEGER
			ACCESS	read-only
			STATUS	current
	DESCRIPTION ""
			::= { mbusC6 21 }

mbusC6VIF08		OBJECT-TYPE
			SYNTAX	INTEGER
			ACCESS	read-only
			STATUS	current
	DESCRIPTION ""
			::= { mbusC6 22 }

mbusC6Value08		OBJECT-TYPE
			SYNTAX	INTEGER
			ACCESS	read-only
			STATUS	current
	DESCRIPTION ""
			::= { mbusC6 23 }

mbusC6VIF09		OBJECT-TYPE
			SYNTAX	INTEGER
			ACCESS	read-only
			STATUS	current
	DESCRIPTION ""
			::= { mbusC6 24 }

mbusC6Value09		OBJECT-TYPE
			SYNTAX	INTEGER
			ACCESS	read-only
			STATUS	current
	DESCRIPTION ""
			::= { mbusC6 25 }

mbusC6VIF0A		OBJECT-TYPE
			SYNTAX	INTEGER
			ACCESS	read-only
			STATUS	current
	DESCRIPTION ""
			::= { mbusC6 26 }

mbusC6Value0A		OBJECT-TYPE
			SYNTAX	INTEGER
			ACCESS	read-only
			STATUS	current
	DESCRIPTION ""
			::= { mbusC6 27 }

mbusC6VIF0B		OBJECT-TYPE
			SYNTAX	INTEGER
			ACCESS	read-only
			STATUS	current
	DESCRIPTION ""
			::= { mbusC6 28 }

mbusC6Value0B		OBJECT-TYPE
			SYNTAX	INTEGER
			ACCESS	read-only
			STATUS	current
	DESCRIPTION ""
			::= { mbusC6 29 }

mbusC6VIF0C		OBJECT-TYPE
			SYNTAX	INTEGER
			ACCESS	read-only
			STATUS	current
	DESCRIPTION ""
			::= { mbusC6 30 }

mbusC6Value0C		OBJECT-TYPE
			SYNTAX	INTEGER
			ACCESS	read-only
			STATUS	current
	DESCRIPTION ""
			::= { mbusC6 31 }

mbusC6VIF0D		OBJECT-TYPE
			SYNTAX	INTEGER
			ACCESS	read-only
			STATUS	current
	DESCRIPTION ""
			::= { mbusC6 32 }

mbusC6Value0D		OBJECT-TYPE
			SYNTAX	INTEGER
			ACCESS	read-only
			STATUS	current
	DESCRIPTION ""
			::= { mbusC6 33 }

mbusC6VIF0E		OBJECT-TYPE
			SYNTAX	INTEGER
			ACCESS	read-only
			STATUS	current
	DESCRIPTION ""
			::= { mbusC6 34 }

mbusC6Value0E		OBJECT-TYPE
			SYNTAX	INTEGER
			ACCESS	read-only
			STATUS	current
	DESCRIPTION ""
			::= { mbusC6 35 }

mbusC6VIF0F		OBJECT-TYPE
			SYNTAX	INTEGER
			ACCESS	read-only
			STATUS	current
	DESCRIPTION ""
			::= { mbusC6 36 }

mbusC6Value0F		OBJECT-TYPE
			SYNTAX	INTEGER
			ACCESS	read-only
			STATUS	current
	DESCRIPTION ""
			::= { mbusC6 37 }

mbusC6VIF10		OBJECT-TYPE
			SYNTAX	INTEGER
			ACCESS	read-only
			STATUS	current
	DESCRIPTION ""
			::= { mbusC6 38 }

mbusC6Value10		OBJECT-TYPE
			SYNTAX	INTEGER
			ACCESS	read-only
			STATUS	current
	DESCRIPTION ""
			::= { mbusC6 39 }

mbusC6VIF11		OBJECT-TYPE
			SYNTAX	INTEGER
			ACCESS	read-only
			STATUS	current
	DESCRIPTION ""
			::= { mbusC6 40 }

mbusC6Value11		OBJECT-TYPE
			SYNTAX	INTEGER
			ACCESS	read-only
			STATUS	current
	DESCRIPTION ""
			::= { mbusC6 41 }

mbusC6VIF12		OBJECT-TYPE
			SYNTAX	INTEGER
			ACCESS	read-only
			STATUS	current
	DESCRIPTION ""
			::= { mbusC6 42 }

mbusC6Value12		OBJECT-TYPE
			SYNTAX	INTEGER
			ACCESS	read-only
			STATUS	current
	DESCRIPTION ""
			::= { mbusC6 43 }

mbusC6VIF13		OBJECT-TYPE
			SYNTAX	INTEGER
			ACCESS	read-only
			STATUS	current
	DESCRIPTION ""
			::= { mbusC6 44 }

mbusC6Value13		OBJECT-TYPE
			SYNTAX	INTEGER
			ACCESS	read-only
			STATUS	current
	DESCRIPTION ""
			::= { mbusC6 45 }

mbusC6VIF14		OBJECT-TYPE
			SYNTAX	INTEGER
			ACCESS	read-only
			STATUS	current
	DESCRIPTION ""
			::= { mbusC6 46 }

mbusC6Value14		OBJECT-TYPE
			SYNTAX	INTEGER
			ACCESS	read-only
			STATUS	current
	DESCRIPTION ""
			::= { mbusC6 47 }

mbusC6VIF15		OBJECT-TYPE
			SYNTAX	INTEGER
			ACCESS	read-only
			STATUS	current
	DESCRIPTION ""
			::= { mbusC6 48 }

mbusC6Value15		OBJECT-TYPE
			SYNTAX	INTEGER
			ACCESS	read-only
			STATUS	current
	DESCRIPTION ""
			::= { mbusC6 49 }

mbusC6VIF16		OBJECT-TYPE
			SYNTAX	INTEGER
			ACCESS	read-only
			STATUS	current
	DESCRIPTION ""
			::= { mbusC6 50 }

mbusC6Value16		OBJECT-TYPE
			SYNTAX	INTEGER
			ACCESS	read-only
			STATUS	current
	DESCRIPTION ""
			::= { mbusC6 51 }

mbusC6VIF17		OBJECT-TYPE
			SYNTAX	INTEGER
			ACCESS	read-only
			STATUS	current
	DESCRIPTION ""
			::= { mbusC6 52 }

mbusC6Value17		OBJECT-TYPE
			SYNTAX	INTEGER
			ACCESS	read-only
			STATUS	current
	DESCRIPTION ""
			::= { mbusC6 53 }

mbusC6VIF18		OBJECT-TYPE
			SYNTAX	INTEGER
			ACCESS	read-only
			STATUS	current
	DESCRIPTION ""
			::= { mbusC6 54 }

mbusC6Value18		OBJECT-TYPE
			SYNTAX	INTEGER
			ACCESS	read-only
			STATUS	current
	DESCRIPTION ""
			::= { mbusC6 55 }

mbusC6VIF19		OBJECT-TYPE
			SYNTAX	INTEGER
			ACCESS	read-only
			STATUS	current
	DESCRIPTION ""
			::= { mbusC6 56 }

mbusC6Value19		OBJECT-TYPE
			SYNTAX	INTEGER
			ACCESS	read-only
			STATUS	current
	DESCRIPTION ""
			::= { mbusC6 57 }

mbusC6VIF1A		OBJECT-TYPE
			SYNTAX	INTEGER
			ACCESS	read-only
			STATUS	current
	DESCRIPTION ""
			::= { mbusC6 58 }

mbusC6Value1A		OBJECT-TYPE
			SYNTAX	INTEGER
			ACCESS	read-only
			STATUS	current
	DESCRIPTION ""
			::= { mbusC6 59 }

mbusC6VIF1B		OBJECT-TYPE
			SYNTAX	INTEGER
			ACCESS	read-only
			STATUS	current
	DESCRIPTION ""
			::= { mbusC6 60 }

mbusC6Value1B		OBJECT-TYPE
			SYNTAX	INTEGER
			ACCESS	read-only
			STATUS	current
	DESCRIPTION ""
			::= { mbusC6 61 }

mbusC6VIF1C		OBJECT-TYPE
			SYNTAX	INTEGER
			ACCESS	read-only
			STATUS	current
	DESCRIPTION ""
			::= { mbusC6 62 }

mbusC6Value1C		OBJECT-TYPE
			SYNTAX	INTEGER
			ACCESS	read-only
			STATUS	current
	DESCRIPTION ""
			::= { mbusC6 63 }

mbusC6VIF1D		OBJECT-TYPE
			SYNTAX	INTEGER
			ACCESS	read-only
			STATUS	current
	DESCRIPTION ""
			::= { mbusC6 64 }

mbusC6Value1D		OBJECT-TYPE
			SYNTAX	INTEGER
			ACCESS	read-only
			STATUS	current
	DESCRIPTION ""
			::= { mbusC6 65 }

mbusC6VIF1E		OBJECT-TYPE
			SYNTAX	INTEGER
			ACCESS	read-only
			STATUS	current
	DESCRIPTION ""
			::= { mbusC6 66 }

mbusC6Value1E		OBJECT-TYPE
			SYNTAX	INTEGER
			ACCESS	read-only
			STATUS	current
	DESCRIPTION ""
			::= { mbusC6 67 }

mbusC6VIF1F		OBJECT-TYPE
			SYNTAX	INTEGER
			ACCESS	read-only
			STATUS	current
	DESCRIPTION ""
			::= { mbusC6 68 }

mbusC6Value1F		OBJECT-TYPE
			SYNTAX	INTEGER
			ACCESS	read-only
			STATUS	current
	DESCRIPTION ""
			::= { mbusC6 69 }

mbusC6VIF20		OBJECT-TYPE
			SYNTAX	INTEGER
			ACCESS	read-only
			STATUS	current
	DESCRIPTION ""
			::= { mbusC6 70 }

mbusC6Value20		OBJECT-TYPE
			SYNTAX	INTEGER
			ACCESS	read-only
			STATUS	current
	DESCRIPTION ""
			::= { mbusC6 71 }

mbusC6VIF21		OBJECT-TYPE
			SYNTAX	INTEGER
			ACCESS	read-only
			STATUS	current
	DESCRIPTION ""
			::= { mbusC6 72 }

mbusC6Value21		OBJECT-TYPE
			SYNTAX	INTEGER
			ACCESS	read-only
			STATUS	current
	DESCRIPTION ""
			::= { mbusC6 73 }

mbusC6VIF22		OBJECT-TYPE
			SYNTAX	INTEGER
			ACCESS	read-only
			STATUS	current
	DESCRIPTION ""
			::= { mbusC6 74 }

mbusC6Value22		OBJECT-TYPE
			SYNTAX	INTEGER
			ACCESS	read-only
			STATUS	current
	DESCRIPTION ""
			::= { mbusC6 75 }

mbusC6VIF23		OBJECT-TYPE
			SYNTAX	INTEGER
			ACCESS	read-only
			STATUS	current
	DESCRIPTION ""
			::= { mbusC6 76 }

mbusC6Value23		OBJECT-TYPE
			SYNTAX	INTEGER
			ACCESS	read-only
			STATUS	current
	DESCRIPTION ""
			::= { mbusC6 77 }

mbusC6VIF24		OBJECT-TYPE
			SYNTAX	INTEGER
			ACCESS	read-only
			STATUS	current
	DESCRIPTION ""
			::= { mbusC6 78 }

mbusC6Value24		OBJECT-TYPE
			SYNTAX	INTEGER
			ACCESS	read-only
			STATUS	current
	DESCRIPTION ""
			::= { mbusC6 79 }

mbusC6VIF25		OBJECT-TYPE
			SYNTAX	INTEGER
			ACCESS	read-only
			STATUS	current
	DESCRIPTION ""
			::= { mbusC6 80 }

mbusC6Value25		OBJECT-TYPE
			SYNTAX	INTEGER
			ACCESS	read-only
			STATUS	current
	DESCRIPTION ""
			::= { mbusC6 81 }

mbusC6VIF26		OBJECT-TYPE
			SYNTAX	INTEGER
			ACCESS	read-only
			STATUS	current
	DESCRIPTION ""
			::= { mbusC6 82 }

mbusC6Value26		OBJECT-TYPE
			SYNTAX	INTEGER
			ACCESS	read-only
			STATUS	current
	DESCRIPTION ""
			::= { mbusC6 83 }

mbusC6VIF27		OBJECT-TYPE
			SYNTAX	INTEGER
			ACCESS	read-only
			STATUS	current
	DESCRIPTION ""
			::= { mbusC6 84 }

mbusC6Value27		OBJECT-TYPE
			SYNTAX	INTEGER
			ACCESS	read-only
			STATUS	current
	DESCRIPTION ""
			::= { mbusC6 85 }

mbusC6VIF28		OBJECT-TYPE
			SYNTAX	INTEGER
			ACCESS	read-only
			STATUS	current
	DESCRIPTION ""
			::= { mbusC6 86 }

mbusC6Value28		OBJECT-TYPE
			SYNTAX	INTEGER
			ACCESS	read-only
			STATUS	current
	DESCRIPTION ""
			::= { mbusC6 87 }

mbusC6VIF29		OBJECT-TYPE
			SYNTAX	INTEGER
			ACCESS	read-only
			STATUS	current
	DESCRIPTION ""
			::= { mbusC6 88 }

mbusC6Value29		OBJECT-TYPE
			SYNTAX	INTEGER
			ACCESS	read-only
			STATUS	current
	DESCRIPTION ""
			::= { mbusC6 89 }

mbusC6VIF2A		OBJECT-TYPE
			SYNTAX	INTEGER
			ACCESS	read-only
			STATUS	current
	DESCRIPTION ""
			::= { mbusC6 90 }

mbusC6Value2A		OBJECT-TYPE
			SYNTAX	INTEGER
			ACCESS	read-only
			STATUS	current
	DESCRIPTION ""
			::= { mbusC6 91 }

mbusC6VIF2B		OBJECT-TYPE
			SYNTAX	INTEGER
			ACCESS	read-only
			STATUS	current
	DESCRIPTION ""
			::= { mbusC6 92 }

mbusC6Value2B		OBJECT-TYPE
			SYNTAX	INTEGER
			ACCESS	read-only
			STATUS	current
	DESCRIPTION ""
			::= { mbusC6 93 }

mbusC6VIF2C		OBJECT-TYPE
			SYNTAX	INTEGER
			ACCESS	read-only
			STATUS	current
	DESCRIPTION ""
			::= { mbusC6 94 }

mbusC6Value2C		OBJECT-TYPE
			SYNTAX	INTEGER
			ACCESS	read-only
			STATUS	current
	DESCRIPTION ""
			::= { mbusC6 95 }

mbusC6VIF2D		OBJECT-TYPE
			SYNTAX	INTEGER
			ACCESS	read-only
			STATUS	current
	DESCRIPTION ""
			::= { mbusC6 96 }

mbusC6Value2D		OBJECT-TYPE
			SYNTAX	INTEGER
			ACCESS	read-only
			STATUS	current
	DESCRIPTION ""
			::= { mbusC6 97 }

mbusC6VIF2E		OBJECT-TYPE
			SYNTAX	INTEGER
			ACCESS	read-only
			STATUS	current
	DESCRIPTION ""
			::= { mbusC6 98 }

mbusC6Value2E		OBJECT-TYPE
			SYNTAX	INTEGER
			ACCESS	read-only
			STATUS	current
	DESCRIPTION ""
			::= { mbusC6 99 }

mbusC6VIF2F		OBJECT-TYPE
			SYNTAX	INTEGER
			ACCESS	read-only
			STATUS	current
	DESCRIPTION ""
			::= { mbusC6 100 }

mbusC6Value2F		OBJECT-TYPE
			SYNTAX	INTEGER
			ACCESS	read-only
			STATUS	current
	DESCRIPTION ""
			::= { mbusC6 101 }

mbusC7			OBJECT IDENTIFIER ::= { mbus 199 }

mbusC7IdNumber		OBJECT-TYPE
			SYNTAX	Gauge
			ACCESS	read-only
			STATUS	current
	DESCRIPTION ""
			::= { mbusC7 1 }

mbusC7Manufacturer	OBJECT-TYPE
			SYNTAX	Gauge
			ACCESS	read-only
			STATUS	current
	DESCRIPTION ""
			::= { mbusC7 2 }

mbusC7Version		OBJECT-TYPE
			SYNTAX	Gauge
			ACCESS	read-only
			STATUS	current
	DESCRIPTION ""
			::= { mbusC7 3 }

mbusC7Medium		OBJECT-TYPE
			SYNTAX	Gauge
			ACCESS	read-only
			STATUS	current
	DESCRIPTION ""
			::= { mbusC7 4 }

mbusC7Status		OBJECT-TYPE
			SYNTAX	Gauge
			ACCESS	read-only
			STATUS	current
	DESCRIPTION ""
			::= { mbusC7 5 }

mbusC7VIF00		OBJECT-TYPE
			SYNTAX	INTEGER
			ACCESS	read-only
			STATUS	current
	DESCRIPTION ""
			::= { mbusC7 6 }

mbusC7Value00		OBJECT-TYPE
			SYNTAX	INTEGER
			ACCESS	read-only
			STATUS	current
	DESCRIPTION ""
			::= { mbusC7 7 }

mbusC7VIF01		OBJECT-TYPE
			SYNTAX	INTEGER
			ACCESS	read-only
			STATUS	current
	DESCRIPTION ""
			::= { mbusC7 8 }

mbusC7Value01		OBJECT-TYPE
			SYNTAX	INTEGER
			ACCESS	read-only
			STATUS	current
	DESCRIPTION ""
			::= { mbusC7 9 }

mbusC7VIF02		OBJECT-TYPE
			SYNTAX	INTEGER
			ACCESS	read-only
			STATUS	current
	DESCRIPTION ""
			::= { mbusC7 10 }

mbusC7Value02		OBJECT-TYPE
			SYNTAX	INTEGER
			ACCESS	read-only
			STATUS	current
	DESCRIPTION ""
			::= { mbusC7 11 }

mbusC7VIF03		OBJECT-TYPE
			SYNTAX	INTEGER
			ACCESS	read-only
			STATUS	current
	DESCRIPTION ""
			::= { mbusC7 12 }

mbusC7Value03		OBJECT-TYPE
			SYNTAX	INTEGER
			ACCESS	read-only
			STATUS	current
	DESCRIPTION ""
			::= { mbusC7 13 }

mbusC7VIF04		OBJECT-TYPE
			SYNTAX	INTEGER
			ACCESS	read-only
			STATUS	current
	DESCRIPTION ""
			::= { mbusC7 14 }

mbusC7Value04		OBJECT-TYPE
			SYNTAX	INTEGER
			ACCESS	read-only
			STATUS	current
	DESCRIPTION ""
			::= { mbusC7 15 }

mbusC7VIF05		OBJECT-TYPE
			SYNTAX	INTEGER
			ACCESS	read-only
			STATUS	current
	DESCRIPTION ""
			::= { mbusC7 16 }

mbusC7Value05		OBJECT-TYPE
			SYNTAX	INTEGER
			ACCESS	read-only
			STATUS	current
	DESCRIPTION ""
			::= { mbusC7 17 }

mbusC7VIF06		OBJECT-TYPE
			SYNTAX	INTEGER
			ACCESS	read-only
			STATUS	current
	DESCRIPTION ""
			::= { mbusC7 18 }

mbusC7Value06		OBJECT-TYPE
			SYNTAX	INTEGER
			ACCESS	read-only
			STATUS	current
	DESCRIPTION ""
			::= { mbusC7 19 }

mbusC7VIF07		OBJECT-TYPE
			SYNTAX	INTEGER
			ACCESS	read-only
			STATUS	current
	DESCRIPTION ""
			::= { mbusC7 20 }

mbusC7Value07		OBJECT-TYPE
			SYNTAX	INTEGER
			ACCESS	read-only
			STATUS	current
	DESCRIPTION ""
			::= { mbusC7 21 }

mbusC7VIF08		OBJECT-TYPE
			SYNTAX	INTEGER
			ACCESS	read-only
			STATUS	current
	DESCRIPTION ""
			::= { mbusC7 22 }

mbusC7Value08		OBJECT-TYPE
			SYNTAX	INTEGER
			ACCESS	read-only
			STATUS	current
	DESCRIPTION ""
			::= { mbusC7 23 }

mbusC7VIF09		OBJECT-TYPE
			SYNTAX	INTEGER
			ACCESS	read-only
			STATUS	current
	DESCRIPTION ""
			::= { mbusC7 24 }

mbusC7Value09		OBJECT-TYPE
			SYNTAX	INTEGER
			ACCESS	read-only
			STATUS	current
	DESCRIPTION ""
			::= { mbusC7 25 }

mbusC7VIF0A		OBJECT-TYPE
			SYNTAX	INTEGER
			ACCESS	read-only
			STATUS	current
	DESCRIPTION ""
			::= { mbusC7 26 }

mbusC7Value0A		OBJECT-TYPE
			SYNTAX	INTEGER
			ACCESS	read-only
			STATUS	current
	DESCRIPTION ""
			::= { mbusC7 27 }

mbusC7VIF0B		OBJECT-TYPE
			SYNTAX	INTEGER
			ACCESS	read-only
			STATUS	current
	DESCRIPTION ""
			::= { mbusC7 28 }

mbusC7Value0B		OBJECT-TYPE
			SYNTAX	INTEGER
			ACCESS	read-only
			STATUS	current
	DESCRIPTION ""
			::= { mbusC7 29 }

mbusC7VIF0C		OBJECT-TYPE
			SYNTAX	INTEGER
			ACCESS	read-only
			STATUS	current
	DESCRIPTION ""
			::= { mbusC7 30 }

mbusC7Value0C		OBJECT-TYPE
			SYNTAX	INTEGER
			ACCESS	read-only
			STATUS	current
	DESCRIPTION ""
			::= { mbusC7 31 }

mbusC7VIF0D		OBJECT-TYPE
			SYNTAX	INTEGER
			ACCESS	read-only
			STATUS	current
	DESCRIPTION ""
			::= { mbusC7 32 }

mbusC7Value0D		OBJECT-TYPE
			SYNTAX	INTEGER
			ACCESS	read-only
			STATUS	current
	DESCRIPTION ""
			::= { mbusC7 33 }

mbusC7VIF0E		OBJECT-TYPE
			SYNTAX	INTEGER
			ACCESS	read-only
			STATUS	current
	DESCRIPTION ""
			::= { mbusC7 34 }

mbusC7Value0E		OBJECT-TYPE
			SYNTAX	INTEGER
			ACCESS	read-only
			STATUS	current
	DESCRIPTION ""
			::= { mbusC7 35 }

mbusC7VIF0F		OBJECT-TYPE
			SYNTAX	INTEGER
			ACCESS	read-only
			STATUS	current
	DESCRIPTION ""
			::= { mbusC7 36 }

mbusC7Value0F		OBJECT-TYPE
			SYNTAX	INTEGER
			ACCESS	read-only
			STATUS	current
	DESCRIPTION ""
			::= { mbusC7 37 }

mbusC7VIF10		OBJECT-TYPE
			SYNTAX	INTEGER
			ACCESS	read-only
			STATUS	current
	DESCRIPTION ""
			::= { mbusC7 38 }

mbusC7Value10		OBJECT-TYPE
			SYNTAX	INTEGER
			ACCESS	read-only
			STATUS	current
	DESCRIPTION ""
			::= { mbusC7 39 }

mbusC7VIF11		OBJECT-TYPE
			SYNTAX	INTEGER
			ACCESS	read-only
			STATUS	current
	DESCRIPTION ""
			::= { mbusC7 40 }

mbusC7Value11		OBJECT-TYPE
			SYNTAX	INTEGER
			ACCESS	read-only
			STATUS	current
	DESCRIPTION ""
			::= { mbusC7 41 }

mbusC7VIF12		OBJECT-TYPE
			SYNTAX	INTEGER
			ACCESS	read-only
			STATUS	current
	DESCRIPTION ""
			::= { mbusC7 42 }

mbusC7Value12		OBJECT-TYPE
			SYNTAX	INTEGER
			ACCESS	read-only
			STATUS	current
	DESCRIPTION ""
			::= { mbusC7 43 }

mbusC7VIF13		OBJECT-TYPE
			SYNTAX	INTEGER
			ACCESS	read-only
			STATUS	current
	DESCRIPTION ""
			::= { mbusC7 44 }

mbusC7Value13		OBJECT-TYPE
			SYNTAX	INTEGER
			ACCESS	read-only
			STATUS	current
	DESCRIPTION ""
			::= { mbusC7 45 }

mbusC7VIF14		OBJECT-TYPE
			SYNTAX	INTEGER
			ACCESS	read-only
			STATUS	current
	DESCRIPTION ""
			::= { mbusC7 46 }

mbusC7Value14		OBJECT-TYPE
			SYNTAX	INTEGER
			ACCESS	read-only
			STATUS	current
	DESCRIPTION ""
			::= { mbusC7 47 }

mbusC7VIF15		OBJECT-TYPE
			SYNTAX	INTEGER
			ACCESS	read-only
			STATUS	current
	DESCRIPTION ""
			::= { mbusC7 48 }

mbusC7Value15		OBJECT-TYPE
			SYNTAX	INTEGER
			ACCESS	read-only
			STATUS	current
	DESCRIPTION ""
			::= { mbusC7 49 }

mbusC7VIF16		OBJECT-TYPE
			SYNTAX	INTEGER
			ACCESS	read-only
			STATUS	current
	DESCRIPTION ""
			::= { mbusC7 50 }

mbusC7Value16		OBJECT-TYPE
			SYNTAX	INTEGER
			ACCESS	read-only
			STATUS	current
	DESCRIPTION ""
			::= { mbusC7 51 }

mbusC7VIF17		OBJECT-TYPE
			SYNTAX	INTEGER
			ACCESS	read-only
			STATUS	current
	DESCRIPTION ""
			::= { mbusC7 52 }

mbusC7Value17		OBJECT-TYPE
			SYNTAX	INTEGER
			ACCESS	read-only
			STATUS	current
	DESCRIPTION ""
			::= { mbusC7 53 }

mbusC7VIF18		OBJECT-TYPE
			SYNTAX	INTEGER
			ACCESS	read-only
			STATUS	current
	DESCRIPTION ""
			::= { mbusC7 54 }

mbusC7Value18		OBJECT-TYPE
			SYNTAX	INTEGER
			ACCESS	read-only
			STATUS	current
	DESCRIPTION ""
			::= { mbusC7 55 }

mbusC7VIF19		OBJECT-TYPE
			SYNTAX	INTEGER
			ACCESS	read-only
			STATUS	current
	DESCRIPTION ""
			::= { mbusC7 56 }

mbusC7Value19		OBJECT-TYPE
			SYNTAX	INTEGER
			ACCESS	read-only
			STATUS	current
	DESCRIPTION ""
			::= { mbusC7 57 }

mbusC7VIF1A		OBJECT-TYPE
			SYNTAX	INTEGER
			ACCESS	read-only
			STATUS	current
	DESCRIPTION ""
			::= { mbusC7 58 }

mbusC7Value1A		OBJECT-TYPE
			SYNTAX	INTEGER
			ACCESS	read-only
			STATUS	current
	DESCRIPTION ""
			::= { mbusC7 59 }

mbusC7VIF1B		OBJECT-TYPE
			SYNTAX	INTEGER
			ACCESS	read-only
			STATUS	current
	DESCRIPTION ""
			::= { mbusC7 60 }

mbusC7Value1B		OBJECT-TYPE
			SYNTAX	INTEGER
			ACCESS	read-only
			STATUS	current
	DESCRIPTION ""
			::= { mbusC7 61 }

mbusC7VIF1C		OBJECT-TYPE
			SYNTAX	INTEGER
			ACCESS	read-only
			STATUS	current
	DESCRIPTION ""
			::= { mbusC7 62 }

mbusC7Value1C		OBJECT-TYPE
			SYNTAX	INTEGER
			ACCESS	read-only
			STATUS	current
	DESCRIPTION ""
			::= { mbusC7 63 }

mbusC7VIF1D		OBJECT-TYPE
			SYNTAX	INTEGER
			ACCESS	read-only
			STATUS	current
	DESCRIPTION ""
			::= { mbusC7 64 }

mbusC7Value1D		OBJECT-TYPE
			SYNTAX	INTEGER
			ACCESS	read-only
			STATUS	current
	DESCRIPTION ""
			::= { mbusC7 65 }

mbusC7VIF1E		OBJECT-TYPE
			SYNTAX	INTEGER
			ACCESS	read-only
			STATUS	current
	DESCRIPTION ""
			::= { mbusC7 66 }

mbusC7Value1E		OBJECT-TYPE
			SYNTAX	INTEGER
			ACCESS	read-only
			STATUS	current
	DESCRIPTION ""
			::= { mbusC7 67 }

mbusC7VIF1F		OBJECT-TYPE
			SYNTAX	INTEGER
			ACCESS	read-only
			STATUS	current
	DESCRIPTION ""
			::= { mbusC7 68 }

mbusC7Value1F		OBJECT-TYPE
			SYNTAX	INTEGER
			ACCESS	read-only
			STATUS	current
	DESCRIPTION ""
			::= { mbusC7 69 }

mbusC7VIF20		OBJECT-TYPE
			SYNTAX	INTEGER
			ACCESS	read-only
			STATUS	current
	DESCRIPTION ""
			::= { mbusC7 70 }

mbusC7Value20		OBJECT-TYPE
			SYNTAX	INTEGER
			ACCESS	read-only
			STATUS	current
	DESCRIPTION ""
			::= { mbusC7 71 }

mbusC7VIF21		OBJECT-TYPE
			SYNTAX	INTEGER
			ACCESS	read-only
			STATUS	current
	DESCRIPTION ""
			::= { mbusC7 72 }

mbusC7Value21		OBJECT-TYPE
			SYNTAX	INTEGER
			ACCESS	read-only
			STATUS	current
	DESCRIPTION ""
			::= { mbusC7 73 }

mbusC7VIF22		OBJECT-TYPE
			SYNTAX	INTEGER
			ACCESS	read-only
			STATUS	current
	DESCRIPTION ""
			::= { mbusC7 74 }

mbusC7Value22		OBJECT-TYPE
			SYNTAX	INTEGER
			ACCESS	read-only
			STATUS	current
	DESCRIPTION ""
			::= { mbusC7 75 }

mbusC7VIF23		OBJECT-TYPE
			SYNTAX	INTEGER
			ACCESS	read-only
			STATUS	current
	DESCRIPTION ""
			::= { mbusC7 76 }

mbusC7Value23		OBJECT-TYPE
			SYNTAX	INTEGER
			ACCESS	read-only
			STATUS	current
	DESCRIPTION ""
			::= { mbusC7 77 }

mbusC7VIF24		OBJECT-TYPE
			SYNTAX	INTEGER
			ACCESS	read-only
			STATUS	current
	DESCRIPTION ""
			::= { mbusC7 78 }

mbusC7Value24		OBJECT-TYPE
			SYNTAX	INTEGER
			ACCESS	read-only
			STATUS	current
	DESCRIPTION ""
			::= { mbusC7 79 }

mbusC7VIF25		OBJECT-TYPE
			SYNTAX	INTEGER
			ACCESS	read-only
			STATUS	current
	DESCRIPTION ""
			::= { mbusC7 80 }

mbusC7Value25		OBJECT-TYPE
			SYNTAX	INTEGER
			ACCESS	read-only
			STATUS	current
	DESCRIPTION ""
			::= { mbusC7 81 }

mbusC7VIF26		OBJECT-TYPE
			SYNTAX	INTEGER
			ACCESS	read-only
			STATUS	current
	DESCRIPTION ""
			::= { mbusC7 82 }

mbusC7Value26		OBJECT-TYPE
			SYNTAX	INTEGER
			ACCESS	read-only
			STATUS	current
	DESCRIPTION ""
			::= { mbusC7 83 }

mbusC7VIF27		OBJECT-TYPE
			SYNTAX	INTEGER
			ACCESS	read-only
			STATUS	current
	DESCRIPTION ""
			::= { mbusC7 84 }

mbusC7Value27		OBJECT-TYPE
			SYNTAX	INTEGER
			ACCESS	read-only
			STATUS	current
	DESCRIPTION ""
			::= { mbusC7 85 }

mbusC7VIF28		OBJECT-TYPE
			SYNTAX	INTEGER
			ACCESS	read-only
			STATUS	current
	DESCRIPTION ""
			::= { mbusC7 86 }

mbusC7Value28		OBJECT-TYPE
			SYNTAX	INTEGER
			ACCESS	read-only
			STATUS	current
	DESCRIPTION ""
			::= { mbusC7 87 }

mbusC7VIF29		OBJECT-TYPE
			SYNTAX	INTEGER
			ACCESS	read-only
			STATUS	current
	DESCRIPTION ""
			::= { mbusC7 88 }

mbusC7Value29		OBJECT-TYPE
			SYNTAX	INTEGER
			ACCESS	read-only
			STATUS	current
	DESCRIPTION ""
			::= { mbusC7 89 }

mbusC7VIF2A		OBJECT-TYPE
			SYNTAX	INTEGER
			ACCESS	read-only
			STATUS	current
	DESCRIPTION ""
			::= { mbusC7 90 }

mbusC7Value2A		OBJECT-TYPE
			SYNTAX	INTEGER
			ACCESS	read-only
			STATUS	current
	DESCRIPTION ""
			::= { mbusC7 91 }

mbusC7VIF2B		OBJECT-TYPE
			SYNTAX	INTEGER
			ACCESS	read-only
			STATUS	current
	DESCRIPTION ""
			::= { mbusC7 92 }

mbusC7Value2B		OBJECT-TYPE
			SYNTAX	INTEGER
			ACCESS	read-only
			STATUS	current
	DESCRIPTION ""
			::= { mbusC7 93 }

mbusC7VIF2C		OBJECT-TYPE
			SYNTAX	INTEGER
			ACCESS	read-only
			STATUS	current
	DESCRIPTION ""
			::= { mbusC7 94 }

mbusC7Value2C		OBJECT-TYPE
			SYNTAX	INTEGER
			ACCESS	read-only
			STATUS	current
	DESCRIPTION ""
			::= { mbusC7 95 }

mbusC7VIF2D		OBJECT-TYPE
			SYNTAX	INTEGER
			ACCESS	read-only
			STATUS	current
	DESCRIPTION ""
			::= { mbusC7 96 }

mbusC7Value2D		OBJECT-TYPE
			SYNTAX	INTEGER
			ACCESS	read-only
			STATUS	current
	DESCRIPTION ""
			::= { mbusC7 97 }

mbusC7VIF2E		OBJECT-TYPE
			SYNTAX	INTEGER
			ACCESS	read-only
			STATUS	current
	DESCRIPTION ""
			::= { mbusC7 98 }

mbusC7Value2E		OBJECT-TYPE
			SYNTAX	INTEGER
			ACCESS	read-only
			STATUS	current
	DESCRIPTION ""
			::= { mbusC7 99 }

mbusC7VIF2F		OBJECT-TYPE
			SYNTAX	INTEGER
			ACCESS	read-only
			STATUS	current
	DESCRIPTION ""
			::= { mbusC7 100 }

mbusC7Value2F		OBJECT-TYPE
			SYNTAX	INTEGER
			ACCESS	read-only
			STATUS	current
	DESCRIPTION ""
			::= { mbusC7 101 }

mbusC8			OBJECT IDENTIFIER ::= { mbus 200 }

mbusC8IdNumber		OBJECT-TYPE
			SYNTAX	Gauge
			ACCESS	read-only
			STATUS	current
	DESCRIPTION ""
			::= { mbusC8 1 }

mbusC8Manufacturer	OBJECT-TYPE
			SYNTAX	Gauge
			ACCESS	read-only
			STATUS	current
	DESCRIPTION ""
			::= { mbusC8 2 }

mbusC8Version		OBJECT-TYPE
			SYNTAX	Gauge
			ACCESS	read-only
			STATUS	current
	DESCRIPTION ""
			::= { mbusC8 3 }

mbusC8Medium		OBJECT-TYPE
			SYNTAX	Gauge
			ACCESS	read-only
			STATUS	current
	DESCRIPTION ""
			::= { mbusC8 4 }

mbusC8Status		OBJECT-TYPE
			SYNTAX	Gauge
			ACCESS	read-only
			STATUS	current
	DESCRIPTION ""
			::= { mbusC8 5 }

mbusC8VIF00		OBJECT-TYPE
			SYNTAX	INTEGER
			ACCESS	read-only
			STATUS	current
	DESCRIPTION ""
			::= { mbusC8 6 }

mbusC8Value00		OBJECT-TYPE
			SYNTAX	INTEGER
			ACCESS	read-only
			STATUS	current
	DESCRIPTION ""
			::= { mbusC8 7 }

mbusC8VIF01		OBJECT-TYPE
			SYNTAX	INTEGER
			ACCESS	read-only
			STATUS	current
	DESCRIPTION ""
			::= { mbusC8 8 }

mbusC8Value01		OBJECT-TYPE
			SYNTAX	INTEGER
			ACCESS	read-only
			STATUS	current
	DESCRIPTION ""
			::= { mbusC8 9 }

mbusC8VIF02		OBJECT-TYPE
			SYNTAX	INTEGER
			ACCESS	read-only
			STATUS	current
	DESCRIPTION ""
			::= { mbusC8 10 }

mbusC8Value02		OBJECT-TYPE
			SYNTAX	INTEGER
			ACCESS	read-only
			STATUS	current
	DESCRIPTION ""
			::= { mbusC8 11 }

mbusC8VIF03		OBJECT-TYPE
			SYNTAX	INTEGER
			ACCESS	read-only
			STATUS	current
	DESCRIPTION ""
			::= { mbusC8 12 }

mbusC8Value03		OBJECT-TYPE
			SYNTAX	INTEGER
			ACCESS	read-only
			STATUS	current
	DESCRIPTION ""
			::= { mbusC8 13 }

mbusC8VIF04		OBJECT-TYPE
			SYNTAX	INTEGER
			ACCESS	read-only
			STATUS	current
	DESCRIPTION ""
			::= { mbusC8 14 }

mbusC8Value04		OBJECT-TYPE
			SYNTAX	INTEGER
			ACCESS	read-only
			STATUS	current
	DESCRIPTION ""
			::= { mbusC8 15 }

mbusC8VIF05		OBJECT-TYPE
			SYNTAX	INTEGER
			ACCESS	read-only
			STATUS	current
	DESCRIPTION ""
			::= { mbusC8 16 }

mbusC8Value05		OBJECT-TYPE
			SYNTAX	INTEGER
			ACCESS	read-only
			STATUS	current
	DESCRIPTION ""
			::= { mbusC8 17 }

mbusC8VIF06		OBJECT-TYPE
			SYNTAX	INTEGER
			ACCESS	read-only
			STATUS	current
	DESCRIPTION ""
			::= { mbusC8 18 }

mbusC8Value06		OBJECT-TYPE
			SYNTAX	INTEGER
			ACCESS	read-only
			STATUS	current
	DESCRIPTION ""
			::= { mbusC8 19 }

mbusC8VIF07		OBJECT-TYPE
			SYNTAX	INTEGER
			ACCESS	read-only
			STATUS	current
	DESCRIPTION ""
			::= { mbusC8 20 }

mbusC8Value07		OBJECT-TYPE
			SYNTAX	INTEGER
			ACCESS	read-only
			STATUS	current
	DESCRIPTION ""
			::= { mbusC8 21 }

mbusC8VIF08		OBJECT-TYPE
			SYNTAX	INTEGER
			ACCESS	read-only
			STATUS	current
	DESCRIPTION ""
			::= { mbusC8 22 }

mbusC8Value08		OBJECT-TYPE
			SYNTAX	INTEGER
			ACCESS	read-only
			STATUS	current
	DESCRIPTION ""
			::= { mbusC8 23 }

mbusC8VIF09		OBJECT-TYPE
			SYNTAX	INTEGER
			ACCESS	read-only
			STATUS	current
	DESCRIPTION ""
			::= { mbusC8 24 }

mbusC8Value09		OBJECT-TYPE
			SYNTAX	INTEGER
			ACCESS	read-only
			STATUS	current
	DESCRIPTION ""
			::= { mbusC8 25 }

mbusC8VIF0A		OBJECT-TYPE
			SYNTAX	INTEGER
			ACCESS	read-only
			STATUS	current
	DESCRIPTION ""
			::= { mbusC8 26 }

mbusC8Value0A		OBJECT-TYPE
			SYNTAX	INTEGER
			ACCESS	read-only
			STATUS	current
	DESCRIPTION ""
			::= { mbusC8 27 }

mbusC8VIF0B		OBJECT-TYPE
			SYNTAX	INTEGER
			ACCESS	read-only
			STATUS	current
	DESCRIPTION ""
			::= { mbusC8 28 }

mbusC8Value0B		OBJECT-TYPE
			SYNTAX	INTEGER
			ACCESS	read-only
			STATUS	current
	DESCRIPTION ""
			::= { mbusC8 29 }

mbusC8VIF0C		OBJECT-TYPE
			SYNTAX	INTEGER
			ACCESS	read-only
			STATUS	current
	DESCRIPTION ""
			::= { mbusC8 30 }

mbusC8Value0C		OBJECT-TYPE
			SYNTAX	INTEGER
			ACCESS	read-only
			STATUS	current
	DESCRIPTION ""
			::= { mbusC8 31 }

mbusC8VIF0D		OBJECT-TYPE
			SYNTAX	INTEGER
			ACCESS	read-only
			STATUS	current
	DESCRIPTION ""
			::= { mbusC8 32 }

mbusC8Value0D		OBJECT-TYPE
			SYNTAX	INTEGER
			ACCESS	read-only
			STATUS	current
	DESCRIPTION ""
			::= { mbusC8 33 }

mbusC8VIF0E		OBJECT-TYPE
			SYNTAX	INTEGER
			ACCESS	read-only
			STATUS	current
	DESCRIPTION ""
			::= { mbusC8 34 }

mbusC8Value0E		OBJECT-TYPE
			SYNTAX	INTEGER
			ACCESS	read-only
			STATUS	current
	DESCRIPTION ""
			::= { mbusC8 35 }

mbusC8VIF0F		OBJECT-TYPE
			SYNTAX	INTEGER
			ACCESS	read-only
			STATUS	current
	DESCRIPTION ""
			::= { mbusC8 36 }

mbusC8Value0F		OBJECT-TYPE
			SYNTAX	INTEGER
			ACCESS	read-only
			STATUS	current
	DESCRIPTION ""
			::= { mbusC8 37 }

mbusC8VIF10		OBJECT-TYPE
			SYNTAX	INTEGER
			ACCESS	read-only
			STATUS	current
	DESCRIPTION ""
			::= { mbusC8 38 }

mbusC8Value10		OBJECT-TYPE
			SYNTAX	INTEGER
			ACCESS	read-only
			STATUS	current
	DESCRIPTION ""
			::= { mbusC8 39 }

mbusC8VIF11		OBJECT-TYPE
			SYNTAX	INTEGER
			ACCESS	read-only
			STATUS	current
	DESCRIPTION ""
			::= { mbusC8 40 }

mbusC8Value11		OBJECT-TYPE
			SYNTAX	INTEGER
			ACCESS	read-only
			STATUS	current
	DESCRIPTION ""
			::= { mbusC8 41 }

mbusC8VIF12		OBJECT-TYPE
			SYNTAX	INTEGER
			ACCESS	read-only
			STATUS	current
	DESCRIPTION ""
			::= { mbusC8 42 }

mbusC8Value12		OBJECT-TYPE
			SYNTAX	INTEGER
			ACCESS	read-only
			STATUS	current
	DESCRIPTION ""
			::= { mbusC8 43 }

mbusC8VIF13		OBJECT-TYPE
			SYNTAX	INTEGER
			ACCESS	read-only
			STATUS	current
	DESCRIPTION ""
			::= { mbusC8 44 }

mbusC8Value13		OBJECT-TYPE
			SYNTAX	INTEGER
			ACCESS	read-only
			STATUS	current
	DESCRIPTION ""
			::= { mbusC8 45 }

mbusC8VIF14		OBJECT-TYPE
			SYNTAX	INTEGER
			ACCESS	read-only
			STATUS	current
	DESCRIPTION ""
			::= { mbusC8 46 }

mbusC8Value14		OBJECT-TYPE
			SYNTAX	INTEGER
			ACCESS	read-only
			STATUS	current
	DESCRIPTION ""
			::= { mbusC8 47 }

mbusC8VIF15		OBJECT-TYPE
			SYNTAX	INTEGER
			ACCESS	read-only
			STATUS	current
	DESCRIPTION ""
			::= { mbusC8 48 }

mbusC8Value15		OBJECT-TYPE
			SYNTAX	INTEGER
			ACCESS	read-only
			STATUS	current
	DESCRIPTION ""
			::= { mbusC8 49 }

mbusC8VIF16		OBJECT-TYPE
			SYNTAX	INTEGER
			ACCESS	read-only
			STATUS	current
	DESCRIPTION ""
			::= { mbusC8 50 }

mbusC8Value16		OBJECT-TYPE
			SYNTAX	INTEGER
			ACCESS	read-only
			STATUS	current
	DESCRIPTION ""
			::= { mbusC8 51 }

mbusC8VIF17		OBJECT-TYPE
			SYNTAX	INTEGER
			ACCESS	read-only
			STATUS	current
	DESCRIPTION ""
			::= { mbusC8 52 }

mbusC8Value17		OBJECT-TYPE
			SYNTAX	INTEGER
			ACCESS	read-only
			STATUS	current
	DESCRIPTION ""
			::= { mbusC8 53 }

mbusC8VIF18		OBJECT-TYPE
			SYNTAX	INTEGER
			ACCESS	read-only
			STATUS	current
	DESCRIPTION ""
			::= { mbusC8 54 }

mbusC8Value18		OBJECT-TYPE
			SYNTAX	INTEGER
			ACCESS	read-only
			STATUS	current
	DESCRIPTION ""
			::= { mbusC8 55 }

mbusC8VIF19		OBJECT-TYPE
			SYNTAX	INTEGER
			ACCESS	read-only
			STATUS	current
	DESCRIPTION ""
			::= { mbusC8 56 }

mbusC8Value19		OBJECT-TYPE
			SYNTAX	INTEGER
			ACCESS	read-only
			STATUS	current
	DESCRIPTION ""
			::= { mbusC8 57 }

mbusC8VIF1A		OBJECT-TYPE
			SYNTAX	INTEGER
			ACCESS	read-only
			STATUS	current
	DESCRIPTION ""
			::= { mbusC8 58 }

mbusC8Value1A		OBJECT-TYPE
			SYNTAX	INTEGER
			ACCESS	read-only
			STATUS	current
	DESCRIPTION ""
			::= { mbusC8 59 }

mbusC8VIF1B		OBJECT-TYPE
			SYNTAX	INTEGER
			ACCESS	read-only
			STATUS	current
	DESCRIPTION ""
			::= { mbusC8 60 }

mbusC8Value1B		OBJECT-TYPE
			SYNTAX	INTEGER
			ACCESS	read-only
			STATUS	current
	DESCRIPTION ""
			::= { mbusC8 61 }

mbusC8VIF1C		OBJECT-TYPE
			SYNTAX	INTEGER
			ACCESS	read-only
			STATUS	current
	DESCRIPTION ""
			::= { mbusC8 62 }

mbusC8Value1C		OBJECT-TYPE
			SYNTAX	INTEGER
			ACCESS	read-only
			STATUS	current
	DESCRIPTION ""
			::= { mbusC8 63 }

mbusC8VIF1D		OBJECT-TYPE
			SYNTAX	INTEGER
			ACCESS	read-only
			STATUS	current
	DESCRIPTION ""
			::= { mbusC8 64 }

mbusC8Value1D		OBJECT-TYPE
			SYNTAX	INTEGER
			ACCESS	read-only
			STATUS	current
	DESCRIPTION ""
			::= { mbusC8 65 }

mbusC8VIF1E		OBJECT-TYPE
			SYNTAX	INTEGER
			ACCESS	read-only
			STATUS	current
	DESCRIPTION ""
			::= { mbusC8 66 }

mbusC8Value1E		OBJECT-TYPE
			SYNTAX	INTEGER
			ACCESS	read-only
			STATUS	current
	DESCRIPTION ""
			::= { mbusC8 67 }

mbusC8VIF1F		OBJECT-TYPE
			SYNTAX	INTEGER
			ACCESS	read-only
			STATUS	current
	DESCRIPTION ""
			::= { mbusC8 68 }

mbusC8Value1F		OBJECT-TYPE
			SYNTAX	INTEGER
			ACCESS	read-only
			STATUS	current
	DESCRIPTION ""
			::= { mbusC8 69 }

mbusC8VIF20		OBJECT-TYPE
			SYNTAX	INTEGER
			ACCESS	read-only
			STATUS	current
	DESCRIPTION ""
			::= { mbusC8 70 }

mbusC8Value20		OBJECT-TYPE
			SYNTAX	INTEGER
			ACCESS	read-only
			STATUS	current
	DESCRIPTION ""
			::= { mbusC8 71 }

mbusC8VIF21		OBJECT-TYPE
			SYNTAX	INTEGER
			ACCESS	read-only
			STATUS	current
	DESCRIPTION ""
			::= { mbusC8 72 }

mbusC8Value21		OBJECT-TYPE
			SYNTAX	INTEGER
			ACCESS	read-only
			STATUS	current
	DESCRIPTION ""
			::= { mbusC8 73 }

mbusC8VIF22		OBJECT-TYPE
			SYNTAX	INTEGER
			ACCESS	read-only
			STATUS	current
	DESCRIPTION ""
			::= { mbusC8 74 }

mbusC8Value22		OBJECT-TYPE
			SYNTAX	INTEGER
			ACCESS	read-only
			STATUS	current
	DESCRIPTION ""
			::= { mbusC8 75 }

mbusC8VIF23		OBJECT-TYPE
			SYNTAX	INTEGER
			ACCESS	read-only
			STATUS	current
	DESCRIPTION ""
			::= { mbusC8 76 }

mbusC8Value23		OBJECT-TYPE
			SYNTAX	INTEGER
			ACCESS	read-only
			STATUS	current
	DESCRIPTION ""
			::= { mbusC8 77 }

mbusC8VIF24		OBJECT-TYPE
			SYNTAX	INTEGER
			ACCESS	read-only
			STATUS	current
	DESCRIPTION ""
			::= { mbusC8 78 }

mbusC8Value24		OBJECT-TYPE
			SYNTAX	INTEGER
			ACCESS	read-only
			STATUS	current
	DESCRIPTION ""
			::= { mbusC8 79 }

mbusC8VIF25		OBJECT-TYPE
			SYNTAX	INTEGER
			ACCESS	read-only
			STATUS	current
	DESCRIPTION ""
			::= { mbusC8 80 }

mbusC8Value25		OBJECT-TYPE
			SYNTAX	INTEGER
			ACCESS	read-only
			STATUS	current
	DESCRIPTION ""
			::= { mbusC8 81 }

mbusC8VIF26		OBJECT-TYPE
			SYNTAX	INTEGER
			ACCESS	read-only
			STATUS	current
	DESCRIPTION ""
			::= { mbusC8 82 }

mbusC8Value26		OBJECT-TYPE
			SYNTAX	INTEGER
			ACCESS	read-only
			STATUS	current
	DESCRIPTION ""
			::= { mbusC8 83 }

mbusC8VIF27		OBJECT-TYPE
			SYNTAX	INTEGER
			ACCESS	read-only
			STATUS	current
	DESCRIPTION ""
			::= { mbusC8 84 }

mbusC8Value27		OBJECT-TYPE
			SYNTAX	INTEGER
			ACCESS	read-only
			STATUS	current
	DESCRIPTION ""
			::= { mbusC8 85 }

mbusC8VIF28		OBJECT-TYPE
			SYNTAX	INTEGER
			ACCESS	read-only
			STATUS	current
	DESCRIPTION ""
			::= { mbusC8 86 }

mbusC8Value28		OBJECT-TYPE
			SYNTAX	INTEGER
			ACCESS	read-only
			STATUS	current
	DESCRIPTION ""
			::= { mbusC8 87 }

mbusC8VIF29		OBJECT-TYPE
			SYNTAX	INTEGER
			ACCESS	read-only
			STATUS	current
	DESCRIPTION ""
			::= { mbusC8 88 }

mbusC8Value29		OBJECT-TYPE
			SYNTAX	INTEGER
			ACCESS	read-only
			STATUS	current
	DESCRIPTION ""
			::= { mbusC8 89 }

mbusC8VIF2A		OBJECT-TYPE
			SYNTAX	INTEGER
			ACCESS	read-only
			STATUS	current
	DESCRIPTION ""
			::= { mbusC8 90 }

mbusC8Value2A		OBJECT-TYPE
			SYNTAX	INTEGER
			ACCESS	read-only
			STATUS	current
	DESCRIPTION ""
			::= { mbusC8 91 }

mbusC8VIF2B		OBJECT-TYPE
			SYNTAX	INTEGER
			ACCESS	read-only
			STATUS	current
	DESCRIPTION ""
			::= { mbusC8 92 }

mbusC8Value2B		OBJECT-TYPE
			SYNTAX	INTEGER
			ACCESS	read-only
			STATUS	current
	DESCRIPTION ""
			::= { mbusC8 93 }

mbusC8VIF2C		OBJECT-TYPE
			SYNTAX	INTEGER
			ACCESS	read-only
			STATUS	current
	DESCRIPTION ""
			::= { mbusC8 94 }

mbusC8Value2C		OBJECT-TYPE
			SYNTAX	INTEGER
			ACCESS	read-only
			STATUS	current
	DESCRIPTION ""
			::= { mbusC8 95 }

mbusC8VIF2D		OBJECT-TYPE
			SYNTAX	INTEGER
			ACCESS	read-only
			STATUS	current
	DESCRIPTION ""
			::= { mbusC8 96 }

mbusC8Value2D		OBJECT-TYPE
			SYNTAX	INTEGER
			ACCESS	read-only
			STATUS	current
	DESCRIPTION ""
			::= { mbusC8 97 }

mbusC8VIF2E		OBJECT-TYPE
			SYNTAX	INTEGER
			ACCESS	read-only
			STATUS	current
	DESCRIPTION ""
			::= { mbusC8 98 }

mbusC8Value2E		OBJECT-TYPE
			SYNTAX	INTEGER
			ACCESS	read-only
			STATUS	current
	DESCRIPTION ""
			::= { mbusC8 99 }

mbusC8VIF2F		OBJECT-TYPE
			SYNTAX	INTEGER
			ACCESS	read-only
			STATUS	current
	DESCRIPTION ""
			::= { mbusC8 100 }

mbusC8Value2F		OBJECT-TYPE
			SYNTAX	INTEGER
			ACCESS	read-only
			STATUS	current
	DESCRIPTION ""
			::= { mbusC8 101 }

mbusC9			OBJECT IDENTIFIER ::= { mbus 201 }

mbusC9IdNumber		OBJECT-TYPE
			SYNTAX	Gauge
			ACCESS	read-only
			STATUS	current
	DESCRIPTION ""
			::= { mbusC9 1 }

mbusC9Manufacturer	OBJECT-TYPE
			SYNTAX	Gauge
			ACCESS	read-only
			STATUS	current
	DESCRIPTION ""
			::= { mbusC9 2 }

mbusC9Version		OBJECT-TYPE
			SYNTAX	Gauge
			ACCESS	read-only
			STATUS	current
	DESCRIPTION ""
			::= { mbusC9 3 }

mbusC9Medium		OBJECT-TYPE
			SYNTAX	Gauge
			ACCESS	read-only
			STATUS	current
	DESCRIPTION ""
			::= { mbusC9 4 }

mbusC9Status		OBJECT-TYPE
			SYNTAX	Gauge
			ACCESS	read-only
			STATUS	current
	DESCRIPTION ""
			::= { mbusC9 5 }

mbusC9VIF00		OBJECT-TYPE
			SYNTAX	INTEGER
			ACCESS	read-only
			STATUS	current
	DESCRIPTION ""
			::= { mbusC9 6 }

mbusC9Value00		OBJECT-TYPE
			SYNTAX	INTEGER
			ACCESS	read-only
			STATUS	current
	DESCRIPTION ""
			::= { mbusC9 7 }

mbusC9VIF01		OBJECT-TYPE
			SYNTAX	INTEGER
			ACCESS	read-only
			STATUS	current
	DESCRIPTION ""
			::= { mbusC9 8 }

mbusC9Value01		OBJECT-TYPE
			SYNTAX	INTEGER
			ACCESS	read-only
			STATUS	current
	DESCRIPTION ""
			::= { mbusC9 9 }

mbusC9VIF02		OBJECT-TYPE
			SYNTAX	INTEGER
			ACCESS	read-only
			STATUS	current
	DESCRIPTION ""
			::= { mbusC9 10 }

mbusC9Value02		OBJECT-TYPE
			SYNTAX	INTEGER
			ACCESS	read-only
			STATUS	current
	DESCRIPTION ""
			::= { mbusC9 11 }

mbusC9VIF03		OBJECT-TYPE
			SYNTAX	INTEGER
			ACCESS	read-only
			STATUS	current
	DESCRIPTION ""
			::= { mbusC9 12 }

mbusC9Value03		OBJECT-TYPE
			SYNTAX	INTEGER
			ACCESS	read-only
			STATUS	current
	DESCRIPTION ""
			::= { mbusC9 13 }

mbusC9VIF04		OBJECT-TYPE
			SYNTAX	INTEGER
			ACCESS	read-only
			STATUS	current
	DESCRIPTION ""
			::= { mbusC9 14 }

mbusC9Value04		OBJECT-TYPE
			SYNTAX	INTEGER
			ACCESS	read-only
			STATUS	current
	DESCRIPTION ""
			::= { mbusC9 15 }

mbusC9VIF05		OBJECT-TYPE
			SYNTAX	INTEGER
			ACCESS	read-only
			STATUS	current
	DESCRIPTION ""
			::= { mbusC9 16 }

mbusC9Value05		OBJECT-TYPE
			SYNTAX	INTEGER
			ACCESS	read-only
			STATUS	current
	DESCRIPTION ""
			::= { mbusC9 17 }

mbusC9VIF06		OBJECT-TYPE
			SYNTAX	INTEGER
			ACCESS	read-only
			STATUS	current
	DESCRIPTION ""
			::= { mbusC9 18 }

mbusC9Value06		OBJECT-TYPE
			SYNTAX	INTEGER
			ACCESS	read-only
			STATUS	current
	DESCRIPTION ""
			::= { mbusC9 19 }

mbusC9VIF07		OBJECT-TYPE
			SYNTAX	INTEGER
			ACCESS	read-only
			STATUS	current
	DESCRIPTION ""
			::= { mbusC9 20 }

mbusC9Value07		OBJECT-TYPE
			SYNTAX	INTEGER
			ACCESS	read-only
			STATUS	current
	DESCRIPTION ""
			::= { mbusC9 21 }

mbusC9VIF08		OBJECT-TYPE
			SYNTAX	INTEGER
			ACCESS	read-only
			STATUS	current
	DESCRIPTION ""
			::= { mbusC9 22 }

mbusC9Value08		OBJECT-TYPE
			SYNTAX	INTEGER
			ACCESS	read-only
			STATUS	current
	DESCRIPTION ""
			::= { mbusC9 23 }

mbusC9VIF09		OBJECT-TYPE
			SYNTAX	INTEGER
			ACCESS	read-only
			STATUS	current
	DESCRIPTION ""
			::= { mbusC9 24 }

mbusC9Value09		OBJECT-TYPE
			SYNTAX	INTEGER
			ACCESS	read-only
			STATUS	current
	DESCRIPTION ""
			::= { mbusC9 25 }

mbusC9VIF0A		OBJECT-TYPE
			SYNTAX	INTEGER
			ACCESS	read-only
			STATUS	current
	DESCRIPTION ""
			::= { mbusC9 26 }

mbusC9Value0A		OBJECT-TYPE
			SYNTAX	INTEGER
			ACCESS	read-only
			STATUS	current
	DESCRIPTION ""
			::= { mbusC9 27 }

mbusC9VIF0B		OBJECT-TYPE
			SYNTAX	INTEGER
			ACCESS	read-only
			STATUS	current
	DESCRIPTION ""
			::= { mbusC9 28 }

mbusC9Value0B		OBJECT-TYPE
			SYNTAX	INTEGER
			ACCESS	read-only
			STATUS	current
	DESCRIPTION ""
			::= { mbusC9 29 }

mbusC9VIF0C		OBJECT-TYPE
			SYNTAX	INTEGER
			ACCESS	read-only
			STATUS	current
	DESCRIPTION ""
			::= { mbusC9 30 }

mbusC9Value0C		OBJECT-TYPE
			SYNTAX	INTEGER
			ACCESS	read-only
			STATUS	current
	DESCRIPTION ""
			::= { mbusC9 31 }

mbusC9VIF0D		OBJECT-TYPE
			SYNTAX	INTEGER
			ACCESS	read-only
			STATUS	current
	DESCRIPTION ""
			::= { mbusC9 32 }

mbusC9Value0D		OBJECT-TYPE
			SYNTAX	INTEGER
			ACCESS	read-only
			STATUS	current
	DESCRIPTION ""
			::= { mbusC9 33 }

mbusC9VIF0E		OBJECT-TYPE
			SYNTAX	INTEGER
			ACCESS	read-only
			STATUS	current
	DESCRIPTION ""
			::= { mbusC9 34 }

mbusC9Value0E		OBJECT-TYPE
			SYNTAX	INTEGER
			ACCESS	read-only
			STATUS	current
	DESCRIPTION ""
			::= { mbusC9 35 }

mbusC9VIF0F		OBJECT-TYPE
			SYNTAX	INTEGER
			ACCESS	read-only
			STATUS	current
	DESCRIPTION ""
			::= { mbusC9 36 }

mbusC9Value0F		OBJECT-TYPE
			SYNTAX	INTEGER
			ACCESS	read-only
			STATUS	current
	DESCRIPTION ""
			::= { mbusC9 37 }

mbusC9VIF10		OBJECT-TYPE
			SYNTAX	INTEGER
			ACCESS	read-only
			STATUS	current
	DESCRIPTION ""
			::= { mbusC9 38 }

mbusC9Value10		OBJECT-TYPE
			SYNTAX	INTEGER
			ACCESS	read-only
			STATUS	current
	DESCRIPTION ""
			::= { mbusC9 39 }

mbusC9VIF11		OBJECT-TYPE
			SYNTAX	INTEGER
			ACCESS	read-only
			STATUS	current
	DESCRIPTION ""
			::= { mbusC9 40 }

mbusC9Value11		OBJECT-TYPE
			SYNTAX	INTEGER
			ACCESS	read-only
			STATUS	current
	DESCRIPTION ""
			::= { mbusC9 41 }

mbusC9VIF12		OBJECT-TYPE
			SYNTAX	INTEGER
			ACCESS	read-only
			STATUS	current
	DESCRIPTION ""
			::= { mbusC9 42 }

mbusC9Value12		OBJECT-TYPE
			SYNTAX	INTEGER
			ACCESS	read-only
			STATUS	current
	DESCRIPTION ""
			::= { mbusC9 43 }

mbusC9VIF13		OBJECT-TYPE
			SYNTAX	INTEGER
			ACCESS	read-only
			STATUS	current
	DESCRIPTION ""
			::= { mbusC9 44 }

mbusC9Value13		OBJECT-TYPE
			SYNTAX	INTEGER
			ACCESS	read-only
			STATUS	current
	DESCRIPTION ""
			::= { mbusC9 45 }

mbusC9VIF14		OBJECT-TYPE
			SYNTAX	INTEGER
			ACCESS	read-only
			STATUS	current
	DESCRIPTION ""
			::= { mbusC9 46 }

mbusC9Value14		OBJECT-TYPE
			SYNTAX	INTEGER
			ACCESS	read-only
			STATUS	current
	DESCRIPTION ""
			::= { mbusC9 47 }

mbusC9VIF15		OBJECT-TYPE
			SYNTAX	INTEGER
			ACCESS	read-only
			STATUS	current
	DESCRIPTION ""
			::= { mbusC9 48 }

mbusC9Value15		OBJECT-TYPE
			SYNTAX	INTEGER
			ACCESS	read-only
			STATUS	current
	DESCRIPTION ""
			::= { mbusC9 49 }

mbusC9VIF16		OBJECT-TYPE
			SYNTAX	INTEGER
			ACCESS	read-only
			STATUS	current
	DESCRIPTION ""
			::= { mbusC9 50 }

mbusC9Value16		OBJECT-TYPE
			SYNTAX	INTEGER
			ACCESS	read-only
			STATUS	current
	DESCRIPTION ""
			::= { mbusC9 51 }

mbusC9VIF17		OBJECT-TYPE
			SYNTAX	INTEGER
			ACCESS	read-only
			STATUS	current
	DESCRIPTION ""
			::= { mbusC9 52 }

mbusC9Value17		OBJECT-TYPE
			SYNTAX	INTEGER
			ACCESS	read-only
			STATUS	current
	DESCRIPTION ""
			::= { mbusC9 53 }

mbusC9VIF18		OBJECT-TYPE
			SYNTAX	INTEGER
			ACCESS	read-only
			STATUS	current
	DESCRIPTION ""
			::= { mbusC9 54 }

mbusC9Value18		OBJECT-TYPE
			SYNTAX	INTEGER
			ACCESS	read-only
			STATUS	current
	DESCRIPTION ""
			::= { mbusC9 55 }

mbusC9VIF19		OBJECT-TYPE
			SYNTAX	INTEGER
			ACCESS	read-only
			STATUS	current
	DESCRIPTION ""
			::= { mbusC9 56 }

mbusC9Value19		OBJECT-TYPE
			SYNTAX	INTEGER
			ACCESS	read-only
			STATUS	current
	DESCRIPTION ""
			::= { mbusC9 57 }

mbusC9VIF1A		OBJECT-TYPE
			SYNTAX	INTEGER
			ACCESS	read-only
			STATUS	current
	DESCRIPTION ""
			::= { mbusC9 58 }

mbusC9Value1A		OBJECT-TYPE
			SYNTAX	INTEGER
			ACCESS	read-only
			STATUS	current
	DESCRIPTION ""
			::= { mbusC9 59 }

mbusC9VIF1B		OBJECT-TYPE
			SYNTAX	INTEGER
			ACCESS	read-only
			STATUS	current
	DESCRIPTION ""
			::= { mbusC9 60 }

mbusC9Value1B		OBJECT-TYPE
			SYNTAX	INTEGER
			ACCESS	read-only
			STATUS	current
	DESCRIPTION ""
			::= { mbusC9 61 }

mbusC9VIF1C		OBJECT-TYPE
			SYNTAX	INTEGER
			ACCESS	read-only
			STATUS	current
	DESCRIPTION ""
			::= { mbusC9 62 }

mbusC9Value1C		OBJECT-TYPE
			SYNTAX	INTEGER
			ACCESS	read-only
			STATUS	current
	DESCRIPTION ""
			::= { mbusC9 63 }

mbusC9VIF1D		OBJECT-TYPE
			SYNTAX	INTEGER
			ACCESS	read-only
			STATUS	current
	DESCRIPTION ""
			::= { mbusC9 64 }

mbusC9Value1D		OBJECT-TYPE
			SYNTAX	INTEGER
			ACCESS	read-only
			STATUS	current
	DESCRIPTION ""
			::= { mbusC9 65 }

mbusC9VIF1E		OBJECT-TYPE
			SYNTAX	INTEGER
			ACCESS	read-only
			STATUS	current
	DESCRIPTION ""
			::= { mbusC9 66 }

mbusC9Value1E		OBJECT-TYPE
			SYNTAX	INTEGER
			ACCESS	read-only
			STATUS	current
	DESCRIPTION ""
			::= { mbusC9 67 }

mbusC9VIF1F		OBJECT-TYPE
			SYNTAX	INTEGER
			ACCESS	read-only
			STATUS	current
	DESCRIPTION ""
			::= { mbusC9 68 }

mbusC9Value1F		OBJECT-TYPE
			SYNTAX	INTEGER
			ACCESS	read-only
			STATUS	current
	DESCRIPTION ""
			::= { mbusC9 69 }

mbusC9VIF20		OBJECT-TYPE
			SYNTAX	INTEGER
			ACCESS	read-only
			STATUS	current
	DESCRIPTION ""
			::= { mbusC9 70 }

mbusC9Value20		OBJECT-TYPE
			SYNTAX	INTEGER
			ACCESS	read-only
			STATUS	current
	DESCRIPTION ""
			::= { mbusC9 71 }

mbusC9VIF21		OBJECT-TYPE
			SYNTAX	INTEGER
			ACCESS	read-only
			STATUS	current
	DESCRIPTION ""
			::= { mbusC9 72 }

mbusC9Value21		OBJECT-TYPE
			SYNTAX	INTEGER
			ACCESS	read-only
			STATUS	current
	DESCRIPTION ""
			::= { mbusC9 73 }

mbusC9VIF22		OBJECT-TYPE
			SYNTAX	INTEGER
			ACCESS	read-only
			STATUS	current
	DESCRIPTION ""
			::= { mbusC9 74 }

mbusC9Value22		OBJECT-TYPE
			SYNTAX	INTEGER
			ACCESS	read-only
			STATUS	current
	DESCRIPTION ""
			::= { mbusC9 75 }

mbusC9VIF23		OBJECT-TYPE
			SYNTAX	INTEGER
			ACCESS	read-only
			STATUS	current
	DESCRIPTION ""
			::= { mbusC9 76 }

mbusC9Value23		OBJECT-TYPE
			SYNTAX	INTEGER
			ACCESS	read-only
			STATUS	current
	DESCRIPTION ""
			::= { mbusC9 77 }

mbusC9VIF24		OBJECT-TYPE
			SYNTAX	INTEGER
			ACCESS	read-only
			STATUS	current
	DESCRIPTION ""
			::= { mbusC9 78 }

mbusC9Value24		OBJECT-TYPE
			SYNTAX	INTEGER
			ACCESS	read-only
			STATUS	current
	DESCRIPTION ""
			::= { mbusC9 79 }

mbusC9VIF25		OBJECT-TYPE
			SYNTAX	INTEGER
			ACCESS	read-only
			STATUS	current
	DESCRIPTION ""
			::= { mbusC9 80 }

mbusC9Value25		OBJECT-TYPE
			SYNTAX	INTEGER
			ACCESS	read-only
			STATUS	current
	DESCRIPTION ""
			::= { mbusC9 81 }

mbusC9VIF26		OBJECT-TYPE
			SYNTAX	INTEGER
			ACCESS	read-only
			STATUS	current
	DESCRIPTION ""
			::= { mbusC9 82 }

mbusC9Value26		OBJECT-TYPE
			SYNTAX	INTEGER
			ACCESS	read-only
			STATUS	current
	DESCRIPTION ""
			::= { mbusC9 83 }

mbusC9VIF27		OBJECT-TYPE
			SYNTAX	INTEGER
			ACCESS	read-only
			STATUS	current
	DESCRIPTION ""
			::= { mbusC9 84 }

mbusC9Value27		OBJECT-TYPE
			SYNTAX	INTEGER
			ACCESS	read-only
			STATUS	current
	DESCRIPTION ""
			::= { mbusC9 85 }

mbusC9VIF28		OBJECT-TYPE
			SYNTAX	INTEGER
			ACCESS	read-only
			STATUS	current
	DESCRIPTION ""
			::= { mbusC9 86 }

mbusC9Value28		OBJECT-TYPE
			SYNTAX	INTEGER
			ACCESS	read-only
			STATUS	current
	DESCRIPTION ""
			::= { mbusC9 87 }

mbusC9VIF29		OBJECT-TYPE
			SYNTAX	INTEGER
			ACCESS	read-only
			STATUS	current
	DESCRIPTION ""
			::= { mbusC9 88 }

mbusC9Value29		OBJECT-TYPE
			SYNTAX	INTEGER
			ACCESS	read-only
			STATUS	current
	DESCRIPTION ""
			::= { mbusC9 89 }

mbusC9VIF2A		OBJECT-TYPE
			SYNTAX	INTEGER
			ACCESS	read-only
			STATUS	current
	DESCRIPTION ""
			::= { mbusC9 90 }

mbusC9Value2A		OBJECT-TYPE
			SYNTAX	INTEGER
			ACCESS	read-only
			STATUS	current
	DESCRIPTION ""
			::= { mbusC9 91 }

mbusC9VIF2B		OBJECT-TYPE
			SYNTAX	INTEGER
			ACCESS	read-only
			STATUS	current
	DESCRIPTION ""
			::= { mbusC9 92 }

mbusC9Value2B		OBJECT-TYPE
			SYNTAX	INTEGER
			ACCESS	read-only
			STATUS	current
	DESCRIPTION ""
			::= { mbusC9 93 }

mbusC9VIF2C		OBJECT-TYPE
			SYNTAX	INTEGER
			ACCESS	read-only
			STATUS	current
	DESCRIPTION ""
			::= { mbusC9 94 }

mbusC9Value2C		OBJECT-TYPE
			SYNTAX	INTEGER
			ACCESS	read-only
			STATUS	current
	DESCRIPTION ""
			::= { mbusC9 95 }

mbusC9VIF2D		OBJECT-TYPE
			SYNTAX	INTEGER
			ACCESS	read-only
			STATUS	current
	DESCRIPTION ""
			::= { mbusC9 96 }

mbusC9Value2D		OBJECT-TYPE
			SYNTAX	INTEGER
			ACCESS	read-only
			STATUS	current
	DESCRIPTION ""
			::= { mbusC9 97 }

mbusC9VIF2E		OBJECT-TYPE
			SYNTAX	INTEGER
			ACCESS	read-only
			STATUS	current
	DESCRIPTION ""
			::= { mbusC9 98 }

mbusC9Value2E		OBJECT-TYPE
			SYNTAX	INTEGER
			ACCESS	read-only
			STATUS	current
	DESCRIPTION ""
			::= { mbusC9 99 }

mbusC9VIF2F		OBJECT-TYPE
			SYNTAX	INTEGER
			ACCESS	read-only
			STATUS	current
	DESCRIPTION ""
			::= { mbusC9 100 }

mbusC9Value2F		OBJECT-TYPE
			SYNTAX	INTEGER
			ACCESS	read-only
			STATUS	current
	DESCRIPTION ""
			::= { mbusC9 101 }

mbusCA			OBJECT IDENTIFIER ::= { mbus 202 }

mbusCAIdNumber		OBJECT-TYPE
			SYNTAX	Gauge
			ACCESS	read-only
			STATUS	current
	DESCRIPTION ""
			::= { mbusCA 1 }

mbusCAManufacturer	OBJECT-TYPE
			SYNTAX	Gauge
			ACCESS	read-only
			STATUS	current
	DESCRIPTION ""
			::= { mbusCA 2 }

mbusCAVersion		OBJECT-TYPE
			SYNTAX	Gauge
			ACCESS	read-only
			STATUS	current
	DESCRIPTION ""
			::= { mbusCA 3 }

mbusCAMedium		OBJECT-TYPE
			SYNTAX	Gauge
			ACCESS	read-only
			STATUS	current
	DESCRIPTION ""
			::= { mbusCA 4 }

mbusCAStatus		OBJECT-TYPE
			SYNTAX	Gauge
			ACCESS	read-only
			STATUS	current
	DESCRIPTION ""
			::= { mbusCA 5 }

mbusCAVIF00		OBJECT-TYPE
			SYNTAX	INTEGER
			ACCESS	read-only
			STATUS	current
	DESCRIPTION ""
			::= { mbusCA 6 }

mbusCAValue00		OBJECT-TYPE
			SYNTAX	INTEGER
			ACCESS	read-only
			STATUS	current
	DESCRIPTION ""
			::= { mbusCA 7 }

mbusCAVIF01		OBJECT-TYPE
			SYNTAX	INTEGER
			ACCESS	read-only
			STATUS	current
	DESCRIPTION ""
			::= { mbusCA 8 }

mbusCAValue01		OBJECT-TYPE
			SYNTAX	INTEGER
			ACCESS	read-only
			STATUS	current
	DESCRIPTION ""
			::= { mbusCA 9 }

mbusCAVIF02		OBJECT-TYPE
			SYNTAX	INTEGER
			ACCESS	read-only
			STATUS	current
	DESCRIPTION ""
			::= { mbusCA 10 }

mbusCAValue02		OBJECT-TYPE
			SYNTAX	INTEGER
			ACCESS	read-only
			STATUS	current
	DESCRIPTION ""
			::= { mbusCA 11 }

mbusCAVIF03		OBJECT-TYPE
			SYNTAX	INTEGER
			ACCESS	read-only
			STATUS	current
	DESCRIPTION ""
			::= { mbusCA 12 }

mbusCAValue03		OBJECT-TYPE
			SYNTAX	INTEGER
			ACCESS	read-only
			STATUS	current
	DESCRIPTION ""
			::= { mbusCA 13 }

mbusCAVIF04		OBJECT-TYPE
			SYNTAX	INTEGER
			ACCESS	read-only
			STATUS	current
	DESCRIPTION ""
			::= { mbusCA 14 }

mbusCAValue04		OBJECT-TYPE
			SYNTAX	INTEGER
			ACCESS	read-only
			STATUS	current
	DESCRIPTION ""
			::= { mbusCA 15 }

mbusCAVIF05		OBJECT-TYPE
			SYNTAX	INTEGER
			ACCESS	read-only
			STATUS	current
	DESCRIPTION ""
			::= { mbusCA 16 }

mbusCAValue05		OBJECT-TYPE
			SYNTAX	INTEGER
			ACCESS	read-only
			STATUS	current
	DESCRIPTION ""
			::= { mbusCA 17 }

mbusCAVIF06		OBJECT-TYPE
			SYNTAX	INTEGER
			ACCESS	read-only
			STATUS	current
	DESCRIPTION ""
			::= { mbusCA 18 }

mbusCAValue06		OBJECT-TYPE
			SYNTAX	INTEGER
			ACCESS	read-only
			STATUS	current
	DESCRIPTION ""
			::= { mbusCA 19 }

mbusCAVIF07		OBJECT-TYPE
			SYNTAX	INTEGER
			ACCESS	read-only
			STATUS	current
	DESCRIPTION ""
			::= { mbusCA 20 }

mbusCAValue07		OBJECT-TYPE
			SYNTAX	INTEGER
			ACCESS	read-only
			STATUS	current
	DESCRIPTION ""
			::= { mbusCA 21 }

mbusCAVIF08		OBJECT-TYPE
			SYNTAX	INTEGER
			ACCESS	read-only
			STATUS	current
	DESCRIPTION ""
			::= { mbusCA 22 }

mbusCAValue08		OBJECT-TYPE
			SYNTAX	INTEGER
			ACCESS	read-only
			STATUS	current
	DESCRIPTION ""
			::= { mbusCA 23 }

mbusCAVIF09		OBJECT-TYPE
			SYNTAX	INTEGER
			ACCESS	read-only
			STATUS	current
	DESCRIPTION ""
			::= { mbusCA 24 }

mbusCAValue09		OBJECT-TYPE
			SYNTAX	INTEGER
			ACCESS	read-only
			STATUS	current
	DESCRIPTION ""
			::= { mbusCA 25 }

mbusCAVIF0A		OBJECT-TYPE
			SYNTAX	INTEGER
			ACCESS	read-only
			STATUS	current
	DESCRIPTION ""
			::= { mbusCA 26 }

mbusCAValue0A		OBJECT-TYPE
			SYNTAX	INTEGER
			ACCESS	read-only
			STATUS	current
	DESCRIPTION ""
			::= { mbusCA 27 }

mbusCAVIF0B		OBJECT-TYPE
			SYNTAX	INTEGER
			ACCESS	read-only
			STATUS	current
	DESCRIPTION ""
			::= { mbusCA 28 }

mbusCAValue0B		OBJECT-TYPE
			SYNTAX	INTEGER
			ACCESS	read-only
			STATUS	current
	DESCRIPTION ""
			::= { mbusCA 29 }

mbusCAVIF0C		OBJECT-TYPE
			SYNTAX	INTEGER
			ACCESS	read-only
			STATUS	current
	DESCRIPTION ""
			::= { mbusCA 30 }

mbusCAValue0C		OBJECT-TYPE
			SYNTAX	INTEGER
			ACCESS	read-only
			STATUS	current
	DESCRIPTION ""
			::= { mbusCA 31 }

mbusCAVIF0D		OBJECT-TYPE
			SYNTAX	INTEGER
			ACCESS	read-only
			STATUS	current
	DESCRIPTION ""
			::= { mbusCA 32 }

mbusCAValue0D		OBJECT-TYPE
			SYNTAX	INTEGER
			ACCESS	read-only
			STATUS	current
	DESCRIPTION ""
			::= { mbusCA 33 }

mbusCAVIF0E		OBJECT-TYPE
			SYNTAX	INTEGER
			ACCESS	read-only
			STATUS	current
	DESCRIPTION ""
			::= { mbusCA 34 }

mbusCAValue0E		OBJECT-TYPE
			SYNTAX	INTEGER
			ACCESS	read-only
			STATUS	current
	DESCRIPTION ""
			::= { mbusCA 35 }

mbusCAVIF0F		OBJECT-TYPE
			SYNTAX	INTEGER
			ACCESS	read-only
			STATUS	current
	DESCRIPTION ""
			::= { mbusCA 36 }

mbusCAValue0F		OBJECT-TYPE
			SYNTAX	INTEGER
			ACCESS	read-only
			STATUS	current
	DESCRIPTION ""
			::= { mbusCA 37 }

mbusCAVIF10		OBJECT-TYPE
			SYNTAX	INTEGER
			ACCESS	read-only
			STATUS	current
	DESCRIPTION ""
			::= { mbusCA 38 }

mbusCAValue10		OBJECT-TYPE
			SYNTAX	INTEGER
			ACCESS	read-only
			STATUS	current
	DESCRIPTION ""
			::= { mbusCA 39 }

mbusCAVIF11		OBJECT-TYPE
			SYNTAX	INTEGER
			ACCESS	read-only
			STATUS	current
	DESCRIPTION ""
			::= { mbusCA 40 }

mbusCAValue11		OBJECT-TYPE
			SYNTAX	INTEGER
			ACCESS	read-only
			STATUS	current
	DESCRIPTION ""
			::= { mbusCA 41 }

mbusCAVIF12		OBJECT-TYPE
			SYNTAX	INTEGER
			ACCESS	read-only
			STATUS	current
	DESCRIPTION ""
			::= { mbusCA 42 }

mbusCAValue12		OBJECT-TYPE
			SYNTAX	INTEGER
			ACCESS	read-only
			STATUS	current
	DESCRIPTION ""
			::= { mbusCA 43 }

mbusCAVIF13		OBJECT-TYPE
			SYNTAX	INTEGER
			ACCESS	read-only
			STATUS	current
	DESCRIPTION ""
			::= { mbusCA 44 }

mbusCAValue13		OBJECT-TYPE
			SYNTAX	INTEGER
			ACCESS	read-only
			STATUS	current
	DESCRIPTION ""
			::= { mbusCA 45 }

mbusCAVIF14		OBJECT-TYPE
			SYNTAX	INTEGER
			ACCESS	read-only
			STATUS	current
	DESCRIPTION ""
			::= { mbusCA 46 }

mbusCAValue14		OBJECT-TYPE
			SYNTAX	INTEGER
			ACCESS	read-only
			STATUS	current
	DESCRIPTION ""
			::= { mbusCA 47 }

mbusCAVIF15		OBJECT-TYPE
			SYNTAX	INTEGER
			ACCESS	read-only
			STATUS	current
	DESCRIPTION ""
			::= { mbusCA 48 }

mbusCAValue15		OBJECT-TYPE
			SYNTAX	INTEGER
			ACCESS	read-only
			STATUS	current
	DESCRIPTION ""
			::= { mbusCA 49 }

mbusCAVIF16		OBJECT-TYPE
			SYNTAX	INTEGER
			ACCESS	read-only
			STATUS	current
	DESCRIPTION ""
			::= { mbusCA 50 }

mbusCAValue16		OBJECT-TYPE
			SYNTAX	INTEGER
			ACCESS	read-only
			STATUS	current
	DESCRIPTION ""
			::= { mbusCA 51 }

mbusCAVIF17		OBJECT-TYPE
			SYNTAX	INTEGER
			ACCESS	read-only
			STATUS	current
	DESCRIPTION ""
			::= { mbusCA 52 }

mbusCAValue17		OBJECT-TYPE
			SYNTAX	INTEGER
			ACCESS	read-only
			STATUS	current
	DESCRIPTION ""
			::= { mbusCA 53 }

mbusCAVIF18		OBJECT-TYPE
			SYNTAX	INTEGER
			ACCESS	read-only
			STATUS	current
	DESCRIPTION ""
			::= { mbusCA 54 }

mbusCAValue18		OBJECT-TYPE
			SYNTAX	INTEGER
			ACCESS	read-only
			STATUS	current
	DESCRIPTION ""
			::= { mbusCA 55 }

mbusCAVIF19		OBJECT-TYPE
			SYNTAX	INTEGER
			ACCESS	read-only
			STATUS	current
	DESCRIPTION ""
			::= { mbusCA 56 }

mbusCAValue19		OBJECT-TYPE
			SYNTAX	INTEGER
			ACCESS	read-only
			STATUS	current
	DESCRIPTION ""
			::= { mbusCA 57 }

mbusCAVIF1A		OBJECT-TYPE
			SYNTAX	INTEGER
			ACCESS	read-only
			STATUS	current
	DESCRIPTION ""
			::= { mbusCA 58 }

mbusCAValue1A		OBJECT-TYPE
			SYNTAX	INTEGER
			ACCESS	read-only
			STATUS	current
	DESCRIPTION ""
			::= { mbusCA 59 }

mbusCAVIF1B		OBJECT-TYPE
			SYNTAX	INTEGER
			ACCESS	read-only
			STATUS	current
	DESCRIPTION ""
			::= { mbusCA 60 }

mbusCAValue1B		OBJECT-TYPE
			SYNTAX	INTEGER
			ACCESS	read-only
			STATUS	current
	DESCRIPTION ""
			::= { mbusCA 61 }

mbusCAVIF1C		OBJECT-TYPE
			SYNTAX	INTEGER
			ACCESS	read-only
			STATUS	current
	DESCRIPTION ""
			::= { mbusCA 62 }

mbusCAValue1C		OBJECT-TYPE
			SYNTAX	INTEGER
			ACCESS	read-only
			STATUS	current
	DESCRIPTION ""
			::= { mbusCA 63 }

mbusCAVIF1D		OBJECT-TYPE
			SYNTAX	INTEGER
			ACCESS	read-only
			STATUS	current
	DESCRIPTION ""
			::= { mbusCA 64 }

mbusCAValue1D		OBJECT-TYPE
			SYNTAX	INTEGER
			ACCESS	read-only
			STATUS	current
	DESCRIPTION ""
			::= { mbusCA 65 }

mbusCAVIF1E		OBJECT-TYPE
			SYNTAX	INTEGER
			ACCESS	read-only
			STATUS	current
	DESCRIPTION ""
			::= { mbusCA 66 }

mbusCAValue1E		OBJECT-TYPE
			SYNTAX	INTEGER
			ACCESS	read-only
			STATUS	current
	DESCRIPTION ""
			::= { mbusCA 67 }

mbusCAVIF1F		OBJECT-TYPE
			SYNTAX	INTEGER
			ACCESS	read-only
			STATUS	current
	DESCRIPTION ""
			::= { mbusCA 68 }

mbusCAValue1F		OBJECT-TYPE
			SYNTAX	INTEGER
			ACCESS	read-only
			STATUS	current
	DESCRIPTION ""
			::= { mbusCA 69 }

mbusCAVIF20		OBJECT-TYPE
			SYNTAX	INTEGER
			ACCESS	read-only
			STATUS	current
	DESCRIPTION ""
			::= { mbusCA 70 }

mbusCAValue20		OBJECT-TYPE
			SYNTAX	INTEGER
			ACCESS	read-only
			STATUS	current
	DESCRIPTION ""
			::= { mbusCA 71 }

mbusCAVIF21		OBJECT-TYPE
			SYNTAX	INTEGER
			ACCESS	read-only
			STATUS	current
	DESCRIPTION ""
			::= { mbusCA 72 }

mbusCAValue21		OBJECT-TYPE
			SYNTAX	INTEGER
			ACCESS	read-only
			STATUS	current
	DESCRIPTION ""
			::= { mbusCA 73 }

mbusCAVIF22		OBJECT-TYPE
			SYNTAX	INTEGER
			ACCESS	read-only
			STATUS	current
	DESCRIPTION ""
			::= { mbusCA 74 }

mbusCAValue22		OBJECT-TYPE
			SYNTAX	INTEGER
			ACCESS	read-only
			STATUS	current
	DESCRIPTION ""
			::= { mbusCA 75 }

mbusCAVIF23		OBJECT-TYPE
			SYNTAX	INTEGER
			ACCESS	read-only
			STATUS	current
	DESCRIPTION ""
			::= { mbusCA 76 }

mbusCAValue23		OBJECT-TYPE
			SYNTAX	INTEGER
			ACCESS	read-only
			STATUS	current
	DESCRIPTION ""
			::= { mbusCA 77 }

mbusCAVIF24		OBJECT-TYPE
			SYNTAX	INTEGER
			ACCESS	read-only
			STATUS	current
	DESCRIPTION ""
			::= { mbusCA 78 }

mbusCAValue24		OBJECT-TYPE
			SYNTAX	INTEGER
			ACCESS	read-only
			STATUS	current
	DESCRIPTION ""
			::= { mbusCA 79 }

mbusCAVIF25		OBJECT-TYPE
			SYNTAX	INTEGER
			ACCESS	read-only
			STATUS	current
	DESCRIPTION ""
			::= { mbusCA 80 }

mbusCAValue25		OBJECT-TYPE
			SYNTAX	INTEGER
			ACCESS	read-only
			STATUS	current
	DESCRIPTION ""
			::= { mbusCA 81 }

mbusCAVIF26		OBJECT-TYPE
			SYNTAX	INTEGER
			ACCESS	read-only
			STATUS	current
	DESCRIPTION ""
			::= { mbusCA 82 }

mbusCAValue26		OBJECT-TYPE
			SYNTAX	INTEGER
			ACCESS	read-only
			STATUS	current
	DESCRIPTION ""
			::= { mbusCA 83 }

mbusCAVIF27		OBJECT-TYPE
			SYNTAX	INTEGER
			ACCESS	read-only
			STATUS	current
	DESCRIPTION ""
			::= { mbusCA 84 }

mbusCAValue27		OBJECT-TYPE
			SYNTAX	INTEGER
			ACCESS	read-only
			STATUS	current
	DESCRIPTION ""
			::= { mbusCA 85 }

mbusCAVIF28		OBJECT-TYPE
			SYNTAX	INTEGER
			ACCESS	read-only
			STATUS	current
	DESCRIPTION ""
			::= { mbusCA 86 }

mbusCAValue28		OBJECT-TYPE
			SYNTAX	INTEGER
			ACCESS	read-only
			STATUS	current
	DESCRIPTION ""
			::= { mbusCA 87 }

mbusCAVIF29		OBJECT-TYPE
			SYNTAX	INTEGER
			ACCESS	read-only
			STATUS	current
	DESCRIPTION ""
			::= { mbusCA 88 }

mbusCAValue29		OBJECT-TYPE
			SYNTAX	INTEGER
			ACCESS	read-only
			STATUS	current
	DESCRIPTION ""
			::= { mbusCA 89 }

mbusCAVIF2A		OBJECT-TYPE
			SYNTAX	INTEGER
			ACCESS	read-only
			STATUS	current
	DESCRIPTION ""
			::= { mbusCA 90 }

mbusCAValue2A		OBJECT-TYPE
			SYNTAX	INTEGER
			ACCESS	read-only
			STATUS	current
	DESCRIPTION ""
			::= { mbusCA 91 }

mbusCAVIF2B		OBJECT-TYPE
			SYNTAX	INTEGER
			ACCESS	read-only
			STATUS	current
	DESCRIPTION ""
			::= { mbusCA 92 }

mbusCAValue2B		OBJECT-TYPE
			SYNTAX	INTEGER
			ACCESS	read-only
			STATUS	current
	DESCRIPTION ""
			::= { mbusCA 93 }

mbusCAVIF2C		OBJECT-TYPE
			SYNTAX	INTEGER
			ACCESS	read-only
			STATUS	current
	DESCRIPTION ""
			::= { mbusCA 94 }

mbusCAValue2C		OBJECT-TYPE
			SYNTAX	INTEGER
			ACCESS	read-only
			STATUS	current
	DESCRIPTION ""
			::= { mbusCA 95 }

mbusCAVIF2D		OBJECT-TYPE
			SYNTAX	INTEGER
			ACCESS	read-only
			STATUS	current
	DESCRIPTION ""
			::= { mbusCA 96 }

mbusCAValue2D		OBJECT-TYPE
			SYNTAX	INTEGER
			ACCESS	read-only
			STATUS	current
	DESCRIPTION ""
			::= { mbusCA 97 }

mbusCAVIF2E		OBJECT-TYPE
			SYNTAX	INTEGER
			ACCESS	read-only
			STATUS	current
	DESCRIPTION ""
			::= { mbusCA 98 }

mbusCAValue2E		OBJECT-TYPE
			SYNTAX	INTEGER
			ACCESS	read-only
			STATUS	current
	DESCRIPTION ""
			::= { mbusCA 99 }

mbusCAVIF2F		OBJECT-TYPE
			SYNTAX	INTEGER
			ACCESS	read-only
			STATUS	current
	DESCRIPTION ""
			::= { mbusCA 100 }

mbusCAValue2F		OBJECT-TYPE
			SYNTAX	INTEGER
			ACCESS	read-only
			STATUS	current
	DESCRIPTION ""
			::= { mbusCA 101 }

mbusCB			OBJECT IDENTIFIER ::= { mbus 203 }

mbusCBIdNumber		OBJECT-TYPE
			SYNTAX	Gauge
			ACCESS	read-only
			STATUS	current
	DESCRIPTION ""
			::= { mbusCB 1 }

mbusCBManufacturer	OBJECT-TYPE
			SYNTAX	Gauge
			ACCESS	read-only
			STATUS	current
	DESCRIPTION ""
			::= { mbusCB 2 }

mbusCBVersion		OBJECT-TYPE
			SYNTAX	Gauge
			ACCESS	read-only
			STATUS	current
	DESCRIPTION ""
			::= { mbusCB 3 }

mbusCBMedium		OBJECT-TYPE
			SYNTAX	Gauge
			ACCESS	read-only
			STATUS	current
	DESCRIPTION ""
			::= { mbusCB 4 }

mbusCBStatus		OBJECT-TYPE
			SYNTAX	Gauge
			ACCESS	read-only
			STATUS	current
	DESCRIPTION ""
			::= { mbusCB 5 }

mbusCBVIF00		OBJECT-TYPE
			SYNTAX	INTEGER
			ACCESS	read-only
			STATUS	current
	DESCRIPTION ""
			::= { mbusCB 6 }

mbusCBValue00		OBJECT-TYPE
			SYNTAX	INTEGER
			ACCESS	read-only
			STATUS	current
	DESCRIPTION ""
			::= { mbusCB 7 }

mbusCBVIF01		OBJECT-TYPE
			SYNTAX	INTEGER
			ACCESS	read-only
			STATUS	current
	DESCRIPTION ""
			::= { mbusCB 8 }

mbusCBValue01		OBJECT-TYPE
			SYNTAX	INTEGER
			ACCESS	read-only
			STATUS	current
	DESCRIPTION ""
			::= { mbusCB 9 }

mbusCBVIF02		OBJECT-TYPE
			SYNTAX	INTEGER
			ACCESS	read-only
			STATUS	current
	DESCRIPTION ""
			::= { mbusCB 10 }

mbusCBValue02		OBJECT-TYPE
			SYNTAX	INTEGER
			ACCESS	read-only
			STATUS	current
	DESCRIPTION ""
			::= { mbusCB 11 }

mbusCBVIF03		OBJECT-TYPE
			SYNTAX	INTEGER
			ACCESS	read-only
			STATUS	current
	DESCRIPTION ""
			::= { mbusCB 12 }

mbusCBValue03		OBJECT-TYPE
			SYNTAX	INTEGER
			ACCESS	read-only
			STATUS	current
	DESCRIPTION ""
			::= { mbusCB 13 }

mbusCBVIF04		OBJECT-TYPE
			SYNTAX	INTEGER
			ACCESS	read-only
			STATUS	current
	DESCRIPTION ""
			::= { mbusCB 14 }

mbusCBValue04		OBJECT-TYPE
			SYNTAX	INTEGER
			ACCESS	read-only
			STATUS	current
	DESCRIPTION ""
			::= { mbusCB 15 }

mbusCBVIF05		OBJECT-TYPE
			SYNTAX	INTEGER
			ACCESS	read-only
			STATUS	current
	DESCRIPTION ""
			::= { mbusCB 16 }

mbusCBValue05		OBJECT-TYPE
			SYNTAX	INTEGER
			ACCESS	read-only
			STATUS	current
	DESCRIPTION ""
			::= { mbusCB 17 }

mbusCBVIF06		OBJECT-TYPE
			SYNTAX	INTEGER
			ACCESS	read-only
			STATUS	current
	DESCRIPTION ""
			::= { mbusCB 18 }

mbusCBValue06		OBJECT-TYPE
			SYNTAX	INTEGER
			ACCESS	read-only
			STATUS	current
	DESCRIPTION ""
			::= { mbusCB 19 }

mbusCBVIF07		OBJECT-TYPE
			SYNTAX	INTEGER
			ACCESS	read-only
			STATUS	current
	DESCRIPTION ""
			::= { mbusCB 20 }

mbusCBValue07		OBJECT-TYPE
			SYNTAX	INTEGER
			ACCESS	read-only
			STATUS	current
	DESCRIPTION ""
			::= { mbusCB 21 }

mbusCBVIF08		OBJECT-TYPE
			SYNTAX	INTEGER
			ACCESS	read-only
			STATUS	current
	DESCRIPTION ""
			::= { mbusCB 22 }

mbusCBValue08		OBJECT-TYPE
			SYNTAX	INTEGER
			ACCESS	read-only
			STATUS	current
	DESCRIPTION ""
			::= { mbusCB 23 }

mbusCBVIF09		OBJECT-TYPE
			SYNTAX	INTEGER
			ACCESS	read-only
			STATUS	current
	DESCRIPTION ""
			::= { mbusCB 24 }

mbusCBValue09		OBJECT-TYPE
			SYNTAX	INTEGER
			ACCESS	read-only
			STATUS	current
	DESCRIPTION ""
			::= { mbusCB 25 }

mbusCBVIF0A		OBJECT-TYPE
			SYNTAX	INTEGER
			ACCESS	read-only
			STATUS	current
	DESCRIPTION ""
			::= { mbusCB 26 }

mbusCBValue0A		OBJECT-TYPE
			SYNTAX	INTEGER
			ACCESS	read-only
			STATUS	current
	DESCRIPTION ""
			::= { mbusCB 27 }

mbusCBVIF0B		OBJECT-TYPE
			SYNTAX	INTEGER
			ACCESS	read-only
			STATUS	current
	DESCRIPTION ""
			::= { mbusCB 28 }

mbusCBValue0B		OBJECT-TYPE
			SYNTAX	INTEGER
			ACCESS	read-only
			STATUS	current
	DESCRIPTION ""
			::= { mbusCB 29 }

mbusCBVIF0C		OBJECT-TYPE
			SYNTAX	INTEGER
			ACCESS	read-only
			STATUS	current
	DESCRIPTION ""
			::= { mbusCB 30 }

mbusCBValue0C		OBJECT-TYPE
			SYNTAX	INTEGER
			ACCESS	read-only
			STATUS	current
	DESCRIPTION ""
			::= { mbusCB 31 }

mbusCBVIF0D		OBJECT-TYPE
			SYNTAX	INTEGER
			ACCESS	read-only
			STATUS	current
	DESCRIPTION ""
			::= { mbusCB 32 }

mbusCBValue0D		OBJECT-TYPE
			SYNTAX	INTEGER
			ACCESS	read-only
			STATUS	current
	DESCRIPTION ""
			::= { mbusCB 33 }

mbusCBVIF0E		OBJECT-TYPE
			SYNTAX	INTEGER
			ACCESS	read-only
			STATUS	current
	DESCRIPTION ""
			::= { mbusCB 34 }

mbusCBValue0E		OBJECT-TYPE
			SYNTAX	INTEGER
			ACCESS	read-only
			STATUS	current
	DESCRIPTION ""
			::= { mbusCB 35 }

mbusCBVIF0F		OBJECT-TYPE
			SYNTAX	INTEGER
			ACCESS	read-only
			STATUS	current
	DESCRIPTION ""
			::= { mbusCB 36 }

mbusCBValue0F		OBJECT-TYPE
			SYNTAX	INTEGER
			ACCESS	read-only
			STATUS	current
	DESCRIPTION ""
			::= { mbusCB 37 }

mbusCBVIF10		OBJECT-TYPE
			SYNTAX	INTEGER
			ACCESS	read-only
			STATUS	current
	DESCRIPTION ""
			::= { mbusCB 38 }

mbusCBValue10		OBJECT-TYPE
			SYNTAX	INTEGER
			ACCESS	read-only
			STATUS	current
	DESCRIPTION ""
			::= { mbusCB 39 }

mbusCBVIF11		OBJECT-TYPE
			SYNTAX	INTEGER
			ACCESS	read-only
			STATUS	current
	DESCRIPTION ""
			::= { mbusCB 40 }

mbusCBValue11		OBJECT-TYPE
			SYNTAX	INTEGER
			ACCESS	read-only
			STATUS	current
	DESCRIPTION ""
			::= { mbusCB 41 }

mbusCBVIF12		OBJECT-TYPE
			SYNTAX	INTEGER
			ACCESS	read-only
			STATUS	current
	DESCRIPTION ""
			::= { mbusCB 42 }

mbusCBValue12		OBJECT-TYPE
			SYNTAX	INTEGER
			ACCESS	read-only
			STATUS	current
	DESCRIPTION ""
			::= { mbusCB 43 }

mbusCBVIF13		OBJECT-TYPE
			SYNTAX	INTEGER
			ACCESS	read-only
			STATUS	current
	DESCRIPTION ""
			::= { mbusCB 44 }

mbusCBValue13		OBJECT-TYPE
			SYNTAX	INTEGER
			ACCESS	read-only
			STATUS	current
	DESCRIPTION ""
			::= { mbusCB 45 }

mbusCBVIF14		OBJECT-TYPE
			SYNTAX	INTEGER
			ACCESS	read-only
			STATUS	current
	DESCRIPTION ""
			::= { mbusCB 46 }

mbusCBValue14		OBJECT-TYPE
			SYNTAX	INTEGER
			ACCESS	read-only
			STATUS	current
	DESCRIPTION ""
			::= { mbusCB 47 }

mbusCBVIF15		OBJECT-TYPE
			SYNTAX	INTEGER
			ACCESS	read-only
			STATUS	current
	DESCRIPTION ""
			::= { mbusCB 48 }

mbusCBValue15		OBJECT-TYPE
			SYNTAX	INTEGER
			ACCESS	read-only
			STATUS	current
	DESCRIPTION ""
			::= { mbusCB 49 }

mbusCBVIF16		OBJECT-TYPE
			SYNTAX	INTEGER
			ACCESS	read-only
			STATUS	current
	DESCRIPTION ""
			::= { mbusCB 50 }

mbusCBValue16		OBJECT-TYPE
			SYNTAX	INTEGER
			ACCESS	read-only
			STATUS	current
	DESCRIPTION ""
			::= { mbusCB 51 }

mbusCBVIF17		OBJECT-TYPE
			SYNTAX	INTEGER
			ACCESS	read-only
			STATUS	current
	DESCRIPTION ""
			::= { mbusCB 52 }

mbusCBValue17		OBJECT-TYPE
			SYNTAX	INTEGER
			ACCESS	read-only
			STATUS	current
	DESCRIPTION ""
			::= { mbusCB 53 }

mbusCBVIF18		OBJECT-TYPE
			SYNTAX	INTEGER
			ACCESS	read-only
			STATUS	current
	DESCRIPTION ""
			::= { mbusCB 54 }

mbusCBValue18		OBJECT-TYPE
			SYNTAX	INTEGER
			ACCESS	read-only
			STATUS	current
	DESCRIPTION ""
			::= { mbusCB 55 }

mbusCBVIF19		OBJECT-TYPE
			SYNTAX	INTEGER
			ACCESS	read-only
			STATUS	current
	DESCRIPTION ""
			::= { mbusCB 56 }

mbusCBValue19		OBJECT-TYPE
			SYNTAX	INTEGER
			ACCESS	read-only
			STATUS	current
	DESCRIPTION ""
			::= { mbusCB 57 }

mbusCBVIF1A		OBJECT-TYPE
			SYNTAX	INTEGER
			ACCESS	read-only
			STATUS	current
	DESCRIPTION ""
			::= { mbusCB 58 }

mbusCBValue1A		OBJECT-TYPE
			SYNTAX	INTEGER
			ACCESS	read-only
			STATUS	current
	DESCRIPTION ""
			::= { mbusCB 59 }

mbusCBVIF1B		OBJECT-TYPE
			SYNTAX	INTEGER
			ACCESS	read-only
			STATUS	current
	DESCRIPTION ""
			::= { mbusCB 60 }

mbusCBValue1B		OBJECT-TYPE
			SYNTAX	INTEGER
			ACCESS	read-only
			STATUS	current
	DESCRIPTION ""
			::= { mbusCB 61 }

mbusCBVIF1C		OBJECT-TYPE
			SYNTAX	INTEGER
			ACCESS	read-only
			STATUS	current
	DESCRIPTION ""
			::= { mbusCB 62 }

mbusCBValue1C		OBJECT-TYPE
			SYNTAX	INTEGER
			ACCESS	read-only
			STATUS	current
	DESCRIPTION ""
			::= { mbusCB 63 }

mbusCBVIF1D		OBJECT-TYPE
			SYNTAX	INTEGER
			ACCESS	read-only
			STATUS	current
	DESCRIPTION ""
			::= { mbusCB 64 }

mbusCBValue1D		OBJECT-TYPE
			SYNTAX	INTEGER
			ACCESS	read-only
			STATUS	current
	DESCRIPTION ""
			::= { mbusCB 65 }

mbusCBVIF1E		OBJECT-TYPE
			SYNTAX	INTEGER
			ACCESS	read-only
			STATUS	current
	DESCRIPTION ""
			::= { mbusCB 66 }

mbusCBValue1E		OBJECT-TYPE
			SYNTAX	INTEGER
			ACCESS	read-only
			STATUS	current
	DESCRIPTION ""
			::= { mbusCB 67 }

mbusCBVIF1F		OBJECT-TYPE
			SYNTAX	INTEGER
			ACCESS	read-only
			STATUS	current
	DESCRIPTION ""
			::= { mbusCB 68 }

mbusCBValue1F		OBJECT-TYPE
			SYNTAX	INTEGER
			ACCESS	read-only
			STATUS	current
	DESCRIPTION ""
			::= { mbusCB 69 }

mbusCBVIF20		OBJECT-TYPE
			SYNTAX	INTEGER
			ACCESS	read-only
			STATUS	current
	DESCRIPTION ""
			::= { mbusCB 70 }

mbusCBValue20		OBJECT-TYPE
			SYNTAX	INTEGER
			ACCESS	read-only
			STATUS	current
	DESCRIPTION ""
			::= { mbusCB 71 }

mbusCBVIF21		OBJECT-TYPE
			SYNTAX	INTEGER
			ACCESS	read-only
			STATUS	current
	DESCRIPTION ""
			::= { mbusCB 72 }

mbusCBValue21		OBJECT-TYPE
			SYNTAX	INTEGER
			ACCESS	read-only
			STATUS	current
	DESCRIPTION ""
			::= { mbusCB 73 }

mbusCBVIF22		OBJECT-TYPE
			SYNTAX	INTEGER
			ACCESS	read-only
			STATUS	current
	DESCRIPTION ""
			::= { mbusCB 74 }

mbusCBValue22		OBJECT-TYPE
			SYNTAX	INTEGER
			ACCESS	read-only
			STATUS	current
	DESCRIPTION ""
			::= { mbusCB 75 }

mbusCBVIF23		OBJECT-TYPE
			SYNTAX	INTEGER
			ACCESS	read-only
			STATUS	current
	DESCRIPTION ""
			::= { mbusCB 76 }

mbusCBValue23		OBJECT-TYPE
			SYNTAX	INTEGER
			ACCESS	read-only
			STATUS	current
	DESCRIPTION ""
			::= { mbusCB 77 }

mbusCBVIF24		OBJECT-TYPE
			SYNTAX	INTEGER
			ACCESS	read-only
			STATUS	current
	DESCRIPTION ""
			::= { mbusCB 78 }

mbusCBValue24		OBJECT-TYPE
			SYNTAX	INTEGER
			ACCESS	read-only
			STATUS	current
	DESCRIPTION ""
			::= { mbusCB 79 }

mbusCBVIF25		OBJECT-TYPE
			SYNTAX	INTEGER
			ACCESS	read-only
			STATUS	current
	DESCRIPTION ""
			::= { mbusCB 80 }

mbusCBValue25		OBJECT-TYPE
			SYNTAX	INTEGER
			ACCESS	read-only
			STATUS	current
	DESCRIPTION ""
			::= { mbusCB 81 }

mbusCBVIF26		OBJECT-TYPE
			SYNTAX	INTEGER
			ACCESS	read-only
			STATUS	current
	DESCRIPTION ""
			::= { mbusCB 82 }

mbusCBValue26		OBJECT-TYPE
			SYNTAX	INTEGER
			ACCESS	read-only
			STATUS	current
	DESCRIPTION ""
			::= { mbusCB 83 }

mbusCBVIF27		OBJECT-TYPE
			SYNTAX	INTEGER
			ACCESS	read-only
			STATUS	current
	DESCRIPTION ""
			::= { mbusCB 84 }

mbusCBValue27		OBJECT-TYPE
			SYNTAX	INTEGER
			ACCESS	read-only
			STATUS	current
	DESCRIPTION ""
			::= { mbusCB 85 }

mbusCBVIF28		OBJECT-TYPE
			SYNTAX	INTEGER
			ACCESS	read-only
			STATUS	current
	DESCRIPTION ""
			::= { mbusCB 86 }

mbusCBValue28		OBJECT-TYPE
			SYNTAX	INTEGER
			ACCESS	read-only
			STATUS	current
	DESCRIPTION ""
			::= { mbusCB 87 }

mbusCBVIF29		OBJECT-TYPE
			SYNTAX	INTEGER
			ACCESS	read-only
			STATUS	current
	DESCRIPTION ""
			::= { mbusCB 88 }

mbusCBValue29		OBJECT-TYPE
			SYNTAX	INTEGER
			ACCESS	read-only
			STATUS	current
	DESCRIPTION ""
			::= { mbusCB 89 }

mbusCBVIF2A		OBJECT-TYPE
			SYNTAX	INTEGER
			ACCESS	read-only
			STATUS	current
	DESCRIPTION ""
			::= { mbusCB 90 }

mbusCBValue2A		OBJECT-TYPE
			SYNTAX	INTEGER
			ACCESS	read-only
			STATUS	current
	DESCRIPTION ""
			::= { mbusCB 91 }

mbusCBVIF2B		OBJECT-TYPE
			SYNTAX	INTEGER
			ACCESS	read-only
			STATUS	current
	DESCRIPTION ""
			::= { mbusCB 92 }

mbusCBValue2B		OBJECT-TYPE
			SYNTAX	INTEGER
			ACCESS	read-only
			STATUS	current
	DESCRIPTION ""
			::= { mbusCB 93 }

mbusCBVIF2C		OBJECT-TYPE
			SYNTAX	INTEGER
			ACCESS	read-only
			STATUS	current
	DESCRIPTION ""
			::= { mbusCB 94 }

mbusCBValue2C		OBJECT-TYPE
			SYNTAX	INTEGER
			ACCESS	read-only
			STATUS	current
	DESCRIPTION ""
			::= { mbusCB 95 }

mbusCBVIF2D		OBJECT-TYPE
			SYNTAX	INTEGER
			ACCESS	read-only
			STATUS	current
	DESCRIPTION ""
			::= { mbusCB 96 }

mbusCBValue2D		OBJECT-TYPE
			SYNTAX	INTEGER
			ACCESS	read-only
			STATUS	current
	DESCRIPTION ""
			::= { mbusCB 97 }

mbusCBVIF2E		OBJECT-TYPE
			SYNTAX	INTEGER
			ACCESS	read-only
			STATUS	current
	DESCRIPTION ""
			::= { mbusCB 98 }

mbusCBValue2E		OBJECT-TYPE
			SYNTAX	INTEGER
			ACCESS	read-only
			STATUS	current
	DESCRIPTION ""
			::= { mbusCB 99 }

mbusCBVIF2F		OBJECT-TYPE
			SYNTAX	INTEGER
			ACCESS	read-only
			STATUS	current
	DESCRIPTION ""
			::= { mbusCB 100 }

mbusCBValue2F		OBJECT-TYPE
			SYNTAX	INTEGER
			ACCESS	read-only
			STATUS	current
	DESCRIPTION ""
			::= { mbusCB 101 }

mbusCC			OBJECT IDENTIFIER ::= { mbus 204 }

mbusCCIdNumber		OBJECT-TYPE
			SYNTAX	Gauge
			ACCESS	read-only
			STATUS	current
	DESCRIPTION ""
			::= { mbusCC 1 }

mbusCCManufacturer	OBJECT-TYPE
			SYNTAX	Gauge
			ACCESS	read-only
			STATUS	current
	DESCRIPTION ""
			::= { mbusCC 2 }

mbusCCVersion		OBJECT-TYPE
			SYNTAX	Gauge
			ACCESS	read-only
			STATUS	current
	DESCRIPTION ""
			::= { mbusCC 3 }

mbusCCMedium		OBJECT-TYPE
			SYNTAX	Gauge
			ACCESS	read-only
			STATUS	current
	DESCRIPTION ""
			::= { mbusCC 4 }

mbusCCStatus		OBJECT-TYPE
			SYNTAX	Gauge
			ACCESS	read-only
			STATUS	current
	DESCRIPTION ""
			::= { mbusCC 5 }

mbusCCVIF00		OBJECT-TYPE
			SYNTAX	INTEGER
			ACCESS	read-only
			STATUS	current
	DESCRIPTION ""
			::= { mbusCC 6 }

mbusCCValue00		OBJECT-TYPE
			SYNTAX	INTEGER
			ACCESS	read-only
			STATUS	current
	DESCRIPTION ""
			::= { mbusCC 7 }

mbusCCVIF01		OBJECT-TYPE
			SYNTAX	INTEGER
			ACCESS	read-only
			STATUS	current
	DESCRIPTION ""
			::= { mbusCC 8 }

mbusCCValue01		OBJECT-TYPE
			SYNTAX	INTEGER
			ACCESS	read-only
			STATUS	current
	DESCRIPTION ""
			::= { mbusCC 9 }

mbusCCVIF02		OBJECT-TYPE
			SYNTAX	INTEGER
			ACCESS	read-only
			STATUS	current
	DESCRIPTION ""
			::= { mbusCC 10 }

mbusCCValue02		OBJECT-TYPE
			SYNTAX	INTEGER
			ACCESS	read-only
			STATUS	current
	DESCRIPTION ""
			::= { mbusCC 11 }

mbusCCVIF03		OBJECT-TYPE
			SYNTAX	INTEGER
			ACCESS	read-only
			STATUS	current
	DESCRIPTION ""
			::= { mbusCC 12 }

mbusCCValue03		OBJECT-TYPE
			SYNTAX	INTEGER
			ACCESS	read-only
			STATUS	current
	DESCRIPTION ""
			::= { mbusCC 13 }

mbusCCVIF04		OBJECT-TYPE
			SYNTAX	INTEGER
			ACCESS	read-only
			STATUS	current
	DESCRIPTION ""
			::= { mbusCC 14 }

mbusCCValue04		OBJECT-TYPE
			SYNTAX	INTEGER
			ACCESS	read-only
			STATUS	current
	DESCRIPTION ""
			::= { mbusCC 15 }

mbusCCVIF05		OBJECT-TYPE
			SYNTAX	INTEGER
			ACCESS	read-only
			STATUS	current
	DESCRIPTION ""
			::= { mbusCC 16 }

mbusCCValue05		OBJECT-TYPE
			SYNTAX	INTEGER
			ACCESS	read-only
			STATUS	current
	DESCRIPTION ""
			::= { mbusCC 17 }

mbusCCVIF06		OBJECT-TYPE
			SYNTAX	INTEGER
			ACCESS	read-only
			STATUS	current
	DESCRIPTION ""
			::= { mbusCC 18 }

mbusCCValue06		OBJECT-TYPE
			SYNTAX	INTEGER
			ACCESS	read-only
			STATUS	current
	DESCRIPTION ""
			::= { mbusCC 19 }

mbusCCVIF07		OBJECT-TYPE
			SYNTAX	INTEGER
			ACCESS	read-only
			STATUS	current
	DESCRIPTION ""
			::= { mbusCC 20 }

mbusCCValue07		OBJECT-TYPE
			SYNTAX	INTEGER
			ACCESS	read-only
			STATUS	current
	DESCRIPTION ""
			::= { mbusCC 21 }

mbusCCVIF08		OBJECT-TYPE
			SYNTAX	INTEGER
			ACCESS	read-only
			STATUS	current
	DESCRIPTION ""
			::= { mbusCC 22 }

mbusCCValue08		OBJECT-TYPE
			SYNTAX	INTEGER
			ACCESS	read-only
			STATUS	current
	DESCRIPTION ""
			::= { mbusCC 23 }

mbusCCVIF09		OBJECT-TYPE
			SYNTAX	INTEGER
			ACCESS	read-only
			STATUS	current
	DESCRIPTION ""
			::= { mbusCC 24 }

mbusCCValue09		OBJECT-TYPE
			SYNTAX	INTEGER
			ACCESS	read-only
			STATUS	current
	DESCRIPTION ""
			::= { mbusCC 25 }

mbusCCVIF0A		OBJECT-TYPE
			SYNTAX	INTEGER
			ACCESS	read-only
			STATUS	current
	DESCRIPTION ""
			::= { mbusCC 26 }

mbusCCValue0A		OBJECT-TYPE
			SYNTAX	INTEGER
			ACCESS	read-only
			STATUS	current
	DESCRIPTION ""
			::= { mbusCC 27 }

mbusCCVIF0B		OBJECT-TYPE
			SYNTAX	INTEGER
			ACCESS	read-only
			STATUS	current
	DESCRIPTION ""
			::= { mbusCC 28 }

mbusCCValue0B		OBJECT-TYPE
			SYNTAX	INTEGER
			ACCESS	read-only
			STATUS	current
	DESCRIPTION ""
			::= { mbusCC 29 }

mbusCCVIF0C		OBJECT-TYPE
			SYNTAX	INTEGER
			ACCESS	read-only
			STATUS	current
	DESCRIPTION ""
			::= { mbusCC 30 }

mbusCCValue0C		OBJECT-TYPE
			SYNTAX	INTEGER
			ACCESS	read-only
			STATUS	current
	DESCRIPTION ""
			::= { mbusCC 31 }

mbusCCVIF0D		OBJECT-TYPE
			SYNTAX	INTEGER
			ACCESS	read-only
			STATUS	current
	DESCRIPTION ""
			::= { mbusCC 32 }

mbusCCValue0D		OBJECT-TYPE
			SYNTAX	INTEGER
			ACCESS	read-only
			STATUS	current
	DESCRIPTION ""
			::= { mbusCC 33 }

mbusCCVIF0E		OBJECT-TYPE
			SYNTAX	INTEGER
			ACCESS	read-only
			STATUS	current
	DESCRIPTION ""
			::= { mbusCC 34 }

mbusCCValue0E		OBJECT-TYPE
			SYNTAX	INTEGER
			ACCESS	read-only
			STATUS	current
	DESCRIPTION ""
			::= { mbusCC 35 }

mbusCCVIF0F		OBJECT-TYPE
			SYNTAX	INTEGER
			ACCESS	read-only
			STATUS	current
	DESCRIPTION ""
			::= { mbusCC 36 }

mbusCCValue0F		OBJECT-TYPE
			SYNTAX	INTEGER
			ACCESS	read-only
			STATUS	current
	DESCRIPTION ""
			::= { mbusCC 37 }

mbusCCVIF10		OBJECT-TYPE
			SYNTAX	INTEGER
			ACCESS	read-only
			STATUS	current
	DESCRIPTION ""
			::= { mbusCC 38 }

mbusCCValue10		OBJECT-TYPE
			SYNTAX	INTEGER
			ACCESS	read-only
			STATUS	current
	DESCRIPTION ""
			::= { mbusCC 39 }

mbusCCVIF11		OBJECT-TYPE
			SYNTAX	INTEGER
			ACCESS	read-only
			STATUS	current
	DESCRIPTION ""
			::= { mbusCC 40 }

mbusCCValue11		OBJECT-TYPE
			SYNTAX	INTEGER
			ACCESS	read-only
			STATUS	current
	DESCRIPTION ""
			::= { mbusCC 41 }

mbusCCVIF12		OBJECT-TYPE
			SYNTAX	INTEGER
			ACCESS	read-only
			STATUS	current
	DESCRIPTION ""
			::= { mbusCC 42 }

mbusCCValue12		OBJECT-TYPE
			SYNTAX	INTEGER
			ACCESS	read-only
			STATUS	current
	DESCRIPTION ""
			::= { mbusCC 43 }

mbusCCVIF13		OBJECT-TYPE
			SYNTAX	INTEGER
			ACCESS	read-only
			STATUS	current
	DESCRIPTION ""
			::= { mbusCC 44 }

mbusCCValue13		OBJECT-TYPE
			SYNTAX	INTEGER
			ACCESS	read-only
			STATUS	current
	DESCRIPTION ""
			::= { mbusCC 45 }

mbusCCVIF14		OBJECT-TYPE
			SYNTAX	INTEGER
			ACCESS	read-only
			STATUS	current
	DESCRIPTION ""
			::= { mbusCC 46 }

mbusCCValue14		OBJECT-TYPE
			SYNTAX	INTEGER
			ACCESS	read-only
			STATUS	current
	DESCRIPTION ""
			::= { mbusCC 47 }

mbusCCVIF15		OBJECT-TYPE
			SYNTAX	INTEGER
			ACCESS	read-only
			STATUS	current
	DESCRIPTION ""
			::= { mbusCC 48 }

mbusCCValue15		OBJECT-TYPE
			SYNTAX	INTEGER
			ACCESS	read-only
			STATUS	current
	DESCRIPTION ""
			::= { mbusCC 49 }

mbusCCVIF16		OBJECT-TYPE
			SYNTAX	INTEGER
			ACCESS	read-only
			STATUS	current
	DESCRIPTION ""
			::= { mbusCC 50 }

mbusCCValue16		OBJECT-TYPE
			SYNTAX	INTEGER
			ACCESS	read-only
			STATUS	current
	DESCRIPTION ""
			::= { mbusCC 51 }

mbusCCVIF17		OBJECT-TYPE
			SYNTAX	INTEGER
			ACCESS	read-only
			STATUS	current
	DESCRIPTION ""
			::= { mbusCC 52 }

mbusCCValue17		OBJECT-TYPE
			SYNTAX	INTEGER
			ACCESS	read-only
			STATUS	current
	DESCRIPTION ""
			::= { mbusCC 53 }

mbusCCVIF18		OBJECT-TYPE
			SYNTAX	INTEGER
			ACCESS	read-only
			STATUS	current
	DESCRIPTION ""
			::= { mbusCC 54 }

mbusCCValue18		OBJECT-TYPE
			SYNTAX	INTEGER
			ACCESS	read-only
			STATUS	current
	DESCRIPTION ""
			::= { mbusCC 55 }

mbusCCVIF19		OBJECT-TYPE
			SYNTAX	INTEGER
			ACCESS	read-only
			STATUS	current
	DESCRIPTION ""
			::= { mbusCC 56 }

mbusCCValue19		OBJECT-TYPE
			SYNTAX	INTEGER
			ACCESS	read-only
			STATUS	current
	DESCRIPTION ""
			::= { mbusCC 57 }

mbusCCVIF1A		OBJECT-TYPE
			SYNTAX	INTEGER
			ACCESS	read-only
			STATUS	current
	DESCRIPTION ""
			::= { mbusCC 58 }

mbusCCValue1A		OBJECT-TYPE
			SYNTAX	INTEGER
			ACCESS	read-only
			STATUS	current
	DESCRIPTION ""
			::= { mbusCC 59 }

mbusCCVIF1B		OBJECT-TYPE
			SYNTAX	INTEGER
			ACCESS	read-only
			STATUS	current
	DESCRIPTION ""
			::= { mbusCC 60 }

mbusCCValue1B		OBJECT-TYPE
			SYNTAX	INTEGER
			ACCESS	read-only
			STATUS	current
	DESCRIPTION ""
			::= { mbusCC 61 }

mbusCCVIF1C		OBJECT-TYPE
			SYNTAX	INTEGER
			ACCESS	read-only
			STATUS	current
	DESCRIPTION ""
			::= { mbusCC 62 }

mbusCCValue1C		OBJECT-TYPE
			SYNTAX	INTEGER
			ACCESS	read-only
			STATUS	current
	DESCRIPTION ""
			::= { mbusCC 63 }

mbusCCVIF1D		OBJECT-TYPE
			SYNTAX	INTEGER
			ACCESS	read-only
			STATUS	current
	DESCRIPTION ""
			::= { mbusCC 64 }

mbusCCValue1D		OBJECT-TYPE
			SYNTAX	INTEGER
			ACCESS	read-only
			STATUS	current
	DESCRIPTION ""
			::= { mbusCC 65 }

mbusCCVIF1E		OBJECT-TYPE
			SYNTAX	INTEGER
			ACCESS	read-only
			STATUS	current
	DESCRIPTION ""
			::= { mbusCC 66 }

mbusCCValue1E		OBJECT-TYPE
			SYNTAX	INTEGER
			ACCESS	read-only
			STATUS	current
	DESCRIPTION ""
			::= { mbusCC 67 }

mbusCCVIF1F		OBJECT-TYPE
			SYNTAX	INTEGER
			ACCESS	read-only
			STATUS	current
	DESCRIPTION ""
			::= { mbusCC 68 }

mbusCCValue1F		OBJECT-TYPE
			SYNTAX	INTEGER
			ACCESS	read-only
			STATUS	current
	DESCRIPTION ""
			::= { mbusCC 69 }

mbusCCVIF20		OBJECT-TYPE
			SYNTAX	INTEGER
			ACCESS	read-only
			STATUS	current
	DESCRIPTION ""
			::= { mbusCC 70 }

mbusCCValue20		OBJECT-TYPE
			SYNTAX	INTEGER
			ACCESS	read-only
			STATUS	current
	DESCRIPTION ""
			::= { mbusCC 71 }

mbusCCVIF21		OBJECT-TYPE
			SYNTAX	INTEGER
			ACCESS	read-only
			STATUS	current
	DESCRIPTION ""
			::= { mbusCC 72 }

mbusCCValue21		OBJECT-TYPE
			SYNTAX	INTEGER
			ACCESS	read-only
			STATUS	current
	DESCRIPTION ""
			::= { mbusCC 73 }

mbusCCVIF22		OBJECT-TYPE
			SYNTAX	INTEGER
			ACCESS	read-only
			STATUS	current
	DESCRIPTION ""
			::= { mbusCC 74 }

mbusCCValue22		OBJECT-TYPE
			SYNTAX	INTEGER
			ACCESS	read-only
			STATUS	current
	DESCRIPTION ""
			::= { mbusCC 75 }

mbusCCVIF23		OBJECT-TYPE
			SYNTAX	INTEGER
			ACCESS	read-only
			STATUS	current
	DESCRIPTION ""
			::= { mbusCC 76 }

mbusCCValue23		OBJECT-TYPE
			SYNTAX	INTEGER
			ACCESS	read-only
			STATUS	current
	DESCRIPTION ""
			::= { mbusCC 77 }

mbusCCVIF24		OBJECT-TYPE
			SYNTAX	INTEGER
			ACCESS	read-only
			STATUS	current
	DESCRIPTION ""
			::= { mbusCC 78 }

mbusCCValue24		OBJECT-TYPE
			SYNTAX	INTEGER
			ACCESS	read-only
			STATUS	current
	DESCRIPTION ""
			::= { mbusCC 79 }

mbusCCVIF25		OBJECT-TYPE
			SYNTAX	INTEGER
			ACCESS	read-only
			STATUS	current
	DESCRIPTION ""
			::= { mbusCC 80 }

mbusCCValue25		OBJECT-TYPE
			SYNTAX	INTEGER
			ACCESS	read-only
			STATUS	current
	DESCRIPTION ""
			::= { mbusCC 81 }

mbusCCVIF26		OBJECT-TYPE
			SYNTAX	INTEGER
			ACCESS	read-only
			STATUS	current
	DESCRIPTION ""
			::= { mbusCC 82 }

mbusCCValue26		OBJECT-TYPE
			SYNTAX	INTEGER
			ACCESS	read-only
			STATUS	current
	DESCRIPTION ""
			::= { mbusCC 83 }

mbusCCVIF27		OBJECT-TYPE
			SYNTAX	INTEGER
			ACCESS	read-only
			STATUS	current
	DESCRIPTION ""
			::= { mbusCC 84 }

mbusCCValue27		OBJECT-TYPE
			SYNTAX	INTEGER
			ACCESS	read-only
			STATUS	current
	DESCRIPTION ""
			::= { mbusCC 85 }

mbusCCVIF28		OBJECT-TYPE
			SYNTAX	INTEGER
			ACCESS	read-only
			STATUS	current
	DESCRIPTION ""
			::= { mbusCC 86 }

mbusCCValue28		OBJECT-TYPE
			SYNTAX	INTEGER
			ACCESS	read-only
			STATUS	current
	DESCRIPTION ""
			::= { mbusCC 87 }

mbusCCVIF29		OBJECT-TYPE
			SYNTAX	INTEGER
			ACCESS	read-only
			STATUS	current
	DESCRIPTION ""
			::= { mbusCC 88 }

mbusCCValue29		OBJECT-TYPE
			SYNTAX	INTEGER
			ACCESS	read-only
			STATUS	current
	DESCRIPTION ""
			::= { mbusCC 89 }

mbusCCVIF2A		OBJECT-TYPE
			SYNTAX	INTEGER
			ACCESS	read-only
			STATUS	current
	DESCRIPTION ""
			::= { mbusCC 90 }

mbusCCValue2A		OBJECT-TYPE
			SYNTAX	INTEGER
			ACCESS	read-only
			STATUS	current
	DESCRIPTION ""
			::= { mbusCC 91 }

mbusCCVIF2B		OBJECT-TYPE
			SYNTAX	INTEGER
			ACCESS	read-only
			STATUS	current
	DESCRIPTION ""
			::= { mbusCC 92 }

mbusCCValue2B		OBJECT-TYPE
			SYNTAX	INTEGER
			ACCESS	read-only
			STATUS	current
	DESCRIPTION ""
			::= { mbusCC 93 }

mbusCCVIF2C		OBJECT-TYPE
			SYNTAX	INTEGER
			ACCESS	read-only
			STATUS	current
	DESCRIPTION ""
			::= { mbusCC 94 }

mbusCCValue2C		OBJECT-TYPE
			SYNTAX	INTEGER
			ACCESS	read-only
			STATUS	current
	DESCRIPTION ""
			::= { mbusCC 95 }

mbusCCVIF2D		OBJECT-TYPE
			SYNTAX	INTEGER
			ACCESS	read-only
			STATUS	current
	DESCRIPTION ""
			::= { mbusCC 96 }

mbusCCValue2D		OBJECT-TYPE
			SYNTAX	INTEGER
			ACCESS	read-only
			STATUS	current
	DESCRIPTION ""
			::= { mbusCC 97 }

mbusCCVIF2E		OBJECT-TYPE
			SYNTAX	INTEGER
			ACCESS	read-only
			STATUS	current
	DESCRIPTION ""
			::= { mbusCC 98 }

mbusCCValue2E		OBJECT-TYPE
			SYNTAX	INTEGER
			ACCESS	read-only
			STATUS	current
	DESCRIPTION ""
			::= { mbusCC 99 }

mbusCCVIF2F		OBJECT-TYPE
			SYNTAX	INTEGER
			ACCESS	read-only
			STATUS	current
	DESCRIPTION ""
			::= { mbusCC 100 }

mbusCCValue2F		OBJECT-TYPE
			SYNTAX	INTEGER
			ACCESS	read-only
			STATUS	current
	DESCRIPTION ""
			::= { mbusCC 101 }

mbusCD			OBJECT IDENTIFIER ::= { mbus 205 }

mbusCDIdNumber		OBJECT-TYPE
			SYNTAX	Gauge
			ACCESS	read-only
			STATUS	current
	DESCRIPTION ""
			::= { mbusCD 1 }

mbusCDManufacturer	OBJECT-TYPE
			SYNTAX	Gauge
			ACCESS	read-only
			STATUS	current
	DESCRIPTION ""
			::= { mbusCD 2 }

mbusCDVersion		OBJECT-TYPE
			SYNTAX	Gauge
			ACCESS	read-only
			STATUS	current
	DESCRIPTION ""
			::= { mbusCD 3 }

mbusCDMedium		OBJECT-TYPE
			SYNTAX	Gauge
			ACCESS	read-only
			STATUS	current
	DESCRIPTION ""
			::= { mbusCD 4 }

mbusCDStatus		OBJECT-TYPE
			SYNTAX	Gauge
			ACCESS	read-only
			STATUS	current
	DESCRIPTION ""
			::= { mbusCD 5 }

mbusCDVIF00		OBJECT-TYPE
			SYNTAX	INTEGER
			ACCESS	read-only
			STATUS	current
	DESCRIPTION ""
			::= { mbusCD 6 }

mbusCDValue00		OBJECT-TYPE
			SYNTAX	INTEGER
			ACCESS	read-only
			STATUS	current
	DESCRIPTION ""
			::= { mbusCD 7 }

mbusCDVIF01		OBJECT-TYPE
			SYNTAX	INTEGER
			ACCESS	read-only
			STATUS	current
	DESCRIPTION ""
			::= { mbusCD 8 }

mbusCDValue01		OBJECT-TYPE
			SYNTAX	INTEGER
			ACCESS	read-only
			STATUS	current
	DESCRIPTION ""
			::= { mbusCD 9 }

mbusCDVIF02		OBJECT-TYPE
			SYNTAX	INTEGER
			ACCESS	read-only
			STATUS	current
	DESCRIPTION ""
			::= { mbusCD 10 }

mbusCDValue02		OBJECT-TYPE
			SYNTAX	INTEGER
			ACCESS	read-only
			STATUS	current
	DESCRIPTION ""
			::= { mbusCD 11 }

mbusCDVIF03		OBJECT-TYPE
			SYNTAX	INTEGER
			ACCESS	read-only
			STATUS	current
	DESCRIPTION ""
			::= { mbusCD 12 }

mbusCDValue03		OBJECT-TYPE
			SYNTAX	INTEGER
			ACCESS	read-only
			STATUS	current
	DESCRIPTION ""
			::= { mbusCD 13 }

mbusCDVIF04		OBJECT-TYPE
			SYNTAX	INTEGER
			ACCESS	read-only
			STATUS	current
	DESCRIPTION ""
			::= { mbusCD 14 }

mbusCDValue04		OBJECT-TYPE
			SYNTAX	INTEGER
			ACCESS	read-only
			STATUS	current
	DESCRIPTION ""
			::= { mbusCD 15 }

mbusCDVIF05		OBJECT-TYPE
			SYNTAX	INTEGER
			ACCESS	read-only
			STATUS	current
	DESCRIPTION ""
			::= { mbusCD 16 }

mbusCDValue05		OBJECT-TYPE
			SYNTAX	INTEGER
			ACCESS	read-only
			STATUS	current
	DESCRIPTION ""
			::= { mbusCD 17 }

mbusCDVIF06		OBJECT-TYPE
			SYNTAX	INTEGER
			ACCESS	read-only
			STATUS	current
	DESCRIPTION ""
			::= { mbusCD 18 }

mbusCDValue06		OBJECT-TYPE
			SYNTAX	INTEGER
			ACCESS	read-only
			STATUS	current
	DESCRIPTION ""
			::= { mbusCD 19 }

mbusCDVIF07		OBJECT-TYPE
			SYNTAX	INTEGER
			ACCESS	read-only
			STATUS	current
	DESCRIPTION ""
			::= { mbusCD 20 }

mbusCDValue07		OBJECT-TYPE
			SYNTAX	INTEGER
			ACCESS	read-only
			STATUS	current
	DESCRIPTION ""
			::= { mbusCD 21 }

mbusCDVIF08		OBJECT-TYPE
			SYNTAX	INTEGER
			ACCESS	read-only
			STATUS	current
	DESCRIPTION ""
			::= { mbusCD 22 }

mbusCDValue08		OBJECT-TYPE
			SYNTAX	INTEGER
			ACCESS	read-only
			STATUS	current
	DESCRIPTION ""
			::= { mbusCD 23 }

mbusCDVIF09		OBJECT-TYPE
			SYNTAX	INTEGER
			ACCESS	read-only
			STATUS	current
	DESCRIPTION ""
			::= { mbusCD 24 }

mbusCDValue09		OBJECT-TYPE
			SYNTAX	INTEGER
			ACCESS	read-only
			STATUS	current
	DESCRIPTION ""
			::= { mbusCD 25 }

mbusCDVIF0A		OBJECT-TYPE
			SYNTAX	INTEGER
			ACCESS	read-only
			STATUS	current
	DESCRIPTION ""
			::= { mbusCD 26 }

mbusCDValue0A		OBJECT-TYPE
			SYNTAX	INTEGER
			ACCESS	read-only
			STATUS	current
	DESCRIPTION ""
			::= { mbusCD 27 }

mbusCDVIF0B		OBJECT-TYPE
			SYNTAX	INTEGER
			ACCESS	read-only
			STATUS	current
	DESCRIPTION ""
			::= { mbusCD 28 }

mbusCDValue0B		OBJECT-TYPE
			SYNTAX	INTEGER
			ACCESS	read-only
			STATUS	current
	DESCRIPTION ""
			::= { mbusCD 29 }

mbusCDVIF0C		OBJECT-TYPE
			SYNTAX	INTEGER
			ACCESS	read-only
			STATUS	current
	DESCRIPTION ""
			::= { mbusCD 30 }

mbusCDValue0C		OBJECT-TYPE
			SYNTAX	INTEGER
			ACCESS	read-only
			STATUS	current
	DESCRIPTION ""
			::= { mbusCD 31 }

mbusCDVIF0D		OBJECT-TYPE
			SYNTAX	INTEGER
			ACCESS	read-only
			STATUS	current
	DESCRIPTION ""
			::= { mbusCD 32 }

mbusCDValue0D		OBJECT-TYPE
			SYNTAX	INTEGER
			ACCESS	read-only
			STATUS	current
	DESCRIPTION ""
			::= { mbusCD 33 }

mbusCDVIF0E		OBJECT-TYPE
			SYNTAX	INTEGER
			ACCESS	read-only
			STATUS	current
	DESCRIPTION ""
			::= { mbusCD 34 }

mbusCDValue0E		OBJECT-TYPE
			SYNTAX	INTEGER
			ACCESS	read-only
			STATUS	current
	DESCRIPTION ""
			::= { mbusCD 35 }

mbusCDVIF0F		OBJECT-TYPE
			SYNTAX	INTEGER
			ACCESS	read-only
			STATUS	current
	DESCRIPTION ""
			::= { mbusCD 36 }

mbusCDValue0F		OBJECT-TYPE
			SYNTAX	INTEGER
			ACCESS	read-only
			STATUS	current
	DESCRIPTION ""
			::= { mbusCD 37 }

mbusCDVIF10		OBJECT-TYPE
			SYNTAX	INTEGER
			ACCESS	read-only
			STATUS	current
	DESCRIPTION ""
			::= { mbusCD 38 }

mbusCDValue10		OBJECT-TYPE
			SYNTAX	INTEGER
			ACCESS	read-only
			STATUS	current
	DESCRIPTION ""
			::= { mbusCD 39 }

mbusCDVIF11		OBJECT-TYPE
			SYNTAX	INTEGER
			ACCESS	read-only
			STATUS	current
	DESCRIPTION ""
			::= { mbusCD 40 }

mbusCDValue11		OBJECT-TYPE
			SYNTAX	INTEGER
			ACCESS	read-only
			STATUS	current
	DESCRIPTION ""
			::= { mbusCD 41 }

mbusCDVIF12		OBJECT-TYPE
			SYNTAX	INTEGER
			ACCESS	read-only
			STATUS	current
	DESCRIPTION ""
			::= { mbusCD 42 }

mbusCDValue12		OBJECT-TYPE
			SYNTAX	INTEGER
			ACCESS	read-only
			STATUS	current
	DESCRIPTION ""
			::= { mbusCD 43 }

mbusCDVIF13		OBJECT-TYPE
			SYNTAX	INTEGER
			ACCESS	read-only
			STATUS	current
	DESCRIPTION ""
			::= { mbusCD 44 }

mbusCDValue13		OBJECT-TYPE
			SYNTAX	INTEGER
			ACCESS	read-only
			STATUS	current
	DESCRIPTION ""
			::= { mbusCD 45 }

mbusCDVIF14		OBJECT-TYPE
			SYNTAX	INTEGER
			ACCESS	read-only
			STATUS	current
	DESCRIPTION ""
			::= { mbusCD 46 }

mbusCDValue14		OBJECT-TYPE
			SYNTAX	INTEGER
			ACCESS	read-only
			STATUS	current
	DESCRIPTION ""
			::= { mbusCD 47 }

mbusCDVIF15		OBJECT-TYPE
			SYNTAX	INTEGER
			ACCESS	read-only
			STATUS	current
	DESCRIPTION ""
			::= { mbusCD 48 }

mbusCDValue15		OBJECT-TYPE
			SYNTAX	INTEGER
			ACCESS	read-only
			STATUS	current
	DESCRIPTION ""
			::= { mbusCD 49 }

mbusCDVIF16		OBJECT-TYPE
			SYNTAX	INTEGER
			ACCESS	read-only
			STATUS	current
	DESCRIPTION ""
			::= { mbusCD 50 }

mbusCDValue16		OBJECT-TYPE
			SYNTAX	INTEGER
			ACCESS	read-only
			STATUS	current
	DESCRIPTION ""
			::= { mbusCD 51 }

mbusCDVIF17		OBJECT-TYPE
			SYNTAX	INTEGER
			ACCESS	read-only
			STATUS	current
	DESCRIPTION ""
			::= { mbusCD 52 }

mbusCDValue17		OBJECT-TYPE
			SYNTAX	INTEGER
			ACCESS	read-only
			STATUS	current
	DESCRIPTION ""
			::= { mbusCD 53 }

mbusCDVIF18		OBJECT-TYPE
			SYNTAX	INTEGER
			ACCESS	read-only
			STATUS	current
	DESCRIPTION ""
			::= { mbusCD 54 }

mbusCDValue18		OBJECT-TYPE
			SYNTAX	INTEGER
			ACCESS	read-only
			STATUS	current
	DESCRIPTION ""
			::= { mbusCD 55 }

mbusCDVIF19		OBJECT-TYPE
			SYNTAX	INTEGER
			ACCESS	read-only
			STATUS	current
	DESCRIPTION ""
			::= { mbusCD 56 }

mbusCDValue19		OBJECT-TYPE
			SYNTAX	INTEGER
			ACCESS	read-only
			STATUS	current
	DESCRIPTION ""
			::= { mbusCD 57 }

mbusCDVIF1A		OBJECT-TYPE
			SYNTAX	INTEGER
			ACCESS	read-only
			STATUS	current
	DESCRIPTION ""
			::= { mbusCD 58 }

mbusCDValue1A		OBJECT-TYPE
			SYNTAX	INTEGER
			ACCESS	read-only
			STATUS	current
	DESCRIPTION ""
			::= { mbusCD 59 }

mbusCDVIF1B		OBJECT-TYPE
			SYNTAX	INTEGER
			ACCESS	read-only
			STATUS	current
	DESCRIPTION ""
			::= { mbusCD 60 }

mbusCDValue1B		OBJECT-TYPE
			SYNTAX	INTEGER
			ACCESS	read-only
			STATUS	current
	DESCRIPTION ""
			::= { mbusCD 61 }

mbusCDVIF1C		OBJECT-TYPE
			SYNTAX	INTEGER
			ACCESS	read-only
			STATUS	current
	DESCRIPTION ""
			::= { mbusCD 62 }

mbusCDValue1C		OBJECT-TYPE
			SYNTAX	INTEGER
			ACCESS	read-only
			STATUS	current
	DESCRIPTION ""
			::= { mbusCD 63 }

mbusCDVIF1D		OBJECT-TYPE
			SYNTAX	INTEGER
			ACCESS	read-only
			STATUS	current
	DESCRIPTION ""
			::= { mbusCD 64 }

mbusCDValue1D		OBJECT-TYPE
			SYNTAX	INTEGER
			ACCESS	read-only
			STATUS	current
	DESCRIPTION ""
			::= { mbusCD 65 }

mbusCDVIF1E		OBJECT-TYPE
			SYNTAX	INTEGER
			ACCESS	read-only
			STATUS	current
	DESCRIPTION ""
			::= { mbusCD 66 }

mbusCDValue1E		OBJECT-TYPE
			SYNTAX	INTEGER
			ACCESS	read-only
			STATUS	current
	DESCRIPTION ""
			::= { mbusCD 67 }

mbusCDVIF1F		OBJECT-TYPE
			SYNTAX	INTEGER
			ACCESS	read-only
			STATUS	current
	DESCRIPTION ""
			::= { mbusCD 68 }

mbusCDValue1F		OBJECT-TYPE
			SYNTAX	INTEGER
			ACCESS	read-only
			STATUS	current
	DESCRIPTION ""
			::= { mbusCD 69 }

mbusCDVIF20		OBJECT-TYPE
			SYNTAX	INTEGER
			ACCESS	read-only
			STATUS	current
	DESCRIPTION ""
			::= { mbusCD 70 }

mbusCDValue20		OBJECT-TYPE
			SYNTAX	INTEGER
			ACCESS	read-only
			STATUS	current
	DESCRIPTION ""
			::= { mbusCD 71 }

mbusCDVIF21		OBJECT-TYPE
			SYNTAX	INTEGER
			ACCESS	read-only
			STATUS	current
	DESCRIPTION ""
			::= { mbusCD 72 }

mbusCDValue21		OBJECT-TYPE
			SYNTAX	INTEGER
			ACCESS	read-only
			STATUS	current
	DESCRIPTION ""
			::= { mbusCD 73 }

mbusCDVIF22		OBJECT-TYPE
			SYNTAX	INTEGER
			ACCESS	read-only
			STATUS	current
	DESCRIPTION ""
			::= { mbusCD 74 }

mbusCDValue22		OBJECT-TYPE
			SYNTAX	INTEGER
			ACCESS	read-only
			STATUS	current
	DESCRIPTION ""
			::= { mbusCD 75 }

mbusCDVIF23		OBJECT-TYPE
			SYNTAX	INTEGER
			ACCESS	read-only
			STATUS	current
	DESCRIPTION ""
			::= { mbusCD 76 }

mbusCDValue23		OBJECT-TYPE
			SYNTAX	INTEGER
			ACCESS	read-only
			STATUS	current
	DESCRIPTION ""
			::= { mbusCD 77 }

mbusCDVIF24		OBJECT-TYPE
			SYNTAX	INTEGER
			ACCESS	read-only
			STATUS	current
	DESCRIPTION ""
			::= { mbusCD 78 }

mbusCDValue24		OBJECT-TYPE
			SYNTAX	INTEGER
			ACCESS	read-only
			STATUS	current
	DESCRIPTION ""
			::= { mbusCD 79 }

mbusCDVIF25		OBJECT-TYPE
			SYNTAX	INTEGER
			ACCESS	read-only
			STATUS	current
	DESCRIPTION ""
			::= { mbusCD 80 }

mbusCDValue25		OBJECT-TYPE
			SYNTAX	INTEGER
			ACCESS	read-only
			STATUS	current
	DESCRIPTION ""
			::= { mbusCD 81 }

mbusCDVIF26		OBJECT-TYPE
			SYNTAX	INTEGER
			ACCESS	read-only
			STATUS	current
	DESCRIPTION ""
			::= { mbusCD 82 }

mbusCDValue26		OBJECT-TYPE
			SYNTAX	INTEGER
			ACCESS	read-only
			STATUS	current
	DESCRIPTION ""
			::= { mbusCD 83 }

mbusCDVIF27		OBJECT-TYPE
			SYNTAX	INTEGER
			ACCESS	read-only
			STATUS	current
	DESCRIPTION ""
			::= { mbusCD 84 }

mbusCDValue27		OBJECT-TYPE
			SYNTAX	INTEGER
			ACCESS	read-only
			STATUS	current
	DESCRIPTION ""
			::= { mbusCD 85 }

mbusCDVIF28		OBJECT-TYPE
			SYNTAX	INTEGER
			ACCESS	read-only
			STATUS	current
	DESCRIPTION ""
			::= { mbusCD 86 }

mbusCDValue28		OBJECT-TYPE
			SYNTAX	INTEGER
			ACCESS	read-only
			STATUS	current
	DESCRIPTION ""
			::= { mbusCD 87 }

mbusCDVIF29		OBJECT-TYPE
			SYNTAX	INTEGER
			ACCESS	read-only
			STATUS	current
	DESCRIPTION ""
			::= { mbusCD 88 }

mbusCDValue29		OBJECT-TYPE
			SYNTAX	INTEGER
			ACCESS	read-only
			STATUS	current
	DESCRIPTION ""
			::= { mbusCD 89 }

mbusCDVIF2A		OBJECT-TYPE
			SYNTAX	INTEGER
			ACCESS	read-only
			STATUS	current
	DESCRIPTION ""
			::= { mbusCD 90 }

mbusCDValue2A		OBJECT-TYPE
			SYNTAX	INTEGER
			ACCESS	read-only
			STATUS	current
	DESCRIPTION ""
			::= { mbusCD 91 }

mbusCDVIF2B		OBJECT-TYPE
			SYNTAX	INTEGER
			ACCESS	read-only
			STATUS	current
	DESCRIPTION ""
			::= { mbusCD 92 }

mbusCDValue2B		OBJECT-TYPE
			SYNTAX	INTEGER
			ACCESS	read-only
			STATUS	current
	DESCRIPTION ""
			::= { mbusCD 93 }

mbusCDVIF2C		OBJECT-TYPE
			SYNTAX	INTEGER
			ACCESS	read-only
			STATUS	current
	DESCRIPTION ""
			::= { mbusCD 94 }

mbusCDValue2C		OBJECT-TYPE
			SYNTAX	INTEGER
			ACCESS	read-only
			STATUS	current
	DESCRIPTION ""
			::= { mbusCD 95 }

mbusCDVIF2D		OBJECT-TYPE
			SYNTAX	INTEGER
			ACCESS	read-only
			STATUS	current
	DESCRIPTION ""
			::= { mbusCD 96 }

mbusCDValue2D		OBJECT-TYPE
			SYNTAX	INTEGER
			ACCESS	read-only
			STATUS	current
	DESCRIPTION ""
			::= { mbusCD 97 }

mbusCDVIF2E		OBJECT-TYPE
			SYNTAX	INTEGER
			ACCESS	read-only
			STATUS	current
	DESCRIPTION ""
			::= { mbusCD 98 }

mbusCDValue2E		OBJECT-TYPE
			SYNTAX	INTEGER
			ACCESS	read-only
			STATUS	current
	DESCRIPTION ""
			::= { mbusCD 99 }

mbusCDVIF2F		OBJECT-TYPE
			SYNTAX	INTEGER
			ACCESS	read-only
			STATUS	current
	DESCRIPTION ""
			::= { mbusCD 100 }

mbusCDValue2F		OBJECT-TYPE
			SYNTAX	INTEGER
			ACCESS	read-only
			STATUS	current
	DESCRIPTION ""
			::= { mbusCD 101 }

mbusCE			OBJECT IDENTIFIER ::= { mbus 206 }

mbusCEIdNumber		OBJECT-TYPE
			SYNTAX	Gauge
			ACCESS	read-only
			STATUS	current
	DESCRIPTION ""
			::= { mbusCE 1 }

mbusCEManufacturer	OBJECT-TYPE
			SYNTAX	Gauge
			ACCESS	read-only
			STATUS	current
	DESCRIPTION ""
			::= { mbusCE 2 }

mbusCEVersion		OBJECT-TYPE
			SYNTAX	Gauge
			ACCESS	read-only
			STATUS	current
	DESCRIPTION ""
			::= { mbusCE 3 }

mbusCEMedium		OBJECT-TYPE
			SYNTAX	Gauge
			ACCESS	read-only
			STATUS	current
	DESCRIPTION ""
			::= { mbusCE 4 }

mbusCEStatus		OBJECT-TYPE
			SYNTAX	Gauge
			ACCESS	read-only
			STATUS	current
	DESCRIPTION ""
			::= { mbusCE 5 }

mbusCEVIF00		OBJECT-TYPE
			SYNTAX	INTEGER
			ACCESS	read-only
			STATUS	current
	DESCRIPTION ""
			::= { mbusCE 6 }

mbusCEValue00		OBJECT-TYPE
			SYNTAX	INTEGER
			ACCESS	read-only
			STATUS	current
	DESCRIPTION ""
			::= { mbusCE 7 }

mbusCEVIF01		OBJECT-TYPE
			SYNTAX	INTEGER
			ACCESS	read-only
			STATUS	current
	DESCRIPTION ""
			::= { mbusCE 8 }

mbusCEValue01		OBJECT-TYPE
			SYNTAX	INTEGER
			ACCESS	read-only
			STATUS	current
	DESCRIPTION ""
			::= { mbusCE 9 }

mbusCEVIF02		OBJECT-TYPE
			SYNTAX	INTEGER
			ACCESS	read-only
			STATUS	current
	DESCRIPTION ""
			::= { mbusCE 10 }

mbusCEValue02		OBJECT-TYPE
			SYNTAX	INTEGER
			ACCESS	read-only
			STATUS	current
	DESCRIPTION ""
			::= { mbusCE 11 }

mbusCEVIF03		OBJECT-TYPE
			SYNTAX	INTEGER
			ACCESS	read-only
			STATUS	current
	DESCRIPTION ""
			::= { mbusCE 12 }

mbusCEValue03		OBJECT-TYPE
			SYNTAX	INTEGER
			ACCESS	read-only
			STATUS	current
	DESCRIPTION ""
			::= { mbusCE 13 }

mbusCEVIF04		OBJECT-TYPE
			SYNTAX	INTEGER
			ACCESS	read-only
			STATUS	current
	DESCRIPTION ""
			::= { mbusCE 14 }

mbusCEValue04		OBJECT-TYPE
			SYNTAX	INTEGER
			ACCESS	read-only
			STATUS	current
	DESCRIPTION ""
			::= { mbusCE 15 }

mbusCEVIF05		OBJECT-TYPE
			SYNTAX	INTEGER
			ACCESS	read-only
			STATUS	current
	DESCRIPTION ""
			::= { mbusCE 16 }

mbusCEValue05		OBJECT-TYPE
			SYNTAX	INTEGER
			ACCESS	read-only
			STATUS	current
	DESCRIPTION ""
			::= { mbusCE 17 }

mbusCEVIF06		OBJECT-TYPE
			SYNTAX	INTEGER
			ACCESS	read-only
			STATUS	current
	DESCRIPTION ""
			::= { mbusCE 18 }

mbusCEValue06		OBJECT-TYPE
			SYNTAX	INTEGER
			ACCESS	read-only
			STATUS	current
	DESCRIPTION ""
			::= { mbusCE 19 }

mbusCEVIF07		OBJECT-TYPE
			SYNTAX	INTEGER
			ACCESS	read-only
			STATUS	current
	DESCRIPTION ""
			::= { mbusCE 20 }

mbusCEValue07		OBJECT-TYPE
			SYNTAX	INTEGER
			ACCESS	read-only
			STATUS	current
	DESCRIPTION ""
			::= { mbusCE 21 }

mbusCEVIF08		OBJECT-TYPE
			SYNTAX	INTEGER
			ACCESS	read-only
			STATUS	current
	DESCRIPTION ""
			::= { mbusCE 22 }

mbusCEValue08		OBJECT-TYPE
			SYNTAX	INTEGER
			ACCESS	read-only
			STATUS	current
	DESCRIPTION ""
			::= { mbusCE 23 }

mbusCEVIF09		OBJECT-TYPE
			SYNTAX	INTEGER
			ACCESS	read-only
			STATUS	current
	DESCRIPTION ""
			::= { mbusCE 24 }

mbusCEValue09		OBJECT-TYPE
			SYNTAX	INTEGER
			ACCESS	read-only
			STATUS	current
	DESCRIPTION ""
			::= { mbusCE 25 }

mbusCEVIF0A		OBJECT-TYPE
			SYNTAX	INTEGER
			ACCESS	read-only
			STATUS	current
	DESCRIPTION ""
			::= { mbusCE 26 }

mbusCEValue0A		OBJECT-TYPE
			SYNTAX	INTEGER
			ACCESS	read-only
			STATUS	current
	DESCRIPTION ""
			::= { mbusCE 27 }

mbusCEVIF0B		OBJECT-TYPE
			SYNTAX	INTEGER
			ACCESS	read-only
			STATUS	current
	DESCRIPTION ""
			::= { mbusCE 28 }

mbusCEValue0B		OBJECT-TYPE
			SYNTAX	INTEGER
			ACCESS	read-only
			STATUS	current
	DESCRIPTION ""
			::= { mbusCE 29 }

mbusCEVIF0C		OBJECT-TYPE
			SYNTAX	INTEGER
			ACCESS	read-only
			STATUS	current
	DESCRIPTION ""
			::= { mbusCE 30 }

mbusCEValue0C		OBJECT-TYPE
			SYNTAX	INTEGER
			ACCESS	read-only
			STATUS	current
	DESCRIPTION ""
			::= { mbusCE 31 }

mbusCEVIF0D		OBJECT-TYPE
			SYNTAX	INTEGER
			ACCESS	read-only
			STATUS	current
	DESCRIPTION ""
			::= { mbusCE 32 }

mbusCEValue0D		OBJECT-TYPE
			SYNTAX	INTEGER
			ACCESS	read-only
			STATUS	current
	DESCRIPTION ""
			::= { mbusCE 33 }

mbusCEVIF0E		OBJECT-TYPE
			SYNTAX	INTEGER
			ACCESS	read-only
			STATUS	current
	DESCRIPTION ""
			::= { mbusCE 34 }

mbusCEValue0E		OBJECT-TYPE
			SYNTAX	INTEGER
			ACCESS	read-only
			STATUS	current
	DESCRIPTION ""
			::= { mbusCE 35 }

mbusCEVIF0F		OBJECT-TYPE
			SYNTAX	INTEGER
			ACCESS	read-only
			STATUS	current
	DESCRIPTION ""
			::= { mbusCE 36 }

mbusCEValue0F		OBJECT-TYPE
			SYNTAX	INTEGER
			ACCESS	read-only
			STATUS	current
	DESCRIPTION ""
			::= { mbusCE 37 }

mbusCEVIF10		OBJECT-TYPE
			SYNTAX	INTEGER
			ACCESS	read-only
			STATUS	current
	DESCRIPTION ""
			::= { mbusCE 38 }

mbusCEValue10		OBJECT-TYPE
			SYNTAX	INTEGER
			ACCESS	read-only
			STATUS	current
	DESCRIPTION ""
			::= { mbusCE 39 }

mbusCEVIF11		OBJECT-TYPE
			SYNTAX	INTEGER
			ACCESS	read-only
			STATUS	current
	DESCRIPTION ""
			::= { mbusCE 40 }

mbusCEValue11		OBJECT-TYPE
			SYNTAX	INTEGER
			ACCESS	read-only
			STATUS	current
	DESCRIPTION ""
			::= { mbusCE 41 }

mbusCEVIF12		OBJECT-TYPE
			SYNTAX	INTEGER
			ACCESS	read-only
			STATUS	current
	DESCRIPTION ""
			::= { mbusCE 42 }

mbusCEValue12		OBJECT-TYPE
			SYNTAX	INTEGER
			ACCESS	read-only
			STATUS	current
	DESCRIPTION ""
			::= { mbusCE 43 }

mbusCEVIF13		OBJECT-TYPE
			SYNTAX	INTEGER
			ACCESS	read-only
			STATUS	current
	DESCRIPTION ""
			::= { mbusCE 44 }

mbusCEValue13		OBJECT-TYPE
			SYNTAX	INTEGER
			ACCESS	read-only
			STATUS	current
	DESCRIPTION ""
			::= { mbusCE 45 }

mbusCEVIF14		OBJECT-TYPE
			SYNTAX	INTEGER
			ACCESS	read-only
			STATUS	current
	DESCRIPTION ""
			::= { mbusCE 46 }

mbusCEValue14		OBJECT-TYPE
			SYNTAX	INTEGER
			ACCESS	read-only
			STATUS	current
	DESCRIPTION ""
			::= { mbusCE 47 }

mbusCEVIF15		OBJECT-TYPE
			SYNTAX	INTEGER
			ACCESS	read-only
			STATUS	current
	DESCRIPTION ""
			::= { mbusCE 48 }

mbusCEValue15		OBJECT-TYPE
			SYNTAX	INTEGER
			ACCESS	read-only
			STATUS	current
	DESCRIPTION ""
			::= { mbusCE 49 }

mbusCEVIF16		OBJECT-TYPE
			SYNTAX	INTEGER
			ACCESS	read-only
			STATUS	current
	DESCRIPTION ""
			::= { mbusCE 50 }

mbusCEValue16		OBJECT-TYPE
			SYNTAX	INTEGER
			ACCESS	read-only
			STATUS	current
	DESCRIPTION ""
			::= { mbusCE 51 }

mbusCEVIF17		OBJECT-TYPE
			SYNTAX	INTEGER
			ACCESS	read-only
			STATUS	current
	DESCRIPTION ""
			::= { mbusCE 52 }

mbusCEValue17		OBJECT-TYPE
			SYNTAX	INTEGER
			ACCESS	read-only
			STATUS	current
	DESCRIPTION ""
			::= { mbusCE 53 }

mbusCEVIF18		OBJECT-TYPE
			SYNTAX	INTEGER
			ACCESS	read-only
			STATUS	current
	DESCRIPTION ""
			::= { mbusCE 54 }

mbusCEValue18		OBJECT-TYPE
			SYNTAX	INTEGER
			ACCESS	read-only
			STATUS	current
	DESCRIPTION ""
			::= { mbusCE 55 }

mbusCEVIF19		OBJECT-TYPE
			SYNTAX	INTEGER
			ACCESS	read-only
			STATUS	current
	DESCRIPTION ""
			::= { mbusCE 56 }

mbusCEValue19		OBJECT-TYPE
			SYNTAX	INTEGER
			ACCESS	read-only
			STATUS	current
	DESCRIPTION ""
			::= { mbusCE 57 }

mbusCEVIF1A		OBJECT-TYPE
			SYNTAX	INTEGER
			ACCESS	read-only
			STATUS	current
	DESCRIPTION ""
			::= { mbusCE 58 }

mbusCEValue1A		OBJECT-TYPE
			SYNTAX	INTEGER
			ACCESS	read-only
			STATUS	current
	DESCRIPTION ""
			::= { mbusCE 59 }

mbusCEVIF1B		OBJECT-TYPE
			SYNTAX	INTEGER
			ACCESS	read-only
			STATUS	current
	DESCRIPTION ""
			::= { mbusCE 60 }

mbusCEValue1B		OBJECT-TYPE
			SYNTAX	INTEGER
			ACCESS	read-only
			STATUS	current
	DESCRIPTION ""
			::= { mbusCE 61 }

mbusCEVIF1C		OBJECT-TYPE
			SYNTAX	INTEGER
			ACCESS	read-only
			STATUS	current
	DESCRIPTION ""
			::= { mbusCE 62 }

mbusCEValue1C		OBJECT-TYPE
			SYNTAX	INTEGER
			ACCESS	read-only
			STATUS	current
	DESCRIPTION ""
			::= { mbusCE 63 }

mbusCEVIF1D		OBJECT-TYPE
			SYNTAX	INTEGER
			ACCESS	read-only
			STATUS	current
	DESCRIPTION ""
			::= { mbusCE 64 }

mbusCEValue1D		OBJECT-TYPE
			SYNTAX	INTEGER
			ACCESS	read-only
			STATUS	current
	DESCRIPTION ""
			::= { mbusCE 65 }

mbusCEVIF1E		OBJECT-TYPE
			SYNTAX	INTEGER
			ACCESS	read-only
			STATUS	current
	DESCRIPTION ""
			::= { mbusCE 66 }

mbusCEValue1E		OBJECT-TYPE
			SYNTAX	INTEGER
			ACCESS	read-only
			STATUS	current
	DESCRIPTION ""
			::= { mbusCE 67 }

mbusCEVIF1F		OBJECT-TYPE
			SYNTAX	INTEGER
			ACCESS	read-only
			STATUS	current
	DESCRIPTION ""
			::= { mbusCE 68 }

mbusCEValue1F		OBJECT-TYPE
			SYNTAX	INTEGER
			ACCESS	read-only
			STATUS	current
	DESCRIPTION ""
			::= { mbusCE 69 }

mbusCEVIF20		OBJECT-TYPE
			SYNTAX	INTEGER
			ACCESS	read-only
			STATUS	current
	DESCRIPTION ""
			::= { mbusCE 70 }

mbusCEValue20		OBJECT-TYPE
			SYNTAX	INTEGER
			ACCESS	read-only
			STATUS	current
	DESCRIPTION ""
			::= { mbusCE 71 }

mbusCEVIF21		OBJECT-TYPE
			SYNTAX	INTEGER
			ACCESS	read-only
			STATUS	current
	DESCRIPTION ""
			::= { mbusCE 72 }

mbusCEValue21		OBJECT-TYPE
			SYNTAX	INTEGER
			ACCESS	read-only
			STATUS	current
	DESCRIPTION ""
			::= { mbusCE 73 }

mbusCEVIF22		OBJECT-TYPE
			SYNTAX	INTEGER
			ACCESS	read-only
			STATUS	current
	DESCRIPTION ""
			::= { mbusCE 74 }

mbusCEValue22		OBJECT-TYPE
			SYNTAX	INTEGER
			ACCESS	read-only
			STATUS	current
	DESCRIPTION ""
			::= { mbusCE 75 }

mbusCEVIF23		OBJECT-TYPE
			SYNTAX	INTEGER
			ACCESS	read-only
			STATUS	current
	DESCRIPTION ""
			::= { mbusCE 76 }

mbusCEValue23		OBJECT-TYPE
			SYNTAX	INTEGER
			ACCESS	read-only
			STATUS	current
	DESCRIPTION ""
			::= { mbusCE 77 }

mbusCEVIF24		OBJECT-TYPE
			SYNTAX	INTEGER
			ACCESS	read-only
			STATUS	current
	DESCRIPTION ""
			::= { mbusCE 78 }

mbusCEValue24		OBJECT-TYPE
			SYNTAX	INTEGER
			ACCESS	read-only
			STATUS	current
	DESCRIPTION ""
			::= { mbusCE 79 }

mbusCEVIF25		OBJECT-TYPE
			SYNTAX	INTEGER
			ACCESS	read-only
			STATUS	current
	DESCRIPTION ""
			::= { mbusCE 80 }

mbusCEValue25		OBJECT-TYPE
			SYNTAX	INTEGER
			ACCESS	read-only
			STATUS	current
	DESCRIPTION ""
			::= { mbusCE 81 }

mbusCEVIF26		OBJECT-TYPE
			SYNTAX	INTEGER
			ACCESS	read-only
			STATUS	current
	DESCRIPTION ""
			::= { mbusCE 82 }

mbusCEValue26		OBJECT-TYPE
			SYNTAX	INTEGER
			ACCESS	read-only
			STATUS	current
	DESCRIPTION ""
			::= { mbusCE 83 }

mbusCEVIF27		OBJECT-TYPE
			SYNTAX	INTEGER
			ACCESS	read-only
			STATUS	current
	DESCRIPTION ""
			::= { mbusCE 84 }

mbusCEValue27		OBJECT-TYPE
			SYNTAX	INTEGER
			ACCESS	read-only
			STATUS	current
	DESCRIPTION ""
			::= { mbusCE 85 }

mbusCEVIF28		OBJECT-TYPE
			SYNTAX	INTEGER
			ACCESS	read-only
			STATUS	current
	DESCRIPTION ""
			::= { mbusCE 86 }

mbusCEValue28		OBJECT-TYPE
			SYNTAX	INTEGER
			ACCESS	read-only
			STATUS	current
	DESCRIPTION ""
			::= { mbusCE 87 }

mbusCEVIF29		OBJECT-TYPE
			SYNTAX	INTEGER
			ACCESS	read-only
			STATUS	current
	DESCRIPTION ""
			::= { mbusCE 88 }

mbusCEValue29		OBJECT-TYPE
			SYNTAX	INTEGER
			ACCESS	read-only
			STATUS	current
	DESCRIPTION ""
			::= { mbusCE 89 }

mbusCEVIF2A		OBJECT-TYPE
			SYNTAX	INTEGER
			ACCESS	read-only
			STATUS	current
	DESCRIPTION ""
			::= { mbusCE 90 }

mbusCEValue2A		OBJECT-TYPE
			SYNTAX	INTEGER
			ACCESS	read-only
			STATUS	current
	DESCRIPTION ""
			::= { mbusCE 91 }

mbusCEVIF2B		OBJECT-TYPE
			SYNTAX	INTEGER
			ACCESS	read-only
			STATUS	current
	DESCRIPTION ""
			::= { mbusCE 92 }

mbusCEValue2B		OBJECT-TYPE
			SYNTAX	INTEGER
			ACCESS	read-only
			STATUS	current
	DESCRIPTION ""
			::= { mbusCE 93 }

mbusCEVIF2C		OBJECT-TYPE
			SYNTAX	INTEGER
			ACCESS	read-only
			STATUS	current
	DESCRIPTION ""
			::= { mbusCE 94 }

mbusCEValue2C		OBJECT-TYPE
			SYNTAX	INTEGER
			ACCESS	read-only
			STATUS	current
	DESCRIPTION ""
			::= { mbusCE 95 }

mbusCEVIF2D		OBJECT-TYPE
			SYNTAX	INTEGER
			ACCESS	read-only
			STATUS	current
	DESCRIPTION ""
			::= { mbusCE 96 }

mbusCEValue2D		OBJECT-TYPE
			SYNTAX	INTEGER
			ACCESS	read-only
			STATUS	current
	DESCRIPTION ""
			::= { mbusCE 97 }

mbusCEVIF2E		OBJECT-TYPE
			SYNTAX	INTEGER
			ACCESS	read-only
			STATUS	current
	DESCRIPTION ""
			::= { mbusCE 98 }

mbusCEValue2E		OBJECT-TYPE
			SYNTAX	INTEGER
			ACCESS	read-only
			STATUS	current
	DESCRIPTION ""
			::= { mbusCE 99 }

mbusCEVIF2F		OBJECT-TYPE
			SYNTAX	INTEGER
			ACCESS	read-only
			STATUS	current
	DESCRIPTION ""
			::= { mbusCE 100 }

mbusCEValue2F		OBJECT-TYPE
			SYNTAX	INTEGER
			ACCESS	read-only
			STATUS	current
	DESCRIPTION ""
			::= { mbusCE 101 }

mbusCF			OBJECT IDENTIFIER ::= { mbus 207 }

mbusCFIdNumber		OBJECT-TYPE
			SYNTAX	Gauge
			ACCESS	read-only
			STATUS	current
	DESCRIPTION ""
			::= { mbusCF 1 }

mbusCFManufacturer	OBJECT-TYPE
			SYNTAX	Gauge
			ACCESS	read-only
			STATUS	current
	DESCRIPTION ""
			::= { mbusCF 2 }

mbusCFVersion		OBJECT-TYPE
			SYNTAX	Gauge
			ACCESS	read-only
			STATUS	current
	DESCRIPTION ""
			::= { mbusCF 3 }

mbusCFMedium		OBJECT-TYPE
			SYNTAX	Gauge
			ACCESS	read-only
			STATUS	current
	DESCRIPTION ""
			::= { mbusCF 4 }

mbusCFStatus		OBJECT-TYPE
			SYNTAX	Gauge
			ACCESS	read-only
			STATUS	current
	DESCRIPTION ""
			::= { mbusCF 5 }

mbusCFVIF00		OBJECT-TYPE
			SYNTAX	INTEGER
			ACCESS	read-only
			STATUS	current
	DESCRIPTION ""
			::= { mbusCF 6 }

mbusCFValue00		OBJECT-TYPE
			SYNTAX	INTEGER
			ACCESS	read-only
			STATUS	current
	DESCRIPTION ""
			::= { mbusCF 7 }

mbusCFVIF01		OBJECT-TYPE
			SYNTAX	INTEGER
			ACCESS	read-only
			STATUS	current
	DESCRIPTION ""
			::= { mbusCF 8 }

mbusCFValue01		OBJECT-TYPE
			SYNTAX	INTEGER
			ACCESS	read-only
			STATUS	current
	DESCRIPTION ""
			::= { mbusCF 9 }

mbusCFVIF02		OBJECT-TYPE
			SYNTAX	INTEGER
			ACCESS	read-only
			STATUS	current
	DESCRIPTION ""
			::= { mbusCF 10 }

mbusCFValue02		OBJECT-TYPE
			SYNTAX	INTEGER
			ACCESS	read-only
			STATUS	current
	DESCRIPTION ""
			::= { mbusCF 11 }

mbusCFVIF03		OBJECT-TYPE
			SYNTAX	INTEGER
			ACCESS	read-only
			STATUS	current
	DESCRIPTION ""
			::= { mbusCF 12 }

mbusCFValue03		OBJECT-TYPE
			SYNTAX	INTEGER
			ACCESS	read-only
			STATUS	current
	DESCRIPTION ""
			::= { mbusCF 13 }

mbusCFVIF04		OBJECT-TYPE
			SYNTAX	INTEGER
			ACCESS	read-only
			STATUS	current
	DESCRIPTION ""
			::= { mbusCF 14 }

mbusCFValue04		OBJECT-TYPE
			SYNTAX	INTEGER
			ACCESS	read-only
			STATUS	current
	DESCRIPTION ""
			::= { mbusCF 15 }

mbusCFVIF05		OBJECT-TYPE
			SYNTAX	INTEGER
			ACCESS	read-only
			STATUS	current
	DESCRIPTION ""
			::= { mbusCF 16 }

mbusCFValue05		OBJECT-TYPE
			SYNTAX	INTEGER
			ACCESS	read-only
			STATUS	current
	DESCRIPTION ""
			::= { mbusCF 17 }

mbusCFVIF06		OBJECT-TYPE
			SYNTAX	INTEGER
			ACCESS	read-only
			STATUS	current
	DESCRIPTION ""
			::= { mbusCF 18 }

mbusCFValue06		OBJECT-TYPE
			SYNTAX	INTEGER
			ACCESS	read-only
			STATUS	current
	DESCRIPTION ""
			::= { mbusCF 19 }

mbusCFVIF07		OBJECT-TYPE
			SYNTAX	INTEGER
			ACCESS	read-only
			STATUS	current
	DESCRIPTION ""
			::= { mbusCF 20 }

mbusCFValue07		OBJECT-TYPE
			SYNTAX	INTEGER
			ACCESS	read-only
			STATUS	current
	DESCRIPTION ""
			::= { mbusCF 21 }

mbusCFVIF08		OBJECT-TYPE
			SYNTAX	INTEGER
			ACCESS	read-only
			STATUS	current
	DESCRIPTION ""
			::= { mbusCF 22 }

mbusCFValue08		OBJECT-TYPE
			SYNTAX	INTEGER
			ACCESS	read-only
			STATUS	current
	DESCRIPTION ""
			::= { mbusCF 23 }

mbusCFVIF09		OBJECT-TYPE
			SYNTAX	INTEGER
			ACCESS	read-only
			STATUS	current
	DESCRIPTION ""
			::= { mbusCF 24 }

mbusCFValue09		OBJECT-TYPE
			SYNTAX	INTEGER
			ACCESS	read-only
			STATUS	current
	DESCRIPTION ""
			::= { mbusCF 25 }

mbusCFVIF0A		OBJECT-TYPE
			SYNTAX	INTEGER
			ACCESS	read-only
			STATUS	current
	DESCRIPTION ""
			::= { mbusCF 26 }

mbusCFValue0A		OBJECT-TYPE
			SYNTAX	INTEGER
			ACCESS	read-only
			STATUS	current
	DESCRIPTION ""
			::= { mbusCF 27 }

mbusCFVIF0B		OBJECT-TYPE
			SYNTAX	INTEGER
			ACCESS	read-only
			STATUS	current
	DESCRIPTION ""
			::= { mbusCF 28 }

mbusCFValue0B		OBJECT-TYPE
			SYNTAX	INTEGER
			ACCESS	read-only
			STATUS	current
	DESCRIPTION ""
			::= { mbusCF 29 }

mbusCFVIF0C		OBJECT-TYPE
			SYNTAX	INTEGER
			ACCESS	read-only
			STATUS	current
	DESCRIPTION ""
			::= { mbusCF 30 }

mbusCFValue0C		OBJECT-TYPE
			SYNTAX	INTEGER
			ACCESS	read-only
			STATUS	current
	DESCRIPTION ""
			::= { mbusCF 31 }

mbusCFVIF0D		OBJECT-TYPE
			SYNTAX	INTEGER
			ACCESS	read-only
			STATUS	current
	DESCRIPTION ""
			::= { mbusCF 32 }

mbusCFValue0D		OBJECT-TYPE
			SYNTAX	INTEGER
			ACCESS	read-only
			STATUS	current
	DESCRIPTION ""
			::= { mbusCF 33 }

mbusCFVIF0E		OBJECT-TYPE
			SYNTAX	INTEGER
			ACCESS	read-only
			STATUS	current
	DESCRIPTION ""
			::= { mbusCF 34 }

mbusCFValue0E		OBJECT-TYPE
			SYNTAX	INTEGER
			ACCESS	read-only
			STATUS	current
	DESCRIPTION ""
			::= { mbusCF 35 }

mbusCFVIF0F		OBJECT-TYPE
			SYNTAX	INTEGER
			ACCESS	read-only
			STATUS	current
	DESCRIPTION ""
			::= { mbusCF 36 }

mbusCFValue0F		OBJECT-TYPE
			SYNTAX	INTEGER
			ACCESS	read-only
			STATUS	current
	DESCRIPTION ""
			::= { mbusCF 37 }

mbusCFVIF10		OBJECT-TYPE
			SYNTAX	INTEGER
			ACCESS	read-only
			STATUS	current
	DESCRIPTION ""
			::= { mbusCF 38 }

mbusCFValue10		OBJECT-TYPE
			SYNTAX	INTEGER
			ACCESS	read-only
			STATUS	current
	DESCRIPTION ""
			::= { mbusCF 39 }

mbusCFVIF11		OBJECT-TYPE
			SYNTAX	INTEGER
			ACCESS	read-only
			STATUS	current
	DESCRIPTION ""
			::= { mbusCF 40 }

mbusCFValue11		OBJECT-TYPE
			SYNTAX	INTEGER
			ACCESS	read-only
			STATUS	current
	DESCRIPTION ""
			::= { mbusCF 41 }

mbusCFVIF12		OBJECT-TYPE
			SYNTAX	INTEGER
			ACCESS	read-only
			STATUS	current
	DESCRIPTION ""
			::= { mbusCF 42 }

mbusCFValue12		OBJECT-TYPE
			SYNTAX	INTEGER
			ACCESS	read-only
			STATUS	current
	DESCRIPTION ""
			::= { mbusCF 43 }

mbusCFVIF13		OBJECT-TYPE
			SYNTAX	INTEGER
			ACCESS	read-only
			STATUS	current
	DESCRIPTION ""
			::= { mbusCF 44 }

mbusCFValue13		OBJECT-TYPE
			SYNTAX	INTEGER
			ACCESS	read-only
			STATUS	current
	DESCRIPTION ""
			::= { mbusCF 45 }

mbusCFVIF14		OBJECT-TYPE
			SYNTAX	INTEGER
			ACCESS	read-only
			STATUS	current
	DESCRIPTION ""
			::= { mbusCF 46 }

mbusCFValue14		OBJECT-TYPE
			SYNTAX	INTEGER
			ACCESS	read-only
			STATUS	current
	DESCRIPTION ""
			::= { mbusCF 47 }

mbusCFVIF15		OBJECT-TYPE
			SYNTAX	INTEGER
			ACCESS	read-only
			STATUS	current
	DESCRIPTION ""
			::= { mbusCF 48 }

mbusCFValue15		OBJECT-TYPE
			SYNTAX	INTEGER
			ACCESS	read-only
			STATUS	current
	DESCRIPTION ""
			::= { mbusCF 49 }

mbusCFVIF16		OBJECT-TYPE
			SYNTAX	INTEGER
			ACCESS	read-only
			STATUS	current
	DESCRIPTION ""
			::= { mbusCF 50 }

mbusCFValue16		OBJECT-TYPE
			SYNTAX	INTEGER
			ACCESS	read-only
			STATUS	current
	DESCRIPTION ""
			::= { mbusCF 51 }

mbusCFVIF17		OBJECT-TYPE
			SYNTAX	INTEGER
			ACCESS	read-only
			STATUS	current
	DESCRIPTION ""
			::= { mbusCF 52 }

mbusCFValue17		OBJECT-TYPE
			SYNTAX	INTEGER
			ACCESS	read-only
			STATUS	current
	DESCRIPTION ""
			::= { mbusCF 53 }

mbusCFVIF18		OBJECT-TYPE
			SYNTAX	INTEGER
			ACCESS	read-only
			STATUS	current
	DESCRIPTION ""
			::= { mbusCF 54 }

mbusCFValue18		OBJECT-TYPE
			SYNTAX	INTEGER
			ACCESS	read-only
			STATUS	current
	DESCRIPTION ""
			::= { mbusCF 55 }

mbusCFVIF19		OBJECT-TYPE
			SYNTAX	INTEGER
			ACCESS	read-only
			STATUS	current
	DESCRIPTION ""
			::= { mbusCF 56 }

mbusCFValue19		OBJECT-TYPE
			SYNTAX	INTEGER
			ACCESS	read-only
			STATUS	current
	DESCRIPTION ""
			::= { mbusCF 57 }

mbusCFVIF1A		OBJECT-TYPE
			SYNTAX	INTEGER
			ACCESS	read-only
			STATUS	current
	DESCRIPTION ""
			::= { mbusCF 58 }

mbusCFValue1A		OBJECT-TYPE
			SYNTAX	INTEGER
			ACCESS	read-only
			STATUS	current
	DESCRIPTION ""
			::= { mbusCF 59 }

mbusCFVIF1B		OBJECT-TYPE
			SYNTAX	INTEGER
			ACCESS	read-only
			STATUS	current
	DESCRIPTION ""
			::= { mbusCF 60 }

mbusCFValue1B		OBJECT-TYPE
			SYNTAX	INTEGER
			ACCESS	read-only
			STATUS	current
	DESCRIPTION ""
			::= { mbusCF 61 }

mbusCFVIF1C		OBJECT-TYPE
			SYNTAX	INTEGER
			ACCESS	read-only
			STATUS	current
	DESCRIPTION ""
			::= { mbusCF 62 }

mbusCFValue1C		OBJECT-TYPE
			SYNTAX	INTEGER
			ACCESS	read-only
			STATUS	current
	DESCRIPTION ""
			::= { mbusCF 63 }

mbusCFVIF1D		OBJECT-TYPE
			SYNTAX	INTEGER
			ACCESS	read-only
			STATUS	current
	DESCRIPTION ""
			::= { mbusCF 64 }

mbusCFValue1D		OBJECT-TYPE
			SYNTAX	INTEGER
			ACCESS	read-only
			STATUS	current
	DESCRIPTION ""
			::= { mbusCF 65 }

mbusCFVIF1E		OBJECT-TYPE
			SYNTAX	INTEGER
			ACCESS	read-only
			STATUS	current
	DESCRIPTION ""
			::= { mbusCF 66 }

mbusCFValue1E		OBJECT-TYPE
			SYNTAX	INTEGER
			ACCESS	read-only
			STATUS	current
	DESCRIPTION ""
			::= { mbusCF 67 }

mbusCFVIF1F		OBJECT-TYPE
			SYNTAX	INTEGER
			ACCESS	read-only
			STATUS	current
	DESCRIPTION ""
			::= { mbusCF 68 }

mbusCFValue1F		OBJECT-TYPE
			SYNTAX	INTEGER
			ACCESS	read-only
			STATUS	current
	DESCRIPTION ""
			::= { mbusCF 69 }

mbusCFVIF20		OBJECT-TYPE
			SYNTAX	INTEGER
			ACCESS	read-only
			STATUS	current
	DESCRIPTION ""
			::= { mbusCF 70 }

mbusCFValue20		OBJECT-TYPE
			SYNTAX	INTEGER
			ACCESS	read-only
			STATUS	current
	DESCRIPTION ""
			::= { mbusCF 71 }

mbusCFVIF21		OBJECT-TYPE
			SYNTAX	INTEGER
			ACCESS	read-only
			STATUS	current
	DESCRIPTION ""
			::= { mbusCF 72 }

mbusCFValue21		OBJECT-TYPE
			SYNTAX	INTEGER
			ACCESS	read-only
			STATUS	current
	DESCRIPTION ""
			::= { mbusCF 73 }

mbusCFVIF22		OBJECT-TYPE
			SYNTAX	INTEGER
			ACCESS	read-only
			STATUS	current
	DESCRIPTION ""
			::= { mbusCF 74 }

mbusCFValue22		OBJECT-TYPE
			SYNTAX	INTEGER
			ACCESS	read-only
			STATUS	current
	DESCRIPTION ""
			::= { mbusCF 75 }

mbusCFVIF23		OBJECT-TYPE
			SYNTAX	INTEGER
			ACCESS	read-only
			STATUS	current
	DESCRIPTION ""
			::= { mbusCF 76 }

mbusCFValue23		OBJECT-TYPE
			SYNTAX	INTEGER
			ACCESS	read-only
			STATUS	current
	DESCRIPTION ""
			::= { mbusCF 77 }

mbusCFVIF24		OBJECT-TYPE
			SYNTAX	INTEGER
			ACCESS	read-only
			STATUS	current
	DESCRIPTION ""
			::= { mbusCF 78 }

mbusCFValue24		OBJECT-TYPE
			SYNTAX	INTEGER
			ACCESS	read-only
			STATUS	current
	DESCRIPTION ""
			::= { mbusCF 79 }

mbusCFVIF25		OBJECT-TYPE
			SYNTAX	INTEGER
			ACCESS	read-only
			STATUS	current
	DESCRIPTION ""
			::= { mbusCF 80 }

mbusCFValue25		OBJECT-TYPE
			SYNTAX	INTEGER
			ACCESS	read-only
			STATUS	current
	DESCRIPTION ""
			::= { mbusCF 81 }

mbusCFVIF26		OBJECT-TYPE
			SYNTAX	INTEGER
			ACCESS	read-only
			STATUS	current
	DESCRIPTION ""
			::= { mbusCF 82 }

mbusCFValue26		OBJECT-TYPE
			SYNTAX	INTEGER
			ACCESS	read-only
			STATUS	current
	DESCRIPTION ""
			::= { mbusCF 83 }

mbusCFVIF27		OBJECT-TYPE
			SYNTAX	INTEGER
			ACCESS	read-only
			STATUS	current
	DESCRIPTION ""
			::= { mbusCF 84 }

mbusCFValue27		OBJECT-TYPE
			SYNTAX	INTEGER
			ACCESS	read-only
			STATUS	current
	DESCRIPTION ""
			::= { mbusCF 85 }

mbusCFVIF28		OBJECT-TYPE
			SYNTAX	INTEGER
			ACCESS	read-only
			STATUS	current
	DESCRIPTION ""
			::= { mbusCF 86 }

mbusCFValue28		OBJECT-TYPE
			SYNTAX	INTEGER
			ACCESS	read-only
			STATUS	current
	DESCRIPTION ""
			::= { mbusCF 87 }

mbusCFVIF29		OBJECT-TYPE
			SYNTAX	INTEGER
			ACCESS	read-only
			STATUS	current
	DESCRIPTION ""
			::= { mbusCF 88 }

mbusCFValue29		OBJECT-TYPE
			SYNTAX	INTEGER
			ACCESS	read-only
			STATUS	current
	DESCRIPTION ""
			::= { mbusCF 89 }

mbusCFVIF2A		OBJECT-TYPE
			SYNTAX	INTEGER
			ACCESS	read-only
			STATUS	current
	DESCRIPTION ""
			::= { mbusCF 90 }

mbusCFValue2A		OBJECT-TYPE
			SYNTAX	INTEGER
			ACCESS	read-only
			STATUS	current
	DESCRIPTION ""
			::= { mbusCF 91 }

mbusCFVIF2B		OBJECT-TYPE
			SYNTAX	INTEGER
			ACCESS	read-only
			STATUS	current
	DESCRIPTION ""
			::= { mbusCF 92 }

mbusCFValue2B		OBJECT-TYPE
			SYNTAX	INTEGER
			ACCESS	read-only
			STATUS	current
	DESCRIPTION ""
			::= { mbusCF 93 }

mbusCFVIF2C		OBJECT-TYPE
			SYNTAX	INTEGER
			ACCESS	read-only
			STATUS	current
	DESCRIPTION ""
			::= { mbusCF 94 }

mbusCFValue2C		OBJECT-TYPE
			SYNTAX	INTEGER
			ACCESS	read-only
			STATUS	current
	DESCRIPTION ""
			::= { mbusCF 95 }

mbusCFVIF2D		OBJECT-TYPE
			SYNTAX	INTEGER
			ACCESS	read-only
			STATUS	current
	DESCRIPTION ""
			::= { mbusCF 96 }

mbusCFValue2D		OBJECT-TYPE
			SYNTAX	INTEGER
			ACCESS	read-only
			STATUS	current
	DESCRIPTION ""
			::= { mbusCF 97 }

mbusCFVIF2E		OBJECT-TYPE
			SYNTAX	INTEGER
			ACCESS	read-only
			STATUS	current
	DESCRIPTION ""
			::= { mbusCF 98 }

mbusCFValue2E		OBJECT-TYPE
			SYNTAX	INTEGER
			ACCESS	read-only
			STATUS	current
	DESCRIPTION ""
			::= { mbusCF 99 }

mbusCFVIF2F		OBJECT-TYPE
			SYNTAX	INTEGER
			ACCESS	read-only
			STATUS	current
	DESCRIPTION ""
			::= { mbusCF 100 }

mbusCFValue2F		OBJECT-TYPE
			SYNTAX	INTEGER
			ACCESS	read-only
			STATUS	current
	DESCRIPTION ""
			::= { mbusCF 101 }

mbusD0			OBJECT IDENTIFIER ::= { mbus 208 }

mbusD0IdNumber		OBJECT-TYPE
			SYNTAX	Gauge
			ACCESS	read-only
			STATUS	current
	DESCRIPTION ""
			::= { mbusD0 1 }

mbusD0Manufacturer	OBJECT-TYPE
			SYNTAX	Gauge
			ACCESS	read-only
			STATUS	current
	DESCRIPTION ""
			::= { mbusD0 2 }

mbusD0Version		OBJECT-TYPE
			SYNTAX	Gauge
			ACCESS	read-only
			STATUS	current
	DESCRIPTION ""
			::= { mbusD0 3 }

mbusD0Medium		OBJECT-TYPE
			SYNTAX	Gauge
			ACCESS	read-only
			STATUS	current
	DESCRIPTION ""
			::= { mbusD0 4 }

mbusD0Status		OBJECT-TYPE
			SYNTAX	Gauge
			ACCESS	read-only
			STATUS	current
	DESCRIPTION ""
			::= { mbusD0 5 }

mbusD0VIF00		OBJECT-TYPE
			SYNTAX	INTEGER
			ACCESS	read-only
			STATUS	current
	DESCRIPTION ""
			::= { mbusD0 6 }

mbusD0Value00		OBJECT-TYPE
			SYNTAX	INTEGER
			ACCESS	read-only
			STATUS	current
	DESCRIPTION ""
			::= { mbusD0 7 }

mbusD0VIF01		OBJECT-TYPE
			SYNTAX	INTEGER
			ACCESS	read-only
			STATUS	current
	DESCRIPTION ""
			::= { mbusD0 8 }

mbusD0Value01		OBJECT-TYPE
			SYNTAX	INTEGER
			ACCESS	read-only
			STATUS	current
	DESCRIPTION ""
			::= { mbusD0 9 }

mbusD0VIF02		OBJECT-TYPE
			SYNTAX	INTEGER
			ACCESS	read-only
			STATUS	current
	DESCRIPTION ""
			::= { mbusD0 10 }

mbusD0Value02		OBJECT-TYPE
			SYNTAX	INTEGER
			ACCESS	read-only
			STATUS	current
	DESCRIPTION ""
			::= { mbusD0 11 }

mbusD0VIF03		OBJECT-TYPE
			SYNTAX	INTEGER
			ACCESS	read-only
			STATUS	current
	DESCRIPTION ""
			::= { mbusD0 12 }

mbusD0Value03		OBJECT-TYPE
			SYNTAX	INTEGER
			ACCESS	read-only
			STATUS	current
	DESCRIPTION ""
			::= { mbusD0 13 }

mbusD0VIF04		OBJECT-TYPE
			SYNTAX	INTEGER
			ACCESS	read-only
			STATUS	current
	DESCRIPTION ""
			::= { mbusD0 14 }

mbusD0Value04		OBJECT-TYPE
			SYNTAX	INTEGER
			ACCESS	read-only
			STATUS	current
	DESCRIPTION ""
			::= { mbusD0 15 }

mbusD0VIF05		OBJECT-TYPE
			SYNTAX	INTEGER
			ACCESS	read-only
			STATUS	current
	DESCRIPTION ""
			::= { mbusD0 16 }

mbusD0Value05		OBJECT-TYPE
			SYNTAX	INTEGER
			ACCESS	read-only
			STATUS	current
	DESCRIPTION ""
			::= { mbusD0 17 }

mbusD0VIF06		OBJECT-TYPE
			SYNTAX	INTEGER
			ACCESS	read-only
			STATUS	current
	DESCRIPTION ""
			::= { mbusD0 18 }

mbusD0Value06		OBJECT-TYPE
			SYNTAX	INTEGER
			ACCESS	read-only
			STATUS	current
	DESCRIPTION ""
			::= { mbusD0 19 }

mbusD0VIF07		OBJECT-TYPE
			SYNTAX	INTEGER
			ACCESS	read-only
			STATUS	current
	DESCRIPTION ""
			::= { mbusD0 20 }

mbusD0Value07		OBJECT-TYPE
			SYNTAX	INTEGER
			ACCESS	read-only
			STATUS	current
	DESCRIPTION ""
			::= { mbusD0 21 }

mbusD0VIF08		OBJECT-TYPE
			SYNTAX	INTEGER
			ACCESS	read-only
			STATUS	current
	DESCRIPTION ""
			::= { mbusD0 22 }

mbusD0Value08		OBJECT-TYPE
			SYNTAX	INTEGER
			ACCESS	read-only
			STATUS	current
	DESCRIPTION ""
			::= { mbusD0 23 }

mbusD0VIF09		OBJECT-TYPE
			SYNTAX	INTEGER
			ACCESS	read-only
			STATUS	current
	DESCRIPTION ""
			::= { mbusD0 24 }

mbusD0Value09		OBJECT-TYPE
			SYNTAX	INTEGER
			ACCESS	read-only
			STATUS	current
	DESCRIPTION ""
			::= { mbusD0 25 }

mbusD0VIF0A		OBJECT-TYPE
			SYNTAX	INTEGER
			ACCESS	read-only
			STATUS	current
	DESCRIPTION ""
			::= { mbusD0 26 }

mbusD0Value0A		OBJECT-TYPE
			SYNTAX	INTEGER
			ACCESS	read-only
			STATUS	current
	DESCRIPTION ""
			::= { mbusD0 27 }

mbusD0VIF0B		OBJECT-TYPE
			SYNTAX	INTEGER
			ACCESS	read-only
			STATUS	current
	DESCRIPTION ""
			::= { mbusD0 28 }

mbusD0Value0B		OBJECT-TYPE
			SYNTAX	INTEGER
			ACCESS	read-only
			STATUS	current
	DESCRIPTION ""
			::= { mbusD0 29 }

mbusD0VIF0C		OBJECT-TYPE
			SYNTAX	INTEGER
			ACCESS	read-only
			STATUS	current
	DESCRIPTION ""
			::= { mbusD0 30 }

mbusD0Value0C		OBJECT-TYPE
			SYNTAX	INTEGER
			ACCESS	read-only
			STATUS	current
	DESCRIPTION ""
			::= { mbusD0 31 }

mbusD0VIF0D		OBJECT-TYPE
			SYNTAX	INTEGER
			ACCESS	read-only
			STATUS	current
	DESCRIPTION ""
			::= { mbusD0 32 }

mbusD0Value0D		OBJECT-TYPE
			SYNTAX	INTEGER
			ACCESS	read-only
			STATUS	current
	DESCRIPTION ""
			::= { mbusD0 33 }

mbusD0VIF0E		OBJECT-TYPE
			SYNTAX	INTEGER
			ACCESS	read-only
			STATUS	current
	DESCRIPTION ""
			::= { mbusD0 34 }

mbusD0Value0E		OBJECT-TYPE
			SYNTAX	INTEGER
			ACCESS	read-only
			STATUS	current
	DESCRIPTION ""
			::= { mbusD0 35 }

mbusD0VIF0F		OBJECT-TYPE
			SYNTAX	INTEGER
			ACCESS	read-only
			STATUS	current
	DESCRIPTION ""
			::= { mbusD0 36 }

mbusD0Value0F		OBJECT-TYPE
			SYNTAX	INTEGER
			ACCESS	read-only
			STATUS	current
	DESCRIPTION ""
			::= { mbusD0 37 }

mbusD0VIF10		OBJECT-TYPE
			SYNTAX	INTEGER
			ACCESS	read-only
			STATUS	current
	DESCRIPTION ""
			::= { mbusD0 38 }

mbusD0Value10		OBJECT-TYPE
			SYNTAX	INTEGER
			ACCESS	read-only
			STATUS	current
	DESCRIPTION ""
			::= { mbusD0 39 }

mbusD0VIF11		OBJECT-TYPE
			SYNTAX	INTEGER
			ACCESS	read-only
			STATUS	current
	DESCRIPTION ""
			::= { mbusD0 40 }

mbusD0Value11		OBJECT-TYPE
			SYNTAX	INTEGER
			ACCESS	read-only
			STATUS	current
	DESCRIPTION ""
			::= { mbusD0 41 }

mbusD0VIF12		OBJECT-TYPE
			SYNTAX	INTEGER
			ACCESS	read-only
			STATUS	current
	DESCRIPTION ""
			::= { mbusD0 42 }

mbusD0Value12		OBJECT-TYPE
			SYNTAX	INTEGER
			ACCESS	read-only
			STATUS	current
	DESCRIPTION ""
			::= { mbusD0 43 }

mbusD0VIF13		OBJECT-TYPE
			SYNTAX	INTEGER
			ACCESS	read-only
			STATUS	current
	DESCRIPTION ""
			::= { mbusD0 44 }

mbusD0Value13		OBJECT-TYPE
			SYNTAX	INTEGER
			ACCESS	read-only
			STATUS	current
	DESCRIPTION ""
			::= { mbusD0 45 }

mbusD0VIF14		OBJECT-TYPE
			SYNTAX	INTEGER
			ACCESS	read-only
			STATUS	current
	DESCRIPTION ""
			::= { mbusD0 46 }

mbusD0Value14		OBJECT-TYPE
			SYNTAX	INTEGER
			ACCESS	read-only
			STATUS	current
	DESCRIPTION ""
			::= { mbusD0 47 }

mbusD0VIF15		OBJECT-TYPE
			SYNTAX	INTEGER
			ACCESS	read-only
			STATUS	current
	DESCRIPTION ""
			::= { mbusD0 48 }

mbusD0Value15		OBJECT-TYPE
			SYNTAX	INTEGER
			ACCESS	read-only
			STATUS	current
	DESCRIPTION ""
			::= { mbusD0 49 }

mbusD0VIF16		OBJECT-TYPE
			SYNTAX	INTEGER
			ACCESS	read-only
			STATUS	current
	DESCRIPTION ""
			::= { mbusD0 50 }

mbusD0Value16		OBJECT-TYPE
			SYNTAX	INTEGER
			ACCESS	read-only
			STATUS	current
	DESCRIPTION ""
			::= { mbusD0 51 }

mbusD0VIF17		OBJECT-TYPE
			SYNTAX	INTEGER
			ACCESS	read-only
			STATUS	current
	DESCRIPTION ""
			::= { mbusD0 52 }

mbusD0Value17		OBJECT-TYPE
			SYNTAX	INTEGER
			ACCESS	read-only
			STATUS	current
	DESCRIPTION ""
			::= { mbusD0 53 }

mbusD0VIF18		OBJECT-TYPE
			SYNTAX	INTEGER
			ACCESS	read-only
			STATUS	current
	DESCRIPTION ""
			::= { mbusD0 54 }

mbusD0Value18		OBJECT-TYPE
			SYNTAX	INTEGER
			ACCESS	read-only
			STATUS	current
	DESCRIPTION ""
			::= { mbusD0 55 }

mbusD0VIF19		OBJECT-TYPE
			SYNTAX	INTEGER
			ACCESS	read-only
			STATUS	current
	DESCRIPTION ""
			::= { mbusD0 56 }

mbusD0Value19		OBJECT-TYPE
			SYNTAX	INTEGER
			ACCESS	read-only
			STATUS	current
	DESCRIPTION ""
			::= { mbusD0 57 }

mbusD0VIF1A		OBJECT-TYPE
			SYNTAX	INTEGER
			ACCESS	read-only
			STATUS	current
	DESCRIPTION ""
			::= { mbusD0 58 }

mbusD0Value1A		OBJECT-TYPE
			SYNTAX	INTEGER
			ACCESS	read-only
			STATUS	current
	DESCRIPTION ""
			::= { mbusD0 59 }

mbusD0VIF1B		OBJECT-TYPE
			SYNTAX	INTEGER
			ACCESS	read-only
			STATUS	current
	DESCRIPTION ""
			::= { mbusD0 60 }

mbusD0Value1B		OBJECT-TYPE
			SYNTAX	INTEGER
			ACCESS	read-only
			STATUS	current
	DESCRIPTION ""
			::= { mbusD0 61 }

mbusD0VIF1C		OBJECT-TYPE
			SYNTAX	INTEGER
			ACCESS	read-only
			STATUS	current
	DESCRIPTION ""
			::= { mbusD0 62 }

mbusD0Value1C		OBJECT-TYPE
			SYNTAX	INTEGER
			ACCESS	read-only
			STATUS	current
	DESCRIPTION ""
			::= { mbusD0 63 }

mbusD0VIF1D		OBJECT-TYPE
			SYNTAX	INTEGER
			ACCESS	read-only
			STATUS	current
	DESCRIPTION ""
			::= { mbusD0 64 }

mbusD0Value1D		OBJECT-TYPE
			SYNTAX	INTEGER
			ACCESS	read-only
			STATUS	current
	DESCRIPTION ""
			::= { mbusD0 65 }

mbusD0VIF1E		OBJECT-TYPE
			SYNTAX	INTEGER
			ACCESS	read-only
			STATUS	current
	DESCRIPTION ""
			::= { mbusD0 66 }

mbusD0Value1E		OBJECT-TYPE
			SYNTAX	INTEGER
			ACCESS	read-only
			STATUS	current
	DESCRIPTION ""
			::= { mbusD0 67 }

mbusD0VIF1F		OBJECT-TYPE
			SYNTAX	INTEGER
			ACCESS	read-only
			STATUS	current
	DESCRIPTION ""
			::= { mbusD0 68 }

mbusD0Value1F		OBJECT-TYPE
			SYNTAX	INTEGER
			ACCESS	read-only
			STATUS	current
	DESCRIPTION ""
			::= { mbusD0 69 }

mbusD0VIF20		OBJECT-TYPE
			SYNTAX	INTEGER
			ACCESS	read-only
			STATUS	current
	DESCRIPTION ""
			::= { mbusD0 70 }

mbusD0Value20		OBJECT-TYPE
			SYNTAX	INTEGER
			ACCESS	read-only
			STATUS	current
	DESCRIPTION ""
			::= { mbusD0 71 }

mbusD0VIF21		OBJECT-TYPE
			SYNTAX	INTEGER
			ACCESS	read-only
			STATUS	current
	DESCRIPTION ""
			::= { mbusD0 72 }

mbusD0Value21		OBJECT-TYPE
			SYNTAX	INTEGER
			ACCESS	read-only
			STATUS	current
	DESCRIPTION ""
			::= { mbusD0 73 }

mbusD0VIF22		OBJECT-TYPE
			SYNTAX	INTEGER
			ACCESS	read-only
			STATUS	current
	DESCRIPTION ""
			::= { mbusD0 74 }

mbusD0Value22		OBJECT-TYPE
			SYNTAX	INTEGER
			ACCESS	read-only
			STATUS	current
	DESCRIPTION ""
			::= { mbusD0 75 }

mbusD0VIF23		OBJECT-TYPE
			SYNTAX	INTEGER
			ACCESS	read-only
			STATUS	current
	DESCRIPTION ""
			::= { mbusD0 76 }

mbusD0Value23		OBJECT-TYPE
			SYNTAX	INTEGER
			ACCESS	read-only
			STATUS	current
	DESCRIPTION ""
			::= { mbusD0 77 }

mbusD0VIF24		OBJECT-TYPE
			SYNTAX	INTEGER
			ACCESS	read-only
			STATUS	current
	DESCRIPTION ""
			::= { mbusD0 78 }

mbusD0Value24		OBJECT-TYPE
			SYNTAX	INTEGER
			ACCESS	read-only
			STATUS	current
	DESCRIPTION ""
			::= { mbusD0 79 }

mbusD0VIF25		OBJECT-TYPE
			SYNTAX	INTEGER
			ACCESS	read-only
			STATUS	current
	DESCRIPTION ""
			::= { mbusD0 80 }

mbusD0Value25		OBJECT-TYPE
			SYNTAX	INTEGER
			ACCESS	read-only
			STATUS	current
	DESCRIPTION ""
			::= { mbusD0 81 }

mbusD0VIF26		OBJECT-TYPE
			SYNTAX	INTEGER
			ACCESS	read-only
			STATUS	current
	DESCRIPTION ""
			::= { mbusD0 82 }

mbusD0Value26		OBJECT-TYPE
			SYNTAX	INTEGER
			ACCESS	read-only
			STATUS	current
	DESCRIPTION ""
			::= { mbusD0 83 }

mbusD0VIF27		OBJECT-TYPE
			SYNTAX	INTEGER
			ACCESS	read-only
			STATUS	current
	DESCRIPTION ""
			::= { mbusD0 84 }

mbusD0Value27		OBJECT-TYPE
			SYNTAX	INTEGER
			ACCESS	read-only
			STATUS	current
	DESCRIPTION ""
			::= { mbusD0 85 }

mbusD0VIF28		OBJECT-TYPE
			SYNTAX	INTEGER
			ACCESS	read-only
			STATUS	current
	DESCRIPTION ""
			::= { mbusD0 86 }

mbusD0Value28		OBJECT-TYPE
			SYNTAX	INTEGER
			ACCESS	read-only
			STATUS	current
	DESCRIPTION ""
			::= { mbusD0 87 }

mbusD0VIF29		OBJECT-TYPE
			SYNTAX	INTEGER
			ACCESS	read-only
			STATUS	current
	DESCRIPTION ""
			::= { mbusD0 88 }

mbusD0Value29		OBJECT-TYPE
			SYNTAX	INTEGER
			ACCESS	read-only
			STATUS	current
	DESCRIPTION ""
			::= { mbusD0 89 }

mbusD0VIF2A		OBJECT-TYPE
			SYNTAX	INTEGER
			ACCESS	read-only
			STATUS	current
	DESCRIPTION ""
			::= { mbusD0 90 }

mbusD0Value2A		OBJECT-TYPE
			SYNTAX	INTEGER
			ACCESS	read-only
			STATUS	current
	DESCRIPTION ""
			::= { mbusD0 91 }

mbusD0VIF2B		OBJECT-TYPE
			SYNTAX	INTEGER
			ACCESS	read-only
			STATUS	current
	DESCRIPTION ""
			::= { mbusD0 92 }

mbusD0Value2B		OBJECT-TYPE
			SYNTAX	INTEGER
			ACCESS	read-only
			STATUS	current
	DESCRIPTION ""
			::= { mbusD0 93 }

mbusD0VIF2C		OBJECT-TYPE
			SYNTAX	INTEGER
			ACCESS	read-only
			STATUS	current
	DESCRIPTION ""
			::= { mbusD0 94 }

mbusD0Value2C		OBJECT-TYPE
			SYNTAX	INTEGER
			ACCESS	read-only
			STATUS	current
	DESCRIPTION ""
			::= { mbusD0 95 }

mbusD0VIF2D		OBJECT-TYPE
			SYNTAX	INTEGER
			ACCESS	read-only
			STATUS	current
	DESCRIPTION ""
			::= { mbusD0 96 }

mbusD0Value2D		OBJECT-TYPE
			SYNTAX	INTEGER
			ACCESS	read-only
			STATUS	current
	DESCRIPTION ""
			::= { mbusD0 97 }

mbusD0VIF2E		OBJECT-TYPE
			SYNTAX	INTEGER
			ACCESS	read-only
			STATUS	current
	DESCRIPTION ""
			::= { mbusD0 98 }

mbusD0Value2E		OBJECT-TYPE
			SYNTAX	INTEGER
			ACCESS	read-only
			STATUS	current
	DESCRIPTION ""
			::= { mbusD0 99 }

mbusD0VIF2F		OBJECT-TYPE
			SYNTAX	INTEGER
			ACCESS	read-only
			STATUS	current
	DESCRIPTION ""
			::= { mbusD0 100 }

mbusD0Value2F		OBJECT-TYPE
			SYNTAX	INTEGER
			ACCESS	read-only
			STATUS	current
	DESCRIPTION ""
			::= { mbusD0 101 }

mbusD1			OBJECT IDENTIFIER ::= { mbus 209 }

mbusD1IdNumber		OBJECT-TYPE
			SYNTAX	Gauge
			ACCESS	read-only
			STATUS	current
	DESCRIPTION ""
			::= { mbusD1 1 }

mbusD1Manufacturer	OBJECT-TYPE
			SYNTAX	Gauge
			ACCESS	read-only
			STATUS	current
	DESCRIPTION ""
			::= { mbusD1 2 }

mbusD1Version		OBJECT-TYPE
			SYNTAX	Gauge
			ACCESS	read-only
			STATUS	current
	DESCRIPTION ""
			::= { mbusD1 3 }

mbusD1Medium		OBJECT-TYPE
			SYNTAX	Gauge
			ACCESS	read-only
			STATUS	current
	DESCRIPTION ""
			::= { mbusD1 4 }

mbusD1Status		OBJECT-TYPE
			SYNTAX	Gauge
			ACCESS	read-only
			STATUS	current
	DESCRIPTION ""
			::= { mbusD1 5 }

mbusD1VIF00		OBJECT-TYPE
			SYNTAX	INTEGER
			ACCESS	read-only
			STATUS	current
	DESCRIPTION ""
			::= { mbusD1 6 }

mbusD1Value00		OBJECT-TYPE
			SYNTAX	INTEGER
			ACCESS	read-only
			STATUS	current
	DESCRIPTION ""
			::= { mbusD1 7 }

mbusD1VIF01		OBJECT-TYPE
			SYNTAX	INTEGER
			ACCESS	read-only
			STATUS	current
	DESCRIPTION ""
			::= { mbusD1 8 }

mbusD1Value01		OBJECT-TYPE
			SYNTAX	INTEGER
			ACCESS	read-only
			STATUS	current
	DESCRIPTION ""
			::= { mbusD1 9 }

mbusD1VIF02		OBJECT-TYPE
			SYNTAX	INTEGER
			ACCESS	read-only
			STATUS	current
	DESCRIPTION ""
			::= { mbusD1 10 }

mbusD1Value02		OBJECT-TYPE
			SYNTAX	INTEGER
			ACCESS	read-only
			STATUS	current
	DESCRIPTION ""
			::= { mbusD1 11 }

mbusD1VIF03		OBJECT-TYPE
			SYNTAX	INTEGER
			ACCESS	read-only
			STATUS	current
	DESCRIPTION ""
			::= { mbusD1 12 }

mbusD1Value03		OBJECT-TYPE
			SYNTAX	INTEGER
			ACCESS	read-only
			STATUS	current
	DESCRIPTION ""
			::= { mbusD1 13 }

mbusD1VIF04		OBJECT-TYPE
			SYNTAX	INTEGER
			ACCESS	read-only
			STATUS	current
	DESCRIPTION ""
			::= { mbusD1 14 }

mbusD1Value04		OBJECT-TYPE
			SYNTAX	INTEGER
			ACCESS	read-only
			STATUS	current
	DESCRIPTION ""
			::= { mbusD1 15 }

mbusD1VIF05		OBJECT-TYPE
			SYNTAX	INTEGER
			ACCESS	read-only
			STATUS	current
	DESCRIPTION ""
			::= { mbusD1 16 }

mbusD1Value05		OBJECT-TYPE
			SYNTAX	INTEGER
			ACCESS	read-only
			STATUS	current
	DESCRIPTION ""
			::= { mbusD1 17 }

mbusD1VIF06		OBJECT-TYPE
			SYNTAX	INTEGER
			ACCESS	read-only
			STATUS	current
	DESCRIPTION ""
			::= { mbusD1 18 }

mbusD1Value06		OBJECT-TYPE
			SYNTAX	INTEGER
			ACCESS	read-only
			STATUS	current
	DESCRIPTION ""
			::= { mbusD1 19 }

mbusD1VIF07		OBJECT-TYPE
			SYNTAX	INTEGER
			ACCESS	read-only
			STATUS	current
	DESCRIPTION ""
			::= { mbusD1 20 }

mbusD1Value07		OBJECT-TYPE
			SYNTAX	INTEGER
			ACCESS	read-only
			STATUS	current
	DESCRIPTION ""
			::= { mbusD1 21 }

mbusD1VIF08		OBJECT-TYPE
			SYNTAX	INTEGER
			ACCESS	read-only
			STATUS	current
	DESCRIPTION ""
			::= { mbusD1 22 }

mbusD1Value08		OBJECT-TYPE
			SYNTAX	INTEGER
			ACCESS	read-only
			STATUS	current
	DESCRIPTION ""
			::= { mbusD1 23 }

mbusD1VIF09		OBJECT-TYPE
			SYNTAX	INTEGER
			ACCESS	read-only
			STATUS	current
	DESCRIPTION ""
			::= { mbusD1 24 }

mbusD1Value09		OBJECT-TYPE
			SYNTAX	INTEGER
			ACCESS	read-only
			STATUS	current
	DESCRIPTION ""
			::= { mbusD1 25 }

mbusD1VIF0A		OBJECT-TYPE
			SYNTAX	INTEGER
			ACCESS	read-only
			STATUS	current
	DESCRIPTION ""
			::= { mbusD1 26 }

mbusD1Value0A		OBJECT-TYPE
			SYNTAX	INTEGER
			ACCESS	read-only
			STATUS	current
	DESCRIPTION ""
			::= { mbusD1 27 }

mbusD1VIF0B		OBJECT-TYPE
			SYNTAX	INTEGER
			ACCESS	read-only
			STATUS	current
	DESCRIPTION ""
			::= { mbusD1 28 }

mbusD1Value0B		OBJECT-TYPE
			SYNTAX	INTEGER
			ACCESS	read-only
			STATUS	current
	DESCRIPTION ""
			::= { mbusD1 29 }

mbusD1VIF0C		OBJECT-TYPE
			SYNTAX	INTEGER
			ACCESS	read-only
			STATUS	current
	DESCRIPTION ""
			::= { mbusD1 30 }

mbusD1Value0C		OBJECT-TYPE
			SYNTAX	INTEGER
			ACCESS	read-only
			STATUS	current
	DESCRIPTION ""
			::= { mbusD1 31 }

mbusD1VIF0D		OBJECT-TYPE
			SYNTAX	INTEGER
			ACCESS	read-only
			STATUS	current
	DESCRIPTION ""
			::= { mbusD1 32 }

mbusD1Value0D		OBJECT-TYPE
			SYNTAX	INTEGER
			ACCESS	read-only
			STATUS	current
	DESCRIPTION ""
			::= { mbusD1 33 }

mbusD1VIF0E		OBJECT-TYPE
			SYNTAX	INTEGER
			ACCESS	read-only
			STATUS	current
	DESCRIPTION ""
			::= { mbusD1 34 }

mbusD1Value0E		OBJECT-TYPE
			SYNTAX	INTEGER
			ACCESS	read-only
			STATUS	current
	DESCRIPTION ""
			::= { mbusD1 35 }

mbusD1VIF0F		OBJECT-TYPE
			SYNTAX	INTEGER
			ACCESS	read-only
			STATUS	current
	DESCRIPTION ""
			::= { mbusD1 36 }

mbusD1Value0F		OBJECT-TYPE
			SYNTAX	INTEGER
			ACCESS	read-only
			STATUS	current
	DESCRIPTION ""
			::= { mbusD1 37 }

mbusD1VIF10		OBJECT-TYPE
			SYNTAX	INTEGER
			ACCESS	read-only
			STATUS	current
	DESCRIPTION ""
			::= { mbusD1 38 }

mbusD1Value10		OBJECT-TYPE
			SYNTAX	INTEGER
			ACCESS	read-only
			STATUS	current
	DESCRIPTION ""
			::= { mbusD1 39 }

mbusD1VIF11		OBJECT-TYPE
			SYNTAX	INTEGER
			ACCESS	read-only
			STATUS	current
	DESCRIPTION ""
			::= { mbusD1 40 }

mbusD1Value11		OBJECT-TYPE
			SYNTAX	INTEGER
			ACCESS	read-only
			STATUS	current
	DESCRIPTION ""
			::= { mbusD1 41 }

mbusD1VIF12		OBJECT-TYPE
			SYNTAX	INTEGER
			ACCESS	read-only
			STATUS	current
	DESCRIPTION ""
			::= { mbusD1 42 }

mbusD1Value12		OBJECT-TYPE
			SYNTAX	INTEGER
			ACCESS	read-only
			STATUS	current
	DESCRIPTION ""
			::= { mbusD1 43 }

mbusD1VIF13		OBJECT-TYPE
			SYNTAX	INTEGER
			ACCESS	read-only
			STATUS	current
	DESCRIPTION ""
			::= { mbusD1 44 }

mbusD1Value13		OBJECT-TYPE
			SYNTAX	INTEGER
			ACCESS	read-only
			STATUS	current
	DESCRIPTION ""
			::= { mbusD1 45 }

mbusD1VIF14		OBJECT-TYPE
			SYNTAX	INTEGER
			ACCESS	read-only
			STATUS	current
	DESCRIPTION ""
			::= { mbusD1 46 }

mbusD1Value14		OBJECT-TYPE
			SYNTAX	INTEGER
			ACCESS	read-only
			STATUS	current
	DESCRIPTION ""
			::= { mbusD1 47 }

mbusD1VIF15		OBJECT-TYPE
			SYNTAX	INTEGER
			ACCESS	read-only
			STATUS	current
	DESCRIPTION ""
			::= { mbusD1 48 }

mbusD1Value15		OBJECT-TYPE
			SYNTAX	INTEGER
			ACCESS	read-only
			STATUS	current
	DESCRIPTION ""
			::= { mbusD1 49 }

mbusD1VIF16		OBJECT-TYPE
			SYNTAX	INTEGER
			ACCESS	read-only
			STATUS	current
	DESCRIPTION ""
			::= { mbusD1 50 }

mbusD1Value16		OBJECT-TYPE
			SYNTAX	INTEGER
			ACCESS	read-only
			STATUS	current
	DESCRIPTION ""
			::= { mbusD1 51 }

mbusD1VIF17		OBJECT-TYPE
			SYNTAX	INTEGER
			ACCESS	read-only
			STATUS	current
	DESCRIPTION ""
			::= { mbusD1 52 }

mbusD1Value17		OBJECT-TYPE
			SYNTAX	INTEGER
			ACCESS	read-only
			STATUS	current
	DESCRIPTION ""
			::= { mbusD1 53 }

mbusD1VIF18		OBJECT-TYPE
			SYNTAX	INTEGER
			ACCESS	read-only
			STATUS	current
	DESCRIPTION ""
			::= { mbusD1 54 }

mbusD1Value18		OBJECT-TYPE
			SYNTAX	INTEGER
			ACCESS	read-only
			STATUS	current
	DESCRIPTION ""
			::= { mbusD1 55 }

mbusD1VIF19		OBJECT-TYPE
			SYNTAX	INTEGER
			ACCESS	read-only
			STATUS	current
	DESCRIPTION ""
			::= { mbusD1 56 }

mbusD1Value19		OBJECT-TYPE
			SYNTAX	INTEGER
			ACCESS	read-only
			STATUS	current
	DESCRIPTION ""
			::= { mbusD1 57 }

mbusD1VIF1A		OBJECT-TYPE
			SYNTAX	INTEGER
			ACCESS	read-only
			STATUS	current
	DESCRIPTION ""
			::= { mbusD1 58 }

mbusD1Value1A		OBJECT-TYPE
			SYNTAX	INTEGER
			ACCESS	read-only
			STATUS	current
	DESCRIPTION ""
			::= { mbusD1 59 }

mbusD1VIF1B		OBJECT-TYPE
			SYNTAX	INTEGER
			ACCESS	read-only
			STATUS	current
	DESCRIPTION ""
			::= { mbusD1 60 }

mbusD1Value1B		OBJECT-TYPE
			SYNTAX	INTEGER
			ACCESS	read-only
			STATUS	current
	DESCRIPTION ""
			::= { mbusD1 61 }

mbusD1VIF1C		OBJECT-TYPE
			SYNTAX	INTEGER
			ACCESS	read-only
			STATUS	current
	DESCRIPTION ""
			::= { mbusD1 62 }

mbusD1Value1C		OBJECT-TYPE
			SYNTAX	INTEGER
			ACCESS	read-only
			STATUS	current
	DESCRIPTION ""
			::= { mbusD1 63 }

mbusD1VIF1D		OBJECT-TYPE
			SYNTAX	INTEGER
			ACCESS	read-only
			STATUS	current
	DESCRIPTION ""
			::= { mbusD1 64 }

mbusD1Value1D		OBJECT-TYPE
			SYNTAX	INTEGER
			ACCESS	read-only
			STATUS	current
	DESCRIPTION ""
			::= { mbusD1 65 }

mbusD1VIF1E		OBJECT-TYPE
			SYNTAX	INTEGER
			ACCESS	read-only
			STATUS	current
	DESCRIPTION ""
			::= { mbusD1 66 }

mbusD1Value1E		OBJECT-TYPE
			SYNTAX	INTEGER
			ACCESS	read-only
			STATUS	current
	DESCRIPTION ""
			::= { mbusD1 67 }

mbusD1VIF1F		OBJECT-TYPE
			SYNTAX	INTEGER
			ACCESS	read-only
			STATUS	current
	DESCRIPTION ""
			::= { mbusD1 68 }

mbusD1Value1F		OBJECT-TYPE
			SYNTAX	INTEGER
			ACCESS	read-only
			STATUS	current
	DESCRIPTION ""
			::= { mbusD1 69 }

mbusD1VIF20		OBJECT-TYPE
			SYNTAX	INTEGER
			ACCESS	read-only
			STATUS	current
	DESCRIPTION ""
			::= { mbusD1 70 }

mbusD1Value20		OBJECT-TYPE
			SYNTAX	INTEGER
			ACCESS	read-only
			STATUS	current
	DESCRIPTION ""
			::= { mbusD1 71 }

mbusD1VIF21		OBJECT-TYPE
			SYNTAX	INTEGER
			ACCESS	read-only
			STATUS	current
	DESCRIPTION ""
			::= { mbusD1 72 }

mbusD1Value21		OBJECT-TYPE
			SYNTAX	INTEGER
			ACCESS	read-only
			STATUS	current
	DESCRIPTION ""
			::= { mbusD1 73 }

mbusD1VIF22		OBJECT-TYPE
			SYNTAX	INTEGER
			ACCESS	read-only
			STATUS	current
	DESCRIPTION ""
			::= { mbusD1 74 }

mbusD1Value22		OBJECT-TYPE
			SYNTAX	INTEGER
			ACCESS	read-only
			STATUS	current
	DESCRIPTION ""
			::= { mbusD1 75 }

mbusD1VIF23		OBJECT-TYPE
			SYNTAX	INTEGER
			ACCESS	read-only
			STATUS	current
	DESCRIPTION ""
			::= { mbusD1 76 }

mbusD1Value23		OBJECT-TYPE
			SYNTAX	INTEGER
			ACCESS	read-only
			STATUS	current
	DESCRIPTION ""
			::= { mbusD1 77 }

mbusD1VIF24		OBJECT-TYPE
			SYNTAX	INTEGER
			ACCESS	read-only
			STATUS	current
	DESCRIPTION ""
			::= { mbusD1 78 }

mbusD1Value24		OBJECT-TYPE
			SYNTAX	INTEGER
			ACCESS	read-only
			STATUS	current
	DESCRIPTION ""
			::= { mbusD1 79 }

mbusD1VIF25		OBJECT-TYPE
			SYNTAX	INTEGER
			ACCESS	read-only
			STATUS	current
	DESCRIPTION ""
			::= { mbusD1 80 }

mbusD1Value25		OBJECT-TYPE
			SYNTAX	INTEGER
			ACCESS	read-only
			STATUS	current
	DESCRIPTION ""
			::= { mbusD1 81 }

mbusD1VIF26		OBJECT-TYPE
			SYNTAX	INTEGER
			ACCESS	read-only
			STATUS	current
	DESCRIPTION ""
			::= { mbusD1 82 }

mbusD1Value26		OBJECT-TYPE
			SYNTAX	INTEGER
			ACCESS	read-only
			STATUS	current
	DESCRIPTION ""
			::= { mbusD1 83 }

mbusD1VIF27		OBJECT-TYPE
			SYNTAX	INTEGER
			ACCESS	read-only
			STATUS	current
	DESCRIPTION ""
			::= { mbusD1 84 }

mbusD1Value27		OBJECT-TYPE
			SYNTAX	INTEGER
			ACCESS	read-only
			STATUS	current
	DESCRIPTION ""
			::= { mbusD1 85 }

mbusD1VIF28		OBJECT-TYPE
			SYNTAX	INTEGER
			ACCESS	read-only
			STATUS	current
	DESCRIPTION ""
			::= { mbusD1 86 }

mbusD1Value28		OBJECT-TYPE
			SYNTAX	INTEGER
			ACCESS	read-only
			STATUS	current
	DESCRIPTION ""
			::= { mbusD1 87 }

mbusD1VIF29		OBJECT-TYPE
			SYNTAX	INTEGER
			ACCESS	read-only
			STATUS	current
	DESCRIPTION ""
			::= { mbusD1 88 }

mbusD1Value29		OBJECT-TYPE
			SYNTAX	INTEGER
			ACCESS	read-only
			STATUS	current
	DESCRIPTION ""
			::= { mbusD1 89 }

mbusD1VIF2A		OBJECT-TYPE
			SYNTAX	INTEGER
			ACCESS	read-only
			STATUS	current
	DESCRIPTION ""
			::= { mbusD1 90 }

mbusD1Value2A		OBJECT-TYPE
			SYNTAX	INTEGER
			ACCESS	read-only
			STATUS	current
	DESCRIPTION ""
			::= { mbusD1 91 }

mbusD1VIF2B		OBJECT-TYPE
			SYNTAX	INTEGER
			ACCESS	read-only
			STATUS	current
	DESCRIPTION ""
			::= { mbusD1 92 }

mbusD1Value2B		OBJECT-TYPE
			SYNTAX	INTEGER
			ACCESS	read-only
			STATUS	current
	DESCRIPTION ""
			::= { mbusD1 93 }

mbusD1VIF2C		OBJECT-TYPE
			SYNTAX	INTEGER
			ACCESS	read-only
			STATUS	current
	DESCRIPTION ""
			::= { mbusD1 94 }

mbusD1Value2C		OBJECT-TYPE
			SYNTAX	INTEGER
			ACCESS	read-only
			STATUS	current
	DESCRIPTION ""
			::= { mbusD1 95 }

mbusD1VIF2D		OBJECT-TYPE
			SYNTAX	INTEGER
			ACCESS	read-only
			STATUS	current
	DESCRIPTION ""
			::= { mbusD1 96 }

mbusD1Value2D		OBJECT-TYPE
			SYNTAX	INTEGER
			ACCESS	read-only
			STATUS	current
	DESCRIPTION ""
			::= { mbusD1 97 }

mbusD1VIF2E		OBJECT-TYPE
			SYNTAX	INTEGER
			ACCESS	read-only
			STATUS	current
	DESCRIPTION ""
			::= { mbusD1 98 }

mbusD1Value2E		OBJECT-TYPE
			SYNTAX	INTEGER
			ACCESS	read-only
			STATUS	current
	DESCRIPTION ""
			::= { mbusD1 99 }

mbusD1VIF2F		OBJECT-TYPE
			SYNTAX	INTEGER
			ACCESS	read-only
			STATUS	current
	DESCRIPTION ""
			::= { mbusD1 100 }

mbusD1Value2F		OBJECT-TYPE
			SYNTAX	INTEGER
			ACCESS	read-only
			STATUS	current
	DESCRIPTION ""
			::= { mbusD1 101 }

mbusD2			OBJECT IDENTIFIER ::= { mbus 210 }

mbusD2IdNumber		OBJECT-TYPE
			SYNTAX	Gauge
			ACCESS	read-only
			STATUS	current
	DESCRIPTION ""
			::= { mbusD2 1 }

mbusD2Manufacturer	OBJECT-TYPE
			SYNTAX	Gauge
			ACCESS	read-only
			STATUS	current
	DESCRIPTION ""
			::= { mbusD2 2 }

mbusD2Version		OBJECT-TYPE
			SYNTAX	Gauge
			ACCESS	read-only
			STATUS	current
	DESCRIPTION ""
			::= { mbusD2 3 }

mbusD2Medium		OBJECT-TYPE
			SYNTAX	Gauge
			ACCESS	read-only
			STATUS	current
	DESCRIPTION ""
			::= { mbusD2 4 }

mbusD2Status		OBJECT-TYPE
			SYNTAX	Gauge
			ACCESS	read-only
			STATUS	current
	DESCRIPTION ""
			::= { mbusD2 5 }

mbusD2VIF00		OBJECT-TYPE
			SYNTAX	INTEGER
			ACCESS	read-only
			STATUS	current
	DESCRIPTION ""
			::= { mbusD2 6 }

mbusD2Value00		OBJECT-TYPE
			SYNTAX	INTEGER
			ACCESS	read-only
			STATUS	current
	DESCRIPTION ""
			::= { mbusD2 7 }

mbusD2VIF01		OBJECT-TYPE
			SYNTAX	INTEGER
			ACCESS	read-only
			STATUS	current
	DESCRIPTION ""
			::= { mbusD2 8 }

mbusD2Value01		OBJECT-TYPE
			SYNTAX	INTEGER
			ACCESS	read-only
			STATUS	current
	DESCRIPTION ""
			::= { mbusD2 9 }

mbusD2VIF02		OBJECT-TYPE
			SYNTAX	INTEGER
			ACCESS	read-only
			STATUS	current
	DESCRIPTION ""
			::= { mbusD2 10 }

mbusD2Value02		OBJECT-TYPE
			SYNTAX	INTEGER
			ACCESS	read-only
			STATUS	current
	DESCRIPTION ""
			::= { mbusD2 11 }

mbusD2VIF03		OBJECT-TYPE
			SYNTAX	INTEGER
			ACCESS	read-only
			STATUS	current
	DESCRIPTION ""
			::= { mbusD2 12 }

mbusD2Value03		OBJECT-TYPE
			SYNTAX	INTEGER
			ACCESS	read-only
			STATUS	current
	DESCRIPTION ""
			::= { mbusD2 13 }

mbusD2VIF04		OBJECT-TYPE
			SYNTAX	INTEGER
			ACCESS	read-only
			STATUS	current
	DESCRIPTION ""
			::= { mbusD2 14 }

mbusD2Value04		OBJECT-TYPE
			SYNTAX	INTEGER
			ACCESS	read-only
			STATUS	current
	DESCRIPTION ""
			::= { mbusD2 15 }

mbusD2VIF05		OBJECT-TYPE
			SYNTAX	INTEGER
			ACCESS	read-only
			STATUS	current
	DESCRIPTION ""
			::= { mbusD2 16 }

mbusD2Value05		OBJECT-TYPE
			SYNTAX	INTEGER
			ACCESS	read-only
			STATUS	current
	DESCRIPTION ""
			::= { mbusD2 17 }

mbusD2VIF06		OBJECT-TYPE
			SYNTAX	INTEGER
			ACCESS	read-only
			STATUS	current
	DESCRIPTION ""
			::= { mbusD2 18 }

mbusD2Value06		OBJECT-TYPE
			SYNTAX	INTEGER
			ACCESS	read-only
			STATUS	current
	DESCRIPTION ""
			::= { mbusD2 19 }

mbusD2VIF07		OBJECT-TYPE
			SYNTAX	INTEGER
			ACCESS	read-only
			STATUS	current
	DESCRIPTION ""
			::= { mbusD2 20 }

mbusD2Value07		OBJECT-TYPE
			SYNTAX	INTEGER
			ACCESS	read-only
			STATUS	current
	DESCRIPTION ""
			::= { mbusD2 21 }

mbusD2VIF08		OBJECT-TYPE
			SYNTAX	INTEGER
			ACCESS	read-only
			STATUS	current
	DESCRIPTION ""
			::= { mbusD2 22 }

mbusD2Value08		OBJECT-TYPE
			SYNTAX	INTEGER
			ACCESS	read-only
			STATUS	current
	DESCRIPTION ""
			::= { mbusD2 23 }

mbusD2VIF09		OBJECT-TYPE
			SYNTAX	INTEGER
			ACCESS	read-only
			STATUS	current
	DESCRIPTION ""
			::= { mbusD2 24 }

mbusD2Value09		OBJECT-TYPE
			SYNTAX	INTEGER
			ACCESS	read-only
			STATUS	current
	DESCRIPTION ""
			::= { mbusD2 25 }

mbusD2VIF0A		OBJECT-TYPE
			SYNTAX	INTEGER
			ACCESS	read-only
			STATUS	current
	DESCRIPTION ""
			::= { mbusD2 26 }

mbusD2Value0A		OBJECT-TYPE
			SYNTAX	INTEGER
			ACCESS	read-only
			STATUS	current
	DESCRIPTION ""
			::= { mbusD2 27 }

mbusD2VIF0B		OBJECT-TYPE
			SYNTAX	INTEGER
			ACCESS	read-only
			STATUS	current
	DESCRIPTION ""
			::= { mbusD2 28 }

mbusD2Value0B		OBJECT-TYPE
			SYNTAX	INTEGER
			ACCESS	read-only
			STATUS	current
	DESCRIPTION ""
			::= { mbusD2 29 }

mbusD2VIF0C		OBJECT-TYPE
			SYNTAX	INTEGER
			ACCESS	read-only
			STATUS	current
	DESCRIPTION ""
			::= { mbusD2 30 }

mbusD2Value0C		OBJECT-TYPE
			SYNTAX	INTEGER
			ACCESS	read-only
			STATUS	current
	DESCRIPTION ""
			::= { mbusD2 31 }

mbusD2VIF0D		OBJECT-TYPE
			SYNTAX	INTEGER
			ACCESS	read-only
			STATUS	current
	DESCRIPTION ""
			::= { mbusD2 32 }

mbusD2Value0D		OBJECT-TYPE
			SYNTAX	INTEGER
			ACCESS	read-only
			STATUS	current
	DESCRIPTION ""
			::= { mbusD2 33 }

mbusD2VIF0E		OBJECT-TYPE
			SYNTAX	INTEGER
			ACCESS	read-only
			STATUS	current
	DESCRIPTION ""
			::= { mbusD2 34 }

mbusD2Value0E		OBJECT-TYPE
			SYNTAX	INTEGER
			ACCESS	read-only
			STATUS	current
	DESCRIPTION ""
			::= { mbusD2 35 }

mbusD2VIF0F		OBJECT-TYPE
			SYNTAX	INTEGER
			ACCESS	read-only
			STATUS	current
	DESCRIPTION ""
			::= { mbusD2 36 }

mbusD2Value0F		OBJECT-TYPE
			SYNTAX	INTEGER
			ACCESS	read-only
			STATUS	current
	DESCRIPTION ""
			::= { mbusD2 37 }

mbusD2VIF10		OBJECT-TYPE
			SYNTAX	INTEGER
			ACCESS	read-only
			STATUS	current
	DESCRIPTION ""
			::= { mbusD2 38 }

mbusD2Value10		OBJECT-TYPE
			SYNTAX	INTEGER
			ACCESS	read-only
			STATUS	current
	DESCRIPTION ""
			::= { mbusD2 39 }

mbusD2VIF11		OBJECT-TYPE
			SYNTAX	INTEGER
			ACCESS	read-only
			STATUS	current
	DESCRIPTION ""
			::= { mbusD2 40 }

mbusD2Value11		OBJECT-TYPE
			SYNTAX	INTEGER
			ACCESS	read-only
			STATUS	current
	DESCRIPTION ""
			::= { mbusD2 41 }

mbusD2VIF12		OBJECT-TYPE
			SYNTAX	INTEGER
			ACCESS	read-only
			STATUS	current
	DESCRIPTION ""
			::= { mbusD2 42 }

mbusD2Value12		OBJECT-TYPE
			SYNTAX	INTEGER
			ACCESS	read-only
			STATUS	current
	DESCRIPTION ""
			::= { mbusD2 43 }

mbusD2VIF13		OBJECT-TYPE
			SYNTAX	INTEGER
			ACCESS	read-only
			STATUS	current
	DESCRIPTION ""
			::= { mbusD2 44 }

mbusD2Value13		OBJECT-TYPE
			SYNTAX	INTEGER
			ACCESS	read-only
			STATUS	current
	DESCRIPTION ""
			::= { mbusD2 45 }

mbusD2VIF14		OBJECT-TYPE
			SYNTAX	INTEGER
			ACCESS	read-only
			STATUS	current
	DESCRIPTION ""
			::= { mbusD2 46 }

mbusD2Value14		OBJECT-TYPE
			SYNTAX	INTEGER
			ACCESS	read-only
			STATUS	current
	DESCRIPTION ""
			::= { mbusD2 47 }

mbusD2VIF15		OBJECT-TYPE
			SYNTAX	INTEGER
			ACCESS	read-only
			STATUS	current
	DESCRIPTION ""
			::= { mbusD2 48 }

mbusD2Value15		OBJECT-TYPE
			SYNTAX	INTEGER
			ACCESS	read-only
			STATUS	current
	DESCRIPTION ""
			::= { mbusD2 49 }

mbusD2VIF16		OBJECT-TYPE
			SYNTAX	INTEGER
			ACCESS	read-only
			STATUS	current
	DESCRIPTION ""
			::= { mbusD2 50 }

mbusD2Value16		OBJECT-TYPE
			SYNTAX	INTEGER
			ACCESS	read-only
			STATUS	current
	DESCRIPTION ""
			::= { mbusD2 51 }

mbusD2VIF17		OBJECT-TYPE
			SYNTAX	INTEGER
			ACCESS	read-only
			STATUS	current
	DESCRIPTION ""
			::= { mbusD2 52 }

mbusD2Value17		OBJECT-TYPE
			SYNTAX	INTEGER
			ACCESS	read-only
			STATUS	current
	DESCRIPTION ""
			::= { mbusD2 53 }

mbusD2VIF18		OBJECT-TYPE
			SYNTAX	INTEGER
			ACCESS	read-only
			STATUS	current
	DESCRIPTION ""
			::= { mbusD2 54 }

mbusD2Value18		OBJECT-TYPE
			SYNTAX	INTEGER
			ACCESS	read-only
			STATUS	current
	DESCRIPTION ""
			::= { mbusD2 55 }

mbusD2VIF19		OBJECT-TYPE
			SYNTAX	INTEGER
			ACCESS	read-only
			STATUS	current
	DESCRIPTION ""
			::= { mbusD2 56 }

mbusD2Value19		OBJECT-TYPE
			SYNTAX	INTEGER
			ACCESS	read-only
			STATUS	current
	DESCRIPTION ""
			::= { mbusD2 57 }

mbusD2VIF1A		OBJECT-TYPE
			SYNTAX	INTEGER
			ACCESS	read-only
			STATUS	current
	DESCRIPTION ""
			::= { mbusD2 58 }

mbusD2Value1A		OBJECT-TYPE
			SYNTAX	INTEGER
			ACCESS	read-only
			STATUS	current
	DESCRIPTION ""
			::= { mbusD2 59 }

mbusD2VIF1B		OBJECT-TYPE
			SYNTAX	INTEGER
			ACCESS	read-only
			STATUS	current
	DESCRIPTION ""
			::= { mbusD2 60 }

mbusD2Value1B		OBJECT-TYPE
			SYNTAX	INTEGER
			ACCESS	read-only
			STATUS	current
	DESCRIPTION ""
			::= { mbusD2 61 }

mbusD2VIF1C		OBJECT-TYPE
			SYNTAX	INTEGER
			ACCESS	read-only
			STATUS	current
	DESCRIPTION ""
			::= { mbusD2 62 }

mbusD2Value1C		OBJECT-TYPE
			SYNTAX	INTEGER
			ACCESS	read-only
			STATUS	current
	DESCRIPTION ""
			::= { mbusD2 63 }

mbusD2VIF1D		OBJECT-TYPE
			SYNTAX	INTEGER
			ACCESS	read-only
			STATUS	current
	DESCRIPTION ""
			::= { mbusD2 64 }

mbusD2Value1D		OBJECT-TYPE
			SYNTAX	INTEGER
			ACCESS	read-only
			STATUS	current
	DESCRIPTION ""
			::= { mbusD2 65 }

mbusD2VIF1E		OBJECT-TYPE
			SYNTAX	INTEGER
			ACCESS	read-only
			STATUS	current
	DESCRIPTION ""
			::= { mbusD2 66 }

mbusD2Value1E		OBJECT-TYPE
			SYNTAX	INTEGER
			ACCESS	read-only
			STATUS	current
	DESCRIPTION ""
			::= { mbusD2 67 }

mbusD2VIF1F		OBJECT-TYPE
			SYNTAX	INTEGER
			ACCESS	read-only
			STATUS	current
	DESCRIPTION ""
			::= { mbusD2 68 }

mbusD2Value1F		OBJECT-TYPE
			SYNTAX	INTEGER
			ACCESS	read-only
			STATUS	current
	DESCRIPTION ""
			::= { mbusD2 69 }

mbusD2VIF20		OBJECT-TYPE
			SYNTAX	INTEGER
			ACCESS	read-only
			STATUS	current
	DESCRIPTION ""
			::= { mbusD2 70 }

mbusD2Value20		OBJECT-TYPE
			SYNTAX	INTEGER
			ACCESS	read-only
			STATUS	current
	DESCRIPTION ""
			::= { mbusD2 71 }

mbusD2VIF21		OBJECT-TYPE
			SYNTAX	INTEGER
			ACCESS	read-only
			STATUS	current
	DESCRIPTION ""
			::= { mbusD2 72 }

mbusD2Value21		OBJECT-TYPE
			SYNTAX	INTEGER
			ACCESS	read-only
			STATUS	current
	DESCRIPTION ""
			::= { mbusD2 73 }

mbusD2VIF22		OBJECT-TYPE
			SYNTAX	INTEGER
			ACCESS	read-only
			STATUS	current
	DESCRIPTION ""
			::= { mbusD2 74 }

mbusD2Value22		OBJECT-TYPE
			SYNTAX	INTEGER
			ACCESS	read-only
			STATUS	current
	DESCRIPTION ""
			::= { mbusD2 75 }

mbusD2VIF23		OBJECT-TYPE
			SYNTAX	INTEGER
			ACCESS	read-only
			STATUS	current
	DESCRIPTION ""
			::= { mbusD2 76 }

mbusD2Value23		OBJECT-TYPE
			SYNTAX	INTEGER
			ACCESS	read-only
			STATUS	current
	DESCRIPTION ""
			::= { mbusD2 77 }

mbusD2VIF24		OBJECT-TYPE
			SYNTAX	INTEGER
			ACCESS	read-only
			STATUS	current
	DESCRIPTION ""
			::= { mbusD2 78 }

mbusD2Value24		OBJECT-TYPE
			SYNTAX	INTEGER
			ACCESS	read-only
			STATUS	current
	DESCRIPTION ""
			::= { mbusD2 79 }

mbusD2VIF25		OBJECT-TYPE
			SYNTAX	INTEGER
			ACCESS	read-only
			STATUS	current
	DESCRIPTION ""
			::= { mbusD2 80 }

mbusD2Value25		OBJECT-TYPE
			SYNTAX	INTEGER
			ACCESS	read-only
			STATUS	current
	DESCRIPTION ""
			::= { mbusD2 81 }

mbusD2VIF26		OBJECT-TYPE
			SYNTAX	INTEGER
			ACCESS	read-only
			STATUS	current
	DESCRIPTION ""
			::= { mbusD2 82 }

mbusD2Value26		OBJECT-TYPE
			SYNTAX	INTEGER
			ACCESS	read-only
			STATUS	current
	DESCRIPTION ""
			::= { mbusD2 83 }

mbusD2VIF27		OBJECT-TYPE
			SYNTAX	INTEGER
			ACCESS	read-only
			STATUS	current
	DESCRIPTION ""
			::= { mbusD2 84 }

mbusD2Value27		OBJECT-TYPE
			SYNTAX	INTEGER
			ACCESS	read-only
			STATUS	current
	DESCRIPTION ""
			::= { mbusD2 85 }

mbusD2VIF28		OBJECT-TYPE
			SYNTAX	INTEGER
			ACCESS	read-only
			STATUS	current
	DESCRIPTION ""
			::= { mbusD2 86 }

mbusD2Value28		OBJECT-TYPE
			SYNTAX	INTEGER
			ACCESS	read-only
			STATUS	current
	DESCRIPTION ""
			::= { mbusD2 87 }

mbusD2VIF29		OBJECT-TYPE
			SYNTAX	INTEGER
			ACCESS	read-only
			STATUS	current
	DESCRIPTION ""
			::= { mbusD2 88 }

mbusD2Value29		OBJECT-TYPE
			SYNTAX	INTEGER
			ACCESS	read-only
			STATUS	current
	DESCRIPTION ""
			::= { mbusD2 89 }

mbusD2VIF2A		OBJECT-TYPE
			SYNTAX	INTEGER
			ACCESS	read-only
			STATUS	current
	DESCRIPTION ""
			::= { mbusD2 90 }

mbusD2Value2A		OBJECT-TYPE
			SYNTAX	INTEGER
			ACCESS	read-only
			STATUS	current
	DESCRIPTION ""
			::= { mbusD2 91 }

mbusD2VIF2B		OBJECT-TYPE
			SYNTAX	INTEGER
			ACCESS	read-only
			STATUS	current
	DESCRIPTION ""
			::= { mbusD2 92 }

mbusD2Value2B		OBJECT-TYPE
			SYNTAX	INTEGER
			ACCESS	read-only
			STATUS	current
	DESCRIPTION ""
			::= { mbusD2 93 }

mbusD2VIF2C		OBJECT-TYPE
			SYNTAX	INTEGER
			ACCESS	read-only
			STATUS	current
	DESCRIPTION ""
			::= { mbusD2 94 }

mbusD2Value2C		OBJECT-TYPE
			SYNTAX	INTEGER
			ACCESS	read-only
			STATUS	current
	DESCRIPTION ""
			::= { mbusD2 95 }

mbusD2VIF2D		OBJECT-TYPE
			SYNTAX	INTEGER
			ACCESS	read-only
			STATUS	current
	DESCRIPTION ""
			::= { mbusD2 96 }

mbusD2Value2D		OBJECT-TYPE
			SYNTAX	INTEGER
			ACCESS	read-only
			STATUS	current
	DESCRIPTION ""
			::= { mbusD2 97 }

mbusD2VIF2E		OBJECT-TYPE
			SYNTAX	INTEGER
			ACCESS	read-only
			STATUS	current
	DESCRIPTION ""
			::= { mbusD2 98 }

mbusD2Value2E		OBJECT-TYPE
			SYNTAX	INTEGER
			ACCESS	read-only
			STATUS	current
	DESCRIPTION ""
			::= { mbusD2 99 }

mbusD2VIF2F		OBJECT-TYPE
			SYNTAX	INTEGER
			ACCESS	read-only
			STATUS	current
	DESCRIPTION ""
			::= { mbusD2 100 }

mbusD2Value2F		OBJECT-TYPE
			SYNTAX	INTEGER
			ACCESS	read-only
			STATUS	current
	DESCRIPTION ""
			::= { mbusD2 101 }

mbusD3			OBJECT IDENTIFIER ::= { mbus 211 }

mbusD3IdNumber		OBJECT-TYPE
			SYNTAX	Gauge
			ACCESS	read-only
			STATUS	current
	DESCRIPTION ""
			::= { mbusD3 1 }

mbusD3Manufacturer	OBJECT-TYPE
			SYNTAX	Gauge
			ACCESS	read-only
			STATUS	current
	DESCRIPTION ""
			::= { mbusD3 2 }

mbusD3Version		OBJECT-TYPE
			SYNTAX	Gauge
			ACCESS	read-only
			STATUS	current
	DESCRIPTION ""
			::= { mbusD3 3 }

mbusD3Medium		OBJECT-TYPE
			SYNTAX	Gauge
			ACCESS	read-only
			STATUS	current
	DESCRIPTION ""
			::= { mbusD3 4 }

mbusD3Status		OBJECT-TYPE
			SYNTAX	Gauge
			ACCESS	read-only
			STATUS	current
	DESCRIPTION ""
			::= { mbusD3 5 }

mbusD3VIF00		OBJECT-TYPE
			SYNTAX	INTEGER
			ACCESS	read-only
			STATUS	current
	DESCRIPTION ""
			::= { mbusD3 6 }

mbusD3Value00		OBJECT-TYPE
			SYNTAX	INTEGER
			ACCESS	read-only
			STATUS	current
	DESCRIPTION ""
			::= { mbusD3 7 }

mbusD3VIF01		OBJECT-TYPE
			SYNTAX	INTEGER
			ACCESS	read-only
			STATUS	current
	DESCRIPTION ""
			::= { mbusD3 8 }

mbusD3Value01		OBJECT-TYPE
			SYNTAX	INTEGER
			ACCESS	read-only
			STATUS	current
	DESCRIPTION ""
			::= { mbusD3 9 }

mbusD3VIF02		OBJECT-TYPE
			SYNTAX	INTEGER
			ACCESS	read-only
			STATUS	current
	DESCRIPTION ""
			::= { mbusD3 10 }

mbusD3Value02		OBJECT-TYPE
			SYNTAX	INTEGER
			ACCESS	read-only
			STATUS	current
	DESCRIPTION ""
			::= { mbusD3 11 }

mbusD3VIF03		OBJECT-TYPE
			SYNTAX	INTEGER
			ACCESS	read-only
			STATUS	current
	DESCRIPTION ""
			::= { mbusD3 12 }

mbusD3Value03		OBJECT-TYPE
			SYNTAX	INTEGER
			ACCESS	read-only
			STATUS	current
	DESCRIPTION ""
			::= { mbusD3 13 }

mbusD3VIF04		OBJECT-TYPE
			SYNTAX	INTEGER
			ACCESS	read-only
			STATUS	current
	DESCRIPTION ""
			::= { mbusD3 14 }

mbusD3Value04		OBJECT-TYPE
			SYNTAX	INTEGER
			ACCESS	read-only
			STATUS	current
	DESCRIPTION ""
			::= { mbusD3 15 }

mbusD3VIF05		OBJECT-TYPE
			SYNTAX	INTEGER
			ACCESS	read-only
			STATUS	current
	DESCRIPTION ""
			::= { mbusD3 16 }

mbusD3Value05		OBJECT-TYPE
			SYNTAX	INTEGER
			ACCESS	read-only
			STATUS	current
	DESCRIPTION ""
			::= { mbusD3 17 }

mbusD3VIF06		OBJECT-TYPE
			SYNTAX	INTEGER
			ACCESS	read-only
			STATUS	current
	DESCRIPTION ""
			::= { mbusD3 18 }

mbusD3Value06		OBJECT-TYPE
			SYNTAX	INTEGER
			ACCESS	read-only
			STATUS	current
	DESCRIPTION ""
			::= { mbusD3 19 }

mbusD3VIF07		OBJECT-TYPE
			SYNTAX	INTEGER
			ACCESS	read-only
			STATUS	current
	DESCRIPTION ""
			::= { mbusD3 20 }

mbusD3Value07		OBJECT-TYPE
			SYNTAX	INTEGER
			ACCESS	read-only
			STATUS	current
	DESCRIPTION ""
			::= { mbusD3 21 }

mbusD3VIF08		OBJECT-TYPE
			SYNTAX	INTEGER
			ACCESS	read-only
			STATUS	current
	DESCRIPTION ""
			::= { mbusD3 22 }

mbusD3Value08		OBJECT-TYPE
			SYNTAX	INTEGER
			ACCESS	read-only
			STATUS	current
	DESCRIPTION ""
			::= { mbusD3 23 }

mbusD3VIF09		OBJECT-TYPE
			SYNTAX	INTEGER
			ACCESS	read-only
			STATUS	current
	DESCRIPTION ""
			::= { mbusD3 24 }

mbusD3Value09		OBJECT-TYPE
			SYNTAX	INTEGER
			ACCESS	read-only
			STATUS	current
	DESCRIPTION ""
			::= { mbusD3 25 }

mbusD3VIF0A		OBJECT-TYPE
			SYNTAX	INTEGER
			ACCESS	read-only
			STATUS	current
	DESCRIPTION ""
			::= { mbusD3 26 }

mbusD3Value0A		OBJECT-TYPE
			SYNTAX	INTEGER
			ACCESS	read-only
			STATUS	current
	DESCRIPTION ""
			::= { mbusD3 27 }

mbusD3VIF0B		OBJECT-TYPE
			SYNTAX	INTEGER
			ACCESS	read-only
			STATUS	current
	DESCRIPTION ""
			::= { mbusD3 28 }

mbusD3Value0B		OBJECT-TYPE
			SYNTAX	INTEGER
			ACCESS	read-only
			STATUS	current
	DESCRIPTION ""
			::= { mbusD3 29 }

mbusD3VIF0C		OBJECT-TYPE
			SYNTAX	INTEGER
			ACCESS	read-only
			STATUS	current
	DESCRIPTION ""
			::= { mbusD3 30 }

mbusD3Value0C		OBJECT-TYPE
			SYNTAX	INTEGER
			ACCESS	read-only
			STATUS	current
	DESCRIPTION ""
			::= { mbusD3 31 }

mbusD3VIF0D		OBJECT-TYPE
			SYNTAX	INTEGER
			ACCESS	read-only
			STATUS	current
	DESCRIPTION ""
			::= { mbusD3 32 }

mbusD3Value0D		OBJECT-TYPE
			SYNTAX	INTEGER
			ACCESS	read-only
			STATUS	current
	DESCRIPTION ""
			::= { mbusD3 33 }

mbusD3VIF0E		OBJECT-TYPE
			SYNTAX	INTEGER
			ACCESS	read-only
			STATUS	current
	DESCRIPTION ""
			::= { mbusD3 34 }

mbusD3Value0E		OBJECT-TYPE
			SYNTAX	INTEGER
			ACCESS	read-only
			STATUS	current
	DESCRIPTION ""
			::= { mbusD3 35 }

mbusD3VIF0F		OBJECT-TYPE
			SYNTAX	INTEGER
			ACCESS	read-only
			STATUS	current
	DESCRIPTION ""
			::= { mbusD3 36 }

mbusD3Value0F		OBJECT-TYPE
			SYNTAX	INTEGER
			ACCESS	read-only
			STATUS	current
	DESCRIPTION ""
			::= { mbusD3 37 }

mbusD3VIF10		OBJECT-TYPE
			SYNTAX	INTEGER
			ACCESS	read-only
			STATUS	current
	DESCRIPTION ""
			::= { mbusD3 38 }

mbusD3Value10		OBJECT-TYPE
			SYNTAX	INTEGER
			ACCESS	read-only
			STATUS	current
	DESCRIPTION ""
			::= { mbusD3 39 }

mbusD3VIF11		OBJECT-TYPE
			SYNTAX	INTEGER
			ACCESS	read-only
			STATUS	current
	DESCRIPTION ""
			::= { mbusD3 40 }

mbusD3Value11		OBJECT-TYPE
			SYNTAX	INTEGER
			ACCESS	read-only
			STATUS	current
	DESCRIPTION ""
			::= { mbusD3 41 }

mbusD3VIF12		OBJECT-TYPE
			SYNTAX	INTEGER
			ACCESS	read-only
			STATUS	current
	DESCRIPTION ""
			::= { mbusD3 42 }

mbusD3Value12		OBJECT-TYPE
			SYNTAX	INTEGER
			ACCESS	read-only
			STATUS	current
	DESCRIPTION ""
			::= { mbusD3 43 }

mbusD3VIF13		OBJECT-TYPE
			SYNTAX	INTEGER
			ACCESS	read-only
			STATUS	current
	DESCRIPTION ""
			::= { mbusD3 44 }

mbusD3Value13		OBJECT-TYPE
			SYNTAX	INTEGER
			ACCESS	read-only
			STATUS	current
	DESCRIPTION ""
			::= { mbusD3 45 }

mbusD3VIF14		OBJECT-TYPE
			SYNTAX	INTEGER
			ACCESS	read-only
			STATUS	current
	DESCRIPTION ""
			::= { mbusD3 46 }

mbusD3Value14		OBJECT-TYPE
			SYNTAX	INTEGER
			ACCESS	read-only
			STATUS	current
	DESCRIPTION ""
			::= { mbusD3 47 }

mbusD3VIF15		OBJECT-TYPE
			SYNTAX	INTEGER
			ACCESS	read-only
			STATUS	current
	DESCRIPTION ""
			::= { mbusD3 48 }

mbusD3Value15		OBJECT-TYPE
			SYNTAX	INTEGER
			ACCESS	read-only
			STATUS	current
	DESCRIPTION ""
			::= { mbusD3 49 }

mbusD3VIF16		OBJECT-TYPE
			SYNTAX	INTEGER
			ACCESS	read-only
			STATUS	current
	DESCRIPTION ""
			::= { mbusD3 50 }

mbusD3Value16		OBJECT-TYPE
			SYNTAX	INTEGER
			ACCESS	read-only
			STATUS	current
	DESCRIPTION ""
			::= { mbusD3 51 }

mbusD3VIF17		OBJECT-TYPE
			SYNTAX	INTEGER
			ACCESS	read-only
			STATUS	current
	DESCRIPTION ""
			::= { mbusD3 52 }

mbusD3Value17		OBJECT-TYPE
			SYNTAX	INTEGER
			ACCESS	read-only
			STATUS	current
	DESCRIPTION ""
			::= { mbusD3 53 }

mbusD3VIF18		OBJECT-TYPE
			SYNTAX	INTEGER
			ACCESS	read-only
			STATUS	current
	DESCRIPTION ""
			::= { mbusD3 54 }

mbusD3Value18		OBJECT-TYPE
			SYNTAX	INTEGER
			ACCESS	read-only
			STATUS	current
	DESCRIPTION ""
			::= { mbusD3 55 }

mbusD3VIF19		OBJECT-TYPE
			SYNTAX	INTEGER
			ACCESS	read-only
			STATUS	current
	DESCRIPTION ""
			::= { mbusD3 56 }

mbusD3Value19		OBJECT-TYPE
			SYNTAX	INTEGER
			ACCESS	read-only
			STATUS	current
	DESCRIPTION ""
			::= { mbusD3 57 }

mbusD3VIF1A		OBJECT-TYPE
			SYNTAX	INTEGER
			ACCESS	read-only
			STATUS	current
	DESCRIPTION ""
			::= { mbusD3 58 }

mbusD3Value1A		OBJECT-TYPE
			SYNTAX	INTEGER
			ACCESS	read-only
			STATUS	current
	DESCRIPTION ""
			::= { mbusD3 59 }

mbusD3VIF1B		OBJECT-TYPE
			SYNTAX	INTEGER
			ACCESS	read-only
			STATUS	current
	DESCRIPTION ""
			::= { mbusD3 60 }

mbusD3Value1B		OBJECT-TYPE
			SYNTAX	INTEGER
			ACCESS	read-only
			STATUS	current
	DESCRIPTION ""
			::= { mbusD3 61 }

mbusD3VIF1C		OBJECT-TYPE
			SYNTAX	INTEGER
			ACCESS	read-only
			STATUS	current
	DESCRIPTION ""
			::= { mbusD3 62 }

mbusD3Value1C		OBJECT-TYPE
			SYNTAX	INTEGER
			ACCESS	read-only
			STATUS	current
	DESCRIPTION ""
			::= { mbusD3 63 }

mbusD3VIF1D		OBJECT-TYPE
			SYNTAX	INTEGER
			ACCESS	read-only
			STATUS	current
	DESCRIPTION ""
			::= { mbusD3 64 }

mbusD3Value1D		OBJECT-TYPE
			SYNTAX	INTEGER
			ACCESS	read-only
			STATUS	current
	DESCRIPTION ""
			::= { mbusD3 65 }

mbusD3VIF1E		OBJECT-TYPE
			SYNTAX	INTEGER
			ACCESS	read-only
			STATUS	current
	DESCRIPTION ""
			::= { mbusD3 66 }

mbusD3Value1E		OBJECT-TYPE
			SYNTAX	INTEGER
			ACCESS	read-only
			STATUS	current
	DESCRIPTION ""
			::= { mbusD3 67 }

mbusD3VIF1F		OBJECT-TYPE
			SYNTAX	INTEGER
			ACCESS	read-only
			STATUS	current
	DESCRIPTION ""
			::= { mbusD3 68 }

mbusD3Value1F		OBJECT-TYPE
			SYNTAX	INTEGER
			ACCESS	read-only
			STATUS	current
	DESCRIPTION ""
			::= { mbusD3 69 }

mbusD3VIF20		OBJECT-TYPE
			SYNTAX	INTEGER
			ACCESS	read-only
			STATUS	current
	DESCRIPTION ""
			::= { mbusD3 70 }

mbusD3Value20		OBJECT-TYPE
			SYNTAX	INTEGER
			ACCESS	read-only
			STATUS	current
	DESCRIPTION ""
			::= { mbusD3 71 }

mbusD3VIF21		OBJECT-TYPE
			SYNTAX	INTEGER
			ACCESS	read-only
			STATUS	current
	DESCRIPTION ""
			::= { mbusD3 72 }

mbusD3Value21		OBJECT-TYPE
			SYNTAX	INTEGER
			ACCESS	read-only
			STATUS	current
	DESCRIPTION ""
			::= { mbusD3 73 }

mbusD3VIF22		OBJECT-TYPE
			SYNTAX	INTEGER
			ACCESS	read-only
			STATUS	current
	DESCRIPTION ""
			::= { mbusD3 74 }

mbusD3Value22		OBJECT-TYPE
			SYNTAX	INTEGER
			ACCESS	read-only
			STATUS	current
	DESCRIPTION ""
			::= { mbusD3 75 }

mbusD3VIF23		OBJECT-TYPE
			SYNTAX	INTEGER
			ACCESS	read-only
			STATUS	current
	DESCRIPTION ""
			::= { mbusD3 76 }

mbusD3Value23		OBJECT-TYPE
			SYNTAX	INTEGER
			ACCESS	read-only
			STATUS	current
	DESCRIPTION ""
			::= { mbusD3 77 }

mbusD3VIF24		OBJECT-TYPE
			SYNTAX	INTEGER
			ACCESS	read-only
			STATUS	current
	DESCRIPTION ""
			::= { mbusD3 78 }

mbusD3Value24		OBJECT-TYPE
			SYNTAX	INTEGER
			ACCESS	read-only
			STATUS	current
	DESCRIPTION ""
			::= { mbusD3 79 }

mbusD3VIF25		OBJECT-TYPE
			SYNTAX	INTEGER
			ACCESS	read-only
			STATUS	current
	DESCRIPTION ""
			::= { mbusD3 80 }

mbusD3Value25		OBJECT-TYPE
			SYNTAX	INTEGER
			ACCESS	read-only
			STATUS	current
	DESCRIPTION ""
			::= { mbusD3 81 }

mbusD3VIF26		OBJECT-TYPE
			SYNTAX	INTEGER
			ACCESS	read-only
			STATUS	current
	DESCRIPTION ""
			::= { mbusD3 82 }

mbusD3Value26		OBJECT-TYPE
			SYNTAX	INTEGER
			ACCESS	read-only
			STATUS	current
	DESCRIPTION ""
			::= { mbusD3 83 }

mbusD3VIF27		OBJECT-TYPE
			SYNTAX	INTEGER
			ACCESS	read-only
			STATUS	current
	DESCRIPTION ""
			::= { mbusD3 84 }

mbusD3Value27		OBJECT-TYPE
			SYNTAX	INTEGER
			ACCESS	read-only
			STATUS	current
	DESCRIPTION ""
			::= { mbusD3 85 }

mbusD3VIF28		OBJECT-TYPE
			SYNTAX	INTEGER
			ACCESS	read-only
			STATUS	current
	DESCRIPTION ""
			::= { mbusD3 86 }

mbusD3Value28		OBJECT-TYPE
			SYNTAX	INTEGER
			ACCESS	read-only
			STATUS	current
	DESCRIPTION ""
			::= { mbusD3 87 }

mbusD3VIF29		OBJECT-TYPE
			SYNTAX	INTEGER
			ACCESS	read-only
			STATUS	current
	DESCRIPTION ""
			::= { mbusD3 88 }

mbusD3Value29		OBJECT-TYPE
			SYNTAX	INTEGER
			ACCESS	read-only
			STATUS	current
	DESCRIPTION ""
			::= { mbusD3 89 }

mbusD3VIF2A		OBJECT-TYPE
			SYNTAX	INTEGER
			ACCESS	read-only
			STATUS	current
	DESCRIPTION ""
			::= { mbusD3 90 }

mbusD3Value2A		OBJECT-TYPE
			SYNTAX	INTEGER
			ACCESS	read-only
			STATUS	current
	DESCRIPTION ""
			::= { mbusD3 91 }

mbusD3VIF2B		OBJECT-TYPE
			SYNTAX	INTEGER
			ACCESS	read-only
			STATUS	current
	DESCRIPTION ""
			::= { mbusD3 92 }

mbusD3Value2B		OBJECT-TYPE
			SYNTAX	INTEGER
			ACCESS	read-only
			STATUS	current
	DESCRIPTION ""
			::= { mbusD3 93 }

mbusD3VIF2C		OBJECT-TYPE
			SYNTAX	INTEGER
			ACCESS	read-only
			STATUS	current
	DESCRIPTION ""
			::= { mbusD3 94 }

mbusD3Value2C		OBJECT-TYPE
			SYNTAX	INTEGER
			ACCESS	read-only
			STATUS	current
	DESCRIPTION ""
			::= { mbusD3 95 }

mbusD3VIF2D		OBJECT-TYPE
			SYNTAX	INTEGER
			ACCESS	read-only
			STATUS	current
	DESCRIPTION ""
			::= { mbusD3 96 }

mbusD3Value2D		OBJECT-TYPE
			SYNTAX	INTEGER
			ACCESS	read-only
			STATUS	current
	DESCRIPTION ""
			::= { mbusD3 97 }

mbusD3VIF2E		OBJECT-TYPE
			SYNTAX	INTEGER
			ACCESS	read-only
			STATUS	current
	DESCRIPTION ""
			::= { mbusD3 98 }

mbusD3Value2E		OBJECT-TYPE
			SYNTAX	INTEGER
			ACCESS	read-only
			STATUS	current
	DESCRIPTION ""
			::= { mbusD3 99 }

mbusD3VIF2F		OBJECT-TYPE
			SYNTAX	INTEGER
			ACCESS	read-only
			STATUS	current
	DESCRIPTION ""
			::= { mbusD3 100 }

mbusD3Value2F		OBJECT-TYPE
			SYNTAX	INTEGER
			ACCESS	read-only
			STATUS	current
	DESCRIPTION ""
			::= { mbusD3 101 }

mbusD4			OBJECT IDENTIFIER ::= { mbus 212 }

mbusD4IdNumber		OBJECT-TYPE
			SYNTAX	Gauge
			ACCESS	read-only
			STATUS	current
	DESCRIPTION ""
			::= { mbusD4 1 }

mbusD4Manufacturer	OBJECT-TYPE
			SYNTAX	Gauge
			ACCESS	read-only
			STATUS	current
	DESCRIPTION ""
			::= { mbusD4 2 }

mbusD4Version		OBJECT-TYPE
			SYNTAX	Gauge
			ACCESS	read-only
			STATUS	current
	DESCRIPTION ""
			::= { mbusD4 3 }

mbusD4Medium		OBJECT-TYPE
			SYNTAX	Gauge
			ACCESS	read-only
			STATUS	current
	DESCRIPTION ""
			::= { mbusD4 4 }

mbusD4Status		OBJECT-TYPE
			SYNTAX	Gauge
			ACCESS	read-only
			STATUS	current
	DESCRIPTION ""
			::= { mbusD4 5 }

mbusD4VIF00		OBJECT-TYPE
			SYNTAX	INTEGER
			ACCESS	read-only
			STATUS	current
	DESCRIPTION ""
			::= { mbusD4 6 }

mbusD4Value00		OBJECT-TYPE
			SYNTAX	INTEGER
			ACCESS	read-only
			STATUS	current
	DESCRIPTION ""
			::= { mbusD4 7 }

mbusD4VIF01		OBJECT-TYPE
			SYNTAX	INTEGER
			ACCESS	read-only
			STATUS	current
	DESCRIPTION ""
			::= { mbusD4 8 }

mbusD4Value01		OBJECT-TYPE
			SYNTAX	INTEGER
			ACCESS	read-only
			STATUS	current
	DESCRIPTION ""
			::= { mbusD4 9 }

mbusD4VIF02		OBJECT-TYPE
			SYNTAX	INTEGER
			ACCESS	read-only
			STATUS	current
	DESCRIPTION ""
			::= { mbusD4 10 }

mbusD4Value02		OBJECT-TYPE
			SYNTAX	INTEGER
			ACCESS	read-only
			STATUS	current
	DESCRIPTION ""
			::= { mbusD4 11 }

mbusD4VIF03		OBJECT-TYPE
			SYNTAX	INTEGER
			ACCESS	read-only
			STATUS	current
	DESCRIPTION ""
			::= { mbusD4 12 }

mbusD4Value03		OBJECT-TYPE
			SYNTAX	INTEGER
			ACCESS	read-only
			STATUS	current
	DESCRIPTION ""
			::= { mbusD4 13 }

mbusD4VIF04		OBJECT-TYPE
			SYNTAX	INTEGER
			ACCESS	read-only
			STATUS	current
	DESCRIPTION ""
			::= { mbusD4 14 }

mbusD4Value04		OBJECT-TYPE
			SYNTAX	INTEGER
			ACCESS	read-only
			STATUS	current
	DESCRIPTION ""
			::= { mbusD4 15 }

mbusD4VIF05		OBJECT-TYPE
			SYNTAX	INTEGER
			ACCESS	read-only
			STATUS	current
	DESCRIPTION ""
			::= { mbusD4 16 }

mbusD4Value05		OBJECT-TYPE
			SYNTAX	INTEGER
			ACCESS	read-only
			STATUS	current
	DESCRIPTION ""
			::= { mbusD4 17 }

mbusD4VIF06		OBJECT-TYPE
			SYNTAX	INTEGER
			ACCESS	read-only
			STATUS	current
	DESCRIPTION ""
			::= { mbusD4 18 }

mbusD4Value06		OBJECT-TYPE
			SYNTAX	INTEGER
			ACCESS	read-only
			STATUS	current
	DESCRIPTION ""
			::= { mbusD4 19 }

mbusD4VIF07		OBJECT-TYPE
			SYNTAX	INTEGER
			ACCESS	read-only
			STATUS	current
	DESCRIPTION ""
			::= { mbusD4 20 }

mbusD4Value07		OBJECT-TYPE
			SYNTAX	INTEGER
			ACCESS	read-only
			STATUS	current
	DESCRIPTION ""
			::= { mbusD4 21 }

mbusD4VIF08		OBJECT-TYPE
			SYNTAX	INTEGER
			ACCESS	read-only
			STATUS	current
	DESCRIPTION ""
			::= { mbusD4 22 }

mbusD4Value08		OBJECT-TYPE
			SYNTAX	INTEGER
			ACCESS	read-only
			STATUS	current
	DESCRIPTION ""
			::= { mbusD4 23 }

mbusD4VIF09		OBJECT-TYPE
			SYNTAX	INTEGER
			ACCESS	read-only
			STATUS	current
	DESCRIPTION ""
			::= { mbusD4 24 }

mbusD4Value09		OBJECT-TYPE
			SYNTAX	INTEGER
			ACCESS	read-only
			STATUS	current
	DESCRIPTION ""
			::= { mbusD4 25 }

mbusD4VIF0A		OBJECT-TYPE
			SYNTAX	INTEGER
			ACCESS	read-only
			STATUS	current
	DESCRIPTION ""
			::= { mbusD4 26 }

mbusD4Value0A		OBJECT-TYPE
			SYNTAX	INTEGER
			ACCESS	read-only
			STATUS	current
	DESCRIPTION ""
			::= { mbusD4 27 }

mbusD4VIF0B		OBJECT-TYPE
			SYNTAX	INTEGER
			ACCESS	read-only
			STATUS	current
	DESCRIPTION ""
			::= { mbusD4 28 }

mbusD4Value0B		OBJECT-TYPE
			SYNTAX	INTEGER
			ACCESS	read-only
			STATUS	current
	DESCRIPTION ""
			::= { mbusD4 29 }

mbusD4VIF0C		OBJECT-TYPE
			SYNTAX	INTEGER
			ACCESS	read-only
			STATUS	current
	DESCRIPTION ""
			::= { mbusD4 30 }

mbusD4Value0C		OBJECT-TYPE
			SYNTAX	INTEGER
			ACCESS	read-only
			STATUS	current
	DESCRIPTION ""
			::= { mbusD4 31 }

mbusD4VIF0D		OBJECT-TYPE
			SYNTAX	INTEGER
			ACCESS	read-only
			STATUS	current
	DESCRIPTION ""
			::= { mbusD4 32 }

mbusD4Value0D		OBJECT-TYPE
			SYNTAX	INTEGER
			ACCESS	read-only
			STATUS	current
	DESCRIPTION ""
			::= { mbusD4 33 }

mbusD4VIF0E		OBJECT-TYPE
			SYNTAX	INTEGER
			ACCESS	read-only
			STATUS	current
	DESCRIPTION ""
			::= { mbusD4 34 }

mbusD4Value0E		OBJECT-TYPE
			SYNTAX	INTEGER
			ACCESS	read-only
			STATUS	current
	DESCRIPTION ""
			::= { mbusD4 35 }

mbusD4VIF0F		OBJECT-TYPE
			SYNTAX	INTEGER
			ACCESS	read-only
			STATUS	current
	DESCRIPTION ""
			::= { mbusD4 36 }

mbusD4Value0F		OBJECT-TYPE
			SYNTAX	INTEGER
			ACCESS	read-only
			STATUS	current
	DESCRIPTION ""
			::= { mbusD4 37 }

mbusD4VIF10		OBJECT-TYPE
			SYNTAX	INTEGER
			ACCESS	read-only
			STATUS	current
	DESCRIPTION ""
			::= { mbusD4 38 }

mbusD4Value10		OBJECT-TYPE
			SYNTAX	INTEGER
			ACCESS	read-only
			STATUS	current
	DESCRIPTION ""
			::= { mbusD4 39 }

mbusD4VIF11		OBJECT-TYPE
			SYNTAX	INTEGER
			ACCESS	read-only
			STATUS	current
	DESCRIPTION ""
			::= { mbusD4 40 }

mbusD4Value11		OBJECT-TYPE
			SYNTAX	INTEGER
			ACCESS	read-only
			STATUS	current
	DESCRIPTION ""
			::= { mbusD4 41 }

mbusD4VIF12		OBJECT-TYPE
			SYNTAX	INTEGER
			ACCESS	read-only
			STATUS	current
	DESCRIPTION ""
			::= { mbusD4 42 }

mbusD4Value12		OBJECT-TYPE
			SYNTAX	INTEGER
			ACCESS	read-only
			STATUS	current
	DESCRIPTION ""
			::= { mbusD4 43 }

mbusD4VIF13		OBJECT-TYPE
			SYNTAX	INTEGER
			ACCESS	read-only
			STATUS	current
	DESCRIPTION ""
			::= { mbusD4 44 }

mbusD4Value13		OBJECT-TYPE
			SYNTAX	INTEGER
			ACCESS	read-only
			STATUS	current
	DESCRIPTION ""
			::= { mbusD4 45 }

mbusD4VIF14		OBJECT-TYPE
			SYNTAX	INTEGER
			ACCESS	read-only
			STATUS	current
	DESCRIPTION ""
			::= { mbusD4 46 }

mbusD4Value14		OBJECT-TYPE
			SYNTAX	INTEGER
			ACCESS	read-only
			STATUS	current
	DESCRIPTION ""
			::= { mbusD4 47 }

mbusD4VIF15		OBJECT-TYPE
			SYNTAX	INTEGER
			ACCESS	read-only
			STATUS	current
	DESCRIPTION ""
			::= { mbusD4 48 }

mbusD4Value15		OBJECT-TYPE
			SYNTAX	INTEGER
			ACCESS	read-only
			STATUS	current
	DESCRIPTION ""
			::= { mbusD4 49 }

mbusD4VIF16		OBJECT-TYPE
			SYNTAX	INTEGER
			ACCESS	read-only
			STATUS	current
	DESCRIPTION ""
			::= { mbusD4 50 }

mbusD4Value16		OBJECT-TYPE
			SYNTAX	INTEGER
			ACCESS	read-only
			STATUS	current
	DESCRIPTION ""
			::= { mbusD4 51 }

mbusD4VIF17		OBJECT-TYPE
			SYNTAX	INTEGER
			ACCESS	read-only
			STATUS	current
	DESCRIPTION ""
			::= { mbusD4 52 }

mbusD4Value17		OBJECT-TYPE
			SYNTAX	INTEGER
			ACCESS	read-only
			STATUS	current
	DESCRIPTION ""
			::= { mbusD4 53 }

mbusD4VIF18		OBJECT-TYPE
			SYNTAX	INTEGER
			ACCESS	read-only
			STATUS	current
	DESCRIPTION ""
			::= { mbusD4 54 }

mbusD4Value18		OBJECT-TYPE
			SYNTAX	INTEGER
			ACCESS	read-only
			STATUS	current
	DESCRIPTION ""
			::= { mbusD4 55 }

mbusD4VIF19		OBJECT-TYPE
			SYNTAX	INTEGER
			ACCESS	read-only
			STATUS	current
	DESCRIPTION ""
			::= { mbusD4 56 }

mbusD4Value19		OBJECT-TYPE
			SYNTAX	INTEGER
			ACCESS	read-only
			STATUS	current
	DESCRIPTION ""
			::= { mbusD4 57 }

mbusD4VIF1A		OBJECT-TYPE
			SYNTAX	INTEGER
			ACCESS	read-only
			STATUS	current
	DESCRIPTION ""
			::= { mbusD4 58 }

mbusD4Value1A		OBJECT-TYPE
			SYNTAX	INTEGER
			ACCESS	read-only
			STATUS	current
	DESCRIPTION ""
			::= { mbusD4 59 }

mbusD4VIF1B		OBJECT-TYPE
			SYNTAX	INTEGER
			ACCESS	read-only
			STATUS	current
	DESCRIPTION ""
			::= { mbusD4 60 }

mbusD4Value1B		OBJECT-TYPE
			SYNTAX	INTEGER
			ACCESS	read-only
			STATUS	current
	DESCRIPTION ""
			::= { mbusD4 61 }

mbusD4VIF1C		OBJECT-TYPE
			SYNTAX	INTEGER
			ACCESS	read-only
			STATUS	current
	DESCRIPTION ""
			::= { mbusD4 62 }

mbusD4Value1C		OBJECT-TYPE
			SYNTAX	INTEGER
			ACCESS	read-only
			STATUS	current
	DESCRIPTION ""
			::= { mbusD4 63 }

mbusD4VIF1D		OBJECT-TYPE
			SYNTAX	INTEGER
			ACCESS	read-only
			STATUS	current
	DESCRIPTION ""
			::= { mbusD4 64 }

mbusD4Value1D		OBJECT-TYPE
			SYNTAX	INTEGER
			ACCESS	read-only
			STATUS	current
	DESCRIPTION ""
			::= { mbusD4 65 }

mbusD4VIF1E		OBJECT-TYPE
			SYNTAX	INTEGER
			ACCESS	read-only
			STATUS	current
	DESCRIPTION ""
			::= { mbusD4 66 }

mbusD4Value1E		OBJECT-TYPE
			SYNTAX	INTEGER
			ACCESS	read-only
			STATUS	current
	DESCRIPTION ""
			::= { mbusD4 67 }

mbusD4VIF1F		OBJECT-TYPE
			SYNTAX	INTEGER
			ACCESS	read-only
			STATUS	current
	DESCRIPTION ""
			::= { mbusD4 68 }

mbusD4Value1F		OBJECT-TYPE
			SYNTAX	INTEGER
			ACCESS	read-only
			STATUS	current
	DESCRIPTION ""
			::= { mbusD4 69 }

mbusD4VIF20		OBJECT-TYPE
			SYNTAX	INTEGER
			ACCESS	read-only
			STATUS	current
	DESCRIPTION ""
			::= { mbusD4 70 }

mbusD4Value20		OBJECT-TYPE
			SYNTAX	INTEGER
			ACCESS	read-only
			STATUS	current
	DESCRIPTION ""
			::= { mbusD4 71 }

mbusD4VIF21		OBJECT-TYPE
			SYNTAX	INTEGER
			ACCESS	read-only
			STATUS	current
	DESCRIPTION ""
			::= { mbusD4 72 }

mbusD4Value21		OBJECT-TYPE
			SYNTAX	INTEGER
			ACCESS	read-only
			STATUS	current
	DESCRIPTION ""
			::= { mbusD4 73 }

mbusD4VIF22		OBJECT-TYPE
			SYNTAX	INTEGER
			ACCESS	read-only
			STATUS	current
	DESCRIPTION ""
			::= { mbusD4 74 }

mbusD4Value22		OBJECT-TYPE
			SYNTAX	INTEGER
			ACCESS	read-only
			STATUS	current
	DESCRIPTION ""
			::= { mbusD4 75 }

mbusD4VIF23		OBJECT-TYPE
			SYNTAX	INTEGER
			ACCESS	read-only
			STATUS	current
	DESCRIPTION ""
			::= { mbusD4 76 }

mbusD4Value23		OBJECT-TYPE
			SYNTAX	INTEGER
			ACCESS	read-only
			STATUS	current
	DESCRIPTION ""
			::= { mbusD4 77 }

mbusD4VIF24		OBJECT-TYPE
			SYNTAX	INTEGER
			ACCESS	read-only
			STATUS	current
	DESCRIPTION ""
			::= { mbusD4 78 }

mbusD4Value24		OBJECT-TYPE
			SYNTAX	INTEGER
			ACCESS	read-only
			STATUS	current
	DESCRIPTION ""
			::= { mbusD4 79 }

mbusD4VIF25		OBJECT-TYPE
			SYNTAX	INTEGER
			ACCESS	read-only
			STATUS	current
	DESCRIPTION ""
			::= { mbusD4 80 }

mbusD4Value25		OBJECT-TYPE
			SYNTAX	INTEGER
			ACCESS	read-only
			STATUS	current
	DESCRIPTION ""
			::= { mbusD4 81 }

mbusD4VIF26		OBJECT-TYPE
			SYNTAX	INTEGER
			ACCESS	read-only
			STATUS	current
	DESCRIPTION ""
			::= { mbusD4 82 }

mbusD4Value26		OBJECT-TYPE
			SYNTAX	INTEGER
			ACCESS	read-only
			STATUS	current
	DESCRIPTION ""
			::= { mbusD4 83 }

mbusD4VIF27		OBJECT-TYPE
			SYNTAX	INTEGER
			ACCESS	read-only
			STATUS	current
	DESCRIPTION ""
			::= { mbusD4 84 }

mbusD4Value27		OBJECT-TYPE
			SYNTAX	INTEGER
			ACCESS	read-only
			STATUS	current
	DESCRIPTION ""
			::= { mbusD4 85 }

mbusD4VIF28		OBJECT-TYPE
			SYNTAX	INTEGER
			ACCESS	read-only
			STATUS	current
	DESCRIPTION ""
			::= { mbusD4 86 }

mbusD4Value28		OBJECT-TYPE
			SYNTAX	INTEGER
			ACCESS	read-only
			STATUS	current
	DESCRIPTION ""
			::= { mbusD4 87 }

mbusD4VIF29		OBJECT-TYPE
			SYNTAX	INTEGER
			ACCESS	read-only
			STATUS	current
	DESCRIPTION ""
			::= { mbusD4 88 }

mbusD4Value29		OBJECT-TYPE
			SYNTAX	INTEGER
			ACCESS	read-only
			STATUS	current
	DESCRIPTION ""
			::= { mbusD4 89 }

mbusD4VIF2A		OBJECT-TYPE
			SYNTAX	INTEGER
			ACCESS	read-only
			STATUS	current
	DESCRIPTION ""
			::= { mbusD4 90 }

mbusD4Value2A		OBJECT-TYPE
			SYNTAX	INTEGER
			ACCESS	read-only
			STATUS	current
	DESCRIPTION ""
			::= { mbusD4 91 }

mbusD4VIF2B		OBJECT-TYPE
			SYNTAX	INTEGER
			ACCESS	read-only
			STATUS	current
	DESCRIPTION ""
			::= { mbusD4 92 }

mbusD4Value2B		OBJECT-TYPE
			SYNTAX	INTEGER
			ACCESS	read-only
			STATUS	current
	DESCRIPTION ""
			::= { mbusD4 93 }

mbusD4VIF2C		OBJECT-TYPE
			SYNTAX	INTEGER
			ACCESS	read-only
			STATUS	current
	DESCRIPTION ""
			::= { mbusD4 94 }

mbusD4Value2C		OBJECT-TYPE
			SYNTAX	INTEGER
			ACCESS	read-only
			STATUS	current
	DESCRIPTION ""
			::= { mbusD4 95 }

mbusD4VIF2D		OBJECT-TYPE
			SYNTAX	INTEGER
			ACCESS	read-only
			STATUS	current
	DESCRIPTION ""
			::= { mbusD4 96 }

mbusD4Value2D		OBJECT-TYPE
			SYNTAX	INTEGER
			ACCESS	read-only
			STATUS	current
	DESCRIPTION ""
			::= { mbusD4 97 }

mbusD4VIF2E		OBJECT-TYPE
			SYNTAX	INTEGER
			ACCESS	read-only
			STATUS	current
	DESCRIPTION ""
			::= { mbusD4 98 }

mbusD4Value2E		OBJECT-TYPE
			SYNTAX	INTEGER
			ACCESS	read-only
			STATUS	current
	DESCRIPTION ""
			::= { mbusD4 99 }

mbusD4VIF2F		OBJECT-TYPE
			SYNTAX	INTEGER
			ACCESS	read-only
			STATUS	current
	DESCRIPTION ""
			::= { mbusD4 100 }

mbusD4Value2F		OBJECT-TYPE
			SYNTAX	INTEGER
			ACCESS	read-only
			STATUS	current
	DESCRIPTION ""
			::= { mbusD4 101 }

mbusD5			OBJECT IDENTIFIER ::= { mbus 213 }

mbusD5IdNumber		OBJECT-TYPE
			SYNTAX	Gauge
			ACCESS	read-only
			STATUS	current
	DESCRIPTION ""
			::= { mbusD5 1 }

mbusD5Manufacturer	OBJECT-TYPE
			SYNTAX	Gauge
			ACCESS	read-only
			STATUS	current
	DESCRIPTION ""
			::= { mbusD5 2 }

mbusD5Version		OBJECT-TYPE
			SYNTAX	Gauge
			ACCESS	read-only
			STATUS	current
	DESCRIPTION ""
			::= { mbusD5 3 }

mbusD5Medium		OBJECT-TYPE
			SYNTAX	Gauge
			ACCESS	read-only
			STATUS	current
	DESCRIPTION ""
			::= { mbusD5 4 }

mbusD5Status		OBJECT-TYPE
			SYNTAX	Gauge
			ACCESS	read-only
			STATUS	current
	DESCRIPTION ""
			::= { mbusD5 5 }

mbusD5VIF00		OBJECT-TYPE
			SYNTAX	INTEGER
			ACCESS	read-only
			STATUS	current
	DESCRIPTION ""
			::= { mbusD5 6 }

mbusD5Value00		OBJECT-TYPE
			SYNTAX	INTEGER
			ACCESS	read-only
			STATUS	current
	DESCRIPTION ""
			::= { mbusD5 7 }

mbusD5VIF01		OBJECT-TYPE
			SYNTAX	INTEGER
			ACCESS	read-only
			STATUS	current
	DESCRIPTION ""
			::= { mbusD5 8 }

mbusD5Value01		OBJECT-TYPE
			SYNTAX	INTEGER
			ACCESS	read-only
			STATUS	current
	DESCRIPTION ""
			::= { mbusD5 9 }

mbusD5VIF02		OBJECT-TYPE
			SYNTAX	INTEGER
			ACCESS	read-only
			STATUS	current
	DESCRIPTION ""
			::= { mbusD5 10 }

mbusD5Value02		OBJECT-TYPE
			SYNTAX	INTEGER
			ACCESS	read-only
			STATUS	current
	DESCRIPTION ""
			::= { mbusD5 11 }

mbusD5VIF03		OBJECT-TYPE
			SYNTAX	INTEGER
			ACCESS	read-only
			STATUS	current
	DESCRIPTION ""
			::= { mbusD5 12 }

mbusD5Value03		OBJECT-TYPE
			SYNTAX	INTEGER
			ACCESS	read-only
			STATUS	current
	DESCRIPTION ""
			::= { mbusD5 13 }

mbusD5VIF04		OBJECT-TYPE
			SYNTAX	INTEGER
			ACCESS	read-only
			STATUS	current
	DESCRIPTION ""
			::= { mbusD5 14 }

mbusD5Value04		OBJECT-TYPE
			SYNTAX	INTEGER
			ACCESS	read-only
			STATUS	current
	DESCRIPTION ""
			::= { mbusD5 15 }

mbusD5VIF05		OBJECT-TYPE
			SYNTAX	INTEGER
			ACCESS	read-only
			STATUS	current
	DESCRIPTION ""
			::= { mbusD5 16 }

mbusD5Value05		OBJECT-TYPE
			SYNTAX	INTEGER
			ACCESS	read-only
			STATUS	current
	DESCRIPTION ""
			::= { mbusD5 17 }

mbusD5VIF06		OBJECT-TYPE
			SYNTAX	INTEGER
			ACCESS	read-only
			STATUS	current
	DESCRIPTION ""
			::= { mbusD5 18 }

mbusD5Value06		OBJECT-TYPE
			SYNTAX	INTEGER
			ACCESS	read-only
			STATUS	current
	DESCRIPTION ""
			::= { mbusD5 19 }

mbusD5VIF07		OBJECT-TYPE
			SYNTAX	INTEGER
			ACCESS	read-only
			STATUS	current
	DESCRIPTION ""
			::= { mbusD5 20 }

mbusD5Value07		OBJECT-TYPE
			SYNTAX	INTEGER
			ACCESS	read-only
			STATUS	current
	DESCRIPTION ""
			::= { mbusD5 21 }

mbusD5VIF08		OBJECT-TYPE
			SYNTAX	INTEGER
			ACCESS	read-only
			STATUS	current
	DESCRIPTION ""
			::= { mbusD5 22 }

mbusD5Value08		OBJECT-TYPE
			SYNTAX	INTEGER
			ACCESS	read-only
			STATUS	current
	DESCRIPTION ""
			::= { mbusD5 23 }

mbusD5VIF09		OBJECT-TYPE
			SYNTAX	INTEGER
			ACCESS	read-only
			STATUS	current
	DESCRIPTION ""
			::= { mbusD5 24 }

mbusD5Value09		OBJECT-TYPE
			SYNTAX	INTEGER
			ACCESS	read-only
			STATUS	current
	DESCRIPTION ""
			::= { mbusD5 25 }

mbusD5VIF0A		OBJECT-TYPE
			SYNTAX	INTEGER
			ACCESS	read-only
			STATUS	current
	DESCRIPTION ""
			::= { mbusD5 26 }

mbusD5Value0A		OBJECT-TYPE
			SYNTAX	INTEGER
			ACCESS	read-only
			STATUS	current
	DESCRIPTION ""
			::= { mbusD5 27 }

mbusD5VIF0B		OBJECT-TYPE
			SYNTAX	INTEGER
			ACCESS	read-only
			STATUS	current
	DESCRIPTION ""
			::= { mbusD5 28 }

mbusD5Value0B		OBJECT-TYPE
			SYNTAX	INTEGER
			ACCESS	read-only
			STATUS	current
	DESCRIPTION ""
			::= { mbusD5 29 }

mbusD5VIF0C		OBJECT-TYPE
			SYNTAX	INTEGER
			ACCESS	read-only
			STATUS	current
	DESCRIPTION ""
			::= { mbusD5 30 }

mbusD5Value0C		OBJECT-TYPE
			SYNTAX	INTEGER
			ACCESS	read-only
			STATUS	current
	DESCRIPTION ""
			::= { mbusD5 31 }

mbusD5VIF0D		OBJECT-TYPE
			SYNTAX	INTEGER
			ACCESS	read-only
			STATUS	current
	DESCRIPTION ""
			::= { mbusD5 32 }

mbusD5Value0D		OBJECT-TYPE
			SYNTAX	INTEGER
			ACCESS	read-only
			STATUS	current
	DESCRIPTION ""
			::= { mbusD5 33 }

mbusD5VIF0E		OBJECT-TYPE
			SYNTAX	INTEGER
			ACCESS	read-only
			STATUS	current
	DESCRIPTION ""
			::= { mbusD5 34 }

mbusD5Value0E		OBJECT-TYPE
			SYNTAX	INTEGER
			ACCESS	read-only
			STATUS	current
	DESCRIPTION ""
			::= { mbusD5 35 }

mbusD5VIF0F		OBJECT-TYPE
			SYNTAX	INTEGER
			ACCESS	read-only
			STATUS	current
	DESCRIPTION ""
			::= { mbusD5 36 }

mbusD5Value0F		OBJECT-TYPE
			SYNTAX	INTEGER
			ACCESS	read-only
			STATUS	current
	DESCRIPTION ""
			::= { mbusD5 37 }

mbusD5VIF10		OBJECT-TYPE
			SYNTAX	INTEGER
			ACCESS	read-only
			STATUS	current
	DESCRIPTION ""
			::= { mbusD5 38 }

mbusD5Value10		OBJECT-TYPE
			SYNTAX	INTEGER
			ACCESS	read-only
			STATUS	current
	DESCRIPTION ""
			::= { mbusD5 39 }

mbusD5VIF11		OBJECT-TYPE
			SYNTAX	INTEGER
			ACCESS	read-only
			STATUS	current
	DESCRIPTION ""
			::= { mbusD5 40 }

mbusD5Value11		OBJECT-TYPE
			SYNTAX	INTEGER
			ACCESS	read-only
			STATUS	current
	DESCRIPTION ""
			::= { mbusD5 41 }

mbusD5VIF12		OBJECT-TYPE
			SYNTAX	INTEGER
			ACCESS	read-only
			STATUS	current
	DESCRIPTION ""
			::= { mbusD5 42 }

mbusD5Value12		OBJECT-TYPE
			SYNTAX	INTEGER
			ACCESS	read-only
			STATUS	current
	DESCRIPTION ""
			::= { mbusD5 43 }

mbusD5VIF13		OBJECT-TYPE
			SYNTAX	INTEGER
			ACCESS	read-only
			STATUS	current
	DESCRIPTION ""
			::= { mbusD5 44 }

mbusD5Value13		OBJECT-TYPE
			SYNTAX	INTEGER
			ACCESS	read-only
			STATUS	current
	DESCRIPTION ""
			::= { mbusD5 45 }

mbusD5VIF14		OBJECT-TYPE
			SYNTAX	INTEGER
			ACCESS	read-only
			STATUS	current
	DESCRIPTION ""
			::= { mbusD5 46 }

mbusD5Value14		OBJECT-TYPE
			SYNTAX	INTEGER
			ACCESS	read-only
			STATUS	current
	DESCRIPTION ""
			::= { mbusD5 47 }

mbusD5VIF15		OBJECT-TYPE
			SYNTAX	INTEGER
			ACCESS	read-only
			STATUS	current
	DESCRIPTION ""
			::= { mbusD5 48 }

mbusD5Value15		OBJECT-TYPE
			SYNTAX	INTEGER
			ACCESS	read-only
			STATUS	current
	DESCRIPTION ""
			::= { mbusD5 49 }

mbusD5VIF16		OBJECT-TYPE
			SYNTAX	INTEGER
			ACCESS	read-only
			STATUS	current
	DESCRIPTION ""
			::= { mbusD5 50 }

mbusD5Value16		OBJECT-TYPE
			SYNTAX	INTEGER
			ACCESS	read-only
			STATUS	current
	DESCRIPTION ""
			::= { mbusD5 51 }

mbusD5VIF17		OBJECT-TYPE
			SYNTAX	INTEGER
			ACCESS	read-only
			STATUS	current
	DESCRIPTION ""
			::= { mbusD5 52 }

mbusD5Value17		OBJECT-TYPE
			SYNTAX	INTEGER
			ACCESS	read-only
			STATUS	current
	DESCRIPTION ""
			::= { mbusD5 53 }

mbusD5VIF18		OBJECT-TYPE
			SYNTAX	INTEGER
			ACCESS	read-only
			STATUS	current
	DESCRIPTION ""
			::= { mbusD5 54 }

mbusD5Value18		OBJECT-TYPE
			SYNTAX	INTEGER
			ACCESS	read-only
			STATUS	current
	DESCRIPTION ""
			::= { mbusD5 55 }

mbusD5VIF19		OBJECT-TYPE
			SYNTAX	INTEGER
			ACCESS	read-only
			STATUS	current
	DESCRIPTION ""
			::= { mbusD5 56 }

mbusD5Value19		OBJECT-TYPE
			SYNTAX	INTEGER
			ACCESS	read-only
			STATUS	current
	DESCRIPTION ""
			::= { mbusD5 57 }

mbusD5VIF1A		OBJECT-TYPE
			SYNTAX	INTEGER
			ACCESS	read-only
			STATUS	current
	DESCRIPTION ""
			::= { mbusD5 58 }

mbusD5Value1A		OBJECT-TYPE
			SYNTAX	INTEGER
			ACCESS	read-only
			STATUS	current
	DESCRIPTION ""
			::= { mbusD5 59 }

mbusD5VIF1B		OBJECT-TYPE
			SYNTAX	INTEGER
			ACCESS	read-only
			STATUS	current
	DESCRIPTION ""
			::= { mbusD5 60 }

mbusD5Value1B		OBJECT-TYPE
			SYNTAX	INTEGER
			ACCESS	read-only
			STATUS	current
	DESCRIPTION ""
			::= { mbusD5 61 }

mbusD5VIF1C		OBJECT-TYPE
			SYNTAX	INTEGER
			ACCESS	read-only
			STATUS	current
	DESCRIPTION ""
			::= { mbusD5 62 }

mbusD5Value1C		OBJECT-TYPE
			SYNTAX	INTEGER
			ACCESS	read-only
			STATUS	current
	DESCRIPTION ""
			::= { mbusD5 63 }

mbusD5VIF1D		OBJECT-TYPE
			SYNTAX	INTEGER
			ACCESS	read-only
			STATUS	current
	DESCRIPTION ""
			::= { mbusD5 64 }

mbusD5Value1D		OBJECT-TYPE
			SYNTAX	INTEGER
			ACCESS	read-only
			STATUS	current
	DESCRIPTION ""
			::= { mbusD5 65 }

mbusD5VIF1E		OBJECT-TYPE
			SYNTAX	INTEGER
			ACCESS	read-only
			STATUS	current
	DESCRIPTION ""
			::= { mbusD5 66 }

mbusD5Value1E		OBJECT-TYPE
			SYNTAX	INTEGER
			ACCESS	read-only
			STATUS	current
	DESCRIPTION ""
			::= { mbusD5 67 }

mbusD5VIF1F		OBJECT-TYPE
			SYNTAX	INTEGER
			ACCESS	read-only
			STATUS	current
	DESCRIPTION ""
			::= { mbusD5 68 }

mbusD5Value1F		OBJECT-TYPE
			SYNTAX	INTEGER
			ACCESS	read-only
			STATUS	current
	DESCRIPTION ""
			::= { mbusD5 69 }

mbusD5VIF20		OBJECT-TYPE
			SYNTAX	INTEGER
			ACCESS	read-only
			STATUS	current
	DESCRIPTION ""
			::= { mbusD5 70 }

mbusD5Value20		OBJECT-TYPE
			SYNTAX	INTEGER
			ACCESS	read-only
			STATUS	current
	DESCRIPTION ""
			::= { mbusD5 71 }

mbusD5VIF21		OBJECT-TYPE
			SYNTAX	INTEGER
			ACCESS	read-only
			STATUS	current
	DESCRIPTION ""
			::= { mbusD5 72 }

mbusD5Value21		OBJECT-TYPE
			SYNTAX	INTEGER
			ACCESS	read-only
			STATUS	current
	DESCRIPTION ""
			::= { mbusD5 73 }

mbusD5VIF22		OBJECT-TYPE
			SYNTAX	INTEGER
			ACCESS	read-only
			STATUS	current
	DESCRIPTION ""
			::= { mbusD5 74 }

mbusD5Value22		OBJECT-TYPE
			SYNTAX	INTEGER
			ACCESS	read-only
			STATUS	current
	DESCRIPTION ""
			::= { mbusD5 75 }

mbusD5VIF23		OBJECT-TYPE
			SYNTAX	INTEGER
			ACCESS	read-only
			STATUS	current
	DESCRIPTION ""
			::= { mbusD5 76 }

mbusD5Value23		OBJECT-TYPE
			SYNTAX	INTEGER
			ACCESS	read-only
			STATUS	current
	DESCRIPTION ""
			::= { mbusD5 77 }

mbusD5VIF24		OBJECT-TYPE
			SYNTAX	INTEGER
			ACCESS	read-only
			STATUS	current
	DESCRIPTION ""
			::= { mbusD5 78 }

mbusD5Value24		OBJECT-TYPE
			SYNTAX	INTEGER
			ACCESS	read-only
			STATUS	current
	DESCRIPTION ""
			::= { mbusD5 79 }

mbusD5VIF25		OBJECT-TYPE
			SYNTAX	INTEGER
			ACCESS	read-only
			STATUS	current
	DESCRIPTION ""
			::= { mbusD5 80 }

mbusD5Value25		OBJECT-TYPE
			SYNTAX	INTEGER
			ACCESS	read-only
			STATUS	current
	DESCRIPTION ""
			::= { mbusD5 81 }

mbusD5VIF26		OBJECT-TYPE
			SYNTAX	INTEGER
			ACCESS	read-only
			STATUS	current
	DESCRIPTION ""
			::= { mbusD5 82 }

mbusD5Value26		OBJECT-TYPE
			SYNTAX	INTEGER
			ACCESS	read-only
			STATUS	current
	DESCRIPTION ""
			::= { mbusD5 83 }

mbusD5VIF27		OBJECT-TYPE
			SYNTAX	INTEGER
			ACCESS	read-only
			STATUS	current
	DESCRIPTION ""
			::= { mbusD5 84 }

mbusD5Value27		OBJECT-TYPE
			SYNTAX	INTEGER
			ACCESS	read-only
			STATUS	current
	DESCRIPTION ""
			::= { mbusD5 85 }

mbusD5VIF28		OBJECT-TYPE
			SYNTAX	INTEGER
			ACCESS	read-only
			STATUS	current
	DESCRIPTION ""
			::= { mbusD5 86 }

mbusD5Value28		OBJECT-TYPE
			SYNTAX	INTEGER
			ACCESS	read-only
			STATUS	current
	DESCRIPTION ""
			::= { mbusD5 87 }

mbusD5VIF29		OBJECT-TYPE
			SYNTAX	INTEGER
			ACCESS	read-only
			STATUS	current
	DESCRIPTION ""
			::= { mbusD5 88 }

mbusD5Value29		OBJECT-TYPE
			SYNTAX	INTEGER
			ACCESS	read-only
			STATUS	current
	DESCRIPTION ""
			::= { mbusD5 89 }

mbusD5VIF2A		OBJECT-TYPE
			SYNTAX	INTEGER
			ACCESS	read-only
			STATUS	current
	DESCRIPTION ""
			::= { mbusD5 90 }

mbusD5Value2A		OBJECT-TYPE
			SYNTAX	INTEGER
			ACCESS	read-only
			STATUS	current
	DESCRIPTION ""
			::= { mbusD5 91 }

mbusD5VIF2B		OBJECT-TYPE
			SYNTAX	INTEGER
			ACCESS	read-only
			STATUS	current
	DESCRIPTION ""
			::= { mbusD5 92 }

mbusD5Value2B		OBJECT-TYPE
			SYNTAX	INTEGER
			ACCESS	read-only
			STATUS	current
	DESCRIPTION ""
			::= { mbusD5 93 }

mbusD5VIF2C		OBJECT-TYPE
			SYNTAX	INTEGER
			ACCESS	read-only
			STATUS	current
	DESCRIPTION ""
			::= { mbusD5 94 }

mbusD5Value2C		OBJECT-TYPE
			SYNTAX	INTEGER
			ACCESS	read-only
			STATUS	current
	DESCRIPTION ""
			::= { mbusD5 95 }

mbusD5VIF2D		OBJECT-TYPE
			SYNTAX	INTEGER
			ACCESS	read-only
			STATUS	current
	DESCRIPTION ""
			::= { mbusD5 96 }

mbusD5Value2D		OBJECT-TYPE
			SYNTAX	INTEGER
			ACCESS	read-only
			STATUS	current
	DESCRIPTION ""
			::= { mbusD5 97 }

mbusD5VIF2E		OBJECT-TYPE
			SYNTAX	INTEGER
			ACCESS	read-only
			STATUS	current
	DESCRIPTION ""
			::= { mbusD5 98 }

mbusD5Value2E		OBJECT-TYPE
			SYNTAX	INTEGER
			ACCESS	read-only
			STATUS	current
	DESCRIPTION ""
			::= { mbusD5 99 }

mbusD5VIF2F		OBJECT-TYPE
			SYNTAX	INTEGER
			ACCESS	read-only
			STATUS	current
	DESCRIPTION ""
			::= { mbusD5 100 }

mbusD5Value2F		OBJECT-TYPE
			SYNTAX	INTEGER
			ACCESS	read-only
			STATUS	current
	DESCRIPTION ""
			::= { mbusD5 101 }

mbusD6			OBJECT IDENTIFIER ::= { mbus 214 }

mbusD6IdNumber		OBJECT-TYPE
			SYNTAX	Gauge
			ACCESS	read-only
			STATUS	current
	DESCRIPTION ""
			::= { mbusD6 1 }

mbusD6Manufacturer	OBJECT-TYPE
			SYNTAX	Gauge
			ACCESS	read-only
			STATUS	current
	DESCRIPTION ""
			::= { mbusD6 2 }

mbusD6Version		OBJECT-TYPE
			SYNTAX	Gauge
			ACCESS	read-only
			STATUS	current
	DESCRIPTION ""
			::= { mbusD6 3 }

mbusD6Medium		OBJECT-TYPE
			SYNTAX	Gauge
			ACCESS	read-only
			STATUS	current
	DESCRIPTION ""
			::= { mbusD6 4 }

mbusD6Status		OBJECT-TYPE
			SYNTAX	Gauge
			ACCESS	read-only
			STATUS	current
	DESCRIPTION ""
			::= { mbusD6 5 }

mbusD6VIF00		OBJECT-TYPE
			SYNTAX	INTEGER
			ACCESS	read-only
			STATUS	current
	DESCRIPTION ""
			::= { mbusD6 6 }

mbusD6Value00		OBJECT-TYPE
			SYNTAX	INTEGER
			ACCESS	read-only
			STATUS	current
	DESCRIPTION ""
			::= { mbusD6 7 }

mbusD6VIF01		OBJECT-TYPE
			SYNTAX	INTEGER
			ACCESS	read-only
			STATUS	current
	DESCRIPTION ""
			::= { mbusD6 8 }

mbusD6Value01		OBJECT-TYPE
			SYNTAX	INTEGER
			ACCESS	read-only
			STATUS	current
	DESCRIPTION ""
			::= { mbusD6 9 }

mbusD6VIF02		OBJECT-TYPE
			SYNTAX	INTEGER
			ACCESS	read-only
			STATUS	current
	DESCRIPTION ""
			::= { mbusD6 10 }

mbusD6Value02		OBJECT-TYPE
			SYNTAX	INTEGER
			ACCESS	read-only
			STATUS	current
	DESCRIPTION ""
			::= { mbusD6 11 }

mbusD6VIF03		OBJECT-TYPE
			SYNTAX	INTEGER
			ACCESS	read-only
			STATUS	current
	DESCRIPTION ""
			::= { mbusD6 12 }

mbusD6Value03		OBJECT-TYPE
			SYNTAX	INTEGER
			ACCESS	read-only
			STATUS	current
	DESCRIPTION ""
			::= { mbusD6 13 }

mbusD6VIF04		OBJECT-TYPE
			SYNTAX	INTEGER
			ACCESS	read-only
			STATUS	current
	DESCRIPTION ""
			::= { mbusD6 14 }

mbusD6Value04		OBJECT-TYPE
			SYNTAX	INTEGER
			ACCESS	read-only
			STATUS	current
	DESCRIPTION ""
			::= { mbusD6 15 }

mbusD6VIF05		OBJECT-TYPE
			SYNTAX	INTEGER
			ACCESS	read-only
			STATUS	current
	DESCRIPTION ""
			::= { mbusD6 16 }

mbusD6Value05		OBJECT-TYPE
			SYNTAX	INTEGER
			ACCESS	read-only
			STATUS	current
	DESCRIPTION ""
			::= { mbusD6 17 }

mbusD6VIF06		OBJECT-TYPE
			SYNTAX	INTEGER
			ACCESS	read-only
			STATUS	current
	DESCRIPTION ""
			::= { mbusD6 18 }

mbusD6Value06		OBJECT-TYPE
			SYNTAX	INTEGER
			ACCESS	read-only
			STATUS	current
	DESCRIPTION ""
			::= { mbusD6 19 }

mbusD6VIF07		OBJECT-TYPE
			SYNTAX	INTEGER
			ACCESS	read-only
			STATUS	current
	DESCRIPTION ""
			::= { mbusD6 20 }

mbusD6Value07		OBJECT-TYPE
			SYNTAX	INTEGER
			ACCESS	read-only
			STATUS	current
	DESCRIPTION ""
			::= { mbusD6 21 }

mbusD6VIF08		OBJECT-TYPE
			SYNTAX	INTEGER
			ACCESS	read-only
			STATUS	current
	DESCRIPTION ""
			::= { mbusD6 22 }

mbusD6Value08		OBJECT-TYPE
			SYNTAX	INTEGER
			ACCESS	read-only
			STATUS	current
	DESCRIPTION ""
			::= { mbusD6 23 }

mbusD6VIF09		OBJECT-TYPE
			SYNTAX	INTEGER
			ACCESS	read-only
			STATUS	current
	DESCRIPTION ""
			::= { mbusD6 24 }

mbusD6Value09		OBJECT-TYPE
			SYNTAX	INTEGER
			ACCESS	read-only
			STATUS	current
	DESCRIPTION ""
			::= { mbusD6 25 }

mbusD6VIF0A		OBJECT-TYPE
			SYNTAX	INTEGER
			ACCESS	read-only
			STATUS	current
	DESCRIPTION ""
			::= { mbusD6 26 }

mbusD6Value0A		OBJECT-TYPE
			SYNTAX	INTEGER
			ACCESS	read-only
			STATUS	current
	DESCRIPTION ""
			::= { mbusD6 27 }

mbusD6VIF0B		OBJECT-TYPE
			SYNTAX	INTEGER
			ACCESS	read-only
			STATUS	current
	DESCRIPTION ""
			::= { mbusD6 28 }

mbusD6Value0B		OBJECT-TYPE
			SYNTAX	INTEGER
			ACCESS	read-only
			STATUS	current
	DESCRIPTION ""
			::= { mbusD6 29 }

mbusD6VIF0C		OBJECT-TYPE
			SYNTAX	INTEGER
			ACCESS	read-only
			STATUS	current
	DESCRIPTION ""
			::= { mbusD6 30 }

mbusD6Value0C		OBJECT-TYPE
			SYNTAX	INTEGER
			ACCESS	read-only
			STATUS	current
	DESCRIPTION ""
			::= { mbusD6 31 }

mbusD6VIF0D		OBJECT-TYPE
			SYNTAX	INTEGER
			ACCESS	read-only
			STATUS	current
	DESCRIPTION ""
			::= { mbusD6 32 }

mbusD6Value0D		OBJECT-TYPE
			SYNTAX	INTEGER
			ACCESS	read-only
			STATUS	current
	DESCRIPTION ""
			::= { mbusD6 33 }

mbusD6VIF0E		OBJECT-TYPE
			SYNTAX	INTEGER
			ACCESS	read-only
			STATUS	current
	DESCRIPTION ""
			::= { mbusD6 34 }

mbusD6Value0E		OBJECT-TYPE
			SYNTAX	INTEGER
			ACCESS	read-only
			STATUS	current
	DESCRIPTION ""
			::= { mbusD6 35 }

mbusD6VIF0F		OBJECT-TYPE
			SYNTAX	INTEGER
			ACCESS	read-only
			STATUS	current
	DESCRIPTION ""
			::= { mbusD6 36 }

mbusD6Value0F		OBJECT-TYPE
			SYNTAX	INTEGER
			ACCESS	read-only
			STATUS	current
	DESCRIPTION ""
			::= { mbusD6 37 }

mbusD6VIF10		OBJECT-TYPE
			SYNTAX	INTEGER
			ACCESS	read-only
			STATUS	current
	DESCRIPTION ""
			::= { mbusD6 38 }

mbusD6Value10		OBJECT-TYPE
			SYNTAX	INTEGER
			ACCESS	read-only
			STATUS	current
	DESCRIPTION ""
			::= { mbusD6 39 }

mbusD6VIF11		OBJECT-TYPE
			SYNTAX	INTEGER
			ACCESS	read-only
			STATUS	current
	DESCRIPTION ""
			::= { mbusD6 40 }

mbusD6Value11		OBJECT-TYPE
			SYNTAX	INTEGER
			ACCESS	read-only
			STATUS	current
	DESCRIPTION ""
			::= { mbusD6 41 }

mbusD6VIF12		OBJECT-TYPE
			SYNTAX	INTEGER
			ACCESS	read-only
			STATUS	current
	DESCRIPTION ""
			::= { mbusD6 42 }

mbusD6Value12		OBJECT-TYPE
			SYNTAX	INTEGER
			ACCESS	read-only
			STATUS	current
	DESCRIPTION ""
			::= { mbusD6 43 }

mbusD6VIF13		OBJECT-TYPE
			SYNTAX	INTEGER
			ACCESS	read-only
			STATUS	current
	DESCRIPTION ""
			::= { mbusD6 44 }

mbusD6Value13		OBJECT-TYPE
			SYNTAX	INTEGER
			ACCESS	read-only
			STATUS	current
	DESCRIPTION ""
			::= { mbusD6 45 }

mbusD6VIF14		OBJECT-TYPE
			SYNTAX	INTEGER
			ACCESS	read-only
			STATUS	current
	DESCRIPTION ""
			::= { mbusD6 46 }

mbusD6Value14		OBJECT-TYPE
			SYNTAX	INTEGER
			ACCESS	read-only
			STATUS	current
	DESCRIPTION ""
			::= { mbusD6 47 }

mbusD6VIF15		OBJECT-TYPE
			SYNTAX	INTEGER
			ACCESS	read-only
			STATUS	current
	DESCRIPTION ""
			::= { mbusD6 48 }

mbusD6Value15		OBJECT-TYPE
			SYNTAX	INTEGER
			ACCESS	read-only
			STATUS	current
	DESCRIPTION ""
			::= { mbusD6 49 }

mbusD6VIF16		OBJECT-TYPE
			SYNTAX	INTEGER
			ACCESS	read-only
			STATUS	current
	DESCRIPTION ""
			::= { mbusD6 50 }

mbusD6Value16		OBJECT-TYPE
			SYNTAX	INTEGER
			ACCESS	read-only
			STATUS	current
	DESCRIPTION ""
			::= { mbusD6 51 }

mbusD6VIF17		OBJECT-TYPE
			SYNTAX	INTEGER
			ACCESS	read-only
			STATUS	current
	DESCRIPTION ""
			::= { mbusD6 52 }

mbusD6Value17		OBJECT-TYPE
			SYNTAX	INTEGER
			ACCESS	read-only
			STATUS	current
	DESCRIPTION ""
			::= { mbusD6 53 }

mbusD6VIF18		OBJECT-TYPE
			SYNTAX	INTEGER
			ACCESS	read-only
			STATUS	current
	DESCRIPTION ""
			::= { mbusD6 54 }

mbusD6Value18		OBJECT-TYPE
			SYNTAX	INTEGER
			ACCESS	read-only
			STATUS	current
	DESCRIPTION ""
			::= { mbusD6 55 }

mbusD6VIF19		OBJECT-TYPE
			SYNTAX	INTEGER
			ACCESS	read-only
			STATUS	current
	DESCRIPTION ""
			::= { mbusD6 56 }

mbusD6Value19		OBJECT-TYPE
			SYNTAX	INTEGER
			ACCESS	read-only
			STATUS	current
	DESCRIPTION ""
			::= { mbusD6 57 }

mbusD6VIF1A		OBJECT-TYPE
			SYNTAX	INTEGER
			ACCESS	read-only
			STATUS	current
	DESCRIPTION ""
			::= { mbusD6 58 }

mbusD6Value1A		OBJECT-TYPE
			SYNTAX	INTEGER
			ACCESS	read-only
			STATUS	current
	DESCRIPTION ""
			::= { mbusD6 59 }

mbusD6VIF1B		OBJECT-TYPE
			SYNTAX	INTEGER
			ACCESS	read-only
			STATUS	current
	DESCRIPTION ""
			::= { mbusD6 60 }

mbusD6Value1B		OBJECT-TYPE
			SYNTAX	INTEGER
			ACCESS	read-only
			STATUS	current
	DESCRIPTION ""
			::= { mbusD6 61 }

mbusD6VIF1C		OBJECT-TYPE
			SYNTAX	INTEGER
			ACCESS	read-only
			STATUS	current
	DESCRIPTION ""
			::= { mbusD6 62 }

mbusD6Value1C		OBJECT-TYPE
			SYNTAX	INTEGER
			ACCESS	read-only
			STATUS	current
	DESCRIPTION ""
			::= { mbusD6 63 }

mbusD6VIF1D		OBJECT-TYPE
			SYNTAX	INTEGER
			ACCESS	read-only
			STATUS	current
	DESCRIPTION ""
			::= { mbusD6 64 }

mbusD6Value1D		OBJECT-TYPE
			SYNTAX	INTEGER
			ACCESS	read-only
			STATUS	current
	DESCRIPTION ""
			::= { mbusD6 65 }

mbusD6VIF1E		OBJECT-TYPE
			SYNTAX	INTEGER
			ACCESS	read-only
			STATUS	current
	DESCRIPTION ""
			::= { mbusD6 66 }

mbusD6Value1E		OBJECT-TYPE
			SYNTAX	INTEGER
			ACCESS	read-only
			STATUS	current
	DESCRIPTION ""
			::= { mbusD6 67 }

mbusD6VIF1F		OBJECT-TYPE
			SYNTAX	INTEGER
			ACCESS	read-only
			STATUS	current
	DESCRIPTION ""
			::= { mbusD6 68 }

mbusD6Value1F		OBJECT-TYPE
			SYNTAX	INTEGER
			ACCESS	read-only
			STATUS	current
	DESCRIPTION ""
			::= { mbusD6 69 }

mbusD6VIF20		OBJECT-TYPE
			SYNTAX	INTEGER
			ACCESS	read-only
			STATUS	current
	DESCRIPTION ""
			::= { mbusD6 70 }

mbusD6Value20		OBJECT-TYPE
			SYNTAX	INTEGER
			ACCESS	read-only
			STATUS	current
	DESCRIPTION ""
			::= { mbusD6 71 }

mbusD6VIF21		OBJECT-TYPE
			SYNTAX	INTEGER
			ACCESS	read-only
			STATUS	current
	DESCRIPTION ""
			::= { mbusD6 72 }

mbusD6Value21		OBJECT-TYPE
			SYNTAX	INTEGER
			ACCESS	read-only
			STATUS	current
	DESCRIPTION ""
			::= { mbusD6 73 }

mbusD6VIF22		OBJECT-TYPE
			SYNTAX	INTEGER
			ACCESS	read-only
			STATUS	current
	DESCRIPTION ""
			::= { mbusD6 74 }

mbusD6Value22		OBJECT-TYPE
			SYNTAX	INTEGER
			ACCESS	read-only
			STATUS	current
	DESCRIPTION ""
			::= { mbusD6 75 }

mbusD6VIF23		OBJECT-TYPE
			SYNTAX	INTEGER
			ACCESS	read-only
			STATUS	current
	DESCRIPTION ""
			::= { mbusD6 76 }

mbusD6Value23		OBJECT-TYPE
			SYNTAX	INTEGER
			ACCESS	read-only
			STATUS	current
	DESCRIPTION ""
			::= { mbusD6 77 }

mbusD6VIF24		OBJECT-TYPE
			SYNTAX	INTEGER
			ACCESS	read-only
			STATUS	current
	DESCRIPTION ""
			::= { mbusD6 78 }

mbusD6Value24		OBJECT-TYPE
			SYNTAX	INTEGER
			ACCESS	read-only
			STATUS	current
	DESCRIPTION ""
			::= { mbusD6 79 }

mbusD6VIF25		OBJECT-TYPE
			SYNTAX	INTEGER
			ACCESS	read-only
			STATUS	current
	DESCRIPTION ""
			::= { mbusD6 80 }

mbusD6Value25		OBJECT-TYPE
			SYNTAX	INTEGER
			ACCESS	read-only
			STATUS	current
	DESCRIPTION ""
			::= { mbusD6 81 }

mbusD6VIF26		OBJECT-TYPE
			SYNTAX	INTEGER
			ACCESS	read-only
			STATUS	current
	DESCRIPTION ""
			::= { mbusD6 82 }

mbusD6Value26		OBJECT-TYPE
			SYNTAX	INTEGER
			ACCESS	read-only
			STATUS	current
	DESCRIPTION ""
			::= { mbusD6 83 }

mbusD6VIF27		OBJECT-TYPE
			SYNTAX	INTEGER
			ACCESS	read-only
			STATUS	current
	DESCRIPTION ""
			::= { mbusD6 84 }

mbusD6Value27		OBJECT-TYPE
			SYNTAX	INTEGER
			ACCESS	read-only
			STATUS	current
	DESCRIPTION ""
			::= { mbusD6 85 }

mbusD6VIF28		OBJECT-TYPE
			SYNTAX	INTEGER
			ACCESS	read-only
			STATUS	current
	DESCRIPTION ""
			::= { mbusD6 86 }

mbusD6Value28		OBJECT-TYPE
			SYNTAX	INTEGER
			ACCESS	read-only
			STATUS	current
	DESCRIPTION ""
			::= { mbusD6 87 }

mbusD6VIF29		OBJECT-TYPE
			SYNTAX	INTEGER
			ACCESS	read-only
			STATUS	current
	DESCRIPTION ""
			::= { mbusD6 88 }

mbusD6Value29		OBJECT-TYPE
			SYNTAX	INTEGER
			ACCESS	read-only
			STATUS	current
	DESCRIPTION ""
			::= { mbusD6 89 }

mbusD6VIF2A		OBJECT-TYPE
			SYNTAX	INTEGER
			ACCESS	read-only
			STATUS	current
	DESCRIPTION ""
			::= { mbusD6 90 }

mbusD6Value2A		OBJECT-TYPE
			SYNTAX	INTEGER
			ACCESS	read-only
			STATUS	current
	DESCRIPTION ""
			::= { mbusD6 91 }

mbusD6VIF2B		OBJECT-TYPE
			SYNTAX	INTEGER
			ACCESS	read-only
			STATUS	current
	DESCRIPTION ""
			::= { mbusD6 92 }

mbusD6Value2B		OBJECT-TYPE
			SYNTAX	INTEGER
			ACCESS	read-only
			STATUS	current
	DESCRIPTION ""
			::= { mbusD6 93 }

mbusD6VIF2C		OBJECT-TYPE
			SYNTAX	INTEGER
			ACCESS	read-only
			STATUS	current
	DESCRIPTION ""
			::= { mbusD6 94 }

mbusD6Value2C		OBJECT-TYPE
			SYNTAX	INTEGER
			ACCESS	read-only
			STATUS	current
	DESCRIPTION ""
			::= { mbusD6 95 }

mbusD6VIF2D		OBJECT-TYPE
			SYNTAX	INTEGER
			ACCESS	read-only
			STATUS	current
	DESCRIPTION ""
			::= { mbusD6 96 }

mbusD6Value2D		OBJECT-TYPE
			SYNTAX	INTEGER
			ACCESS	read-only
			STATUS	current
	DESCRIPTION ""
			::= { mbusD6 97 }

mbusD6VIF2E		OBJECT-TYPE
			SYNTAX	INTEGER
			ACCESS	read-only
			STATUS	current
	DESCRIPTION ""
			::= { mbusD6 98 }

mbusD6Value2E		OBJECT-TYPE
			SYNTAX	INTEGER
			ACCESS	read-only
			STATUS	current
	DESCRIPTION ""
			::= { mbusD6 99 }

mbusD6VIF2F		OBJECT-TYPE
			SYNTAX	INTEGER
			ACCESS	read-only
			STATUS	current
	DESCRIPTION ""
			::= { mbusD6 100 }

mbusD6Value2F		OBJECT-TYPE
			SYNTAX	INTEGER
			ACCESS	read-only
			STATUS	current
	DESCRIPTION ""
			::= { mbusD6 101 }

mbusD7			OBJECT IDENTIFIER ::= { mbus 215 }

mbusD7IdNumber		OBJECT-TYPE
			SYNTAX	Gauge
			ACCESS	read-only
			STATUS	current
	DESCRIPTION ""
			::= { mbusD7 1 }

mbusD7Manufacturer	OBJECT-TYPE
			SYNTAX	Gauge
			ACCESS	read-only
			STATUS	current
	DESCRIPTION ""
			::= { mbusD7 2 }

mbusD7Version		OBJECT-TYPE
			SYNTAX	Gauge
			ACCESS	read-only
			STATUS	current
	DESCRIPTION ""
			::= { mbusD7 3 }

mbusD7Medium		OBJECT-TYPE
			SYNTAX	Gauge
			ACCESS	read-only
			STATUS	current
	DESCRIPTION ""
			::= { mbusD7 4 }

mbusD7Status		OBJECT-TYPE
			SYNTAX	Gauge
			ACCESS	read-only
			STATUS	current
	DESCRIPTION ""
			::= { mbusD7 5 }

mbusD7VIF00		OBJECT-TYPE
			SYNTAX	INTEGER
			ACCESS	read-only
			STATUS	current
	DESCRIPTION ""
			::= { mbusD7 6 }

mbusD7Value00		OBJECT-TYPE
			SYNTAX	INTEGER
			ACCESS	read-only
			STATUS	current
	DESCRIPTION ""
			::= { mbusD7 7 }

mbusD7VIF01		OBJECT-TYPE
			SYNTAX	INTEGER
			ACCESS	read-only
			STATUS	current
	DESCRIPTION ""
			::= { mbusD7 8 }

mbusD7Value01		OBJECT-TYPE
			SYNTAX	INTEGER
			ACCESS	read-only
			STATUS	current
	DESCRIPTION ""
			::= { mbusD7 9 }

mbusD7VIF02		OBJECT-TYPE
			SYNTAX	INTEGER
			ACCESS	read-only
			STATUS	current
	DESCRIPTION ""
			::= { mbusD7 10 }

mbusD7Value02		OBJECT-TYPE
			SYNTAX	INTEGER
			ACCESS	read-only
			STATUS	current
	DESCRIPTION ""
			::= { mbusD7 11 }

mbusD7VIF03		OBJECT-TYPE
			SYNTAX	INTEGER
			ACCESS	read-only
			STATUS	current
	DESCRIPTION ""
			::= { mbusD7 12 }

mbusD7Value03		OBJECT-TYPE
			SYNTAX	INTEGER
			ACCESS	read-only
			STATUS	current
	DESCRIPTION ""
			::= { mbusD7 13 }

mbusD7VIF04		OBJECT-TYPE
			SYNTAX	INTEGER
			ACCESS	read-only
			STATUS	current
	DESCRIPTION ""
			::= { mbusD7 14 }

mbusD7Value04		OBJECT-TYPE
			SYNTAX	INTEGER
			ACCESS	read-only
			STATUS	current
	DESCRIPTION ""
			::= { mbusD7 15 }

mbusD7VIF05		OBJECT-TYPE
			SYNTAX	INTEGER
			ACCESS	read-only
			STATUS	current
	DESCRIPTION ""
			::= { mbusD7 16 }

mbusD7Value05		OBJECT-TYPE
			SYNTAX	INTEGER
			ACCESS	read-only
			STATUS	current
	DESCRIPTION ""
			::= { mbusD7 17 }

mbusD7VIF06		OBJECT-TYPE
			SYNTAX	INTEGER
			ACCESS	read-only
			STATUS	current
	DESCRIPTION ""
			::= { mbusD7 18 }

mbusD7Value06		OBJECT-TYPE
			SYNTAX	INTEGER
			ACCESS	read-only
			STATUS	current
	DESCRIPTION ""
			::= { mbusD7 19 }

mbusD7VIF07		OBJECT-TYPE
			SYNTAX	INTEGER
			ACCESS	read-only
			STATUS	current
	DESCRIPTION ""
			::= { mbusD7 20 }

mbusD7Value07		OBJECT-TYPE
			SYNTAX	INTEGER
			ACCESS	read-only
			STATUS	current
	DESCRIPTION ""
			::= { mbusD7 21 }

mbusD7VIF08		OBJECT-TYPE
			SYNTAX	INTEGER
			ACCESS	read-only
			STATUS	current
	DESCRIPTION ""
			::= { mbusD7 22 }

mbusD7Value08		OBJECT-TYPE
			SYNTAX	INTEGER
			ACCESS	read-only
			STATUS	current
	DESCRIPTION ""
			::= { mbusD7 23 }

mbusD7VIF09		OBJECT-TYPE
			SYNTAX	INTEGER
			ACCESS	read-only
			STATUS	current
	DESCRIPTION ""
			::= { mbusD7 24 }

mbusD7Value09		OBJECT-TYPE
			SYNTAX	INTEGER
			ACCESS	read-only
			STATUS	current
	DESCRIPTION ""
			::= { mbusD7 25 }

mbusD7VIF0A		OBJECT-TYPE
			SYNTAX	INTEGER
			ACCESS	read-only
			STATUS	current
	DESCRIPTION ""
			::= { mbusD7 26 }

mbusD7Value0A		OBJECT-TYPE
			SYNTAX	INTEGER
			ACCESS	read-only
			STATUS	current
	DESCRIPTION ""
			::= { mbusD7 27 }

mbusD7VIF0B		OBJECT-TYPE
			SYNTAX	INTEGER
			ACCESS	read-only
			STATUS	current
	DESCRIPTION ""
			::= { mbusD7 28 }

mbusD7Value0B		OBJECT-TYPE
			SYNTAX	INTEGER
			ACCESS	read-only
			STATUS	current
	DESCRIPTION ""
			::= { mbusD7 29 }

mbusD7VIF0C		OBJECT-TYPE
			SYNTAX	INTEGER
			ACCESS	read-only
			STATUS	current
	DESCRIPTION ""
			::= { mbusD7 30 }

mbusD7Value0C		OBJECT-TYPE
			SYNTAX	INTEGER
			ACCESS	read-only
			STATUS	current
	DESCRIPTION ""
			::= { mbusD7 31 }

mbusD7VIF0D		OBJECT-TYPE
			SYNTAX	INTEGER
			ACCESS	read-only
			STATUS	current
	DESCRIPTION ""
			::= { mbusD7 32 }

mbusD7Value0D		OBJECT-TYPE
			SYNTAX	INTEGER
			ACCESS	read-only
			STATUS	current
	DESCRIPTION ""
			::= { mbusD7 33 }

mbusD7VIF0E		OBJECT-TYPE
			SYNTAX	INTEGER
			ACCESS	read-only
			STATUS	current
	DESCRIPTION ""
			::= { mbusD7 34 }

mbusD7Value0E		OBJECT-TYPE
			SYNTAX	INTEGER
			ACCESS	read-only
			STATUS	current
	DESCRIPTION ""
			::= { mbusD7 35 }

mbusD7VIF0F		OBJECT-TYPE
			SYNTAX	INTEGER
			ACCESS	read-only
			STATUS	current
	DESCRIPTION ""
			::= { mbusD7 36 }

mbusD7Value0F		OBJECT-TYPE
			SYNTAX	INTEGER
			ACCESS	read-only
			STATUS	current
	DESCRIPTION ""
			::= { mbusD7 37 }

mbusD7VIF10		OBJECT-TYPE
			SYNTAX	INTEGER
			ACCESS	read-only
			STATUS	current
	DESCRIPTION ""
			::= { mbusD7 38 }

mbusD7Value10		OBJECT-TYPE
			SYNTAX	INTEGER
			ACCESS	read-only
			STATUS	current
	DESCRIPTION ""
			::= { mbusD7 39 }

mbusD7VIF11		OBJECT-TYPE
			SYNTAX	INTEGER
			ACCESS	read-only
			STATUS	current
	DESCRIPTION ""
			::= { mbusD7 40 }

mbusD7Value11		OBJECT-TYPE
			SYNTAX	INTEGER
			ACCESS	read-only
			STATUS	current
	DESCRIPTION ""
			::= { mbusD7 41 }

mbusD7VIF12		OBJECT-TYPE
			SYNTAX	INTEGER
			ACCESS	read-only
			STATUS	current
	DESCRIPTION ""
			::= { mbusD7 42 }

mbusD7Value12		OBJECT-TYPE
			SYNTAX	INTEGER
			ACCESS	read-only
			STATUS	current
	DESCRIPTION ""
			::= { mbusD7 43 }

mbusD7VIF13		OBJECT-TYPE
			SYNTAX	INTEGER
			ACCESS	read-only
			STATUS	current
	DESCRIPTION ""
			::= { mbusD7 44 }

mbusD7Value13		OBJECT-TYPE
			SYNTAX	INTEGER
			ACCESS	read-only
			STATUS	current
	DESCRIPTION ""
			::= { mbusD7 45 }

mbusD7VIF14		OBJECT-TYPE
			SYNTAX	INTEGER
			ACCESS	read-only
			STATUS	current
	DESCRIPTION ""
			::= { mbusD7 46 }

mbusD7Value14		OBJECT-TYPE
			SYNTAX	INTEGER
			ACCESS	read-only
			STATUS	current
	DESCRIPTION ""
			::= { mbusD7 47 }

mbusD7VIF15		OBJECT-TYPE
			SYNTAX	INTEGER
			ACCESS	read-only
			STATUS	current
	DESCRIPTION ""
			::= { mbusD7 48 }

mbusD7Value15		OBJECT-TYPE
			SYNTAX	INTEGER
			ACCESS	read-only
			STATUS	current
	DESCRIPTION ""
			::= { mbusD7 49 }

mbusD7VIF16		OBJECT-TYPE
			SYNTAX	INTEGER
			ACCESS	read-only
			STATUS	current
	DESCRIPTION ""
			::= { mbusD7 50 }

mbusD7Value16		OBJECT-TYPE
			SYNTAX	INTEGER
			ACCESS	read-only
			STATUS	current
	DESCRIPTION ""
			::= { mbusD7 51 }

mbusD7VIF17		OBJECT-TYPE
			SYNTAX	INTEGER
			ACCESS	read-only
			STATUS	current
	DESCRIPTION ""
			::= { mbusD7 52 }

mbusD7Value17		OBJECT-TYPE
			SYNTAX	INTEGER
			ACCESS	read-only
			STATUS	current
	DESCRIPTION ""
			::= { mbusD7 53 }

mbusD7VIF18		OBJECT-TYPE
			SYNTAX	INTEGER
			ACCESS	read-only
			STATUS	current
	DESCRIPTION ""
			::= { mbusD7 54 }

mbusD7Value18		OBJECT-TYPE
			SYNTAX	INTEGER
			ACCESS	read-only
			STATUS	current
	DESCRIPTION ""
			::= { mbusD7 55 }

mbusD7VIF19		OBJECT-TYPE
			SYNTAX	INTEGER
			ACCESS	read-only
			STATUS	current
	DESCRIPTION ""
			::= { mbusD7 56 }

mbusD7Value19		OBJECT-TYPE
			SYNTAX	INTEGER
			ACCESS	read-only
			STATUS	current
	DESCRIPTION ""
			::= { mbusD7 57 }

mbusD7VIF1A		OBJECT-TYPE
			SYNTAX	INTEGER
			ACCESS	read-only
			STATUS	current
	DESCRIPTION ""
			::= { mbusD7 58 }

mbusD7Value1A		OBJECT-TYPE
			SYNTAX	INTEGER
			ACCESS	read-only
			STATUS	current
	DESCRIPTION ""
			::= { mbusD7 59 }

mbusD7VIF1B		OBJECT-TYPE
			SYNTAX	INTEGER
			ACCESS	read-only
			STATUS	current
	DESCRIPTION ""
			::= { mbusD7 60 }

mbusD7Value1B		OBJECT-TYPE
			SYNTAX	INTEGER
			ACCESS	read-only
			STATUS	current
	DESCRIPTION ""
			::= { mbusD7 61 }

mbusD7VIF1C		OBJECT-TYPE
			SYNTAX	INTEGER
			ACCESS	read-only
			STATUS	current
	DESCRIPTION ""
			::= { mbusD7 62 }

mbusD7Value1C		OBJECT-TYPE
			SYNTAX	INTEGER
			ACCESS	read-only
			STATUS	current
	DESCRIPTION ""
			::= { mbusD7 63 }

mbusD7VIF1D		OBJECT-TYPE
			SYNTAX	INTEGER
			ACCESS	read-only
			STATUS	current
	DESCRIPTION ""
			::= { mbusD7 64 }

mbusD7Value1D		OBJECT-TYPE
			SYNTAX	INTEGER
			ACCESS	read-only
			STATUS	current
	DESCRIPTION ""
			::= { mbusD7 65 }

mbusD7VIF1E		OBJECT-TYPE
			SYNTAX	INTEGER
			ACCESS	read-only
			STATUS	current
	DESCRIPTION ""
			::= { mbusD7 66 }

mbusD7Value1E		OBJECT-TYPE
			SYNTAX	INTEGER
			ACCESS	read-only
			STATUS	current
	DESCRIPTION ""
			::= { mbusD7 67 }

mbusD7VIF1F		OBJECT-TYPE
			SYNTAX	INTEGER
			ACCESS	read-only
			STATUS	current
	DESCRIPTION ""
			::= { mbusD7 68 }

mbusD7Value1F		OBJECT-TYPE
			SYNTAX	INTEGER
			ACCESS	read-only
			STATUS	current
	DESCRIPTION ""
			::= { mbusD7 69 }

mbusD7VIF20		OBJECT-TYPE
			SYNTAX	INTEGER
			ACCESS	read-only
			STATUS	current
	DESCRIPTION ""
			::= { mbusD7 70 }

mbusD7Value20		OBJECT-TYPE
			SYNTAX	INTEGER
			ACCESS	read-only
			STATUS	current
	DESCRIPTION ""
			::= { mbusD7 71 }

mbusD7VIF21		OBJECT-TYPE
			SYNTAX	INTEGER
			ACCESS	read-only
			STATUS	current
	DESCRIPTION ""
			::= { mbusD7 72 }

mbusD7Value21		OBJECT-TYPE
			SYNTAX	INTEGER
			ACCESS	read-only
			STATUS	current
	DESCRIPTION ""
			::= { mbusD7 73 }

mbusD7VIF22		OBJECT-TYPE
			SYNTAX	INTEGER
			ACCESS	read-only
			STATUS	current
	DESCRIPTION ""
			::= { mbusD7 74 }

mbusD7Value22		OBJECT-TYPE
			SYNTAX	INTEGER
			ACCESS	read-only
			STATUS	current
	DESCRIPTION ""
			::= { mbusD7 75 }

mbusD7VIF23		OBJECT-TYPE
			SYNTAX	INTEGER
			ACCESS	read-only
			STATUS	current
	DESCRIPTION ""
			::= { mbusD7 76 }

mbusD7Value23		OBJECT-TYPE
			SYNTAX	INTEGER
			ACCESS	read-only
			STATUS	current
	DESCRIPTION ""
			::= { mbusD7 77 }

mbusD7VIF24		OBJECT-TYPE
			SYNTAX	INTEGER
			ACCESS	read-only
			STATUS	current
	DESCRIPTION ""
			::= { mbusD7 78 }

mbusD7Value24		OBJECT-TYPE
			SYNTAX	INTEGER
			ACCESS	read-only
			STATUS	current
	DESCRIPTION ""
			::= { mbusD7 79 }

mbusD7VIF25		OBJECT-TYPE
			SYNTAX	INTEGER
			ACCESS	read-only
			STATUS	current
	DESCRIPTION ""
			::= { mbusD7 80 }

mbusD7Value25		OBJECT-TYPE
			SYNTAX	INTEGER
			ACCESS	read-only
			STATUS	current
	DESCRIPTION ""
			::= { mbusD7 81 }

mbusD7VIF26		OBJECT-TYPE
			SYNTAX	INTEGER
			ACCESS	read-only
			STATUS	current
	DESCRIPTION ""
			::= { mbusD7 82 }

mbusD7Value26		OBJECT-TYPE
			SYNTAX	INTEGER
			ACCESS	read-only
			STATUS	current
	DESCRIPTION ""
			::= { mbusD7 83 }

mbusD7VIF27		OBJECT-TYPE
			SYNTAX	INTEGER
			ACCESS	read-only
			STATUS	current
	DESCRIPTION ""
			::= { mbusD7 84 }

mbusD7Value27		OBJECT-TYPE
			SYNTAX	INTEGER
			ACCESS	read-only
			STATUS	current
	DESCRIPTION ""
			::= { mbusD7 85 }

mbusD7VIF28		OBJECT-TYPE
			SYNTAX	INTEGER
			ACCESS	read-only
			STATUS	current
	DESCRIPTION ""
			::= { mbusD7 86 }

mbusD7Value28		OBJECT-TYPE
			SYNTAX	INTEGER
			ACCESS	read-only
			STATUS	current
	DESCRIPTION ""
			::= { mbusD7 87 }

mbusD7VIF29		OBJECT-TYPE
			SYNTAX	INTEGER
			ACCESS	read-only
			STATUS	current
	DESCRIPTION ""
			::= { mbusD7 88 }

mbusD7Value29		OBJECT-TYPE
			SYNTAX	INTEGER
			ACCESS	read-only
			STATUS	current
	DESCRIPTION ""
			::= { mbusD7 89 }

mbusD7VIF2A		OBJECT-TYPE
			SYNTAX	INTEGER
			ACCESS	read-only
			STATUS	current
	DESCRIPTION ""
			::= { mbusD7 90 }

mbusD7Value2A		OBJECT-TYPE
			SYNTAX	INTEGER
			ACCESS	read-only
			STATUS	current
	DESCRIPTION ""
			::= { mbusD7 91 }

mbusD7VIF2B		OBJECT-TYPE
			SYNTAX	INTEGER
			ACCESS	read-only
			STATUS	current
	DESCRIPTION ""
			::= { mbusD7 92 }

mbusD7Value2B		OBJECT-TYPE
			SYNTAX	INTEGER
			ACCESS	read-only
			STATUS	current
	DESCRIPTION ""
			::= { mbusD7 93 }

mbusD7VIF2C		OBJECT-TYPE
			SYNTAX	INTEGER
			ACCESS	read-only
			STATUS	current
	DESCRIPTION ""
			::= { mbusD7 94 }

mbusD7Value2C		OBJECT-TYPE
			SYNTAX	INTEGER
			ACCESS	read-only
			STATUS	current
	DESCRIPTION ""
			::= { mbusD7 95 }

mbusD7VIF2D		OBJECT-TYPE
			SYNTAX	INTEGER
			ACCESS	read-only
			STATUS	current
	DESCRIPTION ""
			::= { mbusD7 96 }

mbusD7Value2D		OBJECT-TYPE
			SYNTAX	INTEGER
			ACCESS	read-only
			STATUS	current
	DESCRIPTION ""
			::= { mbusD7 97 }

mbusD7VIF2E		OBJECT-TYPE
			SYNTAX	INTEGER
			ACCESS	read-only
			STATUS	current
	DESCRIPTION ""
			::= { mbusD7 98 }

mbusD7Value2E		OBJECT-TYPE
			SYNTAX	INTEGER
			ACCESS	read-only
			STATUS	current
	DESCRIPTION ""
			::= { mbusD7 99 }

mbusD7VIF2F		OBJECT-TYPE
			SYNTAX	INTEGER
			ACCESS	read-only
			STATUS	current
	DESCRIPTION ""
			::= { mbusD7 100 }

mbusD7Value2F		OBJECT-TYPE
			SYNTAX	INTEGER
			ACCESS	read-only
			STATUS	current
	DESCRIPTION ""
			::= { mbusD7 101 }

mbusD8			OBJECT IDENTIFIER ::= { mbus 216 }

mbusD8IdNumber		OBJECT-TYPE
			SYNTAX	Gauge
			ACCESS	read-only
			STATUS	current
	DESCRIPTION ""
			::= { mbusD8 1 }

mbusD8Manufacturer	OBJECT-TYPE
			SYNTAX	Gauge
			ACCESS	read-only
			STATUS	current
	DESCRIPTION ""
			::= { mbusD8 2 }

mbusD8Version		OBJECT-TYPE
			SYNTAX	Gauge
			ACCESS	read-only
			STATUS	current
	DESCRIPTION ""
			::= { mbusD8 3 }

mbusD8Medium		OBJECT-TYPE
			SYNTAX	Gauge
			ACCESS	read-only
			STATUS	current
	DESCRIPTION ""
			::= { mbusD8 4 }

mbusD8Status		OBJECT-TYPE
			SYNTAX	Gauge
			ACCESS	read-only
			STATUS	current
	DESCRIPTION ""
			::= { mbusD8 5 }

mbusD8VIF00		OBJECT-TYPE
			SYNTAX	INTEGER
			ACCESS	read-only
			STATUS	current
	DESCRIPTION ""
			::= { mbusD8 6 }

mbusD8Value00		OBJECT-TYPE
			SYNTAX	INTEGER
			ACCESS	read-only
			STATUS	current
	DESCRIPTION ""
			::= { mbusD8 7 }

mbusD8VIF01		OBJECT-TYPE
			SYNTAX	INTEGER
			ACCESS	read-only
			STATUS	current
	DESCRIPTION ""
			::= { mbusD8 8 }

mbusD8Value01		OBJECT-TYPE
			SYNTAX	INTEGER
			ACCESS	read-only
			STATUS	current
	DESCRIPTION ""
			::= { mbusD8 9 }

mbusD8VIF02		OBJECT-TYPE
			SYNTAX	INTEGER
			ACCESS	read-only
			STATUS	current
	DESCRIPTION ""
			::= { mbusD8 10 }

mbusD8Value02		OBJECT-TYPE
			SYNTAX	INTEGER
			ACCESS	read-only
			STATUS	current
	DESCRIPTION ""
			::= { mbusD8 11 }

mbusD8VIF03		OBJECT-TYPE
			SYNTAX	INTEGER
			ACCESS	read-only
			STATUS	current
	DESCRIPTION ""
			::= { mbusD8 12 }

mbusD8Value03		OBJECT-TYPE
			SYNTAX	INTEGER
			ACCESS	read-only
			STATUS	current
	DESCRIPTION ""
			::= { mbusD8 13 }

mbusD8VIF04		OBJECT-TYPE
			SYNTAX	INTEGER
			ACCESS	read-only
			STATUS	current
	DESCRIPTION ""
			::= { mbusD8 14 }

mbusD8Value04		OBJECT-TYPE
			SYNTAX	INTEGER
			ACCESS	read-only
			STATUS	current
	DESCRIPTION ""
			::= { mbusD8 15 }

mbusD8VIF05		OBJECT-TYPE
			SYNTAX	INTEGER
			ACCESS	read-only
			STATUS	current
	DESCRIPTION ""
			::= { mbusD8 16 }

mbusD8Value05		OBJECT-TYPE
			SYNTAX	INTEGER
			ACCESS	read-only
			STATUS	current
	DESCRIPTION ""
			::= { mbusD8 17 }

mbusD8VIF06		OBJECT-TYPE
			SYNTAX	INTEGER
			ACCESS	read-only
			STATUS	current
	DESCRIPTION ""
			::= { mbusD8 18 }

mbusD8Value06		OBJECT-TYPE
			SYNTAX	INTEGER
			ACCESS	read-only
			STATUS	current
	DESCRIPTION ""
			::= { mbusD8 19 }

mbusD8VIF07		OBJECT-TYPE
			SYNTAX	INTEGER
			ACCESS	read-only
			STATUS	current
	DESCRIPTION ""
			::= { mbusD8 20 }

mbusD8Value07		OBJECT-TYPE
			SYNTAX	INTEGER
			ACCESS	read-only
			STATUS	current
	DESCRIPTION ""
			::= { mbusD8 21 }

mbusD8VIF08		OBJECT-TYPE
			SYNTAX	INTEGER
			ACCESS	read-only
			STATUS	current
	DESCRIPTION ""
			::= { mbusD8 22 }

mbusD8Value08		OBJECT-TYPE
			SYNTAX	INTEGER
			ACCESS	read-only
			STATUS	current
	DESCRIPTION ""
			::= { mbusD8 23 }

mbusD8VIF09		OBJECT-TYPE
			SYNTAX	INTEGER
			ACCESS	read-only
			STATUS	current
	DESCRIPTION ""
			::= { mbusD8 24 }

mbusD8Value09		OBJECT-TYPE
			SYNTAX	INTEGER
			ACCESS	read-only
			STATUS	current
	DESCRIPTION ""
			::= { mbusD8 25 }

mbusD8VIF0A		OBJECT-TYPE
			SYNTAX	INTEGER
			ACCESS	read-only
			STATUS	current
	DESCRIPTION ""
			::= { mbusD8 26 }

mbusD8Value0A		OBJECT-TYPE
			SYNTAX	INTEGER
			ACCESS	read-only
			STATUS	current
	DESCRIPTION ""
			::= { mbusD8 27 }

mbusD8VIF0B		OBJECT-TYPE
			SYNTAX	INTEGER
			ACCESS	read-only
			STATUS	current
	DESCRIPTION ""
			::= { mbusD8 28 }

mbusD8Value0B		OBJECT-TYPE
			SYNTAX	INTEGER
			ACCESS	read-only
			STATUS	current
	DESCRIPTION ""
			::= { mbusD8 29 }

mbusD8VIF0C		OBJECT-TYPE
			SYNTAX	INTEGER
			ACCESS	read-only
			STATUS	current
	DESCRIPTION ""
			::= { mbusD8 30 }

mbusD8Value0C		OBJECT-TYPE
			SYNTAX	INTEGER
			ACCESS	read-only
			STATUS	current
	DESCRIPTION ""
			::= { mbusD8 31 }

mbusD8VIF0D		OBJECT-TYPE
			SYNTAX	INTEGER
			ACCESS	read-only
			STATUS	current
	DESCRIPTION ""
			::= { mbusD8 32 }

mbusD8Value0D		OBJECT-TYPE
			SYNTAX	INTEGER
			ACCESS	read-only
			STATUS	current
	DESCRIPTION ""
			::= { mbusD8 33 }

mbusD8VIF0E		OBJECT-TYPE
			SYNTAX	INTEGER
			ACCESS	read-only
			STATUS	current
	DESCRIPTION ""
			::= { mbusD8 34 }

mbusD8Value0E		OBJECT-TYPE
			SYNTAX	INTEGER
			ACCESS	read-only
			STATUS	current
	DESCRIPTION ""
			::= { mbusD8 35 }

mbusD8VIF0F		OBJECT-TYPE
			SYNTAX	INTEGER
			ACCESS	read-only
			STATUS	current
	DESCRIPTION ""
			::= { mbusD8 36 }

mbusD8Value0F		OBJECT-TYPE
			SYNTAX	INTEGER
			ACCESS	read-only
			STATUS	current
	DESCRIPTION ""
			::= { mbusD8 37 }

mbusD8VIF10		OBJECT-TYPE
			SYNTAX	INTEGER
			ACCESS	read-only
			STATUS	current
	DESCRIPTION ""
			::= { mbusD8 38 }

mbusD8Value10		OBJECT-TYPE
			SYNTAX	INTEGER
			ACCESS	read-only
			STATUS	current
	DESCRIPTION ""
			::= { mbusD8 39 }

mbusD8VIF11		OBJECT-TYPE
			SYNTAX	INTEGER
			ACCESS	read-only
			STATUS	current
	DESCRIPTION ""
			::= { mbusD8 40 }

mbusD8Value11		OBJECT-TYPE
			SYNTAX	INTEGER
			ACCESS	read-only
			STATUS	current
	DESCRIPTION ""
			::= { mbusD8 41 }

mbusD8VIF12		OBJECT-TYPE
			SYNTAX	INTEGER
			ACCESS	read-only
			STATUS	current
	DESCRIPTION ""
			::= { mbusD8 42 }

mbusD8Value12		OBJECT-TYPE
			SYNTAX	INTEGER
			ACCESS	read-only
			STATUS	current
	DESCRIPTION ""
			::= { mbusD8 43 }

mbusD8VIF13		OBJECT-TYPE
			SYNTAX	INTEGER
			ACCESS	read-only
			STATUS	current
	DESCRIPTION ""
			::= { mbusD8 44 }

mbusD8Value13		OBJECT-TYPE
			SYNTAX	INTEGER
			ACCESS	read-only
			STATUS	current
	DESCRIPTION ""
			::= { mbusD8 45 }

mbusD8VIF14		OBJECT-TYPE
			SYNTAX	INTEGER
			ACCESS	read-only
			STATUS	current
	DESCRIPTION ""
			::= { mbusD8 46 }

mbusD8Value14		OBJECT-TYPE
			SYNTAX	INTEGER
			ACCESS	read-only
			STATUS	current
	DESCRIPTION ""
			::= { mbusD8 47 }

mbusD8VIF15		OBJECT-TYPE
			SYNTAX	INTEGER
			ACCESS	read-only
			STATUS	current
	DESCRIPTION ""
			::= { mbusD8 48 }

mbusD8Value15		OBJECT-TYPE
			SYNTAX	INTEGER
			ACCESS	read-only
			STATUS	current
	DESCRIPTION ""
			::= { mbusD8 49 }

mbusD8VIF16		OBJECT-TYPE
			SYNTAX	INTEGER
			ACCESS	read-only
			STATUS	current
	DESCRIPTION ""
			::= { mbusD8 50 }

mbusD8Value16		OBJECT-TYPE
			SYNTAX	INTEGER
			ACCESS	read-only
			STATUS	current
	DESCRIPTION ""
			::= { mbusD8 51 }

mbusD8VIF17		OBJECT-TYPE
			SYNTAX	INTEGER
			ACCESS	read-only
			STATUS	current
	DESCRIPTION ""
			::= { mbusD8 52 }

mbusD8Value17		OBJECT-TYPE
			SYNTAX	INTEGER
			ACCESS	read-only
			STATUS	current
	DESCRIPTION ""
			::= { mbusD8 53 }

mbusD8VIF18		OBJECT-TYPE
			SYNTAX	INTEGER
			ACCESS	read-only
			STATUS	current
	DESCRIPTION ""
			::= { mbusD8 54 }

mbusD8Value18		OBJECT-TYPE
			SYNTAX	INTEGER
			ACCESS	read-only
			STATUS	current
	DESCRIPTION ""
			::= { mbusD8 55 }

mbusD8VIF19		OBJECT-TYPE
			SYNTAX	INTEGER
			ACCESS	read-only
			STATUS	current
	DESCRIPTION ""
			::= { mbusD8 56 }

mbusD8Value19		OBJECT-TYPE
			SYNTAX	INTEGER
			ACCESS	read-only
			STATUS	current
	DESCRIPTION ""
			::= { mbusD8 57 }

mbusD8VIF1A		OBJECT-TYPE
			SYNTAX	INTEGER
			ACCESS	read-only
			STATUS	current
	DESCRIPTION ""
			::= { mbusD8 58 }

mbusD8Value1A		OBJECT-TYPE
			SYNTAX	INTEGER
			ACCESS	read-only
			STATUS	current
	DESCRIPTION ""
			::= { mbusD8 59 }

mbusD8VIF1B		OBJECT-TYPE
			SYNTAX	INTEGER
			ACCESS	read-only
			STATUS	current
	DESCRIPTION ""
			::= { mbusD8 60 }

mbusD8Value1B		OBJECT-TYPE
			SYNTAX	INTEGER
			ACCESS	read-only
			STATUS	current
	DESCRIPTION ""
			::= { mbusD8 61 }

mbusD8VIF1C		OBJECT-TYPE
			SYNTAX	INTEGER
			ACCESS	read-only
			STATUS	current
	DESCRIPTION ""
			::= { mbusD8 62 }

mbusD8Value1C		OBJECT-TYPE
			SYNTAX	INTEGER
			ACCESS	read-only
			STATUS	current
	DESCRIPTION ""
			::= { mbusD8 63 }

mbusD8VIF1D		OBJECT-TYPE
			SYNTAX	INTEGER
			ACCESS	read-only
			STATUS	current
	DESCRIPTION ""
			::= { mbusD8 64 }

mbusD8Value1D		OBJECT-TYPE
			SYNTAX	INTEGER
			ACCESS	read-only
			STATUS	current
	DESCRIPTION ""
			::= { mbusD8 65 }

mbusD8VIF1E		OBJECT-TYPE
			SYNTAX	INTEGER
			ACCESS	read-only
			STATUS	current
	DESCRIPTION ""
			::= { mbusD8 66 }

mbusD8Value1E		OBJECT-TYPE
			SYNTAX	INTEGER
			ACCESS	read-only
			STATUS	current
	DESCRIPTION ""
			::= { mbusD8 67 }

mbusD8VIF1F		OBJECT-TYPE
			SYNTAX	INTEGER
			ACCESS	read-only
			STATUS	current
	DESCRIPTION ""
			::= { mbusD8 68 }

mbusD8Value1F		OBJECT-TYPE
			SYNTAX	INTEGER
			ACCESS	read-only
			STATUS	current
	DESCRIPTION ""
			::= { mbusD8 69 }

mbusD8VIF20		OBJECT-TYPE
			SYNTAX	INTEGER
			ACCESS	read-only
			STATUS	current
	DESCRIPTION ""
			::= { mbusD8 70 }

mbusD8Value20		OBJECT-TYPE
			SYNTAX	INTEGER
			ACCESS	read-only
			STATUS	current
	DESCRIPTION ""
			::= { mbusD8 71 }

mbusD8VIF21		OBJECT-TYPE
			SYNTAX	INTEGER
			ACCESS	read-only
			STATUS	current
	DESCRIPTION ""
			::= { mbusD8 72 }

mbusD8Value21		OBJECT-TYPE
			SYNTAX	INTEGER
			ACCESS	read-only
			STATUS	current
	DESCRIPTION ""
			::= { mbusD8 73 }

mbusD8VIF22		OBJECT-TYPE
			SYNTAX	INTEGER
			ACCESS	read-only
			STATUS	current
	DESCRIPTION ""
			::= { mbusD8 74 }

mbusD8Value22		OBJECT-TYPE
			SYNTAX	INTEGER
			ACCESS	read-only
			STATUS	current
	DESCRIPTION ""
			::= { mbusD8 75 }

mbusD8VIF23		OBJECT-TYPE
			SYNTAX	INTEGER
			ACCESS	read-only
			STATUS	current
	DESCRIPTION ""
			::= { mbusD8 76 }

mbusD8Value23		OBJECT-TYPE
			SYNTAX	INTEGER
			ACCESS	read-only
			STATUS	current
	DESCRIPTION ""
			::= { mbusD8 77 }

mbusD8VIF24		OBJECT-TYPE
			SYNTAX	INTEGER
			ACCESS	read-only
			STATUS	current
	DESCRIPTION ""
			::= { mbusD8 78 }

mbusD8Value24		OBJECT-TYPE
			SYNTAX	INTEGER
			ACCESS	read-only
			STATUS	current
	DESCRIPTION ""
			::= { mbusD8 79 }

mbusD8VIF25		OBJECT-TYPE
			SYNTAX	INTEGER
			ACCESS	read-only
			STATUS	current
	DESCRIPTION ""
			::= { mbusD8 80 }

mbusD8Value25		OBJECT-TYPE
			SYNTAX	INTEGER
			ACCESS	read-only
			STATUS	current
	DESCRIPTION ""
			::= { mbusD8 81 }

mbusD8VIF26		OBJECT-TYPE
			SYNTAX	INTEGER
			ACCESS	read-only
			STATUS	current
	DESCRIPTION ""
			::= { mbusD8 82 }

mbusD8Value26		OBJECT-TYPE
			SYNTAX	INTEGER
			ACCESS	read-only
			STATUS	current
	DESCRIPTION ""
			::= { mbusD8 83 }

mbusD8VIF27		OBJECT-TYPE
			SYNTAX	INTEGER
			ACCESS	read-only
			STATUS	current
	DESCRIPTION ""
			::= { mbusD8 84 }

mbusD8Value27		OBJECT-TYPE
			SYNTAX	INTEGER
			ACCESS	read-only
			STATUS	current
	DESCRIPTION ""
			::= { mbusD8 85 }

mbusD8VIF28		OBJECT-TYPE
			SYNTAX	INTEGER
			ACCESS	read-only
			STATUS	current
	DESCRIPTION ""
			::= { mbusD8 86 }

mbusD8Value28		OBJECT-TYPE
			SYNTAX	INTEGER
			ACCESS	read-only
			STATUS	current
	DESCRIPTION ""
			::= { mbusD8 87 }

mbusD8VIF29		OBJECT-TYPE
			SYNTAX	INTEGER
			ACCESS	read-only
			STATUS	current
	DESCRIPTION ""
			::= { mbusD8 88 }

mbusD8Value29		OBJECT-TYPE
			SYNTAX	INTEGER
			ACCESS	read-only
			STATUS	current
	DESCRIPTION ""
			::= { mbusD8 89 }

mbusD8VIF2A		OBJECT-TYPE
			SYNTAX	INTEGER
			ACCESS	read-only
			STATUS	current
	DESCRIPTION ""
			::= { mbusD8 90 }

mbusD8Value2A		OBJECT-TYPE
			SYNTAX	INTEGER
			ACCESS	read-only
			STATUS	current
	DESCRIPTION ""
			::= { mbusD8 91 }

mbusD8VIF2B		OBJECT-TYPE
			SYNTAX	INTEGER
			ACCESS	read-only
			STATUS	current
	DESCRIPTION ""
			::= { mbusD8 92 }

mbusD8Value2B		OBJECT-TYPE
			SYNTAX	INTEGER
			ACCESS	read-only
			STATUS	current
	DESCRIPTION ""
			::= { mbusD8 93 }

mbusD8VIF2C		OBJECT-TYPE
			SYNTAX	INTEGER
			ACCESS	read-only
			STATUS	current
	DESCRIPTION ""
			::= { mbusD8 94 }

mbusD8Value2C		OBJECT-TYPE
			SYNTAX	INTEGER
			ACCESS	read-only
			STATUS	current
	DESCRIPTION ""
			::= { mbusD8 95 }

mbusD8VIF2D		OBJECT-TYPE
			SYNTAX	INTEGER
			ACCESS	read-only
			STATUS	current
	DESCRIPTION ""
			::= { mbusD8 96 }

mbusD8Value2D		OBJECT-TYPE
			SYNTAX	INTEGER
			ACCESS	read-only
			STATUS	current
	DESCRIPTION ""
			::= { mbusD8 97 }

mbusD8VIF2E		OBJECT-TYPE
			SYNTAX	INTEGER
			ACCESS	read-only
			STATUS	current
	DESCRIPTION ""
			::= { mbusD8 98 }

mbusD8Value2E		OBJECT-TYPE
			SYNTAX	INTEGER
			ACCESS	read-only
			STATUS	current
	DESCRIPTION ""
			::= { mbusD8 99 }

mbusD8VIF2F		OBJECT-TYPE
			SYNTAX	INTEGER
			ACCESS	read-only
			STATUS	current
	DESCRIPTION ""
			::= { mbusD8 100 }

mbusD8Value2F		OBJECT-TYPE
			SYNTAX	INTEGER
			ACCESS	read-only
			STATUS	current
	DESCRIPTION ""
			::= { mbusD8 101 }

mbusD9			OBJECT IDENTIFIER ::= { mbus 217 }

mbusD9IdNumber		OBJECT-TYPE
			SYNTAX	Gauge
			ACCESS	read-only
			STATUS	current
	DESCRIPTION ""
			::= { mbusD9 1 }

mbusD9Manufacturer	OBJECT-TYPE
			SYNTAX	Gauge
			ACCESS	read-only
			STATUS	current
	DESCRIPTION ""
			::= { mbusD9 2 }

mbusD9Version		OBJECT-TYPE
			SYNTAX	Gauge
			ACCESS	read-only
			STATUS	current
	DESCRIPTION ""
			::= { mbusD9 3 }

mbusD9Medium		OBJECT-TYPE
			SYNTAX	Gauge
			ACCESS	read-only
			STATUS	current
	DESCRIPTION ""
			::= { mbusD9 4 }

mbusD9Status		OBJECT-TYPE
			SYNTAX	Gauge
			ACCESS	read-only
			STATUS	current
	DESCRIPTION ""
			::= { mbusD9 5 }

mbusD9VIF00		OBJECT-TYPE
			SYNTAX	INTEGER
			ACCESS	read-only
			STATUS	current
	DESCRIPTION ""
			::= { mbusD9 6 }

mbusD9Value00		OBJECT-TYPE
			SYNTAX	INTEGER
			ACCESS	read-only
			STATUS	current
	DESCRIPTION ""
			::= { mbusD9 7 }

mbusD9VIF01		OBJECT-TYPE
			SYNTAX	INTEGER
			ACCESS	read-only
			STATUS	current
	DESCRIPTION ""
			::= { mbusD9 8 }

mbusD9Value01		OBJECT-TYPE
			SYNTAX	INTEGER
			ACCESS	read-only
			STATUS	current
	DESCRIPTION ""
			::= { mbusD9 9 }

mbusD9VIF02		OBJECT-TYPE
			SYNTAX	INTEGER
			ACCESS	read-only
			STATUS	current
	DESCRIPTION ""
			::= { mbusD9 10 }

mbusD9Value02		OBJECT-TYPE
			SYNTAX	INTEGER
			ACCESS	read-only
			STATUS	current
	DESCRIPTION ""
			::= { mbusD9 11 }

mbusD9VIF03		OBJECT-TYPE
			SYNTAX	INTEGER
			ACCESS	read-only
			STATUS	current
	DESCRIPTION ""
			::= { mbusD9 12 }

mbusD9Value03		OBJECT-TYPE
			SYNTAX	INTEGER
			ACCESS	read-only
			STATUS	current
	DESCRIPTION ""
			::= { mbusD9 13 }

mbusD9VIF04		OBJECT-TYPE
			SYNTAX	INTEGER
			ACCESS	read-only
			STATUS	current
	DESCRIPTION ""
			::= { mbusD9 14 }

mbusD9Value04		OBJECT-TYPE
			SYNTAX	INTEGER
			ACCESS	read-only
			STATUS	current
	DESCRIPTION ""
			::= { mbusD9 15 }

mbusD9VIF05		OBJECT-TYPE
			SYNTAX	INTEGER
			ACCESS	read-only
			STATUS	current
	DESCRIPTION ""
			::= { mbusD9 16 }

mbusD9Value05		OBJECT-TYPE
			SYNTAX	INTEGER
			ACCESS	read-only
			STATUS	current
	DESCRIPTION ""
			::= { mbusD9 17 }

mbusD9VIF06		OBJECT-TYPE
			SYNTAX	INTEGER
			ACCESS	read-only
			STATUS	current
	DESCRIPTION ""
			::= { mbusD9 18 }

mbusD9Value06		OBJECT-TYPE
			SYNTAX	INTEGER
			ACCESS	read-only
			STATUS	current
	DESCRIPTION ""
			::= { mbusD9 19 }

mbusD9VIF07		OBJECT-TYPE
			SYNTAX	INTEGER
			ACCESS	read-only
			STATUS	current
	DESCRIPTION ""
			::= { mbusD9 20 }

mbusD9Value07		OBJECT-TYPE
			SYNTAX	INTEGER
			ACCESS	read-only
			STATUS	current
	DESCRIPTION ""
			::= { mbusD9 21 }

mbusD9VIF08		OBJECT-TYPE
			SYNTAX	INTEGER
			ACCESS	read-only
			STATUS	current
	DESCRIPTION ""
			::= { mbusD9 22 }

mbusD9Value08		OBJECT-TYPE
			SYNTAX	INTEGER
			ACCESS	read-only
			STATUS	current
	DESCRIPTION ""
			::= { mbusD9 23 }

mbusD9VIF09		OBJECT-TYPE
			SYNTAX	INTEGER
			ACCESS	read-only
			STATUS	current
	DESCRIPTION ""
			::= { mbusD9 24 }

mbusD9Value09		OBJECT-TYPE
			SYNTAX	INTEGER
			ACCESS	read-only
			STATUS	current
	DESCRIPTION ""
			::= { mbusD9 25 }

mbusD9VIF0A		OBJECT-TYPE
			SYNTAX	INTEGER
			ACCESS	read-only
			STATUS	current
	DESCRIPTION ""
			::= { mbusD9 26 }

mbusD9Value0A		OBJECT-TYPE
			SYNTAX	INTEGER
			ACCESS	read-only
			STATUS	current
	DESCRIPTION ""
			::= { mbusD9 27 }

mbusD9VIF0B		OBJECT-TYPE
			SYNTAX	INTEGER
			ACCESS	read-only
			STATUS	current
	DESCRIPTION ""
			::= { mbusD9 28 }

mbusD9Value0B		OBJECT-TYPE
			SYNTAX	INTEGER
			ACCESS	read-only
			STATUS	current
	DESCRIPTION ""
			::= { mbusD9 29 }

mbusD9VIF0C		OBJECT-TYPE
			SYNTAX	INTEGER
			ACCESS	read-only
			STATUS	current
	DESCRIPTION ""
			::= { mbusD9 30 }

mbusD9Value0C		OBJECT-TYPE
			SYNTAX	INTEGER
			ACCESS	read-only
			STATUS	current
	DESCRIPTION ""
			::= { mbusD9 31 }

mbusD9VIF0D		OBJECT-TYPE
			SYNTAX	INTEGER
			ACCESS	read-only
			STATUS	current
	DESCRIPTION ""
			::= { mbusD9 32 }

mbusD9Value0D		OBJECT-TYPE
			SYNTAX	INTEGER
			ACCESS	read-only
			STATUS	current
	DESCRIPTION ""
			::= { mbusD9 33 }

mbusD9VIF0E		OBJECT-TYPE
			SYNTAX	INTEGER
			ACCESS	read-only
			STATUS	current
	DESCRIPTION ""
			::= { mbusD9 34 }

mbusD9Value0E		OBJECT-TYPE
			SYNTAX	INTEGER
			ACCESS	read-only
			STATUS	current
	DESCRIPTION ""
			::= { mbusD9 35 }

mbusD9VIF0F		OBJECT-TYPE
			SYNTAX	INTEGER
			ACCESS	read-only
			STATUS	current
	DESCRIPTION ""
			::= { mbusD9 36 }

mbusD9Value0F		OBJECT-TYPE
			SYNTAX	INTEGER
			ACCESS	read-only
			STATUS	current
	DESCRIPTION ""
			::= { mbusD9 37 }

mbusD9VIF10		OBJECT-TYPE
			SYNTAX	INTEGER
			ACCESS	read-only
			STATUS	current
	DESCRIPTION ""
			::= { mbusD9 38 }

mbusD9Value10		OBJECT-TYPE
			SYNTAX	INTEGER
			ACCESS	read-only
			STATUS	current
	DESCRIPTION ""
			::= { mbusD9 39 }

mbusD9VIF11		OBJECT-TYPE
			SYNTAX	INTEGER
			ACCESS	read-only
			STATUS	current
	DESCRIPTION ""
			::= { mbusD9 40 }

mbusD9Value11		OBJECT-TYPE
			SYNTAX	INTEGER
			ACCESS	read-only
			STATUS	current
	DESCRIPTION ""
			::= { mbusD9 41 }

mbusD9VIF12		OBJECT-TYPE
			SYNTAX	INTEGER
			ACCESS	read-only
			STATUS	current
	DESCRIPTION ""
			::= { mbusD9 42 }

mbusD9Value12		OBJECT-TYPE
			SYNTAX	INTEGER
			ACCESS	read-only
			STATUS	current
	DESCRIPTION ""
			::= { mbusD9 43 }

mbusD9VIF13		OBJECT-TYPE
			SYNTAX	INTEGER
			ACCESS	read-only
			STATUS	current
	DESCRIPTION ""
			::= { mbusD9 44 }

mbusD9Value13		OBJECT-TYPE
			SYNTAX	INTEGER
			ACCESS	read-only
			STATUS	current
	DESCRIPTION ""
			::= { mbusD9 45 }

mbusD9VIF14		OBJECT-TYPE
			SYNTAX	INTEGER
			ACCESS	read-only
			STATUS	current
	DESCRIPTION ""
			::= { mbusD9 46 }

mbusD9Value14		OBJECT-TYPE
			SYNTAX	INTEGER
			ACCESS	read-only
			STATUS	current
	DESCRIPTION ""
			::= { mbusD9 47 }

mbusD9VIF15		OBJECT-TYPE
			SYNTAX	INTEGER
			ACCESS	read-only
			STATUS	current
	DESCRIPTION ""
			::= { mbusD9 48 }

mbusD9Value15		OBJECT-TYPE
			SYNTAX	INTEGER
			ACCESS	read-only
			STATUS	current
	DESCRIPTION ""
			::= { mbusD9 49 }

mbusD9VIF16		OBJECT-TYPE
			SYNTAX	INTEGER
			ACCESS	read-only
			STATUS	current
	DESCRIPTION ""
			::= { mbusD9 50 }

mbusD9Value16		OBJECT-TYPE
			SYNTAX	INTEGER
			ACCESS	read-only
			STATUS	current
	DESCRIPTION ""
			::= { mbusD9 51 }

mbusD9VIF17		OBJECT-TYPE
			SYNTAX	INTEGER
			ACCESS	read-only
			STATUS	current
	DESCRIPTION ""
			::= { mbusD9 52 }

mbusD9Value17		OBJECT-TYPE
			SYNTAX	INTEGER
			ACCESS	read-only
			STATUS	current
	DESCRIPTION ""
			::= { mbusD9 53 }

mbusD9VIF18		OBJECT-TYPE
			SYNTAX	INTEGER
			ACCESS	read-only
			STATUS	current
	DESCRIPTION ""
			::= { mbusD9 54 }

mbusD9Value18		OBJECT-TYPE
			SYNTAX	INTEGER
			ACCESS	read-only
			STATUS	current
	DESCRIPTION ""
			::= { mbusD9 55 }

mbusD9VIF19		OBJECT-TYPE
			SYNTAX	INTEGER
			ACCESS	read-only
			STATUS	current
	DESCRIPTION ""
			::= { mbusD9 56 }

mbusD9Value19		OBJECT-TYPE
			SYNTAX	INTEGER
			ACCESS	read-only
			STATUS	current
	DESCRIPTION ""
			::= { mbusD9 57 }

mbusD9VIF1A		OBJECT-TYPE
			SYNTAX	INTEGER
			ACCESS	read-only
			STATUS	current
	DESCRIPTION ""
			::= { mbusD9 58 }

mbusD9Value1A		OBJECT-TYPE
			SYNTAX	INTEGER
			ACCESS	read-only
			STATUS	current
	DESCRIPTION ""
			::= { mbusD9 59 }

mbusD9VIF1B		OBJECT-TYPE
			SYNTAX	INTEGER
			ACCESS	read-only
			STATUS	current
	DESCRIPTION ""
			::= { mbusD9 60 }

mbusD9Value1B		OBJECT-TYPE
			SYNTAX	INTEGER
			ACCESS	read-only
			STATUS	current
	DESCRIPTION ""
			::= { mbusD9 61 }

mbusD9VIF1C		OBJECT-TYPE
			SYNTAX	INTEGER
			ACCESS	read-only
			STATUS	current
	DESCRIPTION ""
			::= { mbusD9 62 }

mbusD9Value1C		OBJECT-TYPE
			SYNTAX	INTEGER
			ACCESS	read-only
			STATUS	current
	DESCRIPTION ""
			::= { mbusD9 63 }

mbusD9VIF1D		OBJECT-TYPE
			SYNTAX	INTEGER
			ACCESS	read-only
			STATUS	current
	DESCRIPTION ""
			::= { mbusD9 64 }

mbusD9Value1D		OBJECT-TYPE
			SYNTAX	INTEGER
			ACCESS	read-only
			STATUS	current
	DESCRIPTION ""
			::= { mbusD9 65 }

mbusD9VIF1E		OBJECT-TYPE
			SYNTAX	INTEGER
			ACCESS	read-only
			STATUS	current
	DESCRIPTION ""
			::= { mbusD9 66 }

mbusD9Value1E		OBJECT-TYPE
			SYNTAX	INTEGER
			ACCESS	read-only
			STATUS	current
	DESCRIPTION ""
			::= { mbusD9 67 }

mbusD9VIF1F		OBJECT-TYPE
			SYNTAX	INTEGER
			ACCESS	read-only
			STATUS	current
	DESCRIPTION ""
			::= { mbusD9 68 }

mbusD9Value1F		OBJECT-TYPE
			SYNTAX	INTEGER
			ACCESS	read-only
			STATUS	current
	DESCRIPTION ""
			::= { mbusD9 69 }

mbusD9VIF20		OBJECT-TYPE
			SYNTAX	INTEGER
			ACCESS	read-only
			STATUS	current
	DESCRIPTION ""
			::= { mbusD9 70 }

mbusD9Value20		OBJECT-TYPE
			SYNTAX	INTEGER
			ACCESS	read-only
			STATUS	current
	DESCRIPTION ""
			::= { mbusD9 71 }

mbusD9VIF21		OBJECT-TYPE
			SYNTAX	INTEGER
			ACCESS	read-only
			STATUS	current
	DESCRIPTION ""
			::= { mbusD9 72 }

mbusD9Value21		OBJECT-TYPE
			SYNTAX	INTEGER
			ACCESS	read-only
			STATUS	current
	DESCRIPTION ""
			::= { mbusD9 73 }

mbusD9VIF22		OBJECT-TYPE
			SYNTAX	INTEGER
			ACCESS	read-only
			STATUS	current
	DESCRIPTION ""
			::= { mbusD9 74 }

mbusD9Value22		OBJECT-TYPE
			SYNTAX	INTEGER
			ACCESS	read-only
			STATUS	current
	DESCRIPTION ""
			::= { mbusD9 75 }

mbusD9VIF23		OBJECT-TYPE
			SYNTAX	INTEGER
			ACCESS	read-only
			STATUS	current
	DESCRIPTION ""
			::= { mbusD9 76 }

mbusD9Value23		OBJECT-TYPE
			SYNTAX	INTEGER
			ACCESS	read-only
			STATUS	current
	DESCRIPTION ""
			::= { mbusD9 77 }

mbusD9VIF24		OBJECT-TYPE
			SYNTAX	INTEGER
			ACCESS	read-only
			STATUS	current
	DESCRIPTION ""
			::= { mbusD9 78 }

mbusD9Value24		OBJECT-TYPE
			SYNTAX	INTEGER
			ACCESS	read-only
			STATUS	current
	DESCRIPTION ""
			::= { mbusD9 79 }

mbusD9VIF25		OBJECT-TYPE
			SYNTAX	INTEGER
			ACCESS	read-only
			STATUS	current
	DESCRIPTION ""
			::= { mbusD9 80 }

mbusD9Value25		OBJECT-TYPE
			SYNTAX	INTEGER
			ACCESS	read-only
			STATUS	current
	DESCRIPTION ""
			::= { mbusD9 81 }

mbusD9VIF26		OBJECT-TYPE
			SYNTAX	INTEGER
			ACCESS	read-only
			STATUS	current
	DESCRIPTION ""
			::= { mbusD9 82 }

mbusD9Value26		OBJECT-TYPE
			SYNTAX	INTEGER
			ACCESS	read-only
			STATUS	current
	DESCRIPTION ""
			::= { mbusD9 83 }

mbusD9VIF27		OBJECT-TYPE
			SYNTAX	INTEGER
			ACCESS	read-only
			STATUS	current
	DESCRIPTION ""
			::= { mbusD9 84 }

mbusD9Value27		OBJECT-TYPE
			SYNTAX	INTEGER
			ACCESS	read-only
			STATUS	current
	DESCRIPTION ""
			::= { mbusD9 85 }

mbusD9VIF28		OBJECT-TYPE
			SYNTAX	INTEGER
			ACCESS	read-only
			STATUS	current
	DESCRIPTION ""
			::= { mbusD9 86 }

mbusD9Value28		OBJECT-TYPE
			SYNTAX	INTEGER
			ACCESS	read-only
			STATUS	current
	DESCRIPTION ""
			::= { mbusD9 87 }

mbusD9VIF29		OBJECT-TYPE
			SYNTAX	INTEGER
			ACCESS	read-only
			STATUS	current
	DESCRIPTION ""
			::= { mbusD9 88 }

mbusD9Value29		OBJECT-TYPE
			SYNTAX	INTEGER
			ACCESS	read-only
			STATUS	current
	DESCRIPTION ""
			::= { mbusD9 89 }

mbusD9VIF2A		OBJECT-TYPE
			SYNTAX	INTEGER
			ACCESS	read-only
			STATUS	current
	DESCRIPTION ""
			::= { mbusD9 90 }

mbusD9Value2A		OBJECT-TYPE
			SYNTAX	INTEGER
			ACCESS	read-only
			STATUS	current
	DESCRIPTION ""
			::= { mbusD9 91 }

mbusD9VIF2B		OBJECT-TYPE
			SYNTAX	INTEGER
			ACCESS	read-only
			STATUS	current
	DESCRIPTION ""
			::= { mbusD9 92 }

mbusD9Value2B		OBJECT-TYPE
			SYNTAX	INTEGER
			ACCESS	read-only
			STATUS	current
	DESCRIPTION ""
			::= { mbusD9 93 }

mbusD9VIF2C		OBJECT-TYPE
			SYNTAX	INTEGER
			ACCESS	read-only
			STATUS	current
	DESCRIPTION ""
			::= { mbusD9 94 }

mbusD9Value2C		OBJECT-TYPE
			SYNTAX	INTEGER
			ACCESS	read-only
			STATUS	current
	DESCRIPTION ""
			::= { mbusD9 95 }

mbusD9VIF2D		OBJECT-TYPE
			SYNTAX	INTEGER
			ACCESS	read-only
			STATUS	current
	DESCRIPTION ""
			::= { mbusD9 96 }

mbusD9Value2D		OBJECT-TYPE
			SYNTAX	INTEGER
			ACCESS	read-only
			STATUS	current
	DESCRIPTION ""
			::= { mbusD9 97 }

mbusD9VIF2E		OBJECT-TYPE
			SYNTAX	INTEGER
			ACCESS	read-only
			STATUS	current
	DESCRIPTION ""
			::= { mbusD9 98 }

mbusD9Value2E		OBJECT-TYPE
			SYNTAX	INTEGER
			ACCESS	read-only
			STATUS	current
	DESCRIPTION ""
			::= { mbusD9 99 }

mbusD9VIF2F		OBJECT-TYPE
			SYNTAX	INTEGER
			ACCESS	read-only
			STATUS	current
	DESCRIPTION ""
			::= { mbusD9 100 }

mbusD9Value2F		OBJECT-TYPE
			SYNTAX	INTEGER
			ACCESS	read-only
			STATUS	current
	DESCRIPTION ""
			::= { mbusD9 101 }

mbusDA			OBJECT IDENTIFIER ::= { mbus 218 }

mbusDAIdNumber		OBJECT-TYPE
			SYNTAX	Gauge
			ACCESS	read-only
			STATUS	current
	DESCRIPTION ""
			::= { mbusDA 1 }

mbusDAManufacturer	OBJECT-TYPE
			SYNTAX	Gauge
			ACCESS	read-only
			STATUS	current
	DESCRIPTION ""
			::= { mbusDA 2 }

mbusDAVersion		OBJECT-TYPE
			SYNTAX	Gauge
			ACCESS	read-only
			STATUS	current
	DESCRIPTION ""
			::= { mbusDA 3 }

mbusDAMedium		OBJECT-TYPE
			SYNTAX	Gauge
			ACCESS	read-only
			STATUS	current
	DESCRIPTION ""
			::= { mbusDA 4 }

mbusDAStatus		OBJECT-TYPE
			SYNTAX	Gauge
			ACCESS	read-only
			STATUS	current
	DESCRIPTION ""
			::= { mbusDA 5 }

mbusDAVIF00		OBJECT-TYPE
			SYNTAX	INTEGER
			ACCESS	read-only
			STATUS	current
	DESCRIPTION ""
			::= { mbusDA 6 }

mbusDAValue00		OBJECT-TYPE
			SYNTAX	INTEGER
			ACCESS	read-only
			STATUS	current
	DESCRIPTION ""
			::= { mbusDA 7 }

mbusDAVIF01		OBJECT-TYPE
			SYNTAX	INTEGER
			ACCESS	read-only
			STATUS	current
	DESCRIPTION ""
			::= { mbusDA 8 }

mbusDAValue01		OBJECT-TYPE
			SYNTAX	INTEGER
			ACCESS	read-only
			STATUS	current
	DESCRIPTION ""
			::= { mbusDA 9 }

mbusDAVIF02		OBJECT-TYPE
			SYNTAX	INTEGER
			ACCESS	read-only
			STATUS	current
	DESCRIPTION ""
			::= { mbusDA 10 }

mbusDAValue02		OBJECT-TYPE
			SYNTAX	INTEGER
			ACCESS	read-only
			STATUS	current
	DESCRIPTION ""
			::= { mbusDA 11 }

mbusDAVIF03		OBJECT-TYPE
			SYNTAX	INTEGER
			ACCESS	read-only
			STATUS	current
	DESCRIPTION ""
			::= { mbusDA 12 }

mbusDAValue03		OBJECT-TYPE
			SYNTAX	INTEGER
			ACCESS	read-only
			STATUS	current
	DESCRIPTION ""
			::= { mbusDA 13 }

mbusDAVIF04		OBJECT-TYPE
			SYNTAX	INTEGER
			ACCESS	read-only
			STATUS	current
	DESCRIPTION ""
			::= { mbusDA 14 }

mbusDAValue04		OBJECT-TYPE
			SYNTAX	INTEGER
			ACCESS	read-only
			STATUS	current
	DESCRIPTION ""
			::= { mbusDA 15 }

mbusDAVIF05		OBJECT-TYPE
			SYNTAX	INTEGER
			ACCESS	read-only
			STATUS	current
	DESCRIPTION ""
			::= { mbusDA 16 }

mbusDAValue05		OBJECT-TYPE
			SYNTAX	INTEGER
			ACCESS	read-only
			STATUS	current
	DESCRIPTION ""
			::= { mbusDA 17 }

mbusDAVIF06		OBJECT-TYPE
			SYNTAX	INTEGER
			ACCESS	read-only
			STATUS	current
	DESCRIPTION ""
			::= { mbusDA 18 }

mbusDAValue06		OBJECT-TYPE
			SYNTAX	INTEGER
			ACCESS	read-only
			STATUS	current
	DESCRIPTION ""
			::= { mbusDA 19 }

mbusDAVIF07		OBJECT-TYPE
			SYNTAX	INTEGER
			ACCESS	read-only
			STATUS	current
	DESCRIPTION ""
			::= { mbusDA 20 }

mbusDAValue07		OBJECT-TYPE
			SYNTAX	INTEGER
			ACCESS	read-only
			STATUS	current
	DESCRIPTION ""
			::= { mbusDA 21 }

mbusDAVIF08		OBJECT-TYPE
			SYNTAX	INTEGER
			ACCESS	read-only
			STATUS	current
	DESCRIPTION ""
			::= { mbusDA 22 }

mbusDAValue08		OBJECT-TYPE
			SYNTAX	INTEGER
			ACCESS	read-only
			STATUS	current
	DESCRIPTION ""
			::= { mbusDA 23 }

mbusDAVIF09		OBJECT-TYPE
			SYNTAX	INTEGER
			ACCESS	read-only
			STATUS	current
	DESCRIPTION ""
			::= { mbusDA 24 }

mbusDAValue09		OBJECT-TYPE
			SYNTAX	INTEGER
			ACCESS	read-only
			STATUS	current
	DESCRIPTION ""
			::= { mbusDA 25 }

mbusDAVIF0A		OBJECT-TYPE
			SYNTAX	INTEGER
			ACCESS	read-only
			STATUS	current
	DESCRIPTION ""
			::= { mbusDA 26 }

mbusDAValue0A		OBJECT-TYPE
			SYNTAX	INTEGER
			ACCESS	read-only
			STATUS	current
	DESCRIPTION ""
			::= { mbusDA 27 }

mbusDAVIF0B		OBJECT-TYPE
			SYNTAX	INTEGER
			ACCESS	read-only
			STATUS	current
	DESCRIPTION ""
			::= { mbusDA 28 }

mbusDAValue0B		OBJECT-TYPE
			SYNTAX	INTEGER
			ACCESS	read-only
			STATUS	current
	DESCRIPTION ""
			::= { mbusDA 29 }

mbusDAVIF0C		OBJECT-TYPE
			SYNTAX	INTEGER
			ACCESS	read-only
			STATUS	current
	DESCRIPTION ""
			::= { mbusDA 30 }

mbusDAValue0C		OBJECT-TYPE
			SYNTAX	INTEGER
			ACCESS	read-only
			STATUS	current
	DESCRIPTION ""
			::= { mbusDA 31 }

mbusDAVIF0D		OBJECT-TYPE
			SYNTAX	INTEGER
			ACCESS	read-only
			STATUS	current
	DESCRIPTION ""
			::= { mbusDA 32 }

mbusDAValue0D		OBJECT-TYPE
			SYNTAX	INTEGER
			ACCESS	read-only
			STATUS	current
	DESCRIPTION ""
			::= { mbusDA 33 }

mbusDAVIF0E		OBJECT-TYPE
			SYNTAX	INTEGER
			ACCESS	read-only
			STATUS	current
	DESCRIPTION ""
			::= { mbusDA 34 }

mbusDAValue0E		OBJECT-TYPE
			SYNTAX	INTEGER
			ACCESS	read-only
			STATUS	current
	DESCRIPTION ""
			::= { mbusDA 35 }

mbusDAVIF0F		OBJECT-TYPE
			SYNTAX	INTEGER
			ACCESS	read-only
			STATUS	current
	DESCRIPTION ""
			::= { mbusDA 36 }

mbusDAValue0F		OBJECT-TYPE
			SYNTAX	INTEGER
			ACCESS	read-only
			STATUS	current
	DESCRIPTION ""
			::= { mbusDA 37 }

mbusDAVIF10		OBJECT-TYPE
			SYNTAX	INTEGER
			ACCESS	read-only
			STATUS	current
	DESCRIPTION ""
			::= { mbusDA 38 }

mbusDAValue10		OBJECT-TYPE
			SYNTAX	INTEGER
			ACCESS	read-only
			STATUS	current
	DESCRIPTION ""
			::= { mbusDA 39 }

mbusDAVIF11		OBJECT-TYPE
			SYNTAX	INTEGER
			ACCESS	read-only
			STATUS	current
	DESCRIPTION ""
			::= { mbusDA 40 }

mbusDAValue11		OBJECT-TYPE
			SYNTAX	INTEGER
			ACCESS	read-only
			STATUS	current
	DESCRIPTION ""
			::= { mbusDA 41 }

mbusDAVIF12		OBJECT-TYPE
			SYNTAX	INTEGER
			ACCESS	read-only
			STATUS	current
	DESCRIPTION ""
			::= { mbusDA 42 }

mbusDAValue12		OBJECT-TYPE
			SYNTAX	INTEGER
			ACCESS	read-only
			STATUS	current
	DESCRIPTION ""
			::= { mbusDA 43 }

mbusDAVIF13		OBJECT-TYPE
			SYNTAX	INTEGER
			ACCESS	read-only
			STATUS	current
	DESCRIPTION ""
			::= { mbusDA 44 }

mbusDAValue13		OBJECT-TYPE
			SYNTAX	INTEGER
			ACCESS	read-only
			STATUS	current
	DESCRIPTION ""
			::= { mbusDA 45 }

mbusDAVIF14		OBJECT-TYPE
			SYNTAX	INTEGER
			ACCESS	read-only
			STATUS	current
	DESCRIPTION ""
			::= { mbusDA 46 }

mbusDAValue14		OBJECT-TYPE
			SYNTAX	INTEGER
			ACCESS	read-only
			STATUS	current
	DESCRIPTION ""
			::= { mbusDA 47 }

mbusDAVIF15		OBJECT-TYPE
			SYNTAX	INTEGER
			ACCESS	read-only
			STATUS	current
	DESCRIPTION ""
			::= { mbusDA 48 }

mbusDAValue15		OBJECT-TYPE
			SYNTAX	INTEGER
			ACCESS	read-only
			STATUS	current
	DESCRIPTION ""
			::= { mbusDA 49 }

mbusDAVIF16		OBJECT-TYPE
			SYNTAX	INTEGER
			ACCESS	read-only
			STATUS	current
	DESCRIPTION ""
			::= { mbusDA 50 }

mbusDAValue16		OBJECT-TYPE
			SYNTAX	INTEGER
			ACCESS	read-only
			STATUS	current
	DESCRIPTION ""
			::= { mbusDA 51 }

mbusDAVIF17		OBJECT-TYPE
			SYNTAX	INTEGER
			ACCESS	read-only
			STATUS	current
	DESCRIPTION ""
			::= { mbusDA 52 }

mbusDAValue17		OBJECT-TYPE
			SYNTAX	INTEGER
			ACCESS	read-only
			STATUS	current
	DESCRIPTION ""
			::= { mbusDA 53 }

mbusDAVIF18		OBJECT-TYPE
			SYNTAX	INTEGER
			ACCESS	read-only
			STATUS	current
	DESCRIPTION ""
			::= { mbusDA 54 }

mbusDAValue18		OBJECT-TYPE
			SYNTAX	INTEGER
			ACCESS	read-only
			STATUS	current
	DESCRIPTION ""
			::= { mbusDA 55 }

mbusDAVIF19		OBJECT-TYPE
			SYNTAX	INTEGER
			ACCESS	read-only
			STATUS	current
	DESCRIPTION ""
			::= { mbusDA 56 }

mbusDAValue19		OBJECT-TYPE
			SYNTAX	INTEGER
			ACCESS	read-only
			STATUS	current
	DESCRIPTION ""
			::= { mbusDA 57 }

mbusDAVIF1A		OBJECT-TYPE
			SYNTAX	INTEGER
			ACCESS	read-only
			STATUS	current
	DESCRIPTION ""
			::= { mbusDA 58 }

mbusDAValue1A		OBJECT-TYPE
			SYNTAX	INTEGER
			ACCESS	read-only
			STATUS	current
	DESCRIPTION ""
			::= { mbusDA 59 }

mbusDAVIF1B		OBJECT-TYPE
			SYNTAX	INTEGER
			ACCESS	read-only
			STATUS	current
	DESCRIPTION ""
			::= { mbusDA 60 }

mbusDAValue1B		OBJECT-TYPE
			SYNTAX	INTEGER
			ACCESS	read-only
			STATUS	current
	DESCRIPTION ""
			::= { mbusDA 61 }

mbusDAVIF1C		OBJECT-TYPE
			SYNTAX	INTEGER
			ACCESS	read-only
			STATUS	current
	DESCRIPTION ""
			::= { mbusDA 62 }

mbusDAValue1C		OBJECT-TYPE
			SYNTAX	INTEGER
			ACCESS	read-only
			STATUS	current
	DESCRIPTION ""
			::= { mbusDA 63 }

mbusDAVIF1D		OBJECT-TYPE
			SYNTAX	INTEGER
			ACCESS	read-only
			STATUS	current
	DESCRIPTION ""
			::= { mbusDA 64 }

mbusDAValue1D		OBJECT-TYPE
			SYNTAX	INTEGER
			ACCESS	read-only
			STATUS	current
	DESCRIPTION ""
			::= { mbusDA 65 }

mbusDAVIF1E		OBJECT-TYPE
			SYNTAX	INTEGER
			ACCESS	read-only
			STATUS	current
	DESCRIPTION ""
			::= { mbusDA 66 }

mbusDAValue1E		OBJECT-TYPE
			SYNTAX	INTEGER
			ACCESS	read-only
			STATUS	current
	DESCRIPTION ""
			::= { mbusDA 67 }

mbusDAVIF1F		OBJECT-TYPE
			SYNTAX	INTEGER
			ACCESS	read-only
			STATUS	current
	DESCRIPTION ""
			::= { mbusDA 68 }

mbusDAValue1F		OBJECT-TYPE
			SYNTAX	INTEGER
			ACCESS	read-only
			STATUS	current
	DESCRIPTION ""
			::= { mbusDA 69 }

mbusDAVIF20		OBJECT-TYPE
			SYNTAX	INTEGER
			ACCESS	read-only
			STATUS	current
	DESCRIPTION ""
			::= { mbusDA 70 }

mbusDAValue20		OBJECT-TYPE
			SYNTAX	INTEGER
			ACCESS	read-only
			STATUS	current
	DESCRIPTION ""
			::= { mbusDA 71 }

mbusDAVIF21		OBJECT-TYPE
			SYNTAX	INTEGER
			ACCESS	read-only
			STATUS	current
	DESCRIPTION ""
			::= { mbusDA 72 }

mbusDAValue21		OBJECT-TYPE
			SYNTAX	INTEGER
			ACCESS	read-only
			STATUS	current
	DESCRIPTION ""
			::= { mbusDA 73 }

mbusDAVIF22		OBJECT-TYPE
			SYNTAX	INTEGER
			ACCESS	read-only
			STATUS	current
	DESCRIPTION ""
			::= { mbusDA 74 }

mbusDAValue22		OBJECT-TYPE
			SYNTAX	INTEGER
			ACCESS	read-only
			STATUS	current
	DESCRIPTION ""
			::= { mbusDA 75 }

mbusDAVIF23		OBJECT-TYPE
			SYNTAX	INTEGER
			ACCESS	read-only
			STATUS	current
	DESCRIPTION ""
			::= { mbusDA 76 }

mbusDAValue23		OBJECT-TYPE
			SYNTAX	INTEGER
			ACCESS	read-only
			STATUS	current
	DESCRIPTION ""
			::= { mbusDA 77 }

mbusDAVIF24		OBJECT-TYPE
			SYNTAX	INTEGER
			ACCESS	read-only
			STATUS	current
	DESCRIPTION ""
			::= { mbusDA 78 }

mbusDAValue24		OBJECT-TYPE
			SYNTAX	INTEGER
			ACCESS	read-only
			STATUS	current
	DESCRIPTION ""
			::= { mbusDA 79 }

mbusDAVIF25		OBJECT-TYPE
			SYNTAX	INTEGER
			ACCESS	read-only
			STATUS	current
	DESCRIPTION ""
			::= { mbusDA 80 }

mbusDAValue25		OBJECT-TYPE
			SYNTAX	INTEGER
			ACCESS	read-only
			STATUS	current
	DESCRIPTION ""
			::= { mbusDA 81 }

mbusDAVIF26		OBJECT-TYPE
			SYNTAX	INTEGER
			ACCESS	read-only
			STATUS	current
	DESCRIPTION ""
			::= { mbusDA 82 }

mbusDAValue26		OBJECT-TYPE
			SYNTAX	INTEGER
			ACCESS	read-only
			STATUS	current
	DESCRIPTION ""
			::= { mbusDA 83 }

mbusDAVIF27		OBJECT-TYPE
			SYNTAX	INTEGER
			ACCESS	read-only
			STATUS	current
	DESCRIPTION ""
			::= { mbusDA 84 }

mbusDAValue27		OBJECT-TYPE
			SYNTAX	INTEGER
			ACCESS	read-only
			STATUS	current
	DESCRIPTION ""
			::= { mbusDA 85 }

mbusDAVIF28		OBJECT-TYPE
			SYNTAX	INTEGER
			ACCESS	read-only
			STATUS	current
	DESCRIPTION ""
			::= { mbusDA 86 }

mbusDAValue28		OBJECT-TYPE
			SYNTAX	INTEGER
			ACCESS	read-only
			STATUS	current
	DESCRIPTION ""
			::= { mbusDA 87 }

mbusDAVIF29		OBJECT-TYPE
			SYNTAX	INTEGER
			ACCESS	read-only
			STATUS	current
	DESCRIPTION ""
			::= { mbusDA 88 }

mbusDAValue29		OBJECT-TYPE
			SYNTAX	INTEGER
			ACCESS	read-only
			STATUS	current
	DESCRIPTION ""
			::= { mbusDA 89 }

mbusDAVIF2A		OBJECT-TYPE
			SYNTAX	INTEGER
			ACCESS	read-only
			STATUS	current
	DESCRIPTION ""
			::= { mbusDA 90 }

mbusDAValue2A		OBJECT-TYPE
			SYNTAX	INTEGER
			ACCESS	read-only
			STATUS	current
	DESCRIPTION ""
			::= { mbusDA 91 }

mbusDAVIF2B		OBJECT-TYPE
			SYNTAX	INTEGER
			ACCESS	read-only
			STATUS	current
	DESCRIPTION ""
			::= { mbusDA 92 }

mbusDAValue2B		OBJECT-TYPE
			SYNTAX	INTEGER
			ACCESS	read-only
			STATUS	current
	DESCRIPTION ""
			::= { mbusDA 93 }

mbusDAVIF2C		OBJECT-TYPE
			SYNTAX	INTEGER
			ACCESS	read-only
			STATUS	current
	DESCRIPTION ""
			::= { mbusDA 94 }

mbusDAValue2C		OBJECT-TYPE
			SYNTAX	INTEGER
			ACCESS	read-only
			STATUS	current
	DESCRIPTION ""
			::= { mbusDA 95 }

mbusDAVIF2D		OBJECT-TYPE
			SYNTAX	INTEGER
			ACCESS	read-only
			STATUS	current
	DESCRIPTION ""
			::= { mbusDA 96 }

mbusDAValue2D		OBJECT-TYPE
			SYNTAX	INTEGER
			ACCESS	read-only
			STATUS	current
	DESCRIPTION ""
			::= { mbusDA 97 }

mbusDAVIF2E		OBJECT-TYPE
			SYNTAX	INTEGER
			ACCESS	read-only
			STATUS	current
	DESCRIPTION ""
			::= { mbusDA 98 }

mbusDAValue2E		OBJECT-TYPE
			SYNTAX	INTEGER
			ACCESS	read-only
			STATUS	current
	DESCRIPTION ""
			::= { mbusDA 99 }

mbusDAVIF2F		OBJECT-TYPE
			SYNTAX	INTEGER
			ACCESS	read-only
			STATUS	current
	DESCRIPTION ""
			::= { mbusDA 100 }

mbusDAValue2F		OBJECT-TYPE
			SYNTAX	INTEGER
			ACCESS	read-only
			STATUS	current
	DESCRIPTION ""
			::= { mbusDA 101 }

mbusDB			OBJECT IDENTIFIER ::= { mbus 219 }

mbusDBIdNumber		OBJECT-TYPE
			SYNTAX	Gauge
			ACCESS	read-only
			STATUS	current
	DESCRIPTION ""
			::= { mbusDB 1 }

mbusDBManufacturer	OBJECT-TYPE
			SYNTAX	Gauge
			ACCESS	read-only
			STATUS	current
	DESCRIPTION ""
			::= { mbusDB 2 }

mbusDBVersion		OBJECT-TYPE
			SYNTAX	Gauge
			ACCESS	read-only
			STATUS	current
	DESCRIPTION ""
			::= { mbusDB 3 }

mbusDBMedium		OBJECT-TYPE
			SYNTAX	Gauge
			ACCESS	read-only
			STATUS	current
	DESCRIPTION ""
			::= { mbusDB 4 }

mbusDBStatus		OBJECT-TYPE
			SYNTAX	Gauge
			ACCESS	read-only
			STATUS	current
	DESCRIPTION ""
			::= { mbusDB 5 }

mbusDBVIF00		OBJECT-TYPE
			SYNTAX	INTEGER
			ACCESS	read-only
			STATUS	current
	DESCRIPTION ""
			::= { mbusDB 6 }

mbusDBValue00		OBJECT-TYPE
			SYNTAX	INTEGER
			ACCESS	read-only
			STATUS	current
	DESCRIPTION ""
			::= { mbusDB 7 }

mbusDBVIF01		OBJECT-TYPE
			SYNTAX	INTEGER
			ACCESS	read-only
			STATUS	current
	DESCRIPTION ""
			::= { mbusDB 8 }

mbusDBValue01		OBJECT-TYPE
			SYNTAX	INTEGER
			ACCESS	read-only
			STATUS	current
	DESCRIPTION ""
			::= { mbusDB 9 }

mbusDBVIF02		OBJECT-TYPE
			SYNTAX	INTEGER
			ACCESS	read-only
			STATUS	current
	DESCRIPTION ""
			::= { mbusDB 10 }

mbusDBValue02		OBJECT-TYPE
			SYNTAX	INTEGER
			ACCESS	read-only
			STATUS	current
	DESCRIPTION ""
			::= { mbusDB 11 }

mbusDBVIF03		OBJECT-TYPE
			SYNTAX	INTEGER
			ACCESS	read-only
			STATUS	current
	DESCRIPTION ""
			::= { mbusDB 12 }

mbusDBValue03		OBJECT-TYPE
			SYNTAX	INTEGER
			ACCESS	read-only
			STATUS	current
	DESCRIPTION ""
			::= { mbusDB 13 }

mbusDBVIF04		OBJECT-TYPE
			SYNTAX	INTEGER
			ACCESS	read-only
			STATUS	current
	DESCRIPTION ""
			::= { mbusDB 14 }

mbusDBValue04		OBJECT-TYPE
			SYNTAX	INTEGER
			ACCESS	read-only
			STATUS	current
	DESCRIPTION ""
			::= { mbusDB 15 }

mbusDBVIF05		OBJECT-TYPE
			SYNTAX	INTEGER
			ACCESS	read-only
			STATUS	current
	DESCRIPTION ""
			::= { mbusDB 16 }

mbusDBValue05		OBJECT-TYPE
			SYNTAX	INTEGER
			ACCESS	read-only
			STATUS	current
	DESCRIPTION ""
			::= { mbusDB 17 }

mbusDBVIF06		OBJECT-TYPE
			SYNTAX	INTEGER
			ACCESS	read-only
			STATUS	current
	DESCRIPTION ""
			::= { mbusDB 18 }

mbusDBValue06		OBJECT-TYPE
			SYNTAX	INTEGER
			ACCESS	read-only
			STATUS	current
	DESCRIPTION ""
			::= { mbusDB 19 }

mbusDBVIF07		OBJECT-TYPE
			SYNTAX	INTEGER
			ACCESS	read-only
			STATUS	current
	DESCRIPTION ""
			::= { mbusDB 20 }

mbusDBValue07		OBJECT-TYPE
			SYNTAX	INTEGER
			ACCESS	read-only
			STATUS	current
	DESCRIPTION ""
			::= { mbusDB 21 }

mbusDBVIF08		OBJECT-TYPE
			SYNTAX	INTEGER
			ACCESS	read-only
			STATUS	current
	DESCRIPTION ""
			::= { mbusDB 22 }

mbusDBValue08		OBJECT-TYPE
			SYNTAX	INTEGER
			ACCESS	read-only
			STATUS	current
	DESCRIPTION ""
			::= { mbusDB 23 }

mbusDBVIF09		OBJECT-TYPE
			SYNTAX	INTEGER
			ACCESS	read-only
			STATUS	current
	DESCRIPTION ""
			::= { mbusDB 24 }

mbusDBValue09		OBJECT-TYPE
			SYNTAX	INTEGER
			ACCESS	read-only
			STATUS	current
	DESCRIPTION ""
			::= { mbusDB 25 }

mbusDBVIF0A		OBJECT-TYPE
			SYNTAX	INTEGER
			ACCESS	read-only
			STATUS	current
	DESCRIPTION ""
			::= { mbusDB 26 }

mbusDBValue0A		OBJECT-TYPE
			SYNTAX	INTEGER
			ACCESS	read-only
			STATUS	current
	DESCRIPTION ""
			::= { mbusDB 27 }

mbusDBVIF0B		OBJECT-TYPE
			SYNTAX	INTEGER
			ACCESS	read-only
			STATUS	current
	DESCRIPTION ""
			::= { mbusDB 28 }

mbusDBValue0B		OBJECT-TYPE
			SYNTAX	INTEGER
			ACCESS	read-only
			STATUS	current
	DESCRIPTION ""
			::= { mbusDB 29 }

mbusDBVIF0C		OBJECT-TYPE
			SYNTAX	INTEGER
			ACCESS	read-only
			STATUS	current
	DESCRIPTION ""
			::= { mbusDB 30 }

mbusDBValue0C		OBJECT-TYPE
			SYNTAX	INTEGER
			ACCESS	read-only
			STATUS	current
	DESCRIPTION ""
			::= { mbusDB 31 }

mbusDBVIF0D		OBJECT-TYPE
			SYNTAX	INTEGER
			ACCESS	read-only
			STATUS	current
	DESCRIPTION ""
			::= { mbusDB 32 }

mbusDBValue0D		OBJECT-TYPE
			SYNTAX	INTEGER
			ACCESS	read-only
			STATUS	current
	DESCRIPTION ""
			::= { mbusDB 33 }

mbusDBVIF0E		OBJECT-TYPE
			SYNTAX	INTEGER
			ACCESS	read-only
			STATUS	current
	DESCRIPTION ""
			::= { mbusDB 34 }

mbusDBValue0E		OBJECT-TYPE
			SYNTAX	INTEGER
			ACCESS	read-only
			STATUS	current
	DESCRIPTION ""
			::= { mbusDB 35 }

mbusDBVIF0F		OBJECT-TYPE
			SYNTAX	INTEGER
			ACCESS	read-only
			STATUS	current
	DESCRIPTION ""
			::= { mbusDB 36 }

mbusDBValue0F		OBJECT-TYPE
			SYNTAX	INTEGER
			ACCESS	read-only
			STATUS	current
	DESCRIPTION ""
			::= { mbusDB 37 }

mbusDBVIF10		OBJECT-TYPE
			SYNTAX	INTEGER
			ACCESS	read-only
			STATUS	current
	DESCRIPTION ""
			::= { mbusDB 38 }

mbusDBValue10		OBJECT-TYPE
			SYNTAX	INTEGER
			ACCESS	read-only
			STATUS	current
	DESCRIPTION ""
			::= { mbusDB 39 }

mbusDBVIF11		OBJECT-TYPE
			SYNTAX	INTEGER
			ACCESS	read-only
			STATUS	current
	DESCRIPTION ""
			::= { mbusDB 40 }

mbusDBValue11		OBJECT-TYPE
			SYNTAX	INTEGER
			ACCESS	read-only
			STATUS	current
	DESCRIPTION ""
			::= { mbusDB 41 }

mbusDBVIF12		OBJECT-TYPE
			SYNTAX	INTEGER
			ACCESS	read-only
			STATUS	current
	DESCRIPTION ""
			::= { mbusDB 42 }

mbusDBValue12		OBJECT-TYPE
			SYNTAX	INTEGER
			ACCESS	read-only
			STATUS	current
	DESCRIPTION ""
			::= { mbusDB 43 }

mbusDBVIF13		OBJECT-TYPE
			SYNTAX	INTEGER
			ACCESS	read-only
			STATUS	current
	DESCRIPTION ""
			::= { mbusDB 44 }

mbusDBValue13		OBJECT-TYPE
			SYNTAX	INTEGER
			ACCESS	read-only
			STATUS	current
	DESCRIPTION ""
			::= { mbusDB 45 }

mbusDBVIF14		OBJECT-TYPE
			SYNTAX	INTEGER
			ACCESS	read-only
			STATUS	current
	DESCRIPTION ""
			::= { mbusDB 46 }

mbusDBValue14		OBJECT-TYPE
			SYNTAX	INTEGER
			ACCESS	read-only
			STATUS	current
	DESCRIPTION ""
			::= { mbusDB 47 }

mbusDBVIF15		OBJECT-TYPE
			SYNTAX	INTEGER
			ACCESS	read-only
			STATUS	current
	DESCRIPTION ""
			::= { mbusDB 48 }

mbusDBValue15		OBJECT-TYPE
			SYNTAX	INTEGER
			ACCESS	read-only
			STATUS	current
	DESCRIPTION ""
			::= { mbusDB 49 }

mbusDBVIF16		OBJECT-TYPE
			SYNTAX	INTEGER
			ACCESS	read-only
			STATUS	current
	DESCRIPTION ""
			::= { mbusDB 50 }

mbusDBValue16		OBJECT-TYPE
			SYNTAX	INTEGER
			ACCESS	read-only
			STATUS	current
	DESCRIPTION ""
			::= { mbusDB 51 }

mbusDBVIF17		OBJECT-TYPE
			SYNTAX	INTEGER
			ACCESS	read-only
			STATUS	current
	DESCRIPTION ""
			::= { mbusDB 52 }

mbusDBValue17		OBJECT-TYPE
			SYNTAX	INTEGER
			ACCESS	read-only
			STATUS	current
	DESCRIPTION ""
			::= { mbusDB 53 }

mbusDBVIF18		OBJECT-TYPE
			SYNTAX	INTEGER
			ACCESS	read-only
			STATUS	current
	DESCRIPTION ""
			::= { mbusDB 54 }

mbusDBValue18		OBJECT-TYPE
			SYNTAX	INTEGER
			ACCESS	read-only
			STATUS	current
	DESCRIPTION ""
			::= { mbusDB 55 }

mbusDBVIF19		OBJECT-TYPE
			SYNTAX	INTEGER
			ACCESS	read-only
			STATUS	current
	DESCRIPTION ""
			::= { mbusDB 56 }

mbusDBValue19		OBJECT-TYPE
			SYNTAX	INTEGER
			ACCESS	read-only
			STATUS	current
	DESCRIPTION ""
			::= { mbusDB 57 }

mbusDBVIF1A		OBJECT-TYPE
			SYNTAX	INTEGER
			ACCESS	read-only
			STATUS	current
	DESCRIPTION ""
			::= { mbusDB 58 }

mbusDBValue1A		OBJECT-TYPE
			SYNTAX	INTEGER
			ACCESS	read-only
			STATUS	current
	DESCRIPTION ""
			::= { mbusDB 59 }

mbusDBVIF1B		OBJECT-TYPE
			SYNTAX	INTEGER
			ACCESS	read-only
			STATUS	current
	DESCRIPTION ""
			::= { mbusDB 60 }

mbusDBValue1B		OBJECT-TYPE
			SYNTAX	INTEGER
			ACCESS	read-only
			STATUS	current
	DESCRIPTION ""
			::= { mbusDB 61 }

mbusDBVIF1C		OBJECT-TYPE
			SYNTAX	INTEGER
			ACCESS	read-only
			STATUS	current
	DESCRIPTION ""
			::= { mbusDB 62 }

mbusDBValue1C		OBJECT-TYPE
			SYNTAX	INTEGER
			ACCESS	read-only
			STATUS	current
	DESCRIPTION ""
			::= { mbusDB 63 }

mbusDBVIF1D		OBJECT-TYPE
			SYNTAX	INTEGER
			ACCESS	read-only
			STATUS	current
	DESCRIPTION ""
			::= { mbusDB 64 }

mbusDBValue1D		OBJECT-TYPE
			SYNTAX	INTEGER
			ACCESS	read-only
			STATUS	current
	DESCRIPTION ""
			::= { mbusDB 65 }

mbusDBVIF1E		OBJECT-TYPE
			SYNTAX	INTEGER
			ACCESS	read-only
			STATUS	current
	DESCRIPTION ""
			::= { mbusDB 66 }

mbusDBValue1E		OBJECT-TYPE
			SYNTAX	INTEGER
			ACCESS	read-only
			STATUS	current
	DESCRIPTION ""
			::= { mbusDB 67 }

mbusDBVIF1F		OBJECT-TYPE
			SYNTAX	INTEGER
			ACCESS	read-only
			STATUS	current
	DESCRIPTION ""
			::= { mbusDB 68 }

mbusDBValue1F		OBJECT-TYPE
			SYNTAX	INTEGER
			ACCESS	read-only
			STATUS	current
	DESCRIPTION ""
			::= { mbusDB 69 }

mbusDBVIF20		OBJECT-TYPE
			SYNTAX	INTEGER
			ACCESS	read-only
			STATUS	current
	DESCRIPTION ""
			::= { mbusDB 70 }

mbusDBValue20		OBJECT-TYPE
			SYNTAX	INTEGER
			ACCESS	read-only
			STATUS	current
	DESCRIPTION ""
			::= { mbusDB 71 }

mbusDBVIF21		OBJECT-TYPE
			SYNTAX	INTEGER
			ACCESS	read-only
			STATUS	current
	DESCRIPTION ""
			::= { mbusDB 72 }

mbusDBValue21		OBJECT-TYPE
			SYNTAX	INTEGER
			ACCESS	read-only
			STATUS	current
	DESCRIPTION ""
			::= { mbusDB 73 }

mbusDBVIF22		OBJECT-TYPE
			SYNTAX	INTEGER
			ACCESS	read-only
			STATUS	current
	DESCRIPTION ""
			::= { mbusDB 74 }

mbusDBValue22		OBJECT-TYPE
			SYNTAX	INTEGER
			ACCESS	read-only
			STATUS	current
	DESCRIPTION ""
			::= { mbusDB 75 }

mbusDBVIF23		OBJECT-TYPE
			SYNTAX	INTEGER
			ACCESS	read-only
			STATUS	current
	DESCRIPTION ""
			::= { mbusDB 76 }

mbusDBValue23		OBJECT-TYPE
			SYNTAX	INTEGER
			ACCESS	read-only
			STATUS	current
	DESCRIPTION ""
			::= { mbusDB 77 }

mbusDBVIF24		OBJECT-TYPE
			SYNTAX	INTEGER
			ACCESS	read-only
			STATUS	current
	DESCRIPTION ""
			::= { mbusDB 78 }

mbusDBValue24		OBJECT-TYPE
			SYNTAX	INTEGER
			ACCESS	read-only
			STATUS	current
	DESCRIPTION ""
			::= { mbusDB 79 }

mbusDBVIF25		OBJECT-TYPE
			SYNTAX	INTEGER
			ACCESS	read-only
			STATUS	current
	DESCRIPTION ""
			::= { mbusDB 80 }

mbusDBValue25		OBJECT-TYPE
			SYNTAX	INTEGER
			ACCESS	read-only
			STATUS	current
	DESCRIPTION ""
			::= { mbusDB 81 }

mbusDBVIF26		OBJECT-TYPE
			SYNTAX	INTEGER
			ACCESS	read-only
			STATUS	current
	DESCRIPTION ""
			::= { mbusDB 82 }

mbusDBValue26		OBJECT-TYPE
			SYNTAX	INTEGER
			ACCESS	read-only
			STATUS	current
	DESCRIPTION ""
			::= { mbusDB 83 }

mbusDBVIF27		OBJECT-TYPE
			SYNTAX	INTEGER
			ACCESS	read-only
			STATUS	current
	DESCRIPTION ""
			::= { mbusDB 84 }

mbusDBValue27		OBJECT-TYPE
			SYNTAX	INTEGER
			ACCESS	read-only
			STATUS	current
	DESCRIPTION ""
			::= { mbusDB 85 }

mbusDBVIF28		OBJECT-TYPE
			SYNTAX	INTEGER
			ACCESS	read-only
			STATUS	current
	DESCRIPTION ""
			::= { mbusDB 86 }

mbusDBValue28		OBJECT-TYPE
			SYNTAX	INTEGER
			ACCESS	read-only
			STATUS	current
	DESCRIPTION ""
			::= { mbusDB 87 }

mbusDBVIF29		OBJECT-TYPE
			SYNTAX	INTEGER
			ACCESS	read-only
			STATUS	current
	DESCRIPTION ""
			::= { mbusDB 88 }

mbusDBValue29		OBJECT-TYPE
			SYNTAX	INTEGER
			ACCESS	read-only
			STATUS	current
	DESCRIPTION ""
			::= { mbusDB 89 }

mbusDBVIF2A		OBJECT-TYPE
			SYNTAX	INTEGER
			ACCESS	read-only
			STATUS	current
	DESCRIPTION ""
			::= { mbusDB 90 }

mbusDBValue2A		OBJECT-TYPE
			SYNTAX	INTEGER
			ACCESS	read-only
			STATUS	current
	DESCRIPTION ""
			::= { mbusDB 91 }

mbusDBVIF2B		OBJECT-TYPE
			SYNTAX	INTEGER
			ACCESS	read-only
			STATUS	current
	DESCRIPTION ""
			::= { mbusDB 92 }

mbusDBValue2B		OBJECT-TYPE
			SYNTAX	INTEGER
			ACCESS	read-only
			STATUS	current
	DESCRIPTION ""
			::= { mbusDB 93 }

mbusDBVIF2C		OBJECT-TYPE
			SYNTAX	INTEGER
			ACCESS	read-only
			STATUS	current
	DESCRIPTION ""
			::= { mbusDB 94 }

mbusDBValue2C		OBJECT-TYPE
			SYNTAX	INTEGER
			ACCESS	read-only
			STATUS	current
	DESCRIPTION ""
			::= { mbusDB 95 }

mbusDBVIF2D		OBJECT-TYPE
			SYNTAX	INTEGER
			ACCESS	read-only
			STATUS	current
	DESCRIPTION ""
			::= { mbusDB 96 }

mbusDBValue2D		OBJECT-TYPE
			SYNTAX	INTEGER
			ACCESS	read-only
			STATUS	current
	DESCRIPTION ""
			::= { mbusDB 97 }

mbusDBVIF2E		OBJECT-TYPE
			SYNTAX	INTEGER
			ACCESS	read-only
			STATUS	current
	DESCRIPTION ""
			::= { mbusDB 98 }

mbusDBValue2E		OBJECT-TYPE
			SYNTAX	INTEGER
			ACCESS	read-only
			STATUS	current
	DESCRIPTION ""
			::= { mbusDB 99 }

mbusDBVIF2F		OBJECT-TYPE
			SYNTAX	INTEGER
			ACCESS	read-only
			STATUS	current
	DESCRIPTION ""
			::= { mbusDB 100 }

mbusDBValue2F		OBJECT-TYPE
			SYNTAX	INTEGER
			ACCESS	read-only
			STATUS	current
	DESCRIPTION ""
			::= { mbusDB 101 }

mbusDC			OBJECT IDENTIFIER ::= { mbus 220 }

mbusDCIdNumber		OBJECT-TYPE
			SYNTAX	Gauge
			ACCESS	read-only
			STATUS	current
	DESCRIPTION ""
			::= { mbusDC 1 }

mbusDCManufacturer	OBJECT-TYPE
			SYNTAX	Gauge
			ACCESS	read-only
			STATUS	current
	DESCRIPTION ""
			::= { mbusDC 2 }

mbusDCVersion		OBJECT-TYPE
			SYNTAX	Gauge
			ACCESS	read-only
			STATUS	current
	DESCRIPTION ""
			::= { mbusDC 3 }

mbusDCMedium		OBJECT-TYPE
			SYNTAX	Gauge
			ACCESS	read-only
			STATUS	current
	DESCRIPTION ""
			::= { mbusDC 4 }

mbusDCStatus		OBJECT-TYPE
			SYNTAX	Gauge
			ACCESS	read-only
			STATUS	current
	DESCRIPTION ""
			::= { mbusDC 5 }

mbusDCVIF00		OBJECT-TYPE
			SYNTAX	INTEGER
			ACCESS	read-only
			STATUS	current
	DESCRIPTION ""
			::= { mbusDC 6 }

mbusDCValue00		OBJECT-TYPE
			SYNTAX	INTEGER
			ACCESS	read-only
			STATUS	current
	DESCRIPTION ""
			::= { mbusDC 7 }

mbusDCVIF01		OBJECT-TYPE
			SYNTAX	INTEGER
			ACCESS	read-only
			STATUS	current
	DESCRIPTION ""
			::= { mbusDC 8 }

mbusDCValue01		OBJECT-TYPE
			SYNTAX	INTEGER
			ACCESS	read-only
			STATUS	current
	DESCRIPTION ""
			::= { mbusDC 9 }

mbusDCVIF02		OBJECT-TYPE
			SYNTAX	INTEGER
			ACCESS	read-only
			STATUS	current
	DESCRIPTION ""
			::= { mbusDC 10 }

mbusDCValue02		OBJECT-TYPE
			SYNTAX	INTEGER
			ACCESS	read-only
			STATUS	current
	DESCRIPTION ""
			::= { mbusDC 11 }

mbusDCVIF03		OBJECT-TYPE
			SYNTAX	INTEGER
			ACCESS	read-only
			STATUS	current
	DESCRIPTION ""
			::= { mbusDC 12 }

mbusDCValue03		OBJECT-TYPE
			SYNTAX	INTEGER
			ACCESS	read-only
			STATUS	current
	DESCRIPTION ""
			::= { mbusDC 13 }

mbusDCVIF04		OBJECT-TYPE
			SYNTAX	INTEGER
			ACCESS	read-only
			STATUS	current
	DESCRIPTION ""
			::= { mbusDC 14 }

mbusDCValue04		OBJECT-TYPE
			SYNTAX	INTEGER
			ACCESS	read-only
			STATUS	current
	DESCRIPTION ""
			::= { mbusDC 15 }

mbusDCVIF05		OBJECT-TYPE
			SYNTAX	INTEGER
			ACCESS	read-only
			STATUS	current
	DESCRIPTION ""
			::= { mbusDC 16 }

mbusDCValue05		OBJECT-TYPE
			SYNTAX	INTEGER
			ACCESS	read-only
			STATUS	current
	DESCRIPTION ""
			::= { mbusDC 17 }

mbusDCVIF06		OBJECT-TYPE
			SYNTAX	INTEGER
			ACCESS	read-only
			STATUS	current
	DESCRIPTION ""
			::= { mbusDC 18 }

mbusDCValue06		OBJECT-TYPE
			SYNTAX	INTEGER
			ACCESS	read-only
			STATUS	current
	DESCRIPTION ""
			::= { mbusDC 19 }

mbusDCVIF07		OBJECT-TYPE
			SYNTAX	INTEGER
			ACCESS	read-only
			STATUS	current
	DESCRIPTION ""
			::= { mbusDC 20 }

mbusDCValue07		OBJECT-TYPE
			SYNTAX	INTEGER
			ACCESS	read-only
			STATUS	current
	DESCRIPTION ""
			::= { mbusDC 21 }

mbusDCVIF08		OBJECT-TYPE
			SYNTAX	INTEGER
			ACCESS	read-only
			STATUS	current
	DESCRIPTION ""
			::= { mbusDC 22 }

mbusDCValue08		OBJECT-TYPE
			SYNTAX	INTEGER
			ACCESS	read-only
			STATUS	current
	DESCRIPTION ""
			::= { mbusDC 23 }

mbusDCVIF09		OBJECT-TYPE
			SYNTAX	INTEGER
			ACCESS	read-only
			STATUS	current
	DESCRIPTION ""
			::= { mbusDC 24 }

mbusDCValue09		OBJECT-TYPE
			SYNTAX	INTEGER
			ACCESS	read-only
			STATUS	current
	DESCRIPTION ""
			::= { mbusDC 25 }

mbusDCVIF0A		OBJECT-TYPE
			SYNTAX	INTEGER
			ACCESS	read-only
			STATUS	current
	DESCRIPTION ""
			::= { mbusDC 26 }

mbusDCValue0A		OBJECT-TYPE
			SYNTAX	INTEGER
			ACCESS	read-only
			STATUS	current
	DESCRIPTION ""
			::= { mbusDC 27 }

mbusDCVIF0B		OBJECT-TYPE
			SYNTAX	INTEGER
			ACCESS	read-only
			STATUS	current
	DESCRIPTION ""
			::= { mbusDC 28 }

mbusDCValue0B		OBJECT-TYPE
			SYNTAX	INTEGER
			ACCESS	read-only
			STATUS	current
	DESCRIPTION ""
			::= { mbusDC 29 }

mbusDCVIF0C		OBJECT-TYPE
			SYNTAX	INTEGER
			ACCESS	read-only
			STATUS	current
	DESCRIPTION ""
			::= { mbusDC 30 }

mbusDCValue0C		OBJECT-TYPE
			SYNTAX	INTEGER
			ACCESS	read-only
			STATUS	current
	DESCRIPTION ""
			::= { mbusDC 31 }

mbusDCVIF0D		OBJECT-TYPE
			SYNTAX	INTEGER
			ACCESS	read-only
			STATUS	current
	DESCRIPTION ""
			::= { mbusDC 32 }

mbusDCValue0D		OBJECT-TYPE
			SYNTAX	INTEGER
			ACCESS	read-only
			STATUS	current
	DESCRIPTION ""
			::= { mbusDC 33 }

mbusDCVIF0E		OBJECT-TYPE
			SYNTAX	INTEGER
			ACCESS	read-only
			STATUS	current
	DESCRIPTION ""
			::= { mbusDC 34 }

mbusDCValue0E		OBJECT-TYPE
			SYNTAX	INTEGER
			ACCESS	read-only
			STATUS	current
	DESCRIPTION ""
			::= { mbusDC 35 }

mbusDCVIF0F		OBJECT-TYPE
			SYNTAX	INTEGER
			ACCESS	read-only
			STATUS	current
	DESCRIPTION ""
			::= { mbusDC 36 }

mbusDCValue0F		OBJECT-TYPE
			SYNTAX	INTEGER
			ACCESS	read-only
			STATUS	current
	DESCRIPTION ""
			::= { mbusDC 37 }

mbusDCVIF10		OBJECT-TYPE
			SYNTAX	INTEGER
			ACCESS	read-only
			STATUS	current
	DESCRIPTION ""
			::= { mbusDC 38 }

mbusDCValue10		OBJECT-TYPE
			SYNTAX	INTEGER
			ACCESS	read-only
			STATUS	current
	DESCRIPTION ""
			::= { mbusDC 39 }

mbusDCVIF11		OBJECT-TYPE
			SYNTAX	INTEGER
			ACCESS	read-only
			STATUS	current
	DESCRIPTION ""
			::= { mbusDC 40 }

mbusDCValue11		OBJECT-TYPE
			SYNTAX	INTEGER
			ACCESS	read-only
			STATUS	current
	DESCRIPTION ""
			::= { mbusDC 41 }

mbusDCVIF12		OBJECT-TYPE
			SYNTAX	INTEGER
			ACCESS	read-only
			STATUS	current
	DESCRIPTION ""
			::= { mbusDC 42 }

mbusDCValue12		OBJECT-TYPE
			SYNTAX	INTEGER
			ACCESS	read-only
			STATUS	current
	DESCRIPTION ""
			::= { mbusDC 43 }

mbusDCVIF13		OBJECT-TYPE
			SYNTAX	INTEGER
			ACCESS	read-only
			STATUS	current
	DESCRIPTION ""
			::= { mbusDC 44 }

mbusDCValue13		OBJECT-TYPE
			SYNTAX	INTEGER
			ACCESS	read-only
			STATUS	current
	DESCRIPTION ""
			::= { mbusDC 45 }

mbusDCVIF14		OBJECT-TYPE
			SYNTAX	INTEGER
			ACCESS	read-only
			STATUS	current
	DESCRIPTION ""
			::= { mbusDC 46 }

mbusDCValue14		OBJECT-TYPE
			SYNTAX	INTEGER
			ACCESS	read-only
			STATUS	current
	DESCRIPTION ""
			::= { mbusDC 47 }

mbusDCVIF15		OBJECT-TYPE
			SYNTAX	INTEGER
			ACCESS	read-only
			STATUS	current
	DESCRIPTION ""
			::= { mbusDC 48 }

mbusDCValue15		OBJECT-TYPE
			SYNTAX	INTEGER
			ACCESS	read-only
			STATUS	current
	DESCRIPTION ""
			::= { mbusDC 49 }

mbusDCVIF16		OBJECT-TYPE
			SYNTAX	INTEGER
			ACCESS	read-only
			STATUS	current
	DESCRIPTION ""
			::= { mbusDC 50 }

mbusDCValue16		OBJECT-TYPE
			SYNTAX	INTEGER
			ACCESS	read-only
			STATUS	current
	DESCRIPTION ""
			::= { mbusDC 51 }

mbusDCVIF17		OBJECT-TYPE
			SYNTAX	INTEGER
			ACCESS	read-only
			STATUS	current
	DESCRIPTION ""
			::= { mbusDC 52 }

mbusDCValue17		OBJECT-TYPE
			SYNTAX	INTEGER
			ACCESS	read-only
			STATUS	current
	DESCRIPTION ""
			::= { mbusDC 53 }

mbusDCVIF18		OBJECT-TYPE
			SYNTAX	INTEGER
			ACCESS	read-only
			STATUS	current
	DESCRIPTION ""
			::= { mbusDC 54 }

mbusDCValue18		OBJECT-TYPE
			SYNTAX	INTEGER
			ACCESS	read-only
			STATUS	current
	DESCRIPTION ""
			::= { mbusDC 55 }

mbusDCVIF19		OBJECT-TYPE
			SYNTAX	INTEGER
			ACCESS	read-only
			STATUS	current
	DESCRIPTION ""
			::= { mbusDC 56 }

mbusDCValue19		OBJECT-TYPE
			SYNTAX	INTEGER
			ACCESS	read-only
			STATUS	current
	DESCRIPTION ""
			::= { mbusDC 57 }

mbusDCVIF1A		OBJECT-TYPE
			SYNTAX	INTEGER
			ACCESS	read-only
			STATUS	current
	DESCRIPTION ""
			::= { mbusDC 58 }

mbusDCValue1A		OBJECT-TYPE
			SYNTAX	INTEGER
			ACCESS	read-only
			STATUS	current
	DESCRIPTION ""
			::= { mbusDC 59 }

mbusDCVIF1B		OBJECT-TYPE
			SYNTAX	INTEGER
			ACCESS	read-only
			STATUS	current
	DESCRIPTION ""
			::= { mbusDC 60 }

mbusDCValue1B		OBJECT-TYPE
			SYNTAX	INTEGER
			ACCESS	read-only
			STATUS	current
	DESCRIPTION ""
			::= { mbusDC 61 }

mbusDCVIF1C		OBJECT-TYPE
			SYNTAX	INTEGER
			ACCESS	read-only
			STATUS	current
	DESCRIPTION ""
			::= { mbusDC 62 }

mbusDCValue1C		OBJECT-TYPE
			SYNTAX	INTEGER
			ACCESS	read-only
			STATUS	current
	DESCRIPTION ""
			::= { mbusDC 63 }

mbusDCVIF1D		OBJECT-TYPE
			SYNTAX	INTEGER
			ACCESS	read-only
			STATUS	current
	DESCRIPTION ""
			::= { mbusDC 64 }

mbusDCValue1D		OBJECT-TYPE
			SYNTAX	INTEGER
			ACCESS	read-only
			STATUS	current
	DESCRIPTION ""
			::= { mbusDC 65 }

mbusDCVIF1E		OBJECT-TYPE
			SYNTAX	INTEGER
			ACCESS	read-only
			STATUS	current
	DESCRIPTION ""
			::= { mbusDC 66 }

mbusDCValue1E		OBJECT-TYPE
			SYNTAX	INTEGER
			ACCESS	read-only
			STATUS	current
	DESCRIPTION ""
			::= { mbusDC 67 }

mbusDCVIF1F		OBJECT-TYPE
			SYNTAX	INTEGER
			ACCESS	read-only
			STATUS	current
	DESCRIPTION ""
			::= { mbusDC 68 }

mbusDCValue1F		OBJECT-TYPE
			SYNTAX	INTEGER
			ACCESS	read-only
			STATUS	current
	DESCRIPTION ""
			::= { mbusDC 69 }

mbusDCVIF20		OBJECT-TYPE
			SYNTAX	INTEGER
			ACCESS	read-only
			STATUS	current
	DESCRIPTION ""
			::= { mbusDC 70 }

mbusDCValue20		OBJECT-TYPE
			SYNTAX	INTEGER
			ACCESS	read-only
			STATUS	current
	DESCRIPTION ""
			::= { mbusDC 71 }

mbusDCVIF21		OBJECT-TYPE
			SYNTAX	INTEGER
			ACCESS	read-only
			STATUS	current
	DESCRIPTION ""
			::= { mbusDC 72 }

mbusDCValue21		OBJECT-TYPE
			SYNTAX	INTEGER
			ACCESS	read-only
			STATUS	current
	DESCRIPTION ""
			::= { mbusDC 73 }

mbusDCVIF22		OBJECT-TYPE
			SYNTAX	INTEGER
			ACCESS	read-only
			STATUS	current
	DESCRIPTION ""
			::= { mbusDC 74 }

mbusDCValue22		OBJECT-TYPE
			SYNTAX	INTEGER
			ACCESS	read-only
			STATUS	current
	DESCRIPTION ""
			::= { mbusDC 75 }

mbusDCVIF23		OBJECT-TYPE
			SYNTAX	INTEGER
			ACCESS	read-only
			STATUS	current
	DESCRIPTION ""
			::= { mbusDC 76 }

mbusDCValue23		OBJECT-TYPE
			SYNTAX	INTEGER
			ACCESS	read-only
			STATUS	current
	DESCRIPTION ""
			::= { mbusDC 77 }

mbusDCVIF24		OBJECT-TYPE
			SYNTAX	INTEGER
			ACCESS	read-only
			STATUS	current
	DESCRIPTION ""
			::= { mbusDC 78 }

mbusDCValue24		OBJECT-TYPE
			SYNTAX	INTEGER
			ACCESS	read-only
			STATUS	current
	DESCRIPTION ""
			::= { mbusDC 79 }

mbusDCVIF25		OBJECT-TYPE
			SYNTAX	INTEGER
			ACCESS	read-only
			STATUS	current
	DESCRIPTION ""
			::= { mbusDC 80 }

mbusDCValue25		OBJECT-TYPE
			SYNTAX	INTEGER
			ACCESS	read-only
			STATUS	current
	DESCRIPTION ""
			::= { mbusDC 81 }

mbusDCVIF26		OBJECT-TYPE
			SYNTAX	INTEGER
			ACCESS	read-only
			STATUS	current
	DESCRIPTION ""
			::= { mbusDC 82 }

mbusDCValue26		OBJECT-TYPE
			SYNTAX	INTEGER
			ACCESS	read-only
			STATUS	current
	DESCRIPTION ""
			::= { mbusDC 83 }

mbusDCVIF27		OBJECT-TYPE
			SYNTAX	INTEGER
			ACCESS	read-only
			STATUS	current
	DESCRIPTION ""
			::= { mbusDC 84 }

mbusDCValue27		OBJECT-TYPE
			SYNTAX	INTEGER
			ACCESS	read-only
			STATUS	current
	DESCRIPTION ""
			::= { mbusDC 85 }

mbusDCVIF28		OBJECT-TYPE
			SYNTAX	INTEGER
			ACCESS	read-only
			STATUS	current
	DESCRIPTION ""
			::= { mbusDC 86 }

mbusDCValue28		OBJECT-TYPE
			SYNTAX	INTEGER
			ACCESS	read-only
			STATUS	current
	DESCRIPTION ""
			::= { mbusDC 87 }

mbusDCVIF29		OBJECT-TYPE
			SYNTAX	INTEGER
			ACCESS	read-only
			STATUS	current
	DESCRIPTION ""
			::= { mbusDC 88 }

mbusDCValue29		OBJECT-TYPE
			SYNTAX	INTEGER
			ACCESS	read-only
			STATUS	current
	DESCRIPTION ""
			::= { mbusDC 89 }

mbusDCVIF2A		OBJECT-TYPE
			SYNTAX	INTEGER
			ACCESS	read-only
			STATUS	current
	DESCRIPTION ""
			::= { mbusDC 90 }

mbusDCValue2A		OBJECT-TYPE
			SYNTAX	INTEGER
			ACCESS	read-only
			STATUS	current
	DESCRIPTION ""
			::= { mbusDC 91 }

mbusDCVIF2B		OBJECT-TYPE
			SYNTAX	INTEGER
			ACCESS	read-only
			STATUS	current
	DESCRIPTION ""
			::= { mbusDC 92 }

mbusDCValue2B		OBJECT-TYPE
			SYNTAX	INTEGER
			ACCESS	read-only
			STATUS	current
	DESCRIPTION ""
			::= { mbusDC 93 }

mbusDCVIF2C		OBJECT-TYPE
			SYNTAX	INTEGER
			ACCESS	read-only
			STATUS	current
	DESCRIPTION ""
			::= { mbusDC 94 }

mbusDCValue2C		OBJECT-TYPE
			SYNTAX	INTEGER
			ACCESS	read-only
			STATUS	current
	DESCRIPTION ""
			::= { mbusDC 95 }

mbusDCVIF2D		OBJECT-TYPE
			SYNTAX	INTEGER
			ACCESS	read-only
			STATUS	current
	DESCRIPTION ""
			::= { mbusDC 96 }

mbusDCValue2D		OBJECT-TYPE
			SYNTAX	INTEGER
			ACCESS	read-only
			STATUS	current
	DESCRIPTION ""
			::= { mbusDC 97 }

mbusDCVIF2E		OBJECT-TYPE
			SYNTAX	INTEGER
			ACCESS	read-only
			STATUS	current
	DESCRIPTION ""
			::= { mbusDC 98 }

mbusDCValue2E		OBJECT-TYPE
			SYNTAX	INTEGER
			ACCESS	read-only
			STATUS	current
	DESCRIPTION ""
			::= { mbusDC 99 }

mbusDCVIF2F		OBJECT-TYPE
			SYNTAX	INTEGER
			ACCESS	read-only
			STATUS	current
	DESCRIPTION ""
			::= { mbusDC 100 }

mbusDCValue2F		OBJECT-TYPE
			SYNTAX	INTEGER
			ACCESS	read-only
			STATUS	current
	DESCRIPTION ""
			::= { mbusDC 101 }

mbusDD			OBJECT IDENTIFIER ::= { mbus 221 }

mbusDDIdNumber		OBJECT-TYPE
			SYNTAX	Gauge
			ACCESS	read-only
			STATUS	current
	DESCRIPTION ""
			::= { mbusDD 1 }

mbusDDManufacturer	OBJECT-TYPE
			SYNTAX	Gauge
			ACCESS	read-only
			STATUS	current
	DESCRIPTION ""
			::= { mbusDD 2 }

mbusDDVersion		OBJECT-TYPE
			SYNTAX	Gauge
			ACCESS	read-only
			STATUS	current
	DESCRIPTION ""
			::= { mbusDD 3 }

mbusDDMedium		OBJECT-TYPE
			SYNTAX	Gauge
			ACCESS	read-only
			STATUS	current
	DESCRIPTION ""
			::= { mbusDD 4 }

mbusDDStatus		OBJECT-TYPE
			SYNTAX	Gauge
			ACCESS	read-only
			STATUS	current
	DESCRIPTION ""
			::= { mbusDD 5 }

mbusDDVIF00		OBJECT-TYPE
			SYNTAX	INTEGER
			ACCESS	read-only
			STATUS	current
	DESCRIPTION ""
			::= { mbusDD 6 }

mbusDDValue00		OBJECT-TYPE
			SYNTAX	INTEGER
			ACCESS	read-only
			STATUS	current
	DESCRIPTION ""
			::= { mbusDD 7 }

mbusDDVIF01		OBJECT-TYPE
			SYNTAX	INTEGER
			ACCESS	read-only
			STATUS	current
	DESCRIPTION ""
			::= { mbusDD 8 }

mbusDDValue01		OBJECT-TYPE
			SYNTAX	INTEGER
			ACCESS	read-only
			STATUS	current
	DESCRIPTION ""
			::= { mbusDD 9 }

mbusDDVIF02		OBJECT-TYPE
			SYNTAX	INTEGER
			ACCESS	read-only
			STATUS	current
	DESCRIPTION ""
			::= { mbusDD 10 }

mbusDDValue02		OBJECT-TYPE
			SYNTAX	INTEGER
			ACCESS	read-only
			STATUS	current
	DESCRIPTION ""
			::= { mbusDD 11 }

mbusDDVIF03		OBJECT-TYPE
			SYNTAX	INTEGER
			ACCESS	read-only
			STATUS	current
	DESCRIPTION ""
			::= { mbusDD 12 }

mbusDDValue03		OBJECT-TYPE
			SYNTAX	INTEGER
			ACCESS	read-only
			STATUS	current
	DESCRIPTION ""
			::= { mbusDD 13 }

mbusDDVIF04		OBJECT-TYPE
			SYNTAX	INTEGER
			ACCESS	read-only
			STATUS	current
	DESCRIPTION ""
			::= { mbusDD 14 }

mbusDDValue04		OBJECT-TYPE
			SYNTAX	INTEGER
			ACCESS	read-only
			STATUS	current
	DESCRIPTION ""
			::= { mbusDD 15 }

mbusDDVIF05		OBJECT-TYPE
			SYNTAX	INTEGER
			ACCESS	read-only
			STATUS	current
	DESCRIPTION ""
			::= { mbusDD 16 }

mbusDDValue05		OBJECT-TYPE
			SYNTAX	INTEGER
			ACCESS	read-only
			STATUS	current
	DESCRIPTION ""
			::= { mbusDD 17 }

mbusDDVIF06		OBJECT-TYPE
			SYNTAX	INTEGER
			ACCESS	read-only
			STATUS	current
	DESCRIPTION ""
			::= { mbusDD 18 }

mbusDDValue06		OBJECT-TYPE
			SYNTAX	INTEGER
			ACCESS	read-only
			STATUS	current
	DESCRIPTION ""
			::= { mbusDD 19 }

mbusDDVIF07		OBJECT-TYPE
			SYNTAX	INTEGER
			ACCESS	read-only
			STATUS	current
	DESCRIPTION ""
			::= { mbusDD 20 }

mbusDDValue07		OBJECT-TYPE
			SYNTAX	INTEGER
			ACCESS	read-only
			STATUS	current
	DESCRIPTION ""
			::= { mbusDD 21 }

mbusDDVIF08		OBJECT-TYPE
			SYNTAX	INTEGER
			ACCESS	read-only
			STATUS	current
	DESCRIPTION ""
			::= { mbusDD 22 }

mbusDDValue08		OBJECT-TYPE
			SYNTAX	INTEGER
			ACCESS	read-only
			STATUS	current
	DESCRIPTION ""
			::= { mbusDD 23 }

mbusDDVIF09		OBJECT-TYPE
			SYNTAX	INTEGER
			ACCESS	read-only
			STATUS	current
	DESCRIPTION ""
			::= { mbusDD 24 }

mbusDDValue09		OBJECT-TYPE
			SYNTAX	INTEGER
			ACCESS	read-only
			STATUS	current
	DESCRIPTION ""
			::= { mbusDD 25 }

mbusDDVIF0A		OBJECT-TYPE
			SYNTAX	INTEGER
			ACCESS	read-only
			STATUS	current
	DESCRIPTION ""
			::= { mbusDD 26 }

mbusDDValue0A		OBJECT-TYPE
			SYNTAX	INTEGER
			ACCESS	read-only
			STATUS	current
	DESCRIPTION ""
			::= { mbusDD 27 }

mbusDDVIF0B		OBJECT-TYPE
			SYNTAX	INTEGER
			ACCESS	read-only
			STATUS	current
	DESCRIPTION ""
			::= { mbusDD 28 }

mbusDDValue0B		OBJECT-TYPE
			SYNTAX	INTEGER
			ACCESS	read-only
			STATUS	current
	DESCRIPTION ""
			::= { mbusDD 29 }

mbusDDVIF0C		OBJECT-TYPE
			SYNTAX	INTEGER
			ACCESS	read-only
			STATUS	current
	DESCRIPTION ""
			::= { mbusDD 30 }

mbusDDValue0C		OBJECT-TYPE
			SYNTAX	INTEGER
			ACCESS	read-only
			STATUS	current
	DESCRIPTION ""
			::= { mbusDD 31 }

mbusDDVIF0D		OBJECT-TYPE
			SYNTAX	INTEGER
			ACCESS	read-only
			STATUS	current
	DESCRIPTION ""
			::= { mbusDD 32 }

mbusDDValue0D		OBJECT-TYPE
			SYNTAX	INTEGER
			ACCESS	read-only
			STATUS	current
	DESCRIPTION ""
			::= { mbusDD 33 }

mbusDDVIF0E		OBJECT-TYPE
			SYNTAX	INTEGER
			ACCESS	read-only
			STATUS	current
	DESCRIPTION ""
			::= { mbusDD 34 }

mbusDDValue0E		OBJECT-TYPE
			SYNTAX	INTEGER
			ACCESS	read-only
			STATUS	current
	DESCRIPTION ""
			::= { mbusDD 35 }

mbusDDVIF0F		OBJECT-TYPE
			SYNTAX	INTEGER
			ACCESS	read-only
			STATUS	current
	DESCRIPTION ""
			::= { mbusDD 36 }

mbusDDValue0F		OBJECT-TYPE
			SYNTAX	INTEGER
			ACCESS	read-only
			STATUS	current
	DESCRIPTION ""
			::= { mbusDD 37 }

mbusDDVIF10		OBJECT-TYPE
			SYNTAX	INTEGER
			ACCESS	read-only
			STATUS	current
	DESCRIPTION ""
			::= { mbusDD 38 }

mbusDDValue10		OBJECT-TYPE
			SYNTAX	INTEGER
			ACCESS	read-only
			STATUS	current
	DESCRIPTION ""
			::= { mbusDD 39 }

mbusDDVIF11		OBJECT-TYPE
			SYNTAX	INTEGER
			ACCESS	read-only
			STATUS	current
	DESCRIPTION ""
			::= { mbusDD 40 }

mbusDDValue11		OBJECT-TYPE
			SYNTAX	INTEGER
			ACCESS	read-only
			STATUS	current
	DESCRIPTION ""
			::= { mbusDD 41 }

mbusDDVIF12		OBJECT-TYPE
			SYNTAX	INTEGER
			ACCESS	read-only
			STATUS	current
	DESCRIPTION ""
			::= { mbusDD 42 }

mbusDDValue12		OBJECT-TYPE
			SYNTAX	INTEGER
			ACCESS	read-only
			STATUS	current
	DESCRIPTION ""
			::= { mbusDD 43 }

mbusDDVIF13		OBJECT-TYPE
			SYNTAX	INTEGER
			ACCESS	read-only
			STATUS	current
	DESCRIPTION ""
			::= { mbusDD 44 }

mbusDDValue13		OBJECT-TYPE
			SYNTAX	INTEGER
			ACCESS	read-only
			STATUS	current
	DESCRIPTION ""
			::= { mbusDD 45 }

mbusDDVIF14		OBJECT-TYPE
			SYNTAX	INTEGER
			ACCESS	read-only
			STATUS	current
	DESCRIPTION ""
			::= { mbusDD 46 }

mbusDDValue14		OBJECT-TYPE
			SYNTAX	INTEGER
			ACCESS	read-only
			STATUS	current
	DESCRIPTION ""
			::= { mbusDD 47 }

mbusDDVIF15		OBJECT-TYPE
			SYNTAX	INTEGER
			ACCESS	read-only
			STATUS	current
	DESCRIPTION ""
			::= { mbusDD 48 }

mbusDDValue15		OBJECT-TYPE
			SYNTAX	INTEGER
			ACCESS	read-only
			STATUS	current
	DESCRIPTION ""
			::= { mbusDD 49 }

mbusDDVIF16		OBJECT-TYPE
			SYNTAX	INTEGER
			ACCESS	read-only
			STATUS	current
	DESCRIPTION ""
			::= { mbusDD 50 }

mbusDDValue16		OBJECT-TYPE
			SYNTAX	INTEGER
			ACCESS	read-only
			STATUS	current
	DESCRIPTION ""
			::= { mbusDD 51 }

mbusDDVIF17		OBJECT-TYPE
			SYNTAX	INTEGER
			ACCESS	read-only
			STATUS	current
	DESCRIPTION ""
			::= { mbusDD 52 }

mbusDDValue17		OBJECT-TYPE
			SYNTAX	INTEGER
			ACCESS	read-only
			STATUS	current
	DESCRIPTION ""
			::= { mbusDD 53 }

mbusDDVIF18		OBJECT-TYPE
			SYNTAX	INTEGER
			ACCESS	read-only
			STATUS	current
	DESCRIPTION ""
			::= { mbusDD 54 }

mbusDDValue18		OBJECT-TYPE
			SYNTAX	INTEGER
			ACCESS	read-only
			STATUS	current
	DESCRIPTION ""
			::= { mbusDD 55 }

mbusDDVIF19		OBJECT-TYPE
			SYNTAX	INTEGER
			ACCESS	read-only
			STATUS	current
	DESCRIPTION ""
			::= { mbusDD 56 }

mbusDDValue19		OBJECT-TYPE
			SYNTAX	INTEGER
			ACCESS	read-only
			STATUS	current
	DESCRIPTION ""
			::= { mbusDD 57 }

mbusDDVIF1A		OBJECT-TYPE
			SYNTAX	INTEGER
			ACCESS	read-only
			STATUS	current
	DESCRIPTION ""
			::= { mbusDD 58 }

mbusDDValue1A		OBJECT-TYPE
			SYNTAX	INTEGER
			ACCESS	read-only
			STATUS	current
	DESCRIPTION ""
			::= { mbusDD 59 }

mbusDDVIF1B		OBJECT-TYPE
			SYNTAX	INTEGER
			ACCESS	read-only
			STATUS	current
	DESCRIPTION ""
			::= { mbusDD 60 }

mbusDDValue1B		OBJECT-TYPE
			SYNTAX	INTEGER
			ACCESS	read-only
			STATUS	current
	DESCRIPTION ""
			::= { mbusDD 61 }

mbusDDVIF1C		OBJECT-TYPE
			SYNTAX	INTEGER
			ACCESS	read-only
			STATUS	current
	DESCRIPTION ""
			::= { mbusDD 62 }

mbusDDValue1C		OBJECT-TYPE
			SYNTAX	INTEGER
			ACCESS	read-only
			STATUS	current
	DESCRIPTION ""
			::= { mbusDD 63 }

mbusDDVIF1D		OBJECT-TYPE
			SYNTAX	INTEGER
			ACCESS	read-only
			STATUS	current
	DESCRIPTION ""
			::= { mbusDD 64 }

mbusDDValue1D		OBJECT-TYPE
			SYNTAX	INTEGER
			ACCESS	read-only
			STATUS	current
	DESCRIPTION ""
			::= { mbusDD 65 }

mbusDDVIF1E		OBJECT-TYPE
			SYNTAX	INTEGER
			ACCESS	read-only
			STATUS	current
	DESCRIPTION ""
			::= { mbusDD 66 }

mbusDDValue1E		OBJECT-TYPE
			SYNTAX	INTEGER
			ACCESS	read-only
			STATUS	current
	DESCRIPTION ""
			::= { mbusDD 67 }

mbusDDVIF1F		OBJECT-TYPE
			SYNTAX	INTEGER
			ACCESS	read-only
			STATUS	current
	DESCRIPTION ""
			::= { mbusDD 68 }

mbusDDValue1F		OBJECT-TYPE
			SYNTAX	INTEGER
			ACCESS	read-only
			STATUS	current
	DESCRIPTION ""
			::= { mbusDD 69 }

mbusDDVIF20		OBJECT-TYPE
			SYNTAX	INTEGER
			ACCESS	read-only
			STATUS	current
	DESCRIPTION ""
			::= { mbusDD 70 }

mbusDDValue20		OBJECT-TYPE
			SYNTAX	INTEGER
			ACCESS	read-only
			STATUS	current
	DESCRIPTION ""
			::= { mbusDD 71 }

mbusDDVIF21		OBJECT-TYPE
			SYNTAX	INTEGER
			ACCESS	read-only
			STATUS	current
	DESCRIPTION ""
			::= { mbusDD 72 }

mbusDDValue21		OBJECT-TYPE
			SYNTAX	INTEGER
			ACCESS	read-only
			STATUS	current
	DESCRIPTION ""
			::= { mbusDD 73 }

mbusDDVIF22		OBJECT-TYPE
			SYNTAX	INTEGER
			ACCESS	read-only
			STATUS	current
	DESCRIPTION ""
			::= { mbusDD 74 }

mbusDDValue22		OBJECT-TYPE
			SYNTAX	INTEGER
			ACCESS	read-only
			STATUS	current
	DESCRIPTION ""
			::= { mbusDD 75 }

mbusDDVIF23		OBJECT-TYPE
			SYNTAX	INTEGER
			ACCESS	read-only
			STATUS	current
	DESCRIPTION ""
			::= { mbusDD 76 }

mbusDDValue23		OBJECT-TYPE
			SYNTAX	INTEGER
			ACCESS	read-only
			STATUS	current
	DESCRIPTION ""
			::= { mbusDD 77 }

mbusDDVIF24		OBJECT-TYPE
			SYNTAX	INTEGER
			ACCESS	read-only
			STATUS	current
	DESCRIPTION ""
			::= { mbusDD 78 }

mbusDDValue24		OBJECT-TYPE
			SYNTAX	INTEGER
			ACCESS	read-only
			STATUS	current
	DESCRIPTION ""
			::= { mbusDD 79 }

mbusDDVIF25		OBJECT-TYPE
			SYNTAX	INTEGER
			ACCESS	read-only
			STATUS	current
	DESCRIPTION ""
			::= { mbusDD 80 }

mbusDDValue25		OBJECT-TYPE
			SYNTAX	INTEGER
			ACCESS	read-only
			STATUS	current
	DESCRIPTION ""
			::= { mbusDD 81 }

mbusDDVIF26		OBJECT-TYPE
			SYNTAX	INTEGER
			ACCESS	read-only
			STATUS	current
	DESCRIPTION ""
			::= { mbusDD 82 }

mbusDDValue26		OBJECT-TYPE
			SYNTAX	INTEGER
			ACCESS	read-only
			STATUS	current
	DESCRIPTION ""
			::= { mbusDD 83 }

mbusDDVIF27		OBJECT-TYPE
			SYNTAX	INTEGER
			ACCESS	read-only
			STATUS	current
	DESCRIPTION ""
			::= { mbusDD 84 }

mbusDDValue27		OBJECT-TYPE
			SYNTAX	INTEGER
			ACCESS	read-only
			STATUS	current
	DESCRIPTION ""
			::= { mbusDD 85 }

mbusDDVIF28		OBJECT-TYPE
			SYNTAX	INTEGER
			ACCESS	read-only
			STATUS	current
	DESCRIPTION ""
			::= { mbusDD 86 }

mbusDDValue28		OBJECT-TYPE
			SYNTAX	INTEGER
			ACCESS	read-only
			STATUS	current
	DESCRIPTION ""
			::= { mbusDD 87 }

mbusDDVIF29		OBJECT-TYPE
			SYNTAX	INTEGER
			ACCESS	read-only
			STATUS	current
	DESCRIPTION ""
			::= { mbusDD 88 }

mbusDDValue29		OBJECT-TYPE
			SYNTAX	INTEGER
			ACCESS	read-only
			STATUS	current
	DESCRIPTION ""
			::= { mbusDD 89 }

mbusDDVIF2A		OBJECT-TYPE
			SYNTAX	INTEGER
			ACCESS	read-only
			STATUS	current
	DESCRIPTION ""
			::= { mbusDD 90 }

mbusDDValue2A		OBJECT-TYPE
			SYNTAX	INTEGER
			ACCESS	read-only
			STATUS	current
	DESCRIPTION ""
			::= { mbusDD 91 }

mbusDDVIF2B		OBJECT-TYPE
			SYNTAX	INTEGER
			ACCESS	read-only
			STATUS	current
	DESCRIPTION ""
			::= { mbusDD 92 }

mbusDDValue2B		OBJECT-TYPE
			SYNTAX	INTEGER
			ACCESS	read-only
			STATUS	current
	DESCRIPTION ""
			::= { mbusDD 93 }

mbusDDVIF2C		OBJECT-TYPE
			SYNTAX	INTEGER
			ACCESS	read-only
			STATUS	current
	DESCRIPTION ""
			::= { mbusDD 94 }

mbusDDValue2C		OBJECT-TYPE
			SYNTAX	INTEGER
			ACCESS	read-only
			STATUS	current
	DESCRIPTION ""
			::= { mbusDD 95 }

mbusDDVIF2D		OBJECT-TYPE
			SYNTAX	INTEGER
			ACCESS	read-only
			STATUS	current
	DESCRIPTION ""
			::= { mbusDD 96 }

mbusDDValue2D		OBJECT-TYPE
			SYNTAX	INTEGER
			ACCESS	read-only
			STATUS	current
	DESCRIPTION ""
			::= { mbusDD 97 }

mbusDDVIF2E		OBJECT-TYPE
			SYNTAX	INTEGER
			ACCESS	read-only
			STATUS	current
	DESCRIPTION ""
			::= { mbusDD 98 }

mbusDDValue2E		OBJECT-TYPE
			SYNTAX	INTEGER
			ACCESS	read-only
			STATUS	current
	DESCRIPTION ""
			::= { mbusDD 99 }

mbusDDVIF2F		OBJECT-TYPE
			SYNTAX	INTEGER
			ACCESS	read-only
			STATUS	current
	DESCRIPTION ""
			::= { mbusDD 100 }

mbusDDValue2F		OBJECT-TYPE
			SYNTAX	INTEGER
			ACCESS	read-only
			STATUS	current
	DESCRIPTION ""
			::= { mbusDD 101 }

mbusDE			OBJECT IDENTIFIER ::= { mbus 222 }

mbusDEIdNumber		OBJECT-TYPE
			SYNTAX	Gauge
			ACCESS	read-only
			STATUS	current
	DESCRIPTION ""
			::= { mbusDE 1 }

mbusDEManufacturer	OBJECT-TYPE
			SYNTAX	Gauge
			ACCESS	read-only
			STATUS	current
	DESCRIPTION ""
			::= { mbusDE 2 }

mbusDEVersion		OBJECT-TYPE
			SYNTAX	Gauge
			ACCESS	read-only
			STATUS	current
	DESCRIPTION ""
			::= { mbusDE 3 }

mbusDEMedium		OBJECT-TYPE
			SYNTAX	Gauge
			ACCESS	read-only
			STATUS	current
	DESCRIPTION ""
			::= { mbusDE 4 }

mbusDEStatus		OBJECT-TYPE
			SYNTAX	Gauge
			ACCESS	read-only
			STATUS	current
	DESCRIPTION ""
			::= { mbusDE 5 }

mbusDEVIF00		OBJECT-TYPE
			SYNTAX	INTEGER
			ACCESS	read-only
			STATUS	current
	DESCRIPTION ""
			::= { mbusDE 6 }

mbusDEValue00		OBJECT-TYPE
			SYNTAX	INTEGER
			ACCESS	read-only
			STATUS	current
	DESCRIPTION ""
			::= { mbusDE 7 }

mbusDEVIF01		OBJECT-TYPE
			SYNTAX	INTEGER
			ACCESS	read-only
			STATUS	current
	DESCRIPTION ""
			::= { mbusDE 8 }

mbusDEValue01		OBJECT-TYPE
			SYNTAX	INTEGER
			ACCESS	read-only
			STATUS	current
	DESCRIPTION ""
			::= { mbusDE 9 }

mbusDEVIF02		OBJECT-TYPE
			SYNTAX	INTEGER
			ACCESS	read-only
			STATUS	current
	DESCRIPTION ""
			::= { mbusDE 10 }

mbusDEValue02		OBJECT-TYPE
			SYNTAX	INTEGER
			ACCESS	read-only
			STATUS	current
	DESCRIPTION ""
			::= { mbusDE 11 }

mbusDEVIF03		OBJECT-TYPE
			SYNTAX	INTEGER
			ACCESS	read-only
			STATUS	current
	DESCRIPTION ""
			::= { mbusDE 12 }

mbusDEValue03		OBJECT-TYPE
			SYNTAX	INTEGER
			ACCESS	read-only
			STATUS	current
	DESCRIPTION ""
			::= { mbusDE 13 }

mbusDEVIF04		OBJECT-TYPE
			SYNTAX	INTEGER
			ACCESS	read-only
			STATUS	current
	DESCRIPTION ""
			::= { mbusDE 14 }

mbusDEValue04		OBJECT-TYPE
			SYNTAX	INTEGER
			ACCESS	read-only
			STATUS	current
	DESCRIPTION ""
			::= { mbusDE 15 }

mbusDEVIF05		OBJECT-TYPE
			SYNTAX	INTEGER
			ACCESS	read-only
			STATUS	current
	DESCRIPTION ""
			::= { mbusDE 16 }

mbusDEValue05		OBJECT-TYPE
			SYNTAX	INTEGER
			ACCESS	read-only
			STATUS	current
	DESCRIPTION ""
			::= { mbusDE 17 }

mbusDEVIF06		OBJECT-TYPE
			SYNTAX	INTEGER
			ACCESS	read-only
			STATUS	current
	DESCRIPTION ""
			::= { mbusDE 18 }

mbusDEValue06		OBJECT-TYPE
			SYNTAX	INTEGER
			ACCESS	read-only
			STATUS	current
	DESCRIPTION ""
			::= { mbusDE 19 }

mbusDEVIF07		OBJECT-TYPE
			SYNTAX	INTEGER
			ACCESS	read-only
			STATUS	current
	DESCRIPTION ""
			::= { mbusDE 20 }

mbusDEValue07		OBJECT-TYPE
			SYNTAX	INTEGER
			ACCESS	read-only
			STATUS	current
	DESCRIPTION ""
			::= { mbusDE 21 }

mbusDEVIF08		OBJECT-TYPE
			SYNTAX	INTEGER
			ACCESS	read-only
			STATUS	current
	DESCRIPTION ""
			::= { mbusDE 22 }

mbusDEValue08		OBJECT-TYPE
			SYNTAX	INTEGER
			ACCESS	read-only
			STATUS	current
	DESCRIPTION ""
			::= { mbusDE 23 }

mbusDEVIF09		OBJECT-TYPE
			SYNTAX	INTEGER
			ACCESS	read-only
			STATUS	current
	DESCRIPTION ""
			::= { mbusDE 24 }

mbusDEValue09		OBJECT-TYPE
			SYNTAX	INTEGER
			ACCESS	read-only
			STATUS	current
	DESCRIPTION ""
			::= { mbusDE 25 }

mbusDEVIF0A		OBJECT-TYPE
			SYNTAX	INTEGER
			ACCESS	read-only
			STATUS	current
	DESCRIPTION ""
			::= { mbusDE 26 }

mbusDEValue0A		OBJECT-TYPE
			SYNTAX	INTEGER
			ACCESS	read-only
			STATUS	current
	DESCRIPTION ""
			::= { mbusDE 27 }

mbusDEVIF0B		OBJECT-TYPE
			SYNTAX	INTEGER
			ACCESS	read-only
			STATUS	current
	DESCRIPTION ""
			::= { mbusDE 28 }

mbusDEValue0B		OBJECT-TYPE
			SYNTAX	INTEGER
			ACCESS	read-only
			STATUS	current
	DESCRIPTION ""
			::= { mbusDE 29 }

mbusDEVIF0C		OBJECT-TYPE
			SYNTAX	INTEGER
			ACCESS	read-only
			STATUS	current
	DESCRIPTION ""
			::= { mbusDE 30 }

mbusDEValue0C		OBJECT-TYPE
			SYNTAX	INTEGER
			ACCESS	read-only
			STATUS	current
	DESCRIPTION ""
			::= { mbusDE 31 }

mbusDEVIF0D		OBJECT-TYPE
			SYNTAX	INTEGER
			ACCESS	read-only
			STATUS	current
	DESCRIPTION ""
			::= { mbusDE 32 }

mbusDEValue0D		OBJECT-TYPE
			SYNTAX	INTEGER
			ACCESS	read-only
			STATUS	current
	DESCRIPTION ""
			::= { mbusDE 33 }

mbusDEVIF0E		OBJECT-TYPE
			SYNTAX	INTEGER
			ACCESS	read-only
			STATUS	current
	DESCRIPTION ""
			::= { mbusDE 34 }

mbusDEValue0E		OBJECT-TYPE
			SYNTAX	INTEGER
			ACCESS	read-only
			STATUS	current
	DESCRIPTION ""
			::= { mbusDE 35 }

mbusDEVIF0F		OBJECT-TYPE
			SYNTAX	INTEGER
			ACCESS	read-only
			STATUS	current
	DESCRIPTION ""
			::= { mbusDE 36 }

mbusDEValue0F		OBJECT-TYPE
			SYNTAX	INTEGER
			ACCESS	read-only
			STATUS	current
	DESCRIPTION ""
			::= { mbusDE 37 }

mbusDEVIF10		OBJECT-TYPE
			SYNTAX	INTEGER
			ACCESS	read-only
			STATUS	current
	DESCRIPTION ""
			::= { mbusDE 38 }

mbusDEValue10		OBJECT-TYPE
			SYNTAX	INTEGER
			ACCESS	read-only
			STATUS	current
	DESCRIPTION ""
			::= { mbusDE 39 }

mbusDEVIF11		OBJECT-TYPE
			SYNTAX	INTEGER
			ACCESS	read-only
			STATUS	current
	DESCRIPTION ""
			::= { mbusDE 40 }

mbusDEValue11		OBJECT-TYPE
			SYNTAX	INTEGER
			ACCESS	read-only
			STATUS	current
	DESCRIPTION ""
			::= { mbusDE 41 }

mbusDEVIF12		OBJECT-TYPE
			SYNTAX	INTEGER
			ACCESS	read-only
			STATUS	current
	DESCRIPTION ""
			::= { mbusDE 42 }

mbusDEValue12		OBJECT-TYPE
			SYNTAX	INTEGER
			ACCESS	read-only
			STATUS	current
	DESCRIPTION ""
			::= { mbusDE 43 }

mbusDEVIF13		OBJECT-TYPE
			SYNTAX	INTEGER
			ACCESS	read-only
			STATUS	current
	DESCRIPTION ""
			::= { mbusDE 44 }

mbusDEValue13		OBJECT-TYPE
			SYNTAX	INTEGER
			ACCESS	read-only
			STATUS	current
	DESCRIPTION ""
			::= { mbusDE 45 }

mbusDEVIF14		OBJECT-TYPE
			SYNTAX	INTEGER
			ACCESS	read-only
			STATUS	current
	DESCRIPTION ""
			::= { mbusDE 46 }

mbusDEValue14		OBJECT-TYPE
			SYNTAX	INTEGER
			ACCESS	read-only
			STATUS	current
	DESCRIPTION ""
			::= { mbusDE 47 }

mbusDEVIF15		OBJECT-TYPE
			SYNTAX	INTEGER
			ACCESS	read-only
			STATUS	current
	DESCRIPTION ""
			::= { mbusDE 48 }

mbusDEValue15		OBJECT-TYPE
			SYNTAX	INTEGER
			ACCESS	read-only
			STATUS	current
	DESCRIPTION ""
			::= { mbusDE 49 }

mbusDEVIF16		OBJECT-TYPE
			SYNTAX	INTEGER
			ACCESS	read-only
			STATUS	current
	DESCRIPTION ""
			::= { mbusDE 50 }

mbusDEValue16		OBJECT-TYPE
			SYNTAX	INTEGER
			ACCESS	read-only
			STATUS	current
	DESCRIPTION ""
			::= { mbusDE 51 }

mbusDEVIF17		OBJECT-TYPE
			SYNTAX	INTEGER
			ACCESS	read-only
			STATUS	current
	DESCRIPTION ""
			::= { mbusDE 52 }

mbusDEValue17		OBJECT-TYPE
			SYNTAX	INTEGER
			ACCESS	read-only
			STATUS	current
	DESCRIPTION ""
			::= { mbusDE 53 }

mbusDEVIF18		OBJECT-TYPE
			SYNTAX	INTEGER
			ACCESS	read-only
			STATUS	current
	DESCRIPTION ""
			::= { mbusDE 54 }

mbusDEValue18		OBJECT-TYPE
			SYNTAX	INTEGER
			ACCESS	read-only
			STATUS	current
	DESCRIPTION ""
			::= { mbusDE 55 }

mbusDEVIF19		OBJECT-TYPE
			SYNTAX	INTEGER
			ACCESS	read-only
			STATUS	current
	DESCRIPTION ""
			::= { mbusDE 56 }

mbusDEValue19		OBJECT-TYPE
			SYNTAX	INTEGER
			ACCESS	read-only
			STATUS	current
	DESCRIPTION ""
			::= { mbusDE 57 }

mbusDEVIF1A		OBJECT-TYPE
			SYNTAX	INTEGER
			ACCESS	read-only
			STATUS	current
	DESCRIPTION ""
			::= { mbusDE 58 }

mbusDEValue1A		OBJECT-TYPE
			SYNTAX	INTEGER
			ACCESS	read-only
			STATUS	current
	DESCRIPTION ""
			::= { mbusDE 59 }

mbusDEVIF1B		OBJECT-TYPE
			SYNTAX	INTEGER
			ACCESS	read-only
			STATUS	current
	DESCRIPTION ""
			::= { mbusDE 60 }

mbusDEValue1B		OBJECT-TYPE
			SYNTAX	INTEGER
			ACCESS	read-only
			STATUS	current
	DESCRIPTION ""
			::= { mbusDE 61 }

mbusDEVIF1C		OBJECT-TYPE
			SYNTAX	INTEGER
			ACCESS	read-only
			STATUS	current
	DESCRIPTION ""
			::= { mbusDE 62 }

mbusDEValue1C		OBJECT-TYPE
			SYNTAX	INTEGER
			ACCESS	read-only
			STATUS	current
	DESCRIPTION ""
			::= { mbusDE 63 }

mbusDEVIF1D		OBJECT-TYPE
			SYNTAX	INTEGER
			ACCESS	read-only
			STATUS	current
	DESCRIPTION ""
			::= { mbusDE 64 }

mbusDEValue1D		OBJECT-TYPE
			SYNTAX	INTEGER
			ACCESS	read-only
			STATUS	current
	DESCRIPTION ""
			::= { mbusDE 65 }

mbusDEVIF1E		OBJECT-TYPE
			SYNTAX	INTEGER
			ACCESS	read-only
			STATUS	current
	DESCRIPTION ""
			::= { mbusDE 66 }

mbusDEValue1E		OBJECT-TYPE
			SYNTAX	INTEGER
			ACCESS	read-only
			STATUS	current
	DESCRIPTION ""
			::= { mbusDE 67 }

mbusDEVIF1F		OBJECT-TYPE
			SYNTAX	INTEGER
			ACCESS	read-only
			STATUS	current
	DESCRIPTION ""
			::= { mbusDE 68 }

mbusDEValue1F		OBJECT-TYPE
			SYNTAX	INTEGER
			ACCESS	read-only
			STATUS	current
	DESCRIPTION ""
			::= { mbusDE 69 }

mbusDEVIF20		OBJECT-TYPE
			SYNTAX	INTEGER
			ACCESS	read-only
			STATUS	current
	DESCRIPTION ""
			::= { mbusDE 70 }

mbusDEValue20		OBJECT-TYPE
			SYNTAX	INTEGER
			ACCESS	read-only
			STATUS	current
	DESCRIPTION ""
			::= { mbusDE 71 }

mbusDEVIF21		OBJECT-TYPE
			SYNTAX	INTEGER
			ACCESS	read-only
			STATUS	current
	DESCRIPTION ""
			::= { mbusDE 72 }

mbusDEValue21		OBJECT-TYPE
			SYNTAX	INTEGER
			ACCESS	read-only
			STATUS	current
	DESCRIPTION ""
			::= { mbusDE 73 }

mbusDEVIF22		OBJECT-TYPE
			SYNTAX	INTEGER
			ACCESS	read-only
			STATUS	current
	DESCRIPTION ""
			::= { mbusDE 74 }

mbusDEValue22		OBJECT-TYPE
			SYNTAX	INTEGER
			ACCESS	read-only
			STATUS	current
	DESCRIPTION ""
			::= { mbusDE 75 }

mbusDEVIF23		OBJECT-TYPE
			SYNTAX	INTEGER
			ACCESS	read-only
			STATUS	current
	DESCRIPTION ""
			::= { mbusDE 76 }

mbusDEValue23		OBJECT-TYPE
			SYNTAX	INTEGER
			ACCESS	read-only
			STATUS	current
	DESCRIPTION ""
			::= { mbusDE 77 }

mbusDEVIF24		OBJECT-TYPE
			SYNTAX	INTEGER
			ACCESS	read-only
			STATUS	current
	DESCRIPTION ""
			::= { mbusDE 78 }

mbusDEValue24		OBJECT-TYPE
			SYNTAX	INTEGER
			ACCESS	read-only
			STATUS	current
	DESCRIPTION ""
			::= { mbusDE 79 }

mbusDEVIF25		OBJECT-TYPE
			SYNTAX	INTEGER
			ACCESS	read-only
			STATUS	current
	DESCRIPTION ""
			::= { mbusDE 80 }

mbusDEValue25		OBJECT-TYPE
			SYNTAX	INTEGER
			ACCESS	read-only
			STATUS	current
	DESCRIPTION ""
			::= { mbusDE 81 }

mbusDEVIF26		OBJECT-TYPE
			SYNTAX	INTEGER
			ACCESS	read-only
			STATUS	current
	DESCRIPTION ""
			::= { mbusDE 82 }

mbusDEValue26		OBJECT-TYPE
			SYNTAX	INTEGER
			ACCESS	read-only
			STATUS	current
	DESCRIPTION ""
			::= { mbusDE 83 }

mbusDEVIF27		OBJECT-TYPE
			SYNTAX	INTEGER
			ACCESS	read-only
			STATUS	current
	DESCRIPTION ""
			::= { mbusDE 84 }

mbusDEValue27		OBJECT-TYPE
			SYNTAX	INTEGER
			ACCESS	read-only
			STATUS	current
	DESCRIPTION ""
			::= { mbusDE 85 }

mbusDEVIF28		OBJECT-TYPE
			SYNTAX	INTEGER
			ACCESS	read-only
			STATUS	current
	DESCRIPTION ""
			::= { mbusDE 86 }

mbusDEValue28		OBJECT-TYPE
			SYNTAX	INTEGER
			ACCESS	read-only
			STATUS	current
	DESCRIPTION ""
			::= { mbusDE 87 }

mbusDEVIF29		OBJECT-TYPE
			SYNTAX	INTEGER
			ACCESS	read-only
			STATUS	current
	DESCRIPTION ""
			::= { mbusDE 88 }

mbusDEValue29		OBJECT-TYPE
			SYNTAX	INTEGER
			ACCESS	read-only
			STATUS	current
	DESCRIPTION ""
			::= { mbusDE 89 }

mbusDEVIF2A		OBJECT-TYPE
			SYNTAX	INTEGER
			ACCESS	read-only
			STATUS	current
	DESCRIPTION ""
			::= { mbusDE 90 }

mbusDEValue2A		OBJECT-TYPE
			SYNTAX	INTEGER
			ACCESS	read-only
			STATUS	current
	DESCRIPTION ""
			::= { mbusDE 91 }

mbusDEVIF2B		OBJECT-TYPE
			SYNTAX	INTEGER
			ACCESS	read-only
			STATUS	current
	DESCRIPTION ""
			::= { mbusDE 92 }

mbusDEValue2B		OBJECT-TYPE
			SYNTAX	INTEGER
			ACCESS	read-only
			STATUS	current
	DESCRIPTION ""
			::= { mbusDE 93 }

mbusDEVIF2C		OBJECT-TYPE
			SYNTAX	INTEGER
			ACCESS	read-only
			STATUS	current
	DESCRIPTION ""
			::= { mbusDE 94 }

mbusDEValue2C		OBJECT-TYPE
			SYNTAX	INTEGER
			ACCESS	read-only
			STATUS	current
	DESCRIPTION ""
			::= { mbusDE 95 }

mbusDEVIF2D		OBJECT-TYPE
			SYNTAX	INTEGER
			ACCESS	read-only
			STATUS	current
	DESCRIPTION ""
			::= { mbusDE 96 }

mbusDEValue2D		OBJECT-TYPE
			SYNTAX	INTEGER
			ACCESS	read-only
			STATUS	current
	DESCRIPTION ""
			::= { mbusDE 97 }

mbusDEVIF2E		OBJECT-TYPE
			SYNTAX	INTEGER
			ACCESS	read-only
			STATUS	current
	DESCRIPTION ""
			::= { mbusDE 98 }

mbusDEValue2E		OBJECT-TYPE
			SYNTAX	INTEGER
			ACCESS	read-only
			STATUS	current
	DESCRIPTION ""
			::= { mbusDE 99 }

mbusDEVIF2F		OBJECT-TYPE
			SYNTAX	INTEGER
			ACCESS	read-only
			STATUS	current
	DESCRIPTION ""
			::= { mbusDE 100 }

mbusDEValue2F		OBJECT-TYPE
			SYNTAX	INTEGER
			ACCESS	read-only
			STATUS	current
	DESCRIPTION ""
			::= { mbusDE 101 }

mbusDF			OBJECT IDENTIFIER ::= { mbus 223 }

mbusDFIdNumber		OBJECT-TYPE
			SYNTAX	Gauge
			ACCESS	read-only
			STATUS	current
	DESCRIPTION ""
			::= { mbusDF 1 }

mbusDFManufacturer	OBJECT-TYPE
			SYNTAX	Gauge
			ACCESS	read-only
			STATUS	current
	DESCRIPTION ""
			::= { mbusDF 2 }

mbusDFVersion		OBJECT-TYPE
			SYNTAX	Gauge
			ACCESS	read-only
			STATUS	current
	DESCRIPTION ""
			::= { mbusDF 3 }

mbusDFMedium		OBJECT-TYPE
			SYNTAX	Gauge
			ACCESS	read-only
			STATUS	current
	DESCRIPTION ""
			::= { mbusDF 4 }

mbusDFStatus		OBJECT-TYPE
			SYNTAX	Gauge
			ACCESS	read-only
			STATUS	current
	DESCRIPTION ""
			::= { mbusDF 5 }

mbusDFVIF00		OBJECT-TYPE
			SYNTAX	INTEGER
			ACCESS	read-only
			STATUS	current
	DESCRIPTION ""
			::= { mbusDF 6 }

mbusDFValue00		OBJECT-TYPE
			SYNTAX	INTEGER
			ACCESS	read-only
			STATUS	current
	DESCRIPTION ""
			::= { mbusDF 7 }

mbusDFVIF01		OBJECT-TYPE
			SYNTAX	INTEGER
			ACCESS	read-only
			STATUS	current
	DESCRIPTION ""
			::= { mbusDF 8 }

mbusDFValue01		OBJECT-TYPE
			SYNTAX	INTEGER
			ACCESS	read-only
			STATUS	current
	DESCRIPTION ""
			::= { mbusDF 9 }

mbusDFVIF02		OBJECT-TYPE
			SYNTAX	INTEGER
			ACCESS	read-only
			STATUS	current
	DESCRIPTION ""
			::= { mbusDF 10 }

mbusDFValue02		OBJECT-TYPE
			SYNTAX	INTEGER
			ACCESS	read-only
			STATUS	current
	DESCRIPTION ""
			::= { mbusDF 11 }

mbusDFVIF03		OBJECT-TYPE
			SYNTAX	INTEGER
			ACCESS	read-only
			STATUS	current
	DESCRIPTION ""
			::= { mbusDF 12 }

mbusDFValue03		OBJECT-TYPE
			SYNTAX	INTEGER
			ACCESS	read-only
			STATUS	current
	DESCRIPTION ""
			::= { mbusDF 13 }

mbusDFVIF04		OBJECT-TYPE
			SYNTAX	INTEGER
			ACCESS	read-only
			STATUS	current
	DESCRIPTION ""
			::= { mbusDF 14 }

mbusDFValue04		OBJECT-TYPE
			SYNTAX	INTEGER
			ACCESS	read-only
			STATUS	current
	DESCRIPTION ""
			::= { mbusDF 15 }

mbusDFVIF05		OBJECT-TYPE
			SYNTAX	INTEGER
			ACCESS	read-only
			STATUS	current
	DESCRIPTION ""
			::= { mbusDF 16 }

mbusDFValue05		OBJECT-TYPE
			SYNTAX	INTEGER
			ACCESS	read-only
			STATUS	current
	DESCRIPTION ""
			::= { mbusDF 17 }

mbusDFVIF06		OBJECT-TYPE
			SYNTAX	INTEGER
			ACCESS	read-only
			STATUS	current
	DESCRIPTION ""
			::= { mbusDF 18 }

mbusDFValue06		OBJECT-TYPE
			SYNTAX	INTEGER
			ACCESS	read-only
			STATUS	current
	DESCRIPTION ""
			::= { mbusDF 19 }

mbusDFVIF07		OBJECT-TYPE
			SYNTAX	INTEGER
			ACCESS	read-only
			STATUS	current
	DESCRIPTION ""
			::= { mbusDF 20 }

mbusDFValue07		OBJECT-TYPE
			SYNTAX	INTEGER
			ACCESS	read-only
			STATUS	current
	DESCRIPTION ""
			::= { mbusDF 21 }

mbusDFVIF08		OBJECT-TYPE
			SYNTAX	INTEGER
			ACCESS	read-only
			STATUS	current
	DESCRIPTION ""
			::= { mbusDF 22 }

mbusDFValue08		OBJECT-TYPE
			SYNTAX	INTEGER
			ACCESS	read-only
			STATUS	current
	DESCRIPTION ""
			::= { mbusDF 23 }

mbusDFVIF09		OBJECT-TYPE
			SYNTAX	INTEGER
			ACCESS	read-only
			STATUS	current
	DESCRIPTION ""
			::= { mbusDF 24 }

mbusDFValue09		OBJECT-TYPE
			SYNTAX	INTEGER
			ACCESS	read-only
			STATUS	current
	DESCRIPTION ""
			::= { mbusDF 25 }

mbusDFVIF0A		OBJECT-TYPE
			SYNTAX	INTEGER
			ACCESS	read-only
			STATUS	current
	DESCRIPTION ""
			::= { mbusDF 26 }

mbusDFValue0A		OBJECT-TYPE
			SYNTAX	INTEGER
			ACCESS	read-only
			STATUS	current
	DESCRIPTION ""
			::= { mbusDF 27 }

mbusDFVIF0B		OBJECT-TYPE
			SYNTAX	INTEGER
			ACCESS	read-only
			STATUS	current
	DESCRIPTION ""
			::= { mbusDF 28 }

mbusDFValue0B		OBJECT-TYPE
			SYNTAX	INTEGER
			ACCESS	read-only
			STATUS	current
	DESCRIPTION ""
			::= { mbusDF 29 }

mbusDFVIF0C		OBJECT-TYPE
			SYNTAX	INTEGER
			ACCESS	read-only
			STATUS	current
	DESCRIPTION ""
			::= { mbusDF 30 }

mbusDFValue0C		OBJECT-TYPE
			SYNTAX	INTEGER
			ACCESS	read-only
			STATUS	current
	DESCRIPTION ""
			::= { mbusDF 31 }

mbusDFVIF0D		OBJECT-TYPE
			SYNTAX	INTEGER
			ACCESS	read-only
			STATUS	current
	DESCRIPTION ""
			::= { mbusDF 32 }

mbusDFValue0D		OBJECT-TYPE
			SYNTAX	INTEGER
			ACCESS	read-only
			STATUS	current
	DESCRIPTION ""
			::= { mbusDF 33 }

mbusDFVIF0E		OBJECT-TYPE
			SYNTAX	INTEGER
			ACCESS	read-only
			STATUS	current
	DESCRIPTION ""
			::= { mbusDF 34 }

mbusDFValue0E		OBJECT-TYPE
			SYNTAX	INTEGER
			ACCESS	read-only
			STATUS	current
	DESCRIPTION ""
			::= { mbusDF 35 }

mbusDFVIF0F		OBJECT-TYPE
			SYNTAX	INTEGER
			ACCESS	read-only
			STATUS	current
	DESCRIPTION ""
			::= { mbusDF 36 }

mbusDFValue0F		OBJECT-TYPE
			SYNTAX	INTEGER
			ACCESS	read-only
			STATUS	current
	DESCRIPTION ""
			::= { mbusDF 37 }

mbusDFVIF10		OBJECT-TYPE
			SYNTAX	INTEGER
			ACCESS	read-only
			STATUS	current
	DESCRIPTION ""
			::= { mbusDF 38 }

mbusDFValue10		OBJECT-TYPE
			SYNTAX	INTEGER
			ACCESS	read-only
			STATUS	current
	DESCRIPTION ""
			::= { mbusDF 39 }

mbusDFVIF11		OBJECT-TYPE
			SYNTAX	INTEGER
			ACCESS	read-only
			STATUS	current
	DESCRIPTION ""
			::= { mbusDF 40 }

mbusDFValue11		OBJECT-TYPE
			SYNTAX	INTEGER
			ACCESS	read-only
			STATUS	current
	DESCRIPTION ""
			::= { mbusDF 41 }

mbusDFVIF12		OBJECT-TYPE
			SYNTAX	INTEGER
			ACCESS	read-only
			STATUS	current
	DESCRIPTION ""
			::= { mbusDF 42 }

mbusDFValue12		OBJECT-TYPE
			SYNTAX	INTEGER
			ACCESS	read-only
			STATUS	current
	DESCRIPTION ""
			::= { mbusDF 43 }

mbusDFVIF13		OBJECT-TYPE
			SYNTAX	INTEGER
			ACCESS	read-only
			STATUS	current
	DESCRIPTION ""
			::= { mbusDF 44 }

mbusDFValue13		OBJECT-TYPE
			SYNTAX	INTEGER
			ACCESS	read-only
			STATUS	current
	DESCRIPTION ""
			::= { mbusDF 45 }

mbusDFVIF14		OBJECT-TYPE
			SYNTAX	INTEGER
			ACCESS	read-only
			STATUS	current
	DESCRIPTION ""
			::= { mbusDF 46 }

mbusDFValue14		OBJECT-TYPE
			SYNTAX	INTEGER
			ACCESS	read-only
			STATUS	current
	DESCRIPTION ""
			::= { mbusDF 47 }

mbusDFVIF15		OBJECT-TYPE
			SYNTAX	INTEGER
			ACCESS	read-only
			STATUS	current
	DESCRIPTION ""
			::= { mbusDF 48 }

mbusDFValue15		OBJECT-TYPE
			SYNTAX	INTEGER
			ACCESS	read-only
			STATUS	current
	DESCRIPTION ""
			::= { mbusDF 49 }

mbusDFVIF16		OBJECT-TYPE
			SYNTAX	INTEGER
			ACCESS	read-only
			STATUS	current
	DESCRIPTION ""
			::= { mbusDF 50 }

mbusDFValue16		OBJECT-TYPE
			SYNTAX	INTEGER
			ACCESS	read-only
			STATUS	current
	DESCRIPTION ""
			::= { mbusDF 51 }

mbusDFVIF17		OBJECT-TYPE
			SYNTAX	INTEGER
			ACCESS	read-only
			STATUS	current
	DESCRIPTION ""
			::= { mbusDF 52 }

mbusDFValue17		OBJECT-TYPE
			SYNTAX	INTEGER
			ACCESS	read-only
			STATUS	current
	DESCRIPTION ""
			::= { mbusDF 53 }

mbusDFVIF18		OBJECT-TYPE
			SYNTAX	INTEGER
			ACCESS	read-only
			STATUS	current
	DESCRIPTION ""
			::= { mbusDF 54 }

mbusDFValue18		OBJECT-TYPE
			SYNTAX	INTEGER
			ACCESS	read-only
			STATUS	current
	DESCRIPTION ""
			::= { mbusDF 55 }

mbusDFVIF19		OBJECT-TYPE
			SYNTAX	INTEGER
			ACCESS	read-only
			STATUS	current
	DESCRIPTION ""
			::= { mbusDF 56 }

mbusDFValue19		OBJECT-TYPE
			SYNTAX	INTEGER
			ACCESS	read-only
			STATUS	current
	DESCRIPTION ""
			::= { mbusDF 57 }

mbusDFVIF1A		OBJECT-TYPE
			SYNTAX	INTEGER
			ACCESS	read-only
			STATUS	current
	DESCRIPTION ""
			::= { mbusDF 58 }

mbusDFValue1A		OBJECT-TYPE
			SYNTAX	INTEGER
			ACCESS	read-only
			STATUS	current
	DESCRIPTION ""
			::= { mbusDF 59 }

mbusDFVIF1B		OBJECT-TYPE
			SYNTAX	INTEGER
			ACCESS	read-only
			STATUS	current
	DESCRIPTION ""
			::= { mbusDF 60 }

mbusDFValue1B		OBJECT-TYPE
			SYNTAX	INTEGER
			ACCESS	read-only
			STATUS	current
	DESCRIPTION ""
			::= { mbusDF 61 }

mbusDFVIF1C		OBJECT-TYPE
			SYNTAX	INTEGER
			ACCESS	read-only
			STATUS	current
	DESCRIPTION ""
			::= { mbusDF 62 }

mbusDFValue1C		OBJECT-TYPE
			SYNTAX	INTEGER
			ACCESS	read-only
			STATUS	current
	DESCRIPTION ""
			::= { mbusDF 63 }

mbusDFVIF1D		OBJECT-TYPE
			SYNTAX	INTEGER
			ACCESS	read-only
			STATUS	current
	DESCRIPTION ""
			::= { mbusDF 64 }

mbusDFValue1D		OBJECT-TYPE
			SYNTAX	INTEGER
			ACCESS	read-only
			STATUS	current
	DESCRIPTION ""
			::= { mbusDF 65 }

mbusDFVIF1E		OBJECT-TYPE
			SYNTAX	INTEGER
			ACCESS	read-only
			STATUS	current
	DESCRIPTION ""
			::= { mbusDF 66 }

mbusDFValue1E		OBJECT-TYPE
			SYNTAX	INTEGER
			ACCESS	read-only
			STATUS	current
	DESCRIPTION ""
			::= { mbusDF 67 }

mbusDFVIF1F		OBJECT-TYPE
			SYNTAX	INTEGER
			ACCESS	read-only
			STATUS	current
	DESCRIPTION ""
			::= { mbusDF 68 }

mbusDFValue1F		OBJECT-TYPE
			SYNTAX	INTEGER
			ACCESS	read-only
			STATUS	current
	DESCRIPTION ""
			::= { mbusDF 69 }

mbusDFVIF20		OBJECT-TYPE
			SYNTAX	INTEGER
			ACCESS	read-only
			STATUS	current
	DESCRIPTION ""
			::= { mbusDF 70 }

mbusDFValue20		OBJECT-TYPE
			SYNTAX	INTEGER
			ACCESS	read-only
			STATUS	current
	DESCRIPTION ""
			::= { mbusDF 71 }

mbusDFVIF21		OBJECT-TYPE
			SYNTAX	INTEGER
			ACCESS	read-only
			STATUS	current
	DESCRIPTION ""
			::= { mbusDF 72 }

mbusDFValue21		OBJECT-TYPE
			SYNTAX	INTEGER
			ACCESS	read-only
			STATUS	current
	DESCRIPTION ""
			::= { mbusDF 73 }

mbusDFVIF22		OBJECT-TYPE
			SYNTAX	INTEGER
			ACCESS	read-only
			STATUS	current
	DESCRIPTION ""
			::= { mbusDF 74 }

mbusDFValue22		OBJECT-TYPE
			SYNTAX	INTEGER
			ACCESS	read-only
			STATUS	current
	DESCRIPTION ""
			::= { mbusDF 75 }

mbusDFVIF23		OBJECT-TYPE
			SYNTAX	INTEGER
			ACCESS	read-only
			STATUS	current
	DESCRIPTION ""
			::= { mbusDF 76 }

mbusDFValue23		OBJECT-TYPE
			SYNTAX	INTEGER
			ACCESS	read-only
			STATUS	current
	DESCRIPTION ""
			::= { mbusDF 77 }

mbusDFVIF24		OBJECT-TYPE
			SYNTAX	INTEGER
			ACCESS	read-only
			STATUS	current
	DESCRIPTION ""
			::= { mbusDF 78 }

mbusDFValue24		OBJECT-TYPE
			SYNTAX	INTEGER
			ACCESS	read-only
			STATUS	current
	DESCRIPTION ""
			::= { mbusDF 79 }

mbusDFVIF25		OBJECT-TYPE
			SYNTAX	INTEGER
			ACCESS	read-only
			STATUS	current
	DESCRIPTION ""
			::= { mbusDF 80 }

mbusDFValue25		OBJECT-TYPE
			SYNTAX	INTEGER
			ACCESS	read-only
			STATUS	current
	DESCRIPTION ""
			::= { mbusDF 81 }

mbusDFVIF26		OBJECT-TYPE
			SYNTAX	INTEGER
			ACCESS	read-only
			STATUS	current
	DESCRIPTION ""
			::= { mbusDF 82 }

mbusDFValue26		OBJECT-TYPE
			SYNTAX	INTEGER
			ACCESS	read-only
			STATUS	current
	DESCRIPTION ""
			::= { mbusDF 83 }

mbusDFVIF27		OBJECT-TYPE
			SYNTAX	INTEGER
			ACCESS	read-only
			STATUS	current
	DESCRIPTION ""
			::= { mbusDF 84 }

mbusDFValue27		OBJECT-TYPE
			SYNTAX	INTEGER
			ACCESS	read-only
			STATUS	current
	DESCRIPTION ""
			::= { mbusDF 85 }

mbusDFVIF28		OBJECT-TYPE
			SYNTAX	INTEGER
			ACCESS	read-only
			STATUS	current
	DESCRIPTION ""
			::= { mbusDF 86 }

mbusDFValue28		OBJECT-TYPE
			SYNTAX	INTEGER
			ACCESS	read-only
			STATUS	current
	DESCRIPTION ""
			::= { mbusDF 87 }

mbusDFVIF29		OBJECT-TYPE
			SYNTAX	INTEGER
			ACCESS	read-only
			STATUS	current
	DESCRIPTION ""
			::= { mbusDF 88 }

mbusDFValue29		OBJECT-TYPE
			SYNTAX	INTEGER
			ACCESS	read-only
			STATUS	current
	DESCRIPTION ""
			::= { mbusDF 89 }

mbusDFVIF2A		OBJECT-TYPE
			SYNTAX	INTEGER
			ACCESS	read-only
			STATUS	current
	DESCRIPTION ""
			::= { mbusDF 90 }

mbusDFValue2A		OBJECT-TYPE
			SYNTAX	INTEGER
			ACCESS	read-only
			STATUS	current
	DESCRIPTION ""
			::= { mbusDF 91 }

mbusDFVIF2B		OBJECT-TYPE
			SYNTAX	INTEGER
			ACCESS	read-only
			STATUS	current
	DESCRIPTION ""
			::= { mbusDF 92 }

mbusDFValue2B		OBJECT-TYPE
			SYNTAX	INTEGER
			ACCESS	read-only
			STATUS	current
	DESCRIPTION ""
			::= { mbusDF 93 }

mbusDFVIF2C		OBJECT-TYPE
			SYNTAX	INTEGER
			ACCESS	read-only
			STATUS	current
	DESCRIPTION ""
			::= { mbusDF 94 }

mbusDFValue2C		OBJECT-TYPE
			SYNTAX	INTEGER
			ACCESS	read-only
			STATUS	current
	DESCRIPTION ""
			::= { mbusDF 95 }

mbusDFVIF2D		OBJECT-TYPE
			SYNTAX	INTEGER
			ACCESS	read-only
			STATUS	current
	DESCRIPTION ""
			::= { mbusDF 96 }

mbusDFValue2D		OBJECT-TYPE
			SYNTAX	INTEGER
			ACCESS	read-only
			STATUS	current
	DESCRIPTION ""
			::= { mbusDF 97 }

mbusDFVIF2E		OBJECT-TYPE
			SYNTAX	INTEGER
			ACCESS	read-only
			STATUS	current
	DESCRIPTION ""
			::= { mbusDF 98 }

mbusDFValue2E		OBJECT-TYPE
			SYNTAX	INTEGER
			ACCESS	read-only
			STATUS	current
	DESCRIPTION ""
			::= { mbusDF 99 }

mbusDFVIF2F		OBJECT-TYPE
			SYNTAX	INTEGER
			ACCESS	read-only
			STATUS	current
	DESCRIPTION ""
			::= { mbusDF 100 }

mbusDFValue2F		OBJECT-TYPE
			SYNTAX	INTEGER
			ACCESS	read-only
			STATUS	current
	DESCRIPTION ""
			::= { mbusDF 101 }

mbusE0			OBJECT IDENTIFIER ::= { mbus 224 }

mbusE0IdNumber		OBJECT-TYPE
			SYNTAX	Gauge
			ACCESS	read-only
			STATUS	current
	DESCRIPTION ""
			::= { mbusE0 1 }

mbusE0Manufacturer	OBJECT-TYPE
			SYNTAX	Gauge
			ACCESS	read-only
			STATUS	current
	DESCRIPTION ""
			::= { mbusE0 2 }

mbusE0Version		OBJECT-TYPE
			SYNTAX	Gauge
			ACCESS	read-only
			STATUS	current
	DESCRIPTION ""
			::= { mbusE0 3 }

mbusE0Medium		OBJECT-TYPE
			SYNTAX	Gauge
			ACCESS	read-only
			STATUS	current
	DESCRIPTION ""
			::= { mbusE0 4 }

mbusE0Status		OBJECT-TYPE
			SYNTAX	Gauge
			ACCESS	read-only
			STATUS	current
	DESCRIPTION ""
			::= { mbusE0 5 }

mbusE0VIF00		OBJECT-TYPE
			SYNTAX	INTEGER
			ACCESS	read-only
			STATUS	current
	DESCRIPTION ""
			::= { mbusE0 6 }

mbusE0Value00		OBJECT-TYPE
			SYNTAX	INTEGER
			ACCESS	read-only
			STATUS	current
	DESCRIPTION ""
			::= { mbusE0 7 }

mbusE0VIF01		OBJECT-TYPE
			SYNTAX	INTEGER
			ACCESS	read-only
			STATUS	current
	DESCRIPTION ""
			::= { mbusE0 8 }

mbusE0Value01		OBJECT-TYPE
			SYNTAX	INTEGER
			ACCESS	read-only
			STATUS	current
	DESCRIPTION ""
			::= { mbusE0 9 }

mbusE0VIF02		OBJECT-TYPE
			SYNTAX	INTEGER
			ACCESS	read-only
			STATUS	current
	DESCRIPTION ""
			::= { mbusE0 10 }

mbusE0Value02		OBJECT-TYPE
			SYNTAX	INTEGER
			ACCESS	read-only
			STATUS	current
	DESCRIPTION ""
			::= { mbusE0 11 }

mbusE0VIF03		OBJECT-TYPE
			SYNTAX	INTEGER
			ACCESS	read-only
			STATUS	current
	DESCRIPTION ""
			::= { mbusE0 12 }

mbusE0Value03		OBJECT-TYPE
			SYNTAX	INTEGER
			ACCESS	read-only
			STATUS	current
	DESCRIPTION ""
			::= { mbusE0 13 }

mbusE0VIF04		OBJECT-TYPE
			SYNTAX	INTEGER
			ACCESS	read-only
			STATUS	current
	DESCRIPTION ""
			::= { mbusE0 14 }

mbusE0Value04		OBJECT-TYPE
			SYNTAX	INTEGER
			ACCESS	read-only
			STATUS	current
	DESCRIPTION ""
			::= { mbusE0 15 }

mbusE0VIF05		OBJECT-TYPE
			SYNTAX	INTEGER
			ACCESS	read-only
			STATUS	current
	DESCRIPTION ""
			::= { mbusE0 16 }

mbusE0Value05		OBJECT-TYPE
			SYNTAX	INTEGER
			ACCESS	read-only
			STATUS	current
	DESCRIPTION ""
			::= { mbusE0 17 }

mbusE0VIF06		OBJECT-TYPE
			SYNTAX	INTEGER
			ACCESS	read-only
			STATUS	current
	DESCRIPTION ""
			::= { mbusE0 18 }

mbusE0Value06		OBJECT-TYPE
			SYNTAX	INTEGER
			ACCESS	read-only
			STATUS	current
	DESCRIPTION ""
			::= { mbusE0 19 }

mbusE0VIF07		OBJECT-TYPE
			SYNTAX	INTEGER
			ACCESS	read-only
			STATUS	current
	DESCRIPTION ""
			::= { mbusE0 20 }

mbusE0Value07		OBJECT-TYPE
			SYNTAX	INTEGER
			ACCESS	read-only
			STATUS	current
	DESCRIPTION ""
			::= { mbusE0 21 }

mbusE0VIF08		OBJECT-TYPE
			SYNTAX	INTEGER
			ACCESS	read-only
			STATUS	current
	DESCRIPTION ""
			::= { mbusE0 22 }

mbusE0Value08		OBJECT-TYPE
			SYNTAX	INTEGER
			ACCESS	read-only
			STATUS	current
	DESCRIPTION ""
			::= { mbusE0 23 }

mbusE0VIF09		OBJECT-TYPE
			SYNTAX	INTEGER
			ACCESS	read-only
			STATUS	current
	DESCRIPTION ""
			::= { mbusE0 24 }

mbusE0Value09		OBJECT-TYPE
			SYNTAX	INTEGER
			ACCESS	read-only
			STATUS	current
	DESCRIPTION ""
			::= { mbusE0 25 }

mbusE0VIF0A		OBJECT-TYPE
			SYNTAX	INTEGER
			ACCESS	read-only
			STATUS	current
	DESCRIPTION ""
			::= { mbusE0 26 }

mbusE0Value0A		OBJECT-TYPE
			SYNTAX	INTEGER
			ACCESS	read-only
			STATUS	current
	DESCRIPTION ""
			::= { mbusE0 27 }

mbusE0VIF0B		OBJECT-TYPE
			SYNTAX	INTEGER
			ACCESS	read-only
			STATUS	current
	DESCRIPTION ""
			::= { mbusE0 28 }

mbusE0Value0B		OBJECT-TYPE
			SYNTAX	INTEGER
			ACCESS	read-only
			STATUS	current
	DESCRIPTION ""
			::= { mbusE0 29 }

mbusE0VIF0C		OBJECT-TYPE
			SYNTAX	INTEGER
			ACCESS	read-only
			STATUS	current
	DESCRIPTION ""
			::= { mbusE0 30 }

mbusE0Value0C		OBJECT-TYPE
			SYNTAX	INTEGER
			ACCESS	read-only
			STATUS	current
	DESCRIPTION ""
			::= { mbusE0 31 }

mbusE0VIF0D		OBJECT-TYPE
			SYNTAX	INTEGER
			ACCESS	read-only
			STATUS	current
	DESCRIPTION ""
			::= { mbusE0 32 }

mbusE0Value0D		OBJECT-TYPE
			SYNTAX	INTEGER
			ACCESS	read-only
			STATUS	current
	DESCRIPTION ""
			::= { mbusE0 33 }

mbusE0VIF0E		OBJECT-TYPE
			SYNTAX	INTEGER
			ACCESS	read-only
			STATUS	current
	DESCRIPTION ""
			::= { mbusE0 34 }

mbusE0Value0E		OBJECT-TYPE
			SYNTAX	INTEGER
			ACCESS	read-only
			STATUS	current
	DESCRIPTION ""
			::= { mbusE0 35 }

mbusE0VIF0F		OBJECT-TYPE
			SYNTAX	INTEGER
			ACCESS	read-only
			STATUS	current
	DESCRIPTION ""
			::= { mbusE0 36 }

mbusE0Value0F		OBJECT-TYPE
			SYNTAX	INTEGER
			ACCESS	read-only
			STATUS	current
	DESCRIPTION ""
			::= { mbusE0 37 }

mbusE0VIF10		OBJECT-TYPE
			SYNTAX	INTEGER
			ACCESS	read-only
			STATUS	current
	DESCRIPTION ""
			::= { mbusE0 38 }

mbusE0Value10		OBJECT-TYPE
			SYNTAX	INTEGER
			ACCESS	read-only
			STATUS	current
	DESCRIPTION ""
			::= { mbusE0 39 }

mbusE0VIF11		OBJECT-TYPE
			SYNTAX	INTEGER
			ACCESS	read-only
			STATUS	current
	DESCRIPTION ""
			::= { mbusE0 40 }

mbusE0Value11		OBJECT-TYPE
			SYNTAX	INTEGER
			ACCESS	read-only
			STATUS	current
	DESCRIPTION ""
			::= { mbusE0 41 }

mbusE0VIF12		OBJECT-TYPE
			SYNTAX	INTEGER
			ACCESS	read-only
			STATUS	current
	DESCRIPTION ""
			::= { mbusE0 42 }

mbusE0Value12		OBJECT-TYPE
			SYNTAX	INTEGER
			ACCESS	read-only
			STATUS	current
	DESCRIPTION ""
			::= { mbusE0 43 }

mbusE0VIF13		OBJECT-TYPE
			SYNTAX	INTEGER
			ACCESS	read-only
			STATUS	current
	DESCRIPTION ""
			::= { mbusE0 44 }

mbusE0Value13		OBJECT-TYPE
			SYNTAX	INTEGER
			ACCESS	read-only
			STATUS	current
	DESCRIPTION ""
			::= { mbusE0 45 }

mbusE0VIF14		OBJECT-TYPE
			SYNTAX	INTEGER
			ACCESS	read-only
			STATUS	current
	DESCRIPTION ""
			::= { mbusE0 46 }

mbusE0Value14		OBJECT-TYPE
			SYNTAX	INTEGER
			ACCESS	read-only
			STATUS	current
	DESCRIPTION ""
			::= { mbusE0 47 }

mbusE0VIF15		OBJECT-TYPE
			SYNTAX	INTEGER
			ACCESS	read-only
			STATUS	current
	DESCRIPTION ""
			::= { mbusE0 48 }

mbusE0Value15		OBJECT-TYPE
			SYNTAX	INTEGER
			ACCESS	read-only
			STATUS	current
	DESCRIPTION ""
			::= { mbusE0 49 }

mbusE0VIF16		OBJECT-TYPE
			SYNTAX	INTEGER
			ACCESS	read-only
			STATUS	current
	DESCRIPTION ""
			::= { mbusE0 50 }

mbusE0Value16		OBJECT-TYPE
			SYNTAX	INTEGER
			ACCESS	read-only
			STATUS	current
	DESCRIPTION ""
			::= { mbusE0 51 }

mbusE0VIF17		OBJECT-TYPE
			SYNTAX	INTEGER
			ACCESS	read-only
			STATUS	current
	DESCRIPTION ""
			::= { mbusE0 52 }

mbusE0Value17		OBJECT-TYPE
			SYNTAX	INTEGER
			ACCESS	read-only
			STATUS	current
	DESCRIPTION ""
			::= { mbusE0 53 }

mbusE0VIF18		OBJECT-TYPE
			SYNTAX	INTEGER
			ACCESS	read-only
			STATUS	current
	DESCRIPTION ""
			::= { mbusE0 54 }

mbusE0Value18		OBJECT-TYPE
			SYNTAX	INTEGER
			ACCESS	read-only
			STATUS	current
	DESCRIPTION ""
			::= { mbusE0 55 }

mbusE0VIF19		OBJECT-TYPE
			SYNTAX	INTEGER
			ACCESS	read-only
			STATUS	current
	DESCRIPTION ""
			::= { mbusE0 56 }

mbusE0Value19		OBJECT-TYPE
			SYNTAX	INTEGER
			ACCESS	read-only
			STATUS	current
	DESCRIPTION ""
			::= { mbusE0 57 }

mbusE0VIF1A		OBJECT-TYPE
			SYNTAX	INTEGER
			ACCESS	read-only
			STATUS	current
	DESCRIPTION ""
			::= { mbusE0 58 }

mbusE0Value1A		OBJECT-TYPE
			SYNTAX	INTEGER
			ACCESS	read-only
			STATUS	current
	DESCRIPTION ""
			::= { mbusE0 59 }

mbusE0VIF1B		OBJECT-TYPE
			SYNTAX	INTEGER
			ACCESS	read-only
			STATUS	current
	DESCRIPTION ""
			::= { mbusE0 60 }

mbusE0Value1B		OBJECT-TYPE
			SYNTAX	INTEGER
			ACCESS	read-only
			STATUS	current
	DESCRIPTION ""
			::= { mbusE0 61 }

mbusE0VIF1C		OBJECT-TYPE
			SYNTAX	INTEGER
			ACCESS	read-only
			STATUS	current
	DESCRIPTION ""
			::= { mbusE0 62 }

mbusE0Value1C		OBJECT-TYPE
			SYNTAX	INTEGER
			ACCESS	read-only
			STATUS	current
	DESCRIPTION ""
			::= { mbusE0 63 }

mbusE0VIF1D		OBJECT-TYPE
			SYNTAX	INTEGER
			ACCESS	read-only
			STATUS	current
	DESCRIPTION ""
			::= { mbusE0 64 }

mbusE0Value1D		OBJECT-TYPE
			SYNTAX	INTEGER
			ACCESS	read-only
			STATUS	current
	DESCRIPTION ""
			::= { mbusE0 65 }

mbusE0VIF1E		OBJECT-TYPE
			SYNTAX	INTEGER
			ACCESS	read-only
			STATUS	current
	DESCRIPTION ""
			::= { mbusE0 66 }

mbusE0Value1E		OBJECT-TYPE
			SYNTAX	INTEGER
			ACCESS	read-only
			STATUS	current
	DESCRIPTION ""
			::= { mbusE0 67 }

mbusE0VIF1F		OBJECT-TYPE
			SYNTAX	INTEGER
			ACCESS	read-only
			STATUS	current
	DESCRIPTION ""
			::= { mbusE0 68 }

mbusE0Value1F		OBJECT-TYPE
			SYNTAX	INTEGER
			ACCESS	read-only
			STATUS	current
	DESCRIPTION ""
			::= { mbusE0 69 }

mbusE0VIF20		OBJECT-TYPE
			SYNTAX	INTEGER
			ACCESS	read-only
			STATUS	current
	DESCRIPTION ""
			::= { mbusE0 70 }

mbusE0Value20		OBJECT-TYPE
			SYNTAX	INTEGER
			ACCESS	read-only
			STATUS	current
	DESCRIPTION ""
			::= { mbusE0 71 }

mbusE0VIF21		OBJECT-TYPE
			SYNTAX	INTEGER
			ACCESS	read-only
			STATUS	current
	DESCRIPTION ""
			::= { mbusE0 72 }

mbusE0Value21		OBJECT-TYPE
			SYNTAX	INTEGER
			ACCESS	read-only
			STATUS	current
	DESCRIPTION ""
			::= { mbusE0 73 }

mbusE0VIF22		OBJECT-TYPE
			SYNTAX	INTEGER
			ACCESS	read-only
			STATUS	current
	DESCRIPTION ""
			::= { mbusE0 74 }

mbusE0Value22		OBJECT-TYPE
			SYNTAX	INTEGER
			ACCESS	read-only
			STATUS	current
	DESCRIPTION ""
			::= { mbusE0 75 }

mbusE0VIF23		OBJECT-TYPE
			SYNTAX	INTEGER
			ACCESS	read-only
			STATUS	current
	DESCRIPTION ""
			::= { mbusE0 76 }

mbusE0Value23		OBJECT-TYPE
			SYNTAX	INTEGER
			ACCESS	read-only
			STATUS	current
	DESCRIPTION ""
			::= { mbusE0 77 }

mbusE0VIF24		OBJECT-TYPE
			SYNTAX	INTEGER
			ACCESS	read-only
			STATUS	current
	DESCRIPTION ""
			::= { mbusE0 78 }

mbusE0Value24		OBJECT-TYPE
			SYNTAX	INTEGER
			ACCESS	read-only
			STATUS	current
	DESCRIPTION ""
			::= { mbusE0 79 }

mbusE0VIF25		OBJECT-TYPE
			SYNTAX	INTEGER
			ACCESS	read-only
			STATUS	current
	DESCRIPTION ""
			::= { mbusE0 80 }

mbusE0Value25		OBJECT-TYPE
			SYNTAX	INTEGER
			ACCESS	read-only
			STATUS	current
	DESCRIPTION ""
			::= { mbusE0 81 }

mbusE0VIF26		OBJECT-TYPE
			SYNTAX	INTEGER
			ACCESS	read-only
			STATUS	current
	DESCRIPTION ""
			::= { mbusE0 82 }

mbusE0Value26		OBJECT-TYPE
			SYNTAX	INTEGER
			ACCESS	read-only
			STATUS	current
	DESCRIPTION ""
			::= { mbusE0 83 }

mbusE0VIF27		OBJECT-TYPE
			SYNTAX	INTEGER
			ACCESS	read-only
			STATUS	current
	DESCRIPTION ""
			::= { mbusE0 84 }

mbusE0Value27		OBJECT-TYPE
			SYNTAX	INTEGER
			ACCESS	read-only
			STATUS	current
	DESCRIPTION ""
			::= { mbusE0 85 }

mbusE0VIF28		OBJECT-TYPE
			SYNTAX	INTEGER
			ACCESS	read-only
			STATUS	current
	DESCRIPTION ""
			::= { mbusE0 86 }

mbusE0Value28		OBJECT-TYPE
			SYNTAX	INTEGER
			ACCESS	read-only
			STATUS	current
	DESCRIPTION ""
			::= { mbusE0 87 }

mbusE0VIF29		OBJECT-TYPE
			SYNTAX	INTEGER
			ACCESS	read-only
			STATUS	current
	DESCRIPTION ""
			::= { mbusE0 88 }

mbusE0Value29		OBJECT-TYPE
			SYNTAX	INTEGER
			ACCESS	read-only
			STATUS	current
	DESCRIPTION ""
			::= { mbusE0 89 }

mbusE0VIF2A		OBJECT-TYPE
			SYNTAX	INTEGER
			ACCESS	read-only
			STATUS	current
	DESCRIPTION ""
			::= { mbusE0 90 }

mbusE0Value2A		OBJECT-TYPE
			SYNTAX	INTEGER
			ACCESS	read-only
			STATUS	current
	DESCRIPTION ""
			::= { mbusE0 91 }

mbusE0VIF2B		OBJECT-TYPE
			SYNTAX	INTEGER
			ACCESS	read-only
			STATUS	current
	DESCRIPTION ""
			::= { mbusE0 92 }

mbusE0Value2B		OBJECT-TYPE
			SYNTAX	INTEGER
			ACCESS	read-only
			STATUS	current
	DESCRIPTION ""
			::= { mbusE0 93 }

mbusE0VIF2C		OBJECT-TYPE
			SYNTAX	INTEGER
			ACCESS	read-only
			STATUS	current
	DESCRIPTION ""
			::= { mbusE0 94 }

mbusE0Value2C		OBJECT-TYPE
			SYNTAX	INTEGER
			ACCESS	read-only
			STATUS	current
	DESCRIPTION ""
			::= { mbusE0 95 }

mbusE0VIF2D		OBJECT-TYPE
			SYNTAX	INTEGER
			ACCESS	read-only
			STATUS	current
	DESCRIPTION ""
			::= { mbusE0 96 }

mbusE0Value2D		OBJECT-TYPE
			SYNTAX	INTEGER
			ACCESS	read-only
			STATUS	current
	DESCRIPTION ""
			::= { mbusE0 97 }

mbusE0VIF2E		OBJECT-TYPE
			SYNTAX	INTEGER
			ACCESS	read-only
			STATUS	current
	DESCRIPTION ""
			::= { mbusE0 98 }

mbusE0Value2E		OBJECT-TYPE
			SYNTAX	INTEGER
			ACCESS	read-only
			STATUS	current
	DESCRIPTION ""
			::= { mbusE0 99 }

mbusE0VIF2F		OBJECT-TYPE
			SYNTAX	INTEGER
			ACCESS	read-only
			STATUS	current
	DESCRIPTION ""
			::= { mbusE0 100 }

mbusE0Value2F		OBJECT-TYPE
			SYNTAX	INTEGER
			ACCESS	read-only
			STATUS	current
	DESCRIPTION ""
			::= { mbusE0 101 }

mbusE1			OBJECT IDENTIFIER ::= { mbus 225 }

mbusE1IdNumber		OBJECT-TYPE
			SYNTAX	Gauge
			ACCESS	read-only
			STATUS	current
	DESCRIPTION ""
			::= { mbusE1 1 }

mbusE1Manufacturer	OBJECT-TYPE
			SYNTAX	Gauge
			ACCESS	read-only
			STATUS	current
	DESCRIPTION ""
			::= { mbusE1 2 }

mbusE1Version		OBJECT-TYPE
			SYNTAX	Gauge
			ACCESS	read-only
			STATUS	current
	DESCRIPTION ""
			::= { mbusE1 3 }

mbusE1Medium		OBJECT-TYPE
			SYNTAX	Gauge
			ACCESS	read-only
			STATUS	current
	DESCRIPTION ""
			::= { mbusE1 4 }

mbusE1Status		OBJECT-TYPE
			SYNTAX	Gauge
			ACCESS	read-only
			STATUS	current
	DESCRIPTION ""
			::= { mbusE1 5 }

mbusE1VIF00		OBJECT-TYPE
			SYNTAX	INTEGER
			ACCESS	read-only
			STATUS	current
	DESCRIPTION ""
			::= { mbusE1 6 }

mbusE1Value00		OBJECT-TYPE
			SYNTAX	INTEGER
			ACCESS	read-only
			STATUS	current
	DESCRIPTION ""
			::= { mbusE1 7 }

mbusE1VIF01		OBJECT-TYPE
			SYNTAX	INTEGER
			ACCESS	read-only
			STATUS	current
	DESCRIPTION ""
			::= { mbusE1 8 }

mbusE1Value01		OBJECT-TYPE
			SYNTAX	INTEGER
			ACCESS	read-only
			STATUS	current
	DESCRIPTION ""
			::= { mbusE1 9 }

mbusE1VIF02		OBJECT-TYPE
			SYNTAX	INTEGER
			ACCESS	read-only
			STATUS	current
	DESCRIPTION ""
			::= { mbusE1 10 }

mbusE1Value02		OBJECT-TYPE
			SYNTAX	INTEGER
			ACCESS	read-only
			STATUS	current
	DESCRIPTION ""
			::= { mbusE1 11 }

mbusE1VIF03		OBJECT-TYPE
			SYNTAX	INTEGER
			ACCESS	read-only
			STATUS	current
	DESCRIPTION ""
			::= { mbusE1 12 }

mbusE1Value03		OBJECT-TYPE
			SYNTAX	INTEGER
			ACCESS	read-only
			STATUS	current
	DESCRIPTION ""
			::= { mbusE1 13 }

mbusE1VIF04		OBJECT-TYPE
			SYNTAX	INTEGER
			ACCESS	read-only
			STATUS	current
	DESCRIPTION ""
			::= { mbusE1 14 }

mbusE1Value04		OBJECT-TYPE
			SYNTAX	INTEGER
			ACCESS	read-only
			STATUS	current
	DESCRIPTION ""
			::= { mbusE1 15 }

mbusE1VIF05		OBJECT-TYPE
			SYNTAX	INTEGER
			ACCESS	read-only
			STATUS	current
	DESCRIPTION ""
			::= { mbusE1 16 }

mbusE1Value05		OBJECT-TYPE
			SYNTAX	INTEGER
			ACCESS	read-only
			STATUS	current
	DESCRIPTION ""
			::= { mbusE1 17 }

mbusE1VIF06		OBJECT-TYPE
			SYNTAX	INTEGER
			ACCESS	read-only
			STATUS	current
	DESCRIPTION ""
			::= { mbusE1 18 }

mbusE1Value06		OBJECT-TYPE
			SYNTAX	INTEGER
			ACCESS	read-only
			STATUS	current
	DESCRIPTION ""
			::= { mbusE1 19 }

mbusE1VIF07		OBJECT-TYPE
			SYNTAX	INTEGER
			ACCESS	read-only
			STATUS	current
	DESCRIPTION ""
			::= { mbusE1 20 }

mbusE1Value07		OBJECT-TYPE
			SYNTAX	INTEGER
			ACCESS	read-only
			STATUS	current
	DESCRIPTION ""
			::= { mbusE1 21 }

mbusE1VIF08		OBJECT-TYPE
			SYNTAX	INTEGER
			ACCESS	read-only
			STATUS	current
	DESCRIPTION ""
			::= { mbusE1 22 }

mbusE1Value08		OBJECT-TYPE
			SYNTAX	INTEGER
			ACCESS	read-only
			STATUS	current
	DESCRIPTION ""
			::= { mbusE1 23 }

mbusE1VIF09		OBJECT-TYPE
			SYNTAX	INTEGER
			ACCESS	read-only
			STATUS	current
	DESCRIPTION ""
			::= { mbusE1 24 }

mbusE1Value09		OBJECT-TYPE
			SYNTAX	INTEGER
			ACCESS	read-only
			STATUS	current
	DESCRIPTION ""
			::= { mbusE1 25 }

mbusE1VIF0A		OBJECT-TYPE
			SYNTAX	INTEGER
			ACCESS	read-only
			STATUS	current
	DESCRIPTION ""
			::= { mbusE1 26 }

mbusE1Value0A		OBJECT-TYPE
			SYNTAX	INTEGER
			ACCESS	read-only
			STATUS	current
	DESCRIPTION ""
			::= { mbusE1 27 }

mbusE1VIF0B		OBJECT-TYPE
			SYNTAX	INTEGER
			ACCESS	read-only
			STATUS	current
	DESCRIPTION ""
			::= { mbusE1 28 }

mbusE1Value0B		OBJECT-TYPE
			SYNTAX	INTEGER
			ACCESS	read-only
			STATUS	current
	DESCRIPTION ""
			::= { mbusE1 29 }

mbusE1VIF0C		OBJECT-TYPE
			SYNTAX	INTEGER
			ACCESS	read-only
			STATUS	current
	DESCRIPTION ""
			::= { mbusE1 30 }

mbusE1Value0C		OBJECT-TYPE
			SYNTAX	INTEGER
			ACCESS	read-only
			STATUS	current
	DESCRIPTION ""
			::= { mbusE1 31 }

mbusE1VIF0D		OBJECT-TYPE
			SYNTAX	INTEGER
			ACCESS	read-only
			STATUS	current
	DESCRIPTION ""
			::= { mbusE1 32 }

mbusE1Value0D		OBJECT-TYPE
			SYNTAX	INTEGER
			ACCESS	read-only
			STATUS	current
	DESCRIPTION ""
			::= { mbusE1 33 }

mbusE1VIF0E		OBJECT-TYPE
			SYNTAX	INTEGER
			ACCESS	read-only
			STATUS	current
	DESCRIPTION ""
			::= { mbusE1 34 }

mbusE1Value0E		OBJECT-TYPE
			SYNTAX	INTEGER
			ACCESS	read-only
			STATUS	current
	DESCRIPTION ""
			::= { mbusE1 35 }

mbusE1VIF0F		OBJECT-TYPE
			SYNTAX	INTEGER
			ACCESS	read-only
			STATUS	current
	DESCRIPTION ""
			::= { mbusE1 36 }

mbusE1Value0F		OBJECT-TYPE
			SYNTAX	INTEGER
			ACCESS	read-only
			STATUS	current
	DESCRIPTION ""
			::= { mbusE1 37 }

mbusE1VIF10		OBJECT-TYPE
			SYNTAX	INTEGER
			ACCESS	read-only
			STATUS	current
	DESCRIPTION ""
			::= { mbusE1 38 }

mbusE1Value10		OBJECT-TYPE
			SYNTAX	INTEGER
			ACCESS	read-only
			STATUS	current
	DESCRIPTION ""
			::= { mbusE1 39 }

mbusE1VIF11		OBJECT-TYPE
			SYNTAX	INTEGER
			ACCESS	read-only
			STATUS	current
	DESCRIPTION ""
			::= { mbusE1 40 }

mbusE1Value11		OBJECT-TYPE
			SYNTAX	INTEGER
			ACCESS	read-only
			STATUS	current
	DESCRIPTION ""
			::= { mbusE1 41 }

mbusE1VIF12		OBJECT-TYPE
			SYNTAX	INTEGER
			ACCESS	read-only
			STATUS	current
	DESCRIPTION ""
			::= { mbusE1 42 }

mbusE1Value12		OBJECT-TYPE
			SYNTAX	INTEGER
			ACCESS	read-only
			STATUS	current
	DESCRIPTION ""
			::= { mbusE1 43 }

mbusE1VIF13		OBJECT-TYPE
			SYNTAX	INTEGER
			ACCESS	read-only
			STATUS	current
	DESCRIPTION ""
			::= { mbusE1 44 }

mbusE1Value13		OBJECT-TYPE
			SYNTAX	INTEGER
			ACCESS	read-only
			STATUS	current
	DESCRIPTION ""
			::= { mbusE1 45 }

mbusE1VIF14		OBJECT-TYPE
			SYNTAX	INTEGER
			ACCESS	read-only
			STATUS	current
	DESCRIPTION ""
			::= { mbusE1 46 }

mbusE1Value14		OBJECT-TYPE
			SYNTAX	INTEGER
			ACCESS	read-only
			STATUS	current
	DESCRIPTION ""
			::= { mbusE1 47 }

mbusE1VIF15		OBJECT-TYPE
			SYNTAX	INTEGER
			ACCESS	read-only
			STATUS	current
	DESCRIPTION ""
			::= { mbusE1 48 }

mbusE1Value15		OBJECT-TYPE
			SYNTAX	INTEGER
			ACCESS	read-only
			STATUS	current
	DESCRIPTION ""
			::= { mbusE1 49 }

mbusE1VIF16		OBJECT-TYPE
			SYNTAX	INTEGER
			ACCESS	read-only
			STATUS	current
	DESCRIPTION ""
			::= { mbusE1 50 }

mbusE1Value16		OBJECT-TYPE
			SYNTAX	INTEGER
			ACCESS	read-only
			STATUS	current
	DESCRIPTION ""
			::= { mbusE1 51 }

mbusE1VIF17		OBJECT-TYPE
			SYNTAX	INTEGER
			ACCESS	read-only
			STATUS	current
	DESCRIPTION ""
			::= { mbusE1 52 }

mbusE1Value17		OBJECT-TYPE
			SYNTAX	INTEGER
			ACCESS	read-only
			STATUS	current
	DESCRIPTION ""
			::= { mbusE1 53 }

mbusE1VIF18		OBJECT-TYPE
			SYNTAX	INTEGER
			ACCESS	read-only
			STATUS	current
	DESCRIPTION ""
			::= { mbusE1 54 }

mbusE1Value18		OBJECT-TYPE
			SYNTAX	INTEGER
			ACCESS	read-only
			STATUS	current
	DESCRIPTION ""
			::= { mbusE1 55 }

mbusE1VIF19		OBJECT-TYPE
			SYNTAX	INTEGER
			ACCESS	read-only
			STATUS	current
	DESCRIPTION ""
			::= { mbusE1 56 }

mbusE1Value19		OBJECT-TYPE
			SYNTAX	INTEGER
			ACCESS	read-only
			STATUS	current
	DESCRIPTION ""
			::= { mbusE1 57 }

mbusE1VIF1A		OBJECT-TYPE
			SYNTAX	INTEGER
			ACCESS	read-only
			STATUS	current
	DESCRIPTION ""
			::= { mbusE1 58 }

mbusE1Value1A		OBJECT-TYPE
			SYNTAX	INTEGER
			ACCESS	read-only
			STATUS	current
	DESCRIPTION ""
			::= { mbusE1 59 }

mbusE1VIF1B		OBJECT-TYPE
			SYNTAX	INTEGER
			ACCESS	read-only
			STATUS	current
	DESCRIPTION ""
			::= { mbusE1 60 }

mbusE1Value1B		OBJECT-TYPE
			SYNTAX	INTEGER
			ACCESS	read-only
			STATUS	current
	DESCRIPTION ""
			::= { mbusE1 61 }

mbusE1VIF1C		OBJECT-TYPE
			SYNTAX	INTEGER
			ACCESS	read-only
			STATUS	current
	DESCRIPTION ""
			::= { mbusE1 62 }

mbusE1Value1C		OBJECT-TYPE
			SYNTAX	INTEGER
			ACCESS	read-only
			STATUS	current
	DESCRIPTION ""
			::= { mbusE1 63 }

mbusE1VIF1D		OBJECT-TYPE
			SYNTAX	INTEGER
			ACCESS	read-only
			STATUS	current
	DESCRIPTION ""
			::= { mbusE1 64 }

mbusE1Value1D		OBJECT-TYPE
			SYNTAX	INTEGER
			ACCESS	read-only
			STATUS	current
	DESCRIPTION ""
			::= { mbusE1 65 }

mbusE1VIF1E		OBJECT-TYPE
			SYNTAX	INTEGER
			ACCESS	read-only
			STATUS	current
	DESCRIPTION ""
			::= { mbusE1 66 }

mbusE1Value1E		OBJECT-TYPE
			SYNTAX	INTEGER
			ACCESS	read-only
			STATUS	current
	DESCRIPTION ""
			::= { mbusE1 67 }

mbusE1VIF1F		OBJECT-TYPE
			SYNTAX	INTEGER
			ACCESS	read-only
			STATUS	current
	DESCRIPTION ""
			::= { mbusE1 68 }

mbusE1Value1F		OBJECT-TYPE
			SYNTAX	INTEGER
			ACCESS	read-only
			STATUS	current
	DESCRIPTION ""
			::= { mbusE1 69 }

mbusE1VIF20		OBJECT-TYPE
			SYNTAX	INTEGER
			ACCESS	read-only
			STATUS	current
	DESCRIPTION ""
			::= { mbusE1 70 }

mbusE1Value20		OBJECT-TYPE
			SYNTAX	INTEGER
			ACCESS	read-only
			STATUS	current
	DESCRIPTION ""
			::= { mbusE1 71 }

mbusE1VIF21		OBJECT-TYPE
			SYNTAX	INTEGER
			ACCESS	read-only
			STATUS	current
	DESCRIPTION ""
			::= { mbusE1 72 }

mbusE1Value21		OBJECT-TYPE
			SYNTAX	INTEGER
			ACCESS	read-only
			STATUS	current
	DESCRIPTION ""
			::= { mbusE1 73 }

mbusE1VIF22		OBJECT-TYPE
			SYNTAX	INTEGER
			ACCESS	read-only
			STATUS	current
	DESCRIPTION ""
			::= { mbusE1 74 }

mbusE1Value22		OBJECT-TYPE
			SYNTAX	INTEGER
			ACCESS	read-only
			STATUS	current
	DESCRIPTION ""
			::= { mbusE1 75 }

mbusE1VIF23		OBJECT-TYPE
			SYNTAX	INTEGER
			ACCESS	read-only
			STATUS	current
	DESCRIPTION ""
			::= { mbusE1 76 }

mbusE1Value23		OBJECT-TYPE
			SYNTAX	INTEGER
			ACCESS	read-only
			STATUS	current
	DESCRIPTION ""
			::= { mbusE1 77 }

mbusE1VIF24		OBJECT-TYPE
			SYNTAX	INTEGER
			ACCESS	read-only
			STATUS	current
	DESCRIPTION ""
			::= { mbusE1 78 }

mbusE1Value24		OBJECT-TYPE
			SYNTAX	INTEGER
			ACCESS	read-only
			STATUS	current
	DESCRIPTION ""
			::= { mbusE1 79 }

mbusE1VIF25		OBJECT-TYPE
			SYNTAX	INTEGER
			ACCESS	read-only
			STATUS	current
	DESCRIPTION ""
			::= { mbusE1 80 }

mbusE1Value25		OBJECT-TYPE
			SYNTAX	INTEGER
			ACCESS	read-only
			STATUS	current
	DESCRIPTION ""
			::= { mbusE1 81 }

mbusE1VIF26		OBJECT-TYPE
			SYNTAX	INTEGER
			ACCESS	read-only
			STATUS	current
	DESCRIPTION ""
			::= { mbusE1 82 }

mbusE1Value26		OBJECT-TYPE
			SYNTAX	INTEGER
			ACCESS	read-only
			STATUS	current
	DESCRIPTION ""
			::= { mbusE1 83 }

mbusE1VIF27		OBJECT-TYPE
			SYNTAX	INTEGER
			ACCESS	read-only
			STATUS	current
	DESCRIPTION ""
			::= { mbusE1 84 }

mbusE1Value27		OBJECT-TYPE
			SYNTAX	INTEGER
			ACCESS	read-only
			STATUS	current
	DESCRIPTION ""
			::= { mbusE1 85 }

mbusE1VIF28		OBJECT-TYPE
			SYNTAX	INTEGER
			ACCESS	read-only
			STATUS	current
	DESCRIPTION ""
			::= { mbusE1 86 }

mbusE1Value28		OBJECT-TYPE
			SYNTAX	INTEGER
			ACCESS	read-only
			STATUS	current
	DESCRIPTION ""
			::= { mbusE1 87 }

mbusE1VIF29		OBJECT-TYPE
			SYNTAX	INTEGER
			ACCESS	read-only
			STATUS	current
	DESCRIPTION ""
			::= { mbusE1 88 }

mbusE1Value29		OBJECT-TYPE
			SYNTAX	INTEGER
			ACCESS	read-only
			STATUS	current
	DESCRIPTION ""
			::= { mbusE1 89 }

mbusE1VIF2A		OBJECT-TYPE
			SYNTAX	INTEGER
			ACCESS	read-only
			STATUS	current
	DESCRIPTION ""
			::= { mbusE1 90 }

mbusE1Value2A		OBJECT-TYPE
			SYNTAX	INTEGER
			ACCESS	read-only
			STATUS	current
	DESCRIPTION ""
			::= { mbusE1 91 }

mbusE1VIF2B		OBJECT-TYPE
			SYNTAX	INTEGER
			ACCESS	read-only
			STATUS	current
	DESCRIPTION ""
			::= { mbusE1 92 }

mbusE1Value2B		OBJECT-TYPE
			SYNTAX	INTEGER
			ACCESS	read-only
			STATUS	current
	DESCRIPTION ""
			::= { mbusE1 93 }

mbusE1VIF2C		OBJECT-TYPE
			SYNTAX	INTEGER
			ACCESS	read-only
			STATUS	current
	DESCRIPTION ""
			::= { mbusE1 94 }

mbusE1Value2C		OBJECT-TYPE
			SYNTAX	INTEGER
			ACCESS	read-only
			STATUS	current
	DESCRIPTION ""
			::= { mbusE1 95 }

mbusE1VIF2D		OBJECT-TYPE
			SYNTAX	INTEGER
			ACCESS	read-only
			STATUS	current
	DESCRIPTION ""
			::= { mbusE1 96 }

mbusE1Value2D		OBJECT-TYPE
			SYNTAX	INTEGER
			ACCESS	read-only
			STATUS	current
	DESCRIPTION ""
			::= { mbusE1 97 }

mbusE1VIF2E		OBJECT-TYPE
			SYNTAX	INTEGER
			ACCESS	read-only
			STATUS	current
	DESCRIPTION ""
			::= { mbusE1 98 }

mbusE1Value2E		OBJECT-TYPE
			SYNTAX	INTEGER
			ACCESS	read-only
			STATUS	current
	DESCRIPTION ""
			::= { mbusE1 99 }

mbusE1VIF2F		OBJECT-TYPE
			SYNTAX	INTEGER
			ACCESS	read-only
			STATUS	current
	DESCRIPTION ""
			::= { mbusE1 100 }

mbusE1Value2F		OBJECT-TYPE
			SYNTAX	INTEGER
			ACCESS	read-only
			STATUS	current
	DESCRIPTION ""
			::= { mbusE1 101 }

mbusE2			OBJECT IDENTIFIER ::= { mbus 226 }

mbusE2IdNumber		OBJECT-TYPE
			SYNTAX	Gauge
			ACCESS	read-only
			STATUS	current
	DESCRIPTION ""
			::= { mbusE2 1 }

mbusE2Manufacturer	OBJECT-TYPE
			SYNTAX	Gauge
			ACCESS	read-only
			STATUS	current
	DESCRIPTION ""
			::= { mbusE2 2 }

mbusE2Version		OBJECT-TYPE
			SYNTAX	Gauge
			ACCESS	read-only
			STATUS	current
	DESCRIPTION ""
			::= { mbusE2 3 }

mbusE2Medium		OBJECT-TYPE
			SYNTAX	Gauge
			ACCESS	read-only
			STATUS	current
	DESCRIPTION ""
			::= { mbusE2 4 }

mbusE2Status		OBJECT-TYPE
			SYNTAX	Gauge
			ACCESS	read-only
			STATUS	current
	DESCRIPTION ""
			::= { mbusE2 5 }

mbusE2VIF00		OBJECT-TYPE
			SYNTAX	INTEGER
			ACCESS	read-only
			STATUS	current
	DESCRIPTION ""
			::= { mbusE2 6 }

mbusE2Value00		OBJECT-TYPE
			SYNTAX	INTEGER
			ACCESS	read-only
			STATUS	current
	DESCRIPTION ""
			::= { mbusE2 7 }

mbusE2VIF01		OBJECT-TYPE
			SYNTAX	INTEGER
			ACCESS	read-only
			STATUS	current
	DESCRIPTION ""
			::= { mbusE2 8 }

mbusE2Value01		OBJECT-TYPE
			SYNTAX	INTEGER
			ACCESS	read-only
			STATUS	current
	DESCRIPTION ""
			::= { mbusE2 9 }

mbusE2VIF02		OBJECT-TYPE
			SYNTAX	INTEGER
			ACCESS	read-only
			STATUS	current
	DESCRIPTION ""
			::= { mbusE2 10 }

mbusE2Value02		OBJECT-TYPE
			SYNTAX	INTEGER
			ACCESS	read-only
			STATUS	current
	DESCRIPTION ""
			::= { mbusE2 11 }

mbusE2VIF03		OBJECT-TYPE
			SYNTAX	INTEGER
			ACCESS	read-only
			STATUS	current
	DESCRIPTION ""
			::= { mbusE2 12 }

mbusE2Value03		OBJECT-TYPE
			SYNTAX	INTEGER
			ACCESS	read-only
			STATUS	current
	DESCRIPTION ""
			::= { mbusE2 13 }

mbusE2VIF04		OBJECT-TYPE
			SYNTAX	INTEGER
			ACCESS	read-only
			STATUS	current
	DESCRIPTION ""
			::= { mbusE2 14 }

mbusE2Value04		OBJECT-TYPE
			SYNTAX	INTEGER
			ACCESS	read-only
			STATUS	current
	DESCRIPTION ""
			::= { mbusE2 15 }

mbusE2VIF05		OBJECT-TYPE
			SYNTAX	INTEGER
			ACCESS	read-only
			STATUS	current
	DESCRIPTION ""
			::= { mbusE2 16 }

mbusE2Value05		OBJECT-TYPE
			SYNTAX	INTEGER
			ACCESS	read-only
			STATUS	current
	DESCRIPTION ""
			::= { mbusE2 17 }

mbusE2VIF06		OBJECT-TYPE
			SYNTAX	INTEGER
			ACCESS	read-only
			STATUS	current
	DESCRIPTION ""
			::= { mbusE2 18 }

mbusE2Value06		OBJECT-TYPE
			SYNTAX	INTEGER
			ACCESS	read-only
			STATUS	current
	DESCRIPTION ""
			::= { mbusE2 19 }

mbusE2VIF07		OBJECT-TYPE
			SYNTAX	INTEGER
			ACCESS	read-only
			STATUS	current
	DESCRIPTION ""
			::= { mbusE2 20 }

mbusE2Value07		OBJECT-TYPE
			SYNTAX	INTEGER
			ACCESS	read-only
			STATUS	current
	DESCRIPTION ""
			::= { mbusE2 21 }

mbusE2VIF08		OBJECT-TYPE
			SYNTAX	INTEGER
			ACCESS	read-only
			STATUS	current
	DESCRIPTION ""
			::= { mbusE2 22 }

mbusE2Value08		OBJECT-TYPE
			SYNTAX	INTEGER
			ACCESS	read-only
			STATUS	current
	DESCRIPTION ""
			::= { mbusE2 23 }

mbusE2VIF09		OBJECT-TYPE
			SYNTAX	INTEGER
			ACCESS	read-only
			STATUS	current
	DESCRIPTION ""
			::= { mbusE2 24 }

mbusE2Value09		OBJECT-TYPE
			SYNTAX	INTEGER
			ACCESS	read-only
			STATUS	current
	DESCRIPTION ""
			::= { mbusE2 25 }

mbusE2VIF0A		OBJECT-TYPE
			SYNTAX	INTEGER
			ACCESS	read-only
			STATUS	current
	DESCRIPTION ""
			::= { mbusE2 26 }

mbusE2Value0A		OBJECT-TYPE
			SYNTAX	INTEGER
			ACCESS	read-only
			STATUS	current
	DESCRIPTION ""
			::= { mbusE2 27 }

mbusE2VIF0B		OBJECT-TYPE
			SYNTAX	INTEGER
			ACCESS	read-only
			STATUS	current
	DESCRIPTION ""
			::= { mbusE2 28 }

mbusE2Value0B		OBJECT-TYPE
			SYNTAX	INTEGER
			ACCESS	read-only
			STATUS	current
	DESCRIPTION ""
			::= { mbusE2 29 }

mbusE2VIF0C		OBJECT-TYPE
			SYNTAX	INTEGER
			ACCESS	read-only
			STATUS	current
	DESCRIPTION ""
			::= { mbusE2 30 }

mbusE2Value0C		OBJECT-TYPE
			SYNTAX	INTEGER
			ACCESS	read-only
			STATUS	current
	DESCRIPTION ""
			::= { mbusE2 31 }

mbusE2VIF0D		OBJECT-TYPE
			SYNTAX	INTEGER
			ACCESS	read-only
			STATUS	current
	DESCRIPTION ""
			::= { mbusE2 32 }

mbusE2Value0D		OBJECT-TYPE
			SYNTAX	INTEGER
			ACCESS	read-only
			STATUS	current
	DESCRIPTION ""
			::= { mbusE2 33 }

mbusE2VIF0E		OBJECT-TYPE
			SYNTAX	INTEGER
			ACCESS	read-only
			STATUS	current
	DESCRIPTION ""
			::= { mbusE2 34 }

mbusE2Value0E		OBJECT-TYPE
			SYNTAX	INTEGER
			ACCESS	read-only
			STATUS	current
	DESCRIPTION ""
			::= { mbusE2 35 }

mbusE2VIF0F		OBJECT-TYPE
			SYNTAX	INTEGER
			ACCESS	read-only
			STATUS	current
	DESCRIPTION ""
			::= { mbusE2 36 }

mbusE2Value0F		OBJECT-TYPE
			SYNTAX	INTEGER
			ACCESS	read-only
			STATUS	current
	DESCRIPTION ""
			::= { mbusE2 37 }

mbusE2VIF10		OBJECT-TYPE
			SYNTAX	INTEGER
			ACCESS	read-only
			STATUS	current
	DESCRIPTION ""
			::= { mbusE2 38 }

mbusE2Value10		OBJECT-TYPE
			SYNTAX	INTEGER
			ACCESS	read-only
			STATUS	current
	DESCRIPTION ""
			::= { mbusE2 39 }

mbusE2VIF11		OBJECT-TYPE
			SYNTAX	INTEGER
			ACCESS	read-only
			STATUS	current
	DESCRIPTION ""
			::= { mbusE2 40 }

mbusE2Value11		OBJECT-TYPE
			SYNTAX	INTEGER
			ACCESS	read-only
			STATUS	current
	DESCRIPTION ""
			::= { mbusE2 41 }

mbusE2VIF12		OBJECT-TYPE
			SYNTAX	INTEGER
			ACCESS	read-only
			STATUS	current
	DESCRIPTION ""
			::= { mbusE2 42 }

mbusE2Value12		OBJECT-TYPE
			SYNTAX	INTEGER
			ACCESS	read-only
			STATUS	current
	DESCRIPTION ""
			::= { mbusE2 43 }

mbusE2VIF13		OBJECT-TYPE
			SYNTAX	INTEGER
			ACCESS	read-only
			STATUS	current
	DESCRIPTION ""
			::= { mbusE2 44 }

mbusE2Value13		OBJECT-TYPE
			SYNTAX	INTEGER
			ACCESS	read-only
			STATUS	current
	DESCRIPTION ""
			::= { mbusE2 45 }

mbusE2VIF14		OBJECT-TYPE
			SYNTAX	INTEGER
			ACCESS	read-only
			STATUS	current
	DESCRIPTION ""
			::= { mbusE2 46 }

mbusE2Value14		OBJECT-TYPE
			SYNTAX	INTEGER
			ACCESS	read-only
			STATUS	current
	DESCRIPTION ""
			::= { mbusE2 47 }

mbusE2VIF15		OBJECT-TYPE
			SYNTAX	INTEGER
			ACCESS	read-only
			STATUS	current
	DESCRIPTION ""
			::= { mbusE2 48 }

mbusE2Value15		OBJECT-TYPE
			SYNTAX	INTEGER
			ACCESS	read-only
			STATUS	current
	DESCRIPTION ""
			::= { mbusE2 49 }

mbusE2VIF16		OBJECT-TYPE
			SYNTAX	INTEGER
			ACCESS	read-only
			STATUS	current
	DESCRIPTION ""
			::= { mbusE2 50 }

mbusE2Value16		OBJECT-TYPE
			SYNTAX	INTEGER
			ACCESS	read-only
			STATUS	current
	DESCRIPTION ""
			::= { mbusE2 51 }

mbusE2VIF17		OBJECT-TYPE
			SYNTAX	INTEGER
			ACCESS	read-only
			STATUS	current
	DESCRIPTION ""
			::= { mbusE2 52 }

mbusE2Value17		OBJECT-TYPE
			SYNTAX	INTEGER
			ACCESS	read-only
			STATUS	current
	DESCRIPTION ""
			::= { mbusE2 53 }

mbusE2VIF18		OBJECT-TYPE
			SYNTAX	INTEGER
			ACCESS	read-only
			STATUS	current
	DESCRIPTION ""
			::= { mbusE2 54 }

mbusE2Value18		OBJECT-TYPE
			SYNTAX	INTEGER
			ACCESS	read-only
			STATUS	current
	DESCRIPTION ""
			::= { mbusE2 55 }

mbusE2VIF19		OBJECT-TYPE
			SYNTAX	INTEGER
			ACCESS	read-only
			STATUS	current
	DESCRIPTION ""
			::= { mbusE2 56 }

mbusE2Value19		OBJECT-TYPE
			SYNTAX	INTEGER
			ACCESS	read-only
			STATUS	current
	DESCRIPTION ""
			::= { mbusE2 57 }

mbusE2VIF1A		OBJECT-TYPE
			SYNTAX	INTEGER
			ACCESS	read-only
			STATUS	current
	DESCRIPTION ""
			::= { mbusE2 58 }

mbusE2Value1A		OBJECT-TYPE
			SYNTAX	INTEGER
			ACCESS	read-only
			STATUS	current
	DESCRIPTION ""
			::= { mbusE2 59 }

mbusE2VIF1B		OBJECT-TYPE
			SYNTAX	INTEGER
			ACCESS	read-only
			STATUS	current
	DESCRIPTION ""
			::= { mbusE2 60 }

mbusE2Value1B		OBJECT-TYPE
			SYNTAX	INTEGER
			ACCESS	read-only
			STATUS	current
	DESCRIPTION ""
			::= { mbusE2 61 }

mbusE2VIF1C		OBJECT-TYPE
			SYNTAX	INTEGER
			ACCESS	read-only
			STATUS	current
	DESCRIPTION ""
			::= { mbusE2 62 }

mbusE2Value1C		OBJECT-TYPE
			SYNTAX	INTEGER
			ACCESS	read-only
			STATUS	current
	DESCRIPTION ""
			::= { mbusE2 63 }

mbusE2VIF1D		OBJECT-TYPE
			SYNTAX	INTEGER
			ACCESS	read-only
			STATUS	current
	DESCRIPTION ""
			::= { mbusE2 64 }

mbusE2Value1D		OBJECT-TYPE
			SYNTAX	INTEGER
			ACCESS	read-only
			STATUS	current
	DESCRIPTION ""
			::= { mbusE2 65 }

mbusE2VIF1E		OBJECT-TYPE
			SYNTAX	INTEGER
			ACCESS	read-only
			STATUS	current
	DESCRIPTION ""
			::= { mbusE2 66 }

mbusE2Value1E		OBJECT-TYPE
			SYNTAX	INTEGER
			ACCESS	read-only
			STATUS	current
	DESCRIPTION ""
			::= { mbusE2 67 }

mbusE2VIF1F		OBJECT-TYPE
			SYNTAX	INTEGER
			ACCESS	read-only
			STATUS	current
	DESCRIPTION ""
			::= { mbusE2 68 }

mbusE2Value1F		OBJECT-TYPE
			SYNTAX	INTEGER
			ACCESS	read-only
			STATUS	current
	DESCRIPTION ""
			::= { mbusE2 69 }

mbusE2VIF20		OBJECT-TYPE
			SYNTAX	INTEGER
			ACCESS	read-only
			STATUS	current
	DESCRIPTION ""
			::= { mbusE2 70 }

mbusE2Value20		OBJECT-TYPE
			SYNTAX	INTEGER
			ACCESS	read-only
			STATUS	current
	DESCRIPTION ""
			::= { mbusE2 71 }

mbusE2VIF21		OBJECT-TYPE
			SYNTAX	INTEGER
			ACCESS	read-only
			STATUS	current
	DESCRIPTION ""
			::= { mbusE2 72 }

mbusE2Value21		OBJECT-TYPE
			SYNTAX	INTEGER
			ACCESS	read-only
			STATUS	current
	DESCRIPTION ""
			::= { mbusE2 73 }

mbusE2VIF22		OBJECT-TYPE
			SYNTAX	INTEGER
			ACCESS	read-only
			STATUS	current
	DESCRIPTION ""
			::= { mbusE2 74 }

mbusE2Value22		OBJECT-TYPE
			SYNTAX	INTEGER
			ACCESS	read-only
			STATUS	current
	DESCRIPTION ""
			::= { mbusE2 75 }

mbusE2VIF23		OBJECT-TYPE
			SYNTAX	INTEGER
			ACCESS	read-only
			STATUS	current
	DESCRIPTION ""
			::= { mbusE2 76 }

mbusE2Value23		OBJECT-TYPE
			SYNTAX	INTEGER
			ACCESS	read-only
			STATUS	current
	DESCRIPTION ""
			::= { mbusE2 77 }

mbusE2VIF24		OBJECT-TYPE
			SYNTAX	INTEGER
			ACCESS	read-only
			STATUS	current
	DESCRIPTION ""
			::= { mbusE2 78 }

mbusE2Value24		OBJECT-TYPE
			SYNTAX	INTEGER
			ACCESS	read-only
			STATUS	current
	DESCRIPTION ""
			::= { mbusE2 79 }

mbusE2VIF25		OBJECT-TYPE
			SYNTAX	INTEGER
			ACCESS	read-only
			STATUS	current
	DESCRIPTION ""
			::= { mbusE2 80 }

mbusE2Value25		OBJECT-TYPE
			SYNTAX	INTEGER
			ACCESS	read-only
			STATUS	current
	DESCRIPTION ""
			::= { mbusE2 81 }

mbusE2VIF26		OBJECT-TYPE
			SYNTAX	INTEGER
			ACCESS	read-only
			STATUS	current
	DESCRIPTION ""
			::= { mbusE2 82 }

mbusE2Value26		OBJECT-TYPE
			SYNTAX	INTEGER
			ACCESS	read-only
			STATUS	current
	DESCRIPTION ""
			::= { mbusE2 83 }

mbusE2VIF27		OBJECT-TYPE
			SYNTAX	INTEGER
			ACCESS	read-only
			STATUS	current
	DESCRIPTION ""
			::= { mbusE2 84 }

mbusE2Value27		OBJECT-TYPE
			SYNTAX	INTEGER
			ACCESS	read-only
			STATUS	current
	DESCRIPTION ""
			::= { mbusE2 85 }

mbusE2VIF28		OBJECT-TYPE
			SYNTAX	INTEGER
			ACCESS	read-only
			STATUS	current
	DESCRIPTION ""
			::= { mbusE2 86 }

mbusE2Value28		OBJECT-TYPE
			SYNTAX	INTEGER
			ACCESS	read-only
			STATUS	current
	DESCRIPTION ""
			::= { mbusE2 87 }

mbusE2VIF29		OBJECT-TYPE
			SYNTAX	INTEGER
			ACCESS	read-only
			STATUS	current
	DESCRIPTION ""
			::= { mbusE2 88 }

mbusE2Value29		OBJECT-TYPE
			SYNTAX	INTEGER
			ACCESS	read-only
			STATUS	current
	DESCRIPTION ""
			::= { mbusE2 89 }

mbusE2VIF2A		OBJECT-TYPE
			SYNTAX	INTEGER
			ACCESS	read-only
			STATUS	current
	DESCRIPTION ""
			::= { mbusE2 90 }

mbusE2Value2A		OBJECT-TYPE
			SYNTAX	INTEGER
			ACCESS	read-only
			STATUS	current
	DESCRIPTION ""
			::= { mbusE2 91 }

mbusE2VIF2B		OBJECT-TYPE
			SYNTAX	INTEGER
			ACCESS	read-only
			STATUS	current
	DESCRIPTION ""
			::= { mbusE2 92 }

mbusE2Value2B		OBJECT-TYPE
			SYNTAX	INTEGER
			ACCESS	read-only
			STATUS	current
	DESCRIPTION ""
			::= { mbusE2 93 }

mbusE2VIF2C		OBJECT-TYPE
			SYNTAX	INTEGER
			ACCESS	read-only
			STATUS	current
	DESCRIPTION ""
			::= { mbusE2 94 }

mbusE2Value2C		OBJECT-TYPE
			SYNTAX	INTEGER
			ACCESS	read-only
			STATUS	current
	DESCRIPTION ""
			::= { mbusE2 95 }

mbusE2VIF2D		OBJECT-TYPE
			SYNTAX	INTEGER
			ACCESS	read-only
			STATUS	current
	DESCRIPTION ""
			::= { mbusE2 96 }

mbusE2Value2D		OBJECT-TYPE
			SYNTAX	INTEGER
			ACCESS	read-only
			STATUS	current
	DESCRIPTION ""
			::= { mbusE2 97 }

mbusE2VIF2E		OBJECT-TYPE
			SYNTAX	INTEGER
			ACCESS	read-only
			STATUS	current
	DESCRIPTION ""
			::= { mbusE2 98 }

mbusE2Value2E		OBJECT-TYPE
			SYNTAX	INTEGER
			ACCESS	read-only
			STATUS	current
	DESCRIPTION ""
			::= { mbusE2 99 }

mbusE2VIF2F		OBJECT-TYPE
			SYNTAX	INTEGER
			ACCESS	read-only
			STATUS	current
	DESCRIPTION ""
			::= { mbusE2 100 }

mbusE2Value2F		OBJECT-TYPE
			SYNTAX	INTEGER
			ACCESS	read-only
			STATUS	current
	DESCRIPTION ""
			::= { mbusE2 101 }

mbusE3			OBJECT IDENTIFIER ::= { mbus 227 }

mbusE3IdNumber		OBJECT-TYPE
			SYNTAX	Gauge
			ACCESS	read-only
			STATUS	current
	DESCRIPTION ""
			::= { mbusE3 1 }

mbusE3Manufacturer	OBJECT-TYPE
			SYNTAX	Gauge
			ACCESS	read-only
			STATUS	current
	DESCRIPTION ""
			::= { mbusE3 2 }

mbusE3Version		OBJECT-TYPE
			SYNTAX	Gauge
			ACCESS	read-only
			STATUS	current
	DESCRIPTION ""
			::= { mbusE3 3 }

mbusE3Medium		OBJECT-TYPE
			SYNTAX	Gauge
			ACCESS	read-only
			STATUS	current
	DESCRIPTION ""
			::= { mbusE3 4 }

mbusE3Status		OBJECT-TYPE
			SYNTAX	Gauge
			ACCESS	read-only
			STATUS	current
	DESCRIPTION ""
			::= { mbusE3 5 }

mbusE3VIF00		OBJECT-TYPE
			SYNTAX	INTEGER
			ACCESS	read-only
			STATUS	current
	DESCRIPTION ""
			::= { mbusE3 6 }

mbusE3Value00		OBJECT-TYPE
			SYNTAX	INTEGER
			ACCESS	read-only
			STATUS	current
	DESCRIPTION ""
			::= { mbusE3 7 }

mbusE3VIF01		OBJECT-TYPE
			SYNTAX	INTEGER
			ACCESS	read-only
			STATUS	current
	DESCRIPTION ""
			::= { mbusE3 8 }

mbusE3Value01		OBJECT-TYPE
			SYNTAX	INTEGER
			ACCESS	read-only
			STATUS	current
	DESCRIPTION ""
			::= { mbusE3 9 }

mbusE3VIF02		OBJECT-TYPE
			SYNTAX	INTEGER
			ACCESS	read-only
			STATUS	current
	DESCRIPTION ""
			::= { mbusE3 10 }

mbusE3Value02		OBJECT-TYPE
			SYNTAX	INTEGER
			ACCESS	read-only
			STATUS	current
	DESCRIPTION ""
			::= { mbusE3 11 }

mbusE3VIF03		OBJECT-TYPE
			SYNTAX	INTEGER
			ACCESS	read-only
			STATUS	current
	DESCRIPTION ""
			::= { mbusE3 12 }

mbusE3Value03		OBJECT-TYPE
			SYNTAX	INTEGER
			ACCESS	read-only
			STATUS	current
	DESCRIPTION ""
			::= { mbusE3 13 }

mbusE3VIF04		OBJECT-TYPE
			SYNTAX	INTEGER
			ACCESS	read-only
			STATUS	current
	DESCRIPTION ""
			::= { mbusE3 14 }

mbusE3Value04		OBJECT-TYPE
			SYNTAX	INTEGER
			ACCESS	read-only
			STATUS	current
	DESCRIPTION ""
			::= { mbusE3 15 }

mbusE3VIF05		OBJECT-TYPE
			SYNTAX	INTEGER
			ACCESS	read-only
			STATUS	current
	DESCRIPTION ""
			::= { mbusE3 16 }

mbusE3Value05		OBJECT-TYPE
			SYNTAX	INTEGER
			ACCESS	read-only
			STATUS	current
	DESCRIPTION ""
			::= { mbusE3 17 }

mbusE3VIF06		OBJECT-TYPE
			SYNTAX	INTEGER
			ACCESS	read-only
			STATUS	current
	DESCRIPTION ""
			::= { mbusE3 18 }

mbusE3Value06		OBJECT-TYPE
			SYNTAX	INTEGER
			ACCESS	read-only
			STATUS	current
	DESCRIPTION ""
			::= { mbusE3 19 }

mbusE3VIF07		OBJECT-TYPE
			SYNTAX	INTEGER
			ACCESS	read-only
			STATUS	current
	DESCRIPTION ""
			::= { mbusE3 20 }

mbusE3Value07		OBJECT-TYPE
			SYNTAX	INTEGER
			ACCESS	read-only
			STATUS	current
	DESCRIPTION ""
			::= { mbusE3 21 }

mbusE3VIF08		OBJECT-TYPE
			SYNTAX	INTEGER
			ACCESS	read-only
			STATUS	current
	DESCRIPTION ""
			::= { mbusE3 22 }

mbusE3Value08		OBJECT-TYPE
			SYNTAX	INTEGER
			ACCESS	read-only
			STATUS	current
	DESCRIPTION ""
			::= { mbusE3 23 }

mbusE3VIF09		OBJECT-TYPE
			SYNTAX	INTEGER
			ACCESS	read-only
			STATUS	current
	DESCRIPTION ""
			::= { mbusE3 24 }

mbusE3Value09		OBJECT-TYPE
			SYNTAX	INTEGER
			ACCESS	read-only
			STATUS	current
	DESCRIPTION ""
			::= { mbusE3 25 }

mbusE3VIF0A		OBJECT-TYPE
			SYNTAX	INTEGER
			ACCESS	read-only
			STATUS	current
	DESCRIPTION ""
			::= { mbusE3 26 }

mbusE3Value0A		OBJECT-TYPE
			SYNTAX	INTEGER
			ACCESS	read-only
			STATUS	current
	DESCRIPTION ""
			::= { mbusE3 27 }

mbusE3VIF0B		OBJECT-TYPE
			SYNTAX	INTEGER
			ACCESS	read-only
			STATUS	current
	DESCRIPTION ""
			::= { mbusE3 28 }

mbusE3Value0B		OBJECT-TYPE
			SYNTAX	INTEGER
			ACCESS	read-only
			STATUS	current
	DESCRIPTION ""
			::= { mbusE3 29 }

mbusE3VIF0C		OBJECT-TYPE
			SYNTAX	INTEGER
			ACCESS	read-only
			STATUS	current
	DESCRIPTION ""
			::= { mbusE3 30 }

mbusE3Value0C		OBJECT-TYPE
			SYNTAX	INTEGER
			ACCESS	read-only
			STATUS	current
	DESCRIPTION ""
			::= { mbusE3 31 }

mbusE3VIF0D		OBJECT-TYPE
			SYNTAX	INTEGER
			ACCESS	read-only
			STATUS	current
	DESCRIPTION ""
			::= { mbusE3 32 }

mbusE3Value0D		OBJECT-TYPE
			SYNTAX	INTEGER
			ACCESS	read-only
			STATUS	current
	DESCRIPTION ""
			::= { mbusE3 33 }

mbusE3VIF0E		OBJECT-TYPE
			SYNTAX	INTEGER
			ACCESS	read-only
			STATUS	current
	DESCRIPTION ""
			::= { mbusE3 34 }

mbusE3Value0E		OBJECT-TYPE
			SYNTAX	INTEGER
			ACCESS	read-only
			STATUS	current
	DESCRIPTION ""
			::= { mbusE3 35 }

mbusE3VIF0F		OBJECT-TYPE
			SYNTAX	INTEGER
			ACCESS	read-only
			STATUS	current
	DESCRIPTION ""
			::= { mbusE3 36 }

mbusE3Value0F		OBJECT-TYPE
			SYNTAX	INTEGER
			ACCESS	read-only
			STATUS	current
	DESCRIPTION ""
			::= { mbusE3 37 }

mbusE3VIF10		OBJECT-TYPE
			SYNTAX	INTEGER
			ACCESS	read-only
			STATUS	current
	DESCRIPTION ""
			::= { mbusE3 38 }

mbusE3Value10		OBJECT-TYPE
			SYNTAX	INTEGER
			ACCESS	read-only
			STATUS	current
	DESCRIPTION ""
			::= { mbusE3 39 }

mbusE3VIF11		OBJECT-TYPE
			SYNTAX	INTEGER
			ACCESS	read-only
			STATUS	current
	DESCRIPTION ""
			::= { mbusE3 40 }

mbusE3Value11		OBJECT-TYPE
			SYNTAX	INTEGER
			ACCESS	read-only
			STATUS	current
	DESCRIPTION ""
			::= { mbusE3 41 }

mbusE3VIF12		OBJECT-TYPE
			SYNTAX	INTEGER
			ACCESS	read-only
			STATUS	current
	DESCRIPTION ""
			::= { mbusE3 42 }

mbusE3Value12		OBJECT-TYPE
			SYNTAX	INTEGER
			ACCESS	read-only
			STATUS	current
	DESCRIPTION ""
			::= { mbusE3 43 }

mbusE3VIF13		OBJECT-TYPE
			SYNTAX	INTEGER
			ACCESS	read-only
			STATUS	current
	DESCRIPTION ""
			::= { mbusE3 44 }

mbusE3Value13		OBJECT-TYPE
			SYNTAX	INTEGER
			ACCESS	read-only
			STATUS	current
	DESCRIPTION ""
			::= { mbusE3 45 }

mbusE3VIF14		OBJECT-TYPE
			SYNTAX	INTEGER
			ACCESS	read-only
			STATUS	current
	DESCRIPTION ""
			::= { mbusE3 46 }

mbusE3Value14		OBJECT-TYPE
			SYNTAX	INTEGER
			ACCESS	read-only
			STATUS	current
	DESCRIPTION ""
			::= { mbusE3 47 }

mbusE3VIF15		OBJECT-TYPE
			SYNTAX	INTEGER
			ACCESS	read-only
			STATUS	current
	DESCRIPTION ""
			::= { mbusE3 48 }

mbusE3Value15		OBJECT-TYPE
			SYNTAX	INTEGER
			ACCESS	read-only
			STATUS	current
	DESCRIPTION ""
			::= { mbusE3 49 }

mbusE3VIF16		OBJECT-TYPE
			SYNTAX	INTEGER
			ACCESS	read-only
			STATUS	current
	DESCRIPTION ""
			::= { mbusE3 50 }

mbusE3Value16		OBJECT-TYPE
			SYNTAX	INTEGER
			ACCESS	read-only
			STATUS	current
	DESCRIPTION ""
			::= { mbusE3 51 }

mbusE3VIF17		OBJECT-TYPE
			SYNTAX	INTEGER
			ACCESS	read-only
			STATUS	current
	DESCRIPTION ""
			::= { mbusE3 52 }

mbusE3Value17		OBJECT-TYPE
			SYNTAX	INTEGER
			ACCESS	read-only
			STATUS	current
	DESCRIPTION ""
			::= { mbusE3 53 }

mbusE3VIF18		OBJECT-TYPE
			SYNTAX	INTEGER
			ACCESS	read-only
			STATUS	current
	DESCRIPTION ""
			::= { mbusE3 54 }

mbusE3Value18		OBJECT-TYPE
			SYNTAX	INTEGER
			ACCESS	read-only
			STATUS	current
	DESCRIPTION ""
			::= { mbusE3 55 }

mbusE3VIF19		OBJECT-TYPE
			SYNTAX	INTEGER
			ACCESS	read-only
			STATUS	current
	DESCRIPTION ""
			::= { mbusE3 56 }

mbusE3Value19		OBJECT-TYPE
			SYNTAX	INTEGER
			ACCESS	read-only
			STATUS	current
	DESCRIPTION ""
			::= { mbusE3 57 }

mbusE3VIF1A		OBJECT-TYPE
			SYNTAX	INTEGER
			ACCESS	read-only
			STATUS	current
	DESCRIPTION ""
			::= { mbusE3 58 }

mbusE3Value1A		OBJECT-TYPE
			SYNTAX	INTEGER
			ACCESS	read-only
			STATUS	current
	DESCRIPTION ""
			::= { mbusE3 59 }

mbusE3VIF1B		OBJECT-TYPE
			SYNTAX	INTEGER
			ACCESS	read-only
			STATUS	current
	DESCRIPTION ""
			::= { mbusE3 60 }

mbusE3Value1B		OBJECT-TYPE
			SYNTAX	INTEGER
			ACCESS	read-only
			STATUS	current
	DESCRIPTION ""
			::= { mbusE3 61 }

mbusE3VIF1C		OBJECT-TYPE
			SYNTAX	INTEGER
			ACCESS	read-only
			STATUS	current
	DESCRIPTION ""
			::= { mbusE3 62 }

mbusE3Value1C		OBJECT-TYPE
			SYNTAX	INTEGER
			ACCESS	read-only
			STATUS	current
	DESCRIPTION ""
			::= { mbusE3 63 }

mbusE3VIF1D		OBJECT-TYPE
			SYNTAX	INTEGER
			ACCESS	read-only
			STATUS	current
	DESCRIPTION ""
			::= { mbusE3 64 }

mbusE3Value1D		OBJECT-TYPE
			SYNTAX	INTEGER
			ACCESS	read-only
			STATUS	current
	DESCRIPTION ""
			::= { mbusE3 65 }

mbusE3VIF1E		OBJECT-TYPE
			SYNTAX	INTEGER
			ACCESS	read-only
			STATUS	current
	DESCRIPTION ""
			::= { mbusE3 66 }

mbusE3Value1E		OBJECT-TYPE
			SYNTAX	INTEGER
			ACCESS	read-only
			STATUS	current
	DESCRIPTION ""
			::= { mbusE3 67 }

mbusE3VIF1F		OBJECT-TYPE
			SYNTAX	INTEGER
			ACCESS	read-only
			STATUS	current
	DESCRIPTION ""
			::= { mbusE3 68 }

mbusE3Value1F		OBJECT-TYPE
			SYNTAX	INTEGER
			ACCESS	read-only
			STATUS	current
	DESCRIPTION ""
			::= { mbusE3 69 }

mbusE3VIF20		OBJECT-TYPE
			SYNTAX	INTEGER
			ACCESS	read-only
			STATUS	current
	DESCRIPTION ""
			::= { mbusE3 70 }

mbusE3Value20		OBJECT-TYPE
			SYNTAX	INTEGER
			ACCESS	read-only
			STATUS	current
	DESCRIPTION ""
			::= { mbusE3 71 }

mbusE3VIF21		OBJECT-TYPE
			SYNTAX	INTEGER
			ACCESS	read-only
			STATUS	current
	DESCRIPTION ""
			::= { mbusE3 72 }

mbusE3Value21		OBJECT-TYPE
			SYNTAX	INTEGER
			ACCESS	read-only
			STATUS	current
	DESCRIPTION ""
			::= { mbusE3 73 }

mbusE3VIF22		OBJECT-TYPE
			SYNTAX	INTEGER
			ACCESS	read-only
			STATUS	current
	DESCRIPTION ""
			::= { mbusE3 74 }

mbusE3Value22		OBJECT-TYPE
			SYNTAX	INTEGER
			ACCESS	read-only
			STATUS	current
	DESCRIPTION ""
			::= { mbusE3 75 }

mbusE3VIF23		OBJECT-TYPE
			SYNTAX	INTEGER
			ACCESS	read-only
			STATUS	current
	DESCRIPTION ""
			::= { mbusE3 76 }

mbusE3Value23		OBJECT-TYPE
			SYNTAX	INTEGER
			ACCESS	read-only
			STATUS	current
	DESCRIPTION ""
			::= { mbusE3 77 }

mbusE3VIF24		OBJECT-TYPE
			SYNTAX	INTEGER
			ACCESS	read-only
			STATUS	current
	DESCRIPTION ""
			::= { mbusE3 78 }

mbusE3Value24		OBJECT-TYPE
			SYNTAX	INTEGER
			ACCESS	read-only
			STATUS	current
	DESCRIPTION ""
			::= { mbusE3 79 }

mbusE3VIF25		OBJECT-TYPE
			SYNTAX	INTEGER
			ACCESS	read-only
			STATUS	current
	DESCRIPTION ""
			::= { mbusE3 80 }

mbusE3Value25		OBJECT-TYPE
			SYNTAX	INTEGER
			ACCESS	read-only
			STATUS	current
	DESCRIPTION ""
			::= { mbusE3 81 }

mbusE3VIF26		OBJECT-TYPE
			SYNTAX	INTEGER
			ACCESS	read-only
			STATUS	current
	DESCRIPTION ""
			::= { mbusE3 82 }

mbusE3Value26		OBJECT-TYPE
			SYNTAX	INTEGER
			ACCESS	read-only
			STATUS	current
	DESCRIPTION ""
			::= { mbusE3 83 }

mbusE3VIF27		OBJECT-TYPE
			SYNTAX	INTEGER
			ACCESS	read-only
			STATUS	current
	DESCRIPTION ""
			::= { mbusE3 84 }

mbusE3Value27		OBJECT-TYPE
			SYNTAX	INTEGER
			ACCESS	read-only
			STATUS	current
	DESCRIPTION ""
			::= { mbusE3 85 }

mbusE3VIF28		OBJECT-TYPE
			SYNTAX	INTEGER
			ACCESS	read-only
			STATUS	current
	DESCRIPTION ""
			::= { mbusE3 86 }

mbusE3Value28		OBJECT-TYPE
			SYNTAX	INTEGER
			ACCESS	read-only
			STATUS	current
	DESCRIPTION ""
			::= { mbusE3 87 }

mbusE3VIF29		OBJECT-TYPE
			SYNTAX	INTEGER
			ACCESS	read-only
			STATUS	current
	DESCRIPTION ""
			::= { mbusE3 88 }

mbusE3Value29		OBJECT-TYPE
			SYNTAX	INTEGER
			ACCESS	read-only
			STATUS	current
	DESCRIPTION ""
			::= { mbusE3 89 }

mbusE3VIF2A		OBJECT-TYPE
			SYNTAX	INTEGER
			ACCESS	read-only
			STATUS	current
	DESCRIPTION ""
			::= { mbusE3 90 }

mbusE3Value2A		OBJECT-TYPE
			SYNTAX	INTEGER
			ACCESS	read-only
			STATUS	current
	DESCRIPTION ""
			::= { mbusE3 91 }

mbusE3VIF2B		OBJECT-TYPE
			SYNTAX	INTEGER
			ACCESS	read-only
			STATUS	current
	DESCRIPTION ""
			::= { mbusE3 92 }

mbusE3Value2B		OBJECT-TYPE
			SYNTAX	INTEGER
			ACCESS	read-only
			STATUS	current
	DESCRIPTION ""
			::= { mbusE3 93 }

mbusE3VIF2C		OBJECT-TYPE
			SYNTAX	INTEGER
			ACCESS	read-only
			STATUS	current
	DESCRIPTION ""
			::= { mbusE3 94 }

mbusE3Value2C		OBJECT-TYPE
			SYNTAX	INTEGER
			ACCESS	read-only
			STATUS	current
	DESCRIPTION ""
			::= { mbusE3 95 }

mbusE3VIF2D		OBJECT-TYPE
			SYNTAX	INTEGER
			ACCESS	read-only
			STATUS	current
	DESCRIPTION ""
			::= { mbusE3 96 }

mbusE3Value2D		OBJECT-TYPE
			SYNTAX	INTEGER
			ACCESS	read-only
			STATUS	current
	DESCRIPTION ""
			::= { mbusE3 97 }

mbusE3VIF2E		OBJECT-TYPE
			SYNTAX	INTEGER
			ACCESS	read-only
			STATUS	current
	DESCRIPTION ""
			::= { mbusE3 98 }

mbusE3Value2E		OBJECT-TYPE
			SYNTAX	INTEGER
			ACCESS	read-only
			STATUS	current
	DESCRIPTION ""
			::= { mbusE3 99 }

mbusE3VIF2F		OBJECT-TYPE
			SYNTAX	INTEGER
			ACCESS	read-only
			STATUS	current
	DESCRIPTION ""
			::= { mbusE3 100 }

mbusE3Value2F		OBJECT-TYPE
			SYNTAX	INTEGER
			ACCESS	read-only
			STATUS	current
	DESCRIPTION ""
			::= { mbusE3 101 }

mbusE4			OBJECT IDENTIFIER ::= { mbus 228 }

mbusE4IdNumber		OBJECT-TYPE
			SYNTAX	Gauge
			ACCESS	read-only
			STATUS	current
	DESCRIPTION ""
			::= { mbusE4 1 }

mbusE4Manufacturer	OBJECT-TYPE
			SYNTAX	Gauge
			ACCESS	read-only
			STATUS	current
	DESCRIPTION ""
			::= { mbusE4 2 }

mbusE4Version		OBJECT-TYPE
			SYNTAX	Gauge
			ACCESS	read-only
			STATUS	current
	DESCRIPTION ""
			::= { mbusE4 3 }

mbusE4Medium		OBJECT-TYPE
			SYNTAX	Gauge
			ACCESS	read-only
			STATUS	current
	DESCRIPTION ""
			::= { mbusE4 4 }

mbusE4Status		OBJECT-TYPE
			SYNTAX	Gauge
			ACCESS	read-only
			STATUS	current
	DESCRIPTION ""
			::= { mbusE4 5 }

mbusE4VIF00		OBJECT-TYPE
			SYNTAX	INTEGER
			ACCESS	read-only
			STATUS	current
	DESCRIPTION ""
			::= { mbusE4 6 }

mbusE4Value00		OBJECT-TYPE
			SYNTAX	INTEGER
			ACCESS	read-only
			STATUS	current
	DESCRIPTION ""
			::= { mbusE4 7 }

mbusE4VIF01		OBJECT-TYPE
			SYNTAX	INTEGER
			ACCESS	read-only
			STATUS	current
	DESCRIPTION ""
			::= { mbusE4 8 }

mbusE4Value01		OBJECT-TYPE
			SYNTAX	INTEGER
			ACCESS	read-only
			STATUS	current
	DESCRIPTION ""
			::= { mbusE4 9 }

mbusE4VIF02		OBJECT-TYPE
			SYNTAX	INTEGER
			ACCESS	read-only
			STATUS	current
	DESCRIPTION ""
			::= { mbusE4 10 }

mbusE4Value02		OBJECT-TYPE
			SYNTAX	INTEGER
			ACCESS	read-only
			STATUS	current
	DESCRIPTION ""
			::= { mbusE4 11 }

mbusE4VIF03		OBJECT-TYPE
			SYNTAX	INTEGER
			ACCESS	read-only
			STATUS	current
	DESCRIPTION ""
			::= { mbusE4 12 }

mbusE4Value03		OBJECT-TYPE
			SYNTAX	INTEGER
			ACCESS	read-only
			STATUS	current
	DESCRIPTION ""
			::= { mbusE4 13 }

mbusE4VIF04		OBJECT-TYPE
			SYNTAX	INTEGER
			ACCESS	read-only
			STATUS	current
	DESCRIPTION ""
			::= { mbusE4 14 }

mbusE4Value04		OBJECT-TYPE
			SYNTAX	INTEGER
			ACCESS	read-only
			STATUS	current
	DESCRIPTION ""
			::= { mbusE4 15 }

mbusE4VIF05		OBJECT-TYPE
			SYNTAX	INTEGER
			ACCESS	read-only
			STATUS	current
	DESCRIPTION ""
			::= { mbusE4 16 }

mbusE4Value05		OBJECT-TYPE
			SYNTAX	INTEGER
			ACCESS	read-only
			STATUS	current
	DESCRIPTION ""
			::= { mbusE4 17 }

mbusE4VIF06		OBJECT-TYPE
			SYNTAX	INTEGER
			ACCESS	read-only
			STATUS	current
	DESCRIPTION ""
			::= { mbusE4 18 }

mbusE4Value06		OBJECT-TYPE
			SYNTAX	INTEGER
			ACCESS	read-only
			STATUS	current
	DESCRIPTION ""
			::= { mbusE4 19 }

mbusE4VIF07		OBJECT-TYPE
			SYNTAX	INTEGER
			ACCESS	read-only
			STATUS	current
	DESCRIPTION ""
			::= { mbusE4 20 }

mbusE4Value07		OBJECT-TYPE
			SYNTAX	INTEGER
			ACCESS	read-only
			STATUS	current
	DESCRIPTION ""
			::= { mbusE4 21 }

mbusE4VIF08		OBJECT-TYPE
			SYNTAX	INTEGER
			ACCESS	read-only
			STATUS	current
	DESCRIPTION ""
			::= { mbusE4 22 }

mbusE4Value08		OBJECT-TYPE
			SYNTAX	INTEGER
			ACCESS	read-only
			STATUS	current
	DESCRIPTION ""
			::= { mbusE4 23 }

mbusE4VIF09		OBJECT-TYPE
			SYNTAX	INTEGER
			ACCESS	read-only
			STATUS	current
	DESCRIPTION ""
			::= { mbusE4 24 }

mbusE4Value09		OBJECT-TYPE
			SYNTAX	INTEGER
			ACCESS	read-only
			STATUS	current
	DESCRIPTION ""
			::= { mbusE4 25 }

mbusE4VIF0A		OBJECT-TYPE
			SYNTAX	INTEGER
			ACCESS	read-only
			STATUS	current
	DESCRIPTION ""
			::= { mbusE4 26 }

mbusE4Value0A		OBJECT-TYPE
			SYNTAX	INTEGER
			ACCESS	read-only
			STATUS	current
	DESCRIPTION ""
			::= { mbusE4 27 }

mbusE4VIF0B		OBJECT-TYPE
			SYNTAX	INTEGER
			ACCESS	read-only
			STATUS	current
	DESCRIPTION ""
			::= { mbusE4 28 }

mbusE4Value0B		OBJECT-TYPE
			SYNTAX	INTEGER
			ACCESS	read-only
			STATUS	current
	DESCRIPTION ""
			::= { mbusE4 29 }

mbusE4VIF0C		OBJECT-TYPE
			SYNTAX	INTEGER
			ACCESS	read-only
			STATUS	current
	DESCRIPTION ""
			::= { mbusE4 30 }

mbusE4Value0C		OBJECT-TYPE
			SYNTAX	INTEGER
			ACCESS	read-only
			STATUS	current
	DESCRIPTION ""
			::= { mbusE4 31 }

mbusE4VIF0D		OBJECT-TYPE
			SYNTAX	INTEGER
			ACCESS	read-only
			STATUS	current
	DESCRIPTION ""
			::= { mbusE4 32 }

mbusE4Value0D		OBJECT-TYPE
			SYNTAX	INTEGER
			ACCESS	read-only
			STATUS	current
	DESCRIPTION ""
			::= { mbusE4 33 }

mbusE4VIF0E		OBJECT-TYPE
			SYNTAX	INTEGER
			ACCESS	read-only
			STATUS	current
	DESCRIPTION ""
			::= { mbusE4 34 }

mbusE4Value0E		OBJECT-TYPE
			SYNTAX	INTEGER
			ACCESS	read-only
			STATUS	current
	DESCRIPTION ""
			::= { mbusE4 35 }

mbusE4VIF0F		OBJECT-TYPE
			SYNTAX	INTEGER
			ACCESS	read-only
			STATUS	current
	DESCRIPTION ""
			::= { mbusE4 36 }

mbusE4Value0F		OBJECT-TYPE
			SYNTAX	INTEGER
			ACCESS	read-only
			STATUS	current
	DESCRIPTION ""
			::= { mbusE4 37 }

mbusE4VIF10		OBJECT-TYPE
			SYNTAX	INTEGER
			ACCESS	read-only
			STATUS	current
	DESCRIPTION ""
			::= { mbusE4 38 }

mbusE4Value10		OBJECT-TYPE
			SYNTAX	INTEGER
			ACCESS	read-only
			STATUS	current
	DESCRIPTION ""
			::= { mbusE4 39 }

mbusE4VIF11		OBJECT-TYPE
			SYNTAX	INTEGER
			ACCESS	read-only
			STATUS	current
	DESCRIPTION ""
			::= { mbusE4 40 }

mbusE4Value11		OBJECT-TYPE
			SYNTAX	INTEGER
			ACCESS	read-only
			STATUS	current
	DESCRIPTION ""
			::= { mbusE4 41 }

mbusE4VIF12		OBJECT-TYPE
			SYNTAX	INTEGER
			ACCESS	read-only
			STATUS	current
	DESCRIPTION ""
			::= { mbusE4 42 }

mbusE4Value12		OBJECT-TYPE
			SYNTAX	INTEGER
			ACCESS	read-only
			STATUS	current
	DESCRIPTION ""
			::= { mbusE4 43 }

mbusE4VIF13		OBJECT-TYPE
			SYNTAX	INTEGER
			ACCESS	read-only
			STATUS	current
	DESCRIPTION ""
			::= { mbusE4 44 }

mbusE4Value13		OBJECT-TYPE
			SYNTAX	INTEGER
			ACCESS	read-only
			STATUS	current
	DESCRIPTION ""
			::= { mbusE4 45 }

mbusE4VIF14		OBJECT-TYPE
			SYNTAX	INTEGER
			ACCESS	read-only
			STATUS	current
	DESCRIPTION ""
			::= { mbusE4 46 }

mbusE4Value14		OBJECT-TYPE
			SYNTAX	INTEGER
			ACCESS	read-only
			STATUS	current
	DESCRIPTION ""
			::= { mbusE4 47 }

mbusE4VIF15		OBJECT-TYPE
			SYNTAX	INTEGER
			ACCESS	read-only
			STATUS	current
	DESCRIPTION ""
			::= { mbusE4 48 }

mbusE4Value15		OBJECT-TYPE
			SYNTAX	INTEGER
			ACCESS	read-only
			STATUS	current
	DESCRIPTION ""
			::= { mbusE4 49 }

mbusE4VIF16		OBJECT-TYPE
			SYNTAX	INTEGER
			ACCESS	read-only
			STATUS	current
	DESCRIPTION ""
			::= { mbusE4 50 }

mbusE4Value16		OBJECT-TYPE
			SYNTAX	INTEGER
			ACCESS	read-only
			STATUS	current
	DESCRIPTION ""
			::= { mbusE4 51 }

mbusE4VIF17		OBJECT-TYPE
			SYNTAX	INTEGER
			ACCESS	read-only
			STATUS	current
	DESCRIPTION ""
			::= { mbusE4 52 }

mbusE4Value17		OBJECT-TYPE
			SYNTAX	INTEGER
			ACCESS	read-only
			STATUS	current
	DESCRIPTION ""
			::= { mbusE4 53 }

mbusE4VIF18		OBJECT-TYPE
			SYNTAX	INTEGER
			ACCESS	read-only
			STATUS	current
	DESCRIPTION ""
			::= { mbusE4 54 }

mbusE4Value18		OBJECT-TYPE
			SYNTAX	INTEGER
			ACCESS	read-only
			STATUS	current
	DESCRIPTION ""
			::= { mbusE4 55 }

mbusE4VIF19		OBJECT-TYPE
			SYNTAX	INTEGER
			ACCESS	read-only
			STATUS	current
	DESCRIPTION ""
			::= { mbusE4 56 }

mbusE4Value19		OBJECT-TYPE
			SYNTAX	INTEGER
			ACCESS	read-only
			STATUS	current
	DESCRIPTION ""
			::= { mbusE4 57 }

mbusE4VIF1A		OBJECT-TYPE
			SYNTAX	INTEGER
			ACCESS	read-only
			STATUS	current
	DESCRIPTION ""
			::= { mbusE4 58 }

mbusE4Value1A		OBJECT-TYPE
			SYNTAX	INTEGER
			ACCESS	read-only
			STATUS	current
	DESCRIPTION ""
			::= { mbusE4 59 }

mbusE4VIF1B		OBJECT-TYPE
			SYNTAX	INTEGER
			ACCESS	read-only
			STATUS	current
	DESCRIPTION ""
			::= { mbusE4 60 }

mbusE4Value1B		OBJECT-TYPE
			SYNTAX	INTEGER
			ACCESS	read-only
			STATUS	current
	DESCRIPTION ""
			::= { mbusE4 61 }

mbusE4VIF1C		OBJECT-TYPE
			SYNTAX	INTEGER
			ACCESS	read-only
			STATUS	current
	DESCRIPTION ""
			::= { mbusE4 62 }

mbusE4Value1C		OBJECT-TYPE
			SYNTAX	INTEGER
			ACCESS	read-only
			STATUS	current
	DESCRIPTION ""
			::= { mbusE4 63 }

mbusE4VIF1D		OBJECT-TYPE
			SYNTAX	INTEGER
			ACCESS	read-only
			STATUS	current
	DESCRIPTION ""
			::= { mbusE4 64 }

mbusE4Value1D		OBJECT-TYPE
			SYNTAX	INTEGER
			ACCESS	read-only
			STATUS	current
	DESCRIPTION ""
			::= { mbusE4 65 }

mbusE4VIF1E		OBJECT-TYPE
			SYNTAX	INTEGER
			ACCESS	read-only
			STATUS	current
	DESCRIPTION ""
			::= { mbusE4 66 }

mbusE4Value1E		OBJECT-TYPE
			SYNTAX	INTEGER
			ACCESS	read-only
			STATUS	current
	DESCRIPTION ""
			::= { mbusE4 67 }

mbusE4VIF1F		OBJECT-TYPE
			SYNTAX	INTEGER
			ACCESS	read-only
			STATUS	current
	DESCRIPTION ""
			::= { mbusE4 68 }

mbusE4Value1F		OBJECT-TYPE
			SYNTAX	INTEGER
			ACCESS	read-only
			STATUS	current
	DESCRIPTION ""
			::= { mbusE4 69 }

mbusE4VIF20		OBJECT-TYPE
			SYNTAX	INTEGER
			ACCESS	read-only
			STATUS	current
	DESCRIPTION ""
			::= { mbusE4 70 }

mbusE4Value20		OBJECT-TYPE
			SYNTAX	INTEGER
			ACCESS	read-only
			STATUS	current
	DESCRIPTION ""
			::= { mbusE4 71 }

mbusE4VIF21		OBJECT-TYPE
			SYNTAX	INTEGER
			ACCESS	read-only
			STATUS	current
	DESCRIPTION ""
			::= { mbusE4 72 }

mbusE4Value21		OBJECT-TYPE
			SYNTAX	INTEGER
			ACCESS	read-only
			STATUS	current
	DESCRIPTION ""
			::= { mbusE4 73 }

mbusE4VIF22		OBJECT-TYPE
			SYNTAX	INTEGER
			ACCESS	read-only
			STATUS	current
	DESCRIPTION ""
			::= { mbusE4 74 }

mbusE4Value22		OBJECT-TYPE
			SYNTAX	INTEGER
			ACCESS	read-only
			STATUS	current
	DESCRIPTION ""
			::= { mbusE4 75 }

mbusE4VIF23		OBJECT-TYPE
			SYNTAX	INTEGER
			ACCESS	read-only
			STATUS	current
	DESCRIPTION ""
			::= { mbusE4 76 }

mbusE4Value23		OBJECT-TYPE
			SYNTAX	INTEGER
			ACCESS	read-only
			STATUS	current
	DESCRIPTION ""
			::= { mbusE4 77 }

mbusE4VIF24		OBJECT-TYPE
			SYNTAX	INTEGER
			ACCESS	read-only
			STATUS	current
	DESCRIPTION ""
			::= { mbusE4 78 }

mbusE4Value24		OBJECT-TYPE
			SYNTAX	INTEGER
			ACCESS	read-only
			STATUS	current
	DESCRIPTION ""
			::= { mbusE4 79 }

mbusE4VIF25		OBJECT-TYPE
			SYNTAX	INTEGER
			ACCESS	read-only
			STATUS	current
	DESCRIPTION ""
			::= { mbusE4 80 }

mbusE4Value25		OBJECT-TYPE
			SYNTAX	INTEGER
			ACCESS	read-only
			STATUS	current
	DESCRIPTION ""
			::= { mbusE4 81 }

mbusE4VIF26		OBJECT-TYPE
			SYNTAX	INTEGER
			ACCESS	read-only
			STATUS	current
	DESCRIPTION ""
			::= { mbusE4 82 }

mbusE4Value26		OBJECT-TYPE
			SYNTAX	INTEGER
			ACCESS	read-only
			STATUS	current
	DESCRIPTION ""
			::= { mbusE4 83 }

mbusE4VIF27		OBJECT-TYPE
			SYNTAX	INTEGER
			ACCESS	read-only
			STATUS	current
	DESCRIPTION ""
			::= { mbusE4 84 }

mbusE4Value27		OBJECT-TYPE
			SYNTAX	INTEGER
			ACCESS	read-only
			STATUS	current
	DESCRIPTION ""
			::= { mbusE4 85 }

mbusE4VIF28		OBJECT-TYPE
			SYNTAX	INTEGER
			ACCESS	read-only
			STATUS	current
	DESCRIPTION ""
			::= { mbusE4 86 }

mbusE4Value28		OBJECT-TYPE
			SYNTAX	INTEGER
			ACCESS	read-only
			STATUS	current
	DESCRIPTION ""
			::= { mbusE4 87 }

mbusE4VIF29		OBJECT-TYPE
			SYNTAX	INTEGER
			ACCESS	read-only
			STATUS	current
	DESCRIPTION ""
			::= { mbusE4 88 }

mbusE4Value29		OBJECT-TYPE
			SYNTAX	INTEGER
			ACCESS	read-only
			STATUS	current
	DESCRIPTION ""
			::= { mbusE4 89 }

mbusE4VIF2A		OBJECT-TYPE
			SYNTAX	INTEGER
			ACCESS	read-only
			STATUS	current
	DESCRIPTION ""
			::= { mbusE4 90 }

mbusE4Value2A		OBJECT-TYPE
			SYNTAX	INTEGER
			ACCESS	read-only
			STATUS	current
	DESCRIPTION ""
			::= { mbusE4 91 }

mbusE4VIF2B		OBJECT-TYPE
			SYNTAX	INTEGER
			ACCESS	read-only
			STATUS	current
	DESCRIPTION ""
			::= { mbusE4 92 }

mbusE4Value2B		OBJECT-TYPE
			SYNTAX	INTEGER
			ACCESS	read-only
			STATUS	current
	DESCRIPTION ""
			::= { mbusE4 93 }

mbusE4VIF2C		OBJECT-TYPE
			SYNTAX	INTEGER
			ACCESS	read-only
			STATUS	current
	DESCRIPTION ""
			::= { mbusE4 94 }

mbusE4Value2C		OBJECT-TYPE
			SYNTAX	INTEGER
			ACCESS	read-only
			STATUS	current
	DESCRIPTION ""
			::= { mbusE4 95 }

mbusE4VIF2D		OBJECT-TYPE
			SYNTAX	INTEGER
			ACCESS	read-only
			STATUS	current
	DESCRIPTION ""
			::= { mbusE4 96 }

mbusE4Value2D		OBJECT-TYPE
			SYNTAX	INTEGER
			ACCESS	read-only
			STATUS	current
	DESCRIPTION ""
			::= { mbusE4 97 }

mbusE4VIF2E		OBJECT-TYPE
			SYNTAX	INTEGER
			ACCESS	read-only
			STATUS	current
	DESCRIPTION ""
			::= { mbusE4 98 }

mbusE4Value2E		OBJECT-TYPE
			SYNTAX	INTEGER
			ACCESS	read-only
			STATUS	current
	DESCRIPTION ""
			::= { mbusE4 99 }

mbusE4VIF2F		OBJECT-TYPE
			SYNTAX	INTEGER
			ACCESS	read-only
			STATUS	current
	DESCRIPTION ""
			::= { mbusE4 100 }

mbusE4Value2F		OBJECT-TYPE
			SYNTAX	INTEGER
			ACCESS	read-only
			STATUS	current
	DESCRIPTION ""
			::= { mbusE4 101 }

mbusE5			OBJECT IDENTIFIER ::= { mbus 229 }

mbusE5IdNumber		OBJECT-TYPE
			SYNTAX	Gauge
			ACCESS	read-only
			STATUS	current
	DESCRIPTION ""
			::= { mbusE5 1 }

mbusE5Manufacturer	OBJECT-TYPE
			SYNTAX	Gauge
			ACCESS	read-only
			STATUS	current
	DESCRIPTION ""
			::= { mbusE5 2 }

mbusE5Version		OBJECT-TYPE
			SYNTAX	Gauge
			ACCESS	read-only
			STATUS	current
	DESCRIPTION ""
			::= { mbusE5 3 }

mbusE5Medium		OBJECT-TYPE
			SYNTAX	Gauge
			ACCESS	read-only
			STATUS	current
	DESCRIPTION ""
			::= { mbusE5 4 }

mbusE5Status		OBJECT-TYPE
			SYNTAX	Gauge
			ACCESS	read-only
			STATUS	current
	DESCRIPTION ""
			::= { mbusE5 5 }

mbusE5VIF00		OBJECT-TYPE
			SYNTAX	INTEGER
			ACCESS	read-only
			STATUS	current
	DESCRIPTION ""
			::= { mbusE5 6 }

mbusE5Value00		OBJECT-TYPE
			SYNTAX	INTEGER
			ACCESS	read-only
			STATUS	current
	DESCRIPTION ""
			::= { mbusE5 7 }

mbusE5VIF01		OBJECT-TYPE
			SYNTAX	INTEGER
			ACCESS	read-only
			STATUS	current
	DESCRIPTION ""
			::= { mbusE5 8 }

mbusE5Value01		OBJECT-TYPE
			SYNTAX	INTEGER
			ACCESS	read-only
			STATUS	current
	DESCRIPTION ""
			::= { mbusE5 9 }

mbusE5VIF02		OBJECT-TYPE
			SYNTAX	INTEGER
			ACCESS	read-only
			STATUS	current
	DESCRIPTION ""
			::= { mbusE5 10 }

mbusE5Value02		OBJECT-TYPE
			SYNTAX	INTEGER
			ACCESS	read-only
			STATUS	current
	DESCRIPTION ""
			::= { mbusE5 11 }

mbusE5VIF03		OBJECT-TYPE
			SYNTAX	INTEGER
			ACCESS	read-only
			STATUS	current
	DESCRIPTION ""
			::= { mbusE5 12 }

mbusE5Value03		OBJECT-TYPE
			SYNTAX	INTEGER
			ACCESS	read-only
			STATUS	current
	DESCRIPTION ""
			::= { mbusE5 13 }

mbusE5VIF04		OBJECT-TYPE
			SYNTAX	INTEGER
			ACCESS	read-only
			STATUS	current
	DESCRIPTION ""
			::= { mbusE5 14 }

mbusE5Value04		OBJECT-TYPE
			SYNTAX	INTEGER
			ACCESS	read-only
			STATUS	current
	DESCRIPTION ""
			::= { mbusE5 15 }

mbusE5VIF05		OBJECT-TYPE
			SYNTAX	INTEGER
			ACCESS	read-only
			STATUS	current
	DESCRIPTION ""
			::= { mbusE5 16 }

mbusE5Value05		OBJECT-TYPE
			SYNTAX	INTEGER
			ACCESS	read-only
			STATUS	current
	DESCRIPTION ""
			::= { mbusE5 17 }

mbusE5VIF06		OBJECT-TYPE
			SYNTAX	INTEGER
			ACCESS	read-only
			STATUS	current
	DESCRIPTION ""
			::= { mbusE5 18 }

mbusE5Value06		OBJECT-TYPE
			SYNTAX	INTEGER
			ACCESS	read-only
			STATUS	current
	DESCRIPTION ""
			::= { mbusE5 19 }

mbusE5VIF07		OBJECT-TYPE
			SYNTAX	INTEGER
			ACCESS	read-only
			STATUS	current
	DESCRIPTION ""
			::= { mbusE5 20 }

mbusE5Value07		OBJECT-TYPE
			SYNTAX	INTEGER
			ACCESS	read-only
			STATUS	current
	DESCRIPTION ""
			::= { mbusE5 21 }

mbusE5VIF08		OBJECT-TYPE
			SYNTAX	INTEGER
			ACCESS	read-only
			STATUS	current
	DESCRIPTION ""
			::= { mbusE5 22 }

mbusE5Value08		OBJECT-TYPE
			SYNTAX	INTEGER
			ACCESS	read-only
			STATUS	current
	DESCRIPTION ""
			::= { mbusE5 23 }

mbusE5VIF09		OBJECT-TYPE
			SYNTAX	INTEGER
			ACCESS	read-only
			STATUS	current
	DESCRIPTION ""
			::= { mbusE5 24 }

mbusE5Value09		OBJECT-TYPE
			SYNTAX	INTEGER
			ACCESS	read-only
			STATUS	current
	DESCRIPTION ""
			::= { mbusE5 25 }

mbusE5VIF0A		OBJECT-TYPE
			SYNTAX	INTEGER
			ACCESS	read-only
			STATUS	current
	DESCRIPTION ""
			::= { mbusE5 26 }

mbusE5Value0A		OBJECT-TYPE
			SYNTAX	INTEGER
			ACCESS	read-only
			STATUS	current
	DESCRIPTION ""
			::= { mbusE5 27 }

mbusE5VIF0B		OBJECT-TYPE
			SYNTAX	INTEGER
			ACCESS	read-only
			STATUS	current
	DESCRIPTION ""
			::= { mbusE5 28 }

mbusE5Value0B		OBJECT-TYPE
			SYNTAX	INTEGER
			ACCESS	read-only
			STATUS	current
	DESCRIPTION ""
			::= { mbusE5 29 }

mbusE5VIF0C		OBJECT-TYPE
			SYNTAX	INTEGER
			ACCESS	read-only
			STATUS	current
	DESCRIPTION ""
			::= { mbusE5 30 }

mbusE5Value0C		OBJECT-TYPE
			SYNTAX	INTEGER
			ACCESS	read-only
			STATUS	current
	DESCRIPTION ""
			::= { mbusE5 31 }

mbusE5VIF0D		OBJECT-TYPE
			SYNTAX	INTEGER
			ACCESS	read-only
			STATUS	current
	DESCRIPTION ""
			::= { mbusE5 32 }

mbusE5Value0D		OBJECT-TYPE
			SYNTAX	INTEGER
			ACCESS	read-only
			STATUS	current
	DESCRIPTION ""
			::= { mbusE5 33 }

mbusE5VIF0E		OBJECT-TYPE
			SYNTAX	INTEGER
			ACCESS	read-only
			STATUS	current
	DESCRIPTION ""
			::= { mbusE5 34 }

mbusE5Value0E		OBJECT-TYPE
			SYNTAX	INTEGER
			ACCESS	read-only
			STATUS	current
	DESCRIPTION ""
			::= { mbusE5 35 }

mbusE5VIF0F		OBJECT-TYPE
			SYNTAX	INTEGER
			ACCESS	read-only
			STATUS	current
	DESCRIPTION ""
			::= { mbusE5 36 }

mbusE5Value0F		OBJECT-TYPE
			SYNTAX	INTEGER
			ACCESS	read-only
			STATUS	current
	DESCRIPTION ""
			::= { mbusE5 37 }

mbusE5VIF10		OBJECT-TYPE
			SYNTAX	INTEGER
			ACCESS	read-only
			STATUS	current
	DESCRIPTION ""
			::= { mbusE5 38 }

mbusE5Value10		OBJECT-TYPE
			SYNTAX	INTEGER
			ACCESS	read-only
			STATUS	current
	DESCRIPTION ""
			::= { mbusE5 39 }

mbusE5VIF11		OBJECT-TYPE
			SYNTAX	INTEGER
			ACCESS	read-only
			STATUS	current
	DESCRIPTION ""
			::= { mbusE5 40 }

mbusE5Value11		OBJECT-TYPE
			SYNTAX	INTEGER
			ACCESS	read-only
			STATUS	current
	DESCRIPTION ""
			::= { mbusE5 41 }

mbusE5VIF12		OBJECT-TYPE
			SYNTAX	INTEGER
			ACCESS	read-only
			STATUS	current
	DESCRIPTION ""
			::= { mbusE5 42 }

mbusE5Value12		OBJECT-TYPE
			SYNTAX	INTEGER
			ACCESS	read-only
			STATUS	current
	DESCRIPTION ""
			::= { mbusE5 43 }

mbusE5VIF13		OBJECT-TYPE
			SYNTAX	INTEGER
			ACCESS	read-only
			STATUS	current
	DESCRIPTION ""
			::= { mbusE5 44 }

mbusE5Value13		OBJECT-TYPE
			SYNTAX	INTEGER
			ACCESS	read-only
			STATUS	current
	DESCRIPTION ""
			::= { mbusE5 45 }

mbusE5VIF14		OBJECT-TYPE
			SYNTAX	INTEGER
			ACCESS	read-only
			STATUS	current
	DESCRIPTION ""
			::= { mbusE5 46 }

mbusE5Value14		OBJECT-TYPE
			SYNTAX	INTEGER
			ACCESS	read-only
			STATUS	current
	DESCRIPTION ""
			::= { mbusE5 47 }

mbusE5VIF15		OBJECT-TYPE
			SYNTAX	INTEGER
			ACCESS	read-only
			STATUS	current
	DESCRIPTION ""
			::= { mbusE5 48 }

mbusE5Value15		OBJECT-TYPE
			SYNTAX	INTEGER
			ACCESS	read-only
			STATUS	current
	DESCRIPTION ""
			::= { mbusE5 49 }

mbusE5VIF16		OBJECT-TYPE
			SYNTAX	INTEGER
			ACCESS	read-only
			STATUS	current
	DESCRIPTION ""
			::= { mbusE5 50 }

mbusE5Value16		OBJECT-TYPE
			SYNTAX	INTEGER
			ACCESS	read-only
			STATUS	current
	DESCRIPTION ""
			::= { mbusE5 51 }

mbusE5VIF17		OBJECT-TYPE
			SYNTAX	INTEGER
			ACCESS	read-only
			STATUS	current
	DESCRIPTION ""
			::= { mbusE5 52 }

mbusE5Value17		OBJECT-TYPE
			SYNTAX	INTEGER
			ACCESS	read-only
			STATUS	current
	DESCRIPTION ""
			::= { mbusE5 53 }

mbusE5VIF18		OBJECT-TYPE
			SYNTAX	INTEGER
			ACCESS	read-only
			STATUS	current
	DESCRIPTION ""
			::= { mbusE5 54 }

mbusE5Value18		OBJECT-TYPE
			SYNTAX	INTEGER
			ACCESS	read-only
			STATUS	current
	DESCRIPTION ""
			::= { mbusE5 55 }

mbusE5VIF19		OBJECT-TYPE
			SYNTAX	INTEGER
			ACCESS	read-only
			STATUS	current
	DESCRIPTION ""
			::= { mbusE5 56 }

mbusE5Value19		OBJECT-TYPE
			SYNTAX	INTEGER
			ACCESS	read-only
			STATUS	current
	DESCRIPTION ""
			::= { mbusE5 57 }

mbusE5VIF1A		OBJECT-TYPE
			SYNTAX	INTEGER
			ACCESS	read-only
			STATUS	current
	DESCRIPTION ""
			::= { mbusE5 58 }

mbusE5Value1A		OBJECT-TYPE
			SYNTAX	INTEGER
			ACCESS	read-only
			STATUS	current
	DESCRIPTION ""
			::= { mbusE5 59 }

mbusE5VIF1B		OBJECT-TYPE
			SYNTAX	INTEGER
			ACCESS	read-only
			STATUS	current
	DESCRIPTION ""
			::= { mbusE5 60 }

mbusE5Value1B		OBJECT-TYPE
			SYNTAX	INTEGER
			ACCESS	read-only
			STATUS	current
	DESCRIPTION ""
			::= { mbusE5 61 }

mbusE5VIF1C		OBJECT-TYPE
			SYNTAX	INTEGER
			ACCESS	read-only
			STATUS	current
	DESCRIPTION ""
			::= { mbusE5 62 }

mbusE5Value1C		OBJECT-TYPE
			SYNTAX	INTEGER
			ACCESS	read-only
			STATUS	current
	DESCRIPTION ""
			::= { mbusE5 63 }

mbusE5VIF1D		OBJECT-TYPE
			SYNTAX	INTEGER
			ACCESS	read-only
			STATUS	current
	DESCRIPTION ""
			::= { mbusE5 64 }

mbusE5Value1D		OBJECT-TYPE
			SYNTAX	INTEGER
			ACCESS	read-only
			STATUS	current
	DESCRIPTION ""
			::= { mbusE5 65 }

mbusE5VIF1E		OBJECT-TYPE
			SYNTAX	INTEGER
			ACCESS	read-only
			STATUS	current
	DESCRIPTION ""
			::= { mbusE5 66 }

mbusE5Value1E		OBJECT-TYPE
			SYNTAX	INTEGER
			ACCESS	read-only
			STATUS	current
	DESCRIPTION ""
			::= { mbusE5 67 }

mbusE5VIF1F		OBJECT-TYPE
			SYNTAX	INTEGER
			ACCESS	read-only
			STATUS	current
	DESCRIPTION ""
			::= { mbusE5 68 }

mbusE5Value1F		OBJECT-TYPE
			SYNTAX	INTEGER
			ACCESS	read-only
			STATUS	current
	DESCRIPTION ""
			::= { mbusE5 69 }

mbusE5VIF20		OBJECT-TYPE
			SYNTAX	INTEGER
			ACCESS	read-only
			STATUS	current
	DESCRIPTION ""
			::= { mbusE5 70 }

mbusE5Value20		OBJECT-TYPE
			SYNTAX	INTEGER
			ACCESS	read-only
			STATUS	current
	DESCRIPTION ""
			::= { mbusE5 71 }

mbusE5VIF21		OBJECT-TYPE
			SYNTAX	INTEGER
			ACCESS	read-only
			STATUS	current
	DESCRIPTION ""
			::= { mbusE5 72 }

mbusE5Value21		OBJECT-TYPE
			SYNTAX	INTEGER
			ACCESS	read-only
			STATUS	current
	DESCRIPTION ""
			::= { mbusE5 73 }

mbusE5VIF22		OBJECT-TYPE
			SYNTAX	INTEGER
			ACCESS	read-only
			STATUS	current
	DESCRIPTION ""
			::= { mbusE5 74 }

mbusE5Value22		OBJECT-TYPE
			SYNTAX	INTEGER
			ACCESS	read-only
			STATUS	current
	DESCRIPTION ""
			::= { mbusE5 75 }

mbusE5VIF23		OBJECT-TYPE
			SYNTAX	INTEGER
			ACCESS	read-only
			STATUS	current
	DESCRIPTION ""
			::= { mbusE5 76 }

mbusE5Value23		OBJECT-TYPE
			SYNTAX	INTEGER
			ACCESS	read-only
			STATUS	current
	DESCRIPTION ""
			::= { mbusE5 77 }

mbusE5VIF24		OBJECT-TYPE
			SYNTAX	INTEGER
			ACCESS	read-only
			STATUS	current
	DESCRIPTION ""
			::= { mbusE5 78 }

mbusE5Value24		OBJECT-TYPE
			SYNTAX	INTEGER
			ACCESS	read-only
			STATUS	current
	DESCRIPTION ""
			::= { mbusE5 79 }

mbusE5VIF25		OBJECT-TYPE
			SYNTAX	INTEGER
			ACCESS	read-only
			STATUS	current
	DESCRIPTION ""
			::= { mbusE5 80 }

mbusE5Value25		OBJECT-TYPE
			SYNTAX	INTEGER
			ACCESS	read-only
			STATUS	current
	DESCRIPTION ""
			::= { mbusE5 81 }

mbusE5VIF26		OBJECT-TYPE
			SYNTAX	INTEGER
			ACCESS	read-only
			STATUS	current
	DESCRIPTION ""
			::= { mbusE5 82 }

mbusE5Value26		OBJECT-TYPE
			SYNTAX	INTEGER
			ACCESS	read-only
			STATUS	current
	DESCRIPTION ""
			::= { mbusE5 83 }

mbusE5VIF27		OBJECT-TYPE
			SYNTAX	INTEGER
			ACCESS	read-only
			STATUS	current
	DESCRIPTION ""
			::= { mbusE5 84 }

mbusE5Value27		OBJECT-TYPE
			SYNTAX	INTEGER
			ACCESS	read-only
			STATUS	current
	DESCRIPTION ""
			::= { mbusE5 85 }

mbusE5VIF28		OBJECT-TYPE
			SYNTAX	INTEGER
			ACCESS	read-only
			STATUS	current
	DESCRIPTION ""
			::= { mbusE5 86 }

mbusE5Value28		OBJECT-TYPE
			SYNTAX	INTEGER
			ACCESS	read-only
			STATUS	current
	DESCRIPTION ""
			::= { mbusE5 87 }

mbusE5VIF29		OBJECT-TYPE
			SYNTAX	INTEGER
			ACCESS	read-only
			STATUS	current
	DESCRIPTION ""
			::= { mbusE5 88 }

mbusE5Value29		OBJECT-TYPE
			SYNTAX	INTEGER
			ACCESS	read-only
			STATUS	current
	DESCRIPTION ""
			::= { mbusE5 89 }

mbusE5VIF2A		OBJECT-TYPE
			SYNTAX	INTEGER
			ACCESS	read-only
			STATUS	current
	DESCRIPTION ""
			::= { mbusE5 90 }

mbusE5Value2A		OBJECT-TYPE
			SYNTAX	INTEGER
			ACCESS	read-only
			STATUS	current
	DESCRIPTION ""
			::= { mbusE5 91 }

mbusE5VIF2B		OBJECT-TYPE
			SYNTAX	INTEGER
			ACCESS	read-only
			STATUS	current
	DESCRIPTION ""
			::= { mbusE5 92 }

mbusE5Value2B		OBJECT-TYPE
			SYNTAX	INTEGER
			ACCESS	read-only
			STATUS	current
	DESCRIPTION ""
			::= { mbusE5 93 }

mbusE5VIF2C		OBJECT-TYPE
			SYNTAX	INTEGER
			ACCESS	read-only
			STATUS	current
	DESCRIPTION ""
			::= { mbusE5 94 }

mbusE5Value2C		OBJECT-TYPE
			SYNTAX	INTEGER
			ACCESS	read-only
			STATUS	current
	DESCRIPTION ""
			::= { mbusE5 95 }

mbusE5VIF2D		OBJECT-TYPE
			SYNTAX	INTEGER
			ACCESS	read-only
			STATUS	current
	DESCRIPTION ""
			::= { mbusE5 96 }

mbusE5Value2D		OBJECT-TYPE
			SYNTAX	INTEGER
			ACCESS	read-only
			STATUS	current
	DESCRIPTION ""
			::= { mbusE5 97 }

mbusE5VIF2E		OBJECT-TYPE
			SYNTAX	INTEGER
			ACCESS	read-only
			STATUS	current
	DESCRIPTION ""
			::= { mbusE5 98 }

mbusE5Value2E		OBJECT-TYPE
			SYNTAX	INTEGER
			ACCESS	read-only
			STATUS	current
	DESCRIPTION ""
			::= { mbusE5 99 }

mbusE5VIF2F		OBJECT-TYPE
			SYNTAX	INTEGER
			ACCESS	read-only
			STATUS	current
	DESCRIPTION ""
			::= { mbusE5 100 }

mbusE5Value2F		OBJECT-TYPE
			SYNTAX	INTEGER
			ACCESS	read-only
			STATUS	current
	DESCRIPTION ""
			::= { mbusE5 101 }

mbusE6			OBJECT IDENTIFIER ::= { mbus 230 }

mbusE6IdNumber		OBJECT-TYPE
			SYNTAX	Gauge
			ACCESS	read-only
			STATUS	current
	DESCRIPTION ""
			::= { mbusE6 1 }

mbusE6Manufacturer	OBJECT-TYPE
			SYNTAX	Gauge
			ACCESS	read-only
			STATUS	current
	DESCRIPTION ""
			::= { mbusE6 2 }

mbusE6Version		OBJECT-TYPE
			SYNTAX	Gauge
			ACCESS	read-only
			STATUS	current
	DESCRIPTION ""
			::= { mbusE6 3 }

mbusE6Medium		OBJECT-TYPE
			SYNTAX	Gauge
			ACCESS	read-only
			STATUS	current
	DESCRIPTION ""
			::= { mbusE6 4 }

mbusE6Status		OBJECT-TYPE
			SYNTAX	Gauge
			ACCESS	read-only
			STATUS	current
	DESCRIPTION ""
			::= { mbusE6 5 }

mbusE6VIF00		OBJECT-TYPE
			SYNTAX	INTEGER
			ACCESS	read-only
			STATUS	current
	DESCRIPTION ""
			::= { mbusE6 6 }

mbusE6Value00		OBJECT-TYPE
			SYNTAX	INTEGER
			ACCESS	read-only
			STATUS	current
	DESCRIPTION ""
			::= { mbusE6 7 }

mbusE6VIF01		OBJECT-TYPE
			SYNTAX	INTEGER
			ACCESS	read-only
			STATUS	current
	DESCRIPTION ""
			::= { mbusE6 8 }

mbusE6Value01		OBJECT-TYPE
			SYNTAX	INTEGER
			ACCESS	read-only
			STATUS	current
	DESCRIPTION ""
			::= { mbusE6 9 }

mbusE6VIF02		OBJECT-TYPE
			SYNTAX	INTEGER
			ACCESS	read-only
			STATUS	current
	DESCRIPTION ""
			::= { mbusE6 10 }

mbusE6Value02		OBJECT-TYPE
			SYNTAX	INTEGER
			ACCESS	read-only
			STATUS	current
	DESCRIPTION ""
			::= { mbusE6 11 }

mbusE6VIF03		OBJECT-TYPE
			SYNTAX	INTEGER
			ACCESS	read-only
			STATUS	current
	DESCRIPTION ""
			::= { mbusE6 12 }

mbusE6Value03		OBJECT-TYPE
			SYNTAX	INTEGER
			ACCESS	read-only
			STATUS	current
	DESCRIPTION ""
			::= { mbusE6 13 }

mbusE6VIF04		OBJECT-TYPE
			SYNTAX	INTEGER
			ACCESS	read-only
			STATUS	current
	DESCRIPTION ""
			::= { mbusE6 14 }

mbusE6Value04		OBJECT-TYPE
			SYNTAX	INTEGER
			ACCESS	read-only
			STATUS	current
	DESCRIPTION ""
			::= { mbusE6 15 }

mbusE6VIF05		OBJECT-TYPE
			SYNTAX	INTEGER
			ACCESS	read-only
			STATUS	current
	DESCRIPTION ""
			::= { mbusE6 16 }

mbusE6Value05		OBJECT-TYPE
			SYNTAX	INTEGER
			ACCESS	read-only
			STATUS	current
	DESCRIPTION ""
			::= { mbusE6 17 }

mbusE6VIF06		OBJECT-TYPE
			SYNTAX	INTEGER
			ACCESS	read-only
			STATUS	current
	DESCRIPTION ""
			::= { mbusE6 18 }

mbusE6Value06		OBJECT-TYPE
			SYNTAX	INTEGER
			ACCESS	read-only
			STATUS	current
	DESCRIPTION ""
			::= { mbusE6 19 }

mbusE6VIF07		OBJECT-TYPE
			SYNTAX	INTEGER
			ACCESS	read-only
			STATUS	current
	DESCRIPTION ""
			::= { mbusE6 20 }

mbusE6Value07		OBJECT-TYPE
			SYNTAX	INTEGER
			ACCESS	read-only
			STATUS	current
	DESCRIPTION ""
			::= { mbusE6 21 }

mbusE6VIF08		OBJECT-TYPE
			SYNTAX	INTEGER
			ACCESS	read-only
			STATUS	current
	DESCRIPTION ""
			::= { mbusE6 22 }

mbusE6Value08		OBJECT-TYPE
			SYNTAX	INTEGER
			ACCESS	read-only
			STATUS	current
	DESCRIPTION ""
			::= { mbusE6 23 }

mbusE6VIF09		OBJECT-TYPE
			SYNTAX	INTEGER
			ACCESS	read-only
			STATUS	current
	DESCRIPTION ""
			::= { mbusE6 24 }

mbusE6Value09		OBJECT-TYPE
			SYNTAX	INTEGER
			ACCESS	read-only
			STATUS	current
	DESCRIPTION ""
			::= { mbusE6 25 }

mbusE6VIF0A		OBJECT-TYPE
			SYNTAX	INTEGER
			ACCESS	read-only
			STATUS	current
	DESCRIPTION ""
			::= { mbusE6 26 }

mbusE6Value0A		OBJECT-TYPE
			SYNTAX	INTEGER
			ACCESS	read-only
			STATUS	current
	DESCRIPTION ""
			::= { mbusE6 27 }

mbusE6VIF0B		OBJECT-TYPE
			SYNTAX	INTEGER
			ACCESS	read-only
			STATUS	current
	DESCRIPTION ""
			::= { mbusE6 28 }

mbusE6Value0B		OBJECT-TYPE
			SYNTAX	INTEGER
			ACCESS	read-only
			STATUS	current
	DESCRIPTION ""
			::= { mbusE6 29 }

mbusE6VIF0C		OBJECT-TYPE
			SYNTAX	INTEGER
			ACCESS	read-only
			STATUS	current
	DESCRIPTION ""
			::= { mbusE6 30 }

mbusE6Value0C		OBJECT-TYPE
			SYNTAX	INTEGER
			ACCESS	read-only
			STATUS	current
	DESCRIPTION ""
			::= { mbusE6 31 }

mbusE6VIF0D		OBJECT-TYPE
			SYNTAX	INTEGER
			ACCESS	read-only
			STATUS	current
	DESCRIPTION ""
			::= { mbusE6 32 }

mbusE6Value0D		OBJECT-TYPE
			SYNTAX	INTEGER
			ACCESS	read-only
			STATUS	current
	DESCRIPTION ""
			::= { mbusE6 33 }

mbusE6VIF0E		OBJECT-TYPE
			SYNTAX	INTEGER
			ACCESS	read-only
			STATUS	current
	DESCRIPTION ""
			::= { mbusE6 34 }

mbusE6Value0E		OBJECT-TYPE
			SYNTAX	INTEGER
			ACCESS	read-only
			STATUS	current
	DESCRIPTION ""
			::= { mbusE6 35 }

mbusE6VIF0F		OBJECT-TYPE
			SYNTAX	INTEGER
			ACCESS	read-only
			STATUS	current
	DESCRIPTION ""
			::= { mbusE6 36 }

mbusE6Value0F		OBJECT-TYPE
			SYNTAX	INTEGER
			ACCESS	read-only
			STATUS	current
	DESCRIPTION ""
			::= { mbusE6 37 }

mbusE6VIF10		OBJECT-TYPE
			SYNTAX	INTEGER
			ACCESS	read-only
			STATUS	current
	DESCRIPTION ""
			::= { mbusE6 38 }

mbusE6Value10		OBJECT-TYPE
			SYNTAX	INTEGER
			ACCESS	read-only
			STATUS	current
	DESCRIPTION ""
			::= { mbusE6 39 }

mbusE6VIF11		OBJECT-TYPE
			SYNTAX	INTEGER
			ACCESS	read-only
			STATUS	current
	DESCRIPTION ""
			::= { mbusE6 40 }

mbusE6Value11		OBJECT-TYPE
			SYNTAX	INTEGER
			ACCESS	read-only
			STATUS	current
	DESCRIPTION ""
			::= { mbusE6 41 }

mbusE6VIF12		OBJECT-TYPE
			SYNTAX	INTEGER
			ACCESS	read-only
			STATUS	current
	DESCRIPTION ""
			::= { mbusE6 42 }

mbusE6Value12		OBJECT-TYPE
			SYNTAX	INTEGER
			ACCESS	read-only
			STATUS	current
	DESCRIPTION ""
			::= { mbusE6 43 }

mbusE6VIF13		OBJECT-TYPE
			SYNTAX	INTEGER
			ACCESS	read-only
			STATUS	current
	DESCRIPTION ""
			::= { mbusE6 44 }

mbusE6Value13		OBJECT-TYPE
			SYNTAX	INTEGER
			ACCESS	read-only
			STATUS	current
	DESCRIPTION ""
			::= { mbusE6 45 }

mbusE6VIF14		OBJECT-TYPE
			SYNTAX	INTEGER
			ACCESS	read-only
			STATUS	current
	DESCRIPTION ""
			::= { mbusE6 46 }

mbusE6Value14		OBJECT-TYPE
			SYNTAX	INTEGER
			ACCESS	read-only
			STATUS	current
	DESCRIPTION ""
			::= { mbusE6 47 }

mbusE6VIF15		OBJECT-TYPE
			SYNTAX	INTEGER
			ACCESS	read-only
			STATUS	current
	DESCRIPTION ""
			::= { mbusE6 48 }

mbusE6Value15		OBJECT-TYPE
			SYNTAX	INTEGER
			ACCESS	read-only
			STATUS	current
	DESCRIPTION ""
			::= { mbusE6 49 }

mbusE6VIF16		OBJECT-TYPE
			SYNTAX	INTEGER
			ACCESS	read-only
			STATUS	current
	DESCRIPTION ""
			::= { mbusE6 50 }

mbusE6Value16		OBJECT-TYPE
			SYNTAX	INTEGER
			ACCESS	read-only
			STATUS	current
	DESCRIPTION ""
			::= { mbusE6 51 }

mbusE6VIF17		OBJECT-TYPE
			SYNTAX	INTEGER
			ACCESS	read-only
			STATUS	current
	DESCRIPTION ""
			::= { mbusE6 52 }

mbusE6Value17		OBJECT-TYPE
			SYNTAX	INTEGER
			ACCESS	read-only
			STATUS	current
	DESCRIPTION ""
			::= { mbusE6 53 }

mbusE6VIF18		OBJECT-TYPE
			SYNTAX	INTEGER
			ACCESS	read-only
			STATUS	current
	DESCRIPTION ""
			::= { mbusE6 54 }

mbusE6Value18		OBJECT-TYPE
			SYNTAX	INTEGER
			ACCESS	read-only
			STATUS	current
	DESCRIPTION ""
			::= { mbusE6 55 }

mbusE6VIF19		OBJECT-TYPE
			SYNTAX	INTEGER
			ACCESS	read-only
			STATUS	current
	DESCRIPTION ""
			::= { mbusE6 56 }

mbusE6Value19		OBJECT-TYPE
			SYNTAX	INTEGER
			ACCESS	read-only
			STATUS	current
	DESCRIPTION ""
			::= { mbusE6 57 }

mbusE6VIF1A		OBJECT-TYPE
			SYNTAX	INTEGER
			ACCESS	read-only
			STATUS	current
	DESCRIPTION ""
			::= { mbusE6 58 }

mbusE6Value1A		OBJECT-TYPE
			SYNTAX	INTEGER
			ACCESS	read-only
			STATUS	current
	DESCRIPTION ""
			::= { mbusE6 59 }

mbusE6VIF1B		OBJECT-TYPE
			SYNTAX	INTEGER
			ACCESS	read-only
			STATUS	current
	DESCRIPTION ""
			::= { mbusE6 60 }

mbusE6Value1B		OBJECT-TYPE
			SYNTAX	INTEGER
			ACCESS	read-only
			STATUS	current
	DESCRIPTION ""
			::= { mbusE6 61 }

mbusE6VIF1C		OBJECT-TYPE
			SYNTAX	INTEGER
			ACCESS	read-only
			STATUS	current
	DESCRIPTION ""
			::= { mbusE6 62 }

mbusE6Value1C		OBJECT-TYPE
			SYNTAX	INTEGER
			ACCESS	read-only
			STATUS	current
	DESCRIPTION ""
			::= { mbusE6 63 }

mbusE6VIF1D		OBJECT-TYPE
			SYNTAX	INTEGER
			ACCESS	read-only
			STATUS	current
	DESCRIPTION ""
			::= { mbusE6 64 }

mbusE6Value1D		OBJECT-TYPE
			SYNTAX	INTEGER
			ACCESS	read-only
			STATUS	current
	DESCRIPTION ""
			::= { mbusE6 65 }

mbusE6VIF1E		OBJECT-TYPE
			SYNTAX	INTEGER
			ACCESS	read-only
			STATUS	current
	DESCRIPTION ""
			::= { mbusE6 66 }

mbusE6Value1E		OBJECT-TYPE
			SYNTAX	INTEGER
			ACCESS	read-only
			STATUS	current
	DESCRIPTION ""
			::= { mbusE6 67 }

mbusE6VIF1F		OBJECT-TYPE
			SYNTAX	INTEGER
			ACCESS	read-only
			STATUS	current
	DESCRIPTION ""
			::= { mbusE6 68 }

mbusE6Value1F		OBJECT-TYPE
			SYNTAX	INTEGER
			ACCESS	read-only
			STATUS	current
	DESCRIPTION ""
			::= { mbusE6 69 }

mbusE6VIF20		OBJECT-TYPE
			SYNTAX	INTEGER
			ACCESS	read-only
			STATUS	current
	DESCRIPTION ""
			::= { mbusE6 70 }

mbusE6Value20		OBJECT-TYPE
			SYNTAX	INTEGER
			ACCESS	read-only
			STATUS	current
	DESCRIPTION ""
			::= { mbusE6 71 }

mbusE6VIF21		OBJECT-TYPE
			SYNTAX	INTEGER
			ACCESS	read-only
			STATUS	current
	DESCRIPTION ""
			::= { mbusE6 72 }

mbusE6Value21		OBJECT-TYPE
			SYNTAX	INTEGER
			ACCESS	read-only
			STATUS	current
	DESCRIPTION ""
			::= { mbusE6 73 }

mbusE6VIF22		OBJECT-TYPE
			SYNTAX	INTEGER
			ACCESS	read-only
			STATUS	current
	DESCRIPTION ""
			::= { mbusE6 74 }

mbusE6Value22		OBJECT-TYPE
			SYNTAX	INTEGER
			ACCESS	read-only
			STATUS	current
	DESCRIPTION ""
			::= { mbusE6 75 }

mbusE6VIF23		OBJECT-TYPE
			SYNTAX	INTEGER
			ACCESS	read-only
			STATUS	current
	DESCRIPTION ""
			::= { mbusE6 76 }

mbusE6Value23		OBJECT-TYPE
			SYNTAX	INTEGER
			ACCESS	read-only
			STATUS	current
	DESCRIPTION ""
			::= { mbusE6 77 }

mbusE6VIF24		OBJECT-TYPE
			SYNTAX	INTEGER
			ACCESS	read-only
			STATUS	current
	DESCRIPTION ""
			::= { mbusE6 78 }

mbusE6Value24		OBJECT-TYPE
			SYNTAX	INTEGER
			ACCESS	read-only
			STATUS	current
	DESCRIPTION ""
			::= { mbusE6 79 }

mbusE6VIF25		OBJECT-TYPE
			SYNTAX	INTEGER
			ACCESS	read-only
			STATUS	current
	DESCRIPTION ""
			::= { mbusE6 80 }

mbusE6Value25		OBJECT-TYPE
			SYNTAX	INTEGER
			ACCESS	read-only
			STATUS	current
	DESCRIPTION ""
			::= { mbusE6 81 }

mbusE6VIF26		OBJECT-TYPE
			SYNTAX	INTEGER
			ACCESS	read-only
			STATUS	current
	DESCRIPTION ""
			::= { mbusE6 82 }

mbusE6Value26		OBJECT-TYPE
			SYNTAX	INTEGER
			ACCESS	read-only
			STATUS	current
	DESCRIPTION ""
			::= { mbusE6 83 }

mbusE6VIF27		OBJECT-TYPE
			SYNTAX	INTEGER
			ACCESS	read-only
			STATUS	current
	DESCRIPTION ""
			::= { mbusE6 84 }

mbusE6Value27		OBJECT-TYPE
			SYNTAX	INTEGER
			ACCESS	read-only
			STATUS	current
	DESCRIPTION ""
			::= { mbusE6 85 }

mbusE6VIF28		OBJECT-TYPE
			SYNTAX	INTEGER
			ACCESS	read-only
			STATUS	current
	DESCRIPTION ""
			::= { mbusE6 86 }

mbusE6Value28		OBJECT-TYPE
			SYNTAX	INTEGER
			ACCESS	read-only
			STATUS	current
	DESCRIPTION ""
			::= { mbusE6 87 }

mbusE6VIF29		OBJECT-TYPE
			SYNTAX	INTEGER
			ACCESS	read-only
			STATUS	current
	DESCRIPTION ""
			::= { mbusE6 88 }

mbusE6Value29		OBJECT-TYPE
			SYNTAX	INTEGER
			ACCESS	read-only
			STATUS	current
	DESCRIPTION ""
			::= { mbusE6 89 }

mbusE6VIF2A		OBJECT-TYPE
			SYNTAX	INTEGER
			ACCESS	read-only
			STATUS	current
	DESCRIPTION ""
			::= { mbusE6 90 }

mbusE6Value2A		OBJECT-TYPE
			SYNTAX	INTEGER
			ACCESS	read-only
			STATUS	current
	DESCRIPTION ""
			::= { mbusE6 91 }

mbusE6VIF2B		OBJECT-TYPE
			SYNTAX	INTEGER
			ACCESS	read-only
			STATUS	current
	DESCRIPTION ""
			::= { mbusE6 92 }

mbusE6Value2B		OBJECT-TYPE
			SYNTAX	INTEGER
			ACCESS	read-only
			STATUS	current
	DESCRIPTION ""
			::= { mbusE6 93 }

mbusE6VIF2C		OBJECT-TYPE
			SYNTAX	INTEGER
			ACCESS	read-only
			STATUS	current
	DESCRIPTION ""
			::= { mbusE6 94 }

mbusE6Value2C		OBJECT-TYPE
			SYNTAX	INTEGER
			ACCESS	read-only
			STATUS	current
	DESCRIPTION ""
			::= { mbusE6 95 }

mbusE6VIF2D		OBJECT-TYPE
			SYNTAX	INTEGER
			ACCESS	read-only
			STATUS	current
	DESCRIPTION ""
			::= { mbusE6 96 }

mbusE6Value2D		OBJECT-TYPE
			SYNTAX	INTEGER
			ACCESS	read-only
			STATUS	current
	DESCRIPTION ""
			::= { mbusE6 97 }

mbusE6VIF2E		OBJECT-TYPE
			SYNTAX	INTEGER
			ACCESS	read-only
			STATUS	current
	DESCRIPTION ""
			::= { mbusE6 98 }

mbusE6Value2E		OBJECT-TYPE
			SYNTAX	INTEGER
			ACCESS	read-only
			STATUS	current
	DESCRIPTION ""
			::= { mbusE6 99 }

mbusE6VIF2F		OBJECT-TYPE
			SYNTAX	INTEGER
			ACCESS	read-only
			STATUS	current
	DESCRIPTION ""
			::= { mbusE6 100 }

mbusE6Value2F		OBJECT-TYPE
			SYNTAX	INTEGER
			ACCESS	read-only
			STATUS	current
	DESCRIPTION ""
			::= { mbusE6 101 }

mbusE7			OBJECT IDENTIFIER ::= { mbus 231 }

mbusE7IdNumber		OBJECT-TYPE
			SYNTAX	Gauge
			ACCESS	read-only
			STATUS	current
	DESCRIPTION ""
			::= { mbusE7 1 }

mbusE7Manufacturer	OBJECT-TYPE
			SYNTAX	Gauge
			ACCESS	read-only
			STATUS	current
	DESCRIPTION ""
			::= { mbusE7 2 }

mbusE7Version		OBJECT-TYPE
			SYNTAX	Gauge
			ACCESS	read-only
			STATUS	current
	DESCRIPTION ""
			::= { mbusE7 3 }

mbusE7Medium		OBJECT-TYPE
			SYNTAX	Gauge
			ACCESS	read-only
			STATUS	current
	DESCRIPTION ""
			::= { mbusE7 4 }

mbusE7Status		OBJECT-TYPE
			SYNTAX	Gauge
			ACCESS	read-only
			STATUS	current
	DESCRIPTION ""
			::= { mbusE7 5 }

mbusE7VIF00		OBJECT-TYPE
			SYNTAX	INTEGER
			ACCESS	read-only
			STATUS	current
	DESCRIPTION ""
			::= { mbusE7 6 }

mbusE7Value00		OBJECT-TYPE
			SYNTAX	INTEGER
			ACCESS	read-only
			STATUS	current
	DESCRIPTION ""
			::= { mbusE7 7 }

mbusE7VIF01		OBJECT-TYPE
			SYNTAX	INTEGER
			ACCESS	read-only
			STATUS	current
	DESCRIPTION ""
			::= { mbusE7 8 }

mbusE7Value01		OBJECT-TYPE
			SYNTAX	INTEGER
			ACCESS	read-only
			STATUS	current
	DESCRIPTION ""
			::= { mbusE7 9 }

mbusE7VIF02		OBJECT-TYPE
			SYNTAX	INTEGER
			ACCESS	read-only
			STATUS	current
	DESCRIPTION ""
			::= { mbusE7 10 }

mbusE7Value02		OBJECT-TYPE
			SYNTAX	INTEGER
			ACCESS	read-only
			STATUS	current
	DESCRIPTION ""
			::= { mbusE7 11 }

mbusE7VIF03		OBJECT-TYPE
			SYNTAX	INTEGER
			ACCESS	read-only
			STATUS	current
	DESCRIPTION ""
			::= { mbusE7 12 }

mbusE7Value03		OBJECT-TYPE
			SYNTAX	INTEGER
			ACCESS	read-only
			STATUS	current
	DESCRIPTION ""
			::= { mbusE7 13 }

mbusE7VIF04		OBJECT-TYPE
			SYNTAX	INTEGER
			ACCESS	read-only
			STATUS	current
	DESCRIPTION ""
			::= { mbusE7 14 }

mbusE7Value04		OBJECT-TYPE
			SYNTAX	INTEGER
			ACCESS	read-only
			STATUS	current
	DESCRIPTION ""
			::= { mbusE7 15 }

mbusE7VIF05		OBJECT-TYPE
			SYNTAX	INTEGER
			ACCESS	read-only
			STATUS	current
	DESCRIPTION ""
			::= { mbusE7 16 }

mbusE7Value05		OBJECT-TYPE
			SYNTAX	INTEGER
			ACCESS	read-only
			STATUS	current
	DESCRIPTION ""
			::= { mbusE7 17 }

mbusE7VIF06		OBJECT-TYPE
			SYNTAX	INTEGER
			ACCESS	read-only
			STATUS	current
	DESCRIPTION ""
			::= { mbusE7 18 }

mbusE7Value06		OBJECT-TYPE
			SYNTAX	INTEGER
			ACCESS	read-only
			STATUS	current
	DESCRIPTION ""
			::= { mbusE7 19 }

mbusE7VIF07		OBJECT-TYPE
			SYNTAX	INTEGER
			ACCESS	read-only
			STATUS	current
	DESCRIPTION ""
			::= { mbusE7 20 }

mbusE7Value07		OBJECT-TYPE
			SYNTAX	INTEGER
			ACCESS	read-only
			STATUS	current
	DESCRIPTION ""
			::= { mbusE7 21 }

mbusE7VIF08		OBJECT-TYPE
			SYNTAX	INTEGER
			ACCESS	read-only
			STATUS	current
	DESCRIPTION ""
			::= { mbusE7 22 }

mbusE7Value08		OBJECT-TYPE
			SYNTAX	INTEGER
			ACCESS	read-only
			STATUS	current
	DESCRIPTION ""
			::= { mbusE7 23 }

mbusE7VIF09		OBJECT-TYPE
			SYNTAX	INTEGER
			ACCESS	read-only
			STATUS	current
	DESCRIPTION ""
			::= { mbusE7 24 }

mbusE7Value09		OBJECT-TYPE
			SYNTAX	INTEGER
			ACCESS	read-only
			STATUS	current
	DESCRIPTION ""
			::= { mbusE7 25 }

mbusE7VIF0A		OBJECT-TYPE
			SYNTAX	INTEGER
			ACCESS	read-only
			STATUS	current
	DESCRIPTION ""
			::= { mbusE7 26 }

mbusE7Value0A		OBJECT-TYPE
			SYNTAX	INTEGER
			ACCESS	read-only
			STATUS	current
	DESCRIPTION ""
			::= { mbusE7 27 }

mbusE7VIF0B		OBJECT-TYPE
			SYNTAX	INTEGER
			ACCESS	read-only
			STATUS	current
	DESCRIPTION ""
			::= { mbusE7 28 }

mbusE7Value0B		OBJECT-TYPE
			SYNTAX	INTEGER
			ACCESS	read-only
			STATUS	current
	DESCRIPTION ""
			::= { mbusE7 29 }

mbusE7VIF0C		OBJECT-TYPE
			SYNTAX	INTEGER
			ACCESS	read-only
			STATUS	current
	DESCRIPTION ""
			::= { mbusE7 30 }

mbusE7Value0C		OBJECT-TYPE
			SYNTAX	INTEGER
			ACCESS	read-only
			STATUS	current
	DESCRIPTION ""
			::= { mbusE7 31 }

mbusE7VIF0D		OBJECT-TYPE
			SYNTAX	INTEGER
			ACCESS	read-only
			STATUS	current
	DESCRIPTION ""
			::= { mbusE7 32 }

mbusE7Value0D		OBJECT-TYPE
			SYNTAX	INTEGER
			ACCESS	read-only
			STATUS	current
	DESCRIPTION ""
			::= { mbusE7 33 }

mbusE7VIF0E		OBJECT-TYPE
			SYNTAX	INTEGER
			ACCESS	read-only
			STATUS	current
	DESCRIPTION ""
			::= { mbusE7 34 }

mbusE7Value0E		OBJECT-TYPE
			SYNTAX	INTEGER
			ACCESS	read-only
			STATUS	current
	DESCRIPTION ""
			::= { mbusE7 35 }

mbusE7VIF0F		OBJECT-TYPE
			SYNTAX	INTEGER
			ACCESS	read-only
			STATUS	current
	DESCRIPTION ""
			::= { mbusE7 36 }

mbusE7Value0F		OBJECT-TYPE
			SYNTAX	INTEGER
			ACCESS	read-only
			STATUS	current
	DESCRIPTION ""
			::= { mbusE7 37 }

mbusE7VIF10		OBJECT-TYPE
			SYNTAX	INTEGER
			ACCESS	read-only
			STATUS	current
	DESCRIPTION ""
			::= { mbusE7 38 }

mbusE7Value10		OBJECT-TYPE
			SYNTAX	INTEGER
			ACCESS	read-only
			STATUS	current
	DESCRIPTION ""
			::= { mbusE7 39 }

mbusE7VIF11		OBJECT-TYPE
			SYNTAX	INTEGER
			ACCESS	read-only
			STATUS	current
	DESCRIPTION ""
			::= { mbusE7 40 }

mbusE7Value11		OBJECT-TYPE
			SYNTAX	INTEGER
			ACCESS	read-only
			STATUS	current
	DESCRIPTION ""
			::= { mbusE7 41 }

mbusE7VIF12		OBJECT-TYPE
			SYNTAX	INTEGER
			ACCESS	read-only
			STATUS	current
	DESCRIPTION ""
			::= { mbusE7 42 }

mbusE7Value12		OBJECT-TYPE
			SYNTAX	INTEGER
			ACCESS	read-only
			STATUS	current
	DESCRIPTION ""
			::= { mbusE7 43 }

mbusE7VIF13		OBJECT-TYPE
			SYNTAX	INTEGER
			ACCESS	read-only
			STATUS	current
	DESCRIPTION ""
			::= { mbusE7 44 }

mbusE7Value13		OBJECT-TYPE
			SYNTAX	INTEGER
			ACCESS	read-only
			STATUS	current
	DESCRIPTION ""
			::= { mbusE7 45 }

mbusE7VIF14		OBJECT-TYPE
			SYNTAX	INTEGER
			ACCESS	read-only
			STATUS	current
	DESCRIPTION ""
			::= { mbusE7 46 }

mbusE7Value14		OBJECT-TYPE
			SYNTAX	INTEGER
			ACCESS	read-only
			STATUS	current
	DESCRIPTION ""
			::= { mbusE7 47 }

mbusE7VIF15		OBJECT-TYPE
			SYNTAX	INTEGER
			ACCESS	read-only
			STATUS	current
	DESCRIPTION ""
			::= { mbusE7 48 }

mbusE7Value15		OBJECT-TYPE
			SYNTAX	INTEGER
			ACCESS	read-only
			STATUS	current
	DESCRIPTION ""
			::= { mbusE7 49 }

mbusE7VIF16		OBJECT-TYPE
			SYNTAX	INTEGER
			ACCESS	read-only
			STATUS	current
	DESCRIPTION ""
			::= { mbusE7 50 }

mbusE7Value16		OBJECT-TYPE
			SYNTAX	INTEGER
			ACCESS	read-only
			STATUS	current
	DESCRIPTION ""
			::= { mbusE7 51 }

mbusE7VIF17		OBJECT-TYPE
			SYNTAX	INTEGER
			ACCESS	read-only
			STATUS	current
	DESCRIPTION ""
			::= { mbusE7 52 }

mbusE7Value17		OBJECT-TYPE
			SYNTAX	INTEGER
			ACCESS	read-only
			STATUS	current
	DESCRIPTION ""
			::= { mbusE7 53 }

mbusE7VIF18		OBJECT-TYPE
			SYNTAX	INTEGER
			ACCESS	read-only
			STATUS	current
	DESCRIPTION ""
			::= { mbusE7 54 }

mbusE7Value18		OBJECT-TYPE
			SYNTAX	INTEGER
			ACCESS	read-only
			STATUS	current
	DESCRIPTION ""
			::= { mbusE7 55 }

mbusE7VIF19		OBJECT-TYPE
			SYNTAX	INTEGER
			ACCESS	read-only
			STATUS	current
	DESCRIPTION ""
			::= { mbusE7 56 }

mbusE7Value19		OBJECT-TYPE
			SYNTAX	INTEGER
			ACCESS	read-only
			STATUS	current
	DESCRIPTION ""
			::= { mbusE7 57 }

mbusE7VIF1A		OBJECT-TYPE
			SYNTAX	INTEGER
			ACCESS	read-only
			STATUS	current
	DESCRIPTION ""
			::= { mbusE7 58 }

mbusE7Value1A		OBJECT-TYPE
			SYNTAX	INTEGER
			ACCESS	read-only
			STATUS	current
	DESCRIPTION ""
			::= { mbusE7 59 }

mbusE7VIF1B		OBJECT-TYPE
			SYNTAX	INTEGER
			ACCESS	read-only
			STATUS	current
	DESCRIPTION ""
			::= { mbusE7 60 }

mbusE7Value1B		OBJECT-TYPE
			SYNTAX	INTEGER
			ACCESS	read-only
			STATUS	current
	DESCRIPTION ""
			::= { mbusE7 61 }

mbusE7VIF1C		OBJECT-TYPE
			SYNTAX	INTEGER
			ACCESS	read-only
			STATUS	current
	DESCRIPTION ""
			::= { mbusE7 62 }

mbusE7Value1C		OBJECT-TYPE
			SYNTAX	INTEGER
			ACCESS	read-only
			STATUS	current
	DESCRIPTION ""
			::= { mbusE7 63 }

mbusE7VIF1D		OBJECT-TYPE
			SYNTAX	INTEGER
			ACCESS	read-only
			STATUS	current
	DESCRIPTION ""
			::= { mbusE7 64 }

mbusE7Value1D		OBJECT-TYPE
			SYNTAX	INTEGER
			ACCESS	read-only
			STATUS	current
	DESCRIPTION ""
			::= { mbusE7 65 }

mbusE7VIF1E		OBJECT-TYPE
			SYNTAX	INTEGER
			ACCESS	read-only
			STATUS	current
	DESCRIPTION ""
			::= { mbusE7 66 }

mbusE7Value1E		OBJECT-TYPE
			SYNTAX	INTEGER
			ACCESS	read-only
			STATUS	current
	DESCRIPTION ""
			::= { mbusE7 67 }

mbusE7VIF1F		OBJECT-TYPE
			SYNTAX	INTEGER
			ACCESS	read-only
			STATUS	current
	DESCRIPTION ""
			::= { mbusE7 68 }

mbusE7Value1F		OBJECT-TYPE
			SYNTAX	INTEGER
			ACCESS	read-only
			STATUS	current
	DESCRIPTION ""
			::= { mbusE7 69 }

mbusE7VIF20		OBJECT-TYPE
			SYNTAX	INTEGER
			ACCESS	read-only
			STATUS	current
	DESCRIPTION ""
			::= { mbusE7 70 }

mbusE7Value20		OBJECT-TYPE
			SYNTAX	INTEGER
			ACCESS	read-only
			STATUS	current
	DESCRIPTION ""
			::= { mbusE7 71 }

mbusE7VIF21		OBJECT-TYPE
			SYNTAX	INTEGER
			ACCESS	read-only
			STATUS	current
	DESCRIPTION ""
			::= { mbusE7 72 }

mbusE7Value21		OBJECT-TYPE
			SYNTAX	INTEGER
			ACCESS	read-only
			STATUS	current
	DESCRIPTION ""
			::= { mbusE7 73 }

mbusE7VIF22		OBJECT-TYPE
			SYNTAX	INTEGER
			ACCESS	read-only
			STATUS	current
	DESCRIPTION ""
			::= { mbusE7 74 }

mbusE7Value22		OBJECT-TYPE
			SYNTAX	INTEGER
			ACCESS	read-only
			STATUS	current
	DESCRIPTION ""
			::= { mbusE7 75 }

mbusE7VIF23		OBJECT-TYPE
			SYNTAX	INTEGER
			ACCESS	read-only
			STATUS	current
	DESCRIPTION ""
			::= { mbusE7 76 }

mbusE7Value23		OBJECT-TYPE
			SYNTAX	INTEGER
			ACCESS	read-only
			STATUS	current
	DESCRIPTION ""
			::= { mbusE7 77 }

mbusE7VIF24		OBJECT-TYPE
			SYNTAX	INTEGER
			ACCESS	read-only
			STATUS	current
	DESCRIPTION ""
			::= { mbusE7 78 }

mbusE7Value24		OBJECT-TYPE
			SYNTAX	INTEGER
			ACCESS	read-only
			STATUS	current
	DESCRIPTION ""
			::= { mbusE7 79 }

mbusE7VIF25		OBJECT-TYPE
			SYNTAX	INTEGER
			ACCESS	read-only
			STATUS	current
	DESCRIPTION ""
			::= { mbusE7 80 }

mbusE7Value25		OBJECT-TYPE
			SYNTAX	INTEGER
			ACCESS	read-only
			STATUS	current
	DESCRIPTION ""
			::= { mbusE7 81 }

mbusE7VIF26		OBJECT-TYPE
			SYNTAX	INTEGER
			ACCESS	read-only
			STATUS	current
	DESCRIPTION ""
			::= { mbusE7 82 }

mbusE7Value26		OBJECT-TYPE
			SYNTAX	INTEGER
			ACCESS	read-only
			STATUS	current
	DESCRIPTION ""
			::= { mbusE7 83 }

mbusE7VIF27		OBJECT-TYPE
			SYNTAX	INTEGER
			ACCESS	read-only
			STATUS	current
	DESCRIPTION ""
			::= { mbusE7 84 }

mbusE7Value27		OBJECT-TYPE
			SYNTAX	INTEGER
			ACCESS	read-only
			STATUS	current
	DESCRIPTION ""
			::= { mbusE7 85 }

mbusE7VIF28		OBJECT-TYPE
			SYNTAX	INTEGER
			ACCESS	read-only
			STATUS	current
	DESCRIPTION ""
			::= { mbusE7 86 }

mbusE7Value28		OBJECT-TYPE
			SYNTAX	INTEGER
			ACCESS	read-only
			STATUS	current
	DESCRIPTION ""
			::= { mbusE7 87 }

mbusE7VIF29		OBJECT-TYPE
			SYNTAX	INTEGER
			ACCESS	read-only
			STATUS	current
	DESCRIPTION ""
			::= { mbusE7 88 }

mbusE7Value29		OBJECT-TYPE
			SYNTAX	INTEGER
			ACCESS	read-only
			STATUS	current
	DESCRIPTION ""
			::= { mbusE7 89 }

mbusE7VIF2A		OBJECT-TYPE
			SYNTAX	INTEGER
			ACCESS	read-only
			STATUS	current
	DESCRIPTION ""
			::= { mbusE7 90 }

mbusE7Value2A		OBJECT-TYPE
			SYNTAX	INTEGER
			ACCESS	read-only
			STATUS	current
	DESCRIPTION ""
			::= { mbusE7 91 }

mbusE7VIF2B		OBJECT-TYPE
			SYNTAX	INTEGER
			ACCESS	read-only
			STATUS	current
	DESCRIPTION ""
			::= { mbusE7 92 }

mbusE7Value2B		OBJECT-TYPE
			SYNTAX	INTEGER
			ACCESS	read-only
			STATUS	current
	DESCRIPTION ""
			::= { mbusE7 93 }

mbusE7VIF2C		OBJECT-TYPE
			SYNTAX	INTEGER
			ACCESS	read-only
			STATUS	current
	DESCRIPTION ""
			::= { mbusE7 94 }

mbusE7Value2C		OBJECT-TYPE
			SYNTAX	INTEGER
			ACCESS	read-only
			STATUS	current
	DESCRIPTION ""
			::= { mbusE7 95 }

mbusE7VIF2D		OBJECT-TYPE
			SYNTAX	INTEGER
			ACCESS	read-only
			STATUS	current
	DESCRIPTION ""
			::= { mbusE7 96 }

mbusE7Value2D		OBJECT-TYPE
			SYNTAX	INTEGER
			ACCESS	read-only
			STATUS	current
	DESCRIPTION ""
			::= { mbusE7 97 }

mbusE7VIF2E		OBJECT-TYPE
			SYNTAX	INTEGER
			ACCESS	read-only
			STATUS	current
	DESCRIPTION ""
			::= { mbusE7 98 }

mbusE7Value2E		OBJECT-TYPE
			SYNTAX	INTEGER
			ACCESS	read-only
			STATUS	current
	DESCRIPTION ""
			::= { mbusE7 99 }

mbusE7VIF2F		OBJECT-TYPE
			SYNTAX	INTEGER
			ACCESS	read-only
			STATUS	current
	DESCRIPTION ""
			::= { mbusE7 100 }

mbusE7Value2F		OBJECT-TYPE
			SYNTAX	INTEGER
			ACCESS	read-only
			STATUS	current
	DESCRIPTION ""
			::= { mbusE7 101 }

mbusE8			OBJECT IDENTIFIER ::= { mbus 232 }

mbusE8IdNumber		OBJECT-TYPE
			SYNTAX	Gauge
			ACCESS	read-only
			STATUS	current
	DESCRIPTION ""
			::= { mbusE8 1 }

mbusE8Manufacturer	OBJECT-TYPE
			SYNTAX	Gauge
			ACCESS	read-only
			STATUS	current
	DESCRIPTION ""
			::= { mbusE8 2 }

mbusE8Version		OBJECT-TYPE
			SYNTAX	Gauge
			ACCESS	read-only
			STATUS	current
	DESCRIPTION ""
			::= { mbusE8 3 }

mbusE8Medium		OBJECT-TYPE
			SYNTAX	Gauge
			ACCESS	read-only
			STATUS	current
	DESCRIPTION ""
			::= { mbusE8 4 }

mbusE8Status		OBJECT-TYPE
			SYNTAX	Gauge
			ACCESS	read-only
			STATUS	current
	DESCRIPTION ""
			::= { mbusE8 5 }

mbusE8VIF00		OBJECT-TYPE
			SYNTAX	INTEGER
			ACCESS	read-only
			STATUS	current
	DESCRIPTION ""
			::= { mbusE8 6 }

mbusE8Value00		OBJECT-TYPE
			SYNTAX	INTEGER
			ACCESS	read-only
			STATUS	current
	DESCRIPTION ""
			::= { mbusE8 7 }

mbusE8VIF01		OBJECT-TYPE
			SYNTAX	INTEGER
			ACCESS	read-only
			STATUS	current
	DESCRIPTION ""
			::= { mbusE8 8 }

mbusE8Value01		OBJECT-TYPE
			SYNTAX	INTEGER
			ACCESS	read-only
			STATUS	current
	DESCRIPTION ""
			::= { mbusE8 9 }

mbusE8VIF02		OBJECT-TYPE
			SYNTAX	INTEGER
			ACCESS	read-only
			STATUS	current
	DESCRIPTION ""
			::= { mbusE8 10 }

mbusE8Value02		OBJECT-TYPE
			SYNTAX	INTEGER
			ACCESS	read-only
			STATUS	current
	DESCRIPTION ""
			::= { mbusE8 11 }

mbusE8VIF03		OBJECT-TYPE
			SYNTAX	INTEGER
			ACCESS	read-only
			STATUS	current
	DESCRIPTION ""
			::= { mbusE8 12 }

mbusE8Value03		OBJECT-TYPE
			SYNTAX	INTEGER
			ACCESS	read-only
			STATUS	current
	DESCRIPTION ""
			::= { mbusE8 13 }

mbusE8VIF04		OBJECT-TYPE
			SYNTAX	INTEGER
			ACCESS	read-only
			STATUS	current
	DESCRIPTION ""
			::= { mbusE8 14 }

mbusE8Value04		OBJECT-TYPE
			SYNTAX	INTEGER
			ACCESS	read-only
			STATUS	current
	DESCRIPTION ""
			::= { mbusE8 15 }

mbusE8VIF05		OBJECT-TYPE
			SYNTAX	INTEGER
			ACCESS	read-only
			STATUS	current
	DESCRIPTION ""
			::= { mbusE8 16 }

mbusE8Value05		OBJECT-TYPE
			SYNTAX	INTEGER
			ACCESS	read-only
			STATUS	current
	DESCRIPTION ""
			::= { mbusE8 17 }

mbusE8VIF06		OBJECT-TYPE
			SYNTAX	INTEGER
			ACCESS	read-only
			STATUS	current
	DESCRIPTION ""
			::= { mbusE8 18 }

mbusE8Value06		OBJECT-TYPE
			SYNTAX	INTEGER
			ACCESS	read-only
			STATUS	current
	DESCRIPTION ""
			::= { mbusE8 19 }

mbusE8VIF07		OBJECT-TYPE
			SYNTAX	INTEGER
			ACCESS	read-only
			STATUS	current
	DESCRIPTION ""
			::= { mbusE8 20 }

mbusE8Value07		OBJECT-TYPE
			SYNTAX	INTEGER
			ACCESS	read-only
			STATUS	current
	DESCRIPTION ""
			::= { mbusE8 21 }

mbusE8VIF08		OBJECT-TYPE
			SYNTAX	INTEGER
			ACCESS	read-only
			STATUS	current
	DESCRIPTION ""
			::= { mbusE8 22 }

mbusE8Value08		OBJECT-TYPE
			SYNTAX	INTEGER
			ACCESS	read-only
			STATUS	current
	DESCRIPTION ""
			::= { mbusE8 23 }

mbusE8VIF09		OBJECT-TYPE
			SYNTAX	INTEGER
			ACCESS	read-only
			STATUS	current
	DESCRIPTION ""
			::= { mbusE8 24 }

mbusE8Value09		OBJECT-TYPE
			SYNTAX	INTEGER
			ACCESS	read-only
			STATUS	current
	DESCRIPTION ""
			::= { mbusE8 25 }

mbusE8VIF0A		OBJECT-TYPE
			SYNTAX	INTEGER
			ACCESS	read-only
			STATUS	current
	DESCRIPTION ""
			::= { mbusE8 26 }

mbusE8Value0A		OBJECT-TYPE
			SYNTAX	INTEGER
			ACCESS	read-only
			STATUS	current
	DESCRIPTION ""
			::= { mbusE8 27 }

mbusE8VIF0B		OBJECT-TYPE
			SYNTAX	INTEGER
			ACCESS	read-only
			STATUS	current
	DESCRIPTION ""
			::= { mbusE8 28 }

mbusE8Value0B		OBJECT-TYPE
			SYNTAX	INTEGER
			ACCESS	read-only
			STATUS	current
	DESCRIPTION ""
			::= { mbusE8 29 }

mbusE8VIF0C		OBJECT-TYPE
			SYNTAX	INTEGER
			ACCESS	read-only
			STATUS	current
	DESCRIPTION ""
			::= { mbusE8 30 }

mbusE8Value0C		OBJECT-TYPE
			SYNTAX	INTEGER
			ACCESS	read-only
			STATUS	current
	DESCRIPTION ""
			::= { mbusE8 31 }

mbusE8VIF0D		OBJECT-TYPE
			SYNTAX	INTEGER
			ACCESS	read-only
			STATUS	current
	DESCRIPTION ""
			::= { mbusE8 32 }

mbusE8Value0D		OBJECT-TYPE
			SYNTAX	INTEGER
			ACCESS	read-only
			STATUS	current
	DESCRIPTION ""
			::= { mbusE8 33 }

mbusE8VIF0E		OBJECT-TYPE
			SYNTAX	INTEGER
			ACCESS	read-only
			STATUS	current
	DESCRIPTION ""
			::= { mbusE8 34 }

mbusE8Value0E		OBJECT-TYPE
			SYNTAX	INTEGER
			ACCESS	read-only
			STATUS	current
	DESCRIPTION ""
			::= { mbusE8 35 }

mbusE8VIF0F		OBJECT-TYPE
			SYNTAX	INTEGER
			ACCESS	read-only
			STATUS	current
	DESCRIPTION ""
			::= { mbusE8 36 }

mbusE8Value0F		OBJECT-TYPE
			SYNTAX	INTEGER
			ACCESS	read-only
			STATUS	current
	DESCRIPTION ""
			::= { mbusE8 37 }

mbusE8VIF10		OBJECT-TYPE
			SYNTAX	INTEGER
			ACCESS	read-only
			STATUS	current
	DESCRIPTION ""
			::= { mbusE8 38 }

mbusE8Value10		OBJECT-TYPE
			SYNTAX	INTEGER
			ACCESS	read-only
			STATUS	current
	DESCRIPTION ""
			::= { mbusE8 39 }

mbusE8VIF11		OBJECT-TYPE
			SYNTAX	INTEGER
			ACCESS	read-only
			STATUS	current
	DESCRIPTION ""
			::= { mbusE8 40 }

mbusE8Value11		OBJECT-TYPE
			SYNTAX	INTEGER
			ACCESS	read-only
			STATUS	current
	DESCRIPTION ""
			::= { mbusE8 41 }

mbusE8VIF12		OBJECT-TYPE
			SYNTAX	INTEGER
			ACCESS	read-only
			STATUS	current
	DESCRIPTION ""
			::= { mbusE8 42 }

mbusE8Value12		OBJECT-TYPE
			SYNTAX	INTEGER
			ACCESS	read-only
			STATUS	current
	DESCRIPTION ""
			::= { mbusE8 43 }

mbusE8VIF13		OBJECT-TYPE
			SYNTAX	INTEGER
			ACCESS	read-only
			STATUS	current
	DESCRIPTION ""
			::= { mbusE8 44 }

mbusE8Value13		OBJECT-TYPE
			SYNTAX	INTEGER
			ACCESS	read-only
			STATUS	current
	DESCRIPTION ""
			::= { mbusE8 45 }

mbusE8VIF14		OBJECT-TYPE
			SYNTAX	INTEGER
			ACCESS	read-only
			STATUS	current
	DESCRIPTION ""
			::= { mbusE8 46 }

mbusE8Value14		OBJECT-TYPE
			SYNTAX	INTEGER
			ACCESS	read-only
			STATUS	current
	DESCRIPTION ""
			::= { mbusE8 47 }

mbusE8VIF15		OBJECT-TYPE
			SYNTAX	INTEGER
			ACCESS	read-only
			STATUS	current
	DESCRIPTION ""
			::= { mbusE8 48 }

mbusE8Value15		OBJECT-TYPE
			SYNTAX	INTEGER
			ACCESS	read-only
			STATUS	current
	DESCRIPTION ""
			::= { mbusE8 49 }

mbusE8VIF16		OBJECT-TYPE
			SYNTAX	INTEGER
			ACCESS	read-only
			STATUS	current
	DESCRIPTION ""
			::= { mbusE8 50 }

mbusE8Value16		OBJECT-TYPE
			SYNTAX	INTEGER
			ACCESS	read-only
			STATUS	current
	DESCRIPTION ""
			::= { mbusE8 51 }

mbusE8VIF17		OBJECT-TYPE
			SYNTAX	INTEGER
			ACCESS	read-only
			STATUS	current
	DESCRIPTION ""
			::= { mbusE8 52 }

mbusE8Value17		OBJECT-TYPE
			SYNTAX	INTEGER
			ACCESS	read-only
			STATUS	current
	DESCRIPTION ""
			::= { mbusE8 53 }

mbusE8VIF18		OBJECT-TYPE
			SYNTAX	INTEGER
			ACCESS	read-only
			STATUS	current
	DESCRIPTION ""
			::= { mbusE8 54 }

mbusE8Value18		OBJECT-TYPE
			SYNTAX	INTEGER
			ACCESS	read-only
			STATUS	current
	DESCRIPTION ""
			::= { mbusE8 55 }

mbusE8VIF19		OBJECT-TYPE
			SYNTAX	INTEGER
			ACCESS	read-only
			STATUS	current
	DESCRIPTION ""
			::= { mbusE8 56 }

mbusE8Value19		OBJECT-TYPE
			SYNTAX	INTEGER
			ACCESS	read-only
			STATUS	current
	DESCRIPTION ""
			::= { mbusE8 57 }

mbusE8VIF1A		OBJECT-TYPE
			SYNTAX	INTEGER
			ACCESS	read-only
			STATUS	current
	DESCRIPTION ""
			::= { mbusE8 58 }

mbusE8Value1A		OBJECT-TYPE
			SYNTAX	INTEGER
			ACCESS	read-only
			STATUS	current
	DESCRIPTION ""
			::= { mbusE8 59 }

mbusE8VIF1B		OBJECT-TYPE
			SYNTAX	INTEGER
			ACCESS	read-only
			STATUS	current
	DESCRIPTION ""
			::= { mbusE8 60 }

mbusE8Value1B		OBJECT-TYPE
			SYNTAX	INTEGER
			ACCESS	read-only
			STATUS	current
	DESCRIPTION ""
			::= { mbusE8 61 }

mbusE8VIF1C		OBJECT-TYPE
			SYNTAX	INTEGER
			ACCESS	read-only
			STATUS	current
	DESCRIPTION ""
			::= { mbusE8 62 }

mbusE8Value1C		OBJECT-TYPE
			SYNTAX	INTEGER
			ACCESS	read-only
			STATUS	current
	DESCRIPTION ""
			::= { mbusE8 63 }

mbusE8VIF1D		OBJECT-TYPE
			SYNTAX	INTEGER
			ACCESS	read-only
			STATUS	current
	DESCRIPTION ""
			::= { mbusE8 64 }

mbusE8Value1D		OBJECT-TYPE
			SYNTAX	INTEGER
			ACCESS	read-only
			STATUS	current
	DESCRIPTION ""
			::= { mbusE8 65 }

mbusE8VIF1E		OBJECT-TYPE
			SYNTAX	INTEGER
			ACCESS	read-only
			STATUS	current
	DESCRIPTION ""
			::= { mbusE8 66 }

mbusE8Value1E		OBJECT-TYPE
			SYNTAX	INTEGER
			ACCESS	read-only
			STATUS	current
	DESCRIPTION ""
			::= { mbusE8 67 }

mbusE8VIF1F		OBJECT-TYPE
			SYNTAX	INTEGER
			ACCESS	read-only
			STATUS	current
	DESCRIPTION ""
			::= { mbusE8 68 }

mbusE8Value1F		OBJECT-TYPE
			SYNTAX	INTEGER
			ACCESS	read-only
			STATUS	current
	DESCRIPTION ""
			::= { mbusE8 69 }

mbusE8VIF20		OBJECT-TYPE
			SYNTAX	INTEGER
			ACCESS	read-only
			STATUS	current
	DESCRIPTION ""
			::= { mbusE8 70 }

mbusE8Value20		OBJECT-TYPE
			SYNTAX	INTEGER
			ACCESS	read-only
			STATUS	current
	DESCRIPTION ""
			::= { mbusE8 71 }

mbusE8VIF21		OBJECT-TYPE
			SYNTAX	INTEGER
			ACCESS	read-only
			STATUS	current
	DESCRIPTION ""
			::= { mbusE8 72 }

mbusE8Value21		OBJECT-TYPE
			SYNTAX	INTEGER
			ACCESS	read-only
			STATUS	current
	DESCRIPTION ""
			::= { mbusE8 73 }

mbusE8VIF22		OBJECT-TYPE
			SYNTAX	INTEGER
			ACCESS	read-only
			STATUS	current
	DESCRIPTION ""
			::= { mbusE8 74 }

mbusE8Value22		OBJECT-TYPE
			SYNTAX	INTEGER
			ACCESS	read-only
			STATUS	current
	DESCRIPTION ""
			::= { mbusE8 75 }

mbusE8VIF23		OBJECT-TYPE
			SYNTAX	INTEGER
			ACCESS	read-only
			STATUS	current
	DESCRIPTION ""
			::= { mbusE8 76 }

mbusE8Value23		OBJECT-TYPE
			SYNTAX	INTEGER
			ACCESS	read-only
			STATUS	current
	DESCRIPTION ""
			::= { mbusE8 77 }

mbusE8VIF24		OBJECT-TYPE
			SYNTAX	INTEGER
			ACCESS	read-only
			STATUS	current
	DESCRIPTION ""
			::= { mbusE8 78 }

mbusE8Value24		OBJECT-TYPE
			SYNTAX	INTEGER
			ACCESS	read-only
			STATUS	current
	DESCRIPTION ""
			::= { mbusE8 79 }

mbusE8VIF25		OBJECT-TYPE
			SYNTAX	INTEGER
			ACCESS	read-only
			STATUS	current
	DESCRIPTION ""
			::= { mbusE8 80 }

mbusE8Value25		OBJECT-TYPE
			SYNTAX	INTEGER
			ACCESS	read-only
			STATUS	current
	DESCRIPTION ""
			::= { mbusE8 81 }

mbusE8VIF26		OBJECT-TYPE
			SYNTAX	INTEGER
			ACCESS	read-only
			STATUS	current
	DESCRIPTION ""
			::= { mbusE8 82 }

mbusE8Value26		OBJECT-TYPE
			SYNTAX	INTEGER
			ACCESS	read-only
			STATUS	current
	DESCRIPTION ""
			::= { mbusE8 83 }

mbusE8VIF27		OBJECT-TYPE
			SYNTAX	INTEGER
			ACCESS	read-only
			STATUS	current
	DESCRIPTION ""
			::= { mbusE8 84 }

mbusE8Value27		OBJECT-TYPE
			SYNTAX	INTEGER
			ACCESS	read-only
			STATUS	current
	DESCRIPTION ""
			::= { mbusE8 85 }

mbusE8VIF28		OBJECT-TYPE
			SYNTAX	INTEGER
			ACCESS	read-only
			STATUS	current
	DESCRIPTION ""
			::= { mbusE8 86 }

mbusE8Value28		OBJECT-TYPE
			SYNTAX	INTEGER
			ACCESS	read-only
			STATUS	current
	DESCRIPTION ""
			::= { mbusE8 87 }

mbusE8VIF29		OBJECT-TYPE
			SYNTAX	INTEGER
			ACCESS	read-only
			STATUS	current
	DESCRIPTION ""
			::= { mbusE8 88 }

mbusE8Value29		OBJECT-TYPE
			SYNTAX	INTEGER
			ACCESS	read-only
			STATUS	current
	DESCRIPTION ""
			::= { mbusE8 89 }

mbusE8VIF2A		OBJECT-TYPE
			SYNTAX	INTEGER
			ACCESS	read-only
			STATUS	current
	DESCRIPTION ""
			::= { mbusE8 90 }

mbusE8Value2A		OBJECT-TYPE
			SYNTAX	INTEGER
			ACCESS	read-only
			STATUS	current
	DESCRIPTION ""
			::= { mbusE8 91 }

mbusE8VIF2B		OBJECT-TYPE
			SYNTAX	INTEGER
			ACCESS	read-only
			STATUS	current
	DESCRIPTION ""
			::= { mbusE8 92 }

mbusE8Value2B		OBJECT-TYPE
			SYNTAX	INTEGER
			ACCESS	read-only
			STATUS	current
	DESCRIPTION ""
			::= { mbusE8 93 }

mbusE8VIF2C		OBJECT-TYPE
			SYNTAX	INTEGER
			ACCESS	read-only
			STATUS	current
	DESCRIPTION ""
			::= { mbusE8 94 }

mbusE8Value2C		OBJECT-TYPE
			SYNTAX	INTEGER
			ACCESS	read-only
			STATUS	current
	DESCRIPTION ""
			::= { mbusE8 95 }

mbusE8VIF2D		OBJECT-TYPE
			SYNTAX	INTEGER
			ACCESS	read-only
			STATUS	current
	DESCRIPTION ""
			::= { mbusE8 96 }

mbusE8Value2D		OBJECT-TYPE
			SYNTAX	INTEGER
			ACCESS	read-only
			STATUS	current
	DESCRIPTION ""
			::= { mbusE8 97 }

mbusE8VIF2E		OBJECT-TYPE
			SYNTAX	INTEGER
			ACCESS	read-only
			STATUS	current
	DESCRIPTION ""
			::= { mbusE8 98 }

mbusE8Value2E		OBJECT-TYPE
			SYNTAX	INTEGER
			ACCESS	read-only
			STATUS	current
	DESCRIPTION ""
			::= { mbusE8 99 }

mbusE8VIF2F		OBJECT-TYPE
			SYNTAX	INTEGER
			ACCESS	read-only
			STATUS	current
	DESCRIPTION ""
			::= { mbusE8 100 }

mbusE8Value2F		OBJECT-TYPE
			SYNTAX	INTEGER
			ACCESS	read-only
			STATUS	current
	DESCRIPTION ""
			::= { mbusE8 101 }

mbusE9			OBJECT IDENTIFIER ::= { mbus 233 }

mbusE9IdNumber		OBJECT-TYPE
			SYNTAX	Gauge
			ACCESS	read-only
			STATUS	current
	DESCRIPTION ""
			::= { mbusE9 1 }

mbusE9Manufacturer	OBJECT-TYPE
			SYNTAX	Gauge
			ACCESS	read-only
			STATUS	current
	DESCRIPTION ""
			::= { mbusE9 2 }

mbusE9Version		OBJECT-TYPE
			SYNTAX	Gauge
			ACCESS	read-only
			STATUS	current
	DESCRIPTION ""
			::= { mbusE9 3 }

mbusE9Medium		OBJECT-TYPE
			SYNTAX	Gauge
			ACCESS	read-only
			STATUS	current
	DESCRIPTION ""
			::= { mbusE9 4 }

mbusE9Status		OBJECT-TYPE
			SYNTAX	Gauge
			ACCESS	read-only
			STATUS	current
	DESCRIPTION ""
			::= { mbusE9 5 }

mbusE9VIF00		OBJECT-TYPE
			SYNTAX	INTEGER
			ACCESS	read-only
			STATUS	current
	DESCRIPTION ""
			::= { mbusE9 6 }

mbusE9Value00		OBJECT-TYPE
			SYNTAX	INTEGER
			ACCESS	read-only
			STATUS	current
	DESCRIPTION ""
			::= { mbusE9 7 }

mbusE9VIF01		OBJECT-TYPE
			SYNTAX	INTEGER
			ACCESS	read-only
			STATUS	current
	DESCRIPTION ""
			::= { mbusE9 8 }

mbusE9Value01		OBJECT-TYPE
			SYNTAX	INTEGER
			ACCESS	read-only
			STATUS	current
	DESCRIPTION ""
			::= { mbusE9 9 }

mbusE9VIF02		OBJECT-TYPE
			SYNTAX	INTEGER
			ACCESS	read-only
			STATUS	current
	DESCRIPTION ""
			::= { mbusE9 10 }

mbusE9Value02		OBJECT-TYPE
			SYNTAX	INTEGER
			ACCESS	read-only
			STATUS	current
	DESCRIPTION ""
			::= { mbusE9 11 }

mbusE9VIF03		OBJECT-TYPE
			SYNTAX	INTEGER
			ACCESS	read-only
			STATUS	current
	DESCRIPTION ""
			::= { mbusE9 12 }

mbusE9Value03		OBJECT-TYPE
			SYNTAX	INTEGER
			ACCESS	read-only
			STATUS	current
	DESCRIPTION ""
			::= { mbusE9 13 }

mbusE9VIF04		OBJECT-TYPE
			SYNTAX	INTEGER
			ACCESS	read-only
			STATUS	current
	DESCRIPTION ""
			::= { mbusE9 14 }

mbusE9Value04		OBJECT-TYPE
			SYNTAX	INTEGER
			ACCESS	read-only
			STATUS	current
	DESCRIPTION ""
			::= { mbusE9 15 }

mbusE9VIF05		OBJECT-TYPE
			SYNTAX	INTEGER
			ACCESS	read-only
			STATUS	current
	DESCRIPTION ""
			::= { mbusE9 16 }

mbusE9Value05		OBJECT-TYPE
			SYNTAX	INTEGER
			ACCESS	read-only
			STATUS	current
	DESCRIPTION ""
			::= { mbusE9 17 }

mbusE9VIF06		OBJECT-TYPE
			SYNTAX	INTEGER
			ACCESS	read-only
			STATUS	current
	DESCRIPTION ""
			::= { mbusE9 18 }

mbusE9Value06		OBJECT-TYPE
			SYNTAX	INTEGER
			ACCESS	read-only
			STATUS	current
	DESCRIPTION ""
			::= { mbusE9 19 }

mbusE9VIF07		OBJECT-TYPE
			SYNTAX	INTEGER
			ACCESS	read-only
			STATUS	current
	DESCRIPTION ""
			::= { mbusE9 20 }

mbusE9Value07		OBJECT-TYPE
			SYNTAX	INTEGER
			ACCESS	read-only
			STATUS	current
	DESCRIPTION ""
			::= { mbusE9 21 }

mbusE9VIF08		OBJECT-TYPE
			SYNTAX	INTEGER
			ACCESS	read-only
			STATUS	current
	DESCRIPTION ""
			::= { mbusE9 22 }

mbusE9Value08		OBJECT-TYPE
			SYNTAX	INTEGER
			ACCESS	read-only
			STATUS	current
	DESCRIPTION ""
			::= { mbusE9 23 }

mbusE9VIF09		OBJECT-TYPE
			SYNTAX	INTEGER
			ACCESS	read-only
			STATUS	current
	DESCRIPTION ""
			::= { mbusE9 24 }

mbusE9Value09		OBJECT-TYPE
			SYNTAX	INTEGER
			ACCESS	read-only
			STATUS	current
	DESCRIPTION ""
			::= { mbusE9 25 }

mbusE9VIF0A		OBJECT-TYPE
			SYNTAX	INTEGER
			ACCESS	read-only
			STATUS	current
	DESCRIPTION ""
			::= { mbusE9 26 }

mbusE9Value0A		OBJECT-TYPE
			SYNTAX	INTEGER
			ACCESS	read-only
			STATUS	current
	DESCRIPTION ""
			::= { mbusE9 27 }

mbusE9VIF0B		OBJECT-TYPE
			SYNTAX	INTEGER
			ACCESS	read-only
			STATUS	current
	DESCRIPTION ""
			::= { mbusE9 28 }

mbusE9Value0B		OBJECT-TYPE
			SYNTAX	INTEGER
			ACCESS	read-only
			STATUS	current
	DESCRIPTION ""
			::= { mbusE9 29 }

mbusE9VIF0C		OBJECT-TYPE
			SYNTAX	INTEGER
			ACCESS	read-only
			STATUS	current
	DESCRIPTION ""
			::= { mbusE9 30 }

mbusE9Value0C		OBJECT-TYPE
			SYNTAX	INTEGER
			ACCESS	read-only
			STATUS	current
	DESCRIPTION ""
			::= { mbusE9 31 }

mbusE9VIF0D		OBJECT-TYPE
			SYNTAX	INTEGER
			ACCESS	read-only
			STATUS	current
	DESCRIPTION ""
			::= { mbusE9 32 }

mbusE9Value0D		OBJECT-TYPE
			SYNTAX	INTEGER
			ACCESS	read-only
			STATUS	current
	DESCRIPTION ""
			::= { mbusE9 33 }

mbusE9VIF0E		OBJECT-TYPE
			SYNTAX	INTEGER
			ACCESS	read-only
			STATUS	current
	DESCRIPTION ""
			::= { mbusE9 34 }

mbusE9Value0E		OBJECT-TYPE
			SYNTAX	INTEGER
			ACCESS	read-only
			STATUS	current
	DESCRIPTION ""
			::= { mbusE9 35 }

mbusE9VIF0F		OBJECT-TYPE
			SYNTAX	INTEGER
			ACCESS	read-only
			STATUS	current
	DESCRIPTION ""
			::= { mbusE9 36 }

mbusE9Value0F		OBJECT-TYPE
			SYNTAX	INTEGER
			ACCESS	read-only
			STATUS	current
	DESCRIPTION ""
			::= { mbusE9 37 }

mbusE9VIF10		OBJECT-TYPE
			SYNTAX	INTEGER
			ACCESS	read-only
			STATUS	current
	DESCRIPTION ""
			::= { mbusE9 38 }

mbusE9Value10		OBJECT-TYPE
			SYNTAX	INTEGER
			ACCESS	read-only
			STATUS	current
	DESCRIPTION ""
			::= { mbusE9 39 }

mbusE9VIF11		OBJECT-TYPE
			SYNTAX	INTEGER
			ACCESS	read-only
			STATUS	current
	DESCRIPTION ""
			::= { mbusE9 40 }

mbusE9Value11		OBJECT-TYPE
			SYNTAX	INTEGER
			ACCESS	read-only
			STATUS	current
	DESCRIPTION ""
			::= { mbusE9 41 }

mbusE9VIF12		OBJECT-TYPE
			SYNTAX	INTEGER
			ACCESS	read-only
			STATUS	current
	DESCRIPTION ""
			::= { mbusE9 42 }

mbusE9Value12		OBJECT-TYPE
			SYNTAX	INTEGER
			ACCESS	read-only
			STATUS	current
	DESCRIPTION ""
			::= { mbusE9 43 }

mbusE9VIF13		OBJECT-TYPE
			SYNTAX	INTEGER
			ACCESS	read-only
			STATUS	current
	DESCRIPTION ""
			::= { mbusE9 44 }

mbusE9Value13		OBJECT-TYPE
			SYNTAX	INTEGER
			ACCESS	read-only
			STATUS	current
	DESCRIPTION ""
			::= { mbusE9 45 }

mbusE9VIF14		OBJECT-TYPE
			SYNTAX	INTEGER
			ACCESS	read-only
			STATUS	current
	DESCRIPTION ""
			::= { mbusE9 46 }

mbusE9Value14		OBJECT-TYPE
			SYNTAX	INTEGER
			ACCESS	read-only
			STATUS	current
	DESCRIPTION ""
			::= { mbusE9 47 }

mbusE9VIF15		OBJECT-TYPE
			SYNTAX	INTEGER
			ACCESS	read-only
			STATUS	current
	DESCRIPTION ""
			::= { mbusE9 48 }

mbusE9Value15		OBJECT-TYPE
			SYNTAX	INTEGER
			ACCESS	read-only
			STATUS	current
	DESCRIPTION ""
			::= { mbusE9 49 }

mbusE9VIF16		OBJECT-TYPE
			SYNTAX	INTEGER
			ACCESS	read-only
			STATUS	current
	DESCRIPTION ""
			::= { mbusE9 50 }

mbusE9Value16		OBJECT-TYPE
			SYNTAX	INTEGER
			ACCESS	read-only
			STATUS	current
	DESCRIPTION ""
			::= { mbusE9 51 }

mbusE9VIF17		OBJECT-TYPE
			SYNTAX	INTEGER
			ACCESS	read-only
			STATUS	current
	DESCRIPTION ""
			::= { mbusE9 52 }

mbusE9Value17		OBJECT-TYPE
			SYNTAX	INTEGER
			ACCESS	read-only
			STATUS	current
	DESCRIPTION ""
			::= { mbusE9 53 }

mbusE9VIF18		OBJECT-TYPE
			SYNTAX	INTEGER
			ACCESS	read-only
			STATUS	current
	DESCRIPTION ""
			::= { mbusE9 54 }

mbusE9Value18		OBJECT-TYPE
			SYNTAX	INTEGER
			ACCESS	read-only
			STATUS	current
	DESCRIPTION ""
			::= { mbusE9 55 }

mbusE9VIF19		OBJECT-TYPE
			SYNTAX	INTEGER
			ACCESS	read-only
			STATUS	current
	DESCRIPTION ""
			::= { mbusE9 56 }

mbusE9Value19		OBJECT-TYPE
			SYNTAX	INTEGER
			ACCESS	read-only
			STATUS	current
	DESCRIPTION ""
			::= { mbusE9 57 }

mbusE9VIF1A		OBJECT-TYPE
			SYNTAX	INTEGER
			ACCESS	read-only
			STATUS	current
	DESCRIPTION ""
			::= { mbusE9 58 }

mbusE9Value1A		OBJECT-TYPE
			SYNTAX	INTEGER
			ACCESS	read-only
			STATUS	current
	DESCRIPTION ""
			::= { mbusE9 59 }

mbusE9VIF1B		OBJECT-TYPE
			SYNTAX	INTEGER
			ACCESS	read-only
			STATUS	current
	DESCRIPTION ""
			::= { mbusE9 60 }

mbusE9Value1B		OBJECT-TYPE
			SYNTAX	INTEGER
			ACCESS	read-only
			STATUS	current
	DESCRIPTION ""
			::= { mbusE9 61 }

mbusE9VIF1C		OBJECT-TYPE
			SYNTAX	INTEGER
			ACCESS	read-only
			STATUS	current
	DESCRIPTION ""
			::= { mbusE9 62 }

mbusE9Value1C		OBJECT-TYPE
			SYNTAX	INTEGER
			ACCESS	read-only
			STATUS	current
	DESCRIPTION ""
			::= { mbusE9 63 }

mbusE9VIF1D		OBJECT-TYPE
			SYNTAX	INTEGER
			ACCESS	read-only
			STATUS	current
	DESCRIPTION ""
			::= { mbusE9 64 }

mbusE9Value1D		OBJECT-TYPE
			SYNTAX	INTEGER
			ACCESS	read-only
			STATUS	current
	DESCRIPTION ""
			::= { mbusE9 65 }

mbusE9VIF1E		OBJECT-TYPE
			SYNTAX	INTEGER
			ACCESS	read-only
			STATUS	current
	DESCRIPTION ""
			::= { mbusE9 66 }

mbusE9Value1E		OBJECT-TYPE
			SYNTAX	INTEGER
			ACCESS	read-only
			STATUS	current
	DESCRIPTION ""
			::= { mbusE9 67 }

mbusE9VIF1F		OBJECT-TYPE
			SYNTAX	INTEGER
			ACCESS	read-only
			STATUS	current
	DESCRIPTION ""
			::= { mbusE9 68 }

mbusE9Value1F		OBJECT-TYPE
			SYNTAX	INTEGER
			ACCESS	read-only
			STATUS	current
	DESCRIPTION ""
			::= { mbusE9 69 }

mbusE9VIF20		OBJECT-TYPE
			SYNTAX	INTEGER
			ACCESS	read-only
			STATUS	current
	DESCRIPTION ""
			::= { mbusE9 70 }

mbusE9Value20		OBJECT-TYPE
			SYNTAX	INTEGER
			ACCESS	read-only
			STATUS	current
	DESCRIPTION ""
			::= { mbusE9 71 }

mbusE9VIF21		OBJECT-TYPE
			SYNTAX	INTEGER
			ACCESS	read-only
			STATUS	current
	DESCRIPTION ""
			::= { mbusE9 72 }

mbusE9Value21		OBJECT-TYPE
			SYNTAX	INTEGER
			ACCESS	read-only
			STATUS	current
	DESCRIPTION ""
			::= { mbusE9 73 }

mbusE9VIF22		OBJECT-TYPE
			SYNTAX	INTEGER
			ACCESS	read-only
			STATUS	current
	DESCRIPTION ""
			::= { mbusE9 74 }

mbusE9Value22		OBJECT-TYPE
			SYNTAX	INTEGER
			ACCESS	read-only
			STATUS	current
	DESCRIPTION ""
			::= { mbusE9 75 }

mbusE9VIF23		OBJECT-TYPE
			SYNTAX	INTEGER
			ACCESS	read-only
			STATUS	current
	DESCRIPTION ""
			::= { mbusE9 76 }

mbusE9Value23		OBJECT-TYPE
			SYNTAX	INTEGER
			ACCESS	read-only
			STATUS	current
	DESCRIPTION ""
			::= { mbusE9 77 }

mbusE9VIF24		OBJECT-TYPE
			SYNTAX	INTEGER
			ACCESS	read-only
			STATUS	current
	DESCRIPTION ""
			::= { mbusE9 78 }

mbusE9Value24		OBJECT-TYPE
			SYNTAX	INTEGER
			ACCESS	read-only
			STATUS	current
	DESCRIPTION ""
			::= { mbusE9 79 }

mbusE9VIF25		OBJECT-TYPE
			SYNTAX	INTEGER
			ACCESS	read-only
			STATUS	current
	DESCRIPTION ""
			::= { mbusE9 80 }

mbusE9Value25		OBJECT-TYPE
			SYNTAX	INTEGER
			ACCESS	read-only
			STATUS	current
	DESCRIPTION ""
			::= { mbusE9 81 }

mbusE9VIF26		OBJECT-TYPE
			SYNTAX	INTEGER
			ACCESS	read-only
			STATUS	current
	DESCRIPTION ""
			::= { mbusE9 82 }

mbusE9Value26		OBJECT-TYPE
			SYNTAX	INTEGER
			ACCESS	read-only
			STATUS	current
	DESCRIPTION ""
			::= { mbusE9 83 }

mbusE9VIF27		OBJECT-TYPE
			SYNTAX	INTEGER
			ACCESS	read-only
			STATUS	current
	DESCRIPTION ""
			::= { mbusE9 84 }

mbusE9Value27		OBJECT-TYPE
			SYNTAX	INTEGER
			ACCESS	read-only
			STATUS	current
	DESCRIPTION ""
			::= { mbusE9 85 }

mbusE9VIF28		OBJECT-TYPE
			SYNTAX	INTEGER
			ACCESS	read-only
			STATUS	current
	DESCRIPTION ""
			::= { mbusE9 86 }

mbusE9Value28		OBJECT-TYPE
			SYNTAX	INTEGER
			ACCESS	read-only
			STATUS	current
	DESCRIPTION ""
			::= { mbusE9 87 }

mbusE9VIF29		OBJECT-TYPE
			SYNTAX	INTEGER
			ACCESS	read-only
			STATUS	current
	DESCRIPTION ""
			::= { mbusE9 88 }

mbusE9Value29		OBJECT-TYPE
			SYNTAX	INTEGER
			ACCESS	read-only
			STATUS	current
	DESCRIPTION ""
			::= { mbusE9 89 }

mbusE9VIF2A		OBJECT-TYPE
			SYNTAX	INTEGER
			ACCESS	read-only
			STATUS	current
	DESCRIPTION ""
			::= { mbusE9 90 }

mbusE9Value2A		OBJECT-TYPE
			SYNTAX	INTEGER
			ACCESS	read-only
			STATUS	current
	DESCRIPTION ""
			::= { mbusE9 91 }

mbusE9VIF2B		OBJECT-TYPE
			SYNTAX	INTEGER
			ACCESS	read-only
			STATUS	current
	DESCRIPTION ""
			::= { mbusE9 92 }

mbusE9Value2B		OBJECT-TYPE
			SYNTAX	INTEGER
			ACCESS	read-only
			STATUS	current
	DESCRIPTION ""
			::= { mbusE9 93 }

mbusE9VIF2C		OBJECT-TYPE
			SYNTAX	INTEGER
			ACCESS	read-only
			STATUS	current
	DESCRIPTION ""
			::= { mbusE9 94 }

mbusE9Value2C		OBJECT-TYPE
			SYNTAX	INTEGER
			ACCESS	read-only
			STATUS	current
	DESCRIPTION ""
			::= { mbusE9 95 }

mbusE9VIF2D		OBJECT-TYPE
			SYNTAX	INTEGER
			ACCESS	read-only
			STATUS	current
	DESCRIPTION ""
			::= { mbusE9 96 }

mbusE9Value2D		OBJECT-TYPE
			SYNTAX	INTEGER
			ACCESS	read-only
			STATUS	current
	DESCRIPTION ""
			::= { mbusE9 97 }

mbusE9VIF2E		OBJECT-TYPE
			SYNTAX	INTEGER
			ACCESS	read-only
			STATUS	current
	DESCRIPTION ""
			::= { mbusE9 98 }

mbusE9Value2E		OBJECT-TYPE
			SYNTAX	INTEGER
			ACCESS	read-only
			STATUS	current
	DESCRIPTION ""
			::= { mbusE9 99 }

mbusE9VIF2F		OBJECT-TYPE
			SYNTAX	INTEGER
			ACCESS	read-only
			STATUS	current
	DESCRIPTION ""
			::= { mbusE9 100 }

mbusE9Value2F		OBJECT-TYPE
			SYNTAX	INTEGER
			ACCESS	read-only
			STATUS	current
	DESCRIPTION ""
			::= { mbusE9 101 }

mbusEA			OBJECT IDENTIFIER ::= { mbus 234 }

mbusEAIdNumber		OBJECT-TYPE
			SYNTAX	Gauge
			ACCESS	read-only
			STATUS	current
	DESCRIPTION ""
			::= { mbusEA 1 }

mbusEAManufacturer	OBJECT-TYPE
			SYNTAX	Gauge
			ACCESS	read-only
			STATUS	current
	DESCRIPTION ""
			::= { mbusEA 2 }

mbusEAVersion		OBJECT-TYPE
			SYNTAX	Gauge
			ACCESS	read-only
			STATUS	current
	DESCRIPTION ""
			::= { mbusEA 3 }

mbusEAMedium		OBJECT-TYPE
			SYNTAX	Gauge
			ACCESS	read-only
			STATUS	current
	DESCRIPTION ""
			::= { mbusEA 4 }

mbusEAStatus		OBJECT-TYPE
			SYNTAX	Gauge
			ACCESS	read-only
			STATUS	current
	DESCRIPTION ""
			::= { mbusEA 5 }

mbusEAVIF00		OBJECT-TYPE
			SYNTAX	INTEGER
			ACCESS	read-only
			STATUS	current
	DESCRIPTION ""
			::= { mbusEA 6 }

mbusEAValue00		OBJECT-TYPE
			SYNTAX	INTEGER
			ACCESS	read-only
			STATUS	current
	DESCRIPTION ""
			::= { mbusEA 7 }

mbusEAVIF01		OBJECT-TYPE
			SYNTAX	INTEGER
			ACCESS	read-only
			STATUS	current
	DESCRIPTION ""
			::= { mbusEA 8 }

mbusEAValue01		OBJECT-TYPE
			SYNTAX	INTEGER
			ACCESS	read-only
			STATUS	current
	DESCRIPTION ""
			::= { mbusEA 9 }

mbusEAVIF02		OBJECT-TYPE
			SYNTAX	INTEGER
			ACCESS	read-only
			STATUS	current
	DESCRIPTION ""
			::= { mbusEA 10 }

mbusEAValue02		OBJECT-TYPE
			SYNTAX	INTEGER
			ACCESS	read-only
			STATUS	current
	DESCRIPTION ""
			::= { mbusEA 11 }

mbusEAVIF03		OBJECT-TYPE
			SYNTAX	INTEGER
			ACCESS	read-only
			STATUS	current
	DESCRIPTION ""
			::= { mbusEA 12 }

mbusEAValue03		OBJECT-TYPE
			SYNTAX	INTEGER
			ACCESS	read-only
			STATUS	current
	DESCRIPTION ""
			::= { mbusEA 13 }

mbusEAVIF04		OBJECT-TYPE
			SYNTAX	INTEGER
			ACCESS	read-only
			STATUS	current
	DESCRIPTION ""
			::= { mbusEA 14 }

mbusEAValue04		OBJECT-TYPE
			SYNTAX	INTEGER
			ACCESS	read-only
			STATUS	current
	DESCRIPTION ""
			::= { mbusEA 15 }

mbusEAVIF05		OBJECT-TYPE
			SYNTAX	INTEGER
			ACCESS	read-only
			STATUS	current
	DESCRIPTION ""
			::= { mbusEA 16 }

mbusEAValue05		OBJECT-TYPE
			SYNTAX	INTEGER
			ACCESS	read-only
			STATUS	current
	DESCRIPTION ""
			::= { mbusEA 17 }

mbusEAVIF06		OBJECT-TYPE
			SYNTAX	INTEGER
			ACCESS	read-only
			STATUS	current
	DESCRIPTION ""
			::= { mbusEA 18 }

mbusEAValue06		OBJECT-TYPE
			SYNTAX	INTEGER
			ACCESS	read-only
			STATUS	current
	DESCRIPTION ""
			::= { mbusEA 19 }

mbusEAVIF07		OBJECT-TYPE
			SYNTAX	INTEGER
			ACCESS	read-only
			STATUS	current
	DESCRIPTION ""
			::= { mbusEA 20 }

mbusEAValue07		OBJECT-TYPE
			SYNTAX	INTEGER
			ACCESS	read-only
			STATUS	current
	DESCRIPTION ""
			::= { mbusEA 21 }

mbusEAVIF08		OBJECT-TYPE
			SYNTAX	INTEGER
			ACCESS	read-only
			STATUS	current
	DESCRIPTION ""
			::= { mbusEA 22 }

mbusEAValue08		OBJECT-TYPE
			SYNTAX	INTEGER
			ACCESS	read-only
			STATUS	current
	DESCRIPTION ""
			::= { mbusEA 23 }

mbusEAVIF09		OBJECT-TYPE
			SYNTAX	INTEGER
			ACCESS	read-only
			STATUS	current
	DESCRIPTION ""
			::= { mbusEA 24 }

mbusEAValue09		OBJECT-TYPE
			SYNTAX	INTEGER
			ACCESS	read-only
			STATUS	current
	DESCRIPTION ""
			::= { mbusEA 25 }

mbusEAVIF0A		OBJECT-TYPE
			SYNTAX	INTEGER
			ACCESS	read-only
			STATUS	current
	DESCRIPTION ""
			::= { mbusEA 26 }

mbusEAValue0A		OBJECT-TYPE
			SYNTAX	INTEGER
			ACCESS	read-only
			STATUS	current
	DESCRIPTION ""
			::= { mbusEA 27 }

mbusEAVIF0B		OBJECT-TYPE
			SYNTAX	INTEGER
			ACCESS	read-only
			STATUS	current
	DESCRIPTION ""
			::= { mbusEA 28 }

mbusEAValue0B		OBJECT-TYPE
			SYNTAX	INTEGER
			ACCESS	read-only
			STATUS	current
	DESCRIPTION ""
			::= { mbusEA 29 }

mbusEAVIF0C		OBJECT-TYPE
			SYNTAX	INTEGER
			ACCESS	read-only
			STATUS	current
	DESCRIPTION ""
			::= { mbusEA 30 }

mbusEAValue0C		OBJECT-TYPE
			SYNTAX	INTEGER
			ACCESS	read-only
			STATUS	current
	DESCRIPTION ""
			::= { mbusEA 31 }

mbusEAVIF0D		OBJECT-TYPE
			SYNTAX	INTEGER
			ACCESS	read-only
			STATUS	current
	DESCRIPTION ""
			::= { mbusEA 32 }

mbusEAValue0D		OBJECT-TYPE
			SYNTAX	INTEGER
			ACCESS	read-only
			STATUS	current
	DESCRIPTION ""
			::= { mbusEA 33 }

mbusEAVIF0E		OBJECT-TYPE
			SYNTAX	INTEGER
			ACCESS	read-only
			STATUS	current
	DESCRIPTION ""
			::= { mbusEA 34 }

mbusEAValue0E		OBJECT-TYPE
			SYNTAX	INTEGER
			ACCESS	read-only
			STATUS	current
	DESCRIPTION ""
			::= { mbusEA 35 }

mbusEAVIF0F		OBJECT-TYPE
			SYNTAX	INTEGER
			ACCESS	read-only
			STATUS	current
	DESCRIPTION ""
			::= { mbusEA 36 }

mbusEAValue0F		OBJECT-TYPE
			SYNTAX	INTEGER
			ACCESS	read-only
			STATUS	current
	DESCRIPTION ""
			::= { mbusEA 37 }

mbusEAVIF10		OBJECT-TYPE
			SYNTAX	INTEGER
			ACCESS	read-only
			STATUS	current
	DESCRIPTION ""
			::= { mbusEA 38 }

mbusEAValue10		OBJECT-TYPE
			SYNTAX	INTEGER
			ACCESS	read-only
			STATUS	current
	DESCRIPTION ""
			::= { mbusEA 39 }

mbusEAVIF11		OBJECT-TYPE
			SYNTAX	INTEGER
			ACCESS	read-only
			STATUS	current
	DESCRIPTION ""
			::= { mbusEA 40 }

mbusEAValue11		OBJECT-TYPE
			SYNTAX	INTEGER
			ACCESS	read-only
			STATUS	current
	DESCRIPTION ""
			::= { mbusEA 41 }

mbusEAVIF12		OBJECT-TYPE
			SYNTAX	INTEGER
			ACCESS	read-only
			STATUS	current
	DESCRIPTION ""
			::= { mbusEA 42 }

mbusEAValue12		OBJECT-TYPE
			SYNTAX	INTEGER
			ACCESS	read-only
			STATUS	current
	DESCRIPTION ""
			::= { mbusEA 43 }

mbusEAVIF13		OBJECT-TYPE
			SYNTAX	INTEGER
			ACCESS	read-only
			STATUS	current
	DESCRIPTION ""
			::= { mbusEA 44 }

mbusEAValue13		OBJECT-TYPE
			SYNTAX	INTEGER
			ACCESS	read-only
			STATUS	current
	DESCRIPTION ""
			::= { mbusEA 45 }

mbusEAVIF14		OBJECT-TYPE
			SYNTAX	INTEGER
			ACCESS	read-only
			STATUS	current
	DESCRIPTION ""
			::= { mbusEA 46 }

mbusEAValue14		OBJECT-TYPE
			SYNTAX	INTEGER
			ACCESS	read-only
			STATUS	current
	DESCRIPTION ""
			::= { mbusEA 47 }

mbusEAVIF15		OBJECT-TYPE
			SYNTAX	INTEGER
			ACCESS	read-only
			STATUS	current
	DESCRIPTION ""
			::= { mbusEA 48 }

mbusEAValue15		OBJECT-TYPE
			SYNTAX	INTEGER
			ACCESS	read-only
			STATUS	current
	DESCRIPTION ""
			::= { mbusEA 49 }

mbusEAVIF16		OBJECT-TYPE
			SYNTAX	INTEGER
			ACCESS	read-only
			STATUS	current
	DESCRIPTION ""
			::= { mbusEA 50 }

mbusEAValue16		OBJECT-TYPE
			SYNTAX	INTEGER
			ACCESS	read-only
			STATUS	current
	DESCRIPTION ""
			::= { mbusEA 51 }

mbusEAVIF17		OBJECT-TYPE
			SYNTAX	INTEGER
			ACCESS	read-only
			STATUS	current
	DESCRIPTION ""
			::= { mbusEA 52 }

mbusEAValue17		OBJECT-TYPE
			SYNTAX	INTEGER
			ACCESS	read-only
			STATUS	current
	DESCRIPTION ""
			::= { mbusEA 53 }

mbusEAVIF18		OBJECT-TYPE
			SYNTAX	INTEGER
			ACCESS	read-only
			STATUS	current
	DESCRIPTION ""
			::= { mbusEA 54 }

mbusEAValue18		OBJECT-TYPE
			SYNTAX	INTEGER
			ACCESS	read-only
			STATUS	current
	DESCRIPTION ""
			::= { mbusEA 55 }

mbusEAVIF19		OBJECT-TYPE
			SYNTAX	INTEGER
			ACCESS	read-only
			STATUS	current
	DESCRIPTION ""
			::= { mbusEA 56 }

mbusEAValue19		OBJECT-TYPE
			SYNTAX	INTEGER
			ACCESS	read-only
			STATUS	current
	DESCRIPTION ""
			::= { mbusEA 57 }

mbusEAVIF1A		OBJECT-TYPE
			SYNTAX	INTEGER
			ACCESS	read-only
			STATUS	current
	DESCRIPTION ""
			::= { mbusEA 58 }

mbusEAValue1A		OBJECT-TYPE
			SYNTAX	INTEGER
			ACCESS	read-only
			STATUS	current
	DESCRIPTION ""
			::= { mbusEA 59 }

mbusEAVIF1B		OBJECT-TYPE
			SYNTAX	INTEGER
			ACCESS	read-only
			STATUS	current
	DESCRIPTION ""
			::= { mbusEA 60 }

mbusEAValue1B		OBJECT-TYPE
			SYNTAX	INTEGER
			ACCESS	read-only
			STATUS	current
	DESCRIPTION ""
			::= { mbusEA 61 }

mbusEAVIF1C		OBJECT-TYPE
			SYNTAX	INTEGER
			ACCESS	read-only
			STATUS	current
	DESCRIPTION ""
			::= { mbusEA 62 }

mbusEAValue1C		OBJECT-TYPE
			SYNTAX	INTEGER
			ACCESS	read-only
			STATUS	current
	DESCRIPTION ""
			::= { mbusEA 63 }

mbusEAVIF1D		OBJECT-TYPE
			SYNTAX	INTEGER
			ACCESS	read-only
			STATUS	current
	DESCRIPTION ""
			::= { mbusEA 64 }

mbusEAValue1D		OBJECT-TYPE
			SYNTAX	INTEGER
			ACCESS	read-only
			STATUS	current
	DESCRIPTION ""
			::= { mbusEA 65 }

mbusEAVIF1E		OBJECT-TYPE
			SYNTAX	INTEGER
			ACCESS	read-only
			STATUS	current
	DESCRIPTION ""
			::= { mbusEA 66 }

mbusEAValue1E		OBJECT-TYPE
			SYNTAX	INTEGER
			ACCESS	read-only
			STATUS	current
	DESCRIPTION ""
			::= { mbusEA 67 }

mbusEAVIF1F		OBJECT-TYPE
			SYNTAX	INTEGER
			ACCESS	read-only
			STATUS	current
	DESCRIPTION ""
			::= { mbusEA 68 }

mbusEAValue1F		OBJECT-TYPE
			SYNTAX	INTEGER
			ACCESS	read-only
			STATUS	current
	DESCRIPTION ""
			::= { mbusEA 69 }

mbusEAVIF20		OBJECT-TYPE
			SYNTAX	INTEGER
			ACCESS	read-only
			STATUS	current
	DESCRIPTION ""
			::= { mbusEA 70 }

mbusEAValue20		OBJECT-TYPE
			SYNTAX	INTEGER
			ACCESS	read-only
			STATUS	current
	DESCRIPTION ""
			::= { mbusEA 71 }

mbusEAVIF21		OBJECT-TYPE
			SYNTAX	INTEGER
			ACCESS	read-only
			STATUS	current
	DESCRIPTION ""
			::= { mbusEA 72 }

mbusEAValue21		OBJECT-TYPE
			SYNTAX	INTEGER
			ACCESS	read-only
			STATUS	current
	DESCRIPTION ""
			::= { mbusEA 73 }

mbusEAVIF22		OBJECT-TYPE
			SYNTAX	INTEGER
			ACCESS	read-only
			STATUS	current
	DESCRIPTION ""
			::= { mbusEA 74 }

mbusEAValue22		OBJECT-TYPE
			SYNTAX	INTEGER
			ACCESS	read-only
			STATUS	current
	DESCRIPTION ""
			::= { mbusEA 75 }

mbusEAVIF23		OBJECT-TYPE
			SYNTAX	INTEGER
			ACCESS	read-only
			STATUS	current
	DESCRIPTION ""
			::= { mbusEA 76 }

mbusEAValue23		OBJECT-TYPE
			SYNTAX	INTEGER
			ACCESS	read-only
			STATUS	current
	DESCRIPTION ""
			::= { mbusEA 77 }

mbusEAVIF24		OBJECT-TYPE
			SYNTAX	INTEGER
			ACCESS	read-only
			STATUS	current
	DESCRIPTION ""
			::= { mbusEA 78 }

mbusEAValue24		OBJECT-TYPE
			SYNTAX	INTEGER
			ACCESS	read-only
			STATUS	current
	DESCRIPTION ""
			::= { mbusEA 79 }

mbusEAVIF25		OBJECT-TYPE
			SYNTAX	INTEGER
			ACCESS	read-only
			STATUS	current
	DESCRIPTION ""
			::= { mbusEA 80 }

mbusEAValue25		OBJECT-TYPE
			SYNTAX	INTEGER
			ACCESS	read-only
			STATUS	current
	DESCRIPTION ""
			::= { mbusEA 81 }

mbusEAVIF26		OBJECT-TYPE
			SYNTAX	INTEGER
			ACCESS	read-only
			STATUS	current
	DESCRIPTION ""
			::= { mbusEA 82 }

mbusEAValue26		OBJECT-TYPE
			SYNTAX	INTEGER
			ACCESS	read-only
			STATUS	current
	DESCRIPTION ""
			::= { mbusEA 83 }

mbusEAVIF27		OBJECT-TYPE
			SYNTAX	INTEGER
			ACCESS	read-only
			STATUS	current
	DESCRIPTION ""
			::= { mbusEA 84 }

mbusEAValue27		OBJECT-TYPE
			SYNTAX	INTEGER
			ACCESS	read-only
			STATUS	current
	DESCRIPTION ""
			::= { mbusEA 85 }

mbusEAVIF28		OBJECT-TYPE
			SYNTAX	INTEGER
			ACCESS	read-only
			STATUS	current
	DESCRIPTION ""
			::= { mbusEA 86 }

mbusEAValue28		OBJECT-TYPE
			SYNTAX	INTEGER
			ACCESS	read-only
			STATUS	current
	DESCRIPTION ""
			::= { mbusEA 87 }

mbusEAVIF29		OBJECT-TYPE
			SYNTAX	INTEGER
			ACCESS	read-only
			STATUS	current
	DESCRIPTION ""
			::= { mbusEA 88 }

mbusEAValue29		OBJECT-TYPE
			SYNTAX	INTEGER
			ACCESS	read-only
			STATUS	current
	DESCRIPTION ""
			::= { mbusEA 89 }

mbusEAVIF2A		OBJECT-TYPE
			SYNTAX	INTEGER
			ACCESS	read-only
			STATUS	current
	DESCRIPTION ""
			::= { mbusEA 90 }

mbusEAValue2A		OBJECT-TYPE
			SYNTAX	INTEGER
			ACCESS	read-only
			STATUS	current
	DESCRIPTION ""
			::= { mbusEA 91 }

mbusEAVIF2B		OBJECT-TYPE
			SYNTAX	INTEGER
			ACCESS	read-only
			STATUS	current
	DESCRIPTION ""
			::= { mbusEA 92 }

mbusEAValue2B		OBJECT-TYPE
			SYNTAX	INTEGER
			ACCESS	read-only
			STATUS	current
	DESCRIPTION ""
			::= { mbusEA 93 }

mbusEAVIF2C		OBJECT-TYPE
			SYNTAX	INTEGER
			ACCESS	read-only
			STATUS	current
	DESCRIPTION ""
			::= { mbusEA 94 }

mbusEAValue2C		OBJECT-TYPE
			SYNTAX	INTEGER
			ACCESS	read-only
			STATUS	current
	DESCRIPTION ""
			::= { mbusEA 95 }

mbusEAVIF2D		OBJECT-TYPE
			SYNTAX	INTEGER
			ACCESS	read-only
			STATUS	current
	DESCRIPTION ""
			::= { mbusEA 96 }

mbusEAValue2D		OBJECT-TYPE
			SYNTAX	INTEGER
			ACCESS	read-only
			STATUS	current
	DESCRIPTION ""
			::= { mbusEA 97 }

mbusEAVIF2E		OBJECT-TYPE
			SYNTAX	INTEGER
			ACCESS	read-only
			STATUS	current
	DESCRIPTION ""
			::= { mbusEA 98 }

mbusEAValue2E		OBJECT-TYPE
			SYNTAX	INTEGER
			ACCESS	read-only
			STATUS	current
	DESCRIPTION ""
			::= { mbusEA 99 }

mbusEAVIF2F		OBJECT-TYPE
			SYNTAX	INTEGER
			ACCESS	read-only
			STATUS	current
	DESCRIPTION ""
			::= { mbusEA 100 }

mbusEAValue2F		OBJECT-TYPE
			SYNTAX	INTEGER
			ACCESS	read-only
			STATUS	current
	DESCRIPTION ""
			::= { mbusEA 101 }

mbusEB			OBJECT IDENTIFIER ::= { mbus 235 }

mbusEBIdNumber		OBJECT-TYPE
			SYNTAX	Gauge
			ACCESS	read-only
			STATUS	current
	DESCRIPTION ""
			::= { mbusEB 1 }

mbusEBManufacturer	OBJECT-TYPE
			SYNTAX	Gauge
			ACCESS	read-only
			STATUS	current
	DESCRIPTION ""
			::= { mbusEB 2 }

mbusEBVersion		OBJECT-TYPE
			SYNTAX	Gauge
			ACCESS	read-only
			STATUS	current
	DESCRIPTION ""
			::= { mbusEB 3 }

mbusEBMedium		OBJECT-TYPE
			SYNTAX	Gauge
			ACCESS	read-only
			STATUS	current
	DESCRIPTION ""
			::= { mbusEB 4 }

mbusEBStatus		OBJECT-TYPE
			SYNTAX	Gauge
			ACCESS	read-only
			STATUS	current
	DESCRIPTION ""
			::= { mbusEB 5 }

mbusEBVIF00		OBJECT-TYPE
			SYNTAX	INTEGER
			ACCESS	read-only
			STATUS	current
	DESCRIPTION ""
			::= { mbusEB 6 }

mbusEBValue00		OBJECT-TYPE
			SYNTAX	INTEGER
			ACCESS	read-only
			STATUS	current
	DESCRIPTION ""
			::= { mbusEB 7 }

mbusEBVIF01		OBJECT-TYPE
			SYNTAX	INTEGER
			ACCESS	read-only
			STATUS	current
	DESCRIPTION ""
			::= { mbusEB 8 }

mbusEBValue01		OBJECT-TYPE
			SYNTAX	INTEGER
			ACCESS	read-only
			STATUS	current
	DESCRIPTION ""
			::= { mbusEB 9 }

mbusEBVIF02		OBJECT-TYPE
			SYNTAX	INTEGER
			ACCESS	read-only
			STATUS	current
	DESCRIPTION ""
			::= { mbusEB 10 }

mbusEBValue02		OBJECT-TYPE
			SYNTAX	INTEGER
			ACCESS	read-only
			STATUS	current
	DESCRIPTION ""
			::= { mbusEB 11 }

mbusEBVIF03		OBJECT-TYPE
			SYNTAX	INTEGER
			ACCESS	read-only
			STATUS	current
	DESCRIPTION ""
			::= { mbusEB 12 }

mbusEBValue03		OBJECT-TYPE
			SYNTAX	INTEGER
			ACCESS	read-only
			STATUS	current
	DESCRIPTION ""
			::= { mbusEB 13 }

mbusEBVIF04		OBJECT-TYPE
			SYNTAX	INTEGER
			ACCESS	read-only
			STATUS	current
	DESCRIPTION ""
			::= { mbusEB 14 }

mbusEBValue04		OBJECT-TYPE
			SYNTAX	INTEGER
			ACCESS	read-only
			STATUS	current
	DESCRIPTION ""
			::= { mbusEB 15 }

mbusEBVIF05		OBJECT-TYPE
			SYNTAX	INTEGER
			ACCESS	read-only
			STATUS	current
	DESCRIPTION ""
			::= { mbusEB 16 }

mbusEBValue05		OBJECT-TYPE
			SYNTAX	INTEGER
			ACCESS	read-only
			STATUS	current
	DESCRIPTION ""
			::= { mbusEB 17 }

mbusEBVIF06		OBJECT-TYPE
			SYNTAX	INTEGER
			ACCESS	read-only
			STATUS	current
	DESCRIPTION ""
			::= { mbusEB 18 }

mbusEBValue06		OBJECT-TYPE
			SYNTAX	INTEGER
			ACCESS	read-only
			STATUS	current
	DESCRIPTION ""
			::= { mbusEB 19 }

mbusEBVIF07		OBJECT-TYPE
			SYNTAX	INTEGER
			ACCESS	read-only
			STATUS	current
	DESCRIPTION ""
			::= { mbusEB 20 }

mbusEBValue07		OBJECT-TYPE
			SYNTAX	INTEGER
			ACCESS	read-only
			STATUS	current
	DESCRIPTION ""
			::= { mbusEB 21 }

mbusEBVIF08		OBJECT-TYPE
			SYNTAX	INTEGER
			ACCESS	read-only
			STATUS	current
	DESCRIPTION ""
			::= { mbusEB 22 }

mbusEBValue08		OBJECT-TYPE
			SYNTAX	INTEGER
			ACCESS	read-only
			STATUS	current
	DESCRIPTION ""
			::= { mbusEB 23 }

mbusEBVIF09		OBJECT-TYPE
			SYNTAX	INTEGER
			ACCESS	read-only
			STATUS	current
	DESCRIPTION ""
			::= { mbusEB 24 }

mbusEBValue09		OBJECT-TYPE
			SYNTAX	INTEGER
			ACCESS	read-only
			STATUS	current
	DESCRIPTION ""
			::= { mbusEB 25 }

mbusEBVIF0A		OBJECT-TYPE
			SYNTAX	INTEGER
			ACCESS	read-only
			STATUS	current
	DESCRIPTION ""
			::= { mbusEB 26 }

mbusEBValue0A		OBJECT-TYPE
			SYNTAX	INTEGER
			ACCESS	read-only
			STATUS	current
	DESCRIPTION ""
			::= { mbusEB 27 }

mbusEBVIF0B		OBJECT-TYPE
			SYNTAX	INTEGER
			ACCESS	read-only
			STATUS	current
	DESCRIPTION ""
			::= { mbusEB 28 }

mbusEBValue0B		OBJECT-TYPE
			SYNTAX	INTEGER
			ACCESS	read-only
			STATUS	current
	DESCRIPTION ""
			::= { mbusEB 29 }

mbusEBVIF0C		OBJECT-TYPE
			SYNTAX	INTEGER
			ACCESS	read-only
			STATUS	current
	DESCRIPTION ""
			::= { mbusEB 30 }

mbusEBValue0C		OBJECT-TYPE
			SYNTAX	INTEGER
			ACCESS	read-only
			STATUS	current
	DESCRIPTION ""
			::= { mbusEB 31 }

mbusEBVIF0D		OBJECT-TYPE
			SYNTAX	INTEGER
			ACCESS	read-only
			STATUS	current
	DESCRIPTION ""
			::= { mbusEB 32 }

mbusEBValue0D		OBJECT-TYPE
			SYNTAX	INTEGER
			ACCESS	read-only
			STATUS	current
	DESCRIPTION ""
			::= { mbusEB 33 }

mbusEBVIF0E		OBJECT-TYPE
			SYNTAX	INTEGER
			ACCESS	read-only
			STATUS	current
	DESCRIPTION ""
			::= { mbusEB 34 }

mbusEBValue0E		OBJECT-TYPE
			SYNTAX	INTEGER
			ACCESS	read-only
			STATUS	current
	DESCRIPTION ""
			::= { mbusEB 35 }

mbusEBVIF0F		OBJECT-TYPE
			SYNTAX	INTEGER
			ACCESS	read-only
			STATUS	current
	DESCRIPTION ""
			::= { mbusEB 36 }

mbusEBValue0F		OBJECT-TYPE
			SYNTAX	INTEGER
			ACCESS	read-only
			STATUS	current
	DESCRIPTION ""
			::= { mbusEB 37 }

mbusEBVIF10		OBJECT-TYPE
			SYNTAX	INTEGER
			ACCESS	read-only
			STATUS	current
	DESCRIPTION ""
			::= { mbusEB 38 }

mbusEBValue10		OBJECT-TYPE
			SYNTAX	INTEGER
			ACCESS	read-only
			STATUS	current
	DESCRIPTION ""
			::= { mbusEB 39 }

mbusEBVIF11		OBJECT-TYPE
			SYNTAX	INTEGER
			ACCESS	read-only
			STATUS	current
	DESCRIPTION ""
			::= { mbusEB 40 }

mbusEBValue11		OBJECT-TYPE
			SYNTAX	INTEGER
			ACCESS	read-only
			STATUS	current
	DESCRIPTION ""
			::= { mbusEB 41 }

mbusEBVIF12		OBJECT-TYPE
			SYNTAX	INTEGER
			ACCESS	read-only
			STATUS	current
	DESCRIPTION ""
			::= { mbusEB 42 }

mbusEBValue12		OBJECT-TYPE
			SYNTAX	INTEGER
			ACCESS	read-only
			STATUS	current
	DESCRIPTION ""
			::= { mbusEB 43 }

mbusEBVIF13		OBJECT-TYPE
			SYNTAX	INTEGER
			ACCESS	read-only
			STATUS	current
	DESCRIPTION ""
			::= { mbusEB 44 }

mbusEBValue13		OBJECT-TYPE
			SYNTAX	INTEGER
			ACCESS	read-only
			STATUS	current
	DESCRIPTION ""
			::= { mbusEB 45 }

mbusEBVIF14		OBJECT-TYPE
			SYNTAX	INTEGER
			ACCESS	read-only
			STATUS	current
	DESCRIPTION ""
			::= { mbusEB 46 }

mbusEBValue14		OBJECT-TYPE
			SYNTAX	INTEGER
			ACCESS	read-only
			STATUS	current
	DESCRIPTION ""
			::= { mbusEB 47 }

mbusEBVIF15		OBJECT-TYPE
			SYNTAX	INTEGER
			ACCESS	read-only
			STATUS	current
	DESCRIPTION ""
			::= { mbusEB 48 }

mbusEBValue15		OBJECT-TYPE
			SYNTAX	INTEGER
			ACCESS	read-only
			STATUS	current
	DESCRIPTION ""
			::= { mbusEB 49 }

mbusEBVIF16		OBJECT-TYPE
			SYNTAX	INTEGER
			ACCESS	read-only
			STATUS	current
	DESCRIPTION ""
			::= { mbusEB 50 }

mbusEBValue16		OBJECT-TYPE
			SYNTAX	INTEGER
			ACCESS	read-only
			STATUS	current
	DESCRIPTION ""
			::= { mbusEB 51 }

mbusEBVIF17		OBJECT-TYPE
			SYNTAX	INTEGER
			ACCESS	read-only
			STATUS	current
	DESCRIPTION ""
			::= { mbusEB 52 }

mbusEBValue17		OBJECT-TYPE
			SYNTAX	INTEGER
			ACCESS	read-only
			STATUS	current
	DESCRIPTION ""
			::= { mbusEB 53 }

mbusEBVIF18		OBJECT-TYPE
			SYNTAX	INTEGER
			ACCESS	read-only
			STATUS	current
	DESCRIPTION ""
			::= { mbusEB 54 }

mbusEBValue18		OBJECT-TYPE
			SYNTAX	INTEGER
			ACCESS	read-only
			STATUS	current
	DESCRIPTION ""
			::= { mbusEB 55 }

mbusEBVIF19		OBJECT-TYPE
			SYNTAX	INTEGER
			ACCESS	read-only
			STATUS	current
	DESCRIPTION ""
			::= { mbusEB 56 }

mbusEBValue19		OBJECT-TYPE
			SYNTAX	INTEGER
			ACCESS	read-only
			STATUS	current
	DESCRIPTION ""
			::= { mbusEB 57 }

mbusEBVIF1A		OBJECT-TYPE
			SYNTAX	INTEGER
			ACCESS	read-only
			STATUS	current
	DESCRIPTION ""
			::= { mbusEB 58 }

mbusEBValue1A		OBJECT-TYPE
			SYNTAX	INTEGER
			ACCESS	read-only
			STATUS	current
	DESCRIPTION ""
			::= { mbusEB 59 }

mbusEBVIF1B		OBJECT-TYPE
			SYNTAX	INTEGER
			ACCESS	read-only
			STATUS	current
	DESCRIPTION ""
			::= { mbusEB 60 }

mbusEBValue1B		OBJECT-TYPE
			SYNTAX	INTEGER
			ACCESS	read-only
			STATUS	current
	DESCRIPTION ""
			::= { mbusEB 61 }

mbusEBVIF1C		OBJECT-TYPE
			SYNTAX	INTEGER
			ACCESS	read-only
			STATUS	current
	DESCRIPTION ""
			::= { mbusEB 62 }

mbusEBValue1C		OBJECT-TYPE
			SYNTAX	INTEGER
			ACCESS	read-only
			STATUS	current
	DESCRIPTION ""
			::= { mbusEB 63 }

mbusEBVIF1D		OBJECT-TYPE
			SYNTAX	INTEGER
			ACCESS	read-only
			STATUS	current
	DESCRIPTION ""
			::= { mbusEB 64 }

mbusEBValue1D		OBJECT-TYPE
			SYNTAX	INTEGER
			ACCESS	read-only
			STATUS	current
	DESCRIPTION ""
			::= { mbusEB 65 }

mbusEBVIF1E		OBJECT-TYPE
			SYNTAX	INTEGER
			ACCESS	read-only
			STATUS	current
	DESCRIPTION ""
			::= { mbusEB 66 }

mbusEBValue1E		OBJECT-TYPE
			SYNTAX	INTEGER
			ACCESS	read-only
			STATUS	current
	DESCRIPTION ""
			::= { mbusEB 67 }

mbusEBVIF1F		OBJECT-TYPE
			SYNTAX	INTEGER
			ACCESS	read-only
			STATUS	current
	DESCRIPTION ""
			::= { mbusEB 68 }

mbusEBValue1F		OBJECT-TYPE
			SYNTAX	INTEGER
			ACCESS	read-only
			STATUS	current
	DESCRIPTION ""
			::= { mbusEB 69 }

mbusEBVIF20		OBJECT-TYPE
			SYNTAX	INTEGER
			ACCESS	read-only
			STATUS	current
	DESCRIPTION ""
			::= { mbusEB 70 }

mbusEBValue20		OBJECT-TYPE
			SYNTAX	INTEGER
			ACCESS	read-only
			STATUS	current
	DESCRIPTION ""
			::= { mbusEB 71 }

mbusEBVIF21		OBJECT-TYPE
			SYNTAX	INTEGER
			ACCESS	read-only
			STATUS	current
	DESCRIPTION ""
			::= { mbusEB 72 }

mbusEBValue21		OBJECT-TYPE
			SYNTAX	INTEGER
			ACCESS	read-only
			STATUS	current
	DESCRIPTION ""
			::= { mbusEB 73 }

mbusEBVIF22		OBJECT-TYPE
			SYNTAX	INTEGER
			ACCESS	read-only
			STATUS	current
	DESCRIPTION ""
			::= { mbusEB 74 }

mbusEBValue22		OBJECT-TYPE
			SYNTAX	INTEGER
			ACCESS	read-only
			STATUS	current
	DESCRIPTION ""
			::= { mbusEB 75 }

mbusEBVIF23		OBJECT-TYPE
			SYNTAX	INTEGER
			ACCESS	read-only
			STATUS	current
	DESCRIPTION ""
			::= { mbusEB 76 }

mbusEBValue23		OBJECT-TYPE
			SYNTAX	INTEGER
			ACCESS	read-only
			STATUS	current
	DESCRIPTION ""
			::= { mbusEB 77 }

mbusEBVIF24		OBJECT-TYPE
			SYNTAX	INTEGER
			ACCESS	read-only
			STATUS	current
	DESCRIPTION ""
			::= { mbusEB 78 }

mbusEBValue24		OBJECT-TYPE
			SYNTAX	INTEGER
			ACCESS	read-only
			STATUS	current
	DESCRIPTION ""
			::= { mbusEB 79 }

mbusEBVIF25		OBJECT-TYPE
			SYNTAX	INTEGER
			ACCESS	read-only
			STATUS	current
	DESCRIPTION ""
			::= { mbusEB 80 }

mbusEBValue25		OBJECT-TYPE
			SYNTAX	INTEGER
			ACCESS	read-only
			STATUS	current
	DESCRIPTION ""
			::= { mbusEB 81 }

mbusEBVIF26		OBJECT-TYPE
			SYNTAX	INTEGER
			ACCESS	read-only
			STATUS	current
	DESCRIPTION ""
			::= { mbusEB 82 }

mbusEBValue26		OBJECT-TYPE
			SYNTAX	INTEGER
			ACCESS	read-only
			STATUS	current
	DESCRIPTION ""
			::= { mbusEB 83 }

mbusEBVIF27		OBJECT-TYPE
			SYNTAX	INTEGER
			ACCESS	read-only
			STATUS	current
	DESCRIPTION ""
			::= { mbusEB 84 }

mbusEBValue27		OBJECT-TYPE
			SYNTAX	INTEGER
			ACCESS	read-only
			STATUS	current
	DESCRIPTION ""
			::= { mbusEB 85 }

mbusEBVIF28		OBJECT-TYPE
			SYNTAX	INTEGER
			ACCESS	read-only
			STATUS	current
	DESCRIPTION ""
			::= { mbusEB 86 }

mbusEBValue28		OBJECT-TYPE
			SYNTAX	INTEGER
			ACCESS	read-only
			STATUS	current
	DESCRIPTION ""
			::= { mbusEB 87 }

mbusEBVIF29		OBJECT-TYPE
			SYNTAX	INTEGER
			ACCESS	read-only
			STATUS	current
	DESCRIPTION ""
			::= { mbusEB 88 }

mbusEBValue29		OBJECT-TYPE
			SYNTAX	INTEGER
			ACCESS	read-only
			STATUS	current
	DESCRIPTION ""
			::= { mbusEB 89 }

mbusEBVIF2A		OBJECT-TYPE
			SYNTAX	INTEGER
			ACCESS	read-only
			STATUS	current
	DESCRIPTION ""
			::= { mbusEB 90 }

mbusEBValue2A		OBJECT-TYPE
			SYNTAX	INTEGER
			ACCESS	read-only
			STATUS	current
	DESCRIPTION ""
			::= { mbusEB 91 }

mbusEBVIF2B		OBJECT-TYPE
			SYNTAX	INTEGER
			ACCESS	read-only
			STATUS	current
	DESCRIPTION ""
			::= { mbusEB 92 }

mbusEBValue2B		OBJECT-TYPE
			SYNTAX	INTEGER
			ACCESS	read-only
			STATUS	current
	DESCRIPTION ""
			::= { mbusEB 93 }

mbusEBVIF2C		OBJECT-TYPE
			SYNTAX	INTEGER
			ACCESS	read-only
			STATUS	current
	DESCRIPTION ""
			::= { mbusEB 94 }

mbusEBValue2C		OBJECT-TYPE
			SYNTAX	INTEGER
			ACCESS	read-only
			STATUS	current
	DESCRIPTION ""
			::= { mbusEB 95 }

mbusEBVIF2D		OBJECT-TYPE
			SYNTAX	INTEGER
			ACCESS	read-only
			STATUS	current
	DESCRIPTION ""
			::= { mbusEB 96 }

mbusEBValue2D		OBJECT-TYPE
			SYNTAX	INTEGER
			ACCESS	read-only
			STATUS	current
	DESCRIPTION ""
			::= { mbusEB 97 }

mbusEBVIF2E		OBJECT-TYPE
			SYNTAX	INTEGER
			ACCESS	read-only
			STATUS	current
	DESCRIPTION ""
			::= { mbusEB 98 }

mbusEBValue2E		OBJECT-TYPE
			SYNTAX	INTEGER
			ACCESS	read-only
			STATUS	current
	DESCRIPTION ""
			::= { mbusEB 99 }

mbusEBVIF2F		OBJECT-TYPE
			SYNTAX	INTEGER
			ACCESS	read-only
			STATUS	current
	DESCRIPTION ""
			::= { mbusEB 100 }

mbusEBValue2F		OBJECT-TYPE
			SYNTAX	INTEGER
			ACCESS	read-only
			STATUS	current
	DESCRIPTION ""
			::= { mbusEB 101 }

mbusEC			OBJECT IDENTIFIER ::= { mbus 236 }

mbusECIdNumber		OBJECT-TYPE
			SYNTAX	Gauge
			ACCESS	read-only
			STATUS	current
	DESCRIPTION ""
			::= { mbusEC 1 }

mbusECManufacturer	OBJECT-TYPE
			SYNTAX	Gauge
			ACCESS	read-only
			STATUS	current
	DESCRIPTION ""
			::= { mbusEC 2 }

mbusECVersion		OBJECT-TYPE
			SYNTAX	Gauge
			ACCESS	read-only
			STATUS	current
	DESCRIPTION ""
			::= { mbusEC 3 }

mbusECMedium		OBJECT-TYPE
			SYNTAX	Gauge
			ACCESS	read-only
			STATUS	current
	DESCRIPTION ""
			::= { mbusEC 4 }

mbusECStatus		OBJECT-TYPE
			SYNTAX	Gauge
			ACCESS	read-only
			STATUS	current
	DESCRIPTION ""
			::= { mbusEC 5 }

mbusECVIF00		OBJECT-TYPE
			SYNTAX	INTEGER
			ACCESS	read-only
			STATUS	current
	DESCRIPTION ""
			::= { mbusEC 6 }

mbusECValue00		OBJECT-TYPE
			SYNTAX	INTEGER
			ACCESS	read-only
			STATUS	current
	DESCRIPTION ""
			::= { mbusEC 7 }

mbusECVIF01		OBJECT-TYPE
			SYNTAX	INTEGER
			ACCESS	read-only
			STATUS	current
	DESCRIPTION ""
			::= { mbusEC 8 }

mbusECValue01		OBJECT-TYPE
			SYNTAX	INTEGER
			ACCESS	read-only
			STATUS	current
	DESCRIPTION ""
			::= { mbusEC 9 }

mbusECVIF02		OBJECT-TYPE
			SYNTAX	INTEGER
			ACCESS	read-only
			STATUS	current
	DESCRIPTION ""
			::= { mbusEC 10 }

mbusECValue02		OBJECT-TYPE
			SYNTAX	INTEGER
			ACCESS	read-only
			STATUS	current
	DESCRIPTION ""
			::= { mbusEC 11 }

mbusECVIF03		OBJECT-TYPE
			SYNTAX	INTEGER
			ACCESS	read-only
			STATUS	current
	DESCRIPTION ""
			::= { mbusEC 12 }

mbusECValue03		OBJECT-TYPE
			SYNTAX	INTEGER
			ACCESS	read-only
			STATUS	current
	DESCRIPTION ""
			::= { mbusEC 13 }

mbusECVIF04		OBJECT-TYPE
			SYNTAX	INTEGER
			ACCESS	read-only
			STATUS	current
	DESCRIPTION ""
			::= { mbusEC 14 }

mbusECValue04		OBJECT-TYPE
			SYNTAX	INTEGER
			ACCESS	read-only
			STATUS	current
	DESCRIPTION ""
			::= { mbusEC 15 }

mbusECVIF05		OBJECT-TYPE
			SYNTAX	INTEGER
			ACCESS	read-only
			STATUS	current
	DESCRIPTION ""
			::= { mbusEC 16 }

mbusECValue05		OBJECT-TYPE
			SYNTAX	INTEGER
			ACCESS	read-only
			STATUS	current
	DESCRIPTION ""
			::= { mbusEC 17 }

mbusECVIF06		OBJECT-TYPE
			SYNTAX	INTEGER
			ACCESS	read-only
			STATUS	current
	DESCRIPTION ""
			::= { mbusEC 18 }

mbusECValue06		OBJECT-TYPE
			SYNTAX	INTEGER
			ACCESS	read-only
			STATUS	current
	DESCRIPTION ""
			::= { mbusEC 19 }

mbusECVIF07		OBJECT-TYPE
			SYNTAX	INTEGER
			ACCESS	read-only
			STATUS	current
	DESCRIPTION ""
			::= { mbusEC 20 }

mbusECValue07		OBJECT-TYPE
			SYNTAX	INTEGER
			ACCESS	read-only
			STATUS	current
	DESCRIPTION ""
			::= { mbusEC 21 }

mbusECVIF08		OBJECT-TYPE
			SYNTAX	INTEGER
			ACCESS	read-only
			STATUS	current
	DESCRIPTION ""
			::= { mbusEC 22 }

mbusECValue08		OBJECT-TYPE
			SYNTAX	INTEGER
			ACCESS	read-only
			STATUS	current
	DESCRIPTION ""
			::= { mbusEC 23 }

mbusECVIF09		OBJECT-TYPE
			SYNTAX	INTEGER
			ACCESS	read-only
			STATUS	current
	DESCRIPTION ""
			::= { mbusEC 24 }

mbusECValue09		OBJECT-TYPE
			SYNTAX	INTEGER
			ACCESS	read-only
			STATUS	current
	DESCRIPTION ""
			::= { mbusEC 25 }

mbusECVIF0A		OBJECT-TYPE
			SYNTAX	INTEGER
			ACCESS	read-only
			STATUS	current
	DESCRIPTION ""
			::= { mbusEC 26 }

mbusECValue0A		OBJECT-TYPE
			SYNTAX	INTEGER
			ACCESS	read-only
			STATUS	current
	DESCRIPTION ""
			::= { mbusEC 27 }

mbusECVIF0B		OBJECT-TYPE
			SYNTAX	INTEGER
			ACCESS	read-only
			STATUS	current
	DESCRIPTION ""
			::= { mbusEC 28 }

mbusECValue0B		OBJECT-TYPE
			SYNTAX	INTEGER
			ACCESS	read-only
			STATUS	current
	DESCRIPTION ""
			::= { mbusEC 29 }

mbusECVIF0C		OBJECT-TYPE
			SYNTAX	INTEGER
			ACCESS	read-only
			STATUS	current
	DESCRIPTION ""
			::= { mbusEC 30 }

mbusECValue0C		OBJECT-TYPE
			SYNTAX	INTEGER
			ACCESS	read-only
			STATUS	current
	DESCRIPTION ""
			::= { mbusEC 31 }

mbusECVIF0D		OBJECT-TYPE
			SYNTAX	INTEGER
			ACCESS	read-only
			STATUS	current
	DESCRIPTION ""
			::= { mbusEC 32 }

mbusECValue0D		OBJECT-TYPE
			SYNTAX	INTEGER
			ACCESS	read-only
			STATUS	current
	DESCRIPTION ""
			::= { mbusEC 33 }

mbusECVIF0E		OBJECT-TYPE
			SYNTAX	INTEGER
			ACCESS	read-only
			STATUS	current
	DESCRIPTION ""
			::= { mbusEC 34 }

mbusECValue0E		OBJECT-TYPE
			SYNTAX	INTEGER
			ACCESS	read-only
			STATUS	current
	DESCRIPTION ""
			::= { mbusEC 35 }

mbusECVIF0F		OBJECT-TYPE
			SYNTAX	INTEGER
			ACCESS	read-only
			STATUS	current
	DESCRIPTION ""
			::= { mbusEC 36 }

mbusECValue0F		OBJECT-TYPE
			SYNTAX	INTEGER
			ACCESS	read-only
			STATUS	current
	DESCRIPTION ""
			::= { mbusEC 37 }

mbusECVIF10		OBJECT-TYPE
			SYNTAX	INTEGER
			ACCESS	read-only
			STATUS	current
	DESCRIPTION ""
			::= { mbusEC 38 }

mbusECValue10		OBJECT-TYPE
			SYNTAX	INTEGER
			ACCESS	read-only
			STATUS	current
	DESCRIPTION ""
			::= { mbusEC 39 }

mbusECVIF11		OBJECT-TYPE
			SYNTAX	INTEGER
			ACCESS	read-only
			STATUS	current
	DESCRIPTION ""
			::= { mbusEC 40 }

mbusECValue11		OBJECT-TYPE
			SYNTAX	INTEGER
			ACCESS	read-only
			STATUS	current
	DESCRIPTION ""
			::= { mbusEC 41 }

mbusECVIF12		OBJECT-TYPE
			SYNTAX	INTEGER
			ACCESS	read-only
			STATUS	current
	DESCRIPTION ""
			::= { mbusEC 42 }

mbusECValue12		OBJECT-TYPE
			SYNTAX	INTEGER
			ACCESS	read-only
			STATUS	current
	DESCRIPTION ""
			::= { mbusEC 43 }

mbusECVIF13		OBJECT-TYPE
			SYNTAX	INTEGER
			ACCESS	read-only
			STATUS	current
	DESCRIPTION ""
			::= { mbusEC 44 }

mbusECValue13		OBJECT-TYPE
			SYNTAX	INTEGER
			ACCESS	read-only
			STATUS	current
	DESCRIPTION ""
			::= { mbusEC 45 }

mbusECVIF14		OBJECT-TYPE
			SYNTAX	INTEGER
			ACCESS	read-only
			STATUS	current
	DESCRIPTION ""
			::= { mbusEC 46 }

mbusECValue14		OBJECT-TYPE
			SYNTAX	INTEGER
			ACCESS	read-only
			STATUS	current
	DESCRIPTION ""
			::= { mbusEC 47 }

mbusECVIF15		OBJECT-TYPE
			SYNTAX	INTEGER
			ACCESS	read-only
			STATUS	current
	DESCRIPTION ""
			::= { mbusEC 48 }

mbusECValue15		OBJECT-TYPE
			SYNTAX	INTEGER
			ACCESS	read-only
			STATUS	current
	DESCRIPTION ""
			::= { mbusEC 49 }

mbusECVIF16		OBJECT-TYPE
			SYNTAX	INTEGER
			ACCESS	read-only
			STATUS	current
	DESCRIPTION ""
			::= { mbusEC 50 }

mbusECValue16		OBJECT-TYPE
			SYNTAX	INTEGER
			ACCESS	read-only
			STATUS	current
	DESCRIPTION ""
			::= { mbusEC 51 }

mbusECVIF17		OBJECT-TYPE
			SYNTAX	INTEGER
			ACCESS	read-only
			STATUS	current
	DESCRIPTION ""
			::= { mbusEC 52 }

mbusECValue17		OBJECT-TYPE
			SYNTAX	INTEGER
			ACCESS	read-only
			STATUS	current
	DESCRIPTION ""
			::= { mbusEC 53 }

mbusECVIF18		OBJECT-TYPE
			SYNTAX	INTEGER
			ACCESS	read-only
			STATUS	current
	DESCRIPTION ""
			::= { mbusEC 54 }

mbusECValue18		OBJECT-TYPE
			SYNTAX	INTEGER
			ACCESS	read-only
			STATUS	current
	DESCRIPTION ""
			::= { mbusEC 55 }

mbusECVIF19		OBJECT-TYPE
			SYNTAX	INTEGER
			ACCESS	read-only
			STATUS	current
	DESCRIPTION ""
			::= { mbusEC 56 }

mbusECValue19		OBJECT-TYPE
			SYNTAX	INTEGER
			ACCESS	read-only
			STATUS	current
	DESCRIPTION ""
			::= { mbusEC 57 }

mbusECVIF1A		OBJECT-TYPE
			SYNTAX	INTEGER
			ACCESS	read-only
			STATUS	current
	DESCRIPTION ""
			::= { mbusEC 58 }

mbusECValue1A		OBJECT-TYPE
			SYNTAX	INTEGER
			ACCESS	read-only
			STATUS	current
	DESCRIPTION ""
			::= { mbusEC 59 }

mbusECVIF1B		OBJECT-TYPE
			SYNTAX	INTEGER
			ACCESS	read-only
			STATUS	current
	DESCRIPTION ""
			::= { mbusEC 60 }

mbusECValue1B		OBJECT-TYPE
			SYNTAX	INTEGER
			ACCESS	read-only
			STATUS	current
	DESCRIPTION ""
			::= { mbusEC 61 }

mbusECVIF1C		OBJECT-TYPE
			SYNTAX	INTEGER
			ACCESS	read-only
			STATUS	current
	DESCRIPTION ""
			::= { mbusEC 62 }

mbusECValue1C		OBJECT-TYPE
			SYNTAX	INTEGER
			ACCESS	read-only
			STATUS	current
	DESCRIPTION ""
			::= { mbusEC 63 }

mbusECVIF1D		OBJECT-TYPE
			SYNTAX	INTEGER
			ACCESS	read-only
			STATUS	current
	DESCRIPTION ""
			::= { mbusEC 64 }

mbusECValue1D		OBJECT-TYPE
			SYNTAX	INTEGER
			ACCESS	read-only
			STATUS	current
	DESCRIPTION ""
			::= { mbusEC 65 }

mbusECVIF1E		OBJECT-TYPE
			SYNTAX	INTEGER
			ACCESS	read-only
			STATUS	current
	DESCRIPTION ""
			::= { mbusEC 66 }

mbusECValue1E		OBJECT-TYPE
			SYNTAX	INTEGER
			ACCESS	read-only
			STATUS	current
	DESCRIPTION ""
			::= { mbusEC 67 }

mbusECVIF1F		OBJECT-TYPE
			SYNTAX	INTEGER
			ACCESS	read-only
			STATUS	current
	DESCRIPTION ""
			::= { mbusEC 68 }

mbusECValue1F		OBJECT-TYPE
			SYNTAX	INTEGER
			ACCESS	read-only
			STATUS	current
	DESCRIPTION ""
			::= { mbusEC 69 }

mbusECVIF20		OBJECT-TYPE
			SYNTAX	INTEGER
			ACCESS	read-only
			STATUS	current
	DESCRIPTION ""
			::= { mbusEC 70 }

mbusECValue20		OBJECT-TYPE
			SYNTAX	INTEGER
			ACCESS	read-only
			STATUS	current
	DESCRIPTION ""
			::= { mbusEC 71 }

mbusECVIF21		OBJECT-TYPE
			SYNTAX	INTEGER
			ACCESS	read-only
			STATUS	current
	DESCRIPTION ""
			::= { mbusEC 72 }

mbusECValue21		OBJECT-TYPE
			SYNTAX	INTEGER
			ACCESS	read-only
			STATUS	current
	DESCRIPTION ""
			::= { mbusEC 73 }

mbusECVIF22		OBJECT-TYPE
			SYNTAX	INTEGER
			ACCESS	read-only
			STATUS	current
	DESCRIPTION ""
			::= { mbusEC 74 }

mbusECValue22		OBJECT-TYPE
			SYNTAX	INTEGER
			ACCESS	read-only
			STATUS	current
	DESCRIPTION ""
			::= { mbusEC 75 }

mbusECVIF23		OBJECT-TYPE
			SYNTAX	INTEGER
			ACCESS	read-only
			STATUS	current
	DESCRIPTION ""
			::= { mbusEC 76 }

mbusECValue23		OBJECT-TYPE
			SYNTAX	INTEGER
			ACCESS	read-only
			STATUS	current
	DESCRIPTION ""
			::= { mbusEC 77 }

mbusECVIF24		OBJECT-TYPE
			SYNTAX	INTEGER
			ACCESS	read-only
			STATUS	current
	DESCRIPTION ""
			::= { mbusEC 78 }

mbusECValue24		OBJECT-TYPE
			SYNTAX	INTEGER
			ACCESS	read-only
			STATUS	current
	DESCRIPTION ""
			::= { mbusEC 79 }

mbusECVIF25		OBJECT-TYPE
			SYNTAX	INTEGER
			ACCESS	read-only
			STATUS	current
	DESCRIPTION ""
			::= { mbusEC 80 }

mbusECValue25		OBJECT-TYPE
			SYNTAX	INTEGER
			ACCESS	read-only
			STATUS	current
	DESCRIPTION ""
			::= { mbusEC 81 }

mbusECVIF26		OBJECT-TYPE
			SYNTAX	INTEGER
			ACCESS	read-only
			STATUS	current
	DESCRIPTION ""
			::= { mbusEC 82 }

mbusECValue26		OBJECT-TYPE
			SYNTAX	INTEGER
			ACCESS	read-only
			STATUS	current
	DESCRIPTION ""
			::= { mbusEC 83 }

mbusECVIF27		OBJECT-TYPE
			SYNTAX	INTEGER
			ACCESS	read-only
			STATUS	current
	DESCRIPTION ""
			::= { mbusEC 84 }

mbusECValue27		OBJECT-TYPE
			SYNTAX	INTEGER
			ACCESS	read-only
			STATUS	current
	DESCRIPTION ""
			::= { mbusEC 85 }

mbusECVIF28		OBJECT-TYPE
			SYNTAX	INTEGER
			ACCESS	read-only
			STATUS	current
	DESCRIPTION ""
			::= { mbusEC 86 }

mbusECValue28		OBJECT-TYPE
			SYNTAX	INTEGER
			ACCESS	read-only
			STATUS	current
	DESCRIPTION ""
			::= { mbusEC 87 }

mbusECVIF29		OBJECT-TYPE
			SYNTAX	INTEGER
			ACCESS	read-only
			STATUS	current
	DESCRIPTION ""
			::= { mbusEC 88 }

mbusECValue29		OBJECT-TYPE
			SYNTAX	INTEGER
			ACCESS	read-only
			STATUS	current
	DESCRIPTION ""
			::= { mbusEC 89 }

mbusECVIF2A		OBJECT-TYPE
			SYNTAX	INTEGER
			ACCESS	read-only
			STATUS	current
	DESCRIPTION ""
			::= { mbusEC 90 }

mbusECValue2A		OBJECT-TYPE
			SYNTAX	INTEGER
			ACCESS	read-only
			STATUS	current
	DESCRIPTION ""
			::= { mbusEC 91 }

mbusECVIF2B		OBJECT-TYPE
			SYNTAX	INTEGER
			ACCESS	read-only
			STATUS	current
	DESCRIPTION ""
			::= { mbusEC 92 }

mbusECValue2B		OBJECT-TYPE
			SYNTAX	INTEGER
			ACCESS	read-only
			STATUS	current
	DESCRIPTION ""
			::= { mbusEC 93 }

mbusECVIF2C		OBJECT-TYPE
			SYNTAX	INTEGER
			ACCESS	read-only
			STATUS	current
	DESCRIPTION ""
			::= { mbusEC 94 }

mbusECValue2C		OBJECT-TYPE
			SYNTAX	INTEGER
			ACCESS	read-only
			STATUS	current
	DESCRIPTION ""
			::= { mbusEC 95 }

mbusECVIF2D		OBJECT-TYPE
			SYNTAX	INTEGER
			ACCESS	read-only
			STATUS	current
	DESCRIPTION ""
			::= { mbusEC 96 }

mbusECValue2D		OBJECT-TYPE
			SYNTAX	INTEGER
			ACCESS	read-only
			STATUS	current
	DESCRIPTION ""
			::= { mbusEC 97 }

mbusECVIF2E		OBJECT-TYPE
			SYNTAX	INTEGER
			ACCESS	read-only
			STATUS	current
	DESCRIPTION ""
			::= { mbusEC 98 }

mbusECValue2E		OBJECT-TYPE
			SYNTAX	INTEGER
			ACCESS	read-only
			STATUS	current
	DESCRIPTION ""
			::= { mbusEC 99 }

mbusECVIF2F		OBJECT-TYPE
			SYNTAX	INTEGER
			ACCESS	read-only
			STATUS	current
	DESCRIPTION ""
			::= { mbusEC 100 }

mbusECValue2F		OBJECT-TYPE
			SYNTAX	INTEGER
			ACCESS	read-only
			STATUS	current
	DESCRIPTION ""
			::= { mbusEC 101 }

mbusED			OBJECT IDENTIFIER ::= { mbus 237 }

mbusEDIdNumber		OBJECT-TYPE
			SYNTAX	Gauge
			ACCESS	read-only
			STATUS	current
	DESCRIPTION ""
			::= { mbusED 1 }

mbusEDManufacturer	OBJECT-TYPE
			SYNTAX	Gauge
			ACCESS	read-only
			STATUS	current
	DESCRIPTION ""
			::= { mbusED 2 }

mbusEDVersion		OBJECT-TYPE
			SYNTAX	Gauge
			ACCESS	read-only
			STATUS	current
	DESCRIPTION ""
			::= { mbusED 3 }

mbusEDMedium		OBJECT-TYPE
			SYNTAX	Gauge
			ACCESS	read-only
			STATUS	current
	DESCRIPTION ""
			::= { mbusED 4 }

mbusEDStatus		OBJECT-TYPE
			SYNTAX	Gauge
			ACCESS	read-only
			STATUS	current
	DESCRIPTION ""
			::= { mbusED 5 }

mbusEDVIF00		OBJECT-TYPE
			SYNTAX	INTEGER
			ACCESS	read-only
			STATUS	current
	DESCRIPTION ""
			::= { mbusED 6 }

mbusEDValue00		OBJECT-TYPE
			SYNTAX	INTEGER
			ACCESS	read-only
			STATUS	current
	DESCRIPTION ""
			::= { mbusED 7 }

mbusEDVIF01		OBJECT-TYPE
			SYNTAX	INTEGER
			ACCESS	read-only
			STATUS	current
	DESCRIPTION ""
			::= { mbusED 8 }

mbusEDValue01		OBJECT-TYPE
			SYNTAX	INTEGER
			ACCESS	read-only
			STATUS	current
	DESCRIPTION ""
			::= { mbusED 9 }

mbusEDVIF02		OBJECT-TYPE
			SYNTAX	INTEGER
			ACCESS	read-only
			STATUS	current
	DESCRIPTION ""
			::= { mbusED 10 }

mbusEDValue02		OBJECT-TYPE
			SYNTAX	INTEGER
			ACCESS	read-only
			STATUS	current
	DESCRIPTION ""
			::= { mbusED 11 }

mbusEDVIF03		OBJECT-TYPE
			SYNTAX	INTEGER
			ACCESS	read-only
			STATUS	current
	DESCRIPTION ""
			::= { mbusED 12 }

mbusEDValue03		OBJECT-TYPE
			SYNTAX	INTEGER
			ACCESS	read-only
			STATUS	current
	DESCRIPTION ""
			::= { mbusED 13 }

mbusEDVIF04		OBJECT-TYPE
			SYNTAX	INTEGER
			ACCESS	read-only
			STATUS	current
	DESCRIPTION ""
			::= { mbusED 14 }

mbusEDValue04		OBJECT-TYPE
			SYNTAX	INTEGER
			ACCESS	read-only
			STATUS	current
	DESCRIPTION ""
			::= { mbusED 15 }

mbusEDVIF05		OBJECT-TYPE
			SYNTAX	INTEGER
			ACCESS	read-only
			STATUS	current
	DESCRIPTION ""
			::= { mbusED 16 }

mbusEDValue05		OBJECT-TYPE
			SYNTAX	INTEGER
			ACCESS	read-only
			STATUS	current
	DESCRIPTION ""
			::= { mbusED 17 }

mbusEDVIF06		OBJECT-TYPE
			SYNTAX	INTEGER
			ACCESS	read-only
			STATUS	current
	DESCRIPTION ""
			::= { mbusED 18 }

mbusEDValue06		OBJECT-TYPE
			SYNTAX	INTEGER
			ACCESS	read-only
			STATUS	current
	DESCRIPTION ""
			::= { mbusED 19 }

mbusEDVIF07		OBJECT-TYPE
			SYNTAX	INTEGER
			ACCESS	read-only
			STATUS	current
	DESCRIPTION ""
			::= { mbusED 20 }

mbusEDValue07		OBJECT-TYPE
			SYNTAX	INTEGER
			ACCESS	read-only
			STATUS	current
	DESCRIPTION ""
			::= { mbusED 21 }

mbusEDVIF08		OBJECT-TYPE
			SYNTAX	INTEGER
			ACCESS	read-only
			STATUS	current
	DESCRIPTION ""
			::= { mbusED 22 }

mbusEDValue08		OBJECT-TYPE
			SYNTAX	INTEGER
			ACCESS	read-only
			STATUS	current
	DESCRIPTION ""
			::= { mbusED 23 }

mbusEDVIF09		OBJECT-TYPE
			SYNTAX	INTEGER
			ACCESS	read-only
			STATUS	current
	DESCRIPTION ""
			::= { mbusED 24 }

mbusEDValue09		OBJECT-TYPE
			SYNTAX	INTEGER
			ACCESS	read-only
			STATUS	current
	DESCRIPTION ""
			::= { mbusED 25 }

mbusEDVIF0A		OBJECT-TYPE
			SYNTAX	INTEGER
			ACCESS	read-only
			STATUS	current
	DESCRIPTION ""
			::= { mbusED 26 }

mbusEDValue0A		OBJECT-TYPE
			SYNTAX	INTEGER
			ACCESS	read-only
			STATUS	current
	DESCRIPTION ""
			::= { mbusED 27 }

mbusEDVIF0B		OBJECT-TYPE
			SYNTAX	INTEGER
			ACCESS	read-only
			STATUS	current
	DESCRIPTION ""
			::= { mbusED 28 }

mbusEDValue0B		OBJECT-TYPE
			SYNTAX	INTEGER
			ACCESS	read-only
			STATUS	current
	DESCRIPTION ""
			::= { mbusED 29 }

mbusEDVIF0C		OBJECT-TYPE
			SYNTAX	INTEGER
			ACCESS	read-only
			STATUS	current
	DESCRIPTION ""
			::= { mbusED 30 }

mbusEDValue0C		OBJECT-TYPE
			SYNTAX	INTEGER
			ACCESS	read-only
			STATUS	current
	DESCRIPTION ""
			::= { mbusED 31 }

mbusEDVIF0D		OBJECT-TYPE
			SYNTAX	INTEGER
			ACCESS	read-only
			STATUS	current
	DESCRIPTION ""
			::= { mbusED 32 }

mbusEDValue0D		OBJECT-TYPE
			SYNTAX	INTEGER
			ACCESS	read-only
			STATUS	current
	DESCRIPTION ""
			::= { mbusED 33 }

mbusEDVIF0E		OBJECT-TYPE
			SYNTAX	INTEGER
			ACCESS	read-only
			STATUS	current
	DESCRIPTION ""
			::= { mbusED 34 }

mbusEDValue0E		OBJECT-TYPE
			SYNTAX	INTEGER
			ACCESS	read-only
			STATUS	current
	DESCRIPTION ""
			::= { mbusED 35 }

mbusEDVIF0F		OBJECT-TYPE
			SYNTAX	INTEGER
			ACCESS	read-only
			STATUS	current
	DESCRIPTION ""
			::= { mbusED 36 }

mbusEDValue0F		OBJECT-TYPE
			SYNTAX	INTEGER
			ACCESS	read-only
			STATUS	current
	DESCRIPTION ""
			::= { mbusED 37 }

mbusEDVIF10		OBJECT-TYPE
			SYNTAX	INTEGER
			ACCESS	read-only
			STATUS	current
	DESCRIPTION ""
			::= { mbusED 38 }

mbusEDValue10		OBJECT-TYPE
			SYNTAX	INTEGER
			ACCESS	read-only
			STATUS	current
	DESCRIPTION ""
			::= { mbusED 39 }

mbusEDVIF11		OBJECT-TYPE
			SYNTAX	INTEGER
			ACCESS	read-only
			STATUS	current
	DESCRIPTION ""
			::= { mbusED 40 }

mbusEDValue11		OBJECT-TYPE
			SYNTAX	INTEGER
			ACCESS	read-only
			STATUS	current
	DESCRIPTION ""
			::= { mbusED 41 }

mbusEDVIF12		OBJECT-TYPE
			SYNTAX	INTEGER
			ACCESS	read-only
			STATUS	current
	DESCRIPTION ""
			::= { mbusED 42 }

mbusEDValue12		OBJECT-TYPE
			SYNTAX	INTEGER
			ACCESS	read-only
			STATUS	current
	DESCRIPTION ""
			::= { mbusED 43 }

mbusEDVIF13		OBJECT-TYPE
			SYNTAX	INTEGER
			ACCESS	read-only
			STATUS	current
	DESCRIPTION ""
			::= { mbusED 44 }

mbusEDValue13		OBJECT-TYPE
			SYNTAX	INTEGER
			ACCESS	read-only
			STATUS	current
	DESCRIPTION ""
			::= { mbusED 45 }

mbusEDVIF14		OBJECT-TYPE
			SYNTAX	INTEGER
			ACCESS	read-only
			STATUS	current
	DESCRIPTION ""
			::= { mbusED 46 }

mbusEDValue14		OBJECT-TYPE
			SYNTAX	INTEGER
			ACCESS	read-only
			STATUS	current
	DESCRIPTION ""
			::= { mbusED 47 }

mbusEDVIF15		OBJECT-TYPE
			SYNTAX	INTEGER
			ACCESS	read-only
			STATUS	current
	DESCRIPTION ""
			::= { mbusED 48 }

mbusEDValue15		OBJECT-TYPE
			SYNTAX	INTEGER
			ACCESS	read-only
			STATUS	current
	DESCRIPTION ""
			::= { mbusED 49 }

mbusEDVIF16		OBJECT-TYPE
			SYNTAX	INTEGER
			ACCESS	read-only
			STATUS	current
	DESCRIPTION ""
			::= { mbusED 50 }

mbusEDValue16		OBJECT-TYPE
			SYNTAX	INTEGER
			ACCESS	read-only
			STATUS	current
	DESCRIPTION ""
			::= { mbusED 51 }

mbusEDVIF17		OBJECT-TYPE
			SYNTAX	INTEGER
			ACCESS	read-only
			STATUS	current
	DESCRIPTION ""
			::= { mbusED 52 }

mbusEDValue17		OBJECT-TYPE
			SYNTAX	INTEGER
			ACCESS	read-only
			STATUS	current
	DESCRIPTION ""
			::= { mbusED 53 }

mbusEDVIF18		OBJECT-TYPE
			SYNTAX	INTEGER
			ACCESS	read-only
			STATUS	current
	DESCRIPTION ""
			::= { mbusED 54 }

mbusEDValue18		OBJECT-TYPE
			SYNTAX	INTEGER
			ACCESS	read-only
			STATUS	current
	DESCRIPTION ""
			::= { mbusED 55 }

mbusEDVIF19		OBJECT-TYPE
			SYNTAX	INTEGER
			ACCESS	read-only
			STATUS	current
	DESCRIPTION ""
			::= { mbusED 56 }

mbusEDValue19		OBJECT-TYPE
			SYNTAX	INTEGER
			ACCESS	read-only
			STATUS	current
	DESCRIPTION ""
			::= { mbusED 57 }

mbusEDVIF1A		OBJECT-TYPE
			SYNTAX	INTEGER
			ACCESS	read-only
			STATUS	current
	DESCRIPTION ""
			::= { mbusED 58 }

mbusEDValue1A		OBJECT-TYPE
			SYNTAX	INTEGER
			ACCESS	read-only
			STATUS	current
	DESCRIPTION ""
			::= { mbusED 59 }

mbusEDVIF1B		OBJECT-TYPE
			SYNTAX	INTEGER
			ACCESS	read-only
			STATUS	current
	DESCRIPTION ""
			::= { mbusED 60 }

mbusEDValue1B		OBJECT-TYPE
			SYNTAX	INTEGER
			ACCESS	read-only
			STATUS	current
	DESCRIPTION ""
			::= { mbusED 61 }

mbusEDVIF1C		OBJECT-TYPE
			SYNTAX	INTEGER
			ACCESS	read-only
			STATUS	current
	DESCRIPTION ""
			::= { mbusED 62 }

mbusEDValue1C		OBJECT-TYPE
			SYNTAX	INTEGER
			ACCESS	read-only
			STATUS	current
	DESCRIPTION ""
			::= { mbusED 63 }

mbusEDVIF1D		OBJECT-TYPE
			SYNTAX	INTEGER
			ACCESS	read-only
			STATUS	current
	DESCRIPTION ""
			::= { mbusED 64 }

mbusEDValue1D		OBJECT-TYPE
			SYNTAX	INTEGER
			ACCESS	read-only
			STATUS	current
	DESCRIPTION ""
			::= { mbusED 65 }

mbusEDVIF1E		OBJECT-TYPE
			SYNTAX	INTEGER
			ACCESS	read-only
			STATUS	current
	DESCRIPTION ""
			::= { mbusED 66 }

mbusEDValue1E		OBJECT-TYPE
			SYNTAX	INTEGER
			ACCESS	read-only
			STATUS	current
	DESCRIPTION ""
			::= { mbusED 67 }

mbusEDVIF1F		OBJECT-TYPE
			SYNTAX	INTEGER
			ACCESS	read-only
			STATUS	current
	DESCRIPTION ""
			::= { mbusED 68 }

mbusEDValue1F		OBJECT-TYPE
			SYNTAX	INTEGER
			ACCESS	read-only
			STATUS	current
	DESCRIPTION ""
			::= { mbusED 69 }

mbusEDVIF20		OBJECT-TYPE
			SYNTAX	INTEGER
			ACCESS	read-only
			STATUS	current
	DESCRIPTION ""
			::= { mbusED 70 }

mbusEDValue20		OBJECT-TYPE
			SYNTAX	INTEGER
			ACCESS	read-only
			STATUS	current
	DESCRIPTION ""
			::= { mbusED 71 }

mbusEDVIF21		OBJECT-TYPE
			SYNTAX	INTEGER
			ACCESS	read-only
			STATUS	current
	DESCRIPTION ""
			::= { mbusED 72 }

mbusEDValue21		OBJECT-TYPE
			SYNTAX	INTEGER
			ACCESS	read-only
			STATUS	current
	DESCRIPTION ""
			::= { mbusED 73 }

mbusEDVIF22		OBJECT-TYPE
			SYNTAX	INTEGER
			ACCESS	read-only
			STATUS	current
	DESCRIPTION ""
			::= { mbusED 74 }

mbusEDValue22		OBJECT-TYPE
			SYNTAX	INTEGER
			ACCESS	read-only
			STATUS	current
	DESCRIPTION ""
			::= { mbusED 75 }

mbusEDVIF23		OBJECT-TYPE
			SYNTAX	INTEGER
			ACCESS	read-only
			STATUS	current
	DESCRIPTION ""
			::= { mbusED 76 }

mbusEDValue23		OBJECT-TYPE
			SYNTAX	INTEGER
			ACCESS	read-only
			STATUS	current
	DESCRIPTION ""
			::= { mbusED 77 }

mbusEDVIF24		OBJECT-TYPE
			SYNTAX	INTEGER
			ACCESS	read-only
			STATUS	current
	DESCRIPTION ""
			::= { mbusED 78 }

mbusEDValue24		OBJECT-TYPE
			SYNTAX	INTEGER
			ACCESS	read-only
			STATUS	current
	DESCRIPTION ""
			::= { mbusED 79 }

mbusEDVIF25		OBJECT-TYPE
			SYNTAX	INTEGER
			ACCESS	read-only
			STATUS	current
	DESCRIPTION ""
			::= { mbusED 80 }

mbusEDValue25		OBJECT-TYPE
			SYNTAX	INTEGER
			ACCESS	read-only
			STATUS	current
	DESCRIPTION ""
			::= { mbusED 81 }

mbusEDVIF26		OBJECT-TYPE
			SYNTAX	INTEGER
			ACCESS	read-only
			STATUS	current
	DESCRIPTION ""
			::= { mbusED 82 }

mbusEDValue26		OBJECT-TYPE
			SYNTAX	INTEGER
			ACCESS	read-only
			STATUS	current
	DESCRIPTION ""
			::= { mbusED 83 }

mbusEDVIF27		OBJECT-TYPE
			SYNTAX	INTEGER
			ACCESS	read-only
			STATUS	current
	DESCRIPTION ""
			::= { mbusED 84 }

mbusEDValue27		OBJECT-TYPE
			SYNTAX	INTEGER
			ACCESS	read-only
			STATUS	current
	DESCRIPTION ""
			::= { mbusED 85 }

mbusEDVIF28		OBJECT-TYPE
			SYNTAX	INTEGER
			ACCESS	read-only
			STATUS	current
	DESCRIPTION ""
			::= { mbusED 86 }

mbusEDValue28		OBJECT-TYPE
			SYNTAX	INTEGER
			ACCESS	read-only
			STATUS	current
	DESCRIPTION ""
			::= { mbusED 87 }

mbusEDVIF29		OBJECT-TYPE
			SYNTAX	INTEGER
			ACCESS	read-only
			STATUS	current
	DESCRIPTION ""
			::= { mbusED 88 }

mbusEDValue29		OBJECT-TYPE
			SYNTAX	INTEGER
			ACCESS	read-only
			STATUS	current
	DESCRIPTION ""
			::= { mbusED 89 }

mbusEDVIF2A		OBJECT-TYPE
			SYNTAX	INTEGER
			ACCESS	read-only
			STATUS	current
	DESCRIPTION ""
			::= { mbusED 90 }

mbusEDValue2A		OBJECT-TYPE
			SYNTAX	INTEGER
			ACCESS	read-only
			STATUS	current
	DESCRIPTION ""
			::= { mbusED 91 }

mbusEDVIF2B		OBJECT-TYPE
			SYNTAX	INTEGER
			ACCESS	read-only
			STATUS	current
	DESCRIPTION ""
			::= { mbusED 92 }

mbusEDValue2B		OBJECT-TYPE
			SYNTAX	INTEGER
			ACCESS	read-only
			STATUS	current
	DESCRIPTION ""
			::= { mbusED 93 }

mbusEDVIF2C		OBJECT-TYPE
			SYNTAX	INTEGER
			ACCESS	read-only
			STATUS	current
	DESCRIPTION ""
			::= { mbusED 94 }

mbusEDValue2C		OBJECT-TYPE
			SYNTAX	INTEGER
			ACCESS	read-only
			STATUS	current
	DESCRIPTION ""
			::= { mbusED 95 }

mbusEDVIF2D		OBJECT-TYPE
			SYNTAX	INTEGER
			ACCESS	read-only
			STATUS	current
	DESCRIPTION ""
			::= { mbusED 96 }

mbusEDValue2D		OBJECT-TYPE
			SYNTAX	INTEGER
			ACCESS	read-only
			STATUS	current
	DESCRIPTION ""
			::= { mbusED 97 }

mbusEDVIF2E		OBJECT-TYPE
			SYNTAX	INTEGER
			ACCESS	read-only
			STATUS	current
	DESCRIPTION ""
			::= { mbusED 98 }

mbusEDValue2E		OBJECT-TYPE
			SYNTAX	INTEGER
			ACCESS	read-only
			STATUS	current
	DESCRIPTION ""
			::= { mbusED 99 }

mbusEDVIF2F		OBJECT-TYPE
			SYNTAX	INTEGER
			ACCESS	read-only
			STATUS	current
	DESCRIPTION ""
			::= { mbusED 100 }

mbusEDValue2F		OBJECT-TYPE
			SYNTAX	INTEGER
			ACCESS	read-only
			STATUS	current
	DESCRIPTION ""
			::= { mbusED 101 }

mbusEE			OBJECT IDENTIFIER ::= { mbus 238 }

mbusEEIdNumber		OBJECT-TYPE
			SYNTAX	Gauge
			ACCESS	read-only
			STATUS	current
	DESCRIPTION ""
			::= { mbusEE 1 }

mbusEEManufacturer	OBJECT-TYPE
			SYNTAX	Gauge
			ACCESS	read-only
			STATUS	current
	DESCRIPTION ""
			::= { mbusEE 2 }

mbusEEVersion		OBJECT-TYPE
			SYNTAX	Gauge
			ACCESS	read-only
			STATUS	current
	DESCRIPTION ""
			::= { mbusEE 3 }

mbusEEMedium		OBJECT-TYPE
			SYNTAX	Gauge
			ACCESS	read-only
			STATUS	current
	DESCRIPTION ""
			::= { mbusEE 4 }

mbusEEStatus		OBJECT-TYPE
			SYNTAX	Gauge
			ACCESS	read-only
			STATUS	current
	DESCRIPTION ""
			::= { mbusEE 5 }

mbusEEVIF00		OBJECT-TYPE
			SYNTAX	INTEGER
			ACCESS	read-only
			STATUS	current
	DESCRIPTION ""
			::= { mbusEE 6 }

mbusEEValue00		OBJECT-TYPE
			SYNTAX	INTEGER
			ACCESS	read-only
			STATUS	current
	DESCRIPTION ""
			::= { mbusEE 7 }

mbusEEVIF01		OBJECT-TYPE
			SYNTAX	INTEGER
			ACCESS	read-only
			STATUS	current
	DESCRIPTION ""
			::= { mbusEE 8 }

mbusEEValue01		OBJECT-TYPE
			SYNTAX	INTEGER
			ACCESS	read-only
			STATUS	current
	DESCRIPTION ""
			::= { mbusEE 9 }

mbusEEVIF02		OBJECT-TYPE
			SYNTAX	INTEGER
			ACCESS	read-only
			STATUS	current
	DESCRIPTION ""
			::= { mbusEE 10 }

mbusEEValue02		OBJECT-TYPE
			SYNTAX	INTEGER
			ACCESS	read-only
			STATUS	current
	DESCRIPTION ""
			::= { mbusEE 11 }

mbusEEVIF03		OBJECT-TYPE
			SYNTAX	INTEGER
			ACCESS	read-only
			STATUS	current
	DESCRIPTION ""
			::= { mbusEE 12 }

mbusEEValue03		OBJECT-TYPE
			SYNTAX	INTEGER
			ACCESS	read-only
			STATUS	current
	DESCRIPTION ""
			::= { mbusEE 13 }

mbusEEVIF04		OBJECT-TYPE
			SYNTAX	INTEGER
			ACCESS	read-only
			STATUS	current
	DESCRIPTION ""
			::= { mbusEE 14 }

mbusEEValue04		OBJECT-TYPE
			SYNTAX	INTEGER
			ACCESS	read-only
			STATUS	current
	DESCRIPTION ""
			::= { mbusEE 15 }

mbusEEVIF05		OBJECT-TYPE
			SYNTAX	INTEGER
			ACCESS	read-only
			STATUS	current
	DESCRIPTION ""
			::= { mbusEE 16 }

mbusEEValue05		OBJECT-TYPE
			SYNTAX	INTEGER
			ACCESS	read-only
			STATUS	current
	DESCRIPTION ""
			::= { mbusEE 17 }

mbusEEVIF06		OBJECT-TYPE
			SYNTAX	INTEGER
			ACCESS	read-only
			STATUS	current
	DESCRIPTION ""
			::= { mbusEE 18 }

mbusEEValue06		OBJECT-TYPE
			SYNTAX	INTEGER
			ACCESS	read-only
			STATUS	current
	DESCRIPTION ""
			::= { mbusEE 19 }

mbusEEVIF07		OBJECT-TYPE
			SYNTAX	INTEGER
			ACCESS	read-only
			STATUS	current
	DESCRIPTION ""
			::= { mbusEE 20 }

mbusEEValue07		OBJECT-TYPE
			SYNTAX	INTEGER
			ACCESS	read-only
			STATUS	current
	DESCRIPTION ""
			::= { mbusEE 21 }

mbusEEVIF08		OBJECT-TYPE
			SYNTAX	INTEGER
			ACCESS	read-only
			STATUS	current
	DESCRIPTION ""
			::= { mbusEE 22 }

mbusEEValue08		OBJECT-TYPE
			SYNTAX	INTEGER
			ACCESS	read-only
			STATUS	current
	DESCRIPTION ""
			::= { mbusEE 23 }

mbusEEVIF09		OBJECT-TYPE
			SYNTAX	INTEGER
			ACCESS	read-only
			STATUS	current
	DESCRIPTION ""
			::= { mbusEE 24 }

mbusEEValue09		OBJECT-TYPE
			SYNTAX	INTEGER
			ACCESS	read-only
			STATUS	current
	DESCRIPTION ""
			::= { mbusEE 25 }

mbusEEVIF0A		OBJECT-TYPE
			SYNTAX	INTEGER
			ACCESS	read-only
			STATUS	current
	DESCRIPTION ""
			::= { mbusEE 26 }

mbusEEValue0A		OBJECT-TYPE
			SYNTAX	INTEGER
			ACCESS	read-only
			STATUS	current
	DESCRIPTION ""
			::= { mbusEE 27 }

mbusEEVIF0B		OBJECT-TYPE
			SYNTAX	INTEGER
			ACCESS	read-only
			STATUS	current
	DESCRIPTION ""
			::= { mbusEE 28 }

mbusEEValue0B		OBJECT-TYPE
			SYNTAX	INTEGER
			ACCESS	read-only
			STATUS	current
	DESCRIPTION ""
			::= { mbusEE 29 }

mbusEEVIF0C		OBJECT-TYPE
			SYNTAX	INTEGER
			ACCESS	read-only
			STATUS	current
	DESCRIPTION ""
			::= { mbusEE 30 }

mbusEEValue0C		OBJECT-TYPE
			SYNTAX	INTEGER
			ACCESS	read-only
			STATUS	current
	DESCRIPTION ""
			::= { mbusEE 31 }

mbusEEVIF0D		OBJECT-TYPE
			SYNTAX	INTEGER
			ACCESS	read-only
			STATUS	current
	DESCRIPTION ""
			::= { mbusEE 32 }

mbusEEValue0D		OBJECT-TYPE
			SYNTAX	INTEGER
			ACCESS	read-only
			STATUS	current
	DESCRIPTION ""
			::= { mbusEE 33 }

mbusEEVIF0E		OBJECT-TYPE
			SYNTAX	INTEGER
			ACCESS	read-only
			STATUS	current
	DESCRIPTION ""
			::= { mbusEE 34 }

mbusEEValue0E		OBJECT-TYPE
			SYNTAX	INTEGER
			ACCESS	read-only
			STATUS	current
	DESCRIPTION ""
			::= { mbusEE 35 }

mbusEEVIF0F		OBJECT-TYPE
			SYNTAX	INTEGER
			ACCESS	read-only
			STATUS	current
	DESCRIPTION ""
			::= { mbusEE 36 }

mbusEEValue0F		OBJECT-TYPE
			SYNTAX	INTEGER
			ACCESS	read-only
			STATUS	current
	DESCRIPTION ""
			::= { mbusEE 37 }

mbusEEVIF10		OBJECT-TYPE
			SYNTAX	INTEGER
			ACCESS	read-only
			STATUS	current
	DESCRIPTION ""
			::= { mbusEE 38 }

mbusEEValue10		OBJECT-TYPE
			SYNTAX	INTEGER
			ACCESS	read-only
			STATUS	current
	DESCRIPTION ""
			::= { mbusEE 39 }

mbusEEVIF11		OBJECT-TYPE
			SYNTAX	INTEGER
			ACCESS	read-only
			STATUS	current
	DESCRIPTION ""
			::= { mbusEE 40 }

mbusEEValue11		OBJECT-TYPE
			SYNTAX	INTEGER
			ACCESS	read-only
			STATUS	current
	DESCRIPTION ""
			::= { mbusEE 41 }

mbusEEVIF12		OBJECT-TYPE
			SYNTAX	INTEGER
			ACCESS	read-only
			STATUS	current
	DESCRIPTION ""
			::= { mbusEE 42 }

mbusEEValue12		OBJECT-TYPE
			SYNTAX	INTEGER
			ACCESS	read-only
			STATUS	current
	DESCRIPTION ""
			::= { mbusEE 43 }

mbusEEVIF13		OBJECT-TYPE
			SYNTAX	INTEGER
			ACCESS	read-only
			STATUS	current
	DESCRIPTION ""
			::= { mbusEE 44 }

mbusEEValue13		OBJECT-TYPE
			SYNTAX	INTEGER
			ACCESS	read-only
			STATUS	current
	DESCRIPTION ""
			::= { mbusEE 45 }

mbusEEVIF14		OBJECT-TYPE
			SYNTAX	INTEGER
			ACCESS	read-only
			STATUS	current
	DESCRIPTION ""
			::= { mbusEE 46 }

mbusEEValue14		OBJECT-TYPE
			SYNTAX	INTEGER
			ACCESS	read-only
			STATUS	current
	DESCRIPTION ""
			::= { mbusEE 47 }

mbusEEVIF15		OBJECT-TYPE
			SYNTAX	INTEGER
			ACCESS	read-only
			STATUS	current
	DESCRIPTION ""
			::= { mbusEE 48 }

mbusEEValue15		OBJECT-TYPE
			SYNTAX	INTEGER
			ACCESS	read-only
			STATUS	current
	DESCRIPTION ""
			::= { mbusEE 49 }

mbusEEVIF16		OBJECT-TYPE
			SYNTAX	INTEGER
			ACCESS	read-only
			STATUS	current
	DESCRIPTION ""
			::= { mbusEE 50 }

mbusEEValue16		OBJECT-TYPE
			SYNTAX	INTEGER
			ACCESS	read-only
			STATUS	current
	DESCRIPTION ""
			::= { mbusEE 51 }

mbusEEVIF17		OBJECT-TYPE
			SYNTAX	INTEGER
			ACCESS	read-only
			STATUS	current
	DESCRIPTION ""
			::= { mbusEE 52 }

mbusEEValue17		OBJECT-TYPE
			SYNTAX	INTEGER
			ACCESS	read-only
			STATUS	current
	DESCRIPTION ""
			::= { mbusEE 53 }

mbusEEVIF18		OBJECT-TYPE
			SYNTAX	INTEGER
			ACCESS	read-only
			STATUS	current
	DESCRIPTION ""
			::= { mbusEE 54 }

mbusEEValue18		OBJECT-TYPE
			SYNTAX	INTEGER
			ACCESS	read-only
			STATUS	current
	DESCRIPTION ""
			::= { mbusEE 55 }

mbusEEVIF19		OBJECT-TYPE
			SYNTAX	INTEGER
			ACCESS	read-only
			STATUS	current
	DESCRIPTION ""
			::= { mbusEE 56 }

mbusEEValue19		OBJECT-TYPE
			SYNTAX	INTEGER
			ACCESS	read-only
			STATUS	current
	DESCRIPTION ""
			::= { mbusEE 57 }

mbusEEVIF1A		OBJECT-TYPE
			SYNTAX	INTEGER
			ACCESS	read-only
			STATUS	current
	DESCRIPTION ""
			::= { mbusEE 58 }

mbusEEValue1A		OBJECT-TYPE
			SYNTAX	INTEGER
			ACCESS	read-only
			STATUS	current
	DESCRIPTION ""
			::= { mbusEE 59 }

mbusEEVIF1B		OBJECT-TYPE
			SYNTAX	INTEGER
			ACCESS	read-only
			STATUS	current
	DESCRIPTION ""
			::= { mbusEE 60 }

mbusEEValue1B		OBJECT-TYPE
			SYNTAX	INTEGER
			ACCESS	read-only
			STATUS	current
	DESCRIPTION ""
			::= { mbusEE 61 }

mbusEEVIF1C		OBJECT-TYPE
			SYNTAX	INTEGER
			ACCESS	read-only
			STATUS	current
	DESCRIPTION ""
			::= { mbusEE 62 }

mbusEEValue1C		OBJECT-TYPE
			SYNTAX	INTEGER
			ACCESS	read-only
			STATUS	current
	DESCRIPTION ""
			::= { mbusEE 63 }

mbusEEVIF1D		OBJECT-TYPE
			SYNTAX	INTEGER
			ACCESS	read-only
			STATUS	current
	DESCRIPTION ""
			::= { mbusEE 64 }

mbusEEValue1D		OBJECT-TYPE
			SYNTAX	INTEGER
			ACCESS	read-only
			STATUS	current
	DESCRIPTION ""
			::= { mbusEE 65 }

mbusEEVIF1E		OBJECT-TYPE
			SYNTAX	INTEGER
			ACCESS	read-only
			STATUS	current
	DESCRIPTION ""
			::= { mbusEE 66 }

mbusEEValue1E		OBJECT-TYPE
			SYNTAX	INTEGER
			ACCESS	read-only
			STATUS	current
	DESCRIPTION ""
			::= { mbusEE 67 }

mbusEEVIF1F		OBJECT-TYPE
			SYNTAX	INTEGER
			ACCESS	read-only
			STATUS	current
	DESCRIPTION ""
			::= { mbusEE 68 }

mbusEEValue1F		OBJECT-TYPE
			SYNTAX	INTEGER
			ACCESS	read-only
			STATUS	current
	DESCRIPTION ""
			::= { mbusEE 69 }

mbusEEVIF20		OBJECT-TYPE
			SYNTAX	INTEGER
			ACCESS	read-only
			STATUS	current
	DESCRIPTION ""
			::= { mbusEE 70 }

mbusEEValue20		OBJECT-TYPE
			SYNTAX	INTEGER
			ACCESS	read-only
			STATUS	current
	DESCRIPTION ""
			::= { mbusEE 71 }

mbusEEVIF21		OBJECT-TYPE
			SYNTAX	INTEGER
			ACCESS	read-only
			STATUS	current
	DESCRIPTION ""
			::= { mbusEE 72 }

mbusEEValue21		OBJECT-TYPE
			SYNTAX	INTEGER
			ACCESS	read-only
			STATUS	current
	DESCRIPTION ""
			::= { mbusEE 73 }

mbusEEVIF22		OBJECT-TYPE
			SYNTAX	INTEGER
			ACCESS	read-only
			STATUS	current
	DESCRIPTION ""
			::= { mbusEE 74 }

mbusEEValue22		OBJECT-TYPE
			SYNTAX	INTEGER
			ACCESS	read-only
			STATUS	current
	DESCRIPTION ""
			::= { mbusEE 75 }

mbusEEVIF23		OBJECT-TYPE
			SYNTAX	INTEGER
			ACCESS	read-only
			STATUS	current
	DESCRIPTION ""
			::= { mbusEE 76 }

mbusEEValue23		OBJECT-TYPE
			SYNTAX	INTEGER
			ACCESS	read-only
			STATUS	current
	DESCRIPTION ""
			::= { mbusEE 77 }

mbusEEVIF24		OBJECT-TYPE
			SYNTAX	INTEGER
			ACCESS	read-only
			STATUS	current
	DESCRIPTION ""
			::= { mbusEE 78 }

mbusEEValue24		OBJECT-TYPE
			SYNTAX	INTEGER
			ACCESS	read-only
			STATUS	current
	DESCRIPTION ""
			::= { mbusEE 79 }

mbusEEVIF25		OBJECT-TYPE
			SYNTAX	INTEGER
			ACCESS	read-only
			STATUS	current
	DESCRIPTION ""
			::= { mbusEE 80 }

mbusEEValue25		OBJECT-TYPE
			SYNTAX	INTEGER
			ACCESS	read-only
			STATUS	current
	DESCRIPTION ""
			::= { mbusEE 81 }

mbusEEVIF26		OBJECT-TYPE
			SYNTAX	INTEGER
			ACCESS	read-only
			STATUS	current
	DESCRIPTION ""
			::= { mbusEE 82 }

mbusEEValue26		OBJECT-TYPE
			SYNTAX	INTEGER
			ACCESS	read-only
			STATUS	current
	DESCRIPTION ""
			::= { mbusEE 83 }

mbusEEVIF27		OBJECT-TYPE
			SYNTAX	INTEGER
			ACCESS	read-only
			STATUS	current
	DESCRIPTION ""
			::= { mbusEE 84 }

mbusEEValue27		OBJECT-TYPE
			SYNTAX	INTEGER
			ACCESS	read-only
			STATUS	current
	DESCRIPTION ""
			::= { mbusEE 85 }

mbusEEVIF28		OBJECT-TYPE
			SYNTAX	INTEGER
			ACCESS	read-only
			STATUS	current
	DESCRIPTION ""
			::= { mbusEE 86 }

mbusEEValue28		OBJECT-TYPE
			SYNTAX	INTEGER
			ACCESS	read-only
			STATUS	current
	DESCRIPTION ""
			::= { mbusEE 87 }

mbusEEVIF29		OBJECT-TYPE
			SYNTAX	INTEGER
			ACCESS	read-only
			STATUS	current
	DESCRIPTION ""
			::= { mbusEE 88 }

mbusEEValue29		OBJECT-TYPE
			SYNTAX	INTEGER
			ACCESS	read-only
			STATUS	current
	DESCRIPTION ""
			::= { mbusEE 89 }

mbusEEVIF2A		OBJECT-TYPE
			SYNTAX	INTEGER
			ACCESS	read-only
			STATUS	current
	DESCRIPTION ""
			::= { mbusEE 90 }

mbusEEValue2A		OBJECT-TYPE
			SYNTAX	INTEGER
			ACCESS	read-only
			STATUS	current
	DESCRIPTION ""
			::= { mbusEE 91 }

mbusEEVIF2B		OBJECT-TYPE
			SYNTAX	INTEGER
			ACCESS	read-only
			STATUS	current
	DESCRIPTION ""
			::= { mbusEE 92 }

mbusEEValue2B		OBJECT-TYPE
			SYNTAX	INTEGER
			ACCESS	read-only
			STATUS	current
	DESCRIPTION ""
			::= { mbusEE 93 }

mbusEEVIF2C		OBJECT-TYPE
			SYNTAX	INTEGER
			ACCESS	read-only
			STATUS	current
	DESCRIPTION ""
			::= { mbusEE 94 }

mbusEEValue2C		OBJECT-TYPE
			SYNTAX	INTEGER
			ACCESS	read-only
			STATUS	current
	DESCRIPTION ""
			::= { mbusEE 95 }

mbusEEVIF2D		OBJECT-TYPE
			SYNTAX	INTEGER
			ACCESS	read-only
			STATUS	current
	DESCRIPTION ""
			::= { mbusEE 96 }

mbusEEValue2D		OBJECT-TYPE
			SYNTAX	INTEGER
			ACCESS	read-only
			STATUS	current
	DESCRIPTION ""
			::= { mbusEE 97 }

mbusEEVIF2E		OBJECT-TYPE
			SYNTAX	INTEGER
			ACCESS	read-only
			STATUS	current
	DESCRIPTION ""
			::= { mbusEE 98 }

mbusEEValue2E		OBJECT-TYPE
			SYNTAX	INTEGER
			ACCESS	read-only
			STATUS	current
	DESCRIPTION ""
			::= { mbusEE 99 }

mbusEEVIF2F		OBJECT-TYPE
			SYNTAX	INTEGER
			ACCESS	read-only
			STATUS	current
	DESCRIPTION ""
			::= { mbusEE 100 }

mbusEEValue2F		OBJECT-TYPE
			SYNTAX	INTEGER
			ACCESS	read-only
			STATUS	current
	DESCRIPTION ""
			::= { mbusEE 101 }

mbusEF			OBJECT IDENTIFIER ::= { mbus 239 }

mbusEFIdNumber		OBJECT-TYPE
			SYNTAX	Gauge
			ACCESS	read-only
			STATUS	current
	DESCRIPTION ""
			::= { mbusEF 1 }

mbusEFManufacturer	OBJECT-TYPE
			SYNTAX	Gauge
			ACCESS	read-only
			STATUS	current
	DESCRIPTION ""
			::= { mbusEF 2 }

mbusEFVersion		OBJECT-TYPE
			SYNTAX	Gauge
			ACCESS	read-only
			STATUS	current
	DESCRIPTION ""
			::= { mbusEF 3 }

mbusEFMedium		OBJECT-TYPE
			SYNTAX	Gauge
			ACCESS	read-only
			STATUS	current
	DESCRIPTION ""
			::= { mbusEF 4 }

mbusEFStatus		OBJECT-TYPE
			SYNTAX	Gauge
			ACCESS	read-only
			STATUS	current
	DESCRIPTION ""
			::= { mbusEF 5 }

mbusEFVIF00		OBJECT-TYPE
			SYNTAX	INTEGER
			ACCESS	read-only
			STATUS	current
	DESCRIPTION ""
			::= { mbusEF 6 }

mbusEFValue00		OBJECT-TYPE
			SYNTAX	INTEGER
			ACCESS	read-only
			STATUS	current
	DESCRIPTION ""
			::= { mbusEF 7 }

mbusEFVIF01		OBJECT-TYPE
			SYNTAX	INTEGER
			ACCESS	read-only
			STATUS	current
	DESCRIPTION ""
			::= { mbusEF 8 }

mbusEFValue01		OBJECT-TYPE
			SYNTAX	INTEGER
			ACCESS	read-only
			STATUS	current
	DESCRIPTION ""
			::= { mbusEF 9 }

mbusEFVIF02		OBJECT-TYPE
			SYNTAX	INTEGER
			ACCESS	read-only
			STATUS	current
	DESCRIPTION ""
			::= { mbusEF 10 }

mbusEFValue02		OBJECT-TYPE
			SYNTAX	INTEGER
			ACCESS	read-only
			STATUS	current
	DESCRIPTION ""
			::= { mbusEF 11 }

mbusEFVIF03		OBJECT-TYPE
			SYNTAX	INTEGER
			ACCESS	read-only
			STATUS	current
	DESCRIPTION ""
			::= { mbusEF 12 }

mbusEFValue03		OBJECT-TYPE
			SYNTAX	INTEGER
			ACCESS	read-only
			STATUS	current
	DESCRIPTION ""
			::= { mbusEF 13 }

mbusEFVIF04		OBJECT-TYPE
			SYNTAX	INTEGER
			ACCESS	read-only
			STATUS	current
	DESCRIPTION ""
			::= { mbusEF 14 }

mbusEFValue04		OBJECT-TYPE
			SYNTAX	INTEGER
			ACCESS	read-only
			STATUS	current
	DESCRIPTION ""
			::= { mbusEF 15 }

mbusEFVIF05		OBJECT-TYPE
			SYNTAX	INTEGER
			ACCESS	read-only
			STATUS	current
	DESCRIPTION ""
			::= { mbusEF 16 }

mbusEFValue05		OBJECT-TYPE
			SYNTAX	INTEGER
			ACCESS	read-only
			STATUS	current
	DESCRIPTION ""
			::= { mbusEF 17 }

mbusEFVIF06		OBJECT-TYPE
			SYNTAX	INTEGER
			ACCESS	read-only
			STATUS	current
	DESCRIPTION ""
			::= { mbusEF 18 }

mbusEFValue06		OBJECT-TYPE
			SYNTAX	INTEGER
			ACCESS	read-only
			STATUS	current
	DESCRIPTION ""
			::= { mbusEF 19 }

mbusEFVIF07		OBJECT-TYPE
			SYNTAX	INTEGER
			ACCESS	read-only
			STATUS	current
	DESCRIPTION ""
			::= { mbusEF 20 }

mbusEFValue07		OBJECT-TYPE
			SYNTAX	INTEGER
			ACCESS	read-only
			STATUS	current
	DESCRIPTION ""
			::= { mbusEF 21 }

mbusEFVIF08		OBJECT-TYPE
			SYNTAX	INTEGER
			ACCESS	read-only
			STATUS	current
	DESCRIPTION ""
			::= { mbusEF 22 }

mbusEFValue08		OBJECT-TYPE
			SYNTAX	INTEGER
			ACCESS	read-only
			STATUS	current
	DESCRIPTION ""
			::= { mbusEF 23 }

mbusEFVIF09		OBJECT-TYPE
			SYNTAX	INTEGER
			ACCESS	read-only
			STATUS	current
	DESCRIPTION ""
			::= { mbusEF 24 }

mbusEFValue09		OBJECT-TYPE
			SYNTAX	INTEGER
			ACCESS	read-only
			STATUS	current
	DESCRIPTION ""
			::= { mbusEF 25 }

mbusEFVIF0A		OBJECT-TYPE
			SYNTAX	INTEGER
			ACCESS	read-only
			STATUS	current
	DESCRIPTION ""
			::= { mbusEF 26 }

mbusEFValue0A		OBJECT-TYPE
			SYNTAX	INTEGER
			ACCESS	read-only
			STATUS	current
	DESCRIPTION ""
			::= { mbusEF 27 }

mbusEFVIF0B		OBJECT-TYPE
			SYNTAX	INTEGER
			ACCESS	read-only
			STATUS	current
	DESCRIPTION ""
			::= { mbusEF 28 }

mbusEFValue0B		OBJECT-TYPE
			SYNTAX	INTEGER
			ACCESS	read-only
			STATUS	current
	DESCRIPTION ""
			::= { mbusEF 29 }

mbusEFVIF0C		OBJECT-TYPE
			SYNTAX	INTEGER
			ACCESS	read-only
			STATUS	current
	DESCRIPTION ""
			::= { mbusEF 30 }

mbusEFValue0C		OBJECT-TYPE
			SYNTAX	INTEGER
			ACCESS	read-only
			STATUS	current
	DESCRIPTION ""
			::= { mbusEF 31 }

mbusEFVIF0D		OBJECT-TYPE
			SYNTAX	INTEGER
			ACCESS	read-only
			STATUS	current
	DESCRIPTION ""
			::= { mbusEF 32 }

mbusEFValue0D		OBJECT-TYPE
			SYNTAX	INTEGER
			ACCESS	read-only
			STATUS	current
	DESCRIPTION ""
			::= { mbusEF 33 }

mbusEFVIF0E		OBJECT-TYPE
			SYNTAX	INTEGER
			ACCESS	read-only
			STATUS	current
	DESCRIPTION ""
			::= { mbusEF 34 }

mbusEFValue0E		OBJECT-TYPE
			SYNTAX	INTEGER
			ACCESS	read-only
			STATUS	current
	DESCRIPTION ""
			::= { mbusEF 35 }

mbusEFVIF0F		OBJECT-TYPE
			SYNTAX	INTEGER
			ACCESS	read-only
			STATUS	current
	DESCRIPTION ""
			::= { mbusEF 36 }

mbusEFValue0F		OBJECT-TYPE
			SYNTAX	INTEGER
			ACCESS	read-only
			STATUS	current
	DESCRIPTION ""
			::= { mbusEF 37 }

mbusEFVIF10		OBJECT-TYPE
			SYNTAX	INTEGER
			ACCESS	read-only
			STATUS	current
	DESCRIPTION ""
			::= { mbusEF 38 }

mbusEFValue10		OBJECT-TYPE
			SYNTAX	INTEGER
			ACCESS	read-only
			STATUS	current
	DESCRIPTION ""
			::= { mbusEF 39 }

mbusEFVIF11		OBJECT-TYPE
			SYNTAX	INTEGER
			ACCESS	read-only
			STATUS	current
	DESCRIPTION ""
			::= { mbusEF 40 }

mbusEFValue11		OBJECT-TYPE
			SYNTAX	INTEGER
			ACCESS	read-only
			STATUS	current
	DESCRIPTION ""
			::= { mbusEF 41 }

mbusEFVIF12		OBJECT-TYPE
			SYNTAX	INTEGER
			ACCESS	read-only
			STATUS	current
	DESCRIPTION ""
			::= { mbusEF 42 }

mbusEFValue12		OBJECT-TYPE
			SYNTAX	INTEGER
			ACCESS	read-only
			STATUS	current
	DESCRIPTION ""
			::= { mbusEF 43 }

mbusEFVIF13		OBJECT-TYPE
			SYNTAX	INTEGER
			ACCESS	read-only
			STATUS	current
	DESCRIPTION ""
			::= { mbusEF 44 }

mbusEFValue13		OBJECT-TYPE
			SYNTAX	INTEGER
			ACCESS	read-only
			STATUS	current
	DESCRIPTION ""
			::= { mbusEF 45 }

mbusEFVIF14		OBJECT-TYPE
			SYNTAX	INTEGER
			ACCESS	read-only
			STATUS	current
	DESCRIPTION ""
			::= { mbusEF 46 }

mbusEFValue14		OBJECT-TYPE
			SYNTAX	INTEGER
			ACCESS	read-only
			STATUS	current
	DESCRIPTION ""
			::= { mbusEF 47 }

mbusEFVIF15		OBJECT-TYPE
			SYNTAX	INTEGER
			ACCESS	read-only
			STATUS	current
	DESCRIPTION ""
			::= { mbusEF 48 }

mbusEFValue15		OBJECT-TYPE
			SYNTAX	INTEGER
			ACCESS	read-only
			STATUS	current
	DESCRIPTION ""
			::= { mbusEF 49 }

mbusEFVIF16		OBJECT-TYPE
			SYNTAX	INTEGER
			ACCESS	read-only
			STATUS	current
	DESCRIPTION ""
			::= { mbusEF 50 }

mbusEFValue16		OBJECT-TYPE
			SYNTAX	INTEGER
			ACCESS	read-only
			STATUS	current
	DESCRIPTION ""
			::= { mbusEF 51 }

mbusEFVIF17		OBJECT-TYPE
			SYNTAX	INTEGER
			ACCESS	read-only
			STATUS	current
	DESCRIPTION ""
			::= { mbusEF 52 }

mbusEFValue17		OBJECT-TYPE
			SYNTAX	INTEGER
			ACCESS	read-only
			STATUS	current
	DESCRIPTION ""
			::= { mbusEF 53 }

mbusEFVIF18		OBJECT-TYPE
			SYNTAX	INTEGER
			ACCESS	read-only
			STATUS	current
	DESCRIPTION ""
			::= { mbusEF 54 }

mbusEFValue18		OBJECT-TYPE
			SYNTAX	INTEGER
			ACCESS	read-only
			STATUS	current
	DESCRIPTION ""
			::= { mbusEF 55 }

mbusEFVIF19		OBJECT-TYPE
			SYNTAX	INTEGER
			ACCESS	read-only
			STATUS	current
	DESCRIPTION ""
			::= { mbusEF 56 }

mbusEFValue19		OBJECT-TYPE
			SYNTAX	INTEGER
			ACCESS	read-only
			STATUS	current
	DESCRIPTION ""
			::= { mbusEF 57 }

mbusEFVIF1A		OBJECT-TYPE
			SYNTAX	INTEGER
			ACCESS	read-only
			STATUS	current
	DESCRIPTION ""
			::= { mbusEF 58 }

mbusEFValue1A		OBJECT-TYPE
			SYNTAX	INTEGER
			ACCESS	read-only
			STATUS	current
	DESCRIPTION ""
			::= { mbusEF 59 }

mbusEFVIF1B		OBJECT-TYPE
			SYNTAX	INTEGER
			ACCESS	read-only
			STATUS	current
	DESCRIPTION ""
			::= { mbusEF 60 }

mbusEFValue1B		OBJECT-TYPE
			SYNTAX	INTEGER
			ACCESS	read-only
			STATUS	current
	DESCRIPTION ""
			::= { mbusEF 61 }

mbusEFVIF1C		OBJECT-TYPE
			SYNTAX	INTEGER
			ACCESS	read-only
			STATUS	current
	DESCRIPTION ""
			::= { mbusEF 62 }

mbusEFValue1C		OBJECT-TYPE
			SYNTAX	INTEGER
			ACCESS	read-only
			STATUS	current
	DESCRIPTION ""
			::= { mbusEF 63 }

mbusEFVIF1D		OBJECT-TYPE
			SYNTAX	INTEGER
			ACCESS	read-only
			STATUS	current
	DESCRIPTION ""
			::= { mbusEF 64 }

mbusEFValue1D		OBJECT-TYPE
			SYNTAX	INTEGER
			ACCESS	read-only
			STATUS	current
	DESCRIPTION ""
			::= { mbusEF 65 }

mbusEFVIF1E		OBJECT-TYPE
			SYNTAX	INTEGER
			ACCESS	read-only
			STATUS	current
	DESCRIPTION ""
			::= { mbusEF 66 }

mbusEFValue1E		OBJECT-TYPE
			SYNTAX	INTEGER
			ACCESS	read-only
			STATUS	current
	DESCRIPTION ""
			::= { mbusEF 67 }

mbusEFVIF1F		OBJECT-TYPE
			SYNTAX	INTEGER
			ACCESS	read-only
			STATUS	current
	DESCRIPTION ""
			::= { mbusEF 68 }

mbusEFValue1F		OBJECT-TYPE
			SYNTAX	INTEGER
			ACCESS	read-only
			STATUS	current
	DESCRIPTION ""
			::= { mbusEF 69 }

mbusEFVIF20		OBJECT-TYPE
			SYNTAX	INTEGER
			ACCESS	read-only
			STATUS	current
	DESCRIPTION ""
			::= { mbusEF 70 }

mbusEFValue20		OBJECT-TYPE
			SYNTAX	INTEGER
			ACCESS	read-only
			STATUS	current
	DESCRIPTION ""
			::= { mbusEF 71 }

mbusEFVIF21		OBJECT-TYPE
			SYNTAX	INTEGER
			ACCESS	read-only
			STATUS	current
	DESCRIPTION ""
			::= { mbusEF 72 }

mbusEFValue21		OBJECT-TYPE
			SYNTAX	INTEGER
			ACCESS	read-only
			STATUS	current
	DESCRIPTION ""
			::= { mbusEF 73 }

mbusEFVIF22		OBJECT-TYPE
			SYNTAX	INTEGER
			ACCESS	read-only
			STATUS	current
	DESCRIPTION ""
			::= { mbusEF 74 }

mbusEFValue22		OBJECT-TYPE
			SYNTAX	INTEGER
			ACCESS	read-only
			STATUS	current
	DESCRIPTION ""
			::= { mbusEF 75 }

mbusEFVIF23		OBJECT-TYPE
			SYNTAX	INTEGER
			ACCESS	read-only
			STATUS	current
	DESCRIPTION ""
			::= { mbusEF 76 }

mbusEFValue23		OBJECT-TYPE
			SYNTAX	INTEGER
			ACCESS	read-only
			STATUS	current
	DESCRIPTION ""
			::= { mbusEF 77 }

mbusEFVIF24		OBJECT-TYPE
			SYNTAX	INTEGER
			ACCESS	read-only
			STATUS	current
	DESCRIPTION ""
			::= { mbusEF 78 }

mbusEFValue24		OBJECT-TYPE
			SYNTAX	INTEGER
			ACCESS	read-only
			STATUS	current
	DESCRIPTION ""
			::= { mbusEF 79 }

mbusEFVIF25		OBJECT-TYPE
			SYNTAX	INTEGER
			ACCESS	read-only
			STATUS	current
	DESCRIPTION ""
			::= { mbusEF 80 }

mbusEFValue25		OBJECT-TYPE
			SYNTAX	INTEGER
			ACCESS	read-only
			STATUS	current
	DESCRIPTION ""
			::= { mbusEF 81 }

mbusEFVIF26		OBJECT-TYPE
			SYNTAX	INTEGER
			ACCESS	read-only
			STATUS	current
	DESCRIPTION ""
			::= { mbusEF 82 }

mbusEFValue26		OBJECT-TYPE
			SYNTAX	INTEGER
			ACCESS	read-only
			STATUS	current
	DESCRIPTION ""
			::= { mbusEF 83 }

mbusEFVIF27		OBJECT-TYPE
			SYNTAX	INTEGER
			ACCESS	read-only
			STATUS	current
	DESCRIPTION ""
			::= { mbusEF 84 }

mbusEFValue27		OBJECT-TYPE
			SYNTAX	INTEGER
			ACCESS	read-only
			STATUS	current
	DESCRIPTION ""
			::= { mbusEF 85 }

mbusEFVIF28		OBJECT-TYPE
			SYNTAX	INTEGER
			ACCESS	read-only
			STATUS	current
	DESCRIPTION ""
			::= { mbusEF 86 }

mbusEFValue28		OBJECT-TYPE
			SYNTAX	INTEGER
			ACCESS	read-only
			STATUS	current
	DESCRIPTION ""
			::= { mbusEF 87 }

mbusEFVIF29		OBJECT-TYPE
			SYNTAX	INTEGER
			ACCESS	read-only
			STATUS	current
	DESCRIPTION ""
			::= { mbusEF 88 }

mbusEFValue29		OBJECT-TYPE
			SYNTAX	INTEGER
			ACCESS	read-only
			STATUS	current
	DESCRIPTION ""
			::= { mbusEF 89 }

mbusEFVIF2A		OBJECT-TYPE
			SYNTAX	INTEGER
			ACCESS	read-only
			STATUS	current
	DESCRIPTION ""
			::= { mbusEF 90 }

mbusEFValue2A		OBJECT-TYPE
			SYNTAX	INTEGER
			ACCESS	read-only
			STATUS	current
	DESCRIPTION ""
			::= { mbusEF 91 }

mbusEFVIF2B		OBJECT-TYPE
			SYNTAX	INTEGER
			ACCESS	read-only
			STATUS	current
	DESCRIPTION ""
			::= { mbusEF 92 }

mbusEFValue2B		OBJECT-TYPE
			SYNTAX	INTEGER
			ACCESS	read-only
			STATUS	current
	DESCRIPTION ""
			::= { mbusEF 93 }

mbusEFVIF2C		OBJECT-TYPE
			SYNTAX	INTEGER
			ACCESS	read-only
			STATUS	current
	DESCRIPTION ""
			::= { mbusEF 94 }

mbusEFValue2C		OBJECT-TYPE
			SYNTAX	INTEGER
			ACCESS	read-only
			STATUS	current
	DESCRIPTION ""
			::= { mbusEF 95 }

mbusEFVIF2D		OBJECT-TYPE
			SYNTAX	INTEGER
			ACCESS	read-only
			STATUS	current
	DESCRIPTION ""
			::= { mbusEF 96 }

mbusEFValue2D		OBJECT-TYPE
			SYNTAX	INTEGER
			ACCESS	read-only
			STATUS	current
	DESCRIPTION ""
			::= { mbusEF 97 }

mbusEFVIF2E		OBJECT-TYPE
			SYNTAX	INTEGER
			ACCESS	read-only
			STATUS	current
	DESCRIPTION ""
			::= { mbusEF 98 }

mbusEFValue2E		OBJECT-TYPE
			SYNTAX	INTEGER
			ACCESS	read-only
			STATUS	current
	DESCRIPTION ""
			::= { mbusEF 99 }

mbusEFVIF2F		OBJECT-TYPE
			SYNTAX	INTEGER
			ACCESS	read-only
			STATUS	current
	DESCRIPTION ""
			::= { mbusEF 100 }

mbusEFValue2F		OBJECT-TYPE
			SYNTAX	INTEGER
			ACCESS	read-only
			STATUS	current
	DESCRIPTION ""
			::= { mbusEF 101 }

mbusF0			OBJECT IDENTIFIER ::= { mbus 240 }

mbusF0IdNumber		OBJECT-TYPE
			SYNTAX	Gauge
			ACCESS	read-only
			STATUS	current
	DESCRIPTION ""
			::= { mbusF0 1 }

mbusF0Manufacturer	OBJECT-TYPE
			SYNTAX	Gauge
			ACCESS	read-only
			STATUS	current
	DESCRIPTION ""
			::= { mbusF0 2 }

mbusF0Version		OBJECT-TYPE
			SYNTAX	Gauge
			ACCESS	read-only
			STATUS	current
	DESCRIPTION ""
			::= { mbusF0 3 }

mbusF0Medium		OBJECT-TYPE
			SYNTAX	Gauge
			ACCESS	read-only
			STATUS	current
	DESCRIPTION ""
			::= { mbusF0 4 }

mbusF0Status		OBJECT-TYPE
			SYNTAX	Gauge
			ACCESS	read-only
			STATUS	current
	DESCRIPTION ""
			::= { mbusF0 5 }

mbusF0VIF00		OBJECT-TYPE
			SYNTAX	INTEGER
			ACCESS	read-only
			STATUS	current
	DESCRIPTION ""
			::= { mbusF0 6 }

mbusF0Value00		OBJECT-TYPE
			SYNTAX	INTEGER
			ACCESS	read-only
			STATUS	current
	DESCRIPTION ""
			::= { mbusF0 7 }

mbusF0VIF01		OBJECT-TYPE
			SYNTAX	INTEGER
			ACCESS	read-only
			STATUS	current
	DESCRIPTION ""
			::= { mbusF0 8 }

mbusF0Value01		OBJECT-TYPE
			SYNTAX	INTEGER
			ACCESS	read-only
			STATUS	current
	DESCRIPTION ""
			::= { mbusF0 9 }

mbusF0VIF02		OBJECT-TYPE
			SYNTAX	INTEGER
			ACCESS	read-only
			STATUS	current
	DESCRIPTION ""
			::= { mbusF0 10 }

mbusF0Value02		OBJECT-TYPE
			SYNTAX	INTEGER
			ACCESS	read-only
			STATUS	current
	DESCRIPTION ""
			::= { mbusF0 11 }

mbusF0VIF03		OBJECT-TYPE
			SYNTAX	INTEGER
			ACCESS	read-only
			STATUS	current
	DESCRIPTION ""
			::= { mbusF0 12 }

mbusF0Value03		OBJECT-TYPE
			SYNTAX	INTEGER
			ACCESS	read-only
			STATUS	current
	DESCRIPTION ""
			::= { mbusF0 13 }

mbusF0VIF04		OBJECT-TYPE
			SYNTAX	INTEGER
			ACCESS	read-only
			STATUS	current
	DESCRIPTION ""
			::= { mbusF0 14 }

mbusF0Value04		OBJECT-TYPE
			SYNTAX	INTEGER
			ACCESS	read-only
			STATUS	current
	DESCRIPTION ""
			::= { mbusF0 15 }

mbusF0VIF05		OBJECT-TYPE
			SYNTAX	INTEGER
			ACCESS	read-only
			STATUS	current
	DESCRIPTION ""
			::= { mbusF0 16 }

mbusF0Value05		OBJECT-TYPE
			SYNTAX	INTEGER
			ACCESS	read-only
			STATUS	current
	DESCRIPTION ""
			::= { mbusF0 17 }

mbusF0VIF06		OBJECT-TYPE
			SYNTAX	INTEGER
			ACCESS	read-only
			STATUS	current
	DESCRIPTION ""
			::= { mbusF0 18 }

mbusF0Value06		OBJECT-TYPE
			SYNTAX	INTEGER
			ACCESS	read-only
			STATUS	current
	DESCRIPTION ""
			::= { mbusF0 19 }

mbusF0VIF07		OBJECT-TYPE
			SYNTAX	INTEGER
			ACCESS	read-only
			STATUS	current
	DESCRIPTION ""
			::= { mbusF0 20 }

mbusF0Value07		OBJECT-TYPE
			SYNTAX	INTEGER
			ACCESS	read-only
			STATUS	current
	DESCRIPTION ""
			::= { mbusF0 21 }

mbusF0VIF08		OBJECT-TYPE
			SYNTAX	INTEGER
			ACCESS	read-only
			STATUS	current
	DESCRIPTION ""
			::= { mbusF0 22 }

mbusF0Value08		OBJECT-TYPE
			SYNTAX	INTEGER
			ACCESS	read-only
			STATUS	current
	DESCRIPTION ""
			::= { mbusF0 23 }

mbusF0VIF09		OBJECT-TYPE
			SYNTAX	INTEGER
			ACCESS	read-only
			STATUS	current
	DESCRIPTION ""
			::= { mbusF0 24 }

mbusF0Value09		OBJECT-TYPE
			SYNTAX	INTEGER
			ACCESS	read-only
			STATUS	current
	DESCRIPTION ""
			::= { mbusF0 25 }

mbusF0VIF0A		OBJECT-TYPE
			SYNTAX	INTEGER
			ACCESS	read-only
			STATUS	current
	DESCRIPTION ""
			::= { mbusF0 26 }

mbusF0Value0A		OBJECT-TYPE
			SYNTAX	INTEGER
			ACCESS	read-only
			STATUS	current
	DESCRIPTION ""
			::= { mbusF0 27 }

mbusF0VIF0B		OBJECT-TYPE
			SYNTAX	INTEGER
			ACCESS	read-only
			STATUS	current
	DESCRIPTION ""
			::= { mbusF0 28 }

mbusF0Value0B		OBJECT-TYPE
			SYNTAX	INTEGER
			ACCESS	read-only
			STATUS	current
	DESCRIPTION ""
			::= { mbusF0 29 }

mbusF0VIF0C		OBJECT-TYPE
			SYNTAX	INTEGER
			ACCESS	read-only
			STATUS	current
	DESCRIPTION ""
			::= { mbusF0 30 }

mbusF0Value0C		OBJECT-TYPE
			SYNTAX	INTEGER
			ACCESS	read-only
			STATUS	current
	DESCRIPTION ""
			::= { mbusF0 31 }

mbusF0VIF0D		OBJECT-TYPE
			SYNTAX	INTEGER
			ACCESS	read-only
			STATUS	current
	DESCRIPTION ""
			::= { mbusF0 32 }

mbusF0Value0D		OBJECT-TYPE
			SYNTAX	INTEGER
			ACCESS	read-only
			STATUS	current
	DESCRIPTION ""
			::= { mbusF0 33 }

mbusF0VIF0E		OBJECT-TYPE
			SYNTAX	INTEGER
			ACCESS	read-only
			STATUS	current
	DESCRIPTION ""
			::= { mbusF0 34 }

mbusF0Value0E		OBJECT-TYPE
			SYNTAX	INTEGER
			ACCESS	read-only
			STATUS	current
	DESCRIPTION ""
			::= { mbusF0 35 }

mbusF0VIF0F		OBJECT-TYPE
			SYNTAX	INTEGER
			ACCESS	read-only
			STATUS	current
	DESCRIPTION ""
			::= { mbusF0 36 }

mbusF0Value0F		OBJECT-TYPE
			SYNTAX	INTEGER
			ACCESS	read-only
			STATUS	current
	DESCRIPTION ""
			::= { mbusF0 37 }

mbusF0VIF10		OBJECT-TYPE
			SYNTAX	INTEGER
			ACCESS	read-only
			STATUS	current
	DESCRIPTION ""
			::= { mbusF0 38 }

mbusF0Value10		OBJECT-TYPE
			SYNTAX	INTEGER
			ACCESS	read-only
			STATUS	current
	DESCRIPTION ""
			::= { mbusF0 39 }

mbusF0VIF11		OBJECT-TYPE
			SYNTAX	INTEGER
			ACCESS	read-only
			STATUS	current
	DESCRIPTION ""
			::= { mbusF0 40 }

mbusF0Value11		OBJECT-TYPE
			SYNTAX	INTEGER
			ACCESS	read-only
			STATUS	current
	DESCRIPTION ""
			::= { mbusF0 41 }

mbusF0VIF12		OBJECT-TYPE
			SYNTAX	INTEGER
			ACCESS	read-only
			STATUS	current
	DESCRIPTION ""
			::= { mbusF0 42 }

mbusF0Value12		OBJECT-TYPE
			SYNTAX	INTEGER
			ACCESS	read-only
			STATUS	current
	DESCRIPTION ""
			::= { mbusF0 43 }

mbusF0VIF13		OBJECT-TYPE
			SYNTAX	INTEGER
			ACCESS	read-only
			STATUS	current
	DESCRIPTION ""
			::= { mbusF0 44 }

mbusF0Value13		OBJECT-TYPE
			SYNTAX	INTEGER
			ACCESS	read-only
			STATUS	current
	DESCRIPTION ""
			::= { mbusF0 45 }

mbusF0VIF14		OBJECT-TYPE
			SYNTAX	INTEGER
			ACCESS	read-only
			STATUS	current
	DESCRIPTION ""
			::= { mbusF0 46 }

mbusF0Value14		OBJECT-TYPE
			SYNTAX	INTEGER
			ACCESS	read-only
			STATUS	current
	DESCRIPTION ""
			::= { mbusF0 47 }

mbusF0VIF15		OBJECT-TYPE
			SYNTAX	INTEGER
			ACCESS	read-only
			STATUS	current
	DESCRIPTION ""
			::= { mbusF0 48 }

mbusF0Value15		OBJECT-TYPE
			SYNTAX	INTEGER
			ACCESS	read-only
			STATUS	current
	DESCRIPTION ""
			::= { mbusF0 49 }

mbusF0VIF16		OBJECT-TYPE
			SYNTAX	INTEGER
			ACCESS	read-only
			STATUS	current
	DESCRIPTION ""
			::= { mbusF0 50 }

mbusF0Value16		OBJECT-TYPE
			SYNTAX	INTEGER
			ACCESS	read-only
			STATUS	current
	DESCRIPTION ""
			::= { mbusF0 51 }

mbusF0VIF17		OBJECT-TYPE
			SYNTAX	INTEGER
			ACCESS	read-only
			STATUS	current
	DESCRIPTION ""
			::= { mbusF0 52 }

mbusF0Value17		OBJECT-TYPE
			SYNTAX	INTEGER
			ACCESS	read-only
			STATUS	current
	DESCRIPTION ""
			::= { mbusF0 53 }

mbusF0VIF18		OBJECT-TYPE
			SYNTAX	INTEGER
			ACCESS	read-only
			STATUS	current
	DESCRIPTION ""
			::= { mbusF0 54 }

mbusF0Value18		OBJECT-TYPE
			SYNTAX	INTEGER
			ACCESS	read-only
			STATUS	current
	DESCRIPTION ""
			::= { mbusF0 55 }

mbusF0VIF19		OBJECT-TYPE
			SYNTAX	INTEGER
			ACCESS	read-only
			STATUS	current
	DESCRIPTION ""
			::= { mbusF0 56 }

mbusF0Value19		OBJECT-TYPE
			SYNTAX	INTEGER
			ACCESS	read-only
			STATUS	current
	DESCRIPTION ""
			::= { mbusF0 57 }

mbusF0VIF1A		OBJECT-TYPE
			SYNTAX	INTEGER
			ACCESS	read-only
			STATUS	current
	DESCRIPTION ""
			::= { mbusF0 58 }

mbusF0Value1A		OBJECT-TYPE
			SYNTAX	INTEGER
			ACCESS	read-only
			STATUS	current
	DESCRIPTION ""
			::= { mbusF0 59 }

mbusF0VIF1B		OBJECT-TYPE
			SYNTAX	INTEGER
			ACCESS	read-only
			STATUS	current
	DESCRIPTION ""
			::= { mbusF0 60 }

mbusF0Value1B		OBJECT-TYPE
			SYNTAX	INTEGER
			ACCESS	read-only
			STATUS	current
	DESCRIPTION ""
			::= { mbusF0 61 }

mbusF0VIF1C		OBJECT-TYPE
			SYNTAX	INTEGER
			ACCESS	read-only
			STATUS	current
	DESCRIPTION ""
			::= { mbusF0 62 }

mbusF0Value1C		OBJECT-TYPE
			SYNTAX	INTEGER
			ACCESS	read-only
			STATUS	current
	DESCRIPTION ""
			::= { mbusF0 63 }

mbusF0VIF1D		OBJECT-TYPE
			SYNTAX	INTEGER
			ACCESS	read-only
			STATUS	current
	DESCRIPTION ""
			::= { mbusF0 64 }

mbusF0Value1D		OBJECT-TYPE
			SYNTAX	INTEGER
			ACCESS	read-only
			STATUS	current
	DESCRIPTION ""
			::= { mbusF0 65 }

mbusF0VIF1E		OBJECT-TYPE
			SYNTAX	INTEGER
			ACCESS	read-only
			STATUS	current
	DESCRIPTION ""
			::= { mbusF0 66 }

mbusF0Value1E		OBJECT-TYPE
			SYNTAX	INTEGER
			ACCESS	read-only
			STATUS	current
	DESCRIPTION ""
			::= { mbusF0 67 }

mbusF0VIF1F		OBJECT-TYPE
			SYNTAX	INTEGER
			ACCESS	read-only
			STATUS	current
	DESCRIPTION ""
			::= { mbusF0 68 }

mbusF0Value1F		OBJECT-TYPE
			SYNTAX	INTEGER
			ACCESS	read-only
			STATUS	current
	DESCRIPTION ""
			::= { mbusF0 69 }

mbusF0VIF20		OBJECT-TYPE
			SYNTAX	INTEGER
			ACCESS	read-only
			STATUS	current
	DESCRIPTION ""
			::= { mbusF0 70 }

mbusF0Value20		OBJECT-TYPE
			SYNTAX	INTEGER
			ACCESS	read-only
			STATUS	current
	DESCRIPTION ""
			::= { mbusF0 71 }

mbusF0VIF21		OBJECT-TYPE
			SYNTAX	INTEGER
			ACCESS	read-only
			STATUS	current
	DESCRIPTION ""
			::= { mbusF0 72 }

mbusF0Value21		OBJECT-TYPE
			SYNTAX	INTEGER
			ACCESS	read-only
			STATUS	current
	DESCRIPTION ""
			::= { mbusF0 73 }

mbusF0VIF22		OBJECT-TYPE
			SYNTAX	INTEGER
			ACCESS	read-only
			STATUS	current
	DESCRIPTION ""
			::= { mbusF0 74 }

mbusF0Value22		OBJECT-TYPE
			SYNTAX	INTEGER
			ACCESS	read-only
			STATUS	current
	DESCRIPTION ""
			::= { mbusF0 75 }

mbusF0VIF23		OBJECT-TYPE
			SYNTAX	INTEGER
			ACCESS	read-only
			STATUS	current
	DESCRIPTION ""
			::= { mbusF0 76 }

mbusF0Value23		OBJECT-TYPE
			SYNTAX	INTEGER
			ACCESS	read-only
			STATUS	current
	DESCRIPTION ""
			::= { mbusF0 77 }

mbusF0VIF24		OBJECT-TYPE
			SYNTAX	INTEGER
			ACCESS	read-only
			STATUS	current
	DESCRIPTION ""
			::= { mbusF0 78 }

mbusF0Value24		OBJECT-TYPE
			SYNTAX	INTEGER
			ACCESS	read-only
			STATUS	current
	DESCRIPTION ""
			::= { mbusF0 79 }

mbusF0VIF25		OBJECT-TYPE
			SYNTAX	INTEGER
			ACCESS	read-only
			STATUS	current
	DESCRIPTION ""
			::= { mbusF0 80 }

mbusF0Value25		OBJECT-TYPE
			SYNTAX	INTEGER
			ACCESS	read-only
			STATUS	current
	DESCRIPTION ""
			::= { mbusF0 81 }

mbusF0VIF26		OBJECT-TYPE
			SYNTAX	INTEGER
			ACCESS	read-only
			STATUS	current
	DESCRIPTION ""
			::= { mbusF0 82 }

mbusF0Value26		OBJECT-TYPE
			SYNTAX	INTEGER
			ACCESS	read-only
			STATUS	current
	DESCRIPTION ""
			::= { mbusF0 83 }

mbusF0VIF27		OBJECT-TYPE
			SYNTAX	INTEGER
			ACCESS	read-only
			STATUS	current
	DESCRIPTION ""
			::= { mbusF0 84 }

mbusF0Value27		OBJECT-TYPE
			SYNTAX	INTEGER
			ACCESS	read-only
			STATUS	current
	DESCRIPTION ""
			::= { mbusF0 85 }

mbusF0VIF28		OBJECT-TYPE
			SYNTAX	INTEGER
			ACCESS	read-only
			STATUS	current
	DESCRIPTION ""
			::= { mbusF0 86 }

mbusF0Value28		OBJECT-TYPE
			SYNTAX	INTEGER
			ACCESS	read-only
			STATUS	current
	DESCRIPTION ""
			::= { mbusF0 87 }

mbusF0VIF29		OBJECT-TYPE
			SYNTAX	INTEGER
			ACCESS	read-only
			STATUS	current
	DESCRIPTION ""
			::= { mbusF0 88 }

mbusF0Value29		OBJECT-TYPE
			SYNTAX	INTEGER
			ACCESS	read-only
			STATUS	current
	DESCRIPTION ""
			::= { mbusF0 89 }

mbusF0VIF2A		OBJECT-TYPE
			SYNTAX	INTEGER
			ACCESS	read-only
			STATUS	current
	DESCRIPTION ""
			::= { mbusF0 90 }

mbusF0Value2A		OBJECT-TYPE
			SYNTAX	INTEGER
			ACCESS	read-only
			STATUS	current
	DESCRIPTION ""
			::= { mbusF0 91 }

mbusF0VIF2B		OBJECT-TYPE
			SYNTAX	INTEGER
			ACCESS	read-only
			STATUS	current
	DESCRIPTION ""
			::= { mbusF0 92 }

mbusF0Value2B		OBJECT-TYPE
			SYNTAX	INTEGER
			ACCESS	read-only
			STATUS	current
	DESCRIPTION ""
			::= { mbusF0 93 }

mbusF0VIF2C		OBJECT-TYPE
			SYNTAX	INTEGER
			ACCESS	read-only
			STATUS	current
	DESCRIPTION ""
			::= { mbusF0 94 }

mbusF0Value2C		OBJECT-TYPE
			SYNTAX	INTEGER
			ACCESS	read-only
			STATUS	current
	DESCRIPTION ""
			::= { mbusF0 95 }

mbusF0VIF2D		OBJECT-TYPE
			SYNTAX	INTEGER
			ACCESS	read-only
			STATUS	current
	DESCRIPTION ""
			::= { mbusF0 96 }

mbusF0Value2D		OBJECT-TYPE
			SYNTAX	INTEGER
			ACCESS	read-only
			STATUS	current
	DESCRIPTION ""
			::= { mbusF0 97 }

mbusF0VIF2E		OBJECT-TYPE
			SYNTAX	INTEGER
			ACCESS	read-only
			STATUS	current
	DESCRIPTION ""
			::= { mbusF0 98 }

mbusF0Value2E		OBJECT-TYPE
			SYNTAX	INTEGER
			ACCESS	read-only
			STATUS	current
	DESCRIPTION ""
			::= { mbusF0 99 }

mbusF0VIF2F		OBJECT-TYPE
			SYNTAX	INTEGER
			ACCESS	read-only
			STATUS	current
	DESCRIPTION ""
			::= { mbusF0 100 }

mbusF0Value2F		OBJECT-TYPE
			SYNTAX	INTEGER
			ACCESS	read-only
			STATUS	current
	DESCRIPTION ""
			::= { mbusF0 101 }

mbusF1			OBJECT IDENTIFIER ::= { mbus 241 }

mbusF1IdNumber		OBJECT-TYPE
			SYNTAX	Gauge
			ACCESS	read-only
			STATUS	current
	DESCRIPTION ""
			::= { mbusF1 1 }

mbusF1Manufacturer	OBJECT-TYPE
			SYNTAX	Gauge
			ACCESS	read-only
			STATUS	current
	DESCRIPTION ""
			::= { mbusF1 2 }

mbusF1Version		OBJECT-TYPE
			SYNTAX	Gauge
			ACCESS	read-only
			STATUS	current
	DESCRIPTION ""
			::= { mbusF1 3 }

mbusF1Medium		OBJECT-TYPE
			SYNTAX	Gauge
			ACCESS	read-only
			STATUS	current
	DESCRIPTION ""
			::= { mbusF1 4 }

mbusF1Status		OBJECT-TYPE
			SYNTAX	Gauge
			ACCESS	read-only
			STATUS	current
	DESCRIPTION ""
			::= { mbusF1 5 }

mbusF1VIF00		OBJECT-TYPE
			SYNTAX	INTEGER
			ACCESS	read-only
			STATUS	current
	DESCRIPTION ""
			::= { mbusF1 6 }

mbusF1Value00		OBJECT-TYPE
			SYNTAX	INTEGER
			ACCESS	read-only
			STATUS	current
	DESCRIPTION ""
			::= { mbusF1 7 }

mbusF1VIF01		OBJECT-TYPE
			SYNTAX	INTEGER
			ACCESS	read-only
			STATUS	current
	DESCRIPTION ""
			::= { mbusF1 8 }

mbusF1Value01		OBJECT-TYPE
			SYNTAX	INTEGER
			ACCESS	read-only
			STATUS	current
	DESCRIPTION ""
			::= { mbusF1 9 }

mbusF1VIF02		OBJECT-TYPE
			SYNTAX	INTEGER
			ACCESS	read-only
			STATUS	current
	DESCRIPTION ""
			::= { mbusF1 10 }

mbusF1Value02		OBJECT-TYPE
			SYNTAX	INTEGER
			ACCESS	read-only
			STATUS	current
	DESCRIPTION ""
			::= { mbusF1 11 }

mbusF1VIF03		OBJECT-TYPE
			SYNTAX	INTEGER
			ACCESS	read-only
			STATUS	current
	DESCRIPTION ""
			::= { mbusF1 12 }

mbusF1Value03		OBJECT-TYPE
			SYNTAX	INTEGER
			ACCESS	read-only
			STATUS	current
	DESCRIPTION ""
			::= { mbusF1 13 }

mbusF1VIF04		OBJECT-TYPE
			SYNTAX	INTEGER
			ACCESS	read-only
			STATUS	current
	DESCRIPTION ""
			::= { mbusF1 14 }

mbusF1Value04		OBJECT-TYPE
			SYNTAX	INTEGER
			ACCESS	read-only
			STATUS	current
	DESCRIPTION ""
			::= { mbusF1 15 }

mbusF1VIF05		OBJECT-TYPE
			SYNTAX	INTEGER
			ACCESS	read-only
			STATUS	current
	DESCRIPTION ""
			::= { mbusF1 16 }

mbusF1Value05		OBJECT-TYPE
			SYNTAX	INTEGER
			ACCESS	read-only
			STATUS	current
	DESCRIPTION ""
			::= { mbusF1 17 }

mbusF1VIF06		OBJECT-TYPE
			SYNTAX	INTEGER
			ACCESS	read-only
			STATUS	current
	DESCRIPTION ""
			::= { mbusF1 18 }

mbusF1Value06		OBJECT-TYPE
			SYNTAX	INTEGER
			ACCESS	read-only
			STATUS	current
	DESCRIPTION ""
			::= { mbusF1 19 }

mbusF1VIF07		OBJECT-TYPE
			SYNTAX	INTEGER
			ACCESS	read-only
			STATUS	current
	DESCRIPTION ""
			::= { mbusF1 20 }

mbusF1Value07		OBJECT-TYPE
			SYNTAX	INTEGER
			ACCESS	read-only
			STATUS	current
	DESCRIPTION ""
			::= { mbusF1 21 }

mbusF1VIF08		OBJECT-TYPE
			SYNTAX	INTEGER
			ACCESS	read-only
			STATUS	current
	DESCRIPTION ""
			::= { mbusF1 22 }

mbusF1Value08		OBJECT-TYPE
			SYNTAX	INTEGER
			ACCESS	read-only
			STATUS	current
	DESCRIPTION ""
			::= { mbusF1 23 }

mbusF1VIF09		OBJECT-TYPE
			SYNTAX	INTEGER
			ACCESS	read-only
			STATUS	current
	DESCRIPTION ""
			::= { mbusF1 24 }

mbusF1Value09		OBJECT-TYPE
			SYNTAX	INTEGER
			ACCESS	read-only
			STATUS	current
	DESCRIPTION ""
			::= { mbusF1 25 }

mbusF1VIF0A		OBJECT-TYPE
			SYNTAX	INTEGER
			ACCESS	read-only
			STATUS	current
	DESCRIPTION ""
			::= { mbusF1 26 }

mbusF1Value0A		OBJECT-TYPE
			SYNTAX	INTEGER
			ACCESS	read-only
			STATUS	current
	DESCRIPTION ""
			::= { mbusF1 27 }

mbusF1VIF0B		OBJECT-TYPE
			SYNTAX	INTEGER
			ACCESS	read-only
			STATUS	current
	DESCRIPTION ""
			::= { mbusF1 28 }

mbusF1Value0B		OBJECT-TYPE
			SYNTAX	INTEGER
			ACCESS	read-only
			STATUS	current
	DESCRIPTION ""
			::= { mbusF1 29 }

mbusF1VIF0C		OBJECT-TYPE
			SYNTAX	INTEGER
			ACCESS	read-only
			STATUS	current
	DESCRIPTION ""
			::= { mbusF1 30 }

mbusF1Value0C		OBJECT-TYPE
			SYNTAX	INTEGER
			ACCESS	read-only
			STATUS	current
	DESCRIPTION ""
			::= { mbusF1 31 }

mbusF1VIF0D		OBJECT-TYPE
			SYNTAX	INTEGER
			ACCESS	read-only
			STATUS	current
	DESCRIPTION ""
			::= { mbusF1 32 }

mbusF1Value0D		OBJECT-TYPE
			SYNTAX	INTEGER
			ACCESS	read-only
			STATUS	current
	DESCRIPTION ""
			::= { mbusF1 33 }

mbusF1VIF0E		OBJECT-TYPE
			SYNTAX	INTEGER
			ACCESS	read-only
			STATUS	current
	DESCRIPTION ""
			::= { mbusF1 34 }

mbusF1Value0E		OBJECT-TYPE
			SYNTAX	INTEGER
			ACCESS	read-only
			STATUS	current
	DESCRIPTION ""
			::= { mbusF1 35 }

mbusF1VIF0F		OBJECT-TYPE
			SYNTAX	INTEGER
			ACCESS	read-only
			STATUS	current
	DESCRIPTION ""
			::= { mbusF1 36 }

mbusF1Value0F		OBJECT-TYPE
			SYNTAX	INTEGER
			ACCESS	read-only
			STATUS	current
	DESCRIPTION ""
			::= { mbusF1 37 }

mbusF1VIF10		OBJECT-TYPE
			SYNTAX	INTEGER
			ACCESS	read-only
			STATUS	current
	DESCRIPTION ""
			::= { mbusF1 38 }

mbusF1Value10		OBJECT-TYPE
			SYNTAX	INTEGER
			ACCESS	read-only
			STATUS	current
	DESCRIPTION ""
			::= { mbusF1 39 }

mbusF1VIF11		OBJECT-TYPE
			SYNTAX	INTEGER
			ACCESS	read-only
			STATUS	current
	DESCRIPTION ""
			::= { mbusF1 40 }

mbusF1Value11		OBJECT-TYPE
			SYNTAX	INTEGER
			ACCESS	read-only
			STATUS	current
	DESCRIPTION ""
			::= { mbusF1 41 }

mbusF1VIF12		OBJECT-TYPE
			SYNTAX	INTEGER
			ACCESS	read-only
			STATUS	current
	DESCRIPTION ""
			::= { mbusF1 42 }

mbusF1Value12		OBJECT-TYPE
			SYNTAX	INTEGER
			ACCESS	read-only
			STATUS	current
	DESCRIPTION ""
			::= { mbusF1 43 }

mbusF1VIF13		OBJECT-TYPE
			SYNTAX	INTEGER
			ACCESS	read-only
			STATUS	current
	DESCRIPTION ""
			::= { mbusF1 44 }

mbusF1Value13		OBJECT-TYPE
			SYNTAX	INTEGER
			ACCESS	read-only
			STATUS	current
	DESCRIPTION ""
			::= { mbusF1 45 }

mbusF1VIF14		OBJECT-TYPE
			SYNTAX	INTEGER
			ACCESS	read-only
			STATUS	current
	DESCRIPTION ""
			::= { mbusF1 46 }

mbusF1Value14		OBJECT-TYPE
			SYNTAX	INTEGER
			ACCESS	read-only
			STATUS	current
	DESCRIPTION ""
			::= { mbusF1 47 }

mbusF1VIF15		OBJECT-TYPE
			SYNTAX	INTEGER
			ACCESS	read-only
			STATUS	current
	DESCRIPTION ""
			::= { mbusF1 48 }

mbusF1Value15		OBJECT-TYPE
			SYNTAX	INTEGER
			ACCESS	read-only
			STATUS	current
	DESCRIPTION ""
			::= { mbusF1 49 }

mbusF1VIF16		OBJECT-TYPE
			SYNTAX	INTEGER
			ACCESS	read-only
			STATUS	current
	DESCRIPTION ""
			::= { mbusF1 50 }

mbusF1Value16		OBJECT-TYPE
			SYNTAX	INTEGER
			ACCESS	read-only
			STATUS	current
	DESCRIPTION ""
			::= { mbusF1 51 }

mbusF1VIF17		OBJECT-TYPE
			SYNTAX	INTEGER
			ACCESS	read-only
			STATUS	current
	DESCRIPTION ""
			::= { mbusF1 52 }

mbusF1Value17		OBJECT-TYPE
			SYNTAX	INTEGER
			ACCESS	read-only
			STATUS	current
	DESCRIPTION ""
			::= { mbusF1 53 }

mbusF1VIF18		OBJECT-TYPE
			SYNTAX	INTEGER
			ACCESS	read-only
			STATUS	current
	DESCRIPTION ""
			::= { mbusF1 54 }

mbusF1Value18		OBJECT-TYPE
			SYNTAX	INTEGER
			ACCESS	read-only
			STATUS	current
	DESCRIPTION ""
			::= { mbusF1 55 }

mbusF1VIF19		OBJECT-TYPE
			SYNTAX	INTEGER
			ACCESS	read-only
			STATUS	current
	DESCRIPTION ""
			::= { mbusF1 56 }

mbusF1Value19		OBJECT-TYPE
			SYNTAX	INTEGER
			ACCESS	read-only
			STATUS	current
	DESCRIPTION ""
			::= { mbusF1 57 }

mbusF1VIF1A		OBJECT-TYPE
			SYNTAX	INTEGER
			ACCESS	read-only
			STATUS	current
	DESCRIPTION ""
			::= { mbusF1 58 }

mbusF1Value1A		OBJECT-TYPE
			SYNTAX	INTEGER
			ACCESS	read-only
			STATUS	current
	DESCRIPTION ""
			::= { mbusF1 59 }

mbusF1VIF1B		OBJECT-TYPE
			SYNTAX	INTEGER
			ACCESS	read-only
			STATUS	current
	DESCRIPTION ""
			::= { mbusF1 60 }

mbusF1Value1B		OBJECT-TYPE
			SYNTAX	INTEGER
			ACCESS	read-only
			STATUS	current
	DESCRIPTION ""
			::= { mbusF1 61 }

mbusF1VIF1C		OBJECT-TYPE
			SYNTAX	INTEGER
			ACCESS	read-only
			STATUS	current
	DESCRIPTION ""
			::= { mbusF1 62 }

mbusF1Value1C		OBJECT-TYPE
			SYNTAX	INTEGER
			ACCESS	read-only
			STATUS	current
	DESCRIPTION ""
			::= { mbusF1 63 }

mbusF1VIF1D		OBJECT-TYPE
			SYNTAX	INTEGER
			ACCESS	read-only
			STATUS	current
	DESCRIPTION ""
			::= { mbusF1 64 }

mbusF1Value1D		OBJECT-TYPE
			SYNTAX	INTEGER
			ACCESS	read-only
			STATUS	current
	DESCRIPTION ""
			::= { mbusF1 65 }

mbusF1VIF1E		OBJECT-TYPE
			SYNTAX	INTEGER
			ACCESS	read-only
			STATUS	current
	DESCRIPTION ""
			::= { mbusF1 66 }

mbusF1Value1E		OBJECT-TYPE
			SYNTAX	INTEGER
			ACCESS	read-only
			STATUS	current
	DESCRIPTION ""
			::= { mbusF1 67 }

mbusF1VIF1F		OBJECT-TYPE
			SYNTAX	INTEGER
			ACCESS	read-only
			STATUS	current
	DESCRIPTION ""
			::= { mbusF1 68 }

mbusF1Value1F		OBJECT-TYPE
			SYNTAX	INTEGER
			ACCESS	read-only
			STATUS	current
	DESCRIPTION ""
			::= { mbusF1 69 }

mbusF1VIF20		OBJECT-TYPE
			SYNTAX	INTEGER
			ACCESS	read-only
			STATUS	current
	DESCRIPTION ""
			::= { mbusF1 70 }

mbusF1Value20		OBJECT-TYPE
			SYNTAX	INTEGER
			ACCESS	read-only
			STATUS	current
	DESCRIPTION ""
			::= { mbusF1 71 }

mbusF1VIF21		OBJECT-TYPE
			SYNTAX	INTEGER
			ACCESS	read-only
			STATUS	current
	DESCRIPTION ""
			::= { mbusF1 72 }

mbusF1Value21		OBJECT-TYPE
			SYNTAX	INTEGER
			ACCESS	read-only
			STATUS	current
	DESCRIPTION ""
			::= { mbusF1 73 }

mbusF1VIF22		OBJECT-TYPE
			SYNTAX	INTEGER
			ACCESS	read-only
			STATUS	current
	DESCRIPTION ""
			::= { mbusF1 74 }

mbusF1Value22		OBJECT-TYPE
			SYNTAX	INTEGER
			ACCESS	read-only
			STATUS	current
	DESCRIPTION ""
			::= { mbusF1 75 }

mbusF1VIF23		OBJECT-TYPE
			SYNTAX	INTEGER
			ACCESS	read-only
			STATUS	current
	DESCRIPTION ""
			::= { mbusF1 76 }

mbusF1Value23		OBJECT-TYPE
			SYNTAX	INTEGER
			ACCESS	read-only
			STATUS	current
	DESCRIPTION ""
			::= { mbusF1 77 }

mbusF1VIF24		OBJECT-TYPE
			SYNTAX	INTEGER
			ACCESS	read-only
			STATUS	current
	DESCRIPTION ""
			::= { mbusF1 78 }

mbusF1Value24		OBJECT-TYPE
			SYNTAX	INTEGER
			ACCESS	read-only
			STATUS	current
	DESCRIPTION ""
			::= { mbusF1 79 }

mbusF1VIF25		OBJECT-TYPE
			SYNTAX	INTEGER
			ACCESS	read-only
			STATUS	current
	DESCRIPTION ""
			::= { mbusF1 80 }

mbusF1Value25		OBJECT-TYPE
			SYNTAX	INTEGER
			ACCESS	read-only
			STATUS	current
	DESCRIPTION ""
			::= { mbusF1 81 }

mbusF1VIF26		OBJECT-TYPE
			SYNTAX	INTEGER
			ACCESS	read-only
			STATUS	current
	DESCRIPTION ""
			::= { mbusF1 82 }

mbusF1Value26		OBJECT-TYPE
			SYNTAX	INTEGER
			ACCESS	read-only
			STATUS	current
	DESCRIPTION ""
			::= { mbusF1 83 }

mbusF1VIF27		OBJECT-TYPE
			SYNTAX	INTEGER
			ACCESS	read-only
			STATUS	current
	DESCRIPTION ""
			::= { mbusF1 84 }

mbusF1Value27		OBJECT-TYPE
			SYNTAX	INTEGER
			ACCESS	read-only
			STATUS	current
	DESCRIPTION ""
			::= { mbusF1 85 }

mbusF1VIF28		OBJECT-TYPE
			SYNTAX	INTEGER
			ACCESS	read-only
			STATUS	current
	DESCRIPTION ""
			::= { mbusF1 86 }

mbusF1Value28		OBJECT-TYPE
			SYNTAX	INTEGER
			ACCESS	read-only
			STATUS	current
	DESCRIPTION ""
			::= { mbusF1 87 }

mbusF1VIF29		OBJECT-TYPE
			SYNTAX	INTEGER
			ACCESS	read-only
			STATUS	current
	DESCRIPTION ""
			::= { mbusF1 88 }

mbusF1Value29		OBJECT-TYPE
			SYNTAX	INTEGER
			ACCESS	read-only
			STATUS	current
	DESCRIPTION ""
			::= { mbusF1 89 }

mbusF1VIF2A		OBJECT-TYPE
			SYNTAX	INTEGER
			ACCESS	read-only
			STATUS	current
	DESCRIPTION ""
			::= { mbusF1 90 }

mbusF1Value2A		OBJECT-TYPE
			SYNTAX	INTEGER
			ACCESS	read-only
			STATUS	current
	DESCRIPTION ""
			::= { mbusF1 91 }

mbusF1VIF2B		OBJECT-TYPE
			SYNTAX	INTEGER
			ACCESS	read-only
			STATUS	current
	DESCRIPTION ""
			::= { mbusF1 92 }

mbusF1Value2B		OBJECT-TYPE
			SYNTAX	INTEGER
			ACCESS	read-only
			STATUS	current
	DESCRIPTION ""
			::= { mbusF1 93 }

mbusF1VIF2C		OBJECT-TYPE
			SYNTAX	INTEGER
			ACCESS	read-only
			STATUS	current
	DESCRIPTION ""
			::= { mbusF1 94 }

mbusF1Value2C		OBJECT-TYPE
			SYNTAX	INTEGER
			ACCESS	read-only
			STATUS	current
	DESCRIPTION ""
			::= { mbusF1 95 }

mbusF1VIF2D		OBJECT-TYPE
			SYNTAX	INTEGER
			ACCESS	read-only
			STATUS	current
	DESCRIPTION ""
			::= { mbusF1 96 }

mbusF1Value2D		OBJECT-TYPE
			SYNTAX	INTEGER
			ACCESS	read-only
			STATUS	current
	DESCRIPTION ""
			::= { mbusF1 97 }

mbusF1VIF2E		OBJECT-TYPE
			SYNTAX	INTEGER
			ACCESS	read-only
			STATUS	current
	DESCRIPTION ""
			::= { mbusF1 98 }

mbusF1Value2E		OBJECT-TYPE
			SYNTAX	INTEGER
			ACCESS	read-only
			STATUS	current
	DESCRIPTION ""
			::= { mbusF1 99 }

mbusF1VIF2F		OBJECT-TYPE
			SYNTAX	INTEGER
			ACCESS	read-only
			STATUS	current
	DESCRIPTION ""
			::= { mbusF1 100 }

mbusF1Value2F		OBJECT-TYPE
			SYNTAX	INTEGER
			ACCESS	read-only
			STATUS	current
	DESCRIPTION ""
			::= { mbusF1 101 }

mbusF2			OBJECT IDENTIFIER ::= { mbus 242 }

mbusF2IdNumber		OBJECT-TYPE
			SYNTAX	Gauge
			ACCESS	read-only
			STATUS	current
	DESCRIPTION ""
			::= { mbusF2 1 }

mbusF2Manufacturer	OBJECT-TYPE
			SYNTAX	Gauge
			ACCESS	read-only
			STATUS	current
	DESCRIPTION ""
			::= { mbusF2 2 }

mbusF2Version		OBJECT-TYPE
			SYNTAX	Gauge
			ACCESS	read-only
			STATUS	current
	DESCRIPTION ""
			::= { mbusF2 3 }

mbusF2Medium		OBJECT-TYPE
			SYNTAX	Gauge
			ACCESS	read-only
			STATUS	current
	DESCRIPTION ""
			::= { mbusF2 4 }

mbusF2Status		OBJECT-TYPE
			SYNTAX	Gauge
			ACCESS	read-only
			STATUS	current
	DESCRIPTION ""
			::= { mbusF2 5 }

mbusF2VIF00		OBJECT-TYPE
			SYNTAX	INTEGER
			ACCESS	read-only
			STATUS	current
	DESCRIPTION ""
			::= { mbusF2 6 }

mbusF2Value00		OBJECT-TYPE
			SYNTAX	INTEGER
			ACCESS	read-only
			STATUS	current
	DESCRIPTION ""
			::= { mbusF2 7 }

mbusF2VIF01		OBJECT-TYPE
			SYNTAX	INTEGER
			ACCESS	read-only
			STATUS	current
	DESCRIPTION ""
			::= { mbusF2 8 }

mbusF2Value01		OBJECT-TYPE
			SYNTAX	INTEGER
			ACCESS	read-only
			STATUS	current
	DESCRIPTION ""
			::= { mbusF2 9 }

mbusF2VIF02		OBJECT-TYPE
			SYNTAX	INTEGER
			ACCESS	read-only
			STATUS	current
	DESCRIPTION ""
			::= { mbusF2 10 }

mbusF2Value02		OBJECT-TYPE
			SYNTAX	INTEGER
			ACCESS	read-only
			STATUS	current
	DESCRIPTION ""
			::= { mbusF2 11 }

mbusF2VIF03		OBJECT-TYPE
			SYNTAX	INTEGER
			ACCESS	read-only
			STATUS	current
	DESCRIPTION ""
			::= { mbusF2 12 }

mbusF2Value03		OBJECT-TYPE
			SYNTAX	INTEGER
			ACCESS	read-only
			STATUS	current
	DESCRIPTION ""
			::= { mbusF2 13 }

mbusF2VIF04		OBJECT-TYPE
			SYNTAX	INTEGER
			ACCESS	read-only
			STATUS	current
	DESCRIPTION ""
			::= { mbusF2 14 }

mbusF2Value04		OBJECT-TYPE
			SYNTAX	INTEGER
			ACCESS	read-only
			STATUS	current
	DESCRIPTION ""
			::= { mbusF2 15 }

mbusF2VIF05		OBJECT-TYPE
			SYNTAX	INTEGER
			ACCESS	read-only
			STATUS	current
	DESCRIPTION ""
			::= { mbusF2 16 }

mbusF2Value05		OBJECT-TYPE
			SYNTAX	INTEGER
			ACCESS	read-only
			STATUS	current
	DESCRIPTION ""
			::= { mbusF2 17 }

mbusF2VIF06		OBJECT-TYPE
			SYNTAX	INTEGER
			ACCESS	read-only
			STATUS	current
	DESCRIPTION ""
			::= { mbusF2 18 }

mbusF2Value06		OBJECT-TYPE
			SYNTAX	INTEGER
			ACCESS	read-only
			STATUS	current
	DESCRIPTION ""
			::= { mbusF2 19 }

mbusF2VIF07		OBJECT-TYPE
			SYNTAX	INTEGER
			ACCESS	read-only
			STATUS	current
	DESCRIPTION ""
			::= { mbusF2 20 }

mbusF2Value07		OBJECT-TYPE
			SYNTAX	INTEGER
			ACCESS	read-only
			STATUS	current
	DESCRIPTION ""
			::= { mbusF2 21 }

mbusF2VIF08		OBJECT-TYPE
			SYNTAX	INTEGER
			ACCESS	read-only
			STATUS	current
	DESCRIPTION ""
			::= { mbusF2 22 }

mbusF2Value08		OBJECT-TYPE
			SYNTAX	INTEGER
			ACCESS	read-only
			STATUS	current
	DESCRIPTION ""
			::= { mbusF2 23 }

mbusF2VIF09		OBJECT-TYPE
			SYNTAX	INTEGER
			ACCESS	read-only
			STATUS	current
	DESCRIPTION ""
			::= { mbusF2 24 }

mbusF2Value09		OBJECT-TYPE
			SYNTAX	INTEGER
			ACCESS	read-only
			STATUS	current
	DESCRIPTION ""
			::= { mbusF2 25 }

mbusF2VIF0A		OBJECT-TYPE
			SYNTAX	INTEGER
			ACCESS	read-only
			STATUS	current
	DESCRIPTION ""
			::= { mbusF2 26 }

mbusF2Value0A		OBJECT-TYPE
			SYNTAX	INTEGER
			ACCESS	read-only
			STATUS	current
	DESCRIPTION ""
			::= { mbusF2 27 }

mbusF2VIF0B		OBJECT-TYPE
			SYNTAX	INTEGER
			ACCESS	read-only
			STATUS	current
	DESCRIPTION ""
			::= { mbusF2 28 }

mbusF2Value0B		OBJECT-TYPE
			SYNTAX	INTEGER
			ACCESS	read-only
			STATUS	current
	DESCRIPTION ""
			::= { mbusF2 29 }

mbusF2VIF0C		OBJECT-TYPE
			SYNTAX	INTEGER
			ACCESS	read-only
			STATUS	current
	DESCRIPTION ""
			::= { mbusF2 30 }

mbusF2Value0C		OBJECT-TYPE
			SYNTAX	INTEGER
			ACCESS	read-only
			STATUS	current
	DESCRIPTION ""
			::= { mbusF2 31 }

mbusF2VIF0D		OBJECT-TYPE
			SYNTAX	INTEGER
			ACCESS	read-only
			STATUS	current
	DESCRIPTION ""
			::= { mbusF2 32 }

mbusF2Value0D		OBJECT-TYPE
			SYNTAX	INTEGER
			ACCESS	read-only
			STATUS	current
	DESCRIPTION ""
			::= { mbusF2 33 }

mbusF2VIF0E		OBJECT-TYPE
			SYNTAX	INTEGER
			ACCESS	read-only
			STATUS	current
	DESCRIPTION ""
			::= { mbusF2 34 }

mbusF2Value0E		OBJECT-TYPE
			SYNTAX	INTEGER
			ACCESS	read-only
			STATUS	current
	DESCRIPTION ""
			::= { mbusF2 35 }

mbusF2VIF0F		OBJECT-TYPE
			SYNTAX	INTEGER
			ACCESS	read-only
			STATUS	current
	DESCRIPTION ""
			::= { mbusF2 36 }

mbusF2Value0F		OBJECT-TYPE
			SYNTAX	INTEGER
			ACCESS	read-only
			STATUS	current
	DESCRIPTION ""
			::= { mbusF2 37 }

mbusF2VIF10		OBJECT-TYPE
			SYNTAX	INTEGER
			ACCESS	read-only
			STATUS	current
	DESCRIPTION ""
			::= { mbusF2 38 }

mbusF2Value10		OBJECT-TYPE
			SYNTAX	INTEGER
			ACCESS	read-only
			STATUS	current
	DESCRIPTION ""
			::= { mbusF2 39 }

mbusF2VIF11		OBJECT-TYPE
			SYNTAX	INTEGER
			ACCESS	read-only
			STATUS	current
	DESCRIPTION ""
			::= { mbusF2 40 }

mbusF2Value11		OBJECT-TYPE
			SYNTAX	INTEGER
			ACCESS	read-only
			STATUS	current
	DESCRIPTION ""
			::= { mbusF2 41 }

mbusF2VIF12		OBJECT-TYPE
			SYNTAX	INTEGER
			ACCESS	read-only
			STATUS	current
	DESCRIPTION ""
			::= { mbusF2 42 }

mbusF2Value12		OBJECT-TYPE
			SYNTAX	INTEGER
			ACCESS	read-only
			STATUS	current
	DESCRIPTION ""
			::= { mbusF2 43 }

mbusF2VIF13		OBJECT-TYPE
			SYNTAX	INTEGER
			ACCESS	read-only
			STATUS	current
	DESCRIPTION ""
			::= { mbusF2 44 }

mbusF2Value13		OBJECT-TYPE
			SYNTAX	INTEGER
			ACCESS	read-only
			STATUS	current
	DESCRIPTION ""
			::= { mbusF2 45 }

mbusF2VIF14		OBJECT-TYPE
			SYNTAX	INTEGER
			ACCESS	read-only
			STATUS	current
	DESCRIPTION ""
			::= { mbusF2 46 }

mbusF2Value14		OBJECT-TYPE
			SYNTAX	INTEGER
			ACCESS	read-only
			STATUS	current
	DESCRIPTION ""
			::= { mbusF2 47 }

mbusF2VIF15		OBJECT-TYPE
			SYNTAX	INTEGER
			ACCESS	read-only
			STATUS	current
	DESCRIPTION ""
			::= { mbusF2 48 }

mbusF2Value15		OBJECT-TYPE
			SYNTAX	INTEGER
			ACCESS	read-only
			STATUS	current
	DESCRIPTION ""
			::= { mbusF2 49 }

mbusF2VIF16		OBJECT-TYPE
			SYNTAX	INTEGER
			ACCESS	read-only
			STATUS	current
	DESCRIPTION ""
			::= { mbusF2 50 }

mbusF2Value16		OBJECT-TYPE
			SYNTAX	INTEGER
			ACCESS	read-only
			STATUS	current
	DESCRIPTION ""
			::= { mbusF2 51 }

mbusF2VIF17		OBJECT-TYPE
			SYNTAX	INTEGER
			ACCESS	read-only
			STATUS	current
	DESCRIPTION ""
			::= { mbusF2 52 }

mbusF2Value17		OBJECT-TYPE
			SYNTAX	INTEGER
			ACCESS	read-only
			STATUS	current
	DESCRIPTION ""
			::= { mbusF2 53 }

mbusF2VIF18		OBJECT-TYPE
			SYNTAX	INTEGER
			ACCESS	read-only
			STATUS	current
	DESCRIPTION ""
			::= { mbusF2 54 }

mbusF2Value18		OBJECT-TYPE
			SYNTAX	INTEGER
			ACCESS	read-only
			STATUS	current
	DESCRIPTION ""
			::= { mbusF2 55 }

mbusF2VIF19		OBJECT-TYPE
			SYNTAX	INTEGER
			ACCESS	read-only
			STATUS	current
	DESCRIPTION ""
			::= { mbusF2 56 }

mbusF2Value19		OBJECT-TYPE
			SYNTAX	INTEGER
			ACCESS	read-only
			STATUS	current
	DESCRIPTION ""
			::= { mbusF2 57 }

mbusF2VIF1A		OBJECT-TYPE
			SYNTAX	INTEGER
			ACCESS	read-only
			STATUS	current
	DESCRIPTION ""
			::= { mbusF2 58 }

mbusF2Value1A		OBJECT-TYPE
			SYNTAX	INTEGER
			ACCESS	read-only
			STATUS	current
	DESCRIPTION ""
			::= { mbusF2 59 }

mbusF2VIF1B		OBJECT-TYPE
			SYNTAX	INTEGER
			ACCESS	read-only
			STATUS	current
	DESCRIPTION ""
			::= { mbusF2 60 }

mbusF2Value1B		OBJECT-TYPE
			SYNTAX	INTEGER
			ACCESS	read-only
			STATUS	current
	DESCRIPTION ""
			::= { mbusF2 61 }

mbusF2VIF1C		OBJECT-TYPE
			SYNTAX	INTEGER
			ACCESS	read-only
			STATUS	current
	DESCRIPTION ""
			::= { mbusF2 62 }

mbusF2Value1C		OBJECT-TYPE
			SYNTAX	INTEGER
			ACCESS	read-only
			STATUS	current
	DESCRIPTION ""
			::= { mbusF2 63 }

mbusF2VIF1D		OBJECT-TYPE
			SYNTAX	INTEGER
			ACCESS	read-only
			STATUS	current
	DESCRIPTION ""
			::= { mbusF2 64 }

mbusF2Value1D		OBJECT-TYPE
			SYNTAX	INTEGER
			ACCESS	read-only
			STATUS	current
	DESCRIPTION ""
			::= { mbusF2 65 }

mbusF2VIF1E		OBJECT-TYPE
			SYNTAX	INTEGER
			ACCESS	read-only
			STATUS	current
	DESCRIPTION ""
			::= { mbusF2 66 }

mbusF2Value1E		OBJECT-TYPE
			SYNTAX	INTEGER
			ACCESS	read-only
			STATUS	current
	DESCRIPTION ""
			::= { mbusF2 67 }

mbusF2VIF1F		OBJECT-TYPE
			SYNTAX	INTEGER
			ACCESS	read-only
			STATUS	current
	DESCRIPTION ""
			::= { mbusF2 68 }

mbusF2Value1F		OBJECT-TYPE
			SYNTAX	INTEGER
			ACCESS	read-only
			STATUS	current
	DESCRIPTION ""
			::= { mbusF2 69 }

mbusF2VIF20		OBJECT-TYPE
			SYNTAX	INTEGER
			ACCESS	read-only
			STATUS	current
	DESCRIPTION ""
			::= { mbusF2 70 }

mbusF2Value20		OBJECT-TYPE
			SYNTAX	INTEGER
			ACCESS	read-only
			STATUS	current
	DESCRIPTION ""
			::= { mbusF2 71 }

mbusF2VIF21		OBJECT-TYPE
			SYNTAX	INTEGER
			ACCESS	read-only
			STATUS	current
	DESCRIPTION ""
			::= { mbusF2 72 }

mbusF2Value21		OBJECT-TYPE
			SYNTAX	INTEGER
			ACCESS	read-only
			STATUS	current
	DESCRIPTION ""
			::= { mbusF2 73 }

mbusF2VIF22		OBJECT-TYPE
			SYNTAX	INTEGER
			ACCESS	read-only
			STATUS	current
	DESCRIPTION ""
			::= { mbusF2 74 }

mbusF2Value22		OBJECT-TYPE
			SYNTAX	INTEGER
			ACCESS	read-only
			STATUS	current
	DESCRIPTION ""
			::= { mbusF2 75 }

mbusF2VIF23		OBJECT-TYPE
			SYNTAX	INTEGER
			ACCESS	read-only
			STATUS	current
	DESCRIPTION ""
			::= { mbusF2 76 }

mbusF2Value23		OBJECT-TYPE
			SYNTAX	INTEGER
			ACCESS	read-only
			STATUS	current
	DESCRIPTION ""
			::= { mbusF2 77 }

mbusF2VIF24		OBJECT-TYPE
			SYNTAX	INTEGER
			ACCESS	read-only
			STATUS	current
	DESCRIPTION ""
			::= { mbusF2 78 }

mbusF2Value24		OBJECT-TYPE
			SYNTAX	INTEGER
			ACCESS	read-only
			STATUS	current
	DESCRIPTION ""
			::= { mbusF2 79 }

mbusF2VIF25		OBJECT-TYPE
			SYNTAX	INTEGER
			ACCESS	read-only
			STATUS	current
	DESCRIPTION ""
			::= { mbusF2 80 }

mbusF2Value25		OBJECT-TYPE
			SYNTAX	INTEGER
			ACCESS	read-only
			STATUS	current
	DESCRIPTION ""
			::= { mbusF2 81 }

mbusF2VIF26		OBJECT-TYPE
			SYNTAX	INTEGER
			ACCESS	read-only
			STATUS	current
	DESCRIPTION ""
			::= { mbusF2 82 }

mbusF2Value26		OBJECT-TYPE
			SYNTAX	INTEGER
			ACCESS	read-only
			STATUS	current
	DESCRIPTION ""
			::= { mbusF2 83 }

mbusF2VIF27		OBJECT-TYPE
			SYNTAX	INTEGER
			ACCESS	read-only
			STATUS	current
	DESCRIPTION ""
			::= { mbusF2 84 }

mbusF2Value27		OBJECT-TYPE
			SYNTAX	INTEGER
			ACCESS	read-only
			STATUS	current
	DESCRIPTION ""
			::= { mbusF2 85 }

mbusF2VIF28		OBJECT-TYPE
			SYNTAX	INTEGER
			ACCESS	read-only
			STATUS	current
	DESCRIPTION ""
			::= { mbusF2 86 }

mbusF2Value28		OBJECT-TYPE
			SYNTAX	INTEGER
			ACCESS	read-only
			STATUS	current
	DESCRIPTION ""
			::= { mbusF2 87 }

mbusF2VIF29		OBJECT-TYPE
			SYNTAX	INTEGER
			ACCESS	read-only
			STATUS	current
	DESCRIPTION ""
			::= { mbusF2 88 }

mbusF2Value29		OBJECT-TYPE
			SYNTAX	INTEGER
			ACCESS	read-only
			STATUS	current
	DESCRIPTION ""
			::= { mbusF2 89 }

mbusF2VIF2A		OBJECT-TYPE
			SYNTAX	INTEGER
			ACCESS	read-only
			STATUS	current
	DESCRIPTION ""
			::= { mbusF2 90 }

mbusF2Value2A		OBJECT-TYPE
			SYNTAX	INTEGER
			ACCESS	read-only
			STATUS	current
	DESCRIPTION ""
			::= { mbusF2 91 }

mbusF2VIF2B		OBJECT-TYPE
			SYNTAX	INTEGER
			ACCESS	read-only
			STATUS	current
	DESCRIPTION ""
			::= { mbusF2 92 }

mbusF2Value2B		OBJECT-TYPE
			SYNTAX	INTEGER
			ACCESS	read-only
			STATUS	current
	DESCRIPTION ""
			::= { mbusF2 93 }

mbusF2VIF2C		OBJECT-TYPE
			SYNTAX	INTEGER
			ACCESS	read-only
			STATUS	current
	DESCRIPTION ""
			::= { mbusF2 94 }

mbusF2Value2C		OBJECT-TYPE
			SYNTAX	INTEGER
			ACCESS	read-only
			STATUS	current
	DESCRIPTION ""
			::= { mbusF2 95 }

mbusF2VIF2D		OBJECT-TYPE
			SYNTAX	INTEGER
			ACCESS	read-only
			STATUS	current
	DESCRIPTION ""
			::= { mbusF2 96 }

mbusF2Value2D		OBJECT-TYPE
			SYNTAX	INTEGER
			ACCESS	read-only
			STATUS	current
	DESCRIPTION ""
			::= { mbusF2 97 }

mbusF2VIF2E		OBJECT-TYPE
			SYNTAX	INTEGER
			ACCESS	read-only
			STATUS	current
	DESCRIPTION ""
			::= { mbusF2 98 }

mbusF2Value2E		OBJECT-TYPE
			SYNTAX	INTEGER
			ACCESS	read-only
			STATUS	current
	DESCRIPTION ""
			::= { mbusF2 99 }

mbusF2VIF2F		OBJECT-TYPE
			SYNTAX	INTEGER
			ACCESS	read-only
			STATUS	current
	DESCRIPTION ""
			::= { mbusF2 100 }

mbusF2Value2F		OBJECT-TYPE
			SYNTAX	INTEGER
			ACCESS	read-only
			STATUS	current
	DESCRIPTION ""
			::= { mbusF2 101 }

mbusF3			OBJECT IDENTIFIER ::= { mbus 243 }

mbusF3IdNumber		OBJECT-TYPE
			SYNTAX	Gauge
			ACCESS	read-only
			STATUS	current
	DESCRIPTION ""
			::= { mbusF3 1 }

mbusF3Manufacturer	OBJECT-TYPE
			SYNTAX	Gauge
			ACCESS	read-only
			STATUS	current
	DESCRIPTION ""
			::= { mbusF3 2 }

mbusF3Version		OBJECT-TYPE
			SYNTAX	Gauge
			ACCESS	read-only
			STATUS	current
	DESCRIPTION ""
			::= { mbusF3 3 }

mbusF3Medium		OBJECT-TYPE
			SYNTAX	Gauge
			ACCESS	read-only
			STATUS	current
	DESCRIPTION ""
			::= { mbusF3 4 }

mbusF3Status		OBJECT-TYPE
			SYNTAX	Gauge
			ACCESS	read-only
			STATUS	current
	DESCRIPTION ""
			::= { mbusF3 5 }

mbusF3VIF00		OBJECT-TYPE
			SYNTAX	INTEGER
			ACCESS	read-only
			STATUS	current
	DESCRIPTION ""
			::= { mbusF3 6 }

mbusF3Value00		OBJECT-TYPE
			SYNTAX	INTEGER
			ACCESS	read-only
			STATUS	current
	DESCRIPTION ""
			::= { mbusF3 7 }

mbusF3VIF01		OBJECT-TYPE
			SYNTAX	INTEGER
			ACCESS	read-only
			STATUS	current
	DESCRIPTION ""
			::= { mbusF3 8 }

mbusF3Value01		OBJECT-TYPE
			SYNTAX	INTEGER
			ACCESS	read-only
			STATUS	current
	DESCRIPTION ""
			::= { mbusF3 9 }

mbusF3VIF02		OBJECT-TYPE
			SYNTAX	INTEGER
			ACCESS	read-only
			STATUS	current
	DESCRIPTION ""
			::= { mbusF3 10 }

mbusF3Value02		OBJECT-TYPE
			SYNTAX	INTEGER
			ACCESS	read-only
			STATUS	current
	DESCRIPTION ""
			::= { mbusF3 11 }

mbusF3VIF03		OBJECT-TYPE
			SYNTAX	INTEGER
			ACCESS	read-only
			STATUS	current
	DESCRIPTION ""
			::= { mbusF3 12 }

mbusF3Value03		OBJECT-TYPE
			SYNTAX	INTEGER
			ACCESS	read-only
			STATUS	current
	DESCRIPTION ""
			::= { mbusF3 13 }

mbusF3VIF04		OBJECT-TYPE
			SYNTAX	INTEGER
			ACCESS	read-only
			STATUS	current
	DESCRIPTION ""
			::= { mbusF3 14 }

mbusF3Value04		OBJECT-TYPE
			SYNTAX	INTEGER
			ACCESS	read-only
			STATUS	current
	DESCRIPTION ""
			::= { mbusF3 15 }

mbusF3VIF05		OBJECT-TYPE
			SYNTAX	INTEGER
			ACCESS	read-only
			STATUS	current
	DESCRIPTION ""
			::= { mbusF3 16 }

mbusF3Value05		OBJECT-TYPE
			SYNTAX	INTEGER
			ACCESS	read-only
			STATUS	current
	DESCRIPTION ""
			::= { mbusF3 17 }

mbusF3VIF06		OBJECT-TYPE
			SYNTAX	INTEGER
			ACCESS	read-only
			STATUS	current
	DESCRIPTION ""
			::= { mbusF3 18 }

mbusF3Value06		OBJECT-TYPE
			SYNTAX	INTEGER
			ACCESS	read-only
			STATUS	current
	DESCRIPTION ""
			::= { mbusF3 19 }

mbusF3VIF07		OBJECT-TYPE
			SYNTAX	INTEGER
			ACCESS	read-only
			STATUS	current
	DESCRIPTION ""
			::= { mbusF3 20 }

mbusF3Value07		OBJECT-TYPE
			SYNTAX	INTEGER
			ACCESS	read-only
			STATUS	current
	DESCRIPTION ""
			::= { mbusF3 21 }

mbusF3VIF08		OBJECT-TYPE
			SYNTAX	INTEGER
			ACCESS	read-only
			STATUS	current
	DESCRIPTION ""
			::= { mbusF3 22 }

mbusF3Value08		OBJECT-TYPE
			SYNTAX	INTEGER
			ACCESS	read-only
			STATUS	current
	DESCRIPTION ""
			::= { mbusF3 23 }

mbusF3VIF09		OBJECT-TYPE
			SYNTAX	INTEGER
			ACCESS	read-only
			STATUS	current
	DESCRIPTION ""
			::= { mbusF3 24 }

mbusF3Value09		OBJECT-TYPE
			SYNTAX	INTEGER
			ACCESS	read-only
			STATUS	current
	DESCRIPTION ""
			::= { mbusF3 25 }

mbusF3VIF0A		OBJECT-TYPE
			SYNTAX	INTEGER
			ACCESS	read-only
			STATUS	current
	DESCRIPTION ""
			::= { mbusF3 26 }

mbusF3Value0A		OBJECT-TYPE
			SYNTAX	INTEGER
			ACCESS	read-only
			STATUS	current
	DESCRIPTION ""
			::= { mbusF3 27 }

mbusF3VIF0B		OBJECT-TYPE
			SYNTAX	INTEGER
			ACCESS	read-only
			STATUS	current
	DESCRIPTION ""
			::= { mbusF3 28 }

mbusF3Value0B		OBJECT-TYPE
			SYNTAX	INTEGER
			ACCESS	read-only
			STATUS	current
	DESCRIPTION ""
			::= { mbusF3 29 }

mbusF3VIF0C		OBJECT-TYPE
			SYNTAX	INTEGER
			ACCESS	read-only
			STATUS	current
	DESCRIPTION ""
			::= { mbusF3 30 }

mbusF3Value0C		OBJECT-TYPE
			SYNTAX	INTEGER
			ACCESS	read-only
			STATUS	current
	DESCRIPTION ""
			::= { mbusF3 31 }

mbusF3VIF0D		OBJECT-TYPE
			SYNTAX	INTEGER
			ACCESS	read-only
			STATUS	current
	DESCRIPTION ""
			::= { mbusF3 32 }

mbusF3Value0D		OBJECT-TYPE
			SYNTAX	INTEGER
			ACCESS	read-only
			STATUS	current
	DESCRIPTION ""
			::= { mbusF3 33 }

mbusF3VIF0E		OBJECT-TYPE
			SYNTAX	INTEGER
			ACCESS	read-only
			STATUS	current
	DESCRIPTION ""
			::= { mbusF3 34 }

mbusF3Value0E		OBJECT-TYPE
			SYNTAX	INTEGER
			ACCESS	read-only
			STATUS	current
	DESCRIPTION ""
			::= { mbusF3 35 }

mbusF3VIF0F		OBJECT-TYPE
			SYNTAX	INTEGER
			ACCESS	read-only
			STATUS	current
	DESCRIPTION ""
			::= { mbusF3 36 }

mbusF3Value0F		OBJECT-TYPE
			SYNTAX	INTEGER
			ACCESS	read-only
			STATUS	current
	DESCRIPTION ""
			::= { mbusF3 37 }

mbusF3VIF10		OBJECT-TYPE
			SYNTAX	INTEGER
			ACCESS	read-only
			STATUS	current
	DESCRIPTION ""
			::= { mbusF3 38 }

mbusF3Value10		OBJECT-TYPE
			SYNTAX	INTEGER
			ACCESS	read-only
			STATUS	current
	DESCRIPTION ""
			::= { mbusF3 39 }

mbusF3VIF11		OBJECT-TYPE
			SYNTAX	INTEGER
			ACCESS	read-only
			STATUS	current
	DESCRIPTION ""
			::= { mbusF3 40 }

mbusF3Value11		OBJECT-TYPE
			SYNTAX	INTEGER
			ACCESS	read-only
			STATUS	current
	DESCRIPTION ""
			::= { mbusF3 41 }

mbusF3VIF12		OBJECT-TYPE
			SYNTAX	INTEGER
			ACCESS	read-only
			STATUS	current
	DESCRIPTION ""
			::= { mbusF3 42 }

mbusF3Value12		OBJECT-TYPE
			SYNTAX	INTEGER
			ACCESS	read-only
			STATUS	current
	DESCRIPTION ""
			::= { mbusF3 43 }

mbusF3VIF13		OBJECT-TYPE
			SYNTAX	INTEGER
			ACCESS	read-only
			STATUS	current
	DESCRIPTION ""
			::= { mbusF3 44 }

mbusF3Value13		OBJECT-TYPE
			SYNTAX	INTEGER
			ACCESS	read-only
			STATUS	current
	DESCRIPTION ""
			::= { mbusF3 45 }

mbusF3VIF14		OBJECT-TYPE
			SYNTAX	INTEGER
			ACCESS	read-only
			STATUS	current
	DESCRIPTION ""
			::= { mbusF3 46 }

mbusF3Value14		OBJECT-TYPE
			SYNTAX	INTEGER
			ACCESS	read-only
			STATUS	current
	DESCRIPTION ""
			::= { mbusF3 47 }

mbusF3VIF15		OBJECT-TYPE
			SYNTAX	INTEGER
			ACCESS	read-only
			STATUS	current
	DESCRIPTION ""
			::= { mbusF3 48 }

mbusF3Value15		OBJECT-TYPE
			SYNTAX	INTEGER
			ACCESS	read-only
			STATUS	current
	DESCRIPTION ""
			::= { mbusF3 49 }

mbusF3VIF16		OBJECT-TYPE
			SYNTAX	INTEGER
			ACCESS	read-only
			STATUS	current
	DESCRIPTION ""
			::= { mbusF3 50 }

mbusF3Value16		OBJECT-TYPE
			SYNTAX	INTEGER
			ACCESS	read-only
			STATUS	current
	DESCRIPTION ""
			::= { mbusF3 51 }

mbusF3VIF17		OBJECT-TYPE
			SYNTAX	INTEGER
			ACCESS	read-only
			STATUS	current
	DESCRIPTION ""
			::= { mbusF3 52 }

mbusF3Value17		OBJECT-TYPE
			SYNTAX	INTEGER
			ACCESS	read-only
			STATUS	current
	DESCRIPTION ""
			::= { mbusF3 53 }

mbusF3VIF18		OBJECT-TYPE
			SYNTAX	INTEGER
			ACCESS	read-only
			STATUS	current
	DESCRIPTION ""
			::= { mbusF3 54 }

mbusF3Value18		OBJECT-TYPE
			SYNTAX	INTEGER
			ACCESS	read-only
			STATUS	current
	DESCRIPTION ""
			::= { mbusF3 55 }

mbusF3VIF19		OBJECT-TYPE
			SYNTAX	INTEGER
			ACCESS	read-only
			STATUS	current
	DESCRIPTION ""
			::= { mbusF3 56 }

mbusF3Value19		OBJECT-TYPE
			SYNTAX	INTEGER
			ACCESS	read-only
			STATUS	current
	DESCRIPTION ""
			::= { mbusF3 57 }

mbusF3VIF1A		OBJECT-TYPE
			SYNTAX	INTEGER
			ACCESS	read-only
			STATUS	current
	DESCRIPTION ""
			::= { mbusF3 58 }

mbusF3Value1A		OBJECT-TYPE
			SYNTAX	INTEGER
			ACCESS	read-only
			STATUS	current
	DESCRIPTION ""
			::= { mbusF3 59 }

mbusF3VIF1B		OBJECT-TYPE
			SYNTAX	INTEGER
			ACCESS	read-only
			STATUS	current
	DESCRIPTION ""
			::= { mbusF3 60 }

mbusF3Value1B		OBJECT-TYPE
			SYNTAX	INTEGER
			ACCESS	read-only
			STATUS	current
	DESCRIPTION ""
			::= { mbusF3 61 }

mbusF3VIF1C		OBJECT-TYPE
			SYNTAX	INTEGER
			ACCESS	read-only
			STATUS	current
	DESCRIPTION ""
			::= { mbusF3 62 }

mbusF3Value1C		OBJECT-TYPE
			SYNTAX	INTEGER
			ACCESS	read-only
			STATUS	current
	DESCRIPTION ""
			::= { mbusF3 63 }

mbusF3VIF1D		OBJECT-TYPE
			SYNTAX	INTEGER
			ACCESS	read-only
			STATUS	current
	DESCRIPTION ""
			::= { mbusF3 64 }

mbusF3Value1D		OBJECT-TYPE
			SYNTAX	INTEGER
			ACCESS	read-only
			STATUS	current
	DESCRIPTION ""
			::= { mbusF3 65 }

mbusF3VIF1E		OBJECT-TYPE
			SYNTAX	INTEGER
			ACCESS	read-only
			STATUS	current
	DESCRIPTION ""
			::= { mbusF3 66 }

mbusF3Value1E		OBJECT-TYPE
			SYNTAX	INTEGER
			ACCESS	read-only
			STATUS	current
	DESCRIPTION ""
			::= { mbusF3 67 }

mbusF3VIF1F		OBJECT-TYPE
			SYNTAX	INTEGER
			ACCESS	read-only
			STATUS	current
	DESCRIPTION ""
			::= { mbusF3 68 }

mbusF3Value1F		OBJECT-TYPE
			SYNTAX	INTEGER
			ACCESS	read-only
			STATUS	current
	DESCRIPTION ""
			::= { mbusF3 69 }

mbusF3VIF20		OBJECT-TYPE
			SYNTAX	INTEGER
			ACCESS	read-only
			STATUS	current
	DESCRIPTION ""
			::= { mbusF3 70 }

mbusF3Value20		OBJECT-TYPE
			SYNTAX	INTEGER
			ACCESS	read-only
			STATUS	current
	DESCRIPTION ""
			::= { mbusF3 71 }

mbusF3VIF21		OBJECT-TYPE
			SYNTAX	INTEGER
			ACCESS	read-only
			STATUS	current
	DESCRIPTION ""
			::= { mbusF3 72 }

mbusF3Value21		OBJECT-TYPE
			SYNTAX	INTEGER
			ACCESS	read-only
			STATUS	current
	DESCRIPTION ""
			::= { mbusF3 73 }

mbusF3VIF22		OBJECT-TYPE
			SYNTAX	INTEGER
			ACCESS	read-only
			STATUS	current
	DESCRIPTION ""
			::= { mbusF3 74 }

mbusF3Value22		OBJECT-TYPE
			SYNTAX	INTEGER
			ACCESS	read-only
			STATUS	current
	DESCRIPTION ""
			::= { mbusF3 75 }

mbusF3VIF23		OBJECT-TYPE
			SYNTAX	INTEGER
			ACCESS	read-only
			STATUS	current
	DESCRIPTION ""
			::= { mbusF3 76 }

mbusF3Value23		OBJECT-TYPE
			SYNTAX	INTEGER
			ACCESS	read-only
			STATUS	current
	DESCRIPTION ""
			::= { mbusF3 77 }

mbusF3VIF24		OBJECT-TYPE
			SYNTAX	INTEGER
			ACCESS	read-only
			STATUS	current
	DESCRIPTION ""
			::= { mbusF3 78 }

mbusF3Value24		OBJECT-TYPE
			SYNTAX	INTEGER
			ACCESS	read-only
			STATUS	current
	DESCRIPTION ""
			::= { mbusF3 79 }

mbusF3VIF25		OBJECT-TYPE
			SYNTAX	INTEGER
			ACCESS	read-only
			STATUS	current
	DESCRIPTION ""
			::= { mbusF3 80 }

mbusF3Value25		OBJECT-TYPE
			SYNTAX	INTEGER
			ACCESS	read-only
			STATUS	current
	DESCRIPTION ""
			::= { mbusF3 81 }

mbusF3VIF26		OBJECT-TYPE
			SYNTAX	INTEGER
			ACCESS	read-only
			STATUS	current
	DESCRIPTION ""
			::= { mbusF3 82 }

mbusF3Value26		OBJECT-TYPE
			SYNTAX	INTEGER
			ACCESS	read-only
			STATUS	current
	DESCRIPTION ""
			::= { mbusF3 83 }

mbusF3VIF27		OBJECT-TYPE
			SYNTAX	INTEGER
			ACCESS	read-only
			STATUS	current
	DESCRIPTION ""
			::= { mbusF3 84 }

mbusF3Value27		OBJECT-TYPE
			SYNTAX	INTEGER
			ACCESS	read-only
			STATUS	current
	DESCRIPTION ""
			::= { mbusF3 85 }

mbusF3VIF28		OBJECT-TYPE
			SYNTAX	INTEGER
			ACCESS	read-only
			STATUS	current
	DESCRIPTION ""
			::= { mbusF3 86 }

mbusF3Value28		OBJECT-TYPE
			SYNTAX	INTEGER
			ACCESS	read-only
			STATUS	current
	DESCRIPTION ""
			::= { mbusF3 87 }

mbusF3VIF29		OBJECT-TYPE
			SYNTAX	INTEGER
			ACCESS	read-only
			STATUS	current
	DESCRIPTION ""
			::= { mbusF3 88 }

mbusF3Value29		OBJECT-TYPE
			SYNTAX	INTEGER
			ACCESS	read-only
			STATUS	current
	DESCRIPTION ""
			::= { mbusF3 89 }

mbusF3VIF2A		OBJECT-TYPE
			SYNTAX	INTEGER
			ACCESS	read-only
			STATUS	current
	DESCRIPTION ""
			::= { mbusF3 90 }

mbusF3Value2A		OBJECT-TYPE
			SYNTAX	INTEGER
			ACCESS	read-only
			STATUS	current
	DESCRIPTION ""
			::= { mbusF3 91 }

mbusF3VIF2B		OBJECT-TYPE
			SYNTAX	INTEGER
			ACCESS	read-only
			STATUS	current
	DESCRIPTION ""
			::= { mbusF3 92 }

mbusF3Value2B		OBJECT-TYPE
			SYNTAX	INTEGER
			ACCESS	read-only
			STATUS	current
	DESCRIPTION ""
			::= { mbusF3 93 }

mbusF3VIF2C		OBJECT-TYPE
			SYNTAX	INTEGER
			ACCESS	read-only
			STATUS	current
	DESCRIPTION ""
			::= { mbusF3 94 }

mbusF3Value2C		OBJECT-TYPE
			SYNTAX	INTEGER
			ACCESS	read-only
			STATUS	current
	DESCRIPTION ""
			::= { mbusF3 95 }

mbusF3VIF2D		OBJECT-TYPE
			SYNTAX	INTEGER
			ACCESS	read-only
			STATUS	current
	DESCRIPTION ""
			::= { mbusF3 96 }

mbusF3Value2D		OBJECT-TYPE
			SYNTAX	INTEGER
			ACCESS	read-only
			STATUS	current
	DESCRIPTION ""
			::= { mbusF3 97 }

mbusF3VIF2E		OBJECT-TYPE
			SYNTAX	INTEGER
			ACCESS	read-only
			STATUS	current
	DESCRIPTION ""
			::= { mbusF3 98 }

mbusF3Value2E		OBJECT-TYPE
			SYNTAX	INTEGER
			ACCESS	read-only
			STATUS	current
	DESCRIPTION ""
			::= { mbusF3 99 }

mbusF3VIF2F		OBJECT-TYPE
			SYNTAX	INTEGER
			ACCESS	read-only
			STATUS	current
	DESCRIPTION ""
			::= { mbusF3 100 }

mbusF3Value2F		OBJECT-TYPE
			SYNTAX	INTEGER
			ACCESS	read-only
			STATUS	current
	DESCRIPTION ""
			::= { mbusF3 101 }

mbusF4			OBJECT IDENTIFIER ::= { mbus 244 }

mbusF4IdNumber		OBJECT-TYPE
			SYNTAX	Gauge
			ACCESS	read-only
			STATUS	current
	DESCRIPTION ""
			::= { mbusF4 1 }

mbusF4Manufacturer	OBJECT-TYPE
			SYNTAX	Gauge
			ACCESS	read-only
			STATUS	current
	DESCRIPTION ""
			::= { mbusF4 2 }

mbusF4Version		OBJECT-TYPE
			SYNTAX	Gauge
			ACCESS	read-only
			STATUS	current
	DESCRIPTION ""
			::= { mbusF4 3 }

mbusF4Medium		OBJECT-TYPE
			SYNTAX	Gauge
			ACCESS	read-only
			STATUS	current
	DESCRIPTION ""
			::= { mbusF4 4 }

mbusF4Status		OBJECT-TYPE
			SYNTAX	Gauge
			ACCESS	read-only
			STATUS	current
	DESCRIPTION ""
			::= { mbusF4 5 }

mbusF4VIF00		OBJECT-TYPE
			SYNTAX	INTEGER
			ACCESS	read-only
			STATUS	current
	DESCRIPTION ""
			::= { mbusF4 6 }

mbusF4Value00		OBJECT-TYPE
			SYNTAX	INTEGER
			ACCESS	read-only
			STATUS	current
	DESCRIPTION ""
			::= { mbusF4 7 }

mbusF4VIF01		OBJECT-TYPE
			SYNTAX	INTEGER
			ACCESS	read-only
			STATUS	current
	DESCRIPTION ""
			::= { mbusF4 8 }

mbusF4Value01		OBJECT-TYPE
			SYNTAX	INTEGER
			ACCESS	read-only
			STATUS	current
	DESCRIPTION ""
			::= { mbusF4 9 }

mbusF4VIF02		OBJECT-TYPE
			SYNTAX	INTEGER
			ACCESS	read-only
			STATUS	current
	DESCRIPTION ""
			::= { mbusF4 10 }

mbusF4Value02		OBJECT-TYPE
			SYNTAX	INTEGER
			ACCESS	read-only
			STATUS	current
	DESCRIPTION ""
			::= { mbusF4 11 }

mbusF4VIF03		OBJECT-TYPE
			SYNTAX	INTEGER
			ACCESS	read-only
			STATUS	current
	DESCRIPTION ""
			::= { mbusF4 12 }

mbusF4Value03		OBJECT-TYPE
			SYNTAX	INTEGER
			ACCESS	read-only
			STATUS	current
	DESCRIPTION ""
			::= { mbusF4 13 }

mbusF4VIF04		OBJECT-TYPE
			SYNTAX	INTEGER
			ACCESS	read-only
			STATUS	current
	DESCRIPTION ""
			::= { mbusF4 14 }

mbusF4Value04		OBJECT-TYPE
			SYNTAX	INTEGER
			ACCESS	read-only
			STATUS	current
	DESCRIPTION ""
			::= { mbusF4 15 }

mbusF4VIF05		OBJECT-TYPE
			SYNTAX	INTEGER
			ACCESS	read-only
			STATUS	current
	DESCRIPTION ""
			::= { mbusF4 16 }

mbusF4Value05		OBJECT-TYPE
			SYNTAX	INTEGER
			ACCESS	read-only
			STATUS	current
	DESCRIPTION ""
			::= { mbusF4 17 }

mbusF4VIF06		OBJECT-TYPE
			SYNTAX	INTEGER
			ACCESS	read-only
			STATUS	current
	DESCRIPTION ""
			::= { mbusF4 18 }

mbusF4Value06		OBJECT-TYPE
			SYNTAX	INTEGER
			ACCESS	read-only
			STATUS	current
	DESCRIPTION ""
			::= { mbusF4 19 }

mbusF4VIF07		OBJECT-TYPE
			SYNTAX	INTEGER
			ACCESS	read-only
			STATUS	current
	DESCRIPTION ""
			::= { mbusF4 20 }

mbusF4Value07		OBJECT-TYPE
			SYNTAX	INTEGER
			ACCESS	read-only
			STATUS	current
	DESCRIPTION ""
			::= { mbusF4 21 }

mbusF4VIF08		OBJECT-TYPE
			SYNTAX	INTEGER
			ACCESS	read-only
			STATUS	current
	DESCRIPTION ""
			::= { mbusF4 22 }

mbusF4Value08		OBJECT-TYPE
			SYNTAX	INTEGER
			ACCESS	read-only
			STATUS	current
	DESCRIPTION ""
			::= { mbusF4 23 }

mbusF4VIF09		OBJECT-TYPE
			SYNTAX	INTEGER
			ACCESS	read-only
			STATUS	current
	DESCRIPTION ""
			::= { mbusF4 24 }

mbusF4Value09		OBJECT-TYPE
			SYNTAX	INTEGER
			ACCESS	read-only
			STATUS	current
	DESCRIPTION ""
			::= { mbusF4 25 }

mbusF4VIF0A		OBJECT-TYPE
			SYNTAX	INTEGER
			ACCESS	read-only
			STATUS	current
	DESCRIPTION ""
			::= { mbusF4 26 }

mbusF4Value0A		OBJECT-TYPE
			SYNTAX	INTEGER
			ACCESS	read-only
			STATUS	current
	DESCRIPTION ""
			::= { mbusF4 27 }

mbusF4VIF0B		OBJECT-TYPE
			SYNTAX	INTEGER
			ACCESS	read-only
			STATUS	current
	DESCRIPTION ""
			::= { mbusF4 28 }

mbusF4Value0B		OBJECT-TYPE
			SYNTAX	INTEGER
			ACCESS	read-only
			STATUS	current
	DESCRIPTION ""
			::= { mbusF4 29 }

mbusF4VIF0C		OBJECT-TYPE
			SYNTAX	INTEGER
			ACCESS	read-only
			STATUS	current
	DESCRIPTION ""
			::= { mbusF4 30 }

mbusF4Value0C		OBJECT-TYPE
			SYNTAX	INTEGER
			ACCESS	read-only
			STATUS	current
	DESCRIPTION ""
			::= { mbusF4 31 }

mbusF4VIF0D		OBJECT-TYPE
			SYNTAX	INTEGER
			ACCESS	read-only
			STATUS	current
	DESCRIPTION ""
			::= { mbusF4 32 }

mbusF4Value0D		OBJECT-TYPE
			SYNTAX	INTEGER
			ACCESS	read-only
			STATUS	current
	DESCRIPTION ""
			::= { mbusF4 33 }

mbusF4VIF0E		OBJECT-TYPE
			SYNTAX	INTEGER
			ACCESS	read-only
			STATUS	current
	DESCRIPTION ""
			::= { mbusF4 34 }

mbusF4Value0E		OBJECT-TYPE
			SYNTAX	INTEGER
			ACCESS	read-only
			STATUS	current
	DESCRIPTION ""
			::= { mbusF4 35 }

mbusF4VIF0F		OBJECT-TYPE
			SYNTAX	INTEGER
			ACCESS	read-only
			STATUS	current
	DESCRIPTION ""
			::= { mbusF4 36 }

mbusF4Value0F		OBJECT-TYPE
			SYNTAX	INTEGER
			ACCESS	read-only
			STATUS	current
	DESCRIPTION ""
			::= { mbusF4 37 }

mbusF4VIF10		OBJECT-TYPE
			SYNTAX	INTEGER
			ACCESS	read-only
			STATUS	current
	DESCRIPTION ""
			::= { mbusF4 38 }

mbusF4Value10		OBJECT-TYPE
			SYNTAX	INTEGER
			ACCESS	read-only
			STATUS	current
	DESCRIPTION ""
			::= { mbusF4 39 }

mbusF4VIF11		OBJECT-TYPE
			SYNTAX	INTEGER
			ACCESS	read-only
			STATUS	current
	DESCRIPTION ""
			::= { mbusF4 40 }

mbusF4Value11		OBJECT-TYPE
			SYNTAX	INTEGER
			ACCESS	read-only
			STATUS	current
	DESCRIPTION ""
			::= { mbusF4 41 }

mbusF4VIF12		OBJECT-TYPE
			SYNTAX	INTEGER
			ACCESS	read-only
			STATUS	current
	DESCRIPTION ""
			::= { mbusF4 42 }

mbusF4Value12		OBJECT-TYPE
			SYNTAX	INTEGER
			ACCESS	read-only
			STATUS	current
	DESCRIPTION ""
			::= { mbusF4 43 }

mbusF4VIF13		OBJECT-TYPE
			SYNTAX	INTEGER
			ACCESS	read-only
			STATUS	current
	DESCRIPTION ""
			::= { mbusF4 44 }

mbusF4Value13		OBJECT-TYPE
			SYNTAX	INTEGER
			ACCESS	read-only
			STATUS	current
	DESCRIPTION ""
			::= { mbusF4 45 }

mbusF4VIF14		OBJECT-TYPE
			SYNTAX	INTEGER
			ACCESS	read-only
			STATUS	current
	DESCRIPTION ""
			::= { mbusF4 46 }

mbusF4Value14		OBJECT-TYPE
			SYNTAX	INTEGER
			ACCESS	read-only
			STATUS	current
	DESCRIPTION ""
			::= { mbusF4 47 }

mbusF4VIF15		OBJECT-TYPE
			SYNTAX	INTEGER
			ACCESS	read-only
			STATUS	current
	DESCRIPTION ""
			::= { mbusF4 48 }

mbusF4Value15		OBJECT-TYPE
			SYNTAX	INTEGER
			ACCESS	read-only
			STATUS	current
	DESCRIPTION ""
			::= { mbusF4 49 }

mbusF4VIF16		OBJECT-TYPE
			SYNTAX	INTEGER
			ACCESS	read-only
			STATUS	current
	DESCRIPTION ""
			::= { mbusF4 50 }

mbusF4Value16		OBJECT-TYPE
			SYNTAX	INTEGER
			ACCESS	read-only
			STATUS	current
	DESCRIPTION ""
			::= { mbusF4 51 }

mbusF4VIF17		OBJECT-TYPE
			SYNTAX	INTEGER
			ACCESS	read-only
			STATUS	current
	DESCRIPTION ""
			::= { mbusF4 52 }

mbusF4Value17		OBJECT-TYPE
			SYNTAX	INTEGER
			ACCESS	read-only
			STATUS	current
	DESCRIPTION ""
			::= { mbusF4 53 }

mbusF4VIF18		OBJECT-TYPE
			SYNTAX	INTEGER
			ACCESS	read-only
			STATUS	current
	DESCRIPTION ""
			::= { mbusF4 54 }

mbusF4Value18		OBJECT-TYPE
			SYNTAX	INTEGER
			ACCESS	read-only
			STATUS	current
	DESCRIPTION ""
			::= { mbusF4 55 }

mbusF4VIF19		OBJECT-TYPE
			SYNTAX	INTEGER
			ACCESS	read-only
			STATUS	current
	DESCRIPTION ""
			::= { mbusF4 56 }

mbusF4Value19		OBJECT-TYPE
			SYNTAX	INTEGER
			ACCESS	read-only
			STATUS	current
	DESCRIPTION ""
			::= { mbusF4 57 }

mbusF4VIF1A		OBJECT-TYPE
			SYNTAX	INTEGER
			ACCESS	read-only
			STATUS	current
	DESCRIPTION ""
			::= { mbusF4 58 }

mbusF4Value1A		OBJECT-TYPE
			SYNTAX	INTEGER
			ACCESS	read-only
			STATUS	current
	DESCRIPTION ""
			::= { mbusF4 59 }

mbusF4VIF1B		OBJECT-TYPE
			SYNTAX	INTEGER
			ACCESS	read-only
			STATUS	current
	DESCRIPTION ""
			::= { mbusF4 60 }

mbusF4Value1B		OBJECT-TYPE
			SYNTAX	INTEGER
			ACCESS	read-only
			STATUS	current
	DESCRIPTION ""
			::= { mbusF4 61 }

mbusF4VIF1C		OBJECT-TYPE
			SYNTAX	INTEGER
			ACCESS	read-only
			STATUS	current
	DESCRIPTION ""
			::= { mbusF4 62 }

mbusF4Value1C		OBJECT-TYPE
			SYNTAX	INTEGER
			ACCESS	read-only
			STATUS	current
	DESCRIPTION ""
			::= { mbusF4 63 }

mbusF4VIF1D		OBJECT-TYPE
			SYNTAX	INTEGER
			ACCESS	read-only
			STATUS	current
	DESCRIPTION ""
			::= { mbusF4 64 }

mbusF4Value1D		OBJECT-TYPE
			SYNTAX	INTEGER
			ACCESS	read-only
			STATUS	current
	DESCRIPTION ""
			::= { mbusF4 65 }

mbusF4VIF1E		OBJECT-TYPE
			SYNTAX	INTEGER
			ACCESS	read-only
			STATUS	current
	DESCRIPTION ""
			::= { mbusF4 66 }

mbusF4Value1E		OBJECT-TYPE
			SYNTAX	INTEGER
			ACCESS	read-only
			STATUS	current
	DESCRIPTION ""
			::= { mbusF4 67 }

mbusF4VIF1F		OBJECT-TYPE
			SYNTAX	INTEGER
			ACCESS	read-only
			STATUS	current
	DESCRIPTION ""
			::= { mbusF4 68 }

mbusF4Value1F		OBJECT-TYPE
			SYNTAX	INTEGER
			ACCESS	read-only
			STATUS	current
	DESCRIPTION ""
			::= { mbusF4 69 }

mbusF4VIF20		OBJECT-TYPE
			SYNTAX	INTEGER
			ACCESS	read-only
			STATUS	current
	DESCRIPTION ""
			::= { mbusF4 70 }

mbusF4Value20		OBJECT-TYPE
			SYNTAX	INTEGER
			ACCESS	read-only
			STATUS	current
	DESCRIPTION ""
			::= { mbusF4 71 }

mbusF4VIF21		OBJECT-TYPE
			SYNTAX	INTEGER
			ACCESS	read-only
			STATUS	current
	DESCRIPTION ""
			::= { mbusF4 72 }

mbusF4Value21		OBJECT-TYPE
			SYNTAX	INTEGER
			ACCESS	read-only
			STATUS	current
	DESCRIPTION ""
			::= { mbusF4 73 }

mbusF4VIF22		OBJECT-TYPE
			SYNTAX	INTEGER
			ACCESS	read-only
			STATUS	current
	DESCRIPTION ""
			::= { mbusF4 74 }

mbusF4Value22		OBJECT-TYPE
			SYNTAX	INTEGER
			ACCESS	read-only
			STATUS	current
	DESCRIPTION ""
			::= { mbusF4 75 }

mbusF4VIF23		OBJECT-TYPE
			SYNTAX	INTEGER
			ACCESS	read-only
			STATUS	current
	DESCRIPTION ""
			::= { mbusF4 76 }

mbusF4Value23		OBJECT-TYPE
			SYNTAX	INTEGER
			ACCESS	read-only
			STATUS	current
	DESCRIPTION ""
			::= { mbusF4 77 }

mbusF4VIF24		OBJECT-TYPE
			SYNTAX	INTEGER
			ACCESS	read-only
			STATUS	current
	DESCRIPTION ""
			::= { mbusF4 78 }

mbusF4Value24		OBJECT-TYPE
			SYNTAX	INTEGER
			ACCESS	read-only
			STATUS	current
	DESCRIPTION ""
			::= { mbusF4 79 }

mbusF4VIF25		OBJECT-TYPE
			SYNTAX	INTEGER
			ACCESS	read-only
			STATUS	current
	DESCRIPTION ""
			::= { mbusF4 80 }

mbusF4Value25		OBJECT-TYPE
			SYNTAX	INTEGER
			ACCESS	read-only
			STATUS	current
	DESCRIPTION ""
			::= { mbusF4 81 }

mbusF4VIF26		OBJECT-TYPE
			SYNTAX	INTEGER
			ACCESS	read-only
			STATUS	current
	DESCRIPTION ""
			::= { mbusF4 82 }

mbusF4Value26		OBJECT-TYPE
			SYNTAX	INTEGER
			ACCESS	read-only
			STATUS	current
	DESCRIPTION ""
			::= { mbusF4 83 }

mbusF4VIF27		OBJECT-TYPE
			SYNTAX	INTEGER
			ACCESS	read-only
			STATUS	current
	DESCRIPTION ""
			::= { mbusF4 84 }

mbusF4Value27		OBJECT-TYPE
			SYNTAX	INTEGER
			ACCESS	read-only
			STATUS	current
	DESCRIPTION ""
			::= { mbusF4 85 }

mbusF4VIF28		OBJECT-TYPE
			SYNTAX	INTEGER
			ACCESS	read-only
			STATUS	current
	DESCRIPTION ""
			::= { mbusF4 86 }

mbusF4Value28		OBJECT-TYPE
			SYNTAX	INTEGER
			ACCESS	read-only
			STATUS	current
	DESCRIPTION ""
			::= { mbusF4 87 }

mbusF4VIF29		OBJECT-TYPE
			SYNTAX	INTEGER
			ACCESS	read-only
			STATUS	current
	DESCRIPTION ""
			::= { mbusF4 88 }

mbusF4Value29		OBJECT-TYPE
			SYNTAX	INTEGER
			ACCESS	read-only
			STATUS	current
	DESCRIPTION ""
			::= { mbusF4 89 }

mbusF4VIF2A		OBJECT-TYPE
			SYNTAX	INTEGER
			ACCESS	read-only
			STATUS	current
	DESCRIPTION ""
			::= { mbusF4 90 }

mbusF4Value2A		OBJECT-TYPE
			SYNTAX	INTEGER
			ACCESS	read-only
			STATUS	current
	DESCRIPTION ""
			::= { mbusF4 91 }

mbusF4VIF2B		OBJECT-TYPE
			SYNTAX	INTEGER
			ACCESS	read-only
			STATUS	current
	DESCRIPTION ""
			::= { mbusF4 92 }

mbusF4Value2B		OBJECT-TYPE
			SYNTAX	INTEGER
			ACCESS	read-only
			STATUS	current
	DESCRIPTION ""
			::= { mbusF4 93 }

mbusF4VIF2C		OBJECT-TYPE
			SYNTAX	INTEGER
			ACCESS	read-only
			STATUS	current
	DESCRIPTION ""
			::= { mbusF4 94 }

mbusF4Value2C		OBJECT-TYPE
			SYNTAX	INTEGER
			ACCESS	read-only
			STATUS	current
	DESCRIPTION ""
			::= { mbusF4 95 }

mbusF4VIF2D		OBJECT-TYPE
			SYNTAX	INTEGER
			ACCESS	read-only
			STATUS	current
	DESCRIPTION ""
			::= { mbusF4 96 }

mbusF4Value2D		OBJECT-TYPE
			SYNTAX	INTEGER
			ACCESS	read-only
			STATUS	current
	DESCRIPTION ""
			::= { mbusF4 97 }

mbusF4VIF2E		OBJECT-TYPE
			SYNTAX	INTEGER
			ACCESS	read-only
			STATUS	current
	DESCRIPTION ""
			::= { mbusF4 98 }

mbusF4Value2E		OBJECT-TYPE
			SYNTAX	INTEGER
			ACCESS	read-only
			STATUS	current
	DESCRIPTION ""
			::= { mbusF4 99 }

mbusF4VIF2F		OBJECT-TYPE
			SYNTAX	INTEGER
			ACCESS	read-only
			STATUS	current
	DESCRIPTION ""
			::= { mbusF4 100 }

mbusF4Value2F		OBJECT-TYPE
			SYNTAX	INTEGER
			ACCESS	read-only
			STATUS	current
	DESCRIPTION ""
			::= { mbusF4 101 }

mbusF5			OBJECT IDENTIFIER ::= { mbus 245 }

mbusF5IdNumber		OBJECT-TYPE
			SYNTAX	Gauge
			ACCESS	read-only
			STATUS	current
	DESCRIPTION ""
			::= { mbusF5 1 }

mbusF5Manufacturer	OBJECT-TYPE
			SYNTAX	Gauge
			ACCESS	read-only
			STATUS	current
	DESCRIPTION ""
			::= { mbusF5 2 }

mbusF5Version		OBJECT-TYPE
			SYNTAX	Gauge
			ACCESS	read-only
			STATUS	current
	DESCRIPTION ""
			::= { mbusF5 3 }

mbusF5Medium		OBJECT-TYPE
			SYNTAX	Gauge
			ACCESS	read-only
			STATUS	current
	DESCRIPTION ""
			::= { mbusF5 4 }

mbusF5Status		OBJECT-TYPE
			SYNTAX	Gauge
			ACCESS	read-only
			STATUS	current
	DESCRIPTION ""
			::= { mbusF5 5 }

mbusF5VIF00		OBJECT-TYPE
			SYNTAX	INTEGER
			ACCESS	read-only
			STATUS	current
	DESCRIPTION ""
			::= { mbusF5 6 }

mbusF5Value00		OBJECT-TYPE
			SYNTAX	INTEGER
			ACCESS	read-only
			STATUS	current
	DESCRIPTION ""
			::= { mbusF5 7 }

mbusF5VIF01		OBJECT-TYPE
			SYNTAX	INTEGER
			ACCESS	read-only
			STATUS	current
	DESCRIPTION ""
			::= { mbusF5 8 }

mbusF5Value01		OBJECT-TYPE
			SYNTAX	INTEGER
			ACCESS	read-only
			STATUS	current
	DESCRIPTION ""
			::= { mbusF5 9 }

mbusF5VIF02		OBJECT-TYPE
			SYNTAX	INTEGER
			ACCESS	read-only
			STATUS	current
	DESCRIPTION ""
			::= { mbusF5 10 }

mbusF5Value02		OBJECT-TYPE
			SYNTAX	INTEGER
			ACCESS	read-only
			STATUS	current
	DESCRIPTION ""
			::= { mbusF5 11 }

mbusF5VIF03		OBJECT-TYPE
			SYNTAX	INTEGER
			ACCESS	read-only
			STATUS	current
	DESCRIPTION ""
			::= { mbusF5 12 }

mbusF5Value03		OBJECT-TYPE
			SYNTAX	INTEGER
			ACCESS	read-only
			STATUS	current
	DESCRIPTION ""
			::= { mbusF5 13 }

mbusF5VIF04		OBJECT-TYPE
			SYNTAX	INTEGER
			ACCESS	read-only
			STATUS	current
	DESCRIPTION ""
			::= { mbusF5 14 }

mbusF5Value04		OBJECT-TYPE
			SYNTAX	INTEGER
			ACCESS	read-only
			STATUS	current
	DESCRIPTION ""
			::= { mbusF5 15 }

mbusF5VIF05		OBJECT-TYPE
			SYNTAX	INTEGER
			ACCESS	read-only
			STATUS	current
	DESCRIPTION ""
			::= { mbusF5 16 }

mbusF5Value05		OBJECT-TYPE
			SYNTAX	INTEGER
			ACCESS	read-only
			STATUS	current
	DESCRIPTION ""
			::= { mbusF5 17 }

mbusF5VIF06		OBJECT-TYPE
			SYNTAX	INTEGER
			ACCESS	read-only
			STATUS	current
	DESCRIPTION ""
			::= { mbusF5 18 }

mbusF5Value06		OBJECT-TYPE
			SYNTAX	INTEGER
			ACCESS	read-only
			STATUS	current
	DESCRIPTION ""
			::= { mbusF5 19 }

mbusF5VIF07		OBJECT-TYPE
			SYNTAX	INTEGER
			ACCESS	read-only
			STATUS	current
	DESCRIPTION ""
			::= { mbusF5 20 }

mbusF5Value07		OBJECT-TYPE
			SYNTAX	INTEGER
			ACCESS	read-only
			STATUS	current
	DESCRIPTION ""
			::= { mbusF5 21 }

mbusF5VIF08		OBJECT-TYPE
			SYNTAX	INTEGER
			ACCESS	read-only
			STATUS	current
	DESCRIPTION ""
			::= { mbusF5 22 }

mbusF5Value08		OBJECT-TYPE
			SYNTAX	INTEGER
			ACCESS	read-only
			STATUS	current
	DESCRIPTION ""
			::= { mbusF5 23 }

mbusF5VIF09		OBJECT-TYPE
			SYNTAX	INTEGER
			ACCESS	read-only
			STATUS	current
	DESCRIPTION ""
			::= { mbusF5 24 }

mbusF5Value09		OBJECT-TYPE
			SYNTAX	INTEGER
			ACCESS	read-only
			STATUS	current
	DESCRIPTION ""
			::= { mbusF5 25 }

mbusF5VIF0A		OBJECT-TYPE
			SYNTAX	INTEGER
			ACCESS	read-only
			STATUS	current
	DESCRIPTION ""
			::= { mbusF5 26 }

mbusF5Value0A		OBJECT-TYPE
			SYNTAX	INTEGER
			ACCESS	read-only
			STATUS	current
	DESCRIPTION ""
			::= { mbusF5 27 }

mbusF5VIF0B		OBJECT-TYPE
			SYNTAX	INTEGER
			ACCESS	read-only
			STATUS	current
	DESCRIPTION ""
			::= { mbusF5 28 }

mbusF5Value0B		OBJECT-TYPE
			SYNTAX	INTEGER
			ACCESS	read-only
			STATUS	current
	DESCRIPTION ""
			::= { mbusF5 29 }

mbusF5VIF0C		OBJECT-TYPE
			SYNTAX	INTEGER
			ACCESS	read-only
			STATUS	current
	DESCRIPTION ""
			::= { mbusF5 30 }

mbusF5Value0C		OBJECT-TYPE
			SYNTAX	INTEGER
			ACCESS	read-only
			STATUS	current
	DESCRIPTION ""
			::= { mbusF5 31 }

mbusF5VIF0D		OBJECT-TYPE
			SYNTAX	INTEGER
			ACCESS	read-only
			STATUS	current
	DESCRIPTION ""
			::= { mbusF5 32 }

mbusF5Value0D		OBJECT-TYPE
			SYNTAX	INTEGER
			ACCESS	read-only
			STATUS	current
	DESCRIPTION ""
			::= { mbusF5 33 }

mbusF5VIF0E		OBJECT-TYPE
			SYNTAX	INTEGER
			ACCESS	read-only
			STATUS	current
	DESCRIPTION ""
			::= { mbusF5 34 }

mbusF5Value0E		OBJECT-TYPE
			SYNTAX	INTEGER
			ACCESS	read-only
			STATUS	current
	DESCRIPTION ""
			::= { mbusF5 35 }

mbusF5VIF0F		OBJECT-TYPE
			SYNTAX	INTEGER
			ACCESS	read-only
			STATUS	current
	DESCRIPTION ""
			::= { mbusF5 36 }

mbusF5Value0F		OBJECT-TYPE
			SYNTAX	INTEGER
			ACCESS	read-only
			STATUS	current
	DESCRIPTION ""
			::= { mbusF5 37 }

mbusF5VIF10		OBJECT-TYPE
			SYNTAX	INTEGER
			ACCESS	read-only
			STATUS	current
	DESCRIPTION ""
			::= { mbusF5 38 }

mbusF5Value10		OBJECT-TYPE
			SYNTAX	INTEGER
			ACCESS	read-only
			STATUS	current
	DESCRIPTION ""
			::= { mbusF5 39 }

mbusF5VIF11		OBJECT-TYPE
			SYNTAX	INTEGER
			ACCESS	read-only
			STATUS	current
	DESCRIPTION ""
			::= { mbusF5 40 }

mbusF5Value11		OBJECT-TYPE
			SYNTAX	INTEGER
			ACCESS	read-only
			STATUS	current
	DESCRIPTION ""
			::= { mbusF5 41 }

mbusF5VIF12		OBJECT-TYPE
			SYNTAX	INTEGER
			ACCESS	read-only
			STATUS	current
	DESCRIPTION ""
			::= { mbusF5 42 }

mbusF5Value12		OBJECT-TYPE
			SYNTAX	INTEGER
			ACCESS	read-only
			STATUS	current
	DESCRIPTION ""
			::= { mbusF5 43 }

mbusF5VIF13		OBJECT-TYPE
			SYNTAX	INTEGER
			ACCESS	read-only
			STATUS	current
	DESCRIPTION ""
			::= { mbusF5 44 }

mbusF5Value13		OBJECT-TYPE
			SYNTAX	INTEGER
			ACCESS	read-only
			STATUS	current
	DESCRIPTION ""
			::= { mbusF5 45 }

mbusF5VIF14		OBJECT-TYPE
			SYNTAX	INTEGER
			ACCESS	read-only
			STATUS	current
	DESCRIPTION ""
			::= { mbusF5 46 }

mbusF5Value14		OBJECT-TYPE
			SYNTAX	INTEGER
			ACCESS	read-only
			STATUS	current
	DESCRIPTION ""
			::= { mbusF5 47 }

mbusF5VIF15		OBJECT-TYPE
			SYNTAX	INTEGER
			ACCESS	read-only
			STATUS	current
	DESCRIPTION ""
			::= { mbusF5 48 }

mbusF5Value15		OBJECT-TYPE
			SYNTAX	INTEGER
			ACCESS	read-only
			STATUS	current
	DESCRIPTION ""
			::= { mbusF5 49 }

mbusF5VIF16		OBJECT-TYPE
			SYNTAX	INTEGER
			ACCESS	read-only
			STATUS	current
	DESCRIPTION ""
			::= { mbusF5 50 }

mbusF5Value16		OBJECT-TYPE
			SYNTAX	INTEGER
			ACCESS	read-only
			STATUS	current
	DESCRIPTION ""
			::= { mbusF5 51 }

mbusF5VIF17		OBJECT-TYPE
			SYNTAX	INTEGER
			ACCESS	read-only
			STATUS	current
	DESCRIPTION ""
			::= { mbusF5 52 }

mbusF5Value17		OBJECT-TYPE
			SYNTAX	INTEGER
			ACCESS	read-only
			STATUS	current
	DESCRIPTION ""
			::= { mbusF5 53 }

mbusF5VIF18		OBJECT-TYPE
			SYNTAX	INTEGER
			ACCESS	read-only
			STATUS	current
	DESCRIPTION ""
			::= { mbusF5 54 }

mbusF5Value18		OBJECT-TYPE
			SYNTAX	INTEGER
			ACCESS	read-only
			STATUS	current
	DESCRIPTION ""
			::= { mbusF5 55 }

mbusF5VIF19		OBJECT-TYPE
			SYNTAX	INTEGER
			ACCESS	read-only
			STATUS	current
	DESCRIPTION ""
			::= { mbusF5 56 }

mbusF5Value19		OBJECT-TYPE
			SYNTAX	INTEGER
			ACCESS	read-only
			STATUS	current
	DESCRIPTION ""
			::= { mbusF5 57 }

mbusF5VIF1A		OBJECT-TYPE
			SYNTAX	INTEGER
			ACCESS	read-only
			STATUS	current
	DESCRIPTION ""
			::= { mbusF5 58 }

mbusF5Value1A		OBJECT-TYPE
			SYNTAX	INTEGER
			ACCESS	read-only
			STATUS	current
	DESCRIPTION ""
			::= { mbusF5 59 }

mbusF5VIF1B		OBJECT-TYPE
			SYNTAX	INTEGER
			ACCESS	read-only
			STATUS	current
	DESCRIPTION ""
			::= { mbusF5 60 }

mbusF5Value1B		OBJECT-TYPE
			SYNTAX	INTEGER
			ACCESS	read-only
			STATUS	current
	DESCRIPTION ""
			::= { mbusF5 61 }

mbusF5VIF1C		OBJECT-TYPE
			SYNTAX	INTEGER
			ACCESS	read-only
			STATUS	current
	DESCRIPTION ""
			::= { mbusF5 62 }

mbusF5Value1C		OBJECT-TYPE
			SYNTAX	INTEGER
			ACCESS	read-only
			STATUS	current
	DESCRIPTION ""
			::= { mbusF5 63 }

mbusF5VIF1D		OBJECT-TYPE
			SYNTAX	INTEGER
			ACCESS	read-only
			STATUS	current
	DESCRIPTION ""
			::= { mbusF5 64 }

mbusF5Value1D		OBJECT-TYPE
			SYNTAX	INTEGER
			ACCESS	read-only
			STATUS	current
	DESCRIPTION ""
			::= { mbusF5 65 }

mbusF5VIF1E		OBJECT-TYPE
			SYNTAX	INTEGER
			ACCESS	read-only
			STATUS	current
	DESCRIPTION ""
			::= { mbusF5 66 }

mbusF5Value1E		OBJECT-TYPE
			SYNTAX	INTEGER
			ACCESS	read-only
			STATUS	current
	DESCRIPTION ""
			::= { mbusF5 67 }

mbusF5VIF1F		OBJECT-TYPE
			SYNTAX	INTEGER
			ACCESS	read-only
			STATUS	current
	DESCRIPTION ""
			::= { mbusF5 68 }

mbusF5Value1F		OBJECT-TYPE
			SYNTAX	INTEGER
			ACCESS	read-only
			STATUS	current
	DESCRIPTION ""
			::= { mbusF5 69 }

mbusF5VIF20		OBJECT-TYPE
			SYNTAX	INTEGER
			ACCESS	read-only
			STATUS	current
	DESCRIPTION ""
			::= { mbusF5 70 }

mbusF5Value20		OBJECT-TYPE
			SYNTAX	INTEGER
			ACCESS	read-only
			STATUS	current
	DESCRIPTION ""
			::= { mbusF5 71 }

mbusF5VIF21		OBJECT-TYPE
			SYNTAX	INTEGER
			ACCESS	read-only
			STATUS	current
	DESCRIPTION ""
			::= { mbusF5 72 }

mbusF5Value21		OBJECT-TYPE
			SYNTAX	INTEGER
			ACCESS	read-only
			STATUS	current
	DESCRIPTION ""
			::= { mbusF5 73 }

mbusF5VIF22		OBJECT-TYPE
			SYNTAX	INTEGER
			ACCESS	read-only
			STATUS	current
	DESCRIPTION ""
			::= { mbusF5 74 }

mbusF5Value22		OBJECT-TYPE
			SYNTAX	INTEGER
			ACCESS	read-only
			STATUS	current
	DESCRIPTION ""
			::= { mbusF5 75 }

mbusF5VIF23		OBJECT-TYPE
			SYNTAX	INTEGER
			ACCESS	read-only
			STATUS	current
	DESCRIPTION ""
			::= { mbusF5 76 }

mbusF5Value23		OBJECT-TYPE
			SYNTAX	INTEGER
			ACCESS	read-only
			STATUS	current
	DESCRIPTION ""
			::= { mbusF5 77 }

mbusF5VIF24		OBJECT-TYPE
			SYNTAX	INTEGER
			ACCESS	read-only
			STATUS	current
	DESCRIPTION ""
			::= { mbusF5 78 }

mbusF5Value24		OBJECT-TYPE
			SYNTAX	INTEGER
			ACCESS	read-only
			STATUS	current
	DESCRIPTION ""
			::= { mbusF5 79 }

mbusF5VIF25		OBJECT-TYPE
			SYNTAX	INTEGER
			ACCESS	read-only
			STATUS	current
	DESCRIPTION ""
			::= { mbusF5 80 }

mbusF5Value25		OBJECT-TYPE
			SYNTAX	INTEGER
			ACCESS	read-only
			STATUS	current
	DESCRIPTION ""
			::= { mbusF5 81 }

mbusF5VIF26		OBJECT-TYPE
			SYNTAX	INTEGER
			ACCESS	read-only
			STATUS	current
	DESCRIPTION ""
			::= { mbusF5 82 }

mbusF5Value26		OBJECT-TYPE
			SYNTAX	INTEGER
			ACCESS	read-only
			STATUS	current
	DESCRIPTION ""
			::= { mbusF5 83 }

mbusF5VIF27		OBJECT-TYPE
			SYNTAX	INTEGER
			ACCESS	read-only
			STATUS	current
	DESCRIPTION ""
			::= { mbusF5 84 }

mbusF5Value27		OBJECT-TYPE
			SYNTAX	INTEGER
			ACCESS	read-only
			STATUS	current
	DESCRIPTION ""
			::= { mbusF5 85 }

mbusF5VIF28		OBJECT-TYPE
			SYNTAX	INTEGER
			ACCESS	read-only
			STATUS	current
	DESCRIPTION ""
			::= { mbusF5 86 }

mbusF5Value28		OBJECT-TYPE
			SYNTAX	INTEGER
			ACCESS	read-only
			STATUS	current
	DESCRIPTION ""
			::= { mbusF5 87 }

mbusF5VIF29		OBJECT-TYPE
			SYNTAX	INTEGER
			ACCESS	read-only
			STATUS	current
	DESCRIPTION ""
			::= { mbusF5 88 }

mbusF5Value29		OBJECT-TYPE
			SYNTAX	INTEGER
			ACCESS	read-only
			STATUS	current
	DESCRIPTION ""
			::= { mbusF5 89 }

mbusF5VIF2A		OBJECT-TYPE
			SYNTAX	INTEGER
			ACCESS	read-only
			STATUS	current
	DESCRIPTION ""
			::= { mbusF5 90 }

mbusF5Value2A		OBJECT-TYPE
			SYNTAX	INTEGER
			ACCESS	read-only
			STATUS	current
	DESCRIPTION ""
			::= { mbusF5 91 }

mbusF5VIF2B		OBJECT-TYPE
			SYNTAX	INTEGER
			ACCESS	read-only
			STATUS	current
	DESCRIPTION ""
			::= { mbusF5 92 }

mbusF5Value2B		OBJECT-TYPE
			SYNTAX	INTEGER
			ACCESS	read-only
			STATUS	current
	DESCRIPTION ""
			::= { mbusF5 93 }

mbusF5VIF2C		OBJECT-TYPE
			SYNTAX	INTEGER
			ACCESS	read-only
			STATUS	current
	DESCRIPTION ""
			::= { mbusF5 94 }

mbusF5Value2C		OBJECT-TYPE
			SYNTAX	INTEGER
			ACCESS	read-only
			STATUS	current
	DESCRIPTION ""
			::= { mbusF5 95 }

mbusF5VIF2D		OBJECT-TYPE
			SYNTAX	INTEGER
			ACCESS	read-only
			STATUS	current
	DESCRIPTION ""
			::= { mbusF5 96 }

mbusF5Value2D		OBJECT-TYPE
			SYNTAX	INTEGER
			ACCESS	read-only
			STATUS	current
	DESCRIPTION ""
			::= { mbusF5 97 }

mbusF5VIF2E		OBJECT-TYPE
			SYNTAX	INTEGER
			ACCESS	read-only
			STATUS	current
	DESCRIPTION ""
			::= { mbusF5 98 }

mbusF5Value2E		OBJECT-TYPE
			SYNTAX	INTEGER
			ACCESS	read-only
			STATUS	current
	DESCRIPTION ""
			::= { mbusF5 99 }

mbusF5VIF2F		OBJECT-TYPE
			SYNTAX	INTEGER
			ACCESS	read-only
			STATUS	current
	DESCRIPTION ""
			::= { mbusF5 100 }

mbusF5Value2F		OBJECT-TYPE
			SYNTAX	INTEGER
			ACCESS	read-only
			STATUS	current
	DESCRIPTION ""
			::= { mbusF5 101 }

mbusF6			OBJECT IDENTIFIER ::= { mbus 246 }

mbusF6IdNumber		OBJECT-TYPE
			SYNTAX	Gauge
			ACCESS	read-only
			STATUS	current
	DESCRIPTION ""
			::= { mbusF6 1 }

mbusF6Manufacturer	OBJECT-TYPE
			SYNTAX	Gauge
			ACCESS	read-only
			STATUS	current
	DESCRIPTION ""
			::= { mbusF6 2 }

mbusF6Version		OBJECT-TYPE
			SYNTAX	Gauge
			ACCESS	read-only
			STATUS	current
	DESCRIPTION ""
			::= { mbusF6 3 }

mbusF6Medium		OBJECT-TYPE
			SYNTAX	Gauge
			ACCESS	read-only
			STATUS	current
	DESCRIPTION ""
			::= { mbusF6 4 }

mbusF6Status		OBJECT-TYPE
			SYNTAX	Gauge
			ACCESS	read-only
			STATUS	current
	DESCRIPTION ""
			::= { mbusF6 5 }

mbusF6VIF00		OBJECT-TYPE
			SYNTAX	INTEGER
			ACCESS	read-only
			STATUS	current
	DESCRIPTION ""
			::= { mbusF6 6 }

mbusF6Value00		OBJECT-TYPE
			SYNTAX	INTEGER
			ACCESS	read-only
			STATUS	current
	DESCRIPTION ""
			::= { mbusF6 7 }

mbusF6VIF01		OBJECT-TYPE
			SYNTAX	INTEGER
			ACCESS	read-only
			STATUS	current
	DESCRIPTION ""
			::= { mbusF6 8 }

mbusF6Value01		OBJECT-TYPE
			SYNTAX	INTEGER
			ACCESS	read-only
			STATUS	current
	DESCRIPTION ""
			::= { mbusF6 9 }

mbusF6VIF02		OBJECT-TYPE
			SYNTAX	INTEGER
			ACCESS	read-only
			STATUS	current
	DESCRIPTION ""
			::= { mbusF6 10 }

mbusF6Value02		OBJECT-TYPE
			SYNTAX	INTEGER
			ACCESS	read-only
			STATUS	current
	DESCRIPTION ""
			::= { mbusF6 11 }

mbusF6VIF03		OBJECT-TYPE
			SYNTAX	INTEGER
			ACCESS	read-only
			STATUS	current
	DESCRIPTION ""
			::= { mbusF6 12 }

mbusF6Value03		OBJECT-TYPE
			SYNTAX	INTEGER
			ACCESS	read-only
			STATUS	current
	DESCRIPTION ""
			::= { mbusF6 13 }

mbusF6VIF04		OBJECT-TYPE
			SYNTAX	INTEGER
			ACCESS	read-only
			STATUS	current
	DESCRIPTION ""
			::= { mbusF6 14 }

mbusF6Value04		OBJECT-TYPE
			SYNTAX	INTEGER
			ACCESS	read-only
			STATUS	current
	DESCRIPTION ""
			::= { mbusF6 15 }

mbusF6VIF05		OBJECT-TYPE
			SYNTAX	INTEGER
			ACCESS	read-only
			STATUS	current
	DESCRIPTION ""
			::= { mbusF6 16 }

mbusF6Value05		OBJECT-TYPE
			SYNTAX	INTEGER
			ACCESS	read-only
			STATUS	current
	DESCRIPTION ""
			::= { mbusF6 17 }

mbusF6VIF06		OBJECT-TYPE
			SYNTAX	INTEGER
			ACCESS	read-only
			STATUS	current
	DESCRIPTION ""
			::= { mbusF6 18 }

mbusF6Value06		OBJECT-TYPE
			SYNTAX	INTEGER
			ACCESS	read-only
			STATUS	current
	DESCRIPTION ""
			::= { mbusF6 19 }

mbusF6VIF07		OBJECT-TYPE
			SYNTAX	INTEGER
			ACCESS	read-only
			STATUS	current
	DESCRIPTION ""
			::= { mbusF6 20 }

mbusF6Value07		OBJECT-TYPE
			SYNTAX	INTEGER
			ACCESS	read-only
			STATUS	current
	DESCRIPTION ""
			::= { mbusF6 21 }

mbusF6VIF08		OBJECT-TYPE
			SYNTAX	INTEGER
			ACCESS	read-only
			STATUS	current
	DESCRIPTION ""
			::= { mbusF6 22 }

mbusF6Value08		OBJECT-TYPE
			SYNTAX	INTEGER
			ACCESS	read-only
			STATUS	current
	DESCRIPTION ""
			::= { mbusF6 23 }

mbusF6VIF09		OBJECT-TYPE
			SYNTAX	INTEGER
			ACCESS	read-only
			STATUS	current
	DESCRIPTION ""
			::= { mbusF6 24 }

mbusF6Value09		OBJECT-TYPE
			SYNTAX	INTEGER
			ACCESS	read-only
			STATUS	current
	DESCRIPTION ""
			::= { mbusF6 25 }

mbusF6VIF0A		OBJECT-TYPE
			SYNTAX	INTEGER
			ACCESS	read-only
			STATUS	current
	DESCRIPTION ""
			::= { mbusF6 26 }

mbusF6Value0A		OBJECT-TYPE
			SYNTAX	INTEGER
			ACCESS	read-only
			STATUS	current
	DESCRIPTION ""
			::= { mbusF6 27 }

mbusF6VIF0B		OBJECT-TYPE
			SYNTAX	INTEGER
			ACCESS	read-only
			STATUS	current
	DESCRIPTION ""
			::= { mbusF6 28 }

mbusF6Value0B		OBJECT-TYPE
			SYNTAX	INTEGER
			ACCESS	read-only
			STATUS	current
	DESCRIPTION ""
			::= { mbusF6 29 }

mbusF6VIF0C		OBJECT-TYPE
			SYNTAX	INTEGER
			ACCESS	read-only
			STATUS	current
	DESCRIPTION ""
			::= { mbusF6 30 }

mbusF6Value0C		OBJECT-TYPE
			SYNTAX	INTEGER
			ACCESS	read-only
			STATUS	current
	DESCRIPTION ""
			::= { mbusF6 31 }

mbusF6VIF0D		OBJECT-TYPE
			SYNTAX	INTEGER
			ACCESS	read-only
			STATUS	current
	DESCRIPTION ""
			::= { mbusF6 32 }

mbusF6Value0D		OBJECT-TYPE
			SYNTAX	INTEGER
			ACCESS	read-only
			STATUS	current
	DESCRIPTION ""
			::= { mbusF6 33 }

mbusF6VIF0E		OBJECT-TYPE
			SYNTAX	INTEGER
			ACCESS	read-only
			STATUS	current
	DESCRIPTION ""
			::= { mbusF6 34 }

mbusF6Value0E		OBJECT-TYPE
			SYNTAX	INTEGER
			ACCESS	read-only
			STATUS	current
	DESCRIPTION ""
			::= { mbusF6 35 }

mbusF6VIF0F		OBJECT-TYPE
			SYNTAX	INTEGER
			ACCESS	read-only
			STATUS	current
	DESCRIPTION ""
			::= { mbusF6 36 }

mbusF6Value0F		OBJECT-TYPE
			SYNTAX	INTEGER
			ACCESS	read-only
			STATUS	current
	DESCRIPTION ""
			::= { mbusF6 37 }

mbusF6VIF10		OBJECT-TYPE
			SYNTAX	INTEGER
			ACCESS	read-only
			STATUS	current
	DESCRIPTION ""
			::= { mbusF6 38 }

mbusF6Value10		OBJECT-TYPE
			SYNTAX	INTEGER
			ACCESS	read-only
			STATUS	current
	DESCRIPTION ""
			::= { mbusF6 39 }

mbusF6VIF11		OBJECT-TYPE
			SYNTAX	INTEGER
			ACCESS	read-only
			STATUS	current
	DESCRIPTION ""
			::= { mbusF6 40 }

mbusF6Value11		OBJECT-TYPE
			SYNTAX	INTEGER
			ACCESS	read-only
			STATUS	current
	DESCRIPTION ""
			::= { mbusF6 41 }

mbusF6VIF12		OBJECT-TYPE
			SYNTAX	INTEGER
			ACCESS	read-only
			STATUS	current
	DESCRIPTION ""
			::= { mbusF6 42 }

mbusF6Value12		OBJECT-TYPE
			SYNTAX	INTEGER
			ACCESS	read-only
			STATUS	current
	DESCRIPTION ""
			::= { mbusF6 43 }

mbusF6VIF13		OBJECT-TYPE
			SYNTAX	INTEGER
			ACCESS	read-only
			STATUS	current
	DESCRIPTION ""
			::= { mbusF6 44 }

mbusF6Value13		OBJECT-TYPE
			SYNTAX	INTEGER
			ACCESS	read-only
			STATUS	current
	DESCRIPTION ""
			::= { mbusF6 45 }

mbusF6VIF14		OBJECT-TYPE
			SYNTAX	INTEGER
			ACCESS	read-only
			STATUS	current
	DESCRIPTION ""
			::= { mbusF6 46 }

mbusF6Value14		OBJECT-TYPE
			SYNTAX	INTEGER
			ACCESS	read-only
			STATUS	current
	DESCRIPTION ""
			::= { mbusF6 47 }

mbusF6VIF15		OBJECT-TYPE
			SYNTAX	INTEGER
			ACCESS	read-only
			STATUS	current
	DESCRIPTION ""
			::= { mbusF6 48 }

mbusF6Value15		OBJECT-TYPE
			SYNTAX	INTEGER
			ACCESS	read-only
			STATUS	current
	DESCRIPTION ""
			::= { mbusF6 49 }

mbusF6VIF16		OBJECT-TYPE
			SYNTAX	INTEGER
			ACCESS	read-only
			STATUS	current
	DESCRIPTION ""
			::= { mbusF6 50 }

mbusF6Value16		OBJECT-TYPE
			SYNTAX	INTEGER
			ACCESS	read-only
			STATUS	current
	DESCRIPTION ""
			::= { mbusF6 51 }

mbusF6VIF17		OBJECT-TYPE
			SYNTAX	INTEGER
			ACCESS	read-only
			STATUS	current
	DESCRIPTION ""
			::= { mbusF6 52 }

mbusF6Value17		OBJECT-TYPE
			SYNTAX	INTEGER
			ACCESS	read-only
			STATUS	current
	DESCRIPTION ""
			::= { mbusF6 53 }

mbusF6VIF18		OBJECT-TYPE
			SYNTAX	INTEGER
			ACCESS	read-only
			STATUS	current
	DESCRIPTION ""
			::= { mbusF6 54 }

mbusF6Value18		OBJECT-TYPE
			SYNTAX	INTEGER
			ACCESS	read-only
			STATUS	current
	DESCRIPTION ""
			::= { mbusF6 55 }

mbusF6VIF19		OBJECT-TYPE
			SYNTAX	INTEGER
			ACCESS	read-only
			STATUS	current
	DESCRIPTION ""
			::= { mbusF6 56 }

mbusF6Value19		OBJECT-TYPE
			SYNTAX	INTEGER
			ACCESS	read-only
			STATUS	current
	DESCRIPTION ""
			::= { mbusF6 57 }

mbusF6VIF1A		OBJECT-TYPE
			SYNTAX	INTEGER
			ACCESS	read-only
			STATUS	current
	DESCRIPTION ""
			::= { mbusF6 58 }

mbusF6Value1A		OBJECT-TYPE
			SYNTAX	INTEGER
			ACCESS	read-only
			STATUS	current
	DESCRIPTION ""
			::= { mbusF6 59 }

mbusF6VIF1B		OBJECT-TYPE
			SYNTAX	INTEGER
			ACCESS	read-only
			STATUS	current
	DESCRIPTION ""
			::= { mbusF6 60 }

mbusF6Value1B		OBJECT-TYPE
			SYNTAX	INTEGER
			ACCESS	read-only
			STATUS	current
	DESCRIPTION ""
			::= { mbusF6 61 }

mbusF6VIF1C		OBJECT-TYPE
			SYNTAX	INTEGER
			ACCESS	read-only
			STATUS	current
	DESCRIPTION ""
			::= { mbusF6 62 }

mbusF6Value1C		OBJECT-TYPE
			SYNTAX	INTEGER
			ACCESS	read-only
			STATUS	current
	DESCRIPTION ""
			::= { mbusF6 63 }

mbusF6VIF1D		OBJECT-TYPE
			SYNTAX	INTEGER
			ACCESS	read-only
			STATUS	current
	DESCRIPTION ""
			::= { mbusF6 64 }

mbusF6Value1D		OBJECT-TYPE
			SYNTAX	INTEGER
			ACCESS	read-only
			STATUS	current
	DESCRIPTION ""
			::= { mbusF6 65 }

mbusF6VIF1E		OBJECT-TYPE
			SYNTAX	INTEGER
			ACCESS	read-only
			STATUS	current
	DESCRIPTION ""
			::= { mbusF6 66 }

mbusF6Value1E		OBJECT-TYPE
			SYNTAX	INTEGER
			ACCESS	read-only
			STATUS	current
	DESCRIPTION ""
			::= { mbusF6 67 }

mbusF6VIF1F		OBJECT-TYPE
			SYNTAX	INTEGER
			ACCESS	read-only
			STATUS	current
	DESCRIPTION ""
			::= { mbusF6 68 }

mbusF6Value1F		OBJECT-TYPE
			SYNTAX	INTEGER
			ACCESS	read-only
			STATUS	current
	DESCRIPTION ""
			::= { mbusF6 69 }

mbusF6VIF20		OBJECT-TYPE
			SYNTAX	INTEGER
			ACCESS	read-only
			STATUS	current
	DESCRIPTION ""
			::= { mbusF6 70 }

mbusF6Value20		OBJECT-TYPE
			SYNTAX	INTEGER
			ACCESS	read-only
			STATUS	current
	DESCRIPTION ""
			::= { mbusF6 71 }

mbusF6VIF21		OBJECT-TYPE
			SYNTAX	INTEGER
			ACCESS	read-only
			STATUS	current
	DESCRIPTION ""
			::= { mbusF6 72 }

mbusF6Value21		OBJECT-TYPE
			SYNTAX	INTEGER
			ACCESS	read-only
			STATUS	current
	DESCRIPTION ""
			::= { mbusF6 73 }

mbusF6VIF22		OBJECT-TYPE
			SYNTAX	INTEGER
			ACCESS	read-only
			STATUS	current
	DESCRIPTION ""
			::= { mbusF6 74 }

mbusF6Value22		OBJECT-TYPE
			SYNTAX	INTEGER
			ACCESS	read-only
			STATUS	current
	DESCRIPTION ""
			::= { mbusF6 75 }

mbusF6VIF23		OBJECT-TYPE
			SYNTAX	INTEGER
			ACCESS	read-only
			STATUS	current
	DESCRIPTION ""
			::= { mbusF6 76 }

mbusF6Value23		OBJECT-TYPE
			SYNTAX	INTEGER
			ACCESS	read-only
			STATUS	current
	DESCRIPTION ""
			::= { mbusF6 77 }

mbusF6VIF24		OBJECT-TYPE
			SYNTAX	INTEGER
			ACCESS	read-only
			STATUS	current
	DESCRIPTION ""
			::= { mbusF6 78 }

mbusF6Value24		OBJECT-TYPE
			SYNTAX	INTEGER
			ACCESS	read-only
			STATUS	current
	DESCRIPTION ""
			::= { mbusF6 79 }

mbusF6VIF25		OBJECT-TYPE
			SYNTAX	INTEGER
			ACCESS	read-only
			STATUS	current
	DESCRIPTION ""
			::= { mbusF6 80 }

mbusF6Value25		OBJECT-TYPE
			SYNTAX	INTEGER
			ACCESS	read-only
			STATUS	current
	DESCRIPTION ""
			::= { mbusF6 81 }

mbusF6VIF26		OBJECT-TYPE
			SYNTAX	INTEGER
			ACCESS	read-only
			STATUS	current
	DESCRIPTION ""
			::= { mbusF6 82 }

mbusF6Value26		OBJECT-TYPE
			SYNTAX	INTEGER
			ACCESS	read-only
			STATUS	current
	DESCRIPTION ""
			::= { mbusF6 83 }

mbusF6VIF27		OBJECT-TYPE
			SYNTAX	INTEGER
			ACCESS	read-only
			STATUS	current
	DESCRIPTION ""
			::= { mbusF6 84 }

mbusF6Value27		OBJECT-TYPE
			SYNTAX	INTEGER
			ACCESS	read-only
			STATUS	current
	DESCRIPTION ""
			::= { mbusF6 85 }

mbusF6VIF28		OBJECT-TYPE
			SYNTAX	INTEGER
			ACCESS	read-only
			STATUS	current
	DESCRIPTION ""
			::= { mbusF6 86 }

mbusF6Value28		OBJECT-TYPE
			SYNTAX	INTEGER
			ACCESS	read-only
			STATUS	current
	DESCRIPTION ""
			::= { mbusF6 87 }

mbusF6VIF29		OBJECT-TYPE
			SYNTAX	INTEGER
			ACCESS	read-only
			STATUS	current
	DESCRIPTION ""
			::= { mbusF6 88 }

mbusF6Value29		OBJECT-TYPE
			SYNTAX	INTEGER
			ACCESS	read-only
			STATUS	current
	DESCRIPTION ""
			::= { mbusF6 89 }

mbusF6VIF2A		OBJECT-TYPE
			SYNTAX	INTEGER
			ACCESS	read-only
			STATUS	current
	DESCRIPTION ""
			::= { mbusF6 90 }

mbusF6Value2A		OBJECT-TYPE
			SYNTAX	INTEGER
			ACCESS	read-only
			STATUS	current
	DESCRIPTION ""
			::= { mbusF6 91 }

mbusF6VIF2B		OBJECT-TYPE
			SYNTAX	INTEGER
			ACCESS	read-only
			STATUS	current
	DESCRIPTION ""
			::= { mbusF6 92 }

mbusF6Value2B		OBJECT-TYPE
			SYNTAX	INTEGER
			ACCESS	read-only
			STATUS	current
	DESCRIPTION ""
			::= { mbusF6 93 }

mbusF6VIF2C		OBJECT-TYPE
			SYNTAX	INTEGER
			ACCESS	read-only
			STATUS	current
	DESCRIPTION ""
			::= { mbusF6 94 }

mbusF6Value2C		OBJECT-TYPE
			SYNTAX	INTEGER
			ACCESS	read-only
			STATUS	current
	DESCRIPTION ""
			::= { mbusF6 95 }

mbusF6VIF2D		OBJECT-TYPE
			SYNTAX	INTEGER
			ACCESS	read-only
			STATUS	current
	DESCRIPTION ""
			::= { mbusF6 96 }

mbusF6Value2D		OBJECT-TYPE
			SYNTAX	INTEGER
			ACCESS	read-only
			STATUS	current
	DESCRIPTION ""
			::= { mbusF6 97 }

mbusF6VIF2E		OBJECT-TYPE
			SYNTAX	INTEGER
			ACCESS	read-only
			STATUS	current
	DESCRIPTION ""
			::= { mbusF6 98 }

mbusF6Value2E		OBJECT-TYPE
			SYNTAX	INTEGER
			ACCESS	read-only
			STATUS	current
	DESCRIPTION ""
			::= { mbusF6 99 }

mbusF6VIF2F		OBJECT-TYPE
			SYNTAX	INTEGER
			ACCESS	read-only
			STATUS	current
	DESCRIPTION ""
			::= { mbusF6 100 }

mbusF6Value2F		OBJECT-TYPE
			SYNTAX	INTEGER
			ACCESS	read-only
			STATUS	current
	DESCRIPTION ""
			::= { mbusF6 101 }

mbusF7			OBJECT IDENTIFIER ::= { mbus 247 }

mbusF7IdNumber		OBJECT-TYPE
			SYNTAX	Gauge
			ACCESS	read-only
			STATUS	current
	DESCRIPTION ""
			::= { mbusF7 1 }

mbusF7Manufacturer	OBJECT-TYPE
			SYNTAX	Gauge
			ACCESS	read-only
			STATUS	current
	DESCRIPTION ""
			::= { mbusF7 2 }

mbusF7Version		OBJECT-TYPE
			SYNTAX	Gauge
			ACCESS	read-only
			STATUS	current
	DESCRIPTION ""
			::= { mbusF7 3 }

mbusF7Medium		OBJECT-TYPE
			SYNTAX	Gauge
			ACCESS	read-only
			STATUS	current
	DESCRIPTION ""
			::= { mbusF7 4 }

mbusF7Status		OBJECT-TYPE
			SYNTAX	Gauge
			ACCESS	read-only
			STATUS	current
	DESCRIPTION ""
			::= { mbusF7 5 }

mbusF7VIF00		OBJECT-TYPE
			SYNTAX	INTEGER
			ACCESS	read-only
			STATUS	current
	DESCRIPTION ""
			::= { mbusF7 6 }

mbusF7Value00		OBJECT-TYPE
			SYNTAX	INTEGER
			ACCESS	read-only
			STATUS	current
	DESCRIPTION ""
			::= { mbusF7 7 }

mbusF7VIF01		OBJECT-TYPE
			SYNTAX	INTEGER
			ACCESS	read-only
			STATUS	current
	DESCRIPTION ""
			::= { mbusF7 8 }

mbusF7Value01		OBJECT-TYPE
			SYNTAX	INTEGER
			ACCESS	read-only
			STATUS	current
	DESCRIPTION ""
			::= { mbusF7 9 }

mbusF7VIF02		OBJECT-TYPE
			SYNTAX	INTEGER
			ACCESS	read-only
			STATUS	current
	DESCRIPTION ""
			::= { mbusF7 10 }

mbusF7Value02		OBJECT-TYPE
			SYNTAX	INTEGER
			ACCESS	read-only
			STATUS	current
	DESCRIPTION ""
			::= { mbusF7 11 }

mbusF7VIF03		OBJECT-TYPE
			SYNTAX	INTEGER
			ACCESS	read-only
			STATUS	current
	DESCRIPTION ""
			::= { mbusF7 12 }

mbusF7Value03		OBJECT-TYPE
			SYNTAX	INTEGER
			ACCESS	read-only
			STATUS	current
	DESCRIPTION ""
			::= { mbusF7 13 }

mbusF7VIF04		OBJECT-TYPE
			SYNTAX	INTEGER
			ACCESS	read-only
			STATUS	current
	DESCRIPTION ""
			::= { mbusF7 14 }

mbusF7Value04		OBJECT-TYPE
			SYNTAX	INTEGER
			ACCESS	read-only
			STATUS	current
	DESCRIPTION ""
			::= { mbusF7 15 }

mbusF7VIF05		OBJECT-TYPE
			SYNTAX	INTEGER
			ACCESS	read-only
			STATUS	current
	DESCRIPTION ""
			::= { mbusF7 16 }

mbusF7Value05		OBJECT-TYPE
			SYNTAX	INTEGER
			ACCESS	read-only
			STATUS	current
	DESCRIPTION ""
			::= { mbusF7 17 }

mbusF7VIF06		OBJECT-TYPE
			SYNTAX	INTEGER
			ACCESS	read-only
			STATUS	current
	DESCRIPTION ""
			::= { mbusF7 18 }

mbusF7Value06		OBJECT-TYPE
			SYNTAX	INTEGER
			ACCESS	read-only
			STATUS	current
	DESCRIPTION ""
			::= { mbusF7 19 }

mbusF7VIF07		OBJECT-TYPE
			SYNTAX	INTEGER
			ACCESS	read-only
			STATUS	current
	DESCRIPTION ""
			::= { mbusF7 20 }

mbusF7Value07		OBJECT-TYPE
			SYNTAX	INTEGER
			ACCESS	read-only
			STATUS	current
	DESCRIPTION ""
			::= { mbusF7 21 }

mbusF7VIF08		OBJECT-TYPE
			SYNTAX	INTEGER
			ACCESS	read-only
			STATUS	current
	DESCRIPTION ""
			::= { mbusF7 22 }

mbusF7Value08		OBJECT-TYPE
			SYNTAX	INTEGER
			ACCESS	read-only
			STATUS	current
	DESCRIPTION ""
			::= { mbusF7 23 }

mbusF7VIF09		OBJECT-TYPE
			SYNTAX	INTEGER
			ACCESS	read-only
			STATUS	current
	DESCRIPTION ""
			::= { mbusF7 24 }

mbusF7Value09		OBJECT-TYPE
			SYNTAX	INTEGER
			ACCESS	read-only
			STATUS	current
	DESCRIPTION ""
			::= { mbusF7 25 }

mbusF7VIF0A		OBJECT-TYPE
			SYNTAX	INTEGER
			ACCESS	read-only
			STATUS	current
	DESCRIPTION ""
			::= { mbusF7 26 }

mbusF7Value0A		OBJECT-TYPE
			SYNTAX	INTEGER
			ACCESS	read-only
			STATUS	current
	DESCRIPTION ""
			::= { mbusF7 27 }

mbusF7VIF0B		OBJECT-TYPE
			SYNTAX	INTEGER
			ACCESS	read-only
			STATUS	current
	DESCRIPTION ""
			::= { mbusF7 28 }

mbusF7Value0B		OBJECT-TYPE
			SYNTAX	INTEGER
			ACCESS	read-only
			STATUS	current
	DESCRIPTION ""
			::= { mbusF7 29 }

mbusF7VIF0C		OBJECT-TYPE
			SYNTAX	INTEGER
			ACCESS	read-only
			STATUS	current
	DESCRIPTION ""
			::= { mbusF7 30 }

mbusF7Value0C		OBJECT-TYPE
			SYNTAX	INTEGER
			ACCESS	read-only
			STATUS	current
	DESCRIPTION ""
			::= { mbusF7 31 }

mbusF7VIF0D		OBJECT-TYPE
			SYNTAX	INTEGER
			ACCESS	read-only
			STATUS	current
	DESCRIPTION ""
			::= { mbusF7 32 }

mbusF7Value0D		OBJECT-TYPE
			SYNTAX	INTEGER
			ACCESS	read-only
			STATUS	current
	DESCRIPTION ""
			::= { mbusF7 33 }

mbusF7VIF0E		OBJECT-TYPE
			SYNTAX	INTEGER
			ACCESS	read-only
			STATUS	current
	DESCRIPTION ""
			::= { mbusF7 34 }

mbusF7Value0E		OBJECT-TYPE
			SYNTAX	INTEGER
			ACCESS	read-only
			STATUS	current
	DESCRIPTION ""
			::= { mbusF7 35 }

mbusF7VIF0F		OBJECT-TYPE
			SYNTAX	INTEGER
			ACCESS	read-only
			STATUS	current
	DESCRIPTION ""
			::= { mbusF7 36 }

mbusF7Value0F		OBJECT-TYPE
			SYNTAX	INTEGER
			ACCESS	read-only
			STATUS	current
	DESCRIPTION ""
			::= { mbusF7 37 }

mbusF7VIF10		OBJECT-TYPE
			SYNTAX	INTEGER
			ACCESS	read-only
			STATUS	current
	DESCRIPTION ""
			::= { mbusF7 38 }

mbusF7Value10		OBJECT-TYPE
			SYNTAX	INTEGER
			ACCESS	read-only
			STATUS	current
	DESCRIPTION ""
			::= { mbusF7 39 }

mbusF7VIF11		OBJECT-TYPE
			SYNTAX	INTEGER
			ACCESS	read-only
			STATUS	current
	DESCRIPTION ""
			::= { mbusF7 40 }

mbusF7Value11		OBJECT-TYPE
			SYNTAX	INTEGER
			ACCESS	read-only
			STATUS	current
	DESCRIPTION ""
			::= { mbusF7 41 }

mbusF7VIF12		OBJECT-TYPE
			SYNTAX	INTEGER
			ACCESS	read-only
			STATUS	current
	DESCRIPTION ""
			::= { mbusF7 42 }

mbusF7Value12		OBJECT-TYPE
			SYNTAX	INTEGER
			ACCESS	read-only
			STATUS	current
	DESCRIPTION ""
			::= { mbusF7 43 }

mbusF7VIF13		OBJECT-TYPE
			SYNTAX	INTEGER
			ACCESS	read-only
			STATUS	current
	DESCRIPTION ""
			::= { mbusF7 44 }

mbusF7Value13		OBJECT-TYPE
			SYNTAX	INTEGER
			ACCESS	read-only
			STATUS	current
	DESCRIPTION ""
			::= { mbusF7 45 }

mbusF7VIF14		OBJECT-TYPE
			SYNTAX	INTEGER
			ACCESS	read-only
			STATUS	current
	DESCRIPTION ""
			::= { mbusF7 46 }

mbusF7Value14		OBJECT-TYPE
			SYNTAX	INTEGER
			ACCESS	read-only
			STATUS	current
	DESCRIPTION ""
			::= { mbusF7 47 }

mbusF7VIF15		OBJECT-TYPE
			SYNTAX	INTEGER
			ACCESS	read-only
			STATUS	current
	DESCRIPTION ""
			::= { mbusF7 48 }

mbusF7Value15		OBJECT-TYPE
			SYNTAX	INTEGER
			ACCESS	read-only
			STATUS	current
	DESCRIPTION ""
			::= { mbusF7 49 }

mbusF7VIF16		OBJECT-TYPE
			SYNTAX	INTEGER
			ACCESS	read-only
			STATUS	current
	DESCRIPTION ""
			::= { mbusF7 50 }

mbusF7Value16		OBJECT-TYPE
			SYNTAX	INTEGER
			ACCESS	read-only
			STATUS	current
	DESCRIPTION ""
			::= { mbusF7 51 }

mbusF7VIF17		OBJECT-TYPE
			SYNTAX	INTEGER
			ACCESS	read-only
			STATUS	current
	DESCRIPTION ""
			::= { mbusF7 52 }

mbusF7Value17		OBJECT-TYPE
			SYNTAX	INTEGER
			ACCESS	read-only
			STATUS	current
	DESCRIPTION ""
			::= { mbusF7 53 }

mbusF7VIF18		OBJECT-TYPE
			SYNTAX	INTEGER
			ACCESS	read-only
			STATUS	current
	DESCRIPTION ""
			::= { mbusF7 54 }

mbusF7Value18		OBJECT-TYPE
			SYNTAX	INTEGER
			ACCESS	read-only
			STATUS	current
	DESCRIPTION ""
			::= { mbusF7 55 }

mbusF7VIF19		OBJECT-TYPE
			SYNTAX	INTEGER
			ACCESS	read-only
			STATUS	current
	DESCRIPTION ""
			::= { mbusF7 56 }

mbusF7Value19		OBJECT-TYPE
			SYNTAX	INTEGER
			ACCESS	read-only
			STATUS	current
	DESCRIPTION ""
			::= { mbusF7 57 }

mbusF7VIF1A		OBJECT-TYPE
			SYNTAX	INTEGER
			ACCESS	read-only
			STATUS	current
	DESCRIPTION ""
			::= { mbusF7 58 }

mbusF7Value1A		OBJECT-TYPE
			SYNTAX	INTEGER
			ACCESS	read-only
			STATUS	current
	DESCRIPTION ""
			::= { mbusF7 59 }

mbusF7VIF1B		OBJECT-TYPE
			SYNTAX	INTEGER
			ACCESS	read-only
			STATUS	current
	DESCRIPTION ""
			::= { mbusF7 60 }

mbusF7Value1B		OBJECT-TYPE
			SYNTAX	INTEGER
			ACCESS	read-only
			STATUS	current
	DESCRIPTION ""
			::= { mbusF7 61 }

mbusF7VIF1C		OBJECT-TYPE
			SYNTAX	INTEGER
			ACCESS	read-only
			STATUS	current
	DESCRIPTION ""
			::= { mbusF7 62 }

mbusF7Value1C		OBJECT-TYPE
			SYNTAX	INTEGER
			ACCESS	read-only
			STATUS	current
	DESCRIPTION ""
			::= { mbusF7 63 }

mbusF7VIF1D		OBJECT-TYPE
			SYNTAX	INTEGER
			ACCESS	read-only
			STATUS	current
	DESCRIPTION ""
			::= { mbusF7 64 }

mbusF7Value1D		OBJECT-TYPE
			SYNTAX	INTEGER
			ACCESS	read-only
			STATUS	current
	DESCRIPTION ""
			::= { mbusF7 65 }

mbusF7VIF1E		OBJECT-TYPE
			SYNTAX	INTEGER
			ACCESS	read-only
			STATUS	current
	DESCRIPTION ""
			::= { mbusF7 66 }

mbusF7Value1E		OBJECT-TYPE
			SYNTAX	INTEGER
			ACCESS	read-only
			STATUS	current
	DESCRIPTION ""
			::= { mbusF7 67 }

mbusF7VIF1F		OBJECT-TYPE
			SYNTAX	INTEGER
			ACCESS	read-only
			STATUS	current
	DESCRIPTION ""
			::= { mbusF7 68 }

mbusF7Value1F		OBJECT-TYPE
			SYNTAX	INTEGER
			ACCESS	read-only
			STATUS	current
	DESCRIPTION ""
			::= { mbusF7 69 }

mbusF7VIF20		OBJECT-TYPE
			SYNTAX	INTEGER
			ACCESS	read-only
			STATUS	current
	DESCRIPTION ""
			::= { mbusF7 70 }

mbusF7Value20		OBJECT-TYPE
			SYNTAX	INTEGER
			ACCESS	read-only
			STATUS	current
	DESCRIPTION ""
			::= { mbusF7 71 }

mbusF7VIF21		OBJECT-TYPE
			SYNTAX	INTEGER
			ACCESS	read-only
			STATUS	current
	DESCRIPTION ""
			::= { mbusF7 72 }

mbusF7Value21		OBJECT-TYPE
			SYNTAX	INTEGER
			ACCESS	read-only
			STATUS	current
	DESCRIPTION ""
			::= { mbusF7 73 }

mbusF7VIF22		OBJECT-TYPE
			SYNTAX	INTEGER
			ACCESS	read-only
			STATUS	current
	DESCRIPTION ""
			::= { mbusF7 74 }

mbusF7Value22		OBJECT-TYPE
			SYNTAX	INTEGER
			ACCESS	read-only
			STATUS	current
	DESCRIPTION ""
			::= { mbusF7 75 }

mbusF7VIF23		OBJECT-TYPE
			SYNTAX	INTEGER
			ACCESS	read-only
			STATUS	current
	DESCRIPTION ""
			::= { mbusF7 76 }

mbusF7Value23		OBJECT-TYPE
			SYNTAX	INTEGER
			ACCESS	read-only
			STATUS	current
	DESCRIPTION ""
			::= { mbusF7 77 }

mbusF7VIF24		OBJECT-TYPE
			SYNTAX	INTEGER
			ACCESS	read-only
			STATUS	current
	DESCRIPTION ""
			::= { mbusF7 78 }

mbusF7Value24		OBJECT-TYPE
			SYNTAX	INTEGER
			ACCESS	read-only
			STATUS	current
	DESCRIPTION ""
			::= { mbusF7 79 }

mbusF7VIF25		OBJECT-TYPE
			SYNTAX	INTEGER
			ACCESS	read-only
			STATUS	current
	DESCRIPTION ""
			::= { mbusF7 80 }

mbusF7Value25		OBJECT-TYPE
			SYNTAX	INTEGER
			ACCESS	read-only
			STATUS	current
	DESCRIPTION ""
			::= { mbusF7 81 }

mbusF7VIF26		OBJECT-TYPE
			SYNTAX	INTEGER
			ACCESS	read-only
			STATUS	current
	DESCRIPTION ""
			::= { mbusF7 82 }

mbusF7Value26		OBJECT-TYPE
			SYNTAX	INTEGER
			ACCESS	read-only
			STATUS	current
	DESCRIPTION ""
			::= { mbusF7 83 }

mbusF7VIF27		OBJECT-TYPE
			SYNTAX	INTEGER
			ACCESS	read-only
			STATUS	current
	DESCRIPTION ""
			::= { mbusF7 84 }

mbusF7Value27		OBJECT-TYPE
			SYNTAX	INTEGER
			ACCESS	read-only
			STATUS	current
	DESCRIPTION ""
			::= { mbusF7 85 }

mbusF7VIF28		OBJECT-TYPE
			SYNTAX	INTEGER
			ACCESS	read-only
			STATUS	current
	DESCRIPTION ""
			::= { mbusF7 86 }

mbusF7Value28		OBJECT-TYPE
			SYNTAX	INTEGER
			ACCESS	read-only
			STATUS	current
	DESCRIPTION ""
			::= { mbusF7 87 }

mbusF7VIF29		OBJECT-TYPE
			SYNTAX	INTEGER
			ACCESS	read-only
			STATUS	current
	DESCRIPTION ""
			::= { mbusF7 88 }

mbusF7Value29		OBJECT-TYPE
			SYNTAX	INTEGER
			ACCESS	read-only
			STATUS	current
	DESCRIPTION ""
			::= { mbusF7 89 }

mbusF7VIF2A		OBJECT-TYPE
			SYNTAX	INTEGER
			ACCESS	read-only
			STATUS	current
	DESCRIPTION ""
			::= { mbusF7 90 }

mbusF7Value2A		OBJECT-TYPE
			SYNTAX	INTEGER
			ACCESS	read-only
			STATUS	current
	DESCRIPTION ""
			::= { mbusF7 91 }

mbusF7VIF2B		OBJECT-TYPE
			SYNTAX	INTEGER
			ACCESS	read-only
			STATUS	current
	DESCRIPTION ""
			::= { mbusF7 92 }

mbusF7Value2B		OBJECT-TYPE
			SYNTAX	INTEGER
			ACCESS	read-only
			STATUS	current
	DESCRIPTION ""
			::= { mbusF7 93 }

mbusF7VIF2C		OBJECT-TYPE
			SYNTAX	INTEGER
			ACCESS	read-only
			STATUS	current
	DESCRIPTION ""
			::= { mbusF7 94 }

mbusF7Value2C		OBJECT-TYPE
			SYNTAX	INTEGER
			ACCESS	read-only
			STATUS	current
	DESCRIPTION ""
			::= { mbusF7 95 }

mbusF7VIF2D		OBJECT-TYPE
			SYNTAX	INTEGER
			ACCESS	read-only
			STATUS	current
	DESCRIPTION ""
			::= { mbusF7 96 }

mbusF7Value2D		OBJECT-TYPE
			SYNTAX	INTEGER
			ACCESS	read-only
			STATUS	current
	DESCRIPTION ""
			::= { mbusF7 97 }

mbusF7VIF2E		OBJECT-TYPE
			SYNTAX	INTEGER
			ACCESS	read-only
			STATUS	current
	DESCRIPTION ""
			::= { mbusF7 98 }

mbusF7Value2E		OBJECT-TYPE
			SYNTAX	INTEGER
			ACCESS	read-only
			STATUS	current
	DESCRIPTION ""
			::= { mbusF7 99 }

mbusF7VIF2F		OBJECT-TYPE
			SYNTAX	INTEGER
			ACCESS	read-only
			STATUS	current
	DESCRIPTION ""
			::= { mbusF7 100 }

mbusF7Value2F		OBJECT-TYPE
			SYNTAX	INTEGER
			ACCESS	read-only
			STATUS	current
	DESCRIPTION ""
			::= { mbusF7 101 }

mbusF8			OBJECT IDENTIFIER ::= { mbus 248 }

mbusF8IdNumber		OBJECT-TYPE
			SYNTAX	Gauge
			ACCESS	read-only
			STATUS	current
	DESCRIPTION ""
			::= { mbusF8 1 }

mbusF8Manufacturer	OBJECT-TYPE
			SYNTAX	Gauge
			ACCESS	read-only
			STATUS	current
	DESCRIPTION ""
			::= { mbusF8 2 }

mbusF8Version		OBJECT-TYPE
			SYNTAX	Gauge
			ACCESS	read-only
			STATUS	current
	DESCRIPTION ""
			::= { mbusF8 3 }

mbusF8Medium		OBJECT-TYPE
			SYNTAX	Gauge
			ACCESS	read-only
			STATUS	current
	DESCRIPTION ""
			::= { mbusF8 4 }

mbusF8Status		OBJECT-TYPE
			SYNTAX	Gauge
			ACCESS	read-only
			STATUS	current
	DESCRIPTION ""
			::= { mbusF8 5 }

mbusF8VIF00		OBJECT-TYPE
			SYNTAX	INTEGER
			ACCESS	read-only
			STATUS	current
	DESCRIPTION ""
			::= { mbusF8 6 }

mbusF8Value00		OBJECT-TYPE
			SYNTAX	INTEGER
			ACCESS	read-only
			STATUS	current
	DESCRIPTION ""
			::= { mbusF8 7 }

mbusF8VIF01		OBJECT-TYPE
			SYNTAX	INTEGER
			ACCESS	read-only
			STATUS	current
	DESCRIPTION ""
			::= { mbusF8 8 }

mbusF8Value01		OBJECT-TYPE
			SYNTAX	INTEGER
			ACCESS	read-only
			STATUS	current
	DESCRIPTION ""
			::= { mbusF8 9 }

mbusF8VIF02		OBJECT-TYPE
			SYNTAX	INTEGER
			ACCESS	read-only
			STATUS	current
	DESCRIPTION ""
			::= { mbusF8 10 }

mbusF8Value02		OBJECT-TYPE
			SYNTAX	INTEGER
			ACCESS	read-only
			STATUS	current
	DESCRIPTION ""
			::= { mbusF8 11 }

mbusF8VIF03		OBJECT-TYPE
			SYNTAX	INTEGER
			ACCESS	read-only
			STATUS	current
	DESCRIPTION ""
			::= { mbusF8 12 }

mbusF8Value03		OBJECT-TYPE
			SYNTAX	INTEGER
			ACCESS	read-only
			STATUS	current
	DESCRIPTION ""
			::= { mbusF8 13 }

mbusF8VIF04		OBJECT-TYPE
			SYNTAX	INTEGER
			ACCESS	read-only
			STATUS	current
	DESCRIPTION ""
			::= { mbusF8 14 }

mbusF8Value04		OBJECT-TYPE
			SYNTAX	INTEGER
			ACCESS	read-only
			STATUS	current
	DESCRIPTION ""
			::= { mbusF8 15 }

mbusF8VIF05		OBJECT-TYPE
			SYNTAX	INTEGER
			ACCESS	read-only
			STATUS	current
	DESCRIPTION ""
			::= { mbusF8 16 }

mbusF8Value05		OBJECT-TYPE
			SYNTAX	INTEGER
			ACCESS	read-only
			STATUS	current
	DESCRIPTION ""
			::= { mbusF8 17 }

mbusF8VIF06		OBJECT-TYPE
			SYNTAX	INTEGER
			ACCESS	read-only
			STATUS	current
	DESCRIPTION ""
			::= { mbusF8 18 }

mbusF8Value06		OBJECT-TYPE
			SYNTAX	INTEGER
			ACCESS	read-only
			STATUS	current
	DESCRIPTION ""
			::= { mbusF8 19 }

mbusF8VIF07		OBJECT-TYPE
			SYNTAX	INTEGER
			ACCESS	read-only
			STATUS	current
	DESCRIPTION ""
			::= { mbusF8 20 }

mbusF8Value07		OBJECT-TYPE
			SYNTAX	INTEGER
			ACCESS	read-only
			STATUS	current
	DESCRIPTION ""
			::= { mbusF8 21 }

mbusF8VIF08		OBJECT-TYPE
			SYNTAX	INTEGER
			ACCESS	read-only
			STATUS	current
	DESCRIPTION ""
			::= { mbusF8 22 }

mbusF8Value08		OBJECT-TYPE
			SYNTAX	INTEGER
			ACCESS	read-only
			STATUS	current
	DESCRIPTION ""
			::= { mbusF8 23 }

mbusF8VIF09		OBJECT-TYPE
			SYNTAX	INTEGER
			ACCESS	read-only
			STATUS	current
	DESCRIPTION ""
			::= { mbusF8 24 }

mbusF8Value09		OBJECT-TYPE
			SYNTAX	INTEGER
			ACCESS	read-only
			STATUS	current
	DESCRIPTION ""
			::= { mbusF8 25 }

mbusF8VIF0A		OBJECT-TYPE
			SYNTAX	INTEGER
			ACCESS	read-only
			STATUS	current
	DESCRIPTION ""
			::= { mbusF8 26 }

mbusF8Value0A		OBJECT-TYPE
			SYNTAX	INTEGER
			ACCESS	read-only
			STATUS	current
	DESCRIPTION ""
			::= { mbusF8 27 }

mbusF8VIF0B		OBJECT-TYPE
			SYNTAX	INTEGER
			ACCESS	read-only
			STATUS	current
	DESCRIPTION ""
			::= { mbusF8 28 }

mbusF8Value0B		OBJECT-TYPE
			SYNTAX	INTEGER
			ACCESS	read-only
			STATUS	current
	DESCRIPTION ""
			::= { mbusF8 29 }

mbusF8VIF0C		OBJECT-TYPE
			SYNTAX	INTEGER
			ACCESS	read-only
			STATUS	current
	DESCRIPTION ""
			::= { mbusF8 30 }

mbusF8Value0C		OBJECT-TYPE
			SYNTAX	INTEGER
			ACCESS	read-only
			STATUS	current
	DESCRIPTION ""
			::= { mbusF8 31 }

mbusF8VIF0D		OBJECT-TYPE
			SYNTAX	INTEGER
			ACCESS	read-only
			STATUS	current
	DESCRIPTION ""
			::= { mbusF8 32 }

mbusF8Value0D		OBJECT-TYPE
			SYNTAX	INTEGER
			ACCESS	read-only
			STATUS	current
	DESCRIPTION ""
			::= { mbusF8 33 }

mbusF8VIF0E		OBJECT-TYPE
			SYNTAX	INTEGER
			ACCESS	read-only
			STATUS	current
	DESCRIPTION ""
			::= { mbusF8 34 }

mbusF8Value0E		OBJECT-TYPE
			SYNTAX	INTEGER
			ACCESS	read-only
			STATUS	current
	DESCRIPTION ""
			::= { mbusF8 35 }

mbusF8VIF0F		OBJECT-TYPE
			SYNTAX	INTEGER
			ACCESS	read-only
			STATUS	current
	DESCRIPTION ""
			::= { mbusF8 36 }

mbusF8Value0F		OBJECT-TYPE
			SYNTAX	INTEGER
			ACCESS	read-only
			STATUS	current
	DESCRIPTION ""
			::= { mbusF8 37 }

mbusF8VIF10		OBJECT-TYPE
			SYNTAX	INTEGER
			ACCESS	read-only
			STATUS	current
	DESCRIPTION ""
			::= { mbusF8 38 }

mbusF8Value10		OBJECT-TYPE
			SYNTAX	INTEGER
			ACCESS	read-only
			STATUS	current
	DESCRIPTION ""
			::= { mbusF8 39 }

mbusF8VIF11		OBJECT-TYPE
			SYNTAX	INTEGER
			ACCESS	read-only
			STATUS	current
	DESCRIPTION ""
			::= { mbusF8 40 }

mbusF8Value11		OBJECT-TYPE
			SYNTAX	INTEGER
			ACCESS	read-only
			STATUS	current
	DESCRIPTION ""
			::= { mbusF8 41 }

mbusF8VIF12		OBJECT-TYPE
			SYNTAX	INTEGER
			ACCESS	read-only
			STATUS	current
	DESCRIPTION ""
			::= { mbusF8 42 }

mbusF8Value12		OBJECT-TYPE
			SYNTAX	INTEGER
			ACCESS	read-only
			STATUS	current
	DESCRIPTION ""
			::= { mbusF8 43 }

mbusF8VIF13		OBJECT-TYPE
			SYNTAX	INTEGER
			ACCESS	read-only
			STATUS	current
	DESCRIPTION ""
			::= { mbusF8 44 }

mbusF8Value13		OBJECT-TYPE
			SYNTAX	INTEGER
			ACCESS	read-only
			STATUS	current
	DESCRIPTION ""
			::= { mbusF8 45 }

mbusF8VIF14		OBJECT-TYPE
			SYNTAX	INTEGER
			ACCESS	read-only
			STATUS	current
	DESCRIPTION ""
			::= { mbusF8 46 }

mbusF8Value14		OBJECT-TYPE
			SYNTAX	INTEGER
			ACCESS	read-only
			STATUS	current
	DESCRIPTION ""
			::= { mbusF8 47 }

mbusF8VIF15		OBJECT-TYPE
			SYNTAX	INTEGER
			ACCESS	read-only
			STATUS	current
	DESCRIPTION ""
			::= { mbusF8 48 }

mbusF8Value15		OBJECT-TYPE
			SYNTAX	INTEGER
			ACCESS	read-only
			STATUS	current
	DESCRIPTION ""
			::= { mbusF8 49 }

mbusF8VIF16		OBJECT-TYPE
			SYNTAX	INTEGER
			ACCESS	read-only
			STATUS	current
	DESCRIPTION ""
			::= { mbusF8 50 }

mbusF8Value16		OBJECT-TYPE
			SYNTAX	INTEGER
			ACCESS	read-only
			STATUS	current
	DESCRIPTION ""
			::= { mbusF8 51 }

mbusF8VIF17		OBJECT-TYPE
			SYNTAX	INTEGER
			ACCESS	read-only
			STATUS	current
	DESCRIPTION ""
			::= { mbusF8 52 }

mbusF8Value17		OBJECT-TYPE
			SYNTAX	INTEGER
			ACCESS	read-only
			STATUS	current
	DESCRIPTION ""
			::= { mbusF8 53 }

mbusF8VIF18		OBJECT-TYPE
			SYNTAX	INTEGER
			ACCESS	read-only
			STATUS	current
	DESCRIPTION ""
			::= { mbusF8 54 }

mbusF8Value18		OBJECT-TYPE
			SYNTAX	INTEGER
			ACCESS	read-only
			STATUS	current
	DESCRIPTION ""
			::= { mbusF8 55 }

mbusF8VIF19		OBJECT-TYPE
			SYNTAX	INTEGER
			ACCESS	read-only
			STATUS	current
	DESCRIPTION ""
			::= { mbusF8 56 }

mbusF8Value19		OBJECT-TYPE
			SYNTAX	INTEGER
			ACCESS	read-only
			STATUS	current
	DESCRIPTION ""
			::= { mbusF8 57 }

mbusF8VIF1A		OBJECT-TYPE
			SYNTAX	INTEGER
			ACCESS	read-only
			STATUS	current
	DESCRIPTION ""
			::= { mbusF8 58 }

mbusF8Value1A		OBJECT-TYPE
			SYNTAX	INTEGER
			ACCESS	read-only
			STATUS	current
	DESCRIPTION ""
			::= { mbusF8 59 }

mbusF8VIF1B		OBJECT-TYPE
			SYNTAX	INTEGER
			ACCESS	read-only
			STATUS	current
	DESCRIPTION ""
			::= { mbusF8 60 }

mbusF8Value1B		OBJECT-TYPE
			SYNTAX	INTEGER
			ACCESS	read-only
			STATUS	current
	DESCRIPTION ""
			::= { mbusF8 61 }

mbusF8VIF1C		OBJECT-TYPE
			SYNTAX	INTEGER
			ACCESS	read-only
			STATUS	current
	DESCRIPTION ""
			::= { mbusF8 62 }

mbusF8Value1C		OBJECT-TYPE
			SYNTAX	INTEGER
			ACCESS	read-only
			STATUS	current
	DESCRIPTION ""
			::= { mbusF8 63 }

mbusF8VIF1D		OBJECT-TYPE
			SYNTAX	INTEGER
			ACCESS	read-only
			STATUS	current
	DESCRIPTION ""
			::= { mbusF8 64 }

mbusF8Value1D		OBJECT-TYPE
			SYNTAX	INTEGER
			ACCESS	read-only
			STATUS	current
	DESCRIPTION ""
			::= { mbusF8 65 }

mbusF8VIF1E		OBJECT-TYPE
			SYNTAX	INTEGER
			ACCESS	read-only
			STATUS	current
	DESCRIPTION ""
			::= { mbusF8 66 }

mbusF8Value1E		OBJECT-TYPE
			SYNTAX	INTEGER
			ACCESS	read-only
			STATUS	current
	DESCRIPTION ""
			::= { mbusF8 67 }

mbusF8VIF1F		OBJECT-TYPE
			SYNTAX	INTEGER
			ACCESS	read-only
			STATUS	current
	DESCRIPTION ""
			::= { mbusF8 68 }

mbusF8Value1F		OBJECT-TYPE
			SYNTAX	INTEGER
			ACCESS	read-only
			STATUS	current
	DESCRIPTION ""
			::= { mbusF8 69 }

mbusF8VIF20		OBJECT-TYPE
			SYNTAX	INTEGER
			ACCESS	read-only
			STATUS	current
	DESCRIPTION ""
			::= { mbusF8 70 }

mbusF8Value20		OBJECT-TYPE
			SYNTAX	INTEGER
			ACCESS	read-only
			STATUS	current
	DESCRIPTION ""
			::= { mbusF8 71 }

mbusF8VIF21		OBJECT-TYPE
			SYNTAX	INTEGER
			ACCESS	read-only
			STATUS	current
	DESCRIPTION ""
			::= { mbusF8 72 }

mbusF8Value21		OBJECT-TYPE
			SYNTAX	INTEGER
			ACCESS	read-only
			STATUS	current
	DESCRIPTION ""
			::= { mbusF8 73 }

mbusF8VIF22		OBJECT-TYPE
			SYNTAX	INTEGER
			ACCESS	read-only
			STATUS	current
	DESCRIPTION ""
			::= { mbusF8 74 }

mbusF8Value22		OBJECT-TYPE
			SYNTAX	INTEGER
			ACCESS	read-only
			STATUS	current
	DESCRIPTION ""
			::= { mbusF8 75 }

mbusF8VIF23		OBJECT-TYPE
			SYNTAX	INTEGER
			ACCESS	read-only
			STATUS	current
	DESCRIPTION ""
			::= { mbusF8 76 }

mbusF8Value23		OBJECT-TYPE
			SYNTAX	INTEGER
			ACCESS	read-only
			STATUS	current
	DESCRIPTION ""
			::= { mbusF8 77 }

mbusF8VIF24		OBJECT-TYPE
			SYNTAX	INTEGER
			ACCESS	read-only
			STATUS	current
	DESCRIPTION ""
			::= { mbusF8 78 }

mbusF8Value24		OBJECT-TYPE
			SYNTAX	INTEGER
			ACCESS	read-only
			STATUS	current
	DESCRIPTION ""
			::= { mbusF8 79 }

mbusF8VIF25		OBJECT-TYPE
			SYNTAX	INTEGER
			ACCESS	read-only
			STATUS	current
	DESCRIPTION ""
			::= { mbusF8 80 }

mbusF8Value25		OBJECT-TYPE
			SYNTAX	INTEGER
			ACCESS	read-only
			STATUS	current
	DESCRIPTION ""
			::= { mbusF8 81 }

mbusF8VIF26		OBJECT-TYPE
			SYNTAX	INTEGER
			ACCESS	read-only
			STATUS	current
	DESCRIPTION ""
			::= { mbusF8 82 }

mbusF8Value26		OBJECT-TYPE
			SYNTAX	INTEGER
			ACCESS	read-only
			STATUS	current
	DESCRIPTION ""
			::= { mbusF8 83 }

mbusF8VIF27		OBJECT-TYPE
			SYNTAX	INTEGER
			ACCESS	read-only
			STATUS	current
	DESCRIPTION ""
			::= { mbusF8 84 }

mbusF8Value27		OBJECT-TYPE
			SYNTAX	INTEGER
			ACCESS	read-only
			STATUS	current
	DESCRIPTION ""
			::= { mbusF8 85 }

mbusF8VIF28		OBJECT-TYPE
			SYNTAX	INTEGER
			ACCESS	read-only
			STATUS	current
	DESCRIPTION ""
			::= { mbusF8 86 }

mbusF8Value28		OBJECT-TYPE
			SYNTAX	INTEGER
			ACCESS	read-only
			STATUS	current
	DESCRIPTION ""
			::= { mbusF8 87 }

mbusF8VIF29		OBJECT-TYPE
			SYNTAX	INTEGER
			ACCESS	read-only
			STATUS	current
	DESCRIPTION ""
			::= { mbusF8 88 }

mbusF8Value29		OBJECT-TYPE
			SYNTAX	INTEGER
			ACCESS	read-only
			STATUS	current
	DESCRIPTION ""
			::= { mbusF8 89 }

mbusF8VIF2A		OBJECT-TYPE
			SYNTAX	INTEGER
			ACCESS	read-only
			STATUS	current
	DESCRIPTION ""
			::= { mbusF8 90 }

mbusF8Value2A		OBJECT-TYPE
			SYNTAX	INTEGER
			ACCESS	read-only
			STATUS	current
	DESCRIPTION ""
			::= { mbusF8 91 }

mbusF8VIF2B		OBJECT-TYPE
			SYNTAX	INTEGER
			ACCESS	read-only
			STATUS	current
	DESCRIPTION ""
			::= { mbusF8 92 }

mbusF8Value2B		OBJECT-TYPE
			SYNTAX	INTEGER
			ACCESS	read-only
			STATUS	current
	DESCRIPTION ""
			::= { mbusF8 93 }

mbusF8VIF2C		OBJECT-TYPE
			SYNTAX	INTEGER
			ACCESS	read-only
			STATUS	current
	DESCRIPTION ""
			::= { mbusF8 94 }

mbusF8Value2C		OBJECT-TYPE
			SYNTAX	INTEGER
			ACCESS	read-only
			STATUS	current
	DESCRIPTION ""
			::= { mbusF8 95 }

mbusF8VIF2D		OBJECT-TYPE
			SYNTAX	INTEGER
			ACCESS	read-only
			STATUS	current
	DESCRIPTION ""
			::= { mbusF8 96 }

mbusF8Value2D		OBJECT-TYPE
			SYNTAX	INTEGER
			ACCESS	read-only
			STATUS	current
	DESCRIPTION ""
			::= { mbusF8 97 }

mbusF8VIF2E		OBJECT-TYPE
			SYNTAX	INTEGER
			ACCESS	read-only
			STATUS	current
	DESCRIPTION ""
			::= { mbusF8 98 }

mbusF8Value2E		OBJECT-TYPE
			SYNTAX	INTEGER
			ACCESS	read-only
			STATUS	current
	DESCRIPTION ""
			::= { mbusF8 99 }

mbusF8VIF2F		OBJECT-TYPE
			SYNTAX	INTEGER
			ACCESS	read-only
			STATUS	current
	DESCRIPTION ""
			::= { mbusF8 100 }

mbusF8Value2F		OBJECT-TYPE
			SYNTAX	INTEGER
			ACCESS	read-only
			STATUS	current
	DESCRIPTION ""
			::= { mbusF8 101 }

mbusF9			OBJECT IDENTIFIER ::= { mbus 249 }

mbusF9IdNumber		OBJECT-TYPE
			SYNTAX	Gauge
			ACCESS	read-only
			STATUS	current
	DESCRIPTION ""
			::= { mbusF9 1 }

mbusF9Manufacturer	OBJECT-TYPE
			SYNTAX	Gauge
			ACCESS	read-only
			STATUS	current
	DESCRIPTION ""
			::= { mbusF9 2 }

mbusF9Version		OBJECT-TYPE
			SYNTAX	Gauge
			ACCESS	read-only
			STATUS	current
	DESCRIPTION ""
			::= { mbusF9 3 }

mbusF9Medium		OBJECT-TYPE
			SYNTAX	Gauge
			ACCESS	read-only
			STATUS	current
	DESCRIPTION ""
			::= { mbusF9 4 }

mbusF9Status		OBJECT-TYPE
			SYNTAX	Gauge
			ACCESS	read-only
			STATUS	current
	DESCRIPTION ""
			::= { mbusF9 5 }

mbusF9VIF00		OBJECT-TYPE
			SYNTAX	INTEGER
			ACCESS	read-only
			STATUS	current
	DESCRIPTION ""
			::= { mbusF9 6 }

mbusF9Value00		OBJECT-TYPE
			SYNTAX	INTEGER
			ACCESS	read-only
			STATUS	current
	DESCRIPTION ""
			::= { mbusF9 7 }

mbusF9VIF01		OBJECT-TYPE
			SYNTAX	INTEGER
			ACCESS	read-only
			STATUS	current
	DESCRIPTION ""
			::= { mbusF9 8 }

mbusF9Value01		OBJECT-TYPE
			SYNTAX	INTEGER
			ACCESS	read-only
			STATUS	current
	DESCRIPTION ""
			::= { mbusF9 9 }

mbusF9VIF02		OBJECT-TYPE
			SYNTAX	INTEGER
			ACCESS	read-only
			STATUS	current
	DESCRIPTION ""
			::= { mbusF9 10 }

mbusF9Value02		OBJECT-TYPE
			SYNTAX	INTEGER
			ACCESS	read-only
			STATUS	current
	DESCRIPTION ""
			::= { mbusF9 11 }

mbusF9VIF03		OBJECT-TYPE
			SYNTAX	INTEGER
			ACCESS	read-only
			STATUS	current
	DESCRIPTION ""
			::= { mbusF9 12 }

mbusF9Value03		OBJECT-TYPE
			SYNTAX	INTEGER
			ACCESS	read-only
			STATUS	current
	DESCRIPTION ""
			::= { mbusF9 13 }

mbusF9VIF04		OBJECT-TYPE
			SYNTAX	INTEGER
			ACCESS	read-only
			STATUS	current
	DESCRIPTION ""
			::= { mbusF9 14 }

mbusF9Value04		OBJECT-TYPE
			SYNTAX	INTEGER
			ACCESS	read-only
			STATUS	current
	DESCRIPTION ""
			::= { mbusF9 15 }

mbusF9VIF05		OBJECT-TYPE
			SYNTAX	INTEGER
			ACCESS	read-only
			STATUS	current
	DESCRIPTION ""
			::= { mbusF9 16 }

mbusF9Value05		OBJECT-TYPE
			SYNTAX	INTEGER
			ACCESS	read-only
			STATUS	current
	DESCRIPTION ""
			::= { mbusF9 17 }

mbusF9VIF06		OBJECT-TYPE
			SYNTAX	INTEGER
			ACCESS	read-only
			STATUS	current
	DESCRIPTION ""
			::= { mbusF9 18 }

mbusF9Value06		OBJECT-TYPE
			SYNTAX	INTEGER
			ACCESS	read-only
			STATUS	current
	DESCRIPTION ""
			::= { mbusF9 19 }

mbusF9VIF07		OBJECT-TYPE
			SYNTAX	INTEGER
			ACCESS	read-only
			STATUS	current
	DESCRIPTION ""
			::= { mbusF9 20 }

mbusF9Value07		OBJECT-TYPE
			SYNTAX	INTEGER
			ACCESS	read-only
			STATUS	current
	DESCRIPTION ""
			::= { mbusF9 21 }

mbusF9VIF08		OBJECT-TYPE
			SYNTAX	INTEGER
			ACCESS	read-only
			STATUS	current
	DESCRIPTION ""
			::= { mbusF9 22 }

mbusF9Value08		OBJECT-TYPE
			SYNTAX	INTEGER
			ACCESS	read-only
			STATUS	current
	DESCRIPTION ""
			::= { mbusF9 23 }

mbusF9VIF09		OBJECT-TYPE
			SYNTAX	INTEGER
			ACCESS	read-only
			STATUS	current
	DESCRIPTION ""
			::= { mbusF9 24 }

mbusF9Value09		OBJECT-TYPE
			SYNTAX	INTEGER
			ACCESS	read-only
			STATUS	current
	DESCRIPTION ""
			::= { mbusF9 25 }

mbusF9VIF0A		OBJECT-TYPE
			SYNTAX	INTEGER
			ACCESS	read-only
			STATUS	current
	DESCRIPTION ""
			::= { mbusF9 26 }

mbusF9Value0A		OBJECT-TYPE
			SYNTAX	INTEGER
			ACCESS	read-only
			STATUS	current
	DESCRIPTION ""
			::= { mbusF9 27 }

mbusF9VIF0B		OBJECT-TYPE
			SYNTAX	INTEGER
			ACCESS	read-only
			STATUS	current
	DESCRIPTION ""
			::= { mbusF9 28 }

mbusF9Value0B		OBJECT-TYPE
			SYNTAX	INTEGER
			ACCESS	read-only
			STATUS	current
	DESCRIPTION ""
			::= { mbusF9 29 }

mbusF9VIF0C		OBJECT-TYPE
			SYNTAX	INTEGER
			ACCESS	read-only
			STATUS	current
	DESCRIPTION ""
			::= { mbusF9 30 }

mbusF9Value0C		OBJECT-TYPE
			SYNTAX	INTEGER
			ACCESS	read-only
			STATUS	current
	DESCRIPTION ""
			::= { mbusF9 31 }

mbusF9VIF0D		OBJECT-TYPE
			SYNTAX	INTEGER
			ACCESS	read-only
			STATUS	current
	DESCRIPTION ""
			::= { mbusF9 32 }

mbusF9Value0D		OBJECT-TYPE
			SYNTAX	INTEGER
			ACCESS	read-only
			STATUS	current
	DESCRIPTION ""
			::= { mbusF9 33 }

mbusF9VIF0E		OBJECT-TYPE
			SYNTAX	INTEGER
			ACCESS	read-only
			STATUS	current
	DESCRIPTION ""
			::= { mbusF9 34 }

mbusF9Value0E		OBJECT-TYPE
			SYNTAX	INTEGER
			ACCESS	read-only
			STATUS	current
	DESCRIPTION ""
			::= { mbusF9 35 }

mbusF9VIF0F		OBJECT-TYPE
			SYNTAX	INTEGER
			ACCESS	read-only
			STATUS	current
	DESCRIPTION ""
			::= { mbusF9 36 }

mbusF9Value0F		OBJECT-TYPE
			SYNTAX	INTEGER
			ACCESS	read-only
			STATUS	current
	DESCRIPTION ""
			::= { mbusF9 37 }

mbusF9VIF10		OBJECT-TYPE
			SYNTAX	INTEGER
			ACCESS	read-only
			STATUS	current
	DESCRIPTION ""
			::= { mbusF9 38 }

mbusF9Value10		OBJECT-TYPE
			SYNTAX	INTEGER
			ACCESS	read-only
			STATUS	current
	DESCRIPTION ""
			::= { mbusF9 39 }

mbusF9VIF11		OBJECT-TYPE
			SYNTAX	INTEGER
			ACCESS	read-only
			STATUS	current
	DESCRIPTION ""
			::= { mbusF9 40 }

mbusF9Value11		OBJECT-TYPE
			SYNTAX	INTEGER
			ACCESS	read-only
			STATUS	current
	DESCRIPTION ""
			::= { mbusF9 41 }

mbusF9VIF12		OBJECT-TYPE
			SYNTAX	INTEGER
			ACCESS	read-only
			STATUS	current
	DESCRIPTION ""
			::= { mbusF9 42 }

mbusF9Value12		OBJECT-TYPE
			SYNTAX	INTEGER
			ACCESS	read-only
			STATUS	current
	DESCRIPTION ""
			::= { mbusF9 43 }

mbusF9VIF13		OBJECT-TYPE
			SYNTAX	INTEGER
			ACCESS	read-only
			STATUS	current
	DESCRIPTION ""
			::= { mbusF9 44 }

mbusF9Value13		OBJECT-TYPE
			SYNTAX	INTEGER
			ACCESS	read-only
			STATUS	current
	DESCRIPTION ""
			::= { mbusF9 45 }

mbusF9VIF14		OBJECT-TYPE
			SYNTAX	INTEGER
			ACCESS	read-only
			STATUS	current
	DESCRIPTION ""
			::= { mbusF9 46 }

mbusF9Value14		OBJECT-TYPE
			SYNTAX	INTEGER
			ACCESS	read-only
			STATUS	current
	DESCRIPTION ""
			::= { mbusF9 47 }

mbusF9VIF15		OBJECT-TYPE
			SYNTAX	INTEGER
			ACCESS	read-only
			STATUS	current
	DESCRIPTION ""
			::= { mbusF9 48 }

mbusF9Value15		OBJECT-TYPE
			SYNTAX	INTEGER
			ACCESS	read-only
			STATUS	current
	DESCRIPTION ""
			::= { mbusF9 49 }

mbusF9VIF16		OBJECT-TYPE
			SYNTAX	INTEGER
			ACCESS	read-only
			STATUS	current
	DESCRIPTION ""
			::= { mbusF9 50 }

mbusF9Value16		OBJECT-TYPE
			SYNTAX	INTEGER
			ACCESS	read-only
			STATUS	current
	DESCRIPTION ""
			::= { mbusF9 51 }

mbusF9VIF17		OBJECT-TYPE
			SYNTAX	INTEGER
			ACCESS	read-only
			STATUS	current
	DESCRIPTION ""
			::= { mbusF9 52 }

mbusF9Value17		OBJECT-TYPE
			SYNTAX	INTEGER
			ACCESS	read-only
			STATUS	current
	DESCRIPTION ""
			::= { mbusF9 53 }

mbusF9VIF18		OBJECT-TYPE
			SYNTAX	INTEGER
			ACCESS	read-only
			STATUS	current
	DESCRIPTION ""
			::= { mbusF9 54 }

mbusF9Value18		OBJECT-TYPE
			SYNTAX	INTEGER
			ACCESS	read-only
			STATUS	current
	DESCRIPTION ""
			::= { mbusF9 55 }

mbusF9VIF19		OBJECT-TYPE
			SYNTAX	INTEGER
			ACCESS	read-only
			STATUS	current
	DESCRIPTION ""
			::= { mbusF9 56 }

mbusF9Value19		OBJECT-TYPE
			SYNTAX	INTEGER
			ACCESS	read-only
			STATUS	current
	DESCRIPTION ""
			::= { mbusF9 57 }

mbusF9VIF1A		OBJECT-TYPE
			SYNTAX	INTEGER
			ACCESS	read-only
			STATUS	current
	DESCRIPTION ""
			::= { mbusF9 58 }

mbusF9Value1A		OBJECT-TYPE
			SYNTAX	INTEGER
			ACCESS	read-only
			STATUS	current
	DESCRIPTION ""
			::= { mbusF9 59 }

mbusF9VIF1B		OBJECT-TYPE
			SYNTAX	INTEGER
			ACCESS	read-only
			STATUS	current
	DESCRIPTION ""
			::= { mbusF9 60 }

mbusF9Value1B		OBJECT-TYPE
			SYNTAX	INTEGER
			ACCESS	read-only
			STATUS	current
	DESCRIPTION ""
			::= { mbusF9 61 }

mbusF9VIF1C		OBJECT-TYPE
			SYNTAX	INTEGER
			ACCESS	read-only
			STATUS	current
	DESCRIPTION ""
			::= { mbusF9 62 }

mbusF9Value1C		OBJECT-TYPE
			SYNTAX	INTEGER
			ACCESS	read-only
			STATUS	current
	DESCRIPTION ""
			::= { mbusF9 63 }

mbusF9VIF1D		OBJECT-TYPE
			SYNTAX	INTEGER
			ACCESS	read-only
			STATUS	current
	DESCRIPTION ""
			::= { mbusF9 64 }

mbusF9Value1D		OBJECT-TYPE
			SYNTAX	INTEGER
			ACCESS	read-only
			STATUS	current
	DESCRIPTION ""
			::= { mbusF9 65 }

mbusF9VIF1E		OBJECT-TYPE
			SYNTAX	INTEGER
			ACCESS	read-only
			STATUS	current
	DESCRIPTION ""
			::= { mbusF9 66 }

mbusF9Value1E		OBJECT-TYPE
			SYNTAX	INTEGER
			ACCESS	read-only
			STATUS	current
	DESCRIPTION ""
			::= { mbusF9 67 }

mbusF9VIF1F		OBJECT-TYPE
			SYNTAX	INTEGER
			ACCESS	read-only
			STATUS	current
	DESCRIPTION ""
			::= { mbusF9 68 }

mbusF9Value1F		OBJECT-TYPE
			SYNTAX	INTEGER
			ACCESS	read-only
			STATUS	current
	DESCRIPTION ""
			::= { mbusF9 69 }

mbusF9VIF20		OBJECT-TYPE
			SYNTAX	INTEGER
			ACCESS	read-only
			STATUS	current
	DESCRIPTION ""
			::= { mbusF9 70 }

mbusF9Value20		OBJECT-TYPE
			SYNTAX	INTEGER
			ACCESS	read-only
			STATUS	current
	DESCRIPTION ""
			::= { mbusF9 71 }

mbusF9VIF21		OBJECT-TYPE
			SYNTAX	INTEGER
			ACCESS	read-only
			STATUS	current
	DESCRIPTION ""
			::= { mbusF9 72 }

mbusF9Value21		OBJECT-TYPE
			SYNTAX	INTEGER
			ACCESS	read-only
			STATUS	current
	DESCRIPTION ""
			::= { mbusF9 73 }

mbusF9VIF22		OBJECT-TYPE
			SYNTAX	INTEGER
			ACCESS	read-only
			STATUS	current
	DESCRIPTION ""
			::= { mbusF9 74 }

mbusF9Value22		OBJECT-TYPE
			SYNTAX	INTEGER
			ACCESS	read-only
			STATUS	current
	DESCRIPTION ""
			::= { mbusF9 75 }

mbusF9VIF23		OBJECT-TYPE
			SYNTAX	INTEGER
			ACCESS	read-only
			STATUS	current
	DESCRIPTION ""
			::= { mbusF9 76 }

mbusF9Value23		OBJECT-TYPE
			SYNTAX	INTEGER
			ACCESS	read-only
			STATUS	current
	DESCRIPTION ""
			::= { mbusF9 77 }

mbusF9VIF24		OBJECT-TYPE
			SYNTAX	INTEGER
			ACCESS	read-only
			STATUS	current
	DESCRIPTION ""
			::= { mbusF9 78 }

mbusF9Value24		OBJECT-TYPE
			SYNTAX	INTEGER
			ACCESS	read-only
			STATUS	current
	DESCRIPTION ""
			::= { mbusF9 79 }

mbusF9VIF25		OBJECT-TYPE
			SYNTAX	INTEGER
			ACCESS	read-only
			STATUS	current
	DESCRIPTION ""
			::= { mbusF9 80 }

mbusF9Value25		OBJECT-TYPE
			SYNTAX	INTEGER
			ACCESS	read-only
			STATUS	current
	DESCRIPTION ""
			::= { mbusF9 81 }

mbusF9VIF26		OBJECT-TYPE
			SYNTAX	INTEGER
			ACCESS	read-only
			STATUS	current
	DESCRIPTION ""
			::= { mbusF9 82 }

mbusF9Value26		OBJECT-TYPE
			SYNTAX	INTEGER
			ACCESS	read-only
			STATUS	current
	DESCRIPTION ""
			::= { mbusF9 83 }

mbusF9VIF27		OBJECT-TYPE
			SYNTAX	INTEGER
			ACCESS	read-only
			STATUS	current
	DESCRIPTION ""
			::= { mbusF9 84 }

mbusF9Value27		OBJECT-TYPE
			SYNTAX	INTEGER
			ACCESS	read-only
			STATUS	current
	DESCRIPTION ""
			::= { mbusF9 85 }

mbusF9VIF28		OBJECT-TYPE
			SYNTAX	INTEGER
			ACCESS	read-only
			STATUS	current
	DESCRIPTION ""
			::= { mbusF9 86 }

mbusF9Value28		OBJECT-TYPE
			SYNTAX	INTEGER
			ACCESS	read-only
			STATUS	current
	DESCRIPTION ""
			::= { mbusF9 87 }

mbusF9VIF29		OBJECT-TYPE
			SYNTAX	INTEGER
			ACCESS	read-only
			STATUS	current
	DESCRIPTION ""
			::= { mbusF9 88 }

mbusF9Value29		OBJECT-TYPE
			SYNTAX	INTEGER
			ACCESS	read-only
			STATUS	current
	DESCRIPTION ""
			::= { mbusF9 89 }

mbusF9VIF2A		OBJECT-TYPE
			SYNTAX	INTEGER
			ACCESS	read-only
			STATUS	current
	DESCRIPTION ""
			::= { mbusF9 90 }

mbusF9Value2A		OBJECT-TYPE
			SYNTAX	INTEGER
			ACCESS	read-only
			STATUS	current
	DESCRIPTION ""
			::= { mbusF9 91 }

mbusF9VIF2B		OBJECT-TYPE
			SYNTAX	INTEGER
			ACCESS	read-only
			STATUS	current
	DESCRIPTION ""
			::= { mbusF9 92 }

mbusF9Value2B		OBJECT-TYPE
			SYNTAX	INTEGER
			ACCESS	read-only
			STATUS	current
	DESCRIPTION ""
			::= { mbusF9 93 }

mbusF9VIF2C		OBJECT-TYPE
			SYNTAX	INTEGER
			ACCESS	read-only
			STATUS	current
	DESCRIPTION ""
			::= { mbusF9 94 }

mbusF9Value2C		OBJECT-TYPE
			SYNTAX	INTEGER
			ACCESS	read-only
			STATUS	current
	DESCRIPTION ""
			::= { mbusF9 95 }

mbusF9VIF2D		OBJECT-TYPE
			SYNTAX	INTEGER
			ACCESS	read-only
			STATUS	current
	DESCRIPTION ""
			::= { mbusF9 96 }

mbusF9Value2D		OBJECT-TYPE
			SYNTAX	INTEGER
			ACCESS	read-only
			STATUS	current
	DESCRIPTION ""
			::= { mbusF9 97 }

mbusF9VIF2E		OBJECT-TYPE
			SYNTAX	INTEGER
			ACCESS	read-only
			STATUS	current
	DESCRIPTION ""
			::= { mbusF9 98 }

mbusF9Value2E		OBJECT-TYPE
			SYNTAX	INTEGER
			ACCESS	read-only
			STATUS	current
	DESCRIPTION ""
			::= { mbusF9 99 }

mbusF9VIF2F		OBJECT-TYPE
			SYNTAX	INTEGER
			ACCESS	read-only
			STATUS	current
	DESCRIPTION ""
			::= { mbusF9 100 }

mbusF9Value2F		OBJECT-TYPE
			SYNTAX	INTEGER
			ACCESS	read-only
			STATUS	current
	DESCRIPTION ""
			::= { mbusF9 101 }

mbusFA			OBJECT IDENTIFIER ::= { mbus 250 }

mbusFAIdNumber		OBJECT-TYPE
			SYNTAX	Gauge
			ACCESS	read-only
			STATUS	current
	DESCRIPTION ""
			::= { mbusFA 1 }

mbusFAManufacturer	OBJECT-TYPE
			SYNTAX	Gauge
			ACCESS	read-only
			STATUS	current
	DESCRIPTION ""
			::= { mbusFA 2 }

mbusFAVersion		OBJECT-TYPE
			SYNTAX	Gauge
			ACCESS	read-only
			STATUS	current
	DESCRIPTION ""
			::= { mbusFA 3 }

mbusFAMedium		OBJECT-TYPE
			SYNTAX	Gauge
			ACCESS	read-only
			STATUS	current
	DESCRIPTION ""
			::= { mbusFA 4 }

mbusFAStatus		OBJECT-TYPE
			SYNTAX	Gauge
			ACCESS	read-only
			STATUS	current
	DESCRIPTION ""
			::= { mbusFA 5 }

mbusFAVIF00		OBJECT-TYPE
			SYNTAX	INTEGER
			ACCESS	read-only
			STATUS	current
	DESCRIPTION ""
			::= { mbusFA 6 }

mbusFAValue00		OBJECT-TYPE
			SYNTAX	INTEGER
			ACCESS	read-only
			STATUS	current
	DESCRIPTION ""
			::= { mbusFA 7 }

mbusFAVIF01		OBJECT-TYPE
			SYNTAX	INTEGER
			ACCESS	read-only
			STATUS	current
	DESCRIPTION ""
			::= { mbusFA 8 }

mbusFAValue01		OBJECT-TYPE
			SYNTAX	INTEGER
			ACCESS	read-only
			STATUS	current
	DESCRIPTION ""
			::= { mbusFA 9 }

mbusFAVIF02		OBJECT-TYPE
			SYNTAX	INTEGER
			ACCESS	read-only
			STATUS	current
	DESCRIPTION ""
			::= { mbusFA 10 }

mbusFAValue02		OBJECT-TYPE
			SYNTAX	INTEGER
			ACCESS	read-only
			STATUS	current
	DESCRIPTION ""
			::= { mbusFA 11 }

mbusFAVIF03		OBJECT-TYPE
			SYNTAX	INTEGER
			ACCESS	read-only
			STATUS	current
	DESCRIPTION ""
			::= { mbusFA 12 }

mbusFAValue03		OBJECT-TYPE
			SYNTAX	INTEGER
			ACCESS	read-only
			STATUS	current
	DESCRIPTION ""
			::= { mbusFA 13 }

mbusFAVIF04		OBJECT-TYPE
			SYNTAX	INTEGER
			ACCESS	read-only
			STATUS	current
	DESCRIPTION ""
			::= { mbusFA 14 }

mbusFAValue04		OBJECT-TYPE
			SYNTAX	INTEGER
			ACCESS	read-only
			STATUS	current
	DESCRIPTION ""
			::= { mbusFA 15 }

mbusFAVIF05		OBJECT-TYPE
			SYNTAX	INTEGER
			ACCESS	read-only
			STATUS	current
	DESCRIPTION ""
			::= { mbusFA 16 }

mbusFAValue05		OBJECT-TYPE
			SYNTAX	INTEGER
			ACCESS	read-only
			STATUS	current
	DESCRIPTION ""
			::= { mbusFA 17 }

mbusFAVIF06		OBJECT-TYPE
			SYNTAX	INTEGER
			ACCESS	read-only
			STATUS	current
	DESCRIPTION ""
			::= { mbusFA 18 }

mbusFAValue06		OBJECT-TYPE
			SYNTAX	INTEGER
			ACCESS	read-only
			STATUS	current
	DESCRIPTION ""
			::= { mbusFA 19 }

mbusFAVIF07		OBJECT-TYPE
			SYNTAX	INTEGER
			ACCESS	read-only
			STATUS	current
	DESCRIPTION ""
			::= { mbusFA 20 }

mbusFAValue07		OBJECT-TYPE
			SYNTAX	INTEGER
			ACCESS	read-only
			STATUS	current
	DESCRIPTION ""
			::= { mbusFA 21 }

mbusFAVIF08		OBJECT-TYPE
			SYNTAX	INTEGER
			ACCESS	read-only
			STATUS	current
	DESCRIPTION ""
			::= { mbusFA 22 }

mbusFAValue08		OBJECT-TYPE
			SYNTAX	INTEGER
			ACCESS	read-only
			STATUS	current
	DESCRIPTION ""
			::= { mbusFA 23 }

mbusFAVIF09		OBJECT-TYPE
			SYNTAX	INTEGER
			ACCESS	read-only
			STATUS	current
	DESCRIPTION ""
			::= { mbusFA 24 }

mbusFAValue09		OBJECT-TYPE
			SYNTAX	INTEGER
			ACCESS	read-only
			STATUS	current
	DESCRIPTION ""
			::= { mbusFA 25 }

mbusFAVIF0A		OBJECT-TYPE
			SYNTAX	INTEGER
			ACCESS	read-only
			STATUS	current
	DESCRIPTION ""
			::= { mbusFA 26 }

mbusFAValue0A		OBJECT-TYPE
			SYNTAX	INTEGER
			ACCESS	read-only
			STATUS	current
	DESCRIPTION ""
			::= { mbusFA 27 }

mbusFAVIF0B		OBJECT-TYPE
			SYNTAX	INTEGER
			ACCESS	read-only
			STATUS	current
	DESCRIPTION ""
			::= { mbusFA 28 }

mbusFAValue0B		OBJECT-TYPE
			SYNTAX	INTEGER
			ACCESS	read-only
			STATUS	current
	DESCRIPTION ""
			::= { mbusFA 29 }

mbusFAVIF0C		OBJECT-TYPE
			SYNTAX	INTEGER
			ACCESS	read-only
			STATUS	current
	DESCRIPTION ""
			::= { mbusFA 30 }

mbusFAValue0C		OBJECT-TYPE
			SYNTAX	INTEGER
			ACCESS	read-only
			STATUS	current
	DESCRIPTION ""
			::= { mbusFA 31 }

mbusFAVIF0D		OBJECT-TYPE
			SYNTAX	INTEGER
			ACCESS	read-only
			STATUS	current
	DESCRIPTION ""
			::= { mbusFA 32 }

mbusFAValue0D		OBJECT-TYPE
			SYNTAX	INTEGER
			ACCESS	read-only
			STATUS	current
	DESCRIPTION ""
			::= { mbusFA 33 }

mbusFAVIF0E		OBJECT-TYPE
			SYNTAX	INTEGER
			ACCESS	read-only
			STATUS	current
	DESCRIPTION ""
			::= { mbusFA 34 }

mbusFAValue0E		OBJECT-TYPE
			SYNTAX	INTEGER
			ACCESS	read-only
			STATUS	current
	DESCRIPTION ""
			::= { mbusFA 35 }

mbusFAVIF0F		OBJECT-TYPE
			SYNTAX	INTEGER
			ACCESS	read-only
			STATUS	current
	DESCRIPTION ""
			::= { mbusFA 36 }

mbusFAValue0F		OBJECT-TYPE
			SYNTAX	INTEGER
			ACCESS	read-only
			STATUS	current
	DESCRIPTION ""
			::= { mbusFA 37 }

mbusFAVIF10		OBJECT-TYPE
			SYNTAX	INTEGER
			ACCESS	read-only
			STATUS	current
	DESCRIPTION ""
			::= { mbusFA 38 }

mbusFAValue10		OBJECT-TYPE
			SYNTAX	INTEGER
			ACCESS	read-only
			STATUS	current
	DESCRIPTION ""
			::= { mbusFA 39 }

mbusFAVIF11		OBJECT-TYPE
			SYNTAX	INTEGER
			ACCESS	read-only
			STATUS	current
	DESCRIPTION ""
			::= { mbusFA 40 }

mbusFAValue11		OBJECT-TYPE
			SYNTAX	INTEGER
			ACCESS	read-only
			STATUS	current
	DESCRIPTION ""
			::= { mbusFA 41 }

mbusFAVIF12		OBJECT-TYPE
			SYNTAX	INTEGER
			ACCESS	read-only
			STATUS	current
	DESCRIPTION ""
			::= { mbusFA 42 }

mbusFAValue12		OBJECT-TYPE
			SYNTAX	INTEGER
			ACCESS	read-only
			STATUS	current
	DESCRIPTION ""
			::= { mbusFA 43 }

mbusFAVIF13		OBJECT-TYPE
			SYNTAX	INTEGER
			ACCESS	read-only
			STATUS	current
	DESCRIPTION ""
			::= { mbusFA 44 }

mbusFAValue13		OBJECT-TYPE
			SYNTAX	INTEGER
			ACCESS	read-only
			STATUS	current
	DESCRIPTION ""
			::= { mbusFA 45 }

mbusFAVIF14		OBJECT-TYPE
			SYNTAX	INTEGER
			ACCESS	read-only
			STATUS	current
	DESCRIPTION ""
			::= { mbusFA 46 }

mbusFAValue14		OBJECT-TYPE
			SYNTAX	INTEGER
			ACCESS	read-only
			STATUS	current
	DESCRIPTION ""
			::= { mbusFA 47 }

mbusFAVIF15		OBJECT-TYPE
			SYNTAX	INTEGER
			ACCESS	read-only
			STATUS	current
	DESCRIPTION ""
			::= { mbusFA 48 }

mbusFAValue15		OBJECT-TYPE
			SYNTAX	INTEGER
			ACCESS	read-only
			STATUS	current
	DESCRIPTION ""
			::= { mbusFA 49 }

mbusFAVIF16		OBJECT-TYPE
			SYNTAX	INTEGER
			ACCESS	read-only
			STATUS	current
	DESCRIPTION ""
			::= { mbusFA 50 }

mbusFAValue16		OBJECT-TYPE
			SYNTAX	INTEGER
			ACCESS	read-only
			STATUS	current
	DESCRIPTION ""
			::= { mbusFA 51 }

mbusFAVIF17		OBJECT-TYPE
			SYNTAX	INTEGER
			ACCESS	read-only
			STATUS	current
	DESCRIPTION ""
			::= { mbusFA 52 }

mbusFAValue17		OBJECT-TYPE
			SYNTAX	INTEGER
			ACCESS	read-only
			STATUS	current
	DESCRIPTION ""
			::= { mbusFA 53 }

mbusFAVIF18		OBJECT-TYPE
			SYNTAX	INTEGER
			ACCESS	read-only
			STATUS	current
	DESCRIPTION ""
			::= { mbusFA 54 }

mbusFAValue18		OBJECT-TYPE
			SYNTAX	INTEGER
			ACCESS	read-only
			STATUS	current
	DESCRIPTION ""
			::= { mbusFA 55 }

mbusFAVIF19		OBJECT-TYPE
			SYNTAX	INTEGER
			ACCESS	read-only
			STATUS	current
	DESCRIPTION ""
			::= { mbusFA 56 }

mbusFAValue19		OBJECT-TYPE
			SYNTAX	INTEGER
			ACCESS	read-only
			STATUS	current
	DESCRIPTION ""
			::= { mbusFA 57 }

mbusFAVIF1A		OBJECT-TYPE
			SYNTAX	INTEGER
			ACCESS	read-only
			STATUS	current
	DESCRIPTION ""
			::= { mbusFA 58 }

mbusFAValue1A		OBJECT-TYPE
			SYNTAX	INTEGER
			ACCESS	read-only
			STATUS	current
	DESCRIPTION ""
			::= { mbusFA 59 }

mbusFAVIF1B		OBJECT-TYPE
			SYNTAX	INTEGER
			ACCESS	read-only
			STATUS	current
	DESCRIPTION ""
			::= { mbusFA 60 }

mbusFAValue1B		OBJECT-TYPE
			SYNTAX	INTEGER
			ACCESS	read-only
			STATUS	current
	DESCRIPTION ""
			::= { mbusFA 61 }

mbusFAVIF1C		OBJECT-TYPE
			SYNTAX	INTEGER
			ACCESS	read-only
			STATUS	current
	DESCRIPTION ""
			::= { mbusFA 62 }

mbusFAValue1C		OBJECT-TYPE
			SYNTAX	INTEGER
			ACCESS	read-only
			STATUS	current
	DESCRIPTION ""
			::= { mbusFA 63 }

mbusFAVIF1D		OBJECT-TYPE
			SYNTAX	INTEGER
			ACCESS	read-only
			STATUS	current
	DESCRIPTION ""
			::= { mbusFA 64 }

mbusFAValue1D		OBJECT-TYPE
			SYNTAX	INTEGER
			ACCESS	read-only
			STATUS	current
	DESCRIPTION ""
			::= { mbusFA 65 }

mbusFAVIF1E		OBJECT-TYPE
			SYNTAX	INTEGER
			ACCESS	read-only
			STATUS	current
	DESCRIPTION ""
			::= { mbusFA 66 }

mbusFAValue1E		OBJECT-TYPE
			SYNTAX	INTEGER
			ACCESS	read-only
			STATUS	current
	DESCRIPTION ""
			::= { mbusFA 67 }

mbusFAVIF1F		OBJECT-TYPE
			SYNTAX	INTEGER
			ACCESS	read-only
			STATUS	current
	DESCRIPTION ""
			::= { mbusFA 68 }

mbusFAValue1F		OBJECT-TYPE
			SYNTAX	INTEGER
			ACCESS	read-only
			STATUS	current
	DESCRIPTION ""
			::= { mbusFA 69 }

mbusFAVIF20		OBJECT-TYPE
			SYNTAX	INTEGER
			ACCESS	read-only
			STATUS	current
	DESCRIPTION ""
			::= { mbusFA 70 }

mbusFAValue20		OBJECT-TYPE
			SYNTAX	INTEGER
			ACCESS	read-only
			STATUS	current
	DESCRIPTION ""
			::= { mbusFA 71 }

mbusFAVIF21		OBJECT-TYPE
			SYNTAX	INTEGER
			ACCESS	read-only
			STATUS	current
	DESCRIPTION ""
			::= { mbusFA 72 }

mbusFAValue21		OBJECT-TYPE
			SYNTAX	INTEGER
			ACCESS	read-only
			STATUS	current
	DESCRIPTION ""
			::= { mbusFA 73 }

mbusFAVIF22		OBJECT-TYPE
			SYNTAX	INTEGER
			ACCESS	read-only
			STATUS	current
	DESCRIPTION ""
			::= { mbusFA 74 }

mbusFAValue22		OBJECT-TYPE
			SYNTAX	INTEGER
			ACCESS	read-only
			STATUS	current
	DESCRIPTION ""
			::= { mbusFA 75 }

mbusFAVIF23		OBJECT-TYPE
			SYNTAX	INTEGER
			ACCESS	read-only
			STATUS	current
	DESCRIPTION ""
			::= { mbusFA 76 }

mbusFAValue23		OBJECT-TYPE
			SYNTAX	INTEGER
			ACCESS	read-only
			STATUS	current
	DESCRIPTION ""
			::= { mbusFA 77 }

mbusFAVIF24		OBJECT-TYPE
			SYNTAX	INTEGER
			ACCESS	read-only
			STATUS	current
	DESCRIPTION ""
			::= { mbusFA 78 }

mbusFAValue24		OBJECT-TYPE
			SYNTAX	INTEGER
			ACCESS	read-only
			STATUS	current
	DESCRIPTION ""
			::= { mbusFA 79 }

mbusFAVIF25		OBJECT-TYPE
			SYNTAX	INTEGER
			ACCESS	read-only
			STATUS	current
	DESCRIPTION ""
			::= { mbusFA 80 }

mbusFAValue25		OBJECT-TYPE
			SYNTAX	INTEGER
			ACCESS	read-only
			STATUS	current
	DESCRIPTION ""
			::= { mbusFA 81 }

mbusFAVIF26		OBJECT-TYPE
			SYNTAX	INTEGER
			ACCESS	read-only
			STATUS	current
	DESCRIPTION ""
			::= { mbusFA 82 }

mbusFAValue26		OBJECT-TYPE
			SYNTAX	INTEGER
			ACCESS	read-only
			STATUS	current
	DESCRIPTION ""
			::= { mbusFA 83 }

mbusFAVIF27		OBJECT-TYPE
			SYNTAX	INTEGER
			ACCESS	read-only
			STATUS	current
	DESCRIPTION ""
			::= { mbusFA 84 }

mbusFAValue27		OBJECT-TYPE
			SYNTAX	INTEGER
			ACCESS	read-only
			STATUS	current
	DESCRIPTION ""
			::= { mbusFA 85 }

mbusFAVIF28		OBJECT-TYPE
			SYNTAX	INTEGER
			ACCESS	read-only
			STATUS	current
	DESCRIPTION ""
			::= { mbusFA 86 }

mbusFAValue28		OBJECT-TYPE
			SYNTAX	INTEGER
			ACCESS	read-only
			STATUS	current
	DESCRIPTION ""
			::= { mbusFA 87 }

mbusFAVIF29		OBJECT-TYPE
			SYNTAX	INTEGER
			ACCESS	read-only
			STATUS	current
	DESCRIPTION ""
			::= { mbusFA 88 }

mbusFAValue29		OBJECT-TYPE
			SYNTAX	INTEGER
			ACCESS	read-only
			STATUS	current
	DESCRIPTION ""
			::= { mbusFA 89 }

mbusFAVIF2A		OBJECT-TYPE
			SYNTAX	INTEGER
			ACCESS	read-only
			STATUS	current
	DESCRIPTION ""
			::= { mbusFA 90 }

mbusFAValue2A		OBJECT-TYPE
			SYNTAX	INTEGER
			ACCESS	read-only
			STATUS	current
	DESCRIPTION ""
			::= { mbusFA 91 }

mbusFAVIF2B		OBJECT-TYPE
			SYNTAX	INTEGER
			ACCESS	read-only
			STATUS	current
	DESCRIPTION ""
			::= { mbusFA 92 }

mbusFAValue2B		OBJECT-TYPE
			SYNTAX	INTEGER
			ACCESS	read-only
			STATUS	current
	DESCRIPTION ""
			::= { mbusFA 93 }

mbusFAVIF2C		OBJECT-TYPE
			SYNTAX	INTEGER
			ACCESS	read-only
			STATUS	current
	DESCRIPTION ""
			::= { mbusFA 94 }

mbusFAValue2C		OBJECT-TYPE
			SYNTAX	INTEGER
			ACCESS	read-only
			STATUS	current
	DESCRIPTION ""
			::= { mbusFA 95 }

mbusFAVIF2D		OBJECT-TYPE
			SYNTAX	INTEGER
			ACCESS	read-only
			STATUS	current
	DESCRIPTION ""
			::= { mbusFA 96 }

mbusFAValue2D		OBJECT-TYPE
			SYNTAX	INTEGER
			ACCESS	read-only
			STATUS	current
	DESCRIPTION ""
			::= { mbusFA 97 }

mbusFAVIF2E		OBJECT-TYPE
			SYNTAX	INTEGER
			ACCESS	read-only
			STATUS	current
	DESCRIPTION ""
			::= { mbusFA 98 }

mbusFAValue2E		OBJECT-TYPE
			SYNTAX	INTEGER
			ACCESS	read-only
			STATUS	current
	DESCRIPTION ""
			::= { mbusFA 99 }

mbusFAVIF2F		OBJECT-TYPE
			SYNTAX	INTEGER
			ACCESS	read-only
			STATUS	current
	DESCRIPTION ""
			::= { mbusFA 100 }

mbusFAValue2F		OBJECT-TYPE
			SYNTAX	INTEGER
			ACCESS	read-only
			STATUS	current
	DESCRIPTION ""
			::= { mbusFA 101 }

mbusFB			OBJECT IDENTIFIER ::= { mbus 251 }

mbusFBIdNumber		OBJECT-TYPE
			SYNTAX	Gauge
			ACCESS	read-only
			STATUS	current
	DESCRIPTION ""
			::= { mbusFB 1 }

mbusFBManufacturer	OBJECT-TYPE
			SYNTAX	Gauge
			ACCESS	read-only
			STATUS	current
	DESCRIPTION ""
			::= { mbusFB 2 }

mbusFBVersion		OBJECT-TYPE
			SYNTAX	Gauge
			ACCESS	read-only
			STATUS	current
	DESCRIPTION ""
			::= { mbusFB 3 }

mbusFBMedium		OBJECT-TYPE
			SYNTAX	Gauge
			ACCESS	read-only
			STATUS	current
	DESCRIPTION ""
			::= { mbusFB 4 }

mbusFBStatus		OBJECT-TYPE
			SYNTAX	Gauge
			ACCESS	read-only
			STATUS	current
	DESCRIPTION ""
			::= { mbusFB 5 }

mbusFBVIF00		OBJECT-TYPE
			SYNTAX	INTEGER
			ACCESS	read-only
			STATUS	current
	DESCRIPTION ""
			::= { mbusFB 6 }

mbusFBValue00		OBJECT-TYPE
			SYNTAX	INTEGER
			ACCESS	read-only
			STATUS	current
	DESCRIPTION ""
			::= { mbusFB 7 }

mbusFBVIF01		OBJECT-TYPE
			SYNTAX	INTEGER
			ACCESS	read-only
			STATUS	current
	DESCRIPTION ""
			::= { mbusFB 8 }

mbusFBValue01		OBJECT-TYPE
			SYNTAX	INTEGER
			ACCESS	read-only
			STATUS	current
	DESCRIPTION ""
			::= { mbusFB 9 }

mbusFBVIF02		OBJECT-TYPE
			SYNTAX	INTEGER
			ACCESS	read-only
			STATUS	current
	DESCRIPTION ""
			::= { mbusFB 10 }

mbusFBValue02		OBJECT-TYPE
			SYNTAX	INTEGER
			ACCESS	read-only
			STATUS	current
	DESCRIPTION ""
			::= { mbusFB 11 }

mbusFBVIF03		OBJECT-TYPE
			SYNTAX	INTEGER
			ACCESS	read-only
			STATUS	current
	DESCRIPTION ""
			::= { mbusFB 12 }

mbusFBValue03		OBJECT-TYPE
			SYNTAX	INTEGER
			ACCESS	read-only
			STATUS	current
	DESCRIPTION ""
			::= { mbusFB 13 }

mbusFBVIF04		OBJECT-TYPE
			SYNTAX	INTEGER
			ACCESS	read-only
			STATUS	current
	DESCRIPTION ""
			::= { mbusFB 14 }

mbusFBValue04		OBJECT-TYPE
			SYNTAX	INTEGER
			ACCESS	read-only
			STATUS	current
	DESCRIPTION ""
			::= { mbusFB 15 }

mbusFBVIF05		OBJECT-TYPE
			SYNTAX	INTEGER
			ACCESS	read-only
			STATUS	current
	DESCRIPTION ""
			::= { mbusFB 16 }

mbusFBValue05		OBJECT-TYPE
			SYNTAX	INTEGER
			ACCESS	read-only
			STATUS	current
	DESCRIPTION ""
			::= { mbusFB 17 }

mbusFBVIF06		OBJECT-TYPE
			SYNTAX	INTEGER
			ACCESS	read-only
			STATUS	current
	DESCRIPTION ""
			::= { mbusFB 18 }

mbusFBValue06		OBJECT-TYPE
			SYNTAX	INTEGER
			ACCESS	read-only
			STATUS	current
	DESCRIPTION ""
			::= { mbusFB 19 }

mbusFBVIF07		OBJECT-TYPE
			SYNTAX	INTEGER
			ACCESS	read-only
			STATUS	current
	DESCRIPTION ""
			::= { mbusFB 20 }

mbusFBValue07		OBJECT-TYPE
			SYNTAX	INTEGER
			ACCESS	read-only
			STATUS	current
	DESCRIPTION ""
			::= { mbusFB 21 }

mbusFBVIF08		OBJECT-TYPE
			SYNTAX	INTEGER
			ACCESS	read-only
			STATUS	current
	DESCRIPTION ""
			::= { mbusFB 22 }

mbusFBValue08		OBJECT-TYPE
			SYNTAX	INTEGER
			ACCESS	read-only
			STATUS	current
	DESCRIPTION ""
			::= { mbusFB 23 }

mbusFBVIF09		OBJECT-TYPE
			SYNTAX	INTEGER
			ACCESS	read-only
			STATUS	current
	DESCRIPTION ""
			::= { mbusFB 24 }

mbusFBValue09		OBJECT-TYPE
			SYNTAX	INTEGER
			ACCESS	read-only
			STATUS	current
	DESCRIPTION ""
			::= { mbusFB 25 }

mbusFBVIF0A		OBJECT-TYPE
			SYNTAX	INTEGER
			ACCESS	read-only
			STATUS	current
	DESCRIPTION ""
			::= { mbusFB 26 }

mbusFBValue0A		OBJECT-TYPE
			SYNTAX	INTEGER
			ACCESS	read-only
			STATUS	current
	DESCRIPTION ""
			::= { mbusFB 27 }

mbusFBVIF0B		OBJECT-TYPE
			SYNTAX	INTEGER
			ACCESS	read-only
			STATUS	current
	DESCRIPTION ""
			::= { mbusFB 28 }

mbusFBValue0B		OBJECT-TYPE
			SYNTAX	INTEGER
			ACCESS	read-only
			STATUS	current
	DESCRIPTION ""
			::= { mbusFB 29 }

mbusFBVIF0C		OBJECT-TYPE
			SYNTAX	INTEGER
			ACCESS	read-only
			STATUS	current
	DESCRIPTION ""
			::= { mbusFB 30 }

mbusFBValue0C		OBJECT-TYPE
			SYNTAX	INTEGER
			ACCESS	read-only
			STATUS	current
	DESCRIPTION ""
			::= { mbusFB 31 }

mbusFBVIF0D		OBJECT-TYPE
			SYNTAX	INTEGER
			ACCESS	read-only
			STATUS	current
	DESCRIPTION ""
			::= { mbusFB 32 }

mbusFBValue0D		OBJECT-TYPE
			SYNTAX	INTEGER
			ACCESS	read-only
			STATUS	current
	DESCRIPTION ""
			::= { mbusFB 33 }

mbusFBVIF0E		OBJECT-TYPE
			SYNTAX	INTEGER
			ACCESS	read-only
			STATUS	current
	DESCRIPTION ""
			::= { mbusFB 34 }

mbusFBValue0E		OBJECT-TYPE
			SYNTAX	INTEGER
			ACCESS	read-only
			STATUS	current
	DESCRIPTION ""
			::= { mbusFB 35 }

mbusFBVIF0F		OBJECT-TYPE
			SYNTAX	INTEGER
			ACCESS	read-only
			STATUS	current
	DESCRIPTION ""
			::= { mbusFB 36 }

mbusFBValue0F		OBJECT-TYPE
			SYNTAX	INTEGER
			ACCESS	read-only
			STATUS	current
	DESCRIPTION ""
			::= { mbusFB 37 }

mbusFBVIF10		OBJECT-TYPE
			SYNTAX	INTEGER
			ACCESS	read-only
			STATUS	current
	DESCRIPTION ""
			::= { mbusFB 38 }

mbusFBValue10		OBJECT-TYPE
			SYNTAX	INTEGER
			ACCESS	read-only
			STATUS	current
	DESCRIPTION ""
			::= { mbusFB 39 }

mbusFBVIF11		OBJECT-TYPE
			SYNTAX	INTEGER
			ACCESS	read-only
			STATUS	current
	DESCRIPTION ""
			::= { mbusFB 40 }

mbusFBValue11		OBJECT-TYPE
			SYNTAX	INTEGER
			ACCESS	read-only
			STATUS	current
	DESCRIPTION ""
			::= { mbusFB 41 }

mbusFBVIF12		OBJECT-TYPE
			SYNTAX	INTEGER
			ACCESS	read-only
			STATUS	current
	DESCRIPTION ""
			::= { mbusFB 42 }

mbusFBValue12		OBJECT-TYPE
			SYNTAX	INTEGER
			ACCESS	read-only
			STATUS	current
	DESCRIPTION ""
			::= { mbusFB 43 }

mbusFBVIF13		OBJECT-TYPE
			SYNTAX	INTEGER
			ACCESS	read-only
			STATUS	current
	DESCRIPTION ""
			::= { mbusFB 44 }

mbusFBValue13		OBJECT-TYPE
			SYNTAX	INTEGER
			ACCESS	read-only
			STATUS	current
	DESCRIPTION ""
			::= { mbusFB 45 }

mbusFBVIF14		OBJECT-TYPE
			SYNTAX	INTEGER
			ACCESS	read-only
			STATUS	current
	DESCRIPTION ""
			::= { mbusFB 46 }

mbusFBValue14		OBJECT-TYPE
			SYNTAX	INTEGER
			ACCESS	read-only
			STATUS	current
	DESCRIPTION ""
			::= { mbusFB 47 }

mbusFBVIF15		OBJECT-TYPE
			SYNTAX	INTEGER
			ACCESS	read-only
			STATUS	current
	DESCRIPTION ""
			::= { mbusFB 48 }

mbusFBValue15		OBJECT-TYPE
			SYNTAX	INTEGER
			ACCESS	read-only
			STATUS	current
	DESCRIPTION ""
			::= { mbusFB 49 }

mbusFBVIF16		OBJECT-TYPE
			SYNTAX	INTEGER
			ACCESS	read-only
			STATUS	current
	DESCRIPTION ""
			::= { mbusFB 50 }

mbusFBValue16		OBJECT-TYPE
			SYNTAX	INTEGER
			ACCESS	read-only
			STATUS	current
	DESCRIPTION ""
			::= { mbusFB 51 }

mbusFBVIF17		OBJECT-TYPE
			SYNTAX	INTEGER
			ACCESS	read-only
			STATUS	current
	DESCRIPTION ""
			::= { mbusFB 52 }

mbusFBValue17		OBJECT-TYPE
			SYNTAX	INTEGER
			ACCESS	read-only
			STATUS	current
	DESCRIPTION ""
			::= { mbusFB 53 }

mbusFBVIF18		OBJECT-TYPE
			SYNTAX	INTEGER
			ACCESS	read-only
			STATUS	current
	DESCRIPTION ""
			::= { mbusFB 54 }

mbusFBValue18		OBJECT-TYPE
			SYNTAX	INTEGER
			ACCESS	read-only
			STATUS	current
	DESCRIPTION ""
			::= { mbusFB 55 }

mbusFBVIF19		OBJECT-TYPE
			SYNTAX	INTEGER
			ACCESS	read-only
			STATUS	current
	DESCRIPTION ""
			::= { mbusFB 56 }

mbusFBValue19		OBJECT-TYPE
			SYNTAX	INTEGER
			ACCESS	read-only
			STATUS	current
	DESCRIPTION ""
			::= { mbusFB 57 }

mbusFBVIF1A		OBJECT-TYPE
			SYNTAX	INTEGER
			ACCESS	read-only
			STATUS	current
	DESCRIPTION ""
			::= { mbusFB 58 }

mbusFBValue1A		OBJECT-TYPE
			SYNTAX	INTEGER
			ACCESS	read-only
			STATUS	current
	DESCRIPTION ""
			::= { mbusFB 59 }

mbusFBVIF1B		OBJECT-TYPE
			SYNTAX	INTEGER
			ACCESS	read-only
			STATUS	current
	DESCRIPTION ""
			::= { mbusFB 60 }

mbusFBValue1B		OBJECT-TYPE
			SYNTAX	INTEGER
			ACCESS	read-only
			STATUS	current
	DESCRIPTION ""
			::= { mbusFB 61 }

mbusFBVIF1C		OBJECT-TYPE
			SYNTAX	INTEGER
			ACCESS	read-only
			STATUS	current
	DESCRIPTION ""
			::= { mbusFB 62 }

mbusFBValue1C		OBJECT-TYPE
			SYNTAX	INTEGER
			ACCESS	read-only
			STATUS	current
	DESCRIPTION ""
			::= { mbusFB 63 }

mbusFBVIF1D		OBJECT-TYPE
			SYNTAX	INTEGER
			ACCESS	read-only
			STATUS	current
	DESCRIPTION ""
			::= { mbusFB 64 }

mbusFBValue1D		OBJECT-TYPE
			SYNTAX	INTEGER
			ACCESS	read-only
			STATUS	current
	DESCRIPTION ""
			::= { mbusFB 65 }

mbusFBVIF1E		OBJECT-TYPE
			SYNTAX	INTEGER
			ACCESS	read-only
			STATUS	current
	DESCRIPTION ""
			::= { mbusFB 66 }

mbusFBValue1E		OBJECT-TYPE
			SYNTAX	INTEGER
			ACCESS	read-only
			STATUS	current
	DESCRIPTION ""
			::= { mbusFB 67 }

mbusFBVIF1F		OBJECT-TYPE
			SYNTAX	INTEGER
			ACCESS	read-only
			STATUS	current
	DESCRIPTION ""
			::= { mbusFB 68 }

mbusFBValue1F		OBJECT-TYPE
			SYNTAX	INTEGER
			ACCESS	read-only
			STATUS	current
	DESCRIPTION ""
			::= { mbusFB 69 }

mbusFBVIF20		OBJECT-TYPE
			SYNTAX	INTEGER
			ACCESS	read-only
			STATUS	current
	DESCRIPTION ""
			::= { mbusFB 70 }

mbusFBValue20		OBJECT-TYPE
			SYNTAX	INTEGER
			ACCESS	read-only
			STATUS	current
	DESCRIPTION ""
			::= { mbusFB 71 }

mbusFBVIF21		OBJECT-TYPE
			SYNTAX	INTEGER
			ACCESS	read-only
			STATUS	current
	DESCRIPTION ""
			::= { mbusFB 72 }

mbusFBValue21		OBJECT-TYPE
			SYNTAX	INTEGER
			ACCESS	read-only
			STATUS	current
	DESCRIPTION ""
			::= { mbusFB 73 }

mbusFBVIF22		OBJECT-TYPE
			SYNTAX	INTEGER
			ACCESS	read-only
			STATUS	current
	DESCRIPTION ""
			::= { mbusFB 74 }

mbusFBValue22		OBJECT-TYPE
			SYNTAX	INTEGER
			ACCESS	read-only
			STATUS	current
	DESCRIPTION ""
			::= { mbusFB 75 }

mbusFBVIF23		OBJECT-TYPE
			SYNTAX	INTEGER
			ACCESS	read-only
			STATUS	current
	DESCRIPTION ""
			::= { mbusFB 76 }

mbusFBValue23		OBJECT-TYPE
			SYNTAX	INTEGER
			ACCESS	read-only
			STATUS	current
	DESCRIPTION ""
			::= { mbusFB 77 }

mbusFBVIF24		OBJECT-TYPE
			SYNTAX	INTEGER
			ACCESS	read-only
			STATUS	current
	DESCRIPTION ""
			::= { mbusFB 78 }

mbusFBValue24		OBJECT-TYPE
			SYNTAX	INTEGER
			ACCESS	read-only
			STATUS	current
	DESCRIPTION ""
			::= { mbusFB 79 }

mbusFBVIF25		OBJECT-TYPE
			SYNTAX	INTEGER
			ACCESS	read-only
			STATUS	current
	DESCRIPTION ""
			::= { mbusFB 80 }

mbusFBValue25		OBJECT-TYPE
			SYNTAX	INTEGER
			ACCESS	read-only
			STATUS	current
	DESCRIPTION ""
			::= { mbusFB 81 }

mbusFBVIF26		OBJECT-TYPE
			SYNTAX	INTEGER
			ACCESS	read-only
			STATUS	current
	DESCRIPTION ""
			::= { mbusFB 82 }

mbusFBValue26		OBJECT-TYPE
			SYNTAX	INTEGER
			ACCESS	read-only
			STATUS	current
	DESCRIPTION ""
			::= { mbusFB 83 }

mbusFBVIF27		OBJECT-TYPE
			SYNTAX	INTEGER
			ACCESS	read-only
			STATUS	current
	DESCRIPTION ""
			::= { mbusFB 84 }

mbusFBValue27		OBJECT-TYPE
			SYNTAX	INTEGER
			ACCESS	read-only
			STATUS	current
	DESCRIPTION ""
			::= { mbusFB 85 }

mbusFBVIF28		OBJECT-TYPE
			SYNTAX	INTEGER
			ACCESS	read-only
			STATUS	current
	DESCRIPTION ""
			::= { mbusFB 86 }

mbusFBValue28		OBJECT-TYPE
			SYNTAX	INTEGER
			ACCESS	read-only
			STATUS	current
	DESCRIPTION ""
			::= { mbusFB 87 }

mbusFBVIF29		OBJECT-TYPE
			SYNTAX	INTEGER
			ACCESS	read-only
			STATUS	current
	DESCRIPTION ""
			::= { mbusFB 88 }

mbusFBValue29		OBJECT-TYPE
			SYNTAX	INTEGER
			ACCESS	read-only
			STATUS	current
	DESCRIPTION ""
			::= { mbusFB 89 }

mbusFBVIF2A		OBJECT-TYPE
			SYNTAX	INTEGER
			ACCESS	read-only
			STATUS	current
	DESCRIPTION ""
			::= { mbusFB 90 }

mbusFBValue2A		OBJECT-TYPE
			SYNTAX	INTEGER
			ACCESS	read-only
			STATUS	current
	DESCRIPTION ""
			::= { mbusFB 91 }

mbusFBVIF2B		OBJECT-TYPE
			SYNTAX	INTEGER
			ACCESS	read-only
			STATUS	current
	DESCRIPTION ""
			::= { mbusFB 92 }

mbusFBValue2B		OBJECT-TYPE
			SYNTAX	INTEGER
			ACCESS	read-only
			STATUS	current
	DESCRIPTION ""
			::= { mbusFB 93 }

mbusFBVIF2C		OBJECT-TYPE
			SYNTAX	INTEGER
			ACCESS	read-only
			STATUS	current
	DESCRIPTION ""
			::= { mbusFB 94 }

mbusFBValue2C		OBJECT-TYPE
			SYNTAX	INTEGER
			ACCESS	read-only
			STATUS	current
	DESCRIPTION ""
			::= { mbusFB 95 }

mbusFBVIF2D		OBJECT-TYPE
			SYNTAX	INTEGER
			ACCESS	read-only
			STATUS	current
	DESCRIPTION ""
			::= { mbusFB 96 }

mbusFBValue2D		OBJECT-TYPE
			SYNTAX	INTEGER
			ACCESS	read-only
			STATUS	current
	DESCRIPTION ""
			::= { mbusFB 97 }

mbusFBVIF2E		OBJECT-TYPE
			SYNTAX	INTEGER
			ACCESS	read-only
			STATUS	current
	DESCRIPTION ""
			::= { mbusFB 98 }

mbusFBValue2E		OBJECT-TYPE
			SYNTAX	INTEGER
			ACCESS	read-only
			STATUS	current
	DESCRIPTION ""
			::= { mbusFB 99 }

mbusFBVIF2F		OBJECT-TYPE
			SYNTAX	INTEGER
			ACCESS	read-only
			STATUS	current
	DESCRIPTION ""
			::= { mbusFB 100 }

mbusFBValue2F		OBJECT-TYPE
			SYNTAX	INTEGER
			ACCESS	read-only
			STATUS	current
	DESCRIPTION ""
			::= { mbusFB 101 }

mbusFC			OBJECT IDENTIFIER ::= { mbus 252 }

mbusFCIdNumber		OBJECT-TYPE
			SYNTAX	Gauge
			ACCESS	read-only
			STATUS	current
	DESCRIPTION ""
			::= { mbusFC 1 }

mbusFCManufacturer	OBJECT-TYPE
			SYNTAX	Gauge
			ACCESS	read-only
			STATUS	current
	DESCRIPTION ""
			::= { mbusFC 2 }

mbusFCVersion		OBJECT-TYPE
			SYNTAX	Gauge
			ACCESS	read-only
			STATUS	current
	DESCRIPTION ""
			::= { mbusFC 3 }

mbusFCMedium		OBJECT-TYPE
			SYNTAX	Gauge
			ACCESS	read-only
			STATUS	current
	DESCRIPTION ""
			::= { mbusFC 4 }

mbusFCStatus		OBJECT-TYPE
			SYNTAX	Gauge
			ACCESS	read-only
			STATUS	current
	DESCRIPTION ""
			::= { mbusFC 5 }

mbusFCVIF00		OBJECT-TYPE
			SYNTAX	INTEGER
			ACCESS	read-only
			STATUS	current
	DESCRIPTION ""
			::= { mbusFC 6 }

mbusFCValue00		OBJECT-TYPE
			SYNTAX	INTEGER
			ACCESS	read-only
			STATUS	current
	DESCRIPTION ""
			::= { mbusFC 7 }

mbusFCVIF01		OBJECT-TYPE
			SYNTAX	INTEGER
			ACCESS	read-only
			STATUS	current
	DESCRIPTION ""
			::= { mbusFC 8 }

mbusFCValue01		OBJECT-TYPE
			SYNTAX	INTEGER
			ACCESS	read-only
			STATUS	current
	DESCRIPTION ""
			::= { mbusFC 9 }

mbusFCVIF02		OBJECT-TYPE
			SYNTAX	INTEGER
			ACCESS	read-only
			STATUS	current
	DESCRIPTION ""
			::= { mbusFC 10 }

mbusFCValue02		OBJECT-TYPE
			SYNTAX	INTEGER
			ACCESS	read-only
			STATUS	current
	DESCRIPTION ""
			::= { mbusFC 11 }

mbusFCVIF03		OBJECT-TYPE
			SYNTAX	INTEGER
			ACCESS	read-only
			STATUS	current
	DESCRIPTION ""
			::= { mbusFC 12 }

mbusFCValue03		OBJECT-TYPE
			SYNTAX	INTEGER
			ACCESS	read-only
			STATUS	current
	DESCRIPTION ""
			::= { mbusFC 13 }

mbusFCVIF04		OBJECT-TYPE
			SYNTAX	INTEGER
			ACCESS	read-only
			STATUS	current
	DESCRIPTION ""
			::= { mbusFC 14 }

mbusFCValue04		OBJECT-TYPE
			SYNTAX	INTEGER
			ACCESS	read-only
			STATUS	current
	DESCRIPTION ""
			::= { mbusFC 15 }

mbusFCVIF05		OBJECT-TYPE
			SYNTAX	INTEGER
			ACCESS	read-only
			STATUS	current
	DESCRIPTION ""
			::= { mbusFC 16 }

mbusFCValue05		OBJECT-TYPE
			SYNTAX	INTEGER
			ACCESS	read-only
			STATUS	current
	DESCRIPTION ""
			::= { mbusFC 17 }

mbusFCVIF06		OBJECT-TYPE
			SYNTAX	INTEGER
			ACCESS	read-only
			STATUS	current
	DESCRIPTION ""
			::= { mbusFC 18 }

mbusFCValue06		OBJECT-TYPE
			SYNTAX	INTEGER
			ACCESS	read-only
			STATUS	current
	DESCRIPTION ""
			::= { mbusFC 19 }

mbusFCVIF07		OBJECT-TYPE
			SYNTAX	INTEGER
			ACCESS	read-only
			STATUS	current
	DESCRIPTION ""
			::= { mbusFC 20 }

mbusFCValue07		OBJECT-TYPE
			SYNTAX	INTEGER
			ACCESS	read-only
			STATUS	current
	DESCRIPTION ""
			::= { mbusFC 21 }

mbusFCVIF08		OBJECT-TYPE
			SYNTAX	INTEGER
			ACCESS	read-only
			STATUS	current
	DESCRIPTION ""
			::= { mbusFC 22 }

mbusFCValue08		OBJECT-TYPE
			SYNTAX	INTEGER
			ACCESS	read-only
			STATUS	current
	DESCRIPTION ""
			::= { mbusFC 23 }

mbusFCVIF09		OBJECT-TYPE
			SYNTAX	INTEGER
			ACCESS	read-only
			STATUS	current
	DESCRIPTION ""
			::= { mbusFC 24 }

mbusFCValue09		OBJECT-TYPE
			SYNTAX	INTEGER
			ACCESS	read-only
			STATUS	current
	DESCRIPTION ""
			::= { mbusFC 25 }

mbusFCVIF0A		OBJECT-TYPE
			SYNTAX	INTEGER
			ACCESS	read-only
			STATUS	current
	DESCRIPTION ""
			::= { mbusFC 26 }

mbusFCValue0A		OBJECT-TYPE
			SYNTAX	INTEGER
			ACCESS	read-only
			STATUS	current
	DESCRIPTION ""
			::= { mbusFC 27 }

mbusFCVIF0B		OBJECT-TYPE
			SYNTAX	INTEGER
			ACCESS	read-only
			STATUS	current
	DESCRIPTION ""
			::= { mbusFC 28 }

mbusFCValue0B		OBJECT-TYPE
			SYNTAX	INTEGER
			ACCESS	read-only
			STATUS	current
	DESCRIPTION ""
			::= { mbusFC 29 }

mbusFCVIF0C		OBJECT-TYPE
			SYNTAX	INTEGER
			ACCESS	read-only
			STATUS	current
	DESCRIPTION ""
			::= { mbusFC 30 }

mbusFCValue0C		OBJECT-TYPE
			SYNTAX	INTEGER
			ACCESS	read-only
			STATUS	current
	DESCRIPTION ""
			::= { mbusFC 31 }

mbusFCVIF0D		OBJECT-TYPE
			SYNTAX	INTEGER
			ACCESS	read-only
			STATUS	current
	DESCRIPTION ""
			::= { mbusFC 32 }

mbusFCValue0D		OBJECT-TYPE
			SYNTAX	INTEGER
			ACCESS	read-only
			STATUS	current
	DESCRIPTION ""
			::= { mbusFC 33 }

mbusFCVIF0E		OBJECT-TYPE
			SYNTAX	INTEGER
			ACCESS	read-only
			STATUS	current
	DESCRIPTION ""
			::= { mbusFC 34 }

mbusFCValue0E		OBJECT-TYPE
			SYNTAX	INTEGER
			ACCESS	read-only
			STATUS	current
	DESCRIPTION ""
			::= { mbusFC 35 }

mbusFCVIF0F		OBJECT-TYPE
			SYNTAX	INTEGER
			ACCESS	read-only
			STATUS	current
	DESCRIPTION ""
			::= { mbusFC 36 }

mbusFCValue0F		OBJECT-TYPE
			SYNTAX	INTEGER
			ACCESS	read-only
			STATUS	current
	DESCRIPTION ""
			::= { mbusFC 37 }

mbusFCVIF10		OBJECT-TYPE
			SYNTAX	INTEGER
			ACCESS	read-only
			STATUS	current
	DESCRIPTION ""
			::= { mbusFC 38 }

mbusFCValue10		OBJECT-TYPE
			SYNTAX	INTEGER
			ACCESS	read-only
			STATUS	current
	DESCRIPTION ""
			::= { mbusFC 39 }

mbusFCVIF11		OBJECT-TYPE
			SYNTAX	INTEGER
			ACCESS	read-only
			STATUS	current
	DESCRIPTION ""
			::= { mbusFC 40 }

mbusFCValue11		OBJECT-TYPE
			SYNTAX	INTEGER
			ACCESS	read-only
			STATUS	current
	DESCRIPTION ""
			::= { mbusFC 41 }

mbusFCVIF12		OBJECT-TYPE
			SYNTAX	INTEGER
			ACCESS	read-only
			STATUS	current
	DESCRIPTION ""
			::= { mbusFC 42 }

mbusFCValue12		OBJECT-TYPE
			SYNTAX	INTEGER
			ACCESS	read-only
			STATUS	current
	DESCRIPTION ""
			::= { mbusFC 43 }

mbusFCVIF13		OBJECT-TYPE
			SYNTAX	INTEGER
			ACCESS	read-only
			STATUS	current
	DESCRIPTION ""
			::= { mbusFC 44 }

mbusFCValue13		OBJECT-TYPE
			SYNTAX	INTEGER
			ACCESS	read-only
			STATUS	current
	DESCRIPTION ""
			::= { mbusFC 45 }

mbusFCVIF14		OBJECT-TYPE
			SYNTAX	INTEGER
			ACCESS	read-only
			STATUS	current
	DESCRIPTION ""
			::= { mbusFC 46 }

mbusFCValue14		OBJECT-TYPE
			SYNTAX	INTEGER
			ACCESS	read-only
			STATUS	current
	DESCRIPTION ""
			::= { mbusFC 47 }

mbusFCVIF15		OBJECT-TYPE
			SYNTAX	INTEGER
			ACCESS	read-only
			STATUS	current
	DESCRIPTION ""
			::= { mbusFC 48 }

mbusFCValue15		OBJECT-TYPE
			SYNTAX	INTEGER
			ACCESS	read-only
			STATUS	current
	DESCRIPTION ""
			::= { mbusFC 49 }

mbusFCVIF16		OBJECT-TYPE
			SYNTAX	INTEGER
			ACCESS	read-only
			STATUS	current
	DESCRIPTION ""
			::= { mbusFC 50 }

mbusFCValue16		OBJECT-TYPE
			SYNTAX	INTEGER
			ACCESS	read-only
			STATUS	current
	DESCRIPTION ""
			::= { mbusFC 51 }

mbusFCVIF17		OBJECT-TYPE
			SYNTAX	INTEGER
			ACCESS	read-only
			STATUS	current
	DESCRIPTION ""
			::= { mbusFC 52 }

mbusFCValue17		OBJECT-TYPE
			SYNTAX	INTEGER
			ACCESS	read-only
			STATUS	current
	DESCRIPTION ""
			::= { mbusFC 53 }

mbusFCVIF18		OBJECT-TYPE
			SYNTAX	INTEGER
			ACCESS	read-only
			STATUS	current
	DESCRIPTION ""
			::= { mbusFC 54 }

mbusFCValue18		OBJECT-TYPE
			SYNTAX	INTEGER
			ACCESS	read-only
			STATUS	current
	DESCRIPTION ""
			::= { mbusFC 55 }

mbusFCVIF19		OBJECT-TYPE
			SYNTAX	INTEGER
			ACCESS	read-only
			STATUS	current
	DESCRIPTION ""
			::= { mbusFC 56 }

mbusFCValue19		OBJECT-TYPE
			SYNTAX	INTEGER
			ACCESS	read-only
			STATUS	current
	DESCRIPTION ""
			::= { mbusFC 57 }

mbusFCVIF1A		OBJECT-TYPE
			SYNTAX	INTEGER
			ACCESS	read-only
			STATUS	current
	DESCRIPTION ""
			::= { mbusFC 58 }

mbusFCValue1A		OBJECT-TYPE
			SYNTAX	INTEGER
			ACCESS	read-only
			STATUS	current
	DESCRIPTION ""
			::= { mbusFC 59 }

mbusFCVIF1B		OBJECT-TYPE
			SYNTAX	INTEGER
			ACCESS	read-only
			STATUS	current
	DESCRIPTION ""
			::= { mbusFC 60 }

mbusFCValue1B		OBJECT-TYPE
			SYNTAX	INTEGER
			ACCESS	read-only
			STATUS	current
	DESCRIPTION ""
			::= { mbusFC 61 }

mbusFCVIF1C		OBJECT-TYPE
			SYNTAX	INTEGER
			ACCESS	read-only
			STATUS	current
	DESCRIPTION ""
			::= { mbusFC 62 }

mbusFCValue1C		OBJECT-TYPE
			SYNTAX	INTEGER
			ACCESS	read-only
			STATUS	current
	DESCRIPTION ""
			::= { mbusFC 63 }

mbusFCVIF1D		OBJECT-TYPE
			SYNTAX	INTEGER
			ACCESS	read-only
			STATUS	current
	DESCRIPTION ""
			::= { mbusFC 64 }

mbusFCValue1D		OBJECT-TYPE
			SYNTAX	INTEGER
			ACCESS	read-only
			STATUS	current
	DESCRIPTION ""
			::= { mbusFC 65 }

mbusFCVIF1E		OBJECT-TYPE
			SYNTAX	INTEGER
			ACCESS	read-only
			STATUS	current
	DESCRIPTION ""
			::= { mbusFC 66 }

mbusFCValue1E		OBJECT-TYPE
			SYNTAX	INTEGER
			ACCESS	read-only
			STATUS	current
	DESCRIPTION ""
			::= { mbusFC 67 }

mbusFCVIF1F		OBJECT-TYPE
			SYNTAX	INTEGER
			ACCESS	read-only
			STATUS	current
	DESCRIPTION ""
			::= { mbusFC 68 }

mbusFCValue1F		OBJECT-TYPE
			SYNTAX	INTEGER
			ACCESS	read-only
			STATUS	current
	DESCRIPTION ""
			::= { mbusFC 69 }

mbusFCVIF20		OBJECT-TYPE
			SYNTAX	INTEGER
			ACCESS	read-only
			STATUS	current
	DESCRIPTION ""
			::= { mbusFC 70 }

mbusFCValue20		OBJECT-TYPE
			SYNTAX	INTEGER
			ACCESS	read-only
			STATUS	current
	DESCRIPTION ""
			::= { mbusFC 71 }

mbusFCVIF21		OBJECT-TYPE
			SYNTAX	INTEGER
			ACCESS	read-only
			STATUS	current
	DESCRIPTION ""
			::= { mbusFC 72 }

mbusFCValue21		OBJECT-TYPE
			SYNTAX	INTEGER
			ACCESS	read-only
			STATUS	current
	DESCRIPTION ""
			::= { mbusFC 73 }

mbusFCVIF22		OBJECT-TYPE
			SYNTAX	INTEGER
			ACCESS	read-only
			STATUS	current
	DESCRIPTION ""
			::= { mbusFC 74 }

mbusFCValue22		OBJECT-TYPE
			SYNTAX	INTEGER
			ACCESS	read-only
			STATUS	current
	DESCRIPTION ""
			::= { mbusFC 75 }

mbusFCVIF23		OBJECT-TYPE
			SYNTAX	INTEGER
			ACCESS	read-only
			STATUS	current
	DESCRIPTION ""
			::= { mbusFC 76 }

mbusFCValue23		OBJECT-TYPE
			SYNTAX	INTEGER
			ACCESS	read-only
			STATUS	current
	DESCRIPTION ""
			::= { mbusFC 77 }

mbusFCVIF24		OBJECT-TYPE
			SYNTAX	INTEGER
			ACCESS	read-only
			STATUS	current
	DESCRIPTION ""
			::= { mbusFC 78 }

mbusFCValue24		OBJECT-TYPE
			SYNTAX	INTEGER
			ACCESS	read-only
			STATUS	current
	DESCRIPTION ""
			::= { mbusFC 79 }

mbusFCVIF25		OBJECT-TYPE
			SYNTAX	INTEGER
			ACCESS	read-only
			STATUS	current
	DESCRIPTION ""
			::= { mbusFC 80 }

mbusFCValue25		OBJECT-TYPE
			SYNTAX	INTEGER
			ACCESS	read-only
			STATUS	current
	DESCRIPTION ""
			::= { mbusFC 81 }

mbusFCVIF26		OBJECT-TYPE
			SYNTAX	INTEGER
			ACCESS	read-only
			STATUS	current
	DESCRIPTION ""
			::= { mbusFC 82 }

mbusFCValue26		OBJECT-TYPE
			SYNTAX	INTEGER
			ACCESS	read-only
			STATUS	current
	DESCRIPTION ""
			::= { mbusFC 83 }

mbusFCVIF27		OBJECT-TYPE
			SYNTAX	INTEGER
			ACCESS	read-only
			STATUS	current
	DESCRIPTION ""
			::= { mbusFC 84 }

mbusFCValue27		OBJECT-TYPE
			SYNTAX	INTEGER
			ACCESS	read-only
			STATUS	current
	DESCRIPTION ""
			::= { mbusFC 85 }

mbusFCVIF28		OBJECT-TYPE
			SYNTAX	INTEGER
			ACCESS	read-only
			STATUS	current
	DESCRIPTION ""
			::= { mbusFC 86 }

mbusFCValue28		OBJECT-TYPE
			SYNTAX	INTEGER
			ACCESS	read-only
			STATUS	current
	DESCRIPTION ""
			::= { mbusFC 87 }

mbusFCVIF29		OBJECT-TYPE
			SYNTAX	INTEGER
			ACCESS	read-only
			STATUS	current
	DESCRIPTION ""
			::= { mbusFC 88 }

mbusFCValue29		OBJECT-TYPE
			SYNTAX	INTEGER
			ACCESS	read-only
			STATUS	current
	DESCRIPTION ""
			::= { mbusFC 89 }

mbusFCVIF2A		OBJECT-TYPE
			SYNTAX	INTEGER
			ACCESS	read-only
			STATUS	current
	DESCRIPTION ""
			::= { mbusFC 90 }

mbusFCValue2A		OBJECT-TYPE
			SYNTAX	INTEGER
			ACCESS	read-only
			STATUS	current
	DESCRIPTION ""
			::= { mbusFC 91 }

mbusFCVIF2B		OBJECT-TYPE
			SYNTAX	INTEGER
			ACCESS	read-only
			STATUS	current
	DESCRIPTION ""
			::= { mbusFC 92 }

mbusFCValue2B		OBJECT-TYPE
			SYNTAX	INTEGER
			ACCESS	read-only
			STATUS	current
	DESCRIPTION ""
			::= { mbusFC 93 }

mbusFCVIF2C		OBJECT-TYPE
			SYNTAX	INTEGER
			ACCESS	read-only
			STATUS	current
	DESCRIPTION ""
			::= { mbusFC 94 }

mbusFCValue2C		OBJECT-TYPE
			SYNTAX	INTEGER
			ACCESS	read-only
			STATUS	current
	DESCRIPTION ""
			::= { mbusFC 95 }

mbusFCVIF2D		OBJECT-TYPE
			SYNTAX	INTEGER
			ACCESS	read-only
			STATUS	current
	DESCRIPTION ""
			::= { mbusFC 96 }

mbusFCValue2D		OBJECT-TYPE
			SYNTAX	INTEGER
			ACCESS	read-only
			STATUS	current
	DESCRIPTION ""
			::= { mbusFC 97 }

mbusFCVIF2E		OBJECT-TYPE
			SYNTAX	INTEGER
			ACCESS	read-only
			STATUS	current
	DESCRIPTION ""
			::= { mbusFC 98 }

mbusFCValue2E		OBJECT-TYPE
			SYNTAX	INTEGER
			ACCESS	read-only
			STATUS	current
	DESCRIPTION ""
			::= { mbusFC 99 }

mbusFCVIF2F		OBJECT-TYPE
			SYNTAX	INTEGER
			ACCESS	read-only
			STATUS	current
	DESCRIPTION ""
			::= { mbusFC 100 }

mbusFCValue2F		OBJECT-TYPE
			SYNTAX	INTEGER
			ACCESS	read-only
			STATUS	current
	DESCRIPTION ""
			::= { mbusFC 101 }

mbusFD			OBJECT IDENTIFIER ::= { mbus 253 }

mbusFDIdNumber		OBJECT-TYPE
			SYNTAX	Gauge
			ACCESS	read-only
			STATUS	current
	DESCRIPTION ""
			::= { mbusFD 1 }

mbusFDManufacturer	OBJECT-TYPE
			SYNTAX	Gauge
			ACCESS	read-only
			STATUS	current
	DESCRIPTION ""
			::= { mbusFD 2 }

mbusFDVersion		OBJECT-TYPE
			SYNTAX	Gauge
			ACCESS	read-only
			STATUS	current
	DESCRIPTION ""
			::= { mbusFD 3 }

mbusFDMedium		OBJECT-TYPE
			SYNTAX	Gauge
			ACCESS	read-only
			STATUS	current
	DESCRIPTION ""
			::= { mbusFD 4 }

mbusFDStatus		OBJECT-TYPE
			SYNTAX	Gauge
			ACCESS	read-only
			STATUS	current
	DESCRIPTION ""
			::= { mbusFD 5 }

mbusFDVIF00		OBJECT-TYPE
			SYNTAX	INTEGER
			ACCESS	read-only
			STATUS	current
	DESCRIPTION ""
			::= { mbusFD 6 }

mbusFDValue00		OBJECT-TYPE
			SYNTAX	INTEGER
			ACCESS	read-only
			STATUS	current
	DESCRIPTION ""
			::= { mbusFD 7 }

mbusFDVIF01		OBJECT-TYPE
			SYNTAX	INTEGER
			ACCESS	read-only
			STATUS	current
	DESCRIPTION ""
			::= { mbusFD 8 }

mbusFDValue01		OBJECT-TYPE
			SYNTAX	INTEGER
			ACCESS	read-only
			STATUS	current
	DESCRIPTION ""
			::= { mbusFD 9 }

mbusFDVIF02		OBJECT-TYPE
			SYNTAX	INTEGER
			ACCESS	read-only
			STATUS	current
	DESCRIPTION ""
			::= { mbusFD 10 }

mbusFDValue02		OBJECT-TYPE
			SYNTAX	INTEGER
			ACCESS	read-only
			STATUS	current
	DESCRIPTION ""
			::= { mbusFD 11 }

mbusFDVIF03		OBJECT-TYPE
			SYNTAX	INTEGER
			ACCESS	read-only
			STATUS	current
	DESCRIPTION ""
			::= { mbusFD 12 }

mbusFDValue03		OBJECT-TYPE
			SYNTAX	INTEGER
			ACCESS	read-only
			STATUS	current
	DESCRIPTION ""
			::= { mbusFD 13 }

mbusFDVIF04		OBJECT-TYPE
			SYNTAX	INTEGER
			ACCESS	read-only
			STATUS	current
	DESCRIPTION ""
			::= { mbusFD 14 }

mbusFDValue04		OBJECT-TYPE
			SYNTAX	INTEGER
			ACCESS	read-only
			STATUS	current
	DESCRIPTION ""
			::= { mbusFD 15 }

mbusFDVIF05		OBJECT-TYPE
			SYNTAX	INTEGER
			ACCESS	read-only
			STATUS	current
	DESCRIPTION ""
			::= { mbusFD 16 }

mbusFDValue05		OBJECT-TYPE
			SYNTAX	INTEGER
			ACCESS	read-only
			STATUS	current
	DESCRIPTION ""
			::= { mbusFD 17 }

mbusFDVIF06		OBJECT-TYPE
			SYNTAX	INTEGER
			ACCESS	read-only
			STATUS	current
	DESCRIPTION ""
			::= { mbusFD 18 }

mbusFDValue06		OBJECT-TYPE
			SYNTAX	INTEGER
			ACCESS	read-only
			STATUS	current
	DESCRIPTION ""
			::= { mbusFD 19 }

mbusFDVIF07		OBJECT-TYPE
			SYNTAX	INTEGER
			ACCESS	read-only
			STATUS	current
	DESCRIPTION ""
			::= { mbusFD 20 }

mbusFDValue07		OBJECT-TYPE
			SYNTAX	INTEGER
			ACCESS	read-only
			STATUS	current
	DESCRIPTION ""
			::= { mbusFD 21 }

mbusFDVIF08		OBJECT-TYPE
			SYNTAX	INTEGER
			ACCESS	read-only
			STATUS	current
	DESCRIPTION ""
			::= { mbusFD 22 }

mbusFDValue08		OBJECT-TYPE
			SYNTAX	INTEGER
			ACCESS	read-only
			STATUS	current
	DESCRIPTION ""
			::= { mbusFD 23 }

mbusFDVIF09		OBJECT-TYPE
			SYNTAX	INTEGER
			ACCESS	read-only
			STATUS	current
	DESCRIPTION ""
			::= { mbusFD 24 }

mbusFDValue09		OBJECT-TYPE
			SYNTAX	INTEGER
			ACCESS	read-only
			STATUS	current
	DESCRIPTION ""
			::= { mbusFD 25 }

mbusFDVIF0A		OBJECT-TYPE
			SYNTAX	INTEGER
			ACCESS	read-only
			STATUS	current
	DESCRIPTION ""
			::= { mbusFD 26 }

mbusFDValue0A		OBJECT-TYPE
			SYNTAX	INTEGER
			ACCESS	read-only
			STATUS	current
	DESCRIPTION ""
			::= { mbusFD 27 }

mbusFDVIF0B		OBJECT-TYPE
			SYNTAX	INTEGER
			ACCESS	read-only
			STATUS	current
	DESCRIPTION ""
			::= { mbusFD 28 }

mbusFDValue0B		OBJECT-TYPE
			SYNTAX	INTEGER
			ACCESS	read-only
			STATUS	current
	DESCRIPTION ""
			::= { mbusFD 29 }

mbusFDVIF0C		OBJECT-TYPE
			SYNTAX	INTEGER
			ACCESS	read-only
			STATUS	current
	DESCRIPTION ""
			::= { mbusFD 30 }

mbusFDValue0C		OBJECT-TYPE
			SYNTAX	INTEGER
			ACCESS	read-only
			STATUS	current
	DESCRIPTION ""
			::= { mbusFD 31 }

mbusFDVIF0D		OBJECT-TYPE
			SYNTAX	INTEGER
			ACCESS	read-only
			STATUS	current
	DESCRIPTION ""
			::= { mbusFD 32 }

mbusFDValue0D		OBJECT-TYPE
			SYNTAX	INTEGER
			ACCESS	read-only
			STATUS	current
	DESCRIPTION ""
			::= { mbusFD 33 }

mbusFDVIF0E		OBJECT-TYPE
			SYNTAX	INTEGER
			ACCESS	read-only
			STATUS	current
	DESCRIPTION ""
			::= { mbusFD 34 }

mbusFDValue0E		OBJECT-TYPE
			SYNTAX	INTEGER
			ACCESS	read-only
			STATUS	current
	DESCRIPTION ""
			::= { mbusFD 35 }

mbusFDVIF0F		OBJECT-TYPE
			SYNTAX	INTEGER
			ACCESS	read-only
			STATUS	current
	DESCRIPTION ""
			::= { mbusFD 36 }

mbusFDValue0F		OBJECT-TYPE
			SYNTAX	INTEGER
			ACCESS	read-only
			STATUS	current
	DESCRIPTION ""
			::= { mbusFD 37 }

mbusFDVIF10		OBJECT-TYPE
			SYNTAX	INTEGER
			ACCESS	read-only
			STATUS	current
	DESCRIPTION ""
			::= { mbusFD 38 }

mbusFDValue10		OBJECT-TYPE
			SYNTAX	INTEGER
			ACCESS	read-only
			STATUS	current
	DESCRIPTION ""
			::= { mbusFD 39 }

mbusFDVIF11		OBJECT-TYPE
			SYNTAX	INTEGER
			ACCESS	read-only
			STATUS	current
	DESCRIPTION ""
			::= { mbusFD 40 }

mbusFDValue11		OBJECT-TYPE
			SYNTAX	INTEGER
			ACCESS	read-only
			STATUS	current
	DESCRIPTION ""
			::= { mbusFD 41 }

mbusFDVIF12		OBJECT-TYPE
			SYNTAX	INTEGER
			ACCESS	read-only
			STATUS	current
	DESCRIPTION ""
			::= { mbusFD 42 }

mbusFDValue12		OBJECT-TYPE
			SYNTAX	INTEGER
			ACCESS	read-only
			STATUS	current
	DESCRIPTION ""
			::= { mbusFD 43 }

mbusFDVIF13		OBJECT-TYPE
			SYNTAX	INTEGER
			ACCESS	read-only
			STATUS	current
	DESCRIPTION ""
			::= { mbusFD 44 }

mbusFDValue13		OBJECT-TYPE
			SYNTAX	INTEGER
			ACCESS	read-only
			STATUS	current
	DESCRIPTION ""
			::= { mbusFD 45 }

mbusFDVIF14		OBJECT-TYPE
			SYNTAX	INTEGER
			ACCESS	read-only
			STATUS	current
	DESCRIPTION ""
			::= { mbusFD 46 }

mbusFDValue14		OBJECT-TYPE
			SYNTAX	INTEGER
			ACCESS	read-only
			STATUS	current
	DESCRIPTION ""
			::= { mbusFD 47 }

mbusFDVIF15		OBJECT-TYPE
			SYNTAX	INTEGER
			ACCESS	read-only
			STATUS	current
	DESCRIPTION ""
			::= { mbusFD 48 }

mbusFDValue15		OBJECT-TYPE
			SYNTAX	INTEGER
			ACCESS	read-only
			STATUS	current
	DESCRIPTION ""
			::= { mbusFD 49 }

mbusFDVIF16		OBJECT-TYPE
			SYNTAX	INTEGER
			ACCESS	read-only
			STATUS	current
	DESCRIPTION ""
			::= { mbusFD 50 }

mbusFDValue16		OBJECT-TYPE
			SYNTAX	INTEGER
			ACCESS	read-only
			STATUS	current
	DESCRIPTION ""
			::= { mbusFD 51 }

mbusFDVIF17		OBJECT-TYPE
			SYNTAX	INTEGER
			ACCESS	read-only
			STATUS	current
	DESCRIPTION ""
			::= { mbusFD 52 }

mbusFDValue17		OBJECT-TYPE
			SYNTAX	INTEGER
			ACCESS	read-only
			STATUS	current
	DESCRIPTION ""
			::= { mbusFD 53 }

mbusFDVIF18		OBJECT-TYPE
			SYNTAX	INTEGER
			ACCESS	read-only
			STATUS	current
	DESCRIPTION ""
			::= { mbusFD 54 }

mbusFDValue18		OBJECT-TYPE
			SYNTAX	INTEGER
			ACCESS	read-only
			STATUS	current
	DESCRIPTION ""
			::= { mbusFD 55 }

mbusFDVIF19		OBJECT-TYPE
			SYNTAX	INTEGER
			ACCESS	read-only
			STATUS	current
	DESCRIPTION ""
			::= { mbusFD 56 }

mbusFDValue19		OBJECT-TYPE
			SYNTAX	INTEGER
			ACCESS	read-only
			STATUS	current
	DESCRIPTION ""
			::= { mbusFD 57 }

mbusFDVIF1A		OBJECT-TYPE
			SYNTAX	INTEGER
			ACCESS	read-only
			STATUS	current
	DESCRIPTION ""
			::= { mbusFD 58 }

mbusFDValue1A		OBJECT-TYPE
			SYNTAX	INTEGER
			ACCESS	read-only
			STATUS	current
	DESCRIPTION ""
			::= { mbusFD 59 }

mbusFDVIF1B		OBJECT-TYPE
			SYNTAX	INTEGER
			ACCESS	read-only
			STATUS	current
	DESCRIPTION ""
			::= { mbusFD 60 }

mbusFDValue1B		OBJECT-TYPE
			SYNTAX	INTEGER
			ACCESS	read-only
			STATUS	current
	DESCRIPTION ""
			::= { mbusFD 61 }

mbusFDVIF1C		OBJECT-TYPE
			SYNTAX	INTEGER
			ACCESS	read-only
			STATUS	current
	DESCRIPTION ""
			::= { mbusFD 62 }

mbusFDValue1C		OBJECT-TYPE
			SYNTAX	INTEGER
			ACCESS	read-only
			STATUS	current
	DESCRIPTION ""
			::= { mbusFD 63 }

mbusFDVIF1D		OBJECT-TYPE
			SYNTAX	INTEGER
			ACCESS	read-only
			STATUS	current
	DESCRIPTION ""
			::= { mbusFD 64 }

mbusFDValue1D		OBJECT-TYPE
			SYNTAX	INTEGER
			ACCESS	read-only
			STATUS	current
	DESCRIPTION ""
			::= { mbusFD 65 }

mbusFDVIF1E		OBJECT-TYPE
			SYNTAX	INTEGER
			ACCESS	read-only
			STATUS	current
	DESCRIPTION ""
			::= { mbusFD 66 }

mbusFDValue1E		OBJECT-TYPE
			SYNTAX	INTEGER
			ACCESS	read-only
			STATUS	current
	DESCRIPTION ""
			::= { mbusFD 67 }

mbusFDVIF1F		OBJECT-TYPE
			SYNTAX	INTEGER
			ACCESS	read-only
			STATUS	current
	DESCRIPTION ""
			::= { mbusFD 68 }

mbusFDValue1F		OBJECT-TYPE
			SYNTAX	INTEGER
			ACCESS	read-only
			STATUS	current
	DESCRIPTION ""
			::= { mbusFD 69 }

mbusFDVIF20		OBJECT-TYPE
			SYNTAX	INTEGER
			ACCESS	read-only
			STATUS	current
	DESCRIPTION ""
			::= { mbusFD 70 }

mbusFDValue20		OBJECT-TYPE
			SYNTAX	INTEGER
			ACCESS	read-only
			STATUS	current
	DESCRIPTION ""
			::= { mbusFD 71 }

mbusFDVIF21		OBJECT-TYPE
			SYNTAX	INTEGER
			ACCESS	read-only
			STATUS	current
	DESCRIPTION ""
			::= { mbusFD 72 }

mbusFDValue21		OBJECT-TYPE
			SYNTAX	INTEGER
			ACCESS	read-only
			STATUS	current
	DESCRIPTION ""
			::= { mbusFD 73 }

mbusFDVIF22		OBJECT-TYPE
			SYNTAX	INTEGER
			ACCESS	read-only
			STATUS	current
	DESCRIPTION ""
			::= { mbusFD 74 }

mbusFDValue22		OBJECT-TYPE
			SYNTAX	INTEGER
			ACCESS	read-only
			STATUS	current
	DESCRIPTION ""
			::= { mbusFD 75 }

mbusFDVIF23		OBJECT-TYPE
			SYNTAX	INTEGER
			ACCESS	read-only
			STATUS	current
	DESCRIPTION ""
			::= { mbusFD 76 }

mbusFDValue23		OBJECT-TYPE
			SYNTAX	INTEGER
			ACCESS	read-only
			STATUS	current
	DESCRIPTION ""
			::= { mbusFD 77 }

mbusFDVIF24		OBJECT-TYPE
			SYNTAX	INTEGER
			ACCESS	read-only
			STATUS	current
	DESCRIPTION ""
			::= { mbusFD 78 }

mbusFDValue24		OBJECT-TYPE
			SYNTAX	INTEGER
			ACCESS	read-only
			STATUS	current
	DESCRIPTION ""
			::= { mbusFD 79 }

mbusFDVIF25		OBJECT-TYPE
			SYNTAX	INTEGER
			ACCESS	read-only
			STATUS	current
	DESCRIPTION ""
			::= { mbusFD 80 }

mbusFDValue25		OBJECT-TYPE
			SYNTAX	INTEGER
			ACCESS	read-only
			STATUS	current
	DESCRIPTION ""
			::= { mbusFD 81 }

mbusFDVIF26		OBJECT-TYPE
			SYNTAX	INTEGER
			ACCESS	read-only
			STATUS	current
	DESCRIPTION ""
			::= { mbusFD 82 }

mbusFDValue26		OBJECT-TYPE
			SYNTAX	INTEGER
			ACCESS	read-only
			STATUS	current
	DESCRIPTION ""
			::= { mbusFD 83 }

mbusFDVIF27		OBJECT-TYPE
			SYNTAX	INTEGER
			ACCESS	read-only
			STATUS	current
	DESCRIPTION ""
			::= { mbusFD 84 }

mbusFDValue27		OBJECT-TYPE
			SYNTAX	INTEGER
			ACCESS	read-only
			STATUS	current
	DESCRIPTION ""
			::= { mbusFD 85 }

mbusFDVIF28		OBJECT-TYPE
			SYNTAX	INTEGER
			ACCESS	read-only
			STATUS	current
	DESCRIPTION ""
			::= { mbusFD 86 }

mbusFDValue28		OBJECT-TYPE
			SYNTAX	INTEGER
			ACCESS	read-only
			STATUS	current
	DESCRIPTION ""
			::= { mbusFD 87 }

mbusFDVIF29		OBJECT-TYPE
			SYNTAX	INTEGER
			ACCESS	read-only
			STATUS	current
	DESCRIPTION ""
			::= { mbusFD 88 }

mbusFDValue29		OBJECT-TYPE
			SYNTAX	INTEGER
			ACCESS	read-only
			STATUS	current
	DESCRIPTION ""
			::= { mbusFD 89 }

mbusFDVIF2A		OBJECT-TYPE
			SYNTAX	INTEGER
			ACCESS	read-only
			STATUS	current
	DESCRIPTION ""
			::= { mbusFD 90 }

mbusFDValue2A		OBJECT-TYPE
			SYNTAX	INTEGER
			ACCESS	read-only
			STATUS	current
	DESCRIPTION ""
			::= { mbusFD 91 }

mbusFDVIF2B		OBJECT-TYPE
			SYNTAX	INTEGER
			ACCESS	read-only
			STATUS	current
	DESCRIPTION ""
			::= { mbusFD 92 }

mbusFDValue2B		OBJECT-TYPE
			SYNTAX	INTEGER
			ACCESS	read-only
			STATUS	current
	DESCRIPTION ""
			::= { mbusFD 93 }

mbusFDVIF2C		OBJECT-TYPE
			SYNTAX	INTEGER
			ACCESS	read-only
			STATUS	current
	DESCRIPTION ""
			::= { mbusFD 94 }

mbusFDValue2C		OBJECT-TYPE
			SYNTAX	INTEGER
			ACCESS	read-only
			STATUS	current
	DESCRIPTION ""
			::= { mbusFD 95 }

mbusFDVIF2D		OBJECT-TYPE
			SYNTAX	INTEGER
			ACCESS	read-only
			STATUS	current
	DESCRIPTION ""
			::= { mbusFD 96 }

mbusFDValue2D		OBJECT-TYPE
			SYNTAX	INTEGER
			ACCESS	read-only
			STATUS	current
	DESCRIPTION ""
			::= { mbusFD 97 }

mbusFDVIF2E		OBJECT-TYPE
			SYNTAX	INTEGER
			ACCESS	read-only
			STATUS	current
	DESCRIPTION ""
			::= { mbusFD 98 }

mbusFDValue2E		OBJECT-TYPE
			SYNTAX	INTEGER
			ACCESS	read-only
			STATUS	current
	DESCRIPTION ""
			::= { mbusFD 99 }

mbusFDVIF2F		OBJECT-TYPE
			SYNTAX	INTEGER
			ACCESS	read-only
			STATUS	current
	DESCRIPTION ""
			::= { mbusFD 100 }

mbusFDValue2F		OBJECT-TYPE
			SYNTAX	INTEGER
			ACCESS	read-only
			STATUS	current
	DESCRIPTION ""
			::= { mbusFD 101 }

mbusFE			OBJECT IDENTIFIER ::= { mbus 254 }

mbusFEIdNumber		OBJECT-TYPE
			SYNTAX	Gauge
			ACCESS	read-only
			STATUS	current
	DESCRIPTION ""
			::= { mbusFE 1 }

mbusFEManufacturer	OBJECT-TYPE
			SYNTAX	Gauge
			ACCESS	read-only
			STATUS	current
	DESCRIPTION ""
			::= { mbusFE 2 }

mbusFEVersion		OBJECT-TYPE
			SYNTAX	Gauge
			ACCESS	read-only
			STATUS	current
	DESCRIPTION ""
			::= { mbusFE 3 }

mbusFEMedium		OBJECT-TYPE
			SYNTAX	Gauge
			ACCESS	read-only
			STATUS	current
	DESCRIPTION ""
			::= { mbusFE 4 }

mbusFEStatus		OBJECT-TYPE
			SYNTAX	Gauge
			ACCESS	read-only
			STATUS	current
	DESCRIPTION ""
			::= { mbusFE 5 }

mbusFEVIF00		OBJECT-TYPE
			SYNTAX	INTEGER
			ACCESS	read-only
			STATUS	current
	DESCRIPTION ""
			::= { mbusFE 6 }

mbusFEValue00		OBJECT-TYPE
			SYNTAX	INTEGER
			ACCESS	read-only
			STATUS	current
	DESCRIPTION ""
			::= { mbusFE 7 }

mbusFEVIF01		OBJECT-TYPE
			SYNTAX	INTEGER
			ACCESS	read-only
			STATUS	current
	DESCRIPTION ""
			::= { mbusFE 8 }

mbusFEValue01		OBJECT-TYPE
			SYNTAX	INTEGER
			ACCESS	read-only
			STATUS	current
	DESCRIPTION ""
			::= { mbusFE 9 }

mbusFEVIF02		OBJECT-TYPE
			SYNTAX	INTEGER
			ACCESS	read-only
			STATUS	current
	DESCRIPTION ""
			::= { mbusFE 10 }

mbusFEValue02		OBJECT-TYPE
			SYNTAX	INTEGER
			ACCESS	read-only
			STATUS	current
	DESCRIPTION ""
			::= { mbusFE 11 }

mbusFEVIF03		OBJECT-TYPE
			SYNTAX	INTEGER
			ACCESS	read-only
			STATUS	current
	DESCRIPTION ""
			::= { mbusFE 12 }

mbusFEValue03		OBJECT-TYPE
			SYNTAX	INTEGER
			ACCESS	read-only
			STATUS	current
	DESCRIPTION ""
			::= { mbusFE 13 }

mbusFEVIF04		OBJECT-TYPE
			SYNTAX	INTEGER
			ACCESS	read-only
			STATUS	current
	DESCRIPTION ""
			::= { mbusFE 14 }

mbusFEValue04		OBJECT-TYPE
			SYNTAX	INTEGER
			ACCESS	read-only
			STATUS	current
	DESCRIPTION ""
			::= { mbusFE 15 }

mbusFEVIF05		OBJECT-TYPE
			SYNTAX	INTEGER
			ACCESS	read-only
			STATUS	current
	DESCRIPTION ""
			::= { mbusFE 16 }

mbusFEValue05		OBJECT-TYPE
			SYNTAX	INTEGER
			ACCESS	read-only
			STATUS	current
	DESCRIPTION ""
			::= { mbusFE 17 }

mbusFEVIF06		OBJECT-TYPE
			SYNTAX	INTEGER
			ACCESS	read-only
			STATUS	current
	DESCRIPTION ""
			::= { mbusFE 18 }

mbusFEValue06		OBJECT-TYPE
			SYNTAX	INTEGER
			ACCESS	read-only
			STATUS	current
	DESCRIPTION ""
			::= { mbusFE 19 }

mbusFEVIF07		OBJECT-TYPE
			SYNTAX	INTEGER
			ACCESS	read-only
			STATUS	current
	DESCRIPTION ""
			::= { mbusFE 20 }

mbusFEValue07		OBJECT-TYPE
			SYNTAX	INTEGER
			ACCESS	read-only
			STATUS	current
	DESCRIPTION ""
			::= { mbusFE 21 }

mbusFEVIF08		OBJECT-TYPE
			SYNTAX	INTEGER
			ACCESS	read-only
			STATUS	current
	DESCRIPTION ""
			::= { mbusFE 22 }

mbusFEValue08		OBJECT-TYPE
			SYNTAX	INTEGER
			ACCESS	read-only
			STATUS	current
	DESCRIPTION ""
			::= { mbusFE 23 }

mbusFEVIF09		OBJECT-TYPE
			SYNTAX	INTEGER
			ACCESS	read-only
			STATUS	current
	DESCRIPTION ""
			::= { mbusFE 24 }

mbusFEValue09		OBJECT-TYPE
			SYNTAX	INTEGER
			ACCESS	read-only
			STATUS	current
	DESCRIPTION ""
			::= { mbusFE 25 }

mbusFEVIF0A		OBJECT-TYPE
			SYNTAX	INTEGER
			ACCESS	read-only
			STATUS	current
	DESCRIPTION ""
			::= { mbusFE 26 }

mbusFEValue0A		OBJECT-TYPE
			SYNTAX	INTEGER
			ACCESS	read-only
			STATUS	current
	DESCRIPTION ""
			::= { mbusFE 27 }

mbusFEVIF0B		OBJECT-TYPE
			SYNTAX	INTEGER
			ACCESS	read-only
			STATUS	current
	DESCRIPTION ""
			::= { mbusFE 28 }

mbusFEValue0B		OBJECT-TYPE
			SYNTAX	INTEGER
			ACCESS	read-only
			STATUS	current
	DESCRIPTION ""
			::= { mbusFE 29 }

mbusFEVIF0C		OBJECT-TYPE
			SYNTAX	INTEGER
			ACCESS	read-only
			STATUS	current
	DESCRIPTION ""
			::= { mbusFE 30 }

mbusFEValue0C		OBJECT-TYPE
			SYNTAX	INTEGER
			ACCESS	read-only
			STATUS	current
	DESCRIPTION ""
			::= { mbusFE 31 }

mbusFEVIF0D		OBJECT-TYPE
			SYNTAX	INTEGER
			ACCESS	read-only
			STATUS	current
	DESCRIPTION ""
			::= { mbusFE 32 }

mbusFEValue0D		OBJECT-TYPE
			SYNTAX	INTEGER
			ACCESS	read-only
			STATUS	current
	DESCRIPTION ""
			::= { mbusFE 33 }

mbusFEVIF0E		OBJECT-TYPE
			SYNTAX	INTEGER
			ACCESS	read-only
			STATUS	current
	DESCRIPTION ""
			::= { mbusFE 34 }

mbusFEValue0E		OBJECT-TYPE
			SYNTAX	INTEGER
			ACCESS	read-only
			STATUS	current
	DESCRIPTION ""
			::= { mbusFE 35 }

mbusFEVIF0F		OBJECT-TYPE
			SYNTAX	INTEGER
			ACCESS	read-only
			STATUS	current
	DESCRIPTION ""
			::= { mbusFE 36 }

mbusFEValue0F		OBJECT-TYPE
			SYNTAX	INTEGER
			ACCESS	read-only
			STATUS	current
	DESCRIPTION ""
			::= { mbusFE 37 }

mbusFEVIF10		OBJECT-TYPE
			SYNTAX	INTEGER
			ACCESS	read-only
			STATUS	current
	DESCRIPTION ""
			::= { mbusFE 38 }

mbusFEValue10		OBJECT-TYPE
			SYNTAX	INTEGER
			ACCESS	read-only
			STATUS	current
	DESCRIPTION ""
			::= { mbusFE 39 }

mbusFEVIF11		OBJECT-TYPE
			SYNTAX	INTEGER
			ACCESS	read-only
			STATUS	current
	DESCRIPTION ""
			::= { mbusFE 40 }

mbusFEValue11		OBJECT-TYPE
			SYNTAX	INTEGER
			ACCESS	read-only
			STATUS	current
	DESCRIPTION ""
			::= { mbusFE 41 }

mbusFEVIF12		OBJECT-TYPE
			SYNTAX	INTEGER
			ACCESS	read-only
			STATUS	current
	DESCRIPTION ""
			::= { mbusFE 42 }

mbusFEValue12		OBJECT-TYPE
			SYNTAX	INTEGER
			ACCESS	read-only
			STATUS	current
	DESCRIPTION ""
			::= { mbusFE 43 }

mbusFEVIF13		OBJECT-TYPE
			SYNTAX	INTEGER
			ACCESS	read-only
			STATUS	current
	DESCRIPTION ""
			::= { mbusFE 44 }

mbusFEValue13		OBJECT-TYPE
			SYNTAX	INTEGER
			ACCESS	read-only
			STATUS	current
	DESCRIPTION ""
			::= { mbusFE 45 }

mbusFEVIF14		OBJECT-TYPE
			SYNTAX	INTEGER
			ACCESS	read-only
			STATUS	current
	DESCRIPTION ""
			::= { mbusFE 46 }

mbusFEValue14		OBJECT-TYPE
			SYNTAX	INTEGER
			ACCESS	read-only
			STATUS	current
	DESCRIPTION ""
			::= { mbusFE 47 }

mbusFEVIF15		OBJECT-TYPE
			SYNTAX	INTEGER
			ACCESS	read-only
			STATUS	current
	DESCRIPTION ""
			::= { mbusFE 48 }

mbusFEValue15		OBJECT-TYPE
			SYNTAX	INTEGER
			ACCESS	read-only
			STATUS	current
	DESCRIPTION ""
			::= { mbusFE 49 }

mbusFEVIF16		OBJECT-TYPE
			SYNTAX	INTEGER
			ACCESS	read-only
			STATUS	current
	DESCRIPTION ""
			::= { mbusFE 50 }

mbusFEValue16		OBJECT-TYPE
			SYNTAX	INTEGER
			ACCESS	read-only
			STATUS	current
	DESCRIPTION ""
			::= { mbusFE 51 }

mbusFEVIF17		OBJECT-TYPE
			SYNTAX	INTEGER
			ACCESS	read-only
			STATUS	current
	DESCRIPTION ""
			::= { mbusFE 52 }

mbusFEValue17		OBJECT-TYPE
			SYNTAX	INTEGER
			ACCESS	read-only
			STATUS	current
	DESCRIPTION ""
			::= { mbusFE 53 }

mbusFEVIF18		OBJECT-TYPE
			SYNTAX	INTEGER
			ACCESS	read-only
			STATUS	current
	DESCRIPTION ""
			::= { mbusFE 54 }

mbusFEValue18		OBJECT-TYPE
			SYNTAX	INTEGER
			ACCESS	read-only
			STATUS	current
	DESCRIPTION ""
			::= { mbusFE 55 }

mbusFEVIF19		OBJECT-TYPE
			SYNTAX	INTEGER
			ACCESS	read-only
			STATUS	current
	DESCRIPTION ""
			::= { mbusFE 56 }

mbusFEValue19		OBJECT-TYPE
			SYNTAX	INTEGER
			ACCESS	read-only
			STATUS	current
	DESCRIPTION ""
			::= { mbusFE 57 }

mbusFEVIF1A		OBJECT-TYPE
			SYNTAX	INTEGER
			ACCESS	read-only
			STATUS	current
	DESCRIPTION ""
			::= { mbusFE 58 }

mbusFEValue1A		OBJECT-TYPE
			SYNTAX	INTEGER
			ACCESS	read-only
			STATUS	current
	DESCRIPTION ""
			::= { mbusFE 59 }

mbusFEVIF1B		OBJECT-TYPE
			SYNTAX	INTEGER
			ACCESS	read-only
			STATUS	current
	DESCRIPTION ""
			::= { mbusFE 60 }

mbusFEValue1B		OBJECT-TYPE
			SYNTAX	INTEGER
			ACCESS	read-only
			STATUS	current
	DESCRIPTION ""
			::= { mbusFE 61 }

mbusFEVIF1C		OBJECT-TYPE
			SYNTAX	INTEGER
			ACCESS	read-only
			STATUS	current
	DESCRIPTION ""
			::= { mbusFE 62 }

mbusFEValue1C		OBJECT-TYPE
			SYNTAX	INTEGER
			ACCESS	read-only
			STATUS	current
	DESCRIPTION ""
			::= { mbusFE 63 }

mbusFEVIF1D		OBJECT-TYPE
			SYNTAX	INTEGER
			ACCESS	read-only
			STATUS	current
	DESCRIPTION ""
			::= { mbusFE 64 }

mbusFEValue1D		OBJECT-TYPE
			SYNTAX	INTEGER
			ACCESS	read-only
			STATUS	current
	DESCRIPTION ""
			::= { mbusFE 65 }

mbusFEVIF1E		OBJECT-TYPE
			SYNTAX	INTEGER
			ACCESS	read-only
			STATUS	current
	DESCRIPTION ""
			::= { mbusFE 66 }

mbusFEValue1E		OBJECT-TYPE
			SYNTAX	INTEGER
			ACCESS	read-only
			STATUS	current
	DESCRIPTION ""
			::= { mbusFE 67 }

mbusFEVIF1F		OBJECT-TYPE
			SYNTAX	INTEGER
			ACCESS	read-only
			STATUS	current
	DESCRIPTION ""
			::= { mbusFE 68 }

mbusFEValue1F		OBJECT-TYPE
			SYNTAX	INTEGER
			ACCESS	read-only
			STATUS	current
	DESCRIPTION ""
			::= { mbusFE 69 }

mbusFEVIF20		OBJECT-TYPE
			SYNTAX	INTEGER
			ACCESS	read-only
			STATUS	current
	DESCRIPTION ""
			::= { mbusFE 70 }

mbusFEValue20		OBJECT-TYPE
			SYNTAX	INTEGER
			ACCESS	read-only
			STATUS	current
	DESCRIPTION ""
			::= { mbusFE 71 }

mbusFEVIF21		OBJECT-TYPE
			SYNTAX	INTEGER
			ACCESS	read-only
			STATUS	current
	DESCRIPTION ""
			::= { mbusFE 72 }

mbusFEValue21		OBJECT-TYPE
			SYNTAX	INTEGER
			ACCESS	read-only
			STATUS	current
	DESCRIPTION ""
			::= { mbusFE 73 }

mbusFEVIF22		OBJECT-TYPE
			SYNTAX	INTEGER
			ACCESS	read-only
			STATUS	current
	DESCRIPTION ""
			::= { mbusFE 74 }

mbusFEValue22		OBJECT-TYPE
			SYNTAX	INTEGER
			ACCESS	read-only
			STATUS	current
	DESCRIPTION ""
			::= { mbusFE 75 }

mbusFEVIF23		OBJECT-TYPE
			SYNTAX	INTEGER
			ACCESS	read-only
			STATUS	current
	DESCRIPTION ""
			::= { mbusFE 76 }

mbusFEValue23		OBJECT-TYPE
			SYNTAX	INTEGER
			ACCESS	read-only
			STATUS	current
	DESCRIPTION ""
			::= { mbusFE 77 }

mbusFEVIF24		OBJECT-TYPE
			SYNTAX	INTEGER
			ACCESS	read-only
			STATUS	current
	DESCRIPTION ""
			::= { mbusFE 78 }

mbusFEValue24		OBJECT-TYPE
			SYNTAX	INTEGER
			ACCESS	read-only
			STATUS	current
	DESCRIPTION ""
			::= { mbusFE 79 }

mbusFEVIF25		OBJECT-TYPE
			SYNTAX	INTEGER
			ACCESS	read-only
			STATUS	current
	DESCRIPTION ""
			::= { mbusFE 80 }

mbusFEValue25		OBJECT-TYPE
			SYNTAX	INTEGER
			ACCESS	read-only
			STATUS	current
	DESCRIPTION ""
			::= { mbusFE 81 }

mbusFEVIF26		OBJECT-TYPE
			SYNTAX	INTEGER
			ACCESS	read-only
			STATUS	current
	DESCRIPTION ""
			::= { mbusFE 82 }

mbusFEValue26		OBJECT-TYPE
			SYNTAX	INTEGER
			ACCESS	read-only
			STATUS	current
	DESCRIPTION ""
			::= { mbusFE 83 }

mbusFEVIF27		OBJECT-TYPE
			SYNTAX	INTEGER
			ACCESS	read-only
			STATUS	current
	DESCRIPTION ""
			::= { mbusFE 84 }

mbusFEValue27		OBJECT-TYPE
			SYNTAX	INTEGER
			ACCESS	read-only
			STATUS	current
	DESCRIPTION ""
			::= { mbusFE 85 }

mbusFEVIF28		OBJECT-TYPE
			SYNTAX	INTEGER
			ACCESS	read-only
			STATUS	current
	DESCRIPTION ""
			::= { mbusFE 86 }

mbusFEValue28		OBJECT-TYPE
			SYNTAX	INTEGER
			ACCESS	read-only
			STATUS	current
	DESCRIPTION ""
			::= { mbusFE 87 }

mbusFEVIF29		OBJECT-TYPE
			SYNTAX	INTEGER
			ACCESS	read-only
			STATUS	current
	DESCRIPTION ""
			::= { mbusFE 88 }

mbusFEValue29		OBJECT-TYPE
			SYNTAX	INTEGER
			ACCESS	read-only
			STATUS	current
	DESCRIPTION ""
			::= { mbusFE 89 }

mbusFEVIF2A		OBJECT-TYPE
			SYNTAX	INTEGER
			ACCESS	read-only
			STATUS	current
	DESCRIPTION ""
			::= { mbusFE 90 }

mbusFEValue2A		OBJECT-TYPE
			SYNTAX	INTEGER
			ACCESS	read-only
			STATUS	current
	DESCRIPTION ""
			::= { mbusFE 91 }

mbusFEVIF2B		OBJECT-TYPE
			SYNTAX	INTEGER
			ACCESS	read-only
			STATUS	current
	DESCRIPTION ""
			::= { mbusFE 92 }

mbusFEValue2B		OBJECT-TYPE
			SYNTAX	INTEGER
			ACCESS	read-only
			STATUS	current
	DESCRIPTION ""
			::= { mbusFE 93 }

mbusFEVIF2C		OBJECT-TYPE
			SYNTAX	INTEGER
			ACCESS	read-only
			STATUS	current
	DESCRIPTION ""
			::= { mbusFE 94 }

mbusFEValue2C		OBJECT-TYPE
			SYNTAX	INTEGER
			ACCESS	read-only
			STATUS	current
	DESCRIPTION ""
			::= { mbusFE 95 }

mbusFEVIF2D		OBJECT-TYPE
			SYNTAX	INTEGER
			ACCESS	read-only
			STATUS	current
	DESCRIPTION ""
			::= { mbusFE 96 }

mbusFEValue2D		OBJECT-TYPE
			SYNTAX	INTEGER
			ACCESS	read-only
			STATUS	current
	DESCRIPTION ""
			::= { mbusFE 97 }

mbusFEVIF2E		OBJECT-TYPE
			SYNTAX	INTEGER
			ACCESS	read-only
			STATUS	current
	DESCRIPTION ""
			::= { mbusFE 98 }

mbusFEValue2E		OBJECT-TYPE
			SYNTAX	INTEGER
			ACCESS	read-only
			STATUS	current
	DESCRIPTION ""
			::= { mbusFE 99 }

mbusFEVIF2F		OBJECT-TYPE
			SYNTAX	INTEGER
			ACCESS	read-only
			STATUS	current
	DESCRIPTION ""
			::= { mbusFE 100 }

mbusFEValue2F		OBJECT-TYPE
			SYNTAX	INTEGER
			ACCESS	read-only
			STATUS	current
	DESCRIPTION ""
			::= { mbusFE 101 }

END
