-- *****************************************************************
-- CISCO-DIST-DIRECTOR-CAPABILITY.my:
-- 	Cisco Distributed Director MIB AGENT-CAPABILITIES
-- 
-- April 2002, Jun Xie
-- 
-- Copyright (c) 2002 by Cisco Systems, Inc.
-- All rights reserved.
-- 
-- *****************************************************************

CISCO-DIST-DIRECTOR-CAPABILITY DEFINITIONS ::= BEGIN

IMPORTS
	MODULE-IDENTITY
		FROM SNMPv2-SMI
	AGENT-CAPABILITIES
		FROM SNMPv2-CONF
	ciscoAgentCapability
		FROM CISCO-SMI;

ciscoDistDirCapability MODULE-IDENTITY
	LAST-UPDATED	"200204230000Z"
	ORGANIZATION    "Cisco Systems, Inc."
	CONTACT-INFO
		"	Cisco Systems
			Customer Service

		Postal:	170 West Tasman Drive
			San Jose, CA  95134
			USA

		   Tel:	+1 800 553-NETS

		E-mail:	cs-dd@cisco.com"
	DESCRIPTION
		"Agent capabilities for CISCO-DIST-DIRECTOR-MIB"
	REVISION	"200204230000Z"
	DESCRIPTION
		"Initial version of this MIB module."
	::= { ciscoAgentCapability 267 }

ciscoDistDirCapabilityV12R02 AGENT-CAPABILITIES
	PRODUCT-RELEASE "Cisco IOS 12.2(8)T"
	STATUS		current
	DESCRIPTION	"Cisco Distributed Director MIB capabilities"

	SUPPORTS	CISCO-DIST-DIRECTOR-MIB
	INCLUDES	{ ciscoDistDirGeneralGroup,
			  ciscoDistDirHostGroup,
			  ciscoDistDirServerGroup,
			  ciscoDistDirMappingGroup,
			  ciscoDistDirNotificationGroup
			}

	VARIATION	cddGeneralMetricProfPriority
	ACCESS		read-only
	DESCRIPTION	"Create and write are not yet supported."

	VARIATION	cddGeneralMetricProfWeight
	ACCESS		read-only
	DESCRIPTION	"Create and write are not yet supported."

	VARIATION	cddGeneralMetricProfRowStatus
	ACCESS		read-only
	DESCRIPTION	"Create and write are not yet supported."

	VARIATION	cddGeneralCacheEnable
	ACCESS		read-only
	DESCRIPTION	"Write is not yet supported."

	VARIATION	cddGeneralCacheTime
	ACCESS		read-only
	DESCRIPTION	"Write is not yet supported."

	VARIATION	cddGeneralTTL
	ACCESS		read-only
	DESCRIPTION	"Write is not yet supported."

	VARIATION	cddGeneralDefPriorityWeight
	ACCESS		read-only
	DESCRIPTION	"Write is not yet supported."

	VARIATION	cddHostServicePort
	ACCESS		read-only
	DESCRIPTION	"Create and write are not yet supported."

	VARIATION	cddHostPriorityWeight
	ACCESS		read-only
	DESCRIPTION	"Create and write are not yet supported."

	VARIATION	cddHostDrpMed
	ACCESS		read-only
	DESCRIPTION	"Create and write are not yet supported."

	VARIATION	cddHostDrpRttProbes
	ACCESS		read-only
	DESCRIPTION	"Create and write are not yet supported."

	VARIATION	cddHostDrpRttTol
	ACCESS		read-only
	DESCRIPTION	"Create and write are not yet supported."

	VARIATION	cddHostAccessControl
	ACCESS		read-only
	DESCRIPTION	"Create and write are not yet supported."

	VARIATION	cddHostMultipleRecord
	ACCESS		read-only
	DESCRIPTION	"Create and write are not yet supported."

	VARIATION	cddHostLogging
	ACCESS		read-only
	DESCRIPTION	"Create and write are not yet supported."

	VARIATION	cddHostUrlString
	ACCESS		read-only
	DESCRIPTION	"Create and write are not yet supported."

	VARIATION	cddHostUrlIntv
	ACCESS		read-only
	DESCRIPTION	"Create and write are not yet supported."

	VARIATION	cddHostRowStatus
	ACCESS		read-only
	DESCRIPTION	"Create and write are not yet supported."

	VARIATION	cddHostConnectCfgIntv
	ACCESS		read-only
	DESCRIPTION	"Create and write are not yet supported."

	VARIATION	cddHostConnectCfgRowStatus
	ACCESS		read-only
	DESCRIPTION	"Create and write are not yet supported."

	VARIATION	cddHostTolCfgPerc
	ACCESS		read-only
	DESCRIPTION	"Create and write are not yet supported."

	VARIATION	cddHostTolCfgRowStatus
	ACCESS		read-only
	DESCRIPTION	"Create and write are not yet supported."

	VARIATION	cddServerDrpAddrType
	ACCESS		read-only
	DESCRIPTION	"Create and write are not yet supported."

	VARIATION	cddServerDrpAddr
	ACCESS		read-only
	DESCRIPTION	"Create and write are not yet supported."

	VARIATION	cddServerAdmin
	ACCESS		read-only
	DESCRIPTION	"Create and write are not yet supported."

	VARIATION	cddServerPortion
	ACCESS		read-only
	DESCRIPTION	"Create and write are not yet supported."

	VARIATION	cddServerName
	ACCESS		read-only
	DESCRIPTION	"Create and write are not yet supported."

	VARIATION	cddServerAvail
	ACCESS		read-only
	DESCRIPTION	"Create and write are not yet supported."

	VARIATION	cddServerRowStatus
	ACCESS		read-only
	DESCRIPTION	"Create and write are not yet supported."

	VARIATION	cddServerPortAdmin
	ACCESS		read-only
	DESCRIPTION	"Create and write are not yet supported."

	VARIATION	cddServerPortConnIntv
	ACCESS		read-only
	DESCRIPTION	"Create and write are not yet supported."

	VARIATION	cddServerPortPortion
	ACCESS		read-only
	DESCRIPTION	"Create and write are not yet supported."

	VARIATION	cddServerPortAvail
	ACCESS		read-only
	DESCRIPTION	"Create and write are not yet supported."

	VARIATION	cddServerPortUrlString
	ACCESS		read-only
	DESCRIPTION	"Create and write are not yet supported."

	VARIATION	cddServerPortUrlIntv
	ACCESS		read-only
	DESCRIPTION	"Create and write are not yet supported."

	VARIATION	cddServerPortRowStatus
	ACCESS		read-only
	DESCRIPTION	"Create and write are not yet supported."

	VARIATION	cddServerPortMetricWeight
	ACCESS		read-only
	DESCRIPTION	"Create and write are not yet supported."

	VARIATION	cddServerPortMetricRowStatus
	ACCESS		read-only
	DESCRIPTION	"Create and write are not yet supported."

	VARIATION	cddHostServerMappingRowStatus
	ACCESS		read-only
	DESCRIPTION	"Create and write are not yet supported."

::= { ciscoDistDirCapability 1 }

END
