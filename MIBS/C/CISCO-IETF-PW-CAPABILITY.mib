-- *****************************************************************
-- CISCO-IETF-PW-CAPABILITY.my:  Capability statement for 
--     Cisco's implementation of the IETF PW-MIB
--
-- Febuary 2005 - Tim Swanson
--
-- Copyright (c) 2004, 2005 by Cisco Systems, Inc.
-- All rights reserved.
-- 
-- *****************************************************************

CISCO-IETF-PW-CAPABILITY DEFINITIONS ::= BEGIN

IMPORTS
   MODULE-IDENTITY
      FROM SNMPv2-SMI

   AGENT-CAPABILITIES 
      FROM SNMPv2-CONF

   ciscoAgentCapability
      FROM CISCO-SMI;

   
ciscoIetfPwCapability MODULE-IDENTITY
        LAST-UPDATED   "200502091200Z" -- 09 Feb 2005 12:00:00
        ORGANIZATION   "Cisco Systems, Inc."
        CONTACT-INFO
                "       Cisco Systems
                        Customer Service

                Postal: 170 W Tasman Drive
                        San Jose, CA  95134
                        USA

                   Tel: +1 800 553-NETS

                E-mail: mpls-mib@cisco.com"
        DESCRIPTION
                "Agent capabilities for CISCO-IETF-PW-MIB."
        REVISION       "200502091200Z" -- 09 Feb 2005 12:00:00
        DESCRIPTION
                "Initial version:  ciscoIetfPwCapabilityV12R00.
                "
        ::= {  ciscoAgentCapability 432 }

ciscoIetfPwCapabilityV12R00 AGENT-CAPABILITIES

        PRODUCT-RELEASE "Cisco IOS 12.0(28)S, Cisco IOS 12.2"
        STATUS      current
        DESCRIPTION "Pseudowire MIB capabilities"

        SUPPORTS    CISCO-IETF-PW-MIB
        INCLUDES    { 
                      cpwVcGroup,
                      cpwVcPeformanceGroup,
                      cpwVcMappingTablesGroup,
                      cpwVcNotificationsGroup
                    }

        -- cpwVcGroup Variations 
        VARIATION   cpwVcType
        ACCESS      read-only
        DESCRIPTION
            "The implementation does not allow setting this
             object through the MIB."

        VARIATION   cpwVcOwner
        ACCESS      read-only
        DESCRIPTION
            "The implementation does not allow setting this
             object through the MIB."

        VARIATION   cpwVcPsnType
        ACCESS      read-only
        DESCRIPTION
            "The implementation does not allow setting this
             object through the MIB."

        VARIATION   cpwVcSetUpPriority
        ACCESS      read-only
        DESCRIPTION
            "This implementation does not support this object. 
             Therefore, it always returns 0."

        VARIATION   cpwVcHoldingPriority
        ACCESS      read-only
        DESCRIPTION
            "This implementation does not support this object.
             Therefore, it always returns 0."

        VARIATION   cpwVcInboundMode
        ACCESS      read-only
        DESCRIPTION
            "The implementation does not allow setting this
             object through the MIB."

        VARIATION   cpwVcPeerAddrType
        ACCESS      read-only
        DESCRIPTION
            "The implementation does not allow setting this
             object through the MIB."

        VARIATION   cpwVcPeerAddr
        ACCESS      read-only
        DESCRIPTION
            "The implementation does not allow setting this
             object through the MIB."

        VARIATION   cpwVcID
        ACCESS      read-only
        DESCRIPTION
            "The implementation does not allow setting this
             object through the MIB."

        VARIATION   cpwVcLocalGroupID
        ACCESS      read-only
        DESCRIPTION
            "The implementation does not allow setting this
             object through the MIB."

        VARIATION   cpwVcControlWord
        ACCESS      read-only
        DESCRIPTION
            "The implementation does not allow setting this
             object through the MIB."

        VARIATION   cpwVcLocalIfMtu
        ACCESS      read-only
        DESCRIPTION
            "The implementation does not allow setting this
             object through the MIB."

        VARIATION   cpwVcLocalIfString
        ACCESS      read-only
        DESCRIPTION
            "The implementation does not allow setting this
             object through the MIB."

        VARIATION   cpwVcRemoteControlWord
        ACCESS      read-only
        DESCRIPTION
            "The implementation does not allow setting this
             object through the MIB."

        VARIATION   cpwVcOutboundVcLabel
        ACCESS      read-only
        DESCRIPTION
            "The implementation does not allow setting this
             object through the MIB."

        VARIATION   cpwVcInboundVcLabel
        ACCESS      read-only
        DESCRIPTION
            "The implementation does not allow setting this
             object through the MIB."

        VARIATION   cpwVcName
        ACCESS      read-only
        DESCRIPTION
            "The implementation does not allow setting this
             object through the MIB."

        VARIATION   cpwVcDescr
        ACCESS      read-only
        DESCRIPTION
            "The implementation does not allow setting this 
             object through the MIB."

        VARIATION   cpwVcAdminStatus
        ACCESS      read-only
        DESCRIPTION
            "The implementation does not allow setting this 
             object through the MIB."

        VARIATION   cpwVcTimeElapsed
        DESCRIPTION 
            "The cpwVcPerfCurrentTable and cpwVcPerfIntervalTable 
             are not supported.  Therefore this object has no meaning
             and always returns 0."

        VARIATION   cpwVcValidIntervals
        DESCRIPTION 
            "The cpwVcPerfCurrentTable and cpwVcPerfIntervalTable 
             are not supported.  Therefore this object has no meaning
             and always returns 0."

        VARIATION   cpwVcRowStatus
        ACCESS      read-only
        DESCRIPTION 
            "The implementation of the cpwVcTable is 
             read-only and does not allow dynamic creation
             of rows via RowStatus.  This object will 
             always be set to 'active'."

        VARIATION   cpwVcStorageType
        ACCESS      read-only
        DESCRIPTION 
            "The implementation of the cpwVcTable is 
             read-only.  This object will always be set to
             'volatile'."

        VARIATION   cpwVcNotifRate
        ACCESS      read-only
        DESCRIPTION 
            "This object is not implemented and will always 
             return 0."

        -- cpwVcPerformanceGroup Variations
        VARIATION   cpwVcPerfCurrentInHCPackets
        ACCESS      not-implemented
        DESCRIPTION 
            "The cpwVcPerfCurrentTable is not implemented
             in this release."

        VARIATION   cpwVcPerfCurrentInHCBytes
        ACCESS      not-implemented
        DESCRIPTION 
            "The cpwVcPerfCurrentTable is not implemented
             in this release."

        VARIATION   cpwVcPerfCurrentOutHCPackets
        ACCESS      not-implemented
        DESCRIPTION 
            "The cpwVcPerfCurrentTable is not implemented
             in this release."

        VARIATION   cpwVcPerfCurrentOutHCBytes
        ACCESS      not-implemented
        DESCRIPTION 
            "The cpwVcPerfCurrentTable is not implemented
             in this release."

        VARIATION   cpwVcPerfIntervalValidData
        ACCESS      not-implemented
        DESCRIPTION 
            "The cpwVcPerfIntervalTable is not implemented
             in this release."

        VARIATION   cpwVcPerfIntervalTimeElapsed
        ACCESS      not-implemented
        DESCRIPTION 
            "The cpwVcPerfIntervalTable is not implemented
             in this release."

        VARIATION   cpwVcPerfIntervalInHCPackets
        ACCESS      not-implemented
        DESCRIPTION 
            "The cpwVcPerfIntervalTable is not implemented
             in this release."

        VARIATION   cpwVcPerfIntervalInHCBytes
        ACCESS      not-implemented
        DESCRIPTION 
            "The cpwVcPerfIntervalTable is not implemented
             in this release."

        VARIATION   cpwVcPerfIntervalOutHCPackets
        ACCESS      not-implemented
        DESCRIPTION 
            "The cpwVcPerfIntervalTable is not implemented
             in this release."

        VARIATION   cpwVcPerfIntervalOutHCBytes
        ACCESS      not-implemented
        DESCRIPTION 
            "The cpwVcPerfIntervalTable is not implemented
             in this release."

        -- cpwVcNotificationsGroup Variations
        VARIATION   cpwVcDown
        DESCRIPTION 
            "The ability to indicate a range of 
             cpwVcOperStatus entries per notification is not
             supported.  The two instances of cpwVcOperStatus 
             in this notification will always be identical."

        VARIATION   cpwVcUp
        DESCRIPTION 
            "The ability to indicate a range of 
             cpwVcOperStatus entries per notification is not
             supported.  The two instances of cpwVcOperStatus 
             in this notification will always be identical."

        ::= { ciscoIetfPwCapability 1 }

END
