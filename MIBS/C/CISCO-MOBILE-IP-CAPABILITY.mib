-- *******************************************************************
-- CISCO-MOBILE-IP-CAPABILITY.my: 
--                      CISCO-MOBILE-IP-MIB AGENT-CAPABILITIES
--
-- Aug 2005, Ganesh Srinivasan
--
-- Copyright (c) 2005 by Cisco Systems, Inc.
-- All rights reserved.
--
-- *******************************************************************


CISCO-MOBILE-IP-CAPABILITY DEFINITIONS ::= BEGIN

IMPORTS
        MODULE-IDENTITY
                FROM SNMPv2-SMI
        AGENT-CAPABILITIES
                FROM SNMPv2-CONF
        ciscoAgentCapability
                FROM CISCO-SMI;

ciscoMobileIPCapability MODULE-IDENTITY
        LAST-UPDATED    "200509090000Z"
        ORGANIZATION    "Cisco Systems, Inc."
        CONTACT-INFO
                 "       Cisco Systems
                         Customer Service
                        
                 Postal: 170 West Tasman Drive
                         San Jose, CA  95134
                         USA
                        
                    Tel: +1 800 553-NETS
                        
                 E-mail: cs-mobileip@cisco.com"
        DESCRIPTION
                 "Agent capabilities for CISCO-MOBILE-IP-MIB 
                 (MobileIP MIB)."
        REVISION        "200509090000Z"
        DESCRIPTION
                 "Initial version of this MIB module."
        ::= { ciscoAgentCapability 449 }

ciscoMobileIPCapabilityV12R04 AGENT-CAPABILITIES

PRODUCT-RELEASE "Cisco IOS 12.4(3)"
STATUS          current
DESCRIPTION     "Cisco MobileIP mib capabilities"

SUPPORTS        CISCO-MOBILE-IP-MIB
INCLUDES        { ciscoMobileIpHaRedunGroup, 
                  ciscoMobileIpSecViolationGroup,
                  ciscoMobileIpMaRegGroup,
                  ciscoMobileIpFaAdvertisementGroup,
                  ciscoMobileIpFaSystemGroup,
                  ciscoMobileIpMnDiscoveryGroup,
                  ciscoMobileIpMnRegistrationGroup,
                  ciscoMobileIpHaMobNetGroup,
                  ciscoMobileIpMrDiscoveryGroup,
                  ciscoMobileIpMrRegistrationGroup,
                  ciscoMobileIpSecAssocGroupV12R02,
                  cmiMaAdvertisementGroup,
                  ciscoMobileIpFaRegGroupV12R03r2,
                  ciscoMobileIpHaRegGroupV12R03r2,
                  ciscoMobileIpTrapObjectsGroupV2,
                  ciscoMobileIpHaRegGroupV12R03r2,
                  ciscoMobileIpMrNotificationGroupV2,
                  ciscoMobileIpMrSystemGroupV3 }

VARIATION       cmiFaTotalRegRequests
ACCESS          not-implemented
DESCRIPTION     "This object is not supported in the current
                MIB implementation."

VARIATION       cmiFaTotalRegReplies
ACCESS          not-implemented
DESCRIPTION     "This object is not supported in the current
                MIB implementation."

VARIATION       cmiFaMnFaAuthFailures
ACCESS          not-implemented
DESCRIPTION     "This object is not supported in the current
                MIB implementation."

VARIATION       cmiFaMnAAAAuthFailures
ACCESS          not-implemented
DESCRIPTION     "This object is not supported in the current
                MIB implementation."

VARIATION       cmiHaMnHaAuthFailures
ACCESS          not-implemented
DESCRIPTION     "This object is not supported in the current
                MIB implementation."

VARIATION       cmiHaMnAAAAuthFailures
ACCESS          not-implemented
DESCRIPTION     "This object is not supported in the current
                MIB implementation."

VARIATION       cmiNtRegCOA
ACCESS          not-implemented
DESCRIPTION     "This object is not supported in the current
                MIB implementation."

VARIATION       cmiNtRegCOAType
ACCESS          not-implemented
DESCRIPTION     "This object is not supported in the current
                MIB implementation."

VARIATION       cmiNtRegHAAddrType
ACCESS          not-implemented
DESCRIPTION     "This object is not supported in the current
                MIB implementation."

VARIATION       cmiNtRegHomeAgent
ACCESS          not-implemented
DESCRIPTION     "This object is not supported in the current
                MIB implementation."

VARIATION       cmiNtRegHomeAddressType
ACCESS          not-implemented
DESCRIPTION     "This object is not supported in the current
                MIB implementation."

VARIATION       cmiNtRegHomeAddress
ACCESS          not-implemented
DESCRIPTION     "This object is not supported in the current
                MIB implementation."

VARIATION       cmiNtRegNAI
ACCESS          not-implemented
DESCRIPTION     "This object is not supported in the current
                MIB implementation."

VARIATION       cmiNtRegDeniedCode
ACCESS          not-implemented
DESCRIPTION     "This object is not supported in the current
                MIB implementation."

VARIATION       cmiHaMnRegReqFailed
ACCESS          not-implemented
DESCRIPTION     "This object is not supported in the current
                MIB implementation."

        ::= { ciscoMobileIPCapability 1 }

END
