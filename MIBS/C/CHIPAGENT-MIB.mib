--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--

CHIPAGENT-MIB DEFINITIONS ::= BEGIN

IMPORTS
	enterprises, NetworkAddress, IpAddress,
	Counter, Gauge, TimeTicks, DisplayString
		FROM RFC1155-SMI
	OBJECT-TYPE
		FROM RFC-1212;

chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }


-- The chipGen Group
--
-- Implementation of the chipGen group is mandatory for all agent products.
-- 
-- The chipGen Group is used by all agent products.  It provides
-- objects that identify what the product is and who is managing it.
--



chipGenProduct OBJECT-TYPE
	SYNTAX INTEGER {
		product-5100M-MGT(1),	-- EMM
		product-5102B-EE(2),	-- OEBM

		product-8383B(3),	-- Midnight
		product-5112H-UTP(4),	-- 12 port Workgroup Hub

		product-5300M-MGT(5),	-- FMM
		product-5200M-MGT(7)	-- TRMM

	}
	ACCESS read-only
	STATUS mandatory
	DESCRIPTION
		"The product type represented by this agent."
	::= { chipGen 1 }

chipGenServiceDate OBJECT-TYPE
	SYNTAX DisplayString (SIZE(6))
	ACCESS read-only
	STATUS mandatory
	DESCRIPTION
		"The date that the product was last serviced in the
		format yymmdd.  If this date is unknown, the value of this
		object is '000000'."
	::= { chipGen 2 }

chipGenNetman OBJECT-TYPE
	SYNTAX IpAddress
	ACCESS read-only
	STATUS mandatory
	DESCRIPTION
		"The IP (source) Address of the last authenticated SNMP PDU 
		received by this entity before this request.  An IP Address
		of 00.00.00.00 represents the default value."
	::= { chipGen 3 } 

chipGenDiagnostics OBJECT-TYPE
	SYNTAX INTEGER {
		passed(1),
		failed(2)
	}
	ACCESS read-only
	STATUS mandatory
	DESCRIPTION
		"The result of this product's diagnostic test(s).  If
		any test fails, this will have the failed(2) value.
		Note, many products do not operate after a diagnostic
		failure.  In this case, no SNMP communication would
		be available."
	::= { chipGen 4 } 

chipGenSerial OBJECT-TYPE
	SYNTAX DisplayString (SIZE(1..128))
	ACCESS read-only
	STATUS mandatory
	DESCRIPTION
		"The serial number of this product."
	::= { chipGen 5 }

chipGenID OBJECT-TYPE
	SYNTAX INTEGER
	ACCESS read-write
	STATUS mandatory
	DESCRIPTION
		"A unique ID used for grouping disparate agents together.
		For example, a concentrator may contain multiple agents.
		This ID is could be assigned by the management station 
                to identify all of these agents as being contained in the  
		same concentrator."
	::= { chipGen 6 }

chipGenVers OBJECT-TYPE
	SYNTAX DisplayString (SIZE(0..80))
	ACCESS read-only
	STATUS mandatory
	DESCRIPTION
		"The version identifier(s) for this agent."
	::= { chipGen 7 }

chipGenAuthFailureAddr OBJECT-TYPE
	SYNTAX IpAddress
	ACCESS read-only
	STATUS mandatory
	DESCRIPTION
		"The source IP Address of the last SNMP request that caused
		an authentication failure trap to be generated. This
		object is also included in the SNMP authenticationFailure
		trap."
	::= { chipGen 8 }

chipGenTimeLastChanged OBJECT-TYPE
	SYNTAX TimeTicks
	ACCESS read-only
	STATUS mandatory
	DESCRIPTION
		"A snapshot of sysUpTime when the last trap was generated.
		This attribute can be used to save polling by a management
		station.  If there have been no traps generated since the last 
		poll, there is no need for the station to poll again."
	::= { chipGen 9 }



-- The chipEcho Group
--
-- Implementation of the chipEcho group is mandatory for all agent
-- products.
-- 
-- The chipEcho Group is used by a station to initiate a Ping from 
-- this agent to the address denoted by chipEchoAddr.  When all of
-- the pings are sent, the agent issues a ping trap (enterprise specific)
-- reporting the total number of responses received at that time.
--
-- To ping another host, you must minimally set the chipEchoAddr to the
-- host that you want to ping and chipEchoStart to startEcho(2).  The
-- other objects let you change the characteristic of the Ping packets.
-- Note that only one Ping can be processed at a time.
-- 

chipEchoStart OBJECT-TYPE
	SYNTAX INTEGER {
		noEcho(1),
		startEcho(2)
		}
	ACCESS read-write
	STATUS mandatory
	DESCRIPTION
		"Setting chipEchoStart to startEcho(2) causes the device
		to begin an ICMP echo sequence using the parameters 
		indicated by the rest of the chipEcho group."
	::= { chipEcho 1 }

chipEchoAddr OBJECT-TYPE
	SYNTAX IpAddress
	ACCESS read-write
	STATUS mandatory
	DESCRIPTION
		"The IP Address to which the device will ping.  The default
		value is the loopback address 127.0.0.1 ."
	::= { chipEcho 2 }

chipEchoPattern OBJECT-TYPE
	SYNTAX INTEGER {
		zeroes(1),
		ones(2),
		mixed(3)
		}
	ACCESS read-write
	STATUS mandatory
	DESCRIPTION
		"The actual pattern to be contained in the ICMP echo packet."
	::= { chipEcho 3 }


chipEchoNumber OBJECT-TYPE
	SYNTAX INTEGER (1..255)
	ACCESS read-write
	STATUS mandatory
	DESCRIPTION
		"The number of ICMP echo packets (pings) to send."
	::= { chipEcho 4 }


chipEchoSize OBJECT-TYPE
	SYNTAX INTEGER (64..1500)
	ACCESS read-write
	STATUS mandatory
	DESCRIPTION
		"The size of the ICMP echo packet (ping) to send when
		chipEchoStart is set. The valid range is between 64 and
		1500 octets."
	::= { chipEcho 5 }

chipEchoResponseCounts OBJECT-TYPE
	SYNTAX Counter
	ACCESS read-only
	STATUS mandatory
	DESCRIPTION
		"The count of ICMP echo response packets received since
		the last PING was initiated. "
	::= { chipEcho 6 }




-- The chipTTY Group:
-- 
-- The following group is used to manage agent terminal ports.
--
-- 

chipTTYNumber OBJECT-TYPE
	SYNTAX INTEGER
	ACCESS read-only
	STATUS mandatory
	DESCRIPTION
		"The number of terminal ports on this agent product."
	::= { chipTTY 1 }

chipTTYTable OBJECT-TYPE
	SYNTAX  SEQUENCE OF ChipTTYEntry
	ACCESS  not-accessible
	STATUS  mandatory
	DESCRIPTION
		"A table of TTY specific information associated with 
                this agent."
	::= { chipTTY 2 }

chipTTYEntry OBJECT-TYPE
	SYNTAX  ChipTTYEntry
	ACCESS  not-accessible
	STATUS  mandatory
	DESCRIPTION
		"A profile of a specific TTY interface associated with 
		this agent."
	INDEX 	{ chipTTYIndex }
	::= { chipTTYTable 1 }

ChipTTYEntry ::=
	SEQUENCE {
		chipTTYIndex
			INTEGER,
		chipTTYBaud
			INTEGER,
		chipTTYParity
			INTEGER,
		chipTTYStop
			INTEGER,
		chipTTYData
			INTEGER,
		chipTTYTimeout
			INTEGER,
		chipTTYPrompt
			DisplayString,
		chipTTYDTR
			INTEGER,
                chipTTYTerminalType
			DisplayString
		}

chipTTYIndex 	OBJECT-TYPE
	SYNTAX	INTEGER
	ACCESS  read-only
	STATUS	mandatory
	DESCRIPTION
		"The TTY to which this entry refers."
	::= { chipTTYEntry 1 }	

chipTTYBaud 	OBJECT-TYPE
	SYNTAX	INTEGER {
		one-hundred-ten(110),
		three-hundred(300),
		twelve-hundred(1200),
		twenty-four-hundred(2400),
		forty-eight-hundred(4800),
		ninety-six-hundred(9600),	
		nineteen-two-hundred(19200),
		thirty-eight-thousand-four-hundred(38400)
		}
	ACCESS  read-write
	STATUS	mandatory
	DESCRIPTION
		"The baud rate for this TTY. It should be noted that all
		 serial ports do not support all of the above baud rates."
	::= { chipTTYEntry 2 }	

chipTTYParity 	OBJECT-TYPE
	SYNTAX	INTEGER {
		odd(1),
		even(2),
		none(3)
		}
	ACCESS  read-write
	STATUS	mandatory
	DESCRIPTION
		"The parity setting for this TTY."
	::= { chipTTYEntry 3 }	

chipTTYStop 	OBJECT-TYPE
	SYNTAX	INTEGER {
		one(1),
		two(2)
		}
	ACCESS  read-write
	STATUS	mandatory
	DESCRIPTION
		"The number of stop bits for this TTY."
	::= { chipTTYEntry 4 }	

chipTTYData 	OBJECT-TYPE
	SYNTAX	INTEGER {
		seven(7),	
		eight(8)
		}		
	ACCESS  read-write
	STATUS	mandatory
	DESCRIPTION
		"The number of data bits for this TTY."
	::= { chipTTYEntry 5 }	

chipTTYTimeout 	OBJECT-TYPE
	SYNTAX	INTEGER
	ACCESS  read-write
	STATUS	mandatory
	DESCRIPTION
		"The number of minutes to wait before this agent logs out
		an inactive login session on this TTY.
		NOTE: In some implementations, this is a single variable 
                      that is used by all of the terminal and telnet 
                      sessions."
	::= { chipTTYEntry 6 }	

chipTTYPrompt 	OBJECT-TYPE
	SYNTAX	DisplayString (SIZE(0..15))
	ACCESS  read-write
	STATUS	mandatory
	DESCRIPTION
		"The terminal prompt to display on this TTY.
		NOTE: In some implementations, this is a single variable 
                      that is used by all of the terminal and telnet 
                      sessions."
	::= { chipTTYEntry 7 }	

chipTTYDTR 	OBJECT-TYPE
	SYNTAX	INTEGER {
			asserted(1),
			deasserted(2)
		}
	ACCESS  read-write
	STATUS	mandatory
	DESCRIPTION
		"This value dictates the behavior of the RS-232 Data
		Terminal Ready (DTR) signal at the time a session ends
		due to a logout, timeout, or shutdown.  This is used by
		some modems as an indication that they should hangup.
                This variable is only support if the RS-232 port has a 
                DTR signal."
	::= { chipTTYEntry 8 }	

chipTTYTerminalType   OBJECT-TYPE
      SYNTAX  DisplayString (SIZE(1..40))
      ACCESS  read-write
      STATUS  mandatory
      DESCRIPTION
              "A string which indicates the type of terminal that
              is attached to the serial port. It should be noted that
              the string is passed to a telnet server whenever the server
              issues the IAC DO TERMINAL-TYPE command (see rfc884)."
      ::= { chipTTYEntry 9 }

-- The chipTFTP Group
--
-- Implementation of the chipTFTP group is mandatory for all agent
-- products that support TFTP file transfers.
-- 
-- The chipTFTP Group is used by a station to initiate a TFTP transfer
-- from a TFTP server to this agent (the TFTP client).  
--
-- In order to initiate a TFTP file transfer, the client must know
-- the following information:
--
-- 1. The operation to perform, either a get or a put (chipTFTPStart).
-- 2. What station is acting as the TFTP server (chipTFTPIpAddress).
-- 3. The file name (chipTFTPFileName) and the file type (chipTFTPFileType).
--        The file name can be a pathname.  The file type indicates to
--	  the agent what kind of information is being transferred.
-- 4. What module should receive the file (chipTFTPSlot).
--
--
-- For example, if one wished to inband download flash code to this agent,
-- one would set:
--
-- File type 	= Flash code
-- Slot number 	= This agent (255).
-- File name    = Pathname on the server where the file is located.
-- IP Address   = The IP of the TFTP file server.
-- TFTP Start   = get - retrieve the file from the server.
--
-- After setting the start object, the transfer takes place.  The  
-- chipTFTPResult object contains the result of the last TFTP transfer
-- attempted.
-- 

chipTFTPStart OBJECT-TYPE
	SYNTAX INTEGER {
		tftpNoTransfer(1),
		tftpGet(2),	-- download to agent
		tftpPut(3)	-- upload to server
		}
	ACCESS read-write
	STATUS mandatory
	DESCRIPTION
		"Setting chipTFTPStart to tftpGet(2) initiates a file
		transfer to the agent (download); tftpPut(3) initiates
		a file transfer to the server (upload)."
	::= { chipTFTP 1 }

chipTFTPSlot OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		agent-slot(255)
	}
	ACCESS	read-write
	STATUS 	mandatory
	DESCRIPTION
		"The slot number of the module that is to be involved 
		in the TFTP transfer with the TFTP server (chipTFTPIpAddress)."
	::= { chipTFTP 2 }
		
chipTFTPIpAddress OBJECT-TYPE
	SYNTAX IpAddress
	ACCESS read-write
	STATUS mandatory
	DESCRIPTION
		"The IP Address of the TFTP server."
	::= { chipTFTP 3 }

chipTFTPFileName OBJECT-TYPE
	SYNTAX DisplayString (SIZE(0..128))
	ACCESS read-write
	STATUS mandatory
	DESCRIPTION
		"The file name of the file to retrieve (tftpGet), or the 
		name of	the file to create (tftpPut). "
	::= { chipTFTP 4 }


chipTFTPFileType OBJECT-TYPE
	SYNTAX INTEGER {
		flashCode(1),
		bootCode(2)
		}
	ACCESS read-write
	STATUS mandatory
	DESCRIPTION
		"The type of file image to upload/download.  The file
		type indicates to the agent what kind of file it is
		receiving.  flashCode(1) indicates a code upgrade of
		the operational proms.  bootCode(2) indicates a code
		upgrade of the boot proms."
	::= { chipTFTP 5 }


chipTFTPResult OBJECT-TYPE
	SYNTAX INTEGER {
		clear(1),--not initialized
		xferInProgress(2),
		okay(3),
		otherTFTPError(4),
		fileNotFound(5),-- check for valid file name
		accessError(6),
		diskFull(7),-- server disk is full
 		illegalTFTPOperation(8),
		invalidTFTPTransactionID(9),
		noResponse(10),-- check valid server IP address 
		invalidDownloadKey(11),
		invalidSlot(12),
		invalidNetwork(13),
		fepromErase(14),
		fepromProg(15),
		xferError(16),
		decodeError(17)
		}	
	ACCESS read-only
	STATUS mandatory
	DESCRIPTION
		"The result of the last TFTP operation."
	::= { chipTFTP 6 }




-- chipDownload Group
--
-- To begin an in_band download through SNMP the following mib objects 
-- along with the chipTFTP objects must be completed with the correct
-- information.  
--
-- Before download is allowed to begin, the agent will verify the
-- Software Key.  If the Software Key is found to be valid, download
-- will follow.  Otherwise, chipTFTPResult is set to (9)invalidDown-
-- loadKey.


chipDownloadUDKSerial OBJECT-TYPE
	SYNTAX DisplayString (SIZE(0..8))
     	ACCESS read-write
     	STATUS mandatory
     	DESCRIPTION
		"A string representing the serial number of the
		 Upgrade Distribution Kit."
	::= { chipDownload 1 }

chipDownloadKey OBJECT-TYPE
	SYNTAX DisplayString (SIZE(0..8))
	ACCESS read-write
	STATUS mandatory
	DESCRIPTION
		"The key code provided by your VAR. Available by
		 calling technical support at +1 508 460 6195."
	::= { chipDownload 2 }

chipDownloadDateTime OBJECT-TYPE
	SYNTAX DisplayString (SIZE(0..20))
	ACCESS read-only
	STATUS mandatory
	DESCRIPTION
		"The date of the last successful download in the 
		 format hh:mm day DD Mon YY"
	::= { chipDownload 3 }








	

END
