-- *********************************************************************
-- CISCO-FC-FE-MIB.my: Cisco Fibre Channel Fibre Element MIB
--   
-- September 2002, Srini Kode
--   
-- Copyright (c) 2002-2014 by cisco Systems Inc.
-- All rights reserved.
--   
-- *******************************************************************

CISCO-FC-FE-MIB DEFINITIONS ::= BEGIN

IMPORTS
    MODULE-IDENTITY,
    OBJECT-TYPE,
    Counter32,
    Counter64,
    Integer32,
    Unsigned32,
    NOTIFICATION-TYPE
        FROM SNMPv2-SMI
    MODULE-COMPLIANCE,
    OBJECT-GROUP,
    NOTIFICATION-GROUP
        FROM SNMPv2-CONF
    TEXTUAL-CONVENTION,
    TruthValue
        FROM SNMPv2-TC
    SnmpAdminString
        FROM SNMP-FRAMEWORK-MIB
    ifIndex,
    InterfaceIndexOrZero
        FROM IF-MIB
    entPhysicalIndex
        FROM ENTITY-MIB
    MicroSeconds
        FROM CISCO-TC
    FcNameId,
    FcAddressId,
    FcClassOfServices,
    FcPortTypes,
    FcPortTxTypes,
    FcIfSpeed,
    FcPortModuleTypes,
    FcIfServiceStateType
        FROM CISCO-ST-TC
    vsanIndex
        FROM CISCO-VSAN-MIB
    FcList
        FROM CISCO-ZS-MIB
    cieIfOperStatusCause
        FROM CISCO-IF-EXTENSION-MIB
    ciscoMgmt
        FROM CISCO-SMI;


ciscoFcFeMIB MODULE-IDENTITY
    LAST-UPDATED    "201402060000Z"
    ORGANIZATION    "Cisco Systems Inc."
    CONTACT-INFO
            "Cisco Systems
            Customer Service
            Postal: 170 W Tasman Drive
            San Jose, CA  95134
            USA
            Tel: +1 800 553 -NETS
            E-mail: cs-san@cisco.com"
    DESCRIPTION
        "This is the Cisco fibre element management MIB module.
        It covers:
        - Cisco extension to the interface MIB ( IF-MIB )
        - Contains all the groups from FIBRE-CHANNEL-FE-MIB
          relevant to Cisco fabric.
        - Other features specific to Cisco fabric.

        This MIB supports all the port types defined by the
        textual convention FcPortTypes. In addition it also
        supports Nx_port, where Nx_port can be either N_port or
        NL_port. The FC standards define Interconnect_Ports
        to be E_ports or B_Ports.

        This MIB supports Port Channel ports. Port 
        Channel port is a single logical port, which contains 
        multiple physical ports as its members. Presently only 
        E_ports can be a member of Port Channel port.

        In addition it provides GigE and port channel information 
        for all the Gigabit Ethernet (GigE) ports in the fabric.
        Terminology 
                    ELP : Exchange Link parameters 
                    EPP : Exchange Peer Parameters."
    REVISION        "201402060000Z"
    DESCRIPTION
        "-Added the following objects to FcIfEntry:
        fcIfAdminFECState,
        fcIfOperFECState
        -Added the following objects to FcIfErrorEntry:
        fcIfFECCorrectedBlks,
        fcIfFECUncorrectedBlks
        -Added the following new groups:
                fcIfGroupRev4
                fcIfErrorGroupRev3
        -Deprecated cffFcFeMIBComplianceRev13 compliance statement.
        -Added cffFcFeMIBComplianceRev14 compliance statement."
    REVISION        "201304090000Z"
    DESCRIPTION
        "-Added the following objects to FcIfErrorEntry:
        fcIfBBCreditTransistionToZero,
        fcHCIfBBCreditTransistionFromZero,
        fcHCIfBBCreditTransistionToZero."
    REVISION        "201211190000Z"
    DESCRIPTION
        "-Added the following enums for FcIfOperStatusReason:
        ficonNoPortSwapLogicalPort,
        ficonInvalidPortNum,
        remotePortInL2vpnDown,
        suspendedDueToNoLacpPdus,
        fcotValidationFailedAtDriver,
        unsupportedTransceiverMd5DigestNotSame,
        unsupportedTransceiver,
        adminStateConfigChange,
        vlanAllowedList,
        vlanAllowedListOverride,
        vlanAllowedListAdd,
        vlanAllowedRemove,
        vlanCfgStateChange,
        vlanCfgDelete,
        pppPeerNotResponding,
        pppAuthFailed,
        xcvrAuthFailed,
        badFramesRcvdFromLink.
        Also changed the description for 
        fcIfTxWtAvgBBCreditTransitionToZero and
        fcIfBBCreditTransistionFromZero."
    REVISION        "201106150000Z"
    DESCRIPTION
        "-Added the following enums for FcIfOperStatusReason:
        xcvrInitializing,
        xcvrAbsent,
        xcvrInvalid,
        vfcBindingInvalid,
        vlanNotFcoeEnabled,
        pvlanNativeVlanErr,
        ethL2VlanDown,
        ethIntfInvalidBinding,
        pmonFailure,
        l3NotReady,
        speedMismatch,
        flowControlMismatch,
        vdcMode,
        suspendedDueToMinLinks,
        enmPinFailLinkDown,
        inactiveM1PortFpathActiveVlan,
        parentPortDown,
        moduleRemoved,
        corePortMct,
        nonCorePortMct,
        ficonInorderNotActive,
        invalidEncapsulation,
        modemLineDeasserted,
        ipSecHndshkInProgress,
        sfpEthCompliantErr,
        cellularModemUnattached,
        outOfGlblRxBuffers,
        sfpFcCompliantErr,
        ethIntfNotLicensed,
        domainIdsInvalid,
        fabricNameInvalid"
    REVISION        "201008180900Z"
    DESCRIPTION
        "-Added the following objects to FcIfErrorEntry:
        fcIfTimeOutDiscards,
        fcIfOutDiscards,
        fcIfCreditLoss,
        fcIfTxWtAvgBBCreditTransitionToZero.
        -Added the following object to FcIfGigEEntry:
        fcIfGigConnectorType.
        -Added the following new groups:
        fcIfGigEinfoExtGroupRev1
        fcIfErrorGroupRev2    
        -Deprecated cffFcFeMIBComplianceRev11 compliance statement.
        -Added cffFcFeMIBComplianceRev12 compliance statement."
    REVISION        "201003040900Z"
    DESCRIPTION
        "-Added the following enums for FcIfOperStatusReason:
        ipQosMgrPolicyAppFailure,
        pauseRateLimitErrDisabled,
        lstGrpUplinkDown,
        stickyDnLinkFailure,
        routerMacFailure,
        dcxMultipleMsapIds,
        dcxHundredPdusRcvdNoAck,
        enmSatIncompatibleUplink,
        enmLoopDetected,
        nonStickyExternallyDisabled,
        subGroupIdNotAssigned,
        vemUnlicensed,
        profileNotFound,
        nonExistentVlan,
        vlanInvalidType,
        vlanDown,
        vpcPeerUpgrade,
        ipQosDcbxpCompatFailure,
        nonCiscoHbaVfTag,
        domainIdConfigMismatch and
        sfpSpeedMismatch."
    REVISION        "200905130900Z"
    DESCRIPTION
        "-Added the following enums for FcIfOperStatusReason:
        portDisabled,
        tunnelModeNotConfigured,
        tunnelSrcNotConfigured,
        tunnelDstNotConfigured,
        tunnelUnableToResolveSrcIP
        tunnelUnableToResolveDstIP,
        tunnelVrfDown,
        sifAdminDown,
        phyIntfDown,
        ifSifLimitExceeded,
        sifHoldDown,
        noFcoe,
        dcxCompatMismatch,
        isolateBundleLimitExceeded,
        sifNotBound,
        errDisabledLacpMiscfg,
        satFabricIfDown,
        invalidSatFabricIf,
        noRemoteChassis,
        vicEnableNotReceived,
        vicDisableReceived,
        vlanVsanMappingNotEnabled,
        stpNotFwdingInFcoeMappedVlan,
        moduleOffline,
        udldAggModeLinkFailure,
        stpInconsVpcPeerDisabled,
        setPortStateFailed,
        suspendedByVpc,
        vpcCfgInProgress,
        vpcPeerLinkDown,
        vpcNoRspFromPeer,
        protoPortSuspend,
        tunnelSrcDown,
        cdpInfoUnavailable,
        fexSfpInvalid,
        errDisabledIpConflict,
        fcotClkRateMismatch,
        portGuardTrustSecViolation,
        sdpTimeout,
        satIncompatTopo,
        waitForFlogi,
        satNotConfigured,
        npivNotEnabledInUpstream,
        vsanMismatchWithUpstreamSwPort,
        portGuardBitErrRate,
        portGuardSigLoss,
        portGuardSyncLoss,
        portGuardLinkReset and
        portGuardCreditLoss.
        -Added the following new enums to 
        fcIfFlapCtrlConfigReason:
        bitErrorRate,
        signalLoss,
        syncLoss,
        linkReset and
        creditLoss."
    REVISION        "200902050900Z"
    DESCRIPTION
        "-Added new object fcIfModuleXcvrFrequencyConfig to
        fcIfModuleTable. 
        -Deprecated fcIfToggleCtrlConfigTable
        -Added fcIfFlapCtrlConfigTable
        -Deprecated fcIfModuleGroup
        -Added the following new groups:
                fcIfFlapCtrlConfigGroup        
                fcIfModuleGroupRev1
        -Deprecated cffFcFeMIBComplianceRev10 compliance statement.
        -Added cffFcFeMIBComplianceRev11 compliance statement."
    REVISION        "200812030900Z"
    DESCRIPTION
        "-Added the following enums for FcIfOperStatusReason:
        sfpReadError,
        stickyDownOnLinkFailure,
        tooManyLinkFlapsErr,
        unidirectionalUDLD,
        txRxLoopUDLD,
        neighborMismatchUDLD,
        authzPending,
        hotStdbyInBundle,
        incompleteConfig,
        incompleteTunnelCfg,
        hwProgrammingFailed,
        tunnelDstUnreachable,
        suspendByMtu,
        sfpInvalid,
        sfpAbsent,
        portCapabilitiesUnknown,
        channelErrDisabled,
        vrfMismatch,
        vrfForwardReferencing,
        dupTunnelConfigDetected,
        primaryVLANDown,
        vrfUnusable,
        errDisableHandShkFailure,
        errDisabledBPDUGuard,
        dot1xSecViolationErrDisabled,
        emptyEchoUDLD and
        vfTaggingCapErr.
        -Added fcIfToggleCtrlConfigTable.
        Deprecated cffFcFeMIBComplianceRev8 compliance statement.
        Deprecated cffFcFeMIBComplianceRev9 compliance statement.
        Added cffFcFeMIBComplianceRev10 compliance statement."
    REVISION        "200708020000Z"
    DESCRIPTION
        "-Added the following enums for FcIfOperStatusReason:
        unavailableNPVUpstreamPort
        unavailableNPVPrefUpstreamPort."
    REVISION        "200701180000Z"
    DESCRIPTION
        "-Added new object fcIfModuleBandwidthFairnessOper to
        fcIfModuleTable."
    REVISION        "200701090000Z"
    DESCRIPTION
        "-Added new object fcIfModuleBandwidthFairnessConfig to
        fcIfModuleTable.
        -Added the following enums for FcIfOperStatusReason:
            fcidAllocationFailed,
            externallyDisabled."
    REVISION        "200611260000Z"
    DESCRIPTION
        "-Added fcIfModuleTable.
        -Added following objects to fcIfCapTable:
            fcIfIsServiceStateCapable
            fcIfIsPortRateModeCapable
            fcIfIsAdminRxBbCreditExtendedCapable
        -Added following objects to fcIfTable:
            fcIfPortType        
        -Added the following enums for FcIfOperStatusReason:
            fcRedirectIsolation,
            portActLicenseNotAvailable,
            sdmIsolation.
        -Added the following OBJECT-GROUPS:
            fcIfCapableGroup
            fcIfInfoPortGroup
            fcIfModuleGroup
        -Added cffFcFeMIBComplianceRev9 MODULE-COMPLIANCE."
    REVISION        "200605100000Z"
    DESCRIPTION
        "Added new object fcIfAdminBbScnMode to fcIfTable.
        fcIfBbScnGroup OBJECT-GROUP added.
        cffFcFeMIBComplianceRev8 MODULE-COMPLIANCE added."
    REVISION        "200604130000Z"
    DESCRIPTION
        "Added the following enums to FcIfOperStatusReason:
        localRcf,
        twoSwitchesWithSameWWN,
        invalidOtherSidePrincEFPReqRecd,
        domainOther."
    REVISION        "200602200000Z"
    DESCRIPTION
        "- Added the following objects to fcIfTable:
        fcIfServiceState,
        fcIfFcTunnelIfIndex and
        fcIfAdminRxBbCreditExtended.
        - Updated the description of the following objects:
        fcIfAdminRxBbCreditModeISL,
        fcIfAdminRxBbCreditModeFx and
        fcIfOperRxBbCredit.
        - Changed the enums for object fcIfPortRateMode from
        'frm' to 'dedicated' and 'osm' to 'shared'.
        - Added the following objects to FcIfGigEEntry: 
        fcIfGigEAutoNegotiate,
        fcIfGigEBeaconMode.
        - Added the following enums to FcIfOperStatusReason:
        portBringupIsolation,
        domainNotAllowedIsolated,
        virtualIvrDomainOverlapIsolation,
        outOfService,
        portAuthFailed,
        bundleStandby,
        portConnectorTypeErr,
        errorDisabledReInitLimitReached,
        ficonDupPortNum."
    REVISION        "200502150000Z"
    DESCRIPTION
        "In FcIfOperStatusReason, corrected typo.
        isolatedBundel changed to isolatedBundle."
    REVISION        "200410190000Z"
    DESCRIPTION
        "Added new table 'fcIfGigETable' to provide the port
        channel information for the Gigabit Ethernet (GigE) 
        interfaces in the fibre channel switch.
        Added two new notifications 'fcotInserted' and
        'fcotRemoved'.
        Added new enums to FcIfOperStatusReason."
    REVISION        "200403300000Z"
    DESCRIPTION
        "Added new object fcIfPortInitStatus to fcIfTable.
        Added new enums to FcIfOperStatusReason.
        Added fcIfRNIDInfoTable."
    REVISION        "200311140000Z"
    DESCRIPTION
        "Added new enums to FcIfOperStatusReason."
    REVISION        "200311060000Z"
    DESCRIPTION
        "Added Compliance statement for
        fcIfAdminRxBbCreditModeISL and 
        fcIfAdminRxBbCreditModeFx."
    REVISION        "200310170000Z"
    DESCRIPTION
        "Updated Compliance statement."
    REVISION        "200309220000Z"
    DESCRIPTION
        "Added the following objects for Loop Initialization
        Primitive Sequence (LIP) counters to  'fcIfErrorTable':
        fcIfLipF8In, fcIfLipF8Out, fcIfNonLipF8In and
        fcIfNonLipF8Out.
        Added new enums to FcIfOperStatusReason.
        Modified conformance information."
    REVISION        "200308180000Z"
    DESCRIPTION
        "Added fcIfStatTable. Modified conformance information."
    REVISION        "200306120000Z"
    DESCRIPTION
        "Added FcPerfBuffer TC. Added the following to fcIfTable:
        fcIfPortRateMode,fcIfAdminRxPerfBuffer,
        fcIfOperRxPerfBuffer,fcIfBbScn.
        Added the following to fcIfCapTable:
        fcIfCapBbScnCapable,fcIfCapBbScnMax,
        fcIfCapOsmFrmCapable.
        Added fcIfCapOsmTable,fcIfCapFrmTable.
        Added more reason codes in FcIfOperStatusReason.
        Replaced AUGMENTS clause with INDEX clause for the
        following tables: fcIfCapTable,fcIfErrorTable.
        Modified conformance information.
        Deprecated following objects in fcIfCapTable:
        fcIfCapRxBbCreditMax, fcIfCapRxBbCreditMin,
        fcIfCapISLRxBbCreditMax,fcIfCapISLRxBbCreditMin,
        fcIfCapRxBbCreditWriteable,fcIfCapRxBbCreditDefault,
        fcIfCapISLRxBbCreditDefault."
    REVISION        "200305140000Z"
    DESCRIPTION
        "Modified description of fcIfAllowedVsanList2k,
        fcIfAllowedVsanList4k, fcIfAdminSpeed, 
        fcIfAdminRxBbCredit."
    REVISION        "200304180000Z"
    DESCRIPTION
        "updated the textual convention, FcIfOperStatusReason.
        Added enumerations: firstPortUpAsEport,firstPortNotUp,
        peerFCIPPortClosedConnection,peerFCIPPortResetConnection,
        fcipPortMaxReTx,fcipPortKeepAliveTimerExpire,
        fcipPortPersistTimerExpire,fcipPortSrcLinkDown,
        fcipPortSrcAdminDown,fcipPortAdminCfgChange,
        fcipSrcPortRemoved,fcipSrcModuleNotOnline,invalidConfig,
        portBindFailure,portFabricBindFailure,
        noCommonVsanIsolation."
    REVISION        "200303250000Z"
    DESCRIPTION
        "Added: fcIfActiveVsanUpList2k, fcIfActiveVsanUpList4k.
        Modified conformance information."
    REVISION        "200211110000Z"
    DESCRIPTION
        "Modified fcTrunkIfUpNotify description."
    REVISION        "200211010000Z"
    DESCRIPTION
        "Modifed fcIfTable, fcIfCapTable."
    REVISION        "200210020000Z"
    DESCRIPTION
        "Initial version of this MIB module."
    ::= { ciscoMgmt 289 }


ciscoFcFeObjects  OBJECT IDENTIFIER
    ::= { ciscoFcFeMIB 1 }

cffFcFeMIBConformance  OBJECT IDENTIFIER
    ::= { ciscoFcFeMIB 2 }

cffFcFeConfig  OBJECT IDENTIFIER
    ::= { ciscoFcFeObjects 1 }

cffFcFeStatistics  OBJECT IDENTIFIER
    ::= { ciscoFcFeObjects 2 }

cffFcFeNotification  OBJECT IDENTIFIER
    ::= { ciscoFcFeObjects 3 }

cffFcFeNotifications  OBJECT IDENTIFIER
    ::= { cffFcFeNotification 0 }


-- Textual Conventions

FcphVersion ::= TEXTUAL-CONVENTION
    STATUS          current
    DESCRIPTION
        "Represents the version of FC-PH supported by an
        NxPort or FC-Port."
    SYNTAX          Integer32 (0..255)

FcBbCredit ::= TEXTUAL-CONVENTION
    STATUS          current
    DESCRIPTION
        "Represents the buffer-to-buffer credit of an
        NxPort or FC-Port."
    SYNTAX          Integer32 (0..32767)

FcRxDataFieldSize ::= TEXTUAL-CONVENTION
    STATUS          current
    DESCRIPTION
        "Represents the receive data field size of an
        NxPort or FC-Port."
    SYNTAX          Integer32 (128..2112)

FcBbCreditModel ::= TEXTUAL-CONVENTION
    STATUS          current
    DESCRIPTION
        "Represents the Buffer-to-Buffer Credit model of
        an FC-Port.
        regular(1)   - Credit model is regular
        alternate(2) - Credit model is alternate."
    SYNTAX          INTEGER  {
                        regular(1),
                        alternate(2)
                    }

FcIfOperStatusReason ::= TEXTUAL-CONVENTION
    STATUS          current
    DESCRIPTION
        "The cause of current operational state of the
        port.

        GLOSSARY:

        BB        - Buffer-to-Buffer.

        BB_Credit - Buffer-to-Buffer credit, a link level flow
                    control mechanism.

        B_Port    - A Fibre Channel, Bridging port.

        BPDU      - Bridge Protocol Data Unit.

        CDP       - Cisco Discovery Protocol.

        Class F   - A connectionless service with notification on 
                    non-delivery between E_Ports, used for control, 
                    coordination, and configuration of the Fabric.

        Class N   - Refers to any class of service (different types
                    of frame delivery services) other than Class F.

        E_D_TOV   - Error Detect Timeout Value.

        ENM       - Egress Non-Multicast.

        ELP       - Exchange Link Parameter.

        E-mode    - A fibre channel port providing E_Port 
                    functionality. 

        E_Port    - A Fabric Expansion Port.  

        EPP       - Exchange Peer Parameters.

        ESC       - Exchange Switch Capabilities.

        Fabric    - The set of physically connected fibre channel
                    switches.

        FEX       - Fabric EXtender.

        FC-FS     - Fibre Channel Framing and Signaling.

        FCIP      - Fibre Channel over IP protocol.

        FCID      - Fibre Channel Domain ID.

        FCOE      - Fibre Channel Over Ethernet.

        FCOT      - Fibre channel optical transmitter.

        FC-PH     - The Fibre Channel Physical and Signaling 
                    standard.

        FCSP      - Fibre Channel Security Protocol. 

        Fibre Channel - The primary protocol for building SANs. 

        FICON     - An I\O protocol used between IBM (and compatible) 
                    mainframes and storage.

        FLOGI     - Fabric Login, used by a node port to establish a
                    session with the fabric.

        GBIC      - Gigabit Interface Converter; a removable 
                    transceiver module permitting Fibre Channel and 
                    Gigabit Ethernet physical-layer transport.

        Interconnect_Ports - Switch Ports that assume either the
                    E_Port or B_Port mode are generally referred to 
                    as Interconnect_Ports.

        LACP      - Link Access Control Protocol.

        LIP       - Loop Initialization Primitive sequence.

        LR        - Link Reset, the FC-PH defined primitive sequence 
                    used to initiate a link reset.

        MTU       - Maximun transmission unit. 

        NOS       - Not Operational Sequence, the FC-PH defined 
                    primitive sequence to indicate that the 
                    transmitting port has detected a link failure (or)
                    offline condition.

        VIC       - Virtual Interface Card.

        VPC       - Virtual Port Channel.

        NPIV      - N Port Identifier Virtualization.

        NPV       - NPort Virtualizer.

        Nx_Port   - A Fiber Channel Node Port. 

        OLS       - Offline Sequence, the FC-PH defined primitive 
                    sequence to indicate that the port is entering
                    into offline state.

        OHMS      - Online Health Management System.

        PMON      - Port Monitor.

        R_A_TOV   - Resource Allocation Timeout Value.

        RCF       - Reconfigure Fabric. 

        Rxbbcredit - Receive BB credit value configured for 
                     a FC interface.

        SAN       - Storage Area Network; a network linking computing 
                    devices to disk or tape arrays and other devices 
                    over Fibre Channel.

        SIF       - Service Information Field.

        SDM       - Security Device Manager.

        SDP       - Secure Device Provisioning.

        SFP       - Small Formfactor Pluggable.

        TE_Port   - Trunking E_Port.

        TOV       - Time out value.

        UDLD      - Uni Directional Link Detection.

        VDC       - Virtual Device Context.

        VEM       - Virtual Ethernet Module.

        VFC       - Virtual Fibre Channel.

        VRF       - VPN Routing and Forwarding.

        VSAN      - Virtual Storage Area Network.

        WWN       - World Wide Name.

        xE_Port   - A Fiber channel port that can assume either 
                    E_Port or TE_Port mode.

        The enumerated values which provides the cause of the current
        operational state of the interface are:

        'other(1)' - reasons other than defined here.
        'none(2)' - no failure
        'hwFailure(3)' - hardware failure.  
        'loopbackDiagFailure(4)' - loopback diagnostics 
            failure.
        'errorDisabled(5)' - the port is not operational 
            due to some error conditions that require
            administrative attention.
        'swFailure(6)' - software failure.
        'linkFailure(7)' - physical link failure.
        'offline(8)' -  physical link is in offline state
            as defined in the FC-FS standards.
        'nonParticipating(9)' - during loop initialization,
            the port is not allowed to participate in loop
            operations.
        'initializing(10)' - port is being initialized. 
        'vsanInactive(11)'- port VSAN is inactive. The port
            becomes operational again when the port VSAN is
            active. 
        'adminDown(12)' - 'ifAdminStatus' is down(2).
        'channelAdminDown(13)' - this port is a member of
            a port channel and that port channel's
            ifAdminStatus is 'down(2)'. 
        'channelOperSuspended(14)' - this port is a member
            of a port channel and its operational 
            parameters are incompatible with the port 
            channel parameters.  
        'channelConfigurationInProgress(15)' - this port 
            is undergoing a port channel configuration.
        'rcfInProgress(16)' -  an isolated xE_port is 
            transmiting an reconfigure fabric, requesting
            a disruptive reconfiguration in an attempt to 
            build a single, non-isolated fabric.
        Only the Interconnect_Ports can become isolated. 
        'elpFailureIsolation(17)' - during a port 
            initialization the prospective 
            Interconnect_Ports find incompatible link
            parameters.
        'escFailureIsolation(18) - during a port 
            initialization the prospective 
            Interconnect_Ports are unable to proceed with
            initialization as a result of Exchange Switch
            Capabilities (ESC).
        'domainOverlapIsolation(19)' - there is a overlap 
            in domains while attempting to connect two
            existing fabrics.
        'domainAddrAssignFailureIsolation(20)' - the 
            elected principal switch is not capable of
            performing domain address manager functions so
            no Nx_port traffic can be forwarded across
            switches, hence all Interconnect_Ports in the
            switch are isolated.
        'domainOtherSideEportIsolation(21)' - the peer 
            e-port is isolated.
        'domainInvalidRCFReceived(22)' - Invalid rcf 
            received.
        'domainManagerDisabled(23) - domain manager is
            disabled.
        'zoneMergeFailureIsolation(24)' - the two 
            Interconnect_Ports cannot merge zoning 
            configuration after having exchanged merging 
            request for zoning.
        'vsanMismatchIsolation(25)' - this vsan is not 
            configured on both sides of a trunk port.
        'parentDown(26)' - the physical port to which this
            interface is bound is down.
        'srcPortNotBound(27)'- no source port is specified
            for this interface.
        'interfaceRemoved(28)' - interface is being 
            removed.
        'fcotNotPresent(29)' - fcot(GBIC) not present.
        'fcotVendorNotSupported(30)' - fcot(GBIC) vendor 
            is not supported. 
        'incompatibleAdminMode(31)' - port admin mode is
            incompatible with port capabilities. 
        'incompatibleAdminSpeed(32)' - port speed is
            incompatible with port capabilities. 
        'suspendedByMode(33)' -  port that belongs to a
            port channel is suspended due to incompatible
            operational mode.                         
        'suspendedBySpeed(34)' - port that belongs to a
            port channel is suspended due to incompatible
            operational speed.
        'suspendedByWWN(35)' - port that belongs to a
            port channel is suspended due to incompatible
            remote switch WWN.
        'domainMaxReTxFailure(36)' - domain manager 
            failure after maximum retries.
        'eppFailure(37)' - trunk negotiation protocol
            failure after maximum retries.
        'portVsanMismatchIsolation(38)' - an attempt is
            made to connect two switches using 
            non-trunking ports having different port 
            VSANs. 
        'loopbackIsolation(39)' - port is connected to
            another port in the same switch.
        'upgradeInProgress(40)' - linecard upgrade in 
            progress.
        'incompatibleAdminRxBBCredit(41)' - receive
            BB credit is incompatible.
        'incompatibleAdminRxBufferSize(42)' - receive
            buffer size is incompatible.
        'portChannelMembersDown(43)' - no operational
            members.
        'zoneRemoteNoRespIsolation(44)' - isolation
            due to remote zone server not responding.
        'firstPortUpAsEport(45)' - in a over subscribed
            line card, when the first port in a group 
            is up in E mode, other ports in that group
            cannot be brought up.
        'firstPortNotUp(46)' - in a over subscribed
            line card, first port cannot be brought up
            in E-mode when the other ports in the group
            are up.
        'peerFCIPPortClosedConnection(47)' - port went
            down because peer FCIP port closed TCP 
            connection.    
        'peerFCIPPortResetConnection(48)' - port went
            down because the TCP connection was reset
            by the peer fcip port.
        'fcipPortMaxReTx(49)' - fcip port went down due
            to max tcp re-transmissions reached the
            configured limit.
        'fcipPortKeepAliveTimerExpire(50)' - fcip port 
            went down due to TCP keep alive timer expired.
        'fcipPortPersistTimerExpire(51)' - fcip port went
            down due  to TCP persist timer expired.
        'fcipPortSrcLinkDown(52)' - fcip port went down 
            due to ethernet link down.
        'fcipPortSrcAdminDown(53)' - fcip port went down 
            because the source ethernet link was 
            administratively shutdown.
        'fcipPortAdminCfgChange(54)' - fcip port went down 
            due to configuration change. 
        'fcipSrcPortRemoved(55)' - fcip port went down due
            to source port removal.
        'fcipSrcModuleNotOnline(56)' - fcip port went down
            due to source module not online.
        'invalidConfig(57)' - this port has a 
            misconfiguration with respect to port channels.
        'portBindFailure(58)' - port got isolated due to
            port bind failure.  
        'portFabricBindFailure(59)' - port got isolated
            due to fabric bind failure.    
        'noCommonVsanIsolation(60)' - trunk is isolated
            because there are no common vsans with peer.
        'ficonVsanDown' - Ficon vsan down
        'invalidAttachment' -  Invalid attachment
        'portBlocked' - Port blocked due to Ficon 
        'incomAdminRxBBCreditPerBuf' - disabled due
            to incompatible admin port rxbbcredit,
            performance buffers.
        'tooManyInvalidFLOGIs' - Suspended due to too 
            many invalid flogis. 
        'deniedDueToPortBinding' - Suspended due to 
            port binding.
        'elpFailureRevMismatch' - Isolated for ELP failure
            due to revision mismatch.
        'elpFailureClassFParamErr' - Isolated for ELP 
            failure due to class F param error.
        'elpFailureClassNParamErr' - Isolated for ELP 
            failure due to class N param error.
        'elpFailureUnknownFlowCTLCode' - Isolated for ELP 
            failure due to invalid flow control code
        'elpFailureInvalidFlowCTLParam' - Isolated for ELP 
            failure due to invalid flow control param.
        'elpFailureInvalidPortName' - Isolated for ELP 
            failure due to invalid port name.
        'elpFailureInvalidSwitchName' - Isolated for ELP 
            failure due to invalid switch name.
        'elpFailureRatovEdtovMismatch' - Isolated for ELP 
            failure due to R_A_TOV or E_D_TOV mismatch.
        'elpFailureLoopbackDetected' - Isolated for ELP 
            failure due to loopback detected.
        'elpFailureInvalidTxBBCredit' - Isolated for ELP 
            failure due to invalid transmit B2B credit.
        'elpFailureInvalidPayloadSize' - Isolated for ELP 
            failure due to invalid payload size.
        'bundleMisCfg' - misconfiguration in portchannel
            membership detected.
        'bitErrRTThresExceeded' - bit error rate too high.
        'linkFailLinkReset' - link failure due to link 
            reset.
        'linkFailPortInitFail' - link failure due to 
            port initialization failure.
        'linkFailPortUnusable' - link failure due to 
            port unusable.
        'linkFailLossOfSignal' - link failure due to
            loss of signal. 
        'linkFailLossOfSync' - link failure due to
            loss of sync.
        'linkFailNOSRcvd' - link failure due to
            non-operational sequences received.
        'linkFailOLSRcvd' - link failure due to  offline
            sequences received.
        'linkFailDebounceTimeout' - link failure due to
            re-negotiation failed.
        'linkFailLRRcvdB2B' - link failure when 
            link reset(LR) operation fails due to 
            non-empty receive queue.  
        'linkFailCreditLoss' - link failure due to 
            excessive credit loss indications.
        'linkFailRxQOverFlow' - link failure due to
            receive queue overflow.
        'linkFailTooManyINTR' - link failure due to
            excessive port interrupts.
        'linkFailLIPRcvdB2B' - link failure when
            loop initialization(LIP) operation fails due
            to non empty receive queue.
        'linkFailCreditLossB2B' - link failure when
            link reset(LR) operation fails due to
            queue not empty.                        
        'linkFailOPNyTMOB2B' - link failure due to
            open primitive signal timeout while receive
            queue not empty.                      
        'linkFailOPNyRETB2B' - link failure due to
            open primitive signal returned while receive
            queue not empty. 
        'linkFailLIPF8Rcvd' - link failure due to F8 LIP
             received.
        'linkFailLineCardPortShutdown' - link failure due
            to port shutdown.
        'fcspAuthenfailure' - fibre channel security
            protocol authorization fail.
        'fcotChksumErr' - FCOT SPROM checksum error. 
        'ohmsExtLBTest' - link suspended due to external 
            loopback diagnostics failure.
        'invalidFabricBindExh' - invalid fabric binding
            exchange.
        'tovMismatch' - link isolation due to TOV 
            mismatch.
        'ficonNotEnabled - Ficon not enabled.
        'ficonNoPortnumber' - no Ficon portnumber.
        'ficonBeingEnabled' - Ficon is being enabled.
        'ePortProhibited' - port down because FICON 
            prohibit mask in place for E/TE port.
        'portGracefulShutdown' - port has been shutdown
            gracefully.
        'trunkNotFullyActive' - some of the VSANs which 
            are common with the peer are not up.
        'fabricBindingSWWNNotFound' - Peer switch WWN
            not found in fabric binding active database.
        'fabricBindingDomainInvalid' - Peer domain ID
            is invalid in fabric binding active
            database.
        'fabricBindingDBMismatch' - fabric binding
            active database mismatch with peer. 
        'fabricBindingNoRspFromPeer' - fabric binding
            no response from peer. 
        'vsanSuspended' - dynamic VSAN is suspended.
        'vsanNotFound' - dynamic VSAN not found.
        'trackedPortDown' - tracked port is down.
        'ecSuspendedLoop' - EC is currently suspended 
            for loopback.
        'isolatedBundle' - isolated bundle due to
            misconfigurations.
        'peerNotSupportBundle' - peer deivice does not 
            support port channel.
        'portBringupIsolation' - trunk port 
            isolated during bringup time.
        'domainNotAllowedIsolated' - port isolated
            due to domain not allowed.
        'virtualIvrDomainOverlapIsolation' - port
            isolated due to virtual IVR domain overlap.
        'outOfService' - port is in out of service
            state.
        'portAuthFailed' - port has encountered
            an 802.1x authentication failure.
        'bundleStandby' - port cannot be brought
            up in a bundle, since the bundle has maximum
            members.
        'portConnectorTypeErr' - Error in the
            port connector type (SFP).
        'errorDisabledReInitLimitReached' - the port
            is not operational after trying to
            initialize the port multiple times due
            to some errors.
        'ficonDupPortNum' - the FICON VSAN has a
            duplicate port number.
        'localRcf' - local disruptive reconfiguration 
            (the local domain became invalid; no RCF 
            frames have been sent outside the local 
            switch). 
        'twoSwitchesWithSameWWN' - merge attempt between 
            VSANs containing the same WWN. If the user 
            attempts to merge two different VSANs and 
            both have at least one switch with the same
            WWN then the link in between the VSANs is 
            isolated.
        'invalidOtherSidePrincEFPReqRecd' - EFP request 
            frame indicating a principal switch other 
            than the locally known one.
        'domainOther' - other domain manager reasons 
            not defined here.
         'elpFailureAllZeroPeerWWNRcvd' - isolated for 
            ELP failure due to peer WWN is received 
            with all zeros.
         'preferredPathIsolation' - port isolated due to
            preferred path not able to program the routes.
         'fcRedirectIsolation' - port isolated due to
            FC Redirect not being able to program routes.
         'portActLicenseNotAvailable' - port not brought up
            due to lack of port activation licenses.
         'sdmIsolation' - port isolated due to SDM not being
            able to program routes.
         'fcidAllocationFailed' - port down due to failure
            in FCID allocation.   
         'externallyDisabled' - port externally disabled.
         'unavailableNPVUpstreamPort' - NPV upstream port 
                not available.
         'unavailableNPVPrefUpstreamPort' - NPV preferred 
            upstream port not available.
         'sfpReadError' - the port is not operational due to 
                 SFP read error.
         'stickyDownOnLinkFailure' - the port is not operational 
                 due to link failure in the sticky down mode.
         'tooManyLinkFlapsErr' - too many link flaps on the port
                 in a short interval.
         'unidirectionalUDLD' - unidirectional UDLD detected.
         'txRxLoopUDLD' - UDLD Tx Rx loop.
         'neighborMismatchUDLD' - UDLD neighbor mismatch.
         'authzPending' - authorization pending.
         'hotStdbyInBundle' - hot standby in bundle.
         'incompleteConfig' - all parameters on the port have not been
                 configured.
         'incompleteTunnelCfg' - incomplete tunnel config.
         'hwProgrammingFailed' - hardware programming failed.
         'tunnelDstUnreachable' - no route to tunnel destination
                 address.
         'suspendByMtu' - MTU allocation failed.
         'sfpInvalid' - SFP is not Cisco certified.
         'sfpAbsent' - SFP is absent.
         'portCapabilitiesUnknown' - the capabilities of the port are 
                          unknown.
         'channelErrDisabled' - the port-channel to which the port
                 belongs is in error disabled state.
         'vrfMismatch' - Mismatch in source and transport VRF.
         'vrfForwardReferencing' - Forward referencing transport VRF.
         'dupTunnelConfigDetected' - two tunnel interfaces with same 
                 configuration is not allowed.
         'primaryVLANDown' - primary VLAN is in down state.
         'vrfUnusable' - VRF is unusable.
         'errDisableHandShkFailure' - port is not operational due to
                 an internal handshake failure.
         'errDisabledBPDUGuard' - BPDUGuard triggered error disable on
                 the port.
         'dot1xSecViolationErrDisabled' - error disabled due to dot1x
                 security violation.                         
         'emptyEchoUDLD' - UDLD empty echo.
         'vfTaggingCapErr' - VF Tagging capability mismatch error.
         'portDisabled' - Port disabled.
         'tunnelModeNotConfigured' - Tunnel Mode is not configured.
         'tunnelSrcNotConfigured' - Tunnel Source is not configured. 
         'tunnelDstNotConfigured' - Tunnel Destination is not 
                          configured.
         'tunnelUnableToResolveSrcIP' - Unable to resolve tunnel
                          source IP address. 
         'tunnelUnableToResolveDstIP' - Unable to resolve tunnel 
                          destination IP address.
         'tunnelVrfDown' - Tunnel VRF down.
         'sifAdminDown' - SIF is admin down.
         'phyIntfDown' - Physical interface is down.
         'ifSifLimitExceeded' - Interface SIF limit is exceeded.
         'sifHoldDown' - SIF hold down.
         'noFcoe' - No FCOE configuration.
         'dcxCompatMismatch' - DCX Compatibility Mismatch.
         'isolateBundleLimitExceeded' - Isolation due to bundle
                          limit exceeded.
         'sifNotBound' - SIF is not bound.
         'errDisabledLacpMiscfg' - Error Disabled due to LACP 
                          misconfig.
         'satFabricIfDown' - Satellite fabric interface down.
         'invalidSatFabricIf' - Invalid satellite fabric interface.
         'noRemoteChassis' - No remote chassis.
         'vicEnableNotReceived' - VIC enable not received.
         'vicDisableReceived' - VIC disable received.
         'vlanVsanMappingNotEnabled' - VLAN VSAN mapping not enabled.
         'stpNotFwdingInFcoeMappedVlan' - STP not forwarding in FCOE
                          Mapped Vlan.
         'moduleOffline' - Module Offline.
         'udldAggModeLinkFailure' - UDLD aggresive mode link failure.
         'stpInconsVpcPeerDisabled' - STP inconsistent VPC peer 
                          disabled. 
         'setPortStateFailed' - Set port state failed.
         'suspendedByVpc' - Suspended by VPC.
         'vpcCfgInProgress' - VPC configuration in progress.
         'vpcPeerLinkDown' - VPC peer link down.
         'vpcNoRspFromPeer' - VPC no response from peer.
         'protoPortSuspend' - Proto port suspend.
         'tunnelSrcDown' - Tunnel source down.
         'cdpInfoUnavailable' - CDP information unavailable.
         'fexSfpInvalid' - FEX SFP invalid.
         'errDisabledIpConflict' - Error Disabled due to IP conflict.
         'fcotClkRateMismatch' - FCOT CLK rate mismatch.
         'portGuardTrustSecViolation' - Error disabled due to port guard
                                  (Cisco Trusted Security Violation).
         'sdpTimeout' - SDP timeout.
         'satIncompatTopo' - Satellite incompatible topology.
         'waitForFlogi' - Wait for FLOGI.
         'satNotConfigured' - Satellite not configured.
         'npivNotEnabledInUpstream' - NPIV not enabled in upstream.
         'vsanMismatchWithUpstreamSwPort' - VSAN mismatch with upstream 
                                            switch port.
         'portGuardBitErrRate' - Error disabled due to port guard 
                          (Bit Error Rate).
         'portGuardSigLoss' - Error disabled due to port guard 
                          (Signal Loss).
         'portGuardSyncLoss' - Error disabled due to port guard 
                          (Sync Loss).
         'portGuardLinkReset' - Error disabled due to port guard 
                          (Link Reset).
         'portGuardCreditLoss' - Error disabled due to port guard 
                          (Credit Loss).
         'ipQosMgrPolicyAppFailure' - IP QOS Manager policy 
                                           application failure.
         'pauseRateLimitErrDisabled' - Port error disabled due
                                   to pause rate limit condition.
         'lstGrpUplinkDown' - EthPM LSTGRP downstream link down
                                           due to upstream link down.
         'stickyDnLinkFailure' - Port kept in error disabled
                                           state due to Link Failure.
         'routerMacFailure' - Router MAC failure.
         'dcxMultipleMsapIds' - Port error disabled due to
                                           multiple MSAP IDs (DCX).
         'dcxHundredPdusRcvdNoAck' - Hundred PDUs received without
                                           ACK (DCX).
         'enmSatIncompatibleUplink' - Satellite Incompatible Uplink.
         'enmLoopDetected' - Loop Detected (ENM).
         'nonStickyExternallyDisabled' - Disabled by VPD Manager with
                                           SHut/No Shut allowed.
         'subGroupIdNotAssigned' - Sub-group ID not assigned.
         'vemUnlicensed' - VEM Unlicensed.
         'profileNotFound' - Profile not found.
         'nonExistentVlan' - VLAN does not exist.
         'vlanInvalidType' - Invalid VLAN type.
         'vlanDown' - VLAN down.
         'vpcPeerUpgrade' - VPC Peer Upgrade.
         'ipQosDcbxpCompatFailure' - IPQOS DCBXP compatibility
                                           failure.
         'nonCiscoHbaVfTag' - Error Disabled due to Non-Cisco HBA
                                           VF Tag.
         'domainIdConfigMismatch' - Domain ID config mismatch.
         'sfpSpeedMismatch' - SFP speed mismatch.
         'xcvrInitializing' - Transceiver initializing.
         'xcvrAbsent' - Transceiver absent.
         'xcvrInvalid' - Transceiver invalid.
         'vfcBindingInvalid' - Invalid VFC Binding.
         'vlanNotFcoeEnabled' - VLAN down due to FCOE disabled.
         'pvlanNativeVlanErr' - Private VLAN - Native VLAN error.
         'ethL2VlanDown' - Ethernet L2 VLAN down.
         'ethIntfInvalidBinding' - Invalid Binding to Ethernet 
                                 Interface.
         'pmonFailure' - PMON Failure.
         'l3NotReady' - L3 not ready.
         'speedMismatch' - Speed Mismatch.
         'flowControlMismatch' - Flow Control Mismatch.
         'vdcMode' - VDC mode 
         'suspendedDueToMinLinks' - Suspended due to Min Links.
         'enmPinFailLinkDown' - ENM Pin Fail Link Down.
         'inactiveM1PortFpathActiveVlan' - Inactive M1 Port
                                F Path Active VLAN.
         'parentPortDown' - Parent Port Down.
         'moduleRemoved' - Module Removed.
         'corePortMct' - Core Port MCT.
         'nonCorePortMct' - Non Core port MCT.
         'ficonInorderNotActive'- FICON Inorder Not Active.
         'invalidEncapsulation' - Invalid Encapsulation.
         'modemLineDeasserted' - Modem line asserted.
         'ipSecHndshkInProgress' - IP Sec Handshake in progress.
         'sfpEthCompliantErr' - Sfp Ethernet compliant error.
         'cellularModemUnattached' - Cellular Modem unattached.
         'outOfGlblRxBuffers' - Out of global Rx buffers.
         'sfpFcCompliantErr' - Sfp Fc Compliant Error.
         'ethIntfNotLicensed' - Ethernet interface not licensed.
         'domainIdsInvalid' - Domain IDs Invalid.
         'fabricNameInvalid' - Fabric Name Invalid.
         'ficonNoPortSwapLogicalPort' - Ficon No Port Swap Logical Port.
         'ficonInvalidPortNum ' - Ficon Invalid Port Number.
         'remotePortInL2vpnDown' - Remote Port in L2VPN Down.
         'suspendedDueToNoLacpPdus' - Suspended due to no LACP PDUs.
         'fcotValidationFailedAtDriver' - Fcot validation failed at driver.
         'unsupportedTransceiverMd5DigestNotSame' - Unsupported transceiver MD5 digest not Same.
         'unsupportedTransceiver' - Unsupport transceiver.
         'adminStateConfigChange' - Admin state config change.
         'vlanAllowedList' - Allowed Vlan list configured on the port.
         'vlanAllowedListOverride' - Allowed Vlan list changed on the port.
         'vlanAllowedListAdd' - Vlan has been added to the allowed Vlan list on the port.
         'vlanAllowedListRemove' - Vlan has been removed from the allowed Vlan list on the port.
         'vlanCfgStateChange' - Port affected due to Vlan state change.
         'vlanCfgDelete' - Port affected due to Vlan delete.
         'pppPeerNotResponding' - ppp peer not responding.
         'pppAuthFailed' - ppp authentication failed.
         'xcvrAuthFailed' - Transceiver authentication failed.
         'badFramesRcvdFromLink' - Excessive bad frames received from link."
    SYNTAX          INTEGER  {
                        other(1),
                        none(2),
                        hwFailure(3),
                        loopbackDiagFailure(4),
                        errorDisabled(5),
                        swFailure(6),
                        linkFailure(7),
                        offline(8),
                        nonParticipating(9),
                        initializing(10),
                        vsanInactive(11),
                        adminDown(12),
                        channelAdminDown(13),
                        channelOperSuspended(14),
                        channelConfigurationInProgress(15),
                        rcfInProgress(16),
                        elpFailureIsolation(17),
                        escFailureIsolation(18),
                        domainOverlapIsolation(19),
                        domainAddrAssignFailureIsolation(20),
                        domainOtherSideEportIsolation(21),
                        domainInvalidRCFReceived(22),
                        domainManagerDisabled(23),
                        zoneMergeFailureIsolation(24),
                        vsanMismatchIsolation(25),
                        parentDown(26),
                        srcPortNotBound(27),
                        interfaceRemoved(28),
                        fcotNotPresent(29),
                        fcotVendorNotSupported(30),
                        incompatibleAdminMode(31),
                        incompatibleAdminSpeed(32),
                        suspendedByMode(33),
                        suspendedBySpeed(34),
                        suspendedByWWN(35),
                        domainMaxReTxFailure(36),
                        eppFailure(37),
                        portVsanMismatchIsolation(38),
                        loopbackIsolation(39),
                        upgradeInProgress(40),
                        incompatibleAdminRxBBCredit(41),
                        incompatibleAdminRxBufferSize(42),
                        portChannelMembersDown(43),
                        zoneRemoteNoRespIsolation(44),
                        firstPortUpAsEport(45),
                        firstPortNotUp(46),
                        peerFCIPPortClosedConnection(47),
                        peerFCIPPortResetConnection(48),
                        fcipPortMaxReTx(49),
                        fcipPortKeepAliveTimerExpire(50),
                        fcipPortPersistTimerExpire(51),
                        fcipPortSrcLinkDown(52),
                        fcipPortSrcAdminDown(53),
                        fcipPortAdminCfgChange(54),
                        fcipSrcPortRemoved(55),
                        fcipSrcModuleNotOnline(56),
                        invalidConfig(57),
                        portBindFailure(58),
                        portFabricBindFailure(59),
                        noCommonVsanIsolation(60),
                        ficonVsanDown(61),
                        invalidAttachment(62),
                        portBlocked(63),
                        incomAdminRxBBCreditPerBuf(64),
                        tooManyInvalidFLOGIs(65),
                        deniedDueToPortBinding(66),
                        elpFailureRevMismatch(67),
                        elpFailureClassFParamErr(68),
                        elpFailureClassNParamErr(69),
                        elpFailureUnknownFlowCTLCode(70),
                        elpFailureInvalidFlowCTLParam(71),
                        elpFailureInvalidPortName(72),
                        elpFailureInvalidSwitchName(73),
                        elpFailureRatovEdtovMismatch(74),
                        elpFailureLoopbackDetected(75),
                        elpFailureInvalidTxBBCredit(76),
                        elpFailureInvalidPayloadSize(77),
                        bundleMisCfg(78),
                        bitErrRTThresExceeded(79),
                        linkFailLinkReset(80),
                        linkFailPortInitFail(81),
                        linkFailPortUnusable(82),
                        linkFailLossOfSignal(83),
                        linkFailLossOfSync(84),
                        linkFailNOSRcvd(85),
                        linkFailOLSRcvd(86),
                        linkFailDebounceTimeout(87),
                        linkFailLRRcvdB2B(88),
                        linkFailCreditLoss(89),
                        linkFailRxQOverFlow(90),
                        linkFailTooManyINTR(91),
                        linkFailLIPRcvdB2B(92),
                        linkFailCreditLossB2B(93),
                        linkFailOPNYTMOB2B(94),
                        linkFailOPNYRETB2B(95),
                        linkFailLIPF8Rcvd(96),
                        linkFailLineCardPortShutdown(97),
                        fcspAuthenfailure(98),
                        fcotChksumErr(99),
                        ohmsExtLBTest(100),
                        invalidFabricBindExh(101),
                        tovMismatch(102),
                        ficonNotEnabled(103),
                        ficonNoPortnumber(104),
                        ficonBeingEnabled(105),
                        ePortProhibited(106),
                        portGracefulShutdown(107),
                        trunkNotFullyActive(108),
                        fabricBindingSWWNNotFound(109),
                        fabricBindingDomainInvalid(110),
                        fabricBindingDBMismatch(111),
                        fabricBindingNoRspFromPeer(112),
                        vsanSuspended(113),
                        vsanNotFound(114),
                        trackedPortDown(115),
                        ecSuspendedLoop(116),
                        isolatedBundle(117),
                        peerNotSupportBundle(118),
                        portBringupIsolation(119),
                        domainNotAllowedIsolated(120),
                        virtualIvrDomainOverlapIsolation(121),
                        outOfService(122),
                        portAuthFailed(123),
                        bundleStandby(124),
                        portConnectorTypeErr(125),
                        errorDisabledReInitLimitReached(126),
                        ficonDupPortNum(127),
                        localRcf(128),
                        twoSwitchesWithSameWWN(129),
                        invalidOtherSidePrincEFPReqRecd(130),
                        domainOther(131),
                        elpFailureAllZeroPeerWWNRcvd(132),
                        preferredPathIsolation(133),
                        fcRedirectIsolation(134),
                        portActLicenseNotAvailable(135),
                        sdmIsolation(136),
                        fcidAllocationFailed(137),
                        externallyDisabled(138),
                        unavailableNPVUpstreamPort(139),
                        unavailableNPVPrefUpstreamPort(140),
                        sfpReadError(141),
                        stickyDownOnLinkFailure(142),
                        tooManyLinkFlapsErr(143),
                        unidirectionalUDLD(144),
                        txRxLoopUDLD(145),
                        neighborMismatchUDLD(146),
                        authzPending(147),
                        hotStdbyInBundle(148),
                        incompleteConfig(149),
                        incompleteTunnelCfg(150),
                        hwProgrammingFailed(151),
                        tunnelDstUnreachable(152),
                        suspendByMtu(153),
                        sfpInvalid(154),
                        sfpAbsent(155),
                        portCapabilitiesUnknown(156),
                        channelErrDisabled(157),
                        vrfMismatch(158),
                        vrfForwardReferencing(159),
                        dupTunnelConfigDetected(160),
                        primaryVLANDown(161),
                        vrfUnusable(162),
                        errDisableHandShkFailure(163),
                        errDisabledBPDUGuard(164),
                        dot1xSecViolationErrDisabled(165),
                        emptyEchoUDLD(166),
                        vfTaggingCapErr(167),
                        portDisabled(168),
                        tunnelModeNotConfigured(169),
                        tunnelSrcNotConfigured(170),
                        tunnelDstNotConfigured(171),
                        tunnelUnableToResolveSrcIP(172),
                        tunnelUnableToResolveDstIP(173),
                        tunnelVrfDown(174),
                        sifAdminDown(175),
                        phyIntfDown(176),
                        ifSifLimitExceeded(177),
                        sifHoldDown(178),
                        noFcoe(179),
                        dcxCompatMismatch(180),
                        isolateBundleLimitExceeded(181),
                        sifNotBound(182),
                        errDisabledLacpMiscfg(183),
                        satFabricIfDown(184),
                        invalidSatFabricIf(185),
                        noRemoteChassis(186),
                        vicEnableNotReceived(187),
                        vicDisableReceived(188),
                        vlanVsanMappingNotEnabled(189),
                        stpNotFwdingInFcoeMappedVlan(190),
                        moduleOffline(191),
                        udldAggModeLinkFailure(192),
                        stpInconsVpcPeerDisabled(193),
                        setPortStateFailed(194),
                        suspendedByVpc(195),
                        vpcCfgInProgress(196),
                        vpcPeerLinkDown(197),
                        vpcNoRspFromPeer(198),
                        protoPortSuspend(199),
                        tunnelSrcDown(200),
                        cdpInfoUnavailable(201),
                        fexSfpInvalid(202),
                        errDisabledIpConflict(203),
                        fcotClkRateMismatch(204),
                        portGuardTrustSecViolation(205),
                        sdpTimeout(206),
                        satIncompatTopo(207),
                        waitForFlogi(208),
                        satNotConfigured(209),
                        npivNotEnabledInUpstream(210),
                        vsanMismatchWithUpstreamSwPort(211),
                        portGuardBitErrRate(212),
                        portGuardSigLoss(213),
                        portGuardSyncLoss(214),
                        portGuardLinkReset(215),
                        portGuardCreditLoss(216),
                        ipQosMgrPolicyAppFailure(217),
                        pauseRateLimitErrDisabled(218),
                        lstGrpUplinkDown(219),
                        stickyDnLinkFailure(220),
                        routerMacFailure(221),
                        dcxMultipleMsapIds(222),
                        dcxHundredPdusRcvdNoAck(223),
                        enmSatIncompatibleUplink(224),
                        enmLoopDetected(225),
                        nonStickyExternallyDisabled(226),
                        subGroupIdNotAssigned(227),
                        vemUnlicensed(228),
                        profileNotFound(229),
                        nonExistentVlan(230),
                        vlanInvalidType(231),
                        vlanDown(232),
                        vpcPeerUpgrade(233),
                        ipQosDcbxpCompatFailure(234),
                        nonCiscoHbaVfTag(235),
                        domainIdConfigMismatch(236),
                        sfpSpeedMismatch(237),
                        xcvrInitializing(238),
                        xcvrAbsent(239),
                        xcvrInvalid(240),
                        vfcBindingInvalid(241),
                        vlanNotFcoeEnabled(242),
                        pvlanNativeVlanErr(243),
                        ethL2VlanDown(244),
                        ethIntfInvalidBinding(245),
                        pmonFailure(246),
                        l3NotReady(247),
                        speedMismatch(248),
                        flowControlMismatch(249),
                        vdcMode(250),
                        suspendedDueToMinLinks(251),
                        enmPinFailLinkDown(252),
                        inactiveM1PortFpathActiveVlan(253),
                        parentPortDown(254),
                        moduleRemoved(255),
                        corePortMct(256),
                        nonCorePortMct(257),
                        ficonInorderNotActive(258),
                        invalidEncapsulation(259),
                        modemLineDeasserted(260),
                        ipSecHndshkInProgress(261),
                        sfpEthCompliantErr(262),
                        cellularModemUnattached(263),
                        outOfGlblRxBuffers(264),
                        sfpFcCompliantErr(265),
                        ethIntfNotLicensed(266),
                        domainIdsInvalid(267),
                        fabricNameInvalid(268),
                        ficonNoPortSwapLogicalPort(269),
                        ficonInvalidPortNum(270),
                        remotePortInL2vpnDown(271),
                        suspendedDueToNoLacpPdus(272),
                        fcotValidationFailedAtDriver(273),
                        unsupportedTransceiverMd5DigestNotSame(274),
                        unsupportedTransceiver(275),
                        adminStateConfigChange(276),
                        vlanAllowedList(277),
                        vlanAllowedListOverride(278),
                        vlanAllowedListAdd(279),
                        vlanAllowedRemove(280),
                        vlanCfgStateChange(281),
                        vlanCfgDelete(282),
                        pppPeerNotResponding(283),
                        pppAuthFailed(284),
                        xcvrAuthFailed(285),
                        badFramesRcvdFromLink(286)
                    }

FcPerfBuffer ::= TEXTUAL-CONVENTION
    STATUS          current
    DESCRIPTION
        "Represents the number of performance buffers of a
        physical FC-port. These buffers in addition to the 
        buffer-to-buffer credits are used to improve the
        performance of a port, hence called
        'Performance buffers'. A value of zero for this
        means the agent uses the built-in algorithm to
        calculate the number of performance buffers to be
        used."
    SYNTAX          Integer32 (0..145)

-- fibre element group information

cffFcFeElementName OBJECT-TYPE
    SYNTAX          FcNameId
    MAX-ACCESS      read-write
    STATUS          current
    DESCRIPTION
        "The World-Wide Name of this fabric element. It's a
        64-bit identifier and is unique worldwide." 
    ::= { cffFcFeConfig 1 }
-- fcIfTable

fcIfTable OBJECT-TYPE
    SYNTAX          SEQUENCE OF FcIfEntry 
    MAX-ACCESS      not-accessible
    STATUS          current
    DESCRIPTION
        "This table contains one entry per fibre channel switch
        port interface. Each entry holds the port interface 
        parameters. The entries are created by the fabric 
        switch when a module is inserted and it identifies a
        port on the module. 
        Similarly when a module is removed from the fabric
        switch all the port entries in this table 
        corresponding to that module are removed.
        This table also hold entries for Port Channel ports.  
        NOTE: Nx_ports are not represented in this table."
    ::= { cffFcFeConfig 2 }

fcIfEntry OBJECT-TYPE
    SYNTAX          FcIfEntry
    MAX-ACCESS      not-accessible
    STATUS          current
    DESCRIPTION
        "Each entry contains FC-port configuration parameters
        and state information."
    INDEX           { ifIndex } 
    ::= { fcIfTable 1 }

FcIfEntry ::= SEQUENCE {
        fcIfWwn                     FcNameId,
        fcIfAdminMode               FcPortTypes,
        fcIfOperMode                FcPortTypes,
        fcIfAdminSpeed              FcIfSpeed,
        fcIfBeaconMode              TruthValue,
        fcIfPortChannelIfIndex      InterfaceIndexOrZero,
        fcIfOperStatusCause         FcIfOperStatusReason,
        fcIfOperStatusCauseDescr    SnmpAdminString,
        fcIfAdminTrunkMode          INTEGER,
        fcIfOperTrunkMode           INTEGER,
        fcIfAllowedVsanList2k       FcList,
        fcIfAllowedVsanList4k       FcList,
        fcIfActiveVsanList2k        FcList,
        fcIfActiveVsanList4k        FcList,
        fcIfBbCreditModel           FcBbCreditModel,
        fcIfHoldTime                MicroSeconds,
        fcIfTransmitterType         FcPortTxTypes,
        fcIfConnectorType           FcPortModuleTypes,
        fcIfSerialNo                SnmpAdminString,
        fcIfRevision                SnmpAdminString,
        fcIfVendor                  SnmpAdminString,
        fcIfSFPSerialIDData         SnmpAdminString,
        fcIfPartNumber              SnmpAdminString,
        fcIfAdminRxBbCredit         FcBbCredit,
        fcIfAdminRxBbCreditModeISL  FcBbCredit,
        fcIfAdminRxBbCreditModeFx   FcBbCredit,
        fcIfOperRxBbCredit          FcBbCredit,
        fcIfRxDataFieldSize         FcRxDataFieldSize,
        fcIfActiveVsanUpList2k      FcList,
        fcIfActiveVsanUpList4k      FcList,
        fcIfPortRateMode            INTEGER,
        fcIfAdminRxPerfBuffer       FcPerfBuffer,
        fcIfOperRxPerfBuffer        FcPerfBuffer,
        fcIfBbScn                   Unsigned32,
        fcIfPortInitStatus          TruthValue,
        fcIfAdminRxBbCreditExtended FcBbCredit,
        fcIfFcTunnelIfIndex         InterfaceIndexOrZero,
        fcIfServiceState            FcIfServiceStateType,
        fcIfAdminBbScnMode          TruthValue,
        fcIfPortType                INTEGER,
        fcIfAdminFECState           INTEGER,
        fcIfOperFECState            INTEGER
}

fcIfWwn OBJECT-TYPE
    SYNTAX          FcNameId
    MAX-ACCESS      read-only
    STATUS          current
    DESCRIPTION
        "The World-Wide Name of this FC-Port. It's a 64-bit
        identifier and is unique worldwide." 
    ::= { fcIfEntry 1 }

fcIfAdminMode OBJECT-TYPE
    SYNTAX          FcPortTypes
    MAX-ACCESS      read-write
    STATUS          current
    DESCRIPTION
        "The port mode configured by the user. If the user
        configured the port as auto(1), then the port 
        initialization scheme determines the mode of the port.
        In this case the user can look at 'fcIfOperMode' to 
        determine the current operating mode of port.
        If this interface is a Port Channel port then only
        auto(1) or ePort(4) is allowed."
    DEFVAL          { auto } 
    ::= { fcIfEntry 2 }

fcIfOperMode OBJECT-TYPE
    SYNTAX          FcPortTypes
    MAX-ACCESS      read-only
    STATUS          current
    DESCRIPTION
        "The current operating mode of the port.
        This object will also be an additional varbind sent
        in the linkUp notification ( defined in IF-MIB ) in
        addition to the varbinds defined for this notification." 
    ::= { fcIfEntry 3 }

fcIfAdminSpeed OBJECT-TYPE
    SYNTAX          FcIfSpeed
    MAX-ACCESS      read-write
    STATUS          current
    DESCRIPTION
        "The port speed configured by the user.
        If this interface is a member of a port channel port
        then this object cannot be modified. 
        Since this is a characteristic of a physical port, this
        object may not be applicable for some non-physical
        ports, i.e., the value is instantiated but its value is
        irrelevant."
    DEFVAL          { auto } 
    ::= { fcIfEntry 4 }

fcIfBeaconMode OBJECT-TYPE
    SYNTAX          TruthValue
    MAX-ACCESS      read-write
    STATUS          current
    DESCRIPTION
        "The Beacon mode configured by the user.
        If 'true', the Beacon mode is enabled.
        If 'false', the beacon mode is disabled.
        In Beacon mode, an interface LED is put into flashing 
        mode for easy identification of a particular
        interface."
    DEFVAL          { true } 
    ::= { fcIfEntry 5 }

fcIfPortChannelIfIndex OBJECT-TYPE
    SYNTAX          InterfaceIndexOrZero
    MAX-ACCESS      read-only
    STATUS          current
    DESCRIPTION
        "The ifIndex of the port channel port this port belongs
        to.
        A value of zero indicates that this port is not part
        of any port channel.
        For port channel port this object will have the ifIndex
        of the port channel port itself." 
    ::= { fcIfEntry 6 }

fcIfOperStatusCause OBJECT-TYPE
    SYNTAX          FcIfOperStatusReason
    MAX-ACCESS      read-only
    STATUS          current
    DESCRIPTION
        "The cause of current operational state of the
        port.
        The current operational state of the port is shown by 
        the 'ifOperStatus' defined in IF-MIB. This object
        will show 'none(2)' for all the 'ifOperStatus' values
        except for 'down(2)'. It will show one of the values
        from the 'FcIfOperStatusReason' textual convention
        if 'ifOperStatus' is 'down(2)'. It will show other(1)
        if the operational status cause is not from one
        defined in  'FcIfOperStatusReason'.
        This object will also be an additional varbind sent
        in the linkDown notification ( defined in IF-MIB ) in 
        addition to the varbinds defined for this notification." 
    ::= { fcIfEntry 7 }

fcIfOperStatusCauseDescr OBJECT-TYPE
    SYNTAX          SnmpAdminString
    MAX-ACCESS      read-only
    STATUS          current
    DESCRIPTION
        "The description for the cause of current operational
        state of the port, shown by the object 
        'fcIfOperStatusCause'." 
    ::= { fcIfEntry 8 }

fcIfAdminTrunkMode OBJECT-TYPE
    SYNTAX          INTEGER  {
                        nonTrunk(1),
                        trunk(2),
                        auto(3)
                    }
    MAX-ACCESS      read-write
    STATUS          current
    DESCRIPTION
        "The trunking mode configured by the user.
        When set to 'nonTrunk(1)', the port negotiates and
        converts the link into non-trunking mode. This port
        and the neighboring port's fcIfOperTrunkMode becomes
        non-trunk. When set to 'trunk(2)', the port 
        negotiates and converts the link into trunking mode
        only if the neighboring port, fcIfAdminTrunkMode is
        either 'trunk(2)' or 'auto(3)'. When set to 
        'auto(3)', the port is willing to convert the link
        to a trunk link only if the the neighboring port,
        fcIfAdminTrunkMode is set to 'trunk(2)' mode."
    DEFVAL          { nonTrunk } 
    ::= { fcIfEntry 9 }

fcIfOperTrunkMode OBJECT-TYPE
    SYNTAX          INTEGER  {
                        nonTrunk(1),
                        trunk(2)
                    }
    MAX-ACCESS      read-only
    STATUS          current
    DESCRIPTION
        "The current trunking mode of the port." 
    ::= { fcIfEntry 10 }

fcIfAllowedVsanList2k OBJECT-TYPE
    SYNTAX          FcList
    MAX-ACCESS      read-write
    STATUS          current
    DESCRIPTION
        "The list of VSANs (in the range 0 through 2047)
        which are allowed to be received/transmitted on the
        port when the port is operating in trunking mode.
        Only ports operating in trunk mode can belong to 
        multiple VSANs. Each octet within the value of this
        object specifies a set of eight VSANs, with the first
        octet specifying VSANs 0 through 7, the second octet
        specifying VSANs 8 through 15, etc. Within each octet,
        the most significant bit represents the lowest
        numbered VSAN, and the least significant bit
        represents the highest numbered VSAN.  Thus, each 
        VSAN, is represented by a single bit within the value
        of this object. The corresponding VSAN is allowed on 
        this port if and only if that bit has a value of '1'.
        VSAN 0 is reserved.
        This object is applicable to only ports operating
        in trunk mode.
        The value configured to this object will be retained 
        but will not be applicable when the port is put into
        non-trunking mode. It will be again applicable when
        the port is operating in trunking mode.
        Similarly, it can be modified at the time when this
        object is not applicable, i.e. when the port is 
        operating in non-trunking mode, but the modified value
        is retained for use on subsequent occasions when this
        object is applicable when the port is operating in 
        trunking mode." 
    ::= { fcIfEntry 11 }

fcIfAllowedVsanList4k OBJECT-TYPE
    SYNTAX          FcList
    MAX-ACCESS      read-write
    STATUS          current
    DESCRIPTION
        "The list of VSANs (in the range 2048 to 4096 )
        which are allowed to be received/transmitted on the
        port when the port is operating in trunking mode.
        Only ports operating in trunk mode can belong to 
        multiple VSANs. Each octet within the value of this
        object specifies a set of eight VSANs, with the first
        octet specifying VSANs 2048 through 2055, the second
        octet specifying VSANs 2056 through 2063, etc. Within
        each octet, the most significant bit represents the
        lowest numbered VSAN, and the least significant bit
        represents the highest numbered VSAN.  Thus, each 
        VSAN, is represented by a single bit within the value
        of this object. The corresponding VSAN is allowed on 
        this port if and only if that bit has a value of '1'.
        This object is applicable to only ports operating
        in trunk mode.
        The value configured to this object will be retained 
        but will not be applicable when the port is put into
        non-trunking mode. It will be again applicable when
        the port is operating in trunking mode.
        Similarly, it can be modified at the time when this
        object is not applicable, i.e. when the port is 
        operating in non-trunking mode, but the modified value
        is retained for use on subsequent occasions when this
        object is applicable when the port is operating in 
        trunking mode." 
    ::= { fcIfEntry 12 }

fcIfActiveVsanList2k OBJECT-TYPE
    SYNTAX          FcList
    MAX-ACCESS      read-only
    STATUS          current
    DESCRIPTION
        "The list of VSANs (in the range 0 through 2047)
        this port is associated with. Only ports
        operating in trunk mode can belong to multiple VSANs.
        Each octet within the value of this object specifies 
        a set of eight VSANs, with the first octet specifying
        VSANs 0 through 7, the second octet specifying 
        VSANs 8 through 15, etc. Within each octet, the most
        significant bit represents the lowest numbered
        VSAN, and the least significant bit represents the
        highest numbered VSAN. Thus, each VSAN, that this port
        is associated with, is represented by a single 
        bit within the value of this object. The corresponding 
        VSAN that this port is a member of is active if and
        only if that bit has a value of '1'. 
        Note that the zero-length string represents that none 
        of the VSANs that this port is a member of are active.
        VSAN 0 is reserved.
        This object is applicable to only ports operating
        in trunk mode." 
    ::= { fcIfEntry 13 }

fcIfActiveVsanList4k OBJECT-TYPE
    SYNTAX          FcList
    MAX-ACCESS      read-only
    STATUS          current
    DESCRIPTION
        "The list of VSANs (in the range 2048 through 4096)
        this port is associated with. Only ports
        operating in trunk mode can belong to multiple VSANs.
        Each octet within the value of this object specifies 
        a set of eight VSANs, with the first octet specifying
        VSANs 2048 through 2055, the second octet specifying 
        VSANs 2056 through 2063, etc. Within each octet, the
        most significant bit represents the lowest numbered
        VSAN, and the least significant bit represents the
        highest numbered VSAN.  Thus, each VSAN, that this port
        is associated with, is represented by a single 
        bit within the value of this object. The corresponding 
        VSAN that this port is a member of is active if and
        only if that bit has a value of '1'. 
        Note that the zero-length string represents that none 
        of the VSANs that this port is a member of are active.
        This object is applicable to only ports operating
        in trunk mode." 
    ::= { fcIfEntry 14 }

fcIfBbCreditModel OBJECT-TYPE
    SYNTAX          FcBbCreditModel
    MAX-ACCESS      read-only
    STATUS          current
    DESCRIPTION
        "The BB_Credit model used by the FC-port.
        The alternate BB_Credit management model can be used 
        in the arbitrated loop topology to manage the flow of
        frames between the two ports participating in the
        current loop circuit.
        Since this is a characteristic of a physical port, this
        object is not applicable for Port Channel ports, i.e.,
        the value is instantiated but its value is irrelevant." 
    ::= { fcIfEntry 15 }

fcIfHoldTime OBJECT-TYPE
    SYNTAX          MicroSeconds
    UNITS           "microseconds"
    MAX-ACCESS      read-only
    STATUS          current
    DESCRIPTION
        "The maximum time that the FC-Port shall hold a frame
        in the transmitter buffer before discarding it, if it
        is unable to deliver the frame. 
        The value 0 in this object means the frame will be
        discarded immediately if the port is unable to deliver
        the frame.
        Since this is a characteristic of a physical port, this
        object is not applicable for Port Channel ports, i.e.,
        the value is instantiated but its value is irrelevant." 
    ::= { fcIfEntry 16 }

fcIfTransmitterType OBJECT-TYPE
    SYNTAX          FcPortTxTypes
    MAX-ACCESS      read-only
    STATUS          current
    DESCRIPTION
        "The technology of the port transceiver.
        Since this is a characteristic of a physical port, this
        object is not applicable for Port Channel ports, i.e.,
        the value is instantiated but its value is irrelevant." 
    ::= { fcIfEntry 17 }

fcIfConnectorType OBJECT-TYPE
    SYNTAX          FcPortModuleTypes
    MAX-ACCESS      read-only
    STATUS          current
    DESCRIPTION
        "The module type of the port connector. This object
        refers to the hardware implementation of the port.
        It will be 'embedded' if the hardware equivalent to
        Gigabit interface card ( GBIC ) is part of the line
        card and is unremovable. It will be 'glm' if its a
        gigabit link module ( GLM ). A GLM has a different form
        factor than GBIC. GLM is not supported by our switch.
        It will be 'gbicWithSerialID' if the GBIC serial id 
        can be read, else it will be 'gbicWithoutSerialID'.
        It will be 'sfpWithSerialID', if the small form 
        factor ( SFP ) pluggable GBICs serial id can be read, 
        else it will be 'sfpWithoutSerialID'.
        Since this is a characteristic of a physical port, this
        object is not applicable for Port Channel ports, i.e.,
        the value is instantiated but its value is irrelevant." 
    ::= { fcIfEntry 18 }

fcIfSerialNo OBJECT-TYPE
    SYNTAX          SnmpAdminString
    MAX-ACCESS      read-only
    STATUS          current
    DESCRIPTION
        "The serial number of the connector unit ( e.g.,
        for a GBIC ). If this is not applicable, return a
        zero-length string.
        Since this is a characteristic of a physical port, this
        object is not applicable for Port Channel ports, i.e.,
        the value is instantiated but its value is irrelevant." 
    ::= { fcIfEntry 19 }

fcIfRevision OBJECT-TYPE
    SYNTAX          SnmpAdminString
    MAX-ACCESS      read-only
    STATUS          current
    DESCRIPTION
        "The port revision of the connector unit (e.g., for a
        GBIC). If this is not applicable it returns a
        zero-length string.
        Since this is a characteristic of a physical port, this
        object is not applicable for Port Channel ports, i.e.,
        the value is instantiated but its value is irrelevant." 
    ::= { fcIfEntry 20 }

fcIfVendor OBJECT-TYPE
    SYNTAX          SnmpAdminString
    MAX-ACCESS      read-only
    STATUS          current
    DESCRIPTION
        "The connector unit ( e.g., for a GBIC ) vendor.
        If this is not applicable it returns a
        zero-length string.
        Since this is a characteristic of a physical port, this
        object is not applicable for Port Channel ports, i.e.,
        the value is instantiated but its value is irrelevant." 
    ::= { fcIfEntry 21 }

fcIfSFPSerialIDData OBJECT-TYPE
    SYNTAX          SnmpAdminString
    MAX-ACCESS      read-only
    STATUS          current
    DESCRIPTION
        "The connector unit ( e.g., for a GBIC ) Serial ID
        data.
        If this is not applicable it returns a
        zero-length string.
        Since this is a characteristic of a physical port, this
        object is not applicable for Port Channel ports, i.e.,
        the value is instantiated but its value is irrelevant." 
    ::= { fcIfEntry 22 }

fcIfPartNumber OBJECT-TYPE
    SYNTAX          SnmpAdminString
    MAX-ACCESS      read-only
    STATUS          current
    DESCRIPTION
        "The connector unit ( e.g., for a GBIC ) part number.
        If this is not applicable it returns a
        zero-length string.
        Since this is a characteristic of a physical port, this
        object is not applicable for Port Channel ports, i.e.,
        the value is instantiated but its value is irrelevant." 
    ::= { fcIfEntry 23 }

fcIfAdminRxBbCredit OBJECT-TYPE
    SYNTAX          FcBbCredit
    UNITS           "buffers"
    MAX-ACCESS      read-write
    STATUS          current
    DESCRIPTION
        "The receive buffer-to-buffer credits configured for
        this port. If the value configured is zero, then
        the value of the object fcIfCapOsmRxBbCreditDefault or 
        fcIfCapFrmRxBbCreditDefault is used if the port is 
        operating in Fx mode. Value of 
        fcIfCapOsmRxBbCreditDefault is used if fcIfPortRateMode
        is 'shared'. Value of fcIfCapFrmRxBbCreditDefault is 
        used if fcIfPortRateMode is 'dedicated'.
        Similarly, if the port is operating in inter switch link
        (ISL) mode then the value of the object 
        fcIfCapOsmISLRxBbCreditDefault or 
        fcIfCapFrmISLRxBbCreditDefault is used. Value of
        fcIfCapOsmISLRxBbCreditDefault is used if 
        fcIfPortRateMode is 'shared'. Value of 
        fcIfCapFrmISLRxBbCreditDefault is used if 
        fcIfPortRateMode is 'dedicated'. 
        If a non-zero value is configured for this object then,
        if the values configured for fcIfAdminRxBbCreditModeISL
        and fcIfAdminRxBbCreditModeFx is zero, then the 
        value of this object is used for the port operating
        in either Fx or ISL port mode. But if
        fcIfAdminRxBbCreditModeISL is configured with a valid
        value, then the value of fcIfAdminRxBbCreditModeISL 
        object is used instead of this value, if the port is
        operating in  ISL port mode. Similarly, if
        the values configured for fcIfAdminRxBbCreditModeFx
        is valid, then the value of fcIfAdminRxBbCreditModeFx
        object is used instead of this value, if the port is
        operating in Fx mode. 
        If this object is set to non-zero value then
        objects fcIfAdminRxBbCreditModeISL and 
        fcIfAdminRxBbCreditModeFx are set to zero at that time.
        But later the objects fcIfAdminRxBbCreditModeISL and
        fcIfAdminRxBbCreditModeFx can be configured to non-zero
        values even if this object present value is non-zero. 

        NOTE: The value of this object is not used if 
        cfcFeatureCtrlIndex object is configured with a value 
        of 'extenedCredit' and fcIfAdminRxBbCreditExtended 
        object is configured."
    REFERENCE       "cfcFeatureCtrlIndex in CISCO-FEATURE-CONTROL-MIB." 
    ::= { fcIfEntry 24 }

fcIfAdminRxBbCreditModeISL OBJECT-TYPE
    SYNTAX          FcBbCredit
    UNITS           "buffers"
    MAX-ACCESS      read-write
    STATUS          current
    DESCRIPTION
        "The receive buffer-to-buffer credits configured for
        this port to be used if it is operating in 
        xE_port mode.

        NOTE: The value of this object is not used if 
        cfcFeatureCtrlIndex object is configured with a value 
        of 'extenedCredit' and fcIfAdminRxBbCreditExtended 
        object is configured."
    REFERENCE       "cfcFeatureCtrlIndex in CISCO-FEATURE-CONTROL-MIB." 
    ::= { fcIfEntry 25 }

fcIfAdminRxBbCreditModeFx OBJECT-TYPE
    SYNTAX          FcBbCredit
    UNITS           "buffers"
    MAX-ACCESS      read-write
    STATUS          current
    DESCRIPTION
        "The receive buffer-to-buffer credits configured for
        this port to be used if it is operating in 
        Fx mode.

        NOTE: The value of this object is not used if 
        cfcFeatureCtrlIndex object is configured with a value 
        of 'extenedCredit' and fcIfAdminRxBbCreditExtended 
        object is configured."
    REFERENCE       "cfcFeatureCtrlIndex in CISCO-FEATURE-CONTROL-MIB." 
    ::= { fcIfEntry 26 }

fcIfOperRxBbCredit OBJECT-TYPE
    SYNTAX          FcBbCredit
    UNITS           "buffers"
    MAX-ACCESS      read-only
    STATUS          current
    DESCRIPTION
        "The receive buffer-to-buffer credits configured for
        the operational port mode." 
    ::= { fcIfEntry 27 }

fcIfRxDataFieldSize OBJECT-TYPE
    SYNTAX          FcRxDataFieldSize
    UNITS           "bytes"
    MAX-ACCESS      read-write
    STATUS          current
    DESCRIPTION
        "The largest Data_Field size for an FT_1 frame that
        can be received by this port." 
    ::= { fcIfEntry 28 }

fcIfActiveVsanUpList2k OBJECT-TYPE
    SYNTAX          FcList
    MAX-ACCESS      read-only
    STATUS          current
    DESCRIPTION
        "The list of VSANs (in the range 0 through 2047) whose
        operational state is 'up', that this port is 
        associated with. Only ports operating in trunk mode
        can be associated to multiple VSANs.
        Each octet within the value of this object specifies 
        a set of eight VSANs, with the first octet specifying
        VSANs 0 through 7, the second octet specifying 
        VSANs 8 through 15, etc. Within each octet, the most
        significant bit represents the lowest numbered
        VSAN, and the least significant bit represents the
        highest numbered VSAN. Thus, each VSAN, whose 
        operational state is 'up', that this port is 
        associated with, is represented by a single bit within
        the value of this object. The corresponding 
        VSAN that this port is a member of is operationally
        'up' if and only if that bit has a value of '1'. 
        Note that the zero-length string represents that none 
        of the VSANs that this port is a member of are 
        operationally 'up'. VSAN 0 is reserved.
        This object is applicable to only ports operating
        in trunk mode." 
    ::= { fcIfEntry 29 }

fcIfActiveVsanUpList4k OBJECT-TYPE
    SYNTAX          FcList
    MAX-ACCESS      read-only
    STATUS          current
    DESCRIPTION
        "The list of VSANs (in the range 2048 to 4096 ) whose
        operational state is 'up', that this port is 
        associated with. Only ports operating in trunk mode
        can be associated to multiple VSANs.
        Each octet within the value of this object specifies 
        a set of eight VSANs, with the first octet specifying
        VSANs 2048 through 2055, the second octet specifying 
        VSANs 2056 through 2063, etc. Within each octet, the
        most significant bit represents the lowest numbered
        VSAN, and the least significant bit represents the
        highest numbered VSAN.  Thus, each VSAN, whose 
        operational state is 'up', that this port is  
        associated with, is represented by a single bit within
        the value of this object. The corresponding 
        VSAN that this port is a member of is operationally
        'up' if and only if that bit has a value of '1'.
        Note that the zero-length string represents that none 
        of the VSANs that this port is a member of are active.
        This object is applicable to only ports operating
        in trunk mode." 
    ::= { fcIfEntry 30 }

fcIfPortRateMode OBJECT-TYPE
    SYNTAX          INTEGER  {
                        dedicated(1),
                        shared(2)
                    }
    MAX-ACCESS      read-write
    STATUS          current
    DESCRIPTION
        "The rate of data traffic supported by this port.

        'dedicated'  - this interface is operating in 
                       dedicated rate mode. In dedicated rate 
                       mode each interface has an allocated 
                       fabric bandwidth to sustain line rate 
                       traffic at the maximum configured 
                       operating speed.

        'shared'     - this interface is operating in over 
                       subscription mode. In over subscription 
                       mode the available fabric bandwidth of 
                       a link is shared by more than one 
                       interface, so that multiple front panel 
                       ports share the same link internally to 
                       the switch fabric.

        For modules that are capable of switching between 
        'dedicated' and 'shared' modes, certain restrictions 
        apply based on the available bandwidth and speed. 
        The keywords 'osm' and 'shared', 'frm' and 'dedicated' 
        are interchangeable." 
    ::= { fcIfEntry 31 }

fcIfAdminRxPerfBuffer OBJECT-TYPE
    SYNTAX          FcPerfBuffer
    UNITS           "buffers"
    MAX-ACCESS      read-write
    STATUS          current
    DESCRIPTION
        "The performance buffers configured for this port. These
        buffers in addition to the buffer-to-buffer credits are 
        used to improve the performance of a port, hence called
        'Performance buffers'. If a value of zero is set for this
        object, then the agent uses the built-in algorithm to
        calculate the number of performance buffers to be used."
    DEFVAL          { 0 } 
    ::= { fcIfEntry 32 }

fcIfOperRxPerfBuffer OBJECT-TYPE
    SYNTAX          FcPerfBuffer
    UNITS           "buffers"
    MAX-ACCESS      read-only
    STATUS          current
    DESCRIPTION
        "The performance buffers presently operational on this
        port." 
    ::= { fcIfEntry 33 }

fcIfBbScn OBJECT-TYPE
    SYNTAX          Unsigned32
    MAX-ACCESS      read-only
    STATUS          current
    DESCRIPTION
        "The buffer-to-buffer state change number operational on
        this interface."
    REFERENCE       "FC-FS REV1_90 Section 15.6.2.5" 
    ::= { fcIfEntry 34 }

fcIfPortInitStatus OBJECT-TYPE
    SYNTAX          TruthValue
    MAX-ACCESS      read-only
    STATUS          current
    DESCRIPTION
        "If 'true', this port successfully completed a
        link initialization or there was an error during link
        initialization.
        If 'false', this port did not perform successful link
        initialization since it was brought down by the 
        user or switch was powered up." 
    ::= { fcIfEntry 35 }

fcIfAdminRxBbCreditExtended OBJECT-TYPE
    SYNTAX          FcBbCredit
    UNITS           "buffers"
    MAX-ACCESS      read-write
    STATUS          current
    DESCRIPTION
        "This object specifies the extended BB credits
        that can be configured on an FC port (in the  
        range 256 through 4095).  The acceptable value 
        depends on the BB credit configuration of other 
        ports in the line card. Since this is an optional 
        feature, the value of this object can only be 
        modified after (enabling extended credit feature) 
        cfcFeatureCtrlIndex object is configured with a
        value of 'extenedCredit'. If extended credit
        feature is enabled, the MIB objects 
        fcIfAdminRxBbCredit, fcIfAdminRxBbCreditModeISL, 
        fcIfAdminRxBbCreditModeFx values are not used;
        instead fcIfAdminRxBbCreditExtended is used
        regardless of port mode operation. If
        extended credit feature is disabled, the previous
        configured values of fcIfAdminRxBbCredit
        fcIfAdminRxBbCreditModeISL, 
        fcIfAdminRxBbCreditModeFx are used as defined.

        NOTE: This object can be modified only on certain
        modules having hardware capability to support the
        extended BB credit feature."
    REFERENCE       "cfcFeatureCtrlIndex in CISCO-FEATURE-CONTROL-MIB." 
    ::= { fcIfEntry 36 }

fcIfFcTunnelIfIndex OBJECT-TYPE
    SYNTAX          InterfaceIndexOrZero
    MAX-ACCESS      read-write
    STATUS          current
    DESCRIPTION
        "This object specifies the ifIndex of a FC tunnel
        that represents a logical Fibre Channel data path
        between a source switch and destination switch.
        RSPAN uses a special FC tunnel that originates
        at the ST port in the source switch and terminates
        at the SD port in the destination switch. The FC
        tunnel must be first bound to an ST port in the source
        switch and then mapped to an SD port in the destination
        switch for RSPAN feature configuration, which enables
        monitoring traffic from a remote switch.
        A value of zero indicates that no FC tunnel is mapped to
        a ST port.

        GLOSSARY:
        SPAN: Switch Port Analyzer (SPAN) is a feature that
           enables user to analyze network traffic in a
           switched network using network analyzer attached
           to a switch port.

        RSPAN: Remote SPAN that enables monitoring of traffic
           from remote switches.

        FC tunnel: An FC tunnel is a logical data path
           between a source switch and destination switch.

        SPAN tunnel (ST) port: The ST port is used to forward
           traffic to FC tunnel.

        SPAN destination (SD) port: The SD port is used to 
           forward traffic to an Analyzer for monitoring 
           purposes." 
    ::= { fcIfEntry 37 }

fcIfServiceState OBJECT-TYPE
    SYNTAX          FcIfServiceStateType
    MAX-ACCESS      read-write
    STATUS          current
    DESCRIPTION
        "The service state of the interface. Some but not all
        interfaces, e.g., those on hardware modules with a 
        capability of supporting shared resources, can have 
        their state changed to 'outOfService'. Examples of 
        such shared resources include speed/bandwidth and 
        buffer memory. Shared resources include the values 
        of the following objects:

          fcIfAdminSpeed,
          fcIfAdminMode,
          fcIfPortRateMode,
          fcIfAdminRxBbCredit,
          fcIfAdminRxBbCreditModeISL,
          fcIfAdminRxBbCreditModeFx,
          fcIfAdminRxBbCreditExtended,
          fcIfAdminRxPerfBuffer.

        When an attempt is made to change a particular 
        interface's value for this object to 'outOfService':
          - if the interface's ifAdminStatus is 'up' or if the
            interface is a part of a Port channel, then the 
            change to the value of this object is rejected.
          - if the interface's value of this object is 
            successfully changed to 'outOfService', then each 
            and every user-configured parameter value of the 
            above-listed shared resource objects for that 
            interface is set to its default value.

        When an interface is in the 'outOfService' state then:
          - the interface is not operational and no packets 
            can be passed,
          - the interface's shared resource objects can not be
            configured to non-default values,
          - the interface cannot be added to a port channel.
          - the interface cannot be involved in a port swap 
            (using cficonPortSwapTable in CISCO-FICON-MIB).
          - ifAdminStatus in IF-MIB cannot be changed to 'up' 
            state.
          - other interface objects are not affected.

        Changing the value of this object on one interface to
        'outOfService' does not affect the functionality of any 
        other interface.

        When an attempt is made to change a particular interface's
        value for this object to 'inService', the attempt is 
        rejected if necessary shared resources are unavailable."
    DEFVAL          { inService } 
    ::= { fcIfEntry 38 }

fcIfAdminBbScnMode OBJECT-TYPE
    SYNTAX          TruthValue
    MAX-ACCESS      read-write
    STATUS          current
    DESCRIPTION
        "The Buffer-to-buffer State Change Number (BB_SC_N)
        field (word 1, bits 15-12) specifies the 
        Buffer-to-buffer State Change Number. It indicates 
        that the sender of the PLOGI or FLOGI frame is
        requesting 2 power BB_SC_N number of frames to be 
        sent between two consecutive BB_SCs primitives, and 
        2 power BB_SC_N number of R_RDY primitives to be
        sent between two consecutive BB_SCr primitives. 
        If 'true', the BB_SC_N mode is enabled.
        If 'false', the BB_SC_N mode is disabled."
    REFERENCE       "FC-FS-2 Rev 1.90, Section 15.6.2.5 BB_SC_N."
    DEFVAL          { true } 
    ::= { fcIfEntry 39 }

fcIfPortType OBJECT-TYPE
    SYNTAX          INTEGER  {
                        internal(1),
                        external(2)
                    }
    MAX-ACCESS      read-only
    STATUS          current
    DESCRIPTION
        "Indicates whether this interface is internal orexternal
        interface on the chassis.   
        internal(1) -  This type of interface is not accessible via an
        externally-mounted connector on the device   
        external(2) - This type of interface is accessible via an
        externally-mounted connector on the device
        Except on certain platforms, the interfaces are usually of the
        fcIfPortType 'external'." 
    ::= { fcIfEntry 40 }

fcIfAdminFECState OBJECT-TYPE
    SYNTAX          INTEGER  {
                        up(1),
                        down(2)
                    }
    MAX-ACCESS      read-write
    STATUS          current
    DESCRIPTION
        "The port FEC state configured by the user.
        When set to up(1), the port negotiates and
        converts the link into operational FEC up
        only if the neighboring port fcIfAdminFECState
        is up(1). When set to down(2) the fcIfOperFECState
        for this port and the neighboring port remains
        down(2) after negotiation. If this interface is a 
        member of a port channel then this object cannot be
        modified."
    DEFVAL          { down } 
    ::= { fcIfEntry 41 }

fcIfOperFECState OBJECT-TYPE
    SYNTAX          INTEGER  {
                        up(1),
                        down(2)
                    }
    MAX-ACCESS      read-only
    STATUS          current
    DESCRIPTION
        "The current operating FEC state of the port.The
        value is down(2) by default. If fcIfAdminFECState
        is up(1) for a physical port, the port negotiates
        and converts the link into operational FEC up only
        if the neighboring port fcIfAdminFECState is up(1)."
    DEFVAL          { down } 
    ::= { fcIfEntry 42 }
 

-- fcTrunkIfTable.

fcTrunkIfTable OBJECT-TYPE
    SYNTAX          SEQUENCE OF FcTrunkIfEntry 
    MAX-ACCESS      not-accessible
    STATUS          current
    DESCRIPTION
        "This table contains one entry for each trunking fibre
        channel port per VSAN. When the FC-port goes
        into trunking mode, the fibre channel switch creates
        one entry per FC-port for each active VSAN, from the
        allowed VSAN list for this port. 
        The allowed VSAN list is configured using the objects,
        fcIfAllowedVsanList2k and fcIfAllowedVsanList4k. 
        If an VSAN becomes inactive then the switch removes the
        corresponding entries from this table, if they exist."
    ::= { cffFcFeConfig 3 }

fcTrunkIfEntry OBJECT-TYPE
    SYNTAX          FcTrunkIfEntry
    MAX-ACCESS      not-accessible
    STATUS          current
    DESCRIPTION
        "Each entry contains trunking FC-port parameters."
    INDEX           {
                        ifIndex,
                        vsanIndex
                    } 
    ::= { fcTrunkIfTable 1 }

FcTrunkIfEntry ::= SEQUENCE {
        fcTrunkIfOperStatus           INTEGER,
        fcTrunkIfOperStatusCause      FcIfOperStatusReason,
        fcTrunkIfOperStatusCauseDescr SnmpAdminString
}

fcTrunkIfOperStatus OBJECT-TYPE
    SYNTAX          INTEGER  {
                        up(1),
                        down(2)
                    }
    MAX-ACCESS      read-only
    STATUS          current
    DESCRIPTION
        "The operational state of a VSAN on this port. If the port
        is in trunking mode, it is possible that the port state
        may be 'down(2)' only in some VSANs. If this port is down
        in this VSAN only then port state shown by 'ifOperStatus'
        may not be 'down(2)', but this object will show 
        'down(2)'.
        The 'fcTrunkIfOperStatusCause' object shows the reason
        for port being 'down(2)'." 
    ::= { fcTrunkIfEntry 1 }

fcTrunkIfOperStatusCause OBJECT-TYPE
    SYNTAX          FcIfOperStatusReason
    MAX-ACCESS      read-only
    STATUS          current
    DESCRIPTION
        "The cause of current operational state of the
        port.
        The current operational state of the port is shown by 
        the 'fcTrunkIfOperStatus'. This object will show
        'none(2)' for all the 'fcTrunkIfOperStatus' values
        except for 'down(2)'. It will show one of the values
        from the 'FcIfOperStatusReason' textual convention
        if 'fcTrunkIfOperStatus' is 'down(2)'." 
    ::= { fcTrunkIfEntry 2 }

fcTrunkIfOperStatusCauseDescr OBJECT-TYPE
    SYNTAX          SnmpAdminString
    MAX-ACCESS      read-only
    STATUS          current
    DESCRIPTION
        "The description for the cause of current operational
        state of the port, shown by the object 
        'fcTrunkIfOperStatusCause'." 
    ::= { fcTrunkIfEntry 3 }
 


-- The FC-Port Fabric Login Group

fcIfLoginEntryCount OBJECT-TYPE
    SYNTAX          Unsigned32
    MAX-ACCESS      read-only
    STATUS          current
    DESCRIPTION
        "The number of login entries in fcIfFLoginTable." 
    ::= { cffFcFeConfig 4 }
-- fcIfFLoginTable

fcIfFLoginTable OBJECT-TYPE
    SYNTAX          SEQUENCE OF FcIfFLoginEntry 
    MAX-ACCESS      not-accessible
    STATUS          current
    DESCRIPTION
        "This table contains, one entry for each Nx_Port
        attached to a particular FC-port in this VSAN in the
        Fabric element.
        Each entry contains services parameters established 
        from the most recent Fabric Login, explicit or 
        implicit. In case of private devices attached to port,
        the fabric switch does the login on behalf of the
        private device. The fabric switch creates or deletes an
        entry in this table.
        Note: An FC-port may have one or more Nx_Port 
        logged-in to it."
    ::= { cffFcFeConfig 5 }

fcIfFLoginEntry OBJECT-TYPE
    SYNTAX          FcIfFLoginEntry
    MAX-ACCESS      not-accessible
    STATUS          current
    DESCRIPTION
        "An entry containing service parameters established
        by a successful Fabric Login to the port indicated
        by ifIndex."
    INDEX           {
                        ifIndex,
                        vsanIndex,
                        fcIfNxLoginIndex
                    } 
    ::= { fcIfFLoginTable 1 }

FcIfFLoginEntry ::= SEQUENCE {
        fcIfNxLoginIndex            Unsigned32,
        fcIfNxPortNodeName          FcNameId,
        fcIfNxPortName              FcNameId,
        fcIfNxPortAddress           FcAddressId,
        fcIfNxFcphVersionAgreed     FcphVersion,
        fcIfNxRxBbCredit            FcBbCredit,
        fcIfNxTxBbCredit            FcBbCredit,
        fcIfNxClass2RxDataFieldSize FcRxDataFieldSize,
        fcIfNxClass3RxDataFieldSize FcRxDataFieldSize,
        fcIfNxCosSuppAgreed         FcClassOfServices,
        fcIfNxClass2SeqDelivAgreed  TruthValue,
        fcIfNxClass3SeqDelivAgreed  TruthValue
}

fcIfNxLoginIndex OBJECT-TYPE
    SYNTAX          Unsigned32
    MAX-ACCESS      not-accessible
    STATUS          current
    DESCRIPTION
        "An arbitrary value identifying the associated Nx_Port
        in the attachment for which the entry contains
        information." 
    ::= { fcIfFLoginEntry 1 }

fcIfNxPortNodeName OBJECT-TYPE
    SYNTAX          FcNameId
    MAX-ACCESS      read-only
    STATUS          current
    DESCRIPTION
        "The world wide name of the Remote Node the
        logged-in Nx_Port belongs to." 
    ::= { fcIfFLoginEntry 2 }

fcIfNxPortName OBJECT-TYPE
    SYNTAX          FcNameId
    MAX-ACCESS      read-only
    STATUS          current
    DESCRIPTION
        "The world wide name of the logged-in Nx_Port." 
    ::= { fcIfFLoginEntry 3 }

fcIfNxPortAddress OBJECT-TYPE
    SYNTAX          FcAddressId
    MAX-ACCESS      read-only
    STATUS          current
    DESCRIPTION
        "The address identifier that has been assigned to the
        logged-in Nx_Port." 
    ::= { fcIfFLoginEntry 4 }

fcIfNxFcphVersionAgreed OBJECT-TYPE
    SYNTAX          FcphVersion
    MAX-ACCESS      read-only
    STATUS          current
    DESCRIPTION
        "The version of FC-PH that the Fx_Port has agreed to
        support from the Fabric Login." 
    ::= { fcIfFLoginEntry 5 }

fcIfNxRxBbCredit OBJECT-TYPE
    SYNTAX          FcBbCredit
    MAX-ACCESS      read-only
    STATUS          current
    DESCRIPTION
        "The maximum number of receive buffers available for
        holding Class 2, Class 3 received from the logged-in
        Nx_Port.
        It is for buffer-to-buffer flow control in the 
        incoming direction from the logged-in Nx_Port to 
        FC-port." 
    ::= { fcIfFLoginEntry 6 }

fcIfNxTxBbCredit OBJECT-TYPE
    SYNTAX          FcBbCredit
    MAX-ACCESS      read-only
    STATUS          current
    DESCRIPTION
        "The total number of buffers available for holding
        Class 2, Class 3 frames to be transmitted to 
        the logged-in Nx_Port.  
        It is for buffer-to-buffer flow control in the 
        direction from FC-Port to Nx_Port.
        The buffer-to-buffer flow control mechanism is 
        indicated in the respective fcIfBbCreditModel." 
    ::= { fcIfFLoginEntry 7 }

fcIfNxClass2RxDataFieldSize OBJECT-TYPE
    SYNTAX          FcRxDataFieldSize
    MAX-ACCESS      read-only
    STATUS          current
    DESCRIPTION
        "The Class 2 Receive Data Field Size of the logged-in
        Nx_Port. 
        This object specifies the largest Data Field Size for 
        an FT_1 frame that can be received by the Nx_Port." 
    ::= { fcIfFLoginEntry 8 }

fcIfNxClass3RxDataFieldSize OBJECT-TYPE
    SYNTAX          FcRxDataFieldSize
    MAX-ACCESS      read-only
    STATUS          current
    DESCRIPTION
        "The Class 3 Receive Data Field Size of the logged-in
        Nx_Port. 
        This object specifies the largest Data Field Size for 
        an FT_1 frame that can be received by the Nx_Port." 
    ::= { fcIfFLoginEntry 9 }

fcIfNxCosSuppAgreed OBJECT-TYPE
    SYNTAX          FcClassOfServices
    MAX-ACCESS      read-only
    STATUS          current
    DESCRIPTION
        "The object indicating the classes of services that
        the logged-in Nx_Port has requested the FC-Port to 
        support and the FC-Port has granted the request." 
    ::= { fcIfFLoginEntry 10 }

fcIfNxClass2SeqDelivAgreed OBJECT-TYPE
    SYNTAX          TruthValue
    MAX-ACCESS      read-only
    STATUS          current
    DESCRIPTION
        "The object indicating whether the FC-Port has agreed
        to support Class 2 sequential delivery during the 
        Fabric Login. This is meaningful only if Class 2 
        service has been agreed. This object is applicable only
        to Fx_Ports." 
    ::= { fcIfFLoginEntry 11 }

fcIfNxClass3SeqDelivAgreed OBJECT-TYPE
    SYNTAX          TruthValue
    MAX-ACCESS      read-only
    STATUS          current
    DESCRIPTION
        "The flag indicating whether the Fx_Port has agreed to
        support Class 3 sequential delivery during the Fabric
        Login. This is meaningful only if Class 3 service has
        been agreed. This object is applicable only to
        Fx_Ports." 
    ::= { fcIfFLoginEntry 12 }
 

-- fcIfElpTable

fcIfElpTable OBJECT-TYPE
    SYNTAX          SEQUENCE OF FcIfElpEntry 
    MAX-ACCESS      not-accessible
    STATUS          current
    DESCRIPTION
        "This table contains, one entry for each local
        Interconnect_Port that has performed Exchange Link
        Parameters Switch Fabric Internal Link Service
        exchange with its peer Interconnect_Port.
        Each entry contains Exchange Link Parameters
        established from the most recent ELP exchange between
        the 2 Interconnect_Port.
        The agent creates and deletes each entry in this 
        table. The agent creates an entry in this table on a
        successful completion of a ELP exchange. Similarly the
        agent deletes the entry when the port goes down.
        NOTE: Port Channel ports are not represented in 
        this table."
    ::= { cffFcFeConfig 6 }

fcIfElpEntry OBJECT-TYPE
    SYNTAX          FcIfElpEntry
    MAX-ACCESS      not-accessible
    STATUS          current
    DESCRIPTION
        "An entry containing Exchange Link parameters
        established between the Interconnect_Port indicated 
        by ifIndex and the peer Interconnect_Port indicated by 
        fcIfElpNbrPortName."
    INDEX           { ifIndex } 
    ::= { fcIfElpTable 1 }

FcIfElpEntry ::= SEQUENCE {
        fcIfElpNbrNodeName           FcNameId,
        fcIfElpNbrPortName           FcNameId,
        fcIfElpRxBbCredit            FcBbCredit,
        fcIfElpTxBbCredit            FcBbCredit,
        fcIfElpCosSuppAgreed         FcClassOfServices,
        fcIfElpClass2SeqDelivAgreed  TruthValue,
        fcIfElpClass2RxDataFieldSize FcRxDataFieldSize,
        fcIfElpClass3SeqDelivAgreed  TruthValue,
        fcIfElpClass3RxDataFieldSize FcRxDataFieldSize,
        fcIfElpClassFXII             TruthValue,
        fcIfElpClassFRxDataFieldSize FcRxDataFieldSize,
        fcIfElpClassFConcurrentSeq   Unsigned32,
        fcIfElpClassFEndToEndCredit  Unsigned32,
        fcIfElpClassFOpenSeq         Unsigned32
}

fcIfElpNbrNodeName OBJECT-TYPE
    SYNTAX          FcNameId
    MAX-ACCESS      read-only
    STATUS          current
    DESCRIPTION
        "The node world wide name of the peer Node." 
    ::= { fcIfElpEntry 1 }

fcIfElpNbrPortName OBJECT-TYPE
    SYNTAX          FcNameId
    MAX-ACCESS      read-only
    STATUS          current
    DESCRIPTION
        "The port world wide name of the peer Interconnect_Port." 
    ::= { fcIfElpEntry 2 }

fcIfElpRxBbCredit OBJECT-TYPE
    SYNTAX          FcBbCredit
    MAX-ACCESS      read-only
    STATUS          current
    DESCRIPTION
        "The maximum number of receive buffers available for
        holding Class 2, Class 3, Class F frames received from
        the peer Interconnect_Port.
        It is for buffer-to-buffer flow control in the 
        incoming direction from the peer Interconnect_Port to 
        local Interconnect_Port.
        The buffer-to-buffer flow control mechanism is 
        indicated in the respective fcIfBbCreditModel." 
    ::= { fcIfElpEntry 3 }

fcIfElpTxBbCredit OBJECT-TYPE
    SYNTAX          FcBbCredit
    MAX-ACCESS      read-only
    STATUS          current
    DESCRIPTION
        "The total number of buffers available for holding
        Class 2, Class 3, Class F frames to be transmitted to 
        the peer Interconnect_Port.  
        It is for buffer-to-buffer flow control in the 
        direction from the local Interconnect_Port to 
        peer Interconnect_Port.
        The buffer-to-buffer flow control mechanism is 
        indicated in the corresponding fcIfBbCreditModel." 
    ::= { fcIfElpEntry 4 }

fcIfElpCosSuppAgreed OBJECT-TYPE
    SYNTAX          FcClassOfServices
    MAX-ACCESS      read-only
    STATUS          current
    DESCRIPTION
        "The object indicating the classes of services that
        the peer Interconnect_Port has requested the local 
        Interconnect_Port to support and the local 
        Interconnect_Port has granted the request." 
    ::= { fcIfElpEntry 5 }

fcIfElpClass2SeqDelivAgreed OBJECT-TYPE
    SYNTAX          TruthValue
    MAX-ACCESS      read-only
    STATUS          current
    DESCRIPTION
        "The object indicating whether the local
        Interconnect_Port has agreed to support Class 2 
        sequential delivery during the Exchange Link 
        Parameters Switch Fabric Internal Link Service 
        request. This is meaningful only if Class 2 service 
        has been agreed." 
    ::= { fcIfElpEntry 6 }

fcIfElpClass2RxDataFieldSize OBJECT-TYPE
    SYNTAX          FcRxDataFieldSize
    MAX-ACCESS      read-only
    STATUS          current
    DESCRIPTION
        "The Class 2 Receive Data Field Size of the peer
        Interconnect_Port. 
        This object specifies the largest Data Field Size for 
        an FT_1 frame that can be received by the 
        Interconnect_Port. This is meaningful only if Class 2
        service has been agreed." 
    ::= { fcIfElpEntry 7 }

fcIfElpClass3SeqDelivAgreed OBJECT-TYPE
    SYNTAX          TruthValue
    MAX-ACCESS      read-only
    STATUS          current
    DESCRIPTION
        "The object indicating whether the local
        Interconnect_Port has agreed to support Class 3 
        sequential delivery during the Exchange Link 
        Parameters Switch Fabric Internal Link Service 
        request. This is meaningful only if Class 3 service 
        has been agreed." 
    ::= { fcIfElpEntry 8 }

fcIfElpClass3RxDataFieldSize OBJECT-TYPE
    SYNTAX          FcRxDataFieldSize
    MAX-ACCESS      read-only
    STATUS          current
    DESCRIPTION
        "The Class 3 Receive Data Field Size of the peer
        Interconnect_Port. 
        This object specifies the largest Data Field Size for 
        an FT_1 frame that can be received by the 
        Interconnect_Port. This is meaningful only if Class 3
        service has been agreed." 
    ::= { fcIfElpEntry 9 }

fcIfElpClassFXII OBJECT-TYPE
    SYNTAX          TruthValue
    MAX-ACCESS      read-only
    STATUS          current
    DESCRIPTION
        "The object when true(1) indicates that the peer
        Interconnect_Port supplying this parameter requires
        that an interlock be used during X_ID assignment in
        Class F.
        This is meaningful only if Class F service has been 
        agreed." 
    ::= { fcIfElpEntry 10 }

fcIfElpClassFRxDataFieldSize OBJECT-TYPE
    SYNTAX          FcRxDataFieldSize
    MAX-ACCESS      read-only
    STATUS          current
    DESCRIPTION
        "The Class F Receive Data Field Size of the peer
        Interconnect_Port. Class F service is always
        agreed between two Interconnect_Ports, and thus
        this object is always meaningful.
        This object specifies the largest Data Field Size for 
        an FT_1 frame that can be received by the 
        Interconnect_Port." 
    ::= { fcIfElpEntry 11 }

fcIfElpClassFConcurrentSeq OBJECT-TYPE
    SYNTAX          Unsigned32 (0..255)
    MAX-ACCESS      read-only
    STATUS          current
    DESCRIPTION
        "The object indicating the number of sequence status
        blocks provided by the Interconnect_Port supplying
        the parameters for tracking the progress of a sequence
        as a sequence recipient. The maximum number of 
        concurrent sequences that can be specified is 255. A
        value of zero in this field is reserved." 
    ::= { fcIfElpEntry 12 }

fcIfElpClassFEndToEndCredit OBJECT-TYPE
    SYNTAX          Unsigned32
    MAX-ACCESS      read-only
    STATUS          current
    DESCRIPTION
        "The object indicating the maximum number of Class F
        data frames which can be transmitted by an
        Interconnect_Port without receipt of accompanying
        ACK or Link_Response frames. The minimum value of
        end-to-end credit is one. The end-to-end credit
        field specified is associated with the number of
        buffers available for holding the Data_Field of a
        Class F frame and processing the contents of that
        Data_Field by the Interconnect_Port supplying the
        parameters." 
    ::= { fcIfElpEntry 13 }

fcIfElpClassFOpenSeq OBJECT-TYPE
    SYNTAX          Unsigned32
    MAX-ACCESS      read-only
    STATUS          current
    DESCRIPTION
        "The value of the open sequences per exchange shall
        specify the maximum number of sequences that can be 
        open at one time at the recipient between a pair of
        Interconnect_Ports for one exchange. This value is 
        used for exchange and sequence tracking." 
    ::= { fcIfElpEntry 14 }
 

-- fcIfCapTable

fcIfCapTable OBJECT-TYPE
    SYNTAX          SEQUENCE OF FcIfCapEntry 
    MAX-ACCESS      not-accessible
    STATUS          current
    DESCRIPTION
        "This table contains, one entry for each FC-Port.
        It contains information describing about what each
        FC-port is inherently capable in its current 
        configuration of operating or supporting.
        Entries in this table are created/deleted on an 
        as-needed basis by the agent. This table shows the
        capability of this port hardware as currently 
        configured.
        NOTE: This table has objects which represent the
        characteristics of a physical port. Thus, Port 
        Channel ports are not represented in this table. 
        The recommended method to get the current capability
        for the objects affected by the setting of 
        fcIfPortRateMode is to inspect the relevant objects in
        whichever table corresponds to the value of 
        fcIfPortRateMode.  As a result, the relevant objects in
        this table have been deprecated."
    ::= { cffFcFeConfig 7 }

fcIfCapEntry OBJECT-TYPE
    SYNTAX          FcIfCapEntry
    MAX-ACCESS      not-accessible
    STATUS          current
    DESCRIPTION
        "Each entry contains the Capability of a FC-Port."
    INDEX           { ifIndex } 
    ::= { fcIfCapTable 1 }

FcIfCapEntry ::= SEQUENCE {
        fcIfCapFcphVersionHigh               FcphVersion,
        fcIfCapFcphVersionLow                FcphVersion,
        fcIfCapRxBbCreditMax                 FcBbCredit,
        fcIfCapRxBbCreditMin                 FcBbCredit,
        fcIfCapRxDataFieldSizeMax            FcRxDataFieldSize,
        fcIfCapRxDataFieldSizeMin            FcRxDataFieldSize,
        fcIfCapCos                           FcClassOfServices,
        fcIfCapClass2SeqDeliv                TruthValue,
        fcIfCapClass3SeqDeliv                TruthValue,
        fcIfCapHoldTimeMax                   MicroSeconds,
        fcIfCapHoldTimeMin                   MicroSeconds,
        fcIfCapISLRxBbCreditMax              FcBbCredit,
        fcIfCapISLRxBbCreditMin              FcBbCredit,
        fcIfCapRxBbCreditWriteable           TruthValue,
        fcIfCapRxBbCreditDefault             FcBbCredit,
        fcIfCapISLRxBbCreditDefault          FcBbCredit,
        fcIfCapBbScnCapable                  TruthValue,
        fcIfCapBbScnMax                      Unsigned32,
        fcIfCapOsmFrmCapable                 TruthValue,
        fcIfIsServiceStateCapable            TruthValue,
        fcIfIsPortRateModeCapable            TruthValue,
        fcIfIsAdminRxBbCreditExtendedCapable TruthValue
}

fcIfCapFcphVersionHigh OBJECT-TYPE
    SYNTAX          FcphVersion
    MAX-ACCESS      read-only
    STATUS          current
    DESCRIPTION
        "The highest version of FC-PH that the FC-Port is
        capable of supporting." 
    ::= { fcIfCapEntry 1 }

fcIfCapFcphVersionLow OBJECT-TYPE
    SYNTAX          FcphVersion
    MAX-ACCESS      read-only
    STATUS          current
    DESCRIPTION
        "The lowest version of FC-PH that the FC-Port is
        capable of supporting." 
    ::= { fcIfCapEntry 2 }

fcIfCapRxBbCreditMax OBJECT-TYPE
    SYNTAX          FcBbCredit
    UNITS           "buffers"
    MAX-ACCESS      read-only
    STATUS          deprecated
    DESCRIPTION
        "The maximum number of receive buffers the port
        hardware is capable of receiving 
        from the attached Nx_Port. This object is 
        applicable to ports operating in Fx mode." 
    ::= { fcIfCapEntry 3 }

fcIfCapRxBbCreditMin OBJECT-TYPE
    SYNTAX          FcBbCredit
    UNITS           "buffers"
    MAX-ACCESS      read-only
    STATUS          deprecated
    DESCRIPTION
        "The minimum number of receive buffers the port
        hardware is capable of receiving from 
        the attached Nx_Port. This object is applicable
        to ports operating in  Fx mode." 
    ::= { fcIfCapEntry 4 }

fcIfCapRxDataFieldSizeMax OBJECT-TYPE
    SYNTAX          FcRxDataFieldSize
    MAX-ACCESS      read-only
    STATUS          current
    DESCRIPTION
        "The maximum size in bytes of the Data Field in a frame
        that the FC-Port is capable of receiving from its 
        attached FC-port." 
    ::= { fcIfCapEntry 5 }

fcIfCapRxDataFieldSizeMin OBJECT-TYPE
    SYNTAX          FcRxDataFieldSize
    MAX-ACCESS      read-only
    STATUS          current
    DESCRIPTION
        "The minimum size in bytes of the Data Field in a frame
        that the FC-Port is capable of receiving from its
        attached FC-port." 
    ::= { fcIfCapEntry 6 }

fcIfCapCos OBJECT-TYPE
    SYNTAX          FcClassOfServices
    MAX-ACCESS      read-only
    STATUS          current
    DESCRIPTION
        "The Bit mask indicating the set of Classes of Service
        that the FC-Port is capable of supporting." 
    ::= { fcIfCapEntry 7 }

fcIfCapClass2SeqDeliv OBJECT-TYPE
    SYNTAX          TruthValue
    MAX-ACCESS      read-only
    STATUS          current
    DESCRIPTION
        "The flag indicating whether or not the FC-Port is
        capable of supporting Class 2 Sequential Delivery." 
    ::= { fcIfCapEntry 8 }

fcIfCapClass3SeqDeliv OBJECT-TYPE
    SYNTAX          TruthValue
    MAX-ACCESS      read-only
    STATUS          current
    DESCRIPTION
        "The flag indicating whether or not the FC-Port is
        capable of supporting Class 3 Sequential Delivery." 
    ::= { fcIfCapEntry 9 }

fcIfCapHoldTimeMax OBJECT-TYPE
    SYNTAX          MicroSeconds
    MAX-ACCESS      read-only
    STATUS          current
    DESCRIPTION
        "The maximum holding time ( in microseconds ) that the
        FC-Port is capable of supporting." 
    ::= { fcIfCapEntry 10 }

fcIfCapHoldTimeMin OBJECT-TYPE
    SYNTAX          MicroSeconds
    MAX-ACCESS      read-only
    STATUS          current
    DESCRIPTION
        "The minimum holding time ( in microseconds ) that the
        FC-Port is capable of supporting." 
    ::= { fcIfCapEntry 11 }

fcIfCapISLRxBbCreditMax OBJECT-TYPE
    SYNTAX          FcBbCredit
    UNITS           "buffers"
    MAX-ACCESS      read-only
    STATUS          deprecated
    DESCRIPTION
        "The maximum number of receive buffers the port
        hardware  is capable of receiving from 
        the attached Inter Connect  port. This object 
        is applicable to ports operating in xE_port mode." 
    ::= { fcIfCapEntry 12 }

fcIfCapISLRxBbCreditMin OBJECT-TYPE
    SYNTAX          FcBbCredit
    UNITS           "buffers"
    MAX-ACCESS      read-only
    STATUS          deprecated
    DESCRIPTION
        "The minimum number of receive buffers the port
        hardware is capable of receiving from the
        attached xE_port or B_port. This object is 
        applicable to ports operating in xE_port mode." 
    ::= { fcIfCapEntry 13 }

fcIfCapRxBbCreditWriteable OBJECT-TYPE
    SYNTAX          TruthValue
    MAX-ACCESS      read-only
    STATUS          deprecated
    DESCRIPTION
        "The value indicating whether the port is capable
        of allowing the user to configure receive buffer to
        buffer credit. 
        The values configured for the objects:
        fcIfAdminRxBbCredit, fcIfAdminRxBbCreditModeISL,
        fcIfAdminRxBbCreditModeFx will take effect 
        only if the value of this object is true(1),
        otherwise the default values specified by the 
        objects: fcIfCapRxBbCreditDefault,
        fcIfCapISLRxBbCreditDefault will stay in effect
        depending on the operating mode of the port." 
    ::= { fcIfCapEntry 14 }

fcIfCapRxBbCreditDefault OBJECT-TYPE
    SYNTAX          FcBbCredit
    UNITS           "buffers"
    MAX-ACCESS      read-only
    STATUS          deprecated
    DESCRIPTION
        "The default receive buffer-to-buffer credits if
        the port is operating in Fx mode." 
    ::= { fcIfCapEntry 15 }

fcIfCapISLRxBbCreditDefault OBJECT-TYPE
    SYNTAX          FcBbCredit
    UNITS           "buffers"
    MAX-ACCESS      read-only
    STATUS          deprecated
    DESCRIPTION
        "The default receive buffer-to-buffer credits if
        the port is operating in xE_port mode." 
    ::= { fcIfCapEntry 16 }

fcIfCapBbScnCapable OBJECT-TYPE
    SYNTAX          TruthValue
    MAX-ACCESS      read-only
    STATUS          current
    DESCRIPTION
        "Indicates whether this interface is capable of
        handling buffer-to-buffer state change number.
        'true'  : capable of handling.
        'false' : it is not capable of handling it."
    REFERENCE       "FC-FS REV1_90 Section 15.6.2.5" 
    ::= { fcIfCapEntry 17 }

fcIfCapBbScnMax OBJECT-TYPE
    SYNTAX          Unsigned32
    MAX-ACCESS      read-only
    STATUS          current
    DESCRIPTION
        "The maximum buffer-to-buffer state change number
        this interface can handle." 
    ::= { fcIfCapEntry 18 }

fcIfCapOsmFrmCapable OBJECT-TYPE
    SYNTAX          TruthValue
    MAX-ACCESS      read-only
    STATUS          current
    DESCRIPTION
        "This value indicates whether this interface is
        capable to operate in different port rate modes.
        'true' : the port is capable of being configured
                 with the mode it is to operate in,
                 e.g., a port which can operate in over 
                 subscription mode and full rate mode.
        'false': the port rate mode cannot be changed.
        If the value of this object is 'true' then the
        fcIfCapOsmTable would show the values of the port
        when it operates in over subscribed mode and
        fcIfCapFrmTable would show the values when it
        operates in full rate mode.
        The currently configured mode is given by
        fcIfPortRateMode." 
    ::= { fcIfCapEntry 19 }

fcIfIsServiceStateCapable OBJECT-TYPE
    SYNTAX          TruthValue
    MAX-ACCESS      read-only
    STATUS          current
    DESCRIPTION
        "Indicates whether this interface is capable of
        handling service state change.
        'true'  :  capable of changing the service state of the
                 interface. This means that the user can configure the
                 object fcIfServiceState on this interface. 
        'false' :  not capable of a change in service state of the     
                 interface. The user cannot configure the object
                   fcIfServiceState on this interface." 
    ::= { fcIfCapEntry 20 }

fcIfIsPortRateModeCapable OBJECT-TYPE
    SYNTAX          TruthValue
    MAX-ACCESS      read-only
    STATUS          current
    DESCRIPTION
        "Indicates whether this interface is capable of
        being configured in either of 'dedicated' or 
        'shared' port rate modes.
        'true'  : capable of changing the port rate mode of the       
                  interface. The user can configure the object 
                  fcIfAdminPortRateMode.
        'false' : not capable of changing the port rate mode of the 
                  interface. The user cannot configure the object 
                  fcIfAdminPortRateMode." 
    ::= { fcIfCapEntry 21 }

fcIfIsAdminRxBbCreditExtendedCapable OBJECT-TYPE
    SYNTAX          TruthValue
    MAX-ACCESS      read-only
    STATUS          current
    DESCRIPTION
        "Indicates whether extended buffer-to-buffer credit
        feature can be enabled on a given interface. 
        'true'  : capable of changing the extended buffer-to-buffer    
                credits on the interface. The user can configure the 
                object fcIfAdminRxBbCreditExtended on this interface.  

        'false' : not capable of changing the extended buffer-to-buffer 
                  credits on the interface. The user cannot configure 
                  the object fcIfAdminRxBbCreditExtended on this    
                  interface." 
    ::= { fcIfCapEntry 22 }
 


adminTrunkProtocol OBJECT-TYPE
    SYNTAX          INTEGER  {
                        enable(1),
                        disable(2)
                    }
    MAX-ACCESS      read-write
    STATUS          current
    DESCRIPTION
        "The object to either enable or disable the trunking
        protocol for the device. The trunking protocol is used
        for negotiating trunk mode and calculating operational
        VSANs on an EISL link. It also performs port VSAN
        consistency checks. On non-trunking ISL links, if the
        port VSANs are different, the E ports will be isolated.
        To avoid this isolation, this MIB variable should be 
        set to 'disable(2)'.
        enable(1) - enables trunking protocol.
        disable (2) - disables the trunking protocol." 
    ::= { cffFcFeConfig 8 }

fcIfElpRejectReasonCode OBJECT-TYPE
    SYNTAX          Integer32 (0..2147483647)
    MAX-ACCESS      accessible-for-notify
    STATUS          current
    DESCRIPTION
        "The reason code for the ELP reject."
    REFERENCE       "FC-SW-2 REV 4.9 Section 6.1.2" 
    ::= { cffFcFeConfig 9 }

fcIfElpRejectReasonCodeExpl OBJECT-TYPE
    SYNTAX          Integer32 (0..2147483647)
    MAX-ACCESS      accessible-for-notify
    STATUS          current
    DESCRIPTION
        "The reason code explanation for the ELP reject."
    REFERENCE       "FC-SW-2 REV 4.9 Section 6.1.2" 
    ::= { cffFcFeConfig 10 }
-- fcIfCapOsmTable

fcIfCapOsmTable OBJECT-TYPE
    SYNTAX          SEQUENCE OF FcIfCapOsmEntry 
    MAX-ACCESS      not-accessible
    STATUS          current
    DESCRIPTION
        "This table contains, one entry for each FC-Port
        which is capable of operating in over subscription port
        rate mode.
        It contains information describing about what each
        FC-port is inherently capable of operating or 
        supporting in over subscription mode.   
        Entries in this table are created/deleted on an 
        as-needed basis by the agent. 
        NOTE: This table has objects which represent the
        characteristics of a physical port. Thus, Port 
        Channel ports are not represented in this table."
    ::= { cffFcFeConfig 11 }

fcIfCapOsmEntry OBJECT-TYPE
    SYNTAX          FcIfCapOsmEntry
    MAX-ACCESS      not-accessible
    STATUS          current
    DESCRIPTION
        "Each entry contains the Capability of a FC-Port
        operating in over subscribed mode."
    INDEX           { ifIndex } 
    ::= { fcIfCapOsmTable 1 }

FcIfCapOsmEntry ::= SEQUENCE {
        fcIfCapOsmRxBbCreditWriteable  TruthValue,
        fcIfCapOsmRxBbCreditMax        FcBbCredit,
        fcIfCapOsmRxBbCreditMin        FcBbCredit,
        fcIfCapOsmRxBbCreditDefault    FcBbCredit,
        fcIfCapOsmISLRxBbCreditMax     FcBbCredit,
        fcIfCapOsmISLRxBbCreditMin     FcBbCredit,
        fcIfCapOsmISLRxBbCreditDefault FcBbCredit,
        fcIfCapOsmRxPerfBufWriteable   TruthValue,
        fcIfCapOsmRxPerfBufMax         FcPerfBuffer,
        fcIfCapOsmRxPerfBufMin         FcPerfBuffer,
        fcIfCapOsmRxPerfBufDefault     FcPerfBuffer,
        fcIfCapOsmISLRxPerfBufMax      FcPerfBuffer,
        fcIfCapOsmISLRxPerfBufMin      FcPerfBuffer,
        fcIfCapOsmISLRxPerfBufDefault  FcPerfBuffer
}

fcIfCapOsmRxBbCreditWriteable OBJECT-TYPE
    SYNTAX          TruthValue
    MAX-ACCESS      read-only
    STATUS          current
    DESCRIPTION
        "The value indicating whether the port operating in over
        subscribed mode is capable of allowing the user to
        configure receive buffer to buffer credit. 
        The values configured for the objects:
        fcIfAdminRxBbCredit, fcIfAdminRxBbCreditModeISL,
        fcIfAdminRxBbCreditModeFx will take effect 
        only if the value of this object is true(1),
        otherwise the default values specified by the 
        objects: fcIfCapOsmRxBbCreditDefault,
        fcIfCapOsmISLRxBbCreditDefault will stay in effect
        depending on the operating mode of the port." 
    ::= { fcIfCapOsmEntry 1 }

fcIfCapOsmRxBbCreditMax OBJECT-TYPE
    SYNTAX          FcBbCredit
    MAX-ACCESS      read-only
    STATUS          current
    DESCRIPTION
        "The maximum number of receive buffers the port
        hardware is capable of receiving 
        from the attached Nx_Port. This object is 
        applicable to ports operating in Fx mode. ." 
    ::= { fcIfCapOsmEntry 2 }

fcIfCapOsmRxBbCreditMin OBJECT-TYPE
    SYNTAX          FcBbCredit
    MAX-ACCESS      read-only
    STATUS          current
    DESCRIPTION
        "The minimum number of receive buffers the port
        hardware is capable of receiving from 
        the attached Nx_Port. This object is applicable
        to ports operating in  Fx mode." 
    ::= { fcIfCapOsmEntry 3 }

fcIfCapOsmRxBbCreditDefault OBJECT-TYPE
    SYNTAX          FcBbCredit
    MAX-ACCESS      read-only
    STATUS          current
    DESCRIPTION
        "The default receive buffer-to-buffer credits if
        the port is operating in Fx mode." 
    ::= { fcIfCapOsmEntry 4 }

fcIfCapOsmISLRxBbCreditMax OBJECT-TYPE
    SYNTAX          FcBbCredit
    MAX-ACCESS      read-only
    STATUS          current
    DESCRIPTION
        "The maximum number of receive buffers the port
        hardware  is capable of receiving from 
        the attached Inter Connect  port. This object 
        is applicable to ports operating in inter switch
        link mode." 
    ::= { fcIfCapOsmEntry 5 }

fcIfCapOsmISLRxBbCreditMin OBJECT-TYPE
    SYNTAX          FcBbCredit
    MAX-ACCESS      read-only
    STATUS          current
    DESCRIPTION
        "The minimum number of receive buffers the port
        hardware is capable of receiving from the
        attached xE_port or B_port. This object 
        is applicable to ports operating in inter switch
        link mode." 
    ::= { fcIfCapOsmEntry 6 }

fcIfCapOsmISLRxBbCreditDefault OBJECT-TYPE
    SYNTAX          FcBbCredit
    MAX-ACCESS      read-only
    STATUS          current
    DESCRIPTION
        "The default receive buffer-to-buffer credits if
        the port is operating in inter switch link mode." 
    ::= { fcIfCapOsmEntry 7 }

fcIfCapOsmRxPerfBufWriteable OBJECT-TYPE
    SYNTAX          TruthValue
    MAX-ACCESS      read-only
    STATUS          current
    DESCRIPTION
        "The value indicating whether the port is capable
        of allowing the user to configure receive performance
        buffers. 
        The values configured for the objects:
        fcIfAdminRxPerfBuffer will take effect 
        only if the value of this object is true(1),
        otherwise the default values specified by the 
        objects: fcIfCapOsmRxPerfBufDefault,
        fcIfCapOsmISLRxPerfBufDefault will stay in effect
        depending on the operating mode of the port." 
    ::= { fcIfCapOsmEntry 8 }

fcIfCapOsmRxPerfBufMax OBJECT-TYPE
    SYNTAX          FcPerfBuffer
    MAX-ACCESS      read-only
    STATUS          current
    DESCRIPTION
        "The maximum number of performance buffers that can be
        configured for this port. The object is applicable to
        ports operating in Fx mode." 
    ::= { fcIfCapOsmEntry 9 }

fcIfCapOsmRxPerfBufMin OBJECT-TYPE
    SYNTAX          FcPerfBuffer
    MAX-ACCESS      read-only
    STATUS          current
    DESCRIPTION
        "The minimum number of performance buffers that can be
        configured for this port. The object is applicable to
        ports operating in Fx mode." 
    ::= { fcIfCapOsmEntry 10 }

fcIfCapOsmRxPerfBufDefault OBJECT-TYPE
    SYNTAX          FcPerfBuffer
    MAX-ACCESS      read-only
    STATUS          current
    DESCRIPTION
        "The default performance buffers if the port is
        operating in Fx mode. The object is applicable to
        ports operating in Fx mode." 
    ::= { fcIfCapOsmEntry 11 }

fcIfCapOsmISLRxPerfBufMax OBJECT-TYPE
    SYNTAX          FcPerfBuffer
    MAX-ACCESS      read-only
    STATUS          current
    DESCRIPTION
        "The maximum number of performance buffers that can be
        configured for this port. This object is applicable to
        inter switch link ports." 
    ::= { fcIfCapOsmEntry 12 }

fcIfCapOsmISLRxPerfBufMin OBJECT-TYPE
    SYNTAX          FcPerfBuffer
    MAX-ACCESS      read-only
    STATUS          current
    DESCRIPTION
        "The minimum number of performance buffers that can be
        configured for this port. This object is applicable to
        inter switch link ports." 
    ::= { fcIfCapOsmEntry 13 }

fcIfCapOsmISLRxPerfBufDefault OBJECT-TYPE
    SYNTAX          FcPerfBuffer
    MAX-ACCESS      read-only
    STATUS          current
    DESCRIPTION
        "The default performance buffers if the port is
        operating as an inter switch link port." 
    ::= { fcIfCapOsmEntry 14 }
 

-- fcIfCapFrmTable

fcIfCapFrmTable OBJECT-TYPE
    SYNTAX          SEQUENCE OF FcIfCapFrmEntry 
    MAX-ACCESS      not-accessible
    STATUS          current
    DESCRIPTION
        "This table contains, one entry for each FC-Port
        which is capable of operating in Full Rate mode.
        It contains information describing about what each
        FC-port is inherently capable of operating or 
        supporting in full rate mode. 
        Entries in this table are created/deleted on an 
        as-needed basis by the agent.
        NOTE: This table has objects which represent the
        characteristics of a physical port. Thus, Port 
        Channel ports are not represented in this table."
    ::= { cffFcFeConfig 12 }

fcIfCapFrmEntry OBJECT-TYPE
    SYNTAX          FcIfCapFrmEntry
    MAX-ACCESS      not-accessible
    STATUS          current
    DESCRIPTION
        "Each entry contains the Capability of a FC-Port
        operating in Full Rate mode."
    INDEX           { ifIndex } 
    ::= { fcIfCapFrmTable 1 }

FcIfCapFrmEntry ::= SEQUENCE {
        fcIfCapFrmRxBbCreditWriteable  TruthValue,
        fcIfCapFrmRxBbCreditMax        FcBbCredit,
        fcIfCapFrmRxBbCreditMin        FcBbCredit,
        fcIfCapFrmRxBbCreditDefault    FcBbCredit,
        fcIfCapFrmISLRxBbCreditMax     FcBbCredit,
        fcIfCapFrmISLRxBbCreditMin     FcBbCredit,
        fcIfCapFrmISLRxBbCreditDefault FcBbCredit,
        fcIfCapFrmRxPerfBufWriteable   TruthValue,
        fcIfCapFrmRxPerfBufMax         FcPerfBuffer,
        fcIfCapFrmRxPerfBufMin         FcPerfBuffer,
        fcIfCapFrmRxPerfBufDefault     FcPerfBuffer,
        fcIfCapFrmISLRxPerfBufMax      FcPerfBuffer,
        fcIfCapFrmISLRxPerfBufMin      FcPerfBuffer,
        fcIfCapFrmISLRxPerfBufDefault  FcPerfBuffer
}

fcIfCapFrmRxBbCreditWriteable OBJECT-TYPE
    SYNTAX          TruthValue
    MAX-ACCESS      read-only
    STATUS          current
    DESCRIPTION
        "The value indicating whether the port operating in full
        rate mode is capable of allowing the user to
        configure receive buffer to buffer credit. 
        The values configured for the objects:
        fcIfAdminRxBbCredit, fcIfAdminRxBbCreditModeISL,
        fcIfAdminRxBbCreditModeFx will take effect 
        only if the value of this object is true(1),
        otherwise the default values specified by the 
        objects: fcIfCapFrmRxBbCreditDefault,
        fcIfCapFrmISLRxBbCreditDefault will stay in effect
        depending on the operating mode of the port." 
    ::= { fcIfCapFrmEntry 1 }

fcIfCapFrmRxBbCreditMax OBJECT-TYPE
    SYNTAX          FcBbCredit
    MAX-ACCESS      read-only
    STATUS          current
    DESCRIPTION
        "The maximum number of receive buffers the port
        hardware is capable of receiving 
        from the attached Nx_Port. This object is 
        applicable to ports operating in Fx mode." 
    ::= { fcIfCapFrmEntry 2 }

fcIfCapFrmRxBbCreditMin OBJECT-TYPE
    SYNTAX          FcBbCredit
    MAX-ACCESS      read-only
    STATUS          current
    DESCRIPTION
        "The minimum number of receive buffers the port
        hardware is capable of receiving from 
        the attached Nx_Port. This object is applicable
        to ports operating in  Fx mode." 
    ::= { fcIfCapFrmEntry 3 }

fcIfCapFrmRxBbCreditDefault OBJECT-TYPE
    SYNTAX          FcBbCredit
    MAX-ACCESS      read-only
    STATUS          current
    DESCRIPTION
        "The default receive buffer-to-buffer credits if
        the port is operating in Fx mode." 
    ::= { fcIfCapFrmEntry 4 }

fcIfCapFrmISLRxBbCreditMax OBJECT-TYPE
    SYNTAX          FcBbCredit
    MAX-ACCESS      read-only
    STATUS          current
    DESCRIPTION
        "The maximum number of receive buffers the port
        hardware  is capable of receiving from 
        the attached Inter Connect  port. This object 
        is applicable to ports operating in inter switch
        link mode." 
    ::= { fcIfCapFrmEntry 5 }

fcIfCapFrmISLRxBbCreditMin OBJECT-TYPE
    SYNTAX          FcBbCredit
    MAX-ACCESS      read-only
    STATUS          current
    DESCRIPTION
        "The minimum number of receive buffers the port
        hardware is capable of receiving from the
        attached xE_port or B_port. This object 
        is applicable to ports operating in inter switch
        link mode." 
    ::= { fcIfCapFrmEntry 6 }

fcIfCapFrmISLRxBbCreditDefault OBJECT-TYPE
    SYNTAX          FcBbCredit
    MAX-ACCESS      read-only
    STATUS          current
    DESCRIPTION
        "The default receive buffer-to-buffer credits if
        the port is operating in inter switch link mode." 
    ::= { fcIfCapFrmEntry 7 }

fcIfCapFrmRxPerfBufWriteable OBJECT-TYPE
    SYNTAX          TruthValue
    MAX-ACCESS      read-only
    STATUS          current
    DESCRIPTION
        "The value indicating whether the port is capable
        of allowing the user to configure receive performance
        buffers. 
        The values configured for the objects:
        fcIfAdminRxPerfBuffer will take effect 
        only if the value of this object is true(1),
        otherwise the default values specified by the 
        objects: fcIfCapFrmRxPerfBufDefault,
        fcIfCapFrmISLRxPerfBufDefault will stay in effect
        depending on the operating mode of the port." 
    ::= { fcIfCapFrmEntry 8 }

fcIfCapFrmRxPerfBufMax OBJECT-TYPE
    SYNTAX          FcPerfBuffer
    MAX-ACCESS      read-only
    STATUS          current
    DESCRIPTION
        "The maximum number of performance buffers that can be
        configured for this port. The object is applicable to
        ports operating in Fx mode." 
    ::= { fcIfCapFrmEntry 9 }

fcIfCapFrmRxPerfBufMin OBJECT-TYPE
    SYNTAX          FcPerfBuffer
    MAX-ACCESS      read-only
    STATUS          current
    DESCRIPTION
        "The minimum number of performance buffers that can be
        configured for this port. The object is applicable to
        ports operating in Fx mode." 
    ::= { fcIfCapFrmEntry 10 }

fcIfCapFrmRxPerfBufDefault OBJECT-TYPE
    SYNTAX          FcPerfBuffer
    MAX-ACCESS      read-only
    STATUS          current
    DESCRIPTION
        "The default performance buffers if the port is
        operating in Fx mode. The object is applicable to
        ports operating in Fx mode." 
    ::= { fcIfCapFrmEntry 11 }

fcIfCapFrmISLRxPerfBufMax OBJECT-TYPE
    SYNTAX          FcPerfBuffer
    MAX-ACCESS      read-only
    STATUS          current
    DESCRIPTION
        "The maximum number of performance buffers that can be
        configured for this port. This object is applicable to
        inter switch link ports." 
    ::= { fcIfCapFrmEntry 12 }

fcIfCapFrmISLRxPerfBufMin OBJECT-TYPE
    SYNTAX          FcPerfBuffer
    MAX-ACCESS      read-only
    STATUS          current
    DESCRIPTION
        "The minimum number of performance buffers that can be
        configured for this port. This object is applicable to
        inter switch link ports." 
    ::= { fcIfCapFrmEntry 13 }

fcIfCapFrmISLRxPerfBufDefault OBJECT-TYPE
    SYNTAX          FcPerfBuffer
    MAX-ACCESS      read-only
    STATUS          current
    DESCRIPTION
        "The default performance buffers if the port is
        operating as an inter switch link port." 
    ::= { fcIfCapFrmEntry 14 }
 

-- fcIfRNIDInfoTable

fcIfRNIDInfoTable OBJECT-TYPE
    SYNTAX          SEQUENCE OF FcIfRNIDInfoEntry 
    MAX-ACCESS      not-accessible
    STATUS          current
    DESCRIPTION
        "A table listing the peer node identification data per
        port per VSAN."
    ::= { cffFcFeConfig 13 }

fcIfRNIDInfoEntry OBJECT-TYPE
    SYNTAX          FcIfRNIDInfoEntry
    MAX-ACCESS      not-accessible
    STATUS          current
    DESCRIPTION
        "Each entry provides node identification data of the
        peer. This data is got through performing 
        request-node-identification-data(RNID) extended link
        service. The table would have entry for each port, 
        identified by ifIndex, on this VSAN, identified by 
        vsanIndex.

        This table would hold entries only for physical FC
        ports, FC port channel ports and FCIP ports."
    REFERENCE       "FC-SB-3 rev 1.6,  Section 6.3.8."
    INDEX           {
                        ifIndex,
                        vsanIndex
                    } 
    ::= { fcIfRNIDInfoTable 1 }

FcIfRNIDInfoEntry ::= SEQUENCE {
        fcIfRNIDInfoStatus       INTEGER,
        fcIfRNIDInfoTypeNumber   SnmpAdminString,
        fcIfRNIDInfoModelNumber  SnmpAdminString,
        fcIfRNIDInfoManufacturer SnmpAdminString,
        fcIfRNIDInfoPlantOfMfg   SnmpAdminString,
        fcIfRNIDInfoSerialNumber SnmpAdminString,
        fcIfRNIDInfoUnitType     INTEGER,
        fcIfRNIDInfoPortId       Integer32
}

fcIfRNIDInfoStatus OBJECT-TYPE
    SYNTAX          INTEGER  {
                        valid(1),
                        invalid(2),
                        old(3)
                    }
    MAX-ACCESS      read-write
    STATUS          current
    DESCRIPTION
        "This object specifies the status of the row,
        is valid, invalid or old. 
        The only value that can be assigned by the Network
        Management System(NMS) is invalid(2). The NMS
        cannot set this object to any other value (i.e valid
        (1) or old(3) )." 
    ::= { fcIfRNIDInfoEntry 1 }

fcIfRNIDInfoTypeNumber OBJECT-TYPE
    SYNTAX          SnmpAdminString
    MAX-ACCESS      read-only
    STATUS          current
    DESCRIPTION
        "The type number of the peer node. For example the type
        number could be 002105." 
    ::= { fcIfRNIDInfoEntry 2 }

fcIfRNIDInfoModelNumber OBJECT-TYPE
    SYNTAX          SnmpAdminString
    MAX-ACCESS      read-only
    STATUS          current
    DESCRIPTION
        "The model number of the peer node. For example the model
        number could be F20." 
    ::= { fcIfRNIDInfoEntry 3 }

fcIfRNIDInfoManufacturer OBJECT-TYPE
    SYNTAX          SnmpAdminString
    MAX-ACCESS      read-only
    STATUS          current
    DESCRIPTION
        "The name of the the company that manufactured the
        peer node. For example the Manufacturer info could be
        HTC." 
    ::= { fcIfRNIDInfoEntry 4 }

fcIfRNIDInfoPlantOfMfg OBJECT-TYPE
    SYNTAX          SnmpAdminString
    MAX-ACCESS      read-only
    STATUS          current
    DESCRIPTION
        "The plant code that identifies the plant
        of manufacture of the peer node. For example the plant 
        code of manufacture could be 00." 
    ::= { fcIfRNIDInfoEntry 5 }

fcIfRNIDInfoSerialNumber OBJECT-TYPE
    SYNTAX          SnmpAdminString
    MAX-ACCESS      read-only
    STATUS          current
    DESCRIPTION
        "The sequence number assigned to the peer node during
        manufacturing. For example the serial number could be
        000000023053." 
    ::= { fcIfRNIDInfoEntry 6 }

fcIfRNIDInfoUnitType OBJECT-TYPE
    SYNTAX          INTEGER  {
                        channel(1),
                        controlUnit(2),
                        fabric(3),
                        unknown(4)
                    }
    MAX-ACCESS      read-only
    STATUS          current
    DESCRIPTION
        "The type of the peer node that this port
        is communicating.

        channel      - Host
        controlUnit  - Disk 
        fabric       - Another SAN switch
        unknown      - if fcIfRNIDInfoStatus is 'invalid' this 
                       would be unknown." 
    ::= { fcIfRNIDInfoEntry 7 }

fcIfRNIDInfoPortId OBJECT-TYPE
    SYNTAX          Integer32 (0..255)
    MAX-ACCESS      read-only
    STATUS          current
    DESCRIPTION
        "The identifier of the port in the peer node connected
        to this port.

        If the peer node is a channel, as described
        by the instance of fcIfRNIDInfoUnitType, then 
        fcIfRNIDInfoPortId will be the CHPID (Channel
        Path Identifier) of the channel path that
        contains the port in the peer node connected to this 
        port.

        If the peer node is controlUnit, then 
        fcIfRNIDInfoPortId will be 0.

        If the peer node is fabric, then 
        fcIfRNIDInfoPortId will be port address of the port in
        peer node connected to this port." 
    ::= { fcIfRNIDInfoEntry 8 }
 

-- Port channel Information for gigabit ethernet interfaces
-- in the fibre channel switch.

fcIfGigETable OBJECT-TYPE
    SYNTAX          SEQUENCE OF FcIfGigEEntry 
    MAX-ACCESS      not-accessible
    STATUS          current
    DESCRIPTION
        "This table contains one entry per fibre channel switch
        Gigabit Ethernet (GigE) interface. 

        This table also provides an easy way to find out 
        whether a GigE interface is part of an port 
        channel or not.

        The table is indexed by the 'ifIndex' of the GigE
        port in the fiber channel switch."
    ::= { cffFcFeConfig 14 }

fcIfGigEEntry OBJECT-TYPE
    SYNTAX          FcIfGigEEntry
    MAX-ACCESS      not-accessible
    STATUS          current
    DESCRIPTION
        "Each entry contains GigE port configuration and
        state information."
    INDEX           { ifIndex } 
    ::= { fcIfGigETable 1 }

FcIfGigEEntry ::= SEQUENCE {
        fcIfGigEPortChannelIfIndex InterfaceIndexOrZero,
        fcIfGigEAutoNegotiate      INTEGER,
        fcIfGigEBeaconMode         TruthValue,
        fcIfGigConnectorType       FcPortModuleTypes
}

fcIfGigEPortChannelIfIndex OBJECT-TYPE
    SYNTAX          InterfaceIndexOrZero
    MAX-ACCESS      read-only
    STATUS          current
    DESCRIPTION
        "The ifIndex of the ether channel port this GigE port
        belongs to.
        A value of zero indicates that this GigE port is not 
        part of any port channel.
        For port channel port this object will have the ifIndex
        of the port channel port itself." 
    ::= { fcIfGigEEntry 1 }

fcIfGigEAutoNegotiate OBJECT-TYPE
    SYNTAX          INTEGER  {
                        enabled(1),
                        disabled(2)
                    }
    MAX-ACCESS      read-write
    STATUS          current
    DESCRIPTION
        "This object Indicates whether auto-negotiation
        (of speed and duplex mode) should be used on this 
        interface."
    DEFVAL          { enabled } 
    ::= { fcIfGigEEntry 2 }

fcIfGigEBeaconMode OBJECT-TYPE
    SYNTAX          TruthValue
    MAX-ACCESS      read-write
    STATUS          current
    DESCRIPTION
        "In Beacon mode, an interface LED is put into flashing
        mode for easy identification of a particular
        interface. The Beacon mode configured by the user.
        If 'true', the Beacon mode is enabled.
        If 'false', the beacon mode is disabled."
    DEFVAL          { true } 
    ::= { fcIfGigEEntry 3 }

fcIfGigConnectorType OBJECT-TYPE
    SYNTAX          FcPortModuleTypes
    MAX-ACCESS      read-only
    STATUS          current
    DESCRIPTION
        "The module type of the port connector.
        Since this is a characteristic of a physical port, this
        object is not applicable for Port Channel ports, i.e.,
        the value is instantiated but its value is irrelevant." 
    ::= { fcIfGigEEntry 4 }
 


fcIfModuleTable OBJECT-TYPE
    SYNTAX          SEQUENCE OF FcIfModuleEntry 
    MAX-ACCESS      not-accessible
    STATUS          current
    DESCRIPTION
        "This table is used for configuring the module specific features
        for Fibre Channel modules (or whatever equivalent)."
    ::= { cffFcFeConfig 15 }

fcIfModuleEntry OBJECT-TYPE
    SYNTAX          FcIfModuleEntry
    MAX-ACCESS      not-accessible
    STATUS          current
    DESCRIPTION
        "An entry in fcIfModuleTable. Each entry represents the module
        specific attributes."
    INDEX           { entPhysicalIndex } 
    ::= { fcIfModuleTable 1 }

FcIfModuleEntry ::= SEQUENCE {
        fcIfModuleOverSubscriptionRatioConfig INTEGER,
        fcIfModuleBandwidthFairnessConfig     INTEGER,
        fcIfModuleBandwidthFairnessOper       INTEGER,
        fcIfModuleXcvrFrequencyConfig         INTEGER
}

fcIfModuleOverSubscriptionRatioConfig OBJECT-TYPE
    SYNTAX          INTEGER  {
                        enabled(1),
                        disabled(2)
                    }
    MAX-ACCESS      read-write
    STATUS          current
    DESCRIPTION
        "This object helps the user to control the restriction on
        oversubscription ratio on modules that support it. 

        enable(1)  - Enables the restriction on oversubscription ratio
        disable(2) - Disables the restriction on oversubscription ratio

        By default, the restriction on oversubscription ratio is
        enabled. If the user configures this object to disable (2), all
        the interfaces on the module are capable of operating at
        maximum
        admin speed, given by fcIfAdminSpeed, regardless of the
        available bandwidth." 
    ::= { fcIfModuleEntry 1 }

fcIfModuleBandwidthFairnessConfig OBJECT-TYPE
    SYNTAX          INTEGER  {
                        enable(1),
                        disable(2)
                    }
    MAX-ACCESS      read-write
    STATUS          current
    DESCRIPTION
        "This object helps the user to control bandwidth fairness on
        modules that support it. 

        enable(1)  - Enables the bandwidth fairness
        disable(2) - Disables the bandwidth fairness 

        By default, bandwidth fairness is enabled for a module. If the 
        user configures this object to disable (2), fair bandwidth 
        provisioning will not be guaranteed for interfaces with 
        fcIfPortRadeMode equal to 'dedicated'." 
    ::= { fcIfModuleEntry 2 }

fcIfModuleBandwidthFairnessOper OBJECT-TYPE
    SYNTAX          INTEGER  {
                        enabled(1),
                        disabled(2)
                    }
    MAX-ACCESS      read-only
    STATUS          current
    DESCRIPTION
        "The operational status of bandwidth fairness on the module.

        enabled(1)  -  Bandwidth fairness is enabled on the module
        disabled(2) -  Bandwidth fairness is disabled on the module" 
    ::= { fcIfModuleEntry 3 }

fcIfModuleXcvrFrequencyConfig OBJECT-TYPE
    SYNTAX          INTEGER  {
                        notApplicable(1),
                        xcvrFreqX2FC(2),
                        xcvrFreqX2Eth(3)
                    }
    MAX-ACCESS      read-write
    STATUS          current
    DESCRIPTION
        "This object specifies the transceiver frequency of this
        module.
        notApplicable(1)      - This value is read-only and is always
                                returned for module which does not 
                                support this configuration.
        xcvrFreqX2FC(2)       - Sets the object to 10G FC transceiver
                                frequency.
        xcvrFreqX2Eth(3)      - Sets the object to 10G Ethernet 
                                transceiver frequency."
    REFERENCE       "IEEE Std 802.3ae, ANSI 10GFC Rev 4.0" 
    ::= { fcIfModuleEntry 4 }
 


fcIfToggleCtrlConfigTable OBJECT-TYPE
    SYNTAX          SEQUENCE OF FcIfToggleCtrlConfigEntry 
    MAX-ACCESS      not-accessible
    STATUS          deprecated
    DESCRIPTION
        "This table contains one entry per fibre channel interface. In
        certain scenarios, when an interface in a system transitions to
        a down state, it is likely for the interface to keep toggling
        and flapping between up and down states continuously. The
        objects in each entry of this table help in controlling such
        behaviour on an interface by stopping such frequent transitions
        and holding the interface in down state, if a stipulated number
        of such toggles happen in a given duration, as described in the
        objects."
    ::= { cffFcFeConfig 16 }

fcIfToggleCtrlConfigEntry OBJECT-TYPE
    SYNTAX          FcIfToggleCtrlConfigEntry
    MAX-ACCESS      not-accessible
    STATUS          deprecated
    DESCRIPTION
        "An entry in the fcIfToggleCtrlConfigTable."
    INDEX           { ifIndex } 
    ::= { fcIfToggleCtrlConfigTable 1 }

FcIfToggleCtrlConfigEntry ::= SEQUENCE {
        fcIfToggleCtrlConfigEnable   TruthValue,
        fcIfToggleCtrlConfigReason   INTEGER,
        fcIfToggleCtrlConfigDuration Unsigned32,
        fcIfToggleCtrlConfigNumFlaps Unsigned32
}

fcIfToggleCtrlConfigEnable OBJECT-TYPE
    SYNTAX          TruthValue
    MAX-ACCESS      read-write
    STATUS          deprecated
    DESCRIPTION
        "This object specifies if an interface can be stopped from
        toggling between up and down states or allowed to toggle 
        continuously.
        If 'true', the interface will be stopped from toggling
                        between up and down states.
        If 'false', the interface will be allowed to toggle 
                        continuously." 
    ::= { fcIfToggleCtrlConfigEntry 1 }

fcIfToggleCtrlConfigReason OBJECT-TYPE
    SYNTAX          INTEGER  {
                        notApplicable(1),
                        linkFailure(2)
                    }
    MAX-ACCESS      read-only
    STATUS          deprecated
    DESCRIPTION
        "This object indicates the reason for which a port can
        be allowed to toggle between up and down states.
        notApplicable (1) - this reason is displayed when
                fcIfToggleCtrlConfigEnable is 'false'.        
        linkFailure (2) - physical link failure." 
    ::= { fcIfToggleCtrlConfigEntry 2 }

fcIfToggleCtrlConfigDuration OBJECT-TYPE
    SYNTAX          Unsigned32 (1..2000000)
    UNITS           "seconds"
    MAX-ACCESS      read-write
    STATUS          deprecated
    DESCRIPTION
        "This object specifies the time duration in which the port is
        allowed to toggle as many as the number of times given by
        fcIfToggleCtrlConfigNumFlaps. When fcIfToggleCtrlConfigEnable 
        is 'false', this object does not take effect and its value 
        cannot be changed." 
    ::= { fcIfToggleCtrlConfigEntry 3 }

fcIfToggleCtrlConfigNumFlaps OBJECT-TYPE
    SYNTAX          Unsigned32 (1..1023)
    MAX-ACCESS      read-write
    STATUS          deprecated
    DESCRIPTION
        "This object specifies the number of times a port can flap in
        the duration given by fcIfToggleCtrlConfigDuration. When 
        fcIfToggleCtrlConfigEnable is 'false', this object does not 
        take effect and its value cannot be changed." 
    ::= { fcIfToggleCtrlConfigEntry 4 }
 


fcIfFlapCtrlConfigTable OBJECT-TYPE
    SYNTAX          SEQUENCE OF FcIfFlapCtrlConfigEntry 
    MAX-ACCESS      not-accessible
    STATUS          current
    DESCRIPTION
        "In certain scenarios, when an interface in a system
        transitions to a down state due to a particular reason, it is 
        likely for the interface to keep flapping between up and down 
        states continuously. The objects in each entry of this table 
        help in controlling such behaviour on an interface by stopping 
        such frequent transitions and holding the interface in down 
        state, if a stipulated number of such toggles happen in a given 
        duration, as described in the objects. 
        Per each reason for which the interface flaps, an entry in this
        table can be used to configure the following: whether or not 
        the flapping should be controlled on the interface, the allowed
        number of flaps and the allowed duration before the interface
        is held in down state."
    ::= { cffFcFeConfig 17 }

fcIfFlapCtrlConfigEntry OBJECT-TYPE
    SYNTAX          FcIfFlapCtrlConfigEntry
    MAX-ACCESS      not-accessible
    STATUS          current
    DESCRIPTION
        "An entry in the fcIfFlapCtrlConfigTable."
    INDEX           {
                        fcIfFlapCtrlConfigReason,
                        ifIndex
                    } 
    ::= { fcIfFlapCtrlConfigTable 1 }

FcIfFlapCtrlConfigEntry ::= SEQUENCE {
        fcIfFlapCtrlConfigReason   INTEGER,
        fcIfFlapCtrlConfigEnable   TruthValue,
        fcIfFlapCtrlConfigDuration Unsigned32,
        fcIfFlapCtrlConfigNumFlaps Unsigned32
}

fcIfFlapCtrlConfigReason OBJECT-TYPE
    SYNTAX          INTEGER  {
                        linkFailure(1),
                        trustSecViolation(2),
                        bitErrorRate(3),
                        signalLoss(4),
                        syncLoss(5),
                        linkReset(6),
                        creditLoss(7)
                    }
    MAX-ACCESS      not-accessible
    STATUS          current
    DESCRIPTION
        "This object indicates the reason for which a port can
        be allowed to toggle between up and down states.
        linkFailure (1) - physical link failure.
        trustSecViolation (2) - Cisco Trusted Security violation.
        bitErrorRate (3) - bit error rate threshold exceeded.
        signalLoss (4) - link failure due to loss of signal.
        syncLoss (5) - link failure due to loss of sync.
        linkReset (6) - link failure due to link reset.
        creditLoss (7) - link failure due to excessive credit
                    loss indications." 
    ::= { fcIfFlapCtrlConfigEntry 1 }

fcIfFlapCtrlConfigEnable OBJECT-TYPE
    SYNTAX          TruthValue
    MAX-ACCESS      read-write
    STATUS          current
    DESCRIPTION
        "This object specifies if an interface can be stopped from
        toggling between up and down states or allowed to toggle
        continuously.
        If 'true', the interface will be stopped from toggling
                        between up and down states.
        If 'false', the interface will be allowed to toggle
                        continuously." 
    ::= { fcIfFlapCtrlConfigEntry 2 }

fcIfFlapCtrlConfigDuration OBJECT-TYPE
    SYNTAX          Unsigned32 (1..2000000)
    UNITS           "seconds"
    MAX-ACCESS      read-write
    STATUS          current
    DESCRIPTION
        "This object specifies the time duration in which the port is
        allowed to toggle as many as the number of times given by
        fcIfFlapCtrlConfigNumFlaps. When fcIfFlapCtrlConfigEnable
        is 'false', this object does not take effect and its value
        cannot be changed." 
    ::= { fcIfFlapCtrlConfigEntry 3 }

fcIfFlapCtrlConfigNumFlaps OBJECT-TYPE
    SYNTAX          Unsigned32 (1..1023)
    MAX-ACCESS      read-write
    STATUS          current
    DESCRIPTION
        "This object specifies the number of times a port can flap in
        the duration given by fcIfFlapCtrlConfigDuration. When
        fcIfFlapCtrlConfigEnable is 'false', this object does not
        take effect and its value cannot be changed." 
    ::= { fcIfFlapCtrlConfigEntry 4 }
 

-- fcIfErrorTable

fcIfErrorTable OBJECT-TYPE
    SYNTAX          SEQUENCE OF FcIfErrorEntry 
    MAX-ACCESS      not-accessible
    STATUS          current
    DESCRIPTION
        "This table contains, one entry for each fabric
        channel port( including any Port Channel ports ). It 
        contains counters that record the errors detected.
        This table is an extension to interfaces group defined
        in IF-MIB. It contains additional errors specific
        to this device."
    ::= { cffFcFeStatistics 1 }

fcIfErrorEntry OBJECT-TYPE
    SYNTAX          FcIfErrorEntry
    MAX-ACCESS      not-accessible
    STATUS          current
    DESCRIPTION
        "Each entry contains error counters of a fabric
        channel port."
    INDEX           { ifIndex } 
    ::= { fcIfErrorTable 1 }

FcIfErrorEntry ::= SEQUENCE {
        fcIfLinkFailures                    Counter32,
        fcIfSyncLosses                      Counter32,
        fcIfSigLosses                       Counter32,
        fcIfPrimSeqProtoErrors              Counter32,
        fcIfInvalidTxWords                  Counter32,
        fcIfInvalidCrcs                     Counter32,
        fcIfDelimiterErrors                 Counter32,
        fcIfAddressIdErrors                 Counter32,
        fcIfLinkResetIns                    Counter32,
        fcIfLinkResetOuts                   Counter32,
        fcIfOlsIns                          Counter32,
        fcIfOlsOuts                         Counter32,
        fcIfRuntFramesIn                    Counter32,
        fcIfJabberFramesIn                  Counter32,
        fcIfTxWaitCount                     Counter32,
        fcIfFramesTooLong                   Counter32,
        fcIfFramesTooShort                  Counter32,
        fcIfLRRIn                           Counter32,
        fcIfLRROut                          Counter32,
        fcIfNOSIn                           Counter32,
        fcIfNOSOut                          Counter32,
        fcIfFragFrames                      Counter32,
        fcIfEOFaFrames                      Counter32,
        fcIfUnknownClassFrames              Counter32,
        fcIf8b10bDisparityErrors            Counter32,
        fcIfFramesDiscard                   Counter32,
        fcIfELPFailures                     Counter32,
        fcIfBBCreditTransistionFromZero     Counter32,
        fcIfEISLFramesDiscard               Counter32,
        fcIfFramingErrorFrames              Counter32,
        fcIfLipF8In                         Counter32,
        fcIfLipF8Out                        Counter32,
        fcIfNonLipF8In                      Counter32,
        fcIfNonLipF8Out                     Counter32,
        fcIfTimeOutDiscards                 Counter64,
        fcIfOutDiscards                     Counter64,
        fcIfCreditLoss                      Counter64,
        fcIfTxWtAvgBBCreditTransitionToZero Counter64,
        fcIfBBCreditTransistionToZero       Counter32,
        fcHCIfBBCreditTransistionFromZero   Counter64,
        fcHCIfBBCreditTransistionToZero     Counter64,
        fcIfFECCorrectedBlks                Counter64,
        fcIfFECUncorrectedBlks              Counter64
}

fcIfLinkFailures OBJECT-TYPE
    SYNTAX          Counter32
    MAX-ACCESS      read-only
    STATUS          current
    DESCRIPTION
        "The number of link failures detected by the FC-Port."
    REFERENCE       "FC-PH REV 4.3 Section 29.3.1" 
    ::= { fcIfErrorEntry 1 }

fcIfSyncLosses OBJECT-TYPE
    SYNTAX          Counter32
    MAX-ACCESS      read-only
    STATUS          current
    DESCRIPTION
        "The number of loss of synchronization failures
        detected  by the FC-Port."
    REFERENCE       "FC-PH REV 4.3 Section 12.1.3.1" 
    ::= { fcIfErrorEntry 2 }

fcIfSigLosses OBJECT-TYPE
    SYNTAX          Counter32
    MAX-ACCESS      read-only
    STATUS          current
    DESCRIPTION
        "The number of signal losses detected by the FC-Port."
    REFERENCE       "FC-PH REV 4.3 Section 12.1.3.4" 
    ::= { fcIfErrorEntry 3 }

fcIfPrimSeqProtoErrors OBJECT-TYPE
    SYNTAX          Counter32
    MAX-ACCESS      read-only
    STATUS          current
    DESCRIPTION
        "The number of primitive sequence protocol errors
        detected by the FC-Port."
    REFERENCE       "FC-PH REV 4.3 Section 29.3.3" 
    ::= { fcIfErrorEntry 4 }

fcIfInvalidTxWords OBJECT-TYPE
    SYNTAX          Counter32
    MAX-ACCESS      read-only
    STATUS          current
    DESCRIPTION
        "The number of invalid transmission words detected by
        the FC-Port."
    REFERENCE       "FC-PH REV 4.3 Section 12.1.3.1" 
    ::= { fcIfErrorEntry 5 }

fcIfInvalidCrcs OBJECT-TYPE
    SYNTAX          Counter32
    MAX-ACCESS      read-only
    STATUS          current
    DESCRIPTION
        "The number of invalid CRCs detected by the FC-Port.
        Loop ports should not count CRC errors passing 
        through when monitoring."
    REFERENCE       "FC-PH REV 4.3 Section 29.8" 
    ::= { fcIfErrorEntry 6 }

fcIfDelimiterErrors OBJECT-TYPE
    SYNTAX          Counter32
    MAX-ACCESS      read-only
    STATUS          current
    DESCRIPTION
        "The number of Delimiter Errors detected by the
        FC-Port."
    REFERENCE       "FC-PH REV 4.3 Section 29.9" 
    ::= { fcIfErrorEntry 7 }

fcIfAddressIdErrors OBJECT-TYPE
    SYNTAX          Counter32
    MAX-ACCESS      read-only
    STATUS          current
    DESCRIPTION
        "The number of address identifier errors detected by
        the FC-Port."
    REFERENCE       "FC-PH REV 4.3 Section 29.9" 
    ::= { fcIfErrorEntry 8 }

fcIfLinkResetIns OBJECT-TYPE
    SYNTAX          Counter32
    MAX-ACCESS      read-only
    STATUS          current
    DESCRIPTION
        "The number of link reset protocol errors received by
        the FC-Port from the attached FC-port."
    REFERENCE       "FC-PH REV 4.3 Section 29.4" 
    ::= { fcIfErrorEntry 9 }

fcIfLinkResetOuts OBJECT-TYPE
    SYNTAX          Counter32
    MAX-ACCESS      read-only
    STATUS          current
    DESCRIPTION
        "The number of link reset protocol errors issued by
        the FC-Port to the attached FC-Port."
    REFERENCE       "FC-PH REV 4.3 Section 29.4" 
    ::= { fcIfErrorEntry 10 }

fcIfOlsIns OBJECT-TYPE
    SYNTAX          Counter32
    MAX-ACCESS      read-only
    STATUS          current
    DESCRIPTION
        "The number of Offline Sequence errors received by the
        FC-Port."
    REFERENCE       "FC-PH REV 4.3 Section 16.4.3" 
    ::= { fcIfErrorEntry 11 }

fcIfOlsOuts OBJECT-TYPE
    SYNTAX          Counter32
    MAX-ACCESS      read-only
    STATUS          current
    DESCRIPTION
        "The number of Offline Sequence errors issued by the
        FC-Port."
    REFERENCE       "FC-PH REV 4.3 Section 16.4.3" 
    ::= { fcIfErrorEntry 12 }

fcIfRuntFramesIn OBJECT-TYPE
    SYNTAX          Counter32
    MAX-ACCESS      read-only
    STATUS          current
    DESCRIPTION
        "The number of frames received by the FC-port that are
        shorter than the minimum allowable frame length 
        regardless if the  CRC is good or not." 
    ::= { fcIfErrorEntry 13 }

fcIfJabberFramesIn OBJECT-TYPE
    SYNTAX          Counter32
    MAX-ACCESS      read-only
    STATUS          current
    DESCRIPTION
        "The number of frames received by the FC-port that are
        longer than a maximum frame length and also have a 
        CRC error." 
    ::= { fcIfErrorEntry 14 }

fcIfTxWaitCount OBJECT-TYPE
    SYNTAX          Counter32
    MAX-ACCESS      read-only
    STATUS          current
    DESCRIPTION
        "The number of times the FC-port waited due to lack of
        transmit credits." 
    ::= { fcIfErrorEntry 15 }

fcIfFramesTooLong OBJECT-TYPE
    SYNTAX          Counter32
    MAX-ACCESS      read-only
    STATUS          current
    DESCRIPTION
        "The number of frames received by the FC-port where
        the frame length was greater than what was agreed to 
        in FLOGI/PLOGI. This could be caused by losing the 
        end of frame delimiter." 
    ::= { fcIfErrorEntry 16 }

fcIfFramesTooShort OBJECT-TYPE
    SYNTAX          Counter32
    MAX-ACCESS      read-only
    STATUS          current
    DESCRIPTION
        "The number of frames received by the FC-port where
        the frame length was less than the minimum indicated
        by the frame header (normally 24 bytes), but it could 
        be more if the DFCTL field indicates an optional
        header should be present." 
    ::= { fcIfErrorEntry 17 }

fcIfLRRIn OBJECT-TYPE
    SYNTAX          Counter32
    MAX-ACCESS      read-only
    STATUS          current
    DESCRIPTION
        "The number of Link reset responses received by the
        FC-port."
    REFERENCE       "FC-PH REV 4.3 Section 16.4.5" 
    ::= { fcIfErrorEntry 18 }

fcIfLRROut OBJECT-TYPE
    SYNTAX          Counter32
    MAX-ACCESS      read-only
    STATUS          current
    DESCRIPTION
        "The number of Link reset responses transmitted
        by the FC-port."
    REFERENCE       "FC-PH REV 4.3 Section 16.4.5" 
    ::= { fcIfErrorEntry 19 }

fcIfNOSIn OBJECT-TYPE
    SYNTAX          Counter32
    MAX-ACCESS      read-only
    STATUS          current
    DESCRIPTION
        "The number of non-operational sequences received by
        the FC-port."
    REFERENCE       "FC-PH REV 4.3 Section 16.4.2" 
    ::= { fcIfErrorEntry 20 }

fcIfNOSOut OBJECT-TYPE
    SYNTAX          Counter32
    MAX-ACCESS      read-only
    STATUS          current
    DESCRIPTION
        "The number of non-operational sequences transmitted
        by the FC-port."
    REFERENCE       "FC-PH REV 4.3 Section 16.4.2" 
    ::= { fcIfErrorEntry 21 }

fcIfFragFrames OBJECT-TYPE
    SYNTAX          Counter32
    MAX-ACCESS      read-only
    STATUS          current
    DESCRIPTION
        "The number of fragmented frames received by the
        FC-port." 
    ::= { fcIfErrorEntry 22 }

fcIfEOFaFrames OBJECT-TYPE
    SYNTAX          Counter32
    MAX-ACCESS      read-only
    STATUS          current
    DESCRIPTION
        "The number of frames received by FC-port with
        EOF aborts."
    REFERENCE       "FC-PH REV 4.3 Section 17.6.3" 
    ::= { fcIfErrorEntry 23 }

fcIfUnknownClassFrames OBJECT-TYPE
    SYNTAX          Counter32
    MAX-ACCESS      read-only
    STATUS          current
    DESCRIPTION
        "The number of unknown class frames received by
        FC-port." 
    ::= { fcIfErrorEntry 24 }

fcIf8b10bDisparityErrors OBJECT-TYPE
    SYNTAX          Counter32
    MAX-ACCESS      read-only
    STATUS          current
    DESCRIPTION
        "The number of 8b10b disparity errors." 
    ::= { fcIfErrorEntry 25 }

fcIfFramesDiscard OBJECT-TYPE
    SYNTAX          Counter32
    MAX-ACCESS      read-only
    STATUS          current
    DESCRIPTION
        "The number of frames discarded by the FC-port." 
    ::= { fcIfErrorEntry 26 }

fcIfELPFailures OBJECT-TYPE
    SYNTAX          Counter32
    MAX-ACCESS      read-only
    STATUS          current
    DESCRIPTION
        "The number of Exchange Link Parameters Switch Fabric
        Internal Link service request failures detected by the
        FC-Port. This object is applicable to only 
        Interconnect_Port, which are E_Port or B_Port."
    REFERENCE       "FC-PH REV 4.3 Section 29.3.1" 
    ::= { fcIfErrorEntry 27 }

fcIfBBCreditTransistionFromZero OBJECT-TYPE
    SYNTAX          Counter32
    MAX-ACCESS      read-only
    STATUS          current
    DESCRIPTION
        "fcIfBBCreditTransistionFromZero increments if the transmit b2b
        credit is zero" 
    ::= { fcIfErrorEntry 28 }

fcIfEISLFramesDiscard OBJECT-TYPE
    SYNTAX          Counter32
    MAX-ACCESS      read-only
    STATUS          current
    DESCRIPTION
        "The number of Enhanced Inter Switch Link (EISL) frames
        discarded by the FC-port. EISL frames carry an EISL
        header containing VSAN among other information." 
    ::= { fcIfErrorEntry 29 }

fcIfFramingErrorFrames OBJECT-TYPE
    SYNTAX          Counter32
    MAX-ACCESS      read-only
    STATUS          current
    DESCRIPTION
        "The number of framing errors. This denotes that the
        FC-port detected an inconsistency of frame structure." 
    ::= { fcIfErrorEntry 30 }

fcIfLipF8In OBJECT-TYPE
    SYNTAX          Counter32
    MAX-ACCESS      read-only
    STATUS          current
    DESCRIPTION
        "The number of 'F8' (LIP(F8,x)) type of Loop failures -
        Loop Initialization Primitive Sequence (LIP) errors 
        received by the FC-Port from the attached FC-port."
    REFERENCE       "FC-FS Rev 1.90 Section 5.5.4, and FC-AL-2." 
    ::= { fcIfErrorEntry 31 }

fcIfLipF8Out OBJECT-TYPE
    SYNTAX          Counter32
    MAX-ACCESS      read-only
    STATUS          current
    DESCRIPTION
        "The number of 'F8' (LIP(F8,x)) type of Loop failures -
        Loop Initialization Primitive Sequence (LIP) errors 
        issued by the FC-Port to the attached FC-Port."
    REFERENCE       "FC-FS Rev 1.90 Section 5.5.4, and FC-AL-2." 
    ::= { fcIfErrorEntry 32 }

fcIfNonLipF8In OBJECT-TYPE
    SYNTAX          Counter32
    MAX-ACCESS      read-only
    STATUS          current
    DESCRIPTION
        "The number of Non 'F8' (LIP(F8,x)) type of Loop
        failures - Loop Initialization Primitive Sequence
        (LIP) errors received by the FC-Port from the
        attached FC-port."
    REFERENCE       "FC-FS Rev 1.90 Section 5.5.4, and FC-AL-2." 
    ::= { fcIfErrorEntry 33 }

fcIfNonLipF8Out OBJECT-TYPE
    SYNTAX          Counter32
    MAX-ACCESS      read-only
    STATUS          current
    DESCRIPTION
        "The number of Non 'F8' (LIP(F8,x)) type of Loop
        failures - Loop Initialization Primitive Sequence
        (LIP) errors issued by the FC-Port to the attached
        FC-Port."
    REFERENCE       "FC-FS Rev 1.90 Section 5.5.4, and FC-AL-2." 
    ::= { fcIfErrorEntry 34 }

fcIfTimeOutDiscards OBJECT-TYPE
    SYNTAX          Counter64
    MAX-ACCESS      read-only
    STATUS          current
    DESCRIPTION
        "The number of packets that are dropped due to time-out
        at the FC-port or due to the FC-port going offline." 
    ::= { fcIfErrorEntry 35 }

fcIfOutDiscards OBJECT-TYPE
    SYNTAX          Counter64
    MAX-ACCESS      read-only
    STATUS          current
    DESCRIPTION
        "The total number of packets that are discarded in the
        egress side of the FC-port." 
    ::= { fcIfErrorEntry 36 }

fcIfCreditLoss OBJECT-TYPE
    SYNTAX          Counter64
    MAX-ACCESS      read-only
    STATUS          current
    DESCRIPTION
        "The number of link reset has occurred due to unavailable
        credits from the peer side of the link." 
    ::= { fcIfErrorEntry 37 }

fcIfTxWtAvgBBCreditTransitionToZero OBJECT-TYPE
    SYNTAX          Counter64
    MAX-ACCESS      read-only
    STATUS          current
    DESCRIPTION
        "fcIfTxWtAvgBBCreditTransitionToZero increments if the credit
        available is zero for 100 ms." 
    ::= { fcIfErrorEntry 38 }

fcIfBBCreditTransistionToZero OBJECT-TYPE
    SYNTAX          Counter32
    MAX-ACCESS      read-only
    STATUS          current
    DESCRIPTION
        "fcIfBBCreditTransistionToZero increments if the receive b2b
        credit is zero" 
    ::= { fcIfErrorEntry 39 }

fcHCIfBBCreditTransistionFromZero OBJECT-TYPE
    SYNTAX          Counter64
    MAX-ACCESS      read-only
    STATUS          current
    DESCRIPTION
        "fcHCIfBBCreditTransistionFromZero increments if the transmit b2b
        credit is zero." 
    ::= { fcIfErrorEntry 40 }

fcHCIfBBCreditTransistionToZero OBJECT-TYPE
    SYNTAX          Counter64
    MAX-ACCESS      read-only
    STATUS          current
    DESCRIPTION
        "fcHCIfBBCreditTransistionToZero increments if the receive b2b
        credit is zero." 
    ::= { fcIfErrorEntry 41 }

fcIfFECCorrectedBlks OBJECT-TYPE
    SYNTAX          Counter64
    MAX-ACCESS      read-only
    STATUS          current
    DESCRIPTION
        "The number of blocks corrected by FEC decoder." 
    ::= { fcIfErrorEntry 42 }

fcIfFECUncorrectedBlks OBJECT-TYPE
    SYNTAX          Counter64
    MAX-ACCESS      read-only
    STATUS          current
    DESCRIPTION
        "The number of blocks FEC decoder was unable
        to correct." 
    ::= { fcIfErrorEntry 43 }
 

-- fcIfC2AccountingTable .

fcIfC2AccountingTable OBJECT-TYPE
    SYNTAX          SEQUENCE OF FcIfC2AccountingEntry 
    MAX-ACCESS      not-accessible
    STATUS          current
    DESCRIPTION
        "This table contains, one entry for each F, FL or TL
        ports in the fabric element, including Port Channel
        ports. It contains Class 2 accounting information."
    ::= { cffFcFeStatistics 2 }

fcIfC2AccountingEntry OBJECT-TYPE
    SYNTAX          FcIfC2AccountingEntry
    MAX-ACCESS      not-accessible
    STATUS          current
    DESCRIPTION
        "Each entry contains Class 2 accounting information for
        each F, FL or TL port."
    INDEX           { ifIndex } 
    ::= { fcIfC2AccountingTable 1 }

FcIfC2AccountingEntry ::= SEQUENCE {
        fcIfC2InFrames   Counter64,
        fcIfC2OutFrames  Counter64,
        fcIfC2InOctets   Counter64,
        fcIfC2OutOctets  Counter64,
        fcIfC2Discards   Counter32,
        fcIfC2FbsyFrames Counter32,
        fcIfC2FrjtFrames Counter32,
        fcIfC2PBSYFrames Counter32,
        fcIfC2PRJTFrames Counter32
}

fcIfC2InFrames OBJECT-TYPE
    SYNTAX          Counter64
    MAX-ACCESS      read-only
    STATUS          current
    DESCRIPTION
        "The number of Class 2 frames received by this port from
        its attached Nx_Port." 
    ::= { fcIfC2AccountingEntry 1 }

fcIfC2OutFrames OBJECT-TYPE
    SYNTAX          Counter64
    MAX-ACCESS      read-only
    STATUS          current
    DESCRIPTION
        "The number of Class 2 frames delivered through this
        port to its attached Nx_Port." 
    ::= { fcIfC2AccountingEntry 2 }

fcIfC2InOctets OBJECT-TYPE
    SYNTAX          Counter64
    MAX-ACCESS      read-only
    STATUS          current
    DESCRIPTION
        "The number of Class 2 frame octets, including the frame
        delimiters, received by this port from its attached
        Nx_Port." 
    ::= { fcIfC2AccountingEntry 3 }

fcIfC2OutOctets OBJECT-TYPE
    SYNTAX          Counter64
    MAX-ACCESS      read-only
    STATUS          current
    DESCRIPTION
        "The number of Class 2 frame octets, including the frame
        delimiters, delivered through this port to its attached
        Nx_Port." 
    ::= { fcIfC2AccountingEntry 4 }

fcIfC2Discards OBJECT-TYPE
    SYNTAX          Counter32
    MAX-ACCESS      read-only
    STATUS          current
    DESCRIPTION
        "The number of Class 2 frames discarded by this port." 
    ::= { fcIfC2AccountingEntry 5 }

fcIfC2FbsyFrames OBJECT-TYPE
    SYNTAX          Counter32
    MAX-ACCESS      read-only
    STATUS          current
    DESCRIPTION
        "The number of F_BSY frames generated by this port
        against Class 2 frames."
    REFERENCE       "FC-PH REV 4.3 Section 20.3.3.1" 
    ::= { fcIfC2AccountingEntry 6 }

fcIfC2FrjtFrames OBJECT-TYPE
    SYNTAX          Counter32
    MAX-ACCESS      read-only
    STATUS          current
    DESCRIPTION
        "The number of F_RJT frames generated by this port
        against Class 2 frames."
    REFERENCE       "FC-PH REV 4.3 Section 20.3.3.3" 
    ::= { fcIfC2AccountingEntry 7 }

fcIfC2PBSYFrames OBJECT-TYPE
    SYNTAX          Counter32
    MAX-ACCESS      read-only
    STATUS          current
    DESCRIPTION
        "The number of times that port busy was returned to
        this port as result of a class 2 frame that could not
        be delivered to the other end of the link. This 
        occurs if the destination Nx_Port is temporarily busy.
        PBSY can only occur on SOFc1 frames ( the frames that
        establish a connection )."
    REFERENCE       "FC-PH REV 4.3 Section 29.9.2" 
    ::= { fcIfC2AccountingEntry 8 }

fcIfC2PRJTFrames OBJECT-TYPE
    SYNTAX          Counter32
    MAX-ACCESS      read-only
    STATUS          current
    DESCRIPTION
        "The number of times that port reject was returned to
        this port as a result of a class 2 frame that was 
        rejected at the destination Nx_Port."
    REFERENCE       "FC-PH REV 4.3 Section 29.9.2" 
    ::= { fcIfC2AccountingEntry 9 }
 

-- fcIfC3AccountingTable

fcIfC3AccountingTable OBJECT-TYPE
    SYNTAX          SEQUENCE OF FcIfC3AccountingEntry 
    MAX-ACCESS      not-accessible
    STATUS          current
    DESCRIPTION
        "This table contains, one entry for each F, FL or TL
        ports in the fabric element, including Port Channel
        ports. It contains Class 3 accounting information."
    ::= { cffFcFeStatistics 3 }

fcIfC3AccountingEntry OBJECT-TYPE
    SYNTAX          FcIfC3AccountingEntry
    MAX-ACCESS      not-accessible
    STATUS          current
    DESCRIPTION
        "Each entry contains Class 3 accounting information for
        each F, FL or TL port."
    INDEX           { ifIndex } 
    ::= { fcIfC3AccountingTable 1 }

FcIfC3AccountingEntry ::= SEQUENCE {
        fcIfC3InFrames  Counter64,
        fcIfC3OutFrames Counter64,
        fcIfC3InOctets  Counter64,
        fcIfC3OutOctets Counter64,
        fcIfC3Discards  Counter32
}

fcIfC3InFrames OBJECT-TYPE
    SYNTAX          Counter64
    MAX-ACCESS      read-only
    STATUS          current
    DESCRIPTION
        "The number of Class 3 frames received by this port
        from its attached Nx_Port." 
    ::= { fcIfC3AccountingEntry 1 }

fcIfC3OutFrames OBJECT-TYPE
    SYNTAX          Counter64
    MAX-ACCESS      read-only
    STATUS          current
    DESCRIPTION
        "The number of Class 3 frames transmitted by this
        port to its attached Nx_Port." 
    ::= { fcIfC3AccountingEntry 2 }

fcIfC3InOctets OBJECT-TYPE
    SYNTAX          Counter64
    MAX-ACCESS      read-only
    STATUS          current
    DESCRIPTION
        "The number of Class 3 frame octets, including the
        frame delimiters, received by this port from its 
        attached Nx_Port." 
    ::= { fcIfC3AccountingEntry 3 }

fcIfC3OutOctets OBJECT-TYPE
    SYNTAX          Counter64
    MAX-ACCESS      read-only
    STATUS          current
    DESCRIPTION
        "The number of Class 3 frame octets, including the
        frame delimiters, transmitted by this port to its a
        attached Nx_Port." 
    ::= { fcIfC3AccountingEntry 4 }

fcIfC3Discards OBJECT-TYPE
    SYNTAX          Counter32
    MAX-ACCESS      read-only
    STATUS          current
    DESCRIPTION
        "The number of Class 3 frames discarded by this port." 
    ::= { fcIfC3AccountingEntry 5 }
 

-- fcIfCfAccountingTable

fcIfCfAccountingTable OBJECT-TYPE
    SYNTAX          SEQUENCE OF FcIfCfAccountingEntry 
    MAX-ACCESS      not-accessible
    STATUS          current
    DESCRIPTION
        "A table that contains, one entry for each
        Interconnect_Ports (xE_port, B_port) in the fabric
        element, including Port Channel ports.
        It contains Class F accounting information."
    ::= { cffFcFeStatistics 4 }

fcIfCfAccountingEntry OBJECT-TYPE
    SYNTAX          FcIfCfAccountingEntry
    MAX-ACCESS      not-accessible
    STATUS          current
    DESCRIPTION
        "An entry containing Class F accounting information for
        each xE_port."
    INDEX           { ifIndex } 
    ::= { fcIfCfAccountingTable 1 }

FcIfCfAccountingEntry ::= SEQUENCE {
        fcIfCfInFrames  Counter64,
        fcIfCfOutFrames Counter64,
        fcIfCfInOctets  Counter64,
        fcIfCfOutOctets Counter64,
        fcIfCfDiscards  Counter32
}

fcIfCfInFrames OBJECT-TYPE
    SYNTAX          Counter64
    MAX-ACCESS      read-only
    STATUS          current
    DESCRIPTION
        "The number of Class F frames received by this port." 
    ::= { fcIfCfAccountingEntry 1 }

fcIfCfOutFrames OBJECT-TYPE
    SYNTAX          Counter64
    MAX-ACCESS      read-only
    STATUS          current
    DESCRIPTION
        "The number of Class F frames transmitted by this
        port." 
    ::= { fcIfCfAccountingEntry 2 }

fcIfCfInOctets OBJECT-TYPE
    SYNTAX          Counter64
    MAX-ACCESS      read-only
    STATUS          current
    DESCRIPTION
        "The number of Class F frame octets, including the
        frame delimiters, received by this port from its 
        attached Nx_Port." 
    ::= { fcIfCfAccountingEntry 3 }

fcIfCfOutOctets OBJECT-TYPE
    SYNTAX          Counter64
    MAX-ACCESS      read-only
    STATUS          current
    DESCRIPTION
        "The number of Class F frame octets, including the
        frame delimiters, transmitted by this port to its a
        attached Nx_Port." 
    ::= { fcIfCfAccountingEntry 4 }

fcIfCfDiscards OBJECT-TYPE
    SYNTAX          Counter32
    MAX-ACCESS      read-only
    STATUS          current
    DESCRIPTION
        "The number of Class F frames discarded by this port." 
    ::= { fcIfCfAccountingEntry 5 }
 

-- fcIfStatTable

fcIfStatTable OBJECT-TYPE
    SYNTAX          SEQUENCE OF FcIfStatEntry 
    MAX-ACCESS      not-accessible
    STATUS          current
    DESCRIPTION
        "A table that contains, one entry for each
        physical fibre channel port.
        It contains statistics information."
    ::= { cffFcFeStatistics 5 }

fcIfStatEntry OBJECT-TYPE
    SYNTAX          FcIfStatEntry
    MAX-ACCESS      not-accessible
    STATUS          current
    DESCRIPTION
        "An entry containing statistics information for
        each fibre channel port."
    INDEX           { ifIndex } 
    ::= { fcIfStatTable 1 }

FcIfStatEntry ::= SEQUENCE {
        fcIfCurrRxBbCredit FcBbCredit,
        fcIfCurrTxBbCredit FcBbCredit
}

fcIfCurrRxBbCredit OBJECT-TYPE
    SYNTAX          FcBbCredit
    MAX-ACCESS      read-only
    STATUS          current
    DESCRIPTION
        "The current value of receive buffer-to-buffer credits
        for this port." 
    ::= { fcIfStatEntry 1 }

fcIfCurrTxBbCredit OBJECT-TYPE
    SYNTAX          FcBbCredit
    MAX-ACCESS      read-only
    STATUS          current
    DESCRIPTION
        "The current value of transmit buffer-to-buffer credits
        for this port." 
    ::= { fcIfStatEntry 2 }
 


-- Notifications

fcTrunkIfDownNotify NOTIFICATION-TYPE
    OBJECTS         {
                        fcTrunkIfOperStatus,
                        fcTrunkIfOperStatusCause,
                        fcTrunkIfOperStatusCauseDescr
                    }
    STATUS          current
    DESCRIPTION
        "This notification is generated by the agent
        whenever the fcTrunkifOperStatus object for this
        trunk interface is about to enter the down state from
        some other state. This other state is indicated by 
        the included value of fcTrunkifOperStatus."
   ::= { cffFcFeNotifications 1 }

fcTrunkIfUpNotify NOTIFICATION-TYPE
    OBJECTS         {
                        fcTrunkIfOperStatus,
                        fcTrunkIfOperStatusCause,
                        fcTrunkIfOperStatusCauseDescr
                    }
    STATUS          current
    DESCRIPTION
        "This notification is generated by the agent
        whenever the fcTrunkifOperStatus object for one of
        its trunk interfaces has left the down state and 
        transitioned into some other state. This other
        state is indicated by the included value of
        fcTrunkifOperStatus."
   ::= { cffFcFeNotifications 2 }

fcIfElpReject NOTIFICATION-TYPE
    OBJECTS         {
                        fcIfElpNbrNodeName,
                        fcIfElpNbrPortName,
                        fcIfElpRejectReasonCode,
                        fcIfElpRejectReasonCodeExpl
                    }
    STATUS          current
    DESCRIPTION
        "This notification is generated by the agent
        whenever this interface received a ELP request and
        rejected it."
   ::= { cffFcFeNotifications 3 }

fcotInserted NOTIFICATION-TYPE
    OBJECTS         { cieIfOperStatusCause }
    STATUS          current
    DESCRIPTION
        "This notification indicates that a Fibre Channel Optical
        Transmitter (FCOT) for an interface is inserted.

        This notification is generated by the agent whenever the
        'cieIfOperStatusCause' object for one of its interfaces
        has transitioned into some other state from
        'fcotNotPresent' state.
        This other state is indicated by the included value
        of 'cieIfOperStatusCause'."
   ::= { cffFcFeNotifications 4 }

fcotRemoved NOTIFICATION-TYPE
    OBJECTS         { cieIfOperStatusCause }
    STATUS          current
    DESCRIPTION
        "This notification indicates that a Fibre Channel Optical
        Transmitter (FCOT) for an interface is removed.

        This notification is generated by the agent whenever the
        'cieIfOperStatusCause' object for one of its interfaces
        has entered into 'fcotNotPresent' state."
   ::= { cffFcFeNotifications 5 }
-- conformance information

cffFcFeMIBCompliances  OBJECT IDENTIFIER
    ::= { cffFcFeMIBConformance 1 }

cffFcFeMIBGroups  OBJECT IDENTIFIER
    ::= { cffFcFeMIBConformance 2 }


cffFcFeMIBCompliance MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfCapGroup,
                        fcIfErrorGroup,
                        fcIfC2AccountingGroup,
                        fcIfC3AccountingGroup,
                        fcIfCfAccountingGroup,
                        fcIfNotificationGroup
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."
    ::= { cffFcFeMIBCompliances 1 }

cffFcFeMIBCompliance1 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfCapGroup,
                        fcIfErrorGroup,
                        fcIfC2AccountingGroup,
                        fcIfC3AccountingGroup,
                        fcIfCfAccountingGroup,
                        fcIfNotificationGroup,
                        fcIfGroupRev1
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."
    ::= { cffFcFeMIBCompliances 2 }

cffFcFeMIBCompliance2 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."
    ::= { cffFcFeMIBCompliances 3 }

cffFcFeMIBCompliance3 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."
    ::= { cffFcFeMIBCompliances 4 }

cffFcFeMIBCompliance4 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 5 }

cffFcFeMIBCompliance5 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup
                    }

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 6 }

cffFcFeMIBComplianceRev6 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup
                    }

    GROUP           fcotInfoNotificationGroup
    DESCRIPTION
        "Implementation of this group is optional."

    GROUP           fcIfGigEInfoGroup
    DESCRIPTION
        "Implementation of this group is optional."

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 7 }

cffFcFeMIBComplianceRev7 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup
                    }

    GROUP           fcotInfoNotificationGroup
    DESCRIPTION
        "Implementation of this group is optional."

    GROUP           fcIfGigEInfoGroup
    DESCRIPTION
        "Implementation of this group is optional."

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 8 }

cffFcFeMIBComplianceRev8 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfBbScnGroup
                    }

    GROUP           fcotInfoNotificationGroup
    DESCRIPTION
        "Implementation of this group is optional."

    GROUP           fcIfGigEInfoGroup
    DESCRIPTION
        "Implementation of this group is optional."

    OBJECT          cffFcFeElementName
    MIN-ACCESS      read-only
    DESCRIPTION
        "Write access is not required."

    OBJECT          fcIfRxDataFieldSize
    SYNTAX          Integer32 (256..2112)
    DESCRIPTION
        "It is compliant to support a minimum value of
        of 256 for this object which is larger than 
        the defined minimum value."

    OBJECT          fcIfPortRateMode
    MIN-ACCESS      read-only
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 9 }

cffFcFeMIBComplianceRev9 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfBbScnGroup,
                        fcIfCapableGroup,
                        fcIfInfoPortGroup
                    }

    GROUP           fcotInfoNotificationGroup
    DESCRIPTION
        "Implementation of this group is optional."

    GROUP           fcIfGigEInfoGroup
    DESCRIPTION
        "Implementation of this group is optional."

    GROUP           fcIfModuleGroup
    DESCRIPTION
        "Implementation of this group is optional."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 10 }

cffFcFeMIBComplianceRev10 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfBbScnGroup,
                        fcIfCapableGroup,
                        fcIfInfoPortGroup,
                        fcIfModuleGroup
                    }

    GROUP           fcotInfoNotificationGroup
    DESCRIPTION
        "Implementation of this group is optional."

    GROUP           fcIfGigEInfoGroup
    DESCRIPTION
        "Implementation of this group is optional."

    GROUP           fcIfToggleCtrlConfigGroup
    DESCRIPTION
        "Implementation of this group is optional."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 11 }

cffFcFeMIBComplianceRev11 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfBbScnGroup,
                        fcIfCapableGroup,
                        fcIfInfoPortGroup,
                        fcIfModuleGroupRev1
                    }

    GROUP           fcotInfoNotificationGroup
    DESCRIPTION
        "Implementation of this group is optional."

    GROUP           fcIfGigEInfoGroup
    DESCRIPTION
        "Implementation of this group is optional."

    GROUP           fcIfFlapCtrlConfigGroup
    DESCRIPTION
        "Implementation of this group is optional."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 12 }

cffFcFeMIBComplianceRev12 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfGigEinfoExtGroupRev1,
                        fcIfBbScnGroup,
                        fcIfCapableGroup,
                        fcIfInfoPortGroup,
                        fcIfModuleGroupRev1
                    }

    GROUP           fcotInfoNotificationGroup
    DESCRIPTION
        "Implementation of this group is optional."

    GROUP           fcIfGigEInfoGroup
    DESCRIPTION
        "Implementation of this group is optional."

    GROUP           fcIfFlapCtrlConfigGroup
    DESCRIPTION
        "Implementation of this group is optional."

    GROUP           fcIfErrorGroupRev2
    DESCRIPTION
        "Implementation of this group is mandatory only
        for the devices which support errors of the ports
        in this group."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 13 }

cffFcFeMIBComplianceRev13 MODULE-COMPLIANCE
    STATUS          deprecated
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfGigEinfoExtGroupRev1,
                        fcIfBbScnGroup,
                        fcIfCapableGroup,
                        fcIfInfoPortGroup,
                        fcIfModuleGroupRev1
                    }

    GROUP           fcotInfoNotificationGroup
    DESCRIPTION
        "Implementation of this group is optional."

    GROUP           fcIfGigEInfoGroup
    DESCRIPTION
        "Implementation of this group is optional."

    GROUP           fcIfFlapCtrlConfigGroup
    DESCRIPTION
        "Implementation of this group is optional."

    GROUP           fcIfErrorGroupRev2
    DESCRIPTION
        "Implementation of this group is mandatory only
        for the devices which support errors of the ports
        in this group."

    GROUP           fcIfErrorGroupRev3
    DESCRIPTION
        "Implementation of this group is mandatory only
        for the devices which support errors of the ports
        in this group."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."
    ::= { cffFcFeMIBCompliances 14 }

cffFcFeMIBComplianceRev14 MODULE-COMPLIANCE
    STATUS          current
    DESCRIPTION
        "The compliance statement for entities which
        implement the CISCO-FC-FE-MIB."
    MODULE          -- this module
    MANDATORY-GROUPS {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcIfInfoGroup,
                        fcIfGigEinfoExtGroup,
                        fcIfGigEinfoExtGroupRev1,
                        fcIfBbScnGroup,
                        fcIfCapableGroup,
                        fcIfInfoPortGroup,
                        fcIfModuleGroupRev1,
                        fcIfGroupRev4
                    }

    GROUP           fcotInfoNotificationGroup
    DESCRIPTION
        "Implementation of this group is optional."

    GROUP           fcIfGigEInfoGroup
    DESCRIPTION
        "Implementation of this group is optional."

    GROUP           fcIfFlapCtrlConfigGroup
    DESCRIPTION
        "Implementation of this group is optional."

    GROUP           fcIfErrorGroupRev2
    DESCRIPTION
        "Implementation of this group is mandatory only
        for the devices which support errors of the ports
        in this group."

    GROUP           fcIfErrorGroupRev3
    DESCRIPTION
        "Implementation of this group is mandatory only
        for the devices which support errors of the ports
        in this group."

    GROUP           fcIfErrorGroupRev4
    DESCRIPTION
        "Implementation of this group is mandatory only
        for the devices which support errors of the ports
        in this group."

    OBJECT          cffFcFeElementName
    MIN-ACCESS      read-only
    DESCRIPTION
        "Write access is not required."

    OBJECT          fcIfPortRateMode
    MIN-ACCESS      read-only
    DESCRIPTION
        "Write access is not required."

    OBJECT          fcIfRxDataFieldSize
    SYNTAX          FcRxDataFieldSize
    DESCRIPTION
        "Write access is not required."

    OBJECT          fcIfAdminRxBbCredit
    DESCRIPTION
        "It is compliant to support a range which is
        smaller than the range defined."

    OBJECT          fcIfAdminRxBbCreditModeISL
    DESCRIPTION
        "It is compliant to support a range which is
        smaller than the range defined."

    OBJECT          fcIfAdminRxBbCreditModeFx
    DESCRIPTION
        "It is compliant to support a range which is
        smaller than the range defined."

    OBJECT          fcIfAdminFECState
    MIN-ACCESS      read-only
    DESCRIPTION
        "Write access is not required."
        
    ::= { cffFcFeMIBCompliances 15 }

-- Units of Conformance

fcFeGroup OBJECT-GROUP
    OBJECTS         {
                        cffFcFeElementName,
                        adminTrunkProtocol,
                        fcIfElpRejectReasonCode,
                        fcIfElpRejectReasonCodeExpl
                    }
    STATUS          current
    DESCRIPTION
        "A collection objects giving port information."
    ::= { cffFcFeMIBGroups 1 }

fcIfGroup OBJECT-GROUP
    OBJECTS         {
                        fcIfWwn,
                        fcIfAdminMode,
                        fcIfOperMode,
                        fcIfAdminSpeed,
                        fcIfBeaconMode,
                        fcIfPortChannelIfIndex,
                        fcIfOperStatusCause,
                        fcIfOperStatusCauseDescr,
                        fcIfAdminTrunkMode,
                        fcIfOperTrunkMode,
                        fcIfAllowedVsanList2k,
                        fcIfAllowedVsanList4k,
                        fcIfActiveVsanList2k,
                        fcIfActiveVsanList4k,
                        fcIfBbCreditModel,
                        fcIfHoldTime,
                        fcIfTransmitterType,
                        fcIfConnectorType,
                        fcIfSerialNo,
                        fcIfRevision,
                        fcIfVendor,
                        fcIfSFPSerialIDData,
                        fcIfPartNumber,
                        fcIfAdminRxBbCredit,
                        fcIfAdminRxBbCreditModeISL,
                        fcIfAdminRxBbCreditModeFx,
                        fcIfOperRxBbCredit,
                        fcIfRxDataFieldSize
                    }
    STATUS          current
    DESCRIPTION
        "A collection objects giving port information."
    ::= { cffFcFeMIBGroups 2 }

fcTrunkIfGroup OBJECT-GROUP
    OBJECTS         {
                        fcTrunkIfOperStatus,
                        fcTrunkIfOperStatusCause,
                        fcTrunkIfOperStatusCauseDescr
                    }
    STATUS          current
    DESCRIPTION
        "A collection objects giving trunk port information."
    ::= { cffFcFeMIBGroups 3 }

fcIfLoginGroup OBJECT-GROUP
    OBJECTS         {
                        fcIfLoginEntryCount,
                        fcIfNxPortNodeName,
                        fcIfNxPortName,
                        fcIfNxPortAddress,
                        fcIfNxFcphVersionAgreed,
                        fcIfNxRxBbCredit,
                        fcIfNxTxBbCredit,
                        fcIfNxClass2RxDataFieldSize,
                        fcIfNxClass3RxDataFieldSize,
                        fcIfNxCosSuppAgreed,
                        fcIfNxClass2SeqDelivAgreed,
                        fcIfNxClass3SeqDelivAgreed
                    }
    STATUS          current
    DESCRIPTION
        "A collection of objects giving Fabric Login info for
        Fx_Port."
    ::= { cffFcFeMIBGroups 4 }

fcIfElpGroup OBJECT-GROUP
    OBJECTS         {
                        fcIfElpNbrNodeName,
                        fcIfElpNbrPortName,
                        fcIfElpRxBbCredit,
                        fcIfElpTxBbCredit,
                        fcIfElpCosSuppAgreed,
                        fcIfElpClass2SeqDelivAgreed,
                        fcIfElpClass2RxDataFieldSize,
                        fcIfElpClass3SeqDelivAgreed,
                        fcIfElpClass3RxDataFieldSize,
                        fcIfElpClassFXII,
                        fcIfElpClassFRxDataFieldSize,
                        fcIfElpClassFConcurrentSeq,
                        fcIfElpClassFEndToEndCredit,
                        fcIfElpClassFOpenSeq
                    }
    STATUS          current
    DESCRIPTION
        "A collection of objects giving Exchange Link Parameters
        established between the 2 Interconnect_Ports."
    ::= { cffFcFeMIBGroups 5 }

fcIfCapGroup OBJECT-GROUP
    OBJECTS         {
                        fcIfCapFcphVersionHigh,
                        fcIfCapFcphVersionLow,
                        fcIfCapRxBbCreditMax,
                        fcIfCapRxBbCreditMin,
                        fcIfCapRxDataFieldSizeMax,
                        fcIfCapRxDataFieldSizeMin,
                        fcIfCapCos,
                        fcIfCapClass2SeqDeliv,
                        fcIfCapClass3SeqDeliv,
                        fcIfCapHoldTimeMax,
                        fcIfCapHoldTimeMin,
                        fcIfCapISLRxBbCreditMax,
                        fcIfCapISLRxBbCreditMin,
                        fcIfCapRxBbCreditWriteable,
                        fcIfCapRxBbCreditDefault,
                        fcIfCapISLRxBbCreditDefault
                    }
    STATUS          deprecated
    DESCRIPTION
        "A collection of objects providing information what the
        port is capable of supporting."
    ::= { cffFcFeMIBGroups 6 }

fcIfErrorGroup OBJECT-GROUP
    OBJECTS         {
                        fcIfLinkFailures,
                        fcIfSyncLosses,
                        fcIfSigLosses,
                        fcIfPrimSeqProtoErrors,
                        fcIfInvalidTxWords,
                        fcIfInvalidCrcs,
                        fcIfDelimiterErrors,
                        fcIfAddressIdErrors,
                        fcIfLinkResetIns,
                        fcIfLinkResetOuts,
                        fcIfOlsIns,
                        fcIfOlsOuts,
                        fcIfRuntFramesIn,
                        fcIfJabberFramesIn,
                        fcIfTxWaitCount,
                        fcIfFramesTooLong,
                        fcIfFramesTooShort,
                        fcIfLRRIn,
                        fcIfLRROut,
                        fcIfNOSIn,
                        fcIfNOSOut,
                        fcIfFragFrames,
                        fcIfEOFaFrames,
                        fcIfUnknownClassFrames,
                        fcIf8b10bDisparityErrors,
                        fcIfFramesDiscard,
                        fcIfELPFailures,
                        fcIfBBCreditTransistionFromZero,
                        fcIfEISLFramesDiscard,
                        fcIfFramingErrorFrames
                    }
    STATUS          current
    DESCRIPTION
        "A collection of objects providing errors of the ports."
    ::= { cffFcFeMIBGroups 7 }

fcIfC2AccountingGroup OBJECT-GROUP
    OBJECTS         {
                        fcIfC2InFrames,
                        fcIfC2OutFrames,
                        fcIfC2InOctets,
                        fcIfC2OutOctets,
                        fcIfC2Discards,
                        fcIfC2FbsyFrames,
                        fcIfC2FrjtFrames,
                        fcIfC2PBSYFrames,
                        fcIfC2PRJTFrames
                    }
    STATUS          current
    DESCRIPTION
        "A collection of objects providing class 2 accounting
        information of  the ports."
    ::= { cffFcFeMIBGroups 8 }

fcIfC3AccountingGroup OBJECT-GROUP
    OBJECTS         {
                        fcIfC3InFrames,
                        fcIfC3OutFrames,
                        fcIfC3InOctets,
                        fcIfC3OutOctets,
                        fcIfC3Discards
                    }
    STATUS          current
    DESCRIPTION
        "A collection of objects providing class 3 accounting
        information of  the ports."
    ::= { cffFcFeMIBGroups 9 }

fcIfCfAccountingGroup OBJECT-GROUP
    OBJECTS         {
                        fcIfCfInFrames,
                        fcIfCfOutFrames,
                        fcIfCfInOctets,
                        fcIfCfOutOctets,
                        fcIfCfDiscards
                    }
    STATUS          current
    DESCRIPTION
        "A collection of objects providing class f accounting
        information of the ports."
    ::= { cffFcFeMIBGroups 10 }

fcIfNotificationGroup NOTIFICATION-GROUP
   NOTIFICATIONS    {
                        fcTrunkIfDownNotify,
                        fcTrunkIfUpNotify,
                        fcIfElpReject
                    }
    STATUS          current
    DESCRIPTION
        "A collection of notifications for monitoring fibre
        channel interfaces."
    ::= { cffFcFeMIBGroups 11 }

fcIfGroupRev1 OBJECT-GROUP
    OBJECTS         {
                        fcIfActiveVsanUpList2k,
                        fcIfActiveVsanUpList4k
                    }
    STATUS          current
    DESCRIPTION
        "A collection objects giving port information."
    ::= { cffFcFeMIBGroups 12 }

fcIfCapGroupRev1 OBJECT-GROUP
    OBJECTS         {
                        fcIfCapFcphVersionHigh,
                        fcIfCapFcphVersionLow,
                        fcIfCapRxDataFieldSizeMax,
                        fcIfCapRxDataFieldSizeMin,
                        fcIfCapCos,
                        fcIfCapClass2SeqDeliv,
                        fcIfCapClass3SeqDeliv,
                        fcIfCapHoldTimeMax,
                        fcIfCapHoldTimeMin,
                        fcIfCapBbScnCapable,
                        fcIfCapBbScnMax,
                        fcIfCapOsmFrmCapable,
                        fcIfCapOsmRxBbCreditWriteable,
                        fcIfCapOsmRxBbCreditMax,
                        fcIfCapOsmRxBbCreditMin,
                        fcIfCapOsmRxBbCreditDefault,
                        fcIfCapOsmISLRxBbCreditMax,
                        fcIfCapOsmISLRxBbCreditMin,
                        fcIfCapOsmISLRxBbCreditDefault,
                        fcIfCapOsmRxPerfBufWriteable,
                        fcIfCapOsmRxPerfBufMax,
                        fcIfCapOsmRxPerfBufMin,
                        fcIfCapOsmRxPerfBufDefault,
                        fcIfCapOsmISLRxPerfBufMax,
                        fcIfCapOsmISLRxPerfBufMin,
                        fcIfCapOsmISLRxPerfBufDefault,
                        fcIfCapFrmRxBbCreditWriteable,
                        fcIfCapFrmRxBbCreditMax,
                        fcIfCapFrmRxBbCreditMin,
                        fcIfCapFrmRxBbCreditDefault,
                        fcIfCapFrmISLRxBbCreditMax,
                        fcIfCapFrmISLRxBbCreditMin,
                        fcIfCapFrmISLRxBbCreditDefault,
                        fcIfCapFrmRxPerfBufWriteable,
                        fcIfCapFrmRxPerfBufMax,
                        fcIfCapFrmRxPerfBufMin,
                        fcIfCapFrmRxPerfBufDefault,
                        fcIfCapFrmISLRxPerfBufMax,
                        fcIfCapFrmISLRxPerfBufMin,
                        fcIfCapFrmISLRxPerfBufDefault
                    }
    STATUS          current
    DESCRIPTION
        "A collection of objects providing information what the
        port is capable of supporting."
    ::= { cffFcFeMIBGroups 13 }

fcIfGroupRev2 OBJECT-GROUP
    OBJECTS         {
                        fcIfPortRateMode,
                        fcIfAdminRxPerfBuffer,
                        fcIfOperRxPerfBuffer,
                        fcIfBbScn
                    }
    STATUS          current
    DESCRIPTION
        "A collection objects giving port information."
    ::= { cffFcFeMIBGroups 14 }

fcIfStatGroup OBJECT-GROUP
    OBJECTS         {
                        fcIfCurrRxBbCredit,
                        fcIfCurrTxBbCredit
                    }
    STATUS          current
    DESCRIPTION
        "A collection objects giving port statistics."
    ::= { cffFcFeMIBGroups 15 }

fcIfErrorGroupRev1 OBJECT-GROUP
    OBJECTS         {
                        fcIfLipF8In,
                        fcIfLipF8Out,
                        fcIfNonLipF8In,
                        fcIfNonLipF8Out
                    }
    STATUS          current
    DESCRIPTION
        "A collection of objects providing errors of the ports."
    ::= { cffFcFeMIBGroups 16 }

fcIfGroupRev3 OBJECT-GROUP
    OBJECTS         { fcIfPortInitStatus }
    STATUS          current
    DESCRIPTION
        "A collection objects giving port information."
    ::= { cffFcFeMIBGroups 17 }

fcIfRNIDInfoGroup OBJECT-GROUP
    OBJECTS         {
                        fcIfRNIDInfoStatus,
                        fcIfRNIDInfoTypeNumber,
                        fcIfRNIDInfoModelNumber,
                        fcIfRNIDInfoManufacturer,
                        fcIfRNIDInfoPlantOfMfg,
                        fcIfRNIDInfoSerialNumber,
                        fcIfRNIDInfoUnitType,
                        fcIfRNIDInfoPortId
                    }
    STATUS          current
    DESCRIPTION
        "A collection objects giving the peer node identification
        data."
    ::= { cffFcFeMIBGroups 18 }

fcIfGigEInfoGroup OBJECT-GROUP
    OBJECTS         { fcIfGigEPortChannelIfIndex }
    STATUS          current
    DESCRIPTION
        "A collection objects to provide port channel information
        for gigabit ethernet interfaces."
    ::= { cffFcFeMIBGroups 19 }

fcotInfoNotificationGroup NOTIFICATION-GROUP
   NOTIFICATIONS    {
                        fcotInserted,
                        fcotRemoved
                    }
    STATUS          current
    DESCRIPTION
        "A collection of notifications for FCOT Inserted/Removed."
    ::= { cffFcFeMIBGroups 20 }

fcIfInfoGroup OBJECT-GROUP
    OBJECTS         {
                        fcIfAdminRxBbCreditExtended,
                        fcIfFcTunnelIfIndex,
                        fcIfServiceState
                    }
    STATUS          current
    DESCRIPTION
        "A collection of objects providing information what the
        port is capable of supporting."
    ::= { cffFcFeMIBGroups 21 }

fcIfGigEinfoExtGroup OBJECT-GROUP
    OBJECTS         {
                        fcIfGigEAutoNegotiate,
                        fcIfGigEBeaconMode
                    }
    STATUS          current
    DESCRIPTION
        "A collection objects giving providing information about
        GigE interfaces."
    ::= { cffFcFeMIBGroups 22 }

fcIfBbScnGroup OBJECT-GROUP
    OBJECTS         { fcIfAdminBbScnMode }
    STATUS          current
    DESCRIPTION
        "A collection of objects providing information what the
        port is capable of supporting."
    ::= { cffFcFeMIBGroups 23 }

fcIfCapableGroup OBJECT-GROUP
    OBJECTS         {
                        fcIfIsServiceStateCapable,
                        fcIfIsPortRateModeCapable,
                        fcIfIsAdminRxBbCreditExtendedCapable
                    }
    STATUS          current
    DESCRIPTION
        "This is a group of objects that help the user figure out if the
        system is capable of a change in the given object."
    ::= { cffFcFeMIBGroups 24 }

fcIfInfoPortGroup OBJECT-GROUP
    OBJECTS         { fcIfPortType }
    STATUS          current
    DESCRIPTION
        "A collection objects giving port information."
    ::= { cffFcFeMIBGroups 25 }

fcIfModuleGroup OBJECT-GROUP
    OBJECTS         {
                        fcIfModuleOverSubscriptionRatioConfig,
                        fcIfModuleBandwidthFairnessConfig,
                        fcIfModuleBandwidthFairnessOper
                    }
    STATUS          deprecated
    DESCRIPTION
        "A collection objects giving module information."
    ::= { cffFcFeMIBGroups 26 }

fcIfToggleCtrlConfigGroup OBJECT-GROUP
    OBJECTS         {
                        fcIfToggleCtrlConfigEnable,
                        fcIfToggleCtrlConfigReason,
                        fcIfToggleCtrlConfigDuration,
                        fcIfToggleCtrlConfigNumFlaps
                    }
    STATUS          deprecated
    DESCRIPTION
        "A collection of objects which provides toggle control
        information for fibre channel interface."
    ::= { cffFcFeMIBGroups 27 }

fcIfFlapCtrlConfigGroup OBJECT-GROUP
    OBJECTS         {
                        fcIfFlapCtrlConfigEnable,
                        fcIfFlapCtrlConfigDuration,
                        fcIfFlapCtrlConfigNumFlaps
                    }
    STATUS          current
    DESCRIPTION
        "A collection of objects which provides toggle control
        information for fibre channel interface."
    ::= { cffFcFeMIBGroups 28 }

fcIfModuleGroupRev1 OBJECT-GROUP
    OBJECTS         {
                        fcIfModuleOverSubscriptionRatioConfig,
                        fcIfModuleBandwidthFairnessConfig,
                        fcIfModuleBandwidthFairnessOper,
                        fcIfModuleXcvrFrequencyConfig
                    }
    STATUS          current
    DESCRIPTION
        "A collection objects giving module information."
    ::= { cffFcFeMIBGroups 29 }

fcIfGigEinfoExtGroupRev1 OBJECT-GROUP
    OBJECTS         { fcIfGigConnectorType }
    STATUS          current
    DESCRIPTION
        "A collection objects giving providing information about
        GigE interfaces."
    ::= { cffFcFeMIBGroups 30 }

fcIfErrorGroupRev2 OBJECT-GROUP
    OBJECTS         {
                        fcIfTimeOutDiscards,
                        fcIfOutDiscards,
                        fcIfCreditLoss,
                        fcIfTxWtAvgBBCreditTransitionToZero
                    }
    STATUS          current
    DESCRIPTION
        "A collection of objects providing errors of the ports."
    ::= { cffFcFeMIBGroups 31 }

fcIfErrorGroupRev3 OBJECT-GROUP
    OBJECTS         {
                        fcIfBBCreditTransistionToZero,
                        fcHCIfBBCreditTransistionFromZero,
                        fcHCIfBBCreditTransistionToZero
                    }
    STATUS          current
    DESCRIPTION
        "A collection of objects providing errors of the ports."
    ::= { cffFcFeMIBGroups 32 }

fcIfGroupRev4 OBJECT-GROUP
    OBJECTS         {
                        fcIfAdminFECState,
                        fcIfOperFECState
                    }
    STATUS          current
    DESCRIPTION
        "A collection objects giving port information."
    ::= { cffFcFeMIBGroups 33 }

fcIfErrorGroupRev4 OBJECT-GROUP
    OBJECTS         {
                        fcIfFECCorrectedBlks,
                        fcIfFECUncorrectedBlks
                    }
    STATUS          current
    DESCRIPTION
        "A collection of objects providing errors of the ports."
    ::= { cffFcFeMIBGroups 34 }

END
