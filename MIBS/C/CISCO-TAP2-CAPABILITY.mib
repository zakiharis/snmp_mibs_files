-- *****************************************************************
-- CISCO-TAP2-CAPABILITY.my:
-- Cisco CISCO-TAP2-MIB AGENT-CAPABILITIES
--
-- September 2007, Edward Pham 
--
-- Copyright (c) 2007 by Cisco Systems, Inc.
-- All rights reserved.
-- *****************************************************************

CISCO-TAP2-CAPABILITY DEFINITIONS ::= BEGIN

IMPORTS
        MODULE-IDENTITY
                FROM SNMPv2-SMI
        AGENT-CAPABILITIES
                FROM SNMPv2-CONF
        InetAddressType
                FROM INET-ADDRESS-MIB
        ciscoAgentCapability
                FROM CISCO-SMI;

ciscoTap2Capability MODULE-IDENTITY
        LAST-UPDATED    "200709110000Z"
        ORGANIZATION    "Cisco Systems, Inc."
        CONTACT-INFO
                "       Cisco Systems
                        Customer Service

                Postal: 170 West Tasman Drive
                        San Jose, CA  95134
                        USA

                   Tel: +1 800 553-NETS

                E-mail: cs-li@cisco.com"
        DESCRIPTION
                "The capabilities description of CISCO-TAP2-MIB."
        REVISION        "200709110000Z"
        DESCRIPTION
                "Initial version of this MIB module."
        ::= { ciscoAgentCapability 559 }

ciscoTap2CapV12R0233SXHPCat6k AGENT-CAPABILITIES
    PRODUCT-RELEASE     "Cisco IOS 12.2(33)SXH on Catalyst 6000/6500
                         series devices."
    STATUS              current
    DESCRIPTION         "CISCO-TAP2-MIB capabilities."

    SUPPORTS            CISCO-TAP2-MIB
        INCLUDES        {
                          ciscoTap2MediationComplianceGroup,
                          ciscoTap2StreamComplianceGroup,
                          ciscoTap2MediationCpbComplianceGroup,
                          ciscoTap2NotificationGroup,
                          ciscoTap2StreamHCStatsGroup
                        }
        VARIATION       ciscoTap2Switchover 
        ACCESS          not-implemented
        DESCRIPTION     "Not supported in this platform."

        VARIATION       cTap2MediationCapabilities
        SYNTAX          BITS { ipV4SrcInterface(0), udp(2) }
        DESCRIPTION     "Only limited set of enumerated values are
                        supported."
 
        VARIATION       cTap2MediationDestAddressType 
        SYNTAX          InetAddressType { ipv4(1) } 
        DESCRIPTION     "Only limited set of enumerated values are
                        supported."

        VARIATION       cTap2MediationTimeout 
        DESCRIPTION     "Value of this object is supported up to 
                         35791 minutes."

        VARIATION       cTap2MediationTransport 
        SYNTAX          INTEGER { udp(1) } 
        DESCRIPTION     "Only limited set of enumerated values are
                        supported."

        VARIATION       cTap2MediationSrcInterface 
        DESCRIPTION     "Only the value of zero or the ifIndex value of 
                        a routed interface capable of processing IPv4 traffic
                        can be supported."

        VARIATION       cTap2StreamType 
        SYNTAX          INTEGER { ip(1) } 
        DESCRIPTION     "Only limited set of enumerated values are
                        supported."

    ::= { ciscoTap2Capability 1 }

END
