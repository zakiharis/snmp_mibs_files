--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPENET-MIB DEFINITIONS ::= BEGIN

IMPORTS
	enterprises, NetworkAddress, IpAddress,
	Counter, Gauge, TimeTicks, DisplayString
		FROM RFC1155-SMI
	OBJECT-TYPE
		FROM RFC-1212;

chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }


-- The olEnet Group

-- This group represents information about Ethernet networks.

olEnetStatsTable OBJECT-TYPE
	SYNTAX SEQUENCE OF OlEnetStatsEntry
	ACCESS not-accessible
	STATUS mandatory
	DESCRIPTION
		"A table that contains statistical information about
		Ethernet (IEEE 802.3) networks."
	::= { olEnet 1 }

olEnetStatsEntry OBJECT-TYPE
	SYNTAX OlEnetStatsEntry
	ACCESS not-accessible
	STATUS mandatory
	DESCRIPTION
		"A list of statistical information about each Ethernet
		(IEEE 802.3) network in the concentrator."
	INDEX { olEnetStatsNetID }
	::= { olEnetStatsTable 1 }

OlEnetStatsEntry ::=
	SEQUENCE {
		olEnetStatsNetID
			INTEGER,
		olEnetStatsFramesRcvdOks
			Counter,
		olEnetStatsOctetsRcvdOks
			Counter,
		olEnetStatsMcastRcvdOks
			Counter,
		olEnetStatsBcastRcvdOks
			Counter,
		olEnetStatsFrameTooLongs
			Counter,
		olEnetStatsAlignmentErrors
			Counter,
		olEnetStatsFCSErrors
			Counter,
		olEnetStatsRunts
			Counter,
		olEnetStatsLocalColls
			Counter
		}

olEnetStatsNetID OBJECT-TYPE
	SYNTAX INTEGER {
		ethernet-1(6), -- corresponds to ifIndex
		ethernet-2(7),
		ethernet-3(8)
		}
	ACCESS read-only
	STATUS mandatory
	DESCRIPTION
		"The network index that uniquely identifies this network.
		One of ethernet-1, ethernet-2, or ethernet-3."
	::= { olEnetStatsEntry 1 }

olEnetStatsFramesRcvdOks OBJECT-TYPE
	SYNTAX Counter
	ACCESS read-only
	STATUS mandatory
	DESCRIPTION
		"The count of frames that were successfully received by this
		network.  This counter does not include frames received 
		in error."
	::= { olEnetStatsEntry 2 }

olEnetStatsOctetsRcvdOks OBJECT-TYPE
	SYNTAX Counter
	ACCESS read-only
	STATUS mandatory
	DESCRIPTION
		"The count of the number of octets that were successfully 
		received by this network.  This counter does not include 
		octets that were part of frames that were received in error."
	::= { olEnetStatsEntry 3 }

olEnetStatsMcastRcvdOks OBJECT-TYPE
	SYNTAX Counter
	ACCESS read-only
	STATUS mandatory
	DESCRIPTION
		"The count of the number of multicast frames successfully
		received by this network."
	::= { olEnetStatsEntry 4 }

olEnetStatsBcastRcvdOks OBJECT-TYPE
	SYNTAX Counter
	ACCESS read-only
	STATUS mandatory
	DESCRIPTION
		"The count of the number of broadcast frames successfully
		received by this network."
	::= { olEnetStatsEntry 5 }

olEnetStatsFrameTooLongs OBJECT-TYPE
	SYNTAX Counter
	ACCESS read-only
	STATUS mandatory
	DESCRIPTION
		"The count of the number of frames received by this network
		that exceeds the maximum permitted Ethernet (802.3) frame
		size."
	::= { olEnetStatsEntry 6 }

olEnetStatsAlignmentErrors OBJECT-TYPE
	SYNTAX Counter
	ACCESS read-only
	STATUS mandatory
	DESCRIPTION
		"The count of the number of frames received by this network
		that did not pass the frame check sequence (FCS) check
		and that are not an integral number of octets.  These
		frames are not counted in olEnetStatsFCSErrors."
	::= { olEnetStatsEntry 7 }

olEnetStatsFCSErrors OBJECT-TYPE
	SYNTAX Counter
	ACCESS read-only
	STATUS mandatory
	DESCRIPTION
		"The count of the number of frames received by this network
		that did not pass the frame check sequence (FCS) check
		and are an integral number of octets."
	::= { olEnetStatsEntry 8 }

olEnetStatsRunts OBJECT-TYPE
	SYNTAX Counter
	ACCESS read-only
	STATUS mandatory
	DESCRIPTION
		"The count of the number of frames received by this network
		 that are less than 512 bits long.  "
	::= { olEnetStatsEntry 9 }

olEnetStatsLocalColls OBJECT-TYPE
	SYNTAX Counter
	ACCESS read-only
	STATUS mandatory
	DESCRIPTION
		"The count of the number of times that two or more ports 
		within this concentrator have received traffic simultaneously."
	::= { olEnetStatsEntry 10 }




olEnetStatsModTable OBJECT-TYPE
	SYNTAX SEQUENCE OF OlEnetStatsModEntry
	ACCESS not-accessible
	STATUS mandatory
	DESCRIPTION
		"A table of statistical information counted for each module
		in each Ethernet (IEEE 802.3) network."
	::= { olEnet 2 }

olEnetStatsModEntry OBJECT-TYPE
	SYNTAX OlEnetStatsModEntry
	ACCESS not-accessible
	STATUS mandatory
	DESCRIPTION
		"A list of statistical information for each port
		on each Ethernet (IEEE 802.3) network in the concentrator."
	INDEX { olEnetStatsModNetID, olEnetStatsModSlotIndex }
	::= { olEnetStatsModTable 1 }

OlEnetStatsModEntry ::=
	SEQUENCE {
		olEnetStatsModNetID
			INTEGER,
		olEnetStatsModSlotIndex
			INTEGER,
		olEnetStatsModFramesRcvdOks
			Counter,
		olEnetStatsModOctetsRcvdOks
			Counter,
		olEnetStatsModMcastRcvdOks
			Counter,
		olEnetStatsModBcastRcvdOks
			Counter,
		olEnetStatsModFrameTooLongs
			Counter,
		olEnetStatsModAlignmentErrors
			Counter,
		olEnetStatsModFCSErrors
			Counter,
		olEnetStatsModRunts
			Counter
		}

olEnetStatsModNetID OBJECT-TYPE
	SYNTAX INTEGER {
		ethernet-1(6), -- corresponds to ifIndex
		ethernet-2(7),
		ethernet-3(8)
		}
	ACCESS read-only
	STATUS mandatory
	DESCRIPTION
		"The unique identifier for this network.  
		One of ethernet-1, ethernet-2, or ethernet-3."
	::= { olEnetStatsModEntry 1 }

olEnetStatsModSlotIndex OBJECT-TYPE
	SYNTAX INTEGER
	ACCESS read-only
	STATUS mandatory
	DESCRIPTION
		"The slot number that contains this module."
	::= { olEnetStatsModEntry 2 }

olEnetStatsModFramesRcvdOks OBJECT-TYPE
	SYNTAX Counter
	ACCESS read-only
	STATUS mandatory
	DESCRIPTION
		"The count of frames that were successfully received by this
		module.  This counter does not include frames received in 
		error."
	::= { olEnetStatsModEntry 3 }

olEnetStatsModOctetsRcvdOks OBJECT-TYPE
	SYNTAX Counter
	ACCESS read-only
	STATUS mandatory
	DESCRIPTION
		"The count of the number of octets that were successfully 
		received by this module.  This counter does not include 
		octets that were part of frames that were received in error."
	::= { olEnetStatsModEntry 4 }

olEnetStatsModMcastRcvdOks OBJECT-TYPE
	SYNTAX Counter
	ACCESS read-only
	STATUS mandatory
	DESCRIPTION
		"The count of the number of multicast frames successfully
		received by this module."
	::= { olEnetStatsModEntry 5 }

olEnetStatsModBcastRcvdOks OBJECT-TYPE
	SYNTAX Counter
	ACCESS read-only
	STATUS mandatory
	DESCRIPTION
		"The count of the number of broadcast frames successfully
		received by this module."
	::= { olEnetStatsModEntry 6 }

olEnetStatsModFrameTooLongs OBJECT-TYPE
	SYNTAX Counter
	ACCESS read-only
	STATUS mandatory
	DESCRIPTION
		"The count of the number of frames received by this module
		that exceeds the maximum permitted Ethernet (802.3) frame
		size."
	::= { olEnetStatsModEntry 7 }

olEnetStatsModAlignmentErrors OBJECT-TYPE
	SYNTAX Counter
	ACCESS read-only
	STATUS mandatory
	DESCRIPTION
		"The count of the number of frames received by this module
		that did not pass the frame check sequence (FCS) check
		and that are not an integral number of octets.  These
		frames are not counted in olEnetStatsModFCSErrors."
	::= { olEnetStatsModEntry 8 }

olEnetStatsModFCSErrors OBJECT-TYPE
	SYNTAX Counter
	ACCESS read-only
	STATUS mandatory
	DESCRIPTION
		"The count of the number of frames received by this module
		that did not pass the frame check sequence (FCS) check
		and are an integral number of octets."
	::= { olEnetStatsModEntry 9 }

olEnetStatsModRunts OBJECT-TYPE
	SYNTAX Counter
	ACCESS read-only
	STATUS mandatory
	DESCRIPTION
		"The count of the number of frames received by 
		this module that are less than 512 bits long.  "
	::= { olEnetStatsModEntry 10 }



olEnetStatsPortTable OBJECT-TYPE
	SYNTAX SEQUENCE OF OlEnetStatsPortEntry
	ACCESS not-accessible
	STATUS mandatory
	DESCRIPTION
		"A table of statistical information counted for each port
		in each Ethernet (IEEE 802.3) network."
	::= { olEnet 3 }

olEnetStatsPortEntry OBJECT-TYPE
	SYNTAX OlEnetStatsPortEntry
	ACCESS not-accessible
	STATUS mandatory
	DESCRIPTION
		"A list of statistical information for each port
		on each Ethernet (IEEE 802.3) network in the concentrator."
	INDEX { olEnetStatsPortSlotIndex, olEnetStatsPortIndex }
	::= { olEnetStatsPortTable 1 }

OlEnetStatsPortEntry ::=
	SEQUENCE {
		olEnetStatsPortNetID
			INTEGER,
		olEnetStatsPortSlotIndex
			INTEGER,
		olEnetStatsPortIndex
			INTEGER,
		olEnetStatsPortFramesRcvdOks
			Counter,
		olEnetStatsPortOctetsRcvdOks
			Counter,
		olEnetStatsPortMcastRcvdOks
			 Counter,
		 olEnetStatsPortBcastRcvdOks
			 Counter,
		 olEnetStatsPortFrameTooLongs
			 Counter,
		 olEnetStatsPortAlignmentErrors
			 Counter,
		 olEnetStatsPortFCSErrors
			 Counter,
		 olEnetStatsPortRunts
			 Counter,
		 olEnetStatsPortSrcAddrChanges
			 Counter,
		 olEnetStatsPortLastSrcAddr
			 OCTET STRING (SIZE(6)),
		 olEnetStatsPortLastErrAddr
			 OCTET STRING (SIZE(6))
		 }

olEnetStatsPortNetID OBJECT-TYPE
	 SYNTAX INTEGER {
		 ethernet-1(6), -- corresponds to ifIndex
		 ethernet-2(7),
		 ethernet-3(8)
		 }
	 ACCESS read-only
	 STATUS mandatory
	 DESCRIPTION
		 "The unique identifier for this network.  
		 One of ethernet-1, ethernet-2, or ethernet-3."
	 ::= { olEnetStatsPortEntry 1 }

olEnetStatsPortSlotIndex OBJECT-TYPE
	 SYNTAX INTEGER
	 ACCESS read-only
	 STATUS mandatory
	 DESCRIPTION
		 "The slot number that contains this port."
	 ::= { olEnetStatsPortEntry 2 }

olEnetStatsPortIndex OBJECT-TYPE
	 SYNTAX INTEGER
	 ACCESS read-only
	 STATUS mandatory
	 DESCRIPTION
		 "The port number within this slot."
	 ::= { olEnetStatsPortEntry 3 }

olEnetStatsPortFramesRcvdOks OBJECT-TYPE
	 SYNTAX Counter
	 ACCESS read-only
	 STATUS mandatory
	 DESCRIPTION
		 "The count of frames that were successfully received by this
		 port.  This counter does not include frames received in error."
	 ::= { olEnetStatsPortEntry 4 }

olEnetStatsPortOctetsRcvdOks OBJECT-TYPE
	 SYNTAX Counter
	 ACCESS read-only
	 STATUS mandatory
	 DESCRIPTION
		 "The count of the number of octets that were successfully 
		 received by this port.  This counter does not include 
		 octets that were part of frames that were received in error."
	 ::= { olEnetStatsPortEntry 5 }

olEnetStatsPortMcastRcvdOks OBJECT-TYPE
	 SYNTAX Counter
	 ACCESS read-only
	 STATUS mandatory
	 DESCRIPTION
		 "The count of the number of multicast frames successfully
		 received by this port."
	 ::= { olEnetStatsPortEntry 6 }

olEnetStatsPortBcastRcvdOks OBJECT-TYPE
	 SYNTAX Counter
	 ACCESS read-only
	 STATUS mandatory
	 DESCRIPTION
		 "The count of the number of broadcast frames successfully
		 received by this port."
	 ::= { olEnetStatsPortEntry 7 }

olEnetStatsPortFrameTooLongs OBJECT-TYPE
	 SYNTAX Counter
	 ACCESS read-only
	 STATUS mandatory
	 DESCRIPTION
		 "The count of the number of frames received by this port
		 that exceeds the maximum permitted Ethernet (802.3) frame
		 size."
	 ::= { olEnetStatsPortEntry 8 }

olEnetStatsPortAlignmentErrors OBJECT-TYPE
	 SYNTAX Counter
	 ACCESS read-only
	 STATUS mandatory
	 DESCRIPTION
		 "The count of the number of frames received by this port
		 that did not pass the frame check sequence (FCS) check
		 and that are not an integral number of octets.  These
		 frames are not counted in olEnetStatsPortFCSErrors."
	 ::= { olEnetStatsPortEntry 9 }

olEnetStatsPortFCSErrors OBJECT-TYPE
	 SYNTAX Counter
	 ACCESS read-only
	 STATUS mandatory
	 DESCRIPTION
		 "The count of the number of frames received by this port
		 that did not pass the frame check sequence (FCS) check
		 and are an integral number of octets."
	 ::= { olEnetStatsPortEntry 10 }

olEnetStatsPortRunts OBJECT-TYPE
	 SYNTAX Counter
	 ACCESS read-only
	 STATUS mandatory
	 DESCRIPTION
		 "The count of the number of frames received by this port that
		 are less than 512 bits long.  "
	 ::= { olEnetStatsPortEntry 11 }


olEnetStatsPortSrcAddrChanges OBJECT-TYPE
	 SYNTAX Counter
	 ACCESS read-only
	 STATUS mandatory
	 DESCRIPTION
		 "The count of the number of times that 
		 olEnetStatsPortLastSourceAddr 
		{ olEnetStatsPortEntry 11 } has changed."
	 ::= { olEnetStatsPortEntry 12 }

olEnetStatsPortLastSrcAddr OBJECT-TYPE
	 SYNTAX OCTET STRING (SIZE(6))
	 ACCESS read-only
	 STATUS mandatory
	 DESCRIPTION
		 "The last source address seen on this port for this
		 network for the last successfully received frame."
	 ::= { olEnetStatsPortEntry 13 }

olEnetStatsPortLastErrAddr OBJECT-TYPE
	 SYNTAX OCTET STRING (SIZE(6))
	 ACCESS read-only
	 STATUS mandatory
	 DESCRIPTION
		 "The value stored in the source address portion of
		 a frame received in error (alignment, FCS, or too long).
		 Since the frame was received in error, there is no
		 guarantee that this is an actual valid address."
	 ::= { olEnetStatsPortEntry 14 }

olEnetMapTable OBJECT-TYPE
	 SYNTAX SEQUENCE OF OlEnetMapEntry
	 ACCESS not-accessible
	 STATUS mandatory
	 DESCRIPTION
		 "A table that contains a cache of information relating
		 an Ethernet source address with a specific port for
		 a given network.  An indication of this source's utilization
		 of the network is also provided."
	 ::= { olEnet 4 }

olEnetMapEntry OBJECT-TYPE
	 SYNTAX OlEnetMapEntry
	 ACCESS not-accessible
	 STATUS mandatory
	 DESCRIPTION
		 "A list of information that tracks a source address to
		 a specific port for each network."
	 INDEX { olEnetMapNetID, olEnetMapAddress }
	 ::= { olEnetMapTable 1 }

OlEnetMapEntry ::= 
	 SEQUENCE {
		 olEnetMapNetID
			 INTEGER,
		 olEnetMapAddress
			 OCTET STRING,
		 olEnetMapSlotIndex
			 INTEGER,
		 olEnetMapPortIndex
			 INTEGER,
		 olEnetMapFrames
			 Counter,
		 olEnetMapOctets
			 Counter,
		 olEnetMapTime		
			 TimeTicks
		 }

olEnetMapNetID OBJECT-TYPE
	 SYNTAX INTEGER {
		 ethernet-1(6),  -- corresponds to ifIndex
		 ethernet-2(7),
		 ethernet-3(8)
		 }	
	 ACCESS read-only
	 STATUS mandatory
	 DESCRIPTION
		 "The network index that uniquely identifies this network.
		 One of ethernet-1, ethernet-2, ethernet-3."
	 ::= { olEnetMapEntry 1 }

olEnetMapAddress OBJECT-TYPE
	 SYNTAX OCTET STRING (SIZE(6))
	 ACCESS read-only
	 STATUS mandatory
	 DESCRIPTION
		 "An Ethernet source address received by this port on this
		 network."
	 ::= { olEnetMapEntry 2 }

olEnetMapSlotIndex OBJECT-TYPE
	 SYNTAX INTEGER
	 ACCESS read-only
	 STATUS mandatory
	 DESCRIPTION
		 "The slot number of the port that received this address."
	 ::= { olEnetMapEntry 3 }


olEnetMapPortIndex OBJECT-TYPE
	 SYNTAX INTEGER
	 ACCESS read-only
	 STATUS mandatory
	 DESCRIPTION
		 "The port number within olEnetMapSlotIndex's slot that
		 received this address."
	 ::= { olEnetMapEntry 4 }

olEnetMapFrames OBJECT-TYPE
	 SYNTAX Counter
	 ACCESS read-only
	 STATUS mandatory
	 DESCRIPTION
		 "An estimated count of the number of frames generated by this
		 address.  This count should be interpreted as an
		 indicator, not a true frame count."
	 ::= { olEnetMapEntry 5 }

olEnetMapOctets OBJECT-TYPE
	 SYNTAX Counter
	 ACCESS read-only
	 STATUS mandatory
	 DESCRIPTION
		 "An estimated count of the number of octets generated by this
		 address.  This count should be interpreted as an
		 indicator, not a true octet count."
	 ::= { olEnetMapEntry 6 }

olEnetMapTime OBJECT-TYPE
	 SYNTAX TimeTicks
	 ACCESS read-only
	 STATUS mandatory
	 DESCRIPTION
		 "The time in in hundredths of a second since this address 
		 was last seen.  For example, if olEnetMapTime is 500 
		 ticks, then this adddress was seen 5 seconds ago."
	 ::= { olEnetMapEntry 7 }





END
