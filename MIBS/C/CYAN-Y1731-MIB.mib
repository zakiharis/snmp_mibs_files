CYAN-Y1731-MIB DEFINITIONS ::= BEGIN
IMPORTS
    MODULE-IDENTITY,
    OBJECT-TYPE,
    Unsigned32
                    FROM SNMPv2-SMI

    CyanNoYesTc
                    FROM CYAN-TC-MIB

    cyanMibModules
		    FROM CYAN-MIB

    MODULE-COMPLIANCE,
    OBJECT-GROUP
	            FROM SNMPv2-CONF;


cyanY1731Module MODULE-IDENTITY
    LAST-UPDATED "201412070545Z" -- Sun Dec  7 05:45:32 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for CYAN Y1731 OAMPM"

    REVISION     "201412070545Z" -- Sun Dec  7 05:45:32 2014
    DESCRIPTION  "Release 6.0 build 1416362081"

    ::= { cyanMibModules 40 }

cyanY1731MibObjects           OBJECT IDENTIFIER ::={ cyanY1731Module 1 }

-- *****************************************************************************
-- CYAN Y1731 MEP Configuration Table
-- *****************************************************************************

cyanY1731MepConfigTable    OBJECT-TYPE
    SYNTAX        SEQUENCE OF CyanY1731MepConfigEntry
    MAX-ACCESS    not-accessible
    STATUS        current
    DESCRIPTION
        "A list of Y1731 MEP config entries"
    ::= { cyanY1731MibObjects 1 }

cyanY1731MepConfigEntry    OBJECT-TYPE
    SYNTAX        CyanY1731MepConfigEntry
    MAX-ACCESS    not-accessible
    STATUS        current
    DESCRIPTION
        "An entry of Y1731 MEP Configuration."
    INDEX {
        cyanY1731MepConfigShelfId,
        cyanY1731MepConfigModuleId,
        cyanY1731MepConfigMepId
    }
    ::= { cyanY1731MepConfigTable 1 }

CyanY1731MepConfigEntry  ::=
    SEQUENCE {
        cyanY1731MepConfigShelfId                   Unsigned32,
        cyanY1731MepConfigModuleId                  Unsigned32,
        cyanY1731MepConfigMepId                     Unsigned32,
        cyanY1731MepConfigLMTxInterval              Unsigned32,
        cyanY1731MepConfigDMTxInterval              Unsigned32,
        cyanY1731MepConfigPmEnabled                 CyanNoYesTc,
        cyanY1731MepConfigOneWayLossEnabled         CyanNoYesTc,
        cyanY1731MepConfigTwoWayDelayEnabled        CyanNoYesTc,
        cyanY1731MepConfigTwoWayJitterEnabled       CyanNoYesTc
    }

cyanY1731MepConfigShelfId OBJECT-TYPE
    SYNTAX       Unsigned32 (0..255)
    MAX-ACCESS   not-accessible
    STATUS       current
    DESCRIPTION
        "Shelf Id"

    ::= { cyanY1731MepConfigEntry 1 }

cyanY1731MepConfigModuleId OBJECT-TYPE
    SYNTAX       Unsigned32
    MAX-ACCESS   not-accessible
    STATUS       current
    DESCRIPTION
        "Module Id"

    ::= { cyanY1731MepConfigEntry 2 }

cyanY1731MepConfigMepId OBJECT-TYPE
    SYNTAX       Unsigned32
    MAX-ACCESS   not-accessible
    STATUS       current
    DESCRIPTION
        "MEP Id"

    ::= { cyanY1731MepConfigEntry 3 }

cyanY1731MepConfigLMTxInterval OBJECT-TYPE
    SYNTAX       Unsigned32
    MAX-ACCESS   read-only
    STATUS       current
    DESCRIPTION
        "Loss OAM PDU Tx Interval in Seconds"

    ::= { cyanY1731MepConfigEntry 4 }

cyanY1731MepConfigDMTxInterval OBJECT-TYPE
    SYNTAX       Unsigned32
    MAX-ACCESS   read-only
    STATUS       current
    DESCRIPTION
        "Delay OAM PDU Tx Interval in Seconds"

    ::= { cyanY1731MepConfigEntry 5 }

cyanY1731MepConfigPmEnabled OBJECT-TYPE
    SYNTAX       CyanNoYesTc
    MAX-ACCESS   read-only
    STATUS       current
    DESCRIPTION
        "PM Enabled"

    ::= { cyanY1731MepConfigEntry 6 }

cyanY1731MepConfigOneWayLossEnabled OBJECT-TYPE
    SYNTAX       CyanNoYesTc
    MAX-ACCESS   read-only
    STATUS       current
    DESCRIPTION
        "One-way LOSS Enabled"

    ::= { cyanY1731MepConfigEntry 7 }

cyanY1731MepConfigTwoWayDelayEnabled OBJECT-TYPE
    SYNTAX       CyanNoYesTc
    MAX-ACCESS   read-only
    STATUS       current
    DESCRIPTION
        "Two-way Delay Enabled"

    ::= { cyanY1731MepConfigEntry 8 }

cyanY1731MepConfigTwoWayJitterEnabled OBJECT-TYPE
    SYNTAX       CyanNoYesTc
    MAX-ACCESS   read-only
    STATUS       current
    DESCRIPTION
        "Two-way Jitter Enabled"

    ::= { cyanY1731MepConfigEntry 9 }

-- *****************************************************************************
-- CYAN Y1731 MEP Loss Measurement (LM) Table
-- *****************************************************************************

cyanY1731LMTable    OBJECT-TYPE
    SYNTAX        SEQUENCE OF CyanY1731LMEntry
    MAX-ACCESS    not-accessible
    STATUS        current
    DESCRIPTION
        "A list of Y1731 Packet Loss Mesurement(LM) Entries.
        Each row in this table represents last completed Loss Measurement (LM)
        for a given MEP. Only the last completed historical bucket is supported.
        The value of cyanY1731LMIndex is always 1 and
        this represents last completed historical bucket.
        "

    ::= { cyanY1731MibObjects 2 }

cyanY1731LMEntry    OBJECT-TYPE
    SYNTAX        CyanY1731LMEntry
    MAX-ACCESS    not-accessible
    STATUS        current
    DESCRIPTION
        "An entry of Y1731 Loss Measurement."
    INDEX {
        cyanY1731LMShelfId,
        cyanY1731LMModuleId,
        cyanY1731LMMepId,
        cyanY1731LMIndex
    }

    ::= { cyanY1731LMTable 1 }

CyanY1731LMEntry  ::=
    SEQUENCE {
        cyanY1731LMShelfId                   Unsigned32,
        cyanY1731LMModuleId                  Unsigned32,
        cyanY1731LMMepId                     Unsigned32,
        cyanY1731LMIndex                     Unsigned32,

        cyanY1731LMNe15MinPmCount            Unsigned32,
        cyanY1731LMNe15MinPmTimestamp        Unsigned32,

        cyanY1731LMFe15MinPmCount            Unsigned32,
        cyanY1731LMFe15MinPmTimestamp        Unsigned32,

        cyanY1731LMRatioNe15MinHighValue     Unsigned32,
        cyanY1731LMRatioNe15MinLowValue      Unsigned32,
        cyanY1731LMRatioNe15MinAvgValue      Unsigned32,
        cyanY1731LMRatioNe15MinTimestamp     Unsigned32,

        cyanY1731LMRatioFe15MinHighValue     Unsigned32,
        cyanY1731LMRatioFe15MinLowValue      Unsigned32,
        cyanY1731LMRatioFe15MinAvgValue      Unsigned32,
        cyanY1731LMRatioFe15MinTimestamp     Unsigned32

    }


cyanY1731LMShelfId OBJECT-TYPE
    SYNTAX       Unsigned32 (0..255)
    MAX-ACCESS   not-accessible
    STATUS       current
    DESCRIPTION
        "Shelf Id"

    ::= { cyanY1731LMEntry 1 }

cyanY1731LMModuleId OBJECT-TYPE
    SYNTAX       Unsigned32
    MAX-ACCESS   not-accessible
    STATUS       current
    DESCRIPTION
        "Module Id"

    ::= { cyanY1731LMEntry 2 }

cyanY1731LMMepId OBJECT-TYPE
    SYNTAX       Unsigned32
    MAX-ACCESS   not-accessible
    STATUS       current
    DESCRIPTION
        "MEP Id"

    ::= { cyanY1731LMEntry 3 }

cyanY1731LMIndex    OBJECT-TYPE
    SYNTAX          Unsigned32
    MAX-ACCESS      not-accessible
    STATUS          current
    DESCRIPTION
        "Y1731 LM MEP Bucket Index. Currently only
        one bucket is supported with possible value of 1.
        Value 1 means that it is the latest historical bucket"

    ::= { cyanY1731LMEntry 4 }

cyanY1731LMNe15MinPmCount OBJECT-TYPE
    SYNTAX       Unsigned32
    MAX-ACCESS   read-only
    STATUS       current
    DESCRIPTION
        "Near-end Packet Loss 15 Min Pm Count"

    ::= { cyanY1731LMEntry 5 }

cyanY1731LMNe15MinPmTimestamp OBJECT-TYPE
    SYNTAX       Unsigned32
    MAX-ACCESS   read-only
    STATUS       current
    DESCRIPTION
        "Near-end Packet Loss 15 Min Pm Timestamp"

    ::= { cyanY1731LMEntry 6 }

cyanY1731LMFe15MinPmCount OBJECT-TYPE
    SYNTAX       Unsigned32
    MAX-ACCESS   read-only
    STATUS       current
    DESCRIPTION
        "Far-end Packet Loss 15 Min Pm Count"

    ::= { cyanY1731LMEntry 7 }

cyanY1731LMFe15MinPmTimestamp OBJECT-TYPE
    SYNTAX       Unsigned32
    MAX-ACCESS   read-only
    STATUS       current
    DESCRIPTION
        "Far-end Packet Loss 15 Min Pm Timestamp"

    ::= { cyanY1731LMEntry 8 }

cyanY1731LMRatioNe15MinHighValue OBJECT-TYPE
    SYNTAX       Unsigned32 -- Float value * 1000
    MAX-ACCESS   read-only
    STATUS       current
    DESCRIPTION
        "Near-end Packet Loss Ratio 15 Min High Value"

    ::= { cyanY1731LMEntry 9 }

cyanY1731LMRatioNe15MinLowValue OBJECT-TYPE
    SYNTAX       Unsigned32 -- Float value * 1000
    MAX-ACCESS   read-only
    STATUS       current
    DESCRIPTION
        "Near-end Packet Loss Ratio 15 Min Low Value"

    ::= { cyanY1731LMEntry 10 }

cyanY1731LMRatioNe15MinAvgValue OBJECT-TYPE
    SYNTAX       Unsigned32 -- Float value * 1000
    MAX-ACCESS   read-only
    STATUS       current
    DESCRIPTION
        "Near-end Packet Loss Ratio 15 Min Avg Value"

    ::= { cyanY1731LMEntry 11 }

cyanY1731LMRatioNe15MinTimestamp OBJECT-TYPE
    SYNTAX       Unsigned32
    MAX-ACCESS   read-only
    STATUS       current
    DESCRIPTION
        "Near-end Packet Loss Ratio 15 Min Timestamp"

    ::= { cyanY1731LMEntry 12 }

cyanY1731LMRatioFe15MinHighValue OBJECT-TYPE
    SYNTAX       Unsigned32 -- Float value * 1000
    MAX-ACCESS   read-only
    STATUS       current
    DESCRIPTION
        "Far-end Packet Loss Ratio 15 Min High Value"

    ::= { cyanY1731LMEntry 13 }

cyanY1731LMRatioFe15MinLowValue OBJECT-TYPE
    SYNTAX       Unsigned32 -- Float value * 1000
    MAX-ACCESS   read-only
    STATUS       current
    DESCRIPTION
        "Far-end Packet Loss Ratio 15 Min Low Value"

    ::= { cyanY1731LMEntry 14 }

cyanY1731LMRatioFe15MinAvgValue OBJECT-TYPE
    SYNTAX       Unsigned32 -- Float value * 1000
    MAX-ACCESS   read-only
    STATUS       current
    DESCRIPTION
        "Far-end Packet Loss Ratio 15 Min Avg Value"

    ::= { cyanY1731LMEntry 15 }

cyanY1731LMRatioFe15MinTimestamp OBJECT-TYPE
    SYNTAX       Unsigned32
    MAX-ACCESS   read-only
    STATUS       current
    DESCRIPTION
        "Far-end Packet Loss Ratio 15 Min Timestamp"

    ::= { cyanY1731LMEntry 16 }

-- *****************************************************************************
-- CYAN Y1731 MEP Delay Measurement (DM) Table
-- *****************************************************************************

cyanY1731DMTable    OBJECT-TYPE
    SYNTAX        SEQUENCE OF CyanY1731DMEntry
    MAX-ACCESS    not-accessible
    STATUS        current
    DESCRIPTION
        "A list of Y1731 Packet Delay Mesurement(DM) Current Entries.
        Each row in this table represents last completed Delay Measurement (DM)
        for a given MEP. Only the last completed historical bucket is supported.
        The value of cyanY1731DMMepIndex is always 1 and
        this represents last completed historical bucket.
        "
    ::= { cyanY1731MibObjects 3 }

cyanY1731DMEntry    OBJECT-TYPE
    SYNTAX        CyanY1731DMEntry
    MAX-ACCESS    not-accessible
    STATUS        current
    DESCRIPTION
        "An entry of Y1731 Delay Measurement."
    INDEX {
        cyanY1731DMShelfId,
        cyanY1731DMModuleId,
        cyanY1731DMMepId,
        cyanY1731DMMepIndex
    }
    ::= { cyanY1731DMTable 1 }

CyanY1731DMEntry  ::=
    SEQUENCE {
        cyanY1731DMShelfId                          Unsigned32,
        cyanY1731DMModuleId                         Unsigned32,
        cyanY1731DMMepId                            Unsigned32,
        cyanY1731DMMepIndex                         Unsigned32,

        cyanY1731DMTwoWayDelay15MinHighValue        Unsigned32,
        cyanY1731DMTwoWayDelay15MinLowValue         Unsigned32,
        cyanY1731DMTwoWayDelay15MinAvgValue         Unsigned32,
        cyanY1731DMTwoWayDelay15MinTimestamp        Unsigned32,

        cyanY1731DMTwoWayDelayVar15MinHighValue     Unsigned32,
        cyanY1731DMTwoWayDelayVar15MinLowValue      Unsigned32,
        cyanY1731DMTwoWayDelayVar15MinAvgValue      Unsigned32,
        cyanY1731DMTwoWayDelayVar15MinTimestamp     Unsigned32
    }

cyanY1731DMShelfId OBJECT-TYPE
    SYNTAX       Unsigned32 (0..255)
    MAX-ACCESS   not-accessible
    STATUS       current
    DESCRIPTION
        "Shelf Id"

    ::= { cyanY1731DMEntry 1 }

cyanY1731DMModuleId OBJECT-TYPE
    SYNTAX       Unsigned32
    MAX-ACCESS   not-accessible
    STATUS       current
    DESCRIPTION
        "Module Id"

    ::= { cyanY1731DMEntry 2 }

cyanY1731DMMepId OBJECT-TYPE
    SYNTAX       Unsigned32
    MAX-ACCESS   not-accessible
    STATUS       current
    DESCRIPTION
        "MEP Id"

    ::= { cyanY1731DMEntry 3 }

cyanY1731DMMepIndex OBJECT-TYPE
    SYNTAX          Unsigned32
    MAX-ACCESS      not-accessible
    STATUS          current
    DESCRIPTION
        "Y1731 DM MEP Bucket Index. Currently only
        one bucket is supported with possible value of 1.
        Value 1 means that it is the latest historical bucket"

    ::= { cyanY1731DMEntry 4 }

cyanY1731DMTwoWayDelay15MinHighValue OBJECT-TYPE
    SYNTAX       Unsigned32 -- Float value * 1000
    MAX-ACCESS   read-only
    STATUS       current
    DESCRIPTION
        "Two-way Delay (micro-secs) 15 Min High Value "

    ::= { cyanY1731DMEntry 5 }

cyanY1731DMTwoWayDelay15MinLowValue OBJECT-TYPE
    SYNTAX       Unsigned32 -- Float value * 1000
    MAX-ACCESS   read-only
    STATUS       current
    DESCRIPTION
        "Two-way Delay (micro-secs) 15 Min Low Value "

    ::= { cyanY1731DMEntry 6 }

cyanY1731DMTwoWayDelay15MinAvgValue OBJECT-TYPE
    SYNTAX       Unsigned32 -- Float value * 1000
    MAX-ACCESS   read-only
    STATUS       current
    DESCRIPTION
        "Two-way Delay (micro-secs) 15 Min Avg Value "

    ::= { cyanY1731DMEntry 7 }

cyanY1731DMTwoWayDelay15MinTimestamp OBJECT-TYPE
    SYNTAX       Unsigned32
    MAX-ACCESS   read-only
    STATUS       current
    DESCRIPTION
        "Two-way Delay (micro-secs) 15 Min Time-stamp "

    ::= { cyanY1731DMEntry 8 }

cyanY1731DMTwoWayDelayVar15MinHighValue OBJECT-TYPE
    SYNTAX       Unsigned32 -- Float value * 1000
    MAX-ACCESS   read-only
    STATUS       current
    DESCRIPTION
        "Two-way Delay Var (micro-secs) 15 Min High Value "

    ::= { cyanY1731DMEntry 9 }

cyanY1731DMTwoWayDelayVar15MinLowValue OBJECT-TYPE
    SYNTAX       Unsigned32 -- Float value * 1000
    MAX-ACCESS   read-only
    STATUS       current
    DESCRIPTION
        "Two-way Delay Var (micro-secs) 15 Min Low Value "

    ::= { cyanY1731DMEntry 10 }

cyanY1731DMTwoWayDelayVar15MinAvgValue OBJECT-TYPE
    SYNTAX       Unsigned32 -- Float value * 1000
    MAX-ACCESS   read-only
    STATUS       current
    DESCRIPTION
        "Two-way Delay Var (micro-secs) 15 Min Avg Value "

    ::= { cyanY1731DMEntry 11 }

cyanY1731DMTwoWayDelayVar15MinTimestamp OBJECT-TYPE
    SYNTAX       Unsigned32
    MAX-ACCESS   read-only
    STATUS       current
    DESCRIPTION
        "Two-way Delay Var (micro-secs) 15 Min Time-stamp "

    ::= { cyanY1731DMEntry 12 }


-- ******************************************************************
-- CYAN Y1731 MIB Module Compliance statements
-- ******************************************************************
cyanY1731MepConfigObjectGroup OBJECT-GROUP
    OBJECTS {
        cyanY1731MepConfigLMTxInterval,
        cyanY1731MepConfigDMTxInterval,
        cyanY1731MepConfigPmEnabled,
        cyanY1731MepConfigOneWayLossEnabled,
        cyanY1731MepConfigTwoWayDelayEnabled,
        cyanY1731MepConfigTwoWayJitterEnabled
    }

    STATUS current
    DESCRIPTION        "Group of objects that comes with cyanY1731Config module"
    ::= {cyanY1731Module 100}



cyanY1731MepConfigCompliance MODULE-COMPLIANCE
    STATUS current
    DESCRIPTION
        "The basic info needed to be a cyan cyanY1731Config"
    MODULE
    MANDATORY-GROUPS {
        cyanY1731MepConfigObjectGroup
    }
    ::= { cyanY1731Module 101 }


cyanY1731LMObjectGroup OBJECT-GROUP
    OBJECTS {

        cyanY1731LMNe15MinPmCount,
        cyanY1731LMNe15MinPmTimestamp,

        cyanY1731LMFe15MinPmCount,
        cyanY1731LMFe15MinPmTimestamp,

        cyanY1731LMRatioNe15MinHighValue,
        cyanY1731LMRatioNe15MinLowValue,
        cyanY1731LMRatioNe15MinAvgValue,
        cyanY1731LMRatioNe15MinTimestamp,

        cyanY1731LMRatioFe15MinHighValue,
        cyanY1731LMRatioFe15MinLowValue,
        cyanY1731LMRatioFe15MinAvgValue,
        cyanY1731LMRatioFe15MinTimestamp
    }

    STATUS current
    DESCRIPTION        "Group of objects that comes with cyanY1731LM module"
    ::= {cyanY1731Module 102}



cyanY1731LMCompliance MODULE-COMPLIANCE
    STATUS current
    DESCRIPTION
        "The basic info needed to be a cyan cyanY1731LM"
    MODULE
    MANDATORY-GROUPS {
        cyanY1731LMObjectGroup
    }
    ::= { cyanY1731Module 103 }

cyanY1731DMObjectGroup OBJECT-GROUP
    OBJECTS {

        cyanY1731DMTwoWayDelay15MinHighValue,
        cyanY1731DMTwoWayDelay15MinLowValue,
        cyanY1731DMTwoWayDelay15MinAvgValue,
        cyanY1731DMTwoWayDelay15MinTimestamp,

        cyanY1731DMTwoWayDelayVar15MinHighValue,
        cyanY1731DMTwoWayDelayVar15MinLowValue,
        cyanY1731DMTwoWayDelayVar15MinAvgValue,
        cyanY1731DMTwoWayDelayVar15MinTimestamp
    }

    STATUS current
    DESCRIPTION        "Group of objects that comes with cyanY1731DM module"
    ::= {cyanY1731Module 104}



cyanY1731DMCompliance MODULE-COMPLIANCE
    STATUS current
    DESCRIPTION
        "The basic info needed to be a cyan cyanY1731DM"
    MODULE
    MANDATORY-GROUPS {
        cyanY1731DMObjectGroup
    }
    ::= { cyanY1731Module 105 }


END
