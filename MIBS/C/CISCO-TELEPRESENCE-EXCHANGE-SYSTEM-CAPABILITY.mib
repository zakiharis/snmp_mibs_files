-- *****************************************************************
-- CISCO-TELEPRESENCE-EXCHANGE-SYSTEM-CAPABILITY.my
--   
-- Aug 2012, Tim Evens
--   
-- Copyright (c) 2006-2013 by cisco Systems Inc.
-- All rights reserved.
--   
-- *****************************************************************

CISCO-TELEPRESENCE-EXCHANGE-SYSTEM-CAPABILITY DEFINITIONS ::= BEGIN

IMPORTS
    MODULE-IDENTITY
        FROM SNMPv2-SMI
    AGENT-CAPABILITIES
        FROM SNMPv2-CONF
    ciscoAgentCapability
        FROM CISCO-SMI;


ciscoTelepresenceExchangeSystemCapability MODULE-IDENTITY
    LAST-UPDATED    "201304150000Z"
    ORGANIZATION    "Cisco Systems, Inc."
    CONTACT-INFO
            "Cisco Systems
            Customer Service

            Postal: 170 W Tasman Drive
            San Jose, CA  95134
            USA

            Tel: +1 800 553-NETS

            E-mail: cs-txbu-snmp@cisco.com"
    DESCRIPTION
        "Agent capabilities for CISCO-TELEPRESENCE-EXCHANGE-SYSTEM-MIB"
    REVISION        "201304110000Z"
    DESCRIPTION
        "Added ciscoTelepresenceCapabilityCTXV130 capabilities for
        CISCO-TELEPRESENCE-EXCHANGE-SYSTEM-MIB"
    REVISION        "201208170000Z"
    DESCRIPTION
        "Initial version of this MIB module."
    ::= { ciscoAgentCapability 615 }



ciscoTelepresenceCapabilityCTXV120 AGENT-CAPABILITIES
    PRODUCT-RELEASE "OS=TELEPRESENCE EXCHANGE SYSTEM
                     OSVERSION=1.2.0
                     PLATFORM=TelePresence (TP)
                     INTERFACE=None"
    STATUS          current
    DESCRIPTION
        "TELEPRESENCE EXCHANGE SYSTEM MIB Capabilities"

    SUPPORTS        CISCO-TELEPRESENCE-EXCHANGE-SYSTEM-MIB
    INCLUDES        { ciscoTelepresenceExchangeSystemMIBConfigGroup }
    VARIATION       ctxMediaCapacityLargeMeeting
    DEFVAL          { false }
    DESCRIPTION
        "Large meeting capacity starting in CTX 1.2.0 has been
        deprecated.  This value will always return false(2)."

    ::= { ciscoTelepresenceExchangeSystemCapability 1 }

ciscoTelepresenceCapabilityCTXV130 AGENT-CAPABILITIES
    PRODUCT-RELEASE "OS=TELEPRESENCE EXCHANGE SYSTEM
                     OSVERSION=1.3.0
                     PLATFORM=TelePresence (TP)
                     INTERFACE=None"
    STATUS          current
    DESCRIPTION
        "TELEPRESENCE EXCHANGE SYSTEM MIB Capabilities"

    SUPPORTS        CISCO-TELEPRESENCE-EXCHANGE-SYSTEM-MIB
    INCLUDES        {
                        ciscoTelepresenceExchangeSystemMIBConfigGroup,
                        ciscoTelePresenceExchangeSystemMIBStatsGroup
                    }
    VARIATION       ctxMediaCapacityMaxPorts
    DEFVAL          { false }
    DESCRIPTION
        "This will return value as a multiple of 10. Querying agents
        should divide by 10 to interpret the value up to one decimal."

    VARIATION       ctxAllocActivePorts
    DEFVAL          { false }
    DESCRIPTION
        "This will return value as a multiple of 10. Querying agents
        should divide by 10 to interpret the value up to one decimal."

    VARIATION       ctxAllocAvailPorts
    DEFVAL          { false }
    DESCRIPTION
        "This will return value as a multiple of 10. Querying agents
        should divide by 10 to interpret the value up to one decimal."

    VARIATION       ctxAllocPoolActivePorts
    DEFVAL          { false }
    DESCRIPTION
        "This will return value as a multiple of 10. Querying agents
        should divide by 10 to interpret the value up to one decimal."

    VARIATION       ctxAllocPoolAvailPorts
    DEFVAL          { false }
    DESCRIPTION
        "This will return value as a multiple of 10. Querying agents
        should divide by 10 to interpret the value up to one decimal."

    VARIATION       ctxPeakHistAllocPorts
    DEFVAL          { false }
    DESCRIPTION
        "This will return value as a multiple of 10. Querying agents
        should divide by 10 to interpret the value up to one decimal."

    VARIATION       ctxPeakHistAllocPoolPorts
    DEFVAL          { false }
    DESCRIPTION
        "This will return value as a multiple of 10. Querying agents
        should divide by 10 to interpret the value up to one decimal."

    VARIATION       ctxOrganizationMaxPorts
    DEFVAL          { false }
    DESCRIPTION
        "This will return value as a multiple of 10. Querying agents
        should divide by 10 to interpret the value up to one decimal."

    ::= { ciscoTelepresenceExchangeSystemCapability 2 }

END
