-- *****************************************************************
-- CISCO-IMA-CAPABILITY
--
-- AGENT-CAPABILITIES mib for IMA-MIB in CISCO Products
--
-- August 2002, Wayne W. Cai
--
-- Copyright(c) 2002 by Cisco Systems,Inc.
-- All rights reserved.
--
-- *****************************************************************

CISCO-IMA-CAPABILITY DEFINITIONS ::= BEGIN

IMPORTS
        MODULE-IDENTITY
                FROM SNMPv2-SMI
        MilliSeconds
                FROM IMA-MIB
        AGENT-CAPABILITIES
                FROM SNMPv2-CONF
        ciscoAgentCapability
                FROM CISCO-SMI;

ciscoImaCapability MODULE-IDENTITY
        LAST-UPDATED    "200208150000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
DESCRIPTION
    "This file defines agent capabilities for IMA-MIB."

REVISION    "200208150000Z"
DESCRIPTION
    "Added ciscoImaAxsmeCapabilityV3R00 for 
     Enhanced ATM Switch Service Module(AXSM-E), and
     Enhanced Processor Switch Module 1(PXM1E) uplink."

REVISION    "200204290000Z"
DESCRIPTION
    "Initial version of this MIB module."

::= { ciscoAgentCapability  257 }


ciscoImaAxsmeCapabilityV3R00 AGENT-CAPABILITIES

PRODUCT-RELEASE "MGX8850 Release 3.0"
STATUS          current
DESCRIPTION     "IMA-MIB capabilities."

SUPPORTS        IMA-MIB
INCLUDES        { imaGroupGroup,
                  imaLinkGroup,
                  imaGroupIntervalGroup,
                  imaLinkIntervalGroup }

VARIATION       imaGroupNumber
ACCESS          not-implemented
DESCRIPTION     "Not Supported."

VARIATION       imaAlarmStatus
ACCESS          not-implemented
DESCRIPTION     "Not Supported."

VARIATION       imaAlarmType
ACCESS          not-implemented
DESCRIPTION     "Not Supported."

VARIATION       imaGroupSymmetry
SYNTAX          INTEGER { symmetricOperation(1) }
DESCRIPTION     "Agent only supports symmetricOperation(1).
                 asymmetricOperation(2) and asymmetricConfiguration(3)
                 are not supported."

VARIATION       imaGroupMinNumTxLinks
SYNTAX          INTEGER (1..16)
DESCRIPTION     "Supported with limitation.
                 Agent supports (1..16) instead of (1..32)."

VARIATION       imaGroupMinNumRxLinks
SYNTAX          INTEGER (1..16)
DESCRIPTION     "Supported with limitation.
                 Agent supports (1..16) instead of (1..32)."

VARIATION       imaGroupLastChange
ACCESS          not-implemented
DESCRIPTION     "Not Supported."

VARIATION       imaGroupTxFrameLength
DESCRIPTION     "Supported with limitation.
                 Agent supports all enums of m32, m64, m128, and m256
                 if the ima group is configured as version 1.1. 
                 But agent only support m128 if ima group is configured
                 as version 1.0."

VARIATION       imaGroupRxFrameLength
DESCRIPTION     "Supported with limitation.
                 Agent supports all enums of m32, m64, m128, and m256
                 if the ima group is configured as version 1.1. 
                 But agent only support m128 if ima group is configured
                 as version 1.0."

VARIATION       imaGroupDiffDelayMax
SYNTAX          MilliSeconds (1..275)
DESCRIPTION     "Supported with limitation.
                 Agent supports a range of
                 1 .. 275 for IMA group with T1 lines
                 1 .. 220 for IMA group with E1 lines."

VARIATION       imaGroupAlphaValue
SYNTAX          INTEGER (2..2)
ACCESS          read-only
DESCRIPTION     "Supported with limitation.
                 Agent only suports default value 2.
                 Agent doesn't support 1."

VARIATION       imaGroupBetaValue
SYNTAX          INTEGER (2..2)
ACCESS          read-only
DESCRIPTION     "Supported with limitation.
                 Agent only suports default value 2.
                 Agent doesn't support 1,3,4, and 5."
        
VARIATION       imaGroupGammaValue
SYNTAX          INTEGER (1..1)
ACCESS          read-only
DESCRIPTION     "Supported with limitation.
                 Agent only suports default value 1.
                 Agent doesn't support 2,3,4, and 5."

VARIATION       imaLinkCurrentNeTxNumFailures
ACCESS          not-implemented
DESCRIPTION     "Not Supported."

VARIATION       imaLinkCurrentNeRxNumFailures
ACCESS          not-implemented
DESCRIPTION     "Not Supported."

VARIATION       imaLinkCurrentFeTxNumFailures
ACCESS          not-implemented
DESCRIPTION     "Not Supported."

VARIATION       imaLinkCurrentFeRxNumFailures
ACCESS          not-implemented
DESCRIPTION     "Not Supported."

VARIATION       imaLinkIntervalNeTxNumFailures
ACCESS          not-implemented
DESCRIPTION     "Not Supported."

VARIATION       imaLinkIntervalNeRxNumFailures
ACCESS          not-implemented
DESCRIPTION     "Not Supported."

VARIATION       imaLinkIntervalFeTxNumFailures
ACCESS          not-implemented
DESCRIPTION     "Not Supported."

VARIATION       imaLinkIntervalFeRxNumFailures
ACCESS          not-implemented
DESCRIPTION     "Not Supported."

VARIATION       imaLinkTotalNeTxNumFailures
ACCESS          not-implemented
DESCRIPTION     "Not Supported."

VARIATION       imaLinkTotalNeRxNumFailures
ACCESS          not-implemented
DESCRIPTION     "Not Supported."

VARIATION       imaLinkTotalFeTxNumFailures
ACCESS          not-implemented
DESCRIPTION     "Not Supported."

VARIATION       imaLinkTotalFeRxNumFailures
ACCESS          not-implemented
DESCRIPTION     "Not Supported."

    ::= { ciscoImaCapability 1 }
END
