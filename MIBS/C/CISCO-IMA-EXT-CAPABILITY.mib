-- *****************************************************************
-- CISCO-IMA-EXT-CAPABILITY
--   
-- AGENT-CAPABILITIES mib for CISCO-IMA-MIB
--   
-- March 2002, Wayne W. Cai
-- Copyright(c) 2002-2006 by Cisco Systems,Inc.
--   

-- ****************************************************************

CISCO-IMA-EXT-CAPABILITY DEFINITIONS ::= BEGIN

IMPORTS
    MODULE-IDENTITY
        FROM SNMPv2-SMI
    AGENT-CAPABILITIES
        FROM SNMPv2-CONF
    MilliSeconds
        FROM IMA-MIB
    ciscoAgentCapability
        FROM CISCO-SMI;


ciscoImaExtCapability MODULE-IDENTITY
    LAST-UPDATED    "200611240000Z"
    ORGANIZATION    "Cisco Systems, Inc."
    CONTACT-INFO
            "Cisco Systems
            Customer Service

            Postal: 170 W Tasman Drive
            San Jose, CA  95134
            USA

            Tel: +1 800 553-NETS

            E-mail: cs-wanatm@cisco.com"
    DESCRIPTION     "Agent Capabilities for CISCO-IMA-MIB."
    REVISION        "200611240000Z"
    DESCRIPTION
        "Added ciscoImaExtCapabilityV12R05 for
        Cisco 2800, 3700 and 3800 Series Routers."
    REVISION        "200609260000Z"
    DESCRIPTION
        "Added ciscoImaExtAxsmeCapabilityV5R320 and
        ciscoImaExtCapabilityV5R320."
    REVISION        "200203040000Z"
    DESCRIPTION
        "Initial version of this MIB module."
          ::= { ciscoAgentCapability 524 }



ciscoImaExtAxsmeCapabilityV3R0 AGENT-CAPABILITIES
    PRODUCT-RELEASE "MGX8850 Release 3.0"
    STATUS          current
    DESCRIPTION
        "Agent capabilities for CISCO-IMA-MIB
        for AXSME Service Module in MGX8850 Series."

    SUPPORTS        CISCO-IMA-MIB
    INCLUDES        {
                        ciscoImaGroupGroup,
                        ciscoImaLinkGroup,
                        ciscoImaAlarmGroup,
                        ciscoImaLinkMappingGroup
                    }
    VARIATION       cimaGrpAlarmType
    ACCESS          not-implemented
    DESCRIPTION     "Not Supported."

    VARIATION       cimaLinkAlarmType
    ACCESS          not-implemented
    DESCRIPTION     "Not Supported."

    VARIATION       cimaStuffAndCellIndication
    DESCRIPTION
        "Supported with limitation.
        Agent only supports mandatory '000' and '001'
        stuff events."

    VARIATION       cimaGrpNumTxIcpCells
    ACCESS          not-implemented
    DESCRIPTION     "Not Supported."

    VARIATION       cimaGrpNumRxIcpCells
    ACCESS          not-implemented
    DESCRIPTION     "Not Supported."

    VARIATION       cimaGrpNumRxErrIcpCells
    ACCESS          not-implemented
    DESCRIPTION     "Not Supported."

    VARIATION       cimaGrpNumRxInvalidIcpCells
    ACCESS          not-implemented
    DESCRIPTION     "Not Supported."

    VARIATION       cimaGrpNumRxMissingIcpCells
    ACCESS          not-implemented
    DESCRIPTION     "Not Supported."

    VARIATION       cimaGrpNumTxMissingIcpCells
    ACCESS          not-implemented
    DESCRIPTION     "Not Supported."

    VARIATION       cimaLinkLifIntUpTime
    SYNTAX          MilliSeconds (2500..2500 )
    ACCESS          read-only
    DESCRIPTION
        "Supported with limitation.
        Agent only supports default 2500 milliseconds."

    VARIATION       cimaLinkLifIntDownTime
    SYNTAX          MilliSeconds (10000..10000 )
    ACCESS          read-only
    DESCRIPTION
        "Supported with limitation.
        Agent only supports default 10000 milliseconds."

    VARIATION       cimaLinkLodsIntUpTime
    SYNTAX          MilliSeconds (2500..2500 )
    ACCESS          read-only
    DESCRIPTION
        "Supported with limitation.
        Agent only supports default 2500 milliseconds."

    VARIATION       cimaLinkLodsIntDownTime
    SYNTAX          MilliSeconds (10000..10000 )
    ACCESS          read-only
    DESCRIPTION
        "Supported with limitation.
        Agent only supports default 10000 milliseconds."

    VARIATION       cimaLinkNumTxIcpCells
    ACCESS          not-implemented
    DESCRIPTION     "Not Supported."

    VARIATION       cimaLinkNumRxErrIcpCells
    ACCESS          not-implemented
    DESCRIPTION     "Not Supported."

    VARIATION       cimaLinkNumRxInvalidIcpCells
    ACCESS          not-implemented
    DESCRIPTION     "Not Supported."

    VARIATION       cimaLinkNumRxMissingIcpCells
    ACCESS          not-implemented
    DESCRIPTION     "Not Supported."

    VARIATION       cimaLinkNumTxMissingIcpCells
    ACCESS          not-implemented
    DESCRIPTION     "Not Supported."

    ::= { ciscoImaExtCapability 1 }

ciscoImaExtAxsmeCapabilityV5R320 AGENT-CAPABILITIES
    PRODUCT-RELEASE "MGX8850 Release 5.3.20"
    STATUS          current
    DESCRIPTION
        "Agent capabilities for CISCO-IMA-MIB
        for AXSME Service Module in MGX8850 Series."

    SUPPORTS        CISCO-IMA-MIB
    INCLUDES        {
                        ciscoImaGroupGroup,
                        ciscoImaLinkGroup,
                        ciscoImaAlarmGroup,
                        ciscoImaLinkMappingGroup
                    }
    VARIATION       cimaGrpAlarmType
    ACCESS          not-implemented
    DESCRIPTION     "Not Supported."

    VARIATION       cimaLinkAlarmType
    ACCESS          not-implemented
    DESCRIPTION     "Not Supported."

    VARIATION       cimaStuffAndCellIndication
    DESCRIPTION
        "Supported with limitation.
        Agent only supports mandatory '000' and '001'
        stuff events."

    VARIATION       cimaGrpNumTxIcpCells
    ACCESS          not-implemented
    DESCRIPTION     "Not Supported."

    VARIATION       cimaGrpNumRxIcpCells
    ACCESS          not-implemented
    DESCRIPTION     "Not Supported."

    VARIATION       cimaGrpNumRxErrIcpCells
    ACCESS          not-implemented
    DESCRIPTION     "Not Supported."

    VARIATION       cimaGrpNumRxInvalidIcpCells
    ACCESS          not-implemented
    DESCRIPTION     "Not Supported."

    VARIATION       cimaGrpNumRxMissingIcpCells
    ACCESS          not-implemented
    DESCRIPTION     "Not Supported."

    VARIATION       cimaGrpNumTxMissingIcpCells
    ACCESS          not-implemented
    DESCRIPTION     "Not Supported."

    VARIATION       cimaLinkLifIntUpTime
    SYNTAX          MilliSeconds (2500..2500 )
    ACCESS          read-only
    DESCRIPTION
        "Supported with limitation.
        Agent only supports default 2500 milliseconds."

    VARIATION       cimaLinkLifIntDownTime
    SYNTAX          MilliSeconds (10000..10000 )
    ACCESS          read-only
    DESCRIPTION
        "Supported with limitation.
        Agent only supports default 10000 milliseconds."

    VARIATION       cimaLinkLodsIntUpTime
    SYNTAX          MilliSeconds (2500..2500 )
    ACCESS          read-only
    DESCRIPTION
        "Supported with limitation.
        Agent only supports default 2500 milliseconds."

    VARIATION       cimaLinkLodsIntDownTime
    SYNTAX          MilliSeconds (10000..10000 )
    ACCESS          read-only
    DESCRIPTION
        "Supported with limitation.
        Agent only supports default 10000 milliseconds."

    VARIATION       cimaLinkNumTxIcpCells
    ACCESS          not-implemented
    DESCRIPTION     "Not Supported."

    VARIATION       cimaLinkNumRxErrIcpCells
    ACCESS          not-implemented
    DESCRIPTION     "Not Supported."

    VARIATION       cimaLinkNumRxInvalidIcpCells
    ACCESS          not-implemented
    DESCRIPTION     "Not Supported."

    VARIATION       cimaLinkNumRxMissingIcpCells
    ACCESS          not-implemented
    DESCRIPTION     "Not Supported."

    VARIATION       cimaLinkNumTxMissingIcpCells
    ACCESS          not-implemented
    DESCRIPTION     "Not Supported."

    VARIATION       cimaGrpIntegrationUpTime
    DEFVAL          { 0 }
    DESCRIPTION     "The default value is 0."

    VARIATION       cimaGrpIntegrationDownTime
    DEFVAL          { 4000 }
    DESCRIPTION     "The default value is 4000."

    ::= { ciscoImaExtCapability 2 }

ciscoImaExtCapabilityV5R320 AGENT-CAPABILITIES
    PRODUCT-RELEASE "MGX8950  and MGX8850 Release 5.3.20"
    STATUS          current
    DESCRIPTION
        "CISCO-IMA-MIB Capabilities for Service Module:
        MPSM155,MPSM16T1E1 and Processor Switch Module
        Enhanced (PXM1E) controller card."

    SUPPORTS        CISCO-IMA-MIB
    INCLUDES        { ciscoImaGroupGroup }
    VARIATION       cimaGrpIntegrationUpTime
    DEFVAL          { 0 }
    DESCRIPTION     "The default value is 0."

    VARIATION       cimaGrpIntegrationDownTime
    DEFVAL          { 4000 }
    DESCRIPTION     "The default value is 4000."

    ::= { ciscoImaExtCapability 3 }

ciscoImaExtCapabilityV12R05 AGENT-CAPABILITIES
    PRODUCT-RELEASE "IOS 12.5 for Cisco Access Routers and ISRs"
    STATUS          current
    DESCRIPTION
        "Agent capabilities for Cisco 3700 Series Access
        Routers and 2800, 3800 Series Integrated Services Routers."

    SUPPORTS        CISCO-IMA-MIB
    INCLUDES        { ciscoImaLinkMappingGroup }
    ::= { ciscoImaExtCapability 4 }

END
