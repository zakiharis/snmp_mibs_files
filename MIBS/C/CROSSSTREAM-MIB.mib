CROSSSTREAM-MIB DEFINITIONS ::= BEGIN

-- Title:     ARTEL CROSS STREAM MIB
-- Date:      Dec 6,1999
-- Author:    Viridien Technologies Inc.

IMPORTS
    enterprises, IpAddress
        FROM RFC1155-SMI
    OBJECT-TYPE
        FROM RFC-1212
    TRAP-TYPE
	FROM RFC-1215
    DisplayString, ifIndex
        FROM RFC1213-MIB;

    artel	OBJECT IDENTIFIER ::= { enterprises 4962 }

    -- List of MIB groups common to all products
    common	OBJECT IDENTIFIER ::= { artel  1 }

    -- device group contains product name, version information.
    device	OBJECT IDENTIFIER ::= { common 1 }
    
    -- Each product has a node under this subtree.
    products     OBJECT IDENTIFIER ::= { artel  2 }
    
    -- Cross Stream specific Objects
    crossStream     OBJECT IDENTIFIER ::= { products 1 }

    -- Cross Stream Control Group
    cstrmControl  OBJECT IDENTIFIER ::= { crossStream 1 }

    -- Cross Stream Statistics Group
    cstrmInfo OBJECT IDENTIFIER ::= { crossStream 2 }

    -- Cross Stream Events, Traps & Alarms Group
    cstrmEvents   OBJECT IDENTIFIER ::= { crossStream 3 }

    -- Cross Stream Diagnostics Group
    cstrmDiags    OBJECT IDENTIFIER ::= { crossStream 4 }

    -- Cross Streams group
    cstrmStreamGroup      OBJECT IDENTIFIER ::= { crossStream 5 }

    -- Cross Streams private
    cstrmStreamPrivate      OBJECT IDENTIFIER ::= { crossStream 6 }

    -- textual conventions..

    -- Identical to RowStatus textual convention.
    ConnectionStatus ::= INTEGER
                    {  
		    -- the following values may be read or written
		    active(1),
		    inactive(2),

		    -- this value may be read, but not written. 
		    underCreation(3),

		    -- the following values may be written, but are
		    -- never read.
		    createAndGo(4),
		    createAndWait(5),
		    delete(6)
		    }
	-- The status of a connection entry
	--
        -- Setting this object to the value "createAndGo" or "createAndWait"
	-- makes a new entry. An existing instance of an object cannot be 
	-- set to "createAndGo" or "createAndWait" state. Immediately after 
	-- completing the create operation, agent must set this object to 
	-- "underCreation"

        -- When in "underCreation" state, the entry is partial and will
        -- be in inconsistent state and the following multiple PDUs will
        -- modify the connection information. Entries will exist in 
        -- "underCreation" state until the management station is finished
	-- configuring the entry and sets this object to "active" or 
        -- "inactive".

	-- Setting an entry to "createAndGo" by a management station
	-- creates a new entry and agent updates the state to active.

	-- Setting an entry to "createAndWait" creates a new entry, but
	-- the entry is not available immediately to be managed. The management
        -- station has to fill all the columns and set the state to "active"

        -- Setting an entry to "inactive" temporarily inactivates the
        -- entry but is available for activating again.

	-- Setting an entry to "delete" state will permanently delete this
        -- entry.

	-- Management stations must be prepared to receive
	-- connection tabular information from agents that corresponds
	-- to "inactive" entries. Proper interpretation of such entries
        -- require examination of the relevant ConnectionStatus object.

    StreamDirection ::= INTEGER
                    {  ingress(1),
		       egress(2)	
		    }
    
    StreamState ::=  INTEGER
                  {   active(1),
		      inactive(2)
                  }
		 
    -- Specifies the stream type.
    StreamType ::= INTEGER
                 {
		     atm(1), -- Stream is ATM 
		     asi(2),  -- Stream is ASI
		     ethernet(3) -- Stream is Ethernet
		 }


    StreamIndex ::=  INTEGER

    ProgIndex   ::=  INTEGER
    
    PidIndex    ::=  INTEGER

    ConnectionIndex ::= INTEGER

    -- the device Group
    -- Every Artel device implements this group

    deviceName OBJECT-TYPE
	SYNTAX	DisplayString (SIZE(0..127))
	ACCESS	read-only
	STATUS  mandatory
	DESCRIPTION
	    "Name of the Artel's Product"
	::= { device 1 }

    deviceSerialNum OBJECT-TYPE
	SYNTAX DisplayString
	ACCESS read-only
	STATUS mandatory
	DESCRIPTION
	    "Serial number of the device."
	::= { device 2 }

    deviceModelNum OBJECT-TYPE
	SYNTAX DisplayString
	ACCESS read-only
	STATUS mandatory
	DESCRIPTION
	    "Model Number of the device."
	::= { device 3 }

    deviceFwVer OBJECT-TYPE
	SYNTAX DisplayString
	ACCESS read-only
	STATUS mandatory
	DESCRIPTION
	    "Firmware version of the product in major.minor form"
        ::= { device 4 }

    deviceHwVer OBJECT-TYPE
	SYNTAX DisplayString
	ACCESS read-only
	STATUS mandatory
	DESCRIPTION
	    "Hardware version of the product in major.minor form"
        ::= { device 5 }

    deviceTime OBJECT-TYPE
	SYNTAX DisplayString (SIZE(12))
	ACCESS read-write
	STATUS mandatory
	DESCRIPTION
	    "The current time as measured by the device.
	     The time is specified as YYYYMMDDHHMM,
	     where
	     YYYY - four digits of the year
	     MM   - month (01 through 12)
	     DD   - day of month(01 through 31)
	     HH   - hours(00 through 23)
	     MM   - minutes(00 through 59)"
	::= { device 6 }

    deviceUpTime OBJECT-TYPE
	SYNTAX DisplayString (SIZE(12))
	ACCESS read-only
	STATUS mandatory
	DESCRIPTION
	    "The time when the device is intialized.
	     The time is specified as YYYYMMDDHHMM,
	     where
	     YYYY - four digits of the year
	     MM   - month (01 through 12)
	     DD   - day of month(01 through 31)
	     HH   - hours(00 through 23)
	     MM   - minutes(00 through 59)."
	::= { device 7 }

    deviceIpAddress OBJECT-TYPE
	SYNTAX  IpAddress
	ACCESS  read-write
	STATUS  mandatory
	DESCRIPTION
	    "This object returns the current IP address of the device when
	    read and modifies the IP address to the new value when set."
	::= { device 8 }

    deviceIpNetmask OBJECT-TYPE
	SYNTAX  IpAddress
	ACCESS  read-write
	STATUS  mandatory
	DESCRIPTION
	    "This object returns the netmask of the interface when read
	    and modifies the netmask when set."
	::= { device 9 }

    deviceGwAddress OBJECT-TYPE
	SYNTAX  IpAddress
	ACCESS  read-write
	STATUS  mandatory
	DESCRIPTION
	    "This object returns the default gateway address of the device
	    when read and modifies the default gateway when set."
	::= { device 10 }

    deviceHostAddress OBJECT-TYPE
	SYNTAX  IpAddress
	ACCESS  read-write
	STATUS  mandatory
	DESCRIPTION
	    "This object has the host (TFTP) server ip address which
	    is used for software upgrade."
	::= { device 11 }

    deviceReset OBJECT-TYPE
	SYNTAX  INTEGER
	ACCESS  read-write
	STATUS  mandatory
	DESCRIPTION
	    "Always returns '0' when read and resets the device
	    when set with a nonzero value"
        ::= { device 12 }

    -- the Cross Stream Control Group
    vsarReset   OBJECT-TYPE
	SYNTAX  INTEGER
	ACCESS  read-write
	STATUS  mandatory
	DESCRIPTION
	    "Setting this object to 1 resets the VSAR chip and initializes
	    the VSAR control structures by reading from NVRAM."
	::= { cstrmControl 1 }

    vsarConfigTable  OBJECT-TYPE
	SYNTAX  SEQUENCE OF VsarConfigEntry
	ACCESS  not-accessible
	STATUS  mandatory
	DESCRIPTION
	    "This table contains a list of configuration entries which can
	    be loaded to VSAR chip or store current configuration to non 
	    volatile memory."
	::= { cstrmControl 2 }

    vsarConfigEntry  OBJECT-TYPE
	SYNTAX  VsarConfigEntry
	ACCESS  not-accessible
	STATUS  mandatory
	DESCRIPTION
	    "This entry contains configurationType, action specifying load/
	    store."
	INDEX   { vsarConfigIndex }
	::= { vsarConfigTable 1 }

    VsarConfigEntry ::= SEQUENCE  {
          vsarConfigIndex
	     INTEGER,
	  vsarConfigType
	     INTEGER,
	  vsarConfigAction
	     INTEGER
       }

    vsarConfigIndex OBJECT-TYPE
	SYNTAX  INTEGER
	ACCESS  read-only
	STATUS  mandatory
	DESCRIPTION
	    "The index which points to the different VSAR configurations."
	::= { vsarConfigEntry 1 }

    vsarConfigType  OBJECT-TYPE
	SYNTAX  INTEGER
	ACCESS  read-only  
	STATUS  mandatory
	DESCRIPTION
	    "Configuration type can specify NVRAM configuration, Flash
	    configuration etc."
	::= { vsarConfigEntry 2 }

    vsarConfigAction OBJECT-TYPE
	SYNTAX  INTEGER {
                    load(1),   --- load the configuration to the device.
		    store(2)   --- store the configuration from the device.
		}
	ACCESS  read-write
	STATUS  mandatory
	DESCRIPTION
	    "This specifies the action to be peformed on the configuration 
	    entry. When set is given with 'load' as action the device is
	    loaded with the specified configuration type. If a set is given
	    with 'store' as action, current configuration of the device is
	    stored in the specified configuartion type."
	::= { vsarConfigEntry 4 }

    -- the cstrmInfo Group

    usedAtmStreamsNumber   OBJECT-TYPE
	SYNTAX  INTEGER
	ACCESS  read-only
	STATUS  mandatory
	DESCRIPTION
	    "Currently used number of total available Tranport
	    streams. This includes active and inactive streams"
	::= { cstrmInfo 1 }
    
    activeAtmStreamsNumber OBJECT-TYPE
	SYNTAX  INTEGER
	ACCESS  read-only
	STATUS  mandatory
	DESCRIPTION
	    "Active Number of Transport Streams running in the 
	    system"
	::= { cstrmInfo 2 }
    
    maxAtmStreamsNumber   OBJECT-TYPE
	SYNTAX  INTEGER
	ACCESS  read-only
	STATUS  mandatory
	DESCRIPTION
	    "Max number of available Transport Streams available
	    in the system"
	::= { cstrmInfo 3 }
    
    usedAsiStreamsNumber   OBJECT-TYPE
	SYNTAX  INTEGER
	ACCESS  read-only
	STATUS  mandatory
	DESCRIPTION
	    "Currently used number of total available ASI Tranport
	    streams. This includes active and inactive streams"
	::= { cstrmInfo 4 }
    
    activeAsiStreamsNumber OBJECT-TYPE
	SYNTAX  INTEGER
	ACCESS  read-only
	STATUS  mandatory
	DESCRIPTION
	    "Active Number of ASI Transport Streams running in the 
	    system"
	::= { cstrmInfo 5 }
    
    maxAsiStreamsNumber   OBJECT-TYPE
	SYNTAX  INTEGER
	ACCESS  read-only
	STATUS  mandatory
	DESCRIPTION
	    "Max number of available ASI Transport Streams available
	    in the system"
	::= { cstrmInfo  6 }
    
    usedProgsNumber  OBJECT-TYPE
	SYNTAX  INTEGER
	ACCESS  read-only
	STATUS  mandatory
	DESCRIPTION
	    "Currently used number of programs. This includes
	    active and inactive programs"
	::= { cstrmInfo 7 }
    
    activeProgsNumber OBJECT-TYPE
	SYNTAX  INTEGER
	ACCESS  read-only
	STATUS  mandatory
	DESCRIPTION
	    "Active number of programs running in the system"
	::= { cstrmInfo 8 }
    
    maxProgsNumber  OBJECT-TYPE
	SYNTAX  INTEGER
	ACCESS  read-only
	STATUS  mandatory
	DESCRIPTION
	    "Max number of programs available in the system"
	::= { cstrmInfo 9 }
    
    usedPidsNumber   OBJECT-TYPE
	SYNTAX  INTEGER
	ACCESS  read-only
	STATUS  mandatory
	DESCRIPTION
	    "Currently used number of total available PIDs. This
	    includes active and inactive PIDs"
	::= { cstrmInfo 10 }
    
    activePidsNumber OBJECT-TYPE
	SYNTAX  INTEGER
	ACCESS  read-only
	STATUS  mandatory
	DESCRIPTION
	    "Active number of PIDs running in the system"
	::= { cstrmInfo 11 }
    
    maxPidsNumber  OBJECT-TYPE
	SYNTAX  INTEGER
	ACCESS  read-only
	STATUS  mandatory
	DESCRIPTION
	    "Max number of available PIDs in the system"
	::= { cstrmInfo 12 }

    usedConnectionsNumber   OBJECT-TYPE
	SYNTAX  INTEGER
	ACCESS  read-only
	STATUS  mandatory
	DESCRIPTION
	    "Currently used number of total available connection objects."
	::= { cstrmInfo 13 }
    
    maxConnectionsNumber   OBJECT-TYPE
	SYNTAX  INTEGER
	ACCESS  read-only
	STATUS  mandatory
	DESCRIPTION
	    "Max number of available connection objects."
	::= { cstrmInfo   14 }

--
-- cstrmEvents group.  Diagnostic data is defined here.
--

    cstrmATMPhyTrapID   OBJECT-TYPE
	SYNTAX  INTEGER
	ACCESS  not-accessible
	STATUS  mandatory
	DESCRIPTION
	    ""
	::= { cstrmStreamPrivate   1 }

    cstrmATMPhyTrapStatus   OBJECT-TYPE
	SYNTAX  INTEGER
	ACCESS  not-accessible
	STATUS  mandatory
	DESCRIPTION
	    ""
	::= { cstrmATMPhyTrapID   1 }

    cstrmOAMVCTrapID   OBJECT-TYPE
	SYNTAX  INTEGER
	ACCESS  not-accessible
	STATUS  mandatory
	DESCRIPTION
	    ""
	::= { cstrmStreamPrivate   2 }

    cstrmOAMVCTrapStatus   OBJECT-TYPE
	SYNTAX  INTEGER
	ACCESS  not-accessible
	STATUS  mandatory
	DESCRIPTION
	    ""
	::= { cstrmOAMVCTrapID   1 }

    cstrmOAMVPTrapID   OBJECT-TYPE
	SYNTAX  INTEGER
	ACCESS  not-accessible
	STATUS  mandatory
	DESCRIPTION
	    ""
	::= { cstrmStreamPrivate   3 }

    cstrmOAMVPTrapStatus   OBJECT-TYPE
	SYNTAX  INTEGER
	ACCESS  not-accessible
	STATUS  mandatory
	DESCRIPTION
	    ""
	::= { cstrmOAMVPTrapID   1 }
	 
	cstrmSONETTrapID   OBJECT-TYPE
	SYNTAX  INTEGER
	ACCESS  not-accessible
	STATUS  mandatory
	DESCRIPTION
	    ""
	::= { cstrmStreamPrivate   4 }

	cstrmSONETTrapStatus   OBJECT-TYPE
	SYNTAX  INTEGER
	ACCESS  not-accessible
	STATUS  mandatory
	DESCRIPTION
	    ""
	::= { cstrmSONETTrapID   1 }

	cstrmActDeActTrapID   OBJECT-TYPE
	SYNTAX  INTEGER
	ACCESS  not-accessible
	STATUS  mandatory
	DESCRIPTION
	    ""
	::= { cstrmStreamPrivate   5 }

	cstrmActDeActTrapStatus   OBJECT-TYPE
	SYNTAX  INTEGER
	ACCESS  not-accessible
	STATUS  mandatory
	DESCRIPTION
	    ""
	::= { cstrmActDeActTrapID   1 }

	cstrmIngressPidsChangedTrapID	OBJECT-TYPE
	SYNTAX  INTEGER
	ACCESS  not-accessible
	STATUS  mandatory
	DESCRIPTION
	    ""
	::= { cstrmStreamPrivate   6 }

	cstrmIngressPidsChangedTrapStatus   OBJECT-TYPE
	SYNTAX  INTEGER
	ACCESS  not-accessible
	STATUS  mandatory
	DESCRIPTION
	    ""
	::= { cstrmIngressPidsChangedTrapID   1 }

    
--
-- cstrmDiags group.  Diagnostic data is defined here.
--

    cstrmAirTemp  OBJECT-TYPE
	SYNTAX    INTEGER
	ACCESS    read-only
	STATUS    mandatory
	DESCRIPTION
	    "The ambient temperature in degrees Centigrade at the center of
             the main logic board."
	::= { cstrmDiags 1 }

    cstrmCoreRegTemp  OBJECT-TYPE
	SYNTAX    INTEGER
	ACCESS    read-only
	STATUS    mandatory
	DESCRIPTION
	    "The case temperature in degrees Centigrade of the Core 5 volt
             voltage regulator I.C."
	::= { cstrmDiags 2 }

    cstrm3VRegTemp  OBJECT-TYPE
	SYNTAX    INTEGER
	ACCESS    read-only
	STATUS    mandatory
	DESCRIPTION
	    "The case temperature in degrees Centigrade of the 3.3 volt
             voltage regulator I.C."
	::= { cstrmDiags 3 }

    cstrmHotICTemp  OBJECT-TYPE
	SYNTAX    INTEGER
	ACCESS    read-only
	STATUS    mandatory
	DESCRIPTION
	    "The case temperature in degrees Centigrade of the designated
             hottest I.C. on the main board."
	::= { cstrmDiags 4 }

    cstrm5VCoreVoltage  OBJECT-TYPE
	SYNTAX    INTEGER
	ACCESS    read-only
	STATUS    mandatory
	DESCRIPTION
	    "The voltage in 1/100ths of a volt of the 5 volt core regulator."
	::= { cstrmDiags 5 }

    cstrm3VCoreVoltage  OBJECT-TYPE
	SYNTAX    INTEGER
	ACCESS    read-only
	STATUS    mandatory
	DESCRIPTION
	    "The voltage in 1/100ths of a volt of the 3.3 volt core regulator."
	::= { cstrmDiags 6 }

    cstrm3VIOVoltage  OBJECT-TYPE
	SYNTAX    INTEGER
	ACCESS    read-only
	STATUS    mandatory
	DESCRIPTION
	    "The voltage in 1/100ths of a volt of the 3.3 volt I/O regulator."
	::= { cstrmDiags 7 }

    -- the cstrmStream group

    -- When a stream is created, management station should specify the
    -- type of the stream (ATM/ASI) and also specify if ingress, egress
    -- or both directions are active.

    -- This group has tables to define streams, programs, pids and
    -- and connection tables which are used in multiplexing/demultiplexing
    -- streams, programs, pids.

    streamNextIndex  OBJECT-TYPE
	SYNTAX  INTEGER
	ACCESS  read-only
	STATUS  mandatory
	DESCRIPTION
	    "To create a new entry in streamTable, management station
	    has to first get this object value. The value 0 indicates
	    that no assigned values are available. After each retrieval
	    operation from management stations, agent should modify this to
	    next unassigned index."
	::= { cstrmStreamGroup 1 }

    streamTable  OBJECT-TYPE
	SYNTAX  SEQUENCE OF StreamEntry
	ACCESS  not-accessible
	STATUS  mandatory
	DESCRIPTION
	    "A list of stream entries.
	    An entry specifies the stream type, name and
	    direction. It doesn't included stream specific
	    parameters."
	::= { cstrmStreamGroup 2 }

    streamEntry OBJECT-TYPE
	SYNTAX  StreamEntry
	ACCESS  not-accessible
	STATUS  mandatory
	DESCRIPTION
	    "An entry in the stream table.
	    This entry is used to specify the stream type,
	    stream direction and stream status."
	INDEX   { streamIndex }
	::= { streamTable 1 }

    StreamEntry  ::= SEQUENCE  {
        streamIndex         INTEGER,
	ingressState        StreamState,
	egressState         StreamState,
	streamType          StreamType,
	streamName          DisplayString,
	streamStatus        ConnectionStatus
        }
    
    streamIndex   OBJECT-TYPE
	SYNTAX    INTEGER
        ACCESS    read-only
	STATUS    mandatory
	DESCRIPTION
	    "A unique integer handle that identifies a stream."
	::= { streamEntry 1 }

    ingressState    OBJECT-TYPE
	SYNTAX    StreamState
	ACCESS    read-write
	STATUS    mandatory
	DESCRIPTION
	    "This object specifies the status of the stream in ingress 
	    direction. The ingressState can be set to only 'inactive' by
	    the management station. It is automatically set to 'active'
	    by the agent when a valid connection is established."
	::= { streamEntry 2 }

    egressState    OBJECT-TYPE
	SYNTAX    StreamState
	ACCESS    read-write
	STATUS    mandatory
	DESCRIPTION
	    "This object specifies the status of the stream in egress 
	    direction."
	::= { streamEntry 3 }

    streamType  OBJECT-TYPE
	SYNTAX    StreamType
	ACCESS    read-write
	STATUS    mandatory
	DESCRIPTION
	    "This object specifies the type of the stream."
	::= { streamEntry 4 }

    streamName  OBJECT-TYPE
	SYNTAX    DisplayString
	ACCESS    read-write
	STATUS    mandatory
	DESCRIPTION
	    "This object specifies the name of the stream."
	::= { streamEntry 5 }
    
    streamStatus  OBJECT-TYPE
	SYNTAX    ConnectionStatus
	ACCESS    read-write
	STATUS    mandatory
	DESCRIPTION
	    "This object specifies the status of stream entry."
	::= { streamEntry 6 }

    --ingressStream Table
    ingressStreamTable  OBJECT-TYPE
	SYNTAX  SEQUENCE OF IngressStreamEntry
	ACCESS  not-accessible
	STATUS  mandatory
	DESCRIPTION
	    "This table contains ingress stream configuration parameters,
	    one entry per streamTable for which streamDirection is ingress."
	::= { cstrmStreamGroup 3 }

    ingressStreamEntry OBJECT-TYPE
	SYNTAX  IngressStreamEntry
	ACCESS  not-accessible
	STATUS  mandatory
	DESCRIPTION
	    "An ingress entry specifies the cell rate of the stream."
	INDEX  { streamIndex }
	::= { ingressStreamTable 1 }

    IngressStreamEntry ::= SEQUENCE {
        ingressStreamCellRate INTEGER
	}

    ingressStreamCellRate  OBJECT-TYPE
	SYNTAX      INTEGER
	ACCESS      read-write
	STATUS      mandatory
	DESCRIPTION
	    " Specifies the cellrate of the ingress stream."
	::= { ingressStreamEntry 1 }

    -- egressStream Table.
    
    egressStreamTable  OBJECT-TYPE
	SYNTAX   SEQUENCE OF EgressStreamEntry
	ACCESS   not-accessible
	STATUS   mandatory
	DESCRIPTION
	    "This table contains egress stream configuration parameters,
	    one entry per streamTable for which streamDirection is egress."
	::= { cstrmStreamGroup 4 }

    egressStreamEntry  OBJECT-TYPE
	SYNTAX  EgressStreamEntry
	ACCESS  not-accessible
	STATUS  mandatory
	DESCRIPTION
	    "An egress entry specifies the transport stream rate, buffer
	    control parameters, elasticity table parameters, divisor for
	    center rate of elasticity window."
	INDEX { streamIndex }
	::= { egressStreamTable 1 }

    EgressStreamEntry ::= SEQUENCE {
        egressStreamTsRate
	    INTEGER,
	egressStreamNumBufs
	    INTEGER,
	egressStreamBufThreshold
	    INTEGER,
        egressStreamBufSize
	    INTEGER,
	egressStreamJitter
	    INTEGER
	--- ELASTICITY TABLE parameters are to be added for next version.
	}

    egressStreamTsRate  OBJECT-TYPE
	SYNTAX   INTEGER
	ACCESS   read-write
	STATUS   mandatory
	DESCRIPTION
	    "Transport rate for this egress stream."
	::= { egressStreamEntry 1 }

    egressStreamNumBufs  OBJECT-TYPE
	SYNTAX   INTEGER
	ACCESS   read-write
	STATUS   mandatory
	DESCRIPTION
	    "Number of buffers to be allocated for this egress stream.
	    Setting this '0' to will deallocate the memory. Modify this 
	    value to change the number of buffers from current value."
	::= { egressStreamEntry 2}

    egressStreamBufThreshold  OBJECT-TYPE
	SYNTAX   INTEGER
        ACCESS   read-write
	STATUS   mandatory
	DESCRIPTION
	    "Specifies the uniform dealy threshold for this egress stream."
	::= { egressStreamEntry 3 }

    egressStreamBufSize   OBJECT-TYPE
	SYNTAX   INTEGER
	ACCESS   read-write
	STATUS   mandatory
	DESCRIPTION
	    "Size of each buffer allocated in egress pool."
	::= { egressStreamEntry 4 }

    egressStreamJitter    OBJECT-TYPE
	SYNTAX   INTEGER {
	           enable(1),  -- enable Jitter Attenuation.
		   disable(2)  -- disable Jitter Attenuation.
		 }
	ACCESS   read-write
	STATUS   mandatory
	DESCRIPTION
	    "Enable/disable Jitter Attenuation for this egress stream."
	::= { egressStreamEntry 5 }

    -- AtmStream table
    
    -- After a stream is specified in the streamTable, ATM specific
    -- parameters are set in this table.
    
    atmStreamTable OBJECT-TYPE
	SYNTAX SEQUENCE OF AtmStreamEntry
	ACCESS not-accessible
	STATUS mandatory
	DESCRIPTION
	    "This table contains ATM stream configuration parameters,
	    one entry per streamTable for which streamType is ATM."
	::= { cstrmStreamGroup 5 }
    
    atmStreamEntry OBJECT-TYPE
	SYNTAX  AtmStreamEntry
	ACCESS  not-accessible
	STATUS  mandatory
	DESCRIPTION
	    "An ATM Transport Stream entry contains vpi and vci"
	INDEX   { streamIndex }
	::= { atmStreamTable 1 }
    
    AtmStreamEntry ::= SEQUENCE  {
	  atmStreamVpi
	     INTEGER,
	  atmStreamVci
	     INTEGER
    }
    
    atmStreamVpi  OBJECT-TYPE
	SYNTAX INTEGER
	ACCESS read-write
	STATUS mandatory
	DESCRIPTION
	    " VPI associated with the ATM Stream"
	::= { atmStreamEntry 1 }
    
    atmStreamVci OBJECT-TYPE
	SYNTAX INTEGER
	ACCESS read-write
	STATUS mandatory
	DESCRIPTION
	    "VCI associated with the VCB."
	::= { atmStreamEntry 2 }
    
    -- AsiStream table
    
    -- After a stream is specified in the streamTable, ASI specific
    -- parameters are set in this table.

    asiStreamTable OBJECT-TYPE
	SYNTAX  SEQUENCE OF AsiStreamEntry
	ACCESS  not-accessible
	STATUS  mandatory
	DESCRIPTION
	    "This table contians ASI stream configuration parameters,
	    one entry per streamTable for which streamType is ASI."
	::= { cstrmStreamGroup 6}

    asiStreamEntry  OBJECT-TYPE
	SYNTAX  AsiStreamEntry
	ACCESS  not-accessible
	STATUS  mandatory
	DESCRIPTION
	    "An ASI Transport stream entry specifies the port number."
	INDEX  { streamIndex }
	::= { asiStreamTable 1 }

    AsiStreamEntry ::= SEQUENCE {
        asiStreamPort
	    INTEGER,
	asiStreamChannel
	    INTEGER
	}

    asiStreamPort  OBJECT-TYPE
	SYNTAX   INTEGER
	ACCESS   read-write
	STATUS   mandatory
	DESCRIPTION
	    "Physical port number of the ASI stream."
	::= { asiStreamEntry 1 }

    asiStreamChannel  OBJECT-TYPE
	SYNTAX   INTEGER
	ACCESS   read-write
	STATUS   mandatory
	DESCRIPTION
	    "Channel associated with this ASI stream."
	::= { asiStreamEntry 2 }

    -- Example to create an "ATM Ingress stream "
    -- 
    --   GET ( streamNextIndex.0 ) 
    --      Management station should get a  non-zero positive index which
    --      can be used as a stream handle. If a 'zero' is returned, it 
    --      denotes that stream table if full. 
    --      Let us give the name 'streamIndex' to the returned index.
    -- 
    --   SET ( streamType.<streamIndex> = 'atm')
    --   SET ( streamName.<streamIndex> = "VPI/VCI 0/10")
    --   SET ( ingressStreamCellRate.<streamIndex> = '1000000')
    --   SET ( atmStreamVpi.<streamIndex> = '0')
    --   SET ( atmStreamVci.<streamIndex> = '10')
    --   SET ( ingressState.<streamIndex> = 'inactive')
    --        Note: Management station can't set the stream state to 
    --        active. It will be set to 'active' by agent automatically
    --        when this stream is connected to an egress stream through
    --        the connection objects.


    -- progNextTable

    -- Returns  next availabe program index that can be linked
    -- to a given stream.

    progNextTable  OBJECT-TYPE
	SYNTAX  SEQUENCE OF ProgNextEntry
	ACCESS  not-accessible
	STATUS  mandatory
	DESCRIPTION
	    "To create a new entry in progTable, management station
	    has to first get next program index."
	::= { cstrmStreamGroup  7 }

    progNextEntry   OBJECT-TYPE
	SYNTAX      ProgNextEntry
	ACCESS      not-accessible
	STATUS      mandatory
	DESCRIPTION
	    "This entry contains next program index that can by used by
	    the management stations to add a program in a stream." 
	INDEX { streamIndex }
	::= { progNextTable 1 }

    ProgNextEntry ::=  SEQUENCE {
        progNextIndex
	    INTEGER
	    }

    progNextIndex  OBJECT-TYPE
	SYNTAX     INTEGER
	ACCESS     read-only
	STATUS     mandatory
	DESCRIPTION
	    "Returns an index that can be associated with the given stream.
	    The value '0' indicates that no assigned values are available.
	    After each retrieval operation from management station, agent 
	    should modify this to next unassigned index."
	::= { progNextEntry 1 }

    -- program Table
    
    -- program table is a list of program entries and number of programs.
    -- Each program entry has
    -- transport stream (TS) program number, program name, TS program
    -- length, aggregate transport rate of the program.

    progTable OBJECT-TYPE
	SYNTAX SEQUENCE OF ProgEntry
	ACCESS not-accessible
	STATUS mandatory
	DESCRIPTION
	    "A list of programs linked to one VCB. The number of entries
	    is given by numProgs."
	::= { cstrmStreamGroup 8 }
    
    progEntry OBJECT-TYPE
	SYNTAX ProgEntry
	ACCESS not-accessible
	STATUS mandatory
	DESCRIPTION
	    "progEntry contains program number, program name, TS rate, TS
	    len."
	INDEX  { streamIndex, progIndex } 
	::= { progTable 1 }
    
    ProgEntry ::=  SEQUENCE {
          progIndex
	     INTEGER,
          progNumber
	     INTEGER,
	  progName
	     DisplayString,
	  progTsRate
	     INTEGER,
	  progTsLen
	     INTEGER,
	  progStatus
	     ConnectionStatus
    }

    progIndex OBJECT-TYPE
	SYNTAX INTEGER
	ACCESS read-only
	STATUS mandatory
	DESCRIPTION
	    "A unique handle which identies a program."
	::= { progEntry 1 }
    
    progNumber OBJECT-TYPE
	SYNTAX INTEGER
	ACCESS read-write
	STATUS mandatory
	DESCRIPTION
	    "Program number which identifies a program in a VCB."
	::= { progEntry 2 }
    
    progName   OBJECT-TYPE
	SYNTAX  DisplayString(SIZE(0..31))
	ACCESS  read-write
	STATUS  mandatory
	DESCRIPTION
	    "Human readable program name corresponding to the program
	    number of this entry."
	::= { progEntry 3 }
    
    progTsRate    OBJECT-TYPE
	SYNTAX  INTEGER
	ACCESS  read-write
	STATUS  mandatory
	DESCRIPTION
	    "Aggregate tranport rate of the program."
	::= { progEntry 4 }
    
    progTsLen	  OBJECT-TYPE
	SYNTAX  INTEGER
	ACCESS  read-write
	STATUS  mandatory
	DESCRIPTION
	    "Length of the transport stream packet."
	::= { progEntry 5 }
    
    progStatus OBJECT-TYPE
	SYNTAX  ConnectionStatus
	ACCESS  read-write
	STATUS  mandatory
	DESCRIPTION
	    "Status of this program associated with the VCB."
	::= { progEntry 6 }
    
    -- Example to create a new program.
    -- 
    -- GET ( progNextIndex.<streamIndex> )
    --     Management station should get a non-zero positive index which
    --     can be used a program handle. If a 'zero' is returned, it denotes
    --     that program table is full. 
    --     Let us give the name 'progIndex' to the returned index.
    --
    -- SET ( progNumber.<streamIndex>.<progIndex> = '20')
    -- SET ( progName.<streamIndex>.<progIndex> = "ESPN")
    -- SET ( progTsRate.<streamIndex>.<progIndex> = '40000')
    -- SET ( progTsLen.<streamIndex>.<progIndex> = '188')

    -- SET ( progStatus.<streamIndex>.<progIndex> = 'inactive')

    -- the pidNextTable
    --      Note: Management station can't set the program state to
    --      'active'. It will be set to 'active' by agent automatically
    --      when this program or one of the associated pids is connected
    --      to an egress stream through connection objects.


    -- Returns next available pid index that can be linked a given
    -- stream and program.

    pidNextTable   OBJECT-TYPE
	SYNTAX   SEQUENCE OF PidNextEntry
	ACCESS   not-accessible
	STATUS   mandatory
	DESCRIPTION
	    "To create a new entry pidTable, management stations has
	    to first retrieve a next available pid index."
	::= { cstrmStreamGroup 9 }

    pidNextEntry  OBJECT-TYPE
	SYNTAX    PidNextEntry
	ACCESS    not-accessible
	STATUS    mandatory
	DESCRIPTION
	    "This entry contains next pid index that can by used by
	    the mangement stations to add a pid to the given stream and
	    program."
	INDEX { streamIndex, progIndex }
	::= { pidNextTable 1 }

    PidNextEntry ::= SEQUENCE {
          pidNextIndex
	      INTEGER
          }

    pidNextIndex   OBJECT-TYPE
	SYNTAX     INTEGER
	ACCESS     read-only
	STATUS     mandatory
	DESCRIPTION
	    "Returns an index that can be associated with the given stream
	    and program. The value '0' indicates taht no assigned values are
	    available. After each retrieval operation from management station,
	    agent should modify this to next unassigned index."
	::= { pidNextEntry 1 }

    -- the pidTable
    
    -- pidTable is a list of PID entries associated to each program.
    -- pidTable contains pid number, remap pid number, table type 
    -- identifier, transport rate
    
    pidTable OBJECT-TYPE
	SYNTAX  SEQUENCE OF PidEntry
	ACCESS  not-accessible
	STATUS  mandatory
	DESCRIPTION
	    "List of pids linked to one program. The number of entries
	    is given by numPIDs."
	::= { cstrmStreamGroup 10 }
    
    pidEntry OBJECT-TYPE
	SYNTAX  PidEntry
	ACCESS  not-accessible
	STATUS  mandatory
	DESCRIPTION
	    "pidEntry contains pid number, remap pid number, table 
	    identifier, pid transport rate."
	INDEX { streamIndex, progIndex, pidIndex }
	::= { pidTable 1 }
    
    PidEntry ::=  SEQUENCE   {
          pidIndex
	     INTEGER,
          pidNumber
	     INTEGER,
	  pidTableID
	     INTEGER,
	  pidRate
	     INTEGER,
	  pidStatus
	     ConnectionStatus
    }
    
    pidIndex  OBJECT-TYPE
	SYNTAX  INTEGER
	ACCESS  read-only
	STATUS  mandatory
	DESCRIPTION
	    "A unique integer pid Handle identifying a PID."
	::= { pidEntry 1 }

    pidNumber OBJECT-TYPE
	SYNTAX INTEGER
	ACCESS read-write
	STATUS mandatory
	DESCRIPTION
	    "pid number which uniquely identifies a PID in a program."
	::= { pidEntry 2 }
    
    pidTableID    OBJECT-TYPE
	SYNTAX  INTEGER
	ACCESS  read-write
	STATUS  mandatory
	DESCRIPTION
	    "table type identifier of this PID. This is
	    0 - Program Association Table
	    1 - Program MAP Table
	    2 - PCR PID
	    >2 - Check the manual."
	::= { pidEntry 3 }
    
    pidRate    OBJECT-TYPE
	SYNTAX  INTEGER
	ACCESS  read-write
	STATUS  mandatory
	DESCRIPTION
	    "Tranport rate of a specific PID."
	::= { pidEntry 4 }

    pidStatus  OBJECT-TYPE
	SYNTAX  ConnectionStatus
	ACCESS  read-write
	STATUS  mandatory
	DESCRIPTION
	    "The status of this PID."
	::= { pidEntry 5 }
    
    -- Example to create a new pid object.
    -- 
    -- GET ( pidNextIndex.<streamIndex>.<progIndex> )
    --      Management station should get a non-zero positive index which
    --      can be used as a 'pid' handle. If a 'zero' is returned, it
    --      denotes that pid table is full.
    -- Let us give the name 'pidIndex' to the returned index.
    --
    -- SET ( pidNumber.<streamIndex>.<progIndex>.<pidIndex> = '20')
    -- SET ( pidTableID.<streamIndex>.<progIndex>.<pidIndex> = 'pcr')
    -- SET ( pidRate.<streamIndex>.<progIndex>.<pidIndex> = '30000')
    -- SET ( pidStatus.<streamIndex>.<progIndex>.<pidIndex> = 'inactive')
    --      Note: A management station can't set the pid state to 
    --      'active'. It will be set to 'active' by agent automatically
    --      when this pid is connected to an egress stream through
    --      the connection object.


    -- Cross Stream Connection Table

    -- A connection object is used to make an assocition between an
    -- ingress object and an egress object.
    -- Using this connection object, it is possible 
    --  1)To connect an ingress stream to egress stream.
    --  2)To connect a specific program in an ingress stream to an
    --    egress stream.
    --  3)To connect a specific pid inside a program to an egress
    --    stream.

    cstrmConnNextIndex OBJECT-TYPE
	SYNTAX  INTEGER
	ACCESS  read-only
	STATUS  mandatory
	DESCRIPTION
	    "Returns the next free Index in the connection table."
	::= { cstrmStreamGroup 11 }

		
    cstrmConnTable   OBJECT-TYPE
	SYNTAX  SEQUENCE OF CstrmConnEntry
	ACCESS  not-accessible
	STATUS  mandatory
	DESCRIPTION
	    " A list of Dipersal Entries.."
	::= { cstrmStreamGroup 12 }

    cstrmConnEntry   OBJECT-TYPE
	SYNTAX  CstrmConnEntry
	ACCESS  not-accessible
	STATUS  mandatory
	DESCRIPTION
	    "An cstrmConnEntry contains source program, source pid, dest 
	    program dest pid and asiStreamIndex values. This is the entry 
	    through which management station connect source programs to 
	    destination programs."
	INDEX  { cstrmConnIndex }
	::= {cstrmConnTable 1 }

    CstrmConnEntry ::=
       SEQUENCE {
          cstrmConnIndex
	     INTEGER,
	  ingressStreamIndexVal
	     INTEGER,
	  egressStreamIndexVal
	     INTEGER,
	  ingressProgIndex
	     INTEGER,
	  ingressPidIndex
	     INTEGER,
	  egressProgNum
	     INTEGER,
	  egressPidNum
	     INTEGER,
          pcrAdjust
	     INTEGER,
	  cstrmConnStatus
	     ConnectionStatus
      }

    cstrmConnIndex OBJECT-TYPE
	SYNTAX  INTEGER
	ACCESS  read-only
	STATUS  mandatory
	DESCRIPTION
	    "Index to identify a Connection Table."
	::= { cstrmConnEntry 1 }

    ingressStreamIndexVal OBJECT-TYPE
	SYNTAX  INTEGER
	ACCESS  read-write
	STATUS  mandatory
	DESCRIPTION
	    "Index of the ingress stream."
	::= { cstrmConnEntry 2 }

    egressStreamIndexVal OBJECT-TYPE
	SYNTAX  INTEGER
	ACCESS  read-write
	STATUS  mandatory
	DESCRIPTION
	    "Index of the egress stream"
	::= { cstrmConnEntry 3 }

    ingressProgIndex OBJECT-TYPE
	SYNTAX  INTEGER
	ACCESS  read-write
	STATUS  mandatory
	DESCRIPTION
	    "Source program number associated with the connection table.
	    Source program number is linked to an ingress stream.
	    A value of 'zero' indicates that all programs in the parent
	    stream are connected to the egress stream."
	::= { cstrmConnEntry 4 }

    ingressPidIndex OBJECT-TYPE
	SYNTAX  INTEGER
	ACCESS  read-write
	STATUS  mandatory
	DESCRIPTION
	    "Source PID number associated with the connection table.
	    Source PID number is linked to an ingress stream.
	    A value of 'zero' indicates that all pids in the parent
	    program are connected to the egress stream."
	::= { cstrmConnEntry 5 }

    egressProgNum OBJECT-TYPE
	SYNTAX  INTEGER
	ACCESS  read-write
	STATUS  mandatory
	DESCRIPTION
	    "Destination program number associated with the connection table.
	    Destination program number is linked to an egress stream."
	::= { cstrmConnEntry 6 }

    egressPidNum OBJECT-TYPE
	SYNTAX  INTEGER
	ACCESS  read-write
	STATUS  mandatory
	DESCRIPTION
	    "Destination PID number associated with the connection table.
	    Destination PID number is linked to an egress stream."
	::= { cstrmConnEntry 7 }

    pcrAdjust   OBJECT-TYPE
	SYNTAX  INTEGER {
	          enable(1), -- enable PCR Time Stamp Adjustment.
		  disable(2) -- disable PCR Time Stamp Adjustment.
		}
	ACCESS  read-write
	STATUS  mandatory
	DESCRIPTION
	    "Enable/Disable PCR Time Stamp Adjustment for this
	    connection."
	::= { cstrmConnEntry 8}

    cstrmConnStatus OBJECT-TYPE
	SYNTAX  ConnectionStatus
	ACCESS  read-write
	STATUS  mandatory
	DESCRIPTION
	    "Status of the this connection table."
	::= { cstrmConnEntry 9 }
    
    -- Example to connect an ingress stream(ingressStream)
    -- and egress stream(egressStream). This means all the programs
    -- and pids in 'ingressStream' will be connected to 'egressStream'

    -- GET ( cstrmConnNextIndex.0 )
    --    Management station should get a non-zero positive index which
    --    can be used to specify the mapping. A returned value of 'zero'
    --    denotes that connection table is full.
    --    Let us give the name "connIndex' to the returned index.
    --
    --    SET ( ingressStreamIndexVal.<connIndex> = 'ingressStream')
    --    SET ( egressStreamIndexVal.<connIndex> = 'egressStream')
    --    SET ( ingressProgIndex.<connIndex> = '0')
    --    SET ( ingressPidIndex.<connIndex> = '0')
    --    SET ( cstrmConnStatus.<connIndex> = 'active' )

    -- Example to connect a program 'progA' in an ingress 
    -- stream(ingressStream) to an  egress stream(egressStream). 

    -- GET ( cstrmConnNextIndex.0 )
    --    Management station should get a non-zero positive index which
    --    can be used to specify the mapping. A returned value of 'zero'
    --    denotes that connection table is full.
    --    Let us give the name "connIndex' to the returned index.
    --
    --    SET ( ingressStreamIndexVal.<connIndex> = 'ingressStream')
    --    SET ( egressStreamIndexVal.<connIndex> = 'egressStream')
    --    SET ( ingressProgIndex.<connIndex> = 'progA')
    --    SET ( ingressPidIndex.<connIndex> = '0')
    --    SET ( cstrmConnStatus.<connIndex> = 'active' )

    -- Example to connect a pid 'pidA', in program 'progA' of ingress 
    -- stream(ingressStream) to an  egress stream(egressStream). 

    -- GET ( cstrmConnNextIndex.0 )
    --    Management station should get a non-zero positive index which
    --    can be used to specify the mapping. A returned value of 'zero'
    --    denotes that connection table is full.
    --    Let us give the name "connIndex' to the returned index.
    --
    --    SET ( ingressStreamIndexVal.<connIndex> = 'ingressStream')
    --    SET ( egressStreamIndexVal.<connIndex> = 'egressStream')
    --    SET ( ingressProgIndex.<connIndex> = 'progA')
    --    SET ( ingressPidIndex.<connIndex> = 'pidA')
    --    SET ( cstrmConnStatus.<connIndex> = 'active' )


    connectionStreamTable OBJECT-TYPE
	SYNTAX  SEQUENCE OF ConnectionStreamEntry
	ACCESS  not-accessible
	STATUS  mandatory
	DESCRIPTION
	    "Connection Stream table is used to traverse the stream
	    connections."
	::= { cstrmStreamGroup 13 }

    connectionStreamEntry OBJECT-TYPE
	SYNTAX  ConnectionStreamEntry
	ACCESS  not-accessible
	STATUS  mandatory
	DESCRIPTION
	    "This entry has the connection index for the associated stream.
	    If the ConnectionIndex is zero, connectionStreamIndex will return
	    first connection object for this association."
--	INDEX { StreamDirection, StreamIndex, ConnectionIndex }
	::= { connectionStreamTable 1 }

    ConnectionStreamEntry	::= SEQUENCE {
        connectionStreamIndex
	    INTEGER
	}

    connectionStreamIndex  OBJECT-TYPE
	SYNTAX    INTEGER
	ACCESS    read-only
	STATUS    mandatory
	DESCRIPTION
	    "Returns an active connection object index connected to/from
	    the given stream index."
	::= { connectionStreamEntry 1 }

    connectionProgTable OBJECT-TYPE
	SYNTAX  SEQUENCE OF ConnectionProgEntry
	ACCESS  not-accessible
	STATUS  mandatory
	DESCRIPTION
	    "Connection Prog table is used to traverse the program
	    connections."
	::= { cstrmStreamGroup 14 }

    connectionProgEntry OBJECT-TYPE
	SYNTAX  ConnectionProgEntry
	ACCESS  not-accessible
	STATUS  mandatory
	DESCRIPTION
	    "This entry has the connection index for the given program in
	    the specified stream object. If the ConnectionIndex is zero,
	    connectionProgIndex will return first conneciton object for this
	    association."
--	INDEX { StreamDirection, StreamIndex, ProgIndex, ConnectionIndex }
	::= { connectionProgTable 1 }

    ConnectionProgEntry	::= SEQUENCE {
        connectionProgIndex
	    INTEGER
	}
    
    connectionProgIndex  OBJECT-TYPE
	SYNTAX    INTEGER
	ACCESS    read-only
	STATUS    mandatory
	DESCRIPTION
	    "Returns an active connection object index connected to/from
	    the given program index."
	::= { connectionProgEntry 1 }

    connectionPidTable OBJECT-TYPE
	SYNTAX  SEQUENCE OF ConnectionPidEntry
	ACCESS  not-accessible
	STATUS  mandatory
	DESCRIPTION
	    "Connection pid table is used to traverse the pid
	    connections."
	::= { cstrmStreamGroup 15 }

    connectionPidEntry OBJECT-TYPE
	SYNTAX  ConnectionPidEntry
	ACCESS  not-accessible
	STATUS  mandatory
	DESCRIPTION
	    "This entry has the connection index for the given pid in
	    the specified program & stream object. If the ConnectionIndex is
	    zero, connectionPidIndex will return first connection object
	    for this association."
--	INDEX { StreamDirection, StreamIndex, ProgIndex, PidIndex, ConnectionIndex }
	::= { connectionPidTable 1 }

    ConnectionPidEntry	::= SEQUENCE {
        connectionPidIndex
	    INTEGER
	}
    
    connectionPidIndex  OBJECT-TYPE
	SYNTAX    INTEGER
	ACCESS    read-only
	STATUS    mandatory
	DESCRIPTION
	    "Returns an active connection object index connected to/from
	    the given pid index."
	::= { connectionPidEntry 1 }

--
-- Traps and events are defined here
--

    cstrmOverTemp	TRAP-TYPE
	ENTERPRISE	cstrmEvents
	VARIABLES	{ cstrmAirTemp, cstrmCoreRegTemp,
                          cstrm3VRegTemp, cstrmHotICTemp }
        DESCRIPTION
                  "A cstrmOverTemp trap signifies that one or more of
                   the temperature sensors has exceeded its high
                   threshhold level.  The values of the 4 temperature
                   sensors are sent in Degrees Celsius with the trap."
	::= 1

    cstrmCoolFail	TRAP-TYPE
	ENTERPRISE	cstrmEvents
        DESCRIPTION
                  "A cstrmCoolFail trap signifies that a cooling system
                   failure has occured."
	::= 2

    cstrmPowerMonitor	TRAP-TYPE
	ENTERPRISE	cstrmEvents
	VARIABLES	{ cstrm5VCoreVoltage, cstrm3VCoreVoltage,
                          cstrm3VIOVoltage }
        DESCRIPTION
                  "A cstrmPowerMonitor trap signifies that one or more of
                   the voltage sensors is out of acceptable range.
                   The values of the 3 voltage sensors are sent in
                   100ths of milivolts."
	::= 3

    cstrmATMPhyTrap	TRAP-TYPE
	ENTERPRISE	cstrmEvents
	VARIABLES	{ ifIndex, cstrmATMPhyTrapID, cstrmATMPhyTrapStatus }
	DESCRIPTION
                  ""
	::= 4

    cstrmOAMVPTrap	TRAP-TYPE
	ENTERPRISE	cstrmEvents
	VARIABLES	{ ifIndex, cstrmOAMVPTrapID , atmStreamVpi, cstrmOAMVPTrapStatus }
	DESCRIPTION
                  ""
	::= 5

    cstrmOAMVCTrap	TRAP-TYPE
	ENTERPRISE	cstrmEvents
	VARIABLES	{ ifIndex, cstrmOAMVCTrapID , atmStreamVpi , atmStreamVci, cstrmOAMVCTrapStatus}
	DESCRIPTION
                  ""
	::= 6

    cstrmSONETTrap	TRAP-TYPE
	ENTERPRISE	cstrmEvents
	VARIABLES	{ ifIndex, cstrmSONETTrapID, cstrmSONETTrapStatus}
	DESCRIPTION
                  ""
	::= 7

	cstrmActDeActTrap	TRAP-TYPE
	ENTERPRISE	cstrmEvents 
	VARIABLES	{ ifIndex, cstrmActDeActTrapID , cstrmActDeActTrapStatus}
        DESCRIPTION
                  "This Trap is generated for each of Activate and Deactivate event Alarm."
	::= 8

	cstrmIngressPidsChangedTrap	TRAP-TYPE
	ENTERPRISE	cstrmEvents 
	VARIABLES	{ ifIndex, cstrmIngressPidsChangedTrapID , cstrmIngressPidsChangedTrapStatus}
        DESCRIPTION
                  "This Trap is generated for each of Activate and Deactivate event Alarm."
	::= 9
    END
