CYCLADES-ACS5K-PM-MIB DEFINITIONS ::= BEGIN

-- Avocent Vendor MIB OID Tree
-- Release 3.3.0-9 05/24/2011
-- The cyACS5KPM has the ACS 5000' power mgmt MIB :

IMPORTS
	cyACS5KMgmt
		FROM CYCLADES-ACS5K-MIB
	OBJECT-TYPE, MODULE-IDENTITY, Integer32
		FROM SNMPv2-SMI
	InterfaceIndex, InterfaceIndexOrZero
		FROM IF-MIB
	DisplayString
		FROM SNMPv2-TC;

cyACS5KPM   MODULE-IDENTITY
	LAST-UPDATED	"201007260000Z"
	ORGANIZATION	"Avocent Corporation"
	CONTACT-INFO	"postal : Avocent Corporation
				47281 Bayside Parkway
				Fremont, CA 94538, USA
				e-mail : Technical Support
					  techsupport@avocent.com"
	DESCRIPTION	"This module defines objects of the Proxy for PM "
	REVISION	"201007260000Z"
	DESCRIPTION	"First Draft"
::= { cyACS5KMgmt 5 }

cyNumberOfPM		OBJECT-TYPE
	SYNTAX		Integer32
	MAX-ACCESS	read-only
	STATUS		current
	DESCRIPTION	"The total number of PM's connected on the unit"
::= { cyACS5KPM 1 }
 
cyPMTable OBJECT-TYPE
	SYNTAX		SEQUENCE OF CyPMEntry
	MAX-ACCESS	not-accessible
	STATUS		current
	DESCRIPTION	"Allows to read information about each connected PM"
::= { cyACS5KPM 2 }

cyPMEntry	OBJECT-TYPE
	SYNTAX		CyPMEntry
	MAX-ACCESS	not-accessible
	STATUS		current
	DESCRIPTION	"Information about the connected PM"
	INDEX		{ cyPMSerialPortNumber }
::= { cyPMTable 1 }

CyPMEntry ::= SEQUENCE  {
	cyPMSerialPortNumber	InterfaceIndex,     
	cyPMNumberOutlets Integer32,
	cyPMNumberUnits	Integer32,
	cyPMCurrent	DisplayString,
	cyPMVersion	DisplayString,
	cyPMCommand	DisplayString
}

cyPMSerialPortNumber	OBJECT-TYPE
	SYNTAX		InterfaceIndex	
	MAX-ACCESS	read-only
	STATUS		current
	DESCRIPTION	"The number of the serial port when the PM is connected."
::= { cyPMEntry 1 }

cyPMNumberOutlets	OBJECT-TYPE
	SYNTAX		Integer32	
	MAX-ACCESS	read-only
	STATUS		current
	DESCRIPTION	"Number of outlets."
::= { cyPMEntry 2 }

cyPMNumberUnits		OBJECT-TYPE
	SYNTAX		Integer32	
	MAX-ACCESS	read-only
	STATUS		current
	DESCRIPTION	"Total number of PM unists that are accessed by this 
			serial port."
::= { cyPMEntry 3 }

cyPMCurrent	OBJECT-TYPE
	SYNTAX		DisplayString	
	MAX-ACCESS	read-only
	STATUS		current
	DESCRIPTION	"Current reading for the PM."
::= { cyPMEntry 4 }

cyPMVersion	OBJECT-TYPE
	SYNTAX		DisplayString	
	MAX-ACCESS	read-only
	STATUS		current
	DESCRIPTION	"The software version of the PM."
::= { cyPMEntry 5 }

cyPMCommand		OBJECT-TYPE
	SYNTAX		DisplayString (SIZE (1..100))
	MAX-ACCESS	read-write
	STATUS		current
	DESCRIPTION	"A character string for the user to send commands to
			PM. He can use it to does the save command.
			Or to list the outlets that need to be turned off, 
			or turned on , or cycled or locked or unlocked as a 
			group. The command is the first word and is followed 
			by a space and the outlet list (otulets commands). 
			Valid commands are 'on', 'off', 'cycle', 'lock',
			'unlock', 'save'."
::= { cyPMEntry 7 }

cyPMUnitTable	OBJECT-TYPE
	SYNTAX		SEQUENCE OF CyPMUnitEntry
	MAX-ACCESS	not-accessible
	STATUS		current
	DESCRIPTION	"Allow operations on specific PM unit connected"
::= { cyACS5KPM 3 }

cyPMUnitEntry	OBJECT-TYPE
	SYNTAX		CyPMUnitEntry
	MAX-ACCESS	not-accessible
	STATUS		current
	DESCRIPTION	"Allow operations on outlet"
	INDEX		{ cyPMSerialPortNumber, cyPMUnitNumber }
::= { cyPMUnitTable 1 }

CyPMUnitEntry ::= SEQUENCE  {
	cyPMUnitNumber		InterfaceIndex,     
	cyPMUnitVersion		DisplayString,
	cyPMUnitOutlets		Integer32,
	cyPMUnitFirstOutlet 	Integer32,
	cyPMUnitCurrent		Integer32,
	cyPMUnitMaxCurrent 	Integer32,
	cyPMUnitSequenceInterval	Integer32,
	cyPMUnitCycleInterval	Integer32,	
	cyPMUnitID		DisplayString,
	cyPMUnitPhases		INTEGER,
	cyPMUnitBanks           Integer32,      
	cyPMUnitNominalVoltage  Integer32,
	cyPMUnitPower           Integer32
}

cyPMUnitNumber	OBJECT-TYPE
	SYNTAX		InterfaceIndex	
	MAX-ACCESS	not-accessible
	STATUS		current
	DESCRIPTION	"The number of the PM unit in the daisy-chained mode."
::= { cyPMUnitEntry 1 }

cyPMUnitVersion	OBJECT-TYPE
	SYNTAX		DisplayString	
	MAX-ACCESS	read-only
	STATUS		current
	DESCRIPTION	"The software version of this PM unit."
::= { cyPMUnitEntry 2 }

cyPMUnitOutlets	OBJECT-TYPE
	SYNTAX		Integer32	
	MAX-ACCESS	read-only
	STATUS		current
	DESCRIPTION	"Number of outlets of this PM unit."
::= { cyPMUnitEntry 3 }

cyPMUnitFirstOutlet	OBJECT-TYPE
	SYNTAX		Integer32	
	MAX-ACCESS	read-only
	STATUS		current
	DESCRIPTION	"Number of the first outlet of this PM unit."
::= { cyPMUnitEntry 4 }

cyPMUnitCurrent	OBJECT-TYPE
	SYNTAX		Integer32	
	MAX-ACCESS	read-only
	STATUS		current
	DESCRIPTION	"Current of this PM unit in AMP.
			The value of this object is the actual current in 
                        AMP * 10. You need to translate the readed value
                        (Ex. : value is 5, the current is 0.5 AMP.)" 
::= { cyPMUnitEntry 5 }

cyPMUnitMaxCurrent	OBJECT-TYPE
	SYNTAX		Integer32	
	MAX-ACCESS	read-only
	STATUS		current
	DESCRIPTION	"Maximum current of this PM unit in AMP.
			The value of this object is the maximum current in 
                        AMP * 10. You need to translate the readed value
                        (Ex. : value is 5, the maximum current is 0.5 AMP.)" 
::= { cyPMUnitEntry 6 }

cyPMUnitSequenceInterval OBJECT-TYPE
	SYNTAX		Integer32	
	MAX-ACCESS	read-only
	STATUS		current
	DESCRIPTION	"Sequence interval delay. 
                        Valid values are 2 to 15 (seconds)."
::= { cyPMUnitEntry 9 }

cyPMUnitCycleInterval	OBJECT-TYPE
	SYNTAX		Integer32	
	MAX-ACCESS	read-only
	STATUS		current
	DESCRIPTION	"Number of seconds that a socket stays off 
			before turning it back on."
::= { cyPMUnitEntry 10 }

cyPMUnitID		OBJECT-TYPE
	SYNTAX		DisplayString
	MAX-ACCESS	read-only
	STATUS		current
	DESCRIPTION	"PDU identification."
::= { cyPMUnitEntry 11 }

cyPMUnitPhases	OBJECT-TYPE
	SYNTAX	INTEGER	{
			single-phase(0),
			three-phase(3)
		}
	MAX-ACCESS	read-only
	STATUS		current
	DESCRIPTION	"Number of phases of this PDU unit."
::= { cyPMUnitEntry 12 }

cyPMUnitBanks		OBJECT-TYPE
	SYNTAX		Integer32
	MAX-ACCESS	read-only
	STATUS		current
	DESCRIPTION	"Number of banks of this PDU unit."
::= { cyPMUnitEntry 13 }

cyPMUnitNominalVoltage	OBJECT-TYPE
	SYNTAX		Integer32
	MAX-ACCESS	read-only
	STATUS		current
	DESCRIPTION	"Nominal Voltage configured for this PDU unit, when it does not have voltage sensor"
::= { cyPMUnitEntry 14 }

cyPMUnitPower		OBJECT-TYPE
	SYNTAX		Integer32
	MAX-ACCESS	read-only
	STATUS		current
	DESCRIPTION	"Power Consumption of this PDU unit (it is estimated when PDU does not have voltage sensor)."
::= { cyPMUnitEntry 15 }

cyOutletTable	OBJECT-TYPE
	SYNTAX		SEQUENCE OF CyOutletEntry
	MAX-ACCESS	not-accessible
	STATUS		current
	DESCRIPTION	"Allow operations on outlet"
::= { cyACS5KPM 4 }

cyOutletEntry	OBJECT-TYPE
	SYNTAX		CyOutletEntry
	MAX-ACCESS	not-accessible
	STATUS		current
	DESCRIPTION	"Allow operations on outlet"
	INDEX		{ cyPMSerialPortNumber, cyOutletNumber }
::= { cyOutletTable 1 }

CyOutletEntry ::= SEQUENCE  {
	cyOutletNumber	InterfaceIndexOrZero,     
	cyOutletName	DisplayString,
	cyOutletServer	DisplayString,
	cyOutletPower	INTEGER,
	cyOutletLock	INTEGER,
	cyOutletPUInterval	Integer32,
	cyOutletMinimumOnInterval	 Integer32,
	cyOutletMinimumOffInterval        Integer32,
	cyOutletWakeupState	Integer32,
	cyOutletPduID		DisplayString,
	cyOutletPduNumber 	Integer32
}

cyOutletNumber	OBJECT-TYPE
	SYNTAX		InterfaceIndexOrZero	
	MAX-ACCESS	not-accessible
	STATUS		current
	DESCRIPTION	"The outlet number on the PM. Zero is ALL outlets."
::= { cyOutletEntry 1 }

cyOutletName OBJECT-TYPE
	SYNTAX		DisplayString (SIZE(1 .. 8))	
	MAX-ACCESS	read-write
	STATUS		current
	DESCRIPTION	"The name given to a particular outlet Maximum size is 8 characters."
::= { cyOutletEntry 2 }

cyOutletServer OBJECT-TYPE
	SYNTAX		DisplayString 	
	MAX-ACCESS	read-only
	STATUS		current
	DESCRIPTION	"Alias of the Server connected to this outlet ."
::= { cyOutletEntry 3 }

cyOutletPower	OBJECT-TYPE
	SYNTAX	INTEGER {
			off	(0),
			on	(1),
			cycle	(2),
			unknow  (3)
		}
	MAX-ACCESS	read-write
	STATUS		current
	DESCRIPTION	"Getting this object will return the power state of
			the outlet. Valid return states are UNKNOW, OFF and
			ON. Setting this object will change the power state 
			of the outlet."
::= { cyOutletEntry 4 }

cyOutletLock	OBJECT-TYPE
	SYNTAX	INTEGER {
			unlock	(0),
			lock	(1),
			unknow 	(2)
		}
	MAX-ACCESS	read-write
	STATUS		current
	DESCRIPTION	"Getting this object will return the lock state of
			the outlet. Setting this object will change the 
			lock state of the outlet."
::= { cyOutletEntry 5 }

cyOutletPUInterval	OBJECT-TYPE
	SYNTAX		Integer32	
	MAX-ACCESS	read-write
	STATUS		current
	DESCRIPTION	"The power unit interval of this outlet in seconds.
			The value of this object is the actual interval in 
                        seconds * 10. You need to translate the readed value
                        (Ex. : value is 5, the interval is 0.5 seconds.)" 
::= { cyOutletEntry 6 }

cyOutletMinimumOnInterval OBJECT-TYPE
	SYNTAX		Integer32	
	MAX-ACCESS	read-only
	STATUS		current
	DESCRIPTION	"Minimum time in seconds an outlet will stay on before 
			turning	it off."
::= { cyOutletEntry 7 }

cyOutletMinimumOffInterval OBJECT-TYPE
	SYNTAX		Integer32	
	MAX-ACCESS	read-only
	STATUS		current
	DESCRIPTION	"Minimum time in seconds an outlet will stay off before 
			turning	it on."
::= { cyOutletEntry 8 }

cyOutletWakeupState	OBJECT-TYPE
	SYNTAX		Integer32	
	MAX-ACCESS	read-only
	STATUS		current
	DESCRIPTION	"Outlet state after a cold boot. It can be set to on 
			or off."
::= { cyOutletEntry 9 }

cyOutletPduID	OBJECT-TYPE
	SYNTAX		DisplayString
	MAX-ACCESS	read-only
	STATUS		current
	DESCRIPTION	"PDU identification."
::= { cyOutletEntry 10}

cyOutletPduNumber	OBJECT-TYPE
	SYNTAX		Integer32
	MAX-ACCESS	not-accessible
	STATUS		current
	DESCRIPTION	"The number of the PDU unit in the daisy-chained mode."
::= { cyOutletEntry 11 }

cyPMElecPduTable	OBJECT-TYPE
        SYNTAX          SEQUENCE OF CyPMElecPduTableEntry
        MAX-ACCESS      not-accessible
        STATUS          current
        DESCRIPTION     "Allow operations on elecmon element of the PDUs"
::= { cyACS5KPM 5 }

cyPMElecPduTableEntry	OBJECT-TYPE
	SYNTAX		CyPMElecPduTableEntry
	MAX-ACCESS	not-accessible
	STATUS		current
	DESCRIPTION	"each entry has the information about the elecmon element of the PDUs."
	INDEX           { cyPMElecPduTablePortNumber, cyPMElecPduTablePduNumber }
::= { cyPMElecPduTable 1 }

CyPMElecPduTableEntry ::= SEQUENCE  {
	cyPMElecPduTablePortNumber   InterfaceIndex,   -- serial port #
	cyPMElecPduTablePduNumber    InterfaceIndex,   -- pdu number in the chain
	cyPMElecPduTableCurrentValue    Integer32,           -- actual value for current
	cyPMElecPduTableCurrentMax      Integer32,           -- max value for current
	cyPMElecPduTablePowerValue      Integer32,          -- actual value for power
	cyPMElecPduTablePowerMax        Integer32,           -- max value for power
	cyPMElecPduTableVoltageValue    Integer32,           -- actual value for voltage
	cyPMElecPduTableVoltageMax      Integer32,            -- max value for voltage
	cyPMElecPduTablePowerFactorValue  Integer32,    -- actual value for powerfactor
	cyPMElecPduTablePowerFactorMax    Integer32,    -- max value for powerfactor
	cyPMElecPduTablePowerType       INTEGER,           -- type of power
	cyPMElecPduTableVoltageType     INTEGER,            -- type of voltage
	cyPMElecPduTablePowerFactorType	INTEGER            -- type of powerfactor
}

cyPMElecPduTablePortNumber	OBJECT-TYPE
	SYNTAX		InterfaceIndex
	MAX-ACCESS	read-only
	STATUS		current
	DESCRIPTION	"Serial Port number where the PDU is connected."
::= { cyPMElecPduTableEntry 1 }

cyPMElecPduTablePduNumber 	OBJECT-TYPE
	SYNTAX		InterfaceIndex
	MAX-ACCESS	read-only
	STATUS		current
	DESCRIPTION	"The number of the PDU unit in the daisy-chained mode"
::= { cyPMElecPduTableEntry  2 }

cyPMElecPduTableCurrentValue	OBJECT-TYPE
	SYNTAX		Integer32
	MAX-ACCESS	read-only
	STATUS		current
	DESCRIPTION	"Actual value of current in the element (A x 10)."
::= { cyPMElecPduTableEntry 3 }

cyPMElecPduTableCurrentMax	OBJECT-TYPE
	SYNTAX		Integer32
	MAX-ACCESS	read-write
	STATUS		current
	DESCRIPTION	"Maximum detected value of current in the element (A x 10). 
			Write operation accepts only 0 for reset action."
::= { cyPMElecPduTableEntry 4 }

cyPMElecPduTablePowerValue	OBJECT-TYPE
	SYNTAX		Integer32
	MAX-ACCESS	read-only
	STATUS		current
	DESCRIPTION	"Actual value of power in the element (W x 10)."
::= { cyPMElecPduTableEntry 5 }

cyPMElecPduTablePowerMax	OBJECT-TYPE
	SYNTAX		Integer32
	MAX-ACCESS	read-write
	STATUS		current
	DESCRIPTION	"Maximum value of power in the element (W x 10).
			Write operation accepts only 0 for reset action."
::= { cyPMElecPduTableEntry 6 }

cyPMElecPduTableVoltageValue	OBJECT-TYPE
	SYNTAX		Integer32
	MAX-ACCESS	read-only
	STATUS		current
	DESCRIPTION	"Actual value of voltage in the element (V).When element 
			does not have voltage sensor, it returns 0."
::= { cyPMElecPduTableEntry 7 }

cyPMElecPduTableVoltageMax	OBJECT-TYPE
	SYNTAX		Integer32
	MAX-ACCESS	read-write
	STATUS		current
	DESCRIPTION	"Maximum value of voltage in the element (V). When element 
			does not have voltage sensor, it returns 0. Write operation 
			accepts only 0 for reset action."
::= { cyPMElecPduTableEntry 8 }

cyPMElecPduTablePowerFactorValue	OBJECT-TYPE
	SYNTAX		Integer32
	MAX-ACCESS	read-only
	STATUS		current
	DESCRIPTION	"Actual value of power factor in the element (Pf x 10). 
			When element does not have power factor sensor, returns 0."
::= { cyPMElecPduTableEntry 9 }

cyPMElecPduTablePowerFactorMax	OBJECT-TYPE
	SYNTAX		Integer32
	MAX-ACCESS	read-write
	STATUS		current
	DESCRIPTION	"Maximum value of power factor in the element (Pf x 10). 
			When element does not have power factor sensor, returns 0.
			Write operation accepts only 0 for reset action."
::= { cyPMElecPduTableEntry 10 }

cyPMElecPduTablePowerType	OBJECT-TYPE
	SYNTAX		INTEGER  {
				estimated(1),
				measured(2)
			}
	MAX-ACCESS	read-only
	STATUS		current
	DESCRIPTION	"This PDU unit's Power sensor type."
::= { cyPMElecPduTableEntry 11 }

cyPMElecPduTableVoltageType	OBJECT-TYPE
	SYNTAX		INTEGER  {
				estimated(1),
				measured(2)
			}
	MAX-ACCESS	read-only
	STATUS		current
	DESCRIPTION	"This PDU unit's has voltage sensor type."
::= { cyPMElecPduTableEntry 12 }

cyPMElecPduTablePowerFactorType	OBJECT-TYPE
	SYNTAX		INTEGER  {
				estimated(1),
				measured(2)
			}
	MAX-ACCESS	read-only
	STATUS		current
	DESCRIPTION	"This PDU unit's Power Factor sensor type."
::= { cyPMElecPduTableEntry 13 }

cyPMElecPhaseTable	OBJECT-TYPE
        SYNTAX          SEQUENCE OF CyPMElecPhaseTableEntry
        MAX-ACCESS      not-accessible
        STATUS          current
        DESCRIPTION     "Allow operations on elecmon element for phases"
::= { cyACS5KPM 6 }

cyPMElecPhaseTableEntry	OBJECT-TYPE
	SYNTAX		CyPMElecPhaseTableEntry
	MAX-ACCESS	not-accessible
	STATUS		current
	DESCRIPTION	"each entry has the information about the elecmon for phase."
	INDEX		{ 
				cyPMElecPhaseTablePortNumber,
				cyPMElecPhaseTablePduNumber,
				cyPMElecPhaseTableIndex 
			}
::= { cyPMElecPhaseTable 1 }

CyPMElecPhaseTableEntry ::= SEQUENCE  {
	cyPMElecPhaseTablePortNumber	InterfaceIndex,   -- serial port #
	cyPMElecPhaseTablePduNumber	InterfaceIndex,   -- pdu number in the chain
	cyPMElecPhaseTableIndex		InterfaceIndex,    -- index of the element 
	cyPMElecPhaseTableName		DisplayString,      -- phase sysname
	cyPMElecPhaseTableCurrentValue	Integer32,           -- actual value for current
	cyPMElecPhaseTableCurrentMax	Integer32,           -- max value for current
	cyPMElecPhaseTablePowerValue	Integer32,          -- actual value for power
	cyPMElecPhaseTablePowerMax	Integer32,           -- max value for power
	cyPMElecPhaseTableVoltageValue	Integer32,           -- actual value for voltage
	cyPMElecPhaseTableVoltageMax	Integer32,            -- max value for voltage
	cyPMElecPhaseTablePowerFactorValue	Integer32,    -- actual value for powerfactor
	cyPMElecPhaseTablePowerFactorMax	Integer32,    -- max value for powerfactor
	cyPMElecPhaseTablePowerType       INTEGER,           -- type of power
        cyPMElecPhaseTableVoltageType     INTEGER,            -- type of voltage
        cyPMElecPhaseTablePowerFactorType INTEGER            -- type of powerfactor
}

cyPMElecPhaseTablePortNumber	OBJECT-TYPE
	SYNTAX		InterfaceIndex
	MAX-ACCESS	read-only
	STATUS		current
	DESCRIPTION	"Serial Port number where the PDU is connected."
::= { cyPMElecPhaseTableEntry 1 }

cyPMElecPhaseTablePduNumber	OBJECT-TYPE
	SYNTAX		InterfaceIndex
	MAX-ACCESS	read-only
	STATUS		current
	DESCRIPTION	"The number of the PDU unit in the daisy-chained mode"
::= { cyPMElecPhaseTableEntry  2 }

cyPMElecPhaseTableIndex OBJECT-TYPE
	SYNTAX		InterfaceIndex
	MAX-ACCESS	read-only
	STATUS		current
	DESCRIPTION	"index of the phase in the PDU. Index can be 1,2 or 3."
::= { cyPMElecPhaseTableEntry 3 }

cyPMElecPhaseTableName	OBJECT-TYPE
	SYNTAX		DisplayString
	MAX-ACCESS	read-only
	STATUS		current
	DESCRIPTION	"Sys-name of the phase." 
::= { cyPMElecPhaseTableEntry 4 }

cyPMElecPhaseTableCurrentValue	OBJECT-TYPE
	SYNTAX		Integer32
	MAX-ACCESS	read-only
	STATUS		current
	DESCRIPTION	"Actual value of current in the phase (A x 10)."
::= { cyPMElecPhaseTableEntry 5 }

cyPMElecPhaseTableCurrentMax	OBJECT-TYPE
	SYNTAX		Integer32
	MAX-ACCESS	read-write
	STATUS		current
	DESCRIPTION	"Maximum detected value of current in the phase (A x 10). 
			Write operation accepts only 0 for reset action."
::= { cyPMElecPhaseTableEntry 6 }

cyPMElecPhaseTablePowerValue	OBJECT-TYPE
	SYNTAX		Integer32
	MAX-ACCESS	read-only
	STATUS		current
	DESCRIPTION	"Actual value of power in the phase (W x 10)."
::= { cyPMElecPhaseTableEntry 7 }

cyPMElecPhaseTablePowerMax	OBJECT-TYPE
	SYNTAX		Integer32 
	MAX-ACCESS	read-write 
	STATUS		current
	DESCRIPTION	"Maximum value of power in the phase (W x 10).Write operation
			accepts only 0 for reset action."
::= { cyPMElecPhaseTableEntry 8 }

cyPMElecPhaseTableVoltageValue	OBJECT-TYPE
	SYNTAX		Integer32
	MAX-ACCESS	read-only
	STATUS		current
	DESCRIPTION	"Actual value of voltage in the phase (V).When phase does 
			not have voltage sensor, it returns 0."
::= { cyPMElecPhaseTableEntry 9 }

cyPMElecPhaseTableVoltageMax	OBJECT-TYPE
	SYNTAX		Integer32
	MAX-ACCESS	read-write
	STATUS		current
	DESCRIPTION	"Maximum value of voltage in the phase (V). When phase does 
			not have voltage sensor, it returns 0. Write operation accepts 
			only 0 for reset action."
::= { cyPMElecPhaseTableEntry 10 }

cyPMElecPhaseTablePowerFactorValue	OBJECT-TYPE
	SYNTAX		Integer32
	MAX-ACCESS	read-only
	STATUS		current
	DESCRIPTION	"Actual value of power factor in the phase (Pf x 10). When 
			phase does not have power factor sensor, returns 0."
::= { cyPMElecPhaseTableEntry 11 }

cyPMElecPhaseTablePowerFactorMax	OBJECT-TYPE
	SYNTAX		Integer32
	MAX-ACCESS	read-write
	STATUS		current
	DESCRIPTION	"Maximum value of power factor in the phase (Pf x 10). When 
			phase does not have power factor sensor, returns 0.Write 
			operation accepts only 0 for reset action."
::= { cyPMElecPhaseTableEntry 12 }

cyPMElecPhaseTablePowerType	OBJECT-TYPE
	SYNTAX		INTEGER  {
				estimated(1),
				measured(2)
			}
	MAX-ACCESS	read-only
	STATUS		current
	DESCRIPTION	"The type of Power sensor for this elecmon"
::= { cyPMElecPhaseTableEntry 13 }

cyPMElecPhaseTableVoltageType	OBJECT-TYPE
	SYNTAX		INTEGER  {
				estimated(1),
				measured(2)
			}
	MAX-ACCESS	read-only
	STATUS		current
	DESCRIPTION	"The type of Voltage sensor for this elecmon"
::= { cyPMElecPhaseTableEntry 14 }

cyPMElecPhaseTablePowerFactorType	OBJECT-TYPE
	SYNTAX		INTEGER  {
				estimated(1),
				measured(2)
			}
	MAX-ACCESS	read-only
	STATUS		current
	DESCRIPTION	"The type of Power Factor sensor for this elecmon"
::= { cyPMElecPhaseTableEntry 15 }

cyPMElecBankTable	OBJECT-TYPE
        SYNTAX          SEQUENCE OF CyPMElecBankTableEntry
        MAX-ACCESS      not-accessible
        STATUS          current
        DESCRIPTION     "Allow operations on elecmon element for banks"
::= { cyACS5KPM 7 }

cyPMElecBankTableEntry	OBJECT-TYPE
	SYNTAX		CyPMElecBankTableEntry
	MAX-ACCESS	not-accessible
	STATUS		current
	DESCRIPTION	"each entry has the information about the elecmon for Bank."
	INDEX		{ 
				cyPMElecBankTablePortNumber,
				cyPMElecBankTablePduNumber,
				cyPMElecBankTableIndex 
			}
::= { cyPMElecBankTable 1 }

CyPMElecBankTableEntry ::= SEQUENCE  {
	cyPMElecBankTablePortNumber	InterfaceIndex,   -- serial port #
	cyPMElecBankTablePduNumber	InterfaceIndex,   -- pdu number in the chain
	cyPMElecBankTableIndex		InterfaceIndex,    -- index of the element 
	cyPMElecBankTableName		DisplayString,      -- Bank sysname
	cyPMElecBankTableCurrentValue	Integer32,           -- actual value for current
	cyPMElecBankTableCurrentMax	Integer32,           -- max value for current
	cyPMElecBankTablePowerValue	Integer32,          -- actual value for power
	cyPMElecBankTablePowerMax	Integer32,           -- max value for power
	cyPMElecBankTableVoltageValue	Integer32,           -- actual value for voltage
	cyPMElecBankTableVoltageMax	Integer32,            -- max value for voltage
	cyPMElecBankTablePowerFactorValue	Integer32,    -- actual value for powerfactor
	cyPMElecBankTablePowerFactorMax	Integer32,    -- max value for powerfactor
	cyPMElecBankTablePowerType       INTEGER,           -- type of power
        cyPMElecBankTableVoltageType     INTEGER,            -- type of voltage
        cyPMElecBankTablePowerFactorType INTEGER            -- type of powerfactor
}

cyPMElecBankTablePortNumber	OBJECT-TYPE
	SYNTAX		InterfaceIndex
	MAX-ACCESS	read-only
	STATUS		current
	DESCRIPTION	"Serial Port number where the PDU is connected."
::= { cyPMElecBankTableEntry 1 }

cyPMElecBankTablePduNumber	OBJECT-TYPE
        SYNTAX          InterfaceIndex
        MAX-ACCESS      read-only
        STATUS          current
        DESCRIPTION     "The number of the PDU unit in the daisy-chained mode"
::= { cyPMElecBankTableEntry  2 }

cyPMElecBankTableIndex OBJECT-TYPE
        SYNTAX          InterfaceIndex
        MAX-ACCESS      read-only
        STATUS          current
	DESCRIPTION	"index of the Bank in the PDU. Index can be 1,2, ... number of banks of the PDU."
::= { cyPMElecBankTableEntry 3 }

cyPMElecBankTableName	OBJECT-TYPE
	SYNTAX		DisplayString
	MAX-ACCESS	read-only
	STATUS		current
	DESCRIPTION	"Sys-name of the Bank." 
::= { cyPMElecBankTableEntry 4 }

cyPMElecBankTableCurrentValue	OBJECT-TYPE
	SYNTAX		Integer32
	MAX-ACCESS	read-only
	STATUS		current
	DESCRIPTION	"Actual value of current in the Bank (A x 10)."
::= { cyPMElecBankTableEntry 5 }

cyPMElecBankTableCurrentMax	OBJECT-TYPE
	SYNTAX		Integer32
	MAX-ACCESS	read-write
	STATUS		current
	DESCRIPTION	"Maximum detected value of current in the Bank (A x 10). 
			Write operation accepts only 0 for reset action."
::= { cyPMElecBankTableEntry 6 }

cyPMElecBankTablePowerValue	OBJECT-TYPE
	SYNTAX		Integer32
	MAX-ACCESS	read-only
	STATUS		current
	DESCRIPTION	"Actual value of power in the Bank (W x 10)."
::= { cyPMElecBankTableEntry 7 }

cyPMElecBankTablePowerMax	OBJECT-TYPE
	SYNTAX		Integer32 
	MAX-ACCESS	read-write 
	STATUS		current
	DESCRIPTION	"Maximum value of power in the Bank (W x 10).Write operation
			accepts only 0 for reset action."
::= { cyPMElecBankTableEntry 8 }

cyPMElecBankTableVoltageValue	OBJECT-TYPE
	SYNTAX		Integer32
	MAX-ACCESS	read-only
	STATUS		current
	DESCRIPTION	"Actual value of voltage in the Bank (V).When Bank does 
			not have voltage sensor, it returns 0."
::= { cyPMElecBankTableEntry 9 }

cyPMElecBankTableVoltageMax	OBJECT-TYPE
	SYNTAX		Integer32
	MAX-ACCESS	read-write
	STATUS		current
	DESCRIPTION	"Maximum value of voltage in the Bank (V). When Bank does 
			not have voltage sensor, it returns 0. Write operation accepts 
			only 0 for reset action."
::= { cyPMElecBankTableEntry 10 }

cyPMElecBankTablePowerFactorValue	OBJECT-TYPE
	SYNTAX		Integer32
	MAX-ACCESS	read-only
	STATUS		current
	DESCRIPTION	"Actual value of power factor in the Bank (Pf x 10). When 
			Bank does not have power factor sensor, returns 0."
::= { cyPMElecBankTableEntry 11 }

cyPMElecBankTablePowerFactorMax	OBJECT-TYPE
	SYNTAX		Integer32
	MAX-ACCESS	read-write
	STATUS		current
	DESCRIPTION	"Maximum value of power factor in the Bank (Pf x 10). When 
			Bank does not have power factor sensor, returns 0.Write 
			operation accepts only 0 for reset action."
::= { cyPMElecBankTableEntry 12 }

cyPMElecBankTablePowerType	OBJECT-TYPE
	SYNTAX		INTEGER  {
				estimated(1),
				measured(2)
			}
	MAX-ACCESS	read-only
	STATUS		current
	DESCRIPTION	"The type of Power sensor for this elecmon"
::= { cyPMElecBankTableEntry 13 }

cyPMElecBankTableVoltageType	OBJECT-TYPE
	SYNTAX		INTEGER  {
				estimated(1),
				measured(2)
			}
	MAX-ACCESS	read-only
	STATUS		current
	DESCRIPTION	"The type of Voltage sensor for this elecmon"
::= { cyPMElecBankTableEntry 14 }

cyPMElecBankTablePowerFactorType	OBJECT-TYPE
	SYNTAX		INTEGER  {
				estimated(1),
				measured(2)
			}
	MAX-ACCESS	read-only
	STATUS		current
	DESCRIPTION	"The type of Power Factor sensor for this elecmon"
::= { cyPMElecBankTableEntry 15 }

cyPMElecOutletTable	OBJECT-TYPE
        SYNTAX          SEQUENCE OF CyPMElecOutletTableEntry
        MAX-ACCESS      not-accessible
        STATUS          current
        DESCRIPTION     "Allow operations on elecmon element for outlets"
::= { cyACS5KPM 8 }

cyPMElecOutletTableEntry	OBJECT-TYPE
	SYNTAX		CyPMElecOutletTableEntry
	MAX-ACCESS	not-accessible
	STATUS		current
	DESCRIPTION	"each entry has the information about the elecmon for Outlet."
	INDEX		{ 
				cyPMElecOutletTablePortNumber,
				cyPMElecOutletTablePduNumber,
				cyPMElecOutletTableNumber 
			}
::= { cyPMElecOutletTable 1 }

CyPMElecOutletTableEntry ::= SEQUENCE  {
	cyPMElecOutletTablePortNumber	InterfaceIndex,   -- serial port #
	cyPMElecOutletTablePduNumber	InterfaceIndex,   -- pdu number in the chain
	cyPMElecOutletTableNumber	InterfaceIndex,    -- outlet number in the PDU 
	cyPMElecOutletTableName		DisplayString,      -- Outlet name
	cyPMElecOutletTableCurrentValue	Integer32,           -- actual value for current
	cyPMElecOutletTableCurrentMax	Integer32,           -- max value for current
	cyPMElecOutletTablePowerValue	Integer32,          -- actual value for power
	cyPMElecOutletTablePowerMax	Integer32,           -- max value for power
	cyPMElecOutletTableVoltageValue	Integer32,           -- actual value for voltage
	cyPMElecOutletTableVoltageMax	Integer32,            -- max value for voltage
	cyPMElecOutletTablePowerFactorValue	Integer32,    -- actual value for powerfactor
	cyPMElecOutletTablePowerFactorMax	Integer32,    -- max value for powerfactor
	cyPMElecOutletTablePowerType       INTEGER,           -- type of power
        cyPMElecOutletTableVoltageType     INTEGER,            -- type of voltage
        cyPMElecOutletTablePowerFactorType INTEGER            -- type of powerfactor
}

cyPMElecOutletTablePortNumber	OBJECT-TYPE
	SYNTAX		InterfaceIndex
	MAX-ACCESS	read-only
	STATUS		current
	DESCRIPTION	"Serial Port number where the PDU is connected."
::= { cyPMElecOutletTableEntry 1 }

cyPMElecOutletTablePduNumber	OBJECT-TYPE
	SYNTAX		InterfaceIndex
	MAX-ACCESS	read-only
	STATUS		current
	DESCRIPTION	"The number of the PDU unit in the daisy-chained mode"
::= { cyPMElecOutletTableEntry  2 }

cyPMElecOutletTableNumber	OBJECT-TYPE
	SYNTAX		InterfaceIndex
	MAX-ACCESS	read-only
	STATUS		current
	DESCRIPTION	"outlet number in the PDU"
::= { cyPMElecOutletTableEntry 3 }

cyPMElecOutletTableName	OBJECT-TYPE
	SYNTAX		DisplayString
	MAX-ACCESS	read-only
	STATUS		current
	DESCRIPTION	"name of the Outlet." 
::= { cyPMElecOutletTableEntry 4 }

cyPMElecOutletTableCurrentValue	OBJECT-TYPE
	SYNTAX		Integer32
	MAX-ACCESS	read-only
	STATUS		current
	DESCRIPTION	"Actual value of current in the Outlet (A x 10)."
::= { cyPMElecOutletTableEntry 5 }

cyPMElecOutletTableCurrentMax	OBJECT-TYPE
	SYNTAX		Integer32
	MAX-ACCESS	read-write
	STATUS		current
	DESCRIPTION	"Maximum detected value of current in the Outlet (A x 10). 
			Write operation accepts only 0 for reset action."
::= { cyPMElecOutletTableEntry 6 }

cyPMElecOutletTablePowerValue	OBJECT-TYPE
	SYNTAX		Integer32
	MAX-ACCESS	read-only
	STATUS		current
	DESCRIPTION	"Actual value of power in the Outlet (W x 10)."
::= { cyPMElecOutletTableEntry 7 }

cyPMElecOutletTablePowerMax	OBJECT-TYPE
	SYNTAX		Integer32 
	MAX-ACCESS	read-write 
	STATUS		current
	DESCRIPTION	"Maximum value of power in the Outlet (W x 10).Write operation
			accepts only 0 for reset action."
::= { cyPMElecOutletTableEntry 8 }

cyPMElecOutletTableVoltageValue	OBJECT-TYPE
	SYNTAX		Integer32
	MAX-ACCESS	read-only
	STATUS		current
	DESCRIPTION	"Actual value of voltage in the Outlet (V).When Outlet does 
			not have voltage sensor, it returns 0."
::= { cyPMElecOutletTableEntry 9 }

cyPMElecOutletTableVoltageMax	OBJECT-TYPE
	SYNTAX		Integer32
	MAX-ACCESS	read-write
	STATUS		current
	DESCRIPTION	"Maximum value of voltage in the Outlet (V). When Outlet does 
			not have voltage sensor, it returns 0. Write operation accepts 
			only 0 for reset action."
::= { cyPMElecOutletTableEntry 10 }

cyPMElecOutletTablePowerFactorValue	OBJECT-TYPE
	SYNTAX		Integer32
	MAX-ACCESS	read-only
	STATUS		current
	DESCRIPTION	"Actual value of power factor in the Outlet (Pf x 10). When 
			Outlet does not have power factor sensor, returns 0."
::= { cyPMElecOutletTableEntry 11 }

cyPMElecOutletTablePowerFactorMax	OBJECT-TYPE
	SYNTAX		Integer32
	MAX-ACCESS	read-write
	STATUS		current
	DESCRIPTION	"Maximum value of power factor in the Outlet (Pf x 10). When 
			Outlet does not have power factor sensor, returns 0.Write 
			operation accepts only 0 for reset action."
::= { cyPMElecOutletTableEntry 12 }

cyPMElecOutletTablePowerType	OBJECT-TYPE
	SYNTAX		INTEGER  {
				estimated(1),
				measured(2)
			}
	MAX-ACCESS	read-only
	STATUS		current
	DESCRIPTION	"The type of Power sensor for this elecmon"
::= { cyPMElecOutletTableEntry 13 }

cyPMElecOutletTableVoltageType	OBJECT-TYPE
	SYNTAX		INTEGER  {
				estimated(1),
				measured(2)
			}
	MAX-ACCESS	read-only
	STATUS		current
	DESCRIPTION	"The type of Voltage sensor for this elecmon"
::= { cyPMElecOutletTableEntry 14 }

cyPMElecOutletTablePowerFactorType	OBJECT-TYPE
	SYNTAX		INTEGER  {
				estimated(1),
				measured(2)
			}
	MAX-ACCESS	read-only
	STATUS		current
	DESCRIPTION	"The type of Power Factor sensor for this elecmon"
::= { cyPMElecOutletTableEntry 15 }

cyPMEnvMonTable	OBJECT-TYPE
	SYNTAX		SEQUENCE OF CyPMEnvMonTableEntry
        MAX-ACCESS	not-accessible
	STATUS		current
	DESCRIPTION	"Allow operations on environmental monitors"
::= { cyACS5KPM 9 }

cyPMEnvMonTableEntry  OBJECT-TYPE
	SYNTAX		CyPMEnvMonTableEntry
	MAX-ACCESS	not-accessible
	STATUS		current
	DESCRIPTION	"each entry has the information about the environmental monitors."
	INDEX		{ 
				cyPMEnvMonTablePortNumber,
				cyPMEnvMonTablePduNumber,
				cyPMEnvMonTableIndex 
			}
::= { cyPMEnvMonTable 1 }

CyPMEnvMonTableEntry ::= SEQUENCE  {
	cyPMEnvMonTablePortNumber	InterfaceIndex,   -- serial port #
	cyPMEnvMonTablePduNumber	InterfaceIndex,   -- pdu number in the chain
	cyPMEnvMonTableIndex	InterfaceIndex,  -- index of the monitor 
	cyPMEnvMonTableName	DisplayString,    -- monitor sysname
	cyPMEnvMonTableType	INTEGER,         -- type of the monitor
	cyPMEnvMonTableStatus	INTEGER,	-- status of monitors 
	cyPMEnvMonTableValue	Integer32,	-- current value of monitor 
	cyPMEnvMonTableMaxValue	Integer32
}

cyPMEnvMonTablePortNumber	OBJECT-TYPE
        SYNTAX		InterfaceIndex
        MAX-ACCESS	read-only
        STATUS		current
        DESCRIPTION	"Serial Port number where the PDU is connected."
::= { cyPMEnvMonTableEntry 1 }

cyPMEnvMonTablePduNumber	OBJECT-TYPE
        SYNTAX		InterfaceIndex
        MAX-ACCESS	read-only
        STATUS		current
        DESCRIPTION	"The number of the PDU unit in the daisy-chained mode"
::= { cyPMEnvMonTableEntry  2 }

cyPMEnvMonTableIndex	OBJECT-TYPE
        SYNTAX		InterfaceIndex
        MAX-ACCESS	read-only
        STATUS		current
        DESCRIPTION	"index of the environmental monitor in the PDU."
::= { cyPMEnvMonTableEntry 3 }

cyPMEnvMonTableName	OBJECT-TYPE
        SYNTAX		DisplayString
        MAX-ACCESS	read-only
        STATUS		current
        DESCRIPTION	"Name of the environmental monitor." 
::= { cyPMEnvMonTableEntry 4 }

cyPMEnvMonTableType	OBJECT-TYPE
	SYNTAX	INTEGER {
			temp-internal (1), 
			temperature (2),
			humidity (3),
			air-flow (4),
			smoke (5),
			dry-concact (6),
			water-level (7),
			motion (8),
			unplugged (9),
			unknown (10)
		}        
        MAX-ACCESS	read-only
        STATUS		current
        DESCRIPTION	"The type of environmental monitor."
::= { cyPMEnvMonTableEntry  5 }

cyPMEnvMonTableStatus OBJECT-TYPE
         SYNTAX	INTEGER {
              		normal(1),
              		triggered(2),
			not-applicable(3)
                }        
        MAX-ACCESS	read-only
        STATUS		current
        DESCRIPTION	"The status of Dry-Contact/Water-level/Smoke/Motion monitors. 
			Dry-Contact sensor: Opened(1), closed(2). 
			Water level: Normal (1), Triggered(2). 
			Smoke sensor: not-detected(1), detected(2). 
			Motion sensor: not-detected(1), detected(2)."
::= { cyPMEnvMonTableEntry  6 }

cyPMEnvMonTableValue	OBJECT-TYPE
        SYNTAX		Integer32
        MAX-ACCESS	read-only
        STATUS		current
        DESCRIPTION	"Actual value of Temperature/Humidity/Air-flow monitors (x 10)."
::= { cyPMEnvMonTableEntry 7 }

cyPMEnvMonTableMaxValue	OBJECT-TYPE
        SYNTAX		Integer32
        MAX-ACCESS	read-write
        STATUS		current
        DESCRIPTION	"Maximum detected value of Temperature/Humidity/Air-flow monitor (x 10). 
			Write operation accepts only 0 for reset action."
::= { cyPMEnvMonTableEntry 8 }

END
