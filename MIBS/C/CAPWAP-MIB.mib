-- extracted from draft-yangshi-capwap-base-mib-00.txt
-- at Tue Aug  7 06:08:54 2007

CAPWAP-MIB DEFINITIONS ::= BEGIN

IMPORTS
   MacAddress, DisplayString, TEXTUAL-CONVENTION, TruthValue, TimeStamp
       FROM SNMPv2-TC

   NOTIFICATION-GROUP, OBJECT-GROUP, MODULE-COMPLIANCE
       FROM SNMPv2-CONF

   MODULE-IDENTITY, OBJECT-TYPE, NOTIFICATION-TYPE, mib-2, Integer32,
   IpAddress, Unsigned32, Counter32
       FROM SNMPv2-SMI;

capwapMIB MODULE-IDENTITY
   LAST-UPDATED "200707310000Z"        -- July 31, 2007
   ORGANIZATION "IETF CAPWAP working Group"
   CONTACT-INFO
       "Yang Shi
        H3C, Digital Technology Plaza, NO.9 Shangdi 9th Street,Haidian
        District,Beijing,China(100085)
        Email:  young@h3c.com

        David T. Perkins
        228 Bayview Dr
        San Carlos, CA 94070
        USA
        Phone: +1 408 394-8702
        Email:  dperkins@snmpinfo.com

        Long Gao
        H3C, Digital Technology Plaza, NO.9 Shangdi 9th Street,Haidian
        District,Beijing,China(100085)
        Email:  gaolong@h3c.com"
   DESCRIPTION
       "Copyright (C) 2007 The Internet Society.  This version of
        the MIB module is part of RFC xxx; see the RFC itself
        for full legal notices.

        This MIB module contains managed object definitions for
        the CAPWAP Protocol."
   REVISION    "200707310000Z"
   DESCRIPTION
       "Initial version published as RFC xxx"
        ::= { mib-2 999901 }

-- EdNote: Replace 999901 with a real OID once it is
-- allocated & remove this note.


-- Textual Conventions

CapwapWTPId ::= TEXTUAL-CONVENTION
   STATUS      current
   DESCRIPTION
       "Represents a unique identifier of a WTP instance."
   SYNTAX      OCTET STRING (SIZE (6))

CapwapStationId ::= TEXTUAL-CONVENTION
   STATUS      current
   DESCRIPTION
       "Represents a unique identifier of a station instance."
   SYNTAX      OCTET STRING (SIZE (6))

CapwapRadioId ::= TEXTUAL-CONVENTION
   STATUS      current
   DESCRIPTION
       "Represents a unique identifier of a radio on a WTP."
   SYNTAX      Unsigned32 (1..4294967295)

CapwapWTPTunnelMode ::= TEXTUAL-CONVENTION
    STATUS      current
    DESCRIPTION
        "Represents the tunneling mode for station data that are
         supported by the WTP.
         The possible value could be:
          localBridging(1) - Local Bridging Mode,
          dot3Tunnel(2)    - 802.3 Frame Tunnel Mode,
          nativeTunnel(3)  - Native Frame Tunnel Mode."
    REFERENCE
        "Section 4.6.41. of CAPWAP Protocol Specification, RFC xxx."
    SYNTAX      INTEGER { localBridging(1), dot3Tunnel(2),
                          nativeTunnel(3)}

CapwapWTPMACType ::= TEXTUAL-CONVENTION
    STATUS      current
    DESCRIPTION
        "Represents the MAC mode of operation supported by the WTP.
         The possible value could be:
          localMAC(1) - Local-MAC Mode,
          splitMAC(2) - Split-MAC Mode."
    REFERENCE
        "Section 4.6.44. of CAPWAP Protocol Specification, RFC xxx."
    SYNTAX      INTEGER { localMAC(1), splitMAC(2) }

CapwapWTPRadioTemplateIfIndex ::= TEXTUAL-CONVENTION
    STATUS      current
    DESCRIPTION
        "Represents the TC for a ifindex of 'WTP radio template'
         interface type."
    SYNTAX      Integer32 (1..2147483647)

CapwapChannelType::= TEXTUAL-CONVENTION
    STATUS     current
    DESCRIPTION
        "Represents the channel type for CAPWAP protocol.
         The following values are supported:
          data(1)    - data Channel
          control(2) - control Channel."
    SYNTAX    INTEGER { data(1), control(2) }

CapwapWTPAuthenMethod ::= TEXTUAL-CONVENTION
    STATUS     current
    DESCRIPTION
        "The attribute represents the authentication credential type
         for WTP.
         The following values are supported:
           clear(1) - cleartext and no authentication,
           x509(2)  - X.509 Certificate Based,
           psk(3)   - Pre-Shared Secret,
           other(8) - Other method, for example, vendor specific.
         As mandatory requirement, CAPWAP control channel
         authentication should use DTLS, and either by certificate or
         PSK. For data channel, DTLS is optional."
    SYNTAX    INTEGER { clear(1), x509(2), psk(3), other(8) }

-- Top level components of this MIB

capwapObjects OBJECT IDENTIFIER
    ::= { capwapMIB 1 }
capwapConformance OBJECT IDENTIFIER
    ::= { capwapMIB 2 }
capwapNotifications OBJECT IDENTIFIER
    ::= { capwapMIB 0}

-- Object Groups

-- for State:
capwapObjectState OBJECT IDENTIFIER
    ::= { capwapObjects 1 }

-- for statistics:
capwapObjectsStats OBJECT IDENTIFIER
    ::= { capwapObjects 2 }

-- for notifications

capwapNotifyVarObjects OBJECT IDENTIFIER
    ::= { capwapObjects 3 }


-- AC state Group

capwapACState OBJECT IDENTIFIER
    ::= { capwapObjectState 1 }

capwapACWTPSessions OBJECT-TYPE
    SYNTAX      Unsigned32
    MAX-ACCESS  read-only
    STATUS      current
    DESCRIPTION
        "Represents the total number of WTPs which are connecting to
         AC."
    REFERENCE
        "Section 4.6.1. of CAPWAP Protocol Specification, RFC xxx."
    ::= { capwapACState 1 }

capwapACWTPSessionsLimit  OBJECT-TYPE
    SYNTAX      Unsigned32
    MAX-ACCESS  read-only
    STATUS      current
    DESCRIPTION
        "Represents the maximum number of WTP sessions supported by
         the AC."
    REFERENCE
        "Section 4.6.1. of CAPWAP Protocol Specification, RFC xxx."
    ::= { capwapACState 2 }

capwapACStationSessions  OBJECT-TYPE
    SYNTAX      Unsigned32
    MAX-ACCESS  read-only
    STATUS      current
    DESCRIPTION
        "Represents the total number of stations which are accessing
         the wireless service."
    REFERENCE
        "Section 4.6.1. of CAPWAP Protocol Specification, RFC xxx."
    ::= { capwapACState 3 }

capwapACStationSessionsLimit  OBJECT-TYPE
    SYNTAX      Unsigned32
    MAX-ACCESS  read-only
    STATUS      current
    DESCRIPTION
        "Represents the maximum number of station sessions supported by
         the AC."
    REFERENCE
        "Section 4.6.1. of CAPWAP Protocol Specification, RFC xxx."
    ::= { capwapACState 4 }

capwapACDataChannelSecOptions  OBJECT-TYPE
    SYNTAX      Integer32
    MAX-ACCESS  read-only
    STATUS      current
    DESCRIPTION
        "Represents the security policy supported for CAPWAP data
         channel.
         The AC MAY support more than one option, represented by the bit
         field below.
         clear(1)  -  Clear Text,
         dtls(2)   -  DTLS,
         vendor(3) -  vendor specific."
    REFERENCE
       "Section 4.6.1. of CAPWAP Protocol Specification, RFC xxx."
    ::= { capwapACState 5 }

capwapACWTPAuthenOptions  OBJECT-TYPE
    SYNTAX      Integer32
    MAX-ACCESS  read-only
    STATUS      current
    DESCRIPTION
        "Represents the authentication credentia type supported by the
         AC for control channel.
         The AC MAY support more than one option, represented by the bit
         field below.
         x509(1) -  X.509 Certificate Based
         psk(2)  -  Pre-Shared Secret."
    REFERENCE
       "Section 4.6.1. of CAPWAP Protocol Specification, RFC xxx."
    ::= { capwapACState 6 }

capwapACHwVersion  OBJECT-TYPE
    SYNTAX      OCTET STRING(SIZE(32))
    MAX-ACCESS  read-only
    STATUS      current
    DESCRIPTION
        "Represents the AC's hardware version number."
    REFERENCE
        "Section 4.6.1. of CAPWAP Protocol Specification, RFC xxx."
    ::= { capwapACState 7 }

capwapACSwVersion  OBJECT-TYPE
    SYNTAX      OCTET STRING(SIZE(32))
    MAX-ACCESS  read-only
    STATUS      current
    DESCRIPTION
        "Represents the AC's software version number."
    REFERENCE
        "Section 4.6.1. of CAPWAP Protocol Specification, RFC xxx."
    ::= { capwapACState 8 }

capwapWTPFallbackEnable OBJECT-TYPE
    SYNTAX      TruthValue
    MAX-ACCESS  read-write
    STATUS      current
    DESCRIPTION
        "Represents enable or disable automatic CAPWAP fallback in the
         event that a WTP detects its preferred AC, and is not currently
         connected to it."
    REFERENCE
        "Section 4.6.40. of CAPWAP Protocol Specification, RFC xxx."
    DEFVAL      { true }
    ::= { capwapACState 9 }

capwapWTPACNameList OBJECT-TYPE
    SYNTAX      Unsigned32
    MAX-ACCESS  read-write
    STATUS      current
    DESCRIPTION
        "Represent the name list of ACs and use semicolon to separate AC
         name. The AC name could be configured with the order of
         Primary AC, secondary AC and so on. WTP will try to connect to
         AC name in the list one by one till it connected to one AC."
    REFERENCE
        "Section 4.6.5. of CAPWAP Protocol Specification, RFC xxx."
    ::= { capwapACState 10 }

capwapMaxFailedDTLSSessionRetry OBJECT-TYPE
    SYNTAX      Unsigned32
    MAX-ACCESS  read-only
    STATUS      current
    DESCRIPTION
        "Represent the maximum number of failed DTLS session
         establishment attempts before the CAPWAP device enters a silent
         period."
    REFERENCE
        "Section 4.7.7. of CAPWAP Protocol Specification, RFC xxx."
    DEFVAL      { 3 }
    ::= { capwapACState 11 }

capwapWTPIdleTimeout OBJECT-TYPE
    SYNTAX      Unsigned32
    UNITS       "kbtyes"
    MAX-ACCESS  read-only
    STATUS      current
    DESCRIPTION
        "Represent the time out parameter for WTP idle state."
    REFERENCE
        "Section 4.8.5. of CAPWAP Protocol Specification, RFC xxx."

    DEFVAL      { 300 }
    ::= { capwapACState 12 }

capwapWTPMaxDiscoveries OBJECT-TYPE
    SYNTAX      Unsigned32
    MAX-ACCESS  read-only
    STATUS      current
    DESCRIPTION
        "Represent the maximum number of Discovery Request messages
        that will be sent after a WTP boots"
    REFERENCE
        "Section 4.8.6. of CAPWAP Protocol Specification, RFC xxx."
    DEFVAL      { 10 }
    ::= { capwapACState 13 }

capwapWTPMaxRetransmit OBJECT-TYPE
    SYNTAX      Unsigned32
    MAX-ACCESS  read-only
    STATUS      current
    DESCRIPTION
        "Represent the maximum number of retransmissions for a given
         CAPWAP packet before the link layer considers the peer dead."
    REFERENCE
        "Section 4.8.7. of CAPWAP Protocol Specification, RFC xxx."
    DEFVAL      { 5 }
    ::= { capwapACState 14 }

capwapWTPReportInterval OBJECT-TYPE
    SYNTAX      Unsigned32
    UNITS       "second"
    MAX-ACCESS  read-only
    STATUS      current
    DESCRIPTION
        "Represents the interval for WTP send report."
    REFERENCE
        "Section 4.8.8. of CAPWAP Protocol Specification, RFC xxx."
    DEFVAL      { 120 }
    ::= { capwapACState 15 }

-- End of AC state group


-- capwapWTPStateTable table

capwapWTPStateTable OBJECT-TYPE
    SYNTAX      SEQUENCE OF CapwapWTPStateEntry
    MAX-ACCESS  not-accessible
    STATUS      current
    DESCRIPTION
        "This table provides the state information for WTPs which are
         accessing to AC via CAPWAP protocol."
    ::= { capwapObjectState 2 }

capwapWTPStateEntry  OBJECT-TYPE
    SYNTAX      CapwapWTPStateEntry
    MAX-ACCESS  not-accessible
    STATUS      current
    DESCRIPTION
        "An entry in this table is created by AC for each WTPs which are
         accessing to AC via CAPWAP protocol."
    INDEX { capwapWTPId }
    ::= { capwapWTPStateTable 1 }

CapwapWTPStateEntry ::= SEQUENCE {
    capwapWTPId          CapwapWTPId,
    capwapWTPIPAddress   IpAddress,
    capwapWTPSerialId    OCTET STRING,
    capwapWTPState       INTEGER }

capwapWTPId OBJECT-TYPE
    SYNTAX      CapwapWTPId
    MAX-ACCESS  accessible-for-notify
    STATUS      current
    DESCRIPTION
        "Represents the identifier of a WTP."
    ::= { capwapWTPStateEntry 1 }

capwapWTPIPAddress OBJECT-TYPE
    SYNTAX      IpAddress
    MAX-ACCESS  read-only
    STATUS      current
    DESCRIPTION
        "Represents the IP address of a WTP."
    ::= { capwapWTPStateEntry 2 }

capwapWTPSerialId OBJECT-TYPE
    SYNTAX      OCTET STRING(SIZE(128))
    MAX-ACCESS  read-only
    STATUS      current
    DESCRIPTION
        "Represents the serial number of a WTP."
    REFERENCE
        "Section 4.6.38. of CAPWAP Protocol Specification, RFC xxx."
    ::= { capwapWTPStateEntry 3 }

capwapWTPState  OBJECT-TYPE
    SYNTAX      INTEGER {
                 dtls(1), join(2), image(3), configure(4),
                 run(5), clear(6)
                }
    MAX-ACCESS  read-only
    STATUS      current
    DESCRIPTION
        "Represents WTP current state according to CAPWAP
         protocol's FSM.
         The following values are supported:
          dtls(1)      - DTLS negotiation process
          join(2)      - WTP is joining with AC,
          image(3)     - WTP is downloading software,
          configure(4) - WTP is getting configuration for AC,
          run(5)       - WTP come to run state,
          clear(6)     - WTP is recovery default configuration."
    REFERENCE
        "Section 2.3.1. of CAPWAP Protocol Specification, RFC xxx."
    ::= { capwapWTPStateEntry 4 }

-- End of capwapWTPStateTable Table


-- capwapWTPTable Table

capwapWTPTable OBJECT-TYPE
    SYNTAX      SEQUENCE OF CapwapWTPEntry
    MAX-ACCESS  not-accessible
    STATUS      current
    DESCRIPTION
        "The table provides information for WTPs in running state."
    ::= { capwapObjectState 3 }

capwapWTPEntry  OBJECT-TYPE
    SYNTAX      CapwapWTPEntry
    MAX-ACCESS  not-accessible
    STATUS      current
    DESCRIPTION
        "An entry in this table is created by AC during CAPWAP protocol
         process."
    INDEX { capwapWTPCurrId }
    ::= { capwapWTPTable 1 }

CapwapWTPEntry ::= SEQUENCE {
    capwapWTPCurrId               CapwapWTPId,
    capwapWTPName                 DisplayString,
    capwapWTPLocation             DisplayString,
    capwapWTPManufacturerId       OBJECT IDENTIFIER,
    capwapWTPModelId              Unsigned32,
    capwapWTPBoardId              Unsigned32,
    capwapWTPBoardRevision        Unsigned32,
    capwapWTPBaseMACAddress       MacAddress,
    capwapWTPTunnelModeOptions    CapwapWTPTunnelMode,
    capwapWTPMACTypeOptions       CapwapWTPMACType,
    capwapWTPDiscoveryType        INTEGER,
    capwapWTPRadiosInUseNumber    Unsigned32,
    capwapWTPRadioNumLimit        Unsigned32,
    capwapWTPSwVersion            OCTET STRING,
    capwapWTPSwSize               Unsigned32,
    capwapWTPHwVersion            OCTET STRING,
    capwapWTPStaticIPEnable       TruthValue,
    capwapWTPStaticIP             IpAddress,
    capwapWTPNetmask              IpAddress,
    capwapWTPGateway              IpAddress }

capwapWTPCurrId OBJECT-TYPE
    SYNTAX      CapwapWTPId
    MAX-ACCESS  not-accessible
    STATUS      current
    DESCRIPTION
        "Represents the unique identifier of a WTP Which is
         in running state."
    ::= { capwapWTPEntry 1 }

capwapWTPName  OBJECT-TYPE
    SYNTAX      DisplayString
    MAX-ACCESS  read-write
    STATUS      current
    DESCRIPTION
        "Represents the name of a WTP."
    REFERENCE
        "Section 4.6.45. of CAPWAP Protocol Specification, RFC xxx."
    ::= { capwapWTPEntry 2 }

capwapWTPLocation  OBJECT-TYPE
    SYNTAX      DisplayString
    MAX-ACCESS  read-write
    STATUS      current
    DESCRIPTION
        "Represents the name of a WTP."
    REFERENCE
        "Section 4.6.28. of CAPWAP Protocol Specification, RFC xxx."
    ::= { capwapWTPEntry 3 }

capwapWTPManufacturerId  OBJECT-TYPE
    SYNTAX      OBJECT IDENTIFIER
    MAX-ACCESS  read-only
    STATUS      current
    DESCRIPTION
        "SMI Network Management Private Enterprise Codes, which are
         assigned by the IANA. NMS could know which vendor
         manufactures the WTP."
    REFERENCE
        "Section 4.6.39. of CAPWAP Protocol Specification, RFC xxx."
    ::= { capwapWTPEntry 4 }

capwapWTPModelId  OBJECT-TYPE
    SYNTAX      Unsigned32
    MAX-ACCESS  read-only
    STATUS      current
    DESCRIPTION
        "Represents the WTP Model Number."
    REFERENCE
        "Section 4.6.38. of CAPWAP Protocol Specification, RFC xxx."
    ::= { capwapWTPEntry 5 }

capwapWTPBoardId  OBJECT-TYPE
    SYNTAX      Unsigned32
    MAX-ACCESS  read-only
    STATUS      current
    DESCRIPTION
        "Represents the WTP hardware identifier."
    REFERENCE
        "Section 4.6.38. of CAPWAP Protocol Specification, RFC xxx."
    ::= { capwapWTPEntry 6 }

capwapWTPBoardRevision  OBJECT-TYPE
    SYNTAX      Unsigned32
    MAX-ACCESS  read-only
    STATUS      current
    DESCRIPTION
        "Represents the revision number of the board."
    REFERENCE
        "Section 4.6.38. of CAPWAP Protocol Specification, RFC xxx."
    ::= { capwapWTPEntry 7 }

capwapWTPBaseMACAddress  OBJECT-TYPE
    SYNTAX      MacAddress
    MAX-ACCESS  read-only
    STATUS      current
    DESCRIPTION
        "Represents the WTP's Base MAC Address, which MAY be assigned
         to the primary Ethernet interface."
    REFERENCE
        "Section 4.6.38. of CAPWAP Protocol Specification, RFC xxx."
    ::= { capwapWTPEntry 8 }

capwapWTPTunnelModeOptions  OBJECT-TYPE
    SYNTAX      CapwapWTPTunnelMode
    MAX-ACCESS  read-only
    STATUS      current
    DESCRIPTION
        "Represents the tunneling modes for station data that are
         supported by the WTP.
         The WTP MAY support more than one option, represented by the
         bit field below.
          localBridging(1) - Local Bridging Mode,
          dot3Tunnel(2)    - 802.3 Frame Tunnel Mode,
          nativeTunnel(3)  - Native Frame Tunnel Mode."
    REFERENCE
        "Section 4.6.41. of CAPWAP Protocol Specification, RFC xxx."
    ::= { capwapWTPEntry 9 }

capwapWTPMACTypeOptions  OBJECT-TYPE
    SYNTAX      CapwapWTPMACType
    MAX-ACCESS  read-only
    STATUS      current
    DESCRIPTION
        "Represents the MAC mode of operation supported by the WTP.
         The WTP MAY support more than one option, represented by the
         bit field below.
          localMAC(1) - Local-MAC Mode,
          splitMAC(2) - Split-MAC Mode."
    REFERENCE
        "Section 4.6.44. of CAPWAP Protocol Specification, RFC xxx."
    ::= { capwapWTPEntry 10 }

capwapWTPDiscoveryType OBJECT-TYPE
    SYNTAX      INTEGER {
                 unknown(1), staticConfig(2), dhcp(3), dns(4), acRef(5)
                }
    MAX-ACCESS  read-only
    STATUS      current
    DESCRIPTION
        "Represents how WTP discovered the AC.
         The following values are supported:
          unknown(1)    - the method is unknown,
          staticConfig(2)  - static IP configuration,
          dhcp(3)       - DHCP,
          dns(4)        - DNS,
          acRef(5)      - AC Referral."
    REFERENCE
        "Section 4.6.20. of CAPWAP Protocol Specification, RFC xxx."
    ::= { capwapWTPEntry 11 }

capwapWTPRadiosInUseNumber OBJECT-TYPE
    SYNTAX      Unsigned32
    MAX-ACCESS  read-only
    STATUS      current
    DESCRIPTION
        "Represents the number of radios which are in use."
    REFERENCE
        "Section 4.6.39. of CAPWAP Protocol Specification, RFC xxx."
    ::= { capwapWTPEntry 12 }

capwapWTPRadioNumLimit OBJECT-TYPE
    SYNTAX      Unsigned32
    MAX-ACCESS  read-only
    STATUS      current
    DESCRIPTION
        "Represents the maximum radio number could be supported by WTP."
    REFERENCE
        "Section 4.6.39. of CAPWAP Protocol Specification, RFC xxx."
    ::= { capwapWTPEntry 13 }

capwapWTPSwVersion OBJECT-TYPE
    SYNTAX      OCTET STRING(SIZE(32))
    MAX-ACCESS  read-only
    STATUS      current
    DESCRIPTION
        "Represents the name of WTP software."
    REFERENCE
        "Section 4.6.39. of CAPWAP Protocol Specification, RFC xxx."
    ::= { capwapWTPEntry 14 }

capwapWTPSwSize OBJECT-TYPE
    SYNTAX      Unsigned32
    UNITS       "kbtyes"
    MAX-ACCESS  read-only
    STATUS      current
    DESCRIPTION
        "Represents the size of WTP software."
    REFERENCE
        "Section 9.1. of CAPWAP Protocol Specification, RFC xxx."
    ::= { capwapWTPEntry 15 }

capwapWTPHwVersion OBJECT-TYPE
    SYNTAX      OCTET STRING(SIZE(32))
    MAX-ACCESS  read-only
    STATUS      current
    DESCRIPTION
        "Represents the version of WTP hardware."
    REFERENCE
        "Section 4.6.39. of CAPWAP Protocol Specification, RFC xxx."
    ::= { capwapWTPEntry 16 }

capwapWTPStaticIPEnable OBJECT-TYPE
    SYNTAX      TruthValue
    MAX-ACCESS  read-write
    STATUS      current
    DESCRIPTION
        "Represents whether the WTP should use a static IP address
         or not. A value of zero disables the static IP address,
         while a value of one enables it."
    REFERENCE
        "Section 4.6.49. of CAPWAP Protocol Specification, RFC xxx."
    DEFVAL      { false }
    ::= { capwapWTPEntry 17 }

capwapWTPStaticIP OBJECT-TYPE
    SYNTAX      IpAddress
    MAX-ACCESS  read-write
    STATUS      current
    DESCRIPTION
        "When capwapWTPStaticIPEnable is true, it represents the static
         IP address to assign to the WTP."
    REFERENCE
        "Section 4.6.49. of CAPWAP Protocol Specification, RFC xxx."
    ::= { capwapWTPEntry 18 }

capwapWTPNetmask OBJECT-TYPE
    SYNTAX      IpAddress
    MAX-ACCESS  read-write
    STATUS      current
    DESCRIPTION
        "When capwapWTPStaticIPEnable is true, it represents the netmask
         to assign to the WTP."
    REFERENCE
        "Section 4.6.49. of CAPWAP Protocol Specification, RFC xxx."
    ::= { capwapWTPEntry 19 }

capwapWTPGateway OBJECT-TYPE
    SYNTAX      IpAddress
    MAX-ACCESS  read-write
    STATUS      current
    DESCRIPTION
        "When capwapWTPStaticIPEnable is true, it represents the gateway
         to assign to the WTP."

    REFERENCE
        "Section 4.6.49. of CAPWAP Protocol Specification, RFC xxx."
    ::= { capwapWTPEntry 20 }

-- End of capwapWTPTable table


-- capwapRadioTable Table

capwapRadioTable OBJECT-TYPE
    SYNTAX      SEQUENCE OF CapwapRadioEntry
    MAX-ACCESS  not-accessible
    STATUS      current
    DESCRIPTION
        "The table will describe WTP and radio's relation-ship."
    ::= { capwapObjectState 4 }

capwapRadioEntry  OBJECT-TYPE
    SYNTAX      CapwapRadioEntry
    MAX-ACCESS  not-accessible
    STATUS      current
    DESCRIPTION
        "Each entry contains each radio's information for a specific
         WTP."
    INDEX { capwapWTPCurrId, capwapRadioId }
    ::= { capwapRadioTable 1 }

CapwapRadioEntry ::= SEQUENCE {
    capwapRadioId                    CapwapRadioId,
    capwapWTPRadioTemplateIfIndex    CapwapWTPRadioTemplateIfIndex,
    capwapWirelessBinding            INTEGER,
    capwapAdminStatusEnable          TruthValue,
    capwapOperStatus                 TruthValue
    }

capwapRadioId OBJECT-TYPE
    SYNTAX      CapwapRadioId
    MAX-ACCESS  accessible-for-notify
    STATUS      current
    DESCRIPTION
        "Represents the identifier of a radio on a WTP, and only
         requires unique on a WTP.
         For example, WTP A and WTP B will use same value for
         capwapRadioId for their first radio."
    REFERENCE
        "Section 4.6.31. of CAPWAP Protocol Specification, RFC xxx."
    ::= { capwapRadioEntry 1 }

capwapWTPRadioTemplateIfIndex OBJECT-TYPE
    SYNTAX      CapwapWTPRadioTemplateIfIndex
    MAX-ACCESS  read-write
    STATUS      current
    DESCRIPTION
        "Represents the ifindex for a interface of 'WTP radio template'
         interface type.
         Before WTPs connect to AC and get configuration, administrator
         will prepare configuration for them. For radio related
         configuration, administrator could create a logical interface
         in 'WTP radio template' interface type, and
         configure radio parameter under it.
         The configuration and statistic paramter depend on
         wireless binding type for radio.
         The 'WTP radio template interface' provides a way to
         uniquely identify each radio by logical at AC side.
         As most MIBs use ifindex to identify a interface for
         configuration and statistic data, for example, 802.11 MIB,
         it will be very easy to reuse other MIBs like 802.11 MIB by
         this way.
         Require IANA to assign a ifType for 'WTP radio template'."
    ::= { capwapRadioEntry 2 }

capwapWirelessBinding OBJECT-TYPE
    SYNTAX INTEGER { none(1), dot11(2), dot16(3), epc(4) }
    MAX-ACCESS  read-only
    STATUS      current
    DESCRIPTION
        "Represents the wireless binding type for radio.
         The following values are supported:
          none(1)  - No any wireless bingding defined.
          dot11(2) - IEEE 802.11.
          dot16(3) - IEEE 802.16.
          epc(4)   - EPCGlobal."
    REFERENCE
        "Section 4.3. of CAPWAP Protocol Specification, RFC xxx."
    ::= { capwapRadioEntry 3 }

capwapAdminStatusEnable OBJECT-TYPE
    SYNTAX      TruthValue
    MAX-ACCESS  read-write
    STATUS      current
    DESCRIPTION
        "Represents the administrator status of radio, whether
         it is enabled or not."
    REFERENCE
        "Section 4.6.31. of CAPWAP Protocol Specification, RFC xxx."
    DEFVAL      { true }
    ::= { capwapRadioEntry 4 }

capwapOperStatus OBJECT-TYPE
    SYNTAX      TruthValue
    MAX-ACCESS  read-only
    STATUS      current
    DESCRIPTION
        "Represents the operational status of radio, whether
         it is enabled or not."
    REFERENCE
        "Section 4.6.32. of CAPWAP Protocol Specification, RFC xxx."
    ::= { capwapRadioEntry 5 }

-- End of capwapRadioTable Table


-- capwapStationTable Table

capwapStationTable OBJECT-TYPE
    SYNTAX      SEQUENCE OF CapwapStationEntry
    MAX-ACCESS  not-accessible
    STATUS      current
    DESCRIPTION
        "This table contains the information of stations which are
         associating with the specific radio on the WTP."
    ::= { capwapObjectState 5 }

capwapStationEntry OBJECT-TYPE
    SYNTAX      CapwapStationEntry
    MAX-ACCESS  not-accessible
    STATUS      current
    DESCRIPTION
        "Each entry contains information of each station's association
         information."
    INDEX { capwapWTPCurrId, capwapRadioId, capwapStationId }
    ::= { capwapStationTable 1 }

CapwapStationEntry ::= SEQUENCE {
    capwapStationId           CapwapStationId,
    capwapStationAddedTime    TimeStamp,
    capwapStationVlanName     OCTET STRING
    }

capwapStationId OBJECT-TYPE
    SYNTAX      CapwapStationId
    MAX-ACCESS  not-accessible
    STATUS      current
    DESCRIPTION
        "Represents the identifier of the station."
    REFERENCE
        "Section 4.6.8. of CAPWAP Protocol Specification, RFC xxx."
    ::= { capwapStationEntry 1 }

capwapStationAddedTime OBJECT-TYPE
    SYNTAX      TimeStamp
    MAX-ACCESS  read-only
    STATUS      current
    DESCRIPTION
        "This is the time stamp for the very first time when the station
         is added."
    REFERENCE
        "Section 4.6.8. of CAPWAP Protocol Specification, RFC xxx."
    ::= { capwapStationEntry 2 }

capwapStationVlanName OBJECT-TYPE
    SYNTAX      OCTET STRING (SIZE(32))
    MAX-ACCESS  read-only
    STATUS      current
    DESCRIPTION
        "Represents Vlan name to which the station is associated."
    REFERENCE
        "Section 4.6.8. of CAPWAP Protocol Specification, RFC xxx."
    ::= { capwapStationEntry 3 }

-- End of capwapStationTable Table


--  capwapWTPRebootStatTable

capwapWTPRebootStatsTable  OBJECT-TYPE
    SYNTAX      SEQUENCE OF CapwapWTPRebootStatsEntry
    MAX-ACCESS  not-accessible
    STATUS      current
    DESCRIPTION
        "The table will provide WTP reboot statistic data."
    ::= {capwapObjectsStats 1 }

capwapWTPRebootStatsEntry  OBJECT-TYPE
    SYNTAX      CapwapWTPRebootStatsEntry
    MAX-ACCESS  not-accessible
    STATUS      current
    DESCRIPTION
        "Each entry of the table will provide the reboot statistic data
         for a specific WTP."
    INDEX { capwapWTPCurrId }
    ::= { capwapWTPRebootStatsTable 1 }

CapwapWTPRebootStatsEntry ::= SEQUENCE {
    capwapWTPRebootCount            Counter32,
    capwapWTPInitCount              Counter32,
    capwapWTPLinkFailureCount       Counter32,
    capwapWTPSwFailureCount         Counter32,
    capwapWTPHwFailureCount         Counter32,
    capwapWTPOtherFailureCount      Counter32,
    capwapWTPUnknownFailureCount    Counter32,
    capwapWTPLastFailureType        INTEGER
    }

capwapWTPRebootCount OBJECT-TYPE
    SYNTAX      Counter32
    MAX-ACCESS  read-only
    STATUS      current
    DESCRIPTION
        "Represents the number of reboots that have occurred due to a
         WTP crash.  A value of 65535 implies that this information is
         not available on the WTP."
    REFERENCE
        "Section 4.6.48. of CAPWAP Protocol Specification, RFC xxx."
    ::= { capwapWTPRebootStatsEntry 1 }

capwapWTPInitCount OBJECT-TYPE
    SYNTAX      Counter32
    MAX-ACCESS  read-only
    STATUS      current
    DESCRIPTION
        "Represents the number of reboots that have occurred at the
         request of a CAPWAP protocol message, such as a change in
         configuration that required a reboot or an explicit CAPWAP
         protocol reset request.  A value of 65535 implies that this
         information is not available on the WTP."
    REFERENCE
        "Section 4.6.48. of CAPWAP Protocol Specification, RFC xxx."
    ::= { capwapWTPRebootStatsEntry 2 }

capwapWTPLinkFailureCount OBJECT-TYPE
    SYNTAX      Counter32
    MAX-ACCESS  read-only
    STATUS      current
    DESCRIPTION
        "Represents the number of times that a CAPWAP protocol
         connection with an AC has failed due to link failure."
    REFERENCE
        "Section 4.6.48. of CAPWAP Protocol Specification, RFC xxx."
    ::= { capwapWTPRebootStatsEntry 3 }

capwapWTPSwFailureCount OBJECT-TYPE
    SYNTAX      Counter32
    MAX-ACCESS  read-only
    STATUS      current
    DESCRIPTION
        "Represents the number of times that a CAPWAP protocol
         connection with an AC has failed due to software related
         reasons."
    REFERENCE
        "Section 4.6.48. of CAPWAP Protocol Specification, RFC xxx."
    ::= { capwapWTPRebootStatsEntry 4 }

capwapWTPHwFailureCount OBJECT-TYPE
    SYNTAX      Counter32
    MAX-ACCESS  read-only
    STATUS      current
    DESCRIPTION
        "Represents the number of times that a CAPWAP protocol
         connection with an AC has failed due to hardware related
         reasons."
    REFERENCE
        "Section 4.6.48. of CAPWAP Protocol Specification, RFC xxx."
    ::= { capwapWTPRebootStatsEntry 5 }

capwapWTPOtherFailureCount OBJECT-TYPE
    SYNTAX      Counter32
    MAX-ACCESS  read-only
    STATUS      current
    DESCRIPTION
        "Represents the number of times that a CAPWAP protocol
         connection with an AC has failed due to known reasons, other
         than AC initiated, link, sofware or hardware failure."
    REFERENCE
        "Section 4.6.48. of CAPWAP Protocol Specification, RFC xxx."
    ::= { capwapWTPRebootStatsEntry 6 }

capwapWTPUnknownFailureCount OBJECT-TYPE
    SYNTAX      Counter32
    MAX-ACCESS  read-only
    STATUS      current
    DESCRIPTION
        "Represents the number of times that a CAPWAP protocol
         connection with an AC has failed for unknown reasons."
    REFERENCE
        "Section 4.6.48. of CAPWAP Protocol Specification, RFC xxx."
    ::= { capwapWTPRebootStatsEntry 7 }

capwapWTPLastFailureType OBJECT-TYPE
    SYNTAX      INTEGER {
                 notSupport(1), acInit(2), linkfailure(3),
                 swFailure(4), hwFailure(5),other(6), unknown(255)
                }
    MAX-ACCESS  read-only
    STATUS      current
    DESCRIPTION
        "The failure type of the most recent WTP failure.
         The following values are supported:
          notSupport(1)    - Not Supported,
          acInit(2)        - AC Initiated,
          linkFailure(3)   - Link Failure,
          swFailure(4)     - Software Failure,
          hwFailure(5)     - Hardware Failure,
          otherFailure(6)  - Other Failure,
          unknown(255)     - Unknown (e.g., WTP doesn't keep track
                             of info)."
    REFERENCE
        "Section 4.6.48. of CAPWAP Protocol Specification, RFC xxx."
    ::= { capwapWTPRebootStatsEntry 8 }

--  End of capwapWTPRebootStatsTable table


--  capwapRadioStatsTable table

capwapRadioStatsTable  OBJECT-TYPE
    SYNTAX      SEQUENCE OF CapwapRadioStatsEntry
    MAX-ACCESS  not-accessible
    STATUS      current
    DESCRIPTION
        "The table provides statistics on radio behavior and reasons
         why the WTP radio has been reset."
    ::= { capwapObjectsStats 2 }

capwapRadioStatsEntry  OBJECT-TYPE
    SYNTAX      CapwapRadioStatsEntry
    MAX-ACCESS  not-accessible
    STATUS      current
    DESCRIPTION
        "Each entry of the table will provide the statistic data of
         event happend on a specific radio of a WTP."
    INDEX { capwapWTPCurrId, capwapRadioId }
    ::= { capwapRadioStatsTable 1 }

CapwapRadioStatsEntry ::= SEQUENCE {
    capwapRadioResetCount            Counter32,
    capwapRadioSwFailCount           Counter32,
    capwapRadioHwFailCount           Counter32,
    capwapRadioOtherFailCount        Counter32,
    capwapRadioUnknownFailCount      Counter32,
    capwapRadioConfigUpdateCount     Counter32,
    capwapRadioChannelChangeCount    Counter32,
    capwapRadioBandChangeCount       Counter32,
    capwapRadioCurrentNoiseFloor     Integer32,
    capwapRadioDecryptErrorCount     Counter32,
    capwapRadioTxQueueLevel          Integer32,
    capwapRadioRFLinkFramesPerSec    Counter32,
    capwapRadioLastFailType          INTEGER }

capwapRadioResetCount OBJECT-TYPE
    SYNTAX      Counter32
    MAX-ACCESS  read-only
    STATUS      current
    DESCRIPTION
        "Represents the number of times that that the radio has been
         reset."
    REFERENCE
        "Section 4.6.47. of CAPWAP Protocol Specification, RFC xxx."
    ::= { capwapRadioStatsEntry 1 }

capwapRadioSwFailCount OBJECT-TYPE
    SYNTAX      Counter32
    MAX-ACCESS  read-only
    STATUS      current
    DESCRIPTION
        "Represents the number of times that the radio has failed due
         to software related reasons."
    REFERENCE
        "Section 4.6.47. of CAPWAP Protocol Specification, RFC xxx."
    ::= { capwapRadioStatsEntry 2 }

capwapRadioHwFailCount OBJECT-TYPE
    SYNTAX      Counter32
    MAX-ACCESS  read-only
    STATUS      current
    DESCRIPTION
        "Represents the number of times that the radio has failed due
         to hardware related reasons."
    REFERENCE
        "Section 4.6.47. of CAPWAP Protocol Specification, RFC xxx."
    ::= { capwapRadioStatsEntry 3 }

capwapRadioOtherFailCount OBJECT-TYPE
    SYNTAX      Counter32
    MAX-ACCESS  read-only
    STATUS      current
    DESCRIPTION
        "Represents the number of times that the radio has failed due to
         known reasons, other than software or hardware failure."
    REFERENCE
        "Section 4.6.47. of CAPWAP Protocol Specification, RFC xxx."
    ::= { capwapRadioStatsEntry 4 }

capwapRadioUnknownFailCount OBJECT-TYPE
    SYNTAX      Counter32
    MAX-ACCESS  read-only
    STATUS      current
    DESCRIPTION
        "Represents the number of times that the radio has failed for
         unknown reasons."
    REFERENCE
        "Section 4.6.47. of CAPWAP Protocol Specification, RFC xxx."
    ::= { capwapRadioStatsEntry 5 }

capwapRadioConfigUpdateCount OBJECT-TYPE
    SYNTAX      Counter32
    MAX-ACCESS  read-only
    STATUS      current
    DESCRIPTION
        "Represents the number of times that the radio configuration has
         been updated."
    REFERENCE
        "Section 4.6.47. of CAPWAP Protocol Specification, RFC xxx."
    ::= { capwapRadioStatsEntry 6 }

capwapRadioChannelChangeCount OBJECT-TYPE
    SYNTAX      Counter32
    MAX-ACCESS  read-only
    STATUS      current
    DESCRIPTION
        "Represents the number of times that the radio channel has
         been changed."
    REFERENCE
        "Section 4.6.47. of CAPWAP Protocol Specification, RFC xxx."
    ::= { capwapRadioStatsEntry 7 }

capwapRadioBandChangeCount OBJECT-TYPE
    SYNTAX      Counter32
    MAX-ACCESS  read-only
    STATUS      current
    DESCRIPTION
        "Represents the number of times that the radio has changed
         frequency bands."

    REFERENCE
        "Section 4.6.47. of CAPWAP Protocol Specification, RFC xxx."
    ::= { capwapRadioStatsEntry 8 }

capwapRadioCurrentNoiseFloor OBJECT-TYPE
    SYNTAX      Integer32
    UNITS       "dbm"
    MAX-ACCESS  read-only
    STATUS      current
    DESCRIPTION
        "Represents the noise floor of the radio receiver in units of
         dBm."
    ::= { capwapRadioStatsEntry 9 }

capwapRadioDecryptErrorCount OBJECT-TYPE
    SYNTAX      Counter32
    MAX-ACCESS  read-only
    STATUS      current
    DESCRIPTION
        "Represents the number of decryption errors that occurred on the
         WTP.  Note that this field is only valid in cases where the WTP
         provides encryption/decryption services."
    REFERENCE
        "Section 4.6.47. of CAPWAP Protocol Specification, RFC xxx."
    ::= { capwapRadioStatsEntry 10 }

capwapRadioTxQueueLevel OBJECT-TYPE
    SYNTAX      Integer32 (0..100)
    MAX-ACCESS  read-only
    STATUS      current
    DESCRIPTION
        "Represents the percentage of Wireless Transmit queue
         utilization,calaculated as the sum of utilized transmit queue
         lengths divided by the sum of maximum transmit queue lengths,
         multiplied by 100."
    REFERENCE
        "Section 4.6.46. of CAPWAP Protocol Specification, RFC xxx."
    ::= { capwapRadioStatsEntry 11 }

capwapRadioRFLinkFramesPerSec OBJECT-TYPE
    SYNTAX      Counter32
    MAX-ACCESS  read-only
    STATUS      current
    DESCRIPTION
        "Represents the number of frames transmitted or received per
         second by the WTP over the aur interface."
    REFERENCE
        "Section 4.6.46. of CAPWAP Protocol Specification, RFC xxx."
    ::= { capwapRadioStatsEntry 12 }

capwapRadioLastFailType OBJECT-TYPE
    SYNTAX      INTEGER {
                 notSupport(1),
                 swFailure(2),
                 hwFailure(3),
                 otherFailure(4),
                 unknown(255)
                }
    MAX-ACCESS  read-only
    STATUS      current
    DESCRIPTION
        "Represents the failure type of the most recent radio failure.
         The following values are supported:
          notSupport(1)   - Not Supported,
          swFailure(2)    - Software Failure,
          hwFailure(3)    - Hardware Failure,
          otherFailure(4) - Other Failure,
          unknown(255)    - Unknown."
    ::= { capwapRadioStatsEntry 13 }

--  End of capwapRadioStatsTable table


-- Notifications

capwapChannelUp NOTIFICATION-TYPE
    OBJECTS     { capwapWTPId,
                  capwapChannelType,
                  capwapWTPAuthenMethod }
    STATUS      current
    DESCRIPTION
        "This notification is sent by AC when a CAPWAP channel
         established.The notification is separated for data or control
         channel."
    ::= { capwapNotifications 1 }

capwapChannelDown NOTIFICATION-TYPE
    OBJECTS     { capwapWTPId, capwapChannelDownReason }
    STATUS      current
    DESCRIPTION
        "This notification is sent by AC when CAPWAP channel becomes
         down."
    ::= { capwapNotifications 2 }

capwapDecryptErrorReport NOTIFICATION-TYPE
    OBJECTS     { capwapWTPId,
                  capwapRadioId,
                  capwapIdEntryNum,
                  capwapStationIdList }
    STATUS      current
    DESCRIPTION
        "This notification is generated when a WTP that has occurred
         decryption error since the last report."
    REFERENCE
        "Section 4.6.15. of CAPWAP Protocol Specification, RFC xxx."
    ::= { capwapNotifications 3 }

capwapJoinFailure NOTIFICATION-TYPE
    OBJECTS     { capwapWTPId, capwapJoinFailureReason }
    STATUS      current
    DESCRIPTION
        "This notification is generated when a WTP fails to join."
    REFERENCE
        "Section 4.6.33. of CAPWAP Protocol Specification, RFC xxx."
    ::= { capwapNotifications 4 }

capwapImageUpgradeFailure NOTIFICATION-TYPE
    OBJECTS     { capwapWTPId, capwapImageFailureReason }
    STATUS      current
    DESCRIPTION
        "This notification is generated when a WTP fails to update
         software image."
    REFERENCE
        "Section 4.6.33. of CAPWAP Protocol Specification, RFC xxx."
    ::= { capwapNotifications 5 }

capwapConfigMsgError NOTIFICATION-TYPE
    OBJECTS     { capwapWTPId, capwapConfigMsgErrorType,
                  capwapMsgErrorElements }
    STATUS      current
    DESCRIPTION
        "This notification is generated when a WTP received message
         elements in the Configuration Status Response which it was
         unable to apply locally."
    REFERENCE
        "Section 4.6.34. of CAPWAP Protocol Specification, RFC xxx."
    ::= { capwapNotifications 6 }

capwapRadioOperableStatus NOTIFICATION-TYPE
    OBJECTS     { capwapWTPId,
                  capwapRadioId,
                  capwapRadioOperStatusFlag,
                  capwapRadioFailureReason }
    STATUS      current
    DESCRIPTION
        "The notification will notify which radio become inoperable
         or operable."
    REFERENCE
        "Section 4.6.32. of CAPWAP Protocol Specification, RFC xxx."
    ::= { capwapNotifications 7 }

capwapWTPAuthenticationFailure NOTIFICATION-TYPE
    OBJECTS     { capwapWTPId,
                  capwapChannelType,
                  capwapWTPAuthenMethod,
                  capwapWTPAuthenFailureReason }
    STATUS      current
    DESCRIPTION
        "The notification will notify the authentication failure event,
         and provides the reason for it."
    REFERENCE
        "Section 2.3.1. of CAPWAP Protocol Specification, RFC xxx."
    ::= { capwapNotifications 8 }


-- objects used only in notifications

capwapChannelType OBJECT-TYPE
    SYNTAX      CapwapChannelType
    MAX-ACCESS  accessible-for-notify
    STATUS      current
    DESCRIPTION
        "Represents the channel type for CAPWAP protocol."
    ::= { capwapNotifyVarObjects 1 }

capwapWTPAuthenMethod OBJECT-TYPE
    SYNTAX      CapwapWTPAuthenMethod
    MAX-ACCESS  accessible-for-notify
    STATUS      current
    DESCRIPTION
        "Represents authentication method for Channel."
    ::= { capwapNotifyVarObjects 2 }

capwapChannelDownReason OBJECT-TYPE
    SYNTAX      INTEGER { timeout(1), rekeyfailure(2), apReboot(3) }
    MAX-ACCESS  accessible-for-notify
    STATUS      current
    DESCRIPTION
        "Represents the reason for Channel down.
         The following values are supported:
          timeout(1)       - The keep alive is timeout,
          rekeyfailure(2)  - Rekey process is failed, channel will be
                             broken.
          apReboot(3)      - AC reboot WTP."
    ::= { capwapNotifyVarObjects 3 }

capwapIdEntryNum OBJECT-TYPE
    SYNTAX      Unsigned32
    MAX-ACCESS  accessible-for-notify
    STATUS      current
    DESCRIPTION
        "Represents the entry number of station id in the
         capwapStationIdList."
    REFERENCE
        "Section 4.6.15. of CAPWAP Protocol Specification, RFC xxx."
    ::= { capwapNotifyVarObjects 4 }

capwapStationIdList OBJECT-TYPE
    SYNTAX      OCTET STRING
    MAX-ACCESS  accessible-for-notify
    STATUS      current
    DESCRIPTION
        "Represents the list of station id."
    REFERENCE
        "Section 4.6.15. of CAPWAP Protocol Specification, RFC xxx."
    ::= { capwapNotifyVarObjects 5 }

capwapWTPAuthenFailureReason OBJECT-TYPE
    SYNTAX      INTEGER {
                 keyMismatch(1), invalidCA(2), micError(3),
                 timeout(4), unknown(8)
                }
    MAX-ACCESS  accessible-for-notify
    STATUS      current
    DESCRIPTION
        "Represents reason for WTP authorization failure.
         The following values are supported:
          keyMismatch(1) - WTP's and AC's key is not matched,
          invalidCA(2)   - ca is not valide,
          micError(3)    - detect mic error,
          timeout(4)     - WaitDTLS Timer is timeout,
          unknown(8)     - Unknown reason."
    REFERENCE
        "Section 2.3.1. of CAPWAP Protocol Specification, RFC xxx."
    ::= { capwapNotifyVarObjects 6 }

capwapRadioOperStatusFlag OBJECT-TYPE
    SYNTAX INTEGER { operable(1), inoperable(2) }
    MAX-ACCESS  accessible-for-notify
    STATUS      current
    DESCRIPTION
        "Represents the operation status of a radio.
         The following values are supported:
          inoperable(0) - To indicate radio is inoperable, and
                          capwapRadioFailureReason object will
                          give reason in details,
          operable(1)   - To indicate radio is operable."
    REFERENCE
        "Section 4.6.32. of CAPWAP Protocol Specification, RFC xxx."
    ::= { capwapNotifyVarObjects 7 }

capwapRadioFailureReason OBJECT-TYPE
    SYNTAX      INTEGER {
                 hwError(1), swError(2), adminSet(3), unknown(8)
                }
    MAX-ACCESS  accessible-for-notify
    STATUS      current
    DESCRIPTION
        "Represents errors caused by configuration operation.
         The following values are supported
          hwError(1)  - Radio Failure,
          swError(2)  - Software Failure,
          adminSet(3) - Administratively Set,
          unknown(8)  - Unknown reason."
    REFERENCE
        "Section 4.6.32. of CAPWAP Protocol Specification, RFC xxx."
    ::= { capwapNotifyVarObjects 8 }

capwapJoinFailureReason  OBJECT-TYPE
    SYNTAX      INTEGER {
                 unspecified(1), resDepletion(2), unknownSource(3),
                 incorrectData(4), sessionInUse(5), notSupportHw(6),
                 notSupportBinding(7)
                }
    MAX-ACCESS  accessible-for-notify
    STATUS      current
    DESCRIPTION
        "The following join failure types are supported:
         unspecified(1)       - unspecified failure reason,
         resDepletion(2)      - Resource Depletion,
         unknownSource(3)     - Unknown Source,
         incorrectData(4)     - Incorrect Data,
         sessionInUse(5)      - Session ID already in use,
         notSupportHw(6)      - WTP Hardware not supported,
         notSupportBinding(7) - Binding Not Supported."
    REFERENCE
        "Section 4.6.33. of CAPWAP Protocol Specification, RFC xxx."
    ::= { capwapNotifyVarObjects 9 }

capwapImageFailureReason  OBJECT-TYPE
   SYNTAX      INTEGER {
                invalidChecksum(1),
                invalidLength(2),
                other(3),
                inUse(4)
                }
   MAX-ACCESS  accessible-for-notify
   STATUS      current
   DESCRIPTION
        "The following software upgrade failure types are supported:
         invalidChecksum(1) - Invalid Checksum,
         invalidLength(2)   - Invalid Data Length,
         other(3)           - Other Error,
         inUse(4)           - Image Already Present."
   REFERENCE
        "Section 4.6.33. of CAPWAP Protocol Specification, RFC xxx."
   ::= { capwapNotifyVarObjects 10 }

capwapConfigMsgErrorType  OBJECT-TYPE
   SYNTAX      INTEGER {
                unknownElement(1), unsupportedElement(2),
                unknownValue(3), unsupportedValue(4)
               }
   MAX-ACCESS  accessible-for-notify
   STATUS      current
   DESCRIPTION
        "The following software upgrade failure types are supported:
         unknownElement(1)     - Unknown Message Element,
         unsupportedElement(2) - Unsupported Message Element,
         unknownValue(3)       - Unknown Message Element Value,
         unsupportedValue(4)   - Unsupported Message Element Value."
   REFERENCE
        "Section 4.6.34. of CAPWAP Protocol Specification, RFC xxx."
   ::= { capwapNotifyVarObjects 11 }

capwapMsgErrorElements  OBJECT-TYPE
   SYNTAX      DisplayString
   MAX-ACCESS  accessible-for-notify
   STATUS      current
   DESCRIPTION
        "Represents the message element sent by the AC in the
         Configuration Status Response message that caused the error."
   REFERENCE
        "Section 4.6.34. of CAPWAP Protocol Specification, RFC xxx."
   ::= { capwapNotifyVarObjects 12 }

-- Conformance statements
-- Module Conformance

capwapGroups OBJECT IDENTIFIER
    ::= { capwapConformance 1 }

capwapCompliances OBJECT IDENTIFIER
    ::= { capwapConformance 2 }

-- Object and Notification groups

capwapACNodeGroup    OBJECT-GROUP
    OBJECTS {
        capwapACWTPSessions,
        capwapACWTPSessionsLimit,
        capwapACStationSessions,
        capwapACStationSessionsLimit,
        capwapACDataChannelSecOptions,
        capwapACWTPAuthenOptions,
        capwapACHwVersion,
        capwapACSwVersion
    }
    STATUS  current
    DESCRIPTION
        "The collection of objects which are used to represent
         basic property for AC from CAPWAP protocol perspective."
    ::= { capwapGroups 1 }

capwapWTPStateGroup    OBJECT-GROUP
    OBJECTS {
        capwapWTPIPAddress,
        capwapWTPSerialId,
        capwapWTPState
    }
    STATUS  current
    DESCRIPTION
        "The collection of objects which are used to represent
         WTP state information."
    ::= { capwapGroups 2 }

capwapWTPsGroup    OBJECT-GROUP
    OBJECTS {
        capwapWTPFallbackEnable,
        capwapWTPACNameList,
        capwapMaxFailedDTLSSessionRetry,
        capwapWTPIdleTimeout,
        capwapWTPMaxDiscoveries,
        capwapWTPMaxRetransmit,
        capwapWTPReportInterval,
        capwapWTPName,
        capwapWTPLocation,
        capwapWTPManufacturerId,
        capwapWTPModelId,
        capwapWTPTunnelModeOptions,
        capwapWTPMACTypeOptions,
        capwapWTPDiscoveryType,
        capwapWTPRadiosInUseNumber,
        capwapWTPRadioNumLimit,
        capwapWTPSwVersion,
        capwapWTPSwSize,
        capwapWTPHwVersion
    }
    STATUS  current
    DESCRIPTION
        "The collection of objects which are used to represent
         configuration,version and property information for WTP
         in running state."
    ::= { capwapGroups 3 }

capwapRadiosGroup    OBJECT-GROUP
    OBJECTS {
        capwapWTPRadioTemplateIfIndex,
        capwapWirelessBinding,
        capwapAdminStatusEnable,
        capwapOperStatus
    }
    STATUS  current
    DESCRIPTION
        "The collection of objects which are used to represent
         wireless binding type, administrator status and operational
         status for radio."
    ::= { capwapGroups 4 }

capwapStationsGroup    OBJECT-GROUP
    OBJECTS {
        capwapStationAddedTime,
        capwapStationVlanName
    }
    STATUS  current
    DESCRIPTION
        "The collection of objects which are used to represent
         stations' basic property."
    ::= { capwapGroups 5 }

capwapWTPsPhysicalGroup   OBJECT-GROUP
    OBJECTS {
        capwapWTPBoardId,
        capwapWTPBoardRevision,
        capwapWTPBaseMACAddress
    }
    STATUS  current
    DESCRIPTION
        "Collection of objects that represent hardware information of
         WTP."
    ::= { capwapGroups 6 }

capwapWTPsLayer3Group   OBJECT-GROUP
    OBJECTS {
        capwapWTPStaticIPEnable,
        capwapWTPStaticIP,
        capwapWTPNetmask,
        capwapWTPGateway
    }
    STATUS  current
    DESCRIPTION
        "Collection of objects that represent layer3 information of
         WTP."
    ::= { capwapGroups 7 }

capwapWTPRebootStatsGroup    OBJECT-GROUP
    OBJECTS {
        capwapWTPRebootCount,
        capwapWTPInitCount,
        capwapWTPLinkFailureCount,
        capwapWTPSwFailureCount,
        capwapWTPHwFailureCount,
        capwapWTPOtherFailureCount,
        capwapWTPUnknownFailureCount,
        capwapWTPLastFailureType
    }
    STATUS  current
    DESCRIPTION
        "The collection of objects which are used for collecting
         WTP reboot count, link failure count, hardware failure
         count and so on."
    ::= { capwapGroups 8 }

capwapRadioStatsGroup    OBJECT-GROUP
    OBJECTS {
        capwapRadioResetCount,
        capwapRadioSwFailCount,
        capwapRadioHwFailCount,
        capwapRadioOtherFailCount,
        capwapRadioUnknownFailCount,
        capwapRadioConfigUpdateCount,
        capwapRadioChannelChangeCount,
        capwapRadioBandChangeCount,
        capwapRadioCurrentNoiseFloor,
        capwapRadioDecryptErrorCount,
        capwapRadioTxQueueLevel,
        capwapRadioRFLinkFramesPerSec,
        capwapRadioLastFailType
    }
    STATUS  current
    DESCRIPTION
        "The collection of objects which are used for collecting
         radio reset count, channel change count, hardware failure
         count and so on"
    ::= { capwapGroups 9 }

capwapNofificationGroup    NOTIFICATION-GROUP
    NOTIFICATIONS {
        capwapChannelUp,
        capwapChannelDown,
        capwapDecryptErrorReport,
        capwapJoinFailure,
        capwapImageUpgradeFailure,
        capwapConfigMsgError,
        capwapRadioOperableStatus,
        capwapWTPAuthenticationFailure
    }
    STATUS  current
    DESCRIPTION
        "Collection of notifications in this MIB."
    ::= { capwapGroups 10 }

capwapNotifyVarGroup    OBJECT-GROUP
    OBJECTS {
        capwapWTPId,
        capwapRadioId,
        capwapChannelType,
        capwapWTPAuthenMethod,
        capwapChannelDownReason,
        capwapIdEntryNum,
        capwapStationIdList,
        capwapWTPAuthenFailureReason,
        capwapRadioOperStatusFlag,
        capwapRadioFailureReason,
        capwapJoinFailureReason,
        capwapImageFailureReason,
        capwapConfigMsgErrorType,
        capwapMsgErrorElements
    }
    STATUS  current
    DESCRIPTION
        "Objects used for notification."
    ::= { capwapGroups 11 }


-- Compliance statements

capwapFullCompliance MODULE-COMPLIANCE
   STATUS current
   DESCRIPTION
       "Compliance statement for agents that support the
        configuration and monitoring of CAPWAP MIB."
   MODULE -- this module

      MANDATORY-GROUPS    { capwapACNodeGroup,
                            capwapWTPStateGroup,
                            capwapWTPsGroup,
                            capwapRadiosGroup,
                            capwapStationsGroup }
      GROUP capwapWTPsPhysicalGroup
      DESCRIPTION
          "This group is optional."

      GROUP capwapWTPsLayer3Group
      DESCRIPTION
          "This group is optional."

      GROUP capwapWTPRebootStatsGroup
      DESCRIPTION
          "This group is mandatory."

      GROUP capwapRadioStatsGroup
      DESCRIPTION
          "This group is mandatory."

      GROUP capwapNofificationGroup
      DESCRIPTION
          "This group is optional."

      GROUP capwapNotifyVarGroup
      DESCRIPTION
          "This group is optional. If capwapNofificationGroup is
           supported, this group must be implemented."

      OBJECT      capwapWirelessBinding
      SYNTAX      INTEGER { none(1) }
      DESCRIPTION
          "A value other than none(1) need not be supported if there is
           no wireless binding defined for technologies used."
   ::= { capwapCompliances 1 }

END

-- 
--    Copyright (C) The IETF Trust (2007).
-- 
--    This document is subject to the rights, licenses and restrictions
--    contained in BCP 78, and except as set forth therein, the authors
--    retain all their rights.
-- 
--    This document and the information contained herein are provided
--    on an "AS IS" basis and THE CONTRIBUTOR, THE ORGANIZATION HE/SHE
--    REPRESENTS OR IS SPONSORED BY (IF ANY), THE INTERNET SOCIETY,
--    THE IETF TRUST AND
--    THE INTERNET ENGINEERING TASK FORCE DISCLAIM ALL WARRANTIES,
--    EXPRESS OR IMPLIED, INCLUDING BUT NOT LIMITED TO ANY WARRANTY THAT
--    THE USE OF THE INFORMATION HEREIN WILL NOT INFRINGE ANY RIGHTS OR
--    ANY IMPLIED WARRANTIES OF MERCHANTABILITY OR FITNESS FOR A
--    PARTICULAR PURPOSE.
-- 
-- Intellectual Property
-- 
--    The IETF takes no position regarding the validity or scope of any
--    Intellectual Property Rights or other rights that might be claimed
--    to pertain to the implementation or use of the technology
--    described in this document or the extent to which any license
--    under such rights might or might not be available; nor does it
--    represent that it has made any independent effort to identify any
--    such rights.  Information on the procedures with respect to
--    rights in RFC documents can be found in BCP 78 and BCP 79.
-- 
--    Copies of IPR disclosures made to the IETF Secretariat and any
--    assurances of licenses to be made available, or the result of an
--    attempt made to obtain a general license or permission for the use
--    of such proprietary rights by implementers or users of this
--    specification can be obtained from the IETF on-line IPR repository
--    at http://www.ietf.org/ipr.
-- 
--    The IETF invites any interested party to bring to its attention
--    any copyrights, patents or patent applications, or other
--    proprietary rights that may cover technology that may be required
--    to implement this standard.  Please address the information to the
--    IETF at ietf-ipr@ietf.org.
