--
-- ComtechEFData.my
-- MIB generated by MG-SOFT Visual MIB Builder Version 2.1 Build 199
-- Friday, August 20, 2004 at 10:31:40
--

	ComtechEFData DEFINITIONS ::= BEGIN

		IMPORTS 
			enterprises, MODULE-IDENTITY			
				FROM SNMPv2-SMI;
	
	
		comtechEFData MODULE-IDENTITY
			LAST-UPDATED "200402121600Z"
			ORGANIZATION
				"Comtech EF Data Corp."
			CONTACT-INFO
				"Comtech EF Data Corp.
				2114 W 7th Street
				Tempe, AZ 85281 USA
				
				tel: 480 333-2200
				fax: 480 333-2540
				web: http://www.comtechefdata.com/"
			DESCRIPTION
				"Module for products of Comtech EF Data Corp."
			::= { enterprises 6247 }
		
	
--
-- Node definitions
--
	
	
	END

--
-- ComtechEFData.my
--
