--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPDOT1D-MIB DEFINITIONS ::= BEGIN
IMPORTS
	enterprises, NetworkAddress, IpAddress,
	Counter, Gauge, TimeTicks, DisplayString
		FROM RFC1155-SMI
	OBJECT-TYPE
		FROM RFC-1212;
-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.
-- Similarly, all representations of Bridge-Id in this MIB Module
-- use, as a textual convention (i.e. this convention does not affect
-- their encoding), the data type:

BridgeId ::= OCTET STRING (SIZE (8))   -- the Bridge-Identifier as
                                       -- used in the Spanning Tree
-- Protocol to uniquely identify a bridge.  Its first two octets
-- (in network byte order) contain a priority value and its last
-- 6 octets contain the MAC address used to refer to a bridge in a
-- unique fashion (typically, the numerically smallest MAC address
-- of all ports on the bridge).

-- Several objects in this MIB module represent values of timers
-- used by the Spanning Tree Protocol.  In this MIB, these timers
-- have values in units of hundreths of a second (i.e. 1/100 secs).
-- These timers, when stored in a Spanning Tree Protocol's BPDU,
-- are in units of 1/256 seconds.  Note, however, that 802.1d/D9
-- specifies a settable granularity of no more than 1 second for
-- these timers.  To avoid ambiguity, a data type is defined here
-- as a textual convention and all representation of these timers
-- in this MIB module are defined using this data type.  An algorithm
-- is also defined for converting between the different units, to
-- ensure a timer's value is not distorted by multiple conversions.
-- The data type is:

Timeout ::= INTEGER      -- a STP timer in units of 1/100 seconds

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are done
-- in the order specified (i.e., multiply first, divide second).
--




chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }


-- The chipBridge Group:
-- 
-- The following group is specific to the Chipcom bridge products..
--
-- 

chipBridgeSideSwitchMode OBJECT-TYPE
	SYNTAX INTEGER {
		enabled(1),
		disabled(2)
		}
	ACCESS read-only
	STATUS mandatory
	DESCRIPTION
		"The state of the side switch feature."
	::= { chipBridge 1 }



-- groups in the Bridge MIB

dot1dBase     OBJECT IDENTIFIER ::= { dot1dBridge 1 }

dot1dStp      OBJECT IDENTIFIER ::= { dot1dBridge 2 }

dot1dTp       OBJECT IDENTIFIER ::= { dot1dBridge 4 }

dot1dStatic   OBJECT IDENTIFIER ::= { dot1dBridge 5 }


-- the dot1dBase group

-- Implementation of the dot1dBase group is mandatory for all
-- bridges.

dot1dBaseBridgeAddress OBJECT-TYPE
	SYNTAX  MacAddress
 	ACCESS  read-only
	STATUS  mandatory
	DESCRIPTION
		"The MAC address used by this bridge when it must
		be referred to in a unique fashion.   It is
		recommended that this be the numerically smallest
		MAC address of all ports that belong to this
		bridge.  However it is only required to be unique.
		When concatenated with dot1dStpPriority a unique
		BridgeIdentifier is formed which is used in the
		Spanning Tree Protocol."
	REFERENCE
		"P802.1d/D9, July 14, 1989: Sections 6.4.1.1.3 and 3.12.5"
	::= { dot1dBase 1 }

dot1dBaseNumPorts OBJECT-TYPE
	SYNTAX  INTEGER
 	ACCESS  read-only
	STATUS  mandatory
	DESCRIPTION
		"The number of ports controlled by this bridging
		entity."
	REFERENCE
		"P802.1d/D9, July 14, 1989: Section 6.4.1.1.3"
	::= { dot1dBase 2 }

dot1dBaseType OBJECT-TYPE
	SYNTAX  INTEGER {
		unknown(1),
		transparent-only(2),
		sourceroute-only(3),
            	srt(4)
		}
 	ACCESS  read-only
	STATUS  mandatory
	DESCRIPTION
		"Indicates what type of bridging this bridge can
		perform.  If a bridge is actually performing a
		certain type of bridging this will be indicated by
		entries in the port table for the given type."
	::= { dot1dBase 3 }

-- The Generic Bridge Port Table

dot1dBasePortTable OBJECT-TYPE
	SYNTAX  SEQUENCE OF Dot1dBasePortEntry
 	ACCESS  not-accessible
	STATUS  mandatory
	DESCRIPTION
		"A table that contains generic information about
		every port that is associated with this bridge.
		Transparent, source-route, and srt ports are
		included."
	::= { dot1dBase 4 }

dot1dBasePortEntry OBJECT-TYPE
	SYNTAX  Dot1dBasePortEntry
 	ACCESS  not-accessible
	STATUS  mandatory
	DESCRIPTION
		"A list of information for each port of the
		bridge."
	REFERENCE
		"P802.1d/D9, July 14, 1989: Section 6.4.2, 6.6.1"
              INDEX  { dot1dBasePort }
	::= { dot1dBasePortTable 1 }

Dot1dBasePortEntry ::=
	SEQUENCE {
		dot1dBasePort
			INTEGER,
		dot1dBasePortIfIndex
			INTEGER,
		dot1dBasePortCircuit
			OBJECT IDENTIFIER,
		dot1dBasePortDelayExceededDiscards
			Counter,
		dot1dBasePortMtuExceededDiscards
			Counter
		}

dot1dBasePort OBJECT-TYPE
	SYNTAX  INTEGER
 	ACCESS  read-only
	STATUS  mandatory
	DESCRIPTION
		"The port number of the port for which this entry
		contains bridge management information."
	::= { dot1dBasePortEntry 1 }

dot1dBasePortIfIndex OBJECT-TYPE
	SYNTAX  INTEGER
 	ACCESS  read-only
	STATUS  mandatory
	DESCRIPTION
		"The value of the instance of the ifIndex object,
		defined in [4,6], for the interface corresponding
		to this port."
	::= { dot1dBasePortEntry 2 }

dot1dBasePortCircuit OBJECT-TYPE
	SYNTAX  OBJECT IDENTIFIER
 	ACCESS  read-only
	STATUS  mandatory
	DESCRIPTION
		"For a port which (potentially) has the same value
		of dot1dBasePortIfIndex as another port on the
		same bridge, this object contains the name of an
		object instance unique to this port.  For example,
		in the case where multiple ports correspond one-
		to-one with multiple X.25 virtual circuits, this
		value might identify an (e.g., the first) object
		instance associated with the X.25 virtual circuit
		corresponding to this port.

		For a port which has a unique value of
		dot1dBasePortIfIndex, this object can have the
		value { 0 0 }."
	::= { dot1dBasePortEntry 3 }

dot1dBasePortDelayExceededDiscards OBJECT-TYPE
	SYNTAX  Counter
 	ACCESS  read-only
	STATUS  mandatory
	DESCRIPTION
		"The number of frames discarded by this port due
		to excessive transit delay through the bridge.  It
		is incremented by both transparent and source
		route bridges."
	REFERENCE
		"P802.1d/D9, July 14, 1989: Section 6.6.1.1.3"
	::= { dot1dBasePortEntry 4 }

dot1dBasePortMtuExceededDiscards OBJECT-TYPE
	SYNTAX  Counter
 	ACCESS  read-only
	STATUS  mandatory
	DESCRIPTION
		"The number of frames discarded by this port due
		to an excessive size.  It is incremented by both
		transparent and source route bridges."
	REFERENCE
		"P802.1d/D9, July 14, 1989: Section 6.6.1.1.3"
	::= { dot1dBasePortEntry 5 }


-- the dot1dStp group

-- Implementation of the dot1dStp group is optional.  It is
-- implemented by those bridges that support the Spanning Tree
-- Protocol.  Transparent, Source Route, and SRT bridges will
-- implement this group only if they support the Spanning Tree
-- Protocol.


dot1dStpProtocolSpecification OBJECT-TYPE
	SYNTAX  INTEGER {
		unknown(1),
		decLb100(2),
		ieee8021d(3)
		}
 	ACCESS  read-only
	STATUS  mandatory
	DESCRIPTION
		"An indication of what version of the Spanning
		Tree Protocol is being run.  The value
		'decLb100(2)' indicates the DEC LANbridge 100
		Spanning Tree protocol.  IEEE 802.1d
		implementations will return 'ieee8021d(3)'.  If
		future versions of the IEEE Spanning Tree Protocol
		are released that are incompatible with the
		current version a new value will be defined."
	::= { dot1dStp 1 }

dot1dStpPriority OBJECT-TYPE
	SYNTAX  INTEGER (0..65535)
 	ACCESS  read-write
	STATUS  mandatory
	DESCRIPTION
		"The value of the write-able portion of the Bridge
		ID, i.e., the first two octets of the (8 octet
		long) Bridge ID.  The other (last) 6 octets of the
		Bridge ID are given by the value of
		dot1dBaseBridgeAddress."
	REFERENCE
		"P802.1d/D9, July 14, 1989: Section 4.5.3.7"
	::= { dot1dStp 2 }

dot1dStpTimeSinceTopologyChange OBJECT-TYPE
	SYNTAX  TimeTicks
 	ACCESS  read-only
	STATUS  mandatory
	DESCRIPTION
		"The time (in hundredths of a second) since the
		last time a topology change was detected by the
		bridge entity."
	REFERENCE
		"P802.1d/D9, July 14, 1989: Section 6.8.1.1.3"
	::= { dot1dStp 3 }

dot1dStpTopChanges OBJECT-TYPE
	SYNTAX  Counter
 	ACCESS  read-only
	STATUS  mandatory
	DESCRIPTION
		"The total number of topology changes detected by
		this bridge since the management entity was last
		reset or initialized."
	REFERENCE
		"P802.1d/D9, July 14, 1989: Section 6.8.1.1.3"
	::= { dot1dStp 4 }

dot1dStpDesignatedRoot OBJECT-TYPE
	SYNTAX  BridgeId
 	ACCESS  read-only
	STATUS  mandatory
	DESCRIPTION
		"The bridge identifier of the root of the spanning
		tree as determined by the Spanning Tree Protocol
		as executed by this node.  This value is used as
		the Root Identifier parameter in all Configuration
		Bridge PDUs originated by this node."
	REFERENCE
		"P802.1d/D9, July 14, 1989: Section 4.5.3.1"
	::= { dot1dStp 5 }

dot1dStpRootCost OBJECT-TYPE
	SYNTAX  INTEGER
 	ACCESS  read-only
	STATUS  mandatory
	DESCRIPTION
		"The cost of the path to the root as seen from
		this bridge."
	REFERENCE
		"P802.1d/D9, July 14, 1989: Section 4.5.3.2"
	::= { dot1dStp 6 }

dot1dStpRootPort OBJECT-TYPE
	SYNTAX  INTEGER
 	ACCESS  read-only
	STATUS  mandatory
	DESCRIPTION
		"The port number of the port which offers the
		lowest cost path from this bridge to the root
		bridge."
	REFERENCE
		"P802.1d/D9, July 14, 1989: Section 4.5.3.3"
	::= { dot1dStp 7 }

dot1dStpMaxAge OBJECT-TYPE
	SYNTAX  Timeout
 	ACCESS  read-only
	STATUS  mandatory
	DESCRIPTION
		"The maximum age of Spanning Tree Protocol
		information learned from the network on any port
		before it is discarded, in units of hundredths of
		a second.  This is the actual value that this
		bridge is currently using."
	REFERENCE
		"P802.1d/D9, July 14, 1989: Section 4.5.3.4"
	::= { dot1dStp 8 }

dot1dStpHelloTime OBJECT-TYPE
	SYNTAX  Timeout
 	ACCESS  read-only
	STATUS  mandatory
	DESCRIPTION
		"The amount of time between the transmission of
		Configuration bridge PDUs by this node on any port
		when it is the root of the spanning tree or trying
		to become so, in units of hundredths of a second.
		This is the actual value that this bridge is
		currently using."
	REFERENCE
		"P802.1d/D9, July 14, 1989: Section 4.5.3.5"
	::= { dot1dStp 9 }

dot1dStpHoldTime OBJECT-TYPE
	SYNTAX  INTEGER
 	ACCESS  read-only
	STATUS  mandatory
	DESCRIPTION
		"This time value determines the interval length
		during which no more than two Configuration bridge
		PDUs shall be transmitted by this node, in units
		of hundredths of a second."
	REFERENCE
		"P802.1d/D9, July 14, 1989: Section 4.5.3.14"
	::= { dot1dStp 10 }

dot1dStpForwardDelay OBJECT-TYPE
	SYNTAX  Timeout
 	ACCESS  read-only
	STATUS  mandatory
	DESCRIPTION
		"This time value, measured in units of hundredths
		of a second, controls how fast a port changes its
		spanning state when moving towards the Forwarding
		state.  The value determines how long the port
		stays in a particular state before moving to the
		next state.  For example, how long a port stays in
		the Listening state when moving from Blocking to
		Learning.  This value is also used, when a
		topology change has been detected and is underway,
		to age all dynamic entries in the Forwarding
		Database.  [Note that this value is the one that
		this bridge is currently using, in contrast to
		dot1dStpBridgeForwardDelay which is the value that
		this bridge and all others would start using
		if/when this bridge were to become the root.]"
	REFERENCE
		"P802.1d/D9, July 14, 1989: Section 4.5.3.6"
	::= { dot1dStp 11 }

dot1dStpBridgeMaxAge OBJECT-TYPE
	SYNTAX  Timeout
 	ACCESS  read-write
	STATUS  mandatory
	DESCRIPTION
		"The value that all bridges use for MaxAge when
		this bridge is acting as the root.  Note that
		802.1d/D9 specifies that the range for this
		parameter is related to the value of
		dot1dStpBridgeHelloTime. The granularity of this
		timer is specified by 802.1d/D9 to be 1 second.
		An agent may return a badValue error if a set is
		attempted to a value which is not a whole number
		of seconds."
	REFERENCE
		"P802.1d/D9, July 14, 1989: Section 4.5.3.8"
	::= { dot1dStp 12 }

dot1dStpBridgeHelloTime OBJECT-TYPE
	SYNTAX  Timeout
 	ACCESS  read-write
	STATUS  mandatory
	DESCRIPTION
		"The value that all bridges use for HelloTime when
		this bridge is acting as the root.  The
		granularity of this timer is specified by
		802.1d/D9 to be 1 second.  An agent may return a
		badValue error if a set is attempted to a value
		which is not a whole number of seconds."
	REFERENCE
		"P802.1d/D9, July 14, 1989: Section 4.5.3.9"
	::= { dot1dStp 13 }

dot1dStpBridgeForwardDelay OBJECT-TYPE
	SYNTAX  Timeout
 	ACCESS  read-write
	STATUS  mandatory
	DESCRIPTION
		"The value that all bridges use for ForwardDelay
		when this bridge is acting as the root.  Note that
		802.1d/D9 specifies that the range for this
		parameter is related to the value of
		dot1dStpBridgeMaxAge.  The granularity of this
		timer is specified by 802.1d/D9 to be 1 second.
		An agent may return a badValue error if a set is
		attempted to a value which is not a whole number
		of seconds."
	REFERENCE
		"P802.1d/D9, July 14, 1989: Section 4.5.3.10"
	::= { dot1dStp 14 }


-- The Spanning Tree Port Table

dot1dStpPortTable OBJECT-TYPE
	SYNTAX  SEQUENCE OF Dot1dStpPortEntry
 	ACCESS  not-accessible
	STATUS  mandatory
	DESCRIPTION
		"A table that contains port-specific information
		for the Spanning Tree Protocol."
	::= { dot1dStp 15 }

dot1dStpPortEntry OBJECT-TYPE
	SYNTAX  Dot1dStpPortEntry
 	ACCESS  not-accessible
	STATUS  mandatory
	DESCRIPTION
		"A list of information maintained by every port
		about the Spanning Tree Protocol state for that
		port."
	INDEX   { dot1dStpPort }
	::= { dot1dStpPortTable 1 }

	Dot1dStpPortEntry ::=
	SEQUENCE {
        	dot1dStpPort
			INTEGER,
		dot1dStpPortPriority
			INTEGER,
		dot1dStpPortState
			INTEGER,
		dot1dStpPortEnable
			INTEGER,
		dot1dStpPortPathCost
			INTEGER,
		dot1dStpPortDesignatedRoot
			BridgeId,
		dot1dStpPortDesignatedCost
			INTEGER,
		dot1dStpPortDesignatedBridge
			BridgeId,
		dot1dStpPortDesignatedPort
			OCTET STRING,
		dot1dStpPortForwardTransitions
			Counter
		}

dot1dStpPort OBJECT-TYPE
	SYNTAX  INTEGER
 	ACCESS  read-only
	STATUS  mandatory
	DESCRIPTION
		"The port number of the port for which this entry
		contains Spanning Tree Protocol management
		information."
	REFERENCE
		"P802.1d/D9, July 14, 1989: Section 6.8.2.1.2"
	::= { dot1dStpPortEntry 1 }

dot1dStpPortPriority OBJECT-TYPE
	SYNTAX  INTEGER
 	ACCESS  read-write
	STATUS  mandatory
	DESCRIPTION
		"The value of the priority field which is
		contained in the first (in network byte order)
		octet of the (2 octet long) Port ID.  The other
		octet of the Port ID is given by the value of
		dot1dStpPort."
	REFERENCE
		"P802.1d/D9, July 14, 1989: Section 4.5.5.1"
	::= { dot1dStpPortEntry 2 }

dot1dStpPortState OBJECT-TYPE
	SYNTAX  INTEGER {
		disabled(1),
		blocking(2),
		listening(3),
		learning(4),
		forwarding(5),
		broken(6)
		}
 	ACCESS  read-only
	STATUS  mandatory
	DESCRIPTION
		"The port's current state as defined by
		application of the Spanning Tree Protocol.  This
		state controls what action a port takes on
		reception of a frame.  If the bridge has detected
		a port that is malfunctioning it will place that
		port into the broken(6) state.  For ports which
		are disabled (see dot1dStpPortEnable), this object
		will have a value of disabled(1)."
	REFERENCE
		"P802.1d/D9, July 14, 1989: Section 4.5.5.2"
	::= { dot1dStpPortEntry 3 }

dot1dStpPortEnable OBJECT-TYPE
	SYNTAX  INTEGER {
		enabled(1),
		disabled(2)
		}
 	ACCESS  read-write
	STATUS  mandatory
	DESCRIPTION
		"The enabled/disabled status of the port."
	REFERENCE
		"P802.1d/D9, July 14, 1989: Section 4.5.5.2"
	::= { dot1dStpPortEntry 4 }

dot1dStpPortPathCost OBJECT-TYPE
	SYNTAX  INTEGER
 	ACCESS  read-write
	STATUS  mandatory
	DESCRIPTION
		"The contribution of this port to the path cost of
		paths towards the spanning tree root which include
		this port."
	REFERENCE
		"P802.1d/D9, July 14, 1989: Section 4.5.5.3"
	::= { dot1dStpPortEntry 5 }

dot1dStpPortDesignatedRoot OBJECT-TYPE
	SYNTAX  BridgeId
 	ACCESS  read-only
	STATUS  mandatory
	DESCRIPTION
		"The unique Bridge Identifier of the Bridge
		recorded as the Root in the Configuration BPDUs
		transmitted by the Designated Bridge for the
		segment to which the port is attached."
	REFERENCE
		"P802.1d/D9, July 14, 1989: Section 4.5.5.4"
	::= { dot1dStpPortEntry 6 }

dot1dStpPortDesignatedCost OBJECT-TYPE
	SYNTAX  INTEGER
 	ACCESS  read-only
	STATUS  mandatory
	DESCRIPTION
		"The path cost of the Designated Port of the
		segment connected to this port.  This value is
		compared to the Root Path Cost field in received
		bridge PDUs."
	REFERENCE
		"P802.1d/D9, July 14, 1989: Section 4.5.5.5"
	::= { dot1dStpPortEntry 7 }

dot1dStpPortDesignatedBridge OBJECT-TYPE
	SYNTAX  BridgeId
 	ACCESS  read-only
	STATUS  mandatory
	DESCRIPTION
		"The Bridge Identifier of the bridge which this
		port considers to be the Designated Bridge for
		this port's segment."
	REFERENCE
		"P802.1d/D9, July 14, 1989: Section 4.5.5.6"
	::= { dot1dStpPortEntry 8 }

dot1dStpPortDesignatedPort OBJECT-TYPE
	SYNTAX  OCTET STRING (SIZE (2))
 	ACCESS  read-only
	STATUS  mandatory
	DESCRIPTION
		"The Port Identifier of the port on the Designated
		Bridge for this port's segment."
	REFERENCE
		"P802.1d/D9, July 14, 1989: Section 4.5.5.7"
	::= { dot1dStpPortEntry 9 }

dot1dStpPortForwardTransitions OBJECT-TYPE
	SYNTAX  Counter
 	ACCESS  read-only
	STATUS  mandatory
	DESCRIPTION
		"The number of times this port has transitioned
		from the Learning state to the Forwarding state."
	::= { dot1dStpPortEntry 10 }


-- the dot1dTp group

-- Implementation of the dot1dTp group is optional.  It is
-- implemented by those bridges that support the transparent
-- bridging mode.  A transparent or SRT bridge will implement
-- this group.


dot1dTpLearnedEntryDiscards OBJECT-TYPE
	SYNTAX  Counter
 	ACCESS  read-only
	STATUS  mandatory
	DESCRIPTION
		"The total number of Forwarding Database entries,
		which have been or would have been learnt, but
		have been discarded due to a lack of space to
		store them in the Forwarding Database.  If this
		counter is increasing, it indicates that the
		Forwarding Database is regularly becoming full (a
		condition which has unpleasant performance effects
		on the subnetwork).  If this counter has a
		significant value but is not presently increasing,
		it indicates that the problem has been occurring
		but is not persistent."
	REFERENCE
		"P802.1d/D9, July 14, 1989: Section 6.7.1.1.3"
	::= { dot1dTp 1 }

dot1dTpAgingTime OBJECT-TYPE
	SYNTAX   INTEGER
 	ACCESS   read-write
	STATUS   mandatory
	DESCRIPTION
		"The timeout period in seconds for aging out
		dynamically learned forwarding information."
	REFERENCE
		"P802.1d/D9, July 14, 1989: Section 6.7.1.1.3"
	::= { dot1dTp 2 }


--  Port Table for Transparent Bridges

dot1dTpPortTable OBJECT-TYPE
	SYNTAX  SEQUENCE OF Dot1dTpPortEntry
 	ACCESS  not-accessible
	STATUS  mandatory
	DESCRIPTION
		"A table that contains information about every
		port that is associated with this transparent
		bridge."
	::= { dot1dTp 4 }

dot1dTpPortEntry OBJECT-TYPE
	SYNTAX  Dot1dTpPortEntry
 	ACCESS  not-accessible
	STATUS  mandatory
	DESCRIPTION
		"A list of information for each port of a
		transparent bridge."
	INDEX   { dot1dTpPort }
	::= { dot1dTpPortTable 1 }

Dot1dTpPortEntry ::=
	SEQUENCE {
		dot1dTpPort
			INTEGER,
		dot1dTpPortMaxInfo
			INTEGER,
		dot1dTpPortInFrames
			Counter,
		dot1dTpPortOutFrames
			Counter,
		dot1dTpPortInDiscards
			Counter
		}

dot1dTpPort OBJECT-TYPE
	SYNTAX  INTEGER
 	ACCESS  read-only
	STATUS  mandatory
	DESCRIPTION
		"The port number of the port for which this entry
		contains Transparent bridging management
		information."
	::= { dot1dTpPortEntry 1 }

-- It would be nice if we could use ifMtu as the size of the
-- largest INFO field, but we can't because ifMtu is defined
-- to be the size that the (inter-)network layer can use which
-- can differ from the MAC layer (especially if several layers
-- of encapsulation are used).


dot1dTpPortMaxInfo OBJECT-TYPE
	SYNTAX  INTEGER
 	ACCESS  read-only
	STATUS  mandatory
	DESCRIPTION
		"The maximum size of the INFO (non-MAC) field that
		this port will receive or transmit."
	::= { dot1dTpPortEntry 2 }

dot1dTpPortInFrames OBJECT-TYPE
	SYNTAX  Counter
 	ACCESS  read-only
	STATUS  mandatory
	DESCRIPTION
		"The number of frames that have been received by
		this port from its segment. Note that a frame
		received on the interface corresponding to this
		port is only counted by this object if and only if
		it is for a protocol being processed by the local
		bridging function."
	REFERENCE
		"P802.1d/D9, July 14, 1989: Section 6.6.1.1.3"
	::= { dot1dTpPortEntry 3 }

dot1dTpPortOutFrames OBJECT-TYPE
	SYNTAX  Counter
 	ACCESS  read-only
	STATUS  mandatory
	DESCRIPTION
		"The number of frames that have been transmitted
		by this port to its segment.  Note that a frame
		transmitted on the interface corresponding to this
		port is only counted by this object if and only if
		it is for a protocol being processed by the local
		bridging function."
	REFERENCE
		"P802.1d/D9, July 14, 1989: Section 6.6.1.1.3"
	::= { dot1dTpPortEntry 4 }

dot1dTpPortInDiscards OBJECT-TYPE
	SYNTAX   Counter
 	ACCESS   read-only
	STATUS   mandatory
	DESCRIPTION
		"Count of valid frames received which were
		discarded (i.e., filtered) by the Forwarding
		Process."
	REFERENCE
		"P802.1d/D9, July 14, 1989: Section 6.6.1.1.3"
	::= { dot1dTpPortEntry 5 }

-- Traps for use by Bridges

-- Traps for the Spanning Tree Protocol

newRoot TRAP-TYPE
	ENTERPRISE  dot1dBridge
-- Using this enterprise as it represents the
-- variable dot1dBridge in the implementation of
-- the experimental Bridge MIB Group under this
-- branch of the Chipcom Enterprise specific MIB.
	DESCRIPTION
		"The newRoot trap indicates that the sending agent
		has become the new root of the Spanning Tree; the
		trap is sent by a bridge soon after its election
		as the new root, e.g., upon expiration of the
		Topology Change Timer immediately subsequent to
		its election."
	::= 1

topologyChange TRAP-TYPE
	ENTERPRISE  dot1dBridge
		-- Using this enterprise as it represents the
		-- variable dot1dBridge in the implementation of
		-- the experimental Bridge MIB Group under this
		-- branch of the Chipcom Enterprise specific MIB.
	DESCRIPTION
		"A topologyChange trap is sent by a bridge when
		any of its configured ports transitions from the
		Learning state to the Forwarding state, or from
		the Forwarding state to the Blocking state.  The
		trap is not sent if a newRoot trap is sent for the
		same transition."
	::= 2

END
