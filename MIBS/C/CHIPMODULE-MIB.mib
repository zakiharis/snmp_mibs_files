--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPMODULE-MIB DEFINITIONS ::= BEGIN

IMPORTS
	enterprises, NetworkAddress, IpAddress,
	Counter, Gauge, TimeTicks, DisplayString
		FROM RFC1155-SMI
	OBJECT-TYPE
		FROM RFC-1212;


chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }


-- olSpecMods Group
-- 
-- This group contains the module and port tables specific to the 
-- particular module.  Each module is indexed by the olModType value.
-- For more information, please refer to the MIB information supplied
-- with each module.

-- olSpecMods Group takes the following object identifier format:
-- 
-- olSpecMods.<type>.<level>.1.<object>.<instance>
--
-- where :
-- 	<type> ::= the unique number identifying the type of this module
--			see olModType above.
--	<level> ::= module table (1) ||
-- 	 	    port table (2)   ||
--                  trunk  (3)       

--	1       ::= branch for entry, i.e. module entry or port entry
-- 	<object>::= the object ID as indicated in the MIB documentation for
--			this type module.
-- 	<instance> ::=
--			<slot> for module level ||
--			<slot>.<port> for port level ||
--			<slot>.<trunk> for trunk level

--			
--
--	The lexicographical ordering for this group is:
--
--	1. To walk through all of the instances associated 
--		particular module type.  That is, the group 
--		walks through a module type - all slots, before
--		walking to the next module type.  For example, if
--		module type A is in slot 1 & 5, and module type B
--		is in slot 3 (where A < B), then a tree walk would
--		yield A.1, A.3, and then B.3.
--
--	2. To walk through all of the resources of a particular module
--		before walking to the next module.  All ports and trunks
--		of a module are instantiated in the tree before the
--		the next module is instiated.
--


--
-- ONline Controller Module
--

ol50nnMCTLModTable OBJECT-TYPE
	SYNTAX SEQUENCE OF Ol50nnMCTLModEntry
	ACCESS not-accessible
	STATUS mandatory
	DESCRIPTION
		"A table that contains information about each 50nnM-CTL
		in the concentrator.  Note, current architecture will
		limit the number of instances to one per concentrator."
	::= { ol50nnMCTL 1 }

ol50nnMCTLModEntry OBJECT-TYPE
	SYNTAX Ol50nnMCTLModEntry
	ACCESS not-accessible
	STATUS mandatory
	DESCRIPTION
		"A list of information for each 50nnM-CTL module
		in the concentrator."
	INDEX { ol50nnMCTLModSlotIndex }
	::= { ol50nnMCTLModTable 1 }

Ol50nnMCTLModEntry ::= 
	SEQUENCE {
		ol50nnMCTLModSlotIndex
			INTEGER,
		ol50nnMCTLModTempStatus
			INTEGER
		}

ol50nnMCTLModSlotIndex OBJECT-TYPE
	SYNTAX INTEGER
	ACCESS read-only
	STATUS mandatory
	DESCRIPTION
		"The slot number for this module."
	::= { ol50nnMCTLModEntry 1 }

ol50nnMCTLModTempStatus OBJECT-TYPE
	SYNTAX INTEGER {
		okay(1),
		extremeTemp(2)
		}
	ACCESS read-only
	STATUS mandatory
	DESCRIPTION
		"The temperature as detected by the probes on this module."
	::= { ol50nnMCTLModEntry 2 }


ol51nnMMGTModTable OBJECT-TYPE
	SYNTAX SEQUENCE OF Ol51nnMMGTModEntry
	ACCESS not-accessible
	STATUS mandatory
	DESCRIPTION
		"A table that contains module information about each
		51nnM-MGT module in the concentrator."
	::= { ol51nnMMGT 1 }

ol51nnMMGTModEntry OBJECT-TYPE
	SYNTAX Ol51nnMMGTModEntry
	ACCESS not-accessible
	STATUS mandatory
	DESCRIPTION
		"A list of module information for each 51nnM-MGT module
		in the concentrator."
	INDEX { ol51nnMMGTModSlotIndex }
	::= { ol51nnMMGTModTable 1 }

Ol51nnMMGTModEntry ::= 
	SEQUENCE {
		ol51nnMMGTModSlotIndex
			INTEGER,
		ol51nnMMGTModMasterPriority
			INTEGER,
		ol51nnMMGTModMasterStatus
			INTEGER,
		ol51nnMMGTModStationAddr
			OCTET STRING
		}

ol51nnMMGTModSlotIndex OBJECT-TYPE
	SYNTAX INTEGER
	ACCESS read-only
	STATUS mandatory
	DESCRIPTION
		"The slot number of this module."
	::= { ol51nnMMGTModEntry 1 }

ol51nnMMGTModMasterPriority OBJECT-TYPE
	SYNTAX INTEGER {
		one(1),
		two(2),
		three(3),
		four(4),
		five(5),
		six(6),
		seven(7),
		eight(8),
		nine(9),
		ten(10)
		}	
	ACCESS read-write
	STATUS mandatory
	DESCRIPTION
		"The mastership priority of this agent.  Ten is the
		highest and one is the lowest.  Priority is
		only used when an election occurs.  Mastership is not
		preemptive unless the reset mastership command is used."
	::= { ol51nnMMGTModEntry 2 }

ol51nnMMGTModMasterStatus OBJECT-TYPE
	SYNTAX INTEGER {
		master(1),
		non-master(2),
		electing(3)
		}
	ACCESS read-only
	STATUS mandatory
	DESCRIPTION
		"The mastership status of this agent."
	::= { ol51nnMMGTModEntry 3 }

ol51nnMMGTModStationAddr OBJECT-TYPE
	SYNTAX OCTET STRING (SIZE(6))
	ACCESS read-only
	STATUS mandatory
	DESCRIPTION
		"A 6 octet address that uniquely identifies this module.
		The station address is the mac address of port 1.  Note
		that EMMs before v3.0 will have 00-00-00-00-00-00 as their
		station address."
	::= { ol51nnMMGTModEntry 4 }

ol51nnMMGTPortTable OBJECT-TYPE
	SYNTAX SEQUENCE OF Ol51nnMMGTPortEntry
	ACCESS not-accessible
	STATUS mandatory
	DESCRIPTION
		"A table of information that contains port-specific
		information for each port on each 51nnM-MGT module."
	::= { ol51nnMMGT 2 }

ol51nnMMGTPortEntry OBJECT-TYPE
	SYNTAX Ol51nnMMGTPortEntry
	ACCESS not-accessible
	STATUS mandatory
	DESCRIPTION
		"A list of information about a specific port on a 
		51nnM-MGT module."
	INDEX { ol51nnMMGTPortSlotIndex, ol51nnMMGTPortIndex }
	::= { ol51nnMMGTPortTable 1 }

Ol51nnMMGTPortEntry ::= 
	SEQUENCE {
		ol51nnMMGTPortSlotIndex
			INTEGER,			
		ol51nnMMGTPortIndex
			INTEGER,
		ol51nnMMGTIpAddress
			IpAddress
		}

ol51nnMMGTPortSlotIndex OBJECT-TYPE
	SYNTAX INTEGER
	ACCESS read-only
	STATUS mandatory
	DESCRIPTION
		"The slot number of this port's module."
	::= { ol51nnMMGTPortEntry 1 }


ol51nnMMGTPortIndex OBJECT-TYPE
	SYNTAX INTEGER
	ACCESS read-only
	STATUS mandatory
	DESCRIPTION
		"The port number of this port."
	::= { ol51nnMMGTPortEntry 2 }


ol51nnMMGTIpAddress OBJECT-TYPE
	SYNTAX IpAddress
	ACCESS read-only
	STATUS mandatory
	DESCRIPTION
		"The IP Address associated with this port."
	::= { ol51nnMMGTPortEntry 3 }

-- 
-- ONline Ethernet Synchronous Fiber Module
--


ol51nnMFIBModTable OBJECT-TYPE
	SYNTAX SEQUENCE OF Ol51nnMFIBModEntry
	ACCESS not-accessible
	STATUS mandatory
	DESCRIPTION
		"A table of module-specific information for each
		51nnM-FIB module in the concentrator."
	::= { ol51nnMFIB 1 }

ol51nnMFIBModEntry OBJECT-TYPE
	SYNTAX Ol51nnMFIBModEntry
	ACCESS not-accessible
	STATUS mandatory
	DESCRIPTION
		"A list of module-specific information associated
		with a particular 51nnM-FIB module in the concentrator."
	INDEX { ol51nnMFIBModSlotIndex }
	::= { ol51nnMFIBModTable 1 }

Ol51nnMFIBModEntry ::= 
	SEQUENCE {
		ol51nnMFIBModSlotIndex
			INTEGER,
		ol51nnMFIBModDipNetwork
			INTEGER,
		ol51nnMFIBModLLW
			INTEGER,
		ol51nnMFIBModDipLLW
			INTEGER
		}

ol51nnMFIBModSlotIndex OBJECT-TYPE
	SYNTAX INTEGER
	ACCESS read-only
	STATUS mandatory
	DESCRIPTION
		"The slot number of this module."
	::= { ol51nnMFIBModEntry 1 }

ol51nnMFIBModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMFIBModEntry 2 }

ol51nnMFIBModLLW OBJECT-TYPE
	SYNTAX INTEGER {
		enabled(1),
		disabled(2)
		}
	ACCESS read-write
	STATUS mandatory
	DESCRIPTION
		"The current state of this module's low light warning 
		configuration.	Enabling this feature causes the module to 
		check for low light and to issue a warning if low light is
		present.  Disabling low light has the advantage of faster
		redundancy switchover in the event of a port error."
	::= { ol51nnMFIBModEntry 3 }
	
ol51nnMFIBModDipLLW OBJECT-TYPE
	SYNTAX INTEGER {
		enabled(1),
		disabled(2)
		}
	ACCESS read-only
	STATUS mandatory
	DESCRIPTION
		"The low light warning configuration indicated by this module's
		dip switches."
	::= { ol51nnMFIBModEntry 4 }
	
ol51nnMFIBPortTable OBJECT-TYPE
	SYNTAX SEQUENCE OF Ol51nnMFIBPortEntry
	ACCESS not-accessible
	STATUS mandatory
	DESCRIPTION
		"A table of port-specific information for each port
		of each 51nnM-FIB module."
	::= { ol51nnMFIB 2 }

ol51nnMFIBPortEntry OBJECT-TYPE
	SYNTAX Ol51nnMFIBPortEntry
	ACCESS not-accessible
	STATUS mandatory
	DESCRIPTION
		"A list of information about a specific port on a 
		51nnM-FIB module."
	INDEX { ol51nnMFIBPortSlotIndex, ol51nnMFIBPortIndex }
	::= { ol51nnMFIBPortTable 1 }

Ol51nnMFIBPortEntry ::= 
	SEQUENCE {
		ol51nnMFIBPortSlotIndex
			INTEGER,			
		ol51nnMFIBPortIndex
			INTEGER,
		ol51nnMFIBPortAdminState
			INTEGER,
		ol51nnMFIBPortBuddySlot
			INTEGER,
		ol51nnMFIBPortBuddyPort
			INTEGER,
		ol51nnMFIBPortDipAdminState
			INTEGER
		}

	ol51nnMFIBPortSlotIndex OBJECT-TYPE
	SYNTAX INTEGER
	ACCESS read-only
	STATUS mandatory
	DESCRIPTION
		"The slot number of this port's module."
	::= { ol51nnMFIBPortEntry 1 }


ol51nnMFIBPortIndex OBJECT-TYPE
	SYNTAX INTEGER
	ACCESS read-only
	STATUS mandatory
	DESCRIPTION
		"The port number of this port."
	::= { ol51nnMFIBPortEntry 2 }


ol51nnMFIBPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFIBPortEntry 3 }

ol51nnMFIBPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFIBPortEntry 4 }

ol51nnMFIBPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFIBPortEntry 5 }


ol51nnMFIBPortDipAdminState OBJECT-TYPE
	SYNTAX INTEGER {
		enabled(1),
		disabled(2),
		redundant-primary(3),
		redundant-backup(4)
		}
	ACCESS read-only
	STATUS mandatory
	DESCRIPTION
		"The state of this port as indicated by the port's dip 
		switches."		
	::= { ol51nnMFIBPortEntry 6 }

--
-- ONline Ethernet 10BASE-T Module
--


ol51nnMUTPModTable OBJECT-TYPE
	SYNTAX SEQUENCE OF Ol51nnMUTPModEntry
	ACCESS not-accessible
	STATUS mandatory
	DESCRIPTION
		"A list of module-specific information associated
		with a particular 51nnM-UTP module in the concentrator."
	::= { ol51nnMUTP 1 }

ol51nnMUTPModEntry OBJECT-TYPE
	SYNTAX Ol51nnMUTPModEntry
	ACCESS not-accessible
	STATUS mandatory
	DESCRIPTION
		"A module entry containing objects that describe the 
		module level for that particular module."
	INDEX { ol51nnMUTPModSlotIndex }
	::= { ol51nnMUTPModTable 1 }

Ol51nnMUTPModEntry ::= 
	SEQUENCE {
		ol51nnMUTPModSlotIndex
			INTEGER,
		ol51nnMUTPModDipNetwork
			INTEGER,
		ol51nnMUTPModCrossover
			INTEGER,
		ol51nnMUTPModDipCrossover
			INTEGER,
		ol51nnMUTPModFFL
			INTEGER,
		ol51nnMUTPModDipFFL
			INTEGER
		}

ol51nnMUTPModSlotIndex OBJECT-TYPE
	SYNTAX INTEGER
	ACCESS read-only
	STATUS mandatory
	DESCRIPTION
		"The slot number of this module."
	::= { ol51nnMUTPModEntry 1 }

ol51nnMUTPModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMUTPModEntry 2 }

ol51nnMUTPModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ol51nnMUTPModEntry 3 }
	
ol51nnMUTPModDipCrossover OBJECT-TYPE
	SYNTAX INTEGER {
		crossed(1),
		uncrossed(2)
		}
	ACCESS read-only
	STATUS mandatory
	DESCRIPTION
		"The crossover configuration indicated by this module's
		dip switches."
	::= { ol51nnMUTPModEntry 4 }
	
ol51nnMUTPModFFL OBJECT-TYPE
	SYNTAX INTEGER {
		eight-bits(1),
		seven-bits(2)
		}
	ACCESS read-write
	STATUS mandatory
	DESCRIPTION
		"The number of bits to store in the repeater's fifo
		buffer.  See the module user's guide for more information."
	::= { ol51nnMUTPModEntry 5 }

ol51nnMUTPModDipFFL OBJECT-TYPE
	SYNTAX INTEGER {
		eight-bits(1),
		seven-bits(2)
		}
	ACCESS read-write
	STATUS mandatory
	DESCRIPTION
		"The fifo fill level as indicated by this module's dip
		switches."
	::= { ol51nnMUTPModEntry 6 }

ol51nnMUTPPortTable			 OBJECT-TYPE
	SYNTAX SEQUENCE OF Ol51nnMUTPPortEntry
	ACCESS not-accessible
	STATUS mandatory
	DESCRIPTION
		"A table of port-specific information for each port of
		this module type."
	::= { ol51nnMUTP 2 }

ol51nnMUTPPortEntry OBJECT-TYPE
	SYNTAX Ol51nnMUTPPortEntry
	ACCESS not-accessible
	STATUS mandatory
	DESCRIPTION
		"A port entry containing objects that describe this port."
	INDEX { ol51nnMUTPPortSlotIndex, ol51nnMUTPPortIndex }
	::= { ol51nnMUTPPortTable 1 }

Ol51nnMUTPPortEntry ::= 
	SEQUENCE {
		ol51nnMUTPPortSlotIndex
			INTEGER,			
		ol51nnMUTPPortIndex
			INTEGER,
		ol51nnMUTPPortAdminState
			INTEGER,
		ol51nnMUTPPortBuddySlot
			INTEGER,
		ol51nnMUTPPortBuddyPort
			INTEGER,
		ol51nnMUTPPortDipAdminState
			INTEGER,
		ol51nnMUTPPortLinkInteg
			INTEGER,
		ol51nnMUTPPortDipLinkInteg
			INTEGER,
		ol51nnMUTPPortSquelch
			INTEGER,
		ol51nnMUTPPortDipSquelch
			INTEGER
		}

	ol51nnMUTPPortSlotIndex OBJECT-TYPE
	SYNTAX INTEGER
	ACCESS read-only
	STATUS mandatory
	DESCRIPTION
		"The slot number of this port's module."
	::= { ol51nnMUTPPortEntry 1 }


ol51nnMUTPPortIndex OBJECT-TYPE
	SYNTAX INTEGER
	ACCESS read-only
	STATUS mandatory
	DESCRIPTION
		"The port number of this port."
	::= { ol51nnMUTPPortEntry 2 }

ol51nnMUTPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMUTPPortEntry 3 }

ol51nnMUTPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMUTPPortEntry 4 }

ol51nnMUTPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMUTPPortEntry 5 }

ol51nnMUTPPortDipAdminState OBJECT-TYPE
	SYNTAX INTEGER {
		enabled(1),
		disabled(2)
		}
	ACCESS read-only
	STATUS mandatory
	DESCRIPTION
		"The state of this port as indicated by the port's dip 
		switches."		
	::= { ol51nnMUTPPortEntry 6 }

ol51nnMUTPPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ol51nnMUTPPortEntry 7 }

ol51nnMUTPPortDipLinkInteg OBJECT-TYPE
	SYNTAX INTEGER {
		enabled(1),
		disabled(2)
		}
	ACCESS read-only
	STATUS mandatory
	DESCRIPTION
		"The link integrity configuration as indicated by this
		port's dip switches."
	::= { ol51nnMUTPPortEntry 8 }

ol51nnMUTPPortSquelch	 OBJECT-TYPE
	SYNTAX INTEGER {
		normal(1),		-- high squelch
		low(2)
		}
	ACCESS read-write
	STATUS mandatory
	DESCRIPTION
		"The port's squelch configuration.  See the module's
		user's guide for more information."
	::= { ol51nnMUTPPortEntry 9 }

ol51nnMUTPPortDipSquelch	 OBJECT-TYPE
	SYNTAX INTEGER {
		normal(1),		-- high squelch
		low(2)
		}
	ACCESS read-only
	STATUS mandatory
	DESCRIPTION
		"The port's squelch configuration as indicated by this
		port's dip switches."
	::= { ol51nnMUTPPortEntry 10 }


--
-- ONline Ethernet 10BASE-T Module
--

ol51nnMTPModTable OBJECT-TYPE
	SYNTAX SEQUENCE OF Ol51nnMTPModEntry
	ACCESS not-accessible
	STATUS mandatory
	DESCRIPTION
		"A table of module-specific information for each 
		51nnM-TP module in the concentrator."
	::= { ol51nnMTP 1 }

ol51nnMTPModEntry OBJECT-TYPE
	SYNTAX Ol51nnMTPModEntry
	ACCESS not-accessible
	STATUS mandatory
	DESCRIPTION
		"A list of module-specific information about a 
		specific 51nnM-TP module in the concentrator."
	INDEX { ol51nnMTPModSlotIndex }
	::= { ol51nnMTPModTable 1 }

Ol51nnMTPModEntry ::= 
	SEQUENCE {
		ol51nnMTPModSlotIndex
			INTEGER,
		ol51nnMTPModDipNetwork
			INTEGER,
		ol51nnMTPModCrossover
			INTEGER,
		ol51nnMTPModDipCrossover
			INTEGER
		}

ol51nnMTPModSlotIndex OBJECT-TYPE
	SYNTAX INTEGER
	ACCESS read-only
	STATUS mandatory
	DESCRIPTION
		"The slot number of this module."
	::= { ol51nnMTPModEntry 1 }

ol51nnMTPModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMTPModEntry 2 }

ol51nnMTPModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ol51nnMTPModEntry 3 }
	
ol51nnMTPModDipCrossover OBJECT-TYPE
	SYNTAX INTEGER {
		crossed(1),
		uncrossed(2)
		}
	ACCESS read-only
	STATUS mandatory
	DESCRIPTION
		"The crossover configuration indicated by this module's
		dip switches."
	::= { ol51nnMTPModEntry 4 }
	

ol51nnMTPPortTable			 OBJECT-TYPE
	SYNTAX SEQUENCE OF Ol51nnMTPPortEntry
	ACCESS not-accessible
	STATUS mandatory
	DESCRIPTION
		"A table of port-specific information for each port of
		this module type."
	::= { ol51nnMTP 2 }

ol51nnMTPPortEntry OBJECT-TYPE
	SYNTAX Ol51nnMTPPortEntry
	ACCESS not-accessible
	STATUS mandatory
	DESCRIPTION
		"A port entry containing objects that describe this port."
	INDEX { ol51nnMTPPortSlotIndex, ol51nnMTPPortIndex }
	::= { ol51nnMTPPortTable 1 }

Ol51nnMTPPortEntry ::= 
	SEQUENCE {
		ol51nnMTPPortSlotIndex
			INTEGER,			
		ol51nnMTPPortIndex
			INTEGER,
		ol51nnMTPPortAdminState
			INTEGER,
		ol51nnMTPPortBuddySlot
			INTEGER,
		ol51nnMTPPortBuddyPort
			INTEGER,
		ol51nnMTPPortDipAdminState
			INTEGER,
		ol51nnMTPPortLinkInteg
			INTEGER,
		ol51nnMTPPortDipLinkInteg
			INTEGER,
		ol51nnMTPPortSquelch
			INTEGER,
		ol51nnMTPPortDipSquelch
			INTEGER
		}

	ol51nnMTPPortSlotIndex OBJECT-TYPE
	SYNTAX INTEGER
	ACCESS read-only
	STATUS mandatory
	DESCRIPTION
		"The slot number of this port's module."
	::= { ol51nnMTPPortEntry 1 }


ol51nnMTPPortIndex OBJECT-TYPE
	SYNTAX INTEGER
	ACCESS read-only
	STATUS mandatory
	DESCRIPTION
		"The port number of this port."
	::= { ol51nnMTPPortEntry 2 }

ol51nnMTPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMTPPortEntry 3 }

ol51nnMTPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMTPPortEntry 4 }

ol51nnMTPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMTPPortEntry 5 }

ol51nnMTPPortDipAdminState OBJECT-TYPE
	SYNTAX INTEGER {
		enabled(1),
		disabled(2)
		}
	ACCESS read-only
	STATUS mandatory
	DESCRIPTION
		"The state of this port as indicated by the port's dip 
		switches."		
	::= { ol51nnMTPPortEntry 6 }

ol51nnMTPPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ol51nnMTPPortEntry 7 }

ol51nnMTPPortDipLinkInteg OBJECT-TYPE
	SYNTAX INTEGER {
		enabled(1),
		disabled(2)
		}
	ACCESS read-only
	STATUS mandatory
	DESCRIPTION
		"The link integrity configuration as indicated by this
		port's dip switches."
	::= { ol51nnMTPPortEntry 8 }

ol51nnMTPPortSquelch	 OBJECT-TYPE
	SYNTAX INTEGER {
		normal(1),		-- high squelch
		low(2)
		}
	ACCESS read-write
	STATUS mandatory
	DESCRIPTION
		"The port's squelch configuration.  See the module's
		user's guide for more information."
	::= { ol51nnMTPPortEntry 9 }

ol51nnMTPPortDipSquelch	 OBJECT-TYPE
	SYNTAX INTEGER {
		normal(1),		-- high squelch
		low(2)
		}
	ACCESS read-only
	STATUS mandatory
	DESCRIPTION
		"The port's squelch configuration as indicated by this
		port's dip switches."
	::= { ol51nnMTPPortEntry 10 }

--
-- ONline Ethernet BNC Module
--


ol51nnMBNCModTable OBJECT-TYPE
	SYNTAX SEQUENCE OF Ol51nnMBNCModEntry
	ACCESS not-accessible
	STATUS mandatory
	DESCRIPTION
		"A list of module-specific information associated
		with a particular 51nnM-BNC module in the concentrator."
	::= { ol51nnMBNC 1 }

ol51nnMBNCModEntry OBJECT-TYPE
	SYNTAX Ol51nnMBNCModEntry 
	ACCESS not-accessible
	STATUS mandatory
	DESCRIPTION
		"A module entry containing objects that describe the 
		module level for that particular module."
        INDEX { ol51nnMBNCModSlotIndex }
	::= { ol51nnMBNCModTable 1 }

Ol51nnMBNCModEntry ::=
	SEQUENCE {
		ol51nnMBNCModSlotIndex
			INTEGER,
		ol51nnMBNCModDipNetwork
			INTEGER
		}

ol51nnMBNCModSlotIndex OBJECT-TYPE
	SYNTAX INTEGER
	ACCESS read-only
	STATUS mandatory
	DESCRIPTION
		"The slot number of this module."
	::= { ol51nnMBNCModEntry 1 }

ol51nnMBNCModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMBNCModEntry 2 }

ol51nnMBNCPortTable OBJECT-TYPE
	SYNTAX SEQUENCE OF Ol51nnMBNCPortEntry
	ACCESS not-accessible
	STATUS mandatory
	DESCRIPTION
		"A table of port-specific information for each port of
		this module type."
	::= { ol51nnMBNC 2 }

ol51nnMBNCPortEntry OBJECT-TYPE
	SYNTAX Ol51nnMBNCPortEntry 
	ACCESS not-accessible
	STATUS mandatory
	DESCRIPTION
		"A port entry containing objects that describe this port."
        INDEX { ol51nnMBNCPortSlotIndex, ol51nnMBNCPortIndex }
	::= { ol51nnMBNCPortTable 1 }

Ol51nnMBNCPortEntry ::=
	SEQUENCE {	
		ol51nnMBNCPortSlotIndex
			INTEGER,			
		ol51nnMBNCPortIndex
			INTEGER,
		ol51nnMBNCPortDipAdminState
			INTEGER,
		ol51nnMBNCPortDipTermination
			INTEGER,
		ol51nnMBNCPortDipGround
			INTEGER
		}

ol51nnMBNCPortSlotIndex OBJECT-TYPE
	SYNTAX INTEGER
	ACCESS read-only
	STATUS mandatory
	DESCRIPTION
		"The slot number of this port's module."
	::= { ol51nnMBNCPortEntry 1 }


ol51nnMBNCPortIndex OBJECT-TYPE
	SYNTAX INTEGER
	ACCESS read-only
	STATUS mandatory
	DESCRIPTION
		"The port number of this port."		
	::= { ol51nnMBNCPortEntry 2 }

ol51nnMBNCPortDipAdminState OBJECT-TYPE
	SYNTAX INTEGER {
		enabled(1),
		disabled(2)
		}
	ACCESS read-only
	STATUS mandatory
	DESCRIPTION
		"The state of this port as indicated by the port's dip 
		switches."		
	::= { ol51nnMBNCPortEntry 3 }

ol51nnMBNCPortDipTermination OBJECT-TYPE
	SYNTAX INTEGER {
		terminated(1),
		not-terminated(2)
		}
	ACCESS read-only
	STATUS mandatory
	DESCRIPTION
		"The state of this port's termination as indicated by the
		port's dip switches."		
	::= { ol51nnMBNCPortEntry 4 }

ol51nnMBNCPortDipGround OBJECT-TYPE
	SYNTAX INTEGER {
		grounded(1),
		not-grounded(2)
		}
	ACCESS read-only
	STATUS mandatory
	DESCRIPTION
		"The state of this port's ground as indicated by the port's 
		dip switches."		
	::= { ol51nnMBNCPortEntry 5 }

--
-- ONline Ethernet to Ethernet Bridge Module
--

ol51nnBEEModTable OBJECT-TYPE
	SYNTAX SEQUENCE OF Ol51nnBEEModEntry
	ACCESS not-accessible
	STATUS mandatory
	DESCRIPTION
		"A table of module-specific information for
		each 51nnB-EE module in the concentrator."
	::= { ol51nnBEE 1 }

ol51nnBEEModEntry OBJECT-TYPE
	SYNTAX Ol51nnBEEModEntry
	ACCESS not-accessible
	STATUS mandatory
	DESCRIPTION
		"A list of module-specific information about a specific
		51nnB-EE module in the concentrator."
	INDEX { ol51nnBEEModSlotIndex }
	::= { ol51nnBEEModTable 1 }

Ol51nnBEEModEntry ::= 
	SEQUENCE {
		ol51nnBEEModSlotIndex
			INTEGER,	
		ol51nnBEEModStationAddr
			OCTET STRING,
		ol51nnBEEModProtocols
			DisplayString
		}

ol51nnBEEModSlotIndex OBJECT-TYPE
	SYNTAX INTEGER
	ACCESS read-only
	STATUS mandatory
	DESCRIPTION
		"The slot number of this module."
	::= { ol51nnBEEModEntry 1 }

ol51nnBEEModStationAddr OBJECT-TYPE
	SYNTAX OCTET STRING (SIZE(6))
	ACCESS read-only
	STATUS mandatory
	DESCRIPTION
		"A 6 octet address that uniquely identifies this module.
		The station address is the mac address of port 1."
	::= { ol51nnBEEModEntry 2 }

ol51nnBEEModProtocols OBJECT-TYPE
	SYNTAX DisplayString
	ACCESS read-only
	STATUS mandatory
	DESCRIPTION
		"A textual description of the protocols supported by 
		this module"
	::= { ol51nnBEEModEntry 3 }
		
	
ol51nnBEEPortTable	OBJECT-TYPE
	SYNTAX SEQUENCE OF Ol51nnBEEPortEntry
	ACCESS not-accessible
	STATUS mandatory
	DESCRIPTION
		"A table of port-specific for each port of each 
		51nnBEE module in the concentrator."
	::= { ol51nnBEE 2 }


ol51nnBEEPortEntry OBJECT-TYPE
	SYNTAX Ol51nnBEEPortEntry
	ACCESS not-accessible
	STATUS mandatory
	DESCRIPTION
		"A list of port-specific informatoin about a specific
		51nnB-EE port in the concentrator."
        INDEX { ol51nnBEEPortSlotIndex, ol51nnBEEPortIndex }
	::= { ol51nnBEEPortTable 1 }

Ol51nnBEEPortEntry ::= 
	SEQUENCE {
		ol51nnBEEPortSlotIndex
			INTEGER,
		ol51nnBEEPortIndex
			INTEGER,
		ol51nnBEEPortIpAddress
			IpAddress,
		ol51nnBEEPortDipNetwork
			INTEGER,
		ol51nnBEEPortDefNetwork
			INTEGER
		}

ol51nnBEEPortSlotIndex OBJECT-TYPE
	SYNTAX INTEGER
	ACCESS read-only
	STATUS mandatory
	DESCRIPTION
		"The slot number for this port's module."
	::= { ol51nnBEEPortEntry 1 }

ol51nnBEEPortIndex OBJECT-TYPE
	SYNTAX INTEGER
	ACCESS read-only
	STATUS mandatory
	DESCRIPTION
		"The port number for this port within this slot."
	::= { ol51nnBEEPortEntry 2 }

ol51nnBEEPortIpAddress OBJECT-TYPE
	SYNTAX IpAddress
	ACCESS read-only
	STATUS mandatory
	DESCRIPTION
		"The IP Address associated with this port."
	::= { ol51nnBEEPortEntry 3 }

ol51nnBEEPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnBEEPortEntry 4 }

ol51nnBEEPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OEBM's
		non-volatile storage."
	::= { ol51nnBEEPortEntry 5 }

--
-- ONline Ethernet to Serial Router Module
--


ol51nnRESModTable OBJECT-TYPE
	SYNTAX SEQUENCE OF Ol51nnRESModEntry
	ACCESS not-accessible
	STATUS mandatory
	DESCRIPTION
		"A table of module-specific information for
		each 51nnR-ES module in the concentrator."
	::= { ol51nnRES 1 }

ol51nnRESModEntry OBJECT-TYPE
	SYNTAX Ol51nnRESModEntry
	ACCESS not-accessible
	STATUS mandatory
	DESCRIPTION
		"A list of module-specific information about a specific
		51nnR-ES module in the concentrator."
	INDEX { ol51nnRESModSlotIndex }
	::= { ol51nnRESModTable 1 }

Ol51nnRESModEntry ::= 
	SEQUENCE {
		ol51nnRESModSlotIndex
			INTEGER,	
		ol51nnRESModStationAddr
			OCTET STRING,
		ol51nnRESModProtocols
			DisplayString
		}

ol51nnRESModSlotIndex OBJECT-TYPE
	SYNTAX INTEGER
	ACCESS read-only
	STATUS mandatory
	DESCRIPTION
		"The slot number of this module."
	::= { ol51nnRESModEntry 1 }

ol51nnRESModStationAddr OBJECT-TYPE
	SYNTAX OCTET STRING (SIZE(6))
	ACCESS read-only
	STATUS mandatory
	DESCRIPTION
		"A 6 octet address that uniquely identifies this module.
		The station address is the mac address of port 1."
	::= { ol51nnRESModEntry 2 }


ol51nnRESModProtocols OBJECT-TYPE
	SYNTAX DisplayString
	ACCESS read-only
	STATUS mandatory
	DESCRIPTION
		"A textual description of the protocols supported by 
		this module"
	::= { ol51nnRESModEntry 3 }

ol51nnRESPortTable	OBJECT-TYPE
	SYNTAX SEQUENCE OF Ol51nnRESPortEntry
	ACCESS not-accessible
	STATUS mandatory
	DESCRIPTION
		"A table of port-specific for each port of each 
		51nnR-ES module in the concentrator."
	::= { ol51nnRES 2 }

ol51nnRESPortEntry OBJECT-TYPE
	SYNTAX Ol51nnRESPortEntry
	ACCESS not-accessible
	STATUS mandatory
	DESCRIPTION
		"A list of port-specific informatoin about a specific
		51nnR-ES port in the concentrator."
        INDEX { ol51nnRESPortSlotIndex, ol51nnRESPortIndex }
	::= { ol51nnRESPortTable 1 }

Ol51nnRESPortEntry ::= 
	SEQUENCE {
		ol51nnRESPortSlotIndex
			INTEGER,
		ol51nnRESPortIndex
			INTEGER,
		ol51nnRESPortIpAddress
			IpAddress,
		ol51nnRESPortDipNetwork
			INTEGER,
		ol51nnRESPortDefNetwork
			INTEGER
		}

ol51nnRESPortSlotIndex OBJECT-TYPE
	SYNTAX INTEGER
	ACCESS read-only
	STATUS mandatory
	DESCRIPTION
		"The slot number for this port's module."
	::= { ol51nnRESPortEntry 1 }

ol51nnRESPortIndex OBJECT-TYPE
	SYNTAX INTEGER
	ACCESS read-only
	STATUS mandatory
	DESCRIPTION
		"The port number for this port."
	::= { ol51nnRESPortEntry 2 }

ol51nnRESPortIpAddress OBJECT-TYPE
	SYNTAX IpAddress
	ACCESS read-only
	STATUS mandatory
	DESCRIPTION
		"The IP Address associated with this port."
	::= { ol51nnRESPortEntry 3 }

ol51nnRESPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnRESPortEntry 4 }

ol51nnRESPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { ol51nnRESPortEntry 5 }

--
-- ONline Ethernet to Ethernet Router Module
--


ol51nnREEModTable OBJECT-TYPE
	SYNTAX SEQUENCE OF Ol51nnREEModEntry
	ACCESS not-accessible
	STATUS mandatory
	DESCRIPTION
		"A table of module-specific information for
		each 51nnR-EE module in the concentrator."
	::= { ol51nnREE 1 }

ol51nnREEModEntry OBJECT-TYPE
	SYNTAX Ol51nnREEModEntry
	ACCESS not-accessible
	STATUS mandatory
	DESCRIPTION
		"A list of module-specific information about a specific
		51nnR-EE module in the concentrator."
	INDEX { ol51nnREEModSlotIndex }
	::= { ol51nnREEModTable 1 }

Ol51nnREEModEntry ::= 
	SEQUENCE {
		ol51nnREEModSlotIndex
			INTEGER,	
		ol51nnREEModStationAddr
			OCTET STRING,
		ol51nnREEModProtocols
			DisplayString
		}

ol51nnREEModSlotIndex OBJECT-TYPE
	SYNTAX INTEGER
	ACCESS read-only
	STATUS mandatory
	DESCRIPTION
		"The slot number of this module."
	::= { ol51nnREEModEntry 1 }

ol51nnREEModStationAddr OBJECT-TYPE
	SYNTAX OCTET STRING (SIZE(6))
	ACCESS read-only
	STATUS mandatory
	DESCRIPTION
		"A 6 octet address that uniquely identifies this module.
		The station address is the mac address of port 1."
	::= { ol51nnREEModEntry 2 }


ol51nnREEModProtocols OBJECT-TYPE
	SYNTAX DisplayString
	ACCESS read-only
	STATUS mandatory
	DESCRIPTION
		"A textual description of the protocols supported by 
		this module"
	::= { ol51nnREEModEntry 3 }

ol51nnREEPortTable	OBJECT-TYPE
	SYNTAX SEQUENCE OF Ol51nnREEPortEntry
	ACCESS not-accessible
	STATUS mandatory
	DESCRIPTION
		"A table of port-specific for each port of each 
		51nnR-EE module in the concentrator."
	::= { ol51nnREE 2 }

ol51nnREEPortEntry OBJECT-TYPE
	SYNTAX Ol51nnREEPortEntry
	ACCESS not-accessible
	STATUS mandatory
	DESCRIPTION
		"A list of port-specific informatoin about a specific
		51nnR-EE port in the concentrator."
        INDEX { ol51nnREEPortSlotIndex, ol51nnREEPortIndex }
	::= { ol51nnREEPortTable 1 }

Ol51nnREEPortEntry ::= 
	SEQUENCE {
		ol51nnREEPortSlotIndex
			INTEGER,
		ol51nnREEPortIndex
			INTEGER,
		ol51nnREEPortIpAddress
			IpAddress,
		ol51nnREEPortDipNetwork
			INTEGER,
		ol51nnREEPortDefNetwork
			INTEGER
		}

ol51nnREEPortSlotIndex OBJECT-TYPE
	SYNTAX INTEGER
	ACCESS read-only
	STATUS mandatory
	DESCRIPTION
		"The slot number for this port's module."
	::= { ol51nnREEPortEntry 1 }

ol51nnREEPortIndex OBJECT-TYPE
	SYNTAX INTEGER
	ACCESS read-only
	STATUS mandatory
	DESCRIPTION
		"The port number of this port."
	::= { ol51nnREEPortEntry 2 }

ol51nnREEPortIpAddress OBJECT-TYPE
	SYNTAX IpAddress
	ACCESS read-only
	STATUS mandatory
	DESCRIPTION
		"The IP Address associated with this port."
	::= { ol51nnREEPortEntry 3 }

ol51nnREEPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnREEPortEntry 4 }

ol51nnREEPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { ol51nnREEPortEntry 5 }

-- 
-- ONline Ethernet Female AUI Module
--

ol51nnMAUIFModTable OBJECT-TYPE
	SYNTAX SEQUENCE OF Ol51nnMAUIFModEntry
	ACCESS not-accessible
	STATUS mandatory
	DESCRIPTION
		"A list of module-specific information associated
		with a particular 51nnMAUIF module in the concentrator."
	::= { ol51nnMAUIF 1 }

ol51nnMAUIFModEntry OBJECT-TYPE
	SYNTAX Ol51nnMAUIFModEntry 
	ACCESS not-accessible
	STATUS mandatory
	DESCRIPTION
		"A list of module-specific information about a specific
		51nnMAUIF module in the concentrator."
	INDEX { ol51nnMAUIFModSlotIndex }
	::= { ol51nnMAUIFModTable 1 }

Ol51nnMAUIFModEntry ::=
	SEQUENCE {
		ol51nnMAUIFModSlotIndex
			INTEGER
		}

ol51nnMAUIFModSlotIndex OBJECT-TYPE
	SYNTAX INTEGER
	ACCESS read-only
	STATUS mandatory
	DESCRIPTION
		"The slot number of this module."
	::= { ol51nnMAUIFModEntry 1 }

ol51nnMAUIFPortTable OBJECT-TYPE
	SYNTAX SEQUENCE OF Ol51nnMAUIFPortEntry
	ACCESS not-accessible
	STATUS mandatory
	DESCRIPTION
		"A table of port-specific information for each port of
		this module type."
	::= { ol51nnMAUIF 2 }

ol51nnMAUIFPortEntry OBJECT-TYPE
	SYNTAX Ol51nnMAUIFPortEntry 
	ACCESS not-accessible
	STATUS mandatory
	DESCRIPTION
		"A list of module-specific information about a specific
		51nnM-AUIF port in the concentrator."
	INDEX { ol51nnMAUIFPortSlotIndex, ol51nnMAUIFPortIndex }
	::= { ol51nnMAUIFPortTable 1 }

Ol51nnMAUIFPortEntry ::=
	SEQUENCE {
		ol51nnMAUIFPortSlotIndex
			INTEGER,			
		ol51nnMAUIFPortIndex
			INTEGER,
		ol51nnMAUIFPortAdminState
			INTEGER,
		ol51nnMAUIFPortBuddySlot
			INTEGER,
		ol51nnMAUIFPortBuddyPort
			INTEGER,
		ol51nnMAUIFPortDipAdminState
			INTEGER,
		ol51nnMAUIFPortDipNetwork
			INTEGER
		}

ol51nnMAUIFPortSlotIndex OBJECT-TYPE
	SYNTAX INTEGER
	ACCESS read-only
	STATUS mandatory
	DESCRIPTION
		"The slot number of this port's module."
	::= { ol51nnMAUIFPortEntry 1 }


ol51nnMAUIFPortIndex OBJECT-TYPE
	SYNTAX INTEGER
	ACCESS read-only
	STATUS mandatory
	DESCRIPTION
		"The port number of this port."
	::= { ol51nnMAUIFPortEntry 2 }

ol51nnMAUIFPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMAUIFPortEntry 3 }

ol51nnMAUIFPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMAUIFPortEntry 4 }

ol51nnMAUIFPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMAUIFPortEntry 5 }

ol51nnMAUIFPortDipAdminState OBJECT-TYPE
	SYNTAX INTEGER {
		enabled(1),
		disabled(2),
		redundant-primary(3),
		redundant-backup(4)
		}
	ACCESS read-only
	STATUS mandatory
	DESCRIPTION
		"The state of this port as indicated by the port's dip 
		switches."		
	::= { ol51nnMAUIFPortEntry 6 }


ol51nnMAUIFPortDipNetwork OBJECT-TYPE
	SYNTAX INTEGER {
		isolated(2),
		ethernet-1(6),
		ethernet-2(7),
		ethernet-3(8)
		}
	ACCESS read-only
	STATUS mandatory
	DESCRIPTION
		"The network indicated by the port's dip switches."	
	::= { ol51nnMAUIFPortEntry 7 }


-- 
-- ONline Ethernet Male AUI Module 
--

ol51nnMAUIMModTable OBJECT-TYPE
	SYNTAX SEQUENCE OF Ol51nnMAUIMModEntry
	ACCESS not-accessible
	STATUS mandatory
	DESCRIPTION
		"A list of module-specific information associated
		with a particular 51nnM-AUIM module in the concentrator."
	::= { ol51nnMAUIM 1 }

ol51nnMAUIMModEntry OBJECT-TYPE
	SYNTAX Ol51nnMAUIMModEntry 
	ACCESS not-accessible
	STATUS mandatory
	DESCRIPTION
		"A list of module-specific information about a specific
		51nnM-AUIM module in the concentrator."
	INDEX { ol51nnMAUIMModSlotIndex }
	::= { ol51nnMAUIMModTable 1 }

Ol51nnMAUIMModEntry ::=
	SEQUENCE {
		ol51nnMAUIMModSlotIndex
			INTEGER
		}

ol51nnMAUIMModSlotIndex OBJECT-TYPE
	SYNTAX INTEGER
	ACCESS read-only
	STATUS mandatory
	DESCRIPTION
		"The slot number of this module."
	::= { ol51nnMAUIMModEntry 1 }

ol51nnMAUIMPortTable			 OBJECT-TYPE
	SYNTAX SEQUENCE OF Ol51nnMAUIMPortEntry
	ACCESS not-accessible
	STATUS mandatory
	DESCRIPTION
		"A table of port-specific information for each port of
		this module type."
	::= { ol51nnMAUIM 2 }

ol51nnMAUIMPortEntry OBJECT-TYPE
	SYNTAX Ol51nnMAUIMPortEntry 
	ACCESS not-accessible
	STATUS mandatory
	DESCRIPTION
		"A list of module-specific information about a specific
		51nnM-AUIM port in the concentrator."
	INDEX { ol51nnMAUIMPortSlotIndex, ol51nnMAUIMPortIndex }
	::= { ol51nnMAUIMPortTable 1 }

Ol51nnMAUIMPortEntry ::=
	SEQUENCE {
		ol51nnMAUIMPortSlotIndex
			INTEGER,			
		ol51nnMAUIMPortIndex
			INTEGER,
		ol51nnMAUIMPortAdminState
			INTEGER,
		ol51nnMAUIMPortBuddySlot
			INTEGER,
		ol51nnMAUIMPortBuddyPort
			INTEGER,
		ol51nnMAUIMPortDipAdminState
			INTEGER,
		ol51nnMAUIMPortDipNetwork
			INTEGER,
		ol51nnMAUIMPortSQETest
			INTEGER,
		ol51nnMAUIMPortDipSQETest
			INTEGER,
		ol51nnMAUIMPortCollision
			INTEGER,
		ol51nnMAUIMPortDipCollision
			INTEGER,
		ol51nnMAUIMPortHalfStep
			INTEGER,
		ol51nnMAUIMPortDipHalfStep
			INTEGER
		}

ol51nnMAUIMPortSlotIndex OBJECT-TYPE
	SYNTAX INTEGER
	ACCESS read-only
	STATUS mandatory
	DESCRIPTION
		"The slot number of this port's module."
	::= { ol51nnMAUIMPortEntry 1 }


ol51nnMAUIMPortIndex OBJECT-TYPE
	SYNTAX INTEGER
	ACCESS read-only
	STATUS mandatory
	DESCRIPTION
		"The port number of this port."
	::= { ol51nnMAUIMPortEntry 2 }

ol51nnMAUIMPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMAUIMPortEntry 3 }

ol51nnMAUIMPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMAUIMPortEntry 4 }

ol51nnMAUIMPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMAUIMPortEntry 5 }

ol51nnMAUIMPortDipAdminState OBJECT-TYPE
	SYNTAX INTEGER {
		enabled(1),
		disabled(2)
		}
	ACCESS read-only
	STATUS mandatory
	DESCRIPTION
		"The state of this port as indicated by the port's dip 
		switches."		
	::= { ol51nnMAUIMPortEntry 6 }

ol51nnMAUIMPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMAUIMPortEntry 7 }	

ol51nnMAUIMPortSQETest OBJECT-TYPE
	SYNTAX INTEGER {
		enabled(1),
		disabled(2)
		}
	ACCESS read-write
	STATUS mandatory
	DESCRIPTION
		"The current SQE test configuration for this port."
	::= { ol51nnMAUIMPortEntry 8 }

ol51nnMAUIMPortDipSQETest OBJECT-TYPE
	SYNTAX INTEGER {
		enabled(1),
		disabled(2)
		}
	ACCESS read-only
	STATUS mandatory
	DESCRIPTION
		"The SQE test configuration for this port as indicated
		by the port's dip switches."
	::= { ol51nnMAUIMPortEntry 9 }

ol51nnMAUIMPortCollision OBJECT-TYPE
	SYNTAX INTEGER {
		normal(1),
		alternate(2)
		}
	ACCESS read-write
	STATUS mandatory
	DESCRIPTION
		"The current collision configuration for this port."
	::= { ol51nnMAUIMPortEntry 10 }

ol51nnMAUIMPortDipCollision OBJECT-TYPE
	SYNTAX INTEGER {
		normal(1),
		alternate(2)
		}
	ACCESS read-only
	STATUS mandatory
	DESCRIPTION
		"The collision configuration for this port as indicated
		by the port's dip switches."
	::= { ol51nnMAUIMPortEntry 11 }

ol51nnMAUIMPortHalfStep OBJECT-TYPE
	SYNTAX INTEGER {
		enabled(1),
		disabled(2)
		}
	ACCESS read-write
	STATUS mandatory
	DESCRIPTION
		"The current step configuration for this port."
	::= { ol51nnMAUIMPortEntry 12 }

ol51nnMAUIMPortDipHalfStep OBJECT-TYPE
	SYNTAX INTEGER {
		enabled(1),
		disabled(2)
		}
	ACCESS read-only
	STATUS mandatory
	DESCRIPTION
		"The step configuration for this port as indicated
		by the port's dip switches."
	::= { ol51nnMAUIMPortEntry 13 }

--
-- ONline Token Ring 8-Port MAU Module
--
ol5208MTPModTable OBJECT-TYPE
	SYNTAX SEQUENCE OF Ol5208MTPModEntry
	ACCESS not-accessible
	STATUS mandatory
	DESCRIPTION
		"A list of module-specific information associated
		with a particular 5208M-TP module in the concentrator."
	::= { ol5208MTP 1 }

ol5208MTPModEntry OBJECT-TYPE
	SYNTAX Ol5208MTPModEntry
	ACCESS not-accessible
	STATUS mandatory
	DESCRIPTION
		"A description of the 5208M-TP module attributes."
	INDEX { ol5208MTPModSlotIndex }
	::= { ol5208MTPModTable 1 }

Ol5208MTPModEntry ::= 
	SEQUENCE {
		ol5208MTPModSlotIndex
			INTEGER,
		ol5208MTPModBypsAdminState
			INTEGER,
		ol5208MTPModBypsOperState
			INTEGER,
		ol5208MTPModDipCableImp
			INTEGER
		}

ol5208MTPModSlotIndex OBJECT-TYPE
	SYNTAX INTEGER
	ACCESS read-only
	STATUS mandatory
	DESCRIPTION	
		"The slot number of this module."
	::= { ol5208MTPModEntry 1 }


ol5208MTPModBypsAdminState OBJECT-TYPE
	SYNTAX INTEGER {
		insert(1),
		bypass(2)
		}
	ACCESS read-write
	STATUS mandatory
	DESCRIPTION	
		"The desired state of this module with respect
		to the ring.  Setting this attribute to bypass(2) 
		will cause this module to be removed from the ring
		that passes through the module's ring in and ring out
		ports."
	::= { ol5208MTPModEntry 2 }

ol5208MTPModBypsOperState OBJECT-TYPE
	SYNTAX INTEGER {
		insert(1),
		bypass(2)
		}
	ACCESS read-only
	STATUS mandatory
	DESCRIPTION	
		"The operational state of this module with respect
		to the ring.  If this attribute is equal to bypass(2),
		then the module has been removed from the ring that
		passes through the module's ring in and ring out ports."
	::= { ol5208MTPModEntry 3 }

ol5208MTPModDipCableImp OBJECT-TYPE
	SYNTAX INTEGER {
		ohm100(1),
		ohm150(2)
		}
	ACCESS read-only
	STATUS mandatory
	DESCRIPTION
		"The setting of this module's port impedance matching, with
		100 ohm	corresponding to unshielded twisted pair cabling and
		150 ohm	corresponding to shielded twisted pair cabling.
		This setting is valid for all ports on this module."
	::= { ol5208MTPModEntry 4 }
		

ol5208MTPPortTable OBJECT-TYPE
	SYNTAX SEQUENCE OF Ol5208MTPPortEntry
	ACCESS not-accessible
	STATUS mandatory
	DESCRIPTION
		"A table of port-specific information for each port of
		this module type."
	::= { ol5208MTP 2 }

ol5208MTPPortEntry OBJECT-TYPE
	SYNTAX Ol5208MTPPortEntry
	ACCESS not-accessible
	STATUS mandatory
	DESCRIPTION
		"A description of 5208M-TP port attributes."		
	INDEX { ol5208MTPPortSlotIndex, ol5208MTPPortIndex }
	::= { ol5208MTPPortTable 1 }

Ol5208MTPPortEntry ::= 
	SEQUENCE {
		ol5208MTPPortSlotIndex	
			INTEGER,
		ol5208MTPPortIndex
			INTEGER,	
		ol5208MTPPortDipAdminState
			INTEGER,
		ol5208MTPPortStationType
			INTEGER
		}

ol5208MTPPortSlotIndex OBJECT-TYPE
	SYNTAX INTEGER
	ACCESS read-only
	STATUS mandatory
	DESCRIPTION
		"The slot number of this port's module."
	::= { ol5208MTPPortEntry 1 }


ol5208MTPPortIndex OBJECT-TYPE
	SYNTAX INTEGER
	ACCESS read-only
	STATUS mandatory
	DESCRIPTION
		"The port number of this port."
	::= { ol5208MTPPortEntry 2 }

ol5208MTPPortDipAdminState OBJECT-TYPE
	SYNTAX INTEGER {
		enabled(1),
		disabled(2)
		}
	ACCESS read-only
	STATUS mandatory
	DESCRIPTION
		"The state of this port as indicated by the port's dip 
		switches."		
	::= { ol5208MTPPortEntry 3 }

ol5208MTPPortStationType OBJECT-TYPE
	SYNTAX INTEGER {
		mac-present(1),
		mac-not-present(2)
		}
	ACCESS read-write
	STATUS mandatory
	DESCRIPTION
		"Determines whether the station connected to this port
		has a MAC address."
	::= { ol5208MTPPortEntry 4 }

ol5208MTPTrunkTable OBJECT-TYPE
	SYNTAX SEQUENCE OF Ol5208MTPTrunkEntry
	ACCESS not-accessible
	STATUS mandatory
	DESCRIPTION
		"A list of trunk-specific information about each trunk 
		for this module type."
	::= { ol5208MTP 3 }

ol5208MTPTrunkEntry OBJECT-TYPE
	SYNTAX Ol5208MTPTrunkEntry
	ACCESS not-accessible
	STATUS mandatory
	DESCRIPTION
		"A description of 5208M-TP trunk attributes."		
	INDEX { ol5208MTPTrunkSlotIndex, ol5208MTPTrunkIndex }
	::= { ol5208MTPTrunkTable 1 }

Ol5208MTPTrunkEntry ::= 
	SEQUENCE {
		ol5208MTPTrunkSlotIndex	
			INTEGER,
		ol5208MTPTrunkIndex
			INTEGER,	
		ol5208MTPTrunkDipAdminState
			INTEGER,
		ol5208MTPTrunkCableMon
			INTEGER,
		ol5208MTPTrunkDipCableMon
			INTEGER,
		ol5208MTPTrunkNetMapState
			INTEGER,
		ol5208MTPTrunkExtBcnRecovery
			INTEGER
		}

ol5208MTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol5208MTPTrunkEntry 1 }


ol5208MTPTrunkIndex OBJECT-TYPE
	SYNTAX INTEGER
	ACCESS read-only
	STATUS mandatory
	DESCRIPTION
		"The trunk number for this trunk."
	::= { ol5208MTPTrunkEntry 2 }

ol5208MTPTrunkDipAdminState OBJECT-TYPE
	SYNTAX INTEGER {
		enabled(1),
		disabled(2)
		}
	ACCESS read-only
	STATUS mandatory
	DESCRIPTION
		"The state of this trunk as indicated by the trunk's dip 
		switches."		
	::= { ol5208MTPTrunkEntry 3 }

		
ol5208MTPTrunkCableMon OBJECT-TYPE
	SYNTAX INTEGER {
		enabled(1),
		disabled(2),
		notApplicable(3)	
	}
	ACCESS read-write
	STATUS mandatory
	DESCRIPTION
		"The cable monitor configuration for this trunk."
	::= { ol5208MTPTrunkEntry 4 }

ol5208MTPTrunkDipCableMon OBJECT-TYPE
	SYNTAX INTEGER {
		enabled(1),
		disabled(2),
		notApplicable(3)	
	}
	ACCESS read-only
	STATUS mandatory
	DESCRIPTION
		"The cable monitor configuration as indicated by this trunk's
		dip switches."
	::= { ol5208MTPTrunkEntry 5 }


ol5208MTPTrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This 
		prevents incorrect mapping which can occur when a 
		module in one hub detects the mapping signal from
		another hub. This attribute only applies to copper 
		ring-in trunks."
	::= { ol5208MTPTrunkEntry 6 }


ol5208MTPTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol5208MTPTrunkEntry 7 }


-- 
-- ONline Ethernet Fiber Per-Port Module
--

ol51nnMFPModTable OBJECT-TYPE
	SYNTAX SEQUENCE OF Ol51nnMFPModEntry
	ACCESS not-accessible
	STATUS mandatory
	DESCRIPTION
		"A list of module-specific information associated
		with a particular 51nnM-FP module in the concentrator."
  	::= { ol51nnMFP 1 }

ol51nnMFPModEntry OBJECT-TYPE
	SYNTAX Ol51nnMFPModEntry 
	ACCESS not-accessible
	STATUS mandatory
	DESCRIPTION
		"A list of module-specific information about a specific
		51nnM-FP module in the concentrator."
	INDEX { ol51nnMFPModSlotIndex }
	::= { ol51nnMFPModTable 1 }

Ol51nnMFPModEntry ::=
	SEQUENCE {
		ol51nnMFPModSlotIndex
			INTEGER
		}

ol51nnMFPModSlotIndex OBJECT-TYPE
	SYNTAX INTEGER
	ACCESS read-only
	STATUS mandatory
	DESCRIPTION
		"The slot number of this module."
	::= { ol51nnMFPModEntry 1 }

ol51nnMFPPortTable			 OBJECT-TYPE
	SYNTAX SEQUENCE OF Ol51nnMFPPortEntry
	ACCESS not-accessible
	STATUS mandatory
	DESCRIPTION
		"A table of port-specific information for each port of
		this module type."
	::= { ol51nnMFP 2 }

ol51nnMFPPortEntry OBJECT-TYPE
	SYNTAX Ol51nnMFPPortEntry 
	ACCESS not-accessible
	STATUS mandatory
	DESCRIPTION
		"A list of module-specific information about a specific
		51nnM-FP port in the concentrator."
	INDEX { ol51nnMFPPortSlotIndex, ol51nnMFPPortIndex }
	::= { ol51nnMFPPortTable 1 }

Ol51nnMFPPortEntry ::=
	SEQUENCE {
		ol51nnMFPPortSlotIndex
			INTEGER,			
		ol51nnMFPPortIndex
			INTEGER,
		ol51nnMFPPortAdminState
			INTEGER,
		ol51nnMFPPortBuddySlot
			INTEGER,
		ol51nnMFPPortBuddyPort
			INTEGER,
		ol51nnMFPPortDipAdminState
			INTEGER,
		ol51nnMFPPortDipNetwork
			INTEGER,
		ol51nnMFPPortLLW
			INTEGER,
		ol51nnMFPPortDipLLW
			INTEGER,
		ol51nnMFPPortHipwr
			INTEGER,
		ol51nnMFPPortDipHipwr
			INTEGER
		}

ol51nnMFPPortSlotIndex OBJECT-TYPE
	SYNTAX INTEGER
	ACCESS read-only
	STATUS mandatory
	DESCRIPTION
		"The slot number of this port's module."
	::= { ol51nnMFPPortEntry 1 }


ol51nnMFPPortIndex OBJECT-TYPE
	SYNTAX INTEGER
	ACCESS read-only
	STATUS mandatory
	DESCRIPTION
		"The port number of this port."
	::= { ol51nnMFPPortEntry 2 }

ol51nnMFPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFPPortEntry 3 }

ol51nnMFPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFPPortEntry 4 }

ol51nnMFPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFPPortEntry 5 }

ol51nnMFPPortDipAdminState OBJECT-TYPE
	SYNTAX INTEGER {
		enabled(1),
		disabled(2),
                redundant-primary(3),
                redundant-backup(4)
		}
	ACCESS read-only
	STATUS mandatory
	DESCRIPTION
		"The state of this port as indicated by the port's dip 
		switches."		
	::= { ol51nnMFPPortEntry 6 }

ol51nnMFPPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMFPPortEntry 7 }	

ol51nnMFPPortLLW OBJECT-TYPE
	SYNTAX INTEGER {
		enabled(1),
		disabled(2)
		}
	ACCESS read-write
	STATUS mandatory
	DESCRIPTION
		"The current low light warning configuration for this port."
	::= { ol51nnMFPPortEntry 8 }

ol51nnMFPPortDipLLW OBJECT-TYPE
	SYNTAX INTEGER {
		enabled(1),
		disabled(2)
		}
	ACCESS read-only
	STATUS mandatory
	DESCRIPTION
		"The low light warning configuration indicated by this module's
		dip switches."
	::= { ol51nnMFPPortEntry 9 }
	
ol51nnMFPPortHipwr OBJECT-TYPE
	SYNTAX INTEGER {
		enabled(1),
		disabled(2)
		}
	ACCESS read-write
	STATUS mandatory
	DESCRIPTION
		"The current high power optic configuration for this port."
	::= { ol51nnMFPPortEntry 10 }

ol51nnMFPPortDipHipwr OBJECT-TYPE
	SYNTAX INTEGER {
		enabled(1),
		disabled(2)
		}
	ACCESS read-only
	STATUS mandatory
	DESCRIPTION
		"The high power optic configuration for this port as indicated
		by the port's dip switches."
	::= { ol51nnMFPPortEntry 11 }

-- 
-- ONline Ethernet 10BASE-F Per-Port Module
--

ol51nnMFBPModTable OBJECT-TYPE
	SYNTAX SEQUENCE OF Ol51nnMFBPModEntry
	ACCESS not-accessible
	STATUS mandatory
	DESCRIPTION
		"A list of module-specific information associated
		with a particular 51nnM-FBP module in the concentrator."
	::= { ol51nnMFBP 1 }

ol51nnMFBPModEntry OBJECT-TYPE
	SYNTAX Ol51nnMFBPModEntry 
	ACCESS not-accessible
	STATUS mandatory
	DESCRIPTION
		"A list of module-specific information about a specific
		51nnM-FBP module in the concentrator."
	INDEX { ol51nnMFBPModSlotIndex }
	::= { ol51nnMFBPModTable 1 }

Ol51nnMFBPModEntry ::=
	SEQUENCE {
		ol51nnMFBPModSlotIndex
			INTEGER
		}

ol51nnMFBPModSlotIndex OBJECT-TYPE
	SYNTAX INTEGER
	ACCESS read-only
	STATUS mandatory
	DESCRIPTION
		"The slot number of this module."
	::= { ol51nnMFBPModEntry 1 }

ol51nnMFBPPortTable			 OBJECT-TYPE
	SYNTAX SEQUENCE OF Ol51nnMFBPPortEntry
	ACCESS not-accessible
	STATUS mandatory
	DESCRIPTION
		"A table of port-specific information for each port of
		this module type."
	::= { ol51nnMFBP 2 }

ol51nnMFBPPortEntry OBJECT-TYPE
	SYNTAX Ol51nnMFBPPortEntry 
	ACCESS not-accessible
	STATUS mandatory
	DESCRIPTION
		"A list of module-specific information about a specific
		51nnM-FBP port in the concentrator."
	INDEX { ol51nnMFBPPortSlotIndex, ol51nnMFBPPortIndex }
	::= { ol51nnMFBPPortTable 1 }

Ol51nnMFBPPortEntry ::=
	SEQUENCE {
		ol51nnMFBPPortSlotIndex
			INTEGER,			
		ol51nnMFBPPortIndex
			INTEGER,
		ol51nnMFBPPortAdminState
			INTEGER,
		ol51nnMFBPPortBuddySlot
			INTEGER,
		ol51nnMFBPPortBuddyPort
			INTEGER,
		ol51nnMFBPPortDipAdminState
			INTEGER,
		ol51nnMFBPPortDipNetwork
			INTEGER,
		ol51nnMFBPPortLLW
			INTEGER,
		ol51nnMFBPPortDipLLW
			INTEGER,
		ol51nnMFBPPortHipwr
			INTEGER,
		ol51nnMFBPPortDipHipwr
			INTEGER
		}

ol51nnMFBPPortSlotIndex OBJECT-TYPE
	SYNTAX INTEGER
	ACCESS read-only
	STATUS mandatory
	DESCRIPTION
		"The slot number of this port's module."
	::= { ol51nnMFBPPortEntry 1 }


ol51nnMFBPPortIndex OBJECT-TYPE
	SYNTAX INTEGER
	ACCESS read-only
	STATUS mandatory
	DESCRIPTION
		"The port number of this port."
	::= { ol51nnMFBPPortEntry 2 }

ol51nnMFBPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFBPPortEntry 3 }

ol51nnMFBPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFBPPortEntry 4 }

ol51nnMFBPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFBPPortEntry 5 }

ol51nnMFBPPortDipAdminState OBJECT-TYPE
	SYNTAX INTEGER {
		enabled(1),
		disabled(2),
                redundant-primary(3),
                redundant-backup(4)
		}
	ACCESS read-only
	STATUS mandatory
	DESCRIPTION
		"The state of this port as indicated by the port's dip 
		switches."		
	::= { ol51nnMFBPPortEntry 6 }

ol51nnMFBPPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMFBPPortEntry 7 }	

ol51nnMFBPPortLLW OBJECT-TYPE
	SYNTAX INTEGER {
		enabled(1),
		disabled(2)
		}
	ACCESS read-write
	STATUS mandatory
	DESCRIPTION
		"The current low light warning configuration for this port."
	::= { ol51nnMFBPPortEntry 8 }

ol51nnMFBPPortDipLLW OBJECT-TYPE
	SYNTAX INTEGER {
		enabled(1),
		disabled(2)
		}
	ACCESS read-only
	STATUS mandatory
	DESCRIPTION
		"The low light warning configuration indicated by this module's
		dip switches."
	::= { ol51nnMFBPPortEntry 9 }
	
ol51nnMFBPPortHipwr OBJECT-TYPE
	SYNTAX INTEGER {
		enabled(1),
		disabled(2)
		}
	ACCESS read-write
	STATUS mandatory
	DESCRIPTION
		"The current high power optic configuration for this port."
	::= { ol51nnMFBPPortEntry 10 }

ol51nnMFBPPortDipHipwr OBJECT-TYPE
	SYNTAX INTEGER {
		enabled(1),
		disabled(2)
		}
	ACCESS read-only
	STATUS mandatory
	DESCRIPTION
		"The high power optic configuration for this port as indicated
		by the port's dip switches."
	::= { ol51nnMFBPPortEntry 11 }

-- 
-- ONline Ethernet 10BASE-T Module
--

ol51nnMTPLModTable OBJECT-TYPE
	SYNTAX SEQUENCE OF Ol51nnMTPLModEntry
	ACCESS not-accessible
	STATUS mandatory
	DESCRIPTION
		"A list of module-specific information associated
		with a particular 51nnM-TPL module in the concentrator."
	::= { ol51nnMTPL 1 }

ol51nnMTPLModEntry OBJECT-TYPE
	SYNTAX Ol51nnMTPLModEntry 
	ACCESS not-accessible
	STATUS mandatory
	DESCRIPTION
		"A list of module-specific information about a specific
		51nnM-TPL module in the concentrator."
	INDEX { ol51nnMTPLModSlotIndex }
	::= { ol51nnMTPLModTable 1 }

Ol51nnMTPLModEntry ::=
	SEQUENCE {
		ol51nnMTPLModSlotIndex
			INTEGER,
		ol51nnMTPLModDipNetwork
			INTEGER
		}

ol51nnMTPLModSlotIndex OBJECT-TYPE
	SYNTAX INTEGER
	ACCESS read-only
	STATUS mandatory
	DESCRIPTION
		"The slot number of this module."
	::= { ol51nnMTPLModEntry 1 }

ol51nnMTPLModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ol51nnMTPLModEntry 2 }	
	
ol51nnMTPLPortTable			 OBJECT-TYPE
	SYNTAX SEQUENCE OF Ol51nnMTPLPortEntry
	ACCESS not-accessible
	STATUS mandatory
	DESCRIPTION
		"A table of port-specific information for each port of
		this module type."
	::= { ol51nnMTPL 2 }

ol51nnMTPLPortEntry OBJECT-TYPE
	SYNTAX Ol51nnMTPLPortEntry 
	ACCESS not-accessible
	STATUS mandatory
	DESCRIPTION
		"A list of module-specific information about a specific
		51nnM-TPL port in the concentrator."
	INDEX { ol51nnMTPLPortSlotIndex, ol51nnMTPLPortIndex }
	::= { ol51nnMTPLPortTable 1 }

Ol51nnMTPLPortEntry ::=
	SEQUENCE {
		ol51nnMTPLPortSlotIndex
			INTEGER,			
		ol51nnMTPLPortIndex
			INTEGER,
		ol51nnMTPLPortAdminState
			INTEGER,
		ol51nnMTPLPortBuddySlot
			INTEGER,
		ol51nnMTPLPortBuddyPort
			INTEGER,
		ol51nnMTPLPortDipAdminState
			INTEGER,
		ol51nnMTPLPortLinkInteg
			INTEGER,
		ol51nnMTPLPortDipLinkInteg
			INTEGER,
		ol51nnMTPLPortSquelch
			INTEGER,
		ol51nnMTPLPortJabber
			INTEGER,
		ol51nnMTPLPortDipJabber
			INTEGER
		}

ol51nnMTPLPortSlotIndex OBJECT-TYPE
	SYNTAX INTEGER
	ACCESS read-only
	STATUS mandatory
	DESCRIPTION
		"The slot number of this port's module."	
	::= { ol51nnMTPLPortEntry 1 }


ol51nnMTPLPortIndex OBJECT-TYPE
	SYNTAX INTEGER
	ACCESS read-only
	STATUS mandatory
	DESCRIPTION
		"The port number of this port."
	::= { ol51nnMTPLPortEntry 2 }

ol51nnMTPLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPLPortEntry 3 }

ol51nnMTPLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."
	::= { ol51nnMTPLPortEntry 4 }

ol51nnMTPLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPLPortEntry 5 }

ol51nnMTPLPortDipAdminState OBJECT-TYPE
	SYNTAX INTEGER {
		enabled(1),
		disabled(2)
		}
	ACCESS read-only
	STATUS mandatory
	DESCRIPTION
		"The state of this port as indicated by the port's dip 
		switches."		
	::= { ol51nnMTPLPortEntry 6 }

ol51nnMTPLPortLinkInteg OBJECT-TYPE
	SYNTAX INTEGER {
		enabled(1),
		disabled(2)
		}
	ACCESS read-write
	STATUS mandatory
	DESCRIPTION
		"The current link integrity configuration for this port."
	::= { ol51nnMTPLPortEntry 7 }

ol51nnMTPLPortDipLinkInteg OBJECT-TYPE
	SYNTAX INTEGER {
		enabled(1),
		disabled(2)
		}
	ACCESS read-only
	STATUS mandatory
	DESCRIPTION
		"The link integrity configuration as indicated by this
		module's dip switches."
	::= { ol51nnMTPLPortEntry 8 }

ol51nnMTPLPortSquelch OBJECT-TYPE
	SYNTAX INTEGER {
		normal(1), -- high squelch
		low(2)
		}
	ACCESS read-write
	STATUS mandatory
	DESCRIPTION
		"The current squelch configuration for this port.  See
		the module's user's guide for more information."
	::= { ol51nnMTPLPortEntry 9 }

ol51nnMTPLPortJabber OBJECT-TYPE
	SYNTAX INTEGER {
		enabled(1),
		disabled(2)
		}
	ACCESS read-write
	STATUS mandatory
	DESCRIPTION
		"The current receive jabber configuration for this port."
	::= { ol51nnMTPLPortEntry 10 }

ol51nnMTPLPortDipJabber OBJECT-TYPE
	SYNTAX INTEGER {
		enabled(1),
		disabled(2)
		}
	ACCESS read-only
	STATUS mandatory
	DESCRIPTION
		"The receive jabber configuration as indicated by this
		module's dip switches."
	::= { ol51nnMTPLPortEntry 11 }


-- 
-- ONline Ethernet 10BASE-T Per-Port Module
--

ol51nnMTPPLModTable OBJECT-TYPE
 	SYNTAX SEQUENCE OF Ol51nnMTPPLModEntry
 	ACCESS not-accessible
	STATUS mandatory
	DESCRIPTION
		"A list of module-specific information about a specific
		51nnM-TPPL module in the concentrator."
	::= { ol51nnMTPPL 1 }

ol51nnMTPPLModEntry OBJECT-TYPE
	SYNTAX Ol51nnMTPPLModEntry 
	ACCESS not-accessible
	STATUS mandatory
	DESCRIPTION
		"A list of module-specific information about a specific
		51nnM-TPPL module in the concentrator."
	INDEX { ol51nnMTPPLModSlotIndex }
	::= { ol51nnMTPPLModTable 1 }

Ol51nnMTPPLModEntry ::=
	SEQUENCE {
		ol51nnMTPPLModSlotIndex
			INTEGER
		}

ol51nnMTPPLModSlotIndex OBJECT-TYPE
	SYNTAX INTEGER
	ACCESS read-only
	STATUS mandatory
	DESCRIPTION
		"The slot number of this module."
	::= { ol51nnMTPPLModEntry 1 }

ol51nnMTPPLPortTable			 OBJECT-TYPE
	SYNTAX SEQUENCE OF Ol51nnMTPPLPortEntry
	ACCESS not-accessible
	STATUS mandatory
	DESCRIPTION
		"A table of port-specific information for each port of
		this module type."
	::= { ol51nnMTPPL 2 }

ol51nnMTPPLPortEntry OBJECT-TYPE
	SYNTAX Ol51nnMTPPLPortEntry 
	ACCESS not-accessible
	STATUS mandatory
	DESCRIPTION
		"A list of module-specific information about a specific
		51nnM-TPPL port in the concentrator."
	INDEX { ol51nnMTPPLPortSlotIndex, ol51nnMTPPLPortIndex }
	::= { ol51nnMTPPLPortTable 1 }

Ol51nnMTPPLPortEntry ::=
	SEQUENCE {
		ol51nnMTPPLPortSlotIndex
			INTEGER,			
		ol51nnMTPPLPortIndex
			INTEGER,
		ol51nnMTPPLPortAdminState
			INTEGER,
		ol51nnMTPPLPortBuddySlot
			INTEGER,
		ol51nnMTPPLPortBuddyPort
			INTEGER,
		ol51nnMTPPLPortDipAdminState
			INTEGER,
		ol51nnMTPPLPortDipNetwork
			INTEGER,
		ol51nnMTPPLPortLinkInteg
			INTEGER,
		ol51nnMTPPLPortDipLinkInteg
			INTEGER,
		ol51nnMTPPLPortSquelch
			INTEGER,
		ol51nnMTPPLPortJabber
			INTEGER,
		ol51nnMTPPLPortDipJabber
			INTEGER
		}

ol51nnMTPPLPortSlotIndex OBJECT-TYPE
	SYNTAX INTEGER
	ACCESS read-only
	STATUS mandatory
	DESCRIPTION
		"The slot number of this port's module."
	::= { ol51nnMTPPLPortEntry 1 }


ol51nnMTPPLPortIndex OBJECT-TYPE
	SYNTAX INTEGER
	ACCESS read-only
	STATUS mandatory
	DESCRIPTION
		"The port number of this port."
	::= { ol51nnMTPPLPortEntry 2 }

ol51nnMTPPLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPPLPortEntry 3 }

ol51nnMTPPLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."

	::= { ol51nnMTPPLPortEntry 4 }

ol51nnMTPPLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPPLPortEntry 5 }

ol51nnMTPPLPortDipAdminState OBJECT-TYPE
	SYNTAX INTEGER {
		enabled(1),
		disabled(2)
		}
	ACCESS read-only
	STATUS mandatory
	DESCRIPTION
		"The state of this port as indicated by the port's dip 
		switches."		
	::= { ol51nnMTPPLPortEntry 6 }

ol51nnMTPPLPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMTPPLPortEntry 7 }	

ol51nnMTPPLPortLinkInteg OBJECT-TYPE
	SYNTAX INTEGER {
		enabled(1),
		disabled(2)
		}
	ACCESS read-write
	STATUS mandatory
	DESCRIPTION
		"The current link integrity configuration for this port."
	::= { ol51nnMTPPLPortEntry 8 }

ol51nnMTPPLPortDipLinkInteg OBJECT-TYPE
	SYNTAX INTEGER {
		enabled(1),
		disabled(2)
		}
	ACCESS read-only
	STATUS mandatory
	DESCRIPTION
		"The link integrity configuration as indicated by this
		module's dip switches."
	::= { ol51nnMTPPLPortEntry 9 }

ol51nnMTPPLPortSquelch OBJECT-TYPE
	SYNTAX INTEGER {
		normal(1), -- high squelch
		low(2)
		}
	ACCESS read-write
	STATUS mandatory
	DESCRIPTION
		"The current squelch configuration for this port.  See
		the module's user's guide for more information."
	::= { ol51nnMTPPLPortEntry 10 }

ol51nnMTPPLPortJabber OBJECT-TYPE
	SYNTAX INTEGER {
		enabled(1),
		disabled(2)
		}
	ACCESS read-write
	STATUS mandatory
	DESCRIPTION
		"The current receive jabber configuration for this port."
	::= { ol51nnMTPPLPortEntry 11 }

ol51nnMTPPLPortDipJabber OBJECT-TYPE
	SYNTAX INTEGER {
		enabled(1),
		disabled(2)
		}
	ACCESS read-only
	STATUS mandatory
	DESCRIPTION
		"The receive jabber configuration as indicated by this
		module's dip switches."
	::= { ol51nnMTPPLPortEntry 12 }

--
-- ONline Token Ring Media Module
--
ol52nnMTPModTable OBJECT-TYPE
	SYNTAX SEQUENCE OF Ol52nnMTPModEntry
	ACCESS not-accessible
	STATUS mandatory
	DESCRIPTION
		"A list of module-specific information about a specific
		52nnM-TP module in the concentrator."
	::= { ol52nnMTP 1 }

ol52nnMTPModEntry OBJECT-TYPE
	SYNTAX Ol52nnMTPModEntry
	ACCESS not-accessible
	STATUS mandatory
	DESCRIPTION
		"A description of the 52nnM-TP module attributes."
	INDEX { ol52nnMTPModSlotIndex }
	::= { ol52nnMTPModTable 1 }

Ol52nnMTPModEntry ::= 
	SEQUENCE {
		ol52nnMTPModSlotIndex
			INTEGER,
		ol52nnMTPModRingSpeed
			INTEGER,
		ol52nnMTPModDipRingSpeed
			INTEGER,
		ol52nnMTPModCableImp
			INTEGER,
		ol52nnMTPModDipCableImp
			INTEGER
		}

ol52nnMTPModSlotIndex OBJECT-TYPE
	SYNTAX INTEGER
	ACCESS read-only
	STATUS mandatory
	DESCRIPTION	
		"A unique value that identifies a particular module.  Its
		value ranges between 1 and olModSlotNumber.  The module
		identified by a particular value of this index is the same
		module as indentified by the same value of
		olModSlotIndex."
	::= { ol52nnMTPModEntry 1 }

ol52nnMTPModRingSpeed OBJECT-TYPE
	SYNTAX INTEGER {
		fourMegabit(1),
		sixteenMegabit(2)
		}
	ACCESS read-write
	STATUS mandatory
	DESCRIPTION	
		"The ring's bandwidth."
	::= { ol52nnMTPModEntry 2 }

ol52nnMTPModDipRingSpeed OBJECT-TYPE
	SYNTAX INTEGER {
		fourMegabit(1),
		sixteenMegabit(2)
		}
	ACCESS read-only
	STATUS mandatory
	DESCRIPTION	
		"The dip switch setting for the ring's bandwidth."
	::= { ol52nnMTPModEntry 3 }

ol52nnMTPModCableImp OBJECT-TYPE
	SYNTAX INTEGER {
		ohm100(1),
		ohm150(2)
		}
	ACCESS read-write
	STATUS mandatory
	DESCRIPTION
		"The setting of this module's port impedance matching, with
		100 ohm	corresponding to unshielded twisted pair cabling and
		150 ohm	corresponding to shielded twisted pair cabling.
		This setting is valid for all ports on this module."
	::= { ol52nnMTPModEntry 4 }

ol52nnMTPModDipCableImp OBJECT-TYPE
	SYNTAX INTEGER {
		ohm100(1),
		ohm150(2)
		}
	ACCESS read-only
	STATUS mandatory
	DESCRIPTION
		"The dip switch setting for the module's port impedance
		matching."
	::= { ol52nnMTPModEntry 5 }

ol52nnMTPPortTable OBJECT-TYPE
	SYNTAX SEQUENCE OF Ol52nnMTPPortEntry
	ACCESS not-accessible
	STATUS mandatory
	DESCRIPTION
		"A table of port-specific information for each port of
		this module type."
	::= { ol52nnMTP 2 }

ol52nnMTPPortEntry OBJECT-TYPE
	SYNTAX Ol52nnMTPPortEntry
	ACCESS not-accessible
	STATUS mandatory
	DESCRIPTION
		"A description of 52nnM-TP port attributes."		
	INDEX { ol52nnMTPPortSlotIndex, ol52nnMTPPortIndex }
	::= { ol52nnMTPPortTable 1 }

Ol52nnMTPPortEntry ::= 
	SEQUENCE {
		ol52nnMTPPortSlotIndex	
			INTEGER,
		ol52nnMTPPortIndex
			INTEGER,	
		ol52nnMTPPortDipAdminState
			INTEGER,
		ol52nnMTPPortStationType
			INTEGER
		}

ol52nnMTPPortSlotIndex OBJECT-TYPE
	SYNTAX INTEGER
	ACCESS read-only
	STATUS mandatory
	DESCRIPTION
		"The slot number of this port's module."
	::= { ol52nnMTPPortEntry 1 }


ol52nnMTPPortIndex OBJECT-TYPE
	SYNTAX INTEGER
	ACCESS read-only
	STATUS mandatory
	DESCRIPTION
		"The port number of this port."
	::= { ol52nnMTPPortEntry 2 }

ol52nnMTPPortDipAdminState OBJECT-TYPE
	SYNTAX INTEGER {
		enabled(1),
		disabled(2)
		}
	ACCESS read-only
	STATUS mandatory
	DESCRIPTION
		"The state of this port as indicated by the port's dip 
		switches."		
	::= { ol52nnMTPPortEntry 3 }

ol52nnMTPPortStationType OBJECT-TYPE
	SYNTAX INTEGER {
		mac-present(1),
		mac-not-present(2)
		}
	ACCESS read-write
	STATUS mandatory
	DESCRIPTION
		"Determines whether the station connected to this port
		has a MAC address."
	::= { ol52nnMTPPortEntry 4 }

ol52nnMTPTrunkTable OBJECT-TYPE
	SYNTAX SEQUENCE OF Ol52nnMTPTrunkEntry
	ACCESS not-accessible
	STATUS mandatory
	DESCRIPTION
		"A list of trunk-specific information about each trunk 
		for this module type."
	::= { ol52nnMTP 3 }

ol52nnMTPTrunkEntry OBJECT-TYPE
	SYNTAX Ol52nnMTPTrunkEntry
	ACCESS not-accessible
	STATUS mandatory
	DESCRIPTION
		"A description of 52nnM-TP trunk attributes."		
	INDEX { ol52nnMTPTrunkSlotIndex, ol52nnMTPTrunkIndex }
	::= { ol52nnMTPTrunkTable 1 }

Ol52nnMTPTrunkEntry ::= 
	SEQUENCE {
		ol52nnMTPTrunkSlotIndex	
			INTEGER,
		ol52nnMTPTrunkIndex
			INTEGER,	
		ol52nnMTPTrunkDipAdminState
			INTEGER
		}

ol52nnMTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol52nnMTPTrunkEntry 1 }


ol52nnMTPTrunkIndex OBJECT-TYPE
	SYNTAX INTEGER
	ACCESS read-only
	STATUS mandatory
	DESCRIPTION
		"The trunk number for this trunk."
	::= { ol52nnMTPTrunkEntry 2 }

ol52nnMTPTrunkDipAdminState OBJECT-TYPE
	SYNTAX INTEGER {
		enabled(1),
		disabled(2)
		}
	ACCESS read-only
	STATUS mandatory
	DESCRIPTION
		"The state of this trunk as indicated by the trunk's dip 
		switches."		
	::= { ol52nnMTPTrunkEntry 3 }

--
-- ONline Token Fiberoptic Repeater Module
--
ol52nnMFRModTable OBJECT-TYPE
	SYNTAX SEQUENCE OF Ol52nnMFRModEntry
	ACCESS not-accessible
	STATUS mandatory
	DESCRIPTION
		"A list of module-specific information about a specific
		52nnM-FR module in the concentrator."
	::= { ol52nnMFR 1 }

ol52nnMFRModEntry OBJECT-TYPE
	SYNTAX Ol52nnMFRModEntry
	ACCESS not-accessible
	STATUS mandatory
	DESCRIPTION
		"A description of the 52nnMFR module attributes."
	INDEX { ol52nnMFRModSlotIndex }
	::= { ol52nnMFRModTable 1 }

Ol52nnMFRModEntry ::= 
	SEQUENCE {
		ol52nnMFRModSlotIndex
			INTEGER,
		ol52nnMFRModRingSpeed
			INTEGER,
		ol52nnMFRModDipRingSpeed
			INTEGER
		}

ol52nnMFRModSlotIndex OBJECT-TYPE
	SYNTAX INTEGER
	ACCESS read-only
	STATUS mandatory
	DESCRIPTION	
		"The slot number of this module."
	::= { ol52nnMFRModEntry 1 }

ol52nnMFRModRingSpeed OBJECT-TYPE
	SYNTAX INTEGER {
		fourMegabit(1),
		sixteenMegabit(2)
		}
	ACCESS read-write
	STATUS mandatory
	DESCRIPTION	
		"The ring's bandwidth."
	::= { ol52nnMFRModEntry 2 }

ol52nnMFRModDipRingSpeed OBJECT-TYPE
	SYNTAX INTEGER {
		fourMegabit(1),
		sixteenMegabit(2)
		}
	ACCESS read-only
	STATUS mandatory
	DESCRIPTION	
		"The dip switch setting for the ring's bandwidth."
	::= { ol52nnMFRModEntry 3 }

ol52nnMFRPortTable OBJECT-TYPE
	SYNTAX SEQUENCE OF Ol52nnMFRPortEntry
	ACCESS not-accessible
	STATUS mandatory
	DESCRIPTION
		"A table of port-specific information for each port of
		this module type."
	::= { ol52nnMFR 2 }

ol52nnMFRPortEntry OBJECT-TYPE
	SYNTAX Ol52nnMFRPortEntry
	ACCESS not-accessible
	STATUS mandatory
	DESCRIPTION
		"A description of 52nnMFR port attributes."		
	INDEX { ol52nnMFRPortSlotIndex, ol52nnMFRPortIndex }
	::= { ol52nnMFRPortTable 1 }

Ol52nnMFRPortEntry ::= 
	SEQUENCE {
		ol52nnMFRPortSlotIndex	
			INTEGER,
		ol52nnMFRPortIndex
			INTEGER,	
		ol52nnMFRPortDipAdminState
			INTEGER,
		ol52nnMFRPortCableImp
			INTEGER,
		ol52nnMFRPortStationType
			INTEGER
		}

ol52nnMFRPortSlotIndex OBJECT-TYPE
	SYNTAX INTEGER
	ACCESS read-only
	STATUS mandatory
	DESCRIPTION
		"The slot number of this port's module."
	::= { ol52nnMFRPortEntry 1 }


ol52nnMFRPortIndex OBJECT-TYPE
	SYNTAX INTEGER
	ACCESS read-only
	STATUS mandatory
	DESCRIPTION
		"The port number of this port."
	::= { ol52nnMFRPortEntry 2 }

ol52nnMFRPortDipAdminState OBJECT-TYPE
	SYNTAX INTEGER {
		enabled(1),
		disabled(2)
		}
	ACCESS read-only
	STATUS mandatory
	DESCRIPTION
		"The state of this port as indicated by the port's dip 
		switches."		
	::= { ol52nnMFRPortEntry 3 }

ol52nnMFRPortCableImp OBJECT-TYPE
	SYNTAX INTEGER {
		ohm100(1),
		ohm150(2)
		}
	ACCESS read-only
	STATUS mandatory
	DESCRIPTION
		"The setting of this port's impedance matching, with 100 ohm
		corresponding to unshielded twisted pair cabling and 150 ohm
		corresponding to shielded twisted pair cabling."
	::= { ol52nnMFRPortEntry 4 }
		
ol52nnMFRPortStationType OBJECT-TYPE
	SYNTAX INTEGER {
		mac-present(1),
		mac-not-present(2)
		}
	ACCESS read-write
	STATUS mandatory
	DESCRIPTION
		"Determines whether the station connected to this port
		has a MAC address."
	::= { ol52nnMFRPortEntry 5 }

ol52nnMFRTrunkTable OBJECT-TYPE
	SYNTAX SEQUENCE OF Ol52nnMFRTrunkEntry
	ACCESS not-accessible
	STATUS mandatory
	DESCRIPTION
		"A list of trunk-specific information about each trunk 
		for this module type."
	::= { ol52nnMFR 3 }

ol52nnMFRTrunkEntry OBJECT-TYPE
	SYNTAX Ol52nnMFRTrunkEntry
	ACCESS not-accessible
	STATUS mandatory
	DESCRIPTION
		"A description of 52nnMFR trunk attributes."		
	INDEX { ol52nnMFRTrunkSlotIndex, ol52nnMFRTrunkIndex }
	::= { ol52nnMFRTrunkTable 1 }

Ol52nnMFRTrunkEntry ::= 
	SEQUENCE {
		ol52nnMFRTrunkSlotIndex	
			INTEGER,
		ol52nnMFRTrunkIndex
			INTEGER,	
		ol52nnMFRTrunkDipAdminState
			INTEGER,
		ol52nnMFRTrunkCableMon
			INTEGER,
		ol52nnMFRTrunkDipCableMon
			INTEGER,
		ol52nnMFRTrunkCompMode
			INTEGER,
		ol52nnMFRTrunkDipCompMode
			INTEGER,
		ol52nnMFRTrunkNetMapState
			INTEGER,
	        ol52nnMFRTrunkExtBcnRecovery
			INTEGER
		}

ol52nnMFRTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol52nnMFRTrunkEntry 1 }


ol52nnMFRTrunkIndex OBJECT-TYPE
	SYNTAX INTEGER
	ACCESS read-only
	STATUS mandatory
	DESCRIPTION
		"The trunk number of this trunk."
	::= { ol52nnMFRTrunkEntry 2 }

ol52nnMFRTrunkDipAdminState OBJECT-TYPE
	SYNTAX INTEGER {
		enabled(1),
		disabled(2)
		}
	ACCESS read-only
	STATUS mandatory
	DESCRIPTION
		"The state of this trunk as indicated by the trunk's dip 
		switches."		
	::= { ol52nnMFRTrunkEntry 3 }

ol52nnMFRTrunkCableMon OBJECT-TYPE
	SYNTAX INTEGER {
		enabled(1),
		disabled(2),
		notApplicable(3)	
	}
	ACCESS read-write
	STATUS mandatory
	DESCRIPTION
		"The cable monitor configuration for this trunk. This
		does not apply to fiber trunks."
	::= { ol52nnMFRTrunkEntry 4 }

ol52nnMFRTrunkDipCableMon OBJECT-TYPE
	SYNTAX INTEGER {
		enabled(1),
		disabled(2),
		notApplicable(3)	
	}
	ACCESS read-only
	STATUS mandatory
	DESCRIPTION
		"The cable monitor configuration as indicated by this trunk's
		dip switches. This does not apply to fiber trunks."
	::= { ol52nnMFRTrunkEntry 5 }


ol52nnMFRTrunkCompMode OBJECT-TYPE
	SYNTAX INTEGER {
		enabled(1),
		disabled(2),
		notApplicable(3)	
	}
	ACCESS read-write
	STATUS mandatory
	DESCRIPTION
		"The compatibility mode for this trunk. This
		only applies to fiber trunks."
	::= { ol52nnMFRTrunkEntry 6 }

ol52nnMFRTrunkDipCompMode OBJECT-TYPE
	SYNTAX INTEGER {
		enabled(1),
		disabled(2),
		notApplicable(3)	
	}
	ACCESS read-only
	STATUS mandatory
	DESCRIPTION
		"The compatibility mode as indicated by this trunk's
		dip switches. This only applies to fiber trunks."
	::= { ol52nnMFRTrunkEntry 7 }


ol52nnMFRTrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This 
		prevents incorrect mapping which can occur when a 
		module in one hub detects the mapping signal from
		another hub. This attribute only applies to copper 
		ring-in trunks."
	::= { ol52nnMFRTrunkEntry 8 }


ol52nnMFRTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol52nnMFRTrunkEntry 9 }


--
-- ONline Ethernet Terminal Server Module
--


ol51nnMTSModTable OBJECT-TYPE
        SYNTAX SEQUENCE OF Ol51nnMTSModEntry
        ACCESS not-accessible
        STATUS mandatory
        DESCRIPTION
                "A table of module-specific information for each
                51nnM-TS module in the concentrator."
        ::= { ol51nnMTS 1 }

ol51nnMTSModEntry OBJECT-TYPE
       SYNTAX Ol51nnMTSModEntry
       ACCESS not-accessible
       STATUS mandatory
       DESCRIPTION
               "A list of module information for each 51nnMTS module
               in the concentrator."
       INDEX { ol51nnMTSModSlotIndex }
       ::= { ol51nnMTSModTable 1 }

Ol51nnMTSModEntry ::=
       SEQUENCE {
               ol51nnMTSModSlotIndex
                       INTEGER,
               ol51nnMTSModProtocols
                       DisplayString,
               ol51nnMTSModIpAddress
                       IpAddress,
               ol51nnMTSModTCPPort
                       INTEGER,
               ol51nnMTSModStationAddr
                       OCTET STRING,
               ol51nnMTSModDipNetwork
                       INTEGER,
               ol51nnMTSModCPURev
                       DisplayString
               }

ol51nnMTSModSlotIndex OBJECT-TYPE
       SYNTAX INTEGER
       ACCESS read-only
       STATUS mandatory
       DESCRIPTION
               "The slot number of this module."
       ::= { ol51nnMTSModEntry 1 }

ol51nnMTSModProtocols OBJECT-TYPE
        SYNTAX DisplayString
        ACCESS read-only
        STATUS mandatory
        DESCRIPTION
		"A textual description of the protocols supported by 
		this module"
        ::= { ol51nnMTSModEntry 2 }

ol51nnMTSModIpAddress OBJECT-TYPE
       SYNTAX IpAddress
       ACCESS read-only
       STATUS mandatory
       DESCRIPTION
               "The IP Address of the terminal terver."
       ::= { ol51nnMTSModEntry 3 }

ol51nnMTSModTCPPort OBJECT-TYPE
       SYNTAX INTEGER
       ACCESS read-only
       STATUS mandatory
       DESCRIPTION
               "The TCP port number of the the terminal server's remote
                console port."
       ::= { ol51nnMTSModEntry 4 }

ol51nnMTSModStationAddr OBJECT-TYPE
       SYNTAX OCTET STRING (SIZE(6))
       ACCESS read-only
       STATUS mandatory
       DESCRIPTION
               "A 6 octet address that uniquely identifies this module.
               The station address is the mac address of the terminal server."
       ::= { ol51nnMTSModEntry 5 }

ol51nnMTSModDipNetwork OBJECT-TYPE
       SYNTAX INTEGER {
               isolated(2),
               ethernet-1(6),
               ethernet-2(7),
               ethernet-3(8)
               }
       ACCESS read-only
       STATUS mandatory
       DESCRIPTION
               "The network indicated by the module's dip switches."
       ::= { ol51nnMTSModEntry 6 }

ol51nnMTSModCPURev OBJECT-TYPE
       SYNTAX DisplayString (SIZE(1..10))
       ACCESS read-only
       STATUS mandatory
       DESCRIPTION
               "The terminal server's CPU revision."
       ::= { ol51nnMTSModEntry 7 }


ol51nnMTSPortTable OBJECT-TYPE
       SYNTAX SEQUENCE OF Ol51nnMTSPortEntry
       ACCESS not-accessible
       STATUS mandatory
       DESCRIPTION
               "A table of information that contains port-specific
               information for each port on each 51nnMTS module."
       ::= { ol51nnMTS 2 }

ol51nnMTSPortEntry OBJECT-TYPE
       SYNTAX Ol51nnMTSPortEntry
       ACCESS not-accessible
       STATUS mandatory
       DESCRIPTION
               "A list of information about a specific port on a
               51nnMTS module."
       INDEX { ol51nnMTSPortSlotIndex, ol51nnMTSPortIndex }
       ::= { ol51nnMTSPortTable 1 }

Ol51nnMTSPortEntry ::=
       SEQUENCE {
               ol51nnMTSPortSlotIndex
                       INTEGER,
               ol51nnMTSPortIndex
                       INTEGER,
               ol51nnMTSPortAdminState
                       INTEGER,
               ol51nnMTSPortOperState
                       INTEGER
               }

       ol51nnMTSPortSlotIndex OBJECT-TYPE
       SYNTAX INTEGER
       ACCESS read-only
       STATUS mandatory
       DESCRIPTION
		"The slot number for this port."
       ::= { ol51nnMTSPortEntry 1 }

ol51nnMTSPortIndex OBJECT-TYPE
       SYNTAX INTEGER
       ACCESS read-only
       STATUS mandatory
       DESCRIPTION
		"The port number of this port."
       ::= { ol51nnMTSPortEntry 2 }

ol51nnMTSPortAdminState OBJECT-TYPE
       SYNTAX INTEGER {
               enabled(1),
               disabled(2),
               local(6),
               remote(7)
               }
       ACCESS read-write
       STATUS mandatory
       DESCRIPTION
               "The administrative state of this port."
       ::= { ol51nnMTSPortEntry 3 }

ol51nnMTSPortOperState OBJECT-TYPE
       SYNTAX INTEGER {
               idle(1),
               local(2),
               connected(3)
               }
       ACCESS read-only
       STATUS mandatory
       DESCRIPTION
               "The operational mode of this port."
       ::= { ol51nnMTSPortEntry 4 }


--
-- ONline Ethernet FOIRL MOdule
--


ol51nnMFLModTable OBJECT-TYPE
        SYNTAX SEQUENCE OF Ol51nnMFLModEntry
        ACCESS not-accessible
        STATUS mandatory
        DESCRIPTION
                "A table of module-specific information for each
                51nnM-FL module in the concentrator."
        ::= { ol51nnMFL 1 }

ol51nnMFLModEntry OBJECT-TYPE
        SYNTAX Ol51nnMFLModEntry
        ACCESS not-accessible
        STATUS mandatory
        DESCRIPTION
                "A list of module-specific information associated
                with a particular 51nnM-FL module in the concentrator."
        INDEX { ol51nnMFLModSlotIndex }
        ::= { ol51nnMFLModTable 1 }
 
Ol51nnMFLModEntry ::=
        SEQUENCE {
                ol51nnMFLModSlotIndex
                        INTEGER,
                ol51nnMFLModDipNetwork
                        INTEGER
                }
 
ol51nnMFLModSlotIndex OBJECT-TYPE
        SYNTAX INTEGER
        ACCESS read-only
        STATUS mandatory
        DESCRIPTION
		"The slot number of this module."
        ::= { ol51nnMFLModEntry 1 }
 
ol51nnMFLModDipNetwork OBJECT-TYPE
        SYNTAX INTEGER {
                isolated(2),
                ethernet-1(6),
                ethernet-2(7),
                ethernet-3(8)
                }
        ACCESS read-only
        STATUS mandatory
        DESCRIPTION
                "The network indicated by the module's dip switches."
        ::= { ol51nnMFLModEntry 2 }
 
ol51nnMFLPortTable OBJECT-TYPE
        SYNTAX SEQUENCE OF Ol51nnMFLPortEntry
        ACCESS not-accessible
        STATUS mandatory
        DESCRIPTION
                "A table of port-specific information for each port
                of each 51nnMFL module."
        ::= { ol51nnMFL 2 }
 
ol51nnMFLPortEntry OBJECT-TYPE
        SYNTAX Ol51nnMFLPortEntry
        ACCESS not-accessible
        STATUS mandatory
        DESCRIPTION
                "A list of information about a specific port on a
                51nnMFL module."
        INDEX { ol51nnMFLPortSlotIndex, ol51nnMFLPortIndex }
        ::= { ol51nnMFLPortTable 1 }
 
Ol51nnMFLPortEntry ::=
        SEQUENCE {
                ol51nnMFLPortSlotIndex
                        INTEGER,
                ol51nnMFLPortIndex
                        INTEGER,
                ol51nnMFLPortAdminState
                        INTEGER,
                ol51nnMFLPortBuddySlot
                        INTEGER,
                ol51nnMFLPortBuddyPort
                        INTEGER,
                ol51nnMFLPortDipAdminState
                        INTEGER
                }

        ol51nnMFLPortSlotIndex OBJECT-TYPE
        SYNTAX INTEGER
        ACCESS read-only
        STATUS mandatory
        DESCRIPTION
                "A unique value that identifies a particular module.  Its
                value ranges between 1 and olModSlotNumber.  The module
                identified by a particular value of this index is the same
                module as indentified by the same value of
                olPortSlotIndex."
        ::= { ol51nnMFLPortEntry 1 }
 
 
ol51nnMFLPortIndex OBJECT-TYPE
        SYNTAX INTEGER
        ACCESS read-only
        STATUS mandatory
        DESCRIPTION
		"The port number of this port."
        ::= { ol51nnMFLPortEntry 2 }
 
 
ol51nnMFLPortAdminState OBJECT-TYPE
        SYNTAX INTEGER {
                enabled(1),
                disabled(2),
                redundant-primary(3),
                redundant-backup(4),
		redundant-rfs(5)
                }
        ACCESS read-write
        STATUS mandatory
        DESCRIPTION
                "The desired state of this port.  Setting this port to
                be redundant with invalid settings of buddy slot and
                buddy port will return invalidData error. Remote
		Failure Signaling (RFS), is set on connected module 
		port to permit transmit error detection on local port.
		Port must be set to be RFS when connected port is set to
		be redundant"
        ::= { ol51nnMFLPortEntry 3 }
 
ol51nnMFLPortBuddySlot OBJECT-TYPE
        SYNTAX INTEGER
        ACCESS read-write
        STATUS mandatory
        DESCRIPTION
                "The slot index of the redundant port's buddy.   "
        ::= { ol51nnMFLPortEntry 4 }
 

ol51nnMFLPortBuddyPort  OBJECT-TYPE
        SYNTAX INTEGER
        ACCESS read-write
        STATUS mandatory
        DESCRIPTION
                "The port index of the redundant port's buddy."
        ::= { ol51nnMFLPortEntry 5 }
 
 
ol51nnMFLPortDipAdminState OBJECT-TYPE
        SYNTAX INTEGER {
                enabled(1),
                disabled(2),
                redundant-primary(3),
                redundant-backup(4),
		redundant-rfs(5)
                }
        ACCESS read-only
        STATUS mandatory
        DESCRIPTION
                "The state of this port as indicated by the port's dip
                switches."
        ::= { ol51nnMFLPortEntry 6 }
 


--
-- ONline Redundant Controller Module
--

ol50nnMRCTLModTable OBJECT-TYPE
	SYNTAX SEQUENCE OF Ol50nnMRCTLModEntry
	ACCESS not-accessible
	STATUS mandatory
	DESCRIPTION
		"A table that contains information about each 50nnMRCTL
		in the concentrator.  "
	::= { ol50nnMRCTL 1 }

ol50nnMRCTLModEntry OBJECT-TYPE
	SYNTAX Ol50nnMRCTLModEntry
	ACCESS not-accessible
	STATUS mandatory
	DESCRIPTION
		"A list of information for each 50nnMRCTL module
		in the concentrator."
	INDEX { ol50nnMRCTLModSlotIndex }
	::= { ol50nnMRCTLModTable 1 }

Ol50nnMRCTLModEntry ::= 
	SEQUENCE {
		ol50nnMRCTLModSlotIndex
			INTEGER,
		ol50nnMRCTLModOperState
			INTEGER,
		ol50nnMRCTLModClockStatus
			INTEGER,
		ol50nnMRCTLModTempStatus
			INTEGER
		}

ol50nnMRCTLModSlotIndex OBJECT-TYPE
	SYNTAX INTEGER
	ACCESS read-only
	STATUS mandatory
	DESCRIPTION
		"The slot number for this module."
	::= { ol50nnMRCTLModEntry 1 }

ol50nnMRCTLModOperState OBJECT-TYPE
	SYNTAX INTEGER {
		active(1),
		standby(2)
		}
	ACCESS read-only
	STATUS mandatory
	DESCRIPTION
		"The operational state of the 50nnMRCTL module.  Specifically,
		this is an indicator of whether the 50nnMRCTL module is
		providing clock signals to the backplane.  An active 50nnMRCTL
		module provides clock signals to the backplane while a standby 
		50nnMRCTL module does not.  Note that only one 50nnMRCTL
		module will be active at any given time; all other 50nnMRCTL
		modules in the concentrator will be in standby mode."
	::= { ol50nnMRCTLModEntry 2 }

ol50nnMRCTLModClockStatus OBJECT-TYPE
	SYNTAX INTEGER {
		okay(1),
		faulty(2)
		}
	ACCESS read-only
	STATUS mandatory
	DESCRIPTION
		"The current status of the on-board clocks on this module."
	::= { ol50nnMRCTLModEntry 3 }

ol50nnMRCTLModTempStatus OBJECT-TYPE
	SYNTAX INTEGER {
		okay(1),
		extremeTemp(2)
		}
	ACCESS read-only
	STATUS mandatory
	DESCRIPTION
		"The temperature as detected by the probe on this module."
	::= { ol50nnMRCTLModEntry 4 }

-- 
-- ONline Ethernet 10BASE-F Module
--

ol51nnMFBModTable OBJECT-TYPE
	SYNTAX SEQUENCE OF Ol51nnMFBModEntry
	ACCESS not-accessible
	STATUS mandatory
	DESCRIPTION
		"A list of module-specific information associated
		with a particular 51nnM-FB module in the concentrator."
	::= { ol51nnMFB 1 }

ol51nnMFBModEntry OBJECT-TYPE
	SYNTAX Ol51nnMFBModEntry 
	ACCESS not-accessible
	STATUS mandatory
	DESCRIPTION
		"A list of module-specific information about a specific
		51nnM-FB module in the concentrator."
	INDEX { ol51nnMFBModSlotIndex }
	::= { ol51nnMFBModTable 1 }

Ol51nnMFBModEntry ::=
	SEQUENCE {
		ol51nnMFBModSlotIndex
			INTEGER,
		ol51nnMFBModDipNetwork
			INTEGER,
                ol51nnMFBModLLW
                        INTEGER,
                ol51nnMFBModDipLLW
                        INTEGER
		}

ol51nnMFBModSlotIndex OBJECT-TYPE
	SYNTAX INTEGER
	ACCESS read-only
	STATUS mandatory
	DESCRIPTION
		"The slot number of this module."
	::= { ol51nnMFBModEntry 1 }

ol51nnMFBModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ol51nnMFBModEntry 2 }	

ol51nnMFBModLLW OBJECT-TYPE
        SYNTAX INTEGER {
                enabled(1),
                disabled(2)
                }
        ACCESS read-write
        STATUS mandatory
        DESCRIPTION
                "The current state of this module's low light warning
                configuration.  Enabling this feature causes the module to
                check for low light and to issue a warning if low light is
                present.  Disabling low light has the advantage of faster
                redundancy switchover in the event of a port error."
        ::= { ol51nnMFBModEntry 3 }
 
ol51nnMFBModDipLLW OBJECT-TYPE
        SYNTAX INTEGER {
                enabled(1),
                disabled(2)
                }
        ACCESS read-only
        STATUS mandatory
        DESCRIPTION
                "The low light warning configuration indicated by this module's
                dip switches."
        ::= { ol51nnMFBModEntry 4 }
 
ol51nnMFBPortTable OBJECT-TYPE
	SYNTAX SEQUENCE OF Ol51nnMFBPortEntry
	ACCESS not-accessible
	STATUS mandatory
	DESCRIPTION
		"A table of port-specific information for each port of
		this module type."
	::= { ol51nnMFB 2 }

ol51nnMFBPortEntry OBJECT-TYPE
	SYNTAX Ol51nnMFBPortEntry 
	ACCESS not-accessible
	STATUS mandatory
	DESCRIPTION
		"A list of module-specific information about a specific
		51nnM-FB port in the concentrator."
	INDEX { ol51nnMFBPortSlotIndex, ol51nnMFBPortIndex }
	::= { ol51nnMFBPortTable 1 }

Ol51nnMFBPortEntry ::=
	SEQUENCE {
		ol51nnMFBPortSlotIndex
			INTEGER,			
		ol51nnMFBPortIndex
			INTEGER,
		ol51nnMFBPortAdminState
			INTEGER,
		ol51nnMFBPortBuddySlot
			INTEGER,
		ol51nnMFBPortBuddyPort
			INTEGER,
		ol51nnMFBPortDipAdminState
			INTEGER
		}

ol51nnMFBPortSlotIndex OBJECT-TYPE
	SYNTAX INTEGER
	ACCESS read-only
	STATUS mandatory
	DESCRIPTION
		"The slot number of this port's module."
	::= { ol51nnMFBPortEntry 1 }


ol51nnMFBPortIndex OBJECT-TYPE
	SYNTAX INTEGER
	ACCESS read-only
	STATUS mandatory
	DESCRIPTION
		"The port number of this port."
	::= { ol51nnMFBPortEntry 2 }

ol51nnMFBPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFBPortEntry 3 }

ol51nnMFBPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFBPortEntry 4 }

ol51nnMFBPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFBPortEntry 5 }

ol51nnMFBPortDipAdminState OBJECT-TYPE
	SYNTAX INTEGER {
		enabled(1),
		disabled(2)
		}
	ACCESS read-only
	STATUS mandatory
	DESCRIPTION
		"The state of this port as indicated by the port's dip 
		switches."		
	::= { ol51nnMFBPortEntry 6 }



--
-- FDDI media module with ANSI MIC connector
--

ol53nnMFBMICModTable OBJECT-TYPE
	SYNTAX SEQUENCE OF Ol53nnMFBMICModEntry
	ACCESS not-accessible
	STATUS mandatory
	DESCRIPTION
		"A list of module attributes that apply to this model.
		To access an ol53nnMFBMICModTable entry, the 
		ol53nnMFBMICModSlotIndex attribute is used."
	::= { ol53nnMFBMIC 1 }

ol53nnMFBMICModEntry OBJECT-TYPE
	SYNTAX Ol53nnMFBMICModEntry 
	ACCESS not-accessible
	STATUS mandatory
	DESCRIPTION
		"A list of module-specific information about a specific
		53nnM-FBMIC module in the concentrator."
	INDEX { ol53nnMFBMICModSlotIndex }
	::= { ol53nnMFBMICModTable 1 }

Ol53nnMFBMICModEntry ::=
	SEQUENCE {
		ol53nnMFBMICModSlotIndex
			INTEGER,
		ol53nnMFBMICModDownStreamModule
			INTEGER,
		ol53nnMFBMICModUpStreamModule
			INTEGER,
		ol53nnMFBMICModDownStreamOperPath
			INTEGER,
		ol53nnMFBMICModUpStreamOperPath
			INTEGER,
		ol53nnMFBMICModRingInfo
			OCTET STRING
		}

ol53nnMFBMICModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMFBMICModEntry 1 }

ol53nnMFBMICModDownStreamModule OBJECT-TYPE
	SYNTAX INTEGER (1..16)
	ACCESS read-only
	STATUS mandatory
	DESCRIPTION
                "Down stream slot (transmit to)"
	::= { ol53nnMFBMICModEntry 2 }

ol53nnMFBMICModUpStreamModule OBJECT-TYPE
	SYNTAX INTEGER (1..16)
	ACCESS read-only
	STATUS mandatory
	DESCRIPTION
                "Up stream slot (receve from)"
	::= { ol53nnMFBMICModEntry 3 }

ol53nnMFBMICModDownStreamOperPath OBJECT-TYPE
	SYNTAX INTEGER {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA  (debug only)"
	::= { ol53nnMFBMICModEntry 4 }

ol53nnMFBMICModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
        ACCESS read-only
	STATUS mandatory
	DESCRIPTION
                "Receive DBA (debug only)"
	::= { ol53nnMFBMICModEntry 5 }

ol53nnMFBMICModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMFBMICModEntry 6 }


-- port table

ol53nnMFBMICPortTable OBJECT-TYPE
	SYNTAX SEQUENCE OF Ol53nnMFBMICPortEntry
	ACCESS not-accessible
	STATUS mandatory
	DESCRIPTION
		"A table of port-specific information for each port of
		this module type."
	::= { ol53nnMFBMIC 2 }

ol53nnMFBMICPortEntry OBJECT-TYPE
	SYNTAX Ol53nnMFBMICPortEntry 
	ACCESS not-accessible
	STATUS mandatory
	DESCRIPTION
		"A list of module-specific information about a specific
		53nnM-FBMIC port in the concentrator."
	INDEX { ol53nnMFBMICPortSlotIndex, ol53nnMFBMICPortIndex }
	::= { ol53nnMFBMICPortTable 1 }

Ol53nnMFBMICPortEntry ::=
	SEQUENCE {
		ol53nnMFBMICPortSlotIndex
			INTEGER,			
		ol53nnMFBMICPortIndex
			INTEGER,
		ol53nnMFBMICPortConfig
			INTEGER,
		ol53nnMFBMICPortPcmState
			INTEGER,
		ol53nnMFBMICPortConnectState
			INTEGER,
		ol53nnMFBMICPortNeighbor
			INTEGER,
		ol53nnMFBMICPortRemoteMACIndicated
			INTEGER,
		ol53nnMFBMICPortBSFlag
			INTEGER,
		ol53nnMFBMICPortPCWithhold
			INTEGER,
		ol53nnMFBMICPortLerCondition
			INTEGER
		}

ol53nnMFBMICPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMFBMICPortEntry 1 }


ol53nnMFBMICPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMFBMICPortEntry 2 }

ol53nnMFBMICPortConfig OBJECT-TYPE
	SYNTAX INTEGER {
                slave(3),
                master(4)
		}
	ACCESS read-write
	STATUS mandatory
	DESCRIPTION
                "Specifies the FDDI port type. If the port is on an
                 FPM, the only allowed values are slave(3), and master(4).
                 In addition, there can only be one active slave port on any
                 concentrator FDDI network."
	::= { ol53nnMFBMICPortEntry 3 }

ol53nnMFBMICPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMFBMICPortEntry 4 }

ol53nnMFBMICPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMFBMICPortEntry 5 }

ol53nnMFBMICPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMFBMICPortEntry 6 }

ol53nnMFBMICPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMFBMICPortEntry 7 }

ol53nnMFBMICPortBSFlag OBJECT-TYPE
	SYNTAX INTEGER { true(1), false(2) }
	ACCESS read-only
	STATUS mandatory
	DESCRIPTION
          "The Break State, BS_Flag (refer to ANSI SMT
           9.4.3.4)."
	::= { ol53nnMFBMICPortEntry 8 }

ol53nnMFBMICPortPCWithhold OBJECT-TYPE
	SYNTAX INTEGER  { none(1), m-m(2), other(3) }
	ACCESS read-only
	STATUS mandatory
	DESCRIPTION
           "PC_Withhold, (refer to ANSI SMT 9.4.1)."
	::= { ol53nnMFBMICPortEntry 9 }

ol53nnMFBMICPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMFBMICPortEntry 10 }


-- Trunk Table
-- (only present for compatibility)

ol53nnMFBMICTrunkTable OBJECT-TYPE
	SYNTAX SEQUENCE OF Ol53nnMFBMICTrunkEntry
	ACCESS not-accessible
	STATUS mandatory
	DESCRIPTION
                "FDDI module specific trunk table variables.
                 At present there are none."
	::= { ol53nnMFBMIC 3 }

ol53nnMFBMICTrunkEntry OBJECT-TYPE
	SYNTAX Ol53nnMFBMICTrunkEntry
	ACCESS not-accessible
	STATUS mandatory
	DESCRIPTION
		"A description of 53nnM-FBMIC trunk attributes."		
	INDEX { ol53nnMFBMICTrunkSlotIndex, ol53nnMFBMICTrunkIndex }
	::= { ol53nnMFBMICTrunkTable 1 }

Ol53nnMFBMICTrunkEntry ::= 
	SEQUENCE {
		ol53nnMFBMICTrunkSlotIndex	
			INTEGER,
		ol53nnMFBMICTrunkIndex
			INTEGER
		}

ol53nnMFBMICTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMFBMICTrunkEntry 1 }


ol53nnMFBMICTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMFBMICTrunkEntry 2 }



--
-- FDDI media module with ST connector
--

ol53nnMFIBSTModTable OBJECT-TYPE
	SYNTAX SEQUENCE OF Ol53nnMFIBSTModEntry
	ACCESS not-accessible
	STATUS mandatory
	DESCRIPTION
		"A list of module attributes that apply to this model.
		To access an ol53nnMFIBSTModTable entry, the 
		ol53nnMFIBSTModSlotIndex attribute is used."
	::= { ol53nnMFIBST 1 }

ol53nnMFIBSTModEntry OBJECT-TYPE
	SYNTAX Ol53nnMFIBSTModEntry 
	ACCESS not-accessible
	STATUS mandatory
	DESCRIPTION
		"A list of module-specific information about a specific
		53nnM-FIBST module in the concentrator."
	INDEX { ol53nnMFIBSTModSlotIndex }
	::= { ol53nnMFIBSTModTable 1 }

Ol53nnMFIBSTModEntry ::=
	SEQUENCE {
		ol53nnMFIBSTModSlotIndex
			INTEGER,
		ol53nnMFIBSTModDownStreamModule
			INTEGER,
		ol53nnMFIBSTModUpStreamModule
			INTEGER,
		ol53nnMFIBSTModDownStreamOperPath
			INTEGER,
		ol53nnMFIBSTModUpStreamOperPath
			INTEGER,
		ol53nnMFIBSTModRingInfo
			OCTET STRING
		}

ol53nnMFIBSTModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMFIBSTModEntry 1 }

ol53nnMFIBSTModDownStreamModule OBJECT-TYPE
	SYNTAX INTEGER (1..16)
	ACCESS read-only
	STATUS mandatory
	DESCRIPTION
                "Down stream slot (transmit to)"
	::= { ol53nnMFIBSTModEntry 2 }

ol53nnMFIBSTModUpStreamModule OBJECT-TYPE
	SYNTAX INTEGER (1..16)
	ACCESS read-only
	STATUS mandatory
	DESCRIPTION
                "Up stream slot (receve from)"
	::= { ol53nnMFIBSTModEntry 3 }

ol53nnMFIBSTModDownStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA (debug only)"
	::= { ol53nnMFIBSTModEntry 4 }

ol53nnMFIBSTModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Receive DBA (debug only)"
	::= { ol53nnMFIBSTModEntry 5 }

ol53nnMFIBSTModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMFIBSTModEntry 6 }


-- port table

ol53nnMFIBSTPortTable OBJECT-TYPE
	SYNTAX SEQUENCE OF Ol53nnMFIBSTPortEntry
	ACCESS not-accessible
	STATUS mandatory
	DESCRIPTION
		"A table of port-specific information for each port of
		this module type."
	::= { ol53nnMFIBST 2 }

ol53nnMFIBSTPortEntry OBJECT-TYPE
	SYNTAX Ol53nnMFIBSTPortEntry 
	ACCESS not-accessible
	STATUS mandatory
	DESCRIPTION
		"A list of module-specific information about a specific
		53nnM-FIBST port in the concentrator."
	INDEX { ol53nnMFIBSTPortSlotIndex, ol53nnMFIBSTPortIndex }
	::= { ol53nnMFIBSTPortTable 1 }

Ol53nnMFIBSTPortEntry ::=
	SEQUENCE {
		ol53nnMFIBSTPortSlotIndex
			INTEGER,			
		ol53nnMFIBSTPortIndex
			INTEGER,
		ol53nnMFIBSTPortConfig
			INTEGER,
		ol53nnMFIBSTPortPcmState
			INTEGER,
		ol53nnMFIBSTPortConnectState
			INTEGER,
		ol53nnMFIBSTPortNeighbor
			INTEGER,
		ol53nnMFIBSTPortRemoteMACIndicated
			INTEGER,
		ol53nnMFIBSTPortBSFlag
			INTEGER,
		ol53nnMFIBSTPortPCWithhold
			INTEGER,
		ol53nnMFIBSTPortLerCondition
			INTEGER
		}

ol53nnMFIBSTPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMFIBSTPortEntry 1 }


ol53nnMFIBSTPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMFIBSTPortEntry 2 }

ol53nnMFIBSTPortConfig OBJECT-TYPE
	SYNTAX INTEGER {
                slave(3),
                master(4)
		}
	ACCESS read-write
	STATUS mandatory
	DESCRIPTION
                "Specifies the FDDI port type. If the port is on an
                 FPM, the only allowed values are slave(3) and master(4).
                 In addition, there can only be one active slave port on any
                 concentrator FDDI network."
	::= { ol53nnMFIBSTPortEntry 3 }

ol53nnMFIBSTPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMFIBSTPortEntry 4 }

ol53nnMFIBSTPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMFIBSTPortEntry 5 }

ol53nnMFIBSTPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMFIBSTPortEntry 6 }

ol53nnMFIBSTPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMFIBSTPortEntry 7 }

ol53nnMFIBSTPortBSFlag OBJECT-TYPE
	SYNTAX INTEGER { true(1), false(2) }
	ACCESS read-only
	STATUS mandatory
	DESCRIPTION
          "The Break State, BS_Flag (refer to ANSI SMT
           9.4.3.4)."
	::= { ol53nnMFIBSTPortEntry 8 }

ol53nnMFIBSTPortPCWithhold OBJECT-TYPE
	SYNTAX INTEGER  { none(1), m-m(2), other(3) }
	ACCESS read-only
	STATUS mandatory
	DESCRIPTION
           "PC_Withhold, (refer to ANSI SMT 9.4.1)."
	::= { ol53nnMFIBSTPortEntry 9 }

ol53nnMFIBSTPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMFIBSTPortEntry 10 }



-- Trunk Table
-- (only present for compatibility)

ol53nnMFIBSTTrunkTable OBJECT-TYPE
	SYNTAX SEQUENCE OF Ol53nnMFIBSTTrunkEntry
	ACCESS not-accessible
	STATUS mandatory
	DESCRIPTION
                "FDDI module specific trunk table variables.
                 At present there are none."
	::= { ol53nnMFIBST 3 }

ol53nnMFIBSTTrunkEntry OBJECT-TYPE
	SYNTAX Ol53nnMFIBSTTrunkEntry
	ACCESS not-accessible
	STATUS mandatory
	DESCRIPTION
		"A description of 53nnM-FIBST trunk attributes."		
	INDEX { ol53nnMFIBSTTrunkSlotIndex, ol53nnMFIBSTTrunkIndex }
	::= { ol53nnMFIBSTTrunkTable 1 }

Ol53nnMFIBSTTrunkEntry ::= 
	SEQUENCE {
		ol53nnMFIBSTTrunkSlotIndex	
			INTEGER,
		ol53nnMFIBSTTrunkIndex
			INTEGER
		}

ol53nnMFIBSTTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMFIBSTTrunkEntry 1 }


ol53nnMFIBSTTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMFIBSTTrunkEntry 2 }


--
-- FDDI media module with coper connector
--

ol53nnMSTPModTable OBJECT-TYPE
	SYNTAX SEQUENCE OF Ol53nnMSTPModEntry
	ACCESS not-accessible
	STATUS mandatory
	DESCRIPTION
		"A list of module attributes that apply to this model.
		To access an ol53nnMSTPModTable entry, the 
		ol53nnMSTPModSlotIndex attribute is used."
	::= { ol53nnMSTP 1 }

ol53nnMSTPModEntry OBJECT-TYPE
	SYNTAX Ol53nnMSTPModEntry 
	ACCESS not-accessible
	STATUS mandatory
	DESCRIPTION
		"A list of module-specific information about a specific
		53nnM-FIBSTP module in the concentrator."
	INDEX { ol53nnMSTPModSlotIndex }
	::= { ol53nnMSTPModTable 1 }

Ol53nnMSTPModEntry ::=
	SEQUENCE {
		ol53nnMSTPModSlotIndex
			INTEGER,
		ol53nnMSTPModDownStreamModule
			INTEGER,
		ol53nnMSTPModUpStreamModule
			INTEGER,
		ol53nnMSTPModDownStreamOperPath
			INTEGER,
		ol53nnMSTPModUpStreamOperPath
			INTEGER,
		ol53nnMSTPModRingInfo
			OCTET STRING
		}

ol53nnMSTPModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMSTPModEntry 1 }

ol53nnMSTPModDownStreamModule OBJECT-TYPE
	SYNTAX INTEGER (1..16)
	ACCESS read-only
	STATUS mandatory
	DESCRIPTION
                "Down stream slot (transmit to)"
	::= { ol53nnMSTPModEntry 2 }

ol53nnMSTPModUpStreamModule OBJECT-TYPE
	SYNTAX INTEGER (1..16)
	ACCESS read-only
	STATUS mandatory
	DESCRIPTION
                "Down stream slot (receve from)"
	::= { ol53nnMSTPModEntry 3 }

ol53nnMSTPModDownStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "transmit DBA  (debug only)"
	::= { ol53nnMSTPModEntry 4 }

ol53nnMSTPModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "receive DBA  (debug only)"
	::= { ol53nnMSTPModEntry 5 }

ol53nnMSTPModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMSTPModEntry 6 }


-- port table

ol53nnMSTPPortTable OBJECT-TYPE
	SYNTAX SEQUENCE OF Ol53nnMSTPPortEntry
	ACCESS not-accessible
	STATUS mandatory
	DESCRIPTION
		"A table of port-specific information for each port of
		this module type."
	::= { ol53nnMSTP 2 }

ol53nnMSTPPortEntry OBJECT-TYPE
	SYNTAX Ol53nnMSTPPortEntry 
	ACCESS not-accessible
	STATUS mandatory
	DESCRIPTION
		"A list of module-specific information about a specific
		53nnM-STP port in the concentrator."
	INDEX { ol53nnMSTPPortSlotIndex, ol53nnMSTPPortIndex }
	::= { ol53nnMSTPPortTable 1 }

Ol53nnMSTPPortEntry ::=
	SEQUENCE {
		ol53nnMSTPPortSlotIndex
			INTEGER,			
		ol53nnMSTPPortIndex
			INTEGER,
		ol53nnMSTPPortConfig
			INTEGER,
		ol53nnMSTPPortPcmState
			INTEGER,
		ol53nnMSTPPortConnectState
			INTEGER,
		ol53nnMSTPPortNeighbor
			INTEGER,
		ol53nnMSTPPortRemoteMACIndicated
			INTEGER,
		ol53nnMSTPPortBSFlag
			INTEGER,
		ol53nnMSTPPortPCWithhold
			INTEGER,
		ol53nnMSTPPortLerCondition
			INTEGER,
		ol53nnMSTPPortPersonality
			INTEGER
		}

ol53nnMSTPPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMSTPPortEntry 1 }


ol53nnMSTPPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMSTPPortEntry 2 }

ol53nnMSTPPortConfig OBJECT-TYPE
	SYNTAX INTEGER {
                slave(3),
                master(4)
		}
	ACCESS read-write
	STATUS mandatory
	DESCRIPTION
                "Specifies the FDDI port type. If the port is on an
                 FPM, the only allowed values are slave(3) and master(4).
                 In addition, there can only be one active slave port on any
                 concentrator FDDI network."
	::= { ol53nnMSTPPortEntry 3 }

ol53nnMSTPPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMSTPPortEntry 4 }

ol53nnMSTPPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMSTPPortEntry 5 }

ol53nnMSTPPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMSTPPortEntry 6 }

ol53nnMSTPPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMSTPPortEntry 7 }

ol53nnMSTPPortBSFlag OBJECT-TYPE
	SYNTAX INTEGER { true(1), false(2) }
	ACCESS read-only
	STATUS mandatory
	DESCRIPTION
          "The Break State, BS_Flag (refer to ANSI SMT
           9.4.3.4)."
	::= { ol53nnMSTPPortEntry 8 }

ol53nnMSTPPortPCWithhold OBJECT-TYPE
	SYNTAX INTEGER  { none(1), m-m(2), other(3) }
	ACCESS read-only
	STATUS mandatory
	DESCRIPTION
           "PC_Withhold, (refer to ANSI SMT 9.4.1)."
	::= { ol53nnMSTPPortEntry 9 }

ol53nnMSTPPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMSTPPortEntry 10 }


ol53nnMSTPPortPersonality OBJECT-TYPE
	SYNTAX INTEGER {
                sddi(1),
                tpddi(2)
		}
	ACCESS read-write
	STATUS mandatory
	DESCRIPTION
                "Specifies the physical signaling used by the port, the only 
		 valid values are sddi(3) and tpddi(4)."
	::= { ol53nnMSTPPortEntry 11 }


-- Trunk Table
-- (only present for compatibility)

ol53nnMSTPTrunkTable OBJECT-TYPE
	SYNTAX SEQUENCE OF Ol53nnMSTPTrunkEntry
	ACCESS not-accessible
	STATUS mandatory
	DESCRIPTION
                "FDDI module specific trunk table variables.
                 At present there are none."
	::= { ol53nnMSTP 3 }

ol53nnMSTPTrunkEntry OBJECT-TYPE
	SYNTAX Ol53nnMSTPTrunkEntry
	ACCESS not-accessible
	STATUS mandatory
	DESCRIPTION
		"A description of 53nnM-STP trunk attributes."		
	INDEX { ol53nnMSTPTrunkSlotIndex, ol53nnMSTPTrunkIndex }
	::= { ol53nnMSTPTrunkTable 1 }

Ol53nnMSTPTrunkEntry ::= 
	SEQUENCE {
		ol53nnMSTPTrunkSlotIndex	
			INTEGER,
		ol53nnMSTPTrunkIndex
			INTEGER
		}

ol53nnMSTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMSTPTrunkEntry 1 }


ol53nnMSTPTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMSTPTrunkEntry 2 }


-- 
-- ONline Ethernet 10BASE-T Per-Connector Module
--

ol51nnMTPCLModTable OBJECT-TYPE
 	SYNTAX SEQUENCE OF Ol51nnMTPCLModEntry
 	ACCESS not-accessible
	STATUS mandatory
	DESCRIPTION
		"A list of module-specific information about a specific
		51nnM-TPCL module in the concentrator."
	::= { ol51nnMTPCL 1 }

ol51nnMTPCLModEntry OBJECT-TYPE
	SYNTAX Ol51nnMTPCLModEntry 
	ACCESS not-accessible
	STATUS mandatory
	DESCRIPTION
		"A list of module-specific information about a specific
		51nnM-TPCL module in the concentrator."
	INDEX { ol51nnMTPCLModSlotIndex }
	::= { ol51nnMTPCLModTable 1 }

Ol51nnMTPCLModEntry ::=
	SEQUENCE {
		ol51nnMTPCLModSlotIndex
			INTEGER,
		ol51nnMTPCLModMonitorConn
			INTEGER,
		ol51nnMTPCLModConn1Network
			INTEGER,
		ol51nnMTPCLModConn2Network
			INTEGER,
		ol51nnMTPCLModConn1DipNetwork
			INTEGER,
		ol51nnMTPCLModConn2DipNetwork
			INTEGER,
		ol51nnMTPCLModAutoPartition
			INTEGER
		}

ol51nnMTPCLModSlotIndex OBJECT-TYPE
	SYNTAX INTEGER
	ACCESS read-only
	STATUS mandatory
	DESCRIPTION
		"The slot number of this module."
	::= { ol51nnMTPCLModEntry 1 }

ol51nnMTPCLModMonitorConn OBJECT-TYPE
	SYNTAX INTEGER {
		connector-1(1),
		connector-2(2)
		}
	ACCESS read-write
	STATUS mandatory
	DESCRIPTION
		"When both connectors are on the same network:

		   Setting this object to connector-1 allows the EMM to 
                   monitor the port statistics of port 1-12 on a per-port 
                   basis, and the port statistics of port 13-24 are summed
                   and are reported through port 13.  

                   Setting this object to connector-2 allows the EMM to 
                   monitor the port statistics of port 12-24 on a per-port
                   basis, and the port statistics of port 1-12 are summed 
                   and are reported through port 13.

	         Note: when the 2 connectors are on different networks,
	   	 setting this object to the value connector-1 or 
                 connector-2 will not have any effect.  The port counters 
                 will be cleared whenever the value of this object is 
                 changed."
	::= { ol51nnMTPCLModEntry 2 }

ol51nnMTPCLModConn1Network OBJECT-TYPE
	SYNTAX INTEGER {
		ethernet-1(6),
		ethernet-2(7),
		ethernet-3(8), 
		isolated-1(21),
		isolated-2(22)
		}
	ACCESS read-write
	STATUS mandatory
	DESCRIPTION
		"The network that this connector is attached to."
	::= { ol51nnMTPCLModEntry 3 }

ol51nnMTPCLModConn2Network OBJECT-TYPE
	SYNTAX INTEGER {
		ethernet-1(6),
		ethernet-2(7),
		ethernet-3(8),
		isolated-1(21),
		isolated-2(22)
		}
	ACCESS read-write
	STATUS mandatory
	DESCRIPTION
		"The network that this connector is attached to."

	::= { ol51nnMTPCLModEntry 4 }

ol51nnMTPCLModConn1DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ol51nnMTPCLModEntry 5 }

ol51nnMTPCLModConn2DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ol51nnMTPCLModEntry 6 }

ol51nnMTPCLModAutoPartition OBJECT-TYPE
	SYNTAX INTEGER {
		collisions-31(1),
		collisions-63(2),
		collisions-127(3),
		collisions-255(4)
		}
	ACCESS read-write
	STATUS mandatory
	DESCRIPTION
		"This object holds the consecutive collision count 
                 limit value.  The module goes into the auto-partition 
                 mode whenever the consecutive collision count exceeds
                 the consecutive collision limit count."	
	::= { ol51nnMTPCLModEntry 7 }

ol51nnMTPCLPortTable OBJECT-TYPE
	SYNTAX SEQUENCE OF Ol51nnMTPCLPortEntry
	ACCESS not-accessible
	STATUS mandatory
	DESCRIPTION
		"A table of port-specific information for each port of
		this module type."
	::= { ol51nnMTPCL 2 }

ol51nnMTPCLPortEntry OBJECT-TYPE
	SYNTAX Ol51nnMTPCLPortEntry 
	ACCESS not-accessible
	STATUS mandatory
	DESCRIPTION
		"A list of module-specific information about a specific
		51nnM-TPCL port in the concentrator."
	INDEX { ol51nnMTPCLPortSlotIndex, ol51nnMTPCLPortIndex }
	::= { ol51nnMTPCLPortTable 1 }

Ol51nnMTPCLPortEntry ::=
	SEQUENCE {
		ol51nnMTPCLPortSlotIndex
			INTEGER,			
		ol51nnMTPCLPortIndex
			INTEGER,
		ol51nnMTPCLPortAdminState
			INTEGER,
		ol51nnMTPCLPortBuddySlot
			INTEGER,
		ol51nnMTPCLPortBuddyPort
			INTEGER,
		ol51nnMTPCLPortDipAdminState
			INTEGER,
		ol51nnMTPCLPortLinkInteg
			INTEGER,
		ol51nnMTPCLPortDipLinkInteg
			INTEGER
		}

ol51nnMTPCLPortSlotIndex OBJECT-TYPE
	SYNTAX INTEGER
	ACCESS read-only
	STATUS mandatory
	DESCRIPTION
		"The slot number of this port's module."
	::= { ol51nnMTPCLPortEntry 1 }


ol51nnMTPCLPortIndex OBJECT-TYPE
	SYNTAX INTEGER
	ACCESS read-only
	STATUS mandatory
	DESCRIPTION
		"The port number of this port."
	::= { ol51nnMTPCLPortEntry 2 }

ol51nnMTPCLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPCLPortEntry 3 }

ol51nnMTPCLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."
	::= { ol51nnMTPCLPortEntry 4 }

ol51nnMTPCLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPCLPortEntry 5 }

ol51nnMTPCLPortDipAdminState OBJECT-TYPE
	SYNTAX INTEGER {
		enabled(1),
		disabled(2)
		}
	ACCESS read-only
	STATUS mandatory
	DESCRIPTION
		"The state of this port as indicated by the port's dip 
		switches."		
	::= { ol51nnMTPCLPortEntry 6 }

ol51nnMTPCLPortLinkInteg OBJECT-TYPE
	SYNTAX INTEGER {
		enabled(1),
		disabled(2)
		}
	ACCESS read-write
	STATUS mandatory
	DESCRIPTION
		"The current link integrity configuration for this port."
	::= { ol51nnMTPCLPortEntry 7 }

ol51nnMTPCLPortDipLinkInteg OBJECT-TYPE
	SYNTAX INTEGER {
		enabled(1),
		disabled(2)
		}
	ACCESS read-only
	STATUS mandatory
	DESCRIPTION
		"The link integrity configuration as indicated by this
		dip switch."
	::= { ol51nnMTPCLPortEntry 8 }


--
-- ONline Token Ring to Token Ring Bridge Module
--

ol52nnBTTModTable OBJECT-TYPE
        SYNTAX SEQUENCE OF Ol52nnBTTModEntry
        ACCESS not-accessible
        STATUS mandatory
        DESCRIPTION
                "A table of module-specific information for each
                52nnB-TT module in the concentrator."
        ::= { ol52nnBTT 1 }

ol52nnBTTModEntry OBJECT-TYPE
        SYNTAX Ol52nnBTTModEntry
        ACCESS not-accessible
        STATUS mandatory
        DESCRIPTION
                "A list of module-specific information about a specific
                52nnB-TT module in the concentrator."
        INDEX { ol52nnBTTModSlotIndex }
        ::= {ol52nnBTTModTable 1 }

Ol52nnBTTModEntry ::=
        SEQUENCE {
                ol52nnBTTModSlotIndex
                        INTEGER,
                ol52nnBTTModBridgeType
                        INTEGER,
                ol52nnBTTModSoftwareVersion
                        DisplayString,
                ol52nnBTTModSRBridgeNo
                        INTEGER,
		ol52nnBTTModNetworkStatus
			INTEGER
        }
                
ol52nnBTTModSlotIndex OBJECT-TYPE
        SYNTAX INTEGER
        ACCESS read-only
        STATUS mandatory
        DESCRIPTION
                "The slot number of this module."
        ::= { ol52nnBTTModEntry 1 }
        
ol52nnBTTModBridgeType OBJECT-TYPE
        SYNTAX INTEGER {
                  bridge-type-sr(1),
                  bridge-type-srt(2)
                }
        ACCESS read-only
        STATUS mandatory
        DESCRIPTION
                "Whether the bridge is a source-routing bridge or a
                source-routing-transparent bridge."
        ::= { ol52nnBTTModEntry 2 }

ol52nnBTTModSoftwareVersion OBJECT-TYPE
       SYNTAX DisplayString (SIZE(1..10))
       ACCESS read-only
       STATUS mandatory
       DESCRIPTION
               "The version number of the software loaded into the
		module's flash chips."
       ::= { ol52nnBTTModEntry 3 }

ol52nnBTTModSRBridgeNo OBJECT-TYPE
        SYNTAX INTEGER
        ACCESS read-only
        STATUS mandatory
        DESCRIPTION
                "The module's source routing bridge number."
        ::= { ol52nnBTTModEntry 4 }

ol52nnBTTModNetworkStatus OBJECT-TYPE
	SYNTAX INTEGER {
		okay(1),
		closed(2),
		beaconing(3)
		}
	ACCESS read-only
	STATUS mandatory
	DESCRIPTION
		"The status of the ring containing this module."
	::= {ol52nnBTTModEntry 5}

ol52nnBTTPortTable OBJECT-TYPE
        SYNTAX SEQUENCE OF Ol52nnBTTPortEntry
        ACCESS not-accessible
        STATUS mandatory
        DESCRIPTION
                "A table of port-specific for each port of each
                52nnB-TT module i the concentrator."
        ::= { ol52nnBTT 2 }

ol52nnBTTPortEntry OBJECT-TYPE
        SYNTAX Ol52nnBTTPortEntry
        ACCESS not-accessible
        STATUS mandatory
        DESCRIPTION
                "A list of port-specific information about a specific
                52nnB-TT port in the concentrator."
        INDEX { ol52nnBTTPortSlotIndex, ol52nnBTTPortIndex }
        ::= { ol52nnBTTPortTable 1 }

Ol52nnBTTPortEntry ::=
        SEQUENCE {
                ol52nnBTTPortSlotIndex
                        INTEGER,
                ol52nnBTTPortIndex
                        INTEGER,
                ol52nnBTTPortConnector
                        INTEGER,
                ol52nnBTTPortSTAPState
                        INTEGER,
                ol52nnBTTPortIpAddress
                        IpAddress,
                ol52nnBTTPortMACAddress
                        OCTET STRING,
                ol52nnBTTPortThroughput
                        Gauge,
                ol52nnBTTPortForwarding
                        Gauge,
                ol52nnBTTPortSRRingNo
                        INTEGER,
                ol52nnBTTPortRingSpeed
                        INTEGER
                }

ol52nnBTTPortSlotIndex OBJECT-TYPE
        SYNTAX INTEGER
        ACCESS read-only
        STATUS mandatory
        DESCRIPTION
                "The slot number for this port's module."
        ::= { ol52nnBTTPortEntry 1 }

ol52nnBTTPortIndex OBJECT-TYPE
        SYNTAX INTEGER
        ACCESS read-only
        STATUS mandatory
        DESCRIPTION
                "The port number for this port within this slot."
        ::= { ol52nnBTTPortEntry 2 }
                
ol52nnBTTPortConnector OBJECT-TYPE
        SYNTAX INTEGER {
                backPlane(1),   -- connects directly to backplane
                rj45(8),        -- unshielded
                db-9(10)        -- shielded
                }
        ACCESS read-write
        STATUS mandatory
        DESCRIPTION
                "The port connector. Notice that setting port connector 
                 available only for the front pannel port."
        ::= { ol52nnBTTPortEntry 3 }

ol52nnBTTPortSTAPState OBJECT-TYPE
        SYNTAX INTEGER {
                disabled (1),	-- receive and process frames
		blocking (2),	-- receive and process frames 
		listening (3),  -- receive and process frames
		learning (4),	-- receive and process frames
		forwarding (5),	-- receive, process and forward frames
		off (6)		-- receive and discard frames
                }
        ACCESS read-only
        STATUS mandatory
        DESCRIPTION
                "The port connector. Notice that setting port connector
                 available only for the front pannel port."
        ::= { ol52nnBTTPortEntry 4 }


ol52nnBTTPortIpAddress OBJECT-TYPE
        SYNTAX IpAddress
        ACCESS read-only
        STATUS mandatory
        DESCRIPTION
                "The IP address associated with this port."
        ::= { ol52nnBTTPortEntry 5 }
                
ol52nnBTTPortMACAddress OBJECT-TYPE
        SYNTAX OCTET STRING (SIZE(6))
        ACCESS read-only
        STATUS mandatory
        DESCRIPTION
                "A 6 octet address that uniquely identifies this port."
        ::= { ol52nnBTTPortEntry 6 }
                
ol52nnBTTPortThroughput OBJECT-TYPE
        SYNTAX Gauge
        ACCESS read-only
        STATUS mandatory
        DESCRIPTION
                "Port throughput measured in Kbytes per second."
        ::= { ol52nnBTTPortEntry 7 }
                
ol52nnBTTPortForwarding OBJECT-TYPE
        SYNTAX Gauge
        ACCESS read-only
        STATUS mandatory
        DESCRIPTION
                "Port forwarding rate measured in frames per second."
        ::= { ol52nnBTTPortEntry 8 }
                
ol52nnBTTPortSRRingNo OBJECT-TYPE
        SYNTAX INTEGER
        ACCESS read-only
        STATUS mandatory
        DESCRIPTION
                "The port's source routing ring number."
        ::= { ol52nnBTTPortEntry 9 }

ol52nnBTTPortRingSpeed OBJECT-TYPE
        SYNTAX INTEGER {
                fourMegabit(1),
                sixteenMegabit(2)
                }
        ACCESS read-write
        STATUS mandatory
        DESCRIPTION     
                "The ring's bandwidth."
        ::= { ol52nnBTTPortEntry 10 }
                
                
--
-- Trunk table is for compatibility purposes only
--
 
ol52nnBTTTrunkTable  OBJECT-TYPE 
        SYNTAX SEQUENCE OF Ol52nnBTTTrunkEntry 
        ACCESS not-accessible
        STATUS mandatory 
        DESCRIPTION 
                "A table that contains trunk-specific information for 
                each trunk on each 52nnB-TT in the concentrator." 
        ::= {ol52nnBTT 3} 
 
ol52nnBTTTrunkEntry  OBJECT-TYPE 
        SYNTAX Ol52nnBTTTrunkEntry 
        ACCESS not-accessible 
        STATUS mandatory 
        DESCRIPTION 
                "A list of information about a specific Trunk on a 
                52nnB-TT module in the concentrator." 
        INDEX {ol52nnBTTTrunkSlotIndex, ol52nnBTTTrunkIndex} 
        ::= {ol52nnBTTTrunkTable 1} 
 
Ol52nnBTTTrunkEntry ::= 
        SEQUENCE { 
                ol52nnBTTTrunkSlotIndex 
                        INTEGER, 
                ol52nnBTTTrunkIndex 
                        INTEGER
                } 
 
ol52nnBTTTrunkSlotIndex OBJECT-TYPE 
        SYNTAX INTEGER 
        ACCESS read-only 
        STATUS mandatory 
        DESCRIPTION 
                "The slot number of this module. Its value ranges 
                between 1 and olConcNumSlots."
        ::= {ol52nnBTTTrunkEntry 1} 
  
ol52nnBTTTrunkIndex OBJECT-TYPE
        SYNTAX INTEGER 
        ACCESS read-only 
        STATUS mandatory 
        DESCRIPTION 
                "The trunk number of this module. Its value ranges 
                between 1 and olModNumTrunks." 
        ::= {ol52nnBTTTrunkEntry 2} 


--
-- Token ring management module
--

ol52nnMMGTModTable  OBJECT-TYPE
	SYNTAX SEQUENCE OF Ol52nnMMGTModEntry
	ACCESS not-accessible
	STATUS mandatory
	DESCRIPTION
		"A table that contains module information about
		each 52nnM-MGT in the concentrator."
	::= {ol52nnMMGT 1}

ol52nnMMGTModEntry  OBJECT-TYPE
	SYNTAX Ol52nnMMGTModEntry
	ACCESS not-accessible
	STATUS mandatory
	DESCRIPTION
		"A list of module information for each 52nnM-MGT
		in the concentrator."
	INDEX {ol52nnMMGTModSlotIndex}
	::= {ol52nnMMGTModTable 1}

Ol52nnMMGTModEntry ::=
	SEQUENCE {
		ol52nnMMGTModSlotIndex
			INTEGER,
		ol52nnMMGTModMasterPriority
			INTEGER,
		ol52nnMMGTModMasterStatus
			INTEGER,
		ol52nnMMGTModStationAddr
			OCTET STRING,
		ol52nnMMGTModRingSpeed
			INTEGER,
		ol52nnMMGTModNetworkStatus
			INTEGER
		}

ol52nnMMGTModSlotIndex OBJECT-TYPE
	SYNTAX INTEGER
	ACCESS read-only
	STATUS mandatory
	DESCRIPTION
		"The slot number of this module. Its value ranges
		between 1 and olConcNumSlots."
	::= {ol52nnMMGTModEntry 1}

ol52nnMMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {ol52nnMMGTModEntry 2}

ol52nnMMGTModMasterStatus OBJECT-TYPE
	SYNTAX INTEGER {
		master(1),
		non-master(2),
		electing(3)
		}
	ACCESS read-only
	STATUS mandatory
	DESCRIPTION
		"The mastership status of this agent."
	::= {ol52nnMMGTModEntry 3}

ol52nnMMGTModStationAddr OBJECT-TYPE
	SYNTAX OCTET STRING
	ACCESS read-only
	STATUS mandatory
	DESCRIPTION
		"A 6 octet address that uniquely identifies this module.
		The station address is the MAC address of port 1."
	::= {ol52nnMMGTModEntry 4}

ol52nnMMGTModRingSpeed OBJECT-TYPE
	SYNTAX INTEGER {
		fourMegabit(1),
		sixteenMegabit(2)
		}
	ACCESS read-write
	STATUS mandatory
	DESCRIPTION
		"The ring's bandwidth."
	::= {ol52nnMMGTModEntry 5}

ol52nnMMGTModNetworkStatus OBJECT-TYPE
	SYNTAX INTEGER {
		okay(1),
		closed(2),
		beaconing(3)
		}
	ACCESS read-only
	STATUS mandatory
	DESCRIPTION
		"The status of the ring containing this module."
	::= {ol52nnMMGTModEntry 6}


ol52nnMMGTPortTable  OBJECT-TYPE
	SYNTAX SEQUENCE OF Ol52nnMMGTPortEntry
	ACCESS not-accessible
	STATUS mandatory
	DESCRIPTION
		"A table that contains port-specific information for
		each port on each 52nnM-MGT in the concentrator."
	::= {ol52nnMMGT 2}

ol52nnMMGTPortEntry  OBJECT-TYPE
	SYNTAX Ol52nnMMGTPortEntry
	ACCESS not-accessible
	STATUS mandatory
	DESCRIPTION
		"A list of information about a specific port on a
		52nnM-MGT module in the concentrator."
	INDEX {ol52nnMMGTPortSlotIndex, ol52nnMMGTPortIndex}
	::= {ol52nnMMGTPortTable 1}

Ol52nnMMGTPortEntry ::=
	SEQUENCE {
		ol52nnMMGTPortSlotIndex
			INTEGER,
		ol52nnMMGTPortIndex
			INTEGER,
		ol52nnMMGTPortIpAddress
			IpAddress
		}

ol52nnMMGTPortSlotIndex OBJECT-TYPE
	SYNTAX INTEGER
	ACCESS read-only
	STATUS mandatory
	DESCRIPTION
		"The slot number of this port's module."
	::= {ol52nnMMGTPortEntry 1}

ol52nnMMGTPortIndex OBJECT-TYPE
	SYNTAX INTEGER
	ACCESS read-only
	STATUS mandatory
	DESCRIPTION
		"The port number of this port."
	::= {ol52nnMMGTPortEntry 2}

ol52nnMMGTPortIpAddress  OBJECT-TYPE
	SYNTAX IpAddress
	ACCESS read-write
	STATUS mandatory
	DESCRIPTION
		"The IP address associated with this port."
	::= {ol52nnMMGTPortEntry 3}

ol52nnMMGTTrunkTable  OBJECT-TYPE
	SYNTAX SEQUENCE OF Ol52nnMMGTTrunkEntry
	ACCESS not-accessible
	STATUS mandatory
	DESCRIPTION
		"A table that contains trunk-specific information for
		each trunk on each 52nnM-MGT in the concentrator."
	::= {ol52nnMMGT 3}

ol52nnMMGTTrunkEntry  OBJECT-TYPE
	SYNTAX Ol52nnMMGTTrunkEntry
	ACCESS not-accessible
	STATUS mandatory
	DESCRIPTION
		"A list of information about a specific Trunk on a
		52nnM-MGT module in the concentrator."
	INDEX {ol52nnMMGTTrunkSlotIndex, ol52nnMMGTTrunkIndex}
	::= {ol52nnMMGTTrunkTable 1}

Ol52nnMMGTTrunkEntry ::=
	SEQUENCE {
		ol52nnMMGTTrunkSlotIndex
			INTEGER,
		ol52nnMMGTTrunkIndex
			INTEGER,
		ol52nnMMGTTrunkCableMon
			INTEGER,
		ol52nnMMGTTrunkNetMapState
			INTEGER,
	        ol52nnMMGTTrunkExtBcnRecovery
			INTEGER
		}

ol52nnMMGTTrunkSlotIndex OBJECT-TYPE
	SYNTAX INTEGER
	ACCESS read-only
	STATUS mandatory
	DESCRIPTION
		"The slot number of this module. Its value ranges
		between 1 and olConcNumSlots."
	::= {ol52nnMMGTTrunkEntry 1}

ol52nnMMGTTrunkIndex OBJECT-TYPE
	SYNTAX INTEGER
	ACCESS read-only
	STATUS mandatory
	DESCRIPTION
		"The slot number of this module. Its value ranges
		between 1 and olModNumTrunks."
	::= {ol52nnMMGTTrunkEntry 2}

ol52nnMMGTTrunkCableMon OBJECT-TYPE
	SYNTAX INTEGER {
		enable(1),
		disable(2),
		notApplicable(3)
		}
	ACCESS read-write
	STATUS mandatory
	DESCRIPTION
		"The cable monitor configuration for this trunk."
	::= {ol52nnMMGTTrunkEntry 3}

ol52nnMMGTTrunkNetMapState OBJECT-TYPE
	SYNTAX INTEGER {
		notApplicable(1),
		internal(2),
		external(3)
		}
	ACCESS read-write
	STATUS mandatory
	DESCRIPTION
		"The map state of the copper ring-in trunk. This
		should be set to external for ring-in trunks which
		connect to external hubs. The mapping logic will not
		operate on trunks which are set to external. This
		prevents incorrect mapping which can occur when a
		module in one hub detects the mapping signal from
		another hub. This attribute only applies to copper
		ring-in trunks."
	::= {ol52nnMMGTTrunkEntry 4}


ol52nnMMGTTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol52nnMMGTTrunkEntry 5 }



--
-- ONline Ethernet Interconnect Module
--

ol51nnIxModTable OBJECT-TYPE
	SYNTAX SEQUENCE OF Ol51nnIxModEntry
	ACCESS not-accessible
	STATUS mandatory
	DESCRIPTION
		"A table of module-specific information for
		each 51nnI-x module in the concentrator."
	::= { ol51nnIx 1 }

ol51nnIxModEntry OBJECT-TYPE
	SYNTAX Ol51nnIxModEntry
	ACCESS not-accessible
	STATUS mandatory
	DESCRIPTION
		"A list of module-specific information about a specific
		51nnI-x module in the concentrator."
	INDEX { ol51nnIxModSlotIndex }
	::= { ol51nnIxModTable 1 }

Ol51nnIxModEntry ::= 
	SEQUENCE {
		ol51nnIxModSlotIndex
			INTEGER,	
		ol51nnIxModSwType
			INTEGER,
		ol51nnIxModStationAddr
			OCTET STRING,
		ol51nnIxModDipPromDefaults
			INTEGER,
		ol51nnIxModProtocols
			DisplayString
		}

ol51nnIxModSlotIndex OBJECT-TYPE
	SYNTAX INTEGER
	ACCESS read-only
	STATUS mandatory
	DESCRIPTION
		"The slot number of this module."
	::= { ol51nnIxModEntry 1 }

ol51nnIxModSwType OBJECT-TYPE
	SYNTAX INTEGER {
		bridge(1),
		switch(2),
		router(3)
		}
	ACCESS read-only
	STATUS mandatory
	DESCRIPTION
		"The software currently loaded and executing has the
                module operating as a Bridge, Switch or Router."
	::= { ol51nnIxModEntry 2 }

ol51nnIxModStationAddr OBJECT-TYPE
	SYNTAX OCTET STRING (SIZE(6))
	ACCESS read-only
	STATUS mandatory
	DESCRIPTION
		"A 6 octet address that uniquely identifies this module.
		The station address is the mac address of port 1."
	::= { ol51nnIxModEntry 3 }

ol51nnIxModDipPromDefaults OBJECT-TYPE
	SYNTAX INTEGER {
		true(1),
		false(2)
		}
	ACCESS read-only
	STATUS mandatory
	DESCRIPTION
		"The current module configuration with respect to 
		default PROM values as specified by dip switches."
	::= { ol51nnIxModEntry 4 }


ol51nnIxModProtocols OBJECT-TYPE
	SYNTAX DisplayString
	ACCESS read-only
	STATUS mandatory
	DESCRIPTION
		"A textual description of the protocols supported by 
		this module"
	::= { ol51nnIxModEntry 5 }
		
	
ol51nnIxPortTable	OBJECT-TYPE
	SYNTAX SEQUENCE OF Ol51nnIxPortEntry
	ACCESS not-accessible
	STATUS mandatory
	DESCRIPTION
		"A table of port-specific information for each port of
                each 51nnI-x module in the concentrator."
	::= { ol51nnIx 2 }


ol51nnIxPortEntry OBJECT-TYPE
	SYNTAX Ol51nnIxPortEntry
	ACCESS not-accessible
	STATUS mandatory
	DESCRIPTION
		"A list of port-specific information about a specific
		51nnI-x port in the concentrator."
        INDEX { ol51nnIxPortSlotIndex, ol51nnIxPortIndex }
	::= { ol51nnIxPortTable 1 }

Ol51nnIxPortEntry ::= 
	SEQUENCE {
		ol51nnIxPortSlotIndex
			INTEGER,
		ol51nnIxPortIndex
			INTEGER,
		ol51nnIxPortDipAdminState
			INTEGER,
		ol51nnIxPortSTAPState
			INTEGER,
		ol51nnIxPortIpAddress
			IpAddress,
		ol51nnIxPortDipNetwork
			INTEGER,
		ol51nnIxPortDefNetwork
			INTEGER
		}

ol51nnIxPortSlotIndex OBJECT-TYPE
	SYNTAX INTEGER
	ACCESS read-only
	STATUS mandatory
	DESCRIPTION
		"The slot number for this port's module."
	::= { ol51nnIxPortEntry 1 }

ol51nnIxPortIndex OBJECT-TYPE
	SYNTAX INTEGER
	ACCESS read-only
	STATUS mandatory
	DESCRIPTION
		"The port number for this port within this slot."
	::= { ol51nnIxPortEntry 2 }

ol51nnIxPortDipAdminState OBJECT-TYPE
        SYNTAX INTEGER {
                enabled(1),
                disabled(2)
                }
        ACCESS read-only
        STATUS mandatory
        DESCRIPTION
                "The state of this port as indicated by the port's dip
                switches."
        ::= { ol51nnIxPortEntry 3 }
 
ol51nnIxPortSTAPState OBJECT-TYPE
        SYNTAX INTEGER {
                disabled (1),	-- receive and process frames
		blocking (2),	-- receive and process frames 
		listening (3),  -- receive and process frames
		learning (4),	-- receive and process frames
		forwarding (5),	-- receive, process and forward frames
		off (6),	-- receive SNMP frames, others discarded
		unknown(7)      -- not currently reporting STAP state
                }
        ACCESS read-only
        STATUS mandatory
        DESCRIPTION
                "The current IEEE 802.1d Spanning Tree Algorithm and Protocol
		 state (STAP) of this port."
        ::= { ol51nnIxPortEntry 4 }

ol51nnIxPortIpAddress OBJECT-TYPE
	SYNTAX IpAddress
	ACCESS read-only
	STATUS mandatory
	DESCRIPTION
		"The IP Address associated with this port."
	::= { ol51nnIxPortEntry 5 }

ol51nnIxPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnIxPortEntry 6 }

ol51nnIxPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OEIM's
		non-volatile storage."
	::= { ol51nnIxPortEntry 7 }



--
-- FDDI Management Module
--

ol53nnMMGTModTable OBJECT-TYPE
	SYNTAX SEQUENCE OF Ol53nnMMGTModEntry
	ACCESS not-accessible
	STATUS mandatory
	DESCRIPTION
		"A list of module attributes that apply to this model.
		To access an ol53nnMMGTModTable entry, the 
		ol53nnMMGTModSlotIndex attribute is used."
	::= { ol53nnMMGT 1 }

ol53nnMMGTModEntry OBJECT-TYPE
	SYNTAX Ol53nnMMGTModEntry 
	ACCESS not-accessible
	STATUS mandatory
	DESCRIPTION
		"A list of module-specific information about a specific
		53nnM-MGT module in the concentrator."
	INDEX { ol53nnMMGTModSlotIndex }
	::= { ol53nnMMGTModTable 1 }

Ol53nnMMGTModEntry ::=
	SEQUENCE {
		ol53nnMMGTModSlotIndex
			INTEGER,
		ol53nnMMGTModMasterPriority
			INTEGER,
		ol53nnMMGTModMasterStatus
			INTEGER,
		ol53nnMMGTModStationAddr
			OCTET STRING,
		ol53nnMMGTModIpAddress
			IpAddress,
		ol53nnMMGTModDownStreamMAC
			OCTET STRING,
		ol53nnMMGTModUpStreamMAC
			OCTET STRING,
                ol53nnMMGTModfddiMACPath
                        INTEGER,
		ol53nnMMGTModDownStreamModule
			INTEGER,
		ol53nnMMGTModUpStreamModule
			INTEGER,
		ol53nnMMGTModDownStreamOperPath
			INTEGER,
		ol53nnMMGTModUpStreamOperPath
			INTEGER,
		ol53nnMMGTModRingInfo
			OCTET STRING
		}

ol53nnMMGTModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMMGTModEntry 1 }

ol53nnMMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {ol53nnMMGTModEntry 2 }

ol53nnMMGTModMasterStatus OBJECT-TYPE
	SYNTAX INTEGER {
		master(1),
		non-master(2),
		electing(3)
		}
	ACCESS read-only
	STATUS mandatory
	DESCRIPTION
		"The mastership status of this agent."
	::= {ol53nnMMGTModEntry 3 }

ol53nnMMGTModStationAddr OBJECT-TYPE
	SYNTAX OCTET STRING (SIZE (6))
	ACCESS read-only
	STATUS mandatory
	DESCRIPTION
		"A 6 octet address that uniquely identifies this module.
		The station address is the MAC address of port 1."
	::= {ol53nnMMGTModEntry 4 }

ol53nnMMGTModIpAddress  OBJECT-TYPE
	SYNTAX IpAddress
	ACCESS read-write
	STATUS mandatory
	DESCRIPTION
		"The IP address associated with this module."
	::= {ol53nnMMGTModEntry 5 }

ol53nnMMGTModDownStreamMAC OBJECT-TYPE
	SYNTAX OCTET STRING (SIZE (6))
	ACCESS read-only
	STATUS mandatory
	DESCRIPTION
                "Down stream MAC"
	::= { ol53nnMMGTModEntry 6 }

ol53nnMMGTModUpStreamMAC OBJECT-TYPE
	SYNTAX OCTET STRING (SIZE (6))
	ACCESS read-only
	STATUS mandatory
	DESCRIPTION
                "Up stream MAC"
	::= { ol53nnMMGTModEntry 7 }

ol53nnMMGTModfddiMACPath OBJECT-TYPE
        SYNTAX INTEGER {
                primary(1),
                secondary(2)
                }
        ACCESS read-write
        STATUS mandatory
        DESCRIPTION
                "The FDDI path which should be inserted into the MAC"
        ::= { ol53nnMMGTModEntry 8 }

ol53nnMMGTModDownStreamModule OBJECT-TYPE
	SYNTAX INTEGER (1..16)
	ACCESS read-only
	STATUS mandatory
	DESCRIPTION
                "Down stream slot (transmit to)"
	::= { ol53nnMMGTModEntry 9 }

ol53nnMMGTModUpStreamModule OBJECT-TYPE
	SYNTAX INTEGER (1..16)
	ACCESS read-only
	STATUS mandatory
	DESCRIPTION
                "Up stream slot (receve from)"
	::= { ol53nnMMGTModEntry 10 }

ol53nnMMGTModDownStreamOperPath OBJECT-TYPE
	SYNTAX INTEGER {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA  (debug only)"
	::= { ol53nnMMGTModEntry 11 }

ol53nnMMGTModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
        ACCESS read-only
	STATUS mandatory
	DESCRIPTION
                "Receive DBA (debug only)"
	::= { ol53nnMMGTModEntry 12 }

ol53nnMMGTModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMMGTModEntry 13 }


-- port table

ol53nnMMGTPortTable OBJECT-TYPE
	SYNTAX SEQUENCE OF Ol53nnMMGTPortEntry
	ACCESS not-accessible
	STATUS mandatory
	DESCRIPTION
		"A table of port-specific information for each port of
		this module type."
	::= { ol53nnMMGT 2 }

ol53nnMMGTPortEntry OBJECT-TYPE
	SYNTAX Ol53nnMMGTPortEntry 
	ACCESS not-accessible
	STATUS mandatory
	DESCRIPTION
		"A list of module-specific information about a specific
		53nnM-MGT port in the concentrator."
	INDEX { ol53nnMMGTPortSlotIndex, ol53nnMMGTPortIndex }
	::= { ol53nnMMGTPortTable 1 }

Ol53nnMMGTPortEntry ::=
	SEQUENCE {
		ol53nnMMGTPortSlotIndex
			INTEGER,			
		ol53nnMMGTPortIndex
			INTEGER,
		ol53nnMMGTPortConfig
			INTEGER,
		ol53nnMMGTPortPcmState
			INTEGER,
		ol53nnMMGTPortConnectState
			INTEGER,
		ol53nnMMGTPortNeighbor
			INTEGER,
		ol53nnMMGTPortRemoteMACIndicated
			INTEGER,
		ol53nnMMGTPortBSFlag
			INTEGER,
		ol53nnMMGTPortPCWithhold
			INTEGER,
		ol53nnMMGTPortLerCondition
			INTEGER
		}

ol53nnMMGTPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMMGTPortEntry 1 }


ol53nnMMGTPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMMGTPortEntry 2 }

ol53nnMMGTPortConfig OBJECT-TYPE
	SYNTAX INTEGER {
                a(1),
                b(2)
		}
	ACCESS read-only
	STATUS mandatory
	DESCRIPTION
                "Specifies the FDDI port type (a or b)."
	::= { ol53nnMMGTPortEntry 3 }

ol53nnMMGTPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMMGTPortEntry 4 }

ol53nnMMGTPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMMGTPortEntry 5 }

ol53nnMMGTPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMMGTPortEntry 6 }

ol53nnMMGTPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMMGTPortEntry 7 }

ol53nnMMGTPortBSFlag OBJECT-TYPE
	SYNTAX INTEGER { true(1), false(2) }
	ACCESS read-only
	STATUS mandatory
	DESCRIPTION
          "The Break State, BS_Flag (refer to ANSI SMT
           9.4.3.4)."
	::= { ol53nnMMGTPortEntry 8 }

ol53nnMMGTPortPCWithhold OBJECT-TYPE
	SYNTAX INTEGER  { none(1), m-m(2), other(3) }
	ACCESS read-only
	STATUS mandatory
	DESCRIPTION
           "PC_Withhold, (refer to ANSI SMT 9.4.1)."
	::= { ol53nnMMGTPortEntry 9 }

ol53nnMMGTPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMMGTPortEntry 10 }


-- Trunk Table
-- (only present for compatibility)

ol53nnMMGTTrunkTable OBJECT-TYPE
	SYNTAX SEQUENCE OF Ol53nnMMGTTrunkEntry
	ACCESS not-accessible
	STATUS mandatory
	DESCRIPTION
                "FDDI module specific trunk table variables.
                 At present there are none."
	::= { ol53nnMMGT 3 }

ol53nnMMGTTrunkEntry OBJECT-TYPE
	SYNTAX Ol53nnMMGTTrunkEntry
	ACCESS not-accessible
	STATUS mandatory
	DESCRIPTION
		"A description of 53nnM-MGT trunk attributes."		
	INDEX { ol53nnMMGTTrunkSlotIndex, ol53nnMMGTTrunkIndex }
	::= { ol53nnMMGTTrunkTable 1 }

Ol53nnMMGTTrunkEntry ::= 
	SEQUENCE {
		ol53nnMMGTTrunkSlotIndex	
			INTEGER,
		ol53nnMMGTTrunkIndex
			INTEGER
		}

ol53nnMMGTTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMMGTTrunkEntry 1 }


ol53nnMMGTTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMMGTTrunkEntry 2 }



--
-- ONline Hidden Controller Module
--

ol50nnMHCTLModTable OBJECT-TYPE
	SYNTAX SEQUENCE OF Ol50nnMHCTLModEntry
	ACCESS not-accessible
	STATUS mandatory
	DESCRIPTION
		"A table that contains information about each 50nnM-HCTL
		in the concentrator.  "
	::= { ol50nnMHCTL 1 }

ol50nnMHCTLModEntry OBJECT-TYPE
	SYNTAX Ol50nnMHCTLModEntry
	ACCESS not-accessible
	STATUS mandatory
	DESCRIPTION
		"A list of information for each 50nnM-HCTL module
		in the concentrator."
	INDEX { ol50nnMHCTLModSlotIndex }
	::= { ol50nnMHCTLModTable 1 }

Ol50nnMHCTLModEntry ::= 
	SEQUENCE {
		ol50nnMHCTLModSlotIndex
			INTEGER,
		ol50nnMHCTLModOperState
			INTEGER,
		ol50nnMHCTLModClockStatus
			INTEGER,
		ol50nnMHCTLModTempStatus
			INTEGER,
		ol50nnMHCTLModPDBStatus
			INTEGER,
		ol50nnMHCTLModDipCh1ActCol
			INTEGER,
		ol50nnMHCTLModDipCh2ActCol
			INTEGER,
		ol50nnMHCTLModDipCh3ActCol
			INTEGER
		}

ol50nnMHCTLModSlotIndex OBJECT-TYPE
	SYNTAX INTEGER
	ACCESS read-only
	STATUS mandatory
	DESCRIPTION
		"The slot number for this module.  The value should be 7."
	::= { ol50nnMHCTLModEntry 1 }

ol50nnMHCTLModOperState OBJECT-TYPE
	SYNTAX INTEGER {
		active(1),
		standby(2)
		}
	ACCESS read-only
	STATUS mandatory
	DESCRIPTION
		"The operational state of the 50nnM-HCTL module.  Specifically,
		this is an indicator of whether the 50nnM-HCTL module is
		providing clock signals to the backplane.  An active 50nnM-HCTL
		module provides clock signals to the backplane while a standby 
		50nnM-HCTL module does not.  Note that only one 50nnM-HCTL
		module will be active at any given time; all other 50nnM-HCTL/
		50nnMRCTL modules in the concentrator will be in standby mode."
	::= { ol50nnMHCTLModEntry 2 }

ol50nnMHCTLModClockStatus OBJECT-TYPE
	SYNTAX INTEGER {
		okay(1),
		faulty(2)
		}
	ACCESS read-only
	STATUS mandatory
	DESCRIPTION
		"The current status of the on-board clocks on this module."
	::= { ol50nnMHCTLModEntry 3 }

ol50nnMHCTLModTempStatus OBJECT-TYPE
	SYNTAX INTEGER {
		okay(1),
		extremeTemp(2)
		}
	ACCESS read-only
	STATUS mandatory
	DESCRIPTION
		"The temperature as detected by the probe on this module."
	::= { ol50nnMHCTLModEntry 4 }

ol50nnMHCTLModPDBStatus OBJECT-TYPE
	SYNTAX INTEGER {
		present(1),
		notPresent(2)
		}
	ACCESS read-only
	STATUS mandatory
	DESCRIPTION
		"Indicates whether this 6-slot concentrator contains a power
		distribution board that supports powersupply redundancy."
	::= { ol50nnMHCTLModEntry 5 }

ol50nnMHCTLModDipCh1ActCol OBJECT-TYPE
	SYNTAX INTEGER {
		enabled(1),
		disabled(2)
		}
	ACCESS read-only
	STATUS mandatory
	DESCRIPTION
		"The Ethernet channel 1 activity/collision LED configuration
		as indicated by this module's dip switches."
	::= { ol50nnMHCTLModEntry 6 }

ol50nnMHCTLModDipCh2ActCol OBJECT-TYPE
	SYNTAX INTEGER {
		enabled(1),
		disabled(2)
		}
	ACCESS read-only
	STATUS mandatory
	DESCRIPTION
		"The Ethernet channel 2 activity/collision LED configuration
		as indicated by this module's dip switches."
	::= { ol50nnMHCTLModEntry 7 }

ol50nnMHCTLModDipCh3ActCol OBJECT-TYPE
	SYNTAX INTEGER {
		enabled(1),
		disabled(2)
		}
	ACCESS read-only
	STATUS mandatory
	DESCRIPTION
		"The Ethernet channel 3 activity/collision LED configuration
		as indicated by this module's dip switches."
	::= { ol50nnMHCTLModEntry 8 }




















END
