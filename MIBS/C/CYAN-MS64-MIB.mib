CYAN-MS64-MIB DEFINITIONS ::= BEGIN
IMPORTS
    MODULE-IDENTITY,
    OBJECT-TYPE,
    Integer32,
    Unsigned32
                    FROM SNMPv2-SMI


    CyanSsBitsTc,
    CyanChannelIdTc,
    CyanOpStateTc,
    CyanSecServiceStateTc,
    CyanOpStateQualTc,
    CyanAdminStateTc
                    FROM CYAN-TC-MIB

    cyanEntityModules
		    FROM CYAN-MIB

    MODULE-COMPLIANCE, 
    OBJECT-GROUP
	            FROM SNMPv2-CONF;


cyanMS64Module MODULE-IDENTITY
    LAST-UPDATED "201412070545Z" -- Sun Dec  7 05:45:22 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for OC-192 Line /STM-64 MS layer"

    REVISION     "201412070545Z" -- Sun Dec  7 05:45:22 2014
    DESCRIPTION  "Release 6.0 build 1416362081"

    ::= { cyanEntityModules 230 } 

cyanMS64MibObjects           OBJECT IDENTIFIER ::={ cyanMS64Module 1 }

cyanMS64Table    OBJECT-TYPE
    SYNTAX        SEQUENCE OF CyanMS64Entry
    MAX-ACCESS    not-accessible
    STATUS        current
    DESCRIPTION
        "A list of MS64 entries."
    ::= { cyanMS64MibObjects 1 }

cyanMS64Entry    OBJECT-TYPE
    SYNTAX        CyanMS64Entry
    MAX-ACCESS    not-accessible
    STATUS        current
    DESCRIPTION
        "An entry of MS64."
    INDEX {
        cyanMS64ShelfId ,
        cyanMS64ModuleId ,
        cyanMS64MS64Id 
    }
    ::= { cyanMS64Table 1 }

CyanMS64Entry  ::=
    SEQUENCE {
        cyanMS64ShelfId    Unsigned32,
        cyanMS64ModuleId    Unsigned32,
        cyanMS64MS64Id    Unsigned32,
        cyanMS64Accepted    CyanSsBitsTc,
        cyanMS64AdminState    CyanAdminStateTc,
        cyanMS64AutoinserviceSoakTimeSec    Integer32,
        cyanMS64ChannelId    CyanChannelIdTc,
        cyanMS64Inserted    CyanSsBitsTc,
        cyanMS64OperState    CyanOpStateTc,
        cyanMS64OperStateQual    CyanOpStateQualTc,
        cyanMS64SecServState    CyanSecServiceStateTc
    }

cyanMS64ShelfId OBJECT-TYPE
    SYNTAX       Unsigned32 (0..255)
    MAX-ACCESS   not-accessible
    STATUS       current
    DESCRIPTION
        "Shelf Id"

    ::= { cyanMS64Entry 1 }
cyanMS64ModuleId OBJECT-TYPE
    SYNTAX       Unsigned32
    MAX-ACCESS   not-accessible
    STATUS       current
    DESCRIPTION
        "Module Id"

    ::= { cyanMS64Entry 2 }
cyanMS64MS64Id OBJECT-TYPE
    SYNTAX       Unsigned32
    MAX-ACCESS   not-accessible
    STATUS       current
    DESCRIPTION
        "MS64 Termination Id"

    ::= { cyanMS64Entry 3 }

cyanMS64Accepted OBJECT-TYPE
    SYNTAX       CyanSsBitsTc
    MAX-ACCESS   read-only
    STATUS       current
    DESCRIPTION
        "Receiving SS bits"

    ::= { cyanMS64Entry 4 }

cyanMS64AdminState OBJECT-TYPE
    SYNTAX       CyanAdminStateTc
    MAX-ACCESS   read-only
    STATUS       current
    DESCRIPTION
        "Administrative state"

    ::= { cyanMS64Entry 5 }

cyanMS64AutoinserviceSoakTimeSec OBJECT-TYPE
    SYNTAX       Integer32
    MAX-ACCESS   read-only
    STATUS       current
    DESCRIPTION
        "Auto-In-Service soak time"

    ::= { cyanMS64Entry 6 }

cyanMS64ChannelId OBJECT-TYPE
    SYNTAX       CyanChannelIdTc
    MAX-ACCESS   read-only
    STATUS       current
    DESCRIPTION
        "Channel ID"

    ::= { cyanMS64Entry 7 }

cyanMS64Inserted OBJECT-TYPE
    SYNTAX       CyanSsBitsTc
    MAX-ACCESS   read-only
    STATUS       current
    DESCRIPTION
        "Transmitting SS bits"

    ::= { cyanMS64Entry 8 }

cyanMS64OperState OBJECT-TYPE
    SYNTAX       CyanOpStateTc
    MAX-ACCESS   read-only
    STATUS       current
    DESCRIPTION
        "Primary Operation State"

    ::= { cyanMS64Entry 9 }

cyanMS64OperStateQual OBJECT-TYPE
    SYNTAX       CyanOpStateQualTc
    MAX-ACCESS   read-only
    STATUS       current
    DESCRIPTION
        "Operation state qualifier"

    ::= { cyanMS64Entry 10 }

cyanMS64SecServState OBJECT-TYPE
    SYNTAX       CyanSecServiceStateTc
    MAX-ACCESS   read-only
    STATUS       current
    DESCRIPTION
        "Secondary service state"

    ::= { cyanMS64Entry 11 }

cyanMS64ObjectGroup OBJECT-GROUP
    OBJECTS {
        cyanMS64Accepted,
        cyanMS64AdminState,
        cyanMS64AutoinserviceSoakTimeSec,
        cyanMS64ChannelId,
        cyanMS64Inserted,
        cyanMS64OperState,
        cyanMS64OperStateQual,
        cyanMS64SecServState
    }

    STATUS current
    DESCRIPTION        "Group of objects that comes with MS64 module"
    ::= {cyanMS64Module 20}

cyanMS64Compliance MODULE-COMPLIANCE
    STATUS current
    DESCRIPTION
        "The basic info needed to be a cyan MS64"
    MODULE
    MANDATORY-GROUPS {
        cyanMS64ObjectGroup
    }
    ::= { cyanMS64Module 30 }


END
