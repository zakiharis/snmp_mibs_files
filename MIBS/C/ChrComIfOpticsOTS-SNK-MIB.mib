ChrComIfOpticsOTS-SNK-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfOptics				FROM  Chromatis-MIB
	chrComIfifIndex					FROM  ChrComIfifTable-MIB;

-- chrComIfOpticsOTS-SNK Table

chrComIfOpticsOTS-SNKTable		OBJECT-TYPE
	SYNTAX		SEQUENCE OF ChrComIfOpticsOTS-SNKEntry
	MAX-ACCESS	not-accessible
	STATUS		current
	DESCRIPTION
	"1. The OTS-SNK is managed only for the Ring side of the Metropolis Network (not for the Trib side).
2. When pre-OPA exists, the following ADOM/OMDM does NOT have an OTS-SNK layer This layer should be grayed and not accessible to the user.
"
	::= { chrComIfOptics 1}

chrComIfOpticsOTS-SNKEntry		OBJECT-TYPE
	SYNTAX		ChrComIfOpticsOTS-SNKEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OTS-SNK"
	::= { chrComIfOpticsOTS-SNKTable  1 }

ChrComIfOpticsOTS-SNKEntry  ::=
	SEQUENCE  {
	chrComIfOpticsOtsSnkInPower		Integer32	(-501..300),
	chrComIfOpticsOtsSnkLOOPThr		Integer32	(-501..300),
	chrComIfOpticsAlarmVector		Integer32	(0..65535),
	chrComIfOpticsAlarmSeverityProfileIndex Unsigned32	(0..4294967295)
}

chrComIfOpticsOtsSnkInPower 	OBJECT-TYPE
	SYNTAX		Integer32	(-501..300)
	MAX-ACCESS 	read-only
	STATUS 		current
	DESCRIPTION
	"Total Optical Power Monitored at the input of ADOM/OMDM/pre-OPA/in-line-OPA."
	::= { chrComIfOpticsOTS-SNKEntry  1 }

chrComIfOpticsOtsSnkLOOPThr 	OBJECT-TYPE
	SYNTAX		Integer32	(-501..300)
	MAX-ACCESS 	read-write
	STATUS 		current
	DESCRIPTION
	"This is a threshold on OTS-SNK total input Power. "
	::= { chrComIfOpticsOTS-SNKEntry  2 }

chrComIfOpticsAlarmVector 	OBJECT-TYPE
	SYNTAX		Integer32	(0..65535)
	MAX-ACCESS 	read-only
	STATUS 		current
	DESCRIPTION
	""
	::= { chrComIfOpticsOTS-SNKEntry  3 }

chrComIfOpticsAlarmSeverityProfileIndex 	OBJECT-TYPE
	SYNTAX		Unsigned32	(0..4294967295)
	MAX-ACCESS 	read-write
	STATUS 		current
	DESCRIPTION
	""
	::= { chrComIfOpticsOTS-SNKEntry  4 }


END
