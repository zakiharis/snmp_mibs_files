-- *****************************************************************
-- CISCO-RTTMON-CAPABILITY.my:  Cisco RTTMON MIB AGENT-CAPABILITIES
--
-- December 2005, Bijoy M. Chandrasekharan
--
-- Copyright (c) 2004-2006 by cisco Systems, Inc.
-- All rights reserved.
--
-- *****************************************************************

CISCO-RTTMON-CAPABILITY DEFINITIONS ::= BEGIN

IMPORTS
    MODULE-IDENTITY, Integer32
            FROM SNMPv2-SMI
    AGENT-CAPABILITIES
            FROM SNMPv2-CONF
    ciscoAgentCapability
            FROM CISCO-SMI;

ciscoRttMonCapability MODULE-IDENTITY
    LAST-UPDATED    "200603020000Z"
    ORGANIZATION    "Cisco Systems, Inc."
    CONTACT-INFO
            "       Cisco Systems
                    Customer Service

            Postal: 170 W Tasman Drive
                    San Jose, CA  95134
                    USA

               Tel: +1 800 553-NETS

            E-mail: cs-ipsla@cisco.com"
    DESCRIPTION
        "Agent capabilities for CISCO-RTTMON-MIB"
    REVISION "200603020000Z"
    DESCRIPTION
        "Added capability definition ciscoRttMonCapV12R0201SRB for
         12.2(01)SRB"
    REVISION "200512140000Z"
    DESCRIPTION
        "Agent capabilities for CISCO-RTTMON-MIB on CRS-1
         IOS-XR Release 3.3"
    REVISION "200506090000Z"
    DESCRIPTION
        "Added capability definition ciscoRttMonCapV12R0403rdT for
         12.4(3rd)T"
    REVISION "200505010000Z"
    DESCRIPTION
        "Added capability definition ciscoRttMonCapV12R0402ndT
        for 12.4(2nd)T and ciscoRttMonCapV12R0206thSX for
        12.2(6th)SX"
    REVISION "200405310000Z"
    DESCRIPTION
        "Initial Creation"
    ::= { ciscoAgentCapability 62 }

ciscoRttMonCapabilityRev1 AGENT-CAPABILITIES
    PRODUCT-RELEASE "Cisco IOS 12.3(6th)T"
    STATUS          current
    DESCRIPTION     "Cisco RTTMON MIB capabilities"
    SUPPORTS        CISCO-RTTMON-MIB
        INCLUDES    { ciscoCtrlGroupRev3, ciscoStatsGroup,
                      ciscoHistoryGroup, ciscoCtrlGroupRev1,
                      ciscoCtrlGroupRev2, ciscoLatestOperGroupRev1,
                      ciscoStatsGroupRev1, ciscoStatsGroupRev3,
                      ciscoStatsGroupRev4, ciscoStatsGroupRev5,
                      ciscoApplGroupRev2, ciscoApplGroupRev3,
                      ciscoCtrlGroupRev4, ciscoCtrlGroupRev5,
                      ciscoCtrlGroupRev6, ciscoCtrlGroupRev7,
                      ciscoCtrlGroupRev8, ciscoCtrlGroupRev9,
                      ciscoNotificationGroup }

	VARIATION rttMonEchoAdminProtocol
	DESCRIPTION "protocol value mplsLspPingAppl Not supported"

	VARIATION rttMonEchoAdminLSPFECType
	ACCESS not-implemented
	DESCRIPTION "Not supported"

	VARIATION rttMonEchoAdminLSPSelector         
	ACCESS not-implemented
	DESCRIPTION "Not supported"

	VARIATION rttMonEchoAdminLSPReplyMode	     
	ACCESS not-implemented
	DESCRIPTION "Not supported"

	VARIATION rttMonEchoAdminLSPTTL		     
	ACCESS not-implemented
	DESCRIPTION "Not supported"

	VARIATION rttMonEchoAdminLSPExp		     
	ACCESS not-implemented
	DESCRIPTION "Not supported"

    ::= { ciscoRttMonCapability 1 }

ciscoRttMonCapV12R0402ndT AGENT-CAPABILITIES
    PRODUCT-RELEASE "Cisco IOS 12.4(2nd)T"
    STATUS          current
    DESCRIPTION     "Cisco RTTMON MIB capabilities"
    SUPPORTS        CISCO-RTTMON-MIB
        INCLUDES    { ciscoStatsGroup, ciscoHistoryGroup,
                      ciscoCtrlGroupRev1, ciscoCtrlGroupRev2,
                      ciscoLatestOperGroupRev1, ciscoStatsGroupRev1,
                      ciscoStatsGroupRev3, ciscoStatsGroupRev4,
                      ciscoStatsGroupRev5, ciscoApplGroupRev2,
                      ciscoApplGroupRev3, ciscoCtrlGroupRev4,
                      ciscoCtrlGroupRev6, ciscoCtrlGroupRev7,
                      ciscoCtrlGroupRev9, ciscoCtrlGroupRev10,
                      ciscoCtrlGroupRev11, ciscoNotificationGroupRev1,
                      ciscoStatsGroupRev6, ciscoCtrlGroupRev12 }

        VARIATION rttMonEchoAdminProtocol
        DESCRIPTION "protocol value mplsLspPingAppl Not supported"

        VARIATION rttMonCtrlAdminRttType
        DESCRIPTION "RttMonRttType value lspGroup Not supported"

        VARIATION rttMonEchoAdminLSPFECType
        ACCESS not-implemented
        DESCRIPTION "Not supported"

        VARIATION rttMonEchoAdminLSPSelector
        ACCESS not-implemented
        DESCRIPTION "Not supported"

        VARIATION rttMonEchoAdminLSPReplyMode
        ACCESS not-implemented
        DESCRIPTION "Not supported"

        VARIATION rttMonEchoAdminLSPTTL
        ACCESS not-implemented
        DESCRIPTION "Not supported"

        VARIATION rttMonEchoAdminLSPExp
        ACCESS not-implemented
        DESCRIPTION "Not supported"

        VARIATION rttMonEchoAdminLSPReplyDscp
        ACCESS not-implemented
        DESCRIPTION "Not supported"

        VARIATION rttMonEchoAdminLSPNullShim
        ACCESS not-implemented
        DESCRIPTION "Not supported"

    ::= { ciscoRttMonCapability 2 }

ciscoRttMonCapV12R0206thSX AGENT-CAPABILITIES
    PRODUCT-RELEASE "Cisco IOS 12.2(6th)SX"
    STATUS          current
    DESCRIPTION     "Cisco RTTMON MIB capabilities"
    SUPPORTS        CISCO-RTTMON-MIB
        INCLUDES    { ciscoStatsGroup, ciscoHistoryGroup,
                      ciscoCtrlGroupRev1, ciscoCtrlGroupRev2,
                      ciscoLatestOperGroupRev1, ciscoStatsGroupRev1,
                      ciscoStatsGroupRev3, ciscoStatsGroupRev4,
                      ciscoApplGroupRev2, ciscoApplGroupRev3,
                      ciscoCtrlGroupRev4, ciscoCtrlGroupRev6,
                      ciscoCtrlGroupRev7, ciscoCtrlGroupRev8,
                      ciscoCtrlGroupRev9, ciscoCtrlGroupRev10,
                      ciscoCtrlGroupRev11, ciscoNotificationGroupRev1,
                      ciscoStatsGroupRev7, ciscoCtrlGroupRev13,
                      ciscoNotificationGroupRev2, ciscoApplGroupRev4,
                      ciscoStatsGroupRev7 }

        VARIATION rttMonEchoAdminProtocol
        DESCRIPTION "protocol value voipAppl and rtpAppl Not supported"

        VARIATION rttMonCtrlAdminRttType
        DESCRIPTION "RttMonRttType value voip and rtp Not supported"

        VARIATION rttMonEchoAdminPrecision
        ACCESS not-implemented
        DESCRIPTION "Not supported"

        VARIATION rttMonEchoAdminProbePakPriority
        ACCESS not-implemented
        DESCRIPTION "Not supported"

        VARIATION rttMonEchoAdminOWNTPSyncTolAbs
        ACCESS not-implemented
        DESCRIPTION "Not supported"

        VARIATION rttMonEchoAdminOWNTPSyncTolPct
        ACCESS not-implemented
        DESCRIPTION "Not supported"

        VARIATION rttMonEchoAdminOWNTPSyncTolType
        ACCESS not-implemented
        DESCRIPTION "Not supported"

        VARIATION rttMonEchoAdminCalledNumber
        ACCESS not-implemented
        DESCRIPTION "Not supported"

        VARIATION rttMonEchoAdminDetectPoint
        ACCESS not-implemented
        DESCRIPTION "Not supported"

        VARIATION rttMonEchoAdminGKRegistration
        ACCESS not-implemented
        DESCRIPTION "Not supported"

        VARIATION rttMonEchoAdminSourceVoicePort
        ACCESS not-implemented
        DESCRIPTION "Not supported"

        VARIATION rttMonEchoAdminCallDuration
        ACCESS not-implemented
        DESCRIPTION "Not supported"
    ::= { ciscoRttMonCapability 3 }

ciscoRttMonCapV12R0403rdT AGENT-CAPABILITIES
    PRODUCT-RELEASE "Cisco IOS 12.4(3rd)T"
    STATUS          current
    DESCRIPTION     "Cisco RTTMON MIB capabilities"
    SUPPORTS        CISCO-RTTMON-MIB
        INCLUDES    { ciscoStatsGroup, ciscoHistoryGroup,
                      ciscoCtrlGroupRev1, ciscoCtrlGroupRev2,
                      ciscoLatestOperGroupRev1, ciscoStatsGroupRev1,
                      ciscoStatsGroupRev3, ciscoStatsGroupRev4,
                      ciscoStatsGroupRev5, ciscoApplGroupRev2,
                      ciscoApplGroupRev3, ciscoCtrlGroupRev4,
                      ciscoCtrlGroupRev6, ciscoCtrlGroupRev7,
                      ciscoCtrlGroupRev9, ciscoCtrlGroupRev10,
                      ciscoCtrlGroupRev11, ciscoNotificationGroupRev1,
                      ciscoStatsGroupRev6, ciscoCtrlGroupRev12,
                      ciscoCtrlGroupRev8, ciscoStatsGroupRev7,
                      ciscoCtrlGroupRev13, ciscoNotificationGroupRev2,
                      ciscoApplGroupRev4, ciscoStatsGroupRev8,
		      ciscoStatsGroupRev9, ciscoCtrlGroupRev13
                    }

    ::= { ciscoRttMonCapability 4 }

ciscoRttMonCapCRS1V3R3 AGENT-CAPABILITIES
    PRODUCT-RELEASE "Cisco IOS XR release 3.3 for CRS-1"
    STATUS          current
    DESCRIPTION     "Cisco RTTMON MIB capabilities." 

    SUPPORTS        CISCO-RTTMON-MIB 
    INCLUDES        {        
                      ciscoStatsGroup,     ciscoStatsGroupRev1,
                      ciscoStatsGroupRev3, ciscoStatsGroupRev5,
                      ciscoHistoryGroup,   ciscoApplGroupRev3,
                      ciscoCtrlGroupRev1,  ciscoCtrlGroupRev2,
                      ciscoCtrlGroupRev7,  ciscoCtrlGroupRev10,
                      ciscoCtrlGroupRev11, ciscoNotificationGroupRev1
                    } 

    VARIATION       rttMonStatsCollectNumDisconnects
     ACCESS         not-implemented
     DESCRIPTION    "This object is not supported in the current
                    MIB implementation."

    VARIATION       rttMonStatsCollectTimeouts
     ACCESS         not-implemented
     DESCRIPTION    "This object is not supported in the current
                    MIB implementation."

    VARIATION       rttMonStatsCollectBusies
     ACCESS         not-implemented
     DESCRIPTION    "This object is not supported in the current
                    MIB implementation."

    VARIATION       rttMonStatsCollectNoConnections
     ACCESS         not-implemented
     DESCRIPTION    "This object is not supported in the current
                    MIB implementation."

    VARIATION       rttMonStatsCollectDrops
     ACCESS         not-implemented
     DESCRIPTION    "This object is not supported in the current
                    MIB implementation."

    VARIATION       rttMonStatsCollectSequenceErrors
     ACCESS         not-implemented
     DESCRIPTION    "This object is not supported in the current
                    MIB implementation."

    VARIATION       rttMonStatsCollectVerifyErrors
     ACCESS         not-implemented
     DESCRIPTION    "This object is not supported in the current
                    MIB implementation."

    VARIATION       rttMonStatsCollectAddress
     ACCESS         not-implemented
     DESCRIPTION    "This object is not supported in the current
                    MIB implementation."

    VARIATION       rttMonStatsTotalsElapsedTime
     ACCESS         not-implemented
     DESCRIPTION    "This object is not supported in the current
                    MIB implementation."

    VARIATION       rttMonStatsTotalsInitiations
     ACCESS         not-implemented
     DESCRIPTION    "This object is not supported in the current
                    MIB implementation."

    VARIATION       rttMonHistoryCollectionApplSpecificSense
     ACCESS         not-implemented
     DESCRIPTION    "This object is not supported in the current
                    MIB implementation."

    VARIATION       rttMonHistoryCollectionSenseDescription
     ACCESS         not-implemented
     DESCRIPTION    "This object is not supported in the current
                    MIB implementation."

    VARIATION       rttMonCtrlAdminOwner
     ACCESS         not-implemented
     DESCRIPTION    "This object is not supported in the current
                    MIB implementation."

    VARIATION       rttMonCtrlAdminRttType
     SYNTAX         INTEGER
     {
       echo(1),
       pathEcho(2),
       udpEcho(5),
       jitter(9) 
     }
     DESCRIPTION    "Current MIB implementation supports the rtt
                     types, 'echo', 'pathEcho', 'udpEcho' & 'jitter'."

    VARIATION       rttMonCtrlAdminThreshold
     ACCESS         not-implemented
     DESCRIPTION    "This object is not supported in the current
                    MIB implementation."

    VARIATION       rttMonCtrlAdminFrequency
     SYNTAX         Integer32 (1..604800)
     DESCRIPTION    "Frequency value of 0 is not a valid one, hence
                     setting the minimum frequency to 1 by
                    MIB implementation."

    VARIATION       rttMonCtrlAdminTimeout
     SYNTAX         Integer32 (1..604800000)
     DESCRIPTION    "Timeout value of 0 is not a valid one, hence
                    setting the minimum timeout value to 1 by
                    MIB implementation."

    VARIATION       rttMonCtrlAdminNvgen
     ACCESS         not-implemented
     DESCRIPTION    "This object is not supported in the current
                    MIB implementation."

    VARIATION       rttMonScheduleAdminRttLife
     SYNTAX         Integer32 (1..2147483647)
     DESCRIPTION    "Rtt life value of 0 is not a valid one, hence
                    setting the minimum Rtt life value to 1 by
                    MIB implementation."

    VARIATION       rttMonEchoAdminProtocol
     SYNTAX         INTEGER
     {
       notApplicable(1),
       ipIcmpEcho(2),
       ipUdpEchoAppl(3),
       jitterAppl(27)
     }
     DESCRIPTION    "The current MIB implementation supports only 
                    echo, pathEcho, udpEcho & jitter rttTypes. These
                    uses the above 3 protocols."

    VARIATION       rttMonEchoAdminPktDataResponseSize
     ACCESS         not-implemented
     DESCRIPTION    "This object is not supported in the current
                    MIB implementation,since backend support is not 
                    available."

    VARIATION       rttMonEchoAdminTargetPort
     SYNTAX         Integer32 (1..65535)
     DESCRIPTION    "The valid range of port numbers is 0-65535 and
                    port 0 is not supported by ipsla backend."

    VARIATION       rttMonEchoAdminSourcePort
     SYNTAX         Integer32 (1..65535)
     DESCRIPTION    "The valid range of port numbers is 0-65535 and
                    port 0 is not supported by ipsla backend.
                    This object is applicable to udpEcho & jitter
                    probes only."

    VARIATION       rttMonCtrlOperDiagText
     ACCESS         not-implemented
     DESCRIPTION    "This object is not supported in the current
                    MIB implementation."

    VARIATION       rttMonCtrlOperResetTime
     ACCESS         not-implemented
     DESCRIPTION    "This object is not supported in the current
                    MIB implementation."

    VARIATION       rttMonCtrlOperOctetsInUse
     ACCESS         not-implemented
     DESCRIPTION    "This object is not supported in the current
                    MIB implementation."

    VARIATION       rttMonCtrlOperVerifyErrorOccurred
     ACCESS         not-implemented
     DESCRIPTION    "This object is not supported in the current
                    MIB implementation."

    VARIATION       rttMonCtrlOperState
     SYNTAX         INTEGER
     {
       pending(4),
       inactive(5),
       active(6) 
     }
     DESCRIPTION    "read/write of any other values to this object is not
                    supported by the current MIB implementation."

    VARIATION       rttMonLatestRttOperCompletionTime
     ACCESS         not-implemented
     DESCRIPTION    "This object is not supported in the current
                    MIB implementation."

    VARIATION       rttMonLatestRttOperSense
     ACCESS         not-implemented
     DESCRIPTION    "This object is not supported in the current
                    MIB implementation."

    VARIATION       rttMonLatestRttOperApplSpecificSense
     ACCESS         not-implemented
     DESCRIPTION    "This object is not supported in the current
                    MIB implementation."

    VARIATION       rttMonLatestRttOperSenseDescription
     ACCESS         not-implemented
     DESCRIPTION    "This object is not supported in the current
                    MIB implementation."

    VARIATION       rttMonLatestRttOperTime
     ACCESS         not-implemented
     DESCRIPTION    "This object is not supported in the current
                    MIB implementation."

    VARIATION       rttMonLatestRttOperAddress
     ACCESS         not-implemented
     DESCRIPTION    "This object is not supported in the current
                    MIB implementation."

    VARIATION       rttMonReactTriggerAdminStatus
     ACCESS         not-implemented
     DESCRIPTION    "This object is not supported in the current
                    MIB implementation."

    VARIATION       rttMonReactTriggerOperState
     ACCESS         not-implemented
     DESCRIPTION    "This object is not supported in the current
                    MIB implementation."

    VARIATION       rttMonEchoAdminTargetAddressString
     ACCESS         not-implemented
     DESCRIPTION    "This object is not supported in the current
                    MIB implementation, since DNS probes are not
                    supported by backend"

    VARIATION       rttMonEchoAdminNameServer
     ACCESS         not-implemented
     DESCRIPTION    "This object is not supported in the current
                    MIB implementation, since DNS probes are not
                    supported by backend"

    VARIATION       rttMonEchoAdminOperation
     ACCESS         not-implemented
     DESCRIPTION    "This object is not supported in the current
                    MIB implementation, since HTTP probes are not
                    supported by backend"

    VARIATION       rttMonEchoAdminHTTPVersion
     ACCESS         not-implemented
     DESCRIPTION    "This object is not supported in the current
                    MIB implementation , since HTTP probes are not
                    supported by backend"

    VARIATION       rttMonEchoAdminURL
     ACCESS         not-implemented
     DESCRIPTION    "This object is not supported in the current
                    MIB implementation , since HTTP probes are not
                    supported by backend"

    VARIATION       rttMonEchoAdminCache
     ACCESS         not-implemented
     DESCRIPTION    "This object is not supported in the current
                    MIB implementation , since HTTP probes are not
                    supported by backend"

    VARIATION       rttMonEchoAdminInterval
     SYNTAX         Integer32 (1..60000)
     DESCRIPTION    "An interval value of 0 does not make sense,
                     hence the minimum changed to 1 by the current
                    MIB implementation."

    VARIATION       rttMonEchoAdminProxy
     ACCESS         not-implemented
     DESCRIPTION    "This object is not supported in the current
                    MIB implementation , since HTTP probes are not
                    supported by backend"

    VARIATION       rttMonEchoAdminString1
     ACCESS         not-implemented
     DESCRIPTION    "This object is not supported in the current
                    MIB implementation , since HTTP probes are not
                    supported by backend"

    VARIATION       rttMonEchoAdminString2
     ACCESS         not-implemented
     DESCRIPTION    "This object is not supported in the current
                    MIB implementation , since HTTP probes are not
                    supported by backend"

    VARIATION       rttMonEchoAdminString3
     ACCESS         not-implemented
     DESCRIPTION    "This object is not supported in the current
                    MIB implementation , since HTTP probes are not
                    supported by backend"

    VARIATION       rttMonEchoAdminString4
     ACCESS         not-implemented
     DESCRIPTION    "This object is not supported in the current
                    MIB implementation , since HTTP probes are not
                    supported by backend"

    VARIATION       rttMonEchoAdminString5
     ACCESS         not-implemented
     DESCRIPTION    "This object is not supported in the current
                    MIB implementation , since HTTP probes are not
                    supported by backend"

    VARIATION       rttMonEchoAdminMode
     ACCESS         not-implemented
     DESCRIPTION    "This object is not supported in the current
                    MIB implementation , since FTP probes are not
                    supported by backend"

    VARIATION       rttMonHTTPStatsCompletions
     ACCESS         not-implemented
     DESCRIPTION    "This object is not supported in the current
                    MIB implementation , since HTTP probes are not
                    supported by backend"

    VARIATION       rttMonHTTPStatsOverThresholds
     ACCESS         not-implemented
     DESCRIPTION    "This object is not supported in the current
                    MIB implementation , since HTTP probes are not
                    supported by backend"

    VARIATION       rttMonHTTPStatsRTTSum
     ACCESS         not-implemented
     DESCRIPTION    "This object is not supported in the current
                    MIB implementation , since HTTP probes are not
                    supported by backend"

    VARIATION       rttMonHTTPStatsRTTSum2Low
     ACCESS         not-implemented
     DESCRIPTION    "This object is not supported in the current
                    MIB implementation , since HTTP probes are not
                    supported by backend"

    VARIATION       rttMonHTTPStatsRTTSum2High
     ACCESS         not-implemented
     DESCRIPTION    "This object is not supported in the current
                    MIB implementation , since HTTP probes are not
                    supported by backend"

    VARIATION       rttMonHTTPStatsRTTMin
     ACCESS         not-implemented
     DESCRIPTION    "This object is not supported in the current
                    MIB implementation , since HTTP probes are not
                    supported by backend"

    VARIATION       rttMonHTTPStatsRTTMax
     ACCESS         not-implemented
     DESCRIPTION    "This object is not supported in the current
                    MIB implementation , since HTTP probes are not
                    supported by backend"

    VARIATION       rttMonHTTPStatsDNSRTTSum
     ACCESS         not-implemented
     DESCRIPTION    "This object is not supported in the current
                    MIB implementation , since HTTP probes are not
                    supported by backend"

    VARIATION       rttMonHTTPStatsTCPConnectRTTSum
     ACCESS         not-implemented
     DESCRIPTION    "This object is not supported in the current
                    MIB implementation , since HTTP probes are not
                    supported by backend"

    VARIATION       rttMonHTTPStatsTransactionRTTSum
     ACCESS         not-implemented
     DESCRIPTION    "This object is not supported in the current
                    MIB implementation , since HTTP probes are not
                    supported by backend"

    VARIATION       rttMonHTTPStatsMessageBodyOctetsSum
     ACCESS         not-implemented
     DESCRIPTION    "This object is not supported in the current
                    MIB implementation , since HTTP probes are not
                    supported by backend"

    VARIATION       rttMonHTTPStatsDNSServerTimeout
     ACCESS         not-implemented
     DESCRIPTION    "This object is not supported in the current
                    MIB implementation , since HTTP probes are not
                    supported by backend"

    VARIATION       rttMonHTTPStatsTCPConnectTimeout
     ACCESS         not-implemented
     DESCRIPTION    "This object is not supported in the current
                    MIB implementation , since HTTP probes are not
                    supported by backend"

    VARIATION       rttMonHTTPStatsTransactionTimeout
     ACCESS         not-implemented
     DESCRIPTION    "This object is not supported in the current
                    MIB implementation , since HTTP probes are not
                    supported by backend"

    VARIATION       rttMonHTTPStatsDNSQueryError
     ACCESS         not-implemented
     DESCRIPTION    "This object is not supported in the current
                    MIB implementation , since HTTP probes are not
                    supported by backend"

    VARIATION       rttMonHTTPStatsHTTPError
     ACCESS         not-implemented
     DESCRIPTION    "This object is not supported in the current
                    MIB implementation , since HTTP probes are not
                    supported by backend"

    VARIATION       rttMonHTTPStatsError
     ACCESS         not-implemented
     DESCRIPTION    "This object is not supported in the current
                    MIB implementation , since HTTP probes are not
                    supported by backend"

    VARIATION       rttMonHTTPStatsBusies
     ACCESS         not-implemented
     DESCRIPTION    "This object is not supported in the current
                    MIB implementation , since HTTP probes are not
                    supported by backend"

    VARIATION       rttMonLatestJitterOperOWSumSD
     ACCESS         not-implemented
     DESCRIPTION    "This object is not supported in the current
                    MIB implementation."

    VARIATION       rttMonLatestJitterOperOWSum2SD
     ACCESS         not-implemented
     DESCRIPTION    "This object is not supported in the current
                    MIB implementation."

    VARIATION       rttMonLatestJitterOperOWMinSD
     ACCESS         not-implemented
     DESCRIPTION    "This object is not supported in the current
                    MIB implementation."

    VARIATION       rttMonLatestJitterOperOWMaxSD
     ACCESS         not-implemented
     DESCRIPTION    "This object is not supported in the current
                    MIB implementation."

    VARIATION       rttMonLatestJitterOperOWSumDS
     ACCESS         not-implemented
     DESCRIPTION    "This object is not supported in the current
                    MIB implementation."

    VARIATION       rttMonLatestJitterOperOWSum2DS
     ACCESS         not-implemented
     DESCRIPTION    "This object is not supported in the current
                    MIB implementation."

    VARIATION       rttMonLatestJitterOperOWMinDS
     ACCESS         not-implemented
     DESCRIPTION    "This object is not supported in the current
                    MIB implementation."

    VARIATION       rttMonLatestJitterOperOWMaxDS
     ACCESS         not-implemented
     DESCRIPTION    "This object is not supported in the current
                    MIB implementation."

    VARIATION       rttMonLatestJitterOperNumOfOW
     ACCESS         not-implemented
     DESCRIPTION    "This object is not supported in the current
                    MIB implementation."

    VARIATION       rttMonApplMaxPacketDataSize
     ACCESS         not-implemented
     DESCRIPTION    "This object is not supported in the current
                    MIB implementation."

    VARIATION       rttMonApplTimeOfLastSet
     ACCESS         not-implemented
     DESCRIPTION    "This object is not supported in the current
                    MIB implementation."

    VARIATION       rttMonApplSupportedRttTypesValid
     ACCESS         not-implemented
     DESCRIPTION    "This object is not supported in the current
                    MIB implementation."

    VARIATION       rttMonApplSupportedProtocolsValid
     ACCESS         not-implemented
     DESCRIPTION    "This object is not supported in the current
                    MIB implementation."

    VARIATION       rttMonApplReset
     ACCESS         not-implemented
     DESCRIPTION    "This object is not supported in the current
                    MIB implementation."

    VARIATION       rttMonApplProbeCapacity
     ACCESS         not-implemented
     DESCRIPTION    "This object is not supported in the current
                    MIB implementation."

    VARIATION       rttMonApplLatestSetError
     ACCESS         not-implemented
     DESCRIPTION    "This object is not supported in the current
                    MIB implementation."

    VARIATION       rttMonGrpScheduleAdminProbes
     ACCESS         not-implemented
     DESCRIPTION    "This object is not supported in the current
                    MIB implementation."

    VARIATION       rttMonGrpScheduleAdminPeriod
     ACCESS         not-implemented
     DESCRIPTION    "This object is not supported in the current
                    MIB implementation."

    VARIATION       rttMonGrpScheduleAdminFrequency
     ACCESS         not-implemented
     DESCRIPTION    "This object is not supported in the current
                    MIB implementation."

    VARIATION       rttMonGrpScheduleAdminLife
     ACCESS         not-implemented
     DESCRIPTION    "This object is not supported in the current
                    MIB implementation."

    VARIATION       rttMonGrpScheduleAdminAgeout
     ACCESS         not-implemented
     DESCRIPTION    "This object is not supported in the current
                    MIB implementation."

    VARIATION       rttMonGrpScheduleAdminStatus
     ACCESS         not-implemented
     DESCRIPTION    "This object is not supported in the current
                    MIB implementation."

    VARIATION       rttMonJitterStatsAvgJitter
     ACCESS         not-implemented
     DESCRIPTION    "This object is not supported in the current
                    MIB implementation."

    VARIATION       rttMonJitterStatsAvgJitterSD
     ACCESS         not-implemented
     DESCRIPTION    "This object is not supported in the current
                    MIB implementation."

    VARIATION       rttMonJitterStatsAvgJitterDS
     ACCESS         not-implemented
     DESCRIPTION    "This object is not supported in the current
                    MIB implementation."

    VARIATION       rttMonJitterStatsUnSyncRTs
     ACCESS         not-implemented
     DESCRIPTION    "This object is not supported in the current
                    MIB implementation."

    VARIATION       rttMonLatestJitterOperIAJIn
     ACCESS         not-implemented
     DESCRIPTION    "This object is not supported in the current
                    MIB implementation."

    VARIATION       rttMonLatestJitterOperIAJOut
     ACCESS         not-implemented
     DESCRIPTION    "This object is not supported in the current
                    MIB implementation."

    VARIATION       rttMonLatestJitterOperAvgJitter
     ACCESS         not-implemented
     DESCRIPTION    "This object is not supported in the current
                    MIB implementation."

    VARIATION       rttMonLatestJitterOperAvgSDJ
     ACCESS         not-implemented
     DESCRIPTION    "This object is not supported in the current
                    MIB implementation."

    VARIATION       rttMonLatestJitterOperAvgDSJ
     ACCESS         not-implemented
     DESCRIPTION    "This object is not supported in the current
                    MIB implementation."

    VARIATION       rttMonLatestJitterOperOWAvgSD
     ACCESS         not-implemented
     DESCRIPTION    "This object is not supported in the current
                    MIB implementation."

    VARIATION       rttMonLatestJitterOperOWAvgDS
     ACCESS         not-implemented
     DESCRIPTION    "This object is not supported in the current
                    MIB implementation."

    VARIATION       rttMonLatestJitterOperNTPState
     ACCESS         not-implemented
     DESCRIPTION    "This object is not supported in the current
                    MIB implementation."

    VARIATION       rttMonLatestJitterOperUnSyncRTs
     ACCESS         not-implemented
     DESCRIPTION    "This object is not supported in the current
                    MIB implementation."

    VARIATION       rttMonReactVar
     SYNTAX         INTEGER
     {
       rtt(1),
       jitterSDAvg(2),
       jitterDSAvg(3),
       packetLossSD(4),
       packetLossDS(5),
       timeout(7),
       connectionLoss(8),
       verifyError(9),
       jitterAvg(10)
     }
     DESCRIPTION    "The values mentioned above are supported 
                     for this object."

    VARIATION       rttMonGrpScheduleAdminFreqMax
     ACCESS         not-implemented
     DESCRIPTION    "This object is not supported in the current
                    MIB implementation."

    VARIATION       rttMonGrpScheduleAdminFreqMin
     ACCESS         not-implemented
     DESCRIPTION    "This object is not supported in the current
                    MIB implementation."

    ::= { ciscoRttMonCapability 5 }

ciscoRttMonCapV12R0201SRB AGENT-CAPABILITIES
    PRODUCT-RELEASE "Cisco IOS 12.2(01)SRB"
    STATUS          current
    DESCRIPTION     "Cisco RTTMON MIB capabilities"
    SUPPORTS        CISCO-RTTMON-MIB
        INCLUDES    { ciscoStatsGroup, ciscoHistoryGroup,
                      ciscoCtrlGroupRev1, ciscoCtrlGroupRev2,
                      ciscoLatestOperGroupRev1, ciscoStatsGroupRev1,
                      ciscoStatsGroupRev3, ciscoStatsGroupRev4,
                      ciscoStatsGroupRev5, ciscoApplGroupRev2,
                      ciscoApplGroupRev3, ciscoApplGroupRev4,
                      ciscoNotificationGroupRev1, ciscoNotificationGroupRev2,
                      ciscoCtrlGroupRev4, ciscoCtrlGroupRev6,
                      ciscoCtrlGroupRev7, ciscoStatsGroupRev7,
                      ciscoCtrlGroupRev8, ciscoCtrlGroupRev9,
                      ciscoCtrlGroupRev10, ciscoCtrlGroupRev11,
                      ciscoCtrlGroupRev13, ciscoCtrlGroupRev15
                    }

    VARIATION rttMonEchoAdminProtocol
    DESCRIPTION
        "protocol values rtpAppl and icmpJitterAppl are not supported"

    VARIATION rttMonCtrlAdminRttType
    DESCRIPTION
        "RttMonRttType values rtp and icmpJitter are not supported"

    VARIATION rttMonReactVar
    DESCRIPTION
        "The RttMonReactVar values iaJitterDS, frameLossDS,
         mosLQDS, mosCQDS, rFactorDS, iaJitterSD, rFactorSD, mosCQSD,
         successivePacketLoss, maxOfLatencyDS, maxOfLatencySD,
         latencyDSAvg, latencySDAvg and packetLoss are not supported."

    ::= { ciscoRttMonCapability 6 }

END
