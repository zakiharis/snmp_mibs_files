-- *****************************************************************
-- CISCO-VOICE-ANALOG-IF-CAPABILITY.my: CISCO-VOICE-ANALOG-IF-MIB
--                                      AGENT-CAPABILITIES
--
-- June 1997  Hongchi Shih   
--
-- Copyright (c) 1997 by cisco Systems, Inc.
-- All rights reserved.
-- *****************************************************************

CISCO-VOICE-ANALOG-IF-CAPABILITY DEFINITIONS ::= BEGIN

IMPORTS
    MODULE-IDENTITY
        FROM SNMPv2-SMI
    AGENT-CAPABILITIES
        FROM SNMPv2-CONF
    ciscoAgentCapability
        FROM CISCO-SMI;


ciscoVoiceAnalogIfCapability MODULE-IDENTITY
        LAST-UPDATED    "200304280000Z"
        ORGANIZATION    "Cisco Systems, Inc."
        CONTACT-INFO
                "       Cisco Systems
                        Customer Service

                Postal: 170 W. Tasman Drive
                        San Jose, CA  95134
                        USA

                Tel: +1 800 553-NETS

                E-mail: cs-voice@cisco.com"
        DESCRIPTION
                "Agent capabilities for CISCO-VOICE-ANALOG-IF-MIB"

        REVISION    "200304280000Z"
        DESCRIPTION
		"cvaIfEMCfgLmrMCap & cvaIfEMCfgLmrECap are
		 readonly"

        REVISION    "9706150000Z"
        DESCRIPTION
                "Initial version of this MIB module."

        ::= { ciscoAgentCapability 82 }

ciscoVoiceAnalogIfCapabilityV11R03 AGENT-CAPABILITIES

PRODUCT-RELEASE "Cisco IOS 11.3"
STATUS      current
DESCRIPTION "Cisco Voice Analog Interface MIB capabilities"

SUPPORTS    CISCO-VOICE-ANALOG-IF-MIB
INCLUDES  { cvaIfGeneralGroup,cvaIfEMGroup,cvaIfFXOGroup,cvaIfFXSGroup}

-- cvaIfCfgEntry

    VARIATION cvaIfCfgImpedance
      ACCESS read-only
      DESCRIPTION "write not implemented"

-- cvaIfEMCfgEntry

    VARIATION cvaIfEMCfgSignalType
      ACCESS read-only
      DESCRIPTION "write not implemented"

    VARIATION cvaIfEMCfgOperation
      ACCESS read-only
      DESCRIPTION "write not implemented"

    VARIATION cvaIfEMCfgType
      ACCESS read-only
      DESCRIPTION "write not implemented"

    VARIATION cvaIfEMCfgDialType
      ACCESS read-only
      DESCRIPTION "write not implemented"

    VARIATION cvaIfEMCfgLmrMCap
      ACCESS read-only
      DESCRIPTION "write not implemented"

    VARIATION cvaIfEMCfgLmrECap
      ACCESS read-only
      DESCRIPTION "write not implemented"

-- cvaIfEMTimingEntry

    VARIATION cvaIfEMTimingDigitDuration
      ACCESS read-only
      DESCRIPTION "write not implemented"

    VARIATION cvaIfEMTimingInterDigitDuration
      ACCESS read-only
      DESCRIPTION "write not implemented"

    VARIATION cvaIfEMTimingPulseRate
      ACCESS read-only
      DESCRIPTION "write not implemented"

    VARIATION cvaIfEMTimingPulseInterDigitDuration
      ACCESS read-only
      DESCRIPTION "write not implemented"

    VARIATION cvaIfEMTimingClearWaitDuration
      ACCESS read-only
      DESCRIPTION "write not implemented"

    VARIATION cvaIfEMTimingMaxWinkWaitDuration
      ACCESS read-only
      DESCRIPTION "write not implemented"

    VARIATION cvaIfEMTimingMaxWinkDuration
      ACCESS read-only
      DESCRIPTION "write not implemented"

    VARIATION cvaIfEMTimingDelayStart
      ACCESS read-only
      DESCRIPTION "write not implemented"

    VARIATION cvaIfEMTimingMaxDelayDuration
      ACCESS read-only
      DESCRIPTION "write not implemented"

    VARIATION cvaIfEMTimingMinDelayPulseWidth
      ACCESS read-only
      DESCRIPTION "write not implemented"

    VARIATION cvaIfEMTimingVoiceHangover
      ACCESS read-only
      DESCRIPTION "write not implemented"

    VARIATION cvaIfEMTimeoutLmrTeardown
      ACCESS read-only
      DESCRIPTION "write not implemented"

-- cvaIfFXOCfgEntry

    VARIATION cvaIfFXOCfgSignalType
      ACCESS read-only
      DESCRIPTION "write not implemented"

    VARIATION cvaIfFXOCfgNumberRings
      ACCESS read-only
      DESCRIPTION "write not implemented"

    VARIATION cvaIfFXOCfgSupDisconnect
      ACCESS read-only
      DESCRIPTION "write not implemented"

    VARIATION cvaIfFXOCfgDialType
      ACCESS read-only
      DESCRIPTION "write not implemented"

-- cvaIfFXOTimingEntry

    VARIATION cvaIfFXOTimingDigitDuration
      ACCESS read-only
      DESCRIPTION "write not implemented"

    VARIATION cvaIfFXOTimingInterDigitDuration
      ACCESS read-only
      DESCRIPTION "write not implemented"

    VARIATION cvaIfFXOTimingPulseRate
      ACCESS read-only
      DESCRIPTION "write not implemented"

    VARIATION cvaIfFXOTimingPulseInterDigitDuration
      ACCESS read-only
      DESCRIPTION "write not implemented"

-- cvaIfFXSCfgEntry

    VARIATION cvaIfFXSCfgSignalType
      ACCESS read-only
      DESCRIPTION "write not implemented"

    VARIATION cvaIfFXSRingFrequency
      SYNTAX  INTEGER {ringFrequency25(1), ringFrequency50(2)}
      -- no { ringFrequency20(3), ringFrequency30(4) }
      ACCESS read-only
      DESCRIPTION "write not implemented; 
                   Unable to detect ringFrequency20(3) and 
                   ringFrequency30(4).
                   the default value of the object is 
                   ringFrequency25(1).
                   "

-- cvaIfFXSTimingEntry

    VARIATION cvaIfFXSTimingDigitDuration
      ACCESS read-only
      DESCRIPTION "write not implemented"

    VARIATION cvaIfFXSTimingInterDigitDuration
      ACCESS read-only
      DESCRIPTION "write not implemented"
    ::= { ciscoVoiceAnalogIfCapability 1 }

END
