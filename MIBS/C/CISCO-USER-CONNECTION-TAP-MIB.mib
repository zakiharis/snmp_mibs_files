-- MIB file created 28-Oct-2010 15:03:14, by
--   SMICng version 2.2.11-beta(PRO)(Solaris), January 20, 2001. Enterprise key cisco.com

CISCO-USER-CONNECTION-TAP-MIB DEFINITIONS ::= BEGIN

-- From file: "CISCO-USER-CONNECTION-TAP-MIB.my"
-- Compile options "4 7 F H N W 03 06 0B 0G 0N 0T"

IMPORTS
    RowStatus
            FROM SNMPv2-TC-v1
    cTap2MediationContentId, cTap2StreamIndex
            FROM CISCO-TAP2-MIB
    ciscoMgmt
            FROM CISCO-SMI
    Gauge
            FROM RFC1155-SMI
    OBJECT-TYPE
            FROM RFC-1212;

ciscoUserConnectionTapMIB OBJECT IDENTIFIER ::= { ciscoMgmt 400 }
-- MODULE-IDENTITY
--  LastUpdated
--    200708090000Z
--  OrgName
--    Cisco Systems, Inc.
--  ContactInfo
--    Cisco Systems
--    Customer Service
--    
--    Postal:170 W. Tasman Drive
--    San Jose, CA  95134
--    USA
--    
--    Tel:+1 800 553-NETS
--    
--    E-mail:cs-li@cisco.com
--  Descr
--    This module manages Cisco's intercept feature for
--    user connections.
--    
--    This MIB is used along with CISCO-TAP2-MIB to
--    intercept user traffic. CISCO-TAP2-MIB along with
--    specific filter MIBs like this MIB replace
--    CISCO-TAP-MIB.
--    
--    To create an user connection intercept, an entry 
--    cuctTapStreamEntry is created which contains the filter 
--    details. An entry cTap2StreamEntry of CISCO-TAP2-MIB 
--    is created, which is the common stream information 
--    for all kinds of intercepts and type of the specific
--    stream is set to userconnection in this entry.
--  RevDate
--    200708090000Z
--  RevDescr
--    Correct the DESCRIPTION clause of cutcTapStreamTable.
--  RevDate
--    200403110000Z
--  RevDescr
--    Initial version of this MIB module.

cUserConnectionTapMIBObjects OBJECT IDENTIFIER ::= { ciscoUserConnectionTapMIB 1 }
cUserConnectionTapMIBConform OBJECT IDENTIFIER ::= { ciscoUserConnectionTapMIB 2 }
cuctTapStreamEncodePacket OBJECT IDENTIFIER ::= { cUserConnectionTapMIBObjects 1 }
cUserConnectionTapMIBCompliances OBJECT IDENTIFIER ::= { cUserConnectionTapMIBConform 1 }
cUserConnectionTapMIBGroups OBJECT IDENTIFIER ::= { cUserConnectionTapMIBConform 2 }

cuctTapStreamCapabilities OBJECT-TYPE
    SYNTAX OCTET STRING(SIZE(1..2))
        -- BITS are:
        --   tapEnable(0)
        --   acctSessionId(1)
    ACCESS read-only
    STATUS mandatory
    DESCRIPTION
        "This object displays the types of intercepts supported on
        this device. This may be dependent on hardware capabilities
        or software capabilities. The value of this object is non 
        zero, if the device supports interception of user connection
        traffic. A device may support both types of intercepts at
        the same time.
        The following fields may be supported:
            acctSessonId: packets belonging to a user connection 
                          identified by RADIUS attribute 
                          account-session-ID may be intercepted.
            tapEnable:    set if table entries with
                          cTap2StreamInterceptEnable set to 'false'
                          are used to pre-screen packets for intercept;
                          otherwise these entries are ignored."
    ::= { cuctTapStreamEncodePacket 1 }

cuctTapStreamTable OBJECT-TYPE
    SYNTAX SEQUENCE OF CuctTapStreamEntry
    ACCESS not-accessible
    STATUS mandatory
    DESCRIPTION
        "The Intercept Stream Connection Table lists the user
        connections (sessions) to be intercepted.  The same data 
        stream may be required by multiple taps, and one might 
        assume that often the intercepted stream is a small 
        subset of the traffic that could be intercepted.
        
        
        This essentially provides options for packet selection.
        The only option available is RADIUS attribute 44, 
        account session ID. When a user tries to use a service 
        provided by a Network Access Server(NAS) such as PPP,
        NAS authenticates the user with RADIUS server. Upon
        successful authentication of the user, the user is 
        provided with the requested service and NAS creates an
        accounting record with RADIUS accounting server for 
        the user. The NAS assigns a unique account session id
        for the user session in the accounting record created
        with the RADIUS server. The account session ID may be
        used to intercept traffic belonging to the user session.
        
        
        The value of first index is that of an entry in the
        cTap2MediationTable, which identifies the application
        to which intercepted traffic will be sent to. The second 
        index permits connection classifiers to be used to 
        identify traffic to be intercepted. The value of the
        second index is that of the stream's counter entry 
        in the cTap2StreamTable."
    ::= { cuctTapStreamEncodePacket 2 }

cuctTapStreamEntry OBJECT-TYPE
    SYNTAX CuctTapStreamEntry
    ACCESS not-accessible
    STATUS mandatory
    DESCRIPTION
        "A stream entry indicates a single data stream to be
        intercepted to a Mediation Device. Many selected data
        streams may go to the same application interface, and 
        many application interfaces are supported."
    INDEX { cTap2MediationContentId, cTap2StreamIndex }
    ::= { cuctTapStreamTable 1 }

CuctTapStreamEntry ::= SEQUENCE {
    cuctTapStreamAcctSessID Gauge,
    cuctTapStreamStatus RowStatus
    }

cuctTapStreamAcctSessID OBJECT-TYPE
    SYNTAX Gauge(0..4294967295)
    ACCESS read-write
    STATUS mandatory
    DESCRIPTION
        "This is the RADIUS attribute 44 acct-session-ID. It
        identifies a user connection.  It is used to specify
        a user connection to intercept."
    REFERENCE
        "RFC 2059, RFC 2865"
    DEFVAL { 0 }
    ::= { cuctTapStreamEntry 1 }

cuctTapStreamStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. This object manages
        creation, modification, and deletion of rows in this
        table. When any rows must be changed, 
        cuctTapStreamStatus must be first set to 
        'notInService'."
    ::= { cuctTapStreamEntry 2 }

cuctTapStreamComplianceGroup OBJECT IDENTIFIER ::= { cUserConnectionTapMIBGroups 1 }
-- OBJECT-GROUP
--  Status
--    mandatory
--  Descr
--    These objects are necessary for a description of user
--    traffic packets to select for interception.
--  objects
--    cuctTapStreamCapabilities, cuctTapStreamAcctSessID, 
--    cuctTapStreamStatus

cUserConnectionTapMIBCompliance OBJECT IDENTIFIER ::= { cUserConnectionTapMIBCompliances 1 }
-- MODULE-COMPLIANCE
--  Status
--    mandatory
--  Descr
--    The compliance statement for entities which implement the
--    Cisco Intercept MIB for user connections.
--  Module
--    >>current<<
--   MandGroup
--    cuctTapStreamComplianceGroup


END
