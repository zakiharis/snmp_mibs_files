-- *****************************************************************
-- DHCP-SNOOPING-MIB:  Cisco private MIB
-- ****************************************************************

CIE1000-DHCP-SNOOPING-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000InterfaceIndex FROM CIE1000-TC
    Integer32 FROM SNMPv2-SMI
    IpAddress FROM SNMPv2-SMI
    Unsigned32 FROM SNMPv2-SMI
    MacAddress FROM SNMPv2-TC
    TruthValue FROM SNMPv2-TC
    ;

cie1000DhcpSnoopingMib MODULE-IDENTITY
    LAST-UPDATED "201410100000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the DHCP Snooping MIB"
    REVISION    "201410100000Z"
    DESCRIPTION
        "Editorial changes"
    REVISION    "201407010000Z"
    DESCRIPTION
        "Initial version"
    ::= { cie1000SwitchMgmt 56 }


cie1000DhcpSnoopingMibObjects OBJECT IDENTIFIER
    ::= { cie1000DhcpSnoopingMib 1 }

cie1000DhcpSnoopingConfig OBJECT IDENTIFIER
    ::= { cie1000DhcpSnoopingMibObjects 2 }

cie1000DhcpSnoopingConfigGlobals OBJECT IDENTIFIER
    ::= { cie1000DhcpSnoopingConfig 1 }

cie1000DhcpSnoopingConfigGlobalsMode OBJECT-TYPE
    SYNTAX      TruthValue
    MAX-ACCESS  read-write
    STATUS      current
    DESCRIPTION
        "Indicates the DHCP snooping mode operation. Possible modes are - true:
         Enable DHCP snooping mode operation. When DHCP snooping mode operation
         is enabled, the DHCP request messages will be forwarded to trusted
         ports and only allow reply packets from trusted ports. false: Disable
         DHCP snooping mode operation."
    ::= { cie1000DhcpSnoopingConfigGlobals 1 }

cie1000DhcpSnoopingConfigInterfaceTable OBJECT-TYPE
    SYNTAX      SEQUENCE OF CIE1000DhcpSnoopingConfigInterfaceEntry
    MAX-ACCESS  not-accessible
    STATUS      current
    DESCRIPTION
        "This is a table of DHCP Snooping port configuration parameters"
    ::= { cie1000DhcpSnoopingConfig 2 }

cie1000DhcpSnoopingConfigInterfaceEntry OBJECT-TYPE
    SYNTAX      CIE1000DhcpSnoopingConfigInterfaceEntry
    MAX-ACCESS  not-accessible
    STATUS      current
    DESCRIPTION
        "Each port has a set of parameters"
    INDEX       { cie1000DhcpSnoopingConfigInterfaceIfIndex }
    ::= { cie1000DhcpSnoopingConfigInterfaceTable 1 }

CIE1000DhcpSnoopingConfigInterfaceEntry ::= SEQUENCE {
    cie1000DhcpSnoopingConfigInterfaceIfIndex    CIE1000InterfaceIndex,
    cie1000DhcpSnoopingConfigInterfaceTrustMode  TruthValue
}

cie1000DhcpSnoopingConfigInterfaceIfIndex OBJECT-TYPE
    SYNTAX      CIE1000InterfaceIndex
    MAX-ACCESS  accessible-for-notify
    STATUS      current
    DESCRIPTION
        "Logical interface number of the physical port."
    ::= { cie1000DhcpSnoopingConfigInterfaceEntry 1 }

cie1000DhcpSnoopingConfigInterfaceTrustMode OBJECT-TYPE
    SYNTAX      TruthValue
    MAX-ACCESS  read-write
    STATUS      current
    DESCRIPTION
        "Indicates the DHCP snooping port mode. Possible port modes are - true:
         Configures the port as trusted source of the DHCP messages. false:
         Configures the port as untrusted source of the DHCP messages."
    ::= { cie1000DhcpSnoopingConfigInterfaceEntry 2 }

cie1000DhcpSnoopingStatus OBJECT IDENTIFIER
    ::= { cie1000DhcpSnoopingMibObjects 3 }

cie1000DhcpSnoopingStatusAssignedIpTable OBJECT-TYPE
    SYNTAX      SEQUENCE OF CIE1000DhcpSnoopingStatusAssignedIpEntry
    MAX-ACCESS  not-accessible
    STATUS      current
    DESCRIPTION
        "This is a table of assigned IP information in DHCP Snooping "
    ::= { cie1000DhcpSnoopingStatus 1 }

cie1000DhcpSnoopingStatusAssignedIpEntry OBJECT-TYPE
    SYNTAX      CIE1000DhcpSnoopingStatusAssignedIpEntry
    MAX-ACCESS  not-accessible
    STATUS      current
    DESCRIPTION
        "Each entry has a set of parameters"
    INDEX       { cie1000DhcpSnoopingStatusAssignedIpMacAddress,
                  cie1000DhcpSnoopingStatusAssignedIpVlanId }
    ::= { cie1000DhcpSnoopingStatusAssignedIpTable 1 }

CIE1000DhcpSnoopingStatusAssignedIpEntry ::= SEQUENCE {
    cie1000DhcpSnoopingStatusAssignedIpMacAddress    MacAddress,
    cie1000DhcpSnoopingStatusAssignedIpVlanId        Integer32,
    cie1000DhcpSnoopingStatusAssignedIpIfIndex       CIE1000InterfaceIndex,
    cie1000DhcpSnoopingStatusAssignedIpIpAddress     IpAddress,
    cie1000DhcpSnoopingStatusAssignedIpNetmask       IpAddress,
    cie1000DhcpSnoopingStatusAssignedIpDhcpServerIp  IpAddress
}

cie1000DhcpSnoopingStatusAssignedIpMacAddress OBJECT-TYPE
    SYNTAX      MacAddress
    MAX-ACCESS  accessible-for-notify
    STATUS      current
    DESCRIPTION
        "MAC address."
    ::= { cie1000DhcpSnoopingStatusAssignedIpEntry 1 }

cie1000DhcpSnoopingStatusAssignedIpVlanId OBJECT-TYPE
    SYNTAX      Integer32 (1..4095)
    MAX-ACCESS  accessible-for-notify
    STATUS      current
    DESCRIPTION
        "The VLAN id of the VLAN."
    ::= { cie1000DhcpSnoopingStatusAssignedIpEntry 2 }

cie1000DhcpSnoopingStatusAssignedIpIfIndex OBJECT-TYPE
    SYNTAX      CIE1000InterfaceIndex
    MAX-ACCESS  read-only
    STATUS      current
    DESCRIPTION
        "Logical interface number of the physical port of the DHCP client."
    ::= { cie1000DhcpSnoopingStatusAssignedIpEntry 3 }

cie1000DhcpSnoopingStatusAssignedIpIpAddress OBJECT-TYPE
    SYNTAX      IpAddress
    MAX-ACCESS  read-only
    STATUS      current
    DESCRIPTION
        "IP address assigned to DHCP client by DHCP server."
    ::= { cie1000DhcpSnoopingStatusAssignedIpEntry 4 }

cie1000DhcpSnoopingStatusAssignedIpNetmask OBJECT-TYPE
    SYNTAX      IpAddress
    MAX-ACCESS  read-only
    STATUS      current
    DESCRIPTION
        "Netmask assigned to DHCP client by DHCP server."
    ::= { cie1000DhcpSnoopingStatusAssignedIpEntry 5 }

cie1000DhcpSnoopingStatusAssignedIpDhcpServerIp OBJECT-TYPE
    SYNTAX      IpAddress
    MAX-ACCESS  read-only
    STATUS      current
    DESCRIPTION
        "IP address of the DHCP server that assigns the IP address and netmask."
    ::= { cie1000DhcpSnoopingStatusAssignedIpEntry 6 }

cie1000DhcpSnoopingControl OBJECT IDENTIFIER
    ::= { cie1000DhcpSnoopingMibObjects 4 }

cie1000DhcpSnoopingControlInterfaceClearStatisticsTable OBJECT-TYPE
    SYNTAX      SEQUENCE OF CIE1000DhcpSnoopingControlInterfaceClearStatisticsEntry
    MAX-ACCESS  not-accessible
    STATUS      current
    DESCRIPTION
        "This is a table to clear port statistics in DHCP Snooping"
    ::= { cie1000DhcpSnoopingControl 1 }

cie1000DhcpSnoopingControlInterfaceClearStatisticsEntry OBJECT-TYPE
    SYNTAX      CIE1000DhcpSnoopingControlInterfaceClearStatisticsEntry
    MAX-ACCESS  not-accessible
    STATUS      current
    DESCRIPTION
        "Each port has a set of parameters"
    INDEX       {                   cie1000DhcpSnoopingControlInterfaceClearStatisticsIfIndex }
    ::= { cie1000DhcpSnoopingControlInterfaceClearStatisticsTable 1 }

CIE1000DhcpSnoopingControlInterfaceClearStatisticsEntry ::= SEQUENCE {
    cie1000DhcpSnoopingControlInterfaceClearStatisticsIfIndex  CIE1000InterfaceIndex,
    cie1000DhcpSnoopingControlInterfaceClearStatisticsClear    TruthValue
}

cie1000DhcpSnoopingControlInterfaceClearStatisticsIfIndex OBJECT-TYPE
    SYNTAX      CIE1000InterfaceIndex
    MAX-ACCESS  accessible-for-notify
    STATUS      current
    DESCRIPTION
        "Logical interface number of the physical port."
    ::= { cie1000DhcpSnoopingControlInterfaceClearStatisticsEntry 1 }

cie1000DhcpSnoopingControlInterfaceClearStatisticsClear OBJECT-TYPE
    SYNTAX      TruthValue
    MAX-ACCESS  read-write
    STATUS      current
    DESCRIPTION
        "clear statistics per physical port."
    ::= { cie1000DhcpSnoopingControlInterfaceClearStatisticsEntry 2 }

cie1000DhcpSnoopingStatistics OBJECT IDENTIFIER
    ::= { cie1000DhcpSnoopingMibObjects 5 }

cie1000DhcpSnoopingStatisticsInterfaceTable OBJECT-TYPE
    SYNTAX      SEQUENCE OF CIE1000DhcpSnoopingStatisticsInterfaceEntry
    MAX-ACCESS  not-accessible
    STATUS      current
    DESCRIPTION
        "This is a table of port statistics in DHCP Snooping "
    ::= { cie1000DhcpSnoopingStatistics 2 }

cie1000DhcpSnoopingStatisticsInterfaceEntry OBJECT-TYPE
    SYNTAX      CIE1000DhcpSnoopingStatisticsInterfaceEntry
    MAX-ACCESS  not-accessible
    STATUS      current
    DESCRIPTION
        "Each entry has a set of parameters"
    INDEX       { cie1000DhcpSnoopingStatisticsInterfaceIfIndex }
    ::= { cie1000DhcpSnoopingStatisticsInterfaceTable 1 }

CIE1000DhcpSnoopingStatisticsInterfaceEntry ::= SEQUENCE {
    cie1000DhcpSnoopingStatisticsInterfaceIfIndex             CIE1000InterfaceIndex,
    cie1000DhcpSnoopingStatisticsInterfaceRxDiscover          Unsigned32,
    cie1000DhcpSnoopingStatisticsInterfaceRxOffer             Unsigned32,
    cie1000DhcpSnoopingStatisticsInterfaceRxRequest           Unsigned32,
    cie1000DhcpSnoopingStatisticsInterfaceRxDecline           Unsigned32,
    cie1000DhcpSnoopingStatisticsInterfaceRxAck               Unsigned32,
    cie1000DhcpSnoopingStatisticsInterfaceRxNak               Unsigned32,
    cie1000DhcpSnoopingStatisticsInterfaceRxRelease           Unsigned32,
    cie1000DhcpSnoopingStatisticsInterfaceRxInform            Unsigned32,
    cie1000DhcpSnoopingStatisticsInterfaceRxLeaseQuery        Unsigned32,
    cie1000DhcpSnoopingStatisticsInterfaceRxLeaseUnassigned   Unsigned32,
    cie1000DhcpSnoopingStatisticsInterfaceRxLeaseUnknown      Unsigned32,
    cie1000DhcpSnoopingStatisticsInterfaceRxLeaseActive       Unsigned32,
    cie1000DhcpSnoopingStatisticsInterfaceRxDiscardChksumErr  Unsigned32,
    cie1000DhcpSnoopingStatisticsInterfaceRxDiscardUntrust    Unsigned32,
    cie1000DhcpSnoopingStatisticsInterfaceTxDiscover          Unsigned32,
    cie1000DhcpSnoopingStatisticsInterfaceTxOffer             Unsigned32,
    cie1000DhcpSnoopingStatisticsInterfaceTxRequest           Unsigned32,
    cie1000DhcpSnoopingStatisticsInterfaceTxDecline           Unsigned32,
    cie1000DhcpSnoopingStatisticsInterfaceTxAck               Unsigned32,
    cie1000DhcpSnoopingStatisticsInterfaceTxNak               Unsigned32,
    cie1000DhcpSnoopingStatisticsInterfaceTxRelease           Unsigned32,
    cie1000DhcpSnoopingStatisticsInterfaceTxInform            Unsigned32,
    cie1000DhcpSnoopingStatisticsInterfaceTxLeaseQuery        Unsigned32,
    cie1000DhcpSnoopingStatisticsInterfaceTxLeaseUnassigned   Unsigned32,
    cie1000DhcpSnoopingStatisticsInterfaceTxLeaseUnknown      Unsigned32,
    cie1000DhcpSnoopingStatisticsInterfaceTxLeaseActive       Unsigned32
}

cie1000DhcpSnoopingStatisticsInterfaceIfIndex OBJECT-TYPE
    SYNTAX      CIE1000InterfaceIndex
    MAX-ACCESS  accessible-for-notify
    STATUS      current
    DESCRIPTION
        "Logical interface number of the physical port."
    ::= { cie1000DhcpSnoopingStatisticsInterfaceEntry 1 }

cie1000DhcpSnoopingStatisticsInterfaceRxDiscover OBJECT-TYPE
    SYNTAX      Unsigned32
    MAX-ACCESS  read-only
    STATUS      current
    DESCRIPTION
        "The number of discover (option 53 with value 1) packets received."
    ::= { cie1000DhcpSnoopingStatisticsInterfaceEntry 2 }

cie1000DhcpSnoopingStatisticsInterfaceRxOffer OBJECT-TYPE
    SYNTAX      Unsigned32
    MAX-ACCESS  read-only
    STATUS      current
    DESCRIPTION
        "The number of offer (option 53 with value 2) packets received."
    ::= { cie1000DhcpSnoopingStatisticsInterfaceEntry 3 }

cie1000DhcpSnoopingStatisticsInterfaceRxRequest OBJECT-TYPE
    SYNTAX      Unsigned32
    MAX-ACCESS  read-only
    STATUS      current
    DESCRIPTION
        "The number of request (option 53 with value 3) packets received."
    ::= { cie1000DhcpSnoopingStatisticsInterfaceEntry 4 }

cie1000DhcpSnoopingStatisticsInterfaceRxDecline OBJECT-TYPE
    SYNTAX      Unsigned32
    MAX-ACCESS  read-only
    STATUS      current
    DESCRIPTION
        "The number of decline (option 53 with value 4) packets received."
    ::= { cie1000DhcpSnoopingStatisticsInterfaceEntry 5 }

cie1000DhcpSnoopingStatisticsInterfaceRxAck OBJECT-TYPE
    SYNTAX      Unsigned32
    MAX-ACCESS  read-only
    STATUS      current
    DESCRIPTION
        "The number of ACK (option 53 with value 5) packets received."
    ::= { cie1000DhcpSnoopingStatisticsInterfaceEntry 6 }

cie1000DhcpSnoopingStatisticsInterfaceRxNak OBJECT-TYPE
    SYNTAX      Unsigned32
    MAX-ACCESS  read-only
    STATUS      current
    DESCRIPTION
        "The number of NAK (option 53 with value 6) packets received."
    ::= { cie1000DhcpSnoopingStatisticsInterfaceEntry 7 }

cie1000DhcpSnoopingStatisticsInterfaceRxRelease OBJECT-TYPE
    SYNTAX      Unsigned32
    MAX-ACCESS  read-only
    STATUS      current
    DESCRIPTION
        "The number of release (option 53 with value 7) packets received."
    ::= { cie1000DhcpSnoopingStatisticsInterfaceEntry 8 }

cie1000DhcpSnoopingStatisticsInterfaceRxInform OBJECT-TYPE
    SYNTAX      Unsigned32
    MAX-ACCESS  read-only
    STATUS      current
    DESCRIPTION
        "The number of inform (option 53 with value 8) packets received."
    ::= { cie1000DhcpSnoopingStatisticsInterfaceEntry 9 }

cie1000DhcpSnoopingStatisticsInterfaceRxLeaseQuery OBJECT-TYPE
    SYNTAX      Unsigned32
    MAX-ACCESS  read-only
    STATUS      current
    DESCRIPTION
        "The number of lease query (option 53 with value 10) packets received."
    ::= { cie1000DhcpSnoopingStatisticsInterfaceEntry 10 }

cie1000DhcpSnoopingStatisticsInterfaceRxLeaseUnassigned OBJECT-TYPE
    SYNTAX      Unsigned32
    MAX-ACCESS  read-only
    STATUS      current
    DESCRIPTION
        "The number of lease unassigned (option 53 with value 11) packets
         received."
    ::= { cie1000DhcpSnoopingStatisticsInterfaceEntry 11 }

cie1000DhcpSnoopingStatisticsInterfaceRxLeaseUnknown OBJECT-TYPE
    SYNTAX      Unsigned32
    MAX-ACCESS  read-only
    STATUS      current
    DESCRIPTION
        "The number of lease unknown (option 53 with value 12) packets received."
    ::= { cie1000DhcpSnoopingStatisticsInterfaceEntry 12 }

cie1000DhcpSnoopingStatisticsInterfaceRxLeaseActive OBJECT-TYPE
    SYNTAX      Unsigned32
    MAX-ACCESS  read-only
    STATUS      current
    DESCRIPTION
        "The number of lease active (option 53 with value 13) packets received."
    ::= { cie1000DhcpSnoopingStatisticsInterfaceEntry 13 }

cie1000DhcpSnoopingStatisticsInterfaceRxDiscardChksumErr OBJECT-TYPE
    SYNTAX      Unsigned32
    MAX-ACCESS  read-only
    STATUS      current
    DESCRIPTION
        "The number of discard packet that IP/UDP checksum is error."
    ::= { cie1000DhcpSnoopingStatisticsInterfaceEntry 14 }

cie1000DhcpSnoopingStatisticsInterfaceRxDiscardUntrust OBJECT-TYPE
    SYNTAX      Unsigned32
    MAX-ACCESS  read-only
    STATUS      current
    DESCRIPTION
        "The number of discard packet that are coming from untrusted port."
    ::= { cie1000DhcpSnoopingStatisticsInterfaceEntry 15 }

cie1000DhcpSnoopingStatisticsInterfaceTxDiscover OBJECT-TYPE
    SYNTAX      Unsigned32
    MAX-ACCESS  read-only
    STATUS      current
    DESCRIPTION
        "The number of discover (option 53 with value 1) packets transmited."
    ::= { cie1000DhcpSnoopingStatisticsInterfaceEntry 16 }

cie1000DhcpSnoopingStatisticsInterfaceTxOffer OBJECT-TYPE
    SYNTAX      Unsigned32
    MAX-ACCESS  read-only
    STATUS      current
    DESCRIPTION
        "The number of offer (option 53 with value 2) packets transmited."
    ::= { cie1000DhcpSnoopingStatisticsInterfaceEntry 17 }

cie1000DhcpSnoopingStatisticsInterfaceTxRequest OBJECT-TYPE
    SYNTAX      Unsigned32
    MAX-ACCESS  read-only
    STATUS      current
    DESCRIPTION
        "The number of request (option 53 with value 3) packets transmited."
    ::= { cie1000DhcpSnoopingStatisticsInterfaceEntry 18 }

cie1000DhcpSnoopingStatisticsInterfaceTxDecline OBJECT-TYPE
    SYNTAX      Unsigned32
    MAX-ACCESS  read-only
    STATUS      current
    DESCRIPTION
        "The number of decline (option 53 with value 4) packets transmited."
    ::= { cie1000DhcpSnoopingStatisticsInterfaceEntry 19 }

cie1000DhcpSnoopingStatisticsInterfaceTxAck OBJECT-TYPE
    SYNTAX      Unsigned32
    MAX-ACCESS  read-only
    STATUS      current
    DESCRIPTION
        "The number of ACK (option 53 with value 5) packets transmited."
    ::= { cie1000DhcpSnoopingStatisticsInterfaceEntry 20 }

cie1000DhcpSnoopingStatisticsInterfaceTxNak OBJECT-TYPE
    SYNTAX      Unsigned32
    MAX-ACCESS  read-only
    STATUS      current
    DESCRIPTION
        "The number of NAK (option 53 with value 6) packets transmited."
    ::= { cie1000DhcpSnoopingStatisticsInterfaceEntry 21 }

cie1000DhcpSnoopingStatisticsInterfaceTxRelease OBJECT-TYPE
    SYNTAX      Unsigned32
    MAX-ACCESS  read-only
    STATUS      current
    DESCRIPTION
        "The number of release (option 53 with value 7) packets transmited."
    ::= { cie1000DhcpSnoopingStatisticsInterfaceEntry 22 }

cie1000DhcpSnoopingStatisticsInterfaceTxInform OBJECT-TYPE
    SYNTAX      Unsigned32
    MAX-ACCESS  read-only
    STATUS      current
    DESCRIPTION
        "The number of inform (option 53 with value 8) packets transmited."
    ::= { cie1000DhcpSnoopingStatisticsInterfaceEntry 23 }

cie1000DhcpSnoopingStatisticsInterfaceTxLeaseQuery OBJECT-TYPE
    SYNTAX      Unsigned32
    MAX-ACCESS  read-only
    STATUS      current
    DESCRIPTION
        "The number of lease query (option 53 with value 10) packets transmited."
    ::= { cie1000DhcpSnoopingStatisticsInterfaceEntry 24 }

cie1000DhcpSnoopingStatisticsInterfaceTxLeaseUnassigned OBJECT-TYPE
    SYNTAX      Unsigned32
    MAX-ACCESS  read-only
    STATUS      current
    DESCRIPTION
        "The number of lease unassigned (option 53 with value 11) packets
         transmited."
    ::= { cie1000DhcpSnoopingStatisticsInterfaceEntry 25 }

cie1000DhcpSnoopingStatisticsInterfaceTxLeaseUnknown OBJECT-TYPE
    SYNTAX      Unsigned32
    MAX-ACCESS  read-only
    STATUS      current
    DESCRIPTION
        "The number of lease unknown (option 53 with value 12) packets
         transmited."
    ::= { cie1000DhcpSnoopingStatisticsInterfaceEntry 26 }

cie1000DhcpSnoopingStatisticsInterfaceTxLeaseActive OBJECT-TYPE
    SYNTAX      Unsigned32
    MAX-ACCESS  read-only
    STATUS      current
    DESCRIPTION
        "The number of lease active (option 53 with value 13) packets
         transmited."
    ::= { cie1000DhcpSnoopingStatisticsInterfaceEntry 27 }

cie1000DhcpSnoopingMibConformance OBJECT IDENTIFIER
    ::= { cie1000DhcpSnoopingMib 2 }

cie1000DhcpSnoopingMibCompliances OBJECT IDENTIFIER
    ::= { cie1000DhcpSnoopingMibConformance 1 }

cie1000DhcpSnoopingMibGroups OBJECT IDENTIFIER
    ::= { cie1000DhcpSnoopingMibConformance 2 }

cie1000DhcpSnoopingConfigGlobalsInfoGroup OBJECT-GROUP
    OBJECTS     { cie1000DhcpSnoopingConfigGlobalsMode }
    STATUS      current
    DESCRIPTION
        "A collection of objects."
    ::= { cie1000DhcpSnoopingMibGroups 1 }

cie1000DhcpSnoopingConfigInterfaceInfoGroup OBJECT-GROUP
    OBJECTS     { cie1000DhcpSnoopingConfigInterfaceIfIndex,
                  cie1000DhcpSnoopingConfigInterfaceTrustMode }
    STATUS      current
    DESCRIPTION
        "A collection of objects."
    ::= { cie1000DhcpSnoopingMibGroups 2 }

cie1000DhcpSnoopingStatusAssignedIpTableInfoGroup OBJECT-GROUP
    OBJECTS     { cie1000DhcpSnoopingStatusAssignedIpMacAddress,
                  cie1000DhcpSnoopingStatusAssignedIpVlanId,
                  cie1000DhcpSnoopingStatusAssignedIpIfIndex,
                  cie1000DhcpSnoopingStatusAssignedIpIpAddress,
                  cie1000DhcpSnoopingStatusAssignedIpNetmask,
                  cie1000DhcpSnoopingStatusAssignedIpDhcpServerIp }
    STATUS      current
    DESCRIPTION
        "A collection of objects."
    ::= { cie1000DhcpSnoopingMibGroups 3 }

cie1000DhcpSnoopingControlInterfaceClearStatisticsTableInfoGroup OBJECT-GROUP
    OBJECTS     {                   cie1000DhcpSnoopingControlInterfaceClearStatisticsIfIndex,
                  cie1000DhcpSnoopingControlInterfaceClearStatisticsClear }
    STATUS      current
    DESCRIPTION
        "A collection of objects."
    ::= { cie1000DhcpSnoopingMibGroups 4 }

cie1000DhcpSnoopingStatisticsInterfaceTableInfoGroup OBJECT-GROUP
    OBJECTS     { cie1000DhcpSnoopingStatisticsInterfaceIfIndex,
                  cie1000DhcpSnoopingStatisticsInterfaceRxDiscover,
                  cie1000DhcpSnoopingStatisticsInterfaceRxOffer,
                  cie1000DhcpSnoopingStatisticsInterfaceRxRequest,
                  cie1000DhcpSnoopingStatisticsInterfaceRxDecline,
                  cie1000DhcpSnoopingStatisticsInterfaceRxAck,
                  cie1000DhcpSnoopingStatisticsInterfaceRxNak,
                  cie1000DhcpSnoopingStatisticsInterfaceRxRelease,
                  cie1000DhcpSnoopingStatisticsInterfaceRxInform,
                  cie1000DhcpSnoopingStatisticsInterfaceRxLeaseQuery,
                  cie1000DhcpSnoopingStatisticsInterfaceRxLeaseUnassigned,
                  cie1000DhcpSnoopingStatisticsInterfaceRxLeaseUnknown,
                  cie1000DhcpSnoopingStatisticsInterfaceRxLeaseActive,
                  cie1000DhcpSnoopingStatisticsInterfaceRxDiscardChksumErr,
                  cie1000DhcpSnoopingStatisticsInterfaceRxDiscardUntrust,
                  cie1000DhcpSnoopingStatisticsInterfaceTxDiscover,
                  cie1000DhcpSnoopingStatisticsInterfaceTxOffer,
                  cie1000DhcpSnoopingStatisticsInterfaceTxRequest,
                  cie1000DhcpSnoopingStatisticsInterfaceTxDecline,
                  cie1000DhcpSnoopingStatisticsInterfaceTxAck,
                  cie1000DhcpSnoopingStatisticsInterfaceTxNak,
                  cie1000DhcpSnoopingStatisticsInterfaceTxRelease,
                  cie1000DhcpSnoopingStatisticsInterfaceTxInform,
                  cie1000DhcpSnoopingStatisticsInterfaceTxLeaseQuery,
                  cie1000DhcpSnoopingStatisticsInterfaceTxLeaseUnassigned,
                  cie1000DhcpSnoopingStatisticsInterfaceTxLeaseUnknown,
                  cie1000DhcpSnoopingStatisticsInterfaceTxLeaseActive }
    STATUS      current
    DESCRIPTION
        "A collection of objects."
    ::= { cie1000DhcpSnoopingMibGroups 5 }

cie1000DhcpSnoopingMibCompliance MODULE-COMPLIANCE
    STATUS      current
    DESCRIPTION
        "The compliance statement for the implementation."

    MODULE      -- this module

    MANDATORY-GROUPS { cie1000DhcpSnoopingConfigGlobalsInfoGroup,
                       cie1000DhcpSnoopingConfigInterfaceInfoGroup,
                       cie1000DhcpSnoopingStatusAssignedIpTableInfoGroup,
                       cie1000DhcpSnoopingControlInterfaceClearStatisticsTableInfoGroup,
                       cie1000DhcpSnoopingStatisticsInterfaceTableInfoGroup }

    ::= { cie1000DhcpSnoopingMibCompliances 1 }

END
