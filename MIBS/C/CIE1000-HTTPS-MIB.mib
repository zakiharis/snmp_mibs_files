-- *****************************************************************
-- HTTPS-MIB:  Cisco private MIB
-- ****************************************************************

CIE1000-HTTPS-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    TruthValue FROM SNMPv2-TC
    ;

cie1000HttpsMib MODULE-IDENTITY
    LAST-UPDATED "201410100000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of HTTPS"
    REVISION    "201410100000Z"
    DESCRIPTION
        "Editorial changes"
    REVISION    "201407010000Z"
    DESCRIPTION
        "Initial version"
    ::= { cie1000SwitchMgmt 47 }


cie1000HttpsMibObjects OBJECT IDENTIFIER
    ::= { cie1000HttpsMib 1 }

cie1000HttpsConfig OBJECT IDENTIFIER
    ::= { cie1000HttpsMibObjects 2 }

cie1000HttpsConfigGlobals OBJECT IDENTIFIER
    ::= { cie1000HttpsConfig 1 }

cie1000HttpsConfigGlobalsMode OBJECT-TYPE
    SYNTAX      TruthValue
    MAX-ACCESS  read-write
    STATUS      current
    DESCRIPTION
        "Global mode of HTTPS. true is to enable the functions of HTTPS and
         false is to disable it."
    ::= { cie1000HttpsConfigGlobals 1 }

cie1000HttpsConfigGlobalsRedirectToHttps OBJECT-TYPE
    SYNTAX      TruthValue
    MAX-ACCESS  read-write
    STATUS      current
    DESCRIPTION
        "The flag is to enable/disable the automatic redirection from HTTP to
         HTTPS. true is to enable the redirection and false is to disable the
         redirection."
    ::= { cie1000HttpsConfigGlobals 2 }

cie1000HttpsMibConformance OBJECT IDENTIFIER
    ::= { cie1000HttpsMib 2 }

cie1000HttpsMibCompliances OBJECT IDENTIFIER
    ::= { cie1000HttpsMibConformance 1 }

cie1000HttpsMibGroups OBJECT IDENTIFIER
    ::= { cie1000HttpsMibConformance 2 }

cie1000HttpsConfigGlobalsInfoGroup OBJECT-GROUP
    OBJECTS     { cie1000HttpsConfigGlobalsMode,
                  cie1000HttpsConfigGlobalsRedirectToHttps }
    STATUS      current
    DESCRIPTION
        "A collection of objects."
    ::= { cie1000HttpsMibGroups 1 }

cie1000HttpsMibCompliance MODULE-COMPLIANCE
    STATUS      current
    DESCRIPTION
        "The compliance statement for the implementation."

    MODULE      -- this module

    MANDATORY-GROUPS { cie1000HttpsConfigGlobalsInfoGroup }

    ::= { cie1000HttpsMibCompliances 1 }

END
