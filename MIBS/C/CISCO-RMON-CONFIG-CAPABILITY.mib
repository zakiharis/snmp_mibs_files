-- *****************************************************************
-- CISCO-RMON-CONFIG-CAPABILITY.my:
-- Cisco CISCO-RMON-CONFIG-MIB AGENT-CAPABILITIES
--   
-- March 2004, Liwei Wang
--   
-- Copyright (c) 2004-2006, 2008 by Cisco Systems Inc.
-- All rights reserved.
-- ****************************************************************

CISCO-RMON-CONFIG-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoRmonConfigCapability MODULE-IDENTITY
    LAST-UPDATED    "200810280000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of CISCO-RMON-CONFIG-MIB."
    REVISION        "200810280000Z"
    DESCRIPTION
        "Added capability statement
        crcCapV12R0233SXIPCat6K."
    REVISION        "200805090000Z"
    DESCRIPTION
        "Added capability statement
        ciscoRmonConfigCapDCOS."
    REVISION        "200706280000Z"
    DESCRIPTION
        "Added capability statement
        crcCapV12R0233SXHPCat6k."
    REVISION        "200601180000Z"
    DESCRIPTION
        "Added capability statements
        crcCapV12R0218SXDPCat6k and
        crcCapV12R0218SXEPCat6k."
    REVISION        "200508241000Z"
    DESCRIPTION
        "Added capability statement
        ciscoRmonConfigCapCatOSV08R0501."
    REVISION        "200403300000Z"
    DESCRIPTION
        "Initial version of this MIB module."
    ::= { ciscoAgentCapability 346 }



ciscoRmonConfigCapV12R0111ECat6K AGENT-CAPABILITIES
    PRODUCT-RELEASE "Cisco IOS 12.1(11E) on Catalyst 6000/6500
                         and Cisco 7600 series devices."
    STATUS          current
    DESCRIPTION
        "CISCO-RMON-CONFIG-MIB capabilities."

    SUPPORTS        CISCO-RMON-CONFIG-MIB
    INCLUDES        {
                        smonExtensionsGroup,
                        smonExtensions2Group,
                        smonExtensions3Group,
                        smonExtensions4Group,
                        smonExtensions5Group,
                        smonExtensions6Group,
                        smonExtensions7Group
                    }
    VARIATION       portCopyReflectorPort
    ACCESS          not-implemented
    DESCRIPTION
        "Information not available on Cat6k."

    VARIATION       portCopySessionType
    SYNTAX          INTEGER  {
                        notSpecified(1),
                        local(2),
                        remoteSource(3),
                        remoteDestination(4)
                    }
    DESCRIPTION
        "Only limited set of enumerated values
        are supported."

    ::= { ciscoRmonConfigCapability 1 }

ciscoRmonConfigCapCatOSV6R0301 AGENT-CAPABILITIES
    PRODUCT-RELEASE "Cisco CatOS 6.3(1)."
    STATUS          current
    DESCRIPTION
        "CISCO-RMON-CONFIG-MIB capabilities."

    SUPPORTS        CISCO-RMON-CONFIG-MIB
    INCLUDES        {
                        smonExtensionsGroup,
                        smonExtensions3Group,
                        smonExtensions4Group,
                        smonExtensions5Group
                    }
    VARIATION       portCopySessionType
    SYNTAX          INTEGER  {
                        notSpecified(1),
                        local(2),
                        remoteSource(3),
                        remoteDestination(4)
                    }
    DESCRIPTION
        "Only limited set of enumerated values
        are supported."

    ::= { ciscoRmonConfigCapability 2 }

ciscoRmonConfigCapCatOSV08R0501 AGENT-CAPABILITIES
    PRODUCT-RELEASE "Cisco CatOS 8.5(1)."
    STATUS          current
    DESCRIPTION
        "CISCO-RMON-CONFIG-MIB capabilities."

    SUPPORTS        CISCO-RMON-CONFIG-MIB
    INCLUDES        {
                        smonExtensionsGroup,
                        smonExtensions3Group,
                        smonExtensions4Group,
                        smonExtensions5Group,
                        crcSpanDstPermitListGroup
                    }
    ::= { ciscoRmonConfigCapability 3 }

crcCapV12R0218SXDPCat6k AGENT-CAPABILITIES
    PRODUCT-RELEASE "Cisco IOS 12.2(18)SXD on Catalyst 6000/6500
                         and Cisco 7600 series devices."
    STATUS          current
    DESCRIPTION
        "CISCO-RMON-CONFIG-MIB capabilities."

    SUPPORTS        CISCO-RMON-CONFIG-MIB
    INCLUDES        {
                        smonExtensionsGroup,
                        smonExtensions2Group,
                        smonExtensions3Group,
                        smonExtensions4Group,
                        smonExtensions5Group,
                        smonExtensions6Group,
                        smonExtensions7Group,
                        crcSpanSessionGroup,
                        crcERSpanSessionGroup,
                        crcERSpanIFGroup
                    }
    VARIATION       portCopyReflectorPort
    ACCESS          not-implemented
    DESCRIPTION
        "Information not available on Cat6k."

    VARIATION       portCopySessionType
    SYNTAX          INTEGER  {
                        notSpecified(1),
                        local(2),
                        remoteSource(3),
                        remoteDestination(4)
                    }
    DESCRIPTION
        "Only limited set of enumerated values
        are supported."

    VARIATION       crcSpanSessionEnabled
    DESCRIPTION
        "Modification may not be allowed for SPAN sessions
        that do not support session enable and disable."

    VARIATION       crcERSpanEncapID
    SYNTAX          Unsigned32  (0..1023) 
    DESCRIPTION     "Only limited set of values is supported."

    VARIATION       crcERSpanSessionDescr
    DESCRIPTION
        "Modification may not be allowed for SPAN sessions
        that do not support ERSPAN session description."

    VARIATION       crcERSpanIpType
    SYNTAX          INTEGER  { ipv4(1) }
    DESCRIPTION
        "Only limited set of enumerated values is supported."

    VARIATION       crcSrcERSpanOrigIpType
    SYNTAX          INTEGER  { ipv4(1) }
    DESCRIPTION
        "Only limited set of enumerated values is supported."

    ::= { ciscoRmonConfigCapability 4 }

crcCapV12R0218SXEPCat6k AGENT-CAPABILITIES
    PRODUCT-RELEASE "Cisco IOS 12.2(18)SXE on Catalyst 6000/6500
                         and Cisco 7600 series devices."
    STATUS          current
    DESCRIPTION
        "CISCO-RMON-CONFIG-MIB capabilities."

    SUPPORTS        CISCO-RMON-CONFIG-MIB
    INCLUDES        {
                        smonExtensionsGroup,
                        smonExtensions2Group,
                        smonExtensions3Group,
                        smonExtensions4Group,
                        smonExtensions5Group,
                        smonExtensions6Group,
                        smonExtensions7Group,
                        crcSpanSessionGroup,
                        crcERSpanSessionGroup,
                        crcERSpanIFGroup,
                        crcSpanDstPermitListGroup
                    }

    VARIATION       portCopyReflectorPort
    ACCESS          not-implemented
    DESCRIPTION
        "Information not available on Cat6k."

    VARIATION       portCopySessionType
    SYNTAX          INTEGER  {
                        notSpecified(1),
                        local(2),
                        remoteSource(3),
                        remoteDestination(4)
                    }
    DESCRIPTION
        "Only limited set of enumerated values
        are supported."

    VARIATION       crcSpanSessionEnabled
    DESCRIPTION
        "Modification may not be allowed for SPAN sessions
        without such capability."

    VARIATION       crcERSpanEncapID
    SYNTAX          Unsigned32  (0..1023) 
    DESCRIPTION     "Only limited set of values is supported."

    VARIATION       crcERSpanSessionDescr
    DESCRIPTION
        "Modification may not be allowed for SPAN sessions
        without such capability."

    VARIATION       crcERSpanIpType
    SYNTAX          INTEGER  { ipv4(1) } 
    DESCRIPTION
        "Only limited set of enumerated values is supported."

    VARIATION       crcSrcERSpanOrigIpType
    SYNTAX          INTEGER  { ipv4(1) } 
    DESCRIPTION
        "Only limited set of enumerated values is supported."

    ::= { ciscoRmonConfigCapability 5 }

crcCapV12R0233SXHPCat6k AGENT-CAPABILITIES
    PRODUCT-RELEASE "Cisco IOS 12.2(33)SXH on Catalyst 6000/6500
                         series devices."
    STATUS          current
    DESCRIPTION
        "CISCO-RMON-CONFIG-MIB capabilities."

    SUPPORTS        CISCO-RMON-CONFIG-MIB
    INCLUDES        {
                        smonExtensionsGroup,
                        smonExtensions2Group,
                        smonExtensions3Group,
                        smonExtensions4Group,
                        smonExtensions5Group,
                        smonExtensions6Group,
                        smonExtensions7Group,
                        crcSpanSessionGroup,
                        crcERSpanSessionGroupRev1,
                        crcERSpanIFGroup,
                        crcSpanDstPermitListGroup,
                        smonExtensions9Group,
                        crcERSpanIFOptionGroup,
                        crcSpanEgressReplicationGroup
                    }

    VARIATION       portCopyOption
    SYNTAX          BITS {
                          inpkts(0),
                          learningDisable(1)
                    }
    DESCRIPTION
        "Only limited set of enumerated values is supported."

    VARIATION       portCopyReflectorPort
    ACCESS          not-implemented
    DESCRIPTION
        "Information not available on Cat6k."

    VARIATION       crcSpanSessionEnabled
    DESCRIPTION
        "Modification may not be allowed for SPAN sessions
        without such capability."

    VARIATION       crcERSpanEncapID
    SYNTAX          Unsigned32  (0..1023) 
    DESCRIPTION     "Only limited set of values is supported."

    VARIATION       crcERSpanSessionDescr
    DESCRIPTION
        "Modification may not be allowed for SPAN sessions without
        such capability."

    VARIATION       crcERSpanIpType
    SYNTAX          INTEGER  { ipv4(1) } 
    DESCRIPTION
        "Only limited set of enumerated values is supported."

    VARIATION       crcSrcERSpanOrigIpType
    SYNTAX          INTEGER  { ipv4(1) } 
    DESCRIPTION
        "Only limited set of enumerated values is supported."

    ::= { ciscoRmonConfigCapability 6 }

ciscoRmonConfigCapSanOSV34R1 AGENT-CAPABILITIES
    PRODUCT-RELEASE "Cisco SanOS 3.4(1) on MDS9000 Storage Switches."
    STATUS          current
    DESCRIPTION
        "CISCO-RMON-CONFIG-MIB capabilities."

    SUPPORTS        CISCO-RMON-CONFIG-MIB
    INCLUDES        { rmonAlarmConfigGroup }
    VARIATION       rmonMaxAlarms
    ACCESS          read-only
    DESCRIPTION
        "write access is not supported."

    ::= { ciscoRmonConfigCapability 7 }

crcCapV12R0233SXIPCat6K AGENT-CAPABILITIES
    PRODUCT-RELEASE "Cisco IOS 12.2(33)SXI on Catalyst 6000/6500
                    series devices."
    STATUS          current
    DESCRIPTION     
        "CISCO-RMON-CONFIG-MIB capabilities."

    SUPPORTS        CISCO-RMON-CONFIG-MIB
    INCLUDES        {
                        smonExtensionsGroup,
                        smonExtensions2Group,
                        smonExtensions3Group,
                        smonExtensions4Group,
                        smonExtensions5Group,
                        smonExtensions6Group,
                        smonExtensions7Group,
                        crcSpanSessionGroup,
                        crcERSpanSessionGroupRev1,
                        crcERSpanIFGroup,
                        crcSpanDstPermitListGroup,
                        smonExtensions9Group,
                        crcERSpanIFOptionGroup,
                        crcSpanEgressReplicationGroup,
                        crcSpanCapacityGroup
                    }

    VARIATION       portCopyOption
    SYNTAX          BITS {
                          inpkts(0),
                          learningDisable(1)
                    }
    DESCRIPTION
        "Only limited set of enumerated values is supported."

    VARIATION       portCopyReflectorPort
    ACCESS          not-implemented
    DESCRIPTION
        "Information not available on Cat6k."

    VARIATION       portCopySessionType
    SYNTAX          INTEGER  {
                          notSpecified(1),
                          local(2),
                          remoteSource(3),
                          remoteDestination(4)
                    }
    DESCRIPTION
        "Only limited set of enumerated values are supported."

    VARIATION       crcSpanSessionEnabled
    DESCRIPTION
        "Modification may not be allowed for SPAN sessions without
        such capability."

    VARIATION       crcERSpanEncapID 
    SYNTAX          Unsigned32  (0..1023) 
    DESCRIPTION     "Only limited set of values is supported."

    VARIATION       crcERSpanSessionDescr
    DESCRIPTION
        "Modification may not be allowed for SPAN sessions without
        such capability."

    VARIATION       crcERSpanIpType 
    SYNTAX          INTEGER  { ipv4(1) } 
    DESCRIPTION
        "Only limited set of enumerated values is supported."

    VARIATION       crcSrcERSpanOrigIpType 
    SYNTAX          INTEGER  { ipv4(1) } 
    DESCRIPTION
        "Only limited set of enumerated values is supported."

    ::= { ciscoRmonConfigCapability 8 }

END
