-- *****************************************************************
-- CISCO-VOIP-TAP-CAPABILITY.my:
-- Cisco CISCO-VOIP-TAP-MIB AGENT-CAPABILITIES
--   
-- July 2010, Shekhar Acharya
--   
-- Copyright (c) 2010 by Cisco Systems, Inc.
-- All rights reserved.
-- *****************************************************************

CISCO-VOIP-TAP-CAPABILITY DEFINITIONS ::= BEGIN

IMPORTS
    MODULE-IDENTITY
        FROM SNMPv2-SMI
    AGENT-CAPABILITIES
        FROM SNMPv2-CONF
    ciscoAgentCapability
        FROM CISCO-SMI;


ciscoVoipTapCapability MODULE-IDENTITY
    LAST-UPDATED    "201008240000Z"
    ORGANIZATION    "Cisco Systems, Inc."
    CONTACT-INFO
            "Cisco Systems
            Customer Service

            Postal: 170 West Tasman Drive
            San Jose, CA  95134
            USA

            Tel: +1 800 553-NETS

            E-mail: cs-li@cisco.com"
    DESCRIPTION
        "The capabilities description of CISCO-VOIP-TAP-MIB."
    REVISION        "201008240000Z"
    DESCRIPTION
        "Initial version of this MIB module."
    ::= { ciscoAgentCapability 593 }



ciscoVoipTapCapV15R01SXE31ASR1K AGENT-CAPABILITIES
    PRODUCT-RELEASE "Cisco IOS XE 15.0(01)SXE31 on ASR 1000 
                     series devices."
    STATUS          current
    DESCRIPTION
        "CISCO-VOIP-TAP-MIB capabilities."

    SUPPORTS        CISCO-VOIP-TAP-MIB
    INCLUDES        { ciscoVoIpTapStreamGroup }
    ::= { ciscoVoipTapCapability 1 }

END
