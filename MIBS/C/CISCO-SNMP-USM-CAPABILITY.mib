-- *****************************************************************
-- CISCO-SNMP-USM-CAPABILITY.my:
-- Cisco SNMP-USER-BASED-SM-MIB AGENT-CAPABILITIES
--   
-- August 2003, Binh Le
--   
-- Copyright (c) 2003, 2006, 2008 by Cisco Systems Inc.
-- All rights reserved.
-- *****************************************************************

CISCO-SNMP-USM-CAPABILITY DEFINITIONS ::= BEGIN

IMPORTS
    MODULE-IDENTITY
        FROM SNMPv2-SMI
    AGENT-CAPABILITIES
        FROM SNMPv2-CONF
    ciscoAgentCapability
        FROM CISCO-SMI;


ciscoSnmpUsmCapability MODULE-IDENTITY
    LAST-UPDATED    "200808010000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com, cs-snmp@cisco.com"
    DESCRIPTION
        "The capabilities description of SNMP-USER-BASED-SM-MIB."
    REVISION        "200808010000Z"
    DESCRIPTION
        "Added the correct mib name under the
        SUPPORTS clause for ciscoSnmpUsmCapCatOSV05R0501
        and ciscoSnmpUsmCapACSWV03R000.
        Added terminating quotes for 
        ciscoSnmpUsmCapACSWV03R000 PRODUCT-RELEASE clause.
        Added capability statement 
        ciscoSnmpUsmCapc4710aceVA1R700 for ACE 4710 Application
        Control Engine Appliance."
    REVISION        "200605220000Z"
    DESCRIPTION
        "Added capability statement
        ciscoSnmpUsmCapACSWV03R000 for 
        Application Control Engine (ACE)."
    REVISION        "200308260000Z"
    DESCRIPTION
        "Initial version of this MIB module."
    ::= { ciscoAgentCapability 323 }



ciscoSnmpUsmCapCatOSV05R0501 AGENT-CAPABILITIES
    PRODUCT-RELEASE "Cisco CatOS 5.5(1)."
    STATUS          current
    DESCRIPTION
        "SNMP-USER-BASED-SM-MIB capabilities."

    SUPPORTS        SNMP-USER-BASED-SM-MIB
    INCLUDES        { usmMIBBasicGroup }
    VARIATION       usmUserStorageType
    SYNTAX          INTEGER  {
                        volatile(2),
                        nonVolatile(3)
                    }
    DESCRIPTION
        "Only support volatile(2) and nonVolatile(3)."

    ::= { ciscoSnmpUsmCapability 1 }

ciscoSnmpUsmCapACSWV03R000 AGENT-CAPABILITIES
    PRODUCT-RELEASE "ACSW (Application Control Software) 3.0"
    STATUS          current
    DESCRIPTION
        "SNMP-USER-BASED-SM-MIB capabilities."

    SUPPORTS        SNMP-USER-BASED-SM-MIB
    INCLUDES        { usmMIBBasicGroup }
    VARIATION       usmUserSpinLock
    ACCESS          not-implemented
    DESCRIPTION
        "Not implemented as usmUserTable for the
        current implementation of the MIB has
        read-only support."

    VARIATION       usmUserCloneFrom
    ACCESS          read-only
    DESCRIPTION
        "Create operation not allowed via SNMP."

    VARIATION       usmUserAuthProtocol
    ACCESS          read-only
    DESCRIPTION
        "Create operation not allowed via SNMP."

    VARIATION       usmUserAuthKeyChange
    ACCESS          read-only
    DESCRIPTION
        "Create operation not allowed via SNMP."

    VARIATION       usmUserOwnAuthKeyChange
    ACCESS          read-only
    DESCRIPTION
        "Create operation not allowed via SNMP."

    VARIATION       usmUserPrivProtocol
    ACCESS          read-only
    DESCRIPTION
        "Create operation not allowed via SNMP."

    VARIATION       usmUserPrivKeyChange
    ACCESS          read-only
    DESCRIPTION
        "Create operation not allowed via SNMP."

    VARIATION       usmUserOwnPrivKeyChange
    ACCESS          read-only
    DESCRIPTION
        "Create operation not allowed via SNMP."

    ::= { ciscoSnmpUsmCapability 2 }

ciscoSnmpUsmCapc4710aceVA1R700 AGENT-CAPABILITIES
    PRODUCT-RELEASE "ACSW (Application Control Software) A1(7)
                    for ACE 4710 Application Control Engine 
                    Appliance."
    STATUS          current
    DESCRIPTION
        "SNMP-USER-BASED-SM-MIB capabilities."

    SUPPORTS        SNMP-USER-BASED-SM-MIB
    INCLUDES        { usmMIBBasicGroup }
    VARIATION       usmUserSpinLock
    ACCESS          not-implemented
    DESCRIPTION
        "Not implemented as usmUserTable for the
        current implementation of the MIB has
        read-only support."

    VARIATION       usmUserCloneFrom
    ACCESS          read-only
    DESCRIPTION
        "Create operation not allowed via SNMP."

    VARIATION       usmUserAuthProtocol
    ACCESS          read-only
    DESCRIPTION
        "Create operation not allowed via SNMP."

    VARIATION       usmUserAuthKeyChange
    ACCESS          read-only
    DESCRIPTION
        "Create operation not allowed via SNMP."

    VARIATION       usmUserOwnAuthKeyChange
    ACCESS          read-only
    DESCRIPTION
        "Create operation not allowed via SNMP."

    VARIATION       usmUserPrivProtocol
    ACCESS          read-only
    DESCRIPTION
        "Create operation not allowed via SNMP."

    VARIATION       usmUserPrivKeyChange
    ACCESS          read-only
    DESCRIPTION
        "Create operation not allowed via SNMP."

    VARIATION       usmUserOwnPrivKeyChange
    ACCESS          read-only
    DESCRIPTION
        "Create operation not allowed via SNMP."

    ::= { ciscoSnmpUsmCapability 3 }

END
