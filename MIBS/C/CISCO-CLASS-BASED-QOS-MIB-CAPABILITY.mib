-- *****************************************************************
-- CISCO-CLASS-BASED-QOS-MIB-CAPABILITY.my:
-- Cisco CISCO-CLASS-BASED-QOS-MIB AGENT-CAPABILITIES
--   
-- April 2000,2001 Anders Fung
--   
-- Copyright (c) 2000-2007 by cisco Systems Inc.
-- All rights reserved.
--   
-- ****************************************************************

CISCO-CLASS-BASED-QOS-MIB-CAPABILITY DEFINITIONS ::= BEGIN

IMPORTS
    MODULE-IDENTITY
        FROM SNMPv2-SMI
    AGENT-CAPABILITIES
        FROM SNMPv2-CONF
    ciscoAgentCapability
        FROM CISCO-SMI;


ciscoCBQosMibCapability MODULE-IDENTITY
    LAST-UPDATED    "200707170000Z"
    ORGANIZATION    "Cisco Systems, Inc."
    CONTACT-INFO
            "Cisco Systems
            Customer Service

            Postal: 170 West Tasman Drive
            San Jose, CA  95134
            USA

            Tel: +1 800 553-NETS

            E-mail: cs-qos@cisco.com"
    DESCRIPTION
        "Agent capabilities for CISCO-CLASS-BASED-QOS-MIB."
    REVISION        "200707170000Z"
    DESCRIPTION
        "Added capability statements: 
         ciscoCBQosMibCapV12R0218SXFPCat6KPfc2,
         ciscoCBQosMibCapV12R0218SXFPCat6KPfc3 and
         ciscoCBQosMibCapV12R0233SXHPCat6K."
    REVISION        "200611080000Z"
    DESCRIPTION
        "Added agent capabilities for
        Cisco IOS XR 3.4 on CRS-1
        platform"
    REVISION        "200506220000Z"
    DESCRIPTION
        "Added agent capabilities for
        Cisco IOS XR 3.2.0 on CRS-1
        platform"
    REVISION        "200409010000Z"
    DESCRIPTION
        "Added agent capabilities for 12.0(29)S.
        Added agent capabilities for 
        12.2(RLS7)S."
    REVISION        "200301240000Z"
    DESCRIPTION
        "Added agent capabilities for
        Catalyst 8540MSR platform."
    REVISION        "200106130000Z"
    DESCRIPTION
        "Added agent capabilities for Mainline.
        Modified capabilities for T train."
    REVISION        "200012010000Z"
    DESCRIPTION
        "Added agent capabilities for T train."
    REVISION        "200007130000Z"
    DESCRIPTION
        "The capabilities description of
        Cisco Class Based QoS MIB."
    ::= { ciscoAgentCapability 525 }



ciscoCBQosMibCapabilityV121R02E7500 AGENT-CAPABILITIES
    PRODUCT-RELEASE "Cisco IOS 12.1(2)E on 7500."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroup,
                        cbQosREDCfgGroup,
                        cbQosREDClassCfgGroup,
                        cbQosPoliceCfgGroup,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup
                    }
    ::= { ciscoCBQosMibCapability 1 }

ciscoCBQosMibCapabilityV120R12S7500 AGENT-CAPABILITIES
    PRODUCT-RELEASE "Cisco IOS 12.0(12)S on 7500."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroup,
                        cbQosREDCfgGroup,
                        cbQosREDClassCfgGroup,
                        cbQosPoliceCfgGroup,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosREDClassXmitCountersGroup
                    }
    ::= { ciscoCBQosMibCapability 2 }

ciscoCBQosMibCapabilityV121R05T7200 AGENT-CAPABILITIES
    PRODUCT-RELEASE "Cisco IOS 12.1(5)T for 7200/lower-end platforms."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroup,
                        cbQosREDCfgGroup,
                        cbQosREDClassCfgGroup,
                        cbQosPoliceCfgGroup,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup
                    }
    VARIATION       cbQosQueueingCfgBandwidthUnits
    DESCRIPTION
        "percentageRemaining not supported."

    VARIATION       cbQosSetCfgFeature
    DESCRIPTION
        "AtmClpBit, FrDeBit and L2Cos not supported."

    ::= { ciscoCBQosMibCapability 3 }

ciscoCBQosMibCapabilityV122R01T7200 AGENT-CAPABILITIES
    PRODUCT-RELEASE "Cisco IOS 12.2(2)T on 7200 and lower-end platforms."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroup,
                        cbQosREDCfgGroup,
                        cbQosREDClassCfgGroup,
                        cbQosPoliceCfgGroup,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup,
                        cbQosNewSetCfgGroup
                    }
    ::= { ciscoCBQosMibCapability 4 }

ciscoCBQosMibCapabilityV123R01T AGENT-CAPABILITIES
    PRODUCT-RELEASE "Cisco IOS 12.3(1)T on 7500, 7200 and 
                 lower-end platforms."
    STATUS          current
    DESCRIPTION
        "Class-Based QoS MIB  capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosREDClassCfgGroupRev1,
                        cbQosPoliceCfgGroupRev1,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup,
                        cbQosNewSetCfgGroup,
                        cbQosPoliceActionCfgGroup,
                        cbQosAFPoliceViolateCfgGroup,
                        cbQosREDECNCfgGroup,
                        cbQosREDClassECNMarkCountersGroup
                    }
    ::= { ciscoCBQosMibCapability 5 }

ciscoCBQosMibCapabilityV121R14EB AGENT-CAPABILITIES
    PRODUCT-RELEASE "Cisco IOS 12.1(14)EB on Catalyst 8540MSR platform."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroup,
                        cbQosPoliceCfgGroup,
                        cbQosSetCfgGroup
                    }
    ::= { ciscoCBQosMibCapability 6 }

ciscoCBQosMibCapabilityV12R0306T AGENT-CAPABILITIES
    PRODUCT-RELEASE "Cisco IOS 12.3(6)T on 7200 and 
                 lower-end platforms."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroupRev1,
                        cbQosREDCfgGroupRev1,
                        cbQosREDClassCfgGroupRev1,
                        cbQosPoliceCfgGroupRev1,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup,
                        cbQosNewSetCfgGroup,
                        cbQosPoliceActionCfgGroup,
                        cbQosAFPoliceViolateCfgGroup,
                        cbQosREDECNCfgGroup,
                        cbQosREDClassECNMarkCountersGroup,
                        cbQosEBCfgGroup,
                        cbQosEBStatsGroup
                    }
    ::= { ciscoCBQosMibCapability 7 }

ciscoCBQosMibCapabilityV12R02S AGENT-CAPABILITIES
    PRODUCT-RELEASE "Cisco IOS 12.2S for 7500/7200/lower-end platforms."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroupRev1,
                        cbQosREDCfgGroupRev1,
                        cbQosREDClassCfgGroupRev1,
                        cbQosPoliceCfgGroupRev1,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup,
                        cbQosNewSetCfgGroup,
                        cbQosPoliceActionCfgGroup,
                        cbQosAFPoliceViolateCfgGroup,
                        cbQosREDECNCfgGroup,
                        cbQosREDClassECNMarkCountersGroup
                    }
    ::= { ciscoCBQosMibCapability 8 }

ciscoCBQosMibCapabilityV12R00S AGENT-CAPABILITIES
    PRODUCT-RELEASE "Cisco IOS 12.0S for 7500/7200/lower-end platforms."
    STATUS          current
    DESCRIPTION
        "Class-Based QoS MIB capabilities."

    SUPPORTS        CISCO-CLASS-BASED-QOS-MIB
    INCLUDES        {
                        cbQosServicePolicyGroup,
                        cbQosObjectsGroup,
                        cbQosPolicyMapCfgGroup,
                        cbQosClassMapCfgGroup,
                        cbQosMatchStmtCfgGroup,
                        cbQosQueueingCfgGroupRev1,
                        cbQosREDCfgGroupRev1,
                        cbQosREDClassCfgGroupRev1,
                        cbQosPoliceCfgGroupRev1,
                        cbQosTSCfgGroup,
                        cbQosSetCfgGroup,
                        cbQosClassMapStatsGroup,
                        cbQosMatchStmtStatsGroup,
                        cbQosPoliceStatsGroup,
                        cbQosQueueingStatsGroup,
                        cbQosTSStatsGroup,
                        cbQosREDClassStatsGroup,
                        cbQosAFPoliceCfgGroup,
                        cbQosAFPoliceStatsGroup,
                        cbQosREDDscpCfgGroup,
                        cbQosNewSetCfgGroup,
                        cbQosPoliceActionCfgGroup,
                        cbQosAFPoliceViolateCfgGroup,
                        cbQosREDECNCfgGroup,
                        cbQosREDClassECNMarkCountersGroup
                    }
    ::= { ciscoCBQosMibCapability 9 }

ciscoCBQosMibCapabilityV320CRS1 AGENT-CAPABILITIES
    PRODUCT-RELEASE "Cisco IOS XR 3.2.0 on CRS-1"
    STATUS          current
    DESCRIPTION
        "Class-Based QoS MIB capabilities."

    SUPPORTS        CISCO-CLASS-BASED-QOS-MIB
    INCLUDES        {
                        cbQosServicePolicyGroupRev1,
                        cbQosObjectsGroup,
                        cbQosPolicyMapCfgGroup,
                        cbQosClassMapCfgGroup,
                        cbQosMatchStmtCfgGroup,
                        cbQosQueueingCfgGroupRev1,
                        cbQosREDClassCfgGroupRev1,
                        cbQosPoliceCfgGroupRev1,
                        cbQosTSCfgGroup,
                        cbQosSetCfgGroupRev1,
                        cbQosPoliceStatsGroup,
                        cbQosQueueingStatsGroup,
                        cbQosTSStatsGroup,
                        cbQosREDClassStatsGroup,
                        cbQosAFPoliceStatsGroup,
                        cbQosREDDscpCfgGroup,
                        cbQosNewSetCfgGroup,
                        cbQosPoliceActionCfgGroup,
                        cbQosAFPoliceViolateCfgGroup,
                        cbQosPoliceCfgExtGroup,
                        cbQosREDClassXmitCountersGroup
                    }
    VARIATION       cbQosEntityIndex
    ACCESS          not-implemented
    DESCRIPTION
        "Not applicable for the platform"

    VARIATION       cbQosIfType
    ACCESS          not-implemented
    DESCRIPTION
        "This object is not supported by the platform"

    VARIATION       cbQosFrDLCI
    ACCESS          not-implemented
    DESCRIPTION
        "Not applicable for the platform"

    VARIATION       cbQosAtmVPI
    ACCESS          not-implemented
    DESCRIPTION
        "Not applicable for the platform"

    VARIATION       cbQosAtmVCI
    ACCESS          not-implemented
    DESCRIPTION
        "Not applicable for the platform."

    VARIATION       cbQosInterfacePolicyTable
    ACCESS          not-implemented
    DESCRIPTION
        "Not applicable for the platform."

    VARIATION       cbQosFrameRelayPolicyTable
    ACCESS          not-implemented
    DESCRIPTION
        "Not applicable for the platform."

    VARIATION       cbQosATMPVCPolicyTable
    ACCESS          not-implemented
    DESCRIPTION
        "Not applicable for the platform."

    VARIATION       cbQosQueueingCfgFlowEnabled
    ACCESS          not-implemented
    DESCRIPTION
        "Not applicable for the platform."

    VARIATION       cbQosQueueingCfgDynamicQNumber
    ACCESS          not-implemented
    DESCRIPTION
        "Not applicable for the platform."

    VARIATION       cbQosQueueingCfgPrioBurstSize
    ACCESS          not-implemented
    DESCRIPTION
        "Not applicable for the platform."

    VARIATION       cbQosREDCfgExponWeight
    ACCESS          not-implemented
    DESCRIPTION
        "Not applicable for the platform."

    VARIATION       cbQosREDCfgMeanQsize
    ACCESS          not-implemented
    DESCRIPTION
        "Not applicable for the platform."

    VARIATION       cbQosREDCfgECNEnabled
    ACCESS          not-implemented
    DESCRIPTION
        "Not applicable for the platform."

    VARIATION       cbQosREDCfgMinThreshold
    ACCESS          not-implemented
    DESCRIPTION
        "Not applicable for the platform."

    VARIATION       cbQosREDCfgMaxThreshold
    ACCESS          not-implemented
    DESCRIPTION
        "Not applicable for the platform."

    VARIATION       cbQosTSCfgBurstSize
    ACCESS          not-implemented
    DESCRIPTION
        "Not applicable for the platform."

    VARIATION       cbQosTSCfgAdaptiveEnabled
    ACCESS          not-implemented
    DESCRIPTION
        "Not applicable for the platform."

    VARIATION       cbQosTSCfgExtBurstSize
    ACCESS          not-implemented
    DESCRIPTION
        "Not applicable for the platform."

    VARIATION       cbQosTSCfgAdaptiveRate
    ACCESS          not-implemented
    DESCRIPTION
        "Not applicable for the platform."

    VARIATION       cbQosCMStatsTable
    ACCESS          not-implemented
    DESCRIPTION
        "This table is not supported by the platform."

    VARIATION       cbQosMatchStmtStatsTable
    ACCESS          not-implemented
    DESCRIPTION
        "Not applicable for the platform."

    VARIATION       cbQosQueueingCurrentQDepth
    ACCESS          not-implemented
    DESCRIPTION
        "Not applicable for the platform."

    VARIATION       cbQosQueueingMaxQDepth
    ACCESS          not-implemented
    DESCRIPTION
        "Not applicable for the platform."

    VARIATION       cbQosTSStatsDelayedByteOverflow
    ACCESS          not-implemented
    DESCRIPTION
        "Not applicable for the platform."

    VARIATION       cbQosTSStatsDelayedByte
    ACCESS          not-implemented
    DESCRIPTION
        "Not applicable for the platform."

    VARIATION       cbQosTSStatsDelayedByte64
    ACCESS          not-implemented
    DESCRIPTION
        "Not applicable for the platform."

    VARIATION       cbQosTSStatsDelayedPktOverflow
    ACCESS          not-implemented
    DESCRIPTION
        "Not applicable for the platform."

    VARIATION       cbQosTSStatsDelayedPkt
    ACCESS          not-implemented
    DESCRIPTION
        "Not applicable for the platform."

    VARIATION       cbQosTSStatsDelayedPkt64
    ACCESS          not-implemented
    DESCRIPTION
        "Not applicable for the platform."

    VARIATION       cbQosTSStatsActive
    ACCESS          not-implemented
    DESCRIPTION
        "Not applicable for the platform."

    VARIATION       cbQosTSStatsCurrentQSize
    ACCESS          not-implemented
    DESCRIPTION
        "Not applicable for the platform."

    VARIATION       cbQosREDECNMarkPktOverflow
    ACCESS          not-implemented
    DESCRIPTION
        "Not applicable for the platform."

    VARIATION       cbQosREDECNMarkPkt
    ACCESS          not-implemented
    DESCRIPTION
        "Not applicable for the platform."

    VARIATION       cbQosREDECNMarkPkt64
    ACCESS          not-implemented
    DESCRIPTION
        "Not applicable for the platform."

    VARIATION       cbQosREDECNMarkByteOverflow
    ACCESS          not-implemented
    DESCRIPTION
        "Not applicable for the platform."

    VARIATION       cbQosREDECNMarkByte
    ACCESS          not-implemented
    DESCRIPTION
        "Not applicable for the platform."

    VARIATION       cbQosREDECNMarkByte64
    ACCESS          not-implemented
    DESCRIPTION
        "Not applicable for the platform."

    VARIATION       cbQosREDMeanQSizeUnits
    ACCESS          not-implemented
    DESCRIPTION
        "Not applicable for the platform."

    VARIATION       cbQosREDMeanQSize
    ACCESS          not-implemented
    DESCRIPTION
        "Not applicable for the platform."

    ::= { ciscoCBQosMibCapability 10 }

ciscoCBQosMibCapabilityV3R4CRS1 AGENT-CAPABILITIES
    PRODUCT-RELEASE "Cisco IOS XR 3.4 on CRS-1"
    STATUS          current
    DESCRIPTION
        "Class-Based QoS MIB capabilities."

    SUPPORTS        CISCO-CLASS-BASED-QOS-MIB
    INCLUDES        {
                        cbQosServicePolicyGroupRev1,
                        cbQosObjectsGroup,
                        cbQosPolicyMapCfgGroup,
                        cbQosClassMapCfgGroup,
                        cbQosMatchStmtCfgGroup,
                        cbQosQueueingCfgGroupRev1,
                        cbQosREDClassCfgGroupRev1,
                        cbQosPoliceCfgGroupRev1,
                        cbQosTSCfgGroup,
                        cbQosSetCfgGroupRev1,
                        cbQosPoliceStatsGroup,
                        cbQosQueueingStatsGroup,
                        cbQosTSStatsGroup,
                        cbQosREDClassStatsGroup,
                        cbQosAFPoliceStatsGroup,
                        cbQosREDDscpCfgGroup,
                        cbQosNewSetCfgGroup,
                        cbQosPoliceActionCfgGroup,
                        cbQosAFPoliceViolateCfgGroup,
                        cbQosPoliceCfgExtGroup,
                        cbQosREDClassXmitCountersGroup,
                        cbQosClassMapStatsGroup,
                        cbQosInterfacePolicyGroup
                    }
    VARIATION       cbQosEntityIndex
    ACCESS          not-implemented
    DESCRIPTION
        "Not applicable for the platform"

    VARIATION       cbQosFrDLCI
    ACCESS          not-implemented
    DESCRIPTION
        "Not applicable for the platform"

    VARIATION       cbQosQueueingCfgFlowEnabled
    ACCESS          not-implemented
    DESCRIPTION
        "Not applicable for the platform."

    VARIATION       cbQosQueueingCfgDynamicQNumber
    ACCESS          not-implemented
    DESCRIPTION
        "Not applicable for the platform."

    VARIATION       cbQosQueueingCfgPrioBurstSize
    ACCESS          not-implemented
    DESCRIPTION
        "Not applicable for the platform."

    VARIATION       cbQosREDCfgExponWeight
    ACCESS          not-implemented
    DESCRIPTION
        "Not applicable for the platform."

    VARIATION       cbQosREDCfgMeanQsize
    ACCESS          not-implemented
    DESCRIPTION
        "Not applicable for the platform."

    VARIATION       cbQosREDCfgECNEnabled
    ACCESS          not-implemented
    DESCRIPTION
        "Not applicable for the platform."

    VARIATION       cbQosREDCfgMinThreshold
    ACCESS          not-implemented
    DESCRIPTION
        "Not applicable for the platform."

    VARIATION       cbQosREDCfgMaxThreshold
    ACCESS          not-implemented
    DESCRIPTION
        "Not applicable for the platform."

    VARIATION       cbQosTSCfgBurstSize
    ACCESS          not-implemented
    DESCRIPTION
        "Not applicable for the platform."

    VARIATION       cbQosTSCfgAdaptiveEnabled
    ACCESS          not-implemented
    DESCRIPTION
        "Not applicable for the platform."

    VARIATION       cbQosTSCfgExtBurstSize
    ACCESS          not-implemented
    DESCRIPTION
        "Not applicable for the platform."

    VARIATION       cbQosTSCfgAdaptiveRate
    ACCESS          not-implemented
    DESCRIPTION
        "Not applicable for the platform."

    VARIATION       cbQosTSStatsDelayedByteOverflow
    ACCESS          not-implemented
    DESCRIPTION
        "Not applicable for the platform."

    VARIATION       cbQosTSStatsDelayedByte
    ACCESS          not-implemented
    DESCRIPTION
        "Not applicable for the platform."

    VARIATION       cbQosTSStatsDelayedByte64
    ACCESS          not-implemented
    DESCRIPTION
        "Not applicable for the platform."

    VARIATION       cbQosTSStatsDelayedPktOverflow
    ACCESS          not-implemented
    DESCRIPTION
        "Not applicable for the platform."

    VARIATION       cbQosTSStatsDelayedPkt
    ACCESS          not-implemented
    DESCRIPTION
        "Not applicable for the platform."

    VARIATION       cbQosTSStatsDelayedPkt64
    ACCESS          not-implemented
    DESCRIPTION
        "Not applicable for the platform."

    VARIATION       cbQosTSStatsActive
    ACCESS          not-implemented
    DESCRIPTION
        "Not applicable for the platform."

    VARIATION       cbQosTSStatsCurrentQSize
    ACCESS          not-implemented
    DESCRIPTION
        "Not applicable for the platform."

    VARIATION       cbQosREDECNMarkPktOverflow
    ACCESS          not-implemented
    DESCRIPTION
        "Not applicable for the platform."

    VARIATION       cbQosREDECNMarkPkt
    ACCESS          not-implemented
    DESCRIPTION
        "Not applicable for the platform."

    VARIATION       cbQosREDECNMarkPkt64
    ACCESS          not-implemented
    DESCRIPTION
        "Not applicable for the platform."

    VARIATION       cbQosREDECNMarkByteOverflow
    ACCESS          not-implemented
    DESCRIPTION
        "Not applicable for the platform."

    VARIATION       cbQosREDECNMarkByte
    ACCESS          not-implemented
    DESCRIPTION
        "Not applicable for the platform."

    VARIATION       cbQosREDECNMarkByte64
    ACCESS          not-implemented
    DESCRIPTION
        "Not applicable for the platform."

    VARIATION       cbQosREDMeanQSizeUnits
    ACCESS          not-implemented
    DESCRIPTION
        "Not applicable for the platform."

    VARIATION       cbQosREDMeanQSize
    ACCESS          not-implemented
    DESCRIPTION
        "Not applicable for the platform."

    ::= { ciscoCBQosMibCapability 11 }

ciscoCBQosMibCapV12R0218SXFPCat6KPfc2 AGENT-CAPABILITIES
    PRODUCT-RELEASE "Cisco IOS 12.2(18)SXF on Catalyst 6000/6500
                     and Cisco 7600 series devices with PFC2 card."
    STATUS          current
    DESCRIPTION
        "Class-Based QoS MIB capabilities."

    SUPPORTS        CISCO-CLASS-BASED-QOS-MIB
    INCLUDES        {
                        cbQosServicePolicyGroupRev1,
                        cbQosObjectsGroup,
                        cbQosPolicyMapCfgGroup,
                        cbQosClassMapCfgGroup,
                        cbQosMatchStmtCfgGroup,
                        cbQosPoliceCfgGroupRev2,
                        cbQosSetCfgGroup,
                        cbQosSetCfgMplsImpositionGroup,
                        cbQosSetCfgDiscardClassGroup,
                        cbQosSetCfgMPLSTopMostGroup,
                        cbQosSetCfgSrpPriorityGroup,
                        cbQosSetCfgFrFecnBecnGroup,
                        cbQosClassMapStatsGroup,
                        cbQosMatchStmtStatsGroup,
                        cbQosPoliceStatsGroup,
                        cbQosAFPoliceCfgGroup,
                        cbQosAFPoliceStatsGroup,
                        cbQosNewSetCfgGroup
                    }

        VARIATION       cbQosPoliceCfgPir 
        ACCESS          not-implemented 
        DESCRIPTION     "Not supported in this platform."

        VARIATION       cbQosCMPrePolicyByteOverflow
        DESCRIPTION     "Always return 0."

        VARIATION       cbQosCMPrePolicyByte 
        DESCRIPTION     "Always return 0."

        VARIATION       cbQosCMPrePolicyByte64 
        DESCRIPTION     "Always return 0."

        VARIATION       cbQosCMDropByteOverflow
        DESCRIPTION     "Always return 0."

        VARIATION       cbQosCMDropByte 
        DESCRIPTION     "Always return 0."

        VARIATION       cbQosCMDropByte64
        DESCRIPTION     "Always return 0."

        VARIATION       cbQosMatchPrePolicyByteOverflow
        DESCRIPTION     "Always return 0."

        VARIATION       cbQosMatchPrePolicyByte 
        DESCRIPTION     "Always return 0."

        VARIATION       cbQosMatchPrePolicyByte64
        DESCRIPTION     "Always return 0."

        VARIATION       cbQosPoliceConformedByteOverflow
        DESCRIPTION     "Always return 0."

        VARIATION       cbQosPoliceConformedByte 
        DESCRIPTION     "Always return 0."

        VARIATION       cbQosPoliceConformedByte64
        DESCRIPTION     "Always return 0."

        VARIATION       cbQosPoliceExceededByteOverflow
        DESCRIPTION     "Always return 0."

        VARIATION       cbQosPoliceExceededByte 
        DESCRIPTION     "Always return 0."

        VARIATION       cbQosPoliceExceededByte64
        DESCRIPTION     "Always return 0."

        VARIATION       cbQosPoliceViolatedByteOverflow
        DESCRIPTION     "Always return 0."

        VARIATION       cbQosPoliceViolatedByte 
        DESCRIPTION     "Always return 0."

        VARIATION       cbQosPoliceViolatedByte64
        DESCRIPTION     "Always return 0."

    ::= { ciscoCBQosMibCapability 12 }

ciscoCBQosMibCapV12R0218SXFPCat6KPfc3 AGENT-CAPABILITIES
    PRODUCT-RELEASE "Cisco IOS 12.2(18)SXF on Catalyst 6000/6500
                     and Cisco 7600 series devices with PFC3 card."
    STATUS          current
    DESCRIPTION
        "Class-Based QoS MIB capabilities."

    SUPPORTS        CISCO-CLASS-BASED-QOS-MIB
    INCLUDES        {
                        cbQosServicePolicyGroupRev1,
                        cbQosObjectsGroup,
                        cbQosPolicyMapCfgGroup,
                        cbQosClassMapCfgGroup,
                        cbQosMatchStmtCfgGroup,
                        cbQosPoliceCfgGroupRev2,
                        cbQosSetCfgGroup,
                        cbQosSetCfgMplsImpositionGroup,
                        cbQosSetCfgDiscardClassGroup,
                        cbQosSetCfgMPLSTopMostGroup,
                        cbQosSetCfgSrpPriorityGroup,
                        cbQosSetCfgFrFecnBecnGroup,
                        cbQosClassMapStatsGroup,
                        cbQosMatchStmtStatsGroup,
                        cbQosPoliceStatsGroup,
                        cbQosAFPoliceCfgGroup,
                        cbQosAFPoliceStatsGroup,
                        cbQosNewSetCfgGroup
                    }

        VARIATION       cbQosPoliceCfgPir 
        ACCESS          not-implemented 
        DESCRIPTION     "Not supported in this platform."

        VARIATION       cbQosCMPrePolicyPktOverflow
        DESCRIPTION     "Always return 0."

        VARIATION       cbQosCMPrePolicyPkt 
        DESCRIPTION     "Always return 0."

        VARIATION       cbQosCMPrePolicyPkt64 
        DESCRIPTION     "Always return 0."

        VARIATION       cbQosCMDropPktOverflow
        DESCRIPTION     "Always return 0."

        VARIATION       cbQosCMDropPkt 
        DESCRIPTION     "Always return 0."

        VARIATION       cbQosCMDropPkt64
        DESCRIPTION     "Always return 0."

        VARIATION       cbQosMatchPrePolicyPktOverflow
        DESCRIPTION     "Always return 0."

        VARIATION       cbQosMatchPrePolicyPkt 
        DESCRIPTION     "Always return 0."

        VARIATION       cbQosMatchPrePolicyPkt64
        DESCRIPTION     "Always return 0."

        VARIATION       cbQosPoliceConformedPktOverflow
        DESCRIPTION     "Always return 0."

        VARIATION       cbQosPoliceConformedPkt 
        DESCRIPTION     "Always return 0."

        VARIATION       cbQosPoliceConformedPkt64
        DESCRIPTION     "Always return 0."

        VARIATION       cbQosPoliceExceededPktOverflow
        DESCRIPTION     "Always return 0."

        VARIATION       cbQosPoliceExceededPkt 
        DESCRIPTION     "Always return 0."

        VARIATION       cbQosPoliceExceededPkt64
        DESCRIPTION     "Always return 0."

        VARIATION       cbQosPoliceViolatedPktOverflow
        DESCRIPTION     "Always return 0."

        VARIATION       cbQosPoliceViolatedPkt 
        DESCRIPTION     "Always return 0."

        VARIATION       cbQosPoliceViolatedPkt64
        DESCRIPTION     "Always return 0."

    ::= { ciscoCBQosMibCapability 13 }

ciscoCBQosMibCapV12R0233SXHPCat6K AGENT-CAPABILITIES
    PRODUCT-RELEASE "Cisco IOS 12.2(33)SXH on Catalyst 6000/6500
                     devices."
    STATUS          current
    DESCRIPTION
        "Class-Based QoS MIB capabilities."

    SUPPORTS        CISCO-CLASS-BASED-QOS-MIB
    INCLUDES        {
                        cbQosServicePolicyGroupRev1,
                        cbQosObjectsGroup,
                        cbQosPolicyMapCfgGroup,
                        cbQosClassMapCfgGroup,
                        cbQosMatchStmtCfgGroup,
                        cbQosPoliceCfgGroupRev2,
                        cbQosPoliceCfgExtGroup,
                        cbQosSetCfgGroup,
                        cbQosSetCfgMplsImpositionGroup,
                        cbQosSetCfgDiscardClassGroup,
                        cbQosSetCfgMPLSTopMostGroup,
                        cbQosSetCfgSrpPriorityGroup,
                        cbQosSetCfgFrFecnBecnGroup,
                        cbQosClassMapStatsGroup,
                        cbQosMatchStmtStatsGroup,
                        cbQosPoliceStatsGroup,
                        cbQosAFPoliceCfgGroup,
                        cbQosAFPoliceStatsGroup,
                        cbQosNewSetCfgGroup
                    }

        VARIATION       cbQosPoliceCfgPir 
        ACCESS          not-implemented 
        DESCRIPTION     "Not supported in this platform."

        VARIATION       cbQosCMPrePolicyPktOverflow
        ACCESS          not-implemented 
        DESCRIPTION     "Not supported in this platform."

        VARIATION       cbQosCMPrePolicyPkt 
        ACCESS          not-implemented 
        DESCRIPTION     "Not supported in this platform."

        VARIATION       cbQosCMPrePolicyPkt64 
        ACCESS          not-implemented 
        DESCRIPTION     "Not supported in this platform."

        VARIATION       cbQosCMDropPktOverflow
        ACCESS          not-implemented 
        DESCRIPTION     "Not supported in this platform."

        VARIATION       cbQosCMDropPkt 
        ACCESS          not-implemented 
        DESCRIPTION     "Not supported in this platform."

        VARIATION       cbQosCMDropPkt64
        ACCESS          not-implemented 
        DESCRIPTION     "Not supported in this platform."

        VARIATION       cbQosMatchPrePolicyPktOverflow
        ACCESS          not-implemented 
        DESCRIPTION     "Not supported in this platform."

        VARIATION       cbQosMatchPrePolicyPkt 
        ACCESS          not-implemented 
        DESCRIPTION     "Not supported in this platform."

        VARIATION       cbQosMatchPrePolicyPkt64
        ACCESS          not-implemented 
        DESCRIPTION     "Not supported in this platform."

        VARIATION       cbQosPoliceConformedPktOverflow
        ACCESS          not-implemented 
        DESCRIPTION     "Not supported in this platform."

        VARIATION       cbQosPoliceConformedPkt 
        ACCESS          not-implemented 
        DESCRIPTION     "Not supported in this platform."

        VARIATION       cbQosPoliceConformedPkt64
        ACCESS          not-implemented 
        DESCRIPTION     "Not supported in this platform."

        VARIATION       cbQosPoliceExceededPktOverflow
        ACCESS          not-implemented 
        DESCRIPTION     "Not supported in this platform."

        VARIATION       cbQosPoliceExceededPkt 
        ACCESS          not-implemented 
        DESCRIPTION     "Not supported in this platform."

        VARIATION       cbQosPoliceExceededPkt64
        ACCESS          not-implemented 
        DESCRIPTION     "Not supported in this platform."

        VARIATION       cbQosPoliceViolatedPktOverflow
        ACCESS          not-implemented 
        DESCRIPTION     "Not supported in this platform."

        VARIATION       cbQosPoliceViolatedPkt 
        ACCESS          not-implemented 
        DESCRIPTION     "Not supported in this platform."

        VARIATION       cbQosPoliceViolatedPkt64
        ACCESS          not-implemented 
        DESCRIPTION     "Not supported in this platform."

    ::= { ciscoCBQosMibCapability 14 }

END
