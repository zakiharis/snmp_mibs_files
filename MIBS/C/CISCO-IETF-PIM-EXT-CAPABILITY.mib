-- *****************************************************************
-- CISCO-IETF-PIM-EXT-CAPABILITY.my: CISCO-IETF-PIM-EXT-MIB 
--                                   AGENT-CAPABILITIES
--
-- June 2005, Gayathri Velayutham.
--
-- Copyright (c) 2005 by cisco Systems, Inc.
-- All rights reserved.
--
-- *****************************************************************

CISCO-IETF-PIM-EXT-CAPABILITY DEFINITIONS ::= BEGIN

IMPORTS
        MODULE-IDENTITY
                FROM SNMPv2-SMI
        AGENT-CAPABILITIES
                FROM SNMPv2-CONF
        ciscoAgentCapability
                FROM CISCO-SMI;   

ciscoIetfPimExtCapability MODULE-IDENTITY
    LAST-UPDATED    "200507270000Z"
    ORGANIZATION    "Cisco Systems, Inc."
    CONTACT-INFO  
        "       Cisco Systems
                Customer Service

               Postal: 170 West Tasman Drive
               San Jose, CA  95134
               USA

               Tel: +1 800 553-NETS

               E-mail: cs-ipmulticast@cisco.com"
    DESCRIPTION
       "The capabilities description of CISCO-IETF-PIM-EXT-MIB"

    REVISION        "200507270000Z"
    DESCRIPTION
       "Initial version of this MIB module."
    ::= {  ciscoAgentCapability 443 }
     
cIetfPimExtCapV320CRS1 AGENT-CAPABILITIES
    PRODUCT-RELEASE "Cisco IOS XR 3.2.0 for CRS-1"
    STATUS          current
    DESCRIPTION     "CISCO-IETF-PIM-EXT-MIB capabilities." 

    SUPPORTS        CISCO-IETF-PIM-EXT-MIB 
     INCLUDES       {       
                     ciscoIetfPimExtGeneralGroup,
                     ciscoIetfPimExtNbrGroup,
                     ciscoIetfPimExtBidirGroup      
                    } 

    VARIATION          cpimExtIfGraftRetryInterval 
     ACCESS            not-implemented
     DESCRIPTION       "Not Supported."

    VARIATION          cpimExtIfMaxGraftRetries 
     ACCESS            not-implemented
     DESCRIPTION       "Not Supported."

    VARIATION          cpimExtIfSRTTLThreshold 
     ACCESS            not-implemented
     DESCRIPTION       "Not Supported."

    VARIATION          cpimExtIfBSRBorder 
     ACCESS            not-implemented
     DESCRIPTION       "Not Supported."

    VARIATION          cpimExtNbrTBit 
     ACCESS            not-implemented
     DESCRIPTION       "Not Supported."

    VARIATION          cpimExtMRouteSourceTimer 
     ACCESS            not-implemented
     DESCRIPTION       "Not Supported."

    VARIATION          cpimExtMRouteOriginatorSRTTL 
     ACCESS            not-implemented
     DESCRIPTION       "Not Supported."

    VARIATION          cpimExtCRPTable 
     ACCESS            not-implemented
     DESCRIPTION       "Not Supported."

    VARIATION          cpimExtSourceLifetime 
     ACCESS            not-implemented
     DESCRIPTION       "Not Supported."

    VARIATION          cpimExtStateRefreshInterval 
     ACCESS            not-implemented
     DESCRIPTION       "Not Supported."

    VARIATION          cpimExtStateRefreshLimitInterval 
     ACCESS            not-implemented
     DESCRIPTION       "Not Supported."

    VARIATION          cpimExtStateRefreshTimeToLive 
     ACCESS            not-implemented
     DESCRIPTION       "Not Supported."

    ::= { ciscoIetfPimExtCapability 1 }

END
