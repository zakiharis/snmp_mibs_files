CYAN-RCM-MIB DEFINITIONS ::= BEGIN
IMPORTS
    MODULE-IDENTITY,
    OBJECT-TYPE,
    Integer32,
    Unsigned32
                    FROM SNMPv2-SMI

    DisplayString
                    FROM SNMPv2-TC

    CyanAdminStateTc,
    CyanOpStateQualTc,
    CyanOpStateTc,
    CyanSecServiceStateTc
                    FROM CYAN-TC-MIB

    CyanTypeTc,
    cyanEntityModules
		    FROM CYAN-MIB

    MODULE-COMPLIANCE, 
    OBJECT-GROUP
	            FROM SNMPv2-CONF;


cyanRcmModule MODULE-IDENTITY
    LAST-UPDATED "201412070545Z" -- Sun Dec  7 05:45:22 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Ring Closure Module"

    REVISION     "201412070545Z" -- Sun Dec  7 05:45:22 2014
    DESCRIPTION  "Release 6.0 build 1416362081"

    ::= { cyanEntityModules 70 } 

cyanRcmMibObjects           OBJECT IDENTIFIER ::={ cyanRcmModule 1 }

cyanRcmTable    OBJECT-TYPE
    SYNTAX        SEQUENCE OF CyanRcmEntry
    MAX-ACCESS    not-accessible
    STATUS        current
    DESCRIPTION
        "A list of Rcm entries."
    ::= { cyanRcmMibObjects 1 }

cyanRcmEntry    OBJECT-TYPE
    SYNTAX        CyanRcmEntry
    MAX-ACCESS    not-accessible
    STATUS        current
    DESCRIPTION
        "An entry of Rcm."
    INDEX {
        cyanRcmShelfId ,
        cyanRcmRcmId 
    }
    ::= { cyanRcmTable 1 }

CyanRcmEntry  ::=
    SEQUENCE {
        cyanRcmShelfId    Unsigned32,
        cyanRcmRcmId    Unsigned32,
        cyanRcmAdminState    CyanAdminStateTc,
        cyanRcmAssetTag    DisplayString,
        cyanRcmAutoinserviceSoakTimeSec    Integer32,
        cyanRcmBaseMacAddress    DisplayString,
        cyanRcmDescription    DisplayString,
        cyanRcmIdentifier    DisplayString,
        cyanRcmMacBlockSize    Unsigned32,
        cyanRcmMfgCleiCode    DisplayString,
        cyanRcmMfgEciCode    DisplayString,
        cyanRcmMfgModuleId    Unsigned32,
        cyanRcmMfgPartNumber    DisplayString,
        cyanRcmMfgRevision    DisplayString,
        cyanRcmMfgSerialNumber    DisplayString,
        cyanRcmName    DisplayString,
        cyanRcmOidClass    DisplayString,
        cyanRcmOperState    CyanOpStateTc,
        cyanRcmOperStateQual    CyanOpStateQualTc,
        cyanRcmOssLabel    DisplayString,
        cyanRcmOwner    DisplayString,
        cyanRcmPartNumber    DisplayString,
        cyanRcmSecServState    CyanSecServiceStateTc,
        cyanRcmType    CyanTypeTc
    }

cyanRcmShelfId OBJECT-TYPE
    SYNTAX       Unsigned32 (0..255)
    MAX-ACCESS   not-accessible
    STATUS       current
    DESCRIPTION
        "Shelf Id"

    ::= { cyanRcmEntry 1 }
cyanRcmRcmId OBJECT-TYPE
    SYNTAX       Unsigned32
    MAX-ACCESS   not-accessible
    STATUS       current
    DESCRIPTION
        "RCM Module Id"

    ::= { cyanRcmEntry 2 }

cyanRcmAdminState OBJECT-TYPE
    SYNTAX       CyanAdminStateTc
    MAX-ACCESS   read-only
    STATUS       current
    DESCRIPTION
        "Administrative state"

    ::= { cyanRcmEntry 3 }

cyanRcmAssetTag OBJECT-TYPE
    SYNTAX       DisplayString (SIZE(0..124))
    MAX-ACCESS   read-only
    STATUS       current
    DESCRIPTION
        "Asset Tag"

    ::= { cyanRcmEntry 4 }

cyanRcmAutoinserviceSoakTimeSec OBJECT-TYPE
    SYNTAX       Integer32
    MAX-ACCESS   read-only
    STATUS       current
    DESCRIPTION
        "Auto-In-Service soak time"

    ::= { cyanRcmEntry 5 }

cyanRcmBaseMacAddress OBJECT-TYPE
    SYNTAX       DisplayString
    MAX-ACCESS   read-only
    STATUS       current
    DESCRIPTION
        "Base MAC address of a range of addresses"

    ::= { cyanRcmEntry 6 }

cyanRcmDescription OBJECT-TYPE
    SYNTAX       DisplayString (SIZE(0..255))
    MAX-ACCESS   read-only
    STATUS       current
    DESCRIPTION
        "Description"

    ::= { cyanRcmEntry 7 }

cyanRcmIdentifier OBJECT-TYPE
    SYNTAX       DisplayString
    MAX-ACCESS   read-only
    STATUS       current
    DESCRIPTION
        "string OID"

    ::= { cyanRcmEntry 8 }

cyanRcmMacBlockSize OBJECT-TYPE
    SYNTAX       Unsigned32 (0..255)
    MAX-ACCESS   read-only
    STATUS       current
    DESCRIPTION
        "Number of MAC addresses allocated from the base MAC address"

    ::= { cyanRcmEntry 9 }

cyanRcmMfgCleiCode OBJECT-TYPE
    SYNTAX       DisplayString (SIZE(0..10))
    MAX-ACCESS   read-only
    STATUS       current
    DESCRIPTION
        "Common Language Equipment Identifier"

    ::= { cyanRcmEntry 10 }

cyanRcmMfgEciCode OBJECT-TYPE
    SYNTAX       DisplayString (SIZE(0..6))
    MAX-ACCESS   read-only
    STATUS       current
    DESCRIPTION
        "Equipment Catalog Item"

    ::= { cyanRcmEntry 11 }

cyanRcmMfgModuleId OBJECT-TYPE
    SYNTAX       Unsigned32
    MAX-ACCESS   read-only
    STATUS       current
    DESCRIPTION
        "Module ID"

    ::= { cyanRcmEntry 12 }

cyanRcmMfgPartNumber OBJECT-TYPE
    SYNTAX       DisplayString (SIZE(0..16))
    MAX-ACCESS   read-only
    STATUS       current
    DESCRIPTION
        "Manufacturing part number"

    ::= { cyanRcmEntry 13 }

cyanRcmMfgRevision OBJECT-TYPE
    SYNTAX       DisplayString (SIZE(0..4))
    MAX-ACCESS   read-only
    STATUS       current
    DESCRIPTION
        "Mfg revision number"

    ::= { cyanRcmEntry 14 }

cyanRcmMfgSerialNumber OBJECT-TYPE
    SYNTAX       DisplayString (SIZE(0..16))
    MAX-ACCESS   read-only
    STATUS       current
    DESCRIPTION
        "Mfg serial number"

    ::= { cyanRcmEntry 15 }

cyanRcmName OBJECT-TYPE
    SYNTAX       DisplayString
    MAX-ACCESS   read-only
    STATUS       current
    DESCRIPTION
        "Cyan name"

    ::= { cyanRcmEntry 16 }

cyanRcmOidClass OBJECT-TYPE
    SYNTAX       DisplayString
    MAX-ACCESS   read-only
    STATUS       current
    DESCRIPTION
        "OID Class"

    ::= { cyanRcmEntry 17 }

cyanRcmOperState OBJECT-TYPE
    SYNTAX       CyanOpStateTc
    MAX-ACCESS   read-only
    STATUS       current
    DESCRIPTION
        "Primary Operation State"

    ::= { cyanRcmEntry 18 }

cyanRcmOperStateQual OBJECT-TYPE
    SYNTAX       CyanOpStateQualTc
    MAX-ACCESS   read-only
    STATUS       current
    DESCRIPTION
        "Operation state qualifier"

    ::= { cyanRcmEntry 19 }

cyanRcmOssLabel OBJECT-TYPE
    SYNTAX       DisplayString (SIZE(0..80))
    MAX-ACCESS   read-only
    STATUS       current
    DESCRIPTION
        "CyMS label"

    ::= { cyanRcmEntry 20 }

cyanRcmOwner OBJECT-TYPE
    SYNTAX       DisplayString (SIZE(0..80))
    MAX-ACCESS   read-only
    STATUS       current
    DESCRIPTION
        "Owner"

    ::= { cyanRcmEntry 21 }

cyanRcmPartNumber OBJECT-TYPE
    SYNTAX       DisplayString (SIZE(0..11))
    MAX-ACCESS   read-only
    STATUS       current
    DESCRIPTION
        "Cyan part number"

    ::= { cyanRcmEntry 22 }

cyanRcmSecServState OBJECT-TYPE
    SYNTAX       CyanSecServiceStateTc
    MAX-ACCESS   read-only
    STATUS       current
    DESCRIPTION
        "Secondary service state"

    ::= { cyanRcmEntry 23 }

cyanRcmType OBJECT-TYPE
    SYNTAX       CyanTypeTc
    MAX-ACCESS   read-only
    STATUS       current
    DESCRIPTION
        "Equipment type"

    ::= { cyanRcmEntry 24 }

cyanRcmObjectGroup OBJECT-GROUP
    OBJECTS {
        cyanRcmAdminState,
        cyanRcmAssetTag,
        cyanRcmAutoinserviceSoakTimeSec,
        cyanRcmBaseMacAddress,
        cyanRcmDescription,
        cyanRcmIdentifier,
        cyanRcmMacBlockSize,
        cyanRcmMfgCleiCode,
        cyanRcmMfgEciCode,
        cyanRcmMfgModuleId,
        cyanRcmMfgPartNumber,
        cyanRcmMfgRevision,
        cyanRcmMfgSerialNumber,
        cyanRcmName,
        cyanRcmOidClass,
        cyanRcmOperState,
        cyanRcmOperStateQual,
        cyanRcmOssLabel,
        cyanRcmOwner,
        cyanRcmPartNumber,
        cyanRcmSecServState,
        cyanRcmType
    }

    STATUS current
    DESCRIPTION        "Group of objects that comes with Rcm module"
    ::= {cyanRcmModule 20}

cyanRcmCompliance MODULE-COMPLIANCE
    STATUS current
    DESCRIPTION
        "The basic info needed to be a cyan Rcm"
    MODULE
    MANDATORY-GROUPS {
        cyanRcmObjectGroup
    }
    ::= { cyanRcmModule 30 }


END
