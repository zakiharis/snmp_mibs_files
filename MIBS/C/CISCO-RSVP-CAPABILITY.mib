-- *****************************************************************
-- CISCO-RSVP-CAPABILITY.my
--
-- AGENT-CAPABILITIES for RSVP-MIB 
--
--
-- Copyright(c) 2002 by Cisco Systems,Inc.
--
-- Author: 
-- *****************************************************************

CISCO-RSVP-CAPABILITY DEFINITIONS ::= BEGIN
IMPORTS
        MODULE-IDENTITY
                FROM SNMPv2-SMI
        AGENT-CAPABILITIES
                FROM SNMPv2-CONF
        ciscoAgentCapability
                FROM CISCO-SMI;   

ciscoRsvpCapability MODULE-IDENTITY
        LAST-UPDATED    "200206210000Z"
        ORGANIZATION    "Cisco Systems, Inc."
        CONTACT-INFO
                "       Cisco Systems
                        Customer Service

                Postal: 170 W Tasman Drive
                        San Jose, CA  95134
                        USA

                        Tel: +1 800 553-NETS

                E-mail: cs-rsvp@cisco.com"
        DESCRIPTION
                "The Agent Capabilities for RSVP-MIB."
        ::= { ciscoAgentCapability 10000 }

ciscoRsvpCapabilityVismV3R00 AGENT-CAPABILITIES
PRODUCT-RELEASE      "VISM Release 3.00"
STATUS               current
DESCRIPTION          "RSVP MIB Capabilities."

    SUPPORTS RSVP-MIB
	INCLUDES { rsvpSessionGroup, rsvpSenderGroup, rsvpResvGroup, 
                   rsvpResvFwdGroup, rsvpIfGroup, rsvpNbrGroup, 
                   rsvpGenObjectsGroup, rsvpSenderOutInterfaceGroup
                 }

	VARIATION    rsvpSenderType
	ACCESS	     read-only
	DESCRIPTION  "write access is not supported."

	VARIATION    rsvpSenderDestAddr
	ACCESS	     read-only
	DESCRIPTION  "write access is not supported."

	VARIATION    rsvpSenderAddr
	ACCESS	     read-only
	DESCRIPTION  "write access is not supported."

	VARIATION    rsvpSenderDestAddrLength
	ACCESS	     read-only
	DESCRIPTION  "write access is not supported."

	VARIATION    rsvpSenderAddrLength
	ACCESS	     read-only
	DESCRIPTION  "write access is not supported."

	VARIATION    rsvpSenderProtocol
	ACCESS	     read-only
	DESCRIPTION  "write access is not supported."

	VARIATION    rsvpSenderDestPort
	ACCESS	     read-only
	DESCRIPTION  "write access is not supported."

	VARIATION    rsvpSenderPort
	ACCESS	     read-only
	DESCRIPTION  "write access is not supported."

	VARIATION    rsvpSenderFlowId
        ACCESS       not-implemented
        DESCRIPTION  "Not supported."

	VARIATION    rsvpSenderHopAddr
	ACCESS	     read-only
	DESCRIPTION  "write access is not supported."

	VARIATION    rsvpSenderHopLih
        ACCESS       not-implemented
        DESCRIPTION  "Not supported."

	VARIATION    rsvpSenderInterface
	ACCESS	     read-only
	DESCRIPTION  "write access is not supported."

	VARIATION    rsvpSenderTSpecRate
	ACCESS	     read-only
	DESCRIPTION  "write access is not supported."

	VARIATION    rsvpSenderTSpecPeakRate
	ACCESS	     read-only
	DESCRIPTION  "write access is not supported."

	VARIATION    rsvpSenderTSpecBurst
	ACCESS	     read-only
	DESCRIPTION  "write access is not supported."

	VARIATION    rsvpSenderTSpecMinTU
	ACCESS	     read-only
	DESCRIPTION  "write access is not supported."

	VARIATION    rsvpSenderTSpecMaxTU
	ACCESS	     read-only
	DESCRIPTION  "write access is not supported."

	VARIATION    rsvpSenderInterval
	ACCESS	     read-only
	DESCRIPTION  "write access is not supported."

	VARIATION    rsvpSenderRSVPHop
	ACCESS	     read-only
	DESCRIPTION  "write access is not supported."

	VARIATION    rsvpSenderPolicy
        ACCESS       not-implemented
        DESCRIPTION  "Not supported."

	VARIATION    rsvpSenderAdspecBreak
        ACCESS       not-implemented
        DESCRIPTION  "Not supported."

	VARIATION    rsvpSenderAdspecHopCount
        ACCESS       not-implemented
        DESCRIPTION  "Not supported."

	VARIATION    rsvpSenderAdspecPathBw
        ACCESS       not-implemented
        DESCRIPTION  "Not supported."

	VARIATION    rsvpSenderAdspecMinLatency
        ACCESS       not-implemented
        DESCRIPTION  "Not supported."

	VARIATION    rsvpSenderAdspecMtu
        ACCESS       not-implemented
        DESCRIPTION  "Not supported."

	VARIATION    rsvpSenderAdspecGuaranteedSvc
        ACCESS       not-implemented
        DESCRIPTION  "Not supported."

	VARIATION    rsvpSenderAdspecGuaranteedBreak
        ACCESS       not-implemented
        DESCRIPTION  "Not supported."

	VARIATION    rsvpSenderAdspecGuaranteedCtot
        ACCESS       not-implemented
        DESCRIPTION  "Not supported."

	VARIATION    rsvpSenderAdspecGuaranteedDtot
        ACCESS       not-implemented
        DESCRIPTION  "Not supported."

	VARIATION    rsvpSenderAdspecGuaranteedCsum
        ACCESS       not-implemented
        DESCRIPTION  "Not supported."

	VARIATION    rsvpSenderAdspecGuaranteedDsum
        ACCESS       not-implemented
        DESCRIPTION  "Not supported."

	VARIATION    rsvpSenderAdspecGuaranteedHopCount
        ACCESS       not-implemented
        DESCRIPTION  "Not supported."

	VARIATION    rsvpSenderAdspecGuaranteedPathBw
        ACCESS       not-implemented
        DESCRIPTION  "Not supported."

	VARIATION    rsvpSenderAdspecGuaranteedMinLatency
        ACCESS       not-implemented
        DESCRIPTION  "Not supported."

	VARIATION    rsvpSenderAdspecGuaranteedMtu
        ACCESS       not-implemented
        DESCRIPTION  "Not supported."

	VARIATION    rsvpSenderAdspecCtrlLoadSvc
        ACCESS       not-implemented
        DESCRIPTION  "Not supported."

	VARIATION    rsvpSenderAdspecCtrlLoadBreak
        ACCESS       not-implemented
        DESCRIPTION  "Not supported."

	VARIATION    rsvpSenderAdspecCtrlLoadHopCount
        ACCESS       not-implemented
        DESCRIPTION  "Not supported."

	VARIATION    rsvpSenderAdspecCtrlLoadPathBw
        ACCESS       not-implemented
        DESCRIPTION  "Not supported."

	VARIATION    rsvpSenderAdspecCtrlLoadMinLatency
        ACCESS       not-implemented
        DESCRIPTION  "Not supported."

	VARIATION    rsvpSenderAdspecCtrlLoadMtu
        ACCESS       not-implemented
        DESCRIPTION  "Not supported."

	VARIATION    rsvpSenderStatus
	ACCESS       read-only
	DESCRIPTION  "write access is not supported."

	VARIATION    rsvpResvType
	ACCESS       read-only
	DESCRIPTION  "write access is not supported."

	VARIATION    rsvpResvDestAddr
	ACCESS       read-only
	DESCRIPTION  "write access is not supported."

	VARIATION    rsvpResvSenderAddr
	ACCESS       read-only
	DESCRIPTION  "write access is not supported."

	VARIATION    rsvpResvDestAddrLength
	ACCESS       read-only
	DESCRIPTION  "write access is not supported."

	VARIATION    rsvpResvSenderAddrLength
	ACCESS       read-only
	DESCRIPTION  "write access is not supported."

	VARIATION    rsvpResvProtocol
	ACCESS       read-only
	DESCRIPTION  "write access is not supported."

	VARIATION    rsvpResvDestPort
	ACCESS       read-only
	DESCRIPTION  "write access is not supported."

	VARIATION    rsvpResvPort
	ACCESS       read-only
	DESCRIPTION  "write access is not supported."

	VARIATION    rsvpResvHopAddr
	ACCESS       read-only
	DESCRIPTION  "write access is not supported."

	VARIATION    rsvpResvHopLih
        ACCESS       not-implemented
        DESCRIPTION  "Not supported."

	VARIATION    rsvpResvInterface
	ACCESS       read-only
	DESCRIPTION  "write access is not supported."

	VARIATION    rsvpResvService
	ACCESS       read-only
	DESCRIPTION  "write access is not supported."

	VARIATION    rsvpResvTSpecRate
	ACCESS       read-only
	DESCRIPTION  "write access is not supported."

	VARIATION    rsvpResvTSpecPeakRate
	ACCESS       read-only
	DESCRIPTION  "write access is not supported."

	VARIATION    rsvpResvTSpecBurst
	ACCESS       read-only
	DESCRIPTION  "write access is not supported."

	VARIATION    rsvpResvTSpecMinTU
	ACCESS       read-only
	DESCRIPTION  "write access is not supported."

	VARIATION    rsvpResvTSpecMaxTU
	ACCESS       read-only
	DESCRIPTION  "write access is not supported."

	VARIATION    rsvpResvRSpecRate
	ACCESS       read-only
	DESCRIPTION  "write access is not supported."

	VARIATION    rsvpResvRSpecSlack
	ACCESS       read-only
	DESCRIPTION  "write access is not supported."

	VARIATION    rsvpResvInterval
	ACCESS       read-only
	DESCRIPTION  "write access is not supported."

	VARIATION    rsvpResvScope
	ACCESS       read-only
	DESCRIPTION  "write access is not supported."

	VARIATION    rsvpResvShared
	ACCESS       read-only
	DESCRIPTION  "write access is not supported."

	VARIATION    rsvpResvExplicit
	ACCESS       read-only
	DESCRIPTION  "write access is not supported."

	VARIATION    rsvpResvRSVPHop
	ACCESS       read-only
	DESCRIPTION  "write access is not supported."

	VARIATION    rsvpResvPolicy
        ACCESS       not-implemented
        DESCRIPTION  "Not supported."

	VARIATION    rsvpResvStatus
	ACCESS       read-only
	DESCRIPTION  "write access is not supported."

	VARIATION    rsvpResvTTL
        ACCESS       not-implemented
        DESCRIPTION  "Not supported."

	VARIATION    rsvpResvFlowId
        ACCESS       not-implemented
        DESCRIPTION  "Not supported."

	VARIATION    rsvpResvFwdHopLih
        ACCESS       not-implemented
        DESCRIPTION  "Not supported."

	VARIATION    rsvpResvFwdPolicy
        ACCESS       not-implemented
        DESCRIPTION  "Not supported."

	VARIATION    rsvpResvFwdStatus
	ACCESS       read-only
	DESCRIPTION  "write access is not supported."

	VARIATION    rsvpResvFwdTTL
        ACCESS       not-implemented
        DESCRIPTION  "Not supported."

	VARIATION    rsvpResvFwdFlowId
        ACCESS       not-implemented
        DESCRIPTION  "Not supported."

	VARIATION    rsvpIfUdpNbrs
        ACCESS       not-implemented
        DESCRIPTION  "Not supported."

	VARIATION    rsvpIfTTL
        ACCESS       not-implemented
        DESCRIPTION  "Not supported."

	VARIATION    rsvpIfRouteDelay
        ACCESS       not-implemented
        DESCRIPTION  "Not supported."
     
	VARIATION    rsvpIfUdpRequired
        ACCESS       not-implemented
        DESCRIPTION  "Not supported."

	VARIATION    rsvpIfRefreshBlockadeMultiple 
        ACCESS       read-only
        DESCRIPTION  "write access is not supported." 

	VARIATION    rsvpIfRefreshInterval 
        ACCESS       read-only
        DESCRIPTION  "write access is not supported." 

	VARIATION    rsvpNbrProtocol
	ACCESS       read-only
	DESCRIPTION  "write access is not supported."

	VARIATION    rsvpNbrStatus
	ACCESS       read-only
	DESCRIPTION  "write access is not supported."

	VARIATION    rsvpBadPackets
        ACCESS       not-implemented
        DESCRIPTION  "Not supported."

	VARIATION    rsvpSenderNewIndex
	ACCESS       read-only
	DESCRIPTION  "write access is not supported."

	VARIATION    rsvpResvNewIndex
	ACCESS       read-only
	DESCRIPTION  "write access is not supported."

	VARIATION    rsvpResvFwdNewIndex
	ACCESS       read-only
	DESCRIPTION  "write access is not supported."

	VARIATION    rsvpSessionNewIndex
	ACCESS       read-only
	DESCRIPTION  "write access is not supported."
    
    ::= { ciscoRsvpCapability 1 }
END
