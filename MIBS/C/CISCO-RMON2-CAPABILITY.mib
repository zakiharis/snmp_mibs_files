-- *****************************************************************
-- CISCO-RMON2-CAPABILITY.my:
-- Cisco RMON2-MIB AGENT-CAPABILITIES
--
-- August 2003, Padma Pullela 
--
-- Copyright (c) 2003 by Cisco Systesms, Inc.
-- All rights reserved.
-- *****************************************************************

CISCO-RMON2-CAPABILITY DEFINITIONS ::= BEGIN

IMPORTS
        MODULE-IDENTITY
                FROM SNMPv2-SMI
        AGENT-CAPABILITIES
                FROM SNMPv2-CONF
        ciscoAgentCapability
                FROM CISCO-SMI;

ciscoRmon2Capability MODULE-IDENTITY
        LAST-UPDATED    "200310010000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-rmon@cisco.com"
        DESCRIPTION
                "The capabilities description of 
                 RMON2-MIB."

        REVISION        "200310010000Z"
        DESCRIPTION
                "Initial version of this MIB module."
        ::= { ciscoAgentCapability 361 }

ciscoRmon2CapCatOSV08R0101  AGENT-CAPABILITIES
    PRODUCT-RELEASE     "Cisco CatOS 8.1(1)." 
    STATUS              current
    DESCRIPTION         "RMON2-MIB capabilities."

    SUPPORTS            RMON2-MIB
    INCLUDES            { probeInformationGroup,
                          probeConfigurationGroup, 
                          usrHistoryGroup }

    VARIATION           probeDateTime 
    ACCESS              not-implemented
    DESCRIPTION         "not implemented." 

    VARIATION           probeResetControl 
    ACCESS              not-implemented
    DESCRIPTION         "not implemented." 

    VARIATION           probeDownloadFile 
    ACCESS              not-implemented
    DESCRIPTION         "not implemented." 

    VARIATION           probeDownloadTFTPServer 
    ACCESS              not-implemented
    DESCRIPTION         "not implemented." 

    VARIATION           probeDownloadAction 
    ACCESS              not-implemented
    DESCRIPTION         "not implemented." 

    VARIATION           probeDownloadStatus 
    ACCESS              not-implemented
    DESCRIPTION         "not implemented." 

    VARIATION           serialMode 
    ACCESS              not-implemented
    DESCRIPTION         "not implemented." 

    VARIATION           serialProtocol 
    ACCESS              not-implemented
    DESCRIPTION         "not implemented." 

    VARIATION           serialTimeout 
    ACCESS              not-implemented
    DESCRIPTION         "not implemented." 

    VARIATION           serialModemInitString 
    ACCESS              not-implemented
    DESCRIPTION         "not implemented." 

    VARIATION           serialModemHangUpString 
    ACCESS              not-implemented
    DESCRIPTION         "not implemented." 

    VARIATION           serialModemConnectResp 
    ACCESS              not-implemented
    DESCRIPTION         "not implemented." 

    VARIATION           serialModemNoConnectResp 
    ACCESS              not-implemented
    DESCRIPTION         "not implemented." 

    VARIATION           serialDialoutTimeout 
    ACCESS              not-implemented
    DESCRIPTION         "not implemented." 

    VARIATION           serialStatus 
    ACCESS              not-implemented
    DESCRIPTION         "not implemented." 

    VARIATION           serialConnectDestIpAddress 
    ACCESS              not-implemented
    DESCRIPTION         "not implemented." 

    VARIATION           serialConnectType 
    ACCESS              not-implemented
    DESCRIPTION         "not implemented." 

    VARIATION           serialConnectDialString 
    ACCESS              not-implemented
    DESCRIPTION         "not implemented." 

    VARIATION           serialConnectSwitchConnectSeq 
    ACCESS              not-implemented
    DESCRIPTION         "not implemented." 

    VARIATION           serialConnectSwitchDisconnectSeq 
    ACCESS              not-implemented
    DESCRIPTION         "not implemented." 

    VARIATION           serialConnectSwitchResetSeq 
    ACCESS              not-implemented
    DESCRIPTION         "not implemented." 

    VARIATION           serialConnectOwner 
    ACCESS              not-implemented
    DESCRIPTION         "not implemented." 

    VARIATION           serialConnectStatus 
    ACCESS              not-implemented
    DESCRIPTION         "not implemented." 

    VARIATION           netConfigIPAddress 
    ACCESS              not-implemented
    DESCRIPTION         "not implemented." 

    VARIATION           netConfigSubnetMask 
    ACCESS              not-implemented
    DESCRIPTION         "not implemented." 

    VARIATION           netConfigStatus 
    ACCESS              not-implemented
    DESCRIPTION         "not implemented." 

    VARIATION           netDefaultGateway 
    ACCESS              not-implemented
    DESCRIPTION         "not implemented." 

    ::= { ciscoRmon2Capability 1 }

END
