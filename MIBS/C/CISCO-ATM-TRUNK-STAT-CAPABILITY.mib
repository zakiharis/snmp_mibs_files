-- *****************************************************************
-- CISCO-ATM-TRUNK-STAT-CAPABILITY.my:
-- CISCO-ATM-TRUNK-STAT-MIB AGENT-CAPABILITIES
--
-- September 2005, Rashmi Purandare
--
-- Copyright (c) 2004, 2005 by Cisco Systems, Inc.
-- All rights reserved.
-- *****************************************************************

CISCO-ATM-TRUNK-STAT-CAPABILITY DEFINITIONS ::= BEGIN

IMPORTS
        MODULE-IDENTITY
                FROM SNMPv2-SMI
        AGENT-CAPABILITIES
                FROM SNMPv2-CONF
        ciscoAgentCapability
                FROM CISCO-SMI
			AtmVcIdentifier FROM ATM-TC-MIB;

ciscoAtmTrunkStatCapability MODULE-IDENTITY
        LAST-UPDATED    "200509190000Z"
        ORGANIZATION    "Cisco Systems, Inc."
        CONTACT-INFO
                "       Cisco Systems
                        Customer Service

                Postal: 170 West Tasman Drive
                        San Jose, CA  95134
                        USA

                   Tel: +1 800 553-NETS

                E-mail: cs-snmp@cisco.com"
        DESCRIPTION
                "The capabilities description of 
                 CISCO-ATM-TRUNK-STAT-MIB."

        REVISION        "200509190000Z"
        DESCRIPTION
                "New capabilities for Cisco VISM 
                 Release 3.3.25"

        REVISION        "200411170000Z"
        DESCRIPTION
                "Updated CANA ID."

        REVISION        "200406150000Z"
        DESCRIPTION
                "Initial version of this MIB module."
        ::= { ciscoAgentCapability 420 }


cAtmTrunkStatCapVISM33 AGENT-CAPABILITIES
    PRODUCT-RELEASE    "Cisco VISM Release 3.3."
    STATUS             current
    DESCRIPTION        "CISCO-ATM-TRUNK-STAT-MIB capabilities."

    SUPPORTS           CISCO-ATM-TRUNK-STAT-MIB
    INCLUDES           { catsPvcStatGroup,
                         catsAal2PvcStatGroup,
                         catsAal5PvcStatGroup,
                         catsCidHistoryStatGroup }

    VARIATION          catsAal2PvcCrcErrors
    ACCESS             not-implemented
    DESCRIPTION        "Not supported"

    ::= { ciscoAtmTrunkStatCapability 1 }

cAtmTrunkStatCapVISM3325 AGENT-CAPABILITIES
    PRODUCT-RELEASE    "Cisco VISM Release 3.3.25."
    STATUS             current
    DESCRIPTION        "CISCO-ATM-TRUNK-STAT-MIB capabilities."

    SUPPORTS           CISCO-ATM-TRUNK-STAT-MIB
    INCLUDES           { catsPvcStatGroup,
                         catsAal2PvcStatGroup,
                         catsAal5PvcStatGroup,
                         catsCidHistoryStatGroup }

    VARIATION          catsAal2PvcCrcErrors
    ACCESS             not-implemented
    DESCRIPTION        "Not supported"

    VARIATION          catsPvcVci
    SYNTAX             AtmVcIdentifier (131..510)
    DESCRIPTION        "The allowed range is 131-510." 

    VARIATION          catsAal2PvcVci
    SYNTAX             AtmVcIdentifier (131..510)
    DESCRIPTION        "The allowed range is 131-510."

    VARIATION          catsAal5PvcVci
    SYNTAX             AtmVcIdentifier (131..510)
    DESCRIPTION        "The allowed range is 131-510."

    VARIATION          catsPvcHistoryTable 
    DESCRIPTION        "Only a maximum of 64 entries are 
                        supported."

    VARIATION          catsAal2PvcHistoryTable 
    DESCRIPTION        "Only a maximum of 64 entries are
                        supported."

    VARIATION          catsAal5PvcHistoryTable 
    DESCRIPTION        "Only a maximum of 64 entries are
                        supported."

    ::= { ciscoAtmTrunkStatCapability 2 }
END
