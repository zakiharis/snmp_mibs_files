-- *****************************************************************
-- CISCO-BERT-CAPABILITY
--
-- AGENT-CAPABILITIES mib for CISCO-BERT-MIB for CISCO Products
--
-- December 2003, Yizhong Shen
-- 
-- Copyright(c) 2002-2004 by Cisco Systems,Inc.
-- 
-- *****************************************************************

CISCO-BERT-CAPABILITY DEFINITIONS ::= BEGIN

IMPORTS
        MODULE-IDENTITY, Integer32
                FROM SNMPv2-SMI
        AGENT-CAPABILITIES
                FROM SNMPv2-CONF
        ciscoAgentCapability
                FROM CISCO-SMI;

ciscoBertCapability MODULE-IDENTITY
        LAST-UPDATED    "200408070000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
DESCRIPTION
    "The Agent Capabilities for CISCO-BERT-MIB for
     Cisco Products Series.

     - ciscoBertAxsmeCapabilityV3R00 is for
       Enhanced ATM Switch Service Module(AXSM-E), and
       Enhanced Processor Switch Module 1(PXM1E) uplink."

REVISION    "200408070000Z"
DESCRIPTION
    "Modify ciscoBertCapabilityV5R015 for VXSM release 5.0.15."

REVISION    "200312220000Z"
DESCRIPTION
    "Modify ciscoBertCapabilityV5R00 for VXSM release 5.0.0."

REVISION    "200309190000Z"
DESCRIPTION
    "Added ciscoBertCapabilityV5R00 for VXSM release 5.0.0."

REVISION    "200210300000Z"
DESCRIPTION
    "Added cbRowStatus support description."

REVISION    "200206110000Z"
DESCRIPTION
    "Initial version of this MIB module."

::= { ciscoAgentCapability  274 }


ciscoBertAxsmeCapabilityV3R00 AGENT-CAPABILITIES

PRODUCT-RELEASE "MGX8850 Release 3.0"
STATUS          current
DESCRIPTION     "CISCO-BERT-MIB Capabilities."

SUPPORTS        CISCO-BERT-MIB
INCLUDES        { ciscoBertConfigGroup, ciscoBertStatsGroup }

VARIATION       cbTestPattern
DESCRIPTION     "Supported with limitation.
                 The agent supports following enums:
                     allZeros(1),
                     allOnes(2),
                     altOneZero(3),
                     doubleAltOnesZeros(4),
                     oneIn4(5),
                     oneIn8(6),
                     oneIn16(7),
                     threeIn24(8),
                     inbandLoopBackActivate(9),
                     inbandLoopBackDeactivate(10),
                     twoE3MinusOne(11),
                     twoE4MinusOne(12),
                     twoE5MinusOne(13),
                     twoE6MinusOne(14),
                     twoE7MinusOne(15),
                     twoE7MinusOneFT1Loopup(16),
                     twoE9MinusOne(18),
                     twoE10MinusOne(19),
                     twoE11MinusOne(20),
                     twoE15MinusOne(21),
                     twoE17MinusOne(22),
                     twoE18MinusOne(23),
                     twoE20MinusOne(24),
                     twoE20MinusOneQRSS(25),
                     twoE21MinusOne(26),
                     twoE22MinusOne(27),
                     twoE23MinusOne(28),
                     twoE25MinusOne(29),
                     twoE28MinusOne(30),
                     twoE29MinusOne(31),
                     twoE31MinusOne(32)
                 
                 The agent does not support
                     twoE7MinusOneFT1Loopdown(17),
                     dds1pattern (33),
                     dds2pattern (34),
                     dds3pattern (35),
                     dds4pattern (36),
                     dds5pattern (37),
                     userPattern(38)."

VARIATION       cbUserPattern
ACCESS          not-implemented
DESCRIPTION     "Not Supported."

VARIATION       cbLoopback
ACCESS          not-implemented
DESCRIPTION     "Not Supported."

VARIATION       cbLoopbackCode
SYNTAX          INTEGER {lineLoopbackESF(13)}
DESCRIPTION     "Supported with limitation.
                 lineLoopbackESF(13) only."

VARIATION       cbErrorInsertionRate
SYNTAX          INTEGER {
                    noError(1),
                    oneInHundred(3),
                    oneInThousand(4),
                    oneInTenThousand(5),
                    oneInHundredThousand(6),
                    oneInMillion(7),
                    oneInTenMillion(8)
                    }
DESCRIPTION     "The agent does not support oneInTen(2)."

VARIATION       cbDuration
ACCESS          not-implemented
DESCRIPTION     "Not Supported."

VARIATION       cbRowStatus
DESCRIPTION     "The agent statically maintains a cbTable
                 with all entries corresponding to the T1
                 lines at the card startup. These entries can
                 not be created or deleted. However, a set
                 to 'destroy(6)' will stop the bert test."

VARIATION       cbDS0DPCodeIteration
ACCESS          not-implemented
DESCRIPTION     "Not Supported."

VARIATION       cbTxBitCountLower
ACCESS          not-implemented
DESCRIPTION     "Not Supported."

VARIATION       cbTxBitCountUpper
ACCESS          not-implemented
DESCRIPTION     "Not Supported."

VARIATION       cbHCTxBitCounts
ACCESS          not-implemented
DESCRIPTION     "Not Supported."

VARIATION       cbHCRxBitCounts
ACCESS          not-implemented
DESCRIPTION     "Not Supported."

VARIATION       cbHCRxBitErrCounts
ACCESS          not-implemented
DESCRIPTION     "Not Supported."

VARIATION       cbSyncLossCounts
ACCESS          not-implemented
DESCRIPTION     "Not Supported."

VARIATION       cbPatternLossCounts
ACCESS          not-implemented
DESCRIPTION     "Not Supported."

VARIATION       cbFrameLossCounts
ACCESS          not-implemented
DESCRIPTION     "Not Supported."

VARIATION       cbESsCounts
ACCESS          not-implemented
DESCRIPTION     "Not Supported."

VARIATION       cbSESsCounts
ACCESS          not-implemented
DESCRIPTION     "Not Supported."

VARIATION       cbEFSsCounts
ACCESS          not-implemented
DESCRIPTION     "Not Supported."

    ::= { ciscoBertCapability 1 }

ciscoBertCapabilityV5R00 AGENT-CAPABILITIES

PRODUCT-RELEASE "MGX8850 Release 5.0"
STATUS          current
DESCRIPTION     "CISCO-BERT-MIB capabilities for Voice Switch 
                 Service Module (VXSM) Release 5.0.0"

SUPPORTS     CISCO-BERT-MIB
INCLUDES     { ciscoBertConfigGroup, ciscoBertStatsGroup }
VARIATION    cbConfEntry
CREATION-REQUIRES 
             {
                  cbTestPattern
             }
DESCRIPTION  "The above object is required for row creation."

VARIATION    cbUserPattern
ACCESS       not-implemented
DESCRIPTION  "Not supported."

VARIATION    cbBertTxPatternInv
ACCESS       not-implemented
DESCRIPTION  "Not supported."

VARIATION    cbBertRxPatternInv
ACCESS       not-implemented
DESCRIPTION  "Not supported."

VARIATION    cbSingleBitErrorInsert
ACCESS       not-implemented
DESCRIPTION  "Not supported."

VARIATION    cbFailedReason
ACCESS       not-implemented
DESCRIPTION  "Not supported."

VARIATION    cbStartDateAndTime
ACCESS       not-implemented
DESCRIPTION  "Not supported."

VARIATION    cbDS0DPCodeIteration
ACCESS       not-implemented
DESCRIPTION  "Not supported."

VARIATION    cbTestPattern
SYNTAX       INTEGER { allZeros          (1),
                       allOnes           (2),
                       altOneZero        (3),
                       doubleAltOnesZeros(4),
                       oneIn4            (5),
                       oneIn8            (6),
                       oneIn16           (7),
                       threeIn24         (8),
                       twoE9MinusOne     (18),
                       twoE11MinusOne    (20),
                       twoE15MinusOne    (21),
                       twoE20MinusOne    (24),
                       twoE20MinusOneQRSS(25),
                       twoE23MinusOne    (28)   
                     }
DESCRIPTION  "Supported BERT test patterns."

VARIATION    cbOperStatus
SYNTAX       INTEGER { success   (1),
                       inSync    (2),
                       outOfSync (3),
                       bertFailed(6)
                     }
DESCRIPTION  "Does not support values inLoopback(4) and 
              clockOutOfSync(5)"

VARIATION    cbDuration
SYNTAX       Integer32 (10..86400)
DESCRIPTION  "Default value is 600"

VARIATION    cbDs0BitMap
DESCRIPTION  "The default value is { dsZero0, dsZero1, dsZero2,....,
              dsZero22, dsZero23 } (0xFFFFFF00)"

VARIATION    cbTxBitCountLower
ACCESS       not-implemented
DESCRIPTION  "Not supported."

VARIATION    cbTxBitCountUpper
ACCESS       not-implemented
DESCRIPTION  "Not supported."

VARIATION    cbSyncLossCounts
ACCESS       not-implemented
DESCRIPTION  "Not supported."

VARIATION    cbPatternLossCounts
ACCESS       not-implemented
DESCRIPTION  "Not supported."

VARIATION    cbFrameLossCounts
ACCESS       not-implemented
DESCRIPTION  "Not supported."

VARIATION    cbESsCounts
ACCESS       not-implemented
DESCRIPTION  "Not supported."

VARIATION    cbSESsCounts
ACCESS       not-implemented
DESCRIPTION  "Not supported."

VARIATION    cbEFSsCounts
ACCESS       not-implemented
DESCRIPTION  "Not supported."

VARIATION    cbErrorInjectCounts
ACCESS       not-implemented
DESCRIPTION  "Not supported."

    ::= { ciscoBertCapability 2 }

ciscoBertCapabilityV5R015 AGENT-CAPABILITIES

PRODUCT-RELEASE "MGX8850 Release 5.0.15"
STATUS          current
DESCRIPTION     "CISCO-BERT-MIB capabilities for Voice Switch 
                 Service Module (VXSM) Release 5.0.15"

SUPPORTS     CISCO-BERT-MIB
INCLUDES     { ciscoBertConfigGroup, 
               ciscoBertStatsGroup,
               ciscoBertConfigGroupDs1
             }

VARIATION    cbConfEntry
CREATION-REQUIRES 
             {
                  cbTestPattern
             }
DESCRIPTION  "The above object is required for row creation."

VARIATION    cbUserPattern
ACCESS       not-implemented
DESCRIPTION  "Not supported."

VARIATION    cbBertTxPatternInv
ACCESS       not-implemented
DESCRIPTION  "Not supported."

VARIATION    cbBertRxPatternInv
ACCESS       not-implemented
DESCRIPTION  "Not supported."

VARIATION    cbSingleBitErrorInsert
ACCESS       not-implemented
DESCRIPTION  "Not supported."

VARIATION    cbFailedReason
ACCESS       not-implemented
DESCRIPTION  "Not supported."

VARIATION    cbStartDateAndTime
ACCESS       not-implemented
DESCRIPTION  "Not supported."

VARIATION    cbDS0DPCodeIteration
ACCESS       not-implemented
DESCRIPTION  "Not supported."

VARIATION    cbTestPattern
SYNTAX       INTEGER { allZeros          (1),
                       allOnes           (2),
                       altOneZero        (3),
                       doubleAltOnesZeros(4),
                       oneIn4            (5),
                       oneIn8            (6),
                       oneIn16           (7),
                       threeIn24         (8),
                       twoE9MinusOne     (18),
                       twoE11MinusOne    (20),
                       twoE15MinusOne    (21),
                       twoE20MinusOne    (24),
                       twoE20MinusOneQRSS(25),
                       twoE23MinusOne    (28)   
                     }
DESCRIPTION  "Supported BERT test patterns."

VARIATION    cbOperStatus
SYNTAX       INTEGER { success   (1),
                       inSync    (2),
                       outOfSync (3),
                       bertFailed(6)
                     }
DESCRIPTION  "Does not support values inLoopback(4) and 
              clockOutOfSync(5)"

VARIATION    cbDuration
SYNTAX       Integer32 (10..86400)
DESCRIPTION  "Default value is 600"

VARIATION    cbDs0BitMap
DESCRIPTION  "The default value is { dsZero0, dsZero1, dsZero2,....,
              dsZero22, dsZero23 } (0xFFFFFF00)"

VARIATION    cbTxBitCountLower
ACCESS       not-implemented
DESCRIPTION  "Not supported."

VARIATION    cbTxBitCountUpper
ACCESS       not-implemented
DESCRIPTION  "Not supported."

VARIATION    cbSyncLossCounts
ACCESS       not-implemented
DESCRIPTION  "Not supported."

VARIATION    cbPatternLossCounts
ACCESS       not-implemented
DESCRIPTION  "Not supported."

VARIATION    cbFrameLossCounts
ACCESS       not-implemented
DESCRIPTION  "Not supported."

VARIATION    cbESsCounts
ACCESS       not-implemented
DESCRIPTION  "Not supported."

VARIATION    cbSESsCounts
ACCESS       not-implemented
DESCRIPTION  "Not supported."

VARIATION    cbEFSsCounts
ACCESS       not-implemented
DESCRIPTION  "Not supported."

VARIATION    cbErrorInjectCounts
ACCESS       not-implemented
DESCRIPTION  "Not supported."

    ::= { ciscoBertCapability 3 }

END
