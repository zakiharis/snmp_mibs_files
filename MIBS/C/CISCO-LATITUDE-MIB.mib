-- *------------------------------------------------------------------
-- * CISCO-LATITUDE-MIB.my:
-- *      Cisco Latitude MIB.
-- *
-- * Kim Le, August 2004
-- *
-- * Latitude was acquired by Cisco Systems on January 13, 2004
-- *
-- * Copyright (c) 2004 by Cisco Systems, Inc.
-- * All rights reserved.
-- *
-- *------------------------------------------------------------------

CISCO-LATITUDE-MIB DEFINITIONS ::= BEGIN

IMPORTS
    MODULE-IDENTITY,
    OBJECT-TYPE,
    NOTIFICATION-TYPE,
    Integer32,
    enterprises
        FROM SNMPv2-SMI
    DisplayString
        FROM SNMPv2-TC
    MODULE-COMPLIANCE,
    OBJECT-GROUP,
    NOTIFICATION-GROUP
       FROM SNMPv2-CONF;

-- the root of the sub-tree for Latitude 
latitudeComm MODULE-IDENTITY
    LAST-UPDATED "200408160000Z"
    ORGANIZATION
        "Cisco Systems, Inc."
    CONTACT-INFO
        "        Cisco Systems
                 Customer Service

                 Postal: 170 W Tasman Drive
                         San Jose, CA 95134
                         USA

                    Tel: +1 800 553-NETS

                 E-mail: cse-meetingplace@cisco.com"
    DESCRIPTION
        "The MIB module for the managment of Cisco Latitude MeetingPlace
         conferencing solution.

         MeetignPlace MIB traps are generated under the following 
         conditions.

             - T1 status
             - Gateway System Integrity
             - Major hardware alarm
             - Minor hardware alarm
             - Major software alarm
             - Minor software alarm

         Each major and minor hardware and software notification
         includes an integer alarm code that indicates which software
         module and server reported the alarm.  For hardware alarms,
         four additional codes identify the device type, the device
         address, slot number, and port number."
 

    REVISION "200408160000Z"
    DESCRIPTION
        "Initial version of this MIB."

    ::= { enterprises 7185 }

-- sub-tree for registrations, which includes modules
latitudeReg       OBJECT IDENTIFIER ::= {latitudeComm 1}
latitudeModules   OBJECT IDENTIFIER ::= {latitudeReg 1}

-- sub-tree for company-wide objects and events
latitudeGeneric   OBJECT IDENTIFIER ::= {latitudeComm 2}

-- sub-tree for product-specific objects and events
latitudeProducts  OBJECT IDENTIFIER ::= {latitudeComm 3}
meetingplace      OBJECT IDENTIFIER ::= {latitudeProducts 1}

-- conformance area, containing groups and compliance specifications
meetingplaceConfs           OBJECT IDENTIFIER ::= {meetingplace 1}

-- sub-tree for objects, and for each functional area
meetingplaceObjs            OBJECT IDENTIFIER ::= {meetingplace 2}

-- sub-tree for events
meetingplaceEvents          OBJECT IDENTIFIER ::= {meetingplace 3}
meetingplaceEventsV2        OBJECT IDENTIFIER ::= {meetingplaceEvents 0}


mpExCode OBJECT-TYPE
    SYNTAX      Integer32(0..254)
    MAX-ACCESS  read-only
    STATUS      current
    DESCRIPTION "MeetingPlace Exception Code.

                 This is the primary code associated with each 
                 MeetingPlace exception condition.

                 The mpAlarmDesc OID will provide a textual description 
                 of the exception code.  Refer to the MeetingPlace 
                 System Managers Guide for more details."
    ::= {meetingplaceEvents 1}

mpSysUnit OBJECT-TYPE
    SYNTAX      Integer32(0..254)
    MAX-ACCESS  read-only
    STATUS      current
    DESCRIPTION "MeetingPlace Server Unit Number.
                 This is the unit (server) number of the server that 
                 reported the exception."
    ::= {meetingplaceEvents 2}

mpHwDev OBJECT-TYPE
    SYNTAX INTEGER {
        mpTemperature(1),
        mpPowerSupply(2),
        mpSerialPort(3),
        mpTapeDrive(4),
        mpHardDrive(5),
        mpDisketteDrive(6),
        mpEthernet(7),
        mpModem(8),
        mpSystemMisc(9),
        mpDSPMSC(10),
        mpDSPPRC(11),
        mpT1Blade(12),
        mpAnalogBlade(13),
        mpT1Network(14),
        mpSystemIntegrityCard(15),
        mpMainMemory(16),
        mpE1Blade(17),
        mpE1Network(18),
        mpVoIPBlade(19)
    }
    MAX-ACCESS read-only
    STATUS current
    DESCRIPTION "MeetingPlace Hardware Device Code.
                 This defines the class of device that generated a 
                 hardware fault.

                 'mpTemperature'         - Temperature Sensor
                 'mpPowerSupply'         - Power Supply
                 'mpSerialPort'          - Serial Port
                 'mpTapeDrive'           - Tape Drive
                 'mpHardDrive'           - Hard Drive
                 'mpDisketteDrive'       - Diskette Drive
                 'mpEthernet'            - Ethernet Port
                 'mpModem'               - Modem Port
                 'mpSystemMisc'          - System Misc
                 'mpDSPMSC'              - Master Switch Controller
                 'mpDSPPRC'              - Port Resource Card
                 'mpT1Blade'             - T1 Blade
                 'mpAnalogBlade'         - Analog Blade
                 'mpT1Network'           - T1 Network Interface
                 'mpSystemIntegrityCard' - System Integrity Card
                 'mpMainMemory'          - Main Memory
                 'mpE1Blade'             - E1 Blade
                 'mpE1Network'           - E1 Network Interface
                 'mpVoIPBlade'           - VoIP Blade
                "
    ::= {meetingplaceEvents 3}

mpHwUnit OBJECT-TYPE
    SYNTAX      Integer32(0..254)
    MAX-ACCESS  read-only
    STATUS      current
    DESCRIPTION "MeetingPlace Hardware Device Unit Number.
                 This is the unit number of the hardware device that
                 generated a fault.  For a disk this would be the SCSI 
                 ID.  For a blade this would the the logical card number
                 as defined in the system configuration."
    ::= {meetingplaceEvents 4} 

mpHwSlot OBJECT-TYPE
    SYNTAX      Integer32(0..254)
    MAX-ACCESS  read-only
    STATUS      current
    DESCRIPTION "MeetingPlace Hardware Device Slot Number.
                 This is the location of the hardware device that 
                 generated a fault.  For a blade this would be the slot
                 number."
    ::= {meetingplaceEvents 5} 

mpHwPort OBJECT-TYPE
    SYNTAX      Integer32(0..254)
    MAX-ACCESS  read-only
    STATUS      current
    DESCRIPTION "MeetingPlace Hardware Device Port Number.
                 This is the logical port number associated with a 
                 hardware fault.  For a T1 alarm, this is the logical 
                 span number."
    ::= {meetingplaceEvents 6} 

mpAlarmDesc OBJECT-TYPE
    SYNTAX      DisplayString (SIZE (0..128))
    MAX-ACCESS  read-only
    STATUS      current
    DESCRIPTION "MeetingPlace Alarm Description.
                 This is a one-line text description of the  exception 
                 condition.  It comprises a string indexed by the 
                 exception code filled in with context-specific values."
    ::= {meetingplaceEvents 7} 

mpT1Down NOTIFICATION-TYPE
    STATUS      current
    DESCRIPTION "MeetingPlace T1 Down Alarm.
                 This indicates generically there is a problem with a 
                 telephony port.  There are several possible alarm
                 conditions that will generate this trap.  This is from
                 Release 4.3."
    ::= { meetingplaceEventsV2 1 }

mpGWSimAlarm NOTIFICATION-TYPE
    STATUS      current
    DESCRIPTION "MeetingPlace Gateway Alarm.
                 This indicates an alarm generated by a MeetingPlace 
                 gateway.  There are several alarms that will generate 
                 this trap.  This is from Release 4.3"
    ::= { meetingplaceEventsV2 2 }

mpMajHwAlarm NOTIFICATION-TYPE
    OBJECTS
    {        
        mpExCode,
        mpSysUnit,
        mpHwDev,
        mpHwUnit,
        mpHwSlot,
        mpHwPort
    }
    STATUS      current
    DESCRIPTION "MeetingPlace Major Hardware Alarm.
                 This is generated any time MeetingPlace reports a major
                 hardware alarm."
    ::= { meetingplaceEventsV2 3 }

mpMinHwAlarm NOTIFICATION-TYPE
    OBJECTS
    {        
        mpExCode,
        mpSysUnit,
        mpHwDev,
        mpHwUnit,
        mpHwSlot,
        mpHwPort
    }
    STATUS      current
    DESCRIPTION "MeetingPlace Minor Hardware Alarm.
                 This is generated any time MeetingPlace reports
                 a minor hardware alarm."
    ::= { meetingplaceEventsV2 4 }

mpMajSwAlarm NOTIFICATION-TYPE
    OBJECTS
    {        
        mpExCode,
        mpSysUnit,
        mpAlarmDesc
    }
    STATUS      current
    DESCRIPTION "MeetingPlace Major Software Alarm.
                 This is generated any time MeetingPlace reports a major
                 software alarm."
    ::= { meetingplaceEventsV2 5 }

mpMinSwAlarm NOTIFICATION-TYPE
    OBJECTS
    {        
        mpExCode,
        mpSysUnit,
        mpAlarmDesc
    }
    STATUS      current
    DESCRIPTION "MeetingPlace Minor Software Alarm.
                 This is generated any time MeetingPlace reports
                 a minor hardware alarm."
    ::= { meetingplaceEventsV2 6 }

--
-- Compliance Definations
--

ciscoLatitudeMIBCompliances OBJECT IDENTIFIER ::= 
                                { meetingplaceConfs 1 }
ciscoLatitudeMIBGroups      OBJECT IDENTIFIER ::= 
                                { meetingplaceConfs 2 }

ciscoLatitudeMIBComplianceRev1  MODULE-COMPLIANCE
    STATUS      current
    DESCRIPTION
        "The compliance statement for entities which implement the
         MeetingPlace MIB."
    MODULE
        MANDATORY-GROUPS {
            ciscoLatitudeAlarmGroupRev1,
            ciscoLatitudeNotifsGroupRev1 }
    ::= { ciscoLatitudeMIBCompliances 1 }


ciscoLatitudeAlarmGroupRev1  OBJECT-GROUP
    OBJECTS {
        mpExCode,
        mpSysUnit,
        mpHwDev,
        mpHwUnit,
        mpHwSlot,
        mpHwPort,
        mpAlarmDesc
    }
    STATUS      current
    DESCRIPTION
        "Alarms objects within MeetingPlace."
    ::= { ciscoLatitudeMIBGroups 1 }

ciscoLatitudeNotifsGroupRev1  NOTIFICATION-GROUP
    NOTIFICATIONS {
        mpT1Down,
        mpGWSimAlarm,
        mpMajHwAlarm,
        mpMinHwAlarm,
        mpMajSwAlarm,
        mpMinSwAlarm }
    STATUS      current
    DESCRIPTION
        "Notifications applicable to meetingplace."
    ::= { ciscoLatitudeMIBGroups 2 }

END
