CYAN-GEPORT-MIB DEFINITIONS ::= BEGIN
IMPORTS
    MODULE-IDENTITY,
    OBJECT-TYPE,
    Integer32,
    Unsigned32
                    FROM SNMPv2-SMI

    DisplayString
                    FROM SNMPv2-TC

    CyanOffOnTc,
    CyanLoopbackControlTc,
    CyanTxControlTc,
    CyanOpStateTc,
    CyanSecServiceStateTc,
    CyanOpStateQualTc,
    CyanAdminStateTc,
    CyanEnDisabledTc
                    FROM CYAN-TC-MIB

    cyanEntityModules
		    FROM CYAN-MIB

    MODULE-COMPLIANCE, 
    OBJECT-GROUP
	            FROM SNMPv2-CONF;


cyanGEPortModule MODULE-IDENTITY
    LAST-UPDATED "201412070545Z" -- Sun Dec  7 05:45:29 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Gig Ethernet Port"

    REVISION     "201412070545Z" -- Sun Dec  7 05:45:29 2014
    DESCRIPTION  "Release 6.0 build 1416362081"

    ::= { cyanEntityModules 160 } 

cyanGEPortMibObjects           OBJECT IDENTIFIER ::={ cyanGEPortModule 1 }

cyanGEPortTable    OBJECT-TYPE
    SYNTAX        SEQUENCE OF CyanGEPortEntry
    MAX-ACCESS    not-accessible
    STATUS        current
    DESCRIPTION
        "A list of GEPort entries."
    ::= { cyanGEPortMibObjects 1 }

cyanGEPortEntry    OBJECT-TYPE
    SYNTAX        CyanGEPortEntry
    MAX-ACCESS    not-accessible
    STATUS        current
    DESCRIPTION
        "An entry of GEPort."
    INDEX {
        cyanGEPortShelfId ,
        cyanGEPortModuleId ,
        cyanGEPortXcvrId ,
        cyanGEPortPortId 
    }
    ::= { cyanGEPortTable 1 }

CyanGEPortEntry  ::=
    SEQUENCE {
        cyanGEPortShelfId    Unsigned32,
        cyanGEPortModuleId    Unsigned32,
        cyanGEPortXcvrId    Unsigned32,
        cyanGEPortPortId    Unsigned32,
        cyanGEPortAdminState    CyanAdminStateTc,
        cyanGEPortAutoinserviceSoakTimeSec    Integer32,
        cyanGEPortDescription    DisplayString,
        cyanGEPortExternalFiberMultishelfLink    CyanEnDisabledTc,
        cyanGEPortExternalFiberRemotePort    DisplayString,
        cyanGEPortLoopbackControl    CyanLoopbackControlTc,
        cyanGEPortOperState    CyanOpStateTc,
        cyanGEPortOperStateQual    CyanOpStateQualTc,
        cyanGEPortRxPwr    Integer32,
        cyanGEPortSecServState    CyanSecServiceStateTc,
        cyanGEPortTransmitControl    CyanTxControlTc,
        cyanGEPortTxPwr    Integer32,
        cyanGEPortTxStatus    CyanOffOnTc
    }

cyanGEPortShelfId OBJECT-TYPE
    SYNTAX       Unsigned32 (0..255)
    MAX-ACCESS   not-accessible
    STATUS       current
    DESCRIPTION
        "Shelf Id"

    ::= { cyanGEPortEntry 1 }
cyanGEPortModuleId OBJECT-TYPE
    SYNTAX       Unsigned32
    MAX-ACCESS   not-accessible
    STATUS       current
    DESCRIPTION
        "Module Id"

    ::= { cyanGEPortEntry 2 }
cyanGEPortXcvrId OBJECT-TYPE
    SYNTAX       Unsigned32
    MAX-ACCESS   not-accessible
    STATUS       current
    DESCRIPTION
        "Transceiver Id"

    ::= { cyanGEPortEntry 3 }
cyanGEPortPortId OBJECT-TYPE
    SYNTAX       Unsigned32
    MAX-ACCESS   not-accessible
    STATUS       current
    DESCRIPTION
        "Port Id"

    ::= { cyanGEPortEntry 4 }

cyanGEPortAdminState OBJECT-TYPE
    SYNTAX       CyanAdminStateTc
    MAX-ACCESS   read-only
    STATUS       current
    DESCRIPTION
        "Administrative state"

    ::= { cyanGEPortEntry 5 }

cyanGEPortAutoinserviceSoakTimeSec OBJECT-TYPE
    SYNTAX       Integer32
    MAX-ACCESS   read-only
    STATUS       current
    DESCRIPTION
        "Auto-In-Service soak time"

    ::= { cyanGEPortEntry 6 }

cyanGEPortDescription OBJECT-TYPE
    SYNTAX       DisplayString (SIZE(0..255))
    MAX-ACCESS   read-only
    STATUS       current
    DESCRIPTION
        "Description"

    ::= { cyanGEPortEntry 7 }

cyanGEPortExternalFiberMultishelfLink OBJECT-TYPE
    SYNTAX       CyanEnDisabledTc
    MAX-ACCESS   read-only
    STATUS       current
    DESCRIPTION
        "Assign a port to an inter-node link"

    ::= { cyanGEPortEntry 8 }

cyanGEPortExternalFiberRemotePort OBJECT-TYPE
    SYNTAX       DisplayString (SIZE(0..45))
    MAX-ACCESS   read-only
    STATUS       current
    DESCRIPTION
        "Remote connection point of the inter-node link"

    ::= { cyanGEPortEntry 9 }

cyanGEPortLoopbackControl OBJECT-TYPE
    SYNTAX       CyanLoopbackControlTc
    MAX-ACCESS   read-only
    STATUS       current
    DESCRIPTION
        "Port loopback control"

    ::= { cyanGEPortEntry 10 }

cyanGEPortOperState OBJECT-TYPE
    SYNTAX       CyanOpStateTc
    MAX-ACCESS   read-only
    STATUS       current
    DESCRIPTION
        "Primary Operation State"

    ::= { cyanGEPortEntry 11 }

cyanGEPortOperStateQual OBJECT-TYPE
    SYNTAX       CyanOpStateQualTc
    MAX-ACCESS   read-only
    STATUS       current
    DESCRIPTION
        "Operation state qualifier"

    ::= { cyanGEPortEntry 12 }

cyanGEPortRxPwr OBJECT-TYPE
    SYNTAX       Integer32 -- real32 * 1000
    MAX-ACCESS   read-only
    STATUS       current
    DESCRIPTION
        "RX Power"

    ::= { cyanGEPortEntry 13 }

cyanGEPortSecServState OBJECT-TYPE
    SYNTAX       CyanSecServiceStateTc
    MAX-ACCESS   read-only
    STATUS       current
    DESCRIPTION
        "Secondary service state"

    ::= { cyanGEPortEntry 14 }

cyanGEPortTransmitControl OBJECT-TYPE
    SYNTAX       CyanTxControlTc
    MAX-ACCESS   read-only
    STATUS       current
    DESCRIPTION
        "Transmitter control"

    ::= { cyanGEPortEntry 15 }

cyanGEPortTxPwr OBJECT-TYPE
    SYNTAX       Integer32 -- real32 * 1000
    MAX-ACCESS   read-only
    STATUS       current
    DESCRIPTION
        "TX Power"

    ::= { cyanGEPortEntry 16 }

cyanGEPortTxStatus OBJECT-TYPE
    SYNTAX       CyanOffOnTc
    MAX-ACCESS   read-only
    STATUS       current
    DESCRIPTION
        "Transmitter status"

    ::= { cyanGEPortEntry 17 }

cyanGEPortObjectGroup OBJECT-GROUP
    OBJECTS {
        cyanGEPortAdminState,
        cyanGEPortAutoinserviceSoakTimeSec,
        cyanGEPortDescription,
        cyanGEPortExternalFiberMultishelfLink,
        cyanGEPortExternalFiberRemotePort,
        cyanGEPortLoopbackControl,
        cyanGEPortOperState,
        cyanGEPortOperStateQual,
        cyanGEPortRxPwr,
        cyanGEPortSecServState,
        cyanGEPortTransmitControl,
        cyanGEPortTxPwr,
        cyanGEPortTxStatus
    }

    STATUS current
    DESCRIPTION        "Group of objects that comes with GEPort module"
    ::= {cyanGEPortModule 20}

cyanGEPortCompliance MODULE-COMPLIANCE
    STATUS current
    DESCRIPTION
        "The basic info needed to be a cyan GEPort"
    MODULE
    MANDATORY-GROUPS {
        cyanGEPortObjectGroup
    }
    ::= { cyanGEPortModule 30 }


END
