-- Revision 1.0.1.
-- Copyright 2000 Marconi Corporation.
-- All rights reserved.

 COMMON-GOLF-MIB

DEFINITIONS ::= BEGIN

    IMPORTS
        enterprises, IpAddress      FROM RFC1155-SMI
        OBJECT-TYPE                 FROM RFC-1212
        DisplayString, PhysAddress  FROM RFC1213-MIB;

    -- OwnerString ::= DisplayString
    -- This data type is used to model an administratively assigned name of the
    -- owner of a resource. This information is taken from the NVT ASCII charac-
    -- ter set. It is suggested that this name contain one or more of the 
    -- following:
    --  IP address, management station name, network manager's name, location,
    --  or phone number. SIZE (0..xx).

    fore          OBJECT IDENTIFIER ::= { enterprises 326 }
    systems       OBJECT IDENTIFIER ::= { fore 2 }
    ethernet      OBJECT IDENTIFIER ::= { systems 20 }

    edge          OBJECT IDENTIFIER ::= { ethernet 1 }
    edgecommon    OBJECT IDENTIFIER ::= { edge 1 }
    golf          OBJECT IDENTIFIER ::= { edge 2 }

    golfproducts  OBJECT IDENTIFIER ::= { golf 1 }
    golfcommon    OBJECT IDENTIFIER ::= { golf 2 }

    fore-mgmt               OBJECT IDENTIFIER ::= { golfcommon 2 }
    agentMgmt         OBJECT IDENTIFIER ::= { fore-mgmt 1 }

    -- ****************
    -- agentBasicInfo *
    -- ****************
    agentBasicInfo          OBJECT IDENTIFIER ::= { agentMgmt 1 }
    
    agentRuntimeSwVersion OBJECT-TYPE
        SYNTAX  DisplayString (SIZE (0..12))
        ACCESS  read-only
        STATUS  mandatory
        DESCRIPTION
            "This is a textual description for the runtime software version and
             revision. If the version number is one and revision number is zero
             agentRuntimeSwVersion would be 'Ver. 1.0'"
        ::= { agentBasicInfo 1 }

    agentPromFwVersion OBJECT-TYPE
        SYNTAX  DisplayString (SIZE (0..12))
        ACCESS  read-only
        STATUS  mandatory
        DESCRIPTION
            "This is a textual description of the agent PROM firmware version
             and revision. If the version number is one and revision number is
             zero agentPromFwVersion would be 'Ver. 1.0'"
        ::= { agentBasicInfo 2 }

    agentHwRevision OBJECT-TYPE
        SYNTAX  INTEGER
        ACCESS  read-only
        STATUS  mandatory
        DESCRIPTION
            "This is a integer number for the hardware revision."
        ::= { agentBasicInfo 3 }
    
    agentMgmtProtocolCapability OBJECT-TYPE
        SYNTAX  INTEGER {   
                    other(1),
                    snmp-ip(2),
                    snmp-ipx(3),
                    snmp-ip-ipx(4)
                }
        ACCESS  read-only
        STATUS  mandatory
        DESCRIPTION
            "The network management protocol(s) supported by this agent."
        ::= { agentBasicInfo 4 }


    -- *************************
    -- agentMibcapabilityTable *
    -- *************************

    agentMibCapabilityTable OBJECT-TYPE
        SYNTAX  SEQUENCE OF AgentMibCapabilityEntry
        ACCESS  not-accessible
        STATUS  mandatory
        DESCRIPTION
            "A list of MIB capability entries supported by this agent."    
        ::= { agentBasicInfo 5 }

    agentMibCapabilityEntry OBJECT-TYPE
        SYNTAX  AgentMibCapabilityEntry
        ACCESS  not-accessible
        STATUS  mandatory
        DESCRIPTION
            "A MIB capability entry contains objects describing a particular MIB
             supported by this agent."
        INDEX   { agentMibCapabilityIndex }
        ::= { agentMibCapabilityTable 1 }

    AgentMibCapabilityEntry ::= 
        SEQUENCE {
            agentMibCapabilityIndex
                INTEGER,
            agentMibCapabilityDescr
                DisplayString,
            agentMibCapabilityVersion
                INTEGER,
            agentMibCapabilityType
                INTEGER
        }

    agentMibCapabilityIndex OBJECT-TYPE
        SYNTAX  INTEGER 
        ACCESS  read-only
        STATUS  mandatory
        DESCRIPTION
            "A list of agentMibCapabilityDescr entries."
        ::= { agentMibCapabilityEntry 1 }

    agentMibCapabilityDescr OBJECT-TYPE
        SYNTAX  DisplayString (SIZE (0..35))
        ACCESS  read-only
        STATUS  mandatory
        DESCRIPTION
            "The name of the MIB supported by the agent."
        ::= { agentMibCapabilityEntry 2 }

    agentMibCapabilityVersion OBJECT-TYPE
        SYNTAX  INTEGER 
        ACCESS  read-only
        STATUS  mandatory
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        ACCESS  read-only
        STATUS  mandatory
        DESCRIPTION
            "The type of the MIB specified in this entry."
        ::= { agentMibCapabilityEntry 4 }


    agentStatusConsoleInUse   OBJECT-TYPE
        SYNTAX INTEGER {
               other(1),
               in-use(2),
               not-in-use(3)
               }
        ACCESS read-only
        STATUS mandatory
        DESCRIPTION
            "This indicates whether console is currently in-use."
        ::= { agentBasicInfo 6 }

    agentStatusSaveCfg OBJECT-TYPE
        SYNTAX INTEGER {
               other(1),
               proceeding(2),
               completed(3),
               changed-not-save(4),
               failed(5)
               }
        ACCESS read-only
        STATUS mandatory
        DESCRIPTION
            "This indicates the status of the device configuration.
            
            other(1) - this entry is currently in use but the conditions 
                     under which it will remain so are different from each 
                     of the following values.
            proceeding(2) - the device configuration is being currently saved into the NV-RAM.
            completed(3) - all of the device configuration parameters have been
                     saved into NV-RAM.
            changed-not-save(4) - some of the device configuration parameters have
                     been changed but not saved into NV-RAM.
            failed(5) - The process to save device configuration is failed."
        ::= { agentBasicInfo 7 }

    -- ******************
    -- agentBasicConfig *
    -- ******************
    agentBasicConfig        OBJECT IDENTIFIER ::= { agentMgmt 2 }

    agentUpdateSource OBJECT-TYPE
        SYNTAX  INTEGER {
                    other(1),
                    network-load(2),
                    out-of-band-load(3)
                }
        ACCESS  read-write
        STATUS  mandatory
        DESCRIPTION
            "The source of the runtime software or configuration file to be downloaded 
			 by the system."
        ::= { agentBasicConfig 1 }

    agentCfgUpdateCtrl OBJECT-TYPE
        SYNTAX  INTEGER {
                    other(1),
                    disabled(2),
                    enabled(3)
                }
        ACCESS  read-write
        STATUS  mandatory
        DESCRIPTION
            "This object provides the user to download configuration file. The setting 
			 will take effect when the system is restart." 
        ::= { agentBasicConfig 2 }

    agentCfgUpdateFile OBJECT-TYPE
        SYNTAX  DisplayString  (SIZE (0..64))
        ACCESS  read-write
        STATUS  mandatory
        DESCRIPTION
            "The name of the configuration file to be downloaded from the TFTP server 
            when agentCfgUpdateCtrl is set to enabled."
        ::= { agentBasicConfig 3 }

    agentSoftwareUpdateCtrl OBJECT-TYPE
        SYNTAX  INTEGER {
                    other(1),
                    disabled(2),
                    enabled(3)
                }
        ACCESS  read-write
        STATUS  mandatory
        DESCRIPTION
            "This object provides the user to download runtime software. The setting 
			  will take effect when the system is restart." 
        ::= { agentBasicConfig 4 }

    agentSoftwareUdateFile OBJECT-TYPE
        SYNTAX  DisplayString  (SIZE (0..64))
        ACCESS  read-write
        STATUS  mandatory
        DESCRIPTION
            "The name of the runtime software to be downloaded from the TFTP server 
            when agentSoftwareUpdateCtrl is set to enabled."
        ::= { agentBasicConfig 5 }

    agentSystemReset OBJECT-TYPE
        SYNTAX  INTEGER {
                    other(1),
                    cold-start(2),
                    warm-start(3),
                    no-reset(4)
                }
        ACCESS  read-write
        STATUS  mandatory
        DESCRIPTION
            "This object indicates the agent system reset state. Setting this
             object to no-reset(4) has no effect. Setting this object to
             cold-start(2) or warm-start(3) will reset the agent. The agent 
             always returns no-reset(4) when this object is read."
        ::= { agentBasicConfig 6 }

    agentRs232PortConfig OBJECT-TYPE
        SYNTAX  INTEGER  {
                    other(1),
                    console(2),
                    out-of-band(3),
					notAvail(4)
                }
        ACCESS  read-write
        STATUS  mandatory
        DESCRIPTION
            "This object indicates the RS-232C mode while device restart."
        ::= { agentBasicConfig 7 }

    agentOutOfBandBaudRateConfig OBJECT-TYPE
        SYNTAX  INTEGER {
                    other(1),
                    baudRate-2400 (2),
                    baudRate-9600 (3),
                    baudRate-19200(4),
                    baudRate-38400(5)
                }
        ACCESS  read-write
        STATUS  mandatory
        DESCRIPTION
            "This object allows user to specify out_of_band baud rate. It will take effect
			 when the system is restart."
        ::= { agentBasicConfig 8 }

     agentSaveCfg OBJECT-TYPE
        SYNTAX INTEGER
        ACCESS write-only
        STATUS mandatory
        DESCRIPTION
            "As the object is set, the current device configuration will be saved
             into to NV-RAM."
        ::= { agentBasicConfig 9 }
   
    -- ***********************
    -- agentIpProtocolConfig *
    -- ***********************
    agentIpProtoConfig      OBJECT IDENTIFIER ::= { agentMgmt 3 }

    agentIpNumOfIf OBJECT-TYPE
        SYNTAX  INTEGER
        ACCESS  read-only
        STATUS  mandatory
        DESCRIPTION
            "The total number of IP interfaces supported by this agent."
        ::= {  agentIpProtoConfig 1 }

    agentIpIfTable OBJECT-TYPE
        SYNTAX  SEQUENCE OF AgentIpIfEntry
        ACCESS  not-accessible
        STATUS  mandatory
        DESCRIPTION
            "A list of IP interface entries supported by the agent."
        ::= {  agentIpProtoConfig 2 }

    agentIpIfEntry OBJECT-TYPE
        SYNTAX  AgentIpIfEntry
        ACCESS  not-accessible
        STATUS  mandatory
        DESCRIPTION
            "An agentIPIfEntry contains information about a particular IP
             interface."
        INDEX   { agentIpIfIndex }
        ::= { agentIpIfTable 1 }

    AgentIpIfEntry ::= 
        SEQUENCE {
            agentIpIfIndex
                INTEGER,
            agentIpIfAddress 
                IpAddress,
            agentIpIfNetMask
                IpAddress,
            agentIpIfDefaultRouter
                IpAddress,
            agentIpIfMacAddr
                PhysAddress,
            agentIpIfType
                INTEGER                                                   
        }

    agentIpIfIndex OBJECT-TYPE
        SYNTAX  INTEGER (1..255)
        ACCESS  read-only
        STATUS  mandatory
        DESCRIPTION
            "This object uniquely identifies the IP interface number in the
             agentIpIfTable. This value should never greater than agentIpNumOfIf"
        ::= {  agentIpIfEntry 1 }

    agentIpIfAddress OBJECT-TYPE
        SYNTAX  IpAddress
        ACCESS  read-write
        STATUS  mandatory
        DESCRIPTION
            "The IP address of the interface."
        ::= {  agentIpIfEntry 2 }

    agentIpIfNetMask OBJECT-TYPE
        SYNTAX  IpAddress
        ACCESS  read-write
        STATUS  mandatory
        DESCRIPTION
            "The IP net mask for this interface."
        ::= {  agentIpIfEntry 3 }

    agentIpIfDefaultRouter OBJECT-TYPE
        SYNTAX  IpAddress
        ACCESS  read-write
        STATUS  mandatory
        DESCRIPTION
            "The default gateway for this IP interface."
        ::= {  agentIpIfEntry 4 }

    agentIpIfMacAddr OBJECT-TYPE
        SYNTAX  PhysAddress
        ACCESS  read-only
        STATUS  mandatory
        DESCRIPTION
            "The MAC address of this IP interface. For interfaces which do not
             have such an address. (e.g., a serial line), this object should
             contain an octet string of zero length."
        ::= {  agentIpIfEntry 5 }

    agentIpIfType OBJECT-TYPE
        SYNTAX  INTEGER {
                    other(1),          -- none of the following
                    ethernet-csmacd(6),
                    slip(28)           -- generic SLIP
                }
        ACCESS  read-only
        STATUS  mandatory
        DESCRIPTION
            "The physical layer interface of the IP interface."
        ::= {  agentIpIfEntry 6 }

    agentIpBootServerAddr OBJECT-TYPE
        SYNTAX  IpAddress
        ACCESS  read-write
        STATUS  mandatory
        DESCRIPTION
            "The IP Address of the Boot Server."
        ::= {  agentIpProtoConfig 3 }

    agentIpGetIpFromBootpServer OBJECT-TYPE
        SYNTAX  INTEGER {
                    other(1),
                    manual(2),
                    from-bootp(3),
                    from-dhcp(4)
                }
        ACCESS  read-write
        STATUS  mandatory
        DESCRIPTION
            "This object indicates whether the agent should get its system IP address
             from Bootp server at start up."
        ::= { agentIpProtoConfig 4 }

    agentIpUnauthAddr OBJECT-TYPE
        SYNTAX  IpAddress
        ACCESS  read-only
        STATUS  mandatory
        DESCRIPTION
            "The IP address of an unauthorized SNMP packet."
        ::= { agentIpProtoConfig 5 }

    agentIpUnauthComm OBJECT-TYPE
        SYNTAX  DisplayString (SIZE (0..20))
        ACCESS  read-only
        STATUS  mandatory
        DESCRIPTION
            "The community string of an unauthorized SNMP packet."
        ::= { agentIpProtoConfig 6 }

    agentIpLastBootServerAddr OBJECT-TYPE
        SYNTAX  IpAddress
        ACCESS  read-only
        STATUS  mandatory
        DESCRIPTION
           "The last IP address used by the agent as Boot server IP address."
        ::= {  agentIpProtoConfig 7 }

    agentIpLastIpAddr OBJECT-TYPE
        SYNTAX  IpAddress
        ACCESS  read-only
        STATUS  mandatory
        DESCRIPTION
            "The last IP address used by the agent as system IP address."
        ::= {  agentIpProtoConfig 8 }

    -- ************************
    -- agentIptrapMangerTable *
    -- ************************

    agentIpTrapManagerTable OBJECT-TYPE
        SYNTAX  SEQUENCE OF AgentIpTrapManagerEntry
        ACCESS  not-accessible
        STATUS  mandatory
        DESCRIPTION
            "A list of trap managers to which SNMP traps will be sent."
        ::= {  agentIpProtoConfig 9 }

    agentIpTrapManagerEntry OBJECT-TYPE
        SYNTAX  AgentIpTrapManagerEntry
        ACCESS  not-accessible
        STATUS  mandatory
        DESCRIPTION
            "Each entry contains the particular trap manager settings."
        INDEX   { agentIpTrapManagerIpAddr }
        ::= { agentIpTrapManagerTable 1 }

    AgentIpTrapManagerEntry ::= 
        SEQUENCE {
                    agentIpTrapManagerIpAddr
                        IpAddress,
                    agentIpTrapManagerComm
                        DisplayString,
                    agentIpTrapManagerStatus
                        INTEGER
        }

    agentIpTrapManagerIpAddr OBJECT-TYPE
        SYNTAX  IpAddress
        ACCESS  read-only
        STATUS  mandatory
        DESCRIPTION
            "The IP address where SNMP traps will be destined for"
        ::= { agentIpTrapManagerEntry 1 }

    agentIpTrapManagerComm OBJECT-TYPE
        SYNTAX  DisplayString (SIZE (0..20))
        ACCESS  read-write
        STATUS  mandatory
        DESCRIPTION
            "The community string used to encode SNMP trap packet to be sent to the trap
             manager."
        ::= { agentIpTrapManagerEntry 2 }

    agentIpTrapManagerStatus OBJECT-TYPE
        SYNTAX  INTEGER {
                    other(1),
                    disabled(2),
                    enabled(3)
                }
        ACCESS  read-write
        STATUS  mandatory
        DESCRIPTION
            "This object indicates whether or not the trap should be sent to
             this trap manager."
        ::= { agentIpTrapManagerEntry 3 }

END
