-- *****************************************************************
-- CISCO-VDC-CAPABILITY.my
-- CISCO-VDC-MIB agent capabilities
--   
-- July 2013, Liang Mei
--   
-- Copyright (c) 2012-2013  by Cisco Systems, Inc.
-- All rights reserved.
-- *****************************************************************

CISCO-VDC-CAPABILITY DEFINITIONS ::= BEGIN

IMPORTS
    MODULE-IDENTITY
        FROM SNMPv2-SMI
    AGENT-CAPABILITIES
        FROM SNMPv2-CONF
    ciscoAgentCapability
        FROM CISCO-SMI;


ciscoVdcCapability MODULE-IDENTITY
    LAST-UPDATED    "201307260000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "Agent capabilities for CISCO-VDC-MIB."
    REVISION        "201307260000Z"
    DESCRIPTION
        "Initial version of this MIB module."
    ::= { ciscoAgentCapability 621 }



ciscoVdcCapNxOSV06R0202PN7k AGENT-CAPABILITIES
    PRODUCT-RELEASE "Cisco NX-OS 6.2(2) on Nexus 7000 series devices."
    STATUS          current
    DESCRIPTION
        "CISCO-VDC-MIB agent capabilities."

    SUPPORTS        CISCO-VDC-MIB
    INCLUDES        {
                        ciscoVdcGroup,
                        ciscoVdcExtGroup,
                        ciscoVdcGlobalResUsageGroup,
                        ciscoVdcResUsageGroup,
                        ciscoVdcResTemplateGroup,
                        ciscoVdcGlobalGroup
                    }
    VARIATION       ciscoVdcName
    ACCESS          read-only
    DESCRIPTION
        "Write access is not supported."

    VARIATION       ciscoVdcRowStatus
    ACCESS          read-only
    DESCRIPTION
        "Write access is not supported."

    VARIATION       ciscoVdcSingleSupHaPolicy
    ACCESS          read-only
    DESCRIPTION
        "Write access is not supported."

    VARIATION       ciscoVdcDualSupHaPolicy
    ACCESS          read-only
    DESCRIPTION
        "Write access is not supported."

    VARIATION       ciscoVdcBootOrder
    ACCESS          read-only
    DESCRIPTION
        "Write access is not supported."

    VARIATION       ciscoVdcType
    ACCESS          read-only
    DESCRIPTION
        "Write access is not supported."

    VARIATION       ciscoVdcAdminStatus
    ACCESS          read-only
    DESCRIPTION
        "Write access is not supported."

    VARIATION       ciscoVdcFromUnallocatedIntf
    ACCESS          read-only
    DESCRIPTION
        "Write access is not supported."

    VARIATION       ciscoVdcFeatureSetList
    ACCESS          read-only
    DESCRIPTION
        "Write access is not supported."

    VARIATION       ciscoVdcResourceTemplate
    ACCESS          read-only
    DESCRIPTION
        "Write access is not supported."

    VARIATION       ciscoVdcModuleCapList
    ACCESS          read-only
    DESCRIPTION
        "Write access is not supported."

    VARIATION       ciscoVdcCpuPriority
    ACCESS          read-only
    DESCRIPTION
        "Write access is not supported."

    VARIATION       ciscoVdcResMin
    ACCESS          read-only
    DESCRIPTION
        "Write access is not supported."

    VARIATION       ciscoVdcResMax
    ACCESS          read-only
    DESCRIPTION
        "Write access is not supported."

    VARIATION       ciscoVdcResTemplateMin
    ACCESS          read-only
    DESCRIPTION
        "Write access is not supported."

    VARIATION       ciscoVdcResTemplateMax
    ACCESS          read-only
    DESCRIPTION
        "Write access is not supported."

    VARIATION       ciscoVdcResTemplateStorageType
    ACCESS          read-only
    DESCRIPTION
        "Write access is not supported."

    VARIATION       ciscoVdcResTemplateStatus
    ACCESS          read-only
    DESCRIPTION
        "Write access is not supported."

    VARIATION       ciscoVdcCombinedHostnameEnabled
    ACCESS          read-only
    DESCRIPTION
        "Write access is not supported."

    ::= { ciscoVdcCapability 1 }

END
