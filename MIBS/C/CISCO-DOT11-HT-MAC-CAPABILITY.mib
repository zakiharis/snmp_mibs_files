-- *****************************************************************
-- CISCO-DOT11-HT-MAC-CAPABILITY.my:  Cisco DOT11 HT MAC MIB 
-- MIB CAPABILITIES
--
-- July 2007 -  Prasanna Viswakumar
--
-- Copyright (c) 2007 by Cisco Systems, Inc.
-- All rights reserved.
--
-- *****************************************************************

CISCO-DOT11-HT-MAC-CAPABILITY DEFINITIONS ::= BEGIN

IMPORTS
        MODULE-IDENTITY
                FROM SNMPv2-SMI
        AGENT-CAPABILITIES
                FROM SNMPv2-CONF
        TruthValue
                FROM SNMPv2-TC
        ciscoAgentCapability
                FROM CISCO-SMI;

cDot11HtMacCapability     MODULE-IDENTITY  
        LAST-UPDATED         "200707260000Z"
        ORGANIZATION         "Cisco Systems, Inc."
        CONTACT-INFO
                "            Cisco Systems
                             Customer Service

                             Postal: 170 W Tasman Drive
                             San Jose, CA  95134
                             USA
  
                             Tel: +1 800 553-NETS
 
                             E-mail: cs-wnbu-snmp@cisco.com"
        DESCRIPTION
                "Agent capabilities for CISCO-DOT11-HT-MAC-MIB"

        REVISION       "200707260000Z"
        DESCRIPTION
                "Initial version of this MIB module. "
        ::= { ciscoAgentCapability 550 }

cDot11HtMacCapabilityV12R0410BJA AGENT-CAPABILITIES    
        PRODUCT-RELEASE "Cisco IOS 12.4(10b)JA for the AP1250 802.11 
                         Access Points"
        STATUS          current
        DESCRIPTION     "Cisco DOT11 HT MAC MIB capabilities"

        SUPPORTS        CISCO-DOT11-HT-MAC-MIB
        INCLUDES        { ciscoDot11HtMacStationConfigGroup,
                          ciscoDot11HtMacOperationsGroup
                        }   

        VARIATION       cD11HtMacOperationalMCSSet
        SYNTAX          OCTET STRING (SIZE(1..2))
        DESCRIPTION
                "The implementation supports only 16 MCS rates
                and hence only a maximum of 2 bytes of information
                is supported. "

        VARIATION       cD11HtMacMIMOPowerSave
        SYNTAX          INTEGER { mimo(3) }
        DESCRIPTION
                "Only a limited set of enumerated values is 
                supported."
        
        VARIATION       cD11HtMacNDelayedBlockAckImplemented
        SYNTAX          TruthValue { false(2) }
        DESCRIPTION
                "Only a limited set of enumerated values is 
                supported."
                   
        VARIATION       cD11HtMacMaxAMSDULength
        SYNTAX          INTEGER { amsduSize7935(7935) }
        DESCRIPTION          
                "Only a limited set of enumerated values is 
                supported."

        VARIATION       cD11HtMacPSMPImplemented
        SYNTAX          TruthValue { false(2) }
        DESCRIPTION
                "Only a limited set of enumerated values is 
                supported."
        
        VARIATION       cD11HtMacSTBCControlFrameImplemented
        SYNTAX          TruthValue { false(2) }
        DESCRIPTION
                "Only a limited set of enumerated values is 
                supported."
 
        VARIATION       cD11HtMacLsigTxOpProtectImplemented
        SYNTAX          TruthValue { false(2) }
        DESCRIPTION
                "Only a limited set of enumerated values is 
                supported."

        VARIATION       cD11HtMacMaxRxAMPDUFactor
        SYNTAX          INTEGER ( 3 ) 
        DESCRIPTION
                "The implementation supports only a factor
                of 3. "

        VARIATION       cD11HtMacMPDUDensity
        SYNTAX          INTEGER { eight(8) }
        DESCRIPTION
                "Only a limited set of enumerated values is 
                supported."

        VARIATION       cD11HtMacPCOImplemented
        SYNTAX          TruthValue { false(2) }
        DESCRIPTION
                "Only a limited set of enumerated values is 
                supported."

        VARIATION       cD11HtMacTransitionTime
        SYNTAX          INTEGER { fiveThousand(5000) }
        DESCRIPTION
                "Only a limited set of enumerated values is 
                supported."

        VARIATION       cD11HtMacMCSFeedbackImplemented
        SYNTAX          INTEGER { none(1) }
        DESCRIPTION
                "Only a limited set of enumerated values is 
                supported."

        VARIATION       cD11HtMacAMSDUEnable
        SYNTAX          TruthValue { true(1) }
        ACCESS          read-only
        DESCRIPTION
                "Only a limited set of enumerated values is 
                supported. The implementation also doesn't 
                support write operations on this object. "

        VARIATION       cD11HtMacAMPDUEnable
        SYNTAX          TruthValue { true(1) }
        ACCESS          read-only
        DESCRIPTION
                "Only a limited set of enumerated values is 
                supported. The implementation also doesn't 
                support write operations on this object. "

        VARIATION       cD11HtMacOperatingMode
        ACCESS          not-implemented
        DESCRIPTION
                "This object is not supported. "

        VARIATION       cD11HtMacRIFSMode
        ACCESS          not-implemented
        DESCRIPTION
                "This object is not supported. "

        VARIATION       cD11HtMacPSMPControlledAccess
        SYNTAX          TruthValue { false(2) }
        ACCESS          read-only
        DESCRIPTION
                "Only a limited set of enumerated values is 
                supported. The implementation also doesn't 
                support write operations on this object. "

       VARIATION       cD11HtMacServiceIntervalGranularity
       SYNTAX          INTEGER ( 0 )
       ACCESS          read-only
       DESCRIPTION
               "The implementation supports '0' as the
               only value.  It also doesn't support write
               operations on this object. "

        VARIATION       cD11HtMacDualCTSProtection
        SYNTAX          TruthValue { false(2) }
        ACCESS          read-only
        DESCRIPTION
                "Only a limited set of enumerated values is 
                supported. The implementation also doesn't 
                support write operations on this object. "

        VARIATION       cD11HtMacLSigTxOpFullProtectionEnabled
        SYNTAX          TruthValue { false(2) }
        ACCESS          read-only
        DESCRIPTION
                "Only a limited set of enumerated values is 
                supported. The implementation also doesn't 
                support write operations on this object. "

        VARIATION       cD11HtMacNonGFEntitiesPresent
        SYNTAX          TruthValue { true(1) }
        ACCESS          read-only
        DESCRIPTION
                "Only a limited set of enumerated values is 
                supported. The implementation also doesn't 
                support write operations on this object. "

        VARIATION       cD11HtMacPCOActivated
        SYNTAX          TruthValue { false(2) }
        ACCESS          read-only
        DESCRIPTION
                "Only a limited set of enumerated values is 
                supported. The implementation also doesn't 
                support write operations on this object. "

        VARIATION       cD11HtMacPCO20MaxDuration
        ACCESS          not-implemented
        DESCRIPTION
                "This object is not supported. "

        VARIATION       cD11HtMacPCO40MaxDuration
        ACCESS          not-implemented
        DESCRIPTION
                "This object is not supported. "

        VARIATION       cD11HtMacPCO20MinDuration
        ACCESS          not-implemented
        DESCRIPTION
                "This object is not supported. "

        VARIATION       cD11HtMacPCO40MinDuration
        ACCESS          not-implemented
        DESCRIPTION
                "This object is not supported. "

::= { cDot11HtMacCapability 1 }

END
