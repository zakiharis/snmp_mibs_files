-- *****************************************************************
-- CISCO-BGP-POLICY-ACCOUNTING-MIB.my:  Cisco BGP-Policy Accounting MIB
--
-- November 1999, Vinod B C
--
-- Copyright (c) 2000, 2002 by cisco Systems, Inc.
-- All rights reserved.
--
-- *****************************************************************

CISCO-BGP-POLICY-ACCOUNTING-MIB DEFINITIONS ::= BEGIN

IMPORTS
        MODULE-IDENTITY, OBJECT-TYPE, Integer32,
        Counter64
                FROM SNMPv2-SMI
        MODULE-COMPLIANCE, OBJECT-GROUP
                FROM SNMPv2-CONF
        ciscoMgmt
                FROM CISCO-SMI
        ifIndex
                FROM IF-MIB;
        
ciscoBgpPolAcctMIB MODULE-IDENTITY
        LAST-UPDATED    "200207260000Z"
        ORGANIZATION    "Cisco Systems, Inc."
        CONTACT-INFO
                "       Cisco Systems
                        Customer Service

                Postal: 170 W. Tasman Drive
                        San Jose, CA  95134
                        USA

                   Tel: +1 800 553-NETS

                E-mail: cs-snmp@cisco.com"
        DESCRIPTION
                "BGP policy based accounting information"
        REVISION        "200207260000Z"
        DESCRIPTION
                "Added egress, packet and octet, counters for the BGP
                policy accounting feature."

        REVISION        "9912170000Z"
        DESCRIPTION
                "Initial version of this MIB module."
        ::= { ciscoMgmt 148 }

ciscoBgpPolAcctMIBObjects OBJECT IDENTIFIER ::= { ciscoBgpPolAcctMIB 1 }

cbpAcctTable    OBJECT-TYPE
      SYNTAX      SEQUENCE OF CbpAcctEntry
      MAX-ACCESS  not-accessible
      STATUS      current
      DESCRIPTION
        "The cbpAcctTable provides statistics about ingress and egress 
         traffic on an interface. This data could be used for purposes 
         like billing."
      ::= { ciscoBgpPolAcctMIBObjects 1 }

cbpAcctEntry OBJECT-TYPE
        SYNTAX     CbpAcctEntry
        MAX-ACCESS not-accessible
        STATUS     current
        DESCRIPTION
        "Each cbpAcctEntry provides statistics for traffic of interest
        on an ingress and/or egress interfaces. The traffic of interest 
        may be used for purposes like billing, and is referred to from 
        here on in the MIB by the term 'traffic-type', which corresponds
        to cbpAcctTrafficIndex. Traffic-types are configured by the user
        on a per interface basis.
        
        The statistics include ingress packet counts, ingress octet
        counts, egress packet counts and egress octet counts. Entries 
        are created when traffic-type is configured on an interface.
        Entries are deleted automatically when the user 
        removes the corresponding traffic-type configuration from an
        interface."
        INDEX {ifIndex, cbpAcctTrafficIndex}
        ::= { cbpAcctTable 1 }

CbpAcctEntry ::= SEQUENCE {
        cbpAcctTrafficIndex             Integer32,
        cbpAcctInPacketCount            Counter64,
        cbpAcctInOctetCount             Counter64,
        cbpAcctOutPacketCount           Counter64,
        cbpAcctOutOctetCount            Counter64
        }

cbpAcctTrafficIndex     OBJECT-TYPE
      SYNTAX       Integer32 (1..2147483647)
      MAX-ACCESS   read-only 
      STATUS       current
      DESCRIPTION
        "An integer value greater than 0, that uniquely identifies
        a traffic-type. The traffic-type has no intrinsic meaning.
        It just means the traffic coming into an interface can be
        differentiated into different types. It is up to the user to
        give meaning to and configure the various traffic-types on an 
        interface."
      ::= { cbpAcctEntry 1}

cbpAcctInPacketCount    OBJECT-TYPE
      SYNTAX       Counter64
      MAX-ACCESS   read-only
      STATUS       current
      DESCRIPTION
        "The total number of packets received for a particular
        traffic-type on an interface."
      ::= { cbpAcctEntry 2}

cbpAcctInOctetCount     OBJECT-TYPE
      SYNTAX       Counter64
      MAX-ACCESS   read-only
      STATUS       current
      DESCRIPTION
        "The total number of octets received for a particular
        traffic-type on an interface."
      ::= { cbpAcctEntry 3}

cbpAcctOutPacketCount   OBJECT-TYPE
      SYNTAX       Counter64
      MAX-ACCESS   read-only
      STATUS       current
      DESCRIPTION
        "The total number of packets transmitted for a particular
        traffic-type on an interface."
      ::= { cbpAcctEntry 4}

cbpAcctOutOctetCount    OBJECT-TYPE
      SYNTAX       Counter64
      MAX-ACCESS   read-only
      STATUS       current
      DESCRIPTION
        "The total number of octets transmitted for a particular
        traffic-type on an interface."
      ::= { cbpAcctEntry 5}

-- Conformance Information
 
ciscoBgpPolAcctMIBConformance OBJECT IDENTIFIER ::= 
                                { ciscoBgpPolAcctMIB 3 }

ciscoBgpPolAcctMIBCompliances OBJECT IDENTIFIER ::= 
                                { ciscoBgpPolAcctMIBConformance 1 }

ciscoBgpPolAcctMIBGroups      OBJECT IDENTIFIER ::= 
                                { ciscoBgpPolAcctMIBConformance 2 }

-- Compliance Statement 
ciscoBgpPolAcctMIBCompliance MODULE-COMPLIANCE
        STATUS  deprecated -- superceeded by
                           -- ciscoBgpPolAcctMIBComplianceRev1
        DESCRIPTION
                "The compliance statement for entities which implement
                this Cisco BGP-Policy Traffic Accounting MIB."
        MODULE  -- this module
                MANDATORY-GROUPS {
                                cbpAcctTableGroup
                }
        ::= { ciscoBgpPolAcctMIBCompliances 1 }
 
ciscoBgpPolAcctMIBComplianceRev1 MODULE-COMPLIANCE
        STATUS  current
        DESCRIPTION
                "The compliance statement for entities which implement
                this Cisco BGP-Policy Traffic Accounting MIB."
        MODULE  -- this module
                MANDATORY-GROUPS {
                                cbpAcctTableGroupRev1
                }
        ::= { ciscoBgpPolAcctMIBCompliances 2 }

-- units of conformance:
 
cbpAcctTableGroup OBJECT-GROUP
        OBJECTS {
                cbpAcctTrafficIndex,
                cbpAcctInPacketCount,
                cbpAcctInOctetCount
        }
        STATUS  deprecated -- superceeded by cbpAcctTableGroupRev1
        DESCRIPTION
                "A collection of objects providing customer traffic 
                related parameters."
        ::= { ciscoBgpPolAcctMIBGroups 1 }

cbpAcctTableGroupRev1 OBJECT-GROUP
        OBJECTS {
                cbpAcctTrafficIndex,
                cbpAcctInPacketCount,
                cbpAcctInOctetCount,
                cbpAcctOutPacketCount,
                cbpAcctOutOctetCount
        }
        STATUS  current
        DESCRIPTION
                "A collection of objects providing customer traffic 
                related parameters."
        ::= { ciscoBgpPolAcctMIBGroups 2 }

END
