-- *****************************************************************
-- CISCO-ERM-CAPABILITY.my: CISCO-ERM-MIB AGENT-CAPABILITIES
--
-- March 2006, Ashok Kumar A
--
-- Copyright (c) 2006 by cisco Systems, Inc.
-- All rights reserved.
-- 
-- *****************************************************************

CISCO-ERM-CAPABILITY DEFINITIONS ::= BEGIN

IMPORTS
    MODULE-IDENTITY,
    Integer32
        FROM SNMPv2-SMI
    AGENT-CAPABILITIES
        FROM SNMPv2-CONF
    ciscoAgentCapability
        FROM CISCO-SMI;

ciscoErmCapability MODULE-IDENTITY
    LAST-UPDATED  "200603090000Z"
    ORGANIZATION  "Cisco Systems, Inc."
    CONTACT-INFO  "Cisco Systems
                   Customer Service
           Postal: 170 West Tasman Drive
                   San Jose, CA 95134
                   USA
           E-mail: cs-erm@cisco.com"

    DESCRIPTION
        "Agent capabilities for CISCO-ERM-MIB"

    REVISION "200603090000Z"
    DESCRIPTION
        "Initial version of the capability MIB for the ERM MIB module"
    ::= { ciscoAgentCapability 492 }

ciscoErmCapabilityV12R02SR AGENT-CAPABILITIES

PRODUCT-RELEASE "Cisco IOS 12.2SR"
STATUS          current
DESCRIPTION     "Cisco ERM Capabilities for IOS 12.2SR"

SUPPORTS CISCO-ERM-MIB
INCLUDES { ciscoErmResOwnerGroup,
           ciscoErmResUserTypeGroup,
           ciscoErmResUserGroup,
           ciscoErmResGroupGroup,
           ciscoErmResOwnerResUserOrGroupRelationGroup,
           ciscoErmResMonitorGroup,
           ciscoErmPolicyConfigGroup,
           ciscoErmResGroupConfigGroup,
           ciscoErmNotifControlObjectsGroup,
           ciscoErmNotifObjectsGroup,
           ciscoErmPolicyViolationNotifGroup
         }

         VARIATION cermResOwnerSubTypeMaxUsage
           ACCESS not-implemented
           DESCRIPTION
               "This object is not supported for all resource owners."
 
         VARIATION cermResUserOrGroupMaxUsage
           ACCESS not-implemented
           DESCRIPTION
               "This object is not supported for all resource owners."
 
         VARIATION cermPolicyLoggingEnabled
           ACCESS not-implemented
           DESCRIPTION
               "This object is not supported since enabling or disabling
                syslog per resource policy is not yet implemented in
                the ERM infrastructure.

                By default, syslog is enabled for all resource policies.
                But the capability to selectively enable/disable syslog
                per resource policy has not been implemented. So,
                value of this object would always be 'true'."
 
         VARIATION cermPolicySnmpNotifEnabled
           ACCESS not-implemented
           DESCRIPTION
               "By default, SNMP notification is enabled for all
                resource policies. But the capability to selectively
                enable/disable SNMP notification per resource policy
                has not been implemented. So, value of this object
                would always be 'true'."
 
         VARIATION cermPolicyRisingInterval
           SYNTAX Integer32 (0..86400)
           DESCRIPTION
               "Maximum value supported is 86400."

         VARIATION cermPolicyFallingInterval
           SYNTAX Integer32 (0..86400)
           DESCRIPTION
               "Maximum value supported is 86400."

         VARIATION cermPolicyStorageType
           SYNTAX INTEGER { nonVolatile(3) }
           DESCRIPTION
               "Only nonVolatile(3) is supported."

         VARIATION cermPolicyResOwnerThreshStorageType
           SYNTAX INTEGER { nonVolatile(3) }
           DESCRIPTION
               "Only nonVolatile(3) is supported."
 
         VARIATION cermConfigResGroupStorageType
           SYNTAX INTEGER { nonVolatile(3) }
           DESCRIPTION
               "Only nonVolatile(3) is supported."
 
         VARIATION cermConfigResGroupUserStorageType
           SYNTAX INTEGER { nonVolatile(3) }
           DESCRIPTION
               "Only nonVolatile(3) is supported."
 
         VARIATION cermPolicyApplyStorageType
           SYNTAX INTEGER { nonVolatile(3) }
           DESCRIPTION
               "Only nonVolatile(3) is supported."
 
         VARIATION cermPolicyRowStatus
           SYNTAX INTEGER { active(1),
                            createAndGo(4),
                            destroy(6) } -- subset of RowStatus
           DESCRIPTION
               "notInService(2), notReady(3) and createAndWait(5)
                are not supported since their usefulness is not
                significant compared to the complexity involved
                in supporting these values."
 
         VARIATION cermPolicyResOwnerThreshRowStatus
           SYNTAX INTEGER { active(1),
                            createAndGo(4),
                            destroy(6) } -- subset of RowStatus
           DESCRIPTION
               "notInService(2), notReady(3) and createAndWait(5)
                are not supported since their usefulness is not
                significant compared to the complexity involved
                in supporting these values."
 
         VARIATION cermConfigResGroupRowStatus
           SYNTAX INTEGER { active(1),
                            createAndGo(4),
                            destroy(6) } -- subset of RowStatus
           DESCRIPTION
               "notInService(2), notReady(3) and createAndWait(5)
                are not supported since their usefulness is not
                significant compared to the complexity involved
                in supporting these values."
 
         VARIATION cermConfigResGroupUserRowStatus
           SYNTAX INTEGER { active(1),
                            createAndGo(4),
                            destroy(6) } -- subset of RowStatus
           DESCRIPTION
               "notInService(2), notReady(3) and createAndWait(5)
                are not supported since their usefulness is not
                significant compared to the complexity involved
                in supporting these values."
 
         VARIATION cermPolicyApplyRowStatus
           SYNTAX INTEGER { active(1),
                            createAndGo(4),
                            destroy(6) } -- subset of RowStatus
           DESCRIPTION
               "notInService(2), notReady(3) and createAndWait(5)
                are not supported since their usefulness is not
                significant compared to the complexity involved
                in supporting these values."
 
    ::= { ciscoErmCapability 1 }

END
