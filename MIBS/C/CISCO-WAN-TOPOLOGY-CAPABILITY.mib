-- *****************************************************************
-- ciscoWanTopologyCapabilities MIB
--
-- AGENT-CAPABILITIES mib for CISCO-WAN-TOPOLOGY-MIB in Cisco MGX8800
-- series and other Products.
--
-- Copyright 2001,2002,2003 by Cisco Systems,Inc.
--
-- Author: Shawn Hsu
-- *****************************************************************

CISCO-WAN-TOPOLOGY-CAPABILITY DEFINITIONS ::= BEGIN

IMPORTS
        MODULE-IDENTITY
                FROM SNMPv2-SMI
        AGENT-CAPABILITIES
                FROM SNMPv2-CONF
        ciscoAgentCapability
                FROM CISCO-SMI;   

ciscoWanTopologyCapability MODULE-IDENTITY
        LAST-UPDATED    "200301150000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
           "The Agent Capabilities for CISCO-WAN-TOPOLOGY-MIB.
	    This MIB is used in the MGX8850 product family, which
            contains the MGX8850 and MGX8950 switches."

        REVISION "200301150000Z"
        DESCRIPTION
           "- Added ciscoWanTopologyV4R0000 capability for release
              4.0.00."

        REVISION "200210310000Z"
        DESCRIPTION
           "- Replace the objects cwtLanIP and cwtAtmIP in
              ciscoWanTopologyCapabilityV3R00 with objects
              cwtPrimIPIfType, cwtPrimIPIfName, cwtPrimIPAddrType,
              cwtPrimIP, cwtSecIPIfType, cwtSecIPIfName,
              cwtSecIPAddrType, cwtSecIP.

            - Added ciscoWanTopologyV3R0020 capability for release
              3.0.20."

        REVISION "200110100000Z"
        DESCRIPTION
           "Initial version of this MIB module."
        ::= { ciscoAgentCapability 254 }

ciscoWanTopologyCapabilityV3R00 AGENT-CAPABILITIES
    PRODUCT-RELEASE      "MGX8850 and BPX-SES Release 3.00"
    STATUS               current
    DESCRIPTION          "Persistent Topology MIB Capabilities."

    SUPPORTS CISCO-WAN-TOPOLOGY-MIB
	INCLUDES {   
                   cwtSystemMIBGroups,
                   cwtNodalMIBGroups
                 }

    VARIATION   cwtGatewayNodeFlag 
    ACCESS      read-only
    DESCRIPTION "write and create are not supported."

    VARIATION   cwtNodeId 
    ACCESS      read-only
    DESCRIPTION "write and create are not supported."

    VARIATION   cwtNodeName 
    ACCESS      read-only
    DESCRIPTION "write and create are not supported."

    VARIATION   cwtPrimIPIfType
    ACCESS      read-only
    DESCRIPTION "write and create are not supported."

    VARIATION   cwtPrimIPIfName
    ACCESS      read-only
    DESCRIPTION "write and create are not supported."

    VARIATION   cwtPrimIPAddrType
    ACCESS      read-only
    DESCRIPTION "write and create are not supported."

    VARIATION   cwtPrimIP
    ACCESS      read-only
    DESCRIPTION "write and create are not supported."

    VARIATION   cwtSecIPIfType
    ACCESS      read-only
    DESCRIPTION "write and create are not supported."

    VARIATION   cwtSecIPIfName
    ACCESS      read-only
    DESCRIPTION "write and create are not supported."

    VARIATION   cwtSecIPAddrType
    ACCESS      read-only
    DESCRIPTION "write and create are not supported."

    VARIATION   cwtSecIP
    ACCESS      read-only
    DESCRIPTION "write and create are not supported."

    VARIATION   cwtSysObjId
    ACCESS      read-only
    DESCRIPTION "write and create are not supported."

    VARIATION   cwtDBLastChange 
    ACCESS      not-implemented
    DESCRIPTION "Not supported."

    VARIATION   cwtNodeInfoTimeOutFlag 
    ACCESS      not-implemented
    DESCRIPTION "Not supported."

    VARIATION   cwtRowStatus 
    SYNTAX      INTEGER {
	           active(1),
	           destroy(6)
	        }
    DESCRIPTION "Does not support values notInService(2), notReady(3),
	         createAndGo(4), createAndWait(5)."

    ::= { ciscoWanTopologyCapability 1 }


ciscoWanTopologyCapabilityV3R0020 AGENT-CAPABILITIES
    PRODUCT-RELEASE      "MGX8850 and BPX-SES Release 3.0.20"
    STATUS               current
    DESCRIPTION          "Persistent Topology MIB Capabilities."

    SUPPORTS CISCO-WAN-TOPOLOGY-MIB
	INCLUDES {   
                   cwtSystemMIBGroups,
                   cwtNodalMIBGroups,
                   cwtFeederMIBGroups
                 }

    VARIATION   cwtGatewayNodeFlag 
    ACCESS      read-only
    DESCRIPTION "write and create are not supported."

    VARIATION   cwtNodeId 
    ACCESS      read-only
    DESCRIPTION "write and create are not supported."

    VARIATION   cwtNodeName 
    ACCESS      read-only
    DESCRIPTION "write and create are not supported."

    VARIATION   cwtPrimIPIfType
    ACCESS      read-only
    DESCRIPTION "write and create are not supported."

    VARIATION   cwtPrimIPIfName
    ACCESS      read-only
    DESCRIPTION "write and create are not supported."

    VARIATION   cwtPrimIPAddrType
    ACCESS      read-only
    DESCRIPTION "write and create are not supported."

    VARIATION   cwtPrimIP
    ACCESS      read-only
    DESCRIPTION "write and create are not supported."

    VARIATION   cwtSecIPIfType
    ACCESS      read-only
    DESCRIPTION "write and create are not supported."

    VARIATION   cwtSecIPIfName
    ACCESS      read-only
    DESCRIPTION "write and create are not supported."

    VARIATION   cwtSecIPAddrType
    ACCESS      read-only
    DESCRIPTION "write and create are not supported."

    VARIATION   cwtSecIP
    ACCESS      read-only
    DESCRIPTION "write and create are not supported."

    VARIATION   cwtSysObjId
    ACCESS      read-only
    DESCRIPTION "write and create are not supported."

    VARIATION   cwtDBLastChange 
    ACCESS      not-implemented
    DESCRIPTION "Not supported."

    VARIATION   cwtNodeInfoTimeOutFlag 
    ACCESS      not-implemented
    DESCRIPTION "Not supported."

    VARIATION   cwtRowStatus 
    SYNTAX      INTEGER {
	           active(1),
	           destroy(6)
	        }
    DESCRIPTION "Does not support values notInService(2), notReady(3),
	         createAndGo(4), createAndWait(5)."

    VARIATION   cwtFeederRowStatus 
    SYNTAX      INTEGER {
	           active(1) 
	        }

    DESCRIPTION "Does not support values notInService(2), notReady(3),
	         createAndGo(4), createAndWait(5), destroy(6)."

    ::= { ciscoWanTopologyCapability 2 }

ciscoWanTopologyCapabilityV4R0000 AGENT-CAPABILITIES
    PRODUCT-RELEASE      "MGX8850 and BPX-SES Release 4.0.00"
    STATUS               current
    DESCRIPTION          "Persistent Topology MIB Capabilities."

    SUPPORTS CISCO-WAN-TOPOLOGY-MIB
	INCLUDES {   
                   cwtSystemMIBGroups,
                   cwtNodalMIBGroups,
                   cwtFeederMIBGroups,
                   cwtLinkMIBGroups
                 }


    VARIATION   cwtGatewayNodeFlag 
    ACCESS      read-only
    DESCRIPTION "write and create are not supported."

    VARIATION   cwtNodeId 
    ACCESS      read-only
    DESCRIPTION "write and create are not supported."

    VARIATION   cwtNodeName 
    ACCESS      read-only
    DESCRIPTION "write and create are not supported."

    VARIATION   cwtPrimIPIfType
    ACCESS      read-only
    DESCRIPTION "write and create are not supported."

    VARIATION   cwtPrimIPIfName
    ACCESS      read-only
    DESCRIPTION "write and create are not supported."

    VARIATION   cwtPrimIPAddrType
    ACCESS      read-only
    DESCRIPTION "write and create are not supported."

    VARIATION   cwtPrimIP
    ACCESS      read-only
    DESCRIPTION "write and create are not supported."

    VARIATION   cwtSecIPIfType
    ACCESS      read-only
    DESCRIPTION "write and create are not supported."

    VARIATION   cwtSecIPIfName
    ACCESS      read-only
    DESCRIPTION "write and create are not supported."

    VARIATION   cwtSecIPAddrType
    ACCESS      read-only
    DESCRIPTION "write and create are not supported."

    VARIATION   cwtSecIP
    ACCESS      read-only
    DESCRIPTION "write and create are not supported."

    VARIATION   cwtSysObjId
    ACCESS      read-only
    DESCRIPTION "write and create are not supported."

    VARIATION   cwtDBLastChange 
    ACCESS      not-implemented
    DESCRIPTION "Not supported."

    VARIATION   cwtNodeInfoTimeOutFlag 
    ACCESS      not-implemented
    DESCRIPTION "Not supported."

    VARIATION   cwtRowStatus 
    SYNTAX      INTEGER {
	           active(1),
	           destroy(6)
	        }
    DESCRIPTION "Does not support values notInService(2), notReady(3),
	         createAndGo(4), createAndWait(5)."

    VARIATION   cwtFeederRowStatus 
    SYNTAX      INTEGER {
	           active(1) 
	        }

    DESCRIPTION "Does not support values notInService(2), notReady(3),
	         createAndGo(4), createAndWait(5), destroy(6)."

    VARIATION   cwtLinkLocalNodeId
    ACCESS      read-only
    DESCRIPTION "write and create are not supported."

    VARIATION   cwtLinkRemoteNodeId
    ACCESS      read-only
    DESCRIPTION "write and create are not supported."

    VARIATION   cwtLinkLocalIfIndex
    ACCESS      read-only
    DESCRIPTION "write and create are not supported."

    VARIATION   cwtLinkRemoteIfIndex
    ACCESS      read-only
    DESCRIPTION "write and create are not supported."

    VARIATION   cwtLinkLocalPhysicalId
    ACCESS      read-only
    DESCRIPTION "write and create are not supported."

    VARIATION   cwtLinkRemotePhysicalId
    ACCESS      not-implemented
    DESCRIPTION "Not supported."

    VARIATION   cwtLinkInfoTimeOutFlag
    ACCESS      not-implemented
    DESCRIPTION "Not supported."

    VARIATION   cwtLinkOutsideLink
    ACCESS      read-only
    DESCRIPTION "write and create are not supported."

    VARIATION   cwtLinkRowStatus
    SYNTAX      INTEGER {
	           active(1)
	        }
    DESCRIPTION "Does not support values notInService(2), notReady(3),
	         createAndGo(4), createAndWait(5), destroy(6)."

    ::= { ciscoWanTopologyCapability 3 }

END
