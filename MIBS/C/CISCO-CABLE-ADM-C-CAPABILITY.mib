-- *****************************************************************
-- CISCO-CABLE-ADM-C-CAPABILITY.my: 
--                      CISCO-CABLE-ADMISSION-CTRL-MIB
--                      AGENT-CAPABILITIES
--                       
-- Dec 2004, Westcott Suen
--
-- Copyright (c) 2004-2005 by Cisco Systems, Inc.
-- All rights reserved.
-- *****************************************************************

CISCO-CABLE-ADM-C-CAPABILITY DEFINITIONS ::= BEGIN

IMPORTS
    MODULE-IDENTITY, Unsigned32
        FROM SNMPv2-SMI
    AGENT-CAPABILITIES
        FROM SNMPv2-CONF
    ciscoAgentCapability
        FROM CISCO-SMI;


ciscoCableAdmCtrlCapability MODULE-IDENTITY
                LAST-UPDATED "200412110000Z"
        ORGANIZATION "Cisco Systems, Inc."
        CONTACT-INFO
            "         Cisco Systems
                      Customer Service

            Postal:   Cisco Systems
                      170 West Tasman Drive
                      San Jose, CA 95134
                      U.S.A.
            Phone:    +1 800 553-NETS
            E-mail:   cs-ubr@cisco.com"

        DESCRIPTION
            "Agent capabilities for CISCO-CABLE-ADMISSION-CTR-MIB"
           
        REVISION     "200412110000Z"
        DESCRIPTION
            "This is the initial version."
        ::= { ciscoAgentCapability 427 }


ciscoCableAdmCtrlCapabilityV12R00 AGENT-CAPABILITIES

PRODUCT-RELEASE "Cisco IOS 12.3BC"
STATUS      current
DESCRIPTION "Cisco Cable Admission Control MIB capabilities."

SUPPORTS    CISCO-CABLE-ADMISSION-CTRL-MIB
INCLUDES    { ciscoCableAdmCtrlEventHistGroup
            }

VARIATION       ccacEventHistTableSize
SYNTAX          Unsigned32 (0..5000)
DESCRIPTION     "The maximum size of the event history table is 
		 presently restricted to 5000."
    ::= { ciscoCableAdmCtrlCapability 1 }

END
