-- **************************************************************************  
-- CISCO-WIRELESS-P2MP-PHY-MIB.my:  Cisco Wireless Radio Point to 
--                                  MultiPoint MIB.
--
-- January 2000, Allan Figueredo
--
-- Copyright (c) 2000 by Cisco Systems, Inc.
-- All rights reserved.
-- 
-- **************************************************************************
--
-- **************************************************************************
--
--
--
-- 1.0 Glossary
--
-- The following terms are used in the MIB definitions below.
--
-- Radio Interface:  The radio interface that provides wireless communication 
--                   features.
-- Radio Link:       The bi-directional wireless link that exists between two
--                   communicating wireless radios. 
-- Radio PHY:        Represents the transmission characteristics of the Radio 
--                   Link.
-- RF Unit:          The Radio Frequency components and associated antennas.
-- ALC:              Automatic Line Control
-- SU:               Subscriber Unit
--
--
-- 2.0 Cisco Wireless MIB Organization
--
-- The Cisco Wireless Point to Multipoint Radio PHY MIB is divided into 3 main
-- groups.
--     Radio Base   Objects in this group are present on the Head end and  
--                  also the Subscriber unit.
--     Head End     Objects in this group are only supported on the Head end.
--     Subscriber   Objects in this group are only supported on the Subscriber 
--                     unit.
-- 
-- 2.1 Radio Base
--
-- This group is supported on the head end as well as the subscriber unit.
-- It consists of the following groups.
-- 
-- o.  PHY (physical) Config
--          This group allows the user to configure self-test, cable loss,
--          external reference clock, enable diversity antenna, etc.
--
-- o.  Frequency Resource 
--          This contains information about the Radio frequency transmission
--          and reception resources available on the system. This group 
--          determines the portions of the radio spectrum at which the radio
--          subsystem can operate.
--
-- o.  Test Group 
--          This provides facilities to establish loopback at various points
--          in the hardware for diagnostic purposes.
--
-- o.  Notification Group 
--          It provides the list of traps that the wireless system will
--          generate.  The traps defined in this group are common to both
--          the Head end and the subscriber unit.
--
-- 2.2 Head End
--
--     This group of objects are only supported on the head end and lets the
--     user configure the Automatic Line Control (ALC).  It also provides
--     information about the state of the Intermediate Frequency module.
--
-- 2.3 Subscriber Unit
--
--     This group of objects are only supported on the subscriber unit.  
--     They enable the user enable/disable transmission at the subscriber end,
--     and track the power measured at the different possible center
--     frequencies at power up.
--
--
-- 3.0   MIB Definitions
--
--
 

CISCO-WIRELESS-P2MP-PHY-MIB DEFINITIONS ::= BEGIN

	IMPORTS
	MODULE-IDENTITY, OBJECT-TYPE,
	Integer32, NOTIFICATION-TYPE 
		FROM SNMPv2-SMI
	DisplayString, TruthValue 
		FROM SNMPv2-TC

--      MODULE-COMPLIANCE, OBJECT-GROUP, NOTIFICATION-GROUP
	MODULE-COMPLIANCE, OBJECT-GROUP
                FROM SNMPv2-CONF
        ifIndex
		FROM IF-MIB
	CwrOscState, CwrRfType, CwrRfFreqRange
		FROM CISCO-WIRELESS-TC-MIB
        Unsigned32
                FROM CISCO-TC
        entPhysicalIndex
                FROM ENTITY-MIB
	ciscoMgmt
		FROM CISCO-SMI;

	ciscoWirelessPhyMIB MODULE-IDENTITY
           LAST-UPDATED "200010221910Z"
           ORGANIZATION "Cisco Systems Inc."
           CONTACT-INFO
	   "	Cisco Systems
		Customer Service

	   Postal: 170 W Tasman Drive
		   San Jose, CA  95134
		   USA

		   Tel: +1 800 553-NETS
	           E-mail: wireless-nms@cisco.com"
            DESCRIPTION
	        "This is the MIB Module for the Cisco Wireless Radio 
                 Point to MultiPoint interface."
        REVISION  "200010221910Z"
        DESCRIPTION
                "Changed propWirelessDocsMAC to 
                 propDocsWirelessMaclayer"
        REVISION  "200010041910Z"
        DESCRIPTION
                "Fixed minor typo in spelling of Duplexer
                 Changed valid range for p2mpSuMeasuredPower"
        REVISION  "200007211910Z"
        DESCRIPTION
                "Redefined p2mpDenyService 
                 Redefined p2mpLoopbackTable
                 Added a second index for p2mpSuPowerScanTable"
       ::= { ciscoMgmt 170}

--
-- The Cisco Wireless P2MP Radio MIB Tree
-- 

p2mpRadioObjects       OBJECT IDENTIFIER ::= { ciscoWirelessPhyMIB 1 }
p2mpRadioBaseObjects   OBJECT IDENTIFIER ::= { p2mpRadioObjects 1 }
p2mpRadioSuObjects     OBJECT IDENTIFIER ::= { p2mpRadioObjects 2 }
p2mpRadioHeObjects     OBJECT IDENTIFIER ::= { p2mpRadioObjects 3 }

p2mpPhyConfigGroup     OBJECT IDENTIFIER ::= { p2mpRadioBaseObjects 1 }
p2mpFreqResourceGroup  OBJECT IDENTIFIER ::= { p2mpRadioBaseObjects 2 }
p2mpRadioTestGroup     OBJECT IDENTIFIER ::= { p2mpRadioBaseObjects 3 }
p2mpLedGroup           OBJECT IDENTIFIER ::= { p2mpRadioBaseObjects 4 }

--
--

    p2mpRadioPhyTable OBJECT-TYPE
        SYNTAX SEQUENCE OF P2mpRadioPhyEntry
        MAX-ACCESS not-accessible
        STATUS current
        DESCRIPTION
	        "This table provides facilities to configure the physical
	        layer characteristics of the radio link.
                The objects in this table are supported on the head end and 
                at the subscriber unit."
        ::= { p2mpPhyConfigGroup 1 }

    p2mpRadioPhyEntry OBJECT-TYPE
        SYNTAX P2mpRadioPhyEntry
        MAX-ACCESS not-accessible
        STATUS current
        DESCRIPTION
                "The entry of this table is created when the managed system
                detects a propDocsWirelessMaclayer interface. The entry 
                is removed when the associated propDocsWirelessMaclayer 
                interface is deleted from the ifTable."
        INDEX     { ifIndex }
        ::= { p2mpRadioPhyTable 1 }

    P2mpRadioPhyEntry ::= SEQUENCE {
	p2mpSelfTest                TruthValue,
	p2mpDiversityAntennaPresent TruthValue,
        p2mpCableLoss               Unsigned32,
        p2mpCableLossDiversity      Unsigned32,
	p2mpClockRefExt             TruthValue, 
        p2mpDenyService             TruthValue,
	p2mpCommonTrapEnable        TruthValue,
	p2mpLastPhyFailureType      INTEGER,
        p2mpLastPhyFailureReason    DisplayString 
    }

    p2mpSelfTest OBJECT-TYPE
        SYNTAX TruthValue
        MAX-ACCESS read-write
        STATUS current
        DESCRIPTION
                "This object is used to enable/disable self test.  When set to 
                true(1), the software tests the memory and hardware integrity
                shortly after the router powers up."
        ::= { p2mpRadioPhyEntry 1 }

    p2mpDiversityAntennaPresent OBJECT-TYPE
        SYNTAX TruthValue
        MAX-ACCESS read-write
        STATUS current
        DESCRIPTION
                "When true(1), this object indicates that a diversity
                antenna is being used to receive the wireless transmissions.
                When false(2), the radio system is using a single antenna
                to transmit and receive."
        ::= { p2mpRadioPhyEntry 2 }

    p2mpCableLoss OBJECT-TYPE
        SYNTAX Unsigned32 (0..15)
	UNITS "dB"
        MAX-ACCESS read-write
        STATUS current
        DESCRIPTION
                "This object indicates the measured signal power loss in dB
                due to the cable connecting the radio to the main antenna.
                The hardware compensates for this cable loss by adjusting the
                receive and transmit gain appropriately.  A value of 0 
                indicates no degradation in the signal due to the cable.  The 
                radio hardware can compensate for a cable loss of no more 
                than 15 db.
                This cable loss applies to the main antenna only."
        ::= { p2mpRadioPhyEntry 3 }

    p2mpCableLossDiversity OBJECT-TYPE
        SYNTAX Unsigned32 (0..15)
	UNITS "dB"
        MAX-ACCESS read-write
        STATUS current
        DESCRIPTION
                "This object indicates the measured signal power loss in dB 
                due to the cable connecting the radio to the diversity 
                antenna.  The hardware compensates for this loss by adjusting 
                the receive and transmit gain appropriately.  A value of 0 
                indicates no degradation in the signal due to the cable.  The 
                radio hardware can compensate for a cable loss of no more 
                than 15 dB. 
                This cable loss applies to the diversity antenna only."
        ::= { p2mpRadioPhyEntry 4 }

    p2mpDenyService OBJECT-TYPE
        SYNTAX TruthValue
        MAX-ACCESS read-only
        STATUS current
        DESCRIPTION
                "Indicates if the service is disabled in the unit.
                For Head-end unit, if this object has the value of 
                'true', the link is in loopback mode; otherwise the 
                link is enabled for transmitting / receiving data.
                For Subscriber unit, if this object has the value of 
                'true', the subscriber unit service is disabled; 
                otherwise, the subscriber unit is enabled for 
                transmitting / receiving data"
        ::= { p2mpRadioPhyEntry 5 }

    p2mpClockRefExt OBJECT-TYPE
        SYNTAX TruthValue
        MAX-ACCESS read-write
        STATUS current
        DESCRIPTION
                "This object controls the use of external reference 
                clock for IF module as follows:
                'true(1)'  - an external reference clock is used
                'false(2)' - an internal reference clock is used."
        ::= { p2mpRadioPhyEntry 6 }
 
    p2mpCommonTrapEnable OBJECT-TYPE
        SYNTAX TruthValue
        MAX-ACCESS read-write
        STATUS current
        DESCRIPTION
                "When set to true(1), the notifications common to the head end 
                and subscriber unit are enabled.  When set to false(2), these 
                notifications are disabled.
                The notification controlled by this object are: 
                  - p2mpRadioPhyFailNotification
                  - p2mpTrapRfSupplyVoltage
                  - p2mpTrapRfRxOsc
                  - p2mpTrapRfTxOsc
                  - p2mpTrapRfTemp
                  - p2mpTrapRfCommLinkError
                  - p2mpTrapTxPower
                  - p2mpTrapRfStatusChange"
        DEFVAL   { true }
        ::= { p2mpRadioPhyEntry 7 }

    p2mpLastPhyFailureType OBJECT-TYPE
        SYNTAX INTEGER {
                  none(1),
                  p2mpHwConfigUnsupported(2),
                  p2mpHwConfigMismatch(3),
                  p2mpHwInitFailure(4),
                  p2mpHostIfCommLinkError(5),
                  p2mpAutoCableCompFailure(6)
               }
        MAX-ACCESS read-only
        STATUS current
        DESCRIPTION
                "This object indicates the last physical link failure that 
                resulted in a p2mpRadioPhyFailNotification trap.
 
                    none(1) - no failure
 
                    p2mpHwConfigUnsupported(2) - The radio subsystem has 
                       detected that the configuration requested is not 
                       supported by the hardware.  The p2mpLastPhyFailureReason
                       variable will indicate which configuration parameter is
                       not supported.
 
                    p2mpHwConfigMismatch(3) - The radio subsystem has detected 
                       that the combination of the configuration parameters 
                       requested is inconsistent and cannot be supported.
                       The p2mpLastPhyFailReason variable will indicate the 
                       configuration parameter that causes the mismatch.
 
                    p2mpHwInitFailure(4) - The radio subsystem has failed to 
                       initialize the hardware. This implies that there is a 
                       critical error condition in the associated hardware. 
                       The p2mpLastPhyFailReason specifies the reason why the 
                       init failed.
 
                    p2mpHostIfCommLinkError(5) - The host could not communicate 
                       with the IF module.
 
                    p2mpAutoCableCompFailure(6) - Failed to achieve automatic 
                       cable compensation due to loss of Tx signal."
        ::= { p2mpRadioPhyEntry 8 }

    p2mpLastPhyFailureReason OBJECT-TYPE
        SYNTAX DisplayString (SIZE(0..255))
        MAX-ACCESS read-only
        STATUS current
        DESCRIPTION
	        "This is a text string that describes the last physical link
                failure identified by p2mpLastPhyFailureType."
        ::= { p2mpRadioPhyEntry 9 }

--
--      Frequency Resource Group    
--
--      This group is supported on the head end and at the subscriber unit.
--
-- 

    p2mpRfTable OBJECT-TYPE
        SYNTAX SEQUENCE OF P2mpRfEntry
        MAX-ACCESS not-accessible
        STATUS current
        DESCRIPTION
                "This table contains information about the state of the radio 
	        frequency resources used by the radio system.

	        Physically each RF resource may be realized by one antenna and 
                its associated control hardware. A single antenna and its 
                associated electronics may act as more than 1 RF resource. When
                an RF resource acts as both a transmit and receive resource,
                the transmit and receive frequency ranges may overlap."
        ::= { p2mpFreqResourceGroup 1 }

    p2mpRfEntry OBJECT-TYPE
        SYNTAX P2mpRfEntry
        MAX-ACCESS not-accessible
        STATUS current
        DESCRIPTION
                "This represents one entry in the p2mpRfTable.  
	
                An entry is created in this table when the managed system 
                detects a RF resource. The entry is removed when the RF 
                resource is removed from the wireless system."
        INDEX { ifIndex, p2mpRfIndex }
        ::= { p2mpRfTable 1 }

    P2mpRfEntry ::= SEQUENCE {
	p2mpRfIndex                     Integer32,
        p2mpRfType                      CwrRfType,
	p2mpRfOpMode                    INTEGER,
	p2mpTxFreqRangeMin	        CwrRfFreqRange,
	p2mpTxFreqRangeMax              CwrRfFreqRange,
	p2mpRxFreqRangeMin              CwrRfFreqRange,
	p2mpRxFreqRangeMax              CwrRfFreqRange,
	p2mpMinTxPower                  Integer32,
        p2mpMaxTxPower                  Integer32,
	p2mpRfTemperature		Integer32,
	p2mpRfTxOscState		CwrOscState,
	p2mpRfRxOscState		CwrOscState,
	p2mpRfSupplyVoltageState        INTEGER,
	p2mpRfStatus			INTEGER,
        p2mpRfLoopbackSupported         TruthValue
        }

    p2mpRfIndex OBJECT-TYPE
        SYNTAX Integer32 (1..100)
        MAX-ACCESS not-accessible
        STATUS current
        DESCRIPTION
	        "This object, along with the ifIndex of the MAC layer, 
                represents the index of this entry in the p2mpRfTable. 
                Each entry in the table provides details on the state of  
                the RF resources available in the system."
        ::= { p2mpRfEntry 1 }

    p2mpRfType OBJECT-TYPE
        SYNTAX CwrRfType
        MAX-ACCESS read-only
        STATUS current
        DESCRIPTION
                "This object identifies the RF resource."
        ::= { p2mpRfEntry 2 }
 
    p2mpRfOpMode OBJECT-TYPE
        SYNTAX INTEGER {
                receiveOnly(1),
                transmitOnly(2),
                transmitAndReceive(3)
                }
        MAX-ACCESS read-only
        STATUS current
        DESCRIPTION
	        "This object specifies whether this RF resource can either
                transmit, receive, or do both." 
        ::= { p2mpRfEntry 3 }

    p2mpTxFreqRangeMin OBJECT-TYPE
        SYNTAX CwrRfFreqRange
	UNITS "KHz"
        MAX-ACCESS read-only
        STATUS current
        DESCRIPTION
	        "This object represents the minimum frequency at which this RF 
	        resource can transmit."
        ::= { p2mpRfEntry 4 }

    p2mpTxFreqRangeMax OBJECT-TYPE
        SYNTAX CwrRfFreqRange
	UNITS "KHz"
        MAX-ACCESS read-only
        STATUS current
        DESCRIPTION
	        "This object represents the maximum frequency at which this RF 
	        resource can transmit."
        ::= { p2mpRfEntry 5 }

    p2mpRxFreqRangeMin OBJECT-TYPE
        SYNTAX CwrRfFreqRange
	UNITS "KHz"
        MAX-ACCESS read-only
        STATUS current
        DESCRIPTION
	        "This object represents the lowest transmission frequency this 
	        RF resource can receive. "
        ::= { p2mpRfEntry 6 }

    p2mpRxFreqRangeMax OBJECT-TYPE
        SYNTAX CwrRfFreqRange
	UNITS "KHz"
        MAX-ACCESS read-only
        STATUS current
        DESCRIPTION
	        "This object represents the highest transmission frequency that 
	        this RF resource can receive."
        ::= { p2mpRfEntry 7 }

    p2mpMinTxPower OBJECT-TYPE
        SYNTAX Integer32 (-80..50)
	UNITS "dBm"
        MAX-ACCESS read-only
        STATUS current
        DESCRIPTION
                "This object represents the minimum power that the RF subsystem
	        can supply the antenna. "
        ::= { p2mpRfEntry 8 }

    p2mpMaxTxPower OBJECT-TYPE
        SYNTAX Integer32 (-80..50)
	UNITS "dBm"
        MAX-ACCESS read-only
        STATUS current
        DESCRIPTION
                "This object represents the maximum power that the RF subsystem
	        can supply the antenna."
        ::= { p2mpRfEntry 9 }

    p2mpRfTemperature OBJECT-TYPE
        SYNTAX Integer32 (-40..100)
	UNITS "Degrees Centigrade"
        MAX-ACCESS read-only
        STATUS current
        DESCRIPTION
                "This object represents the current temperature of the RF unit"
        ::= { p2mpRfEntry 10 }

    p2mpRfTxOscState OBJECT-TYPE
        SYNTAX CwrOscState
        MAX-ACCESS read-only
        STATUS current
        DESCRIPTION
	        "This object represents the state of the transmit oscillator. 
	        The oscillator must be in oscillatorOk(1) state for the system 
                to function properly."
        ::= { p2mpRfEntry 11 }

    p2mpRfRxOscState OBJECT-TYPE
        SYNTAX CwrOscState
        MAX-ACCESS read-only
        STATUS current
        DESCRIPTION
	        "This object represents the state of the receive oscillator. 
	        The oscillator must be in oscillatorOk(1) state for the system
	        to function properly."
        ::= { p2mpRfEntry 12 }

    p2mpRfSupplyVoltageState OBJECT-TYPE
        SYNTAX INTEGER {
		withinSpecification(1),
		outsideSpecification(2)
		}
        MAX-ACCESS read-only
        STATUS current
        DESCRIPTION
	        "This object specifies whether the voltage supply to the RF 
             	unit is within specifications or not.  Voltage specifications
                are hardware dependent."
        ::= { p2mpRfEntry 13 }

    p2mpRfStatus OBJECT-TYPE
        SYNTAX INTEGER {
		online(1),
		offline(2)
		}
        MAX-ACCESS read-only
        STATUS current
        DESCRIPTION
	        "This object specifies whether the RF resource is functioning 
	        properly. If it is functioning properly then it will be 
                online(1), else offline(2).
                At the Subscriber Unit, this object will reflect offline(2) 
                if p2mpTxMuteEnable in the p2mpSuRadioPhyTable is true(1)." 
        ::= { p2mpRfEntry 14 }

    p2mpRfLoopbackSupported OBJECT-TYPE
        SYNTAX TruthValue
        MAX-ACCESS read-only
        STATUS current
        DESCRIPTION
	        "This object indicates if the RF unit supports loopback.
                When true(1), the user can configure loopback using the 
                objects in p2mpLoopbackTable. When false(2), any attempt
                to configure RF loopback will fail. "
        ::= { p2mpRfEntry 15 }


--
--
    p2mpDuplexerTable OBJECT-TYPE
        SYNTAX SEQUENCE OF P2mpDuplexerEntry
        MAX-ACCESS not-accessible
        STATUS current
        DESCRIPTION
                "This table contains information about the Duplexers
                available for use on the system.
 
                A Duplexer is a mechanical device, that acts as a band 
                pass filter when installed in an RF resource.
 
                Normally a RF resource is capable of operating over a wide
                frequency range. To operate at restricted frequencies, the user
                has to own that part of the frequency spectrum.  Since the user
                may not own parts of the frequency spectrum over which the RF
                resource may operate, a duplexer is installed at the RF.
                This restricts the RF resource to operate in the passband
                defined by the duplexer."
        ::= { p2mpFreqResourceGroup 2 }
 
    p2mpDuplexerEntry OBJECT-TYPE
        SYNTAX P2mpDuplexerEntry
        MAX-ACCESS not-accessible
        STATUS current
        DESCRIPTION
                "This represents one entry in the p2mpDuplexerTable. 
                Each entry contains information about the duplexers 
                capabilities and the associated RF resource.
 
                An entry is created in this table when the managed system
                detects a RF resource. The entry is removed when the RF
                resource is removed from the wireless system."
        INDEX { ifIndex, p2mpDuplexerIndex }
        ::= { p2mpDuplexerTable 1 }
 
    P2mpDuplexerEntry ::= SEQUENCE {
        p2mpDuplexerIndex               Integer32,
        p2mpDuplexerRF                  CwrRfType,
        p2mpDuplexerLoPassbandMinFreq   CwrRfFreqRange,
        p2mpDuplexerLoPassbandMaxFreq   CwrRfFreqRange,
        p2mpDuplexerHiPassbandMinFreq   CwrRfFreqRange,
        p2mpDuplexerHiPassbandMaxFreq   CwrRfFreqRange,
        p2mpDuplexerReceivePassband     INTEGER,
        p2mpDuplexerTxInsertionLoss     Integer32,
        p2mpDuplexerBurnDate            DisplayString
        }
 
    p2mpDuplexerIndex OBJECT-TYPE
        SYNTAX Integer32 (1..100)
        MAX-ACCESS not-accessible
        STATUS current
        DESCRIPTION
                "This object, along with ifIndex, uniquely identifies 
                an entry in this table.  Each entry contains 
                information about the duplexer's capabilities and also 
                identifies the associated RF resource."
        ::= { p2mpDuplexerEntry 1 }
 
    p2mpDuplexerRF OBJECT-TYPE
        SYNTAX CwrRfType
        MAX-ACCESS read-only
        STATUS current
        DESCRIPTION
                "This object identifies the RF resource associated with this
                duplexer."
        ::= { p2mpDuplexerEntry 2 }
 
   p2mpDuplexerLoPassbandMinFreq OBJECT-TYPE
        SYNTAX CwrRfFreqRange
	UNITS "MHz"
        MAX-ACCESS read-only
        STATUS current
        DESCRIPTION
                "This object identifies the minimum frequency in the low
                passband that this duplexer will pass through without 
                attenuation."
        ::= { p2mpDuplexerEntry 3 }
 
    p2mpDuplexerLoPassbandMaxFreq OBJECT-TYPE
        SYNTAX CwrRfFreqRange
	UNITS "MHz"
        MAX-ACCESS read-only
        STATUS current
        DESCRIPTION
                "This object identifies the maximum frequency in the low
                passband that this duplexer will pass through without 
                attenuation."
        ::= { p2mpDuplexerEntry 4 }
 
    p2mpDuplexerHiPassbandMinFreq OBJECT-TYPE
        SYNTAX CwrRfFreqRange
	UNITS "MHz"
        MAX-ACCESS read-only
        STATUS current
        DESCRIPTION
                "This object identifies the minimum frequency in the high
                passband that this duplexer will pass through without 
                attenuation."
        ::= { p2mpDuplexerEntry 5 }
 
    p2mpDuplexerHiPassbandMaxFreq OBJECT-TYPE
        SYNTAX CwrRfFreqRange
	UNITS "MHz"
        MAX-ACCESS read-only
        STATUS current
        DESCRIPTION
                "This object identifies the maximum frequency in the high
                passband that this duplexer will pass through without 
                attenuation."
        ::= { p2mpDuplexerEntry 6 }
 
    p2mpDuplexerReceivePassband OBJECT-TYPE
        SYNTAX INTEGER {
                   loPassband(1),
                   hiPassband(2)
                   }
        MAX-ACCESS read-only
        STATUS current
        DESCRIPTION
                "This object indicates which of the two passbands are being used
                 to receive transmissions.  The RF Resource can receive on
                 either of the duplexer passbands.
 
                 loPassband(1) - The RF Resource is receiving on a frequency
                                 in the low passband.
                 hiPassband(2) - The RF Resource is receiving on a frequency
                                 in the high passband."
        ::= { p2mpDuplexerEntry 7 }
 
   p2mpDuplexerTxInsertionLoss OBJECT-TYPE
        SYNTAX Integer32
	UNITS "dB"
        MAX-ACCESS read-only
        STATUS current
        DESCRIPTION
                "This object represents the loss in 'dB' that would result in 
                the transmission path due to the duplexer." 
        ::= { p2mpDuplexerEntry 8 }
 
    p2mpDuplexerBurnDate OBJECT-TYPE
        SYNTAX DisplayString
        MAX-ACCESS read-only
        STATUS current
        DESCRIPTION
                "This object indicates the date when the revision information
                was programmed into non-volatile memory."
        ::= { p2mpDuplexerEntry 9 }

--
-- 

    p2mpAntennaTable OBJECT-TYPE
        SYNTAX SEQUENCE OF P2mpAntennaEntry
        MAX-ACCESS not-accessible
        STATUS current
        DESCRIPTION
                "This table contains information about the antennas available 
	        in the system."
        ::= { p2mpFreqResourceGroup 3 }

    p2mpAntennaEntry OBJECT-TYPE
        SYNTAX P2mpAntennaEntry
        MAX-ACCESS not-accessible
        STATUS current
        DESCRIPTION
                "An entry is created in this table when the managed system 
                detects a RF resource. The entry is removed when the RF 
                resource is removed from the wireless system."
        INDEX { ifIndex, p2mpAntennaIndex }
        ::= { p2mpAntennaTable 1 }

    P2mpAntennaEntry ::= SEQUENCE {
	p2mpAntennaIndex	     Unsigned32,
        p2mpRfResource               CwrRfType,
	p2mpAntennaXDim		     Unsigned32,
	p2mpAntennaYDim              Unsigned32,
	p2mpAntennaType		     DisplayString, 
        p2mpAntennaDescr             DisplayString,
	p2mpAntennaGain		     Unsigned32,
	p2mpAntennaPolarization      INTEGER
        }

    p2mpAntennaIndex OBJECT-TYPE
        SYNTAX Unsigned32
        MAX-ACCESS not-accessible
        STATUS current
        DESCRIPTION
	        "This object, along with ifIndex, represents the index of this 
                entry in the p2mpAntennaTable."
        ::= { p2mpAntennaEntry 1 }

    p2mpRfResource OBJECT-TYPE
        SYNTAX CwrRfType
        MAX-ACCESS read-only
        STATUS current
        DESCRIPTION
                "This object identifies if the antenna is connected to the main
                or the diversity RF resource."
        ::= { p2mpAntennaEntry 2 }
 
    p2mpAntennaXDim OBJECT-TYPE
        SYNTAX Unsigned32(1..96)
	UNITS "Inches"
        MAX-ACCESS read-write
        STATUS current
        DESCRIPTION
	        "This object represents the dimension of the antenna in the
                X direction."
        ::= { p2mpAntennaEntry 3 }

    p2mpAntennaYDim OBJECT-TYPE
        SYNTAX Unsigned32 (1..96)
	UNITS "Inches"
        MAX-ACCESS read-write
        STATUS current
        DESCRIPTION
	        "This object represents the dimension of the antenna in the
                Y direction."
        ::= { p2mpAntennaEntry 4 }

    p2mpAntennaType OBJECT-TYPE
        SYNTAX DisplayString (SIZE(0..64))
        MAX-ACCESS read-write
        STATUS current
        DESCRIPTION
	        "This object represents the antenna type. For example, 
                'dish-antenna'."
        ::= { p2mpAntennaEntry 5 }

    p2mpAntennaDescr OBJECT-TYPE
        SYNTAX DisplayString (SIZE(0..64))
        MAX-ACCESS read-write
        STATUS current
        DESCRIPTION
	        "This object is used to describe the antenna.  For example,
                it could be used to identify the manufacturer like in
                'Manufactured by Watkins Johnson'."
        ::= { p2mpAntennaEntry 6 }

    p2mpAntennaGain OBJECT-TYPE
        SYNTAX Unsigned32 (0..60)
	UNITS "dBi : decibel Isotropic"
        MAX-ACCESS read-write
        STATUS current
        DESCRIPTION
	        "This object represents the receive and transmit gain 
                 of this antenna."
        ::= { p2mpAntennaEntry 7 }

    p2mpAntennaPolarization OBJECT-TYPE
        SYNTAX INTEGER {
		vertical(1),
		horizontal(2)
	}
        MAX-ACCESS read-only
        STATUS current
        DESCRIPTION
	        "This object represents the polarization of the antanna."
        ::= { p2mpAntennaEntry 8 }

--
-- The Test Group.  This group is optional
--
 
 
    p2mpLoopbackTable OBJECT-TYPE
        SYNTAX SEQUENCE OF P2mpLoopbackEntry
        MAX-ACCESS not-accessible
        STATUS current
        DESCRIPTION
                "This table provides facilities to establish loopback points to
                exercise various sections of the hardware."
        ::= { p2mpRadioTestGroup 1 }
 
    p2mpLoopbackEntry OBJECT-TYPE
        SYNTAX P2mpLoopbackEntry
        MAX-ACCESS not-accessible
        STATUS current
        DESCRIPTION
                "This represents one entry in the p2mpLoopbackTable.  It
                is created when the managed system detects a 
                propDocsWirelessMaclayer interface. The entry is removed
                when the associated propDocsWirelessMaclayer interface 
                is deleted from the ifTable."
        INDEX { ifIndex }
        ::= { p2mpLoopbackTable 1 }
 
    P2mpLoopbackEntry ::= SEQUENCE {
        p2mpLocalLoopbackMode       INTEGER,
        p2mpLocalLoopbackAntenna    CwrRfType,
        p2mpLocalLoopbackChannel    Unsigned32
        }
 
    p2mpLocalLoopbackMode OBJECT-TYPE
        SYNTAX INTEGER {
                  noLoopback(1),
                  fir(2),
                  if(3),
                  rf(4)
               }
        MAX-ACCESS read-write
        STATUS current
        DESCRIPTION
                "This object is used to configure the system in loopback mode 
                prior to executing some system diagnostic tests.  The user 
                selects the point in the system where the data signal should be
                looped back.  The diagnostic tests outlined in the user manual
                have to be manually executed to determine success or failure.  
                Once all the tests are completed, normal operation is restored
                by setting this object to noLoopback(1).
 
                noLoopback(1)  - no loopback
                fir(2)         - loopback at the Finite Impulse 
                                 Response (FIR) module.
                if(3)          - loopback at the IF module.  This 
                                 exercises the FIR, and IF modules.
                rf(4)          - loopback at the RF unit. This 
                                 exercises the FIR, IF, and RF modules.
                                 This mode is supported only when
                                 p2mpRfLoopbackSupported is true(1)."
        DEFVAL  { noLoopback }
        ::= { p2mpLoopbackEntry 1 }

    p2mpLocalLoopbackAntenna OBJECT-TYPE
        SYNTAX CwrRfType
        MAX-ACCESS read-write
        STATUS current
        DESCRIPTION
                "This object identifies the RF resource used for 
                loopback testing.  This object is not applicable for 
                loopback testing when p2mpLocalLoopbackMode has a 
                value of 'noLoopback(1)'."
        ::= { p2mpLoopbackEntry 2 }
 
    p2mpLocalLoopbackChannel OBJECT-TYPE
        SYNTAX Unsigned32 (1..7)
        MAX-ACCESS read-write
        STATUS current
        DESCRIPTION
                "This object identifies the channel being used to  
                loopback the data.  This object is not applicable 
                for loopback testing when p2mpLocalLoopbackMode has 
                a value of 'noLoopback(1)'."
        ::= { p2mpLoopbackEntry 3 }
 

--
--  The LED Group.
--
--      This group is supported on the head end and at the subscriber unit.


 
    p2mpLedTable OBJECT-TYPE
        SYNTAX     SEQUENCE OF P2mpLedEntry
        MAX-ACCESS not-accessible
        STATUS     current
        DESCRIPTION
                "Entity (Light emitting diode) LED information.  For each LED on
                the entity, an entry will exist in this table, describing the
                location and current status of that LED."
        ::= { p2mpLedGroup 1 }
 
    p2mpLedEntry OBJECT-TYPE
        SYNTAX     P2mpLedEntry
        MAX-ACCESS not-accessible
        STATUS     current
        DESCRIPTION
                "An entry in the table, containing the LED information.
                The entPhysicalIndex identifies the entity on which the LED's
                are present."
        INDEX { entPhysicalIndex, p2mpLedIndex }
        ::= { p2mpLedTable 1 }
 
    P2mpLedEntry ::=
        SEQUENCE {
           p2mpLedIndex                  Integer32,
           p2mpLedType                   INTEGER,
           p2mpLedState                  INTEGER
        }

    p2mpLedIndex OBJECT-TYPE
         SYNTAX      Integer32 (1..16)
         MAX-ACCESS  not-accessible
         STATUS      current
         DESCRIPTION
                 "For a given entPhysicalIndex, this index value uniquely
                 identifies an entry in the p2mpLedTable."
         ::= { p2mpLedEntry 1 }
 
    p2mpLedType OBJECT-TYPE
        SYNTAX  INTEGER {
                   interfaceEnable(0),
                   majorAlarm(1),
                   minorAlarm(2),
                   outOfService(3),
                   carrier(4),
                   transmitData(5),
                   receiveData(6)
                }
        MAX-ACCESS read-only
        STATUS     current
        DESCRIPTION
                "Indicates the type or label of the LED."
        ::= { p2mpLedEntry 2 }
 
    p2mpLedState  OBJECT-TYPE
        SYNTAX INTEGER {
                off(0),
                green(1),
                yellow(2)
        }
        MAX-ACCESS read-only
        STATUS     current
        DESCRIPTION
                "Indicates the state of the LED."
        ::= { p2mpLedEntry 3 }
 
 
--
--   SUBSCRIBER UNIT ONLY!!!!!
--

    p2mpSuRadioPhyTable OBJECT-TYPE
        SYNTAX SEQUENCE OF P2mpSuRadioPhyEntry
        MAX-ACCESS not-accessible
        STATUS current
        DESCRIPTION
                "This table contains information about the currently configured
	        physical layer interfaces in the subscriber unit."
        ::= { p2mpRadioSuObjects 1}

    p2mpSuRadioPhyEntry OBJECT-TYPE
        SYNTAX    P2mpSuRadioPhyEntry
        MAX-ACCESS    not-accessible
        STATUS    current
        DESCRIPTION
                "An entry containing the radio configuration information
                 of the propDocsWirelessMaclayer interface in the 
                 subscriber unit.

                 The entry is created when a propDocsWirelessMaclayer
                 interface is detected in the subscriber unit. The entry
                 is deleted when the associated propDocsWirelessMaclayer
                 interface is removed."
        INDEX     { ifIndex }
        ::= { p2mpSuRadioPhyTable 1 }

    P2mpSuRadioPhyEntry ::= SEQUENCE {
        p2mpSuTxMuteEnable         TruthValue,
        p2mpSuTxMuteDuration       Unsigned32
        }
 
    p2mpSuTxMuteEnable OBJECT-TYPE
        SYNTAX TruthValue
        MAX-ACCESS read-only
        STATUS current
        DESCRIPTION
                "When true(1), this object indicates the subscriber unit 
                transmission has been turned off for a duration indicated by
                p2mpSuTxMuteDuration.  When false(2), this object indicates 
                that the subscriber unit is transmitting."
        ::= { p2mpSuRadioPhyEntry 1 }

    p2mpSuTxMuteDuration OBJECT-TYPE
        SYNTAX Unsigned32 (1..65535)
	UNITS "minutes"
        MAX-ACCESS read-write
        STATUS current
        DESCRIPTION
                " This object indicates the duration of time (in minutes) 
                for which the subscriber transmission will be turned off. "
        ::= { p2mpSuRadioPhyEntry 2 }

--
--      The Power Scan Table. 

    p2mpSuPowerScanTable OBJECT-TYPE
        SYNTAX SEQUENCE OF P2mpSuPowerScanEntry
        MAX-ACCESS not-accessible
        STATUS current
        DESCRIPTION
                "This table contains information about the receive power 
                measured at the different possible center frequencies."
        ::= { p2mpRadioSuObjects 2}

    p2mpSuPowerScanEntry OBJECT-TYPE
        SYNTAX    P2mpSuPowerScanEntry
        MAX-ACCESS    not-accessible
        STATUS    current
        DESCRIPTION
                "An entry containing the power related status 
                information of the propDocsWirelessMaclayer 
                interface in the subscriber unit.

                The entry is created when a propDocsWirelessMaclayer 
                interface is detected in the subscriber unit. The entry 
                is deleted after the associated propDocsWirelessMaylayer
                interface is removed."
        INDEX     { ifIndex, p2mpSuPowerScanIndex }
        ::= { p2mpSuPowerScanTable 1 }

    P2mpSuPowerScanEntry ::= SEQUENCE {
        p2mpSuPowerScanIndex     Integer32,
        p2mpSuCenterFrequency    CwrRfFreqRange,
        p2mpSuMeasuredPower      Integer32
        }

    p2mpSuPowerScanIndex OBJECT-TYPE
         SYNTAX      Integer32 (1..20)
         MAX-ACCESS  not-accessible
         STATUS      current
         DESCRIPTION
                 "For a given ifIndex, this index value uniquely
                 identifies an entry in the p2mpSuPowerScanTable."
        ::= { p2mpSuPowerScanEntry 1 }
 
    p2mpSuCenterFrequency OBJECT-TYPE
        SYNTAX CwrRfFreqRange
        UNITS "KHz"
        MAX-ACCESS read-only
        STATUS current
        DESCRIPTION
                "This object indicates the frequency at which the receive power
                at the subscriber unit was measured."
        ::= { p2mpSuPowerScanEntry 2 }

    p2mpSuMeasuredPower OBJECT-TYPE
        SYNTAX Integer32 (-127..50)
        UNITS "dBm"
        MAX-ACCESS read-only
        STATUS current
        DESCRIPTION
                "This object represents the power measured at the frequency 
                indicated by p2mpSuCenterFrequency."
        ::= { p2mpSuPowerScanEntry 3 }


--
--   HEAD END ONLY!!!!!
--
    
    p2mpHeAlcTable OBJECT-TYPE
        SYNTAX SEQUENCE OF P2mpHeAlcEntry
        MAX-ACCESS not-accessible
        STATUS current
        DESCRIPTION
                "This table contains Automatic Line Control (ALC) configuration 
                information.  It is supported at the head end only."
        ::= { p2mpRadioHeObjects 1}

    p2mpHeAlcEntry OBJECT-TYPE
        SYNTAX    P2mpHeAlcEntry
        MAX-ACCESS    not-accessible
        STATUS    current
        DESCRIPTION
                "An entry containing the ALC configuration information 
                the propDocsWirelessMaylayer interface at the head end.

                The entry is created when a propDocsWirelessMaclayer 
                interface is detected in the head end unit. The entry is
                deleted after the associated propDocsWirelessMaclayer 
                interface is removed."
        INDEX     { ifIndex }
        ::= { p2mpHeAlcTable 1 }

    P2mpHeAlcEntry ::= SEQUENCE {
        p2mpHeAlcEnable            TruthValue,
        p2mpHeAlcInterval          Unsigned32,
        p2mpHeAlcNumMiniSlots      Unsigned32
        }

    p2mpHeAlcEnable OBJECT-TYPE
        SYNTAX TruthValue
        MAX-ACCESS read-write
        STATUS current
        DESCRIPTION
                "This object is used to enable/disable ALC at the Head End.  A
                value of true(1), indicates that ALC is enabled."
        ::= { p2mpHeAlcEntry 1 }

    p2mpHeAlcInterval OBJECT-TYPE
        SYNTAX Unsigned32 (32..1024)
	UNITS "milliseconds"
        MAX-ACCESS read-write
        STATUS current
        DESCRIPTION
                "This object represents the scheduling interval.  It is the
                regular interval at which the ALC grant in Map is transmitted 
                to the SU's"
        ::= { p2mpHeAlcEntry 2 }

    p2mpHeAlcNumMiniSlots OBJECT-TYPE
        SYNTAX Unsigned32 (1..4)
        MAX-ACCESS read-write
        STATUS current
        DESCRIPTION
                "This indicates the number of minislots within each grant."
        ::= { p2mpHeAlcEntry 3 }

--
--      The Intermediate Frequency Resource table.
--

    p2mpHeIntFreqTable OBJECT-TYPE
        SYNTAX SEQUENCE OF P2mpHeIntFreqEntry
        MAX-ACCESS not-accessible
        STATUS current
        DESCRIPTION
                "This table contains information about the state of the 
	        intermediate frequency subsystem in the radio system.  This
                table is supported at the head end only."
        ::= { p2mpRadioHeObjects 2}

    p2mpHeIntFreqEntry OBJECT-TYPE
        SYNTAX P2mpHeIntFreqEntry
        MAX-ACCESS not-accessible
        STATUS current
        DESCRIPTION
                "The entry of this table is created when the managed system 
                detects a propDocsWirelessMaclayer interface in the head
                end unit. 
                The entry is deleted when the associated 
                propDocsWirelessMaclayer interface is removed."
        INDEX { ifIndex }
        ::= { p2mpHeIntFreqTable 1 }

    P2mpHeIntFreqEntry ::= SEQUENCE {
	p2mpHeIfTxOscState	CwrOscState,
	p2mpHeIfRxOscState	CwrOscState,
	p2mpHeIfRefOscState	CwrOscState,
	p2mpHeIfInpFreq		Unsigned32,
        p2mpHeIfOutFreq		Unsigned32,
	p2mpHeTrapEnable        TruthValue
        }

    p2mpHeIfTxOscState OBJECT-TYPE
        SYNTAX CwrOscState
        MAX-ACCESS read-only
        STATUS current
        DESCRIPTION
	        "This object indicates the state of the IF transmit oscillator.
	        The oscillator must be in oscillatorOk(1) state for the system 
                to function properly."
        ::= { p2mpHeIntFreqEntry 1 }

    p2mpHeIfRxOscState OBJECT-TYPE
        SYNTAX CwrOscState
        MAX-ACCESS read-only
        STATUS current
        DESCRIPTION
	        "This object indicates the state of the IF receive oscillator. 
	        The oscillator must be in oscillatorOk(1) state for the system 
                to function properly."
        ::= { p2mpHeIntFreqEntry 2 }

    p2mpHeIfRefOscState OBJECT-TYPE
        SYNTAX CwrOscState
        MAX-ACCESS read-only
        STATUS current
        DESCRIPTION
	       "This object indicates the state of the IF reference oscillator.
	       The oscillator must be in oscillatorOk(1) state for the system 
	       to function properly."
        ::= { p2mpHeIntFreqEntry 3 }

    p2mpHeIfInpFreq OBJECT-TYPE
        SYNTAX Unsigned32(1000..500000)
	UNITS "KHz"
        MAX-ACCESS read-only
        STATUS current
        DESCRIPTION
                "This object represents the IF input frequency."
        ::= { p2mpHeIntFreqEntry  4 }

    p2mpHeIfOutFreq OBJECT-TYPE
        SYNTAX Unsigned32(1000..500000)
	UNITS "KHz"
        MAX-ACCESS read-only
        STATUS current
        DESCRIPTION
                "This object represents the IF output frequency."
        ::= { p2mpHeIntFreqEntry 5 }

    p2mpHeTrapEnable OBJECT-TYPE
        SYNTAX TruthValue
        MAX-ACCESS read-write
        STATUS current
        DESCRIPTION
                "When set to true(1), this enables the notifications
                that are specific to the head end. When set to false(2), 
                these notifications are disabled."
        DEFVAL  { true }
        ::= { p2mpHeIntFreqEntry 6 }

 

-- The following two OBJECT IDENTIFIERS are used to define SNMPv2
-- Notifications that are backward compatible with SNMPv1 Traps.

p2mpPhyMIBNotificationPrefix OBJECT IDENTIFIER ::= {ciscoWirelessPhyMIB 2} 
p2mpPhyMIBNotification OBJECT IDENTIFIER ::= {p2mpPhyMIBNotificationPrefix 0}


--
-- The following traps are generated by the radio system. These traps are not
-- in response to any threshold specification that might have been defined.
--

    p2mpRadioPhyFailNotification NOTIFICATION-TYPE
        OBJECTS {
             p2mpLastPhyFailureType,
             p2mpLastPhyFailureReason
        }
        STATUS  current
        DESCRIPTION
                "A p2mpRadioPhyFailNotification is sent if the value of
                p2mpLastPhyFailureType changes due to the new failure 
                being detected in the Radio interface."
        ::= { p2mpPhyMIBNotification 1 }
 
    p2mpTrapRfSupplyVoltage NOTIFICATION-TYPE
	OBJECTS { p2mpRfSupplyVoltageState }
	STATUS current
	DESCRIPTION
	        "The supply voltage to the RF resource has changed. 
	        The p2mpRfSupplyVoltageState specifies whether the supply 
	        voltage is in spec or not."
        ::= { p2mpPhyMIBNotification 2 }

    p2mpTrapRfRxOsc NOTIFICATION-TYPE
	OBJECTS { p2mpRfRxOscState }
	STATUS current
	DESCRIPTION
	        "The RF receive frequency oscillator has changed state.
	        The p2mpRfRxOscState specifies the current state of 
                the oscillator."
        ::= { p2mpPhyMIBNotification 3 }

    p2mpTrapRfTxOsc NOTIFICATION-TYPE
	OBJECTS { p2mpRfTxOscState }
	STATUS current
	DESCRIPTION
	       "The RF transmit frequency oscillator has changed state.
	       The p2mpRfRxOscState specifies the state of the 
	       oscillator."
        ::= { p2mpPhyMIBNotification 4 }

    p2mpTrapRfTemp NOTIFICATION-TYPE
	OBJECTS { p2mpRfTemperature }
	STATUS current
	DESCRIPTION
	        "The temperature of the RF module identified by p2mpRfIndex
	        has exceeded a defined reference."
        ::= { p2mpPhyMIBNotification 5 }

    p2mpTrapRfCommLinkError NOTIFICATION-TYPE
        OBJECTS { p2mpRfType }
        STATUS current
        DESCRIPTION
        "This trap indicates that the host and the IF module cannot 
        communicate with the RF resource identified by p2mpRfType."
        ::= { p2mpPhyMIBNotification 6 }
 
    p2mpTrapTxPower NOTIFICATION-TYPE
        OBJECTS { p2mpRfType }
        STATUS current
        DESCRIPTION
        "This trap indicates that the transmit power for the RF resource 
        identified by p2mpRfType exceeded a predefined threshold."
        ::= { p2mpPhyMIBNotification 7 }
 
    p2mpTrapRfStatusChange NOTIFICATION-TYPE
	OBJECTS { p2mpRfStatus }
	STATUS current
	DESCRIPTION
	        "This trap indicates that the RF resource either came online(1)
	        or went offline(2)." 
        ::= { p2mpPhyMIBNotification 8 }

    p2mpTrapHeIfRxOsc NOTIFICATION-TYPE
	OBJECTS { p2mpHeIfRxOscState }
	STATUS current
	DESCRIPTION
	"The IF receive frequency oscillator has changed state."
        ::= { p2mpPhyMIBNotification 9 }

    p2mpTrapHeIfTxOsc NOTIFICATION-TYPE
	OBJECTS { p2mpHeIfTxOscState }
	STATUS current
	DESCRIPTION
	"The IF transmit frequency oscillator has changed state."
        ::= { p2mpPhyMIBNotification 10 }

    p2mpTrapHeIfExtRefOsc NOTIFICATION-TYPE
	OBJECTS { p2mpHeIfRefOscState }
	STATUS current
	DESCRIPTION
	"The IF Reference Frequency oscillator has changed state."
        ::= { p2mpPhyMIBNotification 11 }



-- ============================================================================
--
-- Conformance
--
 
p2mpRadioPhyConformance  OBJECT IDENTIFIER ::= { p2mpRadioObjects 4 }
p2mpRadioPhyCompliances  OBJECT IDENTIFIER ::= { p2mpRadioPhyConformance 1 }
p2mpRadioPhyGroups       OBJECT IDENTIFIER ::= { p2mpRadioPhyConformance 2 }
 
-- Compliance 

p2mpRadioPhyCompliance MODULE-COMPLIANCE
        STATUS      current
        DESCRIPTION
            "The compliance statement for devices that implement Point to 
            Multipoint wireless interfaces compliant with the Cisco Systems 
            Inc. specification."
        MODULE  -- ciscoWirelessPhyMIB

        MANDATORY-GROUPS {
                p2mpCommonRadioGroup,
                p2mpCommonRfGroup,
                p2mpCommonTestGroup
--                p2mpCommonNotificationGroup
                }

        GROUP p2mpRadioSuGroup
                DESCRIPTION
                "This group is mandatory for a system that supports the 
                radio subscriber unit feature. It is not implemented at 
                the Head End."

        GROUP p2mpRadioHeGroup
                DESCRIPTION
                "This group is mandatory for a system that supports the 
                radio head end feature. It is not implemented at the 
                Subscriber Unit."

--        GROUP p2mpHeOnlyNotificationGroup
--                DESCRIPTION
--                "This group is mandatory for a system that supports the
--                radio head end feature. It is not implemented at the  
--                Subscriber Unit."

        GROUP p2mpRadioAntennaGroup
                DESCRIPTION
                "This group is optional for a system that supports the 
                radio antenna management feature on Head end or 
                subscriber unit."
 
        ::= { p2mpRadioPhyCompliances 1 }


-- Units of Conformance
 
p2mpCommonRadioGroup OBJECT-GROUP
        OBJECTS {
                p2mpSelfTest,
                p2mpDiversityAntennaPresent,
                p2mpCableLoss,
                p2mpCableLossDiversity,
                p2mpDenyService,
                p2mpClockRefExt,
                p2mpCommonTrapEnable,
                p2mpLastPhyFailureType,
                p2mpLastPhyFailureReason,
                p2mpLedType,
                p2mpLedState
                }
        STATUS      current
        DESCRIPTION
        "Mandatory group of objects implemented to configure a 
         point to multipoint wireless radio."
        ::= { p2mpRadioPhyGroups 1 }

p2mpCommonRfGroup OBJECT-GROUP
        OBJECTS {
                p2mpRfType,
                p2mpRfOpMode,
                p2mpTxFreqRangeMin,
                p2mpTxFreqRangeMax,
                p2mpRxFreqRangeMin,
                p2mpRxFreqRangeMax,
                p2mpMinTxPower,
                p2mpMaxTxPower,
                p2mpRfTxOscState,
                p2mpRfRxOscState,
                p2mpRfTemperature,
                p2mpRfSupplyVoltageState,
                p2mpRfStatus,
                p2mpRfLoopbackSupported,
                p2mpDuplexerRF,
                p2mpDuplexerLoPassbandMinFreq ,
                p2mpDuplexerLoPassbandMaxFreq,
                p2mpDuplexerHiPassbandMinFreq,
                p2mpDuplexerHiPassbandMaxFreq,
                p2mpDuplexerReceivePassband,
                p2mpDuplexerTxInsertionLoss,
                p2mpDuplexerBurnDate
                }
        STATUS      current
        DESCRIPTION
        "Mandatory group of objects implemented to tune the phy quality 
        in a point to multipoint wireless radio."
        ::= { p2mpRadioPhyGroups 2 }

p2mpCommonTestGroup OBJECT-GROUP
        OBJECTS {
                p2mpLocalLoopbackMode,
                p2mpLocalLoopbackAntenna,
                p2mpLocalLoopbackChannel
                }
        STATUS      current
        DESCRIPTION
        "Mandatory group of objects implemented in the point to 
         multi point wireless system for Testing the link."
        ::= { p2mpRadioPhyGroups 3 }

--p2mpCommonNotificationGroup NOTIFICATION-GROUP
--        NOTIFICATIONS {
--                p2mpRadioPhyFailNotification,
--                p2mpTrapRfSupplyVoltage,
--                p2mpTrapRfRxOsc,
--                p2mpTrapRfTxOsc,
--                p2mpTrapRfTemp,
--                p2mpTrapRfCommLinkError,
--                p2mpTrapTxPower,
--                p2mpTrapRfStatusChange
--                }
--        STATUS      current
--        DESCRIPTION
--        "Collection of notifications supported on the head end and the
--        subscriber unit to indicate configuration and RF failures."
--        ::= { p2mpRadioPhyGroups 4 }
--

p2mpRadioSuGroup OBJECT-GROUP
        OBJECTS {
                p2mpSuTxMuteEnable,
                p2mpSuTxMuteDuration,
                p2mpSuCenterFrequency,
                p2mpSuMeasuredPower
                }
        STATUS      current
        DESCRIPTION
        "Group of objects implemented at the Subscriber unit."
        ::= { p2mpRadioPhyGroups 5 }

p2mpRadioHeGroup OBJECT-GROUP
        OBJECTS {
                p2mpHeAlcEnable,
                p2mpHeAlcInterval,
                p2mpHeAlcNumMiniSlots,
                p2mpHeIfTxOscState,
                p2mpHeIfRxOscState,
                p2mpHeIfRefOscState,
                p2mpHeIfInpFreq,
                p2mpHeIfOutFreq,
                p2mpHeTrapEnable
                }
        STATUS      current
        DESCRIPTION
        "Group of objects implemented at the Head End."
        ::= { p2mpRadioPhyGroups 6 }

--p2mpHeOnlyNotificationGroup NOTIFICATION-GROUP
--        NOTIFICATIONS {
--                p2mpTrapHeIfRxOsc,
--                p2mpTrapHeIfTxOsc,
--                p2mpTrapHeIfExtRefOsc
--                }
--        STATUS      current
--        DESCRIPTION
--        "Collection of notifications supported on the head end only.
--        These notification are used to indicate failures pertaining to 
--        the IF module."
--        ::= { p2mpRadioPhyGroups 7 }
--

p2mpRadioAntennaGroup OBJECT-GROUP
        OBJECTS {
                p2mpRfResource,
                p2mpAntennaXDim,
                p2mpAntennaYDim,
                p2mpAntennaType,
                p2mpAntennaDescr,
                p2mpAntennaGain,
                p2mpAntennaPolarization
                }
        STATUS      current
        DESCRIPTION
        "Group of objects implemented in the point to multi point wireless
         system for managing the antennas available in the system."
        ::= { p2mpRadioPhyGroups 8 }
 
 
END
