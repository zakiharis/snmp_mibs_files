-- *****************************************************************
-- CISCO-SLB-EXT-CAPABILITY.my:
-- Cisco CISCO-SLB-EXT-MIB AGENT-CAPABILITIES
--   
-- Jan 2006, Roopeshakumar N. Shalgar
--   
-- Copyright (c) 2006, 2008 by Cisco Systems, Inc.
-- All rights reserved.
-- *****************************************************************

CISCO-SLB-EXT-CAPABILITY DEFINITIONS ::= BEGIN

IMPORTS
    MODULE-IDENTITY
        FROM SNMPv2-SMI
    AGENT-CAPABILITIES
        FROM SNMPv2-CONF
    ciscoAgentCapability
        FROM CISCO-SMI;


ciscoSlbExtCapability MODULE-IDENTITY
    LAST-UPDATED    "200807020000Z"
    ORGANIZATION    "Cisco Systems, Inc."
    CONTACT-INFO
            "Cisco Systems
            Customer Service

            Postal: 170 West Tasman Drive
            San Jose, CA  95134
            USA

            Tel: +1 800 553-NETS

            E-mail: cs-slb@cisco.com"
    DESCRIPTION
        "The capabilities description of
        CISCO-SLB-EXT-MIB."
    REVISION        "200807020000Z"
    DESCRIPTION
        "Added capability statement
        ciscoSlbExtCapc4710aceVA3R100 agent capabilities 
        for ACE 4710 Application Control Engine Appliance."
    REVISION        "200802070000Z"
    DESCRIPTION
        "Added capability statement
        ciscoSlbExtCapc4710aceVA1R700 agent capabilities 
        for ACE 4710 Application Control Engine Appliance."
    REVISION        "200612080000Z"
    DESCRIPTION
        "Added capability statement
        ciscoSlbExtCapabilityACSWV300RA12 for 
        Application Control Engine (ACE)."
    REVISION        "200602210000Z"
    DESCRIPTION
        "Added capability statement
        ciscoSlbExtCapabilityACSWV03R000 for 
        Application Control Engine (ACE)."
    ::= { ciscoAgentCapability 496 }



ciscoSlbExtCapabilityACSWV03R000 AGENT-CAPABILITIES
    PRODUCT-RELEASE "ACSW (Application Control Software) 3.0"
    STATUS          current
    DESCRIPTION
        "ACSW (Application Control Software) 3.0
        CISCO SLB MIB capabilities"

    SUPPORTS        CISCO-SLB-EXT-MIB
    INCLUDES        {
                        cslbxStatsGroup,
                        cslbxServerFarmsGroup,
                        cslbxServerFarmsExtGroup,
                        cslbxStatsHCGroup
                    }
    VARIATION       cslbxStatsServerInitConns
    ACCESS          not-implemented
    DESCRIPTION
        "Not supported."

    VARIATION       cslbxStatsServerInitHCConns
    ACCESS          not-implemented
    DESCRIPTION
        "Not supported."

    VARIATION       cslbxStatsCurrServerInitConns
    ACCESS          not-implemented
    DESCRIPTION
        "Not supported."

    VARIATION       cslbxStatsFailedServerInitConns
    ACCESS          not-implemented
    DESCRIPTION
        "Not supported."

    VARIATION       cslbxStatsNoActiveServerRejects
    ACCESS          not-implemented
    DESCRIPTION
        "Not supported."

    VARIATION       cslbxServerFarmHashMaskAddrType
    ACCESS          read-only
    DESCRIPTION
        "Create operation not allowed."

    VARIATION       cslbxServerFarmHashMaskAddr
    ACCESS          read-only
    DESCRIPTION
        "Create operation not allowed."

    VARIATION       cslbxServerFarmClientNatPool
    ACCESS          not-implemented
    DESCRIPTION
        "Not supported."

    VARIATION       cslbxServerFarmFailAction
    ACCESS          read-only
    DESCRIPTION
        "Create operation not allowed."

    VARIATION       cslbxServerFarmHttpReturnCodeMap
    ACCESS          not-implemented
    DESCRIPTION
        "Not supported."

    VARIATION       cslbxServerFarmInFailedThreshold
    ACCESS          not-implemented
    DESCRIPTION
        "Not supported."

    VARIATION       cslbxServerFarmInbandResetTimer
    ACCESS          read-only
    DESCRIPTION
        "Create operation not allowed."

    VARIATION       cslbxRedirectSvrRelocationStr
    ACCESS          not-implemented
    DESCRIPTION
        "Not supported."

    VARIATION       cslbxRedirectSvrBackupString
    ACCESS          not-implemented
    DESCRIPTION
        "Not supported."

    VARIATION       cslbxRedirectSvrRedirectCode
    ACCESS          not-implemented
    DESCRIPTION
        "Not supported."

    VARIATION       cslbxRedirectSvrRedirectPort
    ACCESS          not-implemented
    DESCRIPTION
        "Not supported."

    VARIATION       cslbxRedirectSvrState
    ACCESS          not-implemented
    DESCRIPTION
        "Not supported."

    VARIATION       cslbxRedirectSvrNumberOfConns
    ACCESS          not-implemented
    DESCRIPTION
        "Not supported."

    VARIATION       cslbxRedirectSvrMaxConns
    ACCESS          not-implemented
    DESCRIPTION
        "Not supported."

    VARIATION       cslbxRedirectSvrAdminWeight
    ACCESS          not-implemented
    DESCRIPTION
        "Not supported."

    VARIATION       cslbxRedirectSvrOperWeight
    ACCESS          not-implemented
    DESCRIPTION
        "Not supported."

    VARIATION       cslbxRedirectSvrMetric
    ACCESS          not-implemented
    DESCRIPTION
        "Not supported."

    VARIATION       cslbxRedirectSvrTotalConns
    ACCESS          not-implemented
    DESCRIPTION
        "Not supported."

    VARIATION       cslbxRedirectSvrHCTotalConns
    ACCESS          not-implemented
    DESCRIPTION
        "Not supported."

    VARIATION       cslbxRedirectSvrRowStatus
    ACCESS          not-implemented
    DESCRIPTION
        "Not supported."

    VARIATION       cslbxServerFarmProbeRowStatus
    ACCESS          read-only
    DESCRIPTION
        "Create operation not allowed."

    VARIATION       cslbxServerFarmTransparent
    ACCESS          read-only
    DESCRIPTION
        "Create operation not allowed."

    VARIATION       cslbxServerFarmSlowStart
    ACCESS          read-only
    DESCRIPTION
        "Create operation not allowed."

    VARIATION       cslbxServerFarmHashHeaderName
    ACCESS          read-only
    DESCRIPTION
        "Create operation not allowed."

    VARIATION       cslbxServerFarmHashCookieName
    ACCESS          read-only
    DESCRIPTION
        "Create operation not allowed."

    VARIATION       cslbxServerFarmUrlPatternBegin
    ACCESS          read-only
    DESCRIPTION
        "Create operation not allowed."

    VARIATION       cslbxServerFarmUrlPatternEnd
    ACCESS          read-only
    DESCRIPTION
        "Create operation not allowed."

    VARIATION       cslbxServerFarmDescription
    ACCESS          read-only
    DESCRIPTION
        "Create operation not allowed."

    VARIATION       cslbxServerFarmType
    ACCESS          read-only
    DESCRIPTION
        "Create operation not allowed."

    ::= { ciscoSlbExtCapability 1 }

ciscoSlbExtCapabilityACSWV300RA12 AGENT-CAPABILITIES
    PRODUCT-RELEASE "ACSW (Application Control Software)
                version 3.0(0)A1(2)."
    STATUS          current
    DESCRIPTION
        "Agent capability for CISCO-SLB-EXT-MIB
        for ACE(Application Control Engine) module."

    SUPPORTS        CISCO-SLB-EXT-MIB
    INCLUDES        {
                        cslbxStatsGroup,
                        cslbxServerFarmsGroup,
                        cslbxServerFarmsExtGroup,
                        cslbxStatsHCGroup
                    }
    VARIATION       cslbxStatsServerInitConns
    ACCESS          not-implemented
    DESCRIPTION
        "Not supported."

    VARIATION       cslbxStatsServerInitHCConns
    ACCESS          not-implemented
    DESCRIPTION
        "Not supported."

    VARIATION       cslbxStatsCurrServerInitConns
    ACCESS          not-implemented
    DESCRIPTION
        "Not supported."

    VARIATION       cslbxStatsFailedServerInitConns
    ACCESS          not-implemented
    DESCRIPTION
        "Not supported."

    VARIATION       cslbxStatsFtpConns
    DESCRIPTION
        "Always returns zero."

    VARIATION       cslbxStatsDroppedRedirectConns
    DESCRIPTION
        "Always returns zero."

    VARIATION       cslbxStatsNoActiveServerRejects
    ACCESS          not-implemented
    DESCRIPTION
        "Not supported."

    VARIATION       cslbxStatsBadSslFormatRejects
    DESCRIPTION
        "Always returns zero."

    VARIATION       cslbxStatsL7ParserErrorRejects
    DESCRIPTION
        "Always returns zero."

    VARIATION       cslbxStatsOutOfMemoryRejects
    DESCRIPTION
        "Always returns zero."

    VARIATION       cslbxStatsTcpChecksumErrorPkts
    DESCRIPTION
        "Always returns zero."

    VARIATION       cslbxStatsIpChecksumErrorPkts
    DESCRIPTION
        "Always returns zero."

    VARIATION       cslbxServerFarmHashMaskAddrType
    ACCESS          read-only
    DESCRIPTION
        "Create operation not allowed."

    VARIATION       cslbxServerFarmHashMaskAddr
    ACCESS          read-only
    DESCRIPTION
        "Create operation not allowed."

    VARIATION       cslbxServerFarmClientNatPool
    ACCESS          not-implemented
    DESCRIPTION
        "Not supported."

    VARIATION       cslbxServerFarmFailAction
    ACCESS          read-only
    DESCRIPTION
        "Create operation not allowed."

    VARIATION       cslbxServerFarmHttpReturnCodeMap
    ACCESS          not-implemented
    DESCRIPTION
        "Not supported."

    VARIATION       cslbxServerFarmInFailedThreshold
    ACCESS          not-implemented
    DESCRIPTION
        "Not supported."

    VARIATION       cslbxServerFarmInbandResetTimer
    ACCESS          read-only
    DESCRIPTION
        "Create operation not allowed."

    VARIATION       cslbxRedirectSvrRelocationStr
    ACCESS          not-implemented
    DESCRIPTION
        "Not supported."

    VARIATION       cslbxRedirectSvrBackupString
    ACCESS          not-implemented
    DESCRIPTION
        "Not supported."

    VARIATION       cslbxRedirectSvrRedirectCode
    ACCESS          not-implemented
    DESCRIPTION
        "Not supported."

    VARIATION       cslbxRedirectSvrRedirectPort
    ACCESS          not-implemented
    DESCRIPTION
        "Not supported."

    VARIATION       cslbxRedirectSvrState
    ACCESS          not-implemented
    DESCRIPTION
        "Not supported."

    VARIATION       cslbxRedirectSvrNumberOfConns
    ACCESS          not-implemented
    DESCRIPTION
        "Not supported."

    VARIATION       cslbxRedirectSvrMaxConns
    ACCESS          not-implemented
    DESCRIPTION
        "Not supported."

    VARIATION       cslbxRedirectSvrAdminWeight
    ACCESS          not-implemented
    DESCRIPTION
        "Not supported."

    VARIATION       cslbxRedirectSvrOperWeight
    ACCESS          not-implemented
    DESCRIPTION
        "Not supported."

    VARIATION       cslbxRedirectSvrMetric
    ACCESS          not-implemented
    DESCRIPTION
        "Not supported."

    VARIATION       cslbxRedirectSvrTotalConns
    ACCESS          not-implemented
    DESCRIPTION
        "Not supported."

    VARIATION       cslbxRedirectSvrHCTotalConns
    ACCESS          not-implemented
    DESCRIPTION
        "Not supported."

    VARIATION       cslbxRedirectSvrRowStatus
    ACCESS          not-implemented
    DESCRIPTION
        "Not supported."

    VARIATION       cslbxServerFarmProbeRowStatus
    ACCESS          read-only
    DESCRIPTION
        "Create operation not allowed."

    VARIATION       cslbxServerFarmTransparent
    ACCESS          read-only
    DESCRIPTION
        "Create operation not allowed."

    VARIATION       cslbxServerFarmSlowStart
    ACCESS          read-only
    DESCRIPTION
        "Create operation not allowed."

    VARIATION       cslbxServerFarmHashHeaderName
    ACCESS          read-only
    DESCRIPTION
        "Create operation not allowed."

    VARIATION       cslbxServerFarmHashCookieName
    ACCESS          read-only
    DESCRIPTION
        "Create operation not allowed."

    VARIATION       cslbxServerFarmUrlPatternBegin
    ACCESS          read-only
    DESCRIPTION
        "Create operation not allowed."

    VARIATION       cslbxServerFarmUrlPatternEnd
    ACCESS          read-only
    DESCRIPTION
        "Create operation not allowed."

    VARIATION       cslbxServerFarmDescription
    ACCESS          read-only
    DESCRIPTION
        "Create operation not allowed."

    VARIATION       cslbxServerFarmType
    ACCESS          read-only
    DESCRIPTION
        "Create operation not allowed."

    ::= { ciscoSlbExtCapability 2 }

ciscoSlbExtCapc4710aceVA1R700 AGENT-CAPABILITIES
    PRODUCT-RELEASE "ACSW (Application Control Software) A1(7)
                    for ACE 4710 Application Control Engine 
                    Appliance"
    STATUS          current
    DESCRIPTION
        "Agent capability for CISCO-SLB-EXT-MIB
        for ACE(Application Control Engine) appliance."

    SUPPORTS        CISCO-SLB-EXT-MIB
    INCLUDES        {
                        cslbxStatsGroup,
                        cslbxServerFarmsGroup,
                        cslbxServerFarmsExtGroup,
                        cslbxStatsHCGroup
                    }
    VARIATION       cslbxStatsServerInitConns
    ACCESS          not-implemented
    DESCRIPTION
        "Not supported."

    VARIATION       cslbxStatsServerInitHCConns
    ACCESS          not-implemented
    DESCRIPTION
        "Not supported."

    VARIATION       cslbxStatsCurrServerInitConns
    ACCESS          not-implemented
    DESCRIPTION
        "Not supported."

    VARIATION       cslbxStatsFailedServerInitConns
    ACCESS          not-implemented
    DESCRIPTION
        "Not supported."

    VARIATION       cslbxStatsFtpConns
    DESCRIPTION
        "Always returns zero."

    VARIATION       cslbxStatsDroppedRedirectConns
    DESCRIPTION
        "Always returns zero."

    VARIATION       cslbxStatsNoActiveServerRejects
    ACCESS          not-implemented
    DESCRIPTION
        "Not supported."

    VARIATION       cslbxStatsBadSslFormatRejects
    DESCRIPTION
        "Always returns zero."

    VARIATION       cslbxStatsL7ParserErrorRejects
    DESCRIPTION
        "Always returns zero."

    VARIATION       cslbxStatsOutOfMemoryRejects
    DESCRIPTION
        "Always returns zero."

    VARIATION       cslbxStatsTcpChecksumErrorPkts
    DESCRIPTION
        "Always returns zero."

    VARIATION       cslbxStatsIpChecksumErrorPkts
    DESCRIPTION
        "Always returns zero."

    VARIATION       cslbxServerFarmHashMaskAddrType
    ACCESS          read-only
    DESCRIPTION
        "Create operation not allowed."

    VARIATION       cslbxServerFarmHashMaskAddr
    ACCESS          read-only
    DESCRIPTION
        "Create operation not allowed."

    VARIATION       cslbxServerFarmClientNatPool
    ACCESS          not-implemented
    DESCRIPTION
        "Not supported."

    VARIATION       cslbxServerFarmFailAction
    ACCESS          read-only
    DESCRIPTION
        "Create operation not allowed."

    VARIATION       cslbxServerFarmHttpReturnCodeMap
    ACCESS          not-implemented
    DESCRIPTION
        "Not supported."

    VARIATION       cslbxServerFarmInFailedThreshold
    ACCESS          not-implemented
    DESCRIPTION
        "Not supported."

    VARIATION       cslbxServerFarmInbandResetTimer
    ACCESS          read-only
    DESCRIPTION
        "Create operation not allowed."

    VARIATION       cslbxRedirectSvrRelocationStr
    ACCESS          not-implemented
    DESCRIPTION
        "Not supported."

    VARIATION       cslbxRedirectSvrBackupString
    ACCESS          not-implemented
    DESCRIPTION
        "Not supported."

    VARIATION       cslbxRedirectSvrRedirectCode
    ACCESS          not-implemented
    DESCRIPTION
        "Not supported."

    VARIATION       cslbxRedirectSvrRedirectPort
    ACCESS          not-implemented
    DESCRIPTION
        "Not supported."

    VARIATION       cslbxRedirectSvrState
    ACCESS          not-implemented
    DESCRIPTION
        "Not supported."

    VARIATION       cslbxRedirectSvrNumberOfConns
    ACCESS          not-implemented
    DESCRIPTION
        "Not supported."

    VARIATION       cslbxRedirectSvrMaxConns
    ACCESS          not-implemented
    DESCRIPTION
        "Not supported."

    VARIATION       cslbxRedirectSvrAdminWeight
    ACCESS          not-implemented
    DESCRIPTION
        "Not supported."

    VARIATION       cslbxRedirectSvrOperWeight
    ACCESS          not-implemented
    DESCRIPTION
        "Not supported."

    VARIATION       cslbxRedirectSvrMetric
    ACCESS          not-implemented
    DESCRIPTION
        "Not supported."

    VARIATION       cslbxRedirectSvrTotalConns
    ACCESS          not-implemented
    DESCRIPTION
        "Not supported."

    VARIATION       cslbxRedirectSvrHCTotalConns
    ACCESS          not-implemented
    DESCRIPTION
        "Not supported."

    VARIATION       cslbxRedirectSvrRowStatus
    ACCESS          not-implemented
    DESCRIPTION
        "Not supported."

    VARIATION       cslbxServerFarmProbeRowStatus
    ACCESS          read-only
    DESCRIPTION
        "Create operation not allowed."

    VARIATION       cslbxServerFarmTransparent
    ACCESS          read-only
    DESCRIPTION
        "Create operation not allowed."

    VARIATION       cslbxServerFarmSlowStart
    ACCESS          read-only
    DESCRIPTION
        "Create operation not allowed."

    VARIATION       cslbxServerFarmHashHeaderName
    ACCESS          read-only
    DESCRIPTION
        "Create operation not allowed."

    VARIATION       cslbxServerFarmHashCookieName
    ACCESS          read-only
    DESCRIPTION
        "Create operation not allowed."

    VARIATION       cslbxServerFarmUrlPatternBegin
    ACCESS          read-only
    DESCRIPTION
        "Create operation not allowed."

    VARIATION       cslbxServerFarmUrlPatternEnd
    ACCESS          read-only
    DESCRIPTION
        "Create operation not allowed."

    VARIATION       cslbxServerFarmDescription
    ACCESS          read-only
    DESCRIPTION
        "Create operation not allowed."

    VARIATION       cslbxServerFarmType
    ACCESS          read-only
    DESCRIPTION
        "Create operation not allowed."

    ::= { ciscoSlbExtCapability 3 }

ciscoSlbExtCapc4710aceVA3R100 AGENT-CAPABILITIES
    PRODUCT-RELEASE "ACSW (Application Control Software) A3(1.0)
                    for ACE 4710 Application Control Engine 
                    Appliance"
    STATUS          current
    DESCRIPTION
        "Agent capability for CISCO-SLB-EXT-MIB
        for ACE(Application Control Engine) appliance."

    SUPPORTS        CISCO-SLB-EXT-MIB
    INCLUDES        {
                        cslbxStatsGroup,
                        cslbxServerFarmsGroup,
                        cslbxServerFarmsExtGroupRev1,
                        cslbxStatsHCGroup,
                        cslbxServerFarmStatsGroup
                    }
    VARIATION       cslbxStatsServerInitConns
    ACCESS          not-implemented
    DESCRIPTION
        "Not supported."

    VARIATION       cslbxStatsServerInitHCConns
    ACCESS          not-implemented
    DESCRIPTION
        "Not supported."

    VARIATION       cslbxStatsCurrServerInitConns
    ACCESS          not-implemented
    DESCRIPTION
        "Not supported."

    VARIATION       cslbxStatsFailedServerInitConns
    ACCESS          not-implemented
    DESCRIPTION
        "Not supported."

    VARIATION       cslbxStatsFtpConns
    DESCRIPTION
        "Always returns zero."

    VARIATION       cslbxStatsDroppedRedirectConns
    DESCRIPTION
        "Always returns zero."

    VARIATION       cslbxStatsNoActiveServerRejects
    ACCESS          not-implemented
    DESCRIPTION
        "Not supported."

    VARIATION       cslbxStatsBadSslFormatRejects
    DESCRIPTION
        "Always returns zero."

    VARIATION       cslbxStatsL7ParserErrorRejects
    DESCRIPTION
        "Always returns zero."

    VARIATION       cslbxStatsOutOfMemoryRejects
    DESCRIPTION
        "Always returns zero."

    VARIATION       cslbxStatsTcpChecksumErrorPkts
    DESCRIPTION
        "Always returns zero."

    VARIATION       cslbxStatsIpChecksumErrorPkts
    DESCRIPTION
        "Always returns zero."

    VARIATION       cslbxServerFarmHashMaskAddrType
    ACCESS          read-only
    DESCRIPTION
        "Create operation not allowed."

    VARIATION       cslbxServerFarmHashMaskAddr
    ACCESS          read-only
    DESCRIPTION
        "Create operation not allowed."

    VARIATION       cslbxServerFarmClientNatPool
    ACCESS          read-only
    DESCRIPTION
        "Create operation not allowed. Value will be
        always returned as null."

    VARIATION       cslbxServerFarmFailAction
    ACCESS          read-only
    DESCRIPTION
        "Create operation not allowed."

    VARIATION       cslbxServerFarmHttpReturnCodeMap
    ACCESS          read-only
    DESCRIPTION
        "Create operation not allowed. Value will be
        always returned as null."

    VARIATION       cslbxServerFarmInFailedThreshold
    ACCESS          read-only
    DESCRIPTION
        "Create operation not allowed."

    VARIATION       cslbxServerFarmInbandResetTimer
    ACCESS          read-only
    DESCRIPTION
        "Create operation not allowed."

    VARIATION       cslbxRedirectSvrRelocationStr
    ACCESS          not-implemented
    DESCRIPTION
        "Not supported."

    VARIATION       cslbxRedirectSvrBackupString
    ACCESS          not-implemented
    DESCRIPTION
        "Not supported."

    VARIATION       cslbxRedirectSvrRedirectCode
    ACCESS          not-implemented
    DESCRIPTION
        "Not supported."

    VARIATION       cslbxRedirectSvrRedirectPort
    ACCESS          not-implemented
    DESCRIPTION
        "Not supported."

    VARIATION       cslbxRedirectSvrState
    ACCESS          not-implemented
    DESCRIPTION
        "Not supported."

    VARIATION       cslbxRedirectSvrNumberOfConns
    ACCESS          not-implemented
    DESCRIPTION
        "Not supported."

    VARIATION       cslbxRedirectSvrMaxConns
    ACCESS          not-implemented
    DESCRIPTION
        "Not supported."

    VARIATION       cslbxRedirectSvrAdminWeight
    ACCESS          not-implemented
    DESCRIPTION
        "Not supported."

    VARIATION       cslbxRedirectSvrOperWeight
    ACCESS          not-implemented
    DESCRIPTION
        "Not supported."

    VARIATION       cslbxRedirectSvrMetric
    ACCESS          not-implemented
    DESCRIPTION
        "Not supported."

    VARIATION       cslbxRedirectSvrTotalConns
    ACCESS          not-implemented
    DESCRIPTION
        "Not supported."

    VARIATION       cslbxRedirectSvrHCTotalConns
    ACCESS          not-implemented
    DESCRIPTION
        "Not supported."

    VARIATION       cslbxRedirectSvrRowStatus
    ACCESS          not-implemented
    DESCRIPTION
        "Not supported."

    VARIATION       cslbxServerFarmProbeRowStatus
    ACCESS          read-only
    DESCRIPTION
        "Create operation not allowed."

    ::= { ciscoSlbExtCapability 4 }

END
