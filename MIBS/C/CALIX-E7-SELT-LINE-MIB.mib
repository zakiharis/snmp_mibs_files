-- *****************************************************************
-- CALIX-E7-SELT-LINE-MIB.my: Calix E7 VDSL SELT MIB Definitions
--
-- Calix Confidential and Proprietary.
--
-- Copyright (c) 2000-2014 Calix Networks, Inc.
-- All rights reserved.
-- *****************************************************************

CALIX-E7-SELT-LINE-MIB DEFINITIONS ::= BEGIN
IMPORTS
    MODULE-IDENTITY, OBJECT-TYPE,
    Counter32, Gauge32,Integer32,
    NOTIFICATION-TYPE,
    transmission, Unsigned32          FROM SNMPv2-SMI
    TruthValue, VariablePointer       FROM SNMPv2-TC
    MODULE-COMPLIANCE, OBJECT-GROUP,
    NOTIFICATION-GROUP                FROM SNMPv2-CONF
    SnmpAdminString                   FROM SNMP-FRAMEWORK-MIB   
    ifIndex                           FROM IF-MIB
    e7, e7Modules                     FROM CALIX-PRODUCT-MIB;
	   
e7SeltTestDiags MODULE-IDENTITY
    LAST-UPDATED "201408070000Z"
    ORGANIZATION "CALIX NETWORKS INC."
    CONTACT-INFO
        "Calix Networks, Inc.

        Postal: 1035 North McDowell Boulevard
        Petaluma, CA  94954-1173
        USA

        Phone: +1 707 766 3000
        Fax: +1 707 766 3100

        E-mail: tech.support@calix.com"
			 
    DESCRIPTION
    "This MIB Module is for E7 xDSL SELT diagnostics."
    ::= { e7 9 }

------------------------------------------------

--          e7XdslSeltLineTable               --
------------------------------------------------

e7XdslSeltLineTable  OBJECT-TYPE
    SYNTAX      SEQUENCE  OF  E7XdslSeltLineEntry
    MAX-ACCESS  not-accessible
    STATUS      current
    DESCRIPTION
    "The table xdslSeltLineTable contains configuration, 
    command and status parameters of the xDSL line. 
   
    Several objects in this table MUST be maintained in 
    a persistent manner. "
    ::= { e7SeltTestDiags 1 }

e7XdslSeltLineEntry  OBJECT-TYPE
    SYNTAX      E7XdslSeltLineEntry
    MAX-ACCESS  not-accessible
    STATUS      current
    DESCRIPTION
    "The index of this table is an interface index where the
    interface has an ifType of xdslSelt(9)."
    INDEX  { ifIndex }
    ::= { e7XdslSeltLineTable 1 }
   
E7XdslSeltLineEntry  ::=
    SEQUENCE {
        e7XdslUsMargin                          INTEGER,
        e7XdslDsMargin                          INTEGER,
        e7XdslUsNumTones                        INTEGER,
        e7XdslDsNumTones                        INTEGER,
        e7XdslUsRate                            Unsigned32,
        e7XdslDsRate                            Unsigned32,
        e7XdslBestFitIdx                        INTEGER,
        e7XdslLoopType                          INTEGER,
        e7XdslLoopLength                        INTEGER,
	e7XdslFitError				INTEGER,
        e7XdslSeltLineCmndConfLdsfFailReason	INTEGER,
        e7XdslSeltLineCmndConfLdsf              INTEGER
   }

e7XdslUsMargin  OBJECT-TYPE
    SYNTAX      INTEGER 
    MAX-ACCESS  read-only
    STATUS      current
    DESCRIPTION
    "Selt US Margin. "
    ::= { e7XdslSeltLineEntry  1 }

e7XdslDsMargin  OBJECT-TYPE
    SYNTAX      INTEGER 
    MAX-ACCESS  read-only
    STATUS      current
    DESCRIPTION
    "Selt DS Margin. "
    ::= { e7XdslSeltLineEntry  2 }
   
e7XdslUsNumTones  OBJECT-TYPE
    SYNTAX      INTEGER 
    MAX-ACCESS  read-only
    STATUS      current
    DESCRIPTION
    "Selt US Number of Tones. "
    ::= { e7XdslSeltLineEntry  3 }
   
e7XdslDsNumTones  OBJECT-TYPE
    SYNTAX      INTEGER 
    MAX-ACCESS  read-only
    STATUS      current
    DESCRIPTION
    "Selt DS Number of Tones. "
    ::= { e7XdslSeltLineEntry  4 }

e7XdslUsRate  OBJECT-TYPE
    SYNTAX      INTEGER 
    MAX-ACCESS  read-only
    STATUS      current
    DESCRIPTION
    "Selt US capacity estimate rate. "
    ::= { e7XdslSeltLineEntry  5 }
   
e7XdslDsRate  OBJECT-TYPE
    SYNTAX      INTEGER 
    MAX-ACCESS  read-only
    STATUS      current
    DESCRIPTION
    "Selt DS capacity estimate rate. "
    ::= { e7XdslSeltLineEntry  6 }

e7XdslBestFitIdx  OBJECT-TYPE
    SYNTAX      INTEGER  
    MAX-ACCESS  read-only
    STATUS      current
    DESCRIPTION
    "Best fit/match reflection report index. "
    ::= { e7XdslSeltLineEntry  7 }

e7XdslLoopType  OBJECT-TYPE
    SYNTAX      INTEGER 
    MAX-ACCESS  read-only
    STATUS      current
    DESCRIPTION
    "Loop Type 0 = Awg 24, 1 = Awg 26. "
    ::= { e7XdslSeltLineEntry  8 }
   
e7XdslLoopLength  OBJECT-TYPE
    SYNTAX      INTEGER 
    MAX-ACCESS  read-only
    STATUS      current
    DESCRIPTION
    "Loop Length Estimate in meters. "
    ::= { e7XdslSeltLineEntry  9 }

e7XdslFitError  OBJECT-TYPE
    SYNTAX      INTEGER 
    MAX-ACCESS  read-only
    STATUS      current
    DESCRIPTION
    "Best Fit Error "
    ::= { e7XdslSeltLineEntry  10 }
   
e7XdslSeltLineCmndConfLdsfFailReason  OBJECT-TYPE
    SYNTAX       INTEGER {
        none(1),
        success(2),
        inProgress(3),
        cannotRun(4),
        aborted(5),
        failed(6)
    }
    MAX-ACCESS  read-only
    STATUS      current
    DESCRIPTION
    "The status of the recent occasion the Loop diagnostics mode
    forced (LDSF) was issued for the associated line.  Possible
    values are:
        none(1)         - The default value in case LDSF was never
                          requested for the associated line.
        success(2)      - The recent command completed
                          successfully.
        inProgress(3)   - The Loop Diagnostics process is in
                          progress.
        cannotRun(4)    - The NE cannot initiate the command, due 
                          to a non-specific reason.
        aborted(5)      - The Loop Diagnostics process aborted.

        failed(6)       - The Loop Diagnostics process failed.
        tableFull(7)    - The NE cannot initiate the command, due
                         to reaching the maximum number of rows in the results table.
        noResources(8)  - The NE cannot initiate the command, due to lack of internal memory resources."
    DEFVAL  { none }
    ::= { e7XdslSeltLineEntry  11 }

e7XdslSeltLineCmndConfLdsf  OBJECT-TYPE
    SYNTAX      INTEGER {
        inhibit(0),
        force(1)
    }
    MAX-ACCESS  read-write
    STATUS      current
    DESCRIPTION
    "Loop diagnostics mode forced (LDSF) for Selt Test.
    
    Defines whether the line should be forced into the Selt loop diagnostics 
    mode by the near-end ATU on this line."
    DEFVAL { inhibit }
    ::= { e7XdslSeltLineEntry  12 }
   
-------------------------------------------------------
--        e7SeltReportStatusTable                    --
--        This table is used for collecting data     --
--	  for SELT Test Reflection Report.   	     --
-------------------------------------------------------

e7SeltReportStatusTable  OBJECT-TYPE
    SYNTAX      SEQUENCE  OF  E7SeltReportStatusEntry
    MAX-ACCESS  not-accessible
    STATUS      current
    DESCRIPTION
    "The table SeltReportStatusTable contains
    status parameters for SELT test reflection report.
	  
    The parameters in this table MUST be updated after a loop
    diagnostic procedure completion"
    ::= { e7SeltTestDiags 2 }

e7SeltReportStatusEntry  OBJECT-TYPE
    SYNTAX      E7SeltReportStatusEntry
    MAX-ACCESS  not-accessible
    STATUS      current
    DESCRIPTION
    "The table SeltReportStatusEntry contains status parameters
    of the SELT test reflection report. 
		
    The index of this table is an interface index."
    INDEX   { ifIndex , e7SeltBestFitIdx }
    ::= { e7SeltReportStatusTable 1 }

E7SeltReportStatusEntry  ::=
    SEQUENCE {
        e7SeltBestFitIdx                INTEGER,
        e7SeltReportValid               INTEGER,
        e7SeltRoundTripDelay            OCTET STRING,					  	
        e7SeltRoundTripError            OCTET STRING,					  	
        e7SeltAttn300KHz                OCTET STRING,
        e7SeltAttn180KHz                OCTET STRING,
        e7SeltAttn1MHz                  OCTET STRING,
        e7SeltAttnEndOfRange            OCTET STRING,
        e7SeltFitError                  OCTET STRING,
        e7SeltTerminationPhase          OCTET STRING,
	e7SeltTransferFunction          OCTET STRING,
        e7SeltRangeStart                INTEGER,
        e7SeltRangeStop                 INTEGER
    }

e7SeltBestFitIdx OBJECT-TYPE
    SYNTAX      INTEGER (0..2) 
    MAX-ACCESS  read-only
    STATUS      current
    DESCRIPTION
    "SELT test best fit index. The valid values are 0, 1, 2. "
    ::= { e7SeltReportStatusEntry 1 }

e7SeltReportValid OBJECT-TYPE
    SYNTAX      INTEGER 
    MAX-ACCESS  read-only
    STATUS      current
    DESCRIPTION
    "SELT test report valid state values. 1 = valid and 0 = not-valid"
    ::= { e7SeltReportStatusEntry 2 }
	
e7SeltRoundTripDelay OBJECT-TYPE
    SYNTAX      OCTET STRING 
    MAX-ACCESS  read-only
    STATUS      current
    DESCRIPTION
    "SELT test round trip delay."
    ::= { e7SeltReportStatusEntry 3 }
	
e7SeltRoundTripError OBJECT-TYPE
    SYNTAX      OCTET STRING
    MAX-ACCESS  read-only
    STATUS      current
    DESCRIPTION
    "SELT test round trip error."
    ::= { e7SeltReportStatusEntry 4 }
	
e7SeltAttn300KHz OBJECT-TYPE
    SYNTAX      OCTET STRING 
    MAX-ACCESS  read-only
    STATUS      current
    DESCRIPTION
    "SELT test attenuation signal 300Khz."
    ::= { e7SeltReportStatusEntry 5 }
	
e7SeltAttn180KHz OBJECT-TYPE
    SYNTAX      OCTET STRING 
    MAX-ACCESS  read-only
    STATUS      current
    DESCRIPTION
    "SELT test attenuation signal 180Khz."
    ::= { e7SeltReportStatusEntry 6 }

e7SeltAttn1MHz OBJECT-TYPE
    SYNTAX      OCTET STRING 
    MAX-ACCESS  read-only
    STATUS      current
    DESCRIPTION
    "SELT test attenuation signal 1 MHz."
    ::= { e7SeltReportStatusEntry 7 }

e7SeltAttnEndOfRange OBJECT-TYPE
    SYNTAX      OCTET STRING 
    MAX-ACCESS  read-only
    STATUS      current
    DESCRIPTION
    "SELT test attenuation end of range."
    ::= { e7SeltReportStatusEntry 8 }

e7SeltFitError OBJECT-TYPE
    SYNTAX      OCTET STRING 
    MAX-ACCESS  read-only
    STATUS      current
    DESCRIPTION
    "SELT test fit error."
    ::= { e7SeltReportStatusEntry 9 }

e7SeltTerminationPhase OBJECT-TYPE
    SYNTAX      OCTET STRING 
    MAX-ACCESS  read-only
    STATUS      current
    DESCRIPTION
    "SELT test termination phase."
    ::= { e7SeltReportStatusEntry 10 }

e7SeltTransferFunction OBJECT-TYPE
    SYNTAX      OCTET STRING 
    MAX-ACCESS  read-only
    STATUS      current
    DESCRIPTION
    "SELT test transfer function."
    ::= { e7SeltReportStatusEntry 11 }

e7SeltRangeStart OBJECT-TYPE
    SYNTAX      INTEGER 
    MAX-ACCESS  read-only
    STATUS      current
    DESCRIPTION
    "SELT test range start."
    ::= { e7SeltReportStatusEntry 12 }	
	
e7SeltRangeStop OBJECT-TYPE
    SYNTAX      INTEGER 
    MAX-ACCESS  read-only
    STATUS      current
    DESCRIPTION
    "SELT test range stop."
    ::= { e7SeltReportStatusEntry 13 }	
	
END
