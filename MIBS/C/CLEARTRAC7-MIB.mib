--
            --                  Lucent Technologies
            --                     ClearTrac MIB
            --
            --                   Version 7.1.0 (R0)
            --
            --
            
            -- 0.   Development history
            --      
            
            -- 1. Introduction
            
            -- This memo describes many SNMP Mib variables that are implemented for
            -- the Lucent ClearTrac Products. 
            
            
            -- 2. MIB Restrictions

            -- Do not use dots '.' in variable names.

            -- Do not use zeroes in enumerations, although there are already a
            -- certain number of them. Zeroes require special treatment so
            -- they should be avoided. 

            -- You cannot remove a mib variable.  If you do that, this MIB
            -- could not be used to manage an older nodes (ex: 7.0.3 and earlier).
            -- It should remain in the mib with a comment stating that it not used in 7.1.

            -- DO NOT change the mib variable names.

            -- 3. Definitions
            
            CLEARTRAC7-MIB DEFINITIONS ::= BEGIN
            
            IMPORTS
                 OBJECT-TYPE
                     FROM RFC-1212
                 enterprises, IpAddress, Counter, Gauge
                     FROM RFC1155-SMI
                 DisplayString
                     FROM RFC1213-MIB
                 TRAP-TYPE
                     FROM RFC-1215;
                                                  
            lucent            OBJECT IDENTIFIER ::= { enterprises 727 }
            
            cleartrac7        OBJECT IDENTIFIER ::= { lucent 7}
            
            -- product              OBJECT IDENTIFIER ::= { cleartrac7 1 }
            mgmt                 OBJECT IDENTIFIER ::= { cleartrac7 2 }
            
            -- ACT products

            -- sdm-8300            OBJECT IDENTIFIER ::= { product 83004 }
            -- sdm-8300-E          OBJECT IDENTIFIER ::= { product 83013 }
            -- sdm-8300-TR         OBJECT IDENTIFIER ::= { product 83024 }                     
            -- sdm-8300-T          OBJECT IDENTIFIER ::= { product 183004 }
            -- sdm-8300-E-T        OBJECT IDENTIFIER ::= { product 183013 }
            -- sdm-8300-TR-T       OBJECT IDENTIFIER ::= { product 183024 }
            -- sdm-8300-S          OBJECT IDENTIFIER ::= { product 283004 }
            -- sdm-8300-E-S        OBJECT IDENTIFIER ::= { product 283013 }
            -- sdm-8300-TR-S       OBJECT IDENTIFIER ::= { product 283024 }
            -- sdm-9530            OBJECT IDENTIFIER ::= { product 95304 }
            -- sdm-9530-E          OBJECT IDENTIFIER ::= { product 95313 }
            -- sdm-9530-TR         OBJECT IDENTIFIER ::= { product 95324 }                    
            -- sdm-9530-T          OBJECT IDENTIFIER ::= { product 195304 }
            -- sdm-9530-E-T        OBJECT IDENTIFIER ::= { product 195313 }
            -- sdm-9530-TR-T       OBJECT IDENTIFIER ::= { product 195324 }
            -- sdm-9530-S          OBJECT IDENTIFIER ::= { product 295304 }
            -- sdm-9530-E-S        OBJECT IDENTIFIER ::= { product 295313 }
            -- sdm-9530-TR-S       OBJECT IDENTIFIER ::= { product 295324 }
            -- sdm-9500            OBJECT IDENTIFIER ::= { product 95000 }
            -- sdm-8200            OBJECT IDENTIFIER ::= { product 82000 }
            -- sdm-9300            OBJECT IDENTIFIER ::= { product 93000 }
            -- sdm-9350            OBJECT IDENTIFIER ::= { product 93500 }
            -- sdm-9400            OBJECT IDENTIFIER ::= { product 94000 }


            -- Lucent products

            -- D300            	OBJECT IDENTIFIER ::= { product 1083004 } aka sdm-8300
            -- D300-E          	OBJECT IDENTIFIER ::= { product 1083013 } aka sdm-8300-E
            -- D300-TR         	OBJECT IDENTIFIER ::= { product 1083024 } aka sdm-8300-TR
            -- D300-T         	OBJECT IDENTIFIER ::= { product 1183004 } aka sdm-8300-T
            -- D300-E-T        	OBJECT IDENTIFIER ::= { product 1183013 } aka sdm-8300-E-T
            -- D300-TR-T       	OBJECT IDENTIFIER ::= { product 1183024 } aka sdm-8300-TR-T
            -- D300-S         	OBJECT IDENTIFIER ::= { product 1283004 } aka sdm-8300-S
            -- D300-E-S        	OBJECT IDENTIFIER ::= { product 1283013 } aka sdm-8300-E-S
            -- D300-TR-S       	OBJECT IDENTIFIER ::= { product 1283024 } aka sdm-8300-TR-S
            -- V530                	OBJECT IDENTIFIER ::= { product 1095304 } aka sdm-9530
            -- V530-E          	OBJECT IDENTIFIER ::= { product 1095313 } aka sdm-9530-E
            -- V530-TR         	OBJECT IDENTIFIER ::= { product 1095324 } aka sdm-9530-TR
            -- V530-T          	OBJECT IDENTIFIER ::= { product 1195304 } aka sdm-9530-T
            -- V530-E-T        	OBJECT IDENTIFIER ::= { product 1195313 } aka sdm-9530-E-T
            -- V530-TR-T	   	OBJECT IDENTIFIER ::= { product 1195324 } aka sdm-9530-TR-T                   
            -- V530-S          	OBJECT IDENTIFIER ::= { product 1295304 } aka sdm-9530-S
            -- V530-E-S        	OBJECT IDENTIFIER ::= { product 1295313 } aka sdm-9530-E-S
            -- V530-TR-S	   	OBJECT IDENTIFIER ::= { product 1295324 } aka sdm-9530-TR-S  
            -- V508                	OBJECT IDENTIFIER ::= { product 195000 }  aka sdm-9500
            -- D200                	OBJECT IDENTIFIER ::= { product 1082000 } aka sdm-8200
            -- V352                	OBJECT IDENTIFIER ::= { product 1093500 } aka sdm-9350
            -- V410                	OBJECT IDENTIFIER ::= { product 1094000 } aka sdm-9400
                        
            --  MIB Sections            
            system               OBJECT IDENTIFIER ::= { mgmt 1  }
            ifwan                OBJECT IDENTIFIER ::= { mgmt 2  }
            iflan                OBJECT IDENTIFIER ::= { mgmt 3  }
            ifvce                OBJECT IDENTIFIER ::= { mgmt 18 }        
            pu                   OBJECT IDENTIFIER ::= { mgmt 4  }
            schedule             OBJECT IDENTIFIER ::= { mgmt 5  }
            bridge               OBJECT IDENTIFIER ::= { mgmt 6  }
            phone                OBJECT IDENTIFIER ::= { mgmt 7  }
            filter               OBJECT IDENTIFIER ::= { mgmt 8  }
            class                OBJECT IDENTIFIER ::= { mgmt 9  }
            pvc                  OBJECT IDENTIFIER ::= { mgmt 10 }
            ipx                  OBJECT IDENTIFIER ::= { mgmt 11 }
            ipstatic             OBJECT IDENTIFIER ::= { mgmt 13 }
            ip                   OBJECT IDENTIFIER ::= { mgmt 14 }
            ospf                 OBJECT IDENTIFIER ::= { mgmt 15 }
            ipxfilter            OBJECT IDENTIFIER ::= { mgmt 16 }
            stat                 OBJECT IDENTIFIER ::= { mgmt 20 }
            intf                 OBJECT IDENTIFIER ::= { mgmt 30 }   
            slot                 OBJECT IDENTIFIER ::= { mgmt 31 }   
            ipaddr               OBJECT IDENTIFIER ::= { mgmt 32 }
            bootp                OBJECT IDENTIFIER ::= { mgmt 33 }
            proxy                OBJECT IDENTIFIER ::= { mgmt 34 }
            timep                OBJECT IDENTIFIER ::= { mgmt 35 }

            
            -- The system group
            
            -- This group lets you configure all parameters that affect the
            -- unit as a whole.
            
            --  GENERAL PURPOSE SYSTEM OBJECTS
            --  ==============================                   
            sysDesc OBJECT-TYPE
                SYNTAX  DisplayString
                ACCESS  read-only
                STATUS  mandatory
                DESCRIPTION
                        "This variable contains a printable octet 
                        string which contains the full name and 
                        version of the product."
                ::= { system 1 }
            
            sysContact OBJECT-TYPE                              --  Configuration CFG-GLOB-CONTACT
                SYNTAX  DisplayString (SIZE (0..32))
                ACCESS  read-write
                STATUS  mandatory
                DESCRIPTION
                        "The textual identification of the contact person
                        for this managed node, together with information
                        on how to contact this person."
                ::= { system 2 }
  
            sysName OBJECT-TYPE                                 --  Configuration CFG-GLOB-ID
                SYNTAX  DisplayString (SIZE (0..32))
                ACCESS  read-write
                STATUS  mandatory
                DESCRIPTION
                        "An administratively-assigned name for this
                        managed node.  By convention, this is the node's
                        fully-qualified domain name."
                ::= { system 3 }
  
            sysUnitRoutingVersion OBJECT-TYPE                   --  Configuration CFG-GLOB-RIPBCX-VERSION
                SYNTAX  INTEGER (1..2)
                ACCESS  read-write
                STATUS  mandatory
                DESCRIPTION
                       "Unit Routing Version: The routing version to be used 
                        on this unit. Select 1 if any cleartrac7 units in 
                        the network are running Unit Routing Version 1 (the 
                        version used in all software releases earlier than 6.7.0).
                        Select 2 if all cleartrac7 units in the network are 
                        running Unit Routing Version 2 (software release 6.7.0)."
                ::= { system 21 }
            
            sysLocation OBJECT-TYPE                             --  Configuration CFG-GLOB-LOCATION
                SYNTAX  DisplayString (SIZE (0..32))
                ACCESS  read-write
                STATUS  mandatory
                DESCRIPTION
                        "The physical location of this node (e.g.,
                        `telephone closet, 3rd floor')."
                ::= { system 4 }

            sysDate OBJECT-TYPE                                 --  Run-time information
                SYNTAX  DisplayString
                ACCESS  read-write
                STATUS  mandatory
                DESCRIPTION
                        "The current date."
                ::= { system 5 }
            
            sysClock OBJECT-TYPE                                --  Run-time information
                SYNTAX  DisplayString
                ACCESS  read-write
                STATUS  mandatory
                DESCRIPTION
                        "The current time."
                ::= { system 6 }
            
            sysDay OBJECT-TYPE                                  --  Run-time information
                SYNTAX  INTEGER {    
                            sunday(1),
                            monday(2),
                            tuesday(3),
                            wednesday(4),
                            thursday(5),
                            friday(6),
                            saturday(7),
                            not-applicable(254),
                            not-available(255)
                        }
                ACCESS  read-write
                STATUS  mandatory
                DESCRIPTION
                        "The current day."
                ::= { system 7 }
              
            sysAcceptLoop OBJECT-TYPE                           --  Configuration CFG-GLOB-ACKLOOP
                SYNTAX  INTEGER {  
                            no(1),
                            yes(2),
                            not-applicable(254),
                            not-available(255)
                        }
                ACCESS  read-write
                STATUS  mandatory
                DESCRIPTION
                       "Control of loopback on the WAN links.  This parameter 
                       determines whether loopback on any link is accepted 
                       (YES) or not accepted (NO).  The unit software detects 
                       the presence of a loopback condition on any WAN link.  
                       Setting ACCEPT LOOP to NO prevents the unit from using 
                       a link that has been placed in loopback mode either 
                       temporarily or accidentally."
                ::= { system 8 }
            
            sysLinkTimeout-s OBJECT-TYPE                        --  Configuration CFG-GLOB-LINK-TIMEOUT
                SYNTAX  INTEGER (0..1000)
                ACCESS  read-write
                STATUS  mandatory
                DESCRIPTION
                       "The delay, in seconds, before a WAN link is declared 
                       down during a link failure.  This timeout can be used 
                       to prevent the accumulation of LINK DOWN alarms in the 
                       unit when brief link failures occur."
                ::= { system 9 }
            
            sysTransitDelay-s OBJECT-TYPE                       --  Configuration CFG-GLOB-TRANSIT-DELAY
                SYNTAX  INTEGER (1..20)
                ACCESS  read-write
                STATUS  mandatory
                DESCRIPTION
                       "The maximum delay, in seconds, allowed to elapse between
                        the reception and transmission of a forwarded frame by a
                        bridge.  a timer is started if a link report that it is
                        too busy to transmit a frame.  Frame that are nor processed
                        within the transit delay are discarded."
                ::= { system 10 }
            
            sysDefaultIpAddr OBJECT-TYPE                        --  Configuration CFG-GLOB-IPADDR
                SYNTAX  IpAddress
                ACCESS  read-write
                STATUS  mandatory
                DESCRIPTION
                        "Default IP address for the unit.  This address is used for
                         PVCR ports and PVCs that do not have a configures IP
                         address (set with the IP LOCAL ADDR parameter for the port
                         or PVC).  It is a 4-byte value in dotted decimal representation
                         with a maximum value of 255 for each byte.  When set to
                         000.000.000.000, no default IP address is defined on the unit."
                ::= { system 11 }
                
            sysDefaultIpMask OBJECT-TYPE                        --  Configuration CFG-GLOB-IPMASK
                SYNTAX  IpAddress
                ACCESS  read-write
                STATUS  mandatory
                DESCRIPTION
                        "Default IP subnet mask associated with the default IP address.
                         It is configured like the default IP address: a 4-byte value
                         in dotted decimal representation, with a maximum value of 255
                         for each byte.  The default IP mask identifies which bits of
                         the IP address correspond to the physical network, and which
                         bits correspond to host identifiers."
                ::= { system 12 }
                
            sysDefaultGateway OBJECT-TYPE                       --  Configuration CFG-GLOB-DEFAULT-GTWAY
                SYNTAX  IpAddress
                ACCESS  read-write
                STATUS  mandatory
                DESCRIPTION
                        "This is the gateway’s IP address to use when a destination 
                        is unknown.  At this time, we’ll transmit all frame with 
                        unknown destination to this gateway."
                ::= { system 13 }
                
            --  END OF GENERAL PURPOSE SYSTEM OBJECTS


            --  CENTRAL SITE MANAGEMENT SYSTEM OBJECTS (Rack Information)
            --  ======================================
                
            sysRackId OBJECT-TYPE                               --  Configuration CFG-GLOB-RACK-ID
                SYNTAX  INTEGER {   
                            cs-product-only(0),
                            rack-1(1),
                            rack-2(2),
                            rack-3(3),
                            rack-4(4),
                            not-applicable(254),
                            not-available(255)
                        }
                ACCESS  read-write
                STATUS  mandatory
                DESCRIPTION
                     "ID of the Rack this board is plugged in"
                ::= { system 15 }       
            
            sysPsAndFansMonitoring OBJECT-TYPE                  --  Configuration CFG-GLOB-PS-AND-FAN-CHECK
                SYNTAX  INTEGER {   
                            cs-product-only(0),
                            none(1),
                            ps(2),
                            fans(3),
                            both(4),
                            not-applicable(254),
                            not-available(255)
                        }
                ACCESS  read-write
                STATUS  mandatory
                DESCRIPTION
                        "The monitoring functionality of the Power Supplies and Fans."
                ::= { system 16 }

            sysPsMonitoring OBJECT-TYPE                         --  Configuration CFG-GLOB-PS-AND-FAN-CHECK
                SYNTAX  INTEGER {   
                            no(1),
                            yes(2),
                            not-applicable(254),
                            not-available(255)
                        }
                ACCESS  read-write
                STATUS  mandatory
                DESCRIPTION
                        "The monitoring functionality of the Power Supplies and Fans."
                ::= { system 47 }

            --  END OF CENTRAL SITE MANAGEMENT SYSTEM OBJECTS


            --  SNMP TRAPS SYSTEM OBJECTS
            --  =========================
            
            sysSnmpTrapIpAddr1 OBJECT-TYPE                      --  Configuration CFG-GLOB-SNMP-TRAP-1
                SYNTAX  IpAddress
                ACCESS  read-write
                STATUS  mandatory
                DESCRIPTION
                        "Specific IP address to sent SNMP trap."
                ::= { system 17 }
                
            sysSnmpTrapIpAddr2 OBJECT-TYPE                      --  Configuration CFG-GLOB-SNMP-TRAP-2
                SYNTAX  IpAddress
                ACCESS  read-write
                STATUS  mandatory
                DESCRIPTION
                        "Specific IP address to sent SNMP trap."
                ::= { system 18 }
                
            sysSnmpTrapIpAddr3 OBJECT-TYPE                      --  Configuration CFG-GLOB-SNMP-TRAP-3
                SYNTAX  IpAddress
                ACCESS  read-write
                STATUS  mandatory
                DESCRIPTION
                        "Specific IP address to sent SNMP trap."
                ::= { system 19 }
                
            sysSnmpTrapIpAddr4 OBJECT-TYPE                      --  Configuration CFG-GLOB-SNMP-TRAP-4
                SYNTAX  IpAddress
                ACCESS  read-write
                STATUS  mandatory
                DESCRIPTION
                        "Specific IP address to sent SNMP trap."
                ::= { system 20 }
                
            --  END OF SNMP TRAPS SYSTEM OBJECTS
            
            
            --  POSITION MANAGEMENT SYSTEM OBJECTS
            --  ==============================
                        
            sysThisPosId OBJECT-TYPE                           --  Run-time information
                SYNTAX  INTEGER {       
                            cs-product-only(0),
                            pos-1(1),
                            pos-2(2),
                            pos-3(3),
                            pos-4(4),
                            pos-5(5),
                            pos-6(6),
                            pos-7(7),
                            pos-8(8),
                            not-applicable(254),
                            not-available(255)
                        }                
                ACCESS  read-only
                STATUS  mandatory
                DESCRIPTION
                     "ID of this board's position"
                ::= { system 30 }

            sysPosNr OBJECT-TYPE                               --  Not a profile parmeter
                SYNTAX  INTEGER  (0..32)
                ACCESS  read-only
                STATUS  mandatory
                DESCRIPTION
                    "The number of positions in the Rack this board belongs to
                     (Always 8, hardware characteristic)"
                ::= { system 31 }
                                                                                                             
            sysRacksNr OBJECT-TYPE                               --  Not a profile parmeter
                SYNTAX  INTEGER  (0..4)
                ACCESS  read-only
                STATUS  mandatory
                DESCRIPTION
                    "The total number of populated Racks 
                     in the system (1 to 4 racks)"
                ::= { system 33 }
                                                                                                             
            sysPosTable OBJECT-TYPE
                SYNTAX  SEQUENCE OF SysPosEntry
                ACCESS  not-accessible
                STATUS  mandatory
                DESCRIPTION
                    "This table represents the entire rack this board belongs
                    to. The number of entries is sysPosNr"
                ::= { system 32 }
                
            sysPosEntry OBJECT-TYPE
                SYNTAX  SysPosEntry
                ACCESS  not-accessible
                STATUS  mandatory
                DESCRIPTION
                    "This entry contains the principal configurable
                    parameters related to CS racks and positions"
                INDEX  { sysPosRackId, sysPosId }
                ::= { sysPosTable 1 }
                   
            SysPosEntry ::=
                SEQUENCE {
                    sysPosId       INTEGER,
                    sysPosProduct  OBJECT IDENTIFIER,
                    sysPosRackId   INTEGER,
                    sysPosIpAddr   IpAddress
                  }

            sysPosId OBJECT-TYPE                               --  Run-time information
                SYNTAX  INTEGER {   
                            cs-product-only(0),
                            pos-1(1),
                            pos-2(2),
                            pos-3(3),
                            pos-4(4),
                            pos-5(5),
                            pos-6(6),
                            pos-7(7),
                            pos-8(8),
                            not-applicable(254),
                            not-available(255)
                        }      
                ACCESS  read-only
                STATUS  mandatory
                DESCRIPTION
                     "ID of the CS-Rack's position that the board at sysPosIndex
                      is plugged in"
                ::= { sysPosEntry 2 }
                
            sysPosProduct OBJECT-TYPE                          --  Run-time information
                SYNTAX  OBJECT IDENTIFIER
                ACCESS  read-only    
                STATUS  mandatory
                DESCRIPTION
                    "The Product descriptor of the board at sysPosIndex
                     in the OID form e.g.:
                     {lucent cleartrac7 product product-id}  "
                ::= { sysPosEntry 3 }                    
                
            sysPosRackId   OBJECT-TYPE                         --  Run-time information
                SYNTAX  INTEGER {   
                            single-rack(0),
                            rack-1(1),
                            rack-2(2),
                            rack-3(3),
                            rack-4(4),
                            not-applicable(254),
                            not-available(255)
                        }
                ACCESS  read-only    
                STATUS  mandatory
                DESCRIPTION
                     "ID of the CS-Rackds as it is configured in the board
                     indexed by sysPosIndex. On a correctly configured
                     installation, all positions in one rack must bear the same
                     rackId"
                ::= { sysPosEntry 4 }
                            
            sysPosIpAddr OBJECT-TYPE                           --  Run-time information
                SYNTAX  IpAddress
                ACCESS  read-only
                STATUS  mandatory
                DESCRIPTION
                        "the (Default) IP address for the unit. It means that,
                        by managing this table in one position, we can see and alter
                        the other position's IP addresses"
                ::= { sysPosEntry 5 }
                
            --  END OF POSITION MANAGEMENT SYSTEM OBJECTS

            --  IP ADDRESSES LIST

            ipaddrNr OBJECT-TYPE                               --  Not a profile parmeter
                SYNTAX  INTEGER  
                ACCESS  read-only
                STATUS  mandatory
                DESCRIPTION
                    "The number ip addresses identifying this unit"
                ::= { ipaddr 1 }
                
            ipaddrTable OBJECT-TYPE
                SYNTAX  SEQUENCE OF IpaddrEntry
                ACCESS  not-accessible
                STATUS  mandatory
                DESCRIPTION
                        "A list of ip addresses entries.  The number of
                        entries is given by the value of ipaddrNr."
                ::= { ipaddr 2 }
            
            ipaddrEntry OBJECT-TYPE
                SYNTAX  IpaddrEntry
                ACCESS  not-accessible
                STATUS  mandatory
                DESCRIPTION
                        "This table is an index list of all
                         ip addresses of this unit."
                INDEX   { ipaddrIndex }
                ::= { ipaddrTable 1 }
            
            IpaddrEntry ::=
                SEQUENCE {
                    ipaddrIndex         INTEGER,
                    ipaddrAddr          IpAddress,
                    ipaddrType          INTEGER,
                    ipaddrIfIndex       INTEGER
                }                       
                
            ipaddrIndex OBJECT-TYPE
                SYNTAX  INTEGER
                ACCESS  read-only
                STATUS  mandatory
                DESCRIPTION
                        ""
                ::= { ipaddrEntry 1 }
            
            ipaddrAddr OBJECT-TYPE
                SYNTAX  IpAddress
                ACCESS  read-write
                STATUS  mandatory
                DESCRIPTION
                        ""
                ::= { ipaddrEntry 2 }
                                                                                                                
            ipaddrType OBJECT-TYPE
                SYNTAX  INTEGER {   
                        undef(0),
                        global(1), 
                        wan(2),
                        lan(3),
                        proxy(4),
                        pvc(5)
                        }   
                ACCESS  read-only
                STATUS  mandatory
                DESCRIPTION
                        ""
                ::= { ipaddrEntry 3 }
            
            ipaddrIfIndex OBJECT-TYPE
                SYNTAX  INTEGER
                ACCESS  read-only
                STATUS  mandatory
                DESCRIPTION
                        ""
                ::= { ipaddrEntry 4 }
            
                                                                
            --  T1 SPECIFIC SYSTEM OBJECTS
            --  =========================                       

            sysDLCI OBJECT-TYPE                                 --  Configuration CFG-GLOB-FP-GLOBAL-DLCI
                SYNTAX  INTEGER
                ACCESS  read-write
                STATUS  mandatory
                DESCRIPTION
                        "The local DLCI address used as Srce field in the
                        connection request to an ACT SDM-FP"
                ::= { system 34 }                
            
            -- ********** VOICE SPECIFIC SYSTEM OBJECTS ******               
            -- **    IMPORTED FROM PAST NETVOICE.MIB        **                        
            
            -- ********** Switching Key Code Length **********
            sysExtensionNumLength OBJECT-TYPE                   --  Configuration CFG-GLOB-EXTENSION-NDIGITS
                SYNTAX  INTEGER (1..5)
                ACCESS  read-write
                STATUS  mandatory
                DESCRIPTION
                       "The number of digits that must be used to define a port Extension Number,
                        or a Destination Extension Number in the Voice Mapping Table for this Node."
                ::= { system 35 }
            
            -- ********** telephone extension number (number of digits.) **********
            sysExtendedDigitsLength OBJECT-TYPE                 --  Configuration CFG-GLOB-EXTENDED-NDIGITS
                SYNTAX  INTEGER (0..16)
                ACCESS  read-write
                STATUS  mandatory
                DESCRIPTION
                       "This parameter sets the number of digits that must be entered into the telephone set when
                        the Extension Number Source of a Voice Mapping Table entry is set to User."
                ::= { system 36 }
                                                                             
            -- ********** System Dial Timer **********
            sysDialTimer OBJECT-TYPE                            --  Configuration CFG-GLOB-DIAL-TIMER
                SYNTAX  INTEGER (0..10)
                ACCESS  read-write
                STATUS  mandatory
                DESCRIPTION
                       "This parameter specifies the amount of time the system should wait
                       for a response to a Call Connect or Call Clear requests."
                ::= { system 37 }

            -- ********** Country Code **********
            sysCountry OBJECT-TYPE                              --  Configuration CFG-GLOB-COUNTRY-CODE
                SYNTAX  INTEGER (0..9999)
                ACCESS  read-write
                STATUS  mandatory
                DESCRIPTION
                       "This parameter determines the type of ring, dial tone, 
                       ringback tone and busy tone that will be generated by the 
                       NetVoice card. To ensure that these signals are generated 
                       according to local standards, set this parameter to the 
                       country where the NetVoice is located."
                ::= { system 38 }

            -- ********** Jitter Buffer (sec) **********
            sysJitterBuf OBJECT-TYPE                            --  Configuration CFG-GLOB-JITTER-BUFFER
                SYNTAX  INTEGER (10..255)
                ACCESS  read-write
                STATUS  mandatory
                DESCRIPTION
                        "The amount of jitter delay, in milliseconds, that the unit
                        voice uses to compensate for the variable arrival time of packets."
                ::= { system 39 }
                
            -- ********** Ring Frequency (Hz) **********
            sysRingFreq OBJECT-TYPE                             --  Configuration CFG-GLOB-RING-FREQUENCY
                SYNTAX  INTEGER {
                        voice-data-only(0),
                        hz-17(1),
                        hz-20(2),
                        hz-25(3),
                        hz-50(4),
                        not-applicable(254),
                        not-available(255)
                        }
                ACCESS  read-write
                STATUS  mandatory
                DESCRIPTION
                        "the frequency in hertz, at which a ring is generated on locally
                         attached equipment"
                ::= { system 40 }
                
            -- ********** Ring Voltage (rms) **********
            sysRingVolt OBJECT-TYPE                             --  Configuration CFG-GLOB-RING-VOLTAGE
                SYNTAX  INTEGER {
                        voice-data-only(0),
                        rms-Volts-60(1),
                        rms-Volts-80(2),
                        not-applicable(254),
                        not-available(255)
                        }
                ACCESS  read-write
                STATUS  mandatory
                DESCRIPTION
                        "the voltage, in volts rms, at which a ring is generated on locally
                        attached equipment."
                ::= { system 41 }
                
            -- ********** Voice Encoding **********
            sysVoiceEncoding OBJECT-TYPE                        --  Configuration CFG-GLOB-VOICE-ENCODING
                SYNTAX  INTEGER {
                        fp-product-only(0),
                        aCode(1),
                        bCode(2),
                        not-applicable(254),
                        not-available(255)
                        }
                ACCESS  read-write
                STATUS  mandatory
                DESCRIPTION
                        "SDM-9400 and V410 Only..."
                ::= { system 42 }
                
            -- ********** Voice Clocking **********
            sysVoiceClocking OBJECT-TYPE                        --  Configuration CFG-GLOB-VOICE-CLOCKING
                SYNTAX  INTEGER {
                        fp-product-only(0),
                        aClock(1),
                        bClock(2),
                        not-applicable(254),
                        not-available(255)
                        }
                ACCESS  read-write
                STATUS  mandatory
                DESCRIPTION
                        "SDM-9400 and V410 Only..."
                ::= { system 43 }
                
            -- ********** Voice log **********
            sysVoiceLog OBJECT-TYPE                             --  Configuration CFG-GLOB-VOICE-LOG
                SYNTAX  INTEGER {
                        no(1),
                        yes(2),
                        not-applicable(254),
                        not-available(255)
                        }
                ACCESS  read-write
                STATUS  mandatory
                DESCRIPTION
                        "Enable logs (accounting) on voice/fax ports"
                ::= { system 44 }
                
            -- ********** Voice speed dial *********
            sysSpeedDialNumLength OBJECT-TYPE                   --  Configuration CFG-GLOB-SPEED-DIAL-NB-DIG
                SYNTAX  INTEGER
                ACCESS  read-write
                STATUS  mandatory
                DESCRIPTION
                        "Number of digit of the MAP numbers"
                ::= { system 45 }
                
            -- ********** Flash config units *********
            sysAutoSaveDelay OBJECT-TYPE                   --  Configuration CFG-GLOB-AUTOSAVE-DELAY
                SYNTAX  INTEGER (0..255)
                ACCESS  read-write
                STATUS  mandatory
                DESCRIPTION
                        "Number of seconds left after a modification and before
                         saving in flash (0 : no auto save)"
                ::= { system 46 }
                
            -- ********** Voice priority **********
            sysVoiceHighestPriority OBJECT-TYPE                             
                SYNTAX  INTEGER {
                        no(1),
                        yes(2),
                        not-applicable(254),
                        not-available(255)
                        }
                ACCESS  read-write
                STATUS  mandatory
                DESCRIPTION
                        "When set to yes, the voice traffic has unconditionnaly the highest possible priority.
                         When set to no, the voice priority is specified by sysVoiceClass."
                ::= { system 48 }
                
            -- ********** Voice class **********
            sysVoiceClass OBJECT-TYPE                             
                SYNTAX  INTEGER (1..8)
                ACCESS  read-write
                STATUS  mandatory
                DESCRIPTION
                        "Associate the voice traffic to a class priority. Effective only if
                         sysVoiceHighestPriority is set to no"
                ::= { system 49 }

            sysHuntForwardingAUnit OBJECT-TYPE
                SYNTAX  DisplayString (SIZE (0..16))
                ACCESS  read-write
                STATUS  mandatory
                DESCRIPTION
                        "Hunt forwarding group A Unit name. Unit name where a busy call for
                         hunt group A will be forwarded to"
                ::= { system 50 }

            sysHuntForwardingBUnit OBJECT-TYPE
                SYNTAX  DisplayString (SIZE (0..16))
                ACCESS  read-write
                STATUS  mandatory
                DESCRIPTION
                        "Hunt forwarding group B Unit name. Unit name where a busy call for
                         hunt group B will be forwarded to"
                ::= { system 51 }

            sysHuntForwardingADLCI OBJECT-TYPE
                SYNTAX  INTEGER
                ACCESS  read-write
                STATUS  mandatory
                DESCRIPTION
                        "Hunt forwarding group A DLCI address. DLCI address where a busy
                         call for hunt group A will be forwarded on an ACT SDM-FP PVC"
                ::= { system 52 }

            sysHuntForwardingBDLCI OBJECT-TYPE
                SYNTAX  INTEGER
                ACCESS  read-write
                STATUS  mandatory
                DESCRIPTION
                        "Hunt forwarding group B DLCI address. DLCI address where a busy
                         call for hunt group B will be forwarded on an ACT SDM-FP PVC"
                ::= { system 53 }

            sysHuntForwardingASvcAddress OBJECT-TYPE
                SYNTAX  DisplayString
                ACCESS  read-write
                STATUS  mandatory
                DESCRIPTION
                        "Hunt forwarding group A SVC address. SVC address where a busy
                         call for hunt group A will be forwarded on an ACT SDM-FP SVC.
                         NOTE: sysHuntForwardingAUnit must be empty otherwise this
                         parameter is ignored"
                ::= { system 54 }

            sysHuntForwardingBSvcAddress OBJECT-TYPE
                SYNTAX  DisplayString
                ACCESS  read-write
                STATUS  mandatory
                DESCRIPTION
                        "Hunt forwarding group A SVC address. SVC address where a busy
                         call for hunt group A will be forwarded on an ACT SDM-FP SVC.
                         NOTE: sysHuntForwardingBUnit must be empty otherwise this
                         parameter is ignored"
                ::= { system 55 }

            sysBackplaneRipVersion OBJECT-TYPE
                SYNTAX  INTEGER {   
                            disable(1),
                            v1(2),
                            v2-broadcast(3),
                            v2-multicast(4),
                            not-applicable(254),
                            not-available(255)
                        }
                ACCESS  read-write
                STATUS  mandatory
                DESCRIPTION
                        "When this parameter is set to V1, the RIP routing
                        is done according to the RIP V1 standard.  With
                        RIP V2, broadcast or multicast can be used.  With
                        RIP V2 MULTICAST, only RIP V2 compliant devices
                        will receive RIP frames."
                ::= { system 56 }
                
            -- END OF VOICE SPECIFIC SYSTEM OBJECTS
                                                 
            sysTrapRackandPos OBJECT-TYPE
                SYNTAX  INTEGER
                ACCESS  read-only
                STATUS  mandatory
                DESCRIPTION
                        "Rack ID X 10 + Position ID."
                ::= { system 57 }
                
            -- ********  END OF  SYSTEM OBJECTS & system GROUP ******
            --  The Proxy group (Not supported by ClearTrac Products)

            proxyNumber OBJECT-TYPE
                SYNTAX  INTEGER
                ACCESS  read-write
                STATUS  mandatory
                DESCRIPTION
                        "Number of proxies in this unit"
                ::= { proxy 1 }

            proxyTable OBJECT-TYPE 
                SYNTAX  SEQUENCE OF ProxyEntry
                ACCESS  not-accessible
                STATUS  mandatory
                DESCRIPTION
                        "List of proxies in this unit"
                ::= { proxy 2 }
                                             
            proxyEntry OBJECT-TYPE
                SYNTAX  ProxyEntry
                ACCESS  not-accessible
                STATUS  mandatory
                DESCRIPTION
                        "This row presents the characteristics that
                         uniquely identifies one proxy board."
                INDEX { proxyIndex }
                ::= { proxyTable 1 }
            
            ProxyEntry ::=
                SEQUENCE {
                    proxyIndex          INTEGER,
                    proxyComm           DisplayString,
                    proxyIpAddr         IpAddress,
                    proxyIpMask         IpAddress,
                    proxyTrapIpAddr     IpAddress,
                    proxyDefaultGateway IpAddress
                }
                                                            
            proxyIndex OBJECT-TYPE
                SYNTAX  INTEGER
                ACCESS  read-only
                STATUS  mandatory
                DESCRIPTION
                        "A unique value for each proxy board."
                ::= { proxyEntry 1 }
            
            proxyComm OBJECT-TYPE
                SYNTAX  DisplayString (SIZE (0..32))
                ACCESS  read-write
                STATUS  mandatory
                DESCRIPTION
                        "The name of the community used to access the proxy
                         agent"
                ::= { proxyEntry 2 }
  
            proxyIpAddr OBJECT-TYPE
                SYNTAX  IpAddress
                ACCESS  read-write
                STATUS  mandatory
                DESCRIPTION
                        "IP address of this proxy agent"
                ::= { proxyEntry 3 }
                
            proxyIpMask OBJECT-TYPE
                SYNTAX  IpAddress
                ACCESS  read-write
                STATUS  mandatory
                DESCRIPTION
                        "IP subnet mask of this proxy agent"
                ::= { proxyEntry 4 }
                
            proxyTrapIpAddr OBJECT-TYPE                     
                SYNTAX  IpAddress
                ACCESS  read-write
                STATUS  mandatory
                DESCRIPTION
                        "Specific IP address to send SNMP trap."
                ::= { proxyEntry 5 }
                
            proxyDefaultGateway OBJECT-TYPE                   
                SYNTAX  IpAddress
                ACCESS  read-write
                STATUS  mandatory
                DESCRIPTION
                        "This is the IP address of the gateway handling routing to
                        all nodes based on ACT'S proprietary NMS"
                ::= { proxyEntry 6 }
                

            --  The intf (interfaces) group
            --  This group provides access to the overall interfaces.
            --  In this realm, everything that connects to anything outside
            --  a ClearTrac system is an interface (only exception: the power
            --  connector, though in future releases we might even document it)
             
            intfNumber OBJECT-TYPE
                SYNTAX  INTEGER
                ACCESS  read-only
                STATUS  mandatory
                DESCRIPTION
                        "The number of overall interfaces present on this system."
                ::= { intf 1 }
                
            -- the intf table    
            
            intfTable OBJECT-TYPE
                SYNTAX  SEQUENCE OF IntfEntry
                ACCESS  not-accessible
                STATUS  mandatory
                DESCRIPTION
                        "A list of interface entries.  The number of
                        entries is given by the value of ifNumber."
                ::= { intf 2 }
            
            intfEntry OBJECT-TYPE
                SYNTAX  IntfEntry
                ACCESS  not-accessible
                STATUS  mandatory
                DESCRIPTION
                        "This table presents the characteristics that
                         uniquely identifies one interface."
                INDEX   { intfIndex }
                ::= { intfTable 1 }
            
            IntfEntry ::=
                SEQUENCE {
                    intfIndex         INTEGER,
                    intfDesc          DisplayString,
                    intfType          INTEGER,
                    intfNumInType     INTEGER,                                      
                    intfSlot          INTEGER,
                    intfSlotType      INTEGER,
                    intfNumInSlot     INTEGER,                                      
                    intfModuleType    INTEGER                                      
                }
            
            intfIndex OBJECT-TYPE
                SYNTAX  INTEGER
                ACCESS  read-only
                STATUS  mandatory
                DESCRIPTION
                        "A unique value for each interface. Matches exaclty the
                        ifIndex of the ifEntry in RFC-1213 "
                ::= { intfEntry 1 }
            
            intfDesc OBJECT-TYPE
                SYNTAX  DisplayString
                ACCESS  read-only
                STATUS  mandatory
                DESCRIPTION
                        "A textual string containing information about 
                        a specific interface."
                ::= { intfEntry 2 }
            
            intfType OBJECT-TYPE
                SYNTAX  INTEGER {
                        wan-on-baseCard(1),
                        voice-on-baseCard(2),
                        wan-on-slot(3),
                        voice-on-slot(4),
                        lan-on-baseCard(5),
                        lan-on-slot(6),
                        proxy-on-slot(7),
                        voice-control-on-slot(8),
                        clock-extract-module(9),
                        other(99),
                        not-applicable(254),
                        not-available(255)         
                        }
                ACCESS  read-only
                STATUS  mandatory
                DESCRIPTION
                        "A unique type value for each interface. "
                ::= { intfEntry 3 }
            
            intfNumInType OBJECT-TYPE
                SYNTAX  INTEGER (1..256)
                ACCESS  read-only
                STATUS  mandatory
                DESCRIPTION
                        "The logical number of this interface amongst those
                         having the same type."   
                ::= { intfEntry 4 }
            
            intfSlot OBJECT-TYPE
                SYNTAX  INTEGER {   
                        baseCard(0),
                        slot-1(1),
                        slot-2(2),
                        slot-3(3),
                        slot-4(4),
                        slot-5(5),
                        slot-6(6),
                        slot-7(7),
                        slot-8(8),
                        slot-A(9),
                        slot-B(10),
                        slot-C(11),
                        slot-D(12),
                        not-applicable(254),
                        not-available(255)
                        }                            
                ACCESS  read-only
                STATUS  mandatory
                DESCRIPTION
                        "The localization of this interface, whether on baseCard
                         or in slot, and on what slot "
                ::= { intfEntry 5 }
            
            intfSlotType OBJECT-TYPE
                SYNTAX  INTEGER {   
                            baseCard(0),
                            ethernet(1),
                            vcf03(2),
                            g703-E1(3),
                            g703-T1(4),
                            g703-E1-ii(5),
                            g703-T1-ii(6),
                            tokenring(7),
                            voice(9),
                            tic(16),
                            tic-75(17),
                            dvc(18),
                            isdn-bri-voice(19),
                            eic(21),
                            eic-120(22),
                            cem(23),
                            vfc03r(51),
                            proxy(36),   
                            unkown(9999),
                            not-applicable(254),
                            not-available(255)
                            }
                ACCESS  read-only
                STATUS  mandatory
                DESCRIPTION
                        "A unique value for each interface. "
                ::= { intfEntry 6 }
            
            intfNumInSlot OBJECT-TYPE
                SYNTAX  INTEGER (1..256)
                ACCESS  read-only
                STATUS  mandatory
                DESCRIPTION
                        "The logical number of this interface within its slot."
                ::= { intfEntry 7 }

            intfModuleType OBJECT-TYPE
                SYNTAX  INTEGER {   
                            module-rs232-dce(0),
                            module-rs232-dte(1),
                            module-v35-dce(2),
                            module-v35-dte(3),
                            module-x21-dce(4),
                            module-x21-dte(5),
                            module-rs530-dce(6),
                            module-rs530-dte(7),
                            module-rs366A-dce(8),
                            module-rs366A-dte(9),
                            module-rs449-dce(10),
                            module-rs449-dte(11),
                            module-univ-dce(17),
                            module-univ-dte(18),
                            module-i430s-dte(19),
                            module-i430u-dte(20),
                            module-i431-T1-dte(21),
                            module-i431-E1-dte(22),
                            module-dsucsu(23),
                            module-undef-dce(255),
                            module-undef-dte(254),
                            module-undef(253),
                            not-applicable(252)
                            }
                ACCESS  read-only
                STATUS  mandatory
                DESCRIPTION
                        "A unique value for each interface. "
                ::= { intfEntry 8 }
            
            -- The slot group
            
            intfSlotNumber OBJECT-TYPE
                SYNTAX  INTEGER
                ACCESS  read-only
                STATUS  mandatory
                DESCRIPTION
                        "The number of overall slots actually presents on this system."
                ::= { slot 1 }
                
            -- the slot/ports-in-slots table    
            
            slotPortInSlotTable OBJECT-TYPE
                SYNTAX  SEQUENCE OF SlotPortInSlotEntry
                ACCESS  not-accessible
                STATUS  mandatory
                DESCRIPTION
                        "This table maps a slot/PortInThisSlot coordinate
                        to the corresponding ifIndex (in intfTable and ifTable)"
                ::= { slot 2 }
            
            slotPortInSlotEntry OBJECT-TYPE
                SYNTAX  SlotPortInSlotEntry
                ACCESS  not-accessible
                STATUS  mandatory
                DESCRIPTION
                        "One element of the above table"
                INDEX   { slotSlot, slotPortInSlot }
                ::= { slotPortInSlotTable 1 }
            
            SlotPortInSlotEntry ::=
                SEQUENCE {
                    slotSlot          INTEGER,
                    slotPortInSlot    INTEGER,
                    slotIfIndex       INTEGER                                      
                }
            
            slotSlot OBJECT-TYPE
                SYNTAX  INTEGER {   
                            baseCard(0),
                            slot-1(1),
                            slot-2(2),
                            slot-3(3),
                            slot-4(4),
                            slot-5(5),
                            slot-6(6),
                            slot-7(7),
                            slot-8(8),
                            slot-A(9),
                            slot-B(10),
                            slot-C(11),
                            slot-D(12),
                            not-applicable(254),
                            not-available(255)
                            }                            
                ACCESS  read-only
                STATUS  mandatory
                DESCRIPTION
                        "The localization of this interface, whether on baseCard
                         or in slot, and on what slot "
                ::= { slotPortInSlotEntry 1 }
            
            slotPortInSlot OBJECT-TYPE
                SYNTAX  INTEGER (1..256)
                ACCESS  read-only
                STATUS  mandatory
                DESCRIPTION
                        "The logical number of this interface within its slot."
                ::= { slotPortInSlotEntry 2 }

            slotIfIndex OBJECT-TYPE
                SYNTAX  INTEGER
                ACCESS  read-only
                STATUS  mandatory
                DESCRIPTION
                        "A unique value for each interface. Matches exaclty the
                        ifIndex of the ifEntry in RFC-1213 "
                ::= { slotPortInSlotEntry 3 }
                        
            
            -- The ifwan group
            
            -- This group lets you configure the parameters for ports.
             
            ifwanNumber OBJECT-TYPE
                SYNTAX  INTEGER
                ACCESS  read-only
                STATUS  mandatory
                DESCRIPTION
                        "The number of wan interfaces present on this system."
                ::= { ifwan 1 }
                
            -- the ifwan table    
            
            ifwanTable OBJECT-TYPE
                SYNTAX  SEQUENCE OF IfwanEntry
                ACCESS  not-accessible
                STATUS  mandatory
                DESCRIPTION
                        "A list of interface entries.  The number of
                        entries is given by the value of ifwanNumber."
                ::= { ifwan 2 }
            
            ifwanEntry OBJECT-TYPE
                SYNTAX  IfwanEntry
                ACCESS  not-accessible
                STATUS  mandatory
                DESCRIPTION
                        "This table contains the principal configurable
                        parameters which are used for a particular wan
                        interface."
                INDEX   { ifwanIndex }
                ::= { ifwanTable 1 }
            
            IfwanEntry ::=
                SEQUENCE {
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanCoding             INTEGER,
                    ifwanModem              INTEGER,
                    ifwanTxStart            INTEGER,
                    ifwanTxStartCop         INTEGER,
                    ifwanTxStartPass        INTEGER,
                    ifwanIdle               INTEGER,
                    ifwanDuplex             INTEGER,
                    ifwanGroupPoll          INTEGER,
                    ifwanGroupAddress       OCTET STRING (SIZE (2)),
                    ifwanPollDelay-ms       INTEGER,
                    ifwanFrameDelay         INTEGER,
                    ifwanFormat             INTEGER,
                    ifwanSync               OCTET STRING (SIZE (2)),
                    ifwanDropSyncCounter    INTEGER,
                    ifwanDropSyncCharacter  OCTET STRING (SIZE (1)),
                    ifwanMode               INTEGER,
                    ifwanBodCall-s          INTEGER,
                    ifwanBodHang-s          INTEGER,
                    ifwanBodLevel           INTEGER,
                    ifwanBackupCall-s       INTEGER,
                    ifwanBackupHang-s       INTEGER,
                    ifwanDialTimeout-s      INTEGER,
                    ifwanPortToBack         INTEGER,
                    ifwanDialer             INTEGER,
                    ifwanClassNumber        INTEGER,
                    ifwanRingNumber         OCTET STRING (SIZE (2)),
                    ifwanIpAddress          IpAddress,
                    ifwanSubnetMask         IpAddress,
                    ifwanMaxFrame           INTEGER,
                    ifwanIpRip              INTEGER,
                    ifwanIpRipTxRx          INTEGER,
                    ifwanIpRipAuthType      INTEGER,
                    ifwanIpRipPassword      DisplayString,
                    ifwanOspfEnable         INTEGER,
                    ifwanOspfAreaId         IpAddress,
                    ifwanOspfTransitDelay   INTEGER,
                    ifwanOspfRetransmitInt  INTEGER,
                    ifwanOspfHelloInt       INTEGER,
                    ifwanOspfDeadInt        INTEGER,
                    ifwanOspfPassword       DisplayString,
                    ifwanOspfMetricCost     INTEGER,
                    ifwanCompression        INTEGER,
                    ifwanPriority           INTEGER,
                    ifwanRemoteUnit         DisplayString,
                    ifwanTimeout            INTEGER,
                    ifwanRetry              INTEGER,
                    ifwanRemotePort         INTEGER,
                    ifwanFlowControl        INTEGER,
                    ifwanMgmtInterface      INTEGER,
                    ifwanEnquiryTimer-s     INTEGER,
                    ifwanReportCycle        INTEGER,
                    ifwanCllm               INTEGER,
                    ifwanIpxRip             INTEGER,
                    ifwanIpxSap             INTEGER,
                    ifwanIpxNetNum          OCTET STRING (SIZE (4)),
                    ifwanRxFlow             INTEGER,
                    ifwanTxFlow             INTEGER,
                    ifwanTxHold-s           INTEGER,
                    ifwanDsOSpeed-bps       INTEGER,
                    ifwanFraming            INTEGER,
                    ifwanTerminating        INTEGER,
                    ifwanCrc4               INTEGER,
                    ifwanLineCoding         INTEGER,
                    ifwanBChannels          INTEGER,
                    ifwanMultiframing       INTEGER,
                    ifwanGainLimit          INTEGER,
                    ifwanSignaling          INTEGER,
                    ifwanIdleCode           OCTET STRING (SIZE(1)),
                    ifwanLineBuild          INTEGER,
                    ifwanT1E1Status         INTEGER,
                    ifwanT1E1LoopBack       INTEGER,
                    ifwanEncodingLaw        INTEGER,
                    ifwanChExp              DisplayString,
                    ifwanChUse              DisplayString,
                    ifwanCellPacketization  INTEGER,
                    ifwanMaxChannels        INTEGER,
                    ifwanCondLMIPort        INTEGER,
                    ifwanExtNumber          DisplayString,
                    ifwanDestExtNumber      DisplayString,
                    ifwanSvcAddressType                     INTEGER,
                    ifwanSvcNetworkAddress                  DisplayString,
                    ifwanSvcMaxTxTimeoutT200                INTEGER,
                    ifwanSvcInactiveTimeoutT203             INTEGER,
                    ifwanSvcIframeRetransmissionsN200       INTEGER,
                    ifwanSvcSetupTimeoutT303                INTEGER,
                    ifwanSvcDisconnectTimeoutT305           INTEGER,
                    ifwanSvcReleaseTimeoutT308              INTEGER,
                    ifwanSvcCallProceedingTimeoutT310       INTEGER,
                    ifwanSvcStatusTimeoutT322               INTEGER,
                    ifwanT1E1InterBit                       INTEGER,
                    ifwanConnTimeout-s                  INTEGER,
                    ifwanTeiMode                        INTEGER,
                    ifwanDigitNumber                    INTEGER,
                    ifwanMsn1                           DisplayString,
                    ifwanMsn2                           DisplayString,
                    ifwanMsn3                           DisplayString,
                    ifwanX25Encapsulation               INTEGER,
                    ifwanPvcNumber                      INTEGER,
                    ifwanQsigPbxAb                      INTEGER,
                    ifwanQsigPbxXy                      INTEGER,
                    ifwanPppSilent                      INTEGER,
                    ifwanPppConfigRestartTimer          INTEGER,
                    ifwanPppConfigRetries               INTEGER,
                    ifwanPppNegociateLocalMru           INTEGER,
                    ifwanPppLocalMru                    INTEGER,
                    ifwanPppNegociatePeerMru            INTEGER,
                    ifwanPppPeerMruUpTo                 INTEGER,
                    ifwanPppNegociateAccm               INTEGER,
                    ifwanPppRequestedAccmChar           OCTET STRING (SIZE (4)),
                    ifwanPppAcceptAccmPeer              INTEGER,
                    ifwanPppAcceptableAccmChar          OCTET STRING (SIZE (4)),
                    ifwanPppRequestMagicNum             INTEGER,
                    ifwanPppAcceptMagicNum              INTEGER,
                    ifwanPppAcceptOldIpAddNeg           INTEGER,
                    ifwanPppNegociateIpAddress          INTEGER,
                    ifwanPppAcceptIpAddress             INTEGER,
                    ifwanPppRemoteIpAddress             IpAddress,
                    ifwanPppRemoteSubnetMask            IpAddress,
                    ifwanHighPriorityTransparentClass   INTEGER,
                    ifwanTransparentClassNumber         INTEGER,
                    ifwanChannelCompressed              INTEGER,
                    ifwanSfType		              INTEGER,
			  ifwanSfMode		              INTEGER,
                    ifwanSfCarrierId                    INTEGER
                    }
            
            ifwanIndex OBJECT-TYPE
                SYNTAX  INTEGER
                ACCESS  read-only
                STATUS  mandatory
                DESCRIPTION
                        "A unique value for each interface."
                ::= { ifwanEntry 1 }
            
            ifwanDesc OBJECT-TYPE
                SYNTAX  DisplayString
                ACCESS  read-only
                STATUS  mandatory
                DESCRIPTION
                        "A textual string containing information about 
                        a specific interface."
                ::= { ifwanEntry 2 }
            
            -- Protocol number must be matched with values in cfg.h with an added offset of one.
            ifwanProtocol OBJECT-TYPE
                SYNTAX  INTEGER {   
                            off(1),
                            p-sdlc(2),
                            s-sdlc(3),
                            hdlc(4),
                            ddcmp(5),
                            t-async(6),
                            r-async(7),
                            bsc(8),
                            cop(9),
                            pvcr(10),
                            passthru(11),
                            console(12),
                            fr-net(17),
                            fr-user(18),
                            ppp(19),
                            g703(28),
                            x25(29),
				    sf(31),
                            not-applicable(254),
                            not-available(255)
                        }
                ACCESS  read-write
                STATUS  mandatory
                DESCRIPTION
                        "Operating protocol for the WAN/user port."
                ::= { ifwanEntry 3 }
            
            ifwanSpeed-bps OBJECT-TYPE
                SYNTAX  INTEGER (110..2000000)
                ACCESS  read-write
                STATUS  mandatory
                DESCRIPTION
                        "Port speed or PVC CIR and BIR.
                        1200 to  64000 for DDCMP, BSC and COP.
                         110 to 115200 for TASYNC and RASYNC.
                        1200 to 128000 for PASSTRHU.
                        1200 to 2000000 for PVCs, PSDLC, SSDLC, HDLC, X25, FR-USER, FR-NET, PVCR."
                ::= { ifwanEntry 4 }
            
            ifwanFallBackSpeed-bps OBJECT-TYPE
                SYNTAX  INTEGER (0..2000000)
                ACCESS  read-write
                STATUS  mandatory
                DESCRIPTION
                        "Fallback speed for the transmitter.  Fallback is 
                        available only if the unit is set for DCE internal 
                        clocking.  If in DTE, the fallback rate is ignored.  
                        Set this parameter to 0 to disable fallback. For all 
                        user protocols except ASYNC and PASSTHRU.
                        Applicable to SDM-8200, SDM-8300 and SDM-9530 only.
                        The maximum for DDCMP, BSC and COP is 64000."
                ::= { ifwanEntry 5 }
            
            ifwanFallBackSpeedEnable OBJECT-TYPE
                SYNTAX  INTEGER {
                        no(1),
                        yes(2),
                        not-applicable(254),
                        not-available(255)
                        }
                ACCESS  read-write
                STATUS  mandatory
                DESCRIPTION
                        "Enable the Fallback speed mechanism for the transmitter.
                        Fallback is available only if the unit is set for DCE internal 
                        clocking.  If in DTE, the fallback rate is ignored.  
                        Set this parameter to no to disable the fallback. The actual
                        fallback speed is automatically computed and set by the
                        unit. For all user protocols except ASYNC and PASSTHRU.
                        Applicable to SDM-9350, SDM-9400, V352 and V410 only"
                ::= { ifwanEntry 91 }
            
            -- Interface numbers must be matched with values in cfg.h. No added offset.
            -- dce-undef(255), dte-undef(254) and type-undef(253) are invalid input values.
            -- They may however be displayed under certain conditions.
            ifwanInterface OBJECT-TYPE
                SYNTAX  INTEGER {   
                            dce-rs232(0),
                            dte-rs232(1),
                            dce-v35(2),
                            dte-v35(3),
                            dce-x21(4),
                            dte-x21(5),
                            dce-rs530(6),
                            dte-rs530(7),
                            dce-rs366a(8),
                            dte-rs366a(9),
                            dce-rs449(10),
                            dte-rs449(11),
                            dte-aui(12),
                            dte-tpe(13),
                            autom(16),
                            dce-univ(17),
                            dte-univ(18),
                            i430s(19),
                            i430u(20),
                            i431-t1(21),
                            i431-e1(22),   
                            dsu-csu(23),
                            dce-undef(255),
                            dte-undef(254),
                            type-undef(253)
                        }
                ACCESS  read-write
                STATUS  mandatory
                DESCRIPTION
                        "Interface selection."
                ::= { ifwanEntry 6 }
            
            ifwanClocking OBJECT-TYPE
                SYNTAX  INTEGER {      
                            internal(1),
                            external(2),
                            ipl(3),
                            itb(4),
                            async(5),
                            iso-int(6),
                            iso-ext(7),
                            t1-e1-B-Rcvd(11),
                            t1-e1-A-Rcvd(12),
                            t1-e1-Local(13),
                            not-applicable(254),
                            not-available(255)
                        }
                ACCESS  read-write
                STATUS  mandatory
                DESCRIPTION
                        "Clock source for the port.  For ports on the 
                        processor/LAN interface board (ports 1 and 2) the
                        clock source is automatically controlled by the unit, 
                        and cannot be changed. For all protocols."
                ::= { ifwanEntry 7 }
            
            ifwanCoding OBJECT-TYPE
                SYNTAX  INTEGER {
                            nrz(1),
                            nrzi(2),
                            nrz-crc0(3),
                            nrzi-crc0(4),
                            not-applicable(254),
                            not-available(255)
                        }
                ACCESS  read-write
                STATUS  mandatory
                DESCRIPTION
                        "For SDLC and HDLC protocols only.  Bit coding for 
                        CRC purposes.  For NORMAL and NRZI coding the 
                        computed CRC is preset at 1.  For normal coding with 
                        CRC0 (CRC0-NML) and NRZI coding with CRC0 (CRC0-NZI) 
                        the computed CRC is preset at 0.  The values NRZ-CRC0 
                        and NRZI-CRC0 are available for the HDLC protocol 
                        only."
                ::= { ifwanEntry 8 }
            
            ifwanModem OBJECT-TYPE
                SYNTAX  INTEGER {   
                            static(1),
                            dynamic(2), 
                            statpass(3),
                            dynapass(4),
                            statfix(5),
                            dynafix(6),
                            not-applicable(254),
                            not-available(255)
                        }
                ACCESS  read-write
                STATUS  mandatory
                DESCRIPTION
                        "Modem control signal operating mode.  If the port is
                        DCE this parameter controls the operating mode of 
                        the DCD control signal.  In STATIC mode the DCD 
                        signal is active at all times.  In DYNAMIC mode it 
                        is active only when a frame is transmitted.  If the 
                        port is DTE this parameter controls the operating 
                        mode of the RTS control signal.  In STATIC mode the 
                        RTS signal is active at all times.  In DYNAMIC mode 
                        it is active only when a frame is transmitted."
                ::= { ifwanEntry 9 }
            
            ifwanTxStart OBJECT-TYPE
                SYNTAX  INTEGER { -- AUTO,MAX,48,96,144,192,256,512,1024,2048,8,16,24,32
                            auto(0),
                            max(1),
                            byte-48(2),
                            byte-96(3),
                            byte-144(4),
                            byte-192(5),
                            byte-256(6),
                            byte-512(7),
                            byte-1024(8),
                            byte-2048(9),
                            byte-8(10),
                            byte-16(11),
                            byte-24(12),
                            byte-32(13),
                            not-applicable(254),
                            not-available(255) 
                        }
                ACCESS  read-write
                STATUS  mandatory
                DESCRIPTION
                        "For all user protocols except ASYNC, PASSTH
                        and COP.
                        
                        Transmit start level.  This is the number of 
                        characters that are accumulated before the 
                        transmitter is enabled when a frame is incomplete.
                        
                        When set to MAX, the transmitter is enabled only 
                        when a complete frame has been accumulated by the 
                        unit.  This value prevents underruns but can introduce 
                        unnecessary delays.
                        
                        When the transmit start level is set to a numeric 
                        value, the transmitter is enabled at that level even 
                        if a frame coming from the remote unit has not been 
                        completely received.  If the port is in DCE-INTRN 
                        mode and fallback is enabled, the transmitter falls 
                        back when the number of characters of an incomplete 
                        frame in the output queue goes below the transmit 
                        start level.  Otherwise, no fallback occurs."
                ::= { ifwanEntry 10 }
            
            ifwanTxStartCop OBJECT-TYPE
                SYNTAX  INTEGER { -- AUTO,MAX, 8, 16, 24, 32, 40, 48, 96, 144, 192, 256, 512, 1024, 2048 
                            auto(0),
                            max(1),
                            byte-8(2),
                            byte-16(3),
                            byte-24(4),
                            byte-32(5),
                            byte-40(6),
                            byte-48(7),
                            byte-96(8),
                            byte-144(9),
                            byte-192(10),
                            byte-256(11),
                            byte-512(12),
                            byte-1024(13),
                            byte-2048(14), 
                            not-applicable(254),
                            not-available(255) 
                        }
                ACCESS  read-write
                STATUS  mandatory
                DESCRIPTION
                        "For COP protocol only.
                        
                        Transmit start level.  This is the number of 
                        characters that are accumulated before the 
                        transmitter is enabled when a frame is incomplete.
                        
                        When set to MAX, the transmitter is enabled only 
                        when a complete frame has been accumulated by the 
                        unit.  This value prevents underruns but can introduce 
                        unnecessary delays.
                        
                        When the transmit start level is set to a numeric 
                        value, the transmitter is enabled at that level even 
                        if a frame coming from the remote unit has not been 
                        completely received.  If the port is in DCE-INTRN 
                        mode and fallback is enabled, the transmitter falls 
                        back when the number of characters of an incomplete 
                        frame in the output queue goes below the transmit 
                        start level.  Otherwise, no fallback occurs."
                ::= { ifwanEntry 89}
            
            ifwanTxStartPass OBJECT-TYPE
                SYNTAX  INTEGER (3..12)
                ACCESS  read-write
                STATUS  mandatory
                DESCRIPTION
                        "For PASSTRHU protocol only.
                        
                        Transmit start level.  This is the number of 
                        transparent blocks that are accumulated before the 
                        transmitter is enabled when a frame is incomplete."
                ::= { ifwanEntry 90 }
            
            ifwanIdle OBJECT-TYPE
                SYNTAX  INTEGER {   
                            space(1),
                            mark(2),
                            flag(3),
                            markd(4),
                            not-applicable(254),
                            not-available(255)
                        }
                ACCESS  read-write
                STATUS  mandatory
                DESCRIPTION
                        "For HDLC, SDLC and COP protocols only.  Transmitter 
                        idle state, which determines the characters to be 
                        sent when no data frame is transmitted.  When 
                        configured as FLAG, the transmitter continuously 
                        sends 7E (flags).  When configured as MARK, it 
                        continuously sends 1.  When configured as MARKD, the MARK
                        IDLE state is postponed 20 msec after the end of a frame.
                        When configured as SPACE, it continuously sends 0."
                ::= { ifwanEntry 11 }
            
            ifwanDuplex OBJECT-TYPE
                SYNTAX  INTEGER {   
                            half(1),
                            full(2),
                            not-applicable(254),
                            not-available(255) 
                        }
                ACCESS  read-write
                STATUS  mandatory
                DESCRIPTION
                        "Port duplex mode.  When set to FULL (DUPLEX), the 
                        SDLC driver can transmit INFO frames to a secondary 
                        port while polling another secondary port."
                ::= { ifwanEntry 12 }
            
            ifwanGroupPoll OBJECT-TYPE
                SYNTAX  INTEGER {   
                            no(1),
                            yes(2),
                            not-applicable(254),
                            not-available(255)
                        }
                ACCESS  read-write
                STATUS  mandatory
                DESCRIPTION
                        "For P-SDLC and S-SDLC protocols only.  Group poll 
                        enabled or disabled.  When this parameter is set to 
                        YES, the group poll feature is enabled, using the 
                        address set with the group address parameter, 
                        described below.  When this parameter is set to NO, 
                        the group poll feature is disabled."
                ::= { ifwanEntry 13 }
            
            ifwanGroupAddress OBJECT-TYPE
                SYNTAX  OCTET STRING (SIZE (2))
                ACCESS  read-write
                STATUS  mandatory
                DESCRIPTION
                        "For P-SDLC and S-SDLC protocols only.  Group 
                        address.  This parameter is used when the group 
                        poll feature is enabled (see ifwanGroupPoll parameter, 
                        above)."
                ::= { ifwanEntry 14 }
            
            ifwanPollDelay-ms OBJECT-TYPE
                SYNTAX  INTEGER (0..1000)
                ACCESS  read-write
                STATUS  mandatory
                DESCRIPTION
                        "The wait time, in milliseconds, before transmitting 
                        a poll."
                ::= { ifwanEntry 15 }
            
           ifwanFrameDelay OBJECT-TYPE
                SYNTAX  INTEGER {   
                            delay-0p0-ms(1),
                            delay-0p5-ms(2),
                            delay-1p0-ms(3),
                            delay-1p5-ms(4),
                            delay-2p0-ms(5),
                            not-applicable(254),
                            not-available(255)
                        }
                ACCESS  read-write
                STATUS  mandatory
                DESCRIPTION
                        "For HDLC protocol only.  Delay, in milliseconds, 
                        added between each frame transmitted on the unit 
                        port.  This delay is required by some DTE equipment 
                        operating at speeds higher than 56 Kbps."
                ::= { ifwanEntry 16 }
            
            ifwanFormat OBJECT-TYPE
                SYNTAX  INTEGER {   
                            fmt-8-none(1),
                            fmt-7-none(2),
                            fmt-7-odd(3),
                            fmt-7-even(4),
                            fmt-7-space(5),
                            fmt-7-mark(6),
                            fmt-7-ignore(7),
                            fmt-8-even(8),
                            fmt-8-odd(9),
                            fmt-8n-2stop(10),
                            fmt-8-bits(11),
                            fmt-6-bits(12),
                            sync(13),
                            async(14),
                            not-applicable(254),
                            not-available(255)
                        }        
                ACCESS  read-write
                STATUS  mandatory
                DESCRIPTION
                        "For ASYNC and COP protocols only.  Character format.  
                        The parameter values are different for the ASYNC and 
                        COP protocols. 
                        
                        ASYNC Protocols:
                        
                        The parameter defines the number of data bits per 
                        character, the parity bit usage, number of stop bits 
                        and idle characters.  When not specified in the 
                        parameter value, the number of stop bits is 1.  
                        8N-2STOP configures the port for 8 bits, no parity 
                        and 2 stop bits.
                        
                        Values: 8-NONE, 8-ODD, 8-EVEN, 7-NONE, 7-ODD, 7-EVEN, 
                                7 SPACE, 7-MARK, 7-IGNORE, 8N-2STOP
                                
                        COP Protocol:
                        
                        The parameter defines the number of bits per character 
                        only.
                        
                        Values: 8 bits, 6 bits"
                ::= { ifwanEntry 17 }
                
            ifwanSync OBJECT-TYPE
                SYNTAX  OCTET STRING (SIZE (2))
                ACCESS  read-write
                STATUS  mandatory
                DESCRIPTION
                        "For COP protocol only.  The hexadecimal value of 
                        the synchronization character."
                ::= { ifwanEntry 18 }
                
            ifwanDropSyncCounter OBJECT-TYPE
                SYNTAX  INTEGER (1..100)
                ACCESS  read-write
                STATUS  mandatory
                DESCRIPTION
                        "For COP protocol only.  Drop synchronization 
                        counter.  This parameter defines the number of 
                        contiguous desynchronization characters that must 
                        be received before the unit drops synchronization 
                        and closes the frame."
                ::= { ifwanEntry 19 }
                
            ifwanDropSyncCharacter OBJECT-TYPE
                SYNTAX  OCTET STRING (SIZE (1))
                ACCESS  read-write
                STATUS  mandatory
                DESCRIPTION
                        "For COP protocol only.  The hexadecimal value of 
                        the desynchronization character.  This parameter 
                        defines the value of the desynchronization character 
                        in hexadecimal."
                ::= { ifwanEntry 20 }
                
            ifwanMode OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
                DESCRIPTION
                        "For PVCR protocol only.  Operating mode of the WAN 
                        link.  This parameter defines the WAN link as a 
                        dedicated link, a backup link or a Bandwidth On 
                        Demand link.  The ANSWER mode is used for the link 
                        that responds to calls.  When you install a backup 
                        or Bandwidth On Demand (BOD) link between two units, 
                        one unit must be configured in call mode (CALL-BACKUP 
                        or CALL-BOD) and the other as ANSWER.  The INACTIVE 
                        mode is used to turn off the link."
                ::= { ifwanEntry 21 }
                
            ifwanBodCall-s OBJECT-TYPE
                SYNTAX  INTEGER (1..1000)
                ACCESS  read-write
                STATUS  mandatory
                DESCRIPTION
                        "The call trigger period, in seconds, for the Bandwidth
                         ON Demand function.  This defines the period of time 
                         during which the combined WAN link usage must be a the
                         BOD level (define with the BOD LEVEL parameter) or
                         higher before another WAN link will be activated. It is,
                         in effect, a means of validating the requirement for
                         a new link"
                ::= { ifwanEntry 22 }
                
            ifwanBodHang-s OBJECT-TYPE
                SYNTAX  INTEGER (1..1000)
                ACCESS  read-write
                STATUS  mandatory
                DESCRIPTION
                        "The hold time, in seconds, for minimum link activation
                        under the Bandwidth On Demand function.  This defines the
                        minimum period of time during which a newly added WAN link
                        will remain activated, even if the usage level drops
                        rapidly.  This parameter can prevent unnecessary link 
                        activation/deactivation procedures when the traffic flow
                        fluctuates widely."
                ::= { ifwanEntry 23 }
                
            ifwanBodLevel OBJECT-TYPE
                SYNTAX  INTEGER (5..95)
                ACCESS  read-write
                STATUS  mandatory
                DESCRIPTION
                        "The call trigger level for the Bandwidth On Demand function.
                         It represents the combined WAN link usage level, given as a
                         percentage of the total bandwidth, at which another link
                         should be activated.  This defines a threshold at which
                         another wan link will be added to ease the traffic flow."
                ::= { ifwanEntry 24 }
                
            ifwanBackupCall-s OBJECT-TYPE
                SYNTAX  INTEGER (1..1000)
                ACCESS  read-write
                STATUS  mandatory
                DESCRIPTION
                        "Delay, in seconds, before activating the backup link when a
                         line failure has occurred on a dedicated link."
                ::= { ifwanEntry 25 }
                
            ifwanDialTimeout-s OBJECT-TYPE
                SYNTAX  INTEGER (30..1000)
                ACCESS  read-write
                STATUS  mandatory
                DESCRIPTION
                        "Delay, in seconds, allowed to establish a dial-up backup
                         link."
                ::= { ifwanEntry 92 }
                
            ifwanBackupHang-s OBJECT-TYPE
                SYNTAX  INTEGER (1..1000)
                ACCESS  read-write
               
                STATUS  mandatory
                DESCRIPTION
                        "Delay, in seconds, before deactivating the backup WAN link
                         after the dedicated link has been restored."
                ::= { ifwanEntry 26 }
                
            ifwanPortToBack OBJECT-TYPE
                SYNTAX  INTEGER { -- Port 1, 2, 3, 4, 5, 6, 7, 8
                            any(15),
                            all(16),
                            port-1(1),
                            port-2(2),
                            port-3(3),
                            port-4(4),
                            port-5(5),
                            port-6(6),
                            port-7(7),
                            port-8(8),
                            not-applicable(254),
                            not-available(255)
                        }
                ACCESS  read-write
                STATUS  mandatory
                DESCRIPTION
                        "The WAN link that this port backs up.  Backup links can be
                         configured to monitor and backup a specific link (1..8)
                         any link that fails (ANY) or all other unit links (ALL).
                         NOTE: The number of available links varies with each product."
                ::= { ifwanEntry 27 }
                
            ifwanDialer OBJECT-TYPE
                SYNTAX  INTEGER {
                            dTR(1),
                            x21-L1(2),
                            x21-L2(3),
                            v25-H(4),
                            v25-B(5),
                            aT-9600(6),
                            aT-19200(7),
                            not-applicable(254),
                            not-available(255)
                        }
                ACCESS  read-write
                STATUS  mandatory
                DESCRIPTION
                        "Backup link dialer mode"
                ::= { ifwanEntry 28 }
                
            ifwanRemoteUnit OBJECT-TYPE
                SYNTAX  DisplayString
                ACCESS  read-write
                STATUS  mandatory
                DESCRIPTION
                        "Remote unit to which data from this port should
                         be directed"
                ::= { ifwanEntry 29 }
                
            ifwanClassNumber OBJECT-TYPE
                SYNTAX  INTEGER (1..8)
                ACCESS  read-write
                STATUS  mandatory
                DESCRIPTION
                        "The priority class for data from this port.  Classes are
                         defined according to bandwidth weight."
                ::= { ifwanEntry 30 }
                
            ifwanRingNumber OBJECT-TYPE
                SYNTAX  OCTET STRING (SIZE (2))
                ACCESS  read-write
                STATUS  mandatory
                DESCRIPTION
                        "The ring number of the remote Token-ring LAN, required
                         for source routing of Token-Ring data via the unit."
                ::= { ifwanEntry 31 }
                
            ifwanIpAddress OBJECT-TYPE
                SYNTAX  IpAddress
                ACCESS  read-write
                STATUS  mandatory
                DESCRIPTION
                        "IP address for the local port. This address is a 4-byte value
                         in dotted decimal representation, with a maximum value of 255
                         for each byte.  When set to 000.000.000.000, no IP address is
                         defined for this port.  In this case the unit will use the
                         default IP address defined with the global DEFAULT IP ADDR
                         parameter."
                ::= { ifwanEntry 32 }
                
            ifwanSubnetMask OBJECT-TYPE
                SYNTAX  IpAddress
                ACCESS  read-write
                STATUS  mandatory
                DESCRIPTION
                        "Subnet mask associated with the port IP address. It is
                         configured like the IP address: a 4-byte value in dotted
                         decimal representation, with a maximum value of 255 for each
                         byte.  The subnet mask identifies which bits of the IP address
                         correspond to the physical network, and which  bits correspond
                         to host identifiers."
                ::= { ifwanEntry 33 }
                
            ifwanMaxFrame OBJECT-TYPE
                SYNTAX  INTEGER (128..8192)
                ACCESS  read-write
                STATUS  mandatory
                DESCRIPTION
                        "Maximum frame size, in octets.  This parameter
                        determines the largest datagram that can be sent
                        or received on the interface in one IP frame.  
                        Datagrams larger than the maximum frame size are 
                        divided into fragments before transmission, the 
                        reassembled at the remote end."
                ::= { ifwanEntry 34 }
  
            ifwanCompression OBJECT-TYPE
                SYNTAX  INTEGER {   
                            no(1),
                            yes(2),
                            not-applicable(254),
                            not-available(255)
                        }     
                ACCESS  read-write
                STATUS  mandatory
                DESCRIPTION
                        "Use compression on the WAN link connection to the remote
                         unit.  With compression, the available bandwidth is used
                         more efficiently.  When compression is not used, higher
                         speeds can be obtained on the link."
                ::= { ifwanEntry 36 }
                
            ifwanPriority OBJECT-TYPE
                SYNTAX  INTEGER (0..255)
                ACCESS  read-only
                STATUS  mandatory
                DESCRIPTION
                        "Priority assigned to the WAN port for the Spanning Tree
                        algorithm."
                ::= { ifwanEntry 37 }
                
            ifwanTimeout OBJECT-TYPE
                SYNTAX  INTEGER (1000..30000)
                ACCESS  read-write
                STATUS  mandatory
                DESCRIPTION
                        "The wait for ACK timeout before retransmitting a frame
                         on the WAN link."
                ::= { ifwanEntry 39 }
                
            ifwanRetry OBJECT-TYPE
                SYNTAX  INTEGER (1..1000)
                ACCESS  read-write
                STATUS  mandatory
                DESCRIPTION
                        "Maximum number of successive retries before the WAN link
                         is declared down."
                ::= { ifwanEntry 40 }
                
            ifwanRemotePort OBJECT-TYPE
                SYNTAX  INTEGER (1..255)
                ACCESS  read-write
                STATUS  mandatory
                DESCRIPTION
                        "For all user protocols except SDLC and PVCR.  The 
                        remote port to which data from the local port is 
                        sent.  Specify the port number on the remote unit."
                ::= { ifwanEntry 41 }
                
            ifwanFlowControl OBJECT-TYPE
                SYNTAX  INTEGER {   
                            off(1),
                            on(2),
                            not-applicable(254),
                            not-available(255)
                        }
                ACCESS  read-write
                STATUS  mandatory
                DESCRIPTION
                        "Congestion flow control notification.  If the FLOW CTRL
                         parameter is ON, the unit will set the Forward and Backward
                         Congestion Bits in the header of the active PVC frame when
                         congestion occurs on the unit port.  Forward data congestion
                         affects data transmitted from Frame Relay equipment to the
                         unit port.  Backward data congestion affects data transmitted
                         from the unit to the Frame Relay equipment.  If the FLOW CTRL
                         parameter is OFF, the unit does not set the congestion bits.
                         In this cas, they are reset to zero"
                ::= { ifwanEntry 42 }
                
            ifwanMgmtInterface OBJECT-TYPE
                SYNTAX  INTEGER {   
                            lmi(1),
                            annex-d(2),
                            q-933(3),
                            none(4),
                            not-applicable(254),
                            not-available(255)
                        }
                ACCESS  read-write
                STATUS  mandatory
                DESCRIPTION
                        "Frame Relay Management Protocol.  The LMI (Local 
                        Management Interface) uses the reserved DLCI 
                        address 1023.  The ANNEX-D and the Q-933 protocols uses
                        the reserved DLCI address 0.  Set this parameter 
                        according to the Management Interface Protocol 
                        used on the network connected to the unit port."
                ::= { ifwanEntry 43 }
                
            ifwanEnquiryTimer-s OBJECT-TYPE
                SYNTAX  INTEGER (1..30)
                ACCESS  read-write
                STATUS  mandatory
                DESCRIPTION
                        "Frame Relay Enquiry Timer.  The unit polls the 
                        network with STATUS ENQUIRY frames when this timer 
                        expires."
                ::= { ifwanEntry 44 }
                
            ifwanReportCycle OBJECT-TYPE
                SYNTAX  INTEGER (1..256)
                ACCESS  read-write
                STATUS  mandatory
                DESCRIPTION
                        "Full Status Enquiry Cycle.  The value of this 
                        parameter determines the number of STATUS ENQUIRY 
                        frames that the unit will send before sending a full 
                        status enquiry to the network.  In response to a 
                        full status enquiry the network will send a full 
                        status report.  This report indicates the currently 
                        active PVC on the network.  The unit uses this 
                        information to determine if a particular PVC is 
                        ready to receive data.  It is also used in determining
                        the number of restart errors for PVCs in PVCR mode."
                ::= { ifwanEntry 45 }
                
            ifwanIpRip OBJECT-TYPE
                SYNTAX  INTEGER {   
                            disable(1),
                            v1(2),
                            v2-broadcast(3),
                            v2-multicast(4),
                            not-applicable(254),
                            not-available(255)
                        }
                ACCESS  read-write
                STATUS  mandatory
                DESCRIPTION
                        "When this parameter is set to V1, the RIP routing
                        is done according to the RIP V1 standard.  With
                        RIP V2, broadcast or multicast can be used.  With
                        RIP V2 MULTICAST, only RIP V2 compliant devices
                        will receive RIP frames."
                ::= { ifwanEntry 46 }
            
            ifwanCllm OBJECT-TYPE
                SYNTAX  INTEGER {   
                            off(1),
                            on(2),
                            not-applicable(254),
                            not-available(255)
                        }
                ACCESS  read-write
                STATUS  mandatory
                DESCRIPTION
                        "Frame Relay CLLM control. The value of this
                        parameter determines the behavior of the unit
                        regarding the Consolidated Link Management Option.
                        When set to OFF, CLLM messages received are discarded
                        and none are generated. When set to ON, CLLM messages
                        are generated on the FR-NET when PVC becomes 
                        congested or blocked and frames received are 
                        analyzed."
                        
                ::= { ifwanEntry 47 }

            ifwanIpxRip OBJECT-TYPE
                SYNTAX  INTEGER {   
                            disable(1),
                            enable(2),
                            not-applicable(254),
                            not-available(255)
                        }
                ACCESS  read-write
                STATUS  mandatory
                DESCRIPTION
                        "if this parameter is enable, the unit will generate 
                        IPX RIP frame on that interface every minute, otherwise 
                        the unit will discard all IPX RIP frame received and no 
                        one will be generated on that port."
                ::= { ifwanEntry 48 }
            
            ifwanIpxSap OBJECT-TYPE
                SYNTAX  INTEGER {   
                            disable(1),
                            enable(2),
                            not-applicable(254),
                            not-available(255)
                        }
                ACCESS  read-write
                STATUS  mandatory
                DESCRIPTION
                        "if this parameter is enable, the unit will generate
                         IPX SAP frame on that interface every minute, otherwise 
                         the unit will discard all IPX SAP frame received and no 
                         one will be generated on that port."
                        
                ::= { ifwanEntry 49 }

            ifwanIpxNetNum OBJECT-TYPE
                SYNTAX  OCTET STRING (SIZE (4))
                ACCESS  read-write
                STATUS  mandatory
                DESCRIPTION
                        "This value  identify the IPX network number which 
                         the unit is connected to"
                ::= { ifwanEntry 50 }

            ifwanRxFlow OBJECT-TYPE
                SYNTAX  INTEGER {   
                            none(5),
                            xon-Xoff(1),
                            hardware(2),
                            not-applicable(254),
                            not-available(255)
                        }
                ACCESS  read-write
                STATUS  mandatory
                DESCRIPTION
                        "For R-ASYNC protocol only.  Flow control on the 
                        receiver.  This parameter describes the method 
                        used by the unit to control the flow of data received 
                        from the attached equipment.  Flow control is 
                        applied when the number of characters on input 
                        exceeds a predefined threshold."
                ::= { ifwanEntry 52 }
                
            ifwanTxFlow OBJECT-TYPE
                SYNTAX  INTEGER {   
                            none(5),
                            xon-Xoff(1),
                            hardware(2),
                            not-applicable(254),
                            not-available(255)
                        }
                ACCESS  read-write
                STATUS  mandatory
                DESCRIPTION
                        "For R-ASYNC protocol only.  Flow control on the 
                        transmitter.  This parameter describes the method 
                        used by the attached equipment to control the flow 
                        of data transmitted by the unit."
                ::= { ifwanEntry 53 }
                
            ifwanTxHold-s OBJECT-TYPE
                SYNTAX  INTEGER (0..1000)
                ACCESS  read-write
                STATUS  mandatory
                DESCRIPTION
                        "For R-ASYNC protocol only.  Transmitter hold time.  
                        This parameter defines the maximum hold time that
                        the transmitter can be blocked due to flow control.  
                        There is no hold time limit if TX HOLD is configured 
                        as 0 seconds."
                ::= { ifwanEntry 54 }

            ifwanDsOSpeed-bps OBJECT-TYPE
                SYNTAX  INTEGER { 
                            bps-64000(1),
                            bps-56000(2),
                            not-applicable(254),
                            not-available(255)
                        }
                ACCESS  read-write
                STATUS  mandatory
                DESCRIPTION
                        "Speed of a DS0 channel: 64000 bps or 56000 bps."
                ::= { ifwanEntry 55 }

            ifwanFraming OBJECT-TYPE
                SYNTAX  INTEGER {   
                            esf(2),
                            d4(3),
                            other(4),
                            not-applicable(254),
                            not-available(255)
                        }
                ACCESS  read-write
                STATUS  mandatory
                DESCRIPTION
                        "Framing format (ESF or D4).
                         ***** NOTE: This parameter applies only to TIC,
                         not to EIC."
                ::= { ifwanEntry 58 }

            ifwanTerminating OBJECT-TYPE
                SYNTAX  INTEGER {
                            tE(1),
                            nT(2),
                            not-applicable(254),
                            not-available(255)
                        }
                ACCESS  read-write
                STATUS  mandatory
                DESCRIPTION
                        "Terminating (NT indicate Network terminating and TE
                         indicate terminal terminating)."
                ::= { ifwanEntry 59 }

            ifwanCrc4 OBJECT-TYPE
                SYNTAX  INTEGER {   
                            disable(1),
                            enable(2),
                            not-applicable(254),
                            not-available(255)
                        }
                ACCESS  read-write
                STATUS  mandatory
                DESCRIPTION
                        "CRC-4 procedure enable or disable."
                ::= { ifwanEntry 60 }

            ifwanLineCoding OBJECT-TYPE
                SYNTAX  INTEGER {   
                            ami-e1(0),
                            hdb3-e1(1),
                            b8zs-t1(2),
                            ami-t1(5),
                            other(4),         
                            b7sz-t1(7),
                            not-applicable(254),
                            not-available(255)
                        }
                ACCESS  read-write
                STATUS  mandatory
                DESCRIPTION
                        "1's density control or zero suppression over the line."
                ::= { ifwanEntry 61 }
            
            ifwanBChannels OBJECT-TYPE
                SYNTAX  INTEGER {   
                            disable(1),
                            b1(2),
                            b2(3),
                            b1-plus-b2(4),
                            not-applicable(254),
                            not-available(255)
                        }
                ACCESS  read-write
                STATUS  mandatory
                DESCRIPTION
                        "This parameter permits to enable two independent 64 kbits/s
                         channel for use as B-channels."
                ::= { ifwanEntry 62 }

            ifwanMultiframing OBJECT-TYPE
                SYNTAX  INTEGER {   
                            disable(1),
                            enable(2),
                            not-applicable(254),
                            not-available(255)
                        }
                ACCESS  read-write
                STATUS  mandatory
                DESCRIPTION
                        "The Multiframing provides a layer1 signalling
                         capability between the TE and the NT."
                ::= { ifwanEntry 63 }

            ifwanOspfEnable OBJECT-TYPE
                SYNTAX  INTEGER {   
                            disable(1),
                            enable(2),
                            not-applicable(254),
                            not-available(255)
                        }
                ACCESS  read-write
                STATUS  mandatory
                DESCRIPTION
                        "Indicates whether or not OSPF is enabled on this 
                         interface."
                ::= { ifwanEntry 64 }

            ifwanOspfAreaId OBJECT-TYPE
                SYNTAX  IpAddress
                ACCESS  read-write
                STATUS  mandatory
                DESCRIPTION
                        "Identifies the area to which this interface 
                         belongs."
                ::= { ifwanEntry 65 }

            ifwanOspfTransitDelay OBJECT-TYPE
                SYNTAX  INTEGER (1..360)
                ACCESS  read-write
                STATUS  mandatory
                DESCRIPTION
                        "The estimated number of seconds it takes to 
                         transmit a Link State Update Packet over this 
                         interface."
                ::= { ifwanEntry 66 }

            ifwanOspfRetransmitInt OBJECT-TYPE
                SYNTAX  INTEGER (1..360)
                ACCESS  read-write
                STATUS  mandatory
                DESCRIPTION
                        "The number of seconds between like state advertisement
                         retransmissions for adjacencies belonging to this
                         interface.  Also used when retransmitting Database
                         Description and Link State Request Packets."
                ::= { ifwanEntry 67 }

            ifwanOspfHelloInt OBJECT-TYPE
                SYNTAX  INTEGER (1..360)
                ACCESS  read-write
                STATUS  mandatory
                DESCRIPTION
                        "The length of time, in seconds, between the Hello
                         Packets that the router sends on the interface.
                         This value is advertised in the router's Hello
                         Packets.  It must be the same for all routers 
                         attached to a common network.  The smaller the 
                         HelloInterval, the faster topological changes will 
                         be detected, but more OSPF routing protocol traffic
                         will ensue."
                ::= { ifwanEntry 68 }

            ifwanOspfDeadInt OBJECT-TYPE
                SYNTAX  INTEGER (1..2000)
                ACCESS  read-write
                STATUS  mandatory
                DESCRIPTION
                        "After ceasing to hear a router's Hello Packets, the 
                         number of seconds before its neighbors declare the 
                         router down.  This is also advertised in the router's 
                         Hello Packets in their RouterDeadInterval field.  
                         This value again bust be the same for all routers 
                         attached to a common network."
                ::= { ifwanEntry 69 }

            ifwanOspfPassword OBJECT-TYPE
                SYNTAX  DisplayString
                ACCESS  read-write
                STATUS  mandatory
                DESCRIPTION
                        "This configured data allows the authentication 
                         procedure to generate and/or verify the 
                         authentication field in the OSPF header.  This 
                         value again must be the same for all routers 
                         attached to a common network."
                ::= { ifwanEntry 70 }

            ifwanOspfMetricCost OBJECT-TYPE
                SYNTAX  INTEGER (1..65534)
                ACCESS  read-write
                STATUS  mandatory
                DESCRIPTION
                        "The cost of sending a packet on the interface, 
                         expressed in the link state metric.  This is 
                         advertised as the link cost for this interface 
                         in the router's router links advertisement."
                ::= { ifwanEntry 71 }
            
            --  Parameter MIBP/CFG-WPORT-CHUSE
            ifwanChUse OBJECT-TYPE
                SYNTAX  DisplayString
                ACCESS  read-write
                STATUS  mandatory
                DESCRIPTION
                        "A 32 byte string describing the use of each DS0 of the span:
                         -  '-' or 'i' means off
                         -  'P' means used in passthru mode
                         -  'V' means used as a voice channel
                         -  'R' means reserved ( cannot be set, valid only on EICs)
                         
                         for example:
                         
                         RV--------------R--------------P

                         DS0 timeslot 1 is represent by the left most character. Timeslot 1 and
                         17 are always reserved when using an E1 span. When using a T1 span all
                         DS0 timeslots are available.
                         This would mean that the DS0 timeslot 1 is used as a reserved channel,
                         the DS0 timeslot 2 is used as a voice channel and the DS0 timeslot 17
                         is used as a reserved channel and DS0 timeslot 32 is used as a passthru
                         channel  "
                ::= { ifwanEntry 72 }

            --  Parameter MIBP/CFG-WPORT-GAINLIMIT
            ifwanGainLimit   OBJECT-TYPE
                SYNTAX  INTEGER {
                        db-30(1),
                        db-36(2),
                        not-applicable(254),
                        not-available(255)
                        }
                ACCESS  read-write
                STATUS  mandatory
                DESCRIPTION
                        "this object specifies the gain to be 
                         applied on received DS1 signal.
                         ***** NOTE: This parameter applies only to TIC,
                         not to EIC."
                ::= { ifwanEntry 77 }

            --  Parameter MIBP/CFG-WPORT-SIGNALLING
            ifwanSignaling OBJECT-TYPE
                SYNTAX  INTEGER {
                        none(1),
                        t1-rob-bit(2),
                        e1-cas (3),
                        e1-ccs (4),
                        trsp-orig(5),
                        trsp-answ(6),
                        qsig(7),
                        not-applicable(254),
                        not-available(255)
                        }
                ACCESS  read-write
                STATUS  mandatory
                DESCRIPTION
                        "Specifies what type of signalling is in effect
                         on this port.

                         NOTE:
                         1) none and t1-rob-bit are valid only for a TIC card.
                         2) e1-cas, trsp-orig, trsp-answ and qsig are valid only for
                            a EIC card.
                         3) e1-ccs is no longer used."
                ::= { ifwanEntry 78 }

            --  Parameter MIBP/CFG-WPORT-IDLECODE
            ifwanIdleCode OBJECT-TYPE
                SYNTAX  OCTET STRING (SIZE(1))
                ACCESS  read-write
                STATUS  mandatory
                DESCRIPTION
                        "this object specifies the byte to be
                        transmitted when no real data to transmit"
                ::= { ifwanEntry 79 }

            --  Parameter MIBP/CFG-WPORT-LINEBUILD
            ifwanLineBuild OBJECT-TYPE
                SYNTAX  INTEGER {
                        ft0-to-133(0),
                        ft133-to-266(1),
                        ft266-to-399(2),
                        ft399-to-533(3),
                        ft533-to-655(4),
                        dbMinus7point5(5),
                        dbMinus15(6),
                        dbMinus22point5(7),
                        ohm-75(8),                                
                        ohm-120(9),
                        not-applicable(254),
                        not-available(255)
                        }
                ACCESS  read-write
                STATUS  mandatory
                DESCRIPTION
                        "this object specifies the build out to be 
                         applied on transmitted DS1 signal.
                         ***** NOTE: This parameter applies only to TIC,
                         not to EIC."
                ::= { ifwanEntry 80 }

            --  Parameter MIBP/CFG-WPORT-T1E1-STAT                
            ifwanT1E1Status  OBJECT-TYPE
                SYNTAX  INTEGER {   
                        disable(1),
                        enable(2),
                        not-applicable(254),
                        not-available(255)
                        }
                ACCESS  read-write
                STATUS  mandatory
                DESCRIPTION
                        "This parameter sets the activation status of the T1 port, that is, the preferred
                         T1 port state (enabled or disabled)."
                ::= { ifwanEntry 84 }

            --  Parameter MIBP/CFG-WPORT-LOOPBACK
            ifwanT1E1LoopBack  OBJECT-TYPE
                SYNTAX  INTEGER {   
                        disable(1),
                        enable(2),
                        lev1-local(3),
                        lev2-local(4),
                        echo(5),
                        not-applicable(254),
                        not-available(255)
                        }
                ACCESS  read-write
                STATUS  mandatory
                DESCRIPTION
                        "This object is used to enable/disable loopback on T1/E1 interfaces.
                         The types of loopback depend on the type of T1/E1 interface used."
                ::= { ifwanEntry 85 }

            --  Parameter MIBP/CFG-WPORT-CHEXP
            ifwanChExp OBJECT-TYPE
                SYNTAX  DisplayString
                ACCESS  read-write
                STATUS  mandatory
                DESCRIPTION
                        "A 32 byte string describing the cross connection of every
                         DS0 of this interface:
                         - DS0 timeslot 1 is represent by the left most character.
                         -  every byte of the field correspond to a DS0 channel assign to a
                         specific DVC slot number, i.e. DS0 number 8 is represented by the
                         second byte of the string and represent timeslot 2 crossconnect to
                         a DVC in slot 8, and so on up to DS0 number 32.
                         -  a digit k ( k in the range '1' to '8') placed at the nth position
                            in the string means that the nth DS0 is crossconnected to the
                            expansion slot number k
                            
                         for example:
                         
                         R8--------------R-------------76

                         Timeslot 1 and 17 are always reserved when using an E1 span.
                         When using a T1 span all DS0 timeslots are available. This would
                         mean that the DS0 nr 2 is crossconnected to slot 8, DS0 nr 31
                         is crossconnected to a DVC in slot 7, DS0 nr 32 is crossconnected to
                         a DVC in slot 6.
                         The - or I characters  means that there is no cross connection. "
                ::= { ifwanEntry 86 }

            --  Parameter MIBP/CFG-WPORT-INTER-BIT
            ifwanT1E1InterBit  OBJECT-TYPE
                SYNTAX  INTEGER {   
                        disable(1),
                        enable(2),
                        not-applicable(254),
                        not-available(255)
                        }
                ACCESS  read-write
                STATUS  mandatory
                DESCRIPTION
                        "Use this parameter to enable or disable setting of the International Bit (I-bit)."
                ::= { ifwanEntry 87 }

            ifwanEncodingLaw  OBJECT-TYPE             
                SYNTAX  INTEGER {   
                        aLaw(0),
                        muLaw(1),
                        not-applicable(254),
                        not-available(255)
                        }   
                ACCESS  read-write
                STATUS  mandatory
                DESCRIPTION
                        "The PCM coding law in effect on this interface.
                        Configuration CFG-WPORT-ENCODING-LAW"
                ::= { ifwanEntry 88 }

            
            ifwanCellPacketization OBJECT-TYPE
                SYNTAX  INTEGER {   
                            disable(1),
                            enable(2),
                            not-applicable(254),
                            not-available(255)
                        }
                ACCESS  read-write
                STATUS  mandatory
                DESCRIPTION
                        "Indicates whether or not cell packetization
                         is enabled on this interface."
                ::= { ifwanEntry 93 }

            ifwanMaxChannels OBJECT-TYPE
                SYNTAX  INTEGER (0..10000)
                ACCESS  read-write
                STATUS  mandatory
                DESCRIPTION
                        "Indicates the maximum number of voice channels
                        permitted on this port."
                ::= { ifwanEntry 94 }

            ifwanCondLMIPort OBJECT-TYPE
                SYNTAX  INTEGER {   
                        none(0),
                        not-applicable(254),
                        not-available(255)
                        }
                ACCESS  read-write
                STATUS  mandatory
                DESCRIPTION
                        "Indicates which FR-USER port will be used as
                         a reference port to respond to LMI request. If
                         'none' is specified, the FR-NET port will always
                         answer to LMI request. If a port is specified,
                         the FR-NET port will answer to LMI request only
                         if the indicated port receives answers to its LMI
                         request."
                ::= { ifwanEntry 95 }

            --  Parameter MIBP/CFG-WPORT-EXTENSION-NUMBER
            ifwanExtNumber OBJECT-TYPE
                SYNTAX  DisplayString
                ACCESS  read-write
                STATUS  mandatory
                DESCRIPTION
                        "Port extension number"
                ::= { ifwanEntry 96 }

            --  Parameter MIBP/CFG-WPORT-REM-EXTENSION-NUMBER
            ifwanDestExtNumber OBJECT-TYPE
                SYNTAX  DisplayString
                ACCESS  read-write
                STATUS  mandatory
                DESCRIPTION
                        "Destination extension number"
                ::= { ifwanEntry 97 }

            --  Parameter MIBP/CFG-WPORT-TIMEOUT
            ifwanConnTimeout-s OBJECT-TYPE
                SYNTAX  INTEGER (10..30)
                ACCESS  read-write
                STATUS  mandatory
                DESCRIPTION
                        "This parameter determines the maximum amount of time, in seconds,
                        that the voice port who initiates the call will wait for a call
                        connect confirmed "
                ::= { ifwanEntry 98 }

            --  Parameter MIBP/CFG-WPORT-SVCP-ADDR-TYPE
            ifwanSvcAddressType OBJECT-TYPE
                SYNTAX  INTEGER
                        {
                        none(1),
                        e-164(2),
                        x-121(3)
                        }
                ACCESS  read-write
                STATUS  mandatory
                DESCRIPTION
                        "This parameter determines the SVC address type supported
                        by this frame relay port (NONE, E.164 or X.121) "
                ::= { ifwanEntry 99 }

            --  Parameter MIBP/CFG-WPORT-SVCP-NET-ADDR
            ifwanSvcNetworkAddress OBJECT-TYPE
                SYNTAX  DisplayString
                ACCESS  read-write
                STATUS  mandatory
                DESCRIPTION
                        "Local SVC Network address."
                ::= { ifwanEntry 100 }

            --  Parameter MIBP/CFG-WPORT-SVCP-TX-ACK-T200
            ifwanSvcMaxTxTimeoutT200 OBJECT-TYPE
                SYNTAX  INTEGER (1..5)
                ACCESS  read-write
                STATUS  mandatory
                DESCRIPTION
                        "Maximum Tx Acknowledge timeout (T200)."
                ::= { ifwanEntry 101 }

            --  Parameter MIBP/CFG-WPORT-SVCP-INACTIVE-T203
            ifwanSvcInactiveTimeoutT203 OBJECT-TYPE
                SYNTAX  INTEGER (1..60)
                ACCESS  read-write
                STATUS  mandatory
                DESCRIPTION
                        "Maximum number of seconds without activity (T203)."
                ::= { ifwanEntry 102 }

            --  Parameter MIBP/CFG-WPORT-SVCP-IFRAME-RE-TX-N200
            ifwanSvcIframeRetransmissionsN200 OBJECT-TYPE
                SYNTAX  INTEGER (1..16)
                ACCESS  read-write
                STATUS  mandatory
                DESCRIPTION
                        "Maximum number of I frame retransmission's (N200)."
                ::= { ifwanEntry 103 }

            --  Parameter MIBP/CFG-WPORT-SVCP-SETUP-T303
            ifwanSvcSetupTimeoutT303 OBJECT-TYPE
                SYNTAX  INTEGER (1..30)
                ACCESS  read-write
                STATUS  mandatory
                DESCRIPTION
                        "Response time-out for Q933 setup message (T303)."
                ::= { ifwanEntry 104 }

            --  Parameter MIBP/CFG-WPORT-SVCP-DISCONNECT-T305
            ifwanSvcDisconnectTimeoutT305 OBJECT-TYPE
                SYNTAX  INTEGER (1..30)
                ACCESS  read-write
                STATUS  mandatory
                DESCRIPTION
                        "Response time-out for Q933 disconnect message (T305)."
                ::= { ifwanEntry 105 }

            --  Parameter MIBP/CFG-WPORT-SVCP-RELEASE-T308
            ifwanSvcReleaseTimeoutT308 OBJECT-TYPE
                SYNTAX  INTEGER (1..30)
                ACCESS  read-write
                STATUS  mandatory
                DESCRIPTION
                        "Response time-out for Q933 release message (T308)."
                ::= { ifwanEntry 106 }

            --  Parameter MIBP/CFG-WPORT-SVCP-CALL-PROC-T310
            ifwanSvcCallProceedingTimeoutT310 OBJECT-TYPE
                SYNTAX  INTEGER (1..30)
                ACCESS  read-write
                STATUS  mandatory
                DESCRIPTION
                        "Response time-out for Q933 call proceeding message (T310)."
                ::= { ifwanEntry 107 }

            --  Parameter MIBP/CFG-WPORT-SVCP-STATUS-ENQ-T322
            ifwanSvcStatusTimeoutT322 OBJECT-TYPE
                SYNTAX  INTEGER (1..30)
                ACCESS  read-write
                STATUS  mandatory
                DESCRIPTION
                        "Response time-out for Q933 status enquiry message (T322)."
                ::= { ifwanEntry 108 }

            ifwanTeiMode OBJECT-TYPE
                SYNTAX  INTEGER {   
                            dynamic(1),
                            fixed(2),
                            not-applicable(254),
                            not-available(255)
                        }
                ACCESS  read-write
                STATUS  mandatory
                DESCRIPTION
                        "Object specific to the ISDN BRI Voice card.  Indicates the
                         TEI mode used for the interface.  When Dynamic is selected,
                         the TEI is negotiated between the NT and the TE devices.
                         Whenever Fixed is selected, the TEI value 0 is used to establish
                         the session."
                ::= { ifwanEntry 109 }

            ifwanDigitNumber OBJECT-TYPE
                SYNTAX  INTEGER (0..8)
                ACCESS  read-write
                STATUS  mandatory
                DESCRIPTION
                        "Object specific to the ISDN BRI Voice card.  It contains the
                         number of digits to wait for before the setup request is
                         forwarded on the port.  This object is usefull only when the
                         ifwanTerminating is set to NT."
                ::= { ifwanEntry 110 }

            ifwanMsn1 OBJECT-TYPE
                SYNTAX  DisplayString
                ACCESS  read-write
                STATUS  mandatory
                DESCRIPTION
                        "Object specific to the ISDN BRI Voice card.  Contains the
                         First ISDN number on which the port will accept an incoming
                         connection request.  This object is usefull only when
                         ifwanTerminating is set to TE."
                ::= { ifwanEntry 111 }

            ifwanMsn2 OBJECT-TYPE
                SYNTAX  DisplayString
                ACCESS  read-write
                STATUS  mandatory
                DESCRIPTION
                        "Object specific to the ISDN BRI Voice card.  Second ISDN number
                         on which the port will accept an incoming connection request.
                         This object is usefull only when ifwanTerminating is set to TE
                         while ifwanTeiMode is set to Dynamic."
                ::= { ifwanEntry 112 }

            ifwanMsn3 OBJECT-TYPE
                SYNTAX  DisplayString
                ACCESS  read-write
                STATUS  mandatory
                DESCRIPTION
                        "Object specific to the ISDN BRI Voice card.  Third ISDN number
                         on which the port will accept an incoming connection request.
                         This object is usefull only when ifwanTerminating is set to TE
                         while ifwanTeiMode is set to Dynamic."
                ::= { ifwanEntry 113 }

            --  Parameter MIBP/CFG-WPORT-X25-ENCAPSULATION
            ifwanX25Encapsulation OBJECT-TYPE
                SYNTAX  INTEGER {
                            annex-f(1),
                            annex-g(2),
                            not-applicable(254),
                            not-available(255)
                        }
                ACCESS  read-write
                STATUS  mandatory
                DESCRIPTION
                        "Defines the encapsulation method used to transport X25 over frame relay."
                ::= { ifwanEntry 114 }

            --  Parameter MIBP/CFG-WPORT-PVC-NUMBER
            ifwanPvcNumber OBJECT-TYPE
                SYNTAX  INTEGER
                ACCESS  read-write
                STATUS  mandatory
                DESCRIPTION
                        "PVC this port will use to carry X25 traffic over frame relay."
                ::= { ifwanEntry 115 }

            ifwanQsigPbxAb OBJECT-TYPE
                SYNTAX  INTEGER {   
                            a(1),
                            b(2),
                            not-applicable(254),
                            not-available(255)
                        }
                ACCESS  read-write
                STATUS  mandatory
                DESCRIPTION
                        "Object specific to the E1 card, when QSIG signaling is used.
                        Specifies the DTE/DCE operation mode of the QSIG port."
                ::= { ifwanEntry 116 }

            ifwanQsigPbxXy OBJECT-TYPE
                SYNTAX  INTEGER {   
                            x(1),
                            y(2),
                            not-applicable(254),
                            not-available(255)
                        }
                ACCESS  read-write
                STATUS  mandatory
                DESCRIPTION
                        "Object specific to the E1 card, when QSIG signaling is used.
                         Object used as an arbitrator in case of collisions between the
                         E1 card and the connected device (i.e. the local PBX).
                         One side of the connection has to be set to X while the other
                         side of the connection has to be set to Y."

                ::= { ifwanEntry 117 }

            ifwanIpRipTxRx OBJECT-TYPE
                SYNTAX  INTEGER {
                            duplex(1),
                            tx-only(2),
                            rx-only(3),
                            not-applicable(254),
                            not-available(255)
                        }
                ACCESS  read-write
                STATUS  mandatory
                DESCRIPTION
                        "This parameter allows RIP frames transmission only,
                        RIP frames reception only or both transmission and
                        reception of RIP frames."
                ::= { ifwanEntry 118 }

            ifwanIpRipAuthType OBJECT-TYPE
                SYNTAX  INTEGER {
                            none(1),
                            simple(2),
                            not-applicable(254),
                            not-available(255)
                        }
                ACCESS  read-write
                STATUS  mandatory
                DESCRIPTION
                        "Enable or disable password authentication for
                        the interface. If you select Simple Password, the
                        password will be included in the sent RIP frames.
                        The received frames containing authentication will be
                        accepted only if the password is valid."
                ::= { ifwanEntry 119 }

            ifwanIpRipPassword OBJECT-TYPE
                SYNTAX  DisplayString
                ACCESS  read-write
                STATUS  mandatory
                DESCRIPTION
                        "This configured data allows the authentication
                        procedure to generate and/or verify the
                        authentication field in the RIP header.  This
                        value again must be the same for each
                        interface on each side of the link."
                ::= { ifwanEntry 120 }

            ifwanPppSilent OBJECT-TYPE
                SYNTAX  INTEGER {
                            send-request(1),
                            wait-for-request(2),
                            not-applicable(254),
                            not-available(255)
                        }
                ACCESS  read-write
                STATUS  mandatory
                DESCRIPTION
                        "This parameter defines how this port participates in the
                         configuration negotiation process.

                         When a PPP port is Silent, it waits for a Configure-Request
                         packet from the remote peer.  Use WAIT FOR REQUEST to configure
                         the port in this way. The port must receive a request before it
                         can negotiate a connection.

	                     When a port is not Silent, it is actively trying to initialize
                         the connection with the remote peer.  Use the SEND REQUEST setting.
                         The port will send Configure-Request packets in a timeout/retry
                         sequence until the remote peer replies, at which point the two peers
                         can negotiate the connection."
                ::= { ifwanEntry 121 }

            ifwanPppConfigRestartTimer OBJECT-TYPE
                SYNTAX  INTEGER (0..255)
                ACCESS  read-write
                STATUS  mandatory
                DESCRIPTION
                        "This parameter defines the duration, in seconds, of the Restart timer,
                         which is started when a Configure-Request or Terminate-Request packet
                         is transmitted. If the timer expires a timeout occurs, followed by
                         retransmission of the packet.

                         Configure the Configuration Restart Timer parameter based on the speed
                         of the link.  The default value, 3 seconds, is designed for low-speed
                         lines (from 2400 to 9600 bps) and links having a high switching
                         latency, such as telephone lines. For higher speed links or links
                         with low switching latency the retransmission time is reduced, so the
                         Retry Period should be reduced also. For example, round trip
                         transmission times for modems at 14,400 bps are in the range of 160 to
                         600 milliseconds. A value of 1 second for the Configuration Restart
                         Timer would be appropriate."
                ::= { ifwanEntry 122 }

            ifwanPppConfigRetries OBJECT-TYPE
                SYNTAX  INTEGER (0..255)
                ACCESS  read-write
                STATUS  mandatory
                DESCRIPTION
                        "This parameter is a restart counter for Configure-Requests.
                         It defines the maximum number of successive retry periods that can
                         elapse when the port attempts to send a Configure-Request packet to
                         the remote peer. The port counts the number of retry periods that
                         elapse before receiving a Configure-Ack, Configure-Nak or
                         Configure-Reject from the peer, until it assumes that the peer is
                         unable to respond.

	                     The values 0 to 254 set a finite number of retry periods. Use the
                         value 255 to allow the port to send a Configure-Request packet an
                         unlimited number of times."
                ::= { ifwanEntry 123 }

            ifwanPppNegociateLocalMru OBJECT-TYPE
                SYNTAX  INTEGER {
                            no(1),
                            yes(2),
                            not-applicable(254),
                            not-available(255)
                        }     
                ACCESS  read-write
                STATUS  mandatory
                DESCRIPTION
                        "This parameter enables the negotiation of another MRU than the
                         default MRU value (1500 bytes). The MRU is used when sending
                         parameter values between peers to negotiate the connection. In
                         particular, it specifies the maximum number of bytes in the
                         Information and Padding fields of the PPP encapsulation frame.

                         If you set this parameter to YES, you must also configure the
                         Negotiated Local MRU parameter."
                ::= { ifwanEntry 124 }

            ifwanPppLocalMru OBJECT-TYPE
                SYNTAX  INTEGER (0..3000)
                ACCESS  read-write
                STATUS  mandatory
                DESCRIPTION
                        "This parameter determines the size of the MRU that the local port
                         offers (if greater than the default value) or requests (if less than
                         the default value) for use by the peer. The MRU specifies the maximum
                         number of bytes allowed in the Information and Padding fields of the
                         PPP encapsulation frame."
                ::= { ifwanEntry 125 }

            ifwanPppNegociatePeerMru OBJECT-TYPE
                SYNTAX  INTEGER {
                            no(1),
                            yes(2),
                            not-applicable(254),
                            not-available(255)
                        }     
                ACCESS  read-write
                STATUS  mandatory
                DESCRIPTION
                        "This parameter determines whether the port will consider either an
                        offer for a larger MRU value or a request for a smaller one. Set this
                        parameter to YES to allow the port to consider an MRU offer or request
                        from the peer. Set it to NO (the default value) to reject it.

                        If you set this parameter to YES, you must also configure the
                        Peer's MRU parameter."
                ::= { ifwanEntry 126 }

            ifwanPppPeerMruUpTo OBJECT-TYPE
                SYNTAX  INTEGER (0..3000)
                ACCESS  read-write
                STATUS  mandatory
                DESCRIPTION
                        "This parameter determines up to what limit above the default MRU value
                         the local port will set its MRU in response to an offer or request
                         from the peer."
                ::= { ifwanEntry 127 }

            ifwanPppNegociateAccm OBJECT-TYPE
                SYNTAX  INTEGER {
                            no(1),
                            yes(2),
                            not-applicable(254),
                            not-available(255)
                        }     
                ACCESS  read-write
                STATUS  mandatory
                DESCRIPTION
                        "This parameter determines whether the port will inform the remote
                         peer that it can enter into Asynchronous Control Character Map (ACCM)
                         negotiation. This option provides a way to negotiate the use of
                         control character mapping on asynchronous links.

                      	 By default, PPP maps all control characters into an appropriate
                         two-character sequence. This is usually not necessary.
                         The cleartrac uses the ACCM negotiation option to inform the remote
                         end which control characters must remain mapped, and which ones do not
                         need to remain mapped when the remote end sends them.

                    	 Set this parameter to YES to permit ACCM negotiation.
                         Set it to NO (the default value) to disallow this negotiation process.

                         If you set this parameter to YES, you must also configure the
                         Requested ACCM Characters parameter."
                ::= { ifwanEntry 128 }

            ifwanPppRequestedAccmChar OBJECT-TYPE
                SYNTAX  OCTET STRING (SIZE (4))
                ACCESS  read-write
                STATUS  mandatory
                DESCRIPTION
                        "This parameter determines the exact characters of the Asynchronous
                         Control Character Map that are requested from the remote peer.
                         The Async-Control-Character-Map field is 4 bytes long. It encoded
                         such that each numbered bit corresponds to the ASCII control
                         character of the same value. If a bit is cleared to zero, then the
                         corresponding ASCII control character must remain mapped.
                         For example, if bit 19 is set to zero, then ASCII control character
                         19 (CTRL-S) will not be changed during transmission."
                ::= { ifwanEntry 129 }

            ifwanPppAcceptAccmPeer OBJECT-TYPE
                SYNTAX  INTEGER {
                            no(1),
                            yes(2),
                            not-applicable(254),
                            not-available(255)
                        }     
                ACCESS  read-write
                STATUS  mandatory
                DESCRIPTION
                        "This parameter determines whether the port will accept a request from
                         the remote peer to enter into Asynchronous Control Character Map
                         (ACCM) negotiation.

                         Set this parameter to YES to accept the peer's request. Set it to
                         NO (the default value) to reject the request for ACCM negotiation.

                         If you set this parameter to YES, you must also configure the
                         Acceptable ACCM Characters parameter."
                ::= { ifwanEntry 130 }

            ifwanPppAcceptableAccmChar OBJECT-TYPE
                SYNTAX  OCTET STRING (SIZE (4))
                ACCESS  read-write
                STATUS  mandatory
                DESCRIPTION
                        "This parameter determines the exact characters of the Asynchronous
                         Control Character Map that will be sent to the remote peer.
                         The Async-Control-Character-Map field is 4 bytes, encoded such that
                         each numbered bit corresponds to the ASCII control character of the
                         same value. If a bit is cleared to zero, then the corresponding ASCII
                         control character must remain mapped. For example, if bit 19 is set
                         to zero, then ASCII control character 19 (CTRL-S) may be sent without
                         change."
                ::= { ifwanEntry 131 }

            ifwanPppRequestMagicNum OBJECT-TYPE
                SYNTAX  INTEGER {
                            no(1),
                            yes(2),
                            not-applicable(254),
                            not-available(255)
                        }     
                ACCESS  read-write
                STATUS  mandatory
                DESCRIPTION
                        "This parameter determines whether the port will request the Magic
                         Number from the remote peer. The Magic Number is a 4-byte field that
                         aids in the detection of link loopback conditions and other data link
                         layer anomalies.

                         Set this parameter to YES (the default value) to request the peer's
                         Magic Number. Set it to NO to disallow a Magic Number request."
                ::= { ifwanEntry 132 }

            ifwanPppAcceptMagicNum OBJECT-TYPE
                SYNTAX  INTEGER {
                            no(1),
                            yes(2),
                            not-applicable(254),
                            not-available(255)
                        }     
                ACCESS  read-write
                STATUS  mandatory
                DESCRIPTION
                        "This parameter determines whether the port will accept a request from
                         the remote peer to send the local Magic Number.

                         Set this parameter to YES (the default value) to accept the peer's
                         Magic Number request.  Set it to NO to reject the request."
                ::= { ifwanEntry 133 }

            ifwanPppAcceptOldIpAddNeg OBJECT-TYPE
                SYNTAX  INTEGER {
                            no(1),
                            yes(2),
                            not-applicable(254),
                            not-available(255)
                        }     
                ACCESS  read-write
                STATUS  mandatory
                DESCRIPTION
                        "This parameter determines whether the port will accept a request
                         from the remote peer to negotiate old IP-Addresses. Set this
                         parameter to YES to accept the peer's IP-Addresses Negotiation
                         request. The port will enter into an obsolete IP address negotiation
                         with the peer. Set it to NO (the default value) to reject this
                         configuration option."
                ::= { ifwanEntry 134 }

            ifwanPppNegociateIpAddress OBJECT-TYPE
                SYNTAX  INTEGER {
                            no(1),
                            yes(2),
                            not-applicable(254),
                            not-available(255)
                        }     
                ACCESS  read-write
                STATUS  mandatory
                DESCRIPTION
                        "This parameter enables the negotiation of an IP Address with the
                         remote peer. Set this parameter to YES (the default value) to allow
                         the port to request and accept an IP Address. Set it to NO to
                         disallow IP address negotiation."
                ::= { ifwanEntry 135 }

            ifwanPppAcceptIpAddress OBJECT-TYPE
                SYNTAX  INTEGER {
                            no(1),
                            yes(2),
                            not-applicable(254),
                            not-available(255)
                        }     
                ACCESS  read-write
                STATUS  mandatory
                DESCRIPTION
                        "This parameter determines whether the port will accept a request
                         from the remote peer to send an IP Address. Set this parameter to YES (
                         the default value) to accept the peer's request for the local IP
                         Address. Set it to NO to reject the request."
                ::= { ifwanEntry 136 }

            ifwanPppRemoteIpAddress OBJECT-TYPE
                SYNTAX  IpAddress
                ACCESS  read-write
                STATUS  mandatory
                DESCRIPTION
                        "This parameter defines the IP-Address to be sent to the remote peer
                         during negotiation of the connection. The IP-Address is specific to
                         a particular PPP session. It is a 4-byte value in dotted decimal
                         representation, with a maximum value of 255 for each byte,
                         for example 128.128.128.122. When this parameter is set to
                         000.000.000.000, no IP-Address is defined."
                ::= { ifwanEntry 137 }
                
            ifwanPppRemoteSubnetMask OBJECT-TYPE
                SYNTAX  IpAddress
                ACCESS  read-write
                STATUS  mandatory
                DESCRIPTION
                        "Subnet mask associated with the Remote IP address. It is
                         configured like the IP address: a 4-byte value in dotted
                         decimal representation, with a maximum value of 255 for each
                         byte.  The subnet mask identifies which bits of the IP address
                         correspond to the physical network, and which  bits correspond
                         to host identifiers."
                ::= { ifwanEntry 138 }

            ifwanHighPriorityTransparentClass OBJECT-TYPE
                SYNTAX  INTEGER {
                            no(1),
                            yes(2),
                            not-applicable(254),
                            not-available(255)
                        }     
                ACCESS  read-write
                STATUS  mandatory
                DESCRIPTION
                        "High priority transparent class."
                ::= { ifwanEntry 139 }

            ifwanTransparentClassNumber OBJECT-TYPE
                SYNTAX  INTEGER (1..8)
                ACCESS  read-write
                STATUS  mandatory
                DESCRIPTION
                        "The transparent priority class for voice. Classes are
                         defined according to bandwidth weight."
                ::= { ifwanEntry 140 }

            ifwanChannelCompressed OBJECT-TYPE
                SYNTAX  INTEGER {
                            no(1),
                            yes(2),
                            not-applicable(254),
                            not-available(255)
                        }     
                ACCESS  read-write
                STATUS  mandatory
                DESCRIPTION
                        "Channel compressed."
                ::= { ifwanEntry 141 }
           
	    ifwanSfType OBJECT-TYPE
                SYNTAX  INTEGER {
                            demodulator(1),
                            modulator(2),
			    expansion(3),
			    agregate(4),
                            not-applicable(254),
                            not-available(255)
                        }
                ACCESS  read-write
                STATUS  mandatory
                DESCRIPTION
                        "Specify the type of Skyframe port configured. It
                        can be a Modulator, Demodulator, Expansion or 
                        Aggregate."
                ::= { ifwanEntry 142 }

            ifwanSfMode OBJECT-TYPE
                SYNTAX  INTEGER {
                            inactive(1),
                            active(2),
                            not-applicable(254),
                            not-available(255)
                        }
                ACCESS  read-write
                STATUS  mandatory
                DESCRIPTION
                        "Enable/disable the data transmission/reception
                        on the port."
                ::= { ifwanEntry 143 }

            ifwanSfCarrierId OBJECT-TYPE
                SYNTAX  INTEGER --  (1..4294967295)
                ACCESS  read-write
                STATUS  mandatory
                DESCRIPTION
                        "Identifier of a physical port in a Skyframe system."
                ::= { ifwanEntry 144 }
           
		    IfwanShortEntry ::=
                SEQUENCE {
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER
                }
                
            IfwanT1Entry ::=
                SEQUENCE {
                    ifwanDsOSpeed-bps       INTEGER,
                    ifwanChUse              DisplayString,
                    ifwanFraming            INTEGER,
                    ifwanTerminating        INTEGER,
                    ifwanCrc4               INTEGER,
                    ifwanLineCoding         INTEGER,
                    ifwanLineBuild          INTEGER,
                    ifwanBChannels          INTEGER,
                    ifwanMultiframing       INTEGER
                }    

            IfwanG703PortEntry ::=
                SEQUENCE {
                    ifwanDesc               DisplayString,
                    ifwanProtocol           INTEGER,
                    ifwanClocking           INTEGER,
                    ifwanFraming            INTEGER,
                    ifwanCrc4               INTEGER,
                    ifwanLineCoding         INTEGER,
                    ifwanT1E1Status         INTEGER,
                    ifwanChUse              DisplayString,
                    ifwanLineBuild          INTEGER,
                    ifwanT1E1LoopBack       INTEGER
                }

            IfwanG703ChannelEntry ::=
                SEQUENCE {
                    ifwanDesc               DisplayString,
                    ifwanChUse              DisplayString,
                    ifwanProtocol           INTEGER,
                    ifwanDsOSpeed-bps       INTEGER,
                    ifwanMode               INTEGER,
                    ifwanBodCall-s          INTEGER,
                    ifwanBodHang-s          INTEGER,
                    ifwanBodLevel           INTEGER,
                    ifwanBackupCall-s       INTEGER,
                    ifwanBackupHang-s       INTEGER,
                    ifwanDialTimeout-s      INTEGER,
                    ifwanPortToBack         INTEGER,
                    ifwanClassNumber        INTEGER,
                    ifwanRingNumber         OCTET STRING (SIZE (2)),
                    ifwanIpAddress          IpAddress,
                    ifwanSubnetMask         IpAddress,
                    ifwanMaxFrame           INTEGER,
                    ifwanIpRip              INTEGER,
                    ifwanIpRipTxRx          INTEGER,
                    ifwanIpRipAuthType      INTEGER,
                    ifwanIpRipPassword      DisplayString,
                    ifwanOspfEnable         INTEGER,
                    ifwanOspfAreaId         IpAddress,
                    ifwanOspfTransitDelay   INTEGER,
                    ifwanOspfRetransmitInt  INTEGER,
                    ifwanOspfHelloInt       INTEGER,
                    ifwanOspfDeadInt        INTEGER,
                    ifwanOspfPassword       DisplayString,
                    ifwanOspfMetricCost     INTEGER,
                    ifwanCompression        INTEGER,
                    ifwanPriority           INTEGER,
                    ifwanRemoteUnit         DisplayString,
                    ifwanTimeout            INTEGER,
                    ifwanRetry              INTEGER,
                    ifwanRemotePort         INTEGER,
                    ifwanFlowControl        INTEGER,
                    ifwanMgmtInterface      INTEGER,
                    ifwanEnquiryTimer-s     INTEGER,
                    ifwanReportCycle        INTEGER,
                    ifwanCllm               INTEGER,
                    ifwanIpxRip             INTEGER,
                    ifwanIpxSap             INTEGER,
                    ifwanIpxNetNum          OCTET STRING (SIZE (4)),
                    ifwanCellPacketization  INTEGER,
                    ifwanCondLMIPort        INTEGER
                }

            IfwanRxTICEICEntry ::=
                SEQUENCE {
                    ifwanCrc4               INTEGER,
                    ifwanLineCoding         INTEGER,
                    ifwanT1E1InterBit       INTEGER,
                    ifwanEncodingLaw        INTEGER,
                    ifwanChExp              DisplayString,
                    ifwanChUse              DisplayString,
                    ifwanClocking           INTEGER,
                    ifwanT1E1LoopBack       INTEGER,
                    ifwanT1E1Status         INTEGER,
                    ifwanLineBuild          INTEGER,
                    ifwanIdleCode           OCTET STRING (SIZE(1)),
                    ifwanSignaling          INTEGER,
                    ifwanFraming            INTEGER,
                    ifwanGainLimit          INTEGER,
                    ifwanRemoteUnit         DisplayString,
                    ifwanExtNumber          DisplayString,
                    ifwanDestExtNumber      DisplayString,
                    ifwanConnTimeout-s      INTEGER,
                    ifwanQsigPbxAb          INTEGER,
                    ifwanQsigPbxXy          INTEGER,
                    ifwanHighPriorityTransparentClass INTEGER,
                    ifwanTransparentClassNumber       INTEGER,
                    ifwanChannelCompressed            INTEGER
                }

            IfwanIsdnBriVoiceEntry ::=
                SEQUENCE {
                    ifwanIndex              INTEGER,
                    ifwanDesc               DisplayString,
                    ifwanTerminating        INTEGER,
                    ifwanEncodingLaw        INTEGER,
                    ifwanTeiMode            INTEGER,
                    ifwanDigitNumber        INTEGER,
                    ifwanMsn1               DisplayString,
                    ifwanMsn2               DisplayString,
                    ifwanMsn3               DisplayString
                }

            IfwanSdlcEntry ::=
                SEQUENCE {
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanCoding             INTEGER,
                    ifwanModem              INTEGER,
                    ifwanTxStart            INTEGER,
                    ifwanIdle               INTEGER,
                    ifwanDuplex             INTEGER,
                    ifwanGroupPoll          INTEGER,
                    ifwanGroupAddress       OCTET STRING (SIZE (2)),
                    ifwanPollDelay-ms       INTEGER
                }                           
                                            
            IfwanHdlcEntry ::=              
                SEQUENCE {                  
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanCoding             INTEGER,
                    ifwanModem              INTEGER,
                    ifwanTxStart            INTEGER,
                    ifwanIdle               INTEGER,
                    ifwanFrameDelay         INTEGER,
                    ifwanRemoteUnit         DisplayString,
                    ifwanClassNumber        INTEGER,
                    ifwanRemotePort         INTEGER,
                    ifwanDsOSpeed-bps       INTEGER,
                    ifwanFraming            INTEGER,
                    ifwanTerminating        INTEGER,
                    ifwanCrc4               INTEGER,
                    ifwanLineCoding         INTEGER,
                    ifwanBChannels          INTEGER,
                    ifwanMultiframing       INTEGER
                }                           
                                            
            IfwanDdcmpEntry ::=             
                SEQUENCE {                  
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanModem              INTEGER,
                    ifwanTxStart            INTEGER,
                    ifwanRemoteUnit         DisplayString,
                    ifwanClassNumber        INTEGER,
                    ifwanRemotePort         INTEGER
                }                           
                                            
             IfwanTAsyncEntry ::=            
                SEQUENCE {                  
                    ifwanIndex              INTEGER,
                    ifwanDesc               DisplayString,
                    ifwanProtocol           INTEGER,
                    ifwanSpeed-bps          INTEGER,
                    ifwanInterface          INTEGER,
                    ifwanClocking           INTEGER,
                    ifwanFormat             INTEGER,
                    ifwanModem              INTEGER,
                    ifwanRemoteUnit         DisplayString,
                    ifwanClassNumber        INTEGER,
                    ifwanRemotePort         INTEGER
                }                           
                                            
             IfwanRAsyncEntry ::=            
                SEQUENCE {                  
                    ifwanIndex              INTEGER,
                    ifwanDesc               DisplayString,
                    ifwanProtocol           INTEGER,
                    ifwanSpeed-bps          INTEGER,
                    ifwanInterface          INTEGER,
                    ifwanClocking           INTEGER,
                    ifwanFormat             INTEGER,
                    ifwanRxFlow             INTEGER,
                    ifwanTxFlow             INTEGER,
                    ifwanTxHold-s           INTEGER,
                    ifwanRemoteUnit         DisplayString,
                    ifwanClassNumber        INTEGER,
                    ifwanRemotePort         INTEGER
                }                           
                                            
             IfwanBscEntry ::=               
                SEQUENCE {                  
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanModem              INTEGER,
                    ifwanTxStart            INTEGER,
                    ifwanRemoteUnit         DisplayString,
                    ifwanClassNumber        INTEGER,
                    ifwanRemotePort         INTEGER
                }                           
                                            
             IfwanCopEntry ::=               
                SEQUENCE {                  
                    ifwanIndex              INTEGER,
                    ifwanDesc               DisplayString,
                    ifwanProtocol           INTEGER,
                    ifwanSpeed-bps          INTEGER,
                    ifwanFallBackSpeed-bps  INTEGER,
                    ifwanFallBackSpeedEnable INTEGER,
                    ifwanInterface          INTEGER,
                    ifwanClocking           INTEGER,
                    ifwanModem              INTEGER,
                    ifwanTxStartCop         INTEGER,
                    ifwanIdle               INTEGER,
                    ifwanFormat             INTEGER,
                    ifwanSync               OCTET STRING (SIZE (2)),
                    ifwanDropSyncCounter    INTEGER,
                    ifwanDropSyncCharacter  OCTET STRING (SIZE (1)),
                    ifwanRemoteUnit         DisplayString,
                    ifwanClassNumber        INTEGER,
                    ifwanRemotePort         INTEGER
                }                           
                                            
            IfwanPvcrEntry ::=              
                SEQUENCE {                  
                    ifwanIndex              INTEGER,
                    ifwanDesc               DisplayString,
                    ifwanProtocol           INTEGER,
                    ifwanSpeed-bps          INTEGER,
                    ifwanInterface          INTEGER,
                    ifwanClocking           INTEGER,
                    ifwanMode               INTEGER,
                    ifwanBodCall-s          INTEGER,
                    ifwanBodHang-s          INTEGER,
                    ifwanBodLevel           INTEGER,
                    ifwanBackupCall-s       INTEGER,
                    ifwanBackupHang-s       INTEGER,
                    ifwanDialTimeout-s      INTEGER,
                    ifwanPortToBack         INTEGER,
                    ifwanDialer             INTEGER,
                    ifwanRingNumber         OCTET STRING (SIZE (2)),
                    ifwanIpAddress          IpAddress,
                    ifwanSubnetMask         IpAddress,
                    ifwanIpRip              INTEGER,
                    ifwanIpRipTxRx          INTEGER,
                    ifwanIpRipAuthType      INTEGER,
                    ifwanIpRipPassword      DisplayString,
                    ifwanOspfEnable         INTEGER,
                    ifwanOspfAreaId         IpAddress,
                    ifwanOspfTransitDelay   INTEGER,
                    ifwanOspfRetransmitInt  INTEGER,
                    ifwanOspfHelloInt       INTEGER,
                    ifwanOspfDeadInt        INTEGER,
                    ifwanOspfPassword       DisplayString,
                    ifwanOspfMetricCost     INTEGER,
                    ifwanCompression        INTEGER,
                    ifwanPriority           INTEGER,
                    ifwanRemoteUnit         DisplayString,
                    ifwanTimeout            INTEGER,
                    ifwanRetry              INTEGER,
                    ifwanIpxRip             INTEGER,
                    ifwanIpxSap             INTEGER,
                    ifwanIpxNetNum          OCTET STRING (SIZE (4)),
                    ifwanDsOSpeed-bps       INTEGER,
                    ifwanFraming            INTEGER,
                    ifwanTerminating        INTEGER,
                    ifwanCrc4               INTEGER,
                    ifwanLineCoding         INTEGER,
                    ifwanBChannels          INTEGER,
                    ifwanMultiframing       INTEGER,
                    ifwanMaxChannels        INTEGER
                }                           
                                            
            IfwanPassthruEntry ::=          
                SEQUENCE {                  
                    ifwanIndex              INTEGER,
                    ifwanDesc               DisplayString,
                    ifwanProtocol           INTEGER,
                    ifwanSpeed-bps          INTEGER,
                    ifwanInterface          INTEGER,
                    ifwanClocking           INTEGER,
                    ifwanModem              INTEGER,
                    ifwanTxStartPass        INTEGER,
                    ifwanRemoteUnit         DisplayString,
                    ifwanClassNumber        INTEGER,
                    ifwanRemotePort         INTEGER
                }                           
                                            
            IfwanFrNetEntry ::=            
                SEQUENCE {                  
                    ifwanIndex              INTEGER,
                    ifwanDesc               DisplayString,
                    ifwanProtocol           INTEGER,
                    ifwanSpeed-bps          INTEGER,
                    ifwanInterface          INTEGER,
                    ifwanClocking           INTEGER,
                    ifwanModem              INTEGER,
                    ifwanFrameDelay         INTEGER,
                    ifwanFallBackSpeed-bps  INTEGER,
                    ifwanFlowControl        INTEGER,
                    ifwanMgmtInterface      INTEGER,
                    ifwanEnquiryTimer-s     INTEGER,
                    ifwanCllm               INTEGER,
                    ifwanDsOSpeed-bps       INTEGER,
                    ifwanFraming            INTEGER,
                    ifwanTerminating        INTEGER,
                    ifwanCrc4               INTEGER,
                    ifwanLineCoding         INTEGER,
                    ifwanBChannels          INTEGER,
                    ifwanMultiframing       INTEGER,
                    ifwanMaxChannels        INTEGER,
                    ifwanCondLMIPort        INTEGER
                }                           
                                            
            IfwanFrUserEntry ::=            
                SEQUENCE {                  
                    ifwanIndex              INTEGER,
                    ifwanDesc               DisplayString,
                    ifwanProtocol           INTEGER,
                    ifwanSpeed-bps          INTEGER,                  
                    ifwanInterface          INTEGER,
                    ifwanClocking           INTEGER,
                    ifwanMgmtInterface      INTEGER,
                    ifwanFlowControl        INTEGER,
                    ifwanEnquiryTimer-s     INTEGER,
                    ifwanReportCycle        INTEGER,
                    ifwanCllm               INTEGER,
                    ifwanDsOSpeed-bps       INTEGER,
                    ifwanFraming            INTEGER,
                    ifwanTerminating        INTEGER,
                    ifwanCrc4               INTEGER,
                    ifwanLineCoding         INTEGER,
                    ifwanBChannels          INTEGER,
                    ifwanMultiframing       INTEGER,
                    ifwanMaxChannels        INTEGER,
                    ifwanSvcAddressType                     INTEGER,
                    ifwanSvcNetworkAddress                  DisplayString,
                    ifwanSvcMaxTxTimeoutT200                INTEGER,
                    ifwanSvcInactiveTimeoutT203             INTEGER,
                    ifwanSvcIframeRetransmissionsN200       INTEGER,
                    ifwanSvcSetupTimeoutT303                INTEGER,
                    ifwanSvcDisconnectTimeoutT305           INTEGER,
                    ifwanSvcReleaseTimeoutT308              INTEGER,
                    ifwanSvcCallProceedingTimeoutT310       INTEGER,
                    ifwanSvcStatusTimeoutT322               INTEGER
                }


            IfwanX25Entry ::=
                SEQUENCE {                  
                    ifwanIndex              INTEGER,
                    ifwanDesc               DisplayString,
                    ifwanProtocol           INTEGER,
                    ifwanSpeed-bps          INTEGER,                  
                    ifwanFallBackSpeed-bps  INTEGER,
                    ifwanFallBackSpeedEnable INTEGER,
                    ifwanInterface          INTEGER,
                    ifwanClocking           INTEGER,
                    ifwanX25Encapsulation   INTEGER,
                    ifwanPvcNumber          INTEGER
                }

            IfwanSFEntry ::=            
                SEQUENCE {                  
                    ifwanIndex              INTEGER,
                    ifwanDesc               DisplayString,
                    ifwanProtocol           INTEGER,
                    ifwanSfType				INTEGER,
                    ifwanSpeed-bps          INTEGER,
                    ifwanInterface          INTEGER,
                    ifwanClocking           INTEGER,
                    ifwanFlowControl        INTEGER,
                    ifwanCllm               INTEGER,
                    ifwanCellPacketization  INTEGER,
                    ifwanMaxChannels        INTEGER,
					ifwanSfMode		        INTEGER,
                    ifwanSfCarrierId        INTEGER
                }                           

            IfwanPppEntry ::=
                SEQUENCE {                  
                    ifwanIndex                  INTEGER,
                    ifwanDesc                   DisplayString,
                    ifwanProtocol               INTEGER,
                    ifwanFormat                 INTEGER,
                    ifwanSpeed-bps              INTEGER,
                    ifwanInterface              INTEGER,
                    ifwanClocking               INTEGER,
                    ifwanCoding                 INTEGER,
                    ifwanModem                  INTEGER,
                    ifwanTxStart                INTEGER,
                    ifwanIdle                   INTEGER,
                    ifwanFrameDelay             INTEGER,
                    ifwanRxFlow                 INTEGER,
                    ifwanTxFlow                 INTEGER,
                    ifwanTxHold-s               INTEGER,
                    ifwanIpAddress              IpAddress,
                    ifwanSubnetMask             IpAddress,
                    ifwanIpRip                  INTEGER,
                    ifwanIpRipTxRx              INTEGER,
                    ifwanIpRipAuthType          INTEGER,
                    ifwanIpRipPassword          DisplayString,
                    ifwanPppSilent              INTEGER,
                    ifwanPppConfigRestartTimer  INTEGER,
                    ifwanPppConfigRetries       INTEGER,
                    ifwanPppNegociateLocalMru   INTEGER,
                    ifwanPppLocalMru            INTEGER,
                    ifwanPppNegociatePeerMru    INTEGER,
                    ifwanPppPeerMruUpTo         INTEGER,
                    ifwanPppNegociateAccm       INTEGER,
                    ifwanPppRequestedAccmChar   OCTET STRING (SIZE (4)),
                    ifwanPppAcceptAccmPeer      INTEGER,
                    ifwanPppAcceptableAccmChar  OCTET STRING (SIZE (4)),
                    ifwanPppRequestMagicNum     INTEGER,
                    ifwanPppAcceptMagicNum      INTEGER,
                    ifwanPppAcceptOldIpAddNeg   INTEGER,
                    ifwanPppNegociateIpAddress  INTEGER,
                    ifwanPppAcceptIpAddress     INTEGER,
                    ifwanPppRemoteIpAddress     IpAddress,
                    ifwanPppRemoteSubnetMask    IpAddress
                }


            -- The ifvce group (voice)
            
            -- This group lets you configure the parameters for voice ports.
            
            ifvceNumber OBJECT-TYPE
                SYNTAX  INTEGER
                ACCESS  read-only
                STATUS  mandatory
                DESCRIPTION
                        "The number of voice interfaces present on this system."
                ::= { ifvce 1 }
                
            -- the ifvce table    
            
            ifvceTable OBJECT-TYPE
                SYNTAX  SEQUENCE OF IfvceEntry
                ACCESS  not-accessible
                STATUS  mandatory
                DESCRIPTION
                        "A list of interface entries.  The number of
                        entries is given by the value of ifvceNumber."
                ::= { ifvce 2 }
            
            ifvceEntry OBJECT-TYPE
                SYNTAX  IfvceEntry
                ACCESS  not-accessible
                STATUS  mandatory
                DESCRIPTION
                        "This table contains the principal configurable
                        parameters which are used for a particular voice
                        interface."
                INDEX   { ifvceIndex }
                ::= { ifvceTable 1 }
            
            IfvceEntry ::=
                SEQUENCE {                                  --  Correspond to the following profile parameters
                    ifvceIndex              INTEGER,
                    ifvceDesc               DisplayString,
                    ifvceProtocol           INTEGER,        --  CFG-VPORT-PROTOCOL
                    ifvceInterface          INTEGER,        --  CFG-VPORT-INTRF
                    ifvceRemotePort         INTEGER,        --  CFG-VPORT-DSTPORT
                    ifvceActivationType     INTEGER,        --  CFG-VPORT-ACTIVATION-TYPE
                    ifvceRemoteUnit         DisplayString,  --  CFG-VPORT-DSTUNIT
                    ifvceHuntGroup          INTEGER,        --  CFG-VPORT-HUNT-GROUP
                    ifvcePulseMakeBreak-ms  INTEGER,        --  CFG-VPORT-PULSE-MAKE-BREAK
                    ifvceToneDetectRegen-s  INTEGER,        --  CFG-VPORT-DTMF-DET-REGEN
                    ifvceToneOn-ms          INTEGER,        --  CFG-VPORT-DTMF-THRESHOLD-ON
                    ifvceToneOff-ms         INTEGER,        --  CFG-VPORT-DTMF-THRESHOLD-OFF
                    ifvceSilenceSuppress    INTEGER,        --  CFG-VPORT-SILENCE-SUP
                    ifvceToneEnergyDetec    INTEGER,        --  CFG-VPORT-DTMF-ENERGY-DETEC
                    ifvceDVCSilenceSuppress INTEGER,        --  CFG-VPORT-SILENCE-SUP
                    ifvceSignaling          INTEGER,        --  CFG-VPORT-SIGNALING
                    ifvceDTalkThreshold     INTEGER,        --  CFG-VPORT-DOUBLE-TALK-THRESHOLD
                    ifvceLocalInbound       INTEGER,        --  CFG-VPORT-INBOUND-LEVEL
                    ifvceDVCLocalInbound    INTEGER,        --  CFG-VPORT-INBOUND-LEVEL
                    ifvceLocalOutbound      INTEGER,        --  CFG-VPORT-OUTBOUND-LEVEL
                    ifvceDVCLocalOutbound   INTEGER,        --  CFG-VPORT-OUTBOUND-LEVEL
                    ifvceFaxModemRelay      INTEGER,        --  CFG-VPORT-FAX-MODEM-RELAY
                    ifvceMaxFaxModemRate    INTEGER,        --  CFG-VPORT-FAX-MODEM-MAX-RATE
                    ifvceFxoTimeout-s       INTEGER,        --  CFG-VPORT-FXO-TIMEOUT
                    ifvceTeTimer-s          INTEGER,        --  CFG-VPORT-E-M-TE-TIMER
                    ifvceFwdDigits          INTEGER,        --  CFG-VPORT-FWD-DIGITS
                    ifvceFwdType            INTEGER,        --  CFG-VPORT-FWD-TYPE
                    ifvceFwdDelay-ms        INTEGER,        --  CFG-VPORT-FWD-DELAY
                    ifvceDelDigits          INTEGER,        --  CFG-VPORT-DEL-DIGITS
                    ifvceExtNumber          DisplayString,  --  CFG-VPORT-EXTENSION-NUMBER
                    ifvceLinkDwnBusy        INTEGER,        --  CFG-VPORT-LINK-DOWN-BUSY
                    ifvceToneType           INTEGER,        --  CFG-VPORT-TONE-TYPE
                    ifvceRate8kx1           INTEGER,        --  CFG-VPORT-RATE-8KX1
                    ifvceRate8kx2           INTEGER,        --  CFG-VPORT-RATE-8KX2
                    ifvceRate8kx3           INTEGER,        --  CFG-VPORT-RATE-8KX3
                    ifvceRate6kx1           INTEGER,        --  CFG-VPORT-RATE-6KX1
                    ifvceRate6kx2           INTEGER,        --  CFG-VPORT-RATE-6KX2
                    ifvceRate6kx3           INTEGER,        --  CFG-VPORT-RATE-6KX3
                    ifvceRate5k8x1          INTEGER,        --  CFG-VPORT-RATE-5K8X1
                    ifvceRate5k8x2          INTEGER,        --  CFG-VPORT-RATE-5K8X2
                    ifvceRate4k8x1          INTEGER,        --  CFG-VPORT-RATE-4K8X1
                    ifvceRate4k8x2          INTEGER,        --  CFG-VPORT-RATE-4K8X2
                    ifvceBroadcastDir       INTEGER,        --  CFG-VPORT-BROADCAST-DIR
                    ifvceBroadcastPvc       INTEGER,        --  CFG-VPORT-BROADCAST-PVC
                    ifvceAnalogLinkDwnBusy  INTEGER,        --  Prior to 7.0.3 only.
                    ifvceSpeedDialNum       DisplayString,  --  CFG-VPORT-SPEED-DIAL
                    ifvceExtendedDigitSrc   INTEGER,        --  CFG-VPORT-EXTENDED-SRC
                    ifvceR2ExtendedDigitSrc INTEGER,        --  No longer supported by the NP Agent
                    ifvceR2Group2Digit      INTEGER,        --  CFG-VPORT-R2-GROUP2
                    ifvceR2CompleteDigit    INTEGER,        --  CFG-VPORT-R2-COMPLETE-DIG
                    ifvceR2BusyDigit        INTEGER,        --  CFG-VPORT-R2-BUSY-DIG
                    ifvceDtmfOnTime         INTEGER,        --  CFG-VPORT-DTMF-ON-TIME
                    ifvceEnableDtmfOnTime   INTEGER         --  CFG-VPORT-ENABLE-DTMF-CFG
                }

            -- ********** Port Number **********
            ifvceIndex OBJECT-TYPE
                SYNTAX  INTEGER                                         --  offsetted profile number
                ACCESS  read-only
                STATUS  mandatory
                DESCRIPTION
                        "A unique value for each voice interface."
                ::= { ifvceEntry 1 }
            
            -- ********** Description **********
            ifvceDesc OBJECT-TYPE
                SYNTAX  DisplayString                                   --  no profile equivalent
                ACCESS  read-only
                STATUS  mandatory
                DESCRIPTION
                        "A textual string containing information about 
                        a specific interface."
                ::= { ifvceEntry 2 }
            
            -- ********** Protocol **********
            ifvceProtocol OBJECT-TYPE                                   --  CFG-VPORT-PROTOCOL
                SYNTAX  INTEGER {                                       --  add a 1 offset to the following profile parameter values:
                            off(1),                                     --  CFG-PORT-PROT-OFF
                            acelp-8-kbs(21),                            --  CFG-PORT-PROT-ACELP8K
                            acelp-4-8-kbs(22),                          --  CFG-PORT-PROT-ACELP4-8K
                            pcm64k(23),                                 --  CFG-PORT-PROT-PCM64K  
                            adpcm32k(24),                               --  CFG-PORT-PROT-ADPCM32K
                            atc16k(26),                                 --  CFG-PORT-PROT-ATC16K
                            acelp-cn(30),                               --  CFG-PORT-PROT-ACELPCN
                            not-applicable(254),
                            not-available(255)
                            }
                ACCESS  read-write
                STATUS  mandatory
                DESCRIPTION
                        "Operating protocol for the NetVoice port. Enter 
                        ACELP 8 kbs, ACELP 4.8 kbs when you want 
                        to use the port for voice/fax transmissions.
                        Select the OFF value when the port is not used."
                ::= { ifvceEntry 3 }
            
            -- ********** Interface Type **********
            ifvceInterface OBJECT-TYPE                                  --  CFG-VPORT-INTRF
                SYNTAX  INTEGER {                                       --  correspond to unoffsetted profile parameter values:
                            fxs(1),                                     --  CALLV-FXS-INTERFACE
                            fx0(2),                                     --  CALLV-FXO-INTERFACE
                            e-and-m(3),                                 --  CALLV-E-M-INTERFACE
                            ac15(4),                                    --  CALLV-AC15-INTERFACE
                            not-applicable(254),
                            not-available(255)
                        }
                ACCESS  read-write
                STATUS  mandatory
                DESCRIPTION
                        "fxs: Used when connecting to a POTS line or fx0 unit.
                        e-and-m: Used when connecting to the trunk side of a PBX.
                        fx0: Used when connecting to a CO or the station side of a PBX."

                ::= { ifvceEntry 4 }
                
            -- ********** Remote port number **********
            ifvceRemotePort OBJECT-TYPE                                 --  CFG-VPORT-DSTPORT
                SYNTAX  INTEGER (1..899)                                --  correspond to unoffsetted profile parameter values:
                ACCESS  read-write
                STATUS  mandatory
                DESCRIPTION
                        "Specifies the port number on the remote unit for 
                        setting up predefined line activation. Select the number of 
                        the port connected to the device you want to reach."
                ::= { ifvceEntry 5 }
                
            -- ********** Remote port number **********
            ifvceActivationType OBJECT-TYPE                             --  CFG-VPORT-ACTIVATION-TYPE
                SYNTAX  INTEGER {                                       --  add a 1 offset to the following profile parameter values:
                            predefined(1),                              --  CALLV-ACTIVATION-PREDEFINED
                            switched(2),                                --  CALLV-ACTIVATION-SWITCHED
                            autodial(3),
                            broadcast(4),
                            not-applicable(254),
                            not-available(255)
                        }
                ACCESS  read-write
                STATUS  mandatory
                DESCRIPTION
                        "For each cleartrac voice port, voice/fax line activation can be configured according
                         to one of the following activation types."
                ::= { ifvceEntry 6 }
                
            -- ********** Remote Unit **********
            ifvceRemoteUnit OBJECT-TYPE                                 --  CFG-VPORT-DSTUNIT
                SYNTAX  DisplayString
                ACCESS  read-write
                STATUS  mandatory
                DESCRIPTION
                        "Specifies the unit name of the NetVoice card at the remote 
                        site, for setting up predefined line activation."
                ::= { ifvceEntry 7 }
                
            -- ********** Hunt Group active **********
            ifvceHuntGroup OBJECT-TYPE                                  --  CFG-VPORT-HUNT-GROUP        
                SYNTAX  INTEGER {                                       --  add a 1 offset to the profile parameter:
                            no(1),
                            a(2),
                            b(3),
                            not-applicable(254),
                            not-available(255)
                            } 
                ACCESS  read-write
                STATUS  mandatory
                DESCRIPTION
                        "When line activation is defined as switched, this parameter 
                        permits hunting more than one port to place an incoming call."
                ::= { ifvceEntry 8 }
                
            -- ********** Tone detection/regenaration **********
            ifvceToneDetectRegen-s OBJECT-TYPE                          --  CFG-VPORT-DTMF-DET-REGEN
                SYNTAX  INTEGER (0..256)                                --  correspond to unoffsetted profile parameter values:
                ACCESS  read-write
                STATUS  mandatory
                DESCRIPTION
                        "This parameter specifies the number of seconds during which
                        Tone tones will be detected and regenerated."
                ::= { ifvceEntry 9 }
                
            -- ********** Pulse make/break ration **********
            ifvcePulseMakeBreak-ms OBJECT-TYPE                         --  CFG-VPORT-PULSE-MAKE-BREAK
                SYNTAX  INTEGER (20..80)                                --  correspond to unoffsetted profile parameter values:
                ACCESS  read-write
                STATUS  mandatory
                DESCRIPTION
                        "This parameter specifies the duration, in milliseconds, of
                        the contact(or make) for each digit that is dialed using rotary
                        type dialing."
                ::= { ifvceEntry 10 }
                
            -- ********** Tone ON threshold (msec) **********
            ifvceToneOn-ms OBJECT-TYPE                                 --  CFG-VPORT-DTMF-THRESHOLD-ON
                SYNTAX  INTEGER (30..1000)                              --  correspond to unoffsetted profile parameter values:
                ACCESS  read-write
                STATUS  mandatory
                DESCRIPTION
                        "This parameter specifies the duration, in milliseconds, of
                        the tone used to produce a single Tone digit."
                ::= { ifvceEntry 11 }
                
            -- ********** Tone OFF threshold (msec) **********
            ifvceToneOff-ms OBJECT-TYPE                                --  CFG-VPORT-DTMF-THRESHOLD-OFF
                SYNTAX  INTEGER (30..1000)                              --  correspond to unoffsetted profile parameter values:
                ACCESS  read-write
                STATUS  mandatory
                DESCRIPTION
                        "This parameter specifies the duration, in milliseconds, of
                        the silence between Tone tones in a dial digit string."
                ::= { ifvceEntry 12 }
                
            -- ********** Silence suppression level **********
            ifvceSilenceSuppress OBJECT-TYPE                            --  CFG-VPORT-SILENCE-SUP
                SYNTAX  INTEGER (4..20)                                 --  correspond to unoffsetted profile parameter values:
                ACCESS  read-write
                STATUS  mandatory
                DESCRIPTION
                        "This parameter specifies the degree to which periods of silence
                         will be suppressed and reduced during transmission. A higher Silence
                         Suppression level increases the attenuation of the line, lowers 
                         background noise and reduces overall bandwidth use.
                         ONLY FOR EXPANSION CARDS OTHER THAN DVC"
                ::= { ifvceEntry 13 }
                
            -- ********** Silence suppression level **********
            ifvceDVCSilenceSuppress OBJECT-TYPE                         --  CFG-VPORT-SILENCE-SUP
                SYNTAX  INTEGER (1..5)                                  --  correspond to unoffsetted profile parameter values:
                ACCESS  read-write
                STATUS  mandatory
                DESCRIPTION
                        "This parameter specifies the degree to which periods of silence
                         will be suppressed and reduced during transmission. A higher Silence
                         Suppression level increases the attenuation of the line, lowers 
                         background noise and reduces overall bandwidth use.
                         ONLY FOR DVC CARDS"
                ::= { ifvceEntry 33 }
                
            -- ********** Signaling type **********
            ifvceSignaling OBJECT-TYPE                                  --  CFG-VPORT-SIGNALING
                SYNTAX  INTEGER {                                       --  add a 1 offset to the following profile parameter values:
                            e-and-m-4w-imm-start(1),                    --  CALLV-FOUR-W-E-M-IMS,
                            e-and-m-2W-imm-start(2),                    --  CALLV-TWO-W-E-M-IMS,
                            loop-start(3),                              --  CALLV-LOOP-START
                            ac15-a(4),                                  --  CALLV-AC15A
                            ac15-c(6),                                  --  CALLV-AC15C
                            e-and-m-4w-timed-e(10),                     --  CALLV-FOUR-W-E-M-TE
                            e-and-m-2W-timed-e(11),                     --  CALLV-TWO-W-E-M-TE,
                            e-and-m-4W-wink-start(12),                  --  CALLV-FOUR-W-E-M-WINK
                            e-and-m-2W-wink-start(13),                  --  CALLV-TWO-W-E-M-WINK,
                            e-and-m-4W-delay-dial(14),                  --  CALLV-FOUR-W-E-M-DD
                            e-and-m-2W-delay-dial(15),                  --  CALLV-TWO-W-E-M-DD,
                            e-and-m-4W-colisee(17),
                            e-and-m-2W-colisee(18),
                            imm-start(21),
                            r2(22),
                            fxo(23),
                            fxs(24),
                            gnd-fxo(25),
                            gnd-fxs(26),
                            plar(27),
                            poi(28),
                            wink-start(32),
                            ab00(30),
                            not-applicable(254),
                            not-available(255)
                        }
                ACCESS  read-write
                STATUS  mandatory
                DESCRIPTION
                        "The signaling protocol of this port."
                ::= { ifvceEntry 14 }

            -- ********** Local inbound voice level (db) **********
            ifvceLocalInbound OBJECT-TYPE                              --  CFG-VPORT-INBOUND-LEVEL
                SYNTAX  INTEGER {                                       --  add a 1 offset to the profile parameter
                        db-22(1),
                        db-21(2),
                        db-20(3),
                        db-19(4),
                        db-18(5),
                        db-17(6),
                        db-16(7),
                        db-15(8),
                        db-14(9),
                        db-13(10),
                        db-12(11),
                        db-11(12),
                        db-10(13),
                        db-9(14),
                        db-8(15),
                        db-7(16),
                        db-6(17),
                        db-5(18),
                        db-4(19),
                        db-3(20),
                        db-2(21),
                        db-1(22),
                        db0(23),
                        db1(24),
                        db2(25),
                        db3(26),
                        db4(27),
                        db5(28),
                        db6(29),
                        db7(30),
                        not-applicable(254),
                        not-available(255)
                        }
                ACCESS  read-write
                STATUS  mandatory
                DESCRIPTION
                        "This parameter specifies the local voice level into the port,
                        measured in 1 db increments.
                        ONLY FOR CARDS OTHER THAN DVC"
                ::= { ifvceEntry 16 }
            
            -- ********** Local outbound voice level (db) **********
            ifvceLocalOutbound OBJECT-TYPE                             --  CFG-VPORT-OUTBOUND-LEVEL
                SYNTAX  INTEGER {                                       --  add a 1 offset to the profile parameter
                        db-22(1),
                        db-21(2),
                        db-20(3),
                        db-19(4),
                        db-18(5),
                        db-17(6),
                        db-16(7),
                        db-15(8),
                        db-14(9),
                        db-13(10),
                        db-12(11),
                        db-11(12),
                        db-10(13),
                        db-9(14),
                        db-8(15),
                        db-7(16),
                        db-6(17),
                        db-5(18),
                        db-4(19),
                        db-3(20),
                        db-2(21),
                        db-1(22),
                        db0(23),
                        db1(24),
                        db2(25),
                        db3(26),
                        db4(27),
                        db5(28),
                        db6(29),
                        db7(30),
                        not-applicable(254),
                        not-available(255)
                        }
                ACCESS  read-write
                STATUS  mandatory
                DESCRIPTION
                        "This parameter specifies the local voice level out of the port,
                        measured in 1 db increments.
                        ONLY FOR CARDS OTHER THAN DVC"
                ::= { ifvceEntry 17 }
                
            -- ********** Local inbound voice level (db) **********
            ifvceDVCLocalInbound OBJECT-TYPE                            --  CFG-VPORT-INBOUND-LEVEL
                SYNTAX  INTEGER {                                       --  add a 1 offset to the profile parameter
                        db-12(9),
                        db-11(10),
                        db-10(11),
                        db-9(12),
                        db-8(13),
                        db-7(14),
                        db-6(15),
                        db-5(16),
                        db-4(17),
                        db-3(18),
                        db-2(19),
                        db-1(20),
                        db0(21),
                        db1(22),
                        db2(23),
                        db3(24),
                        db4(25),
                        db5(26),
                        db6(27),
                        not-applicable(254),
                        not-available(255)
                        }
                ACCESS  read-write
                STATUS  mandatory
                DESCRIPTION
                        "This parameter specifies the local voice level into the port,
                        measured in 1 db increments.
                        ONLY FOR DVC CARDS"
                ::= { ifvceEntry 34 }
            
            -- ********** Local outbound voice level (db) **********
            ifvceDVCLocalOutbound OBJECT-TYPE                           --  CFG-VPORT-OUTBOUND-LEVEL
                SYNTAX  INTEGER {                                       --  add a 1 offset to the profile parameter
                        db-12(9),
                        db-11(10),
                        db-10(11),
                        db-9(12),
                        db-8(13),
                        db-7(14),
                        db-6(15),
                        db-5(16),
                        db-4(17),
                        db-3(18),
                        db-2(19),
                        db-1(20),
                        db0(21),
                        db1(22),
                        db2(23),
                        db3(24),
                        db4(25),
                        db5(26),
                        db6(27),
                        not-applicable(254),
                        not-available(255)
                        }
                ACCESS  read-write
                STATUS  mandatory
                DESCRIPTION
                        "This parameter specifies the local voice level out of the port,
                        measured in 1 db increments.
                        ONLY FOR DVC CARDS"
                ::= { ifvceEntry 35 }
                
            -- ********** FAX/MODEM relay Enable **********
            ifvceFaxModemRelay OBJECT-TYPE                                       --  CFG-VPORT-FAX-MODEM-RELAY
                SYNTAX  INTEGER {                                       --  add a 1 offset to the profile parameter
                        none(1),
                        fax(2),
                        both(3),
                       -- adpcm-16k-bypass(4),
                       -- adpcm-24k-bypass(5),
                       -- adpcm-32k-bypass(6),
                       -- adpcm-40k-bypass(7),
                        not-applicable(254),
                        not-available(255)
                        }
                ACCESS  read-write
                STATUS  mandatory
                DESCRIPTION
                        "This parameter enables or disables handling of fax or modem calls on
                        this unit's voice channel."
                ::= { ifvceEntry 18 }
            
            -- ********** FAX/MODEM maximum rate **********
            ifvceMaxFaxModemRate OBJECT-TYPE                            --  CFG-VPORT-FAX-MODEM-MAX-RATE
                SYNTAX  INTEGER {                                       --  add a 1 offset to the profile parameter
                        rate-14400(1),
                        rate-12000(2),
                        rate-9600(3),
                        rate-7200(4),
                        rate-4800(5),
                        not-applicable(254),
                        not-available(255)
                        }
                ACCESS  read-write
                STATUS  mandatory
                DESCRIPTION
                        "This parameter enables or disables handling of fax or modem calls on
                        this unit's voice channel."
                ::= { ifvceEntry 44 }
            
            -- ********** fx0 timeout (sec) **********
            ifvceFxoTimeout-s OBJECT-TYPE                              --  CFG-VPORT-FXO-TIMEOUT
                SYNTAX  INTEGER (1..99)                                 --  unoffsetted parameter value
                ACCESS  read-write
                STATUS  mandatory
                DESCRIPTION
                        "This parameter determines the maximum amount of time, in seconds,
                        that the local port will wait for a fax transmission to begin."
                ::= { ifvceEntry 19 }
                
            -- ********** TE timer (sec) **********
            ifvceTeTimer-s OBJECT-TYPE                                 --  CFG-VPORT-E-M-TE-TIMER  
                SYNTAX  INTEGER (0..255)                                --  unoffsetted parameter value
                ACCESS  read-write
                STATUS  mandatory
                DESCRIPTION
                        "This parameter determines the delay, in seconds, between
                        M-lead and E-lead activation when the starting method is timed
                        e-and-m."
                ::= { ifvceEntry 20 }
             
            -- ********** Forward tel number (no of digits) **********
            ifvceFwdDigits OBJECT-TYPE                                 --  CFG-VPORT-FWD-DIGITS
                SYNTAX  INTEGER {                                       --  add a 1 offset to the profile parameter
                            none(1),                                    --  CFG-PORT-FWD-NONE               
                            all(2),                                     --  CFG-PORT-FWD-ALL                
                            ext(3),                                     --  CFG-PORT-FWD-EXT                
                            not-applicable(254),
                            not-available(255)
                            }
                ACCESS  read-write
                STATUS  mandatory
                DESCRIPTION
                        "This parameter specifies which dial digits (if any) should be
                        forwarded to the remote unit. When set to 0, no dial
                        digits are forwarded to the destination device when a call is
                        initiated on this channel. When set to a non-zero value, the
                        specified number of dial digits are forwarded."
                ::= { ifvceEntry 21 }
                
             
            -- ********** Forward tel number (encodeing) **********
            ifvceFwdType OBJECT-TYPE                                   --  CFG-VPORT-FWD-TYPE
                SYNTAX  INTEGER {                                       --  add a 1 offset to the profile parameter
                            tone(1),                                    --  CFG-DTMF-DIALING
                            pulse(2),                                   --  CFG-PULSE-DIALING
                            not-applicable(254),
                            not-available(255)
                            }
                ACCESS  read-write
                STATUS  mandatory
                DESCRIPTION
                        "This parameter specifies how the dial digits are sent to the 
                        remote unit for forwarding to the attached device such
                         as a PBX. It can do it using pulse dial or Tone."
                ::= { ifvceEntry 22 }
             
            -- ********** Forward delay **********
            ifvceFwdDelay-ms OBJECT-TYPE                               --  CFG-VPORT-FWD-DELAY
                SYNTAX  INTEGER (0..10000)                              --  unoffsetted parameter value
                ACCESS  read-write
                STATUS  mandatory
                DESCRIPTION
                        "This parameter specifies the length, in milliseconds, of a pause
                        that precedes the forwarded dial digit string. The value entered
                        with a SET is rounded down to the nearest multiple of 250 ms"
                ::= { ifvceEntry 23 }
            
            -- ********** Ext. Source **********
            ifvceDelDigits OBJECT-TYPE                                  --  CFG-VPORT-DEL-DIGITS
                SYNTAX  INTEGER (0..4)                                  --  unoffsetted parameter value
                ACCESS  read-write
                STATUS  mandatory
                DESCRIPTION
                        "This parameter specifies the number of leading dial digits (if any) that will be deleted from
                         a dial string before it is forwarded to the attached voice equipment. When set to 0, no
                         dial digits are deleted."
                ::= { ifvceEntry 24 }
            
            -- **********  **********
            ifvceExtNumber OBJECT-TYPE                                  --  CFG-VPORT-EXTENSION-NUMBER
                SYNTAX  DisplayString
                ACCESS  read-write
                STATUS  mandatory
                DESCRIPTION
                        "This parameter specifies the extension number for the end device attached to this voice port."
                ::= { ifvceEntry 25 }
            
            -- **********  **********
            ifvceLinkDwnBusy OBJECT-TYPE                                
                SYNTAX  INTEGER {                                       
                        no(1),
                        yes(2),
                        broadcast(3),
                        not-applicable(254),
                        not-available(255)
                    }                        
                ACCESS  read-write
                STATUS  mandatory
                DESCRIPTION
                        "Used by SDM-9400 and V410 VFC03 cards and by the SDM-9350
                         and V352 voice ports for versions 7.1.0 and higher.
                         Used only for DVC cards for versions 7.0.3 and lower.
                         See also ifvceAnalogLinkDwnBusy for versions 7.0.3 and lower."
                ::= { ifvceEntry 27 }

          -- **********  **********
            ifvceToneType OBJECT-TYPE                                   --  CFG-VPORT-TONE-TYPE   
                SYNTAX  INTEGER {  
                            dtmf(0),
                            mf(1),
                            r2(2),
                            not-applicable(254),
                            not-available(255)
                        }              
                ACCESS  read-write
                STATUS  mandatory
                DESCRIPTION
                        "This parameter specifies the kind of multi-frequency tone that will be detected on this port."
                ::= { ifvceEntry 28 }
            
            -- **********  **********
            ifvceRate8kx1 OBJECT-TYPE                                --  CFG-VPORT-DVC-RATE-8KX1  
                SYNTAX  INTEGER {  
                            no(1),
                            yes(2),
                            not-applicable(254),
                            not-available(255)
                        }              
                ACCESS  read-write
                STATUS  mandatory
                DESCRIPTION
                        "This parameter enables fallback to 8 Kbps with single buffering."
                ::= { ifvceEntry 29 }
            
            -- **********  **********
            ifvceRate8kx2 OBJECT-TYPE                                --  CFG-VPORT-DVC-RATE-8KX2  
                SYNTAX  INTEGER {  
                            no(1),
                            yes(2),
                            not-applicable(254),
                            not-available(255)
                        }              
                ACCESS  read-write
                STATUS  mandatory
                DESCRIPTION
                        "This parameter enables fallback to 8 Kbps with double buffering."
                ::= { ifvceEntry 30 }
            
            -- **********  **********
            ifvceRate5k8x1 OBJECT-TYPE                               --  CFG-VPORT-DVC-RATE-5K8X1  
                SYNTAX  INTEGER {  
                            no(1),
                            yes(2),
                            not-applicable(254),
                            not-available(255)
                        }              
                ACCESS  read-write
                STATUS  mandatory
                DESCRIPTION
                        "This parameter enables fallback to 5.8 Kbps with single buffering."
                ::= { ifvceEntry 31 }
            
            -- **********  **********
            ifvceRate5k8x2 OBJECT-TYPE                               --  CFG-VPORT-DVC-RATE-5K8X2
                SYNTAX  INTEGER {  
                            no(1),
                            yes(2),
                            not-applicable(254),
                            not-available(255)
                        }              
                ACCESS  read-write
                STATUS  mandatory
                DESCRIPTION
                        "This parameter enables fallback to 5.8 Kbps with double buffering."
                ::= { ifvceEntry 32 }

            -- **********  **********
            ifvceBroadcastDir OBJECT-TYPE 
                SYNTAX  INTEGER {  
                            tX(1),
                            rX(2),
                            not-applicable(254),
                            not-available(255)
                        }              
                ACCESS  read-write
                STATUS  mandatory
                DESCRIPTION
                        "When line activation is broadcast (Activation Type parameter set to BROADCAST), this
                         parameter is used to specify whether the voice port will transmit(TX) or receive (RX)
                         broadcast messages."
                ::= { ifvceEntry 36 }

            -- **********  **********
            ifvceBroadcastPvc OBJECT-TYPE
                SYNTAX  INTEGER (0..300)       
                ACCESS  read-write
                STATUS  mandatory
                DESCRIPTION
                        "This parameter specifies which PVC will be used for transmitting (on the root) or
                         receiving (on leaves) the broadcast frames."
                ::= { ifvceEntry 37 }

              -- **********  **********
              -- Only used by cleartrac versions older than 7.0.3.
              -- Later product will display UNK.
            ifvceAnalogLinkDwnBusy OBJECT-TYPE
                SYNTAX  INTEGER {
                        no(1),
                        yes(2),    
                        broadcast(3),
                        not-applicable(254),
                        not-available(255)
                    }                        
                ACCESS  read-write
                STATUS  mandatory
                DESCRIPTION
                        "Used by SDM-9400 and V410 VFC03 cards and by the SDM-9350
                         and V352 voice ports for versions 7.0.3 and lower.
                         See ifvceLinkDwnBusy for version 7.1.0 and higher and for
                         DVC cards."
                ::= { ifvceEntry 38 }

            -- ********** Speed Dial Number **********
            ifvceSpeedDialNum OBJECT-TYPE
                SYNTAX  DisplayString
                ACCESS  read-write
                STATUS  mandatory
                DESCRIPTION
                        "Specifies the Speed Dial Number to be dialed when a off-hook occurs
                        on a port configured with Autodial activation type."
                ::= { ifvceEntry 39 }

            -- ********** No longer supported by the NP Agent **********
            ifvceR2ExtendedDigitSrc OBJECT-TYPE
                SYNTAX  INTEGER {
                            map(1),
                            user(2),
                            not-applicable(254),
                            not-available(255)
                        }
                ACCESS  read-write
                STATUS  mandatory
                DESCRIPTION
                        "No longer supported by the NP Agent 7.1.0 and higher"
                ::= { ifvceEntry 40 }


            -- ********** R2 Group 2 digit **********
            ifvceR2Group2Digit OBJECT-TYPE              -- CFG-VPORT-R2-GROUP2
                SYNTAX  INTEGER (0..15)
                ACCESS  read-write
                STATUS  mandatory
                DESCRIPTION
                        "This parameter defines a Group 2 Digit that is output when dialing out."
                ::= { ifvceEntry 41 }

            -- ********** R2 Complete digit **********
            ifvceR2CompleteDigit OBJECT-TYPE            -- CFG-VPORT-R2-COMPLETE-DIG
                SYNTAX  INTEGER (1..15)
                ACCESS  read-write
                STATUS  mandatory
                DESCRIPTION
                        "This parameter defines the digit that is output when dialing is complete."
                ::= { ifvceEntry 42 }

            -- ********** R2 Busy digit **********
            ifvceR2BusyDigit OBJECT-TYPE                -- CFG-VPORT-R2-BUSY-DIG
                SYNTAX  INTEGER (1..15)
                ACCESS  read-write
                STATUS  mandatory
                DESCRIPTION
                        "This parameter defines the digit that is output to indicate that the destination is busy."
                ::= { ifvceEntry 43 }


            -- **********  **********
            ifvceRate8kx3 OBJECT-TYPE                                --  CFG-VPORT-DVC-RATE-8KX3  
                SYNTAX  INTEGER {  
                            no(1),
                            yes(2),
                            not-applicable(254),
                            not-available(255)
                        }              
                ACCESS  read-write
                STATUS  mandatory
                DESCRIPTION
                        "This parameter enables fallback to 8 Kbps with triple buffering."
                ::= { ifvceEntry 45 }
            
            -- **********  **********
            ifvceRate6kx1 OBJECT-TYPE                                --  CFG-VPORT-DVC-RATE-6KX1  
                SYNTAX  INTEGER {  
                            no(1),
                            yes(2),
                            not-applicable(254),
                            not-available(255)
                        }              
                ACCESS  read-write
                STATUS  mandatory
                DESCRIPTION
                        "This parameter enables fallback to 6 Kbps with single buffering."
                ::= { ifvceEntry 46 }
            
            -- **********  **********
            ifvceRate6kx2 OBJECT-TYPE                                --  CFG-VPORT-DVC-RATE-6KX2  
                SYNTAX  INTEGER {  
                            no(1),
                            yes(2),
                            not-applicable(254),
                            not-available(255)
                        }              
                ACCESS  read-write
                STATUS  mandatory
                DESCRIPTION
                        "This parameter enables fallback to 6 Kbps with double buffering."
                ::= { ifvceEntry 47 }
            
            -- **********  **********
            ifvceRate6kx3 OBJECT-TYPE                                --  CFG-VPORT-DVC-RATE-6KX3  
                SYNTAX  INTEGER {  
                            no(1),
                            yes(2),
                            not-applicable(254),
                            not-available(255)
                        }              
                ACCESS  read-write
                STATUS  mandatory
                DESCRIPTION
                        "This parameter enables fallback to 6 Kbps with triple buffering."
                ::= { ifvceEntry 48 }
            
            -- **********  **********
            ifvceRate4k8x1 OBJECT-TYPE                               --  CFG-VPORT-DVC-RATE-4K8X1  
                SYNTAX  INTEGER {  
                            no(1),
                            yes(2),
                            not-applicable(254),
                            not-available(255)
                        }              
                ACCESS  read-write
                STATUS  mandatory
                DESCRIPTION
                        "This parameter enables fallback to 4.8 Kbps with single buffering."
                ::= { ifvceEntry 49 }
            
            -- **********  **********
            ifvceRate4k8x2 OBJECT-TYPE                               --  CFG-VPORT-DVC-RATE-4K8X2
                SYNTAX  INTEGER {  
                            no(1),
                            yes(2),
                            not-applicable(254),
                            not-available(255)
                        }              
                ACCESS  read-write
                STATUS  mandatory
                DESCRIPTION
                        "This parameter enables fallback to 4.8 Kbps with double buffering."
                ::= { ifvceEntry 50 }


            -- ********** Double Talk Threshold for voice ports (db) **********
            ifvceDTalkThreshold OBJECT-TYPE                             --  CFG-VPORT-DOUBLE-TALK-THRESHOLD
                SYNTAX  INTEGER {
                        db-12(8),
                        db-11(9),
                        db-10(10),
                        db-9(11),
                        db-8(12),
                        db-7(13),
                        db-6(14),
                        db-5(15),
                        db-4(16),
                        db-3(17),
                        db-2(18),
                        db-1(19),
                        db0(20),
                        db1(21),
                        db2(22),
                        db3(23),
                        db4(24),
                        db5(25),
                        db6(1),
                        db7(2),
                        db8(3),
                        db9(4),
                        db10(5),
                        db11(6),
                        db12(7),
                        disabled(26),
                        not-applicable(254),
                        not-available(255)
                        }
                ACCESS  read-write
                STATUS  mandatory
                DESCRIPTION
                        "This parameter specifies the echo cancellation threshold,
                         measured in 1 db increments."
                ::= { ifvceEntry 51 }

            -- **********  **********
            ifvceToneEnergyDetec OBJECT-TYPE                               --  CFG-VPORT-DVC-RATE-4K8X2
                SYNTAX  INTEGER {  
                            yes(1),
                            no(2),
                            not-applicable(254),
                            not-available(255)
                        }              
                ACCESS  read-write
                STATUS  mandatory
                DESCRIPTION
                        "This parameter controls whether DTMF detection will include the detection of energy as well as tones.
                         In some cases, DTMF detection will work only if the energy is not detected."
                ::= { ifvceEntry 52 }

            ifvceExtendedDigitSrc OBJECT-TYPE
                SYNTAX  INTEGER {
                            map(1),
                            user(2),
                            not-applicable(254),
                            not-available(255)
                        }
                ACCESS  read-write
                STATUS  mandatory
                DESCRIPTION
                        "Specifies the origin of the extended digits that will be forwarded
                         to the remote unit.  Available on a port configured with Autodial
                         activation type."
                ::= { ifvceEntry 53 }

            -- ********** DtmfOnTime **********
            ifvceDtmfOnTime OBJECT-TYPE         -- CFG-VPORT-DTMF-ON-TIME
                SYNTAX  INTEGER (20..50)
                ACCESS  read-write
                STATUS  mandatory
                DESCRIPTION
                        "This parameter specifies the DTMF ON duration, in milliseconds,
                         for filtering unwanted DTMF tones during call progress."
                ::= { ifvceEntry 54 }


            -- ********** Enable Dtmf On Time **********
            ifvceEnableDtmfOnTime OBJECT-TYPE   -- CFG-VPORT-ENABLE-DTMF-CFG
                SYNTAX  INTEGER {
                            no(1),
                            yes(2),
                            not-applicable(254),
                            not-available(255)
                        }              
                ACCESS  read-write
                STATUS  mandatory
                DESCRIPTION
                        "This parameter specifies whether the duration of DTMF ON can be used
                         to filter unwanted DTMF tones during call progress. If DTMF ON-TIME
                         configuration is enabled, the next parameter is also listed."
                ::= { ifvceEntry 55 }

            IfvceDVCEntry ::=
                SEQUENCE {                      --  Correspond to the following profile parameters
                    ifvceIndex              INTEGER,
                    ifvceDesc               DisplayString,
                    ifvceProtocol           INTEGER,        --  CFG-VPORT-PROTOCOL
                    ifvceInterface          INTEGER,        --  CFG-VPORT-INTRF
                    ifvceRemotePort         INTEGER,        --  CFG-VPORT-DSTPORT
                    ifvceActivationType     INTEGER,        --  CFG-VPORT-ACTIVATION-TYPE
                    ifvceRemoteUnit         DisplayString,  --  CFG-VPORT-DSTUNIT
                    ifvceHuntGroup          INTEGER,        --  CFG-VPORT-HUNT-GROUP
                    ifvcePulseMakeBreak-ms  INTEGER,        --  CFG-VPORT-PULSE-MAKE-BREAK
                    ifvceToneDetectRegen-s  INTEGER,        --  CFG-VPORT-DTMF-DET-REGEN
                    ifvceToneOn-ms          INTEGER,        --  CFG-VPORT-DTMF-THRESHOLD-ON
                    ifvceToneOff-ms         INTEGER,        --  CFG-VPORT-DTMF-THRESHOLD-OFF
                    ifvceToneEnergyDetec    INTEGER,        --  CFG-VPORT-DTMF-ENERGY-DETEC
                    ifvceDVCSilenceSuppress INTEGER,        --  CFG-VPORT-SILENCE-SUP
                    ifvceSignaling          INTEGER,        --  CFG-VPORT-SIGNALING
                    ifvceDTalkThreshold     INTEGER,        --  CFG-VPORT-DOUBLE-TALK-THRESHOLD
                    ifvceDVCLocalInbound    INTEGER,        --  CFG-VPORT-INBOUND-LEVEL
                    ifvceDVCLocalOutbound   INTEGER,        --  CFG-VPORT-OUTBOUND-LEVEL
                    ifvceFaxModemRelay      INTEGER,        --  CFG-VPORT-FAX-MODEM-RELAY
                    ifvceMaxFaxModemRate    INTEGER,        --  CFG-VPORT-FAX-MODEM-MAX-RATE
                    ifvceFwdDigits          INTEGER,        --  CFG-VPORT-FWD-DIGITS
                    ifvceFwdType            INTEGER,        --  CFG-VPORT-FWD-TYPE
                    ifvceFwdDelay-ms        INTEGER,        --  CFG-VPORT-FWD-DELAY
                    ifvceDelDigits          INTEGER,        --  CFG-VPORT-DEL-DIGITS
                    ifvceExtNumber          DisplayString,  --  CFG-VPORT-EXTENSION-NUMBER
                    ifvceLinkDwnBusy        INTEGER,        --  CFG-VPORT-LINK-DOWN-BUSY
                    ifvceToneType           INTEGER,        --  CFG-VPORT-TONE-TYPE
                    ifvceRate8kx1           INTEGER,        --  CFG-VPORT-RATE-8KX1
                    ifvceRate8kx2           INTEGER,        --  CFG-VPORT-RATE-8KX2
                    ifvceRate8kx3           INTEGER,        --  CFG-VPORT-RATE-8KX3
                    ifvceRate6kx1           INTEGER,        --  CFG-VPORT-RATE-6KX1
                    ifvceRate6kx2           INTEGER,        --  CFG-VPORT-RATE-6KX2
                    ifvceRate6kx3           INTEGER,        --  CFG-VPORT-RATE-6KX3
                    ifvceRate5k8x1          INTEGER,        --  CFG-VPORT-RATE-5K8X1
                    ifvceRate5k8x2          INTEGER,        --  CFG-VPORT-RATE-5K8X2
                    ifvceRate4k8x1          INTEGER,        --  CFG-VPORT-RATE-4K8X1
                    ifvceRate4k8x2          INTEGER,        --  CFG-VPORT-RATE-4K8X2
                    ifvceSpeedDialNum       DisplayString,  --  CFG-VPORT-SPEED-DIAL
                    ifvceExtendedDigitSrc   INTEGER,        --  CFG-VPORT-EXTENDED-SRC
                    ifvceR2ExtendedDigitSrc INTEGER,        --  Left for compatibility
                    ifvceR2Group2Digit      INTEGER,        --  CFG-VPORT-R2-GROUP2
                    ifvceR2CompleteDigit    INTEGER,        --  CFG-VPORT-R2-COMPLETE-DIG
                    ifvceR2BusyDigit        INTEGER         --  CFG-VPORT-R2-BUSY-DIG
                }

            --  End of ifvce (voice) group
             
            -- The iflan group
            
            -- This group lets you configure the parameters for lan port
            -- such ethernet and token-ring.
             
            iflanNumber OBJECT-TYPE
                SYNTAX  INTEGER
                ACCESS  read-only
                STATUS  mandatory
                DESCRIPTION
                        "The number of network interfaces present on 
                        this system."
                ::= { iflan 1 }
                
            -- the iflan table    
            
            iflanTable OBJECT-TYPE
                SYNTAX  SEQUENCE OF IflanEntry
                ACCESS  not-accessible
                STATUS  mandatory
                DESCRIPTION
                        "A list of interface entries.  The number of
                        entries is given by the value of iflanNumber."
                ::= { iflan 2 }
            
            iflanEntry OBJECT-TYPE
                SYNTAX  IflanEntry
                ACCESS  not-accessible
                STATUS  mandatory
                DESCRIPTION
                        "This table contains the principal configurable
                        parameters which are used for a particular lan 
                        interface."
                INDEX   { iflanIndex }
                ::= { iflanTable 1 }
            
            IflanEntry ::=
                SEQUENCE {
                    iflanIndex              INTEGER,
                    iflanDesc               DisplayString,
                    iflanProtocol           INTEGER,
                    iflanSpeed              INTEGER,
                    iflanPriority           INTEGER,
                    iflanCost               INTEGER,
                    iflanPhysAddr           OCTET STRING (SIZE (6)),
                    iflanIpAddress          IpAddress,
                    iflanSubnetMask         IpAddress,
                    iflanMaxFrame           INTEGER,
                    iflanIpRip              INTEGER,
                    iflanIpRipTxRx          INTEGER,
                    iflanIpRipAuthType      INTEGER,
                    iflanIpRipPassword      DisplayString,
                    iflanOspfEnable         INTEGER,
                    iflanOspfAreaId         IpAddress,
                    iflanOspfPriority       INTEGER,
                    iflanOspfTransitDelay   INTEGER,
                    iflanOspfRetransmitInt  INTEGER,
                    iflanOspfHelloInt       INTEGER,
                    iflanOspfDeadInt        INTEGER,
                    iflanOspfPassword       DisplayString,
                    iflanOspfMetricCost     INTEGER,
                    iflanEth-LinkIntegrity  INTEGER,
                    iflanTr-Monitor         INTEGER,
                    iflanTr-Etr             INTEGER,
                    iflanTr-RingNumber      OCTET STRING (SIZE (2)),
                    iflanIpxRip             INTEGER,
                    iflanIpxSap             INTEGER,
                    iflanIpxNetNum          OCTET STRING (SIZE (4)),
                    iflanIpxLanType         INTEGER
                }
            
            iflanIndex OBJECT-TYPE
                SYNTAX  INTEGER
                ACCESS  read-only
                STATUS  mandatory
                DESCRIPTION
                        "A unique value for each interface."
                ::= { iflanEntry 1 }
            
            iflanDesc OBJECT-TYPE
                SYNTAX  DisplayString
                ACCESS  read-only
                STATUS  mandatory
                DESCRIPTION
                        "A textual string containing information about 
                        a specific interface."
                ::= { iflanEntry 2 }
            
            iflanProtocol OBJECT-TYPE
                SYNTAX  INTEGER {
                            off(1),
                            token-ring(13),
                            ethernet-auto(14),
                            ethernet-802p3(15),
                            ethernet-v2(16),
                            not-applicable(254),
                            not-available(255)
                        }
                ACCESS  read-write
                STATUS  mandatory
                DESCRIPTION
                        "Operating protocol for the LAN port."
                ::= { iflanEntry 3 }
            
            iflanSpeed OBJECT-TYPE
                SYNTAX  INTEGER {   
                            tr-4-Mbps(1),
                            tr-16-Mbps(2),
                            eth-10-Mbps(3),
                            not-applicable(254),
                            not-available(255)
                        }
                ACCESS  read-write
                STATUS  mandatory
                DESCRIPTION
                        "The port speed."
                ::= { iflanEntry 4 }
            
            iflanPriority OBJECT-TYPE
                SYNTAX  INTEGER (0..255)
                ACCESS  read-only
                STATUS  mandatory
                DESCRIPTION
                        "Priority assigned to the LAN port on the unit for the
                         Spanning Tree algorithm."
                ::= { iflanEntry 5 }
                
            iflanCost OBJECT-TYPE
                SYNTAX  INTEGER (0..255)
                ACCESS  read-only
                STATUS  mandatory
                DESCRIPTION
                        "The path cost assigned to the LAN port on the unit for the
                         Spanning Tree algorithm.  This indicates to the automatic
                         single-route bridge function the relative length of the path 
                         between the local unit port and the attached LAN.  The higher
                         the value, the less preferred the route."
                ::= { iflanEntry 6 }
                
            iflanPhysAddr OBJECT-TYPE
                SYNTAX  OCTET STRING (SIZE (6))
                ACCESS  read-write
                STATUS  mandatory
                DESCRIPTION
                        "Network (or MAC) address of the unit.  This address 
                        can be set to any value using 12 hexadecimal digits 
                        (6 bytes).  However, the unit automatically sets the 
                        first byte to 40 for a Token-Ring LAN, or 02 for an 
                        Ethernet LAN, which forces the use of a locally 
                        administered address. When this parameter is set to 
                        000000000000, the unit uses its burned-in address."
                ::= { iflanEntry 7 }
            
            iflanIpAddress OBJECT-TYPE
                SYNTAX  IpAddress
                ACCESS  read-write
                STATUS  mandatory
                DESCRIPTION
                        "IP address for the local port. This address is a 4-byte value
                         in dotted decimal representation, with a maximum value of 255
                         for each byte.  When set to 000.000.000.000, no IP address is
                         defined on the unit."
                ::= { iflanEntry 8 }
                
            iflanSubnetMask OBJECT-TYPE
                SYNTAX  IpAddress
                ACCESS  read-write
                STATUS  mandatory
                DESCRIPTION
                        "Subnet mask associated with the port's IP address. It is
                         configured like the IP address: a 4-byte value in dotted
                         decimal representation, with a maximum value of 255 for each
                         byte.  The subnet mask identifies which bits of the IP address
                         correspond to the physical network, and which  bits correspond
                         to host identifiers."
                ::= { iflanEntry 9 }
                
            iflanMaxFrame OBJECT-TYPE
                SYNTAX  INTEGER (128..8192)
                ACCESS  read-write
                STATUS  mandatory
                DESCRIPTION
                        "Maximum frame size, in octets.  This parameter determines the
                         largest datagram that can be sent or received on the interface
                         in one IP frame.  Datagrams larger than the maximum frame size
                         are divided into fragments before transmission, the reassembled
                         at the remote end."
                ::= { iflanEntry 10 }
                
            iflanEth-LinkIntegrity OBJECT-TYPE
                SYNTAX  INTEGER {   
                            no(1),
                            yes(2),
                            not-applicable(254),
                            not-available(255)
                        }
                ACCESS  read-write
                STATUS  mandatory
                DESCRIPTION
                        "Heartbeat feature enabled or disabled, which 
                        determines whether the unit supports Link Integrity.  
                        When heartbeat is enabled (YES), the unit supports 
                        the Link Integrity mode.  This is required when the 
                        Ethernet 10BASE-T port is connected to a hub.  When 
                        the HEARTBEAT parameter is set to NO, the unit does 
                        not support Link Integrity.  Valid only for Ethernet."
                ::= { iflanEntry 12 }
            
            iflanTr-Monitor OBJECT-TYPE
                SYNTAX  INTEGER {   
                            no(1),
                            yes(2),
                            not-applicable(254),
                            not-available(255)
                        }
                ACCESS  read-write
                STATUS  mandatory
                DESCRIPTION
                        "Contender or non-contender as an active monitor.  
                        When this parameter is set to YES, the unit is a 
                        contender as the ring monitor.  That is, if no ring 
                        monitors are active, the unit will automatically 
                        negotiate with other devices in the network to 
                        select a new monitor, and may become the new ring 
                        monitor.
                        
                        When this parameter is set to NO, the unit is a 
                        non-contender.  That is, it will not negotiate with 
                        other devices and cannot become an active monitor.
                        Valid only for Token-Ring."
                ::= { iflanEntry 13 }
            
            iflanTr-Etr OBJECT-TYPE
                SYNTAX  INTEGER {   
                            no(1),
                            yes(2),
                            not-applicable(254),
                            not-available(255)
                        }
                ACCESS  read-write
                STATUS  mandatory
                DESCRIPTION
                        "Early Token Release feature enabled or disabled.  
                        When this feature is enabled and the TR port speed 
                        is set to 16 Mbps, the unit will send an 'early token'
                        as soon as the transmission of a frame is completed 
                        on the ring.  When ETR is disabled, the unit waits 
                        until the reception of a frame is completed on the 
                        ring before sending a token.  Valid only for 
                        Token-Ring."
                ::= { iflanEntry 14 }
            
            iflanTr-RingNumber OBJECT-TYPE
                SYNTAX  OCTET STRING (SIZE (2)) -- 0x0001 to 0x0FFF
                ACCESS  read-write
                STATUS  mandatory
                DESCRIPTION
                        "The local LAN number, used for a source routing 
                        bridge.  Valid only for Token-Ring."
                ::= { iflanEntry 15 }
            
            iflanIpRip OBJECT-TYPE
                SYNTAX  INTEGER {   
                            disable(1),
                            v1(2),
                            v2-broadcast(3),
                            v2-multicast(4),
                            not-applicable(254),
                            not-available(255)
                        }
                ACCESS  read-write
                STATUS  mandatory
                DESCRIPTION
                        "When this parameter is set to V1, the RIP routing
                         is done according to the RIP V1 standard.  With
                         RIP V2, broadcast or multicast can be used.  With
                         RIP V2 MULTICAST, only RIP V2 compliant devices
                         will receive RIP frames."
                ::= { iflanEntry 16 }
            
            iflanIpxRip OBJECT-TYPE
                SYNTAX  INTEGER {   
                            disable(1),
                            enable(2),
                            not-applicable(254),
                            not-available(255)
                        }
                ACCESS  read-write
                STATUS  mandatory
                DESCRIPTION
                        "if this parameter is enable, the unit will generate 
                        IPX RIP frame on that interface every minute, otherwise 
                        the unit will discard all IPX RIP frame received and no 
                        one will be generated on that port."
                ::= { iflanEntry 17 }
            
            iflanIpxSap OBJECT-TYPE
                SYNTAX  INTEGER {   
                            disable(1),
                            enable(2),
                            not-applicable(254),
                            not-available(255)
                        }
                ACCESS  read-write
                STATUS  mandatory
                DESCRIPTION
                        "if this parameter is enable, the unit will generate
                         IPX SAP frame on that interface every minute, otherwise 
                         the unit will discard all IPX SAP frame received and no 
                         one will be generated on that port."
                ::= { iflanEntry 18 }

            iflanIpxNetNum OBJECT-TYPE
                SYNTAX  OCTET STRING (SIZE (4))
                ACCESS  read-write
                STATUS  mandatory
                DESCRIPTION
                        "This value identify the IPX network number which 
                         the lan port of the unit is connected to"
                ::= { iflanEntry 19 }

            iflanIpxLanType OBJECT-TYPE
                SYNTAX  INTEGER {   
                            ethernet-802p2(1),
                            ethernet-snap(2),
                            ethernet-802p3(3),
                            ethernet-ii(4),
                            not-applicable(254),  
                            not-available(255)
                        }
                ACCESS  read-write
                STATUS  mandatory
                DESCRIPTION
                        " This parameter define the IPX frame type that   
                          the unit will recognize, Other frame type will 
                          be discarded"
                ::= { iflanEntry 20 }
            
            iflanOspfEnable OBJECT-TYPE
                SYNTAX  INTEGER {   
                            disable(1),
                            enable(2),
                            not-applicable(254),
                            not-available(255)
                        }
                ACCESS  read-write
                STATUS  mandatory
                DESCRIPTION
                        "Indicates whether or not OSPF is enabled on this 
                         interface."
                ::= { iflanEntry 21 }

            iflanOspfAreaId OBJECT-TYPE
                SYNTAX  IpAddress
                ACCESS  read-write  
                STATUS  mandatory
                DESCRIPTION
                        "Identifies the area to which this interface 
                         belongs."
                ::= { iflanEntry 22 }

            iflanOspfPriority OBJECT-TYPE
                SYNTAX  INTEGER (0..255)
                ACCESS  read-write
                STATUS  mandatory
                DESCRIPTION
                        "When two routers attached to a network both attempt 
                         to become Designated Router, the one with the 
                         highest Router Priority takes precedence.  A router 
                         whose Router Priority is set to 0 is ineligible to 
                         become Designated Router on the attached network.  
                         Router Priority is only configured for interfaces 
                         to multi-access networks."
                ::= { iflanEntry 23 }

            iflanOspfTransitDelay OBJECT-TYPE
                SYNTAX  INTEGER (1..360)
                ACCESS  read-write
                STATUS  mandatory
                DESCRIPTION
                        "The estimated number of seconds it takes to 
                         transmit a Link State Update Packet over this 
                         interface."
                ::= { iflanEntry 24 }

            iflanOspfRetransmitInt OBJECT-TYPE
                SYNTAX  INTEGER (1..360)
                ACCESS  read-write
                STATUS  mandatory
                DESCRIPTION
                        "The number of seconds between like state advertisement
                         retransmissions for adjacencies belonging to this
                         interface.  Also used when retransmitting Database
                         Description and Link State Request Packets."
                ::= { iflanEntry 25 }

            iflanOspfHelloInt OBJECT-TYPE
                SYNTAX  INTEGER (1..360)
                ACCESS  read-write
                STATUS  mandatory
                DESCRIPTION
                        "The length of time, in seconds, between the Hello
                         Packets that the router sends on the interface.
                         This value is advertised in the router's Hello
                         Packets.  It must be the same for all routers 
                         attached to a common network.  The smaller the 
                         HelloInterval, the faster topological changes will 
                         be detected, but more OSPF routing protocol traffic
                         will ensue."
                ::= { iflanEntry 26 }

            iflanOspfDeadInt OBJECT-TYPE
                SYNTAX  INTEGER (1..2000)
                ACCESS  read-write
                STATUS  mandatory
                DESCRIPTION
                        "After ceasing to hear a router's Hello Packets, the 
                         number of seconds before its neighbors declare the 
                         router down.  This is also advertised in the router's 
                         Hello Packets in their RouterDeadInterval field.  
                         This value again bust be the same for all routers 
                         attached to a common network."
                ::= { iflanEntry 27 }

            iflanOspfPassword OBJECT-TYPE
                SYNTAX  DisplayString
                ACCESS  read-write
                STATUS  mandatory
                DESCRIPTION
                        "This configured data allows the authentication 
                         procedure to generate and/or verify the 
                         authentication field in the OSPF header.  This 
                         value again must be the same for all routers 
                         attached to a common network."
                ::= { iflanEntry 28 }

            iflanOspfMetricCost OBJECT-TYPE
                SYNTAX  INTEGER (1..65534)
                ACCESS  read-write
                STATUS  mandatory
                DESCRIPTION
                        "The cost of sending a packet on the interface, 
                         expressed in the link state metric.  This is 
                         advertised as the link cost for this interface 
                         in the router's router links advertisement."
                ::= { iflanEntry 29 }

            iflanIpRipTxRx OBJECT-TYPE
                SYNTAX  INTEGER {
                            duplex(1),
                            tx-only(2),
                            rx-only(3),
                            not-applicable(254),
                            not-available(255)
                        }
                ACCESS  read-write
                STATUS  mandatory
                DESCRIPTION
                        "This parameter allows RIP frames transmission only,
                        RIP frames reception only or both transmission and
                        reception of RIP frames."
                ::= { iflanEntry 30 }

            iflanIpRipAuthType OBJECT-TYPE
                SYNTAX  INTEGER {
                            none(1),
                            simple(2),
                            not-applicable(254),
                            not-available(255)
                        }
                ACCESS  read-write
                STATUS  mandatory
                DESCRIPTION
                        "Enable or disable password authentication for
                        the interface. If you select Simple Password, the
                        password will be included in the sent RIP frames.
                        The received frames containing authentication will be
                        accepted only if the password is valid."
                ::= { iflanEntry 31 }

            iflanIpRipPassword OBJECT-TYPE
                SYNTAX  DisplayString
                ACCESS  read-write
                STATUS  mandatory
                DESCRIPTION
                        "This configured data allows the authentication
                        procedure to generate and/or verify the
                        authentication field in the RIP header. This
                        value again must be the same for each
                        interface on each side of the link."
                ::= { iflanEntry 32 }

            IflanEthEntry ::=
                SEQUENCE {
                    iflanIndex              INTEGER,
                    iflanDesc               DisplayString,
                    iflanProtocol           INTEGER,
                    iflanSpeed              INTEGER,
                    iflanPriority           INTEGER,
                    iflanCost               INTEGER,
                    iflanPhysAddr           OCTET STRING (SIZE (6)),
                    iflanIpAddress          IpAddress,
                    iflanSubnetMask         IpAddress,
                    iflanMaxFrame           INTEGER,
                    iflanIpRip              INTEGER,
                    iflanIpRipTxRx          INTEGER,
                    iflanIpRipAuthType      INTEGER,
                    iflanIpRipPassword      DisplayString,
                    iflanOspfEnable         INTEGER,
                    iflanOspfAreaId         IpAddress,
                    iflanOspfPriority       INTEGER,
                    iflanOspfTransitDelay   INTEGER,
                    iflanOspfRetransmitInt  INTEGER,
                    iflanOspfHelloInt       INTEGER,
                    iflanOspfDeadInt        INTEGER,
                    iflanOspfPassword       DisplayString,
                    iflanOspfMetricCost     INTEGER,
                    iflanEth-LinkIntegrity  INTEGER,
                    iflanIpxRip             INTEGER,
                    iflanIpxSap             INTEGER,
                    iflanIpxNetNum          OCTET STRING (SIZE (4)),
                    iflanIpxLanType         INTEGER
                }
            
            IflanTrEntry ::=
                SEQUENCE {
                    iflanIndex              INTEGER,
                    iflanDesc               DisplayString,
                    iflanProtocol           INTEGER,
                    iflanSpeed              INTEGER,
                    iflanPriority           INTEGER,
                    iflanCost               INTEGER,
                    iflanPhysAddr           OCTET STRING (SIZE (6)),
                    iflanIpAddress          IpAddress,
                    iflanSubnetMask         IpAddress,
                    iflanMaxFrame           INTEGER,
                    iflanIpRip              INTEGER,
                    iflanIpRipTxRx          INTEGER,
                    iflanIpRipAuthType      INTEGER,
                    iflanIpRipPassword      DisplayString,
                    iflanOspfEnable         INTEGER,
                    iflanOspfAreaId         IpAddress,
                    iflanOspfPriority       INTEGER,
                    iflanOspfTransitDelay   INTEGER,
                    iflanOspfRetransmitInt  INTEGER,
                    iflanOspfHelloInt       INTEGER,
                    iflanOspfDeadInt        INTEGER,
                    iflanOspfPassword       DisplayString,
                    iflanOspfMetricCost     INTEGER,
                    iflanTr-Monitor         INTEGER,
                    iflanTr-Etr             INTEGER,
                    iflanTr-RingNumber      OCTET STRING (SIZE (2)),
                    iflanIpxRip             INTEGER,
                    iflanIpxSap             INTEGER,
                    iflanIpxNetNum          OCTET STRING (SIZE (4)),
                    iflanIpxLanType         INTEGER
                }
            
            
            -- The pu group
            
            -- This group lets you configure the parameters for pu.
             
            puNumber OBJECT-TYPE
                SYNTAX  INTEGER
                ACCESS  read-only
                STATUS  mandatory
                DESCRIPTION
                        "The number of controller present on this 
                        system."
                ::= { pu 1 }
                
            -- the Pu table    
            
            puTable OBJECT-TYPE
                SYNTAX  SEQUENCE OF PuEntry
                ACCESS  not-accessible
                STATUS  mandatory
                DESCRIPTION
                        "A list of controller entries.  The number of
                        entries is given by the value of puNumber."
                ::= { pu 2 }
            
            puEntry OBJECT-TYPE
                SYNTAX  PuEntry
                ACCESS  not-accessible
                STATUS  mandatory
                DESCRIPTION
                        "This table contains the principal configurable
                        parameters who are used for a particular PU."
                INDEX   { puIndex }
                ::= { puTable 1 }
            
            PuEntry ::=
                SEQUENCE {
                    puIndex                 INTEGER,
                    puMode                  INTEGER,
                    puActive                INTEGER,
                    puDelayBeforeConn-s     INTEGER,
                    puRole                  INTEGER,
                    puSdlcPort              INTEGER,
                    puSdlcAddress           OCTET STRING (SIZE (1)),
                    puSdlcPort2             INTEGER,
                    puSdlcAddress2          OCTET STRING (SIZE (1)),
                    puSdlcTimeout-ms        INTEGER,
                    puSdlcRetry             INTEGER,
                    puSdlcWindow            INTEGER,
                    puSdlcMaxFrame          INTEGER,
                    puLlcDa                 OCTET STRING (SIZE (6)),
                    puLlcTr-Routing         INTEGER,
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puLinkRemoteUnit        DisplayString,
                    puLinkClassNumber       INTEGER,
                    puLinkRemPu             INTEGER,
                    puBnnPvc                INTEGER,
                    puBnnFid                INTEGER,
                    puBanDa                 OCTET STRING (SIZE (6)),
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puBanRouting         INTEGER,
                    puXid                   INTEGER,
                    puXidId                 OCTET STRING (SIZE (4)),
                    puXidFormat             INTEGER,
                    puXidPuType             INTEGER
                }
                
            puIndex OBJECT-TYPE
                SYNTAX  INTEGER
                ACCESS  read-only
                STATUS  mandatory
                DESCRIPTION
                        "A unique value for each PU.  Its value ranges 
                        between 1 and the value of puNumber."
                ::= { puEntry 1 }
            
            puMode OBJECT-TYPE
                SYNTAX  INTEGER {
                            off(1),
                            sdlc-llc(2),
                            sdlc-sdlc(3),
                            sdlc-dlsw(4),
                            sdlc-links(5),
                            llc-dlsw(6),
                            llc-links(7),
                            dlsw-links(8),
                            sdlc-ban(9),
                            sdlc-bnn(10),
                            llc-ban(11),
                            llc-bnn(12),
                            dlsw-ban(13),
                            dlsw-bnn(14),
                            ban-link(15),
                            bnn-link(16),
                            not-applicable(254),
                            not-available(255)
                        }
                ACCESS  read-write
                STATUS  mandatory
                DESCRIPTION
                        "The PU operating mode."
                ::= { puEntry 2 }
            
            puActive OBJECT-TYPE
                SYNTAX  INTEGER {   
                            no(1),
                            yes(2),
                            not-applicable(254),
                            not-available(255)
                        }
                ACCESS  read-write
                STATUS  mandatory
                DESCRIPTION
                        "Sets the activation status of the PU."
                ::= { puEntry 3 }
            
            puDelayBeforeConn-s OBJECT-TYPE
                SYNTAX  INTEGER (1..1000)
                ACCESS  read-write
                STATUS  mandatory
                DESCRIPTION
                        "Delay before connection.  Maximum length of time, in 
                        seconds, allowed to establish the PU connection 
                        or change from one connection status to another."
                ::= { puEntry 4 }
            
            puRole OBJECT-TYPE
                SYNTAX  INTEGER {   
                            secondary(1),
                            primary(2),
                            not-applicable(254),
                            not-available(255)
                        }
                ACCESS  read-write
                STATUS  mandatory
                DESCRIPTION
                        "For LLC-DLSW, LLC-LINKS and DLSW-LINKS modes only.
                        
                        For LLC-DLSW and LLC-LINKS, this variable indicates 
                        whether the LLC side acts as a primary (facing the 
                        controller) or secondary (facing the host) unit.  
                        The unit automatically defines the other side with 
                        the opposite value.
                        
                        For DLSW-LINKS, this variable indicates whether the 
                        DLSw side acts as a primary or secondary unit.  The 
                        unit automatically defines the LINKS side with the 
                        opposite value."
                ::= { puEntry 5 }
            
            puSdlcPort OBJECT-TYPE
                SYNTAX  INTEGER
                ACCESS  read-write
                STATUS  mandatory
                DESCRIPTION
                        "For all PU modes with an SDLC connection.  Primary 
                        SNA/SDLC port (configured with the P-SDLC protocol) 
                        to which the PU is attached."
                ::= { puEntry 6 }
            
            puSdlcAddress OBJECT-TYPE
                SYNTAX  OCTET STRING (SIZE (1))
                ACCESS  read-write
                STATUS  mandatory
                DESCRIPTION
                        "For all PU modes with an SDLC connection.  SDLC 
                        address for the PU on the primary side of the 
                        connection.  Two hexadecimal digits must be selected."
                ::= { puEntry 7 }
            
            puSdlcPort2 OBJECT-TYPE
                SYNTAX  INTEGER
                ACCESS  read-write
                STATUS  mandatory
                DESCRIPTION
                        "For SDLC-SDLC mode only.  Secondary port 
                        (configured with the S-SDLC protocol) to which 
                        the PU is attached."
                ::= { puEntry 8 }
            
            puSdlcAddress2 OBJECT-TYPE
                SYNTAX  OCTET STRING (SIZE (1))
                ACCESS  read-write
                STATUS  mandatory
                DESCRIPTION
                        "For SDLC-SDLC mode only.  SDLC address for the PU 
                        on the secondary side of the connection.  Two 
                        hexadecimal digits must be selected."
                ::= { puEntry 9 }
            
            puSdlcTimeout-ms OBJECT-TYPE
                SYNTAX  INTEGER (100..30000)
                ACCESS  read-write
                STATUS  mandatory
                DESCRIPTION
                        "For all PU modes with an SDLC connection.  Wait for 
                        reply timeout before retransmitting a frame.  This 
                        timeout is defined in milliseconds."
                ::= { puEntry 10 }
            
            puSdlcRetry OBJECT-TYPE
                SYNTAX  INTEGER (1..1000)
                ACCESS  read-write
                STATUS  mandatory
                DESCRIPTION
                        "For all PU modes with an SDLC connection.  Maximum 
                        number of successive retries on the SDLC side of the 
                        connection before the PU is declared inoperative."
                ::= { puEntry 11 }
            
            puSdlcWindow OBJECT-TYPE
                SYNTAX  INTEGER (1..7)
                ACCESS  read-write
                STATUS  mandatory
                DESCRIPTION
                        "For all PU modes with an SDLC connection.  
                        Transmitter window size."
                ::= { puEntry 12 }
            
            puSdlcMaxFrame OBJECT-TYPE
                SYNTAX  INTEGER -- 128, 256, 512, 1024, 2048, 4096, 8192
                ACCESS  read-write
                STATUS  mandatory
                DESCRIPTION
                        "For SDLC-LINKS, SDLC-LLC and SDLC-DLSW modes only.
                        Maximum frame size on the SDLC side of the 
                        connection, excluding SNA headers.  For an SDLC-LLC 
                        connection, if the value of this parameter is equal 
                        to that of the puLlcMaxFrame parameter, then no frame 
                        splitting will occur.  On the other hand, if the 
                        value of this parameter is different from that of 
                        the puLlcMaxFrame parameter, the unit will split the 
                        frames according to the smaller max frame value.  
                        The same is true of an SDLC-DLSW connection, where 
                        the value of puSdlcMaxFrame is compared to that of 
                        puDlsMaxFrame."
                ::= { puEntry 13 }
            
            puLlcDa OBJECT-TYPE
                SYNTAX  OCTET STRING (SIZE (6))
                ACCESS  read-write
                STATUS  mandatory
                DESCRIPTION
                        "For all PU modes with an LLC connection.  
                        Destination address of the device to be reached on 
                        the LAN.  This address is defined using 12 
                        hexadecimal digits (6 bytes)."
                ::= { puEntry 14 }
            
            puLlcTr-Routing OBJECT-TYPE
                SYNTAX  INTEGER {   
                            trsp(1),
                            src(2),
                            not-applicable(254),
                            not-available(255)
                        }
                ACCESS  read-write
                STATUS  mandatory
                DESCRIPTION
                        "For all PU modes with an LLC connection, Token-Ring 
                        only.  Type of routing used in the Token-Ring LAN.  
                        This parameter defines the type of routing required 
                        to access the remote station.  Select SRC for source 
                        routing through the LAN.  Select TRSP for transparent 
                        routing."
                ::= { puEntry 15 }
            
            puLlcSsap OBJECT-TYPE
                SYNTAX  OCTET STRING (SIZE (1))
                ACCESS  read-write
                STATUS  mandatory
                DESCRIPTION
                        "For all PU modes with an LLC connection.  Source 
                        SAP (Service Access Point) used by the unit for this 
                        PU.  For an LLC-HOST application (LLC side acts as 
                        primary unit), the unit can handle multiple PUs over 
                        the same pair of network addresses:  the host LAN 
                        destination address (DA) and the network address 
                        of the unit (NA).  To distinguish the PUs attached 
                        to the same host, you must set the Source SAP 
                        parameter to a different value for each PU.  Valid 
                        values are multiples of 4, from 04 to E8.  This 
                        parameter must also be set in the host configuration.
                        For an LLC-CONTROLLER application (LLC side acts as 
                        secondary unit), this parameter should be set to the 
                        default SNA SAP, that is, 04."
                ::= { puEntry 16 }
            
            puLlcDsap OBJECT-TYPE
                SYNTAX  OCTET STRING (SIZE (1))
                ACCESS  read-write
                STATUS  mandatory
                DESCRIPTION
                        "For all PU modes with an LLC connection.  Destination 
                        SAP that will be used by the remote LAN device for 
                        this PU.  Valid values are multiples of 4, from 04 to 
                        E8.  Usually, the SNA destination SAP is 04."
                ::= { puEntry 17 }
            
            puLlcTimeout-ms OBJECT-TYPE
                SYNTAX  INTEGER (100..30000)
                ACCESS  read-write
                STATUS  mandatory
                DESCRIPTION
                        "For all PU modes with an LLC connection.  Wait for 
                        reply timeout before retransmitting a frame.  This 
                        timeout is defined in milliseconds."
                ::= { puEntry 18 }
            
            puLlcRetry OBJECT-TYPE
                SYNTAX  INTEGER (1..1000)
                ACCESS  read-write
                STATUS  mandatory
                DESCRIPTION
                        "For all PU modes with an LLC connection.  Maximum 
                        number of successive retries on the LLC side of the 
                        connection before the PU is declared inoperative."
                ::= { puEntry 19 }
            
            puLlcWindow OBJECT-TYPE
                SYNTAX  INTEGER (1..31)
                ACCESS  read-write
                STATUS  mandatory
                DESCRIPTION
                        "For all PU modes with an LLC connection.  Maximum 
                        transmitter window size on the LAN.  The dynamic 
                        window algorithm increases the window size by one 
                        each time the number of frames defined by the LLC-NW 
                        parameter (see below) has been acknowledged without 
                        a retransmission, until the maximum value defined by 
                        the LLC-WINDOW parameter has been reached.  The 
                        window size is reset to 1 when a retransmission 
                        occurs."
                ::= { puEntry 20 }
            
            puLlcDynamicWindow OBJECT-TYPE
                SYNTAX  INTEGER (1..1000)
                ACCESS  read-write
                STATUS  mandatory
                DESCRIPTION
                        "For all PU modes with an LLC connection.  Number 
                        of information frames that are consecutively 
                        acknowledged without a retransmission before the 
                        window size will be incremented by one.  This 
                        parameter is used for the dynamic window algorithm, 
                        in conjunction with the puLlcWindow parameter."
                ::= { puEntry 21 }
            
            puLlcMaxFrame OBJECT-TYPE
                SYNTAX  INTEGER -- 128, 256, 512, 1024, 2048, 4096, 8192
                ACCESS  read-write
                STATUS  mandatory
                DESCRIPTION
                        "For all PU modes with an LLC connection.  Maximum 
                        frame size on the LLC side of the connection, 
                        excluding LLC and SNA headers.
                        
                        For an SDLC-LLC connection, if the value of this 
                        parameter is equal to that of the puSdlcMaxFrame 
                        parameter, then no frame splitting will occur.  On 
                        the other hand, if the value of this parameter is 
                        different from that of the puSdlcMaxFrame parameter, 
                        the unit will split the frames according to the 
                        smaller max frame value.  The same is true of an 
                        LLC-DLSW connection, where the value of puLlcMaxFrame
                        is compared to that of DLS-MAXFRM."
                ::= { puEntry 23 }
            
            puDlsDa OBJECT-TYPE
                SYNTAX  OCTET STRING (SIZE (6))
                ACCESS  read-write
                STATUS  mandatory
                DESCRIPTION
                        "For all PU modes with a DLSW connection.  
                        Destination address of the device to be reached 
                        via a DLSw connection.  This address is defined 
                        using 12 hexadecimal digits (6 bytes)."
                ::= { puEntry 24 }
            
            puDlsSsap OBJECT-TYPE
                SYNTAX  OCTET STRING (SIZE (1))
                ACCESS  read-write
                STATUS  mandatory
                DESCRIPTION
                        "For all PU modes with a DLSW connection.  Source 
                        SAP (Service Access Point) used by the unit for this 
                        PU.  For a DLSw-HOST application (DLSw side acts as 
                        primary unit), the unit can handle multiple PUs over 
                        the same pair of network addresses:  the host DLSw 
                        destination address (DA) and the network address of 
                        the unit (NA).  To distinguish the PUs attached to 
                        the same host, you must set the DLSw SSAP to a 
                        different value for each PU.  Valid values are 
                        multiples of 4, from 04 to E8.  This parameter must 
                        also be set in the host configuration.  For a 
                        DLSw-CONTROLLER application (DLSw side acts as 
                        secondary unit), this parameter should be set to the 
                        default SNA SAP, that is, 04."
                ::= { puEntry 25 }
            
            puDlsDsap OBJECT-TYPE
                SYNTAX  OCTET STRING (SIZE (1))
                ACCESS  read-write
                STATUS  mandatory
                DESCRIPTION
                        "For all PU modes with a DLSW connection.  
                        Destination SAP that will be used by the remote 
                        DLSw device for this PU.  Valid values are multiples 
                        of 4, from 04 to E8.  Usually, the SNA destination 
                        SAP is 04."
                ::= { puEntry 26 }
            
            puDlsIpSrc OBJECT-TYPE
                SYNTAX  IpAddress
                ACCESS  read-write
                STATUS  mandatory
                DESCRIPTION
                        "For all PU modes with a DLSW connection.  The IP 
                        source address, which identifies the port to reach
                        the remote DLS.  The port may be the LAN port or one
                        of the serial WAN ports.  This address is a 4-byte 
                        value in dotted decimal representation, with a 
                        maximum value of 255 for each byte.  When this 
                        parameter is set to 000.000.000.000, no IP address 
                        is defined."
                ::= { puEntry 27 }
            
            puDlsIpDst OBJECT-TYPE
                SYNTAX  IpAddress
                ACCESS  read-write
                STATUS  mandatory
                DESCRIPTION
                        "For all PU modes with a DLSW connection.  The IP 
                        address of the remote PU.  This address is a 4-byte 
                        value in dotted decimal representation, with a 
                        maximum value of 255 for each byte.  When this 
                        parameter is set to 000.000.000.000, no IP address 
                        is defined."
                ::= { puEntry 28 }
            
            puDlsMaxFrame OBJECT-TYPE
                SYNTAX  INTEGER -- 128, 256, 512, 1024, 2048, 4096, 8192
                ACCESS  read-write
                STATUS  mandatory
                DESCRIPTION
                        "For all PU modes with a DLSW connection.  Maximum 
                        frame size on the DLSw side of the connection, 
                        excluding SNA headers.
                        
                        For an SDLC-DLSW connection, if the value of this 
                        parameter is equal to that of the puSdlcMaxFrame 
                        parameter, then no frame splitting will occur.  On 
                        the other hand, if the value of this parameter is 
                        different from that of the puSdlcMaxFrame parameter, 
                        the unit will split the frames according to the 
                        smaller max frame value.  The same is true of an 
                        LLC-DLSW connection, where the value of puDlsMaxFrame
                        is compared to that of puLlcMaxFrame."
                ::= { puEntry 29 }
            
            puLinkRemoteUnit OBJECT-TYPE
                SYNTAX  DisplayString
                ACCESS  read-write
                STATUS  mandatory
                DESCRIPTION
                        "Remote unit to which data from this pu should
                         be directed"
                ::= { puEntry 30 }
                
            puLinkClassNumber OBJECT-TYPE
                SYNTAX  INTEGER (1..8)
                ACCESS  read-write
                STATUS  mandatory
                DESCRIPTION
                        "The priority class for data from this pu.  Classes are
                         defined according to bandwidth weight."
                ::= { puEntry 31 }
                
            puLinkRemPu OBJECT-TYPE
                SYNTAX  INTEGER (1..64)
                ACCESS  read-write
                STATUS  mandatory
                DESCRIPTION
                        "For all PU modes with a LINKS connection.  The PU 
                        number on the remote unit."
                ::= { puEntry 32 }
            
            puXid OBJECT-TYPE
                SYNTAX  INTEGER {   
                            no(1),
                            yes(2),
                            manual(3),
                            auto(4),
                            not-applicable(254),
                            not-available(255)
                        }
                ACCESS  read-write
                STATUS  mandatory
                DESCRIPTION
                        "For SDLC-SDLC and SDLC-LINKS modes only.  PU 
                        exchanges identification.  This parameter determines 
                        whether the PU expects to exchange PU identification 
                        with the device it is connected to, and ensures the 
                        identity of the remote PU in SNA applications.  Set 
                        to NO if the PU does not support XID."
                ::= { puEntry 33 }
            
            puXidId OBJECT-TYPE
                SYNTAX  OCTET STRING (SIZE (4))
                ACCESS  read-write
                STATUS  mandatory
                DESCRIPTION
                        "For all PU modes with an LLC or DLSW connection.  
                        This parameter contains the ID block (IDBLK) and 
                        ID number (IDNUM) of the PU. The first 3 digits 
                        comprise the IDBLK, and the last 5 digits comprise 
                        the IDNUM."
                ::= { puEntry 34 }
            
            puXidFormat OBJECT-TYPE
                SYNTAX  INTEGER  -- 0 or 1
                ACCESS  read-write
                STATUS  mandatory
                DESCRIPTION
                        "For all PU modes with an LLC or DLSW connection.
                        XID format type.  Only types 0 and 1 are supported 
                        at this time.  Type 0 is used by older IBM 
                        controllers:  the IBM 3274 and some of the old 3174, 
                        5294 and 5394 models.  Type 1 is used by the newer 
                        models."
                ::= { puEntry 35 }
            
            puXidPuType OBJECT-TYPE
                SYNTAX  INTEGER  -- 1 or 2
                ACCESS  read-write
                STATUS  mandatory
                DESCRIPTION
                        "For all PU modes with an LLC or DLSW connection.  
                        The PU type that is possible in the XID.  Only PU 
                        types 1 and 2 are supported at this time."
                ::= { puEntry 36 }
            
            puBnnPvc OBJECT-TYPE
                SYNTAX  INTEGER -- 1 to 300
                ACCESS  read-write
                STATUS  mandatory
                DESCRIPTION
                        "For all PU modes with a BNN connection.
                        The number of the remote PVC to which data from this
                        PU will be sent."
                ::= { puEntry 37 }
            
            puBnnFid OBJECT-TYPE
                SYNTAX  INTEGER {   
                            fID2(1),
                            fID4(2),
                            aPPN(3),
                            not-applicable(254),
                            not-available(255)
                        }
                ACCESS  read-write
                STATUS  mandatory
                DESCRIPTION
                        "For all PU modes with a BNN connection.
                        The type of format Identification Field (FID) for
                        this PU."
                ::= { puEntry 38 }

            puBanDa OBJECT-TYPE
                SYNTAX  OCTET STRING (SIZE (6))
                ACCESS  read-write
                STATUS  mandatory
                DESCRIPTION
                        "For all PU modes with a BAN or BNN connection.  
                        Destination address of the device to be reached on 
                        the BAN/BNN connection.  This address is defined using 12 
                        hexadecimal digits (6 bytes)."
                ::= { puEntry 39 }
            
            puBanBnnSsap OBJECT-TYPE
                SYNTAX  OCTET STRING (SIZE (1))
                ACCESS  read-write
                STATUS  mandatory
                DESCRIPTION
                        "For all PU modes with a BAN or BNN connection.
                        Source SAP (Service Access Point) used by the BayFRAD for
                        this PU.  For an BAN-HOST application (BAN side acts as 
                        primary unit), the BayFRAD can handle multiple PUs attached 
                        to the same host.  For this application you must set the
                        BAN/BNN Source SAP parameter to a different value for each PU.
                        Valid values are multiples of 4, from 04 to DC.
                        For an BAN-CONTROLLER application (BAN side acts as 
                        secondary unit), this parameter should be set to the 
                        default SNA SAP, that is, 04."
                ::= { puEntry 40 }
            
            puBanBnnDsap OBJECT-TYPE
                SYNTAX  OCTET STRING (SIZE (1))
                ACCESS  read-write
                STATUS  mandatory
                DESCRIPTION
                        "For all PU modes with a BAN or BNN connection.
                        Destination SAP that will be used by the remote BAN
                        device for this PU.  Valid values are multiples of 4,
                        from 04 to DC.  Usually, the SNA destination SAP is 04."
                ::= { puEntry 41 }
            
            puBanBnnTimeout-ms OBJECT-TYPE
                SYNTAX  INTEGER (100..30000)
                ACCESS  read-write
                STATUS  mandatory
                DESCRIPTION
                        "For all PU modes with a BAN or BNN connection.
                        Wait for reply timeout before retransmitting a frame.
                        This timeout is defined in milliseconds."
                ::= { puEntry 42 }
            
            puBanBnnRetry OBJECT-TYPE
                SYNTAX  INTEGER (1..1000)
                ACCESS  read-write
                STATUS  mandatory
                DESCRIPTION
                        "For all PU modes with a BAN or BNN connection.
                        Maximum number of successive retries on the BAN/BNN side
                        of the connection before the PU is declared inoperative."
                ::= { puEntry 43 }
            
            puBanBnnWindow OBJECT-TYPE
                SYNTAX  INTEGER (1..31)
                ACCESS  read-write
                STATUS  mandatory
                DESCRIPTION
                        "For all PU modes with a BAN or BNN connection.
                        Maximum transmission window size on the BAN.  The
                        dynamic window algorithm increases the window size by one 
                        each time the number of frames defined by the puBanBnnNw 
                        parameter has been acknowledged without a retransmission,
                        until the maximum value defined by the puBanBnnWindow
                        parameter has been reached.  The window size is reset to 1
                        when a retransmission occurs."
                ::= { puEntry 44 }
            
            puBanBnnNw OBJECT-TYPE
                SYNTAX  INTEGER (1..1000)
                ACCESS  read-write
                STATUS  mandatory
                DESCRIPTION
                        "For all PU modes with a BAN or BNN connection.
                        Number of information frames that are consecutively 
                        acknowledged without a retransmission before the 
                        window size will be incremented by one.  This 
                        parameter is used for the dynamic window algorithm, 
                        in conjunction with the puBanBnnWindow parameter."
                ::= { puEntry 45 }
            
            puBanBnnMaxFrame OBJECT-TYPE
                SYNTAX  INTEGER -- 128, 256, 512, 1024, 2048, 4096, 8192
                ACCESS  read-write
                STATUS  mandatory
                DESCRIPTION
                        "For all PU modes with a BAN or BNN connection.
                        Maximum frame size on the BAN/BNN side of the
                        connection, excluding BAN/BNN and SNA headers.
                        
                        For an SDLC-BAN connection, if the value of this 
                        parameter is equal to that of the puSdlcMaxFrame 
                        parameter, then no frame splitting will occur.  On 
                        the other hand, if the value of this parameter is 
                        different from that of the puSdlcMaxFrame parameter, 
                        the FRAD will split the frames according to the 
                        smaller max frame value.  The same is true of a
                        SDLC-BNN, LLC-BAN and LLC-BNN connection."
                ::= { puEntry 46 }
            
            puBanRouting OBJECT-TYPE
                SYNTAX  INTEGER {
                            transparent(1),
                            source(2),
                            source-a(3),
                            not-applicable(254),
                            not-available(255)
                        }
                ACCESS  read-write
                STATUS  mandatory
                DESCRIPTION
                        "For all PU modes with a BAN or BNN connection.  
                        This parameter defines the type of routing required 
                        to access the remote station.  Select SOURCE for source 
                        routing, or TRANSPARENT for transparent routing or 
                        SOURCE-A for source routing with an all route
                        broadcast response to a single route broadcast request."
                ::= { puEntry 47 }
            
            PuSdlcLlcEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcTimeout-ms        INTEGER,
                    puSdlcRetry             INTEGER,
                    puSdlcWindow            INTEGER,
                    puSdlcMaxFrame          INTEGER,
                    puLlcDa                 OCTET STRING (SIZE (6)),
                    puLlcTr-Routing         INTEGER,
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puXid                   INTEGER,
                    puXidId                 OCTET STRING (SIZE (4)),
                    puXidFormat             INTEGER,
                    puXidPuType             INTEGER
                }
                
            PuSdlcSdlcEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcPort2             INTEGER,
                    puSdlcAddress2          OCTET STRING (SIZE (1)),
                    puSdlcTimeout-ms        INTEGER,
                    puSdlcRetry             INTEGER,
                    puSdlcWindow            INTEGER,
                    puXid                   INTEGER
                }
                
            PuSdlcDlswEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcTimeout-ms        INTEGER,
                    puSdlcRetry             INTEGER,
                    puSdlcWindow            INTEGER,
                    puSdlcMaxFrame          INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puXid                   INTEGER,
                    puXidId                 OCTET STRING (SIZE (4)),
                    puXidFormat             INTEGER,
                    puXidPuType             INTEGER
                }
                
            PuSdlcLinksEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcTimeout-ms        INTEGER,
                    puSdlcRetry             INTEGER,
                    puSdlcWindow            INTEGER,
                    puSdlcMaxFrame          INTEGER,
                    puLinkRemoteUnit        DisplayString,
                    puLinkClassNumber       INTEGER,
                    puLinkRemPu             INTEGER,
                    puXid                   INTEGER
                }
                
            PuLlcDlswEntry ::=
                SEQUENCE {
                    puIndex                 INTEGER,
                    puMode                  INTEGER,
                    puActive                INTEGER,
                    puDelayBeforeConn-s     INTEGER,
                    puRole                  INTEGER,
                    puLlcDa                 OCTET STRING (SIZE (6)),
                    puLlcTr-Routing         INTEGER,
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puXid                   INTEGER,
                    puXidId                 OCTET STRING (SIZE (4)),
                    puXidFormat             INTEGER,
                    puXidPuType             INTEGER
                }
                
            PuLlcLinksEntry ::=
                SEQUENCE {
                    puIndex                 INTEGER,
                    puMode                  INTEGER,
                    puActive                INTEGER,
                    puDelayBeforeConn-s     INTEGER,
                    puRole                  INTEGER,
                    puLlcDa                 OCTET STRING (SIZE (6)),
                    puLlcTr-Routing         INTEGER,
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puLinkRemoteUnit        DisplayString,
                    puLinkClassNumber       INTEGER,
                    puLinkRemPu             INTEGER,
                    puXid                   INTEGER,
                    puXidId                 OCTET STRING (SIZE (4)),
                    puXidFormat             INTEGER,
                    puXidPuType             INTEGER
                }
                
            PuDlswLinksEntry ::=
                SEQUENCE {
                    puIndex                 INTEGER,
                    puMode                  INTEGER,
                    puActive                INTEGER,
                    puDelayBeforeConn-s     INTEGER,
                    puRole                  INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puLinkRemoteUnit        DisplayString,
                    puLinkClassNumber       INTEGER,
                    puLinkRemPu             INTEGER,
                    puXid                   INTEGER,
                    puXidId                 OCTET STRING (SIZE (4)),
                    puXidFormat             INTEGER,
                    puXidPuType             INTEGER
                }
                
            PuSdlcBanEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcTimeout-ms        INTEGER,
                    puSdlcRetry             INTEGER,
                    puSdlcWindow            INTEGER,
                    puSdlcMaxFrame          INTEGER,
                    puBanDa                 OCTET STRING (SIZE (6)),
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puBanRouting            INTEGER,
                    puXid                   INTEGER,
                    puXidId                 OCTET STRING (SIZE (4)),
                    puXidFormat             INTEGER,
                    puXidPuType             INTEGER
                }
                
            PuSdlcBnnEntry ::=
                SEQUENCE {
                    puIndex                 INTEGER,
                    puMode                  INTEGER,
                    puActive                INTEGER,
                    puDelayBeforeConn-s     INTEGER,
                    puSdlcPort              INTEGER,
                    puSdlcAddress           OCTET STRING (SIZE (1)),
                    puSdlcTimeout-ms        INTEGER,
                    puSdlcRetry             INTEGER,
                    puSdlcWindow            INTEGER,
                    puSdlcMaxFrame          INTEGER,
                    puBnnPvc                INTEGER,
                    puBnnFid                INTEGER,
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puXid                   INTEGER,
                    puXidId                 OCTET STRING (SIZE (4)),
                    puXidFormat             INTEGER,
                    puXidPuType             INTEGER
                }
                
            PuLlcBanEntry ::=
                SEQUENCE {
                    puIndex                 INTEGER,
                    puMode                  INTEGER,
                    puActive                INTEGER,
                    puDelayBeforeConn-s     INTEGER,
                    puRole                  INTEGER,
                    puLlcDa                 OCTET STRING (SIZE (6)),
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puBanDa                 OCTET STRING (SIZE (6)),
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puBanRouting            INTEGER,
                    puXid                   INTEGER,
                    puXidId                 OCTET STRING (SIZE (4)),
                    puXidFormat             INTEGER,
                    puXidPuType             INTEGER
                }
                
            PuLlcBnnEntry ::=
                SEQUENCE {
                    puIndex                 INTEGER,
                    puMode                  INTEGER,
                    puActive                INTEGER,
                    puDelayBeforeConn-s     INTEGER,
                    puRole                  INTEGER,
                    puLlcDa                 OCTET STRING (SIZE (6)),
                    puLlcSsap               OCTET STRING (SIZE (1)),
                    puLlcDsap               OCTET STRING (SIZE (1)),
                    puLlcTimeout-ms         INTEGER,
                    puLlcRetry              INTEGER,
                    puLlcWindow             INTEGER,
                    puLlcDynamicWindow      INTEGER,
                    puLlcMaxFrame           INTEGER,
                    puBnnPvc                INTEGER,
                    puBnnFid                INTEGER,
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puXid                   INTEGER,
                    puXidId                 OCTET STRING (SIZE (4)),
                    puXidFormat             INTEGER,
                    puXidPuType             INTEGER
                }

            PuDlsBanEntry ::=
                SEQUENCE {
                    puIndex                 INTEGER,
                    puMode                  INTEGER,
                    puActive                INTEGER,
                    puDelayBeforeConn-s     INTEGER,
                    puRole                  INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puBanDa                 OCTET STRING (SIZE (6)),
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puBanRouting            INTEGER,
                    puXid                   INTEGER,
                    puXidId                 OCTET STRING (SIZE (4)),
                    puXidFormat             INTEGER,
                    puXidPuType             INTEGER
                }
                
            PuDlsBnnEntry ::=
                SEQUENCE {
                    puIndex                 INTEGER,
                    puMode                  INTEGER,
                    puActive                INTEGER,
                    puDelayBeforeConn-s     INTEGER,
                    puRole                  INTEGER,
                    puDlsDa                 OCTET STRING (SIZE (6)),  
                    puDlsSsap               OCTET STRING (SIZE (1)), 
                    puDlsDsap               OCTET STRING (SIZE (1)), 
                    puDlsIpSrc              IpAddress,
                    puDlsIpDst              IpAddress,
                    puDlsMaxFrame           INTEGER,
                    puBnnPvc                INTEGER,
                    puBnnFid                INTEGER,
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puXid                   INTEGER,
                    puXidId                 OCTET STRING (SIZE (4)),
                    puXidFormat             INTEGER,
                    puXidPuType             INTEGER
                }

            PuBanLinkEntry ::=
                SEQUENCE {
                    puIndex                 INTEGER,
                    puMode                  INTEGER,
                    puActive                INTEGER,
                    puDelayBeforeConn-s     INTEGER,
                    puRole                  INTEGER,
                    puBanDa                 OCTET STRING (SIZE (6)),
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puBanRouting            INTEGER,
                    puLinkRemoteUnit        DisplayString,
                    puLinkClassNumber       INTEGER,
                    puLinkRemPu             INTEGER,
                    puXid                   INTEGER,
                    puXidId                 OCTET STRING (SIZE (4)),
                    puXidFormat             INTEGER,
                    puXidPuType             INTEGER
                }
                
            PuBnnLinkEntry ::=
                SEQUENCE {
                    puIndex                 INTEGER,
                    puMode                  INTEGER,
                    puActive                INTEGER,
                    puDelayBeforeConn-s     INTEGER,
                    puRole                  INTEGER,
                    puBnnPvc                INTEGER,
                    puBnnFid                INTEGER,
                    puBanBnnSsap            OCTET STRING (SIZE (1)),
                    puBanBnnDsap            OCTET STRING (SIZE (1)),
                    puBanBnnTimeout-ms      INTEGER,
                    puBanBnnRetry           INTEGER,
                    puBanBnnWindow          INTEGER,
                    puBanBnnNw              INTEGER,
                    puBanBnnMaxFrame        INTEGER,
                    puLinkRemoteUnit        DisplayString,
                    puLinkClassNumber       INTEGER,
                    puLinkRemPu             INTEGER,
                    puXid                   INTEGER,
                    puXidId                 OCTET STRING (SIZE (4)),
                    puXidFormat             INTEGER,
                    puXidPuType             INTEGER
                }

            -- The schedule group
            
            -- This group lets you configure the parameters for periods.
             
            scheduleNumber OBJECT-TYPE
                SYNTAX  INTEGER
                ACCESS  read-only
                STATUS  mandatory
                DESCRIPTION
                        "The number of period present on this system."
                ::= { schedule 1 }
                
            -- The schedule table    
            
            scheduleTable OBJECT-TYPE
                SYNTAX  SEQUENCE OF ScheduleEntry
                ACCESS  not-accessible
                STATUS  mandatory
                DESCRIPTION
                        "A list of period entries.  The number of entries 
                        is given by the value of scheduleNumber."
                ::= { schedule 2 }
            
            scheduleEntry OBJECT-TYPE
                SYNTAX  ScheduleEntry
                ACCESS  not-accessible
                STATUS  mandatory
                DESCRIPTION
                        "This table contains the principal configurable
                        parameters who are used for a particular period."
                INDEX   { schedulePeriod }
                ::= { scheduleTable 1 }
            
            ScheduleEntry ::=
                SEQUENCE {
                    schedulePeriod       INTEGER,
                    scheduleEnable       INTEGER,
                    scheduleDay          INTEGER,
                    scheduleBeginTime    DisplayString,
                    scheduleEndTime      DisplayString,
                    schedulePort1        INTEGER,
                    schedulePort2        INTEGER,
                    schedulePort3        INTEGER,
                    schedulePort4        INTEGER,
                    schedulePort5        INTEGER,
                    schedulePort6        INTEGER,
                    schedulePort7        INTEGER,
                    schedulePort8        INTEGER
                }
                
            schedulePeriod OBJECT-TYPE
                SYNTAX  INTEGER
                ACCESS  read-only
                STATUS  mandatory
                DESCRIPTION
                        "A unique value for each period.  Its value ranges 
                        between 1 and the value of scheduleNumber."
                ::= { scheduleEntry 1 }
                
            scheduleEnable OBJECT-TYPE
                SYNTAX  INTEGER {   
                            no(1),
                            yes(2),
                            not-applicable(254),
                            not-available(255)
                        }
                ACCESS  read-write
                STATUS  mandatory
                DESCRIPTION
                        "Enable period.  This parameter defines whether 
                        the period will be used during the time period it 
                        covers.  When no periods are enabled, or no enabled 
                        period covers the current time, the unit uses the 
                        default operating mode configured with the WAN link 
                        parameters."
                ::= { scheduleEntry 2 }
                
            scheduleDay OBJECT-TYPE
                SYNTAX  INTEGER {   
                            all(1),
                            sunday(2),
                            monday(3),
                            tuesday(4),
                            wednesday(5),
                            thursday(6),
                            friday(7),
                            saturday(8),
                            workday(9),
                            weekend(10),
                            not-applicable(254),
                            not-available(255)
                            }
                ACCESS  read-write
                STATUS  mandatory
                DESCRIPTION
                        "Day(s) of the week during which the period is 
                        effective.  Select ALL to configure the period 
                        for all days of the week.  Use weekend for Saturday
                        and Sunday only.  Use workday for Monday to Friday."
                ::= { scheduleEntry 3 }
                
            scheduleBeginTime OBJECT-TYPE
                SYNTAX  DisplayString
                ACCESS  read-write
                STATUS  mandatory
                DESCRIPTION
                        "Time of day at which the period begins on a 24-hour 
                        clock.  When the period is enabled, the WAN link 
                        operating mode defined for the period will commence 
                        at this time on the configured day(s)."
                ::= { scheduleEntry 4 }
                
            scheduleEndTime OBJECT-TYPE
                SYNTAX  DisplayString
                ACCESS  read-write
                STATUS  mandatory
                DESCRIPTION
                        "Time of day at which the period ends on a 24-hour 
                        clock.  When the period is enabled, the WAN link 
                        operating mode defined for the period will be 
                        disabled at this time on the configured day(s).
                        If no other period is configured and enabled to 
                        commence at this time, the unit will activate the 
                        default operating mode configured with the WAN link 
                        parameters."
                ::= { scheduleEntry 5 }
                
            schedulePort1 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
                DESCRIPTION
                        "Operating mode for the WAN link (port configured 
                        in PVCR protocol) when this period is activated.  
                        The possible settings for this parameter are the 
                        following:
                        
                        DEDICATED:  Communication is carried out over 
                                    a dedicated line.
                        ANSWER:     The port can receive calls only.
                        CALL-BKUP:  Call mode using a backup recovery 
                                    mechanism.  The port is activated in 
                                    case of line failure on the dedicated 
                                    WAN links.
                        CALL-BOD:   Call mode using Bandwidth On Demand(BOND)
                                    processing, which automatically controls 
                                    both dialing over and hanging up the link.
                        INACTIVE:   Deactivation of the link."
                ::= { scheduleEntry 6 }
                
            schedulePort2 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 7 }
                
            schedulePort3 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 8 }
                
            schedulePort4 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 9 }
                
            schedulePort5 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 10 }
                
            schedulePort6 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 11 }
                
            schedulePort7 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 12 }
                
            schedulePort8 OBJECT-TYPE
                SYNTAX  INTEGER {   
                            inactive(1),
                            dedicated(2),
                            answer(3),
                            call-backup(4),
                            call-bod(5),
                            wait-user(6),
                            not-applicable(254),
                            not-available(255)
                        }
                ACCESS  read-write
                STATUS  mandatory
	  		 DESCRIPTION ""
                ::= { scheduleEntry 13 }
                
            -- The bridge group
            
            -- This group lets you configure the parameters for bridge.
             
            bridgeEnable OBJECT-TYPE
                SYNTAX  INTEGER {   
                            no(1),
                            yes(2),
                            not-applicable(254),
                            not-available(255)
                        }
                ACCESS  read-write
                STATUS  mandatory
                DESCRIPTION
                        "This variable defines Bridge enable(yes) or 
                        disable(no).  If you enable the bridge, the unit transfers
                        information between two LAN segments."
                ::= { bridge 1 }
                
            bridgeStpEnable OBJECT-TYPE
                SYNTAX  INTEGER {   
                            no(1),
                            yes(2),
                            not-applicable(254),
                            not-available(255)
                        }
                ACCESS  read-write
                STATUS  mandatory
                DESCRIPTION
                        "This parameter defines whether the Spanning Tree 
                        protocol will be enabled.  The unit uses the spanning 
                        tree algorithm to decide how to forward frames and 
                        how to propagate broadcast packets so that only one 
                        copy of a broadcast frame is delivered to each LAN.
                        For transparent bridging, STP ensures that only one 
                        active route is used at one time during transparent 
                        bridging.  For source route bridging, it is used to 
                        initialize a single-route broadcast route."
                ::= { bridge 2 }
                
            bridgeLanType OBJECT-TYPE
                SYNTAX  INTEGER {   
                            ethernet-auto(1),
                            ethernet-802p3(2),
                            ethernet-v2(3),
                            token-ring(4),
                            not-applicable(254),
                            not-available(255)
                        }
                ACCESS  read-write
                STATUS  mandatory
                DESCRIPTION
                        "The type of LAN data that must be bridged via the unit"
                ::= { bridge 3 }
                
            bridgeAgingTime-s OBJECT-TYPE
                SYNTAX  INTEGER (10..1000000)
                ACCESS  read-write
                STATUS  mandatory
                DESCRIPTION
                        "Aging time, in seconds, for deleting addresses 
                        from the routing table.  In transparent bridging, 
                        the routing table contains a combination of fixed 
                        and learned addresses.  For the learned addresses, 
                        if a station has not been heard from for the AGING 
                        TIME period, its entry can be deleted.  This process 
                        keeps the size of the routing table to a manageable 
                        level, and minimizes the amount of memory and 
                        processing required to search it."
                ::= { bridge 4 }
                
            bridgeHelloTime-s OBJECT-TYPE
                SYNTAX  INTEGER (1..10)
                ACCESS  read-write
                STATUS  mandatory
                DESCRIPTION
                        "The interval, in seconds, between HELLO messages 
                        that the unit transmits to all LAN segments to which 
                        it is connected.  HELLO messages carry timestamp 
                        information as well as information concerning the 
                        current root bridge.  From this information the unit 
                        is able to determine the current network topology 
                        and compute the shortest delay paths to destination 
                        devices.  Automatic single-route broadcast uses the 
                        HELLO message to detect when bridges enter and leave 
                        the network."
                ::= { bridge 5 }
                
            bridgeMaxAge-s OBJECT-TYPE
                SYNTAX  INTEGER (6..40)
                ACCESS  read-write
                STATUS  mandatory
                DESCRIPTION
                        "The maximum time that the bridge can wait for 
                        reception of a HELLO frame.  If this bridge is the 
                        network root bridge, the MAX AGE value will be coded 
                        in all HELLO messages that the unit transmits."
                ::= { bridge 6 }
                
            bridgeForwardDelay-s OBJECT-TYPE
                SYNTAX  INTEGER (4..30)
                ACCESS  read-write
                STATUS  mandatory
                DESCRIPTION
                        "The wait time, in seconds, that the unit spends in 
                        the Learning state before moving to the Forwarding 
                        state.  In the Learning state, the unit is building 
                        address tables and participating in the spanning 
                        tree algorithm, but is not forwarding frames.  In 
                        the Forwarding state, the unit forwards frames in 
                        addition to its other bridge activities."
                ::= { bridge 7 }
                
            bridgePriority OBJECT-TYPE
                SYNTAX  INTEGER (0..65535)
                ACCESS  read-write
                STATUS  mandatory
                DESCRIPTION
                        "Priority assigned to this bridge for the Spanning 
                        Tree algorithm.  The unit uses this parameter to 
                        determine the network topology."
                ::= { bridge 8 }
                
            bridgeTr-Number OBJECT-TYPE
                SYNTAX  OCTET STRING (SIZE (1)) -- 0x00 to 0x0F
                ACCESS  read-write
                STATUS  mandatory
                DESCRIPTION
                        "The bridge number, required for source routing of Tocken-Ring
                         data via the unit.  This number represents the bridge between
                         two links on a Token-Ring network.  You must set the bridge
                         number if the unit acts as an intermediary bridge to reach a
                         remote unit that support a Token-Ring LAN."
                ::= { bridge 9 }
                
            bridgeTr-SteSpan OBJECT-TYPE
                SYNTAX  INTEGER {   
                            auto(1),
                            disable(2),
                            forced(3),
                            not-applicable(254),
                            not-available(255)
                        }
                ACCESS  read-write
                STATUS  mandatory
                DESCRIPTION
                        "Span mode for STE (Spanning Tree Explorer) frames, required when
                         Token-Ring data is bridged via the unit.  This parameter determines
                         how the port will behave when presented with an STE frame (Single
                         Route Broadcast only).  You must set the bridge number if the unit
                         acts as an intermediary bridge to reach a remote unit that
                         support a Token-Ring LAN."
                ::= { bridge 10 }
                
            bridgeTr-MaxHop OBJECT-TYPE
                SYNTAX  INTEGER (0..7)
                ACCESS  read-write
                STATUS  mandatory
                DESCRIPTION
                        "The maximum nember of bridges that a broadcast frame can
                         cross on the way to its destination.  The unit discard any
                         frame with a routing information field that exceeds this
                         limits. This parameter is required for source routing of
                         Tocken-Ring data via the unit.  You must specify the MAX
                         HOP if the unit acts as an intermediary bridge to reach a
                         remote unit that support a Token-Ring LAN."
                ::= { bridge 11 }

            -- The phone group
            
            -- This group lets you configure the parameters for phone.
             
            phoneNumber OBJECT-TYPE
                SYNTAX  INTEGER
                ACCESS  read-only
                STATUS  mandatory
                DESCRIPTION
                        "The number of phone present on this system."
                ::= { phone 1 }
                
            -- The phone table    
            
            phoneTable OBJECT-TYPE
                SYNTAX  SEQUENCE OF PhoneEntry
                ACCESS  not-accessible
                STATUS  mandatory
                DESCRIPTION
                        "A list of phone entries.  The number of entries 
                        is given by the value of phoneNumber."
                ::= { phone 2 }
            
            phoneEntry OBJECT-TYPE
                SYNTAX  PhoneEntry
                ACCESS  not-accessible
                STATUS  mandatory
                DESCRIPTION
                        "This table contains the principal configurable
                        parameters who are used for a particular phone."
                INDEX   { phoneIndex }
                ::= { phoneTable 1 }
            
            PhoneEntry ::=
                SEQUENCE {
                    phoneIndex          INTEGER,
                    phoneRemoteUnit     DisplayString,
                    phonePhoneNumber    DisplayString,
                    phoneNextHop        DisplayString,
                    phoneCost           INTEGER
                }
                
            phoneIndex OBJECT-TYPE
                SYNTAX  INTEGER
                ACCESS  read-only
                STATUS  mandatory
                DESCRIPTION
                        "A unique value for each phone.  Its value ranges 
                        between 1 and the value of phoneNumber."
                ::= { phoneEntry 1 }
                
            phoneRemoteUnit OBJECT-TYPE
                SYNTAX  DisplayString
                ACCESS  read-write
                STATUS  mandatory
                DESCRIPTION
                        "Name of the unit that has to be backup."
                ::= { phoneEntry 2 }
                
            phonePhoneNumber OBJECT-TYPE
                SYNTAX  DisplayString
                ACCESS  read-write
                STATUS  mandatory
                DESCRIPTION
                        "Phone number to dial to backup the Remote unit."
                ::= { phoneEntry 3 }
                
            phoneNextHop OBJECT-TYPE
                SYNTAX  DisplayString
                ACCESS  read-write
                STATUS  mandatory
                DESCRIPTION
                        "Name of the Next hop by which the Remote unit should normally be seen."
                ::= { phoneEntry 4 }

            phoneCost  OBJECT-TYPE
                SYNTAX  INTEGER (0..65534)
                ACCESS  read-write
                STATUS  mandatory
                DESCRIPTION
                        "Normal cost to reach the remote unit."
                ::= { phoneEntry 5 }


            -- The filter group
            
            -- This group lets you configure the parameters for filter.
             
            filterNumber OBJECT-TYPE
                SYNTAX  INTEGER
                ACCESS  read-only
                STATUS  mandatory
                DESCRIPTION
                        "The number of filter present on this system."
                ::= { filter 1 }
                
            -- The filter table    
            
            filterTable OBJECT-TYPE
                SYNTAX  SEQUENCE OF FilterEntry
                ACCESS  not-accessible
                STATUS  mandatory
                DESCRIPTION
                        "A list of filter entries.  The number of entries 
                        is given by the value of filterNumber."
                ::= { filter 2 }
            
            filterEntry OBJECT-TYPE
                SYNTAX  FilterEntry
                ACCESS  not-accessible
                STATUS  mandatory
                DESCRIPTION
                        "This table contains the principal configurable
                        parameters who are used for a particular filter."
                INDEX   { filterIndex }
                ::= { filterTable 1 }
            
            FilterEntry ::=
                SEQUENCE {
                    filterIndex          INTEGER,
                    filterActive         INTEGER,
                    filterDefinition     DisplayString
                }
                
            filterIndex OBJECT-TYPE
                SYNTAX  INTEGER
                ACCESS  read-only
                STATUS  mandatory
                DESCRIPTION
                        "A unique value for each filter.  Its value ranges 
                        between 1 and the value of filterNumber."
                ::= { filterEntry 1 }
                
            filterActive OBJECT-TYPE
                SYNTAX  INTEGER {   
                            no(1),
                            yes(2),
                            not-applicable(254),
                            not-available(255)
                        }
                ACCESS  read-write
                STATUS  mandatory
                DESCRIPTION
                        "Sets the activation status of the filter."
                ::= { filterEntry 2 }
                
            filterDefinition OBJECT-TYPE
                SYNTAX  DisplayString
                ACCESS  read-write
                STATUS  mandatory
                DESCRIPTION
                        "The definition of the filter.  Each filter definition 
                        contains a set of criteria that prevent extraneous 
                        frames from being forwarded, or send specific frames 
                        over the high or low-priority bridge channel of the 
                        composite link.  The latter application allows you 
                        to prioritize a particular traffic type over the 
                        Bridge 1 channel."
                ::= { filterEntry 3 }
                
            -- The class group
            
            -- This group lets you configure the parameters for class.
             
            classNumber OBJECT-TYPE
                SYNTAX  INTEGER
                ACCESS  read-only
                STATUS  mandatory
                DESCRIPTION
                        "The number of class present on this system."
                ::= { class 1 }
                
            classDefaultClass OBJECT-TYPE
                SYNTAX  INTEGER (1..8)
                ACCESS  read-write
                STATUS  mandatory
                DESCRIPTION
                        "The default class to be used when no class is defined
                         for a port, PU or PVC."
                ::= { class 2 }
                
            -- The class table    
            
            classTable OBJECT-TYPE
                SYNTAX  SEQUENCE OF ClassEntry
                ACCESS  not-accessible
                STATUS  mandatory
                DESCRIPTION
                        "A list of class entries.  The number of entries 
                        is given by the value of classNumber."
                ::= { class 3 }
            
            classEntry OBJECT-TYPE
                SYNTAX  ClassEntry
                ACCESS  not-accessible
                STATUS  mandatory
                DESCRIPTION
                        "This table contains the principal configurable
                        parameters who are used for a particular class."
                INDEX   { classIndex }
                ::= { classTable 1 }
            
            ClassEntry ::=
                SEQUENCE {
                    classIndex           INTEGER,
                    classWeight          INTEGER,
                    classPrefRoute       DisplayString
                }
                
            classIndex OBJECT-TYPE
                SYNTAX  INTEGER
                ACCESS  read-only
                STATUS  mandatory
                DESCRIPTION
                        "A unique value for each class.  Its value ranges 
                        between 1 and the value of classNumber."
                ::= { classEntry 1 }
                
            classWeight OBJECT-TYPE
                SYNTAX  INTEGER (1..16)
                ACCESS  read-write
                STATUS  mandatory
                DESCRIPTION
                        "The relative bandwidth weight used by this class on
                         the composite link.  The higher the weight, the
                         greater the amount of bandwidth allocated to traffic
                         in this class.  Thus the class with the highest relative
                         weight will have the highest priority, which can be used
                         to guarantee the response time for mission-critical data."
                ::= { classEntry 2 }
                
            classPrefRoute OBJECT-TYPE
                SYNTAX  DisplayString
                ACCESS  read-write
                STATUS  mandatory
                DESCRIPTION
                        "Identifies the name of the cleartrac unit to be 
                         used as the next hop for sending transparent or PVC 
                         multiplex data over multiple direct links (point-to-point 
                         or rack backbone connections), where more than one route 
                         is available and all available routes are equal in cost. 
                         Assigning a different preferred route to different 
                         classes ensures static load balancing of transparent 
                         traffic over all routes."
                ::= { classEntry 3 }
                
            -- The pvc group
            
            -- This group lets you configure the parameters for PVCs.
             
            pvcNumber OBJECT-TYPE
                SYNTAX  INTEGER
                ACCESS  read-only
                STATUS  mandatory
                DESCRIPTION
                        "The number of pvc present on this system."
                ::= { pvc 1 }
                
            -- The pvc table    
            
            pvcTable OBJECT-TYPE
                SYNTAX  SEQUENCE OF PvcEntry
                ACCESS  not-accessible
                STATUS  mandatory
                DESCRIPTION
                        "A list of pvc entries.  The number of entries 
                        is given by the value of pvcNumber."
                ::= { pvc 2 }
            
            pvcEntry OBJECT-TYPE
                SYNTAX  PvcEntry
                ACCESS  not-accessible
                STATUS  mandatory
                DESCRIPTION
                        "This table contains the principal configurable
                        parameters who are used for a particular pvc."
                INDEX   { pvcIndex }
                ::= { pvcTable 1 }
            
            PvcEntry ::=
                SEQUENCE {
                    pvcIndex                INTEGER,
                    pvcMode                 INTEGER,
                    pvcDlciAddress          INTEGER,
                    pvcPort                 INTEGER,
                    pvcUserPort             INTEGER,
                    pvcInfoRate             INTEGER,
                    pvcBurstInfoRate        INTEGER,
                    pvcType                 INTEGER,
                    pvcBackupCall-s         INTEGER,
                    pvcBackupHang-s         INTEGER,
                    pvcDialTimeout          INTEGER,          
                    pvcBackup               INTEGER,
                    pvcPriority             INTEGER,
                    pvcCost                 INTEGER,
                    pvcRemoteUnit           DisplayString,
                    pvcTimeout-ms           INTEGER,
                    pvcRetry                INTEGER,
                    pvcCompression          INTEGER,
                    pvcIpAddress            IpAddress,
                    pvcSubnetMask           IpAddress,
                    pvcMaxFrame             INTEGER,
                    pvcBroadcastGroup       INTEGER,
                    pvcIpRip                INTEGER,
                    pvcIpRipTxRx            INTEGER,
                    pvcIpRipAuthType        INTEGER,
                    pvcIpRipPassword        DisplayString,
                    pvcOspfEnable           INTEGER,
                    pvcOspfAreaId           IpAddress,
                    pvcOspfTransitDelay     INTEGER,
                    pvcOspfRetransmitInt    INTEGER,
                    pvcOspfHelloInt         INTEGER,
                    pvcOspfDeadInt          INTEGER,
                    pvcOspfPassword         DisplayString,
                    pvcOspfMetricCost       INTEGER,
                    pvcBrgConnection        INTEGER,
                    pvcIpConnection         INTEGER,
                    pvcIpxConnection        INTEGER,
                    pvcLlcConnection        INTEGER,
                    pvcRemotePvc            INTEGER,
                    pvcPvcClass             INTEGER,
                    pvcUserDlci             INTEGER,
                    pvcNetworkDlci          INTEGER,
                    pvcNetworkPort          INTEGER,
                    pvcRingNumber           OCTET STRING (SIZE (2)),
                    pvcIpxRip               INTEGER,
                    pvcIpxSap               INTEGER,
                    pvcIpxNetNum            OCTET STRING (SIZE (4)),
                    pvcProxyAddr            INTEGER (1..8),
                    pvcMaxChannels          INTEGER,
                    pvcHuntForwardingAUnit  DisplayString,
                    pvcHuntForwardingBUnit  DisplayString,
                    pvcRemoteFpUnit         DisplayString
                }
                
            pvcIndex OBJECT-TYPE
                SYNTAX  INTEGER
                ACCESS  read-only
                STATUS  mandatory
                DESCRIPTION
                        "A unique value for each pvc.  Its value ranges 
                        between 1 and the value of pvcNumber."
                ::= { pvcEntry 1 }
                
            pvcMode OBJECT-TYPE
                SYNTAX  INTEGER {   
                            off(1),
                            pvcr(2),
                            multiplex(3),
                            transp(4),
                            rfc-1490(5),
                            fp(7), 
                            broadcast(8),
                            fp-multiplex(9),
                            not-applicable(254),
                            not-available(255)
                        }
                ACCESS  read-write
                STATUS  mandatory
                DESCRIPTION
                        "Operating mode of PVC."
                ::= { pvcEntry 2 }
                
            pvcDlciAddress OBJECT-TYPE
                SYNTAX  INTEGER (0..1022)
                ACCESS  read-write
                STATUS  mandatory
                DESCRIPTION
                        "The DLCI address of the PVC, representing the 
                        virtual connection identification for accessing
                        the remote unit.  This address is provided by the 
                        carrier. The value 0 is use for the AUTO DLCI."
                ::= { pvcEntry 3 }
                
            pvcPort OBJECT-TYPE
                SYNTAX  INTEGER
                ACCESS  read-write
                STATUS  mandatory
                DESCRIPTION
                        "Frame Relay port used by the PVC.  The port you 
                        select must be configured as a FR-USER port, using 
                        the port PROTOCOL parameter."
                ::= { pvcEntry 4 }
                
            pvcUserPort OBJECT-TYPE
                SYNTAX  INTEGER
                ACCESS  read-write
                STATUS  mandatory
                DESCRIPTION
                        "Frame Relay port used by the PVC.  The port you 
                        select must be configured as a FR-USER port, using 
                        the port PROTOCOL parameter."
                ::= { pvcEntry 5 }
                
            pvcInfoRate OBJECT-TYPE
                SYNTAX  INTEGER (1200..2000000)
                ACCESS  read-write
                STATUS  mandatory
                DESCRIPTION
                        "PVC Committed Information Rate (CIR).  The CIR 
                        represents the data throughput that the network can 
                        accept on this PVC.  The CIR, provided by the 
                        carrier, must be set on the unit to prevent data loss 
                        in the network (frames exceeding the CIR can be 
                        discarded)."
                ::= { pvcEntry 6 }
                
            pvcPriority OBJECT-TYPE
                SYNTAX  INTEGER (0..255)
                ACCESS  read-only
                STATUS  mandatory
                DESCRIPTION
                        "Priority assigned to the PVC for the Spanning Tree
                         algorithm."
                ::= { pvcEntry 9 }
                
            pvcCost OBJECT-TYPE
                SYNTAX  INTEGER (1..65535)
                ACCESS  read-only
                STATUS  mandatory
                DESCRIPTION
                        "The path cost assigned to the PVC for the Spanning Tree
                         algorithm.  This indicates to the automatic single-route
                         bridge function the relative length of the path between
                         the local PVC and the attached LAN.  The higher the value,
                         the less preferred the route."
                ::= { pvcEntry 10 }
                
            pvcRemoteUnit OBJECT-TYPE
                SYNTAX  DisplayString
                ACCESS  read-write
                STATUS  mandatory
                DESCRIPTION
                        "Remote unit to which data from this PVC should be directed."
                ::= { pvcEntry 11 }
                
            pvcTimeout-ms OBJECT-TYPE
                SYNTAX  INTEGER (1000..30000)
                ACCESS  read-write
                STATUS  mandatory
                DESCRIPTION
                        "The wait for ACK timeout before retransmitting a frame
                         on the PVC."
                ::= { pvcEntry 12 }
                
            pvcRetry OBJECT-TYPE
                SYNTAX  INTEGER (1..1000)
                ACCESS  read-write
                STATUS  mandatory
                DESCRIPTION
                        "Maximum number of successive retries before the PVC
                         connection is declared down."
                ::= { pvcEntry 13 }
                
            pvcCompression OBJECT-TYPE
                SYNTAX  INTEGER {   
                            no(1),
                            yes(2),
                            not-applicable(254),
                            not-available(255)
                        }
                ACCESS  read-write
                STATUS  mandatory
                DESCRIPTION
                        "Use compression on the PVC connection to the remote
                         unit.  With compression, the available bandwidth is used
                         more efficiently.  When compression is not used, higher
                         speeds can be obtained on the link."
                ::= { pvcEntry 14 }
                
            pvcIpAddress OBJECT-TYPE
                SYNTAX  IpAddress
                ACCESS  read-write
                STATUS  mandatory
                DESCRIPTION
                        "IP address of the local PVC. This address is a 4-byte value
                         in dotted decimal representation, with a maximum value of 255
                         for each byte.  When set to 000.000.000.000, no IP address is
                         defined for this PVC.  In this case the unit will use the
                         default IP address defined with the global DEFAULT IP ADDR
                         parameter."
                ::= { pvcEntry 15 }
                
            pvcSubnetMask OBJECT-TYPE
                SYNTAX  IpAddress
                ACCESS  read-write
                STATUS  mandatory
                DESCRIPTION
                        "Subnet mask associated with the PVC's IP address. It is
                         configured like the IP address: a 4-byte value in dotted
                         decimal representation, with a maximum value of 255 for each
                         byte.  The subnet mask identifies which bits of the IP address
                         correspond to the physical network, and which  bits correspond
                         to host identifiers."
                ::= { pvcEntry 16 }
                
            pvcMaxFrame OBJECT-TYPE
                SYNTAX  INTEGER (128..8192)
                ACCESS  read-write
                STATUS  mandatory
                DESCRIPTION
                        "Maximum frame size, in octets.  This parameter
                        determines the largest datagram that can be sent
                        or received on the interface in one IP frame.  
                        Datagrams larger than the maximum frame size are 
                        divided into fragments before transmission, the 
                        reassembled at the remote end."
                ::= { pvcEntry 17 }
                

            pvcBroadcastGroup OBJECT-TYPE
                SYNTAX  INTEGER {   
                            no(1),
                            yes(2),
                            not-applicable(254),
                            not-available(255)
                        }
                ACCESS  read-write
                STATUS  mandatory
                DESCRIPTION
                        " 0 and 1 apply to a pvc in pvcr mode only to
                          specify if its belongs or not to a broadcast group"
                ::= { pvcEntry 18 }
  
                
            pvcBrgConnection OBJECT-TYPE
                SYNTAX  INTEGER {   
                            no(1),
                            yes(2),
                            not-applicable(254),
                            not-available(255)
                          }
                ACCESS  read-write
                STATUS  mandatory
                DESCRIPTION
                        "Bridge connection.  Set this parameter to YES if the
                         RFC1490-compatible FRAD at the remote end requires
                         bridge frames.  If bridge data it not required, a NO
                         value will prevent the transmission of unnecessary
                         frames from this PVC, thus reducing your network costs."
                ::= { pvcEntry 19 }
                
            pvcIpConnection OBJECT-TYPE
                SYNTAX  INTEGER {   
                            no(1),
                            yes(2),
                            not-applicable(254),
                            not-available(255)
                        }
                ACCESS  read-write
                STATUS  mandatory
                DESCRIPTION
                        "IP connection.  Set this parameter to YES if the
                         RFC1490-compatible FRAD at the remote end requires
                         bridge frames.  If IP data it not required, a NO
                         value will prevent the transmission of unnecessary
                         frames from this PVC, thus reducing your network costs."
                ::= { pvcEntry 20 }
                
            pvcRemotePvc OBJECT-TYPE
                SYNTAX  INTEGER (1..300)
                ACCESS  read-write
                STATUS  mandatory
                DESCRIPTION
                        "The remote PVC to which data from PVC is sent.
                         Specify the remote PVC number."
                ::= { pvcEntry 21 }
                
            pvcPvcClass OBJECT-TYPE
                SYNTAX  INTEGER (1..8)
                ACCESS  read-write
                STATUS  mandatory
                DESCRIPTION
                        "The priority class for data from this PVC. Classes
                         are defined according to bandwidth weight."
                ::= { pvcEntry 22 }
                
            pvcNetworkPort OBJECT-TYPE
                SYNTAX  INTEGER
                ACCESS  read-write
                STATUS  mandatory
                DESCRIPTION
                        "The Frame Relay network port used by the transparent
                         PVC.  The port you select must be configured as a
                         Frame Relay network port (FR-NET protocol) using the
                         port PROTOC parameter.  All frames received on the
                         network port side for that PVC will be transmitted
                         to the user port side."
                ::= { pvcEntry 23 }
                
            pvcRingNumber OBJECT-TYPE
                SYNTAX  OCTET STRING (SIZE (2)) -- 0x0001 to 0x0FFF
                ACCESS  read-write
                STATUS  mandatory
                DESCRIPTION
                        "The ring number of the remote Token-Ring LAN, required
                         for source routing of Token-Ring data via the unit."
                ::= { pvcEntry 24 }
                
            pvcIpRip OBJECT-TYPE
                SYNTAX  INTEGER {   
                            disable(1),
                            v1(2),
                            v2-broadcast(3),
                            v2-multicast(4),
                            not-applicable(254),
                            not-available(255)
                        }
                ACCESS  read-write
                STATUS  mandatory
                DESCRIPTION
                        "When this parameter is set to V1, the RIP routing
                         is done according to the RIP V1 standard.  With
                         RIP V2, broadcast or multicast can be used.  With
                         RIP V2 MULTICAST, only RIP V2 compliant devices
                         will receive RIP frames."
                ::= { pvcEntry 25 }
            
            pvcBurstInfoRate OBJECT-TYPE
                SYNTAX  INTEGER (1200..2000000)
                ACCESS  read-write
                STATUS  mandatory
                DESCRIPTION
                        "PVC Burst Information Rate (BIR).  The BIR 
                        represents the data throughput that the network can 
                        accept on this PVC when the network is not
                        congested."
                ::= { pvcEntry 26 }
                
            pvcUserDlci OBJECT-TYPE
                SYNTAX  INTEGER (0..1022)
                ACCESS  read-write
                STATUS  mandatory
                DESCRIPTION
                        "The DLCI address of the PVC on the user side, 
                        representing the virtual connection identification 
                        on the frame relay interface."
                ::= { pvcEntry 27 }
                
            pvcNetworkDlci OBJECT-TYPE
                SYNTAX  INTEGER (1..1022)
                ACCESS  read-write
                STATUS  mandatory
                DESCRIPTION
                        "The DLCI address of the PVC on the network side, 
                        representing the virtual connection identification 
                        on the frame relay interface."
                ::= { pvcEntry 28 }

            pvcIpxRip OBJECT-TYPE
                SYNTAX  INTEGER {   
                            disable(1),
                            enable(2),
                            not-applicable(254),
                            not-available(255)
                        }
                ACCESS  read-write
                STATUS  mandatory
                DESCRIPTION
                         "if this parameter is enable, the unit will generate 
                         IPX RIP frame on the port ( the one used by this pvc) 
                         every minute, otherwise the unit will discard all IPX 
                         RIP frame received and no one will be generated on 
                         that port."
                ::= { pvcEntry 29 }
            
            pvcIpxSap OBJECT-TYPE
                SYNTAX  INTEGER {   
                            disable(1),
                            enable(2),
                            not-applicable(254),
                            not-available(255)
                        }
                ACCESS  read-write
                STATUS  mandatory
                DESCRIPTION
                         "if this parameter is enable, the unit will generate 
                         IPX SAP frame on the port ( the one used by this pvc) 
                         every minute, otherwise the unit will discard all IPX 
                         SAP frame received and no one will be generated on 
                         that port."
                ::= { pvcEntry 30 }

            pvcIpxNetNum OBJECT-TYPE
                SYNTAX  OCTET STRING (SIZE (4))
                ACCESS  read-write
                STATUS  mandatory
                DESCRIPTION
                        "This value identify the IPX network number which 
                         the unit is connected to"
                ::= { pvcEntry 31 }

            pvcIpxConnection OBJECT-TYPE
                SYNTAX  INTEGER {   
                            no(1),
                            yes(2),
                            not-applicable(254),
                            not-available(255)
                        }
                ACCESS  read-write
                STATUS  mandatory
                DESCRIPTION
                        "IPX connection.  Set this parameter to YES if the
                         RFC1490-compatible FRAD at the remote end requires
                         bridge frames.  If IPX data it not required, a NO
                         value will prevent the transmission of unnecessary
                         frames from this PVC, thus reducing your network costs."
                ::= { pvcEntry 32 }
                
            pvcType OBJECT-TYPE
                SYNTAX  INTEGER {   
                            dedicated(2),
                            answer(3),
                            call-backup(4),
                            not-applicable(254),
                            not-available(255)
                        }
                ACCESS  read-write
                STATUS  mandatory
                DESCRIPTION
                        "For PVCR mode only.  This parameter defines the PVC
                        as a dedicated PVC or a backup PVC.  The ANSWER type 
                        is used for the PVC that responds to calls.  When you 
                        install a backup PVC between two units, one unit must be 
                        configured in CALL-BACKUP type and the other as ANSWER."
                ::= { pvcEntry 33 }
                
            pvcBackupCall-s OBJECT-TYPE
                SYNTAX  INTEGER (1..255)
                ACCESS  read-write
                STATUS  mandatory
                DESCRIPTION
                        "Delay, in seconds, before activating the backup PVC when a
                         line failure has occurred on a dedicated link or PVC."
                ::= { pvcEntry 34 }
                
            pvcBackupHang-s OBJECT-TYPE
                SYNTAX  INTEGER (1..255)
                ACCESS  read-write
                STATUS  mandatory
                DESCRIPTION
                        "Delay, in seconds, before deactivating the backup WAN PVC
                         after the dedicated link or PVC has been restored."
                ::= { pvcEntry 35 }
                
            pvcBackup OBJECT-TYPE
                SYNTAX  INTEGER {   
                            any(15),
                            all(16),
                            not-applicable(254),
                            not-available(255)
                        }
                ACCESS  read-write
                STATUS  mandatory
                DESCRIPTION
                        "Backup PVC can be configured to monitor and backup any 
                         link or PCV that fails (ANY) or all links and PVCs (ALL)."
                ::= { pvcEntry 36 }
                
            pvcOspfEnable OBJECT-TYPE
                SYNTAX  INTEGER {   
                            disable(1),
                            enable(2),
                            not-applicable(254),
                            not-available(255)
                        }
                ACCESS  read-write
                STATUS  mandatory
                DESCRIPTION
                        "Indicates whether or not OSPF is enabled on this 
                         PVC."
                ::= { pvcEntry 37 }

            pvcOspfAreaId OBJECT-TYPE
                SYNTAX  IpAddress
                ACCESS  read-write
                STATUS  mandatory
                DESCRIPTION
                        "Identifies the area to which this PVC belongs."
                ::= { pvcEntry 38 }

            pvcOspfTransitDelay OBJECT-TYPE
                SYNTAX  INTEGER (1..360)
                ACCESS  read-write
                STATUS  mandatory
                DESCRIPTION
                        "The estimated number of seconds it takes to 
                         transmit a Link State Update Packet over this 
                         PVC."
                ::= { pvcEntry 39 }

            pvcOspfRetransmitInt OBJECT-TYPE
                SYNTAX  INTEGER (1..360)
                ACCESS  read-write
                STATUS  mandatory
                DESCRIPTION
                        "The number of seconds between like state advertisement
                         retransmissions for adjacencies belonging to this
                         PVC.  Also used when retransmitting Database
                         Description and Link State Request Packets."
                ::= { pvcEntry 40 }

            pvcOspfHelloInt OBJECT-TYPE
                SYNTAX  INTEGER (1..360)
                ACCESS  read-write
                STATUS  mandatory
                DESCRIPTION
                        "The length of time, in seconds, between the Hello
                         Packets that the router sends on the PVC.
                         This value is advertised in the router's Hello
                         Packets.  It must be the same for all routers 
                         attached to a common network.  The smaller the 
                         HelloInterval, the faster topological changes will 
                         be detected, but more OSPF routing protocol traffic
                         will ensue."
                ::= { pvcEntry 41 }

            pvcOspfDeadInt OBJECT-TYPE
                SYNTAX  INTEGER (1..2000)
                ACCESS  read-write
                STATUS  mandatory
                DESCRIPTION
                        "After ceasing to hear a router's Hello Packets, the 
                         number of seconds before its neighbors declare the 
                         router down.  This is also advertised in the router's 
                         Hello Packets in their RouterDeadInterval field.  
                         This value again bust be the same for all routers 
                         attached to a common network."
                ::= { pvcEntry 42 }

            pvcOspfPassword OBJECT-TYPE
                SYNTAX  DisplayString
                ACCESS  read-write
                STATUS  mandatory
                DESCRIPTION
                        "This configured data allows the authentication 
                         procedure to generate and/or verify the 
                         authentication field in the OSPF header.  This 
                         value again must be the same for all routers 
                         attached to a common network."
                ::= { pvcEntry 43 }

            pvcOspfMetricCost OBJECT-TYPE
                SYNTAX  INTEGER (1..65534)
                ACCESS  read-write
                STATUS  mandatory
                DESCRIPTION
                        "The cost of sending a packet on the PVC
                         expressed in the link state metric.  This is 
                         advertised as the link cost for this PVC 
                         in the router's router links advertisement."
                ::= { pvcEntry 44 }

            pvcProxyAddr OBJECT-TYPE
                SYNTAX  INTEGER (1..8)
                ACCESS  read-write
                STATUS  mandatory
                DESCRIPTION
                        "This variable indicates in what slot of the remote unit 
                         (i.e. the SDM-RX unit where this pvc goes) is the SNMP/NMS
                         proxy agent board "
                ::= { pvcEntry 45 }

            pvcLlcConnection OBJECT-TYPE
                SYNTAX  INTEGER {   
                            no(1),
                            yes(2),
                            not-applicable(254),
                            not-available(255)
                        }
                ACCESS  read-write
                STATUS  mandatory
                DESCRIPTION
                        "IPX connection.  Set this parameter to YES if the
                         RFC1490-compatible FRAD at the remote end requires
                         bridge frames.  If IPX data it not required, a NO
                         value will prevent the transmission of unnecessary
                         frames from this PVC, thus reducing your network costs."
                ::= { pvcEntry 46 }
                
            pvcDialTimeout OBJECT-TYPE
                SYNTAX  INTEGER (30..255)
                ACCESS  read-write
                STATUS  mandatory
                DESCRIPTION
                        "Wait time, in seconds, allowed to establish a backup pvc
                         using a dial phone number"
                ::= { pvcEntry 47 }

            pvcMaxChannels OBJECT-TYPE
                SYNTAX  INTEGER (0..10000)
                ACCESS  read-write
                STATUS  mandatory
                DESCRIPTION
                        "Indicates the maximum number of voice channels
                        permitted on this PVC."
                ::= { pvcEntry 48 }

            pvcHuntForwardingAUnit OBJECT-TYPE
                SYNTAX  DisplayString (SIZE (0..16))
                ACCESS  read-write
                STATUS  mandatory
                DESCRIPTION
                        "Hunt forwarding group A Unit name. Unit name where a busy call for
                         hunt group A will be forwarded to"
                ::= { pvcEntry 49 }

            pvcHuntForwardingBUnit OBJECT-TYPE
                SYNTAX  DisplayString (SIZE (0..16))
                ACCESS  read-write
                STATUS  mandatory
                DESCRIPTION
                        "Hunt forwarding group B Unit name. Unit name where a busy call for
                         hunt group B will be forwarded to"
                ::= { pvcEntry 50 }

            pvcRemoteFpUnit OBJECT-TYPE
                SYNTAX  DisplayString
                ACCESS  read-write
                STATUS  mandatory
                DESCRIPTION
                        "Remote FP unit to which data from this PVC should be directed."
                ::= { pvcEntry 51 }
                
            pvcIpRipTxRx OBJECT-TYPE
                SYNTAX  INTEGER {
                            duplex(1),
                            tx-only(2),
                            rx-only(3),
                            not-applicable(254),
                            not-available(255)
                        }
                ACCESS  read-write
                STATUS  mandatory
                DESCRIPTION
                        "This parameter allows RIP frames transmission only,
                        RIP frames reception only or both transmission and
                        reception of RIP frames."
                ::= { pvcEntry 52 }

            pvcIpRipAuthType OBJECT-TYPE
                SYNTAX  INTEGER {
                            none(1),
                            simple(2),
                            not-applicable(254),
                            not-available(255)
                        }
                ACCESS  read-write
                STATUS  mandatory
                DESCRIPTION
                        "Enable or disable password authentication for
                        the interface. If you select Simple Password, the
                        password will be included in the sent RIP frames.
                        The received frames containing authentication will be
                        accepted only if the password is valid."
                ::= { pvcEntry 53 }

            pvcIpRipPassword OBJECT-TYPE
                SYNTAX  DisplayString
                ACCESS  read-write
                STATUS  mandatory
                DESCRIPTION
                        "This configured data allows the authentication
                        procedure to generate and/or verify the
                        authentication field in the RIP header.  This
                        value again must be the same for each
                        interface on each side of the link."
                ::= { pvcEntry 54 }
                
            PvcPvcrEntry ::=
                SEQUENCE {
                    pvcIndex                INTEGER,
                    pvcMode                 INTEGER,
                    pvcDlciAddress          INTEGER,
                    pvcPort                 INTEGER,
                    pvcInfoRate             INTEGER,
                    pvcBurstInfoRate        INTEGER,
                    pvcType                 INTEGER,
                    pvcBackupCall-s         INTEGER,
                    pvcBackupHang-s         INTEGER,
                    pvcDialTimeout          INTEGER,          
                    pvcBackup               INTEGER,
                    pvcPriority             INTEGER,
                    pvcCost                 INTEGER,
                    pvcRemoteUnit           DisplayString,
                    pvcTimeout-ms           INTEGER,
                    pvcRetry                INTEGER,
                    pvcCompression          INTEGER,
                    pvcIpAddress            IpAddress,
                    pvcSubnetMask           IpAddress,
                    pvcMaxFrame             INTEGER,
                    pvcBroadcastGroup       INTEGER,
                    pvcIpRip                INTEGER,
                    pvcIpRipTxRx            INTEGER,
                    pvcIpRipAuthType        INTEGER,
                    pvcIpRipPassword        DisplayString,
                    pvcOspfEnable           INTEGER,
                    pvcOspfAreaId           IpAddress,
                    pvcOspfTransitDelay     INTEGER,
                    pvcOspfRetransmitInt    INTEGER,
                    pvcOspfHelloInt         INTEGER,
                    pvcOspfDeadInt          INTEGER,
                    pvcOspfPassword         DisplayString,
                    pvcOspfMetricCost       INTEGER,
                    pvcRingNumber           OCTET STRING (SIZE (2)),
                    pvcIpxRip               INTEGER,
                    pvcIpxSap               INTEGER,
                    pvcIpxNetNum            OCTET STRING (SIZE (4)),
                    pvcLlcConnection        INTEGER,
                    pvcMaxChannels          INTEGER
                }
                
            PvcRfc1490Entry ::=
                SEQUENCE {
                    pvcIndex                INTEGER,
                    pvcMode                 INTEGER,
                    pvcDlciAddress          INTEGER,
                    pvcPort                 INTEGER,
                    pvcInfoRate             INTEGER,
                    pvcBurstInfoRate        INTEGER,
                    pvcPriority             INTEGER,
                    pvcCost                 INTEGER,
                    pvcRemoteUnit           DisplayString,
                    pvcIpAddress            IpAddress,
                    pvcSubnetMask           IpAddress,
                    pvcMaxFrame             INTEGER,
                    pvcIpRip                INTEGER,
                    pvcIpRipTxRx            INTEGER,
                    pvcIpRipAuthType        INTEGER,
                    pvcIpRipPassword        DisplayString,
                    pvcOspfEnable           INTEGER,
                    pvcOspfAreaId           IpAddress,
                    pvcOspfTransitDelay     INTEGER,
                    pvcOspfRetransmitInt    INTEGER,
                    pvcOspfHelloInt         INTEGER,
                    pvcOspfDeadInt          INTEGER,
                    pvcOspfPassword         DisplayString,
                    pvcOspfMetricCost       INTEGER,
                    pvcBrgConnection        INTEGER,
                    pvcIpConnection         INTEGER,
                    pvcIpxConnection        INTEGER,
                    pvcLlcConnection        INTEGER,
                    pvcRingNumber           OCTET STRING (SIZE (2)),
                    pvcIpxRip               INTEGER,
                    pvcIpxSap               INTEGER,
                    pvcIpxNetNum            OCTET STRING (SIZE (4)),
                    pvcProxyAddr            INTEGER
                }
                
            PvcMultiplexEntry ::=
                SEQUENCE {
                    pvcIndex                INTEGER,
                    pvcMode                 INTEGER,
                    pvcDlciAddress          INTEGER,
                    pvcPort                 INTEGER,
                    pvcInfoRate             INTEGER,
                    pvcBurstInfoRate        INTEGER,
                    pvcRemoteUnit           DisplayString,
                    pvcRemotePvc            INTEGER,
                    pvcPvcClass             INTEGER,
                    pvcCompression          INTEGER
                }
                
            PvcTranspEntry ::=
                SEQUENCE {
                    pvcIndex                INTEGER,
                    pvcMode                 INTEGER,
                    pvcDlciAddress          INTEGER,
                    pvcUserDlci             INTEGER,
                    pvcUserPort             INTEGER,
                    pvcInfoRate             INTEGER,
                    pvcBurstInfoRate        INTEGER,
                    pvcNetworkDlci          INTEGER,
                    pvcNetworkPort          INTEGER
                }
                
            PvcFPEntry ::=
                SEQUENCE {
                    pvcIndex                INTEGER,
                    pvcMode                 INTEGER,
                    pvcDlciAddress          INTEGER,
                    pvcPort                 INTEGER,
                    pvcInfoRate             INTEGER,
                    pvcBurstInfoRate        INTEGER,
                    pvcRemoteUnit           DisplayString,
                    pvcIpAddress            IpAddress,
                    pvcSubnetMask           IpAddress,
                    pvcMaxFrame             INTEGER,
                    pvcProxyAddr            INTEGER (1..8),
                    pvcMaxChannels          INTEGER,
                    pvcHuntForwardingAUnit  DisplayString,
                    pvcHuntForwardingBUnit  DisplayString
                }

            PvcFpMultiplexEntry ::=
                SEQUENCE {
                    pvcIndex                INTEGER,
                    pvcMode                 INTEGER,
                    pvcRemoteUnit           DisplayString,
                    pvcRemotePvc            INTEGER,
                    pvcPvcClass             INTEGER,
                    pvcCompression          INTEGER,
                    pvcIpAddress            IpAddress,
                    pvcSubnetMask           IpAddress,
                    pvcMaxFrame             INTEGER,
                    pvcProxyAddr            INTEGER (1..8),
                    pvcMaxChannels          INTEGER,
                    pvcHuntForwardingAUnit  DisplayString,
                    pvcHuntForwardingBUnit  DisplayString,
                    pvcRemoteFpUnit         DisplayString
                }


            -- The ipx group
            
            -- This group lets you configure IPX router.

            ipxRouterEnable OBJECT-TYPE
                SYNTAX  INTEGER {   
                            disable(1),
                            enable(2),
                            not-applicable(254),
                            not-available(255)
                        }
                ACCESS  read-write
                STATUS  mandatory
                DESCRIPTION
                        "This variable defines the state of IPX Router (enable or 
                        disable) .  If IPX Router parameter is enable, the 
                        unit will Route all IPX frames  between different IPX
                        networks which unit is connected to, otherwise, all IPX 
                        frames will be bridged (if BRIDGE is enable) or discarded
                        (if not)."
                ::= { ipx 1 }
                
            ipxInternalNetNum OBJECT-TYPE
                SYNTAX  OCTET STRING (SIZE (4))
                ACCESS  read-write
                STATUS  mandatory
                DESCRIPTION
                        "This value identify the IPX internal network number.  
                         This value is used on unnumbered links."
                ::= { ipx 2 }
                
            -- The ip group
            
            -- This group lets you configure IP parameters.

            ipRouterEnable OBJECT-TYPE
                SYNTAX  INTEGER {   
                            disable(1),
                            enable(2),
                            not-applicable(254),
                            not-available(255)
                        }
                ACCESS  read-write
                STATUS  mandatory
                DESCRIPTION
                        "This variable defines the state of IP Router (enable or 
                        disable) .  If IP Router parameter is enable, the 
                        unit will Route  IP frames  between different IP
                        networks which unit is connected to, otherwise, all IP 
                        frames will be bridged (if BRIDGE is enable) or discarded
                        (if not)."
                ::= { ip 1 }
                

            -- The bootp group
            
            -- This group lets you configure IP parameters relevant to BOOTP

            bootpEnable OBJECT-TYPE
                SYNTAX INTEGER {   
                            disable(1),
                            enable(2),
                            not-applicable(254),
                            not-available(255)
                        }
                ACCESS  read-write
                STATUS  mandatory
                DESCRIPTION
                        "This variable defines the state of the BOOTP protocol
                        If the BOOTP protocol is enable, the unit will act as 
                        a BOOTP/DHCP relay agent by forwarding the BOOTP/DHCP
                        frame."
                ::= { bootp 1 }

            bootpMaxHops OBJECT-TYPE
                SYNTAX  INTEGER (0..16)
                ACCESS  read-write
                STATUS  mandatory
                DESCRIPTION
                       "Number maximum of BOOTP relay agent a frame could cross
                       before being discarded"
                ::= { bootp 2 }

            bootpIpDestAddr1 OBJECT-TYPE
                SYNTAX  IpAddress
                ACCESS  read-write
                STATUS  mandatory
                DESCRIPTION
                        "The Destination IP address 1 - The IP address of the 
                        next BOOTP relay agent or server.  When a BOOTREQUEST
                        frame is received, this is where the frame is forwarded.
                        Note:  When all the ‘Destination IP addresses are 0.0.0.0,
                        BOOTP is in BROADCAST MODE (see documentation)."
                ::= { bootp 3 }
                
            bootpIpDestAddr2 OBJECT-TYPE
                SYNTAX  IpAddress
                ACCESS  read-write
                STATUS  mandatory
                DESCRIPTION
                        "The Destination IP address 2 - The IP address of the 
                        next BOOTP relay agent or server.  When a BOOTREQUEST
                        frame is received, this is where the frame is forwarded.
                        Note:  When all the ‘Destination IP addresses are 0.0.0.0,
                        BOOTP is in BROADCAST MODE (see documentation)."
                ::= { bootp 4 }
                
            bootpIpDestAddr3 OBJECT-TYPE
                SYNTAX  IpAddress
                ACCESS  read-write
                STATUS  mandatory
                DESCRIPTION
                        "The Destination IP address 3 - The IP address of the 
                        next BOOTP relay agent or server.  When a BOOTREQUEST
                        frame is received, this is where the frame is forwarded.
                        Note:  When all the ‘Destination IP addresses are 0.0.0.0,
                        BOOTP is in BROADCAST MODE (see documentation)."
                ::= { bootp 5 }
                
            bootpIpDestAddr4 OBJECT-TYPE
                SYNTAX  IpAddress
                ACCESS  read-write
                STATUS  mandatory
                DESCRIPTION
                        "The Destination IP address 4 - The IP address of the 
                        next BOOTP relay agent or server.  When a BOOTREQUEST
                        frame is received, this is where the frame is forwarded.
                        Note:  When all the ‘Destination IP addresses are 0.0.0.0,
                        BOOTP is in BROADCAST MODE (see documentation)."
                ::= { bootp 6 }


            -- The timep group
            
            -- This group lets you configure IP parameters relevant to timep

            timepTimeZoneSign OBJECT-TYPE
                SYNTAX  INTEGER
                     {
                     no(1),
                     yes(2)
                     }
                ACCESS  read-write
                STATUS  mandatory
                DESCRIPTION
                        "Time zone offset sign. YES means negative"
                ::= { timep 1 }

            timepTimeZone OBJECT-TYPE
                SYNTAX  INTEGER (0..720)
                ACCESS  read-write
                STATUS  mandatory
                DESCRIPTION
                        "Time offset from GMT (in minutes)."
                ::= { timep 2 }

            timepDaylightSaving OBJECT-TYPE
                SYNTAX  INTEGER
                        {
                        no(1),
                        yes(2)
                        }
                ACCESS  read-write
                STATUS  mandatory
                DESCRIPTION
                       "Enable daylight saving time (one hour)."
                ::= { timep 3 }

            timepServerProtocol OBJECT-TYPE
                SYNTAX  INTEGER
                        {
                        none(1),
                        udp(2),
                        tcp(3),
                        both(4)
                        }
                ACCESS  read-write
                STATUS  mandatory
                DESCRIPTION
                        "Protocols supported by the time server."
                ::= { timep 4 }
                
            timepClientProtocol OBJECT-TYPE
                SYNTAX  INTEGER
                        {
                        none(1),
                        udp(2),
                        tcp(3)
                        }
                ACCESS  read-write
                STATUS  mandatory
                DESCRIPTION
                        "Protocols used by the time client."
                ::= { timep 5 }

            timepServerIpAddress OBJECT-TYPE
                SYNTAX  IpAddress
                ACCESS  read-write
                STATUS  mandatory
                DESCRIPTION
                        "IP address of time client server."
                ::= { timep 6 }

            timepClientUpdateInterval OBJECT-TYPE
                SYNTAX  INTEGER(1..65534)
                ACCESS  read-write
                STATUS  mandatory
                DESCRIPTION
                        "Time client update interval (in minutes)."
                ::= { timep 7 }

            timepClientUdpTimeout OBJECT-TYPE
                SYNTAX  INTEGER(1..65534)
                ACCESS  read-write
                STATUS  mandatory
                DESCRIPTION
                        "Time client UDP timeout (in seconds)."
                ::= { timep 8 }

            timepClientUdpRetransmissions OBJECT-TYPE
                SYNTAX  INTEGER(1..65534)
                ACCESS  read-write
                STATUS  mandatory
                DESCRIPTION
                        "Time client UDP retransmissions."
                ::= { timep 9 }

            timepGetServerTimeNow OBJECT-TYPE
                SYNTAX  INTEGER(0..1)
                ACCESS  read-write
                STATUS  mandatory
                DESCRIPTION
                        "Get time from time server. Do not wait for update
                         timer to expire. Time client must be enabled and
                         time server must be on line. If everything is up,
                         it will take approximately 60 seconds before the
                         time is updated"
                ::= { timep 10 }

                
            -- The IP static table group
            
            -- This group lets you configure the parameters for IP static entries.

            ipstaticNumber OBJECT-TYPE
                SYNTAX  INTEGER
                ACCESS  read-only
                STATUS  mandatory
                DESCRIPTION
                        "The number of IP static entries present on this system."
                ::= { ipstatic 1 }
                
            -- The IP static table    
            
            ipstaticTable OBJECT-TYPE
                SYNTAX  SEQUENCE OF IpstaticEntry
                ACCESS  not-accessible
                STATUS  mandatory
                DESCRIPTION
                        "A list of IP static entries.  The number of entries 
                        is given by the value of ipstaticNumber."
                ::= { ipstatic 2 }
            
            ipstaticEntry OBJECT-TYPE
                SYNTAX  IpstaticEntry
                ACCESS  not-accessible
                STATUS  mandatory
                DESCRIPTION
                        "This table contains the principal configurable
                        parameters who are used for a particular IP static
                        entry."
                INDEX   { ipstaticIndex }
                ::= { ipstaticTable 1 }
            
            IpstaticEntry ::=
                SEQUENCE {
                    ipstaticIndex        INTEGER,
                    ipstaticValid        INTEGER,
                    ipstaticIpDest       IpAddress,
                    ipstaticMask         IpAddress,
                    ipstaticNextHop      IpAddress
                }
                
            ipstaticIndex OBJECT-TYPE
                SYNTAX  INTEGER
                ACCESS  read-only
                STATUS  mandatory
                DESCRIPTION
                        "A unique value for each entry.  Its value ranges 
                        between 1 and the value of ipstaticNumber."
                ::= { ipstaticEntry 1 }
                
            ipstaticValid OBJECT-TYPE
                SYNTAX  INTEGER {   
                            no(1),
                            yes(2),
                            not-applicable(254),
                            not-available(255)
                        }
                ACCESS  read-write
                STATUS  mandatory
                DESCRIPTION
                        "Sets the activation status of the entry."
                ::= { ipstaticEntry 2 }
                
            ipstaticIpDest OBJECT-TYPE
                SYNTAX  IpAddress
                ACCESS  read-write
                STATUS  mandatory
                DESCRIPTION
                        "The destination IP address which we want include
                         in the address table (e.g. RIP table)"
                ::= { ipstaticEntry 3 }
                
            ipstaticMask OBJECT-TYPE
                SYNTAX  IpAddress
                ACCESS  read-write
                STATUS  mandatory
                DESCRIPTION
                        "The destination IP address mask."
                ::= { ipstaticEntry 4 }
                
            ipstaticNextHop OBJECT-TYPE
                SYNTAX  IpAddress
                ACCESS  read-write
                STATUS  mandatory
                DESCRIPTION
                        "The IP address of the next hop to reach the 
                         destination IP address specified."
                ::= { ipstaticEntry 5 }
                
            -- The ospf group
            
            -- This group lets you configure OSPF parameters.

            ospfGlobal           OBJECT IDENTIFIER ::= { ospf 1 }
            ospfArea             OBJECT IDENTIFIER ::= { ospf 2 }
            ospfRange            OBJECT IDENTIFIER ::= { ospf 3 }
            ospfVLink            OBJECT IDENTIFIER ::= { ospf 4 }

            -- The ospf global group

            ospfGlobalRouterId OBJECT-TYPE
                SYNTAX  IpAddress
                ACCESS  read-write
                STATUS  mandatory
                DESCRIPTION
                        "This is a 32-bit number that uniquely identifies 
                         the router in the Autonomous System."
                ::= { ospfGlobal 1 }

            ospfGlobalAutoVLink OBJECT-TYPE
                SYNTAX  INTEGER {   
                            no(1),
                            yes(2),
                            not-applicable(254),
                            not-available(255)
                        }
                ACCESS  read-write
                STATUS  mandatory
                DESCRIPTION
                        "Indicates if virtual links can be configured 
                         automatically or not."
                ::= { ospfGlobal 2 }
                
            ospfGlobalRackAreaId OBJECT-TYPE
                SYNTAX  IpAddress
                ACCESS  read-write
                STATUS  mandatory
                DESCRIPTION
                        "Identifies the area to which the backplane 
                         belongs.  Valid only on rack products."
                ::= { ospfGlobal 3 }
                
            ospfGlobalGlobalAreaId OBJECT-TYPE
                SYNTAX  IpAddress
                ACCESS  read-write
                STATUS  mandatory
                DESCRIPTION
                        "This parameter identifies the area to which
                         the cleartrac's global Default IP Address belongs."
                ::= { ospfGlobal 4 }

            -- The ospf area group
            
            ospfAreaNumber OBJECT-TYPE
                SYNTAX  INTEGER
                ACCESS  read-only
                STATUS  mandatory
                DESCRIPTION
                        "The number of areas present on this system."
                ::= { ospfArea 1 }
                
            -- The OSPF area table    
            
            ospfAreaTable OBJECT-TYPE
                SYNTAX  SEQUENCE OF OspfAreaEntry
                ACCESS  not-accessible
                STATUS  mandatory
                DESCRIPTION
                        "A list of areas.  The number of areas 
                        is given by the value of ospfAreaNumber."
                ::= { ospfArea 2 }
            
            ospfAreaEntry OBJECT-TYPE
                SYNTAX  OspfAreaEntry
                ACCESS  not-accessible
                STATUS  mandatory
                DESCRIPTION
                        "This table contains the principal configurable
                        parameters who are used for a particular area."
                INDEX   { ospfAreaIndex }
                ::= { ospfAreaTable 1 }
            
            OspfAreaEntry ::=
                SEQUENCE {
                    ospfAreaIndex        INTEGER,
                    ospfAreaAreaId       IpAddress,
                    ospfAreaEnable       INTEGER,
                    ospfAreaAuthType     INTEGER,
                    ospfAreaImportASExt  INTEGER,
                    ospfAreaStubMetric   INTEGER
                }
                
            ospfAreaIndex OBJECT-TYPE
                SYNTAX  INTEGER
                ACCESS  read-only
                STATUS  mandatory
                DESCRIPTION
                        "A unique value for each entry.  Its value ranges 
                        between 1 and the value of ospfAreaNumber."
                ::= { ospfAreaEntry 1 }
                
            ospfAreaAreaId OBJECT-TYPE
                SYNTAX  IpAddress
                ACCESS  read-write
                STATUS  mandatory
                DESCRIPTION
                        "This is a 32-bit number that identifies the area.
                         The Area ID of 0.0.0.0 is reserved for the backbone."
                ::= { ospfAreaEntry 2 }
                
            ospfAreaEnable OBJECT-TYPE
                SYNTAX  INTEGER {   
                            disable(1),
                            enable(2),
                            not-applicable(254),
                            not-available(255)
                        }
                ACCESS  read-write
                STATUS  mandatory
                DESCRIPTION
                        "Allows you to enable and disable this area."
                ::= { ospfAreaEntry 3 }
                
            ospfAreaAuthType OBJECT-TYPE
                SYNTAX  INTEGER {   
                            none(1),
                            simple(2),
                            not-applicable(254),
                            not-available(255)
                        }
                ACCESS  read-write
                STATUS  mandatory
                DESCRIPTION
                        "Enables or disables password authentication for 
                         the area.  If you select Simple Password, only 
                         those routers sharing the correct password will 
                         be able to communicate with each other."
                ::= { ospfAreaEntry 4 }
                
            ospfAreaImportASExt OBJECT-TYPE
                SYNTAX  INTEGER {   
                            no(1),
                            yes(2),
                            not-applicable(254),
                            not-available(255)
                        }
                ACCESS  read-write
                STATUS  mandatory
                DESCRIPTION
                        "Indicates whether or not this area imports AS 
                         external link state advertisements.  If AS external 
                         advertisements are excluded from the area, the area 
                         is called a stub.  The backbone cannot be configured 
                         as a stub area.  Also, virtual links cannot be 
                         configured through stub areas."
                ::= { ospfAreaEntry 5 }
                
            ospfAreaStubMetric OBJECT-TYPE
                SYNTAX  INTEGER (1..255)
                ACCESS  read-write
                STATUS  mandatory
                DESCRIPTION
                        "If the area has been configured as a stub area, and 
                         the router itself is an area border router, then 
                         the StubMetric indicates the cost of the default 
                         summary link that the router should advertise into 
                         the area."
                ::= { ospfAreaEntry 6 }
                
            -- The ospf range group
            
            ospfRangeNumber OBJECT-TYPE
                SYNTAX  INTEGER
                ACCESS  read-only
                STATUS  mandatory
                DESCRIPTION
                        "The number of ranges present on this system."
                ::= { ospfRange 1 }
                
            -- The OSPF range table    
            
            ospfRangeTable OBJECT-TYPE
                SYNTAX  SEQUENCE OF OspfRangeEntry
                ACCESS  not-accessible
                STATUS  mandatory
                DESCRIPTION
                        "A list of ranges.  The number of ranges 
                        is given by the value of ospfRangeNumber."
                ::= { ospfRange 2 }
            
            ospfRangeEntry OBJECT-TYPE
                SYNTAX  OspfRangeEntry
                ACCESS  not-accessible
                STATUS  mandatory
                DESCRIPTION
                        "This table contains the principal configurable
                        parameters who are used for a particular range."
                INDEX   { ospfRangeIndex }
                ::= { ospfRangeTable 1 }
            
            OspfRangeEntry ::=
                SEQUENCE {
                    ospfRangeIndex       INTEGER,
                    ospfRangeNet         IpAddress,
                    ospfRangeMask        IpAddress,
                    ospfRangeEnable      INTEGER,
                    ospfRangeStatus      INTEGER,
                    ospfRangeAddToArea   IpAddress
                }
                
            ospfRangeIndex OBJECT-TYPE
                SYNTAX  INTEGER
                ACCESS  read-only
                STATUS  mandatory
                DESCRIPTION
                        "A unique value for each entry.  Its value ranges 
                        between 1 and the value of ospfRangeNumber."
                ::= { ospfRangeEntry 1 }
                
            ospfRangeNet OBJECT-TYPE
                SYNTAX  IpAddress
                ACCESS  read-write
                STATUS  mandatory
                DESCRIPTION
                        "Describes the collection of Ip addresses contained in 
                         the address range.  This network address, together 
                         with the range mask parameter, specifies the subnets 
                         to be grouped in this area range.  Just one link 
                         summary advertisement will be generated for all 
                         subnets in this range."
                ::= { ospfRangeEntry 2 }
                
            ospfRangeMask OBJECT-TYPE
                SYNTAX  IpAddress
                ACCESS  read-write
                STATUS  mandatory
                DESCRIPTION
                        "This parameter, together with Range Net, indicates 
                         all of the networks that belong to this range."
                ::= { ospfRangeEntry 3 }
                
            ospfRangeEnable OBJECT-TYPE
                SYNTAX  INTEGER {   
                            disable(1),
                            enable(2),
                            not-applicable(254),
                            not-available(255)
                        }
                ACCESS  read-write
                STATUS  mandatory
                DESCRIPTION
                        "Enables or disables this range for the specified 
                         area."
                ::= { ospfRangeEntry 4 }
                
            ospfRangeStatus OBJECT-TYPE
                SYNTAX  INTEGER {   
                            don-t-adv(1),
                            advertise(2),
                            not-applicable(254),
                            not-available(255)
                        }
                ACCESS  read-write
                STATUS  mandatory
                DESCRIPTION
                        "Set to either Advertise or DoNotAdvertise.
                         Unadvertised ranges allow the existence of certain 
                         networks to be intentionally hidden from other areas.
                         Status is set to Advertise by default."
                ::= { ospfRangeEntry 5 }
                
            ospfRangeAddToArea OBJECT-TYPE
                SYNTAX  IpAddress
                ACCESS  read-write
                STATUS  mandatory
                DESCRIPTION
                        "The area ID that identifies the area to which this
                         range belongs."
                ::= { ospfRangeEntry 6 }
            
            -- The ospf vlink group
            
            ospfVLinkNumber OBJECT-TYPE
                SYNTAX  INTEGER
                ACCESS  read-only
                STATUS  mandatory
                DESCRIPTION
                        "The number of virtual links present on this system."
                ::= { ospfVLink 1 }
                
            -- The OSPF vlink table    
            
            ospfVLinkTable OBJECT-TYPE
                SYNTAX  SEQUENCE OF OspfVLinkEntry
                ACCESS  not-accessible
                STATUS  mandatory
                DESCRIPTION
                        "A list of virtual links.  The number of virtual 
                         links is given by the value of ospfVLinkNumber."
                ::= { ospfVLink 2 }
            
            ospfVLinkEntry OBJECT-TYPE
                SYNTAX  OspfVLinkEntry
                ACCESS  not-accessible
                STATUS  mandatory
                DESCRIPTION
                        "This table contains the principal configurable
                        parameters who are used for a particular vlink."
                INDEX   { ospfVLinkIndex }
                ::= { ospfVLinkTable 1 }
            
            OspfVLinkEntry ::=
                SEQUENCE {
                    ospfVLinkIndex         INTEGER,
                    ospfVLinkTransitAreaId IpAddress,
                    ospfVLinkNeighborRtrId IpAddress,
                    ospfVLinkEnable        INTEGER,
                    ospfVLinkTransitDelay  INTEGER,
                    ospfVLinkRetransmitInt INTEGER,
                    ospfVLinkHelloInt      INTEGER,
                    ospfVLinkDeadInt       INTEGER,
                    ospfVLinkPassword      DisplayString
                }
                
            ospfVLinkIndex OBJECT-TYPE
                SYNTAX  INTEGER
                ACCESS  read-only
                STATUS  mandatory
                DESCRIPTION
                        "A unique value for each entry.  Its value ranges 
                        between 1 and the value of ospfVLinkNumber."
                ::= { ospfVLinkEntry 1 }
            
            ospfVLinkTransitAreaId OBJECT-TYPE
                SYNTAX  IpAddress
                ACCESS  read-write
                STATUS  mandatory
                DESCRIPTION
                        "Identifies the transit area ID through which the
                         virtual link is configured."
                ::= { ospfVLinkEntry 2 }
                
            ospfVLinkNeighborRtrId OBJECT-TYPE
                SYNTAX  IpAddress
                ACCESS  read-write
                STATUS  mandatory
                DESCRIPTION
                        "Indicates the neighbor router ID at the other end
                         of this virtual link."
                ::= { ospfVLinkEntry 3 }
                
            ospfVLinkEnable OBJECT-TYPE
                SYNTAX  INTEGER {   
                            disable(1),
                            enable(2),
                            not-applicable(254),
                            not-available(255)
                        }
                ACCESS  read-write
                STATUS  mandatory
                DESCRIPTION
                        "Enables or disables this virtual link."
                ::= { ospfVLinkEntry 4 }
                
            ospfVLinkTransitDelay OBJECT-TYPE
                SYNTAX  INTEGER (1..360)
                ACCESS  read-write
                STATUS  mandatory
                DESCRIPTION
                        "The estimated number of seconds it takes to 
                         transmit a Link State Update Packet over this 
                         interface."
                ::= { ospfVLinkEntry 5 }

            ospfVLinkRetransmitInt OBJECT-TYPE
                SYNTAX  INTEGER (1..360)
                ACCESS  read-write
                STATUS  mandatory
                DESCRIPTION
                        "The number of seconds between like state advertisement
                         retransmissions for adjacencies belonging to this
                         interface.  Also used when retransmitting Database
                         Description and Link State Request Packets."
                ::= { ospfVLinkEntry 6 }

            ospfVLinkHelloInt OBJECT-TYPE
                SYNTAX  INTEGER (1..360)
                ACCESS  read-write
                STATUS  mandatory
                DESCRIPTION
                        "The length of time, in seconds, between the Hello
                         Packets that the router sends on the interface.
                         This value is advertised in the router's Hello
                         Packets.  It must be the same for all routers 
                         attached to a common network.  The smaller the 
                         HelloInterval, the faster topological changes will 
                         be detected, but more OSPF routing protocol traffic
                         will ensue."
                ::= { ospfVLinkEntry 7 }

            ospfVLinkDeadInt OBJECT-TYPE
                SYNTAX  INTEGER (1..2000)
                ACCESS  read-write
                STATUS  mandatory
                DESCRIPTION
                        "After ceasing to hear a router's Hello Packets, the 
                         number of seconds before its neighbors declare the 
                         router down.  This is also advertised in the router's 
                         Hello Packets in their RouterDeadInterval field.  
                         This value again bust be the same for all routers 
                         attached to a common network."
                ::= { ospfVLinkEntry 8 }

            ospfVLinkPassword OBJECT-TYPE
                SYNTAX  DisplayString
                ACCESS  read-write
                STATUS  mandatory
                DESCRIPTION
                        "This configured data allows the authentication 
                         procedure to generate and/or verify the 
                         authentication field in the OSPF header.  This 
                         value again must be the same for all routers 
                         attached to a common network."
                ::= { ospfVLinkEntry 9 }

            -- The ipx filters group
            
            -- This group lets you configure IPX filters.

            ipxfilterNumber OBJECT-TYPE
                SYNTAX  INTEGER
                ACCESS  read-only
                STATUS  mandatory
                DESCRIPTION
                        "The number of IPX filter entries present on this system."
                ::= { ipxfilter 1 }
                
            -- The IPX filters table    
            
            ipxfilterTable OBJECT-TYPE
                SYNTAX  SEQUENCE OF IpxfilterEntry
                ACCESS  not-accessible
                STATUS  mandatory
                DESCRIPTION
                        "A list of IPX filter entries.  The number of entries 
                        is given by the value of ipxfilterNumber."
                ::= { ipxfilter 2 }
            
            ipxfilterEntry OBJECT-TYPE
                SYNTAX  IpxfilterEntry
                ACCESS  not-accessible
                STATUS  mandatory
                DESCRIPTION
                        "This table contains the principal configurable
                        parameters which are used for a particular IP filter
                        entry."
                INDEX   { ipxfilterIndex }
                ::= { ipxfilterTable 1 }
            
            IpxfilterEntry ::=
                SEQUENCE {
                    ipxfilterIndex       INTEGER,
                    ipxfilterEnable      INTEGER,
                    ipxfilterSap         OCTET STRING (SIZE (2)),
                    ipxfilterType        INTEGER
                }
                
            ipxfilterIndex OBJECT-TYPE
                SYNTAX  INTEGER
                ACCESS  read-only
                STATUS  mandatory
                DESCRIPTION
                        "A unique value for each entry.  Its value ranges 
                        between 1 and the value of ipxfilterNumber."
                ::= { ipxfilterEntry 1 }
                
            ipxfilterEnable OBJECT-TYPE
                SYNTAX  INTEGER {
                            disable(1),
                            enable(2)
                        }
                ACCESS  read-write
                STATUS  mandatory
                DESCRIPTION
                        "This variable defines the state of IPX filter (enable or 
                        disable).  If IPX filter parameter is enable, the 
                        unit will filter IPX SAP entries for the SAP given."
                ::= { ipxfilterEntry 2 }
                
            ipxfilterSap OBJECT-TYPE
                SYNTAX  OCTET STRING (SIZE (2)) -- 0x0000 to 0xFFFF
                ACCESS  read-write
                STATUS  mandatory
                DESCRIPTION
                        "This variable defines the SAP value to be filtered."
                ::= { ipxfilterEntry 3 }
                
            ipxfilterType OBJECT-TYPE
                SYNTAX  INTEGER {
                            standard(1),
                            reverse(2)
                        }
                ACCESS  read-write
                STATUS  mandatory
                DESCRIPTION
                        "This variable defines how apply the filter.  If type
                         is standard, the SAP configured is filtered.  If type
                         is reverse, all SAPs except the one configured is 
                         filtered."
                ::= { ipxfilterEntry 4 }
                

            -- The stat group
            
            -- This group is used to see the system statistics, to clear
            -- alarms and to reset all counters.
             
            -- the stat alarms table
            
            statAlarmTable OBJECT-TYPE
                SYNTAX  SEQUENCE OF StatAlarmEntry
                ACCESS  not-accessible
                STATUS  mandatory
                DESCRIPTION
                        "The list of alarms for the system.
                        The number of entries is given by the value 
                        of StatAlarmNumber."
                ::= { stat 1 }
            
            statAlarmEntry OBJECT-TYPE
                SYNTAX  StatAlarmEntry
                ACCESS  not-accessible
                STATUS  mandatory
                DESCRIPTION
                        "This table contains the list of alarms arrived
                        on the system."
                INDEX   { statAlarmIndex }
                ::= { statAlarmTable 1 }
            
            StatAlarmEntry ::=
                SEQUENCE {
                    statAlarmIndex   INTEGER,
                    statAlarmDesc    DisplayString,     
                    statAlarmDate    DisplayString,
                    statAlarmTime    DisplayString,
                    statAlarmModule  INTEGER,
                    statAlarmAlarm   INTEGER,
                    statAlarmArg     INTEGER
                }
                
            statAlarmIndex OBJECT-TYPE
                SYNTAX  INTEGER 
                ACCESS  read-only
                STATUS  mandatory
                DESCRIPTION
                        "A unique value for each alarm.  Its value
                        ranges between 1 and the value of statAlarmNumber."
                ::= { statAlarmEntry 1 }
            
            statAlarmDesc OBJECT-TYPE
                SYNTAX  DisplayString
                ACCESS  read-only
                STATUS  mandatory
                DESCRIPTION
                        "This variable contains a printable octet string
                        which, if available, gives a short description of  
                        the alarm."
                ::= { statAlarmEntry 2 }
            
            statAlarmDate OBJECT-TYPE
                SYNTAX  DisplayString
                ACCESS  read-only
                STATUS  mandatory
                DESCRIPTION
                        "The date of the alarm."
                ::= { statAlarmEntry 3 }
            
            statAlarmTime OBJECT-TYPE
                SYNTAX  DisplayString
                ACCESS  read-only
                STATUS  mandatory
                DESCRIPTION
                        "The time of the alarm."
                ::= { statAlarmEntry 4 }
            
            statAlarmModule OBJECT-TYPE
                SYNTAX  INTEGER 
                ACCESS  read-only
                STATUS  mandatory
                DESCRIPTION
                        "The module who has detected the alarm."
                ::= { statAlarmEntry 5 }
            
            statAlarmAlarm OBJECT-TYPE
                SYNTAX  INTEGER 
                ACCESS  read-only
                STATUS  mandatory
                DESCRIPTION
                        "The name of the alarm."
                ::= { statAlarmEntry 6 }
            
            statAlarmArg OBJECT-TYPE
                SYNTAX  INTEGER 
                ACCESS  read-only
                STATUS  mandatory
                DESCRIPTION
                        "An argument permitting to detect the reason
                        of the alarm"
                ::= { statAlarmEntry 7 }
            
            -- the Stat interfaces wan table
            
            statIfwanTable OBJECT-TYPE
                SYNTAX  SEQUENCE OF StatIfwanEntry
                ACCESS  not-accessible
                STATUS  mandatory
                DESCRIPTION
                        "A list of statistic entries for the wan
                        interfaces.  The number of entries is given 
                        by the value of ifwanNumber."
                ::= { stat 2 }
            
            statIfwanEntry OBJECT-TYPE
                SYNTAX  StatIfwanEntry
                ACCESS  not-accessible
                STATUS  mandatory
                DESCRIPTION
                        "This table contains the principal statistics
                        for the wan interfaces."
                INDEX   { statIfwanIndex }
                ::= { statIfwanTable 1 }
            
            StatIfwanEntry ::=
                SEQUENCE {
                    statIfwanIndex          INTEGER,
                    statIfwanDesc           DisplayString,
                    statIfwanProtocol       INTEGER,
                    statIfwanInterface      DisplayString,
                    statIfwanModemSignal    DisplayString,
                    statIfwanSpeed          INTEGER,
                    statIfwanState          DisplayString,
                    statIfwanDropInsert     DisplayString,
                    statIfwanTrspState      DisplayString,
                    statIfwanTrspLastError  DisplayString,
                    statIfwanMeanTx         Gauge,
                    statIfwanMeanRx         Gauge,
                    statIfwanPeakTx         Gauge,
                    statIfwanPeakRx         Gauge,
                    statIfwanBadFrames      Counter,
                    statIfwanBadFlags       DisplayString,
                    statIfwanUnderruns      Counter,
                    statIfwanRetries        Counter,
                    statIfwanRestart        Counter,
                    statIfwanFramesTx       Counter,
                    statIfwanFramesRx       Counter,
                    statIfwanOctetsTx       Counter,
                    statIfwanOctetsRx       Counter,
                    statIfwanOvrFrames      Counter,
                    statIfwanBadOctets      Counter,
                    statIfwanOvrOctets      Counter,
                    statIfwanCompErrs       Counter,
                    statIfwanChOverflows    Counter,
                    statIfwanChAborts       Counter,
                    statIfwanChSeqErrs      Counter,
                    statIfwanT1E1ESS        Counter,
                    statIfwanT1E1SES        Counter,
                    statIfwanT1E1SEF        Counter,
                    statIfwanT1E1UAS        Counter,
                    statIfwanT1E1CSS        Counter,
                    statIfwanT1E1PCV        Counter,
                    statIfwanT1E1LES        Counter,
                    statIfwanT1E1BES        Counter,
                    statIfwanT1E1DM         Counter,
                    statIfwanT1E1LCV        Counter,
                    statIfwanQ922State      DisplayString
                }
                
            statIfwanIndex OBJECT-TYPE
                SYNTAX  INTEGER
                ACCESS  read-only
                STATUS  mandatory                                     
                DESCRIPTION
                        "A unique value for each interface."
                ::= { statIfwanEntry 1 }    
                
            statIfwanDesc OBJECT-TYPE
                SYNTAX  DisplayString
                ACCESS  read-only
                STATUS  mandatory
                DESCRIPTION
                        "A textual string containing information about 
                        a specific interface."
                ::= { statIfwanEntry 2 }
            
            statIfwanProtocol OBJECT-TYPE
                SYNTAX  INTEGER {   
                            off(1),
                            p-sdlc(2),
                            s-sdlc(3),
                            hdlc(4),
                            ddcmp(5),
                            t-async(6),
                            r-async(7),
                            bsc(8),
                            cop(9),
                            pvcr(10),
                            passthru(11),
                            console(12),
                            fr-net(17),
                            fr-user(18),
                            ppp(19),
                            e1-trsp(24),        --  Configuration for match the old config MIB.
                            isdn-bri(27),       --  Configuration not supported in CFG.
                            g703(28),
                            x25(29),
                            not-applicable(254),
                            not-available(255)
                        }
                ACCESS  read-only
                STATUS  mandatory
                DESCRIPTION
                        "The operating mode of the wan interface."
                ::= { statIfwanEntry 3 }
            
            statIfwanInterface OBJECT-TYPE
                SYNTAX  DisplayString
                ACCESS  read-only
                STATUS  mandatory
                DESCRIPTION
                        "The actual interface used on the port."
                ::= { statIfwanEntry 4 }
            
            statIfwanModemSignal OBJECT-TYPE
                SYNTAX  DisplayString
                ACCESS  read-only
                STATUS  mandatory
                DESCRIPTION
                        "This variable contains the modem signal status."
                ::= { statIfwanEntry 5 }
            
            statIfwanSpeed OBJECT-TYPE
                SYNTAX  INTEGER 
                ACCESS  read-only
                STATUS  mandatory
                DESCRIPTION
                        "This variable contains the speed measured by the
                        system."
                ::= { statIfwanEntry 6 }
            
            statIfwanState OBJECT-TYPE
                SYNTAX  DisplayString
                ACCESS  read-only
                STATUS  mandatory
                DESCRIPTION
                        "This variable contains the status of the port."
                ::= { statIfwanEntry 7 }
            
            statIfwanMeanTx OBJECT-TYPE
                SYNTAX  Gauge
                ACCESS  read-only
                STATUS  mandatory
                DESCRIPTION
                        "This variable contains the average line usage for
                        transmissions on the wan port."
                ::= { statIfwanEntry 8 }
            
            statIfwanMeanRx OBJECT-TYPE
                SYNTAX  Gauge
                ACCESS  read-only
                STATUS  mandatory
                DESCRIPTION
                        "This variable contains the average line usage for 
                        data received on the wan port."
                ::= { statIfwanEntry 9 }
            
            statIfwanPeakTx OBJECT-TYPE
                SYNTAX  Gauge
                ACCESS  read-only
                STATUS  mandatory
                DESCRIPTION
                        "This variable contains the maximum line usage for
                        transmissions on the wan port."
                ::= { statIfwanEntry 10 }
            
            statIfwanPeakRx OBJECT-TYPE
                SYNTAX  Gauge
                ACCESS  read-only
                STATUS  mandatory
                DESCRIPTION
                        "This variable contains the maximum line usage for
                        data received on the wan port."
                ::= { statIfwanEntry 11 }
            
            statIfwanBadFrames OBJECT-TYPE
                SYNTAX  Counter
                ACCESS  read-only
                STATUS  mandatory
                DESCRIPTION
                        "The number of bad frames received."
                ::= { statIfwanEntry 12 }
            
            statIfwanBadFlags OBJECT-TYPE
                SYNTAX  DisplayString
                ACCESS  read-only
                STATUS  mandatory
                DESCRIPTION
                        "These flags are to find the reason of bad frames
                        received.
                         
                           U : Bad length
                           Q : Overflow
                           F : Flush
                           S : Overrun
                           B : Bad CRC
                           A : Abort"

                ::= { statIfwanEntry 13 }
            
            statIfwanUnderruns OBJECT-TYPE
                SYNTAX  Counter
                ACCESS  read-only
                STATUS  mandatory
                DESCRIPTION
                        "The number of underruns."
                ::= { statIfwanEntry 14 }
            
            statIfwanRetries OBJECT-TYPE
                SYNTAX  Counter
                ACCESS  read-only
                STATUS  mandatory
                DESCRIPTION
                        "The number of retries is incremented when there 
                        is a retransmission between the system and the 
                        controller or host."
                ::= { statIfwanEntry 15 }
            
            statIfwanRestart OBJECT-TYPE
                SYNTAX  Counter
                ACCESS  read-only
                STATUS  mandatory
                DESCRIPTION
                        "The number of restarts.  For a user port this 
                        counter is incremented every time an error on the 
                        link caused the port to restart.  These errors 
                        occur over the link, not between equipment.  The 
                        number of restarts is not calculated for user ports 
                        in P-SDLC or S-SDLC."
                ::= { statIfwanEntry 16 }
            
            statIfwanFramesTx OBJECT-TYPE
                SYNTAX  Counter
                ACCESS  read-only
                STATUS  mandatory
                DESCRIPTION
                        "The number of frames transmitted"
                ::= { statIfwanEntry 17 }
            
            statIfwanFramesRx OBJECT-TYPE
                SYNTAX  Counter
                ACCESS  read-only
                STATUS  mandatory
                DESCRIPTION
                        "The number of frames received"
                ::= { statIfwanEntry 18 }
            
            statIfwanOctetsTx OBJECT-TYPE
                SYNTAX  Counter
                ACCESS  read-only
                STATUS  mandatory
                DESCRIPTION
                        "The number of octets transmitted"
                ::= { statIfwanEntry 19 }
            
            statIfwanOctetsRx OBJECT-TYPE
                SYNTAX  Counter
                ACCESS  read-only
                STATUS  mandatory
                DESCRIPTION
                        "The number of octets received"
                ::= { statIfwanEntry 20 }
            
            statIfwanOvrFrames OBJECT-TYPE
                SYNTAX  Counter
                ACCESS  read-only
                STATUS  mandatory
                DESCRIPTION
                        "The number of frames received and deleted 
                        because the input queue is full."                        
                ::= { statIfwanEntry 21 }
            
            statIfwanBadOctets OBJECT-TYPE
                SYNTAX  Counter
                ACCESS  read-only
                STATUS  mandatory
                DESCRIPTION
                        "The number of characters received and deleted 
                        because of a bad frame."  
                ::= { statIfwanEntry 22 }
            
            statIfwanOvrOctets OBJECT-TYPE
                SYNTAX  Counter
                ACCESS  read-only
                STATUS  mandatory
                DESCRIPTION
                        "The number of characters received and deleted 
                        because the input queue is full."
                ::= { statIfwanEntry 23 }
            
            statIfwanT1E1ESS OBJECT-TYPE
                SYNTAX  Counter
                ACCESS  read-only
                STATUS  mandatory
                DESCRIPTION
                        "The number of ESS"
                ::= { statIfwanEntry 24 }
            
            statIfwanT1E1SES OBJECT-TYPE
                SYNTAX  Counter
                ACCESS  read-only
                STATUS  mandatory
                DESCRIPTION
                        "The number of SES"
                ::= { statIfwanEntry 25 }
            
            statIfwanT1E1SEF OBJECT-TYPE
                SYNTAX  Counter
                ACCESS  read-only
                STATUS  mandatory
                DESCRIPTION
                        "The number of SEF"
                ::= { statIfwanEntry 26 }
            
            statIfwanT1E1UAS OBJECT-TYPE
                SYNTAX  Counter
                ACCESS  read-only
                STATUS  mandatory
                DESCRIPTION
                        "+The number of UAS"
                ::= { statIfwanEntry 27 }
            
            statIfwanT1E1CSS OBJECT-TYPE
                SYNTAX  Counter
                ACCESS  read-only
                STATUS  mandatory
                DESCRIPTION
                        "The number of CSS"
                ::= { statIfwanEntry 28 }
            
            statIfwanT1E1PCV OBJECT-TYPE
                SYNTAX  Counter
                ACCESS  read-only
                STATUS  mandatory
                DESCRIPTION
                        "The number of PCV"
                ::= { statIfwanEntry 29 }
            
            statIfwanT1E1LES OBJECT-TYPE
                SYNTAX  Counter
                ACCESS  read-only
                STATUS  mandatory
                DESCRIPTION
                        "The number of LES"
                ::= { statIfwanEntry 30 }
            
            statIfwanT1E1BES OBJECT-TYPE
                SYNTAX  Counter
                ACCESS  read-only
                STATUS  mandatory
                DESCRIPTION
                        "The number of BES"
                ::= { statIfwanEntry 31 }
            
            statIfwanT1E1DM OBJECT-TYPE
                SYNTAX  Counter
                ACCESS  read-only
                STATUS  mandatory
                DESCRIPTION
                        "The number of DM"
                ::= { statIfwanEntry 32 }
            
            statIfwanT1E1LCV OBJECT-TYPE
                SYNTAX  Counter
                ACCESS  read-only
                STATUS  mandatory
                DESCRIPTION
                        "The number of LCV"
                ::= { statIfwanEntry 33 }
            
            statIfwanCompErrs OBJECT-TYPE
                SYNTAX  Counter
                ACCESS  read-only
                STATUS  mandatory
                DESCRIPTION
                        "The number of compression errors"
                ::= { statIfwanEntry 34 }
                 
            statIfwanChOverflows OBJECT-TYPE
                SYNTAX  Counter
                ACCESS  read-only
                STATUS  mandatory
                DESCRIPTION
                        "The number of channel overflows"
                ::=  { statIfwanEntry 35 }
                
            statIfwanChAborts OBJECT-TYPE
                SYNTAX  Counter
                ACCESS  read-only
                STATUS  mandatory
                DESCRIPTION
                        "The number of frames aborted received"
                ::=  { statIfwanEntry 36 }
                
            statIfwanChSeqErrs OBJECT-TYPE
                SYNTAX  Counter
                ACCESS  read-only
                STATUS  mandatory
                DESCRIPTION
                        "The number of frames reception failure due
                         to at least one missing block"
                ::=  { statIfwanEntry 37 }

            statIfwanDropInsert OBJECT-TYPE
                SYNTAX  DisplayString
                ACCESS  read-only
                STATUS  mandatory
                DESCRIPTION
                        "Drop and Insert status."
                ::= { statIfwanEntry 38 }

            statIfwanTrspState OBJECT-TYPE
                SYNTAX  DisplayString
                ACCESS  read-only
                STATUS  mandatory
                DESCRIPTION
                        "Indicates the current logical state of the port."
                ::= { statIfwanEntry 39 }

            statIfwanTrspLastError OBJECT-TYPE
                SYNTAX  DisplayString
                ACCESS  read-only
                STATUS  mandatory
                DESCRIPTION
                        "The last error occurred for this port."
                ::= { statIfwanEntry 40 }
                
            statIfwanQ922State OBJECT-TYPE
                SYNTAX  DisplayString
                ACCESS  read-only
                STATUS  mandatory
                DESCRIPTION
                        "Q922 state of the port if SVC's are enabled.
                         Only on FR-USER ports."
                ::= { statIfwanEntry 41 }
            
            StatIfwanStates ::=
                SEQUENCE {
                    statIfwanIndex          INTEGER,
                    statIfwanDesc           DisplayString,
                    statIfwanProtocol       INTEGER,
                    statIfwanInterface      DisplayString,
                    statIfwanModemSignal    DisplayString,
                    statIfwanSpeed          INTEGER,
                    statIfwanState          DisplayString,
                    statIfwanDropInsert     DisplayString,
                    statIfwanTrspState      DisplayString,
                    statIfwanTrspLastError  DisplayString,
                    statIfwanQ922State      DisplayString
                }
                
            StatIfwanCounters ::=
                SEQUENCE {
                    statIfwanIndex          INTEGER,
                    statIfwanDesc           DisplayString,
                    statIfwanProtocol       INTEGER,
                    statIfwanMeanTx         Gauge,
                    statIfwanMeanRx         Gauge,
                    statIfwanPeakTx         Gauge,
                    statIfwanPeakRx         Gauge,
                    statIfwanFramesTx       Counter,
                    statIfwanFramesRx       Counter,
                    statIfwanOctetsTx       Counter,
                    statIfwanOctetsRx       Counter
                }
                
            StatIfwanErrors ::=
                SEQUENCE {
                    statIfwanIndex          INTEGER,
                    statIfwanDesc           DisplayString,
                    statIfwanProtocol       INTEGER,
                    statIfwanBadFrames      Counter,
                    statIfwanBadFlags       DisplayString,
                    statIfwanUnderruns      Counter,
                    statIfwanRetries        Counter,
                    statIfwanRestart        Counter,
                    statIfwanOvrFrames      Counter,
                    statIfwanBadOctets      Counter,
                    statIfwanOvrOctets      Counter,
                    statIfwanCompErrs       Counter,
                    statIfwanChOverflows    Counter,
                    statIfwanChAborts       Counter,
                    statIfwanChSeqErrs      Counter,
                    statIfwanT1E1ESS        Counter,
                    statIfwanT1E1SES        Counter,
                    statIfwanT1E1SEF        Counter,
                    statIfwanT1E1UAS        Counter,
                    statIfwanT1E1CSS        Counter,
                    statIfwanT1E1PCV        Counter,
                    statIfwanT1E1LES        Counter,
                    statIfwanT1E1BES        Counter,
                    statIfwanT1E1DM         Counter,
                    statIfwanT1E1LCV        Counter
                }
                
            -- the Stat interfaces lan table
            
            statIflanTable OBJECT-TYPE
                SYNTAX  SEQUENCE OF StatIflanEntry
                ACCESS  not-accessible
                STATUS  mandatory
                DESCRIPTION
                        "A list of statistic entries for the lan
                        interfaces.  The number of entries is given 
                        by the value of iflanNumber."
                ::= { stat 3 }
            
            statIflanEntry OBJECT-TYPE
                SYNTAX  StatIflanEntry
                ACCESS  not-accessible
                STATUS  mandatory
                DESCRIPTION
                        "This table contains the principal statistics
                        for the lan interfaces."
                INDEX   { statIflanIndex }
                ::= { statIflanTable 1 }
            
            StatIflanEntry ::=
                SEQUENCE {
                    statIflanIndex                   INTEGER,
                    statIflanProtocol                INTEGER,
                    statIflanSpeed                   INTEGER,
                    statIflanConnectionStatus        DisplayString,
                    statIflanOperatingMode           DisplayString,
                    statIflanEth-Interface           DisplayString,
                    statIflanMeanTx-kbps             Gauge,
                    statIflanMeanRx-kbps             Gauge,
                    statIflanPeakTx-kbps             Gauge,
                    statIflanPeakRx-kbps             Gauge,
                    statIflanRetries                 Counter,
                    statIflanBadFrames               Counter,
                    statIflanBadFlags                DisplayString,
                    statIflanTr-ReceiveCongestion    Counter,
                    statIflanEth-OneCollision        Counter,
                    statIflanEth-TwoCollisions       Counter,
                    statIflanEth-ThreeAndMoreCol     Counter,
                    statIflanEth-DeferredTrans       Counter,
                    statIflanEth-ExcessiveCollision  Counter,
                    statIflanEth-LateCollision       Counter,
                    statIflanEth-FrameCheckSeq       Counter,
                    statIflanEth-Align               Counter,
                    statIflanEth-CarrierSense        Counter
                }
                
            statIflanIndex OBJECT-TYPE
                SYNTAX  INTEGER
                ACCESS  read-only
                STATUS  mandatory
                DESCRIPTION
                        "A unique value for each interface."
                ::= { statIflanEntry 1 }    
                
            statIflanProtocol OBJECT-TYPE
                SYNTAX  INTEGER {
                            off(1),
                            token-ring(13),
                            ethernet-auto(14),
                            ethernet-802p3(15),
                            ethernet-v2(16)
                        }
                ACCESS  read-only
                STATUS  mandatory
                DESCRIPTION
                        "The operating mode of the lan connection."
                ::= { statIflanEntry 2 }
            
            statIflanSpeed OBJECT-TYPE
                SYNTAX  INTEGER {
                            tr-4-Mbps(1),
                            tr-16-Mbps(2),
                            eth-10-Mbps(3)
                        }
                ACCESS  read-only
                STATUS  mandatory
                DESCRIPTION
                        "This variable contains the speed measured by the
                        system."
                ::= { statIflanEntry 3 }
            
            statIflanConnectionStatus OBJECT-TYPE
                SYNTAX  DisplayString
                ACCESS  read-only
                STATUS  mandatory
                DESCRIPTION
                        "The logical connection status of the lan connection."
                ::= { statIflanEntry 4 }
            
            statIflanOperatingMode OBJECT-TYPE
                SYNTAX  DisplayString
                ACCESS  read-only
                STATUS  mandatory
                DESCRIPTION
                        "The operating mode of the lan connection."
                ::= { statIflanEntry 5 }
            
            statIflanEth-Interface OBJECT-TYPE
                SYNTAX  DisplayString
                ACCESS  read-only
                STATUS  mandatory
                DESCRIPTION
                        "The interface used by ethernet."
                ::= { statIflanEntry 6 }
            
            statIflanMeanTx-kbps OBJECT-TYPE
                SYNTAX  Gauge
                ACCESS  read-only
                STATUS  mandatory
                DESCRIPTION
                        "This is the average throughput for transmissions
                        sent to the LAN."
                ::= { statIflanEntry 7 }
            
            statIflanMeanRx-kbps OBJECT-TYPE
                SYNTAX  Gauge
                ACCESS  read-only
                STATUS  mandatory
                DESCRIPTION
                        "This is the average throughput for data received
                        from the LAN."
                ::= { statIflanEntry 8 }
            
            statIflanPeakTx-kbps OBJECT-TYPE
                SYNTAX  Gauge
                ACCESS  read-only
                STATUS  mandatory
                DESCRIPTION
                        "This is the maximum throughput for transmissions
                        sent to the LAN."
                ::= { statIflanEntry 9 }
            
            statIflanPeakRx-kbps OBJECT-TYPE
                SYNTAX  Gauge
                ACCESS  read-only
                STATUS  mandatory
                DESCRIPTION
                        "This is the maximum throughput for data received
                        from the LAN."
                ::= { statIflanEntry 10 }
            
            statIflanRetries OBJECT-TYPE
                SYNTAX  Counter
                ACCESS  read-only
                STATUS  mandatory
                DESCRIPTION
                        "The number of retries is incremented when there 
                        is a retransmission between the system and the 
                        controller or host."
                ::= { statIflanEntry 11 }
            
            statIflanBadFrames OBJECT-TYPE
                SYNTAX  Counter
                ACCESS  read-only
                STATUS  mandatory
                DESCRIPTION
                        "The number of bad frames received."
                ::= { statIflanEntry 12 }
            
            statIflanBadFlags OBJECT-TYPE
                SYNTAX  DisplayString
                ACCESS  read-only
                STATUS  mandatory
                DESCRIPTION
                        "These flags are to find the reason of bad frames
                        received.
                         
                           U : Bad length
                           Q : Overflow
                           F : Flush
                           S : Overrun
                           B : Bad CRC
                           A : Abort"

                ::= { statIflanEntry 13 }
            
            statIflanTr-ReceiveCongestion OBJECT-TYPE
                SYNTAX  Counter
                ACCESS  read-only
                STATUS  mandatory
                DESCRIPTION
                        "This counter contains the number of times 
                        the receiver has overrun.  Token-Ring only."
                ::= { statIflanEntry 14 }
            
            statIflanEth-OneCollision OBJECT-TYPE
                SYNTAX  Counter
                ACCESS  read-only
                STATUS  mandatory
                DESCRIPTION
                        "The number of one collision."
                ::= { statIflanEntry 15 }
            
            statIflanEth-TwoCollisions OBJECT-TYPE
                SYNTAX  Counter
                ACCESS  read-only
                STATUS  mandatory
                DESCRIPTION
                        "The number of two collisions."
                ::= { statIflanEntry 16 }
            
            statIflanEth-ThreeAndMoreCol OBJECT-TYPE
                SYNTAX  Counter
                ACCESS  read-only
                STATUS  mandatory
                DESCRIPTION
                        "The number of three and more collisions."
                ::= { statIflanEntry 17 }
            
            statIflanEth-DeferredTrans OBJECT-TYPE
                SYNTAX  Counter
                ACCESS  read-only
                STATUS  mandatory
                DESCRIPTION
                        "This counter contains the Number of frames deferred
                        before transmission."
                ::= { statIflanEntry 18 }
            
            statIflanEth-ExcessiveCollision OBJECT-TYPE
                SYNTAX  Counter
                ACCESS  read-only
                STATUS  mandatory
                DESCRIPTION
                        "Excessive collisions.  This counter displays the 
                        number of frames aborted during transmission due 
                        to an excessive number of collisions.  These are 
                        frames that have not been transmitted successfully."
                ::= { statIflanEntry 19 }
            
            statIflanEth-LateCollision OBJECT-TYPE
                SYNTAX  Counter
                ACCESS  read-only
                STATUS  mandatory
                DESCRIPTION
                        "Late collisions.  This counter displays the number 
                        of transmit frames with late collision, that is, the 
                        number of times that a collision was detected later 
                        than 512 bits into the transmitted packet."
                ::= { statIflanEntry 20 }
            
            statIflanEth-FrameCheckSeq OBJECT-TYPE
                SYNTAX  Counter
                ACCESS  read-only
                STATUS  mandatory
                DESCRIPTION
                        "Frame check sequence errors.  This counter displays 
                        the number of frames received on the Ethernet port 
                        with FCS errors."
                ::= { statIflanEntry 21 }
            
            statIflanEth-Align OBJECT-TYPE
                SYNTAX  Counter
                ACCESS  read-only
                STATUS  mandatory
                DESCRIPTION
                        "Alignment errors.  This counter displays the number 
                        of incomplete frames received on the Ethernet port 
                        that do not pass the CRC check."
                ::= { statIflanEntry 22 }
            
            statIflanEth-CarrierSense OBJECT-TYPE
                SYNTAX  Counter
                ACCESS  read-only
                STATUS  mandatory
                DESCRIPTION
                        "Carrier sense errors.  This counter indicates the 
                        number of frames transmitted with carrier sense 
                        errors:  either the carrier sense signal from the 
                        physical layer interface was not asserted, or it was 
                        unasserted during transmission of the frame without
                        collision."
                ::= { statIflanEntry 23 }
            
            StatIflanEth ::=
                SEQUENCE {
                    statIflanIndex                   INTEGER,
                    statIflanProtocol                INTEGER,
                    statIflanSpeed                   INTEGER,
                    statIflanConnectionStatus        DisplayString,
                    statIflanOperatingMode           DisplayString,
                    statIflanEth-Interface           DisplayString,
                    statIflanMeanTx-kbps             Gauge,
                    statIflanMeanRx-kbps             Gauge,
                    statIflanPeakTx-kbps             Gauge,
                    statIflanPeakRx-kbps             Gauge,
                    statIflanRetries                 Counter,
                    statIflanBadFrames               Counter,
                    statIflanBadFlags                DisplayString,
                    statIflanEth-OneCollision        Counter,
                    statIflanEth-TwoCollisions       Counter,
                    statIflanEth-ThreeAndMoreCol     Counter,
                    statIflanEth-DeferredTrans       Counter,
                    statIflanEth-ExcessiveCollision  Counter,
                    statIflanEth-LateCollision       Counter,
                    statIflanEth-FrameCheckSeq       Counter,
                    statIflanEth-Align               Counter,
                    statIflanEth-CarrierSense        Counter
                }
                
            StatIflanTr ::=
                SEQUENCE {
                    statIflanIndex                   INTEGER,
                    statIflanProtocol                INTEGER,
                    statIflanSpeed                   INTEGER,
                    statIflanConnectionStatus        DisplayString,
                    statIflanOperatingMode           DisplayString,
                    statIflanMeanTx-kbps             Gauge,
                    statIflanMeanRx-kbps             Gauge,
                    statIflanPeakTx-kbps             Gauge,
                    statIflanPeakRx-kbps             Gauge,
                    statIflanRetries                 Counter,
                    statIflanBadFrames               Counter,
                    statIflanBadFlags                DisplayString,
                    statIflanTr-ReceiveCongestion    Counter
                }
            
            -- The statIfVce group
            
            --  This group is used to see the voice specific statistics,
            --  to clear alarms and to reset all counters of a voice unit.
            
            -- the Stat interfaces voice table

            statIfvceTable OBJECT-TYPE
                SYNTAX  SEQUENCE OF StatIfvceEntry
                ACCESS  not-accessible
                STATUS  mandatory
                DESCRIPTION
                        "A list of statistic entries for the voice
                        interfaces.  The number of entries is given 
                        by the value of ifNumber."
                ::= { stat 10 }
            
            statIfvceEntry OBJECT-TYPE
                SYNTAX  StatIfvceEntry
                ACCESS  not-accessible
                STATUS  mandatory
                DESCRIPTION
                        "This table contains the principal statistics
                        for the voice interfaces."
                INDEX   { statIfvceIndex }
                ::= { statIfvceTable 1 }
            
            StatIfvceEntry ::=
                SEQUENCE {
                    statIfvceIndex          INTEGER,
                    statIfvceDesc           DisplayString,
                    statIfvceState          INTEGER,
                    statIfvceProtocol       INTEGER,
                    statIfvceLastError      INTEGER,
                    statIfvceFaxRate        INTEGER,
                    statIfvceFaxMode        INTEGER,
                    statIfvceOverruns       Counter,
                    statIfvceUnderruns      Counter,
                    statIfvceDvcPortInUse   DisplayString
                }
                
            statIfvceIndex OBJECT-TYPE
                SYNTAX  INTEGER
                ACCESS  read-only
                STATUS  mandatory
                DESCRIPTION
                        "A unique value for each interface: the same value as the ifIndex in RFC1213 that
                         refers to this voice port"
                ::= { statIfvceEntry 1 }    
                
            statIfvceDesc OBJECT-TYPE
                SYNTAX  DisplayString
                ACCESS  read-only
                STATUS  mandatory
                DESCRIPTION
                        "A textual string containing information about 
                        a specific interface."
                ::= { statIfvceEntry 2 }
            
            statIfvceState OBJECT-TYPE
                SYNTAX  INTEGER {
                            inactive(0),
                            idle(1),
                            pause(2),
                            local(3),
                            online(4),
                            disconnect(5)
                            }
                ACCESS  read-only
                STATUS  mandatory
                DESCRIPTION
                        "Indicates the current logical state of the port."
                ::= { statIfvceEntry 3 }
            
            statIfvceProtocol OBJECT-TYPE
                SYNTAX  INTEGER {
                            off(1),
                            acelp-8-kbs(21),
                            acelp-4-8-kbs(22),
                            pcm64k(23),
                            adpcm32k(24),
                            atc16k(26),
                            acelp-cn(30)
                        }
                ACCESS  read-only
                STATUS  mandatory
                DESCRIPTION
                        "Indicates the current protocol setting the port."
                ::= { statIfvceEntry 4 }

            statIfvceLastError OBJECT-TYPE
                SYNTAX  INTEGER {
                            none(0),
                            incompatibility(1),
                            new-parameters(2),
                            rerouting(3),   
                            state-fault(4),
                            unreachable(5),
                            disconnect(6), 
                            port-closure(7),
                            no-destination(8),
                            pvc-closure(9),
                            too-many-calls(10),
                            class-mismatch(11),
                            algo-mismatch(12)
                            }
                ACCESS  read-only
                STATUS  mandatory
                DESCRIPTION
                        "The last error occurred for this port."
                ::= { statIfvceEntry 5 }
            
            statIfvceFaxRate OBJECT-TYPE
                SYNTAX  INTEGER {
                            none(0),                            
                            fx-2-4Kbps(1),
                            fx-4-8Kbps(2),
                            fx-7-2Kbps(3),
                            fx-9-6Kbps(4)
                        }
                ACCESS  read-only
                STATUS  mandatory
                DESCRIPTION
                        "Indicates the current voice compression rate. 
                         The possible rates are 4.8 Kbps and 8 Kbps."
                ::= { statIfvceEntry 6 }
            
            statIfvceFaxMode OBJECT-TYPE
                SYNTAX  INTEGER {           
                            none(255),       
                            out-of-fax(0),
                            in-fax(1)
                        }
                ACCESS  read-only
                STATUS  mandatory
                DESCRIPTION
                        "Indicates the current voice compression rate. 
                         The possible rates are 4.8 Kbps and 8 Kbps."
                ::= { statIfvceEntry 7 }
            
            statIfvceOverruns OBJECT-TYPE
                SYNTAX  Counter
                ACCESS  read-only
                STATUS  mandatory
                DESCRIPTION
                        "The number of receive overruns that have occurred. "
                ::= { statIfvceEntry 8 }
            
            statIfvceUnderruns OBJECT-TYPE
                SYNTAX  Counter
                ACCESS  read-only
                STATUS  mandatory
                DESCRIPTION
                        "The number of transmit underruns that have occurred."
                ::= { statIfvceEntry 9 }

            statIfvceDvcPortInUse OBJECT-TYPE
                SYNTAX  DisplayString
                ACCESS  read-only
                STATUS  mandatory
                DESCRIPTION
                        "Indicates the logical port number that is being used by an
                         active voice connection. For CCS protocols such as QSIG,
                         the E1/CCS card selects which DSP on which DVC card it will
                         use for a connection. The logical port number corresponding
                         to the DSP is reported to the cleartrac baseboard, and
                         comprises the value of the DVC Port In Use statistic.
                         For slot 1 of the DVC card the possible values are 100 to 106, 
                         for slot 2 they are 200 to 206, and so on."
                ::= { statIfvceEntry 10 }

            -- the Stat Voice log table
            --  These statistics will probably not be supporeted via SNMP:
            --  the official way it to ftp them up
            
            -- the Stat PUs table
            
            statPuTable OBJECT-TYPE
                SYNTAX  SEQUENCE OF StatPuEntry
                ACCESS  not-accessible
                STATUS  mandatory
                DESCRIPTION
                        "A list of statistic entries for the PUs.
                        The number of entries is given by the value 
                        of puNumber."
                ::= { stat 4 }
            
            statPuEntry OBJECT-TYPE
                SYNTAX  StatPuEntry
                ACCESS  not-accessible
                STATUS  mandatory
                DESCRIPTION
                        "This table contains the principal statistics
                        for the PUs."
                INDEX   { statPuIndex }
                ::= { statPuTable 1 }
            
            StatPuEntry ::=
                SEQUENCE {
                    statPuIndex             INTEGER,
                    statPuMode              INTEGER,
                    statPuConnectionStatus  DisplayString,
                    statPuCompErrs          Counter,
                    statPuChOverflows       Counter,
                    statPuChAborts          Counter,
                    statPuChSeqErrs         Counter
                }
                
            statPuIndex OBJECT-TYPE
                SYNTAX  INTEGER
                ACCESS  read-only
                STATUS  mandatory
                DESCRIPTION
                        "A unique value for each PU.  Its value ranges
                        between 1 and the value of PuNumber."
                ::= { statPuEntry 1 }   
                
            statPuMode OBJECT-TYPE
                SYNTAX  INTEGER {
                            off(1),
                            sdlc-llc(2),
                            sdlc-sdlc(3),
                            sdlc-dlsw(4),
                            sdlc-links(5),
                            llc-dlsw(6),
                            llc-links(7),
                            dlsw-links(8),
                            sdlc-ban(9),
                            sdlc-bnn(10),
                            llc-ban(11),
                            llc-bnn(12),
                            dlsw-ban(13),
                            dlsw-bnn(14),
                            ban-link(15),
                            bnn-link(16)
                        }
                ACCESS  read-only
                STATUS  mandatory
                DESCRIPTION
                        "The PU operating mode."
                ::= { statPuEntry 2 }
            
            statPuConnectionStatus OBJECT-TYPE
                SYNTAX  DisplayString
                ACCESS  read-only
                STATUS  mandatory
                DESCRIPTION
                        "This variable contains the status of the connection
                        as a whole."
                ::= { statPuEntry 3 }
                
            statPuCompErrs OBJECT-TYPE
                SYNTAX  Counter
                ACCESS  read-only
                STATUS  mandatory
                DESCRIPTION
                        "The number of compression errors"
                ::= { statPuEntry 4 }
                 
            statPuChOverflows OBJECT-TYPE
                SYNTAX  Counter
                ACCESS  read-only
                STATUS  mandatory
                DESCRIPTION
                        "The number of channel overflows"
                ::=  { statPuEntry 5 }
                
            statPuChAborts OBJECT-TYPE
                SYNTAX  Counter
                ACCESS  read-only
                STATUS  mandatory
                DESCRIPTION
                        "The number of frames aborted received"
                ::=  { statPuEntry 6 }
                
            statPuChSeqErrs OBJECT-TYPE
                SYNTAX  Counter
                ACCESS  read-only
                STATUS  mandatory
                DESCRIPTION
                        "The number of frames reception failure due
                         to at least one missing block"
                ::=  { statPuEntry 7 }
                
                        
            -- the Stat bridge
            
            statBridge           OBJECT IDENTIFIER ::= { stat 5 }
            
            statBridgeBridge     OBJECT IDENTIFIER ::= { statBridge 1 }
            statBridgePort       OBJECT IDENTIFIER ::= { statBridge 2 }
            
            statBridgeBridgeAddressDiscard OBJECT-TYPE
                SYNTAX  DisplayString
                ACCESS  read-only
                STATUS  mandatory
                DESCRIPTION
                        "This counter indicates the number of times that an 
                        address entry in the filtering database has been 
                        removed to make room for a new address.  If this 
                        counter increases rapidly, the filtering database is 
                        too small for the number of addresses (stations) in 
                        the network."
                ::= { statBridgeBridge 1 }
            
            statBridgeBridgeFrameDiscard OBJECT-TYPE
                SYNTAX  DisplayString
                ACCESS  read-only
                STATUS  mandatory
                DESCRIPTION
                        "This counter indicates the number of times that a
                         frame has not been bridged because its destination
                         is local."
                ::= { statBridgeBridge 2 }
            
            statBridgeBridgeDesignatedRoot OBJECT-TYPE
                SYNTAX  DisplayString
                ACCESS  read-only
                STATUS  mandatory
                DESCRIPTION
                        "Identifier of the designated root bridge.  This 
                        is an 8 byte hexadecimal label composed of the 
                        bridge priority level (the first 2 bytes) and the 
                        address of the adapter connecting the bridge to 
                        the LAN segment with the lowest LAN segment number.
                        The root bridge has the lowest bridge identifier of 
                        all bridges in the network, and is at the top of the 
                        spanning tree.  It is also the bridge that sends the 
                        'HELLO' message to detect when other bridges enter 
                        and leave the network. The root bridge usually 
                        carries the greatest amount of traffic, since it 
                        connects the two halves of the network together."
                ::= { statBridgeBridge 3 }
            
            statBridgeBridgeRootCost OBJECT-TYPE
                SYNTAX  DisplayString
                ACCESS  read-only
                STATUS  mandatory
                DESCRIPTION
                        "From each unit there are potentially many different 
                        paths to the root bridge.  The root cost is the 
                        lowest path cost, that is, the shortest relative 
                        path length to the root bridge.  When the root cost 
                        is displayed as zero (0), either this unit is the root
                        bridge or there is no direct path from this unit to 
                        the root bridge."
                ::= { statBridgeBridge 4 }
            
            statBridgeBridgeRootPort OBJECT-TYPE
                SYNTAX  DisplayString
                ACCESS  read-only
                STATUS  mandatory
                DESCRIPTION
                        "The root port is the port with the root cost.  In 
                        other words, it is the port in the direction of the 
                        least path cost to the root bridge.  The root port 
                        is identified by the attached equipment:  LAN, 
                        Group 1 (GR1) to Group 4 (GR4).  NONE indicates that 
                        this unit is the root bridge."
                ::= { statBridgeBridge 5 }
            
            statBridgeBridgeFrameFiltered OBJECT-TYPE
                SYNTAX  DisplayString
                ACCESS  read-only
                STATUS  mandatory
                DESCRIPTION
                        "This counter indicates the number of frames that are
                        not forwarded because a filter configured on the unit."
                ::= { statBridgeBridge 6 }
            
            statBridgeBridgeFrameTimeout OBJECT-TYPE
                SYNTAX  DisplayString
                ACCESS  read-only
                STATUS  mandatory
                DESCRIPTION
                        "Number of frames discarded because the transit 
                        delay for this frame has been reached."
                ::= { statBridgeBridge 7 }
            
            statBridgePortTable OBJECT-TYPE
                SYNTAX  SEQUENCE OF StatBridgePortEntry
                ACCESS  not-accessible
                STATUS  mandatory
                DESCRIPTION
                        "A list of statistic entries for the BridgePort."
                ::= { statBridgePort 1 }

            statBridgePortEntry OBJECT-TYPE
                SYNTAX  StatBridgePortEntry
                ACCESS  not-accessible
                STATUS  mandatory
                DESCRIPTION
                        "This table contains the principal statistics for 
                        the BridgePort."
                INDEX   { statBridgePortIndex }
                ::= { statBridgePortTable 1 }
            
            StatBridgePortEntry ::=
                SEQUENCE {
                    statBridgePortIndex                  INTEGER,
                    statBridgePortDestination            DisplayString,
                    statBridgePortState                  DisplayString,
                    statBridgePortDesignatedRoot         DisplayString,
                    statBridgePortDesignatedCost         DisplayString,
                    statBridgePortDesignatedBridge       DisplayString,
                    statBridgePortDesignatedPort         DisplayString,
                    statBridgePortTrspFrameIn            DisplayString,
                    statBridgePortTrspFrameOut           DisplayString,
                    statBridgePortTr-SpecRteFrameIn      DisplayString,
                    statBridgePortTr-SpecRteFrameOut     DisplayString,
                    statBridgePortTr-AllRteFrameIn       DisplayString,
                    statBridgePortTr-AllRteFrameOut      DisplayString,
                    statBridgePortTr-SingleRteFrameIn    DisplayString,
                    statBridgePortTr-SingleRteFrameOut   DisplayString,
                    statBridgePortTr-SegmentMismatch     DisplayString,
                    statBridgePortTr-SegmentDuplicate    DisplayString,
                    statBridgePortTr-HopCntExceeded      DisplayString,
                    statBridgePortTr-FrmLngExceeded      DisplayString
                }
                
            statBridgePortIndex OBJECT-TYPE
                SYNTAX  INTEGER
                ACCESS  read-only
                STATUS  mandatory
                DESCRIPTION
                        "A unique value for each port.  Its value ranges
                        between 1 and the value of groupNumber+iflanNumber."
                ::= { statBridgePortEntry 1 }   
                
            statBridgePortDestination OBJECT-TYPE
                SYNTAX  DisplayString
                ACCESS  read-only
                STATUS  mandatory
                DESCRIPTION
                        "Destination of this port. When the bridge port is
                         the LAN, the displayed destination is always LOCAL
                         LAN.  For the other bridge ports the dispayed
                         destination is the name of the attached remote unit."
                ::= { statBridgePortEntry 2 }   
                
            statBridgePortState OBJECT-TYPE
                SYNTAX  DisplayString
                ACCESS  read-only
                STATUS  mandatory
                DESCRIPTION
                        "Current state of the LAN port (or group) in the 
                        bridge topology.  This state can be one of the 
                        following:
                        
                        DISABLED:   Not participating in the bridge topology
                        BLOCKING:   Participation limited to ensuring that 
                                    another bridge forwards frames onto the 
                                    network segment
                        LISTENING:  Participates in the spanning tree 
                                    algorithm
                        LEARNING:   Participates in the spanning tree 
                                    algorithm and builds address tables
                        FORWARD:    Participates in the spanning tree 
                                    algorithm, builds address tables and 
                                    forwards frames"
                ::= { statBridgePortEntry 3 }   
                
            statBridgePortDesignatedRoot OBJECT-TYPE
                SYNTAX  DisplayString
                ACCESS  read-only
                STATUS  mandatory
                DESCRIPTION
                        "Identifier of the designated root for this port, 
                        that is, the bridge that this port considers to be 
                        the root bridge of the network.  The bridge ID is 
                        an 8-byte hexadecimal label composed of the bridge 
                        priority level (the first 2 bytes) and the address 
                        of the adapter connecting the bridge to the LAN 
                        segment (or group) with the lowest number."
                ::= { statBridgePortEntry 4 }
                
            statBridgePortDesignatedCost OBJECT-TYPE
                SYNTAX  DisplayString
                ACCESS  read-only
                STATUS  mandatory
                DESCRIPTION
                        "The cost of the path to the root bridge provided 
                        by the designated port (see DESIGNATED PORT 
                        parameter, below).  The designated port connects to 
                        the same LAN as the port being examined."
                ::= { statBridgePortEntry 5 }
                
            statBridgePortDesignatedBridge OBJECT-TYPE
                SYNTAX  DisplayString
                ACCESS  read-only
                STATUS  mandatory
                DESCRIPTION
                        "Identifier of the designated bridge.  This is an 
                        8-byte hexadecimal label composed of the bridge 
                        priority level (the first 2 bytes) and the address 
                        of the adapter connecting the bridge to the LAN 
                        segment (or group) with the lowest number.  For 
                        each LAN segment (or group), only one bridge is in 
                        the forwarding state at any one time.  This is the 
                        designated bridge for that LAN (or group).  All 
                        other bridges in the network are in the blocking 
                        state, and do not forward frames or build address 
                        tables."
                ::= { statBridgePortEntry 6 }
                
            statBridgePortDesignatedPort OBJECT-TYPE
                SYNTAX  DisplayString
                ACCESS  read-only
                STATUS  mandatory
                DESCRIPTION
                        "The port that is considered the designated port for 
                        this LAN (the LAN to which the port being examined 
                        is connected).  All LAN data is sent via this port 
                        to the root bridge.  The designated port ID is a 
                        2-byte hexadecimal label, where the high byte 
                        indicates the port priority and the low byte 
                        indicates the port number."
                ::= { statBridgePortEntry 7 }
                
            statBridgePortTrspFrameIn OBJECT-TYPE
                SYNTAX  DisplayString
                ACCESS  read-only
                STATUS  mandatory
                DESCRIPTION
                        "Number of frames received on the port for a 
                        transparent bridge."
                ::= { statBridgePortEntry 8 }   
                
            statBridgePortTrspFrameOut OBJECT-TYPE
                SYNTAX  DisplayString
                ACCESS  read-only
                STATUS  mandatory
                DESCRIPTION
                        "Number of frames forwarded from the port for a 
                        transparent bridge."
                ::= { statBridgePortEntry 9 }   
                
            statBridgePortTr-SpecRteFrameIn OBJECT-TYPE
                SYNTAX  DisplayString
                ACCESS  read-only
                STATUS  mandatory
                DESCRIPTION
                        "Number of frames received on the port that contain 
                        a Routing Information field (other than broadcast 
                        frames).  This statistic is displayed for a source 
                        routing bridge only."
                ::= { statBridgePortEntry 10 }   
                
            statBridgePortTr-SpecRteFrameOut OBJECT-TYPE
                SYNTAX  DisplayString
                ACCESS  read-only
                STATUS  mandatory
                DESCRIPTION
                        "Number of frames forwarded from the port that 
                        contain a Routing Information field (other than 
                        broadcast frames).  This statistic is displayed 
                        for a source routing bridge only."
                ::= { statBridgePortEntry 11 }   
                
            statBridgePortTr-AllRteFrameIn OBJECT-TYPE
                SYNTAX  DisplayString
                ACCESS  read-only
                STATUS  mandatory
                DESCRIPTION
                        "Number of all-routes broadcast frames received 
                        on the port.  This statistic is displayed for a 
                        source routing bridge only."
                ::= { statBridgePortEntry 12 }   
                
            statBridgePortTr-AllRteFrameOut OBJECT-TYPE
                SYNTAX  DisplayString
                ACCESS  read-only
                STATUS  mandatory
                DESCRIPTION
                        "Number of all-routes broadcast frames forwarded 
                        from the port.  This statistic is displayed for a 
                        source routing bridge only."
                ::= { statBridgePortEntry 13 }   
                
            statBridgePortTr-SingleRteFrameIn OBJECT-TYPE
                SYNTAX  DisplayString
                ACCESS  read-only
                STATUS  mandatory
                DESCRIPTION
                        "Number of single-route broadcast frames received 
                        on the port.  This statistic is displayed for a 
                        source routing bridge only."
                ::= { statBridgePortEntry 14 }   
                
            statBridgePortTr-SingleRteFrameOut OBJECT-TYPE
                SYNTAX  DisplayString
                ACCESS  read-only
                STATUS  mandatory
                DESCRIPTION
                        "Number of single-route broadcast frames forwarded 
                        from the port.  This statistic is displayed for a 
                        source routing bridge only."
                ::= { statBridgePortEntry 15 }   
                
            statBridgePortTr-SegmentMismatch OBJECT-TYPE
                SYNTAX  DisplayString
                ACCESS  read-only
                STATUS  mandatory
                DESCRIPTION
                        "Number of single-route or all-routes broadcast 
                        frames that have been discarded by this port because 
                        the Routing Information field contained an invalid 
                        adjacent segment value.  This statistic is displayed 
                        for a source routing bridge only."
                ::= { statBridgePortEntry 16 }   
                
            statBridgePortTr-SegmentDuplicate OBJECT-TYPE
                SYNTAX  DisplayString
                ACCESS  read-only
                STATUS  mandatory
                DESCRIPTION
                        "Number of frames, other than broadcast frames, that 
                        have been discarded by this port because the Routing 
                        Information field contained the same segment 
                        identifier more than once.  This statistic is 
                        displayed for a source routing bridge only."
                ::= { statBridgePortEntry 17 }   
                
            statBridgePortTr-HopCntExceeded OBJECT-TYPE
                SYNTAX  DisplayString
                ACCESS  read-only
                STATUS  mandatory
                DESCRIPTION
                        "Number of single-route or all-routes broadcast 
                        frames that have been discarded by this port because 
                        the Routing Information field reached the maximum 
                        number of hops permitted.  This statistic is 
                        displayed for a source routing bridge only."
                ::= { statBridgePortEntry 18 }   
                
            statBridgePortTr-FrmLngExceeded OBJECT-TYPE
                SYNTAX  DisplayString
                ACCESS  read-only
                STATUS  mandatory
                DESCRIPTION
                        "This counter displays the number of non-broadcast 
                        token-ring frames that have been discarded by this 
                        port because the frame length has passed the maximum 
                        length permitted."
                ::= { statBridgePortEntry 19 }

            StatBridgePort-Ethlan ::=
                SEQUENCE {
                    statBridgePortIndex                  INTEGER,
                    statBridgePortDestination            DisplayString,
                    statBridgePortState                  DisplayString,
                    statBridgePortDesignatedRoot         DisplayString,
                    statBridgePortDesignatedCost         DisplayString,
                    statBridgePortDesignatedBridge       DisplayString,
                    statBridgePortDesignatedPort         DisplayString,
                    statBridgePortTrspFrameIn            DisplayString,
                    statBridgePortTrspFrameOut           DisplayString
                }
                
            StatBridgePort-Trlan ::=
                SEQUENCE {
                    statBridgePortIndex                  INTEGER,
                    statBridgePortDestination            DisplayString,
                    statBridgePortState                  DisplayString,
                    statBridgePortDesignatedRoot         DisplayString,
                    statBridgePortDesignatedCost         DisplayString,
                    statBridgePortDesignatedBridge       DisplayString,
                    statBridgePortDesignatedPort         DisplayString,
                    statBridgePortTrspFrameIn            DisplayString,
                    statBridgePortTrspFrameOut           DisplayString,
                    statBridgePortTr-SpecRteFrameIn      DisplayString,
                    statBridgePortTr-SpecRteFrameOut     DisplayString,
                    statBridgePortTr-AllRteFrameIn       DisplayString,
                    statBridgePortTr-AllRteFrameOut      DisplayString,
                    statBridgePortTr-SingleRteFrameIn    DisplayString,
                    statBridgePortTr-SingleRteFrameOut   DisplayString,
                    statBridgePortTr-SegmentMismatch     DisplayString,
                    statBridgePortTr-SegmentDuplicate    DisplayString,
                    statBridgePortTr-HopCntExceeded      DisplayString,
                    statBridgePortTr-FrmLngExceeded      DisplayString
                }
                
            -- the Stat pvc
            
            statPvcTable OBJECT-TYPE
                SYNTAX  SEQUENCE OF StatPvcEntry
                ACCESS  not-accessible
                STATUS  mandatory
                DESCRIPTION
                        "A list of statistic entries for the PVCs.
                        The number of entries is given by the value 
                        of pvcNumber."
                ::= { stat 6 }
            
            statPvcEntry OBJECT-TYPE
                SYNTAX  StatPvcEntry
                ACCESS  not-accessible
                STATUS  mandatory
                DESCRIPTION
                        "This table contains the principal statistics for 
                        the PVCs."
                INDEX   { statPvcIndex }
                ::= { statPvcTable 1 }
            
            StatPvcEntry ::=
                SEQUENCE {
                    statPvcIndex         INTEGER,
                    statPvcProtocol      DisplayString,
                    statPvcMode          DisplayString,
                    statPvcInfoSignal    DisplayString,
                    statPvcSpeed         DisplayString,
                    statPvcState         DisplayString,
                    statPvcDlci          INTEGER,
                    statPvcMeanTx        Gauge,
                    statPvcMeanRx        Gauge,
                    statPvcPeakTx        Gauge,
                    statPvcPeakRx        Gauge,
                    statPvcError         Counter,
                    statPvcRestart       Counter,
                    statPvcFramesTx      Counter,
                    statPvcFramesRx      Counter,
                    statPvcOctetsTx      Counter,
                    statPvcOctetsRx      Counter,
                    statPvcBadFrames     Counter,
                    statPvcOvrFrames     Counter,
                    statPvcBadOctets     Counter,
                    statPvcOvrOctets     Counter,
                    statPvcCompErrs      Counter,
                    statPvcChOverflows   Counter,
                    statPvcChAborts      Counter,
                    statPvcChSeqErrs     Counter
                }
                
            statPvcIndex OBJECT-TYPE
                SYNTAX  INTEGER
                ACCESS  read-only
                STATUS  mandatory
                DESCRIPTION
                        "A unique value for each PVC.  Its value ranges
                        between 1 and the value of pvcNumber."
                ::= { statPvcEntry 1 }   
                
            statPvcProtocol OBJECT-TYPE
                SYNTAX  DisplayString
                ACCESS  read-only
                STATUS  mandatory
                DESCRIPTION
                        "PVC protocol."
                ::= { statPvcEntry 2 }   
                
            statPvcMode OBJECT-TYPE
                SYNTAX  DisplayString
                ACCESS  read-only
                STATUS  mandatory
                DESCRIPTION
                        "The mode used (PVCR or OFF)."
                ::= { statPvcEntry 3 }   
                
            statPvcInfoSignal OBJECT-TYPE
                SYNTAX  DisplayString
                ACCESS  read-only
                STATUS  mandatory
                DESCRIPTION
                        "The information signal status is displayed with a 
                        five-character field, where the individual characters 
                        have the following meaning:
                        
                                N = New PVC
                                A = Active PVC
                                C = CIR reached
                                F = Forward congestion (to destination PVC)
                                B = Backward congestion (from destination PVC)
                        
                        When an information status signal is not present, the 
                        unit displays a dash [-] in the appropriate position."
                ::= { statPvcEntry 4 }   
                
            statPvcSpeed OBJECT-TYPE
                SYNTAX  DisplayString
                ACCESS  read-only
                STATUS  mandatory
                DESCRIPTION
                        "The port speed measured by the unit."
                ::= { statPvcEntry 5 }
                
            statPvcState OBJECT-TYPE
                SYNTAX  DisplayString
                ACCESS  read-only
                STATUS  mandatory
                DESCRIPTION
                        "The possible states for a PVC in PVCR mode are:
                        
                                OFF  = PVC inactive
                                CALL = Waiting for active signal from the 
                                       network
                                TEST = PVC in test mode
                                DATA = PVC in operation"
                ::= { statPvcEntry 6 }
                
            statPvcMeanTx OBJECT-TYPE
                SYNTAX  Gauge
                ACCESS  read-only
                STATUS  mandatory
                DESCRIPTION
                        "The mean bandwidth usage for transmissions to the 
                        destination PVC."
                ::= { statPvcEntry 7 }
                
            statPvcMeanRx OBJECT-TYPE
                SYNTAX  Gauge
                ACCESS  read-only
                STATUS  mandatory
                DESCRIPTION
                        "The mean bandwidth usage for data received from 
                        the destination PVC."
                ::= { statPvcEntry 8 }
                
            statPvcPeakTx OBJECT-TYPE
                SYNTAX  Gauge
                ACCESS  read-only
                STATUS  mandatory
                DESCRIPTION
                        "The peak bandwidth usage for transmissions to the 
                        destination PVC."
                ::= { statPvcEntry 9 }   
                
            statPvcPeakRx OBJECT-TYPE
                SYNTAX  Gauge
                ACCESS  read-only
                STATUS  mandatory
                DESCRIPTION
                        "The peak bandwidth usage for data received from 
                        the destination PVC."
                ::= { statPvcEntry 10 }   
                
            statPvcError OBJECT-TYPE
                SYNTAX  Counter
                ACCESS  read-only
                STATUS  mandatory
                DESCRIPTION
                        "Number of errors on the PVC.  This counter is 
                        incremented every time the unit detects an error 
                        coming from the PVC."
                ::= { statPvcEntry 11 }   
                
            statPvcRestart OBJECT-TYPE
                SYNTAX  Counter
                ACCESS  read-only
                STATUS  mandatory
                DESCRIPTION
                        "Number of restarts on the PVC.  This counter is 
                        incremented every time the link is down for at least 
                        1 second.  In addition, if the PVC is not restored 
                        within the LINK TIMEOUT value (a Global configuration 
                        parameter), the unit will log a LINK PVC DOWN alarm."
                ::= { statPvcEntry 12 }   
                
            statPvcFramesTx OBJECT-TYPE
                SYNTAX  Counter
                ACCESS  read-only
                STATUS  mandatory
                DESCRIPTION
                        "The number of frames transmitted"
                ::= { statPvcEntry 13 }
            
            statPvcFramesRx OBJECT-TYPE
                SYNTAX  Counter
                ACCESS  read-only
                STATUS  mandatory
                DESCRIPTION
                        "The number of frames received"
                ::= { statPvcEntry 14 }
            
            statPvcOctetsTx OBJECT-TYPE
                SYNTAX  Counter
                ACCESS  read-only
                STATUS  mandatory
                DESCRIPTION
                        "The number of octets transmitted"
                ::= { statPvcEntry 15 }
            
            statPvcOctetsRx OBJECT-TYPE
                SYNTAX  Counter
                ACCESS  read-only
                STATUS  mandatory
                DESCRIPTION
                        "The number of octets received"
                ::= { statPvcEntry 16 }
            
            statPvcBadFrames OBJECT-TYPE
                SYNTAX  Counter
                ACCESS  read-only
                STATUS  mandatory
                DESCRIPTION
                        "The number of frames received and deleted 
                        because the input queue is full."                        
                ::= { statPvcEntry 17 }
            
            statPvcOvrFrames OBJECT-TYPE
                SYNTAX  Counter
                ACCESS  read-only
                STATUS  mandatory
                DESCRIPTION
                        "The number of frames received and deleted 
                        because the input queue is full."                        
                ::= { statPvcEntry 18 }
            
            statPvcBadOctets OBJECT-TYPE
                SYNTAX  Counter
                ACCESS  read-only
                STATUS  mandatory
                DESCRIPTION
                        "The number of characters received and deleted 
                        because of a bad frame."
                ::= { statPvcEntry 19 }
            
            statPvcOvrOctets OBJECT-TYPE
                SYNTAX  Counter
                ACCESS  read-only
                STATUS  mandatory
                DESCRIPTION
                        "The number of characters received and deleted 
                        because the input queue is full."
                ::= { statPvcEntry 20 }
            
                
            statPvcDlci OBJECT-TYPE
                SYNTAX  INTEGER
                ACCESS  read-only
                STATUS  mandatory
                DESCRIPTION
                        "The current DLCI used by this PVC"
                ::= { statPvcEntry 21 }
                
            statPvcCompErrs OBJECT-TYPE
                SYNTAX  Counter
                ACCESS  read-only
                STATUS  mandatory
                DESCRIPTION
                        "The number of compression errors"
                ::= { statPvcEntry 28 }
                 
            statPvcChOverflows OBJECT-TYPE
                SYNTAX  Counter
                ACCESS  read-only
                STATUS  mandatory
                DESCRIPTION
                        "The number of channel overflows"
                ::=  { statPvcEntry 29 }
                
            statPvcChAborts OBJECT-TYPE
                SYNTAX  Counter
                ACCESS  read-only
                STATUS  mandatory
                DESCRIPTION
                        "The number of frames aborted received"
                ::=  { statPvcEntry 30 }
                
            statPvcChSeqErrs OBJECT-TYPE
                SYNTAX  Counter
                ACCESS  read-only
                STATUS  mandatory
                DESCRIPTION
                        "The number of frames reception failure due
                         to at least one missing block"
                ::=  { statPvcEntry 31 }
                
                
            StatPvcStates ::=
                SEQUENCE {
                    statPvcIndex         INTEGER,
                    statPvcProtocol      DisplayString,
                    statPvcMode          DisplayString,
                    statPvcInfoSignal    DisplayString,
                    statPvcSpeed         DisplayString,
                    statPvcState         DisplayString,
                    statPvcDlci          INTEGER
                }
                
            StatPvcCounters ::=
                SEQUENCE {
                    statPvcIndex         INTEGER,
                    statPvcProtocol      DisplayString,
                    statPvcMeanTx        Gauge,
                    statPvcMeanRx        Gauge,
                    statPvcPeakTx        Gauge,
                    statPvcPeakRx        Gauge,
                    statPvcFramesTx      Counter,
                    statPvcFramesRx      Counter,
                    statPvcOctetsTx      Counter,
                    statPvcOctetsRx      Counter,
                    statPvcCompErrs      Counter,
                    statPvcChOverflows   Counter,
                    statPvcChAborts      Counter,
                    statPvcChSeqErrs     Counter
                }
                
            StatPvcErrors ::=
                SEQUENCE {
                    statPvcIndex         INTEGER,
                    statPvcProtocol      DisplayString,
                    statPvcError         Counter,
                    statPvcRestart       Counter,
                    statPvcBadFrames     Counter,
                    statPvcOvrFrames     Counter,
                    statPvcBadOctets     Counter,
                    statPvcOvrOctets     Counter
                }
                
            -- the Stat UNIT Route
            
            statPvcrRouteTable OBJECT-TYPE
                SYNTAX  SEQUENCE OF StatPvcrRouteEntry
                ACCESS  not-accessible
                STATUS  mandatory
                DESCRIPTION
                        "A list of statistic entries for the unit routing."
                ::= { stat 7 }
            
            statPvcrRouteEntry OBJECT-TYPE
                SYNTAX  StatPvcrRouteEntry
                ACCESS  not-accessible
                STATUS  mandatory
                DESCRIPTION
                        "This table contains the principal statistics for 
                        the unit route"
                INDEX   { statPvcrRouteName, statPvcrRouteNextHop }
                ::= { statPvcrRouteTable 1 }
            
            StatPvcrRouteEntry ::=
                SEQUENCE {
                    statPvcrRouteName      DisplayString,
                    statPvcrRouteNextHop   DisplayString,
                    statPvcrRouteValid     INTEGER,
                    statPvcrRouteMetric    Gauge,
                    statPvcrRouteIntrf     INTEGER,
                    statPvcrRouteAge       INTEGER
                }
                
            statPvcrRouteName OBJECT-TYPE
                SYNTAX  DisplayString
                ACCESS  read-only
                STATUS  mandatory
                DESCRIPTION
                        "A unique value for each unit routing entry."
                ::= { statPvcrRouteEntry 1 }   
                
            statPvcrRouteValid OBJECT-TYPE
                SYNTAX  INTEGER {
                            no(1),
                            yes(2)
                        }
                ACCESS  read-only
                STATUS  mandatory
                DESCRIPTION
                        "The VALID value (YES or NO) indicates whether the
                         connection to this destination is currently active."
                ::= { statPvcrRouteEntry 2 }   
                
            statPvcrRouteMetric OBJECT-TYPE
                SYNTAX  Gauge
                ACCESS  read-only
                STATUS  mandatory
                DESCRIPTION
                        "The METRIC provides the hop count, or number of 
                         units that must be passed over to reach the destination.
                         When at 0, it indicates a direct connection to the
                         destination.  Its value is usually between 1 and 15 for
                         an indirect connection.  When at 16, it indicates that 
                         the destination is unreachable."
                ::= { statPvcrRouteEntry 3 }
                
            statPvcrRouteIntrf OBJECT-TYPE
                SYNTAX  INTEGER
                ACCESS  read-only
                STATUS  mandatory
                DESCRIPTION
                        "The interface used to reach the destination."
                ::= { statPvcrRouteEntry 4 }   
                
            statPvcrRouteNextHop OBJECT-TYPE
                SYNTAX  DisplayString
                ACCESS  read-only
                STATUS  mandatory
                DESCRIPTION
                        "The next unit to be reached on the path to the final
                         destination.  The next hop is identified by the IP
                         address of the router that will be used to send
                         the IP frame."
                ::= { statPvcrRouteEntry 5 }   
                
            statPvcrRouteAge OBJECT-TYPE
                SYNTAX  INTEGER
                ACCESS  read-only
                STATUS  mandatory
                DESCRIPTION
                        "The AGE statistic gives the number of seconds since
                         the entry for this destination was entered on the
                         routing table, the aging time for the entry. For a
                         valid connection (VALID = YES), the time is normally
                         between 0 and 30 seconds.  If the destination is 
                         reached"
                ::= { statPvcrRouteEntry 6 }

            -- The stat info global
            
            statSystem           OBJECT IDENTIFIER ::= { stat 20 }
            
            statSystemAlarmNumber OBJECT-TYPE
                SYNTAX  INTEGER 
                ACCESS  read-only
                STATUS  mandatory
                DESCRIPTION
                        "The maximum number of alarms that the system 
                        records"
                ::= { statSystem 1 }
            
            statSystemMeanCompRate OBJECT-TYPE
                SYNTAX  DisplayString
                ACCESS  read-only
                STATUS  mandatory
                DESCRIPTION
                        "Average compression rate."
                ::= { statSystem 2 }
            
            statSystemMeanDecompRate OBJECT-TYPE
                SYNTAX  DisplayString
                ACCESS  read-only
                STATUS  mandatory
                DESCRIPTION
                        "Average decompression rate."
                ::= { statSystem 3 }
            
            statSystemPeakCompRate OBJECT-TYPE
                SYNTAX  DisplayString
                ACCESS  read-only
                STATUS  mandatory
                DESCRIPTION
                        "Maximum compression rate."
                ::= { statSystem 4 }
            
            statSystemPeakDecompRate OBJECT-TYPE
                SYNTAX  DisplayString
                ACCESS  read-only
                STATUS  mandatory
                DESCRIPTION
                        "Maximum decompression rate."
                ::= { statSystem 5 }
            
            statSystemSa OBJECT-TYPE
                SYNTAX  Gauge
                ACCESS  read-only
                STATUS  mandatory
                DESCRIPTION
                        "The number of PUs currently active and running."
                ::= { statSystem 6 }
            
            statSystemSp OBJECT-TYPE
                SYNTAX  Gauge
                ACCESS  read-only
                STATUS  mandatory
                DESCRIPTION
                        "The number of PUs currently trying to get connected."
                ::= { statSystem 7 }
            
            statSystemNa OBJECT-TYPE
                SYNTAX  OCTET STRING (SIZE (6))
                ACCESS  read-only
                STATUS  mandatory
                DESCRIPTION
                        "Network address that the system will use to send 
                        data on the LAN."
                ::= { statSystem 8 }
            
            statSystemBia OBJECT-TYPE
                SYNTAX  OCTET STRING (SIZE (6))
                ACCESS  read-only
                STATUS  mandatory
                DESCRIPTION
                        "Burned-in address of the system."
                ::= { statSystem 9 }
            
            statSystemTr-Nan OBJECT-TYPE
                SYNTAX  OCTET STRING (SIZE (6))
                ACCESS  read-only
                STATUS  mandatory
                DESCRIPTION
                        "The address of the nearest active upstream 
                        neighbor on the Token-Ring."
                ::= { statSystem 10 }
            
            statSystemResetCounters OBJECT-TYPE
                SYNTAX  INTEGER {
                            no(1),
                            yes(2)
                        }
                ACCESS  read-write
                STATUS  mandatory
                DESCRIPTION
                        "When this variable is set to yes, all statistics
                        counters are reset to 0 value."
                ::= { statSystem 11 }
            
            statSystemClearAlarms OBJECT-TYPE
                SYNTAX  INTEGER {
                            no(1),
                            yes(2)
                        }
                ACCESS  read-write
                STATUS  mandatory
                DESCRIPTION
                        "When this variable is set to yes, all alarms are 
                        erased."
                ::= { statSystem 12 }

            statSystemClearErrorLed OBJECT-TYPE
                SYNTAX  INTEGER {
                            no(1),
                            yes(2)
                        }
                ACCESS  read-write
                STATUS  mandatory
                DESCRIPTION
                        "When this variable is set to YES, the error LED is 
                        cleared."
                ::= { statSystem 13 }

            -- The stat info of Bootp

            statBootp           OBJECT IDENTIFIER ::= { stat 21 }
            
            statBootpNbRequestReceived OBJECT-TYPE
                SYNTAX  INTEGER 
                ACCESS  read-only
                STATUS  mandatory
                DESCRIPTION
                        "Number of BOOTREQUEST frame received"
                ::= { statBootp 1 }

            statBootpNbRequestSend OBJECT-TYPE
                SYNTAX  INTEGER 
                ACCESS  read-only
                STATUS  mandatory
                DESCRIPTION
                        "Number of BOOTREQUEST frame send"
                ::= { statBootp 2 }

            statBootpNbReplyReceived OBJECT-TYPE
                SYNTAX  INTEGER 
                ACCESS  read-only
                STATUS  mandatory
                DESCRIPTION
                        "Number of BOOTREPLY frame received"
                ::= { statBootp 3 }

            statBootpNbReplySend OBJECT-TYPE
                SYNTAX  INTEGER 
                ACCESS  read-only
                STATUS  mandatory
                DESCRIPTION
                        "Number of BOOTREPLY frame send"
                ::= { statBootp 4 }

            statBootpReplyWithInvalidGiaddr OBJECT-TYPE
                SYNTAX  INTEGER 
                ACCESS  read-only
                STATUS  mandatory
                DESCRIPTION
                        "A BOOTREPLY was received but the ‘giaddr’
                        (the gateway IP address) fields do not correspond
                        of any IP address of your ports. This frames is discarded."
                ::= { statBootp 5 }

            statBootpHopsLimitExceed OBJECT-TYPE
                SYNTAX  INTEGER 
                ACCESS  read-only
                STATUS  mandatory
                DESCRIPTION
                        "A BOOTREQUEST frame was received with its hops count
                        that exceed the configured Max hops. This frame is discarded."
                ::= { statBootp 6 }

            statBootpRequestReceivedOnPortBootpc OBJECT-TYPE
                SYNTAX  INTEGER 
                ACCESS  read-only
                STATUS  mandatory
                DESCRIPTION
                        "A BOOTREQUEST frame was received on the UDP port BOOTPC.
                        That should never occur. This frame is discarded."
                ::= { statBootp 7 }

            statBootpReplyReceivedOnPortBootpc OBJECT-TYPE
                SYNTAX  INTEGER 
                ACCESS  read-only
                STATUS  mandatory
                DESCRIPTION
                        "A BOOTREPLY frame was received on the UDP port BOOTPC.
                        That could occur when a BOOTP/DHCP server is on the same
                        LAN that we are.  But that is considered unusual.
                        This frame is discarded."
                ::= { statBootp 8 }

            statBootpInvalidOpCodeField OBJECT-TYPE
                SYNTAX  INTEGER 
                ACCESS  read-only
                STATUS  mandatory
                DESCRIPTION
                        "A frame is received on BOOTPC or BOOTPS port with a invalid
                        operation code field:  It was not a BOOTREQUEST nor BOOTREPLY.
                        This frame is discarded."
                ::= { statBootp 9 }

            statBootpCannotRouteFrame OBJECT-TYPE
                SYNTAX  INTEGER 
                ACCESS  read-only
                STATUS  mandatory
                DESCRIPTION
                        "Configuration problem:  in the IP destination address list,
                        which is configurable, we have an address that we cannot route
                        (we don't know on which port transmit the frame).
                        This frame is discarded."
                ::= { statBootp 10 }

            statBootpFrameTooSmallToBeABootpFrame OBJECT-TYPE
                SYNTAX  INTEGER 
                ACCESS  read-only
                STATUS  mandatory
                DESCRIPTION
                        "The frame have not the minimal length of a BOOTP frame,
                        some fields are missing.  This frame is discarded."
                ::= { statBootp 11 }
            
            statBootpCannotReceiveAndForwardOnTheSamePort OBJECT-TYPE
                SYNTAX  INTEGER 
                ACCESS  read-only
                STATUS  mandatory
                DESCRIPTION
                        "Number of frame received and try to be send on the same 
                        port.  This will occur when the relay agents are in BROADCAST 
                        MODE. In normal operation, when the product is well configured, 
                        this should not occur.  This frame is discarded."
                ::= { statBootp 12 }

            --  The stat group info
            
            statGrp     OBJECT IDENTIFIER ::= { stat 22 }
            
            statGrpNumber OBJECT-TYPE
                SYNTAX  INTEGER
                ACCESS  read-only
                STATUS  mandatory
                DESCRIPTION
                        "A list of statistic entries for the groups."
                ::= { statGrp 1 }
            
            statGrpTable OBJECT-TYPE
                SYNTAX  SEQUENCE OF StatGrpEntry
                ACCESS  not-accessible
                STATUS  mandatory
                DESCRIPTION
                        "A list of statistic entries for the groups."
                ::= { statGrp 2 }
            
            statGrpEntry OBJECT-TYPE
                SYNTAX  StatGrpEntry
                ACCESS  not-accessible
                STATUS  mandatory
                DESCRIPTION
                        "This table contains the principal statistics for 
                        the groups."
                INDEX   { statGrpIndex }
                ::= { statGrpTable 1 }
            
            StatGrpEntry ::=
                SEQUENCE {
                    statGrpIndex            INTEGER,         
                    statGrpDestName         DisplayString,    
                    statGrpOutOfSeqErrs     INTEGER,
                    statGrpSorterTimeouts   INTEGER,
                    statGrpSorterOverruns   INTEGER
                }
                
            statGrpIndex OBJECT-TYPE
                SYNTAX  INTEGER
                ACCESS  read-only
                STATUS  mandatory
                DESCRIPTION
                        "A unique value for each group.  Its value ranges
                        between 1 and the number of groups."
                ::= { statGrpEntry 1 }   
                
            statGrpDestName OBJECT-TYPE
                SYNTAX  DisplayString
                ACCESS  read-only
                STATUS  mandatory
                DESCRIPTION
                        "The destination name of the group"
                ::= { statGrpEntry 2 }   
                
            statGrpOutOfSeqErrs OBJECT-TYPE
                SYNTAX  INTEGER
                ACCESS  read-only
                STATUS  mandatory
                DESCRIPTION
                        ""
                ::= { statGrpEntry 3}   
                
            statGrpSorterTimeouts OBJECT-TYPE
                SYNTAX  INTEGER
                ACCESS  read-only
                STATUS  mandatory
                DESCRIPTION
                        ""
                ::= { statGrpEntry 4 }   
                
            statGrpSorterOverruns OBJECT-TYPE
                SYNTAX  INTEGER
                ACCESS  read-only
                STATUS  mandatory
                DESCRIPTION
                        ""
                ::= { statGrpEntry 5 }   
                
            
            --  Timep statistics
            
            statTimep           OBJECT IDENTIFIER ::= { stat 23 }
            
            statTimeNbFrameReceived OBJECT-TYPE
                SYNTAX  INTEGER 
                ACCESS  read-only
                STATUS  mandatory
                DESCRIPTION
                        "Number of frames received."
                ::= { statTimep 1 }

            statTimeNbFrameSent OBJECT-TYPE
                SYNTAX  INTEGER 
                ACCESS  read-only
                STATUS  mandatory
                DESCRIPTION
                        "Number of frames sent."
                ::= { statTimep 2 }

            statTimeNbRequestReceived OBJECT-TYPE
                SYNTAX  INTEGER 
                ACCESS  read-only
                STATUS  mandatory
                DESCRIPTION
                        "Number of requests received by time server."
                ::= { statTimep 3 }

            statTimeNbReplySent OBJECT-TYPE
                SYNTAX  INTEGER 
                ACCESS  read-only
                STATUS  mandatory
                DESCRIPTION
                        "Number of replies sent by time server."
                ::= { statTimep 4 }

            statTimeNbRequestSent OBJECT-TYPE
                SYNTAX  INTEGER 
                ACCESS  read-only
                STATUS  mandatory
                DESCRIPTION
                        "Number of requests sent by time client."
                ::= { statTimep 5 }

            statTimeNbReplyReceived OBJECT-TYPE
                SYNTAX  INTEGER 
                ACCESS  read-only
                STATUS  mandatory
                DESCRIPTION
                        "Number of replies received by time client."
                ::= { statTimep 6 }

            statTimeClientRetransmissions OBJECT-TYPE
                SYNTAX  INTEGER 
                ACCESS  read-only
                STATUS  mandatory
                DESCRIPTION
                        "Number of client retransmission's."
                ::= { statTimep 7 }

            statTimeClientSyncFailures OBJECT-TYPE
                SYNTAX  INTEGER 
                ACCESS  read-only
                STATUS  mandatory
                DESCRIPTION
                        "Number of client sync failures."
                ::= { statTimep 8 }

            statTimeInvalidLocalIpAddress OBJECT-TYPE
                SYNTAX  INTEGER 
                ACCESS  read-only
                STATUS  mandatory
                DESCRIPTION
                        "Number of invalid local IP addresses."
                ::= { statTimep 9 }

            statTimeInvalidPortNumbers OBJECT-TYPE
                SYNTAX  INTEGER 
                ACCESS  read-only
                STATUS  mandatory
                DESCRIPTION
                        "Number of frames with invalid port numbers."
                ::= { statTimep 10 }


            --  Q922 counters (SVC)
            
            statQ922counters           OBJECT IDENTIFIER ::= { stat 24 }
            
            statTxRetransmissions OBJECT-TYPE
                SYNTAX  INTEGER 
                ACCESS  read-only
                STATUS  mandatory
                DESCRIPTION
                        "Number of retransmissions invoked."
                ::= { statQ922counters 1 }

            statReleaseIndications OBJECT-TYPE
                SYNTAX  INTEGER 
                ACCESS  read-only
                STATUS  mandatory
                DESCRIPTION
                        "Number of release indications."
                ::= { statQ922counters 2 }

            statEstablishIndications OBJECT-TYPE
                SYNTAX  INTEGER 
                ACCESS  read-only
                STATUS  mandatory
                DESCRIPTION
                        "Number of establish indications."
                ::= { statQ922counters 3 }

            statLinkEstablished OBJECT-TYPE
                SYNTAX  INTEGER 
                ACCESS  read-only
                STATUS  mandatory
                DESCRIPTION
                        "Number of links established."
                ::= { statQ922counters 4 }

            statTxIframeQdiscards OBJECT-TYPE
                SYNTAX  INTEGER 
                ACCESS  read-only
                STATUS  mandatory
                DESCRIPTION
                        "Number of Iframe Q discards."
                ::= { statQ922counters 5 }

            statRxframes OBJECT-TYPE
                SYNTAX  INTEGER 
                ACCESS  read-only
                STATUS  mandatory
                DESCRIPTION
                        "Number of received frames."
                ::= { statQ922counters 6 }

            statTxframes OBJECT-TYPE
                SYNTAX  INTEGER 
                ACCESS  read-only
                STATUS  mandatory
                DESCRIPTION
                        "Number of transmitted frames."
                ::= { statQ922counters 7 }

            statRxBytes OBJECT-TYPE
                SYNTAX  INTEGER 
                ACCESS  read-only
                STATUS  mandatory
                DESCRIPTION
                        "Number of received bytes."
                ::= { statQ922counters 8 }

            statTxBytes OBJECT-TYPE
                SYNTAX  INTEGER 
                ACCESS  read-only
                STATUS  mandatory
                DESCRIPTION
                        "Number of transmitted bytes."
                ::= { statQ922counters 9 }

            --  Q933 counters (SVC)
            
            statQ922errors           OBJECT IDENTIFIER ::= { stat 25 }
            
            statInvalidRxSizes OBJECT-TYPE
                SYNTAX  INTEGER 
                ACCESS  read-only
                STATUS  mandatory
                DESCRIPTION
                        "Number of frames with invalid lengths."
                ::= { statQ922errors 1 }

            statMissingControlBlocks OBJECT-TYPE
                SYNTAX  INTEGER 
                ACCESS  read-only
                STATUS  mandatory
                DESCRIPTION
                        "Number of frames without control blocks."
                ::= { statQ922errors 2 }

            statRxAcknowledgeExpiry OBJECT-TYPE
                SYNTAX  INTEGER 
                ACCESS  read-only
                STATUS  mandatory
                DESCRIPTION
                        "Number of RR ack Tx from Tack expiry."
                ::= { statQ922errors 3 }

            statTxAcknowledgeExpiry OBJECT-TYPE
                SYNTAX  INTEGER 
                ACCESS  read-only
                STATUS  mandatory
                DESCRIPTION
                        "Number of Tx frame acks delayed waiting for Tack."
                ::= { statQ922errors 4 }

            statQ933counters           OBJECT IDENTIFIER ::= { stat 26 }
            
            statTxSetupMessages OBJECT-TYPE
                SYNTAX  INTEGER 
                ACCESS  read-only
                STATUS  mandatory
                DESCRIPTION
                        "Number of transmitted setup messages."
                ::= { statQ933counters 1 }

            statRxSetupMessages OBJECT-TYPE
                SYNTAX  INTEGER 
                ACCESS  read-only
                STATUS  mandatory
                DESCRIPTION
                        "Number of received setup messages."
                ::= { statQ933counters 2 }

            statTxCallProceedingMessages OBJECT-TYPE
                SYNTAX  INTEGER 
                ACCESS  read-only
                STATUS  mandatory
                DESCRIPTION
                        "Number of transmitted call proceeding messages."
                ::= { statQ933counters 3 }

            statRxCallProceedingMessages OBJECT-TYPE
                SYNTAX  INTEGER 
                ACCESS  read-only
                STATUS  mandatory
                DESCRIPTION
                        "Number of received call proceeding messages."
                ::= { statQ933counters 4 }

            statTxConnectMessages OBJECT-TYPE
                SYNTAX  INTEGER 
                ACCESS  read-only
                STATUS  mandatory
                DESCRIPTION
                        "Number of Tx connect messages."
                ::= { statQ933counters 5 }

            statRxConnectMessages OBJECT-TYPE
                SYNTAX  INTEGER 
                ACCESS  read-only
                STATUS  mandatory
                DESCRIPTION
                        "Number of Rx connect messages."
                ::= { statQ933counters 6 }

            statTxReleaseMessages OBJECT-TYPE
                SYNTAX  INTEGER 
                ACCESS  read-only
                STATUS  mandatory
                DESCRIPTION
                        "Number of transmitted release messages."
                ::= { statQ933counters 7 }

            statRxReleaseMessages OBJECT-TYPE
                SYNTAX  INTEGER 
                ACCESS  read-only
                STATUS  mandatory
                DESCRIPTION
                        "Number of received release messages."
                ::= { statQ933counters 8 }

            statTxReleaseCompleteMessages OBJECT-TYPE
                SYNTAX  INTEGER 
                ACCESS  read-only
                STATUS  mandatory
                DESCRIPTION
                        "Number of transmitted release complete messages."
                ::= { statQ933counters 9 }

            statRxReleaseCompleteMessages OBJECT-TYPE
                SYNTAX  INTEGER 
                ACCESS  read-only
                STATUS  mandatory
                DESCRIPTION
                        "Number of received release complete messages."
                ::= { statQ933counters 10 }

            statTxDisconnectMessages OBJECT-TYPE
                SYNTAX  INTEGER 
                ACCESS  read-only
                STATUS  mandatory
                DESCRIPTION
                        "Number of transmitted disconnect messages."
                ::= { statQ933counters 11 }

            statRxDisconnectMessages OBJECT-TYPE
                SYNTAX  INTEGER 
                ACCESS  read-only
                STATUS  mandatory
                DESCRIPTION
                        "Number of received disconnect messages."
                ::= { statQ933counters 12 }

            statTxStatusMessages OBJECT-TYPE
                SYNTAX  INTEGER 
                ACCESS  read-only
                STATUS  mandatory
                DESCRIPTION
                        "Number of transmitted status messages."
                ::= { statQ933counters 13 }

            statRxStatusMessages OBJECT-TYPE
                SYNTAX  INTEGER 
                ACCESS  read-only
                STATUS  mandatory
                DESCRIPTION
                        "Number of received status messages."
                ::= { statQ933counters 14 }

            statTxStatusEnquiryMessages OBJECT-TYPE
                SYNTAX  INTEGER 
                ACCESS  read-only
                STATUS  mandatory
                DESCRIPTION
                        "Number of transmitted status enquiry messages."
                ::= { statQ933counters 15 }

            statRxStatusEnquiryMessages OBJECT-TYPE
                SYNTAX  INTEGER 
                ACCESS  read-only
                STATUS  mandatory
                DESCRIPTION
                        "Number of received status enquiry messages."
                ::= { statQ933counters 16 }

            statProtocolTimeouts OBJECT-TYPE
                SYNTAX  INTEGER 
                ACCESS  read-only
                STATUS  mandatory
                DESCRIPTION
                        "Number of protocol time-outs."
                ::= { statQ933counters 17 }

            -- the Stat svc
            
            statSvcTable OBJECT-TYPE
                SYNTAX  SEQUENCE OF StatSvcEntry
                ACCESS  not-accessible
                STATUS  mandatory
                DESCRIPTION
                        "A list of statistic entries for the SVCs."
                ::= { stat 27 }
            
            statSvcEntry OBJECT-TYPE
                SYNTAX  StatSvcEntry
                ACCESS  not-accessible
                STATUS  mandatory
                DESCRIPTION
                        "This table contains the principal statistics for 
                        the SVCs."
                INDEX   { statSvcIndex }
                ::= { statSvcTable 1 }

            StatSvcEntry ::=
                SEQUENCE {
                    statSvcIndex         INTEGER,
                    statSvcProtocol      DisplayString,
                    statSvcMode          DisplayString,
                    statSvcInfoSignal    DisplayString,
                    statSvcSpeed         DisplayString,
                    statSvcState         DisplayString,
                    statSvcDlci          INTEGER,
                    statSvcMeanTx        Gauge,
                    statSvcMeanRx        Gauge,
                    statSvcPeakTx        Gauge,
                    statSvcPeakRx        Gauge,
                    statSvcError         Counter,
                    statSvcRestart       Counter,
                    statSvcFramesTx      Counter,
                    statSvcFramesRx      Counter,
                    statSvcOctetsTx      Counter,
                    statSvcOctetsRx      Counter,
                    statSvcBadFrames     Counter,
                    statSvcOvrFrames     Counter,
                    statSvcBadOctets     Counter,
                    statSvcOvrOctets     Counter
                }
                
            statSvcIndex OBJECT-TYPE
                SYNTAX  INTEGER
                ACCESS  read-only
                STATUS  mandatory
                DESCRIPTION
                        "A unique value for each SVC."
                ::= { statSvcEntry 1 }

            statSvcProtocol OBJECT-TYPE
                SYNTAX  DisplayString
                ACCESS  read-only
                STATUS  mandatory
                DESCRIPTION
                        "SVC protocol."
                ::= { statSvcEntry 2 }

            statSvcMode OBJECT-TYPE
                SYNTAX  DisplayString
                ACCESS  read-only
                STATUS  mandatory
                DESCRIPTION
                        "SVC mode. PVCR, FP or OFF"
                ::= { statSvcEntry 3 }

            statSvcInfoSignal OBJECT-TYPE
                SYNTAX  DisplayString
                ACCESS  read-only
                STATUS  mandatory
                DESCRIPTION
                        "The information signal status is displayed with a 
                        five-character field, where the individual characters 
                        have the following meaning:
                        
                                N = New SVC
                                A = Active SVC
                                C = CIR reached
                                F = Forward congestion (to destination SVC)
                                B = Backward congestion (from destination SVC)

                        When an information status signal is not present, the 
                        unit displays a dash [-] in the appropriate position."
                ::= { statSvcEntry 4 }   

            statSvcSpeed OBJECT-TYPE
                SYNTAX  DisplayString
                ACCESS  read-only
                STATUS  mandatory
                DESCRIPTION
                        "The port speed measured by the unit."
                ::= { statSvcEntry 5 }

            statSvcState OBJECT-TYPE
                SYNTAX  DisplayString
                ACCESS  read-only
                STATUS  mandatory
                DESCRIPTION
                        "The possible states for an SVC in PVCR mode are:

                                OFF  = SVC inactive
                                CALL = Waiting for active signal from the
                                       network
                                TEST = SVC in test mode
                                DATA = SVC in operation"
                ::= { statSvcEntry 6 }

            statSvcMeanTx OBJECT-TYPE
                SYNTAX  Gauge
                ACCESS  read-only
                STATUS  mandatory
                DESCRIPTION
                        "The mean bandwidth usage for transmissions to the 
                        destination SVC."
                ::= { statSvcEntry 7 }

            statSvcMeanRx OBJECT-TYPE
                SYNTAX  Gauge
                ACCESS  read-only
                STATUS  mandatory
                DESCRIPTION
                        "The mean bandwidth usage for data received from 
                        the destination SVC."
                ::= { statSvcEntry 8 }

            statSvcPeakTx OBJECT-TYPE
                SYNTAX  Gauge
                ACCESS  read-only
                STATUS  mandatory
                DESCRIPTION
                        "The peak bandwidth usage for transmissions to the 
                        destination SVC."
                ::= { statSvcEntry 9 }

            statSvcPeakRx OBJECT-TYPE
                SYNTAX  Gauge
                ACCESS  read-only
                STATUS  mandatory
                DESCRIPTION
                        "The peak bandwidth usage for data received from 
                        the destination SVC."
                ::= { statSvcEntry 10 }

            statSvcError OBJECT-TYPE
                SYNTAX  Counter
                ACCESS  read-only
                STATUS  mandatory
                DESCRIPTION
                        "Number of errors on the SVC.  This counter is 
                        incremented every time the unit detects an error
                        coming from the SVC."
                ::= { statSvcEntry 11 }

            statSvcRestart OBJECT-TYPE
                SYNTAX  Counter
                ACCESS  read-only
                STATUS  mandatory
                DESCRIPTION
                        "Number of restarts on the SVC.  This counter is 
                        incremented every time the link is down for at least
                        1 second.  In addition, if the SVC is not restored 
                        within the LINK TIMEOUT value (a Global configuration
                        parameter), the unit will log a LINK SVC DOWN alarm."
                ::= { statSvcEntry 12 }

            statSvcFramesTx OBJECT-TYPE
                SYNTAX  Counter
                ACCESS  read-only
                STATUS  mandatory
                DESCRIPTION
                        "The number of frames transmitted"
                ::= { statSvcEntry 13 }

            statSvcFramesRx OBJECT-TYPE
                SYNTAX  Counter
                ACCESS  read-only
                STATUS  mandatory
                DESCRIPTION
                        "The number of frames received"
                ::= { statSvcEntry 14 }

            statSvcOctetsTx OBJECT-TYPE
                SYNTAX  Counter
                ACCESS  read-only
                STATUS  mandatory
                DESCRIPTION
                        "The number of octets transmitted"
                ::= { statSvcEntry 15 }

            statSvcOctetsRx OBJECT-TYPE
                SYNTAX  Counter
                ACCESS  read-only
                STATUS  mandatory
                DESCRIPTION
                        "The number of octets received"
                ::= { statSvcEntry 16 }

            statSvcBadFrames OBJECT-TYPE
                SYNTAX  Counter
                ACCESS  read-only
                STATUS  mandatory
                DESCRIPTION
                        "The number of frames received and deleted 
                        because the input queue is full."                        
                ::= { statSvcEntry 17 }

            statSvcOvrFrames OBJECT-TYPE
                SYNTAX  Counter
                ACCESS  read-only
                STATUS  mandatory
                DESCRIPTION
                        "The number of frames received and deleted 
                        because the input queue is full."                        
                ::= { statSvcEntry 18 }

            statSvcBadOctets OBJECT-TYPE
                SYNTAX  Counter
                ACCESS  read-only
                STATUS  mandatory
                DESCRIPTION
                        "The number of characters received and deleted 
                        because of a bad frame."
                ::= { statSvcEntry 19 }

            statSvcOvrOctets OBJECT-TYPE
                SYNTAX  Counter
                ACCESS  read-only
                STATUS  mandatory
                DESCRIPTION
                        "The number of characters received and deleted 
                        because the input queue is full."
                ::= { statSvcEntry 20 }

                
            statSvcDlci OBJECT-TYPE
                SYNTAX  INTEGER
                ACCESS  read-only
                STATUS  mandatory
                DESCRIPTION
                        "The current DLCI used by this SVC"
                ::= { statSvcEntry 21 }

            StatSvcStates ::=
                SEQUENCE {
                    statSvcIndex         INTEGER,
                    statSvcProtocol      DisplayString,
                    statSvcMode          DisplayString,
                    statSvcInfoSignal    DisplayString,
                    statSvcSpeed         DisplayString,
                    statSvcState         DisplayString,
                    statSvcDlci          INTEGER
                }
                
            StatSvcCounters ::=
                SEQUENCE {
                    statSvcIndex         INTEGER,
                    statSvcProtocol      DisplayString,
                    statSvcMeanTx        Gauge,
                    statSvcMeanRx        Gauge,
                    statSvcPeakTx        Gauge,
                    statSvcPeakRx        Gauge,
                    statSvcFramesTx      Counter,
                    statSvcFramesRx      Counter,
                    statSvcOctetsTx      Counter,
                    statSvcOctetsRx      Counter
                }
                
            StatSvcErrors ::=
                SEQUENCE {
                    statSvcIndex         INTEGER,
                    statSvcProtocol      DisplayString,
                    statSvcError         Counter,
                    statSvcRestart       Counter,
                    statSvcBadFrames     Counter,
                    statSvcOvrFrames     Counter,
                    statSvcBadOctets     Counter,
                    statSvcOvrOctets     Counter
                }
                
            -- the Stat interfaces cem table

            statIfcemTable OBJECT-TYPE
                SYNTAX  SEQUENCE OF StatIfcemEntry
                ACCESS  not-accessible
                STATUS  mandatory
                DESCRIPTION
                        "A list of statistic entries for the cem
                        interfaces."
                ::= { stat 28 }
            
            statIfcemEntry OBJECT-TYPE
                SYNTAX  StatIfcemEntry
                ACCESS  not-accessible
                STATUS  mandatory
                DESCRIPTION
                        "This table contains statistics
                        for the cem interfaces."
                INDEX   { statIfcemIndex }
                ::= { statIfcemTable 1 }

            StatIfcemEntry ::=
                SEQUENCE {
                    statIfcemIndex          INTEGER,
                    statIfcemDesc           DisplayString,
                    statIfcemClockState     DisplayString
                }
                
            statIfcemIndex OBJECT-TYPE
                SYNTAX  INTEGER
                ACCESS  read-only
                STATUS  mandatory                                     
                DESCRIPTION
                        "A unique value for each interface."
                ::= { statIfcemEntry 1 }    

            statIfcemDesc OBJECT-TYPE
                SYNTAX  DisplayString
                ACCESS  read-only
                STATUS  mandatory
                DESCRIPTION
                        "A textual string containing information about 
                        a specific interface."
                ::= { statIfcemEntry 2 }

            statIfcemClockState OBJECT-TYPE
                SYNTAX  DisplayString
                ACCESS  read-only
                STATUS  mandatory
                DESCRIPTION
                        "This variable contains the status of the clock extracting module."
                ::= { statIfcemEntry 3 }

            -- Traps

            connectionDown TRAP-TYPE
                ENTERPRISE  lucent
                VARIABLES   { puIndex }
                DESCRIPTION
                        "This trap indicates that a PU connection has come
                        down."
                ::= 600
                          
            linkDown TRAP-TYPE
                ENTERPRISE  lucent
                VARIABLES   { ifwanIndex }
                DESCRIPTION
                        "This trap indicates that a link has come down."
                ::= 601
                          
            pvcDown TRAP-TYPE
                ENTERPRISE  lucent
                VARIABLES   { pvcIndex }
                DESCRIPTION
                        "This trap indicates that a pvc has come down."
                ::= 602
                          
            cardDown TRAP-TYPE
                ENTERPRISE  lucent
                VARIABLES   { sysTrapRackandPos }
                DESCRIPTION
                        "This trap indicates that a card has come down."
                ::= 603
                          
            connectionUp TRAP-TYPE
                ENTERPRISE  lucent
                VARIABLES   { puIndex }
                DESCRIPTION
                        "This trap indicates that a PU connection has come
                        up."
                ::= 604
                
            linkUp TRAP-TYPE
                ENTERPRISE  lucent
                VARIABLES   { ifwanIndex }
                DESCRIPTION
                        "This trap indicates that a link has come up."
                ::= 605
                
            pvcUp TRAP-TYPE
                ENTERPRISE  lucent
                VARIABLES   { pvcIndex }
                DESCRIPTION
                        "This trap indicates that a pvc has come up."
                ::= 606
                          
            cardup TRAP-TYPE
                ENTERPRISE  lucent
                VARIABLES   { sysTrapRackandPos }
                DESCRIPTION
                        "This trap indicates that a card has come up."
                ::= 607
                          
            periodStarted TRAP-TYPE
                ENTERPRISE  lucent
                VARIABLES   { schedulePeriod }
                DESCRIPTION
                        "This trap indicates that a period is started."
                ::= 608
                
            periodEnded TRAP-TYPE
                ENTERPRISE  lucent
                VARIABLES   { schedulePeriod }
                DESCRIPTION
                        "This trap indicates that a period is ended."
                ::= 609
                
            badDestPort TRAP-TYPE
                ENTERPRISE  lucent
                VARIABLES   { ifwanIndex }
                DESCRIPTION
                        "This trap indicates a bad destination port."
                ::= 610
                          
            badDestPvc TRAP-TYPE
                ENTERPRISE  lucent
                VARIABLES   { ifwanIndex }
                DESCRIPTION
                        "This trap indicates a bad destination pvc."
                ::= 611
                          
            backupCall TRAP-TYPE
                ENTERPRISE  lucent
                DESCRIPTION
                        "A link was activated by the backup mechanism."
                ::= 612
                
            backupHang TRAP-TYPE
                ENTERPRISE  lucent
                DESCRIPTION
                        "A link was de-activated by the backup mechanism."
                ::= 613
                          
            manualCall TRAP-TYPE
                ENTERPRISE  lucent
                DESCRIPTION
                        "A link was manually activated."
                ::= 614
                
            manualHang TRAP-TYPE
                ENTERPRISE  lucent
                DESCRIPTION
                        "A link was manually de-activated."
                ::= 615
                
            bondTrig TRAP-TYPE
                ENTERPRISE  lucent
                DESCRIPTION
                        "Bandwidth On Demand trig."
                ::= 616
                
            bondDeTrig TRAP-TYPE
                ENTERPRISE  lucent
                DESCRIPTION
                        "Bandwidth On Demand de-trig."
                ::= 617
                
            firmwareStored TRAP-TYPE
                ENTERPRISE  lucent
                DESCRIPTION
                        "A new firmware was stored in the unit."
                ::= 618
                
            cfgStored TRAP-TYPE
                ENTERPRISE  lucent
                DESCRIPTION
                        "A new setup was stored in the unit."
                ::= 619
                
            noTrap TRAP-TYPE
                ENTERPRISE  lucent
                DESCRIPTION
                        "The operating system fail to schedule a trap."
                ::= 620
                
            fatalTrap TRAP-TYPE
                ENTERPRISE  lucent
                DESCRIPTION
                        "The operating system fail to execute a trap."
                ::= 621
                
            notMemory TRAP-TYPE
                ENTERPRISE  lucent
                DESCRIPTION
                        "The unit has not enough memory."
                ::= 622
                
            setupReset TRAP-TYPE
                ENTERPRISE  lucent
                DESCRIPTION
                        "The setup was reset by the operator."
                ::= 623
                
            badChecksum TRAP-TYPE
                ENTERPRISE  lucent
                DESCRIPTION
                        "Invalid checksum"
                ::= 624
                
            fatalMsg TRAP-TYPE
                ENTERPRISE  lucent
                DESCRIPTION
                        "The operating system fail to process a msg."
                ::= 625
                
            noMsg TRAP-TYPE
                ENTERPRISE  lucent
                DESCRIPTION
                        "The operating system fail to allocate a msg."
                ::= 626
                
            bothPsUp TRAP-TYPE
                ENTERPRISE  lucent
                DESCRIPTION
                        "Both PS of a rack are running."
                ::= 627
                
            onePsDown TRAP-TYPE
                ENTERPRISE  lucent
                DESCRIPTION
                        "One PS of the rack is not running."
                ::= 628
                
            bothFansUp TRAP-TYPE
                ENTERPRISE  lucent
                DESCRIPTION
                        "Both fans of a rack are running."
                ::= 629
                
            oneOrMoreFanDown TRAP-TYPE
                ENTERPRISE  lucent
                DESCRIPTION
                        "One fan or more on the rack are not running."
                ::= 630
                
            accountingFileFull TRAP-TYPE
                ENTERPRISE  lucent
                DESCRIPTION
                        "Call accounting log file is 90% full."
                ::= 631
                
            frLinkUp TRAP-TYPE
                ENTERPRISE  lucent
                VARIABLES   { ifwanIndex }
                DESCRIPTION
                        "This trap indicates that a frame relay link has come up."
                ::= 665
                
            frLinkDown TRAP-TYPE
                ENTERPRISE  lucent
                VARIABLES   { ifwanIndex }
                DESCRIPTION
                        "This trap indicates that a frame relay link has come down."
                ::= 666
                          
            q922Up TRAP-TYPE
                ENTERPRISE  lucent
                VARIABLES   { ifwanIndex }
                DESCRIPTION
                        "This trap indicates that a Q922 link has come up."
                ::= 667
                
            q922Down TRAP-TYPE
                ENTERPRISE  lucent
                VARIABLES   { ifwanIndex }
                DESCRIPTION
                        "This trap indicates that a Q922 link has come down."
                ::= 668
                          
            accountingFileOverflow TRAP-TYPE
                ENTERPRISE  lucent
                DESCRIPTION
                        "Call accounting log file will overflow on next call."
                ::= 669
                                        
            END
