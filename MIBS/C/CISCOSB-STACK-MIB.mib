CISCOSB-STACK-MIB DEFINITIONS ::= BEGIN

-- Title:               CISCOSB LOCALIZATION ROS
--                      This Private MIB supports the unit id configuration for stack of ROS products
-- Version:             7.40
-- Date:                21 Nov 2005
-- 23-May-2012			Update unit id from 4 to 8 units maximum
-- 19-Dec-2012          Support Lion Native and advanced-hybrid-xg
--
-- 01-Nov-2005 Add rlStackUnitMacAddressAfterReset
-- 21-Nov-2005 Change range of rlStackActiveUnitIdAfterReset
-- 21 mar 2011 In version 7.50, unit id configuration for hybrid stack 
-- 10 Oct 2011 Add port-speed-down 

IMPORTS
    MacAddress      FROM BRIDGE-MIB
    switch001       FROM CISCOSB-MIB OBJECT-TYPE,
    MODULE-IDENTITY FROM SNMPv2-SMI
    TruthValue, TEXTUAL-CONVENTION FROM SNMPv2-TC;


rlStack MODULE-IDENTITY
         LAST-UPDATED "200504140000Z"
         ORGANIZATION "Cisco Small Business"

         CONTACT-INFO
         "Postal: 170 West Tasman Drive
         San Jose , CA 95134-1706
         USA

         Website: Cisco Small Business Home http://www.cisco.com/smb>;,
         Cisco Small Business Support Community <http://www.cisco.com/go/smallbizsupport>"

         DESCRIPTION
                "The private MIB module definition for stack."
         REVISION "200504140000Z"
         DESCRIPTION
                "Initial revision."
        ::= { switch001 107 }

StackMode ::= INTEGER {
   standalone           (1),
   native               (2),
   basic-hybrid         (3),
   advanced-hybrid      (4),
   advanced-hybrid-XG   (5)
}

PortsPair   ::= INTEGER {
   pair-s1s2        (1),
   pair-s3s4        (2),
   pair-s1s25G      (3),
   pair-s1s2Xg      (4),
   pair-lionXg      (5)
}

HybridStackPortSpeed  ::= INTEGER {
   port-speed-1G      (1),
   port-speed-5G      (2),
   port-speed-10G     (3),
   port-speed-auto    (4),
   port-speed-down    (5)
}

HybridStackDeviceMode  ::= INTEGER {
   mode-L2      (1),
   mode-L3      (2)
}

rlStackActiveUnitIdTable OBJECT-TYPE
    SYNTAX SEQUENCE OF RlStackActiveUnitIdEntry
    MAX-ACCESS not-accessible
    STATUS     current
    DESCRIPTION
        " The table listing the active unit id of the requested unit."
    ::= {rlStack 1 }

rlStackActiveUnitIdEntry  OBJECT-TYPE
    SYNTAX      RlStackActiveUnitIdEntry
    MAX-ACCESS  not-accessible
    STATUS      current
    DESCRIPTION
        " An entry in the rlStackActiveUnitIdTable."
    INDEX {rlStackCurrentUnitId }
    ::= {rlStackActiveUnitIdTable  1 }

RlStackActiveUnitIdEntry ::= SEQUENCE {
    rlStackCurrentUnitId             INTEGER,
    rlStackActiveUnitIdAfterReset    INTEGER
}

rlStackCurrentUnitId OBJECT-TYPE
    SYNTAX      INTEGER
    MAX-ACCESS  not-accessible
    STATUS      current
    DESCRIPTION
        "The unit number device, which is the active unit id"
    ::= {rlStackActiveUnitIdEntry 1 }


rlStackActiveUnitIdAfterReset OBJECT-TYPE
    SYNTAX      INTEGER (0..255)
    MAX-ACCESS  read-write
    STATUS      current
    DESCRIPTION
        "Indicates the unit id that will be after reset."
    ::= {rlStackActiveUnitIdEntry 2 }

rlStackUnitModeAfterReset OBJECT-TYPE
    SYNTAX  INTEGER {
                    standalone(1),
                    stack(2)
                    }
    MAX-ACCESS  read-write
    STATUS      current
    DESCRIPTION
        "set unit type that will be after reset, standalone or stack."
    ::= {rlStack 2 }

rlStackUnitMode OBJECT-TYPE
    SYNTAX  INTEGER {
                    standalone(1),
                    stack(2)
                    }
    MAX-ACCESS  read-only
    STATUS      current
    DESCRIPTION
        "show unit type standalone or stack."
    ::= {rlStack 3 }

rlStackUnitMacAddressAfterReset OBJECT-TYPE
    SYNTAX  MacAddress
    MAX-ACCESS  read-write
    STATUS  current
    DESCRIPTION
            "The MAC address used by this bridge after rest."
    REFERENCE
            "IEEE 802.1D-1990: Sections 6.4.1.1.3 and 3.12.5"
    ::= { rlStack 4 }

	
rlStackHybridTable OBJECT-TYPE
    SYNTAX SEQUENCE OF RlStackHybridEntry
    MAX-ACCESS not-accessible
    STATUS     current
    DESCRIPTION
        " The table listing information required for hybrid stack."
    ::= {rlStack 5 }

rlStackHybridEntry  OBJECT-TYPE
    SYNTAX      RlStackHybridEntry
    MAX-ACCESS  not-accessible
    STATUS      current
    DESCRIPTION
        " An entry in the rlStackActiveUnitIdTable."
    INDEX {rlStackHybridUnitId }
    ::= {rlStackHybridTable  1 }


RlStackHybridEntry ::= SEQUENCE {
    rlStackHybridUnitId                  INTEGER,
    rlStackHybridStackMode               StackMode,
    rlStackHybridPortsPair               PortsPair,
    rlStackHybridPortNo1speed            HybridStackPortSpeed,
    rlStackHybridPortNo2speed            HybridStackPortSpeed,
    rlStackHybridUnitIdAfterReset        INTEGER,
    rlStackHybridStackModeAfterReset     StackMode,
    rlStackHybridPortsPairAfterReset     PortsPair,
    rlStackHybridPortNo1speedAfterReset  HybridStackPortSpeed,
    rlStackHybridPortNo2speedAfterReset  HybridStackPortSpeed,
    rlStackHybridDeleteStartupAfterReset TruthValue,
    rlStackHybridDeviceModeAfterReset    HybridStackDeviceMode,
    rlStackHybridXgPortNo1Num            INTEGER,
    rlStackHybridXgPortNo1NumAfterReset  INTEGER,
    rlStackHybridXgPortNo2Num            INTEGER,
    rlStackHybridXgPortNo2NumAfterReset  INTEGER
}

rlStackHybridUnitId OBJECT-TYPE
    SYNTAX      INTEGER (1..8)
    MAX-ACCESS  not-accessible
    STATUS      current
    DESCRIPTION
        "The unit number device, which is the active unit id"
    ::= {rlStackHybridEntry 1 }


rlStackHybridStackMode OBJECT-TYPE
    SYNTAX      StackMode
    MAX-ACCESS  read-only
    STATUS      current
    DESCRIPTION
        "Indicates the unit stack mode."
    ::= {rlStackHybridEntry 2 }


rlStackHybridPortsPair OBJECT-TYPE
    SYNTAX      PortsPair
    MAX-ACCESS  read-only
    STATUS      current
    DESCRIPTION
        "Indicates the PortsPair."
    ::= {rlStackHybridEntry 3 }


rlStackHybridPortNo1speed OBJECT-TYPE
    SYNTAX      HybridStackPortSpeed
    MAX-ACCESS  read-only
    STATUS      current
    DESCRIPTION
        "Indicates the rlStackHybridPortNo1speed."
    ::= {rlStackHybridEntry 4 }

rlStackHybridPortNo2speed OBJECT-TYPE
    SYNTAX      HybridStackPortSpeed
    MAX-ACCESS  read-only
    STATUS      current
    DESCRIPTION
        "Indicates the rlStackHybridPortNo2speed."
    ::= {rlStackHybridEntry 5 }


rlStackHybridUnitIdAfterReset OBJECT-TYPE
    SYNTAX      INTEGER (0..8)
    MAX-ACCESS  read-write
    STATUS      current
    DESCRIPTION
        "Indicates the unit id that will be after reset."
    ::= {rlStackHybridEntry 6 }


rlStackHybridStackModeAfterReset OBJECT-TYPE
    SYNTAX      StackMode
    MAX-ACCESS  read-write
    STATUS      current
    DESCRIPTION
        "Indicates the unit stack mode that will be after reset."
    ::= {rlStackHybridEntry 7 }

rlStackHybridPortsPairAfterReset OBJECT-TYPE
    SYNTAX      PortsPair
    MAX-ACCESS  read-write
    STATUS      current
    DESCRIPTION
        "Indicates the PortsPair that will be after reset."
    ::= {rlStackHybridEntry 8 }


rlStackHybridPortNo1speedAfterReset OBJECT-TYPE
    SYNTAX      HybridStackPortSpeed
    MAX-ACCESS  read-write
    STATUS      current
    DESCRIPTION
        "Indicates the HybridStackPortSpeed that will be after reset."
    ::= {rlStackHybridEntry 9 }

rlStackHybridPortNo2speedAfterReset OBJECT-TYPE
    SYNTAX      HybridStackPortSpeed
    MAX-ACCESS  read-write
    STATUS      current
    DESCRIPTION
        "Indicates the HybridStackPortSpeed that will be after reset."
    ::= {rlStackHybridEntry 10 }

rlStackHybridDeleteStartupAfterReset OBJECT-TYPE
    SYNTAX      TruthValue
    MAX-ACCESS  read-only
    STATUS      current
    DESCRIPTION
        "Indicates whether the startup configuration is deleted after reset."
    ::= {rlStackHybridEntry 11 }

rlStackHybridDeviceModeAfterReset OBJECT-TYPE
    SYNTAX      HybridStackDeviceMode
    MAX-ACCESS  read-write
    STATUS      current
    DESCRIPTION
        "Indicates Device mode (Layer2 or Layer3) after reset."
    ::= {rlStackHybridEntry 12 }

rlStackHybridXgPortNo1Num OBJECT-TYPE
    SYNTAX      INTEGER (1..16)
    MAX-ACCESS  read-only
    STATUS      current
    DESCRIPTION
        "Indicates the 1st stack cascade active port number."
    ::= {rlStackHybridEntry 13 }

rlStackHybridXgPortNo1NumAfterReset OBJECT-TYPE
    SYNTAX      INTEGER (1..16)
    MAX-ACCESS  read-write
    STATUS      current
    DESCRIPTION
        "Indicates the 1st stack cascade port number that will be after reset."
    ::= {rlStackHybridEntry 14 }

rlStackHybridXgPortNo2Num OBJECT-TYPE
    SYNTAX      INTEGER (1..16)
    MAX-ACCESS  read-only
    STATUS      current
    DESCRIPTION
        "Indicates the 2nd stack cascade active port number."
    ::= {rlStackHybridEntry 15 }

rlStackHybridXgPortNo2NumAfterReset OBJECT-TYPE
    SYNTAX      INTEGER (1..16)
    MAX-ACCESS  read-write
    STATUS      current
    DESCRIPTION
        "Indicates the 2nd stack cascade port number that will be after reset."
    ::= {rlStackHybridEntry 16 }


END
