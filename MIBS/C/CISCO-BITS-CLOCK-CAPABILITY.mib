-- *****************************************************************
-- CISCO-BITS-CLOCK-CAPABILITY.my: 
--     Agent capability MIB for CISCO-BITS-CLOCK-MIB
--
-- January 2005, John Linton and Shekhar Acharya
--
-- Copyright (c) 2005 by cisco Systems, Inc.
-- All rights reserved.
-- *****************************************************************
CISCO-BITS-CLOCK-CAPABILITY DEFINITIONS ::= BEGIN

IMPORTS
        MODULE-IDENTITY
                FROM SNMPv2-SMI
                
        AGENT-CAPABILITIES
                FROM SNMPv2-CONF
                
        ciscoAgentCapability
                FROM CISCO-SMI; 
                

ciscoBitsClockCapability MODULE-IDENTITY
                LAST-UPDATED    "200503080000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-ss7@cisco.com"
                DESCRIPTION
                   "Agent capabilities for the CISCO-BITS-CLOCK-MIB."
                        
                REVISION        "200503080000Z"
                DESCRIPTION
                        "Initial version of this MIB module."
        ::= { ciscoAgentCapability 433 }

ciscoBitsClockV12R025000SW1 AGENT-CAPABILITIES

PRODUCT-RELEASE "Cisco IOS 12.2(25)SW1"
  STATUS          current
  DESCRIPTION     "IOS 12.2(25)SW1 Cisco CISCO-BITS-CLOCK-MIB.my 
                   User Agent MIB capabilities."

SUPPORTS        CISCO-BITS-CLOCK-MIB
  INCLUDES      {  ciscoBitsClockSourceGroup,
                   ciscoBitsClockNotifGroup
                }  
                  
--      Table cBitsClkSourceTable
        VARIATION    cBitsClkSourceRoleAdmin
        ACCESS       not-implemented
        DESCRIPTION "Not implemented."

        VARIATION    cBitsClkSourceRoleCurrent
        ACCESS       not-implemented
        DESCRIPTION "Not implemented."

        VARIATION    cBitsClkSourceTimestamp
        ACCESS       not-implemented
        DESCRIPTION "Not implemented."

        VARIATION    cBitsClkSourceActiveSeconds
        ACCESS       not-implemented
        DESCRIPTION "Not implemented."

        VARIATION    cBitsClkSourceInactiveSeconds
        ACCESS       not-implemented
        DESCRIPTION "Not implemented."

        VARIATION    cBitsClkSourceDescription
        ACCESS       not-implemented
        DESCRIPTION "Not implemented."

::= { ciscoBitsClockCapability 1 }
END
