-- extracted from draft-jones-cable-gateway-device-mib-01.txt
-- at Wed Feb  5 06:12:01 2003

   CABH-DEV-MIB DEFINITIONS ::= BEGIN 
   IMPORTS 
      MODULE-IDENTITY, 
      mib-2                FROM SNMPv2-SMI; 

   cabhDevMib MODULE-IDENTITY 
    
       LAST-UPDATED    "200301220000Z"  -- January 22, 2003 
       ORGANIZATION    "CableLabs Broadband Access Department" 
       CONTACT-INFO 
               "Kevin Luehrs 
                Postal: Cable Television Laboratories, Inc. 
                400 Centennial Parkway 
                Louisville, Colorado 80027-1266 
                U.S.A. 
                Phone:  +1 303-661-9100 
                Fax:    +1 303-661-9199 
                E-mail: k.luehrs@cablelabs.com" 
       DESCRIPTION 
          "This is a MIB module defined to hold the full set of 
           CableHome compliant Residential Gateway device."  
       REVISION "200301220000Z" -- January 22, 2003 
       DESCRIPTION 
          "Initial version, published as RFC xxxx." 
           -- RFC editor to assign xxxx 
       ::=  { mib-2 1 } 
    
   END 

--  
--    Copyright (C) The Internet Society (2003). All Rights Reserved. 
--     
--    This document and translations of it may be copied and furnished to 
--    others, and derivative works that comment on or otherwise explain it 
--    or assist in its implementation may be prepared, copied, published 
--    and distributed, in whole or in part, without restriction of any 
--    kind, provided that the above copyright notice and this paragraph are 
--    included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE."
