-- *****************************************************************************
-- Juniper-MPLS-MIB
--
-- Juniper Networks Enterprise MIB
--   Multiprotocol Label Switching (MPLS) MIB
--
-- Copyright (c) 2002 Unisphere Networks, Inc.
-- Copyright (c) 2002, 2003 Juniper Networks, Inc.
--   All Rights Reserved.
-- *****************************************************************************

Juniper-MPLS-MIB  DEFINITIONS ::= BEGIN

IMPORTS
    MODULE-IDENTITY, OBJECT-TYPE, Integer32, IpAddress, Unsigned32
        FROM SNMPv2-SMI
    RowStatus, DisplayString, TruthValue, TEXTUAL-CONVENTION
        FROM SNMPv2-TC
    MODULE-COMPLIANCE, OBJECT-GROUP
        FROM SNMPv2-CONF
    InterfaceIndex, InterfaceIndexOrZero
        FROM IF-MIB
    juniMibs
        FROM Juniper-MIBs
    JuniNextIfIndex
        FROM Juniper-TC;

juniMplsMIB  MODULE-IDENTITY
    LAST-UPDATED "200404220123Z"  -- 21-Apr-04 09:23 PM EDT
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "The MultiProtocol Label Switching (MPLS) MIB for the Juniper Networks
        enterprise.  This MIB contains managed objects for basic MPLS
        configuration of:
         1. Global tasks - common MPLS usage configurations on a given label
                           switching router (LSR).
         2. Interface tasks - MPLS interface (major interface) configurations.
         3. Tunnel tasks - tunnel interface (minor interface) configurations.
         4. Tunnel profile tasks - configured to be used by multiple MPLS
                                   tunnels.
         5. Explicit paths - supports dynamic and manual configurations of
                             explicit paths.
         6. VPNs - supports constraint-based routing label distribution protocol
                   (CR-LDP) and BGP/MPLS virtual private network (VPN)
                   configurations."
    -- Revision History
    REVISION    "200409150543Z"  -- 15-Sep-04 11:13 AM IST  - JUNOSe 5.2.2
    DESCRIPTION
        "Changed the upper bound value of juniMplsGroupLdpSessionRetries from
         128 to 65535."
    REVISION    "200404220123Z"  -- 21-Apr-04 09:23 PM EDT  - JUNOSe 6.0
    DESCRIPTION
        "Obsoleted some objects."
    REVISION    "200404151331Z"  -- 15-Apr-04 09:31 AM EDT  - JUNOSe 6.0
    DESCRIPTION
		"Removed CR-LDP support."
    REVISION    "200309291417Z"  -- 29-Sep-03 10:17 AM EDT  - JUNOSe 5.1
    DESCRIPTION
        "Product rebranding (JUNOSe)."
    REVISION    "200301241823Z"  -- 24-Jan-03 01:23 PM EST  - JUNOSe 5.0
    DESCRIPTION
        "Replaced Unisphere names with Juniper names.
         Added IP TTL Propagate object to the MPLS scalar group."
    REVISION    "200211041535Z"  -- 04-Nov-02 10:35 AM EST  - JUNOSe 4.1
    DESCRIPTION
        "Fixed SMIv2 conformance.
         Added RowStatus support to juniMplsIfMinorPathOptionTable,
            juniMplsTunnelProfilePathOptionTable,
            juniMplsTunnelProfileDynamicEndpointTable and
            juniMplsTunnelProfileTunnelEndpointTable."
    REVISION    "200204032044Z"  -- 03-Apr-02 03:44 PM EST  - JUNOSe 4.0
    DESCRIPTION
        "Initial version of this MIB module."
    ::= { juniMibs 54 }


-- +++++++++++++++++++++++++++++++++++++++++++++++++++++++++++++++++++++++++++++
-- Textual conventions
-- +++++++++++++++++++++++++++++++++++++++++++++++++++++++++++++++++++++++++++++
JuniMajorCfgVciRanges ::= TEXTUAL-CONVENTION
    STATUS      current
    DESCRIPTION
        "Generic VCI label range specifier for both resource reservation
        protocol (RSVP) and label distribution protocol (LDP)."
    SYNTAX      Integer32 (33..65535)

JuniMajorCfgVpiRanges ::= TEXTUAL-CONVENTION
    STATUS      current
    DESCRIPTION
        "Generic VPI label range specifier for both resource reservation
        protocol (RSVP) and label distribution protocol (LDP)."
    SYNTAX      Integer32 (0..255)

JuniMinorCfgBWRanges ::= TEXTUAL-CONVENTION
    STATUS      current
    DESCRIPTION
       "Specifies bandwidth requirements for each MPLS tunnel."
    SYNTAX      Unsigned32

JuniMinorCfgHoldingAndSetupPriorityRanges ::= TEXTUAL-CONVENTION
    STATUS      current
    DESCRIPTION
        "Each LSP has a setup and hold priority before setting it up or
        preempting it relative to the other LSPs.  This convention specifies
        those ranges."
    SYNTAX      Integer32 (0..7)

JuniMinorCfgRetryTimesAndNorouteRanges ::= TEXTUAL-CONVENTION
    STATUS      current
    DESCRIPTION
        "RSVP/LDP will have a number of retries for successfully setting up a
        tunnel.  This value specifies retry value ranges for LDP/RSVP with or
        without no-route notification."
    SYNTAX      Integer32 (0..65535)

JuniMinorCfgRetryIntervalAndNorouteRanges ::= TEXTUAL-CONVENTION
    STATUS      current
    DESCRIPTION
        "RSVP/LDP will have time interval between two successive retries for
        setting up tunnel successfully.  This value specifies the interval
        ranges for LDP/RSVP with or without no-route notification."
    SYNTAX      Integer32 (0..60)

JuniProfileCfgBWRanges ::= TEXTUAL-CONVENTION
    STATUS      current
    DESCRIPTION
        "Bandwidth range specified for each tunnel in tunnel profiling."
    SYNTAX      Unsigned32

JuniProfileCfgHoldingAndSetupPriorityRanges ::= TEXTUAL-CONVENTION
    STATUS      current
    DESCRIPTION
        "Tunnel setup and hold priority range specified for each tunnel in
        tunnel profile configuration."
    SYNTAX      Integer32 (0..7)

JuniProfileCfgRetryTimesAndNorouteRanges ::= TEXTUAL-CONVENTION
    STATUS      current
    DESCRIPTION
        "Range specified for number of retries for tunnel with or without
        no-route notification for RSVP/LDP."
    SYNTAX      Integer32 (0..65535)

JuniProfileCfgRetryIntervalAndNorouteRanges ::= TEXTUAL-CONVENTION
    STATUS      current
    DESCRIPTION
        "Range specified for retry interval for tunnel with or without no-route
        notification for RSVP/LDP."
    SYNTAX     Integer32 (0..60)


-- +++++++++++++++++++++++++++++++++++++++++++++++++++++++++++++++++++++++++++++
-- Managed objects
-- +++++++++++++++++++++++++++++++++++++++++++++++++++++++++++++++++++++++++++++
juniMplsObjects     OBJECT IDENTIFIER ::= { juniMplsMIB 1 }

--
-- MIB object definitions are organized into the following functional sections:
--
juniMplsLsrGlobalConfig     OBJECT IDENTIFIER ::= { juniMplsObjects 1 }
juniMplsMajorLayer          OBJECT IDENTIFIER ::= { juniMplsObjects 2 }
juniMplsMinorLayer          OBJECT IDENTIFIER ::= { juniMplsObjects 3 }
juniMplsTunnelProfile       OBJECT IDENTIFIER ::= { juniMplsObjects 4 }
juniMplsExplicitPath        OBJECT IDENTIFIER ::= { juniMplsObjects 5 }

juniMplsGroup               OBJECT IDENTIFIER ::= { juniMplsLsrGlobalConfig  1 }
juniMplsGroupList           OBJECT IDENTIFIER ::= { juniMplsLsrGlobalConfig  2 }

juniMplsIfMajorLayer        OBJECT IDENTIFIER ::= { juniMplsMajorLayer 1 }

juniMplsIfMinorLayer        OBJECT IDENTIFIER ::= { juniMplsMinorLayer 1 }
juniMplsMinorLayerList      OBJECT IDENTIFIER ::= { juniMplsMinorLayer 2 }

juniMplsTunnelProfileGroup  OBJECT IDENTIFIER ::= { juniMplsTunnelProfile  1 }
juniMplsTunnelProfileList   OBJECT IDENTIFIER ::= { juniMplsTunnelProfile  2 }

juniMplsExplicitPathGroup   OBJECT IDENTIFIER ::= { juniMplsExplicitPath 1 }


-- /////////////////////////////////////////////////////////////////////////////
--
-- Global tasks configurations.
--
-- The set of objects defined under this section supports MPLS global
-- configurations for each virtual router to function as a label switch router
-- (LSR).
-- Apart from that, the set of objects includes topology driven LSP setup
-- configurations.
--
-- /////////////////////////////////////////////////////////////////////////////

juniMplsGroupMplsEnable OBJECT-TYPE
    SYNTAX      INTEGER {
                    disable(0),
                    enable(1) }
    MAX-ACCESS  read-write
    STATUS      current
    DESCRIPTION
        "Enables or disables MPLS on the virtual router.  When MPLS is created
        on the virtual router (VR), it remains adminstratively disabled untill
        it is enabled explicitly.  Without administratively enabling the MPLS on
        VR, it won't function as an LSR even though it holds the MPLS
        configurations until the MPLS context is destroyed for the VR."
    ::= { juniMplsGroup 1 }

juniMplsGroupReopTimer OBJECT-TYPE
    SYNTAX      Integer32 (0..604800)
    UNITS       "seconds"
    MAX-ACCESS  read-write
    STATUS      current
    DESCRIPTION
        "All LSPs setup in MPLS domain are reoptimized for better LSPs as and
        when available.  This object allows configuration of the frequency of
        reoptimization in time interval."
    DEFVAL    { 3600 }
    ::= { juniMplsGroup 2 }

juniMplsGroupLabelRangeLow OBJECT-TYPE
    SYNTAX      Integer32 (16..1048576)
    MAX-ACCESS  read-write
    STATUS      current
    DESCRIPTION
        "The lower end of the range of the platform label space from which the
        interfaces on a given LSR derive their label space.  Ethernet interfaces
        can use only platform label space while ATM interfaces can use either
        platform or interface label space.  For the successful configuration of
        the label range both lower and higher end values must be set
        cuncurrently."
    DEFVAL    { 16 }
    ::= { juniMplsGroup 3 }

juniMplsGroupLabelRangeHigh OBJECT-TYPE
    SYNTAX      Integer32 (16..1048576)
    MAX-ACCESS  read-write
    STATUS      current
    DESCRIPTION
        "The higher end of the range of the platform label space from which the
        interfaces on a given LSR derive their label space.  Ethernet interfaces
        can use only platform label space while ATM interfaces can use either
        platform or interface label space.  For the successful configuration of
        the label range both lower and higher end values must be set
        cuncurrently."
    DEFVAL    { 1048575 }
    ::= { juniMplsGroup 4 }

juniMplsGroupLspRetryTimesNoroute OBJECT-TYPE
    SYNTAX      Integer32 (0..65535)
    MAX-ACCESS  read-write
    STATUS      current
    DESCRIPTION
        "This object configures the number of retries for LSP setup after a
        failure due to no available route."
    DEFVAL    { 0 }
    ::= { juniMplsGroup 5 }

juniMplsGroupLspRetryIntervalNoroute OBJECT-TYPE
    SYNTAX      Integer32 (0..60)
    UNITS       "seconds"
    MAX-ACCESS  read-write
    STATUS      current
    DESCRIPTION
        "This object configures the time interval between two successive LSP
        setup retries after a failure due to no available route."
    DEFVAL    { 5 }
    ::= { juniMplsGroup 6 }

juniMplsGroupLspRetryTimes OBJECT-TYPE
    SYNTAX      Integer32 (0..65535)
    MAX-ACCESS  read-write
    STATUS      current
    DESCRIPTION
        "Use this object to configure number of retries for LSP setup after a
        failure other than one due to no available route."
    DEFVAL    { 0 }
    ::= { juniMplsGroup 7 }

juniMplsGroupLspRetryInterval OBJECT-TYPE
    SYNTAX      Integer32 (0..60)
    UNITS       "seconds"
    MAX-ACCESS  read-write
    STATUS      current
    DESCRIPTION
        "Use this object to configure the time interval between two LSP setup
        retries after a failure other than one due to no available route."
    DEFVAL    { 5 }
    ::= { juniMplsGroup 8 }

juniMplsGroupLdpRetryTimesNoroute OBJECT-TYPE
    SYNTAX      Integer32 (0..65535)
    MAX-ACCESS  read-write
    STATUS      obsolete
    DESCRIPTION
        "Use this object to configure the number of retries for LDP to setup LSP
        after a failure due to no available route."
    DEFVAL { 0 }
    ::= { juniMplsGroup 9 }

juniMplsGroupLdpRetryIntervalNoroute OBJECT-TYPE
    SYNTAX      Integer32 (0..60)
    UNITS       "seconds"
    MAX-ACCESS  read-write
    STATUS      obsolete
    DESCRIPTION
        "Use this object to configure the time interval between two successive
        LSP setup retries by LDP after a failure due to no available route."
    DEFVAL    { 30 }
    ::= { juniMplsGroup 10 }

juniMplsGroupLdpRetryTimes OBJECT-TYPE
    SYNTAX      Integer32 (0..65535)
    MAX-ACCESS  read-write
    STATUS      obsolete
    DESCRIPTION
        "Use this object to configure LSP setup retries by LDP after a failure
        other than one due to no available route."
    DEFVAL    { 0 }
    ::= { juniMplsGroup 11 }

juniMplsGroupLdpRetryInterval OBJECT-TYPE
    SYNTAX      Integer32 (1..60)
    UNITS       "seconds"
    MAX-ACCESS  read-write
    STATUS      current
    DESCRIPTION
        "Use this object to configure time interval between two LSP setup
        retries by LDP after a failure other than one due to no available
        route."
    DEFVAL    { 30 }
    ::= { juniMplsGroup 12 }

juniMplsGroupLdpSessionRetries OBJECT-TYPE
    SYNTAX      Integer32 (0..65535)
    MAX-ACCESS  read-write
    STATUS      current
    DESCRIPTION
        "Use this object to configure the number of LDP session retries."
    DEFVAL    { 10 }
    ::= { juniMplsGroup 13 }

juniMplsGroupLdpSessionRetryTimer OBJECT-TYPE
    SYNTAX      Integer32 (1..60)
    UNITS       "seconds"
    MAX-ACCESS  read-write
    STATUS      current
    DESCRIPTION
        "Use this object to configure the time interval between two LDP session
        retries."
    DEFVAL    { 10 }
    ::= { juniMplsGroup 14 }

juniMplsGroupTopologyDrivenIpProfileName OBJECT-TYPE
    SYNTAX      DisplayString
    MAX-ACCESS  read-write
    STATUS      current
    DESCRIPTION
        "Usually IP interfaces are stacked on top of the MPLS tunnels.  The
        profiled tunnels are associated with IP interfaces with profile of IP
        interfaces.  This object configures the name for the IP profile."
    DEFVAL    { "" }
    ::= { juniMplsGroup 15 }

juniMplsGroupTopologyDrivenLdpEgressIpIntf OBJECT-TYPE
    SYNTAX      TruthValue
    MAX-ACCESS  read-write
    STATUS      current
    DESCRIPTION
        "This object allows enabling/disabling of IP interfaces created over
        egress LSPs setup by topology driven LSP setup configurations."
    DEFVAL    { false }
    ::= { juniMplsGroup 16 }

juniMplsGroupTopologyDrivenLdpIngressIpIntf OBJECT-TYPE
    SYNTAX      TruthValue
    MAX-ACCESS  read-write
    STATUS      current
    DESCRIPTION
        "This object allows enabling/disabling of IP interfaces created over
        ingress LSPs setup by topology driven LSP setup configurations."
    DEFVAL    { false }
    ::= { juniMplsGroup 17 }

juniMplsGroupTopologyDrivenLdpEgressIpIntfHostOnly OBJECT-TYPE
    SYNTAX      TruthValue
    MAX-ACCESS  read-write
    STATUS      current
    DESCRIPTION
        "This object allows enabling/disabling of IP interfaces created over
        egress LSPs to host only IP addresses setup by topology driven LSP setup
        configurations."
    DEFVAL    { false }
    ::= { juniMplsGroup 18 }

juniMplsGroupTopologyDrivenLdpIngressIpIntfHostOnly OBJECT-TYPE
    SYNTAX      TruthValue
    MAX-ACCESS  read-write
    STATUS      current
    DESCRIPTION
        "This object allows enabling/disabling of IP interfaces created over
        ingress LSPs to host only IP addresses setup by topology driven LSP
        setup configurations."
    DEFVAL    { false }
    ::= { juniMplsGroup 19 }

juniMplsGroupTopologyDrivenLdpEgressIpIntfPolicyListType OBJECT-TYPE
    SYNTAX      INTEGER {
                    accessList(1),
                    prefixList(2),
                    noPolicyList(3) }
    MAX-ACCESS  read-write
    STATUS      current
    DESCRIPTION
        "There are two types of policy list type defined for the locally defined
        labels advertisement to neighbors; viz. accessList and prefixList.  This
        object allows configuration of the egress side of LSR for topology
        driven LSPs.  Set the list type and list name cuncurrently."
    DEFVAL    { noPolicyList }
    ::= { juniMplsGroup 20 }

juniMplsGroupTopologyDrivenLdpIngressIpIntfPolicyListType OBJECT-TYPE
    SYNTAX      INTEGER {
                    accessList(1),
                    prefixList(2),
                    noPolicyList(3) }
    MAX-ACCESS  read-write
    STATUS      current
    DESCRIPTION
        "There are two types of policy list type defined for the locally defined
        labels advertisement to neighbors; viz. accessList and prefixList.  This
        object allows configuration of the ingress side of LSR for topology
        driven LSPs.  Set the list type and list name cuncurrently."
    DEFVAL    { noPolicyList }
    ::= { juniMplsGroup 21 }

juniMplsGroupTopologyDrivenLdpEgressIpIntfPolicyList OBJECT-TYPE
    SYNTAX      DisplayString
    MAX-ACCESS  read-write
    STATUS      current
    DESCRIPTION
        "This object used to configure egress list name of topology driven LSPs
        over IP interfaces.  For successful configurations the egress list name
        must be set cunncurently with egress list type.  Set the list type and
        list name cuncurrently."
    DEFVAL    { "" }
    ::= { juniMplsGroup 22 }

juniMplsGroupTopologyDrivenLdpIngressIpIntfPolicyList OBJECT-TYPE
    SYNTAX      DisplayString
    MAX-ACCESS  read-write
    STATUS      current
    DESCRIPTION
        "This object used to configure ingress list name of topology driven LSPs
        over IP interfaces.  For successful configurations ingress listname set
        cunncurently with ingress list type.  Set the list type and list name
        cuncurrently."
    DEFVAL    { "" }
    ::= { juniMplsGroup 23 }

juniMplsGroupTopologyDrivenLdp OBJECT-TYPE
    SYNTAX      INTEGER {
                    disable(0),
                    enable(1) }
    MAX-ACCESS  read-write
    STATUS      current
    DESCRIPTION
        "LDP is used for label distributions control for setting up the LSPs.
        Topology driven LSPs also setup using LDP label distribution control.
        This object allows to enable/disable LDP admin state used for
        topology driven LSPs setup."
    DEFVAL    { disable }
    ::= { juniMplsGroup 24 }

juniMplsGroupLspLabelDistCtrlMode OBJECT-TYPE
    SYNTAX      INTEGER {
                    ordered(0),
                    independent(1),
                    undefined(2) }
    MAX-ACCESS  read-only
    STATUS      current
    DESCRIPTION
        "Some FECs correspond to address prefixes which are distributed via a
        dynamic routing algorithm.  The setup of the LSPs for these FECs can be
        done in one of two ways: Independent LSP Control or Ordered LSP Control.
        This object displays the LSP lable distribution control mode."
    DEFVAL    { ordered }
    ::= { juniMplsGroup 25 }

juniMplsGroupLdpAdvHostOnly OBJECT-TYPE
    SYNTAX      TruthValue
    MAX-ACCESS  read-write
    STATUS      current
    DESCRIPTION
        "This object allows to enable/disable LDP label advertisement mode for
        host only LSPs."
    DEFVAL    { false }
    ::= { juniMplsGroup 26 }

juniMplsGroupLsrState OBJECT-TYPE
    SYNTAX      DisplayString
    MAX-ACCESS  read-only
    STATUS      current
    DESCRIPTION
        "This object value displays the status of MPLS enabled LSR such as state
        is up or down etc."
    ::= { juniMplsGroup 27 }

juniMplsGroupReopNow OBJECT-TYPE
    SYNTAX      TruthValue
    MAX-ACCESS  read-write
    STATUS      current
    DESCRIPTION
        "All LSPs setup in MPLS domain are reoptimized for better LSPs as and
        when available.  Setting this object forces an immediate check for
        better paths for the existing LSPs."
    DEFVAL    { false }
    ::= { juniMplsGroup 28 }

juniMplsGroupIpTtlPropagate OBJECT-TYPE
    SYNTAX      INTEGER {
                    none(0),
                    hideForwardedAndLocal(1),
                    hideForwarded(2),
                    hideLocal(3) }
    MAX-ACCESS  read-write
    STATUS      current
    DESCRIPTION
        "Indicate the IP TTL propagation status on ingress LSPs.
            none                  - Not set to anything.
            hideForwardedAndLocal - Hide LSP topology from local and forwarded
                                    traffic.
            hideForwarded         - Hide LSP topology from forwarded traffic
                                    only.
            hideLocal             - Hide LSP topology from local traffic only."
    DEFVAL    { none }
    ::= { juniMplsGroup 29 }

--
-- Targeted hello send table
--
juniMplsGroupTargetedHelloSendTable OBJECT-TYPE
    SYNTAX      SEQUENCE OF JuniMplsGroupTargetedHelloSendEntry
    MAX-ACCESS  not-accessible
    STATUS      current
    DESCRIPTION
        "This table contains list of send side IP addresses for LDP targeted
        hello messages."
    ::= { juniMplsGroupList 1 }

juniMplsGroupTargetedHelloSendEntry OBJECT-TYPE
    SYNTAX      JuniMplsGroupTargetedHelloSendEntry
    MAX-ACCESS  not-accessible
    STATUS      current
    DESCRIPTION
        "Each entry represents send IP address for targeted hello message."
    INDEX     { juniMplsGroupTargetedHelloSendAddress }
    ::= { juniMplsGroupTargetedHelloSendTable 1 }

JuniMplsGroupTargetedHelloSendEntry ::= SEQUENCE {
    juniMplsGroupTargetedHelloSendAddress    IpAddress,
    juniMplsGroupLdpTargetedHelloSendMode    INTEGER }

juniMplsGroupTargetedHelloSendAddress OBJECT-TYPE
    SYNTAX      IpAddress
    MAX-ACCESS  not-accessible
    STATUS      current
    DESCRIPTION
        "Configure the send side address for targeted hello messages."
    ::= { juniMplsGroupTargetedHelloSendEntry 1 }

juniMplsGroupLdpTargetedHelloSendMode OBJECT-TYPE
    SYNTAX      INTEGER {
                    add(0),
                    delete(1),
                    none(2) }
    MAX-ACCESS  read-create
    STATUS      current
    DESCRIPTION
        "Select mode to add/delete to the list of IP addresses for targeted
        hello messages."
    ::= { juniMplsGroupTargetedHelloSendEntry 2 }


--
-- Targeted hello receive table
--
juniMplsGroupTargetedHelloReceiveTable OBJECT-TYPE
    SYNTAX      SEQUENCE OF JuniMplsGroupTargetedHelloReceiveEntry
    MAX-ACCESS  not-accessible
    STATUS      current
    DESCRIPTION
        "This table contains list of receive side IP addresses for LDP targeted
        hello messages."
    ::= { juniMplsGroupList 2 }

juniMplsGroupTargetedHelloReceiveEntry OBJECT-TYPE
    SYNTAX      JuniMplsGroupTargetedHelloReceiveEntry
    MAX-ACCESS  not-accessible
    STATUS      current
    DESCRIPTION
        "Each entry represents receive IP address for targeted hello message."
    INDEX     { juniMplsGroupTargetedHelloReceiveAddress }
    ::= { juniMplsGroupTargetedHelloReceiveTable 1 }

JuniMplsGroupTargetedHelloReceiveEntry ::= SEQUENCE {
    juniMplsGroupTargetedHelloReceiveAddress    IpAddress,
    juniMplsGroupLdpTargetedHelloReceiveMode    INTEGER }

juniMplsGroupTargetedHelloReceiveAddress OBJECT-TYPE
    SYNTAX      IpAddress
    MAX-ACCESS  not-accessible
    STATUS      current
    DESCRIPTION
        "Configure the receive side address for targeted hello messages."
    ::= { juniMplsGroupTargetedHelloReceiveEntry 1 }

juniMplsGroupLdpTargetedHelloReceiveMode OBJECT-TYPE
    SYNTAX      INTEGER {
                    add(0),
                    delete(1),
                    none(2) }
    MAX-ACCESS  read-create
    STATUS      current
    DESCRIPTION
        "Select mode to add/delete to the list of IP addresses for targeted
        hello messages."
    ::= { juniMplsGroupTargetedHelloReceiveEntry 2 }


--
-- Label Advertisement access list table
--
juniMplsGroupLdpLabelAdverRouteListTable OBJECT-TYPE
    SYNTAX      SEQUENCE OF JuniMplsGroupLdpLabelAdverRouteListEntry
    MAX-ACCESS  not-accessible
    STATUS      current
    DESCRIPTION
        "Table is a list of LDP label advertisement entries."
    ::= { juniMplsGroupList 3 }

juniMplsGroupLdpLabelAdverRouteListEntry OBJECT-TYPE
    SYNTAX      JuniMplsGroupLdpLabelAdverRouteListEntry
    MAX-ACCESS  not-accessible
    STATUS      current
    DESCRIPTION
        "Each entry represents access list pairs for the LDP peers label
        advertisement."
    INDEX     { juniMplsGroupLdpLabelAdverRouteListName,
                juniMplsGroupLdpLabelAdverNbrListName }
    ::= { juniMplsGroupLdpLabelAdverRouteListTable 1 }

JuniMplsGroupLdpLabelAdverRouteListEntry ::= SEQUENCE {
    juniMplsGroupLdpLabelAdverRouteListName  DisplayString,
    juniMplsGroupLdpLabelAdverNbrListName    DisplayString,
    juniMplsGroupLabelAdverListMode          INTEGER }

juniMplsGroupLdpLabelAdverRouteListName OBJECT-TYPE
    SYNTAX      DisplayString (SIZE(0..32))
    MAX-ACCESS  not-accessible
    STATUS      current
    DESCRIPTION
        "This LDP label advertisement route list name for which this entry
        contains information."
    ::= { juniMplsGroupLdpLabelAdverRouteListEntry 1 }

juniMplsGroupLdpLabelAdverNbrListName OBJECT-TYPE
    SYNTAX      DisplayString (SIZE(0..32))
    MAX-ACCESS  not-accessible
    STATUS      current
    DESCRIPTION
        "The LDP label advertisement neighbor route list name for which this
        entry contains information."
    ::= { juniMplsGroupLdpLabelAdverRouteListEntry 2 }

juniMplsGroupLabelAdverListMode OBJECT-TYPE
    SYNTAX      INTEGER {
                    add(0),
                    delete(1),
                    none(2) }
    MAX-ACCESS  read-create
    STATUS      current
    DESCRIPTION
        "This object selects the mode of addition/deletion to the list."
    ::= { juniMplsGroupLdpLabelAdverRouteListEntry 3 }


--
-- LDP Profile table
--
juniMplsGroupLdpProfileTable OBJECT-TYPE
    SYNTAX      SEQUENCE OF JuniMplsGroupLdpProfileEntry
    MAX-ACCESS  not-accessible
    STATUS      current
    DESCRIPTION
        "Table is a list of LDP Profile entries."
    ::= { juniMplsGroupList 4 }

juniMplsGroupLdpProfileEntry OBJECT-TYPE
    SYNTAX      JuniMplsGroupLdpProfileEntry
    MAX-ACCESS  not-accessible
    STATUS      current
    DESCRIPTION
        "Each entry represents one LDP profile settings."
    INDEX     { juniMplsGroupLdpProfileName }
    ::= { juniMplsGroupLdpProfileTable 1 }

JuniMplsGroupLdpProfileEntry ::= SEQUENCE {
    juniMplsGroupLdpProfileName              DisplayString,
    juniMplsGroupLdpProfileHelloHoldTime     Integer32,
    juniMplsGroupLdpProfileCrLdpAdminState   INTEGER,
    juniMplsGroupLdpProfileRowStatus         RowStatus }

juniMplsGroupLdpProfileName OBJECT-TYPE
    SYNTAX      DisplayString (SIZE(0..20))
    MAX-ACCESS  not-accessible
    STATUS      current
    DESCRIPTION
        "LDP profile name identifies unique entry in the table."
    ::= { juniMplsGroupLdpProfileEntry 1 }

juniMplsGroupLdpProfileHelloHoldTime OBJECT-TYPE
    SYNTAX      Integer32 (0..120)
    MAX-ACCESS  read-create
    STATUS      current
    DESCRIPTION
        "Configure the LDP peers hello hold time period."
    DEFVAL    { 0 }
    ::= { juniMplsGroupLdpProfileEntry 2 }

juniMplsGroupLdpProfileCrLdpAdminState OBJECT-TYPE
    SYNTAX      INTEGER {
                 disable(0),
                 enable(1) }
    MAX-ACCESS  read-create
    STATUS      obsolete
    DESCRIPTION
        "Enable or disable the constraint-based routing label distribution
        protocol (CR-LDP) admin state."
    ::= { juniMplsGroupLdpProfileEntry 3 }

juniMplsGroupLdpProfileRowStatus OBJECT-TYPE
    SYNTAX      RowStatus
    MAX-ACCESS  read-create
    STATUS      current
    DESCRIPTION
        "Controls creation/deletion of entries in this table according to the
        RowStatus textual convention, constrained to support the following
        values only:
           createAndGo
           destroy

        To create an entry in this table, the following entry objects MUST be
        explicitly configured:
           juniMplsGroupLdpProfileCrLdpAdminState
           juniMplsGroupLdpProfileRowStatus "
   ::= { juniMplsGroupLdpProfileEntry 4 }


--
-- RSVP Profile table
--
juniMplsGroupRsvpProfileTable OBJECT-TYPE
    SYNTAX      SEQUENCE OF JuniMplsGroupRsvpProfileEntry
    MAX-ACCESS  not-accessible
    STATUS      current
    DESCRIPTION
        "Table is a list of LDP Profile entries."
    ::= { juniMplsGroupList 5 }

juniMplsGroupRsvpProfileEntry OBJECT-TYPE
    SYNTAX      JuniMplsGroupRsvpProfileEntry
    MAX-ACCESS  not-accessible
    STATUS      current
    DESCRIPTION
        "Each entry represents one LDP profile settings."
    INDEX     { juniMplsGroupRsvpProfileName }
    ::= { juniMplsGroupRsvpProfileTable 1 }

JuniMplsGroupRsvpProfileEntry ::= SEQUENCE {
    juniMplsGroupRsvpProfileName                 DisplayString,
    juniMplsGroupRsvpProfileRefreshPeriod        Unsigned32,
    juniMplsGroupRsvpProfileCleanupTimeoutFactor Integer32,
    juniMplsGroupRsvpProfileRowStatus            RowStatus }

juniMplsGroupRsvpProfileName OBJECT-TYPE
    SYNTAX      DisplayString (SIZE(0..20))
    MAX-ACCESS  not-accessible
    STATUS      current
    DESCRIPTION
        "The RSVP profile name identifies unique entry in the table."
    ::= { juniMplsGroupRsvpProfileEntry 1 }

juniMplsGroupRsvpProfileRefreshPeriod OBJECT-TYPE
    SYNTAX      Unsigned32 (1..1000000000)
    MAX-ACCESS  read-create
    STATUS      current
    DESCRIPTION
        "Configure the time out period between the generation of two refresh
        messages."
    DEFVAL    { 30000 }
    ::= { juniMplsGroupRsvpProfileEntry 2 }

juniMplsGroupRsvpProfileCleanupTimeoutFactor OBJECT-TYPE
    SYNTAX      Integer32 (1..10)
    MAX-ACCESS  read-create
    STATUS      current
    DESCRIPTION
        "Confgure the number of refresh messages can be lost before PATH or RESV
        state is ended."
    DEFVAL    { 3 }
    ::= { juniMplsGroupRsvpProfileEntry 3 }

juniMplsGroupRsvpProfileRowStatus OBJECT-TYPE
    SYNTAX      RowStatus
    MAX-ACCESS  read-create
    STATUS      current
    DESCRIPTION
        "Controls creation/deletion of entries in this table according to the
        RowStatus textual convention, constrained to support the following
        values only:
           createAndGo
           destroy

       To create an entry in this table, the following entry object MUST be
       explicitly configured:
           juniMplsGroupRsvpProfileRowStatus "
   ::= { juniMplsGroupRsvpProfileEntry 4 }



-- //////////////////////////////////////////////////////////////////////////
--
-- MPLS  MAJOR INTERFACE LAYER
--
-- The set of obejcts supports the MPLS major interface specific configurations.
-- Interface specific label space configurations are also part of this.
--
-- Management objects are provided to query for an available interface index,
-- and to create/delete interface of this type.
-- Creating/deleting interface of this type using this MIB has
-- the side effect of creating/deleting corresponding entries
-- in the Interface MIB ifTable/ifXTable, and in the Juniper
-- Enterprise Interface MIB juniIfTable.
--
-- //////////////////////////////////////////////////////////////////////////
juniMplsIfMajorNextIfIndex OBJECT-TYPE
    SYNTAX      JuniNextIfIndex
    MAX-ACCESS  read-only
    STATUS      current
    DESCRIPTION
        "Coordinate ifIndex value allocation for entries in the
        juniMplsIfMajorTable.  A GET of this object returns the next available
        ifIndex value to be used to create an entry in the associated interface
        table; or zero, if no valid ifIndex value is available.  This object
        also returns a value of zero when it is the lexicographic successor of a
        varbind presented in an SNMP GETNEXT or GETBULK request, for which
        circumstance it is assumed that ifIndex allocation is unintended.

        Successive GETs will typically return different values, thus avoiding
        collisions among cooperating management clients seeking to create table
        entries simultaneously."
    ::= { juniMplsIfMajorLayer 1 }


--
-- The MPLS Major Interface Table
--
juniMplsIfMajorTable OBJECT-TYPE
    SYNTAX      SEQUENCE OF JuniMplsIfMajorEntry
    MAX-ACCESS  not-accessible
    STATUS      current
    DESCRIPTION
        "This table contains entries for MPLS Major interfaces present in the
        system."
    ::= { juniMplsIfMajorLayer 2 }

juniMplsIfMajorEntry OBJECT-TYPE
    SYNTAX      JuniMplsIfMajorEntry
    MAX-ACCESS  not-accessible
    STATUS      current
    DESCRIPTION
        "Each entry describes the characteristics of an MPLS Major interface.
        Creating/deleting entries in this table causes corresponding entries to
        be created/deleted in ifTable/ifXTable/juniIfTable."
    INDEX     { juniMplsIfMajorIndex }
    ::= { juniMplsIfMajorTable 1 }

JuniMplsIfMajorEntry ::= SEQUENCE {
    juniMplsIfMajorIndex             InterfaceIndex,
    juniMplsIfMajorRowStatus         RowStatus,
    juniMplsIfMajorLowerIfIndex      InterfaceIndexOrZero,
    juniMplsIfMajorAdminStatus       INTEGER,
    juniMplsIfMajorLdpAdminStatus    INTEGER,
    juniMplsIfMajorLdpProfileName    DisplayString,
    juniMplsIfMajorLdpVpiStart       JuniMajorCfgVpiRanges,
    juniMplsIfMajorLdpVpiStop        JuniMajorCfgVpiRanges,
    juniMplsIfMajorLdpVciStart       JuniMajorCfgVciRanges,
    juniMplsIfMajorLdpVciStop        JuniMajorCfgVciRanges,
    juniMplsIfMajorRsvpAdminStatus   INTEGER,
    juniMplsIfMajorRsvpProfileName   DisplayString,
    juniMplsIfMajorRsvpVpiStart      JuniMajorCfgVpiRanges,
    juniMplsIfMajorRsvpVpiStop       JuniMajorCfgVpiRanges,
    juniMplsIfMajorRsvpVciStart      JuniMajorCfgVciRanges,
    juniMplsIfMajorRsvpVciStop       JuniMajorCfgVciRanges,
    juniMplsIfMajorLabelSpaceType    INTEGER,
    juniMplsIfMajorOpState           INTEGER,
    juniMplsIfMajorCrLdpAdminState   INTEGER }

juniMplsIfMajorIndex OBJECT-TYPE
    SYNTAX      InterfaceIndex
    MAX-ACCESS  not-accessible
    STATUS      current
    DESCRIPTION
        "The ifIndex of the MPLS Major interface.  When creating entries in this
        table, suitable values for this object are determined by reading
        juniMplsIfMajorNextIfIndex."
    ::= { juniMplsIfMajorEntry 1 }

juniMplsIfMajorRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniMplsIfMajorRowStatus
            juniMplsIfMajorLowerIfIndex

        In addition, when creating an entry the following conditions must hold:
            A value for juniMplsIfMajorIndex must have been determined
            previously, by reading juniMplsIfMajorNextIfIndex.

        A corresponding entry in ifTable/ifXTable/juniIfTable is created/
        destroyed as a result of creating/destroying an entry in this table."
    ::= { juniMplsIfMajorEntry 2 }

juniMplsIfMajorLowerIfIndex OBJECT-TYPE
    SYNTAX      InterfaceIndexOrZero
    MAX-ACCESS  read-create
    STATUS      current
    DESCRIPTION
        "The ifIndex of an interface over which this MPLS Major interface to be
        layered.  A value of zero indicates no layering.  An implementation may
        choose to require that a nonzero value be configured at entry creation."
    ::= { juniMplsIfMajorEntry 3 }

juniMplsIfMajorAdminStatus OBJECT-TYPE
    SYNTAX      INTEGER {
                    disable(0),
                    enable(1) }
    MAX-ACCESS  read-create
    STATUS      current
    DESCRIPTION
        "Use this object to create MPLS major interface stacked over any link
        layer interface.  Lower layer(index) over which major stacks has to be
        specified for successful creation of the major interface."
    ::= { juniMplsIfMajorEntry  4 }

juniMplsIfMajorLdpAdminStatus OBJECT-TYPE
    SYNTAX      INTEGER {
                    disable(0),
                    enable(1) }
    MAX-ACCESS  read-create
    STATUS      current
    DESCRIPTION
        "This object enables/disables LDP admin status on the MPLS interface."
    ::= { juniMplsIfMajorEntry 5 }

juniMplsIfMajorLdpProfileName OBJECT-TYPE
    SYNTAX      DisplayString (SIZE(0..20))
    MAX-ACCESS  read-create
    STATUS      current
    DESCRIPTION
        "All the LDP settings on the MPLS interface be will associated with the
        profile.  This object allows to associate those configured settings to
        interface by using the LDP profile name."
     DEFVAL    { "" }
    ::= { juniMplsIfMajorEntry 6 }

juniMplsIfMajorLdpVpiStart OBJECT-TYPE
    SYNTAX      JuniMajorCfgVpiRanges
    MAX-ACCESS  read-create
    STATUS      current
    DESCRIPTION
        "This object is defined to support configurations of interface label
        space.  This configures the start range of the LDP VPI.  For successful
        configuration of interface label space LDP VPI ranges, set this object
        with the stop range cunncurrently."
    DEFVAL    { 0 }
    ::= { juniMplsIfMajorEntry 7 }

juniMplsIfMajorLdpVpiStop OBJECT-TYPE
    SYNTAX      JuniMajorCfgVpiRanges
    MAX-ACCESS  read-create
    STATUS      current
    DESCRIPTION
        "This object is defined to support configurations of interface label
        space.  This configures the stop range of the LDP VPI.  For successful
        configuration of interface label space LDP VPI ranges, set this object
        with the start range cunncurrently."
    DEFVAL    { 0 }
    ::= { juniMplsIfMajorEntry 8 }

juniMplsIfMajorLdpVciStart OBJECT-TYPE
    SYNTAX      JuniMajorCfgVciRanges
    MAX-ACCESS  read-create
    STATUS      current
    DESCRIPTION
        "This object is defined to support configurations of interface label
        space.  This configures the start range of the LDP VCI.  For successful
        configuration of interface label space LDP VCI ranges, set this object
        with the stop range cunncurrently."
    ::= { juniMplsIfMajorEntry 9 }

juniMplsIfMajorLdpVciStop OBJECT-TYPE
    SYNTAX      JuniMajorCfgVciRanges
    MAX-ACCESS  read-create
    STATUS      current
    DESCRIPTION
        "This object is defined to support configurations of interface label
        space.  This configures the stop range of the LDP VCI.  For successful
        configuration of interface label space LDP VCI ranges, set this object
        with the start range cunncurrently."
    ::= { juniMplsIfMajorEntry 10 }

juniMplsIfMajorRsvpAdminStatus OBJECT-TYPE
    SYNTAX      INTEGER {
                    disable(0),
                    enable(1) }
    MAX-ACCESS  read-create
    STATUS      current
    DESCRIPTION
        "This object configures RSVP admin status for MPLS interface."
    DEFVAL    { enable }
    ::= { juniMplsIfMajorEntry 11 }

juniMplsIfMajorRsvpProfileName OBJECT-TYPE
    SYNTAX      DisplayString (SIZE(0..20))
    MAX-ACCESS  read-create
    STATUS      current
    DESCRIPTION
        "All the RSVP settings on the MPLS interface be will associated with the
        profile.  This object allows to associate those configured settings to
        interface by using the RSVP profile name."
    DEFVAL    { "" }
    ::= { juniMplsIfMajorEntry 12 }

juniMplsIfMajorRsvpVpiStart OBJECT-TYPE
    SYNTAX      JuniMajorCfgVpiRanges
    MAX-ACCESS  read-create
    STATUS      current
    DESCRIPTION
        "This object is defined to support configurations of interface label
        space.  This configures the start range of the RSVP VPI.  For successful
        configuration of interface label space RSVP VPI ranges, set this object
        with the stop range cunncurrently."
    DEFVAL    { 0 }
    ::= { juniMplsIfMajorEntry 13 }

juniMplsIfMajorRsvpVpiStop OBJECT-TYPE
    SYNTAX      JuniMajorCfgVpiRanges
    MAX-ACCESS  read-create
    STATUS      current
    DESCRIPTION
        "This object is defined to support configurations of interface label
        space.  This configures the stop range of the RSVP VPI.  For successful
        configuration of interface label space RSVP VPI ranges, set this object
        with the start range cunncurrently."
    DEFVAL    { 0 }
    ::= { juniMplsIfMajorEntry 14 }

juniMplsIfMajorRsvpVciStart OBJECT-TYPE
    SYNTAX      JuniMajorCfgVciRanges
    MAX-ACCESS  read-create
    STATUS      current
    DESCRIPTION
        "This object is defined to support configurations of interface label
        space.  This configures the start range of the RSVP VCI.  For successful
        configuration of interface label space RSVP VCI ranges, set this object
        with the stop range cunncurrently."
    ::= { juniMplsIfMajorEntry 15 }

juniMplsIfMajorRsvpVciStop OBJECT-TYPE
    SYNTAX      JuniMajorCfgVciRanges
    MAX-ACCESS  read-create
    STATUS      current
    DESCRIPTION
        "This object is defined to support configurations of interface label
        space.  This configures the stop range of the RSVP VCI.  For successful
        configuration of interface label space RSVP VCI ranges, set this object
        with the start range cunncurrently."
    ::= { juniMplsIfMajorEntry 16 }

juniMplsIfMajorLabelSpaceType OBJECT-TYPE
    SYNTAX      INTEGER {
                    none(0),
                    rsvpVpiVci(1),
                    rsvpVpi(2),
                    rsvpVci(3),
                    ldpVpiVci(4),
                    ldpVpi(5),
                    ldpVci(6) }
    MAX-ACCESS  read-only
    STATUS      current
    DESCRIPTION
        "Displays the label space type for the MPLS interface."
    ::= { juniMplsIfMajorEntry  17 }

juniMplsIfMajorOpState OBJECT-TYPE
    SYNTAX      INTEGER {
                    lowerLayerNotAvailable(0),
                    lowerLayerDown(1),
                    up(2),
                    configIncompleteInterfaceEnabled(3),
                    configIncompleteInterfaceDisabled(4),
                    interfaceDisabled(5) }
    MAX-ACCESS  read-only
    STATUS      current
    DESCRIPTION
        "This object displays MPLS major interface operation state."
    ::= { juniMplsIfMajorEntry 18 }

juniMplsIfMajorCrLdpAdminState OBJECT-TYPE
    SYNTAX      INTEGER {
                    disable(0),
                    enable(1) }
    MAX-ACCESS  read-only
    STATUS      obsolete
    DESCRIPTION
        "This object displays the admin state of CR-LDP."
    ::= { juniMplsIfMajorEntry  19 }


-- //////////////////////////////////////////////////////////////////////
--
-- MPLS  MINOR INTERFACE LAYER
--
-- The set of obejcts supports the MPLS tunnel interface specific
-- configurations.
--
-- Management objects are provided to query for an available interface index,
-- and to create/delete interface of this type.
-- Creating/deleting interface of this type using this MIB has
-- the side effect of creating/deleting corresponding entries
-- in the Interface MIB ifTable/ifXTable, and in the Juniper
-- Enterprise Interface MIB juniIfTable.
--
-- //////////////////////////////////////////////////////////////////////
--
-- IfIndex selection for creating new MPLS Minor interfaces
--
juniMplsIfMinorNextIfIndex OBJECT-TYPE
    SYNTAX      JuniNextIfIndex
    MAX-ACCESS  read-only
    STATUS      current
    DESCRIPTION
        "Coordinates ifIndex value allocation for entries in the
        juniMplsIfMinorTable.  A GET of this object returns the next available
        ifIndex value to be used to create an entry in the associated interface
        table; or zero, if no valid ifIndex value is available.  This object
        also returns a value of zero when it is the lexicographic successor of a
        varbind presented in an SNMP GETNEXT or GETBULK request, for which
        circumstance it is assumed that ifIndex allocation is unintended.

        Successive GETs will typically return different values, thus avoiding
        collisions among cooperating management clients seeking to create table
        entries simultaneously."
    ::= { juniMplsIfMinorLayer 1 }

--
-- The MPLS Minor Interface Table
--
juniMplsIfMinorTable OBJECT-TYPE
    SYNTAX      SEQUENCE OF JuniMplsIfMinorEntry
    MAX-ACCESS  not-accessible
    STATUS      current
    DESCRIPTION
        "This table contains entries for MPLS Minor interfaces present in the
        system."
    ::= { juniMplsIfMinorLayer 2 }

juniMplsIfMinorEntry OBJECT-TYPE
    SYNTAX      JuniMplsIfMinorEntry
    MAX-ACCESS  not-accessible
    STATUS      current
    DESCRIPTION
        "Each entry describes the characteristics of an MPLS Minor interface.
        Creating/deleting entries in this table causes corresponding entries for
        be created/deleted in ifTable/ifXTable/juniIfTable."
    INDEX     { juniMplsIfMinorIndex }
    ::= { juniMplsIfMinorTable 1 }

JuniMplsIfMinorEntry ::= SEQUENCE {
    juniMplsIfMinorIndex                    InterfaceIndex,
    juniMplsIfMinorRowStatus                RowStatus,
    juniMplsIfMinorLowerIfIndex             InterfaceIndexOrZero,
    juniMplsIfMinorAdminStatus              INTEGER,
    juniMplsIfMinorEndpointAddress          IpAddress,
    juniMplsIfMinorEndpointDstMask          IpAddress,
    juniMplsIfMinorTunnelMetricMode         INTEGER,
    juniMplsIfMinorAbsoluteTunnelMetric     Unsigned32,
    juniMplsIfMinorRelativeTunnelMetric     Integer32,
    juniMplsIfMinorLabelDistProto           INTEGER,
    juniMplsIfMinorAnnounceToOspf           TruthValue,
    juniMplsIfMinorAnnounceToIsis           TruthValue,
    juniMplsIfMinorAnnounceToBgp            TruthValue,
    juniMplsIfMinorBandwidth                JuniMinorCfgBWRanges,
    juniMplsIfMinorAffinity                 OCTET STRING,
    juniMplsIfMinorAffinityMask             OCTET STRING,
    juniMplsIfMinorSetupPriority
        JuniMinorCfgHoldingAndSetupPriorityRanges,
    juniMplsIfMinorHoldingPriority
        JuniMinorCfgHoldingAndSetupPriorityRanges,
    juniMplsIfMinorTunnelName               DisplayString,
    juniMplsIfMinorTunnelRetryTimes
        JuniMinorCfgRetryTimesAndNorouteRanges,
    juniMplsIfMinorTunnelRetryInterval
        JuniMinorCfgRetryIntervalAndNorouteRanges,
    juniMplsIfMinorTunnelRetryTimesNoroute
        JuniMinorCfgRetryTimesAndNorouteRanges,
    juniMplsIfMinorTunnelRetryIntervalNoroute
        JuniMinorCfgRetryIntervalAndNorouteRanges,
    juniMplsIfMinorBaseTunnelName           DisplayString,
    juniMplsIfMinorVpnOuiNumber             Integer32,
    juniMplsIfMinorVpnIndex                 IpAddress,
    juniMplsIfMinorTunnelOpState            INTEGER,
    juniMplsIfMinorTargetedDynamicTunnel    TruthValue,
    juniMplsIfMinorReoptimization           TruthValue }

juniMplsIfMinorIndex OBJECT-TYPE
    SYNTAX      InterfaceIndex
    MAX-ACCESS  not-accessible
    STATUS      current
    DESCRIPTION
        "The ifIndex of the MPLS Minor interface.  When creating entries in this
        table, suitable values for this object are determined by reading
        juniMplsMinorNextIfIndex."
    ::= { juniMplsIfMinorEntry 1 }

juniMplsIfMinorRowStatus OBJECT-TYPE
    SYNTAX      RowStatus
    MAX-ACCESS  read-create
    STATUS      current
    DESCRIPTION
        "Controls creation/deletion of entries in this table according to the
        RowStatus textual convention, constrained to support the following
        values only:
            createAndGo
            destroy

        To create/delete an entry in this table, the following entry objects
        MUST be explicitly configured:
            juniMplsIfMinorRowStatus
            juniMplsIfMinorTunnelName

        In addition, when creating an entry the following conditions must hold:
            A value for juniMplsIfMinorIndex must have been determined
            previously, by reading juniMplsMinorNextIfIndex.

        A corresponding entry in ifTable/ifXTable/juniIfTable is created/
        destroyed as a result of creating/destroying an entry in this table."
    ::= { juniMplsIfMinorEntry 2 }

juniMplsIfMinorLowerIfIndex OBJECT-TYPE
    SYNTAX      InterfaceIndexOrZero
    MAX-ACCESS  read-only
    STATUS      current
    DESCRIPTION
        "The ifIndex of an interface over which this MPLS Minor interface is to
        be layered.  A value of zero indicates no layering. As minor interface
        can be created without stacking on major interface, as and when it
        stacks on major interface by signalling protocol, it's value can be
        read."
    ::= { juniMplsIfMinorEntry 3 }

juniMplsIfMinorAdminStatus OBJECT-TYPE
    SYNTAX      INTEGER {
                    disable(0),
                    enable(1) }
    MAX-ACCESS  read-create
    STATUS      current
    DESCRIPTION
        "With this object minor interface admin status can be enabled/disabled."
    ::= { juniMplsIfMinorEntry 4 }

juniMplsIfMinorEndpointAddress OBJECT-TYPE
    SYNTAX      IpAddress
    MAX-ACCESS  read-create
    STATUS      current
    DESCRIPTION
        "This object configures the IP address of the tunnel destination.  This
        object can be set along with the juniMplsIfMinorEndpointDstMask to
        configure the tunnel destination mask, but it is optional."
    ::= { juniMplsIfMinorEntry 5 }

juniMplsIfMinorEndpointDstMask OBJECT-TYPE
    SYNTAX      IpAddress
    MAX-ACCESS  read-create
    STATUS      current
    DESCRIPTION
        "This object configures the tunnel destination mask.  It can be set
        along with the juniMplsIfMinorEndpointAddress."
    DEFVAL    { 0 }
    ::= { juniMplsIfMinorEntry 6 }

juniMplsIfMinorTunnelMetricMode OBJECT-TYPE
    SYNTAX      INTEGER {
                    absolute(0),
                    relative(1) }
    MAX-ACCESS  read-create
    STATUS      current
    DESCRIPTION
        "Select the relative or absolute mode to configure the absolute or
        relative tunnel metric.  To set the tunnel to relative metric,
        juniMplsIfMinorRelativeTunnelMetric has to be set along with this object
        option as relative.  To set the tunnel to absolute metric,
        juniMplsIfMinorAbsoluteTunnelMetric has to be set along with this object
        option as absolute."
    ::= { juniMplsIfMinorEntry  7 }

juniMplsIfMinorAbsoluteTunnelMetric OBJECT-TYPE
    SYNTAX      Unsigned32 (1..4294967295)
    MAX-ACCESS  read-create
    STATUS      current
    DESCRIPTION
        "This object allows configuration of absolute metric values.  Refer to
        juniMplsIfMinorTunnelMetricMode for how set it."
    ::= { juniMplsIfMinorEntry  8 }

juniMplsIfMinorRelativeTunnelMetric OBJECT-TYPE
    SYNTAX      Integer32 (-10..10)
    MAX-ACCESS  read-create
    STATUS      current
    DESCRIPTION
        "This object allows configuration of relative metric values.  Refer to
        juniMplsIfMinorTunnelMetricMode for how set it."
    ::= { juniMplsIfMinorEntry 9 }

juniMplsIfMinorLabelDistProto OBJECT-TYPE
    SYNTAX      INTEGER {
                    crLdp(0),
                    rsvpTe(1),
                    undefined(2) }
    MAX-ACCESS  read-create
    STATUS      obsolete
    DESCRIPTION
        "This object allows to select label distribution protocol.  Label
        distribution protocols are used by two LSRs to negotiate label to FEC
        binding to set up tunnels."
    ::= { juniMplsIfMinorEntry 10 }

juniMplsIfMinorAnnounceToOspf OBJECT-TYPE
    SYNTAX      TruthValue
    MAX-ACCESS  read-create
    STATUS      current
    DESCRIPTION
        "This object allows to register LSP endpoints to OSPF to next hop
        calculation."
    DEFVAL    { false }
    ::= { juniMplsIfMinorEntry 11 }

juniMplsIfMinorAnnounceToIsis OBJECT-TYPE
    SYNTAX      TruthValue
    MAX-ACCESS  read-create
    STATUS      current
    DESCRIPTION
        "This object allows to register LSP endpoints to IS-IS for next hop
        calculation."
    DEFVAL    { false }
    ::= { juniMplsIfMinorEntry 12 }

juniMplsIfMinorAnnounceToBgp OBJECT-TYPE
    SYNTAX      TruthValue
    MAX-ACCESS  read-create
    STATUS      current
    DESCRIPTION
        "This object allows to register LSP endpoints to BGP for next hop
        calculation."
    DEFVAL    { false }
    ::= { juniMplsIfMinorEntry 13 }

juniMplsIfMinorBandwidth OBJECT-TYPE
    SYNTAX      JuniMinorCfgBWRanges
    MAX-ACCESS  read-create
    STATUS      current
    DESCRIPTION
        "This object allows configuration of bandwidth requirements for the
         tunnel."
    DEFVAL    { 0 }
    ::= { juniMplsIfMinorEntry 14 }

juniMplsIfMinorAffinity OBJECT-TYPE
    SYNTAX      OCTET STRING (SIZE(0..4))
    MAX-ACCESS  read-create
    STATUS      current
    DESCRIPTION
        "This object allows configuration of resource class affinity for the
        tunnel."
    DEFVAL    { '00000000'H }
    ::= { juniMplsIfMinorEntry 15 }

juniMplsIfMinorAffinityMask OBJECT-TYPE
    SYNTAX      OCTET STRING (SIZE(0..4))
    MAX-ACCESS  read-create
    STATUS      current
    DESCRIPTION
        "This allows to set the resource class affinity mask.  Since it is a
        mask, set along with the affinity for successful configurations."
    DEFVAL    { '0000ffff'H }
    ::= { juniMplsIfMinorEntry 16 }

juniMplsIfMinorSetupPriority OBJECT-TYPE
    SYNTAX      JuniMinorCfgHoldingAndSetupPriorityRanges
    MAX-ACCESS  read-create
    STATUS      current
    DESCRIPTION
        "This object allows configuration of preemption setup priority for the
        tunnel before and after it has been established.  Lower the value higher
        the priority."
    ::= { juniMplsIfMinorEntry 17 }

juniMplsIfMinorHoldingPriority OBJECT-TYPE
    SYNTAX      JuniMinorCfgHoldingAndSetupPriorityRanges
    MAX-ACCESS  read-create
    STATUS      current
    DESCRIPTION
        "This object allows configuration of the preemption holding priority for
        the tunnel before and after it has been established.  Lower the value
        higher the priority."
    ::= { juniMplsIfMinorEntry 18 }

juniMplsIfMinorTunnelName OBJECT-TYPE
    SYNTAX      DisplayString (SIZE(0..20))
    MAX-ACCESS  read-create
    STATUS      current
    DESCRIPTION
        "This object allows configuration of the tunnel name to be associated
        with tunnel settings."
    ::= { juniMplsIfMinorEntry 19 }

juniMplsIfMinorTunnelRetryTimes OBJECT-TYPE
    SYNTAX      JuniMinorCfgRetryTimesAndNorouteRanges
    MAX-ACCESS  read-create
    STATUS      current
    DESCRIPTION
        "This object allows configuration of the number of retries for tunnel
        setup."
    DEFVAL    { 0 }
    ::= { juniMplsIfMinorEntry 20 }

juniMplsIfMinorTunnelRetryInterval OBJECT-TYPE
    SYNTAX      JuniMinorCfgRetryIntervalAndNorouteRanges
    MAX-ACCESS  read-create
    STATUS      current
    DESCRIPTION
        "This object allows configuration of retry interval for tunnel setup."
    DEFVAL    { 5 }
    ::= { juniMplsIfMinorEntry 21 }

juniMplsIfMinorTunnelRetryTimesNoroute OBJECT-TYPE
    SYNTAX      JuniMinorCfgRetryTimesAndNorouteRanges
    MAX-ACCESS  read-create
    STATUS      current
    DESCRIPTION
        "This object allows configuration of the tunnel retries when no route
        notifications are received."
    DEFVAL    { 0 }
    ::= { juniMplsIfMinorEntry 22 }

juniMplsIfMinorTunnelRetryIntervalNoroute OBJECT-TYPE
    SYNTAX      JuniMinorCfgRetryIntervalAndNorouteRanges
    MAX-ACCESS  read-create
    STATUS      current
    DESCRIPTION
        "This object allows configuration of the tunnel retry interval when no
        route notifications are received."
    DEFVAL    { 5 }
    ::= { juniMplsIfMinorEntry 23 }

juniMplsIfMinorBaseTunnelName OBJECT-TYPE
    SYNTAX      DisplayString
    MAX-ACCESS  read-create
    STATUS      obsolete
    DESCRIPTION
        "This object allows configuration of the base tunnel name over which all
        the tunnels are stacked over."
    DEFVAL    { "" }
    ::= { juniMplsIfMinorEntry 24 }

juniMplsIfMinorVpnOuiNumber OBJECT-TYPE
    SYNTAX      Integer32 (0..16777215)
    MAX-ACCESS  read-create
    STATUS      obsolete
    DESCRIPTION
        "This object allows configuration of the OUI part of VPN ID."
    ::= { juniMplsIfMinorEntry 25 }

juniMplsIfMinorVpnIndex OBJECT-TYPE
    SYNTAX      IpAddress
    MAX-ACCESS  read-create
    STATUS      obsolete
    DESCRIPTION
        "This object allows configuration of the index part of VPN ID."
    ::= { juniMplsIfMinorEntry 26 }

juniMplsIfMinorTunnelOpState OBJECT-TYPE
    SYNTAX      INTEGER {
                    established(0),
                    teNegotiation(1),
                    up(2),
                    down(3),
                    cfgChanged(4),
                    cfgIncEn(5),
                    cfgIncDis(6),
                    disabled(7),
                    rel(8),
                    noChange(9) }
    MAX-ACCESS  read-only
    STATUS      current
    DESCRIPTION
        "This object displays the tunnel operation state.
             established    : Tunnel established
             teNegotiation  : TE Negotiation
             up             : Tunnel Up
             down           : Tunnel Down
             cfgChanged     : Tunnel config changed
             cfgIncEn       : Tunnel incomplete Config Admin State Enable
             cfgIncDis      : Tunnel incomplete Config Admin State Disable
             disabled       : Tunnel disabled
             rel            :
             noChange       : Tunnel state no change "
    ::= { juniMplsIfMinorEntry 27 }

juniMplsIfMinorTargetedDynamicTunnel OBJECT-TYPE
    SYNTAX      TruthValue
    MAX-ACCESS  read-create
    STATUS      obsolete
    DESCRIPTION
        "Configure targeted dynamic tunnel."
    DEFVAL    { false }
    ::= { juniMplsIfMinorEntry 28 }

juniMplsIfMinorReoptimization OBJECT-TYPE
    SYNTAX      TruthValue
    MAX-ACCESS  read-create
    STATUS      current
    DESCRIPTION
        "Configure tunnel reoptimization."
    DEFVAL    { false }
    ::= { juniMplsIfMinorEntry 29 }


--
-- Path Option table for minor interface
--
juniMplsIfMinorPathOptionTable OBJECT-TYPE
    SYNTAX      SEQUENCE OF JuniMplsIfMinorPathOptionEntry
    MAX-ACCESS  not-accessible
    STATUS      current
    DESCRIPTION
        "Table is a list of different LSP paths as option for each LSP setup."
    ::= { juniMplsMinorLayerList 1 }

juniMplsIfMinorPathOptionEntry OBJECT-TYPE
    SYNTAX      JuniMplsIfMinorPathOptionEntry
    MAX-ACCESS  not-accessible
    STATUS      current
    DESCRIPTION
        "Each entry represents one path option for the LSP."
    INDEX     { juniMplsIfMinorPathOptionIndex,
                juniMplsIfMinorPathOptionNumber }
    ::= { juniMplsIfMinorPathOptionTable 1 }

JuniMplsIfMinorPathOptionEntry ::= SEQUENCE {
    juniMplsIfMinorPathOptionIndex       InterfaceIndex,
    juniMplsIfMinorPathOptionNumber      Integer32,
    juniMplsIfMinorPathOptionProtocol    INTEGER,
    juniMplsIfMinorPathOptionLockdown    TruthValue,
    juniMplsIfMinorPathOptionPathName    DisplayString,
    juniMplsIfMinorPathOptionPathId      Integer32,
    juniMplsIfMinorPathOptionRowStatus   RowStatus }

juniMplsIfMinorPathOptionIndex OBJECT-TYPE
    SYNTAX      InterfaceIndex
    MAX-ACCESS  not-accessible
    STATUS      current
    DESCRIPTION
        "Minor interface unique ID."
    ::= { juniMplsIfMinorPathOptionEntry 1 }

juniMplsIfMinorPathOptionNumber OBJECT-TYPE
    SYNTAX      Integer32 (1..1000)
    MAX-ACCESS  not-accessible
    STATUS      current
    DESCRIPTION
        "Unique number to identify each path option configured."
    ::= { juniMplsIfMinorPathOptionEntry 2 }

juniMplsIfMinorPathOptionProtocol OBJECT-TYPE
    SYNTAX      INTEGER {
                    hopByHop(0),
                    isis(1),
                    ospf(2),
                    none(3) }
    MAX-ACCESS  read-create
    STATUS      current
    DESCRIPTION
        "Select the each path option explicit routing protocol."
    ::= { juniMplsIfMinorPathOptionEntry 3 }

juniMplsIfMinorPathOptionLockdown OBJECT-TYPE
    SYNTAX      TruthValue
    MAX-ACCESS  read-create
    STATUS      current
    DESCRIPTION
        "Enable/disable each configured path option reoptimization."
    ::= { juniMplsIfMinorPathOptionEntry 4 }

juniMplsIfMinorPathOptionPathName OBJECT-TYPE
    SYNTAX      DisplayString (SIZE(0..20))
    MAX-ACCESS  read-create
    STATUS      current
    DESCRIPTION
        "Configure the name for each path option."
    ::= { juniMplsIfMinorPathOptionEntry 5 }

juniMplsIfMinorPathOptionPathId OBJECT-TYPE
    SYNTAX      Integer32 (1..65535)
    MAX-ACCESS  read-create
    STATUS      current
    DESCRIPTION
        "Configure the path option ID.  Either the name or ID will be associated
        with a path at a time.  If the path name and ID are set at a same time
        for the path, the name will have precedence over ID."
    ::= { juniMplsIfMinorPathOptionEntry 6 }

juniMplsIfMinorPathOptionRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniMplsIfMinorPathOptionRowStatus."
    ::= { juniMplsIfMinorPathOptionEntry 7 }


-- //////////////////////////////////////////////////////////////////////
--
-- MPLS Tunnel Profile
--
-- //////////////////////////////////////////////////////////////////////
--
-- The MPLS Tunnel Profile Table
--
juniMplsTunnelProfileTable OBJECT-TYPE
    SYNTAX      SEQUENCE OF JuniMplsTunnelProfileEntry
    MAX-ACCESS  not-accessible
    STATUS      current
    DESCRIPTION
        "Table is a list of tunnel profiles for a given VR."
    ::= { juniMplsTunnelProfileGroup 1 }

juniMplsTunnelProfileEntry OBJECT-TYPE
    SYNTAX      JuniMplsTunnelProfileEntry
    MAX-ACCESS  not-accessible
    STATUS      current
    DESCRIPTION
        "Each entry represents one tunnel profile."
    INDEX     { juniMplsTunnelProfileName }
    ::= { juniMplsTunnelProfileTable 1 }

JuniMplsTunnelProfileEntry ::= SEQUENCE {
    juniMplsTunnelProfileName                    DisplayString,
    juniMplsTunnelProfileAdminStatus             INTEGER,
    juniMplsTunnelProfileBaseTunnelName          DisplayString,
    juniMplsTunnelProfileIpProfileName           DisplayString,
    juniMplsTunnelProfileLabelDistProto          INTEGER,
    juniMplsTunnelProfileAnnounceToOspf          TruthValue,
    juniMplsTunnelProfileAnnounceToIsis          TruthValue,
    juniMplsTunnelProfileAnnounceToBgp           TruthValue,
    juniMplsTunnelProfileMetricMode              INTEGER,
    juniMplsTunnelProfileAbsoluteMetric          Unsigned32,
    juniMplsTunnelProfileRelativeMetric          Integer32,
    juniMplsTunnelProfileBandwidth               JuniProfileCfgBWRanges,
    juniMplsTunnelProfileAffinity                OCTET STRING,
    juniMplsTunnelProfileAffinityMask            OCTET STRING,
    juniMplsTunnelProfileSetupPriority
        JuniProfileCfgHoldingAndSetupPriorityRanges,
    juniMplsTunnelProfileHoldingPriority
        JuniProfileCfgHoldingAndSetupPriorityRanges,
    juniMplsTunnelProfileRetryTimes
        JuniProfileCfgRetryTimesAndNorouteRanges,
    juniMplsTunnelProfileRetryInterval
        JuniProfileCfgRetryIntervalAndNorouteRanges,
    juniMplsTunnelProfileRetryTimesNoroute
        JuniProfileCfgRetryTimesAndNorouteRanges,
    juniMplsTunnelProfileRetryIntervalNoroute
        JuniProfileCfgRetryIntervalAndNorouteRanges,
    juniMplsTunnelProfileVpnOuiNumber            Integer32,
    juniMplsTunnelProfileVpnIndex                IpAddress,
    juniMplsTunnelProfileRowStatus               RowStatus,
    juniMplsTunnelProfileTargetedDynamicTunnel   TruthValue }

juniMplsTunnelProfileName OBJECT-TYPE
    SYNTAX      DisplayString (SIZE(0..20))
    MAX-ACCESS  not-accessible
    STATUS      current
    DESCRIPTION
        "Associate a name for the configured tunnel profile settings."
    ::= { juniMplsTunnelProfileEntry 1 }

juniMplsTunnelProfileAdminStatus OBJECT-TYPE
    SYNTAX      INTEGER {
                    disable(0),
                    enable(1) }
    MAX-ACCESS  read-create
    STATUS      current
    DESCRIPTION
        "Enable/disable the adminstatus of the tunnel profile."
    ::= { juniMplsTunnelProfileEntry 2 }

juniMplsTunnelProfileBaseTunnelName OBJECT-TYPE
    SYNTAX      DisplayString
    MAX-ACCESS  read-create
    STATUS      obsolete
    DESCRIPTION
        "Configure the base tunnel name in tunnel profile settings.  This base
        tunnel is the one over which all the other tunnels are stacked over.
        Configured base tunnel name in profile settings will be associated with
        the actual configured base tunnel name."
    DEFVAL    { "" }
    ::= { juniMplsTunnelProfileEntry 3 }

juniMplsTunnelProfileIpProfileName OBJECT-TYPE
    SYNTAX      DisplayString (SIZE(0..20))
    MAX-ACCESS  read-create
    STATUS      current
    DESCRIPTION
        "Configures the name for IP profile settings for the IP interfaces over
        which MPLS tunnels are stacked."
    DEFVAL    { "" }
    ::= { juniMplsTunnelProfileEntry 4 }

juniMplsTunnelProfileLabelDistProto OBJECT-TYPE
    SYNTAX      INTEGER {
                    crLdp(0),
                    rsvpTe(1),
                    undefined(2) }
    MAX-ACCESS  read-create
    STATUS      obsolete
    DESCRIPTION
        "Configure the label distribution protocol to associate with a tunnel
        profile.  Label distribution protocols are used by two LSRs to negotiate
        label to FEC binding to set up tunnels."
    DEFVAL    { undefined }
    ::= { juniMplsTunnelProfileEntry 5 }

juniMplsTunnelProfileAnnounceToOspf OBJECT-TYPE
    SYNTAX      TruthValue
    MAX-ACCESS  read-create
    STATUS      current
    DESCRIPTION
        "Configure the routing protocol for next hop calculations as OSPF."
    DEFVAL    { false }
    ::= { juniMplsTunnelProfileEntry 6 }

juniMplsTunnelProfileAnnounceToIsis OBJECT-TYPE
    SYNTAX      TruthValue
    MAX-ACCESS  read-create
    STATUS      current
    DESCRIPTION
        "Configure routing protocol for next hop calculations as ISIS."
    DEFVAL    { false }
    ::= { juniMplsTunnelProfileEntry 7 }

juniMplsTunnelProfileAnnounceToBgp OBJECT-TYPE
    SYNTAX      TruthValue
    MAX-ACCESS  read-create
    STATUS      current
    DESCRIPTION
        "Configure routing protocol for next hop calculations as BGP."
    DEFVAL    { false }
    ::= { juniMplsTunnelProfileEntry 8 }

juniMplsTunnelProfileMetricMode OBJECT-TYPE
    SYNTAX      INTEGER {
                    absolute(0),
                    relative(1) }
    MAX-ACCESS  read-create
    STATUS      current
    DESCRIPTION
        "Select the relative or absolute mode to configure the absolute or
        relative tunnel profile metric.  To set the tunnel profile to relative
        metric, juniMplsTunnelProfileRelativeMetric has to be set along with
        this object option as relative.  To set the tunnel profile to absolute
        metric, juniMplsTunnelProfileAbsoluteMetric has to be set along with
        this object option as absolute."
    ::= { juniMplsTunnelProfileEntry 9 }

juniMplsTunnelProfileAbsoluteMetric OBJECT-TYPE
    SYNTAX      Unsigned32 (1..4294967295)
    MAX-ACCESS  read-create
    STATUS      current
    DESCRIPTION
        "This object allows configuration of the absolute metric values.  Refer
        to juniMplsTunnelProfileMetricMode for how set it."
    ::= { juniMplsTunnelProfileEntry 10 }

juniMplsTunnelProfileRelativeMetric OBJECT-TYPE
    SYNTAX      Integer32 (-10..10)
    MAX-ACCESS  read-create
    STATUS      current
    DESCRIPTION
        "This object allows configuration of the relative metric values.  Refer
        to juniMplsTunnelProfileMetricMode for how set it."
    ::= { juniMplsTunnelProfileEntry 11 }

juniMplsTunnelProfileBandwidth OBJECT-TYPE
    SYNTAX      JuniProfileCfgBWRanges
    MAX-ACCESS  read-create
    STATUS      current
    DESCRIPTION
        "This object allows configuration of bandwidth requirements for the
        tunnel."
    DEFVAL    { 0 }
    ::= { juniMplsTunnelProfileEntry 12 }

juniMplsTunnelProfileAffinity OBJECT-TYPE
    SYNTAX      OCTET STRING (SIZE(0..4))
    MAX-ACCESS  read-create
    STATUS      current
    DESCRIPTION
        "This object allows configuration of the resource class affinity for the
        tunnel.  This can set independently of
        juniMplsTunnelProfileAffinityMask."
    DEFVAL    { '00000000'H }
    ::= { juniMplsTunnelProfileEntry 13 }

juniMplsTunnelProfileAffinityMask OBJECT-TYPE
    SYNTAX      OCTET STRING (SIZE(0..4))
    MAX-ACCESS  read-create
    STATUS      current
    DESCRIPTION
        "This allows configuration of which bits in the affinity must match the
        resource class bits.  Can't be set independently; always with
        juniMplsTunnelProfileAffinity.  Specify the value in bit mask format."
    DEFVAL    { '0000ffff'H }
    ::= { juniMplsTunnelProfileEntry 14 }

juniMplsTunnelProfileSetupPriority OBJECT-TYPE
    SYNTAX      JuniProfileCfgHoldingAndSetupPriorityRanges
    MAX-ACCESS  read-create
    STATUS      current
    DESCRIPTION
        "This object configuration of the preemption setup priority for the
        tunnel before and after it has been established.  Lower the value higher
        the priority."
    DEFVAL    { 0 }
    ::= { juniMplsTunnelProfileEntry 15 }

juniMplsTunnelProfileHoldingPriority OBJECT-TYPE
    SYNTAX      JuniProfileCfgHoldingAndSetupPriorityRanges
    MAX-ACCESS  read-create
    STATUS      current
    DESCRIPTION
        "This object allows configuration of the preemption holding priority for
        the tunnel before and after it has been established.  Lower the value
        higher the priority."
    DEFVAL    { 0 }
    ::= { juniMplsTunnelProfileEntry 16 }

juniMplsTunnelProfileRetryTimes OBJECT-TYPE
    SYNTAX      JuniProfileCfgRetryTimesAndNorouteRanges
    MAX-ACCESS  read-create
    STATUS      current
    DESCRIPTION
        "This object allows configuration of the number of retries for the
        tunnel setup."
    DEFVAL    { 0 }
    ::= { juniMplsTunnelProfileEntry 17 }

juniMplsTunnelProfileRetryInterval OBJECT-TYPE
    SYNTAX      JuniProfileCfgRetryIntervalAndNorouteRanges
    MAX-ACCESS  read-create
    STATUS      current
    DESCRIPTION
        "This object allows configuration of retry interval for tunnel setup."
    DEFVAL    { 5 }
    ::= { juniMplsTunnelProfileEntry 18 }

juniMplsTunnelProfileRetryTimesNoroute OBJECT-TYPE
    SYNTAX      JuniProfileCfgRetryTimesAndNorouteRanges
    MAX-ACCESS  read-create
    STATUS      current
    DESCRIPTION
        "This object allows configuration of the tunnel retries when no route
        notifications are received."
    DEFVAL    { 0 }
    ::= { juniMplsTunnelProfileEntry 19 }

juniMplsTunnelProfileRetryIntervalNoroute OBJECT-TYPE
    SYNTAX      JuniProfileCfgRetryIntervalAndNorouteRanges
    MAX-ACCESS  read-create
    STATUS      current
    DESCRIPTION
        "This object allows configuration of the tunnel retry interval when no
        route notifications are received."
    DEFVAL    { 5 }
    ::= { juniMplsTunnelProfileEntry 20 }

juniMplsTunnelProfileVpnOuiNumber OBJECT-TYPE
    SYNTAX      Integer32 (0..16777215)
    MAX-ACCESS  read-create
    STATUS      obsolete
    DESCRIPTION
        "This object allows configuration of the OUI part of VPN ID."
    ::= { juniMplsTunnelProfileEntry 21 }

juniMplsTunnelProfileVpnIndex OBJECT-TYPE
    SYNTAX      IpAddress
    MAX-ACCESS  read-create
    STATUS      obsolete
    DESCRIPTION
        "This object allows configuration of the index part of VPN ID."
    ::= { juniMplsTunnelProfileEntry 22 }

juniMplsTunnelProfileRowStatus OBJECT-TYPE
    SYNTAX      RowStatus
    MAX-ACCESS  read-create
    STATUS      current
    DESCRIPTION
        "Controls creation/deletion of entries in this table according to the
        RowStatus textual convention, constrained to support the following
        values only:
           createAndGo
           destroy

       To create an entry in this table, the following entry objects MUST be
       explicitly configured:
           juniMplsTunnelProfileRowStatus "
   ::= { juniMplsTunnelProfileEntry 23 }

juniMplsTunnelProfileTargetedDynamicTunnel OBJECT-TYPE
    SYNTAX      TruthValue
    MAX-ACCESS  read-create
    STATUS      obsolete
    DESCRIPTION
        "Configure targeted dynamic tunnel."
    DEFVAL    { false }
    ::= { juniMplsTunnelProfileEntry 24 }


--
-- Path Option table for tunnel profile
--
juniMplsTunnelProfilePathOptionTable OBJECT-TYPE
    SYNTAX      SEQUENCE OF JuniMplsTunnelProfilePathOptionEntry
    MAX-ACCESS  not-accessible
    STATUS      current
    DESCRIPTION
        "Table is a list of different LSP paths as option for each LSP setup,
        configured as part of tunnel profile settings"
    ::= { juniMplsTunnelProfileList 1 }

juniMplsTunnelProfilePathOptionEntry OBJECT-TYPE
    SYNTAX      JuniMplsTunnelProfilePathOptionEntry
    MAX-ACCESS  not-accessible
    STATUS      current
    DESCRIPTION
        "Each entry represents one path option for the LSP setup, configured as
        a part of tunnel profile settings."
    INDEX     { juniMplsTunnelProfileNamePathOption,
                juniMplsTunnelProfilePathOptionNumber }
    ::= { juniMplsTunnelProfilePathOptionTable 1 }

JuniMplsTunnelProfilePathOptionEntry ::= SEQUENCE {
    juniMplsTunnelProfileNamePathOption      DisplayString,
    juniMplsTunnelProfilePathOptionNumber    Integer32,
    juniMplsTunnelProfilePathOptionProtocol  INTEGER,
    juniMplsTunnelProfilePathOptionLockdown  TruthValue,
    juniMplsTunnelProfilePathOptionPathName  DisplayString,
    juniMplsTunnelProfilePathOptionPathId    Integer32,
    juniMplsTunnelProfilePathOptionRowStatus RowStatus }

juniMplsTunnelProfileNamePathOption OBJECT-TYPE
    SYNTAX      DisplayString (SIZE(0..20))
    MAX-ACCESS  not-accessible
    STATUS      current
    DESCRIPTION
        "Name of the path option."
    ::= { juniMplsTunnelProfilePathOptionEntry 1 }

juniMplsTunnelProfilePathOptionNumber OBJECT-TYPE
    SYNTAX      Integer32 (1..1000)
    MAX-ACCESS  not-accessible
    STATUS      current
    DESCRIPTION
        "Unique identifier for the path option."
    ::= { juniMplsTunnelProfilePathOptionEntry 2 }

juniMplsTunnelProfilePathOptionProtocol OBJECT-TYPE
    SYNTAX      INTEGER {
                    hopByHop(0),
                    isis(1),
                    ospf(2),
                    none(3) }
    MAX-ACCESS  read-create
    STATUS      current
    DESCRIPTION
        "Path selection option protocol."
    ::= { juniMplsTunnelProfilePathOptionEntry 3 }

juniMplsTunnelProfilePathOptionLockdown OBJECT-TYPE
    SYNTAX      TruthValue
    MAX-ACCESS  read-create
    STATUS      current
    DESCRIPTION
        "Enable/disable path selection option reoptimization."
    ::= { juniMplsTunnelProfilePathOptionEntry 4 }

juniMplsTunnelProfilePathOptionPathName OBJECT-TYPE
    SYNTAX      DisplayString (SIZE(0..20))
    MAX-ACCESS  read-create
    STATUS      current
    DESCRIPTION
        "Associate a name with each explicit path."
    ::= { juniMplsTunnelProfilePathOptionEntry 5 }

juniMplsTunnelProfilePathOptionPathId OBJECT-TYPE
    SYNTAX      Integer32 (1..65535)
    MAX-ACCESS  read-create
    STATUS      current
    DESCRIPTION
        "Each explicit path can be associated either name or ID.  This object
        allows configuration of the ID for the explicit path."
    ::= { juniMplsTunnelProfilePathOptionEntry 6 }

juniMplsTunnelProfilePathOptionRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
        juniMplsTunnelProfilePathOptionRowStatus."
    ::= { juniMplsTunnelProfilePathOptionEntry 7 }


--
-- Dynamic endpoint table for tunnel profile
--
juniMplsTunnelProfileDynamicEndpointTable OBJECT-TYPE
    SYNTAX      SEQUENCE OF JuniMplsTunnelProfileDynamicEndpointEntry
    MAX-ACCESS  not-accessible
    STATUS      current
    DESCRIPTION
        "This table contains entries for the dynamic endpoints configured for
        each tunnel profile."
   ::= { juniMplsTunnelProfileList 2 }

juniMplsTunnelProfileDynamicEndpointEntry OBJECT-TYPE
    SYNTAX      JuniMplsTunnelProfileDynamicEndpointEntry
    MAX-ACCESS  not-accessible
    STATUS      current
    DESCRIPTION
        "Dynamic endpoint entries for each tunnel profile."
    INDEX     { juniMplsTunnelProfileNameDynamicEndpoint,
                juniMplsTunnelProfileDynamicEndpointType,
                juniMplsTunnelProfileDynamicEndpointPolicyListType,
                juniMplsTunnelProfileDynamicEndpointListName }
    ::= { juniMplsTunnelProfileDynamicEndpointTable 1 }

JuniMplsTunnelProfileDynamicEndpointEntry ::= SEQUENCE {
    juniMplsTunnelProfileNameDynamicEndpoint             DisplayString,
    juniMplsTunnelProfileDynamicEndpointType             INTEGER,
    juniMplsTunnelProfileDynamicEndpointPolicyListType   INTEGER,
    juniMplsTunnelProfileDynamicEndpointListName         DisplayString,
    juniMplsTunnelProfileDynamicEndpointRowStatus        RowStatus }

juniMplsTunnelProfileNameDynamicEndpoint OBJECT-TYPE
    SYNTAX      DisplayString (SIZE(0..20))
    MAX-ACCESS  not-accessible
    STATUS      current
    DESCRIPTION
        "Configure the tunnel dynamic endpoint in tunnel profile settings."
    ::= { juniMplsTunnelProfileDynamicEndpointEntry 1 }

juniMplsTunnelProfileDynamicEndpointType OBJECT-TYPE
    SYNTAX      INTEGER {
                    isisLevel2(0),
                    ospfBorder(1) }
    MAX-ACCESS  not-accessible
    STATUS      current
    DESCRIPTION
        "Configure the dynamic endpoint type for the tunnel."
    ::= { juniMplsTunnelProfileDynamicEndpointEntry 2 }

juniMplsTunnelProfileDynamicEndpointPolicyListType OBJECT-TYPE
    SYNTAX      INTEGER {
                    accessList(1),
                    prefixList(2),
                    noPolicyList(3) }
    MAX-ACCESS  not-accessible
    STATUS      current
    DESCRIPTION
        "This object allows configuration of the dynamic tunnel policy type
        selection."
     ::= { juniMplsTunnelProfileDynamicEndpointEntry 3 }

juniMplsTunnelProfileDynamicEndpointListName OBJECT-TYPE
    SYNTAX      DisplayString (SIZE(0..20))
    MAX-ACCESS  not-accessible
    STATUS      current
    DESCRIPTION
        "This object allows configuration of the dynamic endpoints access list
        name."
     ::= { juniMplsTunnelProfileDynamicEndpointEntry 4 }

juniMplsTunnelProfileDynamicEndpointRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry object MUST be
        explicitly configured:
            juniMplsTunnelProfileDynamicEndpointRowStatus."
     ::= { juniMplsTunnelProfileDynamicEndpointEntry 5 }


--
-- Tunnel static endpoints table for tunnel profile
--
juniMplsTunnelProfileTunnelEndpointTable OBJECT-TYPE
    SYNTAX      SEQUENCE OF JuniMplsTunnelProfileTunnelEndpointEntry
    MAX-ACCESS  not-accessible
    STATUS      current
    DESCRIPTION
        "Table contains list of tunnel static enpoints configured for each
        tunnel profile."
   ::= { juniMplsTunnelProfileList 3 }

juniMplsTunnelProfileTunnelEndpointEntry OBJECT-TYPE
    SYNTAX      JuniMplsTunnelProfileTunnelEndpointEntry
    MAX-ACCESS  not-accessible
    STATUS      current
    DESCRIPTION
        "Each entry represents one static endpoint configuration for the
        tunnel."
    INDEX     { juniMplsTunnelProfileNameTunnelEndpoint,
                juniMplsTunnelProfileTunnelEndpointAddress,
                juniMplsTunnelProfileTunnelEndpointDstMask }
    ::= { juniMplsTunnelProfileTunnelEndpointTable 1 }

JuniMplsTunnelProfileTunnelEndpointEntry ::= SEQUENCE {
    juniMplsTunnelProfileNameTunnelEndpoint      DisplayString,
    juniMplsTunnelProfileTunnelEndpointAddress   IpAddress,
    juniMplsTunnelProfileTunnelEndpointDstMask   IpAddress,
    juniMplsTunnelProfileTunnelEndpointRowStatus RowStatus }

juniMplsTunnelProfileNameTunnelEndpoint OBJECT-TYPE
    SYNTAX      DisplayString (SIZE(0..20))
    MAX-ACCESS  not-accessible
    STATUS      current
    DESCRIPTION
        "This object configures the tunnel profile name."
    ::= { juniMplsTunnelProfileTunnelEndpointEntry 1 }

juniMplsTunnelProfileTunnelEndpointAddress OBJECT-TYPE
    SYNTAX      IpAddress
    MAX-ACCESS  not-accessible
    STATUS      current
    DESCRIPTION
        "This object configures the IP address of the tunnel destination."
    ::= { juniMplsTunnelProfileTunnelEndpointEntry 2 }

juniMplsTunnelProfileTunnelEndpointDstMask OBJECT-TYPE
    SYNTAX      IpAddress
    MAX-ACCESS  not-accessible
    STATUS      current
    DESCRIPTION
        "This object configures the tunnel destination mask.
	A value of 255.255.255.255 is expected."
   ::= { juniMplsTunnelProfileTunnelEndpointEntry 3 }

juniMplsTunnelProfileTunnelEndpointRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
        juniMplsTunnelProfileTunnelEndpointRowStatus."
     ::= { juniMplsTunnelProfileTunnelEndpointEntry 4 }



-- //////////////////////////////////////////////////////////////////////
--
-- Explicit Path Configurations
--
-- //////////////////////////////////////////////////////////////////////

--
-- Explicit Path Table
--
juniMplsExplicitPathTable OBJECT-TYPE
    SYNTAX      SEQUENCE OF JuniMplsExplicitPathEntry
    MAX-ACCESS  not-accessible
    STATUS      current
    DESCRIPTION
        "Table is a list of hops configurations for explicit paths."
    ::= { juniMplsExplicitPathGroup 1 }

juniMplsExplicitPathEntry OBJECT-TYPE
    SYNTAX      JuniMplsExplicitPathEntry
    MAX-ACCESS  not-accessible
    STATUS      current
    DESCRIPTION
        "Each entry represents one hop configuration for the particular
        explicit path."
    INDEX     { juniMplsExplicitPathName }
    ::= { juniMplsExplicitPathTable 1 }

JuniMplsExplicitPathEntry ::= SEQUENCE {
    juniMplsExplicitPathName         DisplayString,
    juniMplsExplicitPathAdminState   INTEGER,
    juniMplsExplicitPathRowStatus    RowStatus }

juniMplsExplicitPathName OBJECT-TYPE
    SYNTAX      DisplayString (SIZE(0..20))
    MAX-ACCESS  not-accessible
    STATUS      current
    DESCRIPTION
        "Configure the name for the explicit path used as table index."
    ::= { juniMplsExplicitPathEntry 1 }

juniMplsExplicitPathAdminState OBJECT-TYPE
    SYNTAX      INTEGER {
                    disable(0),
                    enable(1) }
    MAX-ACCESS  read-create
    STATUS      current
    DESCRIPTION
        "Enable/disable explicit path adminstatus."
    DEFVAL    { disable }
    ::= { juniMplsExplicitPathEntry 2 }

juniMplsExplicitPathRowStatus OBJECT-TYPE
    SYNTAX      RowStatus
    MAX-ACCESS  read-create
    STATUS      current
    DESCRIPTION
        "Creation/deletion of the explicit path is done through setting this
        object."
    ::= { juniMplsExplicitPathEntry 3 }

--
-- Explicit Path node Table
--
juniMplsExplicitPathNodeTable OBJECT-TYPE
    SYNTAX      SEQUENCE OF JuniMplsExplicitPathNodeEntry
    MAX-ACCESS  not-accessible
    STATUS      current
    DESCRIPTION
        "Table is a list of configured explicit paths."
    ::= { juniMplsExplicitPathGroup 2 }

juniMplsExplicitPathNodeEntry OBJECT-TYPE
    SYNTAX      JuniMplsExplicitPathNodeEntry
    MAX-ACCESS  not-accessible
    STATUS      current
    DESCRIPTION
        "Each entry represents one hop in a particular explicit path."
    INDEX     { juniMplsExplicitPathNodeName,
                juniMplsExplicitPathNodeIndexNumber }
    ::= { juniMplsExplicitPathNodeTable 1 }

JuniMplsExplicitPathNodeEntry ::= SEQUENCE {
    juniMplsExplicitPathNodeName             DisplayString,
    juniMplsExplicitPathNodeIndexNumber      Integer32,
    juniMplsExplicitPathNodeLoose            TruthValue,
    juniMplsExplicitPathNodeHopAddress       IpAddress,
    juniMplsExplicitPathNodeHopAddressMask   IpAddress,
    juniMplsExplicitPathNodeRowStatus        RowStatus }

juniMplsExplicitPathNodeName OBJECT-TYPE
    SYNTAX      DisplayString (SIZE(0..20))
    MAX-ACCESS  not-accessible
    STATUS      current
    DESCRIPTION
        "Configure the name for the explicit path used in the table index."
    ::= { juniMplsExplicitPathNodeEntry 1 }

juniMplsExplicitPathNodeIndexNumber OBJECT-TYPE
    SYNTAX      Integer32 (1..255)
    MAX-ACCESS  not-accessible
    STATUS      current
    DESCRIPTION
        "Each explicit path hop will have an index associated with it.
        Configure each path hop index using this object."
    ::= { juniMplsExplicitPathNodeEntry 2 }

juniMplsExplicitPathNodeLoose OBJECT-TYPE
    SYNTAX      TruthValue
    MAX-ACCESS  read-create
    STATUS      current
    DESCRIPTION
        "Configure the explicit path hop as strict or loose.  Set along with
        HopAddress."
    DEFVAL    { false }
    ::= { juniMplsExplicitPathNodeEntry 3 }

juniMplsExplicitPathNodeHopAddress OBJECT-TYPE
    SYNTAX      IpAddress
    MAX-ACCESS  read-create
    STATUS      current
    DESCRIPTION
        "Configure the hop IP address to setup explicit path.  Explicit path
        next hop will be created when the mentioned hop IP address doesn't
        belong to any of the existing hop even without setting the rowStatus
        createAndGo value.  The rowStatus value is used to destroy the node."
    ::= { juniMplsExplicitPathNodeEntry 4 }

juniMplsExplicitPathNodeHopAddressMask OBJECT-TYPE
    SYNTAX      IpAddress
    MAX-ACCESS  read-create
    STATUS      current
    DESCRIPTION
        "Configure the hop IP address mask.  Set along with hop address."
    DEFVAL    { 'ffffffff'H }
    ::= { juniMplsExplicitPathNodeEntry 5 }

juniMplsExplicitPathNodeRowStatus OBJECT-TYPE
    SYNTAX      RowStatus
    MAX-ACCESS  read-create
    STATUS      current
    DESCRIPTION
        "Use this object for deletion of the node.  For node creation, this
        value have no effect.  Setting the node with IP address create the node.
        To delete the node set only this object."
    ::= { juniMplsExplicitPathNodeEntry 6 }


-- +++++++++++++++++++++++++++++++++++++++++++++++++++++++++++++++++++++++++++++
-- Notifications
-- +++++++++++++++++++++++++++++++++++++++++++++++++++++++++++++++++++++++++++++
-- No notifications are defined in this MIB.


-- +++++++++++++++++++++++++++++++++++++++++++++++++++++++++++++++++++++++++++++
-- Conformance information
-- +++++++++++++++++++++++++++++++++++++++++++++++++++++++++++++++++++++++++++++

juniMplsConformance OBJECT IDENTIFIER ::= { juniMplsMIB 2 }
juniMplsCompliances OBJECT IDENTIFIER ::= { juniMplsConformance 1 }
juniMplsConfGroups  OBJECT IDENTIFIER ::= { juniMplsConformance 2 }

--
-- compliance statements
--
juniMplsCompliance  MODULE-COMPLIANCE
    STATUS      obsolete
    DESCRIPTION
        "Obsolete compliance statement for entities which implement the Juniper
        MPLS MIB.  This statement became obsolete when RowStatus support was
        added to some of the minor layer and tunnel profile tables."
    MODULE   -- this module
        MANDATORY-GROUPS {
        juniMplsLsrGlobalConfGroup,
        juniMplsMajorLayerConfGroup,
        juniMplsMinorLayerConfGroup,
        juniMplsTunnelProfileConfGroup,
        juniMplsExplicitPathConfGroup }
    ::= { juniMplsCompliances 1 }                                  -- JUNOSe 4.0

juniMplsCompliance2  MODULE-COMPLIANCE
    STATUS      obsolete
    DESCRIPTION
        "Obsolete compliance statement for entities which implement the Juniper
        MPLS MIB.  This statement became obsolete when the
        juniMplsGroupIpTtlPropagate object was added to the juniMplsGroup scalar
        group."
    MODULE   -- this module
        MANDATORY-GROUPS {
        juniMplsLsrGlobalConfGroup,
        juniMplsMajorLayerConfGroup,
        juniMplsMinorLayerConfGroup2,
        juniMplsTunnelProfileConfGroup2,
        juniMplsExplicitPathConfGroup }
    ::= { juniMplsCompliances 2 }                                  -- JUNOSe 4.1

juniMplsCompliance3  MODULE-COMPLIANCE
    STATUS      obsolete
    DESCRIPTION
        "Obsolete compliance statement for entities which implement the Juniper
        MPLS MIB. This statement become obsolete when the objects 
	juniMplsIfMajorCrLdpAdminState, juniMplsIfMinorLabelDistProto, 
	juniMplsIfMinorBaseTunnelName, juniMplsIfMinorVpnOuiNumber, 
	juniMplsIfMinorVpnIndex, juniMplsIfMinorTargetedDynamicTunnel, 
        juniMplsTunnelProfileBaseTunnelName, juniMplsTunnelProfileLabelDistProto,
	juniMplsTunnelProfileVpnOuiNumber, juniMplsTunnelProfileVpnIndex,
	juniMplsTunnelProfileTargetedDynamicTunnel,
	juniMplsGroupLdpRetryTimesNoroute, juniMplsGroupLdpRetryTimes,       
	juniMplsGroupLdpRetryIntervalNoroute and 
	juniMplsGroupLdpProfileCrLdpAdminState became obsolete."
    MODULE   -- this module
        MANDATORY-GROUPS {
        juniMplsLsrGlobalConfGroup2,
        juniMplsMajorLayerConfGroup,
        juniMplsMinorLayerConfGroup2,
        juniMplsTunnelProfileConfGroup2,
        juniMplsExplicitPathConfGroup }
    ::= { juniMplsCompliances 3 }                                 -- JUNOSe 6.0


juniMplsCompliance4  MODULE-COMPLIANCE
    STATUS      current
    DESCRIPTION
        "The compliance statement for entities which implement the Juniper
        MPLS MIB."
    MODULE   -- this module
        MANDATORY-GROUPS {
        juniMplsLsrGlobalConfGroup3,
        juniMplsMajorLayerConfGroup2,
        juniMplsMinorLayerConfGroup3,
        juniMplsTunnelProfileConfGroup3,
        juniMplsExplicitPathConfGroup }
    ::= { juniMplsCompliances 4 }                                 -- JUNOSe 6.0


--
-- units of conformance
--
juniMplsLsrGlobalConfGroup  OBJECT-GROUP
    OBJECTS {
        juniMplsGroupMplsEnable,
        juniMplsGroupReopTimer,
        juniMplsGroupLabelRangeLow,
        juniMplsGroupLabelRangeHigh,
        juniMplsGroupLspRetryTimesNoroute,
        juniMplsGroupLspRetryIntervalNoroute,
        juniMplsGroupLspRetryTimes,
        juniMplsGroupLspRetryInterval,
        juniMplsGroupLdpRetryTimesNoroute,
        juniMplsGroupLdpRetryIntervalNoroute,
        juniMplsGroupLdpRetryTimes,
        juniMplsGroupLdpRetryInterval,
        juniMplsGroupLdpSessionRetries,
        juniMplsGroupLdpSessionRetryTimer,
        juniMplsGroupTopologyDrivenIpProfileName,
        juniMplsGroupTopologyDrivenLdpEgressIpIntf,
        juniMplsGroupTopologyDrivenLdpIngressIpIntf,
        juniMplsGroupTopologyDrivenLdpEgressIpIntfHostOnly,
        juniMplsGroupTopologyDrivenLdpIngressIpIntfHostOnly,
        juniMplsGroupTopologyDrivenLdpEgressIpIntfPolicyListType,
        juniMplsGroupTopologyDrivenLdpIngressIpIntfPolicyListType,
        juniMplsGroupTopologyDrivenLdpEgressIpIntfPolicyList,
        juniMplsGroupTopologyDrivenLdpIngressIpIntfPolicyList,
        juniMplsGroupTopologyDrivenLdp,
        juniMplsGroupLspLabelDistCtrlMode,
        juniMplsGroupLdpAdvHostOnly,
        juniMplsGroupLsrState,
        juniMplsGroupReopNow,

        juniMplsGroupLdpTargetedHelloSendMode,

        juniMplsGroupLdpTargetedHelloReceiveMode,

        juniMplsGroupLabelAdverListMode,

        juniMplsGroupLdpProfileHelloHoldTime,
        juniMplsGroupLdpProfileCrLdpAdminState,
        juniMplsGroupLdpProfileRowStatus,

        juniMplsGroupRsvpProfileRefreshPeriod,
        juniMplsGroupRsvpProfileCleanupTimeoutFactor,
        juniMplsGroupRsvpProfileRowStatus }
    STATUS      obsolete
    DESCRIPTION
        "Obsolete collection of objects providing management of MPLS global
        configurations in a Juniper product.  This group became obsolete when
        the object juniMplsGroupIpTtlPropagate was added."
    ::= { juniMplsConfGroups 1 }                                   -- JUNOSe 4.0

juniMplsMajorLayerConfGroup  OBJECT-GROUP
    OBJECTS {
        juniMplsIfMajorNextIfIndex,

        juniMplsIfMajorRowStatus,
        juniMplsIfMajorLowerIfIndex,
        juniMplsIfMajorAdminStatus,
        juniMplsIfMajorLdpAdminStatus,
        juniMplsIfMajorLdpProfileName,
        juniMplsIfMajorLdpVpiStart,
        juniMplsIfMajorLdpVpiStop,
        juniMplsIfMajorLdpVciStart,
        juniMplsIfMajorLdpVciStop,
        juniMplsIfMajorRsvpAdminStatus,
        juniMplsIfMajorRsvpProfileName,
        juniMplsIfMajorRsvpVpiStart,
        juniMplsIfMajorRsvpVpiStop,
        juniMplsIfMajorRsvpVciStart,
        juniMplsIfMajorRsvpVciStop,
        juniMplsIfMajorLabelSpaceType,
        juniMplsIfMajorOpState,
        juniMplsIfMajorCrLdpAdminState }
    STATUS      obsolete
    DESCRIPTION
        "A collection of objects providing management of major MPLS interfaces
        in a Juniper product. This group became obsolete when the object 
	juniMplsIfMajorCrLdpAdminState became obsolete."
    ::= { juniMplsConfGroups 2 }                                   -- JUNOSe 4.0

juniMplsMinorLayerConfGroup  OBJECT-GROUP
    OBJECTS {
        juniMplsIfMinorNextIfIndex,

        juniMplsIfMinorRowStatus,
        juniMplsIfMinorLowerIfIndex,
        juniMplsIfMinorAdminStatus,
        juniMplsIfMinorEndpointAddress,
        juniMplsIfMinorEndpointDstMask,
        juniMplsIfMinorTunnelMetricMode,
        juniMplsIfMinorAbsoluteTunnelMetric,
        juniMplsIfMinorRelativeTunnelMetric,
        juniMplsIfMinorLabelDistProto,
        juniMplsIfMinorAnnounceToOspf,
        juniMplsIfMinorAnnounceToIsis,
        juniMplsIfMinorAnnounceToBgp,
        juniMplsIfMinorBandwidth,
        juniMplsIfMinorAffinity,
        juniMplsIfMinorAffinityMask,
        juniMplsIfMinorSetupPriority,
        juniMplsIfMinorHoldingPriority,
        juniMplsIfMinorTunnelName,
        juniMplsIfMinorTunnelRetryTimes,
        juniMplsIfMinorTunnelRetryInterval,
        juniMplsIfMinorTunnelRetryTimesNoroute,
        juniMplsIfMinorTunnelRetryIntervalNoroute,
        juniMplsIfMinorBaseTunnelName,
        juniMplsIfMinorVpnOuiNumber,
        juniMplsIfMinorVpnIndex,
        juniMplsIfMinorTunnelOpState,
        juniMplsIfMinorTargetedDynamicTunnel,
        juniMplsIfMinorReoptimization,

        juniMplsIfMinorPathOptionProtocol,
        juniMplsIfMinorPathOptionLockdown,
        juniMplsIfMinorPathOptionPathName,
        juniMplsIfMinorPathOptionPathId }
    STATUS      obsolete
    DESCRIPTION
        "Obsolete collection of objects providing management of minor MPLS
        (tunnel) in a Juniper product.  This group became obsolete when the
        juniMplsIfMinorPathOptionRowStatus object was added."
    ::= { juniMplsConfGroups 3 }                                   -- JUNOSe 4.0

juniMplsTunnelProfileConfGroup  OBJECT-GROUP
    OBJECTS {
        juniMplsTunnelProfileAdminStatus,
        juniMplsTunnelProfileBaseTunnelName,
        juniMplsTunnelProfileIpProfileName,
        juniMplsTunnelProfileLabelDistProto,
        juniMplsTunnelProfileAnnounceToOspf,
        juniMplsTunnelProfileAnnounceToIsis,
        juniMplsTunnelProfileAnnounceToBgp,
        juniMplsTunnelProfileMetricMode,
        juniMplsTunnelProfileAbsoluteMetric,
        juniMplsTunnelProfileRelativeMetric,
        juniMplsTunnelProfileBandwidth,
        juniMplsTunnelProfileAffinity,
        juniMplsTunnelProfileAffinityMask,
        juniMplsTunnelProfileSetupPriority,
        juniMplsTunnelProfileHoldingPriority,
        juniMplsTunnelProfileRetryTimes,
        juniMplsTunnelProfileRetryInterval,
        juniMplsTunnelProfileRetryTimesNoroute,
        juniMplsTunnelProfileRetryIntervalNoroute,
        juniMplsTunnelProfileVpnOuiNumber,
        juniMplsTunnelProfileVpnIndex,
        juniMplsTunnelProfileRowStatus,
        juniMplsTunnelProfileTargetedDynamicTunnel,

        juniMplsTunnelProfilePathOptionProtocol,
        juniMplsTunnelProfilePathOptionLockdown,
        juniMplsTunnelProfilePathOptionPathName,
        juniMplsTunnelProfilePathOptionPathId }
    STATUS      obsolete
    DESCRIPTION
        "Obsolete collection of objects providing management of MPLS tunnel
        profiles in a Juniper product.  This group became obsolete when
        RowStatus objects were added to some of the tables."
    ::= { juniMplsConfGroups 4 }                                   -- JUNOSe 4.0

juniMplsExplicitPathConfGroup  OBJECT-GROUP
    OBJECTS {
        juniMplsExplicitPathAdminState,
        juniMplsExplicitPathRowStatus,

        juniMplsExplicitPathNodeLoose,
        juniMplsExplicitPathNodeHopAddress,
        juniMplsExplicitPathNodeHopAddressMask,
        juniMplsExplicitPathNodeRowStatus }
    STATUS      current
    DESCRIPTION
        "A collection of objects providing management of MPLS explicit paths in
        a Juniper product."
    ::= { juniMplsConfGroups 5 }                                   -- JUNOSe 4.0

juniMplsMinorLayerConfGroup2  OBJECT-GROUP
    OBJECTS {
        juniMplsIfMinorNextIfIndex,

        juniMplsIfMinorRowStatus,
        juniMplsIfMinorLowerIfIndex,
        juniMplsIfMinorAdminStatus,
        juniMplsIfMinorEndpointAddress,
        juniMplsIfMinorEndpointDstMask,
        juniMplsIfMinorTunnelMetricMode,
        juniMplsIfMinorAbsoluteTunnelMetric,
        juniMplsIfMinorRelativeTunnelMetric,
        juniMplsIfMinorLabelDistProto,
        juniMplsIfMinorAnnounceToOspf,
        juniMplsIfMinorAnnounceToIsis,
        juniMplsIfMinorAnnounceToBgp,
        juniMplsIfMinorBandwidth,
        juniMplsIfMinorAffinity,
        juniMplsIfMinorAffinityMask,
        juniMplsIfMinorSetupPriority,
        juniMplsIfMinorHoldingPriority,
        juniMplsIfMinorTunnelName,
        juniMplsIfMinorTunnelRetryTimes,
        juniMplsIfMinorTunnelRetryInterval,
        juniMplsIfMinorTunnelRetryTimesNoroute,
        juniMplsIfMinorTunnelRetryIntervalNoroute,
        juniMplsIfMinorBaseTunnelName,
        juniMplsIfMinorVpnOuiNumber,
        juniMplsIfMinorVpnIndex,
        juniMplsIfMinorTunnelOpState,
        juniMplsIfMinorTargetedDynamicTunnel,
        juniMplsIfMinorReoptimization,

        juniMplsIfMinorPathOptionProtocol,
        juniMplsIfMinorPathOptionLockdown,
        juniMplsIfMinorPathOptionPathName,
        juniMplsIfMinorPathOptionPathId,
        juniMplsIfMinorPathOptionRowStatus }
    STATUS      obsolete
    DESCRIPTION
        "A collection of objects providing management of minor MPLS (tunnel)
        interfaces in a Juniper product. This group became obsolete when the
	objects juniMplsIfMinorLabelDistProto, juniMplsIfMinorBaseTunnelName, 
	juniMplsIfMinorVpnOuiNumber, juniMplsIfMinorVpnIndex, 
        juniMplsIfMinorTargetedDynamicTunnel became obsolete."
    ::= { juniMplsConfGroups 6 }                                   -- JUNOSe 4.1

juniMplsTunnelProfileConfGroup2  OBJECT-GROUP
    OBJECTS {
        juniMplsTunnelProfileAdminStatus,
        juniMplsTunnelProfileBaseTunnelName,
        juniMplsTunnelProfileIpProfileName,
        juniMplsTunnelProfileLabelDistProto,
        juniMplsTunnelProfileAnnounceToOspf,
        juniMplsTunnelProfileAnnounceToIsis,
        juniMplsTunnelProfileAnnounceToBgp,
        juniMplsTunnelProfileMetricMode,
        juniMplsTunnelProfileAbsoluteMetric,
        juniMplsTunnelProfileRelativeMetric,
        juniMplsTunnelProfileBandwidth,
        juniMplsTunnelProfileAffinity,
        juniMplsTunnelProfileAffinityMask,
        juniMplsTunnelProfileSetupPriority,
        juniMplsTunnelProfileHoldingPriority,
        juniMplsTunnelProfileRetryTimes,
        juniMplsTunnelProfileRetryInterval,
        juniMplsTunnelProfileRetryTimesNoroute,
        juniMplsTunnelProfileRetryIntervalNoroute,
        juniMplsTunnelProfileVpnOuiNumber,
        juniMplsTunnelProfileVpnIndex,
        juniMplsTunnelProfileRowStatus,
        juniMplsTunnelProfileTargetedDynamicTunnel,

        juniMplsTunnelProfilePathOptionProtocol,
        juniMplsTunnelProfilePathOptionLockdown,
        juniMplsTunnelProfilePathOptionPathName,
        juniMplsTunnelProfilePathOptionPathId,
        juniMplsTunnelProfilePathOptionRowStatus,

        juniMplsTunnelProfileDynamicEndpointRowStatus,

        juniMplsTunnelProfileTunnelEndpointRowStatus }
    STATUS      obsolete
    DESCRIPTION
        "A collection of objects providing management of MPLS tunnel profiles in
        a Juniper product. This group became oboslete when the objects
	juniMplsTunnelProfileBaseTunnelName, juniMplsTunnelProfileLabelDistProto,
	juniMplsTunnelProfileVpnOuiNumber, juniMplsTunnelProfileVpnIndex,
	juniMplsTunnelProfileTargetedDynamicTunnel became obsolete."
    ::= { juniMplsConfGroups 7 }                                   -- JUNOSe 4.1

juniMplsLsrGlobalConfGroup2  OBJECT-GROUP
    OBJECTS {
        juniMplsGroupMplsEnable,
        juniMplsGroupReopTimer,
        juniMplsGroupLabelRangeLow,
        juniMplsGroupLabelRangeHigh,
        juniMplsGroupLspRetryTimesNoroute,
        juniMplsGroupLspRetryIntervalNoroute,
        juniMplsGroupLspRetryTimes,
        juniMplsGroupLspRetryInterval,
        juniMplsGroupLdpRetryTimesNoroute,
        juniMplsGroupLdpRetryIntervalNoroute,
        juniMplsGroupLdpRetryTimes,
        juniMplsGroupLdpRetryInterval,
        juniMplsGroupLdpSessionRetries,
        juniMplsGroupLdpSessionRetryTimer,
        juniMplsGroupTopologyDrivenIpProfileName,
        juniMplsGroupTopologyDrivenLdpEgressIpIntf,
        juniMplsGroupTopologyDrivenLdpIngressIpIntf,
        juniMplsGroupTopologyDrivenLdpEgressIpIntfHostOnly,
        juniMplsGroupTopologyDrivenLdpIngressIpIntfHostOnly,
        juniMplsGroupTopologyDrivenLdpEgressIpIntfPolicyListType,
        juniMplsGroupTopologyDrivenLdpIngressIpIntfPolicyListType,
        juniMplsGroupTopologyDrivenLdpEgressIpIntfPolicyList,
        juniMplsGroupTopologyDrivenLdpIngressIpIntfPolicyList,
        juniMplsGroupTopologyDrivenLdp,
        juniMplsGroupLspLabelDistCtrlMode,
        juniMplsGroupLdpAdvHostOnly,
        juniMplsGroupLsrState,
        juniMplsGroupReopNow,
        juniMplsGroupIpTtlPropagate,

        juniMplsGroupLdpTargetedHelloSendMode,

        juniMplsGroupLdpTargetedHelloReceiveMode,

        juniMplsGroupLabelAdverListMode,

        juniMplsGroupLdpProfileHelloHoldTime,
        juniMplsGroupLdpProfileCrLdpAdminState,
        juniMplsGroupLdpProfileRowStatus,

        juniMplsGroupRsvpProfileRefreshPeriod,
        juniMplsGroupRsvpProfileCleanupTimeoutFactor,
        juniMplsGroupRsvpProfileRowStatus }
    STATUS      obsolete
    DESCRIPTION
        "A collection of objects providing management of MPLS label switching
        routers (LSRs) in a Juniper product. This group became obsolete when 
	the object juniMplsGroupLdpRetryTimesNoroute,         
	juniMplsGroupLdpRetryIntervalNoroute, juniMplsGroupLdpRetryTimes and
	juniMplsGroupLdpProfileCrLdpAdminState became obsolete."
    ::= { juniMplsConfGroups 8 }                                   -- JUNOSe 5.0

juniMplsLsrGlobalConfGroup3 OBJECT-GROUP
    OBJECTS {
        juniMplsGroupMplsEnable,
        juniMplsGroupReopTimer,
        juniMplsGroupLabelRangeLow,
        juniMplsGroupLabelRangeHigh,
        juniMplsGroupLspRetryTimesNoroute,
        juniMplsGroupLspRetryIntervalNoroute,
        juniMplsGroupLspRetryTimes,
        juniMplsGroupLspRetryInterval,
        juniMplsGroupLdpRetryInterval,
        juniMplsGroupLdpSessionRetries,
        juniMplsGroupLdpSessionRetryTimer,
        juniMplsGroupTopologyDrivenIpProfileName,
        juniMplsGroupTopologyDrivenLdpEgressIpIntf,
        juniMplsGroupTopologyDrivenLdpIngressIpIntf,
        juniMplsGroupTopologyDrivenLdpEgressIpIntfHostOnly,
        juniMplsGroupTopologyDrivenLdpIngressIpIntfHostOnly,
        juniMplsGroupTopologyDrivenLdpEgressIpIntfPolicyListType,
        juniMplsGroupTopologyDrivenLdpIngressIpIntfPolicyListType,
        juniMplsGroupTopologyDrivenLdpEgressIpIntfPolicyList,
        juniMplsGroupTopologyDrivenLdpIngressIpIntfPolicyList,
        juniMplsGroupTopologyDrivenLdp,
        juniMplsGroupLspLabelDistCtrlMode,
        juniMplsGroupLdpAdvHostOnly,
        juniMplsGroupLsrState,
        juniMplsGroupReopNow,
        juniMplsGroupIpTtlPropagate,
        juniMplsGroupLdpTargetedHelloSendMode,
        juniMplsGroupLdpTargetedHelloReceiveMode,
        juniMplsGroupLabelAdverListMode,
        juniMplsGroupLdpProfileHelloHoldTime,
        juniMplsGroupLdpProfileRowStatus,
        juniMplsGroupRsvpProfileRefreshPeriod,
        juniMplsGroupRsvpProfileCleanupTimeoutFactor,
        juniMplsGroupRsvpProfileRowStatus }
    STATUS      current
    DESCRIPTION
        "A collection of objects providing management of MPLS label switching
        routers (LSRs) in a Juniper product."
    ::= { juniMplsConfGroups 9 }                                   -- JUNOSe 6.0

juniMplsMajorLayerConfGroup2  OBJECT-GROUP
    OBJECTS {
        juniMplsIfMajorNextIfIndex,

        juniMplsIfMajorRowStatus,
        juniMplsIfMajorLowerIfIndex,
        juniMplsIfMajorAdminStatus,
        juniMplsIfMajorLdpAdminStatus,
        juniMplsIfMajorLdpProfileName,
        juniMplsIfMajorLdpVpiStart,
        juniMplsIfMajorLdpVpiStop,
        juniMplsIfMajorLdpVciStart,
        juniMplsIfMajorLdpVciStop,
        juniMplsIfMajorRsvpAdminStatus,
        juniMplsIfMajorRsvpProfileName,
        juniMplsIfMajorRsvpVpiStart,
        juniMplsIfMajorRsvpVpiStop,
        juniMplsIfMajorRsvpVciStart,
        juniMplsIfMajorRsvpVciStop,
        juniMplsIfMajorLabelSpaceType,
        juniMplsIfMajorOpState }
    STATUS      current
    DESCRIPTION
        "A collection of objects providing management of major MPLS interfaces
        in a Juniper product."
    ::= { juniMplsConfGroups 10 }                                   -- JUNOSe 6.0

juniMplsMinorLayerConfGroup3  OBJECT-GROUP
    OBJECTS {
        juniMplsIfMinorNextIfIndex,
        juniMplsIfMinorRowStatus,
        juniMplsIfMinorLowerIfIndex,
        juniMplsIfMinorAdminStatus,
        juniMplsIfMinorEndpointAddress,
        juniMplsIfMinorEndpointDstMask,
        juniMplsIfMinorTunnelMetricMode,
        juniMplsIfMinorAbsoluteTunnelMetric,
        juniMplsIfMinorRelativeTunnelMetric,
        juniMplsIfMinorAnnounceToOspf,
        juniMplsIfMinorAnnounceToIsis,
        juniMplsIfMinorAnnounceToBgp,
        juniMplsIfMinorBandwidth,
        juniMplsIfMinorAffinity,
        juniMplsIfMinorAffinityMask,
        juniMplsIfMinorSetupPriority,
        juniMplsIfMinorHoldingPriority,
        juniMplsIfMinorTunnelName,
        juniMplsIfMinorTunnelRetryTimes,
        juniMplsIfMinorTunnelRetryInterval,
        juniMplsIfMinorTunnelRetryTimesNoroute,
        juniMplsIfMinorTunnelRetryIntervalNoroute,
        juniMplsIfMinorTunnelOpState,
        juniMplsIfMinorReoptimization,
        juniMplsIfMinorPathOptionProtocol,
        juniMplsIfMinorPathOptionLockdown,
        juniMplsIfMinorPathOptionPathName,
        juniMplsIfMinorPathOptionPathId,
        juniMplsIfMinorPathOptionRowStatus }
    STATUS      current
    DESCRIPTION
        "A collection of objects providing management of minor MPLS (tunnel)
        interfaces in a Juniper product."
    ::= { juniMplsConfGroups 11 }                                   -- JUNOSe 6.0

juniMplsTunnelProfileConfGroup3  OBJECT-GROUP
    OBJECTS {
        juniMplsTunnelProfileAdminStatus,
        juniMplsTunnelProfileIpProfileName,
        juniMplsTunnelProfileAnnounceToOspf,
        juniMplsTunnelProfileAnnounceToIsis,
        juniMplsTunnelProfileAnnounceToBgp,
        juniMplsTunnelProfileMetricMode,
        juniMplsTunnelProfileAbsoluteMetric,
        juniMplsTunnelProfileRelativeMetric,
        juniMplsTunnelProfileBandwidth,
        juniMplsTunnelProfileAffinity,
        juniMplsTunnelProfileAffinityMask,
        juniMplsTunnelProfileSetupPriority,
        juniMplsTunnelProfileHoldingPriority,
        juniMplsTunnelProfileRetryTimes,
        juniMplsTunnelProfileRetryInterval,
        juniMplsTunnelProfileRetryTimesNoroute,
        juniMplsTunnelProfileRetryIntervalNoroute,
        juniMplsTunnelProfileRowStatus,
        juniMplsTunnelProfilePathOptionProtocol,
        juniMplsTunnelProfilePathOptionLockdown,
        juniMplsTunnelProfilePathOptionPathName,
        juniMplsTunnelProfilePathOptionPathId,
        juniMplsTunnelProfilePathOptionRowStatus,
        juniMplsTunnelProfileDynamicEndpointRowStatus,
        juniMplsTunnelProfileTunnelEndpointRowStatus }
    STATUS      current
    DESCRIPTION
        "A collection of objects providing management of MPLS tunnel profiles in
        a Juniper product"
    ::= { juniMplsConfGroups 12 }                                   -- JUNOSe 6.0
END
