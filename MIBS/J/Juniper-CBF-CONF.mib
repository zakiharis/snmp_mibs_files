-- *****************************************************************************
-- Juniper-CBF-CONF
--
-- SNMP Agent Capabilities definitions for the CBF MIB.
--
-- Copyright (c) 2001 Unisphere Networks, Inc.
-- Copyright (c) 2002 Juniper Networks, Inc.
--   All rights reserved.
-- *****************************************************************************

Juniper-CBF-CONF  DEFINITIONS ::= BEGIN

IMPORTS
    MODULE-IDENTITY
        FROM SNMPv2-SMI
    AGENT-CAPABILITIES
        FROM SNMPv2-CONF
    juniAgents
        FROM Juniper-Agents;

juniCbfAgent  MODULE-IDENTITY
    LAST-UPDATED "200209061654Z"  -- 06-Sep-02 12:54 PM EDT
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the Connection-Based Forwarding
        (CBF) protocol management component of the SNMP agent in the Juniper
        E-series family of products."
    -- Revision History
    REVISION    "200209061654Z"  -- 06-Sep-02 12:54 PM EDT  - JUNOSe 5.0
    DESCRIPTION
        "Replaced Unisphere names with Juniper names."
    REVISION    "200103292023Z"  -- 29-Mar-01 03:23 PM EST  - JUNOSe 3.2
    DESCRIPTION
        "The initial release of this management information module."
    ::= { juniAgents 48 }


-- *****************************************************************************
-- CBF SNMP Agent Capabilities definitions
-- *****************************************************************************
juniCbfAgentV1  AGENT-CAPABILITIES
    PRODUCT-RELEASE
        "Version 1 of the Connection-Based Forwarding (CBF) component of the
        JUNOSe SNMP agent.  This version of the CBF component is supported in
        JUNOSe 3.2 and subsequent system releases."
    STATUS      current
    DESCRIPTION
        "The MIB supported by the SNMP agent for the CBF application in JUNOSe."
    SUPPORTS    Juniper-CBF-MIB
        INCLUDES {
            juniCbfGroup }
    ::= { juniCbfAgent 1 }

END
