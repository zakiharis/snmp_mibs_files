-- *****************************************************************************
-- Juniper-SMDS-MIB
--
-- Juniper Networks Enterprise MIB
--   SMDS MIB
--
-- Copyright 2001 Unisphere Networks, Inc.
-- Copyright 2002 Juniper Networks, Inc.
--   All Rights Reserved.
-- *****************************************************************************

Juniper-SMDS-MIB DEFINITIONS ::= BEGIN

IMPORTS
    MODULE-IDENTITY,
    OBJECT-TYPE,
    Counter32,
    Integer32
        FROM SNMPv2-SMI
    RowStatus
        FROM SNMPv2-TC
    MODULE-COMPLIANCE, 
    OBJECT-GROUP  
        FROM SNMPv2-CONF
    InterfaceIndex, InterfaceIndexOrZero
        FROM IF-MIB
    juniMibs
        FROM Juniper-MIBs
    JuniNextIfIndex
        FROM Juniper-TC;

juniSmdsMIB  MODULE-IDENTITY
    LAST-UPDATED "200209162144Z"  -- 16-Sep-02 05:44 PM EDT
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "The Switched Multimegabit Data Service (SMDS) MIB for the Juniper
        Networks enterprise."
    -- Revision History
    REVISION    "200209162144Z"  -- 16-Sep-02 05:44 PM EDT  - JUNOSe 5.0
    DESCRIPTION
        "Replaced Unisphere names with Juniper names."
    REVISION    "200109201441Z"  -- 20-Sep-01 10:41 AM EDT  - JUNOSe 4.0
    DESCRIPTION
        "Added support for major and sub interfaces."
    REVISION    "200103082016Z"  -- 08-Mar-01 03:16 PM EST  - JUNOSe 3.1
    DESCRIPTION
        "Initial version of this MIB module."
    ::= { juniMibs 50 }


-- +++++++++++++++++++++++++++++++++++++++++++++++++++++++++++++++++++++++++++++
-- Managed objects
-- +++++++++++++++++++++++++++++++++++++++++++++++++++++++++++++++++++++++++++++
juniSmdsObjects     OBJECT IDENTIFIER ::= { juniSmdsMIB 1 }

-- 
-- This MIB contains managed objects for SMDS arrangements.
-- Management objects are provided to query for an available
-- interface index, and to create/delete interfaces of this type.
-- Creating/deleting this interface type using this MIB has
-- the side effect of creating/deleting corresponding entries
-- in the Interface MIB ifTable/ifXTable, and in the Juniper
-- Enterprise Interface MIB juniIfTable.
--

-- /////////////////////////////////////////////////////////////////////////////
--
-- SMDS Interfaces
--
-- /////////////////////////////////////////////////////////////////////////////
--
-- IfIndex selection for creating new SMDS interfaces
--
juniSmdsNextIfIndex OBJECT-TYPE
    SYNTAX      JuniNextIfIndex
    MAX-ACCESS  read-only
    STATUS      current
    DESCRIPTION
        "Coordinate ifIndex value allocation for entries in juniSmdsIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { juniSmdsObjects 1 }

--
-- The SMDS Interface Table
--
juniSmdsIfTable OBJECT-TYPE
    SYNTAX      SEQUENCE OF JuniSmdsIfEntry
    MAX-ACCESS  not-accessible
    STATUS      current
    DESCRIPTION
        "This table contains entries for SMDS interfaces present in the system."
    ::= { juniSmdsObjects 2 }

juniSmdsIfEntry OBJECT-TYPE
    SYNTAX      JuniSmdsIfEntry
    MAX-ACCESS  not-accessible
    STATUS      current
    DESCRIPTION
        "Each entry describes the characteristics of an SMDS interface.
        Creating/deleting entries in this table causes corresponding entries for
        be created/deleted in ifTable/ifXTable/juniIfTable."
    INDEX     { juniSmdsIfIndex }
    ::= { juniSmdsIfTable 1 }

JuniSmdsIfEntry ::= SEQUENCE {
    juniSmdsIfIndex         InterfaceIndex,
    juniSmdsIfRowStatus     RowStatus,
    juniSmdsIfLowerIfIndex  InterfaceIndexOrZero }

juniSmdsIfIndex OBJECT-TYPE
    SYNTAX      InterfaceIndex
    MAX-ACCESS  not-accessible
    STATUS      current
    DESCRIPTION
        "The ifIndex of the SMDS interface.  When creating entries in this
        table, suitable values for this object are determined by reading
        juniSmdsNextIfIndex."
    ::= { juniSmdsIfEntry 1 }

juniSmdsIfRowStatus OBJECT-TYPE
    SYNTAX      RowStatus
    MAX-ACCESS  read-create
    STATUS      current
    DESCRIPTION
        "Controls creation/deletion of entries in this table according to the
        RowStatus textual convention, constrained to support the following
        values only:
            createAndGo
            destroy
            
        To create an entry in this table, the following entry objects MUST be
        explicitly configured:
            juniSmdsIfRowStatus
            juniSmdsIfLowerIfIndex

        In addition, when creating an entry the following conditions must hold:

            A value for juniSmdsIfIndex must have been determined previously, by
            reading juniSmdsNextIfIndex.

            The interface identified by juniSmdsIfLowerIfIndex must exist.

        A corresponding entry in ifTable/ifXTable/juniIfTable is created/
        destroyed as a result of creating/destroying an entry in this table.  "
    ::= { juniSmdsIfEntry 2 }

juniSmdsIfLowerIfIndex OBJECT-TYPE
    SYNTAX      InterfaceIndexOrZero
    MAX-ACCESS  read-create
    STATUS      current
    DESCRIPTION
        "The ifIndex of an interface over which this SMDS interface is to be
        layered.  A value of zero indicates no layering.  An implementation may
        choose to require that a nonzero value be configured at entry creation."
    ::= { juniSmdsIfEntry 3 }


-- /////////////////////////////////////////////////////////////////////////////
--
-- SMDS Major Interfaces
--
-- /////////////////////////////////////////////////////////////////////////////
--
-- IfIndex selection for creating new SMDS major interfaces
--
juniSmdsMajorNextIfIndex OBJECT-TYPE
    SYNTAX      JuniNextIfIndex
    MAX-ACCESS  read-only
    STATUS      current
    DESCRIPTION
        "Coordinate ifIndex value allocation for entries in
        juniSmdsMajorIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { juniSmdsObjects 3 }


--
-- The SMDS Major Interface Table
--
juniSmdsMajorIfTable OBJECT-TYPE
    SYNTAX      SEQUENCE OF JuniSmdsMajorIfEntry
    MAX-ACCESS  not-accessible
    STATUS      current
    DESCRIPTION
        "This table contains entries for SMDS major interfaces present in the
        system."
    ::= { juniSmdsObjects 4 }

juniSmdsMajorIfEntry OBJECT-TYPE
    SYNTAX      JuniSmdsMajorIfEntry
    MAX-ACCESS  not-accessible
    STATUS      current
    DESCRIPTION
        "Each entry describes the characteristics of an SMDS major interface.
        Creating/deleting entries in this table causes corresponding entries for
        be created/deleted in ifTable/ifXTable/juniIfTable."
    INDEX     { juniSmdsMajorIfIndex }
    ::= { juniSmdsMajorIfTable 1 }

JuniSmdsMajorIfEntry ::= SEQUENCE {
    juniSmdsMajorIfIndex            InterfaceIndex,
    juniSmdsMajorIfRowStatus        RowStatus,
    juniSmdsMajorIfLowerIfIndex     InterfaceIndexOrZero,
    juniSmdsMajorIfKeepalive        Integer32 }

juniSmdsMajorIfIndex OBJECT-TYPE
    SYNTAX      InterfaceIndex
    MAX-ACCESS  not-accessible
    STATUS      current
    DESCRIPTION
        "The ifIndex of the SMDS major interface.  When creating entries in this
        table, suitable values for this object are determined by reading
        juniSmdsMajorNextIfIndex."
    ::= { juniSmdsMajorIfEntry 1 }

juniSmdsMajorIfRowStatus OBJECT-TYPE
    SYNTAX      RowStatus
    MAX-ACCESS  read-create
    STATUS      current
    DESCRIPTION
        "Controls creation/deletion of entries in this table according to the
        RowStatus textual convention, constrained to support the following
        values only:
            createAndGo
            destroy
            
        To create an entry in this table, the following entry objects MUST be
        explicitly configured:
            juniSmdsMajorIfRowStatus
            juniSmdsMajorIfLowerIfIndex

        In addition, when creating an entry the following conditions must hold:

            A value for juniSmdsMajorIfIndex must have been determined
            previously, by reading juniSmdsMajorNextIfIndex.

            The interface identified by juniSmdsMajorIfLowerIfIndex must exist.

        A corresponding entry in ifTable/ifXTable/juniIfTable is created/
        destroyed as a result of creating/destroying an entry in this table."
    ::= { juniSmdsMajorIfEntry 2 }

juniSmdsMajorIfLowerIfIndex OBJECT-TYPE
    SYNTAX      InterfaceIndexOrZero
    MAX-ACCESS  read-create
    STATUS      current
    DESCRIPTION
        "The ifIndex of an interface over which this SMDS major interface is to
        be layered.  A value of zero indicates no layering.  An implementation
        may choose to require that a nonzero value be configured at entry
        creation."
    ::= { juniSmdsMajorIfEntry 3 }

juniSmdsMajorIfKeepalive OBJECT-TYPE
    SYNTAX      Integer32 (0|5..32767)
    UNITS       "seconds"
    MAX-ACCESS  read-create
    STATUS      current
    DESCRIPTION
        "Keepalive interval in seconds.  A value of zero disables keepalive."
    ::= { juniSmdsMajorIfEntry 4 }


-- /////////////////////////////////////////////////////////////////////////////
--
-- SMDS SubInterfaces
--
-- /////////////////////////////////////////////////////////////////////////////
--
-- IfIndex selection for creating new SMDS subInterfaces
--
juniSmdsSubNextIfIndex OBJECT-TYPE
    SYNTAX      JuniNextIfIndex
    MAX-ACCESS  read-only
    STATUS      current
    DESCRIPTION
        "Coordinate ifIndex value allocation for entries in juniSmdsSubIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { juniSmdsObjects 5 }

--
-- The SMDS Subinterface Table
--
 juniSmdsSubIfTable OBJECT-TYPE
    SYNTAX      SEQUENCE OF JuniSmdsSubIfEntry
    MAX-ACCESS  not-accessible
    STATUS      current
    DESCRIPTION
        "This table contains entries for SMDS subinterfaces present in the
        system."
    ::= { juniSmdsObjects 6 }

juniSmdsSubIfEntry OBJECT-TYPE
    SYNTAX      JuniSmdsSubIfEntry
    MAX-ACCESS  not-accessible
    STATUS      current
    DESCRIPTION
        "Each entry describes the characteristics of an SMDS subinterface.
        Creating/deleting entries in this table causes corresponding entries for
        be created/deleted in ifTable/ifXTable/juniIfTable."
    INDEX     { juniSmdsSubIfIndex }
    ::= { juniSmdsSubIfTable 1 }

JuniSmdsSubIfEntry ::= SEQUENCE {
    juniSmdsSubIfIndex                      InterfaceIndex,
    juniSmdsSubIfRowStatus                  RowStatus,
    juniSmdsSubIfLowerIfIndex               InterfaceIndexOrZero,
    juniSmdsSubIfSmdsAddress                OCTET STRING,
    juniSmdsSubIfSmdsMulticastIpAddress     OCTET STRING,
    juniSmdsSubIfSmdsMulticastArpAddress    OCTET STRING }

juniSmdsSubIfIndex OBJECT-TYPE
    SYNTAX      InterfaceIndex
    MAX-ACCESS  not-accessible
    STATUS      current
    DESCRIPTION
        "The ifIndex of the SMDS subinterface.  When creating entries in this
        table, suitable values for this object are determined by reading
        juniSmdsSubNextIfIndex."
    ::= { juniSmdsSubIfEntry 1 }

juniSmdsSubIfRowStatus OBJECT-TYPE
    SYNTAX      RowStatus
    MAX-ACCESS  read-create
    STATUS      current
    DESCRIPTION
        "Controls creation/deletion of entries in this table according to the
        RowStatus textual convention, constrained to support the following
        values only:
            createAndGo
            destroy
            
        To create an entry in this table, the following entry objects MUST be
        explicitly configured:
            juniSmdsSubIfRowStatus
            juniSmdsSubIfLowerIfIndex

        In addition, when creating an entry the following conditions must hold:

            A value for juniSmdsSubIfIndex must have been determined previously,
            by reading juniSmdsSubNextIfIndex.

            The interface identified by juniSmdsSubIfLowerIfIndex must exist.

        A corresponding entry in ifTable/ifXTable/juniIfTable is created/
        destroyed as a result of creating/destroying an entry in this table.  "
    ::= { juniSmdsSubIfEntry 2 }

juniSmdsSubIfLowerIfIndex OBJECT-TYPE
    SYNTAX      InterfaceIndexOrZero
    MAX-ACCESS  read-create
    STATUS      current
    DESCRIPTION
        "The ifIndex of an interface over which this SMDS subinterface is to be
        layered.  A value of zero indicates no layering.  An implementation may
        choose to require that a nonzero value be configured at entry creation."
    ::= { juniSmdsSubIfEntry 3 }

juniSmdsSubIfSmdsAddress OBJECT-TYPE
    SYNTAX      OCTET STRING (SIZE(8))
    MAX-ACCESS  read-create
    STATUS      current
    DESCRIPTION
        "The 64 bit E.164 SMDS address that has been assigned to this SMDS
        subinterface.  A value of 0 indicates no address is configured."
    ::= { juniSmdsSubIfEntry 4 }

juniSmdsSubIfSmdsMulticastIpAddress OBJECT-TYPE
    SYNTAX      OCTET STRING (SIZE(8))
    MAX-ACCESS  read-create
    STATUS      current
    DESCRIPTION
        "The 64 bit E.164 SMDS ip multicast address that has been assigned to
        this SMDS subinterface.  A value of 0 indicates no address is
        configured."
    ::= { juniSmdsSubIfEntry 5 }

juniSmdsSubIfSmdsMulticastArpAddress OBJECT-TYPE
    SYNTAX      OCTET STRING (SIZE(8))
    MAX-ACCESS  read-create
    STATUS      current
    DESCRIPTION
        "The 64 bit E.164 SMDS multicast arp address that has been assigned to
        this SMDS subinterface.  A value of 0 indicates no address is
        configured."
    ::= { juniSmdsSubIfEntry 6 }


--
-- The SMDS Major Interface Statistics Table
--
juniSmdsMajorIfStatsTable OBJECT-TYPE
    SYNTAX      SEQUENCE OF JuniSmdsMajorIfStatsEntry
    MAX-ACCESS  not-accessible
    STATUS      current
    DESCRIPTION
        "This table contains entries for SMDS major interface statistics present
        in the system."
    ::= { juniSmdsObjects 7 }

juniSmdsMajorIfStatsEntry OBJECT-TYPE
    SYNTAX      JuniSmdsMajorIfStatsEntry
    MAX-ACCESS  not-accessible
    STATUS      current
    DESCRIPTION
        "Each entry describes the statistics of an SMDS major interface."
    AUGMENTS  { juniSmdsMajorIfEntry }
    ::= { juniSmdsMajorIfStatsTable 1 }

JuniSmdsMajorIfStatsEntry ::= SEQUENCE {
    juniSmdsMajorIfStatsInKeepaliveRequests     Counter32,
    juniSmdsMajorIfStatsOutKeepaliveRequests    Counter32,
    juniSmdsMajorIfStatsInKeepaliveReplies      Counter32,
    juniSmdsMajorIfStatsOutKeepaliveReplies     Counter32,
    juniSmdsMajorIfStatsKeepaliveFailures       Counter32 }

juniSmdsMajorIfStatsInKeepaliveRequests OBJECT-TYPE
    SYNTAX      Counter32
    MAX-ACCESS  read-only
    STATUS      current
    DESCRIPTION
        "The number of keepalive requests received."
    ::= { juniSmdsMajorIfStatsEntry 1 }

juniSmdsMajorIfStatsOutKeepaliveRequests OBJECT-TYPE
    SYNTAX      Counter32
    MAX-ACCESS  read-only
    STATUS      current
    DESCRIPTION
        "The number of keepalive requests transmitted."
    ::= { juniSmdsMajorIfStatsEntry 2 }

juniSmdsMajorIfStatsInKeepaliveReplies OBJECT-TYPE
    SYNTAX      Counter32
    MAX-ACCESS  read-only
    STATUS      current
    DESCRIPTION
        "The number of keepalive replies received."
    ::= { juniSmdsMajorIfStatsEntry 3 }

juniSmdsMajorIfStatsOutKeepaliveReplies OBJECT-TYPE
    SYNTAX      Counter32
    MAX-ACCESS  read-only
    STATUS      current
    DESCRIPTION
        "The number of keepalive replies transmitted."
    ::= { juniSmdsMajorIfStatsEntry 4 }

juniSmdsMajorIfStatsKeepaliveFailures OBJECT-TYPE
    SYNTAX      Counter32
    MAX-ACCESS  read-only
    STATUS      current
    DESCRIPTION
        "The number of keepalive failures detected."
    ::= { juniSmdsMajorIfStatsEntry 5 }


-- +++++++++++++++++++++++++++++++++++++++++++++++++++++++++++++++++++++++++++++
-- Notifications
-- +++++++++++++++++++++++++++++++++++++++++++++++++++++++++++++++++++++++++++++
-- No notifications are defined in this MIB.  Placeholders follow.
-- juniSmdsTrapControl      OBJECT IDENTIFIER ::= { juniSmdsMIB 2 }
-- juniSmdsTraps            OBJECT IDENTIFIER ::= { juniSmdsMIB 3 }
-- juniSmdsTrapPrefix       OBJECT IDENTIFIER ::= { juniSmdsTraps 0 }


-- +++++++++++++++++++++++++++++++++++++++++++++++++++++++++++++++++++++++++++++
-- Conformance information
-- +++++++++++++++++++++++++++++++++++++++++++++++++++++++++++++++++++++++++++++
juniSmdsConformance OBJECT IDENTIFIER ::= { juniSmdsMIB 4 }
juniSmdsCompliances OBJECT IDENTIFIER ::= { juniSmdsConformance 1 }
juniSmdsGroups      OBJECT IDENTIFIER ::= { juniSmdsConformance 2 }

--
-- compliance statements
--
juniSmdsCompliance  MODULE-COMPLIANCE
    STATUS      obsolete
    DESCRIPTION
        "Obsolete compliance statement for entities which implement the Juniper
        SMDS MIB.  This statement became obsolete when support was added for
        major and sub interfaces."
    MODULE   -- this module
        MANDATORY-GROUPS {
            juniSmdsGroup }
    ::= { juniSmdsCompliances 1 }                                  -- JUNOSe 3.1

juniSmdsCompliance2  MODULE-COMPLIANCE
    STATUS      current
    DESCRIPTION
        "The compliance statement for entities which implement the Juniper SMDS
        MIB."
    MODULE   -- this module
        MANDATORY-GROUPS {
            juniSmdsGroup2 }
    ::= { juniSmdsCompliances 2 }                                  -- JUNOSe 4.0


--
-- units of conformance
--
juniSmdsGroup  OBJECT-GROUP
    OBJECTS {
        juniSmdsNextIfIndex,

        juniSmdsIfRowStatus,
        juniSmdsIfLowerIfIndex }
    STATUS      obsolete
    DESCRIPTION
        "Obsolete collection of objects providing management of SMDS interfaces
        in a Juniper product.  This group became obsolete when support was added
        for major and sub interfaces."
    ::= { juniSmdsGroups 1 }

juniSmdsGroup2  OBJECT-GROUP
    OBJECTS {
        juniSmdsNextIfIndex,

        juniSmdsIfRowStatus,
        juniSmdsIfLowerIfIndex,

        juniSmdsMajorNextIfIndex,

        juniSmdsMajorIfRowStatus,
        juniSmdsMajorIfLowerIfIndex,
        juniSmdsMajorIfKeepalive,

        juniSmdsSubNextIfIndex,

        juniSmdsSubIfRowStatus,
        juniSmdsSubIfLowerIfIndex,
        juniSmdsSubIfSmdsAddress,
        juniSmdsSubIfSmdsMulticastIpAddress,
        juniSmdsSubIfSmdsMulticastArpAddress,

        juniSmdsMajorIfStatsInKeepaliveRequests,
        juniSmdsMajorIfStatsOutKeepaliveRequests,
        juniSmdsMajorIfStatsInKeepaliveReplies,
        juniSmdsMajorIfStatsOutKeepaliveReplies,
        juniSmdsMajorIfStatsKeepaliveFailures }
    STATUS      current
    DESCRIPTION
        "A collection of objects providing management of SMDS interfaces in a
        Juniper product."
    ::= { juniSmdsGroups 2 }

END
