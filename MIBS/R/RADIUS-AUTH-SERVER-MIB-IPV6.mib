-- extracted from draft-nelson-rfc2619bis-00.txt
-- at Thu Feb 10 06:24:09 2005

     RADIUS-AUTH-SERVER-MIB-IPV6 DEFINITIONS ::= BEGIN

   IMPORTS
          MODULE-IDENTITY, OBJECT-TYPE, OBJECT-IDENTITY,
          mib-2 FROM SNMPv2-SMI
          InetAddressType, InetAddress, InetPortNumber
          FROM INET-ADDRESS-MIB
          MODULE-COMPLIANCE, OBJECT-GROUP  FROM SNMPv2-CONF
          radiusAuthClientEntry, radiusAuthServerExtTable FROM RADIUS-AUTH-CLIENT-MIB;

   radiusAuthServerExtMIB MODULE-IDENTITY
          LAST-UPDATED "200502072051Z"  -- Mon Feb  7 20:51 GMT 2005
          ORGANIZATION "IETF RADIUS Extensions Working Group."
          CONTACT-INFO
                 " David B. Nelson
                   Enterasys Networks
                   50 Minutemann Road
                   Andover, MA 01810
                   US

                   Phone: +1 978 684 1000
                   EMail: dnelson@eterasys.com"
          DESCRIPTION
                "An extension to the MIB module for entities
                 implementing the server side of the Remote Access
                 Dialin User Service (RADIUS) authentication protocol,
                 using IPv6 addressing formats. Updates RFC 2619."
          REVISION "200502072051Z"  -- Mon Feb  7 20:51 GMT 2005
          DESCRIPTION "Initial version, published as RFC xxxx."

   -- RFC Editor: replace xxx with actual RFC number at the time of
   -- publication, and remove this note.

          ::= { mib-2 1 }

   -- RFC Editor: replace TBA with IANA assigned OID value, and
   -- remove this note.

   radiusAuthServerExtMIBNotifications  OBJECT IDENTIFIER
               ::= { radiusAuthServerExtMIB 0 }

   radiusAuthServerExtMIBObjects        OBJECT IDENTIFIER
               ::= { radiusAuthServerExtMIB 1 }

   radiusAuthServerExtMIBConformance    OBJECT IDENTIFIER
               ::= { radiusAuthServerExtMIB 2 }

   -- MIB objects

   radiusAuthClientExtTable OBJECT-TYPE
         SYNTAX      SEQUENCE OF RadiusAuthClientExtEntry
         MAX-ACCESS  not-accessible
         STATUS      current
         DESCRIPTION
              "The (conceptual) table listing the RADIUS
               authentication clients with which the server
               shares a secret."
         ::= { radiusAuthServerExtMIBObjects 1 }

   radiusAuthClientExtEntry OBJECT-TYPE
         SYNTAX     RadiusAuthClientExtEntry
         MAX-ACCESS not-accessible
         STATUS     current
         DESCRIPTION
               "An entry (conceptual row) representing a RADIUS
                authentication client with which the server shares
                a secret."
         AUGMENTS      { radiusAuthClientEntry }
         ::= { radiusAuthServerExtTable 1 }

   RadiusAuthClientExtEntry ::= SEQUENCE {
         radiusAuthClientInetAddressType      InetAddressType,
         radiusAuthClientInetAddress          InetAddress
   }

   radiusAuthClientInetAddressType OBJECT-TYPE
         SYNTAX     InetAddressType
         MAX-ACCESS read-only
         STATUS     current
         DESCRIPTION
               "The type of address format used for the
                radiusAuthClientInetAddress object."
         ::= { radiusAuthClientExtEntry 1 }

   radiusAuthClientInetAddress OBJECT-TYPE
         SYNTAX     InetAddress
         MAX-ACCESS read-only
         STATUS     current
         DESCRIPTION
               "The IP address of the RADIUS authentication
                client referred to in this table entry, using
                the IPv6 adddess format."
         ::= { radiusAuthClientExtEntry 2 }

   -- conformance information

   radiusAuthServerExtMIBCompliances OBJECT IDENTIFIER
         ::= { radiusAuthServerExtMIBConformance 1 }

   radiusAuthServerExtMIBGroups      OBJECT IDENTIFIER
         ::= { radiusAuthServerExtMIBConformance 2 }

   -- compliance statements

   radiusAuthServerExtMIBCompliance MODULE-COMPLIANCE
        STATUS  current
        DESCRIPTION
              "The compliance statement for authentication
               servers implementing the RADIUS Authentication
               Server IPv6 Extensions MIB."
        MODULE  -- this module
               MANDATORY-GROUPS { radiusAuthServerExtMIBGroup }

        ::= { radiusAuthServerExtMIBCompliances 1 }

   -- units of conformance

   radiusAuthServerExtMIBGroup OBJECT-GROUP
        OBJECTS { radiusAuthClientInetAddressType,
                  radiusAuthClientInetAddress
               }
        STATUS  current
        DESCRIPTION
              "The collection of extended objects providing
               management of RADIUS Authentication Servers
               using IPv6 address format."
        ::= { radiusAuthServerExtMIBGroups 1 }

   END

-- 
--    Copyright (C) The Internet Society (2005).  This document is subject
--    to the rights, licenses and restrictions contained in BCP 78, and
--    except as set forth therein, the authors retain all their rights.
-- 
-- 
-- Acknowledgment
-- 
--    Funding for the RFC Editor function is currently provided by the
--    Internet Society.
