RAPID-CITY-VSP DEFINITIONS ::= BEGIN
 
-- ISSUES
--
-- None outstanding

IMPORTS

    TimeInterval, MODULE-IDENTITY, OBJECT-TYPE  FROM SNMPv2-SMI
    TEXTUAL-CONVENTION FROM 		SNMPv2-TC
    enterprises, IpAddress, TimeTicks   FROM RFC1155-SMI 
    Counter                 FROM RFC1155-SMI
    DisplayString           FROM RFC1213-MIB
    RowStatus, TruthValue, MacAddress   FROM SNMPv2-TC
    DateAndTime, TimeStamp, RowPointer      FROM SNMPv2-TC
    Gauge32, Integer32, NOTIFICATION-TYPE   FROM SNMPv2-SMI 
    Unsigned32, Counter32, Counter64    FROM SNMPv2-SMI
    StorageType                             FROM SNMPv2-TC
    MODULE-COMPLIANCE, OBJECT-GROUP         FROM SNMPv2-CONF
    AtmAddr                         FROM ATM-TC-MIB
    PhysAddress,ifIndex             FROM RFC1213-MIB
    InetAddressType, InetAddress            FROM INET-ADDRESS-MIB
    InetAddressPrefixLength                 FROM INET-ADDRESS-MIB
    ifAdminStatus, ifOperStatus 				FROM RFC1213-MIB
    InetPortNumber                          FROM INET-ADDRESS-MIB
    InetAutonomousSystemNumber              FROM INET-ADDRESS-MIB
    Ipv6IfIndex, Ipv6Address                FROM IPV6-TC
    Ipv6AddressPrefix                       FROM IPV6-TC
    Ipv6AddressIfIdentifier                 FROM IPV6-TC
    Ipv6IfIndexOrZero                       FROM IPV6-TC
    ifAdminStatus, ifOperStatus             FROM RFC1213-MIB
    igmpInterfaceIfIndex, igmpInterfaceQuerier	 	FROM IGMP-MIB
    dvmrpInterfaceIfIndex, dvmrpNeighborIfIndex,
    dvmrpNeighborAddress, dvmrpInterfaceOperState 	FROM DVMRP-MIB
    ifAdminStatus, ifOperStatus 				FROM RFC1213-MIB
    igmpCacheAddress, igmpCacheIfIndex		 	FROM IGMP-MIB
    ipNetToMediaNetAddress, ipNetToMediaPhysAddress       FROM RFC1213-MIB
    VrId                                          FROM VRRP-MIB
    SnmpAdminString,SnmpSecurityLevel,SnmpSecurityModel FROM SNMP-FRAMEWORK-MIB
    IndexInteger                                        FROM DIFFSERV-MIB
    MplsTunnelIndex, MplsLabel, MplsExtendedTunnelId,
    MplsTunnelInstanceIndex, MplsLdpIdentifier, MplsLSPID FROM MPLS-TC-STD-MIB
    bgpPeerRemoteAddr, bgpPeerLastError, bgpPeerState FROM BGP4-MIB;
rapidCity MODULE-IDENTITY
       LAST-UPDATED 	"9701010000Z"
       ORGANIZATION 	"Bay Networks, Rapid-City Group"
       CONTACT-INFO 	"		
					Edwin Tsang
                	 Postal: 	Bay Networks, Inc. 
                       			4401 Great America Parkway 
                       			Santa Clara, CA 95052-8185 

                   	 Tel: 		408-495-6159
                   	 Fax: 		408-495-5215 
                	 E-mail:	edwin_tsang@@baynetworks.com 
			"
       DESCRIPTION 	"Enterprise MIB for the Accelar product family."
       ::= { enterprises 2272 }

-- 
-- Local defines to avoid having to pull-in other RFC's.
--
BridgeId	      ::= TEXTUAL-CONVENTION
   STATUS       current
   DESCRIPTION  "An identifier that identifies the Bridge Id"
   SYNTAX       OCTET STRING (SIZE (8))

Timeout	   	::= TEXTUAL-CONVENTION
   STATUS       current
   DESCRIPTION  "An identifier that identifies the timeout value."
   SYNTAX       Integer32


EnableValue		::= TEXTUAL-CONVENTION
   STATUS       current
   DESCRIPTION  "Enable/Disable value."
   SYNTAX       INTEGER { enable(1), disable(2) }

RcLongDisplayString ::= TEXTUAL-CONVENTION
   STATUS       current
   DESCRIPTION  "The semantics are identical to the standard DisplayString 
                in RFC1213 and RFC2579, except for the longer length that
                is allowed with this TC. "
   SYNTAX       OCTET STRING (SIZE(0..65535))
--
-- This variable type is used through out the Rapid-City enterprise
-- MIB to denote the standard ifIndex in mib-2. 
--
InterfaceIndex	::= TEXTUAL-CONVENTION
   STATUS       current
   DESCRIPTION  "Port IfIndex."
   SYNTAX       Integer32 

InterfaceIndexOrZero ::= TEXTUAL-CONVENTION
    DISPLAY-HINT "d"
    STATUS       current
    DESCRIPTION
            "This textual convention is an extension of the
            InterfaceIndex convention.  The latter defines a greater
            than zero value used to identify an interface or interface
            sub-layer in the managed system.  This extension permits the
            additional value of zero.  the value zero is object-specific
            and must therefore be defined as part of the description of
            any object which uses this syntax.  Examples of the usage of
            zero might include situations where interface was unknown,
            or when none or all interfaces need to be referenced."
    SYNTAX       Integer32 (0..2147483647)


--
-- The string is 88 octets long, for a total of 704 bits. Each bit
-- corresponds to a port, as represented by its ifIndex value . When a
-- bit has the value one(1), the corresponding port is a member of the
-- set. When a bit has the value zero(0), the corresponding port is not
-- a member of the set. The encoding is such that the most significant
-- bit of octet #1 corresponds to ifIndex 0, while the least significant
-- bit of octet #88 corresponds to ifIndex 703."
--

PortSet         ::= TEXTUAL-CONVENTION
    STATUS      current
    DESCRIPTION
        "The string is 88 octets long, for a total of 704 bits. Each bit
         corresponds to a port, as represented by its ifIndex value . When a
         bit has the value one(1), the corresponding port is a member of the
         set. When a bit has the value zero(0), the corresponding port is not
         a member of the set. The encoding is such that the most significant
         bit of octet #1 corresponds to ifIndex 0, while the least significant
         bit of octet #88 corresponds to ifIndex 703. In order to accommodate
         future uses of this the string has a max size of 255 bytes."
    SYNTAX      OCTET STRING (SIZE (0..255))


IdList 		::= TEXTUAL-CONVENTION
   STATUS       current
   DESCRIPTION  "An identifier for a list of Ids."
   SYNTAX       OCTET STRING 

VrfIdentifier ::= TEXTUAL-CONVENTION
    STATUS current
    DESCRIPTION
            "Virtual Router Identifier.
             VRFID 0 is reserved for the Administrative VRF
             and cannot be used to create VRF's.
            "
    SYNTAX Unsigned32 (0..512)

Ipv6NextHdr ::= TEXTUAL-CONVENTION
   STATUS       current
   DESCRIPTION  "The ipv6 next header to look for."
   SYNTAX       INTEGER { 
                  hop-by-hop(0),   -- hop-by-hop
                  icmpv4(1),       -- icmpv4
                  igmpv4(2),       -- igmpv4
                  ipInIp(4),       -- ip in ip encapsulation 
                  tcp(6),          -- tcp
                  egp(8),          -- egp
                  udp(17),         -- udp
                  ipv6(41),        -- ipv6
                  routing(43),     -- routing extension hdr
                  frag(44),        -- fragmentation extension hdr
                  rsvp(46),        -- rsvp
                  ipsecESP(50),    -- ipsecESP
                  ipsecAh(51),     -- ipsecAh
                  icmpv6(58),      -- icmpv6
                  noNxtHdr(59),    -- not next hdr
                  destOptions(60), -- destination options extension hdr  
                  undefined(255)   -- not provisioned
                 }

RcVlanIdOrNone ::= TEXTUAL-CONVENTION
    STATUS current
    DESCRIPTION
            "Range of VLAN IDs supported for application"
    SYNTAX INTEGER (1..4084)


--
-- Additions to resolve some SNMP V2 dependencies so we don't
-- have to pull-in a lot of mib modules.
--                  
internet  	OBJECT IDENTIFIER ::= { iso org(3) dod(6) 1 }
snmpV2 		OBJECT IDENTIFIER ::= { internet 6 }
snmpModules 	OBJECT IDENTIFIER ::= { snmpV2 3 }
snmpMIB 	OBJECT IDENTIFIER ::= { snmpModules 1 }
snmpMIBObjects 	OBJECT IDENTIFIER ::= { snmpMIB 1 }
snmpTraps 	OBJECT IDENTIFIER ::= { snmpMIBObjects 5 }

--
-- Enterprise specific MIB groups
--
rcMgmt 			OBJECT IDENTIFIER ::= { rapidCity 1 }
rcA1100			OBJECT IDENTIFIER ::= { rapidCity 2 }
rcA1250    		OBJECT IDENTIFIER ::= { rapidCity 6 }
rcA1150    		OBJECT IDENTIFIER ::= { rapidCity 7 }
rcA1200    		OBJECT IDENTIFIER ::= { rapidCity 8 }
rcA1050    		OBJECT IDENTIFIER ::= { rapidCity 9 }
rcA740                  OBJECT IDENTIFIER ::= { rapidCity 20 }
rcA750                  OBJECT IDENTIFIER ::= { rapidCity 21 }
rcA790                  OBJECT IDENTIFIER ::= { rapidCity 22 }
rcA750S                 OBJECT IDENTIFIER ::= { rapidCity 23 }
rcA8003    		OBJECT IDENTIFIER ::= { rapidCity 280887555 }
rcA8006    		OBJECT IDENTIFIER ::= { rapidCity 280887558 }
rcA8010    		OBJECT IDENTIFIER ::= { rapidCity 280887562 }
rcA8010co               OBJECT IDENTIFIER ::= { rapidCity 1623064842 }
rcA8610    		OBJECT IDENTIFIER ::= { rapidCity 30 }
rcA8606    		OBJECT IDENTIFIER ::= { rapidCity 31 }
rcA8110    		OBJECT IDENTIFIER ::= { rapidCity 32 }
rcA8106    		OBJECT IDENTIFIER ::= { rapidCity 33 }
rcA8603    		OBJECT IDENTIFIER ::= { rapidCity 34 }
rcA8103    		OBJECT IDENTIFIER ::= { rapidCity 35 }
rcA8110co               OBJECT IDENTIFIER ::= { rapidCity 36 }
rcA8610co               OBJECT IDENTIFIER ::= { rapidCity 37 }
rcBayStack              OBJECT IDENTIFIER ::= { rapidCity 40 }
rcA1424                 OBJECT IDENTIFIER ::= { rapidCity 42 }
rcA1648                 OBJECT IDENTIFIER ::= { rapidCity 43 }
rcA1612                 OBJECT IDENTIFIER ::= { rapidCity 44 }
rcA1624                 OBJECT IDENTIFIER ::= { rapidCity 45 }
rcRBS2402               OBJECT IDENTIFIER ::= { rapidCity 46 }
-- From rapidCity 100 to rapidCity 200 is reserved for OM chassises
rcVSP9012               OBJECT IDENTIFIER ::= { rapidCity 201 }

rcSystem  		OBJECT IDENTIFIER ::= { rcMgmt 1 }
rcTftp 	  		OBJECT IDENTIFIER ::= { rcMgmt 2 }
rcVlan 	  		OBJECT IDENTIFIER ::= { rcMgmt 3 }
rcChassis 		OBJECT IDENTIFIER ::= { rcMgmt 4 }
rcMirror		OBJECT IDENTIFIER ::= { rcMgmt 5 }
rcDipSwitch		OBJECT IDENTIFIER ::= { rcMgmt 6 }
rcTblSize		OBJECT IDENTIFIER ::= { rcMgmt 7 }
rcIp			OBJECT IDENTIFIER ::= { rcMgmt 8 }
rcArp			OBJECT IDENTIFIER ::= { rcMgmt 9 }
rcRip			OBJECT IDENTIFIER ::= { rcMgmt 10 }
rcTest			OBJECT IDENTIFIER ::= { rcMgmt 11 }
rcStat			OBJECT IDENTIFIER ::= { rcMgmt 12 }
rcStg			OBJECT IDENTIFIER ::= { rcMgmt 13 }
rcBridge		OBJECT IDENTIFIER ::= { rcMgmt 14 }
rcBoot			OBJECT IDENTIFIER ::= { rcMgmt 15 }
rcDevice		OBJECT IDENTIFIER ::= { rcMgmt 16 }
rcMlt			OBJECT IDENTIFIER ::= { rcMgmt 17 }
rcWeb			OBJECT IDENTIFIER ::= { rcMgmt 18 }
rcCli			OBJECT IDENTIFIER ::= { rcMgmt 19 }
rcError			OBJECT IDENTIFIER ::= { rcMgmt 20 }
rcTraps			OBJECT IDENTIFIER ::= { rcMgmt 21 }
rcSyslog		OBJECT IDENTIFIER ::= { rcMgmt 22 }
rcDiag          	OBJECT IDENTIFIER ::= { rcMgmt 23 }
rcIpx 			OBJECT IDENTIFIER ::= { rcMgmt 24 }
rcPos                   OBJECT IDENTIFIER ::= { rcMgmt 26 }
rcLinkFlapDetect        OBJECT IDENTIFIER ::= { rcMgmt 27 }
rcV1Traps               OBJECT IDENTIFIER ::= { rcMgmt 28 }
rcRadius                OBJECT IDENTIFIER ::= { rcMgmt 29 }
rcIgmp                  OBJECT IDENTIFIER ::= { rcMgmt 30 }
rcUserSetTime           OBJECT IDENTIFIER ::= { rcMgmt 31 }
rcL2Redundancy          OBJECT IDENTIFIER ::= { rcMgmt 32 }
rcNtp        		OBJECT IDENTIFIER ::= { rcMgmt 33 }
rcSsh        		OBJECT IDENTIFIER ::= { rcMgmt 34 }
rcSvlan        		OBJECT IDENTIFIER ::= { rcMgmt 35 }
-- This is a place holder reminder reserved for OM 2.0
-- rcOpm    rcMgmt 36
-- rcVpn    rcMgmt 37
-- rcOeAdm  rcMgmt 38
-- rcTlsVpn rcMgmt 39
-- rcTls    rcMgmt 40
rcTengEnet      	OBJECT IDENTIFIER ::= { rcMgmt 50 }
rcRec                   OBJECT IDENTIFIER ::= { rcMgmt 51 }
-- rcTdc    rcMgmt 52
rcLacp                  OBJECT IDENTIFIER ::= { rcMgmt 53 }
-- rcQos    rcMgmt 54
-- rcFilter rcMgmt 55
rcLicense               OBJECT IDENTIFIER ::= { rcMgmt 56 }
rcEap                   OBJECT IDENTIFIER ::= { rcMgmt 57 }
rcFdb                   OBJECT IDENTIFIER ::= { rcMgmt 60 }
rcIpv6                  OBJECT IDENTIFIER ::= { rcMgmt 62 }
rcIsis                  OBJECT IDENTIFIER ::= { rcMgmt 63 }
rcSlpp                  OBJECT IDENTIFIER ::= { rcMgmt 64 }
--TACACS+
rcTacacs                OBJECT IDENTIFIER ::= { rcMgmt 65 }
rcIpfix                 OBJECT IDENTIFIER ::= { rcMgmt 66 }
rcOspfv3		OBJECT IDENTIFIER ::= { rcMgmt 67 }
rcCfm                   OBJECT IDENTIFIER ::= { rcMgmt 69 }
rcPlugOptMod            OBJECT IDENTIFIER ::= { rcMgmt 71 }
rcVrrp                  OBJECT IDENTIFIER ::= { rcMgmt 73 }
rcMpls  		OBJECT IDENTIFIER ::= { rcMgmt 74 }
rcIpMRoute  		OBJECT IDENTIFIER ::= { rcMgmt 76 }
rcPlsb                  OBJECT IDENTIFIER ::= { rcMgmt 78 }
rcKhi                   OBJECT IDENTIFIER ::= { rcMgmt 85 }

rc2k			OBJECT IDENTIFIER ::= { rcMgmt 100 }
rcPowerRanger           OBJECT IDENTIFIER ::= { rcMgmt 202 }
rcVrf                   OBJECT IDENTIFIER ::= { rcMgmt 203 }
rcCobaltBlue            OBJECT IDENTIFIER ::= { rcMgmt 204 }
rcVrrpv3                OBJECT IDENTIFIER ::= { rcMgmt 206 }
rcVspTalk               OBJECT IDENTIFIER ::= { rcMgmt 208 }

-- LOGICAL (System) Elements

rcSysIpAddr OBJECT-TYPE
        SYNTAX        IpAddress
        MAX-ACCESS    read-only
        STATUS        current
        DESCRIPTION   "This entity's IP address."
        ::= { rcSystem 1 }

rcSysNetMask OBJECT-TYPE
        SYNTAX        IpAddress
        MAX-ACCESS    read-only
        STATUS        current
        DESCRIPTION   "This entity's subnet mask."
        ::= { rcSystem 2 }

rcSysBroadcast OBJECT-TYPE
        SYNTAX        IpAddress
        MAX-ACCESS    read-only
        STATUS        current
        DESCRIPTION   "This entity's broadcast address."
        ::= { rcSystem 3 }

-- Other

rcSysVersion OBJECT-TYPE
	SYNTAX 		DisplayString (SIZE (0..80))
	MAX-ACCESS 		read-only
	STATUS 		current
	DESCRIPTION	"Software version running on device"
	::= { rcSystem 7 }

rcSysResult OBJECT-TYPE
	SYNTAX       INTEGER {
		         none(1),		-- none of the following
		         inProgress(2),		-- in progress
		         success(3),		-- success
		         fail(4),		-- failure
		         flashReadFailed(5),	-- could not read from flash
		         pcmciaReadFailed(6),	-- could not read from pcmcia
		         crcCheckFailed(7),
                         noStandbyCpu(8)
	              }
        MAX-ACCESS    read-only
        STATUS        current
	DESCRIPTION   "Result from the last system action."
	DEFVAL 	      { none }
        ::= { rcSystem 9 }

rcSysLastChange OBJECT-TYPE
        SYNTAX        TimeTicks
        MAX-ACCESS    read-only
        STATUS        current
        DESCRIPTION   "Last management initiated configuration 
		      change since sysUpTime."
        ::= { rcSystem 10 }

rcSysLastVlanChange OBJECT-TYPE
        SYNTAX        TimeTicks
        MAX-ACCESS    read-only
        STATUS        current
        DESCRIPTION   "Last management initiated VLAN configuration 
		      change since sysUpTime."
        ::= { rcSystem 11 }

rcSysLastStatisticsReset OBJECT-TYPE
        SYNTAX        TimeTicks
        MAX-ACCESS    read-only
        STATUS        current
        DESCRIPTION   "Last management initiated statistics reset 
		      since sysUpTime."
        ::= { rcSystem 12 }

-- Global Statistics

rcSysBufferUtil OBJECT-TYPE
	SYNTAX        INTEGER (0..100)
	MAX-ACCESS    read-only
	STATUS        current
	DESCRIPTION   "Buffer utilization as a percentage of the
                      total amount of buffer space in the system.  
                      A high value indicates congestion."
	::= { rcSystem 13 }

rcSysBufferUtilPeak OBJECT-TYPE
	SYNTAX        INTEGER (0..100)
	MAX-ACCESS    read-only
	STATUS        current
	DESCRIPTION   "The largest buffer utilization since sysUpTime"
	::= { rcSystem 14 }

rcSysBufferUtilPeakTime OBJECT-TYPE
	SYNTAX        TimeTicks
	MAX-ACCESS    read-only
	STATUS        current
	DESCRIPTION   "Timestamp for rcSysPeakBandwidth"
	::= { rcSystem 15 }

rcSysNVRamSize OBJECT-TYPE
	SYNTAX        Gauge32
	MAX-ACCESS    read-only
	STATUS        current
	DESCRIPTION   "Total Non-volatile RAM in Kbytes"
	::= { rcSystem 16 }

rcSysNVRamUsed OBJECT-TYPE
	SYNTAX        Gauge32
	MAX-ACCESS    read-only
	STATUS        current
	DESCRIPTION   "Non-volatile RAM in use in Kbytes"
	::= { rcSystem 17 }

rcSysLastSaveToNVRam    OBJECT-TYPE
        SYNTAX        TimeTicks
        MAX-ACCESS    read-only
        STATUS        current
        DESCRIPTION   "SysUpTime of the last time when NVRAM was
                      written to.  This could be a save of the system
                      configuration or via a file transfer of a
                      configuration file."
        ::= { rcSystem 18 }

rcSysLastSaveToStandbyNVRam OBJECT-TYPE
        SYNTAX        TimeTicks
        MAX-ACCESS    read-only
        STATUS        current
        DESCRIPTION   "SysUpTime of the last time when the standby NVRAM
                      (on the back-up CPU board) was written to."
        ::= { rcSystem 19 }

rcSysCpuUtil OBJECT-TYPE
        SYNTAX        Gauge32
        MAX-ACCESS    read-only
        STATUS        deprecated
        DESCRIPTION   "Percentage of CPU utilization.
		      This object is not supported on VSP. VSP uses
		      rcKhiSlotCpuCurrentUtil"
        ::= { rcSystem 20 }

rcSysRmonMemSize OBJECT-TYPE
        SYNTAX        INTEGER (250000..4000000)
        MAX-ACCESS    read-write
        STATUS        current
        DESCRIPTION   "Amount of RAM in bytes to allocate for RMON
                      to use when rcSysRmonEnable is TRUE."
        ::= { rcSystem 22 }

rcSysRmonEnable OBJECT-TYPE
        SYNTAX        TruthValue
        MAX-ACCESS    read-write
        STATUS        current
        DESCRIPTION   "Control whether the RMON feature should be
                      enabled.

		      To enable the RMON feature, set this variable to
		      true.  The RMON agent in the device will get 
                      started immediately if the amount of memory
		      specified by rcSysRmonMemSize is currently
		      available in the device.

		      To disable the RMON feature, set this variable to
		      false, save the new setting to NVRAM, and reboot
		      the device.  After the device is rebooted the
		      RMON agent will not be operational." 
        ::= { rcSystem 23 }

rcSysRmonTrapOption OBJECT-TYPE
        SYNTAX        INTEGER {
		 	 toOwner(1),
			 toAll(2)
		      }
        MAX-ACCESS    read-write
        STATUS        current
        DESCRIPTION   "Used to indicate whether RMON traps should be
		      sent to only the owner of the RMON alarm (i.e.,
		      the manager that created the alarm entry) or 
		      all trap recipients in the system trap receiver
		      table."
	DEFVAL	      { toOwner }
        ::= { rcSystem 25 }

rcSysSupportRouting OBJECT-TYPE
        SYNTAX        TruthValue
        MAX-ACCESS    read-only
        STATUS        current
        DESCRIPTION   "Used to indicate whether routing is supported
                      in this product."
        ::= { rcSystem 26 }

rcSysSupportWebServer OBJECT-TYPE
        SYNTAX        TruthValue
        MAX-ACCESS    read-only
        STATUS        current
        DESCRIPTION   "Used to indicate whether WebServer is supported
                      in this product."
        ::= { rcSystem 27 }

rcSysLastIpAddrChange OBJECT-TYPE
        SYNTAX        TimeTicks
        MAX-ACCESS    read-only
        STATUS        current
        DESCRIPTION   "Last management initiated IP address change 
                       since sysUpTime.  Any addition or deletion of
                       an IP address to a single routable port or
                       a VLAN is time-stamped by this variable."
        ::= { rcSystem 28 }

rcSysAccessPolicyEnable OBJECT-TYPE
        SYNTAX        TruthValue
        MAX-ACCESS    read-write
        STATUS        current
        DESCRIPTION   "Used to configure the system access policy feature.
		      if 'true', the rcSysAccessPolicyTable is examined to
		      determine which packets should be allowed or denied
                      access to this device." 
	DEFVAL	      { false }
        ::= { rcSystem 31 }

rcSysDefaultRuntimeConfigFileName OBJECT-TYPE
        SYNTAX        DisplayString
        MAX-ACCESS    read-only
        STATUS        current
        DESCRIPTION   "default config."
        ::= { rcSystem 32 }
 
rcSysDefaultBootConfigFileName OBJECT-TYPE
        SYNTAX        DisplayString
        MAX-ACCESS    read-only
        STATUS        current
        DESCRIPTION   "default boot config."
        ::= { rcSystem 33 }
 
rcSysConfigFileName OBJECT-TYPE
        SYNTAX        	DisplayString (SIZE(0..255))
        MAX-ACCESS        	read-write
        STATUS        	current
        DESCRIPTION   	"File name used in conjunction with rcSysAction.

			If rcSysAction is set to 'saveRuntimeConfig' or
			'saveRuntimeConfigToSlave' then this file name
			will be used instead of the file name specified
			in rcSysDefaultRuntimeConfigFileName.  

			If rcSysAction is set to 'saveBootConfig' or
			'saveBootConfigToSlave' then this file name will
			be used insteaad of the file name specified in
			rcSysDefaultBootConfigFileName.

			If the file name is blank (i.e., nothing is
			entered) then the default file name will be
			used."
        ::= { rcSystem 34 }
 
rcSysLastRunTimeConfigSave OBJECT-TYPE
        SYNTAX        TimeTicks
        MAX-ACCESS    read-only
        STATUS        current
        DESCRIPTION   "SysUpTime of the last time when the run time
                      configuration was written to."
        ::= { rcSystem 35 }

rcSysLastRunTimeConfigSaveToSlave OBJECT-TYPE
        SYNTAX        TimeTicks
        MAX-ACCESS    read-only
        STATUS        current
        DESCRIPTION   "SysUpTime of the last time when the run time
                      configuration was written to slave NVRAM."
        ::= { rcSystem 36 }

rcSysLastBootConfigSave OBJECT-TYPE
        SYNTAX        TimeTicks
        MAX-ACCESS    read-only
        STATUS        current
        DESCRIPTION   "SysUpTime of the last time when the boot
                      configuration was written to."
        ::= { rcSystem 37 }

rcSysLastBootConfigSaveOnSlave OBJECT-TYPE
        SYNTAX        TimeTicks
        MAX-ACCESS    read-only
        STATUS        current
        DESCRIPTION   "SysUpTime of the last time when the boot
                      configuration was written on the slave NVRAM."
        ::= { rcSystem 38 }

rcSysRmonUtilizationMethod OBJECT-TYPE	--excluded
        SYNTAX        INTEGER {
                         halfDuplex(1),
                         fullDuplex(2)
                      }
        MAX-ACCESS    read-write
        STATUS        current
        DESCRIPTION   "Used to control whether RMON should use a half-duplex
                       or full-duplex formula to calculate port utilization.
                       When set to 'halfDuplex', RMON will use InOctets and
                       the port's speed to calculate port utilization (this
                       is the standard RMON rfc1271 convention).
                       When set to 'fullDuplex', RMON will use InOctets and
                       OutOctets and 2X the port's speed to calculate port
                       utilization. Furthermore, if this variable is set to
                       'fullDuplex', but the port is operating in a
                       half-duplex mode, the calculation defaults back to
                       the rfc1271 convention."
        DEFVAL        { halfDuplex }
        ::= { rcSystem 39 }
 
rcSysOtherBufferUtil OBJECT-TYPE
        SYNTAX        Gauge32
        MAX-ACCESS    read-only
        STATUS        current
        DESCRIPTION   "bw currently consumed"
        ::= { rcSystem 41 }
 
rcSysOtherBufferUtilPeak OBJECT-TYPE
        SYNTAX        Gauge32
        MAX-ACCESS    read-only
        STATUS        current
        DESCRIPTION   "peak bw since reset"
        ::= { rcSystem 42 }

rcSysOtherBufferUtilPeakTime OBJECT-TYPE
        SYNTAX        TimeTicks
        MAX-ACCESS    read-only
        STATUS        current
        DESCRIPTION   "timestamp for rcSysPeakBw"
        ::= { rcSystem 43 }
 
rcSysOtherCpuUtil OBJECT-TYPE
        SYNTAX        Gauge32
        MAX-ACCESS    read-only
        STATUS        current
        DESCRIPTION   "% cpu utilization"
        ::= { rcSystem 44 }

rcSysDramSize OBJECT-TYPE
        SYNTAX        Integer32
        MAX-ACCESS    read-only
        STATUS        current
        DESCRIPTION   "Dram size in mega-bytes"
        ::= { rcSystem 46 }
 
rcSysDramUsed OBJECT-TYPE
        SYNTAX        Gauge32
        MAX-ACCESS    read-only
        STATUS        current
        DESCRIPTION   "Dram used in percentage"
        ::= { rcSystem 47 }
 
rcSysDramFree OBJECT-TYPE
        SYNTAX        Integer32
        MAX-ACCESS    read-only
        STATUS        current
        DESCRIPTION   "Dram free size in kilo-bytes"
        ::= { rcSystem 48 }
 
rcSysDramMaxBlockFree OBJECT-TYPE
        SYNTAX        Integer32
        MAX-ACCESS    read-only
        STATUS        current
        DESCRIPTION   "Dram max block free size in kilo-bytes"
        ::= { rcSystem 49 }
 
rcSysVirtualIpAddr OBJECT-TYPE
        SYNTAX        IpAddress
        MAX-ACCESS    read-write
        STATUS        current
        DESCRIPTION   "Virtual IP is an IP address that owned and
		       advertised only by the master CPU. So whichever 
		       CPU is master registers this IP address. Unlike the
		       management IP address, this address goes in the 
		       switch config file and not the boot config"
        ::= { rcSystem 51 }
 
rcSysVirtualNetMask OBJECT-TYPE
        SYNTAX        IpAddress
        MAX-ACCESS    read-write
        STATUS        current
        DESCRIPTION   "Net mask of the management virtual Ip address"
        ::= { rcSystem 52 }
 
rcSysReadWriteLevel OBJECT-TYPE
        SYNTAX        Integer32
        MAX-ACCESS    read-write
        STATUS        current
        DESCRIPTION   "The status of the read/write level"
        ::= { rcSystem 53 }

rcSysMTUSize OBJECT-TYPE
        SYNTAX        INTEGER {
                         mtu1950(1),
                         mtu9600(2),
                         mtu1522(3)
                      }
        MAX-ACCESS    read-write
        STATUS        current
        DESCRIPTION   "This is the maximum transmission size of frames that all
                       the ports on the chassis support."
        DEFVAL   { mtu1950 }
        ::= { rcSystem 55 }

rcSysForceTrapSender OBJECT-TYPE
        SYNTAX        TruthValue
        MAX-ACCESS    read-write
        STATUS        current
        DESCRIPTION   "This is a flag that if user wants to configured
                       CLIP (Circuit Less IP) as trap originator."
        ::= { rcSystem 57 }

rcSysMrouteStrLimit OBJECT-TYPE
        SYNTAX        TruthValue
        MAX-ACCESS    read-write
        STATUS        current
        DESCRIPTION   "enable or disable mroute stream limit in system."
        DEFVAL        { false }
        ::= { rcSystem 58 }

-- Access Policy Table
 
rcSysAccessPolicyTable OBJECT-TYPE
        SYNTAX        SEQUENCE OF RcSysAccesspolicyEntry
        MAX-ACCESS    not-accessible
        STATUS        current
        DESCRIPTION   "Management access policy table.  This table is 
		       used to permit or deny access to this device via
		       the specified source Id."
        ::= { rcSystem 61 }

rcSysAccessPolicyEntry OBJECT-TYPE
        SYNTAX        RcSysAccesspolicyEntry
        MAX-ACCESS    not-accessible
        STATUS        current
        DESCRIPTION   "An access policy table entry."
        INDEX         { rcSysAccessPolicyId }
        ::= { rcSysAccessPolicyTable 1 }
 
RcSysAccesspolicyEntry ::=
        SEQUENCE {
                rcSysAccessPolicyId INTEGER,
                rcSysAccessPolicyName DisplayString,
                rcSysAccessPolicyPolicyEnable TruthValue,
                rcSysAccessPolicyMode INTEGER,
                rcSysAccessPolicyService INTEGER,
                rcSysAccessPolicyPrecedence INTEGER,
                rcSysAccessPolicyTrustedHostUserName DisplayString,
                rcSysAccessPolicyAccessLevel INTEGER,
                rcSysAccessPolicyLog TruthValue,
                rcSysAccessPolicyUsage Counter32,
                rcSysAccessPolicyRowStatus RowStatus,
                rcSysAccessPolicyAccessStrict TruthValue,
                rcSysAccessPolicyNetInetAddrType INTEGER,
                rcSysAccessPolicyNetInetAddress InetAddress,
                rcSysAccessPolicyNetInetAddrPrefixLen InetAddressPrefixLength,
                rcSysAccessPolicyTrustedHostInetAddress InetAddress
        }
 
rcSysAccessPolicyId OBJECT-TYPE 
        SYNTAX        INTEGER (1..65535)
        MAX-ACCESS    read-only
        STATUS        current
        DESCRIPTION   "Policy Id."
        ::= { rcSysAccessPolicyEntry 1 } 

rcSysAccessPolicyName OBJECT-TYPE
        SYNTAX        DisplayString (SIZE (0..15))
        MAX-ACCESS    read-write
        STATUS        current
        DESCRIPTION   "Name of this policy."
        ::= { rcSysAccessPolicyEntry 2 }

rcSysAccessPolicyPolicyEnable OBJECT-TYPE
        SYNTAX        TruthValue
        MAX-ACCESS    read-write
        STATUS        current
        DESCRIPTION   "Indicate whether this policy is currently 
                       active."
	DEFVAL	      { true }
        ::= { rcSysAccessPolicyEntry 3 }

rcSysAccessPolicyMode OBJECT-TYPE
        SYNTAX        INTEGER {
                        allow(1), 
                        deny(2)
                      }          
        MAX-ACCESS    read-write
        STATUS        current
        DESCRIPTION   "Used to indicate whether a packet having a
		       source IP address that matches this entry
		       should be permitted to enter the device or
 		       denied access." 
	DEFVAL	      { allow }
        ::= { rcSysAccessPolicyEntry 4 }

rcSysAccessPolicyService OBJECT-TYPE
        SYNTAX        INTEGER (0..255) 
        MAX-ACCESS    read-write
        STATUS        current
        DESCRIPTION   "Is represented as bitset to indicate which protocol
                      this entry should be applied to.
                      Value is one of multiple(logical 'OR')
                      of the following values: 
                             telnet(1),
                             snmp(2),
                             tftp(4),
                             ftp(8),
                             http(16),
                             rlogin(32),
                             ssh(64),
                             snmp-v3(128)
                      telnet(1): enables telnet service
                      snmp(2): enables snmp service
                      tftp(4): enables tftp service
                      ftp(8): enables ftp service
                      http(16): enables http service
                      rlogin(32): enables rlogin service
                      ssh(64): enables ssh service
                      snmp-v3(128): enables snmp service for v3 groups
                      Value 0 means no service enabled."
        DEFVAL        { 0 }
        ::= { rcSysAccessPolicyEntry 5 }

-- Following between =begin =end is processed by mib_tools/extras.awk
-- =begin enum
-- rcSysAccessPolicyService none    0
-- rcSysAccessPolicyService telnet  1
-- rcSysAccessPolicyService snmp    2
-- rcSysAccessPolicyService tftp    4
-- rcSysAccessPolicyService ftp     8
-- rcSysAccessPolicyService http    16
-- rcSysAccessPolicyService rlogin  32
-- rcSysAccessPolicyService ssh     64
-- rcSysAccessPolicyService snmp_v3 128
-- rcSysAccessPolicyService all     255
-- =end enum

rcSysAccessPolicyPrecedence OBJECT-TYPE
        SYNTAX        INTEGER (1..128)
        MAX-ACCESS    read-write
        STATUS        current
        DESCRIPTION   "Used to indicate the precedence of this policy.
		       The Lower the number the higher the precedence."
	DEFVAL	      { 10 }
        ::= { rcSysAccessPolicyEntry 6 }

rcSysAccessPolicyTrustedHostUserName OBJECT-TYPE
        SYNTAX        DisplayString (SIZE (0..30))
        MAX-ACCESS    read-write
        STATUS        current
        DESCRIPTION   "User name on the trusted host performing a rlogin
                       into the device."
        ::= { rcSysAccessPolicyEntry 10 }

rcSysAccessPolicyAccessLevel OBJECT-TYPE
        SYNTAX        INTEGER {
                        readOnly(1), 
                        readWrite(2),
                        readWriteAll(3)
                      }          
        MAX-ACCESS    read-write
        STATUS        current
        DESCRIPTION   "Access level of trusted host." 
	DEFVAL	      { readOnly }
        ::= { rcSysAccessPolicyEntry 11 }

rcSysAccessPolicyLog OBJECT-TYPE
        SYNTAX        TruthValue
        MAX-ACCESS    read-write
        STATUS        current
        DESCRIPTION   "Used to indicate whether logging should be 
		       performed if this policy was applied."
	DEFVAL	      { false }
        ::= { rcSysAccessPolicyEntry 12 }

rcSysAccessPolicyUsage OBJECT-TYPE
        SYNTAX  	Counter32
        MAX-ACCESS  	read-only
        STATUS  	current
        DESCRIPTION 	"Usage Counter"
        ::= { rcSysAccessPolicyEntry 13 }

rcSysAccessPolicyRowStatus OBJECT-TYPE
        SYNTAX        RowStatus
        MAX-ACCESS    read-write
        STATUS        current
        DESCRIPTION   "Used to create/delete an entry"
        ::= { rcSysAccessPolicyEntry 14 }

rcSysAccessPolicyAccessStrict OBJECT-TYPE
        SYNTAX        TruthValue
        MAX-ACCESS    read-write
        STATUS        current
        DESCRIPTION   "Used to restrict the access level specified in
                       the system access policy table to exactly the
                       same access level as specified by user. If TRUE
                       then only the access level in the policy table
                       is allowed access. If FALSE, then the default
                       behavior is to assume the access level specified
                       in policy table as the floor."
          DEFVAL        { false }
        ::= { rcSysAccessPolicyEntry 15 }

rcSysAccessPolicyNetInetAddrType OBJECT-TYPE
        SYNTAX        INTEGER {
                          any(0),
                          ipv4(1),
                          ipv6(2)
                      }
        MAX-ACCESS    read-write
        STATUS        current
        DESCRIPTION   "Source network Inet Address Type."
        ::= { rcSysAccessPolicyEntry 16 }

rcSysAccessPolicyNetInetAddress OBJECT-TYPE
        SYNTAX        InetAddress
        MAX-ACCESS    read-write
        STATUS        current
        DESCRIPTION   "Source network Inet Address (prefix/network)."
        ::= { rcSysAccessPolicyEntry 17 }

rcSysAccessPolicyNetInetAddrPrefixLen OBJECT-TYPE
        SYNTAX        InetAddressPrefixLength
        MAX-ACCESS    read-write
        STATUS        current
        DESCRIPTION   "Source network Inet Address Prefix-Length/Mask."
        ::= { rcSysAccessPolicyEntry 18 }

rcSysAccessPolicyTrustedHostInetAddress OBJECT-TYPE
        SYNTAX        InetAddress
        MAX-ACCESS    read-write
        STATUS        current
        DESCRIPTION   "Trusted Inet address of host performing a rlogin
                       into the device."
        ::= { rcSysAccessPolicyEntry 19 }


rcSysAccPolSnmpGrpTable OBJECT-TYPE 
        SYNTAX        SEQUENCE OF RcSysAccPolSnmpGrpEntry 
        MAX-ACCESS    not-accessible 
        STATUS        current 
        DESCRIPTION   "SNMP group list for access policy" 
        ::= { rcSystem 95 } 

rcSysAccPolSnmpGrpEntry OBJECT-TYPE 
        SYNTAX        RcSysAccPolSnmpGrpEntry 
        MAX-ACCESS    not-accessible 
        STATUS        current 
        DESCRIPTION   "The  table entry which covers the groups under snmp service." 
        INDEX         { rcSysAccessPolicyId, rcSysAccPolSnmpGrpName, rcSysAccPolSnmpGrpModel} 
        ::= { rcSysAccPolSnmpGrpTable 1 } 

RcSysAccPolSnmpGrpEntry ::= 
        SEQUENCE { 
                rcSysAccPolSnmpGrpName SnmpAdminString, 
                rcSysAccPolSnmpGrpModel SnmpSecurityModel, 
                rcSysAccPolSnmpGrpRowStatus RowStatus 
        } 

rcSysAccPolSnmpGrpName         OBJECT-TYPE 
        SYNTAX       SnmpAdminString (SIZE(1..32)) 
        MAX-ACCESS   not-accessible 
        STATUS       current 
        DESCRIPTION "The snmp-v3 group name" 
        ::= { rcSysAccPolSnmpGrpEntry 1 } 

rcSysAccPolSnmpGrpModel OBJECT-TYPE 
        SYNTAX       SnmpSecurityModel 
        MAX-ACCESS   not-accessible 
        STATUS       current 
        DESCRIPTION "The snmp model" 
        ::= { rcSysAccPolSnmpGrpEntry 2 } 

rcSysAccPolSnmpGrpRowStatus OBJECT-TYPE 
        SYNTAX       RowStatus 
        MAX-ACCESS   read-write 
        STATUS       current 
        DESCRIPTION "Row status" 
        ::= { rcSysAccPolSnmpGrpEntry 3 } 

-- This is mib have no JDM support


-- Trap Sender Address Table
 
rcSysTrapSenderTable OBJECT-TYPE
        SYNTAX        SEQUENCE OF RcSysTrapSenderEntry
        MAX-ACCESS    not-accessible
        STATUS        current
        DESCRIPTION   "The trap sender table (0 to 25 entries).  This
                      table lists the addresses of Network Management
                      Stations and the Source Address that should receive 
                      trap messages from this entity when an exception 
                      condition occurs."
        ::= { rcSystem 62 }

rcSysTrapSenderEntry OBJECT-TYPE
        SYNTAX        RcSysTrapSenderEntry
        MAX-ACCESS    not-accessible
        STATUS        current
        DESCRIPTION   "A trap sender table entry."
        INDEX         { rcSysTrapSenderRecvAddress }
        ::= { rcSysTrapSenderTable 1 }
 
RcSysTrapSenderEntry ::=
        SEQUENCE {
                rcSysTrapSenderRecvAddress IpAddress,
                rcSysTrapSenderSrcAddress  IpAddress
        }
 
rcSysTrapSenderRecvAddress OBJECT-TYPE
        SYNTAX        IpAddress
        MAX-ACCESS    read-only
        STATUS        current
        DESCRIPTION   "IP address for trap receiver."
        ::= { rcSysTrapSenderEntry 1 }
 
rcSysTrapSenderSrcAddress OBJECT-TYPE
        SYNTAX        IpAddress 
        MAX-ACCESS    read-write
        STATUS	      current
        DESCRIPTION   "IP address for trap sender."
	       ::= { rcSysTrapSenderEntry 2 }

-- DNS Server List Mibs 

rcSysDnsServerListTable OBJECT-TYPE 
        SYNTAX        SEQUENCE OF RcSysDnsServerListEntry 
        MAX-ACCESS    not-accessible 
        STATUS        current 
        DESCRIPTION   "DNS serever list table used to store the 
                       details of the DNS server configured." 
        ::= { rcSystem 64 } 

rcSysDnsServerListEntry OBJECT-TYPE 
        SYNTAX        RcSysDnsServerListEntry 
        MAX-ACCESS    not-accessible 
        STATUS        current 
        DESCRIPTION   "table entry." 
        INDEX         { rcSysDnsServerListType }  
        ::= { rcSysDnsServerListTable 1 } 

RcSysDnsServerListEntry ::= 
        SEQUENCE { 
                rcSysDnsServerListType          INTEGER, 
                rcSysDnsServerListStatus        INTEGER, 
                rcSysDnsServerListRequestCount  Counter32, 
                rcSysDnsServerListSuccessCount  Counter32, 
                rcSysDnsServerListRowStatus     RowStatus,
                rcSysDnsServerListAddressType   InetAddressType,
                rcSysDnsServerListAddress       InetAddress
        } 

rcSysDnsServerListType OBJECT-TYPE 
        SYNTAX        INTEGER { 
                         primary(0), 
                         secondary(1), 
                         tertiary(2) 
                      } 
        MAX-ACCESS    read-only 
        STATUS        current 
        DESCRIPTION   "Type of the DNS server" 
        ::= { rcSysDnsServerListEntry 1 } 

rcSysDnsServerListStatus OBJECT-TYPE 
        SYNTAX        INTEGER { 
                         active(0), 
                         in-active(1) 
                      } 
        MAX-ACCESS    read-only 
        STATUS        current 
        DESCRIPTION   "Status of DNS server" 
        ::= { rcSysDnsServerListEntry 3 } 

rcSysDnsServerListRequestCount OBJECT-TYPE 
        SYNTAX        Counter32 
        MAX-ACCESS    read-only 
        STATUS        current 
        DESCRIPTION   "Number of request send to this server" 
        ::= { rcSysDnsServerListEntry 4 } 

rcSysDnsServerListSuccessCount OBJECT-TYPE 
        SYNTAX        Counter32 
        MAX-ACCESS    read-only 
        STATUS        current 
        DESCRIPTION   "Number of request send to this server which 
                       are successful" 
        ::= { rcSysDnsServerListEntry 5 } 

rcSysDnsServerListRowStatus OBJECT-TYPE 
        SYNTAX        RowStatus 
        MAX-ACCESS    read-write 
        STATUS        current 
        DESCRIPTION   "Used to create/delete DNS server entries 
                       in rcSysDnsServerListTable." 
        ::= { rcSysDnsServerListEntry 6 } 

rcSysDnsServerListAddressType  OBJECT-TYPE
        SYNTAX     InetAddressType
        MAX-ACCESS read-write
        STATUS     current
        DESCRIPTION
               "The address type of DNS Server."
        ::= { rcSysDnsServerListEntry 7 }

rcSysDnsServerListAddress  OBJECT-TYPE
        SYNTAX     InetAddress
        MAX-ACCESS read-write
        STATUS     current
        DESCRIPTION
               "The address of the DNS Server"
        ::= { rcSysDnsServerListEntry 8 }

-- DNS Server List End

-- DNS Host Table

rcSysDnsHostTable OBJECT-TYPE
        SYNTAX        SEQUENCE OF RcSysDnsHostEntry
        MAX-ACCESS    not-accessible
        STATUS        current
        DESCRIPTION   "DNS Host table."
        ::= { rcSystem 65 }

rcSysDnsHostEntry OBJECT-TYPE
        SYNTAX        RcSysDnsHostEntry
        MAX-ACCESS    not-accessible
        STATUS        current
        DESCRIPTION   "table entry."
        INDEX         { rcSysDnsHostData }
        ::= { rcSysDnsHostTable 1 }

RcSysDnsHostEntry ::=
        SEQUENCE {
                rcSysDnsHostData          OCTET STRING,
                rcSysDnsHostName          OCTET STRING (SIZE(0..256)),
                rcSysDnsHostSource        OCTET STRING (SIZE(0..256)),
                rcSysDnsHostAddressType   InetAddressType,
                rcSysDnsHostAddress       InetAddress
        }

rcSysDnsHostData OBJECT-TYPE
        SYNTAX        OCTET STRING (SIZE(0..256))
        MAX-ACCESS    read-only
        STATUS        current
        DESCRIPTION   "Host Name or Host IP Address."
        ::= { rcSysDnsHostEntry 1 }

rcSysDnsHostName OBJECT-TYPE
        SYNTAX        OCTET STRING (SIZE(0..256))
        MAX-ACCESS    read-only
        STATUS        current
        DESCRIPTION   "Host Name."
        ::= { rcSysDnsHostEntry 2 }

rcSysDnsHostSource OBJECT-TYPE
        SYNTAX        OCTET STRING (SIZE(0..256))
        MAX-ACCESS    read-only
        STATUS        obsolete 
        DESCRIPTION   "DNS Server IP or /etc/host file."
        ::= { rcSysDnsHostEntry 4 }

rcSysDnsHostAddressType OBJECT-TYPE
        SYNTAX        InetAddressType
        MAX-ACCESS    read-only
        STATUS        current
        DESCRIPTION   "Address Type of the Host."
        ::= { rcSysDnsHostEntry 5 }

rcSysDnsHostAddress OBJECT-TYPE
        SYNTAX        InetAddress
        MAX-ACCESS    read-only
        STATUS        current
        DESCRIPTION   "Address of the Host."
        ::= { rcSysDnsHostEntry 6 }

-- DNS Host Table End

rcSysMsgLogFrequency OBJECT-TYPE
        SYNTAX        INTEGER (2..500)
        MAX-ACCESS    read-only
        STATUS        current
        DESCRIPTION   "Used to specify the maximum frequency/count
                       of the occurence of the Log Message."
        ::= { rcSystem 66 }

rcSysMsgLogText OBJECT-TYPE
        SYNTAX        DisplayString (SIZE(0..3))
        MAX-ACCESS    read-only
        STATUS        current
        DESCRIPTION   "A textual string containing the first four
                       characters of the Log Message."
        ::= { rcSystem 67 }

rcSysForceIpHdrSender OBJECT-TYPE
        SYNTAX        TruthValue
        MAX-ACCESS    read-write
        STATUS        current
        DESCRIPTION   "Flag to decide if IP header source address will
                       be matched with SNMP header sender networks."
        DEFVAL        { false }
        ::= { rcSystem 68 }

rcSysDnsDomainName OBJECT-TYPE
        SYNTAX        DisplayString (SIZE (0..255))
        MAX-ACCESS    read-write
        STATUS        current
        DESCRIPTION   "Default domain used for querying the DNS Server."
        ::= { rcSystem 70 }
--DNS end

rcSysDnsServerListIpAddr OBJECT-TYPE
        SYNTAX        IpAddress
        MAX-ACCESS    read-only
        STATUS        current
        DESCRIPTION   "DNS server's IP address "
        ::= { rcSystem 71 }

rcSysDnsRequestType OBJECT-TYPE
        SYNTAX        INTEGER {
                      request (0),
                      response (1)
                      }
        MAX-ACCESS    read-only
        STATUS        current
        DESCRIPTION   "DNS Type: Whether it was Dns Request or a Response"
        ::= { rcSystem 72 }

rcSysSpanningTreeOperMode OBJECT-TYPE
        SYNTAX       INTEGER {
                       nortelStpg(1),
                       pvst(2),
                       rstp(3),
                       mstp(4)
                     }
         MAX-ACCESS   read-only
         STATUS       current
         DESCRIPTION  "This object indicates the current spanning-tree mode
                       of the system.
                       The meaning of specific values is:
                       nortelStpg(1) .. The older proprietary mode which
                                  supports multiple spanning tree groups.
                       pvst(2) ..Emulation of C***O spanning tree mode
                       rstp(3) ..IEEE 802.1w mode
                       mstp(4) ..IEEE 802.1s mode ."
         DEFVAL        { nortelStpg }
         ::= { rcSystem 73}

rcSysSpanningTreeAdminMode OBJECT-TYPE
         SYNTAX       INTEGER {
                         nortelStpg(1),
                         pvst(2),
                         rstp(3),
                         mstp(4)
                      }
         MAX-ACCESS   read-write
         STATUS       current
         DESCRIPTION  "This object indicates the desired spanning-tree mode
                       of the system.
                       The meaning of specific values is:
                       nortelStpg(1) .. The older proprietary mode which
                                  supports multiple spanning tree groups.
                       pvst(2) ..Emulation of C***O spanning tree mode
                       rstp(3) ..IEEE 802.1w mode
                       mstp(4) ..IEEE 802.1s mode .
                       Note that depending on the current value of
                       rcSysSpanningTreeOperMode and the value to which this
                       object is set, the operational mode may be immediately
                       changed, or the change may not take effect until
                       the next system reboot."
          DEFVAL        { nortelStpg }
          ::= { rcSystem 74}

rcSysAutoRecoverDelay  OBJECT-TYPE
        SYNTAX        INTEGER (5..3600)
        MAX-ACCESS    read-write
        STATUS        current
        DESCRIPTION  "Time interval in seconds after which auto-recovery
                      runs on ports to clear action taken by cp-limit, 
                      link flap or loop detect"
        ::= { rcSystem 75 }

rcSysMacFlapLimitTime  OBJECT-TYPE
        SYNTAX        INTEGER (10..5000)
        MAX-ACCESS    read-write
        STATUS        current
        DESCRIPTION  "Time limit in milliseconds for MAC flapping for
                      loop-detect feature"
        ::= { rcSystem 76 }

rcSysMacFlapLimitCount  OBJECT-TYPE
        SYNTAX        Integer32
        MAX-ACCESS    read-only
        STATUS        current
        DESCRIPTION  "Number of times mac flapping can happen for loop-detect
                      feature"
        ::= { rcSystem 77 }

rcSysExtCplimitEnable  OBJECT-TYPE
        SYNTAX        TruthValue
        MAX-ACCESS    read-write
        STATUS        current
        DESCRIPTION   "enable or disable extended CP-LIMIT in system."
        DEFVAL        { false }
        ::= { rcSystem 78 }

rcSysExtCplimitMinCongTime  OBJECT-TYPE
        SYNTAX        INTEGER (100..6000)
        MAX-ACCESS    read-write
        STATUS        current
        DESCRIPTION   "Minimum time for which System octapid should be
                      congested to trigger congestion algorithm for extended
                      CP-LIMIT in mSecs"
        DEFVAL        { 3000 }
        ::= { rcSystem 79 }

rcSysExtCplimitMaxPorts  OBJECT-TYPE
        SYNTAX        INTEGER (0..512)
        MAX-ACCESS    read-write
        STATUS        current
        DESCRIPTION   "Maximum number of ports which need to be monitored
                      for congestion in Extended CP-LIMIT"
        DEFVAL        { 0 }
        ::= { rcSystem 80 }

rcSysExtCplimitPortCongTime  OBJECT-TYPE
        SYNTAX        INTEGER (1..600)
        MAX-ACCESS    read-write
        STATUS        current
        DESCRIPTION   "Minimum time for which ingress traffic utilization rate
                      of a monitored port should stay more than the allowed
                      limits in order to disable the port for extended 
                      CP-LIMIT in Secs"
        DEFVAL        { 300 }
        ::= { rcSystem 81 }

rcSysExtCplimitTrapLevel  OBJECT-TYPE
        SYNTAX        INTEGER {
                         none(1),
                         normal(2),
                         verbose(3)
                      }        
        MAX-ACCESS    read-write
        STATUS        current
        DESCRIPTION   "Indicates the trap level for extended CP-LIMIT"
        DEFVAL        { none }
        ::= { rcSystem 82 }

rcSysExtCplimitSysOctapidCongested OBJECT-TYPE
        SYNTAX        TruthValue
        MAX-ACCESS    read-only
        STATUS        current
        DESCRIPTION   "Indicates whether system octapid congestion detected for
                      extended cp-limit"
        DEFVAL        { false }
        ::= {rcSystem 83 }

rcSysExtCplimitPortsMonitored OBJECT-TYPE
        SYNTAX        TruthValue
        MAX-ACCESS    read-only
        STATUS        current
        DESCRIPTION   "Indicates whether ports has been shutdown due to extended
                      cp-limit"
        DEFVAL        { false }
        ::= {rcSystem 84 }

rcSysExtCplimitPortsShutDown OBJECT-TYPE
        SYNTAX        TruthValue
        MAX-ACCESS    read-only
        STATUS        current
        DESCRIPTION   "Indicates whether ports has been shutdown due to
                      extended Cp-limit"
        DEFVAL        { false }
        ::= {rcSystem 85 }

rcSysActionL1 OBJECT-TYPE
        SYNTAX       INTEGER {
                         none(1),
                         resetCounters(2),      -- reset all statistic counters
                         saveRuntimeConfig(7),     -- 8k only
                         saveRuntimeConfigToSlave(8),  -- 8k only
                         loadLicense(11)
                     }
        MAX-ACCESS    read-write
        STATUS        current
        DESCRIPTION   "Initiate a system action for layer1 user"
        DEFVAL        { none } 
        ::= { rcSystem 86 }

rcSysActionL2 OBJECT-TYPE
        SYNTAX       INTEGER {
                         none(1),
                         resetIstStatCounters(2)
                     }
        MAX-ACCESS    read-write
        STATUS        current
        DESCRIPTION   "Initiate a system action for layer2 user"
        DEFVAL        { none }
        ::= { rcSystem 87 }

rcSysActionL3 OBJECT-TYPE
        SYNTAX       INTEGER {
                         none(1),
                         flushIpRouteTbl(2)
                     }
        MAX-ACCESS    read-write
        STATUS        current
        DESCRIPTION   "Initiate a system action for layer3 user"
        DEFVAL        { none }
        ::= { rcSystem 88 }

rcSysActionRwa OBJECT-TYPE
        SYNTAX       INTEGER {
                         none(1),               -- none of the following
                         hardReset(2),          -- power on tests
                         softReset(3),          -- reset w/o power on tests
                         cpuSwitchOver(4)       -- CPU board switch-over
                     }
        MAX-ACCESS    read-write
        STATUS        current
        DESCRIPTION   "Initiate a system action."
        DEFVAL        { none }
        ::= { rcSystem 89 }

rcSysPowerUsage OBJECT-TYPE
        SYNTAX        Integer32
        MAX-ACCESS    read-only
        STATUS        current
        DESCRIPTION   "The current power usage for the whole chassis."
        ::= { rcSystem 90 }

rcSysPowerAvailable OBJECT-TYPE
        SYNTAX        Integer32
        MAX-ACCESS    read-only
        STATUS        current
        DESCRIPTION   "The current power available for the whole chassis."
        ::= { rcSystem 91 }

rcSysFrcMsgControlTable OBJECT-TYPE
        SYNTAX        SEQUENCE OF RcSysFrcMsgControlEntry
        MAX-ACCESS    not-accessible
        STATUS        current
        DESCRIPTION   "Management Force-msg Control table. This table is used to

                       specify the pattern for Force-msg Control"
        ::= { rcSystem 94 }

rcSysVirtualIpv6Addr OBJECT-TYPE
        SYNTAX        Ipv6Address
        MAX-ACCESS    read-write
        STATUS        current
        DESCRIPTION   "Virtual IP is an IP address that owned and
                       advertised only by the master CPU. So whichever
                       CPU is master registers this IP address."
        ::= { rcSystem 96 }

rcSysVirtualIpv6PrefixLength OBJECT-TYPE
        SYNTAX         INTEGER (0..128)
        MAX-ACCESS     read-write
        STATUS         current
        DESCRIPTION    "The length of the virtual ipv6 addr prefix (in bits)."
        ::= { rcSystem 97 }

rcSysLicenseTrialDaysLeft OBJECT-TYPE
        SYNTAX        Unsigned32 (0..60)
        MAX-ACCESS    read-only
        STATUS        current
        DESCRIPTION   "This indicates days left before License Trial
                      Period will expire."
        ::= { rcSystem 100}

rcSysTotalPower OBJECT-TYPE
        SYNTAX        Integer32
        MAX-ACCESS    read-only
        STATUS        current
        DESCRIPTION   "The  total power for the whole chassis."
        ::= { rcSystem 116 }

rcSysRedundantPower OBJECT-TYPE
        SYNTAX        Integer32
        MAX-ACCESS    read-only
        STATUS        current
        DESCRIPTION   "Used to indicate the redundant power on the chassis.
		       The redundant power is per power supply unit"
        ::= { rcSystem 117 }

rcSysAuthSuccessTrapEnable OBJECT-TYPE
        SYNTAX        TruthValue
        MAX-ACCESS    read-write
        STATUS        current
        DESCRIPTION   "Used to enable/disable the trap send for authenticaion
			success trap rcnAuthenticationSuccess. It only allow
			to be set when snmpEnableAuthenTraps is enabled.
			I will be set to disable when snmpEnableAuthenTraps is
			disabled"
        ::= { rcSystem 118 }

rcSysUdpSrcByVirtualIpEnable OBJECT-TYPE
	SYNTAX	      TruthValue
	MAX-ACCESS    read-write
	STATUS        current
	DESCRIPTION   "Used to enable/disable virtual ip as udp source."
	DEFVAL	      { false }
	::= { rcSystem 119 }

rcSysFrcMsgControlEntry OBJECT-TYPE
        SYNTAX        RcSysFrcMsgControlEntry
        MAX-ACCESS    not-accessible
        STATUS        current
        DESCRIPTION   "A  Force-msg Control table entry."
        INDEX         { rcSysFrcMsgControlPatternId }
        ::= { rcSysFrcMsgControlTable 1 }

RcSysFrcMsgControlEntry ::=
        SEQUENCE {
                rcSysFrcMsgControlPatternId Integer32,
                rcSysFrcMsgControlPattern DisplayString,
                rcSysFrcMsgControlRowStatus RowStatus
        }

rcSysFrcMsgControlPatternId OBJECT-TYPE
        SYNTAX        Integer32 (1..32)
        MAX-ACCESS    not-accessible
        STATUS        current
        DESCRIPTION   "Pattern Id."
        ::= { rcSysFrcMsgControlEntry 1 }


rcSysFrcMsgControlPattern OBJECT-TYPE
        SYNTAX        DisplayString (SIZE (4))
        MAX-ACCESS    read-write
        STATUS        current
        DESCRIPTION   "Pattern for filtering the force-msg for msg control"
        ::= { rcSysFrcMsgControlEntry 2 }

rcSysFrcMsgControlRowStatus OBJECT-TYPE
        SYNTAX        RowStatus
        MAX-ACCESS    read-write
        STATUS        current
        DESCRIPTION   "Used to create/delete an entry"
        ::= { rcSysFrcMsgControlEntry 3 }

-- TFTP Upload/Download

rcTftpHost OBJECT-TYPE
        SYNTAX        IpAddress
        MAX-ACCESS    read-write
        STATUS        current
        DESCRIPTION   "Name of source/destination host for the TFTP
                      transfer."
        ::= { rcTftp 1 }

rcTftpFile OBJECT-TYPE
        SYNTAX      DisplayString (SIZE (0..255))
        MAX-ACCESS  read-write
        STATUS      current
        DESCRIPTION "Name of file for the TFTP transfer."
        ::= { rcTftp 2 }

rcTftpAction OBJECT-TYPE
        SYNTAX        INTEGER {
                          none(1),          -- none of the following
                          downloadConfig(2),
                          uploadConfig(3),
                          downloadSwToFlash(4),
                          downloadSwToPcmcia(5),
                          uploadSw(6),
                          downloadSwToDram(7)
                      }
        MAX-ACCESS	  read-write
        STATUS	      current
        DESCRIPTION   "The action for the TFTP transfer."
        DEFVAL        { none }
	::= { rcTftp 3 }

rcTftpResult OBJECT-TYPE
        SYNTAX        INTEGER {
                          none(1),
                          inProgress(2),
                          noResponse(3),
                          fileAccessError(4),
                          badFlash(5),
                          flashEraseFailed(6),
                          pcmciaEraseFailed(7),
                          success(8),
                          fail(9),
                          writeToNvramFailed(10),
                          flashWriteFailed(11),
                          pcmciaWriteFailed(12),
                          configFileTooBig(13),
                          imageFileTooBig(14),
                          noPcmciaDetect(15),
                          pcmciaNotSupported(16),
                          invalidFile(17),
                          noMemory(18),
                          xferError(19),
                          crcError(20),
                          readNvramFailed(21),
                          pcmciaWriteProtect(22)
	              }
        MAX-ACCESS    read-only
        STATUS        current
        DESCRIPTION   "Contains result of the last Tftp action request."
        ::= { rcTftp 4 }


-- VLAN Table

rcVlanNumVlans OBJECT-TYPE
        SYNTAX        INTEGER (1..128)
        MAX-ACCESS    read-only
        STATUS        current
        DESCRIPTION   "The number of VLANs currently defined in the switch."
        ::= { rcVlan 1 }

rcVlanTable OBJECT-TYPE
        SYNTAX        SEQUENCE OF RcVlanEntry
        MAX-ACCESS    not-accessible
        STATUS        current
        DESCRIPTION   "A list of Virtual LAN entries. The number of entries
                      is given by rcVlanNumVlans."
        ::= { rcVlan 2 }

rcVlanEntry OBJECT-TYPE
        SYNTAX        RcVlanEntry
        MAX-ACCESS    not-accessible
        STATUS        current
        DESCRIPTION   "Entry containing configuration information for a 
                      particular Virtual LAN.

                      The relationship between the various port sets in a 
                      VLAN Entry are :

                      o The set of ports defined by PortMembers must be a 
                        subset of the set of ports in the underlying STG of 
                        the VLAN.

                      o The bitwise AND of PortMembers and NotAllowToJoin must 
                        be the empty set.

                      o The bitwise OR of PortMembers and NotAllowToJoin must 
                        be the set of ports in the underlying STG of the VLAN.

                      o The set of ports defined by StaticMembers must be a 
                        subset of the set of ports defined by PortMembers.

                      o The bitwise XOR of PortMembers and StaticMembers defines 
                        the set of dynamic (potential) members of the VLAN.

                      o The set of ports defined by ActiveMembers must be a subset 
                        of the set of ports defined by PortMembers.
                      "
        INDEX         { rcVlanId }
        ::= { rcVlanTable 1 }

RcVlanEntry ::= SEQUENCE {
                rcVlanId RcVlanIdOrNone,
                rcVlanName DisplayString,
                rcVlanColor INTEGER,
                rcVlanIfIndex InterfaceIndex,
                rcVlanAction INTEGER,
                rcVlanResult INTEGER,
                rcVlanStgId INTEGER,
                rcVlanType INTEGER,
                rcVlanPortMembers PortSet,
                rcVlanActiveMembers PortSet,
                rcVlanStaticMembers PortSet,
                rcVlanNotAllowToJoin PortSet,
                rcVlanProtocolId INTEGER,
                rcVlanSubnetAddr IpAddress,
                rcVlanSubnetMask IpAddress,
                rcVlanAgingTime  INTEGER,
                rcVlanMacAddress MacAddress,
                rcVlanRowStatus RowStatus,
                rcVlanUserDefinedPid Integer32,
                rcVlanProtocolIds Integer32,
                rcVlanTosValue INTEGER,
                rcVlanEncap INTEGER,
                rcVlanOspfPassivePortMember PortSet,
                rcVlanFdbAging INTEGER,
                rcVlanNlbMode INTEGER,
                rcVlanVrfId VrfIdentifier,
                rcVlanVrfName DisplayString,
                rcVlanNodalMepList DisplayString,
                rcVlanNumOfNodalMep Integer32,
                rcVlanNodalMipLevelList DisplayString,
                rcVlanNumOfNodalMipLevel Integer32,
                rcVlanPlsbIsid Integer32
        }

rcVlanId OBJECT-TYPE
        SYNTAX        RcVlanIdOrNone
        MAX-ACCESS    read-only
        STATUS        current
        DESCRIPTION   "A value that uniquely identifies the Virtual LAN 
                      associated with this entry. This value corresponds
                      to the lower 12 bits in the IEEE 802.1Q VLAN Tag."
        ::= { rcVlanEntry 1 }

rcVlanName OBJECT-TYPE
        SYNTAX        DisplayString (SIZE (0..64))
        MAX-ACCESS    read-write
        STATUS        current
        DESCRIPTION   "An administratively-assigned name for this VLAN."
        ::= { rcVlanEntry 2 }

rcVlanColor OBJECT-TYPE
        SYNTAX        INTEGER (0..32)
        MAX-ACCESS    read-write
        STATUS        current
        DESCRIPTION   "An administratively-assigned color code for this
                      VLAN. The value of this object is used by the VLAN
                      Manager GUI tool to select a color when it draws
                      this VLAN on the screen."
        ::= { rcVlanEntry 3 }

rcVlanIfIndex OBJECT-TYPE
        SYNTAX        InterfaceIndex 
        MAX-ACCESS    read-only
        STATUS        current
        DESCRIPTION   "When rcVlanRoutingEnable is set to true(1), this 
                      value indicates the 'logical' ifIndex assigned to
                      this VLAN.  Otherwise, this value is meaningless
                      and should be set to zero."
        ::= { rcVlanEntry 6 }

rcVlanAction OBJECT-TYPE
        SYNTAX        INTEGER {
                         none(1),             -- none of the following
                         flushMacFdb(2),      -- flush MAC forwarding table
                         flushArp(3),         -- flush ARP table
                         flushIp(4),          -- flush IP route table
                         flushDynMemb(5),     -- flush Dynamic Members
                         all(6),              -- flush all tables 
			 flushSnoopMemb(7),   -- flush IGMP Snoop Members
                         triggerRipUpdate(8), -- manually trigger rip update
			 flushSnoopMRtr(9),    -- flush snoop multicast router
                         flushIpRsmltEdgePeer(10) -- flush IP rsmlt edge peer
                      }
        MAX-ACCESS    read-write
        STATUS        current
        DESCRIPTION   "VLAN related actions."
        DEFVAL        { none }
        ::= { rcVlanEntry 7 }

rcVlanResult OBJECT-TYPE
        SYNTAX        INTEGER {
                         none(1),        -- none of the following
                         inProgress(2),  -- in progress
                         success(3),     -- success
                         fail(4)         -- failure
                      }
        MAX-ACCESS    read-only
        STATUS        current
        DESCRIPTION   "The result from the last VLAN action."
        DEFVAL        { none }
        ::= { rcVlanEntry 8 }

rcVlanStgId OBJECT-TYPE
        SYNTAX        INTEGER (0..128)
        MAX-ACCESS    read-write
        STATUS        current
        DESCRIPTION   "Indicates the Spanning Tree Group (STG) used by
                      this VLAN to determine the state of its ports.
                      If this VLAN is not associated with any STG, this
                      value should be set to zero."
        DEFVAL        { 1 }
        ::= { rcVlanEntry 9 }

rcVlanType OBJECT-TYPE
        SYNTAX        INTEGER {
                         byPort(1),       -- VLAN by Port 
                         byIpSubnet(2),   -- VLAN by IP subnet 
                         byProtocolId(3), -- VLAN by Protocol Id
                         bySrcMac(4),      -- VLAN by Src MAC address
                         spbm-bvlan(11)        -- PLSB bvlan
                      }
        MAX-ACCESS    read-write
        STATUS        current
        DESCRIPTION   "The type of VLAN, distinguished according to the
                      policy used to define its port membership.
                      VSP9000 does not support bySvlan(6) and ByIds(7)."
        ::= { rcVlanEntry 10 }

rcVlanPortMembers OBJECT-TYPE
        SYNTAX        PortSet
        MAX-ACCESS    read-write
        STATUS        current
        DESCRIPTION   "The set of ports that are members (static or 
                      dynamic) of this VLAN."
        ::= { rcVlanEntry 11 }
 
rcVlanActiveMembers OBJECT-TYPE
        SYNTAX        PortSet
        MAX-ACCESS    read-only
        STATUS        current
        DESCRIPTION   "The set of ports that are currently active in 
                      this VLAN. Active ports include all static ports
                      and any dynamic ports where the VLAN policy was
                      met."
        ::= { rcVlanEntry 12 }
 
rcVlanStaticMembers OBJECT-TYPE
        SYNTAX        PortSet
        MAX-ACCESS    read-write
        STATUS        current
        DESCRIPTION   "The set of ports that are static members of this
                      VLAN. A static member of a VLAN is always active 
                      and is never aged out."
        ::= { rcVlanEntry 13 }

rcVlanNotAllowToJoin OBJECT-TYPE
        SYNTAX        PortSet
        MAX-ACCESS    read-write
        STATUS        current
        DESCRIPTION   "The set of ports that are not allowed to become
                      members of this VLAN."
        ::= { rcVlanEntry 14 }

rcVlanProtocolId OBJECT-TYPE
        SYNTAX        INTEGER {
                         none(0),
                         ip(1),
                         ipx802dot3(2),
                         ipx802dot2(3),
                         ipxSnap(4),
                         ipxEthernet2(5),
                         appleTalk(6),
                         decLat(7),
                         decOther(8),
                         sna802dot2(9),
                         snaEthernet2(10),
                         netBios(11),
                         xns(12),
                         vines(13),
                         ipV6(14), 
                         usrDefined(15),
                         rarp(16),
                         pPPoE(17)
                      }
        MAX-ACCESS    read-write
        STATUS        current
        DESCRIPTION   "The protocol identifier of this VLAN. This value 
                      is meaningful only if rcVlanType is equal to 
                      byProtocolId(3). For other VLAN types it should
                      have the value none(0)."
        ::= { rcVlanEntry 15 }

rcVlanSubnetAddr OBJECT-TYPE
        SYNTAX        IpAddress
        MAX-ACCESS    read-write
        STATUS        current
        DESCRIPTION   "The IP subnet address of this VLAN. This value 
                      is meaningful only if rcVlanType is equal to 
                      byIpSubnet(2). For other VLAN types it should
                      have the value 0.0.0.0."
        ::= { rcVlanEntry 16 }

rcVlanSubnetMask OBJECT-TYPE
        SYNTAX        IpAddress
        MAX-ACCESS    read-write
        STATUS        current
        DESCRIPTION   "The IP subnet mask of this VLAN. This value
                      is meaningful only if rcVlanType is equal to 
                      byIpSubnet(2). For other VLAN types it should
                      have the value 0.0.0.0."
        ::= { rcVlanEntry 17 }

rcVlanAgingTime OBJECT-TYPE
        SYNTAX        INTEGER (0 | 10..1000000)
        MAX-ACCESS    read-write
        STATUS        current
        DESCRIPTION   "The timeout period (in seconds) used for aging
                      out dynamic members of this VLAN. This field is
                      only relevant for policy-based VLANs."
        DEFVAL        { 600 }
        ::= { rcVlanEntry 18 }

rcVlanMacAddress OBJECT-TYPE
        SYNTAX        MacAddress
        MAX-ACCESS    read-only
        STATUS        current
        DESCRIPTION   "The MAC address assigned to the virtual router
                      interface of this VLAN. This field is meaningful 
                      only if rcVlanRoutingEnable is equal to true(1)."
        ::= { rcVlanEntry 19 }

rcVlanRowStatus OBJECT-TYPE
        SYNTAX        RowStatus
        MAX-ACCESS    read-write
        STATUS        current
        DESCRIPTION   "Used to create/delete entries in the rcVlanTable."
        ::= { rcVlanEntry 20 }

rcVlanUserDefinedPid OBJECT-TYPE
        SYNTAX        Integer32
        MAX-ACCESS    read-write
        STATUS        current
        DESCRIPTION   "When rcVlanProtocolId is set to usrDefined(15)
                       in a protocol-based VLAN, this field represents
                       the 16-bit user defined protocol identifier."
        ::= { rcVlanEntry 26 }
 
rcVlanProtocolIds OBJECT-TYPE
        SYNTAX        Integer32
        MAX-ACCESS    read-write
        STATUS        current
        DESCRIPTION   "Bitfield of protocol ids."
        ::= { rcVlanEntry 28 }

rcVlanTosValue OBJECT-TYPE
        SYNTAX        	INTEGER (1..64)
        MAX-ACCESS     	read-write 
        STATUS        	current
        DESCRIPTION   	"Tos value."
	DEFVAL		{ 1 }
        ::= { rcVlanEntry 34 } 

rcVlanEncap OBJECT-TYPE
        SYNTAX          INTEGER {
                            ethernet2(1),
                            llc(2),
                            snap(3),
                            all(4),
                            notapplicable(5)
                        }
        MAX-ACCESS      read-write
        STATUS          current
        DESCRIPTION     "This is the encapsulation type for userdefined protocol
                        based vlans. This is not meaningful for other types of 
                        vlan. The default value is null."
        DEFVAL          { notapplicable }
        ::= { rcVlanEntry 35 }

rcVlanFdbAging OBJECT-TYPE
        SYNTAX        INTEGER (0 | 10..1000000)
        MAX-ACCESS    read-write
        STATUS        current
        DESCRIPTION   "The timeout period (in seconds) used for aging
                      out fdb entries of this VLAN."
        DEFVAL        { 600 }
        ::= { rcVlanEntry 37 }

rcVlanOspfPassivePortMember OBJECT-TYPE
        SYNTAX        	PortSet
        MAX-ACCESS     	read-write 
        STATUS        	current
        DESCRIPTION   	"The set of ports in the vlan that are designated as
                         ospf passive"
        ::= { rcVlanEntry 44 } 

rcVlanNlbMode OBJECT-TYPE
        SYNTAX          INTEGER {
                            nlbAdminDisable(0),
                            nlbAdminIgmpMcast(1),
                            nlbAdminMulticast(2),
                            nlbAdminUnicast(4)
                        }
        MAX-ACCESS      read-write
        STATUS          current
        DESCRIPTION     "NLB mode set on a VLAN."
        DEFVAL          { nlbAdminDisable }
        ::= { rcVlanEntry 46 }

rcVlanVrfId   OBJECT-TYPE
     SYNTAX         VrfIdentifier
     MAX-ACCESS     read-write
     STATUS         current
     DESCRIPTION    "Indicates the Virtual Router to which the VLAN belongs"
        ::= { rcVlanEntry 48 }

rcVlanVrfName   OBJECT-TYPE
     SYNTAX         DisplayString (SIZE (0..32))
     MAX-ACCESS     read-only
     STATUS         current
     DESCRIPTION    "The Name of the Virtual Router to which the VLAN belongs"
        ::= { rcVlanEntry 49 }

rcVlanNodalMepList OBJECT-TYPE
        SYNTAX        DisplayString (SIZE (0..408))
        MAX-ACCESS    read-write
        STATUS        current
        DESCRIPTION   "List of nodal Meps assigned to this vlan. A mep
                       consists of Domain Name, Association name and Mep
                       Id separated by '.'. Each meps is separated by ',':
                       <md1>.<ma1>.<mepid1>,<md2>.<ma2>.<mepid2>,...
                       The maximum number of nodal Mep for each vlan is 8."
        ::= { rcVlanEntry 54}

rcVlanNumOfNodalMep OBJECT-TYPE
        SYNTAX        Integer32 (0..8)
        MAX-ACCESS    read-only
        STATUS        current
        DESCRIPTION   "Number of nodal meps assigned to this vlan"
        ::= { rcVlanEntry 55 }

rcVlanNodalMipLevelList OBJECT-TYPE
        SYNTAX       DisplayString (SIZE (0..16))
        MAX-ACCESS    read-write
        STATUS        current
        DESCRIPTION   "List of nodal Mip levels assigned to this vlan that
                       allows Mip functionality to be enabled on a per level
                       per vlan basis. A mip level is represented by an
                       integer ranging from 0 to 7. The mip levels are
                       separated by ',': <0...7>,<0...7>,... The maximum
                       number of nodal Mip levels for each vlan is 8."
        ::= { rcVlanEntry 56 }

rcVlanNumOfNodalMipLevel OBJECT-TYPE
        SYNTAX        Integer32 (0..8)
        MAX-ACCESS    read-only
        STATUS        current
        DESCRIPTION   "Number of nodal mip levels assigned to this vlan that
                       allows MIP functionality to be enabled on a per level
                       per vlan basis."
        ::= { rcVlanEntry 57 }

rcVlanPlsbIsid OBJECT-TYPE
        SYNTAX        Integer32 (0..16777215)
        MAX-ACCESS    read-write
        STATUS        current
        DESCRIPTION   "Plsb i-sid number assigned to a C-vlan. Default 0 value
		       indicates that no i-sid has been assinged."
	DEFVAL { 0 }
        ::= { rcVlanEntry 61 }

-- VLAN Port Table

rcVlanPortTable OBJECT-TYPE
        SYNTAX        SEQUENCE OF RcVlanPortEntry
        MAX-ACCESS    not-accessible
        STATUS        current
        DESCRIPTION   "A table used to maintain VLAN port related 
                      information." 
        ::= { rcVlan 3 }

rcVlanPortEntry OBJECT-TYPE
        SYNTAX        RcVlanPortEntry
        MAX-ACCESS    not-accessible
        STATUS        current
        DESCRIPTION   "Entry containing VLAN information regarding a 
                      particular port."
        INDEX         { rcVlanPortIndex }
        ::= { rcVlanPortTable 1 }

RcVlanPortEntry ::= SEQUENCE {
                rcVlanPortIndex Integer32,
                rcVlanPortNumVlanIds Integer32,
                rcVlanPortType INTEGER,
                rcVlanPortDiscardTaggedFrames TruthValue,
                rcVlanPortDiscardUntaggedFrames TruthValue,
                rcVlanPortDefaultVlanId INTEGER,
                rcVlanPortPerformTagging TruthValue,
		rcVlanPortLoopDetect TruthValue,
		rcVlanPortFirstPortInOpid InterfaceIndex,
		rcVlanPortLastPortInOpid InterfaceIndex,
                rcVlanPortLoopDetectAction INTEGER,
                rcVlanPortArpDetect TruthValue,
                rcVlanPortSpoofDetect TruthValue,
                rcVlanPortUntagDefaultVlan TruthValue,
		rcVlanPortClassificationSubnet TruthValue,
                rcVlanPortClassificationProtocol TruthValue,
		rcVlanPortClassificationPrec INTEGER,
		rcVlanPortVlanIdList OCTET STRING,
	 	rcVlanPortClassificationSourceMac TruthValue
        }

rcVlanPortIndex OBJECT-TYPE
        SYNTAX        Integer32 (0..2147483647)
        MAX-ACCESS    read-only
        STATUS        current
        DESCRIPTION   "An unique index used to identify a particular 
                      port in the system. This index is equal to the
                      ifIndex of the port."
        ::= { rcVlanPortEntry 1 }

rcVlanPortNumVlanIds OBJECT-TYPE
        SYNTAX        Integer32
        MAX-ACCESS    read-only
        STATUS        current
        DESCRIPTION   "Used to indicate the number of VLAN IDs that
                      are stored in the rcVlanPortVlanIds variable."
        ::= { rcVlanPortEntry 2 }

rcVlanPortType OBJECT-TYPE
        SYNTAX        INTEGER {
                         access(1),     -- access port type
                         trunk(2)       -- trunk port type
                      }
        MAX-ACCESS    read-write
        STATUS        current
        DESCRIPTION   "The type of port: access(1) or trunk(2)."
        DEFVAL        { access }
        ::= { rcVlanPortEntry 4 }

rcVlanPortDiscardTaggedFrames OBJECT-TYPE
        SYNTAX        TruthValue
        MAX-ACCESS    read-write
        STATUS        current
        DESCRIPTION   "A flag used to determine how to process tagged
                      frames received on this access port. When the 
                      flag is set, these frames are discarded by the
                      forwarding process. When the flag is reset, these
                      frames are processed normally.

		      This field is meaningless when the port is not
		      an access port and should be set to false(2)."
        DEFVAL        { false }
        ::= { rcVlanPortEntry 5 }

rcVlanPortDiscardUntaggedFrames OBJECT-TYPE
        SYNTAX        TruthValue
        MAX-ACCESS    read-write
        STATUS        current
        DESCRIPTION   "A flag used to determine how to process untagged
                      frames received on this trunk port. When the flag 
                      is set, these frames are discarded by the 
                      forwarding process. When the flag is reset, these
                      frames are assigned to the VLAN specified by 
                      rcVlanPortDefaultVlanId.

		      This field is meaningless when the port is not
		      a trunk port and should be set to false(2)."
        DEFVAL        { false }
        ::= { rcVlanPortEntry 6 }

rcVlanPortDefaultVlanId OBJECT-TYPE
        SYNTAX        INTEGER (0..4084)
        MAX-ACCESS    read-write
        STATUS        current
        DESCRIPTION   "The VLAN ID assigned to untagged frames received
                      on this trunk port.

		      This field is meaningless when the port is not
		      a trunk port."
        DEFVAL        { 1 }
        ::= { rcVlanPortEntry 7 } 

rcVlanPortPerformTagging OBJECT-TYPE
        SYNTAX        TruthValue
        MAX-ACCESS    read-write
        STATUS        current
        DESCRIPTION   "Enable/disable the port on the current vlan to 
                       perform tagging on the incoming and outgoing traffic."
        DEFVAL        { false }
        ::= { rcVlanPortEntry 8 }

rcVlanPortLoopDetect OBJECT-TYPE
        SYNTAX        TruthValue
        MAX-ACCESS    read-write
        STATUS        current
        DESCRIPTION   "Enable/disable loop detection on this port"
        DEFVAL        { false }
        ::= { rcVlanPortEntry 10 }

rcVlanPortFirstPortInOpid OBJECT-TYPE
        SYNTAX        InterfaceIndex
	MAX-ACCESS    read-only
	STATUS        current
	DESCRIPTION   "This value gives the IfIndex of the first port in the
	               octapid. This value is used to generate an error message
		       when changing port type from normal to uni/nni and
		       viceversa"
        ::= { rcVlanPortEntry 11 }

rcVlanPortLastPortInOpid OBJECT-TYPE
        SYNTAX        InterfaceIndex
	MAX-ACCESS    read-only
	STATUS        current
	DESCRIPTION   "This value gives the IfIndex of the first port in the
	               octapid. This value is used to generate an error message
		       when changing port type from normal to uni/nni and
		       viceversa"
        ::= { rcVlanPortEntry 12 }

rcVlanPortUntagDefaultVlan OBJECT-TYPE
        SYNTAX        TruthValue
        MAX-ACCESS    read-write
        STATUS        current
        DESCRIPTION   "enable/disable Egress Tagging on the Default Vlan of the
                       port.  "
        DEFVAL        { false }
        ::= { rcVlanPortEntry 13 }

rcVlanPortLoopDetectAction OBJECT-TYPE
        SYNTAX        INTEGER {
                         portDown(1),
                         vlanBlock(2),  
                         macDiscard(3)
                      }
        MAX-ACCESS    read-write
        STATUS        current
        DESCRIPTION   "This value is used to specify the action which needs
                      to be taken once a loop is detected on a specific port.
                      VlanBlock is not supported in VSP9000."
        DEFVAL        { portDown }
        ::= { rcVlanPortEntry 14 }

rcVlanPortArpDetect OBJECT-TYPE
        SYNTAX        TruthValue
        MAX-ACCESS    read-write
        STATUS        current
        DESCRIPTION   "Enable/disable Arp detection on this port"
        DEFVAL        { false }
        ::= { rcVlanPortEntry 15 }

rcVlanPortSpoofDetect OBJECT-TYPE 
        SYNTAX        TruthValue 
        MAX-ACCESS    read-write 
        STATUS        current 
        DESCRIPTION   "Enable/disable spoof detection on this port" 
        DEFVAL        { false } 
        ::= { rcVlanPortEntry 16 } 

rcVlanPortClassificationSubnet  OBJECT-TYPE
        SYNTAX        TruthValue
        MAX-ACCESS    read-write
        STATUS        current
        DESCRIPTION   "Enable/disable Subnet based Vlan packets on this port."
        DEFVAL        { true }
        ::= { rcVlanPortEntry 18 }

rcVlanPortClassificationProtocol  OBJECT-TYPE
        SYNTAX        TruthValue
        MAX-ACCESS    read-write
        STATUS        current
        DESCRIPTION   "Enable/disable Protocol based Vlan packets on this port."
        DEFVAL        { true }
        ::= { rcVlanPortEntry 19}
                       
rcVlanPortClassificationPrec OBJECT-TYPE
        SYNTAX      INTEGER {
                        sourceMac (1),
                        subnet (2)
                    }
        MAX-ACCESS  read-write
        STATUS      current
        DESCRIPTION  "Sets the precedence for vlan classification.  A value
                      of 1 puts classification of packets to source mac vlans
                      ahead of subnet based vlans.  A value of 2 puts subnet
                      based vlans ahead of source mac vlans.  Classification
                      to other types of vlans is unaffected as it occurs 
		      following source mac and subnet based vlans."
        DEFVAL      { sourceMac }
        ::= { rcVlanPortEntry 20 }

rcVlanPortVlanIdList OBJECT-TYPE
        SYNTAX        	OCTET STRING (SIZE (0..512))
        MAX-ACCESS      read-write
        STATUS        	current
        DESCRIPTION   	"This bitfield is used to identify which VLANs this port
                      	is assigned to. Each VLAN ID is stored as a bit.
		      	The most-significant (left-most) bit represents Vlan Id 1."
        ::= { rcVlanPortEntry 21 }

rcVlanPortClassificationSourceMac OBJECT-TYPE
        SYNTAX        TruthValue
        MAX-ACCESS    read-write
        STATUS        current
        DESCRIPTION   "Enable/disable SourceMac based Vlan packets on this port."
        DEFVAL        { true }
        ::= { rcVlanPortEntry 22 }



-- VLAN MAC Table

rcVlanMacTable OBJECT-TYPE
        SYNTAX        SEQUENCE OF RcVlanMacEntry
        MAX-ACCESS    not-accessible
        STATUS        current
        DESCRIPTION   "A table used to maintain MAC addresses assigned 
                      to a particular VLAN by MAC address."
        ::= { rcVlan 4 }
 
rcVlanMacEntry OBJECT-TYPE
        SYNTAX        RcVlanMacEntry
        MAX-ACCESS    not-accessible
        STATUS        current
        DESCRIPTION   "Entry containing VLAN information regarding a
                      particular port."
        INDEX         { rcVlanMacVlanId, rcVlanMacAddr }
        ::= { rcVlanMacTable 1 }
 
RcVlanMacEntry ::= SEQUENCE {
                rcVlanMacVlanId Integer32,
                rcVlanMacAddr MacAddress,
                rcVlanMacRowStatus RowStatus
        }
 
rcVlanMacVlanId OBJECT-TYPE
        SYNTAX        Integer32 (0..2147483647)
        MAX-ACCESS    read-only
        STATUS        current
        DESCRIPTION   "An unique index used to identify a VLAN (by MAC 
                      address) in the system."
        ::= { rcVlanMacEntry 1 }

rcVlanMacAddr OBJECT-TYPE
        SYNTAX        MacAddress
        MAX-ACCESS    read-only
        STATUS        current
        DESCRIPTION   "An unique index used to identify a MAC address
                      assigned to a particular VLAN."
        ::= { rcVlanMacEntry 2 }

rcVlanMacRowStatus OBJECT-TYPE
        SYNTAX        RowStatus
        MAX-ACCESS    read-write
        STATUS        current
        DESCRIPTION   "Row status for this entry."
        ::= { rcVlanMacEntry 3 }


-- VLAN IGMP Snoop Table

rcVlanIgmpSnoopNumGroups OBJECT-TYPE
        SYNTAX        Integer32
        MAX-ACCESS    read-only
        STATUS        current
        DESCRIPTION   "The number of entries (rows) in the
                      rcVlanIgmpSnoopTable."
        ::= { rcVlan 5 }

-- Vlan Loop Detected Table     

rcVlanLoopDetectedTable OBJECT-TYPE
        SYNTAX        SEQUENCE OF RcVlanLoopDetectedEntry
        MAX-ACCESS    not-accessible
        STATUS        current
        DESCRIPTION   "A list of Vlans the port belongs to
and the 
                      corresponding loop detected status."
        ::= { rcVlan 10 }

rcVlanLoopDetectedEntry OBJECT-TYPE
        SYNTAX        RcVlanLoopDetectedEntry
        MAX-ACCESS    not-accessible
        STATUS        current
        DESCRIPTION   "Loop-Detected Entry."
        INDEX         { rcVlanLoopDetectedPortIndex, rcVlanLoopDetectedVlanId }
        ::= { rcVlanLoopDetectedTable 1 }

RcVlanLoopDetectedEntry ::= SEQUENCE {
                    rcVlanLoopDetectedPortIndex Integer32,
                    rcVlanLoopDetectedVlanId Integer32,
                    rcVlanLoopDetectedValue INTEGER
                    }

rcVlanLoopDetectedPortIndex OBJECT-TYPE
        SYNTAX        Integer32 (0..2147483647)
        MAX-ACCESS    read-only
        STATUS        current
        DESCRIPTION   "Port Number."
        ::= { rcVlanLoopDetectedEntry 1 }

rcVlanLoopDetectedVlanId OBJECT-TYPE
        SYNTAX        Integer32 (0..4084)
        MAX-ACCESS    read-only
        STATUS        current
        DESCRIPTION   "Gives the VlanId to which the port belongs."
        ::= { rcVlanLoopDetectedEntry 2 }

rcVlanLoopDetectedValue OBJECT-TYPE
        SYNTAX        INTEGER {
                         no(0),      -- loop not detected
                         yes(1)     -- loop detected
                      }
        MAX-ACCESS      read-only
        STATUS          current
        DESCRIPTION    "Gives the Loop Detected status of the port
                       in a vlan."
        DEFVAL        { no }
        ::= { rcVlanLoopDetectedEntry 3 }


-- Vlan Dsap Ssap Table     

rcVlanDsapSsapTable OBJECT-TYPE
        SYNTAX        SEQUENCE OF RcVlanDsapSsapEntry
        MAX-ACCESS    not-accessible
        STATUS        current
        DESCRIPTION   "A table used to maintain DSAP/SSAP values 
                       assigned to a sna802dot2 or userdefined vlan."
        ::= { rcVlan 11 }

rcVlanDsapSsapEntry OBJECT-TYPE
        SYNTAX        RcVlanDsapSsapEntry
        MAX-ACCESS    not-accessible
        STATUS        current
        DESCRIPTION   "An entry in the rcVlanDsapSsap table."
        INDEX         { rcVlanDsapSsapVlanId, rcVlanDsapSsapPid }
        ::= { rcVlanDsapSsapTable 1 }

RcVlanDsapSsapEntry ::= SEQUENCE {
        rcVlanDsapSsapVlanId    Integer32,
        rcVlanDsapSsapPid       INTEGER,
        rcVlanDsapSsapRowStatus RowStatus
        }

rcVlanDsapSsapVlanId OBJECT-TYPE
        SYNTAX        Integer32 (0..4084)
        MAX-ACCESS    not-accessible
        STATUS        current
        DESCRIPTION   "A unique index to identify a vlan."
        ::= { rcVlanDsapSsapEntry 1 }

rcVlanDsapSsapPid OBJECT-TYPE
        SYNTAX        INTEGER (0..'ffff'h)
        MAX-ACCESS    not-accessible
        STATUS        current
        DESCRIPTION   "Values of DSAP/SSAP assigned to a particular 
                       vlan."
        ::= { rcVlanDsapSsapEntry 2 }

rcVlanDsapSsapRowStatus OBJECT-TYPE
        SYNTAX        RowStatus
        MAX-ACCESS    read-write
        STATUS        current
        DESCRIPTION   "Row Status."
        ::= { rcVlanDsapSsapEntry 3 }

rcVlanNewLoopDetectedTable OBJECT-TYPE
        SYNTAX        SEQUENCE OF RcVlanNewLoopDetectedEntry
        MAX-ACCESS    not-accessible
        STATUS        current
        DESCRIPTION   "A list of Vlans the port belongs to and the 
                       corresponding loop detected status."
        ::= { rcVlan 12 }

rcVlanNewLoopDetectedEntry OBJECT-TYPE
        SYNTAX        RcVlanNewLoopDetectedEntry
        MAX-ACCESS    not-accessible
        STATUS        current
        DESCRIPTION   "Loop-Detected Entry."
        INDEX         { rcVlanNewLoopDetectedPortIndex,
                        rcVlanNewLoopDetectedVlanId,
                        rcVlanNewLoopDetectedMac }
        ::= { rcVlanNewLoopDetectedTable 1 }

RcVlanNewLoopDetectedEntry ::= SEQUENCE {
                    rcVlanNewLoopDetectedPortIndex InterfaceIndex,
                    rcVlanNewLoopDetectedVlanId Integer32,
                    rcVlanNewLoopDetectedMac     MacAddress,
                    rcVlanNewLoopDetectedAction  INTEGER,
                    rcVlanNewLoopDetectedSmltRemote TruthValue
                   }

rcVlanNewLoopDetectedPortIndex OBJECT-TYPE
        SYNTAX        InterfaceIndex
        MAX-ACCESS    not-accessible
        STATUS        current
        DESCRIPTION   "Port Number."
        ::= { rcVlanNewLoopDetectedEntry 1 }

rcVlanNewLoopDetectedVlanId OBJECT-TYPE
        SYNTAX        Integer32 (0..2147483647)
        MAX-ACCESS    not-accessible
        STATUS        current
        DESCRIPTION   "Gives the VlanId to which the port belongs."
        ::= { rcVlanNewLoopDetectedEntry 2 }

rcVlanNewLoopDetectedMac     OBJECT-TYPE
        SYNTAX        MacAddress
        MAX-ACCESS    not-accessible
        STATUS        current
        DESCRIPTION   "Mac address"
        ::= {rcVlanNewLoopDetectedEntry 3}

rcVlanNewLoopDetectedAction OBJECT-TYPE
        SYNTAX        INTEGER {
                               portDown(1),
                               vlanBlock(2),
                               macDiscard(3)
                              }
        MAX-ACCESS    read-only
        STATUS        current
        DESCRIPTION   "This value is used to specify the action which
                       needs to be taken once a loop is detected on a 
                       specific port."
        DEFVAL        { portDown }
        ::= { rcVlanNewLoopDetectedEntry 4 }

rcVlanNewLoopDetectedSmltRemote OBJECT-TYPE
        SYNTAX      TruthValue 
        MAX-ACCESS  read-only
        STATUS      current
        DESCRIPTION  "A MAC address indicate for remote learnt,
                      either local or remote."
        ::= { rcVlanNewLoopDetectedEntry 5 }


-- PHYSICAL Elements

rcChasType OBJECT-TYPE
	SYNTAX	      INTEGER {
		         unknown(1),   -- unknown chassis
-- Passport 1000 Types
 		         a1100(2),     -- 3  slot chassis (1/2, 1/2, full)
 		         a1250(6),     -- 4  slot chassis (full, ... , full)
 		         a1150(7),     -- 3  slot chassis (1/2, 1/2, full)
 		         a1200(8),     -- 8  slot chassis (full, ... , full)
			 a1050(9),     -- 2  slot chassis (seahawk)
-- Passport 8000 Types
			 a8006(280887558),    -- 6  slot chassis (raptillion)
			 a8010(280887562),    -- 10 slot chassis (raptillion)
			 a8010co(1623064842), -- 10 slot Central Office Chassis
			 a8003(280887555),    -- 3  slot chassis (raptillion)
-- Cobalt Blue
			 -- Nortel Order#:	NTC201CA
			 -- Customer Order#:	EC1402001
			 a9012(1090388736) -- 0100 0000 1111 1110 0000 0011 0000 0000 0x40FE0300
	              }
	MAX-ACCESS 	  read-only
	STATUS 	      current
	DESCRIPTION   "Chassis Type"
        ::= { rcChassis 1 }

rcChasSerialNumber OBJECT-TYPE
        SYNTAX        DisplayString (SIZE (0..16))
        MAX-ACCESS    read-only
        STATUS        current
        DESCRIPTION   "Unique serial number for this chassis."
        ::= { rcChassis 2 }

rcChasHardwareRevision OBJECT-TYPE
	SYNTAX 	      DisplayString (SIZE (0..20))
	MAX-ACCESS 	  read-only
	STATUS 	      current
	DESCRIPTION   "Device hardware revision level"
	::= { rcChassis 3 }
	
rcChasNumSlots OBJECT-TYPE
        SYNTAX        INTEGER (1..12)
        MAX-ACCESS    read-only
        STATUS        current
        DESCRIPTION   "The number of slots in the chassis available for
                      plug-in cards."
        ::= { rcChassis 4 }

rcChasNumPorts OBJECT-TYPE
        SYNTAX        INTEGER (0..255) 
        MAX-ACCESS    read-only
        STATUS        current
        DESCRIPTION   "The total number of ports currently installed in
		      the chassis."
        ::= { rcChassis 5 }

rcChasFan OBJECT IDENTIFIER ::= { rcChassis 7 }

rcChasFanZoneTable OBJECT-TYPE
     SYNTAX SEQUENCE OF RcChasFanZoneEntry
     MAX-ACCESS   not-accessible
     STATUS       current
     DESCRIPTION  "Table for the zones available on the chassis"
     ::= { rcChasFan 2 }

rcChasFanZoneEntry OBJECT-TYPE
     SYNTAX        RcChasFanZoneEntry
     MAX-ACCESS    not-accessible
     STATUS        current
     DESCRIPTION   "Contains information regarding a zone unit"
     INDEX        { rcChasFanZoneType }
     ::= { rcChasFanZoneTable 1 }

RcChasFanZoneEntry ::=
     SEQUENCE {
           rcChasFanZoneType INTEGER,
           rcChasFanZoneMode INTEGER,
           rcChasFanZoneModeStatus BITS,
           rcChasFanZoneAlarmTimer  Integer32,
           rcChasFanZoneTemperature Gauge32,
           rcChasFanZoneTray1LedColor INTEGER,
           rcChasFanZoneTray2LedColor INTEGER
     }

rcChasFanZoneType OBJECT-TYPE
     SYNTAX INTEGER {
                 front(1),
                 rear(2)
            }
     MAX-ACCESS   not-accessible
     STATUS       current
     DESCRIPTION  "Type of the fan zone."
     ::= { rcChasFanZoneEntry 1 }

rcChasFanZoneMode OBJECT-TYPE
     SYNTAX INTEGER {
                 normal(1),
                 alarm(2)
            }
     MAX-ACCESS   read-only
     STATUS       current
     DESCRIPTION  "Functional mode of the fan zone."
     ::= { rcChasFanZoneEntry 2 }

rcChasFanZoneModeStatus OBJECT-TYPE
     SYNTAX  BITS {
                 normal(0),
                 fanFault(1),
                 alarmThresholdExceeded(2)
            }
     MAX-ACCESS   read-only
     STATUS       current
     DESCRIPTION  "Bit set indicates the alarm type(s)"
     ::= { rcChasFanZoneEntry 3 }

rcChasFanZoneAlarmTimer OBJECT-TYPE
     SYNTAX       Integer32
     UNITS        "seconds"
     MAX-ACCESS   read-only
     STATUS       current
     
     DESCRIPTION  "Alarm timer indicates the remaining time before 
                   system checks and shutdown module when fan is in
		   the alarm state. Zero means the fan i snot in an
                   alarm state"
     ::= { rcChasFanZoneEntry 4 }

rcChasFanZoneTemperature OBJECT-TYPE
     SYNTAX       Gauge32
     MAX-ACCESS   read-only
     STATUS       current
     DESCRIPTION  "Highest temperature measured in celsius degree
		   from all the sensors (inlet and outlet) in the zone"
     ::= { rcChasFanZoneEntry 5 }

rcChasFanZoneTray1LedColor OBJECT-TYPE
     SYNTAX       INTEGER {
                     off(1),
                     green(2),
                     red(3),
                     amber(4)
		  }
     MAX-ACCESS   read-only
     STATUS       current
     DESCRIPTION  "Led color indicate fans operation status on tray
                   off:   Indicates no tray or power off.
                   green: Indicates all fans are operational in a tray.
		   red:   Front Zone Tray: more than one fans in a tray are not opertional.
                          Rear Zone Tray: one of two or both fans fans in a tray are not operational.
                   amber: Front Zone Tray: one of eight fans is not operational.
                           Rear Zone Tray: It is not applicable for Rear Zone tray"
			
     ::= { rcChasFanZoneEntry 6 }

 rcChasFanZoneTray2LedColor OBJECT-TYPE
     SYNTAX       INTEGER {
                     off(1),
		     green(2),
                     red(3),
                     amber(4)
		  }
     MAX-ACCESS   read-only
     STATUS       current
     DESCRIPTION  "Led color indicate fans operation status on tray
		   off:   Indicates no tray or power off.
                   green: Indicates all fans are operational in a tray.
		   red:   Front Zone Tray: more than one fans in a tray are not opertional.
                          Rear Zone Tray: one of two fans or both fans in a tray are not operational.
                   amber: Front Zone Tray: one of eight fans is not operational.
                           Rear Zone Tray: It is not applicable for Rear Zone tray"
     ::= { rcChasFanZoneEntry 7 }

rcChasFanInfoTable OBJECT-TYPE
     SYNTAX        SEQUENCE OF RcChasFanInfoEntry
     MAX-ACCESS    not-accessible
     STATUS        current
     DESCRIPTION   "This table contains information for 
                    all the fans on the chassis"
     ::= { rcChasFan 3 }

rcChasFanInfoEntry OBJECT-TYPE
     SYNTAX        RcChasFanInfoEntry
     MAX-ACCESS    not-accessible
     STATUS        current
     DESCRIPTION   "Contains information regarding a fan unit"
     INDEX        { rcChasFanZoneType, rcChasFanInfoTray, rcChasFanInfoFan }
     ::= { rcChasFanInfoTable 1 }

RcChasFanInfoEntry ::=
     SEQUENCE {
           rcChasFanInfoTray INTEGER,
           rcChasFanInfoFan INTEGER,
           rcChasFanInfoExpectedSpeed INTEGER,
           rcChasFanInfoOperSpeed INTEGER,
           rcChasFanInfoStatus INTEGER
     }

rcChasFanInfoTray OBJECT-TYPE
     SYNTAX INTEGER (1..2)
     MAX-ACCESS   not-accessible 
     STATUS       current
     DESCRIPTION  "Number of trays per zone in chassis"
     ::= { rcChasFanInfoEntry 1 }

rcChasFanInfoFan OBJECT-TYPE
     SYNTAX INTEGER (1..8)
     MAX-ACCESS   not-accessible
     STATUS       current
     DESCRIPTION  "Number of fans per tray"
     ::= { rcChasFanInfoEntry 2 }

rcChasFanInfoExpectedSpeed OBJECT-TYPE
     SYNTAX INTEGER {
                 low(1),
                 medium(2),
                 high(3),
                 hardware(4)
            }
     MAX-ACCESS   read-only
     STATUS       current
     DESCRIPTION  "The administrative setting for the fan speed
                   low:       Low speed set by software
                   medium:    Medium speed set by software
                   high:      High speed set by software
                   hardware:  Speed controlled by hardware"
     ::= { rcChasFanInfoEntry 3 }

rcChasFanInfoOperSpeed OBJECT-TYPE
     SYNTAX INTEGER {
                 low(1),
                 medium(2),
                 high(3),
                 hardware(4)
            }
     MAX-ACCESS   read-only
     STATUS       current
     DESCRIPTION  "Actual speed of the fan"
     ::= { rcChasFanInfoEntry 4 }

rcChasFanInfoStatus OBJECT-TYPE
     SYNTAX INTEGER {
                 ok(1),
                 faulty(2)
            }
     MAX-ACCESS   read-only
     STATUS       current
     DESCRIPTION  "The operational status of the fan. Details below:
                   ok(1):       Fan operating under normal condition(s)
                   faulty(2):   Fan not operating as expected"
     ::= { rcChasFanInfoEntry 5 }

rcChasPowerSupply OBJECT IDENTIFIER ::= { rcChassis 8 }

rcChasPowerSupplyTable OBJECT-TYPE
	SYNTAX        	SEQUENCE OF RcChasPowerSupplyEntry
	MAX-ACCESS        	not-accessible
	STATUS        	current
	DESCRIPTION   	"This table contains information about power 
		      	supplies."
	::= { rcChasPowerSupply 1 }

rcChasPowerSupplyEntry OBJECT-TYPE
	SYNTAX        	RcChasPowerSupplyEntry
	MAX-ACCESS        	not-accessible
	STATUS        	current
	DESCRIPTION   	"Contains information regarding a power supply
		      	unit."
	INDEX  { rcChasPowerSupplyId }
	::= { rcChasPowerSupplyTable 1 }

RcChasPowerSupplyEntry ::=
	SEQUENCE {
		rcChasPowerSupplyId INTEGER,
		rcChasPowerSupplyOperStatus INTEGER
	}

rcChasPowerSupplyId OBJECT-TYPE
	SYNTAX        	INTEGER(1..6)
	MAX-ACCESS        	read-only
	STATUS        	current
	DESCRIPTION    "The power supply Id."
	::= { rcChasPowerSupplyEntry 1 }


rcChasPowerSupplyOperStatus OBJECT-TYPE
	SYNTAX         INTEGER {
		          unknown(1),
		          empty(2),
		          up(3),
	     	          down(4)
	               }
	MAX-ACCESS     read-only
	STATUS         current
	DESCRIPTION   "Actual status of the power supply:
	              - unknown(1) - status can not be determined.
	              - empty(2) - power supply not installed.
	              - up(3) - present and supplying power.
	              - down(4) - present, but failure indicated."
	::= { rcChasPowerSupplyEntry 2 }


rcChasPowerSupplyDetailTable OBJECT-TYPE
	SYNTAX        	SEQUENCE OF RcChasPowerSupplyDetailEntry
	MAX-ACCESS        	not-accessible
	STATUS        	current
	DESCRIPTION   	"This table contains detailed information about
    	                 power supplies."
	::= { rcChasPowerSupply 2 }

rcChasPowerSupplyDetailEntry OBJECT-TYPE
	SYNTAX        	RcChasPowerSupplyDetailEntry
	MAX-ACCESS        	not-accessible
	STATUS        	current
	DESCRIPTION   	"Contains detailed info regarding a power supply
		      	unit."
	INDEX  { rcChasPowerSupplyDetailId }
	::= { rcChasPowerSupplyDetailTable 1 }

RcChasPowerSupplyDetailEntry ::=
	SEQUENCE {
		rcChasPowerSupplyDetailId INTEGER,
		rcChasPowerSupplyDetailType INTEGER,
		rcChasPowerSupplyDetailSerialNumber DisplayString,
		rcChasPowerSupplyDetailHardwareRevision DisplayString,
		rcChasPowerSupplyDetailPartNumber DisplayString,
		rcChasPowerSupplyDetailDescription DisplayString,
                rcChasPowerSupplyDetailInputLineVoltage INTEGER,
		rcChasPowerSupplyDetailOutputWatts   Integer32  	
	}

rcChasPowerSupplyDetailId OBJECT-TYPE
      SYNTAX   	  INTEGER(1..6)
      MAX-ACCESS   	  read-only
      STATUS   	  current
      DESCRIPTION "The power supply Id."
      ::= { rcChasPowerSupplyDetailEntry 1 }

rcChasPowerSupplyDetailType OBJECT-TYPE
      SYNTAX   	   INTEGER {
                       unknown(0),
                       ac(1),
                       dc(2)
                   }
      MAX-ACCESS   	   read-only
      STATUS   	   current
      DESCRIPTION  "The power supply type."
      ::= { rcChasPowerSupplyDetailEntry 2 }

rcChasPowerSupplyDetailSerialNumber OBJECT-TYPE
      SYNTAX      DisplayString (SIZE (0..16))
      MAX-ACCESS  read-only
      STATUS      current
      DESCRIPTION "The power supply serial number."
      ::= { rcChasPowerSupplyDetailEntry 3 }

rcChasPowerSupplyDetailHardwareRevision OBJECT-TYPE
      SYNTAX      DisplayString (SIZE (0..16))
      MAX-ACCESS  read-only
      STATUS      current
      DESCRIPTION "The hardware revision of the power supply."
      ::= { rcChasPowerSupplyDetailEntry 4 }

rcChasPowerSupplyDetailPartNumber OBJECT-TYPE
      SYNTAX      DisplayString (SIZE (0..16))
      MAX-ACCESS  read-only
      STATUS      current
      DESCRIPTION "The power supply part number."
      ::= { rcChasPowerSupplyDetailEntry 5 }

rcChasPowerSupplyDetailDescription OBJECT-TYPE
      SYNTAX      DisplayString (SIZE (0..64))
      MAX-ACCESS  read-only
      STATUS      current
      DESCRIPTION "The detail description of power supply."
      ::= { rcChasPowerSupplyDetailEntry 6 }

rcChasPowerSupplyDetailInputLineVoltage OBJECT-TYPE
      SYNTAX      INTEGER {
                       unknown(0),
                       low110v(1),
                       high220v(2),
                       minus48v(3)
                   }
      MAX-ACCESS   read-only
      STATUS       current
      DESCRIPTION  "The power supply Input Line voltage."
      ::= { rcChasPowerSupplyDetailEntry 8 }

rcChasPowerSupplyDetailOutputWatts OBJECT-TYPE
      SYNTAX      Integer32
      MAX-ACCESS   read-only
      STATUS       current
      DESCRIPTION  "The output power of this power supply"
      ::= { rcChasPowerSupplyDetailEntry 10 }

rcCard OBJECT IDENTIFIER ::= { rcChassis 9 }

rcCardTable OBJECT-TYPE
	SYNTAX        SEQUENCE OF RcCardEntry
	MAX-ACCESS    not-accessible
	STATUS        current
	DESCRIPTION   "A table that contains information about the 
                      cards in this chassis.  For those slots that 
                      do not contain a physical card, the table may 
		      be implemented to contain a conceptual row 
                      with the type of physical module set to 
 		      'chasCardEmpty', or it may be implemented to 
		      have no conceptual row instance."
	::= { rcCard 1 }

rcCardEntry OBJECT-TYPE
	SYNTAX        RcCardEntry
	MAX-ACCESS    not-accessible
	STATUS        current
	DESCRIPTION   "Card attributes"
	INDEX         { rcCardIndex }
	::= { rcCardTable 1 }

RcCardEntry ::=
	SEQUENCE {
		rcCardIndex INTEGER,
		rcCardType INTEGER,
		rcCardOxateCpld DisplayString,
		rcCardOxideFpga DisplayString,
		rcCardCatskillFpga DisplayString,
		rcCardQE DisplayString,
		rcCardK2Fpga DisplayString,
		rcCardIoDateDC DisplayString,
		rcCardIoDateBB DisplayString,
		rcCardIoPimCpld DisplayString,
		rcCardLed0Cpld DisplayString,
		rcCardLed1Cpld DisplayString,
		rcCardZagrosFpga DisplayString,
		rcCardRsp DisplayString,
		rcCardBcmMac DisplayString,
		rcCardPhosphideFpga DisplayString,
		rcCardSulfideFpga DisplayString,
		rcCardFluorateCpld DisplayString,
 		rcCardBme DisplayString
}

rcCardIndex OBJECT-TYPE
        SYNTAX        	INTEGER (1..26)
        MAX-ACCESS     	read-only
        STATUS        	current
        DESCRIPTION   	"A unique value for each module within the chassis.
                      	This value is determined by the chassis slot number
                      	where the module is inserted.  Valid entries are 1
                      	to the value of rcChasNumSlots"
        ::= { rcCardEntry 1 }

rcCardType OBJECT-TYPE
        SYNTAX          INTEGER
        {
            other(1),                       -- no card installed
-- Cobalt Blue: if you change here, you MUST update rc2kCardFrontType in rc2kCardTable
            cbMidplane-28(1090388736),      -- 0100 0000 1111 1110 0000 0011 0000 0000 0x40FE0300
            cbACPowerSupply(1084097280),    -- 0100 0000 1001 1110 0000 0011 0000 0000 0x409E0300
            cbCPFanTray(1085145856),        -- 0100 0000 1010 1110 0000 0011 0000 0000 0x40AE0300
            cbIOFanTray(1085149952),        -- 0100 0000 1001 1110 0000 0011 0000 0000 0x40AE1300
            cbAUX(1091437312),              -- 0100 0001 0000 1110 0000 0011 0000 0000 0x410E0300
            cbSF3200(1075708672),           -- 0100 0000 0001 1110 0000 0011 0000 0000 0x401E0300
            cbSF9600(1075712768),           -- 0100 0000 0001 1110 0001 0011 0000 0000 0x401E1300
            cbCP-CSC(1073873665),           -- 0100 0000 0000 0010 0000 0011 0000 0001 0x40020301
            cb48x1000BaseTX(1075970864),    -- 0100 0000 0010 0010 0000 0011 0011 0000 0x40220330
            cb48x1000BaseTXPOE(1075974960), -- 0100 0000 0010 0010 0001 0011 0011 0000 0x40221330
            cb48x1000SFP(1077044016),       -- 0100 0000 0011 0010 0110 0011 0011 0000 0x40326330
            cb24x10GBaseSFP(1077109528),    -- 0100 0000 0011 0011 0110 0011 0001 1000 0x40336318
            cb48x10GBaseSFP(1077109552)     -- 0100 0000 0011 0011 0110 0011 0011 0000 0x40336330
-- Future CB Cards
        --  cbOPM(1087243008)           0x40CE0300
        --  cbSAS(1087247104)           0x40CE1300  
        --  cbIPFIX(1087251200)         0x40CE2300 
        }
        MAX-ACCESS 	    read-only
        STATUS 	      	current
        DESCRIPTION   	"Used to indicate the card type.  The value returned
                         is defined by the description in rc2kCardTable."
        ::= { rcCardEntry 2 }

rcCardOxateCpld OBJECT-TYPE
        SYNTAX        DisplayString (SIZE (0..8))
        MAX-ACCESS    read-only
        STATUS        current 
        DESCRIPTION   "Oxate CPLD version for CP card"
        ::= { rcCardEntry 9 }

rcCardOxideFpga OBJECT-TYPE
        SYNTAX        DisplayString (SIZE (0..8)) 
        MAX-ACCESS    read-only
        STATUS        current
        DESCRIPTION   "Oxide FGPA version for CP card"
        ::= { rcCardEntry 10 }

rcCardCatskillFpga OBJECT-TYPE
        SYNTAX        DisplayString (SIZE (0..8))
        MAX-ACCESS    read-only
        STATUS        current
        DESCRIPTION   "Catskill FPGA version for CP card"
        ::= { rcCardEntry 11 }

rcCardQE OBJECT-TYPE
        SYNTAX        DisplayString (SIZE (0..8))
        MAX-ACCESS    read-only
        STATUS        current
        DESCRIPTION   "QE version for CP card"
        ::= { rcCardEntry 12 }

rcCardK2Fpga OBJECT-TYPE
        SYNTAX        DisplayString (SIZE (0..8))
        MAX-ACCESS    read-only
        STATUS        current
        DESCRIPTION   "K2 FPGA version for IO card"
        ::= { rcCardEntry 13 }

rcCardIoDateDC OBJECT-TYPE
        SYNTAX        DisplayString (SIZE (0..8))
        MAX-ACCESS    read-only
        STATUS        current
        DESCRIPTION   "IO Date DC CPLD for IO card"
        ::= { rcCardEntry 14 }

rcCardIoDateBB OBJECT-TYPE
        SYNTAX        DisplayString (SIZE (0..8))
        MAX-ACCESS    read-only
        STATUS        current
        DESCRIPTION   "IO Date BaseBoard CPLD for IO card"
        ::= { rcCardEntry 15 } 

rcCardIoPimCpld OBJECT-TYPE
        SYNTAX        DisplayString (SIZE (0..8))
        MAX-ACCESS    read-only
        STATUS        current
        DESCRIPTION   "IO PIM CPLD for IO card"
        ::= { rcCardEntry 16 }

rcCardLed0Cpld OBJECT-TYPE
        SYNTAX        DisplayString (SIZE (0..8))
        MAX-ACCESS    read-only
        STATUS        current
        DESCRIPTION   "LED0 CPLD for IO card"
        ::= { rcCardEntry 17 }

rcCardLed1Cpld OBJECT-TYPE
        SYNTAX        DisplayString (SIZE (0..8))
        MAX-ACCESS    read-only
        STATUS        current
        DESCRIPTION   "LED1 CPLD for IO card"
        ::= { rcCardEntry 18 }

rcCardZagrosFpga OBJECT-TYPE
        SYNTAX        DisplayString (SIZE (0..8))
        MAX-ACCESS    read-only
        STATUS        current
        DESCRIPTION   "Zagros FPGA for IO card"
        ::= { rcCardEntry 19 }

rcCardRsp OBJECT-TYPE
        SYNTAX        DisplayString (SIZE (0..8))
        MAX-ACCESS    read-only
        STATUS        current
        DESCRIPTION   "RSP for IO card" 
        ::= { rcCardEntry 20 }

rcCardBcmMac OBJECT-TYPE
        SYNTAX        DisplayString (SIZE (0..8))
        MAX-ACCESS    read-only
        STATUS        current
        DESCRIPTION   "BCM Mac for IO card"
        ::= { rcCardEntry 21 }

rcCardPhosphideFpga OBJECT-TYPE
        SYNTAX        DisplayString (SIZE (0..8))
        MAX-ACCESS    read-only
        STATUS        current
        DESCRIPTION   "Phosphide FPGA for IO card"
        ::= { rcCardEntry 22 }

rcCardSulfideFpga OBJECT-TYPE
        SYNTAX        DisplayString (SIZE (0..8))
        MAX-ACCESS    read-only
        STATUS        current
        DESCRIPTION   "Sulfide FPGA for IO card"
        ::= { rcCardEntry 23 }

rcCardFluorateCpld OBJECT-TYPE
        SYNTAX        DisplayString (SIZE (0..8))
        MAX-ACCESS    read-only
        STATUS        current
        DESCRIPTION   "Fluorate Cpld for SF card"
        ::= { rcCardEntry 24 }

rcCardBme OBJECT-TYPE
        SYNTAX        DisplayString (SIZE (0..8))
        MAX-ACCESS    read-only
        STATUS        current
        DESCRIPTION   "BME for SF card"
        ::= { rcCardEntry 25 }  


-- Port Table

rcPort OBJECT IDENTIFIER ::= { rcChassis 10 }

rcPortTable OBJECT-TYPE
        SYNTAX	      SEQUENCE OF RcPortEntry
        MAX-ACCESS    not-accessible
        STATUS        current
        DESCRIPTION   "Port table"
        ::= { rcPort 1 }

rcPortEntry OBJECT-TYPE
        SYNTAX        RcPortEntry
        MAX-ACCESS    not-accessible
        STATUS        current
        DESCRIPTION   "Entry containing info. for a particular port"
        INDEX         { rcPortIndex }
        ::= { rcPortTable 1 }

RcPortEntry ::= SEQUENCE {
    rcPortIndex                           InterfaceIndex,
    rcPortType                            INTEGER,
    rcPortAction                          INTEGER,
    rcPortResult                          INTEGER,
    rcPortAutoNegotiate                   TruthValue,
    rcPortAdminDuplex                     INTEGER,
    rcPortOperDuplex                      INTEGER,
    rcPortAdminSpeed                      INTEGER,
    rcPortOperSpeed                       Integer32,
    rcPortMltId                           Integer32,
    rcPortLocked                          TruthValue,
    rcPortAutoNegotiationSupported        TruthValue,
    rcPortSingleRoutablePort              TruthValue,
    rcPortUnknownMacDiscard               TruthValue,
    rcPortNumStateTransition              Counter32,
    rcPortQosLevel                        INTEGER,
    rcPortDiffServEnable                  TruthValue,
    rcPortDiffServType                    INTEGER,
    rcPortVendorDescr                     DisplayString,
    rcPortName                            DisplayString (SIZE (0..42)),
-- OM2.0 place holder added following 
--              rcPortServiceType		      INTEGER,   oid = 41
--              rcPortMode			      INTEGER    oid = 42
    rcPortAdminRouting                    EnableValue,
    rcPortOperRouting                     EnableValue,
--  OID 46 to 49 are being used in 8300 but OID 46 is also used in PR v4.0
    rcPortIeee8021POverrideEnable	  TruthValue,
    rcPortHighSecureEnable                TruthValue,
    rcPortMrouteStrLimit                  INTEGER,
    rcPortMrouteStrTimerCheck             INTEGER,
    rcPortMrouteStrLimitEnable            TruthValue,
    rcPortAutoNegAd                       BITS,
    rcPortAutoRecoverPort                 TruthValue,
    rcPortEgressRateLimit	          INTEGER,
    rcPortEgressRateLimitState            EnableValue,
    rcPortIngressRateLimit                INTEGER,
    rcPortVrfIdList                       IdList,
    rcPortVrfNameList                     OCTET STRING,
    rcPortBrouterVrfId                    VrfIdentifier,
    rcPortBrouterVrfName                  DisplayString,
    rcPortVrfCount                        Counter32,
    rcPortIngressRatePeak		  INTEGER,
    rcPortIngressRateSvc		  INTEGER,
    rcPortCpLimitPktRate                  INTEGER,
    rcPortCpLimitShutDownEnable           TruthValue
}

rcPortIndex OBJECT-TYPE
        SYNTAX        InterfaceIndex
        MAX-ACCESS    read-only
        STATUS        current
        DESCRIPTION   "An index value that uniquely identifies a port.
                      This value is similar to ifIndex in MIB2."
        ::= { rcPortEntry 1 }

rcPortType OBJECT-TYPE
	SYNTAX        INTEGER {
                         other(0),           -- no port installed
                         rc100BaseTX(1),     -- (cat 5)
                         rc100BaseT2(2),     -- (cat 3)
                         rc100BaseF(3),      -- (100 mbps fiber)
                         rc1000BaseF(4),     -- (1000 mbps fiber)
                         rc1000BaseDualF(5), -- (fiber - dual connector)
                         rc10BaseF(6),       -- (10 mbps fiber)
                         rcPosMMF(7),        -- (multi mode fiber)
                         rcPosSMF(8),        -- (single mode fiber)
                         rcAtm(9),           -- (oc3, oc12, ds3, e3)
                         rcGbicLx(10),       -- (gigabit long haul)
                         rcGbicSx(11),       -- (gigabit short haul)
                         rcGbicXd(12),       -- (gigabit extended distance)
                         rcGbicCu(13),       -- (gigabit copper)
                         rcGbicOther(14),    -- (gigabit other)
                         rcOc3cSM(15),       -- (OC-3c SM)
                         rcOc3cMM(16),       -- (OC-3c MM)
                         rcOc3cCOPPER(17),   -- (OC-3c COPPER)
                         rcOc12cSM(18),      -- (OC-12c SM)
                         rcOc12cMM(19),      -- (OC-12c MM)
                         rcDs3(20),          -- (Ds3)
                         rcE3(21),           -- (E3)
                         rcGbicNone(22),     -- (Gbic card feature)
                         rc1000BaseT(23),    -- (1000 base copper)
                         rcGbicZx(24),       -- (gigabit very extended distance)
                         rcOc3cAtmSM(25),    -- (Atm OC-3c SM)
                         rcOc3cAtmMM(26),    -- (Atm OC-3c MM)
                         rcOc12cAtmSM(27),   -- (Atm OC-12c SM)
                         rcOc12cAtmMM(28),   -- (Atm OC-12c MM)
                         rcOc3cPosSM(29),    -- (Pos OC-3c SM)
                         rcOc3cPosMM(30),    -- (Pos OC-3c MM)
                         rcOc12cPosSM(31),   -- (Pos OC-12c SM)
                         rcOc12cPosMM(32),   -- (Pos OC-12c MM)
                         rcGbic1470(33),     -- (gigabit wavelength 1470)
                         rcGbic1490(34),     -- (gigabit wavelength 1490)
                         rcGbic1510(35),     -- (gigabit wavelength 1510)
                         rcGbic1530(36),     -- (gigabit wavelength 1530)
                         rcGbic1550(37),     -- (gigabit wavelength 1550)
                         rcGbic1570(38),     -- (gigabit wavelength 1570)
                         rcGbic1590(39),     -- (gigabit wavelength 1590)
                         rcGbic1610(40),     -- (gigabit wavelength 1610)
                         rcRmon(41),         -- (1000 base TProbe)
                         rcGbic1470APD(42),  -- (gigabit wavelength 1470-APD)
                         rcGbic1490APD(43),  -- (gigabit wavelength 1490-APD)
                         rcGbic1510APD(44),  -- (gigabit wavelength 1510-APD)
                         rcGbic1530APD(45),  -- (gigabit wavelength 1530-APD)
                         rcGbic1550APD(46),  -- (gigabit wavelength 1550-APD)
                         rcGbic1570APD(47),  -- (gigabit wavelength 1570-APD)
                         rcGbic1590APD(48),  -- (gigabit wavelength 1590-APD)
                         rcGbic1610APD(49),  -- (gigabit wavelength 1610-APD)
			 rc10GbLW(50),       -- (10 Gig Ethernet LW)
			 rc10GbLR(51),       -- (10 Gig Ethernet LR)
-- OM2.0 place holder added following 
--                       rcLogicalServerPort(52), 
-- opm Prism used as a server for MPLS
			 rc1000BaseTX(53),   -- (triple speed)
                         rcGbicBx(55),       -- (SFP - Single Fiber Bi-Directional - 100Base-Bxl)
			 rc10GbNone(56),     -- (10 Gig Feature)
                         rc10GbSR(58),       -- (10 Gig SR Ethernet)
                         rc10GbSW(59),       -- (10 Gib SW wavelength 850nm and sonet)
                         rc10GbER(60),       -- (10 Gig ER wavelen 1550nm)
                         rc10GbEW(61),       -- (10 Gig EW)
                         rc10GbOther(62),     -- (10 Gig Ethernet other)
                         rc1000BaseTXPOE(63),    -- (triplespeed withPOE support)
                         rc10GbZR(64),       -- (10 Gig ZR wavelength 1550nm)
                         rc10GbZW(65),       -- (10 Gig ZW wavelength 1550nm)
                         rcGbic1310Xd(66),   -- (gigabit wavelength 1310-distance 40Kms)
                         rcGbic1470Xd(67),   -- (gigabit wavelength 1470-distance 40Kms)
                         rcGbic1490Xd(68),   -- (gigabit wavelength 1490-distance 40Kms)
                         rcGbic1510Xd(69),   -- (gigabit wavelength 1510-distance 40Kms)
                         rcGbic1530Xd(70),   -- (gigabit wavelength 1530-distance 40Kms)
                         rcGbic1550Xd(71),   -- (gigabit wavelength 1550-distance 40Kms)
                         rcGbic1570Xd(72),   -- (gigabit wavelength 1570-distance 40Kms)
                         rcGbic1590Xd(73),   -- (gigabit wavelength 1590-distance 40Kms)
                         rcGbic1610Xd(74),   -- (gigabit wavelength 1610-distance 40Kms)
                         rcGbic1470Zx(75),   -- (gigabit wavelength 1470-distance 70Kms)
                         rcGbic1490Zx(76),   -- (gigabit wavelength 1490-distance 70Kms)
                         rcGbic1510Zx(77),   -- (gigabit wavelength 1510-distance 70Kms)
                         rcGbic1530Zx(78),   -- (gigabit wavelength 1530-distance 70Kms)
                         rcGbic1550Zx(79),   -- (gigabit wavelength 1550-distance 70Kms)
                         rcGbic1570Zx(80),   -- (gigabit wavelength 1570-distance 70Kms)
                         rcGbic1590Zx(81),   -- (gigabit wavelength 1590-distance 70Kms)
                         rcGbic1610Zx(82),   -- (gigabit wavelength 1610-distance 70Kms)
                         rcGbic1690Zx(83),   -- (gigabit wavelength 1690-distance 70Kms)
                         rcGbic1310Bx(84),   -- (gigabit wavelength 1310-distance 10Kms)
                         rcGbic1490Bx(85),   -- (gigabit wavelength 1490-distance 10Kms)
                         rcGbicEx(86),     -- (gigabit wavelength 1550-distance 120 Kms)
                         rcGbic850Sx(87),   -- (gigabit short haul wavelength 850)
                         rcGbic1200Lx(88),   -- (gigabit long haul wavelength 1200)
                         rcGbic1300Lx(89),   -- (gigabit long haul wavelength 1300)
                         rcGbic1310Lx(90),   -- (gigabit long haul wavelength 1310)
                         rcGbic1490Lx(91),   -- (gigabit long haul wavelength 1490)
                         rcGbic1550Lx(92),   -- (gigabit long haul wavelength 1550)
                         rcGbic1550Ex(93),   -- (gigabit wavelength 1550-distance 120Kms)
                         rc1GbFD(94),        -- (100/1000 Fiber Gbic)
                         rc10GbLRM(95),      -- (10 Gig LRM)
                         rc10GbDWDMR(96),    -- (10 Gig DWDM Ethernet)
                         rc10GbDWDMW(97),    -- (10 Gig DWDM Sonet)
			 rc100BaseSX(98),    -- (100 mbps fiber short haul wavelength)
                         rc100BaseLX(99),    -- (100 mbps fiber long haul wavelength)
                         rc100BaseFX(100),   -- (100 mbps fiber)
                         rc100BaseBX(101),   -- (100 mbps fiber)
                         rc100BaseZX(102),   -- (100 mbps fiber)
                         rcGbicMTRJ(103),    -- (Mechanical Transfer - registered jack)
                         rcGbic1300SeFx(104),-- (1300SE-FX Gbic Ethernet)
			 rcGbicCx(105),      -- (copper direct attach cable up to 15 meter)
			 rc10GbCX(106)       -- (copper direct attach cable up to 15 meter)
	              }
	MAX-ACCESS    read-only
	STATUS        current
	DESCRIPTION   "Port type"
	::= { rcPortEntry 2 }

rcPortAction OBJECT-TYPE
        SYNTAX        INTEGER {
                         none(1),            -- none of the following
                         flushMacFdb(2),     -- flush MAC forwarding table
                         flushArp(3),        -- flush ARP table
                         flushIp(4),         -- flush IP route table
                         flushAll(5),        -- flush all tables
			 triggerRipUpdate(6), -- manually trigger rip update
			 clearLoopDetectAlarm(7) -- manually enable the port on all the disabled vlans
                      }
        MAX-ACCESS    read-write
        STATUS        current
        DESCRIPTION   "Port related actions."
        DEFVAL        { none }
        ::= { rcPortEntry 6 }
 
rcPortResult OBJECT-TYPE 
        SYNTAX        	INTEGER { 
                       		none(1),        -- none of the following 
                       	  	inProgress(2),  -- in progress 
                       	  	success(3),     -- success
                       	  	fail(4)         -- failure 
                      	} 
        MAX-ACCESS		read-only 
        STATUS        	current 
        DESCRIPTION   	"Result from the last Vlan action." 
        DEFVAL        	{ none } 
        ::= { rcPortEntry 7 } 

rcPortAutoNegotiate OBJECT-TYPE
        SYNTAX 	      TruthValue
        MAX-ACCESS 	  read-write
        STATUS 	      current
        DESCRIPTION   "Indicate whether this port enabled for auto 
                       negotiations or not."
        DEFVAL	      { true }
	       ::= { rcPortEntry 11 }

rcPortAdminDuplex OBJECT-TYPE
        SYNTAX 		INTEGER { 
                      half(1),	-- half duplex
                      full(2)		-- full duplex  
        		      } 
        MAX-ACCESS 		read-write
        STATUS 		current
        DESCRIPTION     "Indicates the port duplex type "	
        DEFVAL		{ half }
        ::= { rcPortEntry 12 }

rcPortOperDuplex OBJECT-TYPE
        SYNTAX     INTEGER { 
                      half(1),	-- half duplex
                      full(2)		-- full duplex  
                   } 
        MAX-ACCESS 		read-only
        STATUS 		current
        DESCRIPTION 	"Indicate this port's current duplex value."
        ::= { rcPortEntry 13 }

rcPortAdminSpeed OBJECT-TYPE
        SYNTAX     INTEGER { 
                      none(0),
                      mbps10(1),	-- 10Mb/s
                      mbps100(2),	-- 100Mb/s
		      mbps1000(3),      -- 1000Mb/s
		      mbps10000(4)      -- 10Gb/s
                   } 
        MAX-ACCESS 		read-write
        STATUS 		current
        DESCRIPTION 	"Indicate this port's speed."
        DEFVAL		{ mbps10 }
        ::= { rcPortEntry 14 }

rcPortOperSpeed OBJECT-TYPE
        SYNTAX       Integer32  
        MAX-ACCESS   read-only
        STATUS       current
        DESCRIPTION  "Indicate this port's current speed value."
	       ::= { rcPortEntry 15 }

rcPortMltId OBJECT-TYPE
        SYNTAX       Integer32  
        MAX-ACCESS   read-only
        STATUS       current
        DESCRIPTION  "Indicate which multi-link trunk (MLT) this port
                      is assigned to.  If this port is not associated
                      with any MLT, this value will be set to zero(0)."
        DEFVAL		{ 0 }
        ::= { rcPortEntry 16 }

rcPortLocked OBJECT-TYPE
        SYNTAX        	TruthValue
        MAX-ACCESS        	read-only
        STATUS        	current
        DESCRIPTION   	"Indicate whether this port is locked." 
        DEFVAL        	{ false }
        ::= { rcPortEntry 17 }

rcPortAutoNegotiationSupported OBJECT-TYPE
        SYNTAX        	TruthValue
        MAX-ACCESS        	read-only
        STATUS        	current
        DESCRIPTION   	"Indicate whether this port can support 
		      	auto-negotiation." 
        DEFVAL        	{ false }
        ::= { rcPortEntry 18 }

rcPortSingleRoutablePort OBJECT-TYPE
        SYNTAX        	TruthValue
        MAX-ACCESS        	read-only
        STATUS        	current
        DESCRIPTION   	"Indicate whether this port is a single routable
		      	port.  If this value is true, the port functions
			like a traditional router port."
        DEFVAL        	{ false }
        ::= { rcPortEntry 19 }

rcPortUnknownMacDiscard OBJECT-TYPE
        SYNTAX          TruthValue
        MAX-ACCESS      read-write
        STATUS          current
        DESCRIPTION     "If rcUnknownMacDiscard is set to True, 
                         then a packet with an unknown source MAC address
                         is dropped on that port, and other ports then
                         will discard any packets with this MAC address
                         in the destination field.  
                         For example, 
                         suppose 11:22:33:44:55:66 is an unknown source MAC,
                         packets with source MAC 11:22:33:44:55 coming from 
                         this port is discarded, further more, packets with
                         destination MAC 11:22:33:44:55:66 coming from
                         other ports are also discarded, unless this address
                         is later learned on another port or the restriction
                         ages out."

        DEFVAL          { false }
        ::= { rcPortEntry 20 }

rcPortNumStateTransition OBJECT-TYPE
        SYNTAX        	Counter32
        MAX-ACCESS        	read-only
        STATUS        	current
        DESCRIPTION   	"# state transitions."
        ::= { rcPortEntry 21 }

rcPortQosLevel OBJECT-TYPE
        SYNTAX  	INTEGER {
                            level0(0),
                            level1(1),
                            level2(2),
                            level3(3),
                            level4(4),
                            level5(5),
                            level6(6),
                            level7(7)
                        }
	       MAX-ACCESS 	      	read-write
        STATUS 	      	current
        DESCRIPTION     "Used to specify the Qos level packets, carried on this
                        port, should be processed with."
        DEFVAL          { level1 }
	::= { rcPortEntry 30 }

rcPortDiffServEnable OBJECT-TYPE
        SYNTAX        	TruthValue
        MAX-ACCESS        	read-write
        STATUS        	current
        DESCRIPTION   	"Used to enable/disable the Differentiated Service
			feature on this port."
        DEFVAL        	{ false }
        ::= { rcPortEntry 31 }

rcPortDiffServType OBJECT-TYPE
        SYNTAX  	INTEGER {
                            none(0),
                            access(1),
                            core(2)
                        }
	       MAX-ACCESS 	      	read-write
        STATUS 	      	current
	       DESCRIPTION   	"Used to specify the Differentiated Service type
			                   for this port."
        DEFVAL        	{ access }
	::= { rcPortEntry 32 }

rcPortVendorDescr OBJECT-TYPE
        SYNTAX        	DisplayString (SIZE(16))
        MAX-ACCESS        	read-only
        STATUS        	current
        DESCRIPTION   	"Used to show the name of the vendor of this port's
			connector.  Only applicable to ports on a GBIC cards."
        ::= { rcPortEntry 34 }

rcPortName OBJECT-TYPE
        SYNTAX          DisplayString (SIZE (0..42))
        MAX-ACCESS      read-write
        STATUS          current
        DESCRIPTION     "This port's name."
        ::= { rcPortEntry 35 }

rcPortAdminRouting OBJECT-TYPE
        SYNTAX          EnableValue
        MAX-ACCESS      read-write
        STATUS          current
        DESCRIPTION     "Indicate whether the port is routable."
        DEFVAL          { enable }
   ::= { rcPortEntry 43 }

rcPortOperRouting OBJECT-TYPE
        SYNTAX          EnableValue
        MAX-ACCESS      read-only
        STATUS          current
        DESCRIPTION     "The status of the port whether is routable."
   ::= { rcPortEntry 44 }

rcPortIeee8021POverrideEnable OBJECT-TYPE
      SYNTAX          TruthValue
      MAX-ACCESS      read-write
      STATUS          current
      DESCRIPTION     "Used to enable/disable IEEE 802.1P override.
                       If it is enabled, 802.1p value from a tagged
                       frame may not be honored."
      DEFVAL          { false }
      ::= { rcPortEntry 46 }

rcPortHighSecureEnable OBJECT-TYPE
        SYNTAX          TruthValue
        MAX-ACCESS      read-write
        STATUS          current
        DESCRIPTION     "Enable/Disable high secure feature."
        ::= { rcPortEntry 51 }

rcPortMrouteStrLimit OBJECT-TYPE
        SYNTAX          INTEGER (1..32768)
        MAX-ACCESS      read-write
        STATUS          current
        DESCRIPTION     "maximum number of multicast streams that are
                         allowed to ingress to CPU through this port."
        DEFVAL          { 1984 }
        ::= { rcPortEntry 55 }

rcPortMrouteStrTimerCheck OBJECT-TYPE
        SYNTAX          INTEGER (1..3600)
        MAX-ACCESS      read-write
        STATUS          current
        DESCRIPTION     "sampling period to check number of multicast
                         streams that has ingressed CPU through this 
                         port in seconds."
        DEFVAL          { 10 }
        ::= { rcPortEntry 56 }

rcPortMrouteStrLimitEnable OBJECT-TYPE
        SYNTAX          TruthValue
        MAX-ACCESS      read-write
        STATUS          current
        DESCRIPTION     "enable or disable mroute stream limit on port."
        DEFVAL          { false }
        ::= { rcPortEntry 57 }

rcPortAutoNegAd OBJECT-TYPE
      SYNTAX       BITS {
                      advertise10Half(0),
                      advertise10Full(1),
                      advertise100Half(2),
                      advertise100Full(3),
                      advertise1000Full(5),
		      advertiseMacPause(6),  -- Not supported in 8600
		      advertiseAsymPause(7), -- Not supported in 8600	
                      advertiseNone(8)
                   }
      MAX-ACCESS   read-write
      STATUS       current
      DESCRIPTION  "This object is used to specify the port speed
                    and duplex abilities to be advertised during
                    link negotiation.

                    bit 0 - 10 half duplex advertised
                    bit 1 - 10 full duplex advertised
                    bit 2 - 100 half duplex advertised
                    bit 3 - 100 full duplex advertised
                    bit 5 - 1000 full duplex advertised
		    bit 6 - Mac PAUSE frame support advertised
		    bit 7 - Asymmetric PAUSE frame support advertised
                    bit 8 - No advertisements

                    The abilities specified in this object are only used
                    when auto-negotiation is enabled on the port.  If all
                    bits in this object are disabled, and auto-negotiation
                    is enabled on the port, then the physical link process
                    on the port will be disabled (if hardware supports
                    this ability).

                    Any change in the value of this bit map will force the
                    PHY to restart the auto-negotiation process.  This will
                    have the same effect as physically unplugging and
                    reattaching the cable plant attached to this port.

		   The capabilities being advertised are either all the 
                   capabilities supported by the hardware or the user- 
		   configured capabilities which is a subset of all the 
		   capability supported by hardware.
          
                   The default value for this object will be all the 
		   capabilities supported by the hardware.

		   Note that bit 6 and bit 7 are currently not supported
		   in ERS8600."
      ::= { rcPortEntry 62 }

rcPortAutoRecoverPort OBJECT-TYPE
        SYNTAX          TruthValue
        MAX-ACCESS      read-write
        STATUS          current
        DESCRIPTION     "enable or disable auto recovery of port from action
                         taken by cp-limit, link flap or loop detect features"
        DEFVAL          { false }
        ::= { rcPortEntry 64 }

rcPortEgressRateLimit OBJECT-TYPE
        SYNTAX          INTEGER(0|10000..10000000)
        MAX-ACCESS      read-write
        STATUS          current
        DESCRIPTION     "Egress Rate Limit. for VSP 9000, range is
			10000 to 10000000"
        ::= { rcPortEntry 67 }

rcPortEgressRateLimitState OBJECT-TYPE
        SYNTAX          EnableValue
        MAX-ACCESS      read-write
        STATUS          current
        DESCRIPTION     "Used to enable/disable shape/egress-rate-limit 
		        functionality."
        DEFVAL          { disable }
        ::= { rcPortEntry 68 }

rcPortIngressRateLimit OBJECT-TYPE
        SYNTAX          INTEGER(1000..10000000)
        MAX-ACCESS      read-write
        STATUS          current
        DESCRIPTION     "Limits the amount of traffic from this Ingress port."
        ::= { rcPortEntry 85 }

rcPortVrfIdList OBJECT-TYPE
        SYNTAX          IdList (SIZE (0..512))
        MAX-ACCESS      read-only
        STATUS          current
        DESCRIPTION     "The set of VRF ids to which this port belongs."
        ::= { rcPortEntry 87 }

rcPortVrfNameList OBJECT-TYPE
        SYNTAX          OCTET STRING
        MAX-ACCESS      read-only
        STATUS          current
        DESCRIPTION     "The set of VRF names to which this port belongs."
        ::= { rcPortEntry 96 }

rcPortBrouterVrfId OBJECT-TYPE
        SYNTAX          VrfIdentifier
        MAX-ACCESS      read-write
        STATUS          current
        DESCRIPTION     "Gives the VRF Id for this Brouter port. "
        ::= { rcPortEntry 97 }

rcPortBrouterVrfName OBJECT-TYPE
        SYNTAX          DisplayString (SIZE(0..32))
        MAX-ACCESS      read-only
        STATUS          current
        DESCRIPTION     "Gives the VRF Name for this Brouter port. "
        ::= { rcPortEntry 98 }

rcPortVrfCount OBJECT-TYPE
        SYNTAX          Counter32
        MAX-ACCESS      read-only
        STATUS          current
        DESCRIPTION     "The total number of VRFs this port is associated to."
        ::= { rcPortEntry 99 }

rcPortIngressRatePeak OBJECT-TYPE
        SYNTAX           INTEGER(0 | 64..10000000)
        MAX-ACCESS       read-write
        STATUS           current
        DESCRIPTION     "Peak rate limit for this port. 0 means disable"
	DEFVAL          { 0 }
        ::= { rcPortEntry 108 }

rcPortIngressRateSvc OBJECT-TYPE
        SYNTAX           INTEGER(0 | 64..10000000)
        MAX-ACCESS       read-write
        STATUS           current
        DESCRIPTION     "Service rate limit for this port. 0 mean deisable"
        DEFVAL         { 0 }
        ::= { rcPortEntry 109 }

rcPortCpLimitPktRate  OBJECT-TYPE
        SYNTAX          INTEGER(1000..20000)
        MAX-ACCESS      read-write
        STATUS          current
        DESCRIPTION     "Used to limit Control packets on the 
                         port to qos-levels 6 and 7.
                         Sets the limit in packets per second."
        DEFVAL          { 8000 }
        ::= { rcPortEntry 110 }

rcPortCpLimitShutDownEnable  OBJECT-TYPE
        SYNTAX          TruthValue
        MAX-ACCESS      read-write
        STATUS          current
        DESCRIPTION     "Used to indicate if the port should be shutdown 
                         when the CpLimitPktRate is exceeded."
        DEFVAL          { false }
        ::= { rcPortEntry 111 }

-- Port Pcap Table
rcPortPcapTable OBJECT-TYPE
        SYNTAX        SEQUENCE OF RcPortPcapEntry
        MAX-ACCESS    not-accessible
        STATUS        current
        DESCRIPTION   "Port pcap Table"
        ::= { rcPort 2 }

rcPortPcapEntry OBJECT-TYPE
        SYNTAX        RcPortPcapEntry
        MAX-ACCESS    not-accessible
        STATUS        current 
        DESCRIPTION   "Entry containing pcap info. for a particular port"
        INDEX         { rcPortPcapIndex }
        ::= { rcPortPcapTable 1 }

RcPortPcapEntry ::= SEQUENCE {
        rcPortPcapIndex               InterfaceIndex,
        rcPortPcapEnable              TruthValue,
        rcPortPcapMode                INTEGER
        }


rcPortPcapIndex OBJECT-TYPE
        SYNTAX          InterfaceIndex
        MAX-ACCESS      read-only
        STATUS          current 
        DESCRIPTION     "An index value that uniquely identifies a port.
                         This value is similar to ifIndex in MIB2."
        ::= { rcPortPcapEntry 1 }

rcPortPcapEnable OBJECT-TYPE
        SYNTAX          TruthValue
        MAX-ACCESS      read-write
        STATUS          current 
        DESCRIPTION     "To enable pcap for the port"
        DEFVAL          { false }
        ::= { rcPortPcapEntry 2 }

rcPortPcapMode OBJECT-TYPE
        SYNTAX          INTEGER {
                                tx(1),
                                rx(2),
                                both(3)
                        }
        MAX-ACCESS      read-write
        STATUS          current 
        DESCRIPTION     "Mode in which pcap is enabled"
        DEFVAL          { rx }
        ::= { rcPortPcapEntry 3 }


-- Port Lock Group

rcPortLock OBJECT IDENTIFIER ::= { rcChassis 11 }

rcPortLockEnable OBJECT-TYPE
        SYNTAX        	TruthValue
        MAX-ACCESS        	read-write
        STATUS        	current
        DESCRIPTION   	"Indicate whether the port lock feature is enabled."
        DEFVAL        	{ false }
        ::= { rcPortLock 1 }

rcPortLockLockedPorts OBJECT-TYPE
        SYNTAX        	PortSet
        MAX-ACCESS        	read-write
        STATUS        	current
        DESCRIPTION   	"The set of ports that are administratively locked.
		      	Locked ports cannot be modified in anyway until the
		      	port is unlocked first."
        ::= { rcPortLock 2 }

-- PORT LACP 

rcPortLacpTable OBJECT-TYPE
        SYNTAX        SEQUENCE OF RcPortLacpEntry
        MAX-ACCESS    not-accessible
        STATUS        current
        DESCRIPTION   "Port LACP table"
        ::= { rcPort 4 }

rcPortLacpEntry OBJECT-TYPE
        SYNTAX        RcPortLacpEntry
        MAX-ACCESS    not-accessible
        STATUS        current
        DESCRIPTION   "Entry containing info. for a particular port"
        INDEX         { rcPortIndex }
        ::= { rcPortLacpTable 1 }

RcPortLacpEntry ::= SEQUENCE {
    rcPortLacpAdminEnable                 TruthValue,
    rcPortLacpOperEnable                  TruthValue,
    rcPortLacpFastPeriodicTime            INTEGER,
    rcPortLacpSlowPeriodicTime            INTEGER,
    rcPortLacpTimeoutScale                INTEGER,
    rcPortLacpAggrWaitTime                INTEGER,
    rcPortLacpFastPeriodicTimeOper        INTEGER,
    rcPortLacpSlowPeriodicTimeOper        INTEGER,
    rcPortLacpTimeoutScaleOper            INTEGER,
    rcPortLacpAggrWaitTimeOper            INTEGER
    }

rcPortLacpAdminEnable OBJECT-TYPE
        SYNTAX        TruthValue
        MAX-ACCESS    read-write
        STATUS        current
        DESCRIPTION   "Administratively enable/disable LACP on a port"
        DEFVAL        { false }
        ::= { rcPortLacpEntry 1 }

rcPortLacpOperEnable OBJECT-TYPE
        SYNTAX        TruthValue
        MAX-ACCESS    read-only
        STATUS        current
        DESCRIPTION   "Indicates if LACP is operationally enabled or disabled 
                       on a port"
        ::= { rcPortLacpEntry 2 }

rcPortLacpFastPeriodicTime OBJECT-TYPE
        SYNTAX        INTEGER (200..20000)
        MAX-ACCESS    read-write
        STATUS        current
        DESCRIPTION   "The number of miliseconds between periodic transmissions
                       using Short Timeouts."
        DEFVAL        { 1000 }
        ::= { rcPortLacpEntry 3 }

rcPortLacpSlowPeriodicTime OBJECT-TYPE
        SYNTAX        INTEGER (10000..30000)
        MAX-ACCESS    read-write
        STATUS        current
        DESCRIPTION   "The number of miliseconds between periodic transmissions
                       using LONG Timeouts."
        DEFVAL        { 30000 }
        ::= { rcPortLacpEntry 4 }

rcPortLacpTimeoutScale OBJECT-TYPE
        SYNTAX        INTEGER (1..10)
        MAX-ACCESS    read-write
        STATUS        current
        DESCRIPTION   "Scalar value used to calculate timeout time from
                       periodic time. Timeout = PeriodicTime * TimeoutScale"
        DEFVAL        { 3 }
        ::= { rcPortLacpEntry 5 }

rcPortLacpAggrWaitTime OBJECT-TYPE
        SYNTAX        INTEGER (200..2000)
        MAX-ACCESS    read-write
        STATUS        current
        DESCRIPTION   "The number of mili seconds to delay aggregation to
                       allow multiple links to aggregate simultaneously."
        DEFVAL        { 2000 }
        ::= { rcPortLacpEntry 6 }

rcPortLacpFastPeriodicTimeOper OBJECT-TYPE
        SYNTAX        INTEGER (200..20000) 
        MAX-ACCESS    read-only
        STATUS        current
        DESCRIPTION   "The operating value of fast periodic timer on the port."
        ::= { rcPortLacpEntry 7 }

rcPortLacpSlowPeriodicTimeOper OBJECT-TYPE
        SYNTAX        INTEGER (10000..30000) 
        MAX-ACCESS    read-only
        STATUS        current
        DESCRIPTION   "The operating value of slow periodic timer on the port."
        ::= { rcPortLacpEntry 8 }


rcPortLacpTimeoutScaleOper OBJECT-TYPE
        SYNTAX        INTEGER (1..10) 
        MAX-ACCESS    read-only
        STATUS        current
        DESCRIPTION   "The operating value of timeout scale on the port."
        ::= { rcPortLacpEntry 9 }

rcPortLacpAggrWaitTimeOper OBJECT-TYPE
        SYNTAX        INTEGER (200..2000) 
        MAX-ACCESS    read-only
        STATUS        current
        DESCRIPTION   "The operating value of aggreagate wait time on port."
        ::= { rcPortLacpEntry 10 }

rcPortVLacpTable OBJECT-TYPE
        SYNTAX        SEQUENCE OF RcPortVLacpEntry
        MAX-ACCESS    not-accessible
        STATUS        current
        DESCRIPTION   "Port Virtual LACP table"
        ::= { rcPort 5 }

rcPortVLacpEntry OBJECT-TYPE
        SYNTAX        RcPortVLacpEntry
        MAX-ACCESS    not-accessible
        STATUS        current
        DESCRIPTION   "Entry containing info. for a particular port"
        INDEX         { rcPortIndex }
        ::= { rcPortVLacpTable 1 }

RcPortVLacpEntry ::= SEQUENCE {
    rcPortVLacpAdminEnable                 TruthValue,
    rcPortVLacpOperEnable                  TruthValue,
    rcPortVLacpFastPeriodicTimer           INTEGER,
    rcPortVLacpSlowPeriodicTimer           INTEGER,
    rcPortVLacpTimeout                     INTEGER,
    rcPortVLacpTimeoutScale                INTEGER,
    rcPortVLacpEtherType                   Integer32,
    rcPortVLacpEtherMacAddress             MacAddress,
    rcPortVLacpPortState                   INTEGER
    }

rcPortVLacpAdminEnable OBJECT-TYPE
        SYNTAX        TruthValue
        MAX-ACCESS    read-write
        STATUS        current
        DESCRIPTION   "Administratively enable/disable Virtual LACP on a port"
        DEFVAL        { false }
        ::= { rcPortVLacpEntry 1 }

rcPortVLacpOperEnable OBJECT-TYPE
        SYNTAX        TruthValue
        MAX-ACCESS    read-only
        STATUS        current
        DESCRIPTION   "Indicates if Virtual LACP is operationally enabled or 
                       disabled on a port"
        ::= { rcPortVLacpEntry 2 }

rcPortVLacpFastPeriodicTimer OBJECT-TYPE
        SYNTAX        INTEGER (100..20000)
        MAX-ACCESS    read-write
        STATUS        current
        DESCRIPTION   "The number of miliseconds between periodic transmissions
                       using Short Timeouts"
        DEFVAL        { 200 }
        ::= { rcPortVLacpEntry 3 }

rcPortVLacpSlowPeriodicTimer OBJECT-TYPE
        SYNTAX        INTEGER (10000..30000)
        MAX-ACCESS    read-write
        STATUS        current
        DESCRIPTION   "The number of miliseconds between periodic transmissions
                       using LONG Timeouts."
        DEFVAL        { 30000 }
        ::= { rcPortVLacpEntry 4 }

rcPortVLacpTimeout     OBJECT-TYPE
        SYNTAX        INTEGER {
                         short(1),
                         long(2)
                      }
        MAX-ACCESS    read-write
        STATUS        current
        DESCRIPTION   "Timeout control value. Long or Short Timeout"
        ::= { rcPortVLacpEntry 5 }

rcPortVLacpTimeoutScale OBJECT-TYPE
        SYNTAX        INTEGER (1..10)
        MAX-ACCESS    read-write
        STATUS        current
        DESCRIPTION   "Scalar value used to calculate timeout time from
                       periodic time. Timeout = PeriodicTime * TimeoutScale"
        DEFVAL        { 3 }
        ::= { rcPortVLacpEntry 6 }

rcPortVLacpEtherType  OBJECT-TYPE
        SYNTAX        Integer32(1536..65535)
        MAX-ACCESS    read-write
        STATUS        current
        DESCRIPTION   "VLACP Protocol Identification. The id value is 
                       in Hex. Range in hex (0x600..0xffff)"
        DEFVAL        { '8103'h }
        ::= { rcPortVLacpEntry 7 }

rcPortVLacpEtherMacAddress OBJECT-TYPE
        SYNTAX         MacAddress
        MAX-ACCESS     read-write
        STATUS         current
        DESCRIPTION    "Multicast Mac Address exclusively used for VLACPDU's"
        ::= { rcPortVLacpEntry 8 }

rcPortVLacpPortState OBJECT-TYPE
        SYNTAX         INTEGER {
                          up(1),
                          down(2)
                       }
        MAX-ACCESS     read-only
        STATUS         current
        DESCRIPTION    "Display the Vlacp Port State."
        ::= { rcPortVLacpEntry 9 }

-- Port Remote Mirroring Table

rcPortRemoteMirroringTable OBJECT-TYPE
        SYNTAX        SEQUENCE OF RcPortRemoteMirroringEntry
        MAX-ACCESS    not-accessible
        STATUS        current
        DESCRIPTION   "Port Remote Mirroring Table"
        ::= { rcPort 6 }

rcPortRemoteMirroringEntry OBJECT-TYPE
        SYNTAX        RcPortRemoteMirroringEntry
        MAX-ACCESS    not-accessible
        STATUS        current
        DESCRIPTION   "Entry containing remote mirroring info. for a 
                       particular port"
        INDEX         { rcPortRemoteMirroringIndex }
        ::= { rcPortRemoteMirroringTable 1 }

RcPortRemoteMirroringEntry ::= SEQUENCE {
        rcPortRemoteMirroringIndex            InterfaceIndex,
        rcPortRemoteMirroringEnable           TruthValue,
        rcPortRemoteMirroringMode             INTEGER,
        rcPortRemoteMirroringSrcMac           MacAddress,
        rcPortRemoteMirroringDstMac           MacAddress,
        rcPortRemoteMirroringEtherType        INTEGER,
        rcPortRemoteMirroringVlanIdListSize   INTEGER,
        rcPortRemoteMirroringVlanIdList       OCTET STRING (SIZE(4096)),
        rcPortRemoteMirroringRowStatus        RowStatus
        }


rcPortRemoteMirroringIndex OBJECT-TYPE
        SYNTAX          InterfaceIndex
        MAX-ACCESS      read-only
        STATUS          current
        DESCRIPTION     "An index value that uniquely identifies a port.
                         This value is similar to ifIndex in MIB2."
        ::= { rcPortRemoteMirroringEntry 1 }

rcPortRemoteMirroringEnable OBJECT-TYPE
        SYNTAX          TruthValue
        MAX-ACCESS      read-write
        STATUS          current
        DESCRIPTION     "To enable remote Mirroring for the port"
        DEFVAL          { false }
        ::= { rcPortRemoteMirroringEntry 2 }

rcPortRemoteMirroringMode OBJECT-TYPE
        SYNTAX          INTEGER {
                                source(1),
                                termination(2)
                        }
        MAX-ACCESS      read-write
        STATUS          current
        DESCRIPTION     "Mode in which remote mirroring is enabled"
        DEFVAL          { source }
        ::= { rcPortRemoteMirroringEntry 3 }

rcPortRemoteMirroringSrcMac OBJECT-TYPE
        SYNTAX          MacAddress
        MAX-ACCESS      read-write
        STATUS          current
        DESCRIPTION     "Source Mac of the remote mirrored packet. 
                         Remote mirroring packet will be send with  
                         this source mac address"
        ::= { rcPortRemoteMirroringEntry 4 }


rcPortRemoteMirroringDstMac OBJECT-TYPE
        SYNTAX          MacAddress
        MAX-ACCESS      read-write
        STATUS          current
        DESCRIPTION     "Destination Mac of the remote mirrored packet.
                         Packets will be bridged to this mac address. 
                         Remote mirroring packet will be send to this
                         mac address"
        ::= { rcPortRemoteMirroringEntry 5 }

rcPortRemoteMirroringEtherType OBJECT-TYPE
        SYNTAX          INTEGER (0..65535)
        MAX-ACCESS      read-write
        STATUS          current
        DESCRIPTION     "Ethertype of the remote mirrored packet. Packets
                         will be send with this ethertype"
        DEFVAL          { '8103'h }
        ::= { rcPortRemoteMirroringEntry 6 }

rcPortRemoteMirroringVlanIdListSize OBJECT-TYPE
        SYNTAX          INTEGER (0..2000)
        MAX-ACCESS      read-only
        STATUS          current
        DESCRIPTION     "Used to indicate the number of VLAN IDs
                         that are assigned to this port."
        ::= { rcPortRemoteMirroringEntry 7 }

rcPortRemoteMirroringVlanIdList OBJECT-TYPE
        SYNTAX          OCTET STRING (SIZE(4096))
        MAX-ACCESS      read-write
        STATUS          current
        DESCRIPTION     "This field is used only if the port is assigned as
                         remote mirroring termination port. Represents zero 
                         or more filter lists vlan in which the Destination 
                         Mac address resides.  Each VLAN ID is stored as 
                         two bytes in this array starting from offset zero.  
                         Any unused bytes should be set to zero."
        ::= { rcPortRemoteMirroringEntry 8 }

rcPortRemoteMirroringRowStatus OBJECT-TYPE
        SYNTAX          RowStatus
        MAX-ACCESS      read-write
        STATUS          current
        DESCRIPTION     "RowStatus"
        ::= { rcPortRemoteMirroringEntry 9 }

-- Additional Chassis Group Variables

rcChasBrouterPorts OBJECT-TYPE
        SYNTAX        	PortSet 
        MAX-ACCESS      read-only
        STATUS        	current
        DESCRIPTION   	"Used to indicate which ports in the system are
			configured as Brouter ports."
        ::= { rcChassis 17 }

rcChasFtpDaemonInSecondaryCpu OBJECT-TYPE
        SYNTAX          TruthValue
        MAX-ACCESS      read-write
        STATUS          current
        DESCRIPTION     "Used to enable/disable FTP daemon in 2nd cpu."
               DEFVAL           { false }
        ::= { rcChassis 26 }

rcChasNewVlanOptmMode OBJECT-TYPE
        SYNTAX        TruthValue
        MAX-ACCESS    read-write
        STATUS        current
        DESCRIPTION   "Vlan Optimization mode."
        ::= { rcChassis 28 }   
 
rcChasVlanOptmMode OBJECT-TYPE
        SYNTAX        TruthValue
        MAX-ACCESS    read-only
        STATUS        current
        DESCRIPTION   "Vlan Optimization mode the switch currently has
                       booted and will remain the same until the next 
                       reboot."
        ::= { rcChassis 29 }  

rcChasRspMode OBJECT-TYPE
        SYNTAX        TruthValue
        MAX-ACCESS    read-write
        STATUS        current
        DESCRIPTION   "This configuration is for enabling/disabling 256K
                       mode. The change will take effect upon reboot."
        ::= { rcChassis 35 }

rcChasRspOperMode OBJECT-TYPE
        SYNTAX        TruthValue
        MAX-ACCESS    read-only
        STATUS        current
        DESCRIPTION   "R-mode the switch currently has booted and
                       will remain the same until the next reboot."
        ::= { rcChassis 36 }

rcChasRspModeError OBJECT-TYPE
        SYNTAX       INTEGER {
                         none(1),
                         non256KCardOffLine(2)
                      }
        MAX-ACCESS    read-only
        STATUS        current
        DESCRIPTION   "Used to indicate the r-mode error status"
        ::= { rcChassis 37 }

rcChasNewMulticastResourceReservation OBJECT-TYPE
        SYNTAX        Integer32 (64..4083)
        MAX-ACCESS    read-write
        STATUS        current
        DESCRIPTION   "Used to reserve MGIDs for IP Multicast.
                      The change will take effect upon reboot."
        DEFVAL        { 2048 }
        ::= { rcChassis 44 }

rcChasMulticastResourceReservation OBJECT-TYPE
        SYNTAX        Integer32 (64..4083)
        MAX-ACCESS    read-only
        STATUS        current
        DESCRIPTION   "MGIDs the switch currently has reserved for IP       
                      Multicast; will remain the same until the next
                      reboot."
        ::= { rcChassis 45 }

rcChasNewMaxVlanResourceReservation OBJECT-TYPE
        SYNTAX        EnableValue
        MAX-ACCESS    read-write
        STATUS        current
        DESCRIPTION   "A mode where all MGIDs are reserved for VLAN use
                      only; no IPMC.  The change will take effect upon
                      reboot."
        DEFVAL        { disable }
        ::= { rcChassis 46 }
       
rcChasMaxVlanResourceReservation OBJECT-TYPE
        SYNTAX        EnableValue
        MAX-ACCESS    read-only
        STATUS        current
        DESCRIPTION   "Tells if all MGIDs are reserved for VLAN use.  Will
                      remain the same until the next reboot."
        ::= { rcChassis 47 }

rcChasMgidUsageVlanCurrent OBJECT-TYPE
        SYNTAX        Integer32 (1..4084)
        MAX-ACCESS    read-only
        STATUS        current
        DESCRIPTION   "Number of MGIDs currently used for VLAN, including
                      SMLT"
        ::= { rcChassis 48 }

rcChasMgidUsageVlanRemaining OBJECT-TYPE
        SYNTAX        Integer32 (0..4084)
        MAX-ACCESS    read-only
        STATUS        current
        DESCRIPTION   "Number of MGIDs remaining allocated for VLAN"
        ::= { rcChassis 49 }

rcChasMgidUsageMulticastCurrent OBJECT-TYPE
        SYNTAX        Integer32 (0..4083)
        MAX-ACCESS    read-only
        STATUS        current
        DESCRIPTION   "Number of MGIDs currently used for IPMC"
        ::= { rcChassis 50 }

rcChasMgidUsageMulticastRemaining OBJECT-TYPE
        SYNTAX        Integer32 (0..4083)
        MAX-ACCESS    read-only
        STATUS        current
        DESCRIPTION   "Number of MGIDs remaining allocated for IPMC"
        ::= { rcChassis 51 }

rcChasForceTopologyIpFlagEnable OBJECT-TYPE
        SYNTAX          TruthValue
        MAX-ACCESS      read-write
        STATUS          current
        DESCRIPTION     "Used to enable/disable flag which is used to  set the  			 CLIP-ip as topology ip"
         DEFVAL          { false }
        ::= { rcChassis 53 }

-- This Parameter is defined for Network Topology.
-- ER:Q01654904.

rcChasCircuitlessIpId OBJECT-TYPE
        SYNTAX          Integer32 (0..256) 
        MAX-ACCESS      read-write
        STATUS          current
        DESCRIPTION     "The Clip-Id set by the user to be used as Topology-ip.
			'0' means no circuitless IP id while '1..256' is valid
			circuitless Id"
        ::= { rcChassis 54 }


-- Table Size Group

rcTblRmonStatSize OBJECT-TYPE
        SYNTAX        Integer32
        MAX-ACCESS    read-only
        STATUS        current
        DESCRIPTION   "Used to indicate the current size of the RMON
                      Statistic table."
        ::= { rcTblSize 1 }

rcTblRmonHistoryControlSize OBJECT-TYPE
        SYNTAX        Integer32
        MAX-ACCESS    read-only
        STATUS        current
        DESCRIPTION   "Used to indicate the current size of the RMON  
                      History Control table." 
        ::= { rcTblSize 2 }

rcTblRmonHistoryEnetSize OBJECT-TYPE
        SYNTAX        Integer32
        MAX-ACCESS    read-only
        STATUS        current
        DESCRIPTION   "Used to indicate the current size of the RMON  
                      History Ethernet table." 
        ::= { rcTblSize 3 }

rcTblRmonAlarmSize OBJECT-TYPE
        SYNTAX        Integer32
        MAX-ACCESS    read-only
        STATUS        current
        DESCRIPTION   "Used to indicate the current size of the RMON  
                      Alarm table." 
        ::= { rcTblSize 4 }

rcTblRmonEventSize OBJECT-TYPE
        SYNTAX        Integer32
        MAX-ACCESS    read-only
        STATUS        current
        DESCRIPTION   "Used to indicate the current size of the RMON  
                      Event table." 
        ::= { rcTblSize 5 }

rcTblRmonLogSize OBJECT-TYPE
        SYNTAX        Integer32
        MAX-ACCESS    read-only
        STATUS        current
        DESCRIPTION   "Used to indicate the current size of the RMON  
                      Log table." 
        ::= { rcTblSize 6 }

rcTblArTblSize OBJECT-TYPE  
        SYNTAX        Integer32  
        MAX-ACCESS    read-only  
        STATUS        current  
        DESCRIPTION   "Used to indicate the size of the Address 
                      Translation (AR) table."
        ::= { rcTblSize 7 }


rcTblArFree OBJECT-TYPE  
        SYNTAX        Integer32  
        MAX-ACCESS    read-only  
        STATUS        current  
        DESCRIPTION   "Used to indicate the number of free
                      entries that are available in the Address 
                      Translation (AR) table."
        ::= { rcTblSize 8 }

rcTblArNoSpace OBJECT-TYPE  
        SYNTAX        Integer32  
        MAX-ACCESS    read-only  
        STATUS        current  
        DESCRIPTION   "Used to indicate the number of entries that could
                      not be added to the Address Translation (AR) table
                      due to lack of space."  
        ::= { rcTblSize 9 }

rcTblArAdded OBJECT-TYPE
        SYNTAX        Integer32
        MAX-ACCESS    read-only
        STATUS        current
        DESCRIPTION   "Used to indicate the number of entries added to
                      the Address Translation (AR) table." 
        ::= { rcTblSize 10 }

rcTblArDeleted OBJECT-TYPE 
        SYNTAX        Integer32 
        MAX-ACCESS    read-only 
        STATUS        current 
        DESCRIPTION   "Used to indicate the number of entries deleted to
                      the Address Translation (AR) table."
        ::= { rcTblSize 11 }

rcTblArMacAdded OBJECT-TYPE 
        SYNTAX        Integer32 
        MAX-ACCESS    read-only 
        STATUS        current 
        DESCRIPTION   "Used to indicate the number of MAC entries added to
                      the Address Translation (AR) table."
        ::= { rcTblSize 12 }

rcTblArMacDeleted OBJECT-TYPE 
        SYNTAX        Integer32 
        MAX-ACCESS    read-only 
        STATUS        current 
        DESCRIPTION   "Used to indicate the number of MAC entries deleted to
                      the Address Translation (AR) table."
        ::= { rcTblSize 13 }

rcTblArMacMoved OBJECT-TYPE 
        SYNTAX        Integer32 
        MAX-ACCESS    read-only 
        STATUS        current 
        DESCRIPTION   "Used to indicate the number of MAC entries moved in 
                      the Address Translation (AR) table."
        ::= { rcTblSize 14 }

rcTblArIpAdded OBJECT-TYPE 
        SYNTAX        Integer32 
        MAX-ACCESS    read-only 
        STATUS        current 
        DESCRIPTION   "Used to indicate the number of IP entries added to
                      the Address Translation (AR) table."
        ::= { rcTblSize 15 }

rcTblArIpDeleted OBJECT-TYPE  
        SYNTAX        Integer32  
        MAX-ACCESS    read-only  
        STATUS        current  
        DESCRIPTION   "Used to indicate the number of IP entries deleted to 
                      the Address Translation (AR) table."    
        ::= { rcTblSize 16 }

rcTblArMcastTblSize OBJECT-TYPE  
        SYNTAX        Integer32  
        MAX-ACCESS    read-only  
        STATUS        current  
        DESCRIPTION   "Used to indicate the size of the Multicast 
                      Address Translation (AR) table."
        ::= { rcTblSize 17 }


rcTblArFreeMcastGroups OBJECT-TYPE  
        SYNTAX        Integer32  
        MAX-ACCESS    read-only  
        STATUS        current  
        DESCRIPTION   "Used to indicate the number of free multicast
                      groups availabe in the Address Translation (AR) 
                      table."
        ::= { rcTblSize 18 }

rcTblArIpMcastAdded OBJECT-TYPE  
        SYNTAX        Integer32  
        MAX-ACCESS    read-only  
        STATUS        current  
        DESCRIPTION   "Used to indicate the number of Ip multicast
                      entries that are added to the Address 
                      Translation (AR) table."
        ::= { rcTblSize 19 }

rcTblArIpMcastDeleted OBJECT-TYPE  
        SYNTAX        Integer32  
        MAX-ACCESS    read-only  
        STATUS        current  
        DESCRIPTION   "Used to indicate the number of Ip multicast
                      entries that are deleted from the Address 
                      Translation (AR) table."
        ::= { rcTblSize 20 }

rcTblArVlanByPortAdded OBJECT-TYPE  
        SYNTAX        Integer32  
        MAX-ACCESS    read-only  
        STATUS        current  
        DESCRIPTION   "Used to indicate the number of VLAN by port
                      entries that are added to the Address 
                      Translation (AR) table."
        ::= { rcTblSize 21 }

rcTblArVlanByPortDeleted OBJECT-TYPE  
        SYNTAX        Integer32  
        MAX-ACCESS    read-only  
        STATUS        current  
        DESCRIPTION   "Used to indicate the number of VLAN by port
                      entries that are deleted from the Address 
                      Translation (AR) table."
        ::= { rcTblSize 22 }

rcTblArVlanByProtocolAdded OBJECT-TYPE  
        SYNTAX        Integer32  
        MAX-ACCESS    read-only  
        STATUS        current  
        DESCRIPTION   "Used to indicate the number of Vlans by 
                      Protocol Type entries that are added to 
                      the Address Translation (AR) table."
        ::= { rcTblSize 23 }

rcTblArVlanByProtocolDeleted OBJECT-TYPE  
        SYNTAX        Integer32  
        MAX-ACCESS    read-only  
        STATUS        current  
        DESCRIPTION   "Used to indicate the number of Vlans by 
                      Protocol Type entries that are deleted from 
                      the Address Translation (AR) table."
        ::= { rcTblSize 24 }

rcTblArVlanByIpSubnetAdded OBJECT-TYPE  
        SYNTAX        Integer32  
        MAX-ACCESS    read-only  
        STATUS        current  
        DESCRIPTION   "Used to indicate the number of VLAN by Ip 
                      entries that are added to the Address 
                      Translation (AR) table."
        ::= { rcTblSize 25 }

rcTblArVlanByIpSubnetDeleted OBJECT-TYPE  
        SYNTAX        Integer32  
        MAX-ACCESS    read-only  
        STATUS        current  
        DESCRIPTION   "Used to indicate the number of VLAN by Ip 
                      entries that are deleted from the Address 
                      Translation (AR) table."
        ::= { rcTblSize 26 }

rcTblArIpSubnetsAdded OBJECT-TYPE  
        SYNTAX        Integer32  
        MAX-ACCESS    read-only  
        STATUS        current  
        DESCRIPTION   "Used to indicate the number of Ip subnet
                      entries that are added to the Address 
                      Translation (AR) table."
        ::= { rcTblSize 27 }

rcTblArIpSubnetsDeleted OBJECT-TYPE  
        SYNTAX        Integer32  
        MAX-ACCESS    read-only  
        STATUS        current  
        DESCRIPTION   "Used to indicate the number of Ip subnet 
                      entries that are deleted from the Address 
                      Translation (AR) table."
        ::= { rcTblSize 28 }

rcTblArRsvpsAdded OBJECT-TYPE  
        SYNTAX        Integer32  
        MAX-ACCESS    read-only  
        STATUS        current  
        DESCRIPTION   "Used to indicate the number of RSVP
                      entries that are added to the Address 
                      Translation (AR) table."
        ::= { rcTblSize 29 }

rcTblArRsvpsDeleted OBJECT-TYPE  
        SYNTAX        Integer32  
        MAX-ACCESS    read-only  
        STATUS        current  
        DESCRIPTION   "Used to indicate the number of RSVP
                      entries that are deleted from the Address 
                      Translation (AR) table."
        ::= { rcTblSize 30 }


rcTblBrdgFdbSize OBJECT-TYPE  
        SYNTAX        Integer32  
        MAX-ACCESS    read-only  
        STATUS        current  
        DESCRIPTION   "Used to indicate the number of entries in the 
                      dot1d forwarding database table."    
        ::= { rcTblSize 31 }

rcTblBrdgStaticSize OBJECT-TYPE  
        SYNTAX        Integer32  
        MAX-ACCESS    read-only  
        STATUS        current  
        DESCRIPTION   "Used to indicate the number of entries in the 
                      dot1d Static Address Filtering table."    
        ::= { rcTblSize 32 }

rcTblIpAddrSize OBJECT-TYPE  
        SYNTAX        Integer32  
        MAX-ACCESS    read-only  
        STATUS        current  
        DESCRIPTION   "Used to indicate the number of entries in the 
                      IP Address table."    
        ::= { rcTblSize 33 }

rcTblIpForwardingSize OBJECT-TYPE  
        SYNTAX        Integer32  
        MAX-ACCESS    read-only   
        STATUS        current   
        DESCRIPTION   "Used to indicate the number of entries in the 
                       IP Forwarding/Best Route table."        
        ::= { rcTblSize 34 }

rcTblIpNetToMediaSize OBJECT-TYPE  
        SYNTAX        Integer32  
        MAX-ACCESS    read-only   
        STATUS        current   
        DESCRIPTION   "Used to indicate the number of entries in the 
                      IP Net-to-media table."        
        ::= { rcTblSize 35 }

rcTblIpBestPlusAltRouteSize OBJECT-TYPE  
        SYNTAX        Integer32  
        MAX-ACCESS    read-only  
        STATUS        current  
        DESCRIPTION   ""    
        ::= { rcTblSize 36 }

rcTblIpBestPathSize OBJECT-TYPE  
        SYNTAX        Integer32  
        MAX-ACCESS    read-only  
        STATUS        current  
        DESCRIPTION   ""    
        ::= { rcTblSize 37 }

rcTblIpBestPlusAltPathSize OBJECT-TYPE  
        SYNTAX        Integer32  
        MAX-ACCESS    read-only   
        STATUS        current   
        DESCRIPTION   ""        
        ::= { rcTblSize 38 }


-- IP Group

rcIpConf OBJECT IDENTIFIER ::= { rcIp 1 }

-- IP Configuration Table

rcIpConfTable OBJECT-TYPE
        SYNTAX        SEQUENCE OF RcIpConfEntry
        MAX-ACCESS    not-accessible
        STATUS        current
        DESCRIPTION   "A table used to maintain IP routing information 
                      for a particular interface."
        ::= { rcIpConf 1 }
 
rcIpConfEntry OBJECT-TYPE
        SYNTAX        RcIpConfEntry
        MAX-ACCESS    not-accessible
        STATUS        current
        DESCRIPTION   "Entry containing IP routing information.  An entry
                      is automatically created in this table when routing 
		      is enabled for an interface -or- when an ip address 
                      is configured on an interface."
        INDEX         { rcIpConfIfIndex }
        ::= { rcIpConfTable 1 }
 
RcIpConfEntry ::= SEQUENCE {
                rcIpConfIfIndex               InterfaceIndexOrZero,
                rcIpConfAdvertDefRte          TruthValue,
                rcIpConfAcceptDefRte          TruthValue,
                rcIpConfRowStatus             RowStatus,
                rcIpConfRipEnable             TruthValue,
                rcIpConfOspfEnable            TruthValue,
                rcIpConfIgmpEnable            TruthValue,
                rcIpConfAddrAssigned          TruthValue,
                rcIpConfDhcpEnable            TruthValue,
                rcIpConfTriggeredUpdateEnable TruthValue,
                rcIpConfAutoAggrerateEnable   TruthValue,
                rcIpConfGenerateDefaultRoute  TruthValue,
                rcIpConfAdvertiseWhenDown     TruthValue,
                rcIpConfDirectBroadcastEnable TruthValue,
                rcIpConfRipInPolicy           DisplayString,
                rcIpConfRipOutPolicy          DisplayString,
                rcIpConfOspfIfType            INTEGER,
                rcIpConfRipCost               INTEGER,
                rcIpConfRipHolddown           INTEGER,
                rcIpConfRipTimeout            INTEGER,
                rcIpConfRsmltEnable           TruthValue,
                rcIpConfReversePathCheckEnable       TruthValue,
                rcIpConfReversePathCheckMode         INTEGER,
		rcIpConfIpVpnLiteEnable       TruthValue
        }

rcIpConfIfIndex OBJECT-TYPE
        SYNTAX        InterfaceIndexOrZero (0..6142)
        MAX-ACCESS    read-only
        STATUS        current
        DESCRIPTION   "An unique value to identify a physical interface 
 		      or a logical interface (VLAN)."
        ::= { rcIpConfEntry 1 }

rcIpConfAdvertDefRte OBJECT-TYPE
        SYNTAX        TruthValue
        MAX-ACCESS    read-write
        STATUS        current
        DESCRIPTION   "Used to indicate whether this interface should
		      advertize a RIP default route." 
        ::= { rcIpConfEntry 2 }

rcIpConfAcceptDefRte OBJECT-TYPE
        SYNTAX        TruthValue
        MAX-ACCESS    read-write
        STATUS        current
        DESCRIPTION   "Used to indicate whether this interface should
		      accept a RIP default route."
        ::= { rcIpConfEntry 3 }

rcIpConfRowStatus OBJECT-TYPE
        SYNTAX        RowStatus
        MAX-ACCESS    read-write
        STATUS        current
        DESCRIPTION   "Row status for this entry."
        ::= { rcIpConfEntry 4 }

rcIpConfRipEnable OBJECT-TYPE
        SYNTAX        TruthValue
        MAX-ACCESS    read-write
        STATUS        current
        DESCRIPTION   "Enable or disable RIP routing on the specified
                      interface."
        ::= { rcIpConfEntry 5 }
 
rcIpConfOspfEnable OBJECT-TYPE
        SYNTAX        TruthValue
        MAX-ACCESS    read-write
        STATUS        current
        DESCRIPTION   "Enable or disable OSPF routing on the specified
                      interface."
        ::= { rcIpConfEntry 6 }
 
rcIpConfIgmpEnable OBJECT-TYPE
        SYNTAX        TruthValue
        MAX-ACCESS    read-write
        STATUS        current
        DESCRIPTION   "Enable or disable IGMP on the specified
                      interface."
        ::= { rcIpConfEntry 7 }
 
rcIpConfAddrAssigned OBJECT-TYPE
        SYNTAX        TruthValue
        MAX-ACCESS    read-only
        STATUS        current
        DESCRIPTION   "Indicate whether IpAddress has been assigned 
                      for this interface."
        ::= { rcIpConfEntry 8 }

rcIpConfDhcpEnable OBJECT-TYPE
        SYNTAX        TruthValue
        MAX-ACCESS    read-write
        STATUS        current
        DESCRIPTION   "Enable or disable DHCP on the specified
                      interface."
        ::= { rcIpConfEntry 9 }

rcIpConfTriggeredUpdateEnable OBJECT-TYPE
        SYNTAX        TruthValue
        MAX-ACCESS    read-write
        STATUS        current
        DESCRIPTION   "Used to indicate whether the RIP triggered update
		      feature should be enabled on this interface." 
        ::= { rcIpConfEntry 10 }
 
rcIpConfAutoAggrerateEnable OBJECT-TYPE
        SYNTAX        TruthValue
        MAX-ACCESS    read-write
        STATUS        current
        DESCRIPTION   "Used to indicate whether the auto aggregation 
		      feature should be enabled on this interface." 
        ::= { rcIpConfEntry 11 }
 
rcIpConfGenerateDefaultRoute OBJECT-TYPE
        SYNTAX        TruthValue
        MAX-ACCESS    read-write
        STATUS        current
        DESCRIPTION   "Used to indicate whether to generate a default
		      RIP route	on this interface." 
        ::= { rcIpConfEntry 12 }

rcIpConfAdvertiseWhenDown OBJECT-TYPE
        SYNTAX        TruthValue
        MAX-ACCESS    read-write
        STATUS        current
        DESCRIPTION   "The value is used indicated whether vlan state change
                       should be notified to layer 3 or not, provided the vlan
                       is configured as routable interface. Also used for
                       single routable ports, in that case the criteria for
                       state is PortOperStatus.
                       Vlan is considered as UP if atleast one member of the
                       port based vlan has link up, or atleast one port member
                       of the policy based has an entry in the MGID or atleast
                       one static member of the policy based vlan has link up.
                       Otherwise, vlan is considered as DOWN.
                       If the value is 'true' then the interface state change 
                       will not be notified to layer 3. (i.e., it always stays 
                       up). If the value is 'false' then the vlan state change 
                       will be notified to layer 3 so that IP related status 
                       reflects routable interface state."
        DEFVAL        { false }
        ::= { rcIpConfEntry 13 }
 
rcIpConfDirectBroadcastEnable OBJECT-TYPE
        SYNTAX        TruthValue
        MAX-ACCESS    read-write
        STATUS        current
        DESCRIPTION   "Used to indicate whether this interface should
                      forward direct broadcast traffic"
        DEFVAL        { false }
        ::= { rcIpConfEntry 14 }

rcIpConfRipInPolicy OBJECT-TYPE
        SYNTAX        DisplayString (SIZE(0..64))
        MAX-ACCESS    read-write
        STATUS        current
        DESCRIPTION   "Used to indicate whether this interface should
            advertize a RIP default route."
        ::= { rcIpConfEntry 15 }

rcIpConfRipOutPolicy OBJECT-TYPE
        SYNTAX        DisplayString (SIZE(0..64))
        MAX-ACCESS    read-write
        STATUS        current
        DESCRIPTION   "Used to indicate whether this interface should
            accept a RIP default route."
        ::= { rcIpConfEntry 16 }
 
rcIpConfOspfIfType OBJECT-TYPE
        SYNTAX   INTEGER    {
                    broadcast (1),
                    nbma (2),
                    pointToPoint (3),
                    pointToMultipoint (5),
                    passive (99)
                  }
        MAX-ACCESS    read-write
        STATUS        current
        DESCRIPTION   "OSPF Interface Type."
        ::= { rcIpConfEntry 17 } 

rcIpConfRipCost OBJECT-TYPE
        SYNTAX        INTEGER (1..15)
        MAX-ACCESS    read-write
        STATUS        current
        DESCRIPTION   "Used to indicate the rip cost for this interface."
        DEFVAL        { 1 }
        ::= { rcIpConfEntry 18 }

rcIpConfRipHolddown OBJECT-TYPE
        SYNTAX        INTEGER (0..360)
        MAX-ACCESS    read-write
        STATUS        current
        DESCRIPTION   "Used to indicate the rip holddown timer for this
                       interface"
        ::= { rcIpConfEntry 19 }

rcIpConfRipTimeout OBJECT-TYPE
        SYNTAX        INTEGER (15..259200)
        MAX-ACCESS    read-write
        STATUS        current
        DESCRIPTION   "Used to indicate the rip timeout interval for this
                       interface"
        ::= { rcIpConfEntry 20 }        
 
rcIpConfRsmltEnable OBJECT-TYPE
        SYNTAX        TruthValue
        MAX-ACCESS    read-write
        STATUS        current
        DESCRIPTION   "Used to enable Route Smlt feature."
        DEFVAL        { false }
        ::= { rcIpConfEntry 21 }

rcIpConfReversePathCheckEnable OBJECT-TYPE
        SYNTAX        TruthValue
        MAX-ACCESS    read-write
        STATUS        current
        DESCRIPTION   "Used to indicate whether this interface should
                      perform Reverse Path Check"
        DEFVAL        { false }
        ::= { rcIpConfEntry 22 }

rcIpConfReversePathCheckMode OBJECT-TYPE
        SYNTAX   INTEGER    {           
                    exist-only (1),     
                    strict (2)     
                  }                
        MAX-ACCESS    read-write
        STATUS        current   
        DESCRIPTION   "Reverse Path Checking mode."
        DEFVAL        { exist-only }
        ::= { rcIpConfEntry 23 }

rcIpConfIpVpnLiteEnable OBJECT-TYPE
        SYNTAX        TruthValue
        MAX-ACCESS    read-create
        STATUS        current
        DESCRIPTION   "Enable or disable ipvpn-lite capability on the specified
                      circuitless ip interface."
        ::= { rcIpConfEntry 26 }

-- Ospf Configuration Table
 
rcIpConfOspfTable OBJECT-TYPE
        SYNTAX        SEQUENCE OF RcIpConfOspfEntry
        MAX-ACCESS    not-accessible
        STATUS        current
        DESCRIPTION   "A table used to maintain OSPF information
                      for a particular interface."
        ::= { rcIpConf 2 }
 
rcIpConfOspfEntry OBJECT-TYPE
        SYNTAX        RcIpConfOspfEntry
        MAX-ACCESS    not-accessible
        STATUS        current
        DESCRIPTION   "Entry containing OSPF information.  An entry is
                      automatically created in this table when routing 
		      is enabled for an interface -or- when an ip address 
                      is configured on an interface." 
        INDEX         { rcIpConfOspfIfIndex }
        ::= { rcIpConfOspfTable 1 }
 
RcIpConfOspfEntry ::= SEQUENCE {
                rcIpConfOspfIfIndex           InterfaceIndexOrZero,
                rcIpConfOspfRtrPriority       INTEGER,
                rcIpConfOspfMetric            INTEGER,
                rcIpConfOspfAuthKey           DisplayString (SIZE(0..8)),
                rcIpConfOspfRowStatus         RowStatus,
                rcIpConfOspfHelloInterval     INTEGER,
                rcIpConfOspfRtrDeadInterval   INTEGER,
                rcIpConfOspfIfAreaId          IpAddress,
                rcIpConfOspfAuthType          INTEGER,
                rcIpConfOspfPollInterval      INTEGER,
                rcIpConfOspfIfMtuIgnore       INTEGER
        }
 
rcIpConfOspfIfIndex OBJECT-TYPE
        SYNTAX        InterfaceIndexOrZero (0..6142)
        MAX-ACCESS    read-only
        STATUS        current
        DESCRIPTION   "An unique value to identify a physical interface 
 		      or a logical interface (VLAN)."
        ::= { rcIpConfOspfEntry 1 }

rcIpConfOspfRtrPriority OBJECT-TYPE
        SYNTAX        INTEGER (0..'FF'h)
        MAX-ACCESS    read-write
        STATUS        current
        DESCRIPTION   "The priority of this interface.  Used in multi-
                      access networks, this field is used in the
                      designated router election algorithm.  The value 0
                      signifies that the router is not eligible to become
                      the designated router on this particular network.
                      In the event of a tie in this value, routers will
                      use their router id as a tie breaker."
        DEFVAL        { 1 }
        ::= { rcIpConfOspfEntry 2 }
 
rcIpConfOspfMetric OBJECT-TYPE
        SYNTAX        INTEGER (0..'FFFF'h)
        MAX-ACCESS    read-write
        STATUS        current
        DESCRIPTION   "The metric for this type of service (TOS) on this
                      interface.  The default value of the TOS 0 Metric
                      is (10^9 / ifSpeed). The value FFFF means 'no route 
		      via this TOS'. A value of 0 means the interface speed 
                      (rcIpConfOspfDefaultMetric) will be used as metric 
		      value, when the state of the interface is up." 
        DEFVAL        { 0 }
        ::= { rcIpConfOspfEntry 3 }
 
rcIpConfOspfAuthKey OBJECT-TYPE
        SYNTAX        DisplayString (SIZE(0..8))
        MAX-ACCESS    read-write
        STATUS        current
        DESCRIPTION   "The Authentication Key.  If the Area's
                      Authorization Type is simplePassword, and the key
                      length is shorter than 8 octets, the agent will
                      left adjust and zero fill to 8 octets.

                      Note that unauthenticated  interfaces  need  no
                      authentication key, and simple password authen-
                      tication cannot use a key of more  than  8  oc-
                      tets.  Larger keys are useful only with authen-
                      tication mechanisms not specified in this docu-
                      ment.

                      When read, ospfIfAuthKey always returns an Octet
                      String of length zero."
        REFERENCE     "OSPF Version 2, Section 9 The Interface Data
                      Structure"
        ::= { rcIpConfOspfEntry 4 }

rcIpConfOspfRowStatus OBJECT-TYPE
        SYNTAX        RowStatus
        MAX-ACCESS    read-write
        STATUS        current
        DESCRIPTION   "Row status for this entry."
        ::= { rcIpConfOspfEntry 5 }

rcIpConfOspfHelloInterval OBJECT-TYPE
        SYNTAX        INTEGER (1..'FFFF'h)
        MAX-ACCESS    read-write
        STATUS        current
        DESCRIPTION   "The length of time, in seconds, between the 
                      Hello packets that the router sends on the 
                      interface. This value must be the same for all
                      routers attached to a common network."
        DEFVAL        { 10 }
        ::= { rcIpConfOspfEntry 6 }

rcIpConfOspfRtrDeadInterval OBJECT-TYPE
        SYNTAX        INTEGER (0..'7FFFFFFF'h)
        MAX-ACCESS    read-write
        STATUS        current
        DESCRIPTION   "The number of seconds that a router's Hello 
                      packets have not been seen before it's 
                      neighbors declare the router down. This should
                      be some multiple of the Hello interval. This 
                      value must be the same for all routers attached
                      to a common network."
        DEFVAL        { 40 }
        ::= { rcIpConfOspfEntry 7 }

rcIpConfOspfIfAreaId OBJECT-TYPE
         SYNTAX        IpAddress
         MAX-ACCESS    read-write
         STATUS        current
         DESCRIPTION   "A 32-bit integer uniquely identifying the area to
                       which the interface connects.  Area ID 0.0.0.0 is used
                       for the OSPF backbone."
         DEFVAL   { '00000000'H }    -- 0.0.0.0
         ::= { rcIpConfOspfEntry 8 }

rcIpConfOspfAuthType OBJECT-TYPE
         SYNTAX        INTEGER {
                           none (0),
                           simplePassword (1),
                           md5 (2)
                       }
        MAX-ACCESS     read-write
        STATUS         current
        DESCRIPTION    "The authentication type specified for  an  interface.   
                       Additional  authentication types may be assigned locally."
        REFERENCE      "OSPF Version 2, Appendix E Authentication"
        DEFVAL { 0 }        -- no authentication, by default
        ::= { rcIpConfOspfEntry 9 }

rcIpConfOspfPollInterval OBJECT-TYPE
        SYNTAX        INTEGER  (0..2147483647)
        MAX-ACCESS    read-write
        STATUS        current
        DESCRIPTION   "OSPF NBMA Interface Poll Interval."
        ::= { rcIpConfOspfEntry 10 }

rcIpConfOspfIfMtuIgnore OBJECT-TYPE
        SYNTAX       INTEGER {
                        enable(1),
                        disable(2)
                     }
        MAX-ACCESS   read-write
        STATUS       current
        DESCRIPTION
                     "Mtu-ignore flag is for ignoring the mtu checking in 
                     ospf bdb"
        DEFVAL       { disable }
        ::= { rcIpConfOspfEntry 11 }
 
-- Ospf Cost Grp

rcIpConfOspfDefaultMetric   OBJECT IDENTIFIER       ::= { rcIpConf 3 }
 
rcIpConfOspfDefaultMetric10MegPort OBJECT-TYPE
        SYNTAX        INTEGER (1..'FFFF'h)
        MAX-ACCESS    read-write
        STATUS        current
        DESCRIPTION   "Used to indicate the cost associated with
                      10Meg Interface(Port)."
        ::= { rcIpConfOspfDefaultMetric 1 }
 
rcIpConfOspfDefaultMetric100MegPort OBJECT-TYPE
        SYNTAX        INTEGER (1..'FFFF'h)
        MAX-ACCESS    read-write
        STATUS        current
        DESCRIPTION   "Used to indicate the cost associated with
                      100Meg Interface(Port)."
        ::= { rcIpConfOspfDefaultMetric 2 }
 
rcIpConfOspfDefaultMetric1000MegPort OBJECT-TYPE
        SYNTAX        INTEGER (1..'FFFF'h)
        MAX-ACCESS    read-write
        STATUS        current
        DESCRIPTION   "Used to indicate the cost associated with
                      1000Meg Interface(Port)."
        ::= { rcIpConfOspfDefaultMetric 3 }

rcIpConfOspfDefaultMetric10000MegPort OBJECT-TYPE
        SYNTAX        INTEGER (1..'FFFF'h)
        MAX-ACCESS    read-write
        STATUS        current
        DESCRIPTION   "Used to indicate the cost associated with
                      10000Meg Interface(Port)."
        ::= { rcIpConfOspfDefaultMetric 4 }

rcIpConfOspf   OBJECT IDENTIFIER       ::= { rcIpConf 4 }

 
rcIpConfOspfTrapEnable  OBJECT-TYPE
        SYNTAX        TruthValue
        MAX-ACCESS    read-write
        STATUS        current
        DESCRIPTION   "Used to indicate whether Ospf Traps should be sent."
        ::= { rcIpConfOspf 1 }

rcIpConfOspfAutoVirtLinkEnable  OBJECT-TYPE
        SYNTAX        TruthValue
        MAX-ACCESS    read-write
        STATUS        current
        DESCRIPTION   "Used to indicate whether auto virtual link 
                      creation is enabled or not. If set to true
                      OSPF will create virtual links between 
                      ABRs whether it is needed or not, but adjacency
                      will established only when one of the ABR 
                      losses connection to backbone area. If set to
                      false then it is user resposibity to create
                      virtual link whenever needed."
	DEFVAL	      { false }
        ::= { rcIpConfOspf 2 }

rcIpConfOspfSpfHoldDownTime OBJECT-TYPE
         SYNTAX   INTEGER (3..60)
         MAX-ACCESS   read-write
         STATUS   current
         DESCRIPTION   "The SPF Hold Down Timer value. The SPF will run
                        at most once per hold down timer value."
         DEFVAL  { 10 }
         ::= { rcIpConfOspf 3 }

rcIpConfOspfAction OBJECT-TYPE
        SYNTAX        INTEGER {
                           none(0),
                           runSpf(1)
                       }
        MAX-ACCESS    read-write
        STATUS        current
        DESCRIPTION   ""
        ::= { rcIpConfOspf 4 }

rcIpConfOspfRfc1583Compatibility OBJECT-TYPE
        SYNTAX        TruthValue
        MAX-ACCESS    read-write
        STATUS        current
        DESCRIPTION   "Controls the preference rules used when choosing
                       among multiple AS-External-LSAs advertising the
                       same destination. When this is enabled, the
                       preference rule will be same as specified by
                       RFC1583. When disabled, the new preference rule
                       as described in RFC2328 will  be applicable, which
                       potentially prevents the routing loops when
                       AS-External-LSAs for the same destination have
                       been originated from different areas."
        DEFVAL        { false }
        ::= { rcIpConfOspf 5 }

rcIpConfGlobal   OBJECT IDENTIFIER       ::= { rcIpConf 6 }

rcIpConfGlobalRipHoldDownTime OBJECT-TYPE
        SYNTAX	      INTEGER (0..360)
        MAX-ACCESS    read-write
        STATUS        current
        DESCRIPTION   "Used to set the system-wide RIP hold down time
		      in seconds."
        DEFVAL        { 120 }
        ::= { rcIpConfGlobal 1 }

rcIpConfGlobalIcmpNetUnreach OBJECT-TYPE
        SYNTAX        TruthValue
        MAX-ACCESS    read-write
        STATUS        current
        DESCRIPTION   "Used to set the icmp net unreach feature
                       enable/disable."
        DEFVAL        { false }
        ::= { rcIpConfGlobal 2 }

rcIpConfGlobalEcmpEnable OBJECT-TYPE
        SYNTAX        TruthValue
        MAX-ACCESS    read-write
        STATUS        current
        DESCRIPTION   "Used to set the ecmp enable/disable."
        DEFVAL        { false }
        ::= { rcIpConfGlobal 3 }

rcIpConfGlobalEcmpMaxPath OBJECT-TYPE
        SYNTAX        INTEGER(1..8)
        MAX-ACCESS    read-write
        STATUS        current
        DESCRIPTION   "Used to globally configure maximum ECMP paths number."
        DEFVAL        { 1 }
        ::= { rcIpConfGlobal 4 }

rcIpConfGlobalAlternativeEnable OBJECT-TYPE
        SYNTAX        TruthValue
        MAX-ACCESS    read-write
        STATUS        current
        DESCRIPTION   "Used to globally configure alternative enable."
        DEFVAL        { true }
        ::= { rcIpConfGlobal 5 }

rcIpConfGlobalRouteDiscoveryEnable OBJECT-TYPE
     SYNTAX       TruthValue
     MAX-ACCESS   read-write
     STATUS       current
     DESCRIPTION  "Enable/disable ICMP Route Discovery  feature"
     DEFVAL       { true }
     ::= { rcIpConfGlobal 6 }

rcIpConfGlobalRipTimeOutInterval OBJECT-TYPE
     SYNTAX       INTEGER (15..259200)
     MAX-ACCESS   read-write
     STATUS       current
     DESCRIPTION  "Rip TimeOut Interval in seconds"
     DEFVAL       { 180 }
     ::= { rcIpConfGlobal 8 }

rcIpConfGlobalRipDefImportMetric OBJECT-TYPE
     SYNTAX       INTEGER (0..15)
     MAX-ACCESS   read-write
     STATUS       current
     DESCRIPTION  "Rip def import metric"
     DEFVAL       { 8 }
     ::= { rcIpConfGlobal 9 }

rcIpConfGlobalEcmp1PathList OBJECT-TYPE
     SYNTAX       DisplayString
     MAX-ACCESS   read-write
     STATUS       current
     DESCRIPTION  "Routes to networks specified in this prefix-list
                   can have upto 1 ECMP path, irrespective of
                   ecmp-max-path configuration"
     ::= { rcIpConfGlobal 10 }

rcIpConfGlobalEcmp2PathList OBJECT-TYPE
     SYNTAX       DisplayString
     MAX-ACCESS   read-write
     STATUS       current
     DESCRIPTION  "Routes to networks specified in this prefix-list
                   can have upto 2 ECMP path, irrespective of
                   ecmp-max-path configuration."
     ::= { rcIpConfGlobal 11 }

rcIpConfGlobalEcmp3PathList OBJECT-TYPE
     SYNTAX       DisplayString
     MAX-ACCESS   read-write
     STATUS       current
     DESCRIPTION  "Routes to networks specified in this prefix-list
                   can have upto 3 ECMP path, irrespective of
                   ecmp-max-path configuration."
     ::= { rcIpConfGlobal 12 }

rcIpConfGlobalEcmp4PathList OBJECT-TYPE
     SYNTAX       DisplayString
     MAX-ACCESS   read-write
     STATUS       current
     DESCRIPTION  "Routes to networks specified in this prefix-list
                   can have upto 4 ECMP path, irrespective of
                   ecmp-max-path configuration."
     ::= { rcIpConfGlobal 13 }

rcIpConfGlobalEcmpPathListApply OBJECT-TYPE
     SYNTAX       TruthValue
     MAX-ACCESS   read-write
     STATUS       current
     DESCRIPTION  "This is to apply any changes in ECMP path list
                   configuration or in the prefix-lists configured to
                   be used as path list"
     ::= { rcIpConfGlobal 14 }

rcIpConfGlobalIcmpRedirectMsg OBJECT-TYPE
     SYNTAX       TruthValue
     MAX-ACCESS   read-write
     STATUS       current
     DESCRIPTION  ""
     ::= { rcIpConfGlobal 15 }

rcIpConfGlobalArpThreshold OBJECT-TYPE
     SYNTAX       INTEGER (50..1000)
     MAX-ACCESS   read-write
     STATUS       current
     DESCRIPTION  "Defines the maximum number of outstanding arp request
                   a switch can generate."
     DEFVAL       { 500 }
     ::= { rcIpConfGlobal 17 }

rcIpConfGlobalAllowMoreSpecificNonLocalRouteEnable OBJECT-TYPE
     SYNTAX       TruthValue
     MAX-ACCESS   read-write
     STATUS       current
     DESCRIPTION  "Used to determine whether more specific non local routes
                   will go into the routing table."
    DEFVAL        { false }
     ::= { rcIpConfGlobal 18 }

rcIpConfGlobalUdpCheckSumEnable OBJECT-TYPE
     SYNTAX       TruthValue
     MAX-ACCESS   read-write
     STATUS       current
     DESCRIPTION  "Enable/disable UDP checksum calculation"
     DEFVAL       { true }
     ::= { rcIpConfGlobal 19 }

rcIpConfGlobalSuperNetEnable OBJECT-TYPE
     SYNTAX       TruthValue
     MAX-ACCESS   read-write
     STATUS       current
     DESCRIPTION  "Used to globally enable Supernetting/ CIDR 
                   routing for IP"
     DEFVAL       { false }
     ::= { rcIpConfGlobal 20 }

rcIpConfGlobalEcmp5PathList OBJECT-TYPE
     SYNTAX       DisplayString
     MAX-ACCESS   read-write
     STATUS       current
     DESCRIPTION  "Routes to networks specified in this prefix-list
                   can have upto 5 ECMP path, irrespective of
                   ecmp-max-path configuration."
     ::= { rcIpConfGlobal 21 }

rcIpConfGlobalEcmp6PathList OBJECT-TYPE
     SYNTAX       DisplayString
     MAX-ACCESS   read-write
     STATUS       current
     DESCRIPTION  "Routes to networks specified in this prefix-list
                   can have upto 6 ECMP path, irrespective of
                   ecmp-max-path configuration."
     ::= { rcIpConfGlobal 22 }

rcIpConfGlobalEcmp7PathList OBJECT-TYPE
     SYNTAX       DisplayString
     MAX-ACCESS   read-write
     STATUS       current
     DESCRIPTION  "Routes to networks specified in this prefix-list
                   can have upto 7 ECMP path, irrespective of
                   ecmp-max-path configuration."
     ::= { rcIpConfGlobal 23 }

rcIpConfGlobalEcmp8PathList OBJECT-TYPE
     SYNTAX       DisplayString
     MAX-ACCESS   read-write
     STATUS       current
     DESCRIPTION  "Routes to networks specified in this prefix-list
                   can have upto 8  ECMP path, irrespective of
                   ecmp-max-path configuration."
     ::= { rcIpConfGlobal 24 }

rcIpConfGlobalArpMcastMacFlooding OBJECT-TYPE
     SYNTAX       TruthValue
     MAX-ACCESS   read-write
     STATUS       current
     DESCRIPTION  "Enable/disable Ip Arp Multicast Mac Flooding feature."
     DEFVAL       { false }
     ::= { rcIpConfGlobal 26 }


-- Ospf Area Table
 
rcIpConfOspfAreaTable OBJECT-TYPE
        SYNTAX        SEQUENCE OF RcIpConfOspfAreaEntry
        MAX-ACCESS    not-accessible
        STATUS        current
        DESCRIPTION   "A table used to maintain OSPF information
                      for a particular Area."
        ::= { rcIpConf 7 }
 
rcIpConfOspfAreaEntry OBJECT-TYPE
        SYNTAX        RcIpConfOspfAreaEntry
        MAX-ACCESS    not-accessible
        STATUS        current
        DESCRIPTION   "Entry containing OSPF Area configuration 
                      information.  An entry is automatically created 
                      in this table when an area is configured through 
                      ospfAreaTable in (rfc1253rcc.mib)."
        INDEX         { rcIpConfOspfAreaId }
        ::= { rcIpConfOspfAreaTable 1 }
 
RcIpConfOspfAreaEntry ::= SEQUENCE {
                rcIpConfOspfAreaId              IpAddress,
                rcIpConfOspfAreaImportSummary   TruthValue,
                rcIpConfOspfAreaActiveIfCount   Integer32
        }
 
rcIpConfOspfAreaId OBJECT-TYPE
        SYNTAX        IpAddress
        MAX-ACCESS    read-only
        STATUS        current
        DESCRIPTION   "An unique value to identify an area. Area ID
 		      0.0.0.0 is used for the OSPF backbone."
        ::= { rcIpConfOspfAreaEntry 1 }

rcIpConfOspfAreaImportSummary OBJECT-TYPE
        SYNTAX        TruthValue
        MAX-ACCESS    read-write
        STATUS        current
        DESCRIPTION   "The area's support for importing Summary 
                      advertisements into a stub area. This field
                      should be used only if ospfImportASExtern is
                      set to FALSE"
        DEFVAL        { true }
        ::= { rcIpConfOspfAreaEntry 2 }
 
rcIpConfOspfAreaActiveIfCount OBJECT-TYPE
        SYNTAX        Integer32 
        MAX-ACCESS    read-only
        STATUS        current
        DESCRIPTION   "This variable displays the number of active
                      interfaces configured in this area. An area
                      cannot be deleted if this value is > 0."
        ::= { rcIpConfOspfAreaEntry 3 }

 
-- Ospf Area Aggregate Table

rcIpConfOspfAreaAggregateTable OBJECT-TYPE
        SYNTAX        SEQUENCE OF RcIpConfOspfAreaAggregateEntry
        MAX-ACCESS    not-accessible
        STATUS        current
        DESCRIPTION   "A table used to maintain OSPF summary route
                        metric parameter for a particular Area range.  "
       ::= { rcIpConf 10 }

rcIpConfOspfAreaAggregateEntry OBJECT-TYPE
        SYNTAX        RcIpConfOspfAreaAggregateEntry
        MAX-ACCESS    not-accessible
        STATUS        current
        DESCRIPTION   "Entry containing OSPF summary route metric
                        parameter for a particular Area range.
                        An entry is automatically created in this
                        table when an area range is configured through
                        ospfAreaAggregateTable in rfc1850rcc.mib"
        INDEX         { rcIpConfOspfAreaAggregateAreaID,
                        rcIpConfOspfAreaAggregateLsdbType,
                        rcIpConfOspfAreaAggregateNet,
                        rcIpConfOspfAreaAggregateMask }
        ::= { rcIpConfOspfAreaAggregateTable 1 }

RcIpConfOspfAreaAggregateEntry ::= SEQUENCE {
        rcIpConfOspfAreaAggregateAreaID
            IpAddress,
        rcIpConfOspfAreaAggregateLsdbType
            INTEGER,
        rcIpConfOspfAreaAggregateNet
            IpAddress,
        rcIpConfOspfAreaAggregateMask
            IpAddress,
        rcIpConfOspfAreaAggregateAdvertiseMetric
            INTEGER(0..65535),
        rcIpConfOspfAreaAggregateEffect
            INTEGER
        }

rcIpConfOspfAreaAggregateAreaID OBJECT-TYPE
        SYNTAX   IpAddress
        MAX-ACCESS   read-only
        STATUS   current
        DESCRIPTION
           "The Area the Address Aggregate is to be  found
           within."
        REFERENCE
          "OSPF Version 2, Appendix C.2 Area parameters"
        ::= { rcIpConfOspfAreaAggregateEntry 1 }


rcIpConfOspfAreaAggregateLsdbType OBJECT-TYPE
        SYNTAX   INTEGER    {
                    summaryLink (3),
                    nssaExternalLink (7)
                  }
        MAX-ACCESS   read-only
        STATUS   current
        DESCRIPTION
           "The type of the Address Aggregate.  This field
           specifies  the  Lsdb type that this Address Ag-
           gregate applies to."
        REFERENCE
          "OSPF Version 2, Appendix A.4.1 The  Link  State
          Advertisement header"
        ::= { rcIpConfOspfAreaAggregateEntry 2 }


rcIpConfOspfAreaAggregateNet OBJECT-TYPE
        SYNTAX   IpAddress
        MAX-ACCESS   read-only
        STATUS   current
        DESCRIPTION
           "The IP Address of the Net or Subnet  indicated
           by the range."
        REFERENCE
          "OSPF Version 2, Appendix C.2 Area parameters"
        ::= { rcIpConfOspfAreaAggregateEntry 3 }

rcIpConfOspfAreaAggregateMask OBJECT-TYPE
        SYNTAX   IpAddress
        MAX-ACCESS   read-only
        STATUS   current
        DESCRIPTION
           "The Subnet Mask that pertains to  the  Net  or
           Subnet."
        REFERENCE
          "OSPF Version 2, Appendix C.2 Area parameters"
        ::= { rcIpConfOspfAreaAggregateEntry 4 }

rcIpConfOspfAreaAggregateAdvertiseMetric OBJECT-TYPE
        SYNTAX        INTEGER(0..65535)
        MAX-ACCESS    read-write
        STATUS        current
        DESCRIPTION   "Used to specify a metric for a Summary LSA (type
                        3) generated by OSPF through an area range.
                        If this metric is set to 0, OSPF uses the cost
                        to the farthest point in the networks being
                        summarized as the metric."
        ::= { rcIpConfOspfAreaAggregateEntry 5 }

rcIpConfOspfAreaAggregateEffect OBJECT-TYPE
        SYNTAX   INTEGER    {
                    advertiseMatching (1),
                    doNotAdvertiseMatching (2),
                    advertiseDoNotAggregate (3)
                  }
        MAX-ACCESS   read-write
        STATUS       current
        DESCRIPTION
                     "Subnets subsumed by ranges either trigger  the
                     advertisement  of  the indicated aggregate (ad-
                     vertiseMatching), or result in the subnet's not
                     being advertised at all outside the area."
       DEFVAL        { advertiseMatching }
       ::= { rcIpConfOspfAreaAggregateEntry 6 }

-- IP Route Smlt Table

rcIpConfRsmltTable OBJECT-TYPE
        SYNTAX        SEQUENCE OF RcIpConfRsmltEntry
        MAX-ACCESS    not-accessible
        STATUS        current
        DESCRIPTION   "A table used to maintain OSPF summary route
                        metric parameter for a particular Area range.  "
       ::= { rcIpConf 11 }

rcIpConfRsmltEntry OBJECT-TYPE
        SYNTAX        RcIpConfRsmltEntry
        MAX-ACCESS    not-accessible
        STATUS        current
        DESCRIPTION   "Entry containing OSPF summary route metric
                        parameter for a particular Area range.
                        An entry is automatically created in this
                        table when an area range is configured through
                        ospfAreaAggregateTable in rfc1850rcc.mib"
        INDEX         { rcIpConfRsmltIfIndex }
        ::= { rcIpConfRsmltTable 1 }

RcIpConfRsmltEntry ::= SEQUENCE {
        rcIpConfRsmltIfIndex
            InterfaceIndex,
        rcIpConfRsmltHoldDownTimer
            INTEGER,
        rcIpConfRsmltHoldUpTimer
            INTEGER,
        rcIpConfRsmltRowStatus
            RowStatus
        }

rcIpConfRsmltIfIndex OBJECT-TYPE
        SYNTAX       InterfaceIndex
        MAX-ACCESS   read-only
        STATUS       current
        DESCRIPTION  "Interface Index, this is an index  of the table."
        ::= { rcIpConfRsmltEntry 1 }

rcIpConfRsmltHoldDownTimer OBJECT-TYPE
        SYNTAX       INTEGER (0..3600)
        MAX-ACCESS   read-write
        STATUS       current
        DESCRIPTION  "Timer value, the range of value is from 0 to 3600."
        ::= { rcIpConfRsmltEntry 2 }

rcIpConfRsmltHoldUpTimer OBJECT-TYPE
        SYNTAX       INTEGER (0..3600 | 9999)
        MAX-ACCESS   read-write
        STATUS       current
        DESCRIPTION  "The range of value 0 to 3600 or 9999. 9999 means
                      infinity."
        ::= { rcIpConfRsmltEntry 3 }

rcIpConfRsmltRowStatus OBJECT-TYPE
        SYNTAX       RowStatus
        MAX-ACCESS   read-write
        STATUS       current
        DESCRIPTION  "Row Status."
        ::= { rcIpConfRsmltEntry 4 }

-- IP Address Table

rcIpAddrTable OBJECT-TYPE
        SYNTAX        SEQUENCE OF RcIpAddrEntry
        MAX-ACCESS    not-accessible
        STATUS        current
        DESCRIPTION   "The table of addressing information relevant to
                      this entity's IP addresses.

                      This table is identical to the ipAddrTable in 
                      MIB2 except the columns rcIpAdEntIfIndex and 
                      rcIpAdEntAddr are reversed.  Also, the table 
                      is indexed by both these variables."
	::= { rcIp 2 }

rcIpAddrEntry OBJECT-TYPE
	SYNTAX        RcIpAddrEntry
	MAX-ACCESS 	  not-accessible
	STATUS 	      current
	DESCRIPTION   "The addressing information for one of this
                      entity's IP addresses."
	INDEX         { rcIpAdEntIfIndex, rcIpAdEntAddr }
	::= { rcIpAddrTable 1 }

RcIpAddrEntry ::=
    	SEQUENCE {
        	rcIpAdEntIfIndex InterfaceIndex,
	         rcIpAdEntAddr IpAddress,
	         rcIpAdEntNetMask IpAddress,
	         rcIpAdEntBcastAddrFormat INTEGER,
	         rcIpAdEntReasmMaxSize INTEGER (0..65535),
          rcIpAdEntRowStatus RowStatus,
          rcIpAdEntVlanId INTEGER,
          rcIpAdEntBrouterPort TruthValue,
          rcIpAdEntMacOffset INTEGER,
          rcIpAdEntIfType INTEGER,
	  rcIpAdEntVrfId VrfIdentifier
    	}

rcIpAdEntIfIndex OBJECT-TYPE
   	SYNTAX        InterfaceIndex
  	MAX-ACCESS    read-only
  	STATUS        current
	DESCRIPTION   "The index value which uniquely identifies the
                      interface to which this entry is applicable.  The
                      interface identified by a particular value of this
                      index is the same interface as identified by the
                      same value of ifIndex."
	::= { rcIpAddrEntry 1 }

rcIpAdEntAddr OBJECT-TYPE
	SYNTAX        IpAddress
        MAX-ACCESS    read-only
        STATUS        current
        DESCRIPTION   "The IP address to which this entry's addressing
                      information pertains."
	::= { rcIpAddrEntry 2 }

rcIpAdEntNetMask OBJECT-TYPE
        SYNTAX        IpAddress
        MAX-ACCESS    read-write
        STATUS        current
        DESCRIPTION   "The subnet mask associated with the IP address of
                      this entry.  The value of the mask is an IP
                      address with all the network bits set to 1 and all
                      the hosts bits set to 0."
	::= { rcIpAddrEntry 3 }

rcIpAdEntBcastAddrFormat OBJECT-TYPE
        SYNTAX        INTEGER {
			 zeros(0),	-- use zeros
			 ones(1)	-- use ones
		      }
        MAX-ACCESS    read-only
        STATUS        current
        DESCRIPTION   "The IP broadcast address format used on this 
                      interface."
	::= { rcIpAddrEntry 4 }

rcIpAdEntReasmMaxSize OBJECT-TYPE
        SYNTAX        INTEGER (0..65535)
        MAX-ACCESS    read-only
        STATUS        current
        DESCRIPTION   "The size of the largest IP datagram which this
                      entity can re-assemble from incoming IP fragmented
                      datagrams received on this interface."
        ::= { rcIpAddrEntry 5 }

rcIpAdEntRowStatus OBJECT-TYPE
        SYNTAX        RowStatus
        MAX-ACCESS    read-write
        STATUS        current
        DESCRIPTION   "Used to create/delete entries"
        ::= { rcIpAddrEntry 6 }

rcIpAdEntVlanId OBJECT-TYPE
        SYNTAX        INTEGER (0..4096)
        MAX-ACCESS    read-write
        STATUS        current
        DESCRIPTION   "A value that uniquely identifies the Virtual LAN
                      associated with this entry. This value corresponds
                      to the lower 12 bits in the IEEE 802.1Q VLAN Tag."
        ::= { rcIpAddrEntry 7 }

rcIpAdEntBrouterPort OBJECT-TYPE
        SYNTAX        TruthValue
        MAX-ACCESS    read-only
        STATUS        current
        DESCRIPTION   "Used to indicate whether this entry correponds
		      to a brouter port (as oppose to a routable VLAN).
 		      This value cannot be changed after the row is
		      created."
        ::= { rcIpAddrEntry 8 }

rcIpAdEntMacOffset OBJECT-TYPE
        SYNTAX        INTEGER (0..511)
        MAX-ACCESS    read-write
        STATUS        current
        DESCRIPTION   "Used to translate the ip address into mac address.
                       The system has 512 mac addresses of which 0-507 are reserved for
                       Boardwalk box. 508-511 is reserved for MG. One can either 
                       mention a mac offset while configuring an ip on the
                       vlan or it can be alloted by the system within the above range."
        ::= { rcIpAddrEntry 9 }

rcIpAdEntIfType   OBJECT-TYPE
     SYNTAX INTEGER {
                circuitLessIP(1),
                brouterPort(2),
                vlan(3)
            } 
     MAX-ACCESS     read-only
     STATUS         current
     DESCRIPTION    "The address entry IfType indicates the type of the 
							  interface. In the case of circuit-less-IP there is   
                     no association with any ports. In other words, it can 
                     be thought of as a virtual interface. The value 
                     'brouter port' indicates this interface is associated 
                     with a specific physical port. The value 'vlan' 
                     indicates a logical port that contains one or physical 
                     ports/MLT ports."

        ::= { rcIpAddrEntry 10 }

rcIpAdEntVrfId   OBJECT-TYPE 
     SYNTAX         VrfIdentifier
     MAX-ACCESS     read-create
     STATUS         current 
     DESCRIPTION    "The VrfId used in this table is to associate VLANs
		     or Brouter ports to a VRF after the creation of VLANs
		     or Brouter ports.
		     VRFID 0 is reserved for the Administrative VRF."

        ::= { rcIpAddrEntry 12 }

-- FlowContorl Group

rcIpFlowTable OBJECT-TYPE
        SYNTAX        SEQUENCE OF RcIpFlowEntry
        MAX-ACCESS    not-accessible
        STATUS        current
        DESCRIPTION   "IpFlow Table.  This table contain entries that
		      correspond to RSVP records in the switching
		      fabric Address Resolution table.

		      A connection that has a matching entry in this 
                      table will be processed with a higher priority 
                      than connections that do not have an entry."
        ::= { rcIp 3 }

rcIpFlowEntry OBJECT-TYPE
        SYNTAX        RcIpFlowEntry
        MAX-ACCESS    not-accessible
        STATUS        current
        DESCRIPTION   "Proprietary flow control variables."
        INDEX         { rcIpFlowSrcIpAddress, rcIpFlowSrcIpPort,
		        rcIpFlowDstIpAddress, rcIpFlowDstIpPort,
		        rcIpFlowProtocol }
        ::= { rcIpFlowTable 1 }

RcIpFlowEntry ::=
        SEQUENCE {
                rcIpFlowSrcIpAddress IpAddress,
                rcIpFlowSrcIpPort    INTEGER,
                rcIpFlowDstIpAddress IpAddress,
                rcIpFlowDstIpPort    INTEGER,
		rcIpFlowProtocol     INTEGER,
		rcIpFlowRowStatus    RowStatus
        }

rcIpFlowSrcIpAddress OBJECT-TYPE
        SYNTAX        IpAddress
        MAX-ACCESS    read-only
        STATUS        current
        DESCRIPTION   "The source IP address of an IP packet."
        ::= { rcIpFlowEntry 1 }

rcIpFlowSrcIpPort OBJECT-TYPE
        SYNTAX        INTEGER (0..65535)
        MAX-ACCESS    read-only
        STATUS        current
        DESCRIPTION   "The source port of an IP packet.  A zero value 
                      in this field is used as a wildcard value."
        DEFVAL 	      { 0 }
        ::= { rcIpFlowEntry 2 }

rcIpFlowDstIpAddress OBJECT-TYPE
        SYNTAX        IpAddress
        MAX-ACCESS    read-only
        STATUS        current
        DESCRIPTION   "The destination IP address of an IP packet."
        ::= { rcIpFlowEntry 3 }

rcIpFlowDstIpPort OBJECT-TYPE
        SYNTAX        INTEGER (0..65535)
        MAX-ACCESS    read-only
        STATUS        current
        DESCRIPTION   "The destination port of an IP packet.  A zero
                      value in this field is used as a wildcard value."
	DEFVAL	      { 0 }
        ::= { rcIpFlowEntry 4 }

rcIpFlowProtocol OBJECT-TYPE
        SYNTAX 	      INTEGER {
                         ip(4),	        -- ip
			 tcp(6),	-- tcp
			 udp(17)	-- udp
        	      }
        MAX-ACCESS    read-only
        STATUS        current
        DESCRIPTION   "The protocol type of an IP packet.  A zero value
                      in this field is used as a wildcard value."
	DEFVAL 	      { ip }
        ::= { rcIpFlowEntry 5 }

rcIpFlowRowStatus OBJECT-TYPE
        SYNTAX        RowStatus
        MAX-ACCESS    read-write
        STATUS        current
        DESCRIPTION   "Status of entry."
        ::= { rcIpFlowEntry 6 }

-- IP Route Table

rcIpRouteTable OBJECT-TYPE 
        SYNTAX          SEQUENCE OF RcIpRouteEntry
        MAX-ACCESS      not-accessible 
        STATUS          current 
        DESCRIPTION     "This entity's IP Routing table."
    ::= { rcIp 7 }

rcIpRouteEntry OBJECT-TYPE
	SYNTAX  	RcIpRouteEntry
        MAX-ACCESS  	not-accessible
        STATUS  	current
        DESCRIPTION	"A route to a particular destination."
        INDEX   { rcIpRouteDest, rcIpRouteMask, 
                  rcIpRouteNextHop, rcIpRouteAltSequence }
    ::= { rcIpRouteTable 1 }

RcIpRouteEntry ::=
	SEQUENCE {
        	rcIpRouteDest IpAddress,
                rcIpRouteMask IpAddress,
                rcIpRouteNextHop IpAddress,
                rcIpRouteMetric  Integer32,
                rcIpRouteIfIndex InterfaceIndex,
                rcIpRouteType INTEGER,
                rcIpRouteProto INTEGER,
                rcIpRouteAge Integer32,
                rcIpRouteRowStatus RowStatus,
                rcIpRoutePref INTEGER,
                rcIpRouteAltSequence Integer32,
                rcIpRoutePathType INTEGER,
                rcIpRouteSrcVrfId VrfIdentifier,
                rcIpRouteNextHopId DisplayString
              }

rcIpRouteDest OBJECT-TYPE
        SYNTAX  	IpAddress
        MAX-ACCESS  	read-only
        STATUS  	current
        DESCRIPTION 	"The destination IP address of this route.  An
                      	entry with a value of 0.0.0.0 is considered a
                      	default route.  Multiple routes to a single
                      	destination can appear in the table, but access to
                      	such multiple entries is dependent on the table-
                      	access mechanisms defined by the network
                      	management protocol in use."
    ::= { rcIpRouteEntry 1 }

rcIpRouteMask OBJECT-TYPE
        SYNTAX  	IpAddress
        MAX-ACCESS  	read-only
        STATUS  	current
        DESCRIPTION	"Indicate the mask to be logical-ANDed with the
                      	destination address before being compared to the
                      	value in the rcIpRouteDest field.  For those systems
                      	that do not support arbitrary subnet masks, an
                      	agent constructs the value of the rcIpRouteMask by
                      	determining whether the value of the correspondent
                      	rcIpRouteDest field belong to a class-A, B, or C
                      	network, and then using one of:

                           mask           network
                           255.0.0.0      class-A
                           255.255.0.0    class-B
                           255.255.255.0  class-C

                      	If the value of the rcIpRouteDest is 0.0.0.0 (a
                      	default route), then the mask value is also
                      	0.0.0.0.  It should be noted that all IP routing
                      	subsystems implicitly use this mechanism."
    ::= { rcIpRouteEntry 2 }

rcIpRouteNextHop OBJECT-TYPE
        SYNTAX  	IpAddress
        MAX-ACCESS  	read-write
        STATUS  	current
        DESCRIPTION 	"The IP address of the next hop of this route.
                      	(In the case of a route bound to an interface
                      	which is realized via a broadcast media, the value
                      	of this field is the agent's IP address on that
                      	interface)."
    ::= { rcIpRouteEntry 3 }

rcIpRouteMetric OBJECT-TYPE
        SYNTAX  	Integer32
        MAX-ACCESS  	read-write
        STATUS  	current
        DESCRIPTION 	"The primary routing metric for this route.  The
                      	semantics of this metric are determined by the
                      	routing-protocol specified in the route's
                      	rcIpRouteProto value.  If this metric is not used,
                      	its value should be set to -1."
    ::= { rcIpRouteEntry 4 }

rcIpRouteIfIndex OBJECT-TYPE
        SYNTAX  	InterfaceIndex
        MAX-ACCESS  	read-only
        STATUS  	current
        DESCRIPTION 	"The index value which uniquely identifies the
                      	local interface through which the next hop of this
                      	route should be reached.  The interface identified
                      	by a particular value of this index is the same
                      	interface as identified by the same value of
                      	ifIndex."
    ::= { rcIpRouteEntry 5 }

rcIpRouteType OBJECT-TYPE
        SYNTAX  INTEGER {
                    other(1), 
                    direct(3), 
                    indirect(4)
               }
        MAX-ACCESS  	read-only
        STATUS  	current
        DESCRIPTION 	"The type of route."
    ::= { rcIpRouteEntry 6 }

rcIpRouteProto OBJECT-TYPE
        SYNTAX  INTEGER {
                    other(1),       -- none of the following

                                    -- non-protocol information,
                                    -- e.g., manually configured
                    local(2),       -- entries

                                    -- set via a network
                    netmgmt(3),     -- management protocol

                                    -- obtained via ICMP,
                    icmp(4),        -- e.g., Redirect

                                    -- the remaining values are
                                    -- all gateway routing
                                    -- protocols
                    egp(5),
                    ggp(6),
                    hello(7),
                    rip(8),
                    is-is(9),
                    es-is(10),
                    ciscoIgrp(11),
                    bbnSpfIgp(12),
                    ospf(13),
                    bgp(14),
                    vOspf(15),       -- indicates inter-vrf routes added by OSPF
                    vBgp(16),        -- indicates inter-vrf routes added by BGP
                    vRip(17)         -- indicates inter-vrf routes added by RIP
                }
        MAX-ACCESS  	read-only
        STATUS  	current
        DESCRIPTION	"The routing mechanism via which this route was
                      	learned.  Inclusion of values for gateway routing
                      	protocols is not intended to imply that hosts
                      	should support those protocols."
    ::= { rcIpRouteEntry 7 }

rcIpRouteAge OBJECT-TYPE
        SYNTAX  	Integer32
        MAX-ACCESS  	read-only
        STATUS  	current
        DESCRIPTION	"The number of seconds since this route was last
                      	updated or otherwise determined to be correct.
                      	Note that no semantics of `too old' can be implied
                      	except through knowledge of the routing protocol
                      	by which the route was learned."
    ::= { rcIpRouteEntry 8 }

rcIpRouteRowStatus OBJECT-TYPE
        SYNTAX        	RowStatus
        MAX-ACCESS        	read-write
        STATUS        	current
        DESCRIPTION   	"Used to create/delete entries"
    ::= { rcIpRouteEntry 9 }

rcIpRoutePref OBJECT-TYPE
        SYNTAX        	INTEGER (0..255)
        MAX-ACCESS        	read-only
        STATUS        	current
        DESCRIPTION   	""
    ::= { rcIpRouteEntry 10 }

rcIpRouteAltSequence OBJECT-TYPE
        SYNTAX        	Integer32 
        MAX-ACCESS        	read-only
        STATUS        	current
        DESCRIPTION   	"Alternative Route Sequence. 0 denotes Best Route."
    ::= { rcIpRouteEntry 11 }

rcIpRoutePathType OBJECT-TYPE
        SYNTAX  INTEGER {
                    iA(0),     -- Indirect Alternative Route w/o ECMP path
                    iAE(1),    -- Indirect Alternative ECMP path
                    iB(2),     -- Indirect Best Route w/o ECMP path 
                    iBE(3),    -- Indirect Best ECMP path
                    dB(6),     -- Direct Best Route
	            iAN(8),    -- Indirect Alternative route not in HW
		    iAEN(9),   -- Indirect Alternative ECMP route not in HW
 		    iBN(10),   -- Indirect Best route not in HW
		    iBEN(11),  -- Indirect Best ECMP route not in HW
		    dBN(14),   -- Direct Best route not in HW
                    iAU(16),   -- Indirect Alternative Route Unresolved
                    iAEU(17),  -- Indirect Alternative ECMP Unresolved
                    iBU(18),   -- Indirect Best Route Unresolved
                    iBEU(19),  -- Indirect Best ECMP Unresolved
                    dBU(22),   -- Direct Best Route Unresolved
                    iBF(34),   -- Indirect Best route replaced by FTN
                    iBEF(35),  -- Indirect Best ECMP route replaced by FTN
                    iBV(66),  -- Indirect best IPVPN route
                    iBEV(67), -- Indirect best ECMP IPVPN route
		    iBVN(74),  -- Indirect best IPVPN route not in HW
		    iBEVN(75),  -- Indirect best ECMP IPVPN route not in HW
                    iAS(128), -- Indirect alternate route type  
                    iASE(129), -- Indirect alternate ECMP route type
                    iBS(130), -- Indirect Best SPBm Route
                    iBSE(131), -- Indirect Best SPBm Ecmp route
                    iBSN(138), -- SPBm will define this later
                    iBSEN(139), -- SPBm will define this later
                    iASV(192), -- Indirect alternate VPN route type 
                    iASVE(193), -- Indirect alternate ECMP route type 
                    iBSV(194), -- Indirect Best VPN Route over SPBm network
                    iBSVE(195) -- Indirect Best VPN ECMP Route over SPBm network
               }
        MAX-ACCESS  	read-only
        STATUS  	current
        DESCRIPTION 	"The type of route. It is a combination of 
                       direct, indirect, best, alternative and ECMP path."
    ::= { rcIpRouteEntry 12 }

rcIpRouteSrcVrfId OBJECT-TYPE
        SYNTAX  	VrfIdentifier
        MAX-ACCESS      read-write
        STATUS          current
        DESCRIPTION     "srcVrfId of the next-hop address"
    ::= { rcIpRouteEntry 13 }

rcIpRouteNextHopId OBJECT-TYPE
        SYNTAX  	DisplayString (SIZE (24))
        MAX-ACCESS      read-only
        STATUS          current
        DESCRIPTION     "Identifier of the next-hop, hostname or mac adress."
    ::= { rcIpRouteEntry 14 }

-- Ip Config Dhcp Table
 
rcIpConfDhcpTable OBJECT-TYPE 
        SYNTAX          SEQUENCE OF RcIpConfDhcpEntry
        MAX-ACCESS      not-accessible 
        STATUS          current 
        DESCRIPTION     "DHCP configuration table"
    ::= { rcIp 8 }

rcIpConfDhcpEntry OBJECT-TYPE
        SYNTAX        	RcIpConfDhcpEntry
        MAX-ACCESS        	not-accessible
        STATUS        	current
        DESCRIPTION   	"Used to configure DHCP on a particular port.  An
		      	entry is created automatically when the variable
		      	rcIpConfDhcpEnable is set to TRUE.  

 		      	Once created this entry will only be deleted if the 
		      	rcIpConfDhcpRowStatus is set to 'destroy(6)'.  In
		      	which case, the rcIpConfDhcpEnable is automatically
		      	reset to the FALSE setting."
        INDEX         	{ rcIpConfDhcpIfIndex }
        ::= { rcIpConfDhcpTable 1 }
 
RcIpConfDhcpEntry ::=
        SEQUENCE {
                rcIpConfDhcpIfIndex   	    InterfaceIndexOrZero,
                rcIpConfDhcpMaxHop    	    INTEGER,
                rcIpConfDhcpMinSec    	    INTEGER,
                rcIpConfDhcpMode      	    INTEGER,
                rcIpConfDhcpRowStatus 	    RowStatus,
		rcIpConfDhcpNumRequests     Counter32,
		rcIpConfDhcpNumReplies	    Counter32,
                rcIpConfDhcpAlwaysBroadcast TruthValue,
                rcIpConfDhcpCircuitId       TruthValue,
                rcIpConfDhcpRemoteId        TruthValue,
                rcIpConfDhcpTrusted         TruthValue,
                rcIpConfDhcpAgentAddr       IpAddress
        }
 
rcIpConfDhcpIfIndex OBJECT-TYPE
        SYNTAX        	InterfaceIndexOrZero (0..6142)
        MAX-ACCESS        	read-only
        STATUS        	current
        DESCRIPTION   	"Interface number.  The number can represent either
		      	a physical or logical(VLAN) interface."
        ::= { rcIpConfDhcpEntry 1 }
 
rcIpConfDhcpMaxHop OBJECT-TYPE
        SYNTAX        	INTEGER (1..16)
        MAX-ACCESS        	read-write
        STATUS        	current
        DESCRIPTION   	"Used to indicate the maximum number of hops a 
		      	DHCP packet can take from the source device to 
		      	the destination device (i.e., DHCP client to 
		      	DHCP server)."
 	DEFVAL        	{ 4 }
        ::= { rcIpConfDhcpEntry 2 }
 
rcIpConfDhcpMinSec OBJECT-TYPE
        SYNTAX        	INTEGER (0..65535)
        MAX-ACCESS        	read-write
        STATUS        	current
        DESCRIPTION   	"Used to indicate the minimum number of seconds 
		      	to wait between receiving a DHCP packet and
		      	actually forwarding the DHCP packet to the 
		      	destination device.  A value of zero(0) indicates
		      	forwarding should be done immediately without any
		      	delay."
	DEFVAL        	{ 0 }
        ::= { rcIpConfDhcpEntry 3 }
 
rcIpConfDhcpMode OBJECT-TYPE
        SYNTAX		INTEGER {
				none(0),
				bootp(2),
				dhcp(3),
				both(4)
			}
        MAX-ACCESS     	read-write
        STATUS        	current
        DESCRIPTION   	"Used to indicate what type of DHCP packets this
		      	interface should support.  A value of none(1) will
		      	result in all incoming DHCP and BOOTP packets to
		      	be dropped." 
        DEFVAL        	{ both }
        ::= { rcIpConfDhcpEntry 4 }
 
rcIpConfDhcpRowStatus OBJECT-TYPE
        SYNTAX        	RowStatus
        MAX-ACCESS        	read-write
        STATUS        	current
        DESCRIPTION   	"An entry is created automatically when the variable
                      	rcIpConfDhcpEnable is set to TRUE.

                      	Once created this entry will only be deleted if the
                      	rcIpConfDhcpRowStatus is set to 'destroy(6)'.  In
                      	which case, the rcIpConfDhcpEnable is automatically
                      	reset to the FALSE setting."
        ::= { rcIpConfDhcpEntry 5 }

rcIpConfDhcpNumRequests OBJECT-TYPE
        SYNTAX        	Counter32
        MAX-ACCESS        	read-only
        STATUS        	current
        DESCRIPTION   	"The total number of DHCP requests seen on this interface."
        ::= { rcIpConfDhcpEntry 6 }

rcIpConfDhcpNumReplies OBJECT-TYPE
        SYNTAX        	Counter32
        MAX-ACCESS        	read-only
        STATUS        	current
        DESCRIPTION   	"The total number of DHCP replies seen on this interface."
        ::= { rcIpConfDhcpEntry 7 }

rcIpConfDhcpAlwaysBroadcast OBJECT-TYPE
        SYNTAX        	TruthValue
        MAX-ACCESS        	read-write
        STATUS        	current
        DESCRIPTION   	"Used to indicate if DHCP Reply packets should be 
		    	broadcast to the DHCP client on this interface."
	DEFVAL		{ false }
        ::= { rcIpConfDhcpEntry 8 }

rcIpConfDhcpCircuitId OBJECT-TYPE
        SYNTAX          TruthValue
        MAX-ACCESS              read-write
        STATUS          current
        DESCRIPTION     "Used to indicate if DHCP packets should have
                        option82 circuitId info inserted before sent to
                        servers, for this interface."
        DEFVAL          { false }
        ::= { rcIpConfDhcpEntry 11 }

rcIpConfDhcpRemoteId OBJECT-TYPE
        SYNTAX          TruthValue
        MAX-ACCESS              read-write
        STATUS          current
        DESCRIPTION     "Used to indicate if DHCP packets should have
                        option82 remoteId info inserted before sent to
                        servers, for this interface."
        DEFVAL          { false }
        ::= { rcIpConfDhcpEntry 12 }

rcIpConfDhcpTrusted OBJECT-TYPE
        SYNTAX          TruthValue
        MAX-ACCESS              read-write
        STATUS          current
        DESCRIPTION     "Used to indicate if DHCP packets come through a
                         trusted dhcp circuit. This means that packets with
                         giaddr set to 0 having option82 in it, will be forwarded
                         if the circuit is trusted."
        DEFVAL          { false }
        ::= { rcIpConfDhcpEntry 13 }

rcIpConfDhcpAgentAddr OBJECT-TYPE
        SYNTAX          IpAddress
        MAX-ACCESS      read-only
        STATUS          current
        DESCRIPTION     "The IP address configured as relay on this interface; it is either the IP of the
                         physical interface or the IP of the VRRP address"
        ::= { rcIpConfDhcpEntry 14 }


-- Ip Dhcp Forward Table
 
rcIpDhcpForwardTable OBJECT-TYPE 
        SYNTAX	      	SEQUENCE OF RcIpDhcpForwardEntry
        MAX-ACCESS        	not-accessible 
        STATUS        	current 
        DESCRIPTION   	"DHCP forwarding table."
    ::= { rcIp 9 }

rcIpDhcpForwardEntry OBJECT-TYPE
        SYNTAX        	RcIpDhcpForwardEntry
        MAX-ACCESS        	not-accessible
        STATUS        	current
        DESCRIPTION   	"An entry used represents a DHCP forwarding directive."
        INDEX         	{ rcIpDhcpForwardAgentAddr, rcIpDhcpForwardServerAddr }
        ::= { rcIpDhcpForwardTable 1 }
 
RcIpDhcpForwardEntry ::=
        SEQUENCE {
                rcIpDhcpForwardAgentAddr   IpAddress,
                rcIpDhcpForwardServerAddr  IpAddress,
                rcIpDhcpForwardEnable      TruthValue,
                rcIpDhcpForwardMode        INTEGER,
                rcIpDhcpForwardRowStatus   RowStatus
        }
 
rcIpDhcpForwardAgentAddr OBJECT-TYPE
        SYNTAX        	IpAddress
        MAX-ACCESS        	read-only
        STATUS        	current
        DESCRIPTION   	"The IP address configured on an interface
                      	(i.e., a locally configured IP address)."
        ::= { rcIpDhcpForwardEntry 1 }
 
rcIpDhcpForwardServerAddr OBJECT-TYPE
        SYNTAX        	IpAddress
        MAX-ACCESS        	read-only
        STATUS        	current
        DESCRIPTION   	"The IP address of the DHCP server.  If this
	              	IP address corresponds to a locally configured
		      	IP network, the DHCP packet is broadcasted out
	       	      	the interface the IP address is assigned to.
		      	This behavior is known as 'relay agent' mode.

 		      	If this IP address is a remote address, the DHCP
		      	packet is sent via unicast to the remote device.
		      	This behavior is known as 'preferred server' mode."
        ::= { rcIpDhcpForwardEntry 2 }
 
rcIpDhcpForwardEnable OBJECT-TYPE
        SYNTAX        	TruthValue
        MAX-ACCESS        	read-write
        STATUS        	current
        DESCRIPTION   	"Used to indicate whether is entry should be used."
	DEFVAL        	{ true }
        ::= { rcIpDhcpForwardEntry 3 }
 
rcIpDhcpForwardMode OBJECT-TYPE
        SYNTAX        	INTEGER {
				none(0),
				bootp(2),
				dhcp(3),
				both(4)
			}
        MAX-ACCESS        	read-write
        STATUS        	current
        DESCRIPTION   	"Used to indicate whether this entry pertains to
		      	BOOTP packets, DHCP packets, or both."
	DEFVAL        	{ both }
        ::= { rcIpDhcpForwardEntry 4 }
 
rcIpDhcpForwardRowStatus OBJECT-TYPE
        SYNTAX        	RowStatus
        MAX-ACCESS        	read-write
        STATUS        	current
        DESCRIPTION   	"Row status of this entry."
        ::= { rcIpDhcpForwardEntry 5 }


-- Ip DHCP Relay Agent Information Option Statistics Table


rcIpDhcpOp82StatsTable OBJECT-TYPE
        SYNTAX          SEQUENCE OF RcIpDhcpOp82StatsEntry
        MAX-ACCESS      not-accessible
        STATUS          current
        DESCRIPTION     "DHCP statistics table for Relay Agent Information Option"
    ::= { rcIp 29 }

rcIpDhcpOp82StatsEntry OBJECT-TYPE
        SYNTAX          RcIpDhcpOp82StatsEntry
        MAX-ACCESS              not-accessible
        STATUS          current
        DESCRIPTION     "Used to see current statistics on interfaces that have
                         DHCP Option 82 (Relay Agent Information) enabled.
                         This table is read-only."
        INDEX           { rcIpDhcpOp82StatsIfIndex }
        ::= { rcIpDhcpOp82StatsTable 1 }

RcIpDhcpOp82StatsEntry ::=
        SEQUENCE {
                rcIpDhcpOp82StatsIfIndex            InterfaceIndexOrZero,
                rcIpDhcpOp82StatsFoundOp82          Counter32,
                rcIpDhcpOp82StatsDropped            Counter32,
                rcIpDhcpOp82StatsCircuitId          INTEGER,
                rcIpDhcpOp82StatsAddedCircuitId     Counter32,
                rcIpDhcpOp82StatsRemovedCircuitId   Counter32,
                rcIpDhcpOp82StatsRemoteId           MacAddress,
                rcIpDhcpOp82StatsAddedRemoteId      Counter32,
                rcIpDhcpOp82StatsRemovedRemoteId    Counter32,
                rcIpDhcpOp82StatsAgentAddr          IpAddress
        }

rcIpDhcpOp82StatsIfIndex OBJECT-TYPE
        SYNTAX          InterfaceIndexOrZero (0..6142)
        MAX-ACCESS      not-accessible
        STATUS          current
        DESCRIPTION     "Interface number.  The number can represent either
                        a physical or logical(VLAN) interface."
        ::= { rcIpDhcpOp82StatsEntry 1 }

rcIpDhcpOp82StatsFoundOp82 OBJECT-TYPE
        SYNTAX          Counter32
        MAX-ACCESS      read-only
        STATUS          current
        DESCRIPTION     "Represents the number of packets received on the interface
                         that already had Dhcp Option 82 inserted in them"
        ::= { rcIpDhcpOp82StatsEntry 2 }

rcIpDhcpOp82StatsDropped OBJECT-TYPE
        SYNTAX          Counter32
        MAX-ACCESS      read-only
        STATUS          current
        DESCRIPTION     "Represents the number of packets dropped because of reasons related
                         to Dhcp Option 82. These reasons could be that the packet was received
                         from an untrusted source or spoofing was detected."
        ::= { rcIpDhcpOp82StatsEntry 3 }

rcIpDhcpOp82StatsCircuitId OBJECT-TYPE
        SYNTAX          INTEGER
        MAX-ACCESS      read-only
        STATUS          current
        DESCRIPTION     "Represents the value of CircuitId inserted in the packets.
                         This is the Port number of the Dhcp Relay."
        ::= { rcIpDhcpOp82StatsEntry 4 }

rcIpDhcpOp82StatsAddedCircuitId  OBJECT-TYPE
        SYNTAX          Counter32
        MAX-ACCESS      read-only
        STATUS          current
        DESCRIPTION     "Represents the number of packets which had CircuitId inserted on this interface"
        ::= { rcIpDhcpOp82StatsEntry 5 }

rcIpDhcpOp82StatsRemovedCircuitId  OBJECT-TYPE
        SYNTAX          Counter32
        MAX-ACCESS      read-only
        STATUS          current
        DESCRIPTION     "Represents the number of packets which had CircuitId removed on this interface"
        ::= { rcIpDhcpOp82StatsEntry 6 }

rcIpDhcpOp82StatsRemoteId OBJECT-TYPE
        SYNTAX          MacAddress
        MAX-ACCESS      read-only
        STATUS          current
        DESCRIPTION     "Represents the value of RemoteId inserted in the packets.
                         This is the Mac address of the Dhcp Relay."
        ::= { rcIpDhcpOp82StatsEntry 7 }

rcIpDhcpOp82StatsAddedRemoteId  OBJECT-TYPE
        SYNTAX          Counter32
        MAX-ACCESS      read-only
        STATUS          current
        DESCRIPTION     "Represents the number of packets which had RemoteId inserted on this interface"
        ::= { rcIpDhcpOp82StatsEntry 8 }

rcIpDhcpOp82StatsRemovedRemoteId  OBJECT-TYPE
        SYNTAX          Counter32
        MAX-ACCESS      read-only
        STATUS          current
        DESCRIPTION     "Represents the number of packets which had RemoteId removed on this interface"
        ::= { rcIpDhcpOp82StatsEntry 9 }

rcIpDhcpOp82StatsAgentAddr OBJECT-TYPE
        SYNTAX          IpAddress
        MAX-ACCESS      read-only
        STATUS          current
        DESCRIPTION     "The IP address configured as relay on this interface; it is either the IP of the
                         physical interface or the IP of the VRRP address"
        ::= { rcIpDhcpOp82StatsEntry 10 }


-- Ip UDP Protocol Table
 
rcIpUdp OBJECT IDENTIFIER ::= { rcIp 13 }

rcIpUdpProtocolTableSize OBJECT-TYPE
        SYNTAX        Integer32 
        MAX-ACCESS    read-only
        STATUS        current
        DESCRIPTION   "Used to indicate the number of entries in the 
		      rcIpUdpProtocolTable."
        ::= { rcIpUdp 1 }

rcIpUdpProtocolTable OBJECT-TYPE 
        SYNTAX          SEQUENCE OF RcIpUdpProtocolEntry
        MAX-ACCESS      not-accessible 
        STATUS          current 
        DESCRIPTION     "list of UDP protocols. Used to determine whether to
                         forward the UDP broadcast packet or not."
    ::= { rcIpUdp 2 }

rcIpUdpProtocolEntry OBJECT-TYPE
        SYNTAX        	RcIpUdpProtocolEntry
        MAX-ACCESS        	not-accessible
        STATUS        	current
        DESCRIPTION   	"Used to include a particular UDP port in the table.  
		      	An entry in this table indicates that the box might do 
		      	forwarding of UDP broadcast packets if there is a 
                        matching entry for this packet in the 
                        rcIpUdpPortFwdTable."
        INDEX         	{ rcIpUdpProtocolPortNumber }
        ::= { rcIpUdpProtocolTable 1 }
 
RcIpUdpProtocolEntry ::=
        SEQUENCE {
                rcIpUdpProtocolPortNumber      INTEGER,
                rcIpUdpProtocolName    	       DisplayString,
                rcIpUdpProtocolRowStatus       RowStatus
        }
 
rcIpUdpProtocolPortNumber OBJECT-TYPE
        SYNTAX        	INTEGER (1..65535)
        MAX-ACCESS        	read-only
        STATUS        	current
        DESCRIPTION   	"well-known UDP Port number. Pre-assigned port
                         number for this protocol. Port used by the
                         server process as its contact port. It cannot 
                         be BOOTP/DHCP port#s 67, 68."
        ::= { rcIpUdpProtocolEntry 1 }
 
rcIpUdpProtocolName OBJECT-TYPE
        SYNTAX          DisplayString (SIZE(1..15))
        MAX-ACCESS        	read-write
        STATUS        	current
        DESCRIPTION   	"Used to indicate the name of the protocol 
		      	that is running on top of UDP protocol. 
                        cannot change the name once created. This 
                        should be set while creating the entry."  
        ::= { rcIpUdpProtocolEntry 2 }
 
rcIpUdpProtocolRowStatus OBJECT-TYPE
        SYNTAX        	RowStatus
        MAX-ACCESS        	read-write
        STATUS        	current
        DESCRIPTION   	"Rowstatus of this entry."
        ::= { rcIpUdpProtocolEntry 3 }


-- Ip Udp Port Forward Table

rcIpUdpPortFwdTableSize OBJECT-TYPE
        SYNTAX        Integer32
        MAX-ACCESS    read-only
        STATUS        current
        DESCRIPTION   "Used to indicate the number of entries in the
                      rcIpUdpPortFwdTable."
        ::= { rcIpUdp 3 }
 
rcIpUdpPortFwdTable OBJECT-TYPE 
        SYNTAX	      	SEQUENCE OF RcIpUdpPortFwdEntry
        MAX-ACCESS        	not-accessible 
        STATUS        	current 
        DESCRIPTION   	"Udp forward entry table."
    ::= { rcIpUdp 4 }

rcIpUdpPortFwdEntry OBJECT-TYPE
        SYNTAX        	RcIpUdpPortFwdEntry
        MAX-ACCESS        	not-accessible
        STATUS        	current
        DESCRIPTION   	"An entry is configured to specify forwarding policy
                         parameters."
        INDEX         	{ rcIpUdpPortFwdDestPort,
                          rcIpUdpPortFwdDestAddr}
        ::= { rcIpUdpPortFwdTable 1 }
 
RcIpUdpPortFwdEntry ::=
        SEQUENCE {
                rcIpUdpPortFwdDestPort      INTEGER,
                rcIpUdpPortFwdDestAddr      IpAddress,
                rcIpUdpPortFwdId            Integer32,
                rcIpUdpPortFwdFwdListIdListSize INTEGER (0..128),
                rcIpUdpPortFwdFwdListIdList IdList(SIZE(64)),
                rcIpUdpPortFwdNumFwdPackets Counter32,
                rcIpUdpPortFwdNumDropPacketsTtlExpired Counter32,
                rcIpUdpPortFwdNumDropPacketsDestUnreach Counter32,
                rcIpUdpPortFwdRowStatus     RowStatus
        }
 
rcIpUdpPortFwdDestPort OBJECT-TYPE
        SYNTAX        	INTEGER(1..65535)
        MAX-ACCESS        	read-only
        STATUS        	current
        DESCRIPTION   	"The well-known port number defined for UDP/TCP 
                        depending on the value of IpProtoType field in this
                        entry. This port number has to be defined in the
                        rcIpUdpProtoTable. In order to select this policy the 
                        destination port number has to match the DestPort 
                        value."
        ::= { rcIpUdpPortFwdEntry 1 }
 
rcIpUdpPortFwdDestAddr OBJECT-TYPE
        SYNTAX        	IpAddress
        MAX-ACCESS        	read-only
        STATUS        	current
        DESCRIPTION   	"Destination IP address. The IP addres to which the 
                        UDP/TCP broadcast should be forwarded. This IP address 
                        can be any IP server address or subnet broadcast 
                        address.  If the IP address is one of the routable 
                        interface's address on the router, the frame will be 
                        rebroadcast out as a limited broadcast. If the Ip 
                        address is that of a server then the received 
                        broadcast packet will be sent as a unicast packet to 
                        this address."
        ::= { rcIpUdpPortFwdEntry 2 }

rcIpUdpPortFwdId OBJECT-TYPE
        SYNTAX        Integer32
        MAX-ACCESS    read-only
        STATUS        current
        DESCRIPTION   "Identifier of this entry. Used internally to identify
                      this entry."
        ::= { rcIpUdpPortFwdEntry 3 }

rcIpUdpPortFwdFwdListIdListSize OBJECT-TYPE
        SYNTAX        INTEGER (0..128)
        MAX-ACCESS    read-only
        STATUS        current
        DESCRIPTION   "Used to indicate the number of id(s) in the
                      rcIpUdpPortFwdListId variable."
        ::= { rcIpUdpPortFwdEntry 4 }

rcIpUdpPortFwdFwdListIdList OBJECT-TYPE
        SYNTAX        IdList(SIZE(64))
        MAX-ACCESS    read-only
        STATUS        current
        DESCRIPTION   "Used to indicate zero or more rcIpUdpPortFwdListEntry(s)
                      that are referring to this entry.  Each list-id identifier
                      is stored as two bytes in this array starting from
                      offset zero.  Any unused bytes should be set to zero."
        ::= { rcIpUdpPortFwdEntry 5 }
 
rcIpUdpPortFwdNumFwdPackets OBJECT-TYPE
        SYNTAX        	Counter32
        MAX-ACCESS        	read-only
        STATUS        	current
        DESCRIPTION   	"The total number of UDP/TCP broadcast packets forwarded
                        using this policy."
        ::= { rcIpUdpPortFwdEntry 6 }

rcIpUdpPortFwdNumDropPacketsTtlExpired OBJECT-TYPE
        SYNTAX        	Counter32
        MAX-ACCESS        	read-only
        STATUS        	current
        DESCRIPTION   	"The total number of UDP/TCP broadcast packets dropped
                        because the TTL has expired."
        ::= { rcIpUdpPortFwdEntry 7 }

rcIpUdpPortFwdNumDropPacketsDestUnreach OBJECT-TYPE
        SYNTAX        	Counter32
        MAX-ACCESS        	read-only
        STATUS        	current
        DESCRIPTION   	"The total number of UDP/TCP broadcast packets dropped
                        because the rcIpUdpPortFwdDestAddr specified in
                        this policy was unreachable."
        ::= { rcIpUdpPortFwdEntry 8 }

rcIpUdpPortFwdRowStatus OBJECT-TYPE
        SYNTAX        	RowStatus
        MAX-ACCESS        	read-write
        STATUS        	current
        DESCRIPTION   	"Row status of this entry."
        ::= { rcIpUdpPortFwdEntry 9 }

-- Udp Port Fwd List Table 

rcIpUdpPortFwdListTableSize OBJECT-TYPE
        SYNTAX        Integer32
        MAX-ACCESS    read-only
        STATUS        current
        DESCRIPTION   "Used to indicate the number of entries in the
                      rcIpUdpPortFwdListTable."
        ::= { rcIpUdp 5 }

rcIpUdpPortFwdListTable OBJECT-TYPE
        SYNTAX        SEQUENCE OF RcIpUdpPortFwdListEntry
        MAX-ACCESS    not-accessible
        STATUS        current
        DESCRIPTION   "A table used to group rcIpUdpPortFwdEntry(s) 
                      into a list."
        ::= { rcIpUdp 6 }

rcIpUdpPortFwdListEntry OBJECT-TYPE
        SYNTAX        RcIpUdpPortFwdListEntry
        MAX-ACCESS    not-accessible
        STATUS        current
        DESCRIPTION   "Route entry attributes."
        INDEX         { rcIpUdpPortFwdListId }
        ::= { rcIpUdpPortFwdListTable 1 }
 
RcIpUdpPortFwdListEntry ::= SEQUENCE {
                  rcIpUdpPortFwdListId INTEGER (1..1000),
                  rcIpUdpPortFwdListName DisplayString (SIZE(0..15)),
                  rcIpUdpPortFwdListFwdIdListSize INTEGER (0..64),
                  rcIpUdpPortFwdListFwdIdList OCTET STRING (SIZE(128)),
                  rcIpUdpPortFwdListRowStatus RowStatus
                  }

rcIpUdpPortFwdListId OBJECT-TYPE
        SYNTAX        INTEGER (1..1000)
        MAX-ACCESS    read-only
        STATUS        current
        DESCRIPTION   "A value that uniquely identifies this list of 
                       rcIpUdpPortFwdListEntry."
        ::= { rcIpUdpPortFwdListEntry 1 }
 
rcIpUdpPortFwdListName OBJECT-TYPE
        SYNTAX        DisplayString (SIZE (0..15))
        MAX-ACCESS    read-write
        STATUS        current
        DESCRIPTION   "An administratively-assigned name for this list."
        ::= { rcIpUdpPortFwdListEntry 3 }
 
rcIpUdpPortFwdListFwdIdListSize OBJECT-TYPE
        SYNTAX        INTEGER (0..64)
        MAX-ACCESS    read-only
        STATUS        current
        DESCRIPTION   "Used to indicate the number of rcIpUdpPortFwdNetEntry 
                      id(s) in the rcIpUdpPortFwdListIdList variable."
        ::= { rcIpUdpPortFwdListEntry 4 }
 
rcIpUdpPortFwdListFwdIdList OBJECT-TYPE
        SYNTAX        OCTET STRING (SIZE(128))
        MAX-ACCESS    read-write
        STATUS        current
        DESCRIPTION   "Used to indicate zero or more UdpPortFwd entries 
                      that are associated to this list.  Each entry identifier
                      is stored as two bytes in this array starting from
                      offset zero.  Any unused bytes should be set to zero."
        ::= { rcIpUdpPortFwdListEntry 5 }

rcIpUdpPortFwdListRowStatus OBJECT-TYPE
        SYNTAX          RowStatus
        MAX-ACCESS      read-write
        STATUS          current
        DESCRIPTION     "Row status of this entry."
        ::= { rcIpUdpPortFwdListEntry 6 }
 

-- Ip Config Broadcast Forwarding Table

rcIpUdpConfBroadcastIntfTableSize OBJECT-TYPE
        SYNTAX        Integer32
        MAX-ACCESS    read-only
        STATUS        current
        DESCRIPTION   "Used to indicate the number of entries in the
                      rcIpUdpBroadcastIntfTable."
        ::= { rcIpUdp 7 }
 
rcIpUdpConfBroadcastIntfTable OBJECT-TYPE 
        SYNTAX          SEQUENCE OF RcIpUdpConfBroadcastIntfEntry
        MAX-ACCESS      not-accessible 
        STATUS          current 
        DESCRIPTION     "IP broadcast forward configuration table"
    ::= { rcIpUdp 8 }

rcIpUdpConfBroadcastIntfEntry OBJECT-TYPE
        SYNTAX        	RcIpUdpConfBroadcastIntfEntry
        MAX-ACCESS        	not-accessible
        STATUS        	current
        DESCRIPTION   	"Used to configure UDP broadcast forward on a 
                        particular interface."
        INDEX         	{ rcIpUdpConfBroadcastIntfLocalIfAddr }
        ::= { rcIpUdpConfBroadcastIntfTable 1 }
 
RcIpUdpConfBroadcastIntfEntry ::=
        SEQUENCE {
                rcIpUdpConfBroadcastIntfLocalIfAddr   	    IpAddress,
                rcIpUdpConfBroadcastIntfUdpPortFwdListId    INTEGER (0..1000),
                rcIpUdpConfBroadcastIntfMaxTtl    	    INTEGER (1..16),
                rcIpUdpConfBroadcastIntfNumRxPkts           Counter32,
                rcIpUdpConfBroadcastIntfNumFwdPkts          Counter32,
                rcIpUdpConfBroadcastIntfNumDropPktsMaxTtlExpired  Counter32,
                rcIpUdpConfBroadcastIntfNumDropPktsDestUnreach   Counter32,
                rcIpUdpConfBroadcastIntfNumDropPktsUnknownPort   Counter32,
                rcIpUdpConfBroadcastIntfRowStatus 	             RowStatus,
                rcIpUdpConfBroadcastIntfBroadCastMask       IpAddress
 
        }
 
rcIpUdpConfBroadcastIntfLocalIfAddr OBJECT-TYPE
        SYNTAX        	IpAddress 
        MAX-ACCESS        	read-only
        STATUS        	current
        DESCRIPTION   	"The ip address of the local interface that is
           	        partipating in the forwarding UDP broadcast packets."
        ::= { rcIpUdpConfBroadcastIntfEntry 1 }
 
rcIpUdpConfBroadcastIntfUdpPortFwdListId OBJECT-TYPE
        SYNTAX        INTEGER (0..1000)
        MAX-ACCESS    read-write
        STATUS        current
        DESCRIPTION   "Used to indicate the number UDP ports that this 
                      interface is configured to forward.

                      A value of '0' indicates that this interface will not
                      forward any UDP broadcast packets. This is a required
                      field to create an entry."
        ::= { rcIpUdpConfBroadcastIntfEntry 2 }

rcIpUdpConfBroadcastIntfMaxTtl OBJECT-TYPE
        SYNTAX        	INTEGER (1..16)
        MAX-ACCESS        	read-write
        STATUS        	current
        DESCRIPTION   	"Used to indicate the maximum number of hops an 
		      	IP broadcast packet can take from the source 
                        device to the destination device."
 	    DEFVAL        	{ 4 }
        ::= { rcIpUdpConfBroadcastIntfEntry 3 }
 
rcIpUdpConfBroadcastIntfNumRxPkts OBJECT-TYPE
        SYNTAX        	Counter32
        MAX-ACCESS        	read-only
        STATUS        	current
        DESCRIPTION   	"The total number of UDP/TCP broadcast packets 
                        received by this local interface."
        ::= { rcIpUdpConfBroadcastIntfEntry 4 }

rcIpUdpConfBroadcastIntfNumFwdPkts OBJECT-TYPE
        SYNTAX        	Counter32
        MAX-ACCESS        	read-only
        STATUS        	current
        DESCRIPTION   	"The total number of UDP/TCP broadcast packets 
                        forwarded."
        ::= { rcIpUdpConfBroadcastIntfEntry 5 }

rcIpUdpConfBroadcastIntfNumDropPktsMaxTtlExpired OBJECT-TYPE
        SYNTAX        	Counter32
        MAX-ACCESS        	read-only
        STATUS        	current
        DESCRIPTION   	"The total number of UDP/TCP broadcast packets 
                        dropped because the TTL has expired."
        ::= { rcIpUdpConfBroadcastIntfEntry 6 }

rcIpUdpConfBroadcastIntfNumDropPktsDestUnreach OBJECT-TYPE
        SYNTAX        	Counter32
        MAX-ACCESS        	read-only
        STATUS        	current
        DESCRIPTION   	"The total number of UDP broadcast packets 
                        dropped because the destination was unreachable."
        ::= { rcIpUdpConfBroadcastIntfEntry 7 }

rcIpUdpConfBroadcastIntfNumDropPktsUnknownPort OBJECT-TYPE
        SYNTAX        	Counter32
        MAX-ACCESS        	read-only
        STATUS        	current
        DESCRIPTION   	"The total number of UDP/TCP broadcast packets 
                        dropped because the destination port/protocol 
                        specified has no matching forwarding policy." 
        ::= { rcIpUdpConfBroadcastIntfEntry 8 }

rcIpUdpConfBroadcastIntfRowStatus OBJECT-TYPE
        SYNTAX        	RowStatus
        MAX-ACCESS        	read-write
        STATUS        	current
        DESCRIPTION   	"Entry row status."
        ::= { rcIpUdpConfBroadcastIntfEntry 9 }

rcIpUdpConfBroadcastIntfBroadCastMask OBJECT-TYPE
        SYNTAX          IpAddress
        MAX-ACCESS      read-write
        STATUS          current
        DESCRIPTION     "The subnet mask of the local interface that is
                        used for broadcasting the UDP broadcast packets."
        ::= { rcIpUdpConfBroadcastIntfEntry 10 }


--IP PIM

rcIpPim OBJECT IDENTIFIER ::= { rcIp 16 }

rcIpPimGlobal OBJECT IDENTIFIER ::= { rcIpPim 1}

rcIpPimGlobalEnable OBJECT-TYPE
        SYNTAX          TruthValue
        MAX-ACCESS      read-write
        STATUS          current
        DESCRIPTION     "enable feature"
        ::= { rcIpPimGlobal 1 }

rcIpPimGlobalMode OBJECT-TYPE
        SYNTAX          INTEGER {
                                dm(1),
                                sm(2),
                                smdm(3),
                                ssm(4)
                        }
        MAX-ACCESS      read-write
        STATUS          current
        DESCRIPTION     ""
        ::= { rcIpPimGlobal 2 }

rcIpPimGlobalRegisterSuppTimer OBJECT-TYPE
        SYNTAX          INTEGER (6..65535)
        MAX-ACCESS      read-write
        STATUS          current
        DESCRIPTION     "Each source's DR maintains, per (S,G), a Register-                                 Suppression-timer in seconds. The Register-
                         Suppression-timer is started by the Register-Stop                                  message; upon expiration, the source's DR resumes                                  sending data packets to the RP, encapsulated in 
                         the Register message."
        DEFVAL  { 60 }
        ::= { rcIpPimGlobal 4 }

rcIpPimGlobalInterfaceTableSize OBJECT-TYPE
        SYNTAX        Integer32
        MAX-ACCESS    read-only
        STATUS        current
        DESCRIPTION   "table size"
        ::= { rcIpPimGlobal 5 }

rcIpPimGlobalUniRouteChgTimeOut OBJECT-TYPE
        SYNTAX          INTEGER (2..65535)
        MAX-ACCESS      read-write
        STATUS          current
        DESCRIPTION     "This timer allows a better tuning on how fast the
                         routing information is going to get updated from
                         RTM (the frequency at which the RTM is polled for
                         routing information updates)."
        DEFVAL        { 5 }
        ::= { rcIpPimGlobal 6 }

rcIpPimGlobalDiscardDataTimeOut OBJECT-TYPE
        SYNTAX          INTEGER (5..65535)
        MAX-ACCESS      read-write
        STATUS          current
        DESCRIPTION     "This timer is used to discard data until the Join
                         is received from the RP. A ipmc discard record is
                         created and deleted once the timer expires and/or
                         when a Join is received."
        DEFVAL        { 60 }
        ::= { rcIpPimGlobal 7 }

rcIpPimGlobalCRPADVTimeOut OBJECT-TYPE
        SYNTAX          INTEGER (5..26214)
        MAX-ACCESS      read-write
        STATUS          current
        DESCRIPTION     "Routers configured as candidate RPs use this timer
                         to periodically send C-RP-Adv messages. Upon expiry,
                         a C-RP-Adv message is sent to the elected BSR."
        DEFVAL        { 60 }
        ::= { rcIpPimGlobal 8 }

rcIpPimGlobalBootStrapPeriod OBJECT-TYPE
        SYNTAX          INTEGER (5..32757)
        MAX-ACCESS      read-write
        STATUS          current
        DESCRIPTION     "At the elected BSR, this is the interval between
                         originating Bootstrap messages."
        DEFVAL        { 60 }
        ::= { rcIpPimGlobal 9 }

rcIpPimGlobalStaticRP   OBJECT-TYPE
        SYNTAX    TruthValue
        MAX-ACCESS   read-write
        STATUS       current
        DESCRIPTION     "Enable/Disable Static RP feature."
        DEFVAL       { false }
        ::= { rcIpPimGlobal 10 }

rcIpPimGlobalFwdCacheTimeOut OBJECT-TYPE
        SYNTAX          INTEGER (10..86400)
        MAX-ACCESS      read-write
        STATUS          current
        DESCRIPTION     "PIM forward cache expiry value in seconds.This 
                         value is going to be used in aging PIM mroutes 
                         in seconds."
        DEFVAL        { 210 }
        ::= { rcIpPimGlobal 12 }

rcIpPimGlobalFastJoinPrune OBJECT-TYPE
        SYNTAX             EnableValue
        MAX-ACCESS         read-write
        STATUS             current
        DESCRIPTION        "Pim Fast Join Prune."  
        DEFVAL             { disable }
        ::= { rcIpPimGlobal 13 } 

rcIpPimTable OBJECT-TYPE 
        SYNTAX          SEQUENCE OF RcIpPimEntry
        MAX-ACCESS      not-accessible 
        STATUS          current 
        DESCRIPTION     "IP Pim table"
    ::= { rcIpPim 2 }

rcIpPimEntry OBJECT-TYPE
        SYNTAX        	RcIpPimEntry
        MAX-ACCESS       not-accessible
        STATUS        	current
        DESCRIPTION   	"An entry of Ip Pim Table."
        INDEX         	{ rcIpPimIfIndex }
        ::= { rcIpPimTable 1 }
 
RcIpPimEntry ::=
        SEQUENCE {
                rcIpPimIfIndex           InterfaceIndex,
                rcIpPimEnable            TruthValue,
                rcIpPimMode              INTEGER,
                rcIpPimHelloInterval     INTEGER,
                rcIpPimJoinPruneInterval INTEGER,
                rcIpPimCBSRPreference    INTEGER,
                rcIpPimIntfType          INTEGER
        }
 
rcIpPimIfIndex OBJECT-TYPE
        SYNTAX        InterfaceIndex
        MAX-ACCESS    read-only
        STATUS        current
        DESCRIPTION   "port"
        ::= { rcIpPimEntry 1 }

rcIpPimEnable OBJECT-TYPE
        SYNTAX         TruthValue
        MAX-ACCESS     read-write
        STATUS         current
        DESCRIPTION    "enable interface"
        ::= { rcIpPimEntry 2 }

rcIpPimMode OBJECT-TYPE
        SYNTAX        INTEGER {
		         dense(1),
			 sparse(2),
			 sparseDense(3),
			 ssm(4)
		      }
        MAX-ACCESS    read-write
        STATUS        current
        DESCRIPTION   ""
        ::= { rcIpPimEntry 3 }

rcIpPimHelloInterval OBJECT-TYPE
        SYNTAX        INTEGER(0..18724)
        MAX-ACCESS    read-write
        STATUS        current
        DESCRIPTION   "frq. at which hello sent."
	DEFVAL     { 30 }
        ::= { rcIpPimEntry 4 }

rcIpPimJoinPruneInterval OBJECT-TYPE
        SYNTAX        INTEGER(1..18724)
        MAX-ACCESS    read-write
        STATUS        current
        DESCRIPTION   ""
        ::= { rcIpPimEntry 5 }

rcIpPimCBSRPreference OBJECT-TYPE
        SYNTAX        INTEGER (-1..255)
        MAX-ACCESS    read-write
        STATUS        current
        DESCRIPTION   ""
	DEFVAL     { -1 }
        ::= { rcIpPimEntry 6 }

rcIpPimIntfType OBJECT-TYPE
        SYNTAX        INTEGER {
               active(1),
               passive(2)
            }
        MAX-ACCESS    read-write
        STATUS        current
        DESCRIPTION   "Pim interface type."
          DEFVAL     { active }
        ::= { rcIpPimEntry 7 }

-- Pim Interface Table Extension

rcIpPimInterfaceTable OBJECT-TYPE 
        SYNTAX          SEQUENCE OF RcIpPimInterfaceEntry
        MAX-ACCESS      not-accessible 
        STATUS          current 
        DESCRIPTION     "IP Pim table"
    ::= { rcIpPim 3 }

rcIpPimInterfaceEntry OBJECT-TYPE
        SYNTAX        	RcIpPimInterfaceEntry
        MAX-ACCESS        	not-accessible
        STATUS        	current
        DESCRIPTION   	"An entry of Ip Pim Interface Table."
        INDEX         	{ rcIpPimInterfaceIfIndex }
        ::= { rcIpPimInterfaceTable 1 }
 
RcIpPimInterfaceEntry ::=
        SEQUENCE {
                rcIpPimInterfaceIfIndex   InterfaceIndex,
                rcIpPimInterfaceOperState INTEGER,
                rcIpPimInterfaceType      INTEGER 
        }
 
rcIpPimInterfaceIfIndex OBJECT-TYPE
        SYNTAX        InterfaceIndex
        MAX-ACCESS    read-only
        STATUS        current
        DESCRIPTION   "port"
        ::= { rcIpPimInterfaceEntry 1 }

rcIpPimInterfaceOperState OBJECT-TYPE
        SYNTAX         INTEGER { 
                          up(1), 
                          down(2) 
                       }
        MAX-ACCESS     read-only
        STATUS         current
        DESCRIPTION    "The current operational state of this PIM interface. 
                        This object is deprecated in favor of ifOperStatus."
        ::= { rcIpPimInterfaceEntry 2 }

rcIpPimInterfaceType OBJECT-TYPE
        SYNTAX        INTEGER {
               active(1),
               passive(2)
            }
        MAX-ACCESS    read-write
        STATUS        current
        DESCRIPTION   "Pim interface type."
          DEFVAL     { active }
        ::= { rcIpPimInterfaceEntry 3 }


rcIpPimStaticRPTable OBJECT-TYPE
    SYNTAX        SEQUENCE OF RcIpPimStaticRPEntry
    MAX-ACCESS    not-accessible
    STATUS        current
    DESCRIPTION   "The table lists all the RPs configured statically for
                   various IP multicast groups."
    ::= { rcIpPim 4 }

rcIpPimStaticRPEntry OBJECT-TYPE
    SYNTAX        RcIpPimStaticRPEntry
    MAX-ACCESS    not-accessible
    STATUS        current
    DESCRIPTION   "An entry (conceptual row) in the rcIpPimStaticRPTable."
    INDEX      { rcIpPimStaticRPGroupAddress,
                 rcIpPimStaticRPGroupMask,
                 rcIpPimStaticRPAddress }
    ::= { rcIpPimStaticRPTable 1 }

RcIpPimStaticRPEntry ::= SEQUENCE {
    rcIpPimStaticRPGroupAddress  IpAddress,
    rcIpPimStaticRPGroupMask     IpAddress,
    rcIpPimStaticRPAddress       IpAddress,
    rcIpPimStaticRPRowStatus     RowStatus,
    rcIpPimStaticRPStatus        INTEGER
}

rcIpPimStaticRPGroupAddress   OBJECT-TYPE
    SYNTAX        IpAddress
    MAX-ACCESS    read-only
    STATUS        current
    DESCRIPTION   "The IP multicast group address which, when combined with
                   rcIpPimStaticRPGroupMask, identifies a group prefix for
                   which rcIpPimStaticRPAddress is a static-RP."
    ::= { rcIpPimStaticRPEntry 1 }

rcIpPimStaticRPGroupMask   OBJECT-TYPE
    SYNTAX        IpAddress
    MAX-ACCESS    read-only
    STATUS        current
    DESCRIPTION   "The multicast group address mask which, when combined
                  with rcIpPimStaticRPGroupAddress, identifies a group
                    prefix for which rcIpPimStaticRPAddress is a static-RP."
    ::= { rcIpPimStaticRPEntry 2 }

rcIpPimStaticRPAddress  OBJECT-TYPE
    SYNTAX        IpAddress
    MAX-ACCESS    read-only
    STATUS        current
    DESCRIPTION   "The (unicast) address of the static-RP."
    ::= { rcIpPimStaticRPEntry 3 }

rcIpPimStaticRPRowStatus   OBJECT-TYPE
    SYNTAX        RowStatus
    MAX-ACCESS    read-write
    STATUS        current
    DESCRIPTION   "The status of this row, by which new entries may be
                   created, or old entries deleted from this table."
    ::= { rcIpPimStaticRPEntry 4 }

rcIpPimStaticRPStatus   OBJECT-TYPE
    SYNTAX        INTEGER {
	             valid(1),
		     invalid(2)
                  }
    MAX-ACCESS    read-only
    STATUS        current
    DESCRIPTION   "The status of StaticRP."
    ::= { rcIpPimStaticRPEntry 5 }

rcIpPimCurrBsr OBJECT IDENTIFIER ::= { rcIpPim 5 }

rcIpPimCurrBsrAddress OBJECT-TYPE
    SYNTAX        IpAddress
    MAX-ACCESS    read-only
    STATUS        current
    DESCRIPTION   "Current BSR address"
    ::= { rcIpPimCurrBsr 1 }

rcIpPimCurrBsrFragmentTag OBJECT-TYPE
    SYNTAX        Integer32
    MAX-ACCESS    read-only
    STATUS        current
    DESCRIPTION   "Current BSR Fragment Tag"
    DEFVAL        { -1 }
    ::= { rcIpPimCurrBsr 2 }

rcIpPimCurrBsrHashMask OBJECT-TYPE
    SYNTAX        IpAddress 
    MAX-ACCESS    read-only
    STATUS        current
    DESCRIPTION   "Current BSR Hash Mask value"
    ::= { rcIpPimCurrBsr 3 }

rcIpPimCurrBsrPriority OBJECT-TYPE
    SYNTAX        Integer32
    MAX-ACCESS    read-only
    STATUS        current
    DESCRIPTION   "Current BSR Priority"
    DEFVAL        { 0 }
    ::= { rcIpPimCurrBsr 4 }

rcIpPimCurrBsrBootStrapTimer OBJECT-TYPE
    SYNTAX        Integer32
    MAX-ACCESS    read-only
    STATUS        current
    DESCRIPTION   "Current BSR Boot Strap Timer"
    ::= { rcIpPimCurrBsr 5 }

rcIpPimVirtualNbrTable OBJECT-TYPE
        SYNTAX          SEQUENCE OF RcIpPimVirtualNbrEntry
        MAX-ACCESS      not-accessible
        STATUS          current
        DESCRIPTION     "Table listing the router's virtual PIM neighbors"
    ::= { rcIpPim 6 }

rcIpPimVirtualNbrEntry OBJECT-TYPE
        SYNTAX          RcIpPimVirtualNbrEntry
        MAX-ACCESS      not-accessible
        STATUS          current
        DESCRIPTION     "An entry in the virtual PIM neighbors' table."
        INDEX           { rcIpPimVirtualNbrAddress }
        ::= { rcIpPimVirtualNbrTable 1 }

RcIpPimVirtualNbrEntry ::= SEQUENCE {
        rcIpPimVirtualNbrAddress   IpAddress,
        rcIpPimVirtualNbrIfIndex   InterfaceIndex,
        rcIpPimVirtualNbrRowStatus RowStatus
}

rcIpPimVirtualNbrAddress OBJECT-TYPE
    SYNTAX     IpAddress
    MAX-ACCESS not-accessible
    STATUS     current
    DESCRIPTION
            "The IP address of the virtual PIM neighbor for which this entry
             contains information."
    ::= { rcIpPimVirtualNbrEntry 1 }

rcIpPimVirtualNbrIfIndex OBJECT-TYPE
    SYNTAX     InterfaceIndex
    MAX-ACCESS read-create
    STATUS     current
    DESCRIPTION
            "The value of ifIndex for the PIM interface in which this virtual
             neighbor is created. This value is mandatory while trying to create
             a virtual PIM neighbor."
    ::= { rcIpPimVirtualNbrEntry 2 }

rcIpPimVirtualNbrRowStatus OBJECT-TYPE
    SYNTAX     RowStatus
    MAX-ACCESS read-create
    STATUS     current
    DESCRIPTION
            "To create/delete an entry in the virtual PIM neighbors' 
             table."
    ::= { rcIpPimVirtualNbrEntry 3 }

--IP Multicast Arp table

rcIpMulticastArpTable OBJECT-TYPE 
        SYNTAX          SEQUENCE OF RcIpMulticastArpEntry
        MAX-ACCESS      not-accessible 
        STATUS          current 
        DESCRIPTION     "IP Multicast Arp table"
        ::= { rcIp 17 }

rcIpMulticastArpEntry OBJECT-TYPE
        SYNTAX        	RcIpMulticastArpEntry
        MAX-ACCESS        	not-accessible
        STATUS        	current
        DESCRIPTION   	"An entry of Ip Multicast Arp Table."
        INDEX         	{ rcIpMulticastArpVlanId,
                          rcIpMulticastArpMacAddress,
                          rcIpMulticastArpIpAddress }
        ::= { rcIpMulticastArpTable 1 }
 
RcIpMulticastArpEntry ::=
        SEQUENCE {
                rcIpMulticastArpVlanId     Integer32,
                rcIpMulticastArpMacAddress MacAddress,
                rcIpMulticastArpIpAddress  IpAddress,
                rcIpMulticastArpPorts      PortSet,
                rcIpMulticastArpNumMltIds  Integer32,
                rcIpMulticastArpMltIds     IdList,
                rcIpMulticastArpRowStatus  RowStatus
        }
 
rcIpMulticastArpVlanId OBJECT-TYPE
        SYNTAX        Integer32 (0..4084)
        MAX-ACCESS    read-only
        STATUS        current
        DESCRIPTION   "vlan id"
        ::= { rcIpMulticastArpEntry 1 }

rcIpMulticastArpMacAddress OBJECT-TYPE
        SYNTAX         MacAddress
        MAX-ACCESS     read-only
        STATUS         current
        DESCRIPTION    "multicast mac address"
        ::= { rcIpMulticastArpEntry 2 }

rcIpMulticastArpIpAddress OBJECT-TYPE
        SYNTAX        IpAddress
        MAX-ACCESS    read-only
        STATUS        current
        DESCRIPTION   "multicast ip address"
        ::= { rcIpMulticastArpEntry 3 }

rcIpMulticastArpPorts OBJECT-TYPE
        SYNTAX        PortSet
        MAX-ACCESS    read-write
        STATUS        current
        DESCRIPTION   "ports within a particular vlan"
        ::= { rcIpMulticastArpEntry 4 }

rcIpMulticastArpNumMltIds OBJECT-TYPE
        SYNTAX        Integer32
        MAX-ACCESS    read-only
        STATUS        current
        DESCRIPTION   "number of mlt ids"
        ::= { rcIpMulticastArpEntry 5 }

rcIpMulticastArpMltIds OBJECT-TYPE
        SYNTAX        IdList -- 1024 octets
        MAX-ACCESS    read-write
        STATUS        current
        DESCRIPTION   "mlt id"
        ::= { rcIpMulticastArpEntry 6 }

rcIpMulticastArpRowStatus OBJECT-TYPE
        SYNTAX        RowStatus
        MAX-ACCESS    read-write
        STATUS        current
        DESCRIPTION   "row status"
        ::= { rcIpMulticastArpEntry 7 }


-- IP Rip Interface Table

rcIpRipInterface OBJECT IDENTIFIER       ::= { rcIp 20 }

rcIpRipInterfaceTable OBJECT-TYPE
        SYNTAX          SEQUENCE OF RcIpRipInterfaceEntry
        MAX-ACCESS      not-accessible
        STATUS          current
        DESCRIPTION     "IP Rip Interface table"
        ::= { rcIpRipInterface 1 }

rcIpRipInterfaceEntry OBJECT-TYPE
        SYNTAX          RcIpRipInterfaceEntry
        MAX-ACCESS      not-accessible
        STATUS          current
        DESCRIPTION     "An entry of Ip Rip Interface Table."
        INDEX           { rcIpRipInterfaceAddress }
        ::= { rcIpRipInterfaceTable 1 }

RcIpRipInterfaceEntry ::=
        SEQUENCE {
                rcIpRipInterfaceAddress                IpAddress,
                rcIpRipInterfaceIfIndex                InterfaceIndex,
                rcIpRipInterfaceRipEnable              EnableValue,
                rcIpRipInterfaceAccDefRte              TruthValue,
                rcIpRipInterfaceAdvDefRte              TruthValue,
                rcIpRipInterfaceAutoAggregate          TruthValue,
                rcIpRipInterfaceCost                   Integer32,
                rcIpRipInterfaceListen                 TruthValue,
                rcIpRipInterfacePoison                 TruthValue,
                rcIpRipInterfaceSupply                 TruthValue,
                rcIpRipInterfaceTriggeredUpdate        TruthValue,
                rcIpRipInterfaceInPolicy               DisplayString,
                rcIpRipInterfaceOutPolicy              DisplayString,
                rcIpRipInterfaceProxyAnnounceFlag      TruthValue,
                rcIpRipInterfaceHolddown               INTEGER,
                rcIpRipInterfaceTimeout                INTEGER
        }

rcIpRipInterfaceAddress OBJECT-TYPE
        SYNTAX        IpAddress 
        MAX-ACCESS    read-only
        STATUS        current
        DESCRIPTION   "Ip Address"
        ::= { rcIpRipInterfaceEntry 1 }

rcIpRipInterfaceIfIndex OBJECT-TYPE
        SYNTAX        InterfaceIndex
        MAX-ACCESS    read-only
        STATUS        current
        DESCRIPTION   "Rip Interface If Index."
        ::= { rcIpRipInterfaceEntry 2 }

rcIpRipInterfaceRipEnable OBJECT-TYPE
        SYNTAX        EnableValue
        MAX-ACCESS    read-write
        STATUS        current
        DESCRIPTION   ""
        ::= { rcIpRipInterfaceEntry 3 }

rcIpRipInterfaceAccDefRte OBJECT-TYPE
        SYNTAX        TruthValue 
        MAX-ACCESS    read-write
        STATUS        current
        DESCRIPTION   ""
        ::= { rcIpRipInterfaceEntry 4 }

rcIpRipInterfaceAdvDefRte OBJECT-TYPE
        SYNTAX        TruthValue
        MAX-ACCESS    read-write
        STATUS        current
        DESCRIPTION   ""
        ::= { rcIpRipInterfaceEntry 5 }

rcIpRipInterfaceAutoAggregate OBJECT-TYPE
        SYNTAX        TruthValue 
        MAX-ACCESS    read-write
        STATUS        current
        DESCRIPTION   ""
        ::= { rcIpRipInterfaceEntry 6 }

rcIpRipInterfaceCost OBJECT-TYPE
        SYNTAX        Integer32
        MAX-ACCESS    read-write
        STATUS        current
        DESCRIPTION   ""
        ::= { rcIpRipInterfaceEntry 7 }

rcIpRipInterfaceListen OBJECT-TYPE
        SYNTAX        TruthValue 
        MAX-ACCESS    read-write
        STATUS        current
        DESCRIPTION   ""
        ::= { rcIpRipInterfaceEntry 8 }

rcIpRipInterfacePoison OBJECT-TYPE
        SYNTAX        TruthValue 
        MAX-ACCESS    read-write
        STATUS        current
        DESCRIPTION   ""
        ::= { rcIpRipInterfaceEntry 9 }

rcIpRipInterfaceSupply OBJECT-TYPE
        SYNTAX        TruthValue 
        MAX-ACCESS    read-write
        STATUS        current
        DESCRIPTION   ""
        ::= { rcIpRipInterfaceEntry 10 } 

rcIpRipInterfaceTriggeredUpdate OBJECT-TYPE
        SYNTAX        TruthValue 
        MAX-ACCESS    read-write
        STATUS        current
        DESCRIPTION   ""
        ::= { rcIpRipInterfaceEntry 11 }

rcIpRipInterfaceInPolicy OBJECT-TYPE
        SYNTAX        DisplayString
        MAX-ACCESS    read-write
        STATUS        current
        DESCRIPTION   ""
        ::= { rcIpRipInterfaceEntry 12 }

rcIpRipInterfaceOutPolicy OBJECT-TYPE
        SYNTAX        DisplayString
        MAX-ACCESS    read-write
        STATUS        current
        DESCRIPTION   ""
        ::= { rcIpRipInterfaceEntry 13 } 

rcIpRipInterfaceProxyAnnounceFlag OBJECT-TYPE
        SYNTAX        TruthValue 
        MAX-ACCESS    read-write
        STATUS        current
        DESCRIPTION   ""
        ::= { rcIpRipInterfaceEntry 14 }

rcIpRipInterfaceHolddown OBJECT-TYPE
        SYNTAX        INTEGER (0..360)
        MAX-ACCESS    read-write
        STATUS        current
        DESCRIPTION   "Used to indicate the rip holddown timer for this
                       interface"
        ::= { rcIpRipInterfaceEntry 15 }

rcIpRipInterfaceTimeout OBJECT-TYPE
        SYNTAX        INTEGER (15..259200)
        MAX-ACCESS    read-write
        STATUS        current
        DESCRIPTION   "Used to indicate the rip timeout interval for this
                       interface"
        ::= { rcIpRipInterfaceEntry 16 }

-- IP Timed Prune Table

rcIpMulticastTimedPruneTable OBJECT-TYPE
        SYNTAX          SEQUENCE OF RcIpMulticastTimedPruneEntry
        MAX-ACCESS      not-accessible
        STATUS          current
        DESCRIPTION     "This feature provides the ability for the user to 
                         create (S,G)  Forwarding Entries that would not be
                         pruned until a configurable timer expires. This feature 
                         is targeted for Passport 8600. Currently
                         the timer value is set to 0."
        ::= { rcIp 21 }

rcIpMulticastTimedPruneEntry OBJECT-TYPE
        SYNTAX          RcIpMulticastTimedPruneEntry
        MAX-ACCESS      not-accessible
        STATUS          current
        DESCRIPTION     "An entry of Ip Multicast Timed Prune Table."
        INDEX           { rcIpMulticastTimedPruneGroupAddress,
                          rcIpMulticastTimedPruneSourceAddress,
                          rcIpMulticastTimedPruneSrcSubnetMask }
        ::= { rcIpMulticastTimedPruneTable 1 }

RcIpMulticastTimedPruneEntry ::=
        SEQUENCE {
                rcIpMulticastTimedPruneGroupAddress    IpAddress,
                rcIpMulticastTimedPruneSourceAddress   IpAddress,
                rcIpMulticastTimedPruneSrcSubnetMask  IpAddress,
                rcIpMulticastTimedPruneAgingTimer     Integer32,
                rcIpMulticastTimedPruneTimeLeft       Integer32,
                rcIpMulticastTimedPruneLastActivity   TimeTicks,
                rcIpMulticastTimedPruneRowStatus      RowStatus
        }

rcIpMulticastTimedPruneGroupAddress OBJECT-TYPE
        SYNTAX        IpAddress
        MAX-ACCESS    read-write
        STATUS        current
        DESCRIPTION   "This field indicates the IP Multicast Group 
                       Address associated with the IP multicast stream."
        ::= { rcIpMulticastTimedPruneEntry 1 }

rcIpMulticastTimedPruneSourceAddress OBJECT-TYPE
        SYNTAX        IpAddress
        MAX-ACCESS    read-write
        STATUS        current
        DESCRIPTION   "This is the Source Subnet IP address of the 
                       sender of the IP multicast stream."
        ::= { rcIpMulticastTimedPruneEntry 2 }

rcIpMulticastTimedPruneSrcSubnetMask OBJECT-TYPE
        SYNTAX        IpAddress
        MAX-ACCESS    read-write
        STATUS        current
        DESCRIPTION   "This is the Source Subnet Mask IP address of 
                       the sender of the IP multicast stream."
        ::= { rcIpMulticastTimedPruneEntry 3 }

rcIpMulticastTimedPruneAgingTimer OBJECT-TYPE
        SYNTAX        Integer32
        MAX-ACCESS    read-write
        STATUS        current
        DESCRIPTION   "This field represents the amount of time 
                       (in minutes) this timed prune entry will be 
                       kept in the forwarding table when there are no 
                       more receivers. After this timer expires, this 
                       timed prune entry would be treated as a normal 
                       DVMRP/PIM forwarding entry. Aging Timer value of 
                       0 (infinite time) indicates this timed prune entry 
                       will not be deleted even when there are no 
                       more receivers."
        DEFVAL        { 5 }
        ::= { rcIpMulticastTimedPruneEntry 4 }

rcIpMulticastTimedPruneTimeLeft OBJECT-TYPE
        SYNTAX        Integer32
        MAX-ACCESS    read-only
        STATUS        current
        DESCRIPTION   "This read-only field represents the remaining time 
                       for which this timed prune entry will be kept in
                       the forwarding table. After this timer expires, 
                       this timed prune entry would be treated as a normal 
                       DVMRP/PIM forwarding entry. 0 in this field indicates 
                       that this entry would not be aged out."
        ::= { rcIpMulticastTimedPruneEntry 5 }

rcIpMulticastTimedPruneLastActivity OBJECT-TYPE
        SYNTAX        TimeTicks
        MAX-ACCESS    read-only
        STATUS        current
        DESCRIPTION   "This read-only field represents the actual time since 
                       the traffic has come from this Source, Group pair."
        ::= { rcIpMulticastTimedPruneEntry 6 }

rcIpMulticastTimedPruneRowStatus OBJECT-TYPE
        SYNTAX        RowStatus
        MAX-ACCESS    read-write
        STATUS        current
        DESCRIPTION   "row status"
        ::= { rcIpMulticastTimedPruneEntry 7 }


-- ICMP Route discovery parameters

rcIpConfIcmpRdiscTable OBJECT-TYPE
        SYNTAX        SEQUENCE OF RcIpConfIcmpRdiscEntry
        MAX-ACCESS    not-accessible
        STATUS        current
        DESCRIPTION   "A table used to maintain ICMP Route discovery information
                      for a particular interface."
    ::= { rcIp 22 } 

rcIpConfIcmpRdiscEntry OBJECT-TYPE
        SYNTAX        RcIpConfIcmpRdiscEntry
        MAX-ACCESS    not-accessible
        STATUS        current
        DESCRIPTION   "Entry containing ICMP Rdisc information.  An entry is
                      automatically created in this table when routing
                      is enabled for an interface -or- when an ip address
                      is configured on an interface."
        INDEX      { rcIpConfIcmpRdiscIfIndex }
        ::= { rcIpConfIcmpRdiscTable 1 }

RcIpConfIcmpRdiscEntry ::= SEQUENCE {
        rcIpConfIcmpRdiscIfIndex            INTEGER,
        rcIpConfIcmpRdiscAdvAddress         IpAddress,
        rcIpConfIcmpRdiscAdvFlag            TruthValue,
        rcIpConfIcmpRdiscAdvLifetime        INTEGER,
        rcIpConfIcmpRdiscMaxAdvInterval     INTEGER,
        rcIpConfIcmpRdiscMinAdvInterval     INTEGER,
       rcIpConfIcmpRdiscPreferenceLevel     INTEGER
}

rcIpConfIcmpRdiscIfIndex OBJECT-TYPE
        SYNTAX          INTEGER (0..65535)
        MAX-ACCESS      read-only
        STATUS          current
        DESCRIPTION     "An unique value to identify a physical
                        interface or a logical interface (VLAN)."
        ::= { rcIpConfIcmpRdiscEntry 1 }

rcIpConfIcmpRdiscAdvAddress OBJECT-TYPE
         SYNTAX     IpAddress
         MAX-ACCESS read-write
         STATUS     current
         DESCRIPTION "Advertisement address to which the route discovery
                      advertisements transmitted on this interface."
         ::= { rcIpConfIcmpRdiscEntry 2 }

rcIpConfIcmpRdiscAdvFlag OBJECT-TYPE
         SYNTAX     TruthValue
         MAX-ACCESS read-write
         STATUS     current
         DESCRIPTION "Flag to indicate whether or not the address is to
                     be advertised on this interface."
         ::= { rcIpConfIcmpRdiscEntry 3 }

rcIpConfIcmpRdiscAdvLifetime OBJECT-TYPE
         SYNTAX     INTEGER (4..9000)
         MAX-ACCESS read-write
         STATUS     current
         DESCRIPTION "The value to be placed in the lifetime field of
                     Router Advertisements sent from the interface."
         ::= { rcIpConfIcmpRdiscEntry 4 }

rcIpConfIcmpRdiscMaxAdvInterval OBJECT-TYPE
         SYNTAX     INTEGER (4..1800)
         MAX-ACCESS read-write
         STATUS     current
         DESCRIPTION "The maximum time allowed between sending
                     Router Advertisements from this interface."
         ::= { rcIpConfIcmpRdiscEntry 5 }

rcIpConfIcmpRdiscMinAdvInterval OBJECT-TYPE
         SYNTAX     INTEGER (3..1800)
         MAX-ACCESS read-write
         STATUS     current
         DESCRIPTION "The minimum time allowed between sending
                      Router Advertisements from this interface."
         ::= { rcIpConfIcmpRdiscEntry 6 }


rcIpConfIcmpRdiscPreferenceLevel OBJECT-TYPE
         SYNTAX     INTEGER (-2147483648..2147483647)
         MAX-ACCESS read-write
         STATUS     current
         DESCRIPTION "Preferability of the router address as a default
                      Router "
         ::= { rcIpConfIcmpRdiscEntry 7 }


--IP Mcast Software Forwarding Group

rcIpMulticastSoftwareForwarding OBJECT IDENTIFIER ::= { rcIp 23 } 

rcIpMulticastSoftwareForwardingEnable OBJECT-TYPE
        SYNTAX        TruthValue
        MAX-ACCESS    read-write
        STATUS        current
        DESCRIPTION   "Enable/Disable multicast software
forwarding."
        DEFVAL { false }
        ::= { rcIpMulticastSoftwareForwarding 1 }

--IP Mroute-Hw

rcIpMrouteHw OBJECT IDENTIFIER       ::= { rcIp 24 }

rcIpMrouteHwTable OBJECT-TYPE
        SYNTAX        SEQUENCE OF RcIpMrouteHwEntry
        MAX-ACCESS    not-accessible
        STATUS        current
        DESCRIPTION   "The (conceptual) table containing hardware entries of
                       multicast routing information for all the Group Address."
        ::= { rcIpMrouteHw 1 }

rcIpMrouteHwEntry OBJECT-TYPE
        SYNTAX        RcIpMrouteHwEntry
        MAX-ACCESS    not-accessible
        STATUS        current
        DESCRIPTION   "An entry (conceptual row) containing hardware entries of
	                    multicast routing information for a particular Group 
		                 Address."
        INDEX         { rcIpMrouteHwGroupAddress,
                        rcIpMrouteHwSubnet, 
                        rcIpMrouteHwInvlan,
                        rcIpMrouteHwIndex }
        ::= { rcIpMrouteHwTable 1 }

RcIpMrouteHwEntry ::=
        SEQUENCE {
                rcIpMrouteHwGroupAddress        IpAddress,
                rcIpMrouteHwSubnet              IpAddress,
                rcIpMrouteHwInvlan              RcVlanIdOrNone,
                rcIpMrouteHwPruned              TruthValue,
                rcIpMrouteHwIndex               Integer32
        }

rcIpMrouteHwGroupAddress OBJECT-TYPE
        SYNTAX        IpAddress
        MAX-ACCESS    read-only
        STATUS        current
        DESCRIPTION   "The IP multicast group address for which this entry
                       contains multicast routing information."
        ::= { rcIpMrouteHwEntry 1 }

rcIpMrouteHwSubnet OBJECT-TYPE
        SYNTAX        IpAddress
        MAX-ACCESS    read-only
        STATUS        current
        DESCRIPTION   "The network address from where the source is sending the
                       stream of traffic for which this entry contains multicast
                       routing information."
        ::= { rcIpMrouteHwEntry 2 }

rcIpMrouteHwInvlan OBJECT-TYPE
        SYNTAX        RcVlanIdOrNone
        MAX-ACCESS    read-only
        STATUS        current
        DESCRIPTION   "The Ingress vlan Id from where the traffic is coming for
                       which this entry contains multicast routing information."
        ::= { rcIpMrouteHwEntry 3 }

rcIpMrouteHwPruned OBJECT-TYPE
        SYNTAX        TruthValue
        MAX-ACCESS    read-only
        STATUS        current
        DESCRIPTION   "This is to show weather the entry containing multicast
                       routing information has received Prune message or not."
        ::= { rcIpMrouteHwEntry  4 }

rcIpMrouteHwIndex OBJECT-TYPE
        SYNTAX        Integer32 (0..2147483647)
        MAX-ACCESS    read-only
        STATUS        current
        DESCRIPTION   "This Index value keep tracks of the hardware record that
                       has been accessed for displaying the entry containing                           multicast routing information."
        ::= { rcIpMrouteHwEntry  5 }

rcIpMrouteHwPrunesTable OBJECT-TYPE
        SYNTAX        SEQUENCE OF RcIpMrouteHwPrunesEntry
        MAX-ACCESS    not-accessible
        STATUS        current
        DESCRIPTION   "The (conceptual) table containing prune entries of
                       multicast routing information for the Group Address."
        ::= { rcIpMrouteHw 2 }

rcIpMrouteHwPrunesEntry OBJECT-TYPE
        SYNTAX        RcIpMrouteHwPrunesEntry
        MAX-ACCESS    not-accessible
        STATUS        current
        DESCRIPTION   "An entry (conceptual row) containing prune entries of
                       multicast routing information for a particular Group 
                       Address."
        INDEX         { rcIpMrouteHwPrunesGroupAddress,
                        rcIpMrouteHwPrunesSubnet,
                        rcIpMrouteHwPrunesInvlan,
                        rcIpMrouteHwPrunesNeighbor }
        ::= { rcIpMrouteHwPrunesTable 1 }

RcIpMrouteHwPrunesEntry ::=
        SEQUENCE {
                rcIpMrouteHwPrunesGroupAddress  IpAddress,
                rcIpMrouteHwPrunesSubnet        IpAddress,
                rcIpMrouteHwPrunesInvlan        RcVlanIdOrNone,
                rcIpMrouteHwPrunesNeighbor      IpAddress,
                rcIpMrouteHwPrunesTimer         Integer32
        }

rcIpMrouteHwPrunesGroupAddress OBJECT-TYPE
        SYNTAX        IpAddress
        MAX-ACCESS    read-only
        STATUS        current
        DESCRIPTION   "The IP multicast group address for which this entry
                       contains multicast routing information."
        ::= { rcIpMrouteHwPrunesEntry 1 }

rcIpMrouteHwPrunesSubnet OBJECT-TYPE
        SYNTAX        IpAddress
        MAX-ACCESS    read-only
        STATUS        current
        DESCRIPTION   "The network address from where the source is sending the
                       stream of traffic for which this entry contains 
                       multicast routing information."
        ::= { rcIpMrouteHwPrunesEntry 2 }

rcIpMrouteHwPrunesInvlan OBJECT-TYPE
        SYNTAX        RcVlanIdOrNone
        MAX-ACCESS    read-only
        STATUS        current
        DESCRIPTION   "The Ingress vlan Id from where the traffic is coming for
                       which this entry contains multicast routing information."
        ::= { rcIpMrouteHwPrunesEntry 3 }

rcIpMrouteHwPrunesNeighbor OBJECT-TYPE
        SYNTAX        IpAddress
        MAX-ACCESS    read-only
        STATUS        current
        DESCRIPTION   "The IpAddress from where the Prune message has been
                       received."
        ::= { rcIpMrouteHwPrunesEntry 4 }

rcIpMrouteHwPrunesTimer OBJECT-TYPE
        SYNTAX        Integer32
        MAX-ACCESS    read-only
        STATUS        current
        DESCRIPTION   "This is to show how much time is left for this particular
                       entry containing multicast routing information during 
                       which  the graft message can be sent."
        ::= { rcIpMrouteHwPrunesEntry 5 }

rcIpMrouteHwSourcesTable OBJECT-TYPE
        SYNTAX        SEQUENCE OF RcIpMrouteHwSourcesEntry
        MAX-ACCESS    not-accessible
        STATUS        current
        DESCRIPTION   "The (conceptual) table containing source entries of
                       multicast routing information for the Group Address."
        ::= { rcIpMrouteHw 3 }

rcIpMrouteHwSourcesEntry OBJECT-TYPE
        SYNTAX        RcIpMrouteHwSourcesEntry
        MAX-ACCESS    not-accessible
        STATUS        current
        DESCRIPTION   "An entry (conceptual row) containing source entries of
                       multicast routing information for a particular Group 
                       Address."
        INDEX         { rcIpMrouteHwSourcesGroupAddress,
                        rcIpMrouteHwSourcesSubnet,
                        rcIpMrouteHwSourcesInvlan,
                        rcIpMrouteHwSourcesAddress }
        ::= { rcIpMrouteHwSourcesTable 1 }

RcIpMrouteHwSourcesEntry ::=
        SEQUENCE {
                rcIpMrouteHwSourcesGroupAddress  IpAddress,
                rcIpMrouteHwSourcesSubnet        IpAddress,
                rcIpMrouteHwSourcesInvlan        RcVlanIdOrNone,
                rcIpMrouteHwSourcesAddress       IpAddress,
                rcIpMrouteHwSourcesIngressPort   PortSet
        }

rcIpMrouteHwSourcesGroupAddress OBJECT-TYPE
        SYNTAX        IpAddress
        MAX-ACCESS    read-only
        STATUS        current
        DESCRIPTION   "The IP multicast group address for which this entry
                       contains multicast routing information."
        ::= { rcIpMrouteHwSourcesEntry 1 }

rcIpMrouteHwSourcesSubnet OBJECT-TYPE
        SYNTAX        IpAddress
        MAX-ACCESS    read-only
        STATUS        current
        DESCRIPTION   "The network address from where the source is sending the
                       stream of traffic for which this entry contains 
                       multicast routing information."
        ::= { rcIpMrouteHwSourcesEntry 2 }

rcIpMrouteHwSourcesInvlan OBJECT-TYPE
        SYNTAX        RcVlanIdOrNone
        MAX-ACCESS    read-only
        STATUS        current
        DESCRIPTION   "The Ingress vlan Id from where the traffic is coming for
                       which this entry contains multicast routing information."
        ::= { rcIpMrouteHwSourcesEntry 3 }

rcIpMrouteHwSourcesAddress OBJECT-TYPE
        SYNTAX        IpAddress
        MAX-ACCESS    read-only
        STATUS        current
        DESCRIPTION   "The Source Address from where the stream of traffic is                          reaching the corresponding Group Address for which this 
                       entry contains multicast routing information."
        ::= { rcIpMrouteHwSourcesEntry 4 }

rcIpMrouteHwSourcesIngressPort OBJECT-TYPE
        SYNTAX        PortSet
        MAX-ACCESS    read-only
        STATUS        current
        DESCRIPTION   "The Ingress vlan ports from where the traffic is coming,
                       for which this entry contains multicast routing 
                       information."
        ::= { rcIpMrouteHwSourcesEntry 5 }

rcIpMrouteHwEgressVlansTable OBJECT-TYPE
        SYNTAX        SEQUENCE OF RcIpMrouteHwEgressVlansEntry
        MAX-ACCESS    not-accessible
        STATUS        current
        DESCRIPTION   "The (conceptual) table containing egress vlan entries of
                       multicast routing information for the Group Address."
        ::= { rcIpMrouteHw 4 }

rcIpMrouteHwEgressVlansEntry OBJECT-TYPE
        SYNTAX        RcIpMrouteHwEgressVlansEntry
        MAX-ACCESS    not-accessible
        STATUS        current
        DESCRIPTION   "An entry (conceptual row) containing egress vlan entries
                       of multicast routing information for a particular Group 
                       Address."
        INDEX         { rcIpMrouteHwEgressVlansGroupAddress,
                        rcIpMrouteHwEgressVlansSubnet,
                        rcIpMrouteHwEgressVlansInvlan,
                        rcIpMrouteHwEgressVlansId,
                        rcIpMrouteHwEgressVlansIndex }
        ::= { rcIpMrouteHwEgressVlansTable 1 }

RcIpMrouteHwEgressVlansEntry ::=
        SEQUENCE {
                rcIpMrouteHwEgressVlansGroupAddress IpAddress,
                rcIpMrouteHwEgressVlansSubnet       IpAddress,
                rcIpMrouteHwEgressVlansInvlan       RcVlanIdOrNone,
                rcIpMrouteHwEgressVlansId           RcVlanIdOrNone,
                rcIpMrouteHwEgressVlansPorts        PortSet,
                rcIpMrouteHwEgressVlansIndex        Integer32
        }

rcIpMrouteHwEgressVlansGroupAddress OBJECT-TYPE
        SYNTAX        IpAddress
        MAX-ACCESS    read-only
        STATUS        current
        DESCRIPTION   "The IP multicast group address for which this entry 
                       contains multicast routing information."
        ::= { rcIpMrouteHwEgressVlansEntry 1 }

rcIpMrouteHwEgressVlansSubnet OBJECT-TYPE
        SYNTAX        IpAddress
        MAX-ACCESS    read-only
        STATUS        current
        DESCRIPTION   "The network address from where the source is sending the
                       stream of traffic for which this entry contains 
                       multicast routing information."
        ::= { rcIpMrouteHwEgressVlansEntry 2 }

rcIpMrouteHwEgressVlansInvlan OBJECT-TYPE
        SYNTAX        RcVlanIdOrNone
        MAX-ACCESS    read-only
        STATUS        current
        DESCRIPTION   "The Ingress vlan Id from where the traffic is coming for
                       which this entry contains multicast routing information."
        ::= { rcIpMrouteHwEgressVlansEntry 3 }

rcIpMrouteHwEgressVlansId OBJECT-TYPE
        SYNTAX        RcVlanIdOrNone
        MAX-ACCESS    read-only
        STATUS        current
        DESCRIPTION   "The Egress vlan Id from where the traffic is going out
                       for which this entry contains multicast routing
                       information"
        ::= { rcIpMrouteHwEgressVlansEntry 4 }

rcIpMrouteHwEgressVlansPorts OBJECT-TYPE
        SYNTAX        PortSet
        MAX-ACCESS    read-only
        STATUS        current
        DESCRIPTION   "he Egress vlan ports from where the traffic is going out
                       for which this entry contains multicast routing 
                       information."
        ::= { rcIpMrouteHwEgressVlansEntry 5 }

rcIpMrouteHwEgressVlansIndex OBJECT-TYPE
        SYNTAX        Integer32 (0..2147483647)
        MAX-ACCESS    read-only
        STATUS        current
        DESCRIPTION   "This Index value keep tracks of the hardware record that
                       has been accessed for displaying the entry containing 
                       multicast routing information."
        ::= { rcIpMrouteHwEgressVlansEntry  6 }


-- IP Resource Usage Global

rcIpResourceUsage OBJECT IDENTIFIER       ::= { rcIp 25 }

rcIpResourceUsageGlobal OBJECT IDENTIFIER ::= { rcIpResourceUsage 1 }

rcIpResourceUsageGlobalIngressRecInUse OBJECT-TYPE
        SYNTAX        INTEGER (0..32767)
        MAX-ACCESS    read-only
        STATUS        current
        DESCRIPTION   "Used to get the Ingress Record Usage in the switch.
                       (S-G usage)."
        ::= { rcIpResourceUsageGlobal 1 }

rcIpResourceUsageGlobalEgressRecInUse OBJECT-TYPE
        SYNTAX        INTEGER (0..32767)
        MAX-ACCESS    read-only
        STATUS        current
        DESCRIPTION   "Used to get the Egress Record Usage in the switch
                       (pepstream count)."
        ::= { rcIpResourceUsageGlobal 2 }

rcIpResourceUsageGlobalIngressThreshold OBJECT-TYPE
        SYNTAX        INTEGER (0..32767)
        MAX-ACCESS    read-write
        STATUS        current
        DESCRIPTION   "Used to get the threshold count for Ingress records."
        DEFVAL        { 0 }
        ::= { rcIpResourceUsageGlobal 3 }

rcIpResourceUsageGlobalEgressThreshold OBJECT-TYPE
        SYNTAX        INTEGER (0..32767)
        MAX-ACCESS    read-write
        STATUS        current
        DESCRIPTION   "Used to get threshold count for egress records."
        DEFVAL        { 0 }
        ::= { rcIpResourceUsageGlobal  4 }

rcIpResourceUsageGlobalSendTrapAndLog OBJECT-TYPE
        SYNTAX        EnableValue
        MAX-ACCESS    read-write
        STATUS        current
        DESCRIPTION   "A means of alerting the user. If this bool is set,
                       a message will be send to console and also a
                       duReport will be logged."
        DEFVAL        { disable }
        ::= { rcIpResourceUsageGlobal  5 }

rcIpResourceUsageGlobalSendTrapOnly OBJECT-TYPE
        SYNTAX        EnableValue
        MAX-ACCESS    read-write
        STATUS        current
        DESCRIPTION   "A means of alerting the user. If this bool is set,
                       a message will be send to console."
        DEFVAL        { disable }
        ::= { rcIpResourceUsageGlobal  6 }

rcIpResourceUsageGlobalLogMsgOnly OBJECT-TYPE
        SYNTAX        EnableValue
        MAX-ACCESS    read-write
        STATUS        current
        DESCRIPTION   "A means of alerting the user.If this bool is set,
                       a duReport will be logged."
        DEFVAL        { disable }
        ::= { rcIpResourceUsageGlobal  7 }


rcIpRsmlt OBJECT IDENTIFIER       ::= { rcIp 26 }

rcIpRsmltGlobal OBJECT IDENTIFIER ::= { rcIpRsmlt 1 }


rcIpRsmltEdgeSupportEnable OBJECT-TYPE
        SYNTAX        TruthValue
        MAX-ACCESS    read-write
        STATUS        current
        DESCRIPTION   "Used to enable/disable RSMLT Edge Support feature"
        DEFVAL        { false }
        ::= { rcIpRsmltGlobal 2}

rcIpRsmltOperTable OBJECT-TYPE 
        SYNTAX          SEQUENCE OF RcIpRsmltOperEntry
        MAX-ACCESS      not-accessible 
        STATUS          current 
        DESCRIPTION     "Route Smlt Table"
    ::= { rcIpRsmlt 2 }

rcIpRsmltOperEntry OBJECT-TYPE
        SYNTAX        	RcIpRsmltOperEntry
        MAX-ACCESS       not-accessible
        STATUS        	current
        DESCRIPTION   	"An entry of Ip As Path Access List Table."
        INDEX         	{ rcIpRsmltOperIfIndex }
        ::= { rcIpRsmltOperTable 1 }
 
RcIpRsmltOperEntry ::=
        SEQUENCE {
                rcIpRsmltOperIfIndex                 InterfaceIndex,
                rcIpRsmltOperAdminStatus             TruthValue,
                rcIpRsmltOperHoldDownTimer           INTEGER,
                rcIpRsmltOperHoldDownTimeRemaining   INTEGER,
                rcIpRsmltOperHoldUpTimer             INTEGER,
                rcIpRsmltOperHoldUpTimeRemaining     INTEGER,
                rcIpRsmltOperIpAddr                  IpAddress,
                rcIpRsmltOperOperStatus              INTEGER,
                rcIpRsmltOperSmltId                  IdList,
                rcIpRsmltOperVlanId                  INTEGER,
                rcIpRsmltOperMacAddr                 MacAddress,
                rcIpRsmltOperRowStatus               RowStatus,
                rcIpRsmltOperVrfId                   VrfIdentifier,
                rcIpRsmltOperVrfName                 SnmpAdminString
        }
 
rcIpRsmltOperIfIndex OBJECT-TYPE
        SYNTAX        InterfaceIndex
        MAX-ACCESS    read-only
        STATUS        current
        DESCRIPTION   "Route Smlt Oper IfIndex."
        ::= { rcIpRsmltOperEntry 1 }

rcIpRsmltOperAdminStatus OBJECT-TYPE
        SYNTAX        TruthValue
        MAX-ACCESS    read-write
        STATUS        current
        DESCRIPTION   "is a enable/disable flag."
        DEFVAL        { false }
        ::= { rcIpRsmltOperEntry 2 }

rcIpRsmltOperHoldDownTimer OBJECT-TYPE
        SYNTAX        INTEGER (0..3600)
        MAX-ACCESS    read-write
        STATUS        current
        DESCRIPTION   "Timer value, the range of value is from 0 to 3600."
        DEFVAL        { 0 }
        ::= { rcIpRsmltOperEntry 3 }

rcIpRsmltOperHoldDownTimeRemaining OBJECT-TYPE
        SYNTAX        INTEGER (0..3600)
        MAX-ACCESS    read-only
        STATUS        current
        DESCRIPTION   "The time value that indicate how much time
                       remaining of HoldDownTimer."
        DEFVAL        { 0 }
        ::= { rcIpRsmltOperEntry  4 }

rcIpRsmltOperHoldUpTimer OBJECT-TYPE
        SYNTAX        INTEGER (0..3600 | 9999)
        MAX-ACCESS    read-write
        STATUS        current
        DESCRIPTION   "The range of value 0 to 3600 or 9999. 9999 means
                       infinity."
        DEFVAL        { 0 }
        ::= { rcIpRsmltOperEntry  5 }

rcIpRsmltOperHoldUpTimeRemaining OBJECT-TYPE
        SYNTAX        INTEGER (0..3600 | 9999)
        MAX-ACCESS    read-only
        STATUS        current
        DESCRIPTION   "The time value that indicate how much time
                       remaining of HoldUpTimer."
        DEFVAL        { 0 }
        ::= { rcIpRsmltOperEntry  6 }

rcIpRsmltOperIpAddr OBJECT-TYPE
        SYNTAX        IpAddress
        MAX-ACCESS    read-only
        STATUS        current
        DESCRIPTION   "IP Interface with RSMLT on."
        DEFVAL   { '00000000'H }    -- 0.0.0.0
        ::= { rcIpRsmltOperEntry  7 }

rcIpRsmltOperOperStatus OBJECT-TYPE
        SYNTAX        INTEGER {
                        up(1),
                        down(2)
                      }
        MAX-ACCESS    read-only
        STATUS        current
        DESCRIPTION   "The operation status of Rsmlt, up or down."
        DEFVAL        { down }
        ::= { rcIpRsmltOperEntry  8 }

rcIpRsmltOperSmltId OBJECT-TYPE
        SYNTAX        IdList
        MAX-ACCESS    read-only
        STATUS        current
        DESCRIPTION   "The id range for SMLT is 1-32."
        ::= { rcIpRsmltOperEntry  9 }

rcIpRsmltOperVlanId OBJECT-TYPE
        SYNTAX        INTEGER (1..4084)
        MAX-ACCESS    read-only
        STATUS        current
        DESCRIPTION   "Vlan id."
        ::= { rcIpRsmltOperEntry  11 }

rcIpRsmltOperMacAddr OBJECT-TYPE
        SYNTAX        MacAddress
        MAX-ACCESS    read-only
        STATUS        current
        DESCRIPTION   "Mac Address."
        ::= { rcIpRsmltOperEntry  12 }

rcIpRsmltOperRowStatus OBJECT-TYPE
        SYNTAX        RowStatus
        MAX-ACCESS    read-write
        STATUS        current
        DESCRIPTION   "Row Status."
        ::= { rcIpRsmltOperEntry  13 }

rcIpRsmltOperVrfId OBJECT-TYPE
        SYNTAX        VrfIdentifier 
        MAX-ACCESS    read-only
        STATUS        current
        DESCRIPTION   "Indicates the Virtual Router to which the RSMLT
                       Oper instance belongs."
        ::= { rcIpRsmltOperEntry  14 }

rcIpRsmltOperVrfName OBJECT-TYPE
        SYNTAX        SnmpAdminString (SIZE (0..32)) 
        MAX-ACCESS    read-only
        STATUS        current
        DESCRIPTION   "Name of the Virtual Router to which the RSMLT Oper
                       instance belongs."
        ::= { rcIpRsmltOperEntry  15 }

-- Route Smlt Peer Table

rcIpRsmltPeerTable OBJECT-TYPE 
        SYNTAX          SEQUENCE OF RcIpRsmltPeerEntry
        MAX-ACCESS      not-accessible 
        STATUS          current 
        DESCRIPTION     "Route Smlt Table"
    ::= { rcIpRsmlt 3 }

rcIpRsmltPeerEntry OBJECT-TYPE
        SYNTAX        	RcIpRsmltPeerEntry
        MAX-ACCESS       not-accessible
        STATUS        	current
        DESCRIPTION   	"An entry of Ip As Path Access List Table."
        INDEX         	{ rcIpRsmltPeerIfIndex }
        ::= { rcIpRsmltPeerTable 1 }
 
RcIpRsmltPeerEntry ::=
        SEQUENCE {
                rcIpRsmltPeerIfIndex                 InterfaceIndex,
                rcIpRsmltPeerAdminStatus             TruthValue,
                rcIpRsmltPeerHoldDownTimer           INTEGER,
                rcIpRsmltPeerHoldDownTimeRemaining   INTEGER,
                rcIpRsmltPeerHoldUpTimer             INTEGER,
                rcIpRsmltPeerHoldUpTimeRemaining     INTEGER,
                rcIpRsmltPeerIpAddr                  IpAddress,
                rcIpRsmltPeerOperStatus              INTEGER,
                rcIpRsmltPeerSmltId                  IdList,
                rcIpRsmltPeerVlanId                  INTEGER,
                rcIpRsmltPeerMacAddr                 MacAddress,
                rcIpRsmltPeerVrfId                   VrfIdentifier,
                rcIpRsmltPeerVrfName                 SnmpAdminString
        }
 
rcIpRsmltPeerIfIndex OBJECT-TYPE
        SYNTAX        InterfaceIndex
        MAX-ACCESS    read-only
        STATUS        current
        DESCRIPTION   "Route Smlt Oper IfIndex."
        ::= { rcIpRsmltPeerEntry 1 }

rcIpRsmltPeerAdminStatus OBJECT-TYPE
        SYNTAX        TruthValue
        MAX-ACCESS    read-only
        STATUS        current
        DESCRIPTION   "is a enable/disable flag."
        ::= { rcIpRsmltPeerEntry 2 }

rcIpRsmltPeerHoldDownTimer OBJECT-TYPE
        SYNTAX        INTEGER (0..3600)
        MAX-ACCESS    read-only
        STATUS        current
        DESCRIPTION   "Timer value, the range of value is from 0 to 3600."
        DEFVAL        { 0 }
        ::= { rcIpRsmltPeerEntry 3 }

rcIpRsmltPeerHoldDownTimeRemaining OBJECT-TYPE
        SYNTAX        INTEGER (0..3600)
        MAX-ACCESS    read-only
        STATUS        current
        DESCRIPTION   "The time value that indicate how much time
                       remaining of HoldDownTimer."
        DEFVAL        { 0 }
        ::= { rcIpRsmltPeerEntry  4 }

rcIpRsmltPeerHoldUpTimer OBJECT-TYPE
        SYNTAX        INTEGER (0..3600 | 9999)
        MAX-ACCESS    read-only
        STATUS        current
        DESCRIPTION   "The range of value 0 to 3600 or 9999. 9999 means
                       infinity."
        DEFVAL        { 0 }
        ::= { rcIpRsmltPeerEntry  5 }

rcIpRsmltPeerHoldUpTimeRemaining OBJECT-TYPE
        SYNTAX        INTEGER (0..3600 | 9999)
        MAX-ACCESS    read-only
        STATUS        current
        DESCRIPTION   "The time value that indicate how much time
                       remaining of HoldUpTimer."
        DEFVAL        { 0 }
        ::= { rcIpRsmltPeerEntry  6 }

rcIpRsmltPeerIpAddr OBJECT-TYPE
        SYNTAX        IpAddress
        MAX-ACCESS    read-only
        STATUS        current
        DESCRIPTION   "IP Interface with RSMLT on."
        DEFVAL   { '00000000'H }    -- 0.0.0.0
        ::= { rcIpRsmltPeerEntry  7 }

rcIpRsmltPeerOperStatus OBJECT-TYPE
        SYNTAX        INTEGER {
                        up(1),
                        down(2)
                      }
        MAX-ACCESS    read-only
        STATUS        current
        DESCRIPTION   "The operation status of Rsmlt, up or down."
        DEFVAL        { down }
        ::= { rcIpRsmltPeerEntry  8 }

rcIpRsmltPeerSmltId OBJECT-TYPE
        SYNTAX        IdList
        MAX-ACCESS    read-only
        STATUS        current
        DESCRIPTION   "The id range for SMLT is 1-32."
        ::= { rcIpRsmltPeerEntry  9 }

rcIpRsmltPeerVlanId OBJECT-TYPE
        SYNTAX        INTEGER (1..4084)
        MAX-ACCESS    read-only
        STATUS        current
        DESCRIPTION   "Vlan id."
        ::= { rcIpRsmltPeerEntry  11 }

rcIpRsmltPeerMacAddr OBJECT-TYPE
        SYNTAX        MacAddress
        MAX-ACCESS    read-only
        STATUS        current
        DESCRIPTION   "Mac Address."
        ::= { rcIpRsmltPeerEntry  12 }

rcIpRsmltPeerVrfId OBJECT-TYPE
        SYNTAX        VrfIdentifier
        MAX-ACCESS    read-only
        STATUS        current
        DESCRIPTION   "Indicates the Virtual Router to which the RSMLT Peer
                       instance belongs."
        ::= { rcIpRsmltPeerEntry  13 }

rcIpRsmltPeerVrfName OBJECT-TYPE
        SYNTAX        SnmpAdminString (SIZE (0..32))
        MAX-ACCESS    read-only
        STATUS        current
        DESCRIPTION   "Name of the Virtual Router to which the RSMLT Peer
                       instance belongs."
        ::= { rcIpRsmltPeerEntry 14 }

rcIpRsmltEdgePeerTable OBJECT-TYPE
        SYNTAX        SEQUENCE OF RcIpRsmltEdgePeerEntry
        MAX-ACCESS    not-accessible
        STATUS        current
        DESCRIPTION   "RSMLT Edge Support Peer Info table. This 
                      table consists of the RSMLT Peers for which 
                      the switch will act as a PeerForwarder."
        ::= { rcIpRsmlt 4 }

rcIpRsmltEdgePeerEntry OBJECT-TYPE
        SYNTAX        RcIpRsmltEdgePeerEntry
        MAX-ACCESS    not-accessible
        STATUS        current
        DESCRIPTION   "RSMLT Edge Support Peer Info Entry"
        INDEX         { rcIpRsmltEdgeVlanId }
        ::= { rcIpRsmltEdgePeerTable 1 }

RcIpRsmltEdgePeerEntry ::=
        SEQUENCE { 
                rcIpRsmltEdgeVlanId         RcVlanIdOrNone,
                rcIpRsmltEdgePeerIpAddress  IpAddress,
                rcIpRsmltEdgePeerMacAddress MacAddress,
                rcIpRsmltEdgePeerVrfId      VrfIdentifier,
                rcIpRsmltEdgePeerVrfName    SnmpAdminString
        }

rcIpRsmltEdgeVlanId  OBJECT-TYPE
        SYNTAX        RcVlanIdOrNone
        MAX-ACCESS    not-accessible
        STATUS        current
        DESCRIPTION   "A value that uniquely identifies the Virtual LAN
                      associated with this entry."
        ::= { rcIpRsmltEdgePeerEntry 1}

rcIpRsmltEdgePeerIpAddress OBJECT-TYPE
        SYNTAX        IpAddress
        MAX-ACCESS    read-only
        STATUS        current
        DESCRIPTION   "IP address of the Peer RSMLT Interface."
        ::= { rcIpRsmltEdgePeerEntry 2}

rcIpRsmltEdgePeerMacAddress OBJECT-TYPE
        SYNTAX        MacAddress
        MAX-ACCESS    read-only
        STATUS        current
        DESCRIPTION   "The MAC address of the Peer RSMLT interface."
        ::= { rcIpRsmltEdgePeerEntry 3}

rcIpRsmltEdgePeerVrfId OBJECT-TYPE
        SYNTAX        VrfIdentifier
        MAX-ACCESS    read-only
        STATUS        current
        DESCRIPTION   "Indicates the Virtual Router to which the RSMLT Edge Peer
                       instance belongs."
        ::= { rcIpRsmltEdgePeerEntry 4 }

rcIpRsmltEdgePeerVrfName OBJECT-TYPE
        SYNTAX        SnmpAdminString (SIZE (0..32))
        MAX-ACCESS    read-only
        STATUS        current
        DESCRIPTION   "Name of the Virtual Router to which the RSMLT Edge Peer
                       instance belongs."
        ::= { rcIpRsmltEdgePeerEntry 5 }

-- IPv6 RSMLT

rcIpv6RsmltOperTable OBJECT-TYPE
        SYNTAX          SEQUENCE OF RcIpv6RsmltOperEntry
        MAX-ACCESS      not-accessible
        STATUS          current
        DESCRIPTION     "Route Smlt Table"
    ::= { rcIpRsmlt 5 }

rcIpv6RsmltOperEntry OBJECT-TYPE
        SYNTAX          RcIpv6RsmltOperEntry
        MAX-ACCESS      not-accessible
        STATUS          current
        DESCRIPTION     "A local IPv6 RSMLT entry"
        INDEX           { rcIpv6RsmltOperIfIndex,
                          rcIpv6RsmltOperIpv6Addr,
                          rcIpv6RsmltOperIpv6PrefixLength }
        ::= { rcIpv6RsmltOperTable 1 }

RcIpv6RsmltOperEntry ::=
        SEQUENCE {
                rcIpv6RsmltOperIfIndex                 InterfaceIndex,
                rcIpv6RsmltOperIpv6Addr                Ipv6Address,
                rcIpv6RsmltOperIpv6PrefixLength        Integer32,
                rcIpv6RsmltOperAdminStatus             TruthValue,
                rcIpv6RsmltOperHoldDownTimer           Integer32,
                rcIpv6RsmltOperHoldUpTimer             Integer32,
                rcIpv6RsmltOperOperStatus              INTEGER,
                rcIpv6RsmltOperSmltId                  IdList,
                rcIpv6RsmltOperVlanId                  Integer32,
                rcIpv6RsmltOperMacAddr                 MacAddress,
                rcIpv6RsmltOperVrfId                   VrfIdentifier,
                rcIpv6RsmltOperVrfName                 SnmpAdminString
        }

rcIpv6RsmltOperIfIndex OBJECT-TYPE
        SYNTAX        InterfaceIndex
        MAX-ACCESS    not-accessible
        STATUS        current
        DESCRIPTION   "Route Smlt Oper IfIndex."
        ::= { rcIpv6RsmltOperEntry 1 }

rcIpv6RsmltOperIpv6Addr OBJECT-TYPE
        SYNTAX         Ipv6Address
        MAX-ACCESS     not-accessible
        STATUS         current
        DESCRIPTION    "IPv6 Interface with RSMLT on."
        ::= { rcIpv6RsmltOperEntry  2 }

rcIpv6RsmltOperIpv6PrefixLength OBJECT-TYPE
        SYNTAX        Integer32 (0..128)
        MAX-ACCESS    not-accessible
        STATUS        current
        DESCRIPTION   "IPv6 Prefix Length."
        ::= { rcIpv6RsmltOperEntry  3 }

rcIpv6RsmltOperAdminStatus OBJECT-TYPE
        SYNTAX        TruthValue
        MAX-ACCESS    read-write
        STATUS        current
        DESCRIPTION   "is a enable/disable flag."
        DEFVAL        { false }
        ::= { rcIpv6RsmltOperEntry 4 }

rcIpv6RsmltOperHoldDownTimer OBJECT-TYPE
        SYNTAX        Integer32 (0..3600)
        MAX-ACCESS    read-write
        STATUS        current
        DESCRIPTION   "Timer value, the range of value is from 0 to 3600."
        DEFVAL        { 0 }
        ::= { rcIpv6RsmltOperEntry 5 }

rcIpv6RsmltOperHoldUpTimer OBJECT-TYPE
        SYNTAX        Integer32 (0..3600 | 9999)
        MAX-ACCESS    read-write
        STATUS        current
        DESCRIPTION   "The range of value 0 to 3600 or 9999. 9999 means
                       infinity."
        DEFVAL        { 0 }
        ::= { rcIpv6RsmltOperEntry  7 }

rcIpv6RsmltOperOperStatus OBJECT-TYPE
        SYNTAX        INTEGER {
                        up(1),
                        down(2)
                      }
        MAX-ACCESS    read-only
        STATUS        current
        DESCRIPTION   "The operation status of Rsmlt, up or down."
        DEFVAL        { down }
        ::= { rcIpv6RsmltOperEntry  9 }

rcIpv6RsmltOperSmltId OBJECT-TYPE
        SYNTAX        IdList
        MAX-ACCESS    read-only
        STATUS        current
        DESCRIPTION   "The id range for SMLT is 1-32."
        ::= { rcIpv6RsmltOperEntry  10 }

rcIpv6RsmltOperVlanId OBJECT-TYPE
        SYNTAX        Integer32 (1..4093)
        MAX-ACCESS    read-only
        STATUS        current
        DESCRIPTION   "Vlan id."
        ::= { rcIpv6RsmltOperEntry  12 }

rcIpv6RsmltOperMacAddr OBJECT-TYPE
        SYNTAX        MacAddress
        MAX-ACCESS    read-only
        STATUS        current
        DESCRIPTION   "Mac Address."
        ::= { rcIpv6RsmltOperEntry  13 }

rcIpv6RsmltOperVrfId OBJECT-TYPE
        SYNTAX        VrfIdentifier
        MAX-ACCESS    read-only
        STATUS        current
        DESCRIPTION   "Indicates the Virtual Router to which the RSMLT
                       Oper instance belongs."
        ::= { rcIpv6RsmltOperEntry  14 }

rcIpv6RsmltOperVrfName OBJECT-TYPE
        SYNTAX        SnmpAdminString (SIZE (0..64))
        MAX-ACCESS    read-only
        STATUS        current
        DESCRIPTION   "Name of the Virtual Router to which the RSMLT Oper
                       instance belongs."
        ::= { rcIpv6RsmltOperEntry  15 }


-- Route IPv6 Smlt Peer Table

rcIpv6RsmltPeerTable OBJECT-TYPE
        SYNTAX          SEQUENCE OF RcIpv6RsmltPeerEntry
        MAX-ACCESS      not-accessible
        STATUS          current
        DESCRIPTION     "Route Smlt Peer Table"
    ::= { rcIpRsmlt 6 }

rcIpv6RsmltPeerEntry OBJECT-TYPE
        SYNTAX          RcIpv6RsmltPeerEntry
        MAX-ACCESS       not-accessible
        STATUS          current
        DESCRIPTION     "An entry of Ip As Path Access List Table."
        INDEX           { rcIpv6RsmltPeerIfIndex,
                          rcIpv6RsmltPeerIpv6Addr,
                          rcIpv6RsmltPeerIpv6PrefixLength }
        ::= { rcIpv6RsmltPeerTable 1 }

RcIpv6RsmltPeerEntry ::=
        SEQUENCE {
                rcIpv6RsmltPeerIfIndex                 InterfaceIndex,
                rcIpv6RsmltPeerIpv6Addr                Ipv6Address,
                rcIpv6RsmltPeerIpv6PrefixLength        Integer32,
                rcIpv6RsmltPeerAdminStatus             TruthValue,
                rcIpv6RsmltPeerHoldDownTimer           Integer32,
                rcIpv6RsmltPeerHoldDownTimeRemaining   Integer32,
                rcIpv6RsmltPeerHoldUpTimer             Integer32,
                rcIpv6RsmltPeerHoldUpTimeRemaining     Integer32,
                rcIpv6RsmltPeerOperStatus              INTEGER,
                rcIpv6RsmltPeerSmltId                  IdList,
                rcIpv6RsmltPeerVlanId                  Integer32,
                rcIpv6RsmltPeerMacAddr                 MacAddress,
                rcIpv6RsmltPeerVrfId                   VrfIdentifier,
                rcIpv6RsmltPeerVrfName                 SnmpAdminString
        }

rcIpv6RsmltPeerIfIndex OBJECT-TYPE
        SYNTAX        InterfaceIndex
        MAX-ACCESS    not-accessible
        STATUS        current
        DESCRIPTION   "Route Smlt Oper IfIndex."
        ::= { rcIpv6RsmltPeerEntry 1 }

rcIpv6RsmltPeerIpv6Addr OBJECT-TYPE
        SYNTAX        Ipv6Address
        MAX-ACCESS    not-accessible
        STATUS        current
        DESCRIPTION   "IP Interface with RSMLT on."
        ::= { rcIpv6RsmltPeerEntry  2 }

rcIpv6RsmltPeerIpv6PrefixLength OBJECT-TYPE
        SYNTAX        Integer32 (0..128)
        MAX-ACCESS    not-accessible
        STATUS        current
        DESCRIPTION   "IPv6 Prefix Length"
        ::= { rcIpv6RsmltPeerEntry 3 }

rcIpv6RsmltPeerAdminStatus OBJECT-TYPE
        SYNTAX        TruthValue
        MAX-ACCESS    read-only
        STATUS        current
        DESCRIPTION   "is a enable/disable flag."
        ::= { rcIpv6RsmltPeerEntry 4 }

rcIpv6RsmltPeerHoldDownTimer OBJECT-TYPE
        SYNTAX        Integer32 (0..3600)
        MAX-ACCESS    read-only
        STATUS        current
        DESCRIPTION   "Timer value, the range of value is from 0 to 3600."
        DEFVAL        { 0 }
        ::= { rcIpv6RsmltPeerEntry 5 }

rcIpv6RsmltPeerHoldDownTimeRemaining OBJECT-TYPE
        SYNTAX        Integer32 (0..3600)
        MAX-ACCESS    read-only
        STATUS        current
        DESCRIPTION   "The time value that indicate how much time
                       remaining of HoldDownTimer."
        DEFVAL        { 0 }
        ::= { rcIpv6RsmltPeerEntry  6 }

rcIpv6RsmltPeerHoldUpTimer OBJECT-TYPE
        SYNTAX        Integer32 (0..3600 | 9999)
        MAX-ACCESS    read-only
        STATUS        current
        DESCRIPTION   "The range of value 0 to 3600 or 9999. 9999 means
                       infinity."
        DEFVAL        { 0 }
        ::= { rcIpv6RsmltPeerEntry  7 }

rcIpv6RsmltPeerHoldUpTimeRemaining OBJECT-TYPE
        SYNTAX        Integer32 (0..3600 | 9999)
        MAX-ACCESS    read-only
        STATUS        current
        DESCRIPTION   "The time value that indicate how much time
                       remaining of HoldUpTimer."
        DEFVAL        { 0 }
        ::= { rcIpv6RsmltPeerEntry  8 }

rcIpv6RsmltPeerOperStatus OBJECT-TYPE
        SYNTAX        INTEGER {
                        up(1),
                        down(2)
                      }
        MAX-ACCESS    read-only
        STATUS        current
        DESCRIPTION   "The operation status of Rsmlt, up or down."
        DEFVAL        { down }
        ::= { rcIpv6RsmltPeerEntry  9 }

rcIpv6RsmltPeerSmltId OBJECT-TYPE
        SYNTAX        IdList
        MAX-ACCESS    read-only
        STATUS        current
        DESCRIPTION   "The id range for SMLT is 1-32."
        ::= { rcIpv6RsmltPeerEntry  10 }

rcIpv6RsmltPeerVlanId OBJECT-TYPE
        SYNTAX        Integer32 (1..4093)
        MAX-ACCESS    read-only
        STATUS        current
        DESCRIPTION   "Vlan id."
        ::= { rcIpv6RsmltPeerEntry  12 }

rcIpv6RsmltPeerMacAddr OBJECT-TYPE
        SYNTAX        MacAddress
        MAX-ACCESS    read-only
        STATUS        current
        DESCRIPTION   "Mac Address."
        ::= { rcIpv6RsmltPeerEntry  13 }

rcIpv6RsmltPeerVrfId OBJECT-TYPE
        SYNTAX        VrfIdentifier
        MAX-ACCESS    read-only
        STATUS        current
        DESCRIPTION   "Indicates the Virtual Router to which the RSMLT Peer
                       instance belongs."
        ::= { rcIpv6RsmltPeerEntry  14 }

rcIpv6RsmltPeerVrfName OBJECT-TYPE
        SYNTAX        SnmpAdminString (SIZE (0..64))
        MAX-ACCESS    read-only
        STATUS        current
        DESCRIPTION   "Name of the Virtual Router to which the RSMLT Peer
                       instance belongs."
        ::= { rcIpv6RsmltPeerEntry 15 }


-- IPv6 RSMLT Edge Peer table

rcIpv6RsmltEdgePeerTable OBJECT-TYPE
        SYNTAX        SEQUENCE OF RcIpv6RsmltEdgePeerEntry
        MAX-ACCESS    not-accessible
        STATUS        current
        DESCRIPTION   "RSMLT Edge Support Peer Info table. This
                      table consists of the RSMLT Peers for which
                      the switch will act as a PeerForwarder."
        ::= { rcIpRsmlt 7 }

rcIpv6RsmltEdgePeerEntry OBJECT-TYPE
        SYNTAX        RcIpv6RsmltEdgePeerEntry
        MAX-ACCESS    not-accessible
        STATUS        current
        DESCRIPTION   "RSMLT Edge Support Peer Info Entry"
        INDEX         { rcIpv6RsmltEdgePeerVlanId,
                        rcIpv6RsmltEdgePeerIpv6Address,
                        rcIpv6RsmltEdgePeerIpv6PrefixLength }
        ::= { rcIpv6RsmltEdgePeerTable 1 }

RcIpv6RsmltEdgePeerEntry ::=
        SEQUENCE {
                rcIpv6RsmltEdgePeerVlanId           Integer32,
                rcIpv6RsmltEdgePeerIpv6Address      Ipv6Address,
                rcIpv6RsmltEdgePeerIpv6PrefixLength Integer32,
                rcIpv6RsmltEdgePeerMacAddress       MacAddress
        }

rcIpv6RsmltEdgePeerVlanId  OBJECT-TYPE
        SYNTAX        Integer32 (1..4094)
        MAX-ACCESS    not-accessible
        STATUS        current
        DESCRIPTION   "A value that uniquely identifies the Virtual LAN
                      associated with this entry."
        ::= { rcIpv6RsmltEdgePeerEntry 1}

rcIpv6RsmltEdgePeerIpv6Address OBJECT-TYPE
        SYNTAX        Ipv6Address
        MAX-ACCESS    not-accessible
        STATUS        current
        DESCRIPTION   "IP address of the Peer RSMLT Interface."
        ::= { rcIpv6RsmltEdgePeerEntry 2}

rcIpv6RsmltEdgePeerIpv6PrefixLength OBJECT-TYPE
        SYNTAX        Integer32 (0..128)
        MAX-ACCESS    not-accessible
        STATUS        current
        DESCRIPTION   "If set then this prefix can be used
                       for address autoconfig,
                       passed opaquely to Infinity"
        ::= { rcIpv6RsmltEdgePeerEntry 3 }

rcIpv6RsmltEdgePeerMacAddress OBJECT-TYPE
        SYNTAX        MacAddress
        MAX-ACCESS    read-only
        STATUS        current
        DESCRIPTION   "The MAC address of the Peer RSMLT interface."
        ::= { rcIpv6RsmltEdgePeerEntry 4 }

--IP Gen Policy

rcIpGenPolicy OBJECT IDENTIFIER ::= { rcIp 100 }

-- Ip As Path Access List Table

rcIpAsPathAccessListTableSize OBJECT-TYPE
        SYNTAX        Integer32
        MAX-ACCESS    read-only
        STATUS        current
        DESCRIPTION   "table size"
        ::= { rcIpGenPolicy 1 }

rcIpAsPathAccessListTable OBJECT-TYPE 
        SYNTAX          SEQUENCE OF RcIpAsPathAccessListEntry
        MAX-ACCESS      not-accessible 
        STATUS          current 
        DESCRIPTION     "IP As Path Access List table"
    ::= { rcIpGenPolicy 2 }

rcIpAsPathAccessListEntry OBJECT-TYPE
        SYNTAX        	RcIpAsPathAccessListEntry
        MAX-ACCESS        	not-accessible
        STATUS        	current
        DESCRIPTION   	"An entry of Ip As Path Access List Table."
        INDEX         	{ rcIpAsPathAccessListId,
                          rcIpAsPathAccessListMemberId }
        ::= { rcIpAsPathAccessListTable 1 }
 
RcIpAsPathAccessListEntry ::=
        SEQUENCE {
                rcIpAsPathAccessListId                  INTEGER,
                rcIpAsPathAccessListMemberId            INTEGER,
                rcIpAsPathAccessListMode                INTEGER,
                rcIpAsPathAccessListAsRegularExpression OCTET STRING (SIZE(0..256)),
                rcIpAsPathAccessListRowStatus           RowStatus
        }
 
rcIpAsPathAccessListId OBJECT-TYPE
        SYNTAX        INTEGER (1..1024)
        MAX-ACCESS    read-only
        STATUS        current
        DESCRIPTION   "Path Access List entry Id."
        ::= { rcIpAsPathAccessListEntry 1 }

rcIpAsPathAccessListMemberId OBJECT-TYPE
        SYNTAX        INTEGER (0..65535)
        MAX-ACCESS    read-only
        STATUS        current
        DESCRIPTION   "frq. at which hello sent."
        ::= { rcIpAsPathAccessListEntry 2 }

rcIpAsPathAccessListMode OBJECT-TYPE
        SYNTAX        INTEGER {
                          permit(1),
                          deny(2)
                      }
        MAX-ACCESS    read-write
        STATUS        current
        DESCRIPTION   "Path Access List Mode, permit or deny."
        ::= { rcIpAsPathAccessListEntry 3 }

rcIpAsPathAccessListAsRegularExpression OBJECT-TYPE
        SYNTAX        OCTET STRING (SIZE(0..256))
        MAX-ACCESS    read-write
        STATUS        current
        DESCRIPTION   "IP Path Access List Regular Expression"
        ::= { rcIpAsPathAccessListEntry 4 }

rcIpAsPathAccessListRowStatus OBJECT-TYPE
        SYNTAX        RowStatus
        MAX-ACCESS    read-write
        STATUS        current
        DESCRIPTION   "Table row status."
        ::= { rcIpAsPathAccessListEntry 5 }


-- Ip Community Access List Table

rcIpCommunityAccessListTableSize OBJECT-TYPE
        SYNTAX        Integer32
        MAX-ACCESS    read-only
        STATUS        current
        DESCRIPTION   "table size"
        ::= { rcIpGenPolicy 3 }

rcIpCommunityAccessListTable OBJECT-TYPE 
        SYNTAX          SEQUENCE OF RcIpCommunityAccessListEntry
        MAX-ACCESS      not-accessible 
        STATUS          current 
        DESCRIPTION     "IP CommunityAccess List table"
    ::= { rcIpGenPolicy 4 }

rcIpCommunityAccessListEntry OBJECT-TYPE
        SYNTAX        	RcIpCommunityAccessListEntry
        MAX-ACCESS        	not-accessible
        STATUS        	current
        DESCRIPTION   	"An entry of Ip CommunityAccess List Table."
        INDEX         	{ rcIpCommunityAccessListId,
                          rcIpCommunityAccessListMemberId }
        ::= { rcIpCommunityAccessListTable 1 }
 
RcIpCommunityAccessListEntry ::=
        SEQUENCE {
                rcIpCommunityAccessListId        INTEGER,
                rcIpCommunityAccessListMemberId  INTEGER,
                rcIpCommunityAccessListMode      INTEGER,
                rcIpCommunityAccessListCommunity OCTET STRING (SIZE(0..256)),
                rcIpCommunityAccessListRowStatus RowStatus
        }
 
rcIpCommunityAccessListId OBJECT-TYPE
        SYNTAX        INTEGER (1..1024)
        MAX-ACCESS    read-only
        STATUS        current
        DESCRIPTION   "IP CommunityAccess entry List Id"
        ::= { rcIpCommunityAccessListEntry 1 }

rcIpCommunityAccessListMemberId OBJECT-TYPE
        SYNTAX        INTEGER (0..65535)
        MAX-ACCESS    read-only
        STATUS        current
        DESCRIPTION   "frq. at which hello sent."
        ::= { rcIpCommunityAccessListEntry 2 }

rcIpCommunityAccessListMode OBJECT-TYPE
        SYNTAX        INTEGER {
                          permit(1),
                          deny(2)
                      }
        MAX-ACCESS    read-write
        STATUS        current
        DESCRIPTION   "IP Community Access List Mode, permit or deny."
        ::= { rcIpCommunityAccessListEntry 3 }

rcIpCommunityAccessListCommunity OBJECT-TYPE
        SYNTAX        OCTET STRING (SIZE(0..256))
        MAX-ACCESS    read-write
        STATUS        current
        DESCRIPTION   "IP Community Access List Community string."
        ::= { rcIpCommunityAccessListEntry 4 }

rcIpCommunityAccessListRowStatus OBJECT-TYPE
        SYNTAX        RowStatus
        MAX-ACCESS    read-write
        STATUS        current
        DESCRIPTION   "IP Community Access Table Row Status."
        ::= { rcIpCommunityAccessListEntry 5 }

-- Ip Access List Table
 
rcIpAccessListTableSize OBJECT-TYPE
        SYNTAX        Integer32
        MAX-ACCESS    read-only
        STATUS        current
        DESCRIPTION   "table size"
        ::= { rcIpGenPolicy 5 }


rcIpAccessListTable OBJECT-TYPE 
        SYNTAX          SEQUENCE OF RcIpAccessListEntry
        MAX-ACCESS      not-accessible 
        STATUS          current 
        DESCRIPTION     "IP Access List table"
    ::= { rcIpGenPolicy 6 }

rcIpAccessListEntry OBJECT-TYPE
        SYNTAX          RcIpAccessListEntry
        MAX-ACCESS      not-accessible
        STATUS          current
        DESCRIPTION     "An entry of Ip Access List Table."
        INDEX           { rcIpAccessListId,
                          rcIpAccessListMode,
                          rcIpAccessListNetwork,
                          rcIpAccessListNetworkMask }
        ::= { rcIpAccessListTable 1 }
 
RcIpAccessListEntry ::=
        SEQUENCE {
                rcIpAccessListId          INTEGER,
                rcIpAccessListMode        INTEGER,
                rcIpAccessListNetwork     IpAddress,
                rcIpAccessListNetworkMask IpAddress,
                rcIpAccessListName        DisplayString,
                rcIpAccessListRowStatus   RowStatus
        }
 
rcIpAccessListId OBJECT-TYPE
        SYNTAX        INTEGER (1..99)
        MAX-ACCESS    read-only
        STATUS        current
        DESCRIPTION   ""
        ::= { rcIpAccessListEntry 1 }

rcIpAccessListMode OBJECT-TYPE
        SYNTAX        INTEGER {
                          permit(1),
                          deny(2)
                      }
        MAX-ACCESS    read-only
        STATUS        current
        DESCRIPTION   ""
        ::= { rcIpAccessListEntry 2 }

rcIpAccessListNetwork OBJECT-TYPE
        SYNTAX        IpAddress
        MAX-ACCESS    read-write
        STATUS        current
        DESCRIPTION   ""
        ::= { rcIpAccessListEntry 3 }

rcIpAccessListNetworkMask OBJECT-TYPE
        SYNTAX        IpAddress
        MAX-ACCESS    read-write
        STATUS        current
        DESCRIPTION   ""
        ::= { rcIpAccessListEntry 4 }

rcIpAccessListName OBJECT-TYPE
        SYNTAX        DisplayString
        MAX-ACCESS    read-write
        STATUS        current
        DESCRIPTION   ""
        ::= { rcIpAccessListEntry 5 }

rcIpAccessListRowStatus OBJECT-TYPE
        SYNTAX        RowStatus
        MAX-ACCESS    read-write
        STATUS        current
        DESCRIPTION   ""
        ::= { rcIpAccessListEntry 6 }


-- Ip Extended Access List Table


rcIpExtendedAccessListTableSize OBJECT-TYPE
        SYNTAX        Integer32
        MAX-ACCESS    read-only
        STATUS        current
        DESCRIPTION   "table size"
        ::= { rcIpGenPolicy 7 }


rcIpExtendedAccessListTable OBJECT-TYPE
        SYNTAX          SEQUENCE OF RcIpExtendedAccessListEntry
        MAX-ACCESS      not-accessible
        STATUS          current
        DESCRIPTION     "IP Extended Access List table"
        ::= { rcIpGenPolicy 8 }

rcIpExtendedAccessListEntry OBJECT-TYPE
        SYNTAX          RcIpExtendedAccessListEntry
        MAX-ACCESS      not-accessible
        STATUS          current
        DESCRIPTION     "An entry of Ip Extended Access List Table."
        INDEX           { rcIpExtendedAccessListId,
                          rcIpExtendedAccessListMode,
                          rcIpExtendedAccessListNetwork,
                          rcIpExtendedAccessListNetworkWildCard,
                          rcIpExtendedAccessListNetworkMask,
                          rcIpExtendedAccessListNetworkMaskWildCard }
        ::= { rcIpExtendedAccessListTable 1 }

RcIpExtendedAccessListEntry ::=
        SEQUENCE {
                rcIpExtendedAccessListId                  INTEGER,
                rcIpExtendedAccessListMode                INTEGER,
                rcIpExtendedAccessListNetwork             IpAddress,
                rcIpExtendedAccessListNetworkWildCard     IpAddress,
                rcIpExtendedAccessListNetworkMask         IpAddress,
                rcIpExtendedAccessListNetworkMaskWildCard IpAddress,
                rcIpExtendedAccessListName                DisplayString,
                rcIpExtendedAccessListRowStatus           RowStatus
        }

rcIpExtendedAccessListId OBJECT-TYPE
        SYNTAX        INTEGER (100..199)
        MAX-ACCESS    read-only
        STATUS        current
        DESCRIPTION   ""
        ::= { rcIpExtendedAccessListEntry 1 }

rcIpExtendedAccessListMode OBJECT-TYPE
        SYNTAX        INTEGER {
                          permit(1),
                          deny(2)
                      }
        MAX-ACCESS    read-only
        STATUS        current
        DESCRIPTION   ""
        ::= { rcIpExtendedAccessListEntry 2 }

rcIpExtendedAccessListNetwork OBJECT-TYPE
        SYNTAX        IpAddress
        MAX-ACCESS    read-only
        STATUS        current
        DESCRIPTION   ""
        ::= { rcIpExtendedAccessListEntry 3 }

rcIpExtendedAccessListNetworkWildCard OBJECT-TYPE
        SYNTAX        IpAddress
        MAX-ACCESS    read-only
        STATUS        current
        DESCRIPTION   ""
        ::= { rcIpExtendedAccessListEntry 4 }

rcIpExtendedAccessListNetworkMask OBJECT-TYPE
        SYNTAX        IpAddress
        MAX-ACCESS    read-only
        STATUS        current
        DESCRIPTION   ""
        ::= { rcIpExtendedAccessListEntry 5 }

rcIpExtendedAccessListNetworkMaskWildCard OBJECT-TYPE
        SYNTAX        IpAddress
        MAX-ACCESS    read-only
        STATUS        current
        DESCRIPTION   ""
        ::= { rcIpExtendedAccessListEntry 6 }

rcIpExtendedAccessListName OBJECT-TYPE
        SYNTAX        DisplayString
        MAX-ACCESS    read-write
        STATUS        current
        DESCRIPTION   ""
        ::= { rcIpExtendedAccessListEntry 7 }

rcIpExtendedAccessListRowStatus OBJECT-TYPE
        SYNTAX        RowStatus
        MAX-ACCESS    read-write
        STATUS        current
        DESCRIPTION   ""
        ::= { rcIpExtendedAccessListEntry 8 }

-- Ip Prefix List Table
 
rcIpPrefixListTableSize OBJECT-TYPE
        SYNTAX        Integer32
        MAX-ACCESS    read-only
        STATUS        current
        DESCRIPTION   "table size"
        ::= { rcIpGenPolicy 9 } 


rcIpPrefixListTable OBJECT-TYPE 
        SYNTAX          SEQUENCE OF RcIpPrefixListEntry
        MAX-ACCESS      not-accessible 
        STATUS          current 
        DESCRIPTION     "IP Prefix List table"
        ::= { rcIpGenPolicy 10 }

rcIpPrefixListEntry OBJECT-TYPE
        SYNTAX        	RcIpPrefixListEntry
        MAX-ACCESS        	not-accessible
        STATUS        	current
        DESCRIPTION   	"An entry of Ip Prefix List Table."
        INDEX         	{ rcIpPrefixListId, 
                      	  rcIpPrefixListPrefix, 
                      	  rcIpPrefixListPrefixMaskLen }
        ::= { rcIpPrefixListTable 1 }

RcIpPrefixListEntry ::=
        SEQUENCE {
                rcIpPrefixListId               Integer32,
                rcIpPrefixListPrefix           IpAddress,
                rcIpPrefixListPrefixMaskLen    INTEGER,
                rcIpPrefixListMaskLenFrom      INTEGER,
                rcIpPrefixListMaskLenUpto      INTEGER,
                rcIpPrefixListName             DisplayString,
                rcIpPrefixListRowStatus        RowStatus
        }

rcIpPrefixListId OBJECT-TYPE
        SYNTAX        Integer32 (0..2147483647)
        MAX-ACCESS    read-only
        STATUS        current
        DESCRIPTION   "ListId"
        ::= { rcIpPrefixListEntry 1 }

rcIpPrefixListPrefix OBJECT-TYPE
        SYNTAX        IpAddress
        MAX-ACCESS    read-only
        STATUS        current
        DESCRIPTION   "Is a member of a specific prefix list.
                       Adding the prefix to the given prefix list"
        ::= { rcIpPrefixListEntry 2 }

rcIpPrefixListPrefixMaskLen OBJECT-TYPE
        SYNTAX        INTEGER (0..32)
        MAX-ACCESS    read-only
        STATUS        current
        DESCRIPTION   "prefix mask length"
        ::= { rcIpPrefixListEntry 3 }

rcIpPrefixListMaskLenFrom OBJECT-TYPE
        SYNTAX        INTEGER (0..32)
        MAX-ACCESS    read-write
        STATUS        current
        DESCRIPTION   "used with mask len"
        ::= { rcIpPrefixListEntry 4 }

rcIpPrefixListMaskLenUpto OBJECT-TYPE
        SYNTAX        INTEGER (0..32)
        MAX-ACCESS    read-write
        STATUS        current
        DESCRIPTION   "used with mask len"
        ::= { rcIpPrefixListEntry 5 }

rcIpPrefixListName OBJECT-TYPE
        SYNTAX        DisplayString (SIZE(1..64))
        MAX-ACCESS    read-write
        STATUS        current
        DESCRIPTION   "list name"
        ::= { rcIpPrefixListEntry 6 }

rcIpPrefixListRowStatus OBJECT-TYPE
        SYNTAX        RowStatus
        MAX-ACCESS    read-write
        STATUS        current
        DESCRIPTION   "row status"
        ::= { rcIpPrefixListEntry 7 }  

-- Ip Prefix List Name Table

rcIpPrefixListNameTableSize OBJECT-TYPE
        SYNTAX        Integer32
        MAX-ACCESS    read-only
        STATUS        current
        DESCRIPTION   "table size"
        ::= { rcIpGenPolicy 26 }

rcIpPrefixListNameTable OBJECT-TYPE
        SYNTAX          SEQUENCE OF RcIpPrefixListNameEntry
        MAX-ACCESS      not-accessible
        STATUS          current
        DESCRIPTION     "Prefix List Name table"
        ::= { rcIpGenPolicy 27 }

rcIpPrefixListNameEntry OBJECT-TYPE
        SYNTAX          RcIpPrefixListNameEntry
        MAX-ACCESS      not-accessible
        STATUS          current
        DESCRIPTION     "An entry of Prefix List Name Table."
        INDEX           { rcIpPrefixListNameId }
        ::= { rcIpPrefixListNameTable 1 }

RcIpPrefixListNameEntry ::=
        SEQUENCE {
                rcIpPrefixListNameId           Integer32,
                rcIpPrefixListNameName         DisplayString
        }

rcIpPrefixListNameId OBJECT-TYPE
        SYNTAX        Integer32 (0..2147483647)
        MAX-ACCESS    not-accessible
        STATUS        current
        DESCRIPTION   "list id"
        ::= { rcIpPrefixListNameEntry 1 }

rcIpPrefixListNameName OBJECT-TYPE
        SYNTAX        DisplayString (SIZE(1..64))
        MAX-ACCESS    read-only
        STATUS        current
        DESCRIPTION   "list name"
        ::= { rcIpPrefixListNameEntry 2 }


-- Ip Route Policy Name Table

rcIpRoutePolicyNameTable OBJECT-TYPE
        SYNTAX          SEQUENCE OF RcIpRoutePolicyNameEntry
        MAX-ACCESS      not-accessible
        STATUS          current
        DESCRIPTION     "Route Policy Name table for all VRFs"
        ::= { rcIpGenPolicy 28 }

rcIpRoutePolicyNameEntry OBJECT-TYPE
        SYNTAX          RcIpRoutePolicyNameEntry
        MAX-ACCESS      not-accessible
        STATUS          current
        DESCRIPTION     "An entry of Route Policy Name Table."
        INDEX           { rcIpRoutePolicyNameVrfId, rcIpRoutePolicyNameId }
        ::= { rcIpRoutePolicyNameTable 1 }

RcIpRoutePolicyNameEntry ::=
        SEQUENCE {
                rcIpRoutePolicyNameVrfId        VrfIdentifier,
                rcIpRoutePolicyNameId           Integer32,
                rcIpRoutePolicyNameName         DisplayString
        }

rcIpRoutePolicyNameVrfId OBJECT-TYPE
        SYNTAX        VrfIdentifier
        MAX-ACCESS    not-accessible
        STATUS        current
        DESCRIPTION   "route policy vrfId"
        ::= { rcIpRoutePolicyNameEntry 1 }

rcIpRoutePolicyNameId OBJECT-TYPE
        SYNTAX        Integer32 (0..2147483647)
        MAX-ACCESS    not-accessible
        STATUS        current
        DESCRIPTION   "route policy id"
        ::= { rcIpRoutePolicyNameEntry 2 }

rcIpRoutePolicyNameName OBJECT-TYPE
        SYNTAX        DisplayString (SIZE(1..64))
        MAX-ACCESS    read-only
        STATUS        current
        DESCRIPTION   "route policy name"
        ::= { rcIpRoutePolicyNameEntry 3 }


-- Ip Route Policy Table

rcIpRoutePolicyTableSize OBJECT-TYPE
        SYNTAX        Integer32
        MAX-ACCESS    read-only
        STATUS        current
        DESCRIPTION   "table size"
        ::= { rcIpGenPolicy 11 }

rcIpRoutePolicyApply OBJECT-TYPE
        SYNTAX        TruthValue
        MAX-ACCESS    read-write
        STATUS        current
        DESCRIPTION   ""
        ::= { rcIpGenPolicy 12 }

rcIpRoutePolicyTable OBJECT-TYPE
        SYNTAX          SEQUENCE OF RcIpRoutePolicyEntry
        MAX-ACCESS      not-accessible
        STATUS          current
        DESCRIPTION     "IP Route Map table"
        ::= { rcIpGenPolicy 13 }

rcIpRoutePolicyEntry OBJECT-TYPE
        SYNTAX          RcIpRoutePolicyEntry
        MAX-ACCESS      not-accessible
        STATUS          current
        DESCRIPTION     "An entry of Ip Route Map Table."
        INDEX           { rcIpRoutePolicyId, rcIpRoutePolicySequenceNumber }
        ::= { rcIpRoutePolicyTable 1 }

RcIpRoutePolicyEntry ::=
        SEQUENCE {
                rcIpRoutePolicyId                          Integer32,
                rcIpRoutePolicySequenceNumber              Integer32,
                rcIpRoutePolicyName                        DisplayString,
                rcIpRoutePolicyEnable                      TruthValue,
                rcIpRoutePolicyMode                        INTEGER,
                rcIpRoutePolicyMatchProtocol               INTEGER,
                rcIpRoutePolicyMatchAsPath                 DisplayString,
                rcIpRoutePolicyMatchCommunity              DisplayString,
                rcIpRoutePolicyMatchCommunityExact         EnableValue,
                rcIpRoutePolicyMatchNetwork                RcLongDisplayString,
                rcIpRoutePolicyMatchIpRouteSource          RcLongDisplayString,
                rcIpRoutePolicyMatchNextHop                RcLongDisplayString,
                rcIpRoutePolicyMatchInterface              RcLongDisplayString,
                rcIpRoutePolicyMatchRouteType              INTEGER,
                rcIpRoutePolicyMatchMetric                 INTEGER,
                rcIpRoutePolicyMatchTag                    DisplayString,
                rcIpRoutePolicySetRoutePreference          INTEGER,
                rcIpRoutePolicySetAsPath                   DisplayString,
                rcIpRoutePolicySetAsPathMode               INTEGER,
                rcIpRoutePolicySetAutomaticTag             EnableValue,
                rcIpRoutePolicySetCommunityNumber          DisplayString,
                rcIpRoutePolicySetCommunityMode            INTEGER,
                rcIpRoutePolicySetMetricTypeInternal       Integer32,
                rcIpRoutePolicySetMetric                   INTEGER,
                rcIpRoutePolicySetMetricType               INTEGER,
                rcIpRoutePolicySetNextHop                  IpAddress,
                rcIpRoutePolicySetOrigin                   INTEGER,
                rcIpRoutePolicySetLocalPref                Integer32,
                rcIpRoutePolicySetOriginEgpAs              Integer32,
                rcIpRoutePolicySetTag                      Integer32,
                rcIpRoutePolicySetWeight                   Integer32,
                rcIpRoutePolicySetInjectNetList            DisplayString,
                rcIpRoutePolicyRowStatus                   RowStatus,
                rcIpRoutePolicySetMask                     IpAddress,
                rcIpRoutePolicyNssaPbit                    EnableValue,
                rcIpRoutePolicyMatchVrf			   IdList,
	        rcIpRoutePolicyMatchExtCommunity  	   DisplayString,
                rcIpRoutePolicySetExtCommunity      	   DisplayString,
                rcIpRoutePolicySetExtCommunityMode 	   INTEGER,
		rcIpRoutePolicyMatchLocalPref              Integer32,
                rcIpRoutePolicyMatchIpRouteDest            RcLongDisplayString,
                rcIpRoutePolicySetLevel                    INTEGER,
                rcIpRoutePolicyIpv6SetNextHop              Ipv6Address
        }

rcIpRoutePolicyId OBJECT-TYPE
        SYNTAX        Integer32 (0..2147483647)
        MAX-ACCESS    read-only
        STATUS        current
        DESCRIPTION   "Index used to identify a group of policies in
                       the route policy tableRoute map id"
        ::= { rcIpRoutePolicyEntry 1 }

rcIpRoutePolicySequenceNumber OBJECT-TYPE
        SYNTAX        Integer32 (0..2147483647)
        MAX-ACCESS    read-only
        STATUS        current
        DESCRIPTION   "second index used to identify a specific policy
                       with in the route policy group (grouped by Id).
                       This field allows users to specify different
                       MATCH, SET parameters and an action."
        ::= { rcIpRoutePolicyEntry 2 }

rcIpRoutePolicyName OBJECT-TYPE
        SYNTAX        DisplayString(SIZE(1..64))
        MAX-ACCESS    read-write
        STATUS        current
        DESCRIPTION   "Is used to group a set of policies with different
            sequence number. Id & Name have one-on-one
                       relationship. Different policy groups can
                       contain same sequence number, whereas with in
                       a group the sequence number must be different."
        ::= { rcIpRoutePolicyEntry 3 }

rcIpRoutePolicyEnable OBJECT-TYPE
        SYNTAX        TruthValue
        MAX-ACCESS    read-write
        STATUS        current
        DESCRIPTION   "Value specified here indicate whether
                       this policy is enabled or not. If
                       disabled policy sould not be used."
	       DEFVAL        { false } 
        ::= { rcIpRoutePolicyEntry 4 }

rcIpRoutePolicyMode OBJECT-TYPE
        SYNTAX        INTEGER {
                          permit(1),
                          deny(2)
                      }
        MAX-ACCESS    read-write
        STATUS        current
        DESCRIPTION   "specifies the action to be taken when this
                       policy is selected for a specific route.
                       This can be permit or deny or continue.
                       Permit indicates allow the route, deny indicates
                       ignore the route. Continue means continue
                       checking the next match criteria set in the
                       next policy seq, if none take the default action
                       in the given context."
	       DEFVAL        { permit } 
        ::= { rcIpRoutePolicyEntry 5 }

rcIpRoutePolicyMatchProtocol OBJECT-TYPE
        SYNTAX        INTEGER (1..255) 
        MAX-ACCESS    read-write
        STATUS        current
        DESCRIPTION   "Match protocol. Used for RIP and DVMRP announce 
                       policy only.
                       Value is one of multiple (logical 'OR) 
                       of the following values:
                          direct(1),
                          static(2),
                          rip(4),
                          ospf(8),
                          ebgp(16),
                          dvmrp(32),
                          ibgp(64),
                          isis(128),
                          any(255)
                      direct(1): enables direct match-protocol
                      static(2): enables static match-protocol
                      rip(4): enables rip match-protocol
                      ospf(8): enables ospf match-protocol
                      ebgp(16): enables ebgp match-protocol
                      dvmrp(32): enables dvmrp match-protocol
                      ibgp(64): enables ibgp match-protocol
                      isis(128): enables isis match-protocol
                      any(255): enables all match-protocols"
        DEFVAL        {255}              
        ::= { rcIpRoutePolicyEntry 6 }

-- Following between =begin =end is processed by mib_tools/extras.awk
-- =begin enum
-- rcIpRoutePolicyMatchProtocol direct 1
-- rcIpRoutePolicyMatchProtocol static 2
-- rcIpRoutePolicyMatchProtocol rip    4
-- rcIpRoutePolicyMatchProtocol ospf   8
-- rcIpRoutePolicyMatchProtocol ebgp  16
-- rcIpRoutePolicyMatchProtocol dvmrp 32
-- rcIpRoutePolicyMatchProtocol ibgp  64
-- rcIpRoutePolicyMatchProtocol isis  128
-- rcIpRoutePolicyMatchProtocol any  255 
-- =end enum

rcIpRoutePolicyMatchAsPath OBJECT-TYPE
        SYNTAX        DisplayString
        MAX-ACCESS    read-write
        STATUS        current
        DESCRIPTION   "Applicable to BGP protocol only. Match the BGP
                       autonomous system path. This will override the
                         BGP neighbor filter list info."
        ::= { rcIpRoutePolicyEntry 7 }

rcIpRoutePolicyMatchCommunity OBJECT-TYPE
        SYNTAX        DisplayString
        MAX-ACCESS    read-write
        STATUS        current
        DESCRIPTION   "Applicable to BGP protocol only. Filter
                       incoming/outgoing updates based on communities."
        ::= { rcIpRoutePolicyEntry 8 }

rcIpRoutePolicyMatchCommunityExact OBJECT-TYPE
        SYNTAX        EnableValue
        MAX-ACCESS    read-write
        STATUS        current
        DESCRIPTION   "If enabled indicates the match has be an exact
                       (i.e., all of the communities specified in the
                       path has to be matched)."
        DEFVAL         {disable}
        ::= { rcIpRoutePolicyEntry 9 }

rcIpRoutePolicyMatchNetwork OBJECT-TYPE
        SYNTAX        RcLongDisplayString (SIZE(0..259))
        MAX-ACCESS    read-write
        STATUS        current
        DESCRIPTION   "can specify one or more prefix list name or id(s)"
        DEFVAL        {""}
        ::= { rcIpRoutePolicyEntry 10 }

rcIpRoutePolicyMatchIpRouteSource OBJECT-TYPE
        SYNTAX        RcLongDisplayString (SIZE(0..259))
        MAX-ACCESS    read-write
        STATUS        current
        DESCRIPTION   "In case of Rip routes this is equivalent to
                       RipInterface. In case of DVMRP routes this is
                       equivalent to DVMRP gateway. Can specify one
                       or more prefix list name(s) or id(s) seperated by comma."
        DEFVAL        {""}
        ::= { rcIpRoutePolicyEntry 11 }

rcIpRoutePolicyMatchNextHop OBJECT-TYPE
        SYNTAX        RcLongDisplayString (SIZE(0..259))
        MAX-ACCESS    read-write
        STATUS        current
        DESCRIPTION   "In case of Rip routes this is equivalent to
                       RipInterface. In case of DVMRP routes this is
                       equivalent to DVMRP gateway. Can specify one
                       or more prefix list name(s) or id(s) seperated by comma."
        DEFVAL        {""}
        ::= { rcIpRoutePolicyEntry 12 } 

rcIpRoutePolicyMatchInterface OBJECT-TYPE
        SYNTAX        RcLongDisplayString (SIZE(0..259))
        MAX-ACCESS    read-write
        STATUS        current
        DESCRIPTION   "Match received interface. Only for rip routes. 
                       Ignored in all other cases."
        DEFVAL        {""}
        ::= { rcIpRoutePolicyEntry 13 }

rcIpRoutePolicyMatchRouteType OBJECT-TYPE
        SYNTAX        INTEGER {
                          any(0),
                          local(1),
                          internal(2),
                          external(3),
                          externaltype1(4),
                          externaltype2(5)
                      }
        MAX-ACCESS    read-write
        STATUS        current
        DESCRIPTION   "For BGP this choice refers to locally generated
                       routes external routes learned via ebgp nbr. For
            OSPF internal refers to intra and inter area
                       routes (belongs to local autonomous system).
                       External (type1|type2) refers to the routes
                       learned from other ASs and imported as either
                       type1 or type2. if type1/type2 is specified
                       then match only type1/type2."
        DEFVAL         {any}
        ::= { rcIpRoutePolicyEntry 14 }

rcIpRoutePolicyMatchMetric OBJECT-TYPE
        SYNTAX        INTEGER (0..65535)
        MAX-ACCESS    read-write
        STATUS        current
        DESCRIPTION   "Match mec field in the incoming advertisement."
	DEFVAL        { 0 } 
        ::= { rcIpRoutePolicyEntry 15 }

rcIpRoutePolicyMatchTag OBJECT-TYPE
        SYNTAX        DisplayString
        MAX-ACCESS    read-write
        STATUS        current
        DESCRIPTION   "specifies a list of tag(s), that will be used
                       during the match criteria process.contains one
                       or more tag values.."
        ::= { rcIpRoutePolicyEntry 16 } 

rcIpRoutePolicySetRoutePreference OBJECT-TYPE
        SYNTAX        INTEGER (0..255)
        MAX-ACCESS    read-write
        STATUS        current
        DESCRIPTION   "if non-zero specifies the route preference
                       value to be assigned to the routes that applies
                       this policy.contains one or more tag values.."
        ::= { rcIpRoutePolicyEntry 17 }

rcIpRoutePolicySetAsPath OBJECT-TYPE
        SYNTAX        DisplayString
        MAX-ACCESS    read-write
        STATUS        current
        DESCRIPTION   "The AS path vaule to be used whether the
                       SetAsPathMode is Tag or Prepend.as-path string.."
        ::= { rcIpRoutePolicyEntry 18 }

rcIpRoutePolicySetAsPathMode OBJECT-TYPE
        SYNTAX        INTEGER {
                          tag(1),
                          prepend(2)
                      }
        MAX-ACCESS    read-write
        STATUS        current
        DESCRIPTION   "It can be either tag or prepend tag.
                       applicable only while redistributing routes to
                       BGP.Converts the tag of a route into AS path."
        DEFVAL         {prepend}
        ::= { rcIpRoutePolicyEntry 19 }

rcIpRoutePolicySetAutomaticTag OBJECT-TYPE
        SYNTAX        EnableValue
        MAX-ACCESS    read-write
        STATUS        current
        DESCRIPTION   ""
        DEFVAL        {disable}
        ::= { rcIpRoutePolicyEntry 20 }

rcIpRoutePolicySetCommunityNumber OBJECT-TYPE
        SYNTAX        DisplayString
        MAX-ACCESS    read-write
        STATUS        current
        DESCRIPTION   "this value can be a number (1..42949672000)
                       or no-export or no-advertise. Applicable to
                       BGP advertisments.community number."
        ::= { rcIpRoutePolicyEntry 21 }

rcIpRoutePolicySetCommunityMode OBJECT-TYPE
        SYNTAX        INTEGER {
                          unchanged(0),
                          none(1),
                          append(2)
                      }
        MAX-ACCESS    read-write
        STATUS        current
        DESCRIPTION   "this value can be either append or none
                       unchanged - keep the community attribute in the
                                   route path as it is.
                       none - remove the community in the route path
                       additive - adds the community-number specified
                                  in SetCommunityNumber to the
                                  community list attribute.  Applicable
                       to BGP advertisments."
        DEFVAL         {unchanged}
        ::= { rcIpRoutePolicyEntry 22 }

rcIpRoutePolicySetMetricTypeInternal OBJECT-TYPE
        SYNTAX        Integer32
        MAX-ACCESS    read-write
        STATUS        current
        DESCRIPTION   "Indicates to set the MED value for routes
                       advertised to ebgp nbrs to the IGP metric value."
        DEFVAL         {0}
        ::= { rcIpRoutePolicyEntry 23 }

rcIpRoutePolicySetMetric OBJECT-TYPE
        SYNTAX        INTEGER (0..65535)
        MAX-ACCESS    read-write
        STATUS        current
        DESCRIPTION   "Value of the metric to be used while sending an
                       update for the routes that match the matching
                       criteria in this route policy.
                       Default - 0 indicates the internal value defined
            for protocol"
	DEFVAL        { 0 } 
        ::= { rcIpRoutePolicyEntry 24 }

rcIpRoutePolicySetMetricType OBJECT-TYPE
        SYNTAX        INTEGER {
                          type1(1),
                          type2(2),
                          internal(3),
                          external(4)
                      }
        MAX-ACCESS    read-write
        STATUS        current
        DESCRIPTION   "Metric type for the routes to be imported into
                       OSPF routing protocol, which passed the matching
            criteria configured in this route policy."
	    DEFVAL        { type2 } 
        ::= { rcIpRoutePolicyEntry 25 }

rcIpRoutePolicySetNextHop OBJECT-TYPE
        SYNTAX        IpAddress
        MAX-ACCESS    read-write
        STATUS        current
        DESCRIPTION   "IpAddress of the next hop router.  Ignored for 
                       DVMRP routes."
        DEFVAL   { '00000000'H }    -- 0.0.0.0
        ::= { rcIpRoutePolicyEntry 26 }

rcIpRoutePolicySetOrigin OBJECT-TYPE
        SYNTAX        INTEGER {
                          unchanged(0),
                          igp(1),
                          egp(2),
                          incomplete(3)
                      }
        MAX-ACCESS    read-write
        STATUS        current
        DESCRIPTION   "igp/egp/incomplete Applicable to BGP protocol
                       only. If not set uses the route origin from
                       the Ip routing table (protocol)."
        DEFVAL         {unchanged}
        ::= { rcIpRoutePolicyEntry 27 }

rcIpRoutePolicySetLocalPref OBJECT-TYPE
        SYNTAX        Integer32
        MAX-ACCESS    read-write
        STATUS        current
        DESCRIPTION   "this value will be used during route decision
                       process in the BGP protocol. Applicable to BGP
                       only."
        DEFVAL         {0}
        ::= { rcIpRoutePolicyEntry 28 }

rcIpRoutePolicySetOriginEgpAs OBJECT-TYPE
        SYNTAX        Integer32
        MAX-ACCESS    read-write
        STATUS        current
        DESCRIPTION   "indicates the Remote autonomous sys number.
                       Applicable to BGP only."
        DEFVAL         {0}
        ::= { rcIpRoutePolicyEntry 29 }

rcIpRoutePolicySetTag OBJECT-TYPE
        SYNTAX        Integer32
        MAX-ACCESS    read-write
        STATUS        current
        DESCRIPTION   "Value to be used for setting tag of the
                       destination routing protocol. If not specified
                       forward the tag value in the source routing
                       protocol. Value 0 indicates not set"
        DEFVAL         {0}
        ::= { rcIpRoutePolicyEntry 30 }

rcIpRoutePolicySetWeight OBJECT-TYPE
        SYNTAX        Integer32
        MAX-ACCESS    read-write
        STATUS        current
        DESCRIPTION   "Should be using with match as-path condition.
                       Weight value for the routing table. For BGP
                       this value will override the weight configured
                       through NetworkTableEntry or FilterListWeight or
                       NeighborWeight. Used for BGP only.Value 0
                       indicates not set"
        DEFVAL         {0}
        ::= { rcIpRoutePolicyEntry 31 }

rcIpRoutePolicySetInjectNetList OBJECT-TYPE
        SYNTAX        DisplayString 
        MAX-ACCESS    read-write
        STATUS        current
        DESCRIPTION   "specifies the prefix list to be used either
                       for injecting the routes into the routing
                       table or to include the networks in the
                       advertisement. Ignored for DVMRP."
        DEFVAL        {""}
        ::= { rcIpRoutePolicyEntry 32 }

rcIpRoutePolicyRowStatus OBJECT-TYPE
        SYNTAX        RowStatus
        MAX-ACCESS    read-write
        STATUS        current
        DESCRIPTION   "row status"
        ::= { rcIpRoutePolicyEntry 33 }

rcIpRoutePolicySetMask OBJECT-TYPE
        SYNTAX        IpAddress
        MAX-ACCESS    read-write
        STATUS        current
        DESCRIPTION   "Set Mask Ip Address"
        DEFVAL   { '00000000'H }    -- 0.0.0.0
        ::= { rcIpRoutePolicyEntry 34 }

rcIpRoutePolicyNssaPbit OBJECT-TYPE
        SYNTAX        EnableValue
        MAX-ACCESS    read-write
        STATUS        current
        DESCRIPTION   "Set/Reset P bit in specified type 7 LSA.
                       By default P bit is always set in case user
                       set it to disable state for particular route
                       policy than all type 7 LSAs associated with
                       that route policy will have P bit cleared, 
                       with this intact NSSA ABR will not perform
                       translation of these LSAs to type 5."
        DEFVAL        { enable }
        ::= { rcIpRoutePolicyEntry 35 }

rcIpRoutePolicyMatchVrf OBJECT-TYPE
        SYNTAX        IdList (SIZE (0..1024))
        MAX-ACCESS    read-write
        STATUS        current
        DESCRIPTION   "An array used to identify which source VRFs have leaked 
                       routes to the local VRF"
        ::= { rcIpRoutePolicyEntry 36 }

rcIpRoutePolicyMatchExtCommunity OBJECT-TYPE
        SYNTAX        DisplayString
        MAX-ACCESS    read-create
        STATUS        current
        DESCRIPTION   "Filter incoming/outgoing updates based on communities"
        ::= { rcIpRoutePolicyEntry 37 }
 
rcIpRoutePolicySetExtCommunity  OBJECT-TYPE
        SYNTAX        DisplayString
        MAX-ACCESS    read-create
        STATUS        current
        DESCRIPTION   "Set Extended-community string."
        ::= { rcIpRoutePolicyEntry 38 }
 
rcIpRoutePolicySetExtCommunityMode  OBJECT-TYPE
        SYNTAX        INTEGER {
                             append(0),
                             unchanged(1),
                             overwrite(2)
                      }
        MAX-ACCESS    read-create
        STATUS        current
        DESCRIPTION   "This value can be either additive, unchanged or overwrite."
        ::= { rcIpRoutePolicyEntry 39}

rcIpRoutePolicyMatchLocalPref   OBJECT-TYPE
	SYNTAX        Integer32
        MAX-ACCESS    read-create
        STATUS        current
        DESCRIPTION   "Match Local Prefix value."
        ::= { rcIpRoutePolicyEntry 40}

rcIpRoutePolicyMatchIpRouteDest  OBJECT-TYPE
        SYNTAX        RcLongDisplayString (SIZE(0..259))
        MAX-ACCESS    read-create
        STATUS        current
        DESCRIPTION   "to match route destination, one can specify one
                      or more prefix list name(s) or id(s) separated by comma."
        DEFVAL        {""}
        ::= { rcIpRoutePolicyEntry 41 }

rcIpRoutePolicySetLevel OBJECT-TYPE
        SYNTAX        INTEGER {
                                level1(1),
                                level2(2)
                              }
        MAX-ACCESS        read-create
        STATUS        current
        DESCRIPTION   "Level of the Ip routing policy"
        ::= { rcIpRoutePolicyEntry 42 }

rcIpRoutePolicyIpv6SetNextHop OBJECT-TYPE
        SYNTAX        Ipv6Address
        MAX-ACCESS    read-create
        STATUS        current
        DESCRIPTION   "Address of the ipv6 next hop router.  Ignored for
                       DVMRP routes."
        ::= { rcIpRoutePolicyEntry 43 }

-- Ip Redistribute Table

rcIpRedistributeTableSize OBJECT-TYPE
        SYNTAX        Integer32
        MAX-ACCESS    read-only
        STATUS        current
        DESCRIPTION   "table size"
        ::= { rcIpGenPolicy 14 }

rcIpRedistributeApply OBJECT-TYPE
        SYNTAX        TruthValue
        MAX-ACCESS    read-write
        STATUS        current
        DESCRIPTION   ""
	       DEFVAL        { true } 
        ::= { rcIpGenPolicy 15 }

-- Ip Redistribute Table

rcIpRedistributeTableSize OBJECT-TYPE
        SYNTAX        Integer32
        MAX-ACCESS    read-only
        STATUS        current
        DESCRIPTION   "table size"
        ::= { rcIpGenPolicy 14 }

rcIpRedistributeApply OBJECT-TYPE
        SYNTAX        TruthValue
        MAX-ACCESS    read-write
        STATUS        current
        DESCRIPTION   ""
	       DEFVAL        { true } 
        ::= { rcIpGenPolicy 15 }

rcIpRedistributeTable OBJECT-TYPE
        SYNTAX          SEQUENCE OF RcIpRedistributeEntry
        MAX-ACCESS      not-accessible
        STATUS          current
        DESCRIPTION     "IP Redistribute table"
        ::= { rcIpGenPolicy 16 }

rcIpRedistributeEntry OBJECT-TYPE
        SYNTAX          RcIpRedistributeEntry
        MAX-ACCESS      not-accessible
        STATUS          current
        DESCRIPTION     "An entry of Ip Redistribute Table."
        INDEX           { rcIpRedistributeProtocol,
                           rcIpRedistributeRouteSource }
        ::= { rcIpRedistributeTable 1 }

RcIpRedistributeEntry ::=
        SEQUENCE {
                rcIpRedistributeProtocol         INTEGER,
                rcIpRedistributeRouteSource      INTEGER,
                rcIpRedistributeEnable           EnableValue,
                rcIpRedistributeMetric           INTEGER,
                rcIpRedistributeMetricType       INTEGER,
                rcIpRedistributeMatchRouteType   INTEGER,
                rcIpRedistributeSetTag           Integer32,
                rcIpRedistributeSubnets          INTEGER,
                rcIpRedistributeRoutePolicy      DisplayString,
                rcIpRedistributeASNumber         Integer32,
                rcIpRedistributeWeight           Integer32,
                rcIpRedistributeDefaultOriginate Integer32,
                rcIpRedistributeRowStatus        RowStatus
        }

rcIpRedistributeProtocol OBJECT-TYPE
        SYNTAX        INTEGER {
                          ospf(1),
                          bgp(2),
                          isis(3),
                          ospfv3(4),
                          vrf-ext(5)
                      }
        MAX-ACCESS    read-only
        STATUS        current
        DESCRIPTION   "Protocol is any one of the dynamic routing
                       protocol, which  is interested in receiving
                       the external routing info."
        ::= { rcIpRedistributeEntry 1 }

rcIpRedistributeRouteSource OBJECT-TYPE
        SYNTAX        INTEGER {
                          direct(1),
                          static(2),
                          rip(3),
                          ospf(4),
                          bgp(5),
                          extranet(6),
                          v6direct(10), 
                          v6static(11),
                          ospfv3(12),
                          isis(13)    
                      }
        MAX-ACCESS    read-only
        STATUS        current
        DESCRIPTION   "equivalent to the owner field in the routing
                       table. This field indicates that the protocol
                       is interested in knowing/not-knowing the routes
                       learned from this source."
        ::= { rcIpRedistributeEntry 2 }

rcIpRedistributeEnable OBJECT-TYPE
        SYNTAX        EnableValue
        MAX-ACCESS    read-write
        STATUS        current
        DESCRIPTION   "Enable/Disable. By default this is enabled."
        DEFVAL        { disable }
        ::= { rcIpRedistributeEntry 3 }

rcIpRedistributeMetric OBJECT-TYPE
        SYNTAX        INTEGER (0..65535)
        MAX-ACCESS    read-write
        STATUS        current
        DESCRIPTION   "value of the metric to be announced in the
                       advertisment"
        DEFVAL        { 0 }
        ::= { rcIpRedistributeEntry 4 }

rcIpRedistributeMetricType OBJECT-TYPE
        SYNTAX        INTEGER {
                          type1(1),
                          type2(2)
                      }
        MAX-ACCESS    read-write
        STATUS        current
        DESCRIPTION   "specifies the type of the metric type, useful
                       for OSPF and  BGP only."
        DEFVAL        { type2 }
        ::= { rcIpRedistributeEntry 5 }

rcIpRedistributeMatchRouteType OBJECT-TYPE
        SYNTAX        INTEGER {
                          internal(1),
                          external1(2),
                          external2(3)
                      }
        MAX-ACCESS    read-write
        STATUS        current
        DESCRIPTION   "used to filter a route based on the route type.
                       applicable to BGP."
        ::= { rcIpRedistributeEntry 6 }

rcIpRedistributeSetTag OBJECT-TYPE
        SYNTAX        Integer32
        MAX-ACCESS    read-write
        STATUS        current
        DESCRIPTION   "Tag value to be set in the advertisment."
        ::= { rcIpRedistributeEntry 7 }

rcIpRedistributeSubnets OBJECT-TYPE
        SYNTAX        INTEGER {
                          allow(1),
                          supress(2)
                      }
        MAX-ACCESS    read-write
        STATUS        current
        DESCRIPTION   "applicable to OSPF only. Indicates that all the
                       subnets need to be advertised individually."
        DEFVAL        { allow }
        ::= { rcIpRedistributeEntry 8 }

rcIpRedistributeRoutePolicy OBJECT-TYPE
        SYNTAX        DisplayString
        MAX-ACCESS    read-write
        STATUS        current
        DESCRIPTION   "specify the route policy to achieve the final
                       granularity in filtering to determine whether
                       or not a specific route should be advertised
                       to the given protocol.Route map name"
        ::= { rcIpRedistributeEntry 9 }

rcIpRedistributeASNumber OBJECT-TYPE
        SYNTAX        Integer32
        MAX-ACCESS    read-write
        STATUS        current
        DESCRIPTION   "Autonomous system number. Used only for the
                       BGP protocol."
        ::= { rcIpRedistributeEntry 10 }

rcIpRedistributeWeight OBJECT-TYPE
        SYNTAX        Integer32
        MAX-ACCESS    read-write
        STATUS        current
        DESCRIPTION   "used only for the BGP protocol."
        ::= { rcIpRedistributeEntry 11 }

rcIpRedistributeDefaultOriginate OBJECT-TYPE
        SYNTAX        Integer32
        MAX-ACCESS    read-write
        STATUS        current
        DESCRIPTION   "indicates the given protocol will
                        originate/advertise a default route."
        ::= { rcIpRedistributeEntry 12 }

rcIpRedistributeRowStatus OBJECT-TYPE
        SYNTAX        RowStatus
        MAX-ACCESS    read-write
        STATUS        current
        DESCRIPTION   "row status"
        ::= { rcIpRedistributeEntry 13 }

-- IP Ospf In Filter Table

rcIpOspfInFilterTableSize OBJECT-TYPE
        SYNTAX        Integer32
        MAX-ACCESS    read-only
        STATUS        current
        DESCRIPTION   "table size"
        ::= { rcIpGenPolicy 17 }

rcIpOspfInFilterApply OBJECT-TYPE
        SYNTAX        TruthValue
        MAX-ACCESS    read-write
        STATUS        current
        DESCRIPTION   ""
        ::= { rcIpGenPolicy 18 }

rcIpOspfInFilterTable OBJECT-TYPE
        SYNTAX          SEQUENCE OF RcIpOspfInFilterEntry
        MAX-ACCESS      not-accessible
        STATUS          current
        DESCRIPTION     "IP Ospf In Filter table"
        ::= { rcIpGenPolicy 19 }

rcIpOspfInFilterEntry OBJECT-TYPE
        SYNTAX          RcIpOspfInFilterEntry
        MAX-ACCESS      not-accessible
        STATUS          current
        DESCRIPTION     "An entry of Ip Ospf In Filter Table."
        INDEX           { rcIpOspfInFilterAdvertisingRtr }
        ::= { rcIpOspfInFilterTable 1 }

RcIpOspfInFilterEntry ::=
        SEQUENCE {
                rcIpOspfInFilterAdvertisingRtr  IpAddress,
                rcIpOspfInFilterEnable          EnableValue,
                rcIpOspfInFilterMetricType      INTEGER,
                rcIpOspfInFilterPolicyName      DisplayString,
                rcIpOspfInFilterRowStatus       RowStatus
        }

rcIpOspfInFilterAdvertisingRtr OBJECT-TYPE
        SYNTAX        IpAddress
        MAX-ACCESS    read-only
        STATUS        current
        DESCRIPTION   ""
        ::= { rcIpOspfInFilterEntry 1 }

rcIpOspfInFilterEnable OBJECT-TYPE
        SYNTAX        EnableValue
        MAX-ACCESS    read-write
        STATUS        current
        DESCRIPTION   "IfIndex"
        DEFVAL        { disable }
        ::= { rcIpOspfInFilterEntry 2 }

rcIpOspfInFilterMetricType OBJECT-TYPE
        SYNTAX        INTEGER {
                          type1(1),
                          type2(2),
                          any(3)
                      }
        MAX-ACCESS    read-write
        STATUS        current
        DESCRIPTION   ""
        DEFVAL        { any }
        ::= { rcIpOspfInFilterEntry 3 }

rcIpOspfInFilterPolicyName OBJECT-TYPE
        SYNTAX        DisplayString
        MAX-ACCESS    read-write
        STATUS        current
        DESCRIPTION   ""
        ::= { rcIpOspfInFilterEntry 4 }

rcIpOspfInFilterRowStatus OBJECT-TYPE
        SYNTAX        RowStatus
        MAX-ACCESS    read-write
        STATUS        current
        DESCRIPTION   ""
        ::= { rcIpOspfInFilterEntry 5 }


-- Ip Route Pref Table


rcIpRoutePrefTableSize OBJECT-TYPE
        SYNTAX        Integer32
        MAX-ACCESS    read-only
        STATUS        current
        DESCRIPTION   "table size"
        ::= { rcIpGenPolicy 20 }

rcIpRoutePrefTable OBJECT-TYPE
        SYNTAX          SEQUENCE OF RcIpRoutePrefEntry
        MAX-ACCESS      not-accessible
        STATUS          current
        DESCRIPTION     "IP Route Pref table"
        ::= { rcIpGenPolicy 21 }

rcIpRoutePrefEntry OBJECT-TYPE
        SYNTAX          RcIpRoutePrefEntry
        MAX-ACCESS      not-accessible
        STATUS          current
        DESCRIPTION     "An entry of Ip Route Pref Table."
        INDEX           { rcIpRoutePrefProtocol }
        ::= { rcIpRoutePrefTable 1 }

RcIpRoutePrefEntry ::=
        SEQUENCE {
                rcIpRoutePrefProtocol    INTEGER,
                rcIpRoutePrefDefault     INTEGER,
                rcIpRoutePrefConfigured  INTEGER
        }

rcIpRoutePrefProtocol OBJECT-TYPE
        SYNTAX        INTEGER {
                          local(1),
                          static(2),
                          mpls(3),
                          ospfIntra(4),
                          ospfInter(5),
                          isisLevel1(6),
                          isisLevel2(7),
                          ebgp(8),
                          rip(9),
                          ospfExternal1(10),
                          ospfExternal2(11),
                          ibgp(12),
                          staticv6(13),
                          ospfv3Intra(14),
                          ospfv3Inter(15),
                          ospfv3External1(16),
                          ospfv3External2(17),
                          spbmLevel1(18)
                      }
        MAX-ACCESS    read-only
        STATUS        current
        DESCRIPTION   "Protocol"
        ::= { rcIpRoutePrefEntry 1 }

rcIpRoutePrefDefault OBJECT-TYPE
        SYNTAX        INTEGER (0..255)
        MAX-ACCESS    read-only
        STATUS        current
        DESCRIPTION   "Shows the default preference value for the given
                       protocol."
        ::= { rcIpRoutePrefEntry 2 }

rcIpRoutePrefConfigured OBJECT-TYPE
        SYNTAX        INTEGER (0..255)
        MAX-ACCESS    read-write
        STATUS        current
        DESCRIPTION   "This value is configurable by the user"
        ::= { rcIpRoutePrefEntry 3 }

-- Redistribute table

rcIpRedistributeInterVrfTable OBJECT-TYPE
        SYNTAX          SEQUENCE OF RcIpRedistributeInterVrfEntry
        MAX-ACCESS      not-accessible
        STATUS          current
        DESCRIPTION     "IP Redistribute table for Inter-VRFs"
        ::= { rcIpGenPolicy 22 }

rcIpRedistributeInterVrfEntry OBJECT-TYPE
        SYNTAX          RcIpRedistributeInterVrfEntry
        MAX-ACCESS      not-accessible
        STATUS          current
        DESCRIPTION     "An entry of Ip Redistribute Table.(new) "
        INDEX           { rcIpRedistributeInterVrfDstVrfId, 
                          rcIpRedistributeInterVrfProtocol,
                          rcIpRedistributeInterVrfSrcVrfId,
                          rcIpRedistributeInterVrfRouteSource }
        ::= { rcIpRedistributeInterVrfTable 1 }

RcIpRedistributeInterVrfEntry ::=
        SEQUENCE {
                rcIpRedistributeInterVrfDstVrfId         VrfIdentifier,
                rcIpRedistributeInterVrfProtocol         INTEGER,
                rcIpRedistributeInterVrfSrcVrfId         VrfIdentifier,
                rcIpRedistributeInterVrfRouteSource      INTEGER,
                rcIpRedistributeInterVrfEnable           EnableValue,
                rcIpRedistributeInterVrfMetric           INTEGER,
                rcIpRedistributeInterVrfMetricType       INTEGER,
                rcIpRedistributeInterVrfMatchRouteType   INTEGER,
                rcIpRedistributeInterVrfSetTag           Integer32,
                rcIpRedistributeInterVrfSubnets          INTEGER,
                rcIpRedistributeInterVrfRoutePolicy      DisplayString,
                rcIpRedistributeInterVrfASNumber         Integer32,
                rcIpRedistributeInterVrfWeight           Integer32,
                rcIpRedistributeInterVrfDefaultOriginate Integer32,
                rcIpRedistributeInterVrfRowStatus        RowStatus
        }

rcIpRedistributeInterVrfDstVrfId OBJECT-TYPE
        SYNTAX        VrfIdentifier
        MAX-ACCESS    not-accessible
        STATUS        current
        DESCRIPTION   "dst VRF id used in the redistribution"
        ::= { rcIpRedistributeInterVrfEntry 1 }

rcIpRedistributeInterVrfProtocol OBJECT-TYPE
        SYNTAX        INTEGER {
                          ospf(1),
                          bgp(2),
                          isis(3),
                          vrf-ext(4),
                          extranet(5),
                          rip(6),
                          ospfv3(10)
                      }
        MAX-ACCESS    not-accessible
        STATUS        current
        DESCRIPTION   "Protocol is any one of the dynamic routing
                       protocol, which  is interested in receiving
                       the external routing info."
        ::= { rcIpRedistributeInterVrfEntry 2 }

rcIpRedistributeInterVrfSrcVrfId OBJECT-TYPE
        SYNTAX        VrfIdentifier
        MAX-ACCESS    not-accessible
        STATUS        current
        DESCRIPTION   "src VRF id used in the redistribution"
        ::= { rcIpRedistributeInterVrfEntry 3 }

rcIpRedistributeInterVrfRouteSource OBJECT-TYPE
        SYNTAX        INTEGER {
                          direct(1),
                          static(2),
                          rip(3),
                          ospf(4),
                          bgp(5),
                          extranet(6),
                          v6direct(10),
                          v6static(11),
                          ospfv3(12),
                          isis(13)
                      }
        MAX-ACCESS    not-accessible
        STATUS        current
        DESCRIPTION   "equivalent to the owner field in the routing
                       table. This field indicates that the protocol
                       is interested in knowing/not-knowing the routes
                       learned from this source."
        ::= { rcIpRedistributeInterVrfEntry 4 }

rcIpRedistributeInterVrfEnable OBJECT-TYPE
        SYNTAX        EnableValue
        MAX-ACCESS    read-write
        STATUS        current
        DESCRIPTION   "Enable/Disable. By default this is enabled."
        DEFVAL        { disable }
        ::= { rcIpRedistributeInterVrfEntry 5 }


rcIpRedistributeInterVrfMetric OBJECT-TYPE
        SYNTAX        INTEGER (0..65535)
        MAX-ACCESS    read-write
        STATUS        current
        DESCRIPTION   "value of the metric to be announced in the
                       advertisment"
        DEFVAL        { 0 }
        ::= { rcIpRedistributeInterVrfEntry 6 }

rcIpRedistributeInterVrfMetricType OBJECT-TYPE
        SYNTAX        INTEGER {
                          type1(1),
                          type2(2)
                      }
        MAX-ACCESS    read-write
        STATUS        current
        DESCRIPTION   "specifies the type of the metric type, useful
                       for OSPF and  BGP only."
        DEFVAL        { type2 }
        ::= { rcIpRedistributeInterVrfEntry 7 }

rcIpRedistributeInterVrfMatchRouteType OBJECT-TYPE
        SYNTAX        INTEGER {
                          internal(1),
                          external1(2),
                          external2(3)
                      }
        MAX-ACCESS    read-write
        STATUS        current
        DESCRIPTION   "used to filter a route based on the route type.
                       applicable to BGP."
        ::= { rcIpRedistributeInterVrfEntry 8 }


rcIpRedistributeInterVrfSetTag OBJECT-TYPE
        SYNTAX        Integer32
        MAX-ACCESS    read-write
        STATUS        current
        DESCRIPTION   "Tag value to be set in the advertisment."
        ::= { rcIpRedistributeInterVrfEntry 9 }

rcIpRedistributeInterVrfSubnets OBJECT-TYPE
        SYNTAX        INTEGER {
                          allow(1),
                          suppress(2)
                      }
        MAX-ACCESS    read-write
        STATUS        current
        DESCRIPTION   "applicable to OSPF only. Indicates that all the
                       subnets need to be advertised individually."
        DEFVAL        { allow }
        ::= { rcIpRedistributeInterVrfEntry 10 }

rcIpRedistributeInterVrfRoutePolicy OBJECT-TYPE
        SYNTAX        DisplayString
        MAX-ACCESS    read-write
        STATUS        current
        DESCRIPTION   "specify the route policy to achieve the final
                       granularity in filtering to determine whether
                       or not a specific route should be advertised
                       to the given protocol.Route map name"
        ::= { rcIpRedistributeInterVrfEntry 11 }

rcIpRedistributeInterVrfASNumber OBJECT-TYPE
        SYNTAX        Integer32
        MAX-ACCESS    read-write
        STATUS        current
        DESCRIPTION   "Autonomous system number. Used only for the
                       BGP protocol."
        ::= { rcIpRedistributeInterVrfEntry 12 }

rcIpRedistributeInterVrfWeight OBJECT-TYPE
        SYNTAX        Integer32
        MAX-ACCESS    read-write
        STATUS        current
        DESCRIPTION   "used only for the BGP protocol."
        ::= { rcIpRedistributeInterVrfEntry 13 }

rcIpRedistributeInterVrfDefaultOriginate OBJECT-TYPE
        SYNTAX        Integer32
        MAX-ACCESS    read-write
        STATUS        current
        DESCRIPTION   "indicates the given protocol will
                        originate/advertise a default route."
        ::= { rcIpRedistributeInterVrfEntry 14 }

--IpExtCommunityList Table

rcIpExtCommunityAccessListTableSize OBJECT-TYPE
     SYNTAX        Integer32
     MAX-ACCESS    read-only
     STATUS        current
     DESCRIPTION   "IP Extended Community Access List table size."
     ::= {rcIpGenPolicy 23  }

rcIpExtCommunityAccessListTable OBJECT-TYPE
        SYNTAX          SEQUENCE OF RcIpExtCommunityAccessListEntry
        MAX-ACCESS      not-accessible
        STATUS          current
        DESCRIPTION     "IP Extended Community Access List table."
    ::= {rcIpGenPolicy 24 }   
 
rcIpExtCommunityAccessListEntry OBJECT-TYPE
        SYNTAX          RcIpExtCommunityAccessListEntry
        MAX-ACCESS              not-accessible
        STATUS          current
        DESCRIPTION     "An entry of Ip Extended Community Access List Table."
        INDEX           { rcIpExtCommunityAccessListId,
                                   rcIpExtCommunityAccessListMemberId }
        ::= { rcIpExtCommunityAccessListTable 1 }

RcIpExtCommunityAccessListEntry ::=
        SEQUENCE {
                rcIpExtCommunityAccessListId        INTEGER,
                rcIpExtCommunityAccessListMemberId  INTEGER,
                rcIpExtCommunityAccessListRTType     INTEGER,
                rcIpExtCommunityAccessListRTAddress  IpAddress,
                rcIpExtCommunityAccessListRTAsNumber    INTEGER,
                rcIpExtCommunityAccessListRTAssignedNum Unsigned32,
                rcIpExtCommunityAccessListSooType        INTEGER,
                rcIpExtCommunityAccessListSooAddress   IpAddress,
                rcIpExtCommunityAccessListSooAsNumber     INTEGER,
                rcIpExtCommunityAccessListSooAssignedNum Unsigned32,
                rcIpExtCommunityAccessListVrfId       VrfIdentifier,
                rcIpExtCommunityAccessListRowStatus   RowStatus
        }

rcIpExtCommunityAccessListId OBJECT-TYPE
        SYNTAX        INTEGER (1..1024)
        MAX-ACCESS    not-accessible
        STATUS        current
        DESCRIPTION   "IP extended Community Access List Id"
        ::= { rcIpExtCommunityAccessListEntry 1 }
 
rcIpExtCommunityAccessListMemberId OBJECT-TYPE
        SYNTAX        INTEGER (0..65535)
        MAX-ACCESS    not-accessible
        STATUS        current
        DESCRIPTION   "Member Id for the extended-community list to be added"
        ::= { rcIpExtCommunityAccessListEntry 2 }
 
rcIpExtCommunityAccessListRTType  OBJECT-TYPE
        SYNTAX        INTEGER  {
                        	none(0),
                  		asnum(1),
                   		ipaddr(2)
                  		}
        MAX-ACCESS    read-only
        STATUS        current
        DESCRIPTION   "The route target Type for IP Extended Community rule in the list"
        DEFVAL       {asnum}
        ::= { rcIpExtCommunityAccessListEntry 3 }
        
rcIpExtCommunityAccessListRTAddress OBJECT-TYPE
        SYNTAX       IpAddress
        MAX-ACCESS    read-create
        STATUS        current
        DESCRIPTION   "Extended community Ip address for the route-target type entry."
        ::= { rcIpExtCommunityAccessListEntry 4 }

rcIpExtCommunityAccessListRTAsNumber OBJECT-TYPE
        SYNTAX       INTEGER (0..65535)
        MAX-ACCESS    read-create
        STATUS        current
        DESCRIPTION   "Extended community Asnumber for the route-target type entry."
        ::= { rcIpExtCommunityAccessListEntry 5 }

rcIpExtCommunityAccessListRTAssignedNum OBJECT-TYPE
        SYNTAX        Unsigned32 (0..2147483647)
        MAX-ACCESS    read-create
        STATUS        current
        DESCRIPTION   "Extended community assigned number for the route-target type entry."
        ::= { rcIpExtCommunityAccessListEntry 6 }

  rcIpExtCommunityAccessListSooType  OBJECT-TYPE
        SYNTAX        INTEGER  {
                   		none(0),
                    		asnum(1),
                    		ipaddr(2)
                 		}
       MAX-ACCESS     read-only
        STATUS        current
        DESCRIPTION   "The site of origin Type for IP Extended Community Access List"
        DEFVAL       {asnum}
        ::= {  rcIpExtCommunityAccessListEntry 7 }

rcIpExtCommunityAccessListSooAddress OBJECT-TYPE
        SYNTAX       IpAddress
        MAX-ACCESS    read-create
        STATUS        current
        DESCRIPTION   " Extended community Ip address for the site-of-origin type of entry."
        ::= { rcIpExtCommunityAccessListEntry 8 }

rcIpExtCommunityAccessListSooAsNumber OBJECT-TYPE
        SYNTAX       INTEGER (0..65535)
        MAX-ACCESS    read-create
        STATUS        current
        DESCRIPTION   " Extended community AsNumber for the site-of-origin type of entry."
        ::= { rcIpExtCommunityAccessListEntry 9 }
 
rcIpExtCommunityAccessListSooAssignedNum OBJECT-TYPE
        SYNTAX        Unsigned32 (0..2147483647)
        MAX-ACCESS    read-create
        STATUS        current
        DESCRIPTION   " Extended community assigned number for the site-of-origin type of entry."
        ::= { rcIpExtCommunityAccessListEntry 10 }


rcIpExtCommunityAccessListVrfId OBJECT-TYPE
        SYNTAX          VrfIdentifier
        MAX-ACCESS      read-create
        STATUS          current
        DESCRIPTION     "VrfId for the extended-community Access list."
        ::= { rcIpExtCommunityAccessListEntry 11 }

rcIpExtCommunityAccessListRowStatus OBJECT-TYPE
        SYNTAX        RowStatus
        MAX-ACCESS    read-create
        STATUS        current
        DESCRIPTION   "IP Ext Community Table Row Status."
        ::= { rcIpExtCommunityAccessListEntry  12 }

rcIpRedistributeInterVrfRowStatus OBJECT-TYPE
        SYNTAX        RowStatus
        MAX-ACCESS    read-write
        STATUS        current
        DESCRIPTION   "row status"
        ::= { rcIpRedistributeInterVrfEntry 15 }

-- Ip BGP


rcIpBgp OBJECT IDENTIFIER ::= { rcIp 101 }

rcIpBgpGeneralGroup OBJECT IDENTIFIER ::= { rcIpBgp 1 }

rcIpBgpGeneralGroupLocalAs OBJECT-TYPE
        SYNTAX        Integer32 (0..65535)
        MAX-ACCESS    read-write
        STATUS        current
        DESCRIPTION   "Local Autonomous system number"
        ::= { rcIpBgpGeneralGroup 1 }

rcIpBgpGeneralGroupAdminStatus OBJECT-TYPE
        SYNTAX        EnableValue
        MAX-ACCESS    read-write
        STATUS        current
        DESCRIPTION   "Disable or Enable group administrative"
        DEFVAL { enable }
        ::= { rcIpBgpGeneralGroup 2 }

rcIpBgpGeneralGroupDefaultMetric OBJECT-TYPE
        SYNTAX        Integer32 (-1..2147483647)
        MAX-ACCESS    read-write
        STATUS        current
        DESCRIPTION   "The default-metric is used in conjunction with
                       the redistribute router configuration command to cause
                       the bgp routing protocol to use this metric as MED"
        DEFVAL        { -1 }
        ::= { rcIpBgpGeneralGroup 3 }

rcIpBgpGeneralGroupDefaultLocalPreference OBJECT-TYPE
        SYNTAX        Integer32 (0..2147483647)
        MAX-ACCESS    read-write
        STATUS        current
        DESCRIPTION   " Default local preference attribute value to be used "
        DEFVAL {100}
        ::= { rcIpBgpGeneralGroup 4 }

rcIpBgpGeneralGroupDefaultInformationOriginate OBJECT-TYPE
        SYNTAX        TruthValue
        MAX-ACCESS    read-write
        STATUS        current
        DESCRIPTION   "allows the redistribution of network 0.0.0.0 into BGP"
        DEFVAL {false}
        ::= { rcIpBgpGeneralGroup 5 }

rcIpBgpGeneralGroupBestPathMissingAsWorst OBJECT-TYPE
        SYNTAX        EnableValue
        MAX-ACCESS    read-write
        STATUS        current
        DESCRIPTION   "Enable to consider a missing MED attribute in a path
                       as having a value of infinity, making the path without a
                       MED value the least desirable path. To return the router
                       to the default (assign a value of 0 to the missing MED),
                        set the value to disable."
        DEFVAL        {enable}
        ::= { rcIpBgpGeneralGroup 6 }

rcIpBgpGeneralGroupBestPathMedConfed OBJECT-TYPE
        SYNTAX        EnableValue
        MAX-ACCESS    read-write
        STATUS        current
        DESCRIPTION   "To enable MED comparison among paths learned from
                       confederation peers. Disable to prevent considering
                       the MED attribute in comparing paths"
        DEFVAL          {disable}
        ::= { rcIpBgpGeneralGroup 7 }

rcIpBgpGeneralGroupIgnoreIllegalRouterId OBJECT-TYPE
        SYNTAX        EnableValue
        MAX-ACCESS    read-write
        STATUS        current
        DESCRIPTION   "Configures BGP to overlook an illegal router ID.
                       Enables or disable accepting a connection from a peer
                       that sends its open message with a router ID of 0."
        DEFVAL          {disable}
        ::= { rcIpBgpGeneralGroup 8 }

rcIpBgpGeneralGroupAlwaysCompareMed OBJECT-TYPE
        SYNTAX        EnableValue
        MAX-ACCESS    read-write
        STATUS        current
        DESCRIPTION   "Enable to allow the comparison of the Multi Exit
                       Discriminator (MED) for paths from neighbors in
                       different autonomous systems."
        DEFVAL        {disable}
        ::= { rcIpBgpGeneralGroup 9 }

rcIpBgpGeneralGroupAutoPeerRestart OBJECT-TYPE
        SYNTAX        EnableValue
        MAX-ACCESS    read-write
        STATUS        current
        DESCRIPTION   "Enable the feature that automatically restarts the
                       connection to a BGP peer when the connection goes down."
        DEFVAL        {enable}
        ::= { rcIpBgpGeneralGroup 10 }

rcIpBgpGeneralGroupAutoSummary OBJECT-TYPE
        SYNTAX        EnableValue
        MAX-ACCESS    read-write
        STATUS        current
        DESCRIPTION   "Enable BGP to summarize networks based on class limlts
                       (Class A,B,C networks)."
        DEFVAL        {enable}
        ::= { rcIpBgpGeneralGroup 11 }

rcIpBgpGeneralGroupSynchronization OBJECT-TYPE
        SYNTAX        EnableValue
        MAX-ACCESS    read-write
        STATUS        current
        DESCRIPTION   "Enables and disables the router from accepting routes
                       from BGP peers without waiting for an update from the
                       IBGP."
        DEFVAL        {enable}
        ::= { rcIpBgpGeneralGroup 12 }

rcIpBgpGeneralGroupMaxEqualcostRoutes OBJECT-TYPE
        SYNTAX        Integer32 (1..8)
        MAX-ACCESS    read-write
        STATUS        current
        DESCRIPTION   "Sets the number of maximum number of equal-cost routes
                       that can be stored in the routing table."
        DEFVAL          {1}
        ::= { rcIpBgpGeneralGroup 13 }

rcIpBgpGeneralGroupIbgpReportImportRoute OBJECT-TYPE
        SYNTAX        EnableValue
        MAX-ACCESS    read-write
        STATUS        current
        DESCRIPTION   "Configure BGP to report imported routes to an interior
                       BGP peer."
        DEFVAL        {enable}
        ::= { rcIpBgpGeneralGroup 14 }

rcIpBgpGeneralGroupAggregate OBJECT-TYPE
        SYNTAX        EnableValue
        MAX-ACCESS    read-write
        STATUS        current
        DESCRIPTION   " "
        DEFVAL        {enable}
        ::= { rcIpBgpGeneralGroup 15 }

rcIpBgpGeneralGroupFlapDampEnable OBJECT-TYPE
        SYNTAX  EnableValue 
        MAX-ACCESS  read-write
        STATUS  current
        DESCRIPTION "Enabled or Disabled"
        DEFVAL  { disable }
        ::= { rcIpBgpGeneralGroup 16 }

rcIpBgpGeneralGroupDebugMask OBJECT-TYPE
        SYNTAX  Integer32 (0..511) 
        MAX-ACCESS     read-write
        STATUS         current
        DESCRIPTION    " value is one of multiple (logically by 'OR' of
                         following value:
                                 none (0),
                                 error(1),
                                 packet(2),
                                 event(4),
                                 trace(8),
                                 warning(16),
                                 state(32),
                                 init(64),
                                 filter(128),
                                 update(256),
                                 all(511)
			all(511): Enables all debugging messages.
                        none(0): Disables all debugging messages.
                        error(1): Enables disolay of debug error messages.
                        packet(2): Enables display of debug packet messages.
                        event(4): Enables display of debug event messages.
                        trace(8): Enables display debug trace messages.
                        warning(16): Enables display debug warning messages.
                        state(32): Enables display of debug state transtion
                               messages.
                        init(64): Enables display of debug initialization 
                               messages.
                        filter(128): Enables display of debug messages related 
                               to filtering.
                        update(256): Enables display of debug messages related 
                               to sending and receiving updates."
        DEFVAL          { 0 }
        ::= { rcIpBgpGeneralGroup 17 }


-- Following between =begin =end is processed by mib_tools/extras.awk


-- =begin enum
-- rcIpBgpGeneralGroupDebugMask none    0
-- rcIpBgpGeneralGroupDebugMask error   1
-- rcIpBgpGeneralGroupDebugMask packet  2
-- rcIpBgpGeneralGroupDebugMask event   4
-- rcIpBgpGeneralGroupDebugMask trace   8
-- rcIpBgpGeneralGroupDebugMask warning 16
-- rcIpBgpGeneralGroupDebugMask state   32
-- rcIpBgpGeneralGroupDebugMask init    64
-- rcIpBgpGeneralGroupDebugMask filter  128
-- rcIpBgpGeneralGroupDebugMask update  256
-- rcIpBgpGeneralGroupDebugMask all     511
-- =end enum

rcIpBgpGeneralGroupTrapEnable  OBJECT-TYPE
        SYNTAX      EnableValue
        MAX-ACCESS  read-write
        STATUS      current 
        DESCRIPTION ""
        DEFVAL       { disable }
        ::= { rcIpBgpGeneralGroup 18 }

rcIpBgpGeneralGroupQuickStart  OBJECT-TYPE
        SYNTAX      EnableValue
        MAX-ACCESS  read-write
        STATUS      current 
        DESCRIPTION "Enable the flag to avoid flap penalty and trigger
                     the peer start event quickly"
        DEFVAL       { disable }
        ::= { rcIpBgpGeneralGroup 19 }

rcIpBgpGeneralGroupDeterministicMed  OBJECT-TYPE
        SYNTAX      EnableValue
        MAX-ACCESS  read-write
        STATUS      current 
        DESCRIPTION "Enable to allow the comparison of the Multi Exit
                     Discriminator (MED) for paths from neighbors in
                     same autonomous system."
        DEFVAL       { disable }
        ::= { rcIpBgpGeneralGroup 20 }

rcIpBgpGeneralGroupRouteRefresh OBJECT-TYPE
        SYNTAX      EnableValue
        MAX-ACCESS  read-create
        STATUS      current
        DESCRIPTION "Route Refresh for Bgp."
        DEFVAL       { disable }
        ::= { rcIpBgpGeneralGroup 21 }
 
 
rcIpBgpGeneralGroupRoutePolicyIn OBJECT-TYPE
        SYNTAX        DisplayString(SIZE(0..64))
        MAX-ACCESS    read-create
        STATUS        current
        DESCRIPTION   "Route Policy Name that will be applied to all routes which enter the VRF table."
        ::= { rcIpBgpGeneralGroup 22 }
 
rcIpBgpGeneralGroupRoutePolicyOut OBJECT-TYPE
        SYNTAX        DisplayString(SIZE(0..64))
        MAX-ACCESS    read-create
        STATUS        current
        DESCRIPTION   "Route policy name that will be applied to all routes which are sent out of this VRF instance."
        ::= { rcIpBgpGeneralGroup 23 }

rcIpBgpGeneralGroupDefaultInformationOriginateIpv6 OBJECT-TYPE
        SYNTAX        TruthValue
        MAX-ACCESS    read-write
        STATUS        current
        DESCRIPTION   "allows the redistribution of default ipv6 
                       network into BGP"
        DEFVAL {false}
        ::= { rcIpBgpGeneralGroup 24 }

rcIpBgpGeneralGroupNewLocalAs OBJECT-TYPE
        SYNTAX        OCTET STRING(SIZE (0..4))
        MAX-ACCESS    read-write
        STATUS        current
        DESCRIPTION   "Local Autonomous system number"
        ::= { rcIpBgpGeneralGroup 25 }

rcIpBgpGeneralGroup4ByteAs OBJECT-TYPE
        SYNTAX            EnableValue
        MAX-ACCESS    read-write
        STATUS        current
        DESCRIPTION   "4 Byte As number enable"
        ::= { rcIpBgpGeneralGroup 26 }

rcIpBgpGeneralGroupAsDot  OBJECT-TYPE
        SYNTAX            EnableValue
        MAX-ACCESS    read-write
        STATUS        current
        DESCRIPTION   "As number in Dot format"
        ::= { rcIpBgpGeneralGroup 27 }

rcIpBgpAggregateTableSize OBJECT-TYPE
        SYNTAX          Integer32
        MAX-ACCESS      read-only
        STATUS          deprecated
        DESCRIPTION     "Size of Aggregate Table"
        ::= { rcIpBgp 2 }

rcIpBgpAggregateTable OBJECT-TYPE
        SYNTAX          SEQUENCE OF RcIpBgpAggregateEntry
        MAX-ACCESS      not-accessible
        STATUS          deprecated
        DESCRIPTION     "To specify the list of aggregate prefixes to be
                         created  by the BGP routing process and the options
                         to be used while aggregating."
        ::= { rcIpBgp 3 }

rcIpBgpAggregateEntry OBJECT-TYPE
        SYNTAX          RcIpBgpAggregateEntry
        MAX-ACCESS      not-accessible
        STATUS          current
        DESCRIPTION     "An entry of rcIpBgp Aggregate Address In Table."
        INDEX           { rcIpBgpAggregateAddress,
                          rcIpBgpAggregateMask }
        ::= { rcIpBgpAggregateTable 1 }

RcIpBgpAggregateEntry ::= 
        SEQUENCE { 
                  rcIpBgpAggregateAddress                IpAddress, 
                  rcIpBgpAggregateMask                   IpAddress, 
                  rcIpBgpAggregateAsSetGenerate          EnableValue, 
                  rcIpBgpAggregateSummaryOnly            EnableValue, 
                  rcIpBgpAggregateSuppressPolicy         DisplayString, 
                  rcIpBgpAggregateAdvertisePolicy        DisplayString, 
                  rcIpBgpAggregateAttributePolicy        DisplayString, 
                  rcIpBgpAggregateRowStatus              RowStatus
                 }

rcIpBgpAggregateAddress OBJECT-TYPE
        SYNTAX        IpAddress
        MAX-ACCESS    read-only
        STATUS        current
        DESCRIPTION   "Prefix to create an aggregate address in BGP routing table."
        ::= { rcIpBgpAggregateEntry 1 }

rcIpBgpAggregateMask OBJECT-TYPE
        SYNTAX        IpAddress
        MAX-ACCESS    read-only
        STATUS        current
        DESCRIPTION   "Mask for the aggregrate"
        ::= { rcIpBgpAggregateEntry 2 }

rcIpBgpAggregateAsSetGenerate OBJECT-TYPE
        SYNTAX        EnableValue
        MAX-ACCESS    read-write
        STATUS        current
        DESCRIPTION   "Enable Generates autonomous system set path
                       information."
        DEFVAL        {disable}
        ::= { rcIpBgpAggregateEntry 3 }

rcIpBgpAggregateSummaryOnly OBJECT-TYPE
        SYNTAX        EnableValue
        MAX-ACCESS    read-write
        STATUS        current
        DESCRIPTION   "Filters all more specific routes from updates."
        DEFVAL        {disable}
        ::= { rcIpBgpAggregateEntry 4 }

rcIpBgpAggregateSuppressPolicy OBJECT-TYPE
        SYNTAX        DisplayString(SIZE(0..64))
        MAX-ACCESS    read-write
        STATUS        current
        DESCRIPTION   "Name of route policy used to select the
                       routes to be suppressed."
        ::= { rcIpBgpAggregateEntry 5 }

rcIpBgpAggregateAdvertisePolicy OBJECT-TYPE
        SYNTAX        DisplayString(SIZE(0..64))
        MAX-ACCESS    read-write
        STATUS        current
        DESCRIPTION   "Name of route policy used to select the
                       routes to create AS-SET origin communities."
        ::= { rcIpBgpAggregateEntry 6 }

rcIpBgpAggregateAttributePolicy OBJECT-TYPE
        SYNTAX        DisplayString(SIZE(0..64))
        MAX-ACCESS    read-write
        STATUS        current
        DESCRIPTION   "Name of route policy used to set the
                       attribute of the aggregate route."
        ::= { rcIpBgpAggregateEntry 7 }

rcIpBgpAggregateRowStatus OBJECT-TYPE
        SYNTAX        RowStatus
        MAX-ACCESS    read-write
        STATUS        current
        DESCRIPTION   "Row status for create/delete."
        ::= { rcIpBgpAggregateEntry 8 }

rcIpBgpConfederationGroup OBJECT IDENTIFIER ::= { rcIpBgp 4 }

rcIpBgpConfederationIdentifier OBJECT-TYPE
        SYNTAX        INTEGER  (0..65535)
        MAX-ACCESS    read-write
        STATUS        current
        DESCRIPTION   "Confederation AS identifier"
        ::= { rcIpBgpConfederationGroup 1 }

rcIpBgpConfederationPeers OBJECT-TYPE
        SYNTAX        OCTET STRING (SIZE(0..255))
        MAX-ACCESS    read-write
        STATUS        current
        DESCRIPTION   "The string represents ConfederatoinPeers as <length,
                       value>. Maximum size 255,if any, will not be recorded 
                       by this object.
                       The length is a 1-octet field containing the numbner 
                       of peers in the value field.
                       The value field contains one or more peers (AS numbers
                       which are part of the confederation).
                       Each AS is represented in the octet
                       string as a pair of octets according to the
                       following algorithm:
                          first-byte-of-pair = ASNumber / 256;
                          second-byte-of-pair = ASNumber & 255;"
        ::= { rcIpBgpConfederationGroup 2 }


rcIpBgpRouteReflectorGroup OBJECT IDENTIFIER ::= { rcIpBgp 5 }

rcIpBgpRouteReflectionEnable OBJECT-TYPE
        SYNTAX        EnableValue
        MAX-ACCESS    read-write
        STATUS        current
        DESCRIPTION   "Enable Route Reflection on this router"
        DEFVAL        {disable}
        ::= { rcIpBgpRouteReflectorGroup 1 }

rcIpBgpRouteReflectorClusterId OBJECT-TYPE
        SYNTAX        IpAddress
        MAX-ACCESS    read-write
        STATUS        current
        DESCRIPTION   "Cluster ID of this router acting as a route reflector"
        ::= { rcIpBgpRouteReflectorGroup 2 }

rcIpBgpRouteReflectorClientToClientReflection OBJECT-TYPE
        SYNTAX        EnableValue
        MAX-ACCESS    read-write
        STATUS        current
        DESCRIPTION   "When this router is configured as a route reflector, and
                       the clients are fully meshed, a Disable value disables
                       reflection of routes from one client to another."
        DEFVAL  {disable}
        ::= { rcIpBgpRouteReflectorGroup 3 }

rcIpBgpRouteReflectionOperState OBJECT-TYPE
        SYNTAX        EnableValue
        MAX-ACCESS    read-only
        STATUS        current
        DESCRIPTION   "Displays the current route reflection operational state"
        ::= { rcIpBgpRouteReflectorGroup 4 }


rcIpBgpNetworkTableSize OBJECT-TYPE
        SYNTAX        Integer32
        MAX-ACCESS    read-only
        STATUS        deprecated
        DESCRIPTION   "Network Prefix table size"
        ::= { rcIpBgp 6 }

rcIpBgpNetworkTable OBJECT-TYPE
        SYNTAX          SEQUENCE OF RcIpBgpNetworkEntry
        MAX-ACCESS      not-accessible
        STATUS          deprecated
        DESCRIPTION     "The networks in this table are either static/directly
                         connected or learned routes. Bgp advertises these
                         network provided they are reachable and are in the IP
                         routing table"
        ::= { rcIpBgp 7 }

rcIpBgpNetworkEntry OBJECT-TYPE
        SYNTAX          RcIpBgpNetworkEntry
        MAX-ACCESS      not-accessible
        STATUS          current
        DESCRIPTION     "An entry In NetworkTable."
        INDEX           { rcIpBgpNetworkAddr,
                          rcIpBgpNetworkMask }
        ::= { rcIpBgpNetworkTable 1 }

RcIpBgpNetworkEntry ::=
        SEQUENCE {
                  rcIpBgpNetworkAddr      IpAddress,
                  rcIpBgpNetworkMask      IpAddress,
		  rcIpBgpNetworkRowStatus RowStatus,
                  rcIpBgpNetworkMetric    INTEGER
                 }

rcIpBgpNetworkAddr OBJECT-TYPE
        SYNTAX        IpAddress
        MAX-ACCESS    read-write
        STATUS        current
        DESCRIPTION   "Network prefix that BGP will advertise."
        ::= { rcIpBgpNetworkEntry 1 }

rcIpBgpNetworkMask OBJECT-TYPE
        SYNTAX        IpAddress
        MAX-ACCESS    read-only
        STATUS        current
        DESCRIPTION   "Network mask"
        ::= { rcIpBgpNetworkEntry 2 }

rcIpBgpNetworkRowStatus OBJECT-TYPE
        SYNTAX        RowStatus
        MAX-ACCESS    read-write
        STATUS        current
        DESCRIPTION   "Row status for create/delete."
        ::= { rcIpBgpNetworkEntry 3 }

rcIpBgpNetworkMetric OBJECT-TYPE
        SYNTAX        INTEGER (0..65535)
        MAX-ACCESS    read-write
        STATUS        current
        DESCRIPTION   "Value of the metric to be used while sending
                       an update for the routes from the network table.
                       Indicates to set the MED value for the routes
                       advertised to ebgp peers."
        DEFVAL        { 0 }
        ::= { rcIpBgpNetworkEntry 4 }


-- Bgp Peer Table

rcIpBgpPeerTableSize OBJECT-TYPE
        SYNTAX        Integer32
        MAX-ACCESS    read-only
        STATUS        deprecated
        DESCRIPTION   "BGP peer table size"
        ::= { rcIpBgp 8 }

rcIpBgpPeerTable OBJECT-TYPE
        SYNTAX          SEQUENCE OF RcIpBgpPeerEntry
        MAX-ACCESS      not-accessible
        STATUS          deprecated
        DESCRIPTION     "IP BGP Peer table"
        ::= { rcIpBgp 9 }

rcIpBgpPeerEntry OBJECT-TYPE
        SYNTAX          RcIpBgpPeerEntry
        MAX-ACCESS      not-accessible
        STATUS          current
        DESCRIPTION     "An entry of Ip rcIpBgp Peer Table."
        INDEX           { rcIpBgpPeerIpAddress }
        ::= { rcIpBgpPeerTable 1 }

RcIpBgpPeerEntry ::=
        SEQUENCE {
                rcIpBgpPeerEnable                INTEGER,
                rcIpBgpPeerIpAddress             IpAddress,
                rcIpBgpPeerRemoteAs              INTEGER,
                rcIpBgpPeerGroupName         DisplayString,
                rcIpBgpPeerDefaultOriginate      EnableValue,
                rcIpBgpPeerEbgpMultiHop          EnableValue,
                rcIpBgpPeerAdvertisementInterval INTEGER,
                rcIpBgpPeerPassword              DisplayString,
                rcIpBgpPeerWeight                INTEGER,
                rcIpBgpPeerMaxPrefix             INTEGER,
                rcIpBgpPeerNextHopSelf           TruthValue,
                rcIpBgpPeerRoutePolicyIn         DisplayString,
                rcIpBgpPeerRoutePolicyOut        DisplayString,
                rcIpBgpPeerRouteReflectorClient  TruthValue,
                rcIpBgpPeerSoftReconfigurationIn EnableValue,
                rcIpBgpPeerSoftReconfiguration   INTEGER,
                rcIpBgpPeerRemovePrivateAs       EnableValue,
                rcIpBgpPeerRowStatus             RowStatus,
		rcIpBgpPeerMD5Authentication	 EnableValue,
		rcIpBgpPeerDebugMask		 INTEGER,
	        rcIpBgpPeerSendCommunity	 EnableValue,
		rcIpBgpPeerUpdateSourceInterface IpAddress,
-- OM 2.0 place holder 
--              rcIpBgpPeerBgpMplsCutThroughType INTEGER,
--              rcIpBgpPeerBgpMplsCutThroughId   INTEGER
                rcIpBgpPeerState                 INTEGER,
                rcIpBgpPeerLastError             OCTET STRING,
                rcIpBgpPeerVpnv4Address          EnableValue,
                rcIpBgpPeerIpvpnLiteCap          EnableValue,
                rcIpBgpPeerSooAddress            IpAddress,
                rcIpBgpPeerSooAsNumber           INTEGER,
                rcIpBgpPeerSooAssignedNum        Unsigned32,
                rcIpBgpPeerSooType               INTEGER,
                rcIpBgpPeerRouteRefresh          EnableValue,
                rcIpBgpPeerAsOverride		 EnableValue,
                rcIpBgpPeerAllowAsIn		 INTEGER
        }

rcIpBgpPeerEnable OBJECT-TYPE
        SYNTAX  INTEGER {
                    enabled(1),
                    disabled(2)
                }
        MAX-ACCESS  read-write
        STATUS  current
        DESCRIPTION
                "Enable/Disable: controls whether the peer connection is enabled
                or disabled"
        DEFVAL  { disabled }
        ::= { rcIpBgpPeerEntry 1 }

rcIpBgpPeerIpAddress OBJECT-TYPE
        SYNTAX        IpAddress
        MAX-ACCESS    read-only
        STATUS        current
        DESCRIPTION   "The Ip address of this peer"
        ::= { rcIpBgpPeerEntry 2 }

rcIpBgpPeerRemoteAs OBJECT-TYPE
        SYNTAX        INTEGER (0..65535)
        MAX-ACCESS    read-write
        STATUS        current
        DESCRIPTION   "Remote Autonomous system number of this peer"
        ::= { rcIpBgpPeerEntry 3 }

rcIpBgpPeerGroupName OBJECT-TYPE
        SYNTAX        DisplayString(SIZE(0..255))
        MAX-ACCESS    read-write
        STATUS        current
        DESCRIPTION   "Peer group name to which this peer belongs (optional)"
        ::= { rcIpBgpPeerEntry 4 }

rcIpBgpPeerDefaultOriginate OBJECT-TYPE
        SYNTAX        EnableValue
        MAX-ACCESS    read-write
        STATUS        current
        DESCRIPTION   "To allow a BGP speaker (the local router) to send
                       the default route 0.0.0.0 to a neighbor for use as
                       a default route"
        DEFVAL        {disable}
        ::= { rcIpBgpPeerEntry 5 }

rcIpBgpPeerEbgpMultiHop OBJECT-TYPE
        SYNTAX        EnableValue
        MAX-ACCESS    read-write
        STATUS        current
        DESCRIPTION   "To accept and attempt BGP connections to external
                       peers residing on networks that are not directly
                       connected"
        DEFVAL          {disable}
        ::= { rcIpBgpPeerEntry 6 }

rcIpBgpPeerAdvertisementInterval OBJECT-TYPE
        SYNTAX        INTEGER (5..120)
        MAX-ACCESS    read-write
        STATUS        current
        DESCRIPTION   "To set the minimum interval between the sending of
                       BGP routing updates Time in seconds. Integer from 5
                       to 120."
        DEFVAL        { 30 }
        ::= { rcIpBgpPeerEntry 7 }

rcIpBgpPeerPassword OBJECT-TYPE
        SYNTAX        DisplayString(SIZE(0..80))
        MAX-ACCESS    read-write
        STATUS        current
        DESCRIPTION   "To enable MD5 authentication on a TCP connection
                       between two BGP peers Case-sensitive password of
                       up to 80 character"
        ::= { rcIpBgpPeerEntry 8 }

rcIpBgpPeerWeight OBJECT-TYPE
        SYNTAX        INTEGER (0..65535)
        MAX-ACCESS    read-write
        STATUS        current
        DESCRIPTION   "To assign an absolute weight to a BGP network.
                       It can be an integer from 0 to  65535."
        DEFVAL        { 100 }
        ::= { rcIpBgpPeerEntry 9 }

rcIpBgpPeerMaxPrefix OBJECT-TYPE
        SYNTAX        INTEGER (0..2147483647)
        MAX-ACCESS    read-write
        STATUS        current
        DESCRIPTION   "Sets a limit on the number of routes that will be
                       accepted from a neighbor. A value of zero indicates no
                       limit"
        DEFVAL          {12000}
        ::= { rcIpBgpPeerEntry 10 }

rcIpBgpPeerNextHopSelf  OBJECT-TYPE
        SYNTAX        TruthValue
        MAX-ACCESS    read-write
        STATUS        current
        DESCRIPTION   "Set NextHop Attribute to local router address before
                       sending updates to remote peer"
        DEFVAL        { false }
        ::= { rcIpBgpPeerEntry 11 }

rcIpBgpPeerRoutePolicyIn OBJECT-TYPE
        SYNTAX        DisplayString(SIZE(0..64))
        MAX-ACCESS    read-write
        STATUS        current
        DESCRIPTION   "Route Policy Name that will be applied to all networks
                       learned from this peer"
        ::= { rcIpBgpPeerEntry 12 }

rcIpBgpPeerRoutePolicyOut OBJECT-TYPE
        SYNTAX        DisplayString(SIZE(0..64))
        MAX-ACCESS    read-write
        STATUS        current
        DESCRIPTION   "Route policy name that will be applied to all outgoing
                       updates"
        ::= { rcIpBgpPeerEntry 13 }

rcIpBgpPeerRouteReflectorClient OBJECT-TYPE
        SYNTAX        TruthValue
        MAX-ACCESS    read-write
        STATUS        current
        DESCRIPTION   "Indicates whether this peer is a route reflector client."
        DEFVAL        {false}
        ::= { rcIpBgpPeerEntry 14 }

rcIpBgpPeerSoftReconfigurationIn OBJECT-TYPE
        SYNTAX        EnableValue
        MAX-ACCESS    read-write
        STATUS        current
        DESCRIPTION   "If Peer soft reconfiguration is enabled in the in-bound
                       direction, policy can be changed and routes can
                       re-learned without having to reset the bgp connection.
                       Enabling soft reconfig-in causes all bgp routes to be
                       stored in local memory (even non-best routes)"
        DEFVAL        {enable}
        ::= { rcIpBgpPeerEntry 15 }

rcIpBgpPeerSoftReconfiguration OBJECT-TYPE
        SYNTAX        INTEGER {
                                in (1),
                                out(2),
                                none(3)
                              }
        MAX-ACCESS    read-write
        STATUS        current
        DESCRIPTION   "If rcIpBgpPeerSoftReconfigurationIn is enabled in the
                       in-bound direction, policy can be changed and routes can
                       re-learned without having to reset the bgp connection by
                       setting rcIpBgpPeerSoftReconfiguration to in(1). Setting
                       the value to out (2) forces the neighbor to send out all
                       the updates to the remote neighbor without resetting the
                       connection."
        DEFVAL        {none}
        ::= { rcIpBgpPeerEntry 16 }

rcIpBgpPeerRemovePrivateAs OBJECT-TYPE
        SYNTAX       EnableValue
        MAX-ACCESS   read-write
        STATUS       current
        DESCRIPTION  "Enable and disable private AS number from being
                      stripped when sending an update"
        DEFVAL          { enable  }
        ::= { rcIpBgpPeerEntry 17 }

rcIpBgpPeerRowStatus OBJECT-TYPE
        SYNTAX      RowStatus
        MAX-ACCESS  read-write
        STATUS      current
        DESCRIPTION "Used to create/delete entries in the Table."
        ::= { rcIpBgpPeerEntry 18 }

rcIpBgpPeerMD5Authentication  OBJECT-TYPE
	SYNTAX	    EnableValue
	MAX-ACCESS	read-write
	STATUS	    current
	DESCRIPTION "Enable and Disable MD5 authentication"
	DEFVAL	     { disable }
	::= { rcIpBgpPeerEntry 19 }

rcIpBgpPeerDebugMask OBJECT-TYPE
        SYNTAX         INTEGER (0..511) 
        MAX-ACCESS     read-write
        STATUS         current
        DESCRIPTION    " value is one of multiple (logically by 'OR' of
                         following value:
                                 none (0),
                                 error(1),
                                 packet(2),
                                 event(4),
                                 trace(8),
                                 warning(16),
                                 state(32),
                                 init(64),
                                 filter(128),
                                 update(256),
                                 all(511)
                        all(511): Enables all debugging messages.
                        none(0): Disables all debugging messages.
                        error(1): Enables disolay of debug error messages.
                        packet(2): Enables display of debug packet messages.
                        event(4): Enables display of debug event messages.
                        trace(8): Enables display debug trace messages.
                        warning(16): Enables display debug warning messages.
                        state(32): Enables display of debug state transtion
                               messages.
                        init(64): Enables display of debug initialization 
                               messages.
                        filter(128): Enables display of debug messages related 
                               to filtering.
                        update(256): Enables display of debug messages related 
                               to sending and receiving updates."
        DEFVAL          { 0 }
        ::=  { rcIpBgpPeerEntry 20 }

-- Following between =begin =end is processed by mib_tools/extras.awk
-- =begin enum
-- rcIpBgpPeerDebugMask none    0
-- rcIpBgpPeerDebugMask error   1
-- rcIpBgpPeerDebugMask packet  2
-- rcIpBgpPeerDebugMask event   4
-- rcIpBgpPeerDebugMask trace   8
-- rcIpBgpPeerDebugMask warning 16
-- rcIpBgpPeerDebugMask state   32
-- rcIpBgpPeerDebugMask init    64
-- rcIpBgpPeerDebugMask filter	128
-- rcIpBgpPeerDebugMask update	256
-- rcIpBgpPeerDebugMask all     511
-- =end enum

rcIpBgpPeerSendCommunity  OBJECT-TYPE
        SYNTAX      EnableValue
        MAX-ACCESS  read-write
        STATUS      current
        DESCRIPTION ""
        DEFVAL       { disable }
        ::= { rcIpBgpPeerEntry 21 }

rcIpBgpPeerUpdateSourceInterface  OBJECT-TYPE
        SYNTAX        IpAddress
        MAX-ACCESS    read-write
        STATUS        current
        DESCRIPTION   "The IP address to be used for Circuitless IP."
        ::= { rcIpBgpPeerEntry 22 }

rcIpBgpPeerState OBJECT-TYPE
        SYNTAX     INTEGER {
                            idle(1),
                            connect(2),
                            active(3),
                            opensent(4),
                            openconfirm(5),
                            established(6)
                   }
        MAX-ACCESS     read-only
        STATUS     current 
        DESCRIPTION
                   "The BGP peer connection state."
        ::= { rcIpBgpPeerEntry 25 }

rcIpBgpPeerLastError OBJECT-TYPE
        SYNTAX     OCTET STRING (SIZE (2))
        MAX-ACCESS read-only
        STATUS     current 
        DESCRIPTION
                  "The last error code and subcode seen by this
                   peer on this connection.  If no error has
                   occurred, this field is zero.  Otherwise, the
                   first byte of this two byte OCTET STRING
                   contains the error code, and the second byte
                   contains the subcode."
        ::= { rcIpBgpPeerEntry 26 }

rcIpBgpPeerVpnv4Address  OBJECT-TYPE
        SYNTAX      EnableValue
        MAX-ACCESS  read-create
        STATUS      current
        DESCRIPTION " The vpnv4 routes specified."
        DEFVAL       { disable }
        ::= { rcIpBgpPeerEntry 27 }
 
rcIpBgpPeerIpvpnLiteCap OBJECT-TYPE
        SYNTAX      EnableValue
        MAX-ACCESS  read-create
        STATUS      current
        DESCRIPTION "The IPVPN-lite capability can be enabled or disabled on
                   the bgp neighbor peer."
        DEFVAL       { disable }
        ::= { rcIpBgpPeerEntry 28 }
 
rcIpBgpPeerSooAddress     OBJECT-TYPE
        SYNTAX        IpAddress
        MAX-ACCESS    read-create
        STATUS        current
        DESCRIPTION   " The site-of-origin ip address."
        ::= { rcIpBgpPeerEntry 29 }
 
rcIpBgpPeerSooAsNumber  OBJECT-TYPE
        SYNTAX        INTEGER(0..65535)
        MAX-ACCESS    read-create
        STATUS        current
        DESCRIPTION   "The asnum for the site-of-origin for bgp peer."
        ::= { rcIpBgpPeerEntry  30}
 
rcIpBgpPeerSooAssignedNum     OBJECT-TYPE
        SYNTAX        Unsigned32 (0..2147483647)
        MAX-ACCESS    read-create
        STATUS        current
        DESCRIPTION   "The Assigned number required along with asnum or 
			address to configure the site-of-origin for bgp peer."
        ::= { rcIpBgpPeerEntry  31}
 
rcIpBgpPeerSooType        OBJECT-TYPE
        SYNTAX        INTEGER {
                    	none(0),
                    	asnum(1),
                    	ipaddr(2)
                      }
        MAX-ACCESS    read-only
        STATUS        current
        DESCRIPTION   " The soo type can be asnum or ipaddress."
        ::= { rcIpBgpPeerEntry  32}
 
rcIpBgpPeerRouteRefresh           OBJECT-TYPE
        SYNTAX        EnableValue
        MAX-ACCESS    read-create
        STATUS        current
        DESCRIPTION   "Route refresh for bgp peer."
        DEFVAL       { disable }
        ::= { rcIpBgpPeerEntry   33 }


rcIpBgpPeerAsOverride    OBJECT-TYPE
        SYNTAX        EnableValue       
        MAX-ACCESS    read-create
        STATUS        current
        DESCRIPTION   "The AS Override value can be enabled or disabled for bgp peer."
        DEFVAL        { disable }
        ::= { rcIpBgpPeerEntry  34}

rcIpBgpPeerAllowAsIn    OBJECT-TYPE             
        SYNTAX        INTEGER(0..10)      
        MAX-ACCESS    read-create
        STATUS        current
        DESCRIPTION   "The number of as-in allowed for bgp peer "
        ::= { rcIpBgpPeerEntry  35}

-- IP rcIpBgp Peer Group Table

rcIpBgpPeerGroupTableSize OBJECT-TYPE
        SYNTAX        Integer32
        MAX-ACCESS    read-only
        STATUS        current
        DESCRIPTION   "BGP Peer Group table size"
        ::= { rcIpBgp 10 }

rcIpBgpPeerGroupTable OBJECT-TYPE
        SYNTAX          SEQUENCE OF RcIpBgpPeerGroupEntry
        MAX-ACCESS      not-accessible
        STATUS          current
        DESCRIPTION     "IP rcIpBgp Peer Group table. This table contains rows
                         which are template configuration parameters which are
                         shared by a group of peers. Peers belonging to the
                         same group will refer to the same row in this table
                         using a peer group name"
        ::= { rcIpBgp 11 }

rcIpBgpPeerGroupEntry OBJECT-TYPE
        SYNTAX          RcIpBgpPeerGroupEntry
        MAX-ACCESS      not-accessible
        STATUS          current
        DESCRIPTION     "An entry of Ip rcIpBgp Peer Group Table."
        INDEX           { rcIpBgpPeerGroupIndex }
        ::= { rcIpBgpPeerGroupTable 1 }

RcIpBgpPeerGroupEntry ::=
        SEQUENCE {
                rcIpBgpPeerGroupEnable                  EnableValue,
                rcIpBgpPeerGroupIndex                   Integer32,
                rcIpBgpPeerGroupGroupName               DisplayString,
                rcIpBgpPeerGroupRemoteAs                Integer32,
                rcIpBgpPeerGroupDefaultOriginate        INTEGER,
                rcIpBgpPeerGroupEbgpMultiHop            INTEGER,
                rcIpBgpPeerGroupAdvertisementInterval   Integer32,
                rcIpBgpPeerGroupKeepAlive               Integer32,
                rcIpBgpPeerGroupHoldTime                Integer32,
                rcIpBgpPeerGroupWeight                  Integer32,
                rcIpBgpPeerGroupMaxPrefix               Integer32,
                rcIpBgpPeerGroupNextHopSelf             TruthValue,
                rcIpBgpPeerGroupRoutePolicyIn           DisplayString,
                rcIpBgpPeerGroupRoutePolicyOut          DisplayString,
                rcIpBgpPeerGroupRouteReflectorClient    TruthValue,
                rcIpBgpPeerGroupSoftReconfigurationIn   EnableValue,
                rcIpBgpPeerGroupSoftReconfiguration     INTEGER,
                rcIpBgpPeerGroupPassword                DisplayString,
                rcIpBgpPeerGroupRemovePrivateAs         EnableValue,
                rcIpBgpPeerGroupRowStatus               RowStatus,
		rcIpBgpPeerGroupMD5Authentication	EnableValue,
                rcIpBgpPeerGroupSendCommunity           EnableValue,
		rcIpBgpPeerGroupUpdateSourceInterface	IpAddress,
                rcIpBgpPeerGroupVpnv4Address            EnableValue,
                rcIpBgpPeerGroupIpvpnLiteCap            EnableValue,
                rcIpBgpPeerGroupRouteRefresh            EnableValue,
                rcIpBgpPeerGroupAsOverride		EnableValue,
                rcIpBgpPeerGroupAllowAsIn	        Integer32,
                rcIpBgpPeerGroupDefaultOriginateIpv6    TruthValue,
                rcIpBgpPeerGroupAfUpdateSourceInterfaceType InetAddressType,
                rcIpBgpPeerGroupAfUpdateSourceInterface InetAddress,
                rcIpBgpPeerGroupIpv6Cap                 EnableValue,
                rcIpBgpPeerGroupIpv6RoutePolicyIn       DisplayString,
                rcIpBgpPeerGroupIpv6RoutePolicyOut      DisplayString
        }

rcIpBgpPeerGroupEnable OBJECT-TYPE
        SYNTAX        EnableValue
        MAX-ACCESS    read-create
        STATUS        current
        DESCRIPTION   "Allows disabling a group of peers"
        DEFVAL        { disable }
        ::= { rcIpBgpPeerGroupEntry 1 }

rcIpBgpPeerGroupIndex OBJECT-TYPE
        SYNTAX        Integer32 (1..1024)
        MAX-ACCESS    read-only
        STATUS        current
        DESCRIPTION   "Index in to the Peer Group Table"
	DEFVAL	      {1}	
        ::= { rcIpBgpPeerGroupEntry 2 }

rcIpBgpPeerGroupGroupName OBJECT-TYPE
        SYNTAX        DisplayString(SIZE(0..255))
        MAX-ACCESS    read-create
        STATUS        current
        DESCRIPTION   "Name of the BGP peer group to which this neighbor belong"
        ::= { rcIpBgpPeerGroupEntry 3 }

rcIpBgpPeerGroupRemoteAs OBJECT-TYPE
        SYNTAX        Integer32 (0..65535)
        MAX-ACCESS    read-create
        STATUS        current
        DESCRIPTION   "Remote Autonomous system number of this peer group
                       (optional)"
        ::= { rcIpBgpPeerGroupEntry 4 }

rcIpBgpPeerGroupDefaultOriginate OBJECT-TYPE
        SYNTAX        INTEGER {
                               enable(1),
                               disable(2)
                              }
        MAX-ACCESS    read-create
        STATUS        current
        DESCRIPTION   "Enabling this attribute allows a BGP speaker
                      (the local router) to send the default route 0.0.0.0 to
                      the group of neighbors for use as a default route."
        DEFVAL { disable }
        ::= { rcIpBgpPeerGroupEntry 5 }

rcIpBgpPeerGroupEbgpMultiHop OBJECT-TYPE
        SYNTAX        INTEGER {
                               enable(1),
                               disable(2)
				}
        MAX-ACCESS    read-create
        STATUS        current
        DESCRIPTION   "To accept and attempt BGP connections to external
                       peers residing on networks that are not directly
                       connected"
	DEFVAL { disable }
        ::= { rcIpBgpPeerGroupEntry 6 }

rcIpBgpPeerGroupAdvertisementInterval OBJECT-TYPE
        SYNTAX        Integer32 (5..120)
        MAX-ACCESS    read-create
        STATUS        current
        DESCRIPTION   "To set the minimum interval between the sending of
                       BGP routing updates Time in seconds. Integer from 1
                       to 120."
        DEFVAL          {30}
        ::= { rcIpBgpPeerGroupEntry 7 }

rcIpBgpPeerGroupKeepAlive OBJECT-TYPE
        SYNTAX        Integer32 (0..21845)
        MAX-ACCESS    read-create
        STATUS        current
        DESCRIPTION   "To set the time interval in seconds between the sending
                       of BGP keep alive messages to remote peers."
        DEFVAL          {60}
        ::= { rcIpBgpPeerGroupEntry 8 }

rcIpBgpPeerGroupHoldTime OBJECT-TYPE
        SYNTAX        Integer32 (0..65535)
        MAX-ACCESS    read-create
        STATUS        current
        DESCRIPTION   "To configure the hold time for the group of peers in
                       seconds. Usually set to three times the value of the
                       Keepalive time"
        DEFVAL          {180}
        ::= { rcIpBgpPeerGroupEntry 9 }

rcIpBgpPeerGroupWeight OBJECT-TYPE
        SYNTAX        Integer32 (0..65535)
        MAX-ACCESS    read-create
        STATUS        current
        DESCRIPTION   "To assign an absolute weight to a BGP network.
                       Absolute weight, or importance.
                       It can be an integer from 0 to  65535."
        DEFVAL          {100}
        ::= { rcIpBgpPeerGroupEntry 10 }

rcIpBgpPeerGroupMaxPrefix OBJECT-TYPE
        SYNTAX        Integer32 (0..2147483647)
        MAX-ACCESS    read-create
        STATUS        current
        DESCRIPTION   "Sets a limit on the number of routes that will be
                       accepted from this group of neighbors. A value of zero
                       indicates no limit"
        DEFVAL          {12000}
        ::= { rcIpBgpPeerGroupEntry 11 }

rcIpBgpPeerGroupNextHopSelf     OBJECT-TYPE
        SYNTAX        TruthValue
        MAX-ACCESS    read-create
        STATUS        current
        DESCRIPTION   "Set NextHop Attribute to local router address before
                       sending updates to remote peers"
        DEFVAL        { false }
        ::= { rcIpBgpPeerGroupEntry 12 }

rcIpBgpPeerGroupRoutePolicyIn OBJECT-TYPE
        SYNTAX        DisplayString(SIZE(0..64))
        MAX-ACCESS    read-create
        STATUS        current
        DESCRIPTION   "Route Policy Name that will be applied to all networks
                       learned from this group of peers"
        ::= { rcIpBgpPeerGroupEntry 13 }

rcIpBgpPeerGroupRoutePolicyOut OBJECT-TYPE
        SYNTAX        DisplayString(SIZE(0..64))
        MAX-ACCESS    read-create
        STATUS        current
        DESCRIPTION   "Route policy name that will be applied to all
                       outgoing updates to this group of peers"
        ::= { rcIpBgpPeerGroupEntry 14 }

rcIpBgpPeerGroupRouteReflectorClient OBJECT-TYPE
        SYNTAX        TruthValue
        MAX-ACCESS    read-create
        STATUS        current
        DESCRIPTION   "Indicates whether this group of peers is a route reflector client."
        DEFVAL        { false }
        ::= { rcIpBgpPeerGroupEntry 15 }

rcIpBgpPeerGroupSoftReconfigurationIn OBJECT-TYPE
        SYNTAX        EnableValue
        MAX-ACCESS    read-create
        STATUS        current
        DESCRIPTION   "If Peer soft reconfiguration is enabled in the in bound
                       direction, policy can be changed and routes can
                       re-learned without having to reset the bgp connection.
                       Enabling soft reconfig-in causes all bgp routes to be
                       stored in local memory (even non-best routes)"
        DEFVAL        {enable}
        ::= { rcIpBgpPeerGroupEntry 16 }

rcIpBgpPeerGroupSoftReconfiguration OBJECT-TYPE
        SYNTAX        INTEGER {
                                in (1),
                                out(2)
                              }
        MAX-ACCESS    read-write
        STATUS        current
        DESCRIPTION   "If Peer soft reconfiguration-in is enabled in the in
                       bound direction, policy can be changed and routes can
                       re-learned without having to reset the bgp connection by
                       setting rcIpBgpPeerGroupSoftReconfiguration to in(1).
                       Setting the value to out (2) forces the neighbor to send
                       out all the updates to the remote neighbor without
                       resetting the connection."
        ::= { rcIpBgpPeerGroupEntry 17 }

rcIpBgpPeerGroupPassword OBJECT-TYPE
        SYNTAX        DisplayString(SIZE(0..80))
        MAX-ACCESS    read-create
        STATUS        current
        DESCRIPTION   "To enable MD5 authentication on  TCP connections
                       between this local speaker and this group of BGP peers.
                       Case-sensitive password of up to 80 character"
        ::= { rcIpBgpPeerGroupEntry 18 }

rcIpBgpPeerGroupRemovePrivateAs OBJECT-TYPE
        SYNTAX       EnableValue
        MAX-ACCESS   read-create
        STATUS       current
        DESCRIPTION  "Enable and disable private AS number from being
                      stripped when sending an update"
        DEFVAL          { enable  }
        ::= { rcIpBgpPeerGroupEntry 19 }

rcIpBgpPeerGroupRowStatus OBJECT-TYPE
        SYNTAX        RowStatus
        MAX-ACCESS    read-create
        STATUS        current
        DESCRIPTION   "row status"
        ::= { rcIpBgpPeerGroupEntry 20 }

rcIpBgpPeerGroupMD5Authentication  OBJECT-TYPE
        SYNTAX      EnableValue
        MAX-ACCESS  read-create
        STATUS      current
        DESCRIPTION "Enable and Disable MD5 authentication"
        DEFVAL       { disable }
        ::= { rcIpBgpPeerGroupEntry 21 }

rcIpBgpPeerGroupSendCommunity  OBJECT-TYPE
        SYNTAX      EnableValue
        MAX-ACCESS  read-create
        STATUS      current
        DESCRIPTION "Enables or disables sending the update
                     message community attribute to the specified
                     peer."
        DEFVAL       { disable }
        ::= { rcIpBgpPeerGroupEntry 22 }

rcIpBgpPeerGroupUpdateSourceInterface OBJECT-TYPE
        SYNTAX        IpAddress
        MAX-ACCESS    read-create
        STATUS        current
        DESCRIPTION   "The IP address to used for circuitless IP for this peer group."
        ::= { rcIpBgpPeerGroupEntry 23 }

rcIpBgpPeerGroupVpnv4Address OBJECT-TYPE
        SYNTAX        EnableValue
        MAX-ACCESS    read-create
        STATUS        current
        DESCRIPTION   "The vpnv4 routes specified."
        DEFVAL        { disable }
        ::= { rcIpBgpPeerGroupEntry 24 }

rcIpBgpPeerGroupIpvpnLiteCap OBJECT-TYPE
        SYNTAX        EnableValue
        MAX-ACCESS    read-create
        STATUS        current
        DESCRIPTION   "The IPVPN-lite capability can be enabled or disabled                         on the bgp neighbor peer group."
        DEFVAL        { disable }
        ::= { rcIpBgpPeerGroupEntry 25 }

rcIpBgpPeerGroupRouteRefresh OBJECT-TYPE
        SYNTAX        EnableValue
        MAX-ACCESS    read-create
        STATUS        current
        DESCRIPTION   "Route refresh for bgp peer group."
        DEFVAL       { disable }
        ::= { rcIpBgpPeerGroupEntry   30 }

rcIpBgpPeerGroupAsOverride    OBJECT-TYPE
        SYNTAX             EnableValue
        MAX-ACCESS    read-create
        STATUS        current
        DESCRIPTION   "The AS Override value can be enabled or disabled for bgp peer group."
        DEFVAL        { disable }
        ::= { rcIpBgpPeerGroupEntry  31}

rcIpBgpPeerGroupAllowAsIn    OBJECT-TYPE
        SYNTAX        Integer32(0..10) 
        MAX-ACCESS    read-create
        STATUS        current
        DESCRIPTION   "The number of as-in allowed for bgp peer group."
        ::= { rcIpBgpPeerGroupEntry  32}

rcIpBgpPeerGroupDefaultOriginateIpv6  OBJECT-TYPE
        SYNTAX        TruthValue
        MAX-ACCESS    read-create
        STATUS        current
        DESCRIPTION   "Enabling this attribute allows a BGP speaker
                      (the local router) to send the default route to
                      the group of neighbors for use as a default 
                      route."
        DEFVAL { false }
        ::= { rcIpBgpPeerGroupEntry 33 }

rcIpBgpPeerGroupAfUpdateSourceInterfaceType OBJECT-TYPE
        SYNTAX        InetAddressType
        MAX-ACCESS    read-create
        STATUS        current
        DESCRIPTION   "The Inet address type used for circuitless IP 
                       for this peer group."
        ::= { rcIpBgpPeerGroupEntry 34 }

rcIpBgpPeerGroupAfUpdateSourceInterface OBJECT-TYPE
        SYNTAX        InetAddress
        MAX-ACCESS    read-create
        STATUS        current
        DESCRIPTION   "The Inet address to used for circuitless IP for  
                       this peer group."
        ::= { rcIpBgpPeerGroupEntry 35 }

rcIpBgpPeerGroupIpv6Cap  OBJECT-TYPE
        SYNTAX      EnableValue
        MAX-ACCESS  read-create
        STATUS      current
        DESCRIPTION "The ipv6 capability can be enabled or disabled      
                    on the bgp neighbor peer group."
        DEFVAL       { disable }
        ::= { rcIpBgpPeerGroupEntry 36 }

rcIpBgpPeerGroupIpv6RoutePolicyIn OBJECT-TYPE
        SYNTAX        DisplayString(SIZE(0..64))
        MAX-ACCESS    read-create
        STATUS        current
        DESCRIPTION   "Ipv6 Route Policy Name that will be applied to all 
                       networks learned from this group of peers"
        ::= { rcIpBgpPeerGroupEntry 37 }

rcIpBgpPeerGroupIpv6RoutePolicyOut OBJECT-TYPE
        SYNTAX        DisplayString(SIZE(0..64))
        MAX-ACCESS    read-create
        STATUS        current
        DESCRIPTION   "Ipv6 Route policy name that will be applied to all
                       outgoing updates to this group of peers"
        ::= { rcIpBgpPeerGroupEntry 38 }

rcIpBgpRcvdDampenedPathAttrTableSize OBJECT-TYPE
        SYNTAX        Integer32
        MAX-ACCESS    read-only
        STATUS        current
        DESCRIPTION   "table size"
        ::= { rcIpBgp 12 }

rcIpBgpRcvdDampenedPathAttrTable OBJECT-TYPE
        SYNTAX        SEQUENCE OF RcIpBgpDampenedPathAttrEntry
        MAX-ACCESS    not-accessible
        STATUS        current
        DESCRIPTION   "This table contains info about paths to destination
                       networks received from all BGP-4 peers"
        ::= { rcIpBgp 13 }

rcIpBgpDampenedPathAttrEntry OBJECT-TYPE
        SYNTAX        RcIpBgpDampenedPathAttrEntry
        MAX-ACCESS    not-accessible
        STATUS        current
        DESCRIPTION   "Information about a path to a networks"
        INDEX         { rcIpBgpPathAttrIpAddrPrefix,
                        rcIpBgpPathAttrIpAddrPrefixLen,
                        rcIpBgpPathAttrPeer
                      }
        ::=  { rcIpBgpRcvdDampenedPathAttrTable 1 }

RcIpBgpDampenedPathAttrEntry ::=
           SEQUENCE {

                   rcIpBgpPathAttrPeer              IpAddress,
                   rcIpBgpPathAttrIpAddrPrefixLen   INTEGER,
                   rcIpBgpPathAttrIpAddrPrefix      IpAddress,
                   rcIpBgpPathAttrFlapPenalty       Integer32,
                   rcIpBgpPathAttrFlapCount         Integer32,
                   rcIpBgpPathAttrRouteDampened     INTEGER,
		   rcIpBgpPathAttrReuseTime	    Integer32,
                   rcIpBgpPathAttrReuseTimeRemain   Integer32 
           }

rcIpBgpPathAttrPeer OBJECT-TYPE
        SYNTAX        IpAddress
        MAX-ACCESS    read-only
        STATUS        current
        DESCRIPTION   "The IP address of the peer where the path info was
                       learned"
        ::=   { rcIpBgpDampenedPathAttrEntry 1 }

rcIpBgpPathAttrIpAddrPrefixLen OBJECT-TYPE
        SYNTAX        INTEGER (0..32)
        MAX-ACCESS    read-only
        STATUS        current
        DESCRIPTION   "Length in bits of the IP address prefix in the network
                       Layer Reachablity Information field."
        ::=   { rcIpBgpDampenedPathAttrEntry 2 }

rcIpBgpPathAttrIpAddrPrefix OBJECT-TYPE
        SYNTAX        IpAddress
        MAX-ACCESS    read-only
        STATUS        current
        DESCRIPTION   "An Ip address prefix in the NLRI Information field.
                       This object is an IP address containing the prefix
                       with length specified by rcIpBgpPathAttrIpAddrPrefixLen
                       are zeroed."
        ::=   { rcIpBgpDampenedPathAttrEntry 3 }

rcIpBgpPathAttrFlapPenalty OBJECT-TYPE
        SYNTAX        Integer32
        MAX-ACCESS    read-only
        STATUS        current
        DESCRIPTION "Penalty value based on number of route flaps"
        ::= { rcIpBgpDampenedPathAttrEntry 4 }

rcIpBgpPathAttrFlapCount OBJECT-TYPE
        SYNTAX        Integer32
        MAX-ACCESS    read-only
        STATUS        current
        DESCRIPTION   "Number of times a route flapped since the last time the
                      penalty was reset to zero"
        ::= { rcIpBgpDampenedPathAttrEntry 5 }

rcIpBgpPathAttrRouteDampened OBJECT-TYPE
        SYNTAX  INTEGER {
                    announced(1),
                    suppressed(2)
                }
        MAX-ACCESS  read-only
        STATUS  current
        DESCRIPTION "Shows whether this route is currently suppressed from
                     being announced"
        ::= { rcIpBgpDampenedPathAttrEntry 6 }

rcIpBgpPathAttrReuseTime OBJECT-TYPE
        SYNTAX        Integer32
        MAX-ACCESS    read-only
        STATUS        current
        DESCRIPTION   "Re use time is the system configured time for 
                       route reuse"
        ::= { rcIpBgpDampenedPathAttrEntry 7 }

rcIpBgpPathAttrReuseTimeRemain OBJECT-TYPE
        SYNTAX        Integer32
        MAX-ACCESS    read-only
        STATUS        current
        DESCRIPTION   "Re use time Remain is the number of seconds before the                          route will be reused"
        ::= { rcIpBgpDampenedPathAttrEntry 8 }

rcIpBgp4PathAttrTableSize OBJECT-TYPE
        SYNTAX        Integer32
        MAX-ACCESS    read-only
        STATUS        current
        DESCRIPTION   "table size"
        ::= { rcIpBgp 14 }

rcIpBgp4PathAttrTable OBJECT-TYPE
        SYNTAX        SEQUENCE OF RcIpBgp4PathAttrEntry
        MAX-ACCESS    not-accessible
        STATUS        current
        DESCRIPTION   "This table contains info about paths to destination
                       networks received from all BGP-4 peers"
        ::= { rcIpBgp 15 }

rcIpBgp4PathAttrEntry OBJECT-TYPE
        SYNTAX        RcIpBgp4PathAttrEntry
        MAX-ACCESS    not-accessible
        STATUS        current
        DESCRIPTION   ""
        INDEX         { rcIpBgp4PathAttrIpAddrPrefix,
                        rcIpBgp4PathAttrIpAddrPrefixLen,
                        rcIpBgp4PathAttrPeer
                      }
        ::=  { rcIpBgp4PathAttrTable 1 }

RcIpBgp4PathAttrEntry ::=
           SEQUENCE {
                   rcIpBgp4PathAttrPeer              IpAddress,
                   rcIpBgp4PathAttrIpAddrPrefixLen   INTEGER,
                   rcIpBgp4PathAttrIpAddrPrefix      IpAddress,
                   rcIpBgp4PathAttrCommunities       OCTET STRING,
                   rcIpBgp4PathAttrOriginateId       IpAddress,
                   rcIpBgp4PathAttrClusterId         OCTET STRING
           }

rcIpBgp4PathAttrPeer OBJECT-TYPE
        SYNTAX        IpAddress
        MAX-ACCESS    read-only
        STATUS        current
        DESCRIPTION   "The IP address of the peer where the path info was
                       learned"
        ::=   { rcIpBgp4PathAttrEntry 1 }

rcIpBgp4PathAttrIpAddrPrefixLen OBJECT-TYPE
        SYNTAX        INTEGER (0..32)
        MAX-ACCESS    read-only
        STATUS        current
        DESCRIPTION   "Length in bits of the IP address prefix in the network
                       Layer Reachablity Information field."
        ::=   { rcIpBgp4PathAttrEntry 2 }

rcIpBgp4PathAttrIpAddrPrefix OBJECT-TYPE
        SYNTAX        IpAddress
        MAX-ACCESS    read-only
        STATUS        current
        DESCRIPTION   "An Ip address prefix in the NLRI Information field.
                       This object is an IP address containing the prefix
                       with length specified by rcIpBgpPathAttrIpAddrPrefixLen
                       are zeroed."
        ::=   { rcIpBgp4PathAttrEntry 3 }

rcIpBgp4PathAttrCommunities OBJECT-TYPE
        SYNTAX        OCTET STRING (SIZE(255))
        MAX-ACCESS    read-only
        STATUS        current
        DESCRIPTION   "The string represents community path attributes as <length,value>
                        The length is a 1-octet field containing the numbner of community
                        numbers in the value field.The value field contains one or more
                        Community numbers,each community is represented in the octet
                        string as 4 octets.The community numbers in the string beyond
                        maximum size 255,if any, will not be recorded by this object."
        ::=   { rcIpBgp4PathAttrEntry 4 }

rcIpBgp4PathAttrOriginateId OBJECT-TYPE
        SYNTAX        IpAddress
        MAX-ACCESS    read-only
        STATUS        current
        DESCRIPTION   "The IP address of the route who originates the routes"
        ::=   { rcIpBgp4PathAttrEntry 5 }

rcIpBgp4PathAttrClusterId OBJECT-TYPE
        SYNTAX        OCTET STRING (SIZE(255))
        MAX-ACCESS    read-only
        STATUS        current
        DESCRIPTION   "The string represents Cluster Id path attributes as <length,value>
                        The length is a 1-octet field containing the number of Cluster Id
                        numbers in the value field.The value field contains one or more
                        Cluster Id numbers,each Cluster Id is represented in the octet
                        string as 4 octets,each four octets is the IpAddress of the
                        router acting as a route reflector.The Cluster Id numbers in the
                        string beyond maximum size 255,if any, will not be recorded by
                        this object."
        ::=   { rcIpBgp4PathAttrEntry 6 }

rcIpBgpExt OBJECT IDENTIFIER ::= { rcIpBgp 16 }

rcIpBgpExtAggregateAfTableSize OBJECT-TYPE
        SYNTAX          Unsigned32
        MAX-ACCESS      read-only
        STATUS          current
        DESCRIPTION     "Size of address family independent bgp aggregate table"
        ::= { rcIpBgpExt 1 }

rcIpBgpExtAggregateAfTable OBJECT-TYPE
        SYNTAX          SEQUENCE OF RcIpBgpExtAggregateAfEntry
        MAX-ACCESS      not-accessible
        STATUS          current
        DESCRIPTION     "Replaces rcIpBgpAggregateTable.
                         To specify the list of ipv4 and ipv6 aggregate
                         prefixes to be created  by the BGP routing process
                         and the options to be used while aggregating."
        ::= { rcIpBgpExt 2 }

rcIpBgpExtAggregateAfEntry OBJECT-TYPE
        SYNTAX          RcIpBgpExtAggregateAfEntry
        MAX-ACCESS      not-accessible
        STATUS          current
        DESCRIPTION     "An entry of v4/v6 aggregate prefix to be created by
                         BGP routing process and the options to be used
                         while aggregating."
        INDEX           { rcIpBgpExtAggregateAfAddressType,
                          rcIpBgpExtAggregateAfAddress,
                          rcIpBgpExtAggregateAfPrefixLen }
        ::= { rcIpBgpExtAggregateAfTable 1 }

RcIpBgpExtAggregateAfEntry ::= SEQUENCE {
                          rcIpBgpExtAggregateAfAddressType          InetAddressType,
                          rcIpBgpExtAggregateAfAddress              InetAddress, 
                          rcIpBgpExtAggregateAfPrefixLen            InetAddressPrefixLength, 
                          rcIpBgpExtAggregateAfAsSetGenerate        TruthValue,
                          rcIpBgpExtAggregateAfSummaryOnly          TruthValue,
                          rcIpBgpExtAggregateAfSuppressPolicy       SnmpAdminString,
                          rcIpBgpExtAggregateAfAdvertisePolicy      SnmpAdminString,
                          rcIpBgpExtAggregateAfAttributePolicy      SnmpAdminString,
                          rcIpBgpExtAggregateAfRowStatus            RowStatus
                 }

rcIpBgpExtAggregateAfAddressType OBJECT-TYPE
        SYNTAX        InetAddressType
        MAX-ACCESS    not-accessible
        STATUS        current
        DESCRIPTION   "Inet Address Type of aggregate address."
        ::= { rcIpBgpExtAggregateAfEntry 1 }

rcIpBgpExtAggregateAfAddress OBJECT-TYPE
        SYNTAX        InetAddress
        MAX-ACCESS    not-accessible
        STATUS        current
        DESCRIPTION   "V4 or V6 Prefix to create an aggregate address in BGP
                       routing table."
        ::= { rcIpBgpExtAggregateAfEntry 2 }

rcIpBgpExtAggregateAfPrefixLen OBJECT-TYPE
        SYNTAX        InetAddressPrefixLength 
        MAX-ACCESS    not-accessible
        STATUS        current
        DESCRIPTION   "Prefix length of the aggregate inet address"
        ::= { rcIpBgpExtAggregateAfEntry 3 }

rcIpBgpExtAggregateAfAsSetGenerate OBJECT-TYPE
        SYNTAX        TruthValue
        MAX-ACCESS    read-create
        STATUS        current 
        DESCRIPTION   "Enable Generates autonomous system set path
                       information."
        DEFVAL        {false}
        ::= { rcIpBgpExtAggregateAfEntry 4 }

rcIpBgpExtAggregateAfSummaryOnly OBJECT-TYPE
        SYNTAX        TruthValue
        MAX-ACCESS    read-create
        STATUS        current
        DESCRIPTION   "Filters all more specific routes from updates."
        DEFVAL        {false}
        ::= { rcIpBgpExtAggregateAfEntry 5 }

rcIpBgpExtAggregateAfSuppressPolicy OBJECT-TYPE
        SYNTAX        SnmpAdminString(SIZE(0..64))
        MAX-ACCESS    read-create
        STATUS        current
        DESCRIPTION   "Name of route policy used to select the
                       routes to be suppressed."
        ::= { rcIpBgpExtAggregateAfEntry 6 }

rcIpBgpExtAggregateAfAdvertisePolicy OBJECT-TYPE
        SYNTAX        SnmpAdminString(SIZE(0..64))
        MAX-ACCESS    read-create
        STATUS        current
        DESCRIPTION   "Name of route policy used to select the
                       routes to create AS-SET origin communities."
        ::= { rcIpBgpExtAggregateAfEntry 7 }

rcIpBgpExtAggregateAfAttributePolicy OBJECT-TYPE
        SYNTAX        SnmpAdminString(SIZE(0..64))
        MAX-ACCESS    read-create
        STATUS        current
        DESCRIPTION   "Name of route policy used to set the
                       attribute of the aggregate route."
        ::= { rcIpBgpExtAggregateAfEntry 8 }

rcIpBgpExtAggregateAfRowStatus OBJECT-TYPE
        SYNTAX        RowStatus
        MAX-ACCESS    read-create
        STATUS        current
        DESCRIPTION   "Row status for create/delete."
        ::= { rcIpBgpExtAggregateAfEntry 9 }

rcIpBgpExtNetworkAfTableSize OBJECT-TYPE
        SYNTAX        Unsigned32
        MAX-ACCESS    read-only
        STATUS        current
        DESCRIPTION   "Address family independent bgp Network Prefix table size"
        ::= { rcIpBgpExt 3 }

rcIpBgpExtNetworkAfTable OBJECT-TYPE
        SYNTAX          SEQUENCE OF RcIpBgpExtNetworkAfEntry
        MAX-ACCESS      not-accessible
        STATUS          current
        DESCRIPTION     "This table replaces rcIpBgpNetworkTable.
                         This table supports V4 and V6 BGP networks.
                         The networks in this table are either
                         static/directly connected or learned routes.
                         Bgp advertises these network provided they are
                         reachable and are in the IP routing table"
        ::= { rcIpBgpExt 4 }

rcIpBgpExtNetworkAfEntry OBJECT-TYPE
        SYNTAX          RcIpBgpExtNetworkAfEntry
        MAX-ACCESS      not-accessible
        STATUS          current
        DESCRIPTION     "An entry in bgp NetworkTable."
        INDEX           {  rcIpBgpExtNetworkAfAddrType,
                           rcIpBgpExtNetworkAfAddr,
                           rcIpBgpExtNetworkAfPrefixLen }
        ::= { rcIpBgpExtNetworkAfTable 1 }

RcIpBgpExtNetworkAfEntry ::=
        SEQUENCE {
                  rcIpBgpExtNetworkAfAddrType       InetAddressType,
                  rcIpBgpExtNetworkAfAddr           InetAddress,
                  rcIpBgpExtNetworkAfPrefixLen      InetAddressPrefixLength,
                  rcIpBgpExtNetworkAfMetric         Integer32,
                  rcIpBgpExtNetworkAfRowStatus      RowStatus
                 }

rcIpBgpExtNetworkAfAddrType OBJECT-TYPE
        SYNTAX        InetAddressType 
        MAX-ACCESS    not-accessible
        STATUS        current
        DESCRIPTION   "Inet address type of the Network prefix that BGP will
                       advertise."
        ::= { rcIpBgpExtNetworkAfEntry 1 }

rcIpBgpExtNetworkAfAddr OBJECT-TYPE 
        SYNTAX        InetAddress
        MAX-ACCESS    not-accessible
        STATUS        current
        DESCRIPTION   "v4/v6 Network prefix that BGP will advertise."
        ::= { rcIpBgpExtNetworkAfEntry 2 }

rcIpBgpExtNetworkAfPrefixLen OBJECT-TYPE 
        SYNTAX        InetAddressPrefixLength
        MAX-ACCESS    not-accessible
        STATUS        current
        DESCRIPTION   "Prefix length of the v4/v6 bgp network address"
        ::= { rcIpBgpExtNetworkAfEntry 3 }

rcIpBgpExtNetworkAfMetric OBJECT-TYPE
        SYNTAX        Integer32 (0..65535)
        MAX-ACCESS    read-create
        STATUS        current
        DESCRIPTION   "Value of the metric to be used while sending
                       an update for the routes from the network table.
                       Indicates to set the MED value for the routes
                       advertised to ebgp Peers."
        DEFVAL        { 0 }
        ::= { rcIpBgpExtNetworkAfEntry 4 }

rcIpBgpExtNetworkAfRowStatus OBJECT-TYPE
        SYNTAX        RowStatus
        MAX-ACCESS    read-create
        STATUS        current
        DESCRIPTION   "Row status for create/delete."
        ::= { rcIpBgpExtNetworkAfEntry 5 }

rcIpBgpExtPeerAfTableSize OBJECT-TYPE
        SYNTAX        Unsigned32
        MAX-ACCESS    read-only
        STATUS        current
        DESCRIPTION   "Size of Address family independent BGP
                       Peer Table"
        ::= { rcIpBgpExt 5 }

rcIpBgpExtPeerAfTable OBJECT-TYPE
        SYNTAX SEQUENCE OF RcIpBgpExtPeerAfEntry
        MAX-ACCESS not-accessible
        STATUS current
        DESCRIPTION
            "Extension to the BGP peer table.  This table contains,
             one entry per BGP peer, information about the connections
             with BGP Peers, which is not supported by the standard
             MIB draft. This table replaces rcIpBgpPeerTable."
        ::= { rcIpBgpExt 6 }

rcIpBgpExtPeerAfEntry OBJECT-TYPE
        SYNTAX RcIpBgpExtPeerAfEntry
        MAX-ACCESS not-accessible
        STATUS current
        DESCRIPTION
            "Entry containing miscelleneous information (info not
             present in the standard BGP peer table) about the
             connection with a remote BGP peer ."
        AUGMENTS {
            rcIpBgpTmpPeerAfEntry
        }
        ::= { rcIpBgpExtPeerAfTable 1 }

RcIpBgpExtPeerAfEntry ::= SEQUENCE {
        rcIpBgpExtPeerAfGroupName             SnmpAdminString,
        rcIpBgpExtPeerAfDefaultOriginate      TruthValue,
        rcIpBgpExtPeerAfDefaultOriginateIpv6  TruthValue,
        rcIpBgpExtPeerAfEbgpMultiHop          TruthValue,
        rcIpBgpExtPeerAfAdvertisementInterval Integer32,
        rcIpBgpExtPeerAfPassword              SnmpAdminString,
        rcIpBgpExtPeerAfWeight                Integer32,
        rcIpBgpExtPeerAfMaxPrefix             Integer32,
        rcIpBgpExtPeerAfNextHopSelf           TruthValue,
        rcIpBgpExtPeerAfRoutePolicyIn         SnmpAdminString,
        rcIpBgpExtPeerAfRoutePolicyOut        SnmpAdminString,
        rcIpBgpExtPeerAfRouteReflectorClient  TruthValue,
        rcIpBgpExtPeerAfSoftReconfigurationIn TruthValue,
        rcIpBgpExtPeerAfSoftReconfiguration   INTEGER,
        rcIpBgpExtPeerAfRemovePrivateAs       TruthValue,
        rcIpBgpExtPeerAfMD5Authentication     TruthValue,
        rcIpBgpExtPeerAfDebugMask             Integer32,
        rcIpBgpExtPeerAfSendCommunity         TruthValue,
        rcIpBgpExtPeerAfUpdateSourceInterface InetAddress,
        rcIpBgpExtPeerAfVpnv4Address          TruthValue,
        rcIpBgpExtPeerAfIpv6Cap               TruthValue,
        rcIpBgpExtPeerAfIpvpnLiteCap          TruthValue,
        rcIpBgpExtPeerAfSooAddress            IpAddress,
        rcIpBgpExtPeerAfSooAsNumber           Integer32,
        rcIpBgpExtPeerAfSooAssignedNum        Unsigned32,
        rcIpBgpExtPeerAfSooType               INTEGER,
        rcIpBgpExtPeerAfRouteRefresh          TruthValue,
        rcIpBgpExtPeerAfAsOverride            TruthValue,
        rcIpBgpExtPeerAfAllowAsIn             Integer32,
        rcIpBgpExtPeerAfIpv6RoutePolicyIn     SnmpAdminString,
        rcIpBgpExtPeerAfIpv6RoutePolicyOut    SnmpAdminString,
        rcIpBgpExtPeerAfEnable                TruthValue,
        rcIpBgpExtPeerAfRemoteAs              InetAutonomousSystemNumber, 
        rcIpBgpExtPeerAfConnectRetryInterval  Unsigned32,
        rcIpBgpExtPeerAfHoldTimeConfigured    Unsigned32,
        rcIpBgpExtPeerAfKeepAliveConfigured   Unsigned32,
        rcIpBgpExtPeerAfRowStatus             RowStatus,
        rcIpBgpExtPeerAfNewRemoteAs           OCTET STRING
}

rcIpBgpExtPeerAfGroupName OBJECT-TYPE
        SYNTAX        SnmpAdminString(SIZE(0..255))
        MAX-ACCESS    read-create
        STATUS        current
        DESCRIPTION   "Peer group name to which this peer belongs (optional)"
        ::= { rcIpBgpExtPeerAfEntry 1 }

rcIpBgpExtPeerAfDefaultOriginate OBJECT-TYPE
        SYNTAX        TruthValue
        MAX-ACCESS    read-create
        STATUS        current
        DESCRIPTION   "To allow a BGP speaker (the local router) to 
                       send the default route 0.0.0.0 to a neighbor for
                       use as a default route"
        DEFVAL        {false}
        ::= { rcIpBgpExtPeerAfEntry 2 }

rcIpBgpExtPeerAfDefaultOriginateIpv6  OBJECT-TYPE
        SYNTAX        TruthValue
        MAX-ACCESS    read-create
        STATUS        current
        DESCRIPTION   "To allow a BGP speaker (the local router) to 
                       Send the default ipv6 route to a neighbor for
                       use as a default route"
        DEFVAL        {false}
        ::= { rcIpBgpExtPeerAfEntry 3 }

rcIpBgpExtPeerAfEbgpMultiHop OBJECT-TYPE
        SYNTAX        TruthValue
        MAX-ACCESS    read-create
        STATUS        current
        DESCRIPTION   "To accept and attempt BGP connections to
                       external peers residing on networks that are not
                       directly connected"
        DEFVAL          {false}
        ::= { rcIpBgpExtPeerAfEntry 4 }

rcIpBgpExtPeerAfAdvertisementInterval OBJECT-TYPE
        SYNTAX        Integer32 (5..120)
        MAX-ACCESS    read-create
        STATUS        current
        DESCRIPTION   "To set the minimum interval between the sending
                       Of BGP routing updates Time in seconds. Integer
                       from 5 to 120."
        DEFVAL        { 30 }
        ::= { rcIpBgpExtPeerAfEntry 5 }

rcIpBgpExtPeerAfPassword OBJECT-TYPE
        SYNTAX        SnmpAdminString(SIZE(0..80))
        MAX-ACCESS    read-create
        STATUS        current
        DESCRIPTION   "To enable MD5 authentication on a TCP connection
                       between two BGP Peers Case-sensitive password of
                       up to 80 character"
        ::= { rcIpBgpExtPeerAfEntry 6 }

rcIpBgpExtPeerAfWeight OBJECT-TYPE
        SYNTAX        Integer32 (0..65535)
        MAX-ACCESS    read-create
        STATUS        current
        DESCRIPTION   "To assign an absolute weight to a BGP network.
                       It can be an integer from 0 to  65535."
        DEFVAL        { 100 }
        ::= { rcIpBgpExtPeerAfEntry 7 }

rcIpBgpExtPeerAfMaxPrefix OBJECT-TYPE
        SYNTAX        Integer32 (0..2147483647)
        MAX-ACCESS    read-create
        STATUS        current
        DESCRIPTION   "Sets a limit on the number of routes that will
                       be accepted from a neighbor. A value of zero
                       indicates no limit"
        DEFVAL          {12000}
        ::= { rcIpBgpExtPeerAfEntry 8 }

rcIpBgpExtPeerAfNextHopSelf  OBJECT-TYPE
        SYNTAX        TruthValue
        MAX-ACCESS    read-create
        STATUS        current
        DESCRIPTION   "Set NextHop Attribute to local router address
                       Before sending updates to remote peer"
        DEFVAL        { false }
        ::= { rcIpBgpExtPeerAfEntry 9 }

rcIpBgpExtPeerAfRoutePolicyIn OBJECT-TYPE
        SYNTAX        SnmpAdminString(SIZE(0..64))
        MAX-ACCESS    read-create
        STATUS        current
        DESCRIPTION   "Route Policy Name that will be applied to all
                       Networks learned from this peer"
        ::= { rcIpBgpExtPeerAfEntry 10 }

rcIpBgpExtPeerAfRoutePolicyOut OBJECT-TYPE
        SYNTAX        SnmpAdminString(SIZE(0..64))
        MAX-ACCESS    read-create
        STATUS        current
        DESCRIPTION   "Route policy name that will be applied to all              
                       outgoing updates"
        ::= { rcIpBgpExtPeerAfEntry 11 }

rcIpBgpExtPeerAfRouteReflectorClient OBJECT-TYPE
        SYNTAX        TruthValue
        MAX-ACCESS    read-create
        STATUS        current
        DESCRIPTION   "Indicates whether this peer is a route reflector
                       client."
        DEFVAL        {false} 
        ::= { rcIpBgpExtPeerAfEntry 12 }

rcIpBgpExtPeerAfSoftReconfigurationIn OBJECT-TYPE
        SYNTAX        TruthValue
        MAX-ACCESS    read-create
        STATUS        current
        DESCRIPTION   "If Peer soft reconfiguration is enabled in the
                       in-bound direction, policy can be changed and 
                       routes can re-learned without having to reset 
                       the bgp connection. Enabling soft reconfig-in
                       causes all bgp routes to be stored in local
                       memory (even non-best routes)"
        DEFVAL        {true}
        ::= { rcIpBgpExtPeerAfEntry 13 }

rcIpBgpExtPeerAfSoftReconfiguration OBJECT-TYPE
        SYNTAX        INTEGER {
                                in (1),
                                out(2),
                                none(3)
                              }
        MAX-ACCESS    read-create
        STATUS        current
        DESCRIPTION   "If rcIpBgpExtPeerAfSoftReconfigurationIn is enabled
                       in the in-bound direction, policy can be changed
                       and routes can re-learned without having to 
                       reset the bgp connection by setting  
                       rcIpBgpExtPeerAfSoftReconfiguration to in(1).
                       Setting the value to out (2) forces the neighbor
                       to send out all the updates to the remote
                       neighbor without resetting the connection."
        DEFVAL        {none}
        ::= { rcIpBgpExtPeerAfEntry 14 }

rcIpBgpExtPeerAfRemovePrivateAs OBJECT-TYPE
        SYNTAX       TruthValue
        MAX-ACCESS   read-create
        STATUS       current
        DESCRIPTION  "Enable and disable private AS number from being
                      stripped when sending an update"
        DEFVAL          { false  } 
        ::= { rcIpBgpExtPeerAfEntry 15 }

rcIpBgpExtPeerAfMD5Authentication  OBJECT-TYPE
        SYNTAX      TruthValue
        MAX-ACCESS      read-create
        STATUS      current 
        DESCRIPTION "Enable and Disable MD5 authentication"
        DEFVAL       { false }
        ::= { rcIpBgpExtPeerAfEntry 16 }

rcIpBgpExtPeerAfDebugMask OBJECT-TYPE
        SYNTAX         Integer32 (0..511)
        MAX-ACCESS     read-create
        STATUS         current 
        DESCRIPTION    " value is one of multiple (logically by 'OR' of
                         following value:
                                 none (0),
                                 error(1),
                                 packet(2),
                                 event(4),
                                 trace(8),
                                 warning(16),
                                 state(32),
                                 init(64),
                                 filter(128),
                                 update(256),
                                 all(511) 
                        all(511): Enables all debugging messages.
                        none(0): Disables all debugging messages.
                        error(1): Enables display of debug error
                        messages.
                        packet(2): Enables display of debug packet
                        messages. 
                        event(4): Enables display of debug event
                        messages. 
                        trace(8): Enables display debug trace messages.
                        warning(16): Enables display debug warning
                        messages.
                        state(32): Enables display of debug state
                        transition messages.
                        init(64): Enables display of debug
                        initialization messages.
                        filter(128): Enables display of debug messages
                        related to filtering.
                        update(256): Enables display of debug messages
                        related to sending and receiving
                        updates."
        DEFVAL          { 0 }
        ::=  { rcIpBgpExtPeerAfEntry 17 }

-- Following between =begin =end is processed by mib_tools/extras.awk
-- =begin enum
-- rcIpBgpExtPeerAfDebugMask none    0
-- rcIpBgpExtPeerAfDebugMask error   1
-- rcIpBgpExtPeerAfDebugMask packet  2
-- rcIpBgpExtPeerAfDebugMask event   4
-- rcIpBgpExtPeerAfDebugMask trace   8
-- rcIpBgpExtPeerAfDebugMask warning 16
-- rcIpBgpExtPeerAfDebugMask state   32
-- rcIpBgpExtPeerAfDebugMask init    64
-- rcIpBgpExtPeerAfDebugMask filter  128
-- rcIpBgpExtPeerAfDebugMask update  256
-- rcIpBgpExtPeerAfDebugMask all     511
-- =end enum

rcIpBgpExtPeerAfSendCommunity  OBJECT-TYPE
        SYNTAX      TruthValue
        MAX-ACCESS  read-create
        STATUS      current
        DESCRIPTION "Enables or disables sending the update message
                     community attribute to the specified peer."
        DEFVAL       { false }
        ::= { rcIpBgpExtPeerAfEntry 18 }

rcIpBgpExtPeerAfUpdateSourceInterface  OBJECT-TYPE
        SYNTAX        InetAddress
        MAX-ACCESS    read-create
        STATUS        current
        DESCRIPTION   "The Inet address to be used for Circuitless IP."
        ::= { rcIpBgpExtPeerAfEntry 19 }

rcIpBgpExtPeerAfVpnv4Address  OBJECT-TYPE
        SYNTAX      TruthValue
        MAX-ACCESS  read-create
        STATUS      current
        DESCRIPTION " The vpnv4 routes specified."
        DEFVAL       { false }
        ::= { rcIpBgpExtPeerAfEntry 20 }

rcIpBgpExtPeerAfIpv6Cap  OBJECT-TYPE
        SYNTAX      TruthValue
        MAX-ACCESS  read-create
        STATUS      current
        DESCRIPTION " The ipv6 capability can be enabled or
                     disabled on the bgp neighbor peer."
        DEFVAL       { false }
        ::= { rcIpBgpExtPeerAfEntry 21 }

rcIpBgpExtPeerAfIpvpnLiteCap OBJECT-TYPE
        SYNTAX      TruthValue
        MAX-ACCESS  read-create
        STATUS      current
        DESCRIPTION "The IPVPN-lite capability can be enabled or
                     disabled on the bgp neighbor peer."
        DEFVAL       { false }
        ::= { rcIpBgpExtPeerAfEntry 22 }

rcIpBgpExtPeerAfSooAddress     OBJECT-TYPE
        SYNTAX        IpAddress
        MAX-ACCESS    read-create
        STATUS        current
        DESCRIPTION   " The site-of-origin ip address."
        ::= { rcIpBgpExtPeerAfEntry 23 }

rcIpBgpExtPeerAfSooAsNumber  OBJECT-TYPE
        SYNTAX        Integer32(0..65535)
        MAX-ACCESS    read-create
        STATUS        current
        DESCRIPTION   "The asnum for the site-of-origin for bgp peer."
        ::= { rcIpBgpExtPeerAfEntry  24}

rcIpBgpExtPeerAfSooAssignedNum     OBJECT-TYPE
        SYNTAX        Unsigned32 (0..2147483647)
        MAX-ACCESS    read-create
        STATUS        current
        DESCRIPTION   "The Assigned number required along with asnum or
                       address to configure the site-of-origin for bgp
                       peer."
        ::= { rcIpBgpExtPeerAfEntry  25}

rcIpBgpExtPeerAfSooType        OBJECT-TYPE
        SYNTAX        INTEGER {
                        none(0),
                        asnum(1),
                        ipaddr(2)
                      }
        MAX-ACCESS    read-only
        STATUS        current
        DESCRIPTION   " The soo type can be asnum or ipaddress."
        DEFVAL        { none }
        ::= { rcIpBgpExtPeerAfEntry  26}

rcIpBgpExtPeerAfRouteRefresh           OBJECT-TYPE
        SYNTAX        TruthValue
        MAX-ACCESS    read-create  
        STATUS        current
        DESCRIPTION   "Route refresh for bgp peer."
        DEFVAL       { false }
        ::= { rcIpBgpExtPeerAfEntry   27 }

rcIpBgpExtPeerAfAsOverride    OBJECT-TYPE
        SYNTAX        TruthValue
        MAX-ACCESS    read-create
        STATUS        current
        DESCRIPTION   "The AS Override value can be enabled or disabled
                       for bgp peer."
        DEFVAL        { false }
        ::= { rcIpBgpExtPeerAfEntry  28}

rcIpBgpExtPeerAfAllowAsIn    OBJECT-TYPE
        SYNTAX        Integer32(0..10)
        MAX-ACCESS    read-create
        STATUS        current
        DESCRIPTION   "The number of as-in allowed for bgp peer."
        ::= { rcIpBgpExtPeerAfEntry  29}

rcIpBgpExtPeerAfIpv6RoutePolicyIn OBJECT-TYPE
        SYNTAX        SnmpAdminString(SIZE(0..64))
        MAX-ACCESS    read-create
        STATUS        current
        DESCRIPTION   "Ipv6 Route Policy Name that will be applied to all
                       Networks learned from this peer"
        ::= { rcIpBgpExtPeerAfEntry 30 }

rcIpBgpExtPeerAfIpv6RoutePolicyOut OBJECT-TYPE
        SYNTAX        SnmpAdminString(SIZE(0..64))
        MAX-ACCESS    read-create
        STATUS        current
        DESCRIPTION   "Ipv6 Route policy name that will be applied to all
                       outgoing updates"
        ::= { rcIpBgpExtPeerAfEntry 31 }

rcIpBgpExtPeerAfEnable OBJECT-TYPE
        SYNTAX        TruthValue
        MAX-ACCESS    read-create
        STATUS        current
        DESCRIPTION   "Used to enable/disable bgp+ peer"
        ::= { rcIpBgpExtPeerAfEntry 32 }

rcIpBgpExtPeerAfRemoteAs OBJECT-TYPE
        SYNTAX        InetAutonomousSystemNumber
        MAX-ACCESS    read-create
        STATUS        current
        DESCRIPTION   "Used to manually configure the remote as of the bgp+ 
                       peer."
        ::= { rcIpBgpExtPeerAfEntry 33 }

rcIpBgpExtPeerAfConnectRetryInterval OBJECT-TYPE
        SYNTAX        Unsigned32 (1..65535)
        UNITS         "seconds"
        MAX-ACCESS    read-create
        STATUS        current
        DESCRIPTION   "Used to configure the ConnectRetry timer for the 
                       BGP+ peer."
        ::= { rcIpBgpExtPeerAfEntry 34 }

rcIpBgpExtPeerAfHoldTimeConfigured  OBJECT-TYPE
        SYNTAX        Unsigned32 ( 0 | 3..65535 )
        UNITS         "seconds"
        MAX-ACCESS    read-create
        STATUS        current
        DESCRIPTION   "Used to configure the Hold Timer for the BGP+ peer."
        ::= { rcIpBgpExtPeerAfEntry 35 }

rcIpBgpExtPeerAfKeepAliveConfigured OBJECT-TYPE
        SYNTAX        Unsigned32 ( 0 | 1..21845 )
        UNITS         "seconds"
        MAX-ACCESS    read-create
        STATUS        current
        DESCRIPTION   "Used to configure the KeepAlive Timer for the BGP+ peer."
        ::= { rcIpBgpExtPeerAfEntry 36 }

rcIpBgpExtPeerAfRowStatus OBJECT-TYPE
        SYNTAX      RowStatus 
        MAX-ACCESS  read-create
        STATUS      current
        DESCRIPTION "Used to create/delete entries in the Table."
        ::= { rcIpBgpExtPeerAfEntry 37 }

rcIpBgpExtPeerAfNewRemoteAs OBJECT-TYPE
        SYNTAX        OCTET STRING(SIZE (0..4))
        MAX-ACCESS    read-create
        STATUS        current
        DESCRIPTION   "Remote Autonomous system number of this peer"
        ::= { rcIpBgpExtPeerAfEntry 38 }

rcIpBgpExtAfPathAttrTable OBJECT-TYPE
        SYNTAX     SEQUENCE OF RcIpBgpExtAfPathAttrEntry
        MAX-ACCESS not-accessible
        STATUS     current
        DESCRIPTION
            "Extension to rcIpBgpTmpAfPathAttrTable. This table contains
             info about additional BGP path attributes not covered in 
             rcIpBgpTmpAfPathAttrTable."
        ::= { rcIpBgpExt 7 }

rcIpBgpExtAfPathAttrEntry OBJECT-TYPE
        SYNTAX     RcIpBgpExtAfPathAttrEntry
        MAX-ACCESS not-accessible
        STATUS     current
        DESCRIPTION
            "Each entry contains data about additional path attributes
             associated with a given prefix in the rcIpBgpTmpNlriTable."
        AUGMENTS {
            rcIpBgpTmpAfPathAttrEntry
        }
        ::= { rcIpBgpExtAfPathAttrTable 1 }

RcIpBgpExtAfPathAttrEntry ::= SEQUENCE {
        rcIpBgpExtAfPathAttrUnknown OCTET STRING,
        rcIpBgpExtAfPathAttrCommunities OCTET STRING,
        rcIpBgpExtAfPathAttrOriginateId IpAddress,
        rcIpBgpExtAfPathAttrClusterId OCTET STRING
}        
 
rcIpBgpExtAfPathAttrUnknown OBJECT-TYPE
        SYNTAX     OCTET STRING (SIZE(0..255))
        MAX-ACCESS read-only
        STATUS     current
        DESCRIPTION
            "Replaces bgp4PathAttrUnknown.
             One or more path attributes not understood
             by this BGP4 speaker.  Size zero (0)
             indicates the absence of such
             attribute(s). Octets beyond the maximum
             size, if any, are not recorded by this
             object."
        ::= { rcIpBgpExtAfPathAttrEntry 1 }

rcIpBgpExtAfPathAttrCommunities OBJECT-TYPE
        SYNTAX        OCTET STRING (SIZE(0..255))
        MAX-ACCESS    read-only
        STATUS        current
        DESCRIPTION   
            "The string represents BGP+ community path attributes as 
             <length ,value>. The length is a 1-octet field containing the 
             numbner of community numbers in the value field.The value field 
             contains one or more Community numbers,each community is 
             represented in the octet string as 4 octets.The community numbers 
             in the string beyond maximum size 255,if any, will not be recorded 
             by this object."
        ::=   { rcIpBgpExtAfPathAttrEntry 2 }

rcIpBgpExtAfPathAttrOriginateId OBJECT-TYPE
        SYNTAX        IpAddress
        MAX-ACCESS    read-only
        STATUS        current
        DESCRIPTION   "In a BGP+ context, the IP address of the router which 
                       originates the routes."
        ::=   { rcIpBgpExtAfPathAttrEntry 3 }

rcIpBgpExtAfPathAttrClusterId OBJECT-TYPE
        SYNTAX        OCTET STRING (SIZE(0..255))
        MAX-ACCESS    read-only
        STATUS        current
        DESCRIPTION   "The string represents BGP+ Cluster Id path attributes as 
                       <length,value>.  The length is a 1-octet field containing
                       the number of Cluster Id numbers in the value field. The 
                       value field contains one or more Cluster Id numbers, each                       Cluster Id is represented in the octet string as 4 
                       octets, each four octets is the IpAddress of the router 
                       acting as a route reflector.The Cluster Id numbers in the
                       string beyond maximum size 255,if any, will not be 
                       recorded by this object."
        ::=   { rcIpBgpExtAfPathAttrEntry 4 }


    rcIpBgpTmp OBJECT IDENTIFIER ::= { rcIpBgp 17 }

    --
    -- Textual Conventions
    --


    RcIpBgpTmpIdentifierTC ::= TEXTUAL-CONVENTION
        DISPLAY-HINT "1d."
        STATUS       current
        DESCRIPTION
            "The representation of a BGP Identifier.  BGP Identifiers
             are presented in the received network byte order.
             The BGP Identifier is displayed as if it is an IP address,
             even if it would be an illegal one."
        REFERENCE
            "RFC 4273, Section 4.2"
        SYNTAX OCTET STRING(SIZE (4))


    RcIpBgpTmpAddressFamilyIdentifierTC ::= TEXTUAL-CONVENTION
        DISPLAY-HINT "d"
        STATUS       current
        DESCRIPTION
            "The representation of a BGP AFI"
        REFERENCE
            "RFC 4760, Section 3"
        SYNTAX Unsigned32(0..65535)


    RcIpBgpTmpSubsequentAddressFamilyIdentifierTC ::= TEXTUAL-CONVENTION
        DISPLAY-HINT "d"
        STATUS       current
        DESCRIPTION
            "The representation of a BGP SAFI"
        REFERENCE
            "RFC 4760, Section 3"
        SYNTAX Unsigned32(0..255)

    --
    -- Top level scalars for this MIB
    --

    rcIpBgpTmpLocalAsNew OBJECT-TYPE
        SYNTAX     InetAutonomousSystemNumber
        MAX-ACCESS read-only
        STATUS     current
        DESCRIPTION
            "The local autonomous system number.

             This object supports 4 byte ASes and replaces
             bgpLocalAs."
        REFERENCE
                 "RFC 4271, Section 4.2, 'My Autonomous System'.

                  RFC 4893, BGP Support for Four-octet AS Number
                  Space."
        ::= { rcIpBgpTmp 9 }

    --
    -- Address Family (Af) independent per-peer management information.
    --

    rcIpBgpTmpPeerAf
        OBJECT IDENTIFIER ::= { rcIpBgpTmp 10 }

    --
    -- Address Family (Af) independent per-peer session management
    -- information.
    --

    rcIpBgpTmpPeerAfTable OBJECT-TYPE
        SYNTAX     SEQUENCE OF RcIpBgpTmpPeerAfEntry
        MAX-ACCESS not-accessible
        STATUS     current
        DESCRIPTION
            "BGP peer table.  This table contains, one entry per BGP
             peer, information about the connections with BGP peers.

             This table replaces bgpPeerTable."
        ::= { rcIpBgpTmpPeerAf 1 }

    rcIpBgpTmpPeerAfEntry OBJECT-TYPE
        SYNTAX     RcIpBgpTmpPeerAfEntry
        MAX-ACCESS not-accessible
        STATUS     current
        DESCRIPTION
            "Entry containing information about the connection with
             a remote BGP peer."
        INDEX {
            rcIpBgpTmpPeerAfInstance,
            rcIpBgpTmpPeerAfLocalAddrType,
            rcIpBgpTmpPeerAfLocalAddr,
            rcIpBgpTmpPeerAfRemoteAddrType,
            rcIpBgpTmpPeerAfRemoteAddr
        }
        ::= { rcIpBgpTmpPeerAfTable 1 }

    RcIpBgpTmpPeerAfEntry ::= SEQUENCE {
        -- INDEX information
        rcIpBgpTmpPeerAfInstance
            Unsigned32,
        rcIpBgpTmpPeerAfLocalAddrType
            InetAddressType,
        rcIpBgpTmpPeerAfLocalAddr
            InetAddress,
        rcIpBgpTmpPeerAfRemoteAddrType
            InetAddressType,
        rcIpBgpTmpPeerAfRemoteAddr
            InetAddress,

        -- Local
        rcIpBgpTmpPeerAfLocalPort
            InetPortNumber,
        rcIpBgpTmpPeerAfLocalAs
            InetAutonomousSystemNumber,

        -- Remote
        rcIpBgpTmpPeerAfRemotePort
            InetPortNumber,
        rcIpBgpTmpPeerAfRemoteAs
            InetAutonomousSystemNumber,
        rcIpBgpTmpPeerAfIdentifier
            RcIpBgpTmpIdentifierTC,

        -- Session status
        rcIpBgpTmpPeerAfAdminStatus
            INTEGER,
        rcIpBgpTmpPeerAfPeerState
            INTEGER,
        rcIpBgpTmpPeerAfConfiguredVersion
            Unsigned32,
        rcIpBgpTmpPeerAfNegotiatedVersion
            Unsigned32
    }

    rcIpBgpTmpPeerAfInstance OBJECT-TYPE
        SYNTAX     Unsigned32 (1..4294967295)
        MAX-ACCESS not-accessible
        STATUS     current
        DESCRIPTION
            "The routing instance index.

             Some BGP implementations permit the creation of
             multiple instances of a BGP routing process. An
             example includes routers running BGP/MPLS IP Virtual
             Private Networks.

             Implementations that do not support multiple
             routing instances should return 1 for this object."
        ::= { rcIpBgpTmpPeerAfEntry 1 }

    rcIpBgpTmpPeerAfLocalAddrType OBJECT-TYPE
        SYNTAX     InetAddressType
        MAX-ACCESS not-accessible
        STATUS     current
        DESCRIPTION
            "The address family of the local end of the peering
             session."
        ::= { rcIpBgpTmpPeerAfEntry 2 }

    rcIpBgpTmpPeerAfLocalAddr OBJECT-TYPE
        SYNTAX     InetAddress
        MAX-ACCESS not-accessible
        STATUS     current
        DESCRIPTION
            "The local IP address of this entry's BGP connection."
        ::= { rcIpBgpTmpPeerAfEntry 3 }

    rcIpBgpTmpPeerAfRemoteAddrType OBJECT-TYPE
        SYNTAX     InetAddressType
        MAX-ACCESS not-accessible
        STATUS     current
        DESCRIPTION
            "The address family of the remote end of the peering
             session."
        ::= { rcIpBgpTmpPeerAfEntry 4 }

    rcIpBgpTmpPeerAfRemoteAddr OBJECT-TYPE
        SYNTAX     InetAddress
        MAX-ACCESS not-accessible
        STATUS     current
        DESCRIPTION
            "The remote IP address of this entry's BGP peer."
        ::= { rcIpBgpTmpPeerAfEntry 5 }

    rcIpBgpTmpPeerAfLocalPort OBJECT-TYPE
        SYNTAX     InetPortNumber
        MAX-ACCESS read-only
        STATUS     current
        DESCRIPTION
            "The local port for the TCP connection between the BGP
             peers."
        ::= { rcIpBgpTmpPeerAfEntry 6 }

    rcIpBgpTmpPeerAfLocalAs OBJECT-TYPE
        SYNTAX     InetAutonomousSystemNumber
        MAX-ACCESS read-only
        STATUS     current
        DESCRIPTION
            "Some implementations of BGP can represent themselves
             as multiple ASes. This is the AS that this peering
             session is representing itself as to the remote peer."
        ::= { rcIpBgpTmpPeerAfEntry 7 }

    rcIpBgpTmpPeerAfRemotePort OBJECT-TYPE
        SYNTAX     InetPortNumber
        MAX-ACCESS read-only
        STATUS     current
        DESCRIPTION
            "The remote port for the TCP connection between the BGP
             peers.

             Note that the objects rcIpBgpTmpPeerAfLocalAddr,
             rcIpBgpTmpPeerAfLocalPort, rcIpBgpTmpPeerAfRemoteAddr and
             rcIpBgpTmpPeerAfRemotePort provide the appropriate reference to
             the standard MIB TCP connection table, or even the ipv6
             TCP MIB as in RFC 4022."
        REFERENCE
            "RFC 2012 - SNMPv2 Management Information Base for the
             Transmission Control Protocol using SMIv2.
             RFC 4022 - IP Version 6 Management Information Base
             for the Transmission Control Protocol."
        ::= { rcIpBgpTmpPeerAfEntry 8 }

    rcIpBgpTmpPeerAfRemoteAs OBJECT-TYPE
        SYNTAX     InetAutonomousSystemNumber
        MAX-ACCESS read-only
        STATUS     current
        DESCRIPTION
            "The remote autonomous system number received in the BGP
             OPEN message."
        REFERENCE
            "RFC 4271, Section 4.2."
        ::= { rcIpBgpTmpPeerAfEntry 9 }

    rcIpBgpTmpPeerAfIdentifier OBJECT-TYPE
        SYNTAX     RcIpBgpTmpIdentifierTC
        MAX-ACCESS read-only
        STATUS     current
        DESCRIPTION
            "The BGP Identifier of this entry's remote BGP peer.

             This entry should be 0.0.0.0 unless the
             rcIpBgpTmpPeerAfPeerState is in the openconfirm or the
             established state."
        REFERENCE
            "RFC 4271, Section 4.2, 'BGP Identifier'."
        ::= { rcIpBgpTmpPeerAfEntry 10 }

    rcIpBgpTmpPeerAfAdminStatus OBJECT-TYPE
        SYNTAX     INTEGER {
            halted(1),
            running(2)
        }
        MAX-ACCESS read-only
        STATUS     current
        DESCRIPTION
            "Whether or not the BGP FSM for this remote peer is
             halted or running. The BGP FSM for a remote peer is
             halted after processing a Stop event. Likewise, it is
             in the running state after a Start event.

             The rcIpBgpTmpPeerAfState will generally be in the idle state
             when the FSM is halted, although some extensions such
             as Graceful Restart will leave the peer in the Idle
             state but with the FSM running."
        REFERENCE
            "RFC 4271, Section 8.1.2."
        ::= { rcIpBgpTmpPeerAfEntry 11 }

    rcIpBgpTmpPeerAfPeerState OBJECT-TYPE
        SYNTAX     INTEGER {
            idle(1),
            connect(2),
            active(3),
            opensent(4),
            openconfirm(5),
            established(6)
        }
        MAX-ACCESS read-only
        STATUS     current
        DESCRIPTION
            "The BGP peer connection state."
        REFERENCE
            "RFC 4271, Section 8.2.2."
        ::= { rcIpBgpTmpPeerAfEntry 12 }

    rcIpBgpTmpPeerAfConfiguredVersion OBJECT-TYPE
        SYNTAX     Unsigned32 (1..255)
        MAX-ACCESS read-only
        STATUS     current
        DESCRIPTION
            "The configured version to originally start with this
             remote peer. The BGP speaker may permit negotiation to a
             lower version number of the protocol."
        REFERENCE
            "RFC 4271, Section 4.2.
             RFC 4271, Section 7."
        ::= { rcIpBgpTmpPeerAfEntry 13 }

    rcIpBgpTmpPeerAfNegotiatedVersion OBJECT-TYPE
        SYNTAX     Unsigned32 (1..255)
        MAX-ACCESS read-only
        STATUS     current
        DESCRIPTION
            "The negotiated version of BGP running between
             the two peers.

             This entry MUST be zero (0) unless the
             rcIpBgpTmpPeerAfState is in the openconfirm or the
             established state.

             Note that legal values for this object are
             between 0 and 255."
        REFERENCE
            "RFC 4271, Section 4.2.
             RFC 4271, Section 7."
        ::= { rcIpBgpTmpPeerAfEntry 14 }


    --
    -- Address Family (Af) independent per-peer error management
    -- information.
    --

    rcIpBgpTmpPeerAfErrors
        OBJECT IDENTIFIER ::= { rcIpBgpTmpPeerAf 2 }

    rcIpBgpTmpPeerAfErrorsTable OBJECT-TYPE
        SYNTAX     SEQUENCE OF RcIpBgpTmpPeerAfErrorsEntry
        MAX-ACCESS not-accessible
        STATUS     current
        DESCRIPTION
            "On a per-peer basis, this table reflects the last
             protocol-defined error encountered and reported on
             the peer session. If no entry for a given peer
             exists in this table, then no such errors have been
             observed, reported, and recorded on the session."
        ::= { rcIpBgpTmpPeerAfErrors 1 }

    rcIpBgpTmpPeerAfErrorsEntry OBJECT-TYPE
        SYNTAX     RcIpBgpTmpPeerAfErrorsEntry
        MAX-ACCESS not-accessible
        STATUS     current
        DESCRIPTION
            "Each entry contains information about errors sent
             and received for a particular BGP peer."
        AUGMENTS {
            rcIpBgpTmpPeerAfEntry
        }
        ::= { rcIpBgpTmpPeerAfErrorsTable 1 }

    RcIpBgpTmpPeerAfErrorsEntry ::= SEQUENCE {
        rcIpBgpTmpPeerAfLastErrorCodeReceived
            OCTET STRING,
        rcIpBgpTmpPeerAfLastErrorSubCodeReceived
            OCTET STRING,
        rcIpBgpTmpPeerAfLastErrorReceivedTime
            TimeStamp,
        rcIpBgpTmpPeerAfLastErrorReceivedText
            SnmpAdminString,
        rcIpBgpTmpPeerAfLastErrorReceivedData
            OCTET STRING,
        rcIpBgpTmpPeerAfLastErrorCodeSent
            OCTET STRING,
        rcIpBgpTmpPeerAfLastErrorSubCodeSent
            OCTET STRING,
        rcIpBgpTmpPeerAfLastErrorSentTime
            TimeStamp,
        rcIpBgpTmpPeerAfLastErrorSentText
            SnmpAdminString,
        rcIpBgpTmpPeerAfLastErrorSentData
            OCTET STRING
    }

    rcIpBgpTmpPeerAfLastErrorCodeReceived OBJECT-TYPE
        SYNTAX     OCTET STRING (SIZE (1))
        MAX-ACCESS read-only
        STATUS     current
        DESCRIPTION
            "The last error code received from this peer via NOTIFICATION
             message on this connection.  If no error has occurred, this
             field is zero."
        REFERENCE
            "RFC 4271, Section 4.5.
             RFC 4486 optionally supported.
             RFC 3362, Section 5 optionally supported."
        ::= { rcIpBgpTmpPeerAfErrorsEntry 1 }

    rcIpBgpTmpPeerAfLastErrorSubCodeReceived OBJECT-TYPE
        SYNTAX     OCTET STRING (SIZE (1))
        MAX-ACCESS read-only
        STATUS     current
        DESCRIPTION
            "The last subcode received from this peer via NOTIFICATION
             message on this connection.  If no error has occurred, this
             field is zero."
        REFERENCE
            "RFC 4271, Section 4.5.
             RFC 4486 optionally supported.
             RFC 3362, Section 5 optionally supported."
        ::= { rcIpBgpTmpPeerAfErrorsEntry 2 }

    rcIpBgpTmpPeerAfLastErrorReceivedTime OBJECT-TYPE
        SYNTAX     TimeStamp
        MAX-ACCESS read-only
        STATUS     current
        DESCRIPTION
            "The timestamp that the last NOTIFICATION was received from
             this peer."
        REFERENCE
            "RFC 4271, Section 4.5."
        ::= { rcIpBgpTmpPeerAfErrorsEntry 3 }

    rcIpBgpTmpPeerAfLastErrorReceivedText OBJECT-TYPE
        SYNTAX     SnmpAdminString
        MAX-ACCESS read-only
        STATUS     current
        DESCRIPTION
            "This object contains an implementation specific
             explanation of the error that was reported."
        ::= { rcIpBgpTmpPeerAfErrorsEntry 4 }

    rcIpBgpTmpPeerAfLastErrorReceivedData OBJECT-TYPE
        SYNTAX     OCTET STRING (SIZE(0..4075))
        MAX-ACCESS read-only
        STATUS     current
        DESCRIPTION
            "The last error code's data seen by this peer.

             Per RFC 2578, some implementations may have limitations
             dealing with OCTET STRINGS larger than 255.  Thus, this
             data may be truncated."
        REFERENCE
            "RFC 4271, Section 4.5,
             RFC 2578, Section 7.1.2,
             RFC 4486 optionaly supported.
             RFC 3362, Section 5 optionally supported."
        ::= { rcIpBgpTmpPeerAfErrorsEntry 5 }

    rcIpBgpTmpPeerAfLastErrorCodeSent OBJECT-TYPE
        SYNTAX     OCTET STRING (SIZE (1))
        MAX-ACCESS read-only
        STATUS     current
        DESCRIPTION
            "The last error code sent to this peer via NOTIFICATION
             message on this connection.  If no error has occurred, this
             field is zero."
        REFERENCE
            "RFC 4271, Section 4.5.
             RFC 4486 optionally supported.
             RFC 3362, Section 5 optionally supported."
        ::= { rcIpBgpTmpPeerAfErrorsEntry 6 }

    rcIpBgpTmpPeerAfLastErrorSubCodeSent OBJECT-TYPE
        SYNTAX     OCTET STRING (SIZE (1))
        MAX-ACCESS read-only
        STATUS     current
        DESCRIPTION
            "The last subcode sent to this peer via NOTIFICATION
             message on this connection.  If no error has occurred, this
             field is zero."
        REFERENCE
            "RFC 4271, Section 4.5.
             RFC 4486 optionally supported.
             RFC 3362, Section 5 optionally supported."
        ::= { rcIpBgpTmpPeerAfErrorsEntry 7 }

    rcIpBgpTmpPeerAfLastErrorSentTime OBJECT-TYPE
        SYNTAX     TimeStamp
        MAX-ACCESS read-only
        STATUS     current
        DESCRIPTION
            "The timestamp that the last NOTIFICATION was sent to
             this peer."
        REFERENCE
            "RFC 4271, Section 4.5."
        ::= { rcIpBgpTmpPeerAfErrorsEntry 8 }

    rcIpBgpTmpPeerAfLastErrorSentText OBJECT-TYPE
        SYNTAX     SnmpAdminString
        MAX-ACCESS read-only
        STATUS     current
        DESCRIPTION
            "This object contains an implementation specific
             explanation of the error that is being reported."
        ::= { rcIpBgpTmpPeerAfErrorsEntry 9 }

    rcIpBgpTmpPeerAfLastErrorSentData OBJECT-TYPE
        SYNTAX     OCTET STRING (SIZE(0..4075))
        MAX-ACCESS read-only
        STATUS     current
        DESCRIPTION
            "The last error code's data sent to this peer.

             Per RFC 2578, some implementations may have limitations
             dealing with OCTET STRINGS larger than 255.  Thus, this
             data may be truncated."
        REFERENCE
            "RFC 4271, Section 4.5,
             RFC 2578, Section 7.1.2
             RFC 4486 optionaly supported.
             RFC 3362, Section 5 optionally supported."
        ::= { rcIpBgpTmpPeerAfErrorsEntry 10 }

    --
    -- Address Family (Af) independent per-peer timer information
    --

    rcIpBgpTmpPeerAfTimers
        OBJECT IDENTIFIER ::= { rcIpBgpTmpPeerAf 3 }

    --
    -- Per-peer Event Times
    --

    rcIpBgpTmpPeerAfEventTimesTable OBJECT-TYPE
        SYNTAX     SEQUENCE OF RcIpBgpTmpPeerAfEventTimesEntry
        MAX-ACCESS not-accessible
        STATUS     current
        DESCRIPTION
            "A table reporting the per-peering session amount
             of time elapsed and update events since the peering
             session advanced into the established state."
        ::= { rcIpBgpTmpPeerAfTimers 1 }

    rcIpBgpTmpPeerAfEventTimesEntry OBJECT-TYPE
        SYNTAX     RcIpBgpTmpPeerAfEventTimesEntry
        MAX-ACCESS not-accessible
        STATUS     current
        DESCRIPTION
            "Each row contains a set of statistics about time
             spent and events encountered in the peer session
             established state."
        AUGMENTS {
            rcIpBgpTmpPeerAfEntry
        }
        ::= { rcIpBgpTmpPeerAfEventTimesTable 1 }

    RcIpBgpTmpPeerAfEventTimesEntry ::= SEQUENCE {
        rcIpBgpTmpPeerAfFsmEstablishedTime
            Gauge32,
        rcIpBgpTmpPeerAfInUpdatesElapsedTime
            Gauge32
    }

    rcIpBgpTmpPeerAfFsmEstablishedTime OBJECT-TYPE
        SYNTAX     Gauge32
        UNITS      "seconds"
        MAX-ACCESS read-only
        STATUS     current
        DESCRIPTION
            "This timer indicates how long (in seconds) this peer
             has been in the established state or how long since this
             peer was last in the established state.  It is set to
             zero when a new peer is configured or when the router is
             booted.  If the peer has never reached the established
             state, the value remains zero."
        REFERENCE
            "RFC 4271, Section 8."
        ::= { rcIpBgpTmpPeerAfEventTimesEntry 1 }

    rcIpBgpTmpPeerAfInUpdatesElapsedTime OBJECT-TYPE
        SYNTAX     Gauge32
        UNITS      "seconds"
        MAX-ACCESS read-only
        STATUS     current
        DESCRIPTION
            "Elapsed time (in seconds) since the last BGP UPDATE
             message was received from the peer.  Each time
             bgpPeerInUpdates is incremented, the value of this
             object is set to zero (0)."
        REFERENCE
            "RFC 4271, Section 4.3.
             RFC 4271, Section 8.2.2, Established state."
        ::= { rcIpBgpTmpPeerAfEventTimesEntry 2 }

    --
    -- Per-Peer Configured Timers
    --

    rcIpBgpTmpPeerAfConfiguredTimersTable OBJECT-TYPE
        SYNTAX     SEQUENCE OF RcIpBgpTmpPeerAfConfiguredTimersEntry
        MAX-ACCESS not-accessible
        STATUS     current
        DESCRIPTION
            "Per peer management data on BGP session timers."
        ::= { rcIpBgpTmpPeerAfTimers 2 }

    rcIpBgpTmpPeerAfConfiguredTimersEntry OBJECT-TYPE
        SYNTAX     RcIpBgpTmpPeerAfConfiguredTimersEntry
        MAX-ACCESS not-accessible
        STATUS     current
        DESCRIPTION
            "Each entry corresponds to the current state of
             BGP timers on a given peering session."
        AUGMENTS {
            rcIpBgpTmpPeerAfEntry
        }
        ::= { rcIpBgpTmpPeerAfConfiguredTimersTable 1 }

    RcIpBgpTmpPeerAfConfiguredTimersEntry ::= SEQUENCE {
        rcIpBgpTmpPeerAfConnectRetryInterval
            Unsigned32,
        rcIpBgpTmpPeerAfHoldTimeConfigured
            Unsigned32,
        rcIpBgpTmpPeerAfKeepAliveConfigured
            Unsigned32,
        rcIpBgpTmpPeerAfMinASOrigInterval
            Unsigned32,
        rcIpBgpTmpPeerAfMinRouteAdverInterval
            Unsigned32
    }

    rcIpBgpTmpPeerAfConnectRetryInterval OBJECT-TYPE
        SYNTAX     Unsigned32 (1..65535)
        UNITS      "seconds"
        MAX-ACCESS read-only
        STATUS     current
        DESCRIPTION
            "Time interval (in seconds) for the ConnectRetry timer.
             The suggested value for this timer is 120 seconds."
        REFERENCE
            "RFC 4271, Section 8.2.2.  This is the value used
             to initialize the 'ConnectRetryTimer'."
        ::= { rcIpBgpTmpPeerAfConfiguredTimersEntry 1 }

    rcIpBgpTmpPeerAfHoldTimeConfigured OBJECT-TYPE
        SYNTAX     Unsigned32 ( 0 | 3..65535 )
        UNITS      "seconds"
        MAX-ACCESS read-only
        STATUS     current
        DESCRIPTION
            "Time interval (in seconds) for the Hold Timer
             established with the peer.  The value of this object is
             calculated by this BGP speaker, using the smaller of the
             values in bgpPeerHoldTimeConfigured and the Hold Time
             received in the OPEN message.

             This value must be at least three seconds if it is not
             zero (0).

             If the Hold Timer has not been established with the
             peer this object MUST have a value of zero (0).

             If the bgpPeerHoldTimeConfigured object has a value of
             (0), then this object MUST have a value of (0)."
        REFERENCE
            "RFC 4271, Section 4.2."
        ::= { rcIpBgpTmpPeerAfConfiguredTimersEntry 2 }

    rcIpBgpTmpPeerAfKeepAliveConfigured OBJECT-TYPE
        SYNTAX     Unsigned32 ( 0 | 1..21845 )
        UNITS      "seconds"
        MAX-ACCESS read-only
        STATUS     current
        DESCRIPTION
            "Time interval (in seconds) for the KeepAlive timer
             configured for this BGP speaker with this peer.  The
             value of this object will only determine the KEEPALIVE
             messages' frequency relative to the value specified in
             bgpPeerHoldTimeConfigured; the actual time interval for
             the KEEPALIVE messages is indicated by bgpPeerKeepAlive.

             A reasonable maximum value for this timer would be one
             third of that of bgpPeerHoldTimeConfigured.

             If the value of this object is zero (0), no periodic
             KEEPALIVE messages are sent to the peer after the BGP
             connection has been established.  The suggested value
             for this timer is 30 seconds."
        REFERENCE
            "RFC 4271, Section 4.4.
             RFC 4271, Section 10."
        ::= { rcIpBgpTmpPeerAfConfiguredTimersEntry 3 }

    rcIpBgpTmpPeerAfMinASOrigInterval OBJECT-TYPE
        SYNTAX     Unsigned32 (0..65535)
        UNITS      "seconds"
        MAX-ACCESS read-only
        STATUS     current
        DESCRIPTION
            "Time interval (in seconds) for the
             MinASOriginationInterval timer.

             The suggested value for this timer is 15 seconds."
        REFERENCE
            "RFC 4271, Section 9.2.1.2.
             RFC 4271, Section 10."
        ::= { rcIpBgpTmpPeerAfConfiguredTimersEntry 4 }

    rcIpBgpTmpPeerAfMinRouteAdverInterval OBJECT-TYPE
        SYNTAX     Unsigned32 (0..65535)
        UNITS      "seconds"
        MAX-ACCESS read-only
        STATUS     current
        DESCRIPTION
            "Time interval (in seconds) for the
             MinRouteAdvertisementInterval timer.

             The suggested value for this timer is 30 seconds for
             EBGP connections and 5 seconds for IBGP connections."
        REFERENCE
            "RFC 4271, Section 9.2.1.1.
             RFC 4271, Section 10."
        ::= { rcIpBgpTmpPeerAfConfiguredTimersEntry 5 }

    --
    -- Per-Peer Negotiated Timers
    --

    rcIpBgpTmpPeerAfNegotiatedTimersTable OBJECT-TYPE
        SYNTAX     SEQUENCE OF RcIpBgpTmpPeerAfNegotiatedTimersEntry
        MAX-ACCESS not-accessible
        STATUS     current
        DESCRIPTION
            "Configured values of per-peer timers are seen
             in the rcIpBgpTmpPeerAfConfiguredTimersTable.
             Values in this table reflect the current
             operational values, after negotiation from values
             derived from initial configuration."
        ::= { rcIpBgpTmpPeerAfTimers 3 }

    rcIpBgpTmpPeerAfNegotiatedTimersEntry OBJECT-TYPE
        SYNTAX     RcIpBgpTmpPeerAfNegotiatedTimersEntry
        MAX-ACCESS not-accessible
        STATUS     current
        DESCRIPTION
            "Each entry reflects a value of the currently
             operational, negotiated timer as reflected in the
             rcIpBgpTmpPeerAfNegotiatedTimersEntry."
        AUGMENTS {
            rcIpBgpTmpPeerAfEntry
        }
        ::= { rcIpBgpTmpPeerAfNegotiatedTimersTable 1 }

    RcIpBgpTmpPeerAfNegotiatedTimersEntry ::= SEQUENCE {
        rcIpBgpTmpPeerAfHoldTime
            Unsigned32,
        rcIpBgpTmpPeerAfKeepAlive
            Unsigned32
    }

    rcIpBgpTmpPeerAfHoldTime OBJECT-TYPE
        SYNTAX     Unsigned32 ( 0 | 3..65535 )
        UNITS      "seconds"
        MAX-ACCESS read-only
        STATUS     current
        DESCRIPTION
            "The value of this object is calculated by this BGP
             Speaker as being;

             zero (0) - if this was the value sent by the peer and
             this value is permitted by this BGP Speaker. In this
             case, no keepalive messages are sent and the Hold Timer
             is not set.

             At least three (3). This value is the smaller of
             the value sent by this peer in the OPEN message and
             rcIpBgpTmpPeerAfHoldTimeConfigured for this peer.

             This value is only defined when the peering session is
             in the Established state."
        REFERENCE
            "RFC 4271, Section 4.2."
        ::= { rcIpBgpTmpPeerAfNegotiatedTimersEntry 1 }

    rcIpBgpTmpPeerAfKeepAlive OBJECT-TYPE
        SYNTAX     Unsigned32 ( 0 | 1..21845 )
        UNITS      "seconds"
        MAX-ACCESS read-only
        STATUS     current
        DESCRIPTION
            "Time interval in seconds for the KeepAlive timer
             established with the peer. The value of this object
             is calculated by this BGP speaker such that, when
             compared with rcIpBgpTmpPeerAfHoldTime, it has the same
             proportion as what rcIpBgpTmpPeerAfKeepAliveConfigured has
             when compared with rcIpBgpTmpPeerAfHoldTimeConfigured. If
             the value of this object is zero (0), it indicates
             that the KeepAlive timer has not been established
             with the peer, or, the value of
             rcIpBgpTmpPeerAfKeepAliveConfigured is zero (0).

             This value is only defined when the peering session is
             in the Established state."
        REFERENCE
            "RFC 4271, Section 4.4."
        ::= { rcIpBgpTmpPeerAfNegotiatedTimersEntry 2 }

    --
    -- Per-peer counters
    --

    rcIpBgpTmpPeerAfCounters
        OBJECT IDENTIFIER ::= { rcIpBgpTmpPeerAf 4 }

    rcIpBgpTmpPeerAfCountersTable OBJECT-TYPE
        SYNTAX     SEQUENCE OF RcIpBgpTmpPeerAfCountersEntry
        MAX-ACCESS not-accessible
        STATUS     current
        DESCRIPTION
            "The counters associated with a BGP Peer."
        ::= { rcIpBgpTmpPeerAfCounters 1 }

    rcIpBgpTmpPeerAfCountersEntry OBJECT-TYPE
        SYNTAX     RcIpBgpTmpPeerAfCountersEntry
        MAX-ACCESS not-accessible
        STATUS     current
        DESCRIPTION
            "Each entry contains counters of message transmissions
             and FSM transitions for a given BGP Peering session."
        AUGMENTS {
            rcIpBgpTmpPeerAfEntry
        }
        ::= { rcIpBgpTmpPeerAfCountersTable 1 }

    RcIpBgpTmpPeerAfCountersEntry ::= SEQUENCE {
        rcIpBgpTmpPeerAfInUpdates
            Counter32,
        rcIpBgpTmpPeerAfOutUpdates
            Counter32,
        rcIpBgpTmpPeerAfInTotalMessages
            Counter32,
        rcIpBgpTmpPeerAfOutTotalMessages
            Counter32,
        rcIpBgpTmpPeerAfFsmEstablishedTransitions
            Counter32
    }

    rcIpBgpTmpPeerAfInUpdates OBJECT-TYPE
        SYNTAX     Counter32
        MAX-ACCESS read-only
        STATUS     current
        DESCRIPTION
            "The number of BGP UPDATE messages received on this
             connection."
        ::= { rcIpBgpTmpPeerAfCountersEntry 1 }

    rcIpBgpTmpPeerAfOutUpdates OBJECT-TYPE
        SYNTAX     Counter32
        MAX-ACCESS read-only
        STATUS     current
        DESCRIPTION
            "The number of BGP UPDATE messages transmitted on this
             connection."
        ::= { rcIpBgpTmpPeerAfCountersEntry 2 }

    rcIpBgpTmpPeerAfInTotalMessages OBJECT-TYPE
        SYNTAX     Counter32
        MAX-ACCESS read-only
        STATUS     current
        DESCRIPTION
            "The total number of messages received from the remote
             peer on this connection."
        ::= { rcIpBgpTmpPeerAfCountersEntry 3 }

    rcIpBgpTmpPeerAfOutTotalMessages OBJECT-TYPE
        SYNTAX     Counter32
        MAX-ACCESS read-only
        STATUS     current
        DESCRIPTION
            "The total number of messages transmitted to the remote
             peer on this connection."
        ::= { rcIpBgpTmpPeerAfCountersEntry 4 }

    rcIpBgpTmpPeerAfFsmEstablishedTransitions OBJECT-TYPE
        SYNTAX     Counter32
        MAX-ACCESS read-only
        STATUS     current
        DESCRIPTION
            "The total number of times the BGP FSM transitioned into
             the established state for this peer."
        ::= { rcIpBgpTmpPeerAfCountersEntry 5 }

    --
    -- BGP NLRI Data
    --

    rcIpBgpTmpRib
        OBJECT IDENTIFIER ::= { rcIpBgpTmp 11 }

    --
    -- NLRI Table
    --

    rcIpBgpTmpNlriTable OBJECT-TYPE
        SYNTAX     SEQUENCE OF RcIpBgpTmpNlriEntry
        MAX-ACCESS not-accessible
        STATUS     current
        DESCRIPTION
            "The BGP-4 Received Path Attribute Table contains
             information about paths to destination networks
             received from all BGP4 peers. Collectively, this
             represents the Adj-Ribs-In. The route where
             rcIpBgpTmpNlriBest is true represents, for this NLRI,
             the route that is installed in the LocRib from the
             Adj-Ribs-In."
        REFERENCE
            "RFC 4271, Sections 3.2 and 9."
        ::= { rcIpBgpTmpRib 1 }

    rcIpBgpTmpNlriEntry OBJECT-TYPE
        SYNTAX     RcIpBgpTmpNlriEntry
        MAX-ACCESS not-accessible
        STATUS     current
        DESCRIPTION
            "Information about a path to a network."
        INDEX {
            rcIpBgpTmpNlriAfi,
            rcIpBgpTmpNlriSafi,
            rcIpBgpTmpNlriPrefix,
            rcIpBgpTmpNlriPrefixLen,
            rcIpBgpTmpNlriIndex,
            rcIpBgpTmpPeerAfInstance,
            rcIpBgpTmpPeerAfLocalAddrType,
            rcIpBgpTmpPeerAfLocalAddr,
            rcIpBgpTmpPeerAfRemoteAddrType,
            rcIpBgpTmpPeerAfRemoteAddr
        }
        ::= { rcIpBgpTmpNlriTable 1 }

    RcIpBgpTmpNlriEntry ::= SEQUENCE {
        rcIpBgpTmpNlriIndex
            Unsigned32,
        rcIpBgpTmpNlriAfi
            RcIpBgpTmpAddressFamilyIdentifierTC,
        rcIpBgpTmpNlriSafi
            RcIpBgpTmpSubsequentAddressFamilyIdentifierTC,
        rcIpBgpTmpNlriPrefixType
            InetAddressType,
        rcIpBgpTmpNlriPrefix
            InetAddress,
        rcIpBgpTmpNlriPrefixLen
            InetAddressPrefixLength,
        rcIpBgpTmpNlriBest
            TruthValue,
        rcIpBgpTmpNlriCalcLocalPref
            Unsigned32,
        rcIpBgpTmpAfPathAttrIndex
            Unsigned32,
        rcIpBgpTmpAfPathAttrUnknownIndex    -- not supported
            Unsigned32
    }

    rcIpBgpTmpNlriIndex OBJECT-TYPE
        SYNTAX     Unsigned32
        MAX-ACCESS not-accessible
        STATUS     current
        DESCRIPTION
            "This index allows for multiple instances of a base
             prefix for a certain AFI-SAFI from a given peer.
             This is currently useful for two things:
             1. Allowing for a peer in future implementations to
                send more than a single route instance.
             2. Allow for extensions which extend the NLRI field
                to send the same prefix while utilizing other
                extension specific information. An example of
                this is RFC 3107 - Carrying MPLS labels in BGP."
        REFERENCE
            "RFC 3107 - Carrying Label Information in BGP-4."
        ::= { rcIpBgpTmpNlriEntry 1 }

    rcIpBgpTmpNlriAfi OBJECT-TYPE
        SYNTAX     RcIpBgpTmpAddressFamilyIdentifierTC
        MAX-ACCESS not-accessible
        STATUS     current
        DESCRIPTION
            "The address family of the prefix for this NLRI.

             Note that the AFI is not necessarily equivalent to
             the an InetAddressType."
        REFERENCE
            "RFC 4760 - Multiprotocol Extensions for BGP-4"
        ::= { rcIpBgpTmpNlriEntry 2 }

    rcIpBgpTmpNlriSafi OBJECT-TYPE
        SYNTAX     RcIpBgpTmpSubsequentAddressFamilyIdentifierTC
        MAX-ACCESS not-accessible
        STATUS     current
        DESCRIPTION
            "The subsequent address family of the prefix for
             this NLRI"
        REFERENCE
            "RFC 4760 - Multiprotocol Extensions for BGP-4"
        ::= { rcIpBgpTmpNlriEntry 3 }

    rcIpBgpTmpNlriPrefixType OBJECT-TYPE
        SYNTAX     InetAddressType
        MAX-ACCESS read-only
        STATUS     current
        DESCRIPTION
            "The type of the IP address prefix in the
             Network Layer Reachability Information field.
             The value of this object is derived from the
             appropriate value from the rcIpBgpTmpNlriAfi field.
             Where an appropriate InetAddressType is not
             available, the value of the object must be
             unknown(0)."
        ::= { rcIpBgpTmpNlriEntry 4 }

    rcIpBgpTmpNlriPrefix OBJECT-TYPE
        SYNTAX     InetAddress
        MAX-ACCESS not-accessible
        STATUS     current
        DESCRIPTION
            "An IP address prefix in the Network Layer
             Reachability Information field. This object
             is an IP address containing the prefix with
             length specified by
             rcIpBgpTmpAfPathAttrAddrPrefixLen.
             Any bits beyond the length specified by
             rcIpBgpTmpAfPathAttrAddrPrefixLen are zeroed."
        REFERENCE
            "RFC 4271, Section 4.3."
        ::= { rcIpBgpTmpNlriEntry 5 }

    rcIpBgpTmpNlriPrefixLen OBJECT-TYPE
        SYNTAX     InetAddressPrefixLength
        MAX-ACCESS not-accessible
        STATUS     current
        DESCRIPTION
            "Length in bits of the address prefix in
             the Network Layer Reachability Information field."
        ::= { rcIpBgpTmpNlriEntry 6 }

    rcIpBgpTmpNlriBest OBJECT-TYPE
        SYNTAX     TruthValue
        MAX-ACCESS read-only
        STATUS     current
        DESCRIPTION
            "An indication of whether or not this route
             was chosen as the best BGP4 route for this
             destination."
        REFERENCE
            "RFC 4271, Section 9.1.2."
        ::= { rcIpBgpTmpNlriEntry 7 }

    rcIpBgpTmpNlriCalcLocalPref OBJECT-TYPE
        SYNTAX     Unsigned32
        MAX-ACCESS read-only
        STATUS     current
        DESCRIPTION
            "The degree of preference calculated by the
             receiving BGP4 speaker for an advertised
             route.

             In the case where this prefix is ineligible, this
             object will be absent."
        REFERENCE
            "RFC 4271, Section 9.1.1"
        ::= { rcIpBgpTmpNlriEntry 8 }

    rcIpBgpTmpAfPathAttrIndex OBJECT-TYPE
        SYNTAX     Unsigned32
        MAX-ACCESS read-only
        STATUS     current
        DESCRIPTION
            "This value is a unique index for entries in the
             rcIpBgpTmpAfPathAttrTable. It is assigned by the agent at the
             point of creation of the rcIpBgpTmpAfPathAttrTable row entry.
             While its value is guaranteed to be unique at any time,
             it is otherwise opaque to the management application
             with respect to its value or the contiguity of
             rcIpBgpTmpAfPathAttrIndex row instance values across rows of the
             rcIpBgpTmpAfPathAttrTable.

             Note well that this index is used to distinguish unique
             sets of Path Attributes sent as part of BGP NLRI.  The
             implementor is thus encouraged to make this index unique
             per set of all received path attributes.  This value may
             be used to index tables in extension MIBs that share the
             property of belonging to the same received Path Attribute
             tuple."
        ::= { rcIpBgpTmpNlriEntry 9 }

    rcIpBgpTmpAfPathAttrUnknownIndex OBJECT-TYPE  -- not supported
        SYNTAX     Unsigned32
        MAX-ACCESS read-only
        STATUS     current
        DESCRIPTION
            "This value is a unique index for entries in the
             rcIpBgpTmpAfPathAttrUnknownTable. It is assigned by the agent at
             the point of creation of the rcIpBgpTmpAfPathAttrUnknownTable row
             entry.  While its value is guaranteed to be unique at
             any time, it is otherwise opaque to the management
             application with respect to its value or the contiguity
             of rcIpBgpTmpAfPathAttrUnknownIndex row instance values across
             rows of the rcIpBgpTmpAfPathAttrUnknownTable."
        ::= { rcIpBgpTmpNlriEntry 10 }

    --
    -- Path Attribute Counter
    --

    rcIpBgpTmpAfPathAttrCounter OBJECT-TYPE
        SYNTAX     Counter32
        MAX-ACCESS read-only
        STATUS     current
        DESCRIPTION
            "The number of entries in the rcIpBgpTmpAfPathAttrTable."
        ::= { rcIpBgpTmpRib 3 }

    --
    -- Path Attributes Table
    --

    rcIpBgpTmpAfPathAttrTable OBJECT-TYPE
        SYNTAX     SEQUENCE OF RcIpBgpTmpAfPathAttrEntry
        MAX-ACCESS not-accessible
        STATUS     current
        DESCRIPTION
            "Provides per advertised network-prefix attribute data,
             as advertised over a peering session."
        ::= { rcIpBgpTmpRib 4 }

    rcIpBgpTmpAfPathAttrEntry OBJECT-TYPE
        SYNTAX     RcIpBgpTmpAfPathAttrEntry
        MAX-ACCESS not-accessible
        STATUS     current
        DESCRIPTION
            "Each entry contains data about path attributes
             associated with a given prefix in the rcIpBgpTmpNlriTable."
        REFERENCE
             "RFC 4271, Section 5."
        INDEX {
            rcIpBgpTmpAfPathAttrIndex
        }
        ::= { rcIpBgpTmpAfPathAttrTable 1 }

    RcIpBgpTmpAfPathAttrEntry ::= SEQUENCE {
        rcIpBgpTmpAfPathAttrOrigin
            INTEGER,
        rcIpBgpTmpAfPathAttrNextHopAddrType
            InetAddressType,
        rcIpBgpTmpAfPathAttrNextHopAddr
            InetAddress,
        rcIpBgpTmpAfPathAttrLinkLocalNextHopAddrType
            InetAddressType,
        rcIpBgpTmpAfPathAttrLinkLocalNextHopAddr
            InetAddress,
        rcIpBgpTmpAfPathAttrMedPresent
            TruthValue,
        rcIpBgpTmpAfPathAttrMed
            Unsigned32,
        rcIpBgpTmpAfPathAttrLocalPref
            Unsigned32,
        rcIpBgpTmpAfPathAttrAtomicAggregate
            INTEGER,
        rcIpBgpTmpAfPathAttrAggregatorAS
            InetAutonomousSystemNumber,
        rcIpBgpTmpAfPathAttrAggregatorAddr
            RcIpBgpTmpIdentifierTC,
        rcIpBgpTmpAsPathCalcLength
            Unsigned32,
        rcIpBgpTmpAsPathIndex -- not supported
            Unsigned32,
        rcIpBgpTmpAsPathString
            SnmpAdminString
    }

    rcIpBgpTmpAfPathAttrOrigin OBJECT-TYPE
        SYNTAX     INTEGER {
            igp(1),-- networks are interior
            egp(2),-- networks learned via the EGP protocol
            incomplete(3) -- networks that
                          -- are learned by some other
                          -- means
            }
        MAX-ACCESS read-only
        STATUS     current
        DESCRIPTION
            "The ultimate origin of the path information."
        REFERENCE
            "RFC 4271, Section 4.3.
             RFC 4271, Section 5.1.1."
        ::= { rcIpBgpTmpAfPathAttrEntry 1 }

    rcIpBgpTmpAfPathAttrNextHopAddrType OBJECT-TYPE
        SYNTAX     InetAddressType
        MAX-ACCESS read-only
        STATUS     current
        DESCRIPTION
            "The address family of the address for
             the border router that should be used
             to access the destination network."
        ::= { rcIpBgpTmpAfPathAttrEntry 2 }

    rcIpBgpTmpAfPathAttrNextHopAddr OBJECT-TYPE
        SYNTAX     InetAddress (SIZE(4..20))
        MAX-ACCESS read-only
        STATUS     current
        DESCRIPTION
            "The address of the border router that
             should be used to access the destination
             network. This address is the nexthop
             address received in the UPDATE packet associated with
             this prefix.

             Note that for RFC2545 style double nexthops,
             this object will always contain the global scope
             nexthop. bgpPathAttrLinkLocalNextHop will contain
             the linklocal scope nexthop, if it is present.

             In the case a mechanism is developed to use only a link
             local nexthop, rcIpBgpTmpAfPathAttrNextHopAddr will contain the
             link local nexthop."
        REFERENCE
            "RFC 4271, Section 4.3,
             RFC 4271, Section 5.1.3,
             RFC 2545, Section 3."
        ::= { rcIpBgpTmpAfPathAttrEntry 3 }

    rcIpBgpTmpAfPathAttrLinkLocalNextHopAddrType OBJECT-TYPE
        SYNTAX     InetAddressType
        MAX-ACCESS read-only
        STATUS     current
        DESCRIPTION
            "The address type for IPv6 link local addresses.
             This is present only when receiving RFC 2545
             style double nexthops.

             This object is optionally present in BGP
             implementations that do not support IPv6."
        REFERENCE
            "RFC 2545, Section 3."
        ::= { rcIpBgpTmpAfPathAttrEntry 4 }

    rcIpBgpTmpAfPathAttrLinkLocalNextHopAddr OBJECT-TYPE
        SYNTAX     InetAddress
        MAX-ACCESS read-only
        STATUS     current
        DESCRIPTION
            "This value contains an IPv6 link local address
             and is present only when receiving RFC 2545 style
             double nexthops.

             This object is optionally present in BGP
             implementations that do not support IPv6."
        REFERENCE
            "RFC 2545, Section 3."
        ::= { rcIpBgpTmpAfPathAttrEntry 5 }

    rcIpBgpTmpAfPathAttrMedPresent OBJECT-TYPE
        SYNTAX     TruthValue
        MAX-ACCESS read-only
        STATUS     current
        DESCRIPTION
            "This value is true when the MED value was sent in
             the UPDATE message."
        ::= { rcIpBgpTmpAfPathAttrEntry 6 }

    rcIpBgpTmpAfPathAttrMed OBJECT-TYPE
        SYNTAX     Unsigned32
        MAX-ACCESS read-only
        STATUS     current
        DESCRIPTION
            "This metric is used to discriminate between multiple
             exit points to an adjacent autonomous system.  When the MED
             value is absent but has a calculated default value, this
             object will contain the calculated value."
        REFERENCE
            "RFC 4271, Section 4.3.
             RFC 4271, Section 5.1.4."
        ::= { rcIpBgpTmpAfPathAttrEntry 7 }

    rcIpBgpTmpAfPathAttrLocalPref OBJECT-TYPE
        SYNTAX     Unsigned32
        MAX-ACCESS read-only
        STATUS     current
        DESCRIPTION
            "The originating BGP4 speakers degree of preference for an
             advertised route.  If the route was not sent with a LOCAL_PREF
             value, this object will be absent."
        REFERENCE
            "RFC 4271, Section 4.3.
             RFC 4271, Section 5.1.5."
        ::= { rcIpBgpTmpAfPathAttrEntry 8 }

    rcIpBgpTmpAfPathAttrAtomicAggregate OBJECT-TYPE
        SYNTAX     INTEGER {
            atomicAggregatePresent(1),
            atomicAggregateMissing(2)
            }
        MAX-ACCESS read-only
        STATUS     current
        DESCRIPTION
            "When this object is set to atomicAggregatePresent,
             the ATOMIC_AGGREGATE Path Attribute is present and
             indicates that the NLRI MUST NOT be made more
             specific."
        REFERENCE
            "RFC 4271, Sections 5.1.6 and 9.1.4."
        ::= { rcIpBgpTmpAfPathAttrEntry 9 }

    rcIpBgpTmpAfPathAttrAggregatorAS OBJECT-TYPE
        SYNTAX     InetAutonomousSystemNumber
        MAX-ACCESS read-only
        STATUS     current
        DESCRIPTION
            "The AS number of the last BGP4 speaker that performed route
             aggregation. If the AGGREGATOR path attribute is absent, this
             object will not be present in the conceptual row."
        REFERENCE
            "RFC 4271, Section 5.1.7.
             RFC 4271, Section 9.2.2.2."
        ::= { rcIpBgpTmpAfPathAttrEntry 10 }

    rcIpBgpTmpAfPathAttrAggregatorAddr OBJECT-TYPE
        SYNTAX     RcIpBgpTmpIdentifierTC
        MAX-ACCESS read-only
        STATUS     current
        DESCRIPTION
            "The IP address of the last BGP4 speaker that performed route
             aggregation.  If the AGGREGATOR path attribute is absent, this
             object will not be present in the conceptual row."
        REFERENCE
            "RFC 4271, Section 5.1.7.
             RFC 4271, Section 9.2.2.2."
        ::= { rcIpBgpTmpAfPathAttrEntry 11 }

    rcIpBgpTmpAsPathCalcLength OBJECT-TYPE
        SYNTAX     Unsigned32
        MAX-ACCESS read-only
        STATUS     current
        DESCRIPTION
            "This value represents the calculated length of the
             AS Path according to the rules of the BGP
             specification.  This value is used in route selection."
        REFERENCE
            "RFC 4271, Section 9.1.2.2.a"
        ::= { rcIpBgpTmpAfPathAttrEntry 12 }

    rcIpBgpTmpAsPathIndex OBJECT-TYPE    -- not supported
        SYNTAX     Unsigned32
        MAX-ACCESS read-only
        STATUS     current
        DESCRIPTION
            "This value is a unique index for the decomposed AS Path
             in the rcIpBgpTmpAsPathTable. It is assigned by the
             agent at the point of creation of the rcIpBgpTmpAsPathTable
             row entry. While its value is guaranteed to be unique
             at any time, it is otherwise opaque to the management
             application with respect to its value or the contiguity
             of rcIpBgpTmpAsPathIndex row instance values across rows
             of the rcIpBgpTmpAsPathTable."
        ::= { rcIpBgpTmpAfPathAttrEntry 13 }

    rcIpBgpTmpAsPathString OBJECT-TYPE
        SYNTAX     SnmpAdminString
        MAX-ACCESS read-only
        STATUS     current
        DESCRIPTION
            "This is a string depicting the autonomous system
             path to this network which was received from the
             peer which advertised it. The format of the string
             is implementation-dependent, and should be designed
             for operator readability.

             Note that SnmpAdminString is only capable of
             representing a maximum of 255 characters.  This may
             lead to the string being truncated in the presence of
             a large AS Path.  The rcIpBgpTmpAsPathTable will give access
             to the full AS Path."
        ::= { rcIpBgpTmpAfPathAttrEntry 14 }

    --
    -- Mount point for extensions
    --

    rcIpBgpTmpExtensions OBJECT IDENTIFIER ::= { rcIpBgpTmp 12 }

    --
    -- Notifications
    --

    rcIpBgpTmpNotification OBJECT IDENTIFIER ::= { rcIpBgpTmp 0 }

    rcIpBgpTmpEstablishedNotification NOTIFICATION-TYPE
        OBJECTS { bgpPeerRemoteAddr,
                  bgpPeerLastError,
                  bgpPeerState      }
        STATUS  deprecated
        DESCRIPTION
                "The rcIpBgpTmpEstablishedNotification event is generated
                 when the BGP FSM enters the established state.

                 This Notification replaces the bgpEstablished
                 Notification and has been replaced by
                 rcIpBgpTmpAfEstablishedNotification."
        ::= { rcIpBgpTmpNotification 1 }

    rcIpBgpTmpBackwardTransNotification NOTIFICATION-TYPE
        OBJECTS { bgpPeerRemoteAddr,
                  bgpPeerLastError,
                  bgpPeerState      }
        STATUS  deprecated
        DESCRIPTION
                "The rcIpBgpBackwardTransNotification event is
                 generated when the BGP FSM moves from a higher
                 numbered state to a lower numbered state.

                 This Notification replaces the
                 bgpBackwardsTransition Notification and has
                 been replaced by rcIpBgpTmpAfBackwardsNotification."
        ::= { rcIpBgpTmpNotification 2 }

    rcIpBgpTmpAfEstablishedNotification NOTIFICATION-TYPE
        OBJECTS {
            rcIpBgpTmpPeerAfPeerState,
            rcIpBgpTmpPeerAfLocalPort,
            rcIpBgpTmpPeerAfRemotePort
        }
        STATUS current
        DESCRIPTION
            "The BGP Established event is generated when
             the BGP FSM enters the established state."
        ::= { rcIpBgpTmpNotification 3 }

    rcIpBgpTmpAfBackwardTransitionNotification NOTIFICATION-TYPE
        OBJECTS {
            rcIpBgpTmpPeerAfPeerState,
            rcIpBgpTmpPeerAfLocalPort,
            rcIpBgpTmpPeerAfRemotePort,
            rcIpBgpTmpPeerAfLastErrorCodeReceived,
            rcIpBgpTmpPeerAfLastErrorSubCodeReceived,
            rcIpBgpTmpPeerAfLastErrorReceivedText
        }
        STATUS current
        DESCRIPTION
            "The BGPBackwardTransition Event is generated
             when the BGP FSM moves from a higher numbered
             state to a lower numbered state.

             Due to the nature of the BGP state machine, an implementation MAY
             rate limit the generation of this event.  An implementation MAY
             also generate this notification ONLY when the state machine moves
             out of the established state.  An implementation should document
             its specific behavior."
        ::= { rcIpBgpTmpNotification 4 }


--IP Static Route (new)

rcIpInterVrfStaticRoute OBJECT IDENTIFIER       ::= { rcIp 103}

rcIpInterVrfStaticRouteTableSize OBJECT-TYPE
        SYNTAX        Integer32
        MAX-ACCESS    read-only
        STATUS        current
        DESCRIPTION   "size of Ip Static Route Table."
        ::= { rcIpInterVrfStaticRoute 1 }

rcIpInterVrfStaticRouteTable OBJECT-TYPE
        SYNTAX          SEQUENCE OF RcIpInterVrfStaticRouteEntry
        MAX-ACCESS      not-accessible
        STATUS          current
        DESCRIPTION     "This table is used to add static IP routes to
                        the device.  Routes added into this table will
                        automatically show-up in the 'rcIpRouteTable'
                        when the device is actively using the route
                        to forward IP traffic."
    ::= { rcIpInterVrfStaticRoute 2 }

rcIpInterVrfStaticRouteEntry OBJECT-TYPE
        SYNTAX          RcIpInterVrfStaticRouteEntry
        MAX-ACCESS              not-accessible
        STATUS          current
        DESCRIPTION     "A static route to a particular destination."
        INDEX           { rcIpInterVrfStaticRouteOwnerVrfId,
                          rcIpInterVrfStaticRouteDest,
                          rcIpInterVrfStaticRouteMask,
                          rcIpInterVrfStaticRouteNextHop }
        ::= { rcIpInterVrfStaticRouteTable 1 }

RcIpInterVrfStaticRouteEntry ::=
        SEQUENCE {
                rcIpInterVrfStaticRouteOwnerVrfId     VrfIdentifier, 
                rcIpInterVrfStaticRouteDest           IpAddress,
                rcIpInterVrfStaticRouteMask           IpAddress,
                rcIpInterVrfStaticRouteNextHop        IpAddress,
                rcIpInterVrfStaticRouteMetric         INTEGER,
                rcIpInterVrfStaticRouteIfIndex        InterfaceIndex,
                rcIpInterVrfStaticRoutePreference     INTEGER,
                rcIpInterVrfStaticRouteEnable         TruthValue,
                rcIpInterVrfStaticRouteStatus         INTEGER,
                rcIpInterVrfStaticRouteRowStatus      RowStatus,
                rcIpInterVrfStaticRouteLocalNextHop   TruthValue,
                rcIpInterVrfStaticRouteNextHopVrfId   VrfIdentifier

        }

rcIpInterVrfStaticRouteOwnerVrfId OBJECT-TYPE
        SYNTAX        VrfIdentifier
        MAX-ACCESS    not-accessible
        STATUS        current
        DESCRIPTION   "Owner VRF id of the static route"
        ::= { rcIpInterVrfStaticRouteEntry 1 }
 
rcIpInterVrfStaticRouteDest OBJECT-TYPE
        SYNTAX          IpAddress
        MAX-ACCESS      not-accessible 
        STATUS          current
        DESCRIPTION     "The destination IP address of this route.  An
                        entry with a value of 0.0.0.0 is considered a
                        default route.  Multiple routes to a single
                        destination can appear in the table, but access to
                        such multiple entries is dependent on the table-
                        access mechanisms defined by the network
                        management protocol in use."
        ::= { rcIpInterVrfStaticRouteEntry 2 }

rcIpInterVrfStaticRouteMask OBJECT-TYPE
        SYNTAX          IpAddress
        MAX-ACCESS      not-accessible        
        STATUS          current
        DESCRIPTION     "Indicate the mask to be logical-ANDed with the
                        destination address before being compared to the
                        value in the rcIpRouteDest field.  For those systems
                        that do not support arbitrary subnet masks, an
                        agent constructs the value of the rcIpRouteMask by
                        determining whether the value of the correspondent
                        rcIpRouteDest field belong to a class-A, B, or C
                        network, and then using one of:

                           mask           network
                           255.0.0.0      class-A
                           255.255.0.0    class-B
                           255.255.255.0  class-C

                        If the value of the rcIpRouteDest is 0.0.0.0 (a
                        default route), then the mask value is also
                        0.0.0.0.  It should be noted that all IP routing
                        subsystems implicitly use this mechanism."
        ::= { rcIpInterVrfStaticRouteEntry 3 }

rcIpInterVrfStaticRouteNextHop OBJECT-TYPE
        SYNTAX          IpAddress
        MAX-ACCESS      not-accessible        
        STATUS          current
        DESCRIPTION     "The IP address of the next hop of this route.
                        (In the case of a route bound to an interface
                        which is realized via a broadcast media, the value
                        of this field is the agent's IP address on that
                        interface)."
        ::= { rcIpInterVrfStaticRouteEntry 4 }


rcIpInterVrfStaticRouteMetric OBJECT-TYPE
        SYNTAX          INTEGER (1..'FFFF'h)
        MAX-ACCESS              read-write
        STATUS          current
        DESCRIPTION     "The primary routing metric for this route.  The
                        semantics of this metric are determined by the
                        routing-protocol specified in the route's
                        rcIpRouteProto value.  If this metric is not used,
                        its value should be set to -1."
        DEFVAL          { 1 }
        ::= { rcIpInterVrfStaticRouteEntry 5 }

rcIpInterVrfStaticRouteIfIndex OBJECT-TYPE
        SYNTAX          InterfaceIndex (0..65535)
        MAX-ACCESS              read-only
        STATUS          current
        DESCRIPTION     "The index value which uniquely identifies the
                        local interface through which the next hop of this
                        route should be reached.  The interface identified
                        by a particular value of this index is the same
                        interface as identified by the same value of
                        ifIndex."
        ::= { rcIpInterVrfStaticRouteEntry 6 }

rcIpInterVrfStaticRoutePreference OBJECT-TYPE
        SYNTAX          INTEGER (1..255)
        MAX-ACCESS              read-write
        STATUS          current
        DESCRIPTION     "Used to indicate the route preference of this
                        entry.  If there are more than one route that can
                        be used to forward IP traffic, the route that has
                        a highest preference will be used instead of a
                        lower preference one. The higher the number, the higher the preference."
        ::= { rcIpInterVrfStaticRouteEntry 7 }

rcIpInterVrfStaticRouteEnable OBJECT-TYPE
        SYNTAX          TruthValue
        MAX-ACCESS              read-write
        STATUS          current
        DESCRIPTION     "Used to enable/disable this entry."
        DEFVAL        { true }
        ::= { rcIpInterVrfStaticRouteEntry 8 }

rcIpInterVrfStaticRouteStatus OBJECT-TYPE
        SYNTAX          INTEGER {
                                inactive(0),
                                active(1)
                        }
        MAX-ACCESS              read-only
        STATUS          current
        DESCRIPTION     "Used to indicate the current status of
                        this entry."
        DEFVAL          { active }
        ::= { rcIpInterVrfStaticRouteEntry 9 }


rcIpInterVrfStaticRouteRowStatus OBJECT-TYPE
        SYNTAX          RowStatus
        MAX-ACCESS      read-write
        STATUS          current
        DESCRIPTION     "Used to create/delete entries"
        ::= { rcIpInterVrfStaticRouteEntry 10 }

rcIpInterVrfStaticRouteLocalNextHop OBJECT-TYPE
        SYNTAX          TruthValue
        MAX-ACCESS      read-write
        STATUS          current
        DESCRIPTION     "Used to enable/disable this entry. True indicate that the
                         static route becomes active only if switch has a local route
                         to the network. False indicates that the static route becomes
                         active if switch has a local route or dynamic route."
        DEFVAL        { true }
        ::= { rcIpInterVrfStaticRouteEntry 11 }

rcIpInterVrfStaticRouteNextHopVrfId OBJECT-TYPE
        SYNTAX          VrfIdentifier
        MAX-ACCESS      read-write
        STATUS          current
        DESCRIPTION     "Used to indicate nhVrfId in inter-VRF static-route configuration"
        ::= { rcIpInterVrfStaticRouteEntry 12 }

-- IP Mcast Square Smlt

rcIpMulticastSquareSmlt  OBJECT IDENTIFIER ::= { rcIp 109 }

rcIpMulticastSquareSmltEnable OBJECT-TYPE
        SYNTAX        TruthValue
        MAX-ACCESS    read-write
        STATUS        current
        DESCRIPTION   "Enable/Disable multicast Square Smlt."
        DEFVAL { false }
        ::= { rcIpMulticastSquareSmlt 1 }
 
-- ARP Group

rcArpExtLifeTime OBJECT-TYPE
        SYNTAX        Integer32
        MAX-ACCESS    read-write
        STATUS        current
        DESCRIPTION   "The lifetime in minutues of an ARP entry within the 
                      system."
        ::= { rcArp 1 }

rcArpExtTable OBJECT-TYPE
        SYNTAX        SEQUENCE OF RcArpExtEntry
        MAX-ACCESS    not-accessible
        STATUS        current
        DESCRIPTION   "ARP extension table.  This table augments the
		      standard ipNetToMediaTable defined in RFC1213."
        ::= { rcArp 2 }

rcArpExtEntry OBJECT-TYPE
        SYNTAX        RcArpExtEntry
        MAX-ACCESS    not-accessible
        STATUS        current
        DESCRIPTION   "Entry containing Proprietary ARP information.  
                      An entry is automatically created in this table 
                      when an ip address is configured on an interface." 
        INDEX         { rcArpExtEntIfIndex }
        ::= { rcArpExtTable 1 }

RcArpExtEntry ::=
        SEQUENCE {
                rcArpExtEntIfIndex InterfaceIndex,
                rcArpExtEntDoProxy INTEGER,
                rcArpExtEntDoResp INTEGER,
                rcArpExtEntDoFlood INTEGER
        }

rcArpExtEntIfIndex OBJECT-TYPE
        SYNTAX        InterfaceIndex
        MAX-ACCESS    read-only
        STATUS        current
        DESCRIPTION   "The index value which uniquely identifies the
                      interface to which this entry is applicable.
                      The interface identified by a particular value
                      of this index is the same interface as 
                      identified by the same value of ifIndex."
        ::= { rcArpExtEntry 1 }
 
rcArpExtEntDoProxy OBJECT-TYPE
        SYNTAX        INTEGER {
		         disable(1),
			 enable(2)
		      }
        MAX-ACCESS    read-write
        STATUS        current
        DESCRIPTION   "Enable or disable ARP proxy responses on the
		      specified interface."
	DEFVAL        { disable }
        ::= { rcArpExtEntry 2 }
 
rcArpExtEntDoResp OBJECT-TYPE
        SYNTAX        INTEGER {
			 disable(1),
			 enable(2)
		      }
        MAX-ACCESS    read-write
        STATUS        current
        DESCRIPTION   "Enable or disable the sending of ARP responses
		      on the specified interface."
	DEFVAL        { enable }
        ::= { rcArpExtEntry 3 }

rcArpExtEntDoFlood OBJECT-TYPE
        SYNTAX        INTEGER {
                         disable(1),
                         enable(2)
                      }
        MAX-ACCESS    read-write
        STATUS        current
        DESCRIPTION   "Enable or disable flooding of ARP responses for
                      NLBS Virtual Mac on the specified interface."
        DEFVAL        { disable }
        ::= { rcArpExtEntry 4 }


-- RIP Group

rcRipExtOperation OBJECT-TYPE
        SYNTAX        INTEGER	{
                         disable(1),
                         enable(2)
	 	      }
        MAX-ACCESS    read-write
        STATUS        current
        DESCRIPTION   "Enable or disable the operation of RIP on all
		      Interfaces."
        ::= { rcRip 1 }

rcRipExtUpdateTime OBJECT-TYPE
        SYNTAX        Integer32
        MAX-ACCESS    read-write
        STATUS        current
        DESCRIPTION   "The time between transmission of RIP updates
		      on all interfaces."
        ::= { rcRip 2 }

rcRipExtTable OBJECT-TYPE
        SYNTAX        SEQUENCE OF RcRipExtEntry
        MAX-ACCESS    not-accessible
        STATUS        current
        DESCRIPTION   "RIP extension table.  This table augments the
		      standard IfConfTable table in RFC1389."
        ::= { rcRip 3 }

rcRipExtEntry OBJECT-TYPE
        SYNTAX        RcRipExtEntry
        MAX-ACCESS    not-accessible
        STATUS        current
        DESCRIPTION   "Entry containing Proprietary RIP information.  
	  	      An entry is automatically created in this table 
                      when an ip address is configured on an interface."
        INDEX         { rcRipExtEntIfIndex }
        ::= { rcRipExtTable 1 }

RcRipExtEntry ::=
        SEQUENCE {
                rcRipExtEntIfIndex InterfaceIndex,
                rcRipExtEntTalk INTEGER,
                rcRipExtEntListen INTEGER,
                rcRipExtEntPoison INTEGER
        }

rcRipExtEntIfIndex OBJECT-TYPE
        SYNTAX        InterfaceIndex
        MAX-ACCESS    read-only
        STATUS        current
        DESCRIPTION   "The index value which uniquely identifies the
                      interface to which this entry is applicable.
                      The interface identified by a particular value
                      of this index is the same interface as 
                      identified by the same value of ifIndex."
        ::= { rcRipExtEntry 1 }
 
rcRipExtEntTalk OBJECT-TYPE
        SYNTAX       INTEGER {
                        disable(1),
                        enable(2)
		      }	
        MAX-ACCESS    read-write
        STATUS        current
        DESCRIPTION   "Enable or disable RIP transmission on the
		      specified interface."
	DEFVAL        { enable }
        ::= { rcRipExtEntry 2 }
 
rcRipExtEntListen OBJECT-TYPE
        SYNTAX        INTEGER {
                         disable(1),
                         enable(2)
		      }
        MAX-ACCESS    read-write
        STATUS        current
        DESCRIPTION   "Enable or disable RIP reception on the specified
		      interface."
	DEFVAL        { enable }
        ::= { rcRipExtEntry 3 }

rcRipExtEntPoison OBJECT-TYPE
        SYNTAX        INTEGER {
                         disable(1),
                         enable(2)
                      } 
        MAX-ACCESS    read-write
        STATUS        current
        DESCRIPTION   "Enable or disable operation of poison reverse
		      on the specified interface.  If poison is
		      disabled, split-horizon operation is enabled."
	DEFVAL        { disable }
        ::= { rcRipExtEntry 4 }


-- Test Group

rcTestExtTable OBJECT-TYPE
        SYNTAX        SEQUENCE OF RcTestEntry
        MAX-ACCESS    not-accessible
        STATUS        current
        DESCRIPTION   "Test extension table.  This table augments the
                      standard ifTestTable table in RFC1573."
        ::= { rcTest 1 }
 
rcTestEntry OBJECT-TYPE
        SYNTAX        RcTestEntry
        MAX-ACCESS    not-accessible
        STATUS        current    
        DESCRIPTION   "Proprietary test variables."
        INDEX         { rcTestExtIfIndex }
        ::= { rcTestExtTable 1 }
 
RcTestEntry ::=
        SEQUENCE {
                rcTestExtIfIndex InterfaceIndex,
                rcTestExtPassCount Integer32,  
                rcTestExtFailCount Integer32
        }
 
rcTestExtIfIndex OBJECT-TYPE
        SYNTAX        InterfaceIndex
        MAX-ACCESS    read-only
        STATUS        current
        DESCRIPTION   "The index value which uniquely identifies the
                      interface to which this entry is applicable.
                      The interface identified by a particular value
                      of this index is the same interface as
                      identified by the same value of ifIndex."
        ::= { rcTestEntry 1 }

rcTestExtPassCount OBJECT-TYPE
	SYNTAX	      Integer32
	MAX-ACCESS	  read-only
	STATUS	      current
	DESCRIPTION   "The number of iterations of the test case that
		      completed successfully."
	::= { rcTestEntry 2}

rcTestExtFailCount OBJECT-TYPE
        SYNTAX        Integer32
        MAX-ACCESS    read-only
        STATUS        current
        DESCRIPTION   "The number of iterations of the test case that
                      failed."
        ::= { rcTestEntry 3}


rcTestTypes		OBJECT IDENTIFIER	::= { rcTest 2}
rcTestTypesFabric	OBJECT IDENTIFIER	::= { rcTestTypes 1 }
rcTestTypesArTable	OBJECT IDENTIFIER	::= { rcTestTypes 2 }
rcTestTypesExtLoopBack	OBJECT IDENTIFIER	::= { rcTestTypes 3 }


rcTestCodes		OBJECT IDENTIFIER	::= { rcTest 3 }
rcTestCodesNoReceive	OBJECT IDENTIFIER	::= { rcTestCodes 1 }
rcTestCodesBadSeq	OBJECT IDENTIFIER	::= { rcTestCodes 2 }
rcTestCodesBadLen	OBJECT IDENTIFIER	::= { rcTestCodes 3 }
rcTestCodesBadData	OBJECT IDENTIFIER	::= { rcTestCodes 4 }


-- Statistics

rcStatTable OBJECT-TYPE
        SYNTAX        SEQUENCE OF RcStatEntry
        MAX-ACCESS    not-accessible
        STATUS        current
        DESCRIPTION   "A table used to store port statistics."
        ::= { rcStat 1 }
 
rcStatEntry OBJECT-TYPE
        SYNTAX        RcStatEntry
        MAX-ACCESS    not-accessible
        STATUS        current
        DESCRIPTION   "interface counters"
        INDEX         { rcStatPortIndex }
        ::= { rcStatTable 1 }
 
RcStatEntry ::= SEQUENCE {
                rcStatPortIndex            	InterfaceIndex,
                rcStatFrameTooShorts       	Counter32,
 		rcStatBridgeInUnicastFrames	Counter32,
 		rcStatBridgeInMulticastFrames	Counter32,
 		rcStatBridgeInBroadcastFrames	Counter32,
 		rcStatBridgeInDiscards		Counter32,
 		rcStatBridgeOutUnicastFrames	Counter32,
 		rcStatBridgeOutMulticastFrames	Counter32,
 		rcStatBridgeOutBroadcastFrames	Counter32,
 		rcStatRouteInUnicastFrames	Counter32,
 		rcStatRouteInMulticastFrames	Counter32,
 		rcStatRouteInDiscards		Counter32,
 		rcStatRouteOutUnicastFrames	Counter32,
 		rcStatRouteOutMulticastFrames 	Counter32,
		rcStatStgForwardTransitions     Counter32,
		rcStatStgInConfigBpdus          Counter32,
		rcStatStgInTcnBpdus             Counter32,
		rcStatStgInBadBpdus             Counter32,
		rcStatStgOutConfigBpdus         Counter32,
		rcStatStgOutTcnBpdus            Counter32,
		rcStatBridgeOutFrames           Counter32,
                rcStatPolicerTotalBytes         Counter64,
                rcStatPolicerTotalPkts          Counter64,
	 	rcStatPolicerGreenBytes		Counter64,
	 	rcStatPolicerYellowBytes	Counter64,
	 	rcStatPolicerRedBytes		Counter64
        }
 
rcStatPortIndex OBJECT-TYPE
        SYNTAX        InterfaceIndex
        MAX-ACCESS    read-only
        STATUS        current
        DESCRIPTION   "An index value that uniquely identifies a port.
                      This value is similar to ifIndex in MIB2."
        ::= { rcStatEntry 1 }
 
rcStatFrameTooShorts OBJECT-TYPE
        SYNTAX        Counter32
        MAX-ACCESS    read-only
        STATUS        current
        DESCRIPTION   "The total number of frames that are too short 
                      that were encountered on this interface."
        ::= { rcStatEntry 2 }

rcStatBridgeInUnicastFrames OBJECT-TYPE
        SYNTAX        Counter32
        MAX-ACCESS    read-only
        STATUS        current
        DESCRIPTION   "The total number of incoming unicast frames that 
		      were bridged."
        ::= { rcStatEntry 3 }

rcStatBridgeInMulticastFrames OBJECT-TYPE 
        SYNTAX        Counter32 
        MAX-ACCESS    read-only
        STATUS        current 
        DESCRIPTION   "The total number of incoming multicast frames that 
                      were bridged."
        ::= { rcStatEntry 4 }

rcStatBridgeInBroadcastFrames OBJECT-TYPE 
        SYNTAX        Counter32 
        MAX-ACCESS    read-only
        STATUS        current 
        DESCRIPTION   "The total number of incoming broadcast frames that 
                      were bridged."
        ::= { rcStatEntry 5 }

rcStatBridgeInDiscards OBJECT-TYPE 
        SYNTAX        Counter32 
        MAX-ACCESS    read-only
        STATUS        current 
        DESCRIPTION   "The total number of frames that were discarded by
		      the bridging entity."
        ::= { rcStatEntry 6 }

rcStatBridgeOutUnicastFrames OBJECT-TYPE 
        SYNTAX        Counter32 
        MAX-ACCESS    read-only
        STATUS        current 
        DESCRIPTION   "The total number of outgoing unicast frames that 
                      were bridged."
        ::= { rcStatEntry 7 }

rcStatBridgeOutMulticastFrames OBJECT-TYPE 
        SYNTAX        Counter32 
        MAX-ACCESS    read-only
        STATUS        current 
        DESCRIPTION   "The total number of outgoing multicast frames that 
                      were bridged."
        ::= { rcStatEntry 8 }

rcStatBridgeOutBroadcastFrames OBJECT-TYPE 
        SYNTAX        Counter32 
        MAX-ACCESS    read-only
        STATUS        current 
        DESCRIPTION   "The total number of outgoing broadcast frames that 
                      were bridged."
        ::= { rcStatEntry 9 }

rcStatRouteInUnicastFrames OBJECT-TYPE 
        SYNTAX        Counter32 
        MAX-ACCESS    read-only
        STATUS        current 
        DESCRIPTION   "The total number of incoming unicast frames that
                      were routed."
        ::= { rcStatEntry 10 }

rcStatRouteInMulticastFrames OBJECT-TYPE 
        SYNTAX        Counter32 
        MAX-ACCESS    read-only
        STATUS        current 
        DESCRIPTION   "The total number of incoming multicast frames that
                      were routed."
        ::= { rcStatEntry 11 }

rcStatRouteInDiscards OBJECT-TYPE 
        SYNTAX        Counter32 
        MAX-ACCESS    read-only
        STATUS        current 
        DESCRIPTION   "The total number of frames that were discarded by
		      the routing entity."
        ::= { rcStatEntry 12 }

rcStatRouteOutUnicastFrames OBJECT-TYPE 
        SYNTAX        Counter32 
        MAX-ACCESS    read-only
        STATUS        current 
        DESCRIPTION   "The total number of outgoing unicast frames that
                      were routed."
        ::= { rcStatEntry 13 }

rcStatRouteOutMulticastFrames OBJECT-TYPE 
        SYNTAX        Counter32 
        MAX-ACCESS    read-only
        STATUS        current 
        DESCRIPTION   "The total number of outgoing multicast frames that
                      were routed."
        ::= { rcStatEntry 14 }

rcStatStgForwardTransitions OBJECT-TYPE 
        SYNTAX        Counter32 
        MAX-ACCESS    read-only
        STATUS        current 
        DESCRIPTION   "The number of times this port has transitioned
                      from the Learning state to the Forwarding state."
        ::= { rcStatEntry 15 }

rcStatStgInConfigBpdus OBJECT-TYPE 
        SYNTAX        Counter32 
        MAX-ACCESS    read-only
        STATUS        current 
        DESCRIPTION   ""
        ::= { rcStatEntry 16 }

rcStatStgInTcnBpdus OBJECT-TYPE 
        SYNTAX        Counter32 
        MAX-ACCESS    read-only
        STATUS        current 
        DESCRIPTION   ""
        ::= { rcStatEntry 17 }

rcStatStgInBadBpdus OBJECT-TYPE 
        SYNTAX        Counter32 
        MAX-ACCESS    read-only
        STATUS        current 
        DESCRIPTION   ""
        ::= { rcStatEntry 18 }

rcStatStgOutConfigBpdus OBJECT-TYPE 
        SYNTAX        Counter32 
        MAX-ACCESS    read-only
        STATUS        current 
        DESCRIPTION   ""
        ::= { rcStatEntry 19 }

rcStatStgOutTcnBpdus OBJECT-TYPE 
        SYNTAX        Counter32 
        MAX-ACCESS    read-only
        STATUS        current 
        DESCRIPTION   ""
        ::= { rcStatEntry 20 }

rcStatBridgeOutFrames OBJECT-TYPE 
        SYNTAX        Counter32 
        MAX-ACCESS    read-only
        STATUS        current 
        DESCRIPTION     "Used by the Accelar 8000 product family to account
                        for all transmitted bridge unicast, broadcast, and
                        multicast packets.  The individual counters are not
                        supported."

        ::= { rcStatEntry 21 }

rcStatPolicerTotalBytes OBJECT-TYPE
        SYNTAX        Counter64
        MAX-ACCESS    read-only
        STATUS        current
        DESCRIPTION   "The total number of bytes received on the
                       interface."
        ::= { rcStatEntry 25 }

rcStatPolicerTotalPkts OBJECT-TYPE
        SYNTAX        Counter64
        MAX-ACCESS    read-only
        STATUS        current
        DESCRIPTION   "The total number of packets received on the
                       interface."
        ::= { rcStatEntry 26 }

rcStatPolicerGreenBytes OBJECT-TYPE
        SYNTAX        Counter64
        MAX-ACCESS    read-only
        STATUS        current
        DESCRIPTION   "The total number of bytes received on the
                       interface that were below the committed rate."
        ::= { rcStatEntry 27 }

rcStatPolicerYellowBytes OBJECT-TYPE
        SYNTAX        Counter64
        MAX-ACCESS    read-only
        STATUS        current
        DESCRIPTION   "The total number of bytes received on the
                       interface that were above the committed rate
                       but below the peak rate."
        ::= { rcStatEntry 28 }

rcStatPolicerRedBytes OBJECT-TYPE
        SYNTAX        Counter64
        MAX-ACCESS    read-only
        STATUS        current
        DESCRIPTION   "The total number of bytes received on the
                       interface that were above the peak rate."
        ::= { rcStatEntry 29 }


-- rcStatGigTable

rcStatGigTable OBJECT-TYPE
        SYNTAX        SEQUENCE OF RcStatGigEntry
        MAX-ACCESS    not-accessible
        STATUS        current
        DESCRIPTION   "A table used to store Gigport error statistics."
        ::= { rcStat 2 } 
 
rcStatGigEntry OBJECT-TYPE  
        SYNTAX        RcStatGigEntry
        MAX-ACCESS    not-accessible
        STATUS        current
        DESCRIPTION   "Gigabit interface error counters"
        INDEX         { rcStatGigPortIndex }
        ::= { rcStatGigTable 1 }
 
RcStatGigEntry ::= SEQUENCE {
		rcStatGigPortIndex            InterfaceIndex,
		rcStatGigLinkFailures         Counter32,
		rcStatGigPacketErrors         Counter32,
		rcStatGigCarrierErrors        Counter32,
		rcStatGigLinkInactiveErrors   Counter32,
                rcStatGigInFlowCtrlPkts       Counter32,
                rcStatGigOutFlowCtrlPkts      Counter32,
                rcStatGigHCInPfcPkts          Counter64,
                rcStatGigHCOutPfcPkts         Counter64,
                rcStatGigHCInFlowCtrlPkts     Counter64,
                rcStatGigHCOutFlowCtrlPkts    Counter64
        }

rcStatGigPortIndex OBJECT-TYPE
        SYNTAX        InterfaceIndex
        MAX-ACCESS    read-only
        STATUS        current
        DESCRIPTION   "An index value that uniquely identifies a port.
                      This value is similar to ifIndex in MIB2."
        ::= { rcStatGigEntry 1 }

rcStatGigLinkFailures OBJECT-TYPE
        SYNTAX        Counter32
        MAX-ACCESS    read-only
        STATUS        current
        DESCRIPTION   "The total number of link failures encountered on 
                      this interface."
        ::= { rcStatGigEntry 2 }

rcStatGigPacketErrors OBJECT-TYPE
        SYNTAX        Counter32
        MAX-ACCESS    read-only
        STATUS        current
        DESCRIPTION   "The total number of packet errors encountered on 
                      this interface."
        ::= { rcStatGigEntry 3 }

rcStatGigCarrierErrors OBJECT-TYPE
        SYNTAX        Counter32
        MAX-ACCESS    read-only
        STATUS        current
        DESCRIPTION   "The total number of carrier errors encountered on 
                      this interface."
        ::= { rcStatGigEntry 4 }

rcStatGigLinkInactiveErrors OBJECT-TYPE
        SYNTAX        Counter32
        MAX-ACCESS    read-only
        STATUS        current
        DESCRIPTION   "The total number of link inactive errors encountered 
                       on this interface."
        ::= { rcStatGigEntry 5 }

rcStatGigInFlowCtrlPkts OBJECT-TYPE
        SYNTAX        Counter32
        MAX-ACCESS    read-only 
        STATUS        deprecated
        DESCRIPTION   "The total number of flow control packets received
                         by this interface."
        ::= { rcStatGigEntry 6 }

rcStatGigOutFlowCtrlPkts OBJECT-TYPE
        SYNTAX        Counter32
        MAX-ACCESS    read-only 
        STATUS        deprecated
        DESCRIPTION   "The total number of flow control packets transmitted 
                       by this interface."
        ::= { rcStatGigEntry 7 }

rcStatGigHCInPfcPkts OBJECT-TYPE
        SYNTAX        Counter64
        MAX-ACCESS    read-only
        STATUS        current
        DESCRIPTION   "The total number of Priority Flow Control (PFC)
                       packets received by this interface."
        ::= { rcStatGigEntry 8 }

rcStatGigHCOutPfcPkts OBJECT-TYPE
        SYNTAX        Counter64
        MAX-ACCESS    read-only
        STATUS        current
        DESCRIPTION   "The total number of Priority Flow Control (PFC)
                       packets transmitted by this interface."
        ::= { rcStatGigEntry 9 }

rcStatGigHCInFlowCtrlPkts OBJECT-TYPE
        SYNTAX        Counter64
        MAX-ACCESS    read-only
        STATUS        current
        DESCRIPTION   "The total number of flow control packets received
                         by this interface."
        ::= { rcStatGigEntry 10 }

rcStatGigHCOutFlowCtrlPkts OBJECT-TYPE
        SYNTAX        Counter64
        MAX-ACCESS    read-only
        STATUS        current
        DESCRIPTION   "The total number of flow control packets transmitted
                       by this interface."
        ::= { rcStatGigEntry 11 }


rcStatOspf   OBJECT IDENTIFIER       ::= { rcStat 3}
 
rcStatOspfBuffersAllocated OBJECT-TYPE
        SYNTAX        Counter32
        MAX-ACCESS    read-only
        STATUS        current
        DESCRIPTION   "Used to indicate the number of buffers
                      allocated for OSPF."
        ::= { rcStatOspf 1 }
 
rcStatOspfBuffersFreed OBJECT-TYPE
        SYNTAX        Counter32
        MAX-ACCESS    read-only
        STATUS        current
        DESCRIPTION   "Used to indicate the number of buffers
                      that are freed by the OSPF."
        ::= { rcStatOspf 2 }
 
rcStatOspfBufferAllocFailures OBJECT-TYPE
        SYNTAX        Counter32
        MAX-ACCESS    read-only
        STATUS        current
        DESCRIPTION   "Used to indicate the number of times
                      that OSPF has failed to allocate buffers."
        ::= { rcStatOspf 3 }
 
rcStatOspfBufferFreeFailures OBJECT-TYPE
        SYNTAX        Counter32
        MAX-ACCESS    read-only
        STATUS        current
        DESCRIPTION   "Used to indicate the number of times
                      that OSPF has failed to free buffers."
        ::= { rcStatOspf 4 }
 
rcStatOspfTxPackets OBJECT-TYPE
        SYNTAX        Counter32
        MAX-ACCESS    read-only
        STATUS        current
        DESCRIPTION   "Used to indicate the number of packets
                      transmitted by OSPF."
        ::= { rcStatOspf 5 }
 
 
rcStatOspfRxPackets OBJECT-TYPE
        SYNTAX        Counter32
        MAX-ACCESS    read-only
        STATUS        current
        DESCRIPTION   "Used to indicate the number of packets
                      received by OSPF."
        ::= { rcStatOspf 6 }
 
rcStatOspfTxDropPackets OBJECT-TYPE
        SYNTAX        Counter32
        MAX-ACCESS    read-only
        STATUS        current
        DESCRIPTION   "Used to indicate the number of packets
                      dropped before transmitted by OSPF."
        ::= { rcStatOspf 7 }
 
 
rcStatOspfRxDropPackets OBJECT-TYPE
        SYNTAX        Counter32
        MAX-ACCESS    read-only
        STATUS        current
        DESCRIPTION   "Used to indicate the number of packets
                      dropped before received by OSPF."
        ::= { rcStatOspf 8 }
 
rcStatOspfRxBadPackets OBJECT-TYPE
        SYNTAX        Counter32
        MAX-ACCESS    read-only
        STATUS        current
        DESCRIPTION   "Used to indicate the number of packets
                      received by OSPF that are bad."
        ::= { rcStatOspf 9 }
 
rcStatOspfSpfRuns OBJECT-TYPE
        SYNTAX        Counter32
        MAX-ACCESS    read-only
        STATUS        current
        DESCRIPTION   "Used to indicate the total number of SPF
                      calculatations performed by OSPF, which
                      also includes the number of partial route
                      table calculation for Incremental Updates."
        ::= { rcStatOspf 10 }
 
rcStatOspfLastSpfRun OBJECT-TYPE
        SYNTAX        TimeTicks
        MAX-ACCESS    read-only
        STATUS        current
        DESCRIPTION   "Used to indicate the time(SysUpTime) since
                      the last spf calculated by OSPF."
        ::= { rcStatOspf 11 }
 
rcStatOspfLsdbTblSize OBJECT-TYPE
        SYNTAX        Counter32
        MAX-ACCESS    read-only
        STATUS        current
        DESCRIPTION   "Used to indicate the number of entries in
                      the linkstate database table."
        ::= { rcStatOspf 12 }

rcStatOspfRoutes OBJECT-TYPE
        SYNTAX        Counter32
        MAX-ACCESS    read-only
        STATUS        current
        DESCRIPTION   "Used to indicate the number of OSPF routes
                      added to RTM."
        ::= { rcStatOspf 13 }

rcStatOspfAdjacencies OBJECT-TYPE
        SYNTAX        Counter32
        MAX-ACCESS    read-only
        STATUS        current
        DESCRIPTION   "Used to indicate the number of adjacencies 
                      existing."
        ::= { rcStatOspf 14 }

rcStatOspfAreas OBJECT-TYPE
        SYNTAX        Counter32
        MAX-ACCESS    read-only
        STATUS        current
        DESCRIPTION   "Used to indicate the number of areas configured"
        ::= { rcStatOspf 15 }
 
rcStatIgmp   OBJECT IDENTIFIER       ::= { rcStat 4}

rcStatIgmpInMsgs OBJECT-TYPE
        SYNTAX          Counter32
        MAX-ACCESS      read-only
        STATUS          current
        DESCRIPTION     "Used to indicate the number of Igmp packets
                         received by the device."
        ::= { rcStatIgmp 1 }

rcStatIgmpInErrors OBJECT-TYPE
        SYNTAX          Counter32
        MAX-ACCESS      read-only
        STATUS          current
        DESCRIPTION     "Used to indicate the number of Igmp packets
                         received that are with checksum errors."
        ::= { rcStatIgmp 2 }

rcStatIgmpInQueries OBJECT-TYPE
        SYNTAX          Counter32
        MAX-ACCESS      read-only
        STATUS          current
        DESCRIPTION     "Used to indicate the number of Igmp queries
                         received by the device."
        ::= { rcStatIgmp 3 }

rcStatIgmpInReports OBJECT-TYPE
        SYNTAX          Counter32
        MAX-ACCESS      read-only
        STATUS          current
        DESCRIPTION     "Used to indicate the number of Igmp reports
                         received by the device."
        ::= { rcStatIgmp 4 }


rcStatIgmpInLeaves OBJECT-TYPE
        SYNTAX          Counter32
        MAX-ACCESS      read-only
        STATUS          current
        DESCRIPTION     "Used to indicate the number of Igmp Leaves
                         received by the device."
        ::= { rcStatIgmp 5 }

rcStatIgmpInvalid OBJECT-TYPE
        SYNTAX          Counter32
        MAX-ACCESS      read-only
        STATUS          current
        DESCRIPTION     "Used to indicate the number of Igmp packets
                         received by the device that contained invalid
                         type."
        ::= { rcStatIgmp 6 }

rcStatIgmpOutMsgs OBJECT-TYPE
        SYNTAX          Counter32
        MAX-ACCESS      read-only
        STATUS          current
        DESCRIPTION     "Used to indicate the number of Igmp queries
                         sent by the device."
        ::= { rcStatIgmp 7 }

rcStatOspfIfTable OBJECT-TYPE
        SYNTAX        SEQUENCE OF RcStatOspfIfEntry
        MAX-ACCESS    not-accessible
        STATUS        current
        DESCRIPTION   "A table used to store OSPF interface
                      statistics."
        ::= { rcStat 5 }
 
rcStatOspfIfEntry OBJECT-TYPE
        SYNTAX        RcStatOspfIfEntry
        MAX-ACCESS    not-accessible
        STATUS        current
        DESCRIPTION   "Ospf interface statistics"
        INDEX         { rcStatOspfIfIndex }
        ::= { rcStatOspfIfTable 1 }
 
RcStatOspfIfEntry ::= SEQUENCE {
                rcStatOspfIfIndex                   InterfaceIndexOrZero,
                rcStatOspfIfRxHellos                Counter32,
                rcStatOspfIfRxDBDescrs              Counter32,
                rcStatOspfIfRxLSUpdates             Counter32,
                rcStatOspfIfRxLSReqs                Counter32,
                rcStatOspfIfRxLSAcks                Counter32,
                rcStatOspfIfTxHellos                Counter32,
                rcStatOspfIfTxDBDescrs              Counter32,
                rcStatOspfIfTxLSUpdates             Counter32,
                rcStatOspfIfTxLSReqs                Counter32,
                rcStatOspfIfTxLSAcks                Counter32,
                rcStatOspfIfVersionMismatches       Counter32,
                rcStatOspfIfAreaMismatches          Counter32,
                rcStatOspfIfAuthTypeMismatches      Counter32,
                rcStatOspfIfAuthFailures            Counter32,
                rcStatOspfIfNetMaskMismatches       Counter32,
                rcStatOspfIfHelloIntervalMismatches Counter32,
                rcStatOspfIfDeadIntervalMismatches  Counter32,
                rcStatOspfIfOptionMismatches        Counter32
        }
 
rcStatOspfIfIndex OBJECT-TYPE
        SYNTAX        InterfaceIndexOrZero (0..6142)
        MAX-ACCESS    read-only
        STATUS        current
        DESCRIPTION   "An unique value that is used to identify a
                      physical interface."
        ::= { rcStatOspfIfEntry 1 }
 
rcStatOspfIfRxHellos OBJECT-TYPE
        SYNTAX        Counter32
        MAX-ACCESS    read-only
        STATUS        current
        DESCRIPTION   "Used to indicate the number hello packets
                      received by this interface."
        ::= { rcStatOspfIfEntry 2 }

rcStatOspfIfRxDBDescrs OBJECT-TYPE
        SYNTAX        Counter32
        MAX-ACCESS    read-only
        STATUS        current
        DESCRIPTION   "Used to indicate the number database descriptor
                      packets received by this interface."
        ::= { rcStatOspfIfEntry 3 }
 
rcStatOspfIfRxLSUpdates OBJECT-TYPE
        SYNTAX        Counter32
        MAX-ACCESS    read-only
        STATUS        current
        DESCRIPTION   "Used to indicate the number Link state update
                      packets received by this interface."
        ::= { rcStatOspfIfEntry 4 }
 
rcStatOspfIfRxLSReqs OBJECT-TYPE
        SYNTAX        Counter32
        MAX-ACCESS    read-only
        STATUS        current
        DESCRIPTION   "Used to indicate the number Link state request
                      packets received by this interface."
        ::= { rcStatOspfIfEntry 5 }
 
rcStatOspfIfRxLSAcks OBJECT-TYPE
        SYNTAX        Counter32
        MAX-ACCESS    read-only
        STATUS        current
        DESCRIPTION   "Used to indicate the number Link state acknowlege
                      packets received by this interface."
        ::= { rcStatOspfIfEntry 6 }
 
rcStatOspfIfTxHellos OBJECT-TYPE
        SYNTAX        Counter32
        MAX-ACCESS    read-only
        STATUS        current
        DESCRIPTION   "Used to indicate the number hello packets
                      transmitted by this interface."
        ::= { rcStatOspfIfEntry 7 }
 
rcStatOspfIfTxDBDescrs OBJECT-TYPE
        SYNTAX        Counter32
        MAX-ACCESS    read-only
        STATUS        current
        DESCRIPTION   "Used to indicate the number database descriptor
                      packets transmitted by this interface."
        ::= { rcStatOspfIfEntry 8 }
 
rcStatOspfIfTxLSUpdates OBJECT-TYPE
        SYNTAX        Counter32
        MAX-ACCESS    read-only
        STATUS        current
        DESCRIPTION   "Used to indicate the number Link state update
                      packets transmitted by this interface."
        ::= { rcStatOspfIfEntry 9 }
 
rcStatOspfIfTxLSReqs OBJECT-TYPE
        SYNTAX        Counter32
        MAX-ACCESS    read-only
        STATUS        current
        DESCRIPTION   "Used to indicate the number Link state request
                      packets transmitted by this interface."
        ::= { rcStatOspfIfEntry 10 }
 
rcStatOspfIfTxLSAcks OBJECT-TYPE
        SYNTAX        Counter32
        MAX-ACCESS    read-only
        STATUS        current
        DESCRIPTION   "Used to indicate the number Link state acknowlege
                      packets transmitted by this interface."
        ::= { rcStatOspfIfEntry 11 }

rcStatOspfIfVersionMismatches OBJECT-TYPE 
        SYNTAX        Counter32
        MAX-ACCESS    read-only
        STATUS        current
        DESCRIPTION   "Used to indicate the number version
                      mismatches received by this interface."
        ::= { rcStatOspfIfEntry 12 }

rcStatOspfIfAreaMismatches OBJECT-TYPE 
        SYNTAX        Counter32
        MAX-ACCESS    read-only
        STATUS        current
        DESCRIPTION   "Used to indicate the number area
                      mismatches received by this interface."
        ::= { rcStatOspfIfEntry 13 }

rcStatOspfIfAuthTypeMismatches OBJECT-TYPE 
        SYNTAX        Counter32
        MAX-ACCESS    read-only
        STATUS        current
        DESCRIPTION   "Used to indicate the number AuthType 
                      mismatches received by this interface."
        ::= { rcStatOspfIfEntry 14 }

rcStatOspfIfAuthFailures OBJECT-TYPE 
        SYNTAX        Counter32
        MAX-ACCESS    read-only
        STATUS        current
        DESCRIPTION   "Used to indicate the number Authentication
                      failures."
        ::= { rcStatOspfIfEntry 15 }

rcStatOspfIfNetMaskMismatches OBJECT-TYPE 
        SYNTAX        Counter32
        MAX-ACCESS    read-only
        STATUS        current
        DESCRIPTION   "Used to indicate the number net mask
                      mismatches received by this interface."
        ::= { rcStatOspfIfEntry 16 }

rcStatOspfIfHelloIntervalMismatches OBJECT-TYPE 
        SYNTAX        Counter32
        MAX-ACCESS    read-only
        STATUS        current
        DESCRIPTION   "Used to indicate the number hello interval
                      mismatches received by this interface."
        ::= { rcStatOspfIfEntry 17 }

rcStatOspfIfDeadIntervalMismatches OBJECT-TYPE 
        SYNTAX        Counter32
        MAX-ACCESS    read-only
        STATUS        current
        DESCRIPTION   "Used to indicate the number dead interval
                      mismatches received by this interface."
        ::= { rcStatOspfIfEntry 18 }

rcStatOspfIfOptionMismatches OBJECT-TYPE 
        SYNTAX        Counter32
        MAX-ACCESS    read-only
        STATUS        current
        DESCRIPTION   "Used to indicate the number options
                      mismatches received by this interface."
        ::= { rcStatOspfIfEntry 19 }

-- rcStatMlt Group

rcStatMlt      OBJECT IDENTIFIER ::= { rcStat 6 }
 
rcStatMltIfExtnTable OBJECT-TYPE
        SYNTAX        SEQUENCE OF RcStatMltIfExtnEntry
        MAX-ACCESS    not-accessible
        STATUS        current
        DESCRIPTION   "A table used to store Mlt interface
                      statistics."
        ::= { rcStatMlt 1 }
 
rcStatMltIfExtnEntry OBJECT-TYPE
        SYNTAX        RcStatMltIfExtnEntry
        MAX-ACCESS    not-accessible
        STATUS        current
        DESCRIPTION   "Mlt interface statistics"
        INDEX         { rcStatMltIfExtnMltId }
        ::= { rcStatMltIfExtnTable 1 }
 
RcStatMltIfExtnEntry ::= SEQUENCE {
                rcStatMltIfExtnMltId                  INTEGER,
                rcStatMltIfExtnIfInMulticastPkts      Counter32,
                rcStatMltIfExtnIfInBroadcastPkts      Counter32,
                rcStatMltIfExtnIfOutMulticastPkts     Counter32,
                rcStatMltIfExtnIfOutBroadcastPkts     Counter32,
                rcStatMltIfExtnIfHCInOctets           Counter64,
                rcStatMltIfExtnIfHCInUcastPkts        Counter64,
                rcStatMltIfExtnIfHCInMulticastPkt     Counter64,
                rcStatMltIfExtnIfHCInBroadcastPkt     Counter64,
                rcStatMltIfExtnIfHCOutOctets          Counter64,
                rcStatMltIfExtnIfHCOutUcastPkts       Counter64,
                rcStatMltIfExtnIfHCOutMulticast       Counter64,
                rcStatMltIfExtnIfHCOutBroadcast       Counter64,
                rcStatMltIfExtnIfHCInLsmPkts          Counter64,
                rcStatMltIfExtnIfHCOutLsmPkts         Counter64
        }
 
rcStatMltIfExtnMltId OBJECT-TYPE
        SYNTAX        INTEGER (1..512)
        MAX-ACCESS    read-only
        STATUS        current
        DESCRIPTION   "Mlt Id"
        ::= { rcStatMltIfExtnEntry 1 }
 
rcStatMltIfExtnIfInMulticastPkts OBJECT-TYPE
        SYNTAX        Counter32
        MAX-ACCESS    read-only
        STATUS        current
        DESCRIPTION   "multi-pkts to upper"
        ::= { rcStatMltIfExtnEntry 2 }

rcStatMltIfExtnIfInBroadcastPkts OBJECT-TYPE
        SYNTAX        Counter32
        MAX-ACCESS    read-only
        STATUS        current
        DESCRIPTION   "broad-pkts to upper"
        ::= { rcStatMltIfExtnEntry 3 }
 
rcStatMltIfExtnIfOutMulticastPkts OBJECT-TYPE
        SYNTAX        Counter32
        MAX-ACCESS    read-only
        STATUS        current
        DESCRIPTION   "multi-pkts from upper"
        ::= { rcStatMltIfExtnEntry 4 }
 
rcStatMltIfExtnIfOutBroadcastPkts OBJECT-TYPE
        SYNTAX        Counter32
        MAX-ACCESS    read-only
        STATUS        current
        DESCRIPTION   "broad-pkts from upper"
        ::= { rcStatMltIfExtnEntry 5 }
 
rcStatMltIfExtnIfHCInOctets OBJECT-TYPE
        SYNTAX        Counter64
        MAX-ACCESS    read-only
        STATUS        current
        DESCRIPTION   "The total number of octets received 
                       on the MLT interface, including framing 
                       characters."
        ::= { rcStatMltIfExtnEntry 6 }
 
rcStatMltIfExtnIfHCInUcastPkts OBJECT-TYPE
        SYNTAX        Counter64
        MAX-ACCESS    read-only
        STATUS        current
        DESCRIPTION   "The number of packets delivered by this
                       MLT to a higher MLT that were not addressed
                       to a nulticast or broadcase address at this
                       sublayer."
        ::= { rcStatMltIfExtnEntry 7 }
 
rcStatMltIfExtnIfHCInMulticastPkt OBJECT-TYPE
        SYNTAX        Counter64
        MAX-ACCESS    read-only
        STATUS        current
        DESCRIPTION   "The number of packets delivered to this MLT that
                       were addressed to a nulticast address at this
                       sublayer.  For a MAC layer protocol, this number
                       includes both Group and Functional addresses."
        ::= { rcStatMltIfExtnEntry 8 }
 
rcStatMltIfExtnIfHCInBroadcastPkt OBJECT-TYPE
        SYNTAX        Counter64
        MAX-ACCESS    read-only
        STATUS        current
        DESCRIPTION   "The number of packets delivered to this MLT that
 		       were addressed to a broadcast address at this
 		       sublayer."
        ::= { rcStatMltIfExtnEntry 9 }
 
rcStatMltIfExtnIfHCOutOctets OBJECT-TYPE
        SYNTAX        Counter64
        MAX-ACCESS    read-only
        STATUS        current
        DESCRIPTION   "The total number of octets transmitted 
                       out of the MLT interface, including 
                       framing characters."
        ::= { rcStatMltIfExtnEntry 10 }
 
rcStatMltIfExtnIfHCOutUcastPkts OBJECT-TYPE
        SYNTAX        Counter64
        MAX-ACCESS    read-only
        STATUS        current
        DESCRIPTION   "The number of packets that hight-level protocols
                       requested be transmitted that were not addressed 
                       to a multicast address at this MLT.  This total
                       number includes those packets discarded or unsent."
        ::= { rcStatMltIfExtnEntry 11 }

rcStatMltIfExtnIfHCOutMulticast OBJECT-TYPE 
        SYNTAX        Counter64
        MAX-ACCESS    read-only
        STATUS        current
        DESCRIPTION   "The total number of packets that hight-level
                       protocols requested be transmitted, and that 
                       were addressed to a multicast address at this
                       MLT, including those that were discarded or 
                       not sent.  For a MAC layer protocol, this
                       number includes both Group and Functional
                       addresses."
        ::= { rcStatMltIfExtnEntry 12 }

rcStatMltIfExtnIfHCOutBroadcast OBJECT-TYPE 
        SYNTAX        Counter64
        MAX-ACCESS    read-only
        STATUS        current
        DESCRIPTION   "The total number of packets that hight-level
		       protocols requested be transmitted, and that
		       were addressed to a broadcase address at this	
		       MLT, including those that were discarded or 
		       not sent."
        ::= { rcStatMltIfExtnEntry 13 }

rcStatMltIfExtnIfHCInLsmPkts OBJECT-TYPE 
        SYNTAX        Counter64
        MAX-ACCESS    read-only
        STATUS        current
        DESCRIPTION   "The total number of Link State Messaging (LSM) 
                       packets delivered to this MLT."

        ::= { rcStatMltIfExtnEntry 14 }

rcStatMltIfExtnIfHCOutLsmPkts OBJECT-TYPE 
        SYNTAX        Counter64
        MAX-ACCESS    read-only
        STATUS        current
        DESCRIPTION   "The total number of Link State Messaging (LSM) 
                       packets trasmitted on this MLT."

        ::= { rcStatMltIfExtnEntry 15 }

-- Mlt Ether table

rcStatMltEtherTable OBJECT-TYPE
        SYNTAX        SEQUENCE OF RcStatMltEtherEntry
        MAX-ACCESS    not-accessible
        STATUS        current
        DESCRIPTION   "A table used to store Mlt Ethernet
                      statistics."
        ::= { rcStatMlt 2 }
 
rcStatMltEtherEntry OBJECT-TYPE
        SYNTAX        RcStatMltEtherEntry
        MAX-ACCESS    not-accessible
        STATUS        current
        DESCRIPTION   "Mlt enternet statistics"
        INDEX         { rcStatMltEtherMltId }
        ::= { rcStatMltEtherTable 1 }
 
RcStatMltEtherEntry ::= SEQUENCE {
                rcStatMltEtherMltId              INTEGER,
                rcStatMltEtherAlignmentErrors    Counter32,
                rcStatMltEtherFCSErrors          Counter32,
                rcStatMltEtherSingleCollFrames   Counter32,
                rcStatMltEtherMultipleCollFrames Counter32,
                rcStatMltEtherSQETestError       Counter32,
                rcStatMltEtherDeferredTransmiss  Counter32,
                rcStatMltEtherLateCollisions     Counter32,
                rcStatMltEtherExcessiveCollis    Counter32,
                rcStatMltEtherIMacTransmitError  Counter32,
                rcStatMltEtherCarrierSenseError  Counter32,
                rcStatMltEtherFrameTooLong       Counter32,
                rcStatMltEtherIMacReceiveError   Counter32
        }
 
rcStatMltEtherMltId OBJECT-TYPE
        SYNTAX        INTEGER (1..512)
        MAX-ACCESS    read-only
        STATUS        current
        DESCRIPTION   "A value that uniquely identifies the Multi-Link 
                       Trunk associated with this entry."
        ::= { rcStatMltEtherEntry 1 }
 
rcStatMltEtherAlignmentErrors OBJECT-TYPE
        SYNTAX        Counter32
        MAX-ACCESS    read-only
        STATUS        current
        DESCRIPTION   "A count of frames received on a particular MLT
 		       that are not an integral number of octets in
		       length and do not pass the FCS check.  The count
		       represented by an instance of this object is
		       incremented when the alignmentError status is
		       returned by the MAC service to the LLC (or other
		       MAC user).  Received frames for which multiple
	 	       error conditions occur are, according to the 
		       conventions of IEEE 802.3 Layer Management, 
		       counted exclusively according to the error status
		       presented to the LLC."
        ::= { rcStatMltEtherEntry 2 }

rcStatMltEtherFCSErrors OBJECT-TYPE
        SYNTAX        Counter32
        MAX-ACCESS    read-only
        STATUS        current
        DESCRIPTION   "A count of frames received on an MLT that are an
	               integral number of octets in length but do not pass
                       the FCS check.  The count represented by an instance
                       of this object is incremented when the frameCheckError
                       status is returned by the MAC service to the LLC
                       (or other MAC user).  Received frames for which
		       multiple error conditions occur are, according to 
                       the conventions of IEEE 802.3 Layer Management, 
		       counted exclusively according to the error status
		       presented to the LLC."
        ::= { rcStatMltEtherEntry 3 }
 
rcStatMltEtherSingleCollFrames OBJECT-TYPE
        SYNTAX        Counter32
        MAX-ACCESS    read-only
        STATUS        current
        DESCRIPTION   "A count of successfully transmitted frames on 
                       a particular MLT for which transmission is 
                       inhibited by exactly one collision.  A frame 
                       that is counted by an instance of this objects 
                       is also counted by the corresponding instance 
                       of either the ifOutUcastPkts, ifOutMulticastPkts, 
                       or ifOutBroadcastPkts, and it not counted by the 
                       corresponding instance of the MultipleCollisionFrames 
                       object."
        ::= { rcStatMltEtherEntry 4 }
 
rcStatMltEtherMultipleCollFrames OBJECT-TYPE
        SYNTAX        Counter32
        MAX-ACCESS    read-only
        STATUS        current
        DESCRIPTION   "A count of successfully transmitted frames on 
                       a particular MLT for which transmission is 
                       inhibited by more than one collision.  A frame 
                       that is counted by an instance of this object 
                       is also counted by the corresponding instance 
                       of either the ifOutUcastPkts, ifOutMulticastPkts, 
                       or ifOutBroadcastPkts, and is not counted by the 
                       corresponding instance of the SingleCollisionFrames 
                       objects."
        ::= { rcStatMltEtherEntry 5 }
 
rcStatMltEtherSQETestError OBJECT-TYPE
        SYNTAX        Counter32
        MAX-ACCESS    read-only
        STATUS        current
        DESCRIPTION   "A count of times that the SQE TEST ERROR message
		       is generated by the PLS sublayer for a particular
	               MLT. SQE stands for Signal Quality Error."
        ::= { rcStatMltEtherEntry 6 }
 
rcStatMltEtherDeferredTransmiss OBJECT-TYPE
        SYNTAX        Counter32
        MAX-ACCESS    read-only
        STATUS        current
        DESCRIPTION   "A count of frames for which the first transmission
	               attempt on a particular MLT is delayed because the
                       medium is busy.  The count represented by an 
	               instance of this object does not include frames
		       involved in collisions."
        ::= { rcStatMltEtherEntry 7 }
 
rcStatMltEtherLateCollisions OBJECT-TYPE
        SYNTAX        Counter32
        MAX-ACCESS    read-only
        STATUS        current
        DESCRIPTION   "The number of times that a collision is detected 
                       on a particular MLT later than 512 bit-times 
                       (64 octets) into the transmission of a packet. 
                       Five hundred and twelve bit-times corresponds to 
                       51.2 microseconds on a 10 mb/s system.  A (late) 
                       collision included in a count represented by an 
                       instance of this object is also considered as a
                       (generic) collision for purposes of other 
                       collision-related statistics."
        ::= { rcStatMltEtherEntry 8 }
 
rcStatMltEtherExcessiveCollis OBJECT-TYPE
        SYNTAX        Counter32
        MAX-ACCESS    read-only
        STATUS        current
        DESCRIPTION   "A count of frames for which transmission on a 
	               particular MLT fails due to excessive collisions."
        ::= { rcStatMltEtherEntry 9 }
 
rcStatMltEtherIMacTransmitError OBJECT-TYPE
        SYNTAX        Counter32
        MAX-ACCESS    read-only
        STATUS        current
        DESCRIPTION   "A count of frames for which transmission on a 
	               particular MLT fails due to an internal MAC 
                       sublayer transmit error.  A frame is only counted 
                       by an instance of this object if it is not counted
                       by the corresponding instance of either the 
		       LateCollisions object, the ExcessiveCollisions
		       object, or the CarrierSenseError object."
        ::= { rcStatMltEtherEntry 10 }
 
rcStatMltEtherCarrierSenseError OBJECT-TYPE
        SYNTAX        Counter32
        MAX-ACCESS    read-only
        STATUS        current
        DESCRIPTION   "The number of times that the carrier sense 
                       condition was lost or never asserted when 
                       attempting to transmit a frame on a particular
                       MLT.  The count represented by an instance of
	               this object is incremented at most once per
		       transmission attempt, even if the carrier
		       sense condition fluctuates during a 
		       transmission attempt."
        ::= { rcStatMltEtherEntry 11 }

rcStatMltEtherFrameTooLong OBJECT-TYPE 
        SYNTAX        Counter32
        MAX-ACCESS    read-only
        STATUS        current
        DESCRIPTION   "A count of frames received on a particular MLT
                       that exceed the maximum permitted size (1518 
                       octets).  The count represented by an instance
		       os this object is incremented when the frame
	               TooLong status is returned by the MAC service
		       to the LLC (or other MAC user).  Received frames
		       for which multiple error conditions occur are, 
		       according to the conventions of IEEE 802.3 
                       Layer Management, counted exclusively according
		       to the error status presented to the LLC."
        ::= { rcStatMltEtherEntry 12 }

rcStatMltEtherIMacReceiveError OBJECT-TYPE 
        SYNTAX        Counter32
        MAX-ACCESS    read-only
        STATUS        current
        DESCRIPTION   "A count of frames for which reception on a 
		       particular MLT fails due to an internal MAC
		       sublayer receive error.  A frame is only
		       counted by an instance of this object if it 
		       is not counted by the corresponding instance 
		       of either the FrameTooLongs object, the
	               AlignmentErrors object, of the FCSErrors
	               objects.
                       The precise meaning of the count represented
		       by an instance of this object is implementation
	               specific.  In particular, an instance of this
	               object may represent a count of receive errors
                       on a particular interface that are not otherwise
		       counted."
        ::= { rcStatMltEtherEntry 13 }


rcStatSmltIstDownCnt OBJECT-TYPE
        SYNTAX        Counter32
        MAX-ACCESS    read-only
        STATUS        current
        DESCRIPTION   "Counters that counts how the session between the
                       two peering switches has done down since last boot."
        ::= { rcStatMlt 4 } 

rcStatSmltHelloTxMsgCnt OBJECT-TYPE
        SYNTAX        Counter32
        MAX-ACCESS    read-only
        STATUS        current
        DESCRIPTION   "Counters that counts the tx hello msg."
        ::= { rcStatMlt 5 } 

rcStatSmltHelloRxMsgCnt OBJECT-TYPE
        SYNTAX        Counter32
        MAX-ACCESS    read-only
        STATUS        current
        DESCRIPTION   "Counters that counts the rx hello msg."
        ::= { rcStatMlt 6 } 

rcStatSmltLearnMacAddrTxMsgCnt OBJECT-TYPE
        SYNTAX        Counter32
        MAX-ACCESS    read-only
        STATUS        current
        DESCRIPTION   "Counters that counts the tx learn Mac Address msg."
        ::= { rcStatMlt 7 } 

rcStatSmltLearnMacAddrRxMsgCnt OBJECT-TYPE
        SYNTAX        Counter32
        MAX-ACCESS    read-only
        STATUS        current
        DESCRIPTION   "Counters that counts the rx learn Mac Address msg."
        ::= { rcStatMlt 8 } 

rcStatSmltMacAddrAgeOutTxMsgCnt OBJECT-TYPE
        SYNTAX        Counter32
        MAX-ACCESS    read-only
        STATUS        current
        DESCRIPTION   "Counters that counts the tx Mac Address Aging Out msg."
        ::= { rcStatMlt 9 } 

rcStatSmltMacAddrAgeOutRxMsgCnt OBJECT-TYPE
        SYNTAX        Counter32
        MAX-ACCESS    read-only
        STATUS        current
        DESCRIPTION   "Counters that counts the rx Mac Address Aging Out msg."
        ::= { rcStatMlt 10 } 

rcStatSmltMacAddrAgeExpTxMsgCnt OBJECT-TYPE
        SYNTAX        Counter32
        MAX-ACCESS    read-only
        STATUS        current
        DESCRIPTION   "Counters that counts the tx Mac Address age expired msg."
        ::= { rcStatMlt 11 } 

rcStatSmltMacAddrAgeExpRxMsgCnt OBJECT-TYPE
        SYNTAX        Counter32
        MAX-ACCESS    read-only
        STATUS        current
        DESCRIPTION   "Counters that counts the rx Mac Address age expired msg."
        ::= { rcStatMlt 12 } 

rcStatSmltStgInfoTxMsgCnt OBJECT-TYPE
        SYNTAX        Counter32
        MAX-ACCESS    read-only
        STATUS        current
        DESCRIPTION   "Counters that counts the tx Stg information msg."
        ::= { rcStatMlt 13 } 

rcStatSmltStgInfoRxMsgCnt OBJECT-TYPE
        SYNTAX        Counter32
        MAX-ACCESS    read-only
        STATUS        current
        DESCRIPTION   "Counters that counts the rx Stg information msg."
        ::= { rcStatMlt 14 } 

rcStatSmltDelMacAddrTxMsgCnt OBJECT-TYPE
        SYNTAX        Counter32
        MAX-ACCESS    read-only
        STATUS        current
        DESCRIPTION   "Counters that counts the tx deleted MAC address msg."
        ::= { rcStatMlt 15 } 

rcStatSmltDelMacAddrRxMsgCnt OBJECT-TYPE
        SYNTAX        Counter32
        MAX-ACCESS    read-only
        STATUS        current
        DESCRIPTION   "Counters that counts the rx deleted MAC address msg."
        ::= { rcStatMlt 16 } 

rcStatSmltSmltDownTxMsgCnt OBJECT-TYPE
        SYNTAX        Counter32
        MAX-ACCESS    read-only
        STATUS        current
        DESCRIPTION   "Counters that counts the tx Smlt Down msg."
        ::= { rcStatMlt 17 } 

rcStatSmltSmltDownRxMsgCnt OBJECT-TYPE
        SYNTAX        Counter32
        MAX-ACCESS    read-only
        STATUS        current
        DESCRIPTION   "Counters that counts the rx Smlt Down msg."
        ::= { rcStatMlt 18 } 

rcStatSmltSmltUpTxMsgCnt OBJECT-TYPE
        SYNTAX        Counter32
        MAX-ACCESS    read-only
        STATUS        current
        DESCRIPTION   "Counters that counts the tx Smlt Up msg."
        ::= { rcStatMlt 19 }

rcStatSmltSmltUpRxMsgCnt OBJECT-TYPE
        SYNTAX        Counter32
        MAX-ACCESS    read-only
        STATUS        current
        DESCRIPTION   "Counters that counts the rx Smlt Up msg."
        ::= { rcStatMlt 20 }

rcStatSmltSendMacTblTxMsgCnt OBJECT-TYPE
        SYNTAX        Counter32
        MAX-ACCESS    read-only
        STATUS        current
        DESCRIPTION   "Counters that counts the tx Send Mac Table msg."
        ::= { rcStatMlt 21 } 

rcStatSmltSendMacTblRxMsgCnt OBJECT-TYPE
        SYNTAX        Counter32
        MAX-ACCESS    read-only
        STATUS        current
        DESCRIPTION   "Counters that counts the rx Send Mac Table msg."
        ::= { rcStatMlt 22 } 

rcStatSmltIgmpTxMsgCnt OBJECT-TYPE
        SYNTAX        Counter32
        MAX-ACCESS    read-only
        STATUS        current
        DESCRIPTION   "Counters that counts the tx Igmp msg."
        ::= { rcStatMlt 23 } 

rcStatSmltIgmpRxMsgCnt OBJECT-TYPE
        SYNTAX        Counter32
        MAX-ACCESS    read-only
        STATUS        current
        DESCRIPTION   "Counters that counts the rx Igmp msg."
        ::= { rcStatMlt 24 } 

rcStatSmltPortDownTxMsgCnt OBJECT-TYPE
        SYNTAX        Counter32
        MAX-ACCESS    read-only
        STATUS        current
        DESCRIPTION   "Counters that counts the tx port down msg."
        ::= { rcStatMlt 25 } 

rcStatSmltPortDownRxMsgCnt OBJECT-TYPE
        SYNTAX        Counter32
        MAX-ACCESS    read-only
        STATUS        current
        DESCRIPTION   "Counters that counts the rx port down msg."
        ::= { rcStatMlt 26 } 

rcStatSmltReqMacTblTxMsgCnt OBJECT-TYPE
        SYNTAX        Counter32
        MAX-ACCESS    read-only
        STATUS        current
        DESCRIPTION   "Counters that counts the tx request Mac table msg."
        ::= { rcStatMlt 27 } 

rcStatSmltReqMacTblRxMsgCnt OBJECT-TYPE
        SYNTAX        Counter32
        MAX-ACCESS    read-only
        STATUS        current
        DESCRIPTION   "Counters that counts the rx request Mac table msg."
        ::= { rcStatMlt 28 } 

rcStatSmltRxUnknownMsgTypeCnt OBJECT-TYPE
        SYNTAX        Counter32
        MAX-ACCESS    read-only
        STATUS        current
        DESCRIPTION   "Counters that counts the rx unknown msg type."
        ::= { rcStatMlt 29 } 


-- Common resource threshold exceeded counter for all multicast protocols
-- active on the chassis

rcStatMulticast      OBJECT IDENTIFIER ::= { rcStat 9 }

rcStatMulticastSourceGroupThresholdExceeded OBJECT-TYPE
        SYNTAX        Counter32
        MAX-ACCESS    read-only 
        STATUS        current
        DESCRIPTION   "The count of number of times the threshold of 
                       available IP Multicast (Source,Group) Records was 
                       reached. When this threshold is reached, a new IP 
                       Multicast stream ingressing the switch cannot be 
                       forwarded."
        ::= { rcStatMulticast 1 }

rcStatMulticastEgressStreamThresholdExceeded OBJECT-TYPE
        SYNTAX        Counter32
        MAX-ACCESS    read-only
        STATUS        current
        DESCRIPTION   "The count of number of times the threshold of 
                       available IP Multicast Egress Forwarding Records was 
                       reached. When this threshold is reached, a new IP 
                       Multicast Receiver that needs new Egress Forwarding 
                       Record (PepStrem Record) will not be programmed to 
                       receive the subscribing multicast stream."
        ::= { rcStatMulticast 2 }

rcStatBgp			OBJECT IDENTIFIER ::= { rcStat 10 }

rcStatBgpStarts OBJECT-TYPE
        SYNTAX        Counter32
        MAX-ACCESS    read-only
        STATUS        current
        DESCRIPTION   "Number of times BGP connection started"
        ::= { rcStatBgp 1 }

rcStatBgpStops OBJECT-TYPE
        SYNTAX        Counter32
        MAX-ACCESS    read-only
        STATUS        current
        DESCRIPTION   "Number of times BGP connection stopped"
        ::= { rcStatBgp 2 }

rcStatBgpOpens OBJECT-TYPE
        SYNTAX        Counter32
        MAX-ACCESS    read-only
        STATUS        current
        DESCRIPTION   "Number of times BGP opens TCP"
        ::= { rcStatBgp 3 }

rcStatBgpCloses OBJECT-TYPE
        SYNTAX        Counter32
        MAX-ACCESS    read-only
        STATUS        current
        DESCRIPTION   "Number of times BGP closes TCP"
        ::= { rcStatBgp 4 }

rcStatBgpFails OBJECT-TYPE
        SYNTAX        Counter32
        MAX-ACCESS    read-only
        STATUS        current
        DESCRIPTION   "Number of times TCP attempts failed"
        ::= { rcStatBgp 5 }

rcStatBgpFatals OBJECT-TYPE
        SYNTAX        Counter32
        MAX-ACCESS    read-only
        STATUS        current
        DESCRIPTION   "Number of times TCP crashes due to fatal error"
        ::= { rcStatBgp 6 }

rcStatBgpConnExps OBJECT-TYPE
        SYNTAX        Counter32
        MAX-ACCESS    read-only
        STATUS        current
        DESCRIPTION   "Number of times TCP retry timer expired"
        ::= { rcStatBgp 7 }

rcStatBgpHoldExps OBJECT-TYPE
        SYNTAX        Counter32
        MAX-ACCESS    read-only
        STATUS        current
        DESCRIPTION   "Number of times hold timer expired"
        ::= { rcStatBgp 8 }

rcStatBgpKeepExps OBJECT-TYPE
        SYNTAX        Counter32
        MAX-ACCESS    read-only
        STATUS        current
        DESCRIPTION   "Number of times keepalive timer expired"
        ::= { rcStatBgp 9 }

rcStatBgpRxOpens OBJECT-TYPE
        SYNTAX        Counter32
        MAX-ACCESS    read-only
        STATUS        current
        DESCRIPTION   "Number of OPENs BGP receives"
        ::= { rcStatBgp 10 }

rcStatBgpRxKeeps OBJECT-TYPE
        SYNTAX        Counter32
        MAX-ACCESS    read-only
        STATUS        current
        DESCRIPTION   "Number of KEEPALIVEs BGP recieves"
        ::= { rcStatBgp 11 }

rcStatBgpRxUpdates OBJECT-TYPE
        SYNTAX        Counter32
        MAX-ACCESS    read-only
        STATUS        current
        DESCRIPTION   "Number of UPDATEs BGP recieves "
        ::= { rcStatBgp 12 }

rcStatBgpRxNotifys OBJECT-TYPE
        SYNTAX        Counter32
        MAX-ACCESS    read-only
        STATUS        current
        DESCRIPTION   "Number NOTIFICATIONs BGP recieves "
        ::= { rcStatBgp 13 }

rcStatBgpTxOpens OBJECT-TYPE
        SYNTAX        Counter32
        MAX-ACCESS    read-only
        STATUS        current
        DESCRIPTION   "Number of OPENs BGP transmitted"
        ::= { rcStatBgp 14 }

rcStatBgpTxKeeps OBJECT-TYPE
        SYNTAX        Counter32
        MAX-ACCESS    read-only
        STATUS        current
        DESCRIPTION   "Number of KEEPALIVEs BGP transmitted"
        ::= { rcStatBgp 15 }

rcStatBgpTxUpdates OBJECT-TYPE
        SYNTAX        Counter32
        MAX-ACCESS    read-only
        STATUS        current
        DESCRIPTION   "Number of UPDATEs BGP transmits"
        ::= { rcStatBgp 16 }

rcStatBgpTxNotifys OBJECT-TYPE
        SYNTAX        Counter32
        MAX-ACCESS    read-only
        STATUS        current
        DESCRIPTION   "Number of NOTIFICATIONs BGP transmits"
        ::= { rcStatBgp 17 }

rcStatBgpBadEvents OBJECT-TYPE
        SYNTAX        Counter32
        MAX-ACCESS    read-only
        STATUS        current
        DESCRIPTION   "Number of invalid events FSM received"
        ::= { rcStatBgp 18 }

rcStatBgpSyncFails OBJECT-TYPE
        SYNTAX        Counter32
        MAX-ACCESS    read-only
        STATUS        current
        DESCRIPTION   "Number of times FDB sync failed"
        ::= { rcStatBgp 19 }

rcStatBgpTrEvent OBJECT-TYPE
        SYNTAX        Counter32
        MAX-ACCESS    read-only
        STATUS        current
        DESCRIPTION   "Trace event"
        ::= { rcStatBgp 20 }

-- Rx
rcStatBgpRxECodeHeader OBJECT-TYPE
        SYNTAX        Counter32
        MAX-ACCESS    read-only
        STATUS        current
        DESCRIPTION   "Total Header errors received"
        ::= { rcStatBgp 21 }

rcStatBgpRxECodeOpen OBJECT-TYPE
        SYNTAX        Counter32
        MAX-ACCESS    read-only
        STATUS        current
        DESCRIPTION   "Total Open errors received"
        ::= { rcStatBgp 22 }

rcStatBgpRxECodeUpdate OBJECT-TYPE
        SYNTAX        Counter32
        MAX-ACCESS    read-only
        STATUS        current
        DESCRIPTION   "Total Update errors received"
        ::= { rcStatBgp 23 }

rcStatBgpRxECodeHoldtimer OBJECT-TYPE
        SYNTAX        Counter32
        MAX-ACCESS    read-only
        STATUS        current
        DESCRIPTION   "Total Holdtimer errors received"
        ::= { rcStatBgp 24 }

rcStatBgpRxECodeFSM OBJECT-TYPE
        SYNTAX        Counter32
        MAX-ACCESS    read-only
        STATUS        current
        DESCRIPTION   "Total FSM errors received"
        ::= { rcStatBgp 25 }

rcStatBgpRxECodeCease OBJECT-TYPE
        SYNTAX        Counter32
        MAX-ACCESS    read-only
        STATUS        current
        DESCRIPTION   "Total Cease errors received"
        ::= { rcStatBgp 26 }

-- Header
rcStatBgpRxHdrCodeNoSync OBJECT-TYPE
        SYNTAX        Counter32
        MAX-ACCESS    read-only
        STATUS        current
        DESCRIPTION   "Header  Not Synchronized errors received"
        ::= { rcStatBgp 27 }

rcStatBgpRxHdrCodeInvalidMsgLen OBJECT-TYPE
        SYNTAX        Counter32
        MAX-ACCESS    read-only
        STATUS        current
        DESCRIPTION   "Header Invalid msg len errors received"
        ::= { rcStatBgp 28 }

rcStatBgpRxHdrCodeInvalidMsgType OBJECT-TYPE
        SYNTAX        Counter32
        MAX-ACCESS    read-only
        STATUS        current
        DESCRIPTION   "Header Invalid msg type errors received"
        ::= { rcStatBgp 29 }


-- Open
rcStatBgpRxOpCodeBadVer OBJECT-TYPE
        SYNTAX        Counter32
        MAX-ACCESS    read-only
        STATUS        current
        DESCRIPTION   "Open errors received: Bad Version"
        ::= { rcStatBgp 30 }

rcStatBgpRxOpCodeBadAs OBJECT-TYPE
        SYNTAX        Counter32
        MAX-ACCESS    read-only
        STATUS        current
        DESCRIPTION   "Open errors received: Bad AS Number"
        ::= { rcStatBgp 31 }

rcStatBgpRxOpCodeBadRtID OBJECT-TYPE
        SYNTAX        Counter32
        MAX-ACCESS    read-only
        STATUS        current
        DESCRIPTION   "Open errors received: Bad BGP Rtr ID"
        ::= { rcStatBgp 32 }

rcStatBgpRxOpCodeUnsuppOption OBJECT-TYPE
        SYNTAX        Counter32
        MAX-ACCESS    read-only
        STATUS        current
        DESCRIPTION   "Open errors received: Unsupported Option"
        ::= { rcStatBgp 33 }

rcStatBgpRxOpCodeAuthFail OBJECT-TYPE
        SYNTAX        Counter32
        MAX-ACCESS    read-only
        STATUS        current
        DESCRIPTION   "Open errors received: Auth Failures"
        ::= { rcStatBgp 34 }

rcStatBgpRxOpCodeBadHold OBJECT-TYPE
        SYNTAX        Counter32
        MAX-ACCESS    read-only
        STATUS        current
        DESCRIPTION   "Open errors received: Bad Hold Value"
        ::= { rcStatBgp 35 }

-- Update

rcStatBgpRxUpdCodeMalformedAttrList OBJECT-TYPE
        SYNTAX        Counter32
        MAX-ACCESS    read-only
        STATUS        current
        DESCRIPTION   "Update errors received:Malformed Attr List"
        ::= { rcStatBgp 36 }

rcStatBgpRxUpdCodeWelknownAttrUnrecog OBJECT-TYPE
        SYNTAX        Counter32
        MAX-ACCESS    read-only
        STATUS        current
        DESCRIPTION   "Update errors received: Welknown Attr Unrecog"
        ::= { rcStatBgp 37 }

rcStatBgpRxUpdCodeWelknownAttrMiss OBJECT-TYPE
        SYNTAX        Counter32
        MAX-ACCESS    read-only
        STATUS        current
        DESCRIPTION   "Update errors received: Welknown Attr Missing"
        ::= { rcStatBgp 38 }

rcStatBgpRxUpdCodeAttrFlagError OBJECT-TYPE
        SYNTAX        Counter32
        MAX-ACCESS    read-only
        STATUS        current
        DESCRIPTION   "Update errors received: Attr Flag Error"
        ::= { rcStatBgp 39 }

rcStatBgpRxUpdCodeAttrLenError OBJECT-TYPE
        SYNTAX        Counter32
        MAX-ACCESS    read-only
        STATUS        current
        DESCRIPTION   "Update errors received: Attr Len Error"
        ::= { rcStatBgp 40 }

rcStatBgpRxUpdCodeBadORIGINAttr OBJECT-TYPE
        SYNTAX        Counter32
        MAX-ACCESS    read-only
        STATUS        current
        DESCRIPTION   "Update errors received: Bad ORIGIN Attr"
        ::= { rcStatBgp 41 }

rcStatBgpRxUpdCodeASRoutingLoop OBJECT-TYPE
        SYNTAX        Counter32
        MAX-ACCESS    read-only
        STATUS        current
        DESCRIPTION   "Update errors received: AS Routing Loop"
        ::= { rcStatBgp 42 }

rcStatBgpRxUpdCodeBadNHAttr OBJECT-TYPE
        SYNTAX        Counter32
        MAX-ACCESS    read-only
        STATUS        current
        DESCRIPTION   "Update errors received: Bad NEXT-HOP Attr"
        ::= { rcStatBgp 43 }

rcStatBgpRxUpdCodeOptionalAttrError OBJECT-TYPE
        SYNTAX        Counter32
        MAX-ACCESS    read-only
        STATUS        current
        DESCRIPTION   "Update errors received: Optional Attr Error"
        ::= { rcStatBgp 44 }

rcStatBgpRxUpdCodeBadNetworkField OBJECT-TYPE
        SYNTAX        Counter32
        MAX-ACCESS    read-only
        STATUS        current
        DESCRIPTION   "Update errors received: Bad Network Field"
        ::= { rcStatBgp 45 }

rcStatBgpRxUpdCodeMalformedASPath OBJECT-TYPE
        SYNTAX        Counter32
        MAX-ACCESS    read-only
        STATUS        current
        DESCRIPTION   "Update errors received: Malformed AS Path"
        ::= { rcStatBgp 46 }

-- Tx
rcStatBgpTxECodeHeader OBJECT-TYPE
        SYNTAX        Counter32 
        MAX-ACCESS    read-only
        STATUS        current
        DESCRIPTION   "Total Header errors transmitted"
        ::= { rcStatBgp 47 }

rcStatBgpTxECodeOpen OBJECT-TYPE
        SYNTAX        Counter32 
        MAX-ACCESS    read-only
        STATUS        current
        DESCRIPTION   "Total Open errors transmitted"
        ::= { rcStatBgp 48 }

rcStatBgpTxECodeUpdate OBJECT-TYPE
        SYNTAX        Counter32 
        MAX-ACCESS    read-only
        STATUS        current
        DESCRIPTION   "Total Update errors transmitted"
        ::= { rcStatBgp 49 }

rcStatBgpTxECodeHoldtimer OBJECT-TYPE
        SYNTAX        Counter32 
        MAX-ACCESS    read-only
        STATUS        current
        DESCRIPTION   "Total Holdtimer errors transmitted"
        ::= { rcStatBgp 50 }

rcStatBgpTxECodeFSM OBJECT-TYPE
        SYNTAX        Counter32 
        MAX-ACCESS    read-only
        STATUS        current
        DESCRIPTION   "Total FSM errors transmitted"
        ::= { rcStatBgp 51 }

rcStatBgpTxECodeCease OBJECT-TYPE
        SYNTAX        Counter32 
        MAX-ACCESS    read-only
        STATUS        current
        DESCRIPTION   "Total Cease errors transmitted"
        ::= { rcStatBgp 52 }

-- Header
rcStatBgpTxHdrCodeNoSync OBJECT-TYPE
        SYNTAX        Counter32 
        MAX-ACCESS    read-only
        STATUS        current
        DESCRIPTION   "Header  Not Synchronized errors transmitted"
        ::= { rcStatBgp 53 }

rcStatBgpTxHdrCodeInvalidMsgLen OBJECT-TYPE
        SYNTAX        Counter32
        MAX-ACCESS    read-only
        STATUS        current
        DESCRIPTION   "Header Invalid msg len errors transmitted"
        ::= { rcStatBgp 54 }

rcStatBgpTxHdrCodeInvalidMsgType OBJECT-TYPE
        SYNTAX        Counter32
        MAX-ACCESS    read-only
        STATUS        current
        DESCRIPTION   "Header Invalid msg type errors transmitted"
        ::= { rcStatBgp 55 }


-- Open
rcStatBgpTxOpCodeBadVer OBJECT-TYPE
        SYNTAX        Counter32 
        MAX-ACCESS    read-only
        STATUS        current
        DESCRIPTION   "Open errors transmitted: Bad Version"
        ::= { rcStatBgp 56 }

rcStatBgpTxOpCodeBadAs OBJECT-TYPE
        SYNTAX        Counter32
        MAX-ACCESS    read-only
        STATUS        current
        DESCRIPTION   "Open errors transmitted: Bad AS Number"
        ::= { rcStatBgp 57 }

rcStatBgpTxOpCodeBadRtID OBJECT-TYPE
        SYNTAX        Counter32
        MAX-ACCESS    read-only
        STATUS        current
        DESCRIPTION   "Open errors transmitted: Bad BGP Rtr ID"
        ::= { rcStatBgp 58 }

rcStatBgpTxOpCodeUnsuppOption OBJECT-TYPE
        SYNTAX        Counter32
        MAX-ACCESS    read-only
        STATUS        current
        DESCRIPTION   "Open errors transmitted: Unsupported Option"
        ::= { rcStatBgp 59 }

rcStatBgpTxOpCodeAuthFail OBJECT-TYPE
        SYNTAX        Counter32
        MAX-ACCESS    read-only
        STATUS        current
        DESCRIPTION   "Open errors transmitted: Auth Failures"
        ::= { rcStatBgp 60 }

rcStatBgpTxOpCodeBadHold OBJECT-TYPE
        SYNTAX        Counter32
        MAX-ACCESS    read-only
        STATUS        current
        DESCRIPTION   "Open errors transmitted: Bad Hold Value"
        ::= { rcStatBgp 61 }

-- Update

rcStatBgpTxUpdCodeMalformedAttrList OBJECT-TYPE
        SYNTAX        Counter32 
        MAX-ACCESS    read-only
        STATUS        current
        DESCRIPTION   "Update errors transmitted:Malformed Attr List"
		::= { rcStatBgp 62 } 

rcStatBgpTxUpdCodeWelknownAttrUnrecog OBJECT-TYPE
        SYNTAX        Counter32
        MAX-ACCESS    read-only
        STATUS        current
        DESCRIPTION   "Update errors transmitted: Welknown Attr Unrecog"
        ::= { rcStatBgp 63 }

rcStatBgpTxUpdCodeWelknownAttrMiss OBJECT-TYPE
        SYNTAX        Counter32
        MAX-ACCESS    read-only
        STATUS        current
        DESCRIPTION   "Update errors transmitted: Welknown Attr Missing"
        ::= { rcStatBgp 64 }

rcStatBgpTxUpdCodeAttrFlagError OBJECT-TYPE
        SYNTAX        Counter32
        MAX-ACCESS    read-only
        STATUS        current
        DESCRIPTION   "Update errors transmitted: Attr Flag Error"
        ::= { rcStatBgp 65 }

rcStatBgpTxUpdCodeAttrLenError OBJECT-TYPE
        SYNTAX        Counter32
        MAX-ACCESS    read-only
        STATUS        current
        DESCRIPTION   "Update errors transmitted: Attr Len Error"
        ::= { rcStatBgp 66 }

rcStatBgpTxUpdCodeBadORIGINAttr OBJECT-TYPE
        SYNTAX        Counter32
        MAX-ACCESS    read-only
        STATUS        current
        DESCRIPTION   "Update errors transmitted: Bad ORIGIN Attr"
        ::= { rcStatBgp 67 }

rcStatBgpTxUpdCodeASRoutingLoop OBJECT-TYPE
        SYNTAX        Counter32
        MAX-ACCESS    read-only
        STATUS        current
        DESCRIPTION   "Update errors transmitted: AS Routing Loop"
        ::= { rcStatBgp 68 }

rcStatBgpTxUpdCodeBadNHAttr OBJECT-TYPE
        SYNTAX        Counter32
        MAX-ACCESS    read-only
        STATUS        current
        DESCRIPTION   "Update errors transmitted: Bad NEXT-HOP Attr"
        ::= { rcStatBgp 69 }

rcStatBgpTxUpdCodeOptionalAttrError OBJECT-TYPE
        SYNTAX        Counter32
        MAX-ACCESS    read-only
        STATUS        current
        DESCRIPTION   "Update errors transmitted: Optional Attr Error"
        ::= { rcStatBgp 70 }

rcStatBgpTxUpdCodeBadNetworkField OBJECT-TYPE
        SYNTAX        Counter32
        MAX-ACCESS    read-only
        STATUS        current
        DESCRIPTION   "Update errors transmitted: Bad Network Field"
        ::= { rcStatBgp 71 }

rcStatBgpTxUpdCodeMalformedASPath OBJECT-TYPE
        SYNTAX        Counter32
        MAX-ACCESS    read-only
        STATUS        current
        DESCRIPTION   "Update errors transmitted: Malformed AS Path"
        ::= { rcStatBgp 72 }

rcStatBgpReset OBJECT-TYPE
        SYNTAX        EnableValue
        MAX-ACCESS    read-write
        STATUS        current
        DESCRIPTION   "reset Bgp global stats"
        DEFVAL          {disable}
        ::= { rcStatBgp 73 }

-- BGP Peer Stats

rcStatBgpPeerTable OBJECT-TYPE
        SYNTAX        SEQUENCE OF RcStatBgpPeerEntry
        MAX-ACCESS    not-accessible
        STATUS        current
        DESCRIPTION   "A table used to store Bgp Peer statistics."
        ::= { rcStat 11 }

rcStatBgpPeerEntry OBJECT-TYPE
        SYNTAX        RcStatBgpPeerEntry
        MAX-ACCESS    not-accessible
        STATUS        current
        DESCRIPTION   "Bgp Peer statistics"
        INDEX         { rcStatBgpPeerAddr }
        ::= { rcStatBgpPeerTable 1 }

RcStatBgpPeerEntry ::= SEQUENCE {
         rcStatBgpPeerAddr                           IpAddress,
         rcStatBgpPeerStarts                         Counter32,
         rcStatBgpPeerStops                          Counter32,
         rcStatBgpPeerOpens                          Counter32,
         rcStatBgpPeerCloses                         Counter32,
         rcStatBgpPeerFails                          Counter32,
         rcStatBgpPeerFatals                         Counter32,
         rcStatBgpPeerConnExps                       Counter32,
         rcStatBgpPeerHoldExps                       Counter32,
         rcStatBgpPeerKeepExps                       Counter32,
         rcStatBgpPeerTxMsgs                         Counter32,
         rcStatBgpPeerTxOpens                        Counter32,
         rcStatBgpPeerTxKeeps                        Counter32,
         rcStatBgpPeerTxUpdates                      Counter32,
         rcStatBgpPeerTxNotifys                      Counter32,
         rcStatBgpPeerRxMsgs                         Counter32,
         rcStatBgpPeerRxInCompPkts                   Counter32,
         rcStatBgpPeerRxOpens                        Counter32,
         rcStatBgpPeerRxKeeps                        Counter32,
         rcStatBgpPeerRxUpdates                      Counter32,
         rcStatBgpPeerRxNotifys                      Counter32,
         rcStatBgpPeerBadEvents                      Counter32,
         rcStatBgpPeerSyncFails                      Counter32,
         rcStatBgpPeerRcvdTooShort                   Counter32,
         rcStatBgpPeerNoMarker                       Counter32,
         rcStatBgpPeerDropped                        Counter32,
         rcStatBgpPeerBadMsgTypes                    Counter32,
         rcStatBgpPeerTrEvent                        Counter32,
         rcStatBgpPeerTxRoutes                       Counter32,
         rcStatBgpPeerRxRoutesAdded                  Counter32,
         rcStatBgpPeerRxRoutesReplaced               Counter32,
         rcStatBgpPeerRxNlri                         Counter32,
         rcStatBgpPeerRxValidUpdates                 Counter32,
-- Rx
         rcStatBgpPeerRxECodeHeader                  Counter32,
         rcStatBgpPeerRxECodeOpen                    Counter32,
         rcStatBgpPeerRxECodeUpdate                  Counter32,
         rcStatBgpPeerRxECodeHoldtimer               Counter32,
         rcStatBgpPeerRxECodeFSM                     Counter32,
         rcStatBgpPeerRxECodeCease                   Counter32,
         rcStatBgpPeerRxHdrCodeNoSync                Counter32,
         rcStatBgpPeerRxHdrCodeInvalidMsgLen         Counter32,
         rcStatBgpPeerRxHdrCodeInvalidMsgType        Counter32,
         rcStatBgpPeerRxOpCodeBadVer                 Counter32,
         rcStatBgpPeerRxOpCodeBadAs                  Counter32,
         rcStatBgpPeerRxOpCodeBadRtID                Counter32,
         rcStatBgpPeerRxOpCodeUnsuppOption           Counter32,
         rcStatBgpPeerRxOpCodeAuthFail               Counter32,
         rcStatBgpPeerRxOpCodeBadHold                Counter32,
         rcStatBgpPeerRxUpdCodeMalformedAttrList     Counter32,
         rcStatBgpPeerRxUpdCodeWelknownAttrUnrecog   Counter32,
         rcStatBgpPeerRxUpdCodeWelknownAttrMiss      Counter32,
         rcStatBgpPeerRxUpdCodeAttrFlagError         Counter32,
         rcStatBgpPeerRxUpdCodeAttrLenError          Counter32,
         rcStatBgpPeerRxUpdCodeBadORIGINAttr         Counter32,
         rcStatBgpPeerRxUpdCodeASRoutingLoop         Counter32,
         rcStatBgpPeerRxUpdCodeBadNHAttr             Counter32,
         rcStatBgpPeerRxUpdCodeOptionalAttrError     Counter32,
         rcStatBgpPeerRxUpdCodeBadNetworkField       Counter32,
         rcStatBgpPeerRxUpdCodeMalformedASPath       Counter32,
-- Tx
         rcStatBgpPeerTxECodeHeader                  Counter32,
         rcStatBgpPeerTxECodeOpen                    Counter32,
         rcStatBgpPeerTxECodeUpdate                  Counter32,
         rcStatBgpPeerTxECodeHoldtimer               Counter32,
         rcStatBgpPeerTxECodeFSM                     Counter32,
         rcStatBgpPeerTxECodeCease                   Counter32,
         rcStatBgpPeerTxHdrCodeNoSync                Counter32,
         rcStatBgpPeerTxHdrCodeInvalidMsgLen         Counter32,
         rcStatBgpPeerTxHdrCodeInvalidMsgType        Counter32,
         rcStatBgpPeerTxOpCodeBadVer                 Counter32,
         rcStatBgpPeerTxOpCodeBadAs                  Counter32,
         rcStatBgpPeerTxOpCodeBadRtID                Counter32,
         rcStatBgpPeerTxOpCodeUnsuppOption           Counter32,
         rcStatBgpPeerTxOpCodeAuthFail               Counter32,
         rcStatBgpPeerTxOpCodeBadHold                Counter32,
         rcStatBgpPeerTxUpdCodeMalformedAttrList     Counter32,
         rcStatBgpPeerTxUpdCodeWelknownAttrUnrecog   Counter32,
         rcStatBgpPeerTxUpdCodeWelknownAttrMiss      Counter32,
         rcStatBgpPeerTxUpdCodeAttrFlagError         Counter32,
         rcStatBgpPeerTxUpdCodeAttrLenError          Counter32,
         rcStatBgpPeerTxUpdCodeBadORIGINAttr         Counter32,
         rcStatBgpPeerTxUpdCodeASRoutingLoop         Counter32,
         rcStatBgpPeerTxUpdCodeBadNHAttr             Counter32,
         rcStatBgpPeerTxUpdCodeOptionalAttrError     Counter32,
         rcStatBgpPeerTxUpdCodeBadNetworkField       Counter32,
         rcStatBgpPeerTxUpdCodeMalformedASPath       Counter32,
         rcStatBgpPeerReset                          EnableValue

        }

rcStatBgpPeerAddr        OBJECT-TYPE
         SYNTAX         IpAddress
         MAX-ACCESS     read-only
         STATUS         current
         DESCRIPTION    ""
                ::= { rcStatBgpPeerEntry 1 }

rcStatBgpPeerStarts        OBJECT-TYPE
         SYNTAX         Counter32
         MAX-ACCESS     read-only
         STATUS         current
         DESCRIPTION    "Number of times peer BGP connection started"
                ::= { rcStatBgpPeerEntry 2 }

rcStatBgpPeerStops         OBJECT-TYPE
         SYNTAX         Counter32
         MAX-ACCESS     read-only
         STATUS         current
         DESCRIPTION    "Number of times peer BGP connection stopped"
         ::= { rcStatBgpPeerEntry 3 }

rcStatBgpPeerOpens         OBJECT-TYPE
         SYNTAX         Counter32
         MAX-ACCESS     read-only
         STATUS         current
         DESCRIPTION    "Number of times peer opens TCP"
         ::= { rcStatBgpPeerEntry 4 }

rcStatBgpPeerCloses        OBJECT-TYPE
         SYNTAX         Counter32
         MAX-ACCESS     read-only
         STATUS         current
         DESCRIPTION    "Number of times peer closes TCP"
         ::= { rcStatBgpPeerEntry 5 }

rcStatBgpPeerFails         OBJECT-TYPE
         SYNTAX         Counter32
         MAX-ACCESS     read-only
         STATUS         current
         DESCRIPTION    "Number of times peer TCP attempts failed"
         ::= { rcStatBgpPeerEntry 6 }

rcStatBgpPeerFatals        OBJECT-TYPE
         SYNTAX         Counter32
         MAX-ACCESS     read-only
         STATUS         current
         DESCRIPTION    "Number of times peer TCP crashes due to fatal error"
         ::= { rcStatBgpPeerEntry 7 }

rcStatBgpPeerConnExps      OBJECT-TYPE
         SYNTAX         Counter32
         MAX-ACCESS     read-only
         STATUS         current
         DESCRIPTION    "Number of times peer TCP retry timer expired"
         ::= { rcStatBgpPeerEntry 8 }

rcStatBgpPeerHoldExps      OBJECT-TYPE
         SYNTAX         Counter32
         MAX-ACCESS     read-only
         STATUS         current
         DESCRIPTION    "Number of times peer hold timer expired"
         ::= { rcStatBgpPeerEntry 9 }

rcStatBgpPeerKeepExps      OBJECT-TYPE
         SYNTAX         Counter32
         MAX-ACCESS     read-only
         STATUS         current
         DESCRIPTION    "Number of times peer keepalive timer expired"
         ::= { rcStatBgpPeerEntry 10 }

rcStatBgpPeerTxMsgs        OBJECT-TYPE
         SYNTAX         Counter32
         MAX-ACCESS     read-only
         STATUS         current
         DESCRIPTION    "Total messages send by the peer"
         ::= { rcStatBgpPeerEntry 11 }

rcStatBgpPeerTxOpens       OBJECT-TYPE
         SYNTAX         Counter32
         MAX-ACCESS     read-only
         STATUS         current
         DESCRIPTION    "Opens sent by the peer"
         ::= { rcStatBgpPeerEntry 12 }

rcStatBgpPeerTxKeeps       OBJECT-TYPE
         SYNTAX         Counter32
         MAX-ACCESS     read-only
         STATUS         current
         DESCRIPTION    "Keepalives sent by the peer"
         ::= { rcStatBgpPeerEntry 13 }

rcStatBgpPeerTxUpdates     OBJECT-TYPE
         SYNTAX         Counter32
         MAX-ACCESS     read-only
         STATUS         current
         DESCRIPTION    "Updates sent by the peer"
         ::= { rcStatBgpPeerEntry 14 }

rcStatBgpPeerTxNotifys     OBJECT-TYPE
         SYNTAX         Counter32
         MAX-ACCESS     read-only
         STATUS         current
         DESCRIPTION    "Notifications sent by the peer"
         ::= { rcStatBgpPeerEntry 15 }

rcStatBgpPeerRxMsgs        OBJECT-TYPE
         SYNTAX         Counter32
         MAX-ACCESS     read-only
         STATUS         current
         DESCRIPTION    "Total messages received by the peer"
         ::= { rcStatBgpPeerEntry 16 }

rcStatBgpPeerRxInCompPkts  OBJECT-TYPE
         SYNTAX         Counter32
         MAX-ACCESS     read-only
         STATUS         current
         DESCRIPTION    "Incomplete message received by the peer"
         ::= { rcStatBgpPeerEntry 17 }

rcStatBgpPeerRxOpens       OBJECT-TYPE
         SYNTAX         Counter32
         MAX-ACCESS     read-only
         STATUS         current
         DESCRIPTION    "Opens received by the peer"
         ::= { rcStatBgpPeerEntry 18 }

rcStatBgpPeerRxKeeps       OBJECT-TYPE
         SYNTAX         Counter32
         MAX-ACCESS     read-only
         STATUS         current
         DESCRIPTION    "Keepalives received by the peer"
         ::= { rcStatBgpPeerEntry 19 }

rcStatBgpPeerRxUpdates     OBJECT-TYPE
         SYNTAX         Counter32
         MAX-ACCESS     read-only
         STATUS         current
         DESCRIPTION    "Updates received by the peer"
         ::= { rcStatBgpPeerEntry 20 }

rcStatBgpPeerRxNotifys     OBJECT-TYPE
         SYNTAX         Counter32
         MAX-ACCESS     read-only
         STATUS         current
         DESCRIPTION    "Notifications received by the peer"
         ::= { rcStatBgpPeerEntry 21 }

rcStatBgpPeerBadEvents     OBJECT-TYPE
         SYNTAX         Counter32
         MAX-ACCESS     read-only
         STATUS         current
         DESCRIPTION    "Number of invalid events received by the peer"
         ::= { rcStatBgpPeerEntry 22 }

rcStatBgpPeerSyncFails     OBJECT-TYPE
         SYNTAX         Counter32
         MAX-ACCESS     read-only
         STATUS         current
         DESCRIPTION    "Number of times FDB sync failed of the peer"
         ::= { rcStatBgpPeerEntry 23 }

rcStatBgpPeerRcvdTooShort  OBJECT-TYPE
         SYNTAX         Counter32
         MAX-ACCESS     read-only
         STATUS         current
         DESCRIPTION    "Number of messages recieved by the peer that is too sho
rt"
         ::= { rcStatBgpPeerEntry 24 }

rcStatBgpPeerNoMarker      OBJECT-TYPE
         SYNTAX         Counter32
         MAX-ACCESS     read-only
         STATUS         current
         DESCRIPTION    "Number of messages without marker recieved by the peer"
         ::= { rcStatBgpPeerEntry 25 }

rcStatBgpPeerDropped       OBJECT-TYPE
         SYNTAX         Counter32
         MAX-ACCESS     read-only
         STATUS         current
         DESCRIPTION    "Number of messages the peer has dropped"
         ::= { rcStatBgpPeerEntry 26 }

rcStatBgpPeerBadMsgTypes   OBJECT-TYPE
         SYNTAX         Counter32
         MAX-ACCESS     read-only
         STATUS         current
         DESCRIPTION    "Number of messages with invalid message type"
         ::= { rcStatBgpPeerEntry 27 }

rcStatBgpPeerTrEvent       OBJECT-TYPE
         SYNTAX         Counter32
         MAX-ACCESS     read-only
         STATUS         current
         DESCRIPTION    "Peer trace event"
         ::= { rcStatBgpPeerEntry 28 }

rcStatBgpPeerTxRoutes      OBJECT-TYPE
         SYNTAX         Counter32
         MAX-ACCESS     read-only
         STATUS         current
         DESCRIPTION    "Number of NLRI sent by peer"
         ::= { rcStatBgpPeerEntry 29 }

rcStatBgpPeerRxRoutesAdded         OBJECT-TYPE
         SYNTAX         Counter32
         MAX-ACCESS     read-only
         STATUS         current
         DESCRIPTION    "Number of routes added into loc_rib by this peer"
         ::= { rcStatBgpPeerEntry 30 }

rcStatBgpPeerRxRoutesReplaced      OBJECT-TYPE
         SYNTAX         Counter32
         MAX-ACCESS     read-only
         STATUS         current
         DESCRIPTION    "Number of routes replaced by the routes received by the
 peer"
         ::= { rcStatBgpPeerEntry 31 }

rcStatBgpPeerRxNlri        OBJECT-TYPE
         SYNTAX         Counter32
         MAX-ACCESS     read-only
         STATUS         current
         DESCRIPTION    "Number of NLRI received by the peer"
         ::= { rcStatBgpPeerEntry 32 }

rcStatBgpPeerRxValidUpdates        OBJECT-TYPE
         SYNTAX         Counter32
         MAX-ACCESS     read-only
         STATUS         current
         DESCRIPTION    "Number of valid UPDATEs received by the peer"
         ::= { rcStatBgpPeerEntry 33 }

rcStatBgpPeerRxECodeHeader       OBJECT-TYPE
         SYNTAX          Counter32
         MAX-ACCESS     read-only
         STATUS         current
         DESCRIPTION    "Total errors peer received: Header"
         ::= { rcStatBgpPeerEntry 34 }

rcStatBgpPeerRxECodeOpen       OBJECT-TYPE
         SYNTAX          Counter32
         MAX-ACCESS     read-only
         STATUS         current
         DESCRIPTION    "Total errors peer received: Open"
         ::= { rcStatBgpPeerEntry 35 }

rcStatBgpPeerRxECodeUpdate       OBJECT-TYPE
         SYNTAX          Counter32
         MAX-ACCESS     read-only
         STATUS         current
         DESCRIPTION    "Total errors peer received: Update"
         ::= { rcStatBgpPeerEntry 36 }

rcStatBgpPeerRxECodeHoldtimer       OBJECT-TYPE
         SYNTAX          Counter32
         MAX-ACCESS     read-only
         STATUS         current
         DESCRIPTION    "Total errors peer received: Hold"
         ::= { rcStatBgpPeerEntry 37 }

rcStatBgpPeerRxECodeFSM       OBJECT-TYPE
         SYNTAX          Counter32
         MAX-ACCESS     read-only
         STATUS         current
         DESCRIPTION    "Total errors peer received: Fsm"
         ::= { rcStatBgpPeerEntry 38 }

rcStatBgpPeerRxECodeCease       OBJECT-TYPE
         SYNTAX          Counter32
         MAX-ACCESS     read-only
         STATUS         current
         DESCRIPTION    "Total errors peer received: Cease"
         ::= { rcStatBgpPeerEntry 39 }

rcStatBgpPeerRxHdrCodeNoSync     OBJECT-TYPE
         SYNTAX         Counter32
         MAX-ACCESS     read-only
         STATUS         current
         DESCRIPTION    "Header errors peer received: Not Synchronized"
         ::= { rcStatBgpPeerEntry 40 }

rcStatBgpPeerRxHdrCodeInvalidMsgLen     OBJECT-TYPE
         SYNTAX         Counter32
         MAX-ACCESS     read-only
         STATUS         current
         DESCRIPTION    "Header errors peer received: Invalid message length"
         ::= { rcStatBgpPeerEntry 41 }

rcStatBgpPeerRxHdrCodeInvalidMsgType     OBJECT-TYPE
         SYNTAX         Counter32
         MAX-ACCESS     read-only
         STATUS         current
         DESCRIPTION    "Header errors peer received: Invalid message type"
         ::= { rcStatBgpPeerEntry 42 }

rcStatBgpPeerRxOpCodeBadVer      OBJECT-TYPE
         SYNTAX         Counter32
         MAX-ACCESS     read-only
         STATUS         current
         DESCRIPTION    "Open errors peer received: Bad Version"
         ::= { rcStatBgpPeerEntry 43 }

rcStatBgpPeerRxOpCodeBadAs      OBJECT-TYPE
         SYNTAX         Counter32
         MAX-ACCESS     read-only
         STATUS         current
         DESCRIPTION    "Open errors peer received: Bad AS number"
         ::= { rcStatBgpPeerEntry 44 }

rcStatBgpPeerRxOpCodeBadRtID      OBJECT-TYPE
         SYNTAX         Counter32
         MAX-ACCESS     read-only
         STATUS         current
         DESCRIPTION    "Open errors peer received: Bad BGP ID"
         ::= { rcStatBgpPeerEntry 45 }

rcStatBgpPeerRxOpCodeUnsuppOption      OBJECT-TYPE
         SYNTAX         Counter32
         MAX-ACCESS     read-only
         STATUS         current
         DESCRIPTION    "Open errors peer received: Unsupported Options"
         ::= { rcStatBgpPeerEntry 46 }

rcStatBgpPeerRxOpCodeAuthFail      OBJECT-TYPE
         SYNTAX         Counter32
         MAX-ACCESS     read-only
         STATUS         current
         DESCRIPTION    "Open errors peer received: Authorization failures"
         ::= { rcStatBgpPeerEntry 47 }

rcStatBgpPeerRxOpCodeBadHold      OBJECT-TYPE
         SYNTAX         Counter32
         MAX-ACCESS     read-only
         STATUS         current
         DESCRIPTION    "Open errors peer received: Bad Hold value"
         ::= { rcStatBgpPeerEntry 48 }

rcStatBgpPeerRxUpdCodeMalformedAttrList     OBJECT-TYPE
         SYNTAX         Counter32
         MAX-ACCESS     read-only
         STATUS         current
         DESCRIPTION    "Update errors peer received: Malformed Attr List"
         ::= { rcStatBgpPeerEntry 49 }

rcStatBgpPeerRxUpdCodeWelknownAttrUnrecog     OBJECT-TYPE
         SYNTAX         Counter32
         MAX-ACCESS     read-only
         STATUS         current
         DESCRIPTION    "Update errors peer received: Malformed Attr List"
         ::= { rcStatBgpPeerEntry 50 }

rcStatBgpPeerRxUpdCodeWelknownAttrMiss     OBJECT-TYPE
         SYNTAX         Counter32
         MAX-ACCESS     read-only
         STATUS         current
         DESCRIPTION    "Update errors peer received: Malformed Attr List"
         ::= { rcStatBgpPeerEntry 51 }

rcStatBgpPeerRxUpdCodeAttrFlagError     OBJECT-TYPE
         SYNTAX         Counter32
         MAX-ACCESS     read-only
         STATUS         current
         DESCRIPTION    "Update errors peer received: Malformed Attr List"
         ::= { rcStatBgpPeerEntry 52 }

rcStatBgpPeerRxUpdCodeAttrLenError     OBJECT-TYPE
         SYNTAX         Counter32
         MAX-ACCESS     read-only
         STATUS         current
         DESCRIPTION    "Update errors peer received: Malformed Attr List"
         ::= { rcStatBgpPeerEntry 53 }

rcStatBgpPeerRxUpdCodeBadORIGINAttr     OBJECT-TYPE
         SYNTAX         Counter32
         MAX-ACCESS     read-only
         STATUS         current
         DESCRIPTION    "Update errors peer received: Malformed Attr List"
         ::= { rcStatBgpPeerEntry 54 }

rcStatBgpPeerRxUpdCodeASRoutingLoop     OBJECT-TYPE
         SYNTAX         Counter32
         MAX-ACCESS     read-only
         STATUS         current
         DESCRIPTION    "Update errors peer received: Malformed Attr List"
         ::= { rcStatBgpPeerEntry 55 }

rcStatBgpPeerRxUpdCodeBadNHAttr     OBJECT-TYPE
         SYNTAX         Counter32
         MAX-ACCESS     read-only
         STATUS         current
         DESCRIPTION    "Update errors peer received: Malformed Attr List"
         ::= { rcStatBgpPeerEntry 56 }

rcStatBgpPeerRxUpdCodeOptionalAttrError     OBJECT-TYPE
         SYNTAX         Counter32
         MAX-ACCESS     read-only
         STATUS         current
         DESCRIPTION    "Update errors peer received: Malformed Attr List"
         ::= { rcStatBgpPeerEntry 57 }

rcStatBgpPeerRxUpdCodeBadNetworkField     OBJECT-TYPE
         SYNTAX         Counter32
         MAX-ACCESS     read-only
         STATUS         current
         DESCRIPTION    "Update errors peer received: Malformed Attr List"
         ::= { rcStatBgpPeerEntry 58 }

rcStatBgpPeerRxUpdCodeMalformedASPath     OBJECT-TYPE
         SYNTAX         Counter32
         MAX-ACCESS     read-only
         STATUS         current
         DESCRIPTION    "Update errors peer received: Malformed Attr List"
         ::= { rcStatBgpPeerEntry 59 }

rcStatBgpPeerTxECodeHeader       OBJECT-TYPE
         SYNTAX          Counter32
         MAX-ACCESS     read-only
         STATUS         current
         DESCRIPTION    "Total errors peer received: Header"
         ::= { rcStatBgpPeerEntry 60 }

rcStatBgpPeerTxECodeOpen       OBJECT-TYPE
         SYNTAX          Counter32
         MAX-ACCESS     read-only
         STATUS         current
         DESCRIPTION    "Total errors peer received: Open"
         ::= { rcStatBgpPeerEntry 61 }

rcStatBgpPeerTxECodeUpdate       OBJECT-TYPE
         SYNTAX          Counter32
         MAX-ACCESS     read-only
         STATUS         current
         DESCRIPTION    "Total errors peer received: Update"
         ::= { rcStatBgpPeerEntry 62 }

rcStatBgpPeerTxECodeHoldtimer       OBJECT-TYPE
         SYNTAX          Counter32
         MAX-ACCESS     read-only
         STATUS         current
         DESCRIPTION    "Total errors peer received: Hold"
         ::= { rcStatBgpPeerEntry 63 }

rcStatBgpPeerTxECodeFSM       OBJECT-TYPE
         SYNTAX          Counter32
         MAX-ACCESS     read-only
         STATUS         current
         DESCRIPTION    "Total errors peer received: Fsm"
         ::= { rcStatBgpPeerEntry 64 }

rcStatBgpPeerTxECodeCease       OBJECT-TYPE
         SYNTAX          Counter32
         MAX-ACCESS     read-only
         STATUS         current
         DESCRIPTION    "Total errors peer received: Cease"
         ::= { rcStatBgpPeerEntry 65 }

rcStatBgpPeerTxHdrCodeNoSync     OBJECT-TYPE
         SYNTAX         Counter32
         MAX-ACCESS     read-only
         STATUS         current
         DESCRIPTION    "Header errors peer received: Not Synchronized"
         ::= { rcStatBgpPeerEntry 66 }

rcStatBgpPeerTxHdrCodeInvalidMsgLen     OBJECT-TYPE
         SYNTAX         Counter32
         MAX-ACCESS     read-only
         STATUS         current
         DESCRIPTION    "Header errors peer received: Invalid message length"
         ::= { rcStatBgpPeerEntry 67 }

rcStatBgpPeerTxHdrCodeInvalidMsgType     OBJECT-TYPE
         SYNTAX         Counter32
         MAX-ACCESS     read-only
         STATUS         current
         DESCRIPTION    "Header errors peer received: Invalid message type"
         ::= { rcStatBgpPeerEntry 68 }

rcStatBgpPeerTxOpCodeBadVer      OBJECT-TYPE
         SYNTAX         Counter32
         MAX-ACCESS     read-only
         STATUS         current
         DESCRIPTION    "Open errors peer received: Bad Version"
         ::= { rcStatBgpPeerEntry 69 }

rcStatBgpPeerTxOpCodeBadAs      OBJECT-TYPE
         SYNTAX         Counter32
         MAX-ACCESS     read-only
         STATUS         current
         DESCRIPTION    "Open errors peer received: Bad AS number"
         ::= { rcStatBgpPeerEntry 70 }

rcStatBgpPeerTxOpCodeBadRtID      OBJECT-TYPE
         SYNTAX         Counter32
         MAX-ACCESS     read-only
         STATUS         current
         DESCRIPTION    "Open errors peer received: Bad BGP ID"
         ::= { rcStatBgpPeerEntry 71 }

rcStatBgpPeerTxOpCodeUnsuppOption      OBJECT-TYPE
         SYNTAX         Counter32
         MAX-ACCESS     read-only
         STATUS         current
         DESCRIPTION    "Open errors peer received: Unsupported Options"
         ::= { rcStatBgpPeerEntry 72 }

rcStatBgpPeerTxOpCodeAuthFail      OBJECT-TYPE
         SYNTAX         Counter32
         MAX-ACCESS     read-only
         STATUS         current
         DESCRIPTION    "Open errors peer received: Authorization failures"
         ::= { rcStatBgpPeerEntry 73 }

rcStatBgpPeerTxOpCodeBadHold      OBJECT-TYPE
         SYNTAX         Counter32
         MAX-ACCESS     read-only
         STATUS         current
         DESCRIPTION    "Open errors peer received: Bad Hold value"
         ::= { rcStatBgpPeerEntry 74 }

rcStatBgpPeerTxUpdCodeMalformedAttrList     OBJECT-TYPE
         SYNTAX         Counter32
         MAX-ACCESS     read-only
         STATUS         current
         DESCRIPTION    "Update errors peer received: Malformed Attr List"
         ::= { rcStatBgpPeerEntry 75 }

rcStatBgpPeerTxUpdCodeWelknownAttrUnrecog     OBJECT-TYPE
         SYNTAX         Counter32
         MAX-ACCESS     read-only
         STATUS         current
         DESCRIPTION    "Update errors peer received: Malformed Attr List"
         ::= { rcStatBgpPeerEntry 76 }

rcStatBgpPeerTxUpdCodeWelknownAttrMiss     OBJECT-TYPE
         SYNTAX         Counter32
         MAX-ACCESS     read-only
         STATUS         current
         DESCRIPTION    "Update errors peer received: Malformed Attr List"
         ::= { rcStatBgpPeerEntry 77 }

rcStatBgpPeerTxUpdCodeAttrFlagError     OBJECT-TYPE
         SYNTAX         Counter32
         MAX-ACCESS     read-only
         STATUS         current
         DESCRIPTION    "Update errors peer received: Malformed Attr List"
         ::= { rcStatBgpPeerEntry 78 }

rcStatBgpPeerTxUpdCodeAttrLenError     OBJECT-TYPE
         SYNTAX         Counter32
         MAX-ACCESS     read-only
         STATUS         current
         DESCRIPTION    "Update errors peer received: Malformed Attr List"
         ::= { rcStatBgpPeerEntry 79 }

rcStatBgpPeerTxUpdCodeBadORIGINAttr     OBJECT-TYPE
         SYNTAX         Counter32
         MAX-ACCESS     read-only
         STATUS         current
         DESCRIPTION    "Update errors peer received: Malformed Attr List"
         ::= { rcStatBgpPeerEntry 80 }

rcStatBgpPeerTxUpdCodeASRoutingLoop     OBJECT-TYPE
         SYNTAX         Counter32
         MAX-ACCESS     read-only
         STATUS         current
         DESCRIPTION    "Update errors peer received: Malformed Attr List"
         ::= { rcStatBgpPeerEntry 81 }

rcStatBgpPeerTxUpdCodeBadNHAttr     OBJECT-TYPE
         SYNTAX         Counter32
         MAX-ACCESS     read-only
         STATUS         current
         DESCRIPTION    "Update errors peer received: Malformed Attr List"
         ::= { rcStatBgpPeerEntry 82 }

rcStatBgpPeerTxUpdCodeOptionalAttrError     OBJECT-TYPE
         SYNTAX         Counter32
         MAX-ACCESS     read-only
         STATUS         current
         DESCRIPTION    "Update errors peer received: Malformed Attr List"
         ::= { rcStatBgpPeerEntry 83 }

rcStatBgpPeerTxUpdCodeBadNetworkField     OBJECT-TYPE
         SYNTAX         Counter32
         MAX-ACCESS     read-only
         STATUS         current
         DESCRIPTION    "Update errors peer received: Malformed Attr List"
         ::= { rcStatBgpPeerEntry 84 }

rcStatBgpPeerTxUpdCodeMalformedASPath     OBJECT-TYPE
         SYNTAX         Counter32
         MAX-ACCESS     read-only
         STATUS         current
         DESCRIPTION    "Update errors peer received: Malformed Attr List"
         ::= { rcStatBgpPeerEntry 85 }

rcStatBgpPeerReset OBJECT-TYPE
        SYNTAX        EnableValue
        MAX-ACCESS    read-write
        STATUS        current
        DESCRIPTION   "reset peer stats"
        DEFVAL          {disable}
        ::= { rcStatBgpPeerEntry 86 }

-- Address Family Independent BGP Peer Stats

rcStatBgpPeerAfTable OBJECT-TYPE
        SYNTAX        SEQUENCE OF RcStatBgpPeerAfEntry
        MAX-ACCESS    not-accessible
        STATUS        current
        DESCRIPTION   "A table used to store v4/v6 Bgp Peer statistics."
        ::= { rcStat 13 }

rcStatBgpPeerAfEntry OBJECT-TYPE
        SYNTAX        RcStatBgpPeerAfEntry
        MAX-ACCESS    not-accessible
        STATUS        current
        DESCRIPTION   "AF independent Bgp Peer statistics"
        INDEX         { rcStatBgpPeerAfAddrType,
                        rcStatBgpPeerAfAddr }
        ::= { rcStatBgpPeerAfTable 1 }

RcStatBgpPeerAfEntry ::= SEQUENCE {
         rcStatBgpPeerAfAddrType                       InetAddressType,
         rcStatBgpPeerAfAddr                           InetAddress,
         rcStatBgpPeerAfStarts                         Counter32,
         rcStatBgpPeerAfStops                          Counter32,
         rcStatBgpPeerAfOpens                          Counter32,
         rcStatBgpPeerAfCloses                         Counter32,
         rcStatBgpPeerAfFails                          Counter32,
         rcStatBgpPeerAfFatals                         Counter32,
         rcStatBgpPeerAfConnExps                       Counter32,
         rcStatBgpPeerAfHoldExps                       Counter32,
         rcStatBgpPeerAfKeepExps                       Counter32,
         rcStatBgpPeerAfTxMsgs                         Counter32,
         rcStatBgpPeerAfTxOpens                        Counter32,
         rcStatBgpPeerAfTxKeeps                        Counter32,
         rcStatBgpPeerAfTxUpdates                      Counter32,
         rcStatBgpPeerAfTxNotifys                      Counter32,
         rcStatBgpPeerAfRxMsgs                         Counter32,
         rcStatBgpPeerAfRxInCompPkts                   Counter32,
         rcStatBgpPeerAfRxOpens                        Counter32,
         rcStatBgpPeerAfRxKeeps                        Counter32,
         rcStatBgpPeerAfRxUpdates                      Counter32,
         rcStatBgpPeerAfRxNotifys                      Counter32,
         rcStatBgpPeerAfBadEvents                      Counter32,
         rcStatBgpPeerAfSyncFails                      Counter32,
         rcStatBgpPeerAfRcvdTooShort                   Counter32,
         rcStatBgpPeerAfNoMarker                       Counter32,
         rcStatBgpPeerAfDropped                        Counter32,
         rcStatBgpPeerAfBadMsgTypes                    Counter32,
         rcStatBgpPeerAfTrEvent                        Counter32,
         rcStatBgpPeerAfTxRoutes                       Counter32,
         rcStatBgpPeerAfRxRoutesAdded                  Counter32,
         rcStatBgpPeerAfRxRoutesReplaced               Counter32,
         rcStatBgpPeerAfRxNlri                         Counter32,
         rcStatBgpPeerAfRxValidUpdates                 Counter32,
-- Rx
         rcStatBgpPeerAfRxECodeHeader                  Counter32,
         rcStatBgpPeerAfRxECodeOpen                    Counter32,
         rcStatBgpPeerAfRxECodeUpdate                  Counter32,
         rcStatBgpPeerAfRxECodeHoldtimer               Counter32,
         rcStatBgpPeerAfRxECodeFSM                     Counter32,
         rcStatBgpPeerAfRxECodeCease                   Counter32,
         rcStatBgpPeerAfRxHdrCodeNoSync                Counter32,
         rcStatBgpPeerAfRxHdrCodeInvalidMsgLen         Counter32,
         rcStatBgpPeerAfRxHdrCodeInvalidMsgType        Counter32,
         rcStatBgpPeerAfRxOpCodeBadVer                 Counter32,
         rcStatBgpPeerAfRxOpCodeBadAs                  Counter32,
         rcStatBgpPeerAfRxOpCodeBadRtID                Counter32,
         rcStatBgpPeerAfRxOpCodeUnsuppOption           Counter32,
         rcStatBgpPeerAfRxOpCodeAuthFail               Counter32,
         rcStatBgpPeerAfRxOpCodeBadHold                Counter32,
         rcStatBgpPeerAfRxUpdCodeMalformedAttrList     Counter32,
         rcStatBgpPeerAfRxUpdCodeWelknownAttrUnrecog   Counter32,
         rcStatBgpPeerAfRxUpdCodeWelknownAttrMiss      Counter32,
         rcStatBgpPeerAfRxUpdCodeAttrFlagError         Counter32,
         rcStatBgpPeerAfRxUpdCodeAttrLenError          Counter32,
         rcStatBgpPeerAfRxUpdCodeBadORIGINAttr         Counter32,
         rcStatBgpPeerAfRxUpdCodeASRoutingLoop         Counter32,
         rcStatBgpPeerAfRxUpdCodeBadNHAttr             Counter32,
         rcStatBgpPeerAfRxUpdCodeOptionalAttrError     Counter32,
         rcStatBgpPeerAfRxUpdCodeBadNetworkField       Counter32,
         rcStatBgpPeerAfRxUpdCodeMalformedASPath       Counter32,
-- Tx
         rcStatBgpPeerAfTxECodeHeader                  Counter32,
         rcStatBgpPeerAfTxECodeOpen                    Counter32,
         rcStatBgpPeerAfTxECodeUpdate                  Counter32,
         rcStatBgpPeerAfTxECodeHoldtimer               Counter32,
         rcStatBgpPeerAfTxECodeFSM                     Counter32,
         rcStatBgpPeerAfTxECodeCease                   Counter32,
         rcStatBgpPeerAfTxHdrCodeNoSync                Counter32,
         rcStatBgpPeerAfTxHdrCodeInvalidMsgLen         Counter32,
         rcStatBgpPeerAfTxHdrCodeInvalidMsgType        Counter32,
         rcStatBgpPeerAfTxOpCodeBadVer                 Counter32,
         rcStatBgpPeerAfTxOpCodeBadAs                  Counter32,
         rcStatBgpPeerAfTxOpCodeBadRtID                Counter32,
         rcStatBgpPeerAfTxOpCodeUnsuppOption           Counter32,
         rcStatBgpPeerAfTxOpCodeAuthFail               Counter32,
         rcStatBgpPeerAfTxOpCodeBadHold                Counter32,
         rcStatBgpPeerAfTxUpdCodeMalformedAttrList     Counter32,
         rcStatBgpPeerAfTxUpdCodeWelknownAttrUnrecog   Counter32,
         rcStatBgpPeerAfTxUpdCodeWelknownAttrMiss      Counter32,
         rcStatBgpPeerAfTxUpdCodeAttrFlagError         Counter32,
         rcStatBgpPeerAfTxUpdCodeAttrLenError          Counter32,
         rcStatBgpPeerAfTxUpdCodeBadORIGINAttr         Counter32,
         rcStatBgpPeerAfTxUpdCodeASRoutingLoop         Counter32,
         rcStatBgpPeerAfTxUpdCodeBadNHAttr             Counter32,
         rcStatBgpPeerAfTxUpdCodeOptionalAttrError     Counter32,
         rcStatBgpPeerAfTxUpdCodeBadNetworkField       Counter32,
         rcStatBgpPeerAfTxUpdCodeMalformedASPath       Counter32,
         rcStatBgpPeerAfReset                          TruthValue

        }

rcStatBgpPeerAfAddrType OBJECT-TYPE
         SYNTAX         InetAddressType
         MAX-ACCESS     not-accessible
         STATUS         current
         DESCRIPTION    "Inet address type of the AF independent peer"
                ::= { rcStatBgpPeerAfEntry 1 }

rcStatBgpPeerAfAddr        OBJECT-TYPE
         SYNTAX         InetAddress
         MAX-ACCESS     not-accessible
         STATUS         current
         DESCRIPTION    "Inet address of the AF independent peer"
                ::= { rcStatBgpPeerAfEntry 2 }

rcStatBgpPeerAfStarts        OBJECT-TYPE
         SYNTAX         Counter32
         MAX-ACCESS     read-only
         STATUS         current
         DESCRIPTION    "Number of times peer BGP connection started"
                ::= { rcStatBgpPeerAfEntry 3 }

rcStatBgpPeerAfStops         OBJECT-TYPE
         SYNTAX         Counter32
         MAX-ACCESS     read-only
         STATUS         current
         DESCRIPTION    "Number of times peer BGP connection stopped"
         ::= { rcStatBgpPeerAfEntry 4 }

rcStatBgpPeerAfOpens         OBJECT-TYPE
         SYNTAX         Counter32
         MAX-ACCESS     read-only
         STATUS         current
         DESCRIPTION    "Number of times peer opens TCP"
         ::= { rcStatBgpPeerAfEntry 5 }

rcStatBgpPeerAfCloses        OBJECT-TYPE
         SYNTAX         Counter32
         MAX-ACCESS     read-only
         STATUS         current
         DESCRIPTION    "Number of times peer closes TCP"
         ::= { rcStatBgpPeerAfEntry 6 }

rcStatBgpPeerAfFails         OBJECT-TYPE
         SYNTAX         Counter32
         MAX-ACCESS     read-only
         STATUS         current
         DESCRIPTION    "Number of times peer TCP attempts failed"
         ::= { rcStatBgpPeerAfEntry 7 }

rcStatBgpPeerAfFatals        OBJECT-TYPE
         SYNTAX         Counter32
         MAX-ACCESS     read-only
         STATUS         current
         DESCRIPTION    "Number of times peer TCP crashes due to fatal error"
         ::= { rcStatBgpPeerAfEntry 8 }

rcStatBgpPeerAfConnExps      OBJECT-TYPE
         SYNTAX         Counter32
         MAX-ACCESS     read-only
         STATUS         current
         DESCRIPTION    "Number of times peer TCP retry timer expired"
         ::= { rcStatBgpPeerAfEntry 9 }

rcStatBgpPeerAfHoldExps      OBJECT-TYPE
         SYNTAX         Counter32
         MAX-ACCESS     read-only
         STATUS         current
         DESCRIPTION    "Number of times peer hold timer expired"
         ::= { rcStatBgpPeerAfEntry 10 }

rcStatBgpPeerAfKeepExps      OBJECT-TYPE
         SYNTAX         Counter32
         MAX-ACCESS     read-only
         STATUS         current
         DESCRIPTION    "Number of times peer keepalive timer expired"
         ::= { rcStatBgpPeerAfEntry 11 }
rcStatBgpPeerAfTxMsgs        OBJECT-TYPE
         SYNTAX         Counter32
         MAX-ACCESS     read-only
         STATUS         current
         DESCRIPTION    "Total messages send by the peer"
        ::= { rcStatBgpPeerAfEntry 12 }

rcStatBgpPeerAfTxOpens       OBJECT-TYPE
         SYNTAX         Counter32
         MAX-ACCESS     read-only
         STATUS         current
         DESCRIPTION    "Opens sent by the peer"
         ::= { rcStatBgpPeerAfEntry 13 }

rcStatBgpPeerAfTxKeeps       OBJECT-TYPE
         SYNTAX         Counter32
         MAX-ACCESS     read-only
         STATUS         current
         DESCRIPTION    "Keepalives sent by the peer"
         ::= { rcStatBgpPeerAfEntry 14 }

rcStatBgpPeerAfTxUpdates     OBJECT-TYPE
         SYNTAX         Counter32
         MAX-ACCESS     read-only
         STATUS         current
         DESCRIPTION    "Updates sent by the peer"
         ::= { rcStatBgpPeerAfEntry 15 }

rcStatBgpPeerAfTxNotifys     OBJECT-TYPE
         SYNTAX         Counter32
         MAX-ACCESS     read-only
         STATUS         current
         DESCRIPTION    "Notifications sent by the peer"
         ::= { rcStatBgpPeerAfEntry 16 }

rcStatBgpPeerAfRxMsgs        OBJECT-TYPE
         SYNTAX         Counter32
         MAX-ACCESS     read-only
         STATUS         current
         DESCRIPTION    "Total messages received by the peer"
         ::= { rcStatBgpPeerAfEntry 17 }

rcStatBgpPeerAfRxInCompPkts  OBJECT-TYPE
         SYNTAX         Counter32
         MAX-ACCESS     read-only
         STATUS         current
         DESCRIPTION    "Incomplete message received by the peer"
         ::= { rcStatBgpPeerAfEntry 18 }

rcStatBgpPeerAfRxOpens       OBJECT-TYPE
         SYNTAX         Counter32
         MAX-ACCESS     read-only
         STATUS         current
         DESCRIPTION    "Opens received by the peer"
         ::= { rcStatBgpPeerAfEntry 19 }

rcStatBgpPeerAfRxKeeps       OBJECT-TYPE
         SYNTAX         Counter32
         MAX-ACCESS     read-only
         STATUS         current
         DESCRIPTION    "Keepalives received by the peer"
         ::= { rcStatBgpPeerAfEntry 20 }

rcStatBgpPeerAfRxUpdates     OBJECT-TYPE
         SYNTAX         Counter32
         MAX-ACCESS     read-only
         STATUS         current
         DESCRIPTION    "Updates received by the peer"
         ::= { rcStatBgpPeerAfEntry 21 }

rcStatBgpPeerAfRxNotifys     OBJECT-TYPE
         SYNTAX         Counter32
         MAX-ACCESS     read-only
         STATUS         current
         DESCRIPTION    "Notifications received by the peer"
         ::= { rcStatBgpPeerAfEntry 22 }

rcStatBgpPeerAfBadEvents     OBJECT-TYPE
         SYNTAX         Counter32
         MAX-ACCESS     read-only
         STATUS         current
         DESCRIPTION    "Number of invalid events received by the peer"
         ::= { rcStatBgpPeerAfEntry 23 } 

rcStatBgpPeerAfSyncFails     OBJECT-TYPE
         SYNTAX         Counter32
         MAX-ACCESS     read-only
         STATUS         current
         DESCRIPTION    "Number of times FDB sync failed of the peer"
         ::= { rcStatBgpPeerAfEntry 24 } 

rcStatBgpPeerAfRcvdTooShort  OBJECT-TYPE
         SYNTAX         Counter32
         MAX-ACCESS     read-only
         STATUS         current
         DESCRIPTION    "Number of messages recieved by the peer that is too sho
rt"
         ::= { rcStatBgpPeerAfEntry 25 }

rcStatBgpPeerAfNoMarker      OBJECT-TYPE
         SYNTAX         Counter32
         MAX-ACCESS     read-only
         STATUS         current
         DESCRIPTION    "Number of messages without marker recieved by the peer"
         ::= { rcStatBgpPeerAfEntry 26 }

rcStatBgpPeerAfDropped       OBJECT-TYPE
         SYNTAX         Counter32
         MAX-ACCESS     read-only
         STATUS         current
         DESCRIPTION    "Number of messages the peer has dropped"
         ::= { rcStatBgpPeerAfEntry 27 }

rcStatBgpPeerAfBadMsgTypes   OBJECT-TYPE
         SYNTAX         Counter32
         MAX-ACCESS     read-only
         STATUS         current
         DESCRIPTION    "Number of messages with invalid message type"
         ::= { rcStatBgpPeerAfEntry 28 }

rcStatBgpPeerAfTrEvent       OBJECT-TYPE
         SYNTAX         Counter32
         MAX-ACCESS     read-only
         STATUS         current
         DESCRIPTION    "Peer trace event"
         ::= { rcStatBgpPeerAfEntry 29 }

rcStatBgpPeerAfTxRoutes      OBJECT-TYPE
         SYNTAX         Counter32
         MAX-ACCESS     read-only
         STATUS         current
         DESCRIPTION    "Number of NLRI sent by peer"
         ::= { rcStatBgpPeerAfEntry 30 }

rcStatBgpPeerAfRxRoutesAdded         OBJECT-TYPE
         SYNTAX         Counter32
         MAX-ACCESS     read-only
         STATUS         current
         DESCRIPTION    "Number of routes added into loc_rib by this peer"
         ::= { rcStatBgpPeerAfEntry 31 }

rcStatBgpPeerAfRxRoutesReplaced      OBJECT-TYPE
         SYNTAX         Counter32
         MAX-ACCESS     read-only
         STATUS         current
         DESCRIPTION    "Number of routes replaced by the routes received by the
 peer"
         ::= { rcStatBgpPeerAfEntry 32 }

rcStatBgpPeerAfRxNlri        OBJECT-TYPE
         SYNTAX         Counter32
         MAX-ACCESS     read-only
         STATUS         current
         DESCRIPTION    "Number of NLRI received by the peer"
         ::= { rcStatBgpPeerAfEntry 33 }

rcStatBgpPeerAfRxValidUpdates        OBJECT-TYPE
         SYNTAX         Counter32
         MAX-ACCESS     read-only
         STATUS         current
         DESCRIPTION    "Number of valid UPDATEs received by the peer"
         ::= { rcStatBgpPeerAfEntry 34 }

rcStatBgpPeerAfRxECodeHeader       OBJECT-TYPE
         SYNTAX          Counter32
         MAX-ACCESS     read-only
         STATUS         current
         DESCRIPTION    "Total errors peer received: Header"
         ::= { rcStatBgpPeerAfEntry 35 }

rcStatBgpPeerAfRxECodeOpen       OBJECT-TYPE
         SYNTAX          Counter32
         MAX-ACCESS     read-only
         STATUS         current
         DESCRIPTION    "Total errors peer received: Open"
         ::= { rcStatBgpPeerAfEntry 36 }

rcStatBgpPeerAfRxECodeUpdate       OBJECT-TYPE
         SYNTAX          Counter32
         MAX-ACCESS     read-only
         STATUS         current
         DESCRIPTION    "Total errors peer received: Update"
         ::= { rcStatBgpPeerAfEntry 37 }

rcStatBgpPeerAfRxECodeHoldtimer       OBJECT-TYPE
         SYNTAX          Counter32
         MAX-ACCESS     read-only
         STATUS         current
         DESCRIPTION    "Total errors peer received: Hold"
         ::= { rcStatBgpPeerAfEntry 38 }

rcStatBgpPeerAfRxECodeFSM       OBJECT-TYPE
         SYNTAX          Counter32
         MAX-ACCESS     read-only
         STATUS         current
         DESCRIPTION    "Total errors peer received: Fsm"
         ::= { rcStatBgpPeerAfEntry 39 }

rcStatBgpPeerAfRxECodeCease       OBJECT-TYPE
         SYNTAX          Counter32
         MAX-ACCESS     read-only
         STATUS         current
         DESCRIPTION    "Total errors peer received: Cease"
         ::= { rcStatBgpPeerAfEntry 40 }

rcStatBgpPeerAfRxHdrCodeNoSync     OBJECT-TYPE
         SYNTAX         Counter32
         MAX-ACCESS     read-only
         STATUS         current
         DESCRIPTION    "Header errors peer received: Not Synchronized"
         ::= { rcStatBgpPeerAfEntry 41 }

rcStatBgpPeerAfRxHdrCodeInvalidMsgLen     OBJECT-TYPE
         SYNTAX         Counter32
         MAX-ACCESS     read-only
         STATUS         current 
         DESCRIPTION    "Header errors peer received: Invalid message length"
         ::= { rcStatBgpPeerAfEntry 42 }

rcStatBgpPeerAfRxHdrCodeInvalidMsgType     OBJECT-TYPE
         SYNTAX         Counter32
         MAX-ACCESS     read-only
         STATUS         current 
         DESCRIPTION    "Header errors peer received: Invalid message type"
         ::= { rcStatBgpPeerAfEntry 43 } 

rcStatBgpPeerAfRxOpCodeBadVer      OBJECT-TYPE
         SYNTAX         Counter32
         MAX-ACCESS     read-only
         STATUS         current
         DESCRIPTION    "Open errors peer received: Bad Version"
         ::= { rcStatBgpPeerAfEntry 44 }

rcStatBgpPeerAfRxOpCodeBadAs      OBJECT-TYPE
         SYNTAX         Counter32
         MAX-ACCESS     read-only
         STATUS         current
         DESCRIPTION    "Open errors peer received: Bad AS number"
         ::= { rcStatBgpPeerAfEntry 45 }

rcStatBgpPeerAfRxOpCodeBadRtID      OBJECT-TYPE
         SYNTAX         Counter32
         MAX-ACCESS     read-only
         STATUS         current
         DESCRIPTION    "Open errors peer received: Bad BGP ID"
         ::= { rcStatBgpPeerAfEntry 46 }

rcStatBgpPeerAfRxOpCodeUnsuppOption      OBJECT-TYPE
         SYNTAX         Counter32
         MAX-ACCESS     read-only
         STATUS         current
         DESCRIPTION    "Open errors peer received: Unsupported Options"
         ::= { rcStatBgpPeerAfEntry 47 }

rcStatBgpPeerAfRxOpCodeAuthFail      OBJECT-TYPE
         SYNTAX         Counter32
         MAX-ACCESS     read-only
         STATUS         current
         DESCRIPTION    "Open errors peer received: Authorization failures"
         ::= { rcStatBgpPeerAfEntry 48 }

rcStatBgpPeerAfRxOpCodeBadHold      OBJECT-TYPE
         SYNTAX         Counter32
         MAX-ACCESS     read-only
         STATUS         current
         DESCRIPTION    "Open errors peer received: Bad Hold value"
         ::= { rcStatBgpPeerAfEntry 49 }

rcStatBgpPeerAfRxUpdCodeMalformedAttrList     OBJECT-TYPE
         SYNTAX         Counter32
         MAX-ACCESS     read-only
         STATUS         current
         DESCRIPTION    "Update errors peer received: Malformed Attr List"
         ::= { rcStatBgpPeerAfEntry 50 }

rcStatBgpPeerAfRxUpdCodeWelknownAttrUnrecog     OBJECT-TYPE
         SYNTAX         Counter32
         MAX-ACCESS     read-only
         STATUS         current
         DESCRIPTION    "Update errors peer received: Malformed Attr List"
         ::= { rcStatBgpPeerAfEntry 51 }

rcStatBgpPeerAfRxUpdCodeWelknownAttrMiss     OBJECT-TYPE
         SYNTAX         Counter32
         MAX-ACCESS     read-only
         STATUS         current
         DESCRIPTION    "Update errors peer received: Malformed Attr List"
         ::= { rcStatBgpPeerAfEntry 52 }

rcStatBgpPeerAfRxUpdCodeAttrFlagError     OBJECT-TYPE
         SYNTAX         Counter32
         MAX-ACCESS     read-only
         STATUS         current
         DESCRIPTION    "Update errors peer received: Malformed Attr List"
         ::= { rcStatBgpPeerAfEntry 53 }

rcStatBgpPeerAfRxUpdCodeAttrLenError     OBJECT-TYPE
         SYNTAX         Counter32 
         MAX-ACCESS     read-only
         STATUS         current
         DESCRIPTION    "Update errors peer received: Malformed Attr List"
         ::= { rcStatBgpPeerAfEntry 54 }

rcStatBgpPeerAfRxUpdCodeBadORIGINAttr     OBJECT-TYPE
         SYNTAX         Counter32   
         MAX-ACCESS     read-only
         STATUS         current
         DESCRIPTION    "Update errors peer received: Malformed Attr List"
         ::= { rcStatBgpPeerAfEntry 55 }

rcStatBgpPeerAfRxUpdCodeASRoutingLoop     OBJECT-TYPE
         SYNTAX         Counter32
         MAX-ACCESS     read-only
         STATUS         current
         DESCRIPTION    "Update errors peer received: Malformed Attr List"
         ::= { rcStatBgpPeerAfEntry 56 }

rcStatBgpPeerAfRxUpdCodeBadNHAttr     OBJECT-TYPE
         SYNTAX         Counter32    
         MAX-ACCESS     read-only
         STATUS         current
         DESCRIPTION    "Update errors peer received: Malformed Attr List"
         ::= { rcStatBgpPeerAfEntry 57 }

rcStatBgpPeerAfRxUpdCodeOptionalAttrError     OBJECT-TYPE
         SYNTAX         Counter32   
         MAX-ACCESS     read-only
         STATUS         current
         DESCRIPTION    "Update errors peer received: Malformed Attr List"
         ::= { rcStatBgpPeerAfEntry 58 }

rcStatBgpPeerAfRxUpdCodeBadNetworkField     OBJECT-TYPE
         SYNTAX         Counter32
         MAX-ACCESS     read-only
         STATUS         current 
         DESCRIPTION    "Update errors peer received: Malformed Attr List"
         ::= { rcStatBgpPeerAfEntry 59 }

rcStatBgpPeerAfRxUpdCodeMalformedASPath     OBJECT-TYPE
         SYNTAX         Counter32
         MAX-ACCESS     read-only
         STATUS         current 
         DESCRIPTION    "Update errors peer received: Malformed Attr List"
         ::= { rcStatBgpPeerAfEntry 60 }

rcStatBgpPeerAfTxECodeHeader       OBJECT-TYPE
         SYNTAX          Counter32
         MAX-ACCESS     read-only
         STATUS         current 
         DESCRIPTION    "Total errors peer received: Header"
         ::= { rcStatBgpPeerAfEntry 61 }

rcStatBgpPeerAfTxECodeOpen       OBJECT-TYPE
         SYNTAX          Counter32
         MAX-ACCESS     read-only
         STATUS         current 
         DESCRIPTION    "Total errors peer received: Open"
         ::= { rcStatBgpPeerAfEntry 62 }

rcStatBgpPeerAfTxECodeUpdate       OBJECT-TYPE
         SYNTAX          Counter32
         MAX-ACCESS     read-only
         STATUS         current
         DESCRIPTION    "Total errors peer received: Update"
         ::= { rcStatBgpPeerAfEntry 63 }

rcStatBgpPeerAfTxECodeHoldtimer       OBJECT-TYPE
         SYNTAX          Counter32
         MAX-ACCESS     read-only
         STATUS         current
         DESCRIPTION    "Total errors peer received: Hold"
         ::= { rcStatBgpPeerAfEntry 64 }

rcStatBgpPeerAfTxECodeFSM       OBJECT-TYPE
         SYNTAX          Counter32
         MAX-ACCESS     read-only
         STATUS         current
         DESCRIPTION    "Total errors peer received: Fsm"
         ::= { rcStatBgpPeerAfEntry 65 }

rcStatBgpPeerAfTxECodeCease       OBJECT-TYPE
         SYNTAX          Counter32
         MAX-ACCESS     read-only
         STATUS         current
         DESCRIPTION    "Total errors peer received: Cease"
         ::= { rcStatBgpPeerAfEntry 66 }

rcStatBgpPeerAfTxHdrCodeNoSync     OBJECT-TYPE
         SYNTAX         Counter32
         MAX-ACCESS     read-only
         STATUS         current
         DESCRIPTION    "Header errors peer received: Not Synchronized"
         ::= { rcStatBgpPeerAfEntry 67 }

rcStatBgpPeerAfTxHdrCodeInvalidMsgLen     OBJECT-TYPE
         SYNTAX         Counter32
         MAX-ACCESS     read-only
         STATUS         current
         DESCRIPTION    "Header errors peer received: Invalid message length"
         ::= { rcStatBgpPeerAfEntry 68 }

rcStatBgpPeerAfTxHdrCodeInvalidMsgType     OBJECT-TYPE
         SYNTAX         Counter32
         MAX-ACCESS     read-only
         STATUS         current
         DESCRIPTION    "Header errors peer received: Invalid message type"
         ::= { rcStatBgpPeerAfEntry 69 }

rcStatBgpPeerAfTxOpCodeBadVer      OBJECT-TYPE
         SYNTAX         Counter32
         MAX-ACCESS     read-only
         STATUS         current
         DESCRIPTION    "Open errors peer received: Bad Version"
         ::= { rcStatBgpPeerAfEntry 70 }

rcStatBgpPeerAfTxOpCodeBadAs      OBJECT-TYPE
         SYNTAX         Counter32
         MAX-ACCESS     read-only
         STATUS         current
         DESCRIPTION    "Open errors peer received: Bad AS number"
         ::= { rcStatBgpPeerAfEntry 71 }

rcStatBgpPeerAfTxOpCodeBadRtID      OBJECT-TYPE
         SYNTAX         Counter32
         MAX-ACCESS     read-only
         STATUS         current
         DESCRIPTION    "Open errors peer received: Bad BGP ID"
         ::= { rcStatBgpPeerAfEntry 72 }

rcStatBgpPeerAfTxOpCodeUnsuppOption      OBJECT-TYPE
         SYNTAX         Counter32
         MAX-ACCESS     read-only
         STATUS         current
         DESCRIPTION    "Open errors peer received: Unsupported Options"
         ::= { rcStatBgpPeerAfEntry 73 }

rcStatBgpPeerAfTxOpCodeAuthFail      OBJECT-TYPE
         SYNTAX         Counter32
         MAX-ACCESS     read-only
         STATUS         current
         DESCRIPTION    "Open errors peer received: Authorization failures"
         ::= { rcStatBgpPeerAfEntry 74 }

rcStatBgpPeerAfTxOpCodeBadHold      OBJECT-TYPE
         SYNTAX         Counter32
         MAX-ACCESS     read-only
         STATUS         current
         DESCRIPTION    "Open errors peer received: Bad Hold value"
         ::= { rcStatBgpPeerAfEntry 75 }

rcStatBgpPeerAfTxUpdCodeMalformedAttrList     OBJECT-TYPE
         SYNTAX         Counter32  
         MAX-ACCESS     read-only
         STATUS         current 
         DESCRIPTION    "Update errors peer received: Malformed Attr List"
         ::= { rcStatBgpPeerAfEntry 76 }

rcStatBgpPeerAfTxUpdCodeWelknownAttrUnrecog     OBJECT-TYPE
         SYNTAX         Counter32
         MAX-ACCESS     read-only
         STATUS         current 
         DESCRIPTION    "Update errors peer received: Malformed Attr List"
         ::= { rcStatBgpPeerAfEntry 77 }

rcStatBgpPeerAfTxUpdCodeWelknownAttrMiss     OBJECT-TYPE
         SYNTAX         Counter32
         MAX-ACCESS     read-only
         STATUS         current 
         DESCRIPTION    "Update errors peer received: Malformed Attr List"
         ::= { rcStatBgpPeerAfEntry 78 }

rcStatBgpPeerAfTxUpdCodeAttrFlagError     OBJECT-TYPE
         SYNTAX         Counter32  
         MAX-ACCESS     read-only
         STATUS         current
         DESCRIPTION    "Update errors peer received: Malformed Attr List"
         ::= { rcStatBgpPeerAfEntry 79 }

rcStatBgpPeerAfTxUpdCodeAttrLenError     OBJECT-TYPE
         SYNTAX         Counter32 
         MAX-ACCESS     read-only
         STATUS         current
         DESCRIPTION    "Update errors peer received: Malformed Attr List"
         ::= { rcStatBgpPeerAfEntry 80 }

rcStatBgpPeerAfTxUpdCodeBadORIGINAttr     OBJECT-TYPE
         SYNTAX         Counter32
         MAX-ACCESS     read-only
         STATUS         current
         DESCRIPTION    "Update errors peer received: Malformed Attr List"
         ::= { rcStatBgpPeerAfEntry 81 }

rcStatBgpPeerAfTxUpdCodeASRoutingLoop     OBJECT-TYPE
         SYNTAX         Counter32
         MAX-ACCESS     read-only
         STATUS         current
         DESCRIPTION    "Update errors peer received: Malformed Attr List"
         ::= { rcStatBgpPeerAfEntry 82 }

rcStatBgpPeerAfTxUpdCodeBadNHAttr     OBJECT-TYPE
         SYNTAX         Counter32
         MAX-ACCESS     read-only
         STATUS         current
         DESCRIPTION    "Update errors peer received: Malformed Attr List"
         ::= { rcStatBgpPeerAfEntry 83 }

rcStatBgpPeerAfTxUpdCodeOptionalAttrError     OBJECT-TYPE
         SYNTAX         Counter32
         MAX-ACCESS     read-only
         STATUS         current
         DESCRIPTION    "Update errors peer received: Malformed Attr List"
         ::= { rcStatBgpPeerAfEntry 84 }

rcStatBgpPeerAfTxUpdCodeBadNetworkField     OBJECT-TYPE
         SYNTAX         Counter32
         MAX-ACCESS     read-only
         STATUS         current
         DESCRIPTION    "Update errors peer received: Malformed Attr List"
         ::= { rcStatBgpPeerAfEntry 85 }

rcStatBgpPeerAfTxUpdCodeMalformedASPath     OBJECT-TYPE
         SYNTAX         Counter32
         MAX-ACCESS     read-only
         STATUS         current
         DESCRIPTION    "Update errors peer received: Malformed Attr List"
         ::= { rcStatBgpPeerAfEntry 86 }

rcStatBgpPeerAfReset OBJECT-TYPE
        SYNTAX        TruthValue
        MAX-ACCESS    read-create
        STATUS        current
        DESCRIPTION   "reset peer stats"
        DEFVAL          {false}
        ::= { rcStatBgpPeerAfEntry 87 }

-- end of Statistics

-- Spanning Tree Group (STG)

rcStgMaxStgs OBJECT-TYPE
        SYNTAX        Integer32
        MAX-ACCESS    read-write
        STATUS        current
        DESCRIPTION   "The maximum number of spanning tree groups this
		      device can support concurrently."
        ::= { rcStg 1 }

rcStgNumStgs OBJECT-TYPE
        SYNTAX        Integer32
        MAX-ACCESS    read-only
        STATUS        current
        DESCRIPTION   "The number of spanning tree groups that are
		      currently defined."
        ::= { rcStg 2 }

rcStgUnassignedPorts OBJECT-TYPE
        SYNTAX        PortSet
        MAX-ACCESS    read-only
        STATUS        current
        DESCRIPTION   "A bitfield used to identify which ports in
                      the system currently not assigned to any STG.

                      The bitfield is 32 octets long representing 
                      ports 0 to 255 (inclusive)."
        ::= { rcStg 3 }


-- STG Table

rcStgTable OBJECT-TYPE
        SYNTAX        SEQUENCE OF RcStgEntry
        MAX-ACCESS    not-accessible
        STATUS        current
        DESCRIPTION   "A table used to store Spanning Tree Group (STG)
		      information.  Each row in the table specifies
		      a different STG in the device."
        ::= { rcStg 4 } 
 
rcStgEntry OBJECT-TYPE  
        SYNTAX        RcStgEntry
        MAX-ACCESS    not-accessible
        STATUS        current
        DESCRIPTION   "STG attributes"
        INDEX  { rcStgId }
        ::= { rcStgTable 1 }
 
RcStgEntry ::= SEQUENCE {
		rcStgId INTEGER,
		rcStgTaggedBpduAddress MacAddress,
		rcStgTaggedBpduVlanId Integer32,
		rcStgBridgeAddress MacAddress,
		rcStgNumPorts Integer32,
		rcStgProtocolSpecification INTEGER,
		rcStgPriority INTEGER,
		rcStgTimeSinceTopologyChange TimeTicks,
		rcStgTopChanges Counter32,
		rcStgDesignatedRoot BridgeId,
		rcStgRootCost Integer32,
		rcStgRootPort InterfaceIndex,
		rcStgMaxAge Timeout,
		rcStgHelloTime Timeout,
		rcStgHoldTime Integer32,
		rcStgForwardDelay Timeout,
		rcStgBridgeMaxAge Timeout,
		rcStgBridgeHelloTime Timeout,
		rcStgBridgeForwardDelay Timeout,
		rcStgEnableStp TruthValue,
		rcStgStpTrapEnable TruthValue,
		rcStgPortMembers OCTET STRING,
		rcStgRowStatus RowStatus,
		rcStgPortStpState OCTET STRING
        }

rcStgId OBJECT-TYPE 
        SYNTAX  	INTEGER (1..64)
        MAX-ACCESS  	read-only
        STATUS  	current
        DESCRIPTION 	"An identifier used to identify a STG in the device."
        ::= { rcStgEntry 1 }

rcStgTaggedBpduAddress OBJECT-TYPE
        SYNTAX  	MacAddress
        MAX-ACCESS  	read-write
        STATUS  	current
        DESCRIPTION 	"The MAC address to be assigned to the destination
      	       		mac address field in tagged BPDUs.  

	       		The default address is the well known multicast 
	       		group address 01-80-c2-00-00-00."
        DEFVAL          { "01:80:c2:00:00:00" }
  	::= { rcStgEntry 2 }

rcStgTaggedBpduVlanId OBJECT-TYPE 
        SYNTAX  	Integer32  
        MAX-ACCESS  	read-write 
        STATUS  	current  
        DESCRIPTION 	"The VLAN ID to be used for tagging BPDUs." 
        ::= { rcStgEntry 3 }

rcStgBridgeAddress OBJECT-TYPE
        SYNTAX  	MacAddress
        MAX-ACCESS  	read-only
        STATUS  	current
        DESCRIPTION 	"The MAC address used by this bridge when it must
		       	be referred to in a unique fashion.   It is
		       	recommended that this be the numerically smallest
		       	MAC address of all ports that belong to this
		       	bridge.  However it is only required to be unique.
		       	When concatenated with rcStgPriority a unique
		       	BridgeIdentifier is formed which is used in the
		       	Spanning Tree Protocol."
        REFERENCE 	"IEEE 802.1D-1990: Sections 6.4.1.1.3 and 3.12.5"
        ::= { rcStgEntry 4 }

rcStgNumPorts OBJECT-TYPE
        SYNTAX  	Integer32
        MAX-ACCESS  	read-only
        STATUS  	current
        DESCRIPTION 	"The number of ports controlled by this bridging entity."
        REFERENCE 	"IEEE 802.1D-1990: Section 6.4.1.1.3"
        ::= { rcStgEntry 5 }

rcStgProtocolSpecification OBJECT-TYPE
        SYNTAX  	INTEGER {
			      unknown(1),
			      decLb100(2),
			      ieee8021d(3)
		        }
        MAX-ACCESS  	read-only
        STATUS  	current
        DESCRIPTION 	"An indication of what version of the Spanning
                     	Tree Protocol is being run.  The value
                     	'decLb100(2)' indicates the DEC LANbridge 100
                     	Spanning Tree protocol.  IEEE 802.1d
                     	implementations will return 'ieee8021d(3)'.  If
                     	future versions of the IEEE Spanning Tree Protocol
                     	are released that are incompatible with the
                     	current version a new value will be defined."
        ::= { rcStgEntry 6 }

rcStgPriority OBJECT-TYPE
        SYNTAX  	INTEGER (0..65535)
        MAX-ACCESS  	read-write
        STATUS  	current
        DESCRIPTION 	"The value of the write-able portion of the Bridge
	      	       	ID, i.e., the first two octets of the (8 octet
      		       	long) Bridge ID.  The other (last) 6 octets of the
      	       		Bridge ID are given by the value of rcStgBridgeAddress."
        REFERENCE 	"IEEE 802.1D-1990: Section 4.5.3.7"
        DEFVAL          { 32768 }
        ::= { rcStgEntry 7 }

rcStgTimeSinceTopologyChange OBJECT-TYPE
        SYNTAX  	TimeTicks
        MAX-ACCESS  	read-only
        STATUS  	current
        DESCRIPTION 	"The time (in hundredths of a second) since the
	       		last time a topology change was detected by the
	       		bridge entity."
        REFERENCE 	"IEEE 802.1D-1990: Section 6.8.1.1.3"
        ::= { rcStgEntry 8 }

rcStgTopChanges OBJECT-TYPE
        SYNTAX  	Counter32
        MAX-ACCESS  	read-only
        STATUS  	current
        DESCRIPTION 	"The total number of topology changes detected by
	       		this bridge since the management entity was last
	       		reset or initialized."
        REFERENCE 	"IEEE 802.1D-1990: Section 6.8.1.1.3"
        ::= { rcStgEntry 9 }

rcStgDesignatedRoot OBJECT-TYPE
        SYNTAX  	BridgeId
        MAX-ACCESS  	read-only
        STATUS  	current
        DESCRIPTION 	"The bridge identifier of the root of the spanning
	       		tree as determined by the Spanning Tree Protocol
	       		as executed by this node.  This value is used as
                        the Root Identifier parameter in all Configuration
                        Bridge PDUs originated by this node."
        REFERENCE 	"IEEE 802.1D-1990: Section 4.5.3.1"
        ::= { rcStgEntry 10 }

rcStgRootCost OBJECT-TYPE
        SYNTAX  	Integer32
        MAX-ACCESS  	read-only
        STATUS  	current
        DESCRIPTION 	"The cost of the path to the root as seen from
	       		this bridge."
        REFERENCE 	"IEEE 802.1D-1990: Section 4.5.3.2"
        ::= { rcStgEntry 11 }

rcStgRootPort OBJECT-TYPE
        SYNTAX          InterfaceIndex	
        MAX-ACCESS  	read-only
        STATUS  	current
        DESCRIPTION 	"The port number of the port which offers the
	  		lowest cost path from this bridge to the root
               		bridge."
        REFERENCE 	"IEEE 802.1D-1990: Section 4.5.3.3"
        ::= { rcStgEntry 12 }

rcStgMaxAge OBJECT-TYPE
        SYNTAX  	Timeout
        MAX-ACCESS  	read-only
        STATUS  	current
        DESCRIPTION 	"The maximum age of Spanning Tree Protocol
	       		information learned from the network on any port
	       		before it is discarded, in units of hundredths of
	       		a second.  This is the actual value that this
	       		bridge is currently using."
        REFERENCE 	"IEEE 802.1D-1990: Section 4.5.3.4"
        ::= { rcStgEntry 13 }

rcStgHelloTime OBJECT-TYPE
        SYNTAX  	Timeout
        MAX-ACCESS  	read-only
        STATUS  	current
        DESCRIPTION 	"The amount of time between the transmission of
	       		Configuration bridge PDUs by this node on any port
	       		when it is the root of the spanning tree or trying
	       		to become so, in units of hundredths of a second.
	       		This is the actual value that this bridge is
                        currently using."
        REFERENCE 	"IEEE 802.1D-1990: Section 4.5.3.5"
        ::= { rcStgEntry 14 }

rcStgHoldTime OBJECT-TYPE
        SYNTAX  	Integer32
        MAX-ACCESS  	read-only
        STATUS  	current
        DESCRIPTION     "This time value determines the interval length
	                during which no more than two Configuration bridge
	                PDUs shall be transmitted by this node, in units
	             	of hundredths of a second."
        REFERENCE 	"IEEE 802.1D-1990: Section 4.5.3.14"
        ::= { rcStgEntry 15 }

rcStgForwardDelay OBJECT-TYPE
        SYNTAX  	Timeout
        MAX-ACCESS  	read-only
        STATUS  	current
        DESCRIPTION 	"This time value, measured in units of hundredths
	             	of a second, controls how fast a port changes its
	             	spanning state when moving towards the Forwarding
	             	state.  The value determines how long the port
	             	stays in each of the Listening and Learning
	             	states, which precede the Forwarding state.  This
	             	value is also used, when a topology change has
	             	been detected and is underway, to age all dynamic
	             	entries in the Forwarding Database.  [Note that
	             	this value is the one that this bridge is
	             	currently using, in contrast to
	             	rcStgBridgeForwardDelay which is the value that
	             	this bridge and all others would start using
	             	if/when this bridge were to become the root.]"
        REFERENCE 	"IEEE 802.1D-1990: Section 4.5.3.6"
        ::= { rcStgEntry 16 }

rcStgBridgeMaxAge OBJECT-TYPE
        SYNTAX  	Timeout (600..4000)
        MAX-ACCESS  	read-write
        STATUS  	current
        DESCRIPTION 	"The value that all bridges use for MaxAge when
	             	this bridge is acting as the root.  Note that
	             	802.1D-1990 specifies that the range for this
	             	parameter is related to the value of
	             	rcStgBridgeHelloTime. The granularity of this
	             	timer is specified by 802.1D-1990 to be 1 second.
	             	An agent may return a badValue error if a set is
	             	attempted to a value which is not a whole number
	             	of seconds."
        REFERENCE 	"IEEE 802.1D-1990: Section 4.5.3.8"
        DEFVAL          { 2000 }
        ::= { rcStgEntry 17 }

rcStgBridgeHelloTime OBJECT-TYPE
        SYNTAX  	Timeout (100..1000)
        MAX-ACCESS  	read-write
        STATUS  	current
        DESCRIPTION 	"The value that all bridges use for HelloTime when
	             	this bridge is acting as the root.  The
	             	granularity of this timer is specified by 802.1D-
	             	1990 to be 1 second.  An agent may return a
	             	badValue error if a set is attempted to a value
	             	which is not a whole number of seconds."
        REFERENCE 	"IEEE 802.1D-1990: Section 4.5.3.9"
        DEFVAL          { 200 }
        ::= { rcStgEntry 18 }

rcStgBridgeForwardDelay OBJECT-TYPE
        SYNTAX  	Timeout (400..3000)
        MAX-ACCESS  	read-write
        STATUS  	current
        DESCRIPTION 	"The value that all bridges use for ForwardDelay
	             	when this bridge is acting as the root.  Note that
	             	802.1D-1990 specifies that the range for this
	             	parameter is related to the value of
	             	rcStgBridgeMaxAge.  The granularity of this
	             	timer is specified by 802.1D-1990 to be 1 second.
	             	An agent may return a badValue error if a set is
	             	attempted to a value which is not a whole number
	             	of seconds."
        REFERENCE 	"IEEE 802.1D-1990: Section 4.5.3.10"
        DEFVAL          { 1500 }
        ::= { rcStgEntry 19 }

rcStgEnableStp OBJECT-TYPE
        SYNTAX  	TruthValue
        MAX-ACCESS  	read-write
        STATUS  	current
        DESCRIPTION 	"Indicate whether the spanning tree protocol 
	       		should be active in this STG."
        DEFVAL         { true }
        ::= { rcStgEntry 20 }

rcStgStpTrapEnable OBJECT-TYPE
        SYNTAX 	 	TruthValue
        MAX-ACCESS  	read-write
        STATUS  	current
        DESCRIPTION 	"Indicate whether traps relating to the spanning
	       		tree protocol should be sent for this STG."
        DEFVAL         { true }
        ::= { rcStgEntry 21 }

rcStgPortMembers OBJECT-TYPE
        SYNTAX          OCTET STRING (SIZE(0..104))
        MAX-ACCESS      read-write
        STATUS          current
        DESCRIPTION     "A bitfield used to identify which ports in
		   	the system are members this STG.

		   	The bitfield is 104 octets long representing
		   	ports 64 (1/1) to 831 (12/68)  (inclusive)."
        ::= { rcStgEntry 22 }

rcStgRowStatus OBJECT-TYPE
        SYNTAX  	RowStatus
        MAX-ACCESS  	read-write
        STATUS  	current
        DESCRIPTION 	"Row status."
        ::= { rcStgEntry 23 }

rcStgPortStpState OBJECT-TYPE
        SYNTAX          OCTET STRING (SIZE(208))
        MAX-ACCESS      read-only
        STATUS          current
        DESCRIPTION     "Every 2 bitfields used to identify a port state
                        in this STG. Port state is cataloged as non-stp(0),
                        blocking(1), learning(2), and forwarding(3)."
        ::= { rcStgEntry 24 }


-- STG Port Table

rcStgPortTable OBJECT-TYPE
        SYNTAX        SEQUENCE OF RcStgPortEntry
        MAX-ACCESS    not-accessible
        STATUS        current    
        DESCRIPTION   "A table used to store Spanning Tree Group (STG)
                      port related information.  If a port is 
                      associated with more than one STGs, the port  
                      will have one entry in this table for each STG 
                      it assigned to." 
        ::= { rcStg 5 }
 
rcStgPortEntry OBJECT-TYPE
        SYNTAX        RcStgPortEntry
        MAX-ACCESS    not-accessible
        STATUS        current
        DESCRIPTION   "STG Port attributes" 
        INDEX         { rcStgPort, rcStgPortStgId }
        ::= { rcStgPortTable 1 }
 
RcStgPortEntry ::= SEQUENCE {
                  rcStgPort InterfaceIndex,
                  rcStgPortStgId INTEGER,
                  rcStgPortPriority INTEGER,
                  rcStgPortState INTEGER,
                  rcStgPortEnableStp TruthValue,
                  rcStgPortFastStart TruthValue,
                  rcStgPortPathCost INTEGER,
                  rcStgPortDesignatedRoot BridgeId,
                  rcStgPortDesignatedCost Integer32,
                  rcStgPortDesignatedBridge BridgeId,
                  rcStgPortDesignatedPort OCTET STRING,
                  rcStgPortForwardTransitions Counter32,
                  rcStgPortInConfigBpdus Counter32,
                  rcStgPortInTcnBpdus Counter32,
                  rcStgPortInBadBpdus Counter32,
                  rcStgPortOutConfigBpdus Counter32,
                  rcStgPortOutTcnBpdus Counter32,
                  rcStgPortRowStatus RowStatus,
                  rcStgPortChangeDetection TruthValue,
                  rcStgPortPathCost32 Integer32


              }

rcStgPort OBJECT-TYPE
        SYNTAX  	InterfaceIndex
        MAX-ACCESS  	read-only
        STATUS  	current
        DESCRIPTION 	"The port number of the port for which this entry
                     	contains Spanning Tree Protocol management
                     	information."
        REFERENCE 	"IEEE 802.1D-1990: Section 6.8.2.1.2"
        ::= { rcStgPortEntry 1 }

rcStgPortStgId OBJECT-TYPE
        SYNTAX  	INTEGER (1..128)
        MAX-ACCESS  	read-only
        STATUS  	current
	DESCRIPTION 	"The STG identifier this port is assigned to."
        ::= { rcStgPortEntry 2 }

rcStgPortPriority OBJECT-TYPE
        SYNTAX  	INTEGER (0..240)
        MAX-ACCESS  	read-write
        STATUS  	current
        DESCRIPTION 	"The value of the priority field which is
                     	contained in the first (in network byte order)
                     	octet of the (2 octet long) Port ID.  The other
                     	octet of the Port ID is given by the value of
                     	rcStgPort. The original range is 0..255. VSP9000
			supports range is 0..240 with increament of 16"
        REFERENCE 	"IEEE 802.1D-1990: Section 4.5.5.1"
        DEFVAL          { 128 }
        ::= { rcStgPortEntry 3 }

rcStgPortState OBJECT-TYPE
        SYNTAX  	INTEGER {
	                	disabled(1),
       		         	blocking(2),
       	        		listening(3),
		                learning(4),
               		 	forwarding(5),
                		broken(6)
        		}
        MAX-ACCESS  	read-only
        STATUS  	current
        DESCRIPTION 	"The port's current state as defined by
                     	application of the Spanning Tree Protocol.  This
                     	state controls what action a port takes on
                     	reception of a frame.  If the bridge has detected
                     	a port that is malfunctioning it will place that
                     	port into the broken(6) state.  For ports which
                     	are disabled (see rcStgPortEnable), this object
                     	will have a value of disabled(1)."
        REFERENCE 	"IEEE 802.1D-1990: Section 4.5.5.2"
        ::= { rcStgPortEntry 4 }


rcStgPortEnableStp OBJECT-TYPE
        SYNTAX  	TruthValue
        MAX-ACCESS  	read-write
        STATUS  	current
        DESCRIPTION 	"The enabled/disabled status of the port."
        REFERENCE 	"IEEE 802.1D-1990: Section 4.5.5.2"
        DEFVAL           { true }
        ::= { rcStgPortEntry 5 }

rcStgPortFastStart OBJECT-TYPE
        SYNTAX     	TruthValue
        MAX-ACCESS     	read-write
        STATUS     	current
        DESCRIPTION 	"When this flag is set, the port is moved 
                     	straight to the forwarding(5) state upon 
                     	being enabled."
        DEFVAL          { false }
        ::= { rcStgPortEntry 6 }

rcStgPortPathCost OBJECT-TYPE
        SYNTAX  	INTEGER (1..65535)
        MAX-ACCESS  	read-write
        STATUS  	current
        DESCRIPTION 	"The contribution of this port to the path cost of
                     	paths towards the spanning tree root which include
                     	this port.  802.1D-1990 recommends that the
                     	default value of this parameter be in inverse
                     	proportion to the speed of the attached LAN."
        REFERENCE 	"IEEE 802.1D-1990: Section 4.5.5.3"
        ::= { rcStgPortEntry 7 }

rcStgPortDesignatedRoot OBJECT-TYPE
        SYNTAX  	BridgeId
        MAX-ACCESS  	read-only
        STATUS  	current
        DESCRIPTION 	"The unique Bridge Identifier of the Bridge
                     	recorded as the Root in the Configuration BPDUs
                     	transmitted by the Designated Bridge for the
                     	segment to which the port is attached."
        REFERENCE 	"IEEE 802.1D-1990: Section 4.5.5.4"
        ::= { rcStgPortEntry 8 }

rcStgPortDesignatedCost OBJECT-TYPE
        SYNTAX  	Integer32
        MAX-ACCESS  	read-only
        STATUS  	current
        DESCRIPTION 	"The path cost of the Designated Port of the
                     	segment connected to this port.  This value is
                     	compared to the Root Path Cost field in received
                     	bridge PDUs."
        REFERENCE 	"IEEE 802.1D-1990: Section 4.5.5.5"
        ::= { rcStgPortEntry 9 }

rcStgPortDesignatedBridge OBJECT-TYPE
        SYNTAX  	BridgeId
        MAX-ACCESS  	read-only
        STATUS  	current
        DESCRIPTION 	"The Bridge Identifier of the bridge which this
                     	port considers to be the Designated Bridge for
                     	this port's segment."
        REFERENCE 	"IEEE 802.1D-1990: Section 4.5.5.6"
        ::= { rcStgPortEntry 10 }

rcStgPortDesignatedPort OBJECT-TYPE
        SYNTAX  	OCTET STRING (SIZE (2))
        MAX-ACCESS  	read-only
        STATUS  	current
        DESCRIPTION 	"The Port Identifier of the port on the Designated
                     	Bridge for this port's segment."
        REFERENCE 	"IEEE 802.1D-1990: Section 4.5.5.7"
        ::= { rcStgPortEntry 11 }

rcStgPortForwardTransitions OBJECT-TYPE
        SYNTAX  	Counter32
        MAX-ACCESS  	read-only
        STATUS  	current
        DESCRIPTION 	"The number of times this port has transitioned
                     	from the Learning state to the Forwarding state."
        ::= { rcStgPortEntry 12 }

rcStgPortInConfigBpdus OBJECT-TYPE
        SYNTAX  	Counter32
        MAX-ACCESS  	read-only
        STATUS  	current
        DESCRIPTION 	"The number of Config BPUDs received by
                     	this port."
        ::= { rcStgPortEntry 13 }

rcStgPortInTcnBpdus OBJECT-TYPE
        SYNTAX  	Counter32
        MAX-ACCESS  	read-only
        STATUS  	current
        DESCRIPTION 	"The number of Topology Change Notification
                     	BPUDs received by this port."
        ::= { rcStgPortEntry 14 }

rcStgPortInBadBpdus OBJECT-TYPE
        SYNTAX  	Counter32
        MAX-ACCESS  	read-only
        STATUS  	current
        DESCRIPTION 	"The number of Bad BPUDs received by this port."
        ::= { rcStgPortEntry 15 }

rcStgPortOutConfigBpdus OBJECT-TYPE
        SYNTAX  	Counter32
        MAX-ACCESS  	read-only
        STATUS  	current
        DESCRIPTION 	"The number of Config BPUDs transmitted by this port."
        ::= { rcStgPortEntry 16 }

rcStgPortOutTcnBpdus OBJECT-TYPE
        SYNTAX  	Counter32
        MAX-ACCESS  	read-only
        STATUS  	current
        DESCRIPTION 	"The number of Topology Change Notification
                     	BPUDs transmitted by this port."
        ::= { rcStgPortEntry 17 }

rcStgPortRowStatus OBJECT-TYPE
        SYNTAX  	RowStatus
        MAX-ACCESS  	read-write
        STATUS  	current
        DESCRIPTION 	"Row status."
        ::= { rcStgPortEntry 18 }

rcStgPortChangeDetection OBJECT-TYPE
        SYNTAX           TruthValue
        MAX-ACCESS       read-write
        STATUS           current
        DESCRIPTION      "If disabled, topology change notifications 
                          are not sent for the port."
        DEFVAL           { true }
        ::= { rcStgPortEntry 19 }

rcStgPortPathCost32 OBJECT-TYPE
    SYNTAX      Integer32 (1..200000000)
    MAX-ACCESS  read-write
    STATUS      current
    DESCRIPTION
        "The contribution of this port to the path cost of
         paths towards the spanning tree root which include
         this port.  802.1D-1998 recommends that the
         default value of this parameter be in inverse
         proportion to the speed of the attached LAN.
        Replacement for deprecated object dot1dStpPortPathCost."
        ::= { rcStgPortEntry 20 }

rcBridgeFdbTblSize OBJECT-TYPE
        SYNTAX          Integer32
        MAX-ACCESS      read-only
        STATUS          current
        DESCRIPTION     "Used to indicate the number of entries in
                        the bridge forwarding database table."
        ::= { rcBridge 2 }


-- The Static (Destination-Address) Database

rcBridgeStaticTable OBJECT-TYPE
              SYNTAX      SEQUENCE OF RcBridgeStaticEntry
              MAX-ACCESS  not-accessible
              STATUS      current
              DESCRIPTION "This table is a proprietary replacement to the
                    standard dot1dStaticTable in rfc1493."
              ::= { rcBridge 3 }

rcBridgeStaticEntry OBJECT-TYPE
       SYNTAX      RcBridgeStaticEntry
              MAX-ACCESS  not-accessible
              STATUS      current
           DESCRIPTION "A table containing forwarding information about
                    unicast entries configured into the bridge by
                    management. This information is used by the
                    transparent bridging function in determining how
                    to propagate a received frame."
              INDEX   { rcBridgeStaticAddress,
                 rcBridgeStaticPort,
                 rcBridgeStaticVlanId }
       ::= { rcBridgeStaticTable 1 }


RcBridgeStaticEntry ::=
SEQUENCE {
          rcBridgeStaticAddress  MacAddress,
          rcBridgeStaticPort     InterfaceIndex,
	  rcBridgeStaticStatus   INTEGER,
	  rcBridgeStaticVlanId   RcVlanIdOrNone 
	 }

rcBridgeStaticAddress OBJECT-TYPE
        SYNTAX      MacAddress
        MAX-ACCESS  read-only
        STATUS      current
        DESCRIPTION "The MAC address of this entry." 
        ::= { rcBridgeStaticEntry 1 }

rcBridgeStaticPort OBJECT-TYPE
        SYNTAX      InterfaceIndex
        MAX-ACCESS  read-only
        STATUS      current
        DESCRIPTION "Port on which the MAC address is found."
        ::= { rcBridgeStaticEntry 2 }
 
rcBridgeStaticStatus OBJECT-TYPE
       	SYNTAX  	INTEGER {
			    other(1),
			    invalid(2),
			    permanent(3),
			    deleteOnReset(4),
			    deleteOnTimeout(5)
       		        }
        MAX-ACCESS	 read-write
        STATUS      current
        DESCRIPTION "This object indicates the status of this 
                     entry. The default value is permanent(3)."
        ::= { rcBridgeStaticEntry 5 }

rcBridgeStaticVlanId OBJECT-TYPE
        SYNTAX      RcVlanIdOrNone
        MAX-ACCESS  read-only
        STATUS      current
        DESCRIPTION ""
        ::= { rcBridgeStaticEntry 7 }

rcBridgeStaticTblSize OBJECT-TYPE  
        SYNTAX      Integer32  
        MAX-ACCESS  read-only  
        STATUS      current  
        DESCRIPTION "Used to indicate the number of entries in 
                     the bridge static table."    
        ::= { rcBridge 4 }

-- The unknown mac discard config table

rcBridgeUnknownMacDiscardTable OBJECT-TYPE
	SYNTAX  	SEQUENCE OF RcBridgeUnknownMacDiscardEntry
	MAX-ACCESS  	not-accessible
	STATUS  	current
	DESCRIPTION 	"This table is used to configure the 'unknown mac discard' feature.
                        This feature applies to layer 2 and layer 3 packets coming from 
                        or going out to a specific physical port."
	::= { rcBridge 7 }
 
rcBridgeUnknownMacDiscardEntry OBJECT-TYPE
	SYNTAX  	RcBridgeUnknownMacDiscardEntry
	MAX-ACCESS  	not-accessible
	STATUS  	current
	DESCRIPTION 	"A table containing information configuring
                        the 'unknown mac discard' feature."
	INDEX   { rcBridgeUnknownMacDiscardIfIndex }
        ::= { rcBridgeUnknownMacDiscardTable 1 }
 
RcBridgeUnknownMacDiscardEntry ::=
        SEQUENCE {
	    rcBridgeUnknownMacDiscardIfIndex                  InterfaceIndex,
	    rcBridgeUnknownMacDiscardAutoLearnEnable          TruthValue,
	    rcBridgeUnknownMacDiscardAutoLearnMode            INTEGER,
	    rcBridgeUnknownMacDiscardAutoLearnTableMode       INTEGER,
	    rcBridgeUnknownMacDiscardLogViolations            INTEGER,
	    rcBridgeUnknownMacDiscardSendTrap                 INTEGER,
	    rcBridgeUnknownMacDiscardDisablePort              INTEGER,
	    rcBridgeUnknownMacDiscardMacCountMax              INTEGER,
	    rcBridgeUnknownMacDiscardMacCountCur              INTEGER
        }

rcBridgeUnknownMacDiscardIfIndex OBJECT-TYPE
        SYNTAX  	InterfaceIndex
        MAX-ACCESS  	read-only
        STATUS  	current
        DESCRIPTION 	"Port on which this 'unknown mac discard' configuration applied to."
        ::= { rcBridgeUnknownMacDiscardEntry 1 }
 
rcBridgeUnknownMacDiscardAutoLearnEnable OBJECT-TYPE  
        SYNTAX        	TruthValue  
        MAX-ACCESS        	read-write  
        STATUS        	current  
        DESCRIPTION   	"This variable is used to enable/disable the auto-learn capability 
                         of a specific port. The default value is auto-learn disabled."
        ::= { rcBridgeUnknownMacDiscardEntry 2 }

rcBridgeUnknownMacDiscardAutoLearnMode OBJECT-TYPE  
        SYNTAX        	INTEGER {
                               oneShot(1),
                               continuous(2)
                        }
        MAX-ACCESS        	read-write  
        STATUS        	current  
        DESCRIPTION   	"This variable is used to control the auto-learn mode to either 
                         one-shot or continuous. In one-shot mode, the first n MAC addresses 
                         will be learned. The number n is dependents on the system's 
                         available resource. In continuous mode, MAC address is continuous 
                         learned until the resource limit is reached. After that the 
                         subsequent MAC will be disallowed until one of the original 
                         learned MAC is aged out. The default value is one-shot mode."
        ::= { rcBridgeUnknownMacDiscardEntry 3 }

rcBridgeUnknownMacDiscardAutoLearnTableMode OBJECT-TYPE
        SYNTAX  	INTEGER {
		               unlock(1),
       		               lock(2)
       	         	}
        MAX-ACCESS  	read-write
        STATUS  	current
        DESCRIPTION 	"This MIB variable is used to lock or unlock the auto-learn MAC 
                         table. When the auto-learn table is lock neither new MAC will be 
                         learned nor the original learned MAC will be aged out. User needs 
                         to lock the auto-learn table before MAC addresses can be save to 
                         the NVRAM. The whole auto-learn table will be flushed when the 
                         setting change from lock to unlock mode. The default value is 
                         unlock mode."
        ::= { rcBridgeUnknownMacDiscardEntry 4 }

rcBridgeUnknownMacDiscardLogViolations OBJECT-TYPE
        SYNTAX  	INTEGER {
		               disable(1),
       		               enable(2)
       	         	}
        MAX-ACCESS  	read-write
        STATUS  	current
        DESCRIPTION 	"This variable controls the logging action that the system will 
                         take when a MAC address violation event was detected. The 
                         value 'enable' means a log record will be written to the system 
                         log file when a violation event was detected. The default value 
                         is enable."
        ::= { rcBridgeUnknownMacDiscardEntry 5 }

rcBridgeUnknownMacDiscardSendTrap OBJECT-TYPE
        SYNTAX  	INTEGER {
		               disable(1),
       		               enable(2)
       	         	}
        MAX-ACCESS  	read-write
        STATUS  	current
        DESCRIPTION 	"This variable controls the send trap action that system will take 
                         when a MAC address violation event was detected. The value 'enable' 
                         means a SNMP trap packet will be send to the management station 
                         when a violation event was detected. The default value is disable."
        ::= { rcBridgeUnknownMacDiscardEntry 6 }

rcBridgeUnknownMacDiscardDisablePort OBJECT-TYPE
        SYNTAX  	INTEGER {
		               disable(1),
       		               enable(2)
       	         	}
        MAX-ACCESS  	read-write
        STATUS  	current
        DESCRIPTION 	"This variable controls the 'disable-port' action that system 
                         will take when a MAC address violation event was detected. The 
                         value 'enable' means the specific port will be disabled when the 
                         violation event was detected. It needs user manually to bring 
                         the port back once it was disabled. The default value is disable."
        ::= { rcBridgeUnknownMacDiscardEntry 7 }


rcBridgeUnknownMacDiscardMacCountMax OBJECT-TYPE
        SYNTAX          INTEGER (0..2048)
        MAX-ACCESS      read-write
        STATUS          current
        DESCRIPTION     "This variable represents the maxium number of MACc that
                         can be added to some port."
        DEFVAL          { 2048 }
        ::= { rcBridgeUnknownMacDiscardEntry 10 }

rcBridgeUnknownMacDiscardMacCountCur OBJECT-TYPE
        SYNTAX          INTEGER (0..2048)
        MAX-ACCESS      read-only
        STATUS          current
        DESCRIPTION     "This variable represents the current number of MACs that have
                         been added to some port."
        DEFVAL          { 0 }
        ::= { rcBridgeUnknownMacDiscardEntry 11 }

-- The Manual Edit table

rcBridgeManualEditTable OBJECT-TYPE
	SYNTAX  	SEQUENCE OF RcBridgeManualEditEntry
	MAX-ACCESS  	not-accessible
	STATUS  	current
	DESCRIPTION 	"This table is used to specify what MAC addresses can be learned 
                         on each port."
	::= { rcBridge 8 }
 
rcBridgeManualEditEntry OBJECT-TYPE
	SYNTAX  	RcBridgeManualEditEntry
	MAX-ACCESS  	not-accessible
	STATUS  	current
	DESCRIPTION 	"A table containing information of
                        MAC addresses that can be learned."
	INDEX   { rcBridgeManualEditAddress }
        ::= { rcBridgeManualEditTable 1 }
 
RcBridgeManualEditEntry ::=
        SEQUENCE {
	    rcBridgeManualEditAddress    MacAddress,
	    rcBridgeManualEditPorts      PortSet,
	    rcBridgeManualEditMonitor    TruthValue,
	    rcBridgeManualEditPriority   INTEGER,
	    rcBridgeManualEditStatus     INTEGER
        }

rcBridgeManualEditAddress OBJECT-TYPE
        SYNTAX  	MacAddress
        MAX-ACCESS  	read-only
        STATUS  	current
        DESCRIPTION 	"This variable contains the source MAC address of an entry."
        ::= { rcBridgeManualEditEntry 1 }
 
rcBridgeManualEditPorts OBJECT-TYPE  
        SYNTAX        	PortSet  
        MAX-ACCESS        	read-write  
        STATUS        	current  
        DESCRIPTION   	"This variable contains the allowed ports on which the MAC 
                         address of this entry can be learned."
        ::= { rcBridgeManualEditEntry 2 }

rcBridgeManualEditMonitor OBJECT-TYPE  
        SYNTAX        	TruthValue
        MAX-ACCESS        	read-write  
        STATUS        	current  
        DESCRIPTION   	"This variable specifies the monitoring setting of the MAC 
                         address. The value 'true' means a copy of packet frame that 
                         send from or to the MAC address is forwarded to the designated 
                         monitoring port on the system. The default value is false."
        ::= { rcBridgeManualEditEntry 3 }

rcBridgeManualEditPriority OBJECT-TYPE
        SYNTAX  	INTEGER {
		               low(1),
       		               high(2)
       	         	}
        MAX-ACCESS  	read-write
        STATUS  	current
        DESCRIPTION 	"This variable specifies the priority setting of the MAC address. 
                         The value 'low' means packet frames send from the MAC address 
                         is forwarded at low priority. The default value is low."
        ::= { rcBridgeManualEditEntry 4 }

rcBridgeManualEditStatus OBJECT-TYPE
        SYNTAX  	INTEGER {
		               other(1),
		               invalid(2),
       		               active(3)
       	         	}
        MAX-ACCESS  	read-write
        STATUS  	current
        DESCRIPTION 	"The variable controls the status of a MAC address in the table. 
                         The value 'active' is used to add the MAC address entry into the 
                         table. The value 'invalid' is used to delete the MAC address from 
                         the table."
        ::= { rcBridgeManualEditEntry 5 }

rcBridgeManualEditTblSize OBJECT-TYPE  
        SYNTAX        	Integer32  
        MAX-ACCESS        	read-only  
        STATUS        	current  
        DESCRIPTION   	"Used to indicate the number of entries in 
                       	the manual edit table."    
        ::= { rcBridge 9 }

-- The Auto Learn table

rcBridgeAutoLearnTable OBJECT-TYPE
	SYNTAX  	SEQUENCE OF RcBridgeAutoLearnEntry
	MAX-ACCESS  	not-accessible
	STATUS  	current
	DESCRIPTION 	"This table contains information of auto-learned MAC address when 
                         the 'unknow MAC discard' table's auto-learn is enabled. User must 
                         explicitly lock and save the table into NVRAM in order to have 
                         this table has the same configuration cross the system reset."
	::= { rcBridge 10 }
 
rcBridgeAutoLearnEntry OBJECT-TYPE
	SYNTAX  	RcBridgeAutoLearnEntry
	MAX-ACCESS  	not-accessible
	STATUS  	current
	DESCRIPTION 	"Entries in this table are created automatically
                        when the user explicitly does a lock operation on
                        the auto-learn-table (i.e., when 'AutoLearnTableMode'
                        is set to lock(2))."
	INDEX   { rcBridgeAutoLearnAddress }
        ::= { rcBridgeAutoLearnTable 1 }
 
RcBridgeAutoLearnEntry ::=
        SEQUENCE {
	    rcBridgeAutoLearnAddress    MacAddress,
	    rcBridgeAutoLearnPort       PortSet,
	    rcBridgeAutoLearnMonitor    TruthValue,
	    rcBridgeAutoLearnPriority   INTEGER,
	    rcBridgeAutoLearnAction     INTEGER
        }

rcBridgeAutoLearnAddress OBJECT-TYPE
        SYNTAX  	MacAddress
        MAX-ACCESS  	read-only
        STATUS  	current
        DESCRIPTION 	"This variable contains the source MAC address of the entries."
        ::= { rcBridgeAutoLearnEntry 1 }
 
rcBridgeAutoLearnPort OBJECT-TYPE  
        SYNTAX        	PortSet  
        MAX-ACCESS        	read-only  
        STATUS        	current  
        DESCRIPTION   	"This variable contains the port where the MAC address was learned."
        ::= { rcBridgeAutoLearnEntry 2 }

rcBridgeAutoLearnMonitor OBJECT-TYPE  
        SYNTAX        	TruthValue
        MAX-ACCESS        	read-only  
        STATUS        	current  
        DESCRIPTION   	"This variable contains the monitor setting of the MAC address. 
                         The value 'true' means a copy of packet frame that send from or 
                         to the MAC address is forwarded to the designated monitoring port 
                         on the system. This value should be synchronized with the setting 
                         of 'unknow MAC discard' table's 'Default AutoLearnMonitor' setting 
                         when the MAC address was learned."
        ::= { rcBridgeAutoLearnEntry 3 }

rcBridgeAutoLearnPriority OBJECT-TYPE
        SYNTAX  	INTEGER {
		               low(1),
       		               high(2)
       	         	}
        MAX-ACCESS  	read-only
        STATUS  	current
        DESCRIPTION 	"This variable contains the priority setting of the MAC address. 
                         The value 'low' means packet frames send from the MAC address is 
                         forwarded at low priority. The value 'high' means packet frames 
                         send from the MAC address is forwarded at high priority. This 
                         value should be synchronized with the setting of 'unknow MAC 
                         discard' table's 'DefaultAutoLearnPriority' setting when the MAC
                         address was learned."
        ::= { rcBridgeAutoLearnEntry 4 }

rcBridgeAutoLearnAction OBJECT-TYPE
        SYNTAX  	INTEGER {
		               none(0),
		               convertToManualEdit(1)
       	         	}
        MAX-ACCESS  	read-write
        STATUS  	current
        DESCRIPTION 	"This variable is for converting an auto-learned MAC address entry 
                         to a manual edit MAC address entry. This variable provides a mechanism
                         for user to move a MAC address entry from auto-learn table to manual 
                         edit table."
        ::= { rcBridgeAutoLearnEntry 5 }


rcBridgeAutoLearnTblSize OBJECT-TYPE  
        SYNTAX        	Integer32  
        MAX-ACCESS        	read-only  
        STATUS        	current  
        DESCRIPTION   	"Used to indicate the number of entries in 
                       	the auto learn table."    
        ::= { rcBridge 11 }


rcBridgeStaticMulticastTblSize OBJECT-TYPE  	--excluded
        SYNTAX        	Integer32  
        MAX-ACCESS        	read-only  
        STATUS        	obsolete  
        DESCRIPTION   	"Used to indicate the number of entries in 
                       	the static multicast table."    
        ::= { rcBridge 13 }

rcRateLimitTable OBJECT-TYPE
        SYNTAX          SEQUENCE OF RcRateLimitEntry
        MAX-ACCESS      not-accessible
        STATUS          current
        DESCRIPTION     ""
        ::= { rcBridge 14 }

rcRateLimitEntry OBJECT-TYPE
        SYNTAX          RcRateLimitEntry
        MAX-ACCESS      not-accessible
        STATUS          current
        DESCRIPTION     ""
        INDEX   { rcRateLimitIfIndex, rcRateLimitIfTrafficType }
        ::= { rcRateLimitTable 1 }

RcRateLimitEntry ::=
        SEQUENCE {
            rcRateLimitIfIndex              InterfaceIndex,
            rcRateLimitIfTrafficType        INTEGER,
            rcRateLimitIfEnable             TruthValue,
            rcRateLimitIfAllowedRatePps     Integer32
        }

rcRateLimitIfIndex OBJECT-TYPE
        SYNTAX          InterfaceIndex
        MAX-ACCESS      read-only
        STATUS          current
        DESCRIPTION     "Port ifindex."
        ::= { rcRateLimitEntry 1 }

rcRateLimitIfTrafficType OBJECT-TYPE
        SYNTAX          INTEGER {
                                multicast(1),
                                broadcast(2)
                        }
        MAX-ACCESS      read-write
        STATUS          current
        DESCRIPTION     "Type of traffic allowed."
        DEFVAL          { broadcast }
        ::= { rcRateLimitEntry 2 }

rcRateLimitIfEnable OBJECT-TYPE
        SYNTAX          TruthValue
        MAX-ACCESS      read-write
        STATUS          current
        DESCRIPTION     "Turn on/off rate limiting on this interface."
        DEFVAL          { false }
        ::= { rcRateLimitEntry 4 }

rcRateLimitIfAllowedRatePps OBJECT-TYPE
        SYNTAX          Integer32 (0..65535) 
        MAX-ACCESS      read-write
        STATUS          current
        DESCRIPTION     "Allowed traffic rate packets per second. 
			0 means disabled"
        ::= { rcRateLimitEntry 5 }

-- The Static Multicast table

rcBridgeStaticMcastTable OBJECT-TYPE	--excluded
	SYNTAX  	SEQUENCE OF RcBridgeStaticMcastEntry
	MAX-ACCESS  	not-accessible
	STATUS  	current
	DESCRIPTION 	""
	::= { rcBridge 15 }
 
rcBridgeStaticMcastEntry OBJECT-TYPE
	SYNTAX  	RcBridgeStaticMcastEntry
	MAX-ACCESS  	not-accessible
	STATUS  	current
	DESCRIPTION 	""
	INDEX   { rcBridgeStaticMcastVlanId, rcBridgeStaticMcastAddress }
        ::= { rcBridgeStaticMcastTable 1 }
 
RcBridgeStaticMcastEntry ::=
        SEQUENCE {
	    rcBridgeStaticMcastVlanId          INTEGER,
	    rcBridgeStaticMcastAddress         MacAddress,
	    rcBridgeStaticMcastForwardingPorts PortSet,
	    rcBridgeStaticMcastMltIds          IdList,
	    rcBridgeStaticMcastNumMltIds       Integer32,
	    rcBridgeStaticMcastRowStatus       RowStatus
        }

rcBridgeStaticMcastVlanId OBJECT-TYPE  
        SYNTAX           INTEGER (1..4095)	
        MAX-ACCESS        	read-only  
        STATUS        	current  
        DESCRIPTION   	"Vlan Id"
        ::= { rcBridgeStaticMcastEntry 1 } 

rcBridgeStaticMcastAddress OBJECT-TYPE
        SYNTAX  	MacAddress
        MAX-ACCESS  	read-only
        STATUS  	current
        DESCRIPTION 	"src mac addr."
        ::= { rcBridgeStaticMcastEntry 2 }
 
rcBridgeStaticMcastForwardingPorts OBJECT-TYPE  
        SYNTAX        	PortSet  
        MAX-ACCESS        	read-write  
        STATUS        	current  
        DESCRIPTION   	"ports for forward this mac"
        ::= { rcBridgeStaticMcastEntry 3 }

rcBridgeStaticMcastMltIds OBJECT-TYPE  
        SYNTAX        	IdList -- 1024 octets
        MAX-ACCESS        	read-write  
        STATUS        	current  
        DESCRIPTION   	"list of mlts this mac will be forwarded on"
        ::= { rcBridgeStaticMcastEntry 4 }

rcBridgeStaticMcastNumMltIds OBJECT-TYPE  
        SYNTAX        	Integer32
        MAX-ACCESS        	read-only  
        STATUS        	current  
        DESCRIPTION   	"number of mlts Ids"
        ::= { rcBridgeStaticMcastEntry 5 }

rcBridgeStaticMcastRowStatus OBJECT-TYPE
        SYNTAX  	RowStatus
        MAX-ACCESS  	read-write
        STATUS  	current
        DESCRIPTION 	"row status"
        ::= { rcBridgeStaticMcastEntry 6 }

-- rcBridge Fdb Protect Table


rcBridgeFdbProtectTable OBJECT-TYPE
     SYNTAX         SEQUENCE OF RcBridgeFdbProtectEntry
     MAX-ACCESS     not-accessible
     STATUS         current
     DESCRIPTION    "This table gives information about the mac learning
                     limits on a particular port."
   ::= { rcBridge 17 }

rcBridgeFdbProtectEntry OBJECT-TYPE
     SYNTAX         RcBridgeFdbProtectEntry
     MAX-ACCESS     not-accessible
     STATUS         current
     DESCRIPTION    "Information about a specific MAC address learning
                     limits of a specific port."
     INDEX { rcBridgeFdbProtectPortNum }
     ::= { rcBridgeFdbProtectTable 1 }

RcBridgeFdbProtectEntry ::=
     SEQUENCE {
                  rcBridgeFdbProtectPortNum           InterfaceIndex,
                  rcBridgeFdbProtectMaxMacCount       Integer32,
                  rcBridgeFdbProtectMinMacCount       Integer32,
                  rcBridgeFdbProtectEnable            EnableValue,
                  rcBridgeFdbProtectCurrentMacCount   Integer32,
                  rcBridgeFdbProtectMacLearning       TruthValue,
                  rcBridgeFdbProtectViolationLogTrap  EnableValue,
                  rcBridgeFdbProtectViolationDownPort EnableValue
              }

rcBridgeFdbProtectPortNum OBJECT-TYPE
        SYNTAX       InterfaceIndex
        MAX-ACCESS   read-only
        STATUS       current
        DESCRIPTION  "This object is the interface on which MAC address
                      learning limit is applied."
        ::= { rcBridgeFdbProtectEntry 1 }

rcBridgeFdbProtectMaxMacCount OBJECT-TYPE
        SYNTAX       Integer32(1..64000)
        MAX-ACCESS   read-write
        STATUS       current
        DESCRIPTION  "Used to indicate maximum number of MAC address
                      that can be learnt on the port."
        DEFVAL       { 1024 }
        ::= { rcBridgeFdbProtectEntry 2 }

rcBridgeFdbProtectMinMacCount OBJECT-TYPE
        SYNTAX       Integer32(1..64000)
        MAX-ACCESS   read-write
        STATUS       current
        DESCRIPTION  "Used to indicate minimum number of MAC address
                      learnt which mac address learning will be re-enabled
                      on the port."
        DEFVAL       { 512 }
        ::= { rcBridgeFdbProtectEntry 3 }

rcBridgeFdbProtectEnable OBJECT-TYPE
        SYNTAX       EnableValue
        MAX-ACCESS   read-write
        STATUS       current
        DESCRIPTION  "Used to enable or disable MAC learning limit
                      feature on the port."
        ::= { rcBridgeFdbProtectEntry 4 }

rcBridgeFdbProtectCurrentMacCount OBJECT-TYPE
        SYNTAX       Integer32
        MAX-ACCESS   read-only
        STATUS       current
        DESCRIPTION  "This object indicates the current number of
                      MAC address learnt on the port."
        ::= { rcBridgeFdbProtectEntry 5 }

rcBridgeFdbProtectMacLearning OBJECT-TYPE
        SYNTAX       TruthValue
        MAX-ACCESS   read-only
        STATUS       current
        DESCRIPTION  "This object indicates whether the port can 
                      currrently learn new MAC addresses or not."
        ::= { rcBridgeFdbProtectEntry 6 }

rcBridgeFdbProtectViolationLogTrap OBJECT-TYPE
        SYNTAX       EnableValue 
        MAX-ACCESS   read-write
        STATUS       current
        DESCRIPTION  "Used to enable or disable logging and sending 
                      of snmp trap, once MAC learning limit is reached
                      for the port."
        ::= { rcBridgeFdbProtectEntry 7 }

rcBridgeFdbProtectViolationDownPort OBJECT-TYPE
        SYNTAX       EnableValue 
        MAX-ACCESS   read-write
        STATUS       current
        DESCRIPTION  "Used to enable or disable the action of disabling
                      the port, once MAC learning limit is reached
                      for the port."
        ::= { rcBridgeFdbProtectEntry 8 }


-- Forwarding Database for Transparent(TP) Bridges

rcBridgeTpFdbTable OBJECT-TYPE
        SYNTAX          SEQUENCE OF RcBridgeTpFdbEntry
        MAX-ACCESS      not-accessible
        STATUS          current
        DESCRIPTION     "This table is an replacement to the standard
                        dot1dTpFdbTable in rfc1493."
        ::= { rcBridge 20 }

rcBridgeTpFdbEntry OBJECT-TYPE
        SYNTAX          RcBridgeTpFdbEntry
        MAX-ACCESS      not-accessible
        STATUS          current
        DESCRIPTION     "Information about a specific unicast MAC address
                        for which the bridge has some forwarding information."
        INDEX { rcBridgeTpFdbVlanId, rcBridgeTpFdbAddress}
        ::= { rcBridgeTpFdbTable 1 }

RcBridgeTpFdbEntry ::=
        SEQUENCE {
		  rcBridgeTpFdbVlanId       RcVlanIdOrNone,
		  rcBridgeTpFdbAddress      MacAddress,		 	
                  rcBridgeTpFdbStatus       INTEGER,
                  rcBridgeTpFdbPort         InterfaceIndex,
                  rcBridgeTpFdbSmltRemote   TruthValue,
                  rcBridgeTpFdbBMac         MacAddress                    
                 }

rcBridgeTpFdbVlanId OBJECT-TYPE
        SYNTAX      RcVlanIdOrNone
        MAX-ACCESS  not-accessible
        STATUS      current
        DESCRIPTION  "Used to indicate the Vlan ID for this 
                      MAC address."
        ::= { rcBridgeTpFdbEntry 1 }


rcBridgeTpFdbAddress OBJECT-TYPE
        SYNTAX          MacAddress
        MAX-ACCESS      not-accessible
        STATUS          current
        DESCRIPTION     "A unicast MAC address for which the bridge
                        has forwarding and/or filtering information."
        REFERENCE "IEEE 802.1D-1990: Section 3.9.1, 3.9.2"
        ::= { rcBridgeTpFdbEntry 2 }

rcBridgeTpFdbStatus OBJECT-TYPE
        SYNTAX          INTEGER {
                              other(1),
                              invalid(2),
                              learned(3),
                              self(4),
                              mgmt(5)
                        }
        MAX-ACCESS      read-write
        STATUS          current
        DESCRIPTION     "This object indicates the status of this entry."
        ::= { rcBridgeTpFdbEntry 3 }

rcBridgeTpFdbPort OBJECT-TYPE
        SYNTAX          InterfaceIndex
        MAX-ACCESS      read-only
        STATUS          current
        DESCRIPTION     "Either the value '0', or the port number of the
                        port on which a frame having a source address
                        equal to the value of the corresponding instance
                        of rcBridgeTpFdbAddress has been seen.  A value of
                        '0' indicates that the port number has not been
                        learned but that the bridge does have some
                        forwarding/filtering information about this
                        address (e.g. in the dot1dStaticTable).
                        Implementors are encouraged to assign the port
                        value to this object whenever it is learned even
                        for addresses for which the corresponding value of
                        rcBridgeTpFdbStatus is not learned(3)."
        ::= { rcBridgeTpFdbEntry 4 }

rcBridgeTpFdbSmltRemote OBJECT-TYPE
        SYNTAX      TruthValue
        MAX-ACCESS  read-only
        STATUS      current
        DESCRIPTION  "A MAC address indicate for remote learnt,
                       either local or remote."
        ::= { rcBridgeTpFdbEntry 5 }

rcBridgeTpFdbBMac OBJECT-TYPE
        SYNTAX          MacAddress
        MAX-ACCESS      read-only
        STATUS          current
        DESCRIPTION     "If the rcBridgeTpFdbEntry is learned from a SPBM network,
                        instead of using port to track where the rcBridgeTpFdbAddress
                        come from, the backbone MAC address is used to track that."
        ::= { rcBridgeTpFdbEntry 6 }

-- rcBridgeRemoteMacTable

rcBridgeRemoteMacTable OBJECT-TYPE
        SYNTAX          SEQUENCE OF RcBridgeRemoteMacEntry
        MAX-ACCESS      not-accessible
        STATUS          current
        DESCRIPTION     "This table is for PLSB cvlan UNI remote mac entries"
        ::= { rcBridge 21 }

rcBridgeRemoteMacEntry OBJECT-TYPE
        SYNTAX          RcBridgeRemoteMacEntry
        MAX-ACCESS      not-accessible
        STATUS          current
        DESCRIPTION     "Information about a specific cvlan UNI remote MAC 
                        address for which the bridge has the forwarding 
                        information."
        INDEX { rcBridgeRemoteMacVlanId, rcBridgeRemoteMacAddr}
        ::= { rcBridgeRemoteMacTable 1 }

RcBridgeRemoteMacEntry ::=
        SEQUENCE {
              rcBridgeRemoteMacVlanId      Integer32,
              rcBridgeRemoteMacAddr        MacAddress, 
              rcBridgeRemoteMacStatus      INTEGER,
              rcBridgeRemoteMacDestAddr    MacAddress,
              rcBridgeRemoteMacPrimaryBVlanId   Integer32,        
              rcBridgeRemoteMacPrimaryDestSysName OCTET STRING,            
              rcBridgeRemoteMacPrimaryPort         InterfaceIndex,
              rcBridgeRemoteMacSecondaryBVlanId   Integer32,        
              rcBridgeRemoteMacSecondaryDestSysName OCTET STRING,            
              rcBridgeRemoteMacSecondaryPort         InterfaceIndex,  
              rcBridgeRemoteMacSmltRemote TruthValue  
         }

rcBridgeRemoteMacVlanId OBJECT-TYPE
        SYNTAX          Integer32 (1..4094)
        MAX-ACCESS      not-accessible
        STATUS          current
        DESCRIPTION     "Used to indicate the Vlan ID for this 
                         MAC address."
        ::= { rcBridgeRemoteMacEntry 1 }

rcBridgeRemoteMacAddr OBJECT-TYPE
        SYNTAX          MacAddress
        MAX-ACCESS      not-accessible
        STATUS          current
        DESCRIPTION     "A customer MAC address for which the bridge
                        has forwarding and/or filtering information."
        REFERENCE       ""
        ::= { rcBridgeRemoteMacEntry 2 }

rcBridgeRemoteMacStatus OBJECT-TYPE
        SYNTAX  	INTEGER {
			      other(1),
			      invalid(2),
			      learned(3),
			      self(4),
			      mgmt(5)
			}
        MAX-ACCESS 	read-only
        STATUS 	 	current
        DESCRIPTION 	"This object indicates the status of this entry."
        ::= { rcBridgeRemoteMacEntry 3 }

rcBridgeRemoteMacDestAddr OBJECT-TYPE
        SYNTAX          MacAddress
        MAX-ACCESS      read-only
        STATUS          current
        DESCRIPTION     "A provider MAC address for which the bridge
                        has forwarding and/or filtering information."
        REFERENCE       ""
        ::= { rcBridgeRemoteMacEntry 4 }

rcBridgeRemoteMacPrimaryBVlanId OBJECT-TYPE
        SYNTAX          Integer32 (1..4094)
        MAX-ACCESS      read-only
        STATUS          current
        DESCRIPTION     "Used to indicate the BVlan ID for this 
                         MAC address."
        ::= { rcBridgeRemoteMacEntry 5 }

rcBridgeRemoteMacPrimaryDestSysName OBJECT-TYPE
        SYNTAX        OCTET STRING (SIZE (0..255))
        MAX-ACCESS    read-only
        STATUS        current
        DESCRIPTION   "Primary System name of the node where MAC address entry 
                       come from."
        ::= { rcBridgeRemoteMacEntry 6 }

rcBridgeRemoteMacPrimaryPort OBJECT-TYPE
        SYNTAX          InterfaceIndex 
        MAX-ACCESS      read-only
        STATUS          current
        DESCRIPTION     "Either the value '0', or the primary
      	             	port on which a frame came from."      
        ::= { rcBridgeRemoteMacEntry 7  }       

rcBridgeRemoteMacSecondaryBVlanId OBJECT-TYPE
        SYNTAX          Integer32 (1..4094)
        MAX-ACCESS      read-only
        STATUS          current
        DESCRIPTION     "Used to indicate the BVlan ID for this 
                         MAC address."
        ::= { rcBridgeRemoteMacEntry 8 }

rcBridgeRemoteMacSecondaryDestSysName OBJECT-TYPE
        SYNTAX        OCTET STRING (SIZE (0..255))
        MAX-ACCESS    read-only
        STATUS        current
        DESCRIPTION   "Secondary System name of the node where MAC address entry 
                       come from."
        ::= { rcBridgeRemoteMacEntry 9 }

rcBridgeRemoteMacSecondaryPort OBJECT-TYPE
        SYNTAX          InterfaceIndex
        MAX-ACCESS      read-only
        STATUS          current
        DESCRIPTION     "Either the value '0', or the secondary
      	             	port on which a frame came from."      
        ::= { rcBridgeRemoteMacEntry 10  }    

rcBridgeRemoteMacSmltRemote OBJECT-TYPE
        SYNTAX      TruthValue 
        MAX-ACCESS  read-only
        STATUS      current
        DESCRIPTION  "A MAC address indicate for remote learnt from ist peer"
        ::= { rcBridgeRemoteMacEntry 11 }


-- Multi-Link Trunking Table

rcMltNumMlts OBJECT-TYPE
        SYNTAX        	Integer32
        MAX-ACCESS        	read-only
        STATUS        	current
        DESCRIPTION   	"The number of MLTs currently defined in the switch."
        ::= { rcMlt 1 }

rcMltPotentialMembers OBJECT-TYPE
        SYNTAX        	PortSet
        MAX-ACCESS        	read-only
        STATUS        	current
        DESCRIPTION   	"The set of ports that are not members of any MLT."
        ::= { rcMlt 2 }

rcMltIstSessionEnable OBJECT-TYPE
        SYNTAX        EnableValue
        MAX-ACCESS    read-write
        STATUS        current
        DESCRIPTION   "Used to enable/disable mlt functionality."
        ::= { rcMlt 3 }

rcMltIstSessionStatus OBJECT-TYPE
        SYNTAX        INTEGER {
                           up(1),
                           down(2)
                        }
        MAX-ACCESS    read-only
        STATUS        current
        DESCRIPTION   "Used to enable/disable mlt functionality."
        ::= { rcMlt 4 }

rcMltIstPeerIp OBJECT-TYPE
        SYNTAX        IpAddress
        MAX-ACCESS    read-write
        STATUS        current
        DESCRIPTION   "IST mlt Peer Ip address."
        ::= { rcMlt 5 }

rcMltIstVlanId OBJECT-TYPE
        SYNTAX      	INTEGER (0..4084)
        MAX-ACCESS    read-write
        STATUS        current
        DESCRIPTION   "IST mlt Vlan Id. 0 is default when it
                       is not set, VSP supports 0 to 4084"
        ::= { rcMlt 6 }


rcMltTable OBJECT-TYPE
        SYNTAX        	SEQUENCE OF RcMltEntry
        MAX-ACCESS        	not-accessible
        STATUS        	current
        DESCRIPTION   	"A list of Multi-Link Trunk entries. The number of 
                      	entries is given by rcMltNumMlts."
        ::= { rcMlt 10 }

rcMltEntry OBJECT-TYPE
        SYNTAX        	RcMltEntry
        MAX-ACCESS        	not-accessible
        STATUS        	current
        DESCRIPTION   	"Entry containing configuration information for a 
                      	particular Multi-Link Trunk."
        INDEX         	{ rcMltId }
        ::= { rcMltTable 1 }

RcMltEntry ::= SEQUENCE {
                rcMltId	                    INTEGER,
                rcMltName                   DisplayString,
                rcMltPortMembers            PortSet,
		rcMltPortType               INTEGER,	
		rcMltNumVlanIds             Integer32,
                rcMltRowStatus              RowStatus,
		rcMltEnable                 TruthValue,
		rcMltLoadBalance            TruthValue,
		rcMltIfIndex		    InterfaceIndex,
		rcMltMltType   		    INTEGER,
		rcMltRunningType            INTEGER,
		rcMltMulticastDistribution  EnableValue,
		rcMltAggregatable           EnableValue,
		rcMltClearLinkAggregate     INTEGER,
		rcMltDesignatedPort         InterfaceIndex,
		rcMltAggOperState           EnableValue,
		rcMltAggTimeOfLastOperChange TimeTicks,
                rcMltPeerPortMembers         PortSet,
		rcMltCpLimitPktRate	     INTEGER,
		rcMltCpLimitShutDownEnable   TruthValue,
		rcMltVlanIdList		     OCTET STRING,
                rcMltEntryOwner              INTEGER,
                rcMltDatapathProgrammingState INTEGER
        }

rcMltId OBJECT-TYPE
        SYNTAX        	INTEGER (1..512)
        MAX-ACCESS      read-only
        STATUS        	current
        DESCRIPTION   	"A value that uniquely identifies the Multi-Link 
                      	Trunk associated with this entry."
        ::= { rcMltEntry 1 }

rcMltName OBJECT-TYPE
        SYNTAX        	DisplayString (SIZE (0..20))
        MAX-ACCESS        	read-write
        STATUS        	current
        DESCRIPTION   	"An administratively-assigned name for this MLT."
        ::= { rcMltEntry 2 }

rcMltPortMembers OBJECT-TYPE
        SYNTAX        	PortSet
        MAX-ACCESS        	read-write
        STATUS        	current
        DESCRIPTION   	"The set of ports that are members of this MLT." 
        ::= { rcMltEntry 3 }

rcMltPortType OBJECT-TYPE
        SYNTAX        	INTEGER {
                        	access(1),     -- access port type
                         	trunk(2)       -- trunk port type
                      	}
        MAX-ACCESS        	read-write
        STATUS        	current
        DESCRIPTION   	"The type of MLT port: access(1) or trunk(2)."
	DEFVAL 		{ access }
        ::= { rcMltEntry 4 }
 
rcMltNumVlanIds OBJECT-TYPE
        SYNTAX        	Integer32
        MAX-ACCESS        	read-only
        STATUS        	current
        DESCRIPTION   	"Used to indicate the number of VLAN IDs that
                      	are stored in the rcMltVlanIds variable."
        ::= { rcMltEntry 5 }

rcMltRowStatus OBJECT-TYPE
        SYNTAX        	RowStatus
        MAX-ACCESS        	read-write
        STATUS        	current
        DESCRIPTION   	"Used to create/delete entries in the rcMltTable."
        ::= { rcMltEntry 7 }

rcMltEnable OBJECT-TYPE
        SYNTAX        	TruthValue
        MAX-ACCESS        	read-only
        STATUS        	current
        DESCRIPTION   	"Enable the entry."
	DEFVAL 		{ true }
        ::= { rcMltEntry 8 }

rcMltLoadBalance OBJECT-TYPE
        SYNTAX        	TruthValue
        MAX-ACCESS        	read-write
        STATUS        	current
        DESCRIPTION   	"Perform load balance?"
	DEFVAL	{ false }
        ::= { rcMltEntry 9 }

rcMltIfIndex OBJECT-TYPE
        SYNTAX        InterfaceIndex
        MAX-ACCESS    read-only
        STATUS        current
        DESCRIPTION   "Used to indicate the 'logical' ifIndex assigned to
                      this MLT."
        ::= { rcMltEntry 11 }

rcMltMltType OBJECT-TYPE
        SYNTAX        INTEGER {
                        	normalMLT(1),
                        	istMLT(2),
                        	splitMLT(3)
                      } 
        MAX-ACCESS    read-write
        STATUS        current
        DESCRIPTION   "MLT type."
        ::= { rcMltEntry 12 }

rcMltRunningType OBJECT-TYPE
        SYNTAX        INTEGER {
                        	normalMLT(1),
                        	istMLT(2),
                        	splitMLT(3)
                      } 
        MAX-ACCESS    read-only
        STATUS        current
        DESCRIPTION   "Split MLT running type."
        ::= { rcMltEntry 14 } 

rcMltMulticastDistribution OBJECT-TYPE 
        SYNTAX        EnableValue
	       MAX-ACCESS    read-write            
	       STATUS        current             
	       DESCRIPTION   "Enable/Disable multicast distribution per mlt."
	       DEFVAL        { disable }
        ::= { rcMltEntry 16 }

rcMltAggregatable OBJECT-TYPE
        SYNTAX        EnableValue
        MAX-ACCESS        read-write
        STATUS        current
        DESCRIPTION   "Enable/Disable link aggregation on a MLT."
        DEFVAL        { disable }
        ::= { rcMltEntry 18 }

rcMltClearLinkAggregate OBJECT-TYPE
        SYNTAX        INTEGER {
                        	clear(1),
                        	none(2)
                      }
        MAX-ACCESS        read-write
        STATUS        current
        DESCRIPTION   "clear link aggregate, equivalent to disable and 
                       re-enable aggregatable on the MLT."
        ::= { rcMltEntry 19 }

rcMltDesignatedPort OBJECT-TYPE 
        SYNTAX        InterfaceIndex
	       MAX-ACCESS    read-only            
	       STATUS        current             
        DESCRIPTION     "Indicates the Designated port for the MLT."
        ::= { rcMltEntry 21 } 

rcMltAggOperState OBJECT-TYPE
        SYNTAX        EnableValue
        MAX-ACCESS    read-only
        STATUS        current
        DESCRIPTION   "Link aggregation state on a MLT."
        ::= { rcMltEntry 22 }

rcMltAggTimeOfLastOperChange OBJECT-TYPE
        SYNTAX        TimeTicks 
        MAX-ACCESS    read-only
        STATUS        current
        DESCRIPTION   "The time value since the interface entered its 
                       current operational state."
        ::= { rcMltEntry 23 }

rcMltPeerPortMembers OBJECT-TYPE
        SYNTAX        	PortSet
        MAX-ACCESS      read-only
        STATUS        	current
        DESCRIPTION   	"The set of Peer ports which are connected to local ports
                         (rcMltPortMember) of this MLT" 
        ::= { rcMltEntry 39 }

rcMltCpLimitPktRate OBJECT-TYPE
        SYNTAX        	INTEGER(1000..20000)
        MAX-ACCESS      read-write
        STATUS        	current
        DESCRIPTION   	"Used to limit Control packets on the 
			 port to qos-levels 6 and 7.
			 Sets the limit in packets per second." 
	DEFVAL		{ 8000 }
        ::= { rcMltEntry 40 }

rcMltCpLimitShutDownEnable OBJECT-TYPE
        SYNTAX        	TruthValue
        MAX-ACCESS      read-write
        STATUS        	current
        DESCRIPTION   	"Used to indicate if the mlt-ports should  be 
			 shutdown when the CpLimitPktRate is exceeded." 
	DEFVAL		{ false }
        ::= { rcMltEntry 41 }

rcMltVlanIdList OBJECT-TYPE
        SYNTAX        	OCTET STRING (SIZE (0..512))
        MAX-ACCESS      read-write
        STATUS        	current
        DESCRIPTION   	"This bitfield is used to identify which VLANs this MLT 
                      	is associated with.  Each VLAN ID is stored as a bit.
		      	The most-significant (left-most) bit represents Vlan Id 1."
        ::= { rcMltEntry 42 }

rcMltEntryOwner OBJECT-TYPE
        SYNTAX        INTEGER {
                                none(1),
                                local(2),
                                remote(3),
                                localAndRemote(4)
                        }
        MAX-ACCESS      read-only
        STATUS          current
        DESCRIPTION     "Defines the owner of the MLT."
        ::= { rcMltEntry 43 }

rcMltDatapathProgrammingState OBJECT-TYPE
        SYNTAX        INTEGER {
                                none(1),
                                local(2),
                                remote(3),
                                localAndRemote(4)
                        }
        MAX-ACCESS      read-only
        STATUS          current
        DESCRIPTION     "Defines the datapath programming state of
                         the MLT."
        ::= { rcMltEntry 44 }


rcMltMcastDistribution OBJECT IDENTIFIER       ::= { rcMlt 11 }

rcMltMcastDistributionEnable OBJECT-TYPE
        SYNTAX        TruthValue
        MAX-ACCESS    read-write
        STATUS        current
        DESCRIPTION   "Used to enable/disable this feature to
                       distribute multicast traffic on MLT ports. All
                       the cards in the system must be E-Tickets.
                       Cannot perform distribution in a mixed mode."
        ::= { rcMltMcastDistribution 1 }

rcMltMcastDistributionGrpMask OBJECT-TYPE
        SYNTAX        IpAddress
        MAX-ACCESS    read-write
        STATUS        current
        DESCRIPTION   "Group Mask. Create a MLT abstraction layer to
                       distribute traffic basd on (source, group) information
                       of the multicast packet. The algorithm to pick
                       the actual port nedds to generate a fairly random
                       number for different combinations but a lways generate
                       the same number for a given (source, group) pair. By
                       default, the number of active ports of the MLT is used
                       to MOD the pseudo-random number generated by the XOR
                       of each byte of the masked group address with the
                       masked source address."
        ::= { rcMltMcastDistribution 2 }

rcMltMcastDistributionSrcMask OBJECT-TYPE
        SYNTAX        IpAddress
        MAX-ACCESS    read-write
        STATUS        current
        DESCRIPTION   "Source Mask."
        ::= { rcMltMcastDistribution 3 }

rcMltMcastDistributionRedistributionEnable OBJECT-TYPE
        SYNTAX        TruthValue
        MAX-ACCESS    read-write
        STATUS        current
        DESCRIPTION   "Enable redistribution."
        ::= { rcMltMcastDistribution 4 }

-- rcWeb related information

rcWebEnableServer OBJECT-TYPE
        SYNTAX        TruthValue
        MAX-ACCESS    read-write
        STATUS        current
        DESCRIPTION   "Control whether the web server should be enabled.
		      Setting this variable to true will make the server
		      operational.  Setting this variable to false will
		      disable server."
        DEFVAL        { false }
        ::= { rcWeb 1 }

rcWebRWAUserName OBJECT-TYPE
        SYNTAX        DisplayString (SIZE (1..20))
        MAX-ACCESS    read-write
        STATUS        current
        DESCRIPTION   "User name for the read-write-all web-server account."
        ::= { rcWeb 2 }

rcWebRWAPassword OBJECT-TYPE
        SYNTAX        DisplayString (SIZE (1..20))
        MAX-ACCESS    read-write
        STATUS        current
        DESCRIPTION   "Password for the read-write-all web-server account."
        ::= { rcWeb 3 }

rcWebRWUserName OBJECT-TYPE
        SYNTAX        DisplayString (SIZE (1..20))
        MAX-ACCESS    read-write
        STATUS        current
        DESCRIPTION   "User name for the read-write web-server account."
        ::= { rcWeb 4 }
 
rcWebRWPassword OBJECT-TYPE 
        SYNTAX        DisplayString (SIZE (1..20)) 
        MAX-ACCESS    read-write 
        STATUS        current 
        DESCRIPTION   "Password for the read-write web-server account." 
        ::= { rcWeb 5 } 

rcWebROUserName OBJECT-TYPE
        SYNTAX        DisplayString (SIZE (1..20))
        MAX-ACCESS    read-write
        STATUS        current
        DESCRIPTION   "User name for the read-only web-server account."
        ::= { rcWeb 6 }
 
rcWebROPassword OBJECT-TYPE 
        SYNTAX        DisplayString (SIZE (1..20))
        MAX-ACCESS    read-write 
        STATUS        current 
        DESCRIPTION   "Password for the read-only web-server account." 
        ::= { rcWeb 7 } 

rcWebLastChange OBJECT-TYPE 
        SYNTAX        TimeTicks 
        MAX-ACCESS    read-only 
        STATUS        current 
        DESCRIPTION   "Last web-browser initiated configuration
                      change since sysUpTime."
        ::= { rcWeb 8 }
 
rcWebNumHits OBJECT-TYPE
        SYNTAX        Integer32
        MAX-ACCESS    read-only
        STATUS        current
        DESCRIPTION   "Number of hits to the web-server"
	::= { rcWeb 9 } 

rcWebNumAccessChecks OBJECT-TYPE
        SYNTAX        Integer32
        MAX-ACCESS    read-only
        STATUS        current
        DESCRIPTION   "Number of access checks performed by the web-server"
        ::= { rcWeb 10 }

rcWebNumAccessBlocks OBJECT-TYPE
        SYNTAX        Integer32
        MAX-ACCESS    read-only
        STATUS        current
        DESCRIPTION   "Number of accesses blocked by the web-server"
        ::= { rcWeb 11 }

rcWebNumRxErrors OBJECT-TYPE 
        SYNTAX        Integer32 
        MAX-ACCESS    read-only 
        STATUS        current 
        DESCRIPTION   "Number of receive errors encountered by the web-server" 
        ::= { rcWeb 12 }

rcWebNumTxErrors OBJECT-TYPE 
        SYNTAX        Integer32 
        MAX-ACCESS    read-only 
        STATUS        current 
        DESCRIPTION   "Number of transmit errors encountered by the web-server" 
        ::= { rcWeb 13 }

rcWebNumSetRequest OBJECT-TYPE 
        SYNTAX        Integer32 
        MAX-ACCESS    read-only 
        STATUS        current 
        DESCRIPTION   "Number of set-request to the web-server" 
        ::= { rcWeb 14 }

rcWebPrimaryHtmlSourceDir OBJECT-TYPE
        SYNTAX        DisplayString (SIZE(0..64))
        MAX-ACCESS    read-write
        STATUS        current
        DESCRIPTION   "primary html source directory"
	DEFVAL	      { "local" }
        ::= { rcWeb 15 }
 
rcWebSecondaryHtmlSourceDir OBJECT-TYPE
        SYNTAX        DisplayString (SIZE(0..64))
        MAX-ACCESS    read-write
        STATUS        current
        DESCRIPTION   "secondary html source directory"
	DEFVAL	      { "pcmcia" }
        ::= { rcWeb 16 }
 
rcWebTertiaryHtmlSourceDir OBJECT-TYPE
        SYNTAX        DisplayString (SIZE(0..64))
        MAX-ACCESS    read-write
        STATUS        current
        DESCRIPTION   "tertiary html source directory"
        ::= { rcWeb 17 }
 
rcWebRWL3UserName OBJECT-TYPE
        SYNTAX        DisplayString (SIZE (1..20))
        MAX-ACCESS    read-write
        STATUS        current
        DESCRIPTION   "user name for the L3 web server account"
        ::= { rcWeb 18 }
 
rcWebRWL3Password OBJECT-TYPE
        SYNTAX        DisplayString (SIZE (1..20))
        MAX-ACCESS    read-write
        STATUS        current
        DESCRIPTION   "password for the L3 web server account"
        ::= { rcWeb 19 }

rcWebRWL2UserName OBJECT-TYPE
        SYNTAX        DisplayString (SIZE (1..20))
        MAX-ACCESS    read-write
        STATUS        current
        DESCRIPTION   "user name for the L2 web server account"
        ::= { rcWeb 20 }
 
rcWebRWL2Password OBJECT-TYPE
        SYNTAX        DisplayString (SIZE (1..20))
        MAX-ACCESS    read-write
        STATUS        current
        DESCRIPTION   "password for the L2 web server account"
        ::= { rcWeb 21 }
 
rcWebDefaultDisplayRows OBJECT-TYPE
        SYNTAX        INTEGER (10..100)
        MAX-ACCESS    read-write
        STATUS        current
        DESCRIPTION   "default display rows in html page."
	DEFVAL	      { 48 }
        ::= { rcWeb 22 }

rcWebLastHostAccessBlocked OBJECT-TYPE
        SYNTAX        IpAddress
        MAX-ACCESS    read-only
        STATUS        current
        DESCRIPTION   "last host access blocked"
        ::= { rcWeb 23 }
 
rcWebHelpTftpSourceDir OBJECT-TYPE
        SYNTAX        OCTET STRING (SIZE (0..256))
        MAX-ACCESS    read-write
        STATUS        current
        DESCRIPTION   "tftp source directory for help files"
        ::= { rcWeb 24 }

rcWebHttpPort OBJECT-TYPE
        SYNTAX        INTEGER (80 | 1024..49151)
        MAX-ACCESS    read-write
        STATUS        current
        DESCRIPTION   "the HTTP port for web access"
	DEFVAL	      { 80 }
        ::= { rcWeb 25 }

 rcWebSecureOnly OBJECT-TYPE
        SYNTAX        TruthValue
        MAX-ACCESS    read-write
        STATUS        current
        DESCRIPTION   "Control whether the secure only should be enabled.
         	       Setting this variable to true will make the server
		       support HTTPS only. Setting this variable to false
  		       will make the server support both HTTP & HTTPS"
        DEFVAL        { true }
        ::= { rcWeb 26 }
 
rcWebHttpsPort OBJECT-TYPE
        SYNTAX        Integer32 (443 | 1024..49151)
        MAX-ACCESS    read-write
        STATUS        current
        DESCRIPTION   "the HTTPs port for web access"
	DEFVAL	      { 443 }
        ::= { rcWeb 27 }
 

-- rcCli related information

rcCliRWAUserName OBJECT-TYPE
        SYNTAX        DisplayString (SIZE (1..20))
        MAX-ACCESS    read-write
        STATUS        current
        DESCRIPTION   "User name for the read-write-all CLI account."
        ::= { rcCli 1 }

rcCliRWAPassword OBJECT-TYPE
        SYNTAX        DisplayString (SIZE (0..20))
        MAX-ACCESS    read-write
        STATUS        current
        DESCRIPTION   "Password for the read-write-all CLI account."
        ::= { rcCli 2 }

rcCliRWUserName OBJECT-TYPE
        SYNTAX        DisplayString (SIZE (1..20))
        MAX-ACCESS    read-write
        STATUS        current
        DESCRIPTION   "User name for the read-write CLI account."
        ::= { rcCli 3 }
 
rcCliRWPassword OBJECT-TYPE 
        SYNTAX        DisplayString (SIZE (0..20)) 
        MAX-ACCESS    read-write 
        STATUS        current 
        DESCRIPTION   "Password for the read-write CLI account." 
        ::= { rcCli 4 } 

rcCliRWL3UserName OBJECT-TYPE
        SYNTAX        DisplayString (SIZE (1..20))
        MAX-ACCESS    read-write
        STATUS        current
        DESCRIPTION   "User name for the read-write layer-3 CLI account."
        ::= { rcCli 5 }

rcCliRWL3Password OBJECT-TYPE
        SYNTAX        DisplayString (SIZE (0..20))
        MAX-ACCESS    read-write
        STATUS        current
        DESCRIPTION   "Password for the read-write layer-3 CLI account."
        ::= { rcCli 6 }

rcCliRWL2UserName OBJECT-TYPE
        SYNTAX        DisplayString (SIZE (1..20))
        MAX-ACCESS    read-write
        STATUS        current
        DESCRIPTION   "User name for the read-write layer-2 CLI account."   
        ::= { rcCli 7 }  
 
rcCliRWL2Password OBJECT-TYPE
        SYNTAX        DisplayString (SIZE (0..20))
        MAX-ACCESS    read-write
        STATUS        current
        DESCRIPTION   "Password for the read-write layer-2 CLI account."
        ::= { rcCli 8 }

rcCliROUserName OBJECT-TYPE
        SYNTAX        DisplayString (SIZE (1..20))
        MAX-ACCESS    read-write
        STATUS        current
        DESCRIPTION   "User name for the read-only CLI account."
        ::= { rcCli 9 }
 
rcCliROPassword OBJECT-TYPE 
        SYNTAX        DisplayString (SIZE (0..20))
        MAX-ACCESS    read-write 
        STATUS        current 
        DESCRIPTION   "Password for the read-only CLI account." 
        ::= { rcCli 10 } 

rcCliMaxTelnetSessions OBJECT-TYPE 
        SYNTAX        INTEGER (0..8)
        MAX-ACCESS    read-write
        STATUS        current
        DESCRIPTION   "Used to indicate the maximum number of telnet
		      sessions the system will support."
	DEFVAL	      { 8 }
	::= { rcCli 11 } 

rcCliMaxRloginSessions OBJECT-TYPE
        SYNTAX        INTEGER (0..8)
        MAX-ACCESS    read-write  
        STATUS        current
        DESCRIPTION   "Used to indicate the maximum number of rlogin
                      sessions the system will support."
	DEFVAL	      { 8 }
        ::= { rcCli 12 }

rcCliTimeout OBJECT-TYPE
        SYNTAX        INTEGER (30..65535)
        MAX-ACCESS    read-write
        STATUS        current
        DESCRIPTION   "Used to indicate the amount of idle time, in
     		      seconds to wait before timing out telnet and 
		      rlogin sessions."
	DEFVAL        { 900 }
        ::= { rcCli 13 }

rcCliNumAccessViolations OBJECT-TYPE
        SYNTAX        Integer32
        MAX-ACCESS    read-only
        STATUS        current
        DESCRIPTION   "Used to indicate the number of CLI access
		      violations detected by the system."
        ::= { rcCli 14 }

rcCliRWL1UserName OBJECT-TYPE
        SYNTAX        DisplayString (SIZE (1..20))
        MAX-ACCESS    read-write
        STATUS        current
        DESCRIPTION   "User name for the read-write layer-1 CLI account."
        ::= { rcCli 15 }
 
rcCliRWL1Password OBJECT-TYPE
        SYNTAX        DisplayString (SIZE (0..20))
        MAX-ACCESS    read-write
        STATUS        current
        DESCRIPTION   "Password for the read-write layer-1 CLI account."
        ::= { rcCli 16 }

rcCliPasswordChange OBJECT-TYPE
        SYNTAX        INTEGER {
                         ro(1),
                         l1(2),
                         l2(3),
                         l3(4),
                         rw(5),
                         rwa(6),
                         webPassWdRo(18)
                      }
        MAX-ACCESS    read-only
        STATUS        current
        DESCRIPTION   "Used to indication which password is changed when
                       sending a rcCliPasswordChange trap."
        ::= { rcCli 17 }

rcCliPassChangeResult OBJECT-TYPE
        SYNTAX        INTEGER {
                         success(1),
                         fail(2)
                      }
        MAX-ACCESS    read-only
        STATUS        current
        DESCRIPTION   "Used to indication the result of changing password when
                       sending a rcPasswordChange trap."
        ::= { rcCli 18 }

rcCliRWEnable OBJECT-TYPE
        SYNTAX        TruthValue
        MAX-ACCESS    read-write
        STATUS        current
        DESCRIPTION   "Enable/Disable for the read-write CLI account."
        DEFVAL        { true }
        ::= { rcCli 19 }
 
rcCliRWL1Enable OBJECT-TYPE
        SYNTAX        TruthValue
        MAX-ACCESS    read-write
        STATUS        current
        DESCRIPTION   "Enable/Disable for the read-write-layer1 CLI
                       account."
        DEFVAL        { true }
        ::= { rcCli 20 }
 
rcCliRWL2Enable OBJECT-TYPE
        SYNTAX        TruthValue
        MAX-ACCESS    read-write
        STATUS        current
        DESCRIPTION   "Enable/Disable for the read-write-layer2 CLI
                       account."
        DEFVAL        { true }
        ::= { rcCli 21 }
 
rcCliRWL3Enable OBJECT-TYPE
        SYNTAX        TruthValue
        MAX-ACCESS    read-write
        STATUS        current
        DESCRIPTION   "Enable/Disable for the read-write-layer3 CLI
                       account."
        DEFVAL          { true }
        ::= { rcCli 22 }
 
rcCliROEnable OBJECT-TYPE
        SYNTAX        TruthValue
        MAX-ACCESS    read-write
        STATUS        current
        DESCRIPTION   "Enable/Disable for the read-only CLI account."
        DEFVAL          { true }
        ::= { rcCli 23 }        



-- Error Group
 
rcErrorLevel OBJECT-TYPE
        SYNTAX        Integer32
        MAX-ACCESS    read-only
        STATUS        current
        DESCRIPTION   "Error level indicator for the last error
                      reported in the system.  The meaning of
		      this value are :

			0 = Informative Information
			1 = Warning Condition
			2 = Error Condition
			3 = Manufacturing Information
			4 = Fatal Condition
		      "
        ::= { rcError 1 } 
 
rcErrorCode OBJECT-TYPE
        SYNTAX        Integer32
        MAX-ACCESS    read-only
        STATUS        current
        DESCRIPTION   "Error code indicator for the last error
                      reported in the system.  This is an encoded
		      value that identifies the software module
		      that generated the error message as well as
                      a specific error condition within that module.
		      This value is transparent to the user.  This
		      value is intended to help Accelar support and
		      development staff to isolate system problems."
        ::= { rcError 2 }

rcErrorText OBJECT-TYPE
        SYNTAX        DisplayString
        MAX-ACCESS    read-only
        STATUS        current
        DESCRIPTION   "Error string of the last error reported 
                      in the system."
        ::= { rcError 3 }

-- rcIpv6 mib

--
-- Textual convention from ietf-draft-2011-update-11
--

IpAddressOriginTC ::= TEXTUAL-CONVENTION
    STATUS     current
    DESCRIPTION
           "The origin of the address.

            manual(2) indicates that the address was manually configured
            to a specified address, e.g. by user configuration.

            dhcp(4) indicates an address that was assigned to this
            system by a DHCP server.

            linklayer(5) indicates an address created by IPv6 stateless
            auto-configuration.

            random(6) indicates an address chosen by the system at
            random, e.g. an IPv4 address within 169.254/16, or an RFC
            3041 privacy address."
    SYNTAX     INTEGER {
        other(1),
        manual(2),
        dhcp(4),
        linklayer(5),
        random(6)
    }


IpAddressStatusTC ::= TEXTUAL-CONVENTION
    STATUS     current
    DESCRIPTION
           "The status of an address.  Most of the states correspond to
            states from the IPv6 Stateless Address Autoconfiguration
            protocol [5].

            The preferred(1) state indicates that this is a valid
            address that can appear as the destination or source address
            of a packet.

            The deprecated(2) state indicates that this is a valid but
            deprecated address that should no longer be used as a source
            address in new communications, but packets addressed to such
            an address are processed as expected.

            The invalid(3) state indicates that this isn't a valid
            address and it shouldn't appear as the destination or source
            address of a packet.

            The inaccessible(4) state indicates that the address is not
            accessible because the interface to which this address is
            assigned is not operational.

            The unknown(5) state indicates that the status can not be
            determined for some reason.


            The tentative(6) state indicates the uniqueness of the
            address on the link is being verified.  Addresses in this
            state should not be used for general communication and
            should only be used to determine the uniqueness of the
            address.

            The duplicate(7) state indicates the address has been
            determined to be non-unique on the link and so must not be
            used.

            In the absence of other information, an IPv4 address is
            always preferred(1)."
    REFERENCE "RFC 2462"
    SYNTAX     INTEGER {
        preferred(1),
        deprecated(2),
        invalid(3),
        inaccessible(4),
        unknown(5),
        tentative(6),
        duplicate(7)
    }

-- Textual convention from ietf-draft-2011-update-11

rcIpv6Mib		OBJECT IDENTIFIER ::= { rcIpv6 1 }

rcIpv6Notifications	OBJECT IDENTIFIER ::= { rcIpv6Mib 0 }
rcIpv6Objects		OBJECT IDENTIFIER ::= { rcIpv6Mib 1 }

rcIpv6Scalars		OBJECT IDENTIFIER ::= { rcIpv6Objects 1 }

-- IPv6 ICMP rate limiting
rcIpv6IcmpErrorInterval OBJECT-TYPE
        SYNTAX        INTEGER (0..2147483647)
        MAX-ACCESS    read-write
        STATUS        current
        DESCRIPTION   "The rate (in milliseconds) at which 
                      ICMP error messages can be sent out.
                      A value of zero means not be send any."
        DEFVAL        { 1000 }
        ::= { rcIpv6Scalars 1 }


-- IPv6 Unreach  Admin Status
rcIpv6IcmpNetUnreach OBJECT-TYPE
        SYNTAX        TruthValue
        MAX-ACCESS    read-write
        STATUS        current
        DESCRIPTION   "Used to set icmp net unreach feature enable/ 
                       disable."
        DEFVAL        { false }
        ::= { rcIpv6Scalars 3 }

-- IPv6 RedirectMsg Admin Status
rcIpv6IcmpRedirectMsg OBJECT-TYPE
        SYNTAX        TruthValue
        MAX-ACCESS    read-write
        STATUS        current
        DESCRIPTION   "Used to set icmp redirect feature enable/
                       disable."
        DEFVAL        { false }
        ::= { rcIpv6Scalars 4 }

-- IPv6 ICMP rate limiting
rcIpv6IcmpErrorQuota OBJECT-TYPE
        SYNTAX        INTEGER (0..2000000)
        MAX-ACCESS    read-write
        STATUS        current
        DESCRIPTION   "The number of icmp error messages that 
                       can be sent during the icmp error interval.
                      A value of zero means not be send any."
        DEFVAL        { 50 }
        ::= { rcIpv6Scalars 5 }

-- IPv6 Clear Static Routes
rcIpv6RouteStaticClear OBJECT-TYPE
       SYNTAX          TruthValue
       MAX-ACCESS      read-write
       STATUS          current
       DESCRIPTION     "Clear all IPv6 static routes."
       DEFVAL          { false }
       ::= { rcIpv6Scalars 10 }

-- IPv6 Static Routes Global Admin Status
rcIpv6RouteStaticGlobalAdminEnabled OBJECT-TYPE
        SYNTAX        TruthValue
        MAX-ACCESS    read-write
        STATUS        current
        DESCRIPTION   "Used to globally enable/disable all IPv6 static routes."
        DEFVAL        { true }
        ::= { rcIpv6Scalars 11 }

-- IPv6 Interface Table
rcIpv6InterfaceTable OBJECT-TYPE
        SYNTAX          SEQUENCE OF RcIpv6InterfaceEntry
        MAX-ACCESS      not-accessible
        STATUS          current
        DESCRIPTION     "This table contains list of IPv6 interfaces and
             per-interface IPv6-specific information."
        ::= { rcIpv6Objects 2 }

rcIpv6InterfaceEntry OBJECT-TYPE
        SYNTAX          RcIpv6InterfaceEntry
        MAX-ACCESS      not-accessible
        STATUS          current
        DESCRIPTION     "An entry of ipv6 interface In Table containing
                         per-interface information."
        INDEX           { rcIpv6InterfaceIfIndex }
        ::= { rcIpv6InterfaceTable 1 }

RcIpv6InterfaceEntry ::=
        SEQUENCE {
                  rcIpv6InterfaceIfIndex                InterfaceIndex,
                  rcIpv6InterfaceIdentifier             Ipv6AddressIfIdentifier,
                  rcIpv6InterfaceIdentifierLength       INTEGER,
                  rcIpv6InterfaceDescr                  DisplayString,
                  rcIpv6InterfaceVlanId                 RcVlanIdOrNone,
                  rcIpv6InterfaceType                   INTEGER,
                  rcIpv6InterfaceReasmMaxSize           INTEGER,
                  rcIpv6InterfacePhysAddress            PhysAddress,
                  rcIpv6InterfaceAdminStatus            TruthValue,
                  rcIpv6InterfaceOperStatus             INTEGER,
                  rcIpv6InterfaceReachableTime          INTEGER,
                  rcIpv6InterfaceRetransmitTime         INTEGER,
                  rcIpv6InterfaceMulticastAdminStatus   TruthValue,
                  rcIpv6InterfaceRowStatus              RowStatus,
                  rcIpv6InterfaceDhcpEnabled            TruthValue,
                  rcIpv6InterfaceMacOffset              INTEGER,
                  rcIpv6InterfaceRetransmitTimer        Unsigned32,
		          rcIpv6InterfaceCurHopLimit            Integer32,
                  rcIpv6InterfaceClearIcmpStats         TruthValue,
                  rcIpv6InterfaceClearGeneralStats      TruthValue,
                  rcIpv6InterfaceClearNeighborCache     TruthValue,
                  rcIpv6InterfaceClearDestinationCache  TruthValue,
           	      rcIpv6InterfaceReversePathCheckEnable TruthValue,
                  rcIpv6InterfaceReversePathCheckMode   INTEGER,
		          rcIpv6InterfaceForwardingEnabled      TruthValue,
		          rcIpv6InterfaceRsmltEnable            TruthValue 	
                 }

rcIpv6InterfaceIfIndex OBJECT-TYPE
        SYNTAX        InterfaceIndex
        MAX-ACCESS    not-accessible
        STATUS        current
        DESCRIPTION   "An unique value to identify a physical interface
                               or a logical interface (VLAN).
                       For the brouter port it is the ifindex of the
                       port and in the case of the vlan it is the
                       ifindex of the vlan."
        ::= { rcIpv6InterfaceEntry 1 }

rcIpv6InterfaceIdentifier OBJECT-TYPE
        SYNTAX        Ipv6AddressIfIdentifier
        MAX-ACCESS    read-create
        STATUS        current
        DESCRIPTION   "IPv6 address
                       interface identifiers. This is a binary string
                       of up to 8 octets in network byte-order."
        ::= { rcIpv6InterfaceEntry 2 }

rcIpv6InterfaceIdentifierLength OBJECT-TYPE
        SYNTAX        INTEGER (0..64)
        UNITS         "bits"
        MAX-ACCESS    read-create
        STATUS        current
        DESCRIPTION
                      "The length of the Interface Identifier in bits."
        ::= { rcIpv6InterfaceEntry 3 }
rcIpv6InterfaceDescr OBJECT-TYPE
        SYNTAX        DisplayString
        MAX-ACCESS    read-create
        STATUS        current
        DESCRIPTION   "A textual string containing information about the
                      interface. This string may be set by network management system."
        ::= { rcIpv6InterfaceEntry 4 }

rcIpv6InterfaceVlanId OBJECT-TYPE
        SYNTAX        RcVlanIdOrNone
        MAX-ACCESS    read-create
        STATUS        current
        DESCRIPTION   "A value that uniquely identifies the Virtual LAN
                      associated with this entry. This value corresponds
                      to the lower 12 bits in the IEEE 802.1Q VLAN Tag."
        ::= { rcIpv6InterfaceEntry 5 }

rcIpv6InterfaceType OBJECT-TYPE
        SYNTAX        INTEGER {
                      ethernet(1),
                      pointToPoint(2),
                      pointToMultipoint(3)
                      }
        MAX-ACCESS    read-only
        STATUS        current
        DESCRIPTION   "The interface type."
        ::= { rcIpv6InterfaceEntry 6 }

rcIpv6InterfaceReasmMaxSize    OBJECT-TYPE
        SYNTAX        INTEGER (1280..1500 | 1850 | 9500)
        MAX-ACCESS    read-create
        STATUS        current
        DESCRIPTION   "MTU for this IPv6 interface, this value should
                       be same for all the ip addresses defined on
                       this interface.
                       In VSP9000, Supported range for IO interface,
		       supported range is(1280..1500 | 1850 | 9500).
		       For Mgmt interface, Supporyed Range is (1280..1500)"
        DEFVAL        { 1500 }
        ::= { rcIpv6InterfaceEntry 7 }

rcIpv6InterfacePhysAddress    OBJECT-TYPE
        SYNTAX        PhysAddress
        MAX-ACCESS    read-only
        STATUS        current
        DESCRIPTION   "The media-dependent `physical' address, for the
                       ethernet media it is the MAC address"
        ::= { rcIpv6InterfaceEntry 8 }


rcIpv6InterfaceAdminStatus OBJECT-TYPE
        SYNTAX        TruthValue
        MAX-ACCESS    read-create
        STATUS        current
        DESCRIPTION   "The indication of whether IPv6 is enabled (up)
             or disabled (down) on this interface. This object does not
             affect the state of the interface itself, only its
             connection to an IPv6 stack."
        DEFVAL        { false }
        ::= { rcIpv6InterfaceEntry 9 }

rcIpv6InterfaceOperStatus OBJECT-TYPE
        SYNTAX        INTEGER {
                        up(1),
                        down(2)
                      }
        MAX-ACCESS    read-only
        STATUS        current
        DESCRIPTION   "Operating status of the interface."
        ::= { rcIpv6InterfaceEntry 10 }

rcIpv6InterfaceReachableTime  OBJECT-TYPE
    SYNTAX     INTEGER (1..3600000)
    MAX-ACCESS read-create
    STATUS     current
    DESCRIPTION
	   "The time (in milliseconds) a neighbor is considered
            reachable after receiving a reachability confirmation.
            REFERENCE  RFC2461, Section 6.3.2"
        DEFVAL        { 30000 }
        ::= { rcIpv6InterfaceEntry 11 }

rcIpv6InterfaceRetransmitTime OBJECT-TYPE
    SYNTAX     INTEGER (0..3600000)
    MAX-ACCESS read-create
    STATUS     deprecated
    DESCRIPTION
           "Deprecated. Use rcIpv6InterfaceRetransmitTimer instead."
        DEFVAL        { 1000 }
        ::= { rcIpv6InterfaceEntry 12 }

rcIpv6InterfaceMulticastAdminStatus OBJECT-TYPE
        SYNTAX        TruthValue
        MAX-ACCESS    read-create
        STATUS        current
        DESCRIPTION   "This indicates the admin status for multicast
                       for this interface."
        DEFVAL        { false }
        ::= { rcIpv6InterfaceEntry 13 }

rcIpv6InterfaceRowStatus OBJECT-TYPE
        SYNTAX        RowStatus
        MAX-ACCESS    read-create
        STATUS        current
        DESCRIPTION   "Row status for create/delete."
        ::= { rcIpv6InterfaceEntry 14 }

rcIpv6InterfaceDhcpEnabled OBJECT-TYPE
        SYNTAX        TruthValue
        MAX-ACCESS    read-create
        STATUS        current
        DESCRIPTION   "Enable or disable DHCP on the specified
                      interface."
        DEFVAL        {false}
        ::= { rcIpv6InterfaceEntry 15 }

rcIpv6InterfaceMacOffset OBJECT-TYPE
        SYNTAX        INTEGER (0..1535)
        MAX-ACCESS    read-create
        STATUS        current
        DESCRIPTION   "Used to request a particular MAC for an IPv6 VLAN.
                       The system has 1536 mac addresses, last 4 are
                       reserved for MG.
                       One can either mention a mac offset while
                       configuring IPv6 on a vlan or it can be alloted
                       by the system within the above range."
        ::= { rcIpv6InterfaceEntry 16 }

rcIpv6InterfaceRetransmitTimer OBJECT-TYPE
       SYNTAX     Unsigned32 (1..4294967295)
       MAX-ACCESS    read-create
       STATUS        current
       DESCRIPTION   "The time (in milliseconds) between retransmissions of
            Neighbor Solicitation messages to a neighbor when
            resolving the address or when probing the reachability
            of a neighbor. REFERENCE RFC2461, Section 6.3.2"
       DEFVAL        { 1000 }
 ::= { rcIpv6InterfaceEntry 17 }

rcIpv6InterfaceCurHopLimit OBJECT-TYPE
        SYNTAX        Integer32 (1..255)
        MAX-ACCESS    read-create
        STATUS        current
        DESCRIPTION
           "The default value to be placed in the current hop limit
            field in router advertisements sent from this interface.
            The value should be set to the current diameter of the
            Internet.

            The default should be set to the value specified in the IANA
            web pages (www.iana.org) at the time of implementation.
            REFERENCE RFC2461 Section 6.2.1"

        DEFVAL        { 64 }
        ::= {  rcIpv6InterfaceEntry 18 }

rcIpv6InterfaceClearIcmpStats  OBJECT-TYPE
       SYNTAX         TruthValue
       MAX-ACCESS     read-create
       STATUS         current
       DESCRIPTION    "Clear ICMP statistics for an interface"
       DEFVAL             {false}
       ::= { rcIpv6InterfaceEntry 20 } 

rcIpv6InterfaceClearGeneralStats  OBJECT-TYPE
       SYNTAX         TruthValue
       MAX-ACCESS     read-create
       STATUS         current
       DESCRIPTION    "Clear general statistics for an interface"
       DEFVAL             {false}
       ::= { rcIpv6InterfaceEntry 21 }

rcIpv6InterfaceClearNeighborCache  OBJECT-TYPE
       SYNTAX         TruthValue
       MAX-ACCESS     read-create
       STATUS         current
       DESCRIPTION    "Clear Neighbor Cache for an interface"
       DEFVAL             {false}
       ::= { rcIpv6InterfaceEntry 22 }

rcIpv6InterfaceClearDestinationCache  OBJECT-TYPE
       SYNTAX         TruthValue
       MAX-ACCESS     read-create
       STATUS         current
       DESCRIPTION    "Clear Destination Cache for an interface"
       DEFVAL             {false}
       ::= { rcIpv6InterfaceEntry 23 }

rcIpv6InterfaceReversePathCheckEnable OBJECT-TYPE
        SYNTAX        TruthValue
        MAX-ACCESS    read-create
        STATUS        current
        DESCRIPTION   "Used to indicate whether this interface should
                      perform Reverse Path Check"
        DEFVAL        { false }
        ::= { rcIpv6InterfaceEntry 24 }

rcIpv6InterfaceReversePathCheckMode OBJECT-TYPE
        SYNTAX   INTEGER    {           
                    existonly (1),     
                    strict (2)     
                  }                
        MAX-ACCESS    read-create
        STATUS        current   
        DESCRIPTION   "Reverse Path Checking mode."
        DEFVAL        { existonly }
        ::= { rcIpv6InterfaceEntry 25 }

rcIpv6InterfaceForwardingEnabled OBJECT-TYPE
        SYNTAX        TruthValue
        MAX-ACCESS    read-create
        STATUS        current
        DESCRIPTION   "Used to indicate whether this interface should
                      perform forwarding"
        DEFVAL        { true }
        ::= { rcIpv6InterfaceEntry 26 }

rcIpv6InterfaceRsmltEnable OBJECT-TYPE
        SYNTAX        TruthValue
        MAX-ACCESS    read-create
        STATUS        current
        DESCRIPTION   "Used to indicate whether this interface has
                      rsmlt enabled or not"
        DEFVAL        { false }
        ::= { rcIpv6InterfaceEntry 27 }

-- End of IPv6 Interface Table
-- IPv6 Address Table

rcIpv6AddressTable OBJECT-TYPE
    SYNTAX     SEQUENCE OF RcIpv6AddressEntry
    MAX-ACCESS not-accessible
    STATUS     current
    DESCRIPTION
           "This table contains addressing information relevant
            to the entity's interfaces.

            This table does not contain multicast address 
            information. Tables for such information should be 
            contained in multicast specific MIBs such as RFC3019.

            While this table is writable the user will note that several
            objects, such as rcIpv6AddressOrigin, are not. The 
            intention in allowing a user to write to this table is to 
            allow them to add or remove any entry that isn't permanent.
            The user should be  allowed to modify objects and entries 
            when that would not cause inconsistencies within the table.
            Allowing write access to objects such as rcIpv6AddressOrigin
            could allow a user to insert an entry and then label it 
            incorrectly."
    ::= { rcIpv6Objects 3 }


rcIpv6AddressEntry OBJECT-TYPE
    SYNTAX     RcIpv6AddressEntry
    MAX-ACCESS not-accessible
    STATUS     current
    DESCRIPTION
           "An address mapping for a particular interface. Note that 
            when an address is added to an interface the resulted 
            prefix is added to that interface." 
    INDEX { rcIpv6AddressIfIndex, rcIpv6AddressAddr }
    ::= { rcIpv6AddressTable 1 }

RcIpv6AddressEntry ::= SEQUENCE {
        rcIpv6AddressIfIndex      InterfaceIndex,
        rcIpv6AddressAddr         Ipv6Address,
        rcIpv6AddressType         INTEGER,
        rcIpv6AddressPrefixLength INTEGER,
        rcIpv6AddressPrefix       RowPointer,
        rcIpv6AddressOrigin       IpAddressOriginTC,
        rcIpv6AddressStatus       IpAddressStatusTC,
        rcIpv6AddressCreated      TimeStamp,
        rcIpv6AddressLastChanged  TimeStamp,
        rcIpv6AddressRowStatus    RowStatus
    }

rcIpv6AddressIfIndex OBJECT-TYPE
    SYNTAX     InterfaceIndex
    MAX-ACCESS not-accessible
    STATUS     current
    DESCRIPTION
           "The index value which uniquely identifies the interface to
            which this entry is applicable.  The interface identified by
            a particular value of this index is the same interface as
            identified by the same value of the IfIndex field in the
            rcIpv6InterfaceIfIndex."
    ::= { rcIpv6AddressEntry 1 }

rcIpv6AddressAddr OBJECT-TYPE
    SYNTAX     Ipv6Address
    MAX-ACCESS not-accessible
    STATUS     current
    DESCRIPTION
           "The IPv6 address to which this entry's addressing 
            information pertains. This is one of the ipv6 addresses that
            this interface(identified by the rcIpv6AddressIfIndex) has. 

            Implementors need to be aware that if the size of
            ipAddressAddr exceeds 116 octets then OIDS of instances of
            columns in this row will have more than 128 sub-identifiers
            and cannot be accessed using SNMPv1, SNMPv2c or SNMPv3."
    ::= { rcIpv6AddressEntry 2 }

rcIpv6AddressType OBJECT-TYPE
    SYNTAX     INTEGER {
                 unicast(1),
                 anycast(2)
    }
    MAX-ACCESS read-write
    STATUS     current
    DESCRIPTION
           "The type of address.  It is either unicast or anycast
            IPv6 addresses (RFC3513).  "
    DEFVAL { unicast }
    ::= { rcIpv6AddressEntry 3 }

rcIpv6AddressPrefixLength OBJECT-TYPE
    SYNTAX     INTEGER (0..128)
    MAX-ACCESS read-write
    STATUS     current
    DESCRIPTION
           "Prefix Length value for this address. Cannot be changed
            after the creation. This field MUST be provided in order
            to create an entry in this table." 
    ::= { rcIpv6AddressEntry 4 }

rcIpv6AddressPrefix OBJECT-TYPE
    SYNTAX     RowPointer
    MAX-ACCESS read-only
    STATUS     current
    DESCRIPTION
           "A pointer to the row in the prefix table to which this
            address belongs.  May be { 0 0 } if there is no such row."
    ::= { rcIpv6AddressEntry 5 }

rcIpv6AddressOrigin OBJECT-TYPE
    SYNTAX     IpAddressOriginTC
    MAX-ACCESS read-only
    STATUS     current
    DESCRIPTION
           "The origin of the address. The origin of the address, one
            of: other(1),manual(2), dhcp(4),linklayer(5), random(6)"
    ::= { rcIpv6AddressEntry 6 }

rcIpv6AddressStatus OBJECT-TYPE
    SYNTAX     IpAddressStatusTC
    MAX-ACCESS read-only
    STATUS     current
    DESCRIPTION
           "The status of the address, describing if the address can be
            used for communication. It will One of: preferred(1),
            deprecated(2),invalid(3),inaccessible(4),unknown(5),
            tentative(6), duplicate(7)"
    DEFVAL { preferred }
    ::= { rcIpv6AddressEntry 7 }

rcIpv6AddressCreated OBJECT-TYPE
    SYNTAX     TimeStamp
    MAX-ACCESS read-only
    STATUS     current
    DESCRIPTION "The value of sysUpTime at the time this entry was
            created.  If this entry was created prior to the last re-
            initialization of the local network management subsystem,
            then this object contains a zero value."
    ::= { rcIpv6AddressEntry 8 }

rcIpv6AddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { rcIpv6AddressEntry 9 }

rcIpv6AddressRowStatus OBJECT-TYPE
    SYNTAX     RowStatus
    MAX-ACCESS read-create
    STATUS     current
    DESCRIPTION "The status of this conceptual row.
            The RowStatus TC requires that this DESCRIPTION clause
            states under which circumstances other objects in this row
            can be modified.  The value of this object has no effect on
            whether other objects in this conceptual row can be
            modified.
            A conceptual row can not be made active until the
            rcIpv6AddressIfIndex has been set to a valid index. Only
            createAndGo and Delete vlaues are supported. "
    ::= { rcIpv6AddressEntry 10 }

-- Neighbor Discovery Prefix Table

rcIpv6PrefixTable  OBJECT-TYPE
        SYNTAX          SEQUENCE OF RcIpv6PrefixEntry
        MAX-ACCESS      not-accessible
        STATUS          current
        DESCRIPTION     "This table allows the user to 
            determine the source of an IP address or set of 
            IP addresses and allows other tables to
            share the information via pointer rather than by copying.

            For example when the node configures both a unicast and
            anycast address for a prefix the ipAddressPrefix objects for
            those addresses will point to a single row in this table.


            This table primarily provides support for IPv6 prefixes and
            several of the objects are less meaningful for IPv4.  The
            table continues to allow IPv4 addresses to allow future
            flexibility.  In order to promote a common configuration
            this document includes suggestions for default values for
            IPv4 prefixes.  Each of these values may be overridden if an
            object is meaningful to the node.


            All prefixes used by this entity should be included in this
            table independent of how the entity learned the prefix.
            (This table isn't limited to prefixes learned from router
            advertisements.)  "
        ::= { rcIpv6Objects 4 }

rcIpv6PrefixEntry OBJECT-TYPE
        SYNTAX          RcIpv6PrefixEntry
        MAX-ACCESS      not-accessible
        STATUS          current
        DESCRIPTION     "An entry of ipv6 prefix In the Table."
        INDEX           { rcIpv6PrefixIfIndex, 
                          rcIpv6PrefixAddr,
                          rcIpv6PrefixLength } 
        ::= { rcIpv6PrefixTable 1 }

RcIpv6PrefixEntry ::=
        SEQUENCE {
                  rcIpv6PrefixIfIndex         InterfaceIndex, 
                  rcIpv6PrefixAddr            Ipv6Address,
                  rcIpv6PrefixLength          INTEGER,
                  rcIpv6PrefixVlanId          RcVlanIdOrNone,
                  rcIpv6PrefixUseDefaultVal   INTEGER,
                  rcIpv6PrefixAtValidLife     DateAndTime,
                  rcIpv6PrefixAtPreferredLife DateAndTime,
                  rcIpv6PrefixInfinite        TruthValue,
                  rcIpv6PrefixOnLinkFlag      TruthValue,
                  rcIpv6PrefixAutoFlag        TruthValue,
                  rcIpv6PrefixAddressEui      INTEGER,
                  rcIpv6PrefixNoAdvertise     TruthValue,
                  rcIpv6PrefixRowStatus       RowStatus,
                  rcIpv6PrefixValidLifetime   Unsigned32,
                  rcIpv6PrefixPreferredLifetime Unsigned32
                 }

rcIpv6PrefixIfIndex OBJECT-TYPE
        SYNTAX        InterfaceIndex 
        MAX-ACCESS    not-accessible 
        STATUS        current
        DESCRIPTION   "An unique value to identify an ipv6 interface.
                       For the brouter port it is the ifindex of the                        
                       port and in the case of the vlan it is the 
                       ifindex of the vlan."
        ::= { rcIpv6PrefixEntry 1 }

rcIpv6PrefixAddr OBJECT-TYPE
        SYNTAX        Ipv6Address
        MAX-ACCESS    not-accessible 
        STATUS        current
        DESCRIPTION   "Prefix to create an ipv6 address in ipv6 interface 
                       table."
        ::= { rcIpv6PrefixEntry 2 }

rcIpv6PrefixLength OBJECT-TYPE
        SYNTAX        INTEGER (0..128)
        MAX-ACCESS    not-accessible 
        STATUS        current
        DESCRIPTION   "Mask to create an ipv6 prefix entry 
                       either will be advertised or suppressed"
        ::= { rcIpv6PrefixEntry 3 }

rcIpv6PrefixVlanId OBJECT-TYPE
        SYNTAX        RcVlanIdOrNone
        MAX-ACCESS    read-only
        STATUS        current
        DESCRIPTION   "A value that uniquely identifies the Virtual LAN
                      associated with this entry. This value corresponds
                      to the lower 12 bits in the IEEE 802.1Q VLAN Tag."
        ::= { rcIpv6PrefixEntry 4 }


rcIpv6PrefixUseDefaultVal   OBJECT-TYPE
       SYNTAX        INTEGER {
                         none(1),               -- none of the following
                         valid-life(2),
                         preferred-life(3),
                         infinite(4),
                         no-advertise(5)
                      }
        MAX-ACCESS    read-write
        STATUS        current
        DESCRIPTION   "Select one of the value to set/use it's value        
                      to default value. This is a bitmask field, 
                      setting all the bits means that all the options 
                      will be reverted to default values."
        ::= { rcIpv6PrefixEntry 5 }

rcIpv6PrefixAtValidLife OBJECT-TYPE
        SYNTAX        DateAndTime  
        MAX-ACCESS    read-write
        STATUS        current
        DESCRIPTION   "Is the date and time, upon reaching this
                      value the prefix will be expired, 
                      if configured this option will 
                      be included in the neighbor advertisement 
                      for this prefix."
        ::= { rcIpv6PrefixEntry 8 }

rcIpv6PrefixAtPreferredLife OBJECT-TYPE
        SYNTAX        DateAndTime
        MAX-ACCESS    read-write
        STATUS        current
        DESCRIPTION   "Is the date and time, upon reaching this
                      value the prefix will be expired,
                      if configured this option will be
                      included in the neighbor advertisement
                      for this prefix."
        ::= { rcIpv6PrefixEntry 9 }

rcIpv6PrefixInfinite OBJECT-TYPE
        SYNTAX        TruthValue
        MAX-ACCESS    read-write
        STATUS        current
        DESCRIPTION   "if set the prefix's valid lifetime will 
                      not exprie."
        DEFVAL        { false }
        ::= { rcIpv6PrefixEntry 10 }

rcIpv6PrefixOnLinkFlag OBJECT-TYPE
        SYNTAX        TruthValue
        MAX-ACCESS    read-write
        STATUS        current
        DESCRIPTION   "if set then this prefix can be used 
                      for onlink determination. This value 
                      be placed in the L-bit field in the prefix
                      information option. It is a 1 bit flag. "
        DEFVAL        { true }
        ::= { rcIpv6PrefixEntry 11 }

rcIpv6PrefixAutoFlag OBJECT-TYPE
        SYNTAX        TruthValue
        MAX-ACCESS    read-write
        STATUS        current
        DESCRIPTION   "if set then this prefix can be used 
                      for autonomous address config. This value 
                      be placed in the auto-flag field in the prefix
                      information option. It is a 1 bit flag. "
        DEFVAL        { true }
        ::= { rcIpv6PrefixEntry 12 }

rcIpv6PrefixAddressEui OBJECT-TYPE
        SYNTAX     INTEGER {
                            eui-not-used(1),
                            eui-used-with-ul-complement(2),
                            eui-used-without-ul-complement(3)
                       } 
        MAX-ACCESS    read-write
        STATUS        current
        DESCRIPTION   "Use an EUI-64 interface ID in the low-order
                       64bits of the address when not specified in the address field.
                       If enabled use EUI, otherwise use EUI-64 and complement U/L
                       (Universal/Local bit). This operation should
                       be allowed for both global and link local
                       addresses. Once the entry is  create cannot modify this field.
                       This will be valid to use only when the PrefixLength is 64 or less"
        DEFVAL        { eui-not-used }
        ::= { rcIpv6PrefixEntry 13 }

rcIpv6PrefixNoAdvertise OBJECT-TYPE
        SYNTAX        TruthValue
        MAX-ACCESS    read-write
        STATUS        current
        DESCRIPTION   "if set then this prefix can not be included
                      in the neighbor advertisement."
        DEFVAL        { false }
        ::= { rcIpv6PrefixEntry 14 }

rcIpv6PrefixRowStatus OBJECT-TYPE
        SYNTAX        RowStatus
        MAX-ACCESS    read-create
        STATUS        current
        DESCRIPTION   "Row status for create/delete."
        ::= { rcIpv6PrefixEntry 15 }

rcIpv6PrefixValidLifetime OBJECT-TYPE
        SYNTAX        Unsigned32 (0..4294967295)
        MAX-ACCESS    read-create
        STATUS        current
        DESCRIPTION   "Valid lifetime in seconds, indicates
                      how long this prefix advertised in 
                      the nbr advertisement is valid.
                      Value of 4294967295 represents infinity."
        DEFVAL        { 2592000 }
        ::= { rcIpv6PrefixEntry 16 }

rcIpv6PrefixPreferredLifetime OBJECT-TYPE
        SYNTAX        Unsigned32 (0..4294967295)
        MAX-ACCESS    read-create
        STATUS        current
        DESCRIPTION   "Preferred lifetime in seconds, indicates
                      how long this prefix advertised in
                      advertisemt for this prefix.
                      Value of 4294967295 represents infinity."
        DEFVAL        { 604800 }
        ::= { rcIpv6PrefixEntry 17 }

-- IPV6 Neighbor Discovery Route Advertisement Table

rcIpv6RouterAdvertTable  OBJECT-TYPE
        SYNTAX          SEQUENCE OF  RcIpv6RouterAdvertEntry
        MAX-ACCESS      not-accessible
        STATUS          current
        DESCRIPTION     "The table containing information 
               used to construct router advertisements."
        ::= { rcIpv6Objects 5 }

rcIpv6RouterAdvertEntry OBJECT-TYPE
        SYNTAX          RcIpv6RouterAdvertEntry
        MAX-ACCESS      not-accessible
        STATUS          current
        DESCRIPTION
           "An entry containing information used to construct 
            router advertisements."
        INDEX  { rcIpv6RouterAdvertIfIndex }
        ::= { rcIpv6RouterAdvertTable 1 }

RcIpv6RouterAdvertEntry ::=
        SEQUENCE {
                rcIpv6RouterAdvertIfIndex       InterfaceIndex, 
                rcIpv6RouterAdvertSendAdverts   TruthValue,
                rcIpv6RouterAdvertUseDefaultVal INTEGER,
                rcIpv6RouterAdvertMaxInterval   INTEGER,
                rcIpv6RouterAdvertMinInterval   INTEGER,
                rcIpv6RouterAdvertReachableTime INTEGER,
                rcIpv6RouterAdvertRetransmitTimer  INTEGER,
                rcIpv6RouterAdvertDefaultLifeTime  INTEGER,
                rcIpv6RouterAdvertCurHopLimit      INTEGER,
                rcIpv6RouterAdvertManagedFlag      TruthValue,
                rcIpv6RouterAdvertOtherConfigFlag  TruthValue,
                rcIpv6RouterAdvertDadNsNum      INTEGER,
                rcIpv6RouterAdvertLinkMTU       Unsigned32,
		rcIpv6RouterAdvertRetransmitTime   Unsigned32
                 }

rcIpv6RouterAdvertIfIndex OBJECT-TYPE
        SYNTAX        InterfaceIndex 
        MAX-ACCESS    not-accessible  
        STATUS        current
        DESCRIPTION   "An unique value to identify an ipv6 interface.
                       For the brouter port it is the ifindex of the 
                       port and in the case of the vlan it is the 
                       ifindex of the vlan."
        ::= {  rcIpv6RouterAdvertEntry 1 }

rcIpv6RouterAdvertSendAdverts OBJECT-TYPE
    SYNTAX     TruthValue
    MAX-ACCESS read-write
    STATUS     current
    DESCRIPTION
           "A flag indicating whether or not the router sends periodic
            router advertisements and responds to router solicitations
            on this interface. REFERENCE RFC2461 Section 6.2.1"
    DEFVAL { false }
        ::= {  rcIpv6RouterAdvertEntry 2 }

rcIpv6RouterAdvertUseDefaultVal   OBJECT-TYPE
       SYNTAX        INTEGER {
                      none(1),               -- none of the following
                      send-advertisement(2),
                      max-interval(3),
                      min-interval(4),
                      default-life-time(5),
                      hop-limit(6),
                      managed-flag(7),
                      other-config-flag(8),
                      dad-ns-num(9),
		      linkMtu(10),
                      reachableTime(11),
		      retransmitTime(12)
                  }
        MAX-ACCESS    read-write
        STATUS        current
        DESCRIPTION   "Select one of the value to set/use it's
                       value to default value, or set all the bits
                       to indicate all the options will be set to 
                       their default value."
        ::= {  rcIpv6RouterAdvertEntry 3 }

rcIpv6RouterAdvertMaxInterval OBJECT-TYPE
        SYNTAX        INTEGER (4..1800)
        MAX-ACCESS    read-write
        STATUS        current
        DESCRIPTION   "Configure the max interval (in seconds) 
                      at which the transmission of route 
                      advertisments can occur on this interface.
                      This must be no less than 4 seconds and
                      no greater than 1800."
         DEFVAL        { 600 }
        ::= {  rcIpv6RouterAdvertEntry 4 }

 rcIpv6RouterAdvertMinInterval OBJECT-TYPE
        SYNTAX        INTEGER (3..1350)
        MAX-ACCESS    read-write
        STATUS        current
        DESCRIPTION   "Configure the min interval (in seconds) 
                      at which the transmission of route 
                      advertisments can occur on this interface.
                      This must be no less than 3 seconds and
                      no greater than .75* max-interval."
        DEFVAL        { 200 }
        ::= {  rcIpv6RouterAdvertEntry 5 }

 rcIpv6RouterAdvertReachableTime OBJECT-TYPE
        SYNTAX        INTEGER (0..3600000)
        MAX-ACCESS    read-write
        STATUS        current
        DESCRIPTION   "The value (in milliseconds) to be placed                               in the router advertisement message
                      sent by the router. The value zero means 
                      unspecified (by this router). Used to 
                      configure the amount of time that a remote
                      IPv6 node is considered reachable after 
                      some reachability confirmation event has 
                      occured.
                      REFERENCE RFC2461 Section 6.2.1"
        ::= {  rcIpv6RouterAdvertEntry 6 }

rcIpv6RouterAdvertRetransmitTimer OBJECT-TYPE
        SYNTAX        INTEGER (0..36000000) 
        MAX-ACCESS    read-only
        STATUS        deprecated
        DESCRIPTION   "The value (in milliseconds) to be placed                               in the retransmit timer field in router 
                      advertisement message sent from this 
                      interface. The value zero means 
                      unspecified (by this router). Used to 
                      configure the amount of time that router
                      should wait for the transmit to occur.
                      REFERENCE RFC2461 Section 6.2.1
		      Deprecated by rcIpv6RouterAdvertRetransmitTime"
        ::= {  rcIpv6RouterAdvertEntry 7 }

rcIpv6RouterAdvertDefaultLifeTime OBJECT-TYPE
        SYNTAX        INTEGER (0|4..9000)
        MAX-ACCESS    read-write
        STATUS        current
        DESCRIPTION   
           "The value to be placed in the router lifetime field of
            router advertisements sent from this interface.  This value
            MUST be either 0 or between rcIpv6RouterAdvertMaxInterval and
            9000 seconds.


            A value of zero indicates that the router is not to be used
            as a default router.

            The default is 3 * rcIpv6RouterAdvertMaxInterval.
            REFERENCE RFC2461 Section 6.2.1"
        DEFVAL        { 1800 }
        ::= {  rcIpv6RouterAdvertEntry 8 }

rcIpv6RouterAdvertCurHopLimit OBJECT-TYPE
        SYNTAX        INTEGER (0..255)
        MAX-ACCESS    read-write
        STATUS        current
        DESCRIPTION
           "The default value to be placed in the current hop limit
            field in router advertisements sent from this interface.
            The value should be set to the current diameter of the
            Internet.

            A value of zero in the router advertisement indicates that
            the advertisement isn't specifying a value for curHopLimit.

            The default should be set to the value specified in the IANA
            web pages (www.iana.org) at the time of implementation.
            REFERENCE RFC2461 Section 6.2.1"

        DEFVAL        { 64 }
        ::= {  rcIpv6RouterAdvertEntry 9 }

rcIpv6RouterAdvertManagedFlag OBJECT-TYPE
        SYNTAX        TruthValue
        MAX-ACCESS    read-write
        STATUS        current
        DESCRIPTION   "if true then the M-bit(Managed address
                      configureation)  in the router
                      adverisement will be set. 
                      REFERENCE RFC2461 Section 6.2.1"
        DEFVAL        { false }
        ::= {  rcIpv6RouterAdvertEntry 10 }

rcIpv6RouterAdvertOtherConfigFlag OBJECT-TYPE
        SYNTAX        TruthValue
        MAX-ACCESS    read-write
        STATUS        current
        DESCRIPTION   "if true then the O-bit (Other stateful 
                      Configuration) in the router
                      adverisement will be set. REFERENCE 
                      RFC2461 Section 6.2.1"
        DEFVAL        { false }
        ::= {  rcIpv6RouterAdvertEntry 11 }

rcIpv6RouterAdvertDadNsNum OBJECT-TYPE
        SYNTAX        INTEGER (0..600)
        MAX-ACCESS    read-write
        STATUS        current
        DESCRIPTION   "The number of neighbor solicitation
                      messages for DAD (Duplicate address 
                      detection). A value 0 is used to disable
                      DAD process on this interface. A value 1
                      is used to send one advertisment without
                      any retransmissions."
        ::= {  rcIpv6RouterAdvertEntry 12 }

rcIpv6RouterAdvertLinkMTU OBJECT-TYPE
    SYNTAX     Unsigned32 (0 | 1280..1500 | 1850 | 9500)
    MAX-ACCESS read-write
    STATUS     current
    DESCRIPTION
           "The value to be placed in MTU options sent by the 
            router on this interface.  A value of zero 
            indicates that no MTU options are sent. REFERENCE 
            RFC2461 Section 6.2.1"
    ::= { rcIpv6RouterAdvertEntry 13 }

rcIpv6RouterAdvertRetransmitTime OBJECT-TYPE
        SYNTAX        Unsigned32 (0..4294967295) 
        MAX-ACCESS    read-write
        STATUS        current
        DESCRIPTION   "The value (in milliseconds) to be placed                               in the retransmit timer field in router 
                      advertisement message sent from this 
                      interface. The value zero means 
                      unspecified (by this router). Used to 
                      configure the amount of time that router
                      should wait for the transmit to occur.
                      REFERENCE RFC2461 Section 6.2.1.
           	      Use this object to replace
		      rcIpv6RouterAdvertRetransmitTimer"
        ::= {  rcIpv6RouterAdvertEntry 14 }

-- IPV6 Static Route Table

rcIpv6StaticRouteTable OBJECT-TYPE
        SYNTAX          SEQUENCE OF RcIpv6StaticRouteEntry
        MAX-ACCESS      not-accessible
        STATUS          current
        DESCRIPTION     "This table contains list of routes that are
                         created by the user to destination networks."
        ::= { rcIpv6Objects 6 }

rcIpv6StaticRouteEntry OBJECT-TYPE
        SYNTAX          RcIpv6StaticRouteEntry
        MAX-ACCESS      not-accessible
        STATUS          current
        DESCRIPTION     "An entry in the static route table for IPv6
                         can be created for a destination with a specific
                         prefix length; multiple entries to the same
                         destination are created either by specifying the
                         next-hop or interfaceIndex or both to reach the destination.
                         However if the nexthop Ipv6 address is a link-local
                         address then IfIndex must be supplied."
        INDEX           { rcIpv6StaticRouteDest, 
                          rcIpv6StaticRoutePrefixLength,
                          rcIpv6StaticRouteNextHop,
                          rcIpv6StaticRouteIfIndex } 
        ::= { rcIpv6StaticRouteTable 1 }

RcIpv6StaticRouteEntry ::=
        SEQUENCE {
                  rcIpv6StaticRouteDest                  Ipv6Address,
                  rcIpv6StaticRoutePrefixLength          INTEGER,
                  rcIpv6StaticRouteNextHop               Ipv6Address,
                  rcIpv6StaticRouteIfIndex               InterfaceIndex,
                  rcIpv6StaticRouteDistance              INTEGER,
                  rcIpv6StaticRouteEnable                TruthValue,
                  rcIpv6StaticRouteStatus                INTEGER,
                  rcIpv6StaticRoutePreference            INTEGER,
                  rcIpv6StaticRouteRowStatus             RowStatus
                 }

rcIpv6StaticRouteDest OBJECT-TYPE
        SYNTAX        Ipv6Address
        MAX-ACCESS    not-accessible 
        STATUS        current
        DESCRIPTION   "The destination IPv6 address of this route.
                The values for the index objects rcIpv6StaticRouteDest and
                rcIpv6StaticRoutePrefixLength must be consistent.  When
                the value of rcIpv6StaticRouteDest (excluding the zone 
                index, if one is present) is x, then the bitwise 
                logical-AND of x with the value of the mask formed from
                the corresponding index object 
                rcIpv6StaticRoutePrefixLength MUST be equal to x. If 
                not, then the index pair is not consistent and an 
                inconsistentName error must be returned on SET or 
                CREATE requests."

        ::= { rcIpv6StaticRouteEntry 1 }

rcIpv6StaticRoutePrefixLength OBJECT-TYPE
        SYNTAX        INTEGER (0..128)
        MAX-ACCESS    not-accessible 
        STATUS        current
        DESCRIPTION   "Indicates the number of leading one bits which 
                form the mask to be logical-ANDed with the destination 
                address before being compared to the value in the
                rcIpv6StaticRouteDestAddr field."
        ::= { rcIpv6StaticRouteEntry 2 }

rcIpv6StaticRouteNextHop OBJECT-TYPE
        SYNTAX        Ipv6Address
        MAX-ACCESS    not-accessible 
        STATUS        current
        DESCRIPTION   "Next hop IPv6 address for this destination.
                On remote routes, the address of the next system en
                route.  For non-remote routes, a zero length string. " 
        ::= { rcIpv6StaticRouteEntry 3 }

rcIpv6StaticRouteIfIndex OBJECT-TYPE
        SYNTAX        InterfaceIndex
        MAX-ACCESS    not-accessible
        STATUS        current
        DESCRIPTION   "The ifIndex value which identifies the local 
                interface through which the next hop of this route 
                should be reached.  A value of 0 is valid and 
                represents the scenario where no interface is specified."
        ::= { rcIpv6StaticRouteEntry 4 }

rcIpv6StaticRouteDistance OBJECT-TYPE
        SYNTAX        INTEGER (1..65535 )
        MAX-ACCESS    read-write 
        STATUS        current
        DESCRIPTION   "cost/distance to reach the destination for this
                      node."
        DEFVAL        { 1 }
        ::= { rcIpv6StaticRouteEntry 5 }

rcIpv6StaticRouteStatus OBJECT-TYPE
       SYNTAX          INTEGER {
                         notReachable(1),
                         tryToResolve(2),
                         reachableNotInRtm(3),
                         reachableInRtm(4)
                       }
        MAX-ACCESS      read-only
        STATUS        	current
        DESCRIPTION   	"(1)notReachable means the route is not reachable and no 
                            neighbor request entry is built to resolved the next-hop. 
                            It happens when there is no route or neighbor to reach 
                            the static route's next-hop. 
                         (2)tryToResolve means the route is not reachable but a 
                            neighbor request entry is built to resolved the next-hop. 
                            It happens when there is a local equivelent route in system to 
                            reach the next-hop but the neighor is not learnt yet 
                         (3)reachableNotInRtm means the static route is 
                            reachable but it is not in RTM. It happens when the static 
                            route is reachable, but it is not the best among alternative
                            static route. 
                         (4)reachableInRtm means the static route is reachable 
                            and it is in RTM. It happens when the static 
                            route is reachable, and it is the best among alternative
                            static route to be added into RTM. " 
        ::= { rcIpv6StaticRouteEntry 6 }

rcIpv6StaticRoutePreference OBJECT-TYPE
        SYNTAX        INTEGER (1..255)
        MAX-ACCESS    read-write
        STATUS        current
        DESCRIPTION   "Used to indicate the route preference of this
                      entry.  If there are more than one route that can
                      be used to forward IP traffic, the route that has
                      a highest preference will be used instead of a
                      lower preference one. The higher the number,
                      the higher the preference."
        DEFVAL        { 5 }
        ::= { rcIpv6StaticRouteEntry 7 }

rcIpv6StaticRouteEnable OBJECT-TYPE
        SYNTAX         	TruthValue
        MAX-ACCESS     	read-write
        STATUS         	current
        DESCRIPTION    	"Used to enable/disable this entry."
	    DEFVAL        { true }
        ::= { rcIpv6StaticRouteEntry 8 }


rcIpv6StaticRouteRowStatus OBJECT-TYPE
        SYNTAX        RowStatus
        MAX-ACCESS    read-create
        STATUS        current
        DESCRIPTION   "Row status for create/delete."
        ::= { rcIpv6StaticRouteEntry 9 }

-- IPV6 Management Port Static Route Table

rcIpv6MgmtPortStaticRouteTable OBJECT-TYPE
        SYNTAX          SEQUENCE OF RcIpv6MgmtPortStaticRouteEntry
        MAX-ACCESS      not-accessible
        STATUS          current
        DESCRIPTION     "This table contains list of routes that are
                         created by the user to destination networks
			 on the management port."
        ::= { rcIpv6Objects 12 }

rcIpv6MgmtPortStaticRouteEntry OBJECT-TYPE
        SYNTAX          RcIpv6MgmtPortStaticRouteEntry
        MAX-ACCESS      not-accessible
        STATUS          current
        DESCRIPTION     "An entry in the static route table for IPv6
                         can be created for a destination with a specific
                         prefix length; multiple entries to the same
                         destination are created either by specifying the
                         next-hop or interfaceIndex or both to reach the destination.
                         However if the nexthop Ipv6 address is a link-local
                         address then IfIndex must be supplied."
        INDEX           { rcIpv6MgmtPortStaticRouteIfIndex,
			  rcIpv6MgmtPortStaticRouteDest, 
                          rcIpv6MgmtPortStaticRoutePrefixLength,
                          rcIpv6MgmtPortStaticRouteNextHop } 
        ::= { rcIpv6MgmtPortStaticRouteTable 1 }

RcIpv6MgmtPortStaticRouteEntry ::=
        SEQUENCE {
                  rcIpv6MgmtPortStaticRouteIfIndex	InterfaceIndex,
                  rcIpv6MgmtPortStaticRouteDest		Ipv6Address,
                  rcIpv6MgmtPortStaticRoutePrefixLength	INTEGER,
                  rcIpv6MgmtPortStaticRouteNextHop	Ipv6Address,
                  rcIpv6MgmtPortStaticRouteDistance	INTEGER,
                  rcIpv6MgmtPortStaticRouteEnable	TruthValue,
                  rcIpv6MgmtPortStaticRouteStatus	INTEGER,
                  rcIpv6MgmtPortStaticRoutePreference	INTEGER,
                  rcIpv6MgmtPortStaticRouteRowStatus	RowStatus
                 }

rcIpv6MgmtPortStaticRouteIfIndex OBJECT-TYPE
        SYNTAX        InterfaceIndex
        MAX-ACCESS    not-accessible
        STATUS        current
        DESCRIPTION   "The ifIndex value which identifies the local 
                interface through which the next hop of this route 
                should be reached.  A value of 0 is valid and 
                represents the scenario where no interface is specified."
        ::= { rcIpv6MgmtPortStaticRouteEntry 1 }

rcIpv6MgmtPortStaticRouteDest OBJECT-TYPE
        SYNTAX        Ipv6Address
        MAX-ACCESS    not-accessible 
        STATUS        current
        DESCRIPTION   "The destination IPv6 address of this route.
                The values for the index objects rcIpv6StaticRouteDest and
                rcIpv6StaticRoutePrefixLength must be consistent.  When
                the value of rcIpv6StaticRouteDest (excluding the zone 
                index, if one is present) is x, then the bitwise 
                logical-AND of x with the value of the mask formed from
                the corresponding index object 
                rcIpv6StaticRoutePrefixLength MUST be equal to x. If 
                not, then the index pair is not consistent and an 
                inconsistentName error must be returned on SET or 
                CREATE requests."

        ::= { rcIpv6MgmtPortStaticRouteEntry 2 }

rcIpv6MgmtPortStaticRoutePrefixLength OBJECT-TYPE
        SYNTAX        INTEGER (0..128)
        MAX-ACCESS    not-accessible 
        STATUS        current
        DESCRIPTION   "Indicates the number of leading one bits which 
                form the mask to be logical-ANDed with the destination 
                address before being compared to the value in the
                rcIpv6MgmtPortStaticRouteDestAddr field."
        ::= { rcIpv6MgmtPortStaticRouteEntry 3 }

rcIpv6MgmtPortStaticRouteNextHop OBJECT-TYPE
        SYNTAX        Ipv6Address
        MAX-ACCESS    not-accessible 
        STATUS        current
        DESCRIPTION   "Next hop IPv6 address for this destination.
                On remote routes, the address of the next system en
                route.  For non-remote routes, a zero length string. " 
        ::= { rcIpv6MgmtPortStaticRouteEntry 4 }

rcIpv6MgmtPortStaticRouteDistance OBJECT-TYPE
        SYNTAX        INTEGER (1..65535 )
        MAX-ACCESS    read-create
        STATUS        current
        DESCRIPTION   "cost/distance to reach the destination for this
                      node."
        DEFVAL        { 1 }
        ::= { rcIpv6MgmtPortStaticRouteEntry 5 }

rcIpv6MgmtPortStaticRouteStatus OBJECT-TYPE
       SYNTAX          INTEGER {
                         notReachable(1),
                         tryToResolve(2),
                         reachableNotInRtm(3),
                         reachableInRtm(4)
                       }
        MAX-ACCESS      read-only
        STATUS        	current
        DESCRIPTION   	"(1)notReachable means the route is not reachable and no 
                            neighbor request entry is built to resolved the next-hop. 
                            It happens when there is no route or neighbor to reach 
                            the static route's next-hop. 
                         (2)tryToResolve means the route is not reachable but a 
                            neighbor request entry is built to resolved the next-hop. 
                            It happens when there is a local equivelent route in system to 
                            reach the next-hop but the neighor is not learnt yet 
                         (3)reachableNotInRtm means the static route is 
                            reachable but it is not in RTM. It happens when the static 
                            route is reachable, but it is not the best among alternative
                            static route. 
                         (4)reachableInRtm means the static route is reachable 
                            and it is in RTM. It happens when the static 
                            route is reachable, and it is the best among alternative
                            static route to be added into RTM. " 
        ::= { rcIpv6MgmtPortStaticRouteEntry 6 }

rcIpv6MgmtPortStaticRoutePreference OBJECT-TYPE
        SYNTAX        INTEGER (1..255)
        MAX-ACCESS    read-create
        STATUS        current
        DESCRIPTION   "Used to indicate the route preference of this
                      entry.  If there are more than one route that can
                      be used to forward IP traffic, the route that has
                      a highest preference will be used instead of a
                      lower preference one. The higher the number,
                      the higher the preference."
        DEFVAL        { 5 }
        ::= { rcIpv6MgmtPortStaticRouteEntry 7 }

rcIpv6MgmtPortStaticRouteEnable OBJECT-TYPE
        SYNTAX         	TruthValue
        MAX-ACCESS     	read-create
        STATUS         	current
        DESCRIPTION    	"Used to enable/disable this entry."
	    DEFVAL        { true }
        ::= { rcIpv6MgmtPortStaticRouteEntry 8 }


rcIpv6MgmtPortStaticRouteRowStatus OBJECT-TYPE
        SYNTAX        RowStatus
        MAX-ACCESS    read-create
        STATUS        current
        DESCRIPTION   "Row status for create/delete."
        ::= { rcIpv6MgmtPortStaticRouteEntry 9 }

-- the Internet Address Translation table
--

rcIpv6NetToPhysicalTable OBJECT-TYPE
    SYNTAX     SEQUENCE OF RcIpv6NetToPhysicalEntry
    MAX-ACCESS not-accessible
    STATUS     current
    DESCRIPTION
           "The IP Address Translation table used for mapping from IP
            addresses to physical addresses.

            The Address Translation tables contain the IP address to
            'physical' address equivalences.  Some interfaces do not use
            translation tables for determining address equivalences
            (e.g., DDN-X.25 has an algorithmic method); if all
            interfaces are of this type, then the Address Translation
            table is empty, i.e., has zero entries.

            While many protocols may be used to populate this table, ARP
            [10] and Neighbor Discovery [4] are the most likely
            options."
    REFERENCE "RFC0826 and RFC2461"
    ::= { rcIpv6Objects 7 }

rcIpv6NetToPhysicalEntry OBJECT-TYPE
    SYNTAX     RcIpv6NetToPhysicalEntry
    MAX-ACCESS not-accessible
    STATUS     current
    DESCRIPTION
           "Each entry contains one IP address to `physical' address
            equivalence."
    INDEX       { rcIpv6NetToPhysicalIfIndex,
                  rcIpv6NetToPhysicalNetAddress }
    ::= { rcIpv6NetToPhysicalTable 1 }

RcIpv6NetToPhysicalEntry ::= SEQUENCE {
        rcIpv6NetToPhysicalIfIndex         InterfaceIndex,
        rcIpv6NetToPhysicalNetAddress      Ipv6Address,
        rcIpv6NetToPhysicalPhysAddress     PhysAddress,
        rcIpv6NetToPhysicalInterface       Integer32,
        rcIpv6NetToPhysicalLastUpdated     TimeStamp,
        rcIpv6NetToPhysicalType            INTEGER,
        rcIpv6NetToPhysicalState           INTEGER,
        rcIpv6NetToPhysicalRowStatus       RowStatus
    }

rcIpv6NetToPhysicalIfIndex OBJECT-TYPE
    SYNTAX     InterfaceIndex
    MAX-ACCESS not-accessible 
    STATUS     current
    DESCRIPTION
           "The index value which uniquely identifies the interface to
            which this entry is applicable.  The interface identified by
            a particular value of this index is the same interface as
            identified by the same value of the IfIndex field in the
            rcIpv6InterfaceIfIndex."
    ::= { rcIpv6NetToPhysicalEntry 1 }

rcIpv6NetToPhysicalNetAddress OBJECT-TYPE
    SYNTAX     Ipv6Address
    MAX-ACCESS not-accessible
    STATUS     current
    DESCRIPTION
           "The IP Address corresponding to the media-dependent
            `physical' address.  The address type of this object is
            specified in rcIpv6NetToPhysicalAddressType.


            Implementors need to be aware that if the size of
            rcIpv6NetToPhysicalNetAddress exceeds 115 octets then OIDS of
            instances of columns in this row will have more than 128
            sub-identifiers and cannot be accessed using SNMPv1, SNMPv2c
            or SNMPv3."
    ::= { rcIpv6NetToPhysicalEntry 2 }

rcIpv6NetToPhysicalPhysAddress OBJECT-TYPE
    SYNTAX     PhysAddress (SIZE(0..65535))
    MAX-ACCESS read-write
    STATUS     current
    DESCRIPTION
           "The media-dependent `physical' address.

            As the entries in this table are typically not persistent
            when this object is written the entity SHOULD NOT save the
            change to non-volatile storage. In the ethernet case
            it is a MAC address."
    ::= { rcIpv6NetToPhysicalEntry 3 }

rcIpv6NetToPhysicalInterface            OBJECT-TYPE
    SYNTAX     Integer32
    MAX-ACCESS read-write
    STATUS     current
    DESCRIPTION
           "The field represents either a physical port id or the MLT
            port id. This entry is associated either with
            a port or with a MLT in a VLAN/Brouter port. If the value is 
            0 then the interface is CP port."
    ::= { rcIpv6NetToPhysicalEntry 4 }

rcIpv6NetToPhysicalLastUpdated OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { rcIpv6NetToPhysicalEntry 5 }

rcIpv6NetToPhysicalType OBJECT-TYPE
    SYNTAX     INTEGER {
                other(1),        -- none of the following
                dynamic(2),
                static(3),
                local(4)         -- local interface
            }
    MAX-ACCESS read-write
    STATUS     current
    DESCRIPTION
           "The type of mapping.

            The 'dynamic(2)' type indicates that the IP address to
            physical addresses mapping has been dynamically resolved
            using e.g. IPv4 ARP or the IPv6 Neighbor Discovery protocol.

            The 'static(3)' type indicates that the mapping has been
            statically configured.  Both of these refer to entries that
            provide mappings for other entities addresses.

            The 'local(4)' type indicates that the mapping is provided
            for an entity's own interface address.

            As the entries in this table are typically not persistent
            when this object is written the entity SHOULD NOT save the
            change to non-volatile storage."
    DEFVAL { static }
    ::= { rcIpv6NetToPhysicalEntry 6 }

rcIpv6NetToPhysicalState OBJECT-TYPE
    SYNTAX     INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6),   -- state can not be determined
                                   -- for some reason.

                     incomplete(7) -- address resolution is being performed.
                    }
    MAX-ACCESS read-only
    STATUS     current
    DESCRIPTION
           "The Neighbor Unreachability Detection [4] state for the
            interface when the address mapping in this entry is used.
            If Neighbor Unreachability Detection is not in use (eg. for
            IPv4), this object is always unknown(6).
            REFERENCE RFC2461"
    ::= { rcIpv6NetToPhysicalEntry 8 }

rcIpv6NetToPhysicalRowStatus OBJECT-TYPE
    SYNTAX     RowStatus
    MAX-ACCESS read-create
    STATUS     current
    DESCRIPTION
           "The status of this conceptual row.

            The RowStatus TC requires that this DESCRIPTION clause
            states under which circumstances other objects in this row
            can be modified.  The value of this object has no effect on
            whether other objects in this conceptual row can be
            modified.

            A conceptual row can not be made active until the
            rcIpv6NetToPhysicalPhysAddress object has been set.
            Note that if the rcIpv6NetToPhysicalType is set to 
'invalid' the
            managed node may delete the entry independent of the state
            of this object. Only createandGo and Delete operations are 
            supported"
    ::= { rcIpv6NetToPhysicalEntry 9 }

rcIpv6PrefixListTableSize OBJECT-TYPE
        SYNTAX        Unsigned32
        MAX-ACCESS    read-only
        STATUS        current
        DESCRIPTION   "Size of Ipv6 Prefix List Table"
        ::= { rcIpv6Scalars 8 }

rcIpv6PrefixListTable OBJECT-TYPE
        SYNTAX          SEQUENCE OF RcIpv6PrefixListEntry
        MAX-ACCESS      not-accessible
        STATUS          current
        DESCRIPTION     "IPv6 Prefix List table"
        ::= { rcIpv6Objects 8 }

rcIpv6PrefixListEntry OBJECT-TYPE
        SYNTAX          RcIpv6PrefixListEntry
        MAX-ACCESS      not-accessible
        STATUS          current
        DESCRIPTION     "An entry of Ipv6 Prefix List Table."
        INDEX           { rcIpv6PrefixListId,
                          rcIpv6PrefixListPrefix,
                          rcIpv6PrefixListPrefixMaskLen }
        ::= { rcIpv6PrefixListTable 1 }

RcIpv6PrefixListEntry ::=
        SEQUENCE {
                rcIpv6PrefixListId               Unsigned32,
                rcIpv6PrefixListPrefix           Ipv6Address,
                rcIpv6PrefixListPrefixMaskLen    Unsigned32,
                rcIpv6PrefixListMaskLenFrom      Unsigned32,
                rcIpv6PrefixListMaskLenUpto      Unsigned32,
                rcIpv6PrefixListName             SnmpAdminString,
                rcIpv6PrefixListRowStatus        RowStatus
        }

rcIpv6PrefixListId OBJECT-TYPE
        SYNTAX        Unsigned32 (0..2147483647)
        MAX-ACCESS    not-accessible
        STATUS        current
        DESCRIPTION   "Id of an IPv6 Prefix List"
        ::= { rcIpv6PrefixListEntry 1 }

rcIpv6PrefixListPrefix OBJECT-TYPE
        SYNTAX        Ipv6Address
        MAX-ACCESS    not-accessible
        STATUS        current
        DESCRIPTION   "Is a member of a specific ipv6 prefix list.
                       Adding the prefix to the given ipv6 prefix list"
        ::= { rcIpv6PrefixListEntry 2 }

rcIpv6PrefixListPrefixMaskLen OBJECT-TYPE
        SYNTAX        Unsigned32 (0..128)
        MAX-ACCESS    not-accessible
        STATUS        current
        DESCRIPTION   "Mask length of the ipv6 prefix added to the prefix list"
        ::= { rcIpv6PrefixListEntry 3 }

rcIpv6PrefixListMaskLenFrom OBJECT-TYPE
        SYNTAX        Unsigned32 (0..128)
        MAX-ACCESS    read-create
        STATUS        current
        DESCRIPTION   "Lower bound of mask length of the ipv6 prefix added to
                       the prefix list"
        ::= { rcIpv6PrefixListEntry 4 }

rcIpv6PrefixListMaskLenUpto OBJECT-TYPE
        SYNTAX        Unsigned32 (0..128)
        MAX-ACCESS    read-create
        STATUS        current
        DESCRIPTION   "Higher bound of mask length of the ipv6 prefix added to
                       the prefix list"
        ::= { rcIpv6PrefixListEntry 5 }

rcIpv6PrefixListName OBJECT-TYPE
        SYNTAX        SnmpAdminString (SIZE(1..64))
        MAX-ACCESS    read-create
        STATUS        current
        DESCRIPTION   "Name of the Ipv6 prefix list"
        ::= { rcIpv6PrefixListEntry 6 }

rcIpv6PrefixListRowStatus OBJECT-TYPE
        SYNTAX        RowStatus
        MAX-ACCESS    read-create
        STATUS        current
        DESCRIPTION   "Used to create/delete entries in the ipv6 prefix list
                       table"
        ::= { rcIpv6PrefixListEntry 7 }

--
-- IPv6 OSPF MIB draft-ietf-ospf-ospfv3-mib-08.txt
--

-- IPv6 OSPF Texual conventions

UpToRefreshInterval ::= TEXTUAL-CONVENTION
         STATUS        current
         DESCRIPTION
            "The values one might be able to configure for
            variables bounded by the Refresh Interval"
         SYNTAX        Integer32 (1..1800)

RouterDeadRange ::= TEXTUAL-CONVENTION
         STATUS        current
         DESCRIPTION
            "The range of intervals in seconds that a routers hello
            must have not been seen before a neighbor declares the
            router down"
         SYNTAX        Integer32 (1..'FFF'h)


-- Ospfv3
rcOspfv3Mib     OBJECT IDENTIFIER ::= { rcOspfv3 1 }

rcOspfv3Objects     OBJECT IDENTIFIER ::= { rcOspfv3Mib 1 }
rcOspfv3Conformance OBJECT IDENTIFIER ::= { rcOspfv3Mib 2 }

-- OSPFv3 General Variables
rcOspfv3GeneralGroup OBJECT IDENTIFIER ::= { rcOspfv3Objects 1 }

-- These parameters apply globally to the Router's OSPFv3 Process
rcOspfv3RouterId OBJECT-TYPE
        SYNTAX         IpAddress
        MAX-ACCESS     read-write
        STATUS         current
        DESCRIPTION
            "A  32-bit  integer  uniquely  identifying  the
            router in the Autonomous System.
            To  ensure  uniqueness, this may
            default  to  the  value  of  one of the
            router's IPv4 interface addresses if IPv4 is
            configured on the router."
        ::= { rcOspfv3GeneralGroup 1 }

rcOspfv3AdminStat OBJECT-TYPE
        SYNTAX          INTEGER { enabled (1), disabled (2) }
        MAX-ACCESS      read-write
        STATUS          current
        DESCRIPTION
            "The  administrative  status  of  OSPFv3  in  the
            router.   The  value 'enabled' denotes that the
            OSPFv3 Process is active on at least  one  inter-
            face;  'disabled'  disables  it  on  all inter-
            faces."
        ::= { rcOspfv3GeneralGroup 2 }

rcOspfv3VersionNumber OBJECT-TYPE
        SYNTAX          INTEGER { version3(3) }
        MAX-ACCESS      read-only
        STATUS          current
        DESCRIPTION
            "The version number of OSPF for IPv6 is 3."
        ::= { rcOspfv3GeneralGroup 3 }

rcOspfv3AreaBdrRtrStatus OBJECT-TYPE
        SYNTAX          TruthValue
        MAX-ACCESS      read-only
        STATUS          current
        DESCRIPTION
            "A flag to note whether this router is an  area
            border router."
        REFERENCE
            "OSPF Version 2, Section 3 Splitting the AS into
            Areas"
        ::= { rcOspfv3GeneralGroup 4 }

rcOspfv3ASBdrRtrStatus OBJECT-TYPE
        SYNTAX          TruthValue
        MAX-ACCESS      read-write
        STATUS          current
        DESCRIPTION
            "A flag to note whether this router is  config-
            ured as an Autonomous System border router."
        REFERENCE
            "OSPF Version 2, Section 3.3  Classification  of
            routers"
        ::= { rcOspfv3GeneralGroup 5 }

rcOspfv3AsScopeLsaCount OBJECT-TYPE
        SYNTAX          Gauge32
        MAX-ACCESS      read-only
        STATUS          current
        DESCRIPTION
            "The number of AS-Scope (e.g. AS-External) link-state
            advertisements in the link-state database."
        ::= { rcOspfv3GeneralGroup 6 }

rcOspfv3AsScopeLsaCksumSum OBJECT-TYPE
        SYNTAX          Integer32
        MAX-ACCESS      read-only
        STATUS          current
        DESCRIPTION
            "The 32-bit unsigned sum of the LS checksums of
            the  AS-scoped link-state advertisements  con-
            tained in the link-state database. This sum
            can  be  used  to determine if there has been a
            change in a router's link state  database,  and
            to  compare  the  link-state  database  of  two
            routers."
        ::= { rcOspfv3GeneralGroup 7 }

rcOspfv3OriginateNewLsas OBJECT-TYPE
        SYNTAX          Counter32
        MAX-ACCESS      read-only
        STATUS          current
        DESCRIPTION
            "The number of  new  link-state  advertisements
            that  have been originated.  This number is in-
            cremented each time the router originates a new
            LSA."
        ::= { rcOspfv3GeneralGroup 8 }

rcOspfv3RxNewLsas OBJECT-TYPE
        SYNTAX          Counter32
        MAX-ACCESS      read-only
        STATUS          current
        DESCRIPTION
            "The number of  link-state  advertisements  re-
            ceived  determined  to  be  new instantiations.
            This number does not include  newer  instantia-
            tions  of self-originated link-state advertise-
            ments."
        ::= { rcOspfv3GeneralGroup 9 }

rcOspfv3ExtLsaCount OBJECT-TYPE
        SYNTAX          Gauge32
        MAX-ACCESS      read-only
        STATUS          current
        DESCRIPTION
            "The number of External(LS type 0x4005) in the link-
            state database"
        ::= { rcOspfv3GeneralGroup 10 }

rcOspfv3ExtAreaLsdbLimit OBJECT-TYPE
        SYNTAX          Integer32 (-1..'7FFFFFFF'h)
        MAX-ACCESS      read-write
        STATUS          current
        DESCRIPTION
            "The  maximum   number   of   non-default   AS-
            external-LSAs entries that can be stored in the
            link-state database.  If the value is -1, then
            there is no limit.

            When the number of non-default AS-external-LSAs
            in   a  router's  link-state  database  reaches
            rcOspfv3ExtAreaLsdbLimit, the router  enters  Overflow-
            State.   The   router  never  holds  more  than
            rcOspfv3ExtAreaLsdbLimit  non-default  AS-external-LSAs
            in  its  database. OspfExtAreaLsdbLimit MUST be set
            identically in all routers attached to the OSPFv3
            backbone  and/or  any regular OSPFv3 area. (i.e.,
            OSPFv3 stub areas and NSSAs are excluded)."
        ::= { rcOspfv3GeneralGroup 11 }

rcOspfv3MulticastExtensions OBJECT-TYPE
        SYNTAX          BITS {
                                 intraAreaMulticast(0),
                                 interAreaMulticast(1),
                                 interAsMulticast(2)
                             }

        MAX-ACCESS      read-write
        STATUS          current
        DESCRIPTION
            "A Bit Mask indicating whether the router is
            forwarding IPv6 multicast datagrams
            based on the algorithms defined in the  Multi-
            cast Extensions to OSPF.

            If intraAreaMulticast set, indicates that the router
            can forward  IPv6 multicast datagrams in the router's
            directly attached areas (called intra-area mul-
            ticast routing).

            If interAreaMulticast set, indicates that the router
            can forward IPv6 multicast datagrams between OSPFv3
            areas (called inter-area multicast routing).

            If interAsMulticast set, indicates that the router can
            forward  IPv6  multicast datagrams between Auto-
            nomous Systems (called inter-AS multicast rout-
            ing).

            Only certain combinations of bit settings are
            allowed, namely:
                    - All bits cleared (no multicasting)
                    - intraAreaMulticast only,
                    - intraAreaMulticast and interAreaMulticast,
                    - intraAreaMulticast and interAsMulticast
                    - intraAreaMulticast, interAreaMulticast and
                            interAsMulticast
            By default, all bits are cleared."
        ::= { rcOspfv3GeneralGroup 12 }

rcOspfv3ExitOverflowInterval OBJECT-TYPE
        SYNTAX          Unsigned32
        UNITS           "seconds"
        MAX-ACCESS      read-write
        STATUS          current
        DESCRIPTION
            "The number of  seconds  that,  after  entering
            OverflowState,  a  router will attempt to leave
            OverflowState. This allows the router to  again
            originate  non-default  AS-External-LSAs.  When
            set to 0, the router will not  leave  Overflow-
            State until restarted."
        ::= { rcOspfv3GeneralGroup 13 }

rcOspfv3DemandExtensions OBJECT-TYPE
        SYNTAX         TruthValue
        MAX-ACCESS     read-write
        STATUS         current
        DESCRIPTION
            "The router's support for demand routing."
        REFERENCE
            "OSPF Version 2, Appendix on Demand Routing"
        ::= { rcOspfv3GeneralGroup 14 }

rcOspfv3TrafficEngineeringSupport OBJECT-TYPE
        SYNTAX          TruthValue
        MAX-ACCESS      read-write
        STATUS          current
        DESCRIPTION
            "The router's support for traffic engineering
            extensions."
        ::= { rcOspfv3GeneralGroup 15 }

rcOspfv3ReferenceBandwidth OBJECT-TYPE
       SYNTAX       Unsigned32
       MAX-ACCESS   read-write
       STATUS       current
       DESCRIPTION
          "Reference bandwidth in kilobits/second for
          calculating default interface metrics. The
          default value is 100,000 KBPS (100 MBPS)"
    ::= { rcOspfv3GeneralGroup 16 }

rcOspfv3RestartSupport OBJECT-TYPE
       SYNTAX       INTEGER { none (1),
                              plannedOnly (2),
                              plannedAndUnplanned (3)
                         }
       MAX-ACCESS   read-write
       STATUS       current
       DESCRIPTION
          "The router's support for OSPF hitless restart.
          Options include: no restart support, only planned
          restarts or both planned and unplanned restarts."
       ::= { rcOspfv3GeneralGroup 17 }

rcOspfv3RestartInterval OBJECT-TYPE
       SYNTAX       Integer32 (1..1800)
       UNITS        "seconds"
       MAX-ACCESS   read-write
       STATUS       current
       DESCRIPTION
          "Configured OSPF hitless restart timeout interval."
       ::= { rcOspfv3GeneralGroup 18 }

rcOspfv3RestartStatus OBJECT-TYPE
       SYNTAX       INTEGER { notRestarting (1),
                              plannedRestart (2),
                              unplannedRestart (3)
                            }
       MAX-ACCESS   read-only
       STATUS       current
       DESCRIPTION
          "Current status of OSPF hitless restart."
       ::= { rcOspfv3GeneralGroup 19 }

rcOspfv3RestartAge OBJECT-TYPE
       SYNTAX       Integer32 (1..1800)
       UNITS        "seconds"
       MAX-ACCESS   read-only
       STATUS       current
       DESCRIPTION
          "Remaining time in current OSPF hitless restart
          interval."
       ::= { rcOspfv3GeneralGroup 20 }

rcOspfv3RestartExitReason OBJECT-TYPE
       SYNTAX       INTEGER { none (1),           -- none attempted
                              inProgress (2),     -- restart in
                                                  -- progress
                              completed (3),      -- successfully
                                                  -- completed
                              timedOut (4),       -- timed out
                              topologyChanged (5) -- aborted due to
                                                  -- topologychange.
                            }
       MAX-ACCESS   read-only
       STATUS       current
       DESCRIPTION
          "Describes the outcome of the last attempt at a
          hitless restart. If the value is 'none', no restart
           has yet been attempted. If the value is 'inProgress',
          a restart attempt is currently underway."
    ::= { rcOspfv3GeneralGroup 21 }

rcOspfv3BadLsaIgnore OBJECT-TYPE
        SYNTAX          INTEGER { enabled (1), disabled (2) }
        MAX-ACCESS      read-write
        STATUS          current
        DESCRIPTION
            "The  administrative  status  of  OSPFv3  in  the
            router.   The  value 'enabled' denotes that the
            OSPFv3 Process is active on at least  one  inter-
            face;  'disabled'  disables  it  on  all inter-
            faces."
        ::= { rcOspfv3GeneralGroup 22}

-- The OSPFv3 Area Data Structure contains information
-- regarding the various areas. The interfaces and
-- virtual links are configured as part of these areas.
-- Area 0.0.0.0, by definition, is the Backbone Area

rcOspfv3AreaTable OBJECT-TYPE
        SYNTAX          SEQUENCE OF RcOspfv3AreaEntry
        MAX-ACCESS      not-accessible
        STATUS          current
        DESCRIPTION
            "Information describing the configured  parame-
            ters  and cumulative statistics of the router's
            attached areas."
        REFERENCE
            "OSPF Version 2, Section 6 The Area Data Struc-
            ture"
        ::= { rcOspfv3Objects 2 }

rcOspfv3AreaEntry OBJECT-TYPE
        SYNTAX          RcOspfv3AreaEntry
        MAX-ACCESS      not-accessible
        STATUS          current
        DESCRIPTION
            "Information describing the configured parame-
            ters and cumulative statistics of one of the
            router's attached areas."
        INDEX           { rcOspfv3AreaId }
        ::= { rcOspfv3AreaTable 1 }

RcOspfv3AreaEntry ::= SEQUENCE {
        rcOspfv3AreaId
                IpAddress,
        rcOspfv3ImportAsExtern
                INTEGER,
        rcOspfv3AreaSpfRuns
                Counter32,
        rcOspfv3AreaBdrRtrCount
                Gauge32,
        rcOspfv3AreaAsBdrRtrCount
                Gauge32,
        rcOspfv3AreaScopeLsaCount
                Gauge32,
        rcOspfv3AreaScopeLsaCksumSum
                Integer32,
        rcOspfv3AreaSummary
                INTEGER,
        rcOspfv3AreaStatus
                RowStatus,
        rcOspfv3StubMetric
                Integer32,
        rcOspfv3AreaNssaTranslatorRole
                INTEGER,
        rcOspfv3AreaNssaTranslatorState
                INTEGER,
        rcOspfv3AreaNssaTranslatorStabilityInterval
                Unsigned32,
        rcOspfv3AreaNssaTranslatorEvents
                Counter32,
        rcOspfv3AreaStubMetricType
                INTEGER
        }

rcOspfv3AreaId OBJECT-TYPE
        SYNTAX          IpAddress
        MAX-ACCESS      not-accessible
        STATUS          current
        DESCRIPTION
            "A 32-bit integer uniquely identifying an area.
            Area ID 0.0.0.0 is used for the OSPFv3 backbone."
        REFERENCE
            "OSPF Version 2, Appendix C.2 Area parameters"
        ::= { rcOspfv3AreaEntry 1 }

rcOspfv3ImportAsExtern OBJECT-TYPE
        SYNTAX          INTEGER {
                        importExternal(1),   -- normal area
                        importNoExternal(2), -- stub area
                        importNssa(3)        -- not-so-stubby-area
                        }
        MAX-ACCESS      read-write
        STATUS          current
        DESCRIPTION
            "Indicates whether an area is a Stub area, NSSA, or
            standard area. AS-scope LSAs are not imported into Stub
            Areas or NSSAs. NSSAs import AS-External data as Type-7
            LSAs which have Area-scope"
        REFERENCE
            "OSPF Version 2, Appendix C.2 Area parameters"
        DEFVAL { importExternal }
        ::= { rcOspfv3AreaEntry 2 }

rcOspfv3AreaSpfRuns OBJECT-TYPE
        SYNTAX          Counter32
        MAX-ACCESS      read-only
        STATUS          current
        DESCRIPTION
            "The number of times that the intra-area  route
            table  has  been  calculated  using this area's
            link-state database.  This  is  typically  done
            using Dijkstra's algorithm."
        ::= { rcOspfv3AreaEntry 3 }

rcOspfv3AreaBdrRtrCount OBJECT-TYPE
        SYNTAX          Gauge32
        MAX-ACCESS      read-only
        STATUS          current
        DESCRIPTION
            "The total number of area border routers reach-
            able within this area.  This is initially zero,
            and is calculated in each SPF Pass."
        ::= { rcOspfv3AreaEntry 4 }

rcOspfv3AreaAsBdrRtrCount OBJECT-TYPE
        SYNTAX          Gauge32
        MAX-ACCESS      read-only
        STATUS          current
        DESCRIPTION
            "The total number of Autonomous  System  border
            routers  reachable  within  this area.  This is
            initially zero, and is calculated in  each  SPF
            Pass."
        ::= { rcOspfv3AreaEntry 5 }

rcOspfv3AreaScopeLsaCount OBJECT-TYPE
        SYNTAX          Gauge32
        MAX-ACCESS      read-only
        STATUS          current
        DESCRIPTION
            "The total number of Area-Scope link-state
            advertisements in  this  area's link-state
            database."
        ::= { rcOspfv3AreaEntry 6 }

rcOspfv3AreaScopeLsaCksumSum OBJECT-TYPE
        SYNTAX          Integer32
        MAX-ACCESS      read-only
        STATUS          current
        DESCRIPTION
            "The 32-bit unsigned sum of the Area-Scope link-state
            advertisements'  LS  checksums  contained in this
            area's link-state database.  The sum can be used
            to determine if  there  has been  a  change  in a
            router's link state database, and to compare the
            link-state database of two routers."
        ::= { rcOspfv3AreaEntry 7 }

rcOspfv3AreaSummary OBJECT-TYPE
        SYNTAX          INTEGER {
                        noAreaSummary(1),
                        sendAreaSummary(2)
                        }
        MAX-ACCESS      read-write
        STATUS          current
        DESCRIPTION
            "The variable rcOspfv3AreaSummary controls the  im-
            port  of  Inter-Area LSAs into stub areas.  It has
            no effect on other areas.

            If it is noAreaSummary, the router will neither
            originate  nor  propagate Inter-Area LSAs into the
            stub area.  It will rely entirely  on  its  de-
            fault route.

            If it is sendAreaSummary, the router will  both
            summarize and propagate Inter-Area LSAs."
        DEFVAL   { sendAreaSummary }
        ::= { rcOspfv3AreaEntry 8 }

rcOspfv3AreaStatus OBJECT-TYPE
        SYNTAX          RowStatus
        MAX-ACCESS      read-create
        STATUS          current
        DESCRIPTION
            "This variable controls the status of  the  en-
            try. The use of RowStatus is covered in more detail
            in [6]."
        ::= { rcOspfv3AreaEntry 9 }

rcOspfv3StubMetric OBJECT-TYPE
        SYNTAX          Integer32 (0..'FFFFFF'h)
        MAX-ACCESS      read-write
        STATUS          current
        DESCRIPTION
            "The metric value advertised for the default route
             into Stub and NSSA areas."
        ::= { rcOspfv3AreaEntry 10 }

rcOspfv3AreaNssaTranslatorRole OBJECT-TYPE
        SYNTAX          INTEGER { always(1), candidate(2) }
        MAX-ACCESS      read-write
        STATUS          current
        DESCRIPTION
            "Indicates an NSSA Border router's ability to
            perform NSSA translation of type-7 LSAs into
            type-5 LSAs."
        DEFVAL { candidate }
        ::= { rcOspfv3AreaEntry 11 }

rcOspfv3AreaNssaTranslatorState OBJECT-TYPE
        SYNTAX          INTEGER {
                        enabled(1),
                        elected(2),
                        disabled(3)
                        }
        MAX-ACCESS      read-only
        STATUS          current
        DESCRIPTION
            "Indicates if and how an NSSA Border router is
             performing NSSA translation of type-7 LSAs into type-5
             LSAs. When this object is set to enabled, the NSSA
             Border router's rcOspfv3AreaNssTranslatorRole
             has been set to always. When this object is set to
             elected, a candidate NSSA Border router is translating
             type-7 LSAs into type-5. When this object is set to
             disabled, a candidate NSSA Border router is NOT
             translating type-7 LSAs into type-5."
        ::= { rcOspfv3AreaEntry 12 }

rcOspfv3AreaNssaTranslatorStabilityInterval OBJECT-TYPE
        SYNTAX          Unsigned32
        UNITS           "seconds"
        MAX-ACCESS      read-write
        STATUS          current
        DESCRIPTION
            "The number of seconds after an elected translator
            determines its services are no longer required, that
            it should continue to perform its translation duties."
        DEFVAL { 40 }
        ::= { rcOspfv3AreaEntry 13 }

rcOspfv3AreaNssaTranslatorEvents OBJECT-TYPE
        SYNTAX          Counter32
        MAX-ACCESS      read-only
        STATUS          current
        DESCRIPTION
            "Indicates the number of Translator State changes
            that have occurred since the last boot-up."
        ::= { rcOspfv3AreaEntry 14 }

rcOspfv3AreaStubMetricType OBJECT-TYPE
        SYNTAX       INTEGER {
                        ospfv3Metric (1),  -- OSPF Metric
                        comparableCost (2), -- external type 1
                        nonComparable  (3) -- external type 2
                        }
        MAX-ACCESS   read-write
        STATUS       current
        DESCRIPTION
           "This variable displays the type of metric ad-
           vertised as a default route."
        DEFVAL { ospfv3Metric }
        ::= { rcOspfv3AreaEntry 15 }

-- OSPFv3 AS-Scope Link State Database

-- The Link State Database contains the AS-Scope Link State
-- Advertisements from throughout the areas that the
-- device is attached to.

rcOspfv3AsLsdbTable OBJECT-TYPE
        SYNTAX          SEQUENCE OF RcOspfv3AsLsdbEntry
        MAX-ACCESS      not-accessible
        STATUS          current
        DESCRIPTION
            "The OSPFv3 Process's AS-Scope Link State Database."
        ::= { rcOspfv3Objects 3 }

rcOspfv3AsLsdbEntry OBJECT-TYPE
        SYNTAX          RcOspfv3AsLsdbEntry
        MAX-ACCESS      not-accessible
        STATUS          current
        DESCRIPTION
            "A single AS-Scope Link State Advertisement."
        INDEX           { rcOspfv3AsLsdbType,
                          rcOspfv3AsLsdbRouterId,
                          rcOspfv3AsLsdbLsid }
        ::= { rcOspfv3AsLsdbTable 1 }

RcOspfv3AsLsdbEntry ::= SEQUENCE {
        rcOspfv3AsLsdbType
                INTEGER,
        rcOspfv3AsLsdbRouterId
                IpAddress,
        rcOspfv3AsLsdbLsid
                Unsigned32,
        rcOspfv3AsLsdbSequence
                Integer32,
        rcOspfv3AsLsdbAge
                Integer32,
        rcOspfv3AsLsdbChecksum
                Integer32,
        rcOspfv3AsLsdbAdvertisement
                OCTET STRING,
        rcOspfv3AsLsdbTypeKnown
                TruthValue
        }

rcOspfv3AsLsdbType OBJECT-TYPE
        SYNTAX         INTEGER{
        linkLsa (8),
                routerLink (8193),
                networkLink (8194),
                interAreaPrefix (8195),
                interAreaRouter (8196),
                type7 (8199),
                intraAreaPrefix (8201),
        asExternal (16389)
                                }
        MAX-ACCESS      not-accessible
        STATUS          current
        DESCRIPTION
            "The type of the link state advertisement.
            Each link state type has a separate advertise-
            ment format. AS-Scope LSAs not recognized by
            the router may be stored in the database."
        ::= { rcOspfv3AsLsdbEntry 1 }

rcOspfv3AsLsdbRouterId OBJECT-TYPE
        SYNTAX          IpAddress
        MAX-ACCESS      not-accessible
        STATUS          current
        DESCRIPTION
            "The 32 bit number that uniquely identifies the
            originating router in the Autonomous System."
        REFERENCE
            "OSPF Version 2, Appendix C.1 Global parameters"
        ::= { rcOspfv3AsLsdbEntry 2 }

rcOspfv3AsLsdbLsid OBJECT-TYPE
        SYNTAX          Unsigned32
        MAX-ACCESS      not-accessible
        STATUS          current
        DESCRIPTION
            "The Link State ID is an LS Type Specific field
            containing a unique identifier;
            it identifies the piece of the  routing  domain
            that is being described by the advertisement.
            In contrast to OSPFv2, the LSID has no
            addressing semantics."
        ::= { rcOspfv3AsLsdbEntry 3 }

-- Note that the OSPF Sequence Number is a 32 bit signed
-- integer.  It starts with the value '80000001'h,
-- or -'7FFFFFFF'h, and increments until '7FFFFFFF'h
-- Thus, a typical sequence number will be very negative.

rcOspfv3AsLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
        ::= { rcOspfv3AsLsdbEntry 4 }

rcOspfv3AsLsdbAge OBJECT-TYPE
        SYNTAX          Integer32 -- Should be 0..MaxAge
                                  -- unless DoNotAge bit is set
        UNITS           "seconds"
        MAX-ACCESS      read-only
        STATUS          current
        DESCRIPTION
            "This field is the age of the link state adver-
            tisement in seconds."
        REFERENCE
            "OSPF Version 2, Section 12.1.1 LS age"
        ::= { rcOspfv3AsLsdbEntry 5 }

rcOspfv3AsLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
        ::= { rcOspfv3AsLsdbEntry 6 }

rcOspfv3AsLsdbAdvertisement OBJECT-TYPE
        SYNTAX          OCTET STRING (SIZE (1..65535))
        MAX-ACCESS      read-only
        STATUS          current
        DESCRIPTION
            "The entire Link State Advertisement, including
            its header."
        ::= { rcOspfv3AsLsdbEntry 7 }

rcOspfv3AsLsdbTypeKnown OBJECT-TYPE
        SYNTAX          TruthValue
        MAX-ACCESS      read-only
        STATUS          current
        DESCRIPTION
            "Is the LSA type recognized by this Router?"
        ::= { rcOspfv3AsLsdbEntry 8 }


-- OSPFv3 Area-Scope Link State Database

-- The Link State Database contains the Area-Scope Link State
-- Advertisements from throughout the area that the
-- device is attached to.

rcOspfv3AreaLsdbTable OBJECT-TYPE
        SYNTAX          SEQUENCE OF RcOspfv3AreaLsdbEntry
        MAX-ACCESS      not-accessible
        STATUS          current
        DESCRIPTION
            "The OSPFv3 Process's Area-Scope Link State Database."
        ::= { rcOspfv3Objects 4 }

rcOspfv3AreaLsdbEntry OBJECT-TYPE
        SYNTAX          RcOspfv3AreaLsdbEntry
        MAX-ACCESS      not-accessible
        STATUS          current
        DESCRIPTION
            "A single Area-Scope Link State Advertisement."
        INDEX           { rcOspfv3AreaLsdbAreaId,
                          rcOspfv3AreaLsdbType,
                          rcOspfv3AreaLsdbRouterId,
                          rcOspfv3AreaLsdbLsid }
        ::= { rcOspfv3AreaLsdbTable 1 }

RcOspfv3AreaLsdbEntry ::= SEQUENCE {
        rcOspfv3AreaLsdbAreaId
                IpAddress,
        rcOspfv3AreaLsdbType
                INTEGER,
        rcOspfv3AreaLsdbRouterId
                IpAddress,
        rcOspfv3AreaLsdbLsid
                Unsigned32,
        rcOspfv3AreaLsdbSequence
                Integer32,
        rcOspfv3AreaLsdbAge
                Integer32,
        rcOspfv3AreaLsdbChecksum
                Integer32,
        rcOspfv3AreaLsdbAdvertisement
                OCTET STRING,
        rcOspfv3AreaLsdbTypeKnown
                TruthValue
        }

rcOspfv3AreaLsdbAreaId OBJECT-TYPE
        SYNTAX          IpAddress
        MAX-ACCESS      not-accessible
        STATUS          current
        DESCRIPTION
            "The 32 bit identifier of the Area from which the
            LSA was received."
        REFERENCE
            "OSPF Version 2, Appendix C.2 Area parameters"
        ::= { rcOspfv3AreaLsdbEntry 1 }

rcOspfv3AreaLsdbType OBJECT-TYPE
        SYNTAX         INTEGER{
        linkLsa (8),
                routerLink (8193),
                networkLink (8194),
                interAreaPrefix (8195),
                interAreaRouter (8196),
                type7 (8199),
                intraAreaPrefix (8201),
        asExternal (16389)
                                }
        MAX-ACCESS      not-accessible
        STATUS          current
        DESCRIPTION
            "The type  of  the  link  state  advertisement.
            Each  link state type has a separate advertise-
            ment format. Area-Scope LSAs unrecognized by the
            router are also stored in this database."
        ::= { rcOspfv3AreaLsdbEntry 2 }

rcOspfv3AreaLsdbRouterId OBJECT-TYPE
        SYNTAX          IpAddress
        MAX-ACCESS      not-accessible
        STATUS          current
        DESCRIPTION
            "The 32 bit number that uniquely identifies the
            originating router in the Autonomous System."
        REFERENCE
            "OSPF Version 2, Appendix C.1 Global parameters"
        ::= { rcOspfv3AreaLsdbEntry 3 }

rcOspfv3AreaLsdbLsid OBJECT-TYPE
        SYNTAX          Unsigned32
        MAX-ACCESS      not-accessible
        STATUS          current
        DESCRIPTION
            "The Link State ID is an LS Type Specific field
            containing a unique identifier;
            it identifies the piece of the  routing  domain
            that is being described by the advertisement.
            In contrast to OSPFv2, the LSID has no
            addressing semantics."
        ::= { rcOspfv3AreaLsdbEntry 4 }

-- Note that the OSPF Sequence Number is a 32 bit signed
-- integer.  It starts with the value '80000001'h,
-- or -'7FFFFFFF'h, and increments until '7FFFFFFF'h
-- Thus, a typical sequence number will be very negative.

rcOspfv3AreaLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
        ::= { rcOspfv3AreaLsdbEntry 5 }

rcOspfv3AreaLsdbAge OBJECT-TYPE
        SYNTAX          Integer32 -- Should be 0..MaxAge
                                  -- unless DoNotAge bit is set
        UNITS           "seconds"
        MAX-ACCESS      read-only
        STATUS          current
        DESCRIPTION
            "This field is the age of the link state adver-
            tisement in seconds."
        REFERENCE
            "OSPF Version 2, Section 12.1.1 LS age"
        ::= { rcOspfv3AreaLsdbEntry 6 }

rcOspfv3AreaLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
        ::= { rcOspfv3AreaLsdbEntry 7 }

rcOspfv3AreaLsdbAdvertisement OBJECT-TYPE
        SYNTAX          OCTET STRING (SIZE (1..65535))
        MAX-ACCESS      read-only
        STATUS          current
        DESCRIPTION
            "The entire Link State Advertisement, including
            its header."
        ::= { rcOspfv3AreaLsdbEntry 8 }

rcOspfv3AreaLsdbTypeKnown OBJECT-TYPE
        SYNTAX          TruthValue
        MAX-ACCESS      read-only
        STATUS          current
        DESCRIPTION
            "Is the LSA type recognized by this Router?"
        ::= { rcOspfv3AreaLsdbEntry 9 }

-- OSPFv3 Link-Scope Link State Database

-- The Link State Database contains the Link-Scope Link State
-- Advertisements from the links that the
-- device is attached to.

rcOspfv3LinkLsdbTable OBJECT-TYPE
        SYNTAX          SEQUENCE OF RcOspfv3LinkLsdbEntry
        MAX-ACCESS      not-accessible
        STATUS          current
        DESCRIPTION
            "The OSPFv3 Process's Link-Scope Link State Database."
        ::= { rcOspfv3Objects 5 }

rcOspfv3LinkLsdbEntry OBJECT-TYPE
        SYNTAX          RcOspfv3LinkLsdbEntry
        MAX-ACCESS      not-accessible
        STATUS          current
        DESCRIPTION
            "A single Link-Scope Link State Advertisement."
        INDEX           { rcOspfv3LinkLsdbIfIndex,
                          rcOspfv3LinkLsdbType,
                          rcOspfv3LinkLsdbRouterId,
                          rcOspfv3LinkLsdbLsid }
        ::= { rcOspfv3LinkLsdbTable 1 }

RcOspfv3LinkLsdbEntry ::= SEQUENCE {
        rcOspfv3LinkLsdbIfIndex
                InterfaceIndex,
        rcOspfv3LinkLsdbType
                INTEGER,
        rcOspfv3LinkLsdbRouterId
                IpAddress,
        rcOspfv3LinkLsdbLsid
                Unsigned32,
        rcOspfv3LinkLsdbSequence
                Integer32,
        rcOspfv3LinkLsdbAge
                Integer32,
        rcOspfv3LinkLsdbChecksum
                Integer32,
        rcOspfv3LinkLsdbAdvertisement
                OCTET STRING,
        rcOspfv3LinkLsdbTypeKnown
                TruthValue
        }

rcOspfv3LinkLsdbIfIndex OBJECT-TYPE
        SYNTAX         InterfaceIndex
        MAX-ACCESS     not-accessible
        STATUS         current
        DESCRIPTION
            "The identifier of the link from which the LSA
            was received."
        REFERENCE
            "OSPF Version 2, Appendix C.2 Area parameters"
        ::= { rcOspfv3LinkLsdbEntry 1 }

rcOspfv3LinkLsdbType OBJECT-TYPE
        SYNTAX         INTEGER{
        linkLsa (8),
                routerLink (8193),
                networkLink (8194),
                interAreaPrefix (8195),
                interAreaRouter (8196),
                type7 (8199),
                intraAreaPrefix (8201),
        asExternal (16389)
                                }
        MAX-ACCESS      not-accessible
        STATUS          current
        DESCRIPTION
            "The type of the link state advertisement.
            Each link state type has a separate advertise-
            ment format. Link-Scope LSAs unrecognized by the
            router are also stored in this database."
        ::= { rcOspfv3LinkLsdbEntry 2 }

rcOspfv3LinkLsdbRouterId OBJECT-TYPE
        SYNTAX          IpAddress
        MAX-ACCESS      not-accessible
        STATUS          current
        DESCRIPTION
            "The 32 bit number that uniquely identifies the
            originating router in the Autonomous System."
        REFERENCE
            "OSPF Version 2, Appendix C.1 Global parameters"
        ::= { rcOspfv3LinkLsdbEntry 3 }

rcOspfv3LinkLsdbLsid OBJECT-TYPE
        SYNTAX        Unsigned32
        MAX-ACCESS    not-accessible
        STATUS        current
        DESCRIPTION
            "The Link State ID is an LS Type Specific field
            containing a unique identifier;
            it identifies the piece of the  routing  domain
            that is being described by the advertisement.
            In contrast to OSPFv2, the LSID has no
            addressing semantics."
        ::= { rcOspfv3LinkLsdbEntry 4 }

-- Note that the OSPF Sequence Number is a 32 bit signed
-- integer.  It starts with the value '80000001'h,
-- or -'7FFFFFFF'h, and increments until '7FFFFFFF'h
-- Thus, a typical sequence number will be very negative.

rcOspfv3LinkLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
        ::= { rcOspfv3LinkLsdbEntry 5 }

rcOspfv3LinkLsdbAge OBJECT-TYPE
        SYNTAX          Integer32 -- Should be 0..MaxAge
                                  -- unless DoNotAge bit is set
        UNITS           "seconds"
        MAX-ACCESS      read-only
        STATUS          current
        DESCRIPTION
            "This field is the age of the link state
            advertisement in seconds."
        REFERENCE
            "OSPF Version 2, Section 12.1.1 LS age"
        ::= { rcOspfv3LinkLsdbEntry 6 }

rcOspfv3LinkLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
        ::= { rcOspfv3LinkLsdbEntry 7 }

rcOspfv3LinkLsdbAdvertisement OBJECT-TYPE
        SYNTAX          OCTET STRING (SIZE (1..65535))
        MAX-ACCESS      read-only
        STATUS          current
        DESCRIPTION
            "The entire Link State Advertisement, including
            its header."
        ::= { rcOspfv3LinkLsdbEntry 8 }

rcOspfv3LinkLsdbTypeKnown OBJECT-TYPE
        SYNTAX          TruthValue
        MAX-ACCESS      read-only
        STATUS          current
        DESCRIPTION
            "Indicates whether the LSA type is recognized by this
             Router."
        ::= { rcOspfv3LinkLsdbEntry 9 }


-- OSPF Host Table

-- The Host/Metric Table indicates what hosts are directly
-- attached to the Router, and what metrics and types of
-- service should be advertised for them.

rcOspfv3HostTable OBJECT-TYPE
        SYNTAX          SEQUENCE OF RcOspfv3HostEntry
        MAX-ACCESS      not-accessible
        STATUS          current
        DESCRIPTION
            "The list of Hosts, and their metrics, that the
            router will advertise as host routes."
        REFERENCE
            "OSPF Version 2, Appendix C.6  Host route param-
            eters"
        ::= { rcOspfv3Objects 6 }

rcOspfv3HostEntry OBJECT-TYPE
        SYNTAX          RcOspfv3HostEntry
        MAX-ACCESS      not-accessible
        STATUS          current
        DESCRIPTION
            "A metric to be advertised when a given host is
            reachable."
        INDEX           { rcOspfv3HostAddressType,
                          rcOspfv3HostAddress }
        ::= { rcOspfv3HostTable 1 }

RcOspfv3HostEntry ::= SEQUENCE {
        rcOspfv3HostAddressType
                INTEGER,
        rcOspfv3HostAddress
                OCTET STRING,
        rcOspfv3HostMetric
                Integer32,
        rcOspfv3HostStatus
                RowStatus,
        rcOspfv3HostAreaID
                IpAddress
        }

rcOspfv3HostAddressType OBJECT-TYPE
        SYNTAX          INTEGER {
                             unknown(0),
                             ipv4(1),
                             ipv6(2),
                             ipv4z(3),
                             ipv6z(4),
                             dns(16)
                         }
        MAX-ACCESS      not-accessible
        STATUS          current
        DESCRIPTION
            "The address type of rcOspfv3HostAddress. Only IPv6
            addresses without zone index are expected."
        REFERENCE
            "OSPF Version 2, Appendix C.6 Host route parame-
            ters"
        ::= { rcOspfv3HostEntry 1 }


rcOspfv3HostAddress OBJECT-TYPE
        SYNTAX          OCTET STRING (SIZE (16))
        MAX-ACCESS      not-accessible
        STATUS          current
        DESCRIPTION
            "The IPv6 Address of the Host. Must be a Global
             or Site-local address."
        REFERENCE
            "OSPF Version 2, Appendix C.6 Host route parame-
            ters"
        ::= { rcOspfv3HostEntry 2 }

rcOspfv3HostMetric OBJECT-TYPE
        SYNTAX          Integer32 (0..'FFFF'h)
        MAX-ACCESS      read-write
        STATUS          current
        DESCRIPTION
            "The Metric to be advertised."
        REFERENCE
            "OSPF Version 2, Appendix C.6 Host route parame-
            ters"
        ::= { rcOspfv3HostEntry 3 }

rcOspfv3HostStatus OBJECT-TYPE
        SYNTAX          RowStatus
        MAX-ACCESS      read-create
        STATUS          current
        DESCRIPTION
            "This variable controls the status of  the  en-
            try. The use of RowStatus is covered in more detail
            in [6]."
        ::= { rcOspfv3HostEntry 4 }

rcOspfv3HostAreaID OBJECT-TYPE
        SYNTAX          IpAddress
        MAX-ACCESS      read-write
        STATUS          current
        DESCRIPTION
            "The Area the Host Entry is to be found within.
            By  default, the area that a subsuming OSPFv3 in-
            terface is in, or 0.0.0.0"
        REFERENCE
            "OSPF Version 2, Appendix C.2 Area parameters"
        ::= { rcOspfv3HostEntry 5 }

-- OSPFv3 Interface Table

rcOspfv3IfTable OBJECT-TYPE
        SYNTAX          SEQUENCE OF RcOspfv3IfEntry
        MAX-ACCESS      not-accessible
        STATUS          current
        DESCRIPTION
            "The OSPFv3 Interface Table describes the  inter-
            faces from the viewpoint of OSPFv3."
        REFERENCE
            "OSPF Version 2, Appendix C.3  Router  interface
            parameters"
        ::= { rcOspfv3Objects 7 }

rcOspfv3IfEntry OBJECT-TYPE
        SYNTAX          RcOspfv3IfEntry
        MAX-ACCESS      not-accessible
        STATUS          current
        DESCRIPTION
            "The OSPFv3 Interface Entry describes one  inter-
            face from the viewpoint of OSPFv3."
        INDEX           { rcOspfv3IfIndex }
        ::= { rcOspfv3IfTable 1 }


RcOspfv3IfEntry ::= SEQUENCE {
        rcOspfv3IfIndex
                InterfaceIndex,
        rcOspfv3IfAreaId
                IpAddress,
        rcOspfv3IfType
                INTEGER,
        rcOspfv3IfAdminStat
                INTEGER,
        rcOspfv3IfRtrPriority
                Integer32,
        rcOspfv3IfTransitDelay
                Integer32,
        rcOspfv3IfRetransInterval
                Integer32,
        rcOspfv3IfHelloInterval
                Integer32,
        rcOspfv3IfRtrDeadInterval
                 Integer32,
        rcOspfv3IfPollInterval
                Unsigned32,
        rcOspfv3IfState
                INTEGER,
        rcOspfv3IfDesignatedRouter
                IpAddress,
        rcOspfv3IfBackupDesignatedRouter
                IpAddress,
        rcOspfv3IfEvents
                Counter32,
        rcOspfv3IfStatus
                RowStatus,
        rcOspfv3IfMulticastForwarding
                INTEGER,
        rcOspfv3IfDemand
                TruthValue,
        rcOspfv3IfMetricValue
                Integer32,
        rcOspfv3IfLinkScopeLsaCount
                Gauge32,
        rcOspfv3IfLinkLsaCksumSum
                Integer32,
        rcOspfv3IfInstId
                Integer32,
        rcOspfv3IfDemandNbrProbe
                TruthValue,
        rcOspfv3IfDemandNbrProbeRetxLimit
                Unsigned32,
        rcOspfv3IfDemandNbrProbeInterval
                Unsigned32
        }

rcOspfv3IfIndex OBJECT-TYPE
        SYNTAX          InterfaceIndex
        MAX-ACCESS      not-accessible
        STATUS          current
        DESCRIPTION
            "The interface index of this OSPFv3 interface.
             It corresponds to the interface index of the
             IPv6 interface on which OSPFv3 is configured."
        ::= { rcOspfv3IfEntry 1 }

rcOspfv3IfAreaId OBJECT-TYPE
        SYNTAX          IpAddress
        MAX-ACCESS      read-write
        STATUS          current
        DESCRIPTION
            "A 32-bit integer uniquely identifying the area
            to  which  the  interface  connects.   Area  ID
            0.0.0.0 is used for the OSPFv3 backbone."
        DEFVAL          { '00000000'H } -- 0.0.0.0
        ::= { rcOspfv3IfEntry 2 }

rcOspfv3IfType OBJECT-TYPE
        SYNTAX          INTEGER {
                        broadcast(1),
                        nbma(2),
                        pointToPoint(3),
                        pointToMultipoint(5),
			passive(6)
                        }
        MAX-ACCESS      read-write
        STATUS          current
        DESCRIPTION
            "The OSPFv3 interface type."
        ::= { rcOspfv3IfEntry 3 }

rcOspfv3IfAdminStat OBJECT-TYPE
        SYNTAX          INTEGER { enabled (1), disabled (2) }
        MAX-ACCESS      read-write
        STATUS          current
        DESCRIPTION
            "The OSPFv3 interface's  administrative  status.
            The  value formed on the interface, and the in-
            terface will be advertised as an internal route
            to  some  area.   The  value 'disabled' denotes
            that the interface is external to OSPFv3."
        DEFVAL          { enabled }
        ::= { rcOspfv3IfEntry 4 }

rcOspfv3IfRtrPriority OBJECT-TYPE
        SYNTAX          Integer32 (0..'FF'h)
        MAX-ACCESS      read-write
        STATUS          current
        DESCRIPTION
            "The  priority  of  this  interface.   Used  in
            multi-access  networks,  this  field is used in
            the designated router election algorithm.   The
            value 0 signifies that the router is not eligi-
            ble to become the  designated  router  on  this
            particular  network.   In the event of a tie in
            this value, routers will use their Router ID as
            a tie breaker."
        DEFVAL          { 1 }
        ::= { rcOspfv3IfEntry 5 }

rcOspfv3IfTransitDelay OBJECT-TYPE
        SYNTAX          Integer32 (1..1800)
        UNITS           "seconds"
        MAX-ACCESS      read-write
        STATUS          current
        DESCRIPTION
            "The estimated number of seconds  it  takes  to
            transmit  a  link state update packet over this
            interface."
        DEFVAL          { 1 }
        ::= { rcOspfv3IfEntry 6 }

rcOspfv3IfRetransInterval OBJECT-TYPE
        SYNTAX          Integer32 (1..1800)
        UNITS           "seconds"
        MAX-ACCESS      read-write
        STATUS          current
        DESCRIPTION
            "The number of seconds between  link-state  ad-
            vertisement  retransmissions,  for  adjacencies
            belonging to this  interface.   This  value  is
            also used when retransmitting database descrip-
            tion and link-state request packets."
        DEFVAL          { 5 }
        ::= { rcOspfv3IfEntry 7 }

rcOspfv3IfHelloInterval OBJECT-TYPE
        SYNTAX          Integer32 (1..'FFFF'h)
        UNITS           "seconds"
        MAX-ACCESS      read-write
        STATUS          current
        DESCRIPTION
            "The length of time, in  seconds,  between  the
            Hello  packets that the router sends on the in-
            terface.  This value must be the same  for  all
            routers attached to a common network."
        DEFVAL          { 10 }
        ::= { rcOspfv3IfEntry 8 }

rcOspfv3IfRtrDeadInterval OBJECT-TYPE
        SYNTAX          Integer32 (1..'FFFF'h)
        UNITS           "seconds"
        MAX-ACCESS      read-write
        STATUS          current
        DESCRIPTION
            "The number of seconds that  a  router's  Hello
            packets  have  not been seen before it's neigh-
            bors declare the router down.  This  should  be
            some  multiple  of  the  Hello  interval.  This
            value must be the same for all routers attached
            to a common network."
        DEFVAL          { 40 }
        ::= { rcOspfv3IfEntry 9 }

rcOspfv3IfPollInterval OBJECT-TYPE
        SYNTAX          Unsigned32
        UNITS           "seconds"
        MAX-ACCESS      read-write
        STATUS          current
        DESCRIPTION
            "The larger time interval, in seconds,  between
            the  Hello  packets  sent  to  an inactive non-
            broadcast multi- access neighbor."
        DEFVAL          { 120 }
        ::= { rcOspfv3IfEntry 10 }

rcOspfv3IfState OBJECT-TYPE
        SYNTAX          INTEGER {
                        down(1),
                        loopback(2),
                        waiting(3),
                        pointToPoint(4),
                        designatedRouter(5),
                        backupDesignatedRouter(6),
                        otherDesignatedRouter(7)
                        }
        MAX-ACCESS      read-only
        STATUS          current
        DESCRIPTION
            "The OSPFv3 Interface State."
        ::= { rcOspfv3IfEntry 11 }

rcOspfv3IfDesignatedRouter OBJECT-TYPE
        SYNTAX          IpAddress
        MAX-ACCESS      read-only
        STATUS          current
        DESCRIPTION
            "The Router ID of the Designated Router."
        ::= { rcOspfv3IfEntry 12 }

rcOspfv3IfBackupDesignatedRouter OBJECT-TYPE
        SYNTAX          IpAddress
        MAX-ACCESS      read-only
        STATUS          current
        DESCRIPTION
            "The  Router ID of  the  Backup   Designated
            Router."
        ::= { rcOspfv3IfEntry 14 }

rcOspfv3IfEvents OBJECT-TYPE
        SYNTAX          Counter32
        MAX-ACCESS      read-only
        STATUS          current
        DESCRIPTION
            "The number of times this  OSPF  interface  has
            changed its state, or an error has occurred."
        ::= { rcOspfv3IfEntry 15 }

rcOspfv3IfStatus OBJECT-TYPE
        SYNTAX          RowStatus
        MAX-ACCESS      read-create
        STATUS          current
        DESCRIPTION
            "This variable controls the status of  the  en-
            try. The use of RowStatus is covered in more detail in
            [6]."
        ::= { rcOspfv3IfEntry 17 }

rcOspfv3IfMulticastForwarding OBJECT-TYPE
        SYNTAX          INTEGER {
                        blocked(1),   -- no multicast forwarding
                        multicast(2), -- using multicast address
                        unicast(3)    -- to each OSPFv3 neighbor
                        }
        MAX-ACCESS      read-write
        STATUS          current
        DESCRIPTION
            "The way multicasts should  forwarded  on  this
            interface;  not  forwarded,  forwarded  as data
            link multicasts, or forwarded as data link uni-
            casts.   Data link multicasting is not meaning-
            ful on point to point and NBMA interfaces,  and
            setting rcOspfv3MulticastForwarding to 0 effective-
            ly disables all multicast forwarding."
        DEFVAL { blocked }
        ::= { rcOspfv3IfEntry 18 }

rcOspfv3IfDemand OBJECT-TYPE
        SYNTAX          TruthValue
        MAX-ACCESS      read-write
        STATUS          current
        DESCRIPTION
            "Indicates whether Demand OSPFv3 procedures (hel-
            lo suppression to FULL neighbors and setting the
            DoNotAge flag on propagated LSAs) should be per-
            formed on this interface."
        DEFVAL { false }
        ::= { rcOspfv3IfEntry 19 }

rcOspfv3IfMetricValue OBJECT-TYPE
        SYNTAX          Integer32 (0..'FFFF'h)
        MAX-ACCESS      read-write
        STATUS          current
        DESCRIPTION
            "The metric assigned to this interface.
            The default value of the Metric is
            Reference Bandwidth / ifSpeed. The value of the
            reference bandwidth is configured by the
            rcOspfv3ReferenceBandwidth object. A value of '0' means
            the metric value of this interface will depend on the speed
            of the interface, when the state of the interface is up.
            The default (0) metric for Vlan and Tunnel is 10."

        ::= { rcOspfv3IfEntry 20 }

rcOspfv3IfLinkScopeLsaCount OBJECT-TYPE
        SYNTAX          Gauge32
        MAX-ACCESS      read-only
        STATUS          current
        DESCRIPTION
            "The total number of Link-Scope link-state
            advertisements in  this  link's link-state database."
        ::= { rcOspfv3IfEntry 21 }

rcOspfv3IfLinkLsaCksumSum OBJECT-TYPE
        SYNTAX          Integer32
        MAX-ACCESS      read-only
        STATUS          current
        DESCRIPTION
            "The 32-bit unsigned sum of the Link-Scope link-state
            advertisements'  LS  checksums  contained in this
            link's link-state database.  The sum can be used
            to determine if  there  has been  a  change  in a
            router's link state database, and to compare the
            link-state database of two routers."
        ::= { rcOspfv3IfEntry 22 }

rcOspfv3IfInstId OBJECT-TYPE
        SYNTAX          Integer32
        MAX-ACCESS      read-write
        STATUS          current
        DESCRIPTION
            "Enables multiple instances of OSPFv3 to be run over
            a single link. Each protocol instance would be assigned
            a separate ID. This ID has local link significance
            only."
        DEFVAL          { 0 }
        ::= { rcOspfv3IfEntry 23 }

rcOspfv3IfDemandNbrProbe OBJECT-TYPE
        SYNTAX          TruthValue
        MAX-ACCESS      read-write
        STATUS          current
        DESCRIPTION
               " Indicates whether or not neighbor probing is
                 enabled to determine whether or not the neighbor
                 is inactive. Neighbor probing is disabled by
                 default."
        DEFVAL { false }
        ::= { rcOspfv3IfEntry 24 }

rcOspfv3IfDemandNbrProbeRetxLimit OBJECT-TYPE
       SYNTAX       Unsigned32
       UNITS        "seconds"
       MAX-ACCESS   read-write
       STATUS       current
       DESCRIPTION
          " The number of consecutive LSA retransmissions before
            the neighbor is deemed inactive and the neighbor
            adjacency is brought down."
       DEFVAL          { 10 }
       ::= { rcOspfv3IfEntry 25 }

rcOspfv3IfDemandNbrProbeInterval OBJECT-TYPE
       SYNTAX       Unsigned32
       UNITS        "seconds"
       MAX-ACCESS   read-write
       STATUS       current
       DESCRIPTION
          " Defines how often the neighbor will be probed."
       DEFVAL          { 120 }
       ::= { rcOspfv3IfEntry 26 }

-- OSPFv3 Virtual Interface Table

-- The Virtual Interface Table describes the virtual
-- links that the OSPFv3 Process is configured to
-- carry on.

rcOspfv3VirtIfTable OBJECT-TYPE
        SYNTAX          SEQUENCE OF RcOspfv3VirtIfEntry
        MAX-ACCESS      not-accessible
        STATUS          current
        DESCRIPTION
            "Information about this router's virtual inter-
            faces."
        REFERENCE
            "OSPF Version  2,  Appendix  C.4   Virtual  link
            parameters"
        ::= { rcOspfv3Objects 8 }

rcOspfv3VirtIfEntry OBJECT-TYPE
        SYNTAX          RcOspfv3VirtIfEntry
        MAX-ACCESS      not-accessible
        STATUS          current
        DESCRIPTION
            "Information about a single Virtual Interface."
        INDEX           { rcOspfv3VirtIfAreaId,
                          rcOspfv3VirtIfNeighbor }
        ::= { rcOspfv3VirtIfTable 1 }

RcOspfv3VirtIfEntry ::= SEQUENCE {
        rcOspfv3VirtIfAreaId
                IpAddress,
        rcOspfv3VirtIfNeighbor
                IpAddress,
        rcOspfv3VirtIfIndex
                Integer32,
        rcOspfv3VirtIfTransitDelay
                Integer32,
        rcOspfv3VirtIfRetransInterval
                Integer32,
        rcOspfv3VirtIfHelloInterval
                Integer32,
        rcOspfv3VirtIfRtrDeadInterval
                 Integer32,
        rcOspfv3VirtIfState
                INTEGER,
        rcOspfv3VirtIfEvents
                Counter32,
        rcOspfv3VirtIfStatus
                RowStatus,
        rcOspfv3VirtIfLinkScopeLsaCount
                Gauge32,
        rcOspfv3VirtIfLinkLsaCksumSum
                   Integer32
        }

rcOspfv3VirtIfAreaId OBJECT-TYPE
        SYNTAX          IpAddress
        MAX-ACCESS      not-accessible
        STATUS          current
        DESCRIPTION
            "The  Transit  Area  that  the   Virtual   Link
            traverses.  By definition, this is not 0.0.0.0"
        ::= { rcOspfv3VirtIfEntry 1 }

rcOspfv3VirtIfNeighbor OBJECT-TYPE
        SYNTAX          IpAddress
        MAX-ACCESS      not-accessible
        STATUS          current
        DESCRIPTION
            "The Router ID of the Virtual Neighbor."
        ::= { rcOspfv3VirtIfEntry 2 }

rcOspfv3VirtIfIndex OBJECT-TYPE
        SYNTAX          Integer32
        MAX-ACCESS      read-only
        STATUS          current
        DESCRIPTION
            "The interface ID assigned to this OSPFv3 virtual
            interface. It is advertised in Hello's sent over
            the virtal link and in the router's router-LSAs."
        ::= { rcOspfv3VirtIfEntry 3 }

rcOspfv3VirtIfTransitDelay OBJECT-TYPE
        SYNTAX          Integer32 (1..1800)
        UNITS           "seconds"
        MAX-ACCESS      read-write
        STATUS          current
        DESCRIPTION
            "The estimated number of seconds  it  takes  to
            transmit  a link- state update packet over this
            interface."
        DEFVAL          { 1 }
        ::= { rcOspfv3VirtIfEntry 4 }

rcOspfv3VirtIfRetransInterval OBJECT-TYPE
        SYNTAX          Integer32 (1..1800)
        UNITS           "seconds"
        MAX-ACCESS      read-write
        STATUS          current
        DESCRIPTION
            "The number of seconds between  link-state  ad-
            vertisement  retransmissions,  for  adjacencies
            belonging to this  interface.   This  value  is
            also used when retransmitting database descrip-
            tion  and  link-state  request  packets.   This
            value  should  be well over the expected round-
            trip time."
        DEFVAL          { 5 }
        ::= { rcOspfv3VirtIfEntry 5 }

rcOspfv3VirtIfHelloInterval OBJECT-TYPE
        SYNTAX          Integer32 (1..'FFFF'h)
        UNITS           "seconds"
        MAX-ACCESS      read-write
        STATUS          current
        DESCRIPTION
            "The length of time, in  seconds,  between  the
            Hello  packets that the router sends on the in-
            terface.  This value must be the same  for  the
            virtual neighbor."
        DEFVAL          { 10 }
        ::= { rcOspfv3VirtIfEntry 6 }

rcOspfv3VirtIfRtrDeadInterval OBJECT-TYPE
        SYNTAX          Integer32 (1..'FFFF'h)
        UNITS           "seconds"
        MAX-ACCESS      read-write
        STATUS          current
        DESCRIPTION
            "The number of seconds that  a  router's  Hello
            packets  have  not been seen before it's neigh-
            bors declare the router down.  This  should  be
            some  multiple  of  the  Hello  interval.  This
            value must be the same for the  virtual  neigh-
            bor."
        DEFVAL          { 60 }
        ::= { rcOspfv3VirtIfEntry 7 }

rcOspfv3VirtIfState OBJECT-TYPE
        SYNTAX          INTEGER {
                        down(1), -- these use the same encoding
                        pointToPoint(4) -- as the rcOspfv3IfTable
                        }
        MAX-ACCESS      read-only
        STATUS          current
        DESCRIPTION
            "OSPF virtual interface states."
        ::= { rcOspfv3VirtIfEntry 8 }

rcOspfv3VirtIfEvents OBJECT-TYPE
        SYNTAX          Counter32
        MAX-ACCESS      read-only
        STATUS          current
        DESCRIPTION
            "The number of state changes or error events on
            this Virtual Link"
        ::= { rcOspfv3VirtIfEntry 9 }

rcOspfv3VirtIfStatus OBJECT-TYPE
        SYNTAX          RowStatus
        MAX-ACCESS      read-create
        STATUS          current
        DESCRIPTION
            "This variable controls the status of  the  en-
            try. The use of RowStatus is covered in more detail
            in [6]."
        ::= { rcOspfv3VirtIfEntry 10 }

rcOspfv3VirtIfLinkScopeLsaCount OBJECT-TYPE
        SYNTAX          Gauge32
        MAX-ACCESS      read-only
        STATUS          current
        DESCRIPTION
            "The total number of Link-Scope link-state
            advertisements in  this  virtual link's link-state
            database."
        ::= { rcOspfv3VirtIfEntry 11 }

rcOspfv3VirtIfLinkLsaCksumSum OBJECT-TYPE
        SYNTAX          Integer32
        MAX-ACCESS      read-only
        STATUS          current
        DESCRIPTION
            "The 32-bit unsigned sum of the Link-Scope link-state
            advertisements'  LS  checksums  contained in this
            virtual link's link-state database.  The sum can be used
            to determine if  there  has been  a  change  in a
            router's link state database, and to compare the
            link-state database of two routers."
        ::= { rcOspfv3VirtIfEntry 12 }


-- OSPFv3 Neighbor Table

-- The OSPFv3 Neighbor Table describes all neighbors in
-- the locality of the subject router.

rcOspfv3NbrTable OBJECT-TYPE
        SYNTAX          SEQUENCE OF RcOspfv3NbrEntry
        MAX-ACCESS      not-accessible
        STATUS          current
        DESCRIPTION
            "A table of non-virtual neighbor information."
        REFERENCE
            "OSPF Version 2, Section 10  The  Neighbor  Data
            Structure"
        ::= { rcOspfv3Objects 9 }

rcOspfv3NbrEntry OBJECT-TYPE
        SYNTAX          RcOspfv3NbrEntry
        MAX-ACCESS      not-accessible
        STATUS          current
        DESCRIPTION
            "The information regarding a single neighbor."
        REFERENCE
            "OSPF Version 2, Section 10  The  Neighbor  Data
            Structure"
        INDEX           { rcOspfv3NbrIfIndex,
                          rcOspfv3NbrRtrId }
        ::= { rcOspfv3NbrTable 1 }

RcOspfv3NbrEntry ::= SEQUENCE {
        rcOspfv3NbrIfIndex
                InterfaceIndex,
        rcOspfv3NbrRtrId
                IpAddress,
        rcOspfv3NbrAddressType
                INTEGER,
        rcOspfv3NbrAddress
                OCTET STRING,
        rcOspfv3NbrOptions
                Integer32,
        rcOspfv3NbrPriority
                INTEGER,
        rcOspfv3NbrState
                INTEGER,
        rcOspfv3NbrEvents
                Counter32,
        rcOspfv3NbrLsRetransQLen
                Gauge32,
        rcOspfv3NbrHelloSuppressed
                TruthValue,
        rcOspfv3NbrIfId
                Integer32,
        rcOspfv3NbrRestartHelperStatus
                INTEGER,
        rcOspfv3NbrRestartHelperAge
                Integer32,
        rcOspfv3NbrRestartHelperExitReason
                INTEGER,
        rcOspfv3NbrDeadIntCnt
                Integer32
        }

rcOspfv3NbrIfIndex OBJECT-TYPE
        SYNTAX          InterfaceIndex
        MAX-ACCESS      not-accessible
        STATUS          current
        DESCRIPTION
            "The local link ID of the link over which the
             neighbor can be reached."
        ::= { rcOspfv3NbrEntry 1 }

rcOspfv3NbrRtrId OBJECT-TYPE
        SYNTAX          IpAddress
        MAX-ACCESS      not-accessible
        STATUS          current
        DESCRIPTION
            "A 32-bit integer (represented as a type  IpAd-
            dress)  uniquely  identifying  the  neighboring
            router in the Autonomous System."
        ::= { rcOspfv3NbrEntry 2 }

rcOspfv3NbrAddressType OBJECT-TYPE
        SYNTAX          INTEGER {
                            unknown(0),
                            ipv4(1),
                            ipv6(2),
                            ipv4z(3),
                            ipv6z(4),
                            dns(16)
                        }
        MAX-ACCESS      read-only
        STATUS          current
        DESCRIPTION
            "The address type of rcOspfv3NbrAddress. Only IPv6
            addresses without zone index are expected."
        ::= { rcOspfv3NbrEntry 3 }

rcOspfv3NbrAddress OBJECT-TYPE
        SYNTAX          OCTET STRING (SIZE (16))
        MAX-ACCESS      read-only
        STATUS          current
        DESCRIPTION
            "The IPv6 address of the neighbor associated with
            the local link."
        ::= { rcOspfv3NbrEntry 4 }

rcOspfv3NbrOptions OBJECT-TYPE
        SYNTAX          Integer32
        MAX-ACCESS      read-only
        STATUS          current
        DESCRIPTION
            "A Bit Mask corresponding to the neighbor's op-
            tions field."
        REFERENCE
            "OSPF Version 3, Appendix A.2 the Options field"
        ::= { rcOspfv3NbrEntry 5 }

rcOspfv3NbrPriority OBJECT-TYPE
        SYNTAX          INTEGER (0..'FF'h)
        MAX-ACCESS      read-only
        STATUS          current
        DESCRIPTION
            "The priority of this neighbor in the designat-
            ed router election algorithm.  The value 0 sig-
            nifies that the neighbor is not eligible to be-
            come  the  designated router on this particular
            network."
        ::= { rcOspfv3NbrEntry 6 }

rcOspfv3NbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The State of the relationship with this Neigh-
            bor."
        REFERENCE
            "OSPF Version 2, Section 10.1 Neighbor States"
        ::= { rcOspfv3NbrEntry 7 }

rcOspfv3NbrEvents OBJECT-TYPE
        SYNTAX          Counter32
        MAX-ACCESS      read-only
        STATUS          current
        DESCRIPTION
            "The number of times this neighbor relationship
            has changed state, or an error has occurred."
        ::= { rcOspfv3NbrEntry 8 }

rcOspfv3NbrLsRetransQLen OBJECT-TYPE
        SYNTAX          Gauge32
        MAX-ACCESS      read-only
        STATUS          current
        DESCRIPTION
            "The  current  length  of  the   retransmission
            queue."
        ::= { rcOspfv3NbrEntry 9 }

rcOspfv3NbrHelloSuppressed OBJECT-TYPE
        SYNTAX          TruthValue
        MAX-ACCESS      read-only
        STATUS          current
        DESCRIPTION
            "Indicates whether Hellos are being  suppressed
            to the neighbor"
        ::= { rcOspfv3NbrEntry 10 }

rcOspfv3NbrIfId OBJECT-TYPE
        SYNTAX          Integer32
        MAX-ACCESS      read-only
        STATUS          current
        DESCRIPTION
            "The interface ID that the neighbor advertises
            in its Hello Packets on this link, that is, the
            neighbor's local interface index."
        ::= { rcOspfv3NbrEntry 11 }

rcOspfv3NbrRestartHelperStatus OBJECT-TYPE
       SYNTAX       INTEGER { notHelping (1),
                              helping (2)
                            }
       MAX-ACCESS   read-only
       STATUS       current
       DESCRIPTION
          "Indicates whether the router is acting
          as a hitless restart helper for the neighbor."
          ::= { rcOspfv3NbrEntry 12 }

rcOspfv3NbrRestartHelperAge OBJECT-TYPE
       SYNTAX       Integer32 (1..1800)
       UNITS        "seconds"
       MAX-ACCESS   read-only
       STATUS       current
       DESCRIPTION
          "Remaining time in current OSPF hitless restart
          interval, if the router is acting as a restart
          helper for the neighbor."
       ::= { rcOspfv3NbrEntry 13 }

rcOspfv3NbrRestartHelperExitReason OBJECT-TYPE
       SYNTAX       INTEGER { none (1),           -- not attempted
                              inProgress (2),     -- restart in
                                                  -- progress
                              completed (3),      -- successfully
                                                  -- completed
                              timedOut (4),       -- timed out
                              topologyChanged (5) -- aborted due to
                                                  -- topology
                                                  -- change.
                            }
       MAX-ACCESS   read-only
       STATUS       current
       DESCRIPTION
          "Describes the outcome of the last attempt at acting
           as a hitless restart helper for the neighbor."
    ::= { rcOspfv3NbrEntry 14 }

rcOspfv3NbrDeadIntCnt OBJECT-TYPE
        SYNTAX          Integer32
	UNITS           "seconds"
        MAX-ACCESS      read-only
        STATUS          current
        DESCRIPTION
            "This is a Dead interval Count or TTL (time to live) field that 
             indicates how many seconds are left before the Neighbor is 
             declared down.  The starting value is set to the Router Dead 
             Interval value and it decrements to 0 if there is no Hello 
             received for that neighbor (then the neighbor is declared down).
             When a hello is received, the value is reset to the Router Dead 
             Interval value again."
        ::= { rcOspfv3NbrEntry 15 }


-- OSPFv3 NBMA Neighbor Table

-- The OSPFv3 NBMA Neighbor Table describes all configured
-- NBMA neighbors and neighbors dynamically discovered by
-- lower-level protocols such as Inverse Neighbor Discovery.

rcOspfv3NbmaNbrTable OBJECT-TYPE
        SYNTAX          SEQUENCE OF RcOspfv3NbmaNbrEntry
        MAX-ACCESS      not-accessible
        STATUS          current
        DESCRIPTION
            "A table of configured non-virtual neighbor
            information and neighbors dynamically discovered
            by lower-level protocols such as Inverse Neighbor
            Discovery."
        REFERENCE
            "OSPF Version 2, Section 10  The  Neighbor  Data
            Structure"
        ::= { rcOspfv3Objects 10 }

rcOspfv3NbmaNbrEntry OBJECT-TYPE
        SYNTAX          RcOspfv3NbmaNbrEntry
        MAX-ACCESS      not-accessible
        STATUS          current
        DESCRIPTION
            "The information regarding a single configured
            neighbor or neighbor discovered by lower-level
            protocols such as Inverse Neighbor Discovery."
        REFERENCE
            "OSPF Version 2, Section 10  The  Neighbor  Data
            Structure"
        INDEX           { rcOspfv3NbmaNbrIfIndex,
                          rcOspfv3NbmaNbrAddress }
        ::= { rcOspfv3NbmaNbrTable 1 }

RcOspfv3NbmaNbrEntry ::= SEQUENCE {
        rcOspfv3NbmaNbrIfIndex
                InterfaceIndex,
        rcOspfv3NbmaNbrAddress
                Ipv6Address,
        rcOspfv3NbmaNbrPriority
                INTEGER,
        rcOspfv3NbmaNbrRtrId
                IpAddress,
        rcOspfv3NbmaNbrState
                INTEGER,
        rcOspfv3NbmaNbrStorageType
                StorageType,
        rcOspfv3NbmaNbrStatus
                RowStatus
        }

rcOspfv3NbmaNbrIfIndex OBJECT-TYPE
        SYNTAX          InterfaceIndex
        MAX-ACCESS      not-accessible
        STATUS          current
        DESCRIPTION
            "The local link ID of the link over which the
             neighbor can be reached."
        ::= { rcOspfv3NbmaNbrEntry 1 }

rcOspfv3NbmaNbrAddress OBJECT-TYPE
        SYNTAX          Ipv6Address
        MAX-ACCESS      not-accessible
        STATUS          current
        DESCRIPTION
            "The IPv6 address of the neighbor associated with
            the local link."
        ::= { rcOspfv3NbmaNbrEntry 2 }

rcOspfv3NbmaNbrPriority OBJECT-TYPE
        SYNTAX          INTEGER (0..'FF'h)
        MAX-ACCESS      read-write
        STATUS          current
        DESCRIPTION
            "The priority of this neighbor in the designat-
            ed router election algorithm. The value 0 sig-
            nifies that the neighbor is not eligible to be-
            come  the  designated router on this particular
            network."
        DEFVAL          { 1 }
        ::= { rcOspfv3NbmaNbrEntry 3 }

rcOspfv3NbmaNbrRtrId OBJECT-TYPE
        SYNTAX          IpAddress
        MAX-ACCESS      read-only
        STATUS          current
        DESCRIPTION
            "A 32-bit integer (represented as a type IpAd-
            dress) uniquely identifying the neighboring
            router in the Autonomous System. A value of
            0.0.0.0 is returned until a Hello is received
            from the configured neighbor."
        ::= { rcOspfv3NbmaNbrEntry 4 }

rcOspfv3NbmaNbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The State of the relationship with this Neigh-
            bor."
        REFERENCE
            "OSPF Version 2, Section 10.1 Neighbor States"
        ::= { rcOspfv3NbmaNbrEntry 5 }

rcOspfv3NbmaNbrStorageType OBJECT-TYPE
        SYNTAX          StorageType
        MAX-ACCESS      read-write
        STATUS          current
        DESCRIPTION
            "The storage type for this conceptual row.
            Conceptual rows having the value 'permanent' need not
            allow write-access to any columnar objects in the row.
            Manually configured entries will have a storage type
            of nonVolatile while entries dynamically created as a
            result of a lower-level protocol such as Inverse
            Neighbor Discovery will have a storage type of
            volatile."
        DEFVAL          { nonVolatile }
        ::= { rcOspfv3NbmaNbrEntry 6 }

rcOspfv3NbmaNbrStatus OBJECT-TYPE
        SYNTAX          RowStatus
        MAX-ACCESS      read-create
        STATUS          current
        DESCRIPTION
            "This variable controls the status of the en-
            try. The use of RowStatus is covered in more detail
            in [6]."
        ::= { rcOspfv3NbmaNbrEntry 7 }

-- OSPFv3 Virtual Neighbor Table

-- This table describes all virtual neighbors.
-- Since Virtual Links are configured in the
-- virtual interface table, this table is read-only.

rcOspfv3VirtNbrTable OBJECT-TYPE
        SYNTAX          SEQUENCE OF RcOspfv3VirtNbrEntry
        MAX-ACCESS      not-accessible
        STATUS          current
        DESCRIPTION
            "A table of virtual neighbor information."
        REFERENCE
            "OSPF Version 2, Section 15 Virtual Links"
        ::= { rcOspfv3Objects 11 }

rcOspfv3VirtNbrEntry OBJECT-TYPE
        SYNTAX          RcOspfv3VirtNbrEntry
        MAX-ACCESS      not-accessible
        STATUS          current
        DESCRIPTION
            "Virtual neighbor information."
        INDEX           { rcOspfv3VirtNbrArea,
                          rcOspfv3VirtNbrRtrId }
        ::= { rcOspfv3VirtNbrTable 1 }

RcOspfv3VirtNbrEntry ::= SEQUENCE {
        rcOspfv3VirtNbrArea
                IpAddress,
        rcOspfv3VirtNbrRtrId
                IpAddress,
        rcOspfv3VirtNbrIfIndex
                Integer32,
        rcOspfv3VirtNbrAddressType
                INTEGER,
        rcOspfv3VirtNbrAddress
                OCTET STRING,
        rcOspfv3VirtNbrOptions
                Integer32,
        rcOspfv3VirtNbrState
                INTEGER,
        rcOspfv3VirtNbrEvents
                Counter32,
        rcOspfv3VirtNbrLsRetransQLen
                Gauge32,
        rcOspfv3VirtNbrHelloSuppressed
                TruthValue,
        rcOspfv3VirtNbrIfId
                Integer32,
        rcOspfv3VirtNbrRestartHelperStatus
                INTEGER,
        rcOspfv3VirtNbrRestartHelperAge
                Integer32,
        rcOspfv3VirtNbrRestartHelperExitReason
                INTEGER
        }

rcOspfv3VirtNbrArea OBJECT-TYPE
        SYNTAX          IpAddress
        MAX-ACCESS      not-accessible
        STATUS          current
        DESCRIPTION
            "The Transit Area Identifier."
        ::= { rcOspfv3VirtNbrEntry 1 }

rcOspfv3VirtNbrRtrId OBJECT-TYPE
        SYNTAX          IpAddress
        MAX-ACCESS      not-accessible
        STATUS          current
        DESCRIPTION
            "A  32-bit  integer  uniquely  identifying  the
            neighboring router in the Autonomous System."
        ::= { rcOspfv3VirtNbrEntry 2 }

rcOspfv3VirtNbrIfIndex OBJECT-TYPE
        SYNTAX          Integer32
        MAX-ACCESS      read-only
        STATUS          current
        DESCRIPTION
            "The local interface ID for the virtual link over
            which the neighbor can be reached."
        ::= { rcOspfv3VirtNbrEntry 3 }

rcOspfv3VirtNbrAddressType OBJECT-TYPE
        SYNTAX          INTEGER {
                            unknown(0),
                            ipv4(1),
                            ipv6(2),
                            ipv4z(3),
                            ipv6z(4),
                            dns(16)
                        }
        MAX-ACCESS      read-only
        STATUS          current
        DESCRIPTION
            "The address type of rcOspfv3VirtNbrAddress. Only IPv6
            addresses without zone index are expected."
        ::= { rcOspfv3VirtNbrEntry 4 }

rcOspfv3VirtNbrAddress OBJECT-TYPE
        SYNTAX          OCTET STRING (SIZE (16))
        MAX-ACCESS      read-only
        STATUS          current
        DESCRIPTION
            "The IPv6 address advertised by this Virtual Neighbor.
            It must be a Site-Local or Global scope address."
        ::= { rcOspfv3VirtNbrEntry 5 }

rcOspfv3VirtNbrOptions OBJECT-TYPE
        SYNTAX          Integer32
        MAX-ACCESS      read-only
        STATUS          current
        DESCRIPTION
            "A Bit Mask corresponding to the neighbor's op-
            tions field."
        REFERENCE
            "OSPF Version 3, Appendix A.2 the Options field"
        ::= { rcOspfv3VirtNbrEntry 6 }

rcOspfv3VirtNbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The state of the Virtual Neighbor Relation-
            ship."
        ::= { rcOspfv3VirtNbrEntry 7 }

rcOspfv3VirtNbrEvents OBJECT-TYPE
        SYNTAX          Counter32
        MAX-ACCESS      read-only
        STATUS          current
        DESCRIPTION
            "The number of  times  this  virtual  link  has
            changed its state, or an error has occurred."
        ::= { rcOspfv3VirtNbrEntry 8 }

rcOspfv3VirtNbrLsRetransQLen OBJECT-TYPE
        SYNTAX          Gauge32
        MAX-ACCESS      read-only
        STATUS          current
        DESCRIPTION
            "The  current  length  of  the   retransmission
            queue."
        ::= { rcOspfv3VirtNbrEntry 9 }

rcOspfv3VirtNbrHelloSuppressed OBJECT-TYPE
        SYNTAX          TruthValue
        MAX-ACCESS      read-only
        STATUS          current
        DESCRIPTION
            "Indicates whether Hellos are being  suppressed
            to the neighbor"
        ::= { rcOspfv3VirtNbrEntry 10 }

rcOspfv3VirtNbrIfId OBJECT-TYPE
        SYNTAX          Integer32
        MAX-ACCESS      read-only
        STATUS          current
        DESCRIPTION
            "The interface ID that the neighbor advertises
            in its Hello Packets on this virtual link, that is,
            the neighbor's local interface ID."
        ::= { rcOspfv3VirtNbrEntry 11 }

rcOspfv3VirtNbrRestartHelperStatus OBJECT-TYPE
       SYNTAX       INTEGER { notHelping (1),
                              helping (2)
                            }
       MAX-ACCESS   read-only
       STATUS       current
       DESCRIPTION
          "Indicates whether the router is acting
          as a hitless restart helper for the neighbor."
          ::= { rcOspfv3VirtNbrEntry 12 }

rcOspfv3VirtNbrRestartHelperAge OBJECT-TYPE
       SYNTAX       Integer32 (1..1800)
       UNITS        "seconds"
       MAX-ACCESS   read-only
       STATUS       current
       DESCRIPTION
          "Remaining time in current OSPF hitless restart
          interval, if the router is acting as a restart
          helper for the neighbor."
       ::= { rcOspfv3VirtNbrEntry 13 }

rcOspfv3VirtNbrRestartHelperExitReason OBJECT-TYPE
       SYNTAX       INTEGER { none (1),           -- not attempted
                              inProgress (2),     -- restart in
                                                  -- progress
                              completed (3),      -- successfully
                                                  -- completed
                              timedOut (4),       -- timed out
                              topologyChanged (5) -- aborted due to
                                                  -- topology
                                                  -- change.
                            }
       MAX-ACCESS   read-only
       STATUS       current
       DESCRIPTION
          "Describes the outcome of the last attempt at acting
           as a hitless restart helper for the neighbor."
    ::= { rcOspfv3VirtNbrEntry 14 }


--
-- The OSPFv3 Area Aggregate Table
--

rcOspfv3AreaAggregateTable OBJECT-TYPE
        SYNTAX          SEQUENCE OF RcOspfv3AreaAggregateEntry
        MAX-ACCESS      not-accessible
        STATUS          current
        DESCRIPTION
            "A range of IPv6 prefixes specified by a
            prefix/prefix length  pair. Note that if
            ranges are configured such that one range sub-
            sumes  another range the most specific match is
            the preferred one."
        ::= { rcOspfv3Objects 12 }

rcOspfv3AreaAggregateEntry OBJECT-TYPE
        SYNTAX          RcOspfv3AreaAggregateEntry
        MAX-ACCESS      not-accessible
        STATUS          current
        DESCRIPTION
            "A range of IPv6 prefixes specified by a
            prefix/prefix length  pair. Note that if
            ranges are configured such that one range sub-
            sumes  another range the most specific match is
            the preferred one."
        REFERENCE
            "OSPF Version 2, Appendix C.2  Area parameters"
        INDEX           { rcOspfv3AreaAggregateAreaID,
                          rcOspfv3AreaAggregateAreaLsdbType,
                          rcOspfv3AreaAggregatePrefix,
                          rcOspfv3AreaAggregatePrefixLength }
        ::= { rcOspfv3AreaAggregateTable 1 }

RcOspfv3AreaAggregateEntry ::= SEQUENCE {
        rcOspfv3AreaAggregateAreaID
                IpAddress,
        rcOspfv3AreaAggregateAreaLsdbType
                INTEGER,
        rcOspfv3AreaAggregatePrefix
                Ipv6Address,
        rcOspfv3AreaAggregatePrefixLength
                Unsigned32,
        rcOspfv3AreaAggregateStatus
                RowStatus,
        rcOspfv3AreaAggregateEffect
                INTEGER,
        rcOspfv3AreaAggregateRouteTag
                Integer32,
        rcOspfv3AreaAggregateAdvertiseMetric
                INTEGER
        }

rcOspfv3AreaAggregateAreaID OBJECT-TYPE
        SYNTAX          IpAddress
        MAX-ACCESS      not-accessible
        STATUS          current
        DESCRIPTION
            "The Area the Address Aggregate is to be  found
            within."
        REFERENCE
            "OSPF Version 2, Appendix C.2 Area parameters"
        ::= { rcOspfv3AreaAggregateEntry 1 }

rcOspfv3AreaAggregateAreaLsdbType OBJECT-TYPE
        SYNTAX          INTEGER {
                        interAreaPrefixLsa(8195), -- 0x2003
                        nssaExternalLsa(8199)     -- 0x2007
                        }
        MAX-ACCESS      not-accessible
        STATUS          current
        DESCRIPTION
            "The type of the Address Aggregate.  This field
            specifies  the  Area Lsdb type that this Address Ag-
            gregate applies to."
        REFERENCE
            "OSPF Version 2, Appendix A.4.1 The  Link  State
            Advertisement header"
        ::= { rcOspfv3AreaAggregateEntry 2 }

rcOspfv3AreaAggregatePrefix OBJECT-TYPE
        SYNTAX          Ipv6Address
        MAX-ACCESS      not-accessible
        STATUS          current
        DESCRIPTION
            "The IPv6 Prefix."
        REFERENCE
            "OSPF Version 2, Appendix C.2 Area parameters"
        ::= { rcOspfv3AreaAggregateEntry 3 }

rcOspfv3AreaAggregatePrefixLength OBJECT-TYPE
        SYNTAX          Unsigned32 (3..128)
        UNITS           "bits"
        MAX-ACCESS      not-accessible
        STATUS          current
        DESCRIPTION
            "The length of the prefix (in bits). A prefix can
            not be shorter than 3 bits."
        REFERENCE
            "OSPF Version 2, Appendix C.2 Area parameters"
        ::= { rcOspfv3AreaAggregateEntry 4 }

rcOspfv3AreaAggregateStatus OBJECT-TYPE
        SYNTAX          RowStatus
        MAX-ACCESS      read-create
        STATUS          current
        DESCRIPTION
            "This variable controls the status of  the  en-
            try. The use of RowStatus is covered in more detail
            in [6]."
        ::= { rcOspfv3AreaAggregateEntry 5 }

rcOspfv3AreaAggregateEffect OBJECT-TYPE
        SYNTAX          INTEGER {
                        advertiseMatching(1),
                        doNotAdvertiseMatching(2)
                        }
        MAX-ACCESS      read-write
        STATUS          current
        DESCRIPTION
            "Prefixes subsumed by ranges either trigger  the
            advertisement  of  the indicated aggregate (ad-
            vertiseMatching), or result in the prefix not
            being advertised at all outside the area."
        DEFVAL          { advertiseMatching }
        ::= { rcOspfv3AreaAggregateEntry 6 }

rcOspfv3AreaAggregateRouteTag OBJECT-TYPE
        SYNTAX          Integer32
        MAX-ACCESS      read-write
        STATUS          current
        DESCRIPTION
            "This tag is advertised only in the summarized
             As-External LSA when summarizing from type-7 to
             type-5."
        DEFVAL         { 0 }
        ::= { rcOspfv3AreaAggregateEntry 7 }

rcOspfv3AreaAggregateAdvertiseMetric OBJECT-TYPE
        SYNTAX        INTEGER(0..65535)
        MAX-ACCESS    read-write
        STATUS        current
        DESCRIPTION
            "Used to specify a metric for a Summary LSA (type 3)
             generated by OSPF through an area range.
             If this metric is set to 0, OSPF uses the cost
             to the farthest point in the networks being
             summarized as the metric."
        ::= { rcOspfv3AreaAggregateEntry 8 }

-- Ospfv3 Stats group

rcOspfv3Stats    OBJECT IDENTIFIER       ::= { rcOspfv3Objects 13 }

rcOspfv3StatsTxPackets OBJECT-TYPE
        SYNTAX        Counter32
        MAX-ACCESS    read-only
        STATUS        current
        DESCRIPTION   "Used to indicate the number of packets
                      transmitted by OSPF."
        ::= { rcOspfv3Stats 1 }

rcOspfv3StatsRxPackets OBJECT-TYPE
        SYNTAX        Counter32
        MAX-ACCESS    read-only
        STATUS        current
        DESCRIPTION   "Used to indicate the number of packets
                      received by OSPF."
        ::= { rcOspfv3Stats 2 }

rcOspfv3StatsTxDropPackets OBJECT-TYPE
        SYNTAX        Counter32
        MAX-ACCESS    read-only
        STATUS        current
        DESCRIPTION   "Used to indicate the number of packets
                      dropped before transmitted by OSPF."
        ::= { rcOspfv3Stats 3 }


rcOspfv3StatsRxDropPackets OBJECT-TYPE
        SYNTAX        Counter32
        MAX-ACCESS    read-only
        STATUS        current
        DESCRIPTION   "Used to indicate the number of packets
                      dropped before received by OSPF."
        ::= { rcOspfv3Stats 4 }

rcOspfv3StatsRxBadPackets OBJECT-TYPE
        SYNTAX        Counter32
        MAX-ACCESS    read-only
        STATUS        current
        DESCRIPTION   "Used to indicate the number of packets
                      received by OSPF that are bad."
        ::= { rcOspfv3Stats 5 }

rcOspfv3StatsSpfRuns OBJECT-TYPE
        SYNTAX        Counter32
        MAX-ACCESS    read-only
        STATUS        current
        DESCRIPTION   "Used to indicate the total number of SPF
                      calculations performed by OSPF, which
                      also includes the number of partial route
                      table calculation for Incremental Updates."
        ::= { rcOspfv3Stats 6 }

rcOspfv3StatsLastSpfRun OBJECT-TYPE
        SYNTAX        TimeTicks
        MAX-ACCESS    read-only
        STATUS        current
        DESCRIPTION   "Used to indicate the time(SysUpTime) since
                      the last spf calculated by OSPF."
        ::= { rcOspfv3Stats 7 }

rcOspfv3StatsLsdbTblSize OBJECT-TYPE
        SYNTAX        Gauge32
        MAX-ACCESS    read-only
        STATUS        current
        DESCRIPTION   "Used to indicate the number of entries in
                      the linkstate database table."
        ::= { rcOspfv3Stats 8 }

rcOspfv3StatsBadLsReqs OBJECT-TYPE
        SYNTAX        Counter32
        MAX-ACCESS    read-only
        STATUS        current
        DESCRIPTION   "Used to indicate the number of bad ls requests."
        ::= { rcOspfv3Stats 9 }

rcOspfv3StatsSeqMismatches OBJECT-TYPE
        SYNTAX        Counter32
        MAX-ACCESS    read-only
        STATUS        current
        DESCRIPTION   "Used to indicate the number of sequence
                       mismatched packets."
        ::= { rcOspfv3Stats 10 }


-- conformance information

rcOspfv3Groups      OBJECT IDENTIFIER ::= { rcOspfv3Conformance 1 }
rcOspfv3Compliances OBJECT IDENTIFIER ::= { rcOspfv3Conformance 2 }

-- compliance statements

rcOspfv3Compliance MODULE-COMPLIANCE
        STATUS          current
        DESCRIPTION     "The compliance statement "
        MODULE          -- this module
        MANDATORY-GROUPS {
                        rcOspfv3BasicGroup,
                        rcOspfv3AreaGroup,
                        rcOspfv3IfGroup,
                        rcOspfv3VirtIfGroup,
                        rcOspfv3NbrGroup,
                        rcOspfv3NbmaNbrGroup,
                        rcOspfv3VirtNbrGroup,
                        rcOspfv3AreaAggregateGroup
                        }

        GROUP           rcOspfv3AsLsdbGroup
        DESCRIPTION
            "This group is required for OSPFv3 systems that
            display their AS-scope link state database."

        GROUP           rcOspfv3AreaLsdbGroup
        DESCRIPTION
            "This group is required for OSPFv3 systems that
            display their Area-scope link state database."

        GROUP           rcOspfv3LinkLsdbGroup
        DESCRIPTION
            "This group is required for OSPFv3 systems that
            display their Link-scope link state database."

        GROUP           rcOspfv3HostGroup
        DESCRIPTION
            "This group is required for OSPFv3 systems that
            support attached hosts."

--        OBJECT          rcOspfv3NbrAddressType
--        SYNTAX          InetAddressType { ipv6(2) }
--        DESCRIPTION
--            "An implementation is only required to support IPv6
--            address without zone index."

--        OBJECT          rcOspfv3VirtNbrAddressType
--        SYNTAX          InetAddressType { ipv6(2) }
--        DESCRIPTION
--            "An implementation is only required to support IPv6
--            address without zone index."

        ::= { rcOspfv3Compliances 1 }

-- units of conformance

rcOspfv3BasicGroup OBJECT-GROUP
        OBJECTS         {
                        rcOspfv3RouterId,
                        rcOspfv3AdminStat,
                        rcOspfv3VersionNumber,
                        rcOspfv3AreaBdrRtrStatus,
                        rcOspfv3ASBdrRtrStatus,
                        rcOspfv3AsScopeLsaCount,
                        rcOspfv3AsScopeLsaCksumSum,
                        rcOspfv3OriginateNewLsas,
                        rcOspfv3RxNewLsas,
                        rcOspfv3ExtLsaCount,
                        rcOspfv3ExtAreaLsdbLimit,
                        rcOspfv3MulticastExtensions,
                        rcOspfv3ExitOverflowInterval,
                        rcOspfv3DemandExtensions,
                        rcOspfv3TrafficEngineeringSupport,
                        rcOspfv3ReferenceBandwidth,
                        rcOspfv3RestartSupport,
                        rcOspfv3RestartInterval,
                        rcOspfv3RestartStatus,
                        rcOspfv3RestartAge,
                        rcOspfv3RestartExitReason
                        }
        STATUS          current
        DESCRIPTION
            "These objects are required for OSPFv3 systems."
        ::= { rcOspfv3Groups 1 }


rcOspfv3AreaGroup OBJECT-GROUP
        OBJECTS         {
                        rcOspfv3ImportAsExtern,
                        rcOspfv3AreaSpfRuns,
                        rcOspfv3AreaBdrRtrCount,
                        rcOspfv3AreaAsBdrRtrCount,
                        rcOspfv3AreaScopeLsaCount,
                        rcOspfv3AreaScopeLsaCksumSum,
                        rcOspfv3AreaSummary,
                        rcOspfv3AreaStatus,
                        rcOspfv3StubMetric,
                        rcOspfv3AreaNssaTranslatorRole,
                        rcOspfv3AreaNssaTranslatorState,
                        rcOspfv3AreaNssaTranslatorStabilityInterval,
                        rcOspfv3AreaNssaTranslatorEvents,
                        rcOspfv3AreaStubMetricType
                        }
        STATUS          current
        DESCRIPTION
            "These objects are required for OSPFv3 systems
            supporting areas."
        ::= { rcOspfv3Groups 2 }

rcOspfv3AsLsdbGroup OBJECT-GROUP
        OBJECTS         {
                        rcOspfv3AsLsdbSequence,
                        rcOspfv3AsLsdbAge,
                        rcOspfv3AsLsdbChecksum,
                        rcOspfv3AsLsdbAdvertisement,
                        rcOspfv3AsLsdbTypeKnown
                        }
        STATUS          current
        DESCRIPTION
            "These objects are required for OSPFv3 systems
            that display their AS-scope link state database."
        ::= { rcOspfv3Groups 3 }

rcOspfv3AreaLsdbGroup OBJECT-GROUP
        OBJECTS         {
                        rcOspfv3AreaLsdbSequence,
                        rcOspfv3AreaLsdbAge,
                        rcOspfv3AreaLsdbChecksum,
                        rcOspfv3AreaLsdbAdvertisement,
                        rcOspfv3AreaLsdbTypeKnown
                        }
        STATUS          current
        DESCRIPTION
            "These objects are required for OSPFv3 systems
            that display their Area-scope link state database."
        ::= { rcOspfv3Groups 4 }

rcOspfv3LinkLsdbGroup OBJECT-GROUP
        OBJECTS         {
                        rcOspfv3LinkLsdbSequence,
                        rcOspfv3LinkLsdbAge,
                        rcOspfv3LinkLsdbChecksum,
                        rcOspfv3LinkLsdbAdvertisement,
                        rcOspfv3LinkLsdbTypeKnown
                        }
        STATUS          current
        DESCRIPTION
            "These objects are required for OSPFv3  systems
            that display their Link-scope link state database."
        ::= { rcOspfv3Groups 5 }

rcOspfv3HostGroup OBJECT-GROUP
        OBJECTS         {
                        rcOspfv3HostMetric,
                        rcOspfv3HostStatus,
                        rcOspfv3HostAreaID
                        }
        STATUS          current
        DESCRIPTION
            "These objects are required  for  OSPFv3  systems
            that support attached hosts."
        ::= { rcOspfv3Groups 6 }

rcOspfv3IfGroup OBJECT-GROUP
        OBJECTS         {
                        rcOspfv3IfAreaId,
                        rcOspfv3IfType,
                        rcOspfv3IfAdminStat,
                        rcOspfv3IfRtrPriority,
                        rcOspfv3IfTransitDelay,
                        rcOspfv3IfRetransInterval,
                        rcOspfv3IfHelloInterval,
                        rcOspfv3IfRtrDeadInterval,
                        rcOspfv3IfPollInterval,
                        rcOspfv3IfState,
                        rcOspfv3IfDesignatedRouter,
                        rcOspfv3IfBackupDesignatedRouter,
                        rcOspfv3IfEvents,
                        rcOspfv3IfStatus,
                        rcOspfv3IfMulticastForwarding,
                        rcOspfv3IfDemand,
                        rcOspfv3IfMetricValue,
                        rcOspfv3IfLinkScopeLsaCount,
                        rcOspfv3IfLinkLsaCksumSum,
                        rcOspfv3IfInstId,
                        rcOspfv3IfDemandNbrProbe,
                        rcOspfv3IfDemandNbrProbeRetxLimit,
                        rcOspfv3IfDemandNbrProbeInterval
                        }
        STATUS          current
        DESCRIPTION
            "These interface objects are required for
            OSPFv3 systems."
        ::= { rcOspfv3Groups 7 }

rcOspfv3VirtIfGroup OBJECT-GROUP
        OBJECTS         {
                        rcOspfv3VirtIfIndex,
                        rcOspfv3VirtIfTransitDelay,
                        rcOspfv3VirtIfRetransInterval,
                        rcOspfv3VirtIfHelloInterval,
                        rcOspfv3VirtIfRtrDeadInterval,
                        rcOspfv3VirtIfState,
                        rcOspfv3VirtIfEvents,
                        rcOspfv3VirtIfStatus,
                        rcOspfv3VirtIfLinkScopeLsaCount,
                        rcOspfv3VirtIfLinkLsaCksumSum
                        }
        STATUS          current
        DESCRIPTION
            "These virtual interface objects are required for
            OSPFv3 systems."
        ::= { rcOspfv3Groups 8 }

rcOspfv3NbrGroup OBJECT-GROUP
        OBJECTS         {
                        rcOspfv3NbrAddressType,
                        rcOspfv3NbrAddress,
                        rcOspfv3NbrOptions,
                        rcOspfv3NbrPriority,
                        rcOspfv3NbrState,
                        rcOspfv3NbrEvents,
                        rcOspfv3NbrLsRetransQLen,
                        rcOspfv3NbrHelloSuppressed,
                        rcOspfv3NbrIfId,
                        rcOspfv3NbrRestartHelperStatus,
                        rcOspfv3NbrRestartHelperAge,
                        rcOspfv3NbrRestartHelperExitReason
                        }
        STATUS          current
        DESCRIPTION
            "These neighbor objects are required for
            OSPFv3 systems."
        ::= { rcOspfv3Groups 9 }

rcOspfv3NbmaNbrGroup OBJECT-GROUP
        OBJECTS         {
                        rcOspfv3NbmaNbrPriority,
                        rcOspfv3NbmaNbrRtrId,
                        rcOspfv3NbmaNbrState,
                        rcOspfv3NbmaNbrStorageType,
                        rcOspfv3NbmaNbrStatus
                        }
        STATUS          current
        DESCRIPTION
            "These NBMA neighbor objects are required for
            OSPFv3 systems."
        ::= { rcOspfv3Groups 10 }

rcOspfv3VirtNbrGroup OBJECT-GROUP
        OBJECTS         {
                        rcOspfv3VirtNbrIfIndex,
                        rcOspfv3VirtNbrAddressType,
                        rcOspfv3VirtNbrAddress,
                        rcOspfv3VirtNbrOptions,
                        rcOspfv3VirtNbrState,
                        rcOspfv3VirtNbrEvents,
                        rcOspfv3VirtNbrLsRetransQLen,
                        rcOspfv3VirtNbrHelloSuppressed,
                        rcOspfv3VirtNbrIfId,
                        rcOspfv3VirtNbrRestartHelperStatus,
                        rcOspfv3VirtNbrRestartHelperAge,
                        rcOspfv3VirtNbrRestartHelperExitReason
                        }
        STATUS          current
        DESCRIPTION
            "These virtual neighbor objects are required for
            OSPFv3 systems."
        ::= { rcOspfv3Groups 11 }

rcOspfv3AreaAggregateGroup OBJECT-GROUP
        OBJECTS         {
                        rcOspfv3AreaAggregateStatus,
                        rcOspfv3AreaAggregateEffect,
                        rcOspfv3AreaAggregateRouteTag,
                        rcOspfv3AreaAggregateAdvertiseMetric
                        }
        STATUS          current
        DESCRIPTION
            "These area aggregate objects are required for
            OSPFv3 systems."
        ::= { rcOspfv3Groups 12 }


-- END of OSPF v3 MIB

-- BEGIN OF DHCP RELAY FOR IPV6

rcIpv6ConfDhcpRelayTable OBJECT-TYPE
        SYNTAX          SEQUENCE OF RcIpv6ConfDhcpRelayEntry
        MAX-ACCESS      not-accessible
        STATUS          current
        DESCRIPTION     "DHCP Relay for Ipv6 configuration table"
    ::= { rcIpv6Objects  9 }

rcIpv6ConfDhcpRelayEntry OBJECT-TYPE
        SYNTAX          RcIpv6ConfDhcpRelayEntry
        MAX-ACCESS      not-accessible
        STATUS          current
        DESCRIPTION     "Used to configure DHCP on a particular L3 interface.  An
                        entry is created automatically when the variable
                        rcIpv6InterfaceDhcpEnabled is set to TRUE.

                        Once created this entry will only be deleted if the
                        rcIpv6ConfDhcpRowStatus is set to 'destroy(6)'.  In
                        which case, the rcIpv6InterfaceDhcpEnabled is automatically
                        reset to the FALSE setting."
        INDEX           { rcIpv6ConfDhcpIfIndex }
        ::= { rcIpv6ConfDhcpRelayTable 1 }

RcIpv6ConfDhcpRelayEntry ::=
        SEQUENCE {
                rcIpv6ConfDhcpIfIndex               InterfaceIndex,
                rcIpv6ConfDhcpMaxHop                Unsigned32,
                rcIpv6ConfDhcpRemoteIdEnabled       TruthValue,
                rcIpv6ConfDhcpNumRequests           Counter32,
                rcIpv6ConfDhcpNumReplies            Counter32,
                rcIpv6ConfDhcpRowStatus             RowStatus
        }

rcIpv6ConfDhcpIfIndex OBJECT-TYPE
        SYNTAX          InterfaceIndex(1..6142)
        MAX-ACCESS      not-accessible
        STATUS          current
        DESCRIPTION     "Interface number.  The number can represent either
                        a physical or logical(VLAN) interface."
        ::= { rcIpv6ConfDhcpRelayEntry 1 }

rcIpv6ConfDhcpMaxHop OBJECT-TYPE
        SYNTAX          Unsigned32  (1..32)
        MAX-ACCESS      read-write
        STATUS          current
        DESCRIPTION     "Used to indicate the maximum number of hops a
                        DHCP packet can take from the source device to
                        the destination device (i.e., DHCP client to
                        DHCP server)."
        DEFVAL          { 32 }
        ::= { rcIpv6ConfDhcpRelayEntry 2 }


rcIpv6ConfDhcpRemoteIdEnabled OBJECT-TYPE
        SYNTAX          TruthValue
        MAX-ACCESS      read-write
        STATUS          current
        DESCRIPTION     "Used to indicate if remote-id option is enabled."
        DEFVAL          { false }
        ::= { rcIpv6ConfDhcpRelayEntry 3 }


rcIpv6ConfDhcpNumRequests OBJECT-TYPE
        SYNTAX          Counter32
        MAX-ACCESS      read-only
        STATUS          current
        DESCRIPTION     "The total number of DHCP requests seen on this interface."
        ::= { rcIpv6ConfDhcpRelayEntry 4 }

rcIpv6ConfDhcpNumReplies OBJECT-TYPE
        SYNTAX          Counter32
        MAX-ACCESS      read-only
        STATUS          current
        DESCRIPTION     "The total number of DHCP replies seen on this interface."
        ::= { rcIpv6ConfDhcpRelayEntry 5 }


rcIpv6ConfDhcpRowStatus OBJECT-TYPE
        SYNTAX          RowStatus
        MAX-ACCESS      read-write
        STATUS          current
        DESCRIPTION     "An entry is created automatically when the variable
                        rcIpv6InterfaceDhcpEnabled is set to TRUE.

                        Once created this entry will only be deleted if the
                        rcIpv6ConfDhcpRowStatus is set to 'destroy(6)'.  In
                        which case, the rcIpv6InterfaceDhcpEnabled is automatically
                        reset to the FALSE setting."
        ::= { rcIpv6ConfDhcpRelayEntry 6 }



rcIpv6DhcpForwardTable OBJECT-TYPE
        SYNTAX          SEQUENCE OF RcIpv6DhcpForwardEntry
        MAX-ACCESS      not-accessible
        STATUS          current
        DESCRIPTION     "DHCP Relay forwarding table."
    ::= { rcIpv6Objects  10 }

rcIpv6DhcpForwardEntry OBJECT-TYPE
        SYNTAX          RcIpv6DhcpForwardEntry
        MAX-ACCESS              not-accessible
        STATUS          current
        DESCRIPTION     "An entry used represents a DHCP Relayed message forwarding directive."
        INDEX           { rcIpv6DhcpForwardAgentAddr, rcIpv6DhcpForwardServerAddr }
        ::= { rcIpv6DhcpForwardTable 1 }

RcIpv6DhcpForwardEntry ::=
        SEQUENCE {
                rcIpv6DhcpForwardAgentAddr   Ipv6Address,
                rcIpv6DhcpForwardServerAddr  Ipv6Address,
                rcIpv6DhcpForwardEnabled      TruthValue,
                rcIpv6DhcpForwardRowStatus   RowStatus
        }

rcIpv6DhcpForwardAgentAddr OBJECT-TYPE
        SYNTAX          Ipv6Address
        MAX-ACCESS      not-accessible
        STATUS          current
        DESCRIPTION     "The IP address configured on an interface
                        (i.e., a locally configured IP address)."
        ::= { rcIpv6DhcpForwardEntry 1 }

rcIpv6DhcpForwardServerAddr OBJECT-TYPE
        SYNTAX          Ipv6Address
        MAX-ACCESS      not-accessible
        STATUS          current
        DESCRIPTION     "The IP address of the DHCP server.  If this
                        IP address corresponds to a local interface address, the DHCP packet is multicast out
                        the interface the IP address is assigned to.otherwise,the DHCP packet is sent via unicast to the remote device."

        ::= { rcIpv6DhcpForwardEntry 2 }

rcIpv6DhcpForwardEnabled OBJECT-TYPE
        SYNTAX          TruthValue
        MAX-ACCESS      read-write
        STATUS          current
        DESCRIPTION     "Used to indicate whether the entry should be used."
            DEFVAL              { true }
        ::= { rcIpv6DhcpForwardEntry 3 }


rcIpv6DhcpForwardRowStatus OBJECT-TYPE
        SYNTAX          RowStatus
        MAX-ACCESS      read-write
        STATUS          current
        DESCRIPTION     "Row status of this entry."
        ::= { rcIpv6DhcpForwardEntry 4 }

--END OF DHCP RELAY FOR IPV6


-- BEGIN OF IPV6 DESTINATION CACHE SECTION

rcIpv6DestinationCacheTable OBJECT-TYPE
        SYNTAX          SEQUENCE OF RcIpv6DestinationCacheEntry
        MAX-ACCESS      not-accessible
        STATUS          current
        DESCRIPTION     "Ipv6 Destination Cache table"
    ::= { rcIpv6Objects  13 }

rcIpv6DestinationCacheEntry OBJECT-TYPE
        SYNTAX          RcIpv6DestinationCacheEntry
        MAX-ACCESS      not-accessible
        STATUS          current
        DESCRIPTION     "Used to display Destination Cache" 
        INDEX           { rcIpv6DCacheDestAddr, rcIpv6DCacheIfIndex }
        ::= { rcIpv6DestinationCacheTable 1 }

RcIpv6DestinationCacheEntry ::=
        SEQUENCE {
                rcIpv6DCacheDestAddr              Ipv6Address, 
                rcIpv6DCacheIfIndex               Unsigned32,
                rcIpv6DCacheNextHop               Ipv6Address,
                rcIpv6DCacheIfType                INTEGER,
                rcIpv6DCacheIfData                DisplayString,
                rcIpv6DCachePmtu                  Integer32,
                rcIpv6DCachePmtuAge               Counter32 
        }

rcIpv6DCacheDestAddr OBJECT-TYPE
        SYNTAX          Ipv6Address
        MAX-ACCESS      not-accessible 
        STATUS          current
        DESCRIPTION     "IPv6 Destination Address from the 
                         Destination Cache."
        ::= { rcIpv6DestinationCacheEntry 1 }

rcIpv6DCacheIfIndex OBJECT-TYPE
        SYNTAX          Unsigned32
        MAX-ACCESS      not-accessible
        STATUS          current
        DESCRIPTION     "The last 16 bits of this object's value are interpreted as InterfaceIndex
                         (it can represent either a physical, or a VLAN, or a tunnel interface);
                         the first 16 bits are ignored when the object's value is interpreted."
        ::= { rcIpv6DestinationCacheEntry 2 }

rcIpv6DCacheNextHop OBJECT-TYPE
        SYNTAX          Ipv6Address
        MAX-ACCESS      read-only
        STATUS          current
        DESCRIPTION     "Ipv6 Next Hop for a Destination Cache entry."
        ::= { rcIpv6DestinationCacheEntry 3 }

rcIpv6DCacheIfType OBJECT-TYPE
        SYNTAX          INTEGER {real(1), virtual(2)}
        MAX-ACCESS      read-only
        STATUS          current
        DESCRIPTION     "Interface type; it can be a real (i.e. VLAN, brouter, tunnel)
                         or a virtual circuit (i.e. VRRP, RSMLT)."
        ::= { rcIpv6DestinationCacheEntry 4 }

rcIpv6DCacheIfData OBJECT-TYPE
        SYNTAX        DisplayString (SIZE (0..20))
        MAX-ACCESS    read-only
        STATUS        current
        DESCRIPTION   "Used to display additional information about virtual
                      circuits (i.e. if it is a VRRP or RSMLT circuit, the vrId
                      if it is a VRRP circuit); no information is displayed for
                      real circuits."
        ::= { rcIpv6DestinationCacheEntry 5 }

rcIpv6DCachePmtu OBJECT-TYPE
        SYNTAX        Integer32
        MAX-ACCESS    read-only
        STATUS        current
        DESCRIPTION   "Path MTU for the entry."
        ::= { rcIpv6DestinationCacheEntry 6 }

rcIpv6DCachePmtuAge OBJECT-TYPE
        SYNTAX        Counter32
        MAX-ACCESS    read-only
        STATUS        current
        DESCRIPTION   "Indicates how much time (in seconds) has passed since the PMTU
                       was updated the last time."
        ::= { rcIpv6DestinationCacheEntry 7 }

--END OF IPv6 DESTINATION CACHE SECTION

-- END 


-- 
-- *** THIS SECTION IS GENERATED FROM ../mib_tools/error.mib ***

-- This is generated by str2c.py -mib
-- Do not edit this file
-- Instead, edit $(TOPDIR)/mib/mib_tools/error_input.txt

rcErrorReturnCode OBJECT-TYPE
    SYNTAX INTEGER {
	
		none(100),
		resourceNotAvailable(101),
		operationNotAllowed(102),
		operationInProgress(103),
		invalidPortNumber(104),
		invalidSubnetAddress(105),
		invalidSubnetMask(106),
		invalidVlanId(107),
		invalidVlanName(108),
		invalidVlanType(109),
		invalidStgId(110),
		invalidProtocolId(111),
		invalidPortMembers(112),
		invalidStaticMembers(113),
		invalidNotAllowedMembers(114),
		destinationNotReachable(115),
		tableIsFull(116),
		nondualConnectorGigPort(117),
		testIdNotPresent(118),
		invalidTestId(119),
		invalidStatusChange(120),
		invalidCpuCard(121),
		invalidSrcPortChoice(122),
		dstPortUnspecified(123),
		srcPortOneUnspecified(124),
		srcPortTwoUnspecified(125),
		notSupported(126),
		userNameIsNonUnique(127),
		invalidName(128),
		unknownErrorCode1(129),
		cannotModifyThisField(130),
		invalidUserPasswordLength(131),
		thisUsernameExists(132),
		invalidIpAddress(133),
		invalidMacAddress(134),
		nosuchEntry(135),
		anotherLoopBackTestAlreadyRunning(136),
		protocolIdNotRoutable(137),
		autoNegotiateIsOn(138),
		noActionSpecified(139),
		invalidActionSpecified(140),
		cannotModifyAutoNegotiateIsOn(141),
		cannotModifyAutoPortIsFiber(142),
		autoNegotiationNotSupported(143),
		cannotSetAdminSpeed(144),
		cannotSetAdminDuplex(145),
		ospfRtrDeadIntIsnotMultOfHelloInt(146),
		ospfRtrDeadIntLessThan4TimesHelloInt(147),
		notUsed1(148),
		ospfBadAuthValue(149),
		ospfEnabled(150),
		ospfAreaNotFound(151),
		ospfBackboneArea(152),
		notInTestMode(153),
		ospfInvalidAreaRangeMask(154),
		ospfDuplicateEntry(155),
		ospfRangeNotAllocated(156),
		ospfAreaRangeNotFound(157),
		testRunning(158),
		nvramLimitExceeded(159),
		flowAlreadyExist(160),
		flowNotFound(161),
		invalidOspfAreaRangeNet(162),
		duplicateIpAddress(163),
		conflictingIpAddress(164),
		invalidRouteCost(165),
		invalidNextHop(166),
		duplicateRoute(167),
		cannotFindRoute(168),
		cannotDeleteLocalRoute(169),
		badDhcpMinSec(170),
		badDhcpMaxHop(171),
		badDhcpMode(172),
		badAgentAddress(173),
		dhcpNotEnabled(174),
		dhcpForwardNotFound(175),
		dhcpDuplicateForward(176),
		dhcpMaxForward(177),
		dhcpBadEnable(178),
		invalidDeviceFileNumber(179),
		notExecutableDeviceFile(180),
		deletedDeviceFile(181),
		pcmciaNotPresent(182),
		pcmciaWriteProtected(183),
		discontiguousSubnetMask(184),
		invalidOspfMetric(185),
		ospfHostRouteNotFound(186),
		invalidMltId(187),
		invalidMltName(188),
		onlyOnePortInMlt(189),
		moreThan4PortsInMlt(190),
		portsInDifferentQuid(191),
		portAlreadyInAnotherMlt(192),
		invalidVlan(193),
		nonExistIpMcastAddriess(194),
		invalidIpMulticastAddress(195),
		portIsLocked(196),
		accessRestriction(197),
		invalidDeviceFileLength(198),
		duplicateAccessPolicyId(199),
		noDesiredAccessPolicyItem(200),
		ipfFilterNonExist(201),
		ipfInvalidVlanPriority(202),
		ipfInvalidDestinationAddress(203),
		ipfInvalidSourceAddress(204),
		ipfFilterDuplicate(205),
		ipfGlobalListDuplicate(206),
		ipfGlobalListNonExist(207),
		ipfBaseListDuplicate(208),
		ipfBaseListNonExist(209),
		ipfPortDuplicate(210),
		ipfPortNonExist(211),
		ipfListNonExist(212),
		snmpSnoopDisabled(213),
		invalidHostIpAddress(214),
		snoopStaticGroupExist(215),
		ripAnnouncePolicyNotFound(216),
		duplicateRipAnnouncePolicy(217),
		ospfAnnouncePolicyNotFound(218),
		duplicateOspfAnnouncePolicy(219),
		policyMatchNetEntryNotFound(220),
		duplicatePolicyNetEntry(221),
		policyAddrListEntryNotFound(222),
		duplicatePolicyAddrListEntry(223),
		policyAddrListIdNotFound(224),
		policyExactNetListNotFound(225),
		policyRangeNetListNotFound(226),
		policyRipGatewayListNotFound(227),
		policyRipInterfaceListNotFound(228),
		policyOspfRtrIdListNotFound(229),
		policyAnnounceInterfaceListNotFound(230),
		policyAdvertiseNetListNotFound(231),
		policyInjectNetListNotFound(232),
		invalidPolicyListIdListSize(233),
		policyAddrEntryNotFound(234),
		duplicatePolicyAddrEntry(235),
		disableThisPortFirst(236),
		mutinettingNotSupported(237),
		addingGlobalFilterToNonGlobalList(238),
		addingNonGlobalFilterToGlobalList(239),
		setFilteredPortMode(240),
		setFilteredPortEnableValue(241),
		invalidModeType(242),
		duplicateRipAcceptPolicy(243),
		ripAccepPolicyNotFound(244),
		duplicateOspfAcceptPolicy(245),
		ospfAccepPolicyNotFound(246),
		invalidAccessPolicyName(247),
		invalidAccessPolicyPolicyEnable(248),
		invalidAccessPolicyMode(249),
		invalidAccessPolicyService(250),
		invalidAccessPolicyPrecedence(251),
		invalidAccessPolicyNetAddress(252),
		invalidAccessPolicyTrustedHostAddress(253),
		invalidAccessPolicyTrustedHostUserName(254),
		invalidAccessPolicyAccessLevel(255),
		invalidAccessPolicyLogSetting(256),
		invalidAccessPolicyPolicyId(257),
		invalidAreaOptions(258),
		cannotDeleteAreaIfCountIsNotZero(259),
		ospfInterfaceNotFound(260),
		ospfIfAreaIdConflictsWithConfiguredAreaRange(261),
		applyingDuplicateGlobalFilterToPort(262),
		differentMltPortTypes(263),
		addPortToMltFailed(264),
		removePortFromMltFailed(265),
		mirrorPortInMlt(266),
		invalidDhcpAlwaysBroadcast(267),
		interfaceIsSetToTransmitRipV1(268),
		ripInterfaceDoesnotExist(269),
		interfaceIsNotRunningRip(270),
		cannotCreateVirtLinksThroughStubArea(271),
		invalidSyslogEnableSetting(272),
		invalidSyslogMaxHostsSettings(273),
		invalidSyslogHostIpAddr(274),
		invalidSyslogHostUdpPort(275),
		invalidSyslogHostFacility(276),
		invalidSyslogModuleId(277),
		invalidSyslogSeverity(278),
		invalidSyslogMapInfoSeverity(279),
		invalidSyslogMapWarningSeverity(280),
		invalidSyslogMapErrorSeverity(281),
		invalidSyslogMapMfgSeverity(282),
		invalidSyslogMapFatalSeverity(283),
		invalidSyslogMapTraceMsgSetting(284),
		invalidSyslogMapTrapMsgSetting(285),
		invalidSyslogLogTraceMsgSetting(286),
		invalidSyslogLogTrapMsgSetting(287),
		invalidSyslogEntryEnableSetting(288),
		invalidSyslogMaxHostSetting(289),
		invalidSyslogHostId(290),
		duplicateSyslogEntry(291),
		syslogHostTableIsFull(292),
		noDesiredSyslogHostEntryFound(293),
		invalidHoldDownTime(294),
		incompatibleAruHardware(295),
		invalidVrid(296),
		duplicateVrrpEntry(297),
		noVrrpIpAddressSpecified(298),
		invalidVrrpControlValue(299),
		invalidVrrpPriority(300),
		invalidVrrpAdvertisementInterval(301),
		maxNumOfVrrpsEntriesExceeded(302),
		policyNetListEntryNotFound(303),
		duplicatePolicyNetListEntry(304),
		policyNetListIdNotFound(305),
		filterOnAnEnabledPort(306),
		listOnAnEnabledPort(307),
		invalidIpFilterSrcOption(308),
		invalidIpFilterDstOption(309),
		invalidOspfAreaImportextOption(310),
		invalidOspfInterfaceMd5KeyIdLength(311),
		invalidOspfInterfaceMd5KeyLength(312),
		invalidIPXNetworkNumber(313),
		ipxCircuitAlreadyExists(314),
		ipxCircuitDoesNotExist(315),
		encapsulationIsNotAllowedOnSameSegment(316),
		encapsulationDoesNotMatchProtocolBasedVLAN(317),
		invalidDvmrpIfTblEnableValue(318),
		invalidDvmrpIfTblMetricValue(319),
		ipHostPartForSubnetAddrIsNonZero(320),
		globalMulticastNotEnabled(321),
		metricFieldIsCreatedButModified(322),
		invalidIpMRouteInterfaceTblTtlValue(323),
		invalidUdpPortNumber(324),
		invalidUdpProtocolNameLength(325),
		cannotModifyUdpProtocolName(326),
		udpProtocolEntryDoesnotexists(327),
		duplicateUdpProtocolEntry(328),
		cannotDelUdpProtocolEntryFwdEntriesExists(329),
		udpBroadcastIntfEntryDoesnotExists(330),
		duplicateUdpBroadcastIntfEntry(331),
		invalidUdpConfBroacastInterface(332),
		updConfIntfEntryNotEnabledForUdpBcastForwarding(333),
		udpPortFwdEntryDoesnotExists(334),
		duplicateUdpPortFwdEntryDoesnotExists(335),
		udpPortFwdEntryUdpPortInterfaceDoesnotExists(336),
		udpPortFwdListEntryDoesnotExists(337),
		duplicateUdpPortFwdListEntryDoesnotExists(338),
		udpPortFwdListEntryPortFwdIdDoesnotExists(339),
		udpPortFwdListEntryinvalidFwdIdListSize(340),
		cannotDeleteUdpPortFwdListEntryInterfaceUsingThisList(341),
		invalidIgmpSnoopDestAddress(342),
		invalidIgmpSnoopHostAddress(343),
		cannotDeleteDefaultUdpProtocolTblEntry(344),
		nextHopRouteIsStaticRoute(345),
		invalidUpdateIntervalValueInDVMRPGlobalTable(346),
		invalidTriggeredUpdateIntervalValueInDVMRPGlobalTable(347),
		invalidLeafTimeoutValueInDVMRPGlobalTable(348),
		invalidNbrTimeoutValueInDVMRPGlobalTable(349),
		invalidNbrProbeIntervalValueInDVMRPGlobalTable(350),
		invalidQueryIntervalValueInIgmpInterfaceTable(351),
		invalidVersionValueInIgmpInterfaceTable(352),
		invalidQueryMaxResponseTimeValueInIgmpInterfaceTable(353),
		invalidRobustnessValueInIgmpInterfaceTable(354),
		invalidLastMembQueryIntvlValueInIgmpInterfaceTable(355),
		invalidANDMaskInRcIpTosRuleGroup(356),
		invalidORRule1InRcIpTosRuleGroup(357),
		invalidORRule2InRcIpTosRuleGroup(358),
		invalidORRule3InRcIpTosRuleGroup(359),
		deleteStaticPortNotValid(360),
		maxEntriesForIgmpAccTbl(361),
		maxMaskNumberOfHostIgmpAccTbl(362),
		dvmrpIgmpExclusive(363),
		theSpecifiedAreaRangeMaskIsInvalid(364),
		invalidLengthOf2kBootConfigImageSource(365),
		invalidLengthOf2kBootConfigSource(366),
		preferenceOfStaticRouteIsInvalid(367),
		copyFileOutOfSpace(368),
		copyFileFileNotFound(369),
		copyFileInvalidDestination(370),
		copyFileInvalidSource(371),
		copyFileFail(372),
		invalidLinkFlapDetectAutoPortDown(373),
		invalidLinkFlapDetectFrequency(374),
		invalidLinkFlapDetectInterval(375),
		invalidLinkFlapDetectSendTrap(376),
		invalidQosLevel(377),
		invalidQosWeight(378),
		invalidQosThreshold(379),
		invalidTagToQosTableIeee1pValue(380),
		invalidTagToQosTableQosLevel(381),
		invalidDsFieldToQosTableDsField(382),
		invalidDsFieldToQosTableQosLevel(383),
		invalidQosToTagTableQosLevel(384),
		invalidQosToTagTableIeee1pValue(385),
		invalidQosLevelValue(386),
		invalidQosToDsFieldTableDsFieldValue(387),
		invalidQosToDsFieldTableQosLevel(388),
		invalidDiffServEnable(389),
		invalidDiffServType(390),
		invalidIeeeOverride(391),
		invalidVlanQosValue(392),
		invalidVlanTosValue(393),
		operationNotAllowedOnAccessPort(394),
		operationNotAllowedOnTaggingPort(395),
		invalidFileName(396),
		invalidDiaglogueDuplicateMirroredPort(397),
		invalidDiaglogueEnableValue(398),
		invalidDiaglogueEnableSetting(399),
		invalidDiaglogueModeSetting(400),
		invalidDiaglogueEntryId(401),
		srcMacVlanIsNotYetEnabled(402),
		srcMacVlanIsNotYetDisabled(403),
		invalidDiaglogueOperation(404),
		invalidMacAddressSpecied(405),
		maxResponseTimeGreaterThanQueryInterval(406),
		noModifyDsFltrAllowedOnDiffSrvCorePort(407),
		mltMoreThan4PortsInMgMlt(408),
		protocolRulesForThePortHasExceeded16(409),
		routeDoesNotExistsInTheRroutingTable(410),
		diagMirrorByPortTableAccessError(411),
		diagMirrorByPortInvalidMirroringPortSetting(412),
		igmpAdminVersionConfiguredLessThanOperatingVersion(413),
		canOnlyConfigureViaMltTable(414),
		dvmrpInterfaceTableIsFull(415),
		invalidDscpField(416),
		invalidDscpReservedField(417),
		disablePortPriorToChangingDiffServPortType(418),
		ipFilterInvalidId(419),
		rateLimitingExceeded(420),
		diagEntryMaxExceeded(421),
		onlyOneMirroringPortAllow(422),
		radiusServerExist(423),
		radiusServerNotExist(424),
		radiusServerInUse(425),
		radiusMaxServerNumExceeded(426),
		radiusInvalidAttribute(427),
		canNotChangeLocking(428),
		activationDisabled(429),
		zeroMac(430),
		atmBadVpi(431),
		atmBadVci(432),
		atmBadFramingMode(433),
		atmDestroyPvcFailed(434),
		atmBadName(435),
		atmBadEnable(436),
		atmBadpvcEncapsulation(437),
		atmBadPvdServiceType(438),
		atmBadPeakCellRate(439),
		atmBadSustainedCellRate(440),
		atmBadMaxBurstSize(441),
		atmBadMaxMtuSize(442),
		atmBadElanId(443),
		atmUnknownOperation(444),
		atmDestroy1483ElanFailed(445),
		atmBadPerformTagging(446),
		atmIlleagalElanDefinition(447),
		atmCreate1483ElanFailed(448),
		atmBadSnmpMessage(449),
		atmBadScrambleEnable(450),
		atmBadSignalingEnable(451),
		atmBadClockSource(452),
		atmBadLoopback(453),
		badRowStatus(454),
		atmBadLaneConfigMode(455),
		atmLecCreationFailed(456),
		atmBad1438Inarp(457),
		atmF5StartFailed(458),
		atmBadPvcId(459),
		atmBadConnectType(460),
		atmBadIpxEncapMethod(461),
		atmBadUniVersion(462),
		atmCreatePvcFailed(463),
		invalidLoginPromptLength(464),
		invalidPasswordPromptLength(465),
		invalidCliBannerLength(466),
		invalidCliBannerSize(467),
		invalidCliMotdLength(468),
		invalidCliMotdSize(469),
		invalidPortNameLength(470),
		invalidPortName(471),
		invalidMaxAdvertiseInterval(472),
		invalidMinAdvertiseInterval(473),
		invalidMaxInitialAdvertiseInterval(474),
		invalidMaxInitalAdvertments(475),
		invalidNeigborDeadInterval(476),
		invalidUserSetTimeYearValue(477),
		invalidUserSetTimeMonthValue(478),
		invalidUserSetTimeDateValue(479),
		invalidUserSetTimeHourValue(480),
		invalidUserSetTimeMinuteValue(481),
		invalidUserSetTimeSecondValue(482),
		rtcIsNotPresent(483),
		rtcIsNotRunning(484),
		maxMacCount(485),
		maxAdvertiseIntLessThanMinAdvertiseInt(486),
		minAdvertiseIntGreaterThanMaxAdvertiseInt(487),
		dvmrpNotEnabledGlobally(488),
		vrrpCriticalIpAddrNotEnable(489),
		vrrpInvalidCriticalIpAddr(490),
		metricConfigNotAllowed(491),
		posActiveNonBcpEnabledPort(492),
		posVlanNoMorePorts(493),
		posPortCanBeAdded(494),
		posNonBcpCanNotBeEnabled(495),
		posImageFilenameTooLong(496),
		posNoIpcpEnableOnMltPorts(497),
		posNoIpcpEnableOnTagPort(498),
		posNoIpxcpEnableOnMltPort(499),
		posNoIpxcpEnableOnTagPort(500),
		posDisableTagBeforeBcpDisable(501),
		posAssignIpBeforeIpcpEnable(502),
		posAssignIpxBeforeIpxcpEnable(503),
		posAssignIpBeforeRemoteIp(504),
		posKeepRemoteIpInSameSubnet(505),
		staticRouteEnabled(506),
		cannotChangeAutoLearnState(507),
		invalidVirtualIpAddr(508),
		virtualAndPhysicalIpNotInSameSubnet(509),
		vidNotAvailable(510),
		mgidNotAvailable(511),
		posNoIpcpEnableOnPolicyVlanPort(512),
		posNoIpxcpEnableOnPolicyVlanPort(513),
		posVrrpNotAllowed(514),
		webInvalidHttpPort(515),
		cannotAddMulticastStaticMac(516),
		posNoStpEnableWithBCPClosed(517),
		posAtmNoRip1(518),
		ipfFilterNumOverFilterSetLimit(519),
		ipfQosTrafficAverageRateOverLimit(520),
		ipfQosTrafficProfileNotExist(521),
		atmNoIpIpxConfigOnVlan(522),
		atmPvcIsInUse(523),
		globalFilterNotDisabled(524),
		dhcpNotOnByIpSubnetVlan(525),
		cannotConfigureDefaultGateway(526),
		routeExists(527),
		gatewayNotOnMgmtInterfaceSubnet(528),
		mgmtRouteTableFull(529),
		routeNotExists(530),
		invalidMacOffsetRangeForBW(531),
		invalidMacOffsetRangeForMG(532),
		atmPvcBadPeakCellRate(533),
		atmPvcBadSustainedCellRate(534),
		qosReservedQosLevel(535),
		dvmrpGlobInvalidFwdCacheTimeOut(536),
		dvmrpGlobInvalidRouteExpireTimeOut(537),
		dvmrpGlobInvalidRouteDiscardTimeOut(538),
		dvmrpGlobInvalidRouteSwitchTimeOut(539),
		pimCondRPGroupExists(540),
		pimCandRPAddressInvalid(541),
		pimGroupAddressInvalid(542),
		pimNotEnabled(543),
		pimInvalidJPInterval(544),
		pimInvalidMode(545),
		pimInvalidHelloInt(546),
		pimInvalidCBSRPRef(547),
		pimInvalidEnable(548),
		pimAlreadyEnabled(549),
		ipDvmrpAlreadyEnabled(550),
		ospfIntfChangeNotAllowedWhenEnabled(551),
		ospfIntfChangeFromNBMANotAllowed(552),
		ospfPollIntIsnotMultOfHelloInt(553),
		ospfNeigNoCircuit(554),
		ospfNeigSameIp(555),
		ospfCircNotNBMA(556),
		ospfCircPriZero(557),
		ospfNBMANeigExist(558),
		ospfNBMANeigNotFound(559),
		ospfDynNeigExist(560),
		pgmInvalidSessionLifetime(561),
		pgmInvalidMaxRetxStates(562),
		pgmInvalidMaxSessions(563),
		pgmInvalidIfNakRetxInterval(564),
		pgmInvalidIfMaxNakRetxCnt(565),
		pgmInvalidIfNakRdataInt(566),
		pgmInvalidIfNakElimInt(567),
		maxOfMirroringPortAllowedExceed(568),
		duplicatedRoutePolicyEntry(569),
		specifiedRoutePolicyEntryNotFound(570),
		specifiedPrefixListNotFound(571),
		routePolicyListNotSpecify(572),
		routePolicyPrefixListOverLimit(573),
		ipPrefixListDuplicate(574),
		ipPrefixListDuplicateEntry(575),
		ipPrefixListEntryNotFound(576),
		ipPrefixListInvalidName(577),
		ipRedistributeDuplicateEntry(578),
		ipRedistributeEntryNotFound(579),
		ipOspfInFilterDuplicateEntry(580),
		ipOspfInFilterEntryNotFound(581),
		ipEcmpNotDisabled(582),
		ipEcmpMaxExceeded(583),
		ipfQosTrafficAvgRateZeroProfileEnable(584),
		ipmTimePruneEntryInvalidGroup(585),
		ipmTimePruneEntryDuplicate(586),
		ipmTimePruneEntryNotExist(587),
		ipmTimePruneEntryInvalidExpireTime(588),
		smltIstExist(589),
		smltSmltIdExist(590),
		smltIstNotExist(591),
		smltSmltIsEnabled(592),
		smltSmltLocalIpNotExist(593),
		smltInvalidPortTypeForIstMlt(594),
		ntpServerAlreadyExist(595),
		ntpServerDoesNotExist(596),
		ntpKeyAlreadyExists(597),
		ntpKeyDoesNotExist(598),
		ntpMaxKeyExceeded(599),
		ntpServerAlreadyEnabled(600),
		ntpServerAlreadyDisabled(601),
		ntpNoServerConfigured(602),
		ntpMaxServerNumExceeded(603),
		ntpInvalidIntervalValue(604),
		ecmpNotEnabled(605),
		ipfInvalidProtocolType(606),
		assignIpToPortInRouteVlan(607),
		assignIpToVlanWithRoutePortMember(608),
		ipfIstPort(609),
		smltMltIpfExist(610),
		smltMltPortIpfExist(611),
		smltL2fIstPort(612),
		smltMltL2fExist(613),
		smltMltPortL2fExist(614),
		portMirroringEgressNotSupportFullDuplexMode(615),
		pimGlobInvalidRegSupprTimeOut(616),
		smltNotAvailableIn8100(617),
		mltNoPort(618),
		mltInvalidPortType(619),
		inUsedByATM1483Elan(620),
		smltIstStpEnableNotAllowed(621),
		invalidHighestVrrpPrio(622),
		dynamicPortMemberIn8100IsNotAllowed(623),
		ipfGlobalNextHopModeNotSupported(624),
		smltPeerIpNotExist(625),
		smltMltNoThisVlan(626),
		smltNotANormalMlt(627),
		validStaticRtExist(628),
		validBlkHolRtExist(629),
		pimOrIgmpAlreadyEnabled(630),
		routePolicyOverSystemLimit(631),
		routePolicyOverVrfLimit(632),
		communityAlreadyExists(9101),
		communityDoesnotExist(9102),
		communityStorageTypePermanent(9103),
		defaultEntryNotDeletable(9104),
		invalidAccessPolicyStrict(9105),
		targetAddressNotExist(9106),
		cannotChangeCurrentAndDeprecatedMib(9107),
		invalidPath(9108),
		duplicateTargetAddress(9110),
		notifyTagIsOnlyAllowedUpTo32Chars(9112),
		authenticationFailureTrapMustBeEnabledFirst(9113),
		macFlapLimitTimeNotValid(9114),
		udpSrcByVipCannotBeEnabledWithoutVip(9115),
		configFileNameIsRequiredForSaveToSlave(9116),
		noSpaceAllowedInFilename(9117),
		noSpaceAllowedInPathname(9118),
		cannotDeleteAllMgmtVirtualIpWhenUdpSrcByVipEnabled(9119),
		invalidSaveConfigFilename(9120),
		rmonMemFail(9201),
		portMirroringTxNotSupportForThisHardwareRevision(9301),
		cannotSetMode(9302),
		cannotSetFraming(9303),
		cannotModifyInLaneMode(9304),
		stpIsNotAllowedToBeEnabledOnIstPort(9305),
		mirroredPortSupportRXModeOnly(9306),
		secondaryCpuNotActive(9307),
		commandNotAllowedInPrimaryCpu(9308),
		pcapUserDefinedDataInConsistency(9309),
		pcapFilterTblEntryNotFound(9310),
		pcapFilterTblDuplicateEntry(9311),
		pcapBufferSizeExceedsMaximumRamLimit(9312),
		portPcapIsActive(9313),
		pcapCommandNotAllowedWhenPcapIsEnabled(9314),
		invalidNumberOfHexDigits(9315),
		commandNotAllowedInHaCpuMode(9316),
		pcapCommandNotAllowedIn3SlotChassis(9317),
		pcapNoMemoryAllocatedForPcap(9318),
		pcapCannotBeEnabledWhenAutosaveInProgress(9319),
		pcapInvalidTimerRangeValue(9320),
		cannotSetPortAdminRouting(9322),
		smltNotAllowedObBrouterPort(9323),
		pcapOctapidNotInitialized(9324),
		pcapNoPackets(9325),
		pcapInsufficientDiskSpace(9326),
		pcapAutoSaveOrCopyCommandInProgress(9327),
		rmCommandNotAllowedWhenRemoteMirroringIsEnabled(9328),
		rmVlanNotPortBasedVlan(9329),
		rmPortNotMemberOfVlan(9330),
		rmSrcMacAddressNotSet(9331),
		rmRemoteMirroringActiveInOctapd(9332),
		rmRmtExceedsMaxLimit(9333),
		rmVlanIdNotSetForRmtPort(9334),
		rmDstMacNotSet(9335),
		rmPortDuplicateEntry(9336),
		rmPortEntryNotCreated(9337),
		rmRemoteMirroringActiveInRspLane(9382),
		portEapAuthorized(9345),
		portEapEnabled(9362),
		rateLimitingrmodPort(9363),
		bandwidthLimitingNonrmodPort(9364),
		egressRateLimitingNotAppToNonRModPort(9365),
		featureNotApplyToMixedMlt(9368),
		rateLimitingExistsForMlt(9369),
		differentPortConfigurationForMlt(9370),
		rModuleOnlyOneMirroredPortPerLane(9371),
		ieee8021pOverrideNotAppToNonRModPort(9372),
		portMirroringTxFilterNotSupportForThisHardwareRevision(9373),
		portIsDownOperationNotAllowed(9374),
		portSffdEnableError(9375),
		portTxFlowControlNotSupportedForThisHW(9376),
		portFcPause0NotSupportedForThisHW(9377),
		portFcPauseTimeNotSupportedForThisHW(9378),
		slppInvalidTxInterval(9380),
		slppInvalidRxThreshold(9381),
		cannotSetClockSource(9394),
		ingressPoliceNonRsPort(9395),
		customAutoNegAdvertNotSupported(9396),
		autoNegotiateIsDisable(9397),
		slppInvalidEtherType(9398),
		recordReserveTypeInvalid(9401),
		recordReserveOutOfRange(9402),
		recordReserveExceedPhyLim(9403),
		cannotUpNonEticketCard(9404),
		cannotUpNon128KCard(9405),
		naapVlanNotConfigured(9406),
		lpMiniSlotNotPresent(9407),
		lpSlotDisabled(9408),
		lpSlotEnabled(9409),
		cannotUpNonEmmodeCard(9410),
		cannotUpNonRmodeCard(9411),
		cannotUpNonRspCard(9412),
		dnsDuplicateEntry(9413),
		dnsEntryNotFound(9414),
		dnsEntryNotCreated(9415),
		smartCpldNotSupported(9416),
		slotNotPresent(9418),
		rmodeRequired(9419),
		maxVlanDisallow(9420),
		softwareLicenseViolation(9425),
		cpuActionNotAllowed(9426),
		resetOperNotAllowed(9427),
		cpuActionNotAllowedPwrPrio(9428),
		yearAllowedToBeSetExceeds(9438),
		adminStatusCannotBeModifiedOnMasterCP(9439),
		resetOnlyAllowedOnStandbyCPOrIOCardOrSFCard(9440),
		cardIsNotPoweredOn(9441),
		adminEnableOrDisableIsOnlyAllowedOnIOCard(9442),
		powerPriorityOfCPCannotBeModified(9443),
		powerPriorityCannotBeModifiedOnSF1andSF4(9444),
		powerPriorityCannotBeModifedOnThisSlot(9445),
		poweringDownOfMasterCPIsNotAllowed(9446),
		powerDownOnlyAllowedOnIOAndSFSlot(9447),
		powerIsAlreadyOn(9448),
		powerIsAlreadyDown(9449),
		dnsEntryCannotBeCreatedWithoutAddress(9450),
		dnsServerIpv6AddressNotSupported(9451),
		powerPriorityCannotBeSetToCritical(9452),
		fabStatsCaptureCannotBeEnabledWithoutPort(9453),
		resetOnlyAllowedOnOneManagementSFCard(9454),
		onlyOneManagementSFCardPowerDown(9455),
		tenGEMltPortCannotBeAddedToStgWithSMLT(9501),
		tenGEPortCannotBeAddedToStgWithSMLT(9502),
		rstpInvalidVal(9504),
		mstpInvalidVal(9505),
		mstpOperationNotAllowed(9542),
		priorityValueMustBeAMultipleOf4096(9510),
		maxAgeMustEqualOrGreatThan2XPortHelloTimePlus1Second(9520),
		pbtStgCannotEnableStp(9521),
		maxAgeMustEqualOrLessThan2XForwardDelayMinus1Second(9529),
		mappingExistsForInstanceUnmapVlansFirst(9535),
		plsbMstpInstanceAllowedOnlyInMstpMode(9536),
		plsbStgInstanceCannotBeRemovedWhenPlsbVlanExists(9537),
		stgInstanceCannotBeSetToPlsbType(9538),
		plsbMstiCannotEnableForcePortState(9539),
		ospfOverlappingSummarizedRange(9601),
		ospfHelloIntNotGreatDeadInt(9605),
		cluserInvalidId(9901),
		clusterDoesNotExist(9902),
		clusterAlreadyExists(9903),
		clusterSizeExceeded(9904),
		invalidMiniSlot(9905),
		brouterOpNotAllowedOnIsdPort(9907),
		clusterIdMandatory(9906),
		removeVlanBeforeDeletingCluster(9908),
		vlanWithIPXEnabledCannotAdd10GEPortOrMlt(1101),
		addRemDsapSsapNotAllowed(1102),
		maxDsapSsapExceeded(1103),
		vlanInvalidEncap(1104),
		vlanEnforcementNotAllowed(1109),
		vlanNaapVlanPortMustBeTagged(1110),
		vlanRegPortNotAllowedInNaapVlan(1111),
		vlanFwPortNotAllowedInRegVlan(1112),
		invalidVlanIdSpecified(1113),
		retrieve10GEInfoFailure(1115),
		minMacGreaterThanMaxMac(1116),
		maxMacLessThanMinMac(1117),
		prPortNotForStackedVlan(1121),
		prPortNotForIPXVlan(1122),
		vlanAgingTimeNotAppToStaticVlan(1123),
		naapInvalidVlanId(1126),
		clusterIsdAlreadyUsed(1129),
		regularPortsNotAllowedInPeeringVlan(1130),
		regularPortsNotAllowedInClusterSyncVlan(1131),
		mltSdmPortNotAllowed(1132),
		clusterIdNotAllowedForNormalVlan(1133),
		clusterTypeNotSupported(1134),
		clusterMgmtSyncVlanCannotBeSame(1135),
		nsnaPortNotConfigurable(1138),
		nsnaUplinkOperationNotAllowed(1139),
		clusterTpsSizeExceeded(1145),
		clusterNotFwIsd(1148),
		clusterNotTpsIsd(1149),
		vlanFwPortDelNotAllowedInRegVlan(1151),
		fwPortNotAlwdForClusterTypeIs(1152),
		syncVlanNotAlwdForClusterTypeIs(1153),
		portMemberNotAlwdForNonIsCluster(1154),
		portMemberOfIsClusterCannotBeSdmPort(1155),
		portHasPcapEnabled(1156),
		portInSameOctapidAsIsCluster(1157),
		pcapInvalidTypeForAclFilter(1160),
		rmodOnlyOnePcapPortPerLane(1161),
		rstpOnlyDefaultInstanceAllowed(1174),
		maxSubnetVlanReached(1185),
		maxProtocolVlanReached(1186),
		cannotCreateFilterEntryForTdpMac(1187),
		entryAlreadyExists(1188),
		macIsConfiguredAsStaticMacInVlan(1189),
		macHasBeenLearntConfiguredInVlan(1190),
		macIsBeingUsedAsLoopDetectMac(1191),
		cannotCreateFilterEntryForLocalMac(1192),
		cannotCreateFilterEntryForBpudMac(1193),
		cannotUntagPort(1196),
		duplicateProtocolIdRecord(1197),
		cannotAddPortsToPlsbBVlan(1198),
		unsupportedVlanType(1199),
		dynModMaxModule(1201),
		dynModUnknown(1202),
		dynModAlreadyLoaded(1203),
		dynModCantOpenFile(1204),
		dynModNotEnoughSpace(1205),
		circuitlestInvalidIpInterfaceId(1501),
		circuitlessMaxNumberIpInterfacesReached(1502),
		circuitDoesNotExist(1503),
		circuitAlreadyExists(1504),
		circuitlessIpInterfacesOperationNotAllowed(1505),
		priority255SpecialForPhyIpSameAsVrIp(1506),
		icmpRdiscInvalidPreferenceLevel(1507),
		icmpRdiscAdvAddrIsNotBroadcastOrMulticastAddr(1508),
		icmpRdiscInvalidMaxAdvInt(1509),
		icmpRdiscMinAdvIntvGreaterThanMaxAdvIntvOrLessThan3Secs(1510),
		icmpRdiscLifeTimeLessThanMaxAdvIntvOrGreaterThan9000Secs(1511),
		vrrpInvalidFasterAdvertInterval(1512),
		vrrpFasterAdvEnabled(1513),
		vrrpFasterAdvDisabled(1514),
		vrrpInvalidFastAdvEnableValue(1515),
		globalFiltersNotSupportFwdingNextHopMode(1516),
		vrrpPreemptActionNotAllowed(1517),
		rcPimModeIgmpVersionIncompatible(1518),
		invalidOrInconsistentBroadCastMaskValue(1519),
		invalidRipTimeoutInterval(1520),
		rsmltNoCirc(1521),
		rsmltInvalidHoldUpTimer(1522),
		rsmltNoBrouter(1523),
		rsmltNoIst(1524),
		vrrpSetWithRsmltEnable(1527),
		rsmltSetWithVrrpEnable(1528),
		ipEcmpMaxPathExceeded(1530),
		ipEcmpPathListNotAllowedInRmode(1531),
		featureAppliesToRmodulePortsOnly(1532),
		invalidVrrpEntry(1533),
		invalidIpOwnerVrrpPrio(1534),
		circuitlessIpUsedByIpvpnRD(1537),
		arpDeleteSupportedOnlyForDynamicArps(1542),
		arpMulticastMacAddressNotAllowed(1544),
		arpBroadcastMacAddressNotAllowed(1545),
		arpNoIpAddrAssociatedWithPort(1546),
		arpIncorrectIpAddress(1547),
		arpEntryCreateionRequiresMacAddress(1549),
		arpEntryMofifcationNotAllowed(1550),
		interfaceDoesNotHaveIpAddressAssigned(1551),
		cannotConfigSameAddrWithDiffPrefixLength(1552),
		cannotConfigureAddrWhichIsSiteLocal(1553),
		invalidHelpSourcePathname(1601),
		invalidHelpSourceRemotePathname(1602),
		webInvalidHttpsPort(1603),
		invalidDdmMonitorInterval(1801),
		invalidDdmMonitor(1802),
		invalidDdmTrapsSend(1803),
		invalidDdmAlarmPortdown(1804),
		igmpOutOfSsmRange(2301),
		igmpDuplicateSsmTblEntry(2302),
		igmpSsmEntryDoesNotExist(2303),
		igmpSsmTblNotEmpty(2304),
		igmpRpSetExistsInSsmRange(2305),
		igmpCandidateRpExistsInSsmRange(2306),
		igmpIfInvalidQIntervalMrt(2307),
		igmpAlreadyEnabled(2308),
		igmpMaxStreamExceeded(2309),
		igmpStreamLimitAlreadyEnabled(2310),
		igmpStreamLimitNotEnabled(2311),
		igmpPimEnabledInSSMMode(2312),
		igmpDisableV3First(2313),
		igmpSSmConflictsWithSsgEntry(2314),
		igmpSsmCanNotDisableDynamicEntry(2315),
		invalidIpMulticastRange(2316),
		igmpStaticGroupCountExceeded(2317),
		igmpOverlappingStaticRangeNotAllowed(2319),
		igmpCannotEditStaticRecMcastDisabledGloballyOrOnVlan(2320),
		igmpPortMaxStreamExceedsIntfMaxStream(2327),
		igmpQueryMaxResponseUnsupportedOnV1(2328),
		igmpExplicitHostTrackingRequired(2333),
		igmpExplicitHostTrackingUnsupportedOnV1V2(2334),
		igmpCannotDeleteLastPortStaticGroup(2335),
		igmpUnspecifiedPortStaticGroup(2336),
		igmpNotVersion3(2337),
		igmpDisableSsmSnoop(2338),
		ipfStreamAlreadyExists(2401),
		ipfStreamDoesNotExists(2402),
		ipfStreamInvalidStreamType(2403),
		ipfStreamInvalidPortOption(2404),
		ipfStreamNameTooLong(2405),
		ipfStreamInvalidProtocol(2406),
		ipfStreamInvalidDscp(2407),
		ipfDeviceAlreadyExists(2408),
		ipfDeviceUnknownPlatform(2409),
		ipfDeviceUnknownDevice(2410),
		ipfDeviceDoesNotExists(2411),
		ipfDeviceNameTooLong(2412),
		ipfOneZeroIpDestFilterIsAllowed(2413),
		ipfGlobalFilterMaxPerOctapid(2414),
		ipfDeviceMaxPerPort(2415),
		ipfDeviceMaxPerBox(2416),
		ipfDeviceMaxFilterList(2417),
		ipfInvalidRmodPort(2418),
		ipfSourceNextHopModeNotSupported(2419),
		aclErrIdInvalid(2428),
		aclErrNameInvalid(2429),
		aclErrTypeInvalid(2430),
		aclErrNotExist(2431),
		aclErrInUse(2432),
		aclErrExists(2433),
		aceErrAceNotExist(2438),
		aceInvalidMode(2482),
		aceEgressqEgressqnnscInvalid(2483),
		cannotDeleteIntMltId(2501),
		mltNoThisVlan(2502),
		mltPortsDifferentFramingMode(2503),
		moreThan2PortsInMlt(2504),
		portCannotBeAddedToDefualtVLANWithIPXEnabled(2505),
		portMemberNotSupportSMLT(2506),
		tenGEMltPortOrMltCannotBeAddedToVlanWithSmltMember(2507),
		tenGEMltPortCannotRunTogetherWithSMLT(2508),
		portCannotBeAddedToDefualtVLANWithSMLT(2509),
		tenGEPortOrMltCannotBeAddedToVlanWithSmltMember(2510),
		tenGEPortOrMltCannotRunTogetherWithSMLT(2511),
		tenGEPortNotSupportMcastDistribution(2512),
		tenGEPortNotSupportMLT(2513),
		mltSmltIdAlreadyExists(2514),
		mltInvalidSmltId(2515),
		mltSmltNotConfigured(2516),
		mltSmltAlreadyConfigured(2517),
		mltPortIsMemberOfMlt(2518),
		mltPortIsMemberOfSmlt(2519),
		mltSmltIpAddrNotAllowedOnSltPort(2520),
		mltUsedForLacp(2521),
		mltPortUsedForLacp(2522),
		mltUsedForMlt(2523),
		operationNotAllowedOnMltPort(2529),
		mltNsnaUplinkMismatch(2538),
		mltIdInvalidInNonRmode(2539),
		mltNaapVlanCannotBeAddedToIst(2540),
		mltIstCannotBeCreatedOverMltWithNaapVlan(2541),
		mltNaapCannotBeAddedToMltWithActiveIst(2542),
		mltVrfVlanAndLegacyPortCannotBeMembers(2563),
		cannotUntagMlt(2567),
		mltNameIsReservedAsDefautNameForAnotherMlt(2568),
		quotesNotAllowedInsideTheNameString(2569),
		mltNameIsBeingUsedByAnotherMlt(2570),
		mltCpLimitShutdownOnIstMltNotAllowed(2571),
		peerIpAndIstVlanNotInSameSubnet(2572),
		peerIpAndLocalIpCannotBeSame(2573),
		asListOverLimit(2601),
		communityListOverLimit(2602),
		mltSmltLacpInvalidKey(2603),
		extCommunityListOverLimit(2606),
		extCommunityInvalidListId(2607),
		extCommunityListIdExceedsRange(2608),
		mcastMltNotEnabled(2701),
		mcastMltInvalidSrcMask(2702),
		mcastMltInvalidGrpMask(2703),
		mcastMltRedistrNotEnabled(2704),
		mcastMltDiscontiguousSrcMaskValue(2705),
		mcastMltDiscontiguousGrpMaskValue(2706),
		mcastMltNotEnabledOnMlt(2707),
		mcastMltPortOnNonEtkt(2708),
		mcastMltConfMaskDisableMcastMlt(2709),
		ipmcTimePruneConflictsWithSsmEntry(2710),
		mcastMltCannotBeDisabled(2712),
		rcSnmpSyslogDisableSyslogFirst(2801),
		rcSnmpInvalidSyslogHeader(2802),
		configSyslogHostAddrBeforeEnabling(2803),
		dvmrpMBRNotAllowed(2901),
		dvmrpInvalidIntfTypeChange(2902),
		ipxPolicyNetEntryNotFound(3101),
		ipxPolicyNetDuplicateEntry(3102),
		ipxPolicyNetListEntryNotFound(3103),
		ipxPolicyNetListDuplicateEntry(3104),
		ipxPolicyServEntryNotFound(3105),
		ipxPolicyServDuplicateEntry(3106),
		ipxPolicyServeListEntryNotFound(3107),
		ipxPolicyServListDuplicateEntry(3108),
		ipxPolicyPolicyEntryNotFound(3109),
		ipxPlicyPolicyDuplicateEntry(3110),
		ipxRoutePolicyNetListOverLimit(3111),
		ipxRoutePolicyServListOverLimit(3112),
		ipxPolicyRipOutFilterEntryNotFound(3113),
		ipxPolicySapOutFilterEntryNotFound(3114),
		ipxPolicyRipInFilterEntryNotFound(3115),
		ipxPolicySapInFilterEntryNotFound(3116),
		ipxPolicyIpxNetEntryInvalidName(3117),
		ipxPolicyIpxServEntryInvalidName(3118),
		ipxPolicyPolicyEntryInvalidName(3119),
		vlanHas10GEMemberWhichNotSupportIPX(3120),
		vlanContainUnSupportedPrPort(3121),
		invalidLengthOf2kBootConfigLicenseSource(3401),
		licenseFileDoesNotExist(3402),
		invalidModeForAtmMDAType(3901),
		atmInvalidPVCEncapTypeForElan(3902),
		atmInvalidPVCPCRRange(3903),
		unsupportedVPI(3904),
		radiusAuthAcctAttrSame(4101),
		radiusAuthAcctPortSame(4102),
		radiusAuthAcctNoServerConfig(4103),
		radiusReAuthTimerFailed(4104),
		radiusAbortSesionTimerFailed(4105),
		radiusInvalidSnmpUserLength(4106),
		radiusInvalidCliCommandCount(4107),
		radiusAuthAcctNoServerButSnmpConfig(4112),
		radiusDisableAcctBeforeDeletingLastServer(4113),
		radiusEnableRadiusBeforeEnablingAccounting(4114),
		disableAccountingBeforeDisablingRadius(4115),
		ripEnableExceedsMaxLimit(4701),
		pimGlobInvalidUniRouteChangeTimeOut(4801),
		pimGlobInvalidDiscDataTimeOut(4802),
		pimGlobInvalidCRPADVTimeOut(4803),
		pimGlobInvalidBootStrapPeriod(4804),
		pimStaticRpEnabled(4805),
		pimStaticRpNotEnabled(4806),
		pimStaticRpEntryExists(4807),
		pimStaticRpNoRoute(4808),
		pimAddressInSsmRange(4809),
		pimInvalidModeChange(4810),
		pimStaticRpNotAllowed(4811),
		pimMBRNotAllowed(4812),
		pimGlobInvalidActChkInterval(4813),
		pimGlobActChkIntervalNotAllowed(4814),
		pimGlobNotSuppActChkInterval(4817),
		pimVirtualNbrInvalidIfIndex(4818),
		rpsMcastMaskLenToNotAllowed(4901),
		tcpConnectionNotFound(5101),
		tcpInvalidState(5102),
		tcpSessionsInUse(5103),
		bgpPeerNotFound(5201),
		bgpInvalidPeerEnable(5202),
		bgpInvalidPeerRemoteas(5203),
		bgpInvalidPeerGroupName(5204),
		bgpInvalidPeerDefaultOriginate(5205),
		bgpInvalidPeerEbgpMultiNop(5206),
		bgpInvalidPeerAdvertisementInterval(5207),
		bgpInvalidPeerPassword(5208),
		bgpInvalidPeerWeight(5209),
		bgpInvalidPeerNextHopSelf(5210),
		bgpInvalidPeerRoutePolicyIn(5211),
		bgpInvalidPeerRoutePolicyOut(5212),
		bgpInvalidPeerRouteReflectorClient(5213),
		bgpInvalidPeerSoftReconfigurationIn(5214),
		bgpInvalidPeerSoftReconfiguration(5215),
		bgpInvalidPeerRemovePrivateAs(5216),
		bgpInvalidPeerRowStatus(5217),
		bgpNetworkNotFound(5218),
		bgpPeerGroupNotFound(5219),
		bgpInvalidPeerGroupEnable(5220),
		bgpInvalidPeerGroupRemoteAs(5221),
		bgpInvalidPeerGroupDefaultOriginate(5222),
		bgpInvalidPeerGroupUpdateSource(5223),
		bgpInvalidPeerGroupEbgpMultiHop(5224),
		bgpInvalidPeerGroupAdvertisementInterval(5225),
		bgpInvalidPeerGroupPassword(5226),
		bgpInvalidPeerGroupWeight(5227),
		bgpInvalidPeerGroupNextHopSelf(5228),
		bgpInvalidPeerGroupRoutePolicyIn(5229),
		bgpInvalidPeerGroupRoutePolicyOut(5230),
		bgpInvalidPeerGroupRouteReflectorClient(5231),
		bgpInvalidPeerGroupSoftReconfigurationIn(5232),
		bgpInvalidPeerGroupSoftReconfiguration(5233),
		bgpInvalidPeerGroupRemovePrivateAs(5234),
		bgpInvalidPeerGroupHoldTime(5235),
		bgpInvalidPeerGroupKeepAlive(5236),
		bgpInvalidPeerGroupRowStatus(5237),
		bgpInvalidPeerGroupGroupName(5238),
		bgpAggregateNotFound(5239),
		bgpInvalidAggregateAsSetGenerate(5240),
		bgpInvalidAggregateSummaryOnly(5241),
		bgpInvalidAggregateSuppressPolicy(5242),
		bgpInvalidAggregateAdvertisePolicy(5243),
		bgpInvalidAggregateAttributePolicy(5244),
		bgpOperationNotAllowedWhenBgpIsEnabled(5245),
		bgpInvalidPeerHoldTime(5246),
		bgpInvalidPeerKeepAlive(5247),
		bgpInvalidPeerMaxPrefix(5248),
		bgpInvalidPeerGroupMaxPrefix(5249),
		bgpInvalidPeerMD5Authentication(5250),
		bgpInvalidPeerGroupMD5Authentication(5251),
		bgpInvalidPeerGroupIndex(5252),
		bgpInvalidConfederationIdentifier(5253),
		bgpInvalidConfederationPeerAsNumber(5254),
		bgpInvalidConfederationPeerNotFound(5255),
		bgpInvalidConfederationPeerAlreadyExist(5256),
		bgpOperationNotAllowedWhenSoftReconfigInIsDisabled(5257),
		bgpNotAllowedSoftRecfgInIsDisabledForTheGrpOrAnyPeerInGrp(5258),
		bgpCanNotEnablePeerWithoutCfgRemoteAsForThePeer(5259),
		bgpCanNotEnablePeerGrpWoCfgRemoteASPeerGrpOrAnyPeerInGrp(5260),
		bgpOperationNotAllowedWhenPeerIsBGPON(5261),
		bgpOperationNotAllowedWhenPeerGrpOrAnyPeerInGrpIsBGPON(5262),
		bgpOperationNotAllowedExternalPeer(5263),
		bgpOperationNotAllowedInternalPeer(5264),
		asListNotFound(5265),
		asListDuplicate(5266),
		asListAsPathEntryNotFound(5267),
		asListAsPathEntryDuplicate(5268),
		asListInvalidModeOfAsPathEntry(5269),
		asListInvalidAsRegularExpressionOfAsPathEntry(5270),
		asListInvalidRowStatusOfAsPathEntry(5271),
		communityListNotFound(5272),
		communityListDuplicate(5273),
		communityListCommunityPathEntryNotFound(5274),
		communityListCommunityPathEntryDuplicate(5275),
		communityListInvalidModeOfCommunityPathEntry(5276),
		communityListInvalidValueOfCommunityEntry(5277),
		communityListInvalidRowStatusOfCommunityEntry(5278),
		bgpFeatureNotSupport(5279),
		bgpMd5EnabledWithoutPasswd(5280),
		bgpEnabledWithoutLocalAs(5281),
		bgpAggregateAdvertisePolicyWithoutAsSet(5282),
		bgpPeerHoldTimeLessThanKeepAliveTime(5283),
		bgpCommListCommunityStringUsed(5284),
		communityListModificationNotAllowed(5288),
		bgpInvalidPeerGroupAsOverride(5289),
		bgpInvalidPeerGroupAllowAsIn(5290),
		bgpInvalidPeerAllowAsIn(5291),
		bgpInvalidPeerAsOverride(5292),
		extCommunityListNotFound(5293),
		extCommunityListModificationNotAllowed(5294),
		extCommunityListInvalidEntry(5295),
		extCommunityListDuplicateMemberId(5296),
		extCommunityListInfoAlreadyExists(5297),
		extCommunityMemberNotFound(5298),
		bgpPeerLimitExceeded(5299),
		bgpPeerIpv6NotSupport(5301),
		extComListCannotCreateWithoutRtOrSooConfig(5302),
		extComListRtAssignedNumMustBeConfigured(5303),
		extComListSooAssignedNumMustBeConfigured(5304),
		sshEnableTrue(5501),
		rsaKeyNotExist(5502),
		dsaKeyNotExist(5503),
		rsaKeyGenMiss(5504),
		dsaKeyGenMiss(5505),
		sshShutDownInProcess(5506),
		sshInvalidPort(5507),
		sshPortAlreadyInUse(5508),
		sshPortReserved(5509),
		sshAuthenticationNotEnabled(5510),
		sshUnableToRetrieveGlobalData(5511),
		invalidOperationOnWsmOrSamStg(5601),
		invalidOperationOnWsmOrSamVlan(5602),
		invalidOperationOnWsmOrSamPort(5603),
		invalidOperationOnSamPort(5604),
		mplsInvalidRouterId(6109),
		lacpInvalidAggrsysPrio(6501),
		lacpInvalidAggrActorAdminKey(6502),
		lacpInvalidAggrColMaxDelay(6503),
		lacpInconsistentKey(6504),
		lacpInvalidVal(6505),
		lacpOutOfRangeKey(6506),
		lacpPortNotAggregatable(6507),
		lacpKeyModificationNotAllowedOnSltPort(6508),
		vlacpTimeoutScaleRangeBetween3To10(6509),
		lacpOtherPortsWithSameKey(6510),
		vlacpOneofPortorMLTIdIsRequired(6511),
		vlacpDuplicatePeerMacAddress(6512),
		vlacpOutOfRangeMac(6513),
		lacpSmltSysIdSyncIncomplete(6514),
		vlacpOperationReqPortVlacpDis(6515),
		vlacpEtherTypeIsInvalid(6527),
		lacpPortsWithSameKeyHaveLosslessMismatch(6528),
		mirrorByPortNonExistingEntry(6711),
		mirrorEntryNotExist(6712),
		mirrorEntryExists(6713),
		mirrorOneDestAllowed(6714),
		mirrorPortInUse(6715),
		miirorIpNotSupportRemoteVlanId(6716),
		mirrorPortSameAsMirroringPort(6717),
		mirrorPortInConflictWithVlanPort(6718),
		mirrorPortInConflictWithMltPort(6719),
		mirrorPortExistsInAnotherEntry(6720),
		mirroringPortExistsInAnotherEntry(6721),
		mirroredPortsNotConfigured(6722),
		mirroringAndRemoteVlanMustMatch(6723),
		mirroringPortMustExistOnRemoteVlan(6724),
		mirroringMltIsNotPartOfRemoteVlan(6725),
		mirroringVlanShouldHavePortsAssigned(6726),
		mirroringVlanCannotBeRoutable(6727),
		mirroringPortCannotBeBrouter(6728),
		diagEntryWithRemoteMirrorExistsCannotAddIp(6729),
		diagMonitorIpInSameSubnetAsLocalInterface(6730),
		diagEntryWithMonitorIpInSameSubnetExists(6731),
		targetAddressMissing(6801),
		testAlreadyRunning(6802),
		invalidTargetAddress(6803),
		invalidSourceAddress(6804),
		controlEntryAlreadyExists(6805),
		invalidIpAddressFormat(6806),
		invalidDataRange(6807),
		invalidIndex(6808),
		entryDoesNotExist(6809),
		controlEntryMaxLimitReached(6810),
		maxRowOutOfRange(6811),
		ipv6VlanDoesnotExist(7401),
		ipv6InvalidInstance(7402),
		ipv6InvalidParameter(7403),
		ipv6AttrNotImplemented(7404),
		ipv6EntryDuplicate(7405),
		ipv6EntryNotExist(7406),
		ipv6InvalidIdentifierLength(7407),
		ipv6CircuitDoesNotExist(7408),
		ipv6PortNotPowerRanger(7409),
		ipv6InvalidInterfaceIdentifier(7410),
		ipv6CannotChangeWhenAdminEnable(7411),
		ipv6InvalidReasmMaxSize(7412),
		ipv6InvalidReachableTime(7413),
		ipv6InvalidPrefixLength(7414),
		ipv6InvalidSendAdverts(7415),
		ipv6InvalidMaxInterval(7416),
		ipv6InvalidMinInterval(7417),
		ipv6InvalidRetransmitTimer(7418),
		ipv6InvalidDefaultLifeTime(7419),
		ipv6InvalidCurHopLimit(7420),
		ipv6InvalidManagedFlag(7421),
		ipv6InvalidOtherConfigFlag(7422),
		ipv6InvalidDadNsNum(7423),
		ipv6InvalidPhysicalAddress(7424),
		ipv6InvalidNetToPhysicalType(7425),
		ipv6NeighborDuplicate(7426),
		ipv6NeighborDoesNotExist(7427),
		ipv6InvalidInvalidIpv6Addr(7428),
		ipv6PrefixDuplicate(7429),
		ipv6InvalidPrefix(7430),
		ipv6InvalidInterfaceType(7431),
		ipv6NexthopOrIndexReq(7432),
		ipv6NexthopIsLinklocBothIndexHopReq(7433),
		ipv6StaticRouteDistanceReq(7434),
		ipv6StaticRouteDuplicate(7435),
		ipv6StaticRouteInvalid(7436),
		ipv6OspfInvalidRouterId(7437),
		ipv6OspfNotSupported(7438),
		ipv6OspfAreaDoesNotExist(7439),
		ipv6OspfAlreadyExist(7440),
		ipv6OspfInterfaceInvalid(7441),
		ipv6OspfInterfaceExists(7442),
		ipv6OspfInterfaceNotExists(7443),
		ipv6OspfAreaAggregateEntryExists(7444),
		ipv6OspfAreaAggregateEntryDoesNotExist(7445),
		ipv6OspfInvalidAreaRangeMask(7446),
		ipv6OspfAreaCannotModifyBackbone(7447),
		tcpConnectTblPermittedStateIsDelete(7448),
		ipv6InterfaceVlanNotFound(7449),
		ipv6TunnelInterfaceDoesnotExist(7450),
		ipv6TunnelNotImplemented(7451),
		ipv6TunnelInvalidOperation(7452),
		ipv6TunnelInvalidType(7453),
		ipv6TunnelInterfaceAlreadyExist(7454),
		ipv6TunnelRemAddrShldBeZero(7455),
		ipv6VlanDoesNotMatchPreviousVlanid(7456),
		ipv6UvifDoesNotExist(7457),
		ipv6MldNotEnabled(7458),
		ipv6MldInterfaceExists(7459),
		ipv6MldInterfaceDoesNotExist(7460),
		ipv6MldInvalidQueryInterval(7461),
		ipv6MldInvalidVersion(7462),
		ipv6MldInvalidMaxRespdelay(7463),
		ipv6MldInvalidRobvar(7464),
		ipv6MldInvalidLlqi(7465),
		ipv6RedistributionInvalidOperation(7466),
		ipv6InvalidMaxRouterAdvertInterval(7467),
		ipv6InvalidMinRouterAdvertInterval(7468),
		ipv6CannotSetSummaryAsFalseIfNotStubArea(7469),
		ipv6CannotModifyStubMetricIfNotStubArea(7470),
		ipv6GatewayMustBeOnMgmtInterface(7471),
		ipv6OspfNbmaNbrAlreadyExist(7472),
		ipv6OspfInterfaceNotNbma(7473),
		ipv6OspfNbmaTunnelNot624(7474),
		ipv6OspfNbmaNbrNotExist(7475),
		cannotConfigureAddrWhichIsLinkLocal(7476),
		addrEntryDoesNotExist(7477),
		ipv6TunnelCannotHaveMoreThanOneAddr(7478),
		cannotChangeAddressType(7479),
		cannotConfigureNetAddr(7480),
		invalidInetNetworkAndMask(7481),
		cannotConfigureHostAddr(7482),
		ipv6InterfaceIdCannotBeChanged(7483),
		ipv6TunnelLocalAndRemoteIpAddressCannotBeSame(7484),
		ipv6StaticRouteWrongNexthop(7485),
		ipv6EuiInterfacePrefixCannotBeGreaterThan64(7486),
		ipv6CircuitMcastFlagNotSet(7487),
		ipv6MldProxyUnsupported(7488),
		ipv6MtuChangeWhenIntfDisable(7489),
		ipv6OspfNbmaNbrInvalidAddress(7490),
		ipv6AddressAndPrefixSame(7491),
		ipv6IncompatibleAddressTypeAndAddress(7492),
		ipv6DadInProgressTryLater(7493),
		ipv6InterfaceMismatch(7494),
		ipv6StaticNeighborInterfaceNotPresent(7495),
		ipv6RequiresSuperMezz(7496),
		ipv6StaticRouteOnlyIfindexCannotConfigPref(7497),
		ipv6StaticRouteRecursiveRouteNotSupported(7498),
		ipv6TunnelLocalRemoteAddrPairAlreadyExists(7499),
		idInvalid(7501),
		notExist(7502),
		duplicate(7503),
		nameInvalid(7504),
		notenablemixedmlt(7505),
		portconflictmixedmlt(7506),
		cannotConfigureBothNetAndHostAddr(7510),
		actInUse(7601),
		actFieldTooMany(7602),
		actPatternNotExist(7603),
		actErrApplyStateTrue(7604),
		actMaxPatternExceeded(7605),
		aclActNotExist(7606),
		aclTypeInvalid(7607),
		aclDefActionInvalid(7608),
		aclGlobActionInvalid(7609),
		vlanInvalid(7610),
		portInvalid(7611),
		aclMltInvalid(7612),
		aclInUse(7613),
		aclInvalidState(7614),
		aclActNotApplied(7615),
		aclActVlanAttrSpecified(7616),
		aclActPortAttrSpecified(7617),
		aclPortBased(7618),
		aclVlanBased(7619),
		actNoAttributesConfigured(7620),
		aclErrPortAlreadyInAcl(7621),
		aclErrVlanAlreadyInAcl(7622),
		aceAclIdInvalid(7623),
		aceAclNotExist(7624),
		aceInUse(7625),
		aceMax(7626),
		aceModeIllegal(7627),
		aceDscpIllegal(7628),
		aceDot1pIllegal(7629),
		aceUnreachIllegal(7630),
		acePoliceIllegal(7631),
		aceAclInvlanPoliceNotAllLanes(7632),
		aceInvalidAdminState(7633),
		aceEgressQueueInvalid(7634),
		aceEgressQueue1gInvalid(7635),
		aceEgressQueue10gInvalid(7636),
		aceEgressNNSCInvalid(7637),
		acePoliceInvalidMode(7638),
		aceAttrNotExistInAct(7639),
		aceInsuffActionAttr(7640),
		maxAceForSystem(7641),
		aceValMoreThanActPatternLen(7642),
		aceMltIndexIllegal(7643),
		aceModeNotPermit(7644),
		aceNotPermitIngress(7645),
		aceParmNotDefault(7646),
		aceAttrConflict(7647),
		defaultIdnoCreate(7648),
		defaultIdnoDelete(7649),
		defaultIdnoModify(7650),
		mltPortAclConflict(7651),
		aceNoModeModify(7652),
		aclNoAccept(7653),
		aceDebugMirrorDisableToRemoveDest(7658),
		aclDefActionControl(7659),
		aclStateEnable(7660),
		aclStateDisable(7661),
		aceRedirectMaxLimit(7662),
		aceRedirectNotConfigure(7663),
		aceQosAction(7664),
		aceSecurityAction(7665),
		aceActionMaxCount(7666),
		aceCountActionInvalid(7667),
		aceLogActionInvalid(7668),
		aceInoutPortAction(7669),
		aceInoutVlanAction(7670),
		aceAttListRange(7671),
		acenoIpProtoAttr(7672),
		aceEthVlanList(7673),
		aceMask(7674),
		aceL3L4Config(7675),
		noFreeFilterMirrorIdAvail(7676),
		etherTypeAttribFirst(7677),
		aclTypeCannotBeModified(7679),
		aceInvalidOperMask(7680),
		qosAceCannotHaveDenyMode(7681),
		aceSrcMacInvalidAddr(7682),
		aceNotAllowRemoveAllPortsAfterCreation(7683),
		acePortEntryRequiresOnePortForCreation(7684),
		acePortEntryAllowsOnlyOnePort(7685),
		aceEthVlanIdEntryCreationRequiresOperaiotnAndVlanId(7689),
		aceEthVlanTagPrioEntryCreationRequiresOperAndTagPrio(7690),
		aceInvalidOperMacMask(7691),
		aceEthMacEntryCreationRequiresOperaiotnAndMacAddr(7692),
		aceIpEntryCreationRequiresOperaiotnAndIpAddr(7693),
		aclNoMultipleMirrorDest(7694),
		aceProtoPortEntryCreationRequiresOperAndPort(7695),
		entryOnlyAllowOnePortToBeSet(7696),
		portInputFormatIsInvalid(7697),
		operationMaskMustBeZeroWhenOperationIsNotMask(7698),
		aceTcpFlagEntryCreationRequiresOperaiotnAndTcpFlag(7699),
		qosPolicyLaneExist(7701),
		qosPolicyLaneNotExist(7702),
		qosPolicyPkRateInvalid(7703),
		qosPolicySvcRateInvalid(7704),
		qosPolicyLaneInvalid(7705),
		qosPolicyValidAcesPresent(7706),
		qosTxQSetQmaxInvalid(7707),
		qosTxQSetQmaxChangeNotAllowed(7708),
		qosTxQSetBalQInvalid(7709),
		qosTxQSetHipriQInvalid(7710),
		qosTxQSetLopriQInvalid(7711),
		qosTxQSetMaxQExceed(7712),
		qosTxQSetPortNotRMod(7713),
		qosTxQSetQInvalid(7714),
		qosTxQSetQNotAssign(7715),
		qosTxQSetMinRateGtMaxrate(7716),
		qosTxQSetQMaxAfter8Adjust(7717),
		qosTxQSetPortFeIncompatibleQset64(7718),
		qosTxQSetPortGbIncompatibleQset8(7719),
		qosTxQSetModificationNotAllowed(7720),
		qosSvcRateInvalid(7765),
		qosTxQSetQLengthWredModNotAllowed(7766),
		ipv6InterfaceAdminDisabled(7802),
		ipv6ForwadingDisabled(7803),
		noVrrpLinkLocalAddressSpecified(7804),
		vrrpLinkLocalAddressCannotBeChanged(7805),
		vrrpInvalidGlobalAddress(7806),
		invalidLinkLocalAddress(7807),
		addressExistsOnVrrp(7808),
		invalidVrrpAddressOwnerPriority(7809),
		ipv6ValidLifeCanOnlyBeInfinityForInfinite(7810),
		invalidVrrpPrefixEntry(7811),
		vrrpPrefixExists(7812),
		ipv6InterfaceForwardingAlreadyEnabled(7856),
		ipv6InterfaceForwardingAlreadyDisabled(7857),
		ipfixStateAlreadyEnabled(8101),
		ipfixStateAlreadyDisabled(8102),
		ipfixInvalidSlotNumber(8103),
		ipfixNotADPMSlot(8104),
		ipfixInvalidActiveTimeout(8105),
		ipfixInvalidAgingInterval(8106),
		ipfixInvalidExportInterval(8107),
		ipfixInvalidTemplateRefIntervalSec(8108),
		ipfixInvalidTemplateRefIntervalPkts(8109),
		ipfixCollectorNotConfigured(8110),
		ipfixTwoCollectorAlreadyConfigured(8111),
		ipfixOnlyUdpProtocolSupported(8112),
		ipfixInvalidCollectorDestPort(8113),
		ipfixInvalidHashPolynomialCoeff(8114),
		ipfixInvalidHashPolynomialSeed(8115),
		ipfixInvalidHashKeyId(8116),
		ipfixInvalidSamplingRate(8117),
		aceIpfixStateIllegal(8118),
		tacacsIllegalIpAddress(8201),
		tacacsIllegalPriority(8202),
		tacacsMaxServersReached(8203),
		tacacsRadiusEnabled(8204),
		tacacsNoKeyGiven(8205),
		tacacsSourceIpDisabled(8207),
		tacacsServerNotConfigured(8209),
		tacacsPrimaryServerAlreadyExists(8210),
		tacacsBackupServerAlreadyExists(8211),
		tacacsPrimaryServerIsConfiguredWithTheSameIp(8212),
		tacacsBackupServerIsConfiguredWithTheSameIp(8213),
		isisPwdInvalid(8301),
		isisKeyIdInvalid(8302),
		isisPwdExists(8303),
		isisNoKeyId(8304),
		isisInvalidAuthType(8305),
		isisCsnpIntInvalid(8306),
		isisRxmtLspIntInvalid(8307),
		isisRtrTypeInvalid(8308),
		isisNetLenInvalid(8309),
		isisSysidError(8310),
		isisManAreaAddrToomany(8311),
		isisManAreaError(8312),
		isisNetEntryExists(8313),
		isisSummAddrExists(8314),
		isisSummAddrError(8315),
		isisInvalidSubnetMask(8316),
		isisEnabledOnInterface(8317),
		isisCannotChangeMetricTypeFromWideToNarrow(8318),
		isisInvalidCircType(8319),
		isisSysIdInvalid(8320),
		isisSysIdRuntimeChange(8321),
		isisInvalidCircuitId(8322),
		isisCircuitAlreadyExists(8323),
		isisCircuitDoesNotExist(8324),
		isisInvalidIntfIndex(8325),
		isisLevelRouterDoesNotSupp(8326),
		isisManAreaNotConfigured(8327),
		isisL2OnlyNotSupported(8328),
		isisPriorityOnlyForBcastType(8329),
		isisMetricValueInvalidForNarrowType(8330),
		isisL2onlyCircuitExists(8331),
		isisMinLspIntGreaterThanMaxLspInt(8332),
		isisMaxLspIntLessThanMinLspInt(8333),
		isisPlsbNodeNicknameInvalid(8334),
		isisPlsbInstanceAlreadyExists(8335),
		isisOnePlsbInstanceAllowed(8336),
		isisPlsbInstanceDoesNotExist(8337),
		isisCannotDeletePlsbInstanceWithIsid(8338),
		isisCannotDeletePlsbInstanceWithIsisInterface(8339),
		isisOneVlanPerPlsbInstance(8340),
		isisVlanDoesNotExist(8341),
		isisVlanIsNotPlsb(8342),
		isisInterfaceCannotConfigPlsb(8343),
		isisPlsbInstanceNotExistOnInterface(8344),
		isisPlsbInstancePt2ptOnly(8345),
		isisPlsbL1Only(8346),
		isisCannotDeleteVlanWithPlsb(8347),
		isisPlsbNniPortCannotBeAccess(8348),
		isisCannotEnableInterfaceWithoutPlsbInstance(8349),
		isisSystemIdIsnotBasemac(8350),
		isisPlsbInstanceNotConfigured(8351),
		isisNicknameNotConfiguredForPlsbInstance(8352),
		isisBvidNotConfiguredForPlsbInstance(8353),
		isisSpfDelayInvalid(8354),
		isisControlVlanDoesNotExist(8355),
		cannotAddPortToMltWithIsisInterfaceOnBothPortAndMlt(8356),
		cannotCreateIsisIntfOnPortWhichIsMemberOfMltWithIsisIntf(8357),
		cannotCreateIsisIntfOnMltWhichHasPortMemberWithIsisIntf(8358),
		isisSysidCannotBeMulticastAddress(8359),
		deleteIsisInterfaceBeforeDeleteMlt(8360),
		onlyFirst10PortOfLaneCanBeIsisInterface(8361),
		narrowMetricNotSupportedInPlsbMode(8362),
		isisCannotChangeSysIdDueToIsidEpIsEnable(8363),
		isisCannotChangeNickNameDueToIsidEpIsEnable(8364),
		isisCannotChangePlsbVlanDueToIsidEpIsEnable(8365),
		isisBcastNotSupportedOverMlt(8366),
		isisPortIsNotMemberOfPlsbVlan(8367),
		isisMltIsNotMemberOfPlsbVlan(8368),
		isisPlsbVlanDifferentFromDataVlan(8369),
		isisOverloadOnStartUpOutOfRange(8370),
		isisCannotChangeSysIdWhenNodalMepMipAssociatedToPlsbVlan(8371),
		enablePerformTaggingBefPlsbIsisInterfAssociation(8372),
		isisPlsbPrimaryVlanNotAdded(8373),
		isisPlsbPrimaryVlanNotMatch(8374),
		isisCannotUseMulticastAddress(8375),
		isisCannotEnableIpIsis(8376),
		isisPlsbPortConflictWithCvlan(8377),
		isisPlsbMLTConflictWithCvlan(8378),
		isisPlsbMLTISTConflictWithCvlan(8379),
		isisSpbmBvlanNotAllowToRunSlpp(8380),
		isisSpbmInvalidEtherType(8381),
		nsnaNoRedVlan(8401),
		nsnaRedVlanExists(8402),
		nsnaGlobalEnabled(8403),
		nsnaNoVlanColor(8404),
		nsnaVlanHasColor(8405),
		nsnaVlanNonEmpty(8406),
		nsnaNoFilterForNsnaVlan(8407),
		nsnaPortHasFilter(8408),
		nsnaNoUplinkDhcpFilter(8409),
		nsnaYellowSubnetNotSpecified(8410),
		nsnaNoNsnasSubnet(8411),
		nsnaMaxNsnasSubnet(8412),
		nsnaNoSshDaemon(8413),
		nsnaIncorrectGreenVlan(8414),
		nsnaIncorrectUplinkVlan(8415),
		nsnaIncorrectVoipVlan(8416),
		nsnaPortIsEap(8417),
		nsnaPortOperationNotAllowed(8418),
		nsnaUnknownMac(8419),
		nsnaExceedMaxNumEntry(8420),
		nsnaStaticEntryExists(8421),
		nsnaOperationNotAllowedOnMirroredPort(8422),
		nsnaInvalidHelloInact(8423),
		nsnaVlanFlushNotAllowed(8424),
		nsnaNoUplinkVlans(8425),
		nsnaVlanFilterRemapInProgress(8426),
		nsnaVlansCannotBeDeleted(8427),
		nsnaVlanCannotBeMadeGuestVlan(8428),
		nsnaPortCannotBeConfiguredOnNonPrPorts(8429),
		nsnaNotAllowedOnSmltPort(8431),
		cfmNoParamChange(8501),
		cfmDomainExists(8502),
		cfmDomainDoesNotExists(8503),
		cfmMaintenanceAssociationExists(8504),
		cfmMaintenanceAssociationDoesNotExists(8505),
		cfmChangeNotAllowedWhenEnabled(8506),
		cfmMepExists(8507),
		cfmMepDoesNotExists(8508),
		cfmOperationNotAllowedWhenMepsExist(8511),
		cfmMepInUse(8531),
		cfmMaDomainNameFieldCannotBeEmptyForCreation(8535),
		indexIsBeingUsedByOtherDomain(8536),
		cfmAssnIndexCantBeZeroForCreation(8537),
		indexIsBeingUsedByOtherMaAssn(8538),
		cfmOperationNotAllowedWhenMasExistUnderMd(8539),
		cfmDomainIndexCantBeZeroForCreation(8540),
		cfmAssnDoesNotExist(8541),
		cfmMepIdCannotBeNullForCreation(8542),
		cfmMaAssnNameFieldCannotBeEmptyForCreation(8543),
		pbtVlanCannotReassign(8552),
		cfmMepCanNotEnableWhenCfmEtherTypeIsNotSet(8554),
		invalidMepListInputFormat(8562),
		invalidDmOrMaNameLength(8563),
		mepIdMustBeANumber(8564),
		maxNumOfMepEntriesExceeded(8565),
		domainAlreadyAssociatedWithOtherTypeOfService(8567),
		cfmCannotDeleteBeforeRemoveAssociation(8574),
		cfmOperationNotAllowedWhenMipsExistUnderMd(8577),
		invalidMipListInputFormat(8582),
		invalidDmNameLength(8583),
		cannotDeleteVlanWithMepAssociation(8586),
		cfmLbmExceedMaxDataSizeLimit(8642),
		plsbVlanMustUsePlsbStg(8646),
		normalVlanCannotUsePlsbStg(8647),
		cfmPlsbCanHaveOnlyOneStg(8648),
		cfmInvalidName(8649),
		sameLevelMepAlreadyAssignedToVlanOnSamePort(8670),
		sameLevelMipAlreadyAssignedToVlanOnSamePort(8671),
		cfmNodalMepOnPbtVlanNotAllowed(8687),
		cfmCannotAddOrRemoveNodalMepsWhenMepListIsEmptyOrInvalid(8688),
		cfmExceedMinCcmIntervalForNodalVlan(8689),
		cfmMepAlreadyInUseWithOtherNodalVlan(8690),
		cfmMepAlreadyInUseWithOtherServiceType(8691),
		cfmNodalMipLevelOnPbtVlanNotAllowed(8692),
		cfmCannotAddOrRemoveNodalMipsWhenMipListIsEmptyOrInvalid(8693),
		cfmLbmCannotSpecifyBothDataAndFrameSize(8697),
		cfmFrameSizeTooLargeForRmod(8698),
		cfmFrameSizeTooLargeForRCmod(8699),
		cfmNoServiceAssociatedWithMepOrMip(8720),
		cfmMepNotReadyToSetLbm(8721),
		cfmMepNotOkToSetReady(8722),
		cfmMepNotReadyToSetLtm(8723),
		cfmLbmExceedMaxMessagesLimit(8726),
		cfmLbmTestPatternSizeError(8748),
		mepListCannotHaveTwoMepsWithSameMdLevel(8754),
		mipListCannotHaveTwoMipsWithSameMdLevel(8755),
		vrfDoesNotExist(8901),
		vrfAlreadyExists(8902),
		vrfMaxRoutesCouldNotBeSet(8903),
		vrfPortDoesNotBelongToSpecifiedVrf(8904),
		vrfVlanDoesNotBelongToSpecifiedVrf(8905),
		vrfLegacyPortCannotBeAddedToVlanAssociatedWithVrf(8906),
		vrfInvalidVrfId(8908),
		vrfOperationProhibitedForGrt(8909),
		vrfOspfLimitExceeded(8910),
		vrfRipLimitExceeded(8911),
		vrfDhcpLimitExceeded(8912),
		vrfVrrpLimitExceeded(8913),
		vrfRipDoesNotExist(8914),
		vrfOspfDoesNotExist(8915),
		vrfNameInvalid(8916),
		vrfNameDuplicate(8917),
		vrfRipAlreadyExists(8918),
		vrfOspfAlreadyExists(8919),
		vrfCannotChangeAssociationInterfaceExists(8907),
		vrfCannotAssociatePortInVlan(8920),
		vrfCannotAddAssociatedPortToVlan(8921),
		vrfCannotAssociateToVlanWithLegacyPorts(8922),
		vrfCannotAssociateToLegacyPortForBrouter(8923),
		vrfBgpDoesNotExist(8924),
		vrfBgpAlreadyExists(8925),
		vrfBgpLimitExceeded(8926),
		vrfConfigNeedsMezz(8927),
		invalidNextHopVrfName(8928),
		vrfOperationNotAllowed(8931),
		igapCannotBeEnabledOnNonGRTVlan(8934),
		igapAuthCannotBeEnabledOnNonGRTVlan(8935),
		igapAccntCannotBeEnabledOnNonGRTVlan(8936),
		igapIsNotEnabled(8937),
		vrfOperProhForMgmt(8938),
		ripSrcAndDstProtoCannotBeSameWithinOneVrf(8939),
		invalidOperation(9608),
		mplsRouterIdLdpRsvpEnabled(10001),
		mplsInvalidDeleteOperation(10002),
		mplsInvalidInterfaceState(10003),
		mplsInterfaceNotExist(10004),
		mplsInvalidInterfaceMtu(10005),
		mplsExplicitPathInUse(10006),
		mplsTunnelInUse(10007),
		mplsTunnelNoDest(10008),
		mplsTunnelResourceInUse(10009),
		mplsMezzCardAbsent(10010),
		mplsLdpNotReady(10011),
		mplsRsvpNotReady(10012),
		mplsRouterIdSetToZero(10013),
		mplsInterfaceVlanNotFound(10014),
		mplsPortNotRModule(10015),
		mplsIpAddrInUse(10016),
		mplsTunnelNotFound(10017),
		mplsTunnelNotAllLspUp(10018),
		mplsInvalidIndex(10019),
		mplsExplicitPathExists(10020),
		mplsExplicitPathHopExists(10021),
		mplsExplicitPathIndexExists(10022),
		mplsMaxIndex(10023),
		mplsInvalidPathOptionIndex(10024),
		mplsLspExists(10025),
		mplsInvalidLspInstance(10026),
		mplsLspNoName(10027),
		mplsLspNoEPName(10028),
		mplsLspEPNotFound(10029),
		mplsConfigNeedsMezz(10030),
		mplsExpPathIpv4AddrTypeOnly(10031),
		mplsExpPathNoNameChange(10032),
		mplsLspNoNameChange(10033),
		mplsSrcIpNonLocal(10034),
		mplsLspIndexUsed(10035),
		mplsLspNameUsed(10036),
		mplsLspNotActive(10037),
		mplsTunnelSameSrcDest(10038),
		mplsLspNotSameSrc(10039),
		mplsLspNotSameDest(10040),
		mplsTunnelNoALtPath(10041),
		mplsTunnelCfgIngressOnly(10042),
		mplsTunnelInvalidIndex(10043),
		mplsEPInvalidIndex(10044),
		mplsEPHopInvalidIndex(10045),
		mplsResInvalidIndex(10046),
		mplsInvalidLdpKeepAliveRange(10047),
		mplsInvalidLdpHelloHoldTimeRange(10048),
		ipvpnCreateFailed(10201),
		ipvpnDeleteFailed(10202),
		ipvpnAlreadyEnabled(10203),
		ipvpnNotEnabled(10204),
		ipvpnNotSupportedOnDefVRF(10205),
		ipvpnSameRDConf(10206),
		ipvpnInvRDConfOnDefVRF(10207),
		ipvpnInvRDTypeNotSupported(10208),
		ipvpnInvRTConfOnDefVRF(10209),
		ipvpnInvRTTypeNotSupported(10210),
		ipvpnSVCAllocFailed(10211),
		ipvpnSVCILMAddFailed(10212),
		ipvpnLiteSupportOnlyType1(10213),
		ipvpnRDTypeNotSupportedWithLite(10214),
		ipvpnSvcLblChngIfIpvpnDisabledInVRF(10215),
		ipvpnSvcLblOptionAlreadySetInIpvpnVRF(10216),
		ipvpnPeerRRLiteModeConflict(10217),
		ipvpnPeerGroupRRLiteModeConflict(10218),
		ipvpnImplicitReflectInMixedLiteMode(10219),
		ipvpnInvalidPeerSetForAccessPeer(10220),
		ipvpnRouterInNonLiteRRMode(10221),
		ipvpnRouteTargetNotFound(10222),
		bgpOperationNotAllowedWhenDefaultBgpIsEnabled(10223),
		bgpOperationNotAllowedWhenVrfBgpIsEnabled(10224),
		bgpInvalidLocalAsWhenVrfPeerRemoteAs(10225),
		bgpInvalidVrfPeerRemoteAs(10226),
		bgpInvalidVrfPeerGroupRemoteAs(10227),
		ipvpnLiteRequiresVpnv4(10228),
		ipvpnVpnv4DisableRequiresLiteDisable(10229),
		ipvpnEnabledWithoutLocalAs(10230),
		ipvpnInterVrfRedistEnable(10231),
		bgpOperationNotAllowedWhenIpvpnIsEnabled(10232),
		ipvpnInvalidAssignedNumber(10233),
		ipvpnInvalidAsNumber(10234),
		ipvpnInvalidPeerSetForExternalPeer(10235),
		ipvpnInvalidPeerGroupSetForExternalPeer(10236),
		ipvpnMaxRtPerVrfExceeded(10237),
		ipvpnRdOverlapOperNotAllowed(10238),
		ipvpnNotCreated(10239),
		ipvpnAlreadyCreated(10240),
		ipvpnLiteRequiresValidIpAddressInRd(10241),
		ipvpnLiteOperationNotAllowedSameIpConfiguredAsRdInAnotherVrf(10242),
		ipvpnRDInvalidCircuitlessIP(10243),
		ipvpnRDIpNotLiteEnabled(10244),
		ipvpnLiteSupportRDWithClipIp(10245),
		ipvpnLiteSupportOnlyLiteEnabledRDIP(10246),
		ipvpnEnableDisallowedWithoutValidRD(10247),
		ipvpnLiteRDIpConfiguredInMultipleVrf(10248),
		ipvpnIsidAlreadyExist(10249),
		ipvpnBgpBasedOrTaggedPeerNotConfigured(10250),
		ipvpnBothTypeOfIpvpnCreated(10251),
		ipvpnBgpBasedAlreadyCreated(10252),
		ipvpnTaggedPeerAlreadyCreated(10253),
		ipvpnTaggedPeerIsidNotConfigured(10254),
		ipvpnTaggedPeerIsidRuntimeChangeNotAllowed(10255),
		customAutoNegAdvMacPauseNotSupported(10301),
		customAutoNegAdvAsymPauseNotSupported(10302),
		mirrorDestinationNotEntered(10306),
		mirrorLegacyCannotSupportPortList(10307),
		mirrorMltShouldHavePortsAssigned(10308),
		mirrorDestinationNotAttached(10309),
		mirrorDisableEntry(10310),
		mirrorDestinationAlreadyAttached(10311),
		mirrorLegacyCannotSupportVlanOrMlt(10313),
		mirrorDestAlreadyAttachedOrDestSpecifiedNotAttached(10314),
		noAdminSettingForSpeed1000(10330),
		portAlwaysRunAt10GSpeed(10331),
		rmodOnlyOneMirroredPortPerLaneForEgress(10332),
		mirrorTxFilterModeNotAllowedOnRsmod(10333),
		mirrorModeNotValidForRmodRSmod(10334),
		cannotSetAdminSpeed1000AsPerIEEE(10338),
		portMirroringNoMgidsAvailable(10363),
		loopDetectNotAllowedOnIstPorts(10364),
		loopDetectNotAllowedAlreadyEnabled(10365),
		portPcapModeNotSupported(10366),
		svcRateNeedsToBeSetToZeroWhenPeakIsSetToZero(10367),
		peakRateNeedsToBeSetToZeroWhenSvcRateIsSetToZero(10368),
		portCpLimitShutdownOnIstPortNotAllowed(10369),
		portOnly10GEPortsCanBeLossless(10374),
		portIsConfiguredAsLossless(10375),
		portIsConfiguredAsLosslessPfc(10376),
		portIsL2Untrusted(10377),
		portIsConfiguredAsIfPolicer(10378),
		portLaneHasLosslessPort(10379),
		portSliceHasLosslessPort(10380),
		portAllMltPortsCannotBeMadeLossless(10381),
		portConfigNotAllowedLacpKeyInMltIdRange(10383),
		rmVlanIdNotSetForRMSPort(10384),
		rmVlanListNotAllowedForRMS(10385),
		slppTimeToClrPktRxCountNotConfigurable(10386),
		portCannotBeConfiguredAsLosslessPfc(10387),
		portMltListViolatesLosslessLaneLimit(10388),
		portQosInvalidForLosslessPfc(10389),
		portL3TrustedInvalidForLossless(10390),
		portL2UntrustedInvalidForLossless(10391),
		portNoLosslessChangeIfLacpEnabled(10392),
		portMltOnly10GEPortsCanBeLossless(10393),
		portAddOnly10GEPortsCanBeLossless(10394),
		portMltIsConfiguredAsIfPolicer(10395),
		portAddIsConfiguredAsIfPolicer(10396),
		cfmCannotAbortWhenNoLtmInProgress(10442),
		esmMltCannotBeNonUni(10443),
		cfmCannotAbortWhenNoLbmInProgress(10446),
		plsbVlanIsidNotAllowed(10459),
		plsbVlanIsidAlreadyExist(10460),
		plsbVlanIsidWithSingleBvlan(10461),
		plsbSysidCannotBeSameAsIstPeerSysid(10462),
		bgpInvalidPeerSetWhenVpnv4Enabled(10501),
		bgpInvalidPeerGroupSetWhenVpnv4Enabled(10502),
		bgpOverlappingAggregateAddress(10503),
		bgpInvalidLocalAsWhenPeerRemovePrivateAsEnabled(10504),
		bgpInvalidPeerRemovePrivateAsEnableWithoutRemoteAs(10505),
		bgpInvalidPeerGroupRemovePrivateAsEnableWithoutRemoteAs(10506),
		bgpDuplicatePeerNotAllowed(10507),
		bgpPeerDoesNotBelongToPeerGroup(10508),
		bgpOperationNotAllowedWhenRouteReflectorClientIsEnabled(10509),
		bgpInvalidAggregateAdvertisePolicyWithoutAsSetGenerate(10510),
		bgpInvalidPeerDefaultOriginateIpv6(10512),
		bgpInvalidPeerGroupDefaultOriginateIpv6(10513),
		bgpInvalidPeerIpv6Capability(10514),
		bgpOperationNotAllowedForIpv6Peer(10515),
		bgpOperationNotAllowedForIpv6PeerGroup(10516),
		bgpOperationNotAllowedWhenOutboundMapsAreDifferent(10517),
		bgpOperationNotAllowedWhenInboundMapsAreDifferent(10518),
		maxPeerEntriesInPeerGroup(10519),
		bgpOperationNotAllowedWhenNexthopSelfAreDifferent(10520),
		bgpOperationNotAllowedWhenUpdateSourceAreDifferent(10521),
		bgpOperationNotAllowedWhenRemovePrivateAsAreDifferent(10522),
		plsbDeleteIntfBeforeSetPlsbFlag(10701),
		plsbDeletePlsbInstanceBeforeSetPlsbFlag(10702),
		plsbDeleteManualAreaBeforeSetPlsbFlag(10703),
		plsbDeleteSummaryAddrBeforeSetPlsbFlag(10704),
		plsbDisableIsisBeforeSetPlsbFlag(10705),
		plsbDeletePlsbVlanBeforeSetPlsbFlag(10706),
		plsbCannotConfigPlsbInNonplsbMode(10707),
		commandValidOnlyIfInRmode(10708),
		cannotAssociateMoreThan5000IsidToPlsbInstance(10709),
		cannotEnablePlsbWithMmrpConfiguration(10711),
		cannotHaveSameBvlanAsSpIpVlanRCModPort(10712),
		cannotAddRcModPortsToMltWhenSpIpVlanSameAsBvlan(10713),
		cannotConfigPlsbIsisSmltistIntfOnSameIntf(10714),
		plsbDisableAllIsisEndpointsBeforeTogglePlsbState(10715),
		cannotConfigPortInSmltOrIstForPlsbVlan(10716),
		deleteStg63BeforeCreatingPlsbBvlan(10717),
		only2PlsbBvlanSupported(10718),
		plsbInvalidIpSourceAddress(10719),
		plsbMustChangeNicknameAfterChangeSysid(10720),
		plsbWhenEnableIstMustConfigSmltPeerBmac(10721),
		cannotConfigPlsbIsisIntfOnSmlt(10722),
		cannotConfigPlsbIsisIntfOnIstPort(10723),
		plsbZeroSmltPeerBmacMustHaveZeroVirtualBmac(10724),
		plsbZeroSmltPeerBmacMustHavePrimSplitBeb(10725),
		plsbWhenSetVirtualBmacToZeroPeerBmacMustBeZero(10726),
		plsbDeleteIsidFromVlanBeforeSetPlsbFlag(10727),
		plsbIsidNotAllowedForVlanSpbmDisabled(10728),
		plsb16777215IsWellKnownIsid(10729),
		plsbConfigIpSourceAddrBeforeEnableIpSc(10730),
		inUsedAsIsisIpSourceAddr(10731),
		plsbCannotSetIpSourceAddrToZeroWhenIpScEnabled(10732),
		spbmIntfCanBeConfiguredOn10gigPort(10740),
		spbmIntfCanBeConfiguredOnMltWith10gigPort(10741),
		spbmMltMemberAlreadyInSpbmBvlan(10748),
		dhcpSameServerAgentAddress(11226),
		dhcpDiffAgentAddress(11227),
		cfmLbmFrameTooSmall(11401),
		cfmLbmExceedsChassisMtu(11402),
		cfmLbmExceedsUniPortMtu(11403),
		cfmNodalMepIsNotSupportedOnESM(11408),
		cfmNodalMipLevelIsNotSupportedOnESM(11409),
		cfmLbmFrameSizeExceedMaxForNodalMep(11414),
		cannotDeleteVlanWithNodalMipLevelAssociation(11416),
		sameLevelNodalMepAlreadyAssignedToVlan(11417),
		cfmMulticastCcmOnNodalPlsbMepNotAllowed(11422),
		cfmNodalMepOnlyOnPlsbVlan(11424),
		cfmNodalMipOnlyOnPlsbVlan(11425),
		cfmNodalMpOnlyOnePerVlan(11426),
		cfmCannotL2PingWhenLbmInProgress(11427),
		cfmCannotLBMWhenL2PingInProgress(11428),
		cfmCannotAbortWhenNoL2PingInProgress(11429),
		cfmL2PingMepNotOkToSetReady(11430),
		cfmVlanNotReadyToSetL2Ping(11431),
		cfmL2PingExceedMaxMessagesLimit(11432),
		cfmL2PingExceedMaxDataSizeLimit(11433),
		cfmL2PingTestPatternSizeError(11434),
		cfmL2PingFrameTooSmall(11435),
		cfmL2PingFrameSizeExceedMaxForNodalMep(11436),
		cfmCannotLTMWhenL2TraceInProgress(11437),
		cfmCannotL2TraceWhenLTMInProgress(11438),
		cfmCannotAbortWhenNoL2TraceInProgress(11439),
		cfmL2TraceMepNotOkToSetReady(11440),
		cfmVlanNotReadyToSetL2Trace(11441),
		cfmL2CmdVlanNotFound(11442),
		cfmL2TraceInvalidIsid(11443),
		cfmNodalMipOnlyOnePerVlan(11447),
		cfmNodalMepOnlyOnePerVlan(11448),
		cfmMepMustBeEnabledForCmd(11449),
		cfmSpbmVirtualNotSet(11450),
		cfmSpbmVirtualNotPrimary(11451),
		cfmL2IpPingIsNotOkToSetReady(11452),
		cfmNotReadyToSetL2IpPing(11453),
		cfmNotMemoryAllocatedForL2(11454),
		cfmL2IpTraceIsNotOkToSetReady(11455),
		cfmNotReadyToSetL2IpTrace(11456),
		cfmIpLookupRouteFailed(11457),
		invalidIpAddrType(11458),
		cfmL2IpPingEntryMustCreatedFirst(11459),
		cfmL2IpTraceEntryMustCreatedFirst(11460),
		cfmCannotAbortWhenNoL2IpPingInProgress(11464),
		cfmCannotSetTtlTo0(11465),
		qosMapExists(12501),
		qosMapNotExist(12502),
		qosMapDeleteUsedByFilter(12503),
		qosMapDeleteDefaultMap(12504),
		qosInvalidTagToQosTableQosLevel(12505),
		qosInvalidDsFieldToQosTableQosLevel(12506),
		qosInvalidQosToTagTableQosLevel(12507),
		qosInvalidQosLevelValue(12508),
		qosMapInvalidForLosslessPfc(12509),
		qosMapPortQosInvalidForLosslessPfc(12510),
		standbyIpSubnetNotSameAsMaster(12601),
		standbyIpSubnetNotSameAsVirtual(12602),
		standbyIpSameAsVirtual(12603),
		masterIpSubnetNotSameAsStandby(12604),
		masterIpSubnetNotSameAsVirtual(12605),
		masterIpSameAsVirtual(12606),
		cannotReadConfigSourceFile(12607),
		cannotWriteConfigSourceFile(12608),
		configFileInvalidPrefix(12609),
		cpuSerialPortCommandNotAllowedOnSlave(12610),
		ipv6InvalidInvalidIpv6AddrInterfaceId(12701),
		ipv6ReasmMaxSizeExceedSysMtu(12702),
		ipv6InvalidDescriptionLength(12703),
		ipv6InvalidReasmSizeForMgmtPort(12704),
		ipv6AddrCreatedByVirtualManagment(12705),
		ipv6RsmltTempDefRtDeleteModify(12706),
		ipv6OspfAreaCannotModifyAreaType(12707),
		ipv6OspfAreaSetToNssaForTransRole(12708),
		ipv6OspfAreaHasActiveInterface(12709),
		ipv6InterfaceMacOffsetCannotReset(12710),
		ipv6InterfaceMacOffsetDiffSameVlan(12711),
		ipv6InterfaceCannotModifyTunnelEntry(12712),
		unsupportedVlanId(12801),
		invalidVlanIdError(12802),
		vlanAdminStatusConfigNotAllowed(12803),
		configNotAllowedOnVlanInterfaces(12804),
		macSrcMacVlanReached(12805),
		vlanCannotBeDeletedDueToEapAuthorizedPortMember(12806),
		cfmCannotDeleteVlanWithCfmMsgInProgress(12821),
		cfmCannotChangeMepWithCfmMsgInProgress(12822),
		cfmInvalidNodalMipLevel(12825),
		aceIpDscpInvalidSetting(12901),
		aceIpDscpEntryCreationRequiresOperationAndDscpSetting(12902),
		aceEthPortEntryCreationRequiresOperAndPort(12903),
		aceEthTypeEntryCreationRequiresOperAndEtherType(12904),
		aceEtherType8100NotAllowed(12905),
		filterEntryWithMonitorIpInSameSubnetExists(12906),
		vspTalkIpInterfaceNotFound(13201),
		vspTalkDnsNotConfigured(13202),
		vspTalkInvalidMessageGroup(13203),
		vspTalkNotEnabled(13204),
		vspTalkMessageGroupNotExist(13205),
		vspTalkMessageGroupAlreadyEnabled(13206),
		vspTalkUsernameRequiredForPassword(13207),
		vspTalkMessageGroupAlreadyExists(13208),
		readWriteAccessReadOnly(900),
		readWriteAccessLevelOne(901),
		readWriteAccessLevelTwo(902),
		readWriteAccessLevelThree(903),
		readWriteAccessReadWrite(904),
		readWriteAccessReadWriteAll(905),
		readWriteAccessUnknownLevel(906)

	}
	MAX-ACCESS read-only
	STATUS current
	DESCRIPTION "This variable is used primarily as an enumeration
		      to list the proprietary return codes that this
		      device can send to a management station in
		      response to a failed SNMP operation."
	DEFVAL { none }
	::= { rcError 4 }
	
-- *** ABOVE SECTION IS GENERATED FROM ../mib_tools/error.mib ***

rcErrorSendTrap OBJECT-TYPE
        SYNTAX        TruthValue
        MAX-ACCESS    read-write
        STATUS        current
        DESCRIPTION   "Indicates whether to send trap upon receiving an
                      error in the system."
	DEFVAL	      { true }
        ::= { rcError 5 }

-- TRAPS

rcTrapsMib OBJECT IDENTIFIER ::= { rcTraps 0 }

rcnCardDown NOTIFICATION-TYPE
        OBJECTS      { rcCardIndex, rcCardAdminStatus, rcCardOperStatus }
        STATUS       current
        DESCRIPTION  "A rcnCardDown trap signifies that the SNMPv2 entity,
                     acting in an agent role, has detected that the
                     rcCardOperStatus object for one of its cards
                     is about to transition into the down state."
        ::= { rcTrapsMib 1 }

rcnCardUp NOTIFICATION-TYPE
        OBJECTS       { rcCardIndex, rcCardAdminStatus, rcCardOperStatus }
        STATUS        current
        DESCRIPTION   "A rcnCardUp trap signifies that the SNMPv2 entity,
                      acting in an agent role, has detected that the
                      rcCardOperStatus object for one of its cards
                      is about to transition into the up state."
        ::= { rcTrapsMib 2 }
 
rcnErrorNotification NOTIFICATION-TYPE
        OBJECTS       { rcErrorLevel, rcErrorCode, rcErrorText }
        STATUS        current
        DESCRIPTION   "A rcnErrorNotification trap signifies that the
                      SNMPv2 entity, acting in an agent role, has
                      detected that an error condition has occured."
        ::= { rcTrapsMib 3 }

rcnStpNewRoot NOTIFICATION-TYPE
        OBJECTS       { rcStgId }
        STATUS        current
        DESCRIPTION   "A rcnStpNewRoot trap signifies that the
                      SNMPv2 entity, acting in an agent role, has
                      detected the Spanning Tree Protocol has declared
                      the device to be the new root of the spanning
                      tree."
        ::= { rcTrapsMib 4 }

rcnStpTopologyChange NOTIFICATION-TYPE
       OBJECTS        { rcStgId, rcPortIndex }
       STATUS         current
       DESCRIPTION    "A rcnStpTopologyChange trap signifies that the
                      SNMPv2 entity, acting in an agent role, has
                      detected the Spanning Tree Protocol has gone due
                      a topology change event."
       ::= { rcTrapsMib 5 }

rcnChasPowerSupplyDown NOTIFICATION-TYPE
        OBJECTS       { rcChasPowerSupplyId, rcChasPowerSupplyOperStatus}
        STATUS        current
        DESCRIPTION   "A rcnChasPowerSupplyDown trap signifies that the
                      SNMPv2 entity, acting in an agent role, has
                      detected that the rcChasPowerSupplyOperStatus
                      object for one of its power supply unit is
                      about to transition into the down state."
        ::= { rcTrapsMib 6 }

rcnChasFanDown NOTIFICATION-TYPE
        OBJECTS       { rcChasFanId, rcChasFanOperStatus}
        STATUS        current
        DESCRIPTION   "A rcnChasFanDown trap signifies that the
                      SNMPv2 entity, acting in an agent role, has
                      detected that the rcChasFanOperStatus object
                      for one of its power supply unit is about to
                      transition into the down state."
        ::= { rcTrapsMib 7 }

rcnLinkOscillation NOTIFICATION-TYPE
        OBJECTS          { rcPortIndex }
        STATUS             current
        DESCRIPTION   "A rcnLinkOscillation trap signifies that the
                       SNMPv2 entity, acting in an agent role, has
                       detected an excessive number of link state
                       transitions on the specified port."
        ::= { rcTrapsMib 8 }

rcnMacViolation NOTIFICATION-TYPE
        OBJECTS       { rcErrorText, rcPortIndex }
        STATUS        current
        DESCRIPTION   "A rcnMacViolation trap signifies that the
                      SNMPv2 entity, acting in an agent role, has
                      received a PDU with an invalid source MAC
                      address."
        ::= { rcTrapsMib 9 }

rcnSonetTrap NOTIFICATION-TYPE
        OBJECTS       { rcPortIndex, rcPosSonetTrapType, rcPosSonetTrapIndication }
        STATUS        current
        DESCRIPTION   "A rcnSonetTrap trap signifies that the
                      SNMPv2 entity, acting in an agent role, has
                      detected a change of status on a Sonet port."
        ::= { rcTrapsMib 10 }

rcn2kCardDown NOTIFICATION-TYPE
        OBJECTS      { rc2kCardIndex,
                       rc2kCardFrontAdminStatus,
                       rc2kCardFrontOperStatus }
        STATUS       current
        DESCRIPTION  "A rcnCardDown trap signifies that the SNMPv2 entity,
                     acting in an agent role, has detected that the
                     rcCardOperStatus object for one of its cards
                     is about to transition into the down state."
        ::= { rcTrapsMib 11 }
 
rcn2kCardUp NOTIFICATION-TYPE
        OBJECTS       { rc2kCardIndex,
                        rc2kCardFrontAdminStatus,
                        rc2kCardFrontOperStatus }
        STATUS        current
        DESCRIPTION   "A rcnCardUp trap signifies that the SNMPv2 entity,
                      acting in an agent role, has detected that the
                      rcCardOperStatus object for one of its cards
                      is about to transition into the up state."
        ::= { rcTrapsMib 12 }

rcn2kTemperature NOTIFICATION-TYPE
        OBJECTS       { rc2kChassisTemperature }
        STATUS        current
        DESCRIPTION   "A rcn2kTemperature trap signifies that the SNMPv2
                      entity, acting in an agent role, has detected the
                      chassis is over-heating."
        ::= { rcTrapsMib 13 }

rcnChasPowerSupplyUp NOTIFICATION-TYPE
        OBJECTS       { rcChasPowerSupplyId, rcChasPowerSupplyOperStatus}
        STATUS        current
        DESCRIPTION   "A rcnChasPowerSupplyUp trap signifies that the
                      SNMPv2 entity, acting in an agent role, has
                      detected that the rcChasPowerSupplyOperStatus
                      object for one of its power supply unit is
                      about to transition into the up state."
        ::= { rcTrapsMib 14 }

rcn2kAtmPvcLinkStateChange NOTIFICATION-TYPE
        OBJECTS       { rc2kAtmPvcIfIndex,
                        rc2kAtmPvcVpi,
                        rc2kAtmPvcVci,
                        rc2kAtmPvcOamVcStatus }
        STATUS        current
        DESCRIPTION   "A rcn2kAtmPvcLinkStateChange trap signifies that the
                       SNMPv2 entity, acting in an agent role, has detected
                       that the rc2kAtmPvcOamVcStatus object for one of PVC is
                       about to transition into different state, either from
                       up to down or from down to up."
        ::= { rcTrapsMib 15 }

rcnStpTCN NOTIFICATION-TYPE
       OBJECTS        { rcStgId, rcPortIndex, rcStgBridgeAddress }
       STATUS         current
       DESCRIPTION    "A rcnStpTopologyChange trap signifies that the
                      SNMPv2 entity, acting in an agent role, has
                      detected the Spanning Tree Protocol has gone due
                      a topology change event."
       ::= { rcTrapsMib 16 }

rcnSmltIstLinkUp NOTIFICATION-TYPE
        STATUS        current
        DESCRIPTION   "A rcnSmltIstLinkUp trap signifies that the split
                      MLT link is from down to up."
        ::= { rcTrapsMib 17 }

rcnSmltIstLinkDown NOTIFICATION-TYPE
        STATUS        current
        DESCRIPTION   "A rcnSmltIstLinkDown trap signifies that the
                      split MLT link is from up to down."
        ::= { rcTrapsMib 18 }

rcnSmltLinkUp NOTIFICATION-TYPE
        OBJECTS       { rcMltSmltId }
        STATUS        current
        DESCRIPTION   "A rcnMltSmltId trap signifies that the split
                      SMLT link is up."
        ::= { rcTrapsMib 19 }

rcnSmltLinkDown NOTIFICATION-TYPE
        OBJECTS       { rcMltSmltId }
        STATUS        current
        DESCRIPTION   "A rcMltSmltId trap signifies that the split
                      SMLT link is down."
        ::= { rcTrapsMib 20 }


rcnChasFanUp NOTIFICATION-TYPE
        OBJECTS       { rcChasFanId, rcChasFanOperStatus}
        STATUS        current
        DESCRIPTION   "A rcnChasFanUp trap signifies that the
                      SNMPv2 entity, acting in an agent role, has
                      detected that the rcChasFanOperStatus object
                      for one of its power supply unit is about to
                      transition into the up state."
        ::= { rcTrapsMib 21 }

rcnPasswordChange NOTIFICATION-TYPE
        OBJECTS       { rcCliPasswordChange, rcCliPassChangeResult}
        STATUS        current
        DESCRIPTION   "A rcnPasswordChange trap signifies that the
                      SNMPv2 entity, acting in an agent role, has
                      detected that the one of the cli password is
                      changed."
        ::= { rcTrapsMib 22 }

rcnEmError NOTIFICATION-TYPE
        OBJECTS       { rc2kCardIndex, rcChasEmModeError}
        STATUS        current
        DESCRIPTION   "A rcnEmError trap signifies that the
                      SNMPv2 entity, acting in an agent role, has
                      detected Em error."
        ::= { rcTrapsMib 23 }

-- OM 2.0 place holder
-- rcVpnTrap NOTIFICATION-TYPE
--         OBJECTS       { rcVpnVpnId, rcErrorText, rcVpnTunnelLspId,
--                         rcIpMplsGlobalRouterId, rcVpnRemotePeerId, 
--                         rcSyslogHostSeverity}    
--         STATUS        obsolete
--         DESCRIPTION   "L2Vpn will send trap when the Lsp goes down, which
--                        would affect the operational status of the Vpn (given
--                        by the VpnId). The Cause will indicate the reason for
--                        sending the trap. It can either LSP down/failure or
--                        to the bandwidth requirements cannot be fulfilled.
--                        Severity Level can be Warning/Error/Fatal."
--         ::= { rcTraps 24 }
--         
-- rcnVpnTrap NOTIFICATION-TYPE
--         OBJECTS       { rcVpnVpnId, rcErrorText, rcVpnTunnelLspId,
--                         rcIpMplsGlobalRouterId, rcVpnRemotePeerId,
--                         rcSyslogHostSeverity}
--         STATUS        current
--         DESCRIPTION   "L2Vpn will send trap when the Lsp goes down, which
--                        would affect the operational status of the Vpn (given
--                        by the VpnId). The Cause will indicate the reason for
--                        sending the trap. It can either LSP down/failure or
--                        to the bandwidth requirements cannot be fulfilled.
--                        Severity Level can be Warning/Error/Fatal."
--         ::= { rcTrapsMib 24 }
--     

rcnPcmciaCardRemoved NOTIFICATION-TYPE
        STATUS        current
        DESCRIPTION   "A rcnPcmciaRemoved trap signifies that the
                      SNMPv2 entity, acting in an agent role, has
                      detected that the PCMCIA card is being removed."
        ::= { rcTrapsMib 25 }

rcnSmartCpldTimerFired NOTIFICATION-TYPE
        OBJECTS       { rc2kCardIndex }
        STATUS        current
        DESCRIPTION   "A rcnSmartCpldTimerFired trap signifies that the
                       cpld timer fired."
        ::= { rcTrapsMib 26 }

rcnCardCpldNotUpDate NOTIFICATION-TYPE
        OBJECTS       { rc2kCardIndex }
        STATUS        current
        DESCRIPTION   "A rcnCardCpldNotUpDate trap signifies that the
                       cpld is not up to date."
        ::= { rcTrapsMib 27 }

rcnIgapLogFileFull NOTIFICATION-TYPE
        STATUS        current
        DESCRIPTION   "A rcnIgapLogFileFull trap signifies that the
                       Igap accounting time-out Log File reach the
                       maximum."
        ::= { rcTrapsMib 28 }

rcnCpLimitShutDown NOTIFICATION-TYPE
        OBJECTS       { rcPortIndex,
                        ifAdminStatus,
                        ifOperStatus,
                        rcPortCpLimitShutDown }
        STATUS        current
        DESCRIPTION   "A rcnCpLimitShutDown trap signifies that the
                       cp limit for the port is shutting down."
        ::= { rcTrapsMib 29 }

rcnSshServerEnabled NOTIFICATION-TYPE
        OBJECTS       { rcSshGlobalPort }
        STATUS        current
        DESCRIPTION   "A rcnSshServerEnabled trap signifies that the
                       SSH server is enabled."
        ::= { rcTrapsMib 30 }

rcnSshServerDisabled NOTIFICATION-TYPE
        OBJECTS       { rcSshGlobalPort }
        STATUS        current
        DESCRIPTION   "A rcnSshServerDisabled trap signifies that the
                       SSH server is disabled."
        ::= { rcTrapsMib 31 }

rcnSshSessionLogin NOTIFICATION-TYPE
        OBJECTS       { rcSshGlobalHostIpAddr }
        STATUS        deprecated
        DESCRIPTION   "A rcnSshSessionLogin trap signifies that there
                       is a SSH session login.
		       It's deprecated by rcnaSshSessionLogin."
        ::= { rcTrapsMib 32 }

rcnSshSessionLogout NOTIFICATION-TYPE
        OBJECTS       { rcSshGlobalHostIpAddr }
        STATUS        deprecated
        DESCRIPTION   "A rcnSshSessionLogout trap signifies that there
                       is a SSH session logout.
		       It's deprecated by rcnaSshSessionLogout."
        ::= { rcTrapsMib 33 }

rcnSshUnauthorizedAccess NOTIFICATION-TYPE
        OBJECTS       { rcSshGlobalHostIpAddr }
        STATUS        deprecated
        DESCRIPTION   "A rcnSshUnauthorizedAccess trap signifies that
                       an unauthorized access has occured.
		       It's deprecated by rcnaSshUnauthorizedAccess."
        ::= { rcTrapsMib 34 }

rcnHaCpuState NOTIFICATION-TYPE
        OBJECTS       { rc2kCardIndex, rcL2RedundancyHaCpuState }
        STATUS        current
        DESCRIPTION   "A rcnHaCpuState trap signifies that the
                       state of the HA-CPU."
        ::= { rcTrapsMib 35 }

rcnInsufficientMemory NOTIFICATION-TYPE
        OBJECTS       { rc2kCardIndex }
        STATUS        current
        DESCRIPTION   "A rcnInsufficientMemory trap indicates insufficient memory on
                       CPU blade for proper operation. Recommended memory = 256 MB
                       available through Nortel Networks upgrade kit"
        ::= { rcTrapsMib 36 }

-- This is obsolete. Use rcnSaveConfigFile (rcTrapsMib 61)
rcnSaveConfigAction NOTIFICATION-TYPE
        OBJECTS       { rcSysActionL1 }
        STATUS        current
        DESCRIPTION   "A rcnSaveConfigAction trap indicates the switch run
                       time or boot configuration is being saved"
        ::= { rcTrapsMib 37 }

rcnLoopDetectOnPort NOTIFICATION-TYPE
        OBJECTS       { rcVlanId, rcPortIndex }
        STATUS        current
        DESCRIPTION   "A rcnLoopDetectOnPort trap indicates that a loop has
                       been detected on a port. The vlan on that port will
                       be disabled."
        ::= { rcTrapsMib 38 }

rcnbgpEstablished NOTIFICATION-TYPE
        OBJECTS { rcIpBgpPeerIpAddress,
                  rcIpBgpPeerLastError,
                  rcIpBgpPeerState      }
        STATUS  current
        DESCRIPTION
                "The BGP Established event is generated when
                 the BGP FSM enters the ESTABLISHED state."
        ::= { rcTrapsMib 39 }

rcnbgpBackwardTransition NOTIFICATION-TYPE
        OBJECTS { rcIpBgpPeerIpAddress,
                  rcIpBgpPeerLastError,
                  rcIpBgpPeerState      }
        STATUS  current
        DESCRIPTION
                "The BGPBackwardTransition Event is generated
                 when the BGP FSM moves from a higher numbered
                 state to a lower numbered state."
        ::= { rcTrapsMib 40 }

rcnAggLinkUp NOTIFICATION-TYPE
        OBJECTS       { rcMltId }
        STATUS        current
        DESCRIPTION   "A rcnAggLinkUp trap is generated when the operational
                       state of the aggregator changes from down to up."
        ::= { rcTrapsMib 41 }

rcnAggLinkDown NOTIFICATION-TYPE
        OBJECTS       { rcMltId }
        STATUS        current
        DESCRIPTION   "A rcnAggLinkDown trap is generated when the operational
                       state of the aggregator changes from up to down."
        ::= { rcTrapsMib 42 }

rcnIgmpNewGroupMember NOTIFICATION-TYPE
        OBJECTS       { rcIgmpGroupIfIndex,
                        rcIgmpGroupIpAddress,
                        rcIgmpGroupInPort,
                        rcIgmpGroupMembers }
        STATUS        current
        DESCRIPTION   "An IgmpNewGroupMember  trap signifies that a
                       new member has come on an interface."
        ::= { rcTrapsMib 43 }

rcnIgmpLossGroupMember NOTIFICATION-TYPE
        OBJECTS       { rcIgmpGroupMembers,
                        rcIgmpGroupIpAddress,
                        rcIgmpGroupInPort,
                        rcIgmpGroupIfIndex }
        STATUS        current
        DESCRIPTION   "An IgmpLossGroupMember  trap signifies that a
                       group member has been lost on an interface."
        ::= { rcTrapsMib 44 }

rcnIgmpNewQuerier NOTIFICATION-TYPE
        OBJECTS       { igmpInterfaceIfIndex,
                        igmpInterfaceQuerier }
        STATUS        current
        DESCRIPTION   "An igmpNewQuerier trap signifies that a new
                       querier has come up on an interface."
        ::= { rcTrapsMib 45 }

rcnIgmpQuerierChange NOTIFICATION-TYPE
        OBJECTS       { igmpInterfaceIfIndex,
                        rcIgmpInterfaceExtnNewQuerier,
                        igmpInterfaceQuerier }
        STATUS        current
        DESCRIPTION   "An rcnIgmpQuerierChange trap signifies that
                       the querier has changed."
        ::= { rcTrapsMib 46 }

rcnDvmrpIfStateChange NOTIFICATION-TYPE
        OBJECTS       { dvmrpInterfaceIfIndex,
                        dvmrpInterfaceOperState }
        STATUS        current
        DESCRIPTION   "A rcnDvmrpIfStateChange trap signifies that there
                       has been a change in the state of a DVMRP
                       interface."
        ::= { rcTrapsMib 47 }

rcnDvmrpNewNbrChange NOTIFICATION-TYPE
        OBJECTS       { dvmrpNeighborIfIndex,
                        dvmrpNeighborAddress }
        STATUS        current
        DESCRIPTION   "A rcnDvmrpNewNbrChange trap signifies that a new
                       neighbor has come up on a DVMRP interface."
        ::= { rcTrapsMib 48 }

rcnDvmrpNbrLossChange NOTIFICATION-TYPE
        OBJECTS       { dvmrpNeighborIfIndex,
                        dvmrpNeighborAddress }
        STATUS        current
        DESCRIPTION   "A rcnDvmrpNbrLossChange trap signifies that a new
                       neighbor has gone down on a DVMRP interface."
        ::= { rcTrapsMib 49 }

rcnFdbProtectViolation NOTIFICATION-TYPE
        OBJECTS { rcPortIndex,
                  rcVlanId }
        STATUS  current
        DESCRIPTION
                "The rcnFdbProtectViolation trap signifies that the 
                 has violated the user configured limit for total
                 number of fdb-entries learned on that port."
        ::= { rcTrapsMib 59 }


rcnLogMsgControl NOTIFICATION-TYPE
        OBJECTS { rcSysMsgLogFrequency, rcSysMsgLogText }

        STATUS  current
        DESCRIPTION
                "A rcnLogMsgControl trap signifies whether the number of times of
                 repeatation of the particular Log message has exceeded
                 the particular frequency/count or not."
        ::= { rcTrapsMib 60 }


-- New trap for save config. Q00826011
rcnSaveConfigFile       NOTIFICATION-TYPE
        OBJECTS       { rcSysActionL1, rcSysConfigFileName }
        STATUS        current
        DESCRIPTION   "A rcnSaveConfig trap signifies that either the
                       runtime config or the boot config has been saved
                       on the switch"
        ::= { rcTrapsMib 61 }

rcnDNSRequestResponse NOTIFICATION-TYPE
        OBJECTS       { rcSysDnsServerListIpAddr, rcSysDnsRequestType }
        STATUS        current
        DESCRIPTION   "A rcnDnsRequestResponse trap signifies that the
                       switch had sent a query to the DNS server or it had
                       received a successful response from the DNS Server"
        ::= { rcTrapsMib 62 }

rcnDuplicateIpAddress NOTIFICATION-TYPE
        OBJECTS { ipNetToMediaNetAddress,ipNetToMediaPhysAddress }
        STATUS  current
        DESCRIPTION
                "A rcnDuplicateIpAddress trap signifies that a duplicate IP
                 address is detected on the subnet."
        ::= { rcTrapsMib 63 }

rcnLoopDetectPortDown NOTIFICATION-TYPE
        OBJECTS { rcPortIndex,ifAdminStatus,ifOperStatus }
        STATUS  current
        DESCRIPTION
                "A rcnLoopDetectPortDown trap signifies that a loop has been
                 detected on a port and the port is going to shut down."
        ::= { rcTrapsMib 64 }

rcnLoopDetectMacDiscard NOTIFICATION-TYPE
        OBJECTS  { rcBridgeNewFdbAddress, rcPortIndex, rcPortIndex, rcSysMacFlapLimitTime, 
                   rcSysMacFlapLimitCount}
        STATUS     current
        DESCRIPTION  "A rcnLoopDetectMacDiscard  trap signifies that a loop 
                      has been Detected on a port and the mac address will 
                      be discarded on all ports in that vlan"
        ::= { rcTrapsMib 67}

rcnAutoRecoverPort NOTIFICATION-TYPE
        OBJECTS { rcPortIndex }
        STATUS current
        DESCRIPTION "A rcnAutoRecoverPort trap signifies that autorecover 
                     has re-enabled a port disabled by link flap or cp limit"
        ::= {rcTrapsMib 68 }

rcnAutoRecoverLoopDetectedPort NOTIFICATION-TYPE
        OBJECTS { rcPortIndex, rcVlanNewLoopDetectedAction }
        STATUS current
        DESCRIPTION "A rcnAutoRecoverPort trap signifies that autorecover 
                     has cleared the action taken on a port by loop detect"
        ::= {rcTrapsMib 69 }

rcnExtCpLimitShutDown NOTIFICATION-TYPE
        OBJECTS       { rcPortIndex,
                        ifAdminStatus
                      }
        STATUS        current
        DESCRIPTION  "A rcnExtCpLimitShutDown trap signifies that
                      port is shut down due to Extended CP-Limit."
        ::= { rcTrapsMib 70 }

rcnExtCpLimitSopCongestion NOTIFICATION-TYPE
        OBJECTS       { rcSysExtCplimitSysOctapidCongested,
                        rcSysExtCplimitPortsMonitored
                      }
        STATUS        current
        DESCRIPTION  "A rcnExtCpLimitSopCongestion signifies that system octapid
                      polling finds that system octapid is congested or not.
                      rcSysExtCplimitSysOctapidCongested signifies whether 
                      system octapid is congested or not.
                      rcSysExtCplimitPortsMonitored signifies whether ports are
                      selected for monitoring the ingress traffic utilization."
        ::= {rcTrapsMib 71 }

--TACACS+

rcnTacacsAuthFailure NOTIFICATION-TYPE
    OBJECTS       { rcTacacsGlobalLastUserName }
    STATUS        current
    DESCRIPTION   "TACACS+ authentication failed for user"
    ::= { rcTrapsMib 74 }

rcnTacacsNoServers NOTIFICATION-TYPE
    STATUS        current
    DESCRIPTION   "Unable to use any TACACS+ servers for authentication"
    ::= { rcTrapsMib 75 }

rcnTacacsRxUnsupportedFrame NOTIFICATION-TYPE
    OBJECTS       { rcTacacsGlobalLastAddressType, rcTacacsGlobalLastAddress }
    STATUS        current
    DESCRIPTION   "Received unsupported frame from TACACS+ server"
    ::= { rcTrapsMib 76 }

rcnTacacsExceededMaxLogins NOTIFICATION-TYPE
    STATUS        current
    DESCRIPTION   "Attempted to exceed the maximum number of allowed TACACS+ logins"
    ::= { rcTrapsMib 77 }

rcnTacacsClientFailure NOTIFICATION-TYPE
    STATUS        current
    DESCRIPTION   "TACACS+ Client application is down"
    ::= { rcTrapsMib 78 }

rcnVlacpPortDown NOTIFICATION-TYPE
        OBJECTS       { rcPortIndex}
        STATUS        current
        DESCRIPTION  "A rcnVlacpPortDown trap signifies that
                      Vlacp is down on the port specified."
        ::= { rcTrapsMib 80 }

rcnVlacpPortUp NOTIFICATION-TYPE
        OBJECTS       { rcPortIndex}
        STATUS        current
        DESCRIPTION  "A rcnVlacpPortUp trap signifies that
                      Vlacp is Up on the port specified."
        ::= { rcTrapsMib 81 }

rcnExtCpLimitShutDownNormal   NOTIFICATION-TYPE

	STATUS        current
	DESCRIPTION  "An rcnExtCpLimitShutDownNormal trap signifies that
		      Ports are shut down due to Extended CP-Limit in Normal
		      mode." 
	::= { rcTrapsMib 82 }

rcnEapMacIntrusion NOTIFICATION-TYPE
        OBJECTS      {rcSysIpAddr, rcRadiusPaePortNumber,
                      rcRadiusEapLastAuthMac, rcRadiusEapLastRejMac}
        STATUS        current
        DESCRIPTION   "A rcnEapMacIntrusion trap signifies that 
                      an EAP MAC intrusion has occured on this Port."
        ::= { rcTrapsMib 83 }

rcnInterCpuCommStatus NOTIFICATION-TYPE 
        OBJECTS      { rc2kCardIndex, rcCardOperStatus }
        STATUS        current
        DESCRIPTION  "A rcnInterCpuCommStatus trap signifies the
                      current communication status between primary 
                      and secondary CPU."
        ::= { rcTrapsMib 84 }

-- The following are traps that will notify the network management of changes
-- in the status (normal,warning,alarm) of DDI variables

rcPlugOptModTemperatureStatusTrap NOTIFICATION-TYPE
        OBJECTS      { rcPortIndex, rcPlugOptModTemperatureStatus }
        STATUS       current
        DESCRIPTION "Used to trap changes in the temperature status"
        ::= { rcTrapsMib 89}

rcPlugOptModVoltageStatusTrap NOTIFICATION-TYPE
        OBJECTS      { rcPortIndex, rcPlugOptModVoltageStatus }
        STATUS       current
        DESCRIPTION "Used to trap changes in the voltage level"
        ::= { rcTrapsMib 90 }

rcPlugOptModBiasStatusTrap NOTIFICATION-TYPE
        OBJECTS      { rcPortIndex, rcPlugOptModBiasStatus }
        STATUS       current
        DESCRIPTION "Used to trap changes in the laser bias status"
        ::= { rcTrapsMib 91 }

rcPlugOptModTxPowerStatusTrap NOTIFICATION-TYPE
        OBJECTS      { rcPortIndex, rcPlugOptModTxPowerStatus }
        STATUS       current
        DESCRIPTION "Used to trap changes in the transmit power status"
        ::= { rcTrapsMib 92 }

rcPlugOptModRxPowerStatusTrap NOTIFICATION-TYPE
        OBJECTS      { rcPortIndex, rcPlugOptModRxPowerStatus}
        STATUS       current
        DESCRIPTION "Used to trap changes in the received power status"
        ::= { rcTrapsMib 93 }

rcPlugOptModAux1StatusTrap NOTIFICATION-TYPE
        OBJECTS      { rcPortIndex,
		       rcPlugOptModAux1Monitoring,
		       rcPlugOptModAux1Status }
        STATUS       current
        DESCRIPTION "Used to trap changes in the Aux1 status"
        ::= { rcTrapsMib 94 }

rcPlugOptModAux2StatusTrap NOTIFICATION-TYPE
        OBJECTS      { rcPortIndex,
		       rcPlugOptModAux2Monitoring,
		       rcPlugOptModAux2Status }
        STATUS       current
        DESCRIPTION "Used to trap changes in the Aux2 status"
        ::= { rcTrapsMib 95 }

rcnMaxRouteWarnClear NOTIFICATION-TYPE
        OBJECTS      { rcVrfName }
        STATUS        current
        DESCRIPTION  "A rcnMaxRouteWarnClear trap signifies that
                     the number of routes in the routing table of
                     the Virtual Router has droped below its
                     warning threshold."
        ::= { rcTrapsMib 110 }

 rcnMaxRouteWarnSet NOTIFICATION-TYPE
        OBJECTS      { rcVrfName }
        STATUS        current
        DESCRIPTION  "A rcnMaxRouteWarnSet trap signifies that
                     the given Virtual Routers routing table is 
                     reaching its maximum size. Action should be
                     taken to prevent this"
        ::= { rcTrapsMib 111 }

rcnMaxRouteDropClear NOTIFICATION-TYPE
        OBJECTS      { rcVrfName }
        STATUS        current
        DESCRIPTION  "A rcnMaxRouteDropClear signifies that
                     the given Virtual Routers routing table is 
                     no longer dropping new routes as it is below
                     its maximum size."
        ::= { rcTrapsMib 112 }

rcnMaxRouteDropSet NOTIFICATION-TYPE
        OBJECTS      { rcVrfName }
        STATUS        current
        DESCRIPTION  "A rcnMaxRouteDropSet trap signifies that
                     the given Virtual Routers routing table has
                     reached its maximum size, and is now dropping
                     all new non static routes."
        ::= { rcTrapsMib 113 }

rcnMstpNewCistRoot NOTIFICATION-TYPE
        OBJECTS       { rcStgBridgeAddress }
        STATUS        current
        DESCRIPTION   "A rcnMstpNewCistRoot trap signifies that the
                      SNMPv2 entity, acting in an agent role, has
                      detected the Multiple Spanning Tree Protocol has
                      declared the device to be the new root of the common
                      internal spanning tree."
        ::= { rcTrapsMib 117 }


rcnMstpNewMstiRoot NOTIFICATION-TYPE
        OBJECTS       { rcStgBridgeAddress, rcStgId }
        STATUS        current
        DESCRIPTION   "A rcnMstpNewMstiRoot signifies that the
                      SNMPv2 entity, acting in an agent role, has
                      detected the Multiple Spanning Tree Protocol has
                      declared the device to be the new root of the
                      spanning tree instance."
        ::= { rcTrapsMib 118 }

rcnMstpNewCistRegionalRoot NOTIFICATION-TYPE
        OBJECTS       { rcStgBridgeAddress }
        STATUS        current
        DESCRIPTION   "A rcnMstpNewCistRegionalRoot trap signifies that the
                      SNMPv2 entity, acting in an agent role, has
                      detected the Multiple Spanning Tree Protocol has
                      declared the device to be the new regional root of 
                      the common internal spanning tree."
        ::= { rcTrapsMib 119 }

rcnRstpNewRoot NOTIFICATION-TYPE
        OBJECTS       { rcStgBridgeAddress }
        STATUS        current
        DESCRIPTION   "A rcnRstpNewRoot signifies that the
                      SNMPv2 entity, acting in an agent role, has
                      detected the Rapid Spanning Tree Protocol has
                      declared the device to be the new root of the 
                      spanning tree."
        ::= { rcTrapsMib 120 }

rcnRsmltEdgePeerModified NOTIFICATION-TYPE
        OBJECTS      { rcVlanName }
        STATUS        current
        DESCRIPTION  "A rcnRsmltEdgePeerModified signifies that
                     the RSMLT Peer address is different from
                     that of the stored address. Save config is
                     necessary if EdgeSupport has to use this info
                     on next reboot."
        ::= { rcTrapsMib 124 }

rcnTmuxParityError NOTIFICATION-TYPE
        OBJECTS      {rc2kDeviceGlobalSlot}
        STATUS        current
        DESCRIPTION   "A rcnTmuxParityError trap identifies a problem in the FAD
                      /SWIP based on the number of parity errors."
        ::= { rcTrapsMib 165 }

rcnChasPowerSupplyNoRedundancy NOTIFICATION-TYPE
        STATUS        current
        DESCRIPTION  "A rcnChasPowerSupplyNoRedundancy signifies that
                     the chassis is running on power supply without 
                     redundancy."
        ::= { rcTrapsMib 167 }

rcnChasPowerSupplyRedundancy NOTIFICATION-TYPE
        STATUS        current
        DESCRIPTION  "A rcnChasPowerSupplyRedundancy signifies that
                     the chassis is running on power supply with 
                     redundancy."
        ::= { rcTrapsMib 168 }

rcnLicenseTrialPeriodExpired NOTIFICATION-TYPE
        STATUS        current
        DESCRIPTION  "A rcnLicenseTrialPeriodExpired signifies that
                      Trial Period License has expired."
        ::= { rcTrapsMib 171 }

rcnLicenseTrialPeriodExpiry NOTIFICATION-TYPE
        OBJECTS      { rcSysLicenseTrialDaysLeft }
        STATUS        current
        DESCRIPTION  "A rcnLicenseTrialPeriodExpiry signifies
                      the time remaining before License Trial Period
                      expires in days."
        ::= { rcTrapsMib 172 }

rcnVrfUp NOTIFICATION-TYPE
        OBJECTS      { rcVrfName, rcVrfOperStatus }
        STATUS        current
        DESCRIPTION  "This notification is generated when the specified
                      VRF's operational status is toggled from down to up."
        ::= { rcTrapsMib 173 }

rcnVrfDown NOTIFICATION-TYPE
        OBJECTS      { rcVrfName, rcVrfOperStatus }
        STATUS        current
        DESCRIPTION  "This notification is generated when the specified
                      VRF's operational status is toggled from up to down."
        ::= { rcTrapsMib 174 }

-- CR Q01741872 : Added the mibs rcnMrouteIngressThresholdExceeded and
-- rcnMrouteEgressThresholdExceeded

rcnMrouteIngressThresholdExceeded NOTIFICATION-TYPE
        OBJECTS      { rcIpResourceUsageGlobalIngressRecInUse,
                       rcIpResourceUsageGlobalIngressThreshold }
        STATUS        current
        DESCRIPTION  "This notification is generated when the number of
                      mroute ingress records exceeds the ingress threshold."
        ::= { rcTrapsMib 175 }

rcnMrouteEgressThresholdExceeded NOTIFICATION-TYPE
        OBJECTS      { rcIpResourceUsageGlobalEgressRecInUse,
                       rcIpResourceUsageGlobalEgressThreshold }
        STATUS        current
        DESCRIPTION  "This notification is generated when the number of
                      mroute egress records exceeds the egress threshold."
        ::= { rcTrapsMib 176 }

rcnRemoteMirroringStatus  NOTIFICATION-TYPE
        OBJECTS       { rcPortRemoteMirroringIndex,
                        rcPortRemoteMirroringEnable,
                        rcPortRemoteMirroringMode }
        STATUS        current
        DESCRIPTION   " A rcnRemoteMirroringStatus trap signifies whether
                       the remote mirroring is enabled
                       or disabled on a particular port"
        ::= { rcTrapsMib 177 }

rcnChasPowerSupplyRunningLow NOTIFICATION-TYPE
        STATUS        current
        DESCRIPTION  "A rcnChasPowerSupplyRunningLow signifies that
                     the chassis is running on low power supply."
        ::= { rcTrapsMib 185 }

rcnIsisPlsbMetricMismatchTrap  NOTIFICATION-TYPE
        OBJECTS       { rcIsisLocalLspId,  
                        rcIsisLocall1Metric,
			rcIsisNgbLspId,	
			rcIsisNgbl1Metric,
                        rcIsisPlsbTrapType,
                        rcIsisTrapIndicator,
                        rcIsisLocalHostName,
                        rcIsisNgbHostName}
        STATUS        current
        DESCRIPTION   "A PLSB ISIS trap signifies that a LSP with a different 
                       value of l1-metric is received"
        ::= { rcTrapsMib 192 }

rcnIsisPlsbDuplicateSysidTrap  NOTIFICATION-TYPE
        OBJECTS       { rcIsisLocalSysId,
                        rcIsisLocalInterface,                
                        rcIsisPlsbTrapType,
                        rcIsisTrapIndicator}
        STATUS        current
        DESCRIPTION   "A PLSB ISIS trap signifies that a Hello packet with a 
                       duplicate system-id is received"
        ::= { rcTrapsMib 193 }
rcnIsisPlsbLsdbUpdateTrap  NOTIFICATION-TYPE
        OBJECTS       { rcIsisPlsbTrapType}
        STATUS        current
        DESCRIPTION   "A PLSB ISIS trap signifies that LSDB information has 
                       changed"
        ::= { rcTrapsMib 194 }

rcnChasFanCoolingLow NOTIFICATION-TYPE
        OBJECTS       { rcChasFanOperStatus, rcChasFanType,
                        rcErrorLevel, rcErrorText }        -- Q01859608
        STATUS        current
        DESCRIPTION  "A rcnChasFanCoolingLow signifies that
                     the chassis is running on low fan cooling."
        ::= { rcTrapsMib 196 }

rcnAuthenticationSuccess NOTIFICATION-TYPE
        OBJECTS       { rcLoginUserName, rcLoginHostIpAddress }  
        STATUS        deprecated
        DESCRIPTION  "A rcnAuthenticationSuccess trap signifies that a login
		      is success. Trap includes login username and host ip.
		      It's deprecated by rcnaAuthenticationSuccess."
        ::= { rcTrapsMib 268 }

rcnCardInsert NOTIFICATION-TYPE
        OBJECTS       { rc2kCardIndex, rcSlotType }
        STATUS        current
        DESCRIPTION  "A rcnCardInsert trap signifies that a card/module
                      is inserted into the chassis"
        ::= { rcTrapsMib 269 }

rcnCardRemove NOTIFICATION-TYPE
        OBJECTS       { rc2kCardIndex, rcSlotType }
        STATUS        current
        DESCRIPTION  "A rcnCardRemove trap signifies that a card/module
                      is removed from the chassis"
        ::= { rcTrapsMib 270 }

rcnChasFanFail NOTIFICATION-TYPE
        OBJECTS       { rcFanZoneType, rcFanTrayId, rcFanUnitId }
        STATUS        current
        DESCRIPTION  "A rcnChasFanFail trap indicates that a fan unit
                      of a fan tray in a fan zone has fault."
        ::= { rcTrapsMib 271 }

rcnChasFanOk NOTIFICATION-TYPE
        OBJECTS       { rcFanZoneType, rcFanTrayId, rcFanUnitId }
        STATUS        current
        DESCRIPTION  "A rcnChasFanOk trap indicates that a fan unit
                      of a fan tray in a fan zone has recovered from
                      previously detected fan fault."
        ::= { rcTrapsMib 272 }

rcnCardOverheat NOTIFICATION-TYPE
        OBJECTS       { rc2kCardIndex, rcSlotType, rcCardTemp }
        STATUS        current
        DESCRIPTION  "A rcnCardOverheat trap indicates that a card temperature
                      has exceeded the alarm threshold temperature."
        ::= { rcTrapsMib 273 }

rcnCardNormalTemp NOTIFICATION-TYPE
        OBJECTS       { rc2kCardIndex, rcSlotType, rcCardTemp }
        STATUS        current
        DESCRIPTION  "A rcnCardNormalTemp trap indicates that a card
                      temperature has been cool down from previously detected
                      overheat condition."
        ::= { rcTrapsMib 274 }

rcnCardOverheatShutDown NOTIFICATION-TYPE
        OBJECTS       { rc2kCardIndex, rcSlotType, rcCardTemp }
        STATUS        current
        DESCRIPTION  "A rcnCardOverheatShutDown trap indicates that a card
                      has been shut down due to persistent temperature overheat
                      for 15 minutes or temperature has exceeded the shut down
                      threshold temperature."
        ::= { rcTrapsMib 275 }

rcnCardCpuUtilizationHigh NOTIFICATION-TYPE
        OBJECTS       { rc2kCardIndex, rcSlotType, rcCpuUtilization }
        STATUS        current
        DESCRIPTION  "A rcnCardCpuUtilizationHigh trap indicates that 5-minute 
	 	      CPU utilization average on this slot is above 90%."
        ::= { rcTrapsMib 276 }

rcnCardCpuUtilizationNormal NOTIFICATION-TYPE
        OBJECTS       { rc2kCardIndex, rcSlotType, rcCpuUtilization }
        STATUS        current
        DESCRIPTION  "A rcnCardCpuUtilizationNormal trap indicates that 5-minute 
	 	      CPU utilization average on this slot is below 75%."
        ::= { rcTrapsMib 277 }

rcnIsisPlsbBvidMismatchTrap  NOTIFICATION-TYPE
        OBJECTS       { rcIsisLocalSysId,
			rcIsisLocalPrimaryBvid,
			rcIsisLocalPrimaryTieBrkAlg,
			rcIsisLocalSecondaryBvid,
			rcIsisLocalSecondaryTieBrkAlg,
			rcIsisNgbSysId,
			rcIsisNgbPrimaryBvid,
			rcIsisNgbPrimaryTieBrkAlg,
			rcIsisNgbSecondaryBvid, 
			rcIsisNgbSecondaryTieBrkAlg,   
                        rcIsisLocalBvidCounter,
                        rcIsisNgbBvidCounter,
                        rcIsisPlsbTrapType,
                        rcIsisTrapIndicator,
                        rcIsisNgbHostName
                        }
        STATUS        current
        DESCRIPTION   "A PLSB ISIS trap signifies that a Hello packet with mismatched 
                       B-VIDs is received"
        ::= { rcTrapsMib 278 }

rcnIsisPlsbSmltVirtBmacMismatchTrap  NOTIFICATION-TYPE
        OBJECTS       { rcIsisLocalVirtualBmac,
			rcIsisPeerVirtualBmac,
                        rcIsisPlsbTrapType,
                        rcIsisTrapIndicator}
        STATUS        current
        DESCRIPTION   "A PLSB ISIS trap signifies that Virtual BMAC configured in the switch
                       is different from virtual BMAC configured in the IST peer"
        ::= { rcTrapsMib 279 }

rcnIsisPlsbSmltPeerBmacMismatchTrap  NOTIFICATION-TYPE
        OBJECTS       { rcIsisSysId,
			rcIsisSmltPeerSysId,
                        rcIsisPlsbTrapType,
                        rcIsisTrapIndicator}
        STATUS        current
        DESCRIPTION   "A PLSB ISIS trap signifies that either the Smlt Peer BMAC configured 
                       in the IST peer is different from the ISIS SystemId of the local switch OR
                       The Smlt peer BMAC configured in the local switch is different from
                       the ISIS systemId of the IST peer"

        ::= { rcTrapsMib 280 }

rcnIsisPlsbAdjStateTrap  NOTIFICATION-TYPE
        OBJECTS       { rcIsisNgbSysId,
                        rcIsisLocalInterface,                
                        rcIsisPlsbTrapType,
                        rcIsisAdjState,
                        rcIsisNgbHostName}
        STATUS        current
        DESCRIPTION   "A PLSB ISIS trap signifies ISIS adjacency state change."
        ::= { rcTrapsMib 281 }         

rcnIsisPlsbDuplicateNnameTrap  NOTIFICATION-TYPE
        OBJECTS       { rcIsisNgbNickname, 
                        rcIsisPlsbTrapType,
                        rcIsisTrapIndicator,
                        rcIsisNgbSysId,
                        rcIsisDuplicateNnameCounter, 
                        rcIsisNgbHostName}
        STATUS        current
        DESCRIPTION   "A PLSB ISIS trap signifies that a LSP with duplicate
                       nickname is received, this trap should be generated 
                       by all the switches in the network."
        ::= { rcTrapsMib 282 }

rcnIsisPlsbSmltSplitBebMismatchTrap NOTIFICATION-TYPE
        OBJECTS       { rcIsisLocalSmltSplitBeb,
                        rcIsisPeerSmltSplitBeb,
                        rcIsisPlsbTrapType,
                        rcIsisTrapIndicator}
        STATUS        current
        DESCRIPTION   "A PLSB ISIS trap signifies that the Smlt Split-Beb configured in the local
                       switch and IST peer are same. One IST switch shoule be configured as 
                       Split-Beb primary and the IST peer should be configured as Split-Beb
                       secondary."

        ::= { rcTrapsMib 283 }

rcnIsisPlsbMultiLinkAdjTrap NOTIFICATION-TYPE
        OBJECTS       { rcIsisNgbSysId,
                        rcIsisLocalInterface,
                        rcIsisPrevInterface,
                        rcIsisPlsbTrapType,
                        rcIsisNgbHostName,
                        rcIsisTrapIndicator}
        STATUS        current
        DESCRIPTION   "A PLSB ISIS trap signifies that multiple ISIS adjacencies are formed with 
                       the same ISIS node."

        ::= { rcTrapsMib 284 }      


rcnaSshSessionLogout NOTIFICATION-TYPE
        OBJECTS       { rcLoginHostAddressType, rcLoginHostInetAddress }
        STATUS        current
        DESCRIPTION   "A rcnaSshSessionLogout trap signifies that there
                       is a SSH session logout. This trap deprecates the
	 	       rcnSshSessionLogout trap."
        ::= { rcTrapsMib 285 }

rcnaSshUnauthorizedAccess NOTIFICATION-TYPE
        OBJECTS       { rcLoginHostAddressType, rcLoginHostInetAddress }
        STATUS        current
        DESCRIPTION   "A rcnaSshUnauthorizedAccess trap signifies that
                       an unauthorized access has occured. This trap 
		       deprecates the rcnSshUnauthorizedAccess trap."
        ::= { rcTrapsMib 286 }

rcnaAuthenticationSuccess NOTIFICATION-TYPE
        OBJECTS       { rcLoginUserName, rcLoginHostAddressType, rcLoginHostInetAddress }  
        STATUS        current
        DESCRIPTION  "A rcnaAuthenticationSuccess trap signifies that a login
		      is success. Trap includes login username and address 
		      type and inet address. This trap deprecates the  
	              rcnAuthenticationSuccess trap."
        ::= { rcTrapsMib 287 }

rcnaSshSessionLogin NOTIFICATION-TYPE
        OBJECTS       { rcLoginHostAddressType, rcLoginHostInetAddress }
        STATUS        current
        DESCRIPTION   "A rcnaSshSessionLogin trap signifies that there
                       is a SSH session login. This trap deprecates the
	 	       rcnSshSessionLogin trap."
        ::= { rcTrapsMib 288 }

-- Syslog Group
 
rcSyslogGlobal      OBJECT IDENTIFIER ::= { rcSyslog 1 }

rcSyslogGlobalEnable OBJECT-TYPE
        SYNTAX        	TruthValue
        MAX-ACCESS        	read-write
        STATUS        	current
        DESCRIPTION   	"Used to enable/disable the SysLog feature.  When
			enabled this feature will send a message to a server 
			on a network that this configured to receive and
			store diagnostic messages from this device.  The
			type of messages sent is user configurable."
	DEFVAL	      	{ true }
        ::= { rcSyslogGlobal 1 }

rcSyslogGlobalMaxHosts OBJECT-TYPE
        SYNTAX        INTEGER (1..10)
        MAX-ACCESS    read-write
        STATUS        current
        DESCRIPTION   "Maximun number of remote hosts considered 'active'
                       and able to receive messages from the Syslog service
                       on the router."
        DEFVAL        { 5 }
        ::= { rcSyslogGlobal 2 }

rcSyslogGlobalOperState OBJECT-TYPE
        SYNTAX        INTEGER {
                         active(1),
                         inactive(2),
                         emptyHostTbl(3),
                         allHostDisabled(4)
                      }
        MAX-ACCESS    read-only
        STATUS        current
        DESCRIPTION   "The operational state of the syslog service
                       on the router."
        DEFVAL        { active }
        ::= { rcSyslogGlobal 3 }

rcSyslogGlobalHeader OBJECT-TYPE
        SYNTAX        INTEGER {
                         default(1),
                         managementVIP(2),
                         circuitlessIP(3)
                      }
        MAX-ACCESS    read-write
        STATUS        current
        DESCRIPTION   "The IP Header Type for the Syslog Packet."
        DEFVAL        { 1 }
        ::= { rcSyslogGlobal 4 }

rcSyslogHostTbl OBJECT-TYPE
        SYNTAX        SEQUENCE OF RcSyslogHostEntry
        MAX-ACCESS    not-accessible
        STATUS        current
        DESCRIPTION   "Table of remote host destinations for syslog."
        ::= { rcSyslog 2 }

rcSyslogHostEntry OBJECT-TYPE
        SYNTAX        RcSyslogHostEntry
        MAX-ACCESS    not-accessible
        STATUS        current
        DESCRIPTION   "Entry containing information for a particular
                       entry in rcSyslogHostTable."
        INDEX         { rcSyslogHostId }
        ::= { rcSyslogHostTbl 1 }

RcSyslogHostEntry ::= SEQUENCE {
                rcSyslogHostId                  INTEGER,
                rcSyslogHostIpAddr              IpAddress,
                rcSyslogHostUdpPort             INTEGER,
		rcSyslogHostFacility            INTEGER,	
		rcSyslogHostModuleId            INTEGER,
		rcSyslogHostModuleId2           Integer32,
		rcSyslogHostSeverity            INTEGER,
		rcSyslogHostMapInfoSeverity     INTEGER,
		rcSyslogHostMapWarningSeverity  INTEGER,
		rcSyslogHostMapErrorSeverity    INTEGER,
		rcSyslogHostMapMfgSeverity      INTEGER,
		rcSyslogHostMapFatalSeverity    INTEGER,
		rcSyslogHostMapTraceMsg         INTEGER,
		rcSyslogHostMapTrapMsg          INTEGER,
		rcSyslogHostLogTraceMsgs        TruthValue,
		rcSyslogHostLogTrapMsgs         TruthValue,
		rcSyslogHostEnable              TruthValue,
                rcSyslogHostRowStatus           RowStatus,
		rcSyslogHostAddressType         InetAddressType,
		rcSyslogHostAddress             InetAddress	
        }

rcSyslogHostId OBJECT-TYPE
        SYNTAX        INTEGER (1..10)
        MAX-ACCESS    read-only
        STATUS        current
        DESCRIPTION   "Host Id."
        ::= { rcSyslogHostEntry 1 }

rcSyslogHostIpAddr OBJECT-TYPE
        SYNTAX        IpAddress
        MAX-ACCESS    read-write
        STATUS        deprecated
        DESCRIPTION   "Host Ip Address"
        ::= { rcSyslogHostEntry 2 }

rcSyslogHostUdpPort OBJECT-TYPE
        SYNTAX        INTEGER (514..530)
        MAX-ACCESS    read-write
        STATUS        current
        DESCRIPTION   "Specifies the UDP port to use to send syslog 
                      messages to the host." 
        DEFVAL        { 514 }
        ::= { rcSyslogHostEntry 3 }

rcSyslogHostFacility OBJECT-TYPE
        SYNTAX        INTEGER {
                         local0(128),
                         local1(136),
                         local2(144),
                         local3(152),
                         local4(160),
                         local5(168),
                         local6(176),
                         local7(184)
                      }
        MAX-ACCESS    read-write
        STATUS        current
        DESCRIPTION   "Specifies the UNIX facility used in messages
 		      to the syslog host.  Default is LOCAL7."
        DEFVAL        { local7 }
        ::= { rcSyslogHostEntry 4 }
 
rcSyslogHostModuleId OBJECT-TYPE
        SYNTAX        INTEGER {
                         common         (1),      -- '00000001'H
                         snmp           (2),      -- '00000002'H
                         rmon           (4),      -- '00000004'H
                         portmgr        (8),      -- '00000008'H
                         chasmgr       (16),      -- '00000010'H
                         bridge        (32),      -- '00000020'H
                         ospf          (64),      -- '00000040'H
                         hwif         (128),      -- '00000080'H
                         sim          (256),      -- '00000100'H
                         cpp          (512),      -- '00000200'H
                         netdrv      (1024),      -- '00000400'H
                         vlanmgr     (2048),      -- '00000800'H
                         cli         (4096),      -- '00001000'H
                         main        (8192),      -- '00002000'H
                         p2ip       (16384),      -- '00004000'H
                         rcip       (32768),      -- '00008000'H
                         rompager   (65536),      -- '00010000'H
                         acif      (131072),      -- '00020000'H
                         gbip      (262144),      -- '00040000'H
                         wdt       (524288),      -- '00080000'H
                         tdp      (1048576),      -- '00100000'H
                         mandiag  (2097152),      -- '00200000'H
                         mantest  (4194304),      -- '00400000'H
                         igmp     (8388608),      -- '00800000'H
                         ipfil   (16777216),      -- '01000000'H
                         mlt     (33554432),      -- '02000000'H
                         ippolicy(67108864),      -- '04000000'H
                         ipmc   (134217728),      -- '08000000'H
                         syslog (268435456)       -- '10000000'H
                      }
        MAX-ACCESS    read-write
        STATUS        current
        DESCRIPTION   "Specifies for which modules/tasks syslog messages
		       should be sent.  Default is all modules/tasks."
        ::= { rcSyslogHostEntry 5 }

rcSyslogHostModuleId2 OBJECT-TYPE
        SYNTAX        Integer32
        MAX-ACCESS    read-write
        STATUS        current
        DESCRIPTION   "Specifies for which modules/tasks syslog messages
                       should be sent.  Default is all modules/tasks."
        ::= { rcSyslogHostEntry 6 }

rcSyslogHostSeverity OBJECT-TYPE
        SYNTAX        INTEGER (1..31) 
        MAX-ACCESS    read-write
        STATUS        current
        DESCRIPTION   "Specifies the severity level for which syslog messages
		       should be sent for the modules specifies in 
                       'SyslogHostModule'.
                       Value is one of multiple (logical 'OR') of the following:
                         info(1),
                         warning(2),
                         error(4),
                         mfg(8),
                         fatal(16)."
        DEFVAL        { 1 }
        ::= { rcSyslogHostEntry 7 }

-- Following between =begin =end is processed by mib_tools/extras.awk
-- =begin enum
-- rcSyslogHostSeverity info    1
-- rcSyslogHostSeverity warning 2
-- rcSyslogHostSeverity error   4
-- rcSyslogHostSeverity mfg     8
-- rcSyslogHostSeverity fatal  16
-- rcSyslogHostSeverity all    31
-- =end enum

rcSyslogHostMapInfoSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
		       INFO messages.  Default is INFO."
        DEFVAL        { info }
        ::= { rcSyslogHostEntry 8 }

rcSyslogHostMapWarningSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       WARNING messages.  Default is WARNING.  Should be
                       <= INFO."
        DEFVAL        { warning }
        ::= { rcSyslogHostEntry 9 }

rcSyslogHostMapErrorSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       ERROR messages.  Default is ERROR.  Should be
		       <= WARNING."
        DEFVAL        { error }
        ::= { rcSyslogHostEntry 10 }

rcSyslogHostMapMfgSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       Manufactoring messages.  Dafault is ERROR."
        DEFVAL        { error }
        ::= { rcSyslogHostEntry 11 }

rcSyslogHostMapFatalSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       FATAL messages.  Default is EMERGENCY.  Should be
		       <= ERROR."
        DEFVAL        { emergency }
        ::= { rcSyslogHostEntry 12 }

rcSyslogHostMapTraceMsg OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for syslog
		       trace messages.  Default is DEBUG."
        ::= { rcSyslogHostEntry 13 }

rcSyslogHostMapTrapMsg OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the UNIX severity code to use for syslog
		       messages for SNMP traps sent to the syslog host.
                       Default is INFO."
        ::= { rcSyslogHostEntry 14 }

rcSyslogHostLogTraceMsgs OBJECT-TYPE
        SYNTAX        TruthValue
        MAX-ACCESS    read-write
        STATUS        current
        DESCRIPTION   "Indicate whether to activate the host to log the 
                       syslog trace messages."
        ::= { rcSyslogHostEntry 15 }

rcSyslogHostLogTrapMsgs OBJECT-TYPE
        SYNTAX        TruthValue
        MAX-ACCESS    read-write
        STATUS        current
        DESCRIPTION   "Indicate whether to activate the host to log the
	               syslog messages for SNMP traps."
        ::= { rcSyslogHostEntry 16 }

rcSyslogHostEnable OBJECT-TYPE
        SYNTAX        TruthValue
        MAX-ACCESS    read-write
        STATUS        current
        DESCRIPTION   "Enable/Disable messages to be sent to syslog host."
        DEFVAL        { false }
        ::= { rcSyslogHostEntry 17 }

rcSyslogHostRowStatus OBJECT-TYPE
        SYNTAX        RowStatus
        MAX-ACCESS    read-write
        STATUS        current
        DESCRIPTION   "Used to create/delete entries in the rcSyslogTable."
        ::= { rcSyslogHostEntry 18 }

rcSyslogHostAddressType OBJECT-TYPE
        SYNTAX        InetAddressType
        MAX-ACCESS    read-write
        STATUS        current
        DESCRIPTION   "Address Type of the Host."
        ::= {rcSyslogHostEntry  19 }

rcSyslogHostAddress OBJECT-TYPE
        SYNTAX        InetAddress
        MAX-ACCESS    read-write
        STATUS        current
        DESCRIPTION   "Address of the Host."
        ::= {rcSyslogHostEntry  20 }

-- Diag Mirror by port Table

rcDiagMirrorByPortTable OBJECT-TYPE
        SYNTAX        	SEQUENCE OF RcDiagMirrorByPortEntry
        MAX-ACCESS        	not-accessible
        STATUS        	current
        DESCRIPTION   	"This table is used to configure the Mirror By
			Port feature.  This feature allows the device
			to forward a copy of each packet seen on a
			particular port to a different port."
        ::= { rcDiag 1 }

rcDiagMirrorByPortEntry OBJECT-TYPE
        SYNTAX        	RcDiagMirrorByPortEntry
        MAX-ACCESS        	not-accessible
        STATUS        	current
        DESCRIPTION   	"Entry containing mirror by port information."
        INDEX         	{ rcDiagMirrorByPortId }
        ::= { rcDiagMirrorByPortTable 1 }

RcDiagMirrorByPortEntry ::= SEQUENCE {
                rcDiagMirrorByPortId                INTEGER,
                rcDiagMirrorByPortMirroredPort      InterfaceIndex,
                rcDiagMirrorByPortMirroringPort     InterfaceIndex,
                rcDiagMirrorByPortMode              INTEGER,
                rcDiagMirrorByPortEnable            TruthValue,
                rcDiagMirrorByPortRowStatus         RowStatus,
                rcDiagMirrorByPortPid               Integer32, -- obsolete
                rcDiagMirrorRemoteMirrorVlanId      INTEGER,
                rcDiagMirrorByPortMirroredPortList  PortSet,
                rcDiagMirrorByPortMirroringPortList PortSet,
                rcDiagMirrorMirroringVlanId         Integer32,
                rcDiagMirrorMirroringMltId          Integer32,
                rcDiagMirrorMirroringMgId           Integer32,
                rcDiagMirrorMirroringIpAddr         IpAddress,
                rcDiagMirrorMirroringIpTtl          Integer32,
                rcDiagMirrorMirroringIpDscp         Integer32
        }

rcDiagMirrorByPortId OBJECT-TYPE
        SYNTAX        	INTEGER(1..479) 
        MAX-ACCESS        	read-only
        STATUS        	current
        DESCRIPTION   	"Entry id."
        ::= { rcDiagMirrorByPortEntry 1 }

rcDiagMirrorByPortMirroredPort OBJECT-TYPE
        SYNTAX          InterfaceIndex 
        MAX-ACCESS        	read-write
        STATUS        	current
        DESCRIPTION   	"Used to configure the 'mirrored' port.  The port
			where packets are copied from."
        ::= { rcDiagMirrorByPortEntry 2 }

rcDiagMirrorByPortMirroringPort OBJECT-TYPE
        SYNTAX          InterfaceIndex	
        MAX-ACCESS        	read-write
        STATUS        	current
        DESCRIPTION   	"Used to configure the 'mirroring' port.  The port
			where packets are copied to."
        ::= { rcDiagMirrorByPortEntry 3 }

rcDiagMirrorByPortMode OBJECT-TYPE
        SYNTAX        	INTEGER {
                         	tx(1),
                         	rx(2),
                         	both(3)
                      	}
        MAX-ACCESS        	read-write
        STATUS        	current
        DESCRIPTION  	"Used to configure the 'mode' of the mirror operation.
			'tx' means packets being transmitted on the 'mirrored'
			port will be copied.  'rx' means packets received on
			the 'mirrored' port will be copied.  'both' means
			all traffic on the 'mirrored' port will be copied.
			'rxFilter' means packets received on the 'mirrored'
			port is copied only if it macthes filter criteria.
			'txFilter' means packets being transmitted on the 
			'mirrorred' port is copied only if it matches filter
			criteria.  'bothFilter' means both ingress and egress
			traffic will be copied if it matches either ingress or
			egress filter on the 'mirrored' port."
	DEFVAL	      	{ rx }
        ::= { rcDiagMirrorByPortEntry 4 }

rcDiagMirrorByPortEnable OBJECT-TYPE
        SYNTAX        	TruthValue
        MAX-ACCESS        	read-write
        STATUS        	current
        DESCRIPTION   	"Used to enable/disable this entry."
	DEFVAL	      	{ true }
        ::= { rcDiagMirrorByPortEntry 5 }

rcDiagMirrorByPortRowStatus OBJECT-TYPE
        SYNTAX        	RowStatus
        MAX-ACCESS        	read-write
        STATUS        	current
        DESCRIPTION   	"Row status of this entry."
        ::= { rcDiagMirrorByPortEntry 6 }

rcDiagMirrorByPortPid OBJECT-TYPE
        SYNTAX          Integer32
        MAX-ACCESS      read-only
        STATUS          current 
        DESCRIPTION     "Pid for a port."
        ::= { rcDiagMirrorByPortEntry 8 }

rcDiagMirrorRemoteMirrorVlanId OBJECT-TYPE
        SYNTAX          INTEGER(0..4084)
        MAX-ACCESS      read-write
        STATUS          current
        DESCRIPTION     "vlan-id to which mirrored packets needs to 
                         be send for remote mirroring. If set, this
                         vlan id is used in mirror tag of the remote 
                         mirrored packet"
        ::= { rcDiagMirrorByPortEntry 9 }

rcDiagMirrorByPortMirroredPortList OBJECT-TYPE
        SYNTAX          PortSet
        MAX-ACCESS      read-create
        STATUS          current
        DESCRIPTION     "Used to configure the 'mirrored' port.  The port
                        where packets are copied from."
        ::= { rcDiagMirrorByPortEntry 12 }

rcDiagMirrorByPortMirroringPortList OBJECT-TYPE
        SYNTAX          PortSet
        MAX-ACCESS      read-create
        STATUS          current
        DESCRIPTION     "Used to configure the 'mirroring' port.  The port
                        where packets are copied from."
        ::= { rcDiagMirrorByPortEntry 13 }

rcDiagMirrorMirroringVlanId OBJECT-TYPE
        SYNTAX          Integer32(0..4084)
        MAX-ACCESS      read-create  
        STATUS          current
        DESCRIPTION     "Destination is a VLAN."
        ::= { rcDiagMirrorByPortEntry 14 }

rcDiagMirrorMirroringMltId OBJECT-TYPE
        SYNTAX          Integer32 (0..512) 
        MAX-ACCESS      read-create 
        STATUS          current
        DESCRIPTION     "Destination is an MLT."
        ::= { rcDiagMirrorByPortEntry 15 }

rcDiagMirrorMirroringMgId OBJECT-TYPE
        SYNTAX          Integer32 (0..4096) 
        MAX-ACCESS      read-only
        STATUS          current
        DESCRIPTION     "Contains information about the MGID allocated."
        ::= { rcDiagMirrorByPortEntry 16 }

rcDiagMirrorMirroringIpAddr OBJECT-TYPE
        SYNTAX        IpAddress
        MAX-ACCESS    read-write
        STATUS        current
        DESCRIPTION   "Destination IP address."
        ::= { rcDiagMirrorByPortEntry 17 }

rcDiagMirrorMirroringIpTtl OBJECT-TYPE
        SYNTAX          Integer32 (2..255)
        MAX-ACCESS      read-write
        STATUS          current
        DESCRIPTION     "Ttl value for the mirrored packet when mirror
                         destination is IP.  If other than default,
                         the encapsulated packet will have the given ttl."
        DEFVAL          { 64 }
        ::= { rcDiagMirrorByPortEntry 18 }

rcDiagMirrorMirroringIpDscp OBJECT-TYPE
     SYNTAX             Integer32 (0..63)
     MAX-ACCESS         read-write
     STATUS             current
     DESCRIPTION        "Dscp value for mirrored packets when mirror
                         destination is IP.  If other than default,
                         the encapsulated packet will have the given
                         Dscp value."
     DEFVAL             { 0 }
     ::= { rcDiagMirrorByPortEntry 19 }


-- Diag Port Conv Steering Table

rcDiagPortConvSteeringTable OBJECT-TYPE
        SYNTAX        SEQUENCE OF RcDiagPortConvSteeringEntry
        MAX-ACCESS    not-accessible
        STATUS        current
        DESCRIPTION   "Diag Port Conv Steering Table"
        ::= { rcDiag 2 }

rcDiagPortConvSteeringEntry OBJECT-TYPE
        SYNTAX        RcDiagPortConvSteeringEntry
        MAX-ACCESS    not-accessible
        STATUS        current
        DESCRIPTION   "Entry containing information of Diag Port Conv Steering."
        INDEX         { rcDiagPortConvSteeringId }
        ::= { rcDiagPortConvSteeringTable 1 }

RcDiagPortConvSteeringEntry ::= SEQUENCE {
                rcDiagPortConvSteeringId           Integer32,
                rcDiagPortConvSteeringPortOne      Integer32,
                rcDiagPortConvSteeringPortTwo      Integer32,
                rcDiagPortConvSteeringMode         INTEGER,
                rcDiagPortConvSteeringForwardPort  Integer32,
                rcDiagPortConvSteeringEnable       TruthValue,
                rcDiagPortConvSteeringRowStatus    RowStatus
        }

rcDiagPortConvSteeringId OBJECT-TYPE
        SYNTAX        Integer32 (0..2147483647)
        MAX-ACCESS    read-only
        STATUS        current
        DESCRIPTION   "Entry id."
        ::= { rcDiagPortConvSteeringEntry 1 }

rcDiagPortConvSteeringPortOne OBJECT-TYPE
        SYNTAX        Integer32
        MAX-ACCESS    read-write
        STATUS        current
        DESCRIPTION   "IfIndex for port one"
        ::= { rcDiagPortConvSteeringEntry 2 }

rcDiagPortConvSteeringPortTwo OBJECT-TYPE
        SYNTAX        Integer32
        MAX-ACCESS    read-write
        STATUS        current
        DESCRIPTION   "IfIndex for port two"
        ::= { rcDiagPortConvSteeringEntry 3 }

rcDiagPortConvSteeringMode OBJECT-TYPE
        SYNTAX        INTEGER {
                         oneToTwo(1),
                         twoToOne(2),
                         both(3)
                      }
        MAX-ACCESS    read-write
        STATUS        current
        DESCRIPTION   "Used to specify the traffic flow that should be
		      captured between ports one and two."
        ::= { rcDiagPortConvSteeringEntry 4 }

rcDiagPortConvSteeringForwardPort OBJECT-TYPE
        SYNTAX        Integer32
        MAX-ACCESS    read-write
        STATUS        current
        DESCRIPTION   "IfIndex of the port where captured traffic should
		      be forwarded to."
        ::= { rcDiagPortConvSteeringEntry 5 }

rcDiagPortConvSteeringEnable OBJECT-TYPE
        SYNTAX        TruthValue
        MAX-ACCESS    read-write
        STATUS        current
        DESCRIPTION   "Enable this entry."
	DEFVAL	      { true }
        ::= { rcDiagPortConvSteeringEntry 6 }

rcDiagPortConvSteeringRowStatus OBJECT-TYPE
        SYNTAX        RowStatus
        MAX-ACCESS    read-write
        STATUS        current
        DESCRIPTION   "Used to create/delete entries in the rcDiagMirrorByPortTable."
        ::= { rcDiagPortConvSteeringEntry 7 }


-- Diag Mac Conv Steering Table

rcDiagMacConvSteeringTable OBJECT-TYPE
        SYNTAX        SEQUENCE OF RcDiagMacConvSteeringEntry
        MAX-ACCESS    not-accessible
        STATUS        current
        DESCRIPTION   "Diag Mac Conv Steering Table"
        ::= { rcDiag 3 }

rcDiagMacConvSteeringEntry OBJECT-TYPE
        SYNTAX        RcDiagMacConvSteeringEntry
        MAX-ACCESS    not-accessible
        STATUS        current
        DESCRIPTION   "Entry containing information of Diag Mac Conv Steering."
        INDEX         { rcDiagMacConvSteeringId }
        ::= { rcDiagMacConvSteeringTable 1 }

RcDiagMacConvSteeringEntry ::= SEQUENCE {
                rcDiagMacConvSteeringId          Integer32,
                rcDiagMacConvSteeringSrcMac      MacAddress,
                rcDiagMacConvSteeringDstMac      MacAddress,
                rcDiagMacConvSteeringInPort      Integer32,
                rcDiagMacConvSteeringForwardPort Integer32,
                rcDiagMacConvSteeringEnable      TruthValue,
                rcDiagMacConvSteeringRowStatus   RowStatus
        }

rcDiagMacConvSteeringId OBJECT-TYPE
        SYNTAX        Integer32
        MAX-ACCESS    read-only
        STATUS        current
        DESCRIPTION   "Entry id."
        ::= { rcDiagMacConvSteeringEntry 1 }

rcDiagMacConvSteeringSrcMac OBJECT-TYPE
        SYNTAX        MacAddress
        MAX-ACCESS    read-write
        STATUS        current
        DESCRIPTION   "Source MAC address"
        ::= { rcDiagMacConvSteeringEntry 2 }

rcDiagMacConvSteeringDstMac OBJECT-TYPE
        SYNTAX        MacAddress
        MAX-ACCESS    read-write
        STATUS        current
        DESCRIPTION   "Destination MAC address"
        ::= { rcDiagMacConvSteeringEntry 3 }

rcDiagMacConvSteeringInPort OBJECT-TYPE
        SYNTAX        Integer32
        MAX-ACCESS    read-write
        STATUS        current
        DESCRIPTION   "IfIndex of ingress port."
        ::= { rcDiagMacConvSteeringEntry 4 }

rcDiagMacConvSteeringForwardPort OBJECT-TYPE
        SYNTAX        Integer32
        MAX-ACCESS    read-write
        STATUS        current
        DESCRIPTION   "IfIndex of the port where captured traffic should
		      be forwarded to."
        ::= { rcDiagMacConvSteeringEntry 5 }

rcDiagMacConvSteeringEnable OBJECT-TYPE
        SYNTAX        TruthValue
        MAX-ACCESS    read-write
        STATUS        current
        DESCRIPTION   "Enable this entry."
	DEFVAL	      { true }
        ::= { rcDiagMacConvSteeringEntry 6 }

rcDiagMacConvSteeringRowStatus OBJECT-TYPE
        SYNTAX        RowStatus
        MAX-ACCESS    read-write
        STATUS        current
        DESCRIPTION   "Used to create/delete entries in the rcDiagMirrorByPortTable."
        ::= { rcDiagMacConvSteeringEntry 7 }

rcDiagMirrorByPortTblSize OBJECT-TYPE
        SYNTAX      	Integer32
        MAX-ACCESS        	read-only
        STATUS        	current
        DESCRIPTION   	"Used to indicate table size."
        ::= { rcDiag 11 }

rcDiagPortConvSteeringTblSize OBJECT-TYPE
        SYNTAX        	Integer32
        MAX-ACCESS        	read-only
        STATUS        	current
        DESCRIPTION   	"Used to indicate table size."
        ::= { rcDiag 12 }

rcDiagMacConvSteeringTblSize OBJECT-TYPE
        SYNTAX        	Integer32
        MAX-ACCESS        	read-only
        STATUS        	current
        DESCRIPTION   	"Used to indicate table size."
        ::= { rcDiag 13 }


-- rcDiagPcap Group

rcDiagPcap OBJECT IDENTIFIER ::= { rcDiag 15 }

rcDiagPcapEnable   OBJECT-TYPE
      SYNTAX  TruthValue
      MAX-ACCESS    read-write
      STATUS        current
      DESCRIPTION   "To enable pcap in secondary CPU"
      DEFVAL         { false }
      ::= { rcDiagPcap 1 }

rcDiagPcapBufferWrap   OBJECT-TYPE
      SYNTAX        TruthValue
      MAX-ACCESS    read-write
      STATUS        current
      DESCRIPTION   "To enable buffer wrap-around when buffer is full.
                     If set, pcap will continue to capture pkts, otherwise
                     stops pkt storing"
      DEFVAL         { false }
      ::= { rcDiagPcap 2 }

rcDiagPcapPcmciaWrap   OBJECT-TYPE
      SYNTAX        TruthValue
      MAX-ACCESS    read-write
      STATUS        current
      DESCRIPTION   "To wrap around the PCMCIA when saving data in PCMCIA.
                     In Vsp,the name has been changed to wrap-auto-save-file.
                     When this parameter is true it overwrites the file present on extflash/network during autosave.
                     If this parameter is set to false the file present is not overwritten."
      DEFVAL         { false }
      ::= { rcDiagPcap 3 }

rcDiagPcapFrameSize   OBJECT-TYPE
    SYNTAX        INTEGER (64..9600)
    MAX-ACCESS    read-write
    STATUS        current
    DESCRIPTION   "Number of bytes of pkts needs to be stored"
    DEFVAL         { 64 }
      ::= { rcDiagPcap 4 }

rcDiagPcapBufferSize   OBJECT-TYPE
    SYNTAX        INTEGER (2..420)
    MAX-ACCESS    read-write
    STATUS        current
    DESCRIPTION   "memory to be allocated for capturing the pkt"
    DEFVAL        { 32 }
      ::= { rcDiagPcap 5 }

rcDiagPcapAutoSave   OBJECT-TYPE
      SYNTAX        TruthValue
      MAX-ACCESS    read-write
      STATUS        current
      DESCRIPTION   "To save data automatically when buffer is full"
      DEFVAL         { false }
      ::= { rcDiagPcap 6 }

rcDiagPcapAutoSaveFileName   OBJECT-TYPE
      SYNTAX       DisplayString (SIZE (0..40))
      MAX-ACCESS   read-write
      STATUS       current
      DESCRIPTION   "Name of the file in which the pkt is to be stored"
      ::= { rcDiagPcap 7 }

rcDiagPcapAutoSaveDevice   OBJECT-TYPE
      SYNTAX  INTEGER {
                 pcmcia(0),
                 network(1)
              }
      MAX-ACCESS  read-write
      STATUS        current
      DESCRIPTION   "Where to store the captured pkts. If the option is
                     network, the user need to enter an IP address also"
      ::= { rcDiagPcap 8 }

rcDiagPcapAutoSaveNetworkIpAddress   OBJECT-TYPE
      SYNTAX        IpAddress
      MAX-ACCESS    read-write
      STATUS        current
      DESCRIPTION   "ip address of the remote host where the data
                     needs to be stored. This field is valid only
                     if the device is network"
      ::= { rcDiagPcap 9 }


rcDiagPcapFilterTableSize OBJECT-TYPE
        SYNTAX        Integer32
        MAX-ACCESS    read-only
        STATUS        current
        DESCRIPTION   "Used to indicate the number of entries in the
                       Filter table"
        ::= { rcDiagPcap 10 }


-- rcDiagPcapFilterTable

rcDiagPcapFilterTable OBJECT-TYPE
        SYNTAX        SEQUENCE OF RcDiagPcapFilterEntry
        MAX-ACCESS    not-accessible
        STATUS        current
        DESCRIPTION   "A table used to store pcap secondary filters"
        ::= { rcDiagPcap 11 }

rcDiagPcapFilterEntry OBJECT-TYPE
        SYNTAX        RcDiagPcapFilterEntry
        MAX-ACCESS    not-accessible
        STATUS        current
        DESCRIPTION   "Pcap secondary filter desc"
        INDEX         {rcDiagPcapFilterId }
        ::= { rcDiagPcapFilterTable 1 }

RcDiagPcapFilterEntry ::= SEQUENCE {
        rcDiagPcapFilterId                      INTEGER,
        rcDiagPcapFilterEnable                  EnableValue,
        rcDiagPcapFilterAction                  INTEGER,
        rcDiagPcapFilterSrcMac                  MacAddress,
        rcDiagPcapFilterSrcMask                 INTEGER (1..6),
        rcDiagPcapFilterIsInverseSrcMac         TruthValue,
        rcDiagPcapFilterDstMac                  MacAddress,
        rcDiagPcapFilterDstMask                 INTEGER (1..6),
        rcDiagPcapFilterIsInverseDstMac         TruthValue,
        rcDiagPcapFilterVlanId                  INTEGER,
        rcDiagPcapFilterToVlanId                INTEGER,
        rcDiagPcapFilterIsInverseVlanId         TruthValue,
        rcDiagPcapFilterPbit                    INTEGER,
        rcDiagPcapFilterToPbit                  INTEGER,
        rcDiagPcapFilterIsInversePbit           TruthValue,
        rcDiagPcapFilterEtherType               INTEGER,
        rcDiagPcapFilterToEtherType             INTEGER,
        rcDiagPcapFilterIsInverseEtherType      TruthValue,
        rcDiagPcapFilterProtocolType            INTEGER,
        rcDiagPcapFilterToProtocolType          INTEGER,
        rcDiagPcapFilterIsInverseProtocolType   TruthValue,
        rcDiagPcapFilterSrcIp                   IpAddress,
        rcDiagPcapFilterToSrcIp                 IpAddress,
        rcDiagPcapFilterIsInverseSrcIp          TruthValue,
        rcDiagPcapFilterDstIp                   IpAddress,
        rcDiagPcapFilterToDstIp                 IpAddress,
        rcDiagPcapFilterIsInverseDstIp          TruthValue,
        rcDiagPcapFilterDscp                    INTEGER,
        rcDiagPcapFilterToDscp                  INTEGER,
        rcDiagPcapFilterIsInverseDscp           TruthValue,
        rcDiagPcapFilterRowStatus               RowStatus,
        rcDiagPcapFilterDscpMatchZero           TruthValue,
        rcDiagPcapFilterPbitMatchZero           TruthValue
    }

rcDiagPcapFilterId OBJECT-TYPE
        SYNTAX        INTEGER (1..1000)
        MAX-ACCESS    read-only
        STATUS        current
        DESCRIPTION   "Unique ID that represents the filter"
        ::= { rcDiagPcapFilterEntry 1 }

rcDiagPcapFilterEnable OBJECT-TYPE
        SYNTAX        EnableValue
        MAX-ACCESS    read-write
        STATUS        current
        DESCRIPTION   "Filter is enabled or not"
        DEFVAL        { disable }
        ::= { rcDiagPcapFilterEntry 2 }

rcDiagPcapFilterAction   OBJECT-TYPE
        SYNTAX         INTEGER {
                          drop(0),
                          capture(1),
                          trigger-on(2),
                          trigger-off(3)
                       }
        MAX-ACCESS    read-write
        STATUS        current
        DESCRIPTION   "Action to be takesn when policy is matched"
        DEFVAL        { capture }
        ::= { rcDiagPcapFilterEntry 3 }

rcDiagPcapFilterSrcMac   OBJECT-TYPE
        SYNTAX         MacAddress
        MAX-ACCESS    read-write
        STATUS        current
        DESCRIPTION   "Soruce mac address to match"
        ::= { rcDiagPcapFilterEntry 4 }

rcDiagPcapFilterSrcMask  OBJECT-TYPE
        SYNTAX         INTEGER (1..6)
        MAX-ACCESS    read-write
        STATUS        current
        DESCRIPTION   "Soruce mac address mask. Used to specify a range"
        DEFVAL        { 6 }
        ::= { rcDiagPcapFilterEntry 5 }

rcDiagPcapFilterIsInverseSrcMac OBJECT-TYPE
        SYNTAX         TruthValue
        MAX-ACCESS    read-write
        STATUS        current
        DESCRIPTION   "Soruce mac address Inverse. when set the mac
                       addresses otherthan specified is matched"
        DEFVAL         { false }
        ::= { rcDiagPcapFilterEntry 6 }

rcDiagPcapFilterDstMac   OBJECT-TYPE
        SYNTAX        MacAddress
        MAX-ACCESS    read-write
        STATUS        current
        DESCRIPTION   "Destination mac address"
        ::= { rcDiagPcapFilterEntry 7 }

rcDiagPcapFilterDstMask  OBJECT-TYPE
        SYNTAX         INTEGER (1..6)
        MAX-ACCESS    read-write
        STATUS        current
        DESCRIPTION   "Destination mac address mask. Used to specify a range"
        DEFVAL        { 6 }
        ::= { rcDiagPcapFilterEntry 8 }

rcDiagPcapFilterIsInverseDstMac OBJECT-TYPE
        SYNTAX         TruthValue
        MAX-ACCESS    read-write
        STATUS        current
        DESCRIPTION   "Destination mac address Inverse. when set the mac
                       addresses otherthan specified is matched"
        DEFVAL         { false }
        ::= { rcDiagPcapFilterEntry 9 }

rcDiagPcapFilterVlanId  OBJECT-TYPE
        SYNTAX         INTEGER (0..4084)
        MAX-ACCESS    read-write
        STATUS        current
        DESCRIPTION   "Vlan-id of the packet to be matched"
        DEFVAL         { 0 }
        ::= { rcDiagPcapFilterEntry 10 }

rcDiagPcapFilterToVlanId  OBJECT-TYPE
        SYNTAX         INTEGER (0..4084)
        MAX-ACCESS    read-write
        STATUS        current
        DESCRIPTION   "To Vlan-id. Used to specify a range"
        DEFVAL         { 0 }
        ::= { rcDiagPcapFilterEntry 11 }

rcDiagPcapFilterIsInverseVlanId   OBJECT-TYPE
        SYNTAX        TruthValue
        MAX-ACCESS    read-write
        STATUS        current
        DESCRIPTION   "Vlan-Id Inverse. when set the Vlan-Id
                       otherthan specified range is matched"
        DEFVAL         { false }
        ::= { rcDiagPcapFilterEntry 12 }
rcDiagPcapFilterPbit  OBJECT-TYPE
        SYNTAX         INTEGER (0..7)
        MAX-ACCESS    read-write
        STATUS        current
        DESCRIPTION   "pBit of the packet to be matched"
        DEFVAL         { 0 }
        ::= { rcDiagPcapFilterEntry 13 }

rcDiagPcapFilterToPbit  OBJECT-TYPE
        SYNTAX         INTEGER (0..7)
        MAX-ACCESS    read-write
        STATUS        current
        DESCRIPTION   "To pBit. Used to specify a range"
        DEFVAL         { 0 }
        ::= { rcDiagPcapFilterEntry 14 }

rcDiagPcapFilterIsInversePbit   OBJECT-TYPE
        SYNTAX        TruthValue
        MAX-ACCESS    read-write
        STATUS        current
        DESCRIPTION   "pBit Inverse. when set the pBit
                       otherthan specified range is matched"
        DEFVAL         { false }
        ::= { rcDiagPcapFilterEntry 15 }

rcDiagPcapFilterEtherType  OBJECT-TYPE
        SYNTAX         INTEGER (0..65535)
        MAX-ACCESS    read-write
        STATUS        current
        DESCRIPTION   "EtherType of the packet to be matched"
        DEFVAL         { 0 }
        ::= { rcDiagPcapFilterEntry 16 }

rcDiagPcapFilterToEtherType  OBJECT-TYPE
        SYNTAX         INTEGER (0..65535)
        MAX-ACCESS    read-write
        STATUS        current
        DESCRIPTION   "To EtherType. Used to specify a range"
        DEFVAL         { 0 }
        ::= { rcDiagPcapFilterEntry 17 }

rcDiagPcapFilterIsInverseEtherType   OBJECT-TYPE
        SYNTAX        TruthValue
        MAX-ACCESS    read-write
        STATUS        current
        DESCRIPTION   "EtherType Inverse. when set the EtherType
                       otherthan specified range is matched"
        DEFVAL         { false }
        ::= { rcDiagPcapFilterEntry 18 }

rcDiagPcapFilterProtocolType  OBJECT-TYPE
        SYNTAX         INTEGER (0..255)
        MAX-ACCESS    read-write
        STATUS        current
        DESCRIPTION   "ProtocolType of the packet to be matched"
        DEFVAL         { 0 }
        ::= { rcDiagPcapFilterEntry 19 }

rcDiagPcapFilterToProtocolType  OBJECT-TYPE
        SYNTAX         INTEGER (0..255)
        MAX-ACCESS    read-write
        STATUS        current
        DESCRIPTION   "To ProtocolType. Used to specify a range"
        DEFVAL         { 0 }
        ::= { rcDiagPcapFilterEntry 20 }

rcDiagPcapFilterIsInverseProtocolType   OBJECT-TYPE
        SYNTAX        TruthValue
        MAX-ACCESS    read-write
        STATUS        current
        DESCRIPTION   "ProtocolType Inverse. when set the ProtocolType
                       otherthan specified range is matched"
        DEFVAL         { false }
        ::= { rcDiagPcapFilterEntry 21 }

rcDiagPcapFilterSrcIp  OBJECT-TYPE
        SYNTAX        IpAddress
        MAX-ACCESS    read-write
        STATUS        current
        DESCRIPTION   "Source IP address of the packet to be matched"
        ::= { rcDiagPcapFilterEntry 22 }

rcDiagPcapFilterToSrcIp  OBJECT-TYPE
        SYNTAX        IpAddress
        MAX-ACCESS    read-write
        STATUS        current
        DESCRIPTION   "To Source IP address. Used to specify a range"
        ::= { rcDiagPcapFilterEntry 23 }

rcDiagPcapFilterIsInverseSrcIp   OBJECT-TYPE
        SYNTAX        TruthValue
        MAX-ACCESS    read-write
        STATUS        current
        DESCRIPTION   "Source IP address Inverse. when set the source IP
                       otherthan specified range is matched"
        DEFVAL         { false }
        ::= { rcDiagPcapFilterEntry 24 }

rcDiagPcapFilterDstIp  OBJECT-TYPE
        SYNTAX        IpAddress
        MAX-ACCESS    read-write
        STATUS        current
        DESCRIPTION   "Destination IP address of the packet to be matched"
        ::= { rcDiagPcapFilterEntry 25 }

rcDiagPcapFilterToDstIp  OBJECT-TYPE
        SYNTAX        IpAddress
        MAX-ACCESS    read-write
        STATUS        current
        DESCRIPTION   "To Destination IP address. Used to specify a range"
        ::= { rcDiagPcapFilterEntry 26 }

rcDiagPcapFilterIsInverseDstIp   OBJECT-TYPE
        SYNTAX        TruthValue
        MAX-ACCESS    read-write
        STATUS        current
        DESCRIPTION   "Destination IP address Inverse. when set the 
                       Destination IP otherthan specified is range 
                       matched"
        DEFVAL         { false }
        ::= { rcDiagPcapFilterEntry 27 }

rcDiagPcapFilterDscp  OBJECT-TYPE
        SYNTAX         INTEGER (0..63)
        MAX-ACCESS    read-write
        STATUS        current
        DESCRIPTION   "DSCP value of the packet to be matched"
        DEFVAL         { 0 }
        ::= { rcDiagPcapFilterEntry 28 }

rcDiagPcapFilterToDscp  OBJECT-TYPE
        SYNTAX         INTEGER (0..63)
        MAX-ACCESS    read-write
        STATUS        current
        DESCRIPTION   "To DSCP. Used to specify a range"
        DEFVAL         { 0 }
        ::= { rcDiagPcapFilterEntry 29 }

rcDiagPcapFilterIsInverseDscp   OBJECT-TYPE
        SYNTAX        TruthValue
        MAX-ACCESS    read-write
        STATUS        current
        DESCRIPTION   "DSCP Inverse. when set the DSCP
                       otherthan specified range is matched"
        DEFVAL         { false }
        ::= { rcDiagPcapFilterEntry 30 }

rcDiagPcapFilterRowStatus   OBJECT-TYPE
        SYNTAX        RowStatus
        MAX-ACCESS    read-write
        STATUS        current
        DESCRIPTION   "Row Status"
        ::= { rcDiagPcapFilterEntry 31 }

rcDiagPcapFilterDscpMatchZero   OBJECT-TYPE
        SYNTAX        TruthValue
        MAX-ACCESS    read-write
        STATUS        current
        DESCRIPTION   "When this value is set to true, then 0 value of
                       Pbit is not taken as disable value. The user will
                       be allowed to capture packets with Pbit value of
                       0 also. Be default it would be set to FALSE"
        DEFVAL         { false }
        ::= { rcDiagPcapFilterEntry 32 }

rcDiagPcapFilterPbitMatchZero   OBJECT-TYPE
        SYNTAX        TruthValue
        MAX-ACCESS    read-write
        STATUS        current
        DESCRIPTION   "When this value is set to true, then 0 value of
                       Pbit is not taken as disable value. The user will
                       be allowed to capture packets with Pbit value of
                       0 also. Be default it would be set to FALSE"
        DEFVAL         { false }
        ::= { rcDiagPcapFilterEntry 33 }


-- rcDiagPcapAdvancedFilterTable


rcDiagPcapAdvancedFilterTableSize OBJECT-TYPE
        SYNTAX        Integer32
        MAX-ACCESS    read-only
        STATUS        current
        DESCRIPTION   "Used to indicate the number of entries in the
                       Filter table advanced parameter"
        ::= { rcDiagPcap 12 }

rcDiagPcapAdvancedFilterTable OBJECT-TYPE
        SYNTAX        SEQUENCE OF RcDiagPcapAdvancedFilterEntry
        MAX-ACCESS    not-accessible
        STATUS        current
        DESCRIPTION   "A table used to store pcap secondary filters"
        ::= { rcDiagPcap 13 }

rcDiagPcapCopyFileName OBJECT-TYPE
        SYNTAX        DisplayString
        MAX-ACCESS    read-write
        STATUS        current
        DESCRIPTION   "Used to indicate the file name. When set, the PCAP 
                       data from PCAP engine RAM is stored into this file
                       in PCAP engine"
        ::= { rcDiagPcap 14 }

rcDiagPcapResetStat OBJECT-TYPE
        SYNTAX        INTEGER {
                           none(1),
                           resetStat(2)
                       }
        MAX-ACCESS    read-write
        STATUS        current
        DESCRIPTION   "To Reset PCAP statistics"
        ::= { rcDiagPcap 15 }

rcDiagPcapStatPacketCapacityCount OBJECT-TYPE
        SYNTAX         DisplayString
        MAX-ACCESS     read-only
        STATUS         current
        DESCRIPTION    "Packet Capacity Count"
        ::= { rcDiagPcap 16 }

rcDiagPcapStatNumberOfPacketsReceived OBJECT-TYPE
        SYNTAX         DisplayString
        MAX-ACCESS     read-only
        STATUS         current
        DESCRIPTION    "Number of packets received in PCAP engine"
        ::= { rcDiagPcap 17 }

rcDiagPcapStatNumberOfPacketsAccumulated OBJECT-TYPE
        SYNTAX         DisplayString
        MAX-ACCESS     read-only
        STATUS         current
        DESCRIPTION    "Number of packets captured in PCAP engine"
        ::= { rcDiagPcap 18 }

rcDiagPcapStatNumberOfPacketsDroppedInPcapEngine OBJECT-TYPE
        SYNTAX         DisplayString
        MAX-ACCESS     read-only
        STATUS         current
        DESCRIPTION    "Number of packets dropped in PCAP engine by filters"
        ::= { rcDiagPcap 19 }

rcDiagPcapStatNumberOfPacketsDroppedInHardware OBJECT-TYPE
        SYNTAX         DisplayString
        MAX-ACCESS     read-only
        STATUS         current
        DESCRIPTION    "Number of packets dropped in Hardware"
        ::= { rcDiagPcap 20 }

rcDiagPcapDataValid OBJECT-TYPE
        SYNTAX         TruthValue
        MAX-ACCESS     read-only
        STATUS         current
        DESCRIPTION    "A true/false value that indicate the return 
                        data whether is valid."
        ::= { rcDiagPcap 21 }

rcDiagPcapEtherTypeForSvlanLevel OBJECT-TYPE
        SYNTAX         INTEGER ('5dd'h..'ffff'h)
        MAX-ACCESS     read-write
        STATUS         current
        DESCRIPTION    "EtherType of svlan level."
        ::= { rcDiagPcap 22 }


rcDiagPcapAdvancedFilterEntry OBJECT-TYPE
        SYNTAX        RcDiagPcapAdvancedFilterEntry
        MAX-ACCESS    not-accessible
        STATUS        current
        DESCRIPTION   "Pcap secondary Advanced filter desc"
        INDEX         {rcDiagPcapAdvancedFilterId }
        ::= { rcDiagPcapAdvancedFilterTable 1 }

RcDiagPcapAdvancedFilterEntry ::= SEQUENCE {
        rcDiagPcapAdvancedFilterId                                              INTEGER,
        rcDiagPcapAdvancedFilterUdpPort                                         INTEGER,
        rcDiagPcapAdvancedFilterToUdpPort                                       INTEGER,
        rcDiagPcapAdvancedFilterIsInverseUdpPort        TruthValue,
        rcDiagPcapAdvancedFilterTcpPort                                 INTEGER,
        rcDiagPcapAdvancedFilterToTcpPort                               INTEGER,
        rcDiagPcapAdvancedFilterIsInverseTcpPort        TruthValue,
        rcDiagPcapAdvancedFilterUserDefinedData         DisplayString,
        rcDiagPcapAdvancedFilterUserDefinedDataSize     INTEGER,
        rcDiagPcapAdvancedFilterUserDefinedOffset       INTEGER,
        rcDiagPcapAdvancedFilterIsInverseUserDefined    TruthValue,
        rcDiagPcapAdvancedFilterTimer                                   INTEGER,
        rcDiagPcapAdvancedFilterPacketCount                     INTEGER,
        rcDiagPcapAdvancedFilterRefreshTimer                    INTEGER,
        rcDiagPcapAdvancedFilterRowStatus                       RowStatus
    }


rcDiagPcapAdvancedFilterId OBJECT-TYPE
        SYNTAX        INTEGER (1..1000)
        MAX-ACCESS    read-only
        STATUS        current
        DESCRIPTION   "Unique ID that represents the filter"
        ::= { rcDiagPcapAdvancedFilterEntry 1 }

rcDiagPcapAdvancedFilterUdpPort  OBJECT-TYPE
        SYNTAX         INTEGER (0..65535)
        MAX-ACCESS    read-write
        STATUS        current
        DESCRIPTION   "UdpPort of the packet to be matched"
        DEFVAL         { 0 }
        ::= { rcDiagPcapAdvancedFilterEntry 2 }

rcDiagPcapAdvancedFilterToUdpPort  OBJECT-TYPE
        SYNTAX         INTEGER (0..65535)
        MAX-ACCESS    read-write
        STATUS        current
        DESCRIPTION   "To UdpPort. Used to specify a range"
        DEFVAL         { 0 }
        ::= { rcDiagPcapAdvancedFilterEntry 3 }

rcDiagPcapAdvancedFilterIsInverseUdpPort   OBJECT-TYPE
        SYNTAX        TruthValue
        MAX-ACCESS    read-write
        STATUS        current
        DESCRIPTION   "UdpPort Inverse. when set the UdpPort
                       otherthan specified range is matched"
        DEFVAL         { false }
        ::= { rcDiagPcapAdvancedFilterEntry 4 }

rcDiagPcapAdvancedFilterTcpPort  OBJECT-TYPE
        SYNTAX         INTEGER (0..65535)
        MAX-ACCESS    read-write
        STATUS        current
        DESCRIPTION   "TcpPort of the packet to be matched"
        DEFVAL         { 0 }
        ::= { rcDiagPcapAdvancedFilterEntry 5 }

rcDiagPcapAdvancedFilterToTcpPort  OBJECT-TYPE
        SYNTAX         INTEGER (0..65535)
        MAX-ACCESS    read-write
        STATUS        current
        DESCRIPTION   "To TcpPort. Used to specify a range"
        DEFVAL         { 0 }
        ::= { rcDiagPcapAdvancedFilterEntry 6 }

rcDiagPcapAdvancedFilterIsInverseTcpPort   OBJECT-TYPE
        SYNTAX        TruthValue
        MAX-ACCESS    read-write
        STATUS        current
        DESCRIPTION   "TcpPort Inverse. when set the TcpPort
                       otherthan specified range is matched"
        DEFVAL         { false }
        ::= { rcDiagPcapAdvancedFilterEntry 7 }

rcDiagPcapAdvancedFilterUserDefinedData  OBJECT-TYPE
        SYNTAX         DisplayString
        MAX-ACCESS    read-write
        STATUS        current
        DESCRIPTION   "User defined data to match with the packets received"
        DEFVAL         { "\0"  }
        ::= { rcDiagPcapAdvancedFilterEntry 8 }

rcDiagPcapAdvancedFilterUserDefinedDataSize   OBJECT-TYPE
        SYNTAX         INTEGER (0..50)
        MAX-ACCESS    read-write
        STATUS        current
        DESCRIPTION   "Length of user defined data"
        DEFVAL         { 0 }
        ::= { rcDiagPcapAdvancedFilterEntry 9 }

rcDiagPcapAdvancedFilterUserDefinedOffset   OBJECT-TYPE
        SYNTAX         INTEGER (0..9600)
        MAX-ACCESS    read-write
        STATUS        current
        DESCRIPTION   "Offset from which match has to start"
        DEFVAL         { 0 }
        ::= { rcDiagPcapAdvancedFilterEntry 10 }


rcDiagPcapAdvancedFilterIsInverseUserDefined OBJECT-TYPE
        SYNTAX        TruthValue
        MAX-ACCESS    read-write
        STATUS        current
        DESCRIPTION   "TcpPort Inverse. when set the Userdata
                       otherthan specified is matched"
        DEFVAL         { false }
        ::= { rcDiagPcapAdvancedFilterEntry 11 }

rcDiagPcapAdvancedFilterTimer OBJECT-TYPE
        SYNTAX         INTEGER (0..3600000)
        MAX-ACCESS    read-write
        STATUS        current
        DESCRIPTION   "Timer to start the pcap capture window in ms"
        DEFVAL         { 0 }
        ::= { rcDiagPcapAdvancedFilterEntry 12 }

rcDiagPcapAdvancedFilterPacketCount OBJECT-TYPE
        SYNTAX         INTEGER (0..65535)
        MAX-ACCESS    read-write
        STATUS        current
        DESCRIPTION   "Number of packets to be captured before disabling pcap"
        DEFVAL         { 0 }
        ::= { rcDiagPcapAdvancedFilterEntry 13 }

rcDiagPcapAdvancedFilterRefreshTimer OBJECT-TYPE
        SYNTAX         INTEGER (0..3600000)
        MAX-ACCESS    read-write
        STATUS        current
        DESCRIPTION   "Refresh timer in ms"
        DEFVAL         { 0 }
        ::= { rcDiagPcapAdvancedFilterEntry 14 }

rcDiagPcapAdvancedFilterRowStatus OBJECT-TYPE
        SYNTAX         RowStatus
        MAX-ACCESS    read-write
        STATUS        current
        DESCRIPTION   "RowStatus"
        ::= { rcDiagPcapAdvancedFilterEntry 15 }



-- POS PPP IPX Table

rcPosPppIpxTable OBJECT-TYPE
        SYNTAX        SEQUENCE OF RcPosPppIpxEntry
        MAX-ACCESS    not-accessible
        STATUS        current
        DESCRIPTION   ""
	::= { rcPos 1 }

rcPosPppIpxEntry OBJECT-TYPE
	SYNTAX        RcPosPppIpxEntry
	MAX-ACCESS 	  not-accessible
	STATUS 	      current
	DESCRIPTION   ""
	INDEX         { rcPosPppIpxIfIndex }
	::= { rcPosPppIpxTable 1 }

RcPosPppIpxEntry ::=
    	SEQUENCE {
                rcPosPppIpxIfIndex          InterfaceIndex,
                rcPosPppIpxIpxcpAdminStatus INTEGER,
                rcPosPppIpxOperStatus       INTEGER,
                rcPosPppIpxNetAddr          OCTET STRING (SIZE(4)),
                rcPosPppIpxRoutingProtocol  INTEGER
    	}

rcPosPppIpxIfIndex OBJECT-TYPE
   	SYNTAX        InterfaceIndex
  	MAX-ACCESS    read-only
  	STATUS        current
	DESCRIPTION   "port number."
	::= { rcPosPppIpxEntry 1 }

rcPosPppIpxIpxcpAdminStatus OBJECT-TYPE  
        SYNTAX        INTEGER {
                         open(1),
                         close(2)
                      }
        MAX-ACCESS    read-write
        STATUS        current
        DESCRIPTION   ""
        DEFVAL { close }
        ::= { rcPosPppIpxEntry 2 }

rcPosPppIpxOperStatus OBJECT-TYPE  
        SYNTAX        INTEGER {
                         up(1),
                         down(2),
                         unknown(3)
                      }
        MAX-ACCESS    read-only
        STATUS        current
        DESCRIPTION   ""
        ::= { rcPosPppIpxEntry 3 }

rcPosPppIpxNetAddr OBJECT-TYPE
        SYNTAX         OCTET STRING (SIZE(4))
        MAX-ACCESS     read-write
        STATUS         current
        DESCRIPTION    "IPX Network address."
        ::= { rcPosPppIpxEntry 4 }

rcPosPppIpxRoutingProtocol OBJECT-TYPE  
        SYNTAX        INTEGER {
                         none(0),
                         rip(2)
                      }
        MAX-ACCESS    read-write
        STATUS        current
        DESCRIPTION   ""
        DEFVAL { none }
        ::= { rcPosPppIpxEntry 5 }

-- POS SONET Table

rcPosSonetTable OBJECT-TYPE
        SYNTAX        SEQUENCE OF RcPosSonetEntry
        MAX-ACCESS    not-accessible
        STATUS        current
        DESCRIPTION   ""
	::= { rcPos 2 }

rcPosSonetEntry OBJECT-TYPE
	SYNTAX        RcPosSonetEntry
	MAX-ACCESS 	  not-accessible
	STATUS 	      current
	DESCRIPTION   ""
	INDEX         { rcPosSonetIndex }
	::= { rcPosSonetTable 1 }

RcPosSonetEntry ::=
    	SEQUENCE {
                rcPosSonetIndex                     InterfaceIndex,
                rcPosSonetFraming                   INTEGER,
                rcPosSonetSectionTrace              INTEGER,
                rcPosSonetSectionGrowth             INTEGER,
                rcPosSonetSyncronization            INTEGER,
                rcPosSonetStsPathTrace              OCTET STRING (SIZE(64)),
                rcPosSonetPathSignalLabel           INTEGER,
                rcPosSonetClockSource               INTEGER,
                rcPosSonetScramble                  EnableValue,
                rcPosSonetOperStatusFraming         Integer32,
                rcPosSonetOperStatusClockSource     Integer32,
                rcPosSonetOperStatusScramble        EnableValue,
                rcPosSonetOperStatusSectionTrace    Integer32,
                rcPosSonetOperStatusPathSignalLabel Integer32

    	}

rcPosSonetIndex OBJECT-TYPE
   	SYNTAX        InterfaceIndex
  	MAX-ACCESS    read-only
  	STATUS        current
	DESCRIPTION   "pos ifIndex."
	::= { rcPosSonetEntry 1 }

rcPosSonetFraming OBJECT-TYPE
        SYNTAX        INTEGER {
                         sonet(1),
                         sdh(2)
                      }
        MAX-ACCESS    read-write
        STATUS        current
        DESCRIPTION   ""
        ::= { rcPosSonetEntry 2 }

rcPosSonetSectionTrace OBJECT-TYPE  
   	SYNTAX        INTEGER (1..255)
  	MAX-ACCESS    read-write
  	STATUS        current
	DESCRIPTION   "config. J0 byte"
        ::= { rcPosSonetEntry 3 }

rcPosSonetSectionGrowth OBJECT-TYPE  
   	SYNTAX        INTEGER (1..255)
  	MAX-ACCESS    read-write
  	STATUS        current
	DESCRIPTION   "config. Z0 byte"
        ::= { rcPosSonetEntry 4 }

rcPosSonetSyncronization OBJECT-TYPE  
   	SYNTAX        INTEGER (1..255)
  	MAX-ACCESS    read-write
  	STATUS        current
	DESCRIPTION   "config. S1 byte"
        ::= { rcPosSonetEntry 5 }

rcPosSonetStsPathTrace OBJECT-TYPE  
        SYNTAX         OCTET STRING (SIZE(64))
        MAX-ACCESS     read-write
        STATUS         current
        DESCRIPTION    "config. 64/16 byte."
        ::= { rcPosSonetEntry 6 }

rcPosSonetPathSignalLabel OBJECT-TYPE  
   	SYNTAX        INTEGER (1..255)
  	MAX-ACCESS    read-write
  	STATUS        current
	DESCRIPTION   "config. C2 byte"
        ::= { rcPosSonetEntry 7 }

rcPosSonetClockSource OBJECT-TYPE
        SYNTAX        INTEGER {
                         line(1),
                         internal(2)
                      }
        MAX-ACCESS    read-write
        STATUS        current
        DESCRIPTION   ""
        ::= { rcPosSonetEntry 8 }

rcPosSonetScramble OBJECT-TYPE
        SYNTAX        EnableValue
        MAX-ACCESS    read-write
        STATUS        current
        DESCRIPTION   ""
        ::= { rcPosSonetEntry 9 }

rcPosSonetOperStatusFraming OBJECT-TYPE
        SYNTAX        Integer32
        MAX-ACCESS    read-only
        STATUS        current
        DESCRIPTION   ""
        ::= { rcPosSonetEntry 10 }

rcPosSonetOperStatusClockSource OBJECT-TYPE
        SYNTAX        Integer32
        MAX-ACCESS    read-only
        STATUS        current
        DESCRIPTION   ""
        ::= { rcPosSonetEntry 11 }


rcPosSonetOperStatusScramble OBJECT-TYPE
        SYNTAX        EnableValue
        MAX-ACCESS    read-only
        STATUS        current
        DESCRIPTION   ""
        ::= { rcPosSonetEntry 12 }

rcPosSonetOperStatusSectionTrace OBJECT-TYPE
      SYNTAX        Integer32
   MAX-ACCESS    read-only
   STATUS        current
      DESCRIPTION   ""
        ::= { rcPosSonetEntry 13 }

rcPosSonetOperStatusPathSignalLabel OBJECT-TYPE
      SYNTAX        Integer32
   MAX-ACCESS    read-only
   STATUS        current
      DESCRIPTION   ""
        ::= { rcPosSonetEntry 14 }



-- Pos Line Status Table

rcPosLineStatusTable OBJECT-TYPE
        SYNTAX        SEQUENCE OF RcPosLineStatusEntry
        MAX-ACCESS    not-accessible
        STATUS        current
        DESCRIPTION   "Pos Line Status Table"
        ::= { rcPos 3 }

rcPosLineStatusEntry OBJECT-TYPE
        SYNTAX        RcPosLineStatusEntry
        MAX-ACCESS    not-accessible
        STATUS        current
        DESCRIPTION   "Entry containing information of Pos Line Status."
        INDEX         { rcPosLineStatusIndex }
        ::= { rcPosLineStatusTable 1 }

RcPosLineStatusEntry ::= SEQUENCE {
                rcPosLineStatusIndex             InterfaceIndex,
                rcPosLineStatusLocalMACAddress   MacAddress,
                rcPosLineStatusRemoteMACAddress  MacAddress,
                rcPosLineStatusLocalIpAddr       IpAddress,
                rcPosLineStatusRemoteIpAddr      IpAddress,
                rcPosLineStatusOutQuality        Integer32,
                rcPosLineStatusLocalPeriod       Integer32,
                rcPosLineStatusDeviceType        Integer32,
                rcPosLineStatusDeviceRev         Integer32,
                rcPosLineStatusIpxRoutingProtocol Integer32
        }

rcPosLineStatusIndex OBJECT-TYPE
        SYNTAX        InterfaceIndex
        MAX-ACCESS    read-only
        STATUS        current
        DESCRIPTION   "pos ifIndex, same as rcPosPppIpxIfIndex."
        ::= { rcPosLineStatusEntry 1 }

rcPosLineStatusLocalMACAddress OBJECT-TYPE
        SYNTAX        MacAddress
        MAX-ACCESS    read-only
        STATUS        current
        DESCRIPTION   "current local MAC address"
        ::= { rcPosLineStatusEntry 2 }

rcPosLineStatusRemoteMACAddress OBJECT-TYPE
        SYNTAX        MacAddress
        MAX-ACCESS    read-only
        STATUS        current
        DESCRIPTION   "current remote MAC address"
        ::= { rcPosLineStatusEntry 3 }

rcPosLineStatusLocalIpAddr OBJECT-TYPE
        SYNTAX        IpAddress
        MAX-ACCESS    read-only
        STATUS        current
        DESCRIPTION   "current local ip addr"
        ::= { rcPosLineStatusEntry 4 }

rcPosLineStatusRemoteIpAddr OBJECT-TYPE
        SYNTAX        IpAddress
        MAX-ACCESS    read-only
        STATUS        current
        DESCRIPTION   "current remote ip addr"
        ::= { rcPosLineStatusEntry 5 }

rcPosLineStatusOutQuality OBJECT-TYPE
        SYNTAX        Integer32
        MAX-ACCESS    read-only
        STATUS        current
        DESCRIPTION   "current output quality."
        ::= { rcPosLineStatusEntry 6 }

rcPosLineStatusLocalPeriod OBJECT-TYPE
        SYNTAX        Integer32
        MAX-ACCESS    read-only
        STATUS        current
        DESCRIPTION   ""
        ::= { rcPosLineStatusEntry 7 }

rcPosLineStatusDeviceType OBJECT-TYPE
        SYNTAX        Integer32
        MAX-ACCESS    read-only
        STATUS        current
        DESCRIPTION   ""
        ::= { rcPosLineStatusEntry 8 }

rcPosLineStatusDeviceRev OBJECT-TYPE
        SYNTAX        Integer32
        MAX-ACCESS    read-only
        STATUS        current
        DESCRIPTION   ""
        ::= { rcPosLineStatusEntry 9 }

rcPosLineStatusIpxRoutingProtocol OBJECT-TYPE
        SYNTAX        Integer32
        MAX-ACCESS    read-only
        STATUS        current
        DESCRIPTION   ""
        ::= { rcPosLineStatusEntry 10 }


-- Pos Line Config Table

rcPosLineConfigTable OBJECT-TYPE
        SYNTAX        SEQUENCE OF RcPosLineConfigEntry
        MAX-ACCESS    not-accessible
        STATUS        current
        DESCRIPTION   "Pos Line Config Table"
        ::= { rcPos 4 }

rcPosLineConfigEntry OBJECT-TYPE
        SYNTAX        RcPosLineConfigEntry
        MAX-ACCESS    not-accessible
        STATUS        current
        DESCRIPTION   "Entry containing information of Pos Line Config."
        INDEX         { rcPosLineConfigIndex }
        ::= { rcPosLineConfigTable 1 }

RcPosLineConfigEntry ::= SEQUENCE {
                rcPosLineConfigIndex              InterfaceIndex,
                rcPosLineConfigLocalMACAddress    MacAddress,
                rcPosLineConfigRemoteMACAddress   MacAddress,
                rcPosLineConfigLocalIpAddr        IpAddress,
                rcPosLineConfigRemoteIpAddr       IpAddress,
                rcPosLineConfigRemoteReportPeriod INTEGER,
                rcPosLineConfigLqrThreshold       INTEGER,
                rcPosLineConfigOutQuality         Integer32,
                rcPosLineConfigPppStp             EnableValue,
                rcPosLineConfigLoopBack           TruthValue,
                rcPosLineConfigIpxVlanMacAddress  MacAddress,
                rcPosLineConfigIpxRemoteMacAddress MacAddress
        }

rcPosLineConfigIndex OBJECT-TYPE
        SYNTAX        InterfaceIndex
        MAX-ACCESS    read-only
        STATUS        current
        DESCRIPTION   "pos ifIndex, same as rcPosPppIpxIfIndex."
        ::= { rcPosLineConfigEntry 1 }

rcPosLineConfigLocalMACAddress OBJECT-TYPE
        SYNTAX        MacAddress
        MAX-ACCESS    read-write
        STATUS        current
        DESCRIPTION   "current local MAC address"
        ::= { rcPosLineConfigEntry 2 }

rcPosLineConfigRemoteMACAddress OBJECT-TYPE
        SYNTAX        MacAddress
        MAX-ACCESS    read-write
        STATUS        current
        DESCRIPTION   "current remote MAC address"
        ::= { rcPosLineConfigEntry 3 }

rcPosLineConfigLocalIpAddr OBJECT-TYPE
        SYNTAX        IpAddress
        MAX-ACCESS    read-write
        STATUS        current
        DESCRIPTION   "current local ip addr"
        ::= { rcPosLineConfigEntry 4 }

rcPosLineConfigRemoteIpAddr OBJECT-TYPE
        SYNTAX        IpAddress
        MAX-ACCESS    read-write
        STATUS        current
        DESCRIPTION   "current remote ip addr"
        ::= { rcPosLineConfigEntry 5 }

rcPosLineConfigRemoteReportPeriod OBJECT-TYPE
        SYNTAX        INTEGER (1..60)
        MAX-ACCESS    read-write
        STATUS        current
        DESCRIPTION   "config. remote report period."
        ::= { rcPosLineConfigEntry 6 }

rcPosLineConfigLqrThreshold OBJECT-TYPE
        SYNTAX        INTEGER (1..100)
        MAX-ACCESS    read-write
        STATUS        current
        DESCRIPTION   "config. input quality."
        ::= { rcPosLineConfigEntry 7 }

rcPosLineConfigOutQuality OBJECT-TYPE
        SYNTAX        Integer32
        MAX-ACCESS    read-write
        STATUS        current
        DESCRIPTION   "config. output quality."
        ::= { rcPosLineConfigEntry 8 }

rcPosLineConfigPppStp OBJECT-TYPE
        SYNTAX        EnableValue
        MAX-ACCESS    read-write
        STATUS        current
        DESCRIPTION   "STP PPP encoding enable T/F"
        ::= { rcPosLineConfigEntry 9 }

rcPosLineConfigLoopBack OBJECT-TYPE
        SYNTAX        TruthValue
        MAX-ACCESS    read-write
        STATUS        current
        DESCRIPTION   "perform loop-back."
        ::= { rcPosLineConfigEntry 10 }

rcPosLineConfigIpxVlanMacAddress OBJECT-TYPE
        SYNTAX        MacAddress
        MAX-ACCESS    read-write
        STATUS        current
        DESCRIPTION   ""
        ::= { rcPosLineConfigEntry 11 }

rcPosLineConfigIpxRemoteMacAddress OBJECT-TYPE
        SYNTAX        MacAddress
        MAX-ACCESS    read-write
        STATUS        current
        DESCRIPTION   ""
        ::= { rcPosLineConfigEntry 12 }


-- POS Sonet traps --

rcPosSonetTrap        OBJECT IDENTIFIER ::= { rcPos 5 }

rcPosSonetTrapType OBJECT-TYPE
        SYNTAX        INTEGER {
                              sectionAlarm(1),
                              lineAlarm(2),
                              pathAlarm(3)    
                      }
        MAX-ACCESS    read-only
        STATUS        current
        DESCRIPTION   "Used to indicate a particular type of Sonet 
                      trap."
        ::= { rcPosSonetTrap 1 }

rcPosSonetTrapIndication OBJECT-TYPE
        SYNTAX        INTEGER {
                            noDefect(1),         
                            sectionLossOfSignal(2),  
                            sectionLossOfFrame(3),
                            lineAlarmIndication(4),
                            lineRemoteDefectIndication(5),
                            pathLossOfPointer(6),
                            pathAlarmIndication(7),
                            pathRemoteDefectIndication(8),
                            pathUnequipped(9),
                            pathSignalLabelMismatch(10),
                            pathTraceMismatch(11)
                      } 
        MAX-ACCESS    read-only
        STATUS        current
        DESCRIPTION   "Used to indicate an indication for a Sonet trap."
        ::= { rcPosSonetTrap 2 }

-- Pos Sio Card Config Table

rcPosSioCardConfigTable OBJECT-TYPE
        SYNTAX        SEQUENCE OF RcPosSioCardConfigEntry
        MAX-ACCESS    not-accessible
        STATUS        current
        DESCRIPTION   "Pos Sio Card Config Table"
        ::= { rcPos 6 }

rcPosSioCardConfigEntry OBJECT-TYPE
        SYNTAX        RcPosSioCardConfigEntry
        MAX-ACCESS    not-accessible
        STATUS        current
        DESCRIPTION   "Entry containing information of Pos Sio Card Config."
        INDEX         { rcPosSioCardConfigSlotIndex }
        ::= { rcPosSioCardConfigTable 1 }

RcPosSioCardConfigEntry ::= SEQUENCE {
                rcPosSioCardConfigSlotIndex     Integer32,
                rcPosSioCardConfigAction        INTEGER,
                rcPosSioCardConfigTraceMode     INTEGER,
                rcPosSioCardConfigImageFileName DisplayString
        }

rcPosSioCardConfigSlotIndex OBJECT-TYPE
        SYNTAX        Integer32 (0..2147483647)
        MAX-ACCESS    read-only
        STATUS        current
        DESCRIPTION   "slot Index."
        ::= { rcPosSioCardConfigEntry 1 }

rcPosSioCardConfigAction OBJECT-TYPE
        SYNTAX        INTEGER {
                          other(0),
                          reset(1)
                      }
        MAX-ACCESS    read-write
        STATUS        current
        DESCRIPTION   ""
        ::= { rcPosSioCardConfigEntry 2 }

rcPosSioCardConfigTraceMode OBJECT-TYPE
        SYNTAX        INTEGER {
                          other(0),
                          traceOn(1)
                      }
        MAX-ACCESS    read-write
        STATUS        current
        DESCRIPTION   ""
        ::= { rcPosSioCardConfigEntry 3 }

rcPosSioCardConfigImageFileName OBJECT-TYPE
        SYNTAX        DisplayString 
        MAX-ACCESS    read-only
        STATUS        current
        DESCRIPTION   "POS Image file name."
        ::= { rcPosSioCardConfigEntry 4 }



-- POS Operation Status Table

rcPosOperStatusTable OBJECT-TYPE
        SYNTAX        SEQUENCE OF RcPosOperStatusEntry
        MAX-ACCESS    not-accessible
        STATUS        current
        DESCRIPTION   ""
   ::= { rcPos 7 }

rcPosOperStatusEntry OBJECT-TYPE
   SYNTAX        RcPosOperStatusEntry
   MAX-ACCESS     not-accessible
   STATUS         current
   DESCRIPTION   ""
   INDEX         { rcPosOperStatusIndex }
   ::= { rcPosOperStatusTable 1 }

RcPosOperStatusEntry ::=
      SEQUENCE {
                rcPosOperStatusIndex               InterfaceIndex,
                rcPosOperStatusLqrStatus           Integer32,
                rcPosOperStatusLineLqrThreshold    Integer32,
                rcPosOperStatusLinkMagicNumber     Integer32,
                rcPosOperStatusLinePppStp          EnableValue
      }

rcPosOperStatusIndex OBJECT-TYPE
        SYNTAX        InterfaceIndex
        MAX-ACCESS    read-only
        STATUS        current
        DESCRIPTION   "pos ifIndex."
        ::= { rcPosOperStatusEntry 1 }

rcPosOperStatusLqrStatus   OBJECT-TYPE
     SYNTAX      Integer32
     MAX-ACCESS  read-only
     STATUS      current
     DESCRIPTION
            "Operational status of pppLqrConfigStatus."
     ::= { rcPosOperStatusEntry 2 }

rcPosOperStatusLineLqrThreshold OBJECT-TYPE
        SYNTAX        Integer32
        MAX-ACCESS    read-only
        STATUS        current
        DESCRIPTION   "."
        ::= { rcPosOperStatusEntry 3 }

rcPosOperStatusLinkMagicNumber  OBJECT-TYPE
     SYNTAX      Integer32
     MAX-ACCESS  read-only
     STATUS      current
     DESCRIPTION
           "."
     ::= { rcPosOperStatusEntry 4 }

rcPosOperStatusLinePppStp OBJECT-TYPE
        SYNTAX        EnableValue
        MAX-ACCESS    read-only
        STATUS        current
        DESCRIPTION   ""
        ::= { rcPosOperStatusEntry 5 }


-- Link Flap Detect Group

rcLinkFlapDetectAutoPortDownEnable OBJECT-TYPE
        SYNTAX        	TruthValue
        MAX-ACCESS      	read-write
        STATUS        	current
        DESCRIPTION   	"Used to enable/disable the Link Flap Detect
			feature.  When enabled this feature will monitor
			the number of times a port goes down during a
			certain interval.  If the number exceeds a given
			bound the port will be forced out-of-service." 
        ::= { rcLinkFlapDetect 1 }

rcLinkFlapDetectSendTrap OBJECT-TYPE
        SYNTAX        	TruthValue
        MAX-ACCESS      	read-write
        STATUS        	current
        DESCRIPTION   	"Used to configure whether a trap should be
			sent if the port is forced out-of-service."	
        ::= { rcLinkFlapDetect 2 }

rcLinkFlapDetectFrequency OBJECT-TYPE
        SYNTAX        	INTEGER (1..9999)
        MAX-ACCESS      	read-write
        STATUS        	current
        DESCRIPTION   	"Used to configure the number of times the port
			can go down." 
        ::= { rcLinkFlapDetect 3 }

rcLinkFlapDetectInterval OBJECT-TYPE
        SYNTAX        	INTEGER (2..600)
        MAX-ACCESS     	read-write
        STATUS        	current
        DESCRIPTION   	"Used to configure the interval (in minutes)."
        ::= { rcLinkFlapDetect 4 }


-- Radius Group
-- Radius Global Infomation

rcRadiusGlobal   OBJECT IDENTIFIER       ::= { rcRadius 1 }

rcRadiusGlobalEnable OBJECT-TYPE
        SYNTAX        TruthValue
        MAX-ACCESS    read-write
        STATUS        current
        DESCRIPTION   "Enable/disable this feature."
	DEFVAL 	      { false }
        ::= { rcRadiusGlobal 1 }

rcRadiusGlobalMaxNumberServer OBJECT-TYPE
        SYNTAX        INTEGER (1..10)
        MAX-ACCESS    read-write
        STATUS        current
        DESCRIPTION   "Maximum number of RADIUS servers."
	DEFVAL 	      { 10 }
        ::= { rcRadiusGlobal 2 }

rcRadiusGlobalAttributeValue OBJECT-TYPE
        SYNTAX        INTEGER (192..240)
        MAX-ACCESS    read-write
        STATUS        current
        DESCRIPTION   "Integer value for Access-Priority attribute."
        DEFVAL        { 192 }
        ::= { rcRadiusGlobal 3 }

rcRadiusGlobalServerTableSize OBJECT-TYPE
        SYNTAX          Integer32
        MAX-ACCESS      read-only
        STATUS          current
        DESCRIPTION     "Used to indicate the number of entries in the
                        rcRadiusServerTable."
        ::= { rcRadiusGlobal 4 }

rcRadiusGlobalAcctEnable OBJECT-TYPE
        SYNTAX        TruthValue
        MAX-ACCESS    read-write
        STATUS        current
        DESCRIPTION   "Enable/disable Radius Accounting feature."
        DEFVAL        { false }
        ::= { rcRadiusGlobal 5 }

rcRadiusGlobalAcctAttributeValue OBJECT-TYPE
        SYNTAX        INTEGER (192..240)
        MAX-ACCESS    read-write
        STATUS        current
        DESCRIPTION   "Integer value for User-Command attribute."
        DEFVAL        { 193 }
        ::= { rcRadiusGlobal 6 }

rcRadiusGlobalAcctIncludeCli OBJECT-TYPE
        SYNTAX        TruthValue
        MAX-ACCESS    read-write
        STATUS        current
        DESCRIPTION   "Include/Exclude cli-commands in radius
                       acccounting updates."
        DEFVAL        { false }
        ::= { rcRadiusGlobal 7 }

rcRadiusGlobalClearStat OBJECT-TYPE
        SYNTAX        TruthValue
        MAX-ACCESS    read-write
        STATUS        current
        DESCRIPTION   "Clear Radius Statistic for all servers 
                       configured."
        DEFVAL        { false }
        ::= { rcRadiusGlobal 8 }

rcRadiusGlobalMcastAttributeValue OBJECT-TYPE
        SYNTAX        INTEGER (0..255)
        MAX-ACCESS    read-write
        STATUS        current
        DESCRIPTION   "Integer value for multicast address vendor
                       specific attribute."
        DEFVAL        { 90 }
        ::= { rcRadiusGlobal 9 }

rcRadiusGlobalAuthInfoAttributeValue OBJECT-TYPE
        SYNTAX        INTEGER (0..255)
        MAX-ACCESS    read-write
        STATUS        current
        DESCRIPTION   "Integer value for Auth-Info vendor specific attribute."
        DEFVAL        { 91 }
        ::= { rcRadiusGlobal 10 }

rcRadiusGlobalCommandAccess OBJECT-TYPE
        SYNTAX        INTEGER (192..240)
        MAX-ACCESS    read-write
        STATUS        current
        DESCRIPTION   "Integer value for Command-Access attribute."
        DEFVAL        { 194 }
        ::= { rcRadiusGlobal 11 }

rcRadiusGlobalCliCommands OBJECT-TYPE
        SYNTAX        INTEGER (192..240)
        MAX-ACCESS    read-write
        STATUS        current
        DESCRIPTION   "Integer value for Cli-Command attribute."
        DEFVAL        { 195 }
        ::= { rcRadiusGlobal 12 }

rcRadiusGlobalIgapLogFSize OBJECT-TYPE
        SYNTAX        INTEGER (50..8192)
        MAX-ACCESS    read-write
        STATUS        current
        DESCRIPTION   "Maximum size for the IGAP accounting time-out
                       log file in KB."
        DEFVAL        { 512 }
        ::= { rcRadiusGlobal 13 }

rcRadiusGlobalCliProfEnable OBJECT-TYPE
        SYNTAX        TruthValue
        MAX-ACCESS    read-write
        STATUS        current
        DESCRIPTION   "Enable/disable Radius CLI Profiling."
        DEFVAL        { false }
        ::= { rcRadiusGlobal 14 }

rcRadiusGlobalAuthInvalidServerAddress OBJECT-TYPE
        SYNTAX        Counter32
        MAX-ACCESS    read-only
        STATUS        current
        DESCRIPTION   "Number of Access Responses from unknown or 
                       invalid Radius servers."
        ::= { rcRadiusGlobal 15 }

rcRadiusGlobalSourceIpFlag OBJECT-TYPE
        SYNTAX        TruthValue
        MAX-ACCESS    read-write
        STATUS        current
        DESCRIPTION   "Flag to include configured IP address as source 
                       address in RADIUS packets."
        DEFVAL        { false }
        ::= { rcRadiusGlobal 16 }

rcRadiusGlobalCliCmdCount OBJECT-TYPE
        SYNTAX        INTEGER (1..40)
        MAX-ACCESS    read-write
        STATUS        current
        DESCRIPTION   "Integer value for Cli-Command-count."
        DEFVAL        { 40 }
        ::= { rcRadiusGlobal 18 }


-- Radius Serv Table 

rcRadiusServTable OBJECT-TYPE
        SYNTAX        SEQUENCE OF RcRadiusServEntry
        MAX-ACCESS    not-accessible
        STATUS        deprecated
        DESCRIPTION   "The RADIUS table (0 to 10 entries).  This
                      table lists the information of the RADIUS server."
        ::= { rcRadius 3 }

rcRadiusServEntry OBJECT-TYPE
        SYNTAX        RcRadiusServEntry
        MAX-ACCESS    not-accessible
        STATUS        deprecated
        DESCRIPTION   "A RADIUS server table entry."
        INDEX         { rcRadiusServAddress, rcRadiusServUsedBy }
        ::= { rcRadiusServTable 1 }

RcRadiusServEntry ::=
        SEQUENCE {
                rcRadiusServPriority            INTEGER,
                rcRadiusServAddress             IpAddress,
                rcRadiusServTimeOut             INTEGER,
                rcRadiusServEnable              TruthValue,
                rcRadiusServMaxRetries          INTEGER,
                rcRadiusServUdpPort             INTEGER,
                rcRadiusServSecretKey           DisplayString,
                rcRadiusServAccessRequests      Counter32,
                rcRadiusServAccessAccepts       Counter32,
                rcRadiusServAccessRejects       Counter32,
                rcRadiusServBadResponses        Counter32,
                rcRadiusServPendingRequests     Counter32,
                rcRadiusServClientRetries       Counter32,
                rcRadiusServRowStatus           RowStatus,
                rcRadiusServAcctEnable          TruthValue,
                rcRadiusServAcctUdpPort         INTEGER,
                rcRadiusServAcctOnRequests      Counter32,
                rcRadiusServAcctOffRequests     Counter32,
                rcRadiusServAcctStartRequests   Counter32,
                rcRadiusServAcctStopRequests    Counter32,
                rcRadiusServAcctInterimRequests Counter32,
                rcRadiusServAcctBadResponses    Counter32,
                rcRadiusServAcctPendingRequests Counter32,
                rcRadiusServAcctClientRetries   Counter32,
                rcRadiusServUsedBy              INTEGER,
                rcRadiusServNasIpAddress        IpAddress,
                rcRadiusServRoundTripTime       DisplayString,
                rcRadiusServAccessChallanges    Counter32,
                rcRadiusServSourceIpAddr        IpAddress

        }

rcRadiusServPriority OBJECT-TYPE
        SYNTAX        INTEGER (1..10)
        MAX-ACCESS    read-write
        STATUS        deprecated
        DESCRIPTION   "Server priority, used to control which server to choose
                       first to send authentication."
	DEFVAL 	      { 10 }
        ::= { rcRadiusServEntry 1 }

rcRadiusServAddress OBJECT-TYPE
        SYNTAX        IpAddress
        MAX-ACCESS    read-write
        STATUS        deprecated
        DESCRIPTION   "Server IP address of the RADIUS authentication server
                       referred to in this table entry."
        ::= { rcRadiusServEntry 2 }

rcRadiusServTimeOut OBJECT-TYPE
        SYNTAX        INTEGER (1..20)
        MAX-ACCESS    read-write
        STATUS        deprecated
        DESCRIPTION   "The time interval in seconds before the client 
                       retransmit the packet."
	DEFVAL 	      { 3 }
        ::= { rcRadiusServEntry 3 }

rcRadiusServEnable  OBJECT-TYPE
        SYNTAX        TruthValue 
        MAX-ACCESS    read-write
        STATUS        deprecated
        DESCRIPTION   "Enable or disable this server."
	DEFVAL 	      { true }
        ::= { rcRadiusServEntry 4 }

rcRadiusServMaxRetries OBJECT-TYPE
        SYNTAX        INTEGER (0..6)
        MAX-ACCESS    read-write
        STATUS        deprecated
        DESCRIPTION   "Maximum number of retransmissions."
	DEFVAL 	      { 1 }
        ::= { rcRadiusServEntry 5 }

rcRadiusServUdpPort OBJECT-TYPE
        SYNTAX        INTEGER (1..65536)
        MAX-ACCESS    read-write
        STATUS        deprecated
        DESCRIPTION   "The UDP port the client is using to send requests
                       to this server."
	DEFVAL 	      { 1812 }
        ::= { rcRadiusServEntry 6 }

rcRadiusServSecretKey OBJECT-TYPE
        SYNTAX        DisplayString (SIZE (0..32)) 
        MAX-ACCESS    read-write
        STATUS        deprecated
        DESCRIPTION   "The identifier of the RADIUS authentication client."
        ::= { rcRadiusServEntry 7 }

rcRadiusServAccessRequests OBJECT-TYPE
        SYNTAX          Counter32
        MAX-ACCESS      read-only
        STATUS          deprecated
        DESCRIPTION     "The number of RADIUS access-response packets sent to 
                         this server. This does not include retransmissions."
        ::= { rcRadiusServEntry 8 }

rcRadiusServAccessAccepts OBJECT-TYPE
        SYNTAX          Counter32
        MAX-ACCESS      read-only
        STATUS          deprecated
        DESCRIPTION     "The number of RADIUS access-accept packets (valid or 
                         invalid) received from this server."
        ::= { rcRadiusServEntry 9 }

rcRadiusServAccessRejects OBJECT-TYPE
        SYNTAX          Counter32
        MAX-ACCESS      read-only
        STATUS          deprecated
        DESCRIPTION     "The number of RADIUS access-reject packets (valid or 
                         invalid) received from this server."
        ::= { rcRadiusServEntry 10 }

rcRadiusServBadResponses OBJECT-TYPE
        SYNTAX          Counter32
        MAX-ACCESS      read-only
        STATUS          deprecated
        DESCRIPTION     "The number of RADIUS invalid access-response packets 
                         received from this server."
        ::= { rcRadiusServEntry 11 }

rcRadiusServPendingRequests OBJECT-TYPE
        SYNTAX          Counter32
        MAX-ACCESS      read-only
        STATUS          deprecated
        DESCRIPTION     "The number of RADIUS access-request packets destined 
                         for this server that have not yet timed out or 
                         received a response. This variable is incremented 
                         when an access-request is sent and decremented due 
                         to receipt of an access-accept, access-reject, a 
                         timeout or retransmission."
        ::= { rcRadiusServEntry 12 }

rcRadiusServClientRetries OBJECT-TYPE
        SYNTAX          Counter32
        MAX-ACCESS      read-only
        STATUS          deprecated
        DESCRIPTION     "The number of authentication retransmission to 
                         this server."
        ::= { rcRadiusServEntry 13 }

rcRadiusServRowStatus OBJECT-TYPE
        SYNTAX        RowStatus
        MAX-ACCESS    read-write
        STATUS        deprecated
        DESCRIPTION   "Used to create/delete entries."
        ::= { rcRadiusServEntry 14 }

rcRadiusServAcctEnable OBJECT-TYPE
        SYNTAX        TruthValue
        MAX-ACCESS    read-write
        STATUS        deprecated
        DESCRIPTION   "Enable or disable Radius Accounting on this server."
        DEFVAL        { true }
        ::= { rcRadiusServEntry 15 }

rcRadiusServAcctUdpPort OBJECT-TYPE
        SYNTAX        INTEGER (1..65536)
        MAX-ACCESS    read-write
        STATUS        deprecated
        DESCRIPTION   "The UDP port the client used to send accounting
                       requests to this server."
        DEFVAL        { 1813 }
        ::= { rcRadiusServEntry 16 }

rcRadiusServAcctOnRequests OBJECT-TYPE
        SYNTAX          Counter32
        MAX-ACCESS      read-only
        STATUS          deprecated
        DESCRIPTION     "The number of RADIUS accounting-on packets sent to
                         this server. This does not include retransmissions."
        ::= { rcRadiusServEntry 17 }

rcRadiusServAcctOffRequests OBJECT-TYPE
        SYNTAX          Counter32
        MAX-ACCESS      read-only
        STATUS          deprecated
        DESCRIPTION     "The number of RADIUS accounting-off packets sent to
                         this server. This does not include retransmissions."
        ::= { rcRadiusServEntry 18 }

rcRadiusServAcctStartRequests OBJECT-TYPE
        SYNTAX          Counter32
        MAX-ACCESS      read-only
        STATUS          deprecated
        DESCRIPTION     "The number of RADIUS accounting-start packets sent to
                         this server. This does not include retransmissions."
        ::= { rcRadiusServEntry 19 }


rcRadiusServAcctStopRequests OBJECT-TYPE
        SYNTAX          Counter32
        MAX-ACCESS      read-only
        STATUS          deprecated
        DESCRIPTION     "The number of RADIUS accounting-stop packets sent to
                         this server. This does not include retransmissions."
        ::= { rcRadiusServEntry 20 }

rcRadiusServAcctInterimRequests OBJECT-TYPE
        SYNTAX          Counter32
        MAX-ACCESS      read-only
        STATUS          deprecated
        DESCRIPTION     "The number of RADIUS accounting-interim packets sent to
                         this server. This does not include retransmissions."
        ::= { rcRadiusServEntry 21 }

rcRadiusServAcctBadResponses OBJECT-TYPE
        SYNTAX          Counter32
        MAX-ACCESS      read-only
        STATUS          deprecated
        DESCRIPTION     "The number of Invalid responses received from this
                         server."
        ::= { rcRadiusServEntry 22 }

rcRadiusServAcctPendingRequests OBJECT-TYPE
        SYNTAX          Counter32
        MAX-ACCESS      read-only
        STATUS          deprecated
        DESCRIPTION     "The number of RADIUS accounting packets that are waiting
                         be sent to this server. This variable is incremented
                         whenever any accounting-request is sent to this server and
                         decremented when an acknowledgement is received or timeout
                         occurs."
        ::= { rcRadiusServEntry 23 }

rcRadiusServAcctClientRetries OBJECT-TYPE
        SYNTAX          Counter32
        MAX-ACCESS      read-only
        STATUS          deprecated
        DESCRIPTION     "The number of RADIUS accounting packets retransmitted
                         to this server."
        ::= { rcRadiusServEntry 24 }

rcRadiusServUsedBy OBJECT-TYPE
        SYNTAX        INTEGER { 
                         cli(1),
                         igap(2),
                         snmp(3),
                         eap(4),
                         web(5)
                      }
        MAX-ACCESS    read-only
        STATUS        deprecated
        DESCRIPTION   "cli(1): for cli login, igap(2): for igap,snmp(3):
                       for snmp login, eap(4) for EAP PAE Authenticator
                       web(5) for web-server(http/https) login." 
        ::= { rcRadiusServEntry 25 }

rcRadiusServNasIpAddress OBJECT-TYPE
        SYNTAX          IpAddress
        MAX-ACCESS      read-only
        STATUS          deprecated
        DESCRIPTION     "RADIUS Client NAS Identifier for this server."
        ::= { rcRadiusServEntry 26 }

rcRadiusServRoundTripTime OBJECT-TYPE
        SYNTAX          DisplayString (SIZE(0..20))
        MAX-ACCESS      read-only
        STATUS          deprecated
        DESCRIPTION     "Time different between the instance when
                         a RADIUS request is sent and the
                         corresponding response is received."
        ::= { rcRadiusServEntry 27 }

rcRadiusServAccessChallanges OBJECT-TYPE
        SYNTAX          Counter32
        MAX-ACCESS      read-only
        STATUS          deprecated
        DESCRIPTION     "The number of RADIUS access-challanges packets
                         sent to this server. This does not include
                         retransmission."
        ::= { rcRadiusServEntry 28 }

rcRadiusServSourceIpAddr OBJECT-TYPE
        SYNTAX          IpAddress
        MAX-ACCESS      read-write
        STATUS          deprecated
        DESCRIPTION     "source IP address RADIUS packets."
        ::= { rcRadiusServEntry 29 }


rcRadiusGlobalSnmp   OBJECT IDENTIFIER       ::= { rcRadius 4 }

rcRadiusGlobalSnmpEnable OBJECT-TYPE
        SYNTAX        TruthValue
        MAX-ACCESS    read-write
        STATUS        current
        DESCRIPTION   "Enable/disable snmp radius authentication."
	       DEFVAL        { false }
        ::= { rcRadiusGlobalSnmp 1 }

rcRadiusGlobalSnmpAcctEnable OBJECT-TYPE
        SYNTAX        TruthValue
        MAX-ACCESS    read-write
        STATUS        current
        DESCRIPTION   "Enable/disable Radius Accounting for SNMP."
	       DEFVAL        { false }
        ::= { rcRadiusGlobalSnmp 2 }

rcRadiusGlobalSnmpReAuthenticateTimer OBJECT-TYPE
        SYNTAX        INTEGER (30..65535)
        MAX-ACCESS    read-write
        STATUS        current
        DESCRIPTION   "Integer value representing Re-Authenticate
                       Timer in seconds. Timer to be used to Re- 
                       Authenticate a SNMP Session."
        DEFVAL        { 180 }
        ::= { rcRadiusGlobalSnmp 3 }

rcRadiusGlobalSnmpAbortSessionTimer OBJECT-TYPE
        SYNTAX        INTEGER (30..65535)
        MAX-ACCESS      read-write
        STATUS          current
        DESCRIPTION   "Integer value representing the time in seconds
                       after which the snmp session is considered
                       expired and Radius Accounting Stop message
                       is sent."
        DEFVAL        { 180 }
        ::= { rcRadiusGlobalSnmp 4 }

rcRadiusGlobalSnmpUserName OBJECT-TYPE
        SYNTAX        DisplayString (SIZE(0..20))
        MAX-ACCESS    read-write
        STATUS        current
        DESCRIPTION   "User name for Radius SNMP Accounting."
        ::= { rcRadiusGlobalSnmp 5 }

rcRadiusEapLastRejMac OBJECT-TYPE
        SYNTAX        MacAddress
        MAX-ACCESS    read-only
        STATUS        current
        DESCRIPTION   "Used to store the Last Rejected MAC
                       address on an EAP enabled port."
        ::= { rcRadiusGlobalSnmp 6 }

rcRadiusPaePortNumber OBJECT-TYPE
        SYNTAX        InterfaceIndex
        MAX-ACCESS    read-only
        STATUS        current
        DESCRIPTION   "Used to store the Port Number on which
                       the Mac Intrusion happened."
        ::= { rcRadiusGlobalSnmp 7 }

rcRadiusEapLastAuthMac OBJECT-TYPE
        SYNTAX        MacAddress
        MAX-ACCESS    read-only
        STATUS        current
        DESCRIPTION   "Used to store the Last Authenticated MAC
                       address on an EAP enabled port."
        ::= { rcRadiusGlobalSnmp 8 }

-- Radius Serv Host Table 

rcRadiusServHostTable OBJECT-TYPE
        SYNTAX        SEQUENCE OF RcRadiusServHostEntry
        MAX-ACCESS    not-accessible
        STATUS        current
        DESCRIPTION   "The RADIUS Server Host table (0 to 10 entries).  This
                      table lists the information of the RADIUS server."
        ::= { rcRadius 5 }

rcRadiusServHostEntry OBJECT-TYPE
        SYNTAX        RcRadiusServHostEntry
        MAX-ACCESS    not-accessible
        STATUS        current
        DESCRIPTION   "A RADIUS server table entry."
        INDEX         { rcRadiusServHostAddressType, rcRadiusServHostAddress, rcRadiusServHostUsedBy }
        ::= { rcRadiusServHostTable 1 }

RcRadiusServHostEntry ::=
        SEQUENCE {
	 	rcRadiusServHostAddressType         InetAddressType,
                rcRadiusServHostAddress             InetAddress,
                rcRadiusServHostUsedBy              INTEGER,	
                rcRadiusServHostPriority            Integer32,
                rcRadiusServHostTimeOut             Integer32,
                rcRadiusServHostEnable              TruthValue,
                rcRadiusServHostMaxRetries          Integer32,
                rcRadiusServHostUdpPort             Integer32,
                rcRadiusServHostSecretKey           DisplayString,
                rcRadiusServHostAccessRequests      Counter32,
                rcRadiusServHostAccessAccepts       Counter32,
                rcRadiusServHostAccessRejects       Counter32,
                rcRadiusServHostBadResponses        Counter32,
                rcRadiusServHostPendingRequests     Counter32,
                rcRadiusServHostClientRetries       Counter32,
                rcRadiusServHostRowStatus           RowStatus,
                rcRadiusServHostAcctEnable          TruthValue,
                rcRadiusServHostAcctUdpPort         Integer32,
                rcRadiusServHostAcctOnRequests      Counter32,
                rcRadiusServHostAcctOffRequests     Counter32,
                rcRadiusServHostAcctStartRequests   Counter32,
                rcRadiusServHostAcctStopRequests    Counter32,
                rcRadiusServHostAcctInterimRequests Counter32,
                rcRadiusServHostAcctBadResponses    Counter32,
                rcRadiusServHostAcctPendingRequests Counter32,
                rcRadiusServHostAcctClientRetries   Counter32,
                rcRadiusServHostNasIpAddress        InetAddress,
                rcRadiusServHostRoundTripTime       DisplayString,
                rcRadiusServHostAccessChallanges    Counter32,
                rcRadiusServHostSourceIpAddr        InetAddress
        }

rcRadiusServHostAddressType OBJECT-TYPE
        SYNTAX        InetAddressType
        MAX-ACCESS    not-accessible
        STATUS        current
        DESCRIPTION   "Inet Address Type of radius server host address."
        ::= { rcRadiusServHostEntry 1 }

rcRadiusServHostAddress OBJECT-TYPE
        SYNTAX        InetAddress
        MAX-ACCESS    not-accessible
        STATUS        current
        DESCRIPTION   "Server IP address of the RADIUS authentication server
                       referred to in this table entry."
        ::= { rcRadiusServHostEntry 2 }

rcRadiusServHostUsedBy OBJECT-TYPE
        SYNTAX        INTEGER { 
                         cli(1),
                         snmp(3),
                         eap(4),
                         web(5)
                      }
        MAX-ACCESS    not-accessible
        STATUS        current
        DESCRIPTION   "cli(1): for cli login, igap(2): for igap,snmp(3):
                       for snmp login, eap(4) for EAP PAE Authenticator
                       web(5) for web-server(http/https) login.
		       IGAP is not supported on the VSP 9000." 
        ::= { rcRadiusServHostEntry 3 }

rcRadiusServHostPriority OBJECT-TYPE
        SYNTAX        Integer32 (1..10)
        MAX-ACCESS    read-create
        STATUS        current
        DESCRIPTION   "Server priority, used to control which server to choose
                       first to send authentication."
	DEFVAL 	      { 10 }
        ::= { rcRadiusServHostEntry 4 }

rcRadiusServHostTimeOut OBJECT-TYPE
        SYNTAX        Integer32 (1..20)
        MAX-ACCESS    read-create
        STATUS        current
        DESCRIPTION   "The time interval in seconds before the client 
                       retransmit the packet."
	DEFVAL 	      { 3 }
        ::= { rcRadiusServHostEntry 5 }

rcRadiusServHostEnable  OBJECT-TYPE
        SYNTAX        TruthValue 
        MAX-ACCESS    read-create
        STATUS        current
        DESCRIPTION   "Enable or disable this server."
	DEFVAL 	      { true }
        ::= { rcRadiusServHostEntry 6 }

rcRadiusServHostMaxRetries OBJECT-TYPE
        SYNTAX        Integer32 (0..6)
        MAX-ACCESS    read-create
        STATUS        current
        DESCRIPTION   "Maximum number of retransmissions."
	DEFVAL 	      { 1 }
        ::= { rcRadiusServHostEntry 7 }

rcRadiusServHostUdpPort OBJECT-TYPE
        SYNTAX        Integer32 (1..65536)
        MAX-ACCESS    read-create
        STATUS        current
        DESCRIPTION   "The UDP port the client is using to send requests
                       to this server."
	DEFVAL 	      { 1812 }
        ::= { rcRadiusServHostEntry 8 }

rcRadiusServHostSecretKey OBJECT-TYPE
        SYNTAX        DisplayString (SIZE (0..32)) 
        MAX-ACCESS    read-create
        STATUS        current
        DESCRIPTION   "The identifier of the RADIUS authentication client."
        ::= { rcRadiusServHostEntry 9 }

rcRadiusServHostAccessRequests OBJECT-TYPE
        SYNTAX          Counter32
        MAX-ACCESS      read-only
        STATUS          current
        DESCRIPTION     "The number of RADIUS access-response packets sent to 
                         this server. This does not include retransmissions."
        ::= { rcRadiusServHostEntry 10 }

rcRadiusServHostAccessAccepts OBJECT-TYPE
        SYNTAX          Counter32
        MAX-ACCESS      read-only
        STATUS          current
        DESCRIPTION     "The number of RADIUS access-accept packets (valid or 
                         invalid) received from this server."
        ::= { rcRadiusServHostEntry 11 }

rcRadiusServHostAccessRejects OBJECT-TYPE
        SYNTAX          Counter32
        MAX-ACCESS      read-only
        STATUS          current
        DESCRIPTION     "The number of RADIUS access-reject packets (valid or 
                         invalid) received from this server."
        ::= { rcRadiusServHostEntry 12 }

rcRadiusServHostBadResponses OBJECT-TYPE
        SYNTAX          Counter32
        MAX-ACCESS      read-only
        STATUS          current
        DESCRIPTION     "The number of RADIUS invalid access-response packets 
                         received from this server."
        ::= { rcRadiusServHostEntry 13 }

rcRadiusServHostPendingRequests OBJECT-TYPE
        SYNTAX          Counter32
        MAX-ACCESS      read-only
        STATUS          current
        DESCRIPTION     "The number of RADIUS access-request packets destined 
                         for this server that have not yet timed out or 
                         received a response. This variable is incremented 
                         when an access-request is sent and decremented due 
                         to receipt of an access-accept, access-reject, a 
                         timeout or retransmission."
        ::= { rcRadiusServHostEntry 14 }

rcRadiusServHostClientRetries OBJECT-TYPE
        SYNTAX          Counter32
        MAX-ACCESS      read-only
        STATUS          current
        DESCRIPTION     "The number of authentication retransmission to 
                         this server."
        ::= { rcRadiusServHostEntry 15 }

rcRadiusServHostRowStatus OBJECT-TYPE
        SYNTAX        RowStatus
        MAX-ACCESS    read-create
        STATUS        current
        DESCRIPTION   "Used to create/delete entries."
        ::= { rcRadiusServHostEntry 16 }

rcRadiusServHostAcctEnable OBJECT-TYPE
        SYNTAX        TruthValue
        MAX-ACCESS    read-create
        STATUS        current
        DESCRIPTION   "Enable or disable Radius Accounting on this server."
        DEFVAL        { true }
        ::= { rcRadiusServHostEntry 17 }

rcRadiusServHostAcctUdpPort OBJECT-TYPE
        SYNTAX        Integer32 (1..65536)
        MAX-ACCESS    read-create
        STATUS        current
        DESCRIPTION   "The UDP port the client used to send accounting
                       requests to this server."
        DEFVAL        { 1813 }
        ::= { rcRadiusServHostEntry 18 }

rcRadiusServHostAcctOnRequests OBJECT-TYPE
        SYNTAX          Counter32
        MAX-ACCESS      read-only
        STATUS          current
        DESCRIPTION     "The number of RADIUS accounting-on packets sent to
                         this server. This does not include retransmissions."
        ::= { rcRadiusServHostEntry 19 }

rcRadiusServHostAcctOffRequests OBJECT-TYPE
        SYNTAX          Counter32
        MAX-ACCESS      read-only
        STATUS          current
        DESCRIPTION     "The number of RADIUS accounting-off packets sent to
                         this server. This does not include retransmissions."
        ::= { rcRadiusServHostEntry 20 }

rcRadiusServHostAcctStartRequests OBJECT-TYPE
        SYNTAX          Counter32
        MAX-ACCESS      read-only
        STATUS          current
        DESCRIPTION     "The number of RADIUS accounting-start packets sent to
                         this server. This does not include retransmissions."
        ::= { rcRadiusServHostEntry 21 }


rcRadiusServHostAcctStopRequests OBJECT-TYPE
        SYNTAX          Counter32
        MAX-ACCESS      read-only
        STATUS          current
        DESCRIPTION     "The number of RADIUS accounting-stop packets sent to
                         this server. This does not include retransmissions."
        ::= { rcRadiusServHostEntry 22 }

rcRadiusServHostAcctInterimRequests OBJECT-TYPE
        SYNTAX          Counter32
        MAX-ACCESS      read-only
        STATUS          current
        DESCRIPTION     "The number of RADIUS accounting-interim packets sent to
                         this server. This does not include retransmissions."
        ::= { rcRadiusServHostEntry 23 }

rcRadiusServHostAcctBadResponses OBJECT-TYPE
        SYNTAX          Counter32
        MAX-ACCESS      read-only
        STATUS          current
        DESCRIPTION     "The number of Invalid responses received from this
                         server."
        ::= { rcRadiusServHostEntry 24 }

rcRadiusServHostAcctPendingRequests OBJECT-TYPE
        SYNTAX          Counter32
        MAX-ACCESS      read-only
        STATUS          current
        DESCRIPTION     "The number of RADIUS accounting packets that are waiting
                         be sent to this server. This variable is incremented
                         whenever any accounting-request is sent to this server and
                         decremented when an acknowledgement is received or timeout
                         occurs."
        ::= { rcRadiusServHostEntry 25 }

rcRadiusServHostAcctClientRetries OBJECT-TYPE
        SYNTAX          Counter32
        MAX-ACCESS      read-only
        STATUS          current
        DESCRIPTION     "The number of RADIUS accounting packets retransmitted
                         to this server."
        ::= { rcRadiusServHostEntry 26 }

rcRadiusServHostNasIpAddress OBJECT-TYPE
        SYNTAX          InetAddress
        MAX-ACCESS      read-only
        STATUS          current
        DESCRIPTION     "RADIUS Client NAS Identifier for this server."
        ::= { rcRadiusServHostEntry 27 }

rcRadiusServHostRoundTripTime OBJECT-TYPE
        SYNTAX          DisplayString (SIZE(0..20))
        MAX-ACCESS      read-only
        STATUS          current
        DESCRIPTION     "Time different between the instance when
                         a RADIUS request is sent and the
                         corresponding response is received."
        ::= { rcRadiusServHostEntry 28 }

rcRadiusServHostAccessChallanges OBJECT-TYPE
        SYNTAX          Counter32
        MAX-ACCESS      read-only
        STATUS          current
        DESCRIPTION     "The number of RADIUS access-challanges packets
                         sent to this server. This does not include
                         retransmission."
        ::= { rcRadiusServHostEntry 29 }

rcRadiusServHostSourceIpAddr OBJECT-TYPE
        SYNTAX          InetAddress
        MAX-ACCESS      read-create
        STATUS          current
        DESCRIPTION     "source IP address RADIUS packets."
        ::= { rcRadiusServHostEntry 30 }

-- --------------------------------------------------
-- rcTacacsGlobal Group
-- --------------------------------------------------

rcTacacsGlobal OBJECT IDENTIFIER ::= { rcTacacs 1 }

rcTacacsGlobalEnable OBJECT-TYPE
    SYNTAX      TruthValue
    MAX-ACCESS  read-write
    STATUS      current
    DESCRIPTION "Enable/disable this feature."
    DEFVAL      { false }
    ::= { rcTacacsGlobal 1 }

rcTacacsGlobalLastUserName OBJECT-TYPE
    SYNTAX      OCTET STRING (SIZE(1..128))
    MAX-ACCESS  read-only
    STATUS      current
    DESCRIPTION "The last user for which authentication was attempted using TACACS+."
    ::= { rcTacacsGlobal 2 }

rcTacacsGlobalLastAddressType OBJECT-TYPE
    SYNTAX      InetAddressType
    MAX-ACCESS  read-only
    STATUS      current
    DESCRIPTION "The type of address for the TACACS+ server that was most recently accessed"
    ::= { rcTacacsGlobal 3 }

rcTacacsGlobalLastAddress OBJECT-TYPE
    SYNTAX      InetAddress
    MAX-ACCESS  read-only
    STATUS      current
    DESCRIPTION "The address of the TACACS+ server that was most recently accessed"
    ::= { rcTacacsGlobal 4 }

rcTacacsAccounting OBJECT-TYPE
    SYNTAX        BITS {
                      cli(0),
                      ppp(1)
                  }
    MAX-ACCESS    read-write
    STATUS        current
    DESCRIPTION   "Determines which application will be accounted by tacacs+." 
    DEFVAL        { {} }   
    ::= { rcTacacsGlobal 5 }

rcTacacsAuthentication OBJECT-TYPE
    SYNTAX        BITS {
                      cli(0),
                      ppp(1),
                      web(2)
                  }
    MAX-ACCESS    read-write
    STATUS        current
    DESCRIPTION   "Determines which application will be authenticated by tacacs+."
    DEFVAL        { {cli} }   
    ::= { rcTacacsGlobal 6 }


-- --------------------------------------------------
-- rcTacacsServerTable
-- --------------------------------------------------

rcTacacsServerTable OBJECT-TYPE
    SYNTAX      SEQUENCE OF RcTacacsServerEntry
    MAX-ACCESS  not-accessible
    STATUS      current
    DESCRIPTION "The (conceptual) table listing the TACACS+ servers with
                 which the client shares a secret."
    ::= { rcTacacs 2 }

rcTacacsServerEntry OBJECT-TYPE
    SYNTAX      RcTacacsServerEntry
    MAX-ACCESS  not-accessible
    STATUS      current
    DESCRIPTION "An entry (conceptual row) representing a TACACS+ server
                 with which the client shares a secret."
    INDEX       { rcTacacsServerAddressType, rcTacacsServerAddress }
    ::= { rcTacacsServerTable 1 }

RcTacacsServerEntry ::= SEQUENCE {
    rcTacacsServerAddressType               InetAddressType,
    rcTacacsServerAddress                          InetAddress,
    rcTacacsServerPortNumber                   InetPortNumber,
    rcTacacsServerConnectionType          INTEGER,
    rcTacacsServerConnectionStatus        INTEGER,
    rcTacacsServerTimeout                          Integer32,
    rcTacacsServerKey                                   OCTET STRING,
    rcTacacsServerSourceIpInterfaceEnabled  TruthValue, 
    rcTacacsServerSourceIpInterfaceType        InetAddressType, 
    rcTacacsServerSourceIpInterface        InetAddress,
    rcTacacsServerPriority                             Integer32,
    rcTacacsServerRowStatus                     RowStatus
}

rcTacacsServerAddressType  OBJECT-TYPE
    SYNTAX      InetAddressType
    MAX-ACCESS  not-accessible
    STATUS      current
    DESCRIPTION  "Specifies the type of IP address used on the Tacacs+ server."
    ::= { rcTacacsServerEntry 1 }

rcTacacsServerAddress OBJECT-TYPE
    SYNTAX      InetAddress
    MAX-ACCESS  not-accessible
    STATUS      current
    DESCRIPTION  "The IP address of the TACACS+ server referred to in this table entry."
    ::= { rcTacacsServerEntry 2 }

rcTacacsServerPortNumber  OBJECT-TYPE
    SYNTAX      InetPortNumber
    MAX-ACCESS  read-create
    STATUS      current
    DESCRIPTION  "The TCP port on which the client establishes a connection to the server.
	                 A value of 0 indicates that the system specified default value is used."
    DEFVAL      { 49 }
    ::= { rcTacacsServerEntry 3 }

rcTacacsServerConnectionType  OBJECT-TYPE
    SYNTAX       INTEGER {
                     singleConnection(1),
                     perSessionConnection(2)
                 }
    MAX-ACCESS   read-create
    STATUS       current
    DESCRIPTION  "Specifies TCP connection type between device and TACACS+ server.
         Either a single open connection between a device and server
         (SingleConnection), or open/close connection per communication
         session (PerSessionConnection)."
    DEFVAL       { perSessionConnection }
    ::= { rcTacacsServerEntry 4 }

rcTacacsServerConnectionStatus  OBJECT-TYPE
    SYNTAX      INTEGER {
                    connected(1),
                    notConnected(2)
                }
    MAX-ACCESS  read-only
    STATUS      current
    DESCRIPTION  "Specifies status TCP connection type between device and TACACS+
         server."
    ::= { rcTacacsServerEntry 5 }

rcTacacsServerTimeout  OBJECT-TYPE
    SYNTAX      Integer32 (10..30)
    MAX-ACCESS  read-create
    STATUS      current
    DESCRIPTION  "The maximum time (in seconds) to wait for this TACACS+ server to reply."
    DEFVAL      { 10 }
    ::= { rcTacacsServerEntry 6 }

rcTacacsServerKey  OBJECT-TYPE
    SYNTAX      OCTET STRING (SIZE(0..128))
    MAX-ACCESS  read-create
    STATUS      current
    DESCRIPTION "Secret key to be shared with this TACACS+ server.
                 If the key length is zero that indicates no encryption is being used."
    DEFVAL      { ''H }
    ::= { rcTacacsServerEntry 7 }

rcTacacsServerSourceIpInterfaceEnabled  OBJECT-TYPE
    SYNTAX      TruthValue
    MAX-ACCESS  read-create
    STATUS      current
    DESCRIPTION  "Specifies whether source address specification is enabled."
    DEFVAL { false }
    ::= { rcTacacsServerEntry 8 }

rcTacacsServerSourceIpInterfaceType  OBJECT-TYPE
    SYNTAX      InetAddressType
    MAX-ACCESS  read-create
    STATUS      current
    DESCRIPTION  "Specifies the type of IP address used on the interface that
         connects to the Tacacs+ server.  If this value is unknown(0),
         then a system-wide default value will be used."
    DEFVAL { unknown }
    ::= { rcTacacsServerEntry 9 }

rcTacacsServerSourceIpInterface OBJECT-TYPE
    SYNTAX      InetAddress
    MAX-ACCESS  read-create
    STATUS      current
    DESCRIPTION  "IP address of the interface to use with this server."
    DEFVAL      { ''H }
    ::= { rcTacacsServerEntry 10 }

rcTacacsServerPriority OBJECT-TYPE
    SYNTAX      Integer32 (1..65535)
    MAX-ACCESS  read-create
    STATUS      current
    DESCRIPTION  "Determines the order in which the TACACS+ servers will be used,
         when 1 is the highest priority. If more than one server share
         the same priority - they will be used in  lexicographic order
         (the order of entries in this table)."
    DEFVAL      { 1 }
    ::= { rcTacacsServerEntry 11 }

rcTacacsServerRowStatus OBJECT-TYPE
    SYNTAX      RowStatus
    MAX-ACCESS  read-create
    STATUS      current
    DESCRIPTION "The row status variable, can be set to destroy or createAndGo."
    ::= { rcTacacsServerEntry 12 }

-- IGMP

rcIgmpInterfaceExtnTable OBJECT-TYPE
        SYNTAX        SEQUENCE OF RcIgmpInterfaceExtnEntry
        MAX-ACCESS    not-accessible
        STATUS        current
        DESCRIPTION   ""
        ::= { rcIgmp 1 }

rcIgmpInterfaceExtnEntry OBJECT-TYPE
        SYNTAX        RcIgmpInterfaceExtnEntry
        MAX-ACCESS    not-accessible
        STATUS        current
        DESCRIPTION   ""
        INDEX         { rcIgmpInterfaceExtnIfIndex }
        ::= { rcIgmpInterfaceExtnTable 1 }

RcIgmpInterfaceExtnEntry ::=
        SEQUENCE {
                rcIgmpInterfaceExtnIfIndex               InterfaceIndex,
                rcIgmpInterfaceExtnSnoopEnable           TruthValue,
                rcIgmpInterfaceExtnProxySnoopEnable      TruthValue,
                rcIgmpInterfaceExtnMaxAdvertiseInterval  INTEGER,
                rcIgmpInterfaceExtnMinAdvertiseInterval  INTEGER,
                rcIgmpInterfaceExtnMaxInitialAdvertiseInterval Integer32,
                rcIgmpInterfaceExtnMaxInitialAdvertments Integer32,
                rcIgmpInterfaceExtnNeighborDeadInterval  Integer32,
                rcIgmpInterfaceExtnFastLeaveEnable       TruthValue,
                rcIgmpInterfaceExtnFastLeavePortMembers  PortSet,
                rcIgmpInterfaceExtnMrdiscEnable          TruthValue,
                rcIgmpInterfaceExtnDiscoveredRouterPorts PortSet,
                rcIgmpInterfaceExtnSnoopMRouterPorts     PortSet,
                rcIgmpInterfaceExtnSnoopActiveMRouterPorts PortSet,
                rcIgmpInterfaceExtnSnoopMRouterExpiration Integer32,
                rcIgmpInterfaceExtnFlushAction            INTEGER,
                rcIgmpInterfaceExtnRouterAlertEnable      EnableValue,
                rcIgmpInterfaceExtnSsmEnable             TruthValue,
                rcIgmpInterfaceExtnAccntEnable           EnableValue,
                rcIgmpInterfaceExtnAuthEnable            EnableValue,
                rcIgmpInterfaceExtnStreamLimitEnable     EnableValue,
                rcIgmpInterfaceExtnMaxStreams            Integer32,
                rcIgmpInterfaceExtnNumStreams            Integer32,
                rcIgmpInterfaceExtnNewQuerier            IpAddress,
                rcIgmpInterfaceExtnSnoopQuerierEnable    TruthValue,
                rcIgmpInterfaceExtnSnoopQuerierAddr      IpAddress,
                rcIgmpInterfaceExtnMvrEnable             TruthValue,
                rcIgmpInterfaceExtnMvrProxyEnable        TruthValue,
                rcIgmpInterfaceExtnDynamicDowngradeEnable TruthValue,
                rcIgmpInterfaceExtnCompatibilityModeEnable TruthValue,
                rcIgmpInterfaceExtnOperVersion            INTEGER,
                rcIgmpInterfaceExtnExplicitHostTrackingEnable TruthValue
        }

rcIgmpInterfaceExtnIfIndex OBJECT-TYPE
        SYNTAX        InterfaceIndex
        MAX-ACCESS    read-only
        STATUS        current
        DESCRIPTION   "ifindex."
        ::= { rcIgmpInterfaceExtnEntry 1 }

rcIgmpInterfaceExtnSnoopEnable OBJECT-TYPE
        SYNTAX        TruthValue
        MAX-ACCESS    read-write
        STATUS        current
        DESCRIPTION   "enable snoop."
        ::= { rcIgmpInterfaceExtnEntry 2 }

rcIgmpInterfaceExtnProxySnoopEnable OBJECT-TYPE
        SYNTAX        TruthValue
        MAX-ACCESS    read-write
        STATUS        current
        DESCRIPTION   "enable proxy snoop."
        ::= { rcIgmpInterfaceExtnEntry 3 }

rcIgmpInterfaceExtnMaxAdvertiseInterval OBJECT-TYPE
        SYNTAX        INTEGER(2..180)
        MAX-ACCESS    read-write
        STATUS        current
        DESCRIPTION   ""
        DEFVAL        { 20 }
        ::= { rcIgmpInterfaceExtnEntry 4 }

rcIgmpInterfaceExtnMinAdvertiseInterval OBJECT-TYPE
        SYNTAX        INTEGER(3..180)
        MAX-ACCESS    read-write
        STATUS        current
        DESCRIPTION   ""
        DEFVAL        { 15 }
        ::= { rcIgmpInterfaceExtnEntry 5 }

rcIgmpInterfaceExtnMaxInitialAdvertiseInterval OBJECT-TYPE
        SYNTAX        Integer32(2..180) 
        MAX-ACCESS    read-write
        STATUS        current
        DESCRIPTION   ""
        DEFVAL        { 2 }
        ::= { rcIgmpInterfaceExtnEntry 6 }

rcIgmpInterfaceExtnMaxInitialAdvertments OBJECT-TYPE
        SYNTAX        Integer32(2..15)
        MAX-ACCESS    read-write
        STATUS        current
        DESCRIPTION   ""
        DEFVAL        { 3 }
        ::= { rcIgmpInterfaceExtnEntry 7 }

rcIgmpInterfaceExtnNeighborDeadInterval OBJECT-TYPE
        SYNTAX        Integer32(2..180)
        MAX-ACCESS    read-write
        STATUS        current
        DESCRIPTION   ""
        DEFVAL        { 60 }
        ::= { rcIgmpInterfaceExtnEntry 8 }

rcIgmpInterfaceExtnFastLeaveEnable OBJECT-TYPE
        SYNTAX        TruthValue
        MAX-ACCESS    read-write
        STATUS        current
        DESCRIPTION   "Enable fast leave on this interface."
        DEFVAL        { false }
        ::= { rcIgmpInterfaceExtnEntry 9 }

rcIgmpInterfaceExtnFastLeavePortMembers OBJECT-TYPE
        SYNTAX        PortSet
        MAX-ACCESS    read-write
        STATUS        current
        DESCRIPTION   "The set of ports that are enabled for fast leave."
        ::= { rcIgmpInterfaceExtnEntry 10 }

rcIgmpInterfaceExtnMrdiscEnable OBJECT-TYPE
        SYNTAX        TruthValue
        MAX-ACCESS    read-write
        STATUS        current
        DESCRIPTION   "Enable/disable multicast router discovery."
        ::= { rcIgmpInterfaceExtnEntry 11 }

rcIgmpInterfaceExtnDiscoveredRouterPorts OBJECT-TYPE
        SYNTAX        PortSet
        MAX-ACCESS    read-only
        STATUS        current
        DESCRIPTION   "list of ports that discovered by 
                       IGMP Multicast router discovery 
                       (MRDISC) protocol."
        ::= { rcIgmpInterfaceExtnEntry 12 }

rcIgmpInterfaceExtnSnoopMRouterPorts OBJECT-TYPE
        SYNTAX        PortSet
        MAX-ACCESS    read-write
        STATUS        current
        DESCRIPTION   "The set of ports in this interface that provide
                      connectivity to an IP Multicast router."
        ::= { rcIgmpInterfaceExtnEntry 13 }

rcIgmpInterfaceExtnSnoopActiveMRouterPorts OBJECT-TYPE
        SYNTAX        PortSet
        MAX-ACCESS    read-only
        STATUS        current
        DESCRIPTION   "Active ports."
        ::= { rcIgmpInterfaceExtnEntry 14 }

rcIgmpInterfaceExtnSnoopMRouterExpiration OBJECT-TYPE
        SYNTAX        Integer32
        MAX-ACCESS    read-only
        STATUS        current
        DESCRIPTION   "Multicast querier router aging time out."
        ::= { rcIgmpInterfaceExtnEntry 15 }

rcIgmpInterfaceExtnFlushAction OBJECT-TYPE
        SYNTAX        INTEGER {
                         none(1),
                         flushGrpMember(2),
                         flushMrouter(3),
                         flushSender(4)
                      }
        MAX-ACCESS    read-write
        STATUS        current
        DESCRIPTION   "IGMP flush action."
        ::= { rcIgmpInterfaceExtnEntry 16 }

rcIgmpInterfaceExtnRouterAlertEnable OBJECT-TYPE
        SYNTAX        EnableValue
        MAX-ACCESS    read-write
        STATUS        current
        DESCRIPTION   "Enable Router Alert Check."
        ::= { rcIgmpInterfaceExtnEntry 17 }

rcIgmpInterfaceExtnSsmEnable OBJECT-TYPE
        SYNTAX        TruthValue
        MAX-ACCESS    read-write
        STATUS        current
        DESCRIPTION   "enable SSM."
        ::= { rcIgmpInterfaceExtnEntry 18 }

rcIgmpInterfaceExtnAccntEnable OBJECT-TYPE
        SYNTAX        EnableValue
        MAX-ACCESS    read-write
        STATUS        current
        DESCRIPTION   "enable/disable accounting."
        DEFVAL        { enable }
        ::= { rcIgmpInterfaceExtnEntry 20 }

rcIgmpInterfaceExtnAuthEnable OBJECT-TYPE
        SYNTAX        EnableValue
        MAX-ACCESS    read-write
        STATUS        current
        DESCRIPTION   "enable/disable authentication."
        DEFVAL        { enable }
        ::= { rcIgmpInterfaceExtnEntry 21 }

rcIgmpInterfaceExtnStreamLimitEnable OBJECT-TYPE
        SYNTAX        EnableValue
        MAX-ACCESS    read-write
        STATUS        current
        DESCRIPTION   "Stream Limitation enable/disable."
        DEFVAL        { enable }
        ::= { rcIgmpInterfaceExtnEntry 22 }

rcIgmpInterfaceExtnMaxStreams OBJECT-TYPE
        SYNTAX        Integer32
        MAX-ACCESS    read-write
        STATUS        current
        DESCRIPTION   "Maximum number of stream."
        DEFVAL        { 4 }
        ::= { rcIgmpInterfaceExtnEntry 23 }

rcIgmpInterfaceExtnNumStreams OBJECT-TYPE
        SYNTAX        Integer32
        MAX-ACCESS    read-only
        STATUS        current
        DESCRIPTION   "Current number of streams."
        ::= { rcIgmpInterfaceExtnEntry 24 }

rcIgmpInterfaceExtnNewQuerier OBJECT-TYPE
        SYNTAX        IpAddress
        MAX-ACCESS    read-only
        STATUS        current
        DESCRIPTION   "The address of the New IGMP Querier on
                       the IP subnet to which this interface is
                       attached."
        ::= { rcIgmpInterfaceExtnEntry 25 }

rcIgmpInterfaceExtnSnoopQuerierEnable OBJECT-TYPE
        SYNTAX        TruthValue
        MAX-ACCESS    read-write
        STATUS        current
        DESCRIPTION   "enable snoop querier."
        ::= { rcIgmpInterfaceExtnEntry 26 }

rcIgmpInterfaceExtnSnoopQuerierAddr OBJECT-TYPE
        SYNTAX        IpAddress
        MAX-ACCESS    read-write
        STATUS        current
        DESCRIPTION   "The pseudo address of the IGMP Snoop Querier."
        ::= { rcIgmpInterfaceExtnEntry 27 }

rcIgmpInterfaceExtnMvrEnable OBJECT-TYPE
        SYNTAX        TruthValue
        MAX-ACCESS    read-write
        STATUS        current
        DESCRIPTION   "Enable or disable mcast-vlan-registration on a vlan, it
                               is used to specified a vlan works as a mcast-vlan,
                               maximum 16 mcast-vlan is supported."
        ::= { rcIgmpInterfaceExtnEntry 28 }

rcIgmpInterfaceExtnMvrProxyEnable OBJECT-TYPE
        SYNTAX        TruthValue
        MAX-ACCESS    read-write
        STATUS        current
        DESCRIPTION   "enable or disable mcast-vlan-registration proxy on a vlan,
                       you must enable mcast-vlan-registration at first."
        ::= { rcIgmpInterfaceExtnEntry 29 }

rcIgmpInterfaceExtnDynamicDowngradeEnable    OBJECT-TYPE
        SYNTAX        TruthValue
        MAX-ACCESS    read-write
        STATUS        current
        DESCRIPTION   "enable dynamic downgrade the IGMP version when older version query message was received."
        DEFVAL        { true }
        ::= { rcIgmpInterfaceExtnEntry 30 }

rcIgmpInterfaceExtnCompatibilityModeEnable    OBJECT-TYPE
        SYNTAX        TruthValue
        MAX-ACCESS    read-write
        STATUS        current
        DESCRIPTION   "enable v2 v3 compatible mode, which will handle the IGMP v2 message in v3 interface"
        DEFVAL        { false }
        ::= { rcIgmpInterfaceExtnEntry 31 }

rcIgmpInterfaceExtnOperVersion OBJECT-TYPE
        SYNTAX        INTEGER {
                        version1(1),
                        version2(2),
                        version3(3) }
        MAX-ACCESS    read-only
        STATUS        current
        DESCRIPTION   "The operational version of IGMP which is running on this interface."
        ::= { rcIgmpInterfaceExtnEntry 32 }

rcIgmpInterfaceExtnExplicitHostTrackingEnable OBJECT-TYPE
        SYNTAX        TruthValue
        MAX-ACCESS    read-write
        STATUS        current
        DESCRIPTION   "Enable the IGMP protocol running in version 3 to track hosts per channels/groups."
        DEFVAL        { false }
        ::= { rcIgmpInterfaceExtnEntry 33 }


-- IGMP Static

rcIgmpStaticTable OBJECT-TYPE
        SYNTAX        SEQUENCE OF RcIgmpStaticEntry
        MAX-ACCESS    not-accessible
        STATUS        current
        DESCRIPTION   ""
        ::= { rcIgmp 2 }

rcIgmpStaticEntry OBJECT-TYPE
        SYNTAX        RcIgmpStaticEntry
        MAX-ACCESS    not-accessible
        STATUS        current
        DESCRIPTION   ""
        INDEX         { rcIgmpStaticIfIndex, rcIgmpStaticGrpAddr }
        ::= { rcIgmpStaticTable 1 }

RcIgmpStaticEntry ::=
        SEQUENCE {
                rcIgmpStaticIfIndex          InterfaceIndex,
                rcIgmpStaticGrpAddr          IpAddress,
                rcIgmpStaticMemberPorts      PortSet,
                rcIgmpStaticNotAllowedToJoin PortSet,
                rcIgmpStaticRowStatus        RowStatus,
                rcIgmpStaticToGrpAddr        IpAddress
        }

rcIgmpStaticIfIndex OBJECT-TYPE
        SYNTAX        InterfaceIndex
        MAX-ACCESS    read-only
        STATUS        current
        DESCRIPTION   "ifindex"
        ::= { rcIgmpStaticEntry 1 }

rcIgmpStaticGrpAddr OBJECT-TYPE
        SYNTAX        IpAddress
        MAX-ACCESS    read-only
        STATUS        current
        DESCRIPTION   "Ip multicast address. The GrpAddress holds the starting
                       range for the address range.  If the ToGrpAddress is not
                       entered, the it is as good as entering a single address."
        ::= { rcIgmpStaticEntry 2 }

rcIgmpStaticMemberPorts OBJECT-TYPE
        SYNTAX        PortSet
        MAX-ACCESS    read-write
        STATUS        current
        DESCRIPTION   "egressing ports."
        ::= { rcIgmpStaticEntry 3 }

rcIgmpStaticNotAllowedToJoin OBJECT-TYPE
        SYNTAX        PortSet
        MAX-ACCESS    read-write
        STATUS        current
        DESCRIPTION   "not allowed to join."
        ::= { rcIgmpStaticEntry 4 }

rcIgmpStaticRowStatus OBJECT-TYPE
        SYNTAX        RowStatus
        MAX-ACCESS    read-write
        STATUS        current
        DESCRIPTION   "Used to create/delete entries in the rcIgmpStaticEntry."
        ::= { rcIgmpStaticEntry 5 }

rcIgmpStaticToGrpAddr OBJECT-TYPE
        SYNTAX        IpAddress
        MAX-ACCESS    read-write
        STATUS        current
        DESCRIPTION   "To hold the range for the GrpAddress."
        ::= { rcIgmpStaticEntry 6 }

-- IGMP Access

rcIgmpAccessTable OBJECT-TYPE
        SYNTAX        SEQUENCE OF RcIgmpAccessEntry
        MAX-ACCESS    not-accessible
        STATUS        current
        DESCRIPTION   ""
        ::= { rcIgmp 3 }

rcIgmpAccessEntry OBJECT-TYPE
        SYNTAX        RcIgmpAccessEntry
        MAX-ACCESS    not-accessible
        STATUS        current
        DESCRIPTION   ""
        INDEX         { rcIgmpAccessIfIndex, rcIgmpAccessGrpAddr,
                        rcIgmpAccessHostAddr, rcIgmpAccessHostMask }
        ::= { rcIgmpAccessTable 1 }

RcIgmpAccessEntry ::=
        SEQUENCE {
                rcIgmpAccessIfIndex     InterfaceIndex,
                rcIgmpAccessGrpAddr     IpAddress,
                rcIgmpAccessHostAddr    IpAddress,
                rcIgmpAccessMode        INTEGER,
                rcIgmpAccessRowStatus   RowStatus,
                rcIgmpAccessHostMask    IpAddress
        }

rcIgmpAccessIfIndex OBJECT-TYPE
        SYNTAX        InterfaceIndex
        MAX-ACCESS    read-only
        STATUS        current
        DESCRIPTION   "ifindex"
        ::= { rcIgmpAccessEntry 1 }

rcIgmpAccessGrpAddr OBJECT-TYPE
        SYNTAX        IpAddress
        MAX-ACCESS    read-only
        STATUS        current
        DESCRIPTION   "ip multicast addr."
        ::= { rcIgmpAccessEntry 2 }

rcIgmpAccessHostAddr OBJECT-TYPE
        SYNTAX        IpAddress
        MAX-ACCESS    read-only
        STATUS        current
        DESCRIPTION   "host addr."
        ::= { rcIgmpAccessEntry 3 }

rcIgmpAccessMode OBJECT-TYPE
        SYNTAX        INTEGER {
                          denyTX(1),
                          denyRX(2),
                          denyBOTH(3)
                      }
        MAX-ACCESS    read-write
        STATUS        current
        DESCRIPTION   "denyTX(1), denyRX(2), denyBOTH(3)."
        DEFVAL { denyBOTH }
        ::= { rcIgmpAccessEntry 4 }

rcIgmpAccessRowStatus OBJECT-TYPE
        SYNTAX        RowStatus
        MAX-ACCESS    read-write
        STATUS        current
        DESCRIPTION   "Used to create/delete entries in the rcIgmpAccessEntry."
        ::= { rcIgmpAccessEntry 5 }

rcIgmpAccessHostMask OBJECT-TYPE
        SYNTAX        IpAddress
        MAX-ACCESS    read-only
        STATUS        current
        DESCRIPTION   "host mask."
        ::= { rcIgmpAccessEntry 6 }

-- IGMP Sender

rcIgmpSenderTable OBJECT-TYPE
        SYNTAX        SEQUENCE OF RcIgmpSenderEntry
        MAX-ACCESS    not-accessible
        STATUS        current
        DESCRIPTION   ""
        ::= { rcIgmp 4 }

rcIgmpSenderEntry OBJECT-TYPE
        SYNTAX        RcIgmpSenderEntry
        MAX-ACCESS    not-accessible
        STATUS        current
        DESCRIPTION   ""
        INDEX         { rcIgmpSenderGrpAddr, rcIgmpSenderIfIndex,
                        rcIgmpSenderMemberAddr }
        ::= { rcIgmpSenderTable 1 }

RcIgmpSenderEntry ::=
        SEQUENCE {
                rcIgmpSenderGrpAddr     IpAddress,
                rcIgmpSenderIfIndex     InterfaceIndex,
                rcIgmpSenderMemberAddr  IpAddress,
                rcIgmpSenderAction      INTEGER,
                rcIgmpSenderTPort       Integer32,
                rcIgmpSenderState       INTEGER
        }

rcIgmpSenderGrpAddr OBJECT-TYPE
        SYNTAX        IpAddress
        MAX-ACCESS    read-only
        STATUS        current
        DESCRIPTION   "ip multicast addr."
        ::= { rcIgmpSenderEntry 1 }

rcIgmpSenderIfIndex OBJECT-TYPE
        SYNTAX        InterfaceIndex
        MAX-ACCESS    read-only
        STATUS        current
        DESCRIPTION   "ifindex"
        ::= { rcIgmpSenderEntry 2 }

rcIgmpSenderMemberAddr OBJECT-TYPE
        SYNTAX        IpAddress
        MAX-ACCESS    read-only
        STATUS        current
        DESCRIPTION   "host addr."
        ::= { rcIgmpSenderEntry 3 }

rcIgmpSenderAction OBJECT-TYPE
        SYNTAX        INTEGER {
                          none(0),
                          flushEntry(1),
                          flushGrp(2)
                      }
        MAX-ACCESS    read-write
        STATUS        current
        DESCRIPTION   "none(0), flushEntry(1), flushGrp(2)."
        ::= { rcIgmpSenderEntry 4 }

rcIgmpSenderTPort OBJECT-TYPE
        SYNTAX        Integer32
        MAX-ACCESS    read-only
        STATUS        current
        DESCRIPTION   "Igmp Sender Tport."
        ::= { rcIgmpSenderEntry 5 }

rcIgmpSenderState OBJECT-TYPE
        SYNTAX        INTEGER {
                          filtered(1),
                          notfiltered(2)
                      }
        MAX-ACCESS    read-only
        STATUS        current
        DESCRIPTION   "Indicates if a sender exists because of an
                       IGMP access filter or not."
        ::= { rcIgmpSenderEntry 6 }

-- IGMP SSM

rcIgmpSsmGlobal OBJECT IDENTIFIER ::= { rcIgmp 5 }

rcIgmpSsmGlobalDynamicLearning OBJECT-TYPE
        SYNTAX        TruthValue
        MAX-ACCESS    read-write
        STATUS        current
        DESCRIPTION   "Enable/disable dynamic learning 
                       or source/group pair from IGMPv3 report."
        ::= { rcIgmpSsmGlobal 1 }

rcIgmpSsmGlobalAdminAction OBJECT-TYPE
        SYNTAX        INTEGER {
                      none(1),               -- none of the following
                      enableAll(2),          -- enable all Ssm entries
                      disableAll(3)          -- disable all Ssm entries
                      }
        MAX-ACCESS    read-write
        STATUS        current
        DESCRIPTION   "Set the admin status of all the Ssm entries to 
                       enable/disable at once."
        ::= { rcIgmpSsmGlobal 2 }

rcIgmpSsmGlobalRangeGroup OBJECT-TYPE
        SYNTAX        IpAddress
        MAX-ACCESS    read-write
        STATUS        current
        DESCRIPTION   "If multicast group address & RangeMask == RangeGroup, 
                       then RangeGroup is in Ssm Range. Else it is not in 
                       the range."
        ::= { rcIgmpSsmGlobal 3 }

rcIgmpSsmGlobalRangeMask OBJECT-TYPE
        SYNTAX        IpAddress
        MAX-ACCESS    read-write
        STATUS        current
        DESCRIPTION   "Used with RangeGroup."
        ::= { rcIgmpSsmGlobal 4 }

-- IGMP SSM Mapping Table - supported by VSP pre-3.2 releases

rcIgmpSsmTable OBJECT-TYPE
        SYNTAX        SEQUENCE OF RcIgmpSsmEntry
        MAX-ACCESS    not-accessible
        STATUS        deprecated
        DESCRIPTION   ""
        ::= { rcIgmp 6 }

rcIgmpSsmEntry OBJECT-TYPE
        SYNTAX        RcIgmpSsmEntry
        MAX-ACCESS    not-accessible
        STATUS        deprecated
        DESCRIPTION   ""
        INDEX         { rcIgmpSsmIpMulticastGrp }
        ::= { rcIgmpSsmTable 1 }

RcIgmpSsmEntry ::=
        SEQUENCE {
                rcIgmpSsmIpMulticastGrp  IpAddress,
                rcIgmpSsmIpSource        IpAddress,
                rcIgmpSsmLearningMode    INTEGER,
                rcIgmpSsmActivity        TruthValue,
                rcIgmpSsmAdminState      EnableValue,
                rcIgmpSsmRowStatus       RowStatus
        }

rcIgmpSsmIpMulticastGrp OBJECT-TYPE
        SYNTAX        IpAddress
        MAX-ACCESS    read-only
        STATUS        deprecated
        DESCRIPTION   "This is the IP multicast group address 
                       that has default range of 232/8. 
                       This parameter should be configured by the user."
       ::= { rcIgmpSsmEntry 1 }

rcIgmpSsmIpSource OBJECT-TYPE
        SYNTAX        IpAddress
        MAX-ACCESS    read-write
        STATUS        deprecated
        DESCRIPTION   "This is the Source's IP address that will 
                       be sending traffic to the group source. 
                       This parameter should be configured by the user."
       ::= { rcIgmpSsmEntry 2 }

rcIgmpSsmLearningMode OBJECT-TYPE
        SYNTAX        INTEGER {
                         dynamic(1),    
                         static(2)     
                      }
        MAX-ACCESS    read-only
        STATUS        deprecated
        DESCRIPTION   "This is a read only field that provides 
                       information if the entry is statically 
                       configured entry (Static) or a dynamically 
                       learned entry from IGMPv3 (Dynamic). Note 
                       that Dynamic may not be used in the first 
                       step of the implementation."
        ::= { rcIgmpSsmEntry 3 }

rcIgmpSsmActivity OBJECT-TYPE
        SYNTAX        TruthValue
        MAX-ACCESS    read-only
        STATUS        deprecated
        DESCRIPTION   "This is a read only field.  It provides 
                       the activity on the corresponding (S,G). If 
                       the source is active and traffic is flowing 
                       to the switch, this field value should be 
                       Active, otherwise it should say non-active. 
                       This information is useful in knowing if the 
                       group has an active source or not when the group
                      is joined by a member on the switch."
        ::= { rcIgmpSsmEntry 4 }

rcIgmpSsmAdminState OBJECT-TYPE
        SYNTAX        EnableValue
        MAX-ACCESS    read-write
        STATUS        deprecated
        DESCRIPTION   "The admin state provides information on 
                       whether the entry is to be used or not. If the 
                       value of this field is Enabled (default), then 
                       the entry can be used. If the state is Disabled,
                      then the entry will not be used, but will be 
                       saved for future use."
        ::= { rcIgmpSsmEntry 5 }

rcIgmpSsmRowStatus OBJECT-TYPE
        SYNTAX        RowStatus
        MAX-ACCESS    read-write
        STATUS        deprecated
        DESCRIPTION   "Used to create/delete entries."
        ::= { rcIgmpSsmEntry 6 }


-- IGMP New Access

rcIgmpNewAccessTable OBJECT-TYPE
        SYNTAX        SEQUENCE OF RcIgmpNewAccessEntry
        MAX-ACCESS    not-accessible
        STATUS        current
        DESCRIPTION   ""
        ::= { rcIgmp 7 }

rcIgmpNewAccessEntry OBJECT-TYPE
        SYNTAX        RcIgmpNewAccessEntry
        MAX-ACCESS    not-accessible
        STATUS        current
        DESCRIPTION   ""
        INDEX         { rcIgmpNewAccessIfIndex, rcIgmpNewAccessPrefixListId,
                        rcIgmpNewAccessHostAddr, rcIgmpNewAccessHostMask }
        ::= { rcIgmpNewAccessTable 1 }

RcIgmpNewAccessEntry ::=
        SEQUENCE {
                rcIgmpNewAccessIfIndex          InterfaceIndex,
                rcIgmpNewAccessPrefixListId     Integer32,
                rcIgmpNewAccessPrefixListName   DisplayString,
                rcIgmpNewAccessHostAddr         IpAddress,
                rcIgmpNewAccessHostMask         IpAddress,
                rcIgmpNewAccessActionMode       INTEGER,
                rcIgmpNewAccessRowStatus        RowStatus
        }

rcIgmpNewAccessIfIndex OBJECT-TYPE
        SYNTAX        InterfaceIndex
        MAX-ACCESS    read-only
        STATUS        current
        DESCRIPTION   "ifindex"
        ::= { rcIgmpNewAccessEntry 1 }

rcIgmpNewAccessPrefixListId OBJECT-TYPE
        SYNTAX        Integer32 (0..2147483647)
        MAX-ACCESS    read-only
        STATUS        current
        DESCRIPTION   "Prefix List ID."
        ::= { rcIgmpNewAccessEntry 2 }

rcIgmpNewAccessPrefixListName OBJECT-TYPE
        SYNTAX        DisplayString
        MAX-ACCESS    read-write
        STATUS        current
        DESCRIPTION   "Prefix List name."
        ::= { rcIgmpNewAccessEntry 3 }

rcIgmpNewAccessHostAddr OBJECT-TYPE
        SYNTAX        IpAddress
        MAX-ACCESS    read-only
        STATUS        current
        DESCRIPTION   "host addr."
        ::= { rcIgmpNewAccessEntry 4 }

rcIgmpNewAccessHostMask OBJECT-TYPE
        SYNTAX        IpAddress
        MAX-ACCESS    read-only
        STATUS        current
        DESCRIPTION   "host mask."
        ::= { rcIgmpNewAccessEntry 5 }

rcIgmpNewAccessActionMode OBJECT-TYPE
        SYNTAX        INTEGER {
                          denyTX(1),
                          denyRX(2),
                          denyBOTH(3),
                          allowTX(4),
                          allowRX(5),
                          allowBOTH(6)
                      }
        MAX-ACCESS    read-write
        STATUS        current
        DESCRIPTION   "action mode."
        DEFVAL { denyBOTH }
        ::= { rcIgmpNewAccessEntry 6 }

rcIgmpNewAccessRowStatus OBJECT-TYPE
        SYNTAX        RowStatus
        MAX-ACCESS    read-write
        STATUS        current
        DESCRIPTION   "Used to create/delete entries in the rcIgmpNewAccessEntry."
        ::= { rcIgmpNewAccessEntry 7 }

-- rcIgmpChannelLimit Table

rcIgmpChannelLimitTable OBJECT-TYPE
        SYNTAX        SEQUENCE OF RcIgmpChannelLimitEntry
        MAX-ACCESS    not-accessible
        STATUS        current
        DESCRIPTION   ""
        ::= { rcIgmp 8 }

rcIgmpChannelLimitEntry OBJECT-TYPE
        SYNTAX        RcIgmpChannelLimitEntry
        MAX-ACCESS    not-accessible
        STATUS        current
        DESCRIPTION   ""
        INDEX         { rcIgmpChannelLimitIfIndex,
                        rcIgmpChannelLimitPort }
        ::= { rcIgmpChannelLimitTable 1 }

RcIgmpChannelLimitEntry ::=
        SEQUENCE {
                rcIgmpChannelLimitIfIndex     InterfaceIndex,
                rcIgmpChannelLimitPort        Integer32,
                rcIgmpChannelLimitMaxStreams  Integer32,
                rcIgmpChannelLimitNumStreams  Integer32,
                rcIgmpChannelLimitRowStatus   RowStatus
        }

rcIgmpChannelLimitIfIndex OBJECT-TYPE
        SYNTAX        InterfaceIndex
        MAX-ACCESS    read-only
        STATUS        current
        DESCRIPTION   "ifindex"
        ::= { rcIgmpChannelLimitEntry 1 }

rcIgmpChannelLimitPort OBJECT-TYPE
        SYNTAX        Integer32 (0..2147483647)
        MAX-ACCESS    read-only
        STATUS        current
        DESCRIPTION   "The port belong to this vlan."
        ::= { rcIgmpChannelLimitEntry 2 }

rcIgmpChannelLimitMaxStreams OBJECT-TYPE
        SYNTAX        Integer32 (0..65535)
        MAX-ACCESS    read-write
        STATUS        current
        DESCRIPTION   "Maximum number of stream."
        DEFVAL        { 4 }
        ::= { rcIgmpChannelLimitEntry 3 }

rcIgmpChannelLimitNumStreams OBJECT-TYPE
        SYNTAX        Integer32
        MAX-ACCESS    read-only
        STATUS        current
        DESCRIPTION   "Current number of streams."
        ::= { rcIgmpChannelLimitEntry 4 }

rcIgmpChannelLimitRowStatus OBJECT-TYPE
        SYNTAX        RowStatus
        MAX-ACCESS    read-write
        STATUS        current
        DESCRIPTION   "Row Status."
        ::= { rcIgmpChannelLimitEntry 5 }

-- IGMP Global attributes

rcIgmpGlobalParams OBJECT IDENTIFIER ::= { rcIgmp 11 }

rcIgmpFastLeaveMode OBJECT-TYPE
        SYNTAX        INTEGER {
                         none(0),      -- none of the following
                         multipleUser(1),  -- remove leaving member, stop traffic if no more member
                         oneUser(2)    -- first leave stops traffic
                      }
        MAX-ACCESS    read-write
        STATUS        current
        DESCRIPTION   "Set the fast-leave mode to be used by for all 
                       fast-leave enabled IGMP interfaces."
        DEFVAL { multipleUser }
        ::= { rcIgmpGlobalParams 1 }


-- IGMP Cache Extern Table

rcIgmpCacheExtnTable OBJECT-TYPE
        SYNTAX        SEQUENCE OF RcIgmpCacheExtnEntry
        MAX-ACCESS    not-accessible
        STATUS        current
        DESCRIPTION   ""
        ::= { rcIgmp 12 }

rcIgmpCacheExtnEntry OBJECT-TYPE
        SYNTAX        RcIgmpCacheExtnEntry
        MAX-ACCESS    not-accessible
        STATUS        current
        DESCRIPTION   ""
        INDEX         { igmpCacheAddress, igmpCacheIfIndex }
        ::= { rcIgmpCacheExtnTable 1 }

RcIgmpCacheExtnEntry ::=
        SEQUENCE {
                rcIgmpCacheExtnType               INTEGER,
                rcIgmpCacheExtnStaticPorts        PortSet
        }

rcIgmpCacheExtnType OBJECT-TYPE
        SYNTAX        INTEGER {
                         dynamic(1),
                         static(2)
                      }
        MAX-ACCESS    read-only
        STATUS        current
        DESCRIPTION   "It takes up either of the two values, dynamic
                       or static depending upon whether the entry is 
                       learnt Dynamic or is added statically."
        ::= { rcIgmpCacheExtnEntry 1 }

rcIgmpCacheExtnStaticPorts OBJECT-TYPE
        SYNTAX        PortSet
        MAX-ACCESS    read-only
        STATUS        current
        DESCRIPTION   "It displays the static ports for the static joins,
                       this would be null for the dynamic entry."
        ::= { rcIgmpCacheExtnEntry 2 }



-- rcIgmpSnoopTrace

rcIgmpSnoopTraceTable OBJECT-TYPE
        SYNTAX        SEQUENCE OF RcIgmpSnoopTraceEntry
        MAX-ACCESS    not-accessible
        STATUS        current
        DESCRIPTION   "The table listing the multicast groups
                       traversing the snoop enabled router"
        ::= { rcIgmp 13 }

rcIgmpSnoopTraceEntry OBJECT-TYPE
        SYNTAX        RcIgmpSnoopTraceEntry
        MAX-ACCESS    not-accessible
        STATUS        current
        DESCRIPTION   "The entry listing the multicast groups
                       traversing the snoop enabled router"
        INDEX         { rcIgmpSnoopGrpAddr, rcIgmpSnoopSrcAddr, rcIgmpSnoopOutVlan}

        ::= { rcIgmpSnoopTraceTable 1 }

RcIgmpSnoopTraceEntry ::=
        SEQUENCE {
                rcIgmpSnoopGrpAddr         IpAddress,
                rcIgmpSnoopSrcAddr         IpAddress,
                rcIgmpSnoopOutVlan         InterfaceIndex,
                rcIgmpSnoopInPort          InterfaceIndex,
                rcIgmpSnoopInVlan          InterfaceIndex,
                rcIgmpSnoopOutPort         PortSet
        }

rcIgmpSnoopGrpAddr  OBJECT-TYPE
        SYNTAX        IpAddress
        MAX-ACCESS    not-accessible
        STATUS        current
        DESCRIPTION   "ip mcast addr of grp traversing the router"
        ::= { rcIgmpSnoopTraceEntry 1 }

rcIgmpSnoopSrcAddr  OBJECT-TYPE
        SYNTAX        IpAddress
        MAX-ACCESS    not-accessible
        STATUS        current
        DESCRIPTION   "Ip src addr of the mcast grp address"
        ::= { rcIgmpSnoopTraceEntry 2 }

rcIgmpSnoopOutVlan OBJECT-TYPE
        SYNTAX        InterfaceIndex
        MAX-ACCESS    not-accessible
        STATUS        current
        DESCRIPTION   "Egress vlan id for the mcast group"
        ::= { rcIgmpSnoopTraceEntry 3 }

rcIgmpSnoopInPort OBJECT-TYPE
        SYNTAX        InterfaceIndex
        MAX-ACCESS    read-only
        STATUS        current
        DESCRIPTION   "Ingress port for the mcast grp"
        ::= { rcIgmpSnoopTraceEntry 4 }

rcIgmpSnoopInVlan OBJECT-TYPE
        SYNTAX        InterfaceIndex
        MAX-ACCESS    read-only
        STATUS        current
        DESCRIPTION   "Ingress vlan id for the mcast source"
        ::= { rcIgmpSnoopTraceEntry 5 }

rcIgmpSnoopOutPort OBJECT-TYPE
        SYNTAX        PortSet
        MAX-ACCESS    read-only
        STATUS        current
        DESCRIPTION   "Egress port of the mcast grp"
        ::= { rcIgmpSnoopTraceEntry 6 }

--New IGMP Group Table.

rcIgmpNewGroupTable OBJECT-TYPE
        SYNTAX     SEQUENCE OF RcIgmpNewGroupEntry
        MAX-ACCESS not-accessible
        STATUS     current
        DESCRIPTION "The (conceptual) table listing the multicast
                    groups configured in the device."
    ::= { rcIgmp 14 }

rcIgmpNewGroupEntry OBJECT-TYPE
        SYNTAX     RcIgmpNewGroupEntry
        MAX-ACCESS not-accessible
        STATUS     current
        DESCRIPTION "An entry (conceptual row) representing an
                    Igmp group."
        INDEX      {rcIgmpNewGroupIpAddress, rcIgmpNewGroupMembers, rcIgmpNewGroupInPort}
        ::= { rcIgmpNewGroupTable 1 }

RcIgmpNewGroupEntry ::= SEQUENCE {
        rcIgmpNewGroupIpAddress         IpAddress,
        rcIgmpNewGroupMembers           IpAddress,
        rcIgmpNewGroupInPort            INTEGER,
        rcIgmpNewGroupExpiration        Integer32,
        rcIgmpNewGroupIfIndex           InterfaceIndex,
        rcIgmpNewGroupUserId            DisplayString,
        rcIgmpNewGroupMemberState       INTEGER,
        rcIgmpNewGroupSessionTime       Integer32
}

rcIgmpNewGroupIpAddress OBJECT-TYPE
        SYNTAX          IpAddress
        MAX-ACCESS      not-accessible
        STATUS          current
        DESCRIPTION     "Multicast group Address (Class D) that others
                         want to join. A group address can be the same
                         for many incoming ports."
        ::= { rcIgmpNewGroupEntry 1 }

rcIgmpNewGroupMembers OBJECT-TYPE
        SYNTAX          IpAddress
        MAX-ACCESS      not-accessible
        STATUS          current
        DESCRIPTION     "IP Address of a source that has sent group
                         report wishing to join this group."
        ::= { rcIgmpNewGroupEntry 2 }

rcIgmpNewGroupInPort OBJECT-TYPE
        SYNTAX          INTEGER (0..65535)
        MAX-ACCESS      not-accessible
        STATUS          current
        DESCRIPTION     "An unique value to identify a physical
                        interface or a logical interface (VLAN),
                        which has received Group reports from various
                        sources."
        ::= { rcIgmpNewGroupEntry 3 }

rcIgmpNewGroupExpiration OBJECT-TYPE
         SYNTAX     Integer32
         MAX-ACCESS read-only
         STATUS     current
         DESCRIPTION "Time left before the group report expired on this
                      port. Only one of this variable port. This
                      variable is updated upon receiving a group report."
         ::= { rcIgmpNewGroupEntry 4 }

rcIgmpNewGroupIfIndex OBJECT-TYPE
         SYNTAX     InterfaceIndex
         MAX-ACCESS read-only
         STATUS     current
         DESCRIPTION     "An unique value to identify a physical
                        interface or a logical interface (VLAN),
                        which has received Group reports from various
                        sources."
         ::= { rcIgmpNewGroupEntry 5 }

rcIgmpNewGroupUserId OBJECT-TYPE
         SYNTAX     DisplayString (SIZE(0..32))
         MAX-ACCESS read-only
         STATUS     current
         DESCRIPTION "User-id sending this group"
         ::= { rcIgmpNewGroupEntry 6 }

rcIgmpNewGroupMemberState OBJECT-TYPE
         SYNTAX     INTEGER {
                        noState(1),
                        auth(2),
                        accStart(3),
                        authAndAcctStart(4),
                        authAndAcctDisabled(5)
                    }
         MAX-ACCESS read-only
         STATUS     current
         DESCRIPTION "Used for IGAP, to indicated member state."
         ::= { rcIgmpNewGroupEntry 7 }

rcIgmpNewGroupSessionTime OBJECT-TYPE
         SYNTAX     Integer32
         MAX-ACCESS read-only
         STATUS     current
         DESCRIPTION "Used for IGAP, to indicated the session time
                      in seconds for the member. Session time is
                      started after traffic is available to member.
                      It can be also called AccountingTime since its
                      values correspondes to the accounting duration of
                      IGAP user session."
         ::= { rcIgmpNewGroupEntry 8 }


--The IGMPv3 Router Cache Table

rcIgmpv3CacheTable OBJECT-TYPE
         SYNTAX      SEQUENCE OF RcIgmpv3CacheEntry
         MAX-ACCESS  not-accessible
         STATUS      current
         DESCRIPTION "The (conceptual) table listing the Igmpv3 specific data
                     corresponding to each interface, port  and multicast group pair on
                     a Router."
         ::= { rcIgmp 24 }

rcIgmpv3CacheEntry OBJECT-TYPE
         SYNTAX      RcIgmpv3CacheEntry
         MAX-ACCESS  not-accessible
         STATUS      current
         DESCRIPTION "An entry (conceptual row) representing an Igmpv3 Group."
         INDEX       { rcIgmpv3CacheEntryGroupAddress,
                       rcIgmpv3CacheEntryIfIndex,
                       rcIgmpv3CacheEntryInPort
                     }
         ::= { rcIgmpv3CacheTable 1 }

RcIgmpv3CacheEntry ::= SEQUENCE {
         rcIgmpv3CacheEntryGroupAddress              IpAddress,
         rcIgmpv3CacheEntryIfIndex                   InterfaceIndex,
         rcIgmpv3CacheEntryInPort                    INTEGER,
         rcIgmpv3CacheEntryModeExpiryTimer           Integer32,
         rcIgmpv3CacheEntryVersion1HostTimer         Integer32,
         rcIgmpv3CacheEntryVersion2HostTimer         Integer32,
         rcIgmpv3CacheEntrySourceFilterMode          INTEGER
}

rcIgmpv3CacheEntryGroupAddress OBJECT-TYPE
         SYNTAX      IpAddress
         MAX-ACCESS  not-accessible
         STATUS      current
         DESCRIPTION "Multicast group Address (Class D) that others
                      want to join. A group address can be the same
                      for many incoming ports."
         ::= { rcIgmpv3CacheEntry 1 }

rcIgmpv3CacheEntryIfIndex OBJECT-TYPE
         SYNTAX      InterfaceIndex
         MAX-ACCESS  not-accessible
         STATUS      current
         DESCRIPTION "An unique value to identify a physical
                      interface or a logical interface (VLAN),
                      which has received Group reports from various
                      sources."
         ::= { rcIgmpv3CacheEntry 2 }

rcIgmpv3CacheEntryInPort OBJECT-TYPE
         SYNTAX      INTEGER (0..65535)
         MAX-ACCESS  not-accessible
         STATUS      current
         DESCRIPTION "An unique value to identify a physical
                      interface or a logical interface (VLAN),
                      which has received Group reports from various
                      sources."
        ::= { rcIgmpv3CacheEntry 3 }

rcIgmpv3CacheEntryModeExpiryTimer OBJECT-TYPE
         SYNTAX      Integer32
         MAX-ACCESS  read-only
         STATUS      current
         DESCRIPTION "This value is applicable only to IGMPv3-compatible nodes
                      and represents the time remaining before the interface
                      EXCLUDE state expires and the interface state transitions
                      to INCLUDE mode.  This value can never be greater than
                      rcIgmpNewGroupExpiration."
         ::= { rcIgmpv3CacheEntry 4 }

rcIgmpv3CacheEntryVersion1HostTimer OBJECT-TYPE
         SYNTAX      Integer32
         MAX-ACCESS  read-only
         STATUS      current
         DESCRIPTION "The time remaining until the local router will assume that
                      there are no longer any IGMP version 1 members on the IP
                      subnet attached to this interface.  This entry only applies
                      to IGMPv1 hosts. Upon hearing any IGMPv1 Report, this
                      value is reset to the group membership timer.  While this
                      time remaining is non-zero, the local router ignores any
                      IGMPv2 Leave messages for this group that it  receives
                      on this interface."
         ::= { rcIgmpv3CacheEntry 5 }

rcIgmpv3CacheEntryVersion2HostTimer OBJECT-TYPE
         SYNTAX      Integer32
         MAX-ACCESS  read-only
         STATUS      current
         DESCRIPTION "The time remaining until the local router will assume that
                      there are no longer any IGMP version 2 members on the IP
                      subnet attached to this interface. Upon hearing any IGMPv2 Membership
                      Report, this value is reset to the group membership timer.
                      Assuming no IGMPv1 hosts have been detected, the local
                      router does not ignore any IGMPv2 Leave messages for this
                      group that it receives on this interface."
         ::= { rcIgmpv3CacheEntry 6 }

rcIgmpv3CacheEntrySourceFilterMode OBJECT-TYPE
         SYNTAX      INTEGER {
                              include (1),
                              exclude (2)
                     }
         MAX-ACCESS  read-only
         STATUS      current
         DESCRIPTION "The current group state, applicable to IGMPv3-compatible
                      nodes. The value indicates whether the state is INCLUDE or
                      EXCLUDE."
         ::= { rcIgmpv3CacheEntry 7 }


--The IGMPv3 Router Source list Table

--
-- This information helps to interpret the content of the rcIgmpRouterSrcListTable.
-- 1. rcIgmpRouterSrcListHostAddress is not zero; rcIgmpRouterSrcListMemberAddress is zero.
--    This is the case when we have a source in the include list and no receiver asked it
--    explicitly (conflict source).
--    Ex: Two receivers present; one receiver is in EXLCUDE{S1} and the other one is in
--    EXLCUDE{S2}. The group state is EXCLUDE("S2","NULL").
-- 2. rcIgmpRouterSrcListHostAddress is not zero, rcIgmpRouterSrcListMemberAddress is not zero.
--    This is the case when a receiver asked to receive traffic for a specific source.
--    Ex: One receiver present in INCLUDE{S1}
-- 3. rcIgmpRouterSrcListHostAddress is not zero, rcIgmpRouterSrcListMemberAddress is zero.
--    This represent a source that needs to be blocked.
-- 4. rcIgmpRouterSrcListHostAddres is zero  rcIgmpRouterSrcListMemberAddress is not zero.
--    The source zero is used to track the members that are in exclude mode
--    Ex: One receiver R1 in EXCLUDE(S1). Two entries are present in this table.
--    4.1. rcIgmpRouterSrcListHostAddres = S1, rcIgmpRouterSrcListMemberAddress = 0 - blocked source.
--    4.2. rcIgmpRouterSrcListHostAddres = 0, rcIgmpRouterSrcListMemberAddress = R1 - tracked member in exlcude mode.
--
-- If the explicit host tracking is not enabled the only the last reporter for a specific source or group
-- will be present in this table.
--

rcIgmpRouterSrcListTable OBJECT-TYPE
         SYNTAX      SEQUENCE OF RcIgmpRouterSrcListEntry
         MAX-ACCESS  not-accessible
         STATUS      current
         DESCRIPTION "The (conceptual) table listing the Source List entries
                      corresponding to each interface and multicast group pair on
                      a Router."
         ::= { rcIgmp 25 }

rcIgmpRouterSrcListEntry OBJECT-TYPE
         SYNTAX      RcIgmpRouterSrcListEntry
         MAX-ACCESS  not-accessible
         STATUS      current
         DESCRIPTION "An entry (conceptual row) representing an
                      Igmp Source."
         INDEX       { rcIgmpRouterSrcListGroupAddress, 
                       rcIgmpRouterSrcListIfIndex, 
                       rcIgmpRouterSrcListInPort, 
                       rcIgmpRouterSrcListHostAddress,
                       rcIgmpRouterSrcListMemberAddress
                     }
         ::= { rcIgmpRouterSrcListTable 1 }

RcIgmpRouterSrcListEntry ::= SEQUENCE {
         rcIgmpRouterSrcListGroupAddress   IpAddress,
         rcIgmpRouterSrcListIfIndex        InterfaceIndex,
         rcIgmpRouterSrcListInPort         INTEGER,
         rcIgmpRouterSrcListHostAddress    IpAddress,
         rcIgmpRouterSrcListMemberAddress  IpAddress,
         rcIgmpRouterSrcListExpire         Integer32,
         rcIgmpRouterSrcListMode           INTEGER,
         rcIgmpRouterSrcListMemberExpire   Integer32
}

rcIgmpRouterSrcListGroupAddress OBJECT-TYPE
         SYNTAX      IpAddress
         MAX-ACCESS  not-accessible
         STATUS      current
         DESCRIPTION "The IP multicast group address for which this entry
                      contains information."
         ::= { rcIgmpRouterSrcListEntry 1 }

rcIgmpRouterSrcListIfIndex OBJECT-TYPE
         SYNTAX      InterfaceIndex
         MAX-ACCESS  not-accessible
         STATUS      current
         DESCRIPTION "The interface for which this entry contains information
                      for an IP multicast group address."
         ::= { rcIgmpRouterSrcListEntry 2 }

rcIgmpRouterSrcListInPort OBJECT-TYPE
         SYNTAX      INTEGER (0..65535)
         MAX-ACCESS  not-accessible
         STATUS      current
         DESCRIPTION "An unique value to identify a physical
                     interface or a logical interface (VLAN),
                     which has received Group reports for this
                     source."
         ::= { rcIgmpRouterSrcListEntry 3 }

rcIgmpRouterSrcListHostAddress OBJECT-TYPE
         SYNTAX      IpAddress
         MAX-ACCESS  not-accessible
         STATUS      current
         DESCRIPTION "The host address to which this entry corresponds."  
         ::= { rcIgmpRouterSrcListEntry 4 }

rcIgmpRouterSrcListMemberAddress OBJECT-TYPE
         SYNTAX      IpAddress
         MAX-ACCESS  not-accessible
         STATUS      current
         DESCRIPTION "IP Address of a member that has sent source specific
                      report wishing to join this source."
         ::= { rcIgmpRouterSrcListEntry 5 }

rcIgmpRouterSrcListExpire OBJECT-TYPE
         SYNTAX      Integer32 
         MAX-ACCESS  read-only
         STATUS      current
         DESCRIPTION "This value indicates the relevance of the SrcList entry,
                      whereby a non-zero value indicates this is an INCLUDE state
                      value, and a zero value indicates this to be an EXCLUDE
                      state value."
         ::= { rcIgmpRouterSrcListEntry 6 }

rcIgmpRouterSrcListMode OBJECT-TYPE
         SYNTAX      INTEGER {
                              include (1),
                              exclude (2)
                     }
         MAX-ACCESS  read-only
         STATUS      current
         DESCRIPTION "The current member state, applicable to IGMPv3-compatible
                      nodes. The value indicates whether the state is INCLUDE or
                      EXCLUDE."
         ::= { rcIgmpRouterSrcListEntry 7 }

rcIgmpRouterSrcListMemberExpire OBJECT-TYPE
         SYNTAX      Integer32
         MAX-ACCESS  read-only
         STATUS      current
         DESCRIPTION "This value indicates the time until the member for this source
                      will expire" 
         ::= { rcIgmpRouterSrcListEntry 8 }

-- IGMP SSM Mapping Table - supported by VSP 3.2 release

rcIgmpNewSsmTable OBJECT-TYPE
        SYNTAX        SEQUENCE OF RcIgmpNewSsmEntry
        MAX-ACCESS    not-accessible
        STATUS        current
        DESCRIPTION   ""
        ::= { rcIgmp 26 }

rcIgmpNewSsmEntry OBJECT-TYPE
        SYNTAX        RcIgmpNewSsmEntry
        MAX-ACCESS    not-accessible
        STATUS        current
        DESCRIPTION   ""
        INDEX         { rcIgmpNewSsmIpMulticastGrp,
                        rcIgmpNewSsmIpSource }
        ::= { rcIgmpNewSsmTable 1 }

RcIgmpNewSsmEntry ::=
        SEQUENCE {
                rcIgmpNewSsmIpMulticastGrp  IpAddress,
                rcIgmpNewSsmIpSource        IpAddress,
                rcIgmpNewSsmLearningMode    INTEGER,
                rcIgmpNewSsmActivity        TruthValue,
                rcIgmpNewSsmAdminState      EnableValue,
                rcIgmpNewSsmRowStatus       RowStatus
        }

rcIgmpNewSsmIpMulticastGrp OBJECT-TYPE
        SYNTAX        IpAddress
        MAX-ACCESS    not-accessible
        STATUS        current
        DESCRIPTION   "This is the IP multicast group address 
                       that has default range of 232/8. 
                       This parameter should be configured by the user."
       ::= { rcIgmpNewSsmEntry 1 }

rcIgmpNewSsmIpSource OBJECT-TYPE
        SYNTAX        IpAddress
        MAX-ACCESS    not-accessible
        STATUS        current
        DESCRIPTION   "This is the Source's IP address that will 
                       be sending traffic to the group source. 
                       This parameter should be configured by the user."
       ::= { rcIgmpNewSsmEntry 2 }

rcIgmpNewSsmLearningMode OBJECT-TYPE
        SYNTAX        INTEGER {
                         dynamic(1),    
                         static(2)     
                      }
        MAX-ACCESS    read-only
        STATUS        current
        DESCRIPTION   "This is a read only field that provides 
                       information if the entry is statically 
                       configured entry (Static) or a dynamically 
                       learned entry from IGMPv3 (Dynamic). Note 
                       that Dynamic may not be used in the first 
                       step of the implementation."
        ::= { rcIgmpNewSsmEntry 3 }

rcIgmpNewSsmActivity OBJECT-TYPE
        SYNTAX        TruthValue
        MAX-ACCESS    read-only
        STATUS        current
        DESCRIPTION   "This is a read only field.  It provides 
                       the activity on the corresponding (S,G). If 
                       the source is active and traffic is flowing 
                       to the switch, this field value should be 
                       Active, otherwise it should say non-active. 
                       This information is useful in knowing if the 
                       group has an active source or not when the group
                      is joined by a member on the switch."
        ::= { rcIgmpNewSsmEntry 4 }

rcIgmpNewSsmAdminState OBJECT-TYPE
        SYNTAX        EnableValue
        MAX-ACCESS    read-create
        STATUS        current
        DESCRIPTION   "The admin state provides information on 
                       whether the entry is to be used or not. If the 
                       value of this field is Enabled (default), then 
                       the entry can be used. If the state is Disabled,
                      then the entry will not be used, but will be 
                       saved for future use."
        ::= { rcIgmpNewSsmEntry 5 }

rcIgmpNewSsmRowStatus OBJECT-TYPE
        SYNTAX        RowStatus
        MAX-ACCESS    read-create
        STATUS        current
        DESCRIPTION   "Used to create/delete entries."
        ::= { rcIgmpNewSsmEntry 6 }


rcIgmpGenerateTrap OBJECT-TYPE
        SYNTAX        EnableValue
        MAX-ACCESS    read-write
        STATUS        current
        DESCRIPTION   "Enabling the IGMP to generate trap."
        DEFVAL        { disable }
        ::= { rcIgmpGlobalParams 2 }

rcIgmpGenerateLog OBJECT-TYPE
        SYNTAX        EnableValue
        MAX-ACCESS    read-write
        STATUS        current
        DESCRIPTION   "Enabling the IGMP to generate log."
        DEFVAL        { disable }
        ::= { rcIgmpGlobalParams 3 }

--  VRRP 

    rcVrrpMib      OBJECT IDENTIFIER ::= { rcVrrp 1 }
    rcVrrpObjects             OBJECT IDENTIFIER ::= { rcVrrpMib 1 }
    rcVrrpNotifications       OBJECT IDENTIFIER ::= { rcVrrpMib 2 }


-- ---------------------------------------------------------
-- Scalar Objects
-- ---------------------------------------------------------
rcVrrpScalars OBJECT IDENTIFIER ::= { rcVrrpObjects 1 }

rcVrrpPingVirtualAddrEnable  OBJECT-TYPE
        SYNTAX       TruthValue
        MAX-ACCESS   read-write
        STATUS       current
        DESCRIPTION
           "Used to configure whether this device should respond to
           pings directed to a virtual router's IP address."
        DEFVAL { true }
        ::= { rcVrrpScalars 1 }

rcVrrpTrapStateTransitionType OBJECT-TYPE
    SYNTAX        INTEGER {
        none(1),
        masterToBackup(2),
        backupToMaster(3),
        initializeToMaster(4),
        masterToInitialize(5),
        initializeToBackup(6),
        backupToInitialize(7)
    }
    MAX-ACCESS   read-only
    STATUS       current
    DESCRIPTION
            "Potential types of state transitions.
        Used by rcVrrpTrapStateTransition trap."
    ::= { rcVrrpScalars 2 }

rcVrrpTrapStateTransitionCause OBJECT-TYPE
    SYNTAX        INTEGER {
        none(1),
        higherPriorityAdvertizeReceived(2),
        shutdownReceived(3),
        rcVrrpAddrAndPhysicalAddrMatch(4),
        masterDownInterval(5),
        preempted(6)
    }
    MAX-ACCESS   read-only
    STATUS       current
    DESCRIPTION
        "Potential types of causes that will
        generate a rcVrrpTrapStateTransition trap."
    ::= { rcVrrpScalars 3 }


--  VRRP Operations Table
rcVrrpOperTable OBJECT-TYPE
        SYNTAX       SEQUENCE OF RcVrrpOperEntry
        MAX-ACCESS   not-accessible
        STATUS       current
        DESCRIPTION
            "Operations table for a VRRP router which consists of a
             sequence (i.e., one or more conceptual rows) of
             'rcVrrpOperEntry' items."
        ::= { rcVrrpObjects 2 }

rcVrrpOperEntry OBJECT-TYPE
        SYNTAX       RcVrrpOperEntry
        MAX-ACCESS   not-accessible
        STATUS       current
        DESCRIPTION
            "An entry in the rcVrrpOperTable containing the operational
             characteristics of a virtual router. On a VRRP router,
             a given virtual router is identified by a combination
             of the IF index and VRID."
        INDEX    { rcVrrpOperIfIndex, rcVrrpOperVrId }
        ::= { rcVrrpOperTable 1 }

RcVrrpOperEntry ::=
        SEQUENCE {
            rcVrrpOperIfIndex
                InterfaceIndexOrZero,
            rcVrrpOperVrId
                VrId,
            rcVrrpOperIpAddr
                IpAddress,
            rcVrrpOperVirtualMacAddr
                MacAddress,
            rcVrrpOperState
                INTEGER,
            rcVrrpOperControl
                INTEGER,
            rcVrrpOperPriority
                Integer32,
            rcVrrpOperIpAddrCount
                Integer32,
            rcVrrpOperMasterIpAddr
                IpAddress,
            rcVrrpOperAuthType
                INTEGER,
            rcVrrpOperHMACMD5Key                
                OCTET STRING,
            rcVrrpOperAuthKey
                OCTET STRING,
            rcVrrpOperAdvertisementInterval
                Integer32,
            rcVrrpOperPreemptMode
                INTEGER,
            rcVrrpOperVirtualRouterUpTime
                TimeTicks,
            rcVrrpOperRowStatus
                RowStatus,
            rcVrrpOperCriticalIpAddr
                IpAddress,
            rcVrrpOperHoldDownTimer
                INTEGER,
            rcVrrpOperHoldDownState
                INTEGER,
            rcVrrpOperHoldDownTimeRemaining
                INTEGER,
            rcVrrpOperAction
                INTEGER,
            rcVrrpOperCriticalIpAddrEnable
              TruthValue,
            rcVrrpOperBackUpMaster
                INTEGER,
            rcVrrpOperBackUpMasterState
                INTEGER,
            rcVrrpOperFasterAdvInterval
                Integer32,
            rcVrrpOperFasterAdvIntervalEnable
                INTEGER
    }

rcVrrpOperIfIndex OBJECT-TYPE
        SYNTAX       InterfaceIndexOrZero
        MAX-ACCESS   not-accessible
        STATUS       current
        DESCRIPTION  "port interface index."
        ::= { rcVrrpOperEntry 1 }

rcVrrpOperVrId OBJECT-TYPE
        SYNTAX       VrId
        MAX-ACCESS   read-only
        STATUS       current
        DESCRIPTION
            "This object contains the Virtual Router Identifier (VRID)."
        ::= { rcVrrpOperEntry 2 }

rcVrrpOperIpAddr OBJECT-TYPE
        SYNTAX       IpAddress
        MAX-ACCESS   read-write
        STATUS       current
        DESCRIPTION
            "The assigned IP addresses that a virtual router is responsible
            for backing up."
        ::= { rcVrrpOperEntry 3 }

rcVrrpOperVirtualMacAddr OBJECT-TYPE
        SYNTAX       MacAddress
        MAX-ACCESS   read-only
        STATUS       current
        DESCRIPTION
            "The virtual MAC address of the virtual router. This is derived
            as follows: 00-00-5E-00-01-<VRID>.

            Where the first three octets consist of the IANA's OUI; The
            next two octets indicate the address block of the VRRP protocol;
            and the remaining octets consist of the VRID.

            Although this object can be derived from the 'rcVrrpOperVrId'
            object, it is included here, for completeness, so that it
            is easily obtainable by a management application and can be
            included in VRRP-related SNMP traps."
        REFERENCE
            "rfc1903 - MacAddress"
        ::= { rcVrrpOperEntry 4 }

rcVrrpOperState OBJECT-TYPE
        SYNTAX       INTEGER {
            initialize(1),  -- Waiting for a startup event
            backup(2),      -- Monitoring the state/availability of
                            -- master router
            master(3)       -- Forwarding IP addresses associated with
                            -- this virtual router.
        }
        MAX-ACCESS   read-only
        STATUS       current
        DESCRIPTION
            "The current state of the virtual router."
        ::= { rcVrrpOperEntry 5 }

rcVrrpOperControl OBJECT-TYPE
        SYNTAX       INTEGER {
            enabled(1),
            disabled(2)
        }
        MAX-ACCESS   read-write
        STATUS       current
        DESCRIPTION
            "This object will enable/disable the virtual router
            function. Setting the value to 'enabled', will transition
            the state of the router from 'initialize to 'backup';
            Setting the value to 'disabled', will tranisition the
            router from 'master' or 'backup' to 'initialize'."
        DEFVAL    { enabled }
        ::= { rcVrrpOperEntry 6 }

rcVrrpOperPriority OBJECT-TYPE
        SYNTAX       Integer32 (1..255)
        MAX-ACCESS   read-write
        STATUS       current
        DESCRIPTION
            "This object specifies the priority for the virtual
            router (e.g., master election) with respect to other
            virtual routers that are backing up a one or more
            associated IP addresses. Higher values imply higher
            priority.

            A priority of '0', although not settable, is used
            to indicate that this router has ceased to particpate
            in VRRP and a backup virtual router should transition \
            to become a new master.

            A priority of 255 is used for the router that owns the
            associated IP address(es)."
        DEFVAL       { 100 }
        ::= { rcVrrpOperEntry 7 }

rcVrrpOperIpAddrCount OBJECT-TYPE
        SYNTAX       Integer32 (1..65535)
        MAX-ACCESS   read-only
        STATUS       current
        DESCRIPTION
            "The number of IP addresses that are associated with this
            virtual router. This number is equal to the number of rows
            in the vrrpAssoIpAddrTable that correspond to a given IF
            index/VRID pair."
        ::= { rcVrrpOperEntry 8 }

rcVrrpOperMasterIpAddr OBJECT-TYPE
        SYNTAX       IpAddress
        MAX-ACCESS   read-only
        STATUS       current
        DESCRIPTION
            "The master router's real (primary) IP address. This is
            the IP address listed as the source in VRRP advertisement
            last received by this virtual router"
        ::= { rcVrrpOperEntry 9 }

rcVrrpOperAuthType OBJECT-TYPE
        SYNTAX       INTEGER {
            noAuthentication(1),       -- VRRP protocol exchanges are not
                                       -- authenticated.
            simpleTextPassword(2),     -- Exchanges are authenticated by a
                                       -- clear text password.
            ipAuthenticationHeader(3)  -- Exchanges are authenticated using
                                       -- the IP authentication header [x].
        }
        MAX-ACCESS   read-write
        STATUS       current
        DESCRIPTION
            "Authentication type used for VRRP protocol exchanges between
            virtual routers."
        DEFVAL   { noAuthentication }
        ::= { rcVrrpOperEntry 10 }

rcVrrpOperAuthKey OBJECT-TYPE
        SYNTAX       OCTET STRING (SIZE (8))
        MAX-ACCESS   read-write
        STATUS       current
        DESCRIPTION
            "The Authentication Key.  If the virtual router's Authorization
            Type is 'simpleTextPassword', and the key length is shorter
            than 8 octets, the agent will left adjust and zero fill
            to 8 octets.

            When read, rcVrrpOperAuthKey always returns an Octet String
            of length zero."
         DEFVAL   { '0000000000000000'H }    -- 0.0.0.0.0.0.0.0
        ::= { rcVrrpOperEntry 11 }

rcVrrpOperHMACMD5Key OBJECT-TYPE
        SYNTAX       OCTET STRING (SIZE (16))
        MAX-ACCESS   read-write
        STATUS       current
        DESCRIPTION
            "The Authentication Key.  If the virtual router's 'Authorization
            Type' is 'ipAuthenticationHeader', and the key length is shorter
            than 16 octets, the agent will left adjust and zero fill
            to 16 octets.

            When read, rcVrrpOperHMACMD5Key always returns an Octet String
            of length zero."
        DEFVAL   { '00000000000000000000000000000000'H }
        -- 0.0.0.0.0.0.0.0.0.0.0.0.0.0.0.0
        ::= { rcVrrpOperEntry 12 }

rcVrrpOperAdvertisementInterval OBJECT-TYPE
        SYNTAX       Integer32 (1..255)
        MAX-ACCESS   read-write
        STATUS       current
        DESCRIPTION
            "This is the time interval, in seconds, between sending
            advertisement messages. Only the master router sends
            VRRP advertisements."
        DEFVAL       { 1 }
        ::= { rcVrrpOperEntry 13 }

rcVrrpOperPreemptMode OBJECT-TYPE
        SYNTAX       INTEGER {
            true(1),   -- Preempt
            false(2)   -- Do not preempt
        }
        MAX-ACCESS   read-write
        STATUS       current
        DESCRIPTION
            "Controls whether a higher priority virtual router will
            preempt a lower priority master."
        DEFVAL       { true }
        ::= { rcVrrpOperEntry 14 }

rcVrrpOperVirtualRouterUpTime OBJECT-TYPE
        SYNTAX       TimeTicks
        MAX-ACCESS   read-only
        STATUS       current
        DESCRIPTION
            "This is the time interval (in hundredths of a second)
            since this virtual router was initialized."
        ::= { rcVrrpOperEntry 15 }

rcVrrpOperRowStatus OBJECT-TYPE
        SYNTAX       RowStatus
        MAX-ACCESS   read-write
        STATUS       current
        DESCRIPTION
            "The row status variable, used according to installation
            and removal conventions for conceptual rows. Setting this
            object to 'createAndGo' results in enabling the VRRP
            protocol for this virtual router. The information required
            to actually create the conceptual row may be included in
            the SET primitive or may be initialized by the agent on
            the virtual router. Destroying the entry or setting it to
            'notInService' disables VRRP on this virtual router."
        ::= { rcVrrpOperEntry 16 }

rcVrrpOperCriticalIpAddr OBJECT-TYPE
        SYNTAX       IpAddress
        MAX-ACCESS   read-write
        STATUS       current
        DESCRIPTION  "IP address of the interface that will cause a
                     shutdown event."
        ::= { rcVrrpOperEntry 17 }

rcVrrpOperHoldDownTimer OBJECT-TYPE
        SYNTAX       INTEGER (0..21600)
        MAX-ACCESS   read-write
        STATUS       current
        DESCRIPTION
            "Used to configure the amount of time (in seconds)
            to wait before preempting the current vrrp master."
        ::= { rcVrrpOperEntry 18 }

rcVrrpOperHoldDownState OBJECT-TYPE
        SYNTAX       INTEGER {
                        dormant(1),
                        active(2)
                     }
        MAX-ACCESS   read-only
        STATUS       current
        DESCRIPTION
            "Used to indicate the hold-down state of this vrrp
            interface.  If the hold-down timer is operational
            this variable will be set to 'active'.  'dormant'
            otherwise."
        ::= { rcVrrpOperEntry 19 }

rcVrrpOperHoldDownTimeRemaining OBJECT-TYPE
        SYNTAX       INTEGER (0..21600)
        MAX-ACCESS   read-only
        STATUS       current
        DESCRIPTION
            "Used to indicate the amount of time (in seconds)
            left before the rcVrrpOperHoldDownTimer will expire."
        ::= { rcVrrpOperEntry 20 }

rcVrrpOperAction OBJECT-TYPE
        SYNTAX       INTEGER {
                        none(1),
                        preemptHoldDownTimer(2)
                     }
        MAX-ACCESS   read-write
        STATUS       current
        DESCRIPTION
            "Used to trigger an action on this vrrp interface."
        ::= { rcVrrpOperEntry 21 }

rcVrrpOperCriticalIpAddrEnable OBJECT-TYPE
        SYNTAX       TruthValue
        MAX-ACCESS   read-write
        STATUS       current
        DESCRIPTION
            "Indicate if an user-defined critical IP address should be
            enabled. 'NO' = use the default IP address (0.0.0.0).
            No effect if an user-defined IP address does not exist."
        DEFVAL       { false }
        ::= { rcVrrpOperEntry 22 }

rcVrrpOperBackUpMaster OBJECT-TYPE
        SYNTAX       INTEGER {
                        enabled(1),
                        disabled(2)
                     }
        MAX-ACCESS   read-write
        STATUS       current
        DESCRIPTION   "Enable the backup VRRP switch traffic forwarding.
                       This will reduce the traffic in IST link in the time of SMLT."
        DEFVAL       { disabled }
        ::= { rcVrrpOperEntry 23 }

rcVrrpOperBackUpMasterState OBJECT-TYPE
        SYNTAX       INTEGER {
                        up(1),
                        down(2)
                     }
        MAX-ACCESS   read-only
        STATUS       current
        DESCRIPTION "Indicate whether backup VRRP switch traffic forwarding is enabled or not."
        DEFVAL       { down }
        ::= { rcVrrpOperEntry 24 }

rcVrrpOperFasterAdvInterval OBJECT-TYPE
        SYNTAX       Integer32 (200..1000)
        MAX-ACCESS   read-write
        STATUS       current
        DESCRIPTION   "This is the faster advertisement interval, in
                       milliseconds, between sending advertisement messages. When the faster advertisement interval enable is checked, the faster advertisement interval is being used instead of the regular advertisement interval"
        DEFVAL       { 200 }
        ::= { rcVrrpOperEntry 25 }

rcVrrpOperFasterAdvIntervalEnable OBJECT-TYPE
        SYNTAX       INTEGER {
                        enabled(1),
                        disabled(2)
                     }
        MAX-ACCESS   read-write
        STATUS       current
        DESCRIPTION   "Used to indicate if the Faster Advertisement Interval should be used. 'Disable' means use regular Advertisement interval."
        DEFVAL       { disabled }
        ::= { rcVrrpOperEntry 26 }

--   Trap Definitions

rcVrrpTrapStateTransition NOTIFICATION-TYPE
        OBJECTS      { ifIndex,
                       rcVrrpTrapStateTransitionType,
                       rcVrrpTrapStateTransitionCause,
                       rcVrrpOperVrId,
                       rcVrrpOperIpAddr,
                       rcVrrpOperMasterIpAddr
                     }
        STATUS       current
        DESCRIPTION
            "A rcVrrpTrapStateTransition trap signifies a state
            transition has occurred on a particular vrrp interface.
            Implementation of this trap is optional."
        ::= { rcVrrpNotifications 1 }

-- VRRP Router Stats Table

rcVrrpRouterStatsTable OBJECT-TYPE
        SYNTAX SEQUENCE OF RcVrrpRouterStatsEntry
        MAX-ACCESS not-accessible
        STATUS current
        DESCRIPTION
            "Table of virtual router statistics."
        ::= { rcVrrpObjects 3 }
    
rcVrrpRouterStatsEntry OBJECT-TYPE
        SYNTAX RcVrrpRouterStatsEntry
        MAX-ACCESS not-accessible
        STATUS current
        DESCRIPTION
            "An entry in the table, containing statistics information
             about a given virtual router."
        AUGMENTS {
            rcVrrpOperEntry
        }
        ::= { rcVrrpRouterStatsTable 1 }

RcVrrpRouterStatsEntry ::= SEQUENCE {
            rcVrrpStatsIfIndex
                Integer32,
            rcVrrpStatsVrId
                VrId,
            rcVrrpStatsBecomeMaster 
                Counter32,
            rcVrrpStatsAdvertiseRcvd 
                Counter32,
            rcVrrpStatsAdvertiseIntervalErrors 
                Counter32,
            rcVrrpStatsPasswdSecurityViolations
                Counter32,
            rcVrrpStatsHmacSecurityViolations
                Counter32,
            rcVrrpStatsIpTtlErrors 
                Counter32,
            rcVrrpStatsPriorityZeroPktsRcvd 
                Counter32,
            rcVrrpStatsPriorityZeroPktsSent 
                Counter32,
            rcVrrpStatsInvalidTypePktsRcvd 
                Counter32,
            rcVrrpStatsAddressListErrors 
                Counter32,
            rcVrrpStatsUnknownAuthType 
                Counter32,
            rcVrrpStatsAuthTypeErrors 
                Counter32
    }

rcVrrpStatsIfIndex OBJECT-TYPE
        SYNTAX       Integer32
        MAX-ACCESS   read-only
        STATUS       current
        DESCRIPTION  "port interface index."
        ::= { rcVrrpRouterStatsEntry 1 }

rcVrrpStatsVrId OBJECT-TYPE
        SYNTAX       VrId
        MAX-ACCESS   read-only
        STATUS       current
        DESCRIPTION
            "This object contains the Virtual Router Identifier (VRID)."
        ::= { rcVrrpRouterStatsEntry 2 }

rcVrrpStatsBecomeMaster OBJECT-TYPE
        SYNTAX       Counter32
        MAX-ACCESS   read-only
        STATUS       current
        DESCRIPTION
            "The total number of times that this virtual router's state
            has transitioned from BACKUP to MASTER."
        ::= { rcVrrpRouterStatsEntry 3 }

rcVrrpStatsAdvertiseRcvd OBJECT-TYPE
        SYNTAX       Counter32
        MAX-ACCESS   read-only
        STATUS       current
        DESCRIPTION
            "The total number of VRRP advertisements received by this
            virtual router."
        ::= { rcVrrpRouterStatsEntry 4 }

rcVrrpStatsAdvertiseIntervalErrors OBJECT-TYPE
        SYNTAX       Counter32
        MAX-ACCESS   read-only
        STATUS       current
        DESCRIPTION
            "The total number of VRRP advertisement packets received
            for which the advertisement interval is different than the
            one configured for the local virtual router."
        ::= { rcVrrpRouterStatsEntry 5 }

rcVrrpStatsPasswdSecurityViolations OBJECT-TYPE
        SYNTAX       Counter32
        MAX-ACCESS   read-only
        STATUS       current
        DESCRIPTION
            "The total number of VRRP packets received that do not pass
            the simple text password authentification check."
        ::= { rcVrrpRouterStatsEntry 6 }

rcVrrpStatsHmacSecurityViolations OBJECT-TYPE
        SYNTAX       Counter32
        MAX-ACCESS   read-only
        STATUS       current
        DESCRIPTION
            "The total number of VRRP packets received that do not pass
            the HMAC-MD5-96 authentification check."
        ::= { rcVrrpRouterStatsEntry 7 }

rcVrrpStatsIpTtlErrors OBJECT-TYPE
        SYNTAX       Counter32
        MAX-ACCESS   read-only
        STATUS       current
        DESCRIPTION
            "The total number of VRRP packets received by the virtual
            router with IP TTL (Time-To-Live) not equal to 255."
        ::= { rcVrrpRouterStatsEntry 8 }

rcVrrpStatsPriorityZeroPktsRcvd OBJECT-TYPE
        SYNTAX       Counter32
        MAX-ACCESS   read-only
        STATUS       current
        DESCRIPTION
            "The total number of VRRP packets received by the virtual
            router with a priority of '0'."
        ::= { rcVrrpRouterStatsEntry 9 }

rcVrrpStatsPriorityZeroPktsSent OBJECT-TYPE
        SYNTAX       Counter32
        MAX-ACCESS   read-only
        STATUS       current
        DESCRIPTION
            "The total number of VRRP packets sent by the virtual router
            with a priority of '0'."
        ::= { rcVrrpRouterStatsEntry 10 }

rcVrrpStatsInvalidTypePktsRcvd OBJECT-TYPE
        SYNTAX       Counter32
        MAX-ACCESS   read-only
        STATUS       current
        DESCRIPTION
            "The number of VRRP packets received by the virtual router
            with an invalid value in the 'type' field."
        ::= { rcVrrpRouterStatsEntry 11 }

rcVrrpStatsAddressListErrors OBJECT-TYPE
        SYNTAX       Counter32
        MAX-ACCESS   read-only
        STATUS       current
        DESCRIPTION
            "Packets received address list the address list does not
            match the locally configured list for the virtual router."
        ::= { rcVrrpRouterStatsEntry 12 }

rcVrrpStatsUnknownAuthType OBJECT-TYPE
        SYNTAX       Counter32
        MAX-ACCESS   read-only
        STATUS       current
        DESCRIPTION
            "Packets received with an unknown authentication type."
        ::= { rcVrrpRouterStatsEntry 13 }

rcVrrpStatsAuthTypeErrors OBJECT-TYPE
        SYNTAX       Counter32
        MAX-ACCESS   read-only
        STATUS       current
        DESCRIPTION
            "Packets received with 'Auth Type' not equal to the locally
             configured authentication method ('vrrpOperAuthType')."
        ::= { rcVrrpRouterStatsEntry 14 }

-- System Time Grp

rcUserSetTimeYear OBJECT-TYPE
        SYNTAX        INTEGER (1998..2097)
        MAX-ACCESS    read-write
        STATUS        current
        DESCRIPTION   "Year of the time."
        DEFVAL {1998}
        ::= { rcUserSetTime 1 }

rcUserSetTimeMonth OBJECT-TYPE
        SYNTAX        INTEGER (1..12)
        MAX-ACCESS    read-write
        STATUS        current
        DESCRIPTION   "Month of the time."
        DEFVAL {1}
        ::= { rcUserSetTime 2 }

rcUserSetTimeDate OBJECT-TYPE
        SYNTAX        INTEGER (1..31)
        MAX-ACCESS    read-write
        STATUS        current
        DESCRIPTION   "Date of the time."
        DEFVAL {1}
        ::= { rcUserSetTime 3 }

rcUserSetTimeHour OBJECT-TYPE
        SYNTAX        INTEGER (0..23)
        MAX-ACCESS    read-write
        STATUS        current
        DESCRIPTION   "Hour of the time."
        DEFVAL {0}
        ::= { rcUserSetTime 4 }

rcUserSetTimeMinute OBJECT-TYPE
        SYNTAX        INTEGER (0..59)
        MAX-ACCESS    read-write
        STATUS        current
        DESCRIPTION   "Minute of the time."
        DEFVAL {0}
        ::= { rcUserSetTime 5 }

rcUserSetTimeSecond OBJECT-TYPE
        SYNTAX        INTEGER (0..59)
        MAX-ACCESS    read-write
        STATUS        current
        DESCRIPTION   "Second of the time."
        DEFVAL {0}
        ::= { rcUserSetTime 6 }

rcUserSetTimeTimezone OBJECT-TYPE
	SYNTAX        INTEGER {
				cet(1),
				cst6Cdt(2),
				cuba(3),
				eet(4),
				est(5),
				est5Edt(6),
				egypt(7),
				eire(8),
				factory(9),
				gb(10),
				gbEire(11),
				gmt(12),
				gmtE0(13),
				gmtW0(14),
				gmt0(15),
				greenwich(16),
				hst(17),
				hongkong(18),
				iceland(19),
				iran(20),
				israel(21),
				jamaica(22),
				japan(23),
				kwajalein(24),
				libya(25),
				met(26),
				mst(27),
				mst7MDT(28),
				nz(29),
				nzCHAT(30),
				navajo(31),
				prc(32),
				pst8PDT(33),
				poland(34),
				portugal(35),
				roc(36),
				rok(37),
				singapore(38),
				turkey(39),
				uct(40),
				utc(41),
				universal(42),
				wSU(43),
				wet(44),
				zulu(45),
				africa-Abidjan(46),
				africa-Accra(47),
				africa-AddisAbaba(48),
				africa-Algiers(49),
				africa-Asmera(50),
				africa-Bamako(51),
				africa-Bangui(52),
				africa-Banjul(53),
				africa-Bissau(54),
				africa-Blantyre(55),
				africa-Brazzaville(56),
				africa-Bujumbura(57),
				africa-Cairo(58),
				africa-Casablanca(59),
				africa-Ceuta(60),
				africa-Conakry(61),
				africa-Dakar(62),
				africa-DarEsSalaam(63),
				africa-Djibouti(64),
				africa-Douala(65),
				africa-ElAaiun(66),
				africa-Freetown(67),
				africa-Gaborone(68),
				africa-Harare(69),
				africa-Johannesburg(70),
				africa-Kampala(71),
				africa-Khartoum(72),
				africa-Kigali(73),
				africa-Kinshasa(74),
				africa-Lagos(75),
				africa-Libreville(76),
				africa-Lome(77),
				africa-Luanda(78),
				africa-Lubumbashi(79),
				africa-Lusaka(80),
				africa-Malabo(81),
				africa-Maputo(82),
				africa-Maseru(83),
				africa-Mbabane(84),
				africa-Mogadishu(85),
				africa-Monrovia(86),
				africa-Nairobi(87),
				africa-Ndjamena(88),
				africa-Niamey(89),
				africa-Nouakchott(90),
				africa-Ouagadougou(91),
				africa-PortoNovo(92),
				africa-SaoTome(93),
				africa-Timbuktu(94),
				africa-Tripoli(95),
				africa-Tunis(96),
				africa-Windhoek(97),
				america-Adak(98),
				america-Anchorage(99),
				america-Anguilla(100),
				america-Antigua(101),
				america-Araguaina(102),
				america-Aruba(103),
				america-Asuncion(104),
				america-Atikokan(105),
				america-Atka(106),
				america-Bahia(107),
				america-Barbados(108),
				america-Belem(109),
				america-Belize(110),
				america-BlancSablon(111),
				america-BoaVista(112),
				america-Bogota(113),
				america-Boise(114),
				america-BuenosAires(115),
				america-CambridgeBay(116),
				america-CampoGrande(117),
				america-Cancun(118),
				america-Caracas(119),
				america-Catamarca(120),
				america-Cayenne(121),
				america-Cayman(122),
				america-Chicago(123),
				america-Chihuahua(124),
				america-CoralHarbour(125),
				america-Cordoba(126),
				america-CostaRica(127),
				america-Cuiaba(128),
				america-Curacao(129),
				america-Danmarkshavn(130),
				america-Dawson(131),
				america-DawsonCreek(132),
				america-Denver(133),
				america-Detroit(134),
				america-Dominica(135),
				america-Edmonton(136),
				america-Eirunepe(137),
				america-ElSalvador(138),
				america-Ensenada(139),
				america-FortWayne(140),
				america-Fortaleza(141),
				america-GlaceBay(142),
				america-Godthab(143),
				america-GooseBay(144),
				america-GrandTurk(145),
				america-Grenada(146),
				america-Guadeloupe(147),
				america-Guatemala(148),
				america-Guayaquil(149),
				america-Guyana(150),
				america-Halifax(151),
				america-Havana(152),
				america-Hermosillo(153),
				america-Indianapolis(154),
				america-Inuvik(155),
				america-Iqaluit(156),
				america-Jamaica(157),
				america-Jujuy(158),
				america-Juneau(159),
				america-KnoxIN(160),
				america-LaPaz(161),
				america-Lima(162),
				america-LosAngeles(163),
				america-Louisville(164),
				america-Maceio(165),
				america-Managua(166),
				america-Manaus(167),
				america-Martinique(168),
				america-Mazatlan(169),
				america-Mendoza(170),
				america-Menominee(171),
				america-Merida(172),
				america-MexicoCity(173),
				america-Miquelon(174),
				america-Moncton(175),
				america-Monterrey(176),
				america-Montevideo(177),
				america-Montreal(178),
				america-Montserrat(179),
				america-Nassau(180),
				america-NewYork(181),
				america-Nipigon(182),
				america-Nome(183),
				america-Noronha(184),
				america-Panama(185),
				america-Pangnirtung(186),
				america-Paramaribo(187),
				america-Phoenix(188),
				america-PortAuPrince(189),
				america-PortOfSpain(190),
				america-PortoAcre(191),
				america-PortoVelho(192),
				america-PuertoRico(193),
				america-RainyRiver(194),
				america-RankinInlet(195),
				america-Recife(196),
				america-Regina(197),
				america-RioBranco(198),
				america-Rosario(199),
				america-Santiago(200),
				america-SantoDomingo(201),
				america-SaoPaulo(202),
				america-Scoresbysund(203),
				america-Shiprock(204),
				america-StJohns(205),
				america-StKitts(206),
				america-StLucia(207),
				america-StThomas(208),
				america-StVincent(209),
				america-SwiftCurrent(210),
				america-Tegucigalpa(211),
				america-Thule(212),
				america-ThunderBay(213),
				america-Tijuana(214),
				america-Toronto(215),
				america-Tortola(216),
				america-Vancouver(217),
				america-Virgin(218),
				america-Whitehorse(219),
				america-Winnipeg(220),
				america-Yakutat(221),
				america-Yellowknife(222),
				antarctica-Casey(223),
				antarctica-Davis(224),
				antarctica-DumontDUrville(225),
				antarctica-Mawson(226),
				antarctica-McMurdo(227),
				antarctica-Palmer(228),
				antarctica-Rothera(229),
				antarctica-SouthPole(230),
				antarctica-Syowa(231),
				antarctica-Vostok(232),
				arctic-Longyearbyen(233),
				asia-Aden(234),
				asia-Almaty(235),
				asia-Amman(236),
				asia-Anadyr(237),
				asia-Aqtau(238),
				asia-Aqtobe(239),
				asia-Ashgabat(240),
				asia-Ashkhabad(241),
				asia-Baghdad(242),
				asia-Bahrain(243),
				asia-Baku(244),
				asia-Bangkok(245),
				asia-Beirut(246),
				asia-Bishkek(247),
				asia-Brunei(248),
				asia-Calcutta(249),
				asia-Choibalsan(250),
				asia-Chongqing(251),
				asia-Chungking(252),
				asia-Colombo(253),
				asia-Dacca(254),
				asia-Damascus(255),
				asia-Dhaka(256),
				asia-Dili(257),
				asia-Dubai(258),
				asia-Dushanbe(259),
				asia-Gaza(260),
				asia-Harbin(261),
				asia-HongKong(262),
				asia-Hovd(263),
				asia-Irkutsk(264),
				asia-Istanbul(265),
				asia-Jakarta(266),
				asia-Jayapura(267),
				asia-Jerusalem(268),
				asia-Kabul(269),
				asia-Kamchatka(270),
				asia-Karachi(271),
				asia-Kashgar(272),
				asia-Katmandu(273),
				asia-Krasnoyarsk(274),
				asia-KualaLumpur(275),
				asia-Kuching(276),
				asia-Kuwait(277),
				asia-Macao(278),
				asia-Macau(279),
				asia-Magadan(280),
				asia-Makassar(281),
				asia-Manila(282),
				asia-Muscat(283),
				asia-Nicosia(284),
				asia-Novosibirsk(285),
				asia-Omsk(286),
				asia-Oral(287),
				asia-PhnomPenh(288),
				asia-Pontianak(289),
				asia-Pyongyang(290),
				asia-Qatar(291),
				asia-Qyzylorda(292),
				asia-Rangoon(293),
				asia-Riyadh(294),
				asia-Riyadh87(295),
				asia-Riyadh88(296),
				asia-Riyadh89(297),
				asia-Saigon(298),
				asia-Sakhalin(299),
				asia-Samarkand(300),
				asia-Seoul(301),
				asia-Shanghai(302),
				asia-Singapore(303),
				asia-Taipei(304),
				asia-Tashkent(305),
				asia-Tbilisi(306),
				asia-Tehran(307),
				asia-TelAviv(308),
				asia-Thimbu(309),
				asia-Thimphu(310),
				asia-Tokyo(311),
				asia-UjungPandang(312),
				asia-Ulaanbaatar(313),
				asia-UlanBator(314),
				asia-Urumqi(315),
				asia-Vientiane(316),
				asia-Vladivostok(317),
				asia-Yakutsk(318),
				asia-Yekaterinburg(319),
				asia-Yerevan(320),
				atlantic-Azores(321),
				atlantic-Bermuda(322),
				atlantic-Canary(323),
				atlantic-CapeVerde(324),
				atlantic-Faeroe(325),
				atlantic-JanMayen(326),
				atlantic-Madeira(327),
				atlantic-Reykjavik(328),
				atlantic-SouthGeorgia(329),
				atlantic-StHelena(330),
				atlantic-Stanley(331),
				australia-ACT(332),
				australia-Adelaide(333),
				australia-Brisbane(334),
				australia-BrokenHill(335),
				australia-Canberra(336),
				australia-Currie(337),
				australia-Darwin(338),
				australia-Hobart(339),
				australia-LHI(340),
				australia-Lindeman(341),
				australia-LordHowe(342),
				australia-Melbourne(343),
				australia-NSW(344),
				australia-North(345),
				australia-Perth(346),
				australia-Queensland(347),
				australia-South(348),
				australia-Sydney(349),
				australia-Tasmania(350),
				australia-Victoria(351),
				australia-West(352),
				australia-Yancowinna(353),
				brazil-Acre(354),
				brazil-DeNoronha(355),
				brazil-East(356),
				brazil-West(357),
				canada-Atlantic(358),
				canada-Central(359),
				canada-EastSaskatchewan(360),
				canada-Eastern(361),
				canada-Mountain(362),
				canada-Newfoundland(363),
				canada-Pacific(364),
				canada-Saskatchewan(365),
				canada-Yukon(366),
				chile-Continental(367),
				chile-EasterIsland(368),
				etc-GMT(369),
				etc-GMTE0(370),
				etc-GMTE1(371),
				etc-GMTE10(372),
				etc-GMTE11(373),
				etc-GMTE12(374),
				etc-GMTE2(375),
				etc-GMTE3(376),
				etc-GMTE4(377),
				etc-GMTE5(378),
				etc-GMTE6(379),
				etc-GMTE7(380),
				etc-GMTE8(381),
				etc-GMTE9(382),
				etc-GMTW0(383),
				etc-GMTW1(384),
				etc-GMTW10(385),
				etc-GMTW11(386),
				etc-GMTW12(387),
				etc-GMTW13(388),
				etc-GMTW14(389),
				etc-GMTW2(390),
				etc-GMTW3(391),
				etc-GMTW4(392),
				etc-GMTW5(393),
				etc-GMTW6(394),
				etc-GMTW7(395),
				etc-GMTW8(396),
				etc-GMTW9(397),
				etc-GMT0(398),
				etc-Greenwich(399),
				etc-UCT(400),
				etc-UTC(401),
				etc-Universal(402),
				etc-Zulu(403),
				europe-Amsterdam(404),
				europe-Andorra(405),
				europe-Athens(406),
				europe-Belfast(407),
				europe-Belgrade(408),
				europe-Berlin(409),
				europe-Bratislava(410),
				europe-Brussels(411),
				europe-Bucharest(412),
				europe-Budapest(413),
				europe-Chisinau(414),
				europe-Copenhagen(415),
				europe-Dublin(416),
				europe-Gibraltar(417),
				europe-Guernsey(418),
				europe-Helsinki(419),
				europe-IsleOfMan(420),
				europe-Istanbul(421),
				europe-Jersey(422),
				europe-Kaliningrad(423),
				europe-Kiev(424),
				europe-Lisbon(425),
				europe-Ljubljana(426),
				europe-London(427),
				europe-Luxembourg(428),
				europe-Madrid(429),
				europe-Malta(430),
				europe-Mariehamn(431),
				europe-Minsk(432),
				europe-Monaco(433),
				europe-Moscow(434),
				europe-Nicosia(435),
				europe-Oslo(436),
				europe-Paris(437),
				europe-Prague(438),
				europe-Riga(439),
				europe-Rome(440),
				europe-Samara(441),
				europe-SanMarino(442),
				europe-Sarajevo(443),
				europe-Simferopol(444),
				europe-Skopje(445),
				europe-Sofia(446),
				europe-Stockholm(447),
				europe-Tallinn(448),
				europe-Tirane(449),
				europe-Tiraspol(450),
				europe-Uzhgorod(451),
				europe-Vaduz(452),
				europe-Vatican(453),
				europe-Vienna(454),
				europe-Vilnius(455),
				europe-Volgograd(456),
				europe-Warsaw(457),
				europe-Zagreb(458),
				europe-Zaporozhye(459),
				europe-Zurich(460),
				indian-Antananarivo(461),
				indian-Chagos(462),
				indian-Christmas(463),
				indian-Cocos(464),
				indian-Comoro(465),
				indian-Kerguelen(466),
				indian-Mahe(467),
				indian-Maldives(468),
				indian-Mauritius(469),
				indian-Mayotte(470),
				indian-Reunion(471),
				mexico-BajaNorte(472),
				mexico-BajaSur(473),
				mexico-General(474),
				mideast-Riyadh87(475),
				mideast-Riyadh88(476),
				mideast-Riyadh89(477),
				pacific-Apia(478),
				pacific-Auckland(479),
				pacific-Chatham(480),
				pacific-Easter(481),
				pacific-Efate(482),
				pacific-Enderbury(483),
				pacific-Fakaofo(484),
				pacific-Fiji(485),
				pacific-Funafuti(486),
				pacific-Galapagos(487),
				pacific-Gambier(488),
				pacific-Guadalcanal(489),
				pacific-Guam(490),
				pacific-Honolulu(491),
				pacific-Johnston(492),
				pacific-Kiritimati(493),
				pacific-Kosrae(494),
				pacific-Kwajalein(495),
				pacific-Majuro(496),
				pacific-Marquesas(497),
				pacific-Midway(498),
				pacific-Nauru(499),
				pacific-Niue(500),
				pacific-Norfolk(501),
				pacific-Noumea(502),
				pacific-PagoPago(503),
				pacific-Palau(504),
				pacific-Pitcairn(505),
				pacific-Ponape(506),
				pacific-PortMoresby(507),
				pacific-Rarotonga(508),
				pacific-Saipan(509),
				pacific-Samoa(510),
				pacific-Tahiti(511),
				pacific-Tarawa(512),
				pacific-Tongatapu(513),
				pacific-Truk(514),
				pacific-Wake(515),
				pacific-Wallis(516),
				pacific-Yap(517),
				us-Alaska(518),
				us-Aleutian(519),
				us-Arizona(520),
				us-Central(521),
				us-EastIndiana(522),
				us-Eastern(523),
				us-Hawaii(524),
				us-IndianaStarke(525),
				us-Michigan(526),
				us-Mountain(527),
				us-Pacific(528),
				us-PacificNew(529),
				us-Samoa(530),
				america-Argentina-BuenosAires(531),
				america-Argentina-Catamarca(532),
				america-Argentina-ComodRivadavia(533),
				america-Argentina-Cordoba(534),
				america-Argentina-Jujuy(535),
				america-Argentina-LaRioja(536),
				america-Argentina-Mendoza(537),
				america-Argentina-RioGallegos(538),
				america-Argentina-SanJuan(539),
				america-Argentina-Tucuman(540),
				america-Argentina-Ushuaia(541),
				america-Indiana-Indianapolis(542),
				america-Indiana-Knox(543),
				america-Indiana-Marengo(544),
				america-Indiana-Petersburg(545),
				america-Indiana-Vevay(546),
				america-Indiana-Vincennes(547),
				america-Kentucky-Louisville(548),
				america-Kentucky-Monticello(549),
				america-NorthDakota-Center(550),
				america-NorthDakota-NewSalem(551)
		      }
	MAX-ACCESS    read-write
	STATUS	      current
	DESCRIPTION   "Timezone values. Since + is not a valid character inside enum 
		       declaration, E(ast) and W(est) are used to indicate + and - 
		       respectively. For example, etc-GMTE1 indicates Etc-GMT+1 and 
		       etc-GMTW1 indicates Etc-GMT-1."
	::= { rcUserSetTime 7 }

-- rcL2Redundancy Group

rcL2RedundancyHaCpuState OBJECT-TYPE
        SYNTAX          INTEGER
                        {
                            initialization(0),
                            oneWayActive(1),
                            twoWayActive(2),
                            synchronized(3),
                            remoteIncompatible(4),
                            error(5),
                            disabled(6),
                            peerNotConnected(7),
                            peerConnected(8),
                            lostPeerConnection(9),
                            notSynchronized(10),
                            synchronizeInProgress(11)
                        }
        MAX-ACCESS      read-only
        STATUS          current
        DESCRIPTION     "Indicate the Ha-CPU state. 
                         initialization - indicate the CPU is in this state. 
                         oneWayActive - Modules that need to be 
                         synchronized have registered with the framework (either 
                         locally or a message was received from remote CPU (1). 
                         twoWayActive - Modules that need to be synchronized have 
                         registered with the framework (either locally or a message 
                         was received from remote CPU (2). 
                         synchronized  - Table based synchroniztion was completed 
                         on the current CPU (3).  
                         remoteIncompatible - CPUs framework version is incompatible 
                         with the remote CPU (4). 
                         error  - If an invalid event is generated in a given state the 
                         CPU enters Error state (5). 
                         disabled - High Availability is not enabled (6).
                         peerNotConnected - no peer connection is established (7).
                         peerConnected - peer connection is established (8).
                         lostPeerConnection - lost connection to peer/Standby CPU (9).
                         notSynchronized - Table Sync is not complete (10).
                         synchronizeInProgress - Table Sync is in progress (11)."
        ::= { rcL2Redundancy 1 }

rcL2RedundancyHaEvent OBJECT-TYPE
        SYNTAX          INTEGER
                        {
                            restart(0),
                            systemRegistrationDone(1),
                            tableSynchronizationDone(2),
                            versionIncompatible(3),
                            noEvent(4)
                        }
        MAX-ACCESS      read-only
        STATUS          current
        DESCRIPTION     "Indicate the Ha event status. 
                         restart (0) - Causes the state machine to restart 
                         systemRegistrationDone (1)- Causes the CPU to transfer to 
                         One Way or Two Way Active state. Locally or message received 
                         from remote CPU.  
                         tableSynchronizationDone (2) - Causes the CPU to 
                         transfer to Synchronized state. 
                         versionIncompatible (3) - Causes the CPU to go to Remote 
                         Incompatible state 
                         noEvent (4) - Means no event has occured uptill now. "
        ::= { rcL2Redundancy 2 }

rcL2RedundancyEnable OBJECT-TYPE
        SYNTAX          EnableValue
        MAX-ACCESS      read-write
        STATUS          current
        DESCRIPTION     "Indicate the feature enable/disable."
        ::= { rcL2Redundancy 3 }

rcL2RedundancyStandbyCpu OBJECT-TYPE
        SYNTAX          INTEGER {
                           hotStandbyCPU(1),
                           warmStandbyCPU(2),
                           standbyCPUNotPresent(3)
                        }
        MAX-ACCESS      read-only
        STATUS          current
        DESCRIPTION     "Indicate if the L2 Redundancy is enabled on the standby CPU."
        ::= { rcL2Redundancy 4 }


-- Ntp Group
-- Ntp Global Information

rcNtpGlobal   OBJECT IDENTIFIER        ::= { rcNtp 1 }

rcNtpGlobalEnable OBJECT-TYPE
     SYNTAX       TruthValue
     MAX-ACCESS	 read-write
     STATUS       current
     DESCRIPTION  "Enable/disable NTP feature"
     DEFVAL       { false }
     ::= { rcNtpGlobal 1 }

rcNtpGlobalInterval OBJECT-TYPE
     SYNTAX       INTEGER (10..1440)
     MAX-ACCESS	 read-write
     STATUS       current
     DESCRIPTION  "Time interval between successive NTP updates in minutes."
     DEFVAL       { 15 }
     ::= { rcNtpGlobal 2 }		


-- Ntp Server Table Information

rcNtpServerTable OBJECT-TYPE
     SYNTAX       SEQUENCE OF RcNtpServerEntry
     MAX-ACCESS   not-accessible
     STATUS       current
     DESCRIPTION  "The NTP server table. This table lists the information
                   of a NTP server"
     ::= { rcNtp 2 }

rcNtpServerEntry OBJECT-TYPE
        SYNTAX        RcNtpServerEntry
        MAX-ACCESS    not-accessible
        STATUS        current
        DESCRIPTION   "A NTP server table entry."
        INDEX         { rcNtpServerAddress }
        ::= { rcNtpServerTable 1 }

RcNtpServerEntry ::=
     SEQUENCE {
             rcNtpServerAddress IpAddress,
             rcNtpServerEnable TruthValue,
             rcNtpServerAuthentication TruthValue,
  	     rcNtpServerKeyId INTEGER,
             rcNtpServerAccessAttempts Counter32,
             rcNtpServerAccessSuccess Counter32,
             rcNtpServerAccessFailure Counter32,
             rcNtpServerRowStatus RowStatus,
             rcNtpServerStratum DisplayString,
             rcNtpServerVersion DisplayString,
             rcNtpServerRootDelay DisplayString,
             rcNtpServerPrecision DisplayString,
             rcNtpServerReachable DisplayString,
             rcNtpServerSynchronized DisplayString
     }

rcNtpServerAddress OBJECT-TYPE
     SYNTAX         IpAddress
     MAX-ACCESS     read-only
     STATUS         current
     DESCRIPTION    "Server IP address of NTP time source referred to in 
                     this table entry." 
     ::= { rcNtpServerEntry 1 }

rcNtpServerEnable OBJECT-TYPE
     SYNTAX         TruthValue
     MAX-ACCESS     read-write
     STATUS         current
     DESCRIPTION    "Enable or disable this server for participation in
                     time update."
     DEFVAL         { true }  
     ::= { rcNtpServerEntry 2 }

rcNtpServerAuthentication OBJECT-TYPE
     SYNTAX         TruthValue
     MAX-ACCESS     read-write
     STATUS         current
     DESCRIPTION    "Enable or disable the MD5 Authentication on this
                     serve."
     DEFVAL         { false }  
     ::= { rcNtpServerEntry 3 }

rcNtpServerKeyId OBJECT-TYPE
     SYNTAX         INTEGER (0..2147483647)
     MAX-ACCESS     read-write
     STATUS         current
     DESCRIPTION    "Public Key used to generate MD5 digest for this 
                     server."
     DEFVAL         { 0 }  
     ::= { rcNtpServerEntry 4 }

rcNtpServerAccessAttempts OBJECT-TYPE
     SYNTAX         Counter32
     MAX-ACCESS     read-only
     STATUS         current
     DESCRIPTION    "The number of NTP requests sent to this server"
     ::= { rcNtpServerEntry 5 }

rcNtpServerAccessSuccess OBJECT-TYPE
     SYNTAX         Counter32
     MAX-ACCESS     read-only
     STATUS         current
     DESCRIPTION    "The number of times this server was selected to
                     update the time"
     ::= { rcNtpServerEntry 6 }

rcNtpServerAccessFailure OBJECT-TYPE
     SYNTAX         Counter32
     MAX-ACCESS     read-only
     STATUS         current
     DESCRIPTION    "The number of times this server was rejected from
                     updating the time"
     ::= { rcNtpServerEntry 7 }

rcNtpServerRowStatus OBJECT-TYPE
        SYNTAX        RowStatus
        MAX-ACCESS    read-write
        STATUS        current
        DESCRIPTION   "Used to create/delete entries."
        ::= { rcNtpServerEntry 8 }

rcNtpServerStratum OBJECT-TYPE
     SYNTAX         DisplayString (SIZE (0..16))
     MAX-ACCESS     read-only
     STATUS         current
     DESCRIPTION    "Stratum of this server"
     ::= { rcNtpServerEntry 9 }

rcNtpServerVersion OBJECT-TYPE
     SYNTAX         DisplayString (SIZE (0..16))
     MAX-ACCESS     read-only
     STATUS         current
     DESCRIPTION    "NTP version of this server"
     ::= { rcNtpServerEntry 10 }

rcNtpServerRootDelay OBJECT-TYPE
     SYNTAX         DisplayString (SIZE (0..32))
     MAX-ACCESS     read-only
     STATUS         current
     DESCRIPTION    "Root Delay of this server"
     ::= { rcNtpServerEntry 11 }

rcNtpServerPrecision OBJECT-TYPE
     SYNTAX         DisplayString (SIZE (0..32))
     MAX-ACCESS     read-only
     STATUS         current
     DESCRIPTION    "NTP precision of this server in seconds"
     ::= { rcNtpServerEntry 12 }

rcNtpServerReachable OBJECT-TYPE
     SYNTAX         DisplayString (SIZE (0..16))
     MAX-ACCESS     read-only
     STATUS         current
     DESCRIPTION    "NTP Reachability of this server"
     ::= { rcNtpServerEntry 13 }

rcNtpServerSynchronized OBJECT-TYPE
     SYNTAX         DisplayString (SIZE (0..16))
     MAX-ACCESS     read-only
     STATUS         current
     DESCRIPTION    "Status of synchronization with this server"
     ::= { rcNtpServerEntry 14 }

-- Ntp Key Table Information

rcNtpKeyTable OBJECT-TYPE
     SYNTAX       SEQUENCE OF RcNtpKeyEntry
     MAX-ACCESS   not-accessible
     STATUS       current
     DESCRIPTION  "The NTP key table. This table lists the private key
                   of the public key Id"
     ::= {rcNtp 3 }

rcNtpKeyEntry OBJECT-TYPE
        SYNTAX        RcNtpKeyEntry
        MAX-ACCESS    not-accessible
        STATUS        current
        DESCRIPTION   "A NTP key table entry."
        INDEX         { rcNtpKeyId }
        ::= { rcNtpKeyTable 1 }

RcNtpKeyEntry ::=
     SEQUENCE {
             rcNtpKeyId INTEGER,
             rcNtpKeySecret DisplayString,
             rcNtpKeyRowStatus RowStatus
     }

rcNtpKeyId OBJECT-TYPE
     SYNTAX         INTEGER (1..2147483647)
     MAX-ACCESS     read-only
     STATUS         current
     DESCRIPTION    "Public Key used to generate MD5 digest"
     ::= { rcNtpKeyEntry 1 }

rcNtpKeySecret OBJECT-TYPE
     SYNTAX         DisplayString (SIZE (0..8))
     MAX-ACCESS     read-write
     STATUS         current
     DESCRIPTION    "Private Key used to generate MD5 Digest"
     ::= { rcNtpKeyEntry 2 }

rcNtpKeyRowStatus OBJECT-TYPE
     SYNTAX        RowStatus
     MAX-ACCESS    read-write
     STATUS        current
     DESCRIPTION   "Used to create/delete entries."
     ::= { rcNtpKeyEntry 3 }


-- rc2k Group

rc2kChassis     OBJECT IDENTIFIER ::= { rc2k 1 }

rc2kChassisPortOperStatus  OBJECT-TYPE
        SYNTAX          OCTET STRING (SIZE(256))
        MAX-ACCESS      read-only
        STATUS          current
        DESCRIPTION     "A bit array that contains the oper-status
                        of the ports in the device.  2 bits are used
                        for each port.  The high order 2 bits of the
                        first octet represent port #0, the next two
                        bits are used for port #1, etc.  The status
                        is encoded with the following scheme :

                        value   meaning
                        -----   -------
                          0     no-link (admin=up, oper=down)
                          1     up	(admin=up, oper=up)
                          2     down	(admin=down, oper=down)
                          3     testing	(admin=test, oper=test)
                        "
        ::= { rc2kChassis 1 }

rc2kChassisTemperature OBJECT-TYPE
        SYNTAX          Gauge32
        MAX-ACCESS      read-only
        STATUS          current
        DESCRIPTION     "Used to indicate the core operating temperature
                        of the chassis.  This value represents the degree
			in celsius of the air inside the chassis."
        ::= { rc2kChassis 2 }

rc2kChassisBaseMacAddr OBJECT-TYPE 
        SYNTAX          MacAddress 
        MAX-ACCESS      read-only 
        STATUS          current 
        DESCRIPTION     "base mac addr"
        ::= { rc2kChassis 5 }

rc2kChassisMacAddrCapacity OBJECT-TYPE
        SYNTAX          Integer32
	MAX-ACCESS      read-only
	STATUS          current
	DESCRIPTION     "Mac Address Capacity"
	::= { rc2kChassis 6 }

rc2kChassisSystemTempLedColor OBJECT-TYPE
        SYNTAX          INTEGER {
			   green(1),
                           red(2),
                           amber(3)
                        }
	MAX-ACCESS      read-only
	STATUS          current
	DESCRIPTION     "Used to indicate the led color of the system temperature
			 which is under or above the threshold.  The threshold is 60 degree
			 in celsius.		
			 'green' menas normal. And temperature under threshold.
 			 'red' means one of the zone temperature is above the threshold.
                         'amber' is the initial state, means device have not start to
			       chekc the temperature yet."
			 
	::= { rc2kChassis 10 }

-- 2k CPU Serial Port table

rc2kCpuSerialPortTable OBJECT-TYPE
        SYNTAX        SEQUENCE OF Rc2kCpuSerialPortEntry
        MAX-ACCESS    not-accessible
        STATUS        current
        DESCRIPTION   "2k CPU Serial Port table"
        ::= { rc2k 3 }

rc2kCpuSerialPortEntry OBJECT-TYPE
        SYNTAX        Rc2kCpuSerialPortEntry
        MAX-ACCESS    not-accessible
        STATUS        current
        DESCRIPTION   "Entry containing information of 2k CPU Serial Port"
        INDEX         { rc2kCpuSerialPortIfIndex }
        ::= { rc2kCpuSerialPortTable 1 }

Rc2kCpuSerialPortEntry ::= SEQUENCE {
                rc2kCpuSerialPortIfIndex          InterfaceIndex,
		            rc2kCpuSerialPortDescr		  DisplayString,
                rc2kCpuSerialPortMode             INTEGER,
                rc2kCpuSerialPortAdminStatus      INTEGER,
                rc2kCpuSerialPortOperStatus       INTEGER,
                rc2kCpuSerialPortBaudRate         INTEGER,
                rc2kCpuSerialPortDataBits         INTEGER,
                rc2kCpuSerialPortMyAddr           IpAddress,
                rc2kCpuSerialPortPeerAddr         IpAddress,
                rc2kCpuSerialPortSlipMtu          INTEGER,
                rc2kCpuSerialPortSlipTxRxCompress TruthValue,
                rc2kCpuSerialPortSlipRxCompress   TruthValue,
                rc2kCpuSerialPortPppConfigFile    OCTET STRING (SIZE(0..256))
        }

rc2kCpuSerialPortIfIndex OBJECT-TYPE
        SYNTAX        	InterfaceIndex
        MAX-ACCESS       	read-only
        STATUS        	current
        DESCRIPTION   	"IfIndex for this port."
        ::= { rc2kCpuSerialPortEntry 1 }

rc2kCpuSerialPortDescr OBJECT-TYPE
        SYNTAX        	DisplayString (SIZE (0..128))
        MAX-ACCESS      	read-only
        STATUS          current 
        DESCRIPTION   	"Port description."
        ::= { rc2kCpuSerialPortEntry 2 }

rc2kCpuSerialPortMode OBJECT-TYPE
        SYNTAX        	INTEGER
                      	{
                            cli(1),
                            slip(2),
                            ppp(3)
                     	 }
        MAX-ACCESS      	read-write
        STATUS       	current 
        DESCRIPTION   	"Used to configure the mode this port should
			operate in."
        ::= { rc2kCpuSerialPortEntry 3 }

rc2kCpuSerialPortAdminStatus OBJECT-TYPE
        SYNTAX        	INTEGER
                      	{
                            up(1),
                            down(2),
                            unknown(3)
                      	}
        MAX-ACCESS       read-write
        STATUS          current	
        DESCRIPTION     "Used to configure the administrative status
                        setting for this port."
        ::= { rc2kCpuSerialPortEntry 4 }

rc2kCpuSerialPortOperStatus OBJECT-TYPE
        SYNTAX        	INTEGER
                      	{
                            up(1),
                            down(2),
                            unknown(3)
                      	}
        MAX-ACCESS       read-only
        STATUS          current	
        DESCRIPTION     "Used to indicate the operational status
                        setting for this port."
        ::= { rc2kCpuSerialPortEntry 5 }

rc2kCpuSerialPortBaudRate OBJECT-TYPE
        SYNTAX        	INTEGER
                      	{
                            baud2400(2400),
                            baud4800(4800),
                            baud9600(9600),
                            baud19200(19200),
                            baud38400(38400),
                            baud57600(57600),
                            baud115200(115200)
                      	}
        MAX-ACCESS       read-write
        STATUS        	current
        DESCRIPTION   	"Used to configure the baud rate of this port."
        ::= { rc2kCpuSerialPortEntry 6 }

rc2kCpuSerialPortDataBits OBJECT-TYPE
        SYNTAX        	INTEGER
                      	{
                            seven(1),
                            eight(2)
                      	}
        MAX-ACCESS       read-write
        STATUS        	current
        DESCRIPTION   	"Used to configure the number of data bits, per
			byte of data, this port should send/receive."
        ::= { rc2kCpuSerialPortEntry 7 }

rc2kCpuSerialPortMyAddr OBJECT-TYPE
        SYNTAX        	IpAddress
        MAX-ACCESS       read-write
        STATUS          current	
        DESCRIPTION   	"Used to configure this port's IP address.
			Used for both 'slip' and 'ppp' modes."
        ::= { rc2kCpuSerialPortEntry 8 }

rc2kCpuSerialPortPeerAddr OBJECT-TYPE
        SYNTAX        	IpAddress
        MAX-ACCESS       read-write
        STATUS          current 
        DESCRIPTION   	"Used to configure the peer's IP address.
			Used for both 'slip' and 'ppp' modes."
        ::= { rc2kCpuSerialPortEntry 9 }

rc2kCpuSerialPortSlipMtu OBJECT-TYPE
        SYNTAX        	INTEGER (0..224)
        MAX-ACCESS       read-write
        STATUS          current 
        DESCRIPTION   	"Used to configure the MTU for this port.
			Used for slip only."
        ::= { rc2kCpuSerialPortEntry 10 }

rc2kCpuSerialPortSlipTxRxCompress OBJECT-TYPE
        SYNTAX        	TruthValue
        MAX-ACCESS       read-write
        STATUS          current	
        DESCRIPTION   	"Used to enable/disable compression of TCP/IP
			packet headers on this port.  Used for slip only."
	DEFVAL	      	{ true }
        ::= { rc2kCpuSerialPortEntry 11 }

rc2kCpuSerialPortSlipRxCompress OBJECT-TYPE
        SYNTAX        	TruthValue
        MAX-ACCESS       read-write
        STATUS          current	
        DESCRIPTION   	"Used to enable/disable compression for receiving
			packets on this port.  Used for slip only."	
	DEFVAL	      	{ true }
        ::= { rc2kCpuSerialPortEntry 12 }

rc2kCpuSerialPortPppConfigFile OBJECT-TYPE
        SYNTAX        	OCTET STRING (SIZE(0..256))
        MAX-ACCESS       read-write
        STATUS          current	
        DESCRIPTION   	"Used to configure the configuration file to use
			for PPP."
        ::= { rc2kCpuSerialPortEntry 13 }


-- 2k Device Group

rc2kDevice     OBJECT IDENTIFIER ::= { rc2k 4 }

rc2kDeviceGlobalTable OBJECT-TYPE
        SYNTAX        SEQUENCE OF Rc2kDeviceGlobalEntry
        MAX-ACCESS    not-accessible
        STATUS        current
        DESCRIPTION   "2k CPU Ethernet Port table"
        ::= { rc2kDevice 1 }

rc2kDeviceGlobalEntry OBJECT-TYPE
        SYNTAX        Rc2kDeviceGlobalEntry
        MAX-ACCESS    not-accessible
        STATUS        current
        DESCRIPTION   "Entry containing information of 2k CPU Ethernet Port"
        INDEX         { rc2kDeviceGlobalSlot }
        ::= { rc2kDeviceGlobalTable 1 }

Rc2kDeviceGlobalEntry ::= SEQUENCE {
		rc2kDeviceGlobalSlot		INTEGER,
		rc2kDeviceGlobalFlashBytesUsed 	Integer32,
		rc2kDeviceGlobalFlashBytesFree 	Integer32,
		rc2kDeviceGlobalFlashNumFiles 	Integer32,
		rc2kDeviceGlobalPcmciaBytesUsed	Integer32,
		rc2kDeviceGlobalPcmciaBytesFree	Integer32,
		rc2kDeviceGlobalPcmciaNumFiles 	Integer32,
		rc2kDeviceGlobalAction 		INTEGER,
		rc2kDeviceGlobalResult 		INTEGER,
		rc2kDeviceGlobalUsbBytesUsed 	Counter64,
		rc2kDeviceGlobalUsbBytesFree 	Counter64,
		rc2kDeviceGlobalUsbNumFiles 	Integer32,
		rc2kDeviceGlobalExtflashBytesUsed 	Counter64,
		rc2kDeviceGlobalExtflashBytesFree 	Counter64,
		rc2kDeviceGlobalExtflashNumFiles 	Integer32
	}

rc2kDeviceGlobalSlot OBJECT-TYPE
        SYNTAX        INTEGER (1..2)
        MAX-ACCESS    read-only
        STATUS        current
        DESCRIPTION   "slot number"
        ::= { rc2kDeviceGlobalEntry 1 }

rc2kDeviceGlobalFlashBytesUsed OBJECT-TYPE
        SYNTAX        Integer32
        MAX-ACCESS    read-only
        STATUS        current
        DESCRIPTION   "bytes used"
        ::= { rc2kDeviceGlobalEntry 2 }

rc2kDeviceGlobalFlashBytesFree OBJECT-TYPE
        SYNTAX        Integer32
        MAX-ACCESS    read-only
        STATUS        current
        DESCRIPTION   "bytes free"
        ::= { rc2kDeviceGlobalEntry 3 }

rc2kDeviceGlobalFlashNumFiles OBJECT-TYPE
        SYNTAX        Integer32
        MAX-ACCESS    read-only
        STATUS        current
        DESCRIPTION   "# files in flash"
        ::= { rc2kDeviceGlobalEntry 4 }

rc2kDeviceGlobalPcmciaBytesUsed OBJECT-TYPE
        SYNTAX        Integer32
        MAX-ACCESS    read-only
        STATUS        current
        DESCRIPTION   "bytes used"
        ::= { rc2kDeviceGlobalEntry 5 }

rc2kDeviceGlobalPcmciaBytesFree OBJECT-TYPE
        SYNTAX        Integer32
        MAX-ACCESS    read-only
        STATUS        current
        DESCRIPTION   "bytes free"
        ::= { rc2kDeviceGlobalEntry 6 }

rc2kDeviceGlobalPcmciaNumFiles OBJECT-TYPE
        SYNTAX        Integer32
        MAX-ACCESS    read-only
        STATUS        current
        DESCRIPTION   "# files in pcmcia"
        ::= { rc2kDeviceGlobalEntry 7 }
 
rc2kDeviceGlobalAction OBJECT-TYPE
        SYNTAX        INTEGER
                      {
                            none(1)
                      }
        MAX-ACCESS    read-write
        STATUS        current
        DESCRIPTION   "none(1), resetPcmcia(2), .."
        ::= { rc2kDeviceGlobalEntry 8 }

rc2kDeviceGlobalResult OBJECT-TYPE
        SYNTAX        INTEGER {
                            none(1),
                            inProgress(2),
                            success(3),
                            fail(4)
                      }
        MAX-ACCESS    read-only
        STATUS        current
        DESCRIPTION   "Used to indicate the result of the last action
                      performed on one of the system's device."
        ::= { rc2kDeviceGlobalEntry 9 }

rc2kDeviceGlobalUsbBytesUsed OBJECT-TYPE
        SYNTAX        Counter64
        MAX-ACCESS    read-only
        STATUS        current
        DESCRIPTION   "bytes used in USB"
        ::= { rc2kDeviceGlobalEntry 13 }

rc2kDeviceGlobalUsbBytesFree OBJECT-TYPE
        SYNTAX        Counter64
        MAX-ACCESS    read-only
        STATUS        current
        DESCRIPTION   "bytes free in USB"
        ::= { rc2kDeviceGlobalEntry 14 }

rc2kDeviceGlobalUsbNumFiles OBJECT-TYPE
        SYNTAX        Integer32
        MAX-ACCESS    read-only
        STATUS        current
        DESCRIPTION   "# files in USB"
        ::= { rc2kDeviceGlobalEntry 15 }

rc2kDeviceGlobalExtflashBytesUsed OBJECT-TYPE
        SYNTAX        Counter64
        MAX-ACCESS    read-only
        STATUS        current
        DESCRIPTION   "bytes used in Extflash"
        ::= { rc2kDeviceGlobalEntry 16 }

rc2kDeviceGlobalExtflashBytesFree OBJECT-TYPE
        SYNTAX        Counter64
        MAX-ACCESS    read-only
        STATUS        current
        DESCRIPTION   "bytes free in Extflash"
        ::= { rc2kDeviceGlobalEntry 17 }

rc2kDeviceGlobalExtflashNumFiles OBJECT-TYPE
        SYNTAX        Integer32
        MAX-ACCESS    read-only
        STATUS        current
        DESCRIPTION   "# files in Extflash"
        ::= { rc2kDeviceGlobalEntry 18 }

-- 2k Device Separator1 
 
rc2kDeviceSeparator1 OBJECT-TYPE
        SYNTAX        	Integer32
        MAX-ACCESS        	read-only
        STATUS        	current
        DESCRIPTION   	"This leaf is used to provide a separation between
			tables.  No meaningful information is stored in this
			variable." 
        ::= { rc2kDevice 2 }

 
-- 2k Device Intflash File table

rc2kDeviceFlashFileTable OBJECT-TYPE
        SYNTAX        SEQUENCE OF Rc2kDeviceFlashFileEntry
        MAX-ACCESS    not-accessible
        STATUS        current
        DESCRIPTION   "2k Flash table"
        ::= { rc2kDevice 3 }

rc2kDeviceFlashFileEntry OBJECT-TYPE
        SYNTAX        Rc2kDeviceFlashFileEntry
        MAX-ACCESS    not-accessible
        STATUS        current
        DESCRIPTION   "Entry containing information of 2k CPU Serial Port"
        INDEX         { rc2kDeviceFlashFileSlot, 
                        IMPLIED rc2kDeviceFlashFileName }
        ::= { rc2kDeviceFlashFileTable 1 }

Rc2kDeviceFlashFileEntry ::= SEQUENCE {
                rc2kDeviceFlashFileSlot	INTEGER,
                rc2kDeviceFlashFileName DisplayString,
                rc2kDeviceFlashFileDate DisplayString,
                rc2kDeviceFlashFileSize Integer32
        }

rc2kDeviceFlashFileSlot OBJECT-TYPE
        SYNTAX        INTEGER (1..2) 
        MAX-ACCESS    read-only
        STATUS        current
        DESCRIPTION   "slot number"
        ::= { rc2kDeviceFlashFileEntry 1 }

rc2kDeviceFlashFileName OBJECT-TYPE
        SYNTAX        DisplayString (SIZE(1..114))
        MAX-ACCESS    read-only
        STATUS        current
        DESCRIPTION   "name of file"
        ::= { rc2kDeviceFlashFileEntry 2 }

rc2kDeviceFlashFileDate OBJECT-TYPE
        SYNTAX        DisplayString (SIZE(0..32))
        MAX-ACCESS    read-only
        STATUS        current
        DESCRIPTION   "date"
        ::= { rc2kDeviceFlashFileEntry 3 }

rc2kDeviceFlashFileSize OBJECT-TYPE
        SYNTAX        Integer32
        MAX-ACCESS    read-only
        STATUS        current
        DESCRIPTION   "size in bytes"
        ::= { rc2kDeviceFlashFileEntry 4 }

-- 2k Device Pcmcia present

rc2kDevicePcmciaPresent OBJECT-TYPE
        SYNTAX        TruthValue
        MAX-ACCESS    read-only
        STATUS        current
        DESCRIPTION   "pcmcia is a slower device. This leaf is used to
                       stop the access into pcmcia file table when it
                       got the end of flash file table."
        ::= { rc2kDevice 4 }

-- 2k Device Separator2

rc2kDeviceSeparator2 OBJECT-TYPE 
        SYNTAX          Integer32
        MAX-ACCESS      read-only 
        STATUS          current 
        DESCRIPTION     "This leaf is used to provide a separation between 
                        tables.  No meaningful information is stored in this
                        variable."
        ::= { rc2kDevice 6 } 

-- 2k Device Extflash File table

rc2kDeviceExtflashFileTable OBJECT-TYPE
        SYNTAX        SEQUENCE OF Rc2kDeviceExtflashFileEntry
        MAX-ACCESS    not-accessible
        STATUS        current
        DESCRIPTION   "2k Flash table"
        ::= { rc2kDevice 9}

rc2kDeviceExtflashFileEntry OBJECT-TYPE
        SYNTAX        Rc2kDeviceExtflashFileEntry
        MAX-ACCESS    not-accessible
        STATUS        current
        DESCRIPTION   "Entry containing information of extflash files"
        INDEX         { rc2kDeviceExtflashFileSlot, 
                        IMPLIED rc2kDeviceExtflashFileName }
        ::= { rc2kDeviceExtflashFileTable 1 }

Rc2kDeviceExtflashFileEntry ::= SEQUENCE {
                rc2kDeviceExtflashFileSlot Integer32,
                rc2kDeviceExtflashFileName DisplayString,
                rc2kDeviceExtflashFileDate DisplayString,
                rc2kDeviceExtflashFileSize Unsigned32
        }

rc2kDeviceExtflashFileSlot OBJECT-TYPE
        SYNTAX        Integer32 (1..2) 
        MAX-ACCESS    not-accessible
        STATUS        current
        DESCRIPTION   "slot number"
        ::= { rc2kDeviceExtflashFileEntry 1 }

rc2kDeviceExtflashFileName OBJECT-TYPE
        SYNTAX        DisplayString (SIZE(1..114))
        MAX-ACCESS    not-accessible
        STATUS        current
        DESCRIPTION   "name of file"
        ::= { rc2kDeviceExtflashFileEntry 2 }

rc2kDeviceExtflashFileDate OBJECT-TYPE
        SYNTAX        DisplayString (SIZE(0..32))
        MAX-ACCESS    read-only
        STATUS        current
        DESCRIPTION   "date"
        ::= { rc2kDeviceExtflashFileEntry 3 }

rc2kDeviceExtflashFileSize OBJECT-TYPE
        SYNTAX        Unsigned32
        MAX-ACCESS    read-only
        STATUS        current
        DESCRIPTION   "size in bytes"
        ::= { rc2kDeviceExtflashFileEntry 4 }

-- 2k Device USB File table

rc2kDeviceUsbFileTable OBJECT-TYPE
        SYNTAX        SEQUENCE OF Rc2kDeviceUsbFileEntry
        MAX-ACCESS    not-accessible
        STATUS        current
        DESCRIPTION   "2k Usb table"
        ::= { rc2kDevice 10 }

rc2kDeviceUsbFileEntry OBJECT-TYPE
        SYNTAX        Rc2kDeviceUsbFileEntry
        MAX-ACCESS    not-accessible
        STATUS        current
        DESCRIPTION   "Entry containing information of USB files"
        INDEX         { rc2kDeviceUsbFileSlot, 
                        IMPLIED rc2kDeviceUsbFileName }
        ::= { rc2kDeviceUsbFileTable 1 }

Rc2kDeviceUsbFileEntry ::= SEQUENCE {
                rc2kDeviceUsbFileSlot Integer32,
                rc2kDeviceUsbFileName DisplayString,
                rc2kDeviceUsbFileDate DisplayString,
                rc2kDeviceUsbFileSize Unsigned32
        }

rc2kDeviceUsbFileSlot OBJECT-TYPE
        SYNTAX        Integer32 (1..2) 
        MAX-ACCESS    not-accessible
        STATUS        current
        DESCRIPTION   "slot number"
        ::= { rc2kDeviceUsbFileEntry 1 }

rc2kDeviceUsbFileName OBJECT-TYPE
        SYNTAX        DisplayString (SIZE(1..114))
        MAX-ACCESS    not-accessible
        STATUS        current
        DESCRIPTION   "name of file"
        ::= { rc2kDeviceUsbFileEntry 2 }

rc2kDeviceUsbFileDate OBJECT-TYPE
        SYNTAX        DisplayString (SIZE(0..32))
        MAX-ACCESS    read-only
        STATUS        current
        DESCRIPTION   "date"
        ::= { rc2kDeviceUsbFileEntry 3 }

rc2kDeviceUsbFileSize OBJECT-TYPE
        SYNTAX        Unsigned32
        MAX-ACCESS    read-only
        STATUS        current
        DESCRIPTION   "size in bytes"
        ::= { rc2kDeviceUsbFileEntry 4 }


-- 2k Boot Config Table

rc2kBootConfigTable OBJECT-TYPE
        SYNTAX        SEQUENCE OF Rc2kBootConfigEntry
        MAX-ACCESS    not-accessible
        STATUS        current
        DESCRIPTION   "2k Boot Configuration table"
        ::= { rc2k 5 }

rc2kBootConfigEntry OBJECT-TYPE
        SYNTAX        Rc2kBootConfigEntry
        MAX-ACCESS    not-accessible
        STATUS        current
        DESCRIPTION   "Entry containing boot configuration information."
        INDEX         { rc2kBootConfigSlot }
        ::= { rc2kBootConfigTable 1 }

Rc2kBootConfigEntry ::= SEQUENCE {
		rc2kBootConfigSlot 			INTEGER,
		rc2kBootConfigLastBootConfigSource	DisplayString,
		rc2kBootConfigLastRuntimeImageSource	DisplayString,
		rc2kBootConfigLastRuntimeConfigSource	DisplayString,
		rc2kBootConfigPrimaryImageSource	DisplayString,
		rc2kBootConfigPrimaryConfigSource	DisplayString,
		rc2kBootConfigSecondaryImageSource	DisplayString,
		rc2kBootConfigSecondaryConfigSource	DisplayString,
		rc2kBootConfigTertiaryImageSource	DisplayString,
		rc2kBootConfigTertiaryConfigSource	DisplayString,
		rc2kBootConfigEnableAutoBoot		TruthValue,
		rc2kBootConfigEnableFactoryDefaults	TruthValue,
		rc2kBootConfigEnableDebugMode		TruthValue,
		rc2kBootConfigEnableHwWatchDogTimer	TruthValue,
		rc2kBootConfigEnableRebootOnError	TruthValue,
		rc2kBootConfigEnableTelnetServer	TruthValue,
		rc2kBootConfigEnableRloginServer	TruthValue,
		rc2kBootConfigEnableFtpServer		TruthValue,
		rc2kBootConfigEnableTftpServer		TruthValue,
		rc2kBootConfigSwVersion			DisplayString,
                rc2kBootConfigMulticastConfigProfile    INTEGER,
		rc2kBootConfigEnableSshServer		TruthValue,
		rc2kBootConfigEnableAltLed		TruthValue,
		rc2kBootConfigPrimaryBackupConfigSource	DisplayString,
		rc2kBootConfigSecondaryBackupConfigSource	DisplayString,
		rc2kBootConfigTertiaryBackupConfigSource	DisplayString,
		rc2kBootConfigEnable8616ReAutoneg	TruthValue,
		rc2kBootConfigMezzImageSource	        DisplayString,
       	        rc2kBootConfigEnableMezz            TruthValue
        }

rc2kBootConfigSlot OBJECT-TYPE
        SYNTAX        INTEGER (1..2)
        MAX-ACCESS    read-only
        STATUS        current
        DESCRIPTION   "slot number, VSP uses 1,2" 
        ::= { rc2kBootConfigEntry 1 }

rc2kBootConfigLastBootConfigSource OBJECT-TYPE
        SYNTAX        DisplayString (SIZE(0..255))
        MAX-ACCESS    read-only
        STATUS        current
        DESCRIPTION   "boot config source"
        ::= { rc2kBootConfigEntry 2 }

rc2kBootConfigLastRuntimeImageSource OBJECT-TYPE
        SYNTAX        DisplayString (SIZE(0..255))
        MAX-ACCESS    read-only
        STATUS        current
        DESCRIPTION   "runtime image source"
        ::= { rc2kBootConfigEntry 3 }

rc2kBootConfigLastRuntimeConfigSource OBJECT-TYPE
        SYNTAX        DisplayString (SIZE(0..255))
        MAX-ACCESS    read-only
        STATUS        current
        DESCRIPTION   "runtime config source"
        ::= { rc2kBootConfigEntry 4 }

rc2kBootConfigPrimaryImageSource OBJECT-TYPE
        SYNTAX        DisplayString (SIZE(0..255))
        MAX-ACCESS    read-write
        STATUS        current
        DESCRIPTION   "image source"
        ::= { rc2kBootConfigEntry 5 }

rc2kBootConfigPrimaryConfigSource OBJECT-TYPE
        SYNTAX        DisplayString (SIZE(0..255))
        MAX-ACCESS    read-write
        STATUS        current
        DESCRIPTION   "config source"
        ::= { rc2kBootConfigEntry 6 }

rc2kBootConfigSecondaryImageSource OBJECT-TYPE
        SYNTAX        DisplayString (SIZE(0..255))
        MAX-ACCESS    read-write
        STATUS        current
        DESCRIPTION   "image source"
        ::= { rc2kBootConfigEntry 7 }

rc2kBootConfigSecondaryConfigSource OBJECT-TYPE
        SYNTAX        DisplayString (SIZE(0..255))
        MAX-ACCESS    read-write
        STATUS        current
        DESCRIPTION   "config source"
        ::= { rc2kBootConfigEntry 8 }
 
rc2kBootConfigTertiaryImageSource OBJECT-TYPE
        SYNTAX        DisplayString (SIZE(0..255))
        MAX-ACCESS    read-write
        STATUS        current
        DESCRIPTION   "image source"
        ::= { rc2kBootConfigEntry 9 }
 
rc2kBootConfigTertiaryConfigSource OBJECT-TYPE
        SYNTAX        DisplayString (SIZE(0..255))
        MAX-ACCESS    read-write
        STATUS        current
        DESCRIPTION   "config source"
        ::= { rc2kBootConfigEntry 10 }
 
rc2kBootConfigEnableAutoBoot OBJECT-TYPE
        SYNTAX        TruthValue
        MAX-ACCESS    read-write
        STATUS        current
        DESCRIPTION   "auto boot mode"
        ::= { rc2kBootConfigEntry 11 }

rc2kBootConfigEnableFactoryDefaults OBJECT-TYPE
        SYNTAX        TruthValue
        MAX-ACCESS    read-write
        STATUS        current
        DESCRIPTION   "use factory default"
        ::= { rc2kBootConfigEntry 12 }

rc2kBootConfigEnableDebugMode OBJECT-TYPE
        SYNTAX        TruthValue
        MAX-ACCESS    read-write
        STATUS        current
        DESCRIPTION   "debug mode"
        ::= { rc2kBootConfigEntry 13 }

rc2kBootConfigEnableHwWatchDogTimer OBJECT-TYPE
        SYNTAX        TruthValue
        MAX-ACCESS    read-write
        STATUS        current
        DESCRIPTION   "hw watch dog timer"
        ::= { rc2kBootConfigEntry 14 }

rc2kBootConfigEnableRebootOnError OBJECT-TYPE
        SYNTAX        TruthValue
        MAX-ACCESS    read-write
        STATUS        current
        DESCRIPTION   "reboot on error"
        ::= { rc2kBootConfigEntry 15 }

rc2kBootConfigEnableTelnetServer OBJECT-TYPE
        SYNTAX        TruthValue
        MAX-ACCESS    read-write
        STATUS        current
        DESCRIPTION   "telnet server"
        ::= { rc2kBootConfigEntry 16 }

rc2kBootConfigEnableRloginServer OBJECT-TYPE
        SYNTAX        TruthValue
        MAX-ACCESS    read-write
        STATUS        current
        DESCRIPTION   "rlogin server"
        ::= { rc2kBootConfigEntry 17 }

rc2kBootConfigEnableFtpServer OBJECT-TYPE
        SYNTAX        TruthValue
        MAX-ACCESS    read-write
        STATUS        current
        DESCRIPTION   "ftp server"
        ::= { rc2kBootConfigEntry 18 }

rc2kBootConfigEnableTftpServer OBJECT-TYPE
        SYNTAX        TruthValue
        MAX-ACCESS    read-write
        STATUS        current
        DESCRIPTION   "tftp server"
        ::= { rc2kBootConfigEntry 19 }

rc2kBootConfigSwVersion OBJECT-TYPE
        SYNTAX        DisplayString
        MAX-ACCESS    read-only
        STATUS        current
        DESCRIPTION   "current sw version"
        ::= { rc2kBootConfigEntry 20 }
 
rc2kBootConfigMulticastConfigProfile OBJECT-TYPE
        SYNTAX        INTEGER (1..6)
        MAX-ACCESS    read-only
        STATUS        current
        DESCRIPTION   "multicast config"
        DEFVAL        { 1 }
        ::= { rc2kBootConfigEntry 21 }

rc2kBootConfigEnableSshServer OBJECT-TYPE
        SYNTAX        TruthValue
        MAX-ACCESS    read-write
        STATUS        current
        DESCRIPTION   "ssh server"
        ::= { rc2kBootConfigEntry 22 }

rc2kBootConfigEnableAltLed OBJECT-TYPE
        SYNTAX        TruthValue
        MAX-ACCESS    read-write
        STATUS        current
        DESCRIPTION   "Boot flag for enableing Alternate LED"
        ::= { rc2kBootConfigEntry 23 }

rc2kBootConfigPrimaryBackupConfigSource OBJECT-TYPE
        SYNTAX        DisplayString (SIZE(0..255))
        MAX-ACCESS    read-write
        STATUS        current
        DESCRIPTION   "primary backup config source (safeconfig)"
        ::= { rc2kBootConfigEntry 24 }

rc2kBootConfigSecondaryBackupConfigSource OBJECT-TYPE
        SYNTAX        DisplayString (SIZE(0..255))
        MAX-ACCESS    read-write
        STATUS        current
        DESCRIPTION   "secondary backup config source (safeconfig)"
        ::= { rc2kBootConfigEntry 25 }

rc2kBootConfigTertiaryBackupConfigSource OBJECT-TYPE
        SYNTAX        DisplayString (SIZE(0..255))
        MAX-ACCESS    read-write
        STATUS        current
        DESCRIPTION   "tertiary backup config source (safeconfig)"
        ::= { rc2kBootConfigEntry 26 }

rc2kBootConfigEnable8616ReAutoneg OBJECT-TYPE
        SYNTAX        TruthValue
        MAX-ACCESS    read-write
        STATUS        current
        DESCRIPTION   "Enable re-autoneg for 8616SX Cards (Intel GMAC fix)"
        ::= { rc2kBootConfigEntry 27 }

rc2kBootConfigMezzImageSource OBJECT-TYPE
        SYNTAX        DisplayString (SIZE(0..255))
        MAX-ACCESS    read-write
        STATUS        current
        DESCRIPTION   "Mezz image source"
        ::= { rc2kBootConfigEntry 28 }

rc2kBootConfigEnableMezz OBJECT-TYPE
        SYNTAX        TruthValue
        MAX-ACCESS    read-write
        STATUS        current
        DESCRIPTION   "Enable/disable Mezz Flag"
        ::= { rc2kBootConfigEntry 29 }

-- 2k Card table

rc2kCardTable OBJECT-TYPE
        SYNTAX        SEQUENCE OF Rc2kCardEntry
        MAX-ACCESS    not-accessible
        STATUS        current
        DESCRIPTION   "2k Card table"
        ::= { rc2k 6 }

rc2kCardEntry OBJECT-TYPE
        SYNTAX        Rc2kCardEntry
        MAX-ACCESS    not-accessible
        STATUS        current
        DESCRIPTION   "Entry containing information of 2k Card"
        INDEX         { rc2kCardIndex }
        ::= { rc2kCardTable 1 }

Rc2kCardEntry ::= SEQUENCE {
                rc2kCardIndex            INTEGER,
                rc2kCardFrontType        INTEGER,
                rc2kCardFrontDescription DisplayString,
                rc2kCardFrontAdminStatus INTEGER,
                rc2kCardFrontOperStatus  INTEGER,
                rc2kCardFrontSerialNum   DisplayString,
                rc2kCardFrontPartNumber  DisplayString,
                rc2kCardFrontDateCode    DisplayString,
                rc2kCardFrontDeviations  DisplayString,
                rc2kCardFrontMacAddr     MacAddress,    --excluded
                rc2kCardBackType         INTEGER,
                rc2kCardBackDescription  DisplayString,
                rc2kCardBackSerialNum    DisplayString,
                rc2kCardBackHwVersion    DisplayString,
                rc2kCardBackPartNumber   DisplayString,
                rc2kCardBackDateCode     DisplayString,
                rc2kCardBackDeviations   DisplayString,
		rc2kCardASICDescr	 DisplayString,
                rc2kCardSmltOnSingleCpSupported   TruthValue,
                rc2kCardSlotPriority     INTEGER,
		rc2kCardSlotOriginalPriority     INTEGER,
                rc2kCardSlotPower        INTEGER
        }

rc2kCardIndex OBJECT-TYPE
        SYNTAX        INTEGER (1..32)
        MAX-ACCESS    read-only
        STATUS        current
        DESCRIPTION   "slot number."
        ::= { rc2kCardEntry 1 }

rc2kCardFrontType OBJECT-TYPE
        SYNTAX        INTEGER
{
        other(1),                        -- no card installed
        rc2kCPU(537788672),              -- 0010 0000 0000 1110 0000 0001 0000 0000
        rc2k48x100BaseTX(539033904),     -- 0010 0000 0010 0001 0000 0001 0011 0000
        rc2k24x100BaseTX(539033880),     -- 0010 0000 0010 0001 0000 0001 0001 1000
        rc2k32x100BaseTX(539033888),     -- 0010 0000 0010 0001 0000 0001 0010 0000
        rc2k8x1000BaseT(539099400),      -- 0010 0000 0010 0010 0000 0001 0000 1000  
        rc2k16x1000BaseT(539099408),     -- 0010 0000 0010 0010 0000 0001 0001 0000  
        rc2k24x100BaseFX(540082456),     -- 0010 0000 0011 0001 0000 0001 0001 1000
        rc2k8x1000BaseSXBB(540147976),   -- 0010 0000 0011 0010 0000 0001 0000 1000
        rc2k16x1000BaseSXBB(540147984),  -- 0010 0000 0011 0010 0000 0001 0001 0000 
        rc2k8x1000BaseLXBB(540156168),   -- 0010 0000 0011 0010 0010 0001 0000 1000
        rc2k8x1000BaseXDBB(540164360),   -- 0010 0000 0011 0010 0100 0001 0000 1000
        rc2k4x1000BaseOPM(540168452),    -- 0010 0000 0011 0010 0101 0001 0000 0100 
-- OM 2.0 place holder
--      rc2k8x1000BaseOPM(40168456),        0000 0010 0110 0100 1110 1100 0000 1000
        rc2k8x1000BaseIC(540168456),     -- 0010 0000 0011 0010 0101 0001 0000 1000 
        rc2k16x1000BaseIC(540168464),    -- 0010 0000 0011 0010 0101 0001 0001 0000
        rc2k8x1000BaseSXRBB(540180744),  -- 0010 0000 0011 0010 1000 0001 0000 1000
        rc2k8x1000BaseLXRBB(540188936),  -- 0010 0000 0011 0010 1010 0001 0000 1000
        rc2k8xOC3(541327624),            -- 0010 0000 0100 0100 0000 0001 0000 1000
        rc2k2xOC12(541393154),           -- 0010 0000 0100 0101 0000 0001 0000 0010
        rc2k6xPOS(541401350),            -- 0010 0000 0100 0101 0010 0001 0000 0110
        rc2k4xATM(542441732),            -- 0010 0000 0101 0101 0000 0001 0000 0100
        rc2k8xATM(542441736),            -- 0010 0000 0101 0101 0000 0001 0000 1000
        rc2kRMON(545128704),             -- 0010 0000 0111 1110 0000 0001 0000 0000
        rc2k1x10GBaseLW(573767937),      -- 0010 0000 0011 0011 0000 0001 0000 0001
        rc2k1x10GBaseLR(573784321),      -- 0010 0000 0011 0011 0100 0001 0000 0001
        rc2k32x100BaseTXM(572588320),    -- 0010 0010 0010 0001 0000 0001 0010 0000
        rc2k48x100BaseTXM(572588336),    -- 0010 0010 0010 0001 0000 0001 0011 0000
        rc2k8x1000BaseTM(572653832),     -- 0010 0010 0010 0010 0000 0001 0000 1000
        rc2k8x1000BaseSXBBM(573702408),  -- 0010 0010 0011 0010 0000 0001 0000 1000
        rc2k8x1000BaseICM(573722888),    -- 0010 0010 0011 0010 0101 0001 0000 1000
        rc2k6xPOSM(574955782),           -- 0010 0010 0100 0101 0010 0001 0000 0110
        rc2k8xATMM(575996168),           -- 0010 0010 0101 0101 0000 0001 0000 1000
	rc2kPR48X1000BaseTX(606208304),  -- 0010 0100 0010 0010 0000 0001 0011 0000
        rc2kMg48x100BaseTX(807469360),   -- 0011 0000 0010 0001 0000 0001 0011 0000
        rc2kMg32x100BaseTX(807473440),   -- 0011 0000 0010 0001 0001 0001 0010 0000
        rc2kMg16x100BaseFX(808522000),   -- 0011 0000 0011 0001 0001 0001 0001 0000
        rc2kMg8x1000BaseTX(808583432),   -- 0011 0000 0011 0010 0000 0001 0000 1000
        rc2kMg8x1000BaseIC(808603912),   -- 0011 0000 0011 0010 0101 0001 0000 1000
        rc2kMg48x100BaseTC(817955120),   -- 0011 0000 1100 0001 0000 0001 0011 0000
-- Alteon
	rc2kAlteonLP(1893859592),        -- 0111 0000 1110 0010 0000 0001 0000 1000
	rc2kAlteonWSM(1899102468),       -- 0111 0001 0011 0010 0000 0001 0000 0100
	rc2kAlteonASFM(1899106564),      -- 0111 0001 0011 0010 0001 0001 0000 0100
        rc2k61AlteonSAM(1926365441),     -- 0111 0010 1101 0010 0000 0001 0000 0001
        rc2k62AlteonSAM(1926369537),     -- 0111 0010 1101 0010 0001 0001 0000 0001
-- 8300
        rc2kPP8300-CPU8x1000BaseSFP(1342316808), -- 0101 0000 0000 0010 0010 0001 0000 0000 0x50022108
        rc2kPP8300-24x1000BaseTX(1344405784),    -- 0101 0000 0010 0010 0000 0001 0001 1000 0x50220118
        rc2kPP8300-48x100BaseTX(1344340272),     -- 0101 0000 0010 0001 0000 0001 0011 0000 0x50210130
        rc2kPP8300-48x100BaseTXPOE(1344344368),  -- 0101 0000 0010 0001 0001 0001 0011 0000 0x50211130
-- Power Ranger
        rc2kPR30X1000BaseSXBB(607277342),        -- 0010 0100 0011 0010 0101 0001 0001 1110
        rc2kPR3X10GBaseGbic(607338755),          -- 0010 0100 0011 0011 0100 0001 0000 0011 
        rc2kPR3X10GBaseXZW(607346947),           -- 0010 0100 0011 0011 0110 0001 0000 0011 
        rc2kPR48x1000BaseGBRS(607277360),        -- 0010 0100 0011 0010 0101 0001 0011 0000 0x24325130
	rc2kPR48x1000BaseGTRS(606241072),        -- 0010 0100 0010 0010 1000 0001 0011 0000 0x24228130
	rc2kPR12X10GBaseXLRS(607338764),         -- 0010 0100 0011 0011 0100 0001 0000 1100 0x2433410C
	rc2kPR34xXGRS(607277346),      		 -- 0010 0100 0011 0010 0101 0001 0010 0010 0x24325122
-- Cobalt Blue: if you change here, you MUST update rcCardType in rcCardTable
        cbMidplane-28(1090388736),		 -- 0100 0000 1111 1110 0000 0011 0000 0000 0x40FE0300
	cbACPowerSupply(1084097280),		 -- 0100 0000 1001 1110 0000 0011 0000 0000 0x409E0300
	cbCPFanTray(1085145856),		 -- 0100 0000 1010 1110 0000 0011 0000 0000 0x40AE0300
	cbIOFanTray(1085149952),		 -- 0100 0000 1001 1110 0000 0011 0000 0000 0x40AE1300
	cbAUX(1091437312),			 -- 0100 0001 0000 1110 0000 0011 0000 0000 0x410E0300
	cbSF3200(1075708672),			 -- 0100 0000 0001 1110 0000 0011 0000 0000 0x401E0300
	cbSF9600(1075712768),			 -- 0100 0000 0001 1110 0001 0011 0000 0000 0x401E1300
	cbCP-CSC(1073873665),       		 -- 0100 0000 0000 0010 0000 0011 0000 0001 0x40020301
	cb48x1000BaseTX(1075970864),		 -- 0100 0000 0010 0010 0000 0011 0011 0000 0x40220330
	cb48x1000BaseTXPOE(1075974960),		 -- 0100 0000 0010 0010 0001 0011 0011 0000 0x40221330
	cb48x1000SFP(1077044016),		 -- 0100 0000 0011 0010 0110 0011 0011 0000 0x40326330
	cb24x10GBaseSFP(1077109528),		 -- 0100 0000 0011 0011 0110 0011 0001 1000 0x40336318
	cb48x10GBaseSFP(1077109552)		 -- 0100 0000 0011 0011 0110 0011 0011 0000 0x40336330
-- Future CB Cards
--	cbOPM(1087243008)			    0x40CE0300
--	cbSAS(1087247104)			    0x40CE1300	
-- 	cbIPFIX(1087251200)			    0x40CE2300

}
        MAX-ACCESS    read-only
        STATUS        current
        DESCRIPTION     "Used to indicate card types in the Accelar
                        8000 product families.

			For Accelar 8000 devices, all cards use
		      	an encoded value according to the following rule:

        |   6  |   1   |   5   |   4   |  1 |   3   |  4   |      8      |
        +------+-------+-------+-------+------------+------+------+------+
bits  : |31-26 |    25 | 24-20 | 19-16 | 15 | 14-12 | 11-8 |     7-0     |
        +------+-------+-------+-------+----+-------+------+------+------+
field : |  a   |   b   |   c   |   d   |  e |    f  |  g   |      h      |
        +------+-------+-------+-------+----+-------+------+------+------+

     a : Family type/Product line (6 bits (5 bits usuable) (was 4 bits))
            MSB bit31 should not be used (MIB compiler fails)

            0x0-00 = 0000-00 = Reserved
            0x1-00 = 0001-00 = Monoploy non specific (e.g backplane, psu, fans)
            0x2-00 = 0010-00 = Boardwalk
            0x2-01 = 0010-01 = Power Ranger
            0x3-00 = 0011-00 = Marvin Gardens
            0x4-00 = 0100-00 = Cobalt Blue (was Thunderbolt and Pacific before that - both are obsolete)
            0x5-00 = 0101-00 = PP8300 (was ParkPlace)
            0x6-00 = 0110-00 = Central Office (only used in chassis)
            0x7-00 = 0111-00 = Alteon WebSystems

     b : Interface / Device type variation: (Were 3 bits, 2 bits taken by family)
            0x1 = 0 = Non M-Module
            0x1 = 1 = M-module (128K RARU records)

     c : Interface / device type: (5 bits)
            0x0 = 00000 = CPU
            0x1 = 00001 = Switch fabric
            0x2 = 00010 = Copper Ethernet
            0x3 = 00011 = Fiber Ethernet
            0x4 = 00100 = Sonet (Packets)
            0x5 = 00101 = ATM
            0x6 = 00110 = Token Ring
            0x7 = 00111 = RMON
            0x8 = 01000 = BFM (Frame or cells indicated by field 'a' above)
            0x9 = 01001 = PSU
            0xa = 01010 = Fan Tray
            0xb = 01011 = Chassis/Backplane
            0xc = 01100 = CPU Mezz
            0xd = 01101 = SSL
            0xe = 01110 = LaunchPad
            0xf = 01111 = Chassis/Midplane
            0x10 = 10000 = Auxillary Card
            0x11 = 10001 = reserved for future
            0x12 = 10010 = reserved for future
            0x13 = 10011 = WSM Fiber Ethernet

     d : Maximum speed (highest negotiable speed) (4 bits)
            0x0 = 0000 = 10 Mbit  
            0x1 = 0001 = 100 Mbit  
            0x2 = 0010 = 1 Gbit
            0x3 = 0011 = 10 Gbit
            0x4 = 0100 = OC-3
            0x5 = 0101 = OC-12
            0x6 = 0110 = OC-48
            0x7 = 0111 = OC-92
            0x8 = 1000 = OC-192
            0x9 = 1001 = 4 Mbit (TR)
            0xa = 1010 = 16 Mbit (TR)
            0xb = 1011 = E3 
            0xc = 1100 = DS1
            0xd = 1101 = DS3
            0xe = 1110 = none (no PHY interfaces on board)
            0xf = 1111 = Max speed indicated implicitly in field (c) (for expansion)
   
     e : AM&OM-06/28/2006: This bit was originally used to indicate port redundancy.
	 For PR it is used as a differentiator between Boomslang (0) and Copperhead (1).
	 0=non-redundant, 1=redundant; (1 bit)

     f : Card specific info. (3 bits)
             For Gigabit used as follows:
		 000=short-haul (SX)
		 010=long-haul (LX)
		 100=extra-distance (DX)
                 101=GBIC
		 110=SFP
	     For 10 Gigabit used as follws
	         000 = 10GE WAN serial 1310nm (XLW)
		 001 = 10GE WAN serial 1550nm (XEW)
		 100 = 10GE LAN serial 1310nm (XLR)
		 101 = 10GE LAN serial 1550nm (XER)
                 011 = 10GE LAN/WAN 	      (XZW)
	     For ATM/Sonet used as follows
                 000 = multi mode
                 001 = single mode
                 010 = single or multimode
		 011 = not applicable (e.g., copper has no mode)
             For Marvin Gardens, indicates number of MDA slots
                 000 = none
                 001 = one option slots
                 010 = two option slots
                 011 = three option slots
             For Power Supplies:
                 000 = AC PSU
                 001 = DC PSU
             For SSL:
                 000 = server offloading
                 001 = end to end encryption
             For WSM:
                 000 = WSM mode
                 001 = ASFM mode
	     For SF:
		 000 = 3200 card
		 001 = 9600 card
             For Copper Ethernet:
		 000: no POE
		 001: POE
	     For FAN Tray:
		 000: CP
		 001: IO	
	     For Objects with no options:
		 000: CPU, Mezz, OPM, SAS, IPFIX

     g : Chassis type (4 bits, possibly MSB 2 bits are extension of field b)
         0x0 = 00-00 = work-group (single card switches, etc)
         0x1 = 00-01 = back-bone (chassis based products)
         0x2 = 00-10 = MDA (option modules)
	 0x3 = 00-10 = mid-plane (chassis based products)

     h : Number of ports (binary representation obmited) (8 bits)
         (for ACIM/BFM cards, this is number of octapids/blackbirds/dea)
               0x00 =  no ports (CPs, SFs, PS's, etc)
               0x01 =   1-port, 
               0x02 =   2-port, 
               0x04 =   4-port,
               0x06 =   6-port,
               0x08 =   8-port,
               0x0c =  12-port,
               0x10 =  16-port,
               0x18 =  24-port,
               0x22 =  36-port,
               0x30 =  48-port,
               0x40 =  64-port.
               0x80 = 128-port.
		"
        ::= { rc2kCardEntry 2 }

rc2kCardFrontDescription OBJECT-TYPE
        SYNTAX        DisplayString (SIZE (0..20))
        MAX-ACCESS    read-only
        STATUS        current
        DESCRIPTION   "description"
        ::= { rc2kCardEntry 3 }

rc2kCardFrontAdminStatus OBJECT-TYPE
        SYNTAX       INTEGER {
                         up(1),
                         down(2),
                         testing(3),
                         reset(4)
                      }
        MAX-ACCESS    read-write
        STATUS        current
        DESCRIPTION   "Used to indicate the administrative status of this
                       card"
        ::= { rc2kCardEntry 4 }

rc2kCardFrontOperStatus OBJECT-TYPE
        SYNTAX        INTEGER {
                         up(1),
                         down(2),
                         testing(3),
                         unknown(4),
                         dormant(5)
                      }
        MAX-ACCESS    read-only
        STATUS        current
        DESCRIPTION   "Used to indicate the operational status of this card."
        ::= { rc2kCardEntry 5 }

rc2kCardFrontSerialNum OBJECT-TYPE
        SYNTAX        DisplayString (SIZE (0..20))
        MAX-ACCESS    read-only
        STATUS        current
        DESCRIPTION   "manufacturer serial number of card"
        ::= { rc2kCardEntry 6 }

rc2kCardFrontPartNumber OBJECT-TYPE
        SYNTAX        DisplayString (SIZE (0..20))
        MAX-ACCESS    read-only
        STATUS        current
        DESCRIPTION   "manufacturer part number of card"
        ::= { rc2kCardEntry 8 }

rc2kCardFrontDateCode OBJECT-TYPE
        SYNTAX        DisplayString (SIZE (0..20))
        MAX-ACCESS    read-only
        STATUS        current
        DESCRIPTION   "manufacturer date code"
        ::= { rc2kCardEntry 9 }

rc2kCardFrontDeviations OBJECT-TYPE
        SYNTAX        DisplayString (SIZE (0..20))
        MAX-ACCESS    read-only
        STATUS        current
        DESCRIPTION   "deviations"
        ::= { rc2kCardEntry 10 }

rc2kCardFrontMacAddr OBJECT-TYPE
        SYNTAX        MacAddress
        MAX-ACCESS    read-only
        STATUS        current 
        DESCRIPTION   "base mac address"
        ::= { rc2kCardEntry 11 }

rc2kCardBackType OBJECT-TYPE
        SYNTAX        INTEGER {
        none(0),
        other(1),                  -- no card installed
        rc2kBackplane(536969472),  -- 0010 0000 0000 0001 1000 0001 0000 0000
	rc2kSFM(538837248),        -- 0010 0000 0001 1110 0000 0001 0000 0000
	rc2kBFM0(546177280),       -- 0010 0000 1000 1111 0000 0001 0000 0000
	rc2kBFM2(546177282),       -- 0010 0000 1000 1111 0000 0001 0000 0010
	rc2kBFM3(546177283),       -- 0010 0000 1000 1111 0000 0001 0000 0011
	rc2kBFM4(1888354564),      -- 0111 0000 1000 1110 0000 0001 0000 0100
	rc2kBFM6(546177286),       -- 0010 0000 1000 1111 0000 0001 0000 0100
	rc2kBFM8(546177288),       -- 0010 0000 1000 1111 0000 0001 0000 1000
	rc2kMGSFM(807272704),      -- 0011 0000 0001 1110 0000 0001 0000 0000
        rc2kFSFM(605946112),       -- 0010 0100 0001 1110 0000 0001 0000 0000
        rc2kDPM1(613351861),       -- 0010 0100 1000 1111 0000 0001 1011 0101 
	rc2kDPM2(613351682),       -- 0010 0100 1000 1111 0000 0001 0000 0010
        rc2kDPM3(613351863),       -- 0010 0100 1000 1111 0000 0001 1011 0111 
	rc2kEDPM2(613351690),      -- 0010 0100 1000 1111 0000 0001 0000 1010 0x248F010A
        rc2kEDPM3(613351871)       -- 0010 0100 1000 1111 0000 0001 1011 1111 0x248F01BF
}
        MAX-ACCESS    read-only
        STATUS        current 
        DESCRIPTION   "Refer to rc2kCardFrontType for the encoding scheme"
        ::= { rc2kCardEntry 12 }

rc2kCardBackDescription OBJECT-TYPE
        SYNTAX        DisplayString (SIZE (0..20))
        MAX-ACCESS    read-only
        STATUS        current
        DESCRIPTION   "customer card description"
        ::= { rc2kCardEntry 13 }

rc2kCardBackSerialNum OBJECT-TYPE
        SYNTAX        DisplayString (SIZE (0..20))
        MAX-ACCESS    read-only
        STATUS        current
        DESCRIPTION   "customer serial number of card"
        ::= { rc2kCardEntry 14 }

rc2kCardBackHwVersion OBJECT-TYPE
        SYNTAX        DisplayString (SIZE (0..20))
        MAX-ACCESS    read-only
        STATUS        current 
        DESCRIPTION   "hardware version"
        ::= { rc2kCardEntry 15 }

rc2kCardBackPartNumber OBJECT-TYPE
        SYNTAX        DisplayString (SIZE (0..20))
        MAX-ACCESS    read-only
        STATUS        current
        DESCRIPTION   "customer part number"
        ::= { rc2kCardEntry 16 }

rc2kCardBackDateCode OBJECT-TYPE
        SYNTAX        DisplayString (SIZE (0..20))
        MAX-ACCESS    read-only
        STATUS        current
        DESCRIPTION   "customer date code"
        ::= { rc2kCardEntry 17 }

rc2kCardBackDeviations OBJECT-TYPE
        SYNTAX        DisplayString (SIZE (0..20))
        MAX-ACCESS    read-only
        STATUS        current
        DESCRIPTION   "customer deviations"
        ::= { rc2kCardEntry 18 }

rc2kCardASICDescr OBJECT-TYPE
        SYNTAX        	DisplayString (SIZE (0..128))
        MAX-ACCESS      read-only
        STATUS        	current
        DESCRIPTION   	"ASIC descriptor"
        ::= { rc2kCardEntry 21 }

rc2kCardSmltOnSingleCpSupported OBJECT-TYPE
        SYNTAX          TruthValue
        MAX-ACCESS      read-only
        STATUS          current
        DESCRIPTION     "Used to indicate whether an IO card is updated to
                         support SMLT on single Cp feature or not."
        DEFVAL        { false }
        ::= { rc2kCardEntry 23 }

rc2kCardSlotPriority OBJECT-TYPE
        SYNTAX       INTEGER 
                     {
                       critical(1),
                       high(2),
                       low(3)
                     }
        MAX-ACCESS    read-write
        STATUS        current
        DESCRIPTION   "Used to indicate the priority of the slot for power 
                       management. It will take effect only after reboot."
        ::= { rc2kCardEntry 29 }

rc2kCardSlotOriginalPriority OBJECT-TYPE
        SYNTAX       INTEGER
                     {
                       critical(1),
                       high(2),
                       low(3)
                     }
        MAX-ACCESS    read-only
        STATUS        current
        DESCRIPTION   "Priority of the slot for power management which the
                       swtich has currently booted with. It will remain the 
		       same until the next reboot."
        ::= { rc2kCardEntry 30 }

rc2kCardSlotPower  OBJECT-TYPE
        SYNTAX       INTEGER
                     {
                       on(1),
                       off(2)
                     }
        MAX-ACCESS    read-write
        STATUS        current
        DESCRIPTION   "Administrately turn on or off power on this slot.
		       it only applicable on Standby CP & IO and SF Card"
        ::= { rc2kCardEntry 32 }

-- 2k copy file

rc2kCopyFile     OBJECT IDENTIFIER ::= { rc2k 7 }

rc2kCopyFileSource OBJECT-TYPE
        SYNTAX        OCTET STRING (SIZE(0..256))
        MAX-ACCESS    read-write
        STATUS        current
        DESCRIPTION   "source file"
        ::= { rc2kCopyFile 1 }

rc2kCopyFileDestination OBJECT-TYPE
        SYNTAX        OCTET STRING (SIZE(0..256))
        MAX-ACCESS    read-write
        STATUS        current
        DESCRIPTION   "dest file"
        ::= { rc2kCopyFile 2 }

rc2kCopyFileAction OBJECT-TYPE
        SYNTAX        INTEGER
                      {
                            none(1),
                            start(2)
                      }
        MAX-ACCESS    read-write
        STATUS        current
        DESCRIPTION   "start or cancell"
        ::= { rc2kCopyFile 3 }

rc2kCopyFileResult OBJECT-TYPE
        SYNTAX        INTEGER
                      {
                            none(1),
                            inProgress(2),
                            success(3),
                            fail(4),
                            invalidSource(5),
                            invalidDestination(6),
                            outOfMemory(7),
                            outOfSpace(8),
                            fileNotFound(9)
                      }
        MAX-ACCESS    read-only
        STATUS        current
        DESCRIPTION   "result"
        ::= { rc2kCopyFile 4 }

-- 2k Qos

rc2kQos     OBJECT IDENTIFIER ::= { rc2k 8 }

-- 2k Qos Ingress Tag To Qos Table

rc2kQosIngressTagToQosTable OBJECT-TYPE
        SYNTAX        	SEQUENCE OF Rc2kQosIngressTagToQosEntry
        MAX-ACCESS        	not-accessible
        STATUS        	current
        DESCRIPTION   	"This table is used to specify the 802.1P
			to QOS (802.1P->QOS) mapping on packet 
			ingress."
        ::= { rc2kQos 2 }

rc2kQosIngressTagToQosEntry OBJECT-TYPE
        SYNTAX        	Rc2kQosIngressTagToQosEntry
        MAX-ACCESS        	not-accessible
        STATUS        	current
        DESCRIPTION   	"Entry containing information of 8021P->Qos mapping"
        INDEX         	{ rc2kQosIngressTagToQosRow }
        ::= { rc2kQosIngressTagToQosTable 1 }

Rc2kQosIngressTagToQosEntry ::= SEQUENCE {
                rc2kQosIngressTagToQosRow INTEGER,
                rc2kQosIngressTagToQosInIeee8021P INTEGER,
                rc2kQosIngressTagToQosQosLevel INTEGER
        }

rc2kQosIngressTagToQosRow OBJECT-TYPE
        SYNTAX        INTEGER (1..8)
        MAX-ACCESS    read-only
        STATUS        current
        DESCRIPTION   "Used to uniquely identify a row in this table."
        ::= { rc2kQosIngressTagToQosEntry 1 }

rc2kQosIngressTagToQosInIeee8021P OBJECT-TYPE
        SYNTAX        INTEGER (0..7)
        MAX-ACCESS    read-only
        STATUS        current
        DESCRIPTION   "802.1P"
        ::= { rc2kQosIngressTagToQosEntry 2 }

rc2kQosIngressTagToQosQosLevel OBJECT-TYPE
        SYNTAX        INTEGER (0..7)
        MAX-ACCESS    read-write
        STATUS        current
        DESCRIPTION   "Qos level"
        ::= { rc2kQosIngressTagToQosEntry 3 }

-- 2k Egress Qos To Tag Table

rc2kQosEgressQosToTagTable OBJECT-TYPE
        SYNTAX        	SEQUENCE OF Rc2kQosEgressQosToTagEntry
        MAX-ACCESS        	not-accessible
        STATUS        	current
        DESCRIPTION  	"This table is used to specify the QOS to
			802.1P (QOS->802.1P) mapping on packet
			egress."
        ::= { rc2kQos 4 }

rc2kQosEgressQosToTagEntry OBJECT-TYPE
        SYNTAX        Rc2kQosEgressQosToTagEntry
        MAX-ACCESS    not-accessible
        STATUS        current
        DESCRIPTION   "Entry containing information of Qos->Qos mapping"
        INDEX         { rc2kQosEgressQosToTagRow }
        ::= { rc2kQosEgressQosToTagTable 1 }

Rc2kQosEgressQosToTagEntry ::= SEQUENCE {
                rc2kQosEgressQosToTagRow INTEGER,
                rc2kQosEgressQosToTagQosLevel INTEGER,
                rc2kQosEgressQosToTagOutIeee8021P INTEGER
        }

rc2kQosEgressQosToTagRow OBJECT-TYPE
        SYNTAX        INTEGER (1..8)
        MAX-ACCESS    read-only
        STATUS        current
        DESCRIPTION   "Used to uniquely identify a row in this table."
        ::= { rc2kQosEgressQosToTagEntry 1 }

rc2kQosEgressQosToTagQosLevel OBJECT-TYPE
        SYNTAX        INTEGER (0..7)
        MAX-ACCESS    read-only
        STATUS        current
        DESCRIPTION   "qos level"
        ::= { rc2kQosEgressQosToTagEntry 2 }

rc2kQosEgressQosToTagOutIeee8021P OBJECT-TYPE
        SYNTAX        INTEGER (0..7)
        MAX-ACCESS    read-write
        STATUS        current
        DESCRIPTION   "802.1P"
        ::= { rc2kQosEgressQosToTagEntry 3 }

-- 2k Traffic Profile Table

rc2kQosTrafficProfileTable OBJECT-TYPE
        SYNTAX        	SEQUENCE OF Rc2kQosTrafficProfileEntry
        MAX-ACCESS        	not-accessible
        STATUS          current 
        DESCRIPTION   	"This table is used to specify traffic profiles 
			for the system.  These traffic profiles are
			used for policying purposes to guarantee streams
			of traffic do not egress the system above a
			certain rate.  These traffic profiles are applied
			in the 'rcIpFilterTable'."
        ::= { rc2kQos 6 }

rc2kQosTrafficProfileEntry OBJECT-TYPE
        SYNTAX        Rc2kQosTrafficProfileEntry
        MAX-ACCESS    not-accessible
        STATUS        current 
        DESCRIPTION   "Entry containing information of Qos->Qos mapping"
        INDEX         { rc2kQosTrafficProfileId }
        ::= { rc2kQosTrafficProfileTable 1 }

Rc2kQosTrafficProfileEntry ::= SEQUENCE {
                rc2kQosTrafficProfileId INTEGER,
                rc2kQosTrafficProfileName DisplayString,
                rc2kQosTrafficProfileEnable TruthValue,
                rc2kQosTrafficProfileTranslateDscpEnable TruthValue,
                rc2kQosTrafficProfileInProfileDscp DisplayString(SIZE(6)),
                rc2kQosTrafficProfileOutProfileDscp DisplayString(SIZE(6)),
                rc2kQosTrafficProfileDiscardEnable TruthValue,
                rc2kQosTrafficProfileAverageRate Integer32,
                rc2kQosTrafficProfileRowStatus RowStatus
        }

rc2kQosTrafficProfileId OBJECT-TYPE
        SYNTAX        	INTEGER (1..64)
        MAX-ACCESS        	read-only
        STATUS        	current
        DESCRIPTION   	"Profile id"
        ::= { rc2kQosTrafficProfileEntry 1 }

rc2kQosTrafficProfileName OBJECT-TYPE
        SYNTAX        	DisplayString (SIZE (0..32))
        MAX-ACCESS        	read-write
        STATUS        	current
        DESCRIPTION   	"Profile name"
        ::= { rc2kQosTrafficProfileEntry 2 }

rc2kQosTrafficProfileEnable OBJECT-TYPE
        SYNTAX        	TruthValue
        MAX-ACCESS        	read-write
        STATUS        	current
        DESCRIPTION   	"Enable this entry"
	DEFVAL		{ false }
        ::= { rc2kQosTrafficProfileEntry 3 }

rc2kQosTrafficProfileTranslateDscpEnable OBJECT-TYPE
        SYNTAX        	TruthValue
        MAX-ACCESS        	read-write
        STATUS        	current
        DESCRIPTION    	"Used to specify whether translation of the DSCP
			field should be performed.  If enabled, the value 
			in the DSCP field for packets that fall within 
			the traffic profile will get translated to
			'rc2kQosTrafficProfileInProfileDscp'.  Packets
			that fall outside the traffic profile will get
			translated to 'rc2kQosTrafficProfileOutProfileDscp'.
			If disabled, no translation is performed." 
	DEFVAL		{ false }
        ::= { rc2kQosTrafficProfileEntry 4 }

rc2kQosTrafficProfileInProfileDscp OBJECT-TYPE
        SYNTAX          DisplayString(SIZE(6))
        MAX-ACCESS      read-write
        STATUS          current
        DESCRIPTION     "Used to specify the DSCP value for 'good' packets."
        ::= { rc2kQosTrafficProfileEntry 5 }

rc2kQosTrafficProfileOutProfileDscp OBJECT-TYPE
        SYNTAX          DisplayString(SIZE(6))
        MAX-ACCESS      read-write
        STATUS          current
        DESCRIPTION     "Used to specify the DSCP value for 'violation'
                        packets."
        ::= { rc2kQosTrafficProfileEntry 6 }

rc2kQosTrafficProfileDiscardEnable OBJECT-TYPE
        SYNTAX        	TruthValue
        MAX-ACCESS        	read-write
        STATUS        	current
        DESCRIPTION   	"Used to specify whether packets that fall outside
			the traffic profile should be discarded."
	DEFVAL		{ true }
        ::= { rc2kQosTrafficProfileEntry 7 }

rc2kQosTrafficProfileAverageRate OBJECT-TYPE
        SYNTAX        	Integer32
        MAX-ACCESS        	read-write
        STATUS        	current
        DESCRIPTION   	"Average rate in packets per second."
        ::= { rc2kQosTrafficProfileEntry 8 }

rc2kQosTrafficProfileRowStatus OBJECT-TYPE
        SYNTAX        	RowStatus
        MAX-ACCESS        	read-write
        STATUS        	current
        DESCRIPTION   	"Used to create/delete entries."
        ::= { rc2kQosTrafficProfileEntry 10 }

-- 2k Ingress Dscp To Qos Table

rc2kQosIngressDscpToQosTable OBJECT-TYPE
        SYNTAX          SEQUENCE OF Rc2kQosIngressDscpToQosEntry
        MAX-ACCESS      not-accessible
        STATUS          current
        DESCRIPTION     "This table is used to specify the DSCP to
                        QOS (Dscp->QOS) mapping on packet ingress."
        ::= { rc2kQos 7 }

rc2kQosIngressDscpToQosEntry OBJECT-TYPE
        SYNTAX        Rc2kQosIngressDscpToQosEntry
        MAX-ACCESS    not-accessible
        STATUS        current
        DESCRIPTION   "Entry containing information of Dscp->Qos mapping"
        INDEX         { rc2kQosIngressDscpToQosRow }
        ::= { rc2kQosIngressDscpToQosTable 1 }

Rc2kQosIngressDscpToQosEntry ::= SEQUENCE {
                rc2kQosIngressDscpToQosRow INTEGER,
                rc2kQosIngressDscpToQosInDscp INTEGER,
                rc2kQosIngressDscpToQosInDscpBinaryFormat DisplayString(SIZE(6)),
                rc2kQosIngressDscpToQosQosLevel INTEGER
        }

rc2kQosIngressDscpToQosRow OBJECT-TYPE
        SYNTAX        INTEGER (1..64)
        MAX-ACCESS    read-only
        STATUS        current
        DESCRIPTION   "Used to uniquely identify a row in this table."
        ::= { rc2kQosIngressDscpToQosEntry 1 }

rc2kQosIngressDscpToQosInDscp OBJECT-TYPE
        SYNTAX        INTEGER (0..63)
        MAX-ACCESS    read-only
        STATUS        current
        DESCRIPTION   "A 6-bit value used to define the Differentiated
                      Service Code Point(DSCP)."
        ::= { rc2kQosIngressDscpToQosEntry 2 }

rc2kQosIngressDscpToQosInDscpBinaryFormat OBJECT-TYPE
        SYNTAX        DisplayString(SIZE(6))
        MAX-ACCESS    read-only
        STATUS        current
        DESCRIPTION   "The 'rc2kQosIngressDscpToQosInDscp' value shown
                      in a binary format (network order)."
        ::= { rc2kQosIngressDscpToQosEntry 3 }

rc2kQosIngressDscpToQosQosLevel OBJECT-TYPE
        SYNTAX        INTEGER (0..7)
        MAX-ACCESS    read-write
        STATUS        current
        DESCRIPTION   "qos level"
        ::= { rc2kQosIngressDscpToQosEntry 4 }


-- 2k Egress Qos To Dscp Table

rc2kQosEgressQosToDscpTable OBJECT-TYPE
        SYNTAX          SEQUENCE OF Rc2kQosEgressQosToDscpEntry
        MAX-ACCESS      not-accessible
        STATUS          current
        DESCRIPTION     "This table is used to specify the QOS to
                        DSCP field (QOS->DsField) mapping on packet
                        egress."
        ::= { rc2kQos 8 }

rc2kQosEgressQosToDscpEntry OBJECT-TYPE
        SYNTAX        Rc2kQosEgressQosToDscpEntry
        MAX-ACCESS    not-accessible
        STATUS        current
        DESCRIPTION   "Entry containing information of Qos->Qos mapping"
        INDEX         { rc2kQosEgressQosToDscpRow }
        ::= { rc2kQosEgressQosToDscpTable 1 }

Rc2kQosEgressQosToDscpEntry ::= SEQUENCE {
                rc2kQosEgressQosToDscpRow INTEGER,
                rc2kQosEgressQosToDscpQosLevel INTEGER,
                rc2kQosEgressQosToDscpOutDscp INTEGER,
                rc2kQosEgressQosToDscpOutDscpBinaryFormat DisplayString(SIZE(6))
        }

rc2kQosEgressQosToDscpRow OBJECT-TYPE
        SYNTAX        INTEGER (1..8)
        MAX-ACCESS    read-only
        STATUS        current
        DESCRIPTION   "Used to uniquely identify a row in this table."
        ::= { rc2kQosEgressQosToDscpEntry 1 }

rc2kQosEgressQosToDscpQosLevel OBJECT-TYPE
        SYNTAX        INTEGER (0..7)
        MAX-ACCESS    read-only
        STATUS        current
        DESCRIPTION   "qos level"
        ::= { rc2kQosEgressQosToDscpEntry 2 }

rc2kQosEgressQosToDscpOutDscp OBJECT-TYPE
        SYNTAX        INTEGER (0..63)
        MAX-ACCESS    read-write
        STATUS        current
        DESCRIPTION   "A 6-bit value used to define the Differentiated
                      Service Code Point(DSCP)."
        ::= { rc2kQosEgressQosToDscpEntry 3 }

rc2kQosEgressQosToDscpOutDscpBinaryFormat OBJECT-TYPE
        SYNTAX        DisplayString(SIZE(6))
        MAX-ACCESS    read-only
        STATUS        current
        DESCRIPTION   "The 'rc2kQosEgressQosToDscpOutDscp' value show
                      in a binary format (network order)."
        ::= { rc2kQosEgressQosToDscpEntry 4 }

-- rc2kAtm Group

rc2kAtm         OBJECT IDENTIFIER ::= { rc2k 9 }

rc2kAtmGlobal   OBJECT IDENTIFIER ::= { rc2kAtm 1 }


-- Atm Port Table

rc2kAtmPortTable OBJECT-TYPE
        SYNTAX        SEQUENCE OF Rc2kAtmPortEntry
        MAX-ACCESS    not-accessible
        STATUS        current
        DESCRIPTION   "ATM port table"
        ::= { rc2kAtm 2 }

rc2kAtmPortEntry OBJECT-TYPE
        SYNTAX        Rc2kAtmPortEntry
        MAX-ACCESS    not-accessible
        STATUS        current
        DESCRIPTION   "Entry containing information of ATM port"
        INDEX         { rc2kAtmPortIfIndex }
        ::= { rc2kAtmPortTable 1 }

Rc2kAtmPortEntry ::= SEQUENCE {
                rc2kAtmPortIfIndex InterfaceIndex,
                rc2kAtmPortNumVpiBits INTEGER,
                rc2kAtmPortNumVciBits INTEGER,
                rc2kAtmPortMediaType INTEGER,
                rc2kAtmPortScrambleEnable TruthValue,
                rc2kAtmPortFramingMode INTEGER,
                rc2kAtmPortClockSource INTEGER,
                rc2kAtmPortLineSpeed INTEGER,
                rc2kAtmPortLoopBackMode INTEGER,
                rc2kAtmPortMacAddress MacAddress
        }

rc2kAtmPortIfIndex OBJECT-TYPE
        SYNTAX          InterfaceIndex
        MAX-ACCESS      read-only
        STATUS          current
        DESCRIPTION     "port number"
        ::= { rc2kAtmPortEntry 1 }

rc2kAtmPortNumVpiBits OBJECT-TYPE
        SYNTAX          INTEGER (1..8)
        MAX-ACCESS      read-write
        STATUS          current
        DESCRIPTION   	"# of vpi bits. For OC3, the max number of vpibits is 6. 
                         However, for OC12, it is 8.  Both media types share 
                         the same MIB object. "
        ::= { rc2kAtmPortEntry 2 }

rc2kAtmPortNumVciBits OBJECT-TYPE
        SYNTAX          INTEGER (1..16)
        MAX-ACCESS      read-write
        STATUS          current
        DESCRIPTION     "# of vci bits"
        ::= { rc2kAtmPortEntry 3 }

rc2kAtmPortMediaType OBJECT-TYPE
        SYNTAX          INTEGER {
                          smf(1),       -- single mode fiber
                          mmf(2),       -- mixed mode fiber
                          ds3(3)         
                        }
        MAX-ACCESS      read-only
        STATUS          current
        DESCRIPTION     "media type"
        ::= { rc2kAtmPortEntry 4 }

rc2kAtmPortScrambleEnable OBJECT-TYPE
        SYNTAX          TruthValue
        MAX-ACCESS      read-write
        STATUS          current
        DESCRIPTION     "enable scramble"
        DEFVAL          { false }
        ::= { rc2kAtmPortEntry 5 }

rc2kAtmPortFramingMode OBJECT-TYPE
        SYNTAX          INTEGER {
                          sonet(1),
                          sdh(2),
                          ds3CbitAdm(3),
                          ds3CbitPlcp(4),
                          ds3M23Adm(5),
                          ds3M23Plcp(6)
                        }
        MAX-ACCESS      read-write
        STATUS          current
        DESCRIPTION     "port framing mode"
        DEFVAL          { sonet }
        ::= { rc2kAtmPortEntry 6 }

rc2kAtmPortClockSource OBJECT-TYPE
        SYNTAX          INTEGER {
                          loopTimed(1),
                          freeRunning(2)
                        }
        MAX-ACCESS      read-write
        STATUS          current
        DESCRIPTION     "clock source"
        ::= { rc2kAtmPortEntry 7 }

rc2kAtmPortLineSpeed OBJECT-TYPE
        SYNTAX          INTEGER {
                          oc3c(1),
                          oc12c(2),
                          ds3(3)
                        }
        MAX-ACCESS      read-only
        STATUS          current
        DESCRIPTION     "line speed"
        ::= { rc2kAtmPortEntry 8 }

rc2kAtmPortLoopBackMode OBJECT-TYPE
        SYNTAX          INTEGER {
                          off(1),
                          internal(2),
                          external(3),
                          ds3PayloadLoop(4),
                          ds3DiagLoop(5),
                          ds3LineLoop(6)
                        }
        MAX-ACCESS      read-write
        STATUS          current
        DESCRIPTION     "loop back mode"
        DEFVAL          { off }
        ::= { rc2kAtmPortEntry 9 }

rc2kAtmPortMacAddress OBJECT-TYPE
        SYNTAX        MacAddress
        MAX-ACCESS    read-only
        STATUS        current
        DESCRIPTION   "XLR assigned MAC addr"
        ::= { rc2kAtmPortEntry 10 }

-- Atm Pvc Table

rc2kAtmPvcTable OBJECT-TYPE
        SYNTAX        SEQUENCE OF Rc2kAtmPvcEntry
        MAX-ACCESS    not-accessible
        STATUS        current
        DESCRIPTION   "ATM Pvc table"
        ::= { rc2kAtm 3 }

rc2kAtmPvcEntry OBJECT-TYPE
        SYNTAX        Rc2kAtmPvcEntry
        MAX-ACCESS    not-accessible
        STATUS        current
        DESCRIPTION   "Entry containing information of ATM Pvc"
        INDEX         { rc2kAtmPvcIfIndex, rc2kAtmPvcVpi, rc2kAtmPvcVci }
        ::= { rc2kAtmPvcTable 1 }

Rc2kAtmPvcEntry ::= SEQUENCE {
                rc2kAtmPvcIfIndex InterfaceIndex,
                rc2kAtmPvcVpi INTEGER,
                rc2kAtmPvcVci INTEGER,
                rc2kAtmPvcPvcId Integer32,
                rc2kAtmPvcName DisplayString,
                rc2kAtmPvcEncapsulation INTEGER,
                rc2kAtmPvcServiceType INTEGER,
                rc2kAtmPvcPeakCellRate INTEGER,
                rc2kAtmPvcSustainedCellRate INTEGER,
                rc2kAtmPvcMaxBurstSize INTEGER,
                rc2kAtmPvcRowStatus RowStatus,
                rc2kAtmPvcOamLbMgmtEnable     TruthValue,
                rc2kAtmPvcOamLbSendFrequency     INTEGER,
                rc2kAtmPvcOamLbRetryFrequency    INTEGER,
                rc2kAtmPvcOamLbUpCount        INTEGER,
                rc2kAtmPvcOamLbDownCount         INTEGER,
                rc2kAtmPvcOamTrapEnable    TruthValue,
                rc2kAtmPvcOamVcStatus         INTEGER,
                rc2kAtmPvcOamLbRequestSent    Counter32,
                rc2kAtmPvcOamLbReplySent         Counter32,
                rc2kAtmPvcOamLbReplyReceived     Counter32
        }

rc2kAtmPvcIfIndex OBJECT-TYPE
        SYNTAX          InterfaceIndex
        MAX-ACCESS      read-only
        STATUS          current
        DESCRIPTION     "port number"
        ::= { rc2kAtmPvcEntry 1 }

rc2kAtmPvcVpi OBJECT-TYPE
        SYNTAX          INTEGER (0..255)
        MAX-ACCESS      read-only
        STATUS          current
        DESCRIPTION     "vpi of this pvc"
        ::= { rc2kAtmPvcEntry 2 }

rc2kAtmPvcVci OBJECT-TYPE
        SYNTAX          INTEGER (0..4095)
        MAX-ACCESS      read-only
        STATUS          current
        DESCRIPTION     "vci of this pvc"
        ::= { rc2kAtmPvcEntry 3 }

rc2kAtmPvcPvcId OBJECT-TYPE
        SYNTAX        Integer32
        MAX-ACCESS    read-only
        STATUS        current
        DESCRIPTION   "internal pvc id"
        ::= { rc2kAtmPvcEntry 4 }

rc2kAtmPvcName OBJECT-TYPE
        SYNTAX          DisplayString
        MAX-ACCESS      read-write
        STATUS          current
        DESCRIPTION     "name of pvc"
        ::= { rc2kAtmPvcEntry 5 }

rc2kAtmPvcEncapsulation OBJECT-TYPE
        SYNTAX          INTEGER {
                          null(1),
                          llcSnap(2)
                        }
        MAX-ACCESS      read-write
        STATUS          current
        DESCRIPTION     "encapsulation"
        DEFVAL          { llcSnap }
        ::= { rc2kAtmPvcEntry 6 }

rc2kAtmPvcServiceType OBJECT-TYPE
        SYNTAX          INTEGER {
                          ubr(1),
                          vbr(2)
                  }
        MAX-ACCESS      read-write
        STATUS          current
        DESCRIPTION     "service type"
        DEFVAL          { ubr }
        ::= { rc2kAtmPvcEntry 7 }

rc2kAtmPvcPeakCellRate OBJECT-TYPE
        SYNTAX          INTEGER (86..733490)
        MAX-ACCESS      read-write
        STATUS          current
        DESCRIPTION   	"Peak cell rate in cells per second. The maximum 
                         peak cell rate is half of the line rate.  The peak 
                         cell rate for MDA type OC12 must be less than 733491. 
                         However, for OC3, it is less than 182783."
        DEFVAL          { 23584 }
        ::= { rc2kAtmPvcEntry 8 }

rc2kAtmPvcSustainedCellRate OBJECT-TYPE
        SYNTAX          INTEGER (86..733490)
        MAX-ACCESS      read-write
        STATUS          current
        DESCRIPTION   	"Sustained cell rate in cells per second. The maximum 
                         peak cell rate is half of the line rate.  The peak 
                         cell rate for MDA type OC12 must be less than 733491. 
                         However, for OC3, it is less than 182783."
        DEFVAL          { 23584 }
        ::= { rc2kAtmPvcEntry 9 }

rc2kAtmPvcMaxBurstSize OBJECT-TYPE
        SYNTAX          INTEGER (2..255)
        MAX-ACCESS      read-write
        STATUS          current
        DESCRIPTION     "max burst size"
        DEFVAL          { 255 }
        ::= { rc2kAtmPvcEntry 10 }

rc2kAtmPvcRowStatus OBJECT-TYPE
        SYNTAX          RowStatus
        MAX-ACCESS      read-write
        STATUS          current
        DESCRIPTION     "row status"
        ::= { rc2kAtmPvcEntry 11 }

rc2kAtmPvcOamLbMgmtEnable OBJECT-TYPE
        SYNTAX		    TruthValue
        MAX-ACCESS		read-write
        STATUS		    current
        DESCRIPTION    "Indicate whether end-to-end F5 OAM loopback is enabled.
                        When it is enabled, OAM loopback request is sent 
                        periodically"
        DEFVAL		{ true }
        ::= { rc2kAtmPvcEntry  12 }

rc2kAtmPvcOamLbSendFrequency OBJECT-TYPE
        SYNTAX		   INTEGER (1..255)
        MAX-ACCESS		   read-write
        STATUS		   current
        DESCRIPTION	"Number of seconds between transmitting OAM loopback 
                         request"
        DEFVAL		{ 5 }
        ::= { rc2kAtmPvcEntry  13 } 

rc2kAtmPvcOamLbRetryFrequency OBJECT-TYPE
        SYNTAX		   INTEGER (1..255)
        MAX-ACCESS		   read-write
        STATUS		   current
        DESCRIPTION   "Number of seconds between retry"
        DEFVAL		{ 1 }
        ::= { rc2kAtmPvcEntry  14 }

rc2kAtmPvcOamLbUpCount OBJECT-TYPE
        SYNTAX		   INTEGER (1..255)
        MAX-ACCESS		   read-write
        STATUS		   current
        DESCRIPTION    "Number of consecutive end-to-end F5 OAM loopback cell 
                       responses that must be received in order to change a 
                       PVC connection state to up"
        DEFVAL		{ 3 }
        ::= { rc2kAtmPvcEntry  15 }

rc2kAtmPvcOamLbDownCount OBJECT-TYPE
        SYNTAX		   INTEGER (1..255)
        MAX-ACCESS		   read-write
        STATUS		   current
        DESCRIPTION    "Number of consecutive end-to-end F5 OAM loopback cell 
                       responses that are not received in order to change a 
                       PVC state to down."
        DEFVAL		{ 5 }
        ::= { rc2kAtmPvcEntry  16 }

rc2kAtmPvcOamTrapEnable OBJECT-TYPE
        SYNTAX		   TruthValue
        MAX-ACCESS		   read-write
        STATUS		   current
        DESCRIPTION	"Indicate whether OAM trap is enabled. When it is enabled,
                        a trap is sent to the management station when 
                       rc2kAtmPvcOamVcStatus is going up or down."
        DEFVAL		{ false }
        ::= { rc2kAtmPvcEntry 17 } 

rc2kAtmPvcOamVcStatus OBJECT-TYPE
        SYNTAX        	INTEGER {
                          notManaged(1),
                          downVerify(2),
                          down(3),
                          upVerify(4),
                          up(5)
                      	}
        MAX-ACCESS        	read-only
        STATUS        	current
        DESCRIPTION     "Indicate the status of PVC link.
                         Not Managed--VC is not being managed by OAM. 
			 Down Verify --An OAM loopback failed. End-to-end F5 OAM
                          loopback cells are sent at retry frequency to verify 
                          the VC is really down. After down-count unsuccessful 
                          retries, the VC goes to the down state (see definition 
                          of rc2kAtmPvcOamLoopbackDownCount).
                         Down --VC has not received responses to by end-to-end 
                          F5 OAM loopback cells. 
                         Up Verify -- An OAM loopback was successful. 
                          End-to-end F5 OAM loopback cells are sent at retry 
                          frequency to verify the VC is really up. After up-count
                          successive and successful loopback retries, the VC
                          goes to the Up state (see definition of 
                          rc2kAtmPvcOamLoopbackUpCount).
                         Up - End-to-end loopbacks are successful. "
       ::= { rc2kAtmPvcEntry  18 }


rc2kAtmPvcOamLbRequestSent OBJECT-TYPE
       SYNTAX			Counter32
       MAX-ACCESS		   read-only
       STATUS		   current
       DESCRIPTION	"Number of OAM loopback request sent"
       ::= { rc2kAtmPvcEntry  19 }

rc2kAtmPvcOamLbReplySent OBJECT-TYPE
       SYNTAX		   Counter32
       MAX-ACCESS		   read-only
       STATUS		   current
       DESCRIPTION	"Number of OAM loopback reply sent"
       ::= { rc2kAtmPvcEntry  20 }

rc2kAtmPvcOamLbReplyReceived OBJECT-TYPE
       SYNTAX		   Counter32
       MAX-ACCESS		   read-only
       STATUS		   current
       DESCRIPTION	"Number of OAM loopback reply received"
       ::= { rc2kAtmPvcEntry  21 } 

-- Atm 1483Elan Table

rc2kAtm1483ElanTable OBJECT-TYPE
        SYNTAX        SEQUENCE OF Rc2kAtm1483ElanEntry
        MAX-ACCESS    not-accessible
        STATUS        current
        DESCRIPTION   "ATM 1483Elan table"
        ::= { rc2kAtm 5 }

rc2kAtm1483ElanEntry OBJECT-TYPE
        SYNTAX        Rc2kAtm1483ElanEntry
        MAX-ACCESS    not-accessible
        STATUS        current
        DESCRIPTION   "Entry containing information of ATM 1483Elan"
        INDEX         { rc2kAtm1483ElanIfIndex, rc2kAtm1483ElanVlanId }
        ::= { rc2kAtm1483ElanTable 1 }

Rc2kAtm1483ElanEntry ::= SEQUENCE {
                rc2kAtm1483ElanIfIndex InterfaceIndex,
                rc2kAtm1483ElanElanId Integer32,
                rc2kAtm1483ElanNumPvcIds INTEGER,
                rc2kAtm1483ElanPvcIds IdList,
                rc2kAtm1483ElanVlanId Integer32,
                rc2kAtm1483ElanRowStatus RowStatus,
                rc2kAtm1483ElanConnectType INTEGER,
                rc2kAtm1483ElanVlanMacAddress MacAddress,
                rc2kAtm1483ElanDummyMacAddress MacAddress,
                rc2kAtm1483ElanLocalIpAddress IpAddress,
                rc2kAtm1483ElanRemoteIpAddress IpAddress,
                rc2kAtm1483ElanInArpSendEnable TruthValue,
                rc2kAtm1483ElanInArpSendInterval INTEGER,
                rc2kAtm1483ElanIpxVlanEncapMethod INTEGER,
                rc2kAtm1483ElanIpxNetworkNum INTEGER,
                rc2kAtm1483ElanStgId Integer32,
                rc2kAtm1483ElanrcStgTaggedBpduVlanId Integer32,
                rc2kAtm1483ElanIpxNetworkAddr OCTET STRING (SIZE(4))
        }

rc2kAtm1483ElanIfIndex OBJECT-TYPE
        SYNTAX        InterfaceIndex
        MAX-ACCESS    read-only
        STATUS        current
        DESCRIPTION   "port number"
        ::= { rc2kAtm1483ElanEntry 1 }

rc2kAtm1483ElanElanId OBJECT-TYPE
        SYNTAX        Integer32
        MAX-ACCESS    read-only
        STATUS        current
        DESCRIPTION   "Elan Id"
        ::= { rc2kAtm1483ElanEntry 2 }

rc2kAtm1483ElanNumPvcIds OBJECT-TYPE
        SYNTAX        INTEGER (0..64)
        MAX-ACCESS    read-only
        STATUS        current
        DESCRIPTION   "# pvc-ids in list"
        ::= { rc2kAtm1483ElanEntry 3 }

rc2kAtm1483ElanPvcIds OBJECT-TYPE
        SYNTAX        IdList (SIZE (256))
        MAX-ACCESS    read-write
        STATUS        current
        DESCRIPTION   "list of pvc-ids. each pvc-id is represented by a
                      32 bit value  this field can contain a maximum of
                      64 pvc-ids."
        ::= { rc2kAtm1483ElanEntry 4 }

rc2kAtm1483ElanVlanId OBJECT-TYPE
        SYNTAX        Integer32 (0..2147483647)
        MAX-ACCESS    read-write
        STATUS        current
        DESCRIPTION   "vlan tag for this 1483"
        ::= { rc2kAtm1483ElanEntry 5 }

rc2kAtm1483ElanRowStatus OBJECT-TYPE
        SYNTAX        RowStatus
        MAX-ACCESS    read-write
        STATUS        current
        DESCRIPTION   "row status"
        ::= { rc2kAtm1483ElanEntry 6 }

rc2kAtm1483ElanConnectType OBJECT-TYPE
        SYNTAX        INTEGER {
                          bridged(1),
                          ip(2),
                          ipx(3),
                          muxIpIpx(4)
                      }
        MAX-ACCESS    read-write
        STATUS        current
        DESCRIPTION   "connection type"
        ::= { rc2kAtm1483ElanEntry 7 }

rc2kAtm1483ElanVlanMacAddress OBJECT-TYPE
        SYNTAX        MacAddress
        MAX-ACCESS    read-only
        STATUS        current
        DESCRIPTION   "mac for vlan"
        ::= { rc2kAtm1483ElanEntry 8 }

rc2kAtm1483ElanDummyMacAddress OBJECT-TYPE
        SYNTAX        MacAddress
        MAX-ACCESS    read-only
        STATUS        current
        DESCRIPTION   "dummy mac for the other router"
        ::= { rc2kAtm1483ElanEntry 9 }

rc2kAtm1483ElanLocalIpAddress OBJECT-TYPE
        SYNTAX        IpAddress
        MAX-ACCESS    read-write
        STATUS        current
        DESCRIPTION   "local ip, if ConnectType is ip(2)"
        ::= { rc2kAtm1483ElanEntry 10 }

rc2kAtm1483ElanRemoteIpAddress OBJECT-TYPE
        SYNTAX        IpAddress
        MAX-ACCESS    read-write
        STATUS        current
        DESCRIPTION   "remote ip, if ConnectType is ip(2)"
        ::= { rc2kAtm1483ElanEntry 11 }

rc2kAtm1483ElanInArpSendEnable OBJECT-TYPE
        SYNTAX        TruthValue
        MAX-ACCESS    read-write
        STATUS        current
        DESCRIPTION   "enable arp sending on the port, if
                       ConnectType is ip(2)"
        DEFVAL        { false }
        ::= { rc2kAtm1483ElanEntry 12 }

rc2kAtm1483ElanInArpSendInterval OBJECT-TYPE
        SYNTAX        INTEGER (0..60)
        MAX-ACCESS    read-write
        STATUS        current
        DESCRIPTION   "interval of arp sending on the port, if
                       ConnectType is ip(2)"
        ::= { rc2kAtm1483ElanEntry 13 }

rc2kAtm1483ElanIpxVlanEncapMethod OBJECT-TYPE
        SYNTAX        INTEGER {
                          llc(1),
                          snap(2),
                          ether-ii(3),
                          raw(4)
                      }
        MAX-ACCESS    read-write
        STATUS        current
        DESCRIPTION   "vlan encapsulation method, if ConnectType
                       is ipx(3)"
        ::= { rc2kAtm1483ElanEntry 14 }

rc2kAtm1483ElanIpxNetworkNum OBJECT-TYPE
        SYNTAX        INTEGER (0..2147483647)
        MAX-ACCESS    read-write
        STATUS        current
        DESCRIPTION   "network number, if ConnectType is ipx(3)"
        ::= { rc2kAtm1483ElanEntry 15 }

rc2kAtm1483ElanStgId OBJECT-TYPE
        SYNTAX          Integer32
        MAX-ACCESS      read-only
        STATUS          current
        DESCRIPTION     "An identifier used to identify a STG in the device,
                         only in bridge mode"
        ::= { rc2kAtm1483ElanEntry 16 }

rc2kAtm1483ElanrcStgTaggedBpduVlanId OBJECT-TYPE
        SYNTAX          Integer32
        MAX-ACCESS      read-only
        STATUS          current
        DESCRIPTION     "The VLAN ID to be used for tagging BPDUs,
                         only in bridge mode."
        ::= { rc2kAtm1483ElanEntry 17 }

rc2kAtm1483ElanIpxNetworkAddr OBJECT-TYPE
        SYNTAX        OCTET STRING (SIZE(4))
        MAX-ACCESS    read-write
        STATUS        current
        DESCRIPTION   "network number, instead of rc2kAtm1483ElanIpxNetworkNum"
        ::= { rc2kAtm1483ElanEntry 18 }


-- 2kAtm Sio Card Config Table

rc2kAtmSioCardConfigTable OBJECT-TYPE
        SYNTAX        SEQUENCE OF Rc2kAtmSioCardConfigEntry
        MAX-ACCESS    not-accessible
        STATUS        current
        DESCRIPTION   "2kAtm Sio Card Config Table"
        ::= { rc2kAtm 8 }

rc2kAtmSioCardConfigEntry OBJECT-TYPE
        SYNTAX        Rc2kAtmSioCardConfigEntry
        MAX-ACCESS    not-accessible
        STATUS        current
        DESCRIPTION   "Entry containing information of 2kAtm Sio Card Config."
        INDEX         { rc2kAtmSioCardConfigSlotIndex }
        ::= { rc2kAtmSioCardConfigTable 1 }

Rc2kAtmSioCardConfigEntry ::= SEQUENCE {
                rc2kAtmSioCardConfigSlotIndex       Integer32,
                rc2kAtmSioCardConfigAction          INTEGER,
                rc2kAtmSioCardConfigTraceMode       INTEGER,
                rc2kAtmSioCardConfigImageFileName   DisplayString,
                rc2kAtmSioCardConfigElanStatsEnable INTEGER,
                rc2kAtmSioCardConfigStatsPollPeriod INTEGER
        }

rc2kAtmSioCardConfigSlotIndex OBJECT-TYPE
        SYNTAX        Integer32 (0..2147483647)
        MAX-ACCESS    read-only
        STATUS        current
        DESCRIPTION   "slot Index."
        ::= { rc2kAtmSioCardConfigEntry 1 }

rc2kAtmSioCardConfigAction OBJECT-TYPE
        SYNTAX        INTEGER {
                          other(0),
                          reset(1)
                      }
        MAX-ACCESS    read-write
        STATUS        current
        DESCRIPTION   ""
        ::= { rc2kAtmSioCardConfigEntry 2 }

rc2kAtmSioCardConfigTraceMode OBJECT-TYPE
        SYNTAX        INTEGER {
                          other(0),
                          traceOn(1)
                      }
        MAX-ACCESS    read-write
        STATUS        current
        DESCRIPTION   ""
        ::= { rc2kAtmSioCardConfigEntry 3 }

rc2kAtmSioCardConfigImageFileName OBJECT-TYPE
        SYNTAX        DisplayString
        MAX-ACCESS    read-only
        STATUS        current
        DESCRIPTION   "ATM Image file name."
        ::= { rc2kAtmSioCardConfigEntry 4 }

rc2kAtmSioCardConfigElanStatsEnable OBJECT-TYPE
        SYNTAX       INTEGER {
                        disable(1),
                        enable(2)
                     }   
        MAX-ACCESS   read-write
        STATUS       current
        DESCRIPTION  "Enable/Disable Elan Statistics collection"
        DEFVAL       { 1 }
        ::= { rc2kAtmSioCardConfigEntry 5 }

rc2kAtmSioCardConfigStatsPollPeriod OBJECT-TYPE
        SYNTAX       INTEGER(3..15)
        MAX-ACCESS   read-write
        STATUS       current
        DESCRIPTION  "Time interval after which  Elan statistics would 
                      be polled"
        DEFVAL       { 5 }
        ::= { rc2kAtmSioCardConfigEntry 6 }  
    
    
--- ATM port stats

rc2kAtmPortStatsTable OBJECT-TYPE
       SYNTAX        SEQUENCE OF Rc2kAtmPortStatsEntry
       MAX-ACCESS    not-accessible
       STATUS        current
       DESCRIPTION   "ATM port statistics table"
       ::= { rc2kAtm 10 }

rc2kAtmPortStatsEntry OBJECT-TYPE
       SYNTAX        Rc2kAtmPortStatsEntry
       MAX-ACCESS    not-accessible
       STATUS        current
       DESCRIPTION   "Entry containing information of ATM port statistics"
       INDEX         { rc2kAtmPortStatsIfIndex }
       ::= { rc2kAtmPortStatsTable 1 }

Rc2kAtmPortStatsEntry ::= SEQUENCE {
       rc2kAtmPortStatsIfIndex          InterfaceIndex,
       rc2kAtmPortStatsInCells          Counter64,
   	   rc2kAtmPortStatsOutCells         Counter64,
   	   rc2kAtmPortStatsOutIdleCells     Counter64,
   	   rc2kAtmPortStatsInHecCorrected   Counter32,
   	   rc2kAtmPortStatsInHecUncorrected	Counter32,
   	   rc2kAtmPortStatsInUnknownProtos  Counter32,
   	   rc2kAtmPortStatsInPkts           Counter32,
   	   rc2kAtmPortStatsOutPkts          Counter32,
   	   rc2kAtmPortStatsInDroppedPkts    Counter32,
   	   rc2kAtmPortStatsOutDroppedPkts   Counter32
}

rc2kAtmPortStatsIfIndex OBJECT-TYPE
       SYNTAX        InterfaceIndex
       MAX-ACCESS    read-only
       STATUS        current
       DESCRIPTION   "port number"
       ::= { rc2kAtmPortStatsEntry 1 }

rc2kAtmPortStatsInCells OBJECT-TYPE
       SYNTAX        Counter64
       MAX-ACCESS    read-only
       STATUS        current
       DESCRIPTION   "Number of Cells received from ATM interface"
      	::= { rc2kAtmPortStatsEntry 2 }

rc2kAtmPortStatsOutCells OBJECT-TYPE
	      SYNTAX        Counter64
	      MAX-ACCESS    read-only
       STATUS        current
       DESCRIPTION   "Number of Cells transmitted by ATM interface"
       ::= { rc2kAtmPortStatsEntry 3 }

rc2kAtmPortStatsOutIdleCells OBJECT-TYPE
	      SYNTAX        Counter64
       MAX-ACCESS    read-only
       STATUS        current
       DESCRIPTION   "Number of Idle Cells transmitted"
       ::= { rc2kAtmPortStatsEntry 4 }

rc2kAtmPortStatsInHecCorrected OBJECT-TYPE
	      SYNTAX        Counter32
       MAX-ACCESS    read-only
       STATUS        current
       DESCRIPTION   "Number of received cells in which HCS  
                      was corrected"
      	::= { rc2kAtmPortStatsEntry 5 }

rc2kAtmPortStatsInHecUncorrected OBJECT-TYPE
	      SYNTAX        Counter32
       MAX-ACCESS    read-only
       STATUS        current
       DESCRIPTION   "Number of received cells dropped because HCS 
                      couldn't be corrected"
       ::= { rc2kAtmPortStatsEntry 6 }

rc2kAtmPortStatsInUnknownProtos OBJECT-TYPE
	      SYNTAX        Counter32
       MAX-ACCESS    read-only
       STATUS        current
       DESCRIPTION   "Number of received cells dropped with wrong VPI/VCI"
       ::= { rc2kAtmPortStatsEntry 7 }

rc2kAtmPortStatsInPkts OBJECT-TYPE
	      SYNTAX        Counter32
       MAX-ACCESS    read-only
       STATUS        current
       DESCRIPTION   "Number of AAL5 CPCS PDUs received"
       ::= { rc2kAtmPortStatsEntry 8 }

rc2kAtmPortStatsOutPkts OBJECT-TYPE
	      SYNTAX        Counter32
       MAX-ACCESS    read-only
       STATUS        current
       DESCRIPTION   "Number of AAL5 CPCS PDUs transmitted"
       ::= { rc2kAtmPortStatsEntry 9 }

rc2kAtmPortStatsInDroppedPkts OBJECT-TYPE
	      SYNTAX        Counter32
       MAX-ACCESS    read-only
       STATUS        current
       DESCRIPTION   "Number of AAL5 CPCS PDUs dropped due to 
                      resource exhaustion"
       ::= { rc2kAtmPortStatsEntry 10 }

rc2kAtmPortStatsOutDroppedPkts OBJECT-TYPE
	      SYNTAX        Counter32
       MAX-ACCESS    read-only
       STATUS        current
       DESCRIPTION   "Number of AAL5 CPCS PDUs dropped because the
                      transmitter closed the channel"
       ::= { rc2kAtmPortStatsEntry 11 } 

-- ATM vPort Stats

rc2kAtmVPortStatsTable OBJECT-TYPE
	      SYNTAX        SEQUENCE OF Rc2kAtmVPortStatsEntry
       MAX-ACCESS    not-accessible
       STATUS        current
       DESCRIPTION   "ATM Elan statistics table"
       ::= { rc2kAtm 11 }

rc2kAtmVPortStatsEntry OBJECT-TYPE
       SYNTAX        Rc2kAtmVPortStatsEntry
       MAX-ACCESS    not-accessible
       STATUS        current
       DESCRIPTION   "Entry containing information of ATM Elan statistics"
       INDEX         { rc2kAtmVPortStatsIfIndex , rc2kAtmVPortStatsVlanId }
       ::= { rc2kAtmVPortStatsTable 1 }

Rc2kAtmVPortStatsEntry ::= SEQUENCE {
       rc2kAtmVPortStatsIfIndex          InterfaceIndex,
       rc2kAtmVPortStatsVlanId           Integer32,		
       rc2kAtmVPortStatsClear            INTEGER,
       rc2kAtmVPortStatsInOctets         Counter64,
       rc2kAtmVPortStatsOutOctets        Counter64,
       rc2kAtmVPortStatsInErrors         Counter32,
       rc2kAtmVPortStatsOutErrors        Counter32,		
       rc2kAtmVPortStatsInDiscards       Counter32,
       rc2kAtmVPortStatsOutDiscards      Counter32,
       rc2kAtmVPortStatsInUcastPkts      Counter32,
       rc2kAtmVPortStatsOutUcastPkts     Counter32,
       rc2kAtmVPortStatsInMulticastPkts  Counter32,
       rc2kAtmVPortStatsOutMulticastPkts Counter32,
       rc2kAtmVPortStatsInBroadcastPkts  Counter32,
       rc2kAtmVPortStatsOutBroadcastPkts Counter32 
    }

rc2kAtmVPortStatsIfIndex OBJECT-TYPE
       SYNTAX       InterfaceIndex
       MAX-ACCESS   read-only
       STATUS       current
       DESCRIPTION  "port number"
       ::= { rc2kAtmVPortStatsEntry 1 }

rc2kAtmVPortStatsVlanId OBJECT-TYPE
       SYNTAX       Integer32 (0..2147483647)	
       MAX-ACCESS   read-only
       STATUS       current
       DESCRIPTION  "Vlan Id"
       ::= { rc2kAtmVPortStatsEntry 2 }

rc2kAtmVPortStatsClear OBJECT-TYPE
       SYNTAX       INTEGER {
                       other (0),
                       clear (1)
                    } 
       MAX-ACCESS   read-write
       STATUS       current
       DESCRIPTION  "Clear Elan Stats"
       DEFVAL       { 0 }
       ::= { rc2kAtmVPortStatsEntry 3 }

rc2kAtmVPortStatsInOctets OBJECT-TYPE
       SYNTAX       Counter64
       MAX-ACCESS   read-only
       STATUS       current
       DESCRIPTION  "AAL5 CPCS PDU octects received from ATM interface"
       ::= { rc2kAtmVPortStatsEntry 4 }

rc2kAtmVPortStatsOutOctets OBJECT-TYPE
       SYNTAX       Counter64
       MAX-ACCESS   read-only
       STATUS       current
       DESCRIPTION  "AAL5 CPCS PDU octects transmitted out of ATM interface"
       ::= { rc2kAtmVPortStatsEntry 5 }

rc2kAtmVPortStatsInErrors OBJECT-TYPE
       SYNTAX       Counter32
       MAX-ACCESS   read-only
       STATUS       current
       DESCRIPTION "AAL5 CPCS PDUs received with errors from ATM interface.
                    These errors include CRC-32 errors,SAR time-out errors
                    And oversized SDU errors" 
	      ::= { rc2kAtmVPortStatsEntry 6 }

rc2kAtmVPortStatsOutErrors OBJECT-TYPE
       SYNTAX       Counter32
       MAX-ACCESS   read-only
       STATUS       current
       DESCRIPTION  "Number of AAL5 CPCS PDUs that couldn't be transmitted
                     due to errors"
       ::= { rc2kAtmVPortStatsEntry 7 }

rc2kAtmVPortStatsInDiscards OBJECT-TYPE
       SYNTAX       Counter32
       MAX-ACCESS   read-only
       STATUS       current
       DESCRIPTION  "Number of received AAL5 CPCS PDUs discarded "
       ::= { rc2kAtmVPortStatsEntry 8 }

rc2kAtmVPortStatsOutDiscards  OBJECT-TYPE
       SYNTAX       Counter32
       MAX-ACCESS   read-only
       STATUS       current
       DESCRIPTION  "Number of AAL5 CPCS PDUs which are to be transmitted
                     but discarded"
       ::= { rc2kAtmVPortStatsEntry 9 }

rc2kAtmVPortStatsInUcastPkts OBJECT-TYPE
       SYNTAX       Counter32
       MAX-ACCESS   read-only
       STATUS       current
       DESCRIPTION  "Received ethernet/IP/IPX packets whose destination 
                     address is neither a multicast nor a broadcast 
                     address"
       ::= { rc2kAtmVPortStatsEntry 10 }

rc2kAtmVPortStatsOutUcastPkts OBJECT-TYPE
       SYNTAX       Counter32
       MAX-ACCESS   read-only
       STATUS       current
       DESCRIPTION  "Forwarded ethernet/IP/IPX packets whose destination  
                     address is neither a multicast nor a broadcast     
                     address"
       ::= { rc2kAtmVPortStatsEntry 11 }

rc2kAtmVPortStatsInMulticastPkts OBJECT-TYPE
       SYNTAX       Counter32
       MAX-ACCESS   read-only
       STATUS       current
       DESCRIPTION  "Received ethernet/IP/IPX packets whose destination  
                     MAC address(or IP address in case of IP ELAN type)
                     is multicast MAC address or class D IP address 
                     (in case of IP ELAN type) "    
       ::= { rc2kAtmVPortStatsEntry 12 }

rc2kAtmVPortStatsOutMulticastPkts OBJECT-TYPE
       SYNTAX       Counter32
       MAX-ACCESS   read-only
       STATUS       current
       DESCRIPTION  "Forwarded ethernet/IP/IPX packets whose destination  
                     MAC address(or IP address in case of IP ELAN type)
                     is multicast MAC address or class D IP address 
                     (in case of IP ELAN type) "
       ::= { rc2kAtmVPortStatsEntry 13 }

rc2kAtmVPortStatsInBroadcastPkts OBJECT-TYPE
       SYNTAX       Counter32
       MAX-ACCESS   read-only
       STATUS       current
       DESCRIPTION  "Received ethernet/IP/IPX packets whose destination
                     address in broadcast address"
       ::= { rc2kAtmVPortStatsEntry 14 }

rc2kAtmVPortStatsOutBroadcastPkts OBJECT-TYPE
       SYNTAX       Counter32
       MAX-ACCESS   read-only
       STATUS       current
       DESCRIPTION  "Forwarded ethernet/IP/IPX packets whose destination
                     address in broadcast address"
       ::= { rc2kAtmVPortStatsEntry 15 }

-- 2k CPU Ethernet Port Route table for Ipv6

rc2kCpuEthernetPortIpv6RouteTable OBJECT-TYPE
        SYNTAX        SEQUENCE OF Rc2kCpuEthernetPortIpv6RouteEntry
        MAX-ACCESS    not-accessible
        STATUS        current
        DESCRIPTION   "2k CPU Ethernet Port Route table for Ipv6"
        ::= { rc2k 13 }

rc2kCpuEthernetPortIpv6RouteEntry OBJECT-TYPE
        SYNTAX        Rc2kCpuEthernetPortIpv6RouteEntry
        MAX-ACCESS    not-accessible
        STATUS        current
        DESCRIPTION   "Entry containing information of 2k CPU Ethernet Port Ipv6"
        INDEX         { rc2kCpuEthernetPortIpv6RouteNetwork,
                        rc2kCpuEthernetPortIpv6RoutePrefixLength,
                        rc2kCpuEthernetPortIpv6RouteGateway}
        ::= { rc2kCpuEthernetPortIpv6RouteTable 1 }

Rc2kCpuEthernetPortIpv6RouteEntry ::= SEQUENCE {
                rc2kCpuEthernetPortIpv6RouteNetwork       Ipv6Address,
                rc2kCpuEthernetPortIpv6RoutePrefixLength  INTEGER,
                rc2kCpuEthernetPortIpv6RouteGateway       Ipv6Address,
                rc2kCpuEthernetPortIpv6RouteRowStatus     RowStatus
        }

rc2kCpuEthernetPortIpv6RouteNetwork OBJECT-TYPE
        SYNTAX          Ipv6Address
        MAX-ACCESS      not-accessible
        STATUS          current
        DESCRIPTION     "Used to configure the ipv6 network that can be
                        used to remotely manage this device."
        ::= { rc2kCpuEthernetPortIpv6RouteEntry 1 }

rc2kCpuEthernetPortIpv6RoutePrefixLength OBJECT-TYPE
     SYNTAX         INTEGER (0..128)
     MAX-ACCESS     not-accessible
     STATUS         current
     DESCRIPTION    "The length of the prefix (in bits)."
     ::= { rc2kCpuEthernetPortIpv6RouteEntry 2 }

rc2kCpuEthernetPortIpv6RouteGateway OBJECT-TYPE
        SYNTAX          Ipv6Address
        MAX-ACCESS      not-accessible
        STATUS          current
        DESCRIPTION     "Used to configure the the IPv6 address of the
                        gateway that should be used to forward IPv6
                        traffic."
        ::= { rc2kCpuEthernetPortIpv6RouteEntry 3 }

rc2kCpuEthernetPortIpv6RouteRowStatus OBJECT-TYPE
        SYNTAX        RowStatus
        MAX-ACCESS    read-create
        STATUS        current
        DESCRIPTION   "row status"
        ::= { rc2kCpuEthernetPortIpv6RouteEntry 4 }

-- slot power usage info

rc2kPowerConsumptionInfoTable OBJECT-TYPE
        SYNTAX        SEQUENCE OF Rc2kPowerConsumptionInfoEntry
        MAX-ACCESS    not-accessible
        STATUS        current
        DESCRIPTION   "Power consumption info table for all slots"
        ::= { rc2k 17 }

rc2kPowerConsumptionInfoEntry OBJECT-TYPE
        SYNTAX        Rc2kPowerConsumptionInfoEntry
        MAX-ACCESS    not-accessible
        STATUS        current
        DESCRIPTION   "Entry containing power consumption information of
			the slot"
        INDEX         { rc2kPowerConsumptionInfoIndex}
        ::= { rc2kPowerConsumptionInfoTable 1 }

Rc2kPowerConsumptionInfoEntry ::= SEQUENCE {
                rc2kPowerConsumptionInfoIndex            Integer32,
		rc2kPowerConsumptionInfoPowerStatus      INTEGER,
                rc2kPowerConsumptionInfoBasePower        Integer32,
                rc2kPowerConsumptionInfoConsumedPower    Integer32,
                rc2kPowerConsumptionInfoPowerPriority    INTEGER,
		rc2kPowerConsumptionInfoSlotDescription  DisplayString,
		rc2kPowerConsumptionInfoCardDescription  DisplayString
        }

rc2kPowerConsumptionInfoIndex OBJECT-TYPE
        SYNTAX          Integer32 (1..32)
        MAX-ACCESS      not-accessible
        STATUS          current
        DESCRIPTION     "Slot number."
        ::= { rc2kPowerConsumptionInfoEntry 1 }

rc2kPowerConsumptionInfoPowerStatus OBJECT-TYPE
        SYNTAX          INTEGER {
				on(1),
				off(2)
			}
        MAX-ACCESS      read-only	
        STATUS          current
        DESCRIPTION     "Power operation status of this slot"
        ::= { rc2kPowerConsumptionInfoEntry 2 }

rc2kPowerConsumptionInfoBasePower OBJECT-TYPE
        SYNTAX          Integer32
        MAX-ACCESS      read-only	
        STATUS          current
        DESCRIPTION     "The base power required for this slot"
        ::= { rc2kPowerConsumptionInfoEntry 3 }

rc2kPowerConsumptionInfoConsumedPower OBJECT-TYPE
        SYNTAX          Integer32
        MAX-ACCESS      read-only	
        STATUS          current
        DESCRIPTION     "The actual consumed power of this slot.
			Value will be set zero when Power status is 'off'
			rc2kPowerConsumptionInfoPowerStatus"
        ::= { rc2kPowerConsumptionInfoEntry 4 }

rc2kPowerConsumptionInfoPowerPriority OBJECT-TYPE
        SYNTAX          INTEGER
			{
                       	   critical(1),
                           high(2),
                           low(3)
                        }
        MAX-ACCESS      read-only	
        STATUS          current
        DESCRIPTION     "Used to indicate the priority of the slot for power 
                         management"
        ::= { rc2kPowerConsumptionInfoEntry 5 }

rc2kPowerConsumptionInfoSlotDescription OBJECT-TYPE
        SYNTAX          DisplayString (SIZE (0..20)) 
        MAX-ACCESS      read-only	
        STATUS          current
        DESCRIPTION     "User to indicate the slot type information.
                         Such as, 'Slot1'..'Slot12', 'SF1'..'SF4'..etc"
        ::= { rc2kPowerConsumptionInfoEntry 6 }

rc2kPowerConsumptionInfoCardDescription OBJECT-TYPE
        SYNTAX          DisplayString (SIZE (0..20)) 
        MAX-ACCESS      read-only	
        STATUS          current
        DESCRIPTION     "Hardware description of this card"
        ::= { rc2kPowerConsumptionInfoEntry 7 }

--
-- Card Temperature MIB Table
--

rc2kTemperatureTable	OBJECT-TYPE
     SYNTAX SEQUENCE OF Rc2kTemperatureEntry
     MAX-ACCESS   not-accessible
     STATUS       current
     DESCRIPTION  "Table for retrieving the temperatures 
		   of each card (CP, IO, SF) on the chassis"
     ::= { rc2k 18 }

rc2kTemperatureEntry OBJECT-TYPE
     SYNTAX        Rc2kTemperatureEntry
     MAX-ACCESS    not-accessible
     STATUS        current
     DESCRIPTION   "Contains information regarding the temperature of 
		    each slot (CP, IO and SF) on the chassis"
     INDEX        { rc2kTemperatureSlotIndex }
     ::= { rc2kTemperatureTable 1 }

Rc2kTemperatureEntry ::=
     SEQUENCE {
           rc2kTemperatureSlotIndex		Integer32,
           rc2kTemperatureSlotDescription	DisplayString,
	   rc2kTemperatureZone1Temperature	Gauge32,
	   rc2kTemperatureZone2Temperature	Gauge32,
	   rc2kTemperatureZone3Temperature	Gauge32,
	   rc2kTemperatureZone4Temperature	Gauge32,
	   rc2kTemperatureZone5Temperature	Gauge32,
	   rc2kTemperatureHighTemperature	Gauge32,
	   rc2kTemperatureLowTemperature	Gauge32,
	   rc2kTemperatureAlarmThreshold	Gauge32,
	   rc2kTemperatureShutdownThreshold	Gauge32
     }

rc2kTemperatureSlotIndex	OBJECT-TYPE
	SYNTAX		Integer32 (1..12 | 21..26)
	MAX-ACCESS	not-accessible
	STATUS		current
	DESCRIPTION	"Slot number of either a CP (1,2) or IO (3-12)
			 or SF (21-26)."
	::= { rc2kTemperatureEntry 1 }

rc2kTemperatureSlotDescription	OBJECT-TYPE
	SYNTAX		DisplayString (SIZE (0..20))
	MAX-ACCESS	read-only
	STATUS		current
	DESCRIPTION	"Used to indicate the slot type information.
                         Such as, 'Slot1'..'Slot12', 'SF1'..'SF4'..etc."
	::= { rc2kTemperatureEntry 2 }

rc2kTemperatureZone1Temperature	OBJECT-TYPE
	SYNTAX		Gauge32
	MAX-ACCESS	read-only
	STATUS		current
	DESCRIPTION	"Zone 1 temperature measured in celsius degree"
	::= { rc2kTemperatureEntry 3 }

rc2kTemperatureZone2Temperature	OBJECT-TYPE
	SYNTAX		Gauge32
	MAX-ACCESS	read-only
	STATUS		current
	DESCRIPTION	"Zone 2 temperature measured in celsius degree.
			 A value of 0 for this mib object indicates that
			 Zone 2 is not available on this slot."
	::= { rc2kTemperatureEntry 4 }

rc2kTemperatureZone3Temperature	OBJECT-TYPE
	SYNTAX		Gauge32
	MAX-ACCESS	read-only
	STATUS		current
	DESCRIPTION	"Zone 3 temperature measured in celsius degree.
			 A value of 0 for this mib object indicates that
			 Zone 3 is not available on this slot."
	::= { rc2kTemperatureEntry 5 }

rc2kTemperatureZone4Temperature	OBJECT-TYPE
	SYNTAX		Gauge32
	MAX-ACCESS	read-only
	STATUS		current
	DESCRIPTION	"Zone 4 temperature measured in celsius degree"
	::= { rc2kTemperatureEntry 6 }

rc2kTemperatureZone5Temperature	OBJECT-TYPE
	SYNTAX		Gauge32
	MAX-ACCESS	read-only
	STATUS		current
	DESCRIPTION	"Zone 5 2 temperature measured in celsius degree.
			 A value of 0 for this mib object indicates that
			 Zone 5 is not available on this slot."
	::= { rc2kTemperatureEntry 7 }

rc2kTemperatureHighTemperature	OBJECT-TYPE
	SYNTAX		Gauge32
	MAX-ACCESS	read-only
	STATUS		current
	DESCRIPTION	"Highest temperature measured in celsius degree"
	::= { rc2kTemperatureEntry 8 }

rc2kTemperatureLowTemperature	OBJECT-TYPE
	SYNTAX		Gauge32
	MAX-ACCESS	read-only
	STATUS		current
	DESCRIPTION	"Lowest temperature measured in celsius degree"
	::= { rc2kTemperatureEntry 9 }

rc2kTemperatureAlarmThreshold	OBJECT-TYPE
	SYNTAX		Gauge32
	MAX-ACCESS	read-only
	STATUS		current
	DESCRIPTION	"When the card temperature crosses this
			 threshold, an alarm will be set."
	::= { rc2kTemperatureEntry 10 }

rc2kTemperatureShutdownThreshold	OBJECT-TYPE
	SYNTAX		Gauge32
	MAX-ACCESS	read-only
	STATUS		current
	DESCRIPTION	"When the card temperature crosses this 
			 threshold, the card will be shutdown."
	::= { rc2kTemperatureEntry 11 }

-- 10Gb Ethernet MIB table begin

rcTengEnetStats 	OBJECT IDENTIFIER ::= { rcTengEnet 1 }

-- Wis Sonet traps --

rcWisTrap        OBJECT IDENTIFIER ::= { rcTengEnet 2 }

rcWisSonetTrapType OBJECT-TYPE
        SYNTAX        INTEGER {
                              sectionAlarm(1),
                              lineAlarm(2),
                              pathAlarm(3)    
                      }
        MAX-ACCESS    read-only
        STATUS        current
        DESCRIPTION   "Used to indicate a particular type of 10GE Sonet 
                      trap."
        ::= { rcWisTrap 1 }

rcWisSonetTrapIndication OBJECT-TYPE
        SYNTAX        INTEGER {
                            noDefect(1),         
                            sectionLossOfSignal(2),  
                            sectionLossOfFrame(3),
                            lineAlarmIndication(4),
                            lineRemoteDefectIndication(5),
                            pathLossOfPointer(6),
                            pathAlarmIndication(7),
                            pathRemoteDefectIndication(8),
                            pathUnequipped(9),
                            pathSignalLabelMismatch(10),
                            pathTraceMismatch(11)
                      } 
        MAX-ACCESS    read-only
        STATUS        current
        DESCRIPTION   "Used to indicate an indication for a 10GE Sonet trap."
        ::= { rcWisTrap 2 }

-- the 10Gb Ethernet-like Statistics group
      
rcTengDot3StatsTable  OBJECT-TYPE
	SYNTAX         	SEQUENCE OF RcTengDot3StatsEntry
        MAX-ACCESS     	not-accessible
        STATUS         	current
	DESCRIPTION	"Statistics for a collection of ethernet-like
             		interfaces attached to a particular system."
        ::= { rcTengEnetStats 1 }

rcTengDot3StatsEntry   OBJECT-TYPE
	SYNTAX      	RcTengDot3StatsEntry
	MAX-ACCESS  	not-accessible
	STATUS      	current
	DESCRIPTION	"Statistics for a particular interface to an
              		ethernet-like medium."
	INDEX     { rcTengDot3StatsIndex }
	::= { rcTengDot3StatsTable 1 }

RcTengDot3StatsEntry ::= 
	SEQUENCE {
		rcTengDot3StatsIndex                  		Integer32,
		rcTengDot3StatsAlignmentErrors            	Counter64,
		rcTengDot3StatsFCSErrors                  	Counter64,
		rcTengDot3StatsSingleCollisionFrames      	Counter64,
		rcTengDot3StatsMultipleCollisionFrames    	Counter64,
		rcTengDot3StatsSQETestErrors              	Counter64,
		rcTengDot3StatsDeferredTransmissions      	Counter64,
		rcTengDot3StatsLateCollisions             	Counter64, 
		rcTengDot3StatsExcessiveCollisions        	Counter64,
		rcTengDot3StatsInternalMacTransmitErrors  	Counter64,
		rcTengDot3StatsCarrierSenseErrors         	Counter64,
		rcTengDot3StatsFrameTooLongs              	Counter64,
		rcTengDot3StatsInternalMacReceiveErrors   	Counter64,
		rcTengDot3StatsEtherChipSet        		OBJECT IDENTIFIER,
-- copy & combine from rcStatGigTable
                rcTengDot3StatsLinkFailures         		Counter32,
                rcTengDot3StatsPacketErrors         		Counter32,
                rcTengDot3StatsCarrierErrors        		Counter32,
                rcTengDot3StatsLinkInactiveErrors   		Counter32,
                rcTengDot3StatsInFlowCtrlPkts       		Counter64,
                rcTengDot3StatsOutFlowCtrlPkts      		Counter64,
-- copy & cobmine this atrribute from rcTengStatEntry
                rcTengDot3StatsFrameTooShorts             	Counter64,
-- from rcStatGigTable
                rcTengDot3StatsInPfcPkts                        Counter64,
                rcTengDot3StatsOutPfcPkts                       Counter64
 	}
      
rcTengDot3StatsIndex   OBJECT-TYPE
 SYNTAX        Integer32 (0..2147483647)
	MAX-ACCESS  	read-only
	STATUS      	current
	DESCRIPTION	"An index value that uniquely identifies an
              		interface to an ethernet-like medium.  The
              		interface identified by a particular value of
              		this index is the same interface as identified
              		by the same value of ifIndex."
	::= { rcTengDot3StatsEntry 1 }

rcTengDot3StatsAlignmentErrors   OBJECT-TYPE
	SYNTAX     	Counter64
	MAX-ACCESS 		read-only
	STATUS     	current
	DESCRIPTION	"A count of frames received on a particular
             		interface that are not an integral number of
             		octets in length and do not pass the FCS check.
			The count represented by an instance of this
             		object is incremented when the alignmentError
             		status is returned by the MAC service to the
             		LLC (or other MAC user). Received frames for
             		which multiple error conditions obtain are,
             		according to the conventions of IEEE 802.3
             		Layer Management, counted exclusively according
             		to the error status presented to the LLC."
	REFERENCE	"IEEE 802.3 Layer Management"
	::= { rcTengDot3StatsEntry 2 }

rcTengDot3StatsFCSErrors   OBJECT-TYPE
	SYNTAX      	Counter64
	MAX-ACCESS  	read-only
	STATUS      	current
	DESCRIPTION	"A count of frames received on a particular
            		interface that are an integral number of octets
            		in length but do not pass the FCS check.
            		The count represented by an instance of this
            		object is incremented when the frameCheckError
            		status is returned by the MAC service to the
            		LLC (or other MAC user). Received frames for
            		which multiple error conditions obtain are,
            		according to the conventions of IEEE 802.3
            		Layer Management, counted exclusively according
            		to the error status presented to the LLC."
	REFERENCE	"IEEE 802.3 Layer Management"
	::= { rcTengDot3StatsEntry 3 }

rcTengDot3StatsSingleCollisionFrames   OBJECT-TYPE
	SYNTAX		Counter64
	MAX-ACCESS  	read-only
	STATUS      	current
	DESCRIPTION	"A count of successfully transmitted frames on
            		a particular interface for which transmission
            		is inhibited by exactly one collision.
            		A frame that is counted by an instance of this
            		object is also counted by the corresponding
            		instance of either the ifOutUcastPkts,
            		ifOutMulticastPkts, or ifOutBroadcastPkts,
            		and is not counted by the corresponding
            		instance of the dot3StatsMultipleCollisionFrames
            		object."
	REFERENCE	"IEEE 802.3 Layer Management"
	::= { rcTengDot3StatsEntry 4 }

rcTengDot3StatsMultipleCollisionFrames   OBJECT-TYPE
	SYNTAX        	Counter64
	MAX-ACCESS   	read-only
	STATUS      	current
	DESCRIPTION	"A count of successfully transmitted frames on
	                a particular interface for which transmission	
			is inhibited by more than one collision.
			A frame that is counted by an instance of this
			object is also counted by the corresponding
			instance of either the ifOutUcastPkts,
			ifOutMulticastPkts, or ifOutBroadcastPkts,
			and is not counted by the corresponding
			instance of the dot3StatsSingleCollisionFrames
			object."
	REFERENCE	"IEEE 802.3 Layer Management"
        ::= { rcTengDot3StatsEntry 5 }

rcTengDot3StatsSQETestErrors   OBJECT-TYPE
        SYNTAX       	Counter64
	MAX-ACCESS   	read-only
        STATUS       	current
        DESCRIPTION 	"A count of times that the SQE TEST ERROR
                        message is generated by the PLS sublayer for a
			particular interface. The SQE TEST ERROR
			message is defined in section 7.2.2.2.4 of
			ANSI/IEEE 802.3-1985 and its generation is
			described in section 7.2.4.6 of the same
			document."
        REFERENCE	"ANSI/IEEE Std 802.3-1985 Carrier Sense
                        Multiple Access with Collision Detection Access
			Method and Physical Layer Specifications"
        ::= { rcTengDot3StatsEntry 6 }

rcTengDot3StatsDeferredTransmissions   OBJECT-TYPE
        SYNTAX      	Counter64
        MAX-ACCESS  	read-only
        STATUS      	current
        DESCRIPTION	"A count of frames for which the first
                        transmission attempt on a particular interface
                        is delayed because the medium is busy.
			The count represented by an instance of this
			object does not include frames involved in
			collisions."
        REFERENCE	"IEEE 802.3 Layer Management"
        ::= { rcTengDot3StatsEntry 7 }

rcTengDot3StatsLateCollisions   OBJECT-TYPE
        SYNTAX      	Counter64
        MAX-ACCESS  	read-only
        STATUS      	current
        DESCRIPTION	"The number of times that a collision is
                        detected on a particular interface later than
			512 bit-times into the transmission of a
			packet.
			Five hundred and twelve bit-times corresponds
			to 51.2 microseconds on a 10 Mbit/s system. A
			(late) collision included in a count
			represented by an instance of this object is
			also considered as a (generic) collision for
			purposes of other collision-related
			statistics."
	REFERENCE	"IEEE 802.3 Layer Management"
        ::= { rcTengDot3StatsEntry 8 }

rcTengDot3StatsExcessiveCollisions   OBJECT-TYPE
        SYNTAX      	Counter64
        MAX-ACCESS  	read-only
	STATUS      	current
        DESCRIPTION	"A count of frames for which transmission on a
                        particular interface fails due to excessive
                        collisions."
        REFERENCE	"IEEE 802.3 Layer Management"
        ::= { rcTengDot3StatsEntry 9 }

rcTengDot3StatsInternalMacTransmitErrors   OBJECT-TYPE
        SYNTAX      	Counter64
	MAX-ACCESS  	read-only
	STATUS      	current
	DESCRIPTION	"A count of frames for which transmission on a
                        particular interface fails due to an internal
			MAC sublayer transmit error. A frame is only
			counted by an instance of this object if it is
			not counted by the corresponding instance of
			either the rcTengDot3StatsLateCollisions object, the
			rcTengDot3StatsExcessiveCollisions object, or the
			rcTengDot3StatsCarrierSenseErrors object.

			The precise meaning of the count represented by
			an instance of this object is implementation-
			specific.  In particular, an instance of this
			object may represent a count of transmission
			errors on a particular interface that are not
			otherwise counted."
	REFERENCE	"IEEE 802.3 Layer Management"
        ::= { rcTengDot3StatsEntry 10 }

rcTengDot3StatsCarrierSenseErrors   OBJECT-TYPE
        SYNTAX  	Counter64
	MAX-ACCESS  	read-only
        STATUS      	current
        DESCRIPTION	"The number of times that the carrier sense
                        condition was lost or never asserted when
			attempting to transmit a frame on a particular
			interface.	

			The count represented by an instance of this
			object is incremented at most once per
			transmission attempt, even if the carrier sense
			condition fluctuates during a transmission
			attempt."
        REFERENCE	"IEEE 802.3 Layer Management"
        ::= { rcTengDot3StatsEntry 11 }

-- { rcTengDot3StatsEntry 12 } is not assigned

rcTengDot3StatsFrameTooLongs   OBJECT-TYPE
        SYNTAX      	Counter64
        MAX-ACCESS  	read-only
        STATUS      	current
     	DESCRIPTION	"A count of frames received on a particular
            		interface that exceed the maximum permitted
            		frame size.

	            	The count represented by an instance of this
            		object is incremented when the frameTooLong
            		status is returned by the MAC service to the
            		LLC (or other MAC user). Received frames for
            		which multiple error conditions obtain are,
            		according to the conventions of IEEE 802.3
            		Layer Management, counted exclusively according
            		to the error status presented to the LLC."
	REFERENCE	"IEEE 802.3 Layer Management"
	::= { rcTengDot3StatsEntry 13 }

-- { rcTengDot3StatsEntry 14 } is not assigned

-- { rcTengDot3StatsEntry 15 } is not assigned

rcTengDot3StatsInternalMacReceiveErrors   OBJECT-TYPE
	SYNTAX      	Counter64
        MAX-ACCESS  	read-only
        STATUS      	current
        DESCRIPTION	"A count of frames for which reception on a
            		particular interface fails due to an internal
            		MAC sublayer receive error. A frame is only
            		counted by an instance of this object if it is
            		not counted by the corresponding instance of
            		either the rcTengDot3StatsFrameTooLongs object, the
            		rcTengDot3StatsAlignmentErrors object, or the
            		rcTengDot3StatsFCSErrors object.

            		The precise meaning of the count represented by
            		an instance of this object is implementation-
            		specific.  In particular, an instance of this
            		object may represent a count of receive errors
            		on a particular interface that are not
            		otherwise counted."
	REFERENCE	"IEEE 802.3 Layer Management"
        ::= { rcTengDot3StatsEntry 16 }

rcTengDot3StatsEtherChipSet   OBJECT-TYPE
	SYNTAX        	OBJECT IDENTIFIER
        MAX-ACCESS    	read-only
        STATUS        	current
       	DESCRIPTION	"This object contains an OBJECT IDENTIFIER
            		which identifies the chipset used to
            		realize the interface. Ethernet-like
            		interfaces are typically built out of
            		several different chips. The MIB implementor
            		is presented with a decision of which chip
            		to identify via this object. The implementor
            		should identify the chip which is usually
            		called the Medium Access Control chip.
            		If no such chip is easily identifiable,
            		the implementor should identify the chip
            		which actually gathers the transmit
            		and receive statistics and error
            		indications. This would allow a
            		manager station to correlate the
            		statistics and the chip generating
            		them, giving it the ability to take
            		into account any known anomalies
            		in the chip."
	::= { rcTengDot3StatsEntry 17 }

rcTengDot3StatsLinkFailures OBJECT-TYPE
        SYNTAX        	Counter32
        MAX-ACCESS    	read-only
        STATUS        	current
        DESCRIPTION   	"The total number of link failures enCounter32ed on
                      	this interface."
        ::= { rcTengDot3StatsEntry 18 }

rcTengDot3StatsPacketErrors OBJECT-TYPE
        SYNTAX        	Counter32
        MAX-ACCESS    	read-only
        STATUS        	current
        DESCRIPTION   	"The total number of packet errors enCounter32ed on
                      	this interface."
        ::= { rcTengDot3StatsEntry 19 }

rcTengDot3StatsCarrierErrors OBJECT-TYPE
        SYNTAX        	Counter32
        MAX-ACCESS    	read-only
        STATUS        	current
        DESCRIPTION   	"The total number of carrier errors enCounter32ed on
                      	this interface."
        ::= { rcTengDot3StatsEntry 20 }

rcTengDot3StatsLinkInactiveErrors OBJECT-TYPE
        SYNTAX        	Counter32
        MAX-ACCESS    	read-only
        STATUS        	current
        DESCRIPTION   	"The total number of link inactive errors enCounter32ed
                       	on this interface."
        ::= {rcTengDot3StatsEntry 21 }

rcTengDot3StatsInFlowCtrlPkts OBJECT-TYPE
        SYNTAX        	Counter64
        MAX-ACCESS    	read-only
        STATUS        	current
        DESCRIPTION   	"The total number of flow control packets received
                       	by this interface."
        ::= { rcTengDot3StatsEntry 22 }

rcTengDot3StatsOutFlowCtrlPkts OBJECT-TYPE
        SYNTAX        	Counter64
        MAX-ACCESS    	read-only
        STATUS        	current
        DESCRIPTION   	"The total number of flow control packets transmitted
                       	by this interface."
        ::= { rcTengDot3StatsEntry 23 }

rcTengDot3StatsFrameTooShorts OBJECT-TYPE
        SYNTAX        	Counter64
        MAX-ACCESS    	read-only
        STATUS        	current
        DESCRIPTION   	"The total number of frames that are too short
                      	that were enCounter32ed on this interface."
        ::= { rcTengDot3StatsEntry 24 }

rcTengDot3StatsInPfcPkts OBJECT-TYPE
        SYNTAX         Counter64
        MAX-ACCESS     read-only
        STATUS         current
        DESCRIPTION   "The total number of Priority Flow Control (PFC)
                       packets received by this interface."
        ::= { rcTengDot3StatsEntry 26 }

rcTengDot3StatsOutPfcPkts OBJECT-TYPE
        SYNTAX         Counter64
        MAX-ACCESS     read-only
        STATUS         current
        DESCRIPTION   "The total number of Priority Flow Control (PFC)
                       packets transmitted by this interface."
        ::= { rcTengDot3StatsEntry 27 }


-- 10Gb ethernet Stat Tbale

rcTengStatTable OBJECT-TYPE
	SYNTAX        	SEQUENCE OF RcTengStatEntry
        MAX-ACCESS    	not-accessible
        STATUS        	current
        DESCRIPTION   "A table used to store port statistics."
        ::= { rcTengEnetStats 2 }

rcTengStatEntry OBJECT-TYPE
        SYNTAX        	RcTengStatEntry
        MAX-ACCESS    	not-accessible
        STATUS        	current
        DESCRIPTION   	"interface Counter32s"
        INDEX         	{ rcTengStatIndex }
        ::= { rcTengStatTable 1 }

RcTengStatEntry ::= SEQUENCE {
        	rcTengStatIndex                 Integer32,
                rcTengStatBridgeInUnicastFrames     Counter32,
                rcTengStatBridgeInMulticastFrames   Counter32,
                rcTengStatBridgeInBroadcastFrames   Counter32,
                rcTengStatBridgeInDiscards          Counter32,
                rcTengStatBridgeOutUnicastFrames    Counter32,
                rcTengStatBridgeOutMulticastFrames  Counter32,
                rcTengStatBridgeOutBroadcastFrames  Counter32,
                rcTengStatRouteInUnicastFrames      Counter32,
                rcTengStatRouteInMulticastFrames    Counter32,
                rcTengStatRouteInDiscards           Counter32,
                rcTengStatRouteOutUnicastFrames     Counter32,
                rcTengStatRouteOutMulticastFrames   Counter32,
                rcTengStatStgForwardTransitions     Counter32,
                rcTengStatStgInConfigBpdus          Counter32,
                rcTengStatStgInTcnBpdus             Counter32,
                rcTengStatStgInBadBpdus             Counter32,
                rcTengStatStgOutConfigBpdus         Counter32,
                rcTengStatStgOutTcnBpdus            Counter32,
                rcTengStatBridgeOutFrames           Counter32
        }

rcTengStatIndex OBJECT-TYPE
        SYNTAX        Integer32 (0..2147483647)
        MAX-ACCESS    	read-only
        STATUS        	current
        DESCRIPTION   	"An index value that uniquely identifies a port.
                      	This value is similar to ifIndex in MIB2."
        ::= { rcTengStatEntry 1 }

rcTengStatBridgeInUnicastFrames OBJECT-TYPE
        SYNTAX        	Counter32
        MAX-ACCESS    	read-only
        STATUS        	current
        DESCRIPTION   	"The total number of incoming unicast frames that
                      	were bridged."
        ::= { rcTengStatEntry 2 }

rcTengStatBridgeInMulticastFrames OBJECT-TYPE
        SYNTAX        	Counter32
        MAX-ACCESS    	read-only
        STATUS        	current
        DESCRIPTION   	"The total number of incoming multicast frames that
                      	were bridged."
        ::= { rcTengStatEntry 3 }

rcTengStatBridgeInBroadcastFrames OBJECT-TYPE
        SYNTAX        	Counter32
        MAX-ACCESS    	read-only
        STATUS        	current
        DESCRIPTION   	"The total number of incoming broadcast frames that
                      	were bridged."
        ::= { rcTengStatEntry 4 }

rcTengStatBridgeInDiscards OBJECT-TYPE
        SYNTAX        	Counter32
        MAX-ACCESS    	read-only
        STATUS        	current
        DESCRIPTION   	"The total number of frames that were discarded by
                      	the bridging entity."
        ::= { rcTengStatEntry 5 }

rcTengStatBridgeOutUnicastFrames OBJECT-TYPE
        SYNTAX        	Counter32
        MAX-ACCESS    	read-only
        STATUS        	current
        DESCRIPTION   	"The total number of outgoing unicast frames that
                      	were bridged."
        ::= { rcTengStatEntry 6 }

rcTengStatBridgeOutMulticastFrames OBJECT-TYPE
        SYNTAX        	Counter32
        MAX-ACCESS    	read-only
        STATUS        	current
        DESCRIPTION   	"The total number of outgoing multicast frames that
                      	were bridged."
        ::= { rcTengStatEntry 7 }

rcTengStatBridgeOutBroadcastFrames OBJECT-TYPE
        SYNTAX        	Counter32
        MAX-ACCESS    	read-only
        STATUS        	current
        DESCRIPTION   	"The total number of outgoing broadcast frames that
                      	were bridged."
        ::= { rcTengStatEntry 8 }

rcTengStatRouteInUnicastFrames OBJECT-TYPE
        SYNTAX        	Counter32
        MAX-ACCESS    	read-only
        STATUS        	current
        DESCRIPTION   	"The total number of incoming unicast frames that
                      	were routed."
        ::= { rcTengStatEntry 9 }

rcTengStatRouteInMulticastFrames OBJECT-TYPE
        SYNTAX        	Counter32
        MAX-ACCESS    	read-only
        STATUS        	current
        DESCRIPTION   	"The total number of incoming multicast frames that
                      	were routed."
        ::= { rcTengStatEntry 10 }

rcTengStatRouteInDiscards OBJECT-TYPE
        SYNTAX        	Counter32
        MAX-ACCESS    	read-only
        STATUS        	current
        DESCRIPTION   	"The total number of frames that were discarded by
                      	the routing entity."
        ::= { rcTengStatEntry 11 }

rcTengStatRouteOutUnicastFrames OBJECT-TYPE
        SYNTAX        	Counter32
        MAX-ACCESS    	read-only
        STATUS        	current
        DESCRIPTION   	"The total number of outgoing unicast frames that
                      	were routed."
        ::= { rcTengStatEntry 12 }

rcTengStatRouteOutMulticastFrames OBJECT-TYPE
        SYNTAX        	Counter32
        MAX-ACCESS    	read-only
        STATUS        	current
        DESCRIPTION   	"The total number of outgoing multicast frames that
                      	were routed."
        ::= { rcTengStatEntry 13 }

rcTengStatStgForwardTransitions OBJECT-TYPE
        SYNTAX        	Counter32
        MAX-ACCESS    	read-only
        STATUS        	current
        DESCRIPTION   	"The number of times this port has transitioned
                      	from the Learning state to the Forwarding state."
        ::= { rcTengStatEntry 14 }

rcTengStatStgInConfigBpdus OBJECT-TYPE
        SYNTAX        	Counter32
        MAX-ACCESS    	read-only
        STATUS        	current
        DESCRIPTION   	""
        ::= { rcTengStatEntry 15 }

rcTengStatStgInTcnBpdus OBJECT-TYPE
        SYNTAX        	Counter32
        MAX-ACCESS    	read-only
        STATUS        	current
        DESCRIPTION   	""
        ::= { rcTengStatEntry 16 }

rcTengStatStgInBadBpdus OBJECT-TYPE
        SYNTAX        	Counter32
        MAX-ACCESS    	read-only
        STATUS        	current
        DESCRIPTION   	""
        ::= { rcTengStatEntry 17 }

rcTengStatStgOutConfigBpdus OBJECT-TYPE
        SYNTAX        	Counter32
        MAX-ACCESS    	read-only
        STATUS        	current
        DESCRIPTION   	""
        ::= { rcTengStatEntry 18 }

rcTengStatStgOutTcnBpdus OBJECT-TYPE
        SYNTAX        	Counter32
        MAX-ACCESS    	read-only
        STATUS        	current
        DESCRIPTION   	""
        ::= { rcTengStatEntry 19 }

rcTengStatBridgeOutFrames OBJECT-TYPE
        SYNTAX        	Counter32
        MAX-ACCESS    	read-only
        STATUS        	current
        DESCRIPTION     "Used by the Accelar 8000 product family to account
                        for all transmitted bridge unicast, broadcast, and
                        multicast packets.  The individual Counter32s are not
                        supported."

        ::= { rcTengStatEntry 20 }

-- From rfc1573rcc.mib
-- the Interfaces table
-- The Interfaces table contains information on the entity's
-- interfaces.  Each sub-layer below the internetwork-layer
-- of a network interface is considered to be an interface.

rcTengIfTable OBJECT-TYPE
       	SYNTAX      	SEQUENCE OF RcTengIfEntry
       	MAX-ACCESS  	not-accessible
       	STATUS      	current
       	DESCRIPTION	"A list of interface entries.  The number of entries
               		is given by the value of engIfNumber."
       ::= { rcTengEnetStats 3 }

rcTengIfEntry OBJECT-TYPE
       	SYNTAX      	RcTengIfEntry
       	MAX-ACCESS  	not-accessible
       	STATUS      	current
       	DESCRIPTION	"An entry containing management information applicable
               		to a particular interface."
       	INDEX   { rcTengIfIndex }
       	::= { rcTengIfTable 1 }

RcTengIfEntry ::= SEQUENCE {
           rcTengIfIndex                InterfaceIndex,
           rcTengIfDescr                DisplayString,
           rcTengIfType                 INTEGER,
           rcTengIfMtu                  Integer32,
           rcTengIfSpeed                Gauge32,
           rcTengIfPhysAddress          PhysAddress,
           rcTengIfAdminStatus          INTEGER,
           rcTengIfOperStatus           INTEGER,
           rcTengIfLastChange           TimeTicks,
           rcTengIfInOctets             Counter64,
           rcTengIfInUcastPkts          Counter64,
           rcTengIfInDiscards           Counter64,
           rcTengIfInErrors             Counter64,
           rcTengIfInUnknownProtos      Counter64,
           rcTengIfOutOctets            Counter64,
           rcTengIfOutUcastPkts         Counter64,
           rcTengIfOutDiscards          Counter64,
           rcTengIfOutErrors            Counter64
       }

rcTengIfIndex OBJECT-TYPE
       	SYNTAX      	InterfaceIndex
       	MAX-ACCESS  	read-only
       	STATUS      	current
       	DESCRIPTION	"A unique value, greater than zero, for each
               		interface.  It is recommended that values are assigned
               		contiguously starting from 1.  The value for each
               		interface sub-layer must remain constant at least from
               		one re-initialization of the entity's network
               		management system to the next re-initialization."
       ::= { rcTengIfEntry 1 }
   
rcTengIfDescr OBJECT-TYPE
       	SYNTAX      	DisplayString (SIZE (0..255))
       	MAX-ACCESS  	read-only
       	STATUS      	current
       	DESCRIPTION	"A textual string containing information about the
               		interface.  This string should include the name of the
               		manufacturer, the product name and the version of the
               		interface hardware/software."
       	::= { rcTengIfEntry 2 }

rcTengIfType OBJECT-TYPE
       	SYNTAX 		INTEGER {
                   	other(1),          -- none of the following
                   	regular1822(2),
                   	hdh1822(3),
                   	ddnX25(4),
                   	rfc877x25(5),
                   	ethernetCsmacd(6),
                   	iso88023Csmacd(7),
                   	iso88024TokenBus(8),
                   	iso88025TokenRing(9),
                   	iso88026Man(10),
                   	starLan(11),
                   	proteon10Mbit(12),
                   	proteon80Mbit(13),
                   	hyperchannel(14),
                   	fddi(15),
                   	lapb(16),
                   	sdlc(17),
                   	ds1(18),           -- DS1/E1 (RFC 1406)
                   	e1(19),            -- obsolete
                   	basicISDN(20),
                   	primaryISDN(21),
                   	propPointToPointSerial(22), -- proprietary serial
                   	ppp(23),
                   	softwareLoopback(24),
                   	eon(25),            -- CLNP over IP (RFC 1070)
                   	ethernet3Mbit(26),
                   	nsip(27),           -- XNS over IP
                   	slip(28),           -- generic SLIP
                   	ultra(29),          -- ULTRA technologies
                   	ds3(30),            -- T-3
                   	sip(31),            -- SMDS
                   	frameRelay(32),    -- DTE only
                   	rs232(33),
                   	para(34),           -- parallel-port
                   	arcnet(35),         -- arcnet
                   	arcnetPlus(36),     -- arcnet plus
                   	atm(37),            -- ATM cells
                   	miox25(38),
                   	sonet(39),          -- SONET or SDH
                   	x25ple(40),
                   	iso88022llc(41),
                   	localTalk(42),
                   	smdsDxi(43),
                   	frameRelayService(44),  -- Frame relay DCE
                   	v35(45),
                   	hssi(46),
                   	hippi(47),
                   	modem(48),          -- Generic modem
                   	aal5(49),           -- AAL5 over ATM
                   	sonetPath(50),
                   	sonetVT(51),
                   	smdsIcip(52),       -- SMDS InterCarrier Interface
                   	propVirtual(53),    -- proprietary virtual/internal
                   	propMultiplexor(54) -- proprietary multiplexing
		}
       	MAX-ACCESS  	read-only
    	STATUS      	current
       	DESCRIPTION	"The type of interface.  Additional values for IfType
               		are assigned by the Internet Assigned Numbers
               		Authority (IANA), through updating the syntax of the
               		IANAifType textual convention."
       	::= { rcTengIfEntry 3 }

rcTengIfMtu OBJECT-TYPE
       	SYNTAX      	Integer32
       	MAX-ACCESS  	read-only
       	STATUS      	current
       	DESCRIPTION	"The size of the largest packet which can be
               		sent/received on the interface, specified in octets.
               		For interfaces that are used for transmitting network
               		datagrams, this is the size of the largest network
               		datagram that can be sent on the interface."
       	::= { rcTengIfEntry 4 }

rcTengIfSpeed OBJECT-TYPE
       	SYNTAX      	Gauge32
       	MAX-ACCESS  	read-only
       	STATUS      	current
       	DESCRIPTION	"An estimate of the interface's current bandwidth in
               		bits per second.  For interfaces which do not vary in
               		bandwidth or for those where no accurate estimation
               		can be made, this object should contain the nominal
               		bandwidth.  If the bandwidth of the interface is
               		greater than the maximum value reportable by this
               		object then this object should report its maximum
               		value (4,294,967,295) and ifHighSpeed must be used to
               		report the interace's speed.  For a sub-layer which
               		has no concept of bandwidth, this object should be
              		zero."
       	::= { rcTengIfEntry 5 }

rcTengIfPhysAddress OBJECT-TYPE
       	SYNTAX      	PhysAddress
       	MAX-ACCESS  	read-only
       	STATUS      	current
       	DESCRIPTION	"The interface's address at its protocol sub-layer.
               		The interface's media-specific MIB must define the bit
               		and byte ordering and format of the value contained by
               		this object.  For interfaces which do not have such an
               		address (e.g., a serial line), this object should
               		contain an octet string of zero length."
       	::= { rcTengIfEntry 6 }

rcTengIfAdminStatus OBJECT-TYPE
       	SYNTAX 	INTEGER {
                	up(1),       -- ready to pass packets
                   	down(2),
                   	testing(3)   -- in some test mode
               	}
       	MAX-ACCESS  	read-write
       	STATUS      	current
       	DESCRIPTION	"The desired state of the interface.  The testing(3)
               		state indicates that no operational packets can be
               		passed.  When a managed system initializes, all
               		interfaces start with IfAdminStatus in the down(2)
               		state.  As a result of either explicit management
               		action or per configuration information retained by
               		the managed system, IfAdminStatus is then changed to
               		either the up(1) or testing(3) states (or remains in
               		the down(2) state)."
       	::= { rcTengIfEntry 7 }

rcTengIfOperStatus OBJECT-TYPE
       	SYNTAX	INTEGER {
                   	up(1),       	-- ready to pass packets
                   	down(2),
                   	testing(3),  	-- in some test mode
                   	unknown(4),  	-- status can not be determined
                                	-- for some reason.
                   	dormant(5)
               	}
       	MAX-ACCESS  	read-only
       	STATUS      	current
       	DESCRIPTION	"The current operational state of the interface.  The
               		testing(3) state indicates that no operational packets
               		can be passed.  If IfAdminStatus is down(2) then
               		IfOperStatus should be down(2).  If IfAdminStatus is
              	 	changed to up(1) then ifOperStatus should change to
               		up(1) if the interface is ready to transmit and
               		receive network traffic; it should change to
               		dormant(5) if the interface is waiting for external
               		actions (such as a serial line waiting for an
               		incomming connection); it should remain in the down(2)
               		state if and only if there is a fault that prevents if
               		from going to the up(1) state."
       	::= { rcTengIfEntry 8 }

rcTengIfLastChange OBJECT-TYPE
       	SYNTAX      	TimeTicks
       	MAX-ACCESS  	read-only
       	STATUS      	current
       	DESCRIPTION	"The value of sysUpTime at the time the interface
               		entered its current operational state.  If the current
               		state was entered prior to the last re-initialization
               		of the local network management subsystem, then this
               		object contains a zero value."
       	::= { rcTengIfEntry 9 }

rcTengIfInOctets OBJECT-TYPE
       	SYNTAX      	Counter64
       	MAX-ACCESS  	read-only
       	STATUS      	current
       	DESCRIPTION	"The total number of octets received on the interface,
               		including framing characters."
       	::= { rcTengIfEntry 10 }

rcTengIfInUcastPkts OBJECT-TYPE
       	SYNTAX      	Counter64
       	MAX-ACCESS  	read-only
       	STATUS      	current
      	DESCRIPTION	"The number of packets, delivered by this sub-layer to
               		a higher (sub-)layer, which were not addressed to a
               		multicast or broadcast address at this sub-layer."
       	::= { rcTengIfEntry 11 }

rcTengIfInDiscards OBJECT-TYPE
       	SYNTAX      	Counter64
       	MAX-ACCESS  	read-only
       	STATUS      	current
       	DESCRIPTION	"The number of inbound packets which were chosen to be
               		discarded even though no errors had been detected to
               		prevent their being deliverable to a higher-layer
               		protocol.  One possible reason for discarding such a
               		packet could be to free up buffer space."
       	::= { rcTengIfEntry 13 }

rcTengIfInErrors OBJECT-TYPE
       	SYNTAX      	Counter64
       	MAX-ACCESS  	read-only
       	STATUS      	current
       	DESCRIPTION	"For packet-oriented interfaces, the number of inbound
               		packets that contained errors preventing them from
               		being deliverable to a higher-layer protocol.  For
               		character-oriented or fixed-length interfaces, the
               		number of inbound transmission units that contained
               		errors preventing them from being deliverable to a
               		higher-layer protocol."
       	::= { rcTengIfEntry 14 }

rcTengIfInUnknownProtos OBJECT-TYPE
       	SYNTAX      	Counter64
       	MAX-ACCESS  	read-only
       	STATUS      	current
       	DESCRIPTION	"For packet-oriented interfaces, the number of packets
               		received via the interface which were discarded
               		because of an unknown or unsupported protocol.  For
               		character-oriented or fixed-length interfaces which
               		support protocol multiplexing the number of
               		transmission units received via the interface which
               		were discarded because of an unknown or unsupported
               		protocol.  For any interface which does not support
               		protocol multiplexing, this counter will always be 0."
       	::= { rcTengIfEntry 15 }

rcTengIfOutOctets OBJECT-TYPE
       	SYNTAX      	Counter64
       	MAX-ACCESS  	read-only
       	STATUS      	current
       	DESCRIPTION	"The total number of octets transmitted out of the
               		interface, including framing characters."
       	::= { rcTengIfEntry 16 }

rcTengIfOutUcastPkts OBJECT-TYPE
       	SYNTAX      	Counter64
       	MAX-ACCESS  	read-only
       	STATUS      	current
       	DESCRIPTION	"The total number of packets that higher-level
               		protocols requested be transmitted, and which were not
               		addressed to a multicast or broadcast address at this
               		sub-layer, including those that were discarded or not
               		sent."
       	::= { rcTengIfEntry 17 }

rcTengIfOutDiscards OBJECT-TYPE
       	SYNTAX      	Counter64
       	MAX-ACCESS  	read-only
       	STATUS      	current
       	DESCRIPTION	"The number of outbound packets which were chosen to
               		be discarded even though no errors had been detected
               		to prevent their being transmitted.  One possible
               		reason for discarding such a packet could be to free
               		up buffer space."
       	::= { rcTengIfEntry 19 }

rcTengIfOutErrors OBJECT-TYPE
       	SYNTAX      	Counter64
       	MAX-ACCESS  	read-only
       	STATUS      	current
       	DESCRIPTION	"For packet-oriented interfaces, the number of
               		outbound packets that could not be transmitted because
               		of errors.  For character-oriented or fixed-length
               		interfaces, the number of outbound transmission units
               		that could not be transmitted because of errors."
       	::= { rcTengIfEntry 20 }


--
--   Extension to the interface table
--
-- This table replaces the ifExtnsTable table.
--

rcTengIfXTable        	OBJECT-TYPE
       	SYNTAX      	SEQUENCE OF RcTengIfXEntry
       	MAX-ACCESS  	not-accessible
       	STATUS      	current
       	DESCRIPTION	"A list of interface entries.  The number of entries
               		is given by the value of ifNumber.  This table
               		contains additional objects for the interface table."
       	::= { rcTengEnetStats 4 }

rcTengIfXEntry        	OBJECT-TYPE
       	SYNTAX      	RcTengIfXEntry
       	MAX-ACCESS  	not-accessible
       	STATUS      	current
       	DESCRIPTION	"An entry containing additional management information
               		applicable to a particular interface."
       	INDEX    { rcTengIfXIndex }
       	::= { rcTengIfXTable 1 }

RcTengIfXEntry ::= SEQUENCE {           
           rcTengIfXIndex                InterfaceIndex,
           rcTengIfName                  DisplayString,
           rcTengIfInMulticastPkts       Counter64,
           rcTengIfInBroadcastPkts       Counter64,
           rcTengIfOutMulticastPkts      Counter64,
           rcTengIfOutBroadcastPkts      Counter64,
           rcTengIfHCInOctets            Counter64,
           rcTengIfHCInUcastPkts         Counter64,
           rcTengIfHCInMulticastPkts     Counter64,
           rcTengIfHCInBroadcastPkts     Counter64,
           rcTengIfHCOutOctets           Counter64,
           rcTengIfHCOutUcastPkts        Counter64,
           rcTengIfHCOutMulticastPkts    Counter64,
           rcTengIfHCOutBroadcastPkts    Counter64,
           rcTengIfLinkUpDownTrapEnable  INTEGER,
           rcTengIfHighSpeed             Gauge32,
           rcTengIfPromiscuousMode       TruthValue,
           rcTengIfConnectorPresent      TruthValue
       	}

rcTengIfXIndex OBJECT-TYPE
       	SYNTAX      	InterfaceIndex
       	MAX-ACCESS  	read-only
       	STATUS      	current
       	DESCRIPTION	"A unique value, greater than zero, for each
               		interface.  It is recommended that values are assigned
               		contiguously starting from 1.  The value for each
               		interface sub-layer must remain constant at least from
               		one re-initialization of the entity's network
               		management system to the next re-initialization."
       ::= { rcTengIfXEntry 1 }
   
rcTengIfName OBJECT-TYPE
       	SYNTAX      	DisplayString
       	MAX-ACCESS  	read-only
       	STATUS      	current
       	DESCRIPTION	"The textual name of the interface.  The value of this
               		object should be the name of the interface as assigned
               		by the local device and should be suitable for use in
               		commands entered at the device's `console'.  This
               		might be a text name, such as `le0' or a simple port
               		number, such as `1', depending on the interface naming
               		syntax of the device.  If several entries in the
               		rcTengIfTable together represent a single interface as 
			named	by the device, then each will have the same 
			value of rcTengIfName.  If there is no local name, or 
			this object is otherwise not applicable, then this 
			object contains a 0-length string."
       	::= { rcTengIfXEntry 2 }

rcTengIfInMulticastPkts OBJECT-TYPE
       	SYNTAX      	Counter64
       	MAX-ACCESS  	read-only
       	STATUS      	current
       	DESCRIPTION	"The number of packets, delivered by this sub-layer to
               		a higher (sub-)layer, which were addressed to a
               		multicast address at this sub-layer.  For a MAC layer
               		protocol, this includes both Group and Functional
               		addresses."
       	::= { rcTengIfXEntry 3 }

rcTengIfInBroadcastPkts OBJECT-TYPE
       	SYNTAX      	Counter64
       	MAX-ACCESS  	read-only
       	STATUS      	current
       	DESCRIPTION	"The number of packets, delivered by this sub-layer to
               		a higher (sub-)layer, which were addressed to a
               		broadcast address at this sub-layer."
       	::= { rcTengIfXEntry 4 }

rcTengIfOutMulticastPkts OBJECT-TYPE
       	SYNTAX      	Counter64
       	MAX-ACCESS  	read-only
       	STATUS      	current
       	DESCRIPTION	"The total number of packets that higher-level
               		protocols requested be transmitted, and which were
               		addressed to a multicast address at this sub-layer,
               		including those that were discarded or not sent.  For
               		a MAC layer protocol, this includes both Group and
               		Functional addresses."
       	::= { rcTengIfXEntry 5 }

rcTengIfOutBroadcastPkts OBJECT-TYPE
       	SYNTAX      	Counter64
       	MAX-ACCESS  	read-only
       	STATUS      	current
       	DESCRIPTION	"The total number of packets that higher-level
               		protocols requested be transmitted, and which were
               		addressed to a broadcast address at this sub-layer,
               		including those that were discarded or not sent."
       	::= { rcTengIfXEntry 6 }

rcTengIfHCInOctets OBJECT-TYPE
       	SYNTAX      	Counter64
       	MAX-ACCESS 	read-only
       	STATUS      	current
       	DESCRIPTION	"The total number of octets received on the interface,
               		including framing characters.  This object is a 64-bit
               		version of rcTengIfInOctets."
       	::= { rcTengIfXEntry 7 }

rcTengIfHCInUcastPkts OBJECT-TYPE
       	SYNTAX      	Counter64
       	MAX-ACCESS  	read-only
       	STATUS      	current
       	DESCRIPTION	"The number of packets, delivered by this sub-layer to
               		a higher (sub-)layer, which were not addressed to a
               		multicast or broadcast address at this sub-layer.
               		This object is a 64-bit version of rcTengIfInUcastPkts."
       	::= { rcTengIfXEntry 8 }

rcTengIfHCInMulticastPkts OBJECT-TYPE
       	SYNTAX      	Counter64
       	MAX-ACCESS  	read-only
       	STATUS      	current
       	DESCRIPTION	"The number of packets, delivered by this sub-layer to
               		a higher (sub-)layer, which were addressed to a
               		multicast address at this sub-layer.  For a MAC layer
               		protocol, this includes both Group and Functional
               		addresses.  This object is a 64-bit version of
               		rcTengIfInMulticastPkts."
       	::= { rcTengIfXEntry 9 }

rcTengIfHCInBroadcastPkts OBJECT-TYPE
       	SYNTAX      	Counter64
       	MAX-ACCESS  	read-only
       	STATUS      	current
       	DESCRIPTION	"The number of packets, delivered by this sub-layer to
               		a higher (sub-)layer, which were addressed to a
               		broadcast address at this sub-layer.  This object is a
               		64-bit version of IfInBroadcastPkts."
       	::= { rcTengIfXEntry 10 }

rcTengIfHCOutOctets OBJECT-TYPE
       	SYNTAX      	Counter64
       	MAX-ACCESS  	read-only
       	STATUS      	current
       	DESCRIPTION	"The total number of octets transmitted out of the
               		interface, including framing characters.  This object
               		is a 64-bit version of rcTengIfOutOctets."
       	::= { rcTengIfXEntry 11 }

rcTengIfHCOutUcastPkts OBJECT-TYPE
       	SYNTAX      	Counter64
       	MAX-ACCESS  	read-only
       	STATUS      	current
       	DESCRIPTION	"The total number of packets that higher-level
               		protocols requested be transmitted, and which were not
               		addressed to a multicast or broadcast address at this
               		sub-layer, including those that were discarded or not
               		sent.  This object is a 64-bit version of
               		rcTengIfOutUcastPkts."
       	::= { rcTengIfXEntry 12 }

rcTengIfHCOutMulticastPkts OBJECT-TYPE
       	SYNTAX      	Counter64
       	MAX-ACCESS  	read-only
       	STATUS      	current
       	DESCRIPTION	"The total number of packets that higher-level
               		protocols requested be transmitted, and which were
               		addressed to a multicast address at this sub-layer,
               		including those that were discarded or not sent.  For
               		a MAC layer protocol, this includes both Group and
               		Functional addresses.  This object is a 64-bit version
               		of rcTengIfOutMulticastPkts."
       	::= { rcTengIfXEntry 13 }

rcTengIfHCOutBroadcastPkts OBJECT-TYPE
       	SYNTAX      	Counter64
       	MAX-ACCESS  	read-only
       	STATUS      	current
       	DESCRIPTION	"The total number of packets that higher-level
               		protocols requested be transmitted, and which were
               		addressed to a broadcast address at this sub-layer,
               		including those that were discarded or not sent.  This
               		object is a 64-bit version of rcTengIfOutBroadcastPkts."
       	::= { rcTengIfXEntry 14 }

rcTengIfLinkUpDownTrapEnable  OBJECT-TYPE
       	SYNTAX      	INTEGER { enabled(1), disabled(2) }
       	MAX-ACCESS  	read-write
       	STATUS      	current
       	DESCRIPTION	"Indicates whether linkUp/linkDown traps should be
               		generated for this interface.
               		By default, this object should have the value
               		enabled(1) for interfaces which do not operate on
               		'top' of any other interface (as defined in the
               		rcTengIfStackTable), and disabled(2) otherwise."
       	::= { rcTengIfXEntry 15 }

rcTengIfHighSpeed OBJECT-TYPE
       	SYNTAX      	Gauge32
       	MAX-ACCESS  	read-only
       	STATUS      	current
       	DESCRIPTION	"An estimate of the interface's current bandwidth in
               		units of 1,000,000 bits per second.  If this object
               		reports a value of `n' then the speed of the interface
               		is somewhere in the range of `n-500,000' to
               		`n+499,999'.  For interfaces which do not vary in
               		bandwidth or for those where no accurate estimation
               		can be made, this object should contain the nominal
               		bandwidth.  For a sub-layer which has no concept of
               		bandwidth, this object should be zero."
       	::= { rcTengIfXEntry 16 }

rcTengIfPromiscuousMode  OBJECT-TYPE
       	SYNTAX      	TruthValue
       	MAX-ACCESS  	read-write
       	STATUS      	current
       	DESCRIPTION	"This object has a value of false(2) If this interface
               		only accepts packets/frames that are addressed to this
               		station.  This object has a value of true(1) when the
               		station accepts all packets/frames transmitted on the
               		media.  The value true(1) is only legal on certain
               		types of media.  If legal, setting this object to a
               		value of true(1) may require the interface to be reset
               		before becoming effective.

               		The value of rcTengIfPromiscuousMode does not affect the
               		reception of broadcast and multicast packets/frames by
               		the interface."
       	::= { rcTengIfXEntry 17 }

rcTengIfConnectorPresent   OBJECT-TYPE
       	SYNTAX      	TruthValue
       	MAX-ACCESS  	read-only
       	STATUS      	current
       	DESCRIPTION	"This object has the value 'true(1)' if the interface
               		sublayer has a physical connector and the value
               		'false(2)' otherwise."
       	::= { rcTengIfXEntry 18 }

-- RecRecord

rcRecReservTable OBJECT-TYPE
     SYNTAX       SEQUENCE OF RcRecReservEntry
     MAX-ACCESS   not-accessible
     STATUS       current
     DESCRIPTION  "This table would display the statistics of several HW
                   record type used.  This will also let the user reserve
                   certain number of records for each type."
     ::= { rcRec 1 }

rcRecReservTablEntry OBJECT-TYPE
        SYNTAX        RcRecReservEntry
        MAX-ACCESS    not-accessible
        STATUS        current
        DESCRIPTION   ""
        INDEX         { rcRecReservRecordType }
        ::= { rcRecReservTable 1 }

RcRecReservEntry ::=
     SEQUENCE {
             rcRecReservRecordType      INTEGER,
             rcRecReservUsed            Integer32,
             rcRecReservReserved        Integer32,
             rcRecReservNewReserved     Integer32,
             rcRecReservDefReserved     Integer32
     }

rcRecReservRecordType OBJECT-TYPE
     SYNTAX         INTEGER  {
                          filter(1),
                          ipmc(2),
                          local(3),
                          mac(4),
                          static(5),
                          vrrp(6)
                      }
     MAX-ACCESS     read-only
     STATUS         current
     DESCRIPTION    "."
     ::= { rcRecReservTablEntry 1 }

rcRecReservUsed OBJECT-TYPE
     SYNTAX         Integer32
     MAX-ACCESS     read-only
     STATUS         current
     DESCRIPTION    "Displayes the number of HW records actually usee
                     by the recordType."
     ::= { rcRecReservTablEntry 2 }

rcRecReservReserved OBJECT-TYPE
     SYNTAX         Integer32
     MAX-ACCESS     read-only
     STATUS         current
     DESCRIPTION    "Displayes the number of HW records reserved for
                     the recordType."
     ::= { rcRecReservTablEntry 3 }

rcRecReservNewReserved OBJECT-TYPE
     SYNTAX         Integer32
     MAX-ACCESS     read-write
     STATUS         current
     DESCRIPTION    "Displayes the number of HW records that w ill
                     be reserved for this recordType after reset if the
                     configuration is saved."
     ::= { rcRecReservTablEntry 4 }

rcRecReservDefReserved OBJECT-TYPE
     SYNTAX         Integer32
     MAX-ACCESS     read-only
     STATUS         current
     DESCRIPTION    "Number of records reserved for this recordType
                     if loaded with factory default."
     ::= { rcRecReservTablEntry 5 }

-- SSH Group
-- SSH Global Information. All requires RWA access.

rcSshGlobal   OBJECT IDENTIFIER        ::= { rcSsh 1 }

rcSshGlobalVersion OBJECT-TYPE
     SYNTAX       INTEGER {
                         v2only(1),
                         both(2)
                      }
     MAX-ACCESS   read-write
     STATUS       current
     DESCRIPTION  "SSH version"
     DEFVAL       { v2only }
     ::= { rcSshGlobal 1 }

rcSshGlobalPort OBJECT-TYPE
     SYNTAX       Integer32
     MAX-ACCESS   read-write
     STATUS       current
     DESCRIPTION  "SSH connection port."
     DEFVAL       { 22 }
     ::= { rcSshGlobal 2 }

rcSshGlobalMaxSession OBJECT-TYPE
     SYNTAX       INTEGER (0..8)
     MAX-ACCESS   read-write
     STATUS       current
     DESCRIPTION  "Number of session allowed."
     DEFVAL       { 4 }
     ::= { rcSshGlobal 3 }

rcSshGlobalTimeout OBJECT-TYPE
     SYNTAX       INTEGER (1..120)
     MAX-ACCESS   read-write
     STATUS       current
     DESCRIPTION  "SSH connection timeout in seconds."
     DEFVAL       { 60 }
     ::= { rcSshGlobal 4 }

rcSshGlobalRsaKeySize OBJECT-TYPE
     SYNTAX       INTEGER (512..1024)
     MAX-ACCESS   read-write
     STATUS       current
     DESCRIPTION  "SSH Rsa key size."
     DEFVAL       { 1024 }
     ::= { rcSshGlobal 5 }

rcSshGlobalDsaKeySize OBJECT-TYPE
     SYNTAX       INTEGER (512..1024)
     MAX-ACCESS   read-write
     STATUS       current
     DESCRIPTION  "SSH Dsa key size."
     DEFVAL       { 1024 }
     ::= { rcSshGlobal 6 }

rcSshGlobalRsaAuth OBJECT-TYPE
     SYNTAX       TruthValue
     MAX-ACCESS   read-write
     STATUS       current
     DESCRIPTION  "Enable/disable SSH RSA authentication"
     DEFVAL       { true }
     ::= { rcSshGlobal 7 }

rcSshGlobalDsaAuth OBJECT-TYPE
     SYNTAX       TruthValue
     MAX-ACCESS   read-write
     STATUS       current
     DESCRIPTION  "Enable/disable SSH DSA authentication"
     DEFVAL       { true }
     ::= { rcSshGlobal 8 }

rcSshGlobalPassAuth OBJECT-TYPE
     SYNTAX       TruthValue
     MAX-ACCESS   read-write
     STATUS       current
     DESCRIPTION  "Enable/disable SSH RSA authentication"
     DEFVAL       { true }
     ::= { rcSshGlobal 9 }

rcSshGlobalKeyAction OBJECT-TYPE
     SYNTAX       INTEGER  {
                         none(0),
                         generateDsa(1),
                         generateRsa(2),
                         deleteDsa(3),
                         deleteRsa(4)
                      }
     MAX-ACCESS   read-write
     STATUS       current
     DESCRIPTION  "SSH key action."
     ::= { rcSshGlobal 10 }

rcSshGlobalEnable OBJECT-TYPE
     SYNTAX       INTEGER {
                         false(0),
                         true(1),
                         secure(2)
                      }
     MAX-ACCESS   read-write
     STATUS       current
     DESCRIPTION  "Enable/disable, or securely enable SSH. Securely enable
                   turns off other daemon flag, and it takes ffect afte reboot"
     DEFVAL       { false }
     ::= { rcSshGlobal 11 }

-- License scheme

rcLicenseNumber OBJECT-TYPE
	SYNTAX	INTEGER {
	bit8600BASE(0),
-- Thunderbolt definitions no longer exist.  This entry (1) is free now
-- 	bitthunderboltBASE(1),
	bitPP8300BASE(2),
	bitdellBASE(3),
	bit8xx4BASE(4),
	bit8xx5BASE(5),
	bit8xx6BASE(6),
	bit8xx7BASE(7),
	bit8xx8BASE(8),
	bit8xx9BASE(9),
	bit8x10BASE(10),
	bit8x11BASE(11),
	bit8x12BASE(12),
	bit8x13BASE(13),
	bit8x14BASE(14),
	bit8x15BASE(15),
	bit8x16BASE(16),
	bit8x17BASE(17),
	bit8x18BASE(18),
	bit8x19BASE(19),
	bit8x20BASE(20),
	bit8x21BASE(21),
	bit8x22BASE(22),
	bit8x23BASE(23),
	bit8x24BASE(24),
	bit8x25BASE(25),
	bit8x26BASE(26),
	bit8x27BASE(27),
	bit8x28BASE(28),
	bit8x29BASE(29),
	bit8x30BASE(30),
	bit8x31BASE(31),
	--	/* Reserve 32 bits for base */

	--	/* Start package license */
	bitpackageStart(32),

	bitBASIC(33),
	bitUNICAST(34),
	bitMULTICAST(35),
	bitTOOL(36),
        bitADVANCED(37),
        bitPREMIER(39),

	bitpackageEnd(255),
	--	/* End package license */

	--	/* Feature bit start from bit 256 */
	--	/* These bits are from xxxConsistencyCheck */
	bitfeature(256),
	bitrc2kCopyFileGrp(257),
	bitrc2kDeviceGlobalTbl(258),
	bitrcCliCustomGrp(259),
	bitrcCliGrp(260),
	bitrcCliGrpWsm(261),
	bitrcDiagMacConvSteeringTbl(262),
	bitrcDiagMirrorByPortTbl(263),
	bitrcDiagPortConvSteeringTbl(264),
	bitrcSysAccPolicyTbl(265),
	bitrcSysGrp(266),
	bitrcSysTrapTbl(267),
	bitrcUserSetTimeGrp(268),
	bitrcPortLock(269),
	bitrcSyslogGlobalGrp(270),
	bitrcSyslogHostTbl(271),
	bitrcWebGrp(272),
	bitdot1dStaticEntry(273),
	bitsnmpCommunityTbl(274),
	bitrcLoadModule(275),
	bitrcMltGrp(276),
	bitrcMltTbl(277),
	bitsmltMacTblSend(278),
	bitrc2kQosEgressQosToDscpTbl(279),
	bitrc2kQosEgressQosToTagTbl(280),
	bitrc2kQosIngressDscpToQosTbl(281),
	bitrc2kQosIngressTagToQosTbl(282),
	bitrc2kQosQosTbl(283),
	bitrcBridgeAutoLearnTbl(284),
	bitrcBridgeManualEditTbl(285),
	bitrcBridgeUnknownMacDiscardTbl(286),
	bitrcBridgeStaticMulticastTbl(287),
	bitrcSvlanGlobalGrp(288),
	bitrcSvlanTbl(289),
	bitrcVlanMacTbl(290),
	bitrcVlanPortTbl(291),
	bitrcVlanTbl(292),
	bitvlanTbl(293),
	bitrc2kBootConfigTbl(294),
	bitrc2kCpuEthernetPortRouteTbl(295),
	bitrc2kCpuEthernetPortTbl(296),
	bitrc2kCpuSerialPortTbl(297),
	bitrc2kCardTbl(298),
	bitrc2kMdaCardTbl(299),
	bitrcChassisGrp(300),
	bitrcL2RedundancyGrp(301),
	bitrcRecReservTbl(302),
	bitrcTftpGrp(303),
	bitrcFdbTbl(304),
	bitrcFilterTbl(305),
	bitrcStaticTbl(306),
	bitmgMirror(307),
	bitifTbl(308),
	bitifTestTbl(309),
	bitrcChassisPort(310),
	bitrcRateLimitTbl(311),
	bitrcTengIfTbl(312),
	bitrcLinkFlapDetectGrp(313),
	bitifTblMlt(314),
	bitposIfTbl(315),
	bitpppBridgeConfigTbl(316),
	bitpppIpConfigTbl(317),
	bitpppLinkConfigTbl(318),
	bitpppLqrConfigTbl(319),
	bitrcPosLineConfigTbl(320),
	bitrcPosPppIpxTbl(321),
	bitrcPosSioCardConfigTbl(322),
	bitrcPosSonetTbl(323),
	bitatm1483ElanTbl(324),
	bitatmPortTbl(325),
	bitatmPvcTbl(326),
	bitrc2kAtm1483ElanTbl(327),
	bitrc2kAtmPortTbl(328),
	bitrc2kAtmPvcTbl(329),
	bitrc2kAtmSioCardConfigTbl(330),
	bitbrdgStp(331),
	bitbrdgStpPortTbl(332),
	bitrcStg(333),
	bitrcStgPortTbl(334),
	bitrcStgTbl(335),
	bitigmpInterfaceTbl(336),
	bitrcIgmpAccessTbl(337),
	bitrcIgmpInterfaceExtnTbl(338),
	bitrcIgmpSenderTbl(339),
	bitrcIgmpStaticTbl(340),
	bitipfFilterModifyDs(341),
	bitrc2kQosTrafficProfileTbl(342),
	bitrcIpFilterBaseListTbl(343),
	bitrcIpFilterGlobalListTbl(344),
	bitrcIpFilterMediaDevTbl(345),
	bitrcIpFilterMediaStreamTbl(346),
	bitrcIpFilterPortTbl(347),
	bitrcIpFilterTbl(348),
	bitrcIpMulticastSoftwareForwardingGrp(349),
	bitrcIpMulticastTimedPruneTbl(350),
	bitrcMltMcastDistributionGrp(351),
	bitipMRouteInterfaceTbl(352),
	bitdvmrpInterfaceTbl(353),
	bitpimCandidateRPTbl(354),
	bitpimGrp(355),
	bitpimInterfaceTbl(356),
	bitrcNtpGlobalGrp(357),
	bitrcNtpKeyTbl(358),
	bitrcNtpServerTbl(359),
	bitospfAreaAggregateTbl(360),
	bitospfAreaTbl(361),
	bitospfGeneralGrp(362),
	bitospfHostTbl(363),
	bitospfIfMetricTbl(364),
	bitospfIfTbl(365),
	bitospfNbrTbl(366),
	bitospfStubAreaTbl(367),
	bitospfVirtIfTbl(368),
	bitwfPgmGrp(369),
	bitwfPgmIfTbl(370),
	bitwfPgmSessionTbl(371),
	bitrcRadiusGlobalGrp(372),
	bitrcRadiusServerTbl(373),
	bitrcIpFlowTbl(374),
	bitrcIpConfDhcpTbl(375),
	bitrcIpDhcpForwardTbl(376),
	bitrcIpConfDvmrpTbl(377),
	bitrcIpDvmrpGrp(378),
	bitrcArpExtTbl(379),
	bitrcIpAddrTbl(380),
	bitrcIpConfGlobalGrp(381),
	bitrcIpConfIcmpRdiscTbl(382),
	bitrcIpConfTbl(383),
	bitrcIpMulticastArpTbl(384),
	bitrcIpRoutePrefTbl(385),
	bitrcRipExtTbl(386),
	bitrcIpConfOspfAreaAggregateTbl(387),
	bitrcIpConfOspfAreaTbl(388),
	bitrcIpConfOspfTbl(389),
	bitrcIpPimGlobalGrp(390),
	bitrcIpPimStaticRPTbl(391),
	bitrcIpPimTbl(392),
	bitrcIpRipInterfaceTbl(393),
	bitrcIpRouteTbl(394),
	bitrcIpStaticRouteTbl(395),
	bittcpConnTbl(396),
	bitrcIpUdpConfBroadcastIntfTbl(397),
	bitrcIpUdpPortFwdListTbl(398),
	bitrcIpUdpPortFwdTbl(399),
	bitrcIpUdpProtocolTbl(400),
	bitvrrpAssoIpAddrTbl(401),
	bitvrrpOperTbl(402),
	bitvrrpOperationsGrp(403),
	bitvrrpRouterStatsTbl(404),
	bitrcIpxAddrTbl(405),
	bitrcIpxBrouterTbl(406),
	bitrcIpxGrp(407),
	bitrcIpxPolicyListTbl(408),
	bitrcIpxPolicyNetTbl(409),
	bitrcIpxPolicyServTbl(410),
	bitrcIpxRipInFilterTbl(411),
	bitrcIpxRipInterfaceTbl(412),
	bitrcIpxRipOutFilterTbl(413),
	bitrcIpxSapInFilterTbl(414),
	bitrcIpxSapInterfaceTbl(415),
	bitrcIpxSapOutFilterTbl(416),
	bitvlanEncap(417),
	bitrcIpAsPathAccessListTbl(418),
	bitrcIpCommunityAccessListTbl(419),
	bitrcIpGenPolicyGrp(420),
	bitrcIpOspfInFilterTbl(421),
	bitrcIpPrefixListTbl(422),
	bitrcIpRedistributeTbl(423),
	bitrcIpRoutePolicyStrEnt(424),
	bitrcIpRoutePolicyTbl(425),
	bits5EnMsTopInfoGrp(426),
	bitbgpPeerTbl(427),
	bitrcIpBgpAggregateTbl(428),
	bitrcIpBgpConfederationGrp(429),
	bitrcIpBgpGeneralGrp(430),
	bitrcIpBgpNetworkTbl(431),
	bitrcIpBgpPeerGroupTbl(432),
	bitrcIpBgpPeerTbl(433),
	bitrcIpBgpRouteReflectorGrp(434),
	bitrcStatBgpGrp(435),
	bitrcStatBgpPeerTbl(436),
	bitrcSshGlobalGrp(437),
	bitrcDiagPcapAdvancedFilterTbl(438),
	bitrcDiagPcapFilterTbl(439),
	bitrcDiagPcapGrp(440),
	bitrcPortPcapTbl(441),
	bitrcArpExtEntDoProxy(442),
	bitrcIpConfGlobalRouteDiscovery(443),
	bitSuperNetEnable(444),
	bitospfCli(445),

	-- start: import from Yiyu's CLI changes 
	bitTreeCli(446),
	bitShowCmdCli(447),
	bitInfoCmdCli(448),
	bitrcIgmpChannelLimitTbl(449),
	bitrcIgmpSsmTbl(450),
	bitrcIgmpSsmGlobalGrp(451),
	bitrcIgmpIgapGlobalGrp(452),
	bitrcIgmpGlobalParamsGrp(453),
	bitrcRadiusGlobalSnmpGrp(454),
	bitrcSltPortTbl(455),
	bitrcErrorGrp(456),
	bitrcIgmpIgapServiceAbilityTbl(457),
	bitrcVlanDsapSsapTbl(458),
	bitrcIpArpCliClearPortCli(459),
	bitrcIpArpCliClearVlanCli(460),
	bitrcIpArpCliAddCli(461),
	bitrcIpArpCliDeleteCli(462),
	bitrcIpMulticastMacFloodingCliEnableCli(463),
	bitcliMacFlapTimeLimitSetCli(464),
	bitcliWriteRtcCli(465),
	bitipfCliClearStatsCli(466),
	bitipxCliDisableGnsCli(467),
	bitipxCliDisableRipCli(468),
	bitipxCliDisableRouteCli(469),
	bitipxCliDisableSapCli(470),
	bitipxCliRipSetDefDelayTimerCli(471),
	bitipxCliRipSetHoldMultiplierCli(472),
	bitipxCliRipSetDefIntervalTimerCli(473),
	bitipxCliEnableGnsCli(474),
	bitipxCliEnableRipCli(475),
	bitipxCliEnableSapCli(476),
	bitipxCliDisableRoute(477),
	bitipxCliEnableRouteCli(478),
	bitipxCliRipStateCli(479),
	bitipxCliRipSetDelayTimerCli(480),
	bitipxCliRipSetIntervalTimerCli(481),
	bitipxCliSapAddStaticEntryCli(482),
	bitipxCliSapDeleteStaticEntryCli(483),
	bitipxCliSapSetDefDelayTimerCli(484),
	bitipxCliSapSetDefHoldMultiplierCli(485),
	bitipxCliSapSetDefIntervalTimerCli(486),
	bitipxCliSapSetHoldMultiplierCli(487),
	bitipxCliSapSetGnsTieBreakerCli(488),
	bitipxCliSapStateCli(489),
	bitipxCliSapSetDelayTimerCli(490),
	bitipxCliSapSetIntervalTimerCli(491),
	bitipxCliAddRouteEntryCli(492),
	bitipxCliDeleteRouteEntryCli(493),
	bitipxCliSetMaxRouteCli(494),
	bitipxCliSetMaxSapCli(495),
	bitipxCliSetMaxStaticRouteCli(496),
	bitipxCliSetMaxStaticSapCli(497),
	bitipxCliSetNetBiosEnableDisableCli(498),
	bitipxCliSetLearnAfterIncrementEnableDisableCli(499),
	bitcliPasswordROCli(500),
	bitcliPasswordRWL1Cli(501),
	bitcliPasswordRWL2Cli(502),
	bitcliPasswordRWL3Cli(503),
	bitcliPasswordRWCli(504),
	bitcliPasswordRWACli(505),
	bitcliPasswordSLBOPERCli(506),
	bitcliPasswordL4OPERCli(507),
	bitcliPasswordOPERCli(508),
	bitcliPasswordSLBADMINCli(509),
	bitcliPasswordL4ADMINCli(510),
	bitcliPasswordSSLADMINCli(511),
	bitcliMonitorDurationCli(512),
	bitcliMonitorIntervalCli(513),
	bitcliDefaultBannerCli(514),
	bitcliDisplayMotdCli(515),
	bitcliDefaultLoginCli(516),
	bitcliDefaultPasswordCli(517),
	bitcliMoreCli(518),
	bitcliRloginLimitCli(519),
	bitcliScrsizeCli(520),
	bitcliTelnetLimitCli(521),
	bitcliTimeoutCli(522),
	bitlogCliHostCreateCli(523),
	bitlogCliSetTransferFileNameCli(524),
	bitlogCliHostDeleteCli(525),
	bitlogcliLevelCli(526),
	bitlogcliScreenCli(527),
	bitlogCliMsgOnPcmciaCli(528),
	bitcliAddTraceModuleCli(529),
	bitsetAutoTraceStatusCli(530),
	bitsetAutoTraceHighTrackDurationCli(531),
	bitsetAutoTraceLowPercentageCli(532),
	bitsetAutoTraceLowTrackDurationCli(533),
	bitcliRemTraceModuleCli(534),
	bitrcIpxCliPolicyTraceRipOutFilterAddCli(535),
	bitrcIpxCliPolicyTraceRipOutFilterDeleteCli(536),
	bitrcIpxCliPolicyTraceRipInFilterAddCli(537),
	bitrcIpxCliPolicyTraceRipInFilterDeleteCli(538),
	bitrcIpxCliPolicyTraceSapOutFilterAddCli(539),
	bitrcIpxCliPolicyTraceSapOutFilterDelete(540),
	bitrcIpxCliPolicyTraceSapInFilterAddCli(541),
	bitrcIpxCliPolicyTraceSapInFilterDeleteCli(542),
	bittracecliClearCli(543),
	bittracecliLevelCli(544),
	bittracecliOffCli(545),
	bittracecliFilterCli(546),
	bittracecliGrepStringCli(547),
	bittraceCliPolicyCli(548),
	bitdebugcliSlotXCli(549),
	bitripCliSetDefImportMetCli(550),
	bitripCliDisableCli(551),
	bitripCliDomainCli(552),
	bitripCliEnableCli(553),
	bitripCliSetIfDomainCli(554),
	bitripCliSetIfRxModeCli(555),
	bitripCliSetIfTxModeCli(556),
	bitripCliSetHoldDownCli(557),
	bitripCliReceiveCli(558),
	bitripCliSendCli(559),
	bitsysCliSetRmonAlarmCreateCli(560),
	bitsysCliSetRmonAlarmDeleteCli(561),
	bitsysCliSetRmonEventCreateCli(562),
	bitsysCliSetRmonEventDeleteCli(563),
	bitsysCliSetRmonHistoryCreateCli(564),
	bitsysCliSetRmonHistoryDeleteCli(565),
	bitsysCliSetRmonEtherCreateCli(566),
	bitsysCliSetRmonEtherDeleteCli(567),
	bitsysCliSetRmonEtherOwnerCli(568),
	bitcliStartAtmConsoleCli(569),
	bitrebootcliCli(570),
	bittoptreeCli(571),
	bitconvert11configCli(572),
	bitcopyimageCli(573),
	bitcwccliCli(574),
	bitshowdateCli(575),
	bitdirectoryCli(576),
	bitshowDumpAsicAddrCli(577),
	bitshowHwDumpAllCli(578),
	bitshowIcmpStatCli(579),
	bitshowInetStatCli(580),
	bitshowInspectCli(581),
	bitcliinstallCli(582),
	bitreloginCli(583),
	bitshowopDumpErrorRegsCli(584),
	bitshowOspfDumpAllCli(585),
	bitshowOspfDumpSpfInfoCli(586),
	bitpeercliCli(587),
	bitpingcliCli(588),
	bitipxCliPingCli(589),
	bitpwccliCli(590),
	bitshowrarDumpRegsCli(591),
	bitshowRarCheckStatsCli(592),
	bitshowRarErrorCountCli(593),
	bitshowrcDumpIfIndexCli(594),
	bitdeleteimageCli(595),
	bitresetcliCli(596),
	bitrlogincliCli(597),
	bitrshcliCli(598),
	bitsavecliCli(599),
	bitVxshellCli(600),
	bitclisourceCli(601),
	bitshowSpyReportCli(602),
	bitshowSwipDumpCli(603),
	bittelnetcliCli(604),
	bittracerouteCli(605),
	bitshowTaskTraceCli(606),
	bitrcIpRouteCliClearPortCli(607),
	bitrcIpRouteCliClearVlanCli(608),
	bitdumpcliArCli(609),
	bitmltCliClearIstStatsCli(610),
	bitportCliClearStatsCli(611),
	bitcliResetConsoleShellCli(612),
	bitcliKillTelnetSessionCli(613),
	bitatmCliClearVPortStatsCli(614),
	bitatmCliClearF5StatsCli(615),
	bitatmCliClearPortStatsCli(616),
	bitatmCliCardResetCli(617),
	bitatmCliEnableVPortStatsCli(618),
	bitatmCliSetDebugCli(619),
	bitatmCliVPortStatsIntervalCli(620),
	bitatmCliLaneCreateCli(621),
	bitatmCliLaneDeleteCli(622),
	bitatmCliStateCli(623),
	bitigmpOldCliDelAccessListCli(624),
	bitigmpOldCliSetAccessModeCli(625),
	bitposCliCardResetCli(626),
	bitposCliSetDebugCli(627),
	bitposCliSetPosConsoleCli(628),
	bitportCliSetLinktrapCli(629),
	bitportCliFlushIgmpCli(630),
	bitsysCliAccessEnableCli(631),
	bitvlanCliIeeeDiscardRecordAgingCli(632),
	bitvlanCliIeeeAgingDisableCli(633),
	bitvlanCliIeeeAgingEnableCli(634),
	bitsysCliSetSnmpForceTrapSenderCli(635),
	bitsysResetWebPasswdCli(636),
	bitsysResetSnmpCommStringsCli(637),
	bitsysCliSetMgmtVirtualIpCli(638),
	bitsysCliSetContactCli(639),
	bitsysCliSetHighPerformanceCli(640),
	bitsysCliSetLocationCli(641),
	bitsysCliSetMessageControlCli(642),
	bitsysCliSetChassisMTUCli(643),
	bitcliPromptCli(644),
	bitsysCliSetOctapidResetThresholdCli(645),
	bitsysCliSetSmltPortUnlockTimeoutCli(646),
	bitsysCliSetUdpSourceCli(647),
	bitvlanCliFlushIeeeVlanDiscardRecordsCli(648),
	bitposCliSetLEDCli(649),
	bitvlanCliRipManualTrigCli(650),
	bitvlanCliChangeIpxEncapCli(651),
	bitvlanCliSetFdbTimeOutCli(652),
	bitvlanCliSyncFdbCli(653),
	bitportCliRipManualTrigCli(654),
	bitportCliSetCpLimitCli(655),
	bitportCliSetClockSourceCli(656),
	bitportCliSetFlowControlCli(657),
	bitportCliSetFlowControlPause0Cli(658),
	bitportCliSetFlowControlPauseTimeCli(659),
	bitportCliSetSffdCli(660),
	bitsetMgmtIpCli(661),
	bitsetWsmAutoResetCli(662),
	bitreadWSMCommunityCli(663),
	bitwriteWSMCommunityCli(664),
	bittrapWSMCommunityCli(665),
	bitauthTrapWSMCli(666),
	bitlinkTrapWSMCli(667),
	bittelnetWsmCli(668),
	bitsyslogFacilityCli(669),
	bitwsmResetCli(670),
	bitwsmSaveCli(671),
	bitwsmBootChoiceCli(672),
	bitwsmDumpCardDBCli(673),
	bitwsmDumpIPTableCli(674),
	bitwsmDumpTableCli(675),
	bithiddenModeCli(676),
	bitresetSamCli(677),
	bitsamBootBackupCli(678),
	bitsamShowClusterCli(679),
	bitoldieCli(680),
	bitipCliSetBgpRedistApplyCli(681),
	bitrcBgpPeerCli(682),
	bitCliConfigIpBgpMaxInitPeersCli(683),
	bitCliConfigIpBgpMaxTxQueueLenCli(684),
	bitCliConfigIpBgpDebugScreenCli(685),
	bitpolicySetOspfAcceptPrecedenceCli(686),
	bitpolicySetOspfAnnouncePrecedenceCli(687),
	bitpolicySetRipAcceptPrecedenceCli(688),
	bitpolicySetRipAcceptRipIfListCli(689),
	bitpolicySetRipAnnounceOutIfListCli(690),
	bitpolicySetRipAnnouncePrecedenceCli(691),
	bitpolicyRipAnnounceRemoveFromRtSrcCli(692),
	bitospfCliModRangeEffectCli(693),
	bitospfCliModRangeMetricCli(694),
	bitospfCliSetVirtIfMd5KeyTxCli(695),
	bitospfCliSetIfMd5KeyCli(696),
	bitospfCliSetMd5KeyTxCli(697),
	bitospfCliDelIfMd5KeyCli(698),
	bitipCliSetOspfAcceptApplyCli(699),
	bitospfCliSetDefMetricGrpCli(700),
	bitospfCliSetSpfHoldDownTimeCli(701),
	bitospfCliSetSpfRunCli(702),
	bitospfCliSetTrapCli(703),
	bitrcIpVrrpCliClearPortCli(704),
	bitrcIpVrrpCliClearVlanCli(705),
	bitrcIpResourceUsageGlobalGrp(706),
	bitrcIpPimInterfaceTbl(707),
	bitipmcCliSetDvmGlobDisCli(708),
	bitipmcCliSetDvmGlobEnlCli(709),
	bitipmcCliSetDvmGlobLeafTimeoutCli(710),
	bitipmcCliSetDvmGlobNbrTimeoutCli(711),
	bitipmcCliSetDvmGlobNbrProbeIntCli(712),
	bitipmcCliSetDvmGlobTrigUpdateIntervalCli(713),
	bitipmcCliSetDvmGlobUpdateIntervalCli(714),
	bitipmcCliSetDvmGlobFwdCacheTimeoutCli(715),
	bitipmcCliSetDvmGlobRouteExpireTimeoutCli(716),
	bitipmcCliSetDvmGlobRouteDiscTimeoutCli(717),
	bitipmcCliSetDvmGlobRouteSwitchTimeoutCli(718),
	bitipmcCliSetDvmGlobShowNextHopTableCli(719),
	bitipCliSetPimdebugAssertCli(720),
	bitipCliSetPimdebugBootstrapCli(721),
	bitipCliSetPimdebugGroupCli(722),
	bitipCliSetPimdebugHelloCli(723),
	bitipCliSetPimdebugJoinpruneCli(724),
	bitipCliSetPimDbgTraceCli(725),
	bitipCliSetPimDbgLogCli(726),
	bitipCliSetPimdebugRegisterCli(727),
	bitipCliSetPimdebugRegStopCli(728),
	bitipCliSetPimdebugRpadvCli(729),
	bitipCliSetPimdebugSendCli(730),
	bitipCliSetPimdebugRcvCli(731),
	bitipClienabletraceforSGentryCli(732),
	bitipClidisabletraceforSGentryCli(733),
	bitipCliSetPimGlobBrDisCli(734),
	bitipCliSetPimGlobBrEnlCli(735),
	bitportCliSetPimIfCreateCli(736),
	bitportCliSetPimIfTypeCli(737),
	bitdiagCliPingSnoopAddPortsCli(738),
	bitdiagCliPingSnoopCreateCli(739),
	bitdiagCliPingSnoopDeleteCli(740),
	bitdiagCliPingSnoopEnaDisCli(741),
	bitdiagCliPingSnoopRemPortsCli(742),
	bitrcIpBgpPeerCli(743),
	bitospfCliSetVirtIfMd5KeyCli(744),
	bitospfCliDelVirtIfMd5KeyCli(745),
	bitipSetOspfRedistApplyCli(746),
	bitospfSetAutoVlinkCli(747),
	bitospfSetTrapCli(748),
	bitipSetPimdebugSourceCli(749),
	bitportCliSetLoopDetectCli(750),
	bitlogcliClearCli(751),
	bitlogcliWriteCli(752),
	bitsetAutoTraceHighPercentageCli(753),
	bittracecliScreenCli(754),
	bitripCliCliSetIfRxModeCli(755),
	bitripSetIfTxModeCli(756),
	bitripUpdateCli(757),
	bitsysCliSetSendTrapConfigCli(758),
	bitclilsCli(759),
	bitclimkdirCli(760),
	bittelnetSamCli(761),
	bitsysCliV3UserSetCli(762),
	bitsysCliV3GrpSetCli(763),
	bitsysCliV3AccessSetCli(764),
	bitsysCliV3NotifySetCli(765),
	bitsysCliV3ViewSetCli(766),
	bitsysCliV3TargetSetCli(767),
	bitsysCliV3TargetParamsSetCli(768),
	bitsnmpCliViewSetCli(769),
	bitBcli8100Cli(770),
	bitBcliAgentHacpuCli(771),
	bitBcliAttribCli(772),
	bitBcliAutobootCli(773),
	bitBcliAutonegotiateCli(774),
	bitBcliBaudCli(775),
	bitBcliBootCli(776),
	bitBcliBootpCli(777),
	bitBcliCdCli(778),
	bitBcliCfgfileCli(779),
	bitBcliCopyCli(780),
	bitBcliCpCli(781),
	bitBcliCwcCli(782),
	bitBcliDatabitsCli(783),
	bitBcliDcdebugCli(784),
	bitBcliDebugcfgCli(785),
	bitBcliDebugmodeCli(786),
	bitBcliDelayCli(787),
	bitBcliWlandesiredssidCli(788),
	bitBcliDirCli(789),
	bitBcliDosChkdskCli(790),
	bitBcliDosFormatCli(791),
	bitBcliDstCli(792),
	bitBcliDstendCli(793),
	bitBcliDstnameCli(794),
	bitBcliDstoffCli(795),
	bitBcliDststartCli(796),
	bitBcliDumpspromCli(797),
	bitBcliEditCli(798),
	bitBcliEgressloopCli(799),
	bitBcliFactorydefaultsCli(800),
	bitBcliFmmdebugCli(801),
	bitBcliFmmFormatCli(802),
	bitBcliFtpdCli(803),
	bitBcliFtpdebugCli(804),
	bitBcliFullduplexCli(805),
	bitBcliGrepCli(806),
	bitBcliHacpuCli(807),
	bitBcliI2cdebugCli(808),
	bitBcliImagefileCli(809),
	bitBcliLsCli(810),
	bitBcliMasterCli(811),
	bitBcliMcpCli(812),
	bitBcliMfgburninCli(813),
	bitBcliMfgdCli(814),
	bitBcliMfgledCli(815),
	bitBcliMfgmCli(816),
	bitBcliMgmtrouteCli(817),
	bitBcliMkdirCli(818),
	bitBcliMnetipCli(819),
	bitBcliMoreCli(820),
	bitBcliMoreflagCli(821),
	bitBcliMulticastCli(822),
	bitBcliMvCli(823),
	bitBcliNetenableCli(824),
	bitBcliNetipCli(825),
	bitBcliNetrestartCli(826),
	bitBcliNetspeedCli(827),
	bitBcliPcdebugCli(828),
	bitBcliPclogCli(829),
	bitBcliPctraceCli(830),
	bitBcliPeerCli(831),
	bitBcliPingCli(832),
	bitBcliProgrambootCli(833),
	bitBcliPromptCli(834),
	bitBcliPwcCli(835),
	bitBcliPwdCli(836),
	bitBcliRarudipsvCli(837),
	bitBcliRarudrecCli(838),
	bitBcliReadspromCli(839),
	bitBcliRebootonerrorCli(840),
	bitBcliResetCli(841),
	bitBcliResetPasswordCli(842),
	bitBcliRloginCli(843),
	bitBcliRlogindCli(844),
	bitBcliRloginlimitCli(845),
	bitBcliRmCli(846),
	bitBcliRshCli(847),
	bitBcliSaveCli(848),
	bitBcliSavetostandbyCli(849),
	bitBcliScrsizeCli(850),
-- 851 is a duplicate and should not be used
	bitBcliSetbootpimagenameCli(851),
	bitBcliSioenableCli(852),
	bitBcliSiomodeCli(853),
	bitBcliSiomtuCli(854),
	bitBcliSiomyipCli(855),
	bitBcliSiopeeripCli(856),
	bitBcliSiopppfileCli(857),
	bitBcliSiorestartCli(858),
	bitBcliSioslipcomCli(859),
	bitBcliSiosliprxcomCli(860),
	bitBcliSnmpdCli(861),
	bitBcliSourceCli(862),
	bitBcliSshdCli(863),
	bitBcliTelnetCli(864),
	bitBcliTelnetdCli(865),
	bitBcliTelnetlimitCli(866),
	bitBcliTestCli(867),
	bitBcliTestspromCli(868),
	bitBcliTftpdCli(869),
	bitBcliTftpdebugCli(870),
	bitBcliTftphashCli(871),
	bitBcliTftphostCli(872),
	bitBcliTftprexmitCli(873),
	bitBcliTftptimeoutCli(874),
	bitBcliTimeoutCli(875),
	bitBcliTupleCli(876),
	bitBcliTzCli(877),
	bitBcliTzoffCli(878),
	bitBcliUpdatebootCli(879),
	bitBcliVerifycfgCli(880),
	bitBcliVxataCli(881),
	bitBcliVxdcCli(882),
	bitBcliVxdosCli(883),
	bitBcliVxinetCli(884),
	bitBcliVxiosCli(885),
	bitBcliVxmemCli(886),
	bitBcliVxpasswordCli(887),
	bitBcliVxpppCli(888),
	bitBcliVxtiCli(889),
	bitBcliVxuserCli(890),
	bitBcliWdtCli(891),
	bitBcliWlanCli(892),
	bitBcliWlanconfigureCli(893),
	bitBcliWriteRtcCli(894),
	bitBcliWritespromCli(895),
-- 896 is a duplicate and should not be used
	bitBootPCliSetImageNameCli(896),
	bitBootPCliSettingCli(897),
	bitExitTreeCli(898),
	bitMacUpgradeCli(899),
	bitPcmciaStopCli(900),
	bitBcliPrivilegeCli(901),
	bitBcliReadRtcCli(902),
	bitShowHelpCli(903),
	bitShowHistoryCli(904),
	bitOpTreeCli(905),
	bitUpOneTreeCli(906),
	bitBcliHiSecureFlagCli(907),
	bitBoxCli(908),
	bitBcliBlockSwitchOverCli(909),
	bitBcliCtrlRecOptimizeCli(910),
	bitBcliLogParmsCli(911),
	bitPasswordAgeCli(912),
	bitLicenseLoadCli(913),
	bitportCliUnknownMacDiscAddAllowMacCli(914),
-- 915 is a duplicate and should not be used
	bitBootpCliSetImageNameCli(915),
	bitdot3adAggTbl(916),
	bitdot3adAggPortTbl(917),
	bitrcLacpGlobalGrp(918),
	bitrcPortLacpTbl(919),
	bitrcPortVLacpTbl(920),
	bitdot1xPaeSystemGrp(921),
	bitdot1xAuthConfigTbl(922),
	bitdot1xPaePortTbl(923),
	bitdot3adrcPortLacpTbl(924),
	bitrcPortRemoteMirroringTbl(925),
	bitrcIpRsmltCli(926),
	bitsysCliV3NotifyFilterSetCli(927),
	bitsysCliV3NotifyProfileSetCli(928),
	bitsysCliSetSnmpServerCli(929),
        bitrcIpConfRsmltTbl(930),
        bitrcIpxRsmltOperTbl(931),
        bitcliLogCli(932),
        bitipmcCliSetDvmGlobTrapEnlCli(933),
        bitipmcCliSetDvmGlobLogEnlCli(934),
        bitDismanPingTraceroute (935),

	bitNaapCli(974),
	bitBcliAltLedEnableCli(975),
	bitBcliBackupCfgfileCli(976),
        bitrcBridgeFdbProtectTbl(977),
        bitrcSysDnsServer(978),
 	bitBcli8616ReAutonegCli(979),
	bitBcliBootpImageNameSetCli(980),
	bitBcliMezzImageNameSetCli(981),
        bitBcliMacUpgradeCli(982),
        bitLoadConfigCli(983),
        bitBcliBootpImageNameInfo(984),
        bitospfCliSetRfc1583CompatibilityCli(985),
        bitShExecuteCli(986),
        bitsysCliSetHighThroughputModeCli(987),
        bitsysCliSetUdpChecksumCli(988),
        bitBcliMaintCommand(989),
        bitExtCpLimit(990), 
	bitDumpCircuitcli(991),
        bitcppStatscli(992),
        bitfbuffDumpcli(993),
        bitmemShowcli(994),
        bitcheckStackcli(995),
        bitrcDumpSnmpcli(996),
        bitppeGetPortIsLinkUpcli(997),
        bitshowPpcli(998),
        bitdumpFacli(999),
        bitpimVirtualNbrTbl(1012),
        bitcliPasswordLockoutCli(1015),
        bitcliPasswordHistoryCli(1016),
        bitcliPasswordDefLockoutCli(1017),
        bitAutoRecoverSet(1019),
        bitAccessLevelEnDisCli(1020),
 --TACACS+
        bitrcTacacsGlobalGrp(1021),
        bitrcTacacsServerTbl(1022),

	bitPortCliSetSpoofDetectCli(1023),
        bitBcliMd5Cli(1024),
        bitBcliDumpfhCli(1025),
	bitBcliMezzCardBootEnableCli(1027),
        bitPasswordLenCli(1029),
        bitBcliCheckSrcRouteCli(1030),
        bitrcIsisCircuitTbl(1055),
        bitisisCircTbl(1056),
        bitisisCircLevelTbl(1057),
        bitisisManAreaAddrTbl(1058),
        bitisisSummAddrTbl(1059),
        bitrcIsisGlobalGrp(1060),
        bitisisSysObjectGrp(1061),
        bitisisSysLevelTbl(1062),
        bitipCliSetIsisRedistApply(1063),
        bitisisCliClearStatsCli(1076),
        bitLbmCmdCli(1091),
        bitLtmCmdCli(1092),
        bitrcCfmMaintenanceDomainTbl(1125),
        bitrcCfmMaintenanceAssociationTbl(1126),
        bitrcCfmMaintenanceEndPointTbl(1127),
        bitBcliLicensefileCli(1129),
        bitBcliBootpSecImageNameSetCli(1148),

        bitrcMplsNotificationObjectsGrp(1149),
	bitmplsLsrObjectsGrp(1150),
	bitmplsTeObjectsGrp(1151),
	bitmplsTunnelHopTbl(1152),
	bitmplsTunnelTbl(1153),
	bitmplsTunnelResourceTbl(1154),
	bitrcMplsIpStaticFecTbl(1155),
	bitmplsClearLspLdpRsvpStats(1156),
        bitrcIpVpnRouteDistTbl(1157),
        bitrcIpVpnRouteTargetTbl(1158),
        bitrcVrfIpVpnTbl(1159),
        bitrcIpBgpPeerTblIpvpnLiteCap(1160),
        bitrcIpBgpPeerTblVpnv4Address(1161),
        bitmplspingcli(1162),
        bitrcPlsbGlobalGrp(1164),
        bitrcIsisPlsbTbl(1165),
        bitrcIsisCircuitPlsbTbl(1166),
        bitrcIsidEndptCvidClientMipTbl(1168),
        bitisisCliClearLsdbCli(1169),
        bitL2PingCmdCli(1175),
        bitL2TraceCmdCli(1176),
        bitL2TraceReplyCmdCli(1177),
        bitDebugL2vpnCmdCli(1178),
        bitDebugIsisCmdCli(1179),
--  CardType bit numbers start here
	bitcardType(1536),
	bitrc2kCPU(1537),
	bitrc2k48x100BaseTX(1538),
	bitrc2k24x100BaseTX(1539),
	bitrc2k24x100BaseFX(1540),
	bitrc2k2xOC12(1541),
	bitrc2k8xATM(1542),
	bitrc2kRMON(1543),
	bitrc2k8x1000BaseSXBB(1544),
	bitrc2k8x1000BaseLXBB(1545),
	bitrc2k8x1000BaseSXRBB(1546),
	bitrc2k8x1000BaseLXRBB(1547),
	bitrc2k8x1000BaseXDBB(1548),
	bitrc2k8xOC3(1549),
	bitrc2kMg32x100BaseTX(1550),
	bitrc2kMg48x100BaseTX(1551),
	bitrc2kMg16x100BaseFX(1552),
	bitrc2kMg8x1000BaseIC(1553),
	bitrc2k8x1000BaseIC(1554),
	bitrc2kMg48x100BaseTC(1555),
	bitrc2k6xPOS(1556),
	bitrc2k16x1000BaseSXBB(1557),
	bitrc2k8x1000BaseT(1558),
	bitrc2k32x100BaseTX(1559),
	bitrc2k1x10GBaseLW(1560),
	bitrc2k16x1000BaseT(1561),
	bitrc2k1x10GBaseLR(1562),
	bitrc2kAlteonWSM(1563),
	bitrc2k48x100BaseTXM(1564),
	bitrc2k32x100BaseTXM(1565),
	bitrc2k8x1000BaseICM(1566),
	bitrc2k8x1000BaseSXBBM(1567),
	bitrc2k8x1000BaseTM(1568),
	bitrc2k8xATMM(1569),
	bitrc2k6xPOSM(1570),
-- Thunderbolt: 1571 - 1578 have been removed 
	bitrc2kPP8300-CPU8x1000BaseSFP(1579),
	bitrc2kPP8300-24x1000BaseTX(1580),
	bitrc2kPP8300-48x100BaseTX(1581),
	bitrc2kPP8300-48x100BaseTXPOE(1582),
	bitrc2kAlteonLP(1583),
	bitrc2kAlteonASFM(1584),
	bitrc2k61AlteonSAM(1585),
	bitrc2k62AlteonSAM(1586),
        bitrcMplsGlobalGrp(1603),
        bitrcIpMplsInterfaceTbl(1604),
        bitrcVrfConfigTbl(1605),
        bitrcVrfIfConfigTbl(1606),
        bitrcIpv6InterfaceTbl(1607),
        bitrcIpv6AddrTbl(1608),
        bitrcIpv6PrefixTbl(1609),
        bitrcIpv6RouterAdvertTbl(1610),
        bitrcIpv6StaticRouteTbl(1611),
        bitrcIpv6NetToPhysicalTbl(1612),
        bitrcIpv6Scalars(1613),
        bitrcPrFilterAceIpv6SrcAddrTbl(1614),
        bitrcPrFilterAceIpv6DstAddrTbl(1615),
        bitrcPrFilterAceIpv6NextHdr(1616),
        bitrc2kCpuEthernetPortIpv6RouteTbl(1617),
        bitrcIpv6PimGlobalGrp(1618),
        bitrcIpv6PimTbl(1619),
        bitrcIpv6PimStaticRPTbl(1620),
        bitrcIpv6pimVirtualNbrTbl(1621),
        bitrcIpv6MulticastTimedPruneTbl(1622),
        bitrcIpv6MulticastSoftwareForwarding(1623),
        bitrcIpv6PimInterfaceTbl(1624),
        bitrcIpv6MltMcastDistributionGrp(1625),
        bitrcIpv6ResourceUsageGlobalGrp(1626),
        bitIpv6InterfaceTbl(1627),
        bitIpv6RouteTbl(1628),
        bitIpv6NetToMediaTbl(1629),
        bitIpv6MIBObjects(1630),
        bittunnelIfTbl(1631),
        bittunnelInetConfigTbl(1632),
        bitmldInterfaceTbl(1633),
        bitmldCacheTbl(1634),
        bitrcIpv6Ospfv3NbmaNbrTbl(1635),
        bitrcIpv6Ospfv3IfTbl(1636),
        bitrcIpv6Ospfv3VirtIf(1637),
        bitrcIpv6Ospfv3AreaAggregateTbl(1638),
        bitrcIpv6Ospfv3AreaTbl(1639),
        bitrcIpv6Ospfv3GeneralGrp(1640),
        bitrc2kPR48X1000BaseTX(1641),
        bitrc2kPR30X1000BaseSXBB(1642),
        bitrc2kPR3X10GBaseXZW(1643),
        bitrc2kPR3X10GBaseGbic(1644),
	bitrcIpfixConfGlobalGrp(1645),
	bitrcIpfixConfSlotTbl(1646),
	bitrcIpfixCollectorTbl(1647),
	bitrcIpfixConfPortTbl(1648),
	bitrcIpfixHashStatsTbl(1649),
	bitrcIpfixExporterStatsTbl(1650),
	bitTreeSnmp(1654),
        bitInfoCmdSnmp(1655),
        bitShowCmdSnmp(1656),
        bitsnmpLogSnmp(1657),
	bitrc2kPR48x1000BaseGBRS(1658),
        bitrc2kPR48x1000BaseGTRS(1659),
        bitrc2kPR12X10GBaseXLRS(1660),
        bitrc2kPR34xXGRS(1661),
	bitrcPrQosEgressQosToExpTbl(1662),
	bitrcPrQosIngressExpToQosTbl(1663),
	bitrcPomConfGlobalGrp(1664),
        bitrcIpv6DhcpForwardTbl(1672),
        bitrcIpv6ConfDhcpTbl(1673),
        bitrcIpv6VrrpOperTbl(1674),
        bitrcVrrpExtScalarsGrp(1675),
        bitrcVrrpTmpOperationsGrp(1676),
        bitrcIpMulticastSquareSmltGrp(1677),
        bitrcPortLosslessEnetTbl(1684),
	bitcbAUX(1700),
	bitcbSF3200(1701),
	bitcbSF9600(1702),
	bitcbCP-CSC(1703),
	bitcb48x1000BaseTX(1704),
	bitcb48x1000BaseTXPOE(1705),
	bitcb48x1000SFP(1706),
	bitcb24x10GBaseSFP(1707),
	bitcb48x10GBaseSFP(1708),
        bitrcIpRedistributeTblIsis(1721),
	bitlastbitnum(2047)
	}
	MAX-ACCESS  read-only
	STATUS  current
	DESCRIPTION "Bit position number of license bitmap"
	::= { rcLicense 1 }	

rcLicenseBitMap OBJECT-TYPE
	SYNTAX OCTET STRING (SIZE(256))
	MAX-ACCESS read-only
	STATUS current
	DESCRIPTION "License bit map. Bitmap number is defined in rcLicenseNumber"
	::= { rcLicense 2 }

-- end of rcLicense

rcSshGlobalHostIpAddr OBJECT-TYPE
     SYNTAX       IpAddress
     MAX-ACCESS   read-write
     STATUS       current
     DESCRIPTION  "current remote ip addr"
     ::= { rcSshGlobal 12 }


rcSslMipTable OBJECT-TYPE
     SYNTAX       SEQUENCE OF RcSslMipEntry
     MAX-ACCESS   not-accessible
     STATUS       current
     DESCRIPTION  "This table would display the MIP of the SSL blade
                   according to the slot number."
     ::= { rcSsh 2 }

rcSslMipTableEntry OBJECT-TYPE
        SYNTAX        RcSslMipEntry
        MAX-ACCESS    not-accessible
        STATUS        current
        DESCRIPTION   "This table get the MIP of the SSL blade on which
                       the blade is in different cluster."
        INDEX         { rcSslMipSlot }
        ::= { rcSslMipTable 1 }

RcSslMipEntry ::=
     SEQUENCE {
             rcSslMipSlot      Integer32,
             rcSslMipMip       DisplayString
     }

rcSslMipSlot OBJECT-TYPE
     SYNTAX        Integer32 (0..2147483647)
     MAX-ACCESS     read-only
     STATUS         current
     DESCRIPTION    "Used as an index to find out the MIP of SSL blade."
     ::= { rcSslMipTableEntry 1 }

rcSslMipMip OBJECT-TYPE
     SYNTAX         DisplayString
     MAX-ACCESS     read-only
     STATUS         current
     DESCRIPTION    "Master IP of the SSL blade."
     ::= { rcSslMipTableEntry 2 }

-- LACP Group
-- LACP Global Information. 

-- =begin enum
-- rcLacpGlobalFastPeriodicTime min 200
-- =end enum

rcLacpGlobal   OBJECT IDENTIFIER        ::= { rcLacp 1 }

rcLacpGlobalEnable OBJECT-TYPE
     SYNTAX       TruthValue 
     MAX-ACCESS   read-write
     STATUS       current
     DESCRIPTION  "globally enable/disable LACP"
     DEFVAL       { false }
     ::= { rcLacpGlobal 1 }

rcLacpGlobalSystemPriority OBJECT-TYPE
     SYNTAX       Integer32(0..65535) 
     MAX-ACCESS   read-write
     STATUS       current
     DESCRIPTION  "set system priority to all the LACP enabled aggregators 
                   and prots"
     DEFVAL       { 32768 }
     ::= { rcLacpGlobal 2 }

rcLacpGlobalFastPeriodicTime OBJECT-TYPE
     SYNTAX       INTEGER (200..20000) 
     MAX-ACCESS   read-write
     STATUS       current
     DESCRIPTION  "The number of miliseconds between periodic transmissions
                   using Short Timeouts. Set this value to all LACP enabled ports."
     DEFVAL       { 1000 }
     ::= { rcLacpGlobal 3 }

rcLacpGlobalSlowPeriodicTime OBJECT-TYPE
     SYNTAX       INTEGER (10000..30000)
     MAX-ACCESS   read-write
     STATUS       current
     DESCRIPTION  "The number of miliseconds between periodic transmissions 
                   using LONG Timeouts. Set this value to all LACP enabled ports."
     DEFVAL       { 30000 }
     ::= { rcLacpGlobal 4 }

rcLacpGlobalTimeoutScale OBJECT-TYPE
     SYNTAX       INTEGER (1..10) 
     MAX-ACCESS   read-write
     STATUS       current
     DESCRIPTION  "Scalar value used to calculate timeout time from
                   periodic time. Set this value to all LACP enabled ports."
     DEFVAL       { 3 }
     ::= { rcLacpGlobal 5 }

rcLacpGlobalAggrWaitTime OBJECT-TYPE
        SYNTAX        INTEGER (200..2000)
        MAX-ACCESS    read-write
        STATUS        current
        DESCRIPTION   "The number of mili seconds to delay aggregation to
                       allow multiple links to aggregate simultaneously."
        DEFVAL        { 2000 }
        ::= { rcLacpGlobal 6 }

rcLacpGlobalVlacpEnable OBJECT-TYPE
     SYNTAX       TruthValue
     MAX-ACCESS   read-write
     STATUS       current
     DESCRIPTION  "globally enable/disable Virtual LACP"
     DEFVAL       { false }
     ::= { rcLacpGlobal 7 }


rcLacpGlobalFastPeriodicTimeOper OBJECT-TYPE
        SYNTAX       INTEGER (200..20000) 
        MAX-ACCESS    read-only
        STATUS        current
        DESCRIPTION   "The operating value of global fast periodic timer."
        ::= { rcLacpGlobal 9 }

rcLacpGlobalSlowPeriodicTimeOper OBJECT-TYPE
        SYNTAX        INTEGER (10000..30000) 
        MAX-ACCESS    read-only
        STATUS        current
        DESCRIPTION   "The operating value of global show periodic time."
        ::= { rcLacpGlobal 10 }

rcLacpGlobalTimeoutScaleOper OBJECT-TYPE
        SYNTAX        INTEGER (1..10) 
        MAX-ACCESS    read-only
        STATUS        current
        DESCRIPTION   "The operating value of global timeout scale."
        ::= { rcLacpGlobal 11 }

rcLacpGlobalAggrWaitTimeOper OBJECT-TYPE
        SYNTAX        INTEGER (200..2000) 
        MAX-ACCESS    read-only
        STATUS        current
        DESCRIPTION   "The operating value of global aggregate wait time."
        ::= { rcLacpGlobal 12 }

rcLacpGlobalSmltSysId OBJECT-TYPE
        SYNTAX       MacAddress
        MAX-ACCESS   read-write
        STATUS       current
        DESCRIPTION  "LACP system ID for SMLT"
        ::= { rcLacpGlobal 13 }

-- GlobalMacFilter Changes

rcGlobalMacFilterTable OBJECT-TYPE
     SYNTAX        SEQUENCE OF RcGlobalMacFilterEntry
     MAX-ACCESS    not-accessible
     STATUS        current
     DESCRIPTION   "A list of Global Mac filter entries."
     ::= { rcFdb 1 }

rcGlobalMacFilterEntry  OBJECT-TYPE
     SYNTAX          RcGlobalMacFilterEntry
     MAX-ACCESS      not-accessible
     STATUS          current
     DESCRIPTION     "this entry is used for global mac filtering.Any Mac
                      address configured here will be discarded globally 
                      by the switch."
     INDEX { rcGlobalMacFilterAddress }
     ::= { rcGlobalMacFilterTable 1 }

RcGlobalMacFilterEntry  ::=
     SEQUENCE {
               rcGlobalMacFilterAddress MacAddress,
               rcGlobalMacFilterRowStatus RowStatus
              }

rcGlobalMacFilterAddress OBJECT-TYPE
     SYNTAX          MacAddress
     MAX-ACCESS      not-accessible
     STATUS          current
     DESCRIPTION     "A MAC address which will be discarded globally by
                      the switch"
     ::= { rcGlobalMacFilterEntry  1 }

rcGlobalMacFilterRowStatus OBJECT-TYPE
     SYNTAX        RowStatus
     MAX-ACCESS    read-write
     STATUS        current
     DESCRIPTION   "Used to create/delete entries in rcGlobalMacFilterTable."
     ::= { rcGlobalMacFilterEntry 2 }

rcPowerRangerMib           OBJECT IDENTIFIER ::= { rcPowerRanger 1 }
rcPowerRangerNotifications OBJECT IDENTIFIER ::= { rcPowerRangerMib 0 }
rcPowerRangerObjects       OBJECT IDENTIFIER ::= { rcPowerRangerMib 1 }

--
-- Object groups within the Power Ranger MIB
--

rcPrQos    OBJECT IDENTIFIER ::= { rcPowerRangerObjects 1 }
rcPrFilter OBJECT IDENTIFIER ::= { rcPowerRangerObjects 2 }

--
-- The rcPrQos group
--

rcPrQosScalars OBJECT IDENTIFIER ::= { rcPrQos 1 }

LaneSet ::= TEXTUAL-CONVENTION
  STATUS       current
  DESCRIPTION         
              "The set of lanes that are members of this Global
               Policer. The string is 4 octets long, for a total
               of 32 bits. Each bit corresponds to a laneId.
               Each I/O slot has 4 laneIds. When a bit has the
               value one(1), the corresponding laneId is a member
               of the set. When a bit has the value zero(0), the
               corresponding laneId is not a member of the set.
               The encoding is such that the most significant bit
               of octet #1 corresponds to laneId 0, while the
               least significant bit of octet #4 corresponds to
               laneId 31."
  SYNTAX      OCTET STRING (SIZE (4))
  IsisPlsbNodeNickName ::= TEXTUAL-CONVENTION
        STATUS current
        DESCRIPTION
            "Plsb Node Nick name."
        SYNTAX OCTET STRING (SIZE(3))

  IsisSystemID ::= TEXTUAL-CONVENTION
        STATUS current
        DESCRIPTION
            "A system ID."
        SYNTAX OCTET STRING (SIZE(6))


rcPrQosPolicyNumPolicies OBJECT-TYPE
        SYNTAX           INTEGER (0..12288)
        MAX-ACCESS       read-only
        STATUS           current
        DESCRIPTION      "A list of Global Policer (GPID) entries. 
	                 The number of entries is given by
                         rcPrQosPolicyNumPolicies."
        ::= { rcPrQosScalars 1 }

rcPrQosTxQueueNumTemplates  OBJECT-TYPE
        SYNTAX        	INTEGER (0..383)
        MAX-ACCESS    	read-only
        STATUS        	current
        DESCRIPTION   	"The number of egress queue templates currently 
		      	defined in the switch."
        ::= { rcPrQosScalars 2 }

rcPrQosFlowPolicerStatsClear  OBJECT-TYPE
        SYNTAX             TruthValue
        MAX-ACCESS         read-write
        STATUS             current
        DESCRIPTION        "Clear all box-wide policer statistics."
        ::= { rcPrQosScalars 3 }

rcPrQosLossless8021p  OBJECT-TYPE
        SYNTAX        Integer32 (0..6)
        MAX-ACCESS    read-write
        STATUS        current
        DESCRIPTION   "The value used to map Ingress IEEE 1p to lossless
                       internal Qos when lossless Ethernet mode is enabled."
        ::= { rcPrQosScalars 4 }

rcPrQosLosslessPfcEnabled  OBJECT-TYPE
        SYNTAX        TruthValue
        MAX-ACCESS    read-only
        STATUS        current
        DESCRIPTION   "If true then at least one lossless port in the
                       switch has been configured with the value of
                       rcPortLosslessEnetPauseType set to pfc(2).
                       If false then either all lossless ports are currently
                       in fc(1) mode, or no ports are configured in
                       lossless mode."
        ::= { rcPrQosScalars 5 }

rcPrQosLosslessPortsEnablePending  OBJECT-TYPE
        SYNTAX        PortSet
        MAX-ACCESS    read-write
        STATUS        current
        DESCRIPTION   "This object is used to inform the system which ports
                       are pending lossless enable and is for internal use."
        ::= { rcPrQosScalars 6 }

rcPrQosLosslessPortsOperPending  OBJECT-TYPE
        SYNTAX        DisplayString (SIZE(0..255))
        MAX-ACCESS    read-only
        STATUS        current
        DESCRIPTION   "Indicates which ports which would be brought down
                       operationally if the set of ports indicated in
                       rcPrQosLosslessPortsEnablePending are configured
                       for lossless operation."
        ::= { rcPrQosScalars 7 }

-- Power Ranger Qos Policy Policers Table
rcPrQosPolicyTable      OBJECT-TYPE
        SYNTAX          SEQUENCE OF RcPrQosPolicyEntry
        MAX-ACCESS      not-accessible
        STATUS          current
        DESCRIPTION     "A list of GPID entries. The number of entries is
                        given by rcPrQosPolicyNumPolicies."
        ::= { rcPrQos 2 }

rcPrQosPolicyEntry      OBJECT-TYPE
        SYNTAX          RcPrQosPolicyEntry
        MAX-ACCESS      not-accessible
        STATUS          current
        DESCRIPTION     "Entry containing configuration information for a
                        particular global policer."
        INDEX           { rcPrQosPolicyGpId }
        ::= { rcPrQosPolicyTable 1 }

RcPrQosPolicyEntry ::= SEQUENCE {
                rcPrQosPolicyGpId             INTEGER,
                rcPrQosPolicyName             DisplayString,
                rcPrQosPolicyPeakRate         INTEGER,
                rcPrQosPolicySvcRate          INTEGER,
                rcPrQosPolicyLaneMembers      LaneSet,
                rcPrQosPolicyRowStatus        RowStatus
                }

rcPrQosPolicyGpId       OBJECT-TYPE
        SYNTAX          INTEGER (1..16000)
        MAX-ACCESS      read-only
        STATUS          current
        DESCRIPTION     "A value that uniquely identifies Global Policer
                        associated with this entry."
        ::= { rcPrQosPolicyEntry 1 }

rcPrQosPolicyName       OBJECT-TYPE
        SYNTAX          DisplayString (SIZE (0..32))
        MAX-ACCESS      read-write
        STATUS          current
        DESCRIPTION     "An administratively-assigned name for this Global
                        Policer."
        ::= { rcPrQosPolicyEntry 2 }

rcPrQosPolicyPeakRate   OBJECT-TYPE
        SYNTAX          INTEGER (64..5000000)
        MAX-ACCESS      read-write
        STATUS          current
        DESCRIPTION     "Global Policer Peak Rate in Kilobit/sec."
        ::= { rcPrQosPolicyEntry 3 }

rcPrQosPolicySvcRate    OBJECT-TYPE
        SYNTAX          INTEGER (64..5000000)
        MAX-ACCESS      read-write
        STATUS          current
        DESCRIPTION     "Global Policer Service Rate in Kilobit/sec."
        ::= { rcPrQosPolicyEntry 4 }

rcPrQosPolicyLaneMembers      OBJECT-TYPE
        SYNTAX          LaneSet
        MAX-ACCESS      read-write 
        STATUS          current 
        DESCRIPTION     "The set of lanes that are members of this Global
                        Policer. The string is 4 octets long, for a total 
			of 32 bits. Each bit corresponds to a laneId. 
			Each I/O slot has 4 laneIds. When a bit has the 
			value one(1), the corresponding laneId is a member 
			of the set. When a bit has the value zero(0), the 
			corresponding laneId is not a member of the set. 
			The encoding is such that the most significant bit 
			of octet #1 corresponds to laneId 0, while the
			least significant bit of octet #4 corresponds to 
			laneId 31."
        ::= { rcPrQosPolicyEntry 5 }

rcPrQosPolicyRowStatus       OBJECT-TYPE
        SYNTAX          RowStatus
        MAX-ACCESS      read-write
        STATUS          current
        DESCRIPTION     "Create/delete operations for this entry."
        ::= { rcPrQosPolicyEntry 6}


-- Power Ranger Qos Local Policer Table

-- For CB the rcPrQosLocalPolicyTable will be used to collect statistics
-- on a per-policy basis.  The upper range is 16000.

rcPrQosLocalPolicyTable OBJECT-TYPE
        SYNTAX          SEQUENCE OF RcPrQosLocalPolicyEntry
        MAX-ACCESS      not-accessible
        STATUS          current
        DESCRIPTION     "A list of policer entries."
        ::= { rcPrQos 3 }

rcPrQosLocalPolicyEntry OBJECT-TYPE
        SYNTAX          RcPrQosLocalPolicyEntry
        MAX-ACCESS      not-accessible
        STATUS          current
        DESCRIPTION     "An entry containing configuration information for
                        a particular local policer.  This field will
                        return 0 for CB as tap.lane.lpid is not used."
        INDEX           { rcPrQosLocalPolicyGpId, 
                           rcPrQosLocalPolicyIndex }
        ::= { rcPrQosLocalPolicyTable 1 }

RcPrQosLocalPolicyEntry ::= SEQUENCE {
                rcPrQosLocalPolicyGpId                  INTEGER,
                rcPrQosLocalPolicyIndex                 Integer32,
                rcPrQosLocalPolicyPeakRate              INTEGER,
                rcPrQosLocalPolicySvcRate               INTEGER,
                rcPrQosLocalPolicyTotalPkts             Counter64,
                rcPrQosLocalPolicyTotalBytes            Counter64,
                rcPrQosLocalPolicyBytesOverPeak         Counter64,
                rcPrQosLocalPolicyBytesOverSvc          Counter64,
                rcPrQosLocalPolicyTotalPktsDropped      Counter64,
                rcPrQosLocalPolicyLaneMember            OCTET STRING,
                rcPrQosLocalPolicyGreenPackets		Counter64,
                rcPrQosLocalPolicyGreenBytes		Counter64,
                rcPrQosLocalPolicyYellowPackets		Counter64,
                rcPrQosLocalPolicyYellowBytes		Counter64,
                rcPrQosLocalPolicyRedPackets		Counter64,
                rcPrQosLocalPolicyRedBytes		Counter64,
		rcPrQosLocalPolicyStatsClear		TruthValue
              }

rcPrQosLocalPolicyGpId OBJECT-TYPE
        SYNTAX          INTEGER (1..16000) 
        MAX-ACCESS      read-only
        STATUS          current
        DESCRIPTION     "A value of Global Policer ID corresponding to this 
	                local policer."
        ::= { rcPrQosLocalPolicyEntry 1 }

rcPrQosLocalPolicyIndex OBJECT-TYPE
        SYNTAX          Integer32 (3..12)
        MAX-ACCESS      read-only
        STATUS          current
        DESCRIPTION     "The slot number of the VSP chassis on which
			stats are collected.  Valid slots are IO slots
                        which are in slots 3 to 12."
        ::= { rcPrQosLocalPolicyEntry 2 }

rcPrQosLocalPolicyPeakRate OBJECT-TYPE
        SYNTAX          INTEGER (0..10000000)
        MAX-ACCESS      read-only
        STATUS          current 
        DESCRIPTION     "Global Peak Rate in Kilobit/sec." 
        ::= { rcPrQosLocalPolicyEntry 3 }

rcPrQosLocalPolicySvcRate OBJECT-TYPE
        SYNTAX          INTEGER (0..10000000)
        MAX-ACCESS      read-only
        STATUS          current
        DESCRIPTION     "Global Policer Service Rate in Kilobit/sec."
        ::= { rcPrQosLocalPolicyEntry 4 }

rcPrQosLocalPolicyTotalPkts OBJECT-TYPE
        SYNTAX          Counter64
        MAX-ACCESS      read-only
        STATUS          current
        DESCRIPTION     "Global Policer Total Packets Count."
        ::= { rcPrQosLocalPolicyEntry 5 }

rcPrQosLocalPolicyTotalBytes OBJECT-TYPE
        SYNTAX          Counter64
        MAX-ACCESS      read-only
        STATUS          current
        DESCRIPTION     "Global Policer Total Bytes Count."
        ::= { rcPrQosLocalPolicyEntry 6 }

rcPrQosLocalPolicyBytesOverPeak OBJECT-TYPE
        SYNTAX          Counter64
        MAX-ACCESS      read-only
        STATUS          current
        DESCRIPTION     "Global Policer Bytes over Peak Rate Count."
        ::= { rcPrQosLocalPolicyEntry 7 }

rcPrQosLocalPolicyBytesOverSvc OBJECT-TYPE
        SYNTAX          Counter64
        MAX-ACCESS      read-only
        STATUS          current 
        DESCRIPTION     "Global Policer Bytes over Service Rate Count."
        ::= { rcPrQosLocalPolicyEntry 8 }

rcPrQosLocalPolicyTotalPktsDropped OBJECT-TYPE
        SYNTAX          Counter64
        MAX-ACCESS      read-only
        STATUS          current 
        DESCRIPTION     "The count of Global Policer Total Packets dropped
                        due to reasons other than policing, e.g. congestion."
        ::= { rcPrQosLocalPolicyEntry 9 }

rcPrQosLocalPolicyLaneMember OBJECT-TYPE
        SYNTAX          OCTET STRING (SIZE(0..4))
        MAX-ACCESS      read-only
        STATUS          current
        DESCRIPTION     "The lane that this Gpid has a local policing 
                         account on "  
        ::= { rcPrQosLocalPolicyEntry 10 }

rcPrQosLocalPolicyGreenPackets OBJECT-TYPE
        SYNTAX        Counter64
        MAX-ACCESS    read-only
        STATUS        current
        DESCRIPTION   "The total number of packets received
                       that were below committed rate."
        ::= { rcPrQosLocalPolicyEntry 11 }

rcPrQosLocalPolicyGreenBytes OBJECT-TYPE
        SYNTAX        Counter64
        MAX-ACCESS    read-only
        STATUS        current
        DESCRIPTION   "The total number of bytes received 
                       that were below the committed rate."
        ::= { rcPrQosLocalPolicyEntry 12 }

rcPrQosLocalPolicyYellowPackets OBJECT-TYPE
        SYNTAX        Counter64
        MAX-ACCESS    read-only
        STATUS        current
        DESCRIPTION   "The total number of packets received
                       that were above the committed rate but
                       below the peak rate."
        ::= { rcPrQosLocalPolicyEntry 13 }

rcPrQosLocalPolicyYellowBytes OBJECT-TYPE
        SYNTAX        Counter64
        MAX-ACCESS    read-only
        STATUS        current
        DESCRIPTION   "The total number of bytes received 
                       that were above the committed rate but
                       below the peak rate."
        ::= { rcPrQosLocalPolicyEntry 14 }

rcPrQosLocalPolicyRedPackets OBJECT-TYPE
        SYNTAX        Counter64
        MAX-ACCESS    read-only
        STATUS        current
        DESCRIPTION   "The total number of packets received
                       that were above the peak rate."
        ::= { rcPrQosLocalPolicyEntry 15 }

rcPrQosLocalPolicyRedBytes OBJECT-TYPE
        SYNTAX        Counter64
        MAX-ACCESS    read-only
        STATUS        current
        DESCRIPTION   "The total number of bytes received 
                       that were above the peak rate."
        ::= { rcPrQosLocalPolicyEntry 16 }

rcPrQosLocalPolicyStatsClear  OBJECT-TYPE
        SYNTAX             TruthValue
        MAX-ACCESS         read-write
        STATUS             current
        DESCRIPTION        "Clear Qos Policy statistics."
        ::= { rcPrQosLocalPolicyEntry 17 }



-- Power Ranger Qos Egress Queue Template Table
rcPrQosTxQueueTemplateTable OBJECT-TYPE
        SYNTAX        	SEQUENCE OF RcPrQosTxQueueTemplateEntry
        MAX-ACCESS    	not-accessible
        STATUS        	current
        DESCRIPTION   	"A list of egress queue templates. The number of 
			templates is given by rcPrQosTxQueueNumTemplates."
        ::= { rcPrQos 4 }

rcPrQosTxQueueTemplateEntry OBJECT-TYPE
        SYNTAX        	RcPrQosTxQueueTemplateEntry
        MAX-ACCESS    	not-accessible
        STATUS        	current
        DESCRIPTION   	"Entry containing configuration information for a
                      	particular egress queue template. Queue is a set of 
			egress queues."
       	INDEX         	{ rcPrQosTxQueueTemplateId }
        ::= { rcPrQosTxQueueTemplateTable 1 }

RcPrQosTxQueueTemplateEntry ::= SEQUENCE {
                rcPrQosTxQueueTemplateId     		INTEGER,
                rcPrQosTxQueueTemplateName   		DisplayString,
		rcPrQosTxQueueTemplateMaxQueues 	INTEGER,
		rcPrQosTxQueueTemplateBalancedQueues 	INTEGER,
		rcPrQosTxQueueTemplateHiPriQueues 	INTEGER,
		rcPrQosTxQueueTemplateLoPriQueues 	INTEGER,
		rcPrQosTxQueueTemplateTotalQueues 	Integer32,
		rcPrQosTxQueueTemplateBalancedQList 	OCTET STRING,
		rcPrQosTxQueueTemplateHiPriQList 	OCTET STRING,
		rcPrQosTxQueueTemplateLoPriQList 	OCTET STRING,
		rcPrQosTxQueueTemplateTotalQLists	OCTET STRING,
		rcPrQosTxQueueTemplateMinRateTotal 	INTEGER,
		rcPrQosTxQueueTemplateMaxRateHiPri 	INTEGER,
		rcPrQosTxQueueTemplatePortMembers	PortSet,
		rcPrQosTxQueueTemplateFlags		INTEGER,
		rcPrQosTxQueueTemplateApply		TruthValue,
		rcPrQosTxQueueTemplateRowStatus		RowStatus
		}

rcPrQosTxQueueTemplateId OBJECT-TYPE
        SYNTAX        	INTEGER (1..386)
        MAX-ACCESS    	read-only
        STATUS        	current
        DESCRIPTION   	"A value that uniquely identifies Egress Queue 
	                Template."
        ::= { rcPrQosTxQueueTemplateEntry 1 }

rcPrQosTxQueueTemplateName OBJECT-TYPE
        SYNTAX        	DisplayString (SIZE (0..32))
        MAX-ACCESS    	read-write
        STATUS       	current
        DESCRIPTION   	"An administratively-assigned name for this egress 
			Queue Template."
        ::= { rcPrQosTxQueueTemplateEntry 2 }

rcPrQosTxQueueTemplateMaxQueues OBJECT-TYPE
	SYNTAX        	INTEGER {
				eight(8),
				sixtyfour(64)
				}
        MAX-ACCESS    	read-create
        STATUS        	current
	DESCRIPTION   	"Maximum number of queues in this Template."
        ::= { rcPrQosTxQueueTemplateEntry 3 }

rcPrQosTxQueueTemplateBalancedQueues OBJECT-TYPE
        SYNTAX        	INTEGER (0..48)
        MAX-ACCESS    	read-write
        STATUS        	current
        DESCRIPTION   	"Total number of Balanced Queues in this Template."
        ::= { rcPrQosTxQueueTemplateEntry 4 }

rcPrQosTxQueueTemplateHiPriQueues OBJECT-TYPE
        SYNTAX        	INTEGER (0..64)
        MAX-ACCESS    	read-write
        STATUS        	current
        DESCRIPTION   	"Total number of High Priority Queues in this 
			Template."
        ::= { rcPrQosTxQueueTemplateEntry 5 }

rcPrQosTxQueueTemplateLoPriQueues OBJECT-TYPE
        SYNTAX        	INTEGER (0..8)
        MAX-ACCESS    	read-write
        STATUS        	current
        DESCRIPTION   	"Total number of Low Priority Queues in this Template."
        ::= { rcPrQosTxQueueTemplateEntry 6 }

rcPrQosTxQueueTemplateTotalQueues OBJECT-TYPE
	SYNTAX        	Integer32
        MAX-ACCESS    	read-only
        STATUS        	current
	DESCRIPTION   	"Total number of queues in this Template."
        ::= { rcPrQosTxQueueTemplateEntry 7 }

rcPrQosTxQueueTemplateBalancedQList OBJECT-TYPE
        SYNTAX        	OCTET STRING (SIZE(0..200))
        MAX-ACCESS    	read-only
        STATUS        	current
        DESCRIPTION   	"List of Balanced Queues in this Template."
        ::= { rcPrQosTxQueueTemplateEntry 8 }

rcPrQosTxQueueTemplateHiPriQList OBJECT-TYPE
        SYNTAX        	OCTET STRING (SIZE(0..200))
        MAX-ACCESS    	read-only
        STATUS        	current
        DESCRIPTION   	"List of High Priority Queues in this Template."
        ::= { rcPrQosTxQueueTemplateEntry 9 }

rcPrQosTxQueueTemplateLoPriQList OBJECT-TYPE
        SYNTAX        	OCTET STRING (SIZE(0..200))
        MAX-ACCESS    	read-only
        STATUS        	current
        DESCRIPTION   	"List of Low Priority Queues in this Template."
        ::= { rcPrQosTxQueueTemplateEntry 10 }

rcPrQosTxQueueTemplateTotalQLists OBJECT-TYPE
        SYNTAX        	OCTET STRING (SIZE(0..600))
        MAX-ACCESS    	read-only
        STATUS        	current
        DESCRIPTION   	"List of Total Physical Queues in this Template."
        ::= { rcPrQosTxQueueTemplateEntry 11 }

rcPrQosTxQueueTemplateMinRateTotal OBJECT-TYPE
        SYNTAX        	INTEGER (0..100)
        MAX-ACCESS    	read-only
        STATUS        	current
        DESCRIPTION   	"Sum of minimum rate guarantees for this template."
        ::= { rcPrQosTxQueueTemplateEntry 12 }

rcPrQosTxQueueTemplateMaxRateHiPri OBJECT-TYPE
        SYNTAX        	INTEGER (0..100)
        MAX-ACCESS    	read-only
        STATUS        	current
        DESCRIPTION   	"Sum of maximum rate guarantees for high priority
			queues of this template."
        ::= { rcPrQosTxQueueTemplateEntry 13 }

rcPrQosTxQueueTemplatePortMembers OBJECT-TYPE
        SYNTAX        	PortSet
        MAX-ACCESS    	read-write
        STATUS        	current
        DESCRIPTION   	"Port members of this template." 
        ::= { rcPrQosTxQueueTemplateEntry 14 }

rcPrQosTxQueueTemplateFlags OBJECT-TYPE
        SYNTAX        	INTEGER {
			    created(1),
			    committed(2),
			    modified(3)
			}
        MAX-ACCESS    	read-write
        STATUS        	current
        DESCRIPTION   	"Bitset indicated template state."
	DEFVAL		{ created }
        ::= { rcPrQosTxQueueTemplateEntry 15 }

rcPrQosTxQueueTemplateApply OBJECT-TYPE
        SYNTAX          TruthValue
        MAX-ACCESS      read-write
        STATUS          current
        DESCRIPTION    "When apply is issued by the administrator,
                        the Egress Queue Set attributes are committed."
        DEFVAL          { false }
        ::= { rcPrQosTxQueueTemplateEntry 16 }

rcPrQosTxQueueTemplateRowStatus OBJECT-TYPE
        SYNTAX        	RowStatus
        MAX-ACCESS    	read-write
        STATUS        	current
        DESCRIPTION   	"Create/delete operations for this entry." 
        ::= { rcPrQosTxQueueTemplateEntry 17 }

-- Power Ranger Qos Egress Queue Table
rcPrQosTxQueueTable OBJECT-TYPE
        SYNTAX        	SEQUENCE OF RcPrQosTxQueueEntry
        MAX-ACCESS    	not-accessible
        STATUS        	current
        DESCRIPTION   	"A list of elementary Egress queue entries."
        ::= { rcPrQos 5 }

rcPrQosTxQueueEntry OBJECT-TYPE
        SYNTAX        	RcPrQosTxQueueEntry
        MAX-ACCESS    	not-accessible
        STATUS        	current
        DESCRIPTION   	"Entry containing configuration information for a
                      	particular elementary egress queue."
       	INDEX         	{ rcPrQosTxQueueTid, 
			  rcPrQosTxQueueQid }
        ::= { rcPrQosTxQueueTable 1 }

RcPrQosTxQueueEntry ::= SEQUENCE {
                rcPrQosTxQueueTid		INTEGER,
                rcPrQosTxQueueQid		INTEGER,
                rcPrQosTxQueueName		DisplayString,
                rcPrQosTxQueueStyle     	INTEGER,
                rcPrQosTxQueueWeight		Integer32,
                rcPrQosTxQueueMaxRate		Integer32,
                rcPrQosTxQueueMinRate		Integer32,
                rcPrQosTxQueueBquantum  	Integer32,
	    	rcPrQosTxQueueMaxLength         Integer32,
		rcPrQosTxQueueWredCurveSet	INTEGER,
		rcPrQosTxQueueRowStatus		RowStatus
		}

rcPrQosTxQueueTid OBJECT-TYPE
  	SYNTAX        	INTEGER (1..386)
        MAX-ACCESS    	read-write
        STATUS        	current
        DESCRIPTION   "Template ID of the template this queue belongs to."
        ::= { rcPrQosTxQueueEntry 1 }

rcPrQosTxQueueQid OBJECT-TYPE
        SYNTAX        	INTEGER (0..63)
        MAX-ACCESS    	read-only
        STATUS        	current
        DESCRIPTION   	"Queue Offset from the base queue for this port."
        ::= { rcPrQosTxQueueEntry 2 }

rcPrQosTxQueueName OBJECT-TYPE
        SYNTAX        	DisplayString (SIZE (0..32))
        MAX-ACCESS    	read-write
        STATUS       	current
        DESCRIPTION   	"An NNSC name for this egress queue. Allowed only
			for 8 NNSC queues."
        ::= { rcPrQosTxQueueEntry 3 }

rcPrQosTxQueueStyle OBJECT-TYPE
        SYNTAX        	INTEGER {
			    hipri(1),
			    balanced(2),
			    lopri(3)
			}
        MAX-ACCESS    	read-write
        STATUS        	current
        DESCRIPTION   	"Egress queue style."
        ::= { rcPrQosTxQueueEntry 4 } 

rcPrQosTxQueueWeight OBJECT-TYPE
        SYNTAX        	Integer32
        MAX-ACCESS    	read-only
        STATUS        	current
        DESCRIPTION   	"Egress queue weight. 
			Applicable for balanced queues and lo-pri queues only."
        ::= { rcPrQosTxQueueEntry 5 }

rcPrQosTxQueueMaxRate OBJECT-TYPE
        SYNTAX        	Integer32
        MAX-ACCESS    	read-write
        STATUS        	current
        DESCRIPTION   	"Egress queue maximum rate, Kbs"
        ::= { rcPrQosTxQueueEntry 6 }

rcPrQosTxQueueMinRate OBJECT-TYPE
        SYNTAX        	Integer32
        MAX-ACCESS    	read-write
        STATUS        	current
        DESCRIPTION   	"Egress queue minimun rate guarantee, Kbs. 
			Applicable for balanced queues and lo-pri queues only."
        ::= { rcPrQosTxQueueEntry 7 }

rcPrQosTxQueueBquantum OBJECT-TYPE
        SYNTAX        	Integer32
        MAX-ACCESS    	read-only
        STATUS        	current
        DESCRIPTION   	"Bandwidth allocation unit. 
			Applicable for balanced queues and lo-pri queues only."
        ::= { rcPrQosTxQueueEntry 8 }

rcPrQosTxQueueMaxLength OBJECT-TYPE
        SYNTAX        	Integer32
        MAX-ACCESS    	read-write
        STATUS        	current
        DESCRIPTION 	"Maximum queue length."
        ::= { rcPrQosTxQueueEntry 9 }

rcPrQosTxQueueWredCurveSet OBJECT-TYPE
        SYNTAX        	INTEGER {
			    tailDrop(1),
			    lowDrop(2),
			    mediumDrop(3),
			    highDrop(4)
			}
        MAX-ACCESS    	read-write
        STATUS        	current
        DESCRIPTION 	"Random Early Detection Number."
	DEFVAL		{ tailDrop }
        ::= { rcPrQosTxQueueEntry 10 }

rcPrQosTxQueueRowStatus OBJECT-TYPE
        SYNTAX        	RowStatus
        MAX-ACCESS    	read-write
        STATUS        	current
        DESCRIPTION 	"Create/delete operations for this entry."
        ::= { rcPrQosTxQueueEntry 11 }

-- Power Ranger Qos Egress Queue Stats Table
rcPrQosTxQueueStatsTable OBJECT-TYPE
        SYNTAX        	SEQUENCE OF  RcPrQosTxQueueStatsEntry
        MAX-ACCESS    	not-accessible
        STATUS        	current
        DESCRIPTION   	"A list of elementary Egress queue stats entries."
        ::= { rcPrQos 6 }

rcPrQosTxQueueStatsEntry OBJECT-TYPE
        SYNTAX        	RcPrQosTxQueueStatsEntry
        MAX-ACCESS    	not-accessible
        STATUS        	current
        DESCRIPTION   	"Entry containing statistics information for a
                      	particular elementary egress queue."
       	INDEX         	{ rcPrQosTxQueueStatsPort, 
			  rcPrQosTxQueueStatsQid }
        ::= { rcPrQosTxQueueStatsTable 1 }

RcPrQosTxQueueStatsEntry ::= SEQUENCE {
                rcPrQosTxQueueStatsPort         InterfaceIndex,
                rcPrQosTxQueueStatsQid          INTEGER, 
                rcPrQosTxQueueStatsTotalPages   Counter64,
                rcPrQosTxQueueStatsDroppedPages Counter64,
                rcPrQosTxQueueStatsUtilization  INTEGER 
		}

rcPrQosTxQueueStatsPort OBJECT-TYPE
  	    SYNTAX          InterfaceIndex
        MAX-ACCESS    	read-only
        STATUS        	current
        DESCRIPTION   "Port index of the stats table."
        ::= { rcPrQosTxQueueStatsEntry 1 }

rcPrQosTxQueueStatsQid OBJECT-TYPE
        SYNTAX        	INTEGER (0..63)
        MAX-ACCESS    	read-only
        STATUS        	current
        DESCRIPTION   	"Queue Offset from the base queue for this port."
        ::= { rcPrQosTxQueueStatsEntry 2 }

rcPrQosTxQueueStatsTotalPages OBJECT-TYPE
        SYNTAX        	Counter64
        MAX-ACCESS    	read-only
        STATUS        	current
        DESCRIPTION 	"Total pages offered to the queue."
        ::= { rcPrQosTxQueueStatsEntry 3 }

rcPrQosTxQueueStatsDroppedPages OBJECT-TYPE
        SYNTAX        	Counter64
        MAX-ACCESS    	read-only
        STATUS        	current
        DESCRIPTION 	"Total pages dropped by the queue."
        ::= { rcPrQosTxQueueStatsEntry 4 }

rcPrQosTxQueueStatsUtilization OBJECT-TYPE
        SYNTAX        	INTEGER (0..100)
        MAX-ACCESS    	read-only
        STATUS        	current
        DESCRIPTION 	"Utilization percentage of the queue."
        ::= { rcPrQosTxQueueStatsEntry 5 }

-- Power Ranger Ingress Exp Bit To Qos Level Table
rcPrQosIngressExpToQosTable OBJECT-TYPE
        SYNTAX          SEQUENCE OF RcPrQosIngressExpToQosEntry
        MAX-ACCESS      not-accessible
        STATUS          current
        DESCRIPTION     "This table is used to specify the Mpls EXP to
                        QOS (Exp bit->QOS) mapping on packet ingress."
        ::= { rcPrQos 7 }

rcPrQosIngressExpToQosEntry OBJECT-TYPE
        SYNTAX        RcPrQosIngressExpToQosEntry
        MAX-ACCESS    not-accessible
        STATUS        current
        DESCRIPTION   "Entry containing information of Exp bit->Qos mapping"
        INDEX         { rcPrQosIngressExpToQosIndex }
        ::= { rcPrQosIngressExpToQosTable 1 }

RcPrQosIngressExpToQosEntry ::= SEQUENCE {
                rcPrQosIngressExpToQosIndex     INTEGER,
                rcPrQosIngressExpToQosRowStatus RowStatus 
        }

rcPrQosIngressExpToQosIndex OBJECT-TYPE
        SYNTAX        INTEGER (1..8)
        MAX-ACCESS    not-accessible
        STATUS        current
        DESCRIPTION   "Used to uniquely identify a row in this table."
        ::= { rcPrQosIngressExpToQosEntry 1 }

rcPrQosIngressExpToQosRowStatus  OBJECT-TYPE
        SYNTAX        RowStatus
        MAX-ACCESS    read-write
        STATUS        current
        DESCRIPTION   "Create/delete operations for this entry."
        ::= { rcPrQosIngressExpToQosEntry 4}


-- Power Ranger Egress Qos Level to Exp Bit Table
rcPrQosEgressQosToExpTable OBJECT-TYPE
        SYNTAX        SEQUENCE OF RcPrQosEgressQosToExpEntry
        MAX-ACCESS    not-accessible
        STATUS        current
        DESCRIPTION   "This table is used to specify the QOS to
                      Mpls EXP bit field (QOS->Exp bit) mapping on packet
                      egress."
        ::= { rcPrQos 8 }

rcPrQosEgressQosToExpEntry OBJECT-TYPE
        SYNTAX        RcPrQosEgressQosToExpEntry
        MAX-ACCESS    not-accessible
        STATUS        current
        DESCRIPTION   "Entry containing information of Qos->Exp bit mapping"
        INDEX         { rcPrQosEgressQosToExpIndex }
        ::= { rcPrQosEgressQosToExpTable 1 }

RcPrQosEgressQosToExpEntry ::= SEQUENCE {
                rcPrQosEgressQosToExpIndex      INTEGER,
                rcPrQosEgressQosToExpRowStatus  RowStatus 
        }

rcPrQosEgressQosToExpIndex OBJECT-TYPE
        SYNTAX        INTEGER (1..8)
        MAX-ACCESS    not-accessible
        STATUS        current
        DESCRIPTION   "Used to uniquely identify a row in this table."
        ::= { rcPrQosEgressQosToExpEntry 1 }

rcPrQosEgressQosToExpRowStatus  OBJECT-TYPE
        SYNTAX        RowStatus
        MAX-ACCESS    read-write
        STATUS        current
        DESCRIPTION   "Create/delete operations for this entry."
        ::= { rcPrQosEgressQosToExpEntry 4}

--
-- The rcPrFilter group
--

rcPrFilterScalars OBJECT IDENTIFIER ::= { rcPrFilter 1 }

rcPrFilterAclTableSize  OBJECT-TYPE
     SYNTAX             INTEGER (1..2048)
     MAX-ACCESS         read-only
     STATUS             current
     DESCRIPTION        "Used to indicate the number of Acl entries
                        in the rcPrFilterAclTable.  Default table size is 0
                        until the administrator configures any Acl entries."
     ::= { rcPrFilterScalars 2 }

rcPrFilterAceTableSize OBJECT-TYPE
     SYNTAX             INTEGER (0..16384)
     MAX-ACCESS         read-only
     STATUS             current
     DESCRIPTION        "Used to indicate the number of Ace entries in the
                        rcPrFilterAceTable. Default table size is 0 until the
                        administrator configures any Ace entries. The maximum
			size is # of Acls multiplied by # of Aces."
     ::= { rcPrFilterScalars 3 }

rcPrFilterAclBufferWrap OBJECT-TYPE
     SYNTAX             TruthValue
     MAX-ACCESS         read-write
     STATUS             current
     DESCRIPTION        "Used to enable or disable buffer wrapping for 
                         filters log."
     ::= { rcPrFilterScalars 4 }

rcPrFilterAclClearLog OBJECT-TYPE
     SYNTAX             TruthValue
     MAX-ACCESS         read-write
     STATUS             current
     DESCRIPTION        "Used to clear the filter Logs collected."
     ::= { rcPrFilterScalars 5 }

--
-- Power Ranger (PR) Acl MIB specification
--
--   o    The Access Control List (Acl) mib defines management objects for
--        configuration information of the hardware-assisted filtering feature.
--
--   o    Acl is a group of filtering rules organized in an ordered list.
--
--   o    A filtering rule in the Acl is called an Access Control Entry (Ace).
--
--   o	  Max of 2k ACLs.
--	  Each ACL can have a maximum of 2k ACEs. Ports are assigned 
--	  from 1-500 and VLANs are assigned from 501-1000.
--
--   o	  Max of 10k ACEs; each ACE belongs to a single ACL. Precedence
--	  is determined by the Ace-Id (lower Ace-Id means higher precedence).
--

rcPrFilterAct OBJECT IDENTIFIER ::= { rcPrFilter 2 }

-- ACT Table

rcPrFilterActTable OBJECT-TYPE
        SYNTAX          SEQUENCE OF RcPrFilterActEntry
        MAX-ACCESS      not-accessible
        STATUS          current 
        DESCRIPTION     "A table of Acts to store information of each Act
                         entry. This table is indexed by the Act Id."
        ::= { rcPrFilterAct 1 }

rcPrFilterActEntry OBJECT-TYPE
        SYNTAX          RcPrFilterActEntry
        MAX-ACCESS      not-accessible
        STATUS          current 
        DESCRIPTION     "One Act Entry holding Act information."
        INDEX           { rcPrFilterActId }
        ::= { rcPrFilterActTable 1 }

RcPrFilterActEntry ::= SEQUENCE {
        rcPrFilterActId              INTEGER,
        rcPrFilterActName            DisplayString,
        rcPrFilterActArpAttrs        INTEGER, 
        rcPrFilterActEthernetAttrs   INTEGER,
        rcPrFilterActIpAttrs         INTEGER,
        rcPrFilterActProtocolAttrs   INTEGER,
        rcPrFilterActApply           TruthValue,
        rcPrFilterActRowStatus       RowStatus,
        rcPrFilterActIpv6Attrs       INTEGER
}

rcPrFilterActId OBJECT-TYPE
        SYNTAX          INTEGER (1..4096)
        MAX-ACCESS      read-only
        STATUS          current
        DESCRIPTION     "A table of Acts to store information of each 
                        Act. This table is indexed by the Act Id."
        ::= { rcPrFilterActEntry 1 }

rcPrFilterActName OBJECT-TYPE
        SYNTAX          DisplayString (SIZE (0..32))
        MAX-ACCESS      read-write
        STATUS          current 
        DESCRIPTION     "A descriptive name chosen by the administrator 
	                for the Act Entry."
        ::= { rcPrFilterActEntry 2 }

rcPrFilterActArpAttrs OBJECT-TYPE
        SYNTAX        	INTEGER (0..1)
        MAX-ACCESS    	read-write
        STATUS          current	
        DESCRIPTION   	"Value is one or multiple (logical 'OR' of the 
			following):
				none(0),
	                  	operation(1)
			none:      No Arp Attrs are selected or to clear 
			           other choices.
			operation: Only valid option for Arp attributes."
	DEFVAL		{ 0 }
        ::= { rcPrFilterActEntry 3 }

rcPrFilterActEthernetAttrs OBJECT-TYPE
         SYNTAX        	INTEGER (0..63)
        MAX-ACCESS      read-write
        STATUS          current 
        DESCRIPTION     "Value is one or multiple of the following:
			    none(0),
                            srcMac(1),
			    dstMac(2),
			    etherType(4),
			    port(8),
                            vlan(16),
			    vlanTagPrio(32)
			none: If selected then unselect all other selections."
	DEFVAL		{ 0 }
        ::= { rcPrFilterActEntry 4 }

rcPrFilterActIpAttrs OBJECT-TYPE
        SYNTAX        	INTEGER (0..63)
        MAX-ACCESS      read-write
        STATUS          current 
        DESCRIPTION     "Value is one or multiple of the following:
			    none(0),
                            srcIp(1),
			    dstIp(2),
			    ipFragFlag(4),
			    ipOptions(8),
			    ipProtoType(16),
                            dscp(32) 
			none: If selected then unselect all other selections."
	DEFVAL		{ 0 }
        ::= { rcPrFilterActEntry 5 }

rcPrFilterActProtocolAttrs OBJECT-TYPE
        SYNTAX        	INTEGER (0..63)
        MAX-ACCESS      read-write
        STATUS          current 
        DESCRIPTION     "Value is one or multiple of the following:
                            none(0),
                            tcpSrcPort(1),
			    udpSrcPort(2),
			    tcpDstPort(4),
			    udpDstPort(8),
			    tcpFlags(16),
                            icmpMsgType(32) 
			none: If selected then unselect all other selections."
	DEFVAL		{ 0 }
        ::= { rcPrFilterActEntry 6 }

rcPrFilterActApply OBJECT-TYPE
        SYNTAX          TruthValue
        MAX-ACCESS      read-write
        STATUS          current 
        DESCRIPTION    "When apply is issued by the administrator,
                        the ACT attributes cannot be modified."
        DEFVAL          { false }
        ::= { rcPrFilterActEntry 7 }

rcPrFilterActRowStatus  OBJECT-TYPE
        SYNTAX          RowStatus
        MAX-ACCESS      read-write
        STATUS          current 
        DESCRIPTION     "Create/delete operations for this entry. The
                        entry cannot be modified or deleted while there 
                        are Acls configured with this Act entry."
        ::= { rcPrFilterActEntry 8}

rcPrFilterActIpv6Attrs OBJECT-TYPE
        SYNTAX          INTEGER (0..63)
        MAX-ACCESS      read-write
        STATUS          current 
        DESCRIPTION     "Value is one or multiple of the following:
                            none(0),
                            srcIpv6(1),
                            dstIpv6(4),
                            nextHdr(16),
                        none: If selected then unselect all other selections."
        DEFVAL          { 0 }
        ::= { rcPrFilterActEntry 9 }

-- Act Pattern Table to store the template

rcPrFilterActPatternTable OBJECT-TYPE
     SYNTAX             SEQUENCE OF RcPrFilterActPatternEntry
     MAX-ACCESS         not-accessible
     STATUS             current 
     DESCRIPTION        "A table of user-defined parameters of  Acls to
                        store information of each Acl. This table is indexed
                        by the Act Id and PatternIndex."
     ::= { rcPrFilterAct 2 }

rcPrFilterActPatternEntry OBJECT-TYPE
     SYNTAX             RcPrFilterActPatternEntry
     MAX-ACCESS         not-accessible
     STATUS             current
     DESCRIPTION        "Entry containing Configuration information for a
                        particular Act."
     INDEX              { rcPrFilterActPatternActId,
                          rcPrFilterActPatternIndex }
     ::= { rcPrFilterActPatternTable 1 }

RcPrFilterActPatternEntry ::= SEQUENCE {
        rcPrFilterActPatternActId     INTEGER,
        rcPrFilterActPatternIndex     INTEGER,
        rcPrFilterActPatternName      DisplayString,
        rcPrFilterActPatternBase      INTEGER,
        rcPrFilterActPatternOffset    INTEGER,
        rcPrFilterActPatternLength    INTEGER,
        rcPrFilterActPatternRowStatus RowStatus
        }

rcPrFilterActPatternActId OBJECT-TYPE
     SYNTAX             INTEGER (1..4096)
     MAX-ACCESS         read-only
     STATUS             current 
     DESCRIPTION        "An index to the ActPatternEntry, a unique 
	                identifier for Act entry in the range of Table 
			Size."
     ::= { rcPrFilterActPatternEntry 1 }

rcPrFilterActPatternIndex OBJECT-TYPE
     SYNTAX             INTEGER (1..16)
     MAX-ACCESS         read-only
     STATUS             current 
     DESCRIPTION        "Indexes each user defined field pattern in an
                        Acl entry. In this release only 3 patterns are
                        allowed per ACT but we can have multiple 
 			patterns per ACL." 
     ::= { rcPrFilterActPatternEntry 2 }

rcPrFilterActPatternName OBJECT-TYPE
     SYNTAX             DisplayString (SIZE (0..32))
     MAX-ACCESS         read-write
     STATUS             current 
     DESCRIPTION        "A descriptive name chosen by the administrator for
                        the Acl Pattern Entry."
     ::= { rcPrFilterActPatternEntry 3 }

rcPrFilterActPatternBase OBJECT-TYPE
     SYNTAX             INTEGER {
                            none(0),
                            etherBegin(1),
                            macDstBegin(2),
                            macSrcBegin(3),
                            ethTypeLenBegin(4),
                            arpBegin(5),
                            ipHdrBegin(6),
                            ipOptionsBegin(7),
                            ipPayloadBegin(8),
                            ipTosBegin(9),
                            ipProtoBegin(10),
                            ipSrcBegin(11),
                            ipDstBegin(12),
                            tcpBegin(13),
                            tcpSrcportBegin(14),
                            tcpDstportBegin(15),
                            tcpFlagsEnd(16),
                            udpBegin(17),
                            udpSrcportBegin(18),
                            udpDstportBegin(19),
                            etherEnd(20),
                            ipHdrEnd(21),
                            icmpMsgBegin(22),
                            tcpEnd(23),
                            udpEnd(24),
                            ipv6HdrBegin(25)
                        }
     MAX-ACCESS         read-write
     STATUS             current
     DESCRIPTION        "User defined fields from headers to be used in
                        the Aces of the Acl."
     DEFVAL             { none }
     ::= { rcPrFilterActPatternEntry 4 }

rcPrFilterActPatternOffset OBJECT-TYPE -- MA/DZ to confirm maximum
     SYNTAX             INTEGER (0..25)
     MAX-ACCESS         read-write
     STATUS             current
     DESCRIPTION        "Set Offset in bytes to the beginning offset of the user
                        defined field with selected header option as base."
     DEFVAL              { 0 }
     ::= { rcPrFilterActPatternEntry 5 }

rcPrFilterActPatternLength OBJECT-TYPE
     SYNTAX             INTEGER (1..15)
     MAX-ACCESS         read-write
     STATUS             current
     DESCRIPTION        "The number of bytes to extract beginning from the
                        offset is set in rcPrFilterActPatternLength. 
			Only 1-15 are valid."
     DEFVAL             { 1 }
     ::= { rcPrFilterActPatternEntry 6 }

rcPrFilterActPatternRowStatus OBJECT-TYPE
     SYNTAX             RowStatus
     MAX-ACCESS         read-write
     STATUS             current
     DESCRIPTION        "Create/delete operations for this entry."
     ::= { rcPrFilterActPatternEntry 7 }

rcPrFilterAcl OBJECT IDENTIFIER ::= { rcPrFilter 3 }

-- ACL Table

rcPrFilterAclTable      OBJECT-TYPE
     SYNTAX             SEQUENCE OF RcPrFilterAclEntry
     MAX-ACCESS         not-accessible
     STATUS             current
     DESCRIPTION        "A table of Acls to store information of each Acl.
                         This table is indexed by the Acl Id."
     ::= { rcPrFilterAcl 1 }

rcPrFilterAclEntry      OBJECT-TYPE
     SYNTAX             RcPrFilterAclEntry
     MAX-ACCESS         not-accessible
     STATUS             current
     DESCRIPTION        "Entry containing Configuration information for
                        a particular Acl."
     INDEX              { rcPrFilterAclId }
     ::= { rcPrFilterAclTable 1 }

RcPrFilterAclEntry ::= SEQUENCE {
        rcPrFilterAclId                      INTEGER,
        rcPrFilterAclName                    DisplayString,
        rcPrFilterAclType                    INTEGER,
        rcPrFilterAclAceListSize             INTEGER,
        rcPrFilterAclDefaultAction           INTEGER,
        rcPrFilterAclState                   EnableValue,
        rcPrFilterAclVlanList                IdList,
        rcPrFilterAclPortList                PortSet,
        rcPrFilterAclRowStatus               RowStatus,
        rcPrFilterAclNumVlanIds              INTEGER,
        rcPrFilterAclPktType                 INTEGER,
        rcPrFilterAclControlPktRule          INTEGER,
	rcPrFilterAclVlanId                  Integer32,
	rcPrFilterAclMltId                   Integer32,
        rcPrFilterAclDstPortList             PortSet,
        rcPrFilterAclIpfixState              EnableValue
        }

rcPrFilterAclId OBJECT-TYPE
     SYNTAX             INTEGER (1..2048)
     MAX-ACCESS         read-only
     STATUS             current
     DESCRIPTION        "A unique identifier for Acl entry in the range
                        of Table Size."
     ::= { rcPrFilterAclEntry 1 }

rcPrFilterAclName OBJECT-TYPE
     SYNTAX             DisplayString (SIZE (0..32))
     MAX-ACCESS         read-write
     STATUS             current
     DESCRIPTION        "A descriptive name chosen by the administrator for
                        the Acl Entry."
     ::= { rcPrFilterAclEntry 3 }

rcPrFilterAclType OBJECT-TYPE
     SYNTAX             INTEGER {
                            inVlan(1),
                            outVlan(2),
                            inPort(3),
                            outPort(4)
                        }
     MAX-ACCESS         read-write
     STATUS             current
     DESCRIPTION        "An Acl can be vlan-based or port-based.  An Ace 
			has a capability to match packets classified as
			'ingress' and 'egress'. An ingress packet is 
			assigned a value 'in' and an egress packet is 
			assigned a value 'out'."
     ::= { rcPrFilterAclEntry 4 }

rcPrFilterAclAceListSize OBJECT-TYPE
     SYNTAX             INTEGER (0..2000)
     MAX-ACCESS         read-only
     STATUS             current
     DESCRIPTION        "Indicates the number of Aces in a particular Acl."
     ::= { rcPrFilterAclEntry 5 }

rcPrFilterAclDefaultAction OBJECT-TYPE
     SYNTAX              INTEGER {
                             deny(1),
                             permit(2)
                         }
     MAX-ACCESS          read-write
     STATUS              current
     DESCRIPTION         "Indicates action to be taken when none of the
                         Aces in the Acl match."
     DEFVAL              { permit }
     ::= { rcPrFilterAclEntry 6 }

rcPrFilterAclState OBJECT-TYPE
     SYNTAX             EnableValue
     MAX-ACCESS         read-write
     STATUS             current
     DESCRIPTION        "Enables/Disables the state of all Aces in the Acl"
     DEFVAL             { enable }
     ::= { rcPrFilterAclEntry 8 }

rcPrFilterAclVlanList OBJECT-TYPE
     SYNTAX             IdList(SIZE(0..4096))
     MAX-ACCESS         read-write
     STATUS             current
     DESCRIPTION        "An array used to indicate all the VLANs to be
                        associated with this Acl Entry. At present, only 4k 
			Vlans are supported."
     ::= { rcPrFilterAclEntry 9 }

rcPrFilterAclPortList OBJECT-TYPE
     SYNTAX             PortSet
     MAX-ACCESS         read-write
     STATUS             current
     DESCRIPTION        "Indicates the ports to be added to this Acl Entry."
     ::= { rcPrFilterAclEntry 10 }

rcPrFilterAclRowStatus OBJECT-TYPE
     SYNTAX             RowStatus
     MAX-ACCESS         read-write
     STATUS             current
     DESCRIPTION        "Create/delete operations for the entry. Deleting
                        a non-empty Acl results in deletion of member Aces
                        and then the Acl."
     ::= { rcPrFilterAclEntry 11 }

rcPrFilterAclNumVlanIds OBJECT-TYPE
     SYNTAX             INTEGER (1..4096) 
     MAX-ACCESS         read-only
     STATUS             current
     DESCRIPTION        "Used to Indicate the number of VLAN ID's that
                         are stored in the rcPrFilterAclVlanList."
     ::= { rcPrFilterAclEntry 12 }

rcPrFilterAclPktType OBJECT-TYPE
     SYNTAX             INTEGER {
                            ipv4(1),
                            ipv6(2)
                        }
     MAX-ACCESS         read-write
     STATUS             current
     DESCRIPTION        "Indicates the packet type that thsi ACL is
                        applicable to."
     DEFVAL             { ipv4 }
     ::= { rcPrFilterAclEntry 13 }

rcPrFilterAclControlPktRule OBJECT-TYPE
     SYNTAX             INTEGER {
                            deny(1),
                            permit(2)
                        }
     MAX-ACCESS         read-write
     STATUS             current
     DESCRIPTION        "When the rcPrFilterAclDefaultAction object is set
                         to deny then control packets follow this rule.
                         Otherwise, the object value can be ignored."
     DEFVAL             { permit }
     ::= { rcPrFilterAclEntry 14 }

rcPrFilterAclVlanId OBJECT-TYPE
     SYNTAX             Integer32(0..4084)
     MAX-ACCESS         read-write
     STATUS             current
     DESCRIPTION        "Destination Vlan Id for mirroring the packets.
                         The value 0 means no vlan is being mirrored. 
                         When the value of rcPrFilterAclVlanId is non-zero,
                         the values of rcPrFilterAclMltId and
                         rcPrFilterAclDstPortList must be 0."
     DEFVAL             { 0 }
     ::= { rcPrFilterAclEntry 15 }

rcPrFilterAclMltId OBJECT-TYPE
     SYNTAX             Integer32(0..512)
     MAX-ACCESS         read-write
     STATUS             current
     DESCRIPTION        "Destination Mlt Id for mirroring the packets. 
                         The value 0 means no mlt is being mirrored.
                         When the value of rcPrFilterAclMltId is non-zero,
                         the values of rcPrFilterAclVlanId and
                         rcPrFilterAclDstPortList must be 0."
     DEFVAL             { 0 }
     ::= { rcPrFilterAclEntry 16 }

rcPrFilterAclDstPortList OBJECT-TYPE
     SYNTAX             PortSet
     MAX-ACCESS         read-write
     STATUS             current
     DESCRIPTION        "Destination Port List for mirroring the packets.
                         The value 0 means no port(s) is being mirrored.
                         When the value of rcPrFilterAclDstPortList is non-zero,
                         the values of rcPrFilterAclVlanId and
                         rcPrFilterAclMltId must be 0."
     ::= { rcPrFilterAclEntry 17 }

rcPrFilterAclIpfixState OBJECT-TYPE
     SYNTAX          EnableValue
     MAX-ACCESS      read-write
     STATUS          current
     DESCRIPTION     "Value indicating whether ipfix option on the
                      Acl is enabled."
     DEFVAL          { disable }
     ::= { rcPrFilterAclEntry 18 }

 -- Acl Stats Table

rcPrFilterAclStatsTable      OBJECT-TYPE
     SYNTAX             SEQUENCE OF RcPrFilterAclStatsEntry
     MAX-ACCESS         not-accessible
     STATUS             current
     DESCRIPTION        "A table of Acls Statistics entries to store the 
			Default Acl statistics for each Acl. 
			This table is indexed by the Acl Id."
     ::= { rcPrFilterAcl 2 }

rcPrFilterAclStatsEntry      OBJECT-TYPE
     SYNTAX             RcPrFilterAclStatsEntry
     MAX-ACCESS         not-accessible
     STATUS             current
     DESCRIPTION        "Entry containing default statistics information for
                        a particular Acl."
     INDEX              { rcPrFilterAclStatsAclId }
     ::= { rcPrFilterAclStatsTable 1 }

RcPrFilterAclStatsEntry ::= SEQUENCE {
        rcPrFilterAclStatsAclId                      INTEGER,
        rcPrFilterAclStatsClear                   TruthValue,
        rcPrFilterAclStatsMatchDefaultSecurityPkts      Counter64,
        rcPrFilterAclStatsMatchDefaultSecurityOctets    Counter64,
        rcPrFilterAclStatsMatchDefaultQosPkts           Counter64,
        rcPrFilterAclStatsMatchDefaultQosOctets         Counter64,
        rcPrFilterAclStatsMatchGlobalSecurityPkts       Counter64,
        rcPrFilterAclStatsMatchGlobalSecurityOctets     Counter64,
        rcPrFilterAclStatsMatchGlobalQosPkts            Counter64,
        rcPrFilterAclStatsMatchGlobalQosOctets          Counter64
        }


rcPrFilterAclStatsAclId OBJECT-TYPE
     SYNTAX             INTEGER (1..2048)
     MAX-ACCESS         read-only
     STATUS             current
     DESCRIPTION        "A unique identifier for Acl entry in the range
                        of Table Size."
     ::= { rcPrFilterAclStatsEntry 1 }

rcPrFilterAclStatsClear  OBJECT-TYPE
     SYNTAX             TruthValue
     MAX-ACCESS         read-write
     STATUS             current
     DESCRIPTION        "Clear default statistics for ACL Filters."
     ::= { rcPrFilterAclStatsEntry 4 }

rcPrFilterAclStatsMatchDefaultSecurityPkts OBJECT-TYPE
     SYNTAX             Counter64
     MAX-ACCESS         read-only
     STATUS             current
     DESCRIPTION        "Security packet count of traffic not matching any of the
                         ACE rules or hits on Default Action where the count bit
                         is turned on in ACL Global Action."
     ::= { rcPrFilterAclStatsEntry 5 }

rcPrFilterAclStatsMatchDefaultSecurityOctets OBJECT-TYPE
     SYNTAX             Counter64
     MAX-ACCESS         read-only
     STATUS             current
     DESCRIPTION        "Security octet count of traffic not matching any of the
                         ACE rules or hits on Default Action where the count bit
                         is turned on in ACL Global Action."
     ::= { rcPrFilterAclStatsEntry 6 }

rcPrFilterAclStatsMatchDefaultQosPkts OBJECT-TYPE
     SYNTAX             Counter64
     MAX-ACCESS         read-only
     STATUS             current
     DESCRIPTION        "QOS packet count of traffic not matching any of the
                         ACE rules or hits on Default Action where the count bit
                         is turned on in ACL Global Action."
     ::= { rcPrFilterAclStatsEntry 7 }

rcPrFilterAclStatsMatchDefaultQosOctets OBJECT-TYPE
     SYNTAX             Counter64
     MAX-ACCESS         read-only
     STATUS             current
     DESCRIPTION        "QOS octet count of traffic not matching any of the
                         ACE rules or hits on Default Action where the count bit
                         is turned on in ACL Global Action."
     ::= { rcPrFilterAclStatsEntry 8 }

rcPrFilterAclStatsMatchGlobalSecurityPkts OBJECT-TYPE
     SYNTAX             Counter64
     MAX-ACCESS         read-only
     STATUS             current
     DESCRIPTION        "Security packet count of traffic matching any of the
                         ACE rules or hits on Default Action where the count bit
                         is turned on in ACL Global Action."
     ::= { rcPrFilterAclStatsEntry 9 }

rcPrFilterAclStatsMatchGlobalSecurityOctets OBJECT-TYPE
     SYNTAX             Counter64
     MAX-ACCESS         read-only
     STATUS             current
     DESCRIPTION        "Security octet count of traffic matching any of the
                         ACE rules or hits on Default Action where the count bit
                         is turned on in ACL Global Action."
     ::= { rcPrFilterAclStatsEntry 10 }

rcPrFilterAclStatsMatchGlobalQosPkts OBJECT-TYPE
     SYNTAX             Counter64
     MAX-ACCESS         read-only
     STATUS             current
     DESCRIPTION        "QOS packet count of traffic matching any of the
                         ACE rules or hits on Default Action where the count bit
                         is turned on in ACL Global Action."
     ::= { rcPrFilterAclStatsEntry 11 }

rcPrFilterAclStatsMatchGlobalQosOctets OBJECT-TYPE
     SYNTAX             Counter64
     MAX-ACCESS         read-only
     STATUS             current
     DESCRIPTION        "QOS octet count of traffic matching any of the
                         ACE rules or hits on Default Action where the count bit
                         is turned on in ACL Global Action."
     ::= { rcPrFilterAclStatsEntry 12 }



-- Ace Table

rcPrFilterAce OBJECT IDENTIFIER ::= { rcPrFilter 4 }

-- Ace information is organized in 28 entries:
-- rcPrFilterAceEntry
-- rcPrFilterAceEthSrcAddrEntry
-- rcPrFilterAceEthDstAddrEntry 
-- rcPrFilterAceEthEtherEntry
-- rcPrFilterAceEthVlanTagPrioEntry
-- rcPrFilterAceEthPortEntry
-- rcPrFilterAceEthVlanIdEntry
-- rcPrFilterAceArpEntry
-- rcPrFilterAceIpSrcAddrEntry
-- rcPrFilterAceIpDstAddrEntry
-- rcPrFilterAceIpDscpEntry
-- rcPrFilterAceIpProtoEntry
-- rcPrFilterAceIpOptionsEntry
-- rcPrFilterAceIpFragEntry
-- rcPrFilterAceProtoIcmpMsgTypeEntry
-- rcPrFilterAceProtoTcpFlagsEntry
-- rcPrFilterAceStatsEntry
-- rcPrFilterAceEthShowEntry
-- rcPrFilterAceIpShowEntry
-- rcPrFilterAceProtoShowEntry
-- rcPrFilterAceProtoSrcPortEntry
-- rcPrFilterAceProtoDstPortEntry
-- rcPrFilterAceProtoTcpOptionEntry

rcPrFilterAceTable      OBJECT-TYPE
     SYNTAX             SEQUENCE OF RcPrFilterAceEntry
     MAX-ACCESS         not-accessible
     STATUS             current
     DESCRIPTION        "A table of Aces to store information of each Ace
                        in context of its parent Acl. This is indexed by
                        AclId and AceId."
     ::= { rcPrFilterAce 1 }

rcPrFilterAceEntry      OBJECT-TYPE
     SYNTAX             RcPrFilterAceEntry
     MAX-ACCESS         not-accessible
     STATUS             current
     DESCRIPTION        "One Ace entry holding Ace information. Ace is a
                        member of one Acl."
     INDEX              { rcPrFilterAceAclId,
                          rcPrFilterAceId }
     ::= {rcPrFilterAceTable 1}

RcPrFilterAceEntry ::= SEQUENCE {
        rcPrFilterAceAclId              INTEGER,
        rcPrFilterAceId                 INTEGER,
        rcPrFilterAceName               DisplayString,
        rcPrFilterAceMode               INTEGER,
        rcPrFilterAceRemarkDscp         INTEGER,
        rcPrFilterAceRemarkDot1Priority INTEGER,
        rcPrFilterAceRedirectNextHop    IpAddress,
        rcPrFilterAceRedirectUnreach    INTEGER,
        rcPrFilterAcePolice		INTEGER,
        rcPrFilterAceAdminState         EnableValue,
        rcPrFilterAceOperState          INTEGER,
        rcPrFilterAceMltIndex           INTEGER,
        rcPrFilterAceRowStatus          RowStatus,
        rcPrFilterAceIpfixState         EnableValue,
        rcPrFilterAceRedirectNextHopIpv6   Ipv6Address, 
        rcPrFilterAceDstPortList        PortSet,
        rcPrFilterAceDstVlanId          Integer32,
        rcPrFilterAceDstMltId           Integer32,
        rcPrFilterAceInternalQos        Integer32,
	rcPrFilterAceCount	        EnableValue,
	rcPrFilterAceLog	        EnableValue,
	rcPrFilterAceCopytoPcap	        EnableValue,
        rcPrFilterAceDstIp              IpAddress,
        rcPrFilterAceDstIpTtl           Integer32,
        rcPrFilterAceDstIpDscp          INTEGER
        }

rcPrFilterAceAclId OBJECT-TYPE
     SYNTAX             INTEGER (1..2048)
     MAX-ACCESS         read-only
     STATUS             current
     DESCRIPTION        "An index to the AceEntry, a unique 
	                identifier for Acl entry in the range of Table 
			Size."
     ::= { rcPrFilterAceEntry 1 }

rcPrFilterAceId OBJECT-TYPE
     SYNTAX             INTEGER (1..2000)
     MAX-ACCESS         read-only
     STATUS             current
     DESCRIPTION        "AceId uniquely identifies one Ace entry."
     ::= { rcPrFilterAceEntry 2 }

rcPrFilterAceName OBJECT-TYPE
     SYNTAX             DisplayString (SIZE (0..32))
     MAX-ACCESS         read-write
     STATUS             current
     DESCRIPTION        "A descriptive name chosen by the administrator.
                        System automatically assigns a name if the user
                        has not assigned one."
     ::= { rcPrFilterAceEntry 3 }

rcPrFilterAceMode       OBJECT-TYPE
     SYNTAX             INTEGER {
                            none(0),
                            deny(1),
                            permit(2)
                        }
     MAX-ACCESS         read-write
     STATUS             current
     DESCRIPTION        "Operating Mode associated with the Ace is effective
                        on the packets matching this Ace." 
     DEFVAL             { none }
     ::= { rcPrFilterAceEntry 4 }

rcPrFilterAceRemarkDscp OBJECT-TYPE
     SYNTAX             INTEGER {
                            phbcs0(0),
                            phbcs1(8),
                            phbaf11(10),
                            phbaf12(12),
                            phbaf13(14),
                            phbcs2(16),
                            phbaf21(18),
                            phbaf22(20),
                            phbaf23(22),
                            phbcs3(24),
                            phbaf31(26),
                            phbaf32(28),
                            phbaf33(30),
                            phbcs4(32),
                            phbaf41(34),
                            phbaf42(36),
                            phbaf43(38),
                            phbcs5(40),
                            phbef(46),
                            phbcs6(48),
                            phbcs7(56),
                            disable(256) -- Invalid ToS/Dscp value
                        }
     MAX-ACCESS         read-write
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to mark specific diffserv class traffic.
                        Set the field value to desired integer dscp code for
                        rcPrFilterAceRemarkDscp field to mark non-standard
                        traffic classes and local use PHBs."
     DEFVAL             { 256 }
     ::= { rcPrFilterAceEntry 5 }

rcPrFilterAceRemarkDot1Priority OBJECT-TYPE
     SYNTAX             INTEGER {
                            zero(0),
                            one(1),
                            two(2),
                            three(3),
                            four(4),
                            five(5),
                            six(6),
                            seven(7),
                            disable(8)
                        }
     MAX-ACCESS         read-write
     STATUS             current
     DESCRIPTION        "Dot1 Priority as described by Layer 2 standards,
                        802.1Q, 802.1P."
     DEFVAL             { disable }
     ::= { rcPrFilterAceEntry 6 }

rcPrFilterAceRedirectNextHop OBJECT-TYPE
     SYNTAX             IpAddress
     MAX-ACCESS         read-write
     STATUS             current
     DESCRIPTION        "Redirect matching IP traffic to the next hop."
     DEFVAL             { '00000000'H }    -- 0.0.0.0
     ::= { rcPrFilterAceEntry 7 }

rcPrFilterAceRedirectUnreach OBJECT-TYPE
     SYNTAX             INTEGER {
                            deny(1),
                            permit(2)
                        }
     MAX-ACCESS         read-write
     STATUS              current
     DESCRIPTION        "Set the desired behavior for redirected traffic in
                        case the specified next-hop is not reachable."
     DEFVAL             { deny }
     ::= { rcPrFilterAceEntry 8 }

rcPrFilterAcePolice  OBJECT-TYPE
     SYNTAX          INTEGER (0..16000)
     MAX-ACCESS      read-write
     STATUS          current
     DESCRIPTION     "Policing profile Identifier. Set the desired policing
                     profile identifier. Set the value to 0 when policing
                     is not desired."
     DEFVAL          { 0 }
     ::= { rcPrFilterAceEntry 9 }

rcPrFilterAceAdminState OBJECT-TYPE
     SYNTAX          EnableValue
     MAX-ACCESS      read-write
     STATUS          current
     DESCRIPTION     "Value indicating whether the Ace is enabled. 
		     An Ace can only be modified if it is disabled."
     DEFVAL          { disable }
     ::= { rcPrFilterAceEntry 10 }

rcPrFilterAceOperState  OBJECT-TYPE
     SYNTAX          INTEGER {
                         up (1),
                         down (2)
                     }
     MAX-ACCESS      read-only
     STATUS          current
     DESCRIPTION     "The current operational state of the Ace."
     ::= { rcPrFilterAceEntry 11 }

rcPrFilterAceMltIndex OBJECT-TYPE
     SYNTAX             INTEGER (0..16)
     MAX-ACCESS         read-write
     STATUS             current
     DESCRIPTION        "If this action is specified, it will 
                         basically override the mlt-index picked 
                         by the mlt algorithm, when a packet is 
                         being sent out on MLT ports."
     DEFVAL             { 0 } 
     ::= { rcPrFilterAceEntry 18 }

rcPrFilterAceRowStatus OBJECT-TYPE
     SYNTAX             RowStatus
     MAX-ACCESS         read-write
     STATUS             current
     DESCRIPTION        "Create/delete operations for this entry."
     ::= { rcPrFilterAceEntry 19 }

rcPrFilterAceIpfixState OBJECT-TYPE
     SYNTAX          EnableValue
     MAX-ACCESS      read-write
     STATUS          current
     DESCRIPTION     "Value indicating whether ipfix option on the
                      Ace is enabled."
     DEFVAL          { disable }
     ::= { rcPrFilterAceEntry 20 }

rcPrFilterAceRedirectNextHopIpv6 OBJECT-TYPE
     SYNTAX             Ipv6Address
     MAX-ACCESS         read-write
     STATUS             current
     DESCRIPTION        "Redirect matching IPv6 traffic to the next hop."
     ::= { rcPrFilterAceEntry 21 }

rcPrFilterAceDstPortList OBJECT-TYPE
        SYNTAX        PortSet
        MAX-ACCESS    read-create
        STATUS        current
        DESCRIPTION   "Destination Port List for mirroring the packets."
        ::= { rcPrFilterAceEntry 22 }

rcPrFilterAceDstVlanId OBJECT-TYPE
        SYNTAX        Integer32(0..4084)
        MAX-ACCESS    read-create
        STATUS        current
        DESCRIPTION   "Destination Vlan to mirror the packets."
        ::= { rcPrFilterAceEntry 23 }

rcPrFilterAceDstMltId OBJECT-TYPE
        SYNTAX        Integer32 (0..512)
        MAX-ACCESS    read-create
        STATUS        current
        DESCRIPTION   "Destination Mlt to mirror the packets."
        ::= { rcPrFilterAceEntry 24 }

rcPrFilterAceInternalQos OBJECT-TYPE
        SYNTAX          Integer32 (0..8)
        MAX-ACCESS      read-write
        STATUS          current
        DESCRIPTION     "Internal QOS Level assigned to the packet flow DefVal = 8 is disable"
        DEFVAL          { 8 }
        ::= { rcPrFilterAceEntry 25 }

rcPrFilterAceCount OBJECT-TYPE
     SYNTAX          EnableValue
     MAX-ACCESS      read-write
     STATUS          current
     DESCRIPTION     "Value indicating whether Count option on the
                      Ace is enabled."
     DEFVAL          { disable }
     ::= { rcPrFilterAceEntry 26 }

rcPrFilterAceLog OBJECT-TYPE
     SYNTAX          EnableValue
     MAX-ACCESS      read-write
     STATUS          current
     DESCRIPTION     "Value indicating whether log option on the
                      Ace is enabled."
     DEFVAL          { disable }
     ::= { rcPrFilterAceEntry 27 }

rcPrFilterAceCopytoPcap OBJECT-TYPE
     SYNTAX          EnableValue
     MAX-ACCESS      read-write
     STATUS          current
     DESCRIPTION     "Value indicating whether copy to pcap option
                      on the Ace is enabled."
     DEFVAL          { disable }
     ::= { rcPrFilterAceEntry 28 }

rcPrFilterAceDstIp OBJECT-TYPE
     SYNTAX        IpAddress
     MAX-ACCESS    read-write
     STATUS        current
     DESCRIPTION   "Destination IP address to mirror the packets."
     ::= { rcPrFilterAceEntry 29 }

rcPrFilterAceDstIpTtl OBJECT-TYPE
     SYNTAX          Integer32 (2..255)
     MAX-ACCESS      read-write
     STATUS          current
     DESCRIPTION     "Ttl value for the mirrored packet when mirror
                      destination is IP.  If other than default,
                      the encapsulated packet will have the given ttl."
     DEFVAL          { 64 }
     ::= { rcPrFilterAceEntry 30 }

rcPrFilterAceDstIpDscp OBJECT-TYPE
     SYNTAX             INTEGER {
                            phbcs0(0),
                            phbcs1(8),
                            phbaf11(10),
                            phbaf12(12),
                            phbaf13(14),
                            phbcs2(16),
                            phbaf21(18),
                            phbaf22(20),
                            phbaf23(22),
                            phbcs3(24),
                            phbaf31(26),
                            phbaf32(28),
                            phbaf33(30),
                            phbcs4(32),
                            phbaf41(34),
                            phbaf42(36),
                            phbaf43(38),
                            phbcs5(40),
                            phbef(46),
                            phbcs6(48),
                            phbcs7(56),
                            disable(256) -- Invalid ToS/Dscp value
                        }
     MAX-ACCESS         read-write
     STATUS             current
     DESCRIPTION        "Dscp value for the mirrored packet when mirror
                        destination is IP.  The 6-bit DSCP field from the
                        ToS byte in Ipv4 header encodes the PHB information
                        per DiffServ standards (Refer to DiffServ RFCs 2474).
                        Set the Dscp to PHB (like EF) or PHB-class(like AF1 which
                        includes AF11, AF12,AF13) to mark specific diffserv class traffic.
                        Set the field value to desired integer dscp code for
                        rcPrFilterAceIpDscp field to mark non-standard
                        traffic classes and local use PHBs."
     DEFVAL             { 256 }
     ::= { rcPrFilterAceEntry 31 }

     
-- ACE Ethernet Source MAC Address Table

rcPrFilterAceEthSrcAddrTable OBJECT-TYPE
     SYNTAX             SEQUENCE OF RcPrFilterAceEthSrcAddrEntry
     MAX-ACCESS         not-accessible
     STATUS             current
     DESCRIPTION        "A table of Aces to store Ethernet Source MAC
			Address Header information of each Ace in context
                        of its parent Acl."
     ::= { rcPrFilterAce 2 }

rcPrFilterAceEthSrcAddrEntry OBJECT-TYPE
     SYNTAX             RcPrFilterAceEthSrcAddrEntry
     MAX-ACCESS         not-accessible 
     STATUS             current
     DESCRIPTION        "One Ace entry holding Ace Ethernet Source MAC Address
			information. An Ace is a member of one Acl."
     INDEX              { rcPrFilterAceEthSrcAddrAclId,
                          rcPrFilterAceEthSrcAddrAceId }
     ::= { rcPrFilterAceEthSrcAddrTable 1 }

RcPrFilterAceEthSrcAddrEntry ::= SEQUENCE {
        rcPrFilterAceEthSrcAddrAclId	     INTEGER,
        rcPrFilterAceEthSrcAddrAceId	     INTEGER,
        rcPrFilterAceEthSrcAddrList          OCTET STRING,
        rcPrFilterAceEthSrcAddrListCount     INTEGER,
        rcPrFilterAceEthSrcAddrOper          INTEGER,
        rcPrFilterAceEthSrcAddrRowStatus     RowStatus,
	rcPrFilterAceEthSrcAddrOperMask      DisplayString
        }

rcPrFilterAceEthSrcAddrAclId OBJECT-TYPE
     SYNTAX             INTEGER (1..2048)
     MAX-ACCESS         read-only 
     STATUS             current
     DESCRIPTION        "An index to the AceEthernetEntry, a unique 
	                identifier for Acl entry in the range of Table 
			Size."
     ::= { rcPrFilterAceEthSrcAddrEntry 1 }

rcPrFilterAceEthSrcAddrAceId OBJECT-TYPE
     SYNTAX             INTEGER (1..2000)
     MAX-ACCESS         read-only 
     STATUS             current
     DESCRIPTION        "An index to the AceEthernetEntry, a unique 
	                identifier for Acl entry in the range of Table 
			Size."
     ::= { rcPrFilterAceEthSrcAddrEntry 2 }

rcPrFilterAceEthSrcAddrList OBJECT-TYPE
     SYNTAX             OCTET STRING (SIZE(0..1500))
     MAX-ACCESS         read-write
     STATUS             current
     DESCRIPTION        "The list of ethernet source address to match." 
     ::= { rcPrFilterAceEthSrcAddrEntry 3 }

rcPrFilterAceEthSrcAddrListCount OBJECT-TYPE
     SYNTAX             INTEGER(1..100)
     MAX-ACCESS         read-write
     STATUS             current
     DESCRIPTION        "Count to store the number of discrete ranges
                        entered for the ethernet src address."
     ::= { rcPrFilterAceEthSrcAddrEntry 4 }

rcPrFilterAceEthSrcAddrOper OBJECT-TYPE
     SYNTAX             INTEGER {
                            eq(1),    -- exact match
			    mask(8)   -- mask
                   }
     MAX-ACCESS         read-write
     STATUS             current
     DESCRIPTION        "Operators for Ace Ethernet Source MAC Address."
     ::= { rcPrFilterAceEthSrcAddrEntry 5 }

rcPrFilterAceEthSrcAddrRowStatus OBJECT-TYPE
     SYNTAX             RowStatus
     MAX-ACCESS         read-write
     STATUS             current
     DESCRIPTION        "Create/delete operations for this entry."
     ::= { rcPrFilterAceEthSrcAddrEntry 6 }

rcPrFilterAceEthSrcAddrOperMask OBJECT-TYPE
     SYNTAX             DisplayString (SIZE(0..14))
     MAX-ACCESS         read-write
     STATUS             current
     DESCRIPTION         "The Mac Address mask value in hex which can
			be set for the rcPrFilterAceEthSrcAddrOper when
			the option selected is mask. It will be empty or
			set to 000000000000 whenrcPrFilterAceEthSrcAddrOper
			is set to 'eq'. In case of the prefix '0x' is
			specified, 14 charaters is max length"
     ::= { rcPrFilterAceEthSrcAddrEntry 7 }

-- ACE Ethernet Destination MAC Address Table

rcPrFilterAceEthDstAddrTable OBJECT-TYPE
     SYNTAX             SEQUENCE OF RcPrFilterAceEthDstAddrEntry
     MAX-ACCESS         not-accessible
     STATUS             current
     DESCRIPTION        "A table of Aces to store Ethernet Destination MAC
			Address Header information of each Ace in context
                        of its parent Acl."
     ::= { rcPrFilterAce 3 }

rcPrFilterAceEthDstAddrEntry OBJECT-TYPE
     SYNTAX             RcPrFilterAceEthDstAddrEntry
     MAX-ACCESS         not-accessible 
     STATUS             current
     DESCRIPTION        "One Ace entry holding Ace Ethernet Destination
 			MAC Address information. An Ace is a member of one 
			Acl." 
     INDEX              { rcPrFilterAceEthDstAddrAclId,
                          rcPrFilterAceEthDstAddrAceId }
     ::= { rcPrFilterAceEthDstAddrTable 1 }

RcPrFilterAceEthDstAddrEntry ::= SEQUENCE {
        rcPrFilterAceEthDstAddrAclId	       INTEGER,
        rcPrFilterAceEthDstAddrAceId	       INTEGER,
        rcPrFilterAceEthDstAddrList	       OCTET STRING,
        rcPrFilterAceEthDstAddrListCount       INTEGER,
        rcPrFilterAceEthDstAddrOper            INTEGER,
        rcPrFilterAceEthDstAddrRowStatus       RowStatus,
	rcPrFilterAceEthDstAddrOperMask        DisplayString
        }

rcPrFilterAceEthDstAddrAclId OBJECT-TYPE
     SYNTAX             INTEGER (1..2048)
     MAX-ACCESS         read-only 
     STATUS             current
     DESCRIPTION        "An index to the AceEthDstAddrEntry, a unique 
	                identifier for Acl entry in the range of Table 
			Size."
     ::= { rcPrFilterAceEthDstAddrEntry 1 }

rcPrFilterAceEthDstAddrAceId OBJECT-TYPE
     SYNTAX             INTEGER (1..2000)
     MAX-ACCESS         read-only 
     STATUS             current
     DESCRIPTION        "An index to the AceEthDstAddrEntry, a unique 
	                identifier for Acl entry in the range of Table 
			Size."
     ::= { rcPrFilterAceEthDstAddrEntry 2 }

rcPrFilterAceEthDstAddrList OBJECT-TYPE
     SYNTAX             OCTET STRING (SIZE(0..1500))
     MAX-ACCESS         read-write
     STATUS             current
     DESCRIPTION        "List of ethernet destination address to 
			match."
     ::= { rcPrFilterAceEthDstAddrEntry 3 }

rcPrFilterAceEthDstAddrListCount OBJECT-TYPE
     SYNTAX             INTEGER(1..100)
     MAX-ACCESS         read-write 
     STATUS             current
     DESCRIPTION        "Count to store the number of discrete ranges
                        entered for the ethernet dst address."
     ::= { rcPrFilterAceEthDstAddrEntry 4 }

rcPrFilterAceEthDstAddrOper OBJECT-TYPE
     SYNTAX             INTEGER {
                            eq(1),    -- exact match
			    mask(8)   -- mask
                        }
     MAX-ACCESS         read-write
     STATUS             current
     DESCRIPTION        "Operators for Ace Ethernet Destination MAC Address."
     ::= { rcPrFilterAceEthDstAddrEntry 5 }

rcPrFilterAceEthDstAddrRowStatus OBJECT-TYPE
     SYNTAX             RowStatus
     MAX-ACCESS         read-write
     STATUS             current
     DESCRIPTION        "Create/delete operations for this entry."
     ::= { rcPrFilterAceEthDstAddrEntry 6 }

rcPrFilterAceEthDstAddrOperMask OBJECT-TYPE
     SYNTAX             DisplayString (SIZE(0..14))
     MAX-ACCESS         read-write
     STATUS             current
     DESCRIPTION         "The Mac Address mask value in hex which can
			be set for the rcPrFilterAceEthDstAddrOper when
			the option selected is mask. It will be empty or
			set to 000000000000 whenrcPrFilterAceEthDstAddrOper
			is set to 'eq'. In case of the prefix '0x' is
			specified, 14 charaters is max length"
     ::= { rcPrFilterAceEthDstAddrEntry 7 }

-- ACE Ethernet Ether Table

rcPrFilterAceEthEtherTable OBJECT-TYPE
     SYNTAX             SEQUENCE OF RcPrFilterAceEthEtherEntry
     MAX-ACCESS         not-accessible
     STATUS             current
     DESCRIPTION        "A table of Aces to store Ethernet Ether Header 
			information of each Ace in context of its parent 
			Acl."
     ::= { rcPrFilterAce 4 }

rcPrFilterAceEthEtherEntry OBJECT-TYPE
     SYNTAX             RcPrFilterAceEthEtherEntry
     MAX-ACCESS         not-accessible 
     STATUS             current
     DESCRIPTION        "One Ace entry holding Ace Ethernet Ether
 			information. An Ace is a member of one Acl." 
     INDEX              { rcPrFilterAceEthEtherAclId,
                          rcPrFilterAceEthEtherAceId } 
     ::= { rcPrFilterAceEthEtherTable 1 }

RcPrFilterAceEthEtherEntry ::= SEQUENCE {
        rcPrFilterAceEthEtherAclId	     INTEGER,
        rcPrFilterAceEthEtherAceId	     INTEGER,
	rcPrFilterAceEthEtherTypeList        OCTET STRING,
	rcPrFilterAceEthEtherTypeListCount   INTEGER,
        rcPrFilterAceEthEtherTypeOper        INTEGER,
        rcPrFilterAceEthEtherRowStatus       RowStatus
        }

rcPrFilterAceEthEtherAclId OBJECT-TYPE
     SYNTAX             INTEGER (1..2048)
     MAX-ACCESS         read-only 
     STATUS             current
     DESCRIPTION        "An index to the AceEthEtherEntry, a unique 
	                identifier for Acl entry in the range of Table 
			Size."
     ::= { rcPrFilterAceEthEtherEntry 1 }

rcPrFilterAceEthEtherAceId OBJECT-TYPE
     SYNTAX             INTEGER (1..2000)
     MAX-ACCESS         read-only 
     STATUS             current
     DESCRIPTION        "An index to the AceEthEtherEntry, a unique 
	                identifier for Acl entry in the range of Table 
			Size."
     ::= { rcPrFilterAceEthEtherEntry 2 }

rcPrFilterAceEthEtherTypeList OBJECT-TYPE
     SYNTAX             OCTET STRING (SIZE(0..1500))
     MAX-ACCESS         read-write
     STATUS             current
     DESCRIPTION        "EtherType value from ethernet header.  For example ARP
                         uses  0x0806, IP uses 0x0800. The platform support
                         determines the behavior for 802.1Q/p tagged packets.
                         The EtherType for 802.1Q tagged frames is 0x8100.

                         Valid range for the 16-bit Ether-type is 0..65535 
			 and the attribute supports lists/ranges of values.
                         Invalid ether-type value 65536 is interpreted as
                         field is not desired in match criteria."
	::= { rcPrFilterAceEthEtherEntry 3 }

rcPrFilterAceEthEtherTypeListCount OBJECT-TYPE
     SYNTAX             INTEGER(1..100)
     MAX-ACCESS         read-write 
     STATUS             current
     DESCRIPTION        "Count to store the number of discrete ranges
                        entered for the ethernet types."
     ::= { rcPrFilterAceEthEtherEntry 4 }

rcPrFilterAceEthEtherTypeOper OBJECT-TYPE
     SYNTAX             INTEGER {
                            eq(1)    -- exact match
                        }
     MAX-ACCESS         read-write
     STATUS             current
     DESCRIPTION        "Ethernet Type Operators."
     ::= { rcPrFilterAceEthEtherEntry 5 }

rcPrFilterAceEthEtherRowStatus OBJECT-TYPE
     SYNTAX             RowStatus
     MAX-ACCESS         read-write
     STATUS             current
     DESCRIPTION        "Create/delete operations for this entry."
     ::= { rcPrFilterAceEthEtherEntry 6 }

-- ACE Ethernet Vlan Tag Priority Table

rcPrFilterAceEthVlanTagPrioTable OBJECT-TYPE
     SYNTAX             SEQUENCE OF RcPrFilterAceEthVlanTagPrioEntry
     MAX-ACCESS         not-accessible
     STATUS             current
     DESCRIPTION        "A table of Aces to store Ethernet Vlan Tag 
			Priority Header information of each Ace in context 
			of its parent Acl."
     ::= { rcPrFilterAce 5 }

rcPrFilterAceEthVlanTagPrioEntry OBJECT-TYPE
     SYNTAX             RcPrFilterAceEthVlanTagPrioEntry
     MAX-ACCESS         not-accessible 
     STATUS             current
     DESCRIPTION        "One Ace entry holding Ace Ethernet Vlan Tag Priority
 			information. An Ace is a member of one Acl." 
     INDEX              { rcPrFilterAceEthVlanTagPrioAclId,
                          rcPrFilterAceEthVlanTagPrioAceId } 
     ::= { rcPrFilterAceEthVlanTagPrioTable 1 }

RcPrFilterAceEthVlanTagPrioEntry ::= SEQUENCE {
        rcPrFilterAceEthVlanTagPrioAclId	     INTEGER,
        rcPrFilterAceEthVlanTagPrioAceId	     INTEGER,
	rcPrFilterAceEthVlanTagPrioVlanTagPrio 	     INTEGER,
        rcPrFilterAceEthVlanTagPrioOper              INTEGER,
        rcPrFilterAceEthVlanTagPrioRowStatus         RowStatus,
	rcPrFilterAceEthVlanTagPrioOperMask	     Integer32
        }

rcPrFilterAceEthVlanTagPrioAclId OBJECT-TYPE
     SYNTAX             INTEGER (1..2048)
     MAX-ACCESS         read-only 
     STATUS             current
     DESCRIPTION        "An index to the AceEthVlanTagPrioEntry, a unique 
	                identifier for Acl entry in the range of Table 
			Size."
     ::= { rcPrFilterAceEthVlanTagPrioEntry 1 }

rcPrFilterAceEthVlanTagPrioAceId OBJECT-TYPE
     SYNTAX             INTEGER (1..2000)
     MAX-ACCESS         read-only 
     STATUS             current
     DESCRIPTION        "An index to the AceEthVlanTagPrioEntry, a unique 
	                identifier for Acl entry in the range of Table 
			Size."
     ::= { rcPrFilterAceEthVlanTagPrioEntry 2 }

rcPrFilterAceEthVlanTagPrioVlanTagPrio  OBJECT-TYPE
     SYNTAX             INTEGER {
                            zero(0),
                            one(1),
                            two(2),
                            three(3),
                            four(4),
                            five(5),
                            six(6),
                            seven(7)
                        }
     MAX-ACCESS         read-write
     STATUS             current
     DESCRIPTION        "Priority bits (3-bit field) from the 802.1Q/p tag."
     ::= { rcPrFilterAceEthVlanTagPrioEntry 3 }

rcPrFilterAceEthVlanTagPrioOper OBJECT-TYPE
     SYNTAX             INTEGER {
                            eq(1),    -- exact match
                            mask(8)   -- mask
                        }
     MAX-ACCESS         read-write
     STATUS             current
     DESCRIPTION        "Operators for Ace Ethernet Vlan Tag Priority."
     ::= { rcPrFilterAceEthVlanTagPrioEntry 4 }

rcPrFilterAceEthVlanTagPrioRowStatus OBJECT-TYPE
     SYNTAX             RowStatus
     MAX-ACCESS         read-write
     STATUS             current
     DESCRIPTION        "Create/delete operations for this entry."
     ::= { rcPrFilterAceEthVlanTagPrioEntry 5 }

rcPrFilterAceEthVlanTagPrioOperMask OBJECT-TYPE
     SYNTAX             Integer32 (0..'7'h)
     MAX-ACCESS         read-write
     STATUS             current
     DESCRIPTION        "The mask value in hex which can be set for the
			rcPrFilterAceEthVlanTagPrioOper when the option 
                        selected is masked. This object is applicable for
                        VSP9000. Not for ERS8600"
     ::= { rcPrFilterAceEthVlanTagPrioEntry 6 }

-- ACE Ethernet Port Table

rcPrFilterAceEthPortTable OBJECT-TYPE
     SYNTAX             SEQUENCE OF RcPrFilterAceEthPortEntry
     MAX-ACCESS         not-accessible
     STATUS             current
     DESCRIPTION        "A table of Aces to store Ethernet  Port 
			Header information of each Ace in context 
			of its parent Acl."
     ::= { rcPrFilterAce 6 }

rcPrFilterAceEthPortEntry OBJECT-TYPE
     SYNTAX             RcPrFilterAceEthPortEntry
     MAX-ACCESS         not-accessible 
     STATUS             current
     DESCRIPTION        "One Ace entry holding Ace Ethernet Port
 			information. An Ace is a member of one Acl." 
     INDEX              { rcPrFilterAceEthPortAclId,
                          rcPrFilterAceEthPortAceId }
     ::= { rcPrFilterAceEthPortTable 1 }

RcPrFilterAceEthPortEntry ::= SEQUENCE {
        rcPrFilterAceEthPortAclId	 INTEGER,
        rcPrFilterAceEthPortAceId	 INTEGER,
        rcPrFilterAceEthPortPort         PortSet,
        rcPrFilterAceEthPortOper         INTEGER,
        rcPrFilterAceEthPortRowStatus    RowStatus
        }

rcPrFilterAceEthPortAclId OBJECT-TYPE
     SYNTAX             INTEGER (1..2048)
     MAX-ACCESS         read-only 
     STATUS             current
     DESCRIPTION        "An index to the AceEthPortEntry, a unique 
	                identifier for Acl entry in the range of Table 
			Size."
     ::= { rcPrFilterAceEthPortEntry 1 }

rcPrFilterAceEthPortAceId OBJECT-TYPE
     SYNTAX             INTEGER (1..2000)
     MAX-ACCESS         read-only 
     STATUS             current
     DESCRIPTION        "An index to the AceEthPortEntry, a unique 
	                identifier for Acl entry in the range of Table 
			Size."
     ::= { rcPrFilterAceEthPortEntry 2 }

rcPrFilterAceEthPortPort OBJECT-TYPE
     SYNTAX             PortSet
     MAX-ACCESS         read-write
     STATUS             current
     DESCRIPTION        "Port Number or Port List to match on."
     ::= { rcPrFilterAceEthPortEntry 3 }

rcPrFilterAceEthPortOper OBJECT-TYPE
     SYNTAX             INTEGER {
                            eq(1)   -- exact match
                        }
     MAX-ACCESS         read-write
     STATUS             current
     DESCRIPTION        "Operator for Ace Ethernet Port."
     ::= { rcPrFilterAceEthPortEntry 4 }

rcPrFilterAceEthPortRowStatus OBJECT-TYPE
     SYNTAX             RowStatus
     MAX-ACCESS         read-write
     STATUS             current
     DESCRIPTION        "Create/delete operations for this entry."
     ::= { rcPrFilterAceEthPortEntry 5 }

-- ACE Ethernet Vlan Id Table 

rcPrFilterAceEthVlanIdTable OBJECT-TYPE
     SYNTAX             SEQUENCE OF RcPrFilterAceEthVlanIdEntry
     MAX-ACCESS         not-accessible
     STATUS             current
     DESCRIPTION        "A table of Aces to store Ethernet Vlan Id
			Header information of each Ace in context 
			of its parent Acl."
     ::= { rcPrFilterAce 7 }

rcPrFilterAceEthVlanIdEntry OBJECT-TYPE
     SYNTAX             RcPrFilterAceEthVlanIdEntry
     MAX-ACCESS         not-accessible 
     STATUS             current
     DESCRIPTION        "One Ace entry holding Ace Ethernet Vlan Id
 			information. An Ace is a member of one Acl." 
     INDEX              { rcPrFilterAceEthVlanIdAclId,
                          rcPrFilterAceEthVlanIdAceId }
     ::= { rcPrFilterAceEthVlanIdTable 1 }

RcPrFilterAceEthVlanIdEntry ::= SEQUENCE {
        rcPrFilterAceEthVlanIdAclId	     INTEGER,
        rcPrFilterAceEthVlanIdAceId	     INTEGER,
        rcPrFilterAceEthVlanIdVlanIdList     IdList,
        rcPrFilterAceEthVlanIdOper           INTEGER,
        rcPrFilterAceEthVlanIdRowStatus      RowStatus,
	rcPrFilterAceEthVlanIdOperMask       Integer32,
        rcPrFilterAceEthVlanIdVlanId         INTEGER
        }

rcPrFilterAceEthVlanIdAclId OBJECT-TYPE
     SYNTAX             INTEGER (1..2048)
     MAX-ACCESS         read-only 
     STATUS             current
     DESCRIPTION        "An index to the AceEthVlanIdEntry, a unique 
	                identifier for Acl entry in the range of Table 
			Size."
     ::= { rcPrFilterAceEthVlanIdEntry 1 }

rcPrFilterAceEthVlanIdAceId OBJECT-TYPE
     SYNTAX             INTEGER (1..2000)
     MAX-ACCESS         read-only 
     STATUS             current
     DESCRIPTION        "An index to the AceEthVlanIdEntry, a unique 
	                identifier for Acl entry in the range of Table 
			Size."
     ::= { rcPrFilterAceEthVlanIdEntry 2 }

rcPrFilterAceEthVlanIdVlanIdList OBJECT-TYPE
     SYNTAX             IdList(SIZE(4096))
     MAX-ACCESS         read-write
     STATUS             current
     DESCRIPTION        "Vlan Id to match on. This is a ERS 8600 supported object.
		         VSP9000 uses rcPrFilterAceEthVlanIdVlanId instead"
     ::= { rcPrFilterAceEthVlanIdEntry 3 }

rcPrFilterAceEthVlanIdOper OBJECT-TYPE
     SYNTAX             INTEGER {
                            eq(1),  -- exact match
                            mask(8) -- mask
                        }
     MAX-ACCESS         read-write
     STATUS             current
     DESCRIPTION        "Operator for Ace Ethernet VlanId."
     ::= { rcPrFilterAceEthVlanIdEntry 4 }

rcPrFilterAceEthVlanIdRowStatus OBJECT-TYPE
     SYNTAX             RowStatus
     MAX-ACCESS         read-write
     STATUS             current
     DESCRIPTION        "Create/delete operations for this entry."
     ::= { rcPrFilterAceEthVlanIdEntry 5 }

rcPrFilterAceEthVlanIdOperMask OBJECT-TYPE
     SYNTAX             Integer32(0..'FFF'h)
     MAX-ACCESS         read-write
     STATUS             current
     DESCRIPTION        "The mask value in hex which can be set for the
                        rcPrFilterAceEthVlanIdOper when the option
                        selected is mask. This object is used with
			rcPrFilterAceEthVlanIdVlanId in VSP 9000 to
			replace rcPrFilterAceEthVlanIdVlanIdList "
     ::= { rcPrFilterAceEthVlanIdEntry 6 }

rcPrFilterAceEthVlanIdVlanId OBJECT-TYPE
     SYNTAX             INTEGER (1..4084)
     MAX-ACCESS         read-write
     STATUS             current
     DESCRIPTION        "Vlan Id to match on. VSP9000  use this object with
			object rcPrFilterAceEthVlanIdOperMask to replace the
			rcPrFilterAceEthVlanIdVlanIdList"
     ::= { rcPrFilterAceEthVlanIdEntry 7 }


-- ACE Arp Table

rcPrFilterAceArpTable OBJECT-TYPE
     SYNTAX             SEQUENCE OF RcPrFilterAceArpEntry
     MAX-ACCESS         not-accessible
     STATUS             current
     DESCRIPTION        "A table of Aces to store Arp Header information
                         of each Ace in context of its parent Acl. "
     ::= { rcPrFilterAce 8 }

rcPrFilterAceArpEntry OBJECT-TYPE
     SYNTAX             RcPrFilterAceArpEntry
     MAX-ACCESS         not-accessible
     STATUS             current
     DESCRIPTION        "One Ace entry holding Ace Arp Header information.
                        Ace is a member of one Acl."
     INDEX              { rcPrFilterAceArpAclId,
                          rcPrFilterAceArpAceId }
     ::= { rcPrFilterAceArpTable 1 }

RcPrFilterAceArpEntry ::= SEQUENCE {
        rcPrFilterAceArpAclId	      INTEGER,
        rcPrFilterAceArpAceId	      INTEGER,
	rcPrFilterAceArpType          INTEGER,
	rcPrFilterAceArpOper          INTEGER,
	rcPrFilterAceArpValue	      INTEGER,
        rcPrFilterAceArpRowStatus     RowStatus
	}

rcPrFilterAceArpAclId OBJECT-TYPE
     SYNTAX             INTEGER (1..2048)
     MAX-ACCESS         read-only
     STATUS             current
     DESCRIPTION        "An index to the AceArpEntry, a unique 
	                identifier for Acl entry in the range of Table 
			Size."
     ::= { rcPrFilterAceArpEntry 1 }

rcPrFilterAceArpAceId OBJECT-TYPE
     SYNTAX             INTEGER (1..2000)
     MAX-ACCESS         read-only
     STATUS             current
     DESCRIPTION        "An index to the AceArpEntry, a unique 
	                identifier for Acl entry in the range of Table 
			Size."
     ::= { rcPrFilterAceArpEntry 2 }

rcPrFilterAceArpType      OBJECT-TYPE
     SYNTAX             INTEGER {
                            operation(1)
			}
     MAX-ACCESS         read-write
     STATUS             current
     DESCRIPTION        "Ace Arp Operation."
     DEFVAL	        { operation }
     ::= { rcPrFilterAceArpEntry 3 }

rcPrFilterAceArpOper          OBJECT-TYPE
     SYNTAX             INTEGER {
                            eq(1)    -- exact match
                        }
     MAX-ACCESS         read-write
     STATUS             current
     DESCRIPTION        "Operator for Ace Arp Operation."
     ::= { rcPrFilterAceArpEntry 4 }

rcPrFilterAceArpValue	OBJECT-TYPE
     SYNTAX             INTEGER {
                            arpRequest(1),
                            arpResponse(2)
			}
     MAX-ACCESS         read-write
     STATUS             current
     DESCRIPTION        "Ace Arp can be a request or a response."
     ::= { rcPrFilterAceArpEntry 5 }

rcPrFilterAceArpRowStatus OBJECT-TYPE
     SYNTAX             RowStatus
     MAX-ACCESS         read-write
     STATUS             current
     DESCRIPTION        "Create/delete operations for this entry."
     ::= { rcPrFilterAceArpEntry 6 }

-- ACE Ip Source Address Table

rcPrFilterAceIpSrcAddrTable OBJECT-TYPE
     SYNTAX             SEQUENCE OF RcPrFilterAceIpSrcAddrEntry
     MAX-ACCESS         not-accessible
     STATUS             current
     DESCRIPTION        "A table of Aces to store IP Source Address Header 
			information of each Ace in context of its parent Acl."
     ::= { rcPrFilterAce 9 }

rcPrFilterAceIpSrcAddrEntry OBJECT-TYPE
     SYNTAX             RcPrFilterAceIpSrcAddrEntry
     MAX-ACCESS         not-accessible
     STATUS             current
     DESCRIPTION        "One Ace entry holding Ace IP Source Address Header 
			information. An Ace is a member of one Acl."
     INDEX              { rcPrFilterAceIpSrcAddrAclId,
                          rcPrFilterAceIpSrcAddrAceId }
     ::= { rcPrFilterAceIpSrcAddrTable 1 }

RcPrFilterAceIpSrcAddrEntry ::= SEQUENCE {
        rcPrFilterAceIpSrcAddrAclId	     INTEGER,
        rcPrFilterAceIpSrcAddrAceId	     INTEGER,
        rcPrFilterAceIpSrcAddrOper           INTEGER,
        rcPrFilterAceIpSrcAddrRowStatus      RowStatus,
        rcPrFilterAceIpSrcAddrIpAddr         IpAddress,
	rcPrFilterAceIpSrcAddrOperMaskRange  IpAddress
        }

rcPrFilterAceIpSrcAddrAclId OBJECT-TYPE
     SYNTAX             INTEGER (1..2048)
     MAX-ACCESS         read-only
     STATUS             current
     DESCRIPTION        "An index to the AceIpSrcAddrEntry, a unique 
	                identifier for Acl entry in the range of Table 
			Size."
     ::= { rcPrFilterAceIpSrcAddrEntry 1 }

rcPrFilterAceIpSrcAddrAceId OBJECT-TYPE
     SYNTAX             INTEGER (1..2000)
     MAX-ACCESS         read-only
     STATUS             current
     DESCRIPTION        "An index to the AceIpSrcAddrEntry, a unique 
	                identifier for Acl entry in the range of Table 
			Size."
     ::= { rcPrFilterAceIpSrcAddrEntry 2 }

rcPrFilterAceIpSrcAddrOper OBJECT-TYPE
     SYNTAX             INTEGER {
                            eq(1),    -- exact match
			    mask(9), 
			    range(10)
                        }
     MAX-ACCESS         read-write
     STATUS             current
     DESCRIPTION        "Operators for Ace Ip Source Address."
     ::= { rcPrFilterAceIpSrcAddrEntry 5 }

rcPrFilterAceIpSrcAddrRowStatus OBJECT-TYPE
     SYNTAX             RowStatus
     MAX-ACCESS         read-write
     STATUS             current
     DESCRIPTION        "Create/delete operations for this entry."
     ::= { rcPrFilterAceIpSrcAddrEntry 6 }

rcPrFilterAceIpSrcAddrIpAddr OBJECT-TYPE
     SYNTAX        IpAddress
     MAX-ACCESS    read-write
     STATUS        current
     DESCRIPTION   "IP Source Address to match from IP header. 
		       This object is defined and used  to replace
		       the rcPrFilterAceIpSrcAddrList by VSP 9000"
     ::= { rcPrFilterAceIpSrcAddrEntry 7 }

rcPrFilterAceIpSrcAddrOperMaskRange OBJECT-TYPE
     SYNTAX             IpAddress
     MAX-ACCESS         read-write
     STATUS             current
     DESCRIPTION        "The IP Mask value or High IP address based on 
			object rcPrFilterAceIpSrcAddrOper mask/range
			option is selected."
     ::= { rcPrFilterAceIpSrcAddrEntry 8 }

-- ACE Ip Destination Address Table

rcPrFilterAceIpDstAddrTable OBJECT-TYPE
     SYNTAX             SEQUENCE OF RcPrFilterAceIpDstAddrEntry
     MAX-ACCESS         not-accessible
     STATUS             current
     DESCRIPTION        "A table of Aces to store IP Destination Address 
			Header information of each Ace in context of its 
			parent Acl."
     ::= { rcPrFilterAce 10 }

rcPrFilterAceIpDstAddrEntry OBJECT-TYPE
     SYNTAX             RcPrFilterAceIpDstAddrEntry
     MAX-ACCESS         not-accessible
     STATUS             current
     DESCRIPTION        "One Ace entry holding Ace IP Destination Address 
			Header information. An Ace is a member of one Acl."
     INDEX              { rcPrFilterAceIpDstAddrAclId,
                          rcPrFilterAceIpDstAddrAceId }
     ::= { rcPrFilterAceIpDstAddrTable 1 }

RcPrFilterAceIpDstAddrEntry ::= SEQUENCE {
        rcPrFilterAceIpDstAddrAclId	     INTEGER,
        rcPrFilterAceIpDstAddrAceId	     INTEGER,
        rcPrFilterAceIpDstAddrOper           INTEGER,
        rcPrFilterAceIpDstAddrRowStatus      RowStatus,
        rcPrFilterAceIpDstAddrIpAddr         IpAddress,
	rcPrFilterAceIpDstAddrOperMaskRange  IpAddress 
        }

rcPrFilterAceIpDstAddrAclId OBJECT-TYPE
     SYNTAX             INTEGER (1..2048)
     MAX-ACCESS         read-only
     STATUS             current
     DESCRIPTION        "An index to the AceIpDstAddrEntry, a unique 
	                identifier for Acl entry in the range of Table 
			Size."
     ::= { rcPrFilterAceIpDstAddrEntry 1 }

rcPrFilterAceIpDstAddrAceId OBJECT-TYPE
     SYNTAX             INTEGER (1..2000)
     MAX-ACCESS         read-only
     STATUS             current
     DESCRIPTION        "An index to the AceIpDstAddrEntry, a unique 
	                identifier for Acl entry in the range of Table 
			Size."
     ::= { rcPrFilterAceIpDstAddrEntry 2 }

rcPrFilterAceIpDstAddrOper OBJECT-TYPE
     SYNTAX             INTEGER {
                            eq(1),    -- exact match
			    mask(9),
			    range(10)
                        }
     MAX-ACCESS         read-write
     STATUS             current
     DESCRIPTION        "Operators for Ace IP Destination Address."
     ::= { rcPrFilterAceIpDstAddrEntry 5 }

rcPrFilterAceIpDstAddrRowStatus OBJECT-TYPE
     SYNTAX             RowStatus
     MAX-ACCESS         read-write
     STATUS             current
     DESCRIPTION        "Create/delete operations for this entry."
     ::= { rcPrFilterAceIpDstAddrEntry 6 }

rcPrFilterAceIpDstAddrIpAddr OBJECT-TYPE
     SYNTAX             IpAddress
     MAX-ACCESS         read-write
     STATUS             current
     DESCRIPTION        "IP Source Address to match from IP header. 
		         This object is defined and used  to replace
		         the rcPrFilterAceIpSrcAddrList by VSP 9000"
     ::= { rcPrFilterAceIpDstAddrEntry 7 }

rcPrFilterAceIpDstAddrOperMaskRange OBJECT-TYPE
     SYNTAX             IpAddress
     MAX-ACCESS         read-write
     STATUS             current
     DESCRIPTION        "The IP mask value or Hi Ip address based on
                        object rcPrFilterAceIpDstAddrOper mask/range
                        option is selected."
     ::= { rcPrFilterAceIpDstAddrEntry 8 }

-- ACE Ip Dscp Table

rcPrFilterAceIpDscpTable OBJECT-TYPE
     SYNTAX             SEQUENCE OF RcPrFilterAceIpDscpEntry
     MAX-ACCESS         not-accessible
     STATUS             current
     DESCRIPTION        "A table of Aces to store IP Dscp Header information 
			of each Ace in context of its parent Acl."
     ::= { rcPrFilterAce 11 }

rcPrFilterAceIpDscpEntry OBJECT-TYPE
     SYNTAX             RcPrFilterAceIpDscpEntry
     MAX-ACCESS         not-accessible
     STATUS             current
     DESCRIPTION        "One Ace entry holding Ace IP Dscp Header information.
			An Ace is a member of one Acl."
     INDEX              { rcPrFilterAceIpDscpAclId,
                          rcPrFilterAceIpDscpAceId }
     ::= { rcPrFilterAceIpDscpTable 1 }

RcPrFilterAceIpDscpEntry ::= SEQUENCE {
        rcPrFilterAceIpDscpAclId	     INTEGER,
        rcPrFilterAceIpDscpAceId	     INTEGER,
        rcPrFilterAceIpDscpList              OCTET STRING,
        rcPrFilterAceIpDscpListCount         INTEGER,
        rcPrFilterAceIpDscpOper              INTEGER,
        rcPrFilterAceIpDscpRowStatus         RowStatus,
	rcPrFilterAceIpDscpOperMask	     Integer32
        }

rcPrFilterAceIpDscpAclId OBJECT-TYPE
     SYNTAX             INTEGER (1..2048)
     MAX-ACCESS         read-only
     STATUS             current
     DESCRIPTION        "An index to the AceIpDscpEntry, a unique 
	                identifier for Acl entry in the range of Table 
			Size."
     ::= { rcPrFilterAceIpDscpEntry 1 }

rcPrFilterAceIpDscpAceId OBJECT-TYPE
     SYNTAX             INTEGER (1..2000)
     MAX-ACCESS         read-only
     STATUS             current
     DESCRIPTION        "An index to the AceIpDscpEntry, a unique 
	                identifier for Acl entry in the range of Table 
			Size."
     ::= { rcPrFilterAceIpDscpEntry 2 }

rcPrFilterAceIpDscpList  OBJECT-TYPE
     SYNTAX             OCTET STRING (SIZE(0..1500))
     MAX-ACCESS         read-write
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to match specific diffserv class traffic.
                        Set the field value to desired dscp code for
                        'rcPrFilterAceIpDscp' field to match non-standard
                        traffic classes and local use PHBs."
     DEFVAL             { "disable" }
     ::= { rcPrFilterAceIpDscpEntry 3 }

rcPrFilterAceIpDscpListCount OBJECT-TYPE
     SYNTAX             INTEGER(1..100)
     MAX-ACCESS         read-write 
     STATUS             current
     DESCRIPTION        "Count to store the number of discrete ranges
                        entered for the dscp values."
     ::= { rcPrFilterAceIpDscpEntry 4 }

rcPrFilterAceIpDscpOper OBJECT-TYPE
     SYNTAX             INTEGER {
                            eq(1),    -- exact match
                            mask(8)
                        }
     MAX-ACCESS         read-write
     STATUS             current
     DESCRIPTION        "Operators for Ace Ip Dscp."
     ::= { rcPrFilterAceIpDscpEntry 5 }

rcPrFilterAceIpDscpRowStatus OBJECT-TYPE
     SYNTAX             RowStatus
     MAX-ACCESS         read-write
     STATUS             current
     DESCRIPTION        "Create/delete operations for this entry."
     ::= { rcPrFilterAceIpDscpEntry 6 }

rcPrFilterAceIpDscpOperMask OBJECT-TYPE
     SYNTAX             Integer32(0..'40'h)
     MAX-ACCESS         read-write
     STATUS             current
     DESCRIPTION        "The mask value in hex which can be set for the 
                        rcPrFilterAceIpDscpOper when the option 
                        selected is mask. It will be set to 0 or be used
			when rcPrFilterAceIpDscpOper is set ro eq"
     ::= { rcPrFilterAceIpDscpEntry 7 }

-- ACE Ip Proto Table

rcPrFilterAceIpProtoTable OBJECT-TYPE
     SYNTAX             SEQUENCE OF RcPrFilterAceIpProtoEntry
     MAX-ACCESS         not-accessible
     STATUS             current
     DESCRIPTION        "A table of Aces to store IP Proto Header information 
			of each Ace in context of its parent Acl."
     ::= { rcPrFilterAce 12 }

rcPrFilterAceIpProtoEntry OBJECT-TYPE
     SYNTAX             RcPrFilterAceIpProtoEntry
     MAX-ACCESS         not-accessible
     STATUS             current
     DESCRIPTION        "One Ace entry holding Ace IP Proto Header information.
			An Ace is a member of one Acl."
     INDEX              { rcPrFilterAceIpProtoAclId,
                          rcPrFilterAceIpProtoAceId }
     ::= { rcPrFilterAceIpProtoTable 1 }

RcPrFilterAceIpProtoEntry ::= SEQUENCE {
        rcPrFilterAceIpProtoAclId	     INTEGER,
        rcPrFilterAceIpProtoAceId	     INTEGER,
        rcPrFilterAceIpProtoList             OCTET STRING,
        rcPrFilterAceIpProtoListCount        INTEGER,
        rcPrFilterAceIpProtoOper             INTEGER,
        rcPrFilterAceIpProtoRowStatus        RowStatus
        }

rcPrFilterAceIpProtoAclId OBJECT-TYPE
     SYNTAX             INTEGER (1..2048)
     MAX-ACCESS         read-only
     STATUS             current
     DESCRIPTION        "An index to the AceIpProtoEntry, a unique 
	                identifier for Acl entry in the range of Table 
			Size."
     ::= { rcPrFilterAceIpProtoEntry 1 }

rcPrFilterAceIpProtoAceId OBJECT-TYPE
     SYNTAX             INTEGER (1..2000)
     MAX-ACCESS         read-only
     STATUS             current
     DESCRIPTION        "An index to the AceIpProtoEntry, a unique 
	                identifier for Acl entry in the range of Table 
			Size."
     ::= { rcPrFilterAceIpProtoEntry 2 }

rcPrFilterAceIpProtoList OBJECT-TYPE
     SYNTAX             OCTET STRING (SIZE(0..1500))
     MAX-ACCESS         read-write
     STATUS             current 
     DESCRIPTION        "Ip protocol Type from the ip header to be matched.
                        Valid Ip protocol range is 0..255. Few of the Protocol
                        Types are enumerated above. In case the desired
                        protocol number is not available in the enumerated
                        list set protocol to desired integer value"
     ::= { rcPrFilterAceIpProtoEntry 3 }

rcPrFilterAceIpProtoListCount OBJECT-TYPE
     SYNTAX             INTEGER(1..100)
     MAX-ACCESS         read-write 
     STATUS             current
     DESCRIPTION        "Count to store the number of discrete ranges
                        entered for the ethernet protocol ids."
     ::= { rcPrFilterAceIpProtoEntry 4 }

rcPrFilterAceIpProtoOper OBJECT-TYPE
     SYNTAX             INTEGER {
                            eq(1)    -- exact match
                        }
     MAX-ACCESS         read-write
     STATUS             current
     DESCRIPTION        "Operators for Ace Ip Protocols."
     ::= { rcPrFilterAceIpProtoEntry 5 }

rcPrFilterAceIpProtoRowStatus OBJECT-TYPE
     SYNTAX             RowStatus
     MAX-ACCESS         read-write
     STATUS             current
     DESCRIPTION        "Create/delete operations for this entry."
     ::= { rcPrFilterAceIpProtoEntry 6 }

-- ACE Ip Options Table

rcPrFilterAceIpOptionsTable OBJECT-TYPE
     SYNTAX             SEQUENCE OF RcPrFilterAceIpOptionsEntry
     MAX-ACCESS         not-accessible
     STATUS             current
     DESCRIPTION        "A table of Aces to store IP Options Header 
			information of each Ace in context of its parent Acl."
     ::= { rcPrFilterAce 13 }

rcPrFilterAceIpOptionsEntry OBJECT-TYPE
     SYNTAX             RcPrFilterAceIpOptionsEntry
     MAX-ACCESS         not-accessible
     STATUS             current
     DESCRIPTION        "One Ace entry holding Ace IP Options Header 
			information. An Ace is a member of one Acl."
     INDEX              { rcPrFilterAceIpOptionsAclId,
                          rcPrFilterAceIpOptionsAceId }
     ::= { rcPrFilterAceIpOptionsTable 1 }

RcPrFilterAceIpOptionsEntry ::= SEQUENCE {
        rcPrFilterAceIpOptionsAclId	     INTEGER,
        rcPrFilterAceIpOptionsAceId	     INTEGER,
	rcPrFilterAceIpOptionsOptions        INTEGER,
        rcPrFilterAceIpOptionsOper           INTEGER,
        rcPrFilterAceIpOptionsRowStatus      RowStatus
        }

rcPrFilterAceIpOptionsAclId OBJECT-TYPE
     SYNTAX             INTEGER (1..2048)
     MAX-ACCESS         read-only
     STATUS             current
     DESCRIPTION        "An index to the AceIpOptionsEntry, a unique 
	                identifier for Acl entry in the range of Table 
			Size."
     ::= { rcPrFilterAceIpOptionsEntry 1 }

rcPrFilterAceIpOptionsAceId OBJECT-TYPE
     SYNTAX             INTEGER (1..2000)
     MAX-ACCESS         read-only
     STATUS             current
     DESCRIPTION        "An index to the AceIpOptionsEntry, a unique 
	                identifier for Acl entry in the range of Table 
			Size."
     ::= { rcPrFilterAceIpOptionsEntry 2 }

rcPrFilterAceIpOptionsOptions  OBJECT-TYPE  
     SYNTAX             INTEGER {
			    noOperation(1),
			    recordRoute(7),
			    experimentalMeasurement(10),
 			    mtuProbe(11),
			    mtuReply(12),
			    encode(15),
			    timestamp(68),
			    traceroute(82),
			    baseSecurity(130),
			    looseSourceRoute(131),
			    extendedSecurity(133),
			    commercialSecurity(134),
			    streamID(136),
			    strictSourceRouting(137),
			    experimentalAccessControl(142),
			    imiTrafficDescriptor(144),
			    extendedIP(145),
			    addressExtension(147),
			    routeAlert(148),
			    selectiveDirectedBroadcast(149),
			    nsapAddresses(150),
			    dynamicPacketState(151),
			    upstreamMulticastPacket(152),
			    experimentalFlowControl(205)
			}
     MAX-ACCESS         read-write
     STATUS             current
     DESCRIPTION        "Ip options to be matched from the IP Header."
     ::= { rcPrFilterAceIpOptionsEntry 3 }

rcPrFilterAceIpOptionsOper OBJECT-TYPE 
     SYNTAX             INTEGER {
                            any(5)
			}
     MAX-ACCESS         read-write
     STATUS             current
     DESCRIPTION        "Logical Operator - only 'any' is valid at present."
     DEFVAL		{ any }
     ::= { rcPrFilterAceIpOptionsEntry 4 }

rcPrFilterAceIpOptionsRowStatus OBJECT-TYPE
     SYNTAX             RowStatus
     MAX-ACCESS         read-write
     STATUS             current
     DESCRIPTION        "Create/delete operations for this entry."
     ::= { rcPrFilterAceIpOptionsEntry 5 }

-- ACE Ip Fragmentation Table

rcPrFilterAceIpFragTable OBJECT-TYPE
     SYNTAX             SEQUENCE OF RcPrFilterAceIpFragEntry
     MAX-ACCESS         not-accessible
     STATUS             current
     DESCRIPTION        "A table of Aces to store IP Fragmentation Header 
			information of each Ace in context of its parent Acl."
     ::= { rcPrFilterAce 14 }

rcPrFilterAceIpFragEntry OBJECT-TYPE
     SYNTAX             RcPrFilterAceIpFragEntry
     MAX-ACCESS         not-accessible
     STATUS             current
     DESCRIPTION        "One Ace entry holding Ace IP Fragmentation Header 
			information. An Ace is a member of one Acl."
     INDEX              { rcPrFilterAceIpFragAclId,
                          rcPrFilterAceIpFragAceId }
     ::= { rcPrFilterAceIpFragTable 1 }

RcPrFilterAceIpFragEntry ::= SEQUENCE {
        rcPrFilterAceIpFragAclId	     INTEGER,
        rcPrFilterAceIpFragAceId	     INTEGER,
        rcPrFilterAceIpFragFragmentation     INTEGER,
        rcPrFilterAceIpFragOper              INTEGER,
        rcPrFilterAceIpFragRowStatus         RowStatus
        }

rcPrFilterAceIpFragAclId OBJECT-TYPE
     SYNTAX             INTEGER (1..2048)
     MAX-ACCESS         read-only
     STATUS             current
     DESCRIPTION        "An index to the AceIpFragEntry, a unique 
	                identifier for Acl entry in the range of Table 
			Size."
     ::= { rcPrFilterAceIpFragEntry 1 }

rcPrFilterAceIpFragAceId OBJECT-TYPE
     SYNTAX             INTEGER (1..2000)
     MAX-ACCESS         read-only
     STATUS             current
     DESCRIPTION        "An index to the AceIpFragEntry, a unique 
	                identifier for Acl entry in the range of Table 
			Size."
     ::= { rcPrFilterAceIpFragEntry 2 }

rcPrFilterAceIpFragFragmentation OBJECT-TYPE
     SYNTAX             INTEGER {
                            noFragment(0),
                            anyFragment(1),
                            moreFragment(2),
                            unused3(3),
                            lastFragment(4),
                            unused5(5),
                            unused6(6),
                            unused7(7)
                        }
     MAX-ACCESS         read-write
     STATUS             current
     DESCRIPTION        "Ip Fragmentation bits to be matched from the IP
                        Header."
     DEFVAL      { noFragment }
     ::= { rcPrFilterAceIpFragEntry 3 }

rcPrFilterAceIpFragOper OBJECT-TYPE
     SYNTAX             INTEGER {
                            eq(1)    -- exact match
                        }
     MAX-ACCESS         read-write
     STATUS             current
     DESCRIPTION        "Operator for Ip fragmentation."
     ::= { rcPrFilterAceIpFragEntry 4 }

rcPrFilterAceIpFragRowStatus OBJECT-TYPE
     SYNTAX             RowStatus
     MAX-ACCESS         read-write
     STATUS             current
     DESCRIPTION        "Create/delete operations for this entry."
     ::= { rcPrFilterAceIpFragEntry 5 }

-- ACE Protocol TcpSrcPort table

rcPrFilterAceProtoTcpSrcPortTable OBJECT-TYPE
     SYNTAX             SEQUENCE OF RcPrFilterAceProtoTcpSrcPortEntry
     MAX-ACCESS         not-accessible
     STATUS             current
     DESCRIPTION        "A table of Aces to store TCP Source Port information
                        of each Ace in context of its parent Acl."
     ::= { rcPrFilterAce 15 }

rcPrFilterAceProtoTcpSrcPortEntry OBJECT-TYPE
     SYNTAX             RcPrFilterAceProtoTcpSrcPortEntry
     MAX-ACCESS         not-accessible 
     STATUS             current
     DESCRIPTION        "One entry holding Ace Protocol TCP Source Port
			information. An Ace is a member of one Acl."
     INDEX              { rcPrFilterAceProtoTcpSrcPortAclId,
                          rcPrFilterAceProtoTcpSrcPortAceId }
     ::= { rcPrFilterAceProtoTcpSrcPortTable 1 }
         

RcPrFilterAceProtoTcpSrcPortEntry ::= SEQUENCE {
        rcPrFilterAceProtoTcpSrcPortAclId     INTEGER,
        rcPrFilterAceProtoTcpSrcPortAceId     INTEGER,
        rcPrFilterAceProtoTcpSrcPortPort      OCTET STRING,
        rcPrFilterAceProtoTcpSrcPortCount     INTEGER,
        rcPrFilterAceProtoTcpSrcPortOper      INTEGER,
        rcPrFilterAceProtoTcpSrcPortRowStatus RowStatus
        }

rcPrFilterAceProtoTcpSrcPortAclId OBJECT-TYPE
     SYNTAX             INTEGER (1..4096)
     MAX-ACCESS         read-only 
     STATUS             current
     DESCRIPTION        "An index to the AceProtoTcpSrcPortEntry, a unique 
	                identifier for Acl entry in the range of Table 
			Size."
     ::= { rcPrFilterAceProtoTcpSrcPortEntry 1 }
     
rcPrFilterAceProtoTcpSrcPortAceId OBJECT-TYPE
     SYNTAX             INTEGER (1..1000)
     MAX-ACCESS         read-only 
     STATUS             current
     DESCRIPTION        "An index to the AceProtoTcpSrcPortEntry, a unique 
	                identifier for Ace entry in the range of Table 
			Size."
     ::= { rcPrFilterAceProtoTcpSrcPortEntry 2 }

rcPrFilterAceProtoTcpSrcPortPort OBJECT-TYPE
     SYNTAX             OCTET STRING (SIZE(0..1500))
     MAX-ACCESS         read-write
     STATUS             current
     DESCRIPTION        "Port Number or Port List to match on."
     ::= { rcPrFilterAceProtoTcpSrcPortEntry 3 }

rcPrFilterAceProtoTcpSrcPortCount OBJECT-TYPE
     SYNTAX             INTEGER(1..100)
     MAX-ACCESS         read-write 
     STATUS             current
     DESCRIPTION        "Count to store the number of discrete ranges
                        entered for the TCP source port."
     ::= { rcPrFilterAceProtoTcpSrcPortEntry 4 }

rcPrFilterAceProtoTcpSrcPortOper OBJECT-TYPE
     SYNTAX             INTEGER {
                            eq(1),   -- exact match
			    ne(2),    -- not equal
                            le(3),    -- less than or equal to
                            ge(4)     -- greater than or equal to
                        }
     MAX-ACCESS         read-write
     STATUS             current
     DESCRIPTION        "Operator for Ace Protocol TcpSrcPort."
     ::= { rcPrFilterAceProtoTcpSrcPortEntry 5 }

rcPrFilterAceProtoTcpSrcPortRowStatus OBJECT-TYPE
     SYNTAX             RowStatus
     MAX-ACCESS         read-write
     STATUS             current
     DESCRIPTION        "Create/delete operations for this entry."
     ::= { rcPrFilterAceProtoTcpSrcPortEntry 6 }

-- ACE Protocol UdpSrcPort table

rcPrFilterAceProtoUdpSrcPortTable OBJECT-TYPE
     SYNTAX             SEQUENCE OF RcPrFilterAceProtoUdpSrcPortEntry
     MAX-ACCESS         not-accessible
     STATUS             current
     DESCRIPTION        "A table of Aces to store UDP Source Port information
                        of each Ace in context of its parent Acl."
     ::= { rcPrFilterAce 16 }

rcPrFilterAceProtoUdpSrcPortEntry OBJECT-TYPE
     SYNTAX             RcPrFilterAceProtoUdpSrcPortEntry
     MAX-ACCESS         not-accessible 
     STATUS             current
     DESCRIPTION        "One entry holding Ace Protocol UDP Source Port
			information. An Ace is a member of one Acl."
     INDEX              { rcPrFilterAceProtoUdpSrcPortAclId,
                          rcPrFilterAceProtoUdpSrcPortAceId }
     ::= { rcPrFilterAceProtoUdpSrcPortTable 1 }
         

RcPrFilterAceProtoUdpSrcPortEntry ::= SEQUENCE {
        rcPrFilterAceProtoUdpSrcPortAclId     INTEGER,
        rcPrFilterAceProtoUdpSrcPortAceId     INTEGER,
        rcPrFilterAceProtoUdpSrcPortPort      OCTET STRING,
        rcPrFilterAceProtoUdpSrcPortCount     INTEGER,
        rcPrFilterAceProtoUdpSrcPortOper      INTEGER,
        rcPrFilterAceProtoUdpSrcPortRowStatus RowStatus
        }

rcPrFilterAceProtoUdpSrcPortAclId OBJECT-TYPE
     SYNTAX             INTEGER (1..4096)
     MAX-ACCESS         read-only 
     STATUS             current
     DESCRIPTION        "An index to the AceProtoUdpSrcPortEntry, a unique 
	                identifier for Acl entry in the range of Table 
			Size."
     ::= { rcPrFilterAceProtoUdpSrcPortEntry 1 }
     
rcPrFilterAceProtoUdpSrcPortAceId OBJECT-TYPE
     SYNTAX             INTEGER (1..1000)
     MAX-ACCESS         read-only 
     STATUS             current
     DESCRIPTION        "An index to the AceProtoUdpSrcPortEntry, a unique 
	                identifier for Ace entry in the range of Table 
			Size."
     ::= { rcPrFilterAceProtoUdpSrcPortEntry 2 }

rcPrFilterAceProtoUdpSrcPortPort OBJECT-TYPE
     SYNTAX             OCTET STRING (SIZE(0..1500))
     MAX-ACCESS         read-write
     STATUS             current
     DESCRIPTION        "Port Number or Port List to match on."
     ::= { rcPrFilterAceProtoUdpSrcPortEntry 3 }

rcPrFilterAceProtoUdpSrcPortCount OBJECT-TYPE
     SYNTAX             INTEGER(1..100)
     MAX-ACCESS         read-write 
     STATUS             current
     DESCRIPTION        "Count to store the number of discrete ranges
                        entered for the UDP source port."
     ::= { rcPrFilterAceProtoUdpSrcPortEntry 4 }

rcPrFilterAceProtoUdpSrcPortOper OBJECT-TYPE
     SYNTAX             INTEGER {
                            eq(1),   -- exact match
			    ne(2),    -- not equal
                            le(3),    -- less than or equal to
                            ge(4)     -- greater than or equal to
                        }
     MAX-ACCESS         read-write
     STATUS             current
     DESCRIPTION        "Operator for Ace Protocol UdpSrcPort."
     ::= { rcPrFilterAceProtoUdpSrcPortEntry 5 }

rcPrFilterAceProtoUdpSrcPortRowStatus OBJECT-TYPE
     SYNTAX             RowStatus
     MAX-ACCESS         read-write
     STATUS             current
     DESCRIPTION        "Create/delete operations for this entry."
     ::= { rcPrFilterAceProtoUdpSrcPortEntry 6 }

-- ACE Protocol TcpDstPort table

rcPrFilterAceProtoTcpDstPortTable OBJECT-TYPE
     SYNTAX             SEQUENCE OF RcPrFilterAceProtoTcpDstPortEntry
     MAX-ACCESS         not-accessible
     STATUS             current
     DESCRIPTION        "A table of Aces to store TCP Dest Port information
                        of each Ace in context of its parent Acl."
     ::= { rcPrFilterAce 17 }

rcPrFilterAceProtoTcpDstPortEntry OBJECT-TYPE
     SYNTAX             RcPrFilterAceProtoTcpDstPortEntry
     MAX-ACCESS         not-accessible 
     STATUS             current
     DESCRIPTION        "One entry holding Ace Protocol TCP Dest Port
			information. An Ace is a member of one Acl."
     INDEX              { rcPrFilterAceProtoTcpDstPortAclId,
                          rcPrFilterAceProtoTcpDstPortAceId }
     ::= { rcPrFilterAceProtoTcpDstPortTable 1 }
         

RcPrFilterAceProtoTcpDstPortEntry ::= SEQUENCE {
        rcPrFilterAceProtoTcpDstPortAclId     INTEGER,
        rcPrFilterAceProtoTcpDstPortAceId     INTEGER,
        rcPrFilterAceProtoTcpDstPortPort      OCTET STRING,
        rcPrFilterAceProtoTcpDstPortCount     INTEGER,
        rcPrFilterAceProtoTcpDstPortOper      INTEGER,
        rcPrFilterAceProtoTcpDstPortRowStatus RowStatus
        }

rcPrFilterAceProtoTcpDstPortAclId OBJECT-TYPE
     SYNTAX             INTEGER (1..4096)
     MAX-ACCESS         read-only 
     STATUS             current
     DESCRIPTION        "An index to the AceProtoTcpDstPortEntry, a unique 
	                identifier for Acl entry in the range of Table 
			Size."
     ::= { rcPrFilterAceProtoTcpDstPortEntry 1 }
     
rcPrFilterAceProtoTcpDstPortAceId OBJECT-TYPE
     SYNTAX             INTEGER (1..1000)
     MAX-ACCESS         read-only 
     STATUS             current
     DESCRIPTION        "An index to the AceProtoTcpDstPortEntry, a unique 
	                identifier for Ace entry in the range of Table 
			Size."
     ::= { rcPrFilterAceProtoTcpDstPortEntry 2 }

rcPrFilterAceProtoTcpDstPortPort OBJECT-TYPE
     SYNTAX             OCTET STRING (SIZE(0..1500))
     MAX-ACCESS         read-write
     STATUS             current
     DESCRIPTION        "Port Number or Port List to match on."
     ::= { rcPrFilterAceProtoTcpDstPortEntry 3 }

rcPrFilterAceProtoTcpDstPortCount OBJECT-TYPE
     SYNTAX             INTEGER(1..100)
     MAX-ACCESS         read-write 
     STATUS             current
     DESCRIPTION        "Count to store the number of discrete ranges
                        entered for the TCP dest port."
     ::= { rcPrFilterAceProtoTcpDstPortEntry 4 }

rcPrFilterAceProtoTcpDstPortOper OBJECT-TYPE
     SYNTAX             INTEGER {
                            eq(1),   -- exact match
			    ne(2),    -- not equal
                            le(3),    -- less than or equal to
                            ge(4)     -- greater than or equal to
                        }
     MAX-ACCESS         read-write
     STATUS             current
     DESCRIPTION        "Operator for Ace Protocol TcpDstPort."
     ::= { rcPrFilterAceProtoTcpDstPortEntry 5 }

rcPrFilterAceProtoTcpDstPortRowStatus OBJECT-TYPE
     SYNTAX             RowStatus
     MAX-ACCESS         read-write
     STATUS             current
     DESCRIPTION        "Create/delete operations for this entry."
     ::= { rcPrFilterAceProtoTcpDstPortEntry 6 }

-- ACE Protocol UdpDstPort table

rcPrFilterAceProtoUdpDstPortTable OBJECT-TYPE
     SYNTAX             SEQUENCE OF RcPrFilterAceProtoUdpDstPortEntry
     MAX-ACCESS         not-accessible
     STATUS             current
     DESCRIPTION        "A table of Aces to store UDP Dest Port information
                        of each Ace in context of its parent Acl."
     ::= { rcPrFilterAce 18 }

rcPrFilterAceProtoUdpDstPortEntry OBJECT-TYPE
     SYNTAX             RcPrFilterAceProtoUdpDstPortEntry
     MAX-ACCESS         not-accessible 
     STATUS             current
     DESCRIPTION        "One entry holding Ace Protocol UDP Dest Port
			information. An Ace is a member of one Acl."
     INDEX              { rcPrFilterAceProtoUdpDstPortAclId,
                          rcPrFilterAceProtoUdpDstPortAceId }
     ::= { rcPrFilterAceProtoUdpDstPortTable 1 }
         

RcPrFilterAceProtoUdpDstPortEntry ::= SEQUENCE {
        rcPrFilterAceProtoUdpDstPortAclId     INTEGER,
        rcPrFilterAceProtoUdpDstPortAceId     INTEGER,
        rcPrFilterAceProtoUdpDstPortPort      OCTET STRING,
        rcPrFilterAceProtoUdpDstPortCount     INTEGER,
        rcPrFilterAceProtoUdpDstPortOper      INTEGER,
        rcPrFilterAceProtoUdpDstPortRowStatus RowStatus
        }

rcPrFilterAceProtoUdpDstPortAclId OBJECT-TYPE
     SYNTAX             INTEGER (1..4096)
     MAX-ACCESS         read-only 
     STATUS             current
     DESCRIPTION        "An index to the AceProtoUdpDstPortEntry, a unique 
	                identifier for Acl entry in the range of Table 
			Size."
     ::= { rcPrFilterAceProtoUdpDstPortEntry 1 }
     
rcPrFilterAceProtoUdpDstPortAceId OBJECT-TYPE
     SYNTAX             INTEGER (1..1000)
     MAX-ACCESS         read-only 
     STATUS             current
     DESCRIPTION        "An index to the AceProtoUdpDstPortEntry, a unique 
	                identifier for Ace entry in the range of Table 
			Size."
     ::= { rcPrFilterAceProtoUdpDstPortEntry 2 }

rcPrFilterAceProtoUdpDstPortPort OBJECT-TYPE
     SYNTAX             OCTET STRING (SIZE(0..1500))
     MAX-ACCESS         read-write
     STATUS             current
     DESCRIPTION        "Port Number or Port List to match on."
     ::= { rcPrFilterAceProtoUdpDstPortEntry 3 }

rcPrFilterAceProtoUdpDstPortCount OBJECT-TYPE
     SYNTAX             INTEGER(1..100)
     MAX-ACCESS         read-write 
     STATUS             current
     DESCRIPTION        "Count to store the number of discrete ranges
                        entered for the UDP dest port."
     ::= { rcPrFilterAceProtoUdpDstPortEntry 4 }

rcPrFilterAceProtoUdpDstPortOper OBJECT-TYPE
     SYNTAX             INTEGER {
                            eq(1),   -- exact match
			    ne(2),   -- not equal
                            le(3),    -- less than or equal to
                            ge(4)     -- greater than or equal to
                        }
     MAX-ACCESS         read-write
     STATUS             current
     DESCRIPTION        "Operator for Ace Protocol UdpDstPort."
     ::= { rcPrFilterAceProtoUdpDstPortEntry 5 }

rcPrFilterAceProtoUdpDstPortRowStatus OBJECT-TYPE
     SYNTAX             RowStatus
     MAX-ACCESS         read-write
     STATUS             current
     DESCRIPTION        "Create/delete operations for this entry."
     ::= { rcPrFilterAceProtoUdpDstPortEntry 6 }

-- ACE Protocol IcmpMsgType table

rcPrFilterAceProtoIcmpMsgTypeTable OBJECT-TYPE
     SYNTAX             SEQUENCE OF RcPrFilterAceProtoIcmpMsgTypeEntry
     MAX-ACCESS         not-accessible
     STATUS             current
     DESCRIPTION        "A table of Aces to store ICMP message type information
                        of each Ace in context of its parent Acl."
     ::= { rcPrFilterAce 19 }

rcPrFilterAceProtoIcmpMsgTypeEntry OBJECT-TYPE
     SYNTAX             RcPrFilterAceProtoIcmpMsgTypeEntry
     MAX-ACCESS         not-accessible 
     STATUS             current
     DESCRIPTION        "One entry holding Ace ICMP message type 
			information. An Ace is a member of one Acl."
     INDEX              { rcPrFilterAceProtoIcmpMsgTypeAclId,
                          rcPrFilterAceProtoIcmpMsgTypeAceId }
     ::= { rcPrFilterAceProtoIcmpMsgTypeTable 1 }
         

RcPrFilterAceProtoIcmpMsgTypeEntry ::= SEQUENCE {
        rcPrFilterAceProtoIcmpMsgTypeAclId     INTEGER,
        rcPrFilterAceProtoIcmpMsgTypeAceId     INTEGER,
        rcPrFilterAceProtoIcmpMsgTypeList      OCTET STRING,
        rcPrFilterAceProtoIcmpMsgTypeCount     INTEGER, 
        rcPrFilterAceProtoIcmpMsgTypeOper      INTEGER,
        rcPrFilterAceProtoIcmpMsgTypeRowStatus RowStatus
        }

rcPrFilterAceProtoIcmpMsgTypeAclId OBJECT-TYPE
     SYNTAX             INTEGER (1..2048)
     MAX-ACCESS         read-only 
     STATUS             current
     DESCRIPTION        "An index to the AceProtoIcmpMsgTypeEntry, a unique 
	                identifier for Acl entry in the range of Table 
			Size."
     ::= { rcPrFilterAceProtoIcmpMsgTypeEntry 1 }
     
rcPrFilterAceProtoIcmpMsgTypeAceId OBJECT-TYPE
     SYNTAX             INTEGER (1..2000)
     MAX-ACCESS         read-only 
     STATUS             current
     DESCRIPTION        "An index to the AceProtoIcmpMsgTypeEntry, a unique 
	                identifier for Ace entry in the range of Table 
			Size."
     ::= { rcPrFilterAceProtoIcmpMsgTypeEntry 2 }

rcPrFilterAceProtoIcmpMsgTypeList OBJECT-TYPE
     SYNTAX             OCTET STRING (SIZE(0..1500)) 
     MAX-ACCESS         read-write
     STATUS             current
     DESCRIPTION        "One or a list of Icmp messages to be matched. 
			Need to provide strings, number of protocol header 
			types (pre-defined values plus user-defined headers). 
			Valid range is 0 to 255 (reserved)."
     ::= { rcPrFilterAceProtoIcmpMsgTypeEntry 3 }

rcPrFilterAceProtoIcmpMsgTypeCount OBJECT-TYPE
     SYNTAX             INTEGER(1..100)
     MAX-ACCESS         read-write 
     STATUS             current
     DESCRIPTION        "Count to store the number of discrete ranges
                        entered for the ICMP message types."
     ::= { rcPrFilterAceProtoIcmpMsgTypeEntry 4 }

rcPrFilterAceProtoIcmpMsgTypeOper OBJECT-TYPE
     SYNTAX             INTEGER {
                            eq(1)   -- exact match
                        } 
     MAX-ACCESS         read-write
     STATUS             current
     DESCRIPTION        "Operator for Ace Protocol IcmpMsgTypes."
     ::= { rcPrFilterAceProtoIcmpMsgTypeEntry 5 }

rcPrFilterAceProtoIcmpMsgTypeRowStatus OBJECT-TYPE
     SYNTAX             RowStatus
     MAX-ACCESS         read-write
     STATUS             current
     DESCRIPTION        "Create/delete operations for this entry."
     ::= { rcPrFilterAceProtoIcmpMsgTypeEntry 6 }

-- ACE Protocol Tcp-flags table

rcPrFilterAceProtoTcpFlagsTable OBJECT-TYPE
     SYNTAX             SEQUENCE OF RcPrFilterAceProtoTcpFlagsEntry
     MAX-ACCESS         not-accessible
     STATUS             current
     DESCRIPTION        "A table of Aces to store TCP Flags information
                        of each Ace in context of its parent Acl."
     ::= { rcPrFilterAce 20 }

rcPrFilterAceProtoTcpFlagsEntry OBJECT-TYPE
     SYNTAX             RcPrFilterAceProtoTcpFlagsEntry
     MAX-ACCESS         not-accessible 
     STATUS             current
     DESCRIPTION        "One entry holding Ace Protocol TCP flags 
			information. An Ace is a member of one Acl."
     INDEX              { rcPrFilterAceProtoTcpFlagsAclId,
                          rcPrFilterAceProtoTcpFlagsAceId }
     ::= { rcPrFilterAceProtoTcpFlagsTable 1 }
         

RcPrFilterAceProtoTcpFlagsEntry ::= SEQUENCE {
        rcPrFilterAceProtoTcpFlagsAclId     INTEGER,
        rcPrFilterAceProtoTcpFlagsAceId     INTEGER,
        rcPrFilterAceProtoTcpFlagsList      OCTET STRING,
        rcPrFilterAceProtoTcpFlagsCount     INTEGER,
        rcPrFilterAceProtoTcpFlagsOper      INTEGER,
        rcPrFilterAceProtoTcpFlagsRowStatus RowStatus,
	rcPrFilterAceProtoTcpFlagsOperMask  Integer32
        }

rcPrFilterAceProtoTcpFlagsAclId OBJECT-TYPE
     SYNTAX             INTEGER (1..2048)
     MAX-ACCESS         read-only 
     STATUS             current
     DESCRIPTION        "An index to the rcPrFilterAceProtoTcpFlagsEntry,
                    a unique identifier for Acl entry in the range of Table
			        Size."
     ::= { rcPrFilterAceProtoTcpFlagsEntry 1 }
     
rcPrFilterAceProtoTcpFlagsAceId OBJECT-TYPE
     SYNTAX             INTEGER (1..2000)
     MAX-ACCESS         read-only 
     STATUS             current
     DESCRIPTION        "An index to the rcPrFilterAceProtoTcpFlagsEntry, 
                         a unique identifier for Ace entry in the 
                         range of Table Size."
     ::= { rcPrFilterAceProtoTcpFlagsEntry 2 }

rcPrFilterAceProtoTcpFlagsList OBJECT-TYPE
     SYNTAX             OCTET STRING (SIZE(0..1500)) 
     MAX-ACCESS         read-write
     STATUS             current
     DESCRIPTION        "One or a list of Tcp flags to be matched. 
			Need to provide strings, number of protocol header 
			types (pre-defined values plus user-defined headers). 
			Valid range is 0 to 63"
     ::= { rcPrFilterAceProtoTcpFlagsEntry 3 }

rcPrFilterAceProtoTcpFlagsCount OBJECT-TYPE
     SYNTAX             INTEGER(1..100)
     MAX-ACCESS         read-write 
     STATUS             current
     DESCRIPTION        "Count to store the number of discrete ranges
                        entered for the TCP flags."
     ::= { rcPrFilterAceProtoTcpFlagsEntry 4 }

rcPrFilterAceProtoTcpFlagsOper OBJECT-TYPE
     SYNTAX             INTEGER {
                            eq(1),
			    matchAny(6),
			    matchAll(7),
			    mask(8)
                        } 
     MAX-ACCESS         read-write
     STATUS             current
     DESCRIPTION        "Operator for Ace Protocol TcpFlags."
     ::= { rcPrFilterAceProtoTcpFlagsEntry 5 }

rcPrFilterAceProtoTcpFlagsRowStatus OBJECT-TYPE
     SYNTAX             RowStatus
     MAX-ACCESS         read-write
     STATUS             current
     DESCRIPTION        "Create/delete operations for this entry."
     ::= { rcPrFilterAceProtoTcpFlagsEntry 6 }

rcPrFilterAceProtoTcpFlagsOperMask OBJECT-TYPE
     SYNTAX             Integer32(0..'3F'h)
     MAX-ACCESS         read-write
     STATUS             current
     DESCRIPTION        "The mask value in hex which can be set for the
                        rcPrFilterAceProtoTcpFlagsOper when the option
                        selected is mask. It will be set 0x0 when object
			rcPrFilterAceProtoTcpFlagsOper is set to eq"
     ::= { rcPrFilterAceProtoTcpFlagsEntry 7 }

-- ACE Pattern Table

-- Ace Pattern 1
rcPrFilterAcePattern1Table OBJECT-TYPE
     SYNTAX             SEQUENCE OF RcPrFilterAcePattern1Entry
     MAX-ACCESS         not-accessible
     STATUS             current
     DESCRIPTION        "A table of pattern fields for Aces to manage the
                        settings for each user defined field. "
     ::= { rcPrFilterAce 21 }

rcPrFilterAcePattern1Entry OBJECT-TYPE
     SYNTAX             RcPrFilterAcePattern1Entry
     MAX-ACCESS         not-accessible
     STATUS             current
     DESCRIPTION        "One Ace entry holding Ace User Defined Pattern
                        information. Ace is a member of one Acl."
     INDEX              { rcPrFilterAcePattern1AclId, 
                          rcPrFilterAcePattern1AceId }
     ::= { rcPrFilterAcePattern1Table 1 }

RcPrFilterAcePattern1Entry ::= SEQUENCE {
        rcPrFilterAcePattern1AclId	INTEGER,
        rcPrFilterAcePattern1AceId	INTEGER,
        rcPrFilterAcePattern1Name       DisplayString,
        rcPrFilterAcePattern1Value      OCTET STRING,
        rcPrFilterAcePattern1Oper       INTEGER,
        rcPrFilterAcePattern1RowStatus  RowStatus
        }

rcPrFilterAcePattern1AclId OBJECT-TYPE
     SYNTAX             INTEGER (1..4096)
     MAX-ACCESS         read-only
     STATUS             current
     DESCRIPTION        "An index to the AcePatternEntry, a unique 
	                identifier for Acl entry in the range of Table 
			Size."
     ::= { rcPrFilterAcePattern1Entry 1 }

rcPrFilterAcePattern1AceId OBJECT-TYPE
     SYNTAX             INTEGER (1..1000)
     MAX-ACCESS         read-only
     STATUS             current
     DESCRIPTION        "An index to the AcePatternEntry, a unique 
	                identifier for Acl entry in the range of Table 
			Size."
     ::= { rcPrFilterAcePattern1Entry 2 }

rcPrFilterAcePattern1Name OBJECT-TYPE
     SYNTAX             DisplayString (SIZE (0..32))
     MAX-ACCESS         read-write
     STATUS             current
     DESCRIPTION        "A descriptive name chosen by the administrator for
                        the Ace Pattern Entry."
     ::= { rcPrFilterAcePattern1Entry 3 }

rcPrFilterAcePattern1Value OBJECT-TYPE
     SYNTAX             OCTET STRING (SIZE (0..1500))
     MAX-ACCESS         read-write
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern1Entry 4 }

rcPrFilterAcePattern1Oper OBJECT-TYPE
     SYNTAX             INTEGER {
                            eq(1),    -- exact match
                            le(3),    -- less than or equal to
                            ge(4)     -- greater than or equal to
                        }
     MAX-ACCESS         read-write
     STATUS             current
     DESCRIPTION        "Operators for Ace Pattern."
     ::= { rcPrFilterAcePattern1Entry 5 }

rcPrFilterAcePattern1RowStatus OBJECT-TYPE
     SYNTAX             RowStatus
     MAX-ACCESS         read-write
     STATUS             current
     DESCRIPTION        "Create/delete operations for this entry."
        ::= { rcPrFilterAcePattern1Entry 6 }


-- Ace Pattern 2
rcPrFilterAcePattern2Table OBJECT-TYPE
     SYNTAX             SEQUENCE OF RcPrFilterAcePattern2Entry
     MAX-ACCESS         not-accessible
     STATUS             current
     DESCRIPTION        "A table of pattern fields for Aces to manage the
                        settings for each user defined field. "
     ::= { rcPrFilterAce 22 }

rcPrFilterAcePattern2Entry OBJECT-TYPE
     SYNTAX             RcPrFilterAcePattern2Entry
     MAX-ACCESS         not-accessible
     STATUS             current
     DESCRIPTION        "One Ace entry holding Ace User Defined Pattern
                        information. Ace is a member of one Acl."
     INDEX              { rcPrFilterAcePattern2AclId, 
                          rcPrFilterAcePattern2AceId }
     ::= { rcPrFilterAcePattern2Table 1 }

RcPrFilterAcePattern2Entry ::= SEQUENCE {
        rcPrFilterAcePattern2AclId	INTEGER,
        rcPrFilterAcePattern2AceId	INTEGER,
        rcPrFilterAcePattern2Name       DisplayString,
        rcPrFilterAcePattern2Value      OCTET STRING,
        rcPrFilterAcePattern2Oper       INTEGER,
        rcPrFilterAcePattern2RowStatus  RowStatus
        }

rcPrFilterAcePattern2AclId OBJECT-TYPE
     SYNTAX             INTEGER (1..4096)
     MAX-ACCESS         read-only
     STATUS             current
     DESCRIPTION        "An index to the AcePatternEntry, a unique 
	                identifier for Acl entry in the range of Table 
			Size."
     ::= { rcPrFilterAcePattern2Entry 1 }

rcPrFilterAcePattern2AceId OBJECT-TYPE
     SYNTAX             INTEGER (1..1000)
     MAX-ACCESS         read-only
     STATUS             current
     DESCRIPTION        "An index to the AcePatternEntry, a unique 
	                identifier for Acl entry in the range of Table 
			Size."
     ::= { rcPrFilterAcePattern2Entry 2 }

rcPrFilterAcePattern2Name OBJECT-TYPE
     SYNTAX             DisplayString (SIZE (0..32))
     MAX-ACCESS         read-write
     STATUS             current
     DESCRIPTION        "A descriptive name chosen by the administrator for
                        the Ace Pattern Entry."
     ::= { rcPrFilterAcePattern2Entry 3 }

rcPrFilterAcePattern2Value OBJECT-TYPE
     SYNTAX             OCTET STRING (SIZE (0..1500))
     MAX-ACCESS         read-write
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern2Entry 4 }

rcPrFilterAcePattern2Oper OBJECT-TYPE
     SYNTAX             INTEGER {
                            eq(1),    -- exact match
                            le(3),    -- less than or equal to
                            ge(4)     -- greater than or equal to
                        }
     MAX-ACCESS         read-write
     STATUS             current
     DESCRIPTION        "Operators for Ace Pattern."
     ::= { rcPrFilterAcePattern2Entry 5 }

rcPrFilterAcePattern2RowStatus OBJECT-TYPE
     SYNTAX             RowStatus
     MAX-ACCESS         read-write
     STATUS             current
     DESCRIPTION        "Create/delete operations for this entry."
        ::= { rcPrFilterAcePattern2Entry 6 }

-- Ace Pattern 3
rcPrFilterAcePattern3Table OBJECT-TYPE
     SYNTAX             SEQUENCE OF RcPrFilterAcePattern3Entry
     MAX-ACCESS         not-accessible
     STATUS             current
     DESCRIPTION        "A table of pattern fields for Aces to manage the
                        settings for each user defined field. "
     ::= { rcPrFilterAce 23 }

rcPrFilterAcePattern3Entry OBJECT-TYPE
     SYNTAX             RcPrFilterAcePattern3Entry
     MAX-ACCESS         not-accessible
     STATUS             current
     DESCRIPTION        "One Ace entry holding Ace User Defined Pattern
                        information. Ace is a member of one Acl."
     INDEX              { rcPrFilterAcePattern3AclId, 
                          rcPrFilterAcePattern3AceId }
     ::= { rcPrFilterAcePattern3Table 1 }

RcPrFilterAcePattern3Entry ::= SEQUENCE {
        rcPrFilterAcePattern3AclId	INTEGER,
        rcPrFilterAcePattern3AceId	INTEGER,
        rcPrFilterAcePattern3Name       DisplayString,
        rcPrFilterAcePattern3Value      OCTET STRING,
        rcPrFilterAcePattern3Oper       INTEGER,
        rcPrFilterAcePattern3RowStatus  RowStatus
        }

rcPrFilterAcePattern3AclId OBJECT-TYPE
     SYNTAX             INTEGER (1..4096)
     MAX-ACCESS         read-only
     STATUS             current
     DESCRIPTION        "An index to the AcePatternEntry, a unique 
	                identifier for Acl entry in the range of Table 
			Size."
     ::= { rcPrFilterAcePattern3Entry 1 }

rcPrFilterAcePattern3AceId OBJECT-TYPE
     SYNTAX             INTEGER (1..1000)
     MAX-ACCESS         read-only
     STATUS             current
     DESCRIPTION        "An index to the AcePatternEntry, a unique 
	                identifier for Acl entry in the range of Table 
			Size."
     ::= { rcPrFilterAcePattern3Entry 2 }

rcPrFilterAcePattern3Name OBJECT-TYPE
     SYNTAX             DisplayString (SIZE (0..32))
     MAX-ACCESS         read-write
     STATUS             current
     DESCRIPTION        "A descriptive name chosen by the administrator for
                        the Ace Pattern Entry."
     ::= { rcPrFilterAcePattern3Entry 3 }

rcPrFilterAcePattern3Value OBJECT-TYPE
     SYNTAX             OCTET STRING (SIZE (0..1500))
     MAX-ACCESS         read-write
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern3Entry 4 }

rcPrFilterAcePattern3Oper OBJECT-TYPE
     SYNTAX             INTEGER {
                            eq(1),    -- exact match
                            le(3),    -- less than or equal to
                            ge(4)     -- greater than or equal to
                        }
     MAX-ACCESS         read-write
     STATUS             current
     DESCRIPTION        "Operators for Ace Pattern."
     ::= { rcPrFilterAcePattern3Entry 5 }

rcPrFilterAcePattern3RowStatus OBJECT-TYPE
     SYNTAX             RowStatus
     MAX-ACCESS         read-write
     STATUS             current
     DESCRIPTION        "Create/delete operations for this entry."
        ::= { rcPrFilterAcePattern3Entry 6 }

-- Per-ACE-Per-Port Statistics

rcPrFilterAceStatsTable OBJECT-TYPE
     SYNTAX             SEQUENCE OF RcPrFilterAceStatsEntry
     MAX-ACCESS         not-accessible
     STATUS             current
     DESCRIPTION        "A table of ACE Statistics Entries to store per-ACE-per-Port
                         Statistics"
     ::= { rcPrFilterAce 24 }

rcPrFilterAceStatsEntry OBJECT-TYPE
     SYNTAX             RcPrFilterAceStatsEntry
     MAX-ACCESS         not-accessible 
     STATUS             current
     DESCRIPTION        "Ace Statistics entry holding per-ACE-per-port Statistics"
     INDEX              { rcPrFilterAceStatsAclId,
                          rcPrFilterAceStatsAceId,
                          rcPrFilterAceStatsPortId }
     ::= { rcPrFilterAceStatsTable 1 }

RcPrFilterAceStatsEntry ::= SEQUENCE {
        rcPrFilterAceStatsAclId	             INTEGER,
        rcPrFilterAceStatsAceId	             INTEGER,
        rcPrFilterAceStatsPortId             INTEGER,
        rcPrFilterAceStatsMatchCountPkts     Counter64,
        rcPrFilterAceStatsMatchCountOctets   Counter64,
	rcPrFilterAceStatsClear		     TruthValue
        }

rcPrFilterAceStatsAclId OBJECT-TYPE
     SYNTAX             INTEGER (1..2048)
     MAX-ACCESS         read-only 
     STATUS             current
     DESCRIPTION        "An index to the AceStatsEntry, a unique 
	                identifier for Acl entry in the range of Table Size."
     ::= { rcPrFilterAceStatsEntry 1 }

rcPrFilterAceStatsAceId OBJECT-TYPE
     SYNTAX             INTEGER (1..2000)
     MAX-ACCESS         read-only 
     STATUS             current
     DESCRIPTION        "An index to the AceStatsEntry, a unique identifier
                         for ACE entry in the range of Table Size."
     ::= { rcPrFilterAceStatsEntry 2 }

rcPrFilterAceStatsPortId OBJECT-TYPE
     SYNTAX             INTEGER (0..703)
     MAX-ACCESS         read-only 
     STATUS             current
     DESCRIPTION        "An index to the AceStatsEntry, a unique identifier
                         of the portId. This object is not being used in
			 VSP 9000. It should be alway in VVSP 9000"
     ::= { rcPrFilterAceStatsEntry 3 }

rcPrFilterAceStatsMatchCountPkts OBJECT-TYPE
     SYNTAX             Counter64
     MAX-ACCESS         read-only
     STATUS             current
     DESCRIPTION        "Count of packets that match this particular Ace on this 
                         particular port."
     ::= { rcPrFilterAceStatsEntry 4 }

rcPrFilterAceStatsMatchCountOctets OBJECT-TYPE
     SYNTAX             Counter64
     MAX-ACCESS         read-only
     STATUS             current
     DESCRIPTION        "Byte count of traffic that match this particular Ace on 
                         this particular port"
     ::= { rcPrFilterAceStatsEntry 5 }

rcPrFilterAceStatsClear  OBJECT-TYPE
     SYNTAX             TruthValue
     MAX-ACCESS         read-write
     STATUS             current
     DESCRIPTION        "Clear Per-ACE-Per-Port statistics."
     ::= { rcPrFilterAceStatsEntry 6 }

-- ACE Ethernet Show Table

rcPrFilterAceEthShowTable OBJECT-TYPE
     SYNTAX             SEQUENCE OF RcPrFilterAceEthShowEntry
     MAX-ACCESS         not-accessible
     STATUS             current
     DESCRIPTION        "A table of Aces to store Ethernet Header
                        information of each Ace in context of
                        its parent Acl. "
     ::= { rcPrFilterAce 25 }

rcPrFilterAceEthShowEntry OBJECT-TYPE
     SYNTAX             RcPrFilterAceEthShowEntry
     MAX-ACCESS         not-accessible 
     STATUS             current
     DESCRIPTION        "One Ace entry holding Ace Ethernet information.
                         Ace is a member of one Acl."
     INDEX              { rcPrFilterAceEthShowAclId,
                          rcPrFilterAceEthShowAceId}
     ::= { rcPrFilterAceEthShowTable 1 }

RcPrFilterAceEthShowEntry ::= SEQUENCE {
	rcPrFilterAceEthShowAclId		INTEGER,
	rcPrFilterAceEthShowAceId		INTEGER,
        rcPrFilterAceEthShowSrcAddrList        	OCTET STRING,
        rcPrFilterAceEthShowSrcAddrOper        	INTEGER,
        rcPrFilterAceEthShowDstAddrList		OCTET STRING,
        rcPrFilterAceEthShowDstAddrOper        	INTEGER,	
	rcPrFilterAceEthShowEtherTypeList      	OCTET STRING,
        rcPrFilterAceEthShowEtherTypeOper      	INTEGER,
	rcPrFilterAceEthShowVlanTagPrio	 	INTEGER,
        rcPrFilterAceEthShowVlanTagPrioOper     INTEGER,
        rcPrFilterAceEthShowPort         	PortSet,
        rcPrFilterAceEthShowPortOper         	INTEGER,
        rcPrFilterAceEthShowVlanIdOper          INTEGER,
	rcPrFilterAceEthShowSrcAddrOperMask     DisplayString,
	rcPrFilterAceEthShowDstAddrOperMask     DisplayString,
	rcPrFilterAceEthShowVlanTagPrioOperMask	Integer32,
	rcPrFilterAceEthShowVlanIdOperMask      Integer32,
        rcPrFilterAceEthShowVlanId              INTEGER
        }

rcPrFilterAceEthShowAclId OBJECT-TYPE
     SYNTAX             INTEGER (1..2048)
     MAX-ACCESS         read-only 
     STATUS             current
     DESCRIPTION        "An index to the AceEthernetEntry, a unique 
	                identifier for Acl entry in the range of Table 
			Size."
     ::= { rcPrFilterAceEthShowEntry 1 }

rcPrFilterAceEthShowAceId OBJECT-TYPE
     SYNTAX             INTEGER (1..2000)
     MAX-ACCESS         read-only 
     STATUS             current
     DESCRIPTION        "An index to the AceEthernetEntry, a unique 
	                identifier for Acl entry in the range of Table 
			Size."
     ::= { rcPrFilterAceEthShowEntry 2 }

rcPrFilterAceEthShowSrcAddrList OBJECT-TYPE
     SYNTAX             OCTET STRING (SIZE(0..1500))
     MAX-ACCESS         read-only
     STATUS             current
     DESCRIPTION        "The list of ethernet source address to match." 
     ::= { rcPrFilterAceEthShowEntry 3 }

rcPrFilterAceEthShowSrcAddrOper OBJECT-TYPE
     SYNTAX             INTEGER {
                            eq(1),              -- exact match
			    mask(8),            -- mask
                            notConfigured(254)  -- not provisioned
                   }
     MAX-ACCESS         read-only
     STATUS             current
     DESCRIPTION        "Operators for Ace Ethernet Source MAC Address."
     ::= { rcPrFilterAceEthShowEntry 4 }

rcPrFilterAceEthShowDstAddrList OBJECT-TYPE
     SYNTAX             OCTET STRING (SIZE(0..1500))
     MAX-ACCESS         read-only
     STATUS             current
     DESCRIPTION        "List of ethernet destination address to 
			match."
     ::= { rcPrFilterAceEthShowEntry 5 }

rcPrFilterAceEthShowDstAddrOper OBJECT-TYPE
     SYNTAX             INTEGER {
                            eq(1),              -- exact match
			    mask(8),            -- mask
                            notConfigured(254)  -- not provisioned
                        }
     MAX-ACCESS         read-only
     STATUS             current
     DESCRIPTION        "Operators for Ace Ethernet Destination MAC Address."
     ::= { rcPrFilterAceEthShowEntry 6 }

rcPrFilterAceEthShowEtherTypeList OBJECT-TYPE
     SYNTAX             OCTET STRING (SIZE(0..1500))
     MAX-ACCESS         read-only
     STATUS             current
     DESCRIPTION        "EtherType value from ethernet header.  For example ARP
                         uses  0x0806, IP uses 0x0800. The platform support
                         determines the behavior for 802.1Q/p tagged packets.
                         The EtherType for 802.1Q tagged frames is 0x8100.

                         Valid range for the 16-bit Ether-type is 0..65535 
			 and the attribute supports lists/ranges of values.
                         Invalid ether-type value 65536 is interpreted as
                         field is not desired in match criteria."
	::= { rcPrFilterAceEthShowEntry 7 }

rcPrFilterAceEthShowEtherTypeOper OBJECT-TYPE
     SYNTAX             INTEGER {
                            eq(1),              -- exact match
                            notConfigured(254)  -- not provisioned
                        }
     MAX-ACCESS         read-only
     STATUS             current
     DESCRIPTION        "Ethernet Type Operators."
     ::= { rcPrFilterAceEthShowEntry 8 }

rcPrFilterAceEthShowVlanTagPrio  OBJECT-TYPE
     SYNTAX             INTEGER {
                            zero(0),
                            one(1),
                            two(2),
                            three(3),
                            four(4),
                            five(5),
                            six(6),
                            seven(7),
			    notConfigured(255)
                        }
     MAX-ACCESS         read-only
     STATUS             current
     DESCRIPTION        "Priority bits (3-bit field) from the 802.1Q/p tag."
     ::= { rcPrFilterAceEthShowEntry 9 }

rcPrFilterAceEthShowVlanTagPrioOper OBJECT-TYPE
     SYNTAX             INTEGER {
                            eq(1),              -- exact match
                            mask(8),            -- mask
                            notConfigured(254)  -- not provisioned
                        }
     MAX-ACCESS         read-only
     STATUS             current
     DESCRIPTION        "Operators for Ace Ethernet Vlan Tag Priority."
     ::= { rcPrFilterAceEthShowEntry 10 }

rcPrFilterAceEthShowPort OBJECT-TYPE
     SYNTAX             PortSet
     MAX-ACCESS         read-only
     STATUS             current
     DESCRIPTION        "Port Number or Port List to match on."
     ::= { rcPrFilterAceEthShowEntry 11 }

rcPrFilterAceEthShowPortOper OBJECT-TYPE
     SYNTAX             INTEGER {
                            eq(1),              -- exact match
                            notConfigured(254)  -- not provisioned
                        }
     MAX-ACCESS         read-only
     STATUS             current
     DESCRIPTION        "Operator for Ace Ethernet Port."
     ::= { rcPrFilterAceEthShowEntry 12 }

rcPrFilterAceEthShowVlanIdOper OBJECT-TYPE
     SYNTAX             INTEGER {
                            eq(1),             -- exact match
                            mask(8),           -- mask
                            notConfigured(254) -- not provisioned
                        }
     MAX-ACCESS         read-only
     STATUS             current
     DESCRIPTION        "Operator for Ace Ethernet VlanId."
     ::= { rcPrFilterAceEthShowEntry 14 }

rcPrFilterAceEthShowSrcAddrOperMask OBJECT-TYPE
     SYNTAX             DisplayString (SIZE(0..14))
     MAX-ACCESS         read-only
     STATUS             current
     DESCRIPTION        "The mask value in hex which can be set for the
			rcPrFilterAceEthSrcAddrOper when the option 
			selected is mask. It will be empty or
			set to 000000000000 whenrcPrFilterAceEthDstAddrOper
			is set to 'eq'. In case of the prefix '0x' is
			specified, 14 charaters is max length"
     ::= { rcPrFilterAceEthShowEntry 15 }

rcPrFilterAceEthShowDstAddrOperMask OBJECT-TYPE
     SYNTAX             DisplayString (SIZE(0..14))
     MAX-ACCESS         read-only
     STATUS             current
     DESCRIPTION        "The mask value in hex which can be set for the
			rcPrFilterAceEthDstAddrOper when the option 
			selected is mask. It will be empty or
			set to 000000000000 whenrcPrFilterAceEthDstAddrOper
			is set to 'eq'. In case of the prefix '0x' is
			specified, 14 charaters is max length"
     ::= { rcPrFilterAceEthShowEntry 16 }

rcPrFilterAceEthShowVlanTagPrioOperMask OBJECT-TYPE
     SYNTAX             Integer32 (0..'7'h)
     MAX-ACCESS         read-only
     STATUS             current
     DESCRIPTION        "The mask value in hex which can be set for the
			rcPrFilterAceEthVlanTagPrioOper when the option 
                        selected is masked. This object is applicable for
                        VSP9000. Not for ERS8600"
     ::= { rcPrFilterAceEthShowEntry 17 }

rcPrFilterAceEthShowVlanIdOperMask OBJECT-TYPE
     SYNTAX             Integer32(0..'FFF'h)
     MAX-ACCESS         read-only
     STATUS             current
     DESCRIPTION        "The mask value in hex which can be set for the
                        rcPrFilterAceEthVlanIdOper when the option
                        selected is mask. This object is used with
			rcPrFilterAceEthVlanIdVlanId in VSP 9000 to
			replace rcPrFilterAceEthVlanIdVlanIdList "
     ::= { rcPrFilterAceEthShowEntry 18 }

rcPrFilterAceEthShowVlanId OBJECT-TYPE
     SYNTAX             INTEGER (0..4084)
     MAX-ACCESS         read-only
     STATUS             current
     DESCRIPTION        "Vlan Id to match on. VSP9000  use this object with
			object rcPrFilterAceEthVlanIdOperMask to replace the
			rcPrFilterAceEthVlanIdVlanIdList"
     ::= { rcPrFilterAceEthShowEntry 19 }

-- ACE IP Show Table

rcPrFilterAceIpShowTable OBJECT-TYPE
     SYNTAX             SEQUENCE OF RcPrFilterAceIpShowEntry
     MAX-ACCESS         not-accessible
     STATUS             current
     DESCRIPTION        "A table of Aces to store IP Header
                        information of each Ace in context of
                        its parent Acl. "
     ::= { rcPrFilterAce 26 }

rcPrFilterAceIpShowEntry OBJECT-TYPE
     SYNTAX             RcPrFilterAceIpShowEntry
     MAX-ACCESS         not-accessible 
     STATUS             current
     DESCRIPTION        "One Ace entry holding Ace IP information.
                         Ace is a member of one Acl."
     INDEX              { rcPrFilterAceIpShowAclId,
                          rcPrFilterAceIpShowAceId}
     ::= { rcPrFilterAceIpShowTable 1 }

RcPrFilterAceIpShowEntry ::= SEQUENCE {
        rcPrFilterAceIpShowAclId	     	INTEGER,
        rcPrFilterAceIpShowAceId	     	INTEGER,
        rcPrFilterAceIpShowSrcAddrOper 		INTEGER,
        rcPrFilterAceIpShowDstAddrOper      	INTEGER,
        rcPrFilterAceIpShowDscpList         	OCTET STRING,
        rcPrFilterAceIpShowDscpOper         	INTEGER,
        rcPrFilterAceIpShowProtoList        	OCTET STRING,
        rcPrFilterAceIpShowProtoOper        	INTEGER,
	rcPrFilterAceIpShowOptions	     	INTEGER,
        rcPrFilterAceIpShowOptionsOper      	INTEGER,
        rcPrFilterAceIpShowFragmentation    	INTEGER,
        rcPrFilterAceIpShowFragOper         	INTEGER,
        rcPrFilterAceIpShowSrcAddrIpAddr        IpAddress,
	rcPrFilterAceIpShowSrcAddrOperMaskRange IpAddress,
        rcPrFilterAceIpShowDstAddrIpAddr        IpAddress,
	rcPrFilterAceIpShowDstAddrOperMaskRange IpAddress,
	rcPrFilterAceIpShowDscpOperMask	     	Integer32
        }

rcPrFilterAceIpShowAclId OBJECT-TYPE
     SYNTAX             INTEGER (1..2048)
     MAX-ACCESS         read-only
     STATUS             current
     DESCRIPTION        "An index to the AceIpShowEntry, a unique 
	                identifier for Acl entry in the range of Table 
			Size."
     ::= { rcPrFilterAceIpShowEntry 1 }

rcPrFilterAceIpShowAceId OBJECT-TYPE
     SYNTAX             INTEGER (1..2000)
     MAX-ACCESS         read-only
     STATUS             current
     DESCRIPTION        "An index to the AceIpShowEntry, a unique 
	                identifier for Acl entry in the range of Table 
			Size."
     ::= { rcPrFilterAceIpShowEntry 2 }

rcPrFilterAceIpShowSrcAddrOper OBJECT-TYPE
     SYNTAX             INTEGER {
                            eq(1),             -- exact match
			    mask(9),
			    range(10),
			    notConfigured(254) -- not provisioned
                        }
     MAX-ACCESS         read-only
     STATUS             current
     DESCRIPTION        "Operators for Ace Ip Source Address."
     ::= { rcPrFilterAceIpShowEntry 4 }

rcPrFilterAceIpShowDstAddrOper OBJECT-TYPE
     SYNTAX             INTEGER {
                            eq(1),             -- exact match
			    mask(9),
			    range(10),
                            notConfigured(254) -- not provisioned
                        }
     MAX-ACCESS         read-only
     STATUS             current
     DESCRIPTION        "Operators for Ace Ip Destination Address."
     ::= { rcPrFilterAceIpShowEntry 6 }

rcPrFilterAceIpShowDscpList  OBJECT-TYPE
     SYNTAX             OCTET STRING (SIZE(0..1500))
     MAX-ACCESS         read-only
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to match specific diffserv class traffic.
                        Set the field value to desired dscp code for
                        'rcPrFilterAceIpDscp' field to match non-standard
                        traffic classes and local use PHBs."
     DEFVAL             { "disable" }
     ::= { rcPrFilterAceIpShowEntry 7 }

rcPrFilterAceIpShowDscpOper OBJECT-TYPE
     SYNTAX             INTEGER {
                            eq(1),              -- exact match
                            mask(8),
                            notConfigured(254)  -- not provisioned
                        }
     MAX-ACCESS         read-only
     STATUS             current
     DESCRIPTION        "Operators for Ace Ip Dscp."
     ::= { rcPrFilterAceIpShowEntry 8 }

rcPrFilterAceIpShowProtoList OBJECT-TYPE
     SYNTAX             OCTET STRING (SIZE(0..1500))
     MAX-ACCESS         read-only
     STATUS             current 
     DESCRIPTION        "Ip protocol Type from the ip header to be matched.
                        Valid Ip protocol range is 0..255. Few of the Protocol
                        Types are enumerated above. In case the desired
                        protocol number is not available in the enumerated
                        list set protocol to desired integer value"
     ::= { rcPrFilterAceIpShowEntry 9 }

rcPrFilterAceIpShowProtoOper OBJECT-TYPE
     SYNTAX             INTEGER {
                            eq(1),               -- exact match
                            notConfigured(254)   -- not provisioned
                        }
     MAX-ACCESS         read-only
     STATUS             current
     DESCRIPTION        "Operators for Ace Ip Protocols."
     ::= { rcPrFilterAceIpShowEntry 10 }

rcPrFilterAceIpShowOptions  OBJECT-TYPE  
     SYNTAX             INTEGER {
			    noOperation(1),
			    recordRoute(7),
			    experimentalMeasurement(10),
 			    mtuProbe(11),
			    mtuReply(12),
			    encode(15),
			    timestamp(68),
			    traceroute(82),
			    baseSecurity(130),
			    looseSourceRoute(131),
			    extendedSecurity(133),
			    commercialSecurity(134),
			    streamID(136),
			    strictSourceRouting(137),
			    experimentalAccessControl(142),
			    imiTrafficDescriptor(144),
			    extendedIP(145),
			    addressExtension(147),
			    routeAlert(148),
			    selectiveDirectedBroadcast(149),
			    nsapAddresses(150),
			    dynamicPacketState(151),
			    upstreamMulticastPacket(152),
			    experimentalFlowControl(205)
			}
     MAX-ACCESS         read-only
     STATUS             current
     DESCRIPTION        "Ip options to be matched from the IP Header."
     ::= { rcPrFilterAceIpShowEntry 11 }

rcPrFilterAceIpShowOptionsOper OBJECT-TYPE 
     SYNTAX             INTEGER {
                            any(5),
			    notConfigured(254) -- not provisioned
			}
     MAX-ACCESS         read-only
     STATUS             current
     DESCRIPTION        "Logical Operator - only 'any' is valid at present."
     DEFVAL		{ any }
     ::= { rcPrFilterAceIpShowEntry 12 }

rcPrFilterAceIpShowFragmentation OBJECT-TYPE
     SYNTAX             INTEGER {
                            noFragment(0),
                            anyFragment(1),
                            moreFragment(2),
                            unused3(3),
                            lastFragment(4),
                            unused5(5),
                            unused6(6),
                            unused7(7),
                            notConfigured(254)
                        }
     MAX-ACCESS         read-only
     STATUS             current
     DESCRIPTION        "Ip Fragmentation bits to be matched from the IP
                        Header."
     DEFVAL      { noFragment }
     ::= { rcPrFilterAceIpShowEntry 13 }

rcPrFilterAceIpShowFragOper OBJECT-TYPE
     SYNTAX             INTEGER {
                            eq(1),               -- exact match
                            notConfigured(254)   -- not provisioned
                        }
     MAX-ACCESS         read-only
     STATUS             current
     DESCRIPTION        "Operator for Ip fragmentation."
     ::= { rcPrFilterAceIpShowEntry 14 }

rcPrFilterAceIpShowSrcAddrIpAddr OBJECT-TYPE
     SYNTAX             IpAddress
     MAX-ACCESS         read-only
     STATUS        	current
     DESCRIPTION   	"IP Source Address to match from IP header. 
		        This object is defined and used  to replace
		        the rcPrFilterAceIpSrcAddrList by VSP 9000"
     ::= { rcPrFilterAceIpShowEntry 15 }

rcPrFilterAceIpShowSrcAddrOperMaskRange OBJECT-TYPE
     SYNTAX             IpAddress
     MAX-ACCESS         read-only
     STATUS             current
     DESCRIPTION        "The IP Mask value or High IP address based on 
			object rcPrFilterAceIpSrcAddrOper mask/range
			option is selected."
     ::= { rcPrFilterAceIpShowEntry 16 }

rcPrFilterAceIpShowDstAddrIpAddr OBJECT-TYPE
     SYNTAX             IpAddress
     MAX-ACCESS         read-only
     STATUS             current
     DESCRIPTION        "IP Source Address to match from IP header. 
		         This object is defined and used  to replace
		         the rcPrFilterAceIpSrcAddrList by VSP 9000"
     ::= { rcPrFilterAceIpShowEntry 17 }

rcPrFilterAceIpShowDstAddrOperMaskRange OBJECT-TYPE
     SYNTAX             IpAddress
     MAX-ACCESS         read-only
     STATUS             current
     DESCRIPTION        "The IP mask value or Hi Ip address based on
                        object rcPrFilterAceIpDstAddrOper mask/range
                        option is selected."
     ::= { rcPrFilterAceIpShowEntry 18 }

rcPrFilterAceIpShowDscpOperMask OBJECT-TYPE
     SYNTAX             Integer32(0..'40'h)
     MAX-ACCESS         read-only
     STATUS             current
     DESCRIPTION        "The mask value in hex which can be set for the 
                        rcPrFilterAceIpDscpOper when the option 
                        selected is mask. It will be set to 0 or be used
			when rcPrFilterAceIpDscpOper is set ro eq"
     ::= { rcPrFilterAceIpShowEntry 19 }


-- ACE Proto Show Table

rcPrFilterAceProtoShowTable OBJECT-TYPE
     SYNTAX             SEQUENCE OF RcPrFilterAceProtoShowEntry
     MAX-ACCESS         not-accessible
     STATUS             current
     DESCRIPTION        "A table of Aces to store Protocol Header
                        information of each Ace in context of
                        its parent Acl. "
     ::= { rcPrFilterAce 27 }

rcPrFilterAceProtoShowEntry OBJECT-TYPE
     SYNTAX             RcPrFilterAceProtoShowEntry
     MAX-ACCESS         not-accessible 
     STATUS             current
     DESCRIPTION        "One Ace entry holding Ace Ethernet information.
                         Ace is a member of one Acl."
     INDEX              { rcPrFilterAceProtoShowAclId,
                          rcPrFilterAceProtoShowAceId}
     ::= { rcPrFilterAceProtoShowTable 1 }

RcPrFilterAceProtoShowEntry ::= SEQUENCE {
        rcPrFilterAceProtoShowAclId     	INTEGER,
        rcPrFilterAceProtoShowAceId     	INTEGER,
        rcPrFilterAceProtoShowIcmpMsgTypeList  	OCTET STRING,
        rcPrFilterAceProtoShowIcmpMsgTypeOper  	INTEGER,
        rcPrFilterAceProtoShowTcpFlagsList     	OCTET STRING,
        rcPrFilterAceProtoShowTcpFlagsOper	INTEGER,
        rcPrFilterAceProtoShowSrcPort           OCTET STRING,
        rcPrFilterAceProtoShowSrcPortOper       INTEGER,
        rcPrFilterAceProtoShowSrcPortOperMaskRange Integer32,
        rcPrFilterAceProtoShowDstPort		OCTET STRING,
        rcPrFilterAceProtoShowDstPortOper	INTEGER,
	rcPrFilterAceProtoShowDstPortOperMaskRange Integer32,
	rcPrFilterAceProtoShowTcpFlagsOperMask  Integer32
        }

rcPrFilterAceProtoShowAclId OBJECT-TYPE
     SYNTAX             INTEGER (1..2048)
     MAX-ACCESS         read-only 
     STATUS             current
     DESCRIPTION        "An index to the AceProtoShowEntry, a unique 
	                identifier for Acl entry in the range of Table 
			Size."
     ::= { rcPrFilterAceProtoShowEntry 1 }
     
rcPrFilterAceProtoShowAceId OBJECT-TYPE
     SYNTAX             INTEGER (1..2000)
     MAX-ACCESS         read-only 
     STATUS             current
     DESCRIPTION        "An index to the AceProtoShowEntry, a unique 
	                identifier for Ace entry in the range of Table 
			Size."
     ::= { rcPrFilterAceProtoShowEntry 2 }

rcPrFilterAceProtoShowIcmpMsgTypeList OBJECT-TYPE
     SYNTAX             OCTET STRING (SIZE(0..1500)) 
     MAX-ACCESS         read-only
     STATUS             current
     DESCRIPTION        "One or a list of Icmp messages to be matched. 
			Need to provide strings, number of protocol header 
			types (pre-defined values plus user-defined headers). 
			Valid range is 0 to 255 (reserved)."
     ::= { rcPrFilterAceProtoShowEntry 11 }

rcPrFilterAceProtoShowIcmpMsgTypeOper OBJECT-TYPE
     SYNTAX             INTEGER {
                            eq(1),   -- exact match
                            notConfigured(254) -- not provisioned
                        } 
     MAX-ACCESS         read-only
     STATUS             current
     DESCRIPTION        "Operator for Ace Protocol IcmpMsgTypes."
     ::= { rcPrFilterAceProtoShowEntry 12 }

rcPrFilterAceProtoShowTcpFlagsList OBJECT-TYPE
     SYNTAX             OCTET STRING (SIZE(0..1500)) 
     MAX-ACCESS         read-only
     STATUS             current
     DESCRIPTION        "One or a list of Tcp flags to be matched. 
			Need to provide strings, number of protocol header 
			types (pre-defined values plus user-defined headers). 
			Valid range is 0 to 63"
     ::= { rcPrFilterAceProtoShowEntry 13 }

rcPrFilterAceProtoShowTcpFlagsOper OBJECT-TYPE
     SYNTAX             INTEGER {
                            eq(1),
			    matchAny(6),
			    matchAll(7),
			    mask(8),
			    notConfigured(254)  -- not provisioned
                        } 
     MAX-ACCESS         read-only
     STATUS             current
     DESCRIPTION        "Operator for Ace Protocol TcpFlags."
     ::= { rcPrFilterAceProtoShowEntry 14 }

rcPrFilterAceProtoShowSrcPort OBJECT-TYPE
     SYNTAX             OCTET STRING (SIZE(0..1500))
     MAX-ACCESS         read-only
     STATUS             current
     DESCRIPTION        "Port Number or Port List to match on."
     ::= { rcPrFilterAceProtoShowEntry 15 }

rcPrFilterAceProtoShowSrcPortOper OBJECT-TYPE
     SYNTAX             INTEGER {
                            eq(1),   -- exact match
                            mask(8), 
                            range(9),
			    notConfigured(254)
                        }
     MAX-ACCESS         read-only
     STATUS             current
     DESCRIPTION        "Operator for Ace Protocol SrcPort."
     ::= { rcPrFilterAceProtoShowEntry 16 }

rcPrFilterAceProtoShowSrcPortOperMaskRange OBJECT-TYPE
     SYNTAX             Integer32(0..'FFFF'h)
     MAX-ACCESS         read-only
     STATUS             current
     DESCRIPTION        "The value should be displayed in hex when
			rcPrFilterAceProtoSrcPortOper is set to 'mask'.
			This object will be used as a Range high value when
			rcPrFilterAceProtoSrcPortOper is set to 'range'.
			('range' is not supported in this 3.0 release).
			If it is used as range high value, it should be
			displayed in decimal formtat. 
			This object will be set to 0 when
			rcPrFilterAceProtoSrcPortOper is set to 'eq'" 
     ::= { rcPrFilterAceProtoShowEntry 17 }

rcPrFilterAceProtoShowDstPort OBJECT-TYPE
     SYNTAX             OCTET STRING (SIZE(0..1500))
     MAX-ACCESS         read-only
     STATUS             current
     DESCRIPTION        "Port Number or Port List to match on."
     ::= { rcPrFilterAceProtoShowEntry 18 }

rcPrFilterAceProtoShowDstPortOper OBJECT-TYPE
     SYNTAX             INTEGER {
                            eq(1),   -- exact match
                            mask(8),
                            range(9),
			    notConfigured(254)
                        }
     MAX-ACCESS         read-only
     STATUS             current
     DESCRIPTION        "Operator for Ace Protocol DstPort."
     ::= { rcPrFilterAceProtoShowEntry 19 }

rcPrFilterAceProtoShowDstPortOperMaskRange OBJECT-TYPE
     SYNTAX             Integer32(0..'FFFF'h)
     MAX-ACCESS         read-only
     STATUS             current
     DESCRIPTION        "The value should be displayed in hex when
			rcPrFilterAceProtoDstPortOper is set to 'mask'.
			This object will be used as a Range high value when
			rcPrFilterAceProtoDstPortOper is set to 'range'.
			('range' is not supported in this 3.0 release).
			If it is used as range high value, it should be
			displayed in decimal formtat. 
			This object will be set to 0 when
			rcPrFilterAceProtoDstPortOper is set to 'eq'"
     ::= { rcPrFilterAceProtoShowEntry 20 }

rcPrFilterAceProtoShowTcpFlagsOperMask OBJECT-TYPE
     SYNTAX             Integer32(0..'3F'h)
     MAX-ACCESS         read-only
     STATUS             current
     DESCRIPTION        "The mask value in hex which can be set for the
                        rcPrFilterAceProtoTcpFlagsOper when the option
                        selected is mask. It will be set 0x0 when object
			rcPrFilterAceProtoTcpFlagsOper is set to eq"
     ::= { rcPrFilterAceProtoShowEntry 21 }

-- ACE Pattern Show Table

rcPrFilterAcePatternShowTable OBJECT-TYPE
     SYNTAX             SEQUENCE OF RcPrFilterAcePatternShowEntry
     MAX-ACCESS         not-accessible
     STATUS             current
     DESCRIPTION        "A table of Aces to store Pattern 1, 2, 3 
			Header information of each Ace in context of
                        its parent Acl. "
     ::= { rcPrFilterAce 28 }

rcPrFilterAcePatternShowEntry OBJECT-TYPE
     SYNTAX             RcPrFilterAcePatternShowEntry
     MAX-ACCESS         not-accessible 
     STATUS             current
     DESCRIPTION        "One Ace entry holding Ace Pattern 1, 2, 3
			 information.  Ace is a member of one Acl."
     INDEX              { rcPrFilterAcePatternShowAclId,
                          rcPrFilterAcePatternShowAceId}
     ::= { rcPrFilterAcePatternShowTable 1 }

RcPrFilterAcePatternShowEntry ::= SEQUENCE {
        rcPrFilterAcePatternShowAclId		INTEGER,
        rcPrFilterAcePatternShowAceId		INTEGER,
        rcPrFilterAcePatternShowPattern1Name	DisplayString,
        rcPrFilterAcePatternShowPattern1Value  	OCTET STRING,
        rcPrFilterAcePatternShowPattern1Oper   	INTEGER,
        rcPrFilterAcePatternShowPattern2Name   	DisplayString,
        rcPrFilterAcePatternShowPattern2Value  	OCTET STRING,
        rcPrFilterAcePatternShowPattern2Oper   	INTEGER,
        rcPrFilterAcePatternShowPattern3Name   	DisplayString,
        rcPrFilterAcePatternShowPattern3Value  	OCTET STRING,
        rcPrFilterAcePatternShowPattern3Oper   	INTEGER
        }

rcPrFilterAcePatternShowAclId OBJECT-TYPE
     SYNTAX             INTEGER (1..4096)
     MAX-ACCESS         read-only
     STATUS             current
     DESCRIPTION        "An index to the AcePatternEntry, a unique 
	                identifier for Acl entry in the range of Table 
			Size."
     ::= { rcPrFilterAcePatternShowEntry 1 }

rcPrFilterAcePatternShowAceId OBJECT-TYPE
     SYNTAX             INTEGER (1..1000)
     MAX-ACCESS         read-only
     STATUS             current
     DESCRIPTION        "An index to the AcePatternEntry, a unique 
	                identifier for Acl entry in the range of Table 
			Size."
     ::= { rcPrFilterAcePatternShowEntry 2 }

rcPrFilterAcePatternShowPattern1Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 3 }

rcPrFilterAcePatternShowPattern1Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 4 }

rcPrFilterAcePatternShowPattern1Oper OBJECT-TYPE
     SYNTAX             INTEGER {
                            eq(1),    -- exact match
                            le(3),    -- less than or equal to
                            ge(4),    -- greater than or equal to
                            any(255)  -- not provisioned
                        }
     MAX-ACCESS         read-only
     STATUS             current
     DESCRIPTION        "Operators for Ace Pattern."
     ::= { rcPrFilterAcePatternShowEntry 5 }

rcPrFilterAcePatternShowPattern2Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 6 }

rcPrFilterAcePatternShowPattern2Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 7 }

rcPrFilterAcePatternShowPattern2Oper OBJECT-TYPE
     SYNTAX             INTEGER {
                            eq(1),    -- exact match
                            le(3),    -- less than or equal to
                            ge(4),    -- greater than or equal to
                            any(255)  -- not provisioned
                        }
     MAX-ACCESS         read-only
     STATUS             current
     DESCRIPTION        "Operators for Ace Pattern."
     ::= { rcPrFilterAcePatternShowEntry 8 }

rcPrFilterAcePatternShowPattern3Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 9 }

rcPrFilterAcePatternShowPattern3Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 10 }

rcPrFilterAcePatternShowPattern3Oper OBJECT-TYPE
     SYNTAX             INTEGER {
                            eq(1),    -- exact match
                            le(3),    -- less than or equal to
                            ge(4),    -- greater than or equal to
                           any(255)   -- not provisioned
                        }
     MAX-ACCESS         read-only
     STATUS             current
     DESCRIPTION        "Operators for Ace Pattern."
     ::= { rcPrFilterAcePatternShowEntry 11 }

-- ACE Ipv6 Source Address Table

rcPrFilterAceIpv6SrcAddrTable OBJECT-TYPE
     SYNTAX             SEQUENCE OF RcPrFilterAceIpv6SrcAddrEntry
     MAX-ACCESS         not-accessible
     STATUS             current
     DESCRIPTION        "A table of Aces to store IPv6 Source Address Header
                        information of each Ace in context of its parent Acl."
     ::= { rcPrFilterAce 29 }

rcPrFilterAceIpv6SrcAddrEntry OBJECT-TYPE
     SYNTAX             RcPrFilterAceIpv6SrcAddrEntry
     MAX-ACCESS         not-accessible
     STATUS             current
     DESCRIPTION        "One Ace entry holding Ace IPv6 Source Address Header
                        information. An Ace is a member of one Acl."
     INDEX              { rcPrFilterAceIpv6SrcAddrAclId,
                          rcPrFilterAceIpv6SrcAddrAceId }
     ::= { rcPrFilterAceIpv6SrcAddrTable 1 }

RcPrFilterAceIpv6SrcAddrEntry ::= SEQUENCE {
        rcPrFilterAceIpv6SrcAddrAclId          INTEGER,
        rcPrFilterAceIpv6SrcAddrAceId          INTEGER,
        rcPrFilterAceIpv6SrcAddrList           OCTET STRING,
        rcPrFilterAceIpv6SrcAddrListCount      INTEGER,
        rcPrFilterAceIpv6SrcAddrOper           INTEGER,
        rcPrFilterAceIpv6SrcAddrRowStatus      RowStatus
        }

rcPrFilterAceIpv6SrcAddrAclId OBJECT-TYPE
     SYNTAX             INTEGER (1..2048)
     MAX-ACCESS         read-only
     STATUS             current
     DESCRIPTION        "An index to the AceIpv6SrcAddrEntry, a unique
                        identifier for Acl entry in the range of Table
                        Size."
     ::= { rcPrFilterAceIpv6SrcAddrEntry 1 }

rcPrFilterAceIpv6SrcAddrAceId OBJECT-TYPE
     SYNTAX             INTEGER (1..2000)
     MAX-ACCESS         read-only
     STATUS             current
     DESCRIPTION        "An index to the AceIpv6SrcAddrEntry, a unique
                        identifier for Acl entry in the range of Table
                        Size."
     ::= { rcPrFilterAceIpv6SrcAddrEntry 2 }

rcPrFilterAceIpv6SrcAddrList OBJECT-TYPE
     SYNTAX             OCTET STRING (SIZE(0..1500))
     MAX-ACCESS         read-write
     STATUS             current
     DESCRIPTION        "The list of ipv6 source address to match from IPv6
                        header."
     ::= { rcPrFilterAceIpv6SrcAddrEntry 3 }

rcPrFilterAceIpv6SrcAddrListCount OBJECT-TYPE
     SYNTAX             INTEGER(1..100)
     MAX-ACCESS         read-write
     STATUS             current
     DESCRIPTION        "Count to store the number of discrete ranges
                        entered for the ipv6 src address."
     ::= { rcPrFilterAceIpv6SrcAddrEntry 4 }

rcPrFilterAceIpv6SrcAddrOper OBJECT-TYPE
     SYNTAX             INTEGER {
                            eq(1),    -- exact match
                            ne(2)    -- not equal
                        }
     MAX-ACCESS         read-write
     STATUS             current
     DESCRIPTION        "Operators for Ace Ipv6 Source Address."
     ::= { rcPrFilterAceIpv6SrcAddrEntry 5 }

rcPrFilterAceIpv6SrcAddrRowStatus OBJECT-TYPE
     SYNTAX             RowStatus
     MAX-ACCESS         read-create
     STATUS             current
     DESCRIPTION        "Create/delete operations for this entry."
     ::= { rcPrFilterAceIpv6SrcAddrEntry 6 }

-- ACE Ipv6 Destination Address Table

rcPrFilterAceIpv6DstAddrTable OBJECT-TYPE
     SYNTAX             SEQUENCE OF RcPrFilterAceIpv6DstAddrEntry
     MAX-ACCESS         not-accessible
     STATUS             current
     DESCRIPTION        "A table of Aces to store IPv6 Destination Address
                        Header information of each Ace in context of its
                        parent Acl."
     ::= { rcPrFilterAce 30 }

rcPrFilterAceIpv6DstAddrEntry OBJECT-TYPE
     SYNTAX             RcPrFilterAceIpv6DstAddrEntry
     MAX-ACCESS         not-accessible
     STATUS             current
     DESCRIPTION        "One Ace entry holding Ace IPv6 Destination Address
                        Header information. An Ace is a member of one Acl."
     INDEX              { rcPrFilterAceIpv6DstAddrAclId,
                          rcPrFilterAceIpv6DstAddrAceId }
     ::= { rcPrFilterAceIpv6DstAddrTable 1 }

RcPrFilterAceIpv6DstAddrEntry ::= SEQUENCE {
        rcPrFilterAceIpv6DstAddrAclId          INTEGER,
        rcPrFilterAceIpv6DstAddrAceId          INTEGER,
        rcPrFilterAceIpv6DstAddrList           OCTET STRING,
        rcPrFilterAceIpv6DstAddrListCount      INTEGER,
        rcPrFilterAceIpv6DstAddrOper           INTEGER,
        rcPrFilterAceIpv6DstAddrRowStatus      RowStatus
        }

rcPrFilterAceIpv6DstAddrAclId OBJECT-TYPE
     SYNTAX             INTEGER (1..2048)
     MAX-ACCESS         read-only
     STATUS             current
     DESCRIPTION        "An index to the AceIpv6DstAddrEntry, a unique
                        identifier for Acl entry in the range of Table
                        Size."
     ::= { rcPrFilterAceIpv6DstAddrEntry 1 }

rcPrFilterAceIpv6DstAddrAceId OBJECT-TYPE
     SYNTAX             INTEGER (1..2000)
     MAX-ACCESS         read-only
     STATUS             current
     DESCRIPTION        "An index to the AceIpv6DstAddrEntry, a unique
                        identifier for Acl entry in the range of Table
                        Size."
     ::= { rcPrFilterAceIpv6DstAddrEntry 2 }

rcPrFilterAceIpv6DstAddrList OBJECT-TYPE
     SYNTAX             OCTET STRING (SIZE(0..1500))
     MAX-ACCESS         read-write
     STATUS             current
     DESCRIPTION        "The list of ipv6 dst  address to match from IPv6 header."
     ::= { rcPrFilterAceIpv6DstAddrEntry 3 }

rcPrFilterAceIpv6DstAddrListCount OBJECT-TYPE
     SYNTAX             INTEGER(1..100)
     MAX-ACCESS         read-write
     STATUS             current
     DESCRIPTION        "Count to store the number of discrete ranges
                        entered for the IPv6 Destination Address."
     ::= { rcPrFilterAceIpv6DstAddrEntry 4 }

rcPrFilterAceIpv6DstAddrOper OBJECT-TYPE
     SYNTAX             INTEGER {
                            eq(1),    -- exact match
                            ne(2)    -- not equal
                        }
     MAX-ACCESS         read-write
     STATUS             current
     DESCRIPTION        "Operators for Ace IPv6 Destination Address."
     ::= { rcPrFilterAceIpv6DstAddrEntry 5 }

rcPrFilterAceIpv6DstAddrRowStatus OBJECT-TYPE
     SYNTAX             RowStatus
     MAX-ACCESS         read-create
     STATUS             current
     DESCRIPTION        "Create/delete operations for this entry."
     ::= { rcPrFilterAceIpv6DstAddrEntry 6 }

-- ACE Ipv6 Next header Table

rcPrFilterAceIpv6NextHdrTable OBJECT-TYPE
     SYNTAX             SEQUENCE OF RcPrFilterAceIpv6NextHdrEntry
     MAX-ACCESS         not-accessible
     STATUS             current
     DESCRIPTION        "A table of Aces to store IPv6 Next header
                        Header information of each Ace in context of its
                        parent Acl."
     ::= { rcPrFilterAce 31 }

rcPrFilterAceIpv6NextHdrEntry OBJECT-TYPE
     SYNTAX             RcPrFilterAceIpv6NextHdrEntry
     MAX-ACCESS         not-accessible
     STATUS             current
     DESCRIPTION        "One Ace entry holding Ace IPv6 Next header
                         information. An Ace is a member of one Acl."
     INDEX              { rcPrFilterAceIpv6NextHdrAclId,
                          rcPrFilterAceIpv6NextHdrAceId }
     ::= { rcPrFilterAceIpv6NextHdrTable 1 }

RcPrFilterAceIpv6NextHdrEntry ::= SEQUENCE {
        rcPrFilterAceIpv6NextHdrAclId          INTEGER,
        rcPrFilterAceIpv6NextHdrAceId          INTEGER,
        rcPrFilterAceIpv6NextHdrNextHdr        Ipv6NextHdr,
        rcPrFilterAceIpv6NextHdrOper           INTEGER,
        rcPrFilterAceIpv6NextHdrRowStatus      RowStatus
        }

rcPrFilterAceIpv6NextHdrAclId OBJECT-TYPE
     SYNTAX             INTEGER (1..2048)
     MAX-ACCESS         read-only
     STATUS             current
     DESCRIPTION        "An index to the AceIpv6NextHdrEntry, a unique
                        identifier for Acl entry in the range of Table
                        Size."
     ::= { rcPrFilterAceIpv6NextHdrEntry 1 }

rcPrFilterAceIpv6NextHdrAceId OBJECT-TYPE
     SYNTAX             INTEGER (1..2000)
     MAX-ACCESS         read-only
     STATUS             current
     DESCRIPTION        "An index to the AceIpv6NextHdrEntry, a unique
                        identifier for Acl entry in the range of Table
                        Size."
     ::= { rcPrFilterAceIpv6NextHdrEntry 2 }

rcPrFilterAceIpv6NextHdrNextHdr OBJECT-TYPE
     SYNTAX             Ipv6NextHdr
     MAX-ACCESS         read-write
     STATUS             current
     DESCRIPTION        "The ipv6 next header to look for."
     ::= { rcPrFilterAceIpv6NextHdrEntry 3 }

rcPrFilterAceIpv6NextHdrOper OBJECT-TYPE
     SYNTAX             INTEGER {
                            eq(1),    -- exact match
                            ne(2)    -- not equal
                        }
     MAX-ACCESS         read-write
     STATUS             current
     DESCRIPTION        "Operators for Ace IPv6 Next header."
     ::= { rcPrFilterAceIpv6NextHdrEntry 4 }

rcPrFilterAceIpv6NextHdrRowStatus OBJECT-TYPE
     SYNTAX             RowStatus
     MAX-ACCESS         read-create
     STATUS             current
     DESCRIPTION        "Create/delete operations for this entry."
     ::= { rcPrFilterAceIpv6NextHdrEntry 5 }

-- ACE IPv6 Show Table

rcPrFilterAceIpv6ShowTable OBJECT-TYPE
     SYNTAX             SEQUENCE OF RcPrFilterAceIpv6ShowEntry
     MAX-ACCESS         not-accessible
     STATUS             current
     DESCRIPTION        "A table of Aces to display ipv6
                        information of each Ace in context of
                        its parent Acl. "
     ::= { rcPrFilterAce 32 }

rcPrFilterAceIpv6ShowEntry OBJECT-TYPE
     SYNTAX             RcPrFilterAceIpv6ShowEntry
     MAX-ACCESS         not-accessible
     STATUS             current
     DESCRIPTION        "One Ace entry holding Ace ipv6 information.
                         Ace is a member of one Acl."
     INDEX              { rcPrFilterAceIpv6ShowAclId,
                          rcPrFilterAceIpv6ShowAceId}
     ::= { rcPrFilterAceIpv6ShowTable 1 }

RcPrFilterAceIpv6ShowEntry ::= SEQUENCE {
        rcPrFilterAceIpv6ShowAclId               INTEGER,
        rcPrFilterAceIpv6ShowAceId               INTEGER,
        rcPrFilterAceIpv6ShowSrcAddrList         OCTET STRING,
        rcPrFilterAceIpv6ShowSrcAddrOper         INTEGER,
        rcPrFilterAceIpv6ShowDstAddrList         OCTET STRING,
        rcPrFilterAceIpv6ShowDstAddrOper         INTEGER,
        rcPrFilterAceIpv6ShowNxtHdrNxtHdr        Ipv6NextHdr,
        rcPrFilterAceIpv6ShowNxtHdrOper          INTEGER
        }

rcPrFilterAceIpv6ShowAclId OBJECT-TYPE
     SYNTAX                INTEGER (1..2048)
     MAX-ACCESS            read-only
     STATUS                current
     DESCRIPTION           "An index to the AceIpv6Entry, a unique
                        identifier for Acl entry in the range of Table
                        Size."
     ::= { rcPrFilterAceIpv6ShowEntry 1 }

rcPrFilterAceIpv6ShowAceId OBJECT-TYPE
     SYNTAX                INTEGER (1..2000)
     MAX-ACCESS            read-only
     STATUS                current
     DESCRIPTION           "An index to the AceIpv6Entry, a unique
                        identifier for Acl entry in the range of Table
                        Size."
     ::= { rcPrFilterAceIpv6ShowEntry 2 }

rcPrFilterAceIpv6ShowSrcAddrList OBJECT-TYPE
     SYNTAX                      OCTET STRING (SIZE(0..1500))
     MAX-ACCESS                  read-only
     STATUS                      current
     DESCRIPTION                 "The list of v6 source address to display."
     ::= { rcPrFilterAceIpv6ShowEntry 3 }

rcPrFilterAceIpv6ShowSrcAddrOper OBJECT-TYPE
     SYNTAX                      INTEGER {
                                   eq(1),    -- exact match
                                   ne(2),    -- not equal
                                   any(255)  -- not provisioned
                                 }
     MAX-ACCESS                  read-only
     STATUS                      current
     DESCRIPTION                 "Operators for Ace v6 Source Address."
     ::= { rcPrFilterAceIpv6ShowEntry 4 }

rcPrFilterAceIpv6ShowDstAddrList OBJECT-TYPE
     SYNTAX                      OCTET STRING (SIZE(0..1500))
     MAX-ACCESS                  read-only
     STATUS                      current
     DESCRIPTION                 "List of v6 destination address to display."
     ::= { rcPrFilterAceIpv6ShowEntry 5 }

rcPrFilterAceIpv6ShowDstAddrOper OBJECT-TYPE
     SYNTAX                      INTEGER {
                                  eq(1),    -- exact match
                                  ne(2),    -- not equal
                                  any(255)  -- not provisioned
                                 }
     MAX-ACCESS                  read-only
     STATUS                      current
     DESCRIPTION                 "Operators for Ace v6 Destination Address."
     ::= { rcPrFilterAceIpv6ShowEntry 6 }

rcPrFilterAceIpv6ShowNxtHdrNxtHdr OBJECT-TYPE
     SYNTAX                       Ipv6NextHdr
     MAX-ACCESS                   read-only
     STATUS                       current
     DESCRIPTION                  "v6 next hdr to display."
     ::= { rcPrFilterAceIpv6ShowEntry 7 }

rcPrFilterAceIpv6ShowNxtHdrOper OBJECT-TYPE
     SYNTAX                     INTEGER {
                                 eq(1),  -- exact match
                                 ne(2),    -- not equal
                                 any(255)  -- not provisioned
                                }
     MAX-ACCESS                 read-only
     STATUS                     current
     DESCRIPTION                "Operator for Ace v6 next hdr."
     ::= { rcPrFilterAceIpv6ShowEntry 8 }


-- ACE Protocol TCP/UDP Src Port Table

rcPrFilterAceProtoSrcPortTable OBJECT-TYPE
     SYNTAX             SEQUENCE OF RcPrFilterAceProtoSrcPortEntry
     MAX-ACCESS         not-accessible
     STATUS             current
     DESCRIPTION        "A table of Aces to store TCP/UDP Source Port information
                        of each Ace in context of its parent Acl."
     ::= { rcPrFilterAce 33 }

rcPrFilterAceProtoSrcPortEntry OBJECT-TYPE
     SYNTAX             RcPrFilterAceProtoSrcPortEntry
     MAX-ACCESS         not-accessible
     STATUS             current
     DESCRIPTION        "One entry holding Ace Protocol TCP/UDP Source Port
                        information. An Ace is a member of one Acl."
     INDEX              { rcPrFilterAceProtoSrcPortAclId,
                          rcPrFilterAceProtoSrcPortAceId }
     ::= { rcPrFilterAceProtoSrcPortTable 1 }

RcPrFilterAceProtoSrcPortEntry ::= SEQUENCE {
        rcPrFilterAceProtoSrcPortAclId     INTEGER,
        rcPrFilterAceProtoSrcPortAceId     INTEGER,
        rcPrFilterAceProtoSrcPortPort      OCTET STRING,
        rcPrFilterAceProtoSrcPortCount     INTEGER,
        rcPrFilterAceProtoSrcPortOper      INTEGER,
        rcPrFilterAceProtoSrcPortRowStatus RowStatus,
	rcPrFilterAceProtoSrcPortOperMaskRange Integer32
        }

rcPrFilterAceProtoSrcPortAclId OBJECT-TYPE
     SYNTAX             INTEGER (1..2048)
     MAX-ACCESS         read-only
     STATUS             current
     DESCRIPTION        "An index to the AceProtoSrcPortEntry, a unique
                        identifier for Acl entry in the range of Table
                        Size."
     ::= { rcPrFilterAceProtoSrcPortEntry 1 }

rcPrFilterAceProtoSrcPortAceId OBJECT-TYPE
     SYNTAX             INTEGER (1..2000)
     MAX-ACCESS         read-only
     STATUS             current
     DESCRIPTION        "An index to the AceProtoSrcPortEntry, a unique
                        identifier for Ace entry in the range of Table
                        Size."
     ::= { rcPrFilterAceProtoSrcPortEntry 2 }

rcPrFilterAceProtoSrcPortPort OBJECT-TYPE
     SYNTAX             OCTET STRING (SIZE(0..1500))
     MAX-ACCESS         read-write
     STATUS             current
     DESCRIPTION        "Port Number or Port List to match on."
     ::= { rcPrFilterAceProtoSrcPortEntry 3 }

rcPrFilterAceProtoSrcPortCount OBJECT-TYPE
     SYNTAX             INTEGER(1..100)
     MAX-ACCESS         read-write
     STATUS             current
     DESCRIPTION        "Count to store the number of discrete ranges
                        entered for the TCP source port."
     ::= { rcPrFilterAceProtoSrcPortEntry 4 }

rcPrFilterAceProtoSrcPortOper OBJECT-TYPE
     SYNTAX             INTEGER {
                            eq(1),   -- exact match
                            mask(8), 
                            range(9)  
                        }
     MAX-ACCESS         read-write
     STATUS             current
     DESCRIPTION        "Operator for Ace Protocol SrcPort."
     ::= { rcPrFilterAceProtoSrcPortEntry 5 }

rcPrFilterAceProtoSrcPortRowStatus OBJECT-TYPE
     SYNTAX             RowStatus
     MAX-ACCESS         read-write
     STATUS             current
     DESCRIPTION        "Create/delete operations for this entry."
     ::= { rcPrFilterAceProtoSrcPortEntry 6 }

rcPrFilterAceProtoSrcPortOperMaskRange OBJECT-TYPE
     SYNTAX             Integer32(0..'FFFF'h)
     MAX-ACCESS         read-write
     STATUS             current
     DESCRIPTION        "The value should be displayed in hex when
			rcPrFilterAceProtoSrcPortOper is set to 'mask'.
			This object will be used as a Range high value when
			rcPrFilterAceProtoSrcPortOper is set to 'range'.
			('range' is not supported in this 3.0 release).
			If it is used as range high value, it should be
			displayed in decimal formtat. 
			This object will be set to 0 when
			rcPrFilterAceProtoSrcPortOper is set to 'eq'" 
     ::= { rcPrFilterAceProtoSrcPortEntry 7 }

-- ACE Protocol TCP/UDP DstPort Table

rcPrFilterAceProtoDstPortTable OBJECT-TYPE
     SYNTAX             SEQUENCE OF RcPrFilterAceProtoDstPortEntry
     MAX-ACCESS         not-accessible
     STATUS             current
     DESCRIPTION        "A table of Aces to store TCP Dest Port information
                        of each Ace in context of its parent Acl."
     ::= { rcPrFilterAce 34 }

rcPrFilterAceProtoDstPortEntry OBJECT-TYPE
     SYNTAX             RcPrFilterAceProtoDstPortEntry
     MAX-ACCESS         not-accessible
     STATUS             current
     DESCRIPTION        "One entry holding Ace Protocol TCP Dest Port
                        information. An Ace is a member of one Acl."
     INDEX              { rcPrFilterAceProtoDstPortAclId,
                          rcPrFilterAceProtoDstPortAceId }
     ::= { rcPrFilterAceProtoDstPortTable 1 }

RcPrFilterAceProtoDstPortEntry ::= SEQUENCE {
        rcPrFilterAceProtoDstPortAclId     INTEGER,
        rcPrFilterAceProtoDstPortAceId     INTEGER,
        rcPrFilterAceProtoDstPortPort      OCTET STRING,
        rcPrFilterAceProtoDstPortCount     INTEGER,
        rcPrFilterAceProtoDstPortOper      INTEGER,
        rcPrFilterAceProtoDstPortRowStatus RowStatus,
	rcPrFilterAceProtoDstPortOperMaskRange Integer32
        }

rcPrFilterAceProtoDstPortAclId OBJECT-TYPE
     SYNTAX             INTEGER (1..2048)
     MAX-ACCESS         read-only
     STATUS             current
     DESCRIPTION        "An index to the AceProtoDstPortEntry, a unique
                        identifier for Acl entry in the range of Table
                        Size."
     ::= { rcPrFilterAceProtoDstPortEntry 1 }

rcPrFilterAceProtoDstPortAceId OBJECT-TYPE
     SYNTAX             INTEGER (1..2000)
     MAX-ACCESS         read-only
     STATUS             current
     DESCRIPTION        "An index to the AceProtoDstPortEntry, a unique
                        identifier for Ace entry in the range of Table
                        Size."
     ::= { rcPrFilterAceProtoDstPortEntry 2 }

rcPrFilterAceProtoDstPortPort OBJECT-TYPE
     SYNTAX             OCTET STRING (SIZE(0..1500))
     MAX-ACCESS         read-write
     STATUS             current
     DESCRIPTION        "Port Number or Port List to match on."
     ::= { rcPrFilterAceProtoDstPortEntry 3 }

rcPrFilterAceProtoDstPortCount OBJECT-TYPE
     SYNTAX             INTEGER(1..100)
     MAX-ACCESS         read-write
     STATUS             current
     DESCRIPTION        "Count to store the number of discrete ranges
                        entered for the TCP dest port."
     ::= { rcPrFilterAceProtoDstPortEntry 4 }

rcPrFilterAceProtoDstPortOper OBJECT-TYPE
     SYNTAX             INTEGER {
                            eq(1),   -- exact match
                            mask(8),
                            range(9)
                        }
     MAX-ACCESS         read-write
     STATUS             current
     DESCRIPTION        "Operator for Ace Protocol DstPort."
     ::= { rcPrFilterAceProtoDstPortEntry 5 }

rcPrFilterAceProtoDstPortRowStatus OBJECT-TYPE
     SYNTAX             RowStatus
     MAX-ACCESS         read-write
     STATUS             current
     DESCRIPTION        "Create/delete operations for this entry."
     ::= { rcPrFilterAceProtoDstPortEntry 6 }

rcPrFilterAceProtoDstPortOperMaskRange OBJECT-TYPE
     SYNTAX             Integer32(0..'FFFF'h)
     MAX-ACCESS         read-write
     STATUS             current
     DESCRIPTION        "The value should be displayed in hex when
			rcPrFilterAceProtoDstPortOper is set to 'mask'.
			This object will be used as a Range high value when
			rcPrFilterAceProtoDstPortOper is set to 'range'.
			('range' is not supported in this 3.0 release).
			If it is used as range high value, it should be
			displayed in decimal formtat. 
			This object will be set to 0 when
			rcPrFilterAceProtoDstPortOper is set to 'eq'"
     ::= { rcPrFilterAceProtoDstPortEntry 7 }


-- ACE Protocol Tcp-Option  table

rcPrFilterAceProtoTcpOptionTable OBJECT-TYPE
     SYNTAX             SEQUENCE OF RcPrFilterAceProtoTcpOptionEntry
     MAX-ACCESS         not-accessible
     STATUS             current
     DESCRIPTION        "A table of Aces to store TCP Option information
                        of each Ace in context of its parent Acl."
     ::= { rcPrFilterAce 35 }

rcPrFilterAceProtoTcpOptionEntry OBJECT-TYPE
     SYNTAX             RcPrFilterAceProtoTcpOptionEntry
     MAX-ACCESS         not-accessible 
     STATUS             current
     DESCRIPTION        "One entry holding Ace Protocol TCP option 
			information. An Ace is a member of one Acl."
     INDEX              { rcPrFilterAceProtoTcpOptionAclId,
                          rcPrFilterAceProtoTcpOptionAceId }
     ::= { rcPrFilterAceProtoTcpOptionTable 1 }
         

RcPrFilterAceProtoTcpOptionEntry ::= SEQUENCE {
        rcPrFilterAceProtoTcpOptionAclId     INTEGER,
        rcPrFilterAceProtoTcpOptionAceId     INTEGER,
        rcPrFilterAceProtoTcpOptionHeader    INTEGER,
        rcPrFilterAceProtoTcpOptionOper      INTEGER,
        rcPrFilterAceProtoTcpOptionRowStatus RowStatus
        }

rcPrFilterAceProtoTcpOptionAclId OBJECT-TYPE
     SYNTAX             INTEGER (1..2048)
     MAX-ACCESS         read-only 
     STATUS             current
     DESCRIPTION        "An index to the rcPrFilterAceProtoTcpOptionEntry,
                    a unique identifier for Acl entry in the range of Table
			        Size."
     ::= { rcPrFilterAceProtoTcpOptionEntry 1 }
     
rcPrFilterAceProtoTcpOptionAceId OBJECT-TYPE
     SYNTAX             INTEGER (1..2000)
     MAX-ACCESS         read-only 
     STATUS             current
     DESCRIPTION        "An index to the rcPrFilterAceProtoTcpOptionEntry, 
                         a unique identifier for Ace entry in the 
                         range of Table Size."
     ::= { rcPrFilterAceProtoTcpOptionEntry 2 }

rcPrFilterAceProtoTcpOptionHeader  OBJECT-TYPE
     SYNTAX             INTEGER  {
				no-operation(1),
				max-segment-size(2),
				wsopt(3),
				sack-permitted(4),
				sack(5),
				tsopt(8),
				partial-order-conn-perm(9),
				partial-order-service-profile(10),
				cc(11),
				cc-new(12),
				cc-echo(13),
				tcp-alt-checksum-req(14),
				tcp-alt-checksum-data(15),
				md5(19),
				quick-start-resp(27),
				user-timeout-opt(28)
                        }
     MAX-ACCESS         read-write
     STATUS             current
     DESCRIPTION        "TCP options to be matched from the TCP  Header.
                        1  No-Operation  
                        2 MaximumSegmentSize  
                        3 WSOPT - Window Scale
                        4 SACK Permitted 
                        5 SACK
                        8 TSOPT - Time Stamp Option  
                        9 Partial Order Connection Permitted    
                        10 Partial Order Service Profile         
                        11 CC                                    
                        12 CC.NEW                                
                        13  CC.ECHO                               
                        14  TCP Alternate Checksum Request       
                        15  TCP Alternate Checksum Data          
                        19  MD5 Signature Option                 
                        27  Quick-Start Response                
                        28  User Timeout Option                 "  
 ::= {rcPrFilterAceProtoTcpOptionEntry 3 }

rcPrFilterAceProtoTcpOptionOper OBJECT-TYPE
     SYNTAX             INTEGER {
			    any(5)
                        } 
     MAX-ACCESS         read-write
     STATUS             current
     DESCRIPTION        "Logical Operator - only 'any' is valid at present."
     DEFVAL		{ any }
     ::= {rcPrFilterAceProtoTcpOptionEntry 4 }

rcPrFilterAceProtoTcpOptionRowStatus OBJECT-TYPE
     SYNTAX             RowStatus
     MAX-ACCESS         read-write
     STATUS             current
     DESCRIPTION        "Create/delete operations for this entry."
     ::= { rcPrFilterAceProtoTcpOptionEntry 5 }

--
-- The MIB module is the definition of the managed objects for the Virtual Router.
-- These are virtual router mibs extracted from draft-ietf-l3vpn-vr-mib-04.txt
--

--
-- Textual conventions
--


    VPNId ::= TEXTUAL-CONVENTION
        STATUS current
        DESCRIPTION
            "The purpose of a VPN-ID is to uniquely identify a VPN.
             The Global VPN Identifier format is:
             3 octet VPN Authority, Organizationally Unique Identifier
             followed by 4 octet VPN index identifying VPN according
             to OUI"
        REFERENCE
            "Fox, B. and Gleeson, B., 'Virtual Private Networks
             Identifier', RFC 2685, September 1999."
        SYNTAX    OCTET STRING (SIZE (7))
    
    VrfRpTriggerBitCode ::= TEXTUAL-CONVENTION
        STATUS current
        DESCRIPTION
            "This object represents Routing Protocol (RP)
             Triggers on a Virtual Router.  The BITS
             represent an Action-code that specifies the
             action on the Routing Protocols.

             The actions are:  initiate or shutdown.

             When encoding the RP using the BITS construct,
             the value is encoded as an OCTET STRING where
             the first bit (bit 0) is the highest bit of the
             octet.

             Bits 0-3 may be specified in any combination to
             allow multiple Routing Protocols to be acted on
             simultaneously or individually.
            "
        SYNTAX BITS {
                 rip (0),
                 ospf(1),
                 bgp (2)
               }

--
-- Node definitions
--

    rcVrfMib OBJECT IDENTIFIER ::= { rcVrf 1 }
    rcVrfNotifications OBJECT IDENTIFIER ::= { rcVrfMib 0 }
    rcVrfObjects       OBJECT IDENTIFIER ::= { rcVrfMib 1 }
    rcVrfNotificationObjects OBJECT IDENTIFIER ::= { rcVrfMib 2 }

    rcVrfConfig OBJECT IDENTIFIER ::= { rcVrfObjects 1 }

    rcVrfConfigScalars OBJECT IDENTIFIER ::= { rcVrfConfig 1 }

    rcVrfConfigNextAvailableVrfId OBJECT-TYPE
        SYNTAX VrfIdentifier
        MAX-ACCESS read-only
        STATUS current
        DESCRIPTION
            "The next available Virtual Router Id (index).
            This object provides a hint for the rcVrfId value
            to use when administratively creating a new
            rcVrfConfigEntry.

            A GET of this object returns the next available rcVrfId
            value to be used to create an entry in the associated
            rcVrfConfigTable; or zero, if no valid rcVrfId
            value is available. A value of zero(0) indicates that
            it is not possible to create a new rcVrfConfigEntry.
            This object also returns a value of zero when it is the
            lexicographic successor of a varbind presented in an
            SNMP GETNEXT or GETBULK request, for which circumstance
            it is assumed that ifIndex allocation is unintended.

            Successive GETs will typically return different
            values, thus avoiding collisions among cooperating
            management clients seeking to create table entries
            simultaneously.

            Unless specified otherwise by its MAX-ACCESS and
            DESCRIPTION clauses, an object of this type is read-only,
            and a SET of such an object returns a notWritable error."
        ::= { rcVrfConfigScalars 1 }

    rcVrfConfigTable OBJECT-TYPE
        SYNTAX SEQUENCE OF RcVrfConfigEntry
        MAX-ACCESS not-accessible
        STATUS current
        DESCRIPTION
            "This table is for creating the new Virtual Routers."
        ::= { rcVrfConfig 2 }

    rcVrfConfigEntry OBJECT-TYPE
        SYNTAX RcVrfConfigEntry
        MAX-ACCESS not-accessible
        STATUS current
        DESCRIPTION
            "The entries in this table can be added/deleted
            using the rcVrfRowStatus."
        INDEX { rcVrfId }
        ::= { rcVrfConfigTable 1 }

    RcVrfConfigEntry ::=
        SEQUENCE {
            rcVrfId
                VrfIdentifier,
            rcVrfRowStatus
                RowStatus,
            rcVrfName
                DisplayString,
            rcVrfContextName
                SnmpAdminString,
            rcVrfTrapEnable
                TruthValue,
            rcVrfMaxRoutes
                Unsigned32,
            rcVrfAdminStatus
                INTEGER,
            rcVrfVpnId
                VPNId,
            rcVrfRpTrigger
                VrfRpTriggerBitCode,
            rcVrfMaxRoutesTrapEnable
                TruthValue
        }

    rcVrfId OBJECT-TYPE
        SYNTAX VrfIdentifier
        MAX-ACCESS not-accessible
        STATUS current
        DESCRIPTION
            "The unique id of this virtual router instance. A Virtual
             Router cannot not be created with rcVrfId = 0.
             VRFID 0 is reserved for the Administrative VRF.
            "
    ::= { rcVrfConfigEntry 1 }

    rcVrfRowStatus OBJECT-TYPE
        SYNTAX RowStatus
        MAX-ACCESS read-create
        STATUS current
        DESCRIPTION
            "The status column has three defined values:

            - `active', which indicates that the conceptual row is
            available for use by the managed device;
            - `createAndGo', which is supplied by a management
            station wishing to create a new instance of a
            conceptual row and to have its status automatically set
            to active, making it available for use by the managed
            device;

            - `destroy', which is supplied by a management station
            wishing to delete all of the instances associated with
            an existing conceptual row."
    ::= { rcVrfConfigEntry 2 }

    rcVrfName OBJECT-TYPE
        SYNTAX DisplayString (SIZE (0..32))
        MAX-ACCESS read-write
        STATUS current
        DESCRIPTION
            "The Name of the Virtual Router."
    ::= { rcVrfConfigEntry 3 }

    rcVrfContextName OBJECT-TYPE
        SYNTAX SnmpAdminString (SIZE (0..32))
        MAX-ACCESS read-create
        STATUS current
        DESCRIPTION
            "The SNMPv2 Community String or SNMPv3 contextName
            denotes the VRF 'context' and is used to logically
            separate the MIB module management."
    ::= { rcVrfConfigEntry 4 }

    rcVrfTrapEnable OBJECT-TYPE
        SYNTAX TruthValue
        MAX-ACCESS read-create
        STATUS current
        DESCRIPTION
            "This objects is used to enable the generation
            of the VrfUp and VrfDown traps.
                true(1)     - VRF Traps Enabled
                false(2)    - VRF Traps Disabled"
        DEFVAL { true }
    ::= { rcVrfConfigEntry 5 }

    rcVrfMaxRoutes OBJECT-TYPE
        SYNTAX Unsigned32
        MAX-ACCESS read-create
        STATUS current
        DESCRIPTION
            "This object specifies the maximum number of routes that
            this VRF can support. The default value is 10000."
        DEFVAL { 10000 }
    ::= { rcVrfConfigEntry 6 }

    rcVrfAdminStatus OBJECT-TYPE
        SYNTAX  INTEGER {
                 up(1),
                 down(2),
                 testing(3),
                 unknown(4)
                }
        MAX-ACCESS read-create
        STATUS current
        DESCRIPTION
            "The administrative state of the Virtual Router."
        DEFVAL { down }
    ::= { rcVrfConfigEntry 7 }

    rcVrfVpnId OBJECT-TYPE
        SYNTAX  VPNId
        MAX-ACCESS read-create
        STATUS current
        DESCRIPTION
            "The Virtual Private Network Identifier of the Virtual
             Router."
    ::= { rcVrfConfigEntry 8 }

    rcVrfRpTrigger OBJECT-TYPE
        SYNTAX  VrfRpTriggerBitCode
        MAX-ACCESS read-create
        STATUS current
        DESCRIPTION
            "This object represents Routing Protocol (RP)
             Triggers on a Virtual Router and it meant to
             be used to initiate or shutdown routing
             protocols on a VRF.  Multiple RPs can be acted
             on simultaneously.  Also, individual RPs can
             be brought up in steps, which should not
             affect the RPs that were running. The BITS
             represent an Action-code that specifies what
             action is to be performed for the RPs.
             The actions are:  initiate(1) or shutdown(0).

             The running status of an RP shall be available
             in the VRF stats table's rcVrfRpStatus, which has
             a similar format, but represents the status.

             Bits 0-3 may be specified in any combination.
             Individual routing protocols may be enabled
             and disabled independently.  Protocols are
             enabled by setting the respective BIT and are
             disabled by resetting the BIT.

             So, for example, to enable RIP and BGP protocols
             the rcVrfRpTrigger bits 0 and 2 need to be set, and
             as encoded as 10100000.
             All zeros should be interpreted as all protocols
             disable.
            "
        DEFVAL {{ rip, ospf }}
    ::= { rcVrfConfigEntry 9 }

     rcVrfMaxRoutesTrapEnable  OBJECT-TYPE
        SYNTAX TruthValue
        MAX-ACCESS read-create
        STATUS current
        DESCRIPTION
            "This objects is used to enable the generation
             of the VRF Max Routes Exceeded traps.
                true(1)     - VRF Max Routes Exceeded Traps Enabled
                false(2)    - VRF Max Routes Exceeded Traps Disabled"
        DEFVAL { true }
    ::= { rcVrfConfigEntry 10 }

    rcVrfStat OBJECT IDENTIFIER ::= { rcVrfObjects 2 }

    rcVrfStatScalars OBJECT IDENTIFIER ::= { rcVrfStat 1 }

    rcVrfConfiguredVRFs OBJECT-TYPE
        SYNTAX Unsigned32
        MAX-ACCESS read-only
        STATUS current
        DESCRIPTION
            "The number of VRFs configured on this network element."
        ::= { rcVrfStatScalars 1 }

    rcVrfActiveVRFs OBJECT-TYPE
        SYNTAX Unsigned32
        MAX-ACCESS read-only
        STATUS current
        DESCRIPTION
            "The number of VRFs that are active on the network element.
            These are VRFs for which the
            rcVrfStatOperStatus  = up(1)"
        ::= { rcVrfStatScalars 2 }

    rcVrfStatTable OBJECT-TYPE
        SYNTAX SEQUENCE OF RcVrfStatEntry
        MAX-ACCESS not-accessible
        STATUS current
        DESCRIPTION
            "This table contains statistics for the Virtual Router."
        ::= { rcVrfStat 2 }

    rcVrfStatEntry OBJECT-TYPE
        SYNTAX RcVrfStatEntry
        MAX-ACCESS not-accessible
        STATUS current
        DESCRIPTION
            "Entries in this table are per rcVrfId."
        INDEX { rcVrfId }
        ::= { rcVrfStatTable 1 }

    RcVrfStatEntry ::=
        SEQUENCE {
            rcVrfStatRouteEntries
                Unsigned32,
            rcVrfStatFIBEntries
                Unsigned32,
            rcVrfStatUpTime
                TimeTicks,
            rcVrfOperStatus
                INTEGER,
            rcVrfRpStatus
                VrfRpTriggerBitCode,
            rcVrfRouterAddressType
                InetAddressType,
            rcVrfRouterAddress
                InetAddress
         }

    rcVrfStatRouteEntries OBJECT-TYPE
        SYNTAX Unsigned32
        MAX-ACCESS read-only
        STATUS current
        DESCRIPTION
            "Total number of routes for this VRF."
        ::= { rcVrfStatEntry 1 }

    rcVrfStatFIBEntries OBJECT-TYPE
        SYNTAX Unsigned32
        MAX-ACCESS read-only
        STATUS current
        DESCRIPTION
            "Total number of FIB Entries for this VRF."
        ::= { rcVrfStatEntry 2 }

    rcVrfStatUpTime OBJECT-TYPE
        SYNTAX TimeTicks
        MAX-ACCESS read-only
        STATUS current
        DESCRIPTION
            "The time in (in hundredths of a second) since
            this VRF entry has been operational."
        ::= { rcVrfStatEntry 3 }

    rcVrfOperStatus OBJECT-TYPE
        SYNTAX  INTEGER {
                 up(1),
                 down(2),
                 unknown(3)
                }
        MAX-ACCESS read-only
        STATUS current
        DESCRIPTION
            "The operational status of the Virtual Router."
        ::= { rcVrfStatEntry 4 }

    rcVrfRpStatus OBJECT-TYPE
        SYNTAX  VrfRpTriggerBitCode
        MAX-ACCESS read-only
        STATUS current
        DESCRIPTION
            "This object represents the status of Routing
             Protocols on this VRF corresponding to the list
             of RP specified in rcVrfRpTrigger.

             The BITS represent an Action-code that specifies
             the status of the RPs.
             The status are:  initiated (1) or shutdown (0).
             Initiated status is indicated when the respective
             BIT value is 1 and indicates shutdown when the
             respective BIT value is 0.

             Bits 0-3 may appear in any combination to
             indicate that RPs may be enabled and disabled
             independently or that multiple RP are acted on
             simultaneously.
            "
        ::= { rcVrfStatEntry 5 }

    rcVrfRouterAddressType OBJECT-TYPE
        SYNTAX  InetAddressType
        MAX-ACCESS read-only
        STATUS current
        DESCRIPTION
            "Router Address Type of this VRF."
        ::= { rcVrfStatEntry 6 }

    rcVrfRouterAddress OBJECT-TYPE
        SYNTAX  InetAddress
        MAX-ACCESS read-only
        STATUS current
        DESCRIPTION
            "Router Address of this VRF.  It is derived from one of the
            interfaces. If loopback interface is present, the loopback
            interface address can be used. However, loopback interface
            is optional."
        ::= { rcVrfStatEntry 7 }


-- rcIpfix

rcIpfixMib OBJECT IDENTIFIER ::= { rcIpfix 1 }

rcIpfixConfGlobal OBJECT IDENTIFIER ::= { rcIpfixMib 1 }
rcIpfixTable      OBJECT IDENTIFIER ::= { rcIpfixMib 2 }

-- ------------------------------------------
-- rcIpfixConfGlobal Group
-- ------------------------------------------

rcIpfixConfState OBJECT-TYPE
    SYNTAX       EnableValue
    MAX-ACCESS   read-write
    STATUS       current
    DESCRIPTION  "Enables/Disables the state of ipfix on the box."
    DEFVAL       { disable }
    ::= { rcIpfixConfGlobal 1 }

-- ------------------------------------------
-- IPFIX Table (per slot)
-- ------------------------------------------

rcIpfixConfSlotTable OBJECT-TYPE
    SYNTAX       SEQUENCE OF RcIpfixConfSlotEntry
    MAX-ACCESS   not-accessible
    STATUS       current
    DESCRIPTION  "A table to store the configuration details for IPFIX for each
                  slot.  This table is indexed by slot number."
    ::= { rcIpfixTable 1 }

rcIpfixConfSlotEntry OBJECT-TYPE
    SYNTAX       RcIpfixConfSlotEntry
    MAX-ACCESS   not-accessible
    STATUS       current
    DESCRIPTION  "One Entry holding IPFIX config information on slot basis."
    INDEX        { rcIpfixConfSlotNum }
    ::= { rcIpfixConfSlotTable 1 }

RcIpfixConfSlotEntry ::= SEQUENCE {
    rcIpfixConfSlotNum              Integer32,
    rcIpfixConfSlotAgingIntv        Integer32,
    rcIpfixConfSlotActiveTimeout    Integer32,
    rcIpfixConfSlotExportIntv       Integer32,
    rcIpfixConfSlotExportState      EnableValue,
    rcIpfixConfSlotTempRefIntvSec   Integer32,
    rcIpfixConfSlotTempRefIntvPkts  Integer32
}

rcIpfixConfSlotNum OBJECT-TYPE
    SYNTAX       Integer32 (3..12)
    MAX-ACCESS   not-accessible
    STATUS       current
    DESCRIPTION  "Slot number"
    ::= { rcIpfixConfSlotEntry 1 }

rcIpfixConfSlotAgingIntv OBJECT-TYPE
    SYNTAX       Integer32 (10..3600)
    UNITS        "seconds"
    MAX-ACCESS   read-write
    STATUS       current
    DESCRIPTION  "Flow record aging interval (Value in seconds)."
    DEFVAL       { 15 }
    ::= { rcIpfixConfSlotEntry 2 }

rcIpfixConfSlotActiveTimeout OBJECT-TYPE
    SYNTAX       Integer32 (1..60)
    UNITS        "minutes"
    MAX-ACCESS   read-write
    STATUS       current
    DESCRIPTION  "Flow record active timeout value (Value in mins)."
    DEFVAL       { 30 }
    ::= { rcIpfixConfSlotEntry 3 }

rcIpfixConfSlotExportIntv OBJECT-TYPE
    SYNTAX       Integer32 (10..3600)
    UNITS        "seconds"
    MAX-ACCESS   read-write
    STATUS       current
    DESCRIPTION  "Frequency of flow export to collector (Value in sec)."
    DEFVAL       { 50 }
    ::= { rcIpfixConfSlotEntry 4 }

rcIpfixConfSlotExportState OBJECT-TYPE
    SYNTAX       EnableValue
    MAX-ACCESS   read-write
    STATUS       current
    DESCRIPTION  "State of exporter."
    DEFVAL       { enable }
    ::= { rcIpfixConfSlotEntry 5 }

rcIpfixConfSlotTempRefIntvSec OBJECT-TYPE
    SYNTAX       Integer32 (60..3600)
    UNITS        "seconds"
    MAX-ACCESS   read-write
    STATUS       current
    DESCRIPTION  "Template refresh timeout. Template is sent out to the
                  collector at least every x seconds or every y exported
                  packets, whichever occurs first."
    DEFVAL       { 60 }
    ::= { rcIpfixConfSlotEntry 6 }

rcIpfixConfSlotTempRefIntvPkts OBJECT-TYPE
    SYNTAX       Integer32 (1..600)
    MAX-ACCESS   read-write
    STATUS       current
    DESCRIPTION  "Template refresh timeout. Template is sent out to the
                  collector at least every x seconds or every y exported
                  packets, whichever occurs first."
    DEFVAL       { 20 }
    ::= { rcIpfixConfSlotEntry 7 }

-- ------------------------------------------
-- IPFIX Collector Table (per slot)
-- ------------------------------------------

rcIpfixCollectorTable OBJECT-TYPE
    SYNTAX       SEQUENCE OF RcIpfixCollectorEntry
    MAX-ACCESS   not-accessible
    STATUS       current
    DESCRIPTION  "Table to store the configuration details for IPFIX collector
                  for each slot.  This table is indexed by slot number and ip
                  address."
    ::= { rcIpfixTable 2 }

rcIpfixCollectorEntry OBJECT-TYPE
    SYNTAX       RcIpfixCollectorEntry
    MAX-ACCESS   not-accessible
    STATUS       current
    DESCRIPTION  "One entry holds IPFIX collector config information based on
                  slot info and collector ip address."
    INDEX        { rcIpfixCollectorSlotNum,
                   rcIpfixCollectorAddressType,
                   rcIpfixCollectorAddress }
    ::= { rcIpfixCollectorTable 1 }

RcIpfixCollectorEntry ::= SEQUENCE {
    rcIpfixCollectorSlotNum        Integer32,
    rcIpfixCollectorAddressType    InetAddressType,
    rcIpfixCollectorAddress        InetAddress,
    rcIpfixCollectorProtocol       INTEGER,
    rcIpfixCollectorDestPort       InetPortNumber,
    rcIpfixCollectorExporterIpType InetAddressType,
    rcIpfixCollectorExporterIp     InetAddress,
    rcIpfixCollectorProtoVer       INTEGER,
    rcIpfixCollectorState          TruthValue,
    rcIpfixCollectorRowStatus      RowStatus
}

rcIpfixCollectorSlotNum OBJECT-TYPE
    SYNTAX       Integer32 (3..12)
    MAX-ACCESS   not-accessible
    STATUS       current
    DESCRIPTION  "Slot number. An index to the CollectorEntry."
    ::= { rcIpfixCollectorEntry 1 }

rcIpfixCollectorAddressType OBJECT-TYPE
    SYNTAX       InetAddressType
    MAX-ACCESS   not-accessible
    STATUS       current
    DESCRIPTION  "IP address type of the collector.  An index to the
                  CollectorEntry."
    ::= { rcIpfixCollectorEntry 2 }

rcIpfixCollectorAddress OBJECT-TYPE
    SYNTAX       InetAddress
    MAX-ACCESS   not-accessible
    STATUS       current
    DESCRIPTION  "IP address of the collector.  An index to the CollectorEntry."
    ::= { rcIpfixCollectorEntry 3 }

rcIpfixCollectorProtocol OBJECT-TYPE
    SYNTAX       INTEGER {
                            udp(1),
                            tcp(2),
                            sctp(3)
                         }
    MAX-ACCESS   read-create
    STATUS       current
    DESCRIPTION  "Protocol for export data from exporter to collector ."
    DEFVAL       { 1 }
    ::= { rcIpfixCollectorEntry 4 }

rcIpfixCollectorDestPort OBJECT-TYPE
    SYNTAX       InetPortNumber
    MAX-ACCESS   read-create
    STATUS       current
    DESCRIPTION  "Dest port to send the requests."
    DEFVAL       { 9995 }
    ::= { rcIpfixCollectorEntry 5 }

rcIpfixCollectorExporterIpType OBJECT-TYPE
    SYNTAX       InetAddressType
    MAX-ACCESS   read-create
    STATUS       current
    DESCRIPTION  "Ip address type of the exporter for collector."
    ::= { rcIpfixCollectorEntry 6 }

rcIpfixCollectorExporterIp OBJECT-TYPE
    SYNTAX       InetAddress
    MAX-ACCESS   read-create
    STATUS       current
    DESCRIPTION  "Ip address of the exporter for collector."
    ::= { rcIpfixCollectorEntry 7 }

rcIpfixCollectorProtoVer OBJECT-TYPE
    SYNTAX       INTEGER {
                            ipfix(1),
                            preipfixv9(2),
                            preipfixv5(3)
                         }
    MAX-ACCESS   read-create
    STATUS       current
    DESCRIPTION  "This specifies the protocol version for ipfix."
    DEFVAL       { 2 }
    ::= { rcIpfixCollectorEntry 8 }

rcIpfixCollectorState OBJECT-TYPE
    SYNTAX       TruthValue
    MAX-ACCESS   read-create
    STATUS       current
    DESCRIPTION  "State of the particular collector.  Enable is true by
                  default."
    DEFVAL       { true }
    ::= { rcIpfixCollectorEntry 9 }

rcIpfixCollectorRowStatus OBJECT-TYPE
    SYNTAX       RowStatus
    MAX-ACCESS   read-create
    STATUS       current
    DESCRIPTION  "Used to create/delete entries."
    ::= { rcIpfixCollectorEntry 10 }

-- ------------------------------------------
-- IPFIX Table (per port)
-- ------------------------------------------

rcIpfixConfPortTable OBJECT-TYPE
    SYNTAX       SEQUENCE OF RcIpfixConfPortEntry
    MAX-ACCESS   not-accessible
    STATUS       current
    DESCRIPTION  "A table to store the configuration details for IPFIX for each
                  port.  This table is indexed by port number."
    ::= { rcIpfixTable 3 }

rcIpfixConfPortEntry OBJECT-TYPE
    SYNTAX       RcIpfixConfPortEntry
    MAX-ACCESS   not-accessible
    STATUS       current
    DESCRIPTION  "Entry holding IPFIX config information per port."
    INDEX        { rcIpfixConfPortId }
    ::= { rcIpfixConfPortTable 1 }

RcIpfixConfPortEntry ::= SEQUENCE {
    rcIpfixConfPortId              InterfaceIndex,
    rcIpfixConfPortSampleRate      Integer32,
    rcIpfixConfPortHashPolyCoeffs  Integer32,
    rcIpfixConfPortHashPolySeed    Integer32,
    rcIpfixConfPortFlush           INTEGER,
    rcIpfixConfPortAllTraffic      EnableValue,
    rcIpfixConfPortHashKeyId       INTEGER,
    rcIpfixConfPortDynamicSampRate Integer32
}

rcIpfixConfPortId OBJECT-TYPE
    SYNTAX       InterfaceIndex
    MAX-ACCESS   not-accessible
    STATUS       current
    DESCRIPTION  "An index to the IpfixConfPortEntry, a unique identifier of
                  the portId"
    ::= { rcIpfixConfPortEntry 1 }

rcIpfixConfPortSampleRate OBJECT-TYPE
    SYNTAX       Integer32 (1..100000)
    MAX-ACCESS   read-write
    STATUS       current
    DESCRIPTION  "Used to configure the sampling rate. Sample one in every N
                  packets."
    DEFVAL       { 1 }
    ::= { rcIpfixConfPortEntry 2 }

rcIpfixConfPortHashPolyCoeffs OBJECT-TYPE
    SYNTAX       Integer32 ('000401'h..'FFFFFF'h)
    MAX-ACCESS   read-write
    STATUS       current
    DESCRIPTION  "Command to set hash polynomial coeffs."
    DEFVAL       { '0007CC'h }
    ::= { rcIpfixConfPortEntry 3 }

rcIpfixConfPortHashPolySeed OBJECT-TYPE
    SYNTAX       Integer32 ('000000'h..'FFFFFF'h)
    MAX-ACCESS   read-write
    STATUS       current
    DESCRIPTION  "Command to set hash polynomial seed."
    DEFVAL       { 0 }
    ::= { rcIpfixConfPortEntry 4 }

rcIpfixConfPortFlush OBJECT-TYPE
    SYNTAX       INTEGER {
                            none(1),
                            flush(2),
                            exportAndFlush(3)
                         }
    MAX-ACCESS   read-write
    STATUS       current
    DESCRIPTION  "This is used to delete all records stored in COP, or to
                  initiate an export of all records and delete data base after
                  the export is finished."
    DEFVAL       { none }
    ::= { rcIpfixConfPortEntry 5 }

rcIpfixConfPortAllTraffic OBJECT-TYPE
    SYNTAX       EnableValue
    MAX-ACCESS   read-write
    STATUS       current
    DESCRIPTION  "This is used to enable/disable ipfix on all trafiic, for the
                  specified port."
    DEFVAL       { disable }
    ::= { rcIpfixConfPortEntry 6 }

rcIpfixConfPortHashKeyId OBJECT-TYPE
    SYNTAX       INTEGER {
                            hashKeyOne(1),
                            hashKeyTwo(2),
                            hashKeyThree(3),
                            hashKeyFour(4)
                         }
    MAX-ACCESS   read-write
    STATUS       current
    DESCRIPTION  "hash key id."
    DEFVAL       { 1 }
    ::= { rcIpfixConfPortEntry 7 }

rcIpfixConfPortDynamicSampRate OBJECT-TYPE
    SYNTAX       Integer32 (1..100000)
    MAX-ACCESS   read-only
    STATUS       current
    DESCRIPTION  "Indicates the dynamic sampling rate."
    ::= { rcIpfixConfPortEntry 8 }

-- ------------------------------------------
-- Hash Stats Table( per slot)
-- ------------------------------------------

rcIpfixHashStatsTable OBJECT-TYPE
    SYNTAX       SEQUENCE OF RcIpfixHashStatsEntry
    MAX-ACCESS   not-accessible
    STATUS       current
    DESCRIPTION  "A table of hash Statistics entries to store the statistics
                  for each slot. This table is indexed by the slot number."
    ::= { rcIpfixTable 4 }

rcIpfixHashStatsEntry OBJECT-TYPE
    SYNTAX       RcIpfixHashStatsEntry
    MAX-ACCESS   not-accessible
    STATUS       current
    DESCRIPTION  "Entry containing hash statistics information for a particular
                  slot."
    INDEX        { rcIpfixHashStatsSlotNum }
    ::= { rcIpfixHashStatsTable 1 }

RcIpfixHashStatsEntry ::= SEQUENCE {
    rcIpfixHashStatsSlotNum        Integer32,
    rcIpfixHashStatsHashOverflows  Counter64,
    rcIpfixHashStatsHashDrops      Counter64,
    rcIpfixHashStatsClear          INTEGER,
    rcIpfixHashStatsClearTime      TimeStamp
}

rcIpfixHashStatsSlotNum OBJECT-TYPE
    SYNTAX       Integer32 (3..12)
    MAX-ACCESS   not-accessible
    STATUS       current
    DESCRIPTION  "A unique identifier for the table."
    ::= { rcIpfixHashStatsEntry 1 }

rcIpfixHashStatsHashOverflows OBJECT-TYPE
    SYNTAX       Counter64
    MAX-ACCESS   read-only
    STATUS       current
    DESCRIPTION  "Count of hash overflows per slot."
    ::= { rcIpfixHashStatsEntry 2 }

rcIpfixHashStatsHashDrops OBJECT-TYPE
    SYNTAX       Counter64
    MAX-ACCESS   read-only
    STATUS       current
    DESCRIPTION  "Count of hash drops per slot."
    ::= { rcIpfixHashStatsEntry 3 }

rcIpfixHashStatsClear OBJECT-TYPE
    SYNTAX       INTEGER {
                            clear(1)
                         }
    MAX-ACCESS   read-write
    STATUS       current
    DESCRIPTION  "Setting this object will clear hash statistics for a slot."
    ::= { rcIpfixHashStatsEntry 4 }

rcIpfixHashStatsClearTime OBJECT-TYPE
    SYNTAX       TimeStamp
    MAX-ACCESS   read-only
    STATUS       current
    DESCRIPTION  "The value of sysUpTime when the hash statistics were last
                  cleared."
    ::= { rcIpfixHashStatsEntry 5 }

-- ------------------------------------------
-- Exporter Stats Table( per slot, per collector)
-- ------------------------------------------

rcIpfixExporterStatsTable OBJECT-TYPE
    SYNTAX       SEQUENCE OF RcIpfixExporterStatsEntry
    MAX-ACCESS   not-accessible
    STATUS       current
    DESCRIPTION  "A table of Exporter Statistics entries to store the statistics
                  for each slot, each collector.  This table is indexed by the
                  slot number and collector address."
    ::= { rcIpfixTable 5 }

rcIpfixExporterStatsEntry OBJECT-TYPE
    SYNTAX       RcIpfixExporterStatsEntry
    MAX-ACCESS   not-accessible
    STATUS       current
    DESCRIPTION  "Entry containing Exporter statistics information for a
                  particular slot and particular collector."
    INDEX        { rcIpfixExporterStatsSlotNum,
                   rcIpfixExporterStatsCollectorType,
                   rcIpfixExporterStatsCollector }
    ::= { rcIpfixExporterStatsTable 1 }

RcIpfixExporterStatsEntry ::= SEQUENCE {
    rcIpfixExporterStatsSlotNum        Integer32,
    rcIpfixExporterStatsCollectorType  InetAddressType,
    rcIpfixExporterStatsCollector      InetAddress,
    rcIpfixExporterStatsOutPkts        Counter64,
    rcIpfixExporterStatsOutOctets      Counter64,
    rcIpfixExporterStatsPktsLoss       Counter64,
    rcIpfixExporterStatsClear          INTEGER,
    rcIpfixExporterStatsClearTime      TimeStamp
}

rcIpfixExporterStatsSlotNum OBJECT-TYPE
    SYNTAX       Integer32 (3..12)
    MAX-ACCESS   not-accessible
    STATUS       current
    DESCRIPTION  "Index for the table, slot number."
    ::= { rcIpfixExporterStatsEntry 1 }

rcIpfixExporterStatsCollectorType OBJECT-TYPE
    SYNTAX       InetAddressType
    MAX-ACCESS   not-accessible
    STATUS       current
    DESCRIPTION  "Collector IP address type.  This is an index for the table."
    ::= { rcIpfixExporterStatsEntry 2 }

rcIpfixExporterStatsCollector OBJECT-TYPE
    SYNTAX       InetAddress
    MAX-ACCESS   not-accessible
    STATUS       current
    DESCRIPTION  "Index for the table, collector address."
    ::= { rcIpfixExporterStatsEntry 3 }

rcIpfixExporterStatsOutPkts OBJECT-TYPE
    SYNTAX       Counter64
    MAX-ACCESS   read-only
    STATUS       current
    DESCRIPTION  "Number of Packets sent."
    ::= { rcIpfixExporterStatsEntry 4 }

rcIpfixExporterStatsOutOctets OBJECT-TYPE
    SYNTAX       Counter64
    MAX-ACCESS   read-only
    STATUS       current
    DESCRIPTION  "Number of Bytes sent."
    ::= { rcIpfixExporterStatsEntry 5 }

rcIpfixExporterStatsPktsLoss OBJECT-TYPE
    SYNTAX       Counter64
    MAX-ACCESS   read-only
    STATUS       current
    DESCRIPTION  "Number of Records lost."
    ::= { rcIpfixExporterStatsEntry 6 }

rcIpfixExporterStatsClear OBJECT-TYPE
    SYNTAX       INTEGER {
                            clear(1)
                         }
    MAX-ACCESS   read-write
    STATUS       current
    DESCRIPTION  "Setting this object will clear exporter statistics."
    ::= { rcIpfixExporterStatsEntry 7 }

rcIpfixExporterStatsClearTime OBJECT-TYPE
    SYNTAX       TimeStamp
    MAX-ACCESS   read-only
    STATUS       current
    DESCRIPTION  "The value of sysUpTime when exporter statistics were last
                  cleared."
    ::= { rcIpfixExporterStatsEntry 8 }


rcVrfIpVpnTableSize OBJECT-TYPE
        SYNTAX          Integer32
        MAX-ACCESS      read-only
        STATUS          current
        DESCRIPTION     "Size of Vrf IpVpn Table"
        ::= { rcVrfObjects 3 }

rcVrfIpVpnTable   OBJECT-TYPE
    SYNTAX        SEQUENCE OF RcVrfIpVpnTableEntry
    MAX-ACCESS    not-accessible
    STATUS        current
    DESCRIPTION   "Table required to configure vpn under ip."
    ::= { rcVrfObjects 4 }

rcVrfIpVpnTableEntry  OBJECT-TYPE
    SYNTAX         RcVrfIpVpnTableEntry
    MAX-ACCESS     not-accessible
    STATUS         current
    DESCRIPTION    "Entries in this table are per rcVrfId."
    INDEX          { rcVrfIpVpnVrfId }
    ::= { rcVrfIpVpnTable 1 }

RcVrfIpVpnTableEntry ::=
    SEQUENCE {
              rcVrfIpVpnVrfId  VrfIdentifier,
              rcVrfIpVpnStatus EnableValue, 
              rcVrfIpVpnImportRTList           IdList,
              rcVrfIpVpnExportRTList           IdList,
              rcVrfIpVpnSvcLblAllocOpt      INTEGER,
              rcVrfIpVpnRowStatus      RowStatus,
              rcVrfIpVpnIsidNumber        Integer32
             }

rcVrfIpVpnVrfId OBJECT-TYPE
    SYNTAX        VrfIdentifier
    MAX-ACCESS    not-accessible
    STATUS        current
    DESCRIPTION   "The VrfId serves as the Index for the rcIpVpnVrfTable and
                   also for the rcIpVpnRouteDistinguisherTable. It allows to
                   connect to the vrf table to obtain other attributes like the
                   vrf name, rcVrfMaxRoutesTrapEnable etc."
    ::= { rcVrfIpVpnTableEntry 1 }

rcVrfIpVpnStatus  OBJECT-TYPE
    SYNTAX        EnableValue 
    MAX-ACCESS    read-create
    STATUS        current
    DESCRIPTION   "The status of IpVpn."
    DEFVAL        { disable } 
    ::= { rcVrfIpVpnTableEntry 2 }

rcVrfIpVpnImportRTList  OBJECT-TYPE
    SYNTAX        IdList
    MAX-ACCESS    read-create
    STATUS        current
    DESCRIPTION   "The Import RT list is a list of all the route-targets
                   attached to a particular vrf behaving in the import mode."
    ::= { rcVrfIpVpnTableEntry 3 }

rcVrfIpVpnExportRTList  OBJECT-TYPE
    SYNTAX        IdList
    MAX-ACCESS    read-create
    STATUS        current
    DESCRIPTION   "The Export RT list is a list of all the route-targets
                   attached to a particular vrf in the export mode."
    ::= { rcVrfIpVpnTableEntry 4 }

rcVrfIpVpnSvcLblAllocOpt OBJECT-TYPE
    SYNTAX        INTEGER {
                    perVrfperNexthop(1),
                    perVrf(2)
                  }
    MAX-ACCESS    read-create
    STATUS        current
    DESCRIPTION   "The service label allocation option for the ipvpn"
    ::= { rcVrfIpVpnTableEntry 5 }

rcVrfIpVpnRowStatus OBJECT-TYPE
    SYNTAX       RowStatus
    MAX-ACCESS   read-create
    STATUS       current
    DESCRIPTION  "RowStatus for the Vpn Entry."
    ::= { rcVrfIpVpnTableEntry 6 }

rcVrfIpVpnIsidNumber OBJECT-TYPE
        SYNTAX          Integer32 (0..16777215)
        MAX-ACCESS      read-create
        STATUS          current
        DESCRIPTION     "IP VPN I-SID number.Default 0 value indicates
                         that no i-sid has been assinged."
        DEFVAL { 0 }
        ::= { rcVrfIpVpnTableEntry 7 }

rcVrfNameTable OBJECT-TYPE
        SYNTAX SEQUENCE OF RcVrfNameEntry
        MAX-ACCESS not-accessible
        STATUS current
        DESCRIPTION
            "This table is for EDM and SNMP agent to get source vrf name
             for inter-vrf route redistribute."
        ::= { rcVrfObjects 5 }

rcVrfNameEntry OBJECT-TYPE
        SYNTAX RcVrfNameEntry
        MAX-ACCESS not-accessible
        STATUS current
        DESCRIPTION
            "Each entry has the vrfid and name for source vrf needed by
            inter-vrf route redistribute."
        INDEX { rcVrfNameVrfId }
        ::= { rcVrfNameTable 1 }

RcVrfNameEntry ::=
        SEQUENCE {
            rcVrfNameVrfId
                VrfIdentifier,            
            rcVrfNameVrfName
                DisplayString            
        }

rcVrfNameVrfId OBJECT-TYPE
        SYNTAX VrfIdentifier
        MAX-ACCESS not-accessible
        STATUS current
        DESCRIPTION
            "The unique id of this virtual router instance."
    ::= { rcVrfNameEntry 1 }   

rcVrfNameVrfName OBJECT-TYPE
        SYNTAX DisplayString (SIZE (0..32))
        MAX-ACCESS read-only
        STATUS current
        DESCRIPTION
            "The Name of the Virtual Router."
    ::= { rcVrfNameEntry 2 }    

rcSlppMib OBJECT IDENTIFIER ::= { rcSlpp 1 }

rcSlppNotifications OBJECT IDENTIFIER ::= { rcSlppMib 0 }
rcSlppObjects       OBJECT IDENTIFIER ::= { rcSlppMib 1 }
rcSlppNotificationObjects OBJECT IDENTIFIER ::= { rcSlppMib 2 }

rcSlppScalars OBJECT IDENTIFIER ::= { rcSlppObjects 1 }

rcSlppGlobalEnable OBJECT-TYPE
    SYNTAX      TruthValue
    MAX-ACCESS  read-write
    STATUS      current
    DESCRIPTION "Global enable/disable for the simple loop prevention protocol."
    DEFVAL      { false }
    ::= { rcSlppScalars 1 }

rcSlppTransmissionInterval OBJECT-TYPE
    SYNTAX      INTEGER (500..5000)
    MAX-ACCESS  read-write
    STATUS      current
    DESCRIPTION "The interval (in seconds) for which loop detection occurs."
    DEFVAL      { 500  }
    ::= { rcSlppScalars 2 }

rcSlppEtherType OBJECT-TYPE
    SYNTAX        Integer32
    MAX-ACCESS    read-write
    STATUS        current
    DESCRIPTION   "SLPP Protocol Identification. The value is normally in Hex."
    DEFVAL        { '8104'h  }
    ::= { rcSlppScalars 3 } 


rcSlppVlanTable OBJECT-TYPE
    SYNTAX      SEQUENCE OF RcSlppVlanEntry
    MAX-ACCESS  not-accessible
    STATUS      current
    DESCRIPTION "Table of VLANs for which simple loop detection occur on."
    ::= { rcSlppObjects 2 }

rcSlppVlanEntry OBJECT-TYPE
    SYNTAX      RcSlppVlanEntry
    MAX-ACCESS  not-accessible
    STATUS      current
    DESCRIPTION "SLPP VLAN entry. "
    INDEX       { rcSlppVlanVlanId }
    ::= { rcSlppVlanTable 1 }

RcSlppVlanEntry ::= SEQUENCE {
    rcSlppVlanVlanId       RcVlanIdOrNone,
    rcSlppVlanSlppEnable   TruthValue,
    rcSlppVlanRowStatus    RowStatus
}

rcSlppVlanVlanId OBJECT-TYPE
    SYNTAX        RcVlanIdOrNone
    MAX-ACCESS    not-accessible
    STATUS        current
    DESCRIPTION   "Vlan id for which simple loop detection occurs on."
    ::= { rcSlppVlanEntry 1 }

rcSlppVlanSlppEnable OBJECT-TYPE
    SYNTAX        TruthValue
    MAX-ACCESS    read-write
    STATUS        current
    DESCRIPTION   "Flag to indicate whether the VLAN entry is active or not for         SLPP." 
    ::= { rcSlppVlanEntry 2 }

rcSlppVlanRowStatus OBJECT-TYPE
    SYNTAX        RowStatus
    MAX-ACCESS    read-write
    STATUS        current
    DESCRIPTION   "Used to create/delete entries."
    ::= { rcSlppVlanEntry 3 }

rcSlppPortTable OBJECT-TYPE
    SYNTAX      SEQUENCE OF RcSlppPortEntry
    MAX-ACCESS  not-accessible
    STATUS      current
    DESCRIPTION "Table of ports for which simple loop detection occurs on."
    ::= { rcSlppObjects 3 }

rcSlppPortEntry OBJECT-TYPE
    SYNTAX      RcSlppPortEntry
    MAX-ACCESS  not-accessible
    STATUS      current
    DESCRIPTION "SLPP Port entry. "
    INDEX       { rcSlppPortIfIndex }
    ::= { rcSlppPortTable 1 }

RcSlppPortEntry ::= SEQUENCE {
    rcSlppPortIfIndex             InterfaceIndex,
    rcSlppPortPktRxThreshold      Integer32,
    rcSlppPortSlppEnable          TruthValue,
    rcSlppPortIncomingVlanId      RcVlanIdOrNone,
    rcSlppPortSrcNodeType         INTEGER,
    rcSlppPortPktRxCount          Integer32,
    rcSlppPortTimeToClrPktRxCount Unsigned32,
    rcSlppPortRemainingTimeToClrPktRxCount Unsigned32,
    rcSlppPortClearPktRxCount     TruthValue
}

rcSlppPortIfIndex OBJECT-TYPE
    SYNTAX        InterfaceIndex
    MAX-ACCESS    not-accessible
    STATUS        current
    DESCRIPTION   "Port on which simple loop detection occurs on."
    ::= { rcSlppPortEntry 1 }

rcSlppPortPktRxThreshold OBJECT-TYPE
    SYNTAX        Integer32 (1..500)
    MAX-ACCESS    read-write
    STATUS        current
    DESCRIPTION   "Once the number of SLPP packets received on this port reaches       this threshold action will be taken.Normally, the port will be shutdown."        
    DEFVAL         { 1 }
    ::= { rcSlppPortEntry 2 }

rcSlppPortSlppEnable OBJECT-TYPE
    SYNTAX        TruthValue
    MAX-ACCESS    read-write
    STATUS        current
    DESCRIPTION   "Flag to indicate whether the port entry is active or not for        SLPP." 
    DEFVAL        { false }
    ::= { rcSlppPortEntry 3 }

rcSlppPortIncomingVlanId OBJECT-TYPE
    SYNTAX        RcVlanIdOrNone
    MAX-ACCESS    read-only 
    STATUS        current
    DESCRIPTION   "Vlan id of the classified packet on the port brought down by        SLPP."
    ::= { rcSlppPortEntry 5 }

rcSlppPortSrcNodeType OBJECT-TYPE
    SYNTAX        INTEGER {
                         none(0),
                         local(1),
                         peer(2)
                  }
    MAX-ACCESS    read-only 
    STATUS        current
    DESCRIPTION  "The src node type of the received slpp Pkt." 
    ::= { rcSlppPortEntry 6 }

rcSlppPortPktRxCount OBJECT-TYPE
    SYNTAX        Integer32  (1..500)
    MAX-ACCESS    read-only
    STATUS        current
    DESCRIPTION   "Total number of SLPP packets received on the port."
    ::= { rcSlppPortEntry 7}

rcSlppPortTimeToClrPktRxCount OBJECT-TYPE
    SYNTAX        Unsigned32 (1..21600)
    UNITS         "seconds"
    MAX-ACCESS    read-write
    STATUS        current
    DESCRIPTION   "Time to clear the SLPP Rx PDU counter. This has a default
                   value of 21600 seconds. Once SLPP is enabled and port
                   starts receiving SLPP PDUs, a timer is started and once
                   the timer exceeds this configured value, rcSlppPortPktRxCount
                   is reset to zero."
    ::= {rcSlppPortEntry 12}

rcSlppPortRemainingTimeToClrPktRxCount OBJECT-TYPE
    SYNTAX        Unsigned32 (1..21600)
    UNITS         "seconds"
    MAX-ACCESS    read-only
    STATUS        current
    DESCRIPTION   "Remaining time to clear the SLPP Rx PDU counter. It is
                   calculated using rcSlppPortTimeToClrPktRxCount and has
                   a granularity of 5 seconds."
    ::= { rcSlppPortEntry 13}

rcSlppPortClearPktRxCount       OBJECT-TYPE
    SYNTAX        TruthValue
    MAX-ACCESS    read-write
    STATUS        current
    DESCRIPTION   "Clear the SLPP Rx PDU counter."
    ::= { rcSlppPortEntry 14}

rcSlppIncomingVlanId OBJECT-TYPE
    SYNTAX        RcVlanIdOrNone 
    MAX-ACCESS    accessible-for-notify
    STATUS        current
    DESCRIPTION   "Vlan id of the classified packet on the port brought down by        SLPP."
    ::= { rcSlppNotificationObjects 1 }

rcSlppSrcMacAddress OBJECT-TYPE
    SYNTAX              MacAddress
    MAX-ACCESS   accessible-for-notify
    STATUS             current
    DESCRIPTION  "Source MAC address in the classified packet on the port 
       brought down by SLPP."
    ::= { rcSlppNotificationObjects 2 }

rcSlppRxPortIndex OBJECT-TYPE
    SYNTAX        InterfaceIndex
    MAX-ACCESS    accessible-for-notify
    STATUS        current
    DESCRIPTION   "Port on which the SLPP packet is received."
    ::= { rcSlppNotificationObjects 3 }

rcSlppRxVlanId OBJECT-TYPE
    SYNTAX        RcVlanIdOrNone
    MAX-ACCESS    accessible-for-notify
    STATUS        current
    DESCRIPTION   "Vlan on which the SLPP packet is received."
    ::= { rcSlppNotificationObjects 4 }

rcnSlppPortDownEventNew NOTIFICATION-TYPE
    OBJECTS    { rcSlppRxPortIndex, rcSlppRxVlanId, rcSlppIncomingVlanId,
               rcSlppSrcMacAddress }
    STATUS         current
    DESCRIPTION    "A port down event that has occurred due to SLPP. The trap
        includes the port and its Vlan which receives the packet, and
        along with the Vlan ID and source MAC address of the packet coming in
        on the port identified."
    ::= { rcSlppNotifications 2 }

-- MPLS

rcMplsMib                     OBJECT IDENTIFIER ::= { rcMpls 1 }
rcMplsNotifications           OBJECT IDENTIFIER ::= { rcMplsMib 0 }
rcMplsObjects                 OBJECT IDENTIFIER ::= { rcMplsMib 1 }
rcMplsNotificationObjects     OBJECT IDENTIFIER ::= { rcMplsMib 2 }

-- Object groups within the MPLS MIB
--
rcMplsGlobalGroup          OBJECT IDENTIFIER ::= { rcMplsObjects 1 }

rcMplsGlobalScalars        OBJECT IDENTIFIER ::= { rcMplsGlobalGroup 1 }

-- MPLS Global Variables

rcMplsRouterId OBJECT-TYPE
        SYNTAX        IpAddress
        MAX-ACCESS    read-write
        STATUS        current
        DESCRIPTION   "IP address of the circuitless interface to be used as router-id"
        DEFVAL        { '00000000'H }    -- 0.0.0.0  
        ::= { rcMplsGlobalScalars 1 }

-- MPLS LDP Global

rcMplsLdpAdminStatus OBJECT-TYPE
        SYNTAX        EnableValue
        MAX-ACCESS    read-write
        STATUS        current
        DESCRIPTION   "State of global LDP - enabled or disabled"
        DEFVAL        { disable }
        ::= { rcMplsGlobalScalars 2 }

rcMplsLdpPenultimateHopPop OBJECT-TYPE
        SYNTAX        INTEGER {
                         implicit-null(1),
                         explicit-null(2),
                         disabled(3)
                      }
        MAX-ACCESS    read-write
        STATUS        current
        DESCRIPTION   "State of global LDP Penultimate Hop Popping."
        DEFVAL        { implicit-null }
        ::= { rcMplsGlobalScalars 3 }

rcMplsLdpHelloHoldTimer OBJECT-TYPE
         SYNTAX      Unsigned32 (5..65535)
         UNITS       "seconds"
         MAX-ACCESS  read-write
         STATUS      current
         DESCRIPTION "The global Hello Hold Time in seconds."
         DEFVAL { 15 }
         ::= { rcMplsGlobalScalars 4 }

rcMplsLdpSessionKeepAlive  OBJECT-TYPE
         SYNTAX      Unsigned32 (15..65535)
         UNITS       "seconds"
         MAX-ACCESS  read-write
         STATUS      current
         DESCRIPTION "The global Session Keep alive in seconds."
         DEFVAL { 40 }
         ::= { rcMplsGlobalScalars 5 }

rcMplsLdpPathVectorLimit OBJECT-TYPE
         SYNTAX      Integer32 (0..255)
         MAX-ACCESS  read-write
         STATUS      current
         DESCRIPTION "The global path vector limit."
         DEFVAL { 0 }
         ::= { rcMplsGlobalScalars 6 }

rcMplsLdpHopCountLimit OBJECT-TYPE
         SYNTAX      Integer32 (0..255)
         MAX-ACCESS  read-write
         STATUS      current
         DESCRIPTION "The global loop detect hop count limit."
         DEFVAL { 0 }
         ::= { rcMplsGlobalScalars 7 }

rcMplsLdpEgressPolicyStatus  OBJECT-TYPE 
        SYNTAX       EnableValue
        MAX-ACCESS   read-write
        STATUS       current
        DESCRIPTION  "State of LDP Egress-policy enabled or disabled"
        DEFVAL       { disable }
        ::= {rcMplsGlobalScalars 8 }
 
-- MPLS RSVP Global

rcMplsRsvpAdminStatus OBJECT-TYPE
        SYNTAX        EnableValue
        MAX-ACCESS    read-write
        STATUS        current
        DESCRIPTION   "State of global RSVP - enabled or disabled"
        DEFVAL        { disable }
        ::= { rcMplsGlobalScalars 9 }

rcMplsRsvpPenultimateHopPop OBJECT-TYPE
        SYNTAX        INTEGER {
                         implicit-null(1),
                         explicit-null(2),
                         disabled(3)
                      }
        MAX-ACCESS    read-write
        STATUS        current
        DESCRIPTION   "State of global RSVP Penultimate Hop Popping."
        DEFVAL        { implicit-null  }
        ::= { rcMplsGlobalScalars 10 }

 rcMplsRsvpHelloInterval OBJECT-TYPE
         SYNTAX      Unsigned32 (0..65535)
         UNITS       "seconds"
         MAX-ACCESS  read-write
         STATUS      current
         DESCRIPTION "The global RSVP hello interval."
         DEFVAL { 10 }
         ::= { rcMplsGlobalScalars 11 }

rcMplsRsvpRefreshReduction OBJECT-TYPE
        SYNTAX        EnableValue
        MAX-ACCESS    read-write
        STATUS        current
        DESCRIPTION   "State of global RSVP refresh reduction - enabled or disabled"
        DEFVAL        { enable }
        ::= { rcMplsGlobalScalars 12 }

rcMplsRsvpRefreshInterval OBJECT-TYPE
         SYNTAX      Unsigned32 (1..65535)
         UNITS       "seconds"
         MAX-ACCESS  read-write
         STATUS      current
         DESCRIPTION "The global value for RSVP refresh interval."
         DEFVAL { 30 }
        ::= { rcMplsGlobalScalars 13 }

rcMplsRsvpRefreshMultiplier OBJECT-TYPE
         SYNTAX      Unsigned32 (1..255)
         UNITS       "seconds"
         MAX-ACCESS  read-write
         STATUS      current
         DESCRIPTION "The global value for RSVP refresh multiplier."
         DEFVAL { 3 }
        ::= { rcMplsGlobalScalars 14 }
rcMplsRsvpMessageBundling OBJECT-TYPE
        SYNTAX        EnableValue
        MAX-ACCESS    read-write
        STATUS        current
        DESCRIPTION   "State of global RSVP message bundling - enabled or disabled"
        DEFVAL        { enable }
        ::= { rcMplsGlobalScalars 15}

-- MPLS STATISTICS 
rcMplsLspIngressStartLabel OBJECT-TYPE
        SYNTAX      Integer32 (0..1048576)
         MAX-ACCESS  read-write
         STATUS      current
         DESCRIPTION "The global ingress rsp start label."
         DEFVAL { 0 }
         ::= { rcMplsGlobalScalars 16 }

rcMplsLspEgressStartLabel OBJECT-TYPE
        SYNTAX      Integer32 (0..1048576)
        MAX-ACCESS  read-write
        STATUS      current
        DESCRIPTION "The global egress rsp start label."
        DEFVAL { 0 }
        ::= { rcMplsGlobalScalars 17 }

rcMplsLspIngressPktEnable OBJECT-TYPE
        SYNTAX        TruthValue 
        MAX-ACCESS    read-write
        STATUS        current
        DESCRIPTION   "Enable/Disable ingress rsp pkt lsp stats"
        DEFVAL        { false }
        ::= { rcMplsGlobalScalars 18}

rcMplsLspEgressPktEnable OBJECT-TYPE
        SYNTAX        TruthValue 
        MAX-ACCESS    read-write
        STATUS        current
        DESCRIPTION   "Enable/Disable egress rsp pkt lsp stats"
        DEFVAL        { false }
        ::= { rcMplsGlobalScalars 19}

rcMplsLdpClearStats OBJECT-TYPE
        SYNTAX        TruthValue
        MAX-ACCESS    read-write
        STATUS        current
        DESCRIPTION   "Clear global LDP Statistics."
        DEFVAL        { false }
        ::= { rcMplsGlobalScalars 20}

rcMplsRsvpClearStats OBJECT-TYPE
        SYNTAX        TruthValue
        MAX-ACCESS    read-write
        STATUS        current
        DESCRIPTION   "Clear global RSVP Statistics."
        DEFVAL        { false }
        ::= { rcMplsGlobalScalars 21}

rcMplsLspClearStats OBJECT-TYPE
        SYNTAX        INTEGER {
                            none(0),
                            transmit(1),
                            receive(2)
                     }
        MAX-ACCESS    read-write
        STATUS        current
        DESCRIPTION   "Clear 'transmit' or 'receive' lsp statistics."
        ::= { rcMplsGlobalScalars 22 }


-- IP-Static FEC Mapping Table

rcMplsIpStaticFecTable OBJECT-TYPE
        SYNTAX          SEQUENCE OF RcMplsIpStaticFecEntry
        MAX-ACCESS      not-accessible
        STATUS          current
        DESCRIPTION     "This is the table of ip-static fec mappings for both
                         RSVP and LDP ."
    ::= { rcMplsGlobalGroup 2 }

rcMplsIpStaticFecEntry OBJECT-TYPE
        SYNTAX          RcMplsIpStaticFecEntry
        MAX-ACCESS      not-accessible
        STATUS          current
        DESCRIPTION     "A static fec mapping to an rsvp lsp or ldp egress IP address."
        INDEX   { rcMplsIpStaticFecDest,
                  rcMplsIpStaticFecMask }
    ::= { rcMplsIpStaticFecTable 1 }

RcMplsIpStaticFecEntry ::=
        SEQUENCE {
                rcMplsIpStaticFecDest        IpAddress,
                rcMplsIpStaticFecMask        IpAddress,
                rcMplsIpStaticFecTunnelName  DisplayString, 
                rcMplsIpStaticFecTunnelId    MplsTunnelIndex, 
                rcMplsIpStaticFecEgressAddr  IpAddress,
                rcMplsIpStaticFecEgressMask  IpAddress,
                rcMplsIpStaticFecState       INTEGER,
                rcMplsIpStaticFecRowStatus   RowStatus
              }

rcMplsIpStaticFecDest OBJECT-TYPE
        SYNTAX          IpAddress
        MAX-ACCESS      not-accessible
        STATUS          current
        DESCRIPTION     "The statically-configured destination IP address."
    ::= { rcMplsIpStaticFecEntry 1 }

rcMplsIpStaticFecMask OBJECT-TYPE
        SYNTAX          IpAddress
        MAX-ACCESS      not-accessible
        STATUS          current
        DESCRIPTION     "The statically-configured destination IP mask."
    ::= { rcMplsIpStaticFecEntry 2 }

rcMplsIpStaticFecTunnelName OBJECT-TYPE
        SYNTAX          DisplayString(SIZE(0..33)) 
        MAX-ACCESS      read-create
        STATUS          current
        DESCRIPTION     "The rsvp lsp tunnel name associated with 
                         rcMplsIpStaticFecTunnelId. This field will be
                         null if the value of rcMplsIpStaticFecTunnelId is 0."
    ::= { rcMplsIpStaticFecEntry 3 }

rcMplsIpStaticFecTunnelId OBJECT-TYPE
        SYNTAX          MplsTunnelIndex 
        MAX-ACCESS      read-create
        STATUS          current
        DESCRIPTION     "The rsvp lsp tunnel index (from mplsTunnelTable 
                         defined in rfc3812) if this is an rsvp Ip statically
                         mapped address.  This field will be 0 if this is an
                         LDP Egress Address mapping." 
    ::= { rcMplsIpStaticFecEntry 4 }

rcMplsIpStaticFecEgressAddr OBJECT-TYPE
        SYNTAX          IpAddress
        MAX-ACCESS      read-create
        STATUS          current
        DESCRIPTION     "The LDP Egress IP Address.
                         This field will be 0 if this is an rsvp
                         tunnel fec mapping."
    ::= { rcMplsIpStaticFecEntry 5 }

rcMplsIpStaticFecEgressMask OBJECT-TYPE
        SYNTAX          IpAddress
        MAX-ACCESS      read-create
        STATUS          current
        DESCRIPTION     "The LDP Egress IP Mask.
                         This field will be 0 if this is an rsvp
                         tunnel fec mapping."
    ::= { rcMplsIpStaticFecEntry 6 }

rcMplsIpStaticFecState OBJECT-TYPE
      SYNTAX     INTEGER {
                  up(1),
                  down(2)
                }
      MAX-ACCESS    read-only
      STATUS        current
      DESCRIPTION
           "Indicates the actual operational status of this
             static fec."
    ::= { rcMplsIpStaticFecEntry 7 }

rcMplsIpStaticFecRowStatus OBJECT-TYPE
      SYNTAX        RowStatus
      MAX-ACCESS    read-create
      STATUS        current
      DESCRIPTION
           "This variable is used to create, modify, and/or
             delete a row in this table."
    ::= { rcMplsIpStaticFecEntry 8 }

-- Mpls FTN Table 

rcMplsIpFtnTable OBJECT-TYPE
        SYNTAX          SEQUENCE OF RcMplsIpFtnEntry
        MAX-ACCESS      not-accessible
        STATUS          current
        DESCRIPTION     "This is the table of mpls Ip FTN."
    ::= { rcMplsGlobalGroup 3 }

rcMplsIpFtnEntry OBJECT-TYPE
        SYNTAX          RcMplsIpFtnEntry
        MAX-ACCESS      not-accessible
        STATUS          current
        DESCRIPTION     "An mpls FTN entry ."
        INDEX   { rcMplsIpFtnDest,
                  rcMplsIpFtnMask }
    ::= { rcMplsIpFtnTable 1 }

RcMplsIpFtnEntry ::=
        SEQUENCE {
                rcMplsIpFtnDest        IpAddress,
                rcMplsIpFtnMask        IpAddress,
                rcMplsIpFtnType        INTEGER,
                rcMplsIpFtnOutLabel    MplsLabel, 
                rcMplsIpFtnOutIfIndex  InterfaceIndex,
                rcMplsIpFtnNextHop     IpAddress
              } 

rcMplsIpFtnDest OBJECT-TYPE
        SYNTAX          IpAddress
        MAX-ACCESS      not-accessible
        STATUS          current
        DESCRIPTION     "The FTN destination IP address."
    ::= { rcMplsIpFtnEntry 1 }

rcMplsIpFtnMask OBJECT-TYPE
        SYNTAX          IpAddress
        MAX-ACCESS      not-accessible
        STATUS          current
        DESCRIPTION     "The FTN destination IP mask."
    ::= { rcMplsIpFtnEntry 2 }

rcMplsIpFtnType OBJECT-TYPE
        SYNTAX          INTEGER {
                          rsvp-static(1),
                          ldp-static(2),
                          ldp-dynamic(3)
                        }
        MAX-ACCESS      read-only
        STATUS          current
        DESCRIPTION     "The FTN next hop label type."
    ::= { rcMplsIpFtnEntry 3 }

rcMplsIpFtnOutLabel OBJECT-TYPE
        SYNTAX          MplsLabel
        MAX-ACCESS      read-only
        STATUS          current
        DESCRIPTION     "The FTN outgoing label."
    ::= { rcMplsIpFtnEntry 4 }

rcMplsIpFtnOutIfIndex OBJECT-TYPE
        SYNTAX        InterfaceIndex
        MAX-ACCESS    read-only
        STATUS        current
        DESCRIPTION   "The index value which uniquely identifies the
                      interface to which this entry is applicable.  The
                      interface identified by a particular value of this
                      index is the same interface as identified by the
                      same value of ifIndex."
    ::= { rcMplsIpFtnEntry 5 }

rcMplsIpFtnNextHop OBJECT-TYPE
        SYNTAX          IpAddress
        MAX-ACCESS      read-only
        STATUS          current
        DESCRIPTION     "The FTN next hop Ip Address."
    ::= { rcMplsIpFtnEntry 6 }


-- Mpls Ilm Table (Incoming Label Map)

rcMplsIpIlmTable OBJECT-TYPE
        SYNTAX          SEQUENCE OF RcMplsIpIlmEntry
        MAX-ACCESS      not-accessible
        STATUS          current
        DESCRIPTION     "This is the table of mpls Incoming Label Mapping."
    ::= { rcMplsGlobalGroup 4 }

rcMplsIpIlmEntry OBJECT-TYPE
        SYNTAX          RcMplsIpIlmEntry
        MAX-ACCESS      not-accessible
        STATUS          current
        DESCRIPTION     "An mpls Incoming Label Map entry ."
        INDEX   { rcMplsIpIlmInLabel }
    ::= { rcMplsIpIlmTable 1 }

RcMplsIpIlmEntry ::=
        SEQUENCE {
                rcMplsIpIlmInLabel       MplsLabel,
                rcMplsIpIlmInIfIndex     InterfaceIndex,
                rcMplsIpIlmOutLabel      MplsLabel,
                rcMplsIpIlmOutIfIndex    InterfaceIndex,
                rcMplsIpIlmNextHop       IpAddress
              }

rcMplsIpIlmInLabel OBJECT-TYPE
        SYNTAX          MplsLabel
        MAX-ACCESS      not-accessible
        STATUS          current
        DESCRIPTION     "The Incoming Label."
    ::= { rcMplsIpIlmEntry 1 }

rcMplsIpIlmInIfIndex OBJECT-TYPE
        SYNTAX        InterfaceIndex
        MAX-ACCESS    read-only
        STATUS        current
        DESCRIPTION   "The index value which uniquely identifies the
                      incoming interface to which this entry is applicable.  The
                      interface identified by a particular value of this
                      index is the same interface as identified by the
                      same value of ifIndex."
    ::= { rcMplsIpIlmEntry 2 }

rcMplsIpIlmOutLabel OBJECT-TYPE
        SYNTAX          MplsLabel
        MAX-ACCESS      read-only
        STATUS          current
        DESCRIPTION     "The Outgoing Label."
    ::= { rcMplsIpIlmEntry 3 }

rcMplsIpIlmOutIfIndex OBJECT-TYPE
        SYNTAX        InterfaceIndex
        MAX-ACCESS    read-only
        STATUS        current
        DESCRIPTION   "The index value which uniquely identifies the
                      outgoing interface to which this entry is applicable.  The
                      interface identified by a particular value of this
                      index is the same interface as identified by the
                      same value of ifIndex."
    ::= { rcMplsIpIlmEntry 4 }

rcMplsIpIlmNextHop OBJECT-TYPE
        SYNTAX          IpAddress
        MAX-ACCESS      read-only
        STATUS          current
        DESCRIPTION     "The next hop Ip Address."
    ::= { rcMplsIpIlmEntry 5 }


-- Mpls Ingress Lsp Statistics Table 

rcMplsIngressLspStatTable OBJECT-TYPE
        SYNTAX          SEQUENCE OF RcMplsIngressLspStatEntry
        MAX-ACCESS      not-accessible
        STATUS          current
        DESCRIPTION     "This is the table of mpls Incoming Label Stats."
    ::= { rcMplsGlobalGroup 5 }

rcMplsIngressLspStatEntry OBJECT-TYPE
        SYNTAX          RcMplsIngressLspStatEntry 
        MAX-ACCESS      not-accessible
        STATUS          current
        DESCRIPTION     "An mpls Incoming Label Stat entry ."
        INDEX              { rcMplsIngressLspPort,
                             rcMplsIngressLspLabel}
    ::= { rcMplsIngressLspStatTable 1 }

RcMplsIngressLspStatEntry ::=
        SEQUENCE {
                rcMplsIngressLspPort     INTEGER,
                rcMplsIngressLspLabel    MplsLabel,
                rcMplsIngressLspPkts     Counter64
              }

rcMplsIngressLspPort OBJECT-TYPE
        SYNTAX        INTEGER (64..687)
        MAX-ACCESS    not-accessible 
        STATUS        current
        DESCRIPTION   "The incoming port for the lsp."
    ::= { rcMplsIngressLspStatEntry 1 }


rcMplsIngressLspLabel OBJECT-TYPE
        SYNTAX          MplsLabel
        MAX-ACCESS      not-accessible 
        STATUS          current
        DESCRIPTION     "The Incoming Lsp Label."
    ::= { rcMplsIngressLspStatEntry 2 }

rcMplsIngressLspPkts OBJECT-TYPE
         SYNTAX        Counter64
         MAX-ACCESS    read-only
         STATUS        current 
         DESCRIPTION   "Count of incoming packets for the corresponding lsp and port."    
     ::= { rcMplsIngressLspStatEntry 3 } 

-- Mpls Egress Lsp Statistics Table 

rcMplsEgressLspStatTable OBJECT-TYPE
         SYNTAX          SEQUENCE OF RcMplsEgressLspStatEntry
         MAX-ACCESS      not-accessible
         STATUS          current
         DESCRIPTION     "This is the table of mpls OutGoing Label Stats."
     ::= { rcMplsGlobalGroup 6 }
 
rcMplsEgressLspStatEntry OBJECT-TYPE
         SYNTAX          RcMplsEgressLspStatEntry 
         MAX-ACCESS      not-accessible
         STATUS          current
         DESCRIPTION     "An mpls OutGoing Label Stat entry ."
         INDEX             { rcMplsEgressLspPort,
                             rcMplsEgressLspLabel}
     ::= { rcMplsEgressLspStatTable 1 }
 
RcMplsEgressLspStatEntry ::=
         SEQUENCE {
                 rcMplsEgressLspPort     INTEGER,
                 rcMplsEgressLspLabel    MplsLabel,
                 rcMplsEgressLspPkts     Counter64
               }

rcMplsEgressLspPort OBJECT-TYPE
         SYNTAX        INTEGER (64..687)
         MAX-ACCESS    not-accessible
         STATUS        current 
         DESCRIPTION   "The OutGoing port for the lsp."
     ::= { rcMplsEgressLspStatEntry 1 }
 
 
rcMplsEgressLspLabel OBJECT-TYPE
         SYNTAX          MplsLabel
         MAX-ACCESS      not-accessible  
         STATUS          current 
         DESCRIPTION     "The OutGoing Lsp Label."
      ::= { rcMplsEgressLspStatEntry 2 }


rcMplsEgressLspPkts OBJECT-TYPE
         SYNTAX        Counter64
         MAX-ACCESS    read-only
         STATUS        current
         DESCRIPTION   "Count of outgoing packets for the corresponding lsp and port."
     ::= { rcMplsEgressLspStatEntry 3 }


-- Mpls Rsvp Information 

rcMplsRsvpGroup        OBJECT IDENTIFIER ::= { rcMplsObjects 2 }

-- For 'show mpls rsvp summary' command
rcMplsRsvpSummaryGroup OBJECT IDENTIFIER ::= { rcMplsRsvpGroup 1 }

rcMplsRsvpSummaryVersion OBJECT-TYPE
        SYNTAX        Unsigned32
        MAX-ACCESS    read-only
        STATUS        current
        DESCRIPTION   "This is the RSVP version number."
    ::= { rcMplsRsvpSummaryGroup 1 }

rcMplsRsvpSummaryState OBJECT-TYPE
        SYNTAX        EnableValue
        MAX-ACCESS    read-only
        STATUS        current
        DESCRIPTION   "This is the RSVP protocol state."
    ::= { rcMplsRsvpSummaryGroup 2 }

rcMplsRsvpSummaryLSPRetryTimer OBJECT-TYPE
        SYNTAX        Unsigned32
        UNITS         "seconds"
        MAX-ACCESS    read-only
        STATUS        current
        DESCRIPTION   "This is the retry timer (secs) for the LSPs
                       starting from this node, in case of failure.
                       A value of zero means no retry on LSPs."
    ::= { rcMplsRsvpSummaryGroup 3 }

rcMplsRsvpSummaryLSPRetryLimit OBJECT-TYPE
        SYNTAX        Unsigned32
        MAX-ACCESS    read-only
        STATUS        current
        DESCRIPTION   "This is the retry limit for the LSPs starting
                       from this node. It indicates how many times
                       an LSP is retried before giving up.
                       A value of zero means try infinitely."
    ::= { rcMplsRsvpSummaryGroup 4 }

rcMplsRsvpSummaryLSPDecayRate OBJECT-TYPE
        SYNTAX        Unsigned32
        MAX-ACCESS    read-only
        STATUS        current
        DESCRIPTION   "This is the decay rate (percent) for LSPs
                       starting on this node."
    ::= { rcMplsRsvpSummaryGroup 5 }

rcMplsRsvpSummaryPHP OBJECT-TYPE
        SYNTAX        INTEGER {
                         implicit-null(1),
                         explicit-null(2),
                         disabled(3)
                      }

        MAX-ACCESS    read-only
        STATUS        current
        DESCRIPTION   "This is the configured RSVP PHP support on
                       this node.  Possible values are implicit-null,
                       explicit-null, or disabled."
    ::= { rcMplsRsvpSummaryGroup 6 }


-- Mpls Tunnel Extension Table

-- Rapid city extensions to mplsTunnelTable (rfc3812)
rcMplsRsvpTunnelExtTable OBJECT-TYPE
        SYNTAX          SEQUENCE OF RcMplsRsvpTunnelExtEntry
        MAX-ACCESS      not-accessible
        STATUS          current
        DESCRIPTION     "This is the table of mpls rsvp tunnels.  This table 
                         supplements the mplsTunnelTable from rfc3812."
    ::= { rcMplsRsvpGroup 2 }

rcMplsRsvpTunnelExtEntry OBJECT-TYPE
        SYNTAX          RcMplsRsvpTunnelExtEntry
        MAX-ACCESS      not-accessible
        STATUS          current
        DESCRIPTION     "An entry in the mpls tunnel table."
        INDEX   { rcMplsRsvpTunnelExtIndex,
                  rcMplsRsvpTunnelExtInstance,
                  rcMplsRsvpTunnelExtIngressLSRId,
                  rcMplsRsvpTunnelExtEgressLSRId }
    ::= { rcMplsRsvpTunnelExtTable 1 }

RcMplsRsvpTunnelExtEntry ::=
        SEQUENCE {
                rcMplsRsvpTunnelExtIndex                MplsTunnelIndex,
                rcMplsRsvpTunnelExtInstance             MplsTunnelInstanceIndex,
                rcMplsRsvpTunnelExtIngressLSRId         MplsExtendedTunnelId,
                rcMplsRsvpTunnelExtEgressLSRId          MplsExtendedTunnelId,
                rcMplsRsvpTunnelExtName                 SnmpAdminString,
                rcMplsRsvpTunnelExtSwitchover           TruthValue,
                rcMplsRsvpTunnelExtActiveStatus         TruthValue,
                rcMplsRsvpTunnelExtResStyle             SnmpAdminString,
                rcMplsRsvpTunnelExtLspId                MplsLSPID,
                rcMplsRsvpTunnelExtERO                  SnmpAdminString,
                rcMplsRsvpTunnelExtRRO                  SnmpAdminString,
                rcMplsRsvpTunnelExtInIfIndex            InterfaceIndex,
                rcMplsRsvpTunnelExtInLabel              MplsLabel,
                rcMplsRsvpTunnelExtInNeighbor           IpAddress,
                rcMplsRsvpTunnelExtOutIfIndex           InterfaceIndex,
                rcMplsRsvpTunnelExtOutLabel             MplsLabel,
                rcMplsRsvpTunnelExtOutNeighbor          IpAddress,
                rcMplsRsvpTunnelExtTSpecRate            Unsigned32,
                rcMplsRsvpTunnelExtTSpecSize            Unsigned32,
                rcMplsRsvpTunnelExtTSpecPeak            Unsigned32,
                rcMplsRsvpTunnelExtTSpecMin             Unsigned32,
                rcMplsRsvpTunnelExtTSpecMax             Unsigned32,
                rcMplsRsvpTunnelExtInstanceUpTime       TimeTicks,           
                rcMplsRsvpTunnelExtLSPUpTime            TimeTicks
         }

rcMplsRsvpTunnelExtIndex OBJECT-TYPE
        SYNTAX          MplsTunnelIndex
        MAX-ACCESS      not-accessible
        STATUS          current
        DESCRIPTION     "The Tunnel Index.  The value of this object
                         should mimic the value of mplsTunnelIndex of the
                         MplsTunnelEntry of the mpls tunnel for which
                         this extended tunnel table entry row applies." 
    ::= { rcMplsRsvpTunnelExtEntry 1 }

rcMplsRsvpTunnelExtInstance OBJECT-TYPE
        SYNTAX          MplsTunnelInstanceIndex
        MAX-ACCESS      not-accessible
        STATUS          current
        DESCRIPTION     "The Tunnel Instance.  The value of this object
                         should mimic the value of mplsTunnelInstance of the
                         MplsTunnelEntry of the mpls tunnel for which
                         this extended tunnel table entry row applies."
    ::= { rcMplsRsvpTunnelExtEntry 2 }

rcMplsRsvpTunnelExtIngressLSRId OBJECT-TYPE
        SYNTAX          MplsExtendedTunnelId
        MAX-ACCESS      not-accessible
        STATUS          current
        DESCRIPTION     "The Rsvp Tunnel Ingress LSR Id.  The value of
                         this object should mimic the value of the
                         mplsTunnelIngressLSRId of the
                         MplsTunnelEntry of the mpls tunnel for which
                         this extended tunnel table entry row applies." 
    ::= { rcMplsRsvpTunnelExtEntry 3 }

rcMplsRsvpTunnelExtEgressLSRId OBJECT-TYPE
        SYNTAX          MplsExtendedTunnelId
        MAX-ACCESS      not-accessible
        STATUS          current
        DESCRIPTION     "The Rsvp Tunnel Egress LSR Id.  The value of
                         this object should mimic the value of the
                         mplsTunnelEgressLSRId of the
                         MplsTunnelEntry of the mpls tunnel for which
                         this extended tunnel table entry row applies." 
    ::= { rcMplsRsvpTunnelExtEntry 4 }

rcMplsRsvpTunnelExtName OBJECT-TYPE
        SYNTAX SnmpAdminString
        MAX-ACCESS    read-write
        STATUS current
        DESCRIPTION
            "The Name of the tunnel associated with this LSP." 
    ::= { rcMplsRsvpTunnelExtEntry 5 }

rcMplsRsvpTunnelExtSwitchover OBJECT-TYPE
        SYNTAX        TruthValue
        MAX-ACCESS    read-write
        STATUS        current
        DESCRIPTION   "Switch this LSP from active status to inactive
                       status or vice versa."
        DEFVAL        { false }
    ::= { rcMplsRsvpTunnelExtEntry 6 }

rcMplsRsvpTunnelExtActiveStatus OBJECT-TYPE
        SYNTAX        TruthValue
        MAX-ACCESS    read-only
        STATUS        current
        DESCRIPTION   "This is 'true' if this is the active LSP of the tunnel."
    ::= { rcMplsRsvpTunnelExtEntry 7 }

rcMplsRsvpTunnelExtResStyle OBJECT-TYPE
        SYNTAX        SnmpAdminString (SIZE (10))
        MAX-ACCESS    read-only
        STATUS        current
        DESCRIPTION   "This is the reservation style of the tunnel."
    ::= { rcMplsRsvpTunnelExtEntry 8 }

rcMplsRsvpTunnelExtLspId OBJECT-TYPE
        SYNTAX        MplsLSPID
        MAX-ACCESS    read-only
        STATUS        current
        DESCRIPTION   "This is the LSP Id of this LSP."
    ::= { rcMplsRsvpTunnelExtEntry 9 }

rcMplsRsvpTunnelExtERO OBJECT-TYPE
        SYNTAX        SnmpAdminString (SIZE (100))
        MAX-ACCESS    read-only
        STATUS        current
        DESCRIPTION   "This is the Explicit Route associated with this LSP."
    ::= { rcMplsRsvpTunnelExtEntry 10 }

rcMplsRsvpTunnelExtRRO OBJECT-TYPE
        SYNTAX        SnmpAdminString (SIZE (100))
        MAX-ACCESS    read-only
        STATUS        current
        DESCRIPTION   "This is the Recorded Route associated with this LSP."
    ::= { rcMplsRsvpTunnelExtEntry 11 }

rcMplsRsvpTunnelExtInIfIndex OBJECT-TYPE
        SYNTAX        InterfaceIndex
        MAX-ACCESS    read-only
        STATUS        current
        DESCRIPTION   "This is the incoming interface for the LSP.  This
                       applies to rows with mplsTunnelRole set to
                       transit(2) or tail(3)."
    ::= { rcMplsRsvpTunnelExtEntry 12 }

rcMplsRsvpTunnelExtInLabel OBJECT-TYPE
        SYNTAX        MplsLabel
        MAX-ACCESS    read-only
        STATUS        current
        DESCRIPTION   "This is the incoming Mpls Label. This
                       applies to rows with mplsTunnelRole set to
                       transit(2) or tail(3)."
    ::= { rcMplsRsvpTunnelExtEntry 13 }

rcMplsRsvpTunnelExtInNeighbor OBJECT-TYPE
        SYNTAX        IpAddress
        MAX-ACCESS    read-only
        STATUS        current
        DESCRIPTION   "This address of the previous-hop (upstream)
                       router.  This applies to rows with mplsTunnelRole
                       set to transit(2) or tail(3)."
    ::= { rcMplsRsvpTunnelExtEntry 14 }

rcMplsRsvpTunnelExtOutIfIndex OBJECT-TYPE
        SYNTAX        InterfaceIndex
        MAX-ACCESS    read-only
        STATUS        current
        DESCRIPTION   "This is the outgoing interface for the LSP.  This
                       applies to rows with mplsTunnelRole set to
                       head(1) or transit(2)."
    ::= { rcMplsRsvpTunnelExtEntry 15 }

rcMplsRsvpTunnelExtOutLabel OBJECT-TYPE
        SYNTAX        MplsLabel
        MAX-ACCESS    read-only
        STATUS        current
        DESCRIPTION   "This is the outgoing Mpls Label.  This
                       applies to rows with mplsTunnelRole set to
                       head(1) or transit(2)."
    ::= { rcMplsRsvpTunnelExtEntry 16 }

rcMplsRsvpTunnelExtOutNeighbor OBJECT-TYPE
        SYNTAX        IpAddress
        MAX-ACCESS    read-only
        STATUS        current
        DESCRIPTION   "This address of the next-hop (downstream)
                       router.  This applies to rows with
                       applies to rows with mplsTunnelRole set to
                       head(1) or transit(2)."
    ::= { rcMplsRsvpTunnelExtEntry 17 }

rcMplsRsvpTunnelExtTSpecRate OBJECT-TYPE
        SYNTAX        Unsigned32
        MAX-ACCESS    read-only
        STATUS        current
        DESCRIPTION   "This is the primary LSP TSpec Rate.
                       This applies to rows with mplsTunnelRole set to
                       transit(2) or tail(3)."
    ::= { rcMplsRsvpTunnelExtEntry 18 }

rcMplsRsvpTunnelExtTSpecSize OBJECT-TYPE
        SYNTAX        Unsigned32
        MAX-ACCESS    read-only
        STATUS        current
        DESCRIPTION   "This is the primary LSP TSpec Size.
                       This applies to rows with mplsTunnelRole set to
                       transit(2) or tail(3)."
    ::= { rcMplsRsvpTunnelExtEntry 19 }

rcMplsRsvpTunnelExtTSpecPeak OBJECT-TYPE
        SYNTAX        Unsigned32
        MAX-ACCESS    read-only
        STATUS        current
        DESCRIPTION   "This is the primary LSP TSpec Peak.
                       This applies to rows with mplsTunnelRole set to
                       transit(2) or tail(3)."
    ::= { rcMplsRsvpTunnelExtEntry 20 }

rcMplsRsvpTunnelExtTSpecMin OBJECT-TYPE
        SYNTAX        Unsigned32
        MAX-ACCESS    read-only
        STATUS        current
        DESCRIPTION   "This is the primary LSP TSpec Min.
                       This applies to rows with mplsTunnelRole set to
                       transit(2) or tail(3)."
    ::= { rcMplsRsvpTunnelExtEntry 21 }

rcMplsRsvpTunnelExtTSpecMax OBJECT-TYPE
        SYNTAX        Unsigned32
        MAX-ACCESS    read-only
        STATUS        current
        DESCRIPTION   "This is the primary lsp TSpec Max.
                       This applies to rows with mplsTunnelRole set to
                       transit(2) or tail(3)."
    ::= { rcMplsRsvpTunnelExtEntry 22 }

rcMplsRsvpTunnelExtInstanceUpTime OBJECT-TYPE
        SYNTAX        TimeTicks 
        MAX-ACCESS    read-only
        STATUS        current
        DESCRIPTION   "This is the time (in 100ths of a second) 
                       that this instance has been in the Oper 'Up'
                       state.  When the instance transitions out of
                       the Oper 'Up' state the time is reset to 
                       zero." 
    ::= { rcMplsRsvpTunnelExtEntry 23 }

rcMplsRsvpTunnelExtLSPUpTime OBJECT-TYPE
        SYNTAX        TimeTicks 
        MAX-ACCESS    read-only
        STATUS        current
        DESCRIPTION   "This is the time (in 100ths of a second) 
                       that all instances of this LSP have been in 
                       the Oper Up state. The time is calculated
                       based on the create time of the first instance
                       of the LSP to go to the Oper 'Up' state.  When
                       all instances of this LSP have transitioned
                       out of the Oper 'Up' state the time is reset
                       to zero."
    ::= { rcMplsRsvpTunnelExtEntry 24 }

rcMplsRsvpNeighborTable OBJECT-TYPE
        SYNTAX          SEQUENCE OF RcMplsRsvpNeighborEntry
        MAX-ACCESS      not-accessible
        STATUS          current
        DESCRIPTION     "This is the table of mpls rsvp neighbors."
    ::= { rcMplsRsvpGroup 3 }

rcMplsRsvpNeighborEntry OBJECT-TYPE
        SYNTAX          RcMplsRsvpNeighborEntry
        MAX-ACCESS      not-accessible
        STATUS          current
        DESCRIPTION     "An entry in the mpls rsvp tunnel table."
        INDEX   { rcMplsRsvpNeighborAddress }
    ::= { rcMplsRsvpNeighborTable 1 }

RcMplsRsvpNeighborEntry ::=
        SEQUENCE {
                rcMplsRsvpNeighborAddress        IpAddress,
                rcMplsRsvpNeighborHelloState     SnmpAdminString, 
                rcMplsRsvpNeighborIfIndex        InterfaceIndex,
                rcMplsRsvpNeighborTime           Integer32,
                rcMplsRsvpNeighborPeriod         Integer32,
                rcMplsRsvpNeighborSendCnt        Integer32,
                rcMplsRsvpNeighborRcvCnt         Integer32,
                rcMplsRsvpNeighborLocalInstance  Integer32,
                rcMplsRsvpNeighborRemoteInstance Integer32,
                rcMplsRsvpNeighborCreationTime   Integer32,
                rcMplsRsvpNeighborLastPktRxTime  Integer32,
                rcMplsRsvpNeighborRefReduction   SnmpAdminString 
         }

rcMplsRsvpNeighborAddress OBJECT-TYPE
        SYNTAX        IpAddress
        MAX-ACCESS    not-accessible
        STATUS        current
        DESCRIPTION   "This is the address of a learned neighbor." 
    ::= { rcMplsRsvpNeighborEntry 1 }

rcMplsRsvpNeighborHelloState OBJECT-TYPE
        SYNTAX        SnmpAdminString (SIZE (20))
        MAX-ACCESS    read-only
        STATUS        current
        DESCRIPTION   "This is the state of hello exchange with
                       the neighbor." 
    ::= { rcMplsRsvpNeighborEntry 2 }

rcMplsRsvpNeighborIfIndex OBJECT-TYPE
        SYNTAX        InterfaceIndex
        MAX-ACCESS    read-only
        STATUS        current
        DESCRIPTION   "This is the interface index of the neighbor." 
    ::= { rcMplsRsvpNeighborEntry 3 }

rcMplsRsvpNeighborTime OBJECT-TYPE
        SYNTAX        Integer32
        MAX-ACCESS    read-only
        STATUS        current
        DESCRIPTION   "This is the time the neighbor was learned." 
    ::= { rcMplsRsvpNeighborEntry 4 }

rcMplsRsvpNeighborPeriod OBJECT-TYPE
        SYNTAX        Integer32
        MAX-ACCESS    read-only
        STATUS        current
        DESCRIPTION   "This is the RSVP Hello Interval."
    ::= { rcMplsRsvpNeighborEntry 5 }

rcMplsRsvpNeighborSendCnt OBJECT-TYPE
        SYNTAX        Integer32
        MAX-ACCESS    read-only
        STATUS        current
        DESCRIPTION   "This is the number of Hello packets sent
                       to the neighbor."
    ::= { rcMplsRsvpNeighborEntry 6 }

rcMplsRsvpNeighborRcvCnt OBJECT-TYPE
        SYNTAX        Integer32
        MAX-ACCESS    read-only
        STATUS        current
        DESCRIPTION   "This is the number of Hellp packets received
                       from the neighbor."
    ::= { rcMplsRsvpNeighborEntry 7 }

rcMplsRsvpNeighborLocalInstance OBJECT-TYPE
        SYNTAX        Integer32
        MAX-ACCESS    read-only
        STATUS        current
        DESCRIPTION   "This is the identification sent to the remote
                       router during Hello message exchange."
    ::= { rcMplsRsvpNeighborEntry 8 }

rcMplsRsvpNeighborRemoteInstance OBJECT-TYPE
        SYNTAX        Integer32
        MAX-ACCESS    read-only
        STATUS        current
        DESCRIPTION   "This is the identification provided by the
                       remote router during Hello message exchange."
    ::= { rcMplsRsvpNeighborEntry 9 }

rcMplsRsvpNeighborCreationTime OBJECT-TYPE
        SYNTAX        Integer32
        MAX-ACCESS    read-only
        STATUS        current
        DESCRIPTION   "This is the time the neighbor instance was created." 
    ::= { rcMplsRsvpNeighborEntry 10 }

rcMplsRsvpNeighborLastPktRxTime OBJECT-TYPE
        SYNTAX        Integer32
        MAX-ACCESS    read-only
        STATUS        current
        DESCRIPTION   "This is the time that the last Hello message 
                       was received from the remote router."
    ::= { rcMplsRsvpNeighborEntry 11 }

rcMplsRsvpNeighborRefReduction OBJECT-TYPE
        SYNTAX        SnmpAdminString (SIZE (50))
        MAX-ACCESS    read-only
        STATUS        current
        DESCRIPTION   "This is the refresh-reduction status between the
                       local router and the neighbor."
    ::= { rcMplsRsvpNeighborEntry 12 }


-- For 'show mpls rsvp interface' command 
rcMplsRsvpInterfaceTable OBJECT-TYPE
        SYNTAX          SEQUENCE OF RcMplsRsvpInterfaceEntry
        MAX-ACCESS      not-accessible
        STATUS          current
        DESCRIPTION     "This is the table of mpls rsvp interfaces."
    ::= { rcMplsRsvpGroup 4 }

rcMplsRsvpInterfaceEntry OBJECT-TYPE
        SYNTAX          RcMplsRsvpInterfaceEntry
        MAX-ACCESS      not-accessible
        STATUS          current
        DESCRIPTION     "An entry in the mpls rsvp interface table."
        INDEX   { rcMplsRsvpInterfaceIfIndex }
    ::= { rcMplsRsvpInterfaceTable 1 }

RcMplsRsvpInterfaceEntry ::=
        SEQUENCE {
                rcMplsRsvpInterfaceIfIndex          InterfaceIndex,
                rcMplsRsvpInterfaceAddress          IpAddress,
                rcMplsRsvpInterfaceRefreshInterval  Unsigned32,
                rcMplsRsvpInterfaceRefreshMult      Unsigned32,
                rcMplsRsvpInterfaceHelloInterval    Unsigned32,
                rcMplsRsvpInterfaceRefreshReduction Unsigned32,
                rcMplsRsvpInterfaceMessageBundling  Unsigned32
         }

rcMplsRsvpInterfaceIfIndex OBJECT-TYPE
        SYNTAX        InterfaceIndex
        MAX-ACCESS    not-accessible
        STATUS        current
        DESCRIPTION   "This is the interface index."
    ::= { rcMplsRsvpInterfaceEntry 1 }

rcMplsRsvpInterfaceAddress OBJECT-TYPE
        SYNTAX        IpAddress
        MAX-ACCESS    read-only 
        STATUS        current
        DESCRIPTION   "This is the address of the interface."
    ::= { rcMplsRsvpInterfaceEntry 2 }

rcMplsRsvpInterfaceRefreshInterval  OBJECT-TYPE
        SYNTAX        Unsigned32
        MAX-ACCESS    read-only
        STATUS        current
        DESCRIPTION   "This is the RSVP refresh interval for the
                       interface(seconds)."
    ::= { rcMplsRsvpInterfaceEntry 3 }

rcMplsRsvpInterfaceRefreshMult  OBJECT-TYPE
        SYNTAX        Unsigned32
        MAX-ACCESS    read-only
        STATUS        current
        DESCRIPTION   "This is the configured RSVP refresh 
                       multiplier for the interface(seconds)."
    ::= { rcMplsRsvpInterfaceEntry 4 }

rcMplsRsvpInterfaceHelloInterval  OBJECT-TYPE
        SYNTAX        Unsigned32
        MAX-ACCESS    read-only
        STATUS        current
        DESCRIPTION   "This is the configured RSVP Hello Interval
                       of the interface (seconds)." 
    ::= { rcMplsRsvpInterfaceEntry 5 }

rcMplsRsvpInterfaceRefreshReduction OBJECT-TYPE
        SYNTAX        Unsigned32
        MAX-ACCESS    read-only
        STATUS        current
        DESCRIPTION   "This is the configured RSVP refresh reduction
                       support on the interface." 
    ::= { rcMplsRsvpInterfaceEntry 6 }

rcMplsRsvpInterfaceMessageBundling OBJECT-TYPE
        SYNTAX        Unsigned32
        MAX-ACCESS    read-only
        STATUS        current
        DESCRIPTION   "This indicates state of message bundling on the interface." 
    ::= { rcMplsRsvpInterfaceEntry 7 }


-- For 'show mpls rsvp statistics' command 
rcMplsRsvpStatsTable OBJECT-TYPE
        SYNTAX          SEQUENCE OF RcMplsRsvpStatsEntry
        MAX-ACCESS      not-accessible
        STATUS          current
        DESCRIPTION     "This is the table of mpls rsvp statistics."
    ::= { rcMplsRsvpGroup 5 }

rcMplsRsvpStatsEntry OBJECT-TYPE
        SYNTAX          RcMplsRsvpStatsEntry
        MAX-ACCESS      not-accessible
        STATUS          current
        DESCRIPTION     "An entry in the mpls rsvp statistics table."
        INDEX          { rcMplsRsvpStatsIfIndex }
    ::= { rcMplsRsvpStatsTable 1 }

RcMplsRsvpStatsEntry ::=
        SEQUENCE {
                rcMplsRsvpStatsIfIndex          InterfaceIndex,
                rcMplsRsvpStatsPathRcv          Counter32,
                rcMplsRsvpStatsPathSent         Counter32,
                rcMplsRsvpStatsPathErrRcv       Counter32,
                rcMplsRsvpStatsPathErrSent      Counter32,
                rcMplsRsvpStatsPathTearRcv      Counter32,
                rcMplsRsvpStatsPathTearSent     Counter32,
                rcMplsRsvpStatsResvRcv          Counter32,
                rcMplsRsvpStatsResvSent         Counter32,
                rcMplsRsvpStatsResvErrRcv       Counter32,
                rcMplsRsvpStatsResvErrSent      Counter32,
                rcMplsRsvpStatsResvTearRcv      Counter32,
                rcMplsRsvpStatsResvTearSent     Counter32,
                rcMplsRsvpStatsConfTearRcv      Counter32,
                rcMplsRsvpStatsConfTearSent     Counter32,
                rcMplsRsvpStatsAckRcv           Counter32,
                rcMplsRsvpStatsAckSent          Counter32,
                rcMplsRsvpStatsSRefreshRcv      Counter32,
                rcMplsRsvpStatsSRefreshSent     Counter32,
                rcMplsRsvpStatsHelloReqRcv      Counter32,
                rcMplsRsvpStatsHelloReqSent     Counter32,
                rcMplsRsvpStatsHelloAckRcv      Counter32,
                rcMplsRsvpStatsHelloAckSent     Counter32,
                rcMplsRsvpStatsBadIpHdr         Counter32,
                rcMplsRsvpStatsBadVersion       Counter32,
                rcMplsRsvpStatsBadRsvpLen       Counter32,
                rcMplsRsvpStatsBadCksum         Counter32,
                rcMplsRsvpStatsBadMsgType       Counter32,
                rcMplsRsvpStatsBadMsgForm       Counter32,
                rcMplsRsvpStatsBadIntf          Counter32
         }

rcMplsRsvpStatsIfIndex OBJECT-TYPE
        SYNTAX        InterfaceIndex
        MAX-ACCESS    not-accessible
        STATUS        current
        DESCRIPTION   "This is the interface index. This value can be 0 or
                       a valid interface index.  When 0 the global rsvp 
                       statistics are retrieved." 
    ::= { rcMplsRsvpStatsEntry 1 }

rcMplsRsvpStatsPathRcv OBJECT-TYPE
        SYNTAX        Counter32
        MAX-ACCESS    read-only
        STATUS        current
        DESCRIPTION   "This is the path received count." 
    ::= { rcMplsRsvpStatsEntry 2 }

rcMplsRsvpStatsPathSent OBJECT-TYPE
        SYNTAX        Counter32
        MAX-ACCESS    read-only
        STATUS        current
        DESCRIPTION   "This is the path sent count." 
    ::= { rcMplsRsvpStatsEntry 3 }

rcMplsRsvpStatsPathErrRcv OBJECT-TYPE
        SYNTAX        Counter32
        MAX-ACCESS    read-only
        STATUS        current
        DESCRIPTION   "This is the path error receives count."
    ::= { rcMplsRsvpStatsEntry 4 }

rcMplsRsvpStatsPathErrSent OBJECT-TYPE
        SYNTAX        Counter32
        MAX-ACCESS    read-only
        STATUS        current
        DESCRIPTION   "This is the path error sent count."
    ::= { rcMplsRsvpStatsEntry 5 }

rcMplsRsvpStatsPathTearRcv OBJECT-TYPE
        SYNTAX        Counter32
        MAX-ACCESS    read-only
        STATUS        current
        DESCRIPTION   "This is the path tear receives count."
    ::= { rcMplsRsvpStatsEntry 6 }

rcMplsRsvpStatsPathTearSent OBJECT-TYPE
        SYNTAX        Counter32
        MAX-ACCESS    read-only
        STATUS        current
        DESCRIPTION   "This is the path tear sent count."
    ::= { rcMplsRsvpStatsEntry 7 }

rcMplsRsvpStatsResvRcv OBJECT-TYPE
        SYNTAX        Counter32
        MAX-ACCESS    read-only
        STATUS        current
        DESCRIPTION   "This is the reservation received count."
    ::= { rcMplsRsvpStatsEntry 8 }

rcMplsRsvpStatsResvSent OBJECT-TYPE
        SYNTAX        Counter32
        MAX-ACCESS    read-only
        STATUS        current
        DESCRIPTION   "This is the reservation sent count."
    ::= { rcMplsRsvpStatsEntry 9 }

rcMplsRsvpStatsResvErrRcv OBJECT-TYPE
        SYNTAX        Counter32
        MAX-ACCESS    read-only
        STATUS        current
        DESCRIPTION   "This is the reservation error receives count."
    ::= { rcMplsRsvpStatsEntry 10 }

rcMplsRsvpStatsResvErrSent OBJECT-TYPE
        SYNTAX        Counter32
        MAX-ACCESS    read-only
        STATUS        current
        DESCRIPTION   "This is the reservation error sent count."
    ::= { rcMplsRsvpStatsEntry 11 }

rcMplsRsvpStatsResvTearRcv OBJECT-TYPE
        SYNTAX        Counter32
        MAX-ACCESS    read-only
        STATUS        current
        DESCRIPTION   "This is the resv tear receives count."
    ::= { rcMplsRsvpStatsEntry 12 }

rcMplsRsvpStatsResvTearSent OBJECT-TYPE
        SYNTAX        Counter32
        MAX-ACCESS    read-only
        STATUS        current
        DESCRIPTION   "This is the resv tear sent count."
    ::= { rcMplsRsvpStatsEntry 13 }

rcMplsRsvpStatsConfTearRcv OBJECT-TYPE
        SYNTAX        Counter32
        MAX-ACCESS    read-only
        STATUS        current
        DESCRIPTION   "This is the conf tear receives count."
    ::= { rcMplsRsvpStatsEntry 14 }

rcMplsRsvpStatsConfTearSent OBJECT-TYPE
        SYNTAX        Counter32
        MAX-ACCESS    read-only
        STATUS        current
        DESCRIPTION   "This is the conf tear sent count."
    ::= { rcMplsRsvpStatsEntry 15 }

rcMplsRsvpStatsAckRcv OBJECT-TYPE
        SYNTAX        Counter32
        MAX-ACCESS    read-only
        STATUS        current
        DESCRIPTION   "This is the acks receives count."
    ::= { rcMplsRsvpStatsEntry 16 }

rcMplsRsvpStatsAckSent OBJECT-TYPE
        SYNTAX        Counter32
        MAX-ACCESS    read-only
        STATUS        current
        DESCRIPTION   "This is the acks sent count."
    ::= { rcMplsRsvpStatsEntry 17 }

rcMplsRsvpStatsSRefreshRcv OBJECT-TYPE
        SYNTAX        Counter32
        MAX-ACCESS    read-only
        STATUS        current
        DESCRIPTION   "This is the summary refresh receives count."
    ::= { rcMplsRsvpStatsEntry 18 }

rcMplsRsvpStatsSRefreshSent OBJECT-TYPE
        SYNTAX        Counter32
        MAX-ACCESS    read-only
        STATUS        current
        DESCRIPTION   "This is the summary refresh sent count."
    ::= { rcMplsRsvpStatsEntry 19 }

rcMplsRsvpStatsHelloReqRcv OBJECT-TYPE
        SYNTAX        Counter32
        MAX-ACCESS    read-only
        STATUS        current
        DESCRIPTION   "This is the hello request receives count."
    ::= { rcMplsRsvpStatsEntry 20 }

rcMplsRsvpStatsHelloReqSent OBJECT-TYPE
        SYNTAX        Counter32
        MAX-ACCESS    read-only
        STATUS        current
        DESCRIPTION   "This is the hello request sent count."
    ::= { rcMplsRsvpStatsEntry 21 }

rcMplsRsvpStatsHelloAckRcv OBJECT-TYPE
        SYNTAX        Counter32
        MAX-ACCESS    read-only
        STATUS        current
        DESCRIPTION   "This is the hello ack receives count."
    ::= { rcMplsRsvpStatsEntry 22 }

rcMplsRsvpStatsHelloAckSent OBJECT-TYPE
        SYNTAX        Counter32
        MAX-ACCESS    read-only
        STATUS        current
        DESCRIPTION   "This is the hello ack sent count."
    ::= { rcMplsRsvpStatsEntry 23 }

rcMplsRsvpStatsBadIpHdr OBJECT-TYPE
        SYNTAX        Counter32
        MAX-ACCESS    read-only
        STATUS        current
        DESCRIPTION   "This is the count of pkts with bad IP Header."
    ::= { rcMplsRsvpStatsEntry 24}

rcMplsRsvpStatsBadVersion OBJECT-TYPE
        SYNTAX        Counter32
        MAX-ACCESS    read-only
        STATUS        current
        DESCRIPTION   "This is the count of pkts with Bad Version." 
    ::= { rcMplsRsvpStatsEntry 25}

rcMplsRsvpStatsBadRsvpLen OBJECT-TYPE
        SYNTAX        Counter32
        MAX-ACCESS    read-only
        STATUS        current
        DESCRIPTION   "This is the count of pkts with Bad Rsvp length."
    ::= { rcMplsRsvpStatsEntry 26}

rcMplsRsvpStatsBadCksum OBJECT-TYPE
        SYNTAX        Counter32
        MAX-ACCESS    read-only
        STATUS        current
        DESCRIPTION   "This is the count of pkts with Bad Checksum."
    ::= { rcMplsRsvpStatsEntry 27}

rcMplsRsvpStatsBadMsgType OBJECT-TYPE
        SYNTAX        Counter32
        MAX-ACCESS    read-only
        STATUS        current
        DESCRIPTION   "This is the count of pkts with Bad Message type." 
    ::= { rcMplsRsvpStatsEntry 28}

rcMplsRsvpStatsBadMsgForm OBJECT-TYPE
        SYNTAX        Counter32
        MAX-ACCESS    read-only
        STATUS        current
        DESCRIPTION   "This is the count of pkts with Bad Message Form." 
    ::= { rcMplsRsvpStatsEntry 29}

rcMplsRsvpStatsBadIntf OBJECT-TYPE
        SYNTAX        Counter32
        MAX-ACCESS    read-only
        STATUS        current
        DESCRIPTION   "This is the count of pkts received on a
                       Bad Interface."
    ::= { rcMplsRsvpStatsEntry 30}

-- Mpls Ldp Information

rcMplsLdpGroup        OBJECT IDENTIFIER ::= { rcMplsObjects 3 }

-- For 'show mpls ldp summary' command
rcMplsLdpSummaryGroup OBJECT IDENTIFIER ::= { rcMplsLdpGroup 1 }

rcMplsLdpSummaryIntAdjCount OBJECT-TYPE
        SYNTAX        Unsigned32
        MAX-ACCESS    read-only
        STATUS        current
        DESCRIPTION   "This is the LDP summary index."
    ::= { rcMplsLdpSummaryGroup 1 }

rcMplsLdpSummaryExtAdjCount OBJECT-TYPE
        SYNTAX        Unsigned32
        MAX-ACCESS    read-only
        STATUS        current
        DESCRIPTION   "This is the LDP summary index."
    ::= { rcMplsLdpSummaryGroup 2 }

rcMplsLdpSummarySessionCount OBJECT-TYPE
        SYNTAX        Unsigned32
        MAX-ACCESS    read-only
        STATUS        current
        DESCRIPTION   "This is the LDP summary session count."
    ::= { rcMplsLdpSummaryGroup 3 }

rcMplsLdpSummaryRouteCount OBJECT-TYPE
        SYNTAX        Unsigned32
        MAX-ACCESS    read-only
        STATUS        current
        DESCRIPTION   "This is the LDP summary route count."
    ::= { rcMplsLdpSummaryGroup 4 }

rcMplsLdpSummaryLdpId OBJECT-TYPE
        SYNTAX        MplsLdpIdentifier
        MAX-ACCESS    read-only
        STATUS        current
        DESCRIPTION   "This is the LDP summary Local LDP Id."
    ::= { rcMplsLdpSummaryGroup 5 }

rcMplsLdpSummaryLspCount OBJECT-TYPE
        SYNTAX        Unsigned32
        MAX-ACCESS    read-only
        STATUS        current
        DESCRIPTION   "This is the LDP summary LSP count."
    ::= { rcMplsLdpSummaryGroup 6 }

rcMplsLdpSummaryInSegCount OBJECT-TYPE
        SYNTAX        Unsigned32
        MAX-ACCESS    read-only
        STATUS        current
        DESCRIPTION   "This is the LDP summary in segment count."
    ::= { rcMplsLdpSummaryGroup 7 }

rcMplsLdpSummaryOutSegCount OBJECT-TYPE
        SYNTAX        Unsigned32
        MAX-ACCESS    read-only
        STATUS        current
        DESCRIPTION   "This is the LDP summary out segment count."
    ::= { rcMplsLdpSummaryGroup 8 }

rcMplsLdpSummaryRedistConn OBJECT-TYPE
        SYNTAX        EnableValue
        MAX-ACCESS    read-only
        STATUS        current
        DESCRIPTION   "This is the LDP policy redist enable flag."
    ::= { rcMplsLdpSummaryGroup 9 }

-- For 'show mpls ldp discovery' command 
rcMplsLdpDiscoveryTable OBJECT-TYPE
        SYNTAX          SEQUENCE OF RcMplsLdpDiscoveryEntry
        MAX-ACCESS      not-accessible
        STATUS          current
        DESCRIPTION     "This is the table of mpls ldp discoveries."
    ::= { rcMplsLdpGroup 2 }

rcMplsLdpDiscoveryEntry OBJECT-TYPE
        SYNTAX          RcMplsLdpDiscoveryEntry
        MAX-ACCESS      not-accessible
        STATUS          current
        DESCRIPTION     "An entry in the mpls ldp discovery table."
        INDEX           { rcMplsLdpDiscoveryIfIndex,
                          rcMplsLdpDiscoveryPeerLdpId }
    ::= { rcMplsLdpDiscoveryTable 1 }

RcMplsLdpDiscoveryEntry ::=
        SEQUENCE {
                rcMplsLdpDiscoveryIfIndex            InterfaceIndex,
                rcMplsLdpDiscoveryPeerLdpId          MplsLdpIdentifier,
                rcMplsLdpDiscoveryPeerTransportAddr  IpAddress, 
                rcMplsLdpDiscoveryNegotiatedHoldTime Unsigned32, 
                rcMplsLdpDiscoveryConfSeqNum         Unsigned32, 
                rcMplsLdpDiscoveryExtendedDiscovery  Unsigned32
         }

rcMplsLdpDiscoveryIfIndex OBJECT-TYPE
        SYNTAX        InterfaceIndex
        MAX-ACCESS    not-accessible
        STATUS        current
        DESCRIPTION   "This is the interface index."
    ::= { rcMplsLdpDiscoveryEntry 1 }

rcMplsLdpDiscoveryPeerLdpId OBJECT-TYPE
        SYNTAX        MplsLdpIdentifier
        MAX-ACCESS    not-accessible
        STATUS        current
        DESCRIPTION   "This is the peer ldp id." 
    ::= { rcMplsLdpDiscoveryEntry 2 }

rcMplsLdpDiscoveryPeerTransportAddr OBJECT-TYPE
        SYNTAX        IpAddress
        MAX-ACCESS    read-only
        STATUS        current
        DESCRIPTION   "This is the peer transport address to which
                       an LDP session has been provisioned." 
    ::= { rcMplsLdpDiscoveryEntry 3 }

rcMplsLdpDiscoveryNegotiatedHoldTime OBJECT-TYPE
        SYNTAX        Unsigned32
        MAX-ACCESS    read-only
        STATUS        current
        DESCRIPTION   "This is the hold time negotiated between peers." 
    ::= { rcMplsLdpDiscoveryEntry 4 }

rcMplsLdpDiscoveryConfSeqNum OBJECT-TYPE
        SYNTAX        Unsigned32
        MAX-ACCESS    read-only
        STATUS        current
        DESCRIPTION   "This is the configured sequence number sent
                       by the peer." 
    ::= { rcMplsLdpDiscoveryEntry 5 }

rcMplsLdpDiscoveryExtendedDiscovery OBJECT-TYPE
        SYNTAX        Unsigned32
        MAX-ACCESS    read-only
        STATUS        current
        DESCRIPTION   "If set to 1, extended discovery is enabled.
                       If set to 0, basic discovery is enabled."
    ::= { rcMplsLdpDiscoveryEntry 6 }


-- For 'show mpls ldp path' command 
rcMplsLdpPathTable OBJECT-TYPE
        SYNTAX          SEQUENCE OF RcMplsLdpPathEntry
        MAX-ACCESS      not-accessible
        STATUS          current
        DESCRIPTION     "This is the table of mpls LDP Paths between
                         a local peer and a remote peer."
    ::= { rcMplsLdpGroup 3 }

rcMplsLdpPathEntry OBJECT-TYPE
        SYNTAX          RcMplsLdpPathEntry
        MAX-ACCESS      not-accessible
        STATUS          current
        DESCRIPTION     "An entry in the mpls ldp path table."
        INDEX           { rcMplsLdpPathType,
                          rcMplsLdpPathAddrType,
                          rcMplsLdpPathAddrPrefixLength,
                          rcMplsLdpPathAddr }
    ::= { rcMplsLdpPathTable 1 }

RcMplsLdpPathEntry ::=
        SEQUENCE {
                rcMplsLdpPathType                  INTEGER,
                rcMplsLdpPathAddrType              InetAddressType,
                rcMplsLdpPathAddrPrefixLength      InetAddressPrefixLength,
                rcMplsLdpPathAddr                  InetAddress, 
                rcMplsLdpPathInLabel               MplsLabel
         }

rcMplsLdpPathType OBJECT-TYPE
        SYNTAX        INTEGER  {
                              none(0),
                              host(1),
                              prefix(2),
                              vc(3),
                              vcgenid(4)
                      }
        MAX-ACCESS    not-accessible 
        STATUS        current
        DESCRIPTION   "This is the path type.

                       ATG_NHR_LDP_FEC_TYPE_NONE       0
                       ATG_NHR_LDP_FEC_TYPE_HOST       1
                       ATG_NHR_LDP_FEC_TYPE_PREFIX     2
                       ATG_NHR_LDP_FEC_TYPE_VC         3
                       ATG_NHR_LDP_FEC_TYPE_VC_GEN_ID  4."
    ::= { rcMplsLdpPathEntry 1 }

rcMplsLdpPathAddrType OBJECT-TYPE
        SYNTAX        InetAddressType 
        MAX-ACCESS    not-accessible 
        STATUS        current
        DESCRIPTION   "This is the path address type." 
    ::= { rcMplsLdpPathEntry 2 }

rcMplsLdpPathAddrPrefixLength OBJECT-TYPE
        SYNTAX        InetAddressPrefixLength 
        MAX-ACCESS    not-accessible 
        STATUS        current
        DESCRIPTION   "This is the path address prefix length."
   ::= { rcMplsLdpPathEntry 3 }

rcMplsLdpPathAddr OBJECT-TYPE
        SYNTAX        InetAddress
        MAX-ACCESS    not-accessible 
        STATUS        current
        DESCRIPTION   "This is the path address."
    ::= { rcMplsLdpPathEntry 4 }

rcMplsLdpPathInLabel OBJECT-TYPE
        SYNTAX        MplsLabel
        MAX-ACCESS    read-only
        STATUS        current
        DESCRIPTION   "This is the path address prefix length."
    ::= { rcMplsLdpPathEntry 5 }

-- For 'show mpls ldp path' command
rcMplsLdpPathRemotePeerTable OBJECT-TYPE
        SYNTAX          SEQUENCE OF RcMplsLdpPathRemotePeerEntry
        MAX-ACCESS      not-accessible
        STATUS          current
        DESCRIPTION     "This is the table of LDP paths to a given
                         remote peer."
    ::= { rcMplsLdpGroup 4 }

rcMplsLdpPathRemotePeerEntry OBJECT-TYPE
        SYNTAX          RcMplsLdpPathRemotePeerEntry
        MAX-ACCESS      not-accessible
        STATUS          current
        DESCRIPTION     "An entry in the mpls ldp path remote
                         peer table."
        INDEX           { rcMplsLdpPathRemotePeerType,
                          rcMplsLdpPathRemotePeerAddrType,
                          rcMplsLdpPathRemotePeerAddrPrefixLength,
                          rcMplsLdpPathRemotePeerAddr,
                          rcMplsLdpPathRemotePeerId }
    ::= { rcMplsLdpPathRemotePeerTable 1 }

RcMplsLdpPathRemotePeerEntry ::=
        SEQUENCE {
                rcMplsLdpPathRemotePeerType        INTEGER,
                rcMplsLdpPathRemotePeerAddrType    InetAddressType,
                rcMplsLdpPathRemotePeerAddrPrefixLength  InetAddressPrefixLength,
                rcMplsLdpPathRemotePeerAddr        InetAddress,
                rcMplsLdpPathRemotePeerId          INTEGER, 
                rcMplsLdpPathRemotePeerLdpId       MplsLdpIdentifier, 
                rcMplsLdpPathRemotePeerOutLabel    MplsLabel,
                rcMplsLdpPathRemotePeerState       INTEGER
        }

rcMplsLdpPathRemotePeerType OBJECT-TYPE
        SYNTAX        INTEGER  {
                              none(0),
                              host(1),
                              prefix(2),
                              vc(3),
                              vcgenid(4)
                      }
        MAX-ACCESS    not-accessible
        STATUS        current
        DESCRIPTION   "This is the path type.
                       ATG_NHR_LDP_FEC_TYPE_NONE       0
                       ATG_NHR_LDP_FEC_TYPE_HOST       1
                       ATG_NHR_LDP_FEC_TYPE_PREFIX     2
                       ATG_NHR_LDP_FEC_TYPE_VC         3
                       ATG_NHR_LDP_FEC_TYPE_VC_GEN_ID  4."
    ::= { rcMplsLdpPathRemotePeerEntry 1 }

rcMplsLdpPathRemotePeerAddrType OBJECT-TYPE
        SYNTAX        InetAddressType
        MAX-ACCESS    not-accessible
        STATUS        current
        DESCRIPTION   "This is the type of the path address."
    ::= { rcMplsLdpPathRemotePeerEntry 2 }

rcMplsLdpPathRemotePeerAddrPrefixLength OBJECT-TYPE
        SYNTAX        InetAddressPrefixLength 
        MAX-ACCESS    not-accessible
        STATUS        current
        DESCRIPTION   "This is the path address prefix length."
    ::= { rcMplsLdpPathRemotePeerEntry 3 }

rcMplsLdpPathRemotePeerAddr OBJECT-TYPE
        SYNTAX        InetAddress
        MAX-ACCESS    not-accessible
        STATUS        current
        DESCRIPTION   "This is the path address."
    ::= { rcMplsLdpPathRemotePeerEntry 4 }

rcMplsLdpPathRemotePeerId OBJECT-TYPE
        SYNTAX        INTEGER (1..8) 
        MAX-ACCESS    not-accessible
        STATUS        current
        DESCRIPTION   "This is the Id of the remote peer of the path." 
    ::= { rcMplsLdpPathRemotePeerEntry 5 }

rcMplsLdpPathRemotePeerLdpId OBJECT-TYPE
        SYNTAX        MplsLdpIdentifier 
        MAX-ACCESS    read-only
        STATUS        current
        DESCRIPTION   "This is the LDP Id of the remote peer of the path." 
    ::= { rcMplsLdpPathRemotePeerEntry 6 }

rcMplsLdpPathRemotePeerOutLabel OBJECT-TYPE
        SYNTAX        MplsLabel
        MAX-ACCESS    read-only
        STATUS        current
        DESCRIPTION   "This is the Out Label for this instance
                       of the Remote Peer Id." 
    ::= { rcMplsLdpPathRemotePeerEntry 7 }

rcMplsLdpPathRemotePeerState OBJECT-TYPE
        SYNTAX        INTEGER {
                         active(1),
                         inactive(2)
                      }
        MAX-ACCESS    read-only
        STATUS        current
        DESCRIPTION   "This is the state of the remote peer." 
    ::= { rcMplsLdpPathRemotePeerEntry 8 }

-- For 'show mpls ldp route' command 
rcMplsLdpRouteTable OBJECT-TYPE
        SYNTAX          SEQUENCE OF RcMplsLdpRouteEntry
        MAX-ACCESS      not-accessible
        STATUS          current
        DESCRIPTION     "This is the table of mpls ldp routes."


    ::= { rcMplsLdpGroup 5 }

rcMplsLdpRouteEntry OBJECT-TYPE
        SYNTAX          RcMplsLdpRouteEntry
        MAX-ACCESS      not-accessible
        STATUS          current
        DESCRIPTION     "An entry in the mpls ldp route table."
        INDEX           { rcMplsLdpRouteType,
                          rcMplsLdpRouteAddrType,
                          rcMplsLdpRouteAddrPrefixLength, 
                          rcMplsLdpRouteAddr }
    ::= { rcMplsLdpRouteTable 1 }

RcMplsLdpRouteEntry ::=
        SEQUENCE {
                rcMplsLdpRouteType              INTEGER, 
                rcMplsLdpRouteAddrType          InetAddressType, 
                rcMplsLdpRouteAddrPrefixLength  InetAddressPrefixLength, 
                rcMplsLdpRouteAddr              InetAddress, 
                rcMplsLdpRouteIfIndex           InterfaceIndex,
                rcMplsLdpRouteNextHopAddrType   InetAddressType, 
                rcMplsLdpRouteNextHopAddr       InetAddress 
         }
rcMplsLdpRouteType OBJECT-TYPE
        SYNTAX        INTEGER {
                         none(0),
                         host(1),
                         prefix(2),
                         vc(3),
                         vcgenid(4)
                      } 
        MAX-ACCESS    not-accessible 
        STATUS        current
        DESCRIPTION   "This is the route type.
			----------------------
                       ATG_NHR_LDP_FEC_TYPE_NONE       0
                       ATG_NHR_LDP_FEC_TYPE_HOST       1
                       ATG_NHR_LDP_FEC_TYPE_PREFIX     2
                       ATG_NHR_LDP_FEC_TYPE_VC         3
                       ATG_NHR_LDP_FEC_TYPE_VC_GEN_ID  4."
    ::= { rcMplsLdpRouteEntry 1 }

rcMplsLdpRouteAddrType OBJECT-TYPE
        SYNTAX        InetAddressType 
        MAX-ACCESS    not-accessible 
        STATUS        current
        DESCRIPTION   "This is the route address prefix length." 
    ::= { rcMplsLdpRouteEntry 2 }

rcMplsLdpRouteAddrPrefixLength OBJECT-TYPE
        SYNTAX        InetAddressPrefixLength 
        MAX-ACCESS    not-accessible 
        STATUS        current
        DESCRIPTION   "This is the route address prefix length."
    ::= { rcMplsLdpRouteEntry 3 }

rcMplsLdpRouteAddr OBJECT-TYPE
        SYNTAX        InetAddress 
        MAX-ACCESS    not-accessible 
        STATUS        current
        DESCRIPTION   "This is the route address."
    ::= { rcMplsLdpRouteEntry 4 }

rcMplsLdpRouteIfIndex OBJECT-TYPE
        SYNTAX        InterfaceIndex
        MAX-ACCESS    read-only
        STATUS        current
        DESCRIPTION   "This is the interface index of the route entry." 
    ::= { rcMplsLdpRouteEntry 5 }

rcMplsLdpRouteNextHopAddrType OBJECT-TYPE
        SYNTAX        InetAddressType 
        MAX-ACCESS    read-only
        STATUS        current
        DESCRIPTION   "This is the address type of the next hop." 
    ::= { rcMplsLdpRouteEntry 6 }

rcMplsLdpRouteNextHopAddr OBJECT-TYPE
        SYNTAX        InetAddress
        MAX-ACCESS    read-only
        STATUS        current
        DESCRIPTION   "This is the address of the next hop."
    ::= { rcMplsLdpRouteEntry 7 }

-- For 'show mpls ldp session' command 
rcMplsLdpSessionTable OBJECT-TYPE
        SYNTAX          SEQUENCE OF RcMplsLdpSessionEntry
        MAX-ACCESS      not-accessible
        STATUS          current
        DESCRIPTION     "This is the table of mpls ldp sessions."
    ::= { rcMplsLdpGroup 6 }

rcMplsLdpSessionEntry OBJECT-TYPE
        SYNTAX          RcMplsLdpSessionEntry
        MAX-ACCESS      not-accessible
        STATUS          current
        DESCRIPTION     "An entry in the mpls ldp session table."
        INDEX           { rcMplsLdpSessionEntityLdpId,
                          rcMplsLdpSessionEntityIndex,
                          rcMplsLdpSessionPeerLdpId }
    ::= { rcMplsLdpSessionTable 1 }

RcMplsLdpSessionEntry ::=
        SEQUENCE {
                rcMplsLdpSessionEntityLdpId          MplsLdpIdentifier, 
                rcMplsLdpSessionEntityIndex          IndexInteger,
                rcMplsLdpSessionPeerLdpId            MplsLdpIdentifier, 
                rcMplsLdpSessionStateLastChange      Unsigned32, 
                rcMplsLdpSessionState                INTEGER, 
                rcMplsLdpSessionRole                 INTEGER, 
                rcMplsLdpSessionProtocolVersion      Unsigned32, 
                rcMplsLdpSessionKeepAliveHoldTimeRem Integer32, 
                rcMplsLdpSessionKeepAliveTime        Unsigned32, 
                rcMplsLdpSessionMaxPduLength         Unsigned32, 
                rcMplsLdpSessionDiscontinuityTime    Integer32, 
                rcMplsLdpSessionHoldTime             Unsigned32, 
                rcMplsLdpSessionUpTime               Integer32, 
                rcMplsLdpSessionMessagesSent         Counter32, 
                rcMplsLdpSessionMessagesRecv         Counter32 
         }

rcMplsLdpSessionEntityLdpId OBJECT-TYPE
        SYNTAX        MplsLdpIdentifier
        MAX-ACCESS    not-accessible
        STATUS        current
        DESCRIPTION   "This is the entity LDP ID for the session." 
    ::= { rcMplsLdpSessionEntry 1 }

rcMplsLdpSessionEntityIndex OBJECT-TYPE
        SYNTAX        IndexInteger
        MAX-ACCESS    not-accessible
        STATUS        current
        DESCRIPTION   "This is the entity LDP ID for the session." 
    ::= { rcMplsLdpSessionEntry 2 }

rcMplsLdpSessionPeerLdpId OBJECT-TYPE
        SYNTAX        MplsLdpIdentifier
        MAX-ACCESS    not-accessible
        STATUS        current
        DESCRIPTION   "This is the peer LDP ID for the session." 
    ::= { rcMplsLdpSessionEntry 3 }

rcMplsLdpSessionStateLastChange OBJECT-TYPE
        SYNTAX        Unsigned32
        MAX-ACCESS    read-only
        STATUS        current
        DESCRIPTION   "The time this Session entered its current state
                      as denoted by the rcMplsLdpSessionState object." 
    ::= { rcMplsLdpSessionEntry 4 }

rcMplsLdpSessionState OBJECT-TYPE
        SYNTAX      INTEGER {
                        nonexistent(1),
                        initialized(2),
                        openrec(3),
                        opensent(4),
                        operational(5)
                      }       
        MAX-ACCESS    read-only
        STATUS        current
        DESCRIPTION   "The current state of the session, all of the
             states 1 to 5 are based on the state machine
             for session negotiation behavior 
             1- nonexistent, 2- initialized, 3- openrec, 4- opensent, 5- operational. "  
        REFERENCE
             "RFC3036, LDP Specification, Section 2.5.4,
             Initialization State Machine."
    ::= { rcMplsLdpSessionEntry 5 }

rcMplsLdpSessionRole OBJECT-TYPE
        SYNTAX      INTEGER {
                        unknown(1),
                        active(2),
                        passive(3)
                     } 
        MAX-ACCESS    read-only
        STATUS        current
        DESCRIPTION   "During session establishment the LSR/LER takes either
             the active role or the passive role based on address
             comparisons.  This object indicates whether this LSR/LER
             was behaving in an active role or passive role during
             this session's establishment, 1- unknown, 2- active, 3- passive.
             The value of unknown(1), indicates that the role is not
             able to be determined at the present time." 
         REFERENCE
             "RFC3036, LDP Specification, Section 2.5.3.,
             Session Initialization."
    ::= { rcMplsLdpSessionEntry 6 }

rcMplsLdpSessionProtocolVersion OBJECT-TYPE
        SYNTAX        Unsigned32
        MAX-ACCESS    read-only
        STATUS        current
        DESCRIPTION   "This is the protocol version." 
    ::= { rcMplsLdpSessionEntry 7 }

rcMplsLdpSessionKeepAliveHoldTimeRem OBJECT-TYPE
        SYNTAX        Integer32
        MAX-ACCESS    read-only
        STATUS        current
        DESCRIPTION   "This is the session keep alive hold time remaining." 
    ::= { rcMplsLdpSessionEntry 8 }

rcMplsLdpSessionKeepAliveTime OBJECT-TYPE
        SYNTAX        Unsigned32
        MAX-ACCESS    read-only
        STATUS        current
        DESCRIPTION   "This is the session keep alive time." 
    ::= { rcMplsLdpSessionEntry 9 }

rcMplsLdpSessionMaxPduLength OBJECT-TYPE
        SYNTAX        Unsigned32
        MAX-ACCESS    read-only
        STATUS        current
        DESCRIPTION   "This is the session's max pdu length." 
    ::= { rcMplsLdpSessionEntry 10 }

rcMplsLdpSessionDiscontinuityTime OBJECT-TYPE
        SYNTAX        Integer32
        MAX-ACCESS    read-only
        STATUS        current
        DESCRIPTION   "This is the session's discontinuity time." 
    ::= { rcMplsLdpSessionEntry 11 }

rcMplsLdpSessionHoldTime OBJECT-TYPE
        SYNTAX        Unsigned32
        MAX-ACCESS    read-only
        STATUS        current
        DESCRIPTION   "This is the session's hold time." 
    ::= { rcMplsLdpSessionEntry 12 }

rcMplsLdpSessionUpTime OBJECT-TYPE
        SYNTAX        Integer32
        MAX-ACCESS    read-only
        STATUS        current
        DESCRIPTION   "This is the session's up time." 
    ::= { rcMplsLdpSessionEntry 13 }

rcMplsLdpSessionMessagesSent OBJECT-TYPE
        SYNTAX        Counter32
        MAX-ACCESS    read-only
        STATUS        current
        DESCRIPTION   "This is the session total messages sent."
    ::= { rcMplsLdpSessionEntry 14 }

rcMplsLdpSessionMessagesRecv OBJECT-TYPE
        SYNTAX        Counter32
        MAX-ACCESS    read-only
        STATUS        current
        DESCRIPTION   "This is the session total messages received."
    ::= { rcMplsLdpSessionEntry 15 }

-- For 'show mpls ldp interface' command 
rcMplsLdpInterfaceTable OBJECT-TYPE
        SYNTAX          SEQUENCE OF RcMplsLdpInterfaceEntry
        MAX-ACCESS      not-accessible
        STATUS          current
        DESCRIPTION     "This is the table of mpls ldp interface."
    ::= { rcMplsLdpGroup 7 }

rcMplsLdpInterfaceEntry OBJECT-TYPE
        SYNTAX          RcMplsLdpInterfaceEntry
        MAX-ACCESS      not-accessible
        STATUS          current
        DESCRIPTION     "An entry in the mpls ldp interface table."
        INDEX   { rcMplsLdpInterfaceIfIndex }
    ::= { rcMplsLdpInterfaceTable 1 }

RcMplsLdpInterfaceEntry ::=
        SEQUENCE {
                rcMplsLdpInterfaceIfIndex           InterfaceIndex,
                rcMplsLdpInterfaceNbrCount          Unsigned32,
                rcMplsLdpInterfaceNextHello         Unsigned32,
                rcMplsLdpInterfaceConfHoldTime      Unsigned32,
                rcMplsLdpInterfaceNegHoldTime       Unsigned32,
                rcMplsLdpInterfaceHelloInterval     Unsigned32
         }

rcMplsLdpInterfaceIfIndex OBJECT-TYPE
        SYNTAX        InterfaceIndex
        MAX-ACCESS    not-accessible
        STATUS        current
        DESCRIPTION   "This is the LDP interface if index." 
    ::= { rcMplsLdpInterfaceEntry 1 }

rcMplsLdpInterfaceNbrCount OBJECT-TYPE
        SYNTAX        Unsigned32
        MAX-ACCESS    read-only 
        STATUS        current
        DESCRIPTION   "This is the number of neighbors." 
    ::= { rcMplsLdpInterfaceEntry 2 }

rcMplsLdpInterfaceNextHello OBJECT-TYPE
        SYNTAX        Unsigned32
        MAX-ACCESS    read-only 
        STATUS        current
        DESCRIPTION   "This is the next hello time." 
    ::= { rcMplsLdpInterfaceEntry 3 }

rcMplsLdpInterfaceConfHoldTime OBJECT-TYPE
        SYNTAX        Unsigned32
        MAX-ACCESS    read-only 
        STATUS        current
        DESCRIPTION   "This is the configured hello hold time." 
    ::= { rcMplsLdpInterfaceEntry 4 }

rcMplsLdpInterfaceNegHoldTime OBJECT-TYPE
        SYNTAX        Unsigned32
        MAX-ACCESS    read-only 
        STATUS        current
        DESCRIPTION   "This is the negotiated hello hold time." 
    ::= { rcMplsLdpInterfaceEntry 5 }

rcMplsLdpInterfaceHelloInterval OBJECT-TYPE
	SYNTAX        Unsigned32
	MAX-ACCESS    read-only
	STATUS        current
	DESCRIPTION   "This is one third of the negotiated hello hold time."
    ::= { rcMplsLdpInterfaceEntry 6 }

-- For 'show mpls ldp statistics' command
rcMplsLdpStatsTable OBJECT-TYPE
        SYNTAX          SEQUENCE OF RcMplsLdpStatsEntry
        MAX-ACCESS      not-accessible
        STATUS          current
        DESCRIPTION     "This is the table of mpls ldp statistics."
    ::= { rcMplsLdpGroup 8 }

rcMplsLdpStatsEntry OBJECT-TYPE
        SYNTAX          RcMplsLdpStatsEntry
        MAX-ACCESS      not-accessible
        STATUS          current
        DESCRIPTION     "An entry in the mpls ldp statistics table."
        INDEX          { rcMplsLdpStatsPeerAddress }
    ::= { rcMplsLdpStatsTable 1 }

RcMplsLdpStatsEntry ::=
        SEQUENCE {
             rcMplsLdpStatsPeerAddress                         IpAddress,
             rcMplsLdpStatsNotifyRecv                          Counter32,
             rcMplsLdpStatsNotifySent                          Counter32,
             rcMplsLdpStatsHelloRecv                           Counter32,
             rcMplsLdpStatsHelloSent                           Counter32,
             rcMplsLdpStatsInitRecv                            Counter32,
             rcMplsLdpStatsInitSent                            Counter32,
             rcMplsLdpStatsKeepRecv                            Counter32,
             rcMplsLdpStatsKeepSent                            Counter32,
             rcMplsLdpStatsAddrRecv                            Counter32,
             rcMplsLdpStatsAddrSent                            Counter32,
             rcMplsLdpStatsAddrWdrRecv                         Counter32,
             rcMplsLdpStatsAddrWdrSent                         Counter32,
             rcMplsLdpStatsLabelMapRecv                        Counter32,
             rcMplsLdpStatsLabelMapSent                        Counter32,
             rcMplsLdpStatsLabelReqRecv                        Counter32,
             rcMplsLdpStatsLabelReqSent                        Counter32,
             rcMplsLdpStatsLabelWdrRecv                        Counter32,
             rcMplsLdpStatsLabelWdrSent                        Counter32,
             rcMplsLdpStatsLabelRelRecv                        Counter32,
             rcMplsLdpStatsLabelRelSent                        Counter32,
             rcMplsLdpStatsLabelAbrRecv                        Counter32,
             rcMplsLdpStatsLabelAbrSent                        Counter32,
             rcMplsLdpStatsSessionUp                           Counter32,
             rcMplsLdpStatsSessionDown                         Counter32,
             rcMplsLdpStatsBadLdpIdentifierErrors              Counter32,
             rcMplsLdpStatsBadPduLengthErrors                  Counter32,
             rcMplsLdpStatsBadMessageLengthErrors              Counter32,
             rcMplsLdpStatsUnknownMessageErrors                Counter32,
             rcMplsLdpStatsUnknownTlvErrors                    Counter32,
             rcMplsLdpStatsBadTlvLengthErrors                  Counter32,
             rcMplsLdpStatsMalformedTlvValueErrors             Counter32,
             rcMplsLdpStatsHoldTimerExpErrors                  Counter32,
             rcMplsLdpStatsSessionRejectedNoHelloErrors        Counter32,
             rcMplsLdpStatsSessionRejectedBadParmAdvErrors     Counter32,
             rcMplsLdpStatsSessionRejectedMaxPduErrors         Counter32,
             rcMplsLdpStatsSessionRejectedBadLabelRangeErrors  Counter32,
             rcMplsLdpStatsSessionRejectedSetupAbortErrors     Counter32,
             rcMplsLdpStatsSessionRejectedBadKeepaliveErrors   Counter32,
             rcMplsLdpStatsSessionOtherErrors                  Counter32
     }

rcMplsLdpStatsPeerAddress OBJECT-TYPE
        SYNTAX        IpAddress
        MAX-ACCESS    not-accessible
        STATUS        current
        DESCRIPTION   "This is the LDP Peer Address key for search.  This value
                       can be a valid peer address or 0.0.0.0.  If 0.0.0.0 
                       then global LDP statistics are retrieved." 
    ::= { rcMplsLdpStatsEntry 1 }

rcMplsLdpStatsNotifyRecv OBJECT-TYPE
        SYNTAX        Counter32
        MAX-ACCESS    read-only
        STATUS        current
        DESCRIPTION   "This is the count of notifications received."
    ::= { rcMplsLdpStatsEntry 2 }

rcMplsLdpStatsNotifySent OBJECT-TYPE
        SYNTAX        Counter32
        MAX-ACCESS    read-only
        STATUS        current
        DESCRIPTION   "This is the count of notifications sent."
    ::= { rcMplsLdpStatsEntry 3 }

rcMplsLdpStatsHelloRecv OBJECT-TYPE
        SYNTAX        Counter32
        MAX-ACCESS    read-only
        STATUS        current
        DESCRIPTION   "This is the count of hellos received."
    ::= { rcMplsLdpStatsEntry 4 }

rcMplsLdpStatsHelloSent OBJECT-TYPE
        SYNTAX        Counter32
        MAX-ACCESS    read-only
        STATUS        current
        DESCRIPTION   "This is the count of hellos sent."
    ::= { rcMplsLdpStatsEntry 5 }

rcMplsLdpStatsInitRecv OBJECT-TYPE
        SYNTAX        Counter32
        MAX-ACCESS    read-only
        STATUS        current
        DESCRIPTION   "This is the count of initializations received."
    ::= { rcMplsLdpStatsEntry 6 }

rcMplsLdpStatsInitSent OBJECT-TYPE
        SYNTAX        Counter32
        MAX-ACCESS    read-only
        STATUS        current
        DESCRIPTION   "This is the count of initializations sent."
    ::= { rcMplsLdpStatsEntry 7 }

rcMplsLdpStatsKeepRecv OBJECT-TYPE
        SYNTAX        Counter32
        MAX-ACCESS    read-only
        STATUS        current
        DESCRIPTION   "This is the count of keep alives received."
    ::= { rcMplsLdpStatsEntry 8 }

rcMplsLdpStatsKeepSent OBJECT-TYPE
        SYNTAX        Counter32
        MAX-ACCESS    read-only
        STATUS        current
        DESCRIPTION   "This is the count of keep alives sent."
    ::= { rcMplsLdpStatsEntry 9 }

rcMplsLdpStatsAddrRecv OBJECT-TYPE
        SYNTAX        Counter32
        MAX-ACCESS    read-only
        STATUS        current
        DESCRIPTION   "This is the count of addrs received."
    ::= { rcMplsLdpStatsEntry 10 }

rcMplsLdpStatsAddrSent OBJECT-TYPE
        SYNTAX        Counter32
        MAX-ACCESS    read-only
        STATUS        current
        DESCRIPTION   "This is the count of addrs sent."
    ::= { rcMplsLdpStatsEntry 11 }

rcMplsLdpStatsAddrWdrRecv OBJECT-TYPE
        SYNTAX        Counter32
        MAX-ACCESS    read-only
        STATUS        current
        DESCRIPTION   "This is the count of addr withdraws received."
    ::= { rcMplsLdpStatsEntry 12 }

rcMplsLdpStatsAddrWdrSent OBJECT-TYPE
        SYNTAX        Counter32
        MAX-ACCESS    read-only
        STATUS        current
        DESCRIPTION   "This is the count of addr withdraws sent."
    ::= { rcMplsLdpStatsEntry 13 }

rcMplsLdpStatsLabelMapRecv OBJECT-TYPE
        SYNTAX        Counter32
        MAX-ACCESS    read-only
        STATUS        current
        DESCRIPTION   "This is the count of label maps received."
    ::= { rcMplsLdpStatsEntry 14 }

rcMplsLdpStatsLabelMapSent OBJECT-TYPE
        SYNTAX        Counter32
        MAX-ACCESS    read-only
        STATUS        current
        DESCRIPTION   "This is the count of label maps sent."
    ::= { rcMplsLdpStatsEntry 15 }

rcMplsLdpStatsLabelReqRecv OBJECT-TYPE
        SYNTAX        Counter32
        MAX-ACCESS    read-only
        STATUS        current
        DESCRIPTION   "This is the count of label reqs received."
    ::= { rcMplsLdpStatsEntry 16 }

rcMplsLdpStatsLabelReqSent OBJECT-TYPE
        SYNTAX        Counter32
        MAX-ACCESS    read-only
        STATUS        current
        DESCRIPTION   "This is the count of label reqs sent."
    ::= { rcMplsLdpStatsEntry 17 }

rcMplsLdpStatsLabelWdrRecv OBJECT-TYPE
        SYNTAX        Counter32
        MAX-ACCESS    read-only
        STATUS        current
        DESCRIPTION   "This is the count of label withdraws received."
    ::= { rcMplsLdpStatsEntry 18 }

rcMplsLdpStatsLabelWdrSent OBJECT-TYPE
        SYNTAX        Counter32
        MAX-ACCESS    read-only
        STATUS        current
        DESCRIPTION   "This is the count of label withdraws sent."
    ::= { rcMplsLdpStatsEntry 19 }

rcMplsLdpStatsLabelRelRecv OBJECT-TYPE
        SYNTAX        Counter32
        MAX-ACCESS    read-only
        STATUS        current
        DESCRIPTION   "This is the count of label withdraws received."
    ::= { rcMplsLdpStatsEntry 20 }

rcMplsLdpStatsLabelRelSent OBJECT-TYPE
        SYNTAX        Counter32
        MAX-ACCESS    read-only
        STATUS        current
        DESCRIPTION   "This is the count of label withdraws sent."
    ::= { rcMplsLdpStatsEntry 21 }

rcMplsLdpStatsLabelAbrRecv OBJECT-TYPE
        SYNTAX        Counter32
        MAX-ACCESS    read-only
        STATUS        current
        DESCRIPTION   "This is the count of label aborts received."
    ::= { rcMplsLdpStatsEntry 22 }

rcMplsLdpStatsLabelAbrSent OBJECT-TYPE
        SYNTAX        Counter32
        MAX-ACCESS    read-only
        STATUS        current
        DESCRIPTION   "This is the count of label aborts sent."
    ::= { rcMplsLdpStatsEntry 23 }

rcMplsLdpStatsSessionUp OBJECT-TYPE
        SYNTAX        Counter32
        MAX-ACCESS    read-only
        STATUS        current
        DESCRIPTION   "This is the count of session up."
    ::= { rcMplsLdpStatsEntry 24 }

rcMplsLdpStatsSessionDown OBJECT-TYPE
        SYNTAX        Counter32
        MAX-ACCESS    read-only
        STATUS        current
        DESCRIPTION   "This is the count of session down."
    ::= { rcMplsLdpStatsEntry 25 }

rcMplsLdpStatsBadLdpIdentifierErrors OBJECT-TYPE
        SYNTAX        Counter32
        MAX-ACCESS    read-only
        STATUS        current
        DESCRIPTION   "This is the count of bad LDP ID errors."
    ::= { rcMplsLdpStatsEntry 26 }

rcMplsLdpStatsBadPduLengthErrors OBJECT-TYPE
        SYNTAX        Counter32
        MAX-ACCESS    read-only
        STATUS        current
        DESCRIPTION   "This is the count of Bad PDU length
                       errors." 
    ::= { rcMplsLdpStatsEntry 27 }

rcMplsLdpStatsBadMessageLengthErrors OBJECT-TYPE
        SYNTAX        Counter32
        MAX-ACCESS    read-only
        STATUS        current
        DESCRIPTION   "This is the count of bad message length
                       errors."
    ::= { rcMplsLdpStatsEntry 28 }

rcMplsLdpStatsUnknownMessageErrors OBJECT-TYPE
        SYNTAX        Counter32
        MAX-ACCESS    read-only
        STATUS        current
        DESCRIPTION   "This is the count of unknown message
                       errors."
    ::= { rcMplsLdpStatsEntry 29 }

rcMplsLdpStatsUnknownTlvErrors OBJECT-TYPE
        SYNTAX        Counter32
        MAX-ACCESS    read-only
        STATUS        current
        DESCRIPTION   "This is the count of unknown TLV errors."
    ::= { rcMplsLdpStatsEntry 30 }

rcMplsLdpStatsBadTlvLengthErrors OBJECT-TYPE
        SYNTAX        Counter32
        MAX-ACCESS    read-only
        STATUS        current
        DESCRIPTION   "This is the count of bad TLV Length errors."
    ::= { rcMplsLdpStatsEntry 31 }

rcMplsLdpStatsMalformedTlvValueErrors OBJECT-TYPE
        SYNTAX        Counter32
        MAX-ACCESS    read-only
        STATUS        current
        DESCRIPTION   "This is the count of Malinformed TLV
                       value errors." 
    ::= { rcMplsLdpStatsEntry 32 }

rcMplsLdpStatsHoldTimerExpErrors OBJECT-TYPE
        SYNTAX        Counter32
        MAX-ACCESS    read-only
        STATUS        current
        DESCRIPTION   "This is the count of hold time 
                       expired errors."
    ::= { rcMplsLdpStatsEntry 33 }

rcMplsLdpStatsSessionRejectedNoHelloErrors OBJECT-TYPE
        SYNTAX        Counter32
        MAX-ACCESS    read-only
        STATUS        current
        DESCRIPTION   "This is the count of session reject -
                       no hello errors."
    ::= { rcMplsLdpStatsEntry 34 }

rcMplsLdpStatsSessionRejectedBadParmAdvErrors OBJECT-TYPE
        SYNTAX        Counter32
        MAX-ACCESS    read-only
        STATUS        current
        DESCRIPTION   "This is the count of session reject -
                       bad parameter advertisement errors."
    ::= { rcMplsLdpStatsEntry 35 }

rcMplsLdpStatsSessionRejectedMaxPduErrors OBJECT-TYPE
        SYNTAX        Counter32
        MAX-ACCESS    read-only
        STATUS        current
        DESCRIPTION   "This is the count of session reject -
                       Max PDU Errors."
    ::= { rcMplsLdpStatsEntry 36 }

rcMplsLdpStatsSessionRejectedBadLabelRangeErrors OBJECT-TYPE
        SYNTAX        Counter32
        MAX-ACCESS    read-only
        STATUS        current
        DESCRIPTION   "This is the count of session reject -
                       Bad Label Range errors." 
    ::= { rcMplsLdpStatsEntry 37 }

rcMplsLdpStatsSessionRejectedSetupAbortErrors OBJECT-TYPE
        SYNTAX        Counter32
        MAX-ACCESS    read-only
        STATUS        current
        DESCRIPTION   "This is the count of session reject -
                       Setup Abort errors." 
    ::= { rcMplsLdpStatsEntry 38 }

rcMplsLdpStatsSessionRejectedBadKeepaliveErrors OBJECT-TYPE
        SYNTAX        Counter32
        MAX-ACCESS    read-only
        STATUS        current
        DESCRIPTION   "This is the count of session reject -
                       Bad Keepalive Errors."
    ::= { rcMplsLdpStatsEntry 39 }

rcMplsLdpStatsSessionOtherErrors OBJECT-TYPE
        SYNTAX        Counter32
        MAX-ACCESS    read-only
        STATUS        current
        DESCRIPTION   "This is the count of other errors."
    ::= { rcMplsLdpStatsEntry 40 }

-- Notification Objects group within the MPLS MIB
--
-- MPLS LDP Trap Enable/Disable Flags
--
rcMplsLdpStatusNotificationEnable OBJECT-TYPE
        SYNTAX        TruthValue
        MAX-ACCESS    read-write
        STATUS        current
        DESCRIPTION   "If this object is true, then it enables the
                      generation of LDP Session Up or Down Traps,
                      otherwise these traps are not emitted."
        DEFVAL        { false }
        ::= { rcMplsNotificationObjects 1 }

rcMplsLdpSessionThresholdNotificationEnable OBJECT-TYPE
        SYNTAX        TruthValue
        MAX-ACCESS    read-write
        STATUS        current
        DESCRIPTION   "If this object is true, then it enables the
                      generation of LDP Session Threshold Exceeded Traps,
                      otherwise these traps are not emitted."
        DEFVAL        { false }
        ::= { rcMplsNotificationObjects 2 }

rcMplsLdpPathVectorLimitNotificationEnable OBJECT-TYPE
        SYNTAX        TruthValue
        MAX-ACCESS    read-write
        STATUS        current
        DESCRIPTION   "If this object is true, then it enables the
                      generation of LDP Path Vector Limit Exceeded Traps,
                      otherwise these traps are not emitted."
        DEFVAL        { false }
        ::= { rcMplsNotificationObjects 3 }

-- This MIB defines the serial information that can be read from
-- SFPs and SFPs including the vendor specific Nortel supplied data.
-- The INF-8074i SFP MSA and the SFF-8053 SFP specifications defined
-- the first 256 bytes of serial ID information.  The SFF-8472
-- standard adds new options to those previously defined and adds
-- new transceiver types.  The SFF-8472 standard also defines an
-- enhanced digital diagnostic monitoring interface for optical
-- devices which allows real-time access to device operating
-- parameters.
--
-- If the target device supports the SFF-8472 standard, there is an
-- extra 256 bit address space.  Pertinant information from that
-- space is also described here.
-- TXT about XFPs 


rcPlugOptModTable OBJECT-TYPE
        SYNTAX	  SEQUENCE OF RcPlugOptModEntry
        MAX-ACCESS  not-accessible
        STATUS      current
        DESCRIPTION "Gibc SFF diagnostic info table"
        ::= {  rcPlugOptMod 1 }

rcPlugOptModEntry OBJECT-TYPE
        SYNTAX      RcPlugOptModEntry
        MAX-ACCESS  not-accessible
        STATUS      current
        DESCRIPTION "Entry containing info. for a particular port"
        INDEX         { rcPlugOptModPortIndex }
	::= { rcPlugOptModTable 1 }
  
RcPlugOptModEntry ::= SEQUENCE {
    rcPlugOptModPortIndex                 InterfaceIndex,          -- 1

-- Control information:

    rcPlugOptModDdmStatusMask             BITS,                    -- 2
    rcPlugOptModCalibration               INTEGER,                 -- 3
    rcPlugOptModPowerMeasure              INTEGER,                 -- 4
    rcPlugOptModConnectorType             DisplayString(SIZE(17)), -- 5 ; 16+1
    rcPlugOptModVendorName                DisplayString(SIZE(17)), -- 6 ; 16+1
    rcPlugOptModVendorPartNumber          DisplayString(SIZE(17)), -- 7 ; 16+1
    rcPlugOptModVendorRevNumber           DisplayString(SIZE(5)),  -- 8 ;  4+1
    rcPlugOptModVendorSN                  DisplayString(SIZE(17)), -- 9 ; 16+1
    rcPlugOptModVendorDateCode            DisplayString(SIZE(9)),  -- 10;  8+1
 
-- Vendor information:

    rcPlugOptModPEC                       DisplayString(SIZE(17)), -- 11 ;16+1
    rcPlugOptModCLEI                      DisplayString(SIZE(11)), -- 12 ;10+1
    rcPlugOptModSupportsDDM               TruthValue,              -- 13
    rcPlugOptModAux1Monitoring            INTEGER,                 -- 14
    rcPlugOptModAux2Monitoring            INTEGER,                 -- 15
    rcPlugOptModWaveLength                Integer32,               -- 16

-- The DDM information:

    rcPlugOptModTemperature                   INTEGER,             -- 17
    rcPlugOptModTemperatureHighAlarmThreshold  INTEGER,            -- 18
    rcPlugOptModTemperatureLowAlarmThreshold   INTEGER,            -- 19
    rcPlugOptModTemperatureHighWarningThreshold INTEGER,           -- 20
    rcPlugOptModTemperatureLowWarningThreshold INTEGER,            -- 21
    rcPlugOptModVoltage                       INTEGER,             -- 22
    rcPlugOptModVoltageHighAlarmThreshold     INTEGER,             -- 23
    rcPlugOptModVoltageLowAlarmThreshold      INTEGER,             -- 24
    rcPlugOptModVoltageHighWarningThreshold   INTEGER,             -- 25
    rcPlugOptModVoltageLowWarningThreshold    INTEGER,             -- 26
    rcPlugOptModBias                          INTEGER,             -- 27
    rcPlugOptModBiasHighAlarmThreshold        INTEGER,             -- 28
    rcPlugOptModBiasLowAlarmThreshold         INTEGER,             -- 29
    rcPlugOptModBiasHighWarningThreshold      INTEGER,             -- 30
    rcPlugOptModBiasLowWarningThreshold       INTEGER,             -- 31
    rcPlugOptModTxPower                       INTEGER,             -- 32
    rcPlugOptModTxPowerHighAlarmThreshold     INTEGER,             -- 33
    rcPlugOptModTxPowerLowAlarmThreshold      INTEGER,             -- 34
    rcPlugOptModTxPowerHighWarningThreshold   INTEGER,             -- 35
    rcPlugOptModTxPowerLowWarningThreshold    INTEGER,             -- 36
    rcPlugOptModRxPower                       INTEGER,             -- 37
    rcPlugOptModRxPowerHighAlarmThreshold     INTEGER,             -- 38
    rcPlugOptModRxPowerLowAlarmThreshold      INTEGER,             -- 39
    rcPlugOptModRxPowerHighWarningThreshold   INTEGER,             -- 40
    rcPlugOptModRxPowerLowWarningThreshold    INTEGER,             -- 41
    rcPlugOptModAux1                          INTEGER,             -- 42
    rcPlugOptModAux1HighAlarmThreshold        INTEGER,             -- 43
    rcPlugOptModAux1LowAlarmThreshold         INTEGER,             -- 44
    rcPlugOptModAux1HighWarningThreshold      INTEGER,             -- 45
    rcPlugOptModAux1LowWarningThreshold       INTEGER,             -- 46
    rcPlugOptModAux2                          INTEGER,             -- 47
    rcPlugOptModAux2HighAlarmThreshold        INTEGER,             -- 48
    rcPlugOptModAux2LowAlarmThreshold         INTEGER,             -- 49
    rcPlugOptModAux2HighWarningThreshold      INTEGER,             -- 50
    rcPlugOptModAux2LowWarningThreshold       INTEGER,             -- 51

    rcPlugOptModTemperatureStatus         INTEGER,                 -- 52
    rcPlugOptModVoltageStatus             INTEGER,                 -- 53
    rcPlugOptModBiasStatus                INTEGER,                 -- 54
    rcPlugOptModTxPowerStatus             INTEGER,                 -- 55
    rcPlugOptModRxPowerStatus             INTEGER,                 -- 56
    rcPlugOptModAux1Status                INTEGER,                 -- 57
    rcPlugOptModAux2Status                INTEGER                  -- 58
    }
    
rcPlugOptModPortIndex OBJECT-TYPE
        SYNTAX      InterfaceIndex
        MAX-ACCESS  read-only
        STATUS      current
        DESCRIPTION "An index value that uniquely identifies a port on a 
                     blade or line-card."
        ::= { rcPlugOptModEntry 1 }

rcPlugOptModDdmStatusMask OBJECT-TYPE
        SYNTAX      BITS {
                        ddm-ok(0),
                        ddm-checksum-error(1),
                        ddm-i2c-read-error(2),
                        ddm-threshold-error(3),
                        ddm-calibration-error(4)
                    }
        MAX-ACCESS  read-only
        STATUS      current
        DESCRIPTION "Each bit other than ddm-ok represents a specific error. 
                     Any combination of error bits is allowed."
        ::= { rcPlugOptModEntry 2}

rcPlugOptModCalibration OBJECT-TYPE
        SYNTAX      INTEGER {
                        internal    (1),
                        external    (2)
                    }
        MAX-ACCESS  read-only
        STATUS      current
        DESCRIPTION "The identifier value indicates type of calibration."
        ::= { rcPlugOptModEntry 3}

rcPlugOptModPowerMeasure OBJECT-TYPE
        SYNTAX      INTEGER {
                        omi        (1),
                        average    (2)
                    }
        MAX-ACCESS  read-only
        STATUS      current
        DESCRIPTION "The identifier value indicates type of external power."
        ::= { rcPlugOptModEntry 4}

rcPlugOptModConnectorType OBJECT-TYPE
        SYNTAX      DisplayString(SIZE(17))
        MAX-ACCESS  read-only
        STATUS      current
        DESCRIPTION "The connector type is a 16 character field that
                     contains ASCII characters, left-aligned and padded
                     on the right with ASCII spaces. This is an assigned
                     name that indicates some characteristic of the 
                     layer-1 interface."
        ::= { rcPlugOptModEntry 5 }

rcPlugOptModVendorName OBJECT-TYPE
        SYNTAX      DisplayString(SIZE(17))
        MAX-ACCESS  read-only
        STATUS      current
        DESCRIPTION "The vendor name is a 16 character field that
                     contains ASCII characters, left-aligned and padded
                     on the right with ASCII spaces. The vendor name
                     shall be the full name of the corporation, a
                     commonly accepted abbreviation of the name, the
                     SCSI company code, or the stock exchange code for
                     the corporation."
        ::= { rcPlugOptModEntry 6 }
	
rcPlugOptModVendorPartNumber OBJECT-TYPE
        SYNTAX      DisplayString(SIZE(17))
        MAX-ACCESS  read-only
        STATUS      current
        DESCRIPTION "The vendor part number is a 16 byte field that
                     contains ASCII characters, left-aligned and padded
                     on the right with ASCII spaces, defining the vendor
                     part number or product name."
        ::= { rcPlugOptModEntry 7 }

rcPlugOptModVendorRevNumber OBJECT-TYPE
        SYNTAX      DisplayString(SIZE(5))
        MAX-ACCESS  read-only
        STATUS      current
        DESCRIPTION "The vendor revision number is a 4-byte field that
                     contains ASCII characters, left-aligned and padded
                     on the right with ASCII spaces, defining the
                     vendor product revision number."
        ::= { rcPlugOptModEntry 8 }

rcPlugOptModVendorSN OBJECT-TYPE
        SYNTAX      DisplayString(SIZE(17))
        MAX-ACCESS  read-only
        STATUS      current
        DESCRIPTION "The vendor serial number is a 16 character field
                     that contains ASCII characters, left-aligned and
                     padded on the right with ASCII spaces, defining
                     the vendor serial number for the transceiver."
        ::= { rcPlugOptModEntry 9 }

rcPlugOptModVendorDateCode OBJECT-TYPE
        SYNTAX      DisplayString(SIZE(9)) 
        MAX-ACCESS  read-only
        STATUS      current
        DESCRIPTION "The date code is an 8-byte field that contains the
                     vendor's date code in ASCII. This field is
                     mandatory and takes the form: YYMMDDLC where
                     YY is the 2 low order digits of the year (00=2000),
                     MM is the month, 01 thru 12,
                     DD is the day, 01 thru 31, and
                     LC is an optional vendor specific lot code."
        ::= { rcPlugOptModEntry 10 }

rcPlugOptModPEC OBJECT-TYPE
        SYNTAX      DisplayString(SIZE(17))
        MAX-ACCESS  read-only
        STATUS      current
        DESCRIPTION "This is a 16 byte left-justified ASCII field that
                     records the Nortel Product Equipment Code order
                     number for the module. Nortel part numbers are 9
                     bytes long, so the 10th through 16th byte should
                     be NULL."
        ::= { rcPlugOptModEntry 11 }

rcPlugOptModCLEI OBJECT-TYPE
        SYNTAX      DisplayString(SIZE(11))
        MAX-ACCESS  read-only
        STATUS      current
        DESCRIPTION "This is a 10 byte left-justified ASCII field that
                     records the Nortel supplied Common Language
                     Equipment Identifier code for the device. The CLEI
                     code is a Telcordia human-readable representation
                     of the 1D barcode."
        ::= { rcPlugOptModEntry 12 }
 
rcPlugOptModSupportsDDM OBJECT-TYPE
        SYNTAX      TruthValue
        MAX-ACCESS  read-only
        STATUS      current
        DESCRIPTION "This boolean indicates whether or not the device
                     supports the DDM capability."
        ::= { rcPlugOptModEntry 13 }
	
rcPlugOptModAux1Monitoring OBJECT-TYPE
        SYNTAX      INTEGER
        MAX-ACCESS  read-only
        STATUS      current
        DESCRIPTION "This value tells what Aux1 is measuring.The values are
                     as follows:
        
                     0  Auxiliary monitoring not implemented
                     1  APD Bias Voltage mV (units of 10 mV)
                     2  Reserved
                     3  TEC Current (mA)
                     4  Laser Temperature
                     5  Laser Wavelength
                     6  +5V Supply Voltage
                     7  +3.3V Supply Voltage
                     8  +1.8V Supply Voltage
                     9  -5.2V Supply Voltage
                    10  +5.0V Supply Current (unit of 100 uA)
                    13  +3.3V Supply Current (unit of 100 uA)
                    14  +1.8V Supply Current (unit of 100 uA)
                    15  -5.2V Supply Current (unit of 100 uA)
                     "
        ::= { rcPlugOptModEntry 14 } 
        
rcPlugOptModAux2Monitoring OBJECT-TYPE
        SYNTAX      INTEGER
        MAX-ACCESS  read-only
        STATUS      current
        DESCRIPTION "This value tells you what AUX2 is measuring.The values are
                     as follows:
        
                     0  Auxiliary monitoring not implemented
                     1  APD Bias Voltage mV (units of 10 mV)
                     2  Reserved
                     3  TEC Current (mA)
                     4  Laser Temperature
                     5  Laser Wavelength
                     6  +5V Supply Voltage
                     7  +3.3V Supply Voltage
                     8  +1.8V Supply Voltage
                     9  -5.2V Supply Voltage
                    10  +5.0V Supply Current (unit of 100 uA)
                    13  +3.3V Supply Current (unit of 100 uA)
                    14  +1.8V Supply Current (unit of 100 uA)
                    15  -5.2V Supply Current (unit of 100 uA)
                     "
        ::= { rcPlugOptModEntry 15 } 

rcPlugOptModWaveLength OBJECT-TYPE
        SYNTAX      Integer32 (0..65535)
        MAX-ACCESS  read-only
        STATUS      current
        DESCRIPTION "Nominal transmitter output wavelength at room
                     temperature. It is expressed in nano-meters."
        ::= {rcPlugOptModEntry 16 }


-- These next variables represent either measured values or fixed
-- threshold values.  Sometimes they involve an integer and a fractional
-- component and sometimes we may want to convert from mW to dBm.
-- So maybe what we have in the MIB definition is not the raw numeric
-- data but rather the ASCII representation of that data including a
-- minus sign, if necessary, and a decimal point in the right place.
-- In all cases, we need to display the calibrated data if external
-- calibration is being used.  For temperature, voltage, bias current
-- and transmitter power, this involves multiplying the raw value by
-- a vendor specified slope constant (contained in the device EEPROM)
-- then adding a vendor specified offset (also contained in the device
-- EEPROM).  For received power, it involves running the raw value
-- through a polynomial. The vendor specified coefficients for that
-- polynomial are contained in the device in IEEE 754 floating-point
-- format.

rcPlugOptModTemperature OBJECT-TYPE
        SYNTAX      INTEGER
        MAX-ACCESS  read-only
        STATUS      current
        DESCRIPTION "This value represents the internally measured
                     module temperature. It is expressed in units of
                     1/256 of a degree Celsius and can range from -40C
		     to +125C with 0.0001 accuracy.The most significant byte is
                     the signed integer part of the number and the
                     least significant byte is the fraction."
        ::= { rcPlugOptModEntry 17 }

rcPlugOptModTemperatureHighAlarmThreshold OBJECT-TYPE
        SYNTAX      INTEGER
        MAX-ACCESS  read-only
        STATUS      current
        DESCRIPTION "This value represents the vendor specified high
                     temperature threshold. If the device
                     temperature exceeds this value, a temperature high
                     is asserted. It is expressed in the same
                     units as the measured temperature."
        ::= { rcPlugOptModEntry 18 }

rcPlugOptModTemperatureLowAlarmThreshold OBJECT-TYPE
        SYNTAX      INTEGER
        MAX-ACCESS  read-only
        STATUS      current
        DESCRIPTION "This value represents the vendor specified low
                     temperature threshold. If the device
                     temperature falls below this value, a temperature
                     low is asserted. It is expressed in the same
                     units as the measured temperature."
        ::= { rcPlugOptModEntry 19 }

rcPlugOptModTemperatureHighWarningThreshold OBJECT-TYPE
        SYNTAX      INTEGER
        MAX-ACCESS  read-only
        STATUS      current
        DESCRIPTION "This value represents the vendor specified high
                     temperature warning threshold. If the device
                     temperature exceeds this value, a temperature high
                     warning is asserted. It is expressed in the same
                     units as the measured temperature."
        ::= { rcPlugOptModEntry  20 }

rcPlugOptModTemperatureLowWarningThreshold OBJECT-TYPE
        SYNTAX      INTEGER
        MAX-ACCESS  read-only
        STATUS      current
        DESCRIPTION "This value represents the vendor specified low
                     temperature warning threshold. If the device
                     temperature falls below this value, a temperature
                     low warning is asserted. It is expressed in the
                     same units as the measured temperature."
        ::= { rcPlugOptModEntry 21 }

rcPlugOptModVoltage OBJECT-TYPE
        SYNTAX      INTEGER
        MAX-ACCESS  read-only
        STATUS      current
        DESCRIPTION "This value represents the internally measured
                     supply voltage. It is a positive number expressed
                     in microvolts and can range from 0 to 65535 mV."
        ::= { rcPlugOptModEntry 22 }

rcPlugOptModVoltageHighAlarmThreshold OBJECT-TYPE
        SYNTAX      INTEGER
        MAX-ACCESS  read-only
        STATUS      current
        DESCRIPTION "This value represents the vendor specified high
                     voltage threshold. If the measured voltage exceeds
                     this value, a high voltage is asserted. It
                     is a positive number expressed in microvolts."
        ::= { rcPlugOptModEntry 23 }

rcPlugOptModVoltageLowAlarmThreshold OBJECT-TYPE
        SYNTAX      INTEGER
        MAX-ACCESS  read-only
        STATUS      current
        DESCRIPTION "This value represents the vendor specified low
                     voltage threshold. If the measured voltage falls
                     below this value, a low voltage is asserted.
                     It is a positive number expressed in microvolts."
        ::= { rcPlugOptModEntry 24 }

rcPlugOptModVoltageHighWarningThreshold OBJECT-TYPE
        SYNTAX      INTEGER
        MAX-ACCESS  read-only
        STATUS      current
        DESCRIPTION "This value represents the vendor specified high
                     voltage warning threshold. If the measured voltage
                     exceeds this value, a high voltage warning is
                     asserted. It is a positive number expressed in
                     microvolts."
        ::= { rcPlugOptModEntry 25 }

rcPlugOptModVoltageLowWarningThreshold OBJECT-TYPE 
        SYNTAX      INTEGER
        MAX-ACCESS  read-only
        STATUS      current
        DESCRIPTION "This value represents the vendor specified low
                     voltage warning threshold. If the measured voltage
                     falls below this value, a low voltage warning is
                     asserted. It is a positive number expressed in
                     microvolts."
        ::= { rcPlugOptModEntry 26 }

rcPlugOptModBias OBJECT-TYPE    
        SYNTAX      INTEGER
        MAX-ACCESS  read-only
        STATUS      current
        DESCRIPTION "This value represents the internally measured
                     transmitter laser bias current. It is a positive
                     number expressed in units of 2 microamps and can
                     range from 0 to 131 mA with 0.0001 accuracy."
        ::= { rcPlugOptModEntry 27 }

rcPlugOptModBiasHighAlarmThreshold OBJECT-TYPE
        SYNTAX      INTEGER
        MAX-ACCESS  read-only
        STATUS      current
        DESCRIPTION "This value represents the vendor specified high
                     current threshold. If the measured bias
                     current exceeds this value, a high current alarm
                     is asserted. It is a positive number expressed
                     in units of 2 microamps and can range from 0 to
                     131 mA with 0.0001 accuracy."
        ::= { rcPlugOptModEntry 28 }

rcPlugOptModBiasLowAlarmThreshold OBJECT-TYPE
        SYNTAX      INTEGER
        MAX-ACCESS  read-only
        STATUS      current
        DESCRIPTION "This value represents the vendor specified low
                     current threshold. If the measured bias
                     current falls below this value, a low current
                     is asserted. It is a positive number
                     expressed in units of 2 microamps and can range
                     from 0 to 131 mA with 0.0001 accuracy."
        ::= { rcPlugOptModEntry 29 }

rcPlugOptModBiasHighWarningThreshold OBJECT-TYPE
        SYNTAX      INTEGER
        MAX-ACCESS  read-only
        STATUS      current
        DESCRIPTION "This value represents the vendor specified high
                     current warning threshold. If the measured bias
                     current exceeds this value, a high current warning
                     is asserted. It is a positive number expressed in
                     units of 2 microamps and can range from 0 to
                     131 mA with 0.0001 accuracy."
        ::= { rcPlugOptModEntry 30 }

rcPlugOptModBiasLowWarningThreshold OBJECT-TYPE
        SYNTAX      INTEGER
        MAX-ACCESS  read-only
        STATUS      current
        DESCRIPTION "This value represents the vendor specified low
                     current warning threshold. If the measured bias
                     current falls below this value, a low current
                     warning is asserted. It is a positive number
                     expressed in units of 2 microamps and can range
                     from 0 to 131 mA with 0.0001 accuracy."
        ::= { rcPlugOptModEntry 31 }

-- For power readings, we should really display these values in dBm
-- CP code can convert from mW to dBm.

rcPlugOptModTxPower OBJECT-TYPE
        SYNTAX      INTEGER
        MAX-ACCESS  read-only
        STATUS      current
        DESCRIPTION "This value represents the internally measured
                     coupled TX output power. It is a positive number
                     expressed in units of micro watts and can range
                     from 0 to 65.535 mW (-40 to 18.16 dBm)."
        ::= { rcPlugOptModEntry 32 }

rcPlugOptModTxPowerHighAlarmThreshold OBJECT-TYPE
        SYNTAX      INTEGER
        MAX-ACCESS  read-only
        STATUS      current
        DESCRIPTION "This value represents the vendor specified high
                     transmit power threshold. If the measured
                     transmitter power exceeds this value, a
                     transmitter power high is asserted. It is
                     a positive number expressed in units of micro
                     watts and can range from 0 to 65.535 mW (-40 to 18.16 dBm)."
        ::= { rcPlugOptModEntry 33 }

rcPlugOptModTxPowerLowAlarmThreshold OBJECT-TYPE
        SYNTAX      INTEGER
        MAX-ACCESS  read-only
        STATUS      current
        DESCRIPTION "This value represents the vendor specified low
                     transmit power threshold. If the measured
                     transmitter power falls below this value, a
                     transmitter power low is asserted. It is a
                     positive number expressed in units of micro watts
                     and can range from 0 to 65.535 mW (-40 to 18.16 dBm)."
        ::= { rcPlugOptModEntry 34 }

rcPlugOptModTxPowerHighWarningThreshold OBJECT-TYPE
        SYNTAX      INTEGER
        MAX-ACCESS  read-only
        STATUS      current
        DESCRIPTION "This value represents the vendor specified high
                     transmit power warning threshold. If the measured
                     transmitter power exceeds this value, a
                     transmitter power high warning is asserted. It is
                     a positive number expressed in units of units of
                     micro watts and can range from 0 to 65.535 mW (-40 to 18.16 dBm)."
        ::= { rcPlugOptModEntry 35 }

rcPlugOptModTxPowerLowWarningThreshold OBJECT-TYPE
        SYNTAX      INTEGER
        MAX-ACCESS  read-only
        STATUS      current
        DESCRIPTION "This value represents the vendor specified low
                     transmit power warning threshold. If the measured
                     transmitter power falls below this value, a
                     transmitter power low warning is asserted. It is
                     a positive number expressed in units of micro
                     watts and can range from 0 to 65.535 mW (-40 to 18.16 dBm)."
        ::= { rcPlugOptModEntry 36 }

rcPlugOptModRxPower OBJECT-TYPE
        SYNTAX      INTEGER
        MAX-ACCESS  read-only
        STATUS      current
        DESCRIPTION "This value represents the internally measured
                     received power. It is a positive number expressed
                     in units of micro watts and can range from 0 to
                     65.535 mW (-40 to 18.16 dBm)."
        ::= { rcPlugOptModEntry 37 }

rcPlugOptModRxPowerHighAlarmThreshold OBJECT-TYPE
        SYNTAX      INTEGER
        MAX-ACCESS  read-only
        STATUS      current
        DESCRIPTION "This value represents the vendor specified high
                     receiver power threshold. If the measured
                     received power exceeds this value, a receiver
                     power high is asserted. It is a positive
                     number expressed in units of micro watts and can
                     range from 0 to 65.535 mW (-40 to 18.16 dBm)."
        ::= { rcPlugOptModEntry 38 }

rcPlugOptModRxPowerLowAlarmThreshold OBJECT-TYPE
        SYNTAX      INTEGER
        MAX-ACCESS  read-only
        STATUS      current
        DESCRIPTION "This value represents the vendor specified low
                     receiver power threshold. If the measured
                     received power falls below this value, a receiver
                     power low is asserted. It is a positive
                     number expressed in units of micro watts and can
                     range from 0 to 65.535 mW (-40 to 18.16 dBm)."
        ::= { rcPlugOptModEntry 39 }

rcPlugOptModRxPowerHighWarningThreshold OBJECT-TYPE
        SYNTAX      INTEGER
        MAX-ACCESS  read-only
        STATUS      current
        DESCRIPTION "This value represents the vendor specified high
                     receiver power warning threshold. If the measured
                     received power exceeds this value, a receiver
                     power high warning is asserted. It is a positive
                     number expressed in units of units of micro watts
                     and can range from 0 to 65.535 uW (-40 to 18.16 dBm)."
        ::= { rcPlugOptModEntry 40 }

rcPlugOptModRxPowerLowWarningThreshold OBJECT-TYPE
        SYNTAX      INTEGER
        MAX-ACCESS  read-only
        STATUS      current
        DESCRIPTION "This value represents the vendor specified low
                     receiver power warning threshold. If the measured
                     received power falls below this value, a receiver
                     power low warning is asserted. It is a positive
                     number expressed in units of units of micro watts
                     and can range from 0 to 65.535 mW (-40 to 18.16 dBm)."
        ::= { rcPlugOptModEntry 41 }

rcPlugOptModAux1 OBJECT-TYPE
        SYNTAX      INTEGER
        MAX-ACCESS  read-only
        STATUS      current
        DESCRIPTION "This represents the internally measured A/D
                     value specified."
        ::= { rcPlugOptModEntry 42 }

rcPlugOptModAux1HighAlarmThreshold OBJECT-TYPE
        SYNTAX      INTEGER
        MAX-ACCESS  read-only
        STATUS      current
        DESCRIPTION "This value represents the vendor specified high
                     Aux1 threshold."
        ::= { rcPlugOptModEntry 43 }

rcPlugOptModAux1LowAlarmThreshold OBJECT-TYPE
        SYNTAX      INTEGER
        MAX-ACCESS  read-only
        STATUS      current
        DESCRIPTION "This value represents the vendor specified low
                     Aux1 threshold."
        ::= { rcPlugOptModEntry 44 }

rcPlugOptModAux1HighWarningThreshold OBJECT-TYPE
        SYNTAX      INTEGER
        MAX-ACCESS  read-only
        STATUS      current
        DESCRIPTION "This value represents the vendor specified high
                     Aux1 warning threshold."
        ::= { rcPlugOptModEntry 45 }

rcPlugOptModAux1LowWarningThreshold OBJECT-TYPE
        SYNTAX      INTEGER
        MAX-ACCESS  read-only
        STATUS      current
        DESCRIPTION "This value represents the vendor specified low
                     Aux1 warning threshold."
        ::= { rcPlugOptModEntry 46 }

rcPlugOptModAux2 OBJECT-TYPE
        SYNTAX      INTEGER
        MAX-ACCESS  read-only
        STATUS      current
        DESCRIPTION "This represents the internally measured A/D
                     value specified."
        ::= { rcPlugOptModEntry 47 }

rcPlugOptModAux2HighAlarmThreshold OBJECT-TYPE
        SYNTAX      INTEGER
        MAX-ACCESS  read-only
        STATUS      current
        DESCRIPTION "This value represents the vendor specified high
                     Aux1 threshold."
        ::= { rcPlugOptModEntry 48 }

rcPlugOptModAux2LowAlarmThreshold OBJECT-TYPE
        SYNTAX      INTEGER
        MAX-ACCESS  read-only
        STATUS      current
        DESCRIPTION "This value represents the vendor specified low
                     Aux1 threshold."
        ::= { rcPlugOptModEntry 49 }

rcPlugOptModAux2HighWarningThreshold OBJECT-TYPE
        SYNTAX      INTEGER
        MAX-ACCESS  read-only
        STATUS      current
        DESCRIPTION "This value represents the vendor specified high
                     Aux1 warning threshold."
        ::= { rcPlugOptModEntry 50 }

rcPlugOptModAux2LowWarningThreshold OBJECT-TYPE
        SYNTAX      INTEGER
        MAX-ACCESS  read-only
        STATUS      current
        DESCRIPTION "This value represents the vendor specified low
                     Aux1 warning threshold."
        ::= { rcPlugOptModEntry 51 }



-- These next entries represent the defined and warning bits
-- contained in DDI bytes at offsets 112 thru 117.

rcPlugOptModTemperatureStatus OBJECT-TYPE
        SYNTAX      INTEGER {
                        normal(1),
                        highWarning(2),
                        highAlarm(3),
                        lowWarning(4),
                        lowAlarm(5)
                    }
        MAX-ACCESS  read-only
        STATUS 	    current
        DESCRIPTION "Used to indicate the current temperature status"
        DEFVAL      { normal }
	::= { rcPlugOptModEntry 52 }

rcPlugOptModVoltageStatus OBJECT-TYPE
        SYNTAX      INTEGER {
                        normal(1),
                        highWarning(2),
                        highAlarm(3),
                        lowWarning(4),
                        lowAlarm(5)
                    }
        MAX-ACCESS  read-only
        STATUS 	    current
        DESCRIPTION "Used to indicate the current voltage status"
        DEFVAL      { normal }
        ::= { rcPlugOptModEntry 53 }


rcPlugOptModBiasStatus OBJECT-TYPE
        SYNTAX      INTEGER {
                        normal(1),
                        highWarning(2),
                        highAlarm(3),
                        lowWarning(4),
                        lowAlarm(5)
                    }
        MAX-ACCESS  read-only
        STATUS      current
        DESCRIPTION "Used to indicate the current laser bias status"
        DEFVAL      { normal }
        ::= { rcPlugOptModEntry 54 }

rcPlugOptModTxPowerStatus OBJECT-TYPE
        SYNTAX      INTEGER {
                        normal(1),
                        highWarning(2),
                        highAlarm(3),
                        lowWarning(4),
                        lowAlarm(5)
                    }
        MAX-ACCESS  read-only
        STATUS      current
        DESCRIPTION "Used to indicate the current transmitter power
                     status"
        DEFVAL      { normal }
        ::= { rcPlugOptModEntry 55 }

rcPlugOptModRxPowerStatus OBJECT-TYPE
        SYNTAX      INTEGER {
                        normal(1),
                        highWarning(2),
                        highAlarm(3),
                        lowWarning(4),
                        lowAlarm(5)
                    }
        MAX-ACCESS  read-only
        STATUS      current
        DESCRIPTION "Used to indicate the current receiver power status"
        DEFVAL      { normal }
        ::= { rcPlugOptModEntry 56 }

rcPlugOptModAux1Status OBJECT-TYPE
        SYNTAX      INTEGER {
                        normal(1),
                        highWarning(2),
                        highAlarm(3),
                        lowWarning(4),
                        lowAlarm(5)
                    }
        MAX-ACCESS  read-only
        STATUS      current
        DESCRIPTION "Used to indicate the current Aux1 status"
        DEFVAL      { normal }
        ::= { rcPlugOptModEntry 57 }

rcPlugOptModAux2Status OBJECT-TYPE
        SYNTAX      INTEGER {
                        normal(1),
                        highWarning(2),
                        highAlarm(3),
                        lowWarning(4),
                        lowAlarm(5)
                    }
        MAX-ACCESS  read-only
        STATUS      current
        DESCRIPTION "Used to indicate the current Aux2 status"
        DEFVAL      { normal }
        ::= { rcPlugOptModEntry 58 }


-- ----------------------------------------------------------
--Global configuration of DDI
-- ----------------------------------------------------------

rcPlugOptModScalars OBJECT IDENTIFIER ::= { rcPlugOptMod 2 }

rcPlugOptModDdmMonitor OBJECT-TYPE
        SYNTAX        EnableValue
        MAX-ACCESS    read-write
        STATUS        current
        DESCRIPTION   "Enable/disable the global polling monitor for DDM"
        DEFVAL  { disable }
        ::= { rcPlugOptModScalars 1 }

rcPlugOptModDdmMonitorInterval OBJECT-TYPE
        SYNTAX        INTEGER (5..60)
        MAX-ACCESS    read-write
        STATUS        current
        DESCRIPTION   "Indicate the interval in which the DDM alert registers is polled"
        DEFVAL  { 5 }
        ::= { rcPlugOptModScalars 2 }

rcPlugOptModDdmTrapSend OBJECT-TYPE
        SYNTAX        EnableValue
        MAX-ACCESS    read-write
        STATUS        current
        DESCRIPTION   " Enable/disable the global ddm trap send to SNMP manager "
        DEFVAL  { enable }
        ::= { rcPlugOptModScalars 3 }

rcPlugOptModDdmAlarmPortdown OBJECT-TYPE
        SYNTAX        EnableValue
        MAX-ACCESS    read-write
        STATUS        current
        DESCRIPTION   " Enable/disable the global portdown option when ddm alarm occurs "
        DEFVAL  { enable }
        ::= { rcPlugOptModScalars 4 }


-- COBALT BLUE MIBs

rcCobaltBlueMib 	  OBJECT IDENTIFIER ::= { rcCobaltBlue 1 }

DeviceStatus ::= TEXTUAL-CONVENTION
  STATUS	current
  DESCRIPTION	"Standard card states for slotted chassis based products"
  SYNTAX	INTEGER {
			invalid(1),
			down(2),
			up(3),
			disabled(4)
		}

DscpValueSet ::= TEXTUAL-CONVENTION
  STATUS	current
  DESCRIPTION	"DSCP Values"
  SYNTAX	INTEGER {
                      phbcs0(0),
		          val1(1),
		          val2(2),
 		          val3(3),
		          val4(4),
		          val5(5),
		          val6(6),
		          val7(7),
                      phbcs1(8),
		          val9(9),
                      phbaf11(10),
		          val11(11),
                      phbaf12(12),
		          val13(13),
                      phbaf13(14),
		          val15(15),
                      phbcs2(16),
		          val17(17),
                      phbaf21(18),
		          val19(19),
                      phbaf22(20),
		          val21(21),
                      phbaf23(22),
		          val23(23),
                      phbcs3(24),
		          val25(25),
                      phbaf31(26),
		          val27(27),
                      phbaf32(28),
		          val29(29),
                      phbaf33(30),
		          val31(31),
                      phbcs4(32),
		          val33(33),
                      phbaf41(34),
		          val35(35),
                      phbaf42(36),
		          val37(37),
                      phbaf43(38),
		          val39(39),
                      phbcs5(40),
		          val41(41),
			    val42(42),
		          val43(43),
		          val44(44),
		          val45(45),
                      phbef(46),
		          val47(47),
                      phbcs6(48),
		          val49(49),
		          val50(50),
		          val51(51),
		          val52(52),
		          val53(53),
		          val54(54),
		          val55(55),
                      phbcs7(56),
		          val57(57),
		          val58(58),
		          val59(59),
		          val60(60),
			    val61(61),
		          val62(62),
		          val63(63),
                      disableOrInvalid(64)
			}

DropPrecedence ::= TEXTUAL-CONVENTION
  STATUS	current
  DESCRIPTION	"QOS Drop Precedence"
  SYNTAX	INTEGER {
		     low(0),
		     medium(1),
		     high(2)
		}

LaneList ::= TEXTUAL-CONVENTION
  STATUS         current
  DESCRIPTION    "The string is 8 octets long, for a total
                  of 64 bits. Each bit corresponds to a lane.
                  Each I/O slot can have 4 or 6 lanes based on the 
	            card type. When a bit has the value one(1), 
                  the corresponding lane is a member of the set. 
                  When a bit has the value zero(0), the corresponding 
                  lane is not a member of the set.
                  The encoding is such that the most significant bit
                  of octet #1 corresponds to laneId 0, while the
                  least significant bit of octet #8 corresponds to
                  laneId 63. LaneIds 60, 61, 62, and 63 are not used
	            for CB release 1."
  SYNTAX         OCTET STRING (SIZE (8))

QosLevelValueSet ::= TEXTUAL-CONVENTION
  STATUS	  current
  DESCRIPTION "QOS Levels"
  SYNTAX	  INTEGER {
                        zero(0),
                        one(1),
                        two(2),
                        three(3),
                        four(4),
                        five(5),
                        six(6),
                        seven(7),
                        disable(8)
		 }

Dot1pValueSet ::= TEXTUAL-CONVENTION
  STATUS	  current
  DESCRIPTION "802.1p Values"
  SYNTAX	  INTEGER {
                        zero(0),
                        one(1),
                        two(2),
                        three(3),
                        four(4),
                        five(5),
                        six(6),
                        seven(7),
                        disable(8)
		 }

MplsExpValueSet ::= TEXTUAL-CONVENTION
  STATUS	  current
  DESCRIPTION "Mpls Exp Values"
  SYNTAX	  INTEGER {
                        zero(0),
                        one(1),
                        two(2),
                        three(3),
                        four(4),
                        five(5),
                        six(6),
                        seven(7),
                        disable(8)
		 }


SfDeviceMode ::= TEXTUAL-CONVENTION
  STATUS        current
  DESCRIPTION   "Mode of given Fast SE Device either BME or SE"
  SYNTAX        INTEGER {
			other (1),
                        bme(2),
                        se(3)
                }

--
-- Object groups within the Cobalt Blue MIB
--

rcCbNotifications         OBJECT IDENTIFIER ::= { rcCobaltBlueMib 0 }
rcCbObjects               OBJECT IDENTIFIER ::= { rcCobaltBlueMib 1 }

rcCbSwitchFabric          OBJECT IDENTIFIER ::= { rcCbObjects 1 }

rcCbSwitchFabricScalars   OBJECT IDENTIFIER ::= { rcCbSwitchFabric 1 }
rcCbSwitchFabricStats	  OBJECT IDENTIFIER ::= { rcCbSwitchFabricScalars 1 }

rcCbSwitchFabricDropPrec1AcceptedPackets	OBJECT-TYPE
	SYNTAX          Counter64
	MAX-ACCESS      read-only
        STATUS          current
        DESCRIPTION     "Accepted number of packets from drop precedence 1. The drop precedence is a function of the front end policer."
        ::= { rcCbSwitchFabricStats 1 }

rcCbSwitchFabricDropPrec1AcceptedBytes		OBJECT-TYPE
	SYNTAX          Counter64
	MAX-ACCESS      read-only
        STATUS          current
        DESCRIPTION     "Accepted number of bytes from drop precedence 1"
        ::= { rcCbSwitchFabricStats 2 }

rcCbSwitchFabricDropPrec1CongestionMarkedPackets		OBJECT-TYPE
	SYNTAX          Counter64
	MAX-ACCESS      read-only
        STATUS          current
        DESCRIPTION     "Congestion marked number of packets from drop precedence 1."
        ::= { rcCbSwitchFabricStats 3 }

rcCbSwitchFabricDropPrec1CongestionMarkedBytes		OBJECT-TYPE
	SYNTAX          Counter64
	MAX-ACCESS      read-only
        STATUS          current
        DESCRIPTION     "Congestion marked number of bytes from drop precedence 1."
        ::= { rcCbSwitchFabricStats 4 }

rcCbSwitchFabricDropPrec1DiscardDroppedPackets		OBJECT-TYPE
	SYNTAX          Counter64
	MAX-ACCESS      read-only
        STATUS          current
        DESCRIPTION     "WRED dropped number of packets from drop precedence 1."
        ::= { rcCbSwitchFabricStats 5 }

rcCbSwitchFabricDropPrec1DiscardDroppedBytes		OBJECT-TYPE
	SYNTAX          Counter64
	MAX-ACCESS      read-only
        STATUS          current
        DESCRIPTION     "WRED dropped number of bytes from drop precedence 1."
        ::= { rcCbSwitchFabricStats 6 }

rcCbSwitchFabricDropPrec2AcceptedPackets	OBJECT-TYPE
	SYNTAX          Counter64
	MAX-ACCESS      read-only
        STATUS          current
        DESCRIPTION     "Accepted number of packets from drop precedence 2"
        ::= { rcCbSwitchFabricStats 7 }

rcCbSwitchFabricDropPrec2AcceptedBytes		OBJECT-TYPE
	SYNTAX          Counter64
	MAX-ACCESS      read-only
        STATUS          current
        DESCRIPTION     "Accepted number of bytes from drop precedence 2"
        ::= { rcCbSwitchFabricStats 8 }

rcCbSwitchFabricDropPrec2CongestionMarkedPackets		OBJECT-TYPE
	SYNTAX          Counter64
	MAX-ACCESS      read-only
        STATUS          current
        DESCRIPTION     "Congestion marked number of packets from drop precedence 2."
        ::= { rcCbSwitchFabricStats 9 }

rcCbSwitchFabricDropPrec2CongestionMarkedBytes		OBJECT-TYPE
	SYNTAX          Counter64
	MAX-ACCESS      read-only
        STATUS          current
        DESCRIPTION     "Congestion marked number of bytes from drop precedence 2."
        ::= { rcCbSwitchFabricStats 10 }

rcCbSwitchFabricDropPrec2DiscardDroppedPackets		OBJECT-TYPE
	SYNTAX          Counter64
	MAX-ACCESS      read-only
        STATUS          current
        DESCRIPTION     "WRED dropped number of packets from drop precedence 2."
        ::= { rcCbSwitchFabricStats 11 }

rcCbSwitchFabricDropPrec2DiscardDroppedBytes		OBJECT-TYPE
	SYNTAX          Counter64
	MAX-ACCESS      read-only
        STATUS          current
        DESCRIPTION     "WRED dropped number of bytes from drop precedence 2."
        ::= { rcCbSwitchFabricStats 12 }

rcCbSwitchFabricDropPrec3AcceptedPackets    OBJECT-TYPE
    SYNTAX          Counter64
    MAX-ACCESS      read-only
        STATUS          current
        DESCRIPTION     "Accepted number of packets from drop precedence 3"
        ::= { rcCbSwitchFabricStats 13 }

rcCbSwitchFabricDropPrec3AcceptedBytes      OBJECT-TYPE
    SYNTAX          Counter64
    MAX-ACCESS      read-only
        STATUS          current
        DESCRIPTION     "Accepted number of bytes from drop precedence 3"
        ::= { rcCbSwitchFabricStats 14 }

rcCbSwitchFabricDropPrec3CongestionMarkedPackets		OBJECT-TYPE
	SYNTAX          Counter64
	MAX-ACCESS      read-only
        STATUS          current
        DESCRIPTION     "Congestion marked number of packets from drop precedence 3."
        ::= { rcCbSwitchFabricStats 15 }

rcCbSwitchFabricDropPrec3CongestionMarkedBytes		OBJECT-TYPE
	SYNTAX          Counter64
	MAX-ACCESS      read-only
        STATUS          current
        DESCRIPTION     "Congestion marked number of bytes from drop precedence 3."
        ::= { rcCbSwitchFabricStats 16 }

rcCbSwitchFabricDropPrec3DiscardDroppedPackets		OBJECT-TYPE
	SYNTAX          Counter64
	MAX-ACCESS      read-only
        STATUS          current
        DESCRIPTION     "WRED dropped number of packets from drop precedence 3."
        ::= { rcCbSwitchFabricStats 17 }

rcCbSwitchFabricDropPrec3DiscardDroppedBytes		OBJECT-TYPE
	SYNTAX          Counter64
	MAX-ACCESS      read-only
        STATUS          current
        DESCRIPTION     "WRED dropped number of bytes from drop precedence 3."
        ::= { rcCbSwitchFabricStats 18 }

rcCbSwitchFabricDropPrec4AcceptedPackets    OBJECT-TYPE
    SYNTAX          Counter64
    MAX-ACCESS      read-only
        STATUS          current
        DESCRIPTION     "Accepted number of packets from drop precedence 4"
        ::= { rcCbSwitchFabricStats 19 }

rcCbSwitchFabricDropPrec4AcceptedBytes      OBJECT-TYPE
    SYNTAX          Counter64
    MAX-ACCESS      read-only
        STATUS          current
        DESCRIPTION     "Accepted number of bytes from drop precedence 4"
        ::= { rcCbSwitchFabricStats 20 }

rcCbSwitchFabricNonWredDroppedPackets		OBJECT-TYPE
	SYNTAX          Counter64
	MAX-ACCESS      read-only
        STATUS          current
        DESCRIPTION     "Dropped packets due to non Random Early Detection"
        ::= { rcCbSwitchFabricStats 21 }

rcCbSwitchFabricNonWredDroppedBytes		OBJECT-TYPE
	SYNTAX          Counter64
	MAX-ACCESS      read-only
        STATUS          current
        DESCRIPTION     "Dropped packets bytes due to non Random Early Detection"
        ::= { rcCbSwitchFabricStats 22 }

rcCbSwitchFabricDequeuedPackets		OBJECT-TYPE
	SYNTAX          Counter64
	MAX-ACCESS      read-only
        STATUS          current
        DESCRIPTION     "Packets dequeued once inside the switch fabric"
        ::= { rcCbSwitchFabricStats 23 }

rcCbSwitchFabricDequeuedBytes		OBJECT-TYPE
	SYNTAX          Counter64
	MAX-ACCESS      read-only
        STATUS          current
        DESCRIPTION     "Packets bytes dequeued once inside the switch fabric"
        ::= { rcCbSwitchFabricStats 24 }

rcCbSwitchFabricDropPrec1DroppedPackets		OBJECT-TYPE
	SYNTAX          Counter64
	MAX-ACCESS      read-only
        STATUS          current
        DESCRIPTION     "non-WRED dropped number of packets from drop precedence 1."
        ::= { rcCbSwitchFabricStats 25 }

rcCbSwitchFabricDropPrec1DroppedBytes		OBJECT-TYPE
	SYNTAX          Counter64
	MAX-ACCESS      read-only
        STATUS          current
        DESCRIPTION     "non-WRED dropped number of bytes from drop precedence 1."
        ::= { rcCbSwitchFabricStats 26 }

rcCbSwitchFabricDropPrec2DroppedPackets		OBJECT-TYPE
	SYNTAX          Counter64
	MAX-ACCESS      read-only
        STATUS          current
        DESCRIPTION     "non-WRED dropped number of packets from drop precedence 2."
        ::= { rcCbSwitchFabricStats 27 }

rcCbSwitchFabricDropPrec2DroppedBytes		OBJECT-TYPE
	SYNTAX          Counter64
	MAX-ACCESS      read-only
        STATUS          current
        DESCRIPTION     "non-WRED dropped number of bytes from drop precedence 2."
        ::= { rcCbSwitchFabricStats 28 }

rcCbSwitchFabricDropPrec3DroppedPackets		OBJECT-TYPE
	SYNTAX          Counter64
	MAX-ACCESS      read-only
        STATUS          current
        DESCRIPTION     "non-WRED dropped number of packets from drop precedence 3."
        ::= { rcCbSwitchFabricStats 29 }

rcCbSwitchFabricDropPrec3DroppedBytes		OBJECT-TYPE
	SYNTAX          Counter64
	MAX-ACCESS      read-only
        STATUS          current
        DESCRIPTION     "non-WRED dropped number of bytes from drop precedence 3."
        ::= { rcCbSwitchFabricStats 30 }

rcCbSwitchFabricDropPrec4CongestionMarkedPackets		OBJECT-TYPE
	SYNTAX          Counter64
	MAX-ACCESS      read-only
        STATUS          current
        DESCRIPTION     "Congestion marked number of packets from drop precedence 4."
        ::= { rcCbSwitchFabricStats 31 }

rcCbSwitchFabricDropPrec4CongestionMarkedBytes		OBJECT-TYPE
	SYNTAX          Counter64
	MAX-ACCESS      read-only
        STATUS          current
        DESCRIPTION     "Congestion marked number of bytes from drop precedence 4."
        ::= { rcCbSwitchFabricStats 32 }

rcCbSwitchFabricDropPrec4DiscardDroppedPackets		OBJECT-TYPE
	SYNTAX          Counter64
	MAX-ACCESS      read-only
        STATUS          current
        DESCRIPTION     "WRED dropped number of packets from drop precedence 4."
        ::= { rcCbSwitchFabricStats 33 }

rcCbSwitchFabricDropPrec4DiscardDroppedBytes		OBJECT-TYPE
	SYNTAX          Counter64
	MAX-ACCESS      read-only
        STATUS          current
        DESCRIPTION     "WRED dropped number of bytes from drop precedence 4."
        ::= { rcCbSwitchFabricStats 34 }

rcCbSwitchFabricDropPrec4DroppedPackets		OBJECT-TYPE
	SYNTAX          Counter64
	MAX-ACCESS      read-only
        STATUS          current
        DESCRIPTION     "non-WRED dropped number of packets from drop precedence 4."
        ::= { rcCbSwitchFabricStats 35 }

rcCbSwitchFabricDropPrec4DroppedBytes		OBJECT-TYPE
	SYNTAX          Counter64
	MAX-ACCESS      read-only
        STATUS          current
        DESCRIPTION     "non-WRED dropped number of bytes from drop precedence 4."
        ::= { rcCbSwitchFabricStats 36 }

rcCbSwitchFabricOverSubscribeTotalDroppedPkts    OBJECT-TYPE
	SYNTAX          Counter64
	MAX-ACCESS      read-only
        STATUS          current
        DESCRIPTION     "Dropped number of packets due to free list underflow."
        ::= { rcCbSwitchFabricStats 37 }

rcCbSwitchFabricOverSubscribeTotalDroppedBytes    OBJECT-TYPE
	SYNTAX          Counter64
	MAX-ACCESS      read-only
        STATUS          current
        DESCRIPTION     "Dropped number of bytes due to free list underflow."
        ::= { rcCbSwitchFabricStats 38 }

rcCbSwitchFabricOverSubscribeGuaranteeDroppedPkts    OBJECT-TYPE
	SYNTAX          Counter64
	MAX-ACCESS      read-only
        STATUS          current
        DESCRIPTION     "Dropped number of packets Gbl buf thres guarantee."
        ::= { rcCbSwitchFabricStats 39 }

rcCbSwitchFabricOverSubscribeGuaranteeDroppedBytes    OBJECT-TYPE
	SYNTAX          Counter64
	MAX-ACCESS      read-only
        STATUS          current
        DESCRIPTION     "Dropped number of bytes Gbl buf thres guarantee."
        ::= { rcCbSwitchFabricStats 40 }

rcCbSwitchFabricOutPkts    OBJECT-TYPE
	SYNTAX          Counter64
	MAX-ACCESS      read-only
        STATUS          current
        DESCRIPTION     "Number of packets out from egress interface."
        ::= { rcCbSwitchFabricStats 41 }

rcCbSwitchFabricOutBytes    OBJECT-TYPE
	SYNTAX          Counter64
	MAX-ACCESS      read-only
        STATUS          current
        DESCRIPTION     "Number of bytes out from egress interface."
        ::= { rcCbSwitchFabricStats 42 }

rcCbSwitchFabricStatsCapture	OBJECT-TYPE
	SYNTAX          TruthValue
	MAX-ACCESS      read-write
        STATUS          current
        DESCRIPTION     "Control to turn stats collection on or off"
        ::= { rcCbSwitchFabricScalars 2 }

rcCbSwitchFabricStatsPortId	OBJECT-TYPE
	SYNTAX          InterfaceIndex 
	MAX-ACCESS      read-write
        STATUS          current
        DESCRIPTION     "The port on which stats is to be collected on.
                         Must select a data port."
        ::= { rcCbSwitchFabricScalars 3}

rcCbSwitchFabricStatsCosId	OBJECT-TYPE
	SYNTAX          Integer32 (0..7)
	MAX-ACCESS      read-write
        STATUS          current
        DESCRIPTION     "The CoS or VOQ to collect Stats on"
	::= {  rcCbSwitchFabricScalars 4}

rcCbBmeActiveBme	OBJECT-TYPE
	SYNTAX          INTEGER {
				  activeArbitorId0(1), -- slot 24
                  activeArbitorId1(2)  -- slot 21
			}
	MAX-ACCESS      read-only
        STATUS          current
        DESCRIPTION     "The location of the active BME in the system.
			 BME stands for Bandwidth Manager Engine."
        ::= {  rcCbSwitchFabricScalars 5}

rcCbBmeRedundancyMode	OBJECT-TYPE
	SYNTAX          INTEGER {
				manual(1),
				onePlusOneControlAndData(2),
				onePlusOneControlOnly(3)
			}
	MAX-ACCESS      read-only
        STATUS          current
        DESCRIPTION     "Redundancy mode for BMEs."
        ::= {  rcCbSwitchFabricScalars 6}

rcCbProfileType  	OBJECT-TYPE
	SYNTAX          INTEGER {
				balanced(1),
				unicastOptimized(2),
				multicastOptimized(3)
			}
	MAX-ACCESS      read-write
        STATUS          current
        DESCRIPTION     "Switch fabric profile type."
        DEFVAL        { balanced }
        ::= {  rcCbSwitchFabricScalars 7}

rcCbSwitchFabricDeviceRead        OBJECT-TYPE
        SYNTAX          TruthValue
        MAX-ACCESS      read-write
        STATUS          current
        DESCRIPTION     "If turned on statistics for switch fabric counters
                         are collected directly from devices.  Otherwise,
                         a cached copy is returned."
        DEFVAL        { true }
        ::= {  rcCbSwitchFabricScalars 8}

rcCbQueuingEngine2kTable OBJECT-TYPE
        SYNTAX          SEQUENCE OF RcCBQueuingEngine2kEntry
        MAX-ACCESS      not-accessible
        STATUS          current
        DESCRIPTION     "Table containing the 2k based queuing engine
			entries for the system."
        ::= { rcCbSwitchFabric 2 }

rcCbQueuingEngine2kEntry  OBJECT-TYPE
        SYNTAX          RcCBQueuingEngine2kEntry
        MAX-ACCESS      not-accessible
        STATUS          current
        DESCRIPTION     "Entry for the QE Table"
	INDEX		{ rcCbQueuingEngine2kId }
    ::= { rcCbQueuingEngine2kTable 1 }

RcCBQueuingEngine2kEntry ::= SEQUENCE {
		rcCbQueuingEngine2kId             Integer32,
		rcCbQueuingEngine2kStatus         DeviceStatus
		}

rcCbQueuingEngine2kId	OBJECT-TYPE
	SYNTAX          Integer32 (1..32)
	MAX-ACCESS      not-accessible
        STATUS          current
        DESCRIPTION     "Index for an entry in the QE Table.  Here is the layout
			 of the IDs in relation to the system:

			Location	ID(s)
			---------------------
			IO on slot 3:   1..3
			IO on slot 4:   4..6	
			CP on slot 1:	7
			CP on slot 2:	8
			IO on slot 5:   9..11
			IO on slot 6:   12..14	
			...
			IO on slot 12:	30..32
			"
        ::= { rcCbQueuingEngine2kEntry 1 }

rcCbQueuingEngine2kStatus	OBJECT-TYPE
	SYNTAX          DeviceStatus
	MAX-ACCESS      read-only
        STATUS          current
        DESCRIPTION     "Status of a given QE interface."
        ::= { rcCbQueuingEngine2kEntry 2 }

rcCbSwitchingEngine4kTable OBJECT-TYPE
        SYNTAX          SEQUENCE OF RcCBSwitchingEngine4kEntry
        MAX-ACCESS      not-accessible
        STATUS          current
        DESCRIPTION     "Table containing the 4k based switching
			 engine entries for the system."
        ::= { rcCbSwitchFabric 3 }

rcCbSwitchingEngine4kEntry           OBJECT-TYPE
        SYNTAX          RcCBSwitchingEngine4kEntry
        MAX-ACCESS      not-accessible
        STATUS          current
        DESCRIPTION     "Entry for the SE Table."
	INDEX		{ rcCbSwitchingEngine4kId }
    ::= { rcCbSwitchingEngine4kTable 1 }

RcCBSwitchingEngine4kEntry ::= SEQUENCE {
		rcCbSwitchingEngine4kId             Integer32,
		rcCbSwitchingEngine4kStatus         DeviceStatus
		}

rcCbSwitchingEngine4kId	OBJECT-TYPE
	SYNTAX          Integer32 (1..18)
	MAX-ACCESS      not-accessible
        STATUS          current
        DESCRIPTION     "Index for the SE Table.  Here is the layout
			 of the IDs in relation to the system:

			Location	ID(s)
			---------------------
			SF on slot 13:  1..3
			SF on slot 14:  4..6
			...
			SF on slot 18:	16..18	
			"
        ::= { rcCbSwitchingEngine4kEntry 1 }

rcCbSwitchingEngine4kStatus	OBJECT-TYPE
	SYNTAX          DeviceStatus
	MAX-ACCESS      read-only
        STATUS          current
        DESCRIPTION     "Status of a given SE Device."
        ::= { rcCbSwitchingEngine4kEntry 2 }

rcCbSwitchingEngine9600Table OBJECT-TYPE
        SYNTAX          SEQUENCE OF RcCBSwitchingEngine9600Entry
        MAX-ACCESS      not-accessible
        STATUS          current
        DESCRIPTION     "Table containing the 9600 based switching
			 engine entries for the system."
        ::= { rcCbSwitchFabric 4 }

rcCbSwitchingEngine9600Entry           OBJECT-TYPE
        SYNTAX          RcCBSwitchingEngine9600Entry
        MAX-ACCESS      not-accessible
        STATUS          current
        DESCRIPTION     "Entry for the SE 9600 Table."
	INDEX		{ rcCbSwitchingEngine9600Id }
    ::= { rcCbSwitchingEngine9600Table 1 }

RcCBSwitchingEngine9600Entry ::= SEQUENCE {
		rcCbSwitchingEngine9600Id             Integer32,
		rcCbSwitchingEngine9600Status         DeviceStatus,
                rcCbSwitchingEngine9600Mode           SfDeviceMode
		}

rcCbSwitchingEngine9600Id	OBJECT-TYPE
	SYNTAX          Integer32 (1..12)
	MAX-ACCESS      not-accessible
        STATUS          current
        DESCRIPTION     "Index for the SE Table.  Here is the layout
			 of the IDs in relation to the system:

			Location	ID(s)
			---------------------
			SF on slot 21:  1..2
			SF on slot 22:  3..4
			...
			SF on slot 26:	11..12
			"
        ::= { rcCbSwitchingEngine9600Entry 1 }

rcCbSwitchingEngine9600Status	OBJECT-TYPE
	SYNTAX          DeviceStatus
	MAX-ACCESS      read-only
        STATUS          current
        DESCRIPTION     "Status of a given Fast SE Device."
        ::= { rcCbSwitchingEngine9600Entry 2 }

rcCbSwitchingEngine9600Mode   OBJECT-TYPE
        SYNTAX          SfDeviceMode
        MAX-ACCESS      read-only
        STATUS          current 
        DESCRIPTION     "Mode of given Fast SE Device either BME or SE."
        ::= { rcCbSwitchingEngine9600Entry 3 }

rcCbQe2kSerdesLinkTable OBJECT-TYPE
        SYNTAX          SEQUENCE OF RcCbQe2kSerdesLinkEntry
        MAX-ACCESS      not-accessible
        STATUS          current
        DESCRIPTION     "Table containing the Serdes Link Information
			for the system."
        ::= { rcCbSwitchFabric 5 }

rcCbQe2kSerdesLinkEntry   OBJECT-TYPE
        SYNTAX          RcCbQe2kSerdesLinkEntry
        MAX-ACCESS      not-accessible
        STATUS          current
        DESCRIPTION     "Entry for a QE based Serdes Link Interface.
			 The combination of the QE ID and Serdes Link ID
			 uniquely identifies a link."
	INDEX		{ rcCbQe2kSerdesLinkId}
    ::= { rcCbQe2kSerdesLinkTable 1 }

RcCbQe2kSerdesLinkEntry ::= SEQUENCE {
		rcCbQe2kSerdesLinkId             Integer32,
		rcCbQe2kSerdesLinkType           INTEGER,
		rcCbQe2kSerdesLinkStatus         DeviceStatus,
		rcCbQe2kSerdesLinkConnectedToDevice    Integer32,
		rcCbQe2kSerdesLinkConnectedToSlot      Integer32
		}

rcCbQe2kSerdesLinkId	OBJECT-TYPE
	SYNTAX          Integer32 (1..640)
	MAX-ACCESS      not-accessible
        STATUS          current
        DESCRIPTION     "This ID maps to a particular serdes port number
			 for the identified device.  Here's the mapping:

			 rcCbQe2kSerdesLinkId  1 = port 0; Slot 3; QE Device 1
			 ...
 			 rcCbQe2kSerdesLinkId 20 = port 19; Slot 3; QE Device 1
			 rcCbQe2kSerdesLinkId 21 = port 0; Slot 3; QE Device 2
			 rcCbQe2kSerdesLinkId 41 = port 0; Slot 3; QE Device 3
			 rcCbQe2kSerdesLinkId 61 = port 0; Slot 4; QE Device 1
			 rcCbQe2kSerdesLinkId 121 = port 0; Slot 1; QE Device 1
			 rcCbQe2kSerdesLinkId 141 = port 0; Slot 1; QE Device 1
			 rcCbQe2kSerdesLinkId 161 = port 0; Slot 5; QE Device 1
			 rcCbQe2kSerdesLinkId 221 = port 0; Slot 6; QE Device 1
			 ... with slots 6-12 in order ...
			 rcCbQe2kSerdesLinkId 640 = port 19; Slot 12; QE Device 3
			 Note link 15 & 17 are used when QE2k is connected to SF96."
        ::= { rcCbQe2kSerdesLinkEntry 1 }

rcCbQe2kSerdesLinkType	OBJECT-TYPE
	SYNTAX          INTEGER {
				sci(1),
				sfi(2)
			}
	MAX-ACCESS      read-only
        STATUS          current
        DESCRIPTION     "Link type of the serdes interface"
        ::= { rcCbQe2kSerdesLinkEntry 2 }

rcCbQe2kSerdesLinkStatus	OBJECT-TYPE
	SYNTAX          DeviceStatus
	MAX-ACCESS      read-only
        STATUS          current
        DESCRIPTION     "Interface Status"
        ::= { rcCbQe2kSerdesLinkEntry 3 }

rcCbQe2kSerdesLinkConnectedToDevice	OBJECT-TYPE
	SYNTAX          Integer32 (1..20)
	MAX-ACCESS      read-only
        STATUS          current
        DESCRIPTION     "The SE/BME ID to which the QE2k ID is attached
			 to.  Note that IDs 16 & 18 are unused."
        ::= { rcCbQe2kSerdesLinkEntry 4 }

rcCbQe2kSerdesLinkConnectedToSlot   OBJECT-TYPE
        SYNTAX          Integer32 (21..26)
        MAX-ACCESS      read-only
        STATUS          current
        DESCRIPTION     "The slot number of the switch fabric card to which the QE2k ID is attached to."
        ::= { rcCbQe2kSerdesLinkEntry 5 }

rcCbSESerdesLinkTable OBJECT-TYPE
        SYNTAX          SEQUENCE OF RcCBSESerdesLinkEntry
        MAX-ACCESS      not-accessible
        STATUS          current
        DESCRIPTION     "Table containing the Serdes Link Information
			for the system."
        ::= { rcCbSwitchFabric 6 }

rcCbSESerdesLinkEntry   OBJECT-TYPE
        SYNTAX          RcCBSESerdesLinkEntry
        MAX-ACCESS      not-accessible
        STATUS          current
        DESCRIPTION     "Entry for an SE based Serdes Link Interface.  
			 The combination of the QE ID and Serdes Link ID
			 uniquely identifies a link."
	INDEX		{ rcCbSESerdesLinkId}
    ::= { rcCbSESerdesLinkTable 1 }

RcCBSESerdesLinkEntry ::= SEQUENCE {
		rcCbSESerdesLinkId             Integer32,
		rcCbSESerdesLinkType           INTEGER,
		rcCbSESerdesLinkStatus         DeviceStatus,
		rcCbSESerdesLinkConnectedToDevice    Integer32,
		rcCbSESerdesLinkConnectedToSlot      Integer32
		}

rcCbSESerdesLinkId	OBJECT-TYPE
	SYNTAX          Integer32 (1..640)
	MAX-ACCESS      not-accessible
        STATUS          current
        DESCRIPTION     "This ID maps to a particular serdes port number
			 for the identified device.  Here's the mapping:

			 SESerdesLinkId  1  = port 0; Slot 21; Device 1
			 SESerdesLinkId  33 = port 0; Slot 21; Device 2
			 SESerdesLinkId  65 = port 0; Slot 21; Device 3
			 SESerdesLinkId  97 = port 0; Slot 22; Device 1
			 ...
			 SESerdesLinkId 640 = port 31; Slot 26; Device 3"
        ::= { rcCbSESerdesLinkEntry 1 }

rcCbSESerdesLinkType	OBJECT-TYPE
	SYNTAX          INTEGER {
				sci(1),
				sfi(2)
			}
	MAX-ACCESS      read-only
        STATUS          current
        DESCRIPTION     "Link Type of the Serdes interface.  Switch control
		         interface is sci.  Switch forwarding interface is sfi."
        ::= { rcCbSESerdesLinkEntry 2 }

rcCbSESerdesLinkStatus	OBJECT-TYPE
	SYNTAX          DeviceStatus
	MAX-ACCESS      read-only
        STATUS          current
        DESCRIPTION     "Interface Status"
        ::= { rcCbSESerdesLinkEntry 3 }

rcCbSESerdesLinkConnectedToDevice	OBJECT-TYPE
	SYNTAX          Integer32 (1..32)
	MAX-ACCESS      read-only
        STATUS          current
        DESCRIPTION     "The QE2k ID to which the SE/BME ID is attached to."
        ::= { rcCbSESerdesLinkEntry 4 }

rcCbSESerdesLinkConnectedToSlot     OBJECT-TYPE
        SYNTAX          Integer32 (1..32)
        MAX-ACCESS      read-only
        STATUS          current
        DESCRIPTION     "The slot number of the switch fabric card to which the QE2k ID is attached to."
        ::= { rcCbSESerdesLinkEntry 5 }

rcCbSE9600SerdesLinkTable OBJECT-TYPE
        SYNTAX          SEQUENCE OF RcCBSE9600SerdesLinkEntry
        MAX-ACCESS      not-accessible
        STATUS          current
        DESCRIPTION     "Table containing the Fast Serdes Link Information
			for the system."
        ::= { rcCbSwitchFabric 7 }

rcCbSE9600SerdesLinkEntry   OBJECT-TYPE
        SYNTAX          RcCBSE9600SerdesLinkEntry
        MAX-ACCESS      not-accessible
        STATUS          current
        DESCRIPTION     "Entry for an SE based Serdes Link Interface.  
			 The combination of the QE ID and Serdes Link ID
			 uniquely identifies a link."
	INDEX		{ rcCbSE9600SerdesLinkId}
    ::= { rcCbSE9600SerdesLinkTable 1 }

RcCBSE9600SerdesLinkEntry ::= SEQUENCE {
		rcCbSE9600SerdesLinkId             Integer32,
		rcCbSE9600SerdesLinkType           INTEGER,
		rcCbSE9600SerdesLinkStatus         DeviceStatus,
		rcCbSE9600SerdesLinkConnectedToDevice    Integer32,
		rcCbSE9600SerdesLinkConnectedToSlot      Integer32
		}

rcCbSE9600SerdesLinkId	OBJECT-TYPE
	SYNTAX          Integer32 (1..1152)
	MAX-ACCESS      not-accessible
        STATUS          current
        DESCRIPTION     "This ID maps to a particular serdes port number
			 for the identified device.  Here's the mapping:

			 SESerdesLinkId  1   = port 0; Slot 21; Device 1
			 SESerdesLinkId  97  = port 0; Slot 21; Device 2
			 SESerdesLinkId  193 = port 0; Slot 22; Device 1
			 SESerdesLinkId  289 = port 0; Slot 22; Device 2
			 ...
			 SESerdesLinkId 1152 = port 96; Slot 26; Device 2"
        ::= { rcCbSE9600SerdesLinkEntry 1 }

rcCbSE9600SerdesLinkType	OBJECT-TYPE
	SYNTAX          INTEGER {
				sci(1),
				sfi(2)
			}
	MAX-ACCESS      read-only
        STATUS          current
        DESCRIPTION     "Link Type of the Serdes interface.  Switch control
		         interface is sci.  Switch forwarding interface is sfi."
        ::= { rcCbSE9600SerdesLinkEntry 2 }

rcCbSE9600SerdesLinkStatus	OBJECT-TYPE
	SYNTAX          DeviceStatus
	MAX-ACCESS      read-only
        STATUS          current
        DESCRIPTION     "Interface Status"
        ::= { rcCbSE9600SerdesLinkEntry 3 }

rcCbSE9600SerdesLinkConnectedToDevice	OBJECT-TYPE
	SYNTAX          Integer32 (1..32)
	MAX-ACCESS      read-only
        STATUS          current
        DESCRIPTION     "The QE2k ID to which the SE/BME ID is attached to."
        ::= { rcCbSE9600SerdesLinkEntry 4 }

rcCbSE9600SerdesLinkConnectedToSlot OBJECT-TYPE
        SYNTAX          Integer32 (1..12)
        MAX-ACCESS      read-only
        STATUS          current
        DESCRIPTION     "The slot number of the switch fabric card to which the QE2k ID is attached to."
        ::= { rcCbSE9600SerdesLinkEntry 5 }

rcCbSPITable		OBJECT-TYPE
	SYNTAX          SEQUENCE OF RcCBSPIEntry
        MAX-ACCESS      not-accessible
        STATUS          obsolete
        DESCRIPTION     "Table containing the system peripheral interface info."
        ::= { rcCbSwitchFabric 8 }

rcCbSPIEntry	OBJECT-TYPE
        SYNTAX          RcCBSPIEntry
        MAX-ACCESS      not-accessible
        STATUS          obsolete
        DESCRIPTION     "SPI table entry"
	INDEX		{ rcCbSPIId }
    ::= { rcCbSPITable 1 }

RcCBSPIEntry ::= SEQUENCE {
		rcCbSPIId			Integer32,
		rcCbSPIStatus			DeviceStatus
		}

rcCbSPIId		OBJECT-TYPE
	SYNTAX          Integer32 (1..72)
	MAX-ACCESS      not-accessible
        STATUS          obsolete
        DESCRIPTION     "The Index for the SPI Table.  Here is the layout
			 of the IDs in relation to the system:

			Location	ID(s)
			---------------------
			Slot 1:  	1..6
			Slot 2:		7..12
			...
			Slot 12:	57..72

			Current implementation uses the first 6 IDs for each slot.
			"
        ::= { rcCbSPIEntry 1 }

rcCbSPIStatus		OBJECT-TYPE
	SYNTAX          DeviceStatus
	MAX-ACCESS      read-only
        STATUS          obsolete
        DESCRIPTION     "SPI Status"
        ::= { rcCbSPIEntry 2 }

-- Notification

rcLoginUserName OBJECT-TYPE
        SYNTAX        DisplayString (SIZE (1..20))
        MAX-ACCESS    accessible-for-notify
        STATUS        current
        DESCRIPTION   "Used to inidcation the login user name for notification"
        ::= { rcCbNotifications 1 }        

rcLoginHostIpAddress  OBJECT-TYPE
        SYNTAX        IpAddress
        MAX-ACCESS    accessible-for-notify
        STATUS        current
        DESCRIPTION   "Used to inidcation the login host ip address for
		      notification"
        ::= {rcCbNotifications 2 }   

rcSlotType OBJECT-TYPE
        SYNTAX       INTEGER {
                         slot1(1),
                         slot2(2),
                         slot3(3),
                         slot4(4),
                         slot5(5),
                         slot6(6),
                         slot7(7),
                         slot8(8),
                         slot9(9),
                         slot10(10),
                         slot11(11),
                         slot12(12),
                         ps1(13),
                         ps2(14),
                         ps3(15),
                         ps4(16),
                         ps5(17),
                         ps6(18),
                         mid1(19),
                         mid2(20),
                         sf1(21),
                         sf2(22),
                         sf3(23),
                         sf4(24),
                         sf5(25),
                         sf6(26),
                         aux1(27),
                         aux2(28),
                         iofan1(29),
                         iofan2(30),
                         sffan1(31),
                         sffan2(32)
                      }
        MAX-ACCESS    accessible-for-notify
        STATUS        current
        DESCRIPTION   "Used to inidcate the slot type"
        ::= { rcCbNotifications 3 }

rcFanZoneType OBJECT-TYPE
        SYNTAX INTEGER {
                         front(1),
                         rear(2)
                       }
        MAX-ACCESS    accessible-for-notify
        STATUS        current
        DESCRIPTION  "Type of the fan zone."
        ::= { rcCbNotifications 4 }

rcFanTrayId OBJECT-TYPE
        SYNTAX INTEGER (1..2)
        MAX-ACCESS    accessible-for-notify
        STATUS       current
        DESCRIPTION  "Fan tray number in the fan zone"
        ::= { rcCbNotifications 5 }

rcFanUnitId OBJECT-TYPE
        SYNTAX INTEGER (1..8)
        MAX-ACCESS    accessible-for-notify
        STATUS       current
        DESCRIPTION  "Fan unit number in the fan tray"
        ::= { rcCbNotifications 6 }

rcCardTemp OBJECT-TYPE
        SYNTAX        Integer32
        MAX-ACCESS    accessible-for-notify
        STATUS        current
        DESCRIPTION   "Used to inidcate the card temperature"
        ::= { rcCbNotifications 7 }

rcCpuUtilization OBJECT-TYPE
        SYNTAX        Unsigned32
        MAX-ACCESS    accessible-for-notify
        STATUS        current
        DESCRIPTION   "Used to inidcate the CPU utilization"
        ::= { rcCbNotifications 8 }

rcLoginHostAddressType  OBJECT-TYPE
        SYNTAX        InetAddressType
        MAX-ACCESS    accessible-for-notify
        STATUS        current
        DESCRIPTION   "Used to inidcation the login host address type for
		      notification"
        ::= {rcCbNotifications 9 } 
  
rcLoginHostInetAddress  OBJECT-TYPE
        SYNTAX        InetAddress
        MAX-ACCESS    accessible-for-notify
        STATUS        current
        DESCRIPTION   "Used to inidcation the login host inet address for
		      notification"
        ::= {rcCbNotifications 10 } 
  
-- Khi Mibs

rcKhiConfig             OBJECT IDENTIFIER ::= { rcKhi 1 }

rcKhiConfigKhiAdminState    OBJECT-TYPE
    SYNTAX  TruthValue
    MAX-ACCESS  read-write
    STATUS  current   
    DESCRIPTION "Key Health Inidaction, this object is used turn off the KHI feature administratively.  true(1) means On, false(2) means off. By default, it is always set to true(1)."
     DEFVAL { true }
        ::= { rcKhiConfig 1 }

rcKhiConfigKhiBootDelay     OBJECT-TYPE
    SYNTAX  Unsigned32 (0..6)
    MAX-ACCESS  read-write
    STATUS  current
    DESCRIPTION "Time interval from system up and running to start the KHI feature. Set to 0 to disable to the time interval."
     DEFVAL { 5 }     
        ::= { rcKhiConfig 2 }

rcKhiConfigClearAction  OBJECT-TYPE
    SYNTAX  BITS {    
            chassis(0), 
            performance(1),
            port(2), 
            forwarding(3),
            ip(4),    
            protocol(5), 
            mgmt(6)   
        }
    MAX-ACCESS  read-write 
    STATUS  current
    DESCRIPTION "Clear action with bits set. 0 Bit means from left (most significant) bit to right (least significant) bit."
        ::= { rcKhiConfig 3 }

rcKhiConfigPortKhiAdminState OBJECT-TYPE
    SYNTAX  TruthValue
    MAX-ACCESS  read-write
    STATUS  current
    DESCRIPTION "Key Health Indication, this object is used to turn off the Port KHI feature administratively.  true(1) means On, false(2) means off. By default, it is always set to true(1)"
     DEFVAL { true }
        ::= { rcKhiConfig 4 }

rcKhiConfigPerfKhiAdminState OBJECT-TYPE
    SYNTAX  TruthValue
    MAX-ACCESS  read-write
    STATUS  current
    DESCRIPTION "Key Health Indication, this object is used to turn off the Performance KHI feature administratively.  true(1) means On, false(2) means off. By default, it is always set to true(1)"
     DEFVAL { true }
        ::= { rcKhiConfig 5 }

rcKhiConfigChasKhiAdminState OBJECT-TYPE
        SYNTAX        TruthValue
        MAX-ACCESS    read-write
        STATUS        current
        DESCRIPTION   "Key Health Inidcation, this object is used to turn off the Chassis KHI feature
                                     administratively. true(1) means On, false(2) means off. By default, it is always
                                     set to true(1)."
        DEFVAL { true }
        ::= { rcKhiConfig 6 }


rcKhiConfigForwardingKhiAdminState OBJECT-TYPE
    SYNTAX  TruthValue
    MAX-ACCESS  read-write
    STATUS  current
    DESCRIPTION "Key Health Indication, this object is used to turn off the Forwarding KHI feature administratively. true(1) means On, false(2) means off. By default, it is always set to true(1)"
    DEFVAL  { true }
        ::= { rcKhiConfig 7 }

rcKhiConfigForwardingClearSlot OBJECT-TYPE
        SYNTAX  INTEGER (3..12)
        MAX-ACCESS  read-write
        STATUS  current
        DESCRIPTION "Clear KHI Forwarding stats for a particular Slot"
        ::= { rcKhiConfig 9}

rcKhiSlot		OBJECT IDENTIFIER ::= { rcKhi 10 }

-- Slot Performance Table
rcKhiSlotPerfTable OBJECT-TYPE
        SYNTAX        SEQUENCE OF RcKhiSlotPerfEntry
        MAX-ACCESS    not-accessible
        STATUS        current
        DESCRIPTION   "Slot Performance Information"
        ::= { rcKhiSlot 1 }

rcKhiSlotPerfEntry OBJECT-TYPE
        SYNTAX        RcKhiSlotPerfEntry
        MAX-ACCESS    not-accessible
        STATUS        current
        DESCRIPTION   "Slot Performance Entry"
        INDEX         { rcKhiSlotIndex }
	::= { rcKhiSlotPerfTable 1 }

RcKhiSlotPerfEntry ::=
        SEQUENCE {
        rcKhiSlotIndex                Integer32,
		rcKhiSlotCpuCurrentUtil       Integer32,
		rcKhiSlotCpu5MinAve           INTEGER, 
		rcKhiSlotCpu5MinHi            INTEGER,
		rcKhiSlotCpu5MinHiTime        DateAndTime,
		rcKhiSlotMemUsed              Integer32,
		rcKhiSlotMemFree              Integer32,
		rcKhiSlotMemUtil              Integer32,
		rcKhiSlotMem5MinAve           Integer32, 
		rcKhiSlotMem5MinHi            Integer32,
		rcKhiSlotMem5MinHiTime        DateAndTime,
		rcKhiSlotUsedFbuf             Integer32,
		rcKhiSlotFreeFbuf             Integer32,
        rcKhiSlotNoFbuf               Integer32, 
        rcKhiSlotNetStackSysFreeMbuf  Integer32,
        rcKhiSlotNetStackDataFreeMbuf Integer32, 
        rcKhiSlotNetStackSysUsedMbuf  Integer32,
        rcKhiSlotNetStackDataUsedMbuf Integer32, 
        rcKhiSlotNetStackSysSocketMbuf Integer32,  
		rcKhiSlotQHigh                Integer32,
		rcKhiSlotQNormal              Integer32,
		rcKhiSlotFreeQEntries         Integer32
	}

rcKhiSlotIndex OBJECT-TYPE
        SYNTAX        Integer32 (1..12 | 21..26)
        MAX-ACCESS    not-accessible
        STATUS        current
        DESCRIPTION   "An unique index used to identify the slot"
        ::= { rcKhiSlotPerfEntry 1 }

rcKhiSlotCpuCurrentUtil  OBJECT-TYPE
	SYNTAX        Integer32 (1..1000)
        MAX-ACCESS    read-only
        STATUS        current
        DESCRIPTION   "Percentage CPU utilization under current
	         	operating conditions.  Value is in tenth's
                       of a percent."
        ::= { rcKhiSlotPerfEntry 2 }

rcKhiSlotCpu5MinAve  OBJECT-TYPE
	SYNTAX        INTEGER (0..1000)
        MAX-ACCESS    read-only 
        STATUS        current
        DESCRIPTION   "Average percentage CPU utilization over
			the past 5 minutes. Value is in tenth's
                       of a percent."
        ::= { rcKhiSlotPerfEntry 3 }

rcKhiSlotCpu5MinHi  OBJECT-TYPE
	SYNTAX        INTEGER (0..1000)
        MAX-ACCESS    read-only 
        STATUS        current
        DESCRIPTION   "Hi watermark for percentage CPU utilization
			over the past 5 minutes. Value is in tenth's
                       of a percent."
        ::= { rcKhiSlotPerfEntry 4 }

rcKhiSlotCpu5MinHiTime  OBJECT-TYPE
	SYNTAX        DateAndTime
        MAX-ACCESS    read-only
	STATUS        current
        DESCRIPTION   "Last time at which sampling occured."
        ::= { rcKhiSlotPerfEntry 5 }

rcKhiSlotMemUsed  OBJECT-TYPE
	SYNTAX        Integer32
	MAX-ACCESS    read-only
	STATUS        current
        DESCRIPTION   "The amount of DRAM memory consumed in KB."
        ::= { rcKhiSlotPerfEntry 6 }

rcKhiSlotMemFree  OBJECT-TYPE
	SYNTAX        Integer32
	MAX-ACCESS    read-only
	STATUS        current
        DESCRIPTION   "The amount of DRAM memory available in KB."
        ::= { rcKhiSlotPerfEntry 7 }

rcKhiSlotMemUtil  OBJECT-TYPE
        SYNTAX        Integer32 (1..100)
        MAX-ACCESS    read-only
        STATUS        current
        DESCRIPTION   "Current percentage of memory utilization."
        ::= { rcKhiSlotPerfEntry 8 }

rcKhiSlotMem5MinAve  OBJECT-TYPE
	SYNTAX        Integer32 (1..100)
        MAX-ACCESS    read-only
        STATUS        current
        DESCRIPTION   "Average percentage of memory utilization over the
			past 5 minutes."
        ::= { rcKhiSlotPerfEntry 9 }

rcKhiSlotMem5MinHi  OBJECT-TYPE
	SYNTAX        Integer32 (1..100)
        MAX-ACCESS    read-only
        STATUS        current
        DESCRIPTION   "High watermark for percentage memory
			utilization over the past 5 minutes."
        ::= { rcKhiSlotPerfEntry 10 }

rcKhiSlotMem5MinHiTime  OBJECT-TYPE
	SYNTAX        DateAndTime
        MAX-ACCESS    read-only
        STATUS        current
        DESCRIPTION   "The last time memory information was registered."
    	::= { rcKhiSlotPerfEntry 11 }

rcKhiSlotUsedFbuf  OBJECT-TYPE
	SYNTAX        Integer32
        MAX-ACCESS    read-only
        STATUS        current
        DESCRIPTION   "The number of Fbufs in use."
        ::= { rcKhiSlotPerfEntry 12 }

rcKhiSlotFreeFbuf  OBJECT-TYPE
	SYNTAX        Integer32
        MAX-ACCESS    read-only
        STATUS        current
        DESCRIPTION   "The number of Fbufs available."
        ::= { rcKhiSlotPerfEntry 13 }

rcKhiSlotNoFbuf  OBJECT-TYPE
    SYNTAX        Integer32
        MAX-ACCESS    read-only
        STATUS        current
        DESCRIPTION   "The number of times when running out of Fbuff"
        ::= { rcKhiSlotPerfEntry 14 }

rcKhiSlotNetStackSysFreeMbuf  OBJECT-TYPE
	SYNTAX        Integer32
        MAX-ACCESS    read-only
        STATUS        current
        DESCRIPTION   "The number of network stack system Mbufs available."
        ::= { rcKhiSlotPerfEntry 15 }

rcKhiSlotNetStackDataFreeMbuf  OBJECT-TYPE
    SYNTAX        Integer32
        MAX-ACCESS    read-only
        STATUS        current
        DESCRIPTION   "The number of network stack data Mbufs available."
        ::= { rcKhiSlotPerfEntry 16 }

rcKhiSlotNetStackSysUsedMbuf  OBJECT-TYPE
	SYNTAX        Integer32
        MAX-ACCESS    read-only
        STATUS        current
        DESCRIPTION   "The number of network stack system Mbufs in use."
        ::= { rcKhiSlotPerfEntry 17 }

rcKhiSlotNetStackDataUsedMbuf OBJECT-TYPE
    SYNTAX        Integer32
        MAX-ACCESS    read-only
        STATUS        current
        DESCRIPTION   "The number of network stack data Mbufs in use."
        ::= { rcKhiSlotPerfEntry 18 }

rcKhiSlotNetStackSysSocketMbuf OBJECT-TYPE
     SYNTAX        Integer32
        MAX-ACCESS    read-only
        STATUS        current
        DESCRIPTION   "The number of network stack system sockets."
        ::= { rcKhiSlotPerfEntry 19 }

rcKhiSlotQHigh  OBJECT-TYPE
	SYNTAX        Integer32
        MAX-ACCESS    read-only
        STATUS        current
        DESCRIPTION   "The highest number of queue entries consumed
			for system messaging."
        ::= { rcKhiSlotPerfEntry 20 }

rcKhiSlotQNormal  OBJECT-TYPE
	SYNTAX        Integer32
        MAX-ACCESS    read-only
        STATUS        current
        DESCRIPTION   "The current number of queue entries consumed
			for system messaging."
        ::= { rcKhiSlotPerfEntry 21 }

rcKhiSlotFreeQEntries  OBJECT-TYPE
	SYNTAX        Integer32
        MAX-ACCESS    read-only
        STATUS        current
        DESCRIPTION   "The current available number of queue entries
			for system messaging."
        ::= { rcKhiSlotPerfEntry 22 }



-- Slot Process Table
rcKhiSlotProcessTable OBJECT-TYPE
        SYNTAX        SEQUENCE OF RcKhiSlotProcessEntry
        MAX-ACCESS    not-accessible
        STATUS        current
        DESCRIPTION   "CP Process Information"
        ::= { rcKhiSlot 2 }

rcKhiSlotProcessEntry OBJECT-TYPE
        SYNTAX        RcKhiSlotProcessEntry
        MAX-ACCESS    not-accessible
        STATUS        current
        DESCRIPTION   "Slot Process Entry"
        INDEX         { rcKhiSlotIndex,
			rcKhiSlotProcessId }
        ::= { rcKhiSlotProcessTable 1 }

RcKhiSlotProcessEntry ::=
        SEQUENCE {
		rcKhiSlotProcessId            Integer32,
        rcKhiSlotProcessParentId      Integer32,
		rcKhiSlotProcessName          DisplayString,
		rcKhiSlotProcessVmSize        Integer32,
		rcKhiSlotProcessVmLck         Integer32,
		rcKhiSlotProcessVmRss         Integer32,
		rcKhiSlotProcessVmData        Integer32,
		rcKhiSlotProcessVmStk         Integer32,
		rcKhiSlotProcessVmExe         Integer32,
		rcKhiSlotProcessVmLib         Integer32
	}

rcKhiSlotProcessId  OBJECT-TYPE
	SYNTAX        Integer32
        MAX-ACCESS    not-accessible
        STATUS        current
        DESCRIPTION   "Process ID"
        ::= { rcKhiSlotProcessEntry 1}

rcKhiSlotProcessParentId  OBJECT-TYPE
	SYNTAX        Integer32
        MAX-ACCESS    read-only
        STATUS        current
        DESCRIPTION   "Parent Process ID"
        ::= { rcKhiSlotProcessEntry 2 }


rcKhiSlotProcessName  OBJECT-TYPE
	SYNTAX        DisplayString (SIZE(0..80))
        MAX-ACCESS    read-only
        STATUS        current
        DESCRIPTION   "Name of the process running"
        ::= { rcKhiSlotProcessEntry 3 }

rcKhiSlotProcessVmSize OBJECT-TYPE
        SYNTAX        Integer32
        MAX-ACCESS    read-only
        STATUS        current
        DESCRIPTION   "The size of the virtual memory allocated to the process"
        ::= { rcKhiSlotProcessEntry 4 }

rcKhiSlotProcessVmLck OBJECT-TYPE
        SYNTAX        Integer32
        MAX-ACCESS    read-only
        STATUS        current
        DESCRIPTION   "The amount of locked memory"
        ::= { rcKhiSlotProcessEntry 5 }

rcKhiSlotProcessVmRss OBJECT-TYPE
        SYNTAX        Integer32
        MAX-ACCESS    read-only
        STATUS        current
        DESCRIPTION   "The amount of memory mapped in RAM ( instead of swapped out) "
        ::= { rcKhiSlotProcessEntry 6 }

rcKhiSlotProcessVmData OBJECT-TYPE
        SYNTAX        Integer32
        MAX-ACCESS    read-only
        STATUS        current
        DESCRIPTION   "The size of the Data segment"
        ::= { rcKhiSlotProcessEntry 7 }

rcKhiSlotProcessVmStk OBJECT-TYPE
        SYNTAX        Integer32
        MAX-ACCESS    read-only
        STATUS        current
        DESCRIPTION   "The stack size"
        ::= { rcKhiSlotProcessEntry 8 }

rcKhiSlotProcessVmExe OBJECT-TYPE
        SYNTAX        Integer32
        MAX-ACCESS    read-only
        STATUS        current
        DESCRIPTION   "The size of the executable segment"
        ::= { rcKhiSlotProcessEntry 9 }

rcKhiSlotProcessVmLib OBJECT-TYPE
        SYNTAX        Integer32
        MAX-ACCESS    read-only
        STATUS        current
        DESCRIPTION   "The size of the library code"
        ::= { rcKhiSlotProcessEntry 10 }


-- Slot Task Info

rcKhiSlotPThreadTable OBJECT-TYPE
        SYNTAX        SEQUENCE OF RcKhiSlotPThreadEntry
        MAX-ACCESS    not-accessible
        STATUS        current
        DESCRIPTION   "Slot pthread information"
        ::= { rcKhiSlot 3 }

rcKhiSlotPThreadEntry OBJECT-TYPE
        SYNTAX        RcKhiSlotPThreadEntry
        MAX-ACCESS    not-accessible
        STATUS        current
        DESCRIPTION   "Slot pthread entry"
        INDEX         { rcKhiSlotIndex,
                        rcKhiSlotProcessId,
                        rcKhiSlotPThreadTaskId }
        ::= { rcKhiSlotPThreadTable 1 }

RcKhiSlotPThreadEntry ::=
        SEQUENCE {
            rcKhiSlotPThreadTaskId               Integer32,
            rcKhiSlotPThreadName          DisplayString,
            rcKhiSlotPThreadCpuCurrentUtil       Integer32,
            rcKhiSlotPThreadCpu5MinAve           Integer32, 
            rcKhiSlotPThreadCpu5MinHi            Integer32,
            rcKhiSlotPthread5MinHiTime           DateAndTime
           }
rcKhiSlotPThreadTaskId  OBJECT-TYPE
    SYNTAX        Integer32
    MAX-ACCESS    not-accessible
    STATUS        current
    DESCRIPTION   "Task ID"
    ::= { rcKhiSlotPThreadEntry 1 }

rcKhiSlotPThreadName  OBJECT-TYPE
    SYNTAX        DisplayString (SIZE(0..80))
    MAX-ACCESS    read-only
    STATUS        current
    DESCRIPTION   "Name of the process running"
    ::= { rcKhiSlotPThreadEntry 2 }

rcKhiSlotPThreadCpuCurrentUtil  OBJECT-TYPE
    SYNTAX        Integer32 (1..1000)
    MAX-ACCESS    read-only
    STATUS        current
    DESCRIPTION   "Percentage CPU utilization under current
                   operating conditions.  Value is in tenth's
                   of a percent."
    ::= { rcKhiSlotPThreadEntry 3 }

rcKhiSlotPThreadCpu5MinAve  OBJECT-TYPE
    SYNTAX        Integer32 (0..1000)
    MAX-ACCESS    read-only 
    STATUS        current
    DESCRIPTION   "Average percentage CPU utilization over
                   the past 5 minutes.  Value is in tenth's
                   of a percent."
    ::= { rcKhiSlotPThreadEntry 4 }

rcKhiSlotPThreadCpu5MinHi  OBJECT-TYPE
     SYNTAX        Integer32 (0..1000)
     MAX-ACCESS    read-only  
     STATUS        current
     DESCRIPTION   "Hi watermark for percentage CPU utilization
                    over the past 5 minutes.  Value is in tenth's
                    of a percent."
     ::= { rcKhiSlotPThreadEntry 5 }

rcKhiSlotPthread5MinHiTime  OBJECT-TYPE
     SYNTAX        DateAndTime
     MAX-ACCESS    read-only
     STATUS        current
     DESCRIPTION   "Last time at which sampling occured."
     ::= { rcKhiSlotPThreadEntry 6 }

rcKhiForwardingCb    OBJECT IDENTIFIER ::= { rcKhi 11 }


-- KHI Forwarding Interface Table

rcKhiForwardingCbIfTable  OBJECT-TYPE
     SYNTAX          SEQUENCE OF RcKhiForwardingCbIfEntry
     MAX-ACCESS      not-accessible
     STATUS          current
     DESCRIPTION     "Forwarding Interface Key Health Indicator MIB - All Cobalt Blue Data."
     ::= { rcKhiForwardingCb 1 }

rcKhiForwardingCbIfEntry OBJECT-TYPE
     SYNTAX          RcKhiForwardingCbIfEntry
     MAX-ACCESS      not-accessible
     STATUS          current
     DESCRIPTION     "Forwarding Interface KHI - Cobalt Blue table entry."
     INDEX           { rcKhiForwardingCbIfIndex }
     ::= { rcKhiForwardingCbIfTable 1 }

RcKhiForwardingCbIfEntry ::=
     SEQUENCE {
     rcKhiForwardingCbIfIndex           InterfaceIndex,
     rcKhiForwardingCbIfRxOk            Counter64,
     rcKhiForwardingCbIfTxOk            Counter64,
     rcKhiForwardingCbIfRxErr           Counter64,
     rcKhiForwardingCbIfTxErr           Counter64,
     rcKhiForwardingCbIfRdbgc0          Counter64,
     rcKhiForwardingCbIfRdbgc0Mask      Counter64,
     rcKhiForwardingCbIfTdbgc0          Counter64,
     rcKhiForwardingCbIfTdbgc0Mask      Counter64,
     rcKhiForwardingCbIfK2IpmcDrops     Counter64
    }

rcKhiForwardingCbIfIndex  OBJECT-TYPE
     SYNTAX         InterfaceIndex
     MAX-ACCESS     not-accessible
     STATUS         current
     DESCRIPTION    "Interface index for CB's KHI Forwarding data.
                     Indicies are essentially port based."
     ::= { rcKhiForwardingCbIfEntry 1 }

rcKhiForwardingCbIfRxOk  OBJECT-TYPE
     SYNTAX         Counter64
     MAX-ACCESS     read-only
     STATUS         current
     DESCRIPTION    "Receieve OK Packets"
     ::= { rcKhiForwardingCbIfEntry 2 }

rcKhiForwardingCbIfTxOk  OBJECT-TYPE
     SYNTAX         Counter64
     MAX-ACCESS     read-only
     STATUS         current
     DESCRIPTION    "Transmit OK Packets"
     ::= { rcKhiForwardingCbIfEntry 3 }

rcKhiForwardingCbIfRxErr  OBJECT-TYPE
     SYNTAX         Counter64
     MAX-ACCESS     read-only
     STATUS         current
     DESCRIPTION    "Receive Error Packets"
     ::= { rcKhiForwardingCbIfEntry 4 }

rcKhiForwardingCbIfTxErr  OBJECT-TYPE
     SYNTAX         Counter64
     MAX-ACCESS     read-only
     STATUS         current
     DESCRIPTION    "Transmit Error Packets"
     ::= { rcKhiForwardingCbIfEntry 5 }

rcKhiForwardingCbIfRdbgc0 OBJECT-TYPE
     SYNTAX         Counter64
     MAX-ACCESS     read-only
     STATUS         current
     DESCRIPTION    "RDBGC0 Packets"
     ::= { rcKhiForwardingCbIfEntry 6 }

rcKhiForwardingCbIfRdbgc0Mask OBJECT-TYPE
     SYNTAX         Counter64
     MAX-ACCESS     read-only
     STATUS         current
     DESCRIPTION    "RDBGC0 Mask"
     ::= { rcKhiForwardingCbIfEntry 7 }

rcKhiForwardingCbIfTdbgc0 OBJECT-TYPE
     SYNTAX         Counter64
     MAX-ACCESS     read-only
     STATUS         current
     DESCRIPTION    "TDBGC0 Packets"
     ::= { rcKhiForwardingCbIfEntry 8 }

rcKhiForwardingCbIfTdbgc0Mask OBJECT-TYPE
     SYNTAX         Counter64
     MAX-ACCESS     read-only
     STATUS         current
     DESCRIPTION    "TDBGC0 Mask"
     ::= { rcKhiForwardingCbIfEntry 9 }

rcKhiForwardingCbIfK2IpmcDrops OBJECT-TYPE
     SYNTAX         Counter64
     MAX-ACCESS     read-only
     STATUS         current
     DESCRIPTION    "IP Multicast Drops"
     ::= { rcKhiForwardingCbIfEntry 10 }


-- KHI Forwarding Mac-Higig table

rcKhiForwardingCbMachigigTable OBJECT-TYPE
     SYNTAX          SEQUENCE OF RcKhiForwardingCbMachigigEntry
     MAX-ACCESS      not-accessible
     STATUS          current
     DESCRIPTION     "Forwarding Mac-Higig Key Health Indicator MIB - All Cobalt Blue Data."
     ::= { rcKhiForwardingCb 2}

rcKhiForwardingCbMachigigEntry OBJECT-TYPE
     SYNTAX          RcKhiForwardingCbMachigigEntry
     MAX-ACCESS      not-accessible
     STATUS          current
     DESCRIPTION     "Forwarding Mac-Higig KHI - Cobalt Blue table entry."
     INDEX           { rcKhiForwardingCbMachigigIndex }
     ::= { rcKhiForwardingCbMachigigTable 1 }

RcKhiForwardingCbMachigigEntry ::=
     SEQUENCE {	
	rcKhiForwardingCbMachigigIndex        INTEGER,
     	rcKhiForwardingCbMachigigMacK2        Counter64,
     	rcKhiForwardingCbMachigigMacK2Mac     Counter64,
     	rcKhiForwardingCbMachigigRDGBC0       Counter64,
     	rcKhiForwardingCbMachigigRDGBC0mask   Counter64,
     	rcKhiForwardingCbMachigigTDGBC0       Counter64,
     	rcKhiForwardingCbMachigigTDGBC0mask   Counter64,
     	rcKhiForwardingCbMachigigIFPDOSDrops  Counter64
	}

rcKhiForwardingCbMachigigIndex  OBJECT-TYPE
     SYNTAX         INTEGER (1..60)
     MAX-ACCESS     not-accessible
     STATUS         current
     DESCRIPTION    "Index for CB's Forwarding MAc-Higig Health data.  There are 6 
                    indicies reserved on a per slot basis.  Depending on
                    the card present and the data being requested not all 
                    indicies may be used."
     ::= { rcKhiForwardingCbMachigigEntry 1 } 

rcKhiForwardingCbMachigigMacK2    OBJECT-TYPE
     SYNTAX         Counter64
     MAX-ACCESS     read-only
     STATUS         current
     DESCRIPTION    ""
     ::= { rcKhiForwardingCbMachigigEntry 2 }

rcKhiForwardingCbMachigigMacK2Mac     OBJECT-TYPE
     SYNTAX         Counter64
     MAX-ACCESS     read-only
     STATUS         current
     DESCRIPTION    ""
     ::= { rcKhiForwardingCbMachigigEntry 3 }

rcKhiForwardingCbMachigigRDGBC0    OBJECT-TYPE
     SYNTAX         Counter64
     MAX-ACCESS     read-only
     STATUS         current
     DESCRIPTION    ""
     ::= { rcKhiForwardingCbMachigigEntry 4 }

rcKhiForwardingCbMachigigRDGBC0mask     OBJECT-TYPE
     SYNTAX         Counter64
     MAX-ACCESS     read-only
     STATUS         current
     DESCRIPTION    ""
     ::= { rcKhiForwardingCbMachigigEntry 5 }

rcKhiForwardingCbMachigigTDGBC0     OBJECT-TYPE
     SYNTAX         Counter64
     MAX-ACCESS     read-only
     STATUS         current
     DESCRIPTION    ""
     ::= { rcKhiForwardingCbMachigigEntry 6 }

rcKhiForwardingCbMachigigTDGBC0mask     OBJECT-TYPE
     SYNTAX         Counter64
     MAX-ACCESS     read-only
     STATUS         current
     DESCRIPTION    ""
     ::= { rcKhiForwardingCbMachigigEntry 7 }

rcKhiForwardingCbMachigigIFPDOSDrops    OBJECT-TYPE
     SYNTAX         Counter64
     MAX-ACCESS     read-only
     STATUS         current
     DESCRIPTION    ""
     ::= { rcKhiForwardingCbMachigigEntry 8 }


-- KHI Forwarding K2 table

rcKhiForwardingCbK2Table OBJECT-TYPE
     SYNTAX          SEQUENCE OF RcKhiForwardingCbK2Entry
     MAX-ACCESS      not-accessible
     STATUS          current
     DESCRIPTION     "Forwarding K2 Key Health Indicator MIB - All Cobalt Blue Data."
     ::= { rcKhiForwardingCb 3}

rcKhiForwardingCbK2Entry OBJECT-TYPE
     SYNTAX          RcKhiForwardingCbK2Entry
     MAX-ACCESS      not-accessible
     STATUS          current
     DESCRIPTION     "Forwarding K2 KHI - Cobalt Blue table entry."
     INDEX           { rcKhiForwardingCbK2Index }
     ::= { rcKhiForwardingCbK2Table 1 }

RcKhiForwardingCbK2Entry ::=
     SEQUENCE {	
	rcKhiForwardingCbK2Index           INTEGER,
	rcKhiForwardingCbK2MacK2           Counter64,
     	rcKhiForwardingCbK2Zagros          Counter64,
     	rcKhiForwardingCbK2ZagrosK2        Counter64,
     	rcKhiForwardingCbK2Mac             Counter64,
     	rcKhiForwardingCbK2MacK2Err        Counter64,
     	rcKhiForwardingCbK2ZagrosErr       Counter64,
     	rcKhiForwardingCbK2ZagrosK2Err     Counter64,
     	rcKhiForwardingCbK2MacErr          Counter64
}

rcKhiForwardingCbK2Index  OBJECT-TYPE
     SYNTAX         INTEGER (1..60)
     MAX-ACCESS     not-accessible
     STATUS         current
     DESCRIPTION    "Index for CB's Forwarding K2 Health data.  There are 6 
                    indicies reserved on a per slot basis.  Depending on
                    the card present and the data being requested not all 
                    indicies may be used."
     ::= { rcKhiForwardingCbK2Entry 1 } 

rcKhiForwardingCbK2MacK2    OBJECT-TYPE
     SYNTAX         Counter64
     MAX-ACCESS     read-only
     STATUS         current
     DESCRIPTION    ""
     ::= { rcKhiForwardingCbK2Entry 2 }

rcKhiForwardingCbK2Zagros    OBJECT-TYPE
     SYNTAX         Counter64
     MAX-ACCESS     read-only
     STATUS         current
     DESCRIPTION    ""
     ::= { rcKhiForwardingCbK2Entry 3 }

rcKhiForwardingCbK2ZagrosK2    OBJECT-TYPE
     SYNTAX         Counter64
     MAX-ACCESS     read-only
     STATUS         current
     DESCRIPTION    ""
     ::= { rcKhiForwardingCbK2Entry 4 }

rcKhiForwardingCbK2Mac    OBJECT-TYPE
     SYNTAX         Counter64
     MAX-ACCESS     read-only
     STATUS         current
     DESCRIPTION    ""
     ::= { rcKhiForwardingCbK2Entry 5 }

rcKhiForwardingCbK2MacK2Err    OBJECT-TYPE
     SYNTAX         Counter64
     MAX-ACCESS     read-only
     STATUS         current
     DESCRIPTION    ""
     ::= { rcKhiForwardingCbK2Entry 6 }

rcKhiForwardingCbK2ZagrosErr    OBJECT-TYPE
     SYNTAX         Counter64
     MAX-ACCESS     read-only
     STATUS         current
     DESCRIPTION    ""
     ::= { rcKhiForwardingCbK2Entry 7 }

rcKhiForwardingCbK2ZagrosK2Err    OBJECT-TYPE
     SYNTAX         Counter64
     MAX-ACCESS     read-only
     STATUS         current
     DESCRIPTION    ""
     ::= { rcKhiForwardingCbK2Entry 8 }

rcKhiForwardingCbK2MacErr    OBJECT-TYPE
     SYNTAX         Counter64
     MAX-ACCESS     read-only
     STATUS         current
     DESCRIPTION    ""
     ::= { rcKhiForwardingCbK2Entry 9 }


-- KHI Forwarding Zagros table

rcKhiForwardingCbZagrosTable  OBJECT-TYPE
     SYNTAX          SEQUENCE OF RcKhiForwardingCbZagrosEntry
     MAX-ACCESS      not-accessible
     STATUS          current
     DESCRIPTION     "Zagros Forwarding Zagros Key Health Indicator MIB - All Cobalt Blue Data."
     ::= { rcKhiForwardingCb 4 }

rcKhiForwardingCbZagrosEntry OBJECT-TYPE
     SYNTAX          RcKhiForwardingCbZagrosEntry
     MAX-ACCESS      not-accessible
     STATUS          current
     DESCRIPTION     "Zagros Forwarding KHI - Cobalt Blue table entry."
     INDEX           { rcKhiForwardingCbZagrosIndex }
     ::= { rcKhiForwardingCbZagrosTable 1 }

RcKhiForwardingCbZagrosEntry ::=
     SEQUENCE {
	rcKhiForwardingCbZagrosIndex                    INTEGER,
     	rcKhiForwardingCbZagrosK2Zagros                 Counter64,
     	rcKhiForwardingCbZagrosRsp                      Counter64,
     	rcKhiForwardingCbZagrosQe          		Counter64,
     	rcKhiForwardingCbZagrosQeZagros    		Counter64,
     	rcKhiForwardingCbZagrosK2          		Counter64,
     	rcKhiForwardingCbZagrosPmmPoolLo   		Counter64,
     	rcKhiForwardingCbZagrosPmmPoolHigh 		Counter64,
     	rcKhiForwardingCbZagrosPmmRspDropCounters 	Counter64,
     	rcKhiForwardingCbZagrosPmmoutputDropCount 	Counter64,
     	rcKhiForwardingCbZagrosPmmAdmissionRspDropCount Counter64,
     	rcKhiForwardingCbZagrosPmmAdmissionErrDropCount Counter64,
     	rcKhiForwardingCbZagrosPmmPool1Drop 		Counter64,
     	rcKhiForwardingCbZagrosPmmPool2Drop 		Counter64,
     	rcKhiForwardingCbZagrosPmmPool3Drop 		Counter64,
     	rcKhiForwardingCbZagrosPmmPool4Drop 		Counter64,
     	rcKhiForwardingCbZagrosPmmPool5Drop 		Counter64,
     	rcKhiForwardingCbZagrosPmmPool6Drop 		Counter64,
     	rcKhiForwardingCbZagrosPmmPool7Drop 		Counter64,
     	rcKhiForwardingCbZagrosPmmPool8Drop 		Counter64,
     	rcKhiForwardingCbZagrosPmmPool9Drop 		Counter64,
     	rcKhiForwardingCbZagrosPmmPool10Drop 		Counter64,
     	rcKhiForwardingCbZagrosHbeCommandDrops 		Counter64,
     	rcKhiForwardingCbZagrosTcamSearchError 		Counter64,
     	rcKhiForwardingCbZagrosEhpAllPortDownIstCounter Counter64,
     	rcKhiForwardingCbZagrosEhpAllPortDownMltCounter Counter64,
     	rcKhiForwardingCbZagrosEhpErrorDropCounter 	Counter64,
    	rcKhiForwardingCbZagrosIgrFilterDropCount 	Counter64,
     	rcKhiForwardingCbZagrosZapTxCtl 		Counter64,
     	rcKhiForwardingCbZagrosZapTxDat 		Counter64,
     	rcKhiForwardingCbZagrosZapRxCtl 		Counter64,
     	rcKhiForwardingCbZagrosZapRxDat 		Counter64,
     	rcKhiForwardingCbZagrosZapTxHbe 		Counter64,
     	rcKhiForwardingCbZagrosTcamSearchVal 		Counter64,
     	rcKhiForwardingCbZagrosEmbDropCount 		Counter64,
     	rcKhiForwardingCbZagrosEhpFilterDropCount 	Counter64,
     	rcKhiForwardingCbZagrosEgrIpmcDropCount 	Counter64,
     	rcKhiForwardingCbZagrosEgressEsb1Count 		Counter64,
     	rcKhiForwardingCbZagrosEgressEsb2Count 		Counter64,
     	rcKhiForwardingCbZagrosEgressEsb3Count 		Counter64,
     	rcKhiForwardingCbZagrosEgressEsb4Count 		Counter64,
     	rcKhiForwardingCbZagrosEgressEsb5Count 		Counter64,
     	rcKhiForwardingCbZagrosEgressEsb6Count 		Counter64,
     	rcKhiForwardingCbZagrosRspRx 			Counter64,
     	rcKhiForwardingCbZagrosOpTx 			Counter64,
     	rcKhiForwardingCbZagrosRspTx 			Counter64,
     	rcKhiForwardingCbZagrosCifRqCount 		Counter64,
     	rcKhiForwardingCbZagrosCifRsCounter 		Counter64,
        rcKhiForwardingCbZagrosPage1Count               Counter64, --obsolete
        rcKhiForwardingCbZagrosPage2Count               Counter64, --obsolete
        rcKhiForwardingCbZagrosPage3Count               Counter64, --obsolete
        rcKhiForwardingCbZagrosPage4Count               Counter64, --obsolete
        rcKhiForwardingCbZagrosPage5Count               Counter64, --obsolete
        rcKhiForwardingCbZagrosPage6Count               Counter64, --obsolete
        rcKhiForwardingCbZagrosPage7Count               Counter64, --obsolete
        rcKhiForwardingCbZagrosPage8Count               Counter64, --obsolete
        rcKhiForwardingCbZagrosPage9Count               Counter64, --obsolete
        rcKhiForwardingCbZagrosPage10Count              Counter64, --obsolete
        rcKhiForwardingCbZagrosShPp                     Counter64, --obsolete
        rcKhiForwardingCbZagrosFpCounts                 Counter64, --obsolete
     	rcKhiForwardingCbZagrosRspPlcThresholdReg 	Counter64,
     	rcKhiForwardingCbZagrosRePlc 			Counter64,
        rcKhiForwardingCbZagrosNumPools                 Counter64,
        rcKhiForwardingCbZagrosFpCntOPA                 Counter32,
        rcKhiForwardingCbZagrosFpCntRPA                 Counter32,
        rcKhiForwardingCbZagrosFpCntFPM                 Counter32,
        rcKhiForwardingCbZagrosRspPlcPktCntPeak         Counter32,
        rcKhiForwardingCbZagrosRspPlcPktCntCurr         Counter32,
        rcKhiForwardingCbZagrosRePlcPktCntPeak          Counter32,
        rcKhiForwardingCbZagrosRePlcPktCntCurr          Counter32,
        rcKhiForwardingCbZagrosShPpPeak                 Counter32,
        rcKhiForwardingCbZagrosShPpCurr                 Counter32,
        rcKhiForwardingCbZagrosEgressMultiCastPeak      Counter32,
        rcKhiForwardingCbZagrosEgressMultiCastCurr      Counter32,
        rcKhiForwardingCbZagrosEgressOOBPeak            Counter32,
        rcKhiForwardingCbZagrosEgressOOBCurr            Counter32,
        rcKhiForwardingCbZagrosIngressHeartbeatPeak     Counter32,
        rcKhiForwardingCbZagrosIngressHeartbeatCurr     Counter32,
        rcKhiForwardingCbZagrosIngressCOPInsertPeak     Counter32,
        rcKhiForwardingCbZagrosIngressCOPInsertCurr     Counter32,
        rcKhiForwardingCbZagrosIngressEfCtlPeak         Counter32,
        rcKhiForwardingCbZagrosIngressEfCtlCurr         Counter32,
        rcKhiForwardingCbZagrosIngressAfBePeak          Counter32,
        rcKhiForwardingCbZagrosIngressAfBeCurr          Counter32,
        rcKhiForwardingCbZagrosEgressL2BcUcPeak         Counter32,
        rcKhiForwardingCbZagrosEgressL2BcUcCurr         Counter32,
        rcKhiForwardingCbZagrosEgressMirrorPeak         Counter32,
        rcKhiForwardingCbZagrosEgressMirrorCurr         Counter32,
        rcKhiForwardingCbZagrosPool9Peak                Counter32,
        rcKhiForwardingCbZagrosPool9Curr                Counter32

}

rcKhiForwardingCbZagrosIndex  OBJECT-TYPE
     SYNTAX         INTEGER (1..60)
     MAX-ACCESS     not-accessible
     STATUS         current
     DESCRIPTION    "Index for CB's Forwarding Zagros Health data.  There are 6 
                    indicies reserved on a per slot basis.  Depending on
                    the card present and the data being requested not all 
                    indicies may be used."
     ::= { rcKhiForwardingCbZagrosEntry 1 } 

rcKhiForwardingCbZagrosK2Zagros   OBJECT-TYPE
     SYNTAX         Counter64
     MAX-ACCESS     read-only
     STATUS         current
     DESCRIPTION    ""
     ::= { rcKhiForwardingCbZagrosEntry 2 }

rcKhiForwardingCbZagrosRsp   OBJECT-TYPE
     SYNTAX         Counter64
     MAX-ACCESS     read-only
     STATUS         current
     DESCRIPTION    ""
     ::= { rcKhiForwardingCbZagrosEntry 3 }

rcKhiForwardingCbZagrosQe   OBJECT-TYPE
     SYNTAX         Counter64
     MAX-ACCESS     read-only
     STATUS         current
     DESCRIPTION    ""
     ::= { rcKhiForwardingCbZagrosEntry 4 }

rcKhiForwardingCbZagrosQeZagros    OBJECT-TYPE
     SYNTAX         Counter64
     MAX-ACCESS     read-only
     STATUS         current
     DESCRIPTION    ""
     ::= { rcKhiForwardingCbZagrosEntry 5 }

rcKhiForwardingCbZagrosK2    OBJECT-TYPE
     SYNTAX         Counter64
     MAX-ACCESS     read-only
     STATUS         current
     DESCRIPTION    ""
     ::= { rcKhiForwardingCbZagrosEntry 6 }

rcKhiForwardingCbZagrosPmmPoolLo   OBJECT-TYPE
     SYNTAX         Counter64
     MAX-ACCESS     read-only
     STATUS         current
     DESCRIPTION    ""
     ::= { rcKhiForwardingCbZagrosEntry 7 }

rcKhiForwardingCbZagrosPmmPoolHigh   OBJECT-TYPE
     SYNTAX         Counter64
     MAX-ACCESS     read-only
     STATUS         current
     DESCRIPTION    ""
     ::= { rcKhiForwardingCbZagrosEntry 8 }

rcKhiForwardingCbZagrosPmmRspDropCounters   OBJECT-TYPE
     SYNTAX         Counter64
     MAX-ACCESS     read-only
     STATUS         current
     DESCRIPTION    ""
     ::= { rcKhiForwardingCbZagrosEntry 9 }

rcKhiForwardingCbZagrosPmmoutputDropCount   OBJECT-TYPE
     SYNTAX         Counter64
     MAX-ACCESS     read-only
     STATUS         current
     DESCRIPTION    ""
     ::= { rcKhiForwardingCbZagrosEntry 10 }

rcKhiForwardingCbZagrosPmmAdmissionRspDropCount   OBJECT-TYPE
     SYNTAX         Counter64
     MAX-ACCESS     read-only
     STATUS         current
     DESCRIPTION    ""
     ::= { rcKhiForwardingCbZagrosEntry 11 }

rcKhiForwardingCbZagrosPmmAdmissionErrDropCount   OBJECT-TYPE
     SYNTAX         Counter64
     MAX-ACCESS     read-only
     STATUS         current
     DESCRIPTION    ""
     ::= { rcKhiForwardingCbZagrosEntry 12 }

rcKhiForwardingCbZagrosPmmPool1Drop   OBJECT-TYPE
     SYNTAX         Counter64
     MAX-ACCESS     read-only
     STATUS         current
     DESCRIPTION    ""
     ::= { rcKhiForwardingCbZagrosEntry 13 }

rcKhiForwardingCbZagrosPmmPool2Drop   OBJECT-TYPE
     SYNTAX         Counter64
     MAX-ACCESS     read-only
     STATUS         current
     DESCRIPTION    ""
     ::= { rcKhiForwardingCbZagrosEntry 14 }

rcKhiForwardingCbZagrosPmmPool3Drop   OBJECT-TYPE
     SYNTAX         Counter64
     MAX-ACCESS     read-only
     STATUS         current
     DESCRIPTION    ""
     ::= { rcKhiForwardingCbZagrosEntry 15 }

rcKhiForwardingCbZagrosPmmPool4Drop   OBJECT-TYPE
     SYNTAX         Counter64
     MAX-ACCESS     read-only
     STATUS         current
     DESCRIPTION    ""
     ::= { rcKhiForwardingCbZagrosEntry 16 }

rcKhiForwardingCbZagrosPmmPool5Drop   OBJECT-TYPE
     SYNTAX         Counter64
     MAX-ACCESS     read-only
     STATUS         current
     DESCRIPTION    ""
     ::= { rcKhiForwardingCbZagrosEntry 17 }

rcKhiForwardingCbZagrosPmmPool6Drop   OBJECT-TYPE
     SYNTAX         Counter64
     MAX-ACCESS     read-only
     STATUS         current
     DESCRIPTION    ""
     ::= { rcKhiForwardingCbZagrosEntry 18 }

rcKhiForwardingCbZagrosPmmPool7Drop   OBJECT-TYPE
     SYNTAX         Counter64
     MAX-ACCESS     read-only
     STATUS         current
     DESCRIPTION    ""
     ::= { rcKhiForwardingCbZagrosEntry 19 }

rcKhiForwardingCbZagrosPmmPool8Drop   OBJECT-TYPE
     SYNTAX         Counter64
     MAX-ACCESS     read-only
     STATUS         current
     DESCRIPTION    ""
     ::= { rcKhiForwardingCbZagrosEntry 20 }

rcKhiForwardingCbZagrosPmmPool9Drop   OBJECT-TYPE
     SYNTAX         Counter64
     MAX-ACCESS     read-only
     STATUS         current
     DESCRIPTION    ""
     ::= { rcKhiForwardingCbZagrosEntry 21 }

rcKhiForwardingCbZagrosPmmPool10Drop   OBJECT-TYPE
     SYNTAX         Counter64
     MAX-ACCESS     read-only
     STATUS         current
     DESCRIPTION    ""
     ::= { rcKhiForwardingCbZagrosEntry 22 }

rcKhiForwardingCbZagrosHbeCommandDrops   OBJECT-TYPE
     SYNTAX         Counter64
     MAX-ACCESS     read-only
     STATUS         current
     DESCRIPTION    ""
     ::= { rcKhiForwardingCbZagrosEntry 23 }

rcKhiForwardingCbZagrosTcamSearchError   OBJECT-TYPE
     SYNTAX         Counter64
     MAX-ACCESS     read-only
     STATUS         current
     DESCRIPTION    ""
     ::= { rcKhiForwardingCbZagrosEntry 24 }

rcKhiForwardingCbZagrosEhpAllPortDownIstCounter   OBJECT-TYPE
     SYNTAX         Counter64
     MAX-ACCESS     read-only
     STATUS         current
     DESCRIPTION    ""
     ::= { rcKhiForwardingCbZagrosEntry 25 }

rcKhiForwardingCbZagrosEhpAllPortDownMltCounter   OBJECT-TYPE
     SYNTAX         Counter64
     MAX-ACCESS     read-only
     STATUS         current
     DESCRIPTION    ""
     ::= { rcKhiForwardingCbZagrosEntry 26 }

rcKhiForwardingCbZagrosEhpErrorDropCounter   OBJECT-TYPE
     SYNTAX         Counter64
     MAX-ACCESS     read-only
     STATUS         current
     DESCRIPTION    ""
     ::= { rcKhiForwardingCbZagrosEntry 27 }

rcKhiForwardingCbZagrosIgrFilterDropCount  OBJECT-TYPE
     SYNTAX         Counter64
     MAX-ACCESS     read-only
     STATUS         current
     DESCRIPTION    ""
     ::= { rcKhiForwardingCbZagrosEntry 28 }

rcKhiForwardingCbZagrosZapTxCtl   OBJECT-TYPE
     SYNTAX         Counter64
     MAX-ACCESS     read-only
     STATUS         current
     DESCRIPTION    ""
     ::= { rcKhiForwardingCbZagrosEntry 29 }

rcKhiForwardingCbZagrosZapTxDat   OBJECT-TYPE
     SYNTAX         Counter64
     MAX-ACCESS     read-only
     STATUS         current
     DESCRIPTION    ""
     ::= { rcKhiForwardingCbZagrosEntry 30 }

rcKhiForwardingCbZagrosZapRxCtl   OBJECT-TYPE
     SYNTAX         Counter64
     MAX-ACCESS     read-only
     STATUS         current
     DESCRIPTION    ""
     ::= { rcKhiForwardingCbZagrosEntry 31 }

rcKhiForwardingCbZagrosZapRxDat   OBJECT-TYPE
     SYNTAX         Counter64
     MAX-ACCESS     read-only
     STATUS         current
     DESCRIPTION    ""
     ::= { rcKhiForwardingCbZagrosEntry 32 }

rcKhiForwardingCbZagrosZapTxHbe   OBJECT-TYPE
     SYNTAX         Counter64
     MAX-ACCESS     read-only
     STATUS         current
     DESCRIPTION    ""
     ::= { rcKhiForwardingCbZagrosEntry 33 }

rcKhiForwardingCbZagrosTcamSearchVal   OBJECT-TYPE
     SYNTAX         Counter64
     MAX-ACCESS     read-only
     STATUS         current
     DESCRIPTION    ""
     ::= { rcKhiForwardingCbZagrosEntry 34 }

rcKhiForwardingCbZagrosEmbDropCount   OBJECT-TYPE
     SYNTAX         Counter64
     MAX-ACCESS     read-only
     STATUS         current
     DESCRIPTION    ""
     ::= { rcKhiForwardingCbZagrosEntry 35 }

rcKhiForwardingCbZagrosEhpFilterDropCount   OBJECT-TYPE
     SYNTAX         Counter64
     MAX-ACCESS     read-only
     STATUS         current
     DESCRIPTION    ""
     ::= { rcKhiForwardingCbZagrosEntry 36 }

rcKhiForwardingCbZagrosEgrIpmcDropCount   OBJECT-TYPE
     SYNTAX         Counter64
     MAX-ACCESS     read-only
     STATUS         current
     DESCRIPTION    ""
     ::= { rcKhiForwardingCbZagrosEntry 37 }

rcKhiForwardingCbZagrosEgressEsb1Count   OBJECT-TYPE
     SYNTAX         Counter64
     MAX-ACCESS     read-only
     STATUS         current
     DESCRIPTION    ""
     ::= { rcKhiForwardingCbZagrosEntry 38 }

rcKhiForwardingCbZagrosEgressEsb2Count   OBJECT-TYPE
     SYNTAX         Counter64
     MAX-ACCESS     read-only
     STATUS         current
     DESCRIPTION    ""
     ::= { rcKhiForwardingCbZagrosEntry 39 }

rcKhiForwardingCbZagrosEgressEsb3Count   OBJECT-TYPE
     SYNTAX         Counter64
     MAX-ACCESS     read-only
     STATUS         current
     DESCRIPTION    ""
     ::= { rcKhiForwardingCbZagrosEntry 40 }

rcKhiForwardingCbZagrosEgressEsb4Count   OBJECT-TYPE
     SYNTAX         Counter64
     MAX-ACCESS     read-only
     STATUS         current
     DESCRIPTION    ""
     ::= { rcKhiForwardingCbZagrosEntry 41 }

rcKhiForwardingCbZagrosEgressEsb5Count   OBJECT-TYPE
     SYNTAX         Counter64
     MAX-ACCESS     read-only
     STATUS         current
     DESCRIPTION    ""
     ::= { rcKhiForwardingCbZagrosEntry 42 }

rcKhiForwardingCbZagrosEgressEsb6Count   OBJECT-TYPE
     SYNTAX         Counter64
     MAX-ACCESS     read-only
     STATUS         current
     DESCRIPTION    ""
     ::= { rcKhiForwardingCbZagrosEntry 43 }

rcKhiForwardingCbZagrosRspRx  OBJECT-TYPE
     SYNTAX         Counter64
     MAX-ACCESS     read-only
     STATUS         current
     DESCRIPTION    ""
     ::= { rcKhiForwardingCbZagrosEntry 44 }

rcKhiForwardingCbZagrosOpTx  OBJECT-TYPE
     SYNTAX         Counter64
     MAX-ACCESS     read-only
     STATUS         current
     DESCRIPTION    ""
     ::= { rcKhiForwardingCbZagrosEntry 45 }

rcKhiForwardingCbZagrosRspTx  OBJECT-TYPE
     SYNTAX         Counter64
     MAX-ACCESS     read-only
     STATUS         current
     DESCRIPTION    ""
     ::= { rcKhiForwardingCbZagrosEntry 46 }

rcKhiForwardingCbZagrosCifRqCount  OBJECT-TYPE
     SYNTAX         Counter64
     MAX-ACCESS     read-only
     STATUS         current
     DESCRIPTION    ""
     ::= { rcKhiForwardingCbZagrosEntry 47 }

rcKhiForwardingCbZagrosCifRsCounter  OBJECT-TYPE
     SYNTAX         Counter64
     MAX-ACCESS     read-only
     STATUS         current
     DESCRIPTION    ""
     ::= { rcKhiForwardingCbZagrosEntry 48 }


rcKhiForwardingCbZagrosPage1Count  OBJECT-TYPE
     SYNTAX         Counter64
     MAX-ACCESS     read-only
     STATUS         obsolete 
     DESCRIPTION    ""
     ::= { rcKhiForwardingCbZagrosEntry 49 }


rcKhiForwardingCbZagrosPage2Count  OBJECT-TYPE
     SYNTAX         Counter64
     MAX-ACCESS     read-only
     STATUS         obsolete
     DESCRIPTION    ""
     ::= { rcKhiForwardingCbZagrosEntry 50 }


rcKhiForwardingCbZagrosPage3Count  OBJECT-TYPE
     SYNTAX         Counter64
     MAX-ACCESS     read-only
     STATUS         obsolete 
     DESCRIPTION    ""
     ::= { rcKhiForwardingCbZagrosEntry 51 }


rcKhiForwardingCbZagrosPage4Count  OBJECT-TYPE
     SYNTAX         Counter64
     MAX-ACCESS     read-only
     STATUS         obsolete 
     DESCRIPTION    ""
     ::= { rcKhiForwardingCbZagrosEntry 52 }

rcKhiForwardingCbZagrosPage5Count  OBJECT-TYPE
     SYNTAX         Counter64
     MAX-ACCESS     read-only
     STATUS         obsolete 
     DESCRIPTION    ""
     ::= { rcKhiForwardingCbZagrosEntry 53 }

rcKhiForwardingCbZagrosPage6Count  OBJECT-TYPE
     SYNTAX         Counter64
     MAX-ACCESS     read-only
     STATUS         obsolete
     DESCRIPTION    ""
     ::= { rcKhiForwardingCbZagrosEntry 54 }

rcKhiForwardingCbZagrosPage7Count  OBJECT-TYPE
     SYNTAX         Counter64
     MAX-ACCESS     read-only
     STATUS         obsolete
     DESCRIPTION    ""
     ::= { rcKhiForwardingCbZagrosEntry 55 }

rcKhiForwardingCbZagrosPage8Count  OBJECT-TYPE
     SYNTAX         Counter64
     MAX-ACCESS     read-only
     STATUS         obsolete
     DESCRIPTION    ""
     ::= { rcKhiForwardingCbZagrosEntry 56 }

rcKhiForwardingCbZagrosPage9Count  OBJECT-TYPE
     SYNTAX         Counter64
     MAX-ACCESS     read-only
     STATUS         obsolete
     DESCRIPTION    ""
     ::= { rcKhiForwardingCbZagrosEntry 57 }

rcKhiForwardingCbZagrosPage10Count  OBJECT-TYPE
     SYNTAX         Counter64
     MAX-ACCESS     read-only
     STATUS         obsolete 
     DESCRIPTION    ""
     ::= { rcKhiForwardingCbZagrosEntry 58 }

rcKhiForwardingCbZagrosShPp  OBJECT-TYPE
     SYNTAX         Counter64
     MAX-ACCESS     read-only
     STATUS         obsolete 
     DESCRIPTION    ""
     ::= { rcKhiForwardingCbZagrosEntry 59 }

rcKhiForwardingCbZagrosFpCounts  OBJECT-TYPE
     SYNTAX         Counter64
     MAX-ACCESS     read-only
     STATUS         obsolete 
     DESCRIPTION    ""
     ::= { rcKhiForwardingCbZagrosEntry 60 }

rcKhiForwardingCbZagrosRspPlcThresholdReg  OBJECT-TYPE
     SYNTAX         Counter64
     MAX-ACCESS     read-only
     STATUS         current
     DESCRIPTION    ""
     ::= { rcKhiForwardingCbZagrosEntry 61 }

rcKhiForwardingCbZagrosRePlc  OBJECT-TYPE
     SYNTAX         Counter64
     MAX-ACCESS     read-only
     STATUS         current
     DESCRIPTION    ""
     ::= { rcKhiForwardingCbZagrosEntry 62 }

rcKhiForwardingCbZagrosNumPools  OBJECT-TYPE
     SYNTAX         Counter64
     MAX-ACCESS     read-only
     STATUS         current
     DESCRIPTION    ""
     ::= { rcKhiForwardingCbZagrosEntry 63 }

rcKhiForwardingCbZagrosFpCntOPA  OBJECT-TYPE
     SYNTAX         Counter32
     MAX-ACCESS     read-only
     STATUS         current
     DESCRIPTION    "Free page counter for OPA(Output Packet Assembler)"
     ::= { rcKhiForwardingCbZagrosEntry 64 }

rcKhiForwardingCbZagrosFpCntRPA OBJECT-TYPE
     SYNTAX         Counter32
     MAX-ACCESS     read-only
     STATUS         current
     DESCRIPTION    "Free page counter for RPA(RSP Packet Assembler)"
     ::= { rcKhiForwardingCbZagrosEntry 65 }

rcKhiForwardingCbZagrosFpCntFPM  OBJECT-TYPE
     SYNTAX         Counter32
     MAX-ACCESS     read-only
     STATUS         current
     DESCRIPTION    "Free page counter for FPM(Free Page Manager)"
     ::= { rcKhiForwardingCbZagrosEntry 66 }

rcKhiForwardingCbZagrosRspPlcPktCntPeak OBJECT-TYPE
     SYNTAX         Counter32
     MAX-ACCESS     read-only
     STATUS         current
     DESCRIPTION    "RSP PLC Peak Packet Count"
     ::= { rcKhiForwardingCbZagrosEntry 67 }

rcKhiForwardingCbZagrosRspPlcPktCntCurr OBJECT-TYPE
     SYNTAX         Counter32
     MAX-ACCESS     read-only
     STATUS         current
     DESCRIPTION    "RSP PLC Current Packet Count"
     ::= { rcKhiForwardingCbZagrosEntry 68 }

rcKhiForwardingCbZagrosRePlcPktCntPeak OBJECT-TYPE
     SYNTAX         Counter32
     MAX-ACCESS     read-only
     STATUS         current
     DESCRIPTION    "RE PLC(Replica Engine Packet Limit Count)Peak Packet Count"
     ::= { rcKhiForwardingCbZagrosEntry 69 }

rcKhiForwardingCbZagrosRePlcPktCntCurr OBJECT-TYPE
     SYNTAX         Counter32
     MAX-ACCESS     read-only
     STATUS         current
     DESCRIPTION    "RE PLC Current Packet Count"
     ::= { rcKhiForwardingCbZagrosEntry 70 }

rcKhiForwardingCbZagrosShPpPeak OBJECT-TYPE
     SYNTAX         Counter32
     MAX-ACCESS     read-only
     STATUS         current
     DESCRIPTION    "PMM shared pool Peak Value"
     ::= { rcKhiForwardingCbZagrosEntry 71 }

rcKhiForwardingCbZagrosShPpCurr OBJECT-TYPE
     SYNTAX         Counter32
     MAX-ACCESS     read-only
     STATUS         current
     DESCRIPTION    "PMM shared pool Current Value"
     ::= { rcKhiForwardingCbZagrosEntry 72 }

rcKhiForwardingCbZagrosEgressMultiCastPeak OBJECT-TYPE
     SYNTAX         Counter32
     MAX-ACCESS     read-only
     STATUS         current
     DESCRIPTION    "PMM EgressMultiCast Peak Value"
     ::= { rcKhiForwardingCbZagrosEntry 73 }

rcKhiForwardingCbZagrosEgressMultiCastCurr OBJECT-TYPE
     SYNTAX         Counter32
     MAX-ACCESS     read-only
     STATUS         current
     DESCRIPTION    "PMM EgressMultiCast Current Value"
     ::= { rcKhiForwardingCbZagrosEntry 74 }

rcKhiForwardingCbZagrosEgressOOBPeak OBJECT-TYPE
     SYNTAX         Counter32
     MAX-ACCESS     read-only
     STATUS         current
     DESCRIPTION    "PMM EgressOOB(Out Of Band) Peak Value"
     ::= { rcKhiForwardingCbZagrosEntry 75 }

rcKhiForwardingCbZagrosEgressOOBCurr OBJECT-TYPE
     SYNTAX         Counter32
     MAX-ACCESS     read-only
     STATUS         current
     DESCRIPTION    "PMM EgressOOB Current Value"
     ::= { rcKhiForwardingCbZagrosEntry 76 }

rcKhiForwardingCbZagrosIngressHeartbeatPeak OBJECT-TYPE
     SYNTAX         Counter32
     MAX-ACCESS     read-only
     STATUS         current
     DESCRIPTION    "PMM IngressHeartbeat Peak Value"
     ::= { rcKhiForwardingCbZagrosEntry 77 }

rcKhiForwardingCbZagrosIngressHeartbeatCurr OBJECT-TYPE
     SYNTAX         Counter32
     MAX-ACCESS     read-only
     STATUS         current
     DESCRIPTION    "PMM IngressHeartbeat Current Value"
     ::= { rcKhiForwardingCbZagrosEntry 78 }

rcKhiForwardingCbZagrosIngressCOPInsertPeak OBJECT-TYPE
     SYNTAX         Counter32
     MAX-ACCESS     read-only
     STATUS         current
     DESCRIPTION    "PMM IngressCOPInsert Peak Value"
     ::= { rcKhiForwardingCbZagrosEntry 79 }

rcKhiForwardingCbZagrosIngressCOPInsertCurr OBJECT-TYPE
     SYNTAX         Counter32
     MAX-ACCESS     read-only
     STATUS         current
     DESCRIPTION    "PMM IngressCOPInsert Current Value"
     ::= { rcKhiForwardingCbZagrosEntry 80 }

rcKhiForwardingCbZagrosIngressEfCtlPeak OBJECT-TYPE
     SYNTAX         Counter32
     MAX-ACCESS     read-only
     STATUS         current
     DESCRIPTION    "PMM Ingress EF/CTL(Expedited Forward/Control)Peak Value"
     ::= { rcKhiForwardingCbZagrosEntry 81 }

rcKhiForwardingCbZagrosIngressEfCtlCurr OBJECT-TYPE
     SYNTAX         Counter32
     MAX-ACCESS     read-only
     STATUS         current
     DESCRIPTION    "PMM Ingress EF/CTL Current Value"
     ::= { rcKhiForwardingCbZagrosEntry 82 }

rcKhiForwardingCbZagrosIngressAfBePeak OBJECT-TYPE
     SYNTAX         Counter32
     MAX-ACCESS     read-only
     STATUS         current
     DESCRIPTION    "PMM Ingress AF/BE(Assured Forwarding/Best Effort)Peak Value"
     ::= { rcKhiForwardingCbZagrosEntry 83 }

rcKhiForwardingCbZagrosIngressAfBeCurr OBJECT-TYPE
     SYNTAX         Counter32
     MAX-ACCESS     read-only
     STATUS         current
     DESCRIPTION    "PMM Ingress AF/BE Current Value"
     ::= { rcKhiForwardingCbZagrosEntry 84 }

rcKhiForwardingCbZagrosEgressL2BcUcPeak OBJECT-TYPE
     SYNTAX         Counter32
     MAX-ACCESS     read-only
     STATUS         current
     DESCRIPTION    "PMM Egress L2BC/UC(Layer 2 Broadcast/Unicast)Peak Value"
     ::= { rcKhiForwardingCbZagrosEntry 85 }

rcKhiForwardingCbZagrosEgressL2BcUcCurr OBJECT-TYPE
     SYNTAX         Counter32
     MAX-ACCESS     read-only
     STATUS         current
     DESCRIPTION    "PMM Egress L2BC/UC Current Value"
     ::= { rcKhiForwardingCbZagrosEntry 86 }

rcKhiForwardingCbZagrosEgressMirrorPeak OBJECT-TYPE
     SYNTAX         Counter32
     MAX-ACCESS     read-only
     STATUS         current
     DESCRIPTION    "PMM Egress Mirror Peak Value"
     ::= { rcKhiForwardingCbZagrosEntry 87 }

rcKhiForwardingCbZagrosEgressMirrorCurr OBJECT-TYPE
     SYNTAX         Counter32
     MAX-ACCESS     read-only
     STATUS         current
     DESCRIPTION    "PMM Egress Mirror Current Value"
     ::= { rcKhiForwardingCbZagrosEntry 88 }

forwardingCbZagrosPool9Peak OBJECT-TYPE
     SYNTAX         Counter32
     MAX-ACCESS     read-only
     STATUS         current
     DESCRIPTION    "PMM Pool9 Peak Value"
     ::= { rcKhiForwardingCbZagrosEntry 89 }

rcKhiForwardingCbZagrosPool9Curr OBJECT-TYPE
     SYNTAX         Counter32
     MAX-ACCESS     read-only
     STATUS         current
     DESCRIPTION    "PMM Pool9 Current Value"
     ::= { rcKhiForwardingCbZagrosEntry 90 }

-- KHI Forwarding Rsp table

rcKhiForwardingCbRspTable OBJECT-TYPE
     SYNTAX          SEQUENCE OF RcKhiForwardingCbRspEntry
     MAX-ACCESS      not-accessible
     STATUS          current
     DESCRIPTION     "Forwarding Rsp Key Health Indicator MIB - All Cobalt Blue Data."
     ::= { rcKhiForwardingCb 5}

rcKhiForwardingCbRspEntry OBJECT-TYPE
     SYNTAX          RcKhiForwardingCbRspEntry
     MAX-ACCESS      not-accessible
     STATUS          current
     DESCRIPTION     "Forwarding Rsp KHI - Cobalt Blue table entry."
     INDEX           { rcKhiForwardingCbRspIndex }
     ::= { rcKhiForwardingCbRspTable 1 }

RcKhiForwardingCbRspEntry ::=
     SEQUENCE {	
	rcKhiForwardingCbRspIndex                        INTEGER,
     	rcKhiForwardingCbRspLsmDrops                     Counter64,
     	rcKhiForwardingCbRspExceptionDrops               Counter64,
     	rcKhiForwardingCbRspFrameErrorDrops              Counter64,
     	rcKhiForwardingCbRspFdibFullDrops                Counter64,
     	rcKhiForwardingCbRspIngrMltAllPortDown           Counter64,
     	rcKhiForwardingCbRspEgressMltAllPortDownDrops    Counter64,
     	rcKhiForwardingCbRspEgressIpMcastRecordsNotFound Counter64,
     	rcKhiForwardingCbRspEgressIpMcastMltWrongPort    Counter64,
     	rcKhiForwardingCbRspEgressIpMcastSourceKnockout  Counter64,
     	rcKhiForwardingCbRspIngressDaNotFoundDrops       Counter64,
     	rcKhiForwardingCbRspIngressUnknown               Counter64,
     	rcKhiForwardingCbRspIngressDiscardDestIdDrops    Counter64,
     	rcKhiForwardingCbRspMacLearningPacketDrops       Counter64,
     	rcKhiForwardingCbRspIngrMltAllPortsDown          Counter64,
     	rcKhiForwardingCbRspIngressIpmcSupressionDrops   Counter64,
     	rcKhiForwardingCbRspUnsupportedFeatureDrops      Counter64,
     	rcKhiForwardingCbRspAclDiscards                  Counter64,
     	rcKhiForwardingCbRspIngressIpmcLookupFails       Counter64,
     	rcKhiForwardingCbRspIpv4DestIpLookupFails        Counter64,
     	rcKhiForwardingCbRspIpv4SourceIpLookupFails      Counter64,
        rcKhiForwardingCbRspL3MirrorDrops                Counter64,
        rcKhiForwardingCbRspIpV6LookupFails                Counter64,
        rcKhiForwardingCbRspIpV6TunnelLookupV4Fails        Counter64
}

rcKhiForwardingCbRspIndex  OBJECT-TYPE
     SYNTAX         INTEGER (1..60)
     MAX-ACCESS     not-accessible
     STATUS         current
     DESCRIPTION    "Index for CB's Forwarding Rsp Health data.  There are 6 
                    indicies reserved on a per slot basis.  Depending on
                    the card present and the data being requested not all 
                    indicies may be used."
     ::= { rcKhiForwardingCbRspEntry 1 } 

rcKhiForwardingCbRspLsmDrops    OBJECT-TYPE
     SYNTAX         Counter64
     MAX-ACCESS     read-only
     STATUS         current
     DESCRIPTION    ""
     ::= { rcKhiForwardingCbRspEntry 2 }

rcKhiForwardingCbRspExceptionDrops    OBJECT-TYPE
     SYNTAX         Counter64
     MAX-ACCESS     read-only
     STATUS         current
     DESCRIPTION    ""
     ::= { rcKhiForwardingCbRspEntry 3 }

rcKhiForwardingCbRspFrameErrorDrops    OBJECT-TYPE
     SYNTAX         Counter64
     MAX-ACCESS     read-only
     STATUS         current
     DESCRIPTION    ""
     ::= { rcKhiForwardingCbRspEntry 4 }

rcKhiForwardingCbRspFdibFullDrops    OBJECT-TYPE
     SYNTAX         Counter64
     MAX-ACCESS     read-only
     STATUS         current
     DESCRIPTION    ""
     ::= { rcKhiForwardingCbRspEntry 5 }

rcKhiForwardingCbRspIngrMltAllPortDown    OBJECT-TYPE
     SYNTAX         Counter64
     MAX-ACCESS     read-only
     STATUS         current
     DESCRIPTION    ""
     ::= { rcKhiForwardingCbRspEntry 6 }

rcKhiForwardingCbRspEgressMltAllPortDownDrops    OBJECT-TYPE
     SYNTAX         Counter64
     MAX-ACCESS     read-only
     STATUS         current
     DESCRIPTION    ""
     ::= { rcKhiForwardingCbRspEntry 7 }

rcKhiForwardingCbRspEgressIpMcastRecordsNotFound    OBJECT-TYPE
     SYNTAX         Counter64
     MAX-ACCESS     read-only
     STATUS         current
     DESCRIPTION    ""
     ::= { rcKhiForwardingCbRspEntry 8 }

rcKhiForwardingCbRspEgressIpMcastMltWrongPort    OBJECT-TYPE
     SYNTAX         Counter64
     MAX-ACCESS     read-only
     STATUS         current
     DESCRIPTION    ""
     ::= { rcKhiForwardingCbRspEntry 9 }

rcKhiForwardingCbRspEgressIpMcastSourceKnockout    OBJECT-TYPE
     SYNTAX         Counter64
     MAX-ACCESS     read-only
     STATUS         current
     DESCRIPTION    ""
     ::= { rcKhiForwardingCbRspEntry 10 }

rcKhiForwardingCbRspIngressDaNotFoundDrops    OBJECT-TYPE
     SYNTAX         Counter64
     MAX-ACCESS     read-only
     STATUS         current
     DESCRIPTION    ""
     ::= { rcKhiForwardingCbRspEntry 11 }

rcKhiForwardingCbRspIngressUnknown    OBJECT-TYPE
     SYNTAX         Counter64
     MAX-ACCESS     read-only
     STATUS         current
     DESCRIPTION    ""
     ::= { rcKhiForwardingCbRspEntry 12 }

rcKhiForwardingCbRspIngressDiscardDestIdDrops    OBJECT-TYPE
     SYNTAX         Counter64
     MAX-ACCESS     read-only
     STATUS         current
     DESCRIPTION    ""
     ::= { rcKhiForwardingCbRspEntry 13 }

rcKhiForwardingCbRspMacLearningPacketDrops    OBJECT-TYPE
     SYNTAX         Counter64
     MAX-ACCESS     read-only
     STATUS         current
     DESCRIPTION    ""
     ::= { rcKhiForwardingCbRspEntry 14 }

rcKhiForwardingCbRspIngrMltAllPortsDown    OBJECT-TYPE
     SYNTAX         Counter64
     MAX-ACCESS     read-only
     STATUS         current
     DESCRIPTION    ""
     ::= { rcKhiForwardingCbRspEntry 15 }

rcKhiForwardingCbRspIngressIpmcSupressionDrops    OBJECT-TYPE
     SYNTAX         Counter64
     MAX-ACCESS     read-only
     STATUS         current
     DESCRIPTION    ""
     ::= { rcKhiForwardingCbRspEntry 16 }

rcKhiForwardingCbRspUnsupportedFeatureDrops    OBJECT-TYPE
     SYNTAX         Counter64
     MAX-ACCESS     read-only
     STATUS         current
     DESCRIPTION    ""
     ::= { rcKhiForwardingCbRspEntry 17 }

rcKhiForwardingCbRspAclDiscards    OBJECT-TYPE
     SYNTAX         Counter64
     MAX-ACCESS     read-only
     STATUS         current
     DESCRIPTION    ""
     ::= { rcKhiForwardingCbRspEntry 18 }

rcKhiForwardingCbRspIngressIpmcLookupFails    OBJECT-TYPE
     SYNTAX         Counter64
     MAX-ACCESS     read-only
     STATUS         current
     DESCRIPTION    ""
     ::= { rcKhiForwardingCbRspEntry 19 }

rcKhiForwardingCbRspIpv4DestIpLookupFails    OBJECT-TYPE
     SYNTAX         Counter64
     MAX-ACCESS     read-only
     STATUS         current
     DESCRIPTION    ""
     ::= { rcKhiForwardingCbRspEntry 20 }

rcKhiForwardingCbRspIpv4SourceIpLookupFails    OBJECT-TYPE
     SYNTAX         Counter64
     MAX-ACCESS     read-only
     STATUS         current
     DESCRIPTION    ""
     ::= { rcKhiForwardingCbRspEntry 21 }

rcKhiForwardingCbRspL3MirrorDrops    OBJECT-TYPE
     SYNTAX         Counter64
     MAX-ACCESS     read-only
     STATUS         current
     DESCRIPTION    ""
     ::= { rcKhiForwardingCbRspEntry 22 }

rcKhiForwardingCbRspIpV6LookupFails    OBJECT-TYPE
     SYNTAX         Counter64
     MAX-ACCESS     read-only
     STATUS         current
     DESCRIPTION    ""
     ::= { rcKhiForwardingCbRspEntry 23 }

rcKhiForwardingCbRspIpV6TunnelLookupV4Fails    OBJECT-TYPE
     SYNTAX         Counter64
     MAX-ACCESS     read-only
     STATUS         current
     DESCRIPTION    ""
     ::= { rcKhiForwardingCbRspEntry 24 }


-- KHI Forwarding qe table

rcKhiForwardingCbQeTable  OBJECT-TYPE
     SYNTAX          SEQUENCE OF RcKhiForwardingCbQeEntry
     MAX-ACCESS      not-accessible
     STATUS          current
     DESCRIPTION     "Forwarding Qe Key Health Indicator MIB - All Cobalt Blue Data."
     ::= { rcKhiForwardingCb 6 }

rcKhiForwardingCbQeEntry OBJECT-TYPE
     SYNTAX          RcKhiForwardingCbQeEntry
     MAX-ACCESS      not-accessible
     STATUS          current
     DESCRIPTION     "Forwarding Qe KHI - Cobalt Blue table entry."
     INDEX           { rcKhiForwardingCbQeIndex }
     ::= { rcKhiForwardingCbQeTable 1 }

RcKhiForwardingCbQeEntry ::=
     SEQUENCE {
	rcKhiForwardingCbQeIndex                        INTEGER,
	rcKhiForwardingCbQeIngressQmAgrAcceptedPktCnt0  Counter64,
	rcKhiForwardingCbQeIngressQmAgrMarkedPktCnt0    Counter64,	
     	rcKhiForwardingCbQeIngressQmAgrAcceptedPktCnt1  Counter64,
	rcKhiForwardingCbQeIngressQmAgrMarkedPktCnt1    Counter64,
	rcKhiForwardingCbQeIngressQmAgrAcceptedPktCnt2  Counter64,
	rcKhiForwardingCbQeIngressQmAgrMarkedPktCnt2    Counter64,	
     	rcKhiForwardingCbQeIngressQmAgrAcceptedPktCnt3  Counter64,
	rcKhiForwardingCbQeIngressQmAgrDequeuedPktCnt   Counter64,
	rcKhiForwardingCbQeIngressPmSwitchPktCnt        Counter64,
	rcKhiForwardingCbQeIngressPmLocalPktCnt         Counter64,
	rcKhiForwardingCbQeIngressPmSwitchTestPktCnt    Counter64,
	rcKhiForwardingCbQeIngressPmLocalTestPktCnt     Counter64,
	rcKhiForwardingCbQeIngressSr0RxP0PktCnt         Counter64,
	rcKhiForwardingCbQeIngressSr1RxP0PktCnt         Counter64,
	rcKhiForwardingCbQeIngressSr0RxP1PktCnt         Counter64,
	rcKhiForwardingCbQeIngressSr1RxP1PktCnt         Counter64,
	rcKhiForwardingCbQeIngressSr0RxP2PktCnt         Counter64,
	rcKhiForwardingCbQeIngressSr1RxP2PktCnt         Counter64,
	rcKhiForwardingCbQeIngressSr0RxP3PktCnt         Counter64,
	rcKhiForwardingCbQeIngressSr1RxP3PktCnt         Counter64,
	rcKhiForwardingCbQeIngressSr0RxP4PktCnt         Counter64,
	rcKhiForwardingCbQeIngressSr1RxP4PktCnt         Counter64,
	rcKhiForwardingCbQeIngressSr0RxP5PktCnt         Counter64,
	rcKhiForwardingCbQeIngressSr1RxP5PktCnt         Counter64,
	rcKhiForwardingCbQeIngressSr0RxP6PktCnt         Counter64,
	rcKhiForwardingCbQeIngressSr1RxP6PktCnt         Counter64,
	rcKhiForwardingCbQeIngressSr0RxP7PktCnt         Counter64,
	rcKhiForwardingCbQeIngressSr1RxP7PktCnt         Counter64,
	rcKhiForwardingCbQeIngressSr0RxP8PktCnt         Counter64,
	rcKhiForwardingCbQeIngressSr1RxP8PktCnt         Counter64,
	rcKhiForwardingCbQeIngressSr0RxP9PktCnt         Counter64,
	rcKhiForwardingCbQeIngressSr1RxP9PktCnt         Counter64,
	rcKhiForwardingCbQeIngressSr0RxP10PktCnt        Counter64,
	rcKhiForwardingCbQeIngressSr1RxP10PktCnt        Counter64,
	rcKhiForwardingCbQeIngressSr0RxP11PktCnt        Counter64,
	rcKhiForwardingCbQeIngressSr1RxP11PktCnt        Counter64,
	rcKhiForwardingCbQeIngressSr0RxP12PktCnt        Counter64,
	rcKhiForwardingCbQeIngressSr1RxP12PktCnt        Counter64,	
	rcKhiForwardingCbQeIngressSr0RxP13PktCnt        Counter64,
	rcKhiForwardingCbQeIngressSr1RxP13PktCnt        Counter64,
	rcKhiForwardingCbQeIngressSr0RxP14PktCnt        Counter64,
	rcKhiForwardingCbQeIngressSr1RxP14PktCnt        Counter64,
	rcKhiForwardingCbQeIngressSr0RxP15PktCnt        Counter64,
	rcKhiForwardingCbQeIngressSr1RxP15PktCnt        Counter64,
	rcKhiForwardingCbQeIngressSr0RxTestPktCnt       Counter64,
	rcKhiForwardingCbQeIngressSr1RxTestPktCnt       Counter64,
	rcKhiForwardingCbQeIngressRbIdp0RequestPktCnt   Counter64,
	rcKhiForwardingCbQeIngressRbIdp1RequestPktCnt   Counter64,
	rcKhiForwardingCbQeIngressRbIdp2RequestPktCnt   Counter64,
	rcKhiForwardingCbQeIngressRbIdp3RequestPktCnt   Counter64,
	rcKhiForwardingCbQeIngressRbIdp4RequestPktCnt   Counter64,
	rcKhiForwardingCbQeIngressRbEnqrespPktCnt       Counter64,
     	rcKhiForwardingCbQeEgressSvPktCnt               Counter64,
	rcKhiForwardingCbQeEgressSt0P0TxPktCnt          Counter64,
	rcKhiForwardingCbQeEgressSt1P0TxPktCnt          Counter64,
	rcKhiForwardingCbQeEgressSt0P1TxPktCnt          Counter64,
	rcKhiForwardingCbQeEgressSt1P1TxPktCnt          Counter64,
	rcKhiForwardingCbQeEgressSt0P2TxPktCnt          Counter64,
	rcKhiForwardingCbQeEgressSt1P2TxPktCnt          Counter64,
	rcKhiForwardingCbQeEgressSt0P3TxPktCnt          Counter64,
	rcKhiForwardingCbQeEgressSt1P3TxPktCnt          Counter64,
	rcKhiForwardingCbQeEgressSt0P4TxPktCnt          Counter64,
	rcKhiForwardingCbQeEgressSt1P4TxPktCnt          Counter64,
	rcKhiForwardingCbQeEgressSt0P5TxPktCnt          Counter64,
	rcKhiForwardingCbQeEgressSt1P5TxPktCnt          Counter64,
	rcKhiForwardingCbQeEgressSt0P6TxPktCnt          Counter64,
	rcKhiForwardingCbQeEgressSt1P6TxPktCnt          Counter64,
	rcKhiForwardingCbQeEgressSt0P7TxPktCnt          Counter64,
	rcKhiForwardingCbQeEgressSt1P7TxPktCnt          Counter64,
	rcKhiForwardingCbQeEgressSt0P8TxPktCnt          Counter64,
	rcKhiForwardingCbQeEgressSt1P8TxPktCnt          Counter64,
	rcKhiForwardingCbQeEgressSt0P9TxPktCnt          Counter64,
	rcKhiForwardingCbQeEgressSt1P9TxPktCnt          Counter64,
  	rcKhiForwardingCbQeEgressSt0P10TxPktCnt         Counter64,
	rcKhiForwardingCbQeEgressSt1P10TxPktCnt         Counter64,
  	rcKhiForwardingCbQeEgressSt0P11TxPktCnt         Counter64,
	rcKhiForwardingCbQeEgressSt1P11TxPktCnt         Counter64,
  	rcKhiForwardingCbQeEgressSt0P12TxPktCnt         Counter64,
	rcKhiForwardingCbQeEgressSt1P12TxPktCnt         Counter64,
  	rcKhiForwardingCbQeEgressSt0P13TxPktCnt         Counter64,
	rcKhiForwardingCbQeEgressSt1P13TxPktCnt         Counter64,
  	rcKhiForwardingCbQeEgressSt0P14TxPktCnt         Counter64,
	rcKhiForwardingCbQeEgressSt1P14TxPktCnt         Counter64,		
  	rcKhiForwardingCbQeEgressSt0P15TxPktCnt         Counter64,
	rcKhiForwardingCbQeEgressSt1P15TxPktCnt         Counter64,
  	rcKhiForwardingCbQeEgressSt0TxTestPktCnt        Counter64,
	rcKhiForwardingCbQeEgressSt1TxTestPktCnt        Counter64,
	rcKhiForwardingCbQeSvPartialPktCnt 		Counter64,
	rcKhiForwardingCbQeQmAgrWredDroppedPktCnt0      Counter64,
	rcKhiForwardingCbQeQmAgrWredDroppedPktCnt1      Counter64,
	rcKhiForwardingCbQeQmAgrWredDroppedPktCnt2      Counter64,
	rcKhiForwardingCbQeQmAgrPolicedDroppedPktCnt    Counter64,
	rcKhiForwardingCbQeQmAgrNonWredDroppedPktCnt    Counter64,
	rcKhiForwardingCbQeQmError1                     Counter64
    }

rcKhiForwardingCbQeIndex  OBJECT-TYPE
     SYNTAX         INTEGER (1..60)
     MAX-ACCESS     not-accessible
     STATUS         current
     DESCRIPTION    "Index for CB's Forwarding Qe Health data.  There are 6 
                    indicies reserved on a per slot basis.  Depending on
                    the card present and the data being requested not all 
                    indicies may be used."
     ::= { rcKhiForwardingCbQeEntry 1 } 

rcKhiForwardingCbQeIngressQmAgrAcceptedPktCnt0    OBJECT-TYPE
     SYNTAX         Counter64
     MAX-ACCESS     read-only
     STATUS         current
     DESCRIPTION    ""
     ::= { rcKhiForwardingCbQeEntry 2 }

rcKhiForwardingCbQeIngressQmAgrMarkedPktCnt0    OBJECT-TYPE    
     SYNTAX         Counter64
     MAX-ACCESS     read-only
     STATUS         current
     DESCRIPTION    ""
     ::= { rcKhiForwardingCbQeEntry 3 }

rcKhiForwardingCbQeIngressQmAgrAcceptedPktCnt1    OBJECT-TYPE
     SYNTAX         Counter64
     MAX-ACCESS     read-only
     STATUS         current
     DESCRIPTION    ""
     ::= { rcKhiForwardingCbQeEntry 4 }

rcKhiForwardingCbQeIngressQmAgrMarkedPktCnt1    OBJECT-TYPE    
     SYNTAX         Counter64
     MAX-ACCESS     read-only
     STATUS         current
     DESCRIPTION    ""
     ::= { rcKhiForwardingCbQeEntry 5 }

rcKhiForwardingCbQeIngressQmAgrAcceptedPktCnt2    OBJECT-TYPE
     SYNTAX         Counter64
     MAX-ACCESS     read-only
     STATUS         current
     DESCRIPTION    ""
     ::= { rcKhiForwardingCbQeEntry 6 }

rcKhiForwardingCbQeIngressQmAgrMarkedPktCnt2    OBJECT-TYPE    
     SYNTAX         Counter64
     MAX-ACCESS     read-only
     STATUS         current
     DESCRIPTION    ""
     ::= { rcKhiForwardingCbQeEntry 7 }

rcKhiForwardingCbQeIngressQmAgrAcceptedPktCnt3    OBJECT-TYPE
     SYNTAX         Counter64
     MAX-ACCESS     read-only
     STATUS         current
     DESCRIPTION    ""
     ::= { rcKhiForwardingCbQeEntry 8 }

rcKhiForwardingCbQeIngressQmAgrDequeuedPktCnt    OBJECT-TYPE
     SYNTAX         Counter64
     MAX-ACCESS     read-only
     STATUS         current
     DESCRIPTION    ""
     ::= { rcKhiForwardingCbQeEntry 9 }

rcKhiForwardingCbQeIngressPmSwitchPktCnt    OBJECT-TYPE
     SYNTAX         Counter64
     MAX-ACCESS     read-only
     STATUS         current
     DESCRIPTION    ""
     ::= { rcKhiForwardingCbQeEntry 10 }

rcKhiForwardingCbQeIngressPmLocalPktCnt    OBJECT-TYPE
     SYNTAX         Counter64
     MAX-ACCESS     read-only
     STATUS         current
     DESCRIPTION    ""
     ::= { rcKhiForwardingCbQeEntry 11 }

rcKhiForwardingCbQeIngressPmSwitchTestPktCnt    OBJECT-TYPE
     SYNTAX         Counter64
     MAX-ACCESS     read-only
     STATUS         current
     DESCRIPTION    ""
     ::= { rcKhiForwardingCbQeEntry 12 }

rcKhiForwardingCbQeIngressPmLocalTestPktCnt     OBJECT-TYPE
     SYNTAX         Counter64
     MAX-ACCESS     read-only
     STATUS         current
     DESCRIPTION    ""
     ::= { rcKhiForwardingCbQeEntry 13 }

rcKhiForwardingCbQeIngressSr0RxP0PktCnt     OBJECT-TYPE
     SYNTAX         Counter64
     MAX-ACCESS     read-only
     STATUS         current
     DESCRIPTION    ""
     ::= { rcKhiForwardingCbQeEntry 14 }

rcKhiForwardingCbQeIngressSr1RxP0PktCnt     OBJECT-TYPE
     SYNTAX         Counter64
     MAX-ACCESS     read-only
     STATUS         current
     DESCRIPTION    ""
     ::= { rcKhiForwardingCbQeEntry 15 }

rcKhiForwardingCbQeIngressSr0RxP1PktCnt     OBJECT-TYPE
     SYNTAX         Counter64
     MAX-ACCESS     read-only
     STATUS         current
     DESCRIPTION    ""
     ::= { rcKhiForwardingCbQeEntry 16 }

rcKhiForwardingCbQeIngressSr1RxP1PktCnt     OBJECT-TYPE
     SYNTAX         Counter64
     MAX-ACCESS     read-only
     STATUS         current
     DESCRIPTION    ""
     ::= { rcKhiForwardingCbQeEntry 17 }

rcKhiForwardingCbQeIngressSr0RxP2PktCnt     OBJECT-TYPE
     SYNTAX         Counter64
     MAX-ACCESS     read-only
     STATUS         current
     DESCRIPTION    ""
     ::= { rcKhiForwardingCbQeEntry 18 }

rcKhiForwardingCbQeIngressSr1RxP2PktCnt     OBJECT-TYPE
     SYNTAX         Counter64
     MAX-ACCESS     read-only
     STATUS         current
     DESCRIPTION    ""
     ::= { rcKhiForwardingCbQeEntry 19 }

rcKhiForwardingCbQeIngressSr0RxP3PktCnt     OBJECT-TYPE
     SYNTAX         Counter64
     MAX-ACCESS     read-only
     STATUS         current
     DESCRIPTION    ""
     ::= { rcKhiForwardingCbQeEntry 20 }

rcKhiForwardingCbQeIngressSr1RxP3PktCnt     OBJECT-TYPE
     SYNTAX         Counter64
     MAX-ACCESS     read-only
     STATUS         current
     DESCRIPTION    ""
     ::= { rcKhiForwardingCbQeEntry 21 }

rcKhiForwardingCbQeIngressSr0RxP4PktCnt     OBJECT-TYPE
     SYNTAX         Counter64
     MAX-ACCESS     read-only
     STATUS         current
     DESCRIPTION    ""
     ::= { rcKhiForwardingCbQeEntry 22 }

rcKhiForwardingCbQeIngressSr1RxP4PktCnt     OBJECT-TYPE
     SYNTAX         Counter64
     MAX-ACCESS     read-only
     STATUS         current
     DESCRIPTION    ""
     ::= { rcKhiForwardingCbQeEntry 23 }

rcKhiForwardingCbQeIngressSr0RxP5PktCnt     OBJECT-TYPE
     SYNTAX         Counter64
     MAX-ACCESS     read-only
     STATUS         current
     DESCRIPTION    ""
     ::= { rcKhiForwardingCbQeEntry 24 }

rcKhiForwardingCbQeIngressSr1RxP5PktCnt     OBJECT-TYPE
     SYNTAX         Counter64
     MAX-ACCESS     read-only
     STATUS         current
     DESCRIPTION    ""
     ::= { rcKhiForwardingCbQeEntry 25 }

rcKhiForwardingCbQeIngressSr0RxP6PktCnt     OBJECT-TYPE
     SYNTAX         Counter64
     MAX-ACCESS     read-only
     STATUS         current
     DESCRIPTION    ""
     ::= { rcKhiForwardingCbQeEntry 26 }

rcKhiForwardingCbQeIngressSr1RxP6PktCnt     OBJECT-TYPE
     SYNTAX         Counter64
     MAX-ACCESS     read-only
     STATUS         current
     DESCRIPTION    ""
     ::= { rcKhiForwardingCbQeEntry 27 }

rcKhiForwardingCbQeIngressSr0RxP7PktCnt     OBJECT-TYPE
     SYNTAX         Counter64
     MAX-ACCESS     read-only
     STATUS         current
     DESCRIPTION    ""
     ::= { rcKhiForwardingCbQeEntry 28 }

rcKhiForwardingCbQeIngressSr1RxP7PktCnt     OBJECT-TYPE
     SYNTAX         Counter64
     MAX-ACCESS     read-only
     STATUS         current
     DESCRIPTION    ""
     ::= { rcKhiForwardingCbQeEntry 29 }

rcKhiForwardingCbQeIngressSr0RxP8PktCnt     OBJECT-TYPE
     SYNTAX         Counter64
     MAX-ACCESS     read-only
     STATUS         current
     DESCRIPTION    ""
     ::= { rcKhiForwardingCbQeEntry 30 }

rcKhiForwardingCbQeIngressSr1RxP8PktCnt     OBJECT-TYPE
     SYNTAX         Counter64
     MAX-ACCESS     read-only
     STATUS         current
     DESCRIPTION    ""
     ::= { rcKhiForwardingCbQeEntry 31 }

rcKhiForwardingCbQeIngressSr0RxP9PktCnt     OBJECT-TYPE
     SYNTAX         Counter64
     MAX-ACCESS     read-only
     STATUS         current
     DESCRIPTION    ""
     ::= { rcKhiForwardingCbQeEntry 32 }

rcKhiForwardingCbQeIngressSr1RxP9PktCnt     OBJECT-TYPE
     SYNTAX         Counter64
     MAX-ACCESS     read-only
     STATUS         current
     DESCRIPTION    ""
     ::= { rcKhiForwardingCbQeEntry 33 }

rcKhiForwardingCbQeIngressSr0RxP10PktCnt     OBJECT-TYPE
     SYNTAX         Counter64
     MAX-ACCESS     read-only
     STATUS         current
     DESCRIPTION    ""
     ::= { rcKhiForwardingCbQeEntry 34 }

rcKhiForwardingCbQeIngressSr1RxP10PktCnt     OBJECT-TYPE
     SYNTAX         Counter64
     MAX-ACCESS     read-only
     STATUS         current
     DESCRIPTION    ""
     ::= { rcKhiForwardingCbQeEntry 35 }

rcKhiForwardingCbQeIngressSr0RxP11PktCnt     OBJECT-TYPE
     SYNTAX         Counter64
     MAX-ACCESS     read-only
     STATUS         current
     DESCRIPTION    ""
     ::= { rcKhiForwardingCbQeEntry 36 }

rcKhiForwardingCbQeIngressSr1RxP11PktCnt     OBJECT-TYPE
     SYNTAX         Counter64
     MAX-ACCESS     read-only
     STATUS         current
     DESCRIPTION    ""
     ::= { rcKhiForwardingCbQeEntry 37 }
 
rcKhiForwardingCbQeIngressSr0RxP12PktCnt     OBJECT-TYPE
     SYNTAX         Counter64
     MAX-ACCESS     read-only
     STATUS         current
     DESCRIPTION    ""
     ::= { rcKhiForwardingCbQeEntry 38 }

rcKhiForwardingCbQeIngressSr1RxP12PktCnt     OBJECT-TYPE
     SYNTAX         Counter64
     MAX-ACCESS     read-only
     STATUS         current
     DESCRIPTION    ""
     ::= { rcKhiForwardingCbQeEntry 39 }

rcKhiForwardingCbQeIngressSr0RxP13PktCnt     OBJECT-TYPE
     SYNTAX         Counter64
     MAX-ACCESS     read-only
     STATUS         current
     DESCRIPTION    ""
     ::= { rcKhiForwardingCbQeEntry 40 }

rcKhiForwardingCbQeIngressSr1RxP13PktCnt     OBJECT-TYPE
     SYNTAX         Counter64
     MAX-ACCESS     read-only
     STATUS         current
     DESCRIPTION    ""
     ::= { rcKhiForwardingCbQeEntry 41 }

rcKhiForwardingCbQeIngressSr0RxP14PktCnt     OBJECT-TYPE
     SYNTAX         Counter64
     MAX-ACCESS     read-only
     STATUS         current
     DESCRIPTION    ""
     ::= { rcKhiForwardingCbQeEntry 42 }

rcKhiForwardingCbQeIngressSr1RxP14PktCnt     OBJECT-TYPE
     SYNTAX         Counter64
     MAX-ACCESS     read-only
     STATUS         current
     DESCRIPTION    ""
     ::= { rcKhiForwardingCbQeEntry 43 }

rcKhiForwardingCbQeIngressSr0RxP15PktCnt     OBJECT-TYPE
     SYNTAX         Counter64
     MAX-ACCESS     read-only
     STATUS         current
     DESCRIPTION    ""
     ::= { rcKhiForwardingCbQeEntry 44 }

rcKhiForwardingCbQeIngressSr1RxP15PktCnt     OBJECT-TYPE
     SYNTAX         Counter64
     MAX-ACCESS     read-only
     STATUS         current
     DESCRIPTION    ""
     ::= { rcKhiForwardingCbQeEntry 45 }

rcKhiForwardingCbQeIngressSr0RxTestPktCnt     OBJECT-TYPE
     SYNTAX         Counter64
     MAX-ACCESS     read-only
     STATUS         current
     DESCRIPTION    ""
     ::= { rcKhiForwardingCbQeEntry 46 }

rcKhiForwardingCbQeIngressSr1RxTestPktCnt     OBJECT-TYPE
     SYNTAX         Counter64
     MAX-ACCESS     read-only
     STATUS         current
     DESCRIPTION    ""
     ::= { rcKhiForwardingCbQeEntry 47 }

rcKhiForwardingCbQeIngressRbIdp0RequestPktCnt     OBJECT-TYPE
     SYNTAX         Counter64
     MAX-ACCESS     read-only
     STATUS         current
     DESCRIPTION    ""
     ::= { rcKhiForwardingCbQeEntry 48 }

rcKhiForwardingCbQeIngressRbIdp1RequestPktCnt     OBJECT-TYPE
     SYNTAX         Counter64
     MAX-ACCESS     read-only
     STATUS         current
     DESCRIPTION    ""
     ::= { rcKhiForwardingCbQeEntry 49 }

rcKhiForwardingCbQeIngressRbIdp2RequestPktCnt     OBJECT-TYPE
     SYNTAX         Counter64
     MAX-ACCESS     read-only
     STATUS         current
     DESCRIPTION    ""
     ::= { rcKhiForwardingCbQeEntry 50 }

rcKhiForwardingCbQeIngressRbIdp3RequestPktCnt     OBJECT-TYPE
     SYNTAX         Counter64
     MAX-ACCESS     read-only
     STATUS         current
     DESCRIPTION    ""
     ::= { rcKhiForwardingCbQeEntry 51 }

rcKhiForwardingCbQeIngressRbIdp4RequestPktCnt     OBJECT-TYPE
     SYNTAX         Counter64
     MAX-ACCESS     read-only
     STATUS         current
     DESCRIPTION    ""
     ::= { rcKhiForwardingCbQeEntry 52}

rcKhiForwardingCbQeIngressRbEnqrespPktCnt     OBJECT-TYPE
     SYNTAX         Counter64
     MAX-ACCESS     read-only
     STATUS         current
     DESCRIPTION    ""
     ::= { rcKhiForwardingCbQeEntry 53 }

rcKhiForwardingCbQeEgressSvPktCnt     OBJECT-TYPE
     SYNTAX         Counter64
     MAX-ACCESS     read-only
     STATUS         current
     DESCRIPTION    ""
     ::= { rcKhiForwardingCbQeEntry 54 }

rcKhiForwardingCbQeEgressSt0P0TxPktCnt     OBJECT-TYPE
     SYNTAX         Counter64
     MAX-ACCESS     read-only
     STATUS         current
     DESCRIPTION    ""
     ::= { rcKhiForwardingCbQeEntry 55 }

rcKhiForwardingCbQeEgressSt1P0TxPktCnt     OBJECT-TYPE
     SYNTAX         Counter64
     MAX-ACCESS     read-only
     STATUS         current
     DESCRIPTION    ""
     ::= { rcKhiForwardingCbQeEntry 56 }

rcKhiForwardingCbQeEgressSt0P1TxPktCnt     OBJECT-TYPE
     SYNTAX         Counter64
     MAX-ACCESS     read-only
     STATUS         current
     DESCRIPTION    ""
     ::= { rcKhiForwardingCbQeEntry 57 }

rcKhiForwardingCbQeEgressSt1P1TxPktCnt     OBJECT-TYPE
     SYNTAX         Counter64
     MAX-ACCESS     read-only
     STATUS         current
     DESCRIPTION    ""
     ::= { rcKhiForwardingCbQeEntry 58 }

rcKhiForwardingCbQeEgressSt0P2TxPktCnt     OBJECT-TYPE
     SYNTAX         Counter64
     MAX-ACCESS     read-only
     STATUS         current
     DESCRIPTION    ""
     ::= { rcKhiForwardingCbQeEntry 59 }

rcKhiForwardingCbQeEgressSt1P2TxPktCnt     OBJECT-TYPE
     SYNTAX         Counter64
     MAX-ACCESS     read-only
     STATUS         current
     DESCRIPTION    ""
     ::= { rcKhiForwardingCbQeEntry 60 }

rcKhiForwardingCbQeEgressSt0P3TxPktCnt     OBJECT-TYPE
     SYNTAX         Counter64
     MAX-ACCESS     read-only
     STATUS         current
     DESCRIPTION    ""
     ::= { rcKhiForwardingCbQeEntry 61 }

rcKhiForwardingCbQeEgressSt1P3TxPktCnt     OBJECT-TYPE
     SYNTAX         Counter64
     MAX-ACCESS     read-only
     STATUS         current
     DESCRIPTION    ""
     ::= { rcKhiForwardingCbQeEntry 62 }

rcKhiForwardingCbQeEgressSt0P4TxPktCnt     OBJECT-TYPE
     SYNTAX         Counter64
     MAX-ACCESS     read-only
     STATUS         current
     DESCRIPTION    ""
     ::= { rcKhiForwardingCbQeEntry 63 }

rcKhiForwardingCbQeEgressSt1P4TxPktCnt     OBJECT-TYPE
     SYNTAX         Counter64
     MAX-ACCESS     read-only
     STATUS         current
     DESCRIPTION    ""
     ::= { rcKhiForwardingCbQeEntry 64 }

rcKhiForwardingCbQeEgressSt0P5TxPktCnt     OBJECT-TYPE
     SYNTAX         Counter64
     MAX-ACCESS     read-only
     STATUS         current
     DESCRIPTION    ""
     ::= { rcKhiForwardingCbQeEntry 65 }

rcKhiForwardingCbQeEgressSt1P5TxPktCnt     OBJECT-TYPE
     SYNTAX         Counter64
     MAX-ACCESS     read-only
     STATUS         current
     DESCRIPTION    ""
     ::= { rcKhiForwardingCbQeEntry 66 }

rcKhiForwardingCbQeEgressSt0P6TxPktCnt     OBJECT-TYPE
     SYNTAX         Counter64
     MAX-ACCESS     read-only
     STATUS         current
     DESCRIPTION    ""
     ::= { rcKhiForwardingCbQeEntry 67 }

rcKhiForwardingCbQeEgressSt1P6TxPktCnt     OBJECT-TYPE
     SYNTAX         Counter64
     MAX-ACCESS     read-only
     STATUS         current
     DESCRIPTION    ""
     ::= { rcKhiForwardingCbQeEntry 68 }

rcKhiForwardingCbQeEgressSt0P7TxPktCnt     OBJECT-TYPE
     SYNTAX         Counter64
     MAX-ACCESS     read-only
     STATUS         current
     DESCRIPTION    ""
     ::= { rcKhiForwardingCbQeEntry 69 }

rcKhiForwardingCbQeEgressSt1P7TxPktCnt     OBJECT-TYPE
     SYNTAX         Counter64
     MAX-ACCESS     read-only
     STATUS         current
     DESCRIPTION    ""
     ::= { rcKhiForwardingCbQeEntry 70 }

rcKhiForwardingCbQeEgressSt0P8TxPktCnt     OBJECT-TYPE
     SYNTAX         Counter64
     MAX-ACCESS     read-only
     STATUS         current
     DESCRIPTION    ""
     ::= { rcKhiForwardingCbQeEntry 71 }

rcKhiForwardingCbQeEgressSt1P8TxPktCnt     OBJECT-TYPE
     SYNTAX         Counter64
     MAX-ACCESS     read-only
     STATUS         current
     DESCRIPTION    ""
     ::= { rcKhiForwardingCbQeEntry 72 }

rcKhiForwardingCbQeEgressSt0P9TxPktCnt     OBJECT-TYPE
     SYNTAX         Counter64
     MAX-ACCESS     read-only
     STATUS         current
     DESCRIPTION    ""
     ::= { rcKhiForwardingCbQeEntry 73 }

rcKhiForwardingCbQeEgressSt1P9TxPktCnt     OBJECT-TYPE
     SYNTAX         Counter64
     MAX-ACCESS     read-only
     STATUS         current
     DESCRIPTION    ""
     ::= { rcKhiForwardingCbQeEntry 74 }

rcKhiForwardingCbQeEgressSt0P10TxPktCnt     OBJECT-TYPE
     SYNTAX         Counter64
     MAX-ACCESS     read-only
     STATUS         current
     DESCRIPTION    ""
     ::= { rcKhiForwardingCbQeEntry 75 }

rcKhiForwardingCbQeEgressSt1P10TxPktCnt     OBJECT-TYPE
     SYNTAX         Counter64
     MAX-ACCESS     read-only
     STATUS         current
     DESCRIPTION    ""
     ::= { rcKhiForwardingCbQeEntry 76 }

rcKhiForwardingCbQeEgressSt0P11TxPktCnt     OBJECT-TYPE
     SYNTAX         Counter64
     MAX-ACCESS     read-only
     STATUS         current
     DESCRIPTION    ""
     ::= { rcKhiForwardingCbQeEntry 77 }

rcKhiForwardingCbQeEgressSt1P11TxPktCnt     OBJECT-TYPE
     SYNTAX         Counter64
     MAX-ACCESS     read-only
     STATUS         current
     DESCRIPTION    ""
     ::= { rcKhiForwardingCbQeEntry 78 }

rcKhiForwardingCbQeEgressSt0P12TxPktCnt     OBJECT-TYPE
     SYNTAX         Counter64
     MAX-ACCESS     read-only
     STATUS         current
     DESCRIPTION    ""
     ::= { rcKhiForwardingCbQeEntry 79 }

rcKhiForwardingCbQeEgressSt1P12TxPktCnt     OBJECT-TYPE
     SYNTAX         Counter64
     MAX-ACCESS     read-only
     STATUS         current
     DESCRIPTION    ""
     ::= { rcKhiForwardingCbQeEntry 80 }

rcKhiForwardingCbQeEgressSt0P13TxPktCnt     OBJECT-TYPE
     SYNTAX         Counter64
     MAX-ACCESS     read-only
     STATUS         current
     DESCRIPTION    ""
     ::= { rcKhiForwardingCbQeEntry 81 }

rcKhiForwardingCbQeEgressSt1P13TxPktCnt     OBJECT-TYPE
     SYNTAX         Counter64
     MAX-ACCESS     read-only
     STATUS         current
     DESCRIPTION    ""
     ::= { rcKhiForwardingCbQeEntry 82 }

rcKhiForwardingCbQeEgressSt0P14TxPktCnt     OBJECT-TYPE
     SYNTAX         Counter64
     MAX-ACCESS     read-only
     STATUS         current
     DESCRIPTION    ""
     ::= { rcKhiForwardingCbQeEntry 83 }

rcKhiForwardingCbQeEgressSt1P14TxPktCnt     OBJECT-TYPE
     SYNTAX         Counter64
     MAX-ACCESS     read-only
     STATUS         current
     DESCRIPTION    ""
     ::= { rcKhiForwardingCbQeEntry 84 }

rcKhiForwardingCbQeEgressSt0P15TxPktCnt     OBJECT-TYPE
     SYNTAX         Counter64
     MAX-ACCESS     read-only
     STATUS         current
     DESCRIPTION    ""
     ::= { rcKhiForwardingCbQeEntry 85 }

rcKhiForwardingCbQeEgressSt1P15TxPktCnt     OBJECT-TYPE
     SYNTAX         Counter64
     MAX-ACCESS     read-only
     STATUS         current
     DESCRIPTION    ""
     ::= { rcKhiForwardingCbQeEntry 86 }

rcKhiForwardingCbQeEgressSt0TxTestPktCnt     OBJECT-TYPE
     SYNTAX         Counter64
     MAX-ACCESS     read-only
     STATUS         current
     DESCRIPTION    ""
     ::= { rcKhiForwardingCbQeEntry 87 }

rcKhiForwardingCbQeEgressSt1TxTestPktCnt     OBJECT-TYPE
     SYNTAX         Counter64
     MAX-ACCESS     read-only
     STATUS         current
     DESCRIPTION    ""
     ::= { rcKhiForwardingCbQeEntry 88 }

rcKhiForwardingCbQeSvPartialPktCnt     OBJECT-TYPE
     SYNTAX         Counter64
     MAX-ACCESS     read-only
     STATUS         current
     DESCRIPTION    ""
     ::= { rcKhiForwardingCbQeEntry 89 }

rcKhiForwardingCbQeQmAgrWredDroppedPktCnt0     OBJECT-TYPE
     SYNTAX         Counter64
     MAX-ACCESS     read-only
     STATUS         current
     DESCRIPTION    ""
     ::= { rcKhiForwardingCbQeEntry 90 }

rcKhiForwardingCbQeQmAgrWredDroppedPktCnt1     OBJECT-TYPE
     SYNTAX         Counter64
     MAX-ACCESS     read-only
     STATUS         current
     DESCRIPTION    ""
     ::= { rcKhiForwardingCbQeEntry 91 }

rcKhiForwardingCbQeQmAgrWredDroppedPktCnt2     OBJECT-TYPE
     SYNTAX         Counter64
     MAX-ACCESS     read-only
     STATUS         current
     DESCRIPTION    ""
     ::= { rcKhiForwardingCbQeEntry 92 }

rcKhiForwardingCbQeQmAgrPolicedDroppedPktCnt     OBJECT-TYPE
     SYNTAX         Counter64
     MAX-ACCESS     read-only
     STATUS         current
     DESCRIPTION    ""
     ::= { rcKhiForwardingCbQeEntry 93 }

rcKhiForwardingCbQeQmAgrNonWredDroppedPktCnt     OBJECT-TYPE
     SYNTAX         Counter64
     MAX-ACCESS     read-only
     STATUS         current
     DESCRIPTION    ""
     ::= { rcKhiForwardingCbQeEntry 94 }

rcKhiForwardingCbQeQmError1     OBJECT-TYPE
     SYNTAX         Counter64
     MAX-ACCESS     read-only
     STATUS         current
     DESCRIPTION    ""
     ::= { rcKhiForwardingCbQeEntry 95 }  

-- KHI Forwarding IFP Table

rcKhiForwardingIfpTable  OBJECT-TYPE
     SYNTAX          SEQUENCE OF RcKhiForwardingIfpEntry
     MAX-ACCESS      not-accessible
     STATUS          deprecated
     DESCRIPTION     "Forwarding Ifp Key Health Indicator MIB - All VSP Data."
     ::= { rcKhiForwardingCb 7 }

rcKhiForwardingIfpEntry OBJECT-TYPE
     SYNTAX          RcKhiForwardingIfpEntry
     MAX-ACCESS      not-accessible
     STATUS          deprecated
     DESCRIPTION     "Forwarding Ifp KHI - VSP table entry."
     INDEX           { rcKhiForwardingIfpSlot,
                       rcKhiForwardingIfpIndex }
     ::= { rcKhiForwardingIfpTable 1 }

RcKhiForwardingIfpEntry ::=
     SEQUENCE {
        rcKhiForwardingIfpSlot           Integer32,
        rcKhiForwardingIfpIndex          Integer32,
        rcKhiForwardingIfpName           DisplayString,
        rcKhiForwardingIfpSlice0Ports    DisplayString,
        rcKhiForwardingIfpSlice0Cnt      Counter32,
        rcKhiForwardingIfpSlice1Ports    DisplayString,
        rcKhiForwardingIfpSlice1Cnt      Counter32,
        rcKhiForwardingIfpSlice2Ports    DisplayString,
        rcKhiForwardingIfpSlice2Cnt      Counter32
        }

rcKhiForwardingIfpSlot OBJECT-TYPE
    SYNTAX        Integer32 (3..12)
    MAX-ACCESS    not-accessible
    STATUS        deprecated
    DESCRIPTION   "Slot Number"
    ::= { rcKhiForwardingIfpEntry 1 }

rcKhiForwardingIfpIndex OBJECT-TYPE
    SYNTAX        Integer32 (3..500)
    MAX-ACCESS    not-accessible
    STATUS        deprecated
    DESCRIPTION   "Index of the IFP Rule"
    ::= { rcKhiForwardingIfpEntry 2 }

rcKhiForwardingIfpName OBJECT-TYPE
    SYNTAX        DisplayString (SIZE(0..80))
    MAX-ACCESS    read-only
    STATUS        deprecated
    DESCRIPTION   "Name of the IFP Rule"
    ::= { rcKhiForwardingIfpEntry 3 }

rcKhiForwardingIfpSlice0Ports OBJECT-TYPE
    SYNTAX        DisplayString (SIZE (0..15))
    MAX-ACCESS    read-only
    STATUS        deprecated
    DESCRIPTION   "Range of Ports in slice0 of the slot.
                   Display format will have Ports 1-24 or 1-8
                   based on the card type"
    ::= { rcKhiForwardingIfpEntry 4 }

rcKhiForwardingIfpSlice0Cnt OBJECT-TYPE
    SYNTAX        Counter32
    MAX-ACCESS    read-only
    STATUS        deprecated
    DESCRIPTION   "Counter for slice 0"
    ::= { rcKhiForwardingIfpEntry 5 }

rcKhiForwardingIfpSlice1Ports OBJECT-TYPE
    SYNTAX        DisplayString (SIZE (0..15))
    MAX-ACCESS    read-only
    STATUS        deprecated
    DESCRIPTION   "Range of Ports in slice1 of the slot.
                   Display format will have Ports 25-48 or 9-16
                   based on the card type"
    ::= { rcKhiForwardingIfpEntry 6 }

rcKhiForwardingIfpSlice1Cnt OBJECT-TYPE
    SYNTAX        Counter32
    MAX-ACCESS    read-only
    STATUS        deprecated
    DESCRIPTION   "Counter for slice 1"
    ::= { rcKhiForwardingIfpEntry 7 }

rcKhiForwardingIfpSlice2Ports OBJECT-TYPE
    SYNTAX        DisplayString (SIZE (0..15))
    MAX-ACCESS    read-only
    STATUS        deprecated
    DESCRIPTION   "Range of Ports in slice2 of the slot.
                   Display format will have Ports 0 or 17-24
                   based on the card type"
    ::= { rcKhiForwardingIfpEntry 8 }

rcKhiForwardingIfpSlice2Cnt OBJECT-TYPE
    SYNTAX        Counter32
    MAX-ACCESS    read-only
    STATUS        deprecated
    DESCRIPTION   "Counter for slice 2"
    ::= { rcKhiForwardingIfpEntry 9 }

-- KHI Forwarding IFP New Table

rcKhiForwardingIfpNewTable  OBJECT-TYPE
     SYNTAX          SEQUENCE OF RcKhiForwardingIfpNewEntry
     MAX-ACCESS      not-accessible
     STATUS          current
     DESCRIPTION     "Forwarding Ifp New Key Health Indicator MIB.
                      This table replaces the old table
                      rcKhiForwardingIfpTable"
     ::= { rcKhiForwardingCb 8 }

rcKhiForwardingIfpNewEntry OBJECT-TYPE
     SYNTAX          RcKhiForwardingIfpNewEntry
     MAX-ACCESS      not-accessible
     STATUS          current
     DESCRIPTION     "Forwarding Ifp KHI - VSP table entry."
     INDEX           { rcKhiForwardingIfpNewSlot,
                       rcKhiForwardingIfpNewTblType,
                       rcKhiForwardingIfpNewIndex }
     ::= { rcKhiForwardingIfpNewTable 1 }

RcKhiForwardingIfpNewEntry ::=
     SEQUENCE {
        rcKhiForwardingIfpNewSlot           Integer32,
        rcKhiForwardingIfpNewTblType        INTEGER,
        rcKhiForwardingIfpNewIndex          Integer32,
        rcKhiForwardingIfpNewName           DisplayString,
        rcKhiForwardingIfpNewSlice0Ports    DisplayString,
        rcKhiForwardingIfpNewSlice0Cnt      Counter32,
        rcKhiForwardingIfpNewSlice1Ports    DisplayString,
        rcKhiForwardingIfpNewSlice1Cnt      Counter32,
        rcKhiForwardingIfpNewSlice2Ports    DisplayString,
        rcKhiForwardingIfpNewSlice2Cnt      Counter32
        }

rcKhiForwardingIfpNewSlot OBJECT-TYPE
    SYNTAX        Integer32 (3..12)
    MAX-ACCESS    not-accessible
    STATUS        current
    DESCRIPTION   "Slot Number"
    ::= { rcKhiForwardingIfpNewEntry 1 }

rcKhiForwardingIfpNewTblType OBJECT-TYPE
    SYNTAX        INTEGER {
                      ifpPcv(1),
                      ifpPcvMacInMacTagged(2),
                      ifpPcvMacInMacUntagged(3)
                  }
    MAX-ACCESS    not-accessible
    STATUS        current
    DESCRIPTION   "Type of table IFP PCV for both 1G and 10G cards.
                   IFP PCV MAC-in-MAC Tagged and Untagged are for 10G card"
    ::= { rcKhiForwardingIfpNewEntry 2 }

rcKhiForwardingIfpNewIndex OBJECT-TYPE
    SYNTAX        Integer32 (3..500)
    MAX-ACCESS    not-accessible
    STATUS        current
    DESCRIPTION   "Index of the IFP Rule"
    ::= { rcKhiForwardingIfpNewEntry 3 }

rcKhiForwardingIfpNewName OBJECT-TYPE
    SYNTAX        DisplayString (SIZE(0..80))
    MAX-ACCESS    read-only
    STATUS        current
    DESCRIPTION   "Name of the IFP Rule"
    ::= { rcKhiForwardingIfpNewEntry 4 }

rcKhiForwardingIfpNewSlice0Ports OBJECT-TYPE
    SYNTAX        DisplayString (SIZE (0..15))
    MAX-ACCESS    read-only
    STATUS        current
    DESCRIPTION   "Range of Ports in slice0 of the slot.
                   Display format will have Ports 1-24 or 1-8
                   based on the card type"
    ::= { rcKhiForwardingIfpNewEntry 5 }

rcKhiForwardingIfpNewSlice0Cnt OBJECT-TYPE
    SYNTAX        Counter32
    MAX-ACCESS    read-only
    STATUS        current
    DESCRIPTION   "Counter for slice 0"
    ::= { rcKhiForwardingIfpNewEntry 6 }

rcKhiForwardingIfpNewSlice1Ports OBJECT-TYPE
    SYNTAX        DisplayString (SIZE (0..15))
    MAX-ACCESS    read-only
    STATUS        current
    DESCRIPTION   "Range of Ports in slice1 of the slot.
                   Display format will have Ports 25-48 or 9-16
                   based on the card type"
    ::= { rcKhiForwardingIfpNewEntry 7 }

rcKhiForwardingIfpNewSlice1Cnt OBJECT-TYPE
    SYNTAX        Counter32
    MAX-ACCESS    read-only
    STATUS        current
    DESCRIPTION   "Counter for slice 1"
    ::= { rcKhiForwardingIfpNewEntry 8 }

rcKhiForwardingIfpNewSlice2Ports OBJECT-TYPE
    SYNTAX        DisplayString (SIZE (0..15))
    MAX-ACCESS    read-only
    STATUS        current
    DESCRIPTION   "Range of Ports in slice2 of the slot.
                   Display format will have Ports 0 or 17-24
                   based on the card type"
    ::= { rcKhiForwardingIfpNewEntry 9 }

rcKhiForwardingIfpNewSlice2Cnt OBJECT-TYPE
    SYNTAX        Counter32
    MAX-ACCESS    read-only
    STATUS        current
    DESCRIPTION   "Counter for slice 2"
    ::= { rcKhiForwardingIfpNewEntry 10 }


rcKhiCpp OBJECT IDENTIFIER ::= { rcKhi 12 }

rcKhiCppPortStatsClear OBJECT-TYPE
     SYNTAX       TruthValue
     MAX-ACCESS   read-write
     STATUS       current
     DESCRIPTION  "Clear Khi Cpp Port Statistics MIB - All VSP Data."
     ::= { rcKhiCpp 1 }

rcKhiCppIoCopStatsClear OBJECT-TYPE
     SYNTAX       TruthValue
     MAX-ACCESS   read-write
     STATUS       current
     DESCRIPTION  "Clear Khi Cpp Slot Statistics MIB - All VSP Data."
     ::= { rcKhiCpp 2 }

-- KHI Cpp Port Statistics Table

rcKhiCppPortStatsTable OBJECT-TYPE
     SYNTAX          SEQUENCE OF RcKhiCppPortStatsEntry
     MAX-ACCESS      not-accessible
     STATUS          current
     DESCRIPTION     "Khi Cpp Port Statistics MIB - All VSP Data."
     ::= { rcKhiCpp 3 }

rcKhiCppPortStatsEntry OBJECT-TYPE
     SYNTAX          RcKhiCppPortStatsEntry
     MAX-ACCESS      not-accessible
     STATUS          current
     DESCRIPTION     "Khi Cpp Port Statistics - VSP table entry."
     INDEX           { rcKhiCppPortStatsPort,
                       rcKhiCppPortStatsPacket }
     ::= { rcKhiCppPortStatsTable 1 }


RcKhiCppPortStatsEntry ::=
     SEQUENCE {
        rcKhiCppPortStatsPort            InterfaceIndex,
        rcKhiCppPortStatsPacket          Integer32,
        rcKhiCppPortStatsPacketName      DisplayString,
        rcKhiCppPortStatsRxPackets       Counter64,
        rcKhiCppPortStatsTxPackets       Counter64
        }

rcKhiCppPortStatsPort OBJECT-TYPE
    SYNTAX        InterfaceIndex
    MAX-ACCESS    not-accessible
    STATUS        current
    DESCRIPTION   "Port Number-this entry contains information
                   about packet type, count of Rx and Tx packet"
    ::= { rcKhiCppPortStatsEntry 1 }

rcKhiCppPortStatsPacket OBJECT-TYPE
    SYNTAX        Integer32 (0..1023)
    MAX-ACCESS    not-accessible
    STATUS        current
    DESCRIPTION   "Packet Type"
    ::= { rcKhiCppPortStatsEntry 2 }

rcKhiCppPortStatsPacketName OBJECT-TYPE
    SYNTAX        DisplayString (SIZE(0..80))
    MAX-ACCESS    read-only
    STATUS        current
    DESCRIPTION   "Name of the Packet"
    ::= { rcKhiCppPortStatsEntry 3 }

rcKhiCppPortStatsRxPackets OBJECT-TYPE
    SYNTAX        Counter64
    MAX-ACCESS    read-only
    STATUS        current
    DESCRIPTION   "Rx count for a particular Packet Type"
    ::= { rcKhiCppPortStatsEntry 4 }

rcKhiCppPortStatsTxPackets OBJECT-TYPE
    SYNTAX        Counter64
    MAX-ACCESS    read-only
    STATUS        current
    DESCRIPTION   "Tx count for a particular Packet Type"
    ::= { rcKhiCppPortStatsEntry 5 }


-- KHI Cpp IoCop Statistics Table

rcKhiCppIoCopStatsTable OBJECT-TYPE
     SYNTAX          SEQUENCE OF RcKhiCppIoCopStatsEntry
     MAX-ACCESS      not-accessible
     STATUS          current
     DESCRIPTION     "Khi Cpp IoCop Statistics MIB - All VSP Data."
     ::= { rcKhiCpp 4 }

rcKhiCppIoCopStatsEntry OBJECT-TYPE
     SYNTAX          RcKhiCppIoCopStatsEntry
     MAX-ACCESS      not-accessible
     STATUS          current
     DESCRIPTION     "Khi Cpp IoCop Statistics - VSP table entry."
     INDEX           { rcKhiCppIoCopStatsSlot }
     ::= { rcKhiCppIoCopStatsTable 1 }

RcKhiCppIoCopStatsEntry ::=
     SEQUENCE {
        rcKhiCppIoCopStatsSlot              Integer32,
        rcKhiCppIoCopStatsMacMgmtRxPackets  Counter64,
        rcKhiCppIoCopStatsIpFixRxPackets    Counter64
        }

rcKhiCppIoCopStatsSlot OBJECT-TYPE
    SYNTAX        Integer32 (3..12)
    MAX-ACCESS    not-accessible
    STATUS        current
    DESCRIPTION   "Slot Number"
    ::= { rcKhiCppIoCopStatsEntry 1 }

rcKhiCppIoCopStatsMacMgmtRxPackets OBJECT-TYPE
    SYNTAX        Counter64
    MAX-ACCESS    read-only
    STATUS        current
    DESCRIPTION   "MacMgmt Rx Packets"
    ::= { rcKhiCppIoCopStatsEntry 2 }


rcKhiCppIoCopStatsIpFixRxPackets OBJECT-TYPE
    SYNTAX        Counter64
    MAX-ACCESS    read-only
    STATUS        current
    DESCRIPTION   "IpFix Rx Packets"
    ::= { rcKhiCppIoCopStatsEntry 3 }

rcKhiCppProtocolDrops   OBJECT IDENTIFIER ::= { rcKhiCpp 5 }

rcKhiCppProtocolDropsClear OBJECT-TYPE
     SYNTAX             TruthValue
     MAX-ACCESS         read-write
     STATUS             current
     DESCRIPTION        "Clear all protocol drop counters"
     ::= { rcKhiCppProtocolDrops 1 }

rcKhiCppProtocolDropsDataExpCnt OBJECT-TYPE
     SYNTAX             Counter64
     MAX-ACCESS         read-only
     STATUS             current
     DESCRIPTION        "Data Exp Drop Counter"
     ::= { rcKhiCppProtocolDrops 2 }

rcKhiCppProtocolDropsTtlExpCnt OBJECT-TYPE
     SYNTAX             Counter64
     MAX-ACCESS         read-only
     STATUS             current
     DESCRIPTION        "Ttl Exp Drop Counter"
     ::= { rcKhiCppProtocolDrops 3 }

rcKhiCppProtocolDropsIpmcDataCnt OBJECT-TYPE
     SYNTAX             Counter64
     MAX-ACCESS         read-only
     STATUS             current
     DESCRIPTION        "Ipmc Data Drop Counter"
     ::= { rcKhiCppProtocolDrops 4 }

rcKhiCppProtocolDropsMacLearningCnt OBJECT-TYPE
     SYNTAX             Counter64
     MAX-ACCESS         read-only
     STATUS             current
     DESCRIPTION        "Mac learning Drop Counter"
     ::= { rcKhiCppProtocolDrops 5 }

rcKhiCppProtocolDropsIsIsCnt OBJECT-TYPE
     SYNTAX             Counter64
     MAX-ACCESS         read-only
     STATUS             current
     DESCRIPTION        "IsIs Drop Counter"
     ::= { rcKhiCppProtocolDrops 6 }

rcKhiCppProtocolDropsBgpCnt OBJECT-TYPE
     SYNTAX             Counter64
     MAX-ACCESS         read-only
     STATUS             current
     DESCRIPTION        "Bgp Drop Counter"
     ::= { rcKhiCppProtocolDrops 7 }

rcKhiCppProtocolDropsRipV1Cnt OBJECT-TYPE
     SYNTAX             Counter64
     MAX-ACCESS         read-only
     STATUS             current
     DESCRIPTION        "RipV1 Drop Counter"
     ::= { rcKhiCppProtocolDrops 8 }

rcKhiCppProtocolDropsRipV2Cnt OBJECT-TYPE
     SYNTAX             Counter64
     MAX-ACCESS         read-only
     STATUS             current
     DESCRIPTION        "RipV2 Drop Counter"
     ::= { rcKhiCppProtocolDrops 9 }

rcKhiCppProtocolDropsOspfMcCnt OBJECT-TYPE
     SYNTAX             Counter64
     MAX-ACCESS         read-only
     STATUS             current
     DESCRIPTION        "Ospf Mc Drop Counter"
     ::= { rcKhiCppProtocolDrops 10 }

rcKhiCppProtocolDropsFtpCnt OBJECT-TYPE
     SYNTAX             Counter64
     MAX-ACCESS         read-only
     STATUS             current
     DESCRIPTION        "Ftp Drop Counter"
     ::= { rcKhiCppProtocolDrops 11 }

rcKhiCppProtocolDropsTftpCnt OBJECT-TYPE
     SYNTAX             Counter64
     MAX-ACCESS         read-only
     STATUS             current
     DESCRIPTION        "Tftp Drop Counter"
     ::= { rcKhiCppProtocolDrops 12 }

rcKhiCppProtocolDropsSnmpCnt OBJECT-TYPE
     SYNTAX             Counter64
     MAX-ACCESS         read-only
     STATUS             current
     DESCRIPTION        "Snmp Drop Counter"
     ::= { rcKhiCppProtocolDrops 13 }

rcKhiCppProtocolDropsTelnetCnt OBJECT-TYPE
     SYNTAX             Counter64
     MAX-ACCESS         read-only
     STATUS             current
     DESCRIPTION        "Telnet Drop Counter"
     ::= { rcKhiCppProtocolDrops 14 }

rcKhiCppProtocolDropsSshCnt OBJECT-TYPE
     SYNTAX             Counter64
     MAX-ACCESS         read-only
     STATUS             current
     DESCRIPTION        "Ssh Drop Counter"
     ::= { rcKhiCppProtocolDrops 15 }

rcKhiCppProtocolDropsRshCnt OBJECT-TYPE
     SYNTAX             Counter64
     MAX-ACCESS         read-only
     STATUS             current
     DESCRIPTION        "Rsh Drop Counter"
     ::= { rcKhiCppProtocolDrops 16 }

rcKhiCppProtocolDropsIstCtlCnt OBJECT-TYPE
     SYNTAX             Counter64
     MAX-ACCESS         read-only
     STATUS             current
     DESCRIPTION        "IstCtl Drop Counter"
     ::= { rcKhiCppProtocolDrops 17 }

rcKhiCppProtocolDropsRadiusCnt OBJECT-TYPE
     SYNTAX             Counter64
     MAX-ACCESS         read-only
     STATUS             current
     DESCRIPTION        "Radius Drop Counter"
     ::= { rcKhiCppProtocolDrops 18 }

rcKhiCppProtocolDropsNtpCnt OBJECT-TYPE
     SYNTAX             Counter64
     MAX-ACCESS         read-only
     STATUS             current
     DESCRIPTION        "Ntp Drop Counter"
     ::= { rcKhiCppProtocolDrops 19 }

rcKhiCppProtocolDropsDhcpCnt OBJECT-TYPE
     SYNTAX             Counter64
     MAX-ACCESS         read-only
     STATUS             current
     DESCRIPTION        "Dhcp Drop Counter"
     ::= { rcKhiCppProtocolDrops 20 }

rcKhiCppProtocolDropsIcmpV4Cnt OBJECT-TYPE
     SYNTAX             Counter64
     MAX-ACCESS         read-only
     STATUS             current
     DESCRIPTION        "IcmpV4 Drop Counter"
     ::= { rcKhiCppProtocolDrops 21 }

rcKhiCppProtocolDropsIcmpV6Cnt OBJECT-TYPE
     SYNTAX             Counter64
     MAX-ACCESS         read-only
     STATUS             current
     DESCRIPTION        "IcmpV6 Drop Counter"
     ::= { rcKhiCppProtocolDrops 22 }

rcKhiCppProtocolDropsIgmpCnt OBJECT-TYPE
     SYNTAX             Counter64
     MAX-ACCESS         read-only
     STATUS             current
     DESCRIPTION        "Igmp Drop Counter"
     ::= { rcKhiCppProtocolDrops 23 }

rcKhiCppProtocolDropsPimMcCnt OBJECT-TYPE
     SYNTAX             Counter64
     MAX-ACCESS         read-only
     STATUS             current
     DESCRIPTION        "Pim Mc Drop Counter"
     ::= { rcKhiCppProtocolDrops 24 }

rcKhiCppProtocolDropsVrrpCnt OBJECT-TYPE
     SYNTAX             Counter64
     MAX-ACCESS         read-only
     STATUS             current
     DESCRIPTION        "Vrrp Drop Counter"
     ::= { rcKhiCppProtocolDrops 25 }

rcKhiCppProtocolDropsArpReqCnt OBJECT-TYPE
     SYNTAX             Counter64
     MAX-ACCESS         read-only
     STATUS             current
     DESCRIPTION        "Arp Req Drop Counter"
     ::= { rcKhiCppProtocolDrops 26 }

rcKhiCppProtocolDropsArpOtherCnt OBJECT-TYPE
     SYNTAX             Counter64
     MAX-ACCESS         read-only
     STATUS             current
     DESCRIPTION        "Arp Other Drop Counter"
     ::= { rcKhiCppProtocolDrops 27 }

rcKhiCppProtocolDropsRarpReqCnt OBJECT-TYPE
     SYNTAX             Counter64
     MAX-ACCESS         read-only
     STATUS             current
     DESCRIPTION        "Rarp Req Drop Counter"
     ::= { rcKhiCppProtocolDrops 28 }

rcKhiCppProtocolDropsRarpOtherCnt OBJECT-TYPE
     SYNTAX             Counter64
     MAX-ACCESS         read-only
     STATUS             current
     DESCRIPTION        "Rarp Other Drop Counter"
     ::= { rcKhiCppProtocolDrops 29 }

rcKhiCppProtocolDropsSlppCnt OBJECT-TYPE
     SYNTAX             Counter64
     MAX-ACCESS         read-only
     STATUS             current
     DESCRIPTION        "Slpp Drop Counter"
     ::= { rcKhiCppProtocolDrops 30 }

rcKhiCppProtocolDropsBpduCnt OBJECT-TYPE
     SYNTAX             Counter64
     MAX-ACCESS         read-only
     STATUS             current
     DESCRIPTION        "Bpdu Drop Counter"
     ::= { rcKhiCppProtocolDrops 31 }

rcKhiCppProtocolDropsTdpCnt OBJECT-TYPE
     SYNTAX             Counter64
     MAX-ACCESS         read-only
     STATUS             current
     DESCRIPTION        "Tdp Drop Counter"
     ::= { rcKhiCppProtocolDrops 32 }

rcKhiCppProtocolDropsEapCnt OBJECT-TYPE
     SYNTAX             Counter64
     MAX-ACCESS         read-only
     STATUS             current
     DESCRIPTION        "Eap Drop Counter"
     ::= { rcKhiCppProtocolDrops 33 }

rcKhiCppProtocolDropsLacpCnt OBJECT-TYPE
     SYNTAX             Counter64
     MAX-ACCESS         read-only
     STATUS             current
     DESCRIPTION        "Lacp Drop Counter"
     ::= { rcKhiCppProtocolDrops 34 }
rcKhiCppProtocolDropsVlacpCnt OBJECT-TYPE
     SYNTAX             Counter64
     MAX-ACCESS         read-only
     STATUS             current
     DESCRIPTION        "Vlacp Drop Counter"
     ::= { rcKhiCppProtocolDrops 35 }

rcKhiCppProtocolDropsMldV2Cnt OBJECT-TYPE
     SYNTAX             Counter64
     MAX-ACCESS         read-only
     STATUS             current
     DESCRIPTION        "Mld V2 Drop Counter"
     ::= { rcKhiCppProtocolDrops 36 }

rcKhiCppProtocolDropsLldpCnt OBJECT-TYPE
     SYNTAX             Counter64
     MAX-ACCESS         read-only
     STATUS             current
     DESCRIPTION        "Lldp Drop Counter"
     ::= { rcKhiCppProtocolDrops 37 }

rcKhiCppProtocolDropsHttpCnt OBJECT-TYPE
     SYNTAX             Counter64
     MAX-ACCESS         read-only
     STATUS             current
     DESCRIPTION        "Http Drop Counter"
     ::= { rcKhiCppProtocolDrops 38 }

rcKhiCppProtocolDropsPimUcCnt OBJECT-TYPE
     SYNTAX             Counter64
     MAX-ACCESS         read-only
     STATUS             current
     DESCRIPTION        "Pim Uc Drop Counter"
     ::= { rcKhiCppProtocolDrops 39 }

rcKhiCppProtocolDropsOspfUcCnt OBJECT-TYPE
     SYNTAX             Counter64
     MAX-ACCESS         read-only
     STATUS             current
     DESCRIPTION        "Ospf Uc Drop Counter"
     ::= { rcKhiCppProtocolDrops 40 }

rcKhiCppProtocolDropsDnsCnt OBJECT-TYPE
     SYNTAX             Counter64
     MAX-ACCESS         read-only
     STATUS             current
     DESCRIPTION        "Dns Drop Counter"
     ::= { rcKhiCppProtocolDrops 41 }

rcKhiCppProtocolDropsIcmpBcCnt OBJECT-TYPE
     SYNTAX             Counter64
     MAX-ACCESS         read-only
     STATUS             current
     DESCRIPTION        "Icmp Bc Drop Counter"
     ::= { rcKhiCppProtocolDrops 42 }

rcKhiCppProtocolDropsIpfixCnt OBJECT-TYPE
     SYNTAX             Counter64
     MAX-ACCESS         read-only
     STATUS             current
     DESCRIPTION        "Ipfix Drop Counter"
     ::= { rcKhiCppProtocolDrops 43 }

rcKhiCppProtocolDropsTestPktCnt OBJECT-TYPE
     SYNTAX             Counter64
     MAX-ACCESS         read-only
     STATUS             current
     DESCRIPTION        "Test Pkt Drop Counter"
     ::= { rcKhiCppProtocolDrops 44 }


-- Begin of IpMRoute MIB
rcIpMRouteMIBObjects OBJECT IDENTIFIER ::= { rcIpMRoute 1 }

rcIpMRouteScalars OBJECT IDENTIFIER ::= { rcIpMRouteMIBObjects 1 }

--  The IP Multicast Stats enable.
--
rcIpMRouteStatsEnabled OBJECT-TYPE
    SYNTAX     TruthValue
    MAX-ACCESS read-write
    STATUS     current
    DESCRIPTION
            "The enabled status of IP Multicast statistics."
    DEFVAL            { false }
    ::= { rcIpMRouteScalars 2 }
 
rcIpMRouteStatsClear OBJECT-TYPE
    SYNTAX       TruthValue
    MAX-ACCESS   read-write
    STATUS       current
    DESCRIPTION  "Clear ip mroute stats."
    DEFVAL      { false }
    ::= { rcIpMRouteScalars 3 }

--  The IP Multicast Stats Table
--
rcIpMRouteStatsTable OBJECT-TYPE
    SYNTAX     SEQUENCE OF RcIpMRouteStatsEntry
    MAX-ACCESS not-accessible
    STATUS     current
    DESCRIPTION
            "the table containing IP Multicast statistics."
    ::= { rcIpMRouteMIBObjects 6 }

rcIpMRouteStatsEntry OBJECT-TYPE
    SYNTAX     RcIpMRouteStatsEntry
    MAX-ACCESS not-accessible
    STATUS     current
    DESCRIPTION
            "An entry containing the ip multicast statistics
            information for the specific group ip address."
    INDEX      { rcIpMRouteStatsGroupAddress }
    ::= { rcIpMRouteStatsTable 1 }

RcIpMRouteStatsEntry ::= SEQUENCE {
    rcIpMRouteStatsGroupAddress      IpAddress,
    rcIpMRouteStatsSourceCount       Counter32,
    rcIpMRouteStatsPkts              Counter64,
    rcIpMRouteStatsBytes             Counter64,
    rcIpMRouteStatsAverageSizePerPkt Integer32,
    rcIpMRouteStatsDropPkts          Counter64,
    rcIpMRouteStatsDropBytes         Counter64,
    rcIpMRouteStatsPktsPerSecond     Integer32
    }

rcIpMRouteStatsGroupAddress OBJECT-TYPE
    SYNTAX     IpAddress
    MAX-ACCESS not-accessible
    STATUS     current
    DESCRIPTION
            "the IP multicast group address for which this entry
            contains ip multicast statistics."
    ::= { rcIpMRouteStatsEntry 1 }

rcIpMRouteStatsSourceCount OBJECT-TYPE
    SYNTAX     Counter32
    MAX-ACCESS read-only
    STATUS     current
    DESCRIPTION
            "The number of sources corresponding to the specific group and vrf."
    ::= { rcIpMRouteStatsEntry 2 }

rcIpMRouteStatsPkts OBJECT-TYPE
    SYNTAX     Counter64
    MAX-ACCESS read-only
    STATUS     current
    DESCRIPTION
            "The total number of frames that are processed
                      corresponding to the specific group and vrf."
    ::= { rcIpMRouteStatsEntry 3 }

rcIpMRouteStatsBytes OBJECT-TYPE
    SYNTAX     Counter64
    MAX-ACCESS read-only
    STATUS     current
    DESCRIPTION
            "The total number of bytes that are processed
                      corresponding to the specific group and vrf."
    ::= { rcIpMRouteStatsEntry 4 }

rcIpMRouteStatsAverageSizePerPkt OBJECT-TYPE
    SYNTAX     Integer32
    MAX-ACCESS read-only
    STATUS     current
    DESCRIPTION
            "The average length of packets that are processed
                      corresponding to the specific group and vrf."
    ::= { rcIpMRouteStatsEntry 5 }

rcIpMRouteStatsDropPkts OBJECT-TYPE
    SYNTAX     Counter64
    MAX-ACCESS read-only
    STATUS     current
    DESCRIPTION
            "The total number of drop frames that are processed
                      corresponding to the specific group and vrf."
    ::= { rcIpMRouteStatsEntry 6 }

rcIpMRouteStatsDropBytes OBJECT-TYPE
    SYNTAX     Counter64
    MAX-ACCESS read-only
    STATUS     current
    DESCRIPTION
            "The total number of drop bytes that are processed
                      corresponding to the specific group and vrf."
    ::= { rcIpMRouteStatsEntry 7 }

rcIpMRouteStatsPktsPerSecond OBJECT-TYPE
    SYNTAX     Integer32
    MAX-ACCESS read-only
    STATUS     current
    DESCRIPTION
            "The number of packets that are processed
                      corresponding to the specific group and vrf in one second."
    ::= { rcIpMRouteStatsEntry 8 }

-- End of IpMRoute MIB

-- rcVspTalk MIB: Messaging service MIB 

rcVspTalkObjects   		    OBJECT IDENTIFIER ::= { rcVspTalk 1 }
rcVspTalkScalars  		    OBJECT IDENTIFIER ::= { rcVspTalkObjects 1 }

rcVspTalkGlobalEnable OBJECT-TYPE
	SYNTAX	      TruthValue
        MAX-ACCESS    read-write
        STATUS        current
        DESCRIPTION   "Create or destroy the VSPTalk related data structure and threads.
	              When it is false, rcVspTalkGroupTable entry will be removed."
	 DEFVAL { false }
        ::= { rcVspTalkScalars 1 }

rcVspTalkEndpointAddress OBJECT-TYPE
	SYNTAX	      IpAddress
        MAX-ACCESS    read-write
        STATUS        current
        DESCRIPTION   "The assigned circuitless IP address of the application endpoint
	               which must belong to the same subnet of existing IP interface on
		       device. This object assignment requires rcVspTalkEndpointVrfName
		       and rcVspTalkEndpointMacOffset"
        ::= { rcVspTalkScalars 2 }
    
rcVspTalkEndpointVrfName OBJECT-TYPE
	SYNTAX	      DisplayString (SIZE (0..16))
        MAX-ACCESS    read-write
        STATUS        current
        DESCRIPTION   "The name of the virtual Router which rcVspTalkEndpointAddress
	               belong to."
        ::= { rcVspTalkScalars 3 }

rcVspTalkNotificationEnable OBJECT-TYPE
	SYNTAX	      TruthValue
        MAX-ACCESS    read-write
        STATUS        current
        DESCRIPTION   "Enable/disable the notifcation of the register events"
	DEFVAL { false }
        ::= { rcVspTalkScalars 4 }

-- IM/GTALK/AVAYA group table --
    
rcVspTalkGroupTable OBJECT-TYPE
        SYNTAX        SEQUENCE OF RcVspTalkGroupEntry
        MAX-ACCESS    not-accessible
        STATUS        current
        DESCRIPTION   "Vsp Talk Group includes IM configuraton and users"
        ::= { rcVspTalkObjects 2 }

rcVspTalkGroupEntry OBJECT-TYPE
        SYNTAX        RcVspTalkGroupEntry
        MAX-ACCESS    not-accessible
        STATUS        current
        DESCRIPTION   "Entry of the IM group"
        INDEX         { rcVspTalkGroupType }
        ::= { rcVspTalkGroupTable 1 }

RcVspTalkGroupEntry ::=
        SEQUENCE {
                rcVspTalkGroupType                    INTEGER,
	        rcVspTalkGroupServerAddress           DisplayString,
		rcVspTalkGroupServerPort              Integer32,
		rcVspTalkGroupServerOldSslTypeEnable  TruthValue,
		rcVspTalkGroupServerEncryption        INTEGER,
		rcVspTalkGroupServerProxy             DisplayString,
		rcVspTalkGroupClientUsername          DisplayString,
		rcVspTalkGroupClientPassword          DisplayString,
		rcVspTalkGroupClientMembers           DisplayString,
		rcVspTalkGroupEnable                  TruthValue,
		rcVspTalkGroupRowStatus               RowStatus		
        }
     
rcVspTalkGroupType OBJECT-TYPE
        SYNTAX        INTEGER {
			  gtalk(2),
                          avaya(3)
	              }
        MAX-ACCESS    not-accessible
        STATUS        current
        DESCRIPTION   "Type of VSP messaging group"  
        ::= { rcVspTalkGroupEntry 1 }

rcVspTalkGroupServerAddress OBJECT-TYPE
        SYNTAX          DisplayString (SIZE (0..255))	
        MAX-ACCESS      read-create
        STATUS          current
        DESCRIPTION     "Messaging server address" 
        ::= { rcVspTalkGroupEntry 2 }

rcVspTalkGroupServerPort   OBJECT-TYPE
        SYNTAX          Integer32(1..49151)
        MAX-ACCESS      read-create
        STATUS          current
        DESCRIPTION     "The TCP port for Messaging"
        ::= { rcVspTalkGroupEntry 3 }

rcVspTalkGroupServerOldSslTypeEnable  OBJECT-TYPE
        SYNTAX        TruthValue
        MAX-ACCESS    read-create
        STATUS        current
        DESCRIPTION   "Enable/disable using old style SSL interface"
	DEFVAL       { false }
	::= { rcVspTalkGroupEntry 4}
    
rcVspTalkGroupServerEncryption OBJECT-TYPE
        SYNTAX        INTEGER {
			  asRequested(1),
			  required(2)
	              }
        MAX-ACCESS    read-create
        STATUS        current
        DESCRIPTION   "Encrytion option."
	DEFVAL       { required } 
        ::= { rcVspTalkGroupEntry 5 }
    
rcVspTalkGroupServerProxy OBJECT-TYPE
        SYNTAX          DisplayString (SIZE (0..255))	
        MAX-ACCESS      read-create
        STATUS          current
        DESCRIPTION     "Messaging server proxy" 
        ::= { rcVspTalkGroupEntry 6 }
    
rcVspTalkGroupClientUsername OBJECT-TYPE
        SYNTAX          DisplayString (SIZE (0..64))	
        MAX-ACCESS      read-create
        STATUS          current
        DESCRIPTION     "Messaging client Username for this device" 
        ::= { rcVspTalkGroupEntry 7 }

rcVspTalkGroupClientPassword OBJECT-TYPE
        SYNTAX        DisplayString (SIZE (0..80))
        MAX-ACCESS    read-create
        STATUS        current
        DESCRIPTION   "Password for rcVspTalkGroupClientUsername which is registered
                       in the server."
        ::= { rcVspTalkGroupEntry 8 }    

rcVspTalkGroupClientMembers OBJECT-TYPE
        SYNTAX          DisplayString (SIZE (0..1024))	
        MAX-ACCESS      read-create
        STATUS          current
        DESCRIPTION     "A list of members of this messaging group. There is 
                         a max of 12 members, with names seperated by comma" 
        ::= { rcVspTalkGroupEntry 9 }

rcVspTalkGroupEnable  OBJECT-TYPE
        SYNTAX        TruthValue
        MAX-ACCESS    read-create
        STATUS        current
        DESCRIPTION   "Adminstratively Enable/disable this messaging group"
	DEFVAL       { false }
	::= { rcVspTalkGroupEntry 10}

rcVspTalkGroupRowStatus  OBJECT-TYPE
        SYNTAX        RowStatus
        MAX-ACCESS    read-create
        STATUS        current
        DESCRIPTION   "Used to create/delete entries"
	::= { rcVspTalkGroupEntry 11}

-- End of VSPTalk

-- --------------------------------------------------------------
--  Vrrpv3 MIB Groups
--

rcVrrpTmpMib             OBJECT IDENTIFIER ::= { rcVrrpv3 1 }
rcVrrpTmpOperations      OBJECT IDENTIFIER ::= { rcVrrpTmpMib 1 }
rcVrrpTmpStatistics      OBJECT IDENTIFIER ::= { rcVrrpTmpMib 2 }

--
--  Start of MIB objects
--
rcVrrpTmpNotificationCntl  OBJECT-TYPE
   SYNTAX       INTEGER {
       enabled     (1),
       disabled    (2)
   }
   MAX-ACCESS   read-write
   STATUS       current
   DESCRIPTION
      "Indicates whether the VRRP-enabled router will generate
       SNMP notifications for events defined in this MIB.
       'Enabled' results in SNMP notifications; 'disabled', no
       notifications are sent."
   DEFVAL { enabled }
   ::= { rcVrrpTmpOperations 2 }

--
--  Vrrp Operations Table
--

rcVrrpTmpOperationsTable OBJECT-TYPE
   SYNTAX       SEQUENCE OF RcVrrpTmpOperationsEntry
   MAX-ACCESS   not-accessible
   STATUS       current
   DESCRIPTION
       "Unified Operations table for a VRRP router which
        consists of a sequence (i.e., one or more conceptual
        rows) of 'rcVrrpTmpOperationsEntry' items which describe
        the operational characteristics of a virtual router."
   ::= { rcVrrpTmpOperations 7 }

rcVrrpTmpOperationsEntry OBJECT-TYPE
   SYNTAX       RcVrrpTmpOperationsEntry
   MAX-ACCESS   not-accessible
   STATUS       current
   DESCRIPTION
       "An entry in the rcVrrpTmpOperationsTable containing the
        operational characteristics of a virtual router.  On a
        VRRP router, a given virtual router is identified by a
        combination of the IP version, VRID and ifIndex.
        ifIndex represents a physical interface of the router.
        Note that rows in this table can be distinguished on a
        multi-stacked device running VRRP over IPv4 and
        IPv6 on the same physical interface.
        Rows in the table cannot be modified unless the value
        of 'rcVrrpTmpOperationsState' has transitioned to
        'initialize'"
   INDEX    { rcVrrpTmpOperationsIfIndex,rcVrrpTmpOperationsInetAddrType,
              rcVrrpTmpOperationsVrId }
   ::= { rcVrrpTmpOperationsTable 1 }
RcVrrpTmpOperationsEntry ::=
   SEQUENCE {
       rcVrrpTmpOperationsIfIndex                        InterfaceIndex,
       rcVrrpTmpOperationsInetAddrType                   InetAddressType,
       rcVrrpTmpOperationsVrId                           VrId,
       rcVrrpTmpOperationsVirtualMacAddr                 MacAddress,
       rcVrrpTmpOperationsState                          INTEGER,
       rcVrrpTmpOperationsPriority                       Integer32,
       rcVrrpTmpOperationsAddrCount                      Integer32,
       rcVrrpTmpOperationsMasterIpAddr                   InetAddress,
       rcVrrpTmpOperationsPrimaryIpAddr                  InetAddress,
       rcVrrpTmpOperationsAdvInterval                    TimeInterval,
       rcVrrpTmpOperationsPreemptMode                    TruthValue,
       rcVrrpTmpOperationsAcceptMode                     TruthValue,
       rcVrrpTmpOperationsUpTime                         TimeStamp,
       rcVrrpTmpOperationsStorageType                    StorageType,
       rcVrrpTmpOperationsRowStatus                      RowStatus
}

rcVrrpTmpOperationsIfIndex OBJECT-TYPE
        SYNTAX       InterfaceIndex
        MAX-ACCESS   not-accessible
        STATUS       current
        DESCRIPTION  "port interface index."
        ::= { rcVrrpTmpOperationsEntry 1 }

rcVrrpTmpOperationsInetAddrType OBJECT-TYPE
   SYNTAX       InetAddressType
   MAX-ACCESS   not-accessible
   STATUS       current
   DESCRIPTION
       "The IP address type of RcVrrpTmpOperationsEntry. This value
        applies to both rcVrrpTmpOperationsMasterIpAddr and
        rcVrrpTmpOperationsPrimaryIpAddr."
   REFERENCE "RFC 4001"
   ::= { rcVrrpTmpOperationsEntry 2 }

rcVrrpTmpOperationsVrId OBJECT-TYPE
   SYNTAX       VrId
   MAX-ACCESS   not-accessible
   STATUS       current
   DESCRIPTION
       "This object contains the Virtual Router Identifier
        (VRID)."
   REFERENCE "RFC 4001"
   ::= { rcVrrpTmpOperationsEntry 3 }

rcVrrpTmpOperationsVirtualMacAddr OBJECT-TYPE
   SYNTAX       MacAddress
   MAX-ACCESS   read-only
   STATUS       current
   DESCRIPTION
       "The virtual MAC address of the virtual router.
        Although this object can be derived from the
        'rcVrrpTmpOperationsVrId' object, it is defined so that it
        is easily obtainable by a management application and
        can be included in VRRP-related SNMP notifications."
   REFERENCE "STD 58 RFC 2578"
   ::= { rcVrrpTmpOperationsEntry 4 }
rcVrrpTmpOperationsState OBJECT-TYPE
   SYNTAX       INTEGER {
       initialize(1),
       backup(2),
       master(3)
   }
   MAX-ACCESS   read-only
   STATUS       current
   DESCRIPTION
       "The current state of the virtual router. This object
       has three defined values:
         - `initialize', which indicates that the
           virtual router is waiting for a startup event.
         - `backup', which indicates the virtual router is
           monitoring the availability of the master router.
         - `master', which indicates that the virtual router
           is forwarding packets for IP addresses that are
           associated with this router."
   REFERENCE " RFC 3768"
   ::= { rcVrrpTmpOperationsEntry 5 }

rcVrrpTmpOperationsPriority OBJECT-TYPE
   SYNTAX       Integer32 (0..255)
   MAX-ACCESS   read-create
   STATUS       current
   DESCRIPTION
       "This object specifies the priority to be used for the
       virtual router master election process.  Higher values
       imply higher priority.
       A priority of '0', although not settable, is sent by
       the master router to indicate that this router has
       ceased to participate in VRRP and a backup virtual
       router should transition to become a new master.
       A priority of 255 is used for the router that owns the
       associated IP address(es) for VRRP over IPv4 and hence
       not settable.
       A 'badValue(3)' should be returned when a user tries to
       set 0 or 255 for this object. "
   DEFVAL       { 100 }
   ::= { rcVrrpTmpOperationsEntry 6 }

rcVrrpTmpOperationsAddrCount OBJECT-TYPE
   SYNTAX       Integer32 (0..255)
   MAX-ACCESS   read-only
   STATUS       current
   DESCRIPTION
       "The number of IP addresses that are associated with
       this virtual router.  This number is equal to the
       number of rows in the rcVrrpTmpAssociatedAddrTable that
       correspond to a given IP version/VRID/ifIndex."
   REFERENCE "RFC 3768 section 5.3.5.  Count IP Addrs"
   ::= { rcVrrpTmpOperationsEntry 7 }
rcVrrpTmpOperationsMasterIpAddr OBJECT-TYPE
   SYNTAX       InetAddress
   MAX-ACCESS   read-only
   STATUS       current
   DESCRIPTION
       "The master router's real IP address. Master router
       would set this address to rcVrrpTmpOperationsPrimaryIpAddr
       while transitioning to master state. For backup
       routers, this is the IP address listed as the source in
       VRRP advertisement last received by this virtual
       router."
   REFERENCE " RFC 3768"
   ::= { rcVrrpTmpOperationsEntry 8 }

rcVrrpTmpOperationsPrimaryIpAddr OBJECT-TYPE
   SYNTAX       InetAddress
   MAX-ACCESS   read-create
   STATUS       current
   DESCRIPTION
       "In the case where there are more than one IP
       Address (associated IP addresses) for a given
       `ifIndex', this object is used to specify the IP
       address that will become the
       rcVrrpTmpOperationsMasterIpAddr', should the virtual router
       transition from backup state to master."
   ::= { rcVrrpTmpOperationsEntry 9 }

rcVrrpTmpOperationsAdvInterval OBJECT-TYPE
   SYNTAX       TimeInterval (1..40)
   UNITS        "seconds"
   MAX-ACCESS   read-create
   STATUS       current
   DESCRIPTION
       "The time interval between sending advertisement messages. 
	Only the master router sends VRRP advertisements.
	It is configured in seconds, but it is converted into 
	centiseconds that is used in the VRRP packets."
   REFERENCE " RFC 3768 section 5.3.7"
   DEFVAL       { 1 }
   ::= { rcVrrpTmpOperationsEntry 10 }

rcVrrpTmpOperationsPreemptMode OBJECT-TYPE
   SYNTAX       TruthValue
   MAX-ACCESS   read-create
   STATUS       current
   DESCRIPTION
       "Controls whether a higher priority virtual router will
       preempt a lower priority master."
   REFERENCE " RFC 3768 section 6.1"
   DEFVAL       { true }
   ::= { rcVrrpTmpOperationsEntry 11 }
rcVrrpTmpOperationsAcceptMode OBJECT-TYPE
   SYNTAX       TruthValue
   MAX-ACCESS   read-create
   STATUS       current
   DESCRIPTION
       "Controls whether a virtual router in Master state
       will accept packets addressed to the address owner's
       IPv6 address as its own if it is not the IPv6 address
       owner.  Default is False.
       This object is not relevant for rows representing VRRP
       over IPv4 and should be set to false."
   DEFVAL       { false }
   ::= { rcVrrpTmpOperationsEntry 12 }

rcVrrpTmpOperationsUpTime OBJECT-TYPE
   SYNTAX       TimeStamp
   MAX-ACCESS   read-only
   STATUS       current
   DESCRIPTION
       "This is the value of the `sysUpTime' object when this
       virtual router (i.e., the `rcVrrpTmpOperationsState')
       transitioned out of `initialized'."
   REFERENCE " RFC 3768 section 6.1"
   ::= { rcVrrpTmpOperationsEntry 13 }

rcVrrpTmpOperationsStorageType OBJECT-TYPE
  SYNTAX      StorageType
  MAX-ACCESS  read-create
  STATUS      current
  DESCRIPTION
      "The storage type for this conceptual row. Write access
      is not required. It is optional to support nonVolatile
      StorageType enumeration."
  REFERENCE " RFC4181 section 4.6.4"
  DEFVAL       { nonVolatile }
  ::= { rcVrrpTmpOperationsEntry 14 }

rcVrrpTmpOperationsRowStatus OBJECT-TYPE
   SYNTAX       RowStatus
   MAX-ACCESS   read-create
   STATUS       current
   DESCRIPTION
       "The RowStatus variable should be used in accordance to
       installation and removal conventions for conceptual
       rows. When `rcVrrpTmpOperationsRowStatus' is set to
       active(1), no other objects in the conceptual row can
       be modified.
       To create a row in this table, a manager sets this
       object to either createAndGo(4) or createAndWait(5).
       Until instances of all corresponding columns are
       appropriately configured, the value of the
       corresponding instance of the `rcVrrpTmpOperationsRowStatus'
       column will be read as notReady(3).
       In particular, a newly created row cannot be made
       active(1) until (minimally) the corresponding instance
       of rcVrrpTmpOperationsInetAddrType, rcVrrpTmpOperationsVrId and
       rcVrrpTmpOperationsPrimaryIpAddr has been set and there is
       at least one active row in the
       `rcVrrpTmpAssociatedIpAddrTable' defining an associated
       IP address.
       notInService(2) should be used to administratively
       bring the row down.

       A typical order of operation to add a row is:
       1. Create a row in rcVrrpTmpOperationsTable with
       createAndWait(5).
       2. Create one or more corresponding rows in
       rcVrrpTmpAssociatedIpAddrTable.
       3. Populate the rcVrrpTmpOperationsEntry.
       4. set rcVrrpTmpOperationsRowStatus to active(1).

       A typical order of operation to delete an entry is:
       1. Set rcVrrpTmpOperationsRowStatus to notInService(2).
       2. Set the corresponding rows in
       rcVrrpTmpAssociatedIpAddrTable to destroy(6) to delete the
       entry.
       3. set rcVrrpTmpOperationsRowStatus to destroy(6) to delete
       the entry."
   ::= { rcVrrpTmpOperationsEntry 15 }

--
--  Vrrp Associated Address Table
--

rcVrrpTmpAssociatedIpAddrTable OBJECT-TYPE
   SYNTAX       SEQUENCE OF RcVrrpTmpAssociatedIpAddrEntry
   MAX-ACCESS   not-accessible
   STATUS       current
   DESCRIPTION
       "The table of addresses associated with this virtual
        router."
   ::= { rcVrrpTmpOperations 8 }

rcVrrpTmpAssociatedIpAddrEntry OBJECT-TYPE
   SYNTAX       RcVrrpTmpAssociatedIpAddrEntry
   MAX-ACCESS   not-accessible
   STATUS       current
   DESCRIPTION
       "An entry in the table contains an IP address that is
       associated with a virtual router.  The number of rows
       for a given IP version, VrID and ifIndex will equal the
       number of IP addresses associated (e.g., backed up) by
       the virtual router (equivalent to
       'rcVrrpTmpOperationsIpAddrCount').
       Rows in the table cannot be modified unless the value
       of `rcVrrpTmpOperationsState' has transitioned to
       `initialize'."
   INDEX    { rcVrrpTmpOperationsIfIndex,rcVrrpTmpOperationsInetAddrType,
              rcVrrpTmpOperationsVrId,rcVrrpTmpAssociatedIpAddr, rcVrrpTmpAssociatedIpAddrPrefixLength }
   ::= { rcVrrpTmpAssociatedIpAddrTable 1 }
RcVrrpTmpAssociatedIpAddrEntry ::=
   SEQUENCE {
       rcVrrpTmpAssociatedIpAddr
           InetAddress,
       rcVrrpTmpAssociatedIpAddrPrefixLength
           InetAddressPrefixLength,
       rcVrrpTmpAssociatedStorageType
           StorageType,
       rcVrrpTmpAssociatedIpAddrRowStatus
           RowStatus
}

rcVrrpTmpAssociatedIpAddr OBJECT-TYPE
   SYNTAX       InetAddress (SIZE(0|4|16))
   MAX-ACCESS   not-accessible
   STATUS       current
   DESCRIPTION
       "The assigned IP addresses that a virtual router is
       responsible for backing up.
       The size of this object is either 4 or 16 depending on
       rcVrrpTmpOperationsInetAddrType."
   REFERENCE "RFC 3768 Section 5.3.9"
   ::= { rcVrrpTmpAssociatedIpAddrEntry 1 }

rcVrrpTmpAssociatedIpAddrPrefixLength OBJECT-TYPE
   SYNTAX       InetAddressPrefixLength
   MAX-ACCESS   not-accessible
   STATUS       current
   DESCRIPTION
       "The length of the prefix (in bits)."
   ::= { rcVrrpTmpAssociatedIpAddrEntry 2 }

rcVrrpTmpAssociatedStorageType OBJECT-TYPE
  SYNTAX      StorageType
  MAX-ACCESS  read-create
  STATUS      current
  DESCRIPTION
      "The storage type for this conceptual row. Write access
      is not required. It is optional to support nonVolatile
      StorageType enumeration."
  REFERENCE " RFC4181 section 4.6.4"
  DEFVAL       { nonVolatile }
  ::= { rcVrrpTmpAssociatedIpAddrEntry 3 }
rcVrrpTmpAssociatedIpAddrRowStatus OBJECT-TYPE
   SYNTAX       RowStatus
   MAX-ACCESS   read-create
   STATUS       current
   DESCRIPTION
       "The RowStatus variable, used according to
       installation and removal conventions for conceptual
       rows. To create a row in this table, a manager sets
       this object to either createAndGo(4) or
       createAndWait(5). Setting this object to active(1)
       results in the addition of an associated address for a
       virtual router. Setting this object to notInService(2)
       results in administratively bringing down the row.
       Destroying the entry or setting it to destroy(6)
       removes the associated address from the virtual router.
       The use of other values is implementation-dependent.
       Only rcVrrpTmpAssociatedStorageType can be modified when the
       row is in active(1) state for Implementations
       supporting write access to rcVrrpTmpAssociatedStorageType
       Implementations should not allow deletion of the last
       row corresponding to an active row in
       rcVrrpTmpOperationsTable.
       Refer to description of rcVrrpTmpOperationsRowStatus for a
       typical row creation and deletion scenarios."
   ::= { rcVrrpTmpAssociatedIpAddrEntry 4 }

--
--  Vrrp Router Statistics
--

rcVrrpTmpRouterChecksumErrors OBJECT-TYPE

   SYNTAX       Counter32
   MAX-ACCESS   read-only
   STATUS       current
   DESCRIPTION
       "The total number of VRRP packets received with an
        invalid VRRP checksum value."
   REFERENCE "RFC3768 Section 5.3.8"
   ::= { rcVrrpTmpStatistics 1 }

rcVrrpTmpRouterVersionErrors OBJECT-TYPE
   SYNTAX       Counter32
   MAX-ACCESS   read-only
   STATUS       current
   DESCRIPTION
       "The total number of VRRP packets received with an
       unknown or unsupported version number."
   REFERENCE "RFC3768 Section 5.3.1"
   ::= { rcVrrpTmpStatistics 2 }
rcVrrpTmpRouterVrIdErrors OBJECT-TYPE
   SYNTAX       Counter32
   MAX-ACCESS   read-only
  STATUS       current
   DESCRIPTION
       "The total number of VRRP packets received with an
       invalid VRID for this virtual router."
   REFERENCE "RFC3768 Section 5.3.3"
   ::= { rcVrrpTmpStatistics 3 }

--
--  Vrrp Router Statistics Table
--

rcVrrpTmpRouterStatisticsTable OBJECT-TYPE
   SYNTAX       SEQUENCE OF RcVrrpTmpRouterStatisticsEntry
   MAX-ACCESS   not-accessible
   STATUS       current
   DESCRIPTION
       "Table of virtual router statistics."
   ::= { rcVrrpTmpStatistics 5 }

rcVrrpTmpRouterStatisticsEntry OBJECT-TYPE
   SYNTAX       RcVrrpTmpRouterStatisticsEntry
   MAX-ACCESS   not-accessible
   STATUS       current
   DESCRIPTION
       "An entry in the table, containing statistics
       information about a given virtual router."
   AUGMENTS    { rcVrrpTmpOperationsEntry }
   ::= { rcVrrpTmpRouterStatisticsTable 1 }

RcVrrpTmpRouterStatisticsEntry ::=
   SEQUENCE {
       rcVrrpTmpStatisticsMasterTransitions                   Counter32,
       rcVrrpTmpStatisticsRcvdAdvertisements                  Counter32,
       rcVrrpTmpStatisticsAdvIntervalErrors                   Counter32,
       rcVrrpTmpStatisticsIpTtlErrors                         Counter32,
       rcVrrpTmpStatisticsRcvdPriZeroPackets                  Counter32,
       rcVrrpTmpStatisticsSentPriZeroPackets                  Counter32,
       rcVrrpTmpStatisticsRcvdInvalidTypePkts                 Counter32,
       rcVrrpTmpStatisticsAddressListErrors                   Counter32,
       rcVrrpTmpStatisticsPacketLengthErrors                  Counter32,
       rcVrrpTmpStatisticsRcvdInvalidAuthentications          Counter32,
       rcVrrpTmpStatisticsDiscontinuityTime                   TimeStamp,
       rcVrrpTmpStatisticsRefreshRate                         Integer32
   }

rcVrrpTmpStatisticsMasterTransitions OBJECT-TYPE
   SYNTAX       Counter32
   MAX-ACCESS   read-only
   STATUS       current
   DESCRIPTION
       "The total number of times that this virtual router's
       state has transitioned to MASTER.
       Discontinuities in the value of this counter can occur
       at re-initialization of the management system, and at
       other times as indicated by the value of
       rcVrrpTmpStatisticsDiscontinuityTime."
   ::= { rcVrrpTmpRouterStatisticsEntry 1 }
rcVrrpTmpStatisticsRcvdAdvertisements OBJECT-TYPE
   SYNTAX       Counter32
   MAX-ACCESS   read-only
   STATUS       current
   DESCRIPTION
       "The total number of VRRP advertisements received by
       this virtual router.
       Discontinuities in the value of this counter can occur
       at re-initialization of the management system, and at
       other times as indicated by the value of
       rcVrrpTmpStatisticsDiscontinuityTime."
   ::= { rcVrrpTmpRouterStatisticsEntry 2 }

rcVrrpTmpStatisticsAdvIntervalErrors OBJECT-TYPE
   SYNTAX       Counter32
   MAX-ACCESS   read-only
   STATUS       current
   DESCRIPTION
       "The total number of VRRP advertisement packets
       received for which the advertisement interval is
       different than the one configured for the local virtual
       router.
       Discontinuities in the value of this counter can occur
       at re-initialization of the management system, and at
       other times as indicated by the value of
       rcVrrpTmpStatisticsDiscontinuityTime."
   ::= { rcVrrpTmpRouterStatisticsEntry 3 }

rcVrrpTmpStatisticsIpTtlErrors OBJECT-TYPE
   SYNTAX       Counter32
   MAX-ACCESS   read-only
   STATUS       current
   DESCRIPTION
       "The total number of VRRP packets received by the
       Virtual router with IPv4 TTL (for VRRP over IPv4) or
       IPv6 Hop Limit (for VRRP over IPv6) not equal to 255.
       Discontinuities in the value of this counter can occur
       at re-initialization of the management system, and at
       other times as indicated by the value of
       rcVrrpTmpStatisticsDiscontinuityTime."
   REFERENCE "RFC3768 Section 5.2.3"
   ::= { rcVrrpTmpRouterStatisticsEntry 4 }

rcVrrpTmpStatisticsRcvdPriZeroPackets OBJECT-TYPE
   SYNTAX       Counter32
   MAX-ACCESS   read-only
   STATUS       current
   DESCRIPTION
       "The total number of VRRP packets received by the
       virtual router with a priority of '0'.
       Discontinuities in the value of this counter can occur
       at re-initialization of the management system, and at
       other times as indicated by the value of
       rcVrrpTmpStatisticsDiscontinuityTime."
   REFERENCE "RFC3768 Section 5.3.4"
   ::= { rcVrrpTmpRouterStatisticsEntry 5 }

rcVrrpTmpStatisticsSentPriZeroPackets OBJECT-TYPE
   SYNTAX       Counter32
   MAX-ACCESS   read-only
   STATUS       current
   DESCRIPTION
       "The total number of VRRP packets sent by the virtual
       router with a priority of '0'.
       Discontinuities in the value of this counter can occur
       at re-initialization of the management system, and at
       other times as indicated by the value of
       rcVrrpTmpStatisticsDiscontinuityTime."
   REFERENCE "RFC3768 Section 5.3.4"
   ::= { rcVrrpTmpRouterStatisticsEntry 6 }

rcVrrpTmpStatisticsRcvdInvalidTypePkts OBJECT-TYPE
   SYNTAX       Counter32
   MAX-ACCESS   read-only
   STATUS       current
   DESCRIPTION
       "The number of VRRP packets received by the virtual
       router with an invalid value in the 'type' field.
       Discontinuities in the value of this counter can occur
       at re-initialization of the management system, and at
       other times as indicated by the value of
       rcVrrpTmpStatisticsDiscontinuityTime."
   ::= { rcVrrpTmpRouterStatisticsEntry 7 }

rcVrrpTmpStatisticsAddressListErrors OBJECT-TYPE
   SYNTAX       Counter32
   MAX-ACCESS   read-only
   STATUS       current
   DESCRIPTION
       "The total number of packets received for which the
       address list does not match the locally configured list
       for the virtual router.
       Discontinuities in the value of this counter can occur
       at re-initialization of the management system, and at
       other times as indicated by the value of
       rcVrrpTmpStatisticsDiscontinuityTime."
   ::= { rcVrrpTmpRouterStatisticsEntry 8 }

rcVrrpTmpStatisticsPacketLengthErrors OBJECT-TYPE
   SYNTAX       Counter32
   MAX-ACCESS   read-only
   STATUS       current
   DESCRIPTION
       "The total number of packets received with a packet
       length less than the length of the VRRP header.
       Discontinuities in the value of this counter can occur
       at re-initialization of the management system, and at
       other times as indicated by the value of
       rcVrrpTmpStatisticsDiscontinuityTime."
   ::= { rcVrrpTmpRouterStatisticsEntry 9 }
rcVrrpTmpStatisticsRcvdInvalidAuthentications OBJECT-TYPE
SYNTAX       Counter32
MAX-ACCESS   read-only
STATUS       current
DESCRIPTION
    "The total number of packets received with an unknown
     authentication type."
REFERENCE "RFC3768 Section 5.3.6"
::= { rcVrrpTmpRouterStatisticsEntry 10 }

rcVrrpTmpStatisticsDiscontinuityTime OBJECT-TYPE
  SYNTAX     TimeStamp
  MAX-ACCESS read-only
  STATUS     current
  DESCRIPTION
      "The value of sysUpTime on the most recent occasion at
       which any one or more of this entry's counters suffered
       a discontinuity.
       If no such discontinuities have occurred since the last
       re-initialization of the local management subsystem,
       then this object contains a zero value."
  ::= { rcVrrpTmpRouterStatisticsEntry 11 }

rcVrrpTmpStatisticsRefreshRate OBJECT-TYPE
  SYNTAX     Integer32
  UNITS "milli-seconds"
  MAX-ACCESS read-only
  STATUS     current
  DESCRIPTION
      "The minimum reasonable polling interval for this entry.
       This object provides an indication of the minimum
       Amount of time required to update the counters in this
       entry."
  ::= { rcVrrpTmpRouterStatisticsEntry 12 }

--
--   Notification Definitions
--
rcVrrpTmpNotifications   OBJECT IDENTIFIER ::= { rcVrrpTmpMib 0 }

---
--- Objects used in the notifications
---

rcVrrpTmpNewMasterReason OBJECT-TYPE
   SYNTAX        INTEGER {
       notmaster (0),
       priority  (1),
       preempted (2),
       masterNoResponse (3)
   }
   MAX-ACCESS   read-only
   STATUS       current
   DESCRIPTION
       "This indicates the reason for rcVrrpTmpNewMaster trap.
       Used by rcVrrpTmpTrapNewMaster trap. The object can be
       polled if the rcVrrpTmpNewMaster trap is lost to identify
       the reason for transmission. Backup router should
       return notmaster(0) when pooled. "
   ::= { rcVrrpTmpOperations 9 }

rcVrrpTmpTrapProtoErrReason OBJECT-TYPE
   SYNTAX        INTEGER {
       hopLimitError (0),
       versionError  (1),
       checksumError (2),
       vridError(3)
   }
   MAX-ACCESS   accessible-for-notify
   STATUS       current
   DESCRIPTION
       "This indicates the reason for protocol error trap.
       Used by rcVrrpTmpTrapProtoError trap."
   ::= { rcVrrpTmpOperations 10 }


rcVrrpTmpTrapNewMaster NOTIFICATION-TYPE
   OBJECTS      { rcVrrpTmpOperationsMasterIpAddr,
                  rcVrrpTmpNewMasterReason
                }
   STATUS       current
   DESCRIPTION
       "The newMaster trap indicates that the sending agent
       has transitioned to 'Master' state."
   ::= { rcVrrpTmpNotifications 1 }

rcVrrpTmpTrapProtoError NOTIFICATION-TYPE
   OBJECTS      { rcVrrpTmpTrapProtoErrReason
                }
   STATUS       current
   DESCRIPTION
       "The error trap indicates that the sending agent has
       encountered the protocol error indicated by
       rcVrrpTmpTrapProtoErrorReason."
   ::= { rcVrrpTmpNotifications 3 }

-- -----------------------------------------------------------------
--  Vrrp

rcVrrpExtMib               OBJECT IDENTIFIER ::= { rcVrrpv3 2 }
rcVrrpExtObjects           OBJECT IDENTIFIER ::= { rcVrrpExtMib 1 }
rcVrrpExtNotifications     OBJECT IDENTIFIER ::= { rcVrrpExtMib 2 }
rcVrrpExtOperations        OBJECT IDENTIFIER ::= { rcVrrpExtMib 3 }


-- ---------------------------------------------------------------------
-- Scalar Objects
-- ---------------------------------------------------------------------

rcVrrpExtScalars OBJECT IDENTIFIER ::= { rcVrrpExtObjects 1 }

rcVrrpExtVersionNumber OBJECT-TYPE
    SYNTAX          INTEGER { version3(3) }
      MAX-ACCESS      read-only
    STATUS          current
      DESCRIPTION     "The version number of Vrrp for IPv6 is 3."
      ::= { rcVrrpExtScalars 2 }


rcVrrpExtTrapStateTransitionType OBJECT-TYPE
    SYNTAX   INTEGER {
                none(1),
                masterToBackup(2),
                backupToMaster(3),
                initializeToMaster(4),
                masterToInitialize(5),
                initializeToBackup(6),
                backupToInitialize(7)
        }
        MAX-ACCESS   read-only
        STATUS       current
        DESCRIPTION
           "Potential types of state transitions.Used by
            rcVrrpv3TrapStateTransition trap."
      ::= { rcVrrpExtScalars 3 }

rcVrrpExtTrapStateTransitionCause OBJECT-TYPE
     SYNTAX        INTEGER {
                  none(1),
                higherPriorityAdvertizeReceived(2),
                shutdownReceived(3),
                rcVrrpAddrAndPhysicalAddrMatch(4),
                masterDownInterval(5),
                preempted(6)
        }
     MAX-ACCESS   read-only
     STATUS       current
     DESCRIPTION
       "Potential types of causes that will generate a
        rcVrrpExtTrapStateTransition trap."
     ::= { rcVrrpExtScalars 4 }

rcVrrpExtOperationsVrId OBJECT-TYPE
  SYNTAX       VrId
  MAX-ACCESS   read-only
  STATUS       current
  DESCRIPTION
      "This object contains the Virtual Router Identifier
       (VRID).This is used in rcVrrpExtTrapStateTransition."
  REFERENCE "RFC 4001"
  ::= { rcVrrpExtScalars 5 }


--   Trap Definitions

rcVrrpExtTrapStateTransition NOTIFICATION-TYPE
        OBJECTS      { ifIndex,
                        rcVrrpExtTrapStateTransitionType,
                        rcVrrpExtTrapStateTransitionCause,
                      rcVrrpExtOperationsVrId,
                      rcVrrpTmpOperationsPrimaryIpAddr,
                        rcVrrpTmpOperationsMasterIpAddr
        }
      STATUS       current
        DESCRIPTION
          "A rcVrrpExtTrapStateTransition trap signifies a state
             transition has occurred on a particular vrrp interface.
             Implementation of this trap is optional."
      ::= { rcVrrpExtNotifications 1 }
-- ---------------------------------------------------------------------
--
--  Vrrp Ext Operations Table
--
-- ---------------------------------------------------------------------


rcVrrpExtOperationsTable OBJECT-TYPE
   SYNTAX       SEQUENCE OF RcVrrpExtOperationsEntry
   MAX-ACCESS   not-accessible
   STATUS       current
   DESCRIPTION
      "Unified Operations table for a VRRP router which consists of
       a sequence (i.e., one or more conceptual rows) of
       'rcVrrpExtOperationsEntry'and 'rcVrrpTmpOperationsEntry' items
       which describe the operational characteristics of a virtual
       router.
       This table is an extention of 'rcVrrpTmpOperationsTable'.It
       contains the mib objects that are Nortel specific."
   ::= { rcVrrpExtOperations 11 }

rcVrrpExtOperationsEntry OBJECT-TYPE
    SYNTAX       RcVrrpExtOperationsEntry
    MAX-ACCESS   not-accessible
    STATUS       current
    DESCRIPTION
       "An entry in the rcVrrpExtOperationsTable containing the
        operational characteristics of a virtual router.  On a
        VRRP router, a given virtual router is identified by a
        combination of the IP version, VRID and ifIndex.
        ifIndex represents a physical interface of the router.
        Note that rows in this table can be distinguished on a
        multi-stacked device running VRRP over IPv4 and
        IPv6 on the same physical interface.
        Rows in the table cannot be modified unless the value
        of 'rcVrrpTmpOperationsState' has transitioned to
        'initialize'."
   AUGMENTS    { rcVrrpTmpOperationsEntry }
   ::= { rcVrrpExtOperationsTable 1 }

RcVrrpExtOperationsEntry ::=
   SEQUENCE {
    rcVrrpExtOperationsAction                        INTEGER,
    rcVrrpExtOperationsBackUpMaster                  INTEGER,
    rcVrrpExtOperationsBackUpMasterState             INTEGER,
    rcVrrpExtOperationsCriticalIpAddr                InetAddress,
    rcVrrpExtOperationsCriticalIpAddrEnabled         TruthValue,
    rcVrrpExtOperationsControl                       INTEGER,
    rcVrrpExtOperationsHoldDownTimer                 Integer32,
    rcVrrpExtOperationsHoldDownState                 INTEGER,
    rcVrrpExtOperationsHoldDownTimeRemaining         Integer32,
    rcVrrpExtOperationsFasterAdvInterval             Integer32,
    rcVrrpExtOperationsFasterAdvIntervalEnabled      TruthValue,
    rcVrrpExtOperationsLinkLocalAddr                 InetAddress,
    rcVrrpExtOperationsGlobalIpAddr                  InetAddress
   }
rcVrrpExtOperationsAction OBJECT-TYPE
        SYNTAX       INTEGER {
                            none(1),
                        preemptHoldDownTimer(2)
                }
      MAX-ACCESS   read-create
        STATUS       current
      DESCRIPTION
         "Used to trigger an action on this vrrp interface."
      ::= { rcVrrpExtOperationsEntry 1 }

rcVrrpExtOperationsBackUpMaster OBJECT-TYPE
      SYNTAX       INTEGER {
                  enabled(1),
                        disabled(2)
                }
        MAX-ACCESS   read-create
        STATUS       current
    DESCRIPTION
          "Enable the backup VRRP switch traffic forwarding.
               This will reduce the traffic in IST link in the
           time of SMLT."
      DEFVAL       { disabled }
        ::= { rcVrrpExtOperationsEntry 2 }

rcVrrpExtOperationsBackUpMasterState OBJECT-TYPE
        SYNTAX       INTEGER {
                        up(1),
                  down(2)
                }
      MAX-ACCESS   read-only
        STATUS       current
      DESCRIPTION
          "Indicate whether backup VRRP switch traffic
           forwarding is enabled or not."
        DEFVAL       { down }
      ::= { rcVrrpExtOperationsEntry 3 }

rcVrrpExtOperationsCriticalIpAddr OBJECT-TYPE
        SYNTAX       InetAddress
    MAX-ACCESS   read-create
        STATUS       current
      DESCRIPTION
          "IP address of the interface that will cause a
               shutdown event.Only IPv6 address is supported as of now."
      ::= { rcVrrpExtOperationsEntry 4 }

rcVrrpExtOperationsCriticalIpAddrEnabled OBJECT-TYPE
        SYNTAX       TruthValue
      MAX-ACCESS   read-create
        STATUS       current
      DESCRIPTION
             "Indicate if an user-defined critical IP address should be
          enabled. 'NO' = use the default IP address (::).
          No effect if an user-defined IP address does not exist."
    DEFVAL       { false }
    ::= { rcVrrpExtOperationsEntry 5 }
rcVrrpExtOperationsControl OBJECT-TYPE
        SYNTAX       INTEGER {
                    enabled(1),
                    disabled(2)
                }
      MAX-ACCESS   read-create
        STATUS       current
        DESCRIPTION
            "This object will enable/disable the virtual router
            function. Setting the value to 'enabled', will transition
            the state of the router from 'initialize to 'backup';
            Setting the value to 'disabled', will tranisition the
            router from 'master' or 'backup' to 'initialize'."
        DEFVAL    { enabled }
        ::= { rcVrrpExtOperationsEntry 6 }

rcVrrpExtOperationsHoldDownTimer OBJECT-TYPE
        SYNTAX       Integer32 (0..21600)
      UNITS         "seconds"
        MAX-ACCESS   read-create
        STATUS       current
      DESCRIPTION
               "Used to configure the amount of time (in seconds)
          to wait before preempting the current vrrp master."
        DEFVAL    { 0 }
        ::= { rcVrrpExtOperationsEntry 7 }

rcVrrpExtOperationsHoldDownState OBJECT-TYPE
        SYNTAX       INTEGER {
                        dormant(1),
                  active(2)
                }
    MAX-ACCESS   read-only
        STATUS       current
      DESCRIPTION
              "Used to indicate the hold-down state of this vrrp
         interface.  If the hold-down timer is operational
         this variable will be set to 'active'.  'dormant'
         otherwise."
      ::= { rcVrrpExtOperationsEntry 8 }

rcVrrpExtOperationsHoldDownTimeRemaining OBJECT-TYPE
      SYNTAX       Integer32 (0..21600)
    UNITS        "seconds"
        MAX-ACCESS   read-only
      STATUS       current
        DESCRIPTION
           "Used to indicate the amount of time (in seconds) left
          before the rcVrrpExtOperationsHoldDownTimer will expire."
      ::= { rcVrrpExtOperationsEntry 9 }
rcVrrpExtOperationsFasterAdvInterval OBJECT-TYPE
      SYNTAX       Integer32 (200..1000)
        MAX-ACCESS   read-create
      STATUS       current
        DESCRIPTION
          "This is the faster advertisement interval, in milliseconds,
           between sending advertisement messages. When the faster
              advertisement interval enable is checked, the faster
           advertisement interval is being used instead of the regular
           advertisement interval."
        DEFVAL       { 200 }
        ::= { rcVrrpExtOperationsEntry 10 }

rcVrrpExtOperationsFasterAdvIntervalEnabled OBJECT-TYPE
      SYNTAX       TruthValue
    MAX-ACCESS   read-create
        STATUS       current
      DESCRIPTION
         "Used to indicate if the Faster Advertisement Interval
          should be used.'Disable' means use regular Advertisement
          interval."
      DEFVAL       { false }
      ::= { rcVrrpExtOperationsEntry 11 }

rcVrrpExtOperationsLinkLocalAddr OBJECT-TYPE
        SYNTAX       InetAddress
        MAX-ACCESS   read-create
      STATUS       current
        DESCRIPTION
          "The assigned  Linklocal addresses to the  virtual
           router interface. This mib object support only IPv6
           address as of now."
      ::= { rcVrrpExtOperationsEntry 12 }

rcVrrpExtOperationsGlobalIpAddr OBJECT-TYPE
        SYNTAX       InetAddress
        MAX-ACCESS   read-create
        STATUS       current
        DESCRIPTION
          "The assigned Global addresses to the  virtual router
           interface. This mib object support only IPv6 address
           as of now."
        ::= { rcVrrpExtOperationsEntry 13 }

--
--  Lossless Ethernet Port Table

rcPortLosslessEnetTable OBJECT-TYPE
        SYNTAX        SEQUENCE OF RcPortLosslessEnetEntry
        MAX-ACCESS    not-accessible
        STATUS        current
        DESCRIPTION   "Port Lossless Ethernet Table"
        ::= { rcPort 13 }

rcPortLosslessEnetEntry OBJECT-TYPE
        SYNTAX        RcPortLosslessEnetEntry
        MAX-ACCESS    not-accessible
        STATUS        current
        DESCRIPTION   "Entry containing lossless Ethernet information
                       for a particular port."
        INDEX         { rcPortLosslessEnetIndex }
        ::= { rcPortLosslessEnetTable 1 }

RcPortLosslessEnetEntry ::= SEQUENCE {
          rcPortLosslessEnetIndex        InterfaceIndex,
          rcPortLosslessEnetConfigured   TruthValue,
          rcPortLosslessEnetPauseType    INTEGER,
          rcPortLosslessEnetPfcBandwidth Integer32
        }

rcPortLosslessEnetIndex OBJECT-TYPE
        SYNTAX          InterfaceIndex
        MAX-ACCESS      not-accessible 
        STATUS          current
        DESCRIPTION     "An index value that uniquely identifies a port.
                         This value is similar to ifIndex in MIB2.
                         Lossless Ethernet will be limited to 10Gig
                         ports."
        ::= { rcPortLosslessEnetEntry 1 }

rcPortLosslessEnetConfigured OBJECT-TYPE
        SYNTAX          TruthValue
        MAX-ACCESS      read-write
        STATUS          current
        DESCRIPTION     "To enable lossless mode for the port"
        DEFVAL          { false }
        ::= { rcPortLosslessEnetEntry 2 }

rcPortLosslessEnetPauseType OBJECT-TYPE
        SYNTAX          INTEGER {
                                fc(1),
                                pfc(2)
                        }
        MAX-ACCESS      read-write
        STATUS          current
        DESCRIPTION     "Pause frame type.  fc - Pause,
                         pfc - priority-based flow control."
        DEFVAL          { fc }
        ::= { rcPortLosslessEnetEntry 3 }

rcPortLosslessEnetPfcBandwidth OBJECT-TYPE
        SYNTAX          Integer32(2..8)
        MAX-ACCESS      read-write
        STATUS          current
        DESCRIPTION     "Guaranteed bandwidth in Gbps when
                         rcPortLosslessEnetPauseType is set to pfc(2)."
        DEFVAL          { 5 }
        ::= { rcPortLosslessEnetEntry 4 }
-- IS-IS

rcIsisGlobalGroup OBJECT IDENTIFIER ::= { rcIsis 1 }

rcIsisGlobalAreaAuthType  OBJECT-TYPE
        SYNTAX        INTEGER {
                                none(0),
                                simple(1),
                                hmac-md5(2)
                              }
        MAX-ACCESS    read-write
        STATUS        current
        DESCRIPTION   "The authentication type for the area"
	    DEFVAL		{ none }
               ::= { rcIsisGlobalGroup 1 }

rcIsisGlobalAreaKeyId  OBJECT-TYPE
        SYNTAX        Integer32 (1..255)
        MAX-ACCESS    read-write
        STATUS        current
        DESCRIPTION   "Authentication key-id for the area. This is 
                       required if the auth-type is hmac-md5 else it is 
                       not required."
        ::= { rcIsisGlobalGroup 2 }

rcIsisGlobalAreaAuthKey  OBJECT-TYPE
        SYNTAX        OCTET STRING (SIZE(0..255))
        MAX-ACCESS    read-write
        STATUS        current
        DESCRIPTION   "Authentication key, this key will be used to 
                       authenticate the LSP's received on the area"
        ::= { rcIsisGlobalGroup 3 }

rcIsisGlobalDomainAuthType	OBJECT-TYPE
        SYNTAX        INTEGER {
                          none(0),
                          simple(1),
                          hmac-md5(2)
                      } 
	    MAX-ACCESS    read-write
        STATUS        current 
        DESCRIPTION   "The authentication type for the domain"
	    DEFVAL        { none }
        ::= { rcIsisGlobalGroup 4 }

rcIsisGlobalDomainKeyId  OBJECT-TYPE
        SYNTAX        Integer32 (1..255)
        MAX-ACCESS    read-write
        STATUS        current
        DESCRIPTION   "The authentication key-id for the domain. This is
                       required if the auth-type is hmac-md5 else it is
                       not required."
        ::= { rcIsisGlobalGroup 5 }

rcIsisGlobalDomainAuthKey  OBJECT-TYPE
        SYNTAX        OCTET STRING (SIZE(0..255))
        MAX-ACCESS    read-write
        STATUS        current
        DESCRIPTION   "Authentication key, this key will be used to 
                       authenticate the LSP's received on the domain"
        ::= { rcIsisGlobalGroup 6 }

rcIsisGlobalCsnpInt	OBJECT-TYPE
        SYNTAX        Integer32 (1..600)
        MAX-ACCESS    read-write
        STATUS        current
        DESCRIPTION   "Interval of time, in seconds, between periodic
                       transmission of a complete set of CSNPs on
                       multiaccess networks if this router is the
                       designated router at this level.
                       This object follows the resettingTimer behavior.
                       For ResettingTimer description see the ISIS MIB"
	    DEFVAL        { 10 }
        ::= { rcIsisGlobalGroup 7 }

rcIsisGlobalRxmtLspInt  OBJECT-TYPE
        SYNTAX        Integer32 (1..300)
        MAX-ACCESS    read-write
        STATUS        current
        DESCRIPTION   "Minimum interval, in seconds, between 
                       re-transmission of a LSP at this level. This 
                       object follows the resettingTimer behavior.
                       For ResettingTimer description see the ISIS MIB"
        DEFVAL        { 5 }
        ::= { rcIsisGlobalGroup 8 }

rcIsisGlobalPSNPInterval OBJECT-TYPE
        SYNTAX     Integer32 (1..120)
        UNITS      "seconds"
        MAX-ACCESS read-write
        STATUS     current
        DESCRIPTION "Minimum interval in seconds between sending Partial
                     Sequence Number PDUs at this level. This object
                     follows the resettingTimer behavior.
                     For ResettingTimer description see the ISIS MIB"
        DEFVAL { 2 }
        ::= { rcIsisGlobalGroup 9 }

rcIsisGlobalHostName OBJECT-TYPE
        SYNTAX     OCTET STRING (SIZE (0..255))
        MAX-ACCESS read-write
        STATUS     current
        DESCRIPTION   
            "The hostname listed in LSP, or the system name if host 
             name is not configured."
        ::= { rcIsisGlobalGroup 10 }

rcIsisGlobalSpfDelay OBJECT-TYPE
        SYNTAX     Integer32 (0..5000)
        UNITS      "milliseconds"
        MAX-ACCESS read-write
        STATUS     current
        DESCRIPTION "ISIS SPF delay in miliseconds"
        DEFVAL { 100 }
        ::= { rcIsisGlobalGroup 11 }

rcIsisGlobalControlVlan OBJECT-TYPE
        SYNTAX     Integer32 (1..4084)
        MAX-ACCESS read-write
        STATUS     current
        DESCRIPTION "ISIS control vlan ID"
        ::= { rcIsisGlobalGroup 12 }

rcIsisGlobalIpSourceAddress OBJECT-TYPE
        SYNTAX     InetAddress
        MAX-ACCESS read-write
        STATUS     current
        DESCRIPTION "ISIS PLSB IP address. Define an existing router interface
		     for management (ping/traceroute)"
        ::= { rcIsisGlobalGroup 13 }

rcIsisGlobalIpSourceAddressType OBJECT-TYPE
        SYNTAX     InetAddressType
        MAX-ACCESS read-write
        STATUS     current
        DESCRIPTION "The type of address for existing router interface
		     for management (ping/traceroute)"
        ::= { rcIsisGlobalGroup 14 }



-- BEGIN rcIsisCircuitTable --

rcIsisCircuitTable      OBJECT-TYPE
        SYNTAX          SEQUENCE OF RcIsisCircuitEntry
        MAX-ACCESS      not-accessible
        STATUS          current
        DESCRIPTION     "Table of IS-IS Circuit, this is extension
                         to the isisCircTable defined in ISIS MIB"
        ::= { rcIsis 2 }

rcIsisCircuitEntry OBJECT-TYPE
        SYNTAX          RcIsisCircuitEntry
        MAX-ACCESS      not-accessible
        STATUS          current
        DESCRIPTION     "An entry of rcIsisCircuit Table. A Entry in 
                         table exists for each ISIS circuit created"
        INDEX           { rcIsisCircuitIndex }
        ::= { rcIsisCircuitTable 1 }

RcIsisCircuitEntry   ::=
        SEQUENCE {
          rcIsisCircuitIndex        Integer32,
          rcIsisCircuitType         INTEGER,
          rcIsisCircuitAuthType     INTEGER,
          rcIsisCircuitKeyId        INTEGER,
          rcIsisCircuitAuthKey      OCTET STRING,
          rcIsisCircuitAddr         IpAddress,
          rcIsisCircuitMask         IpAddress,
          rcIsisCircuitOperState    INTEGER,
          rcIsisCircuitNumAdj       Integer32,
          rcIsisCircuitNumUpAdj     Integer32
        }

rcIsisCircuitIndex   OBJECT-TYPE
        SYNTAX        Integer32
        MAX-ACCESS    not-accessible
        STATUS        current
        DESCRIPTION  "The identifier of this circuit, unique within the
                      Intermediate System.  This object follows
                      the index behavior.  This is for SNMP Indexing
                      purposes only and need not have any relation to
                      any protocol value."
        ::= { rcIsisCircuitEntry 1 }

rcIsisCircuitType    OBJECT-TYPE
        SYNTAX        INTEGER {
                          bcast(1),
                          ptpt(2), 
                          passive(3)
                      }
        MAX-ACCESS    read-write
        STATUS        current
        DESCRIPTION   "ISIS circuit type this is an extention to 
                       ISIS circuit table, this was required a 
                       standard MIB circuit type does not support
                       passive type"
	    DEFVAL        { bcast }
        ::= { rcIsisCircuitEntry 2 }

rcIsisCircuitAuthType    OBJECT-TYPE
        SYNTAX        INTEGER {
                         none(0),
                         simple(1),
                         hmac-md5(2)
                      }
        MAX-ACCESS    read-write
        STATUS        current
        DESCRIPTION   "Authentication type for IIH to be sent/reveived
                       on the circuit/interface"
	    DEFVAL        { none }
        ::= { rcIsisCircuitEntry 3 }

rcIsisCircuitKeyId     OBJECT-TYPE
        SYNTAX        INTEGER (1..255)
        MAX-ACCESS    read-write
        STATUS        current
        DESCRIPTION   "Authentication key id related to IIH key 
                       This can be set only if the auth-type is hmac-md5"
        ::= { rcIsisCircuitEntry 4 }

rcIsisCircuitAuthKey     OBJECT-TYPE
        SYNTAX        OCTET STRING(SIZE(0..255))
        MAX-ACCESS    read-write
        STATUS        current
        DESCRIPTION   "Authentication key to be used to authenticate
                       IIH sent/reveived on the circuit/interface"
        ::= { rcIsisCircuitEntry 5 }

rcIsisCircuitAddr     OBJECT-TYPE
        SYNTAX        IpAddress
        MAX-ACCESS    read-only
        STATUS        current
        DESCRIPTION   "IP address associated with the interface"
        ::= { rcIsisCircuitEntry 6 }

rcIsisCircuitMask     OBJECT-TYPE
        SYNTAX        IpAddress
        MAX-ACCESS    read-only
        STATUS        current
        DESCRIPTION   "IP mask associated with the interface"
        ::= { rcIsisCircuitEntry 7 }

rcIsisCircuitOperState     OBJECT-TYPE
        SYNTAX        INTEGER {
                        unknown(0),
                        up(1),
                        down(2)
                      }
        MAX-ACCESS    read-only
        STATUS        current
        DESCRIPTION   "This variable tells the operating state of circ"
        ::= { rcIsisCircuitEntry 8 }

rcIsisCircuitNumAdj     OBJECT-TYPE
        SYNTAX        Integer32
        MAX-ACCESS    read-only
        STATUS        current
        DESCRIPTION   "NUmber of adjacencies"
        ::= { rcIsisCircuitEntry 9 }

rcIsisCircuitNumUpAdj     OBJECT-TYPE
        SYNTAX        Integer32
        MAX-ACCESS    read-only
        STATUS        current
        DESCRIPTION   "Number of adjancencies which are UP"
        ::= { rcIsisCircuitEntry 10 }

rcIsisStats OBJECT IDENTIFIER ::= { rcIsis 3 }

rcIsisStatsClearErrorCounters  OBJECT-TYPE
     SYNTAX             TruthValue
     MAX-ACCESS         read-write
     STATUS             current
     DESCRIPTION        "Clear ISIS global and interface error counters."
     DEFVAL             { false }
     ::= { rcIsisStats 1 }

rcIsisStatsClearPacketCounters  OBJECT-TYPE
     SYNTAX             TruthValue
     MAX-ACCESS         read-write
     STATUS             current
     DESCRIPTION        "Clear IS-IS control packets sent and received 
                        at each level on all the interface/circuits."
     DEFVAL             { false }
     ::= { rcIsisStats 2 }


-- BEGIN rcIsisPlsbTable --
 
rcIsisPlsbTable  OBJECT-TYPE
          SYNTAX          SEQUENCE OF RcIsisPlsbEntry
          MAX-ACCESS      not-accessible
          STATUS          current
          DESCRIPTION     "Table of PLSB under IS-IS"
        ::= { rcIsis 4} 

rcIsisPlsbEntry OBJECT-TYPE
        SYNTAX          RcIsisPlsbEntry
        MAX-ACCESS      not-accessible
        STATUS          current
        DESCRIPTION     "An entry of rcIsisPlsb Table. A Entry in 
                         table exists for each plsb instance created"
        INDEX           { rcIsisPlsbId }
        ::= { rcIsisPlsbTable 1 }

RcIsisPlsbEntry   ::=
        SEQUENCE {
        rcIsisPlsbId              Integer32, 
        rcIsisPlsbRowStatus       RowStatus,
        rcIsisPlsbNodeNickName    IsisPlsbNodeNickName,
        rcIsisPlsbVlans           OCTET STRING(SIZE(512)),
        rcIsisPlsbLsdbTrap        EnableValue,
        rcIsisPlsbState           EnableValue,
	rcIsisPlsbIpShortcut	  EnableValue,
	rcIsisPlsbPrimaryVlan	  Integer32, 
	rcIsisPlsbSmltSplitBEB	  INTEGER,
	rcIsisPlsbSmltBmac	  MacAddress,
	rcIsisPlsbSmltPeerSysId   IsisSystemID  
        }

rcIsisPlsbId OBJECT-TYPE
        SYNTAX          Integer32 (1..100)
        MAX-ACCESS      not-accessible
        STATUS          current
        DESCRIPTION
            "PLSB instance ID"
    ::= { rcIsisPlsbEntry 1 }

rcIsisPlsbRowStatus  OBJECT-TYPE
        SYNTAX RowStatus
        MAX-ACCESS read-create
        STATUS current
        DESCRIPTION
            "The state of the rcIsisPlsbEntry.  "
    ::= { rcIsisPlsbEntry 2 }

rcIsisPlsbNodeNickName OBJECT-TYPE
        SYNTAX IsisPlsbNodeNickName
        MAX-ACCESS read-create
        STATUS current
        DESCRIPTION
            "PLSB node's nickname is used to
             calculate ISID multicast mac address."
    ::= { rcIsisPlsbEntry 3 }

rcIsisPlsbVlans OBJECT-TYPE
        SYNTAX          OCTET STRING(SIZE(512))
        MAX-ACCESS      read-create   
        STATUS          current
        DESCRIPTION
            "PLSB ISIS vlans for a PLSB instance."
    ::= { rcIsisPlsbEntry 4 }

rcIsisPlsbLsdbTrap OBJECT-TYPE
        SYNTAX        EnableValue
        MAX-ACCESS    read-create
        STATUS        current
        DESCRIPTION   "isis PLSB lsdb update trap enable on this plsb instance"
	DEFVAL        { disable }
        ::= { rcIsisPlsbEntry 5 }

rcIsisPlsbState OBJECT-TYPE
        SYNTAX        EnableValue
        MAX-ACCESS    read-create
        STATUS        current
        DESCRIPTION   "enable/disable PLSB."
        ::= { rcIsisPlsbEntry 6 }

rcIsisPlsbIpShortcut OBJECT-TYPE
        SYNTAX        EnableValue
        MAX-ACCESS    read-create
        STATUS        current
        DESCRIPTION   "ISIS PLSB IP shortcut enabled"
        DEFVAL        { disable }
        ::= { rcIsisPlsbEntry 7 }

rcIsisPlsbPrimaryVlan OBJECT-TYPE
        SYNTAX        Integer32 (1..4084)
        MAX-ACCESS    read-create
        STATUS        current
        DESCRIPTION   "Primary Vlan Id for this plsb instance."
        ::= { rcIsisPlsbEntry 8 }

rcIsisPlsbSmltSplitBEB OBJECT-TYPE
        SYNTAX        INTEGER {
                          primary(1),
                          secondary(2)
		      }
        MAX-ACCESS    read-only
        STATUS        current
        DESCRIPTION   "ISIS PLSB SMLT split BEB for this plsb instance."
        DEFVAL        { primary }
        ::= { rcIsisPlsbEntry 9 }

rcIsisPlsbSmltBmac OBJECT-TYPE
        SYNTAX        MacAddress 
        MAX-ACCESS    read-create
        STATUS        current
        DESCRIPTION   "ISIS PLSB SMLT virtual MAC for this plsb instance."
        ::= { rcIsisPlsbEntry 10 }

rcIsisPlsbSmltPeerSysId OBJECT-TYPE
        SYNTAX        IsisSystemID
        MAX-ACCESS    read-create
        STATUS        current
        DESCRIPTION   "ISIS PLSB SMLT Peer's system-id for this plsb instance."
        ::= { rcIsisPlsbEntry 11 }

-- BEGIN rcIsisCircuitPlsbTable --

IsisDefaultL1Metric ::= TEXTUAL-CONVENTION
        DISPLAY-HINT "d"
        STATUS current
        DESCRIPTION
            "Integer sub-range for default metric for single hop.
             ISO 10589 provides for 4 types of metric.  Only the
             'default' metric is used in practice."
        SYNTAX Integer32 (1..63)

IsisWideL1Metric ::= TEXTUAL-CONVENTION
        DISPLAY-HINT "d"
        STATUS current
        DESCRIPTION
            "Wide Metric for IS Neighbors.  ISO 10589 provides a
             6 bit metric.  Traffic Engineering extensions provide
             24 bit metrics."
        SYNTAX Integer32 (1..16777215)

rcIsisCircuitPlsbTable      OBJECT-TYPE
        SYNTAX          SEQUENCE OF RcIsisCircuitPlsbEntry
        MAX-ACCESS      not-accessible
        STATUS          current
        DESCRIPTION     "Table of IS-IS Circuit PLSB instance"
        ::= { rcIsis 5 }

rcIsisCircuitPlsbEntry OBJECT-TYPE
        SYNTAX          RcIsisCircuitPlsbEntry
        MAX-ACCESS      not-accessible
        STATUS          current
        DESCRIPTION     "An entry of rcIsisCircuitPlsb Table. A Entry in 
                         table exists for each PLSB instance under a ISIS 
                        circuit created"
        INDEX           { rcIsisCircuitPlsbIndex,
                         rcIsisCircuitPlsbId}
        ::= { rcIsisCircuitPlsbTable 1 }

RcIsisCircuitPlsbEntry   ::=
        SEQUENCE {
          rcIsisCircuitPlsbIndex      Integer32,
          rcIsisCircuitPlsbId         Integer32,        
          rcIsisCircuitPlsbRowStatus  RowStatus,
          rcIsisCircuitPlsbState      EnableValue,
          rcIsisCircuitPlsbType       INTEGER,
          rcIsisCircuitPlsbL1Metric   IsisDefaultL1Metric,
          rcIsisCircuitPlsbWideL1Metric   IsisWideL1Metric
        }

rcIsisCircuitPlsbIndex   OBJECT-TYPE
        SYNTAX        Integer32
        MAX-ACCESS    not-accessible
        STATUS        current
        DESCRIPTION  "The identifier of this circuit, unique within the
                      Intermediate System.  This object follows
                      the index behavior.  This is for SNMP Indexing
                      purposes only and need not have any relation to
                      any protocol value."
        ::= { rcIsisCircuitPlsbEntry 1 }

rcIsisCircuitPlsbId OBJECT-TYPE
        SYNTAX          Integer32 (1..100)
        MAX-ACCESS      not-accessible
        STATUS          current
        DESCRIPTION
            "PLSB instance ID"
    ::= { rcIsisCircuitPlsbEntry 2 }

rcIsisCircuitPlsbRowStatus  OBJECT-TYPE
        SYNTAX RowStatus
        MAX-ACCESS read-create
        STATUS current
        DESCRIPTION
            "The state of the rcIsisCircuitPlsbEntry.  "
    ::= { rcIsisCircuitPlsbEntry 3 }

rcIsisCircuitPlsbState OBJECT-TYPE
        SYNTAX        EnableValue
        MAX-ACCESS    read-create
        STATUS        current
        DESCRIPTION   "PLSB functionality enable on this Plsb 
                      instance at this port"
	DEFVAL        { disable }
        ::= { rcIsisCircuitPlsbEntry 4 }

rcIsisCircuitPlsbType    OBJECT-TYPE
        SYNTAX        INTEGER {
                          bcast(1),
                          ptpt(2)
                      }
        MAX-ACCESS    read-create
        STATUS        current
        DESCRIPTION   "ISIS circuit type this is an extention to 
                       ISIS circuit table, this was required a 
                       standard MIB circuit type does not support
                       passive type"
	    DEFVAL        { ptpt }
        ::= { rcIsisCircuitPlsbEntry 5 }

rcIsisCircuitPlsbL1Metric OBJECT-TYPE
        SYNTAX IsisDefaultL1Metric
        MAX-ACCESS read-create
        STATUS current
        DESCRIPTION
            "The metric value of this circuit for this level."
        DEFVAL { 10 }
    ::= { rcIsisCircuitPlsbEntry 6 }

rcIsisCircuitPlsbWideL1Metric OBJECT-TYPE
        SYNTAX IsisWideL1Metric
        MAX-ACCESS read-create
        STATUS current
        DESCRIPTION
            "The metric value of this circuit for this level."
        DEFVAL { 10 }
    ::= { rcIsisCircuitPlsbEntry 7 }

rcIsisTrap OBJECT IDENTIFIER ::= { rcIsis 9 }

IsisPlsbBvid ::= TEXTUAL-CONVENTION
        STATUS current
        DESCRIPTION
            "ISIS B-VLAN ID."
        SYNTAX Integer32 (0..4084)

IsisPlsbBvidTieBrkAlg ::= TEXTUAL-CONVENTION
        STATUS current
        DESCRIPTION
            "ISIS B-VLAN tie breaking algorithm."
        SYNTAX INTEGER{
		    low-pathid(1),
		    high-pathid(2)
		}

rcIsisLocalLspId OBJECT-TYPE 
        SYNTAX DisplayString(SIZE (17))
        MAX-ACCESS read-only
        STATUS current
        DESCRIPTION
            "The 8 byte Local LSP ID, consisting of the SystemID,
             Circuit ID, and Fragment Number."
    ::= { rcIsisTrap 1 }

rcIsisLocall1Metric OBJECT-TYPE
        SYNTAX IsisDefaultL1Metric
        MAX-ACCESS read-only
        STATUS current
        DESCRIPTION
            "l1-metric for ISIS interface on local Node."
    ::= { rcIsisTrap 2 }

rcIsisNgbLspId  OBJECT-TYPE
        SYNTAX DisplayString(SIZE (17))
        MAX-ACCESS read-only
        STATUS current
        DESCRIPTION
            "The 8 byte neighbor LSP ID, consisting of the SystemID,
             Circuit ID, and Fragment Number."
    ::= { rcIsisTrap 3 }

rcIsisNgbl1Metric OBJECT-TYPE
        SYNTAX IsisDefaultL1Metric
        MAX-ACCESS read-only
        STATUS current
        DESCRIPTION
            "l1-metric for ISIS interface on neighbor Node."
    ::= { rcIsisTrap 4 }

rcIsisPlsbTrapType OBJECT-TYPE
        SYNTAX	        INTEGER {
			   metricMismatch(1),
			   duplicateSysid(2),
			   lsdbUpdate(3),
                           duplicateNickname(4),
                           bvidMismatch(5),         
                           smltVirtBmacMismatch(6),         
                           smltPeerBmacMismatch(7),         
                           adjState(8),
                           smltSplitBebMismatch(9),
                           multiLinkAdj(10)
			}	
	MAX-ACCESS	read-only
	STATUS		current
	DESCRIPTION	""
	::= {rcIsisTrap 5}

rcIsisLocalSysId OBJECT-TYPE
        SYNTAX DisplayString(SIZE (14))
        MAX-ACCESS read-only
        STATUS current
        DESCRIPTION
            "ISIS local node system-id."
    ::= { rcIsisTrap 6 }

rcIsisLocalInterface OBJECT-TYPE
        SYNTAX Integer32
        MAX-ACCESS read-only
        STATUS current
        DESCRIPTION
            "ISIS local interface index."
    ::= { rcIsisTrap 7 }

rcIsisTrapIndicator OBJECT-TYPE
        SYNTAX INTEGER {
			alarm(1),
			clear(2)
  		    }
        MAX-ACCESS read-only
        STATUS current
        DESCRIPTION "indicates that an alarm has been 
                Raised, or an alarm has been cleared."
::= { rcIsisTrap 8 }

rcIsisLocalNickname OBJECT-TYPE
        SYNTAX DisplayString(SIZE (7))
        MAX-ACCESS read-only
        STATUS current
        DESCRIPTION
            "ISIS local node nick-name."
    ::= { rcIsisTrap 9 }

rcIsisNgbNickname OBJECT-TYPE
        SYNTAX DisplayString(SIZE (7))
        MAX-ACCESS read-only
        STATUS current
        DESCRIPTION
            "ISIS neighbor node nick-name."
    ::= { rcIsisTrap 10 }

rcIsisNgbSysId  OBJECT-TYPE
        SYNTAX DisplayString(SIZE (14))
        MAX-ACCESS read-only
        STATUS current
        DESCRIPTION
            "ISIS neighbor node system-id."
    ::= { rcIsisTrap 11 }

rcIsisLocalPrimaryBvid OBJECT-TYPE
	SYNTAX     IsisPlsbBvid
        MAX-ACCESS read-only
        STATUS current
        DESCRIPTION
            "ISIS local primary B-VID."
    ::= { rcIsisTrap 12 }

rcIsisLocalPrimaryTieBrkAlg OBJECT-TYPE
	SYNTAX  IsisPlsbBvidTieBrkAlg  
        MAX-ACCESS read-only
        STATUS current
        DESCRIPTION
            "The tie breaking algorithm applied to local primary B-VID."
    ::= { rcIsisTrap 13 }

rcIsisLocalSecondaryBvid OBJECT-TYPE
	SYNTAX     IsisPlsbBvid 
        MAX-ACCESS read-only
        STATUS current
        DESCRIPTION
            "ISIS local secondary B-VID."
    ::= { rcIsisTrap 14 }

rcIsisLocalSecondaryTieBrkAlg OBJECT-TYPE
	SYNTAX  IsisPlsbBvidTieBrkAlg  
        MAX-ACCESS read-only
        STATUS current
        DESCRIPTION
            "The tie breaking algorithm applied to local seconday B-VID."
    ::= { rcIsisTrap 15 }

rcIsisNgbPrimaryBvid OBJECT-TYPE
	SYNTAX     IsisPlsbBvid
        MAX-ACCESS read-only
        STATUS current
        DESCRIPTION
            "ISIS neighbor primary B-VID."
    ::= { rcIsisTrap 16 }

rcIsisNgbPrimaryTieBrkAlg OBJECT-TYPE
	SYNTAX  IsisPlsbBvidTieBrkAlg  
        MAX-ACCESS read-only
        STATUS current
        DESCRIPTION
            "The neighbor tie breaking algorithm applied to primary B-VID."
    ::= { rcIsisTrap 17 }

rcIsisNgbSecondaryBvid  OBJECT-TYPE
	SYNTAX     IsisPlsbBvid
        MAX-ACCESS read-only
        STATUS current
        DESCRIPTION
            "ISIS neighbor secondary B-VID."
    ::= { rcIsisTrap 18 } 

rcIsisNgbSecondaryTieBrkAlg OBJECT-TYPE
	SYNTAX  IsisPlsbBvidTieBrkAlg  
        MAX-ACCESS read-only
        STATUS current
        DESCRIPTION
            "The neighbor tie breaking algorithm applied to secondary B-VID."
    ::= { rcIsisTrap 19 }

rcIsisLocalVirtualBmac OBJECT-TYPE
	SYNTAX MacAddress 
        MAX-ACCESS read-only
        STATUS current
        DESCRIPTION
            "The SMLT Virtual BMAC configured in the local IST switch."
    ::= { rcIsisTrap 20 }


rcIsisPeerVirtualBmac OBJECT-TYPE
	SYNTAX MacAddress 
        MAX-ACCESS read-only
        STATUS current
        DESCRIPTION
            "The SMLT Virtual BMAC configured in the IST Peer."
    ::= { rcIsisTrap 21 }

rcIsisSysId OBJECT-TYPE
	SYNTAX DisplayString(SIZE (14))
        MAX-ACCESS read-only
        STATUS current
        DESCRIPTION
            "The isis system id configured in the local switch or IST peer."
    ::= { rcIsisTrap 22 }

rcIsisSmltPeerSysId OBJECT-TYPE
	SYNTAX DisplayString(SIZE (14)) 
        MAX-ACCESS read-only
        STATUS current
        DESCRIPTION
            "The SMLT Peer system-id configured in the local switch or IST Peer."
    ::= { rcIsisTrap 23 }

rcIsisAdjState OBJECT-TYPE
        SYNTAX INTEGER  {
			init(2),
                        up(3),	
                        down(4)
  		    }
        MAX-ACCESS read-only
        STATUS current
        DESCRIPTION "indicate different ISIS adjacency states."
::= { rcIsisTrap 24 }

rcIsisDuplicateNnameCounter OBJECT-TYPE
        SYNTAX INTEGER 		
        MAX-ACCESS read-only
        STATUS current
        DESCRIPTION "indicate how many nodes in the network share the nick-name."
::= { rcIsisTrap 25 }

rcIsisLocalBvidCounter OBJECT-TYPE
        SYNTAX INTEGER 		
        MAX-ACCESS read-only
        STATUS current
        DESCRIPTION "indicate how many b-vid configured on local nodes."
::= { rcIsisTrap 26 }

rcIsisNgbBvidCounter OBJECT-TYPE
        SYNTAX INTEGER 		
        MAX-ACCESS read-only
        STATUS current
        DESCRIPTION "indicate how many b-vid configured on a neighbor nodes."
::= { rcIsisTrap 27 }

rcIsisLocalSmltSplitBeb OBJECT-TYPE
        SYNTAX     INTEGER {
                          primary(1),
                          secondary(2)
		     }
        MAX-ACCESS read-only
        STATUS current
        DESCRIPTION
            "The SMLT Split-BEB configured in the local IST switch."
    ::= { rcIsisTrap 28 }

rcIsisPeerSmltSplitBeb OBJECT-TYPE
        SYNTAX     INTEGER {
                          primary(1),
                          secondary(2)
		     }
        MAX-ACCESS read-only
        STATUS current
        DESCRIPTION
            "The SMLT Split-BEB configured in the IST Peer switch."
    ::= { rcIsisTrap 29 }

rcIsisLocalHostName OBJECT-TYPE
        SYNTAX     OCTET STRING (SIZE (0..255))
        MAX-ACCESS read-only
        STATUS     current
        DESCRIPTION   
            "ISIS local host name."
        ::= { rcIsisTrap 30 }

rcIsisNgbHostName OBJECT-TYPE
        SYNTAX     OCTET STRING (SIZE (0..255))
        MAX-ACCESS read-only
        STATUS     current
        DESCRIPTION   
            "ISIS neighbor host name."
        ::= { rcIsisTrap 31 }

rcIsisPrevInterface OBJECT-TYPE
        SYNTAX Integer32
        MAX-ACCESS read-only
        STATUS current
        DESCRIPTION
            "ISIS local interface index for previously found adj."
    ::= { rcIsisTrap 32 }

-- BEGIN rcIsisAdjTable --

rcIsisAdjTable      OBJECT-TYPE
        SYNTAX          SEQUENCE OF RcIsisAdjEntry
        MAX-ACCESS      not-accessible
        STATUS          current
        DESCRIPTION     "Table of IS-IS Adjacency, this is extension
                         to the isisISAdjTable defined in ISIS MIB"
        ::= { rcIsis 10 }

rcIsisAdjEntry OBJECT-TYPE
        SYNTAX          RcIsisAdjEntry
        MAX-ACCESS      not-accessible
        STATUS          current
        DESCRIPTION     "An entry of rcIsisAdj Table. A Entry in 
                         table exists for each ISIS adjacency"
        INDEX           {rcIsisAdjCircIndex,
                         rcIsisAdjIndex }
        ::= { rcIsisAdjTable 1 }

RcIsisAdjEntry   ::=
        SEQUENCE {
          rcIsisAdjCircIndex        Integer32,
          rcIsisAdjIndex            Unsigned32,
          rcIsisAdjHostName         OCTET STRING,
          rcIsisAdjIfIndex          InterfaceIndex
        }

rcIsisAdjCircIndex   OBJECT-TYPE
        SYNTAX        Integer32
        MAX-ACCESS    not-accessible
        STATUS        current
        DESCRIPTION  "The identifier of this circuit, unique within the
                      Intermediate System.  This object follows
                      the index behavior.  This is for SNMP Indexing
                      purposes only and need not have any relation to
                      any protocol value."
        ::= { rcIsisAdjEntry 1 }

rcIsisAdjIndex OBJECT-TYPE
        SYNTAX Unsigned32(1..2147483647)
        MAX-ACCESS not-accessible
        STATUS current
        DESCRIPTION
            "A unique value identifying the IS adjacency from all
             other such adjacencies on this circuit. This value is
             automatically assigned by the system when the adjacency
             is created."
    ::= { rcIsisAdjEntry 2 }

rcIsisAdjHostName OBJECT-TYPE
        SYNTAX     OCTET STRING (SIZE (0..255))
        MAX-ACCESS read-only
        STATUS     current
        DESCRIPTION   
            "The hostname listed in LSP, or the system name if host 
             name is not configured."
        ::= { rcIsisAdjEntry 3 }

rcIsisAdjIfIndex OBJECT-TYPE
        SYNTAX InterfaceIndex
        MAX-ACCESS read-only
        STATUS current
        DESCRIPTION
            "The value of ifIndex for the interface to which this
             circuit corresponds."
    ::= { rcIsisAdjEntry 4 }

-- BEGIN rcIsisLSPTable --

rcIsisLSPTable      OBJECT-TYPE
        SYNTAX          SEQUENCE OF RcIsisLSPEntry
        MAX-ACCESS      not-accessible
        STATUS          current
        DESCRIPTION     "Table of IS-IS LSP, this is extension
                         to the isisLSPSummaryTable defined in ISIS MIB"
        ::= { rcIsis 11 }

rcIsisLSPEntry OBJECT-TYPE
        SYNTAX          RcIsisLSPEntry
        MAX-ACCESS      not-accessible
        STATUS          current
        DESCRIPTION     "An entry of rcIsisLSP Table. A Entry in 
                         table exists for each ISIS LSP"
        INDEX           {rcIsisLSPLevel,
                         rcIsisLSPID }
        ::= { rcIsisLSPTable 1 }

RcIsisLSPEntry   ::=
        SEQUENCE {
          rcIsisLSPLevel            INTEGER,
          rcIsisLSPID               OCTET STRING,
          rcIsisLSPSeq              Unsigned32,
          rcIsisLSPHostName         OCTET STRING,
          rcIsisLSPNickName         Integer32,
          rcIsisLSPLifetimeRemain   Unsigned32
        }

rcIsisLSPLevel OBJECT-TYPE
        SYNTAX INTEGER {
                area(1),        -- L1
                domain(2)       -- L2
        }
        MAX-ACCESS not-accessible
        STATUS current
        DESCRIPTION
            "At which level does this LSP appear?"
    ::= { rcIsisLSPEntry 1 }

rcIsisLSPID OBJECT-TYPE
        SYNTAX OCTET STRING (SIZE (8))
        MAX-ACCESS not-accessible
        STATUS current
        DESCRIPTION
            "The 8 byte LSP ID, consisting of the SystemID,
             Circuit ID, and Fragment Number."
    ::= { rcIsisLSPEntry 2 }

rcIsisLSPSeq OBJECT-TYPE
        SYNTAX Unsigned32
        MAX-ACCESS read-only
        STATUS current
        DESCRIPTION
            "The sequence number for this LSP."
    ::= { rcIsisLSPEntry 3 }

rcIsisLSPHostName OBJECT-TYPE
        SYNTAX     OCTET STRING (SIZE (0..255))
        MAX-ACCESS read-only
        STATUS     current
        DESCRIPTION   
            "The hostname listed in LSP, or the system name if host 
             name is not configured."
        ::= { rcIsisLSPEntry 4 }

rcIsisLSPNickName OBJECT-TYPE
        SYNTAX Integer32 (1..16777215)
        MAX-ACCESS read-only
        STATUS current
        DESCRIPTION
            "PLSB node's nickname"
    ::= { rcIsisLSPEntry 5 }

rcIsisLSPLifetimeRemain OBJECT-TYPE
        SYNTAX Unsigned32
        UNITS "seconds"
        MAX-ACCESS read-only
        STATUS current
        DESCRIPTION
            "The remaining lifetime in seconds for this LSP."
    ::= { rcIsisLSPEntry 6 }

-- ISIS PLSB IP Unicast FIB Table
rcIsisPlsbIpUnicastFibTable      OBJECT-TYPE
        SYNTAX          SEQUENCE OF RcIsisPlsbIpUnicastFibEntry
        MAX-ACCESS      not-accessible
        STATUS          current
        DESCRIPTION     "Table of IS-IS PLSB IP Unicast FIB"
        ::= { rcIsis 12 }

rcIsisPlsbIpUnicastFibEntry OBJECT-TYPE
        SYNTAX          RcIsisPlsbIpUnicastFibEntry
        MAX-ACCESS      not-accessible
        STATUS          current
        DESCRIPTION     "An entry of rcIsisPlsbIpUnicastFib Table. A Entry in
                         table exists for each PLSB IP unicast forwarding entry."
        INDEX           { rcIsisPlsbIpUnicastFibVrfId,
			  rcIsisPlsbIpUnicastFibDestinationIpAddrType,
			  rcIsisPlsbIpUnicastFibDestinationIpAddr,
                          rcIsisPlsbIpUnicastFibDestinationMask,
                          rcIsisPlsbIpUnicastFibNextHopBmac,
                          rcIsisPlsbIpUnicastFibVlan }
        ::= { rcIsisPlsbIpUnicastFibTable 1 }

RcIsisPlsbIpUnicastFibEntry   ::=
        SEQUENCE {
	  rcIsisPlsbIpUnicastFibVrfId                   Integer32,
          rcIsisPlsbIpUnicastFibDestinationIpAddrType   InetAddressType,
          rcIsisPlsbIpUnicastFibDestinationIpAddr       InetAddress,
	  rcIsisPlsbIpUnicastFibDestinationMask         InetAddressPrefixLength,
          rcIsisPlsbIpUnicastFibNextHopBmac             MacAddress,     
          rcIsisPlsbIpUnicastFibVlan                    Integer32,
          rcIsisPlsbIpUnicastFibIsid                    Integer32,
          rcIsisPlsbIpUnicastFibNextHopName             DisplayString,        
          rcIsisPlsbIpUnicastFibOutgoingPort            InterfaceIndex,
          rcIsisPlsbIpUnicastFibPrefixCost              Integer32,         
          rcIsisPlsbIpUnicastFibSpbmCost                Counter64 
        }

rcIsisPlsbIpUnicastFibVrfId OBJECT-TYPE
        SYNTAX        Integer32
        MAX-ACCESS    not-accessible
        STATUS        current
        DESCRIPTION   "VRF ID of the IP unicast FIB entry, 0 indicates NRE."
        ::= { rcIsisPlsbIpUnicastFibEntry 1 }

rcIsisPlsbIpUnicastFibDestinationIpAddrType OBJECT-TYPE
        SYNTAX        InetAddressType
        MAX-ACCESS    not-accessible
        STATUS        current
        DESCRIPTION   "The address type of destination IP Address."
        ::= { rcIsisPlsbIpUnicastFibEntry 2 }

rcIsisPlsbIpUnicastFibDestinationIpAddr OBJECT-TYPE
        SYNTAX        InetAddress (SIZE(4|16))
        MAX-ACCESS    not-accessible
        STATUS        current
        DESCRIPTION   "Destination IP Address of the IP unicast FIB entry.
		       Support ipv4 size(4) and ipv6 size(16)"
        ::= { rcIsisPlsbIpUnicastFibEntry 3 }

rcIsisPlsbIpUnicastFibDestinationMask OBJECT-TYPE
        SYNTAX        InetAddressPrefixLength
        MAX-ACCESS    not-accessible
        STATUS        current
        DESCRIPTION   "Destination IP mask of the IP unicast FIB entry "
        ::= { rcIsisPlsbIpUnicastFibEntry 4 }

rcIsisPlsbIpUnicastFibNextHopBmac OBJECT-TYPE
        SYNTAX        MacAddress
        MAX-ACCESS    not-accessible
        STATUS        current
        DESCRIPTION   "the nexthop BMAC of the IP unicast FIB entry "
        ::= { rcIsisPlsbIpUnicastFibEntry 5 }

rcIsisPlsbIpUnicastFibVlan OBJECT-TYPE
        SYNTAX        Integer32 (1..4084)
        MAX-ACCESS    not-accessible
        STATUS        current
        DESCRIPTION   "Vlan of the IP unicast FIB entry"
        ::= { rcIsisPlsbIpUnicastFibEntry 6 }

rcIsisPlsbIpUnicastFibIsid OBJECT-TYPE
        SYNTAX        Integer32
        MAX-ACCESS    read-only
        STATUS        current
        DESCRIPTION   "ISID of the IP unicast FIB entry"
        ::= { rcIsisPlsbIpUnicastFibEntry 7 }

rcIsisPlsbIpUnicastFibNextHopName OBJECT-TYPE
        SYNTAX        DisplayString
        MAX-ACCESS    read-only
        STATUS        current
        DESCRIPTION   "the nexthop hostname of the IP unicast FIB entry "
        ::= { rcIsisPlsbIpUnicastFibEntry 8 }

rcIsisPlsbIpUnicastFibOutgoingPort  OBJECT-TYPE
        SYNTAX        InterfaceIndex
        MAX-ACCESS    read-only
        STATUS        current
        DESCRIPTION   "Outgoing port of the IP unicast Fib entry."
        ::= { rcIsisPlsbIpUnicastFibEntry 9 }

rcIsisPlsbIpUnicastFibPrefixCost OBJECT-TYPE
        SYNTAX        Integer32
        MAX-ACCESS    read-only
        STATUS        current
        DESCRIPTION   "prefix cost of the IP unicast FIB entry"
        ::= { rcIsisPlsbIpUnicastFibEntry 10 }

rcIsisPlsbIpUnicastFibSpbmCost  OBJECT-TYPE
        SYNTAX        Counter64
        MAX-ACCESS    read-only
        STATUS        current
        DESCRIPTION   "bmac cost of the IP unicast FIB entry" 
        ::= { rcIsisPlsbIpUnicastFibEntry 11 }

-- ISIS PLSB Unicast FIB Table
rcIsisPlsbUcastFibTable      OBJECT-TYPE
        SYNTAX          SEQUENCE OF RcIsisPlsbUcastFibEntry
        MAX-ACCESS      not-accessible
        STATUS          current
        DESCRIPTION     "Table of IS-IS PLSB Unicast FIB"
        ::= { rcIsis 13 }

rcIsisPlsbUcastFibEntry OBJECT-TYPE
        SYNTAX          RcIsisPlsbUcastFibEntry
        MAX-ACCESS      not-accessible
        STATUS          current
        DESCRIPTION    	"An entry of rcIsisPlsbUcastFib Table. A Entry in
                        table exists for each PLSB unicast forwarding entry
                       	generated by ISIS SPF computation"
        INDEX           { rcIsisPlsbUcastFibSysId,
		          rcIsisPlsbUcastFibVlan,
		          rcIsisPlsbUcastFibDestinationMacAddr}
        ::= { rcIsisPlsbUcastFibTable 1 }

RcIsisPlsbUcastFibEntry   ::=
        SEQUENCE {
          rcIsisPlsbUcastFibSysId                   	OCTET STRING,
          rcIsisPlsbUcastFibVlan                    	Integer32,
          rcIsisPlsbUcastFibDestinationMacAddr          MacAddress,
          rcIsisPlsbUcastFibOutgoingPort            	InterfaceIndex,
          rcIsisPlsbUcastFibHostName                   	OCTET STRING,
	  rcIsisPlsbUcastFibCost                        Counter64 
        }

rcIsisPlsbUcastFibSysId OBJECT-TYPE
        SYNTAX        OCTET STRING (SIZE (6))
        MAX-ACCESS    not-accessible
        STATUS        current
        DESCRIPTION   "System ID of the node where unicast FIB entry 
                       come from"
        ::= { rcIsisPlsbUcastFibEntry 1 }

rcIsisPlsbUcastFibVlan OBJECT-TYPE
        SYNTAX        Integer32 (1..4084)
        MAX-ACCESS    not-accessible
        STATUS        current
        DESCRIPTION   "Vlan of the unicast FIB entry"
        ::= { rcIsisPlsbUcastFibEntry 2 }

rcIsisPlsbUcastFibDestinationMacAddr OBJECT-TYPE
        SYNTAX        MacAddress
        MAX-ACCESS    not-accessible
        STATUS        current
        DESCRIPTION   "Destination Mac Address of the unicast FIB entry "
        ::= { rcIsisPlsbUcastFibEntry 3 }

rcIsisPlsbUcastFibOutgoingPort  OBJECT-TYPE
        SYNTAX        InterfaceIndex
        MAX-ACCESS    read-only
        STATUS        current
        DESCRIPTION   "Outgoing port of the unicast Fib entry."
        ::= { rcIsisPlsbUcastFibEntry 4 }

rcIsisPlsbUcastFibHostName  OBJECT-TYPE
        SYNTAX        OCTET STRING (SIZE (0..255))
        MAX-ACCESS    read-only
        STATUS        current
        DESCRIPTION   "Host name of the node where unicast FIB entry 
                       come from"
        ::= { rcIsisPlsbUcastFibEntry 5 }

rcIsisPlsbUcastFibCost  OBJECT-TYPE
        SYNTAX        Counter64
        MAX-ACCESS    read-only
        STATUS        current
        DESCRIPTION   "unicast FIB cost" 
        ::= { rcIsisPlsbUcastFibEntry 6 }

-- ISIS PLSB Multicast FIB Table

rcIsisPlsbMcastFibTable      OBJECT-TYPE
        SYNTAX          SEQUENCE OF RcIsisPlsbMcastFibEntry
        MAX-ACCESS     	not-accessible
        STATUS         	current
        DESCRIPTION     "Table of IS-IS PLSB Multicast FIB"
        ::= { rcIsis 14 }

rcIsisPlsbMcastFibEntry OBJECT-TYPE
        SYNTAX         	RcIsisPlsbMcastFibEntry
        MAX-ACCESS      not-accessible
        STATUS         	current
        DESCRIPTION     "An entry of rcIsisPlsbMcastFib Table. A Entry in
                        table exists for each PLSB Multicast forwarding entry
                        generated by ISIS SPF computation"
        INDEX           { rcIsisPlsbMcastFibSysId,
		          rcIsisPlsbMcastFibVlan,
		          rcIsisPlsbMcastFibMcastDestMacAddr
		        }
        ::= { rcIsisPlsbMcastFibTable 1 }

RcIsisPlsbMcastFibEntry   ::=
        SEQUENCE {
          rcIsisPlsbMcastFibSysId                 	OCTET STRING,
          rcIsisPlsbMcastFibVlan                  	Integer32,
          rcIsisPlsbMcastFibMcastDestMacAddr            MacAddress,
          rcIsisPlsbMcastFibIsid                        Integer32,
          rcIsisPlsbMcastFibNickName                    Integer32,
          rcIsisPlsbMcastFibType                        INTEGER,
          rcIsisPlsbMcastFibOutgoingPorts         	DisplayString,
          rcIsisPlsbMcastFibHostName                   	OCTET STRING
        }
	
rcIsisPlsbMcastFibSysId OBJECT-TYPE
        SYNTAX        OCTET STRING (SIZE (6))
        MAX-ACCESS    not-accessible
        STATUS        current
        DESCRIPTION   "System ID of the node where multicast FIB entry 
                       come from"
        ::= { rcIsisPlsbMcastFibEntry 1 }

rcIsisPlsbMcastFibVlan OBJECT-TYPE
        SYNTAX        Integer32 (1..4084)
        MAX-ACCESS    not-accessible
        STATUS        current
        DESCRIPTION   "Vlan of the multicast FIB entry"
        ::= { rcIsisPlsbMcastFibEntry 2 }

rcIsisPlsbMcastFibMcastDestMacAddr OBJECT-TYPE
        SYNTAX        MacAddress
        MAX-ACCESS    not-accessible
        STATUS        current
        DESCRIPTION   "Multicast destination Mac Address of the 
                       multicast FIB entry "
        ::= { rcIsisPlsbMcastFibEntry 3 }

rcIsisPlsbMcastFibIsid OBJECT-TYPE
        SYNTAX        Integer32 (1..16777215)
        MAX-ACCESS    read-only
        STATUS        current
        DESCRIPTION   "Isid id of the multicast FIB entry"
        ::= { rcIsisPlsbMcastFibEntry 4 }

rcIsisPlsbMcastFibNickName OBJECT-TYPE
        SYNTAX        Integer32 (1..16777215)
        MAX-ACCESS    read-only
        STATUS        current
        DESCRIPTION   "nick name of node where this i-sid got 
                       configured or discovered"
        ::= { rcIsisPlsbMcastFibEntry 5 }

rcIsisPlsbMcastFibType OBJECT-TYPE	
        SYNTAX	      INTEGER {
			  config(1),
			  discover(2)
                      }
        MAX-ACCESS    read-only
        STATUS        current
        DESCRIPTION   "PLSB i-sid type"
        ::= { rcIsisPlsbMcastFibEntry 6 }

rcIsisPlsbMcastFibOutgoingPorts  OBJECT-TYPE
        SYNTAX        DisplayString
        MAX-ACCESS    read-only
        STATUS        current
        DESCRIPTION   "Nni port of the multicast Fib entry."
        ::= { rcIsisPlsbMcastFibEntry 7 }

rcIsisPlsbMcastFibHostName  OBJECT-TYPE
        SYNTAX        OCTET STRING (SIZE (0..255))
        MAX-ACCESS    read-only
        STATUS        current
        DESCRIPTION   "Host name of the node where multicast FIB entry 
                       come from"
        ::= { rcIsisPlsbMcastFibEntry 8 }

rcIsisPlsbNodeTable      OBJECT-TYPE
        SYNTAX          SEQUENCE OF RcIsisPlsbNodeEntry
        MAX-ACCESS      not-accessible
        STATUS          current
        DESCRIPTION     "Table of IS-IS PLSB Node"
        ::= { rcIsis 15 }

rcIsisPlsbNodeEntry OBJECT-TYPE
        SYNTAX          RcIsisPlsbNodeEntry
        MAX-ACCESS      not-accessible
        STATUS          current
        DESCRIPTION    	"An entry of rcIsisPlsbNode Table. A Entry in
                        table exists for each node running PLSB ISIS 
                        in the setup."
        INDEX           { rcIsisPlsbNodeSysId }
        ::= { rcIsisPlsbNodeTable 1 }

RcIsisPlsbNodeEntry   ::=
        SEQUENCE {
          rcIsisPlsbNodeSysId                           OCTET STRING,      
	  rcIsisPlsbNodePrimaryParentSysId              OCTET STRING,  
          rcIsisPlsbNodePrimaryBvlan                    Integer32,
          rcIsisPlsbNodeSecondaryParentSysId            OCTET STRING,
          rcIsisPlsbNodeSecondaryBvlan                  Integer32  
        }

rcIsisPlsbNodeSysId OBJECT-TYPE
        SYNTAX        OCTET STRING (SIZE (6))
        MAX-ACCESS    not-accessible
        STATUS        current
        DESCRIPTION   "System ID of the PLSB node entry"
        ::= { rcIsisPlsbNodeEntry 1 }

rcIsisPlsbNodePrimaryParentSysId OBJECT-TYPE
        SYNTAX        OCTET STRING (SIZE (6))
        MAX-ACCESS    read-only
        STATUS        current
        DESCRIPTION   "System ID of parent node of the PLSB node entry for
                       primary bvlan"
        ::= { rcIsisPlsbNodeEntry 2 }

rcIsisPlsbNodePrimaryBvlan OBJECT-TYPE
        SYNTAX        Integer32 (1..4084)
        MAX-ACCESS    read-only
        STATUS        current
        DESCRIPTION   "spbm primary b-vlan"
        ::= { rcIsisPlsbNodeEntry 3 }

rcIsisPlsbNodeSecondaryParentSysId OBJECT-TYPE
        SYNTAX        OCTET STRING (SIZE (6))
        MAX-ACCESS    read-only
        STATUS        current
        DESCRIPTION   "System ID of parent node of the PLSB node entry for
                       secondary bvlan"
        ::= { rcIsisPlsbNodeEntry 4 }

rcIsisPlsbNodeSecondaryBvlan OBJECT-TYPE
        SYNTAX        Integer32 (1..4084)
        MAX-ACCESS    read-only
        STATUS        current
        DESCRIPTION   "spbm secondary b-vlan"
        ::= { rcIsisPlsbNodeEntry 5 }



rcPlsbGlobal  OBJECT IDENTIFIER ::= {rcPlsb 1}

rcPlsbGlobalVlans OBJECT-TYPE
   	SYNTAX		OCTET STRING(SIZE(512))
    	MAX-ACCESS	read-write
    	STATUS		current
    	DESCRIPTION	"PLSB vlan entry."
    	::= { rcPlsbGlobal 1}

rcPlsbGlobalEnable OBJECT-TYPE
   	SYNTAX		EnableValue
    	MAX-ACCESS	read-write
    	STATUS		current
    	DESCRIPTION	"Enable/Disable PLSB global flag."
        DEFVAL          {disable}
    	::= { rcPlsbGlobal 2}

rcPlsbGlobalMsti OBJECT-TYPE
        SYNTAX        INTEGER (0..63)
        MAX-ACCESS    read-write
        STATUS        current
        DESCRIPTION   "MSTI instance ID for PLSB VLANS"
	DEFVAL       { 0 }	
        ::= { rcPlsbGlobal 3}

rcPlsbGlobalEtherType OBJECT-TYPE
	SYNTAX        Integer32 (1..'FFFF'h)
        MAX-ACCESS    read-write
        STATUS        current
        DESCRIPTION   "SPBM Ethertype"
	DEFVAL        { '8100'h } 
	::= { rcPlsbGlobal 4}

-- CFM Tables
-- Maintenance Domain Table

rcCfmMaintenanceDomainTable OBJECT-TYPE
	SYNTAX		SEQUENCE OF RcCfmMaintenanceDomainEntry
	MAX-ACCESS	not-accessible
	STATUS		current
	DESCRIPTION	"Connectivity Fault Management Maintenance Domain table"
	::= { rcCfm 1}

rcCfmMaintenanceDomainEntry OBJECT-TYPE
	SYNTAX		RcCfmMaintenanceDomainEntry
	MAX-ACCESS	not-accessible
	STATUS		current
	DESCRIPTION	"Connectivity Fault Management Maintenance Domain entry."
	INDEX		{rcCfmMaintenanceDomainIndex }
	::= { rcCfmMaintenanceDomainTable 1}

RcCfmMaintenanceDomainEntry ::=
	SEQUENCE {
		rcCfmMaintenanceDomainIndex		INTEGER,
		rcCfmMaintenanceDomainName		DisplayString,
		rcCfmMaintenanceDomainRowStatus		RowStatus,
	        rcCfmMaintenanceDomainNumOfMa		Integer32,
                rcCfmMaintenanceDomainLevel		INTEGER,
	        rcCfmMaintenanceDomainNumOfMip		Integer32,
                rcCfmMaintenanceDomainType              INTEGER 
		}

rcCfmMaintenanceDomainIndex OBJECT-TYPE
	SYNTAX		INTEGER (1..2147483647)
	MAX-ACCESS	not-accessible
	STATUS		current
	DESCRIPTION	"Maintenance Domain index"
	::= { rcCfmMaintenanceDomainEntry 1}

rcCfmMaintenanceDomainName OBJECT-TYPE	
	SYNTAX	        DisplayString(SIZE (1..22))
	MAX-ACCESS	read-create
	STATUS		current
	DESCRIPTION	"Maintenance Domain Name"
	::= { rcCfmMaintenanceDomainEntry 2}

rcCfmMaintenanceDomainRowStatus OBJECT-TYPE
	SYNTAX		RowStatus
	MAX-ACCESS	read-create
	STATUS		current
	DESCRIPTION	"Used to create/delete entries"
	::= { rcCfmMaintenanceDomainEntry 3}

rcCfmMaintenanceDomainNumOfMa OBJECT-TYPE
        SYNTAX        	Integer32
        MAX-ACCESS      read-only
        STATUS        	current
        DESCRIPTION   	"Used to indicate the number of MAs belong
                      	to this maintenance domain"
        ::= { rcCfmMaintenanceDomainEntry 4 }

rcCfmMaintenanceDomainLevel OBJECT-TYPE
	SYNTAX		INTEGER (0..7)
        MAX-ACCESS      read-create
        STATUS          current
        DESCRIPTION     "To set the maintenance level in this domain"
	DEFVAL		{4}
        ::= { rcCfmMaintenanceDomainEntry 6 }

rcCfmMaintenanceDomainNumOfMip OBJECT-TYPE
        SYNTAX        	Integer32
        MAX-ACCESS      read-only
        STATUS        	current
        DESCRIPTION   	"Used to indicate the number of Mips belong
                      	to this maintenance domain"
        ::= { rcCfmMaintenanceDomainEntry 7 }

rcCfmMaintenanceDomainType OBJECT-TYPE
        SYNTAX          INTEGER {
                            none(0),
                            trunk(1),
                            sg(2),
                            endpt(3),
                            vlan(4),
                            port(5),
                            mimencapvlan(6),
                            nodal(7)
                         }
        MAX-ACCESS      read-only
        STATUS          current
        DESCRIPTION     "To indicate the type of domain" 
        ::= { rcCfmMaintenanceDomainEntry 8 }

-- Maintenance Association Table

rcCfmMaintenanceAssociationTable OBJECT-TYPE
	SYNTAX		SEQUENCE OF RcCfmMaintenanceAssociationEntry
	MAX-ACCESS	not-accessible
	STATUS		current
	DESCRIPTION	"Connectivity Fault Management Maintenance Association table"
	::= { rcCfm 2}

rcCfmMaintenanceAssociationEntry OBJECT-TYPE
	SYNTAX		RcCfmMaintenanceAssociationEntry
	MAX-ACCESS	not-accessible
	STATUS		current
	DESCRIPTION	"Connectivity Fault Management Maintenance Association entry."
	INDEX		{rcCfmMaintenanceAssociationDomainIndex, rcCfmMaintenanceAssociationAssociationIndex }
	::= { rcCfmMaintenanceAssociationTable 1}

RcCfmMaintenanceAssociationEntry ::=
	SEQUENCE {
		rcCfmMaintenanceAssociationDomainIndex		INTEGER,
                rcCfmMaintenanceAssociationAssociationIndex    	INTEGER,
		rcCfmMaintenanceAssociationDomainName		DisplayString,
                rcCfmMaintenanceAssociationAssociationName	DisplayString,
                rcCfmMaintenanceAssociationAdminState		EnableValue,
		rcCfmMaintenanceAssociationRowStatus		RowStatus,
                rcCfmMaintenanceAssociationNumOfMep     	Integer32
   		}

rcCfmMaintenanceAssociationDomainIndex OBJECT-TYPE
	SYNTAX		INTEGER (1..2147483647)
	MAX-ACCESS	not-accessible
	STATUS		current
	DESCRIPTION	"Maintenance Association Domain Index"
	::= { rcCfmMaintenanceAssociationEntry 1}

rcCfmMaintenanceAssociationAssociationIndex OBJECT-TYPE
	SYNTAX		INTEGER (1..2147483647)
	MAX-ACCESS	not-accessible
	STATUS		current
	DESCRIPTION	"Maintenance Association Index"
	::= { rcCfmMaintenanceAssociationEntry 2}

rcCfmMaintenanceAssociationDomainName OBJECT-TYPE
	SYNTAX		DisplayString(SIZE (1..22))
	MAX-ACCESS	read-only
	STATUS		current
	DESCRIPTION	"Maintenance Association Domain Name"
	::= { rcCfmMaintenanceAssociationEntry 3}

rcCfmMaintenanceAssociationAssociationName OBJECT-TYPE
	SYNTAX		DisplayString(SIZE (1..22))
	MAX-ACCESS	read-create
	STATUS		current
	DESCRIPTION	"Maintenance Association Name"
	::= { rcCfmMaintenanceAssociationEntry 4}

rcCfmMaintenanceAssociationAdminState OBJECT-TYPE
        SYNTAX        EnableValue
        MAX-ACCESS    read-create
        STATUS        current
        DESCRIPTION   "Administratively enable or disable a maintenance association."
	DEFVAL        { disable }
        ::= { rcCfmMaintenanceAssociationEntry 5}

rcCfmMaintenanceAssociationRowStatus OBJECT-TYPE
	SYNTAX		RowStatus
	MAX-ACCESS	read-create
	STATUS		current
	DESCRIPTION	"Used to create/delete entries"
	::= { rcCfmMaintenanceAssociationEntry 6}

rcCfmMaintenanceAssociationNumOfMep OBJECT-TYPE
        SYNTAX        	Integer32
        MAX-ACCESS      read-only
        STATUS        	current
        DESCRIPTION   	"Used to indicate the number of MEPs belong
                      	to this maintenance association"
        ::= { rcCfmMaintenanceAssociationEntry 12 }


-- Maintenance EndPoint Table

rcCfmMaintenanceEndPointTable OBJECT-TYPE
	SYNTAX		SEQUENCE OF RcCfmMaintenanceEndPointEntry
	MAX-ACCESS	not-accessible
	STATUS		current
	DESCRIPTION	"Connectivity Fault Management Maintenance Association table"
	::= { rcCfm 3}

rcCfmMaintenanceEndPointEntry OBJECT-TYPE
	SYNTAX		RcCfmMaintenanceEndPointEntry
	MAX-ACCESS	not-accessible
	STATUS		current
	DESCRIPTION	"Connectivity Fault Management Maintenance EndPoint entry."
	INDEX		{rcCfmMaintenanceEndPointDomainIndex, rcCfmMaintenanceEndPointAssociationIndex, rcCfmMaintenanceEndPointId }
	::= { rcCfmMaintenanceEndPointTable 1}

RcCfmMaintenanceEndPointEntry ::=
	SEQUENCE {
		rcCfmMaintenanceEndPointDomainIndex		Integer32,
                rcCfmMaintenanceEndPointAssociationIndex	Integer32,
		rcCfmMaintenanceEndPointId			Integer32,
                rcCfmMaintenanceEndPointDomainName		DisplayString,
                rcCfmMaintenanceEndPointAssociationName		DisplayString,
                rcCfmMaintenanceEndPointAdminState		EnableValue,
		rcCfmMaintenanceEndPointRowStatus		RowStatus,
                rcCfmMaintenanceEndPointMepType         	INTEGER,
                rcCfmMaintenanceEndPointServiceDescription      DisplayString,  
                rcCfmMaintenanceEndPointMepStatus               INTEGER
      		}

rcCfmMaintenanceEndPointDomainIndex OBJECT-TYPE
	SYNTAX		Integer32 (1..2147483647)
	MAX-ACCESS	not-accessible
	STATUS		current
	DESCRIPTION	"Maintenance Domain Name"
	::= { rcCfmMaintenanceEndPointEntry 1}

rcCfmMaintenanceEndPointAssociationIndex OBJECT-TYPE
	SYNTAX		Integer32 (1..2147483647)
	MAX-ACCESS	not-accessible
	STATUS		current
	DESCRIPTION	"Maintenance Association Name"
	::= { rcCfmMaintenanceEndPointEntry 2}

rcCfmMaintenanceEndPointId OBJECT-TYPE
	SYNTAX		Integer32 (1..8191)
	MAX-ACCESS	not-accessible
	STATUS		current
	DESCRIPTION	"Maintenance EndPoint ID"
	::= { rcCfmMaintenanceEndPointEntry 3}

rcCfmMaintenanceEndPointDomainName OBJECT-TYPE
	SYNTAX		DisplayString(SIZE (1..22))
	MAX-ACCESS	read-only
	STATUS		current
	DESCRIPTION	"Maintenance Domain Name"
	::= { rcCfmMaintenanceEndPointEntry 4}

rcCfmMaintenanceEndPointAssociationName OBJECT-TYPE
	SYNTAX		DisplayString(SIZE (1..22))
	MAX-ACCESS	read-only
	STATUS		current
	DESCRIPTION	"Maintenance Association Name"
	::= { rcCfmMaintenanceEndPointEntry 5}

rcCfmMaintenanceEndPointAdminState OBJECT-TYPE
        SYNTAX        EnableValue
        MAX-ACCESS    read-create
        STATUS        current
        DESCRIPTION   "Administratively enable or disable a maintenance EndPoint."
	DEFVAL        { disable }
        ::= { rcCfmMaintenanceEndPointEntry 6}

rcCfmMaintenanceEndPointRowStatus OBJECT-TYPE
	SYNTAX		RowStatus
	MAX-ACCESS	read-create
	STATUS		current
	DESCRIPTION	"Used to create/delete entries"
	::= { rcCfmMaintenanceEndPointEntry 7}

rcCfmMaintenanceEndPointMepType OBJECT-TYPE
        SYNTAX        INTEGER { 
                          trunk(1),
                          sg(2),
                          endpt(4),
                          unused(8),
			  vlan(16),
			  port(32),
                          endptClient(64),
                          nodal(3145728),
                          remotetrunk(32769),
                          remotesg(32770),
                          remoteendpt(32772),
			  remoteVlan(32784),
			  remotePort(32800),
			  remoteEndptClient(32832)
                       }
        MAX-ACCESS    read-only
        STATUS        current
        DESCRIPTION   "Mep Type"
        ::= { rcCfmMaintenanceEndPointEntry 11 }

rcCfmMaintenanceEndPointServiceDescription OBJECT-TYPE
        SYNTAX          DisplayString(SIZE (0..48))
        MAX-ACCESS      read-only
        STATUS          current
        DESCRIPTION     "Used to specify what service this mep assigned to"
        ::= { rcCfmMaintenanceEndPointEntry 13}

rcCfmMaintenanceEndPointMepStatus OBJECT-TYPE
        SYNTAX        INTEGER { 
                          active(1),
                          inactive(2) 
                      }
        MAX-ACCESS    read-only
        STATUS        current
        DESCRIPTION   "Indicating if the mep status is active or inactive. 
                       Only Dual-Home Ring endpoint client meps can have       
                       active/inactive status. All other mep types have
                       active status." 
	::= { rcCfmMaintenanceEndPointEntry 15 }

-- The Transmit Loopback Table

rcCfmTransmitLbmTable OBJECT-TYPE
	SYNTAX		SEQUENCE OF RcCfmTransmitLbmEntry
	MAX-ACCESS	not-accessible
	STATUS		current
	DESCRIPTION	"Connectivity Fault Management transmit LBM table"
	::= { rcCfm 17}

rcCfmTransmitLbmEntry OBJECT-TYPE
	SYNTAX		RcCfmTransmitLbmEntry
	MAX-ACCESS	not-accessible
	STATUS		current
	DESCRIPTION	"Connectivity Fault Management Maintenance EndPoint LBM entry."
	INDEX		{rcCfmTransmitLbmDomainIndex, rcCfmTransmitLbmAssociationIndex, rcCfmTransmitLbmIndex }
	::= { rcCfmTransmitLbmTable 1}

RcCfmTransmitLbmEntry ::=
	SEQUENCE {
		rcCfmTransmitLbmDomainIndex		Integer32,
                rcCfmTransmitLbmAssociationIndex	Integer32,
		rcCfmTransmitLbmIndex			Integer32,
                rcCfmTransmitLbmDomainName		DisplayString,
                rcCfmTransmitLbmAssociationName		DisplayString,
		rcCfmTransmitLbmDestMacAddress		MacAddress,
		rcCfmTransmitLbmDestMepId		Integer32,
		rcCfmTransmitLbmDestIsMepId		TruthValue,
		rcCfmTransmitLbmMessages		Integer32,
		rcCfmTransmitLbmVlanPriority		Integer32,
		rcCfmTransmitLbmVlanDropEnable		TruthValue,
		rcCfmTransmitLbmSeqNumber		Integer32,
		rcCfmTransmitLbmResultOk		TruthValue,
		rcCfmTransmitLbmStatus			INTEGER,
		rcCfmTransmitLbmResult                  DisplayString,
                rcCfmTransmitLbmTimeoutInt              Integer32,
                rcCfmTransmitLbmInterFrameInt           Integer32,
                rcCfmTransmitLbmTestPattern             INTEGER,
		rcCfmTransmitLbmDataSize	        Integer32,
		rcCfmTransmitLbmFrameSize	        Integer32,
	        rcCfmTransmitLbmSourceMode              INTEGER
	}

rcCfmTransmitLbmDomainIndex OBJECT-TYPE
	SYNTAX		Integer32 (1..2147483647)
	MAX-ACCESS	not-accessible
	STATUS		current
	DESCRIPTION	"Maintenance Domain Name"
	::= { rcCfmTransmitLbmEntry 1}

rcCfmTransmitLbmAssociationIndex OBJECT-TYPE
	SYNTAX		Integer32 (1..2147483647)
	MAX-ACCESS	not-accessible
	STATUS		current
	DESCRIPTION	"Maintenance Association Name"
	::= { rcCfmTransmitLbmEntry 2}

rcCfmTransmitLbmIndex OBJECT-TYPE
	SYNTAX		Integer32 (1..8191)
	MAX-ACCESS	not-accessible
	STATUS		current
	DESCRIPTION	"Maintenance EndPoint Index"
	::= { rcCfmTransmitLbmEntry 3}

rcCfmTransmitLbmDomainName OBJECT-TYPE
	SYNTAX		DisplayString(SIZE (1..22))
	MAX-ACCESS	read-only
	STATUS		current
	DESCRIPTION	"Maintenance Domain Name"
	::= { rcCfmTransmitLbmEntry 4}

rcCfmTransmitLbmAssociationName OBJECT-TYPE
	SYNTAX		DisplayString(SIZE (1..22))
	MAX-ACCESS	read-only
	STATUS		current
	DESCRIPTION	"Maintenance Association Name"
	::= { rcCfmTransmitLbmEntry 5}

rcCfmTransmitLbmDestMacAddress OBJECT-TYPE
	SYNTAX 		MacAddress
	MAX-ACCESS	read-write
	STATUS		current
	DESCRIPTION	"An indication of the target MAC Address Field to 
			be transmitted, either:
			A unicast destination MAC address."
	::= { rcCfmTransmitLbmEntry 6}

rcCfmTransmitLbmDestMepId OBJECT-TYPE
	SYNTAX 		Integer32 (0..8191)
	MAX-ACCESS	read-write
	STATUS		current
	DESCRIPTION	"An indication of the target MAC Address Field to 
			be transmitted, either:
			The Maintenance Assiciation End Point identifier of 
			another MEP in the same Maintenance Association"
	::= { rcCfmTransmitLbmEntry 7}

rcCfmTransmitLbmDestIsMepId OBJECT-TYPE
	SYNTAX 		TruthValue
	MAX-ACCESS	read-write
	STATUS		current
	DESCRIPTION	"True indicates that MepId of the target MEP is used
			for Loopback transmission.
			False indicates that unicast destination MAC address 
			of the target MEP is used for Loopback transmission."
	::= { rcCfmTransmitLbmEntry 8}

rcCfmTransmitLbmMessages  OBJECT-TYPE
	SYNTAX  	Integer32 (1..10000)
	MAX-ACCESS	read-write
	STATUS		current
	DESCRIPTION	"The number of loopback messages to be transmitted."
               
	DEFVAL {1}
	::= { rcCfmTransmitLbmEntry 9}

rcCfmTransmitLbmVlanPriority OBJECT-TYPE
	SYNTAX  	Integer32 (0..7)
	MAX-ACCESS	read-write
	STATUS		current
	DESCRIPTION	"Priority. 3 bit value to be used in the VLAN tsg, if present in 
			the transmitted frame."
	DEFVAL {7}
	::= { rcCfmTransmitLbmEntry 11}

rcCfmTransmitLbmVlanDropEnable OBJECT-TYPE
	SYNTAX  	TruthValue
	MAX-ACCESS	read-write
	STATUS		current
	DESCRIPTION	"Drop Enable bit value to be used in the VLAN tag, if present in 
			the transmitted frame."
	DEFVAL {false}
	::= { rcCfmTransmitLbmEntry 12}

rcCfmTransmitLbmSeqNumber OBJECT-TYPE
	SYNTAX 		Integer32
	MAX-ACCESS	read-only
	STATUS		current
	DESCRIPTION	"The transaction identifier/sequence number of the first loopback 
			message (to be) sent."
	DEFVAL {0}
	::= { rcCfmTransmitLbmEntry 13}		

rcCfmTransmitLbmResultOk OBJECT-TYPE
	SYNTAX 		TruthValue
	MAX-ACCESS	read-only
	STATUS		current
	DESCRIPTION	"Indicates the result of the operation:
			-true.      The Loopback Message(s) will be (or have been) sent.
			-false.   The Loopback Message(s) will not be sent."
	DEFVAL {true}
	::= { rcCfmTransmitLbmEntry 14}
	 
rcCfmTransmitLbmStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to transmit, 
				     the Loopback messages.
                        -abort       The service is aborted or about to abort the Loopback messages.

			This column will also be used to avoid concurrency or 
                        race condition problems that could occur if two or 
                        more management entities try to 
			use the service at the same time. "
	REFERENCE       "Delete notReady status due to CR Q01482201"
	DEFVAL {ready}
	::= { rcCfmTransmitLbmEntry 15}

rcCfmTransmitLbmResult  OBJECT-TYPE
	SYNTAX 		DisplayString(SIZE (1..799))
	MAX-ACCESS	read-only
	STATUS		current
	DESCRIPTION	"Display the LBM result."
	::= { rcCfmTransmitLbmEntry 16}
	 
rcCfmTransmitLbmTimeoutInt  OBJECT-TYPE
        SYNTAX          Integer32 (1..10)
        MAX-ACCESS      read-write
        STATUS          current
        DESCRIPTION    "The interval to wait for an LBM time-out with a 
                       range of (1..10)  seconds with a default value of 3 
                       seconds."
        DEFVAL {3}
        ::= { rcCfmTransmitLbmEntry 18}

rcCfmTransmitLbmInterFrameInt  OBJECT-TYPE
        SYNTAX          Integer32 (0..1000)
        MAX-ACCESS      read-write
        STATUS          current
        DESCRIPTION     "The interval between LBM frames with a range of 
                        (0..1000) msecs with a default value of 500 msecs.
                        The value of 0 msecs indicates to send the frames as 
                        fast as possible."
        DEFVAL {500}
        ::= { rcCfmTransmitLbmEntry 19}

rcCfmTransmitLbmTestPattern OBJECT-TYPE
        SYNTAX          INTEGER {
                               allZero(1),
                               allZeroCrc(2),
                               pseudoRandomBitSequence(3),
                               pseudoRandomBitSequenceCrc(4)
                        }
        MAX-ACCESS      read-write
        STATUS          current
        DESCRIPTION     "The test pattern to use in the LBM PDU with range of 
                        values namely allZero, allZeroCrc, 
                        pseudoRandomBitSequence and pseudoRandomBitSequenceCrc 
                        and with a default value of allZero.
                        value                  meaning
                        --------               -------
                        allZero(1)             Null signal without CRC-32
                        allZeroCrc(2)          Null signal with CRC-32    
                        pseudoRandomBitSequence(3) PRBS 1/2^31-1 without CRC-32
                        pseudoRandomBitSequenceCrc(4) PBRS 1/2^31-1 with CRC-32"
        DEFVAL {allZero}
        ::= { rcCfmTransmitLbmEntry 20}

rcCfmTransmitLbmDataSize  OBJECT-TYPE
	SYNTAX  	Integer32 (0..400)
	MAX-ACCESS	read-write
	STATUS		current
	DESCRIPTION	"An arbitrary amount of data to be included in the data TLV, if the
			Data Size is selected to be sent."
	DEFVAL {0}
	::= { rcCfmTransmitLbmEntry 21}


rcCfmTransmitLbmFrameSize  OBJECT-TYPE
	SYNTAX  	Integer32 (0..9600)
	MAX-ACCESS	read-write
	STATUS		current
	DESCRIPTION	"If the frame size (64-500 for R-Mod and 64-9600 for RC-Mod)is specified then the data size shall be internally calculated and the calculated data size shall be included in the data TLV."
	DEFVAL {0}
	::= { rcCfmTransmitLbmEntry 22}

rcCfmTransmitLbmSourceMode  OBJECT-TYPE
        SYNTAX        INTEGER {
			      nodal(1),
			      smltVirtual(2)             
                      }
        MAX-ACCESS      read-write
        STATUS          current
        DESCRIPTION     "Source modes of the transmit loopback service. "
        DEFVAL {nodal}
        ::= { rcCfmTransmitLbmEntry 23}

-- The Transmit Linktrace Table

rcCfmTransmitLtmTable OBJECT-TYPE
	SYNTAX		SEQUENCE OF RcCfmTransmitLtmEntry
	MAX-ACCESS	not-accessible
	STATUS		current
	DESCRIPTION	"Connectivity Fault Management transmit LTM table"
	::= { rcCfm 18}

rcCfmTransmitLtmEntry OBJECT-TYPE
	SYNTAX		RcCfmTransmitLtmEntry
	MAX-ACCESS	not-accessible
	STATUS		current
	DESCRIPTION	"Connectivity Fault Management Maintenance EndPoint LTM entry."
	INDEX		{rcCfmTransmitLtmDomainIndex, rcCfmTransmitLtmAssociationIndex, rcCfmTransmitLtmIndex }
	::= { rcCfmTransmitLtmTable 1}

RcCfmTransmitLtmEntry ::=
	SEQUENCE {
		rcCfmTransmitLtmDomainIndex		Integer32,
                rcCfmTransmitLtmAssociationIndex	Integer32,
		rcCfmTransmitLtmIndex			Integer32,
                rcCfmTransmitLtmDomainName		DisplayString,
                rcCfmTransmitLtmAssociationName		DisplayString,
		rcCfmTransmitLtmVlanPriority		Integer32,
		rcCfmTransmitLtmDestMacAddress		MacAddress,
		rcCfmTransmitLtmDestMepId		Integer32,
		rcCfmTransmitLtmDestIsMepId		TruthValue,
		rcCfmTransmitLtmTtl 			Integer32,
		rcCfmTransmitLtmSeqNumber		Integer32,
		rcCfmTransmitLtmResultOk		TruthValue,
		rcCfmTransmitLtmStatus			INTEGER,
		rcCfmTransmitLtmResult                  DisplayString,
                rcCfmTransmitLtmFlag                    INTEGER,
		rcCfmTransmitLtmSourceMode              INTEGER
	}

rcCfmTransmitLtmDomainIndex OBJECT-TYPE
	SYNTAX		Integer32 (1..2147483647)
	MAX-ACCESS	not-accessible
	STATUS		current
	DESCRIPTION	"Maintenance Domain Name"
	::= { rcCfmTransmitLtmEntry 1}

rcCfmTransmitLtmAssociationIndex OBJECT-TYPE
	SYNTAX		Integer32 (1..2147483647)
	MAX-ACCESS	not-accessible
	STATUS		current
	DESCRIPTION	"Maintenance Association Name"
	::= { rcCfmTransmitLtmEntry 2}

rcCfmTransmitLtmIndex OBJECT-TYPE
	SYNTAX		Integer32 (1..8191)
	MAX-ACCESS	not-accessible
	STATUS		current
	DESCRIPTION	"Maintenance EndPoint Index"
	::= { rcCfmTransmitLtmEntry 3}

rcCfmTransmitLtmDomainName OBJECT-TYPE
	SYNTAX		DisplayString(SIZE (1..22))
	MAX-ACCESS	read-only
	STATUS		current
	DESCRIPTION	"Maintenance Domain Name"
	::= { rcCfmTransmitLtmEntry 4}

rcCfmTransmitLtmAssociationName OBJECT-TYPE
	SYNTAX		DisplayString(SIZE (1..22))
	MAX-ACCESS	read-only
	STATUS		current
	DESCRIPTION	"Maintenance Association Name"
	::= { rcCfmTransmitLtmEntry 5}

rcCfmTransmitLtmVlanPriority OBJECT-TYPE
        SYNTAX          Integer32 (0..7)
        MAX-ACCESS      read-write
        STATUS          current
        DESCRIPTION     "Priority. 3 bit value to be used in the VLAN tag, if present in
                        the transmitted frame."
        DEFVAL {7}
	::= { rcCfmTransmitLtmEntry 6}

rcCfmTransmitLtmDestMacAddress OBJECT-TYPE
	SYNTAX 		MacAddress
	MAX-ACCESS	read-write
	STATUS		current
	DESCRIPTION	"An indication of the target MAC Address Field to 
			be transmitted, either:
			A unicast destination MAC address."
	::= { rcCfmTransmitLtmEntry 7}

rcCfmTransmitLtmDestMepId OBJECT-TYPE
	SYNTAX 		Integer32 (0..8191)
	MAX-ACCESS	read-write
	STATUS		current
	DESCRIPTION	"An indication of the target MAC Address Field to 
			be transmitted, either:
			The Maintenance Assiciation End Point identifier of 
			another MEP in the same Maintenance Association"
	::= { rcCfmTransmitLtmEntry 8}

rcCfmTransmitLtmDestIsMepId OBJECT-TYPE
	SYNTAX 		TruthValue
	MAX-ACCESS	read-write
	STATUS		current
	DESCRIPTION	"True indicates that MepId of the target MEP is used
			for Loopback transmission.
			False indicates that unicast destination MAC address 
			of the target MEP is used for Loopback transmission."
	::= { rcCfmTransmitLtmEntry 9}

rcCfmTransmitLtmTtl     OBJECT-TYPE
	SYNTAX  	Integer32 (0..255)
	MAX-ACCESS	read-write
	STATUS		current
	DESCRIPTION	"The number of hops remaining to this LTM. 
			 Decremented by 1 by each Bridge that handles the LTM. 
			 The decremented value is returned in the LTR. If 0 
                         on output, the LTM is not transmitted to the next 
                         hop. The value of the TTL Field in the LTM 
                         transmitted by the originating MEP is controlled by a 
                         Managed Object; The default value if none is 
                         specified is 64."
	DEFVAL {64}
	::= { rcCfmTransmitLtmEntry 10}

rcCfmTransmitLtmSeqNumber OBJECT-TYPE
	SYNTAX 		Integer32
	MAX-ACCESS	read-only
	STATUS		current
	DESCRIPTION	"The transaction identifier/sequence number of the first loopback 
			message (to be) sent."
	DEFVAL {0}
	::= { rcCfmTransmitLtmEntry 11}		

rcCfmTransmitLtmResultOk OBJECT-TYPE
	SYNTAX 		TruthValue
	MAX-ACCESS	read-only
	STATUS		current
	DESCRIPTION	"Indicates the result of the operation:
			-true.      The Loopback Message(s) will be (or have been) sent.
			-false.   The Loopback Message(s) will not be sent."
	DEFVAL {true}
	::= { rcCfmTransmitLtmEntry 12}
	 
rcCfmTransmitLtmStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to 
                                     transmit, the Loopback messages.

			-abort.      The service is aborted, or about to abort
                                     the LTM message

			This column will also be used to avoid concurrency or 
                        race condition problems that could occur if two or 
                        more management entities try to 
			use the service at the same time. "
	REFERENCE       "Delete notReady status due to CR Q01482201"
	DEFVAL {ready}
	::= { rcCfmTransmitLtmEntry 13}

rcCfmTransmitLtmResult  OBJECT-TYPE
	SYNTAX 		DisplayString(SIZE (1..1023))
	MAX-ACCESS	read-only
	STATUS	        obsolete 	
	DESCRIPTION	"Display the LTM result."
	::= { rcCfmTransmitLtmEntry 14}

rcCfmTransmitLtmFlag    OBJECT-TYPE
	SYNTAX 		INTEGER {
				none(1),
				internalError(2),
                                noRemoteMep(3),
                                invalidRemoteMepMac(4),
                                noRemoteMepMacLearned(5),
                                mepDisabled(6), 
                                noLtrResponse(7),
                                ltmToOwnMepMac(8),
                                epDisabled(9),
                                trunkDisabled(10),
                                ltmComplete(11),
				ltmLeafNode(12)
			}
	MAX-ACCESS	read-only
	STATUS	        current 	
	DESCRIPTION	"LTM result flag indicating LTM status or error code. 
                         Each enum value represents a status or error case.  
                         1 - No error  
                         2 - Ltm Internal Error
                         3 - Unknown Remote Maintenance End Point
                         4 - Invalid Remote Maintenance End Point Mac Address
                         5 - Unset Remote Maintenance End Point Mac Address
                         6 - Mep must be enabled in order to perform LTM
                         7 - No Ltr response received
                         8 - Linktrace to own Mep MAC is not sent
                         9 - Endpoint must be enabled in order to perform LTM
                         10 - Pbt-trunk must be enabled in order to perform LTM
                         11 - LTM completed
			 12 - LTM leaf node"
	::= { rcCfmTransmitLtmEntry 15}

rcCfmTransmitLtmSourceMode  OBJECT-TYPE
        SYNTAX        INTEGER {
			      nodal(1),
			      smltVirtual(2)             
                      }
        MAX-ACCESS      read-write
        STATUS          current
        DESCRIPTION     "Source modes of the transmit linktrace service. "
        DEFVAL {nodal}
        ::= {rcCfmTransmitLtmEntry 16 }

-- The Linktrace Reply Table

CfmRelayActionFieldValue ::= TEXTUAL-CONVENTION
    STATUS current
    DESCRIPTION
            "Possible values the Relay action field can take."
    REFERENCE
            "802.1ag clauses 12.14.7.5.3:g, 20.36.2.5, 21.9.5, and
             Table 21-27"
    SYNTAX INTEGER {
             rlyHit (1),
             rlyFdb (2),
             rlyMpdb (3),
             unknown (4)
    }

CfmIngressActionFieldValue ::= TEXTUAL-CONVENTION
    STATUS current
    DESCRIPTION
            "Possible values returned in the ingress action field."
    REFERENCE
            "802.1ag clauses 12.14.7.5.3:g, 20.36.2.6, 21.9.8.1, and
            Table 21-30"
    SYNTAX INTEGER {
             ingOk (1),
             ingDown (2),
             ingBlocked (3),
             ingVid (4),
             ingNoTlv (5)
    }

CfmEgressActionFieldValue ::= TEXTUAL-CONVENTION
    STATUS current
    DESCRIPTION
            "Possible values returned in the egress action field"
    REFERENCE
            "802.1ag clauses 12.14.7.5.3:o, 20.36.2.10, 21.9.9.1, and
             Table 21-32"
    SYNTAX INTEGER {
             egrOk (1),
             egrDown (2),
             egrBlocked (3),
             egrVid (4),
             egrNoTlv (5)
    }

LldpPortIdSubtype ::= TEXTUAL-CONVENTION
    STATUS      current
    DESCRIPTION
            "This TC describes the source of a particular type of Port 
             identifier used in the LLDP MIB. The enumeration 'interfaceAlias(1)'
             represents a port identifier based on the ifAlias MIB object, 
             defined in IETF RFC 2863. The enumeration 'portComponent(2)'
             represents a port identifier based on the value of 
             entPhysicalAlias (defined in IETF RFC 2737) for a port component 
             (i.e., entPhysicalClass value of 'port(10)'), within the 
             containing chassis. The enumeration 'macAddress(3)' represents a 
             port identifier based on a unicast source address (encoded in 
             network byte order and IEEE 802.3 canonical bit order), which has
             been detected by the agent and associated with a particular port 
             (IEEE Std 802-2001). The enumeration 'networkAddress(4)' represents
             a port identifier based on a network address, detected by the 
             agent and associated with a particular port. The enumeration 
             'interfaceName(5)' represents a port identifier based on the 
             ifName MIB object, defined in IETF RFC 2863. The enumeration
             'agentCircuitId(6)' represents a port identifier based on the 
             agent-local identifier of the circuit (defined in RFC 3046), 
             detected by the agent and associated with a particular port. The 
             enumeration 'local(7)' represents a port identifier based on a 
             value locally assigned."
    SYNTAX   INTEGER {
             interfaceAlias(1),
             portComponent(2),
             macAddress(3),
             networkAddress(4),
             interfaceName(5),
             agentCircuitId(6),
             local(7)
    }

LldpPortId ::= TEXTUAL-CONVENTION
    STATUS      current
    DESCRIPTION
            "This TC describes the format of a port identifier string. 
            Objects of this type are always used with an associated 
            LldpPortIdSubtype object, which identifies the format of the 
            particular LldpPortId object instance. If the associated 
            LldpPortIdSubtype object has a value of 
            '342/200/230interfaceAlias(1)', then the octet string identifies 
            a particular instance of the ifAlias object (defined in IETF RFC 
            2863). If the particular ifAlias object does not contain any
            values, another port identifier type should be used. If the 
            associated LldpPortIdSubtype object has a value of 
            'portComponent(2)', then the octet string identifies a particular 
            instance of the entPhysicalAlias object (defined in IETF RFC 2737)
            for a port or backplane component. If the associated 
            LldpPortIdSubtype object has a value of 'macAddress(3)', then 
            this string identifies a Particular unicast source address 
            (encoded in network byte order and IEEE 802.3 canonical bit order)
            associated with the port (IEEE Std 802-2001). If the associated 
            LldpPortIdSubtype object has a value of 'networkAddress(4)', then 
            this string identifies a Network address associated with the port. 
            The first octet contains the IANA AddressFamilyNumbers enumeration 
            value for the specific address type, and octets 2 through N 
            contain the networkAddress address value in network byte order. If 
            the associated LldpPortIdSubtype object has a value of 
            'interfaceName(5)', then the octet string identifies A particular 
            instance of the ifName object (defined in IETF RFC 2863). If the 
            particular ifName object does not contain any values, another port 
            identifier type should be used. If the associated ldpPortIdSubtype 
            object has a value of 'agentCircuitId(6)', then this string 
            identifies a agent-local identifier of the circuit (defined in RFC
            3046). If the associated LldpPortIdSubtype object has a value of 
            '342/200/230local(7)', then this string identifies a locally 
            assigned port ID."
    SYNTAX      OCTET STRING (SIZE (1..255))

rcCfmLtrReplyTable OBJECT-TYPE
        SYNTAX          SEQUENCE OF RcCfmLtrReplyEntry
        MAX-ACCESS      not-accessible
        STATUS          current 
        DESCRIPTION     
                "This table contains a list of Linktrace replies received 
                by a specific MEP in response to a linktrace message."
        ::= { rcCfm 33}

rcCfmLtrReplyEntry OBJECT-TYPE
        SYNTAX          RcCfmLtrReplyEntry
        MAX-ACCESS      not-accessible
        STATUS          current
        DESCRIPTION     "The Linktrace Reply table entry."
        INDEX           {rcCfmLtrReplyDomainIndex, 
                         rcCfmLtrReplyAssociationIndex,
                         rcCfmLtrReplyMepId, 
                         rcCfmLtrReplySeqNumber, 
                         rcCfmLtrReplyHop,
                         rcCfmLtrReplyReceiveOrder}
        ::= { rcCfmLtrReplyTable 1}
    
RcCfmLtrReplyEntry ::=
        SEQUENCE {
                rcCfmLtrReplyDomainIndex          Integer32,
                rcCfmLtrReplyAssociationIndex     Integer32,
                rcCfmLtrReplyMepId                Integer32,
                rcCfmLtrReplySeqNumber            Integer32,
                rcCfmLtrReplyHop                  Integer32,
                rcCfmLtrReplyReceiveOrder         Integer32,
                rcCfmLtrReplyTtl                  Integer32,
                rcCfmLtrReplyDomainName           DisplayString,
                rcCfmLtrReplyAssociationName      DisplayString,
                rcCfmLtrReplyForwarded            TruthValue,
                rcCfmLtrReplyTerminalMep          TruthValue,
                rcCfmLtrReplyLastEgressIdentifier OCTET STRING,
                rcCfmLtrReplyNextEgressIdentifier OCTET STRING,
                rcCfmLtrReplyRelayAction          CfmRelayActionFieldValue,
                rcCfmLtrReplySrcMac               MacAddress,
                rcCfmLtrReplyIngressAction        CfmIngressActionFieldValue,
                rcCfmLtrReplyIngressMac           MacAddress,
                rcCfmLtrReplyIngressPortIdSubtype LldpPortIdSubtype,
                rcCfmLtrReplyIngressPortId        LldpPortId,
                rcCfmLtrReplyEgressAction         CfmEgressActionFieldValue,
                rcCfmLtrReplyEgressMac            MacAddress, 
                rcCfmLtrReplyEgressPortIdSubtype  LldpPortIdSubtype,
                rcCfmLtrReplyEgressPortId         LldpPortId
             }
rcCfmLtrReplyDomainIndex OBJECT-TYPE
        SYNTAX          Integer32 (1..2147483647)
        MAX-ACCESS      not-accessible
        STATUS          current
        DESCRIPTION     "Maintenance Domain Index"
        ::= { rcCfmLtrReplyEntry 1}

rcCfmLtrReplyAssociationIndex OBJECT-TYPE
        SYNTAX          Integer32 (1..2147483647) 
        MAX-ACCESS      not-accessible
        STATUS          current
        DESCRIPTION     "Maintenance Association Index"
        ::= { rcCfmLtrReplyEntry 2}
    
rcCfmLtrReplyMepId OBJECT-TYPE
        SYNTAX          Integer32 (1..8191)
        MAX-ACCESS      not-accessible
        STATUS          current
        DESCRIPTION     "Maintenance EndPoint ID"
        ::= { rcCfmLtrReplyEntry 3}

rcCfmLtrReplySeqNumber OBJECT-TYPE
        SYNTAX          Integer32 (0..2147483647)  
        MAX-ACCESS      not-accessible
        STATUS          current
        DESCRIPTION     
                "The transaction identifier/sequence number returned by a 
                previous transmit linktrace message command, indicating which 
                LTM's response is going to be returned."
        DEFVAL {0}
        ::= { rcCfmLtrReplyEntry 4}

rcCfmLtrReplyHop     OBJECT-TYPE
        SYNTAX          Integer32 (0..255)
        MAX-ACCESS      not-accessible
        STATUS          current
        DESCRIPTION     "The number of hops away from LTM initiator"
        ::= { rcCfmLtrReplyEntry 5}

rcCfmLtrReplyReceiveOrder OBJECT-TYPE
        SYNTAX          Integer32 (1..2147483647)
        MAX-ACCESS      not-accessible
        STATUS          current
        DESCRIPTION     
                "An index to distinguish among multiple LTRs with the same 
                LTR Transaction Identifier field  value. This value is 
                assigned sequentially from 1, in the order that the Linktrace 
                Initiator received the LTRs."
        ::= { rcCfmLtrReplyEntry 6}

rcCfmLtrReplyTtl     OBJECT-TYPE
        SYNTAX          Integer32 (0..255)
        MAX-ACCESS      read-only
        STATUS          current
        DESCRIPTION     "Ttl field value for a returned LTR."
        ::= { rcCfmLtrReplyEntry 7}

rcCfmLtrReplyDomainName OBJECT-TYPE
        SYNTAX          DisplayString(SIZE(1..22))
        MAX-ACCESS      read-only
        STATUS          current
        DESCRIPTION     "Maintenance Domain Name"
        ::= { rcCfmLtrReplyEntry 8}

rcCfmLtrReplyAssociationName OBJECT-TYPE
        SYNTAX          DisplayString(SIZE(1..22))
        MAX-ACCESS      read-only
        STATUS          current
        DESCRIPTION     "Maintenance Association Name"
        ::= { rcCfmLtrReplyEntry 9}

rcCfmLtrReplyForwarded OBJECT-TYPE
        SYNTAX          TruthValue
        MAX-ACCESS      read-only
        STATUS          current
        DESCRIPTION     
                "Indicates if a LTM was forwarded by the responding MP, as 
                returned in the 'FwdYes' flag of the flags field."
        ::= { rcCfmLtrReplyEntry 10}

rcCfmLtrReplyTerminalMep OBJECT-TYPE
        SYNTAX          TruthValue
        MAX-ACCESS      read-only
        STATUS          current
        DESCRIPTION     
                "A boolean value stating whether the forwarded LTM reached 
                a MEP enclosing its MA, as returned in the Terminal MEP flag 
                of the Flags field."
        ::= { rcCfmLtrReplyEntry 11}

rcCfmLtrReplyLastEgressIdentifier OBJECT-TYPE
        SYNTAX          OCTET STRING (SIZE(8))
        MAX-ACCESS      read-only 
        STATUS          current
        DESCRIPTION     
                "An octet field holding the Last Egress Identifier returned 
                in the LTR Egress   Identifier TLV of the LTR. The Last Egress 
                Identifier identifies the MEP Linktrace Indicator that 
                originated, or the Linktrace Responder that forwarded, the LTM 
                to which this LTR is the response. This is the same value as 
                the Egress Identifier TLV of that LTM."
        ::= { rcCfmLtrReplyEntry 12}


rcCfmLtrReplyNextEgressIdentifier OBJECT-TYPE
        SYNTAX          OCTET STRING (SIZE(8))
        MAX-ACCESS      read-only 
        STATUS          current
        DESCRIPTION     
                "An octet field holding the Next Egress Identifier returned in 
                the LTR Egress Identifier TLV of the LTR. The Next Egress 
                Identifier Identifies the Linktrace Responder that transmitted 
                this LTR, and can forward the LTM to the next hop. This is the 
                same value as the Egress Identifier TLV of the forwarded LTM, 
                if any. If the FwdYes bit of the Flags field is false, the 
                contents of this field are undefined, and the field is ignored 
                by the receiver."
        ::= { rcCfmLtrReplyEntry 13}

rcCfmLtrReplyRelayAction OBJECT-TYPE
        SYNTAX          CfmRelayActionFieldValue
        MAX-ACCESS      read-only 
        STATUS           current
        DESCRIPTION     "Value returned in the Relay Action field."
        DEFVAL          { unknown } 
        ::= { rcCfmLtrReplyEntry 14}


rcCfmLtrReplySrcMac OBJECT-TYPE
        SYNTAX          MacAddress
        MAX-ACCESS      read-only
        STATUS          current
        DESCRIPTION     
                "Mac address of the MP that respond to the LTM request for 
                this LTR"  
        ::= { rcCfmLtrReplyEntry 15}

rcCfmLtrReplyIngressAction OBJECT-TYPE 
        SYNTAX          CfmIngressActionFieldValue
        MAX-ACCESS      read-only
        STATUS          current
        DESCRIPTION     
                "The value returned in the Ingress Action Field of the LTM. 
                The value ingNoTlv(5) indicates that no Reply Ingress TLV 
                was returned in the LTM."
        ::= { rcCfmLtrReplyEntry 16} 

rcCfmLtrReplyIngressMac OBJECT-TYPE
        SYNTAX          MacAddress
        MAX-ACCESS      read-only
        STATUS          current
        DESCRIPTION     
                "Mac address returned in the ingress MAC address field. If the 
                rcCfmLtrReplyIngress object contains the value ingNoTlv(5), then 
                the contents of this object are meaningless."
        ::= { rcCfmLtrReplyEntry 17}

rcCfmLtrReplyIngressPortIdSubtype OBJECT-TYPE
        SYNTAX          LldpPortIdSubtype
        MAX-ACCESS      read-only
        STATUS          current
        DESCRIPTION     
                "Format of the Ingress Port ID. If the rcCfmLtrReplyIngress 
                object contains the value ingNoTlv(5), then the contents of 
                this object are meaningless."
        ::= { rcCfmLtrReplyEntry 18}

rcCfmLtrReplyIngressPortId OBJECT-TYPE
        SYNTAX          LldpPortId
        MAX-ACCESS      read-only
        STATUS          current
        DESCRIPTION     
                "Ingress Port ID. The format of this object is determined by 
                the value of the rcCfmLtrReplyIngressPortIdSubtype object. 
                If the rcCfmLtrReplyIngress object contains the value 
                ingNoTlv(5), then 
                the contents of this object are meaningless."
        ::= { rcCfmLtrReplyEntry 19}

rcCfmLtrReplyEgressAction OBJECT-TYPE
        SYNTAX          CfmEgressActionFieldValue
        MAX-ACCESS      read-only
        STATUS          current
        DESCRIPTION     
                "The value returned in the Egress Action Field of the LTM. The 
                value egrNoTlv(5) indicates that no Reply Egress TLV was 
                returned in the LTM."
        ::= { rcCfmLtrReplyEntry 20}

rcCfmLtrReplyEgressMac OBJECT-TYPE
        SYNTAX          MacAddress
        MAX-ACCESS      read-only
        STATUS          current
        DESCRIPTION     
                "Mac address returned in the egress MAC address field. If the 
                rcCfmLtrReplyEgress object contains the value egrNoTlv(5), 
                then the contents of this object are meaningless."
        ::= { rcCfmLtrReplyEntry 21}

rcCfmLtrReplyEgressPortIdSubtype OBJECT-TYPE
        SYNTAX          LldpPortIdSubtype
        MAX-ACCESS      read-only
        STATUS          current
        DESCRIPTION     
                "Format of the Egress Port ID. If the rcCfmLtrReplyEgress 
                 object contains the value egrNoTlv(5), then the contents 
                 of this object are meaningless."
        ::= { rcCfmLtrReplyEntry 22}

rcCfmLtrReplyEgressPortId OBJECT-TYPE
        SYNTAX          LldpPortId
        MAX-ACCESS      read-only
        STATUS          current
        DESCRIPTION     
                "Egress Port ID. The format of this object is determined by 
                the value of the rcCfmLtrReplyEgressPortIdSubtype object. 
                If the rcCfmLtrReplyEgress object contains the value 
                egrNoTlv(5), then the contents of this object are meaningless."
        ::= { rcCfmLtrReplyEntry 23}

-- The Transmit L2Ping Table

rcCfmTransmitL2PingTable OBJECT-TYPE
	SYNTAX		SEQUENCE OF RcCfmTransmitL2PingEntry
	MAX-ACCESS	not-accessible
	STATUS		current
	DESCRIPTION	"Connectivity Fault Management transmit L2Ping table"
	::= { rcCfm 34}

rcCfmTransmitL2PingEntry OBJECT-TYPE
	SYNTAX		RcCfmTransmitL2PingEntry
	MAX-ACCESS	not-accessible
	STATUS		current
	DESCRIPTION	"Connectivity Fault Management Maintenance EndPoint L2Ping entry."
	INDEX		{rcCfmTransmitL2PingVlanId }
	::= { rcCfmTransmitL2PingTable 1}

RcCfmTransmitL2PingEntry ::=
	SEQUENCE {
		rcCfmTransmitL2PingVlanId	        Integer32,
		rcCfmTransmitL2PingDestMacAddress       MacAddress,
		rcCfmTransmitL2PingHostName             OCTET STRING,	
		rcCfmTransmitL2PingDestIsHostName       TruthValue,
		rcCfmTransmitL2PingMessages		Integer32,
		rcCfmTransmitL2PingPriority		Integer32,
	        rcCfmTransmitL2PingTimeoutInt           Integer32,
	        rcCfmTransmitL2PingTestPattern          INTEGER,
	        rcCfmTransmitL2PingDataSize	        Integer32,
	        rcCfmTransmitL2PingFrameSize	        Integer32,
	        rcCfmTransmitL2PingSourceMode           INTEGER,
		rcCfmTransmitL2PingSeqNumber		Integer32,
		rcCfmTransmitL2PingResultOk		TruthValue,
		rcCfmTransmitL2PingStatus		INTEGER,
		rcCfmTransmitL2PingResult               DisplayString
 	}

rcCfmTransmitL2PingVlanId OBJECT-TYPE
	SYNTAX		Integer32 (1..4084)
	MAX-ACCESS	not-accessible
	STATUS		current
	DESCRIPTION	"A value that uniquely identifies the Customer Vlan"
	::= { rcCfmTransmitL2PingEntry 1}

rcCfmTransmitL2PingDestMacAddress OBJECT-TYPE
	SYNTAX		MacAddress
	MAX-ACCESS	read-write
	STATUS		current
	DESCRIPTION	"An indication of the target MAC Address field to be transmitted"
	::= { rcCfmTransmitL2PingEntry 2}

rcCfmTransmitL2PingHostName OBJECT-TYPE
	SYNTAX		OCTET STRING (SIZE (0..255))
	MAX-ACCESS	read-write
	STATUS		current
	DESCRIPTION	"The target host name"
	::= { rcCfmTransmitL2PingEntry 3}

rcCfmTransmitL2PingDestIsHostName OBJECT-TYPE
	SYNTAX 		TruthValue
	MAX-ACCESS	read-write
	STATUS		current
	DESCRIPTION	"True indicates that the host name is used for L2Ping transmission"
	::= { rcCfmTransmitL2PingEntry 4}

rcCfmTransmitL2PingMessages  OBJECT-TYPE
	SYNTAX  	Integer32(1..200)
	MAX-ACCESS	read-write
	STATUS		current
	DESCRIPTION	"The number of L2Ping messages to be transmitted."
               
	DEFVAL {1}
	::= { rcCfmTransmitL2PingEntry 5}

rcCfmTransmitL2PingPriority OBJECT-TYPE
	SYNTAX  	Integer32(0..7)
	MAX-ACCESS	read-write
	STATUS		current
	DESCRIPTION	"Priority. 3 bit value to be used in the VLAN hdr,  
			if present in the transmitted frame."
	DEFVAL {7}
	::= { rcCfmTransmitL2PingEntry 6}

rcCfmTransmitL2PingTimeoutInt  OBJECT-TYPE
        SYNTAX          Integer32(1..10)
        MAX-ACCESS      read-write
        STATUS          current
        DESCRIPTION    "The interval to wait for an L2Ping time-out with a 
                       range of (1..10)  seconds with a default value of 3 
                       seconds."
        DEFVAL {3}
        ::= { rcCfmTransmitL2PingEntry 7}

rcCfmTransmitL2PingTestPattern OBJECT-TYPE
        SYNTAX          INTEGER {
                               allZero(1),
                               allZeroCrc(2),
                               pseudoRandomBitSequence(3),
                               pseudoRandomBitSequenceCrc(4)
                        }
        MAX-ACCESS      read-write
        STATUS          current
        DESCRIPTION     "The test pattern to use in the L2Ping PDU with range of 
                        values namely allZero, allZeroCrc, 
                        pseudoRandomBitSequence and pseudoRandomBitSequenceCrc 
                        and with a default value of allZero.
                        value                  meaning
                        --------               -------
                        allZero(1)             Null signal without CRC-32
                        allZeroCrc(2)          Null signal with CRC-32    
                        pseudoRandomBitSequence(3) PRBS 1/2^31-1 without CRC-32
                        pseudoRandomBitSequenceCrc(4) PBRS 1/2^31-1 with CRC-32"
        DEFVAL {allZero}
        ::= { rcCfmTransmitL2PingEntry 8}

rcCfmTransmitL2PingDataSize  OBJECT-TYPE
	SYNTAX  	Integer32(0..400)
	MAX-ACCESS	read-write
	STATUS		current
	DESCRIPTION	"An arbitrary amount of data to be included in the data TLV, if the
			Data Size is selected to be sent."
	DEFVAL {0}
	::= { rcCfmTransmitL2PingEntry 9}

rcCfmTransmitL2PingFrameSize  OBJECT-TYPE
	SYNTAX  	Integer32(0..9600)
	MAX-ACCESS	read-write
	STATUS		current
	DESCRIPTION	"If the frame size is specified then the data size 
                        shall be internally calculated and the calculated data
                        size shall be included in the data TLV."
	DEFVAL {0}
	::= { rcCfmTransmitL2PingEntry 10}

rcCfmTransmitL2PingSourceMode  OBJECT-TYPE
        SYNTAX        INTEGER {
			      nodal(1),
			      smltVirtual(2)             
                      }
        MAX-ACCESS      read-write
        STATUS          current
        DESCRIPTION     "Source modes of the transmit loopback service. "
        DEFVAL {nodal}
        ::= { rcCfmTransmitL2PingEntry 11}


rcCfmTransmitL2PingSeqNumber OBJECT-TYPE
	SYNTAX 		Integer32
	MAX-ACCESS	read-only
	STATUS		current
	DESCRIPTION	"The transaction identifier/sequence number of the first loopback 
			message (to be) sent."
	DEFVAL {0}
	::= { rcCfmTransmitL2PingEntry 12}		

rcCfmTransmitL2PingResultOk OBJECT-TYPE
	SYNTAX 		TruthValue
	MAX-ACCESS	read-only
	STATUS		current
	DESCRIPTION	"Indicates the result of the operation:
			-true.    The L2Ping Message(s) will be (or have been) sent.
			-false.   The L2Ping Message(s) will not be sent."
	DEFVAL {true}
	::= { rcCfmTransmitL2PingEntry 13}
	 
rcCfmTransmitL2PingStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to 
                                     transmit, the L2Ping messages.
                        -abort       The service is aborted or about to abort 
                                     the L2Ping messages.

			This column will also be used to avoid concurrency or 
                        race condition problems that could occur if two or 
                        more management entities try to 
			use the service at the same time. "
	REFERENCE       "Delete notReady status due to CR Q01482201"
	DEFVAL {ready}
	::= { rcCfmTransmitL2PingEntry 14}

rcCfmTransmitL2PingResult  OBJECT-TYPE
	SYNTAX 		DisplayString(SIZE (1..799))
	MAX-ACCESS	read-only
	STATUS		current
	DESCRIPTION	"Display the L2Ping result."
	::= { rcCfmTransmitL2PingEntry 15}
	 

-- The Transmit L2Trace Table

rcCfmTransmitL2TraceTable OBJECT-TYPE
	SYNTAX		SEQUENCE OF RcCfmTransmitL2TraceEntry
	MAX-ACCESS	not-accessible
	STATUS		current
	DESCRIPTION	"Connectivity Fault Management transmit L2Trace table"
	::= { rcCfm 35}

rcCfmTransmitL2TraceEntry OBJECT-TYPE
	SYNTAX		RcCfmTransmitL2TraceEntry
	MAX-ACCESS	not-accessible
	STATUS		current
	DESCRIPTION	"Connectivity Fault Management Maintenance EndPoint L2Trace entry."
	INDEX		{rcCfmTransmitL2TraceVlanId }
	::= { rcCfmTransmitL2TraceTable 1}

RcCfmTransmitL2TraceEntry ::=
	SEQUENCE {
		rcCfmTransmitL2TraceVlanId	        	Integer32,
	        rcCfmTransmitL2TracePriority			Integer32,
		rcCfmTransmitL2TraceDestMacAddress      	MacAddress,
		rcCfmTransmitL2TraceHostName            	OCTET STRING,
	        rcCfmTransmitL2TraceIsid                        Integer32,
	        rcCfmTransmitL2TraceNickName                    DisplayString,	
		rcCfmTransmitL2TraceDestIsHostName      	TruthValue,
		rcCfmTransmitL2TraceIsidTree			TruthValue,
		rcCfmTransmitL2TraceTtl 			Integer32,
	        rcCfmTransmitL2TraceSourceMode            	INTEGER,
		rcCfmTransmitL2TraceSeqNumber			Integer32,
		rcCfmTransmitL2TraceResultOk			TruthValue,
		rcCfmTransmitL2TraceStatus		        INTEGER,
       		rcCfmTransmitL2TraceFlag		        INTEGER
	}

rcCfmTransmitL2TraceVlanId OBJECT-TYPE
	SYNTAX		Integer32 (1..4084)
	MAX-ACCESS	not-accessible
	STATUS		current
	DESCRIPTION	"A value that uniquely identifies the Customer Vlan"
	::= { rcCfmTransmitL2TraceEntry 1}

rcCfmTransmitL2TracePriority OBJECT-TYPE
	SYNTAX  	Integer32(0..7)
	MAX-ACCESS	read-write
	STATUS		current
	DESCRIPTION	"Priority. 3 bit value to be used in the VLAN hdr, 
                        if present in the transmitted frame."
	DEFVAL {7}
	::= { rcCfmTransmitL2TraceEntry 2}

rcCfmTransmitL2TraceDestMacAddress OBJECT-TYPE
	SYNTAX		MacAddress
	MAX-ACCESS	read-write
	STATUS		current
	DESCRIPTION	"An indication of the target MAC Address field to be transmitted"
	::= { rcCfmTransmitL2TraceEntry 3}

rcCfmTransmitL2TraceHostName OBJECT-TYPE
	SYNTAX		OCTET STRING (SIZE (0..255))
	MAX-ACCESS	read-write
	STATUS		current
	DESCRIPTION	"The target host name"
	::= { rcCfmTransmitL2TraceEntry 4}

rcCfmTransmitL2TraceIsid  OBJECT-TYPE
	SYNTAX        Integer32 (1..16777215)
        MAX-ACCESS    read-write
        STATUS        current
        DESCRIPTION   "Isid Id"
	::= { rcCfmTransmitL2TraceEntry 5}

rcCfmTransmitL2TraceNickName OBJECT-TYPE
	SYNTAX        DisplayString (SIZE (7))
 	MAX-ACCESS    read-only
	STATUS        current
        DESCRIPTION   "Local Node nick name"
	::= { rcCfmTransmitL2TraceEntry 6}

rcCfmTransmitL2TraceDestIsHostName OBJECT-TYPE
	SYNTAX 		TruthValue
	MAX-ACCESS	read-write
	STATUS		current
	DESCRIPTION	"True indicates that the host name is used for L2Trace transmission"
	::= { rcCfmTransmitL2TraceEntry 7}

rcCfmTransmitL2TraceIsidTree  OBJECT-TYPE
	SYNTAX 		TruthValue
	MAX-ACCESS	read-write
	STATUS		current
	DESCRIPTION	"True indicates that the multicast tree will be traced.
		         False indicates that the unicast path will be traced"
	::= { rcCfmTransmitL2TraceEntry 8}

rcCfmTransmitL2TraceTtl     OBJECT-TYPE
	SYNTAX  	Integer32(0..255)
	MAX-ACCESS	read-write
	STATUS		current
	DESCRIPTION	"The number of hops remaining to this L2Trace. 
			 Decremented by 1 by each Bridge that handles the L2Trace. 
			 The decremented value is returned in the L2Trace. If 0 
                         on output, the L2Trace is not transmitted to the next 
                         hop. The value of the TTL Field in the L2Trace
                         transmitted by the originating MEP is controlled by a 
                         Managed Object; The default value if none is 
                         specified is 64."
	DEFVAL {64}
	::= { rcCfmTransmitL2TraceEntry 9}


rcCfmTransmitL2TraceSourceMode  OBJECT-TYPE
        SYNTAX        INTEGER {
			      nodal(1),
			      smltVirtual(2)             
                      }
        MAX-ACCESS      read-write
        STATUS          current
        DESCRIPTION     "Source modes of the transmit loopback service. "
        DEFVAL {nodal}
        ::= { rcCfmTransmitL2TraceEntry 10}

rcCfmTransmitL2TraceSeqNumber OBJECT-TYPE
	SYNTAX 		Integer32
	MAX-ACCESS	read-only
	STATUS		current
	DESCRIPTION	"The transaction identifier/sequence number of the first loopback 
			message (to be) sent."
	DEFVAL {0}
	::= { rcCfmTransmitL2TraceEntry 11}		

rcCfmTransmitL2TraceResultOk OBJECT-TYPE
	SYNTAX 		TruthValue
	MAX-ACCESS	read-only
	STATUS		current
	DESCRIPTION	"Indicates the result of the operation:
			-true.    The L2Trace Message(s) will be (or have been) sent.
			-false.   The L2Trace Message(s) will not be sent."
	DEFVAL {true}
	::= { rcCfmTransmitL2TraceEntry 12}
	 
rcCfmTransmitL2TraceStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to 
                                     transmit, the L2Trace messages.
                        -abort       The service is aborted or about to abort 
                                     the L2Trace messages.

			This column will also be used to avoid concurrency or 
                        race condition problems that could occur if two or 
                        more management entities try to 
			use the service at the same time. "
	REFERENCE       "Delete notReady status due to CR Q01482201"
	DEFVAL {ready}
	::= { rcCfmTransmitL2TraceEntry 13}

rcCfmTransmitL2TraceFlag    OBJECT-TYPE
	SYNTAX 		INTEGER {
				none(1),
				internalError(2),
                                invalidMac(3),
                                mepDisabled(4), 
                                noL2TraceResponse(5),
                                l2TraceToOwnMepMac(6),
                                l2TraceComplete(7),
			        l2TraceLookupFailure(8),
				l2TraceLeafNode(9),
				l2TraceNotInTree(10),
				l2TraceSmltNotPrimary(11)
			}
	MAX-ACCESS	read-only
	STATUS	        current 	
	DESCRIPTION	"L2Trace result flag indicating L2Trace status or error code. 
                         Each enum value represents a status or error case.  
                         1 - No error  
                         2 - L2Trace Internal Error
                         3 - Invalid Mac Address
                         4 - Mep must be enabled in order to perform L2Trace
                         5 - No L2Trace response received
                         6 - L2Trace to own Mep MAC is not sent
                         7 - L2Trace completed
			 8 - Lookup failure for L2Trace
			 9 - On a leaf node in the i-sid tree
			10 - Not in the i-sid tree
			11 - Requested SMLT Source from Non-Primary Node"
	
		 
	::= { rcCfmTransmitL2TraceEntry 14}	 

-- L2Trace Reply Table

rcCfmL2TraceReplyTable OBJECT-TYPE
        SYNTAX          SEQUENCE OF RcCfmL2TraceReplyEntry
        MAX-ACCESS      not-accessible
        STATUS          current 
        DESCRIPTION     
                "This table contains a list of l2trace replies received 
                by a specific MEP in response to a linktrace message."
        ::= { rcCfm 36}

rcCfmL2TraceReplyEntry OBJECT-TYPE
        SYNTAX          RcCfmL2TraceReplyEntry
        MAX-ACCESS      not-accessible
        STATUS          current
        DESCRIPTION     "The Linktrace Reply table entry."
        INDEX           {rcCfmL2TraceReplyVlanId,rcCfmL2TraceReplySeqNumber,
                         rcCfmL2TraceReplyHop,rcCfmL2TraceReplyReceiveOrder}
        ::= { rcCfmL2TraceReplyTable 1}
    
RcCfmL2TraceReplyEntry ::=
        SEQUENCE {
		rcCfmL2TraceReplyVlanId	              Integer32,
		rcCfmL2TraceReplySeqNumber	      Integer32,
		rcCfmL2TraceReplyHop                  Integer32,	
                rcCfmL2TraceReplyReceiveOrder         Integer32,
		rcCfmL2TraceReplyTtl                  Integer32,	
                rcCfmL2TraceReplySrcMac               MacAddress,
		rcCfmL2TraceReplyHostName             OCTET STRING,
		rcCfmL2TraceReplyLastSrcMac            MacAddress,
		rcCfmL2TraceReplyLastHostName          OCTET STRING
             }

rcCfmL2TraceReplyVlanId OBJECT-TYPE
	SYNTAX		Integer32 (1..4084)
	MAX-ACCESS	not-accessible
	STATUS		current
	DESCRIPTION	"A value that uniquely identifies the Customer Vlan"
	::= {rcCfmL2TraceReplyEntry 1}

rcCfmL2TraceReplySeqNumber OBJECT-TYPE
        SYNTAX          Integer32 (0..2147483647)  
        MAX-ACCESS      not-accessible
        STATUS          current
        DESCRIPTION     
                "The transaction identifier/sequence number returned by a 
                previous transmit linktrace message command, indicating which 
                L2Trace's response is going to be returned."
        DEFVAL {0}
        ::= { rcCfmL2TraceReplyEntry 2}

rcCfmL2TraceReplyHop     OBJECT-TYPE
        SYNTAX          Integer32 (0..255)
        MAX-ACCESS      not-accessible
        STATUS          current
        DESCRIPTION     "The number of hops away from L2Trace initiator."
        ::= { rcCfmL2TraceReplyEntry 3}

rcCfmL2TraceReplyReceiveOrder OBJECT-TYPE
        SYNTAX          Integer32 (1..2147483647)
        MAX-ACCESS      not-accessible
        STATUS          current
        DESCRIPTION     
                "An index to distinguish among multiple L2Trace responses 
                with the same Transaction Identifier field  value. This value 
                is assigned sequentially from 1, in the order that the 
                Linktrace Initiator received the responses."
        ::= { rcCfmL2TraceReplyEntry 4}

rcCfmL2TraceReplyTtl     OBJECT-TYPE
        SYNTAX          Integer32 (0..255)
        MAX-ACCESS      read-only
        STATUS          current
        DESCRIPTION     "Ttl field value for a returned L2Trace response."
        ::= { rcCfmL2TraceReplyEntry 5}

rcCfmL2TraceReplySrcMac OBJECT-TYPE
        SYNTAX          MacAddress
        MAX-ACCESS      read-only
        STATUS          current
        DESCRIPTION     
                "Mac address of the MP that respond to the L2Trace request for 
                this L2traceReply"  
        ::= { rcCfmL2TraceReplyEntry 6}

rcCfmL2TraceReplyHostName OBJECT-TYPE
	SYNTAX    OCTET STRING (SIZE (0..255))
	MAX-ACCESS      read-only
        STATUS          current
        DESCRIPTION     
                "The host name of the replying node"
	::= { rcCfmL2TraceReplyEntry 7}

rcCfmL2TraceReplyLastSrcMac OBJECT-TYPE
	SYNTAX          MacAddress
        MAX-ACCESS      read-only
        STATUS          current
        DESCRIPTION     
                "The MAC address of the node that forwarded the L2Trace to the responding node"
	::= { rcCfmL2TraceReplyEntry 8}
	
rcCfmL2TraceReplyLastHostName OBJECT-TYPE
	SYNTAX    OCTET STRING (SIZE (0..255))
	MAX-ACCESS      read-only
        STATUS          current
        DESCRIPTION     
                "The host name of the node that forwarded the L2Trace to the responding node"
	::= { rcCfmL2TraceReplyEntry 9}

-- The Transmit L2 Ip Ping Table

rcCfmTransmitL2IpPingTable OBJECT-TYPE
	SYNTAX		SEQUENCE OF RcCfmTransmitL2IpPingEntry
	MAX-ACCESS	not-accessible
	STATUS		current
	DESCRIPTION	"Connectivity Fault Management transmit L2IpPing table"
	::= { rcCfm 37}

rcCfmTransmitL2IpPingEntry OBJECT-TYPE
	SYNTAX		RcCfmTransmitL2IpPingEntry
	MAX-ACCESS	not-accessible
	STATUS		current
	DESCRIPTION	"L2IpPing entry."
	INDEX		{rcCfmTransmitL2IpPingIpAddrType,
                         rcCfmTransmitL2IpPingIpAddr}
	::= { rcCfmTransmitL2IpPingTable 1}

RcCfmTransmitL2IpPingEntry ::=
	SEQUENCE {
                rcCfmTransmitL2IpPingIpAddrType         InetAddressType,
                rcCfmTransmitL2IpPingIpAddr             InetAddress,
                rcCfmTransmitL2IpPingVrfId              Integer32,
                rcCfmTransmitL2IpPingVrfName            DisplayString,  
		rcCfmTransmitL2IpPingMessages		Integer32,
	        rcCfmTransmitL2IpPingTimeoutInt         Integer32,
	        rcCfmTransmitL2IpPingTestPattern        INTEGER,
	        rcCfmTransmitL2IpPingDataSize	        Integer32,
		rcCfmTransmitL2IpPingStatus		INTEGER,
		rcCfmTransmitL2IpPingResultOk		TruthValue,
                rcCfmTransmitL2IpPingPathsFound         Integer32,
                rcCfmTransmitL2IpPingRowStatus          RowStatus
 	}

rcCfmTransmitL2IpPingIpAddrType OBJECT-TYPE
        SYNTAX        InetAddressType
        MAX-ACCESS    not-accessible
        STATUS        current
        DESCRIPTION   "The address type of destination IP Address "
        ::= { rcCfmTransmitL2IpPingEntry 1 }

rcCfmTransmitL2IpPingIpAddr OBJECT-TYPE
        SYNTAX        InetAddress
        MAX-ACCESS    not-accessible
        STATUS        current
        DESCRIPTION   "Destination IP Address. Support ipv4 at this time"
        ::= { rcCfmTransmitL2IpPingEntry 2 }

rcCfmTransmitL2IpPingVrfId OBJECT-TYPE
        SYNTAX        Integer32
        MAX-ACCESS    read-only
        STATUS        current
        DESCRIPTION   "VRF ID "
        ::= { rcCfmTransmitL2IpPingEntry 3 }

rcCfmTransmitL2IpPingVrfName   OBJECT-TYPE
     SYNTAX         DisplayString (SIZE (0..64))
     MAX-ACCESS     read-only
     STATUS         current
     DESCRIPTION    "The Name of the Virtual Router"
        ::= {rcCfmTransmitL2IpPingEntry 4 }

rcCfmTransmitL2IpPingMessages  OBJECT-TYPE
	SYNTAX  	Integer32(1..200)
	MAX-ACCESS	read-create
	STATUS		current
	DESCRIPTION	"The number of L2IpPing messages to be transmitted 
                         per mac/vlan pair."               
	DEFVAL {1}
	::= { rcCfmTransmitL2IpPingEntry 5}

rcCfmTransmitL2IpPingTimeoutInt  OBJECT-TYPE
        SYNTAX          Integer32(1..10)
        MAX-ACCESS      read-create
        STATUS          current
        DESCRIPTION    "The interval to wait for an L2IpPing time-out with a 
                       range of (1..10)  seconds with a default value of 3 
                       seconds."
        DEFVAL {3}
        ::= { rcCfmTransmitL2IpPingEntry 6}

rcCfmTransmitL2IpPingTestPattern OBJECT-TYPE
        SYNTAX          INTEGER {
                               allZero(1),
                               allZeroCrc(2),
                               pseudoRandomBitSequence(3),
                               pseudoRandomBitSequenceCrc(4)
                        }
        MAX-ACCESS      read-create
        STATUS          current
        DESCRIPTION     "The test pattern to use in the L2IpPing PDUs 
                        with range of values namely allZero, allZeroCrc, 
                        pseudoRandomBitSequence and pseudoRandomBitSequenceCrc 
                        and with a default value of allZero.
                        value                  meaning
                        --------               -------
                        allZero(1)             Null signal without CRC-32
                        allZeroCrc(2)          Null signal with CRC-32    
                        pseudoRandomBitSequence(3) PRBS 1/2^31-1 without CRC-32
                        pseudoRandomBitSequenceCrc(4) PBRS 1/2^31-1 with CRC-32"
        DEFVAL {allZero}
        ::= { rcCfmTransmitL2IpPingEntry 7}

rcCfmTransmitL2IpPingDataSize  OBJECT-TYPE
	SYNTAX  	Integer32(0..400)
	MAX-ACCESS	read-create
	STATUS		current
	DESCRIPTION	"An arbitrary amount of data to be included in the 
                        data TLV, if the Data Size is selected to be sent."
	DEFVAL {0}
	::= { rcCfmTransmitL2IpPingEntry 8}

rcCfmTransmitL2IpPingStatus 	OBJECT-TYPE
	SYNTAX 		INTEGER {
				ready(1),
				transmit(2),
                                abort(3)
			}
	MAX-ACCESS	read-create
	STATUS		current
	DESCRIPTION	"Status of the transmit loopback service:
			-ready.      The service is available.
			-transmit.   The service is transmitting, or about to 
                                     transmit, the L2IpPing messages.
                        -abort       The service is aborted or about to abort 
                                     the L2IpPing messages.

			This column will also be used to avoid concurrency or 
                        race condition problems that could occur if two or 
                        more management entities try to 
			use the service at the same time. "
	REFERENCE       "Delete notReady status due to CR Q01482201"
	DEFVAL {ready}
	::= { rcCfmTransmitL2IpPingEntry 9}

rcCfmTransmitL2IpPingResultOk OBJECT-TYPE
	SYNTAX 		TruthValue
	MAX-ACCESS	read-only
	STATUS		current
	DESCRIPTION	"Indicates the result of the operation:
			-true.    L2IpPing Message(s) will be/have been sent.
			-false.   L2IpPing Message(s) will not be sent."
	DEFVAL {true}
	::= { rcCfmTransmitL2IpPingEntry 10}
	 
rcCfmTransmitL2IpPingPathsFound   OBJECT-TYPE
	SYNTAX  	Integer32
	MAX-ACCESS	read-only
	STATUS	        current 	
	DESCRIPTION	"The number of paths found to execute l2ping command"
        DEFVAL          { 0 }
	::= { rcCfmTransmitL2IpPingEntry 11}	

rcCfmTransmitL2IpPingRowStatus OBJECT-TYPE
        SYNTAX        RowStatus
        MAX-ACCESS    read-create
        STATUS        current
        DESCRIPTION   "Used to create/delete entries in the 
                       rcCfmTransmitL2IpPingTable. Deletion of an entry
                       in this table results in corresponding
                       rcCfmL2IpPingReplyTable entries being deleted."
        ::= { rcCfmTransmitL2IpPingEntry 12 }

-- L2 Ip Ping Reply Table

rcCfmL2IpPingReplyTable OBJECT-TYPE
        SYNTAX          SEQUENCE OF RcCfmL2IpPingReplyEntry
        MAX-ACCESS      not-accessible
        STATUS          current 
        DESCRIPTION     
                "This table contains a list of l2 ip ping replies received "
        ::= { rcCfm 38}

rcCfmL2IpPingReplyEntry OBJECT-TYPE
        SYNTAX          RcCfmL2IpPingReplyEntry
        MAX-ACCESS      not-accessible
        STATUS          current
        DESCRIPTION     "The L2 Ip Ping Reply table entry."
        INDEX           {rcCfmL2IpPingReplyIpAddrType,
                         rcCfmL2IpPingReplyIpAddr,
                         rcCfmL2IpPingReplySendOrder}
        ::= { rcCfmL2IpPingReplyTable 1}
    
RcCfmL2IpPingReplyEntry ::=
        SEQUENCE {
                rcCfmL2IpPingReplyIpAddrType            InetAddressType,
                rcCfmL2IpPingReplyIpAddr                InetAddress,
                rcCfmL2IpPingReplySendOrder             Integer32,
                rcCfmL2IpPingReplyVrfId                 Integer32,
		rcCfmL2IpPingReplyVlanId                Integer32,
                rcCfmL2IpPingReplyDestMacAddress        MacAddress,
                rcCfmL2IpPingReplyPortNum               InterfaceIndex,
		rcCfmL2IpPingReplyDestHostName          OCTET STRING,
		rcCfmL2IpPingReplySize                  Integer32,
		rcCfmL2IpPingReplyPktsTx                Integer32,
		rcCfmL2IpPingReplyPktsRx                Integer32,
		rcCfmL2IpPingReplyPercentLossWhole      Integer32,	
		rcCfmL2IpPingReplyPercentLossFract      Integer32,	
                rcCfmL2IpPingReplyMinRoundTrip          Integer32,
                rcCfmL2IpPingReplyMaxRoundTrip          Integer32,
                rcCfmL2IpPingReplyRttAvgWhole           Integer32,
                rcCfmL2IpPingReplyRttAvgFract           Integer32,
                rcCfmL2IpPingReplyFlag                  INTEGER
             }

rcCfmL2IpPingReplyIpAddrType OBJECT-TYPE
        SYNTAX        InetAddressType
        MAX-ACCESS    not-accessible
        STATUS        current
        DESCRIPTION   "The address type of destination IP Address "
        ::= { rcCfmL2IpPingReplyEntry 1 }

rcCfmL2IpPingReplyIpAddr OBJECT-TYPE
        SYNTAX        InetAddress
        MAX-ACCESS    not-accessible
        STATUS        current
        DESCRIPTION   "Destination IP Address. Support ipv4 at this time"
        ::= { rcCfmL2IpPingReplyEntry 2 }

rcCfmL2IpPingReplySendOrder OBJECT-TYPE
        SYNTAX          Integer32 (0..2147483647)
        MAX-ACCESS      not-accessible
        STATUS          current
        DESCRIPTION     
                "An index to distinguish among multiple L2Ping sessions 
                This value is assigned sequentially from 1. It denotes
                order that sessions were sent. It correlates to the number
                of paths found and stored in the rcCfmTransmitL2IpPingEntry."
        ::= { rcCfmL2IpPingReplyEntry 3}

rcCfmL2IpPingReplyVrfId OBJECT-TYPE
        SYNTAX        Integer32
        MAX-ACCESS    read-only
        STATUS        current
        DESCRIPTION   "VRF ID "
        ::= { rcCfmL2IpPingReplyEntry 4 }

rcCfmL2IpPingReplyVlanId OBJECT-TYPE
	SYNTAX		Integer32 (1..4084)
	MAX-ACCESS	read-only
	STATUS		current
	DESCRIPTION	"Vlan found from L3 lookup and used for transmission"
	::= {rcCfmL2IpPingReplyEntry 5}

rcCfmL2IpPingReplyDestMacAddress OBJECT-TYPE
	SYNTAX		MacAddress
	MAX-ACCESS	read-only
	STATUS		current
	DESCRIPTION	"An indication of the target MAC Address transmitted"
	::= { rcCfmL2IpPingReplyEntry 6}

rcCfmL2IpPingReplyPortNum OBJECT-TYPE
        SYNTAX          InterfaceIndex
        MAX-ACCESS      read-only
        STATUS          current
        DESCRIPTION     "Either the value '0', or the port number of the
                        port used for the l2ping.  "
        ::= { rcCfmL2IpPingReplyEntry 7 }

rcCfmL2IpPingReplyDestHostName OBJECT-TYPE
	SYNTAX    OCTET STRING (SIZE (0..255))
	MAX-ACCESS      read-only
        STATUS          current
        DESCRIPTION     
                "The host name of the responding node"
	::= { rcCfmL2IpPingReplyEntry 8}

rcCfmL2IpPingReplySize OBJECT-TYPE
        SYNTAX          Integer32 (0..9600)  
        MAX-ACCESS      read-only
        STATUS          current
        DESCRIPTION     
                "The number of bytes of data sent"
        DEFVAL {0}
        ::= { rcCfmL2IpPingReplyEntry 9}

rcCfmL2IpPingReplyPktsTx     OBJECT-TYPE
        SYNTAX          Integer32 
        MAX-ACCESS      read-only
        STATUS          current
        DESCRIPTION     "Number of Packets transmitted for this vlan/mac"
        ::= { rcCfmL2IpPingReplyEntry 10}

rcCfmL2IpPingReplyPktsRx     OBJECT-TYPE
        SYNTAX          Integer32 
        MAX-ACCESS      read-only
        STATUS          current
        DESCRIPTION     "Number of Packets received for this vlan/mac"
        ::= { rcCfmL2IpPingReplyEntry 11}

rcCfmL2IpPingReplyPercentLossWhole     OBJECT-TYPE
        SYNTAX          Integer32 (0..100) 
        MAX-ACCESS      read-only
        STATUS          current
        DESCRIPTION     "Percentage of packet loss for this vlan/mac"
        ::= { rcCfmL2IpPingReplyEntry 12}

rcCfmL2IpPingReplyPercentLossFract     OBJECT-TYPE
        SYNTAX          Integer32 (0..100) 
        MAX-ACCESS      read-only
        STATUS          current
        DESCRIPTION     "Percentage of packet loss for this vlan/mac"
        ::= { rcCfmL2IpPingReplyEntry 13}

rcCfmL2IpPingReplyMinRoundTrip    OBJECT-TYPE
        SYNTAX          Integer32  
        MAX-ACCESS      read-only
        STATUS          current
        DESCRIPTION     "Min time for round-trip for this vlan/mac in us"
        ::= { rcCfmL2IpPingReplyEntry 14}

rcCfmL2IpPingReplyMaxRoundTrip    OBJECT-TYPE
        SYNTAX          Integer32  
        MAX-ACCESS      read-only
        STATUS          current
        DESCRIPTION     "Max time for round-trip for this vlan/mac in us"
        ::= { rcCfmL2IpPingReplyEntry 15}

rcCfmL2IpPingReplyRttAvgWhole    OBJECT-TYPE
        SYNTAX          Integer32  
        MAX-ACCESS      read-only
        STATUS          current
        DESCRIPTION     "Average time for round-trip for this vlan/mac in us"
        ::= { rcCfmL2IpPingReplyEntry 16}

rcCfmL2IpPingReplyRttAvgFract    OBJECT-TYPE
        SYNTAX          Integer32  
        MAX-ACCESS      read-only
        STATUS          current
        DESCRIPTION     "Fractional portion of Average time for round-trip"
        ::= { rcCfmL2IpPingReplyEntry 17}

rcCfmL2IpPingReplyFlag     OBJECT-TYPE
	SYNTAX 		INTEGER {
				none(1),
				internalError(2),
                                invalidMac(3),
                                mepDisabled(4), 
                                invalidMD(5),
                                invalidMA(6),
			        noMepFound(7),
                                unknownServiceInstance(8),
                                l2PingToOwnMepMac(9),
                                l2PingComplete(10)
			}
	MAX-ACCESS	read-only
	STATUS	        current 	
	DESCRIPTION	"Result flag indicating status or error code. 
                         Each enum value represents a status or error case.  
                         1 - No error  
                         2 - Internal Error
                         3 - Invalid Ip
                         4 - L2Trace completed
			 5 - Lookup failure for IP (no vlan/mac entries)"
        ::= { rcCfmL2IpPingReplyEntry 18}

-- The Transmit L2 Ip Trace Table
rcCfmTransmitL2IpTraceTable OBJECT-TYPE
	SYNTAX		SEQUENCE OF RcCfmTransmitL2IpTraceEntry
	MAX-ACCESS	not-accessible
	STATUS		current
	DESCRIPTION	"Connectivity Fault Management transmit L2IpTrace table"
	::= { rcCfm 39}

rcCfmTransmitL2IpTraceEntry OBJECT-TYPE
	SYNTAX		RcCfmTransmitL2IpTraceEntry
	MAX-ACCESS	not-accessible
	STATUS		current
	DESCRIPTION	"L2IpTrace entry."
	INDEX		{rcCfmTransmitL2IpTraceIpAddrType,
                         rcCfmTransmitL2IpTraceIpAddr }
	::= { rcCfmTransmitL2IpTraceTable 1}

RcCfmTransmitL2IpTraceEntry ::=
	SEQUENCE {
                rcCfmTransmitL2IpTraceIpAddrType        InetAddressType,
                rcCfmTransmitL2IpTraceIpAddr            InetAddress,
                rcCfmTransmitL2IpTraceVrfId             Integer32,
                rcCfmTransmitL2IpTraceVrfName           DisplayString,  
		rcCfmTransmitL2IpTraceTtl 	        Integer32,
		rcCfmTransmitL2IpTraceStatus		INTEGER,
		rcCfmTransmitL2IpTraceResultOk		TruthValue,
                rcCfmTransmitL2IpTracePathsFound        Integer32,
                rcCfmTransmitL2IpTraceRowStatus         RowStatus
	}

rcCfmTransmitL2IpTraceIpAddrType OBJECT-TYPE
        SYNTAX        InetAddressType
        MAX-ACCESS    not-accessible
        STATUS        current
        DESCRIPTION   "The address type of destination IP Address "
        ::= { rcCfmTransmitL2IpTraceEntry 1 }

rcCfmTransmitL2IpTraceIpAddr OBJECT-TYPE
        SYNTAX        InetAddress 
        MAX-ACCESS    not-accessible
        STATUS        current
        DESCRIPTION   "Destination IP Address. Support ipv4 at this time"
        ::= { rcCfmTransmitL2IpTraceEntry 2 }

rcCfmTransmitL2IpTraceVrfId OBJECT-TYPE
        SYNTAX        Integer32
        MAX-ACCESS    read-only
        STATUS        current
        DESCRIPTION   "VRF ID "
        ::= { rcCfmTransmitL2IpTraceEntry 3 }

rcCfmTransmitL2IpTraceVrfName   OBJECT-TYPE
     SYNTAX         DisplayString (SIZE (0..64))
     MAX-ACCESS     read-only
     STATUS         current
     DESCRIPTION    "The Name of the Virtual Router"
        ::= {rcCfmTransmitL2IpTraceEntry 4 }

rcCfmTransmitL2IpTraceTtl     OBJECT-TYPE
	SYNTAX  	Integer32(0..255)
	MAX-ACCESS	read-create
	STATUS		current
	DESCRIPTION	"The number of hops remaining to this L2Trace. 
			 Decremented by 1 by each Bridge that handles the L2Trace. 
			 The decremented value is returned in the L2Trace. If 0 
                         on output, the L2Trace is not transmitted to the next 
                         hop. The value of the TTL Field in the L2Trace
                         transmitted by the originating MEP is controlled by a 
                         Managed Object; The default value if none is 
                         specified is 64."
	DEFVAL {64}
	::= { rcCfmTransmitL2IpTraceEntry 5}

rcCfmTransmitL2IpTraceStatus 	OBJECT-TYPE
	SYNTAX 		INTEGER {
				ready(1),
				transmit(2),
                                abort(3)
			}
	MAX-ACCESS	read-create
	STATUS		current
	DESCRIPTION	"Status of the transmit loopback service:
			-ready.      The service is available.
			-transmit.   The service is transmitting, or about to 
                                     transmit, the L2Trace messages.
                        -abort       The service is aborted or about to abort 
                                     the L2Trace messages.

			This column will also be used to avoid concurrency or 
                        race condition problems that could occur if two or 
                        more management entities try to 
			use the service at the same time. "
	REFERENCE       "Delete notReady status due to CR Q01482201"
	DEFVAL {ready}
	::= { rcCfmTransmitL2IpTraceEntry 6}

rcCfmTransmitL2IpTraceResultOk OBJECT-TYPE
	SYNTAX 		TruthValue
	MAX-ACCESS	read-only
	STATUS		current
	DESCRIPTION	"Indicates the result of the operation:
			-true.    The Trace Message(s) will be/have been sent.
			-false.   The Trace Message(s) will not be sent."
	DEFVAL {true}
	::= { rcCfmTransmitL2IpTraceEntry 7}
	
rcCfmTransmitL2IpTracePathsFound   OBJECT-TYPE
	SYNTAX  	Integer32
	MAX-ACCESS	read-only
	STATUS	        current 	
	DESCRIPTION	"The number of paths found to execute l2trace command"
        DEFVAL          { 0 }
	::= { rcCfmTransmitL2IpTraceEntry 8}	

rcCfmTransmitL2IpTraceRowStatus OBJECT-TYPE
        SYNTAX        RowStatus
        MAX-ACCESS    read-create
        STATUS        current
        DESCRIPTION   "Used to create/delete entries in the 
                       rcCfmTransmitL2IpTraceTable. Deletion of an entry
                       in this table results in corresponding
                       rcCfmL2IpTraceReplyTable entries being deleted."
        ::= { rcCfmTransmitL2IpTraceEntry 9 }

 
-- L2IpTrace Reply Table

rcCfmL2IpTraceReplyTable OBJECT-TYPE
        SYNTAX          SEQUENCE OF RcCfmL2IpTraceReplyEntry
        MAX-ACCESS      not-accessible
        STATUS          current 
        DESCRIPTION     
                "This table contains a list of l2 ip trace replies received 
                by a specific MEP in response to a linktrace message."
        ::= { rcCfm 40}

rcCfmL2IpTraceReplyEntry OBJECT-TYPE
        SYNTAX          RcCfmL2IpTraceReplyEntry
        MAX-ACCESS      not-accessible
        STATUS          current
        DESCRIPTION     "The L2 Ip Trace Reply table entry."
        INDEX           {rcCfmL2IpTraceReplyIpAddrType,
                         rcCfmL2IpTraceReplyIpAddr,
                         rcCfmL2IpTraceReplySendOrder,
                         rcCfmL2IpTraceReplyHop,
                         rcCfmL2IpTraceReplyReceiveOrder}
        ::= { rcCfmL2IpTraceReplyTable 1}
    
RcCfmL2IpTraceReplyEntry ::=
        SEQUENCE {
                rcCfmL2IpTraceReplyIpAddrType          InetAddressType,
                rcCfmL2IpTraceReplyIpAddr              InetAddress,
                rcCfmL2IpTraceReplySendOrder           Integer32,
		rcCfmL2IpTraceReplyHop                 Integer32,	
                rcCfmL2IpTraceReplyReceiveOrder        Integer32,
		rcCfmL2IpTraceReplyTtl                 Integer32,	
                rcCfmL2IpTraceReplyVrfId               Integer32,
		rcCfmL2IpTraceReplyVlanId	       Integer32,
                rcCfmL2IpTraceReplyDestMacAddress      MacAddress,
                rcCfmL2IpTraceReplyPortNum             InterfaceIndex,
		rcCfmL2IpTraceReplySeqNumber	       Integer32,
                rcCfmL2IpTraceReplySrcMac              MacAddress,
		rcCfmL2IpTraceReplyHostName            OCTET STRING,
		rcCfmL2IpTraceReplyLastSrcMac          MacAddress,
		rcCfmL2IpTraceReplyLastHostName        OCTET STRING,
                rcCfmL2IpTraceReplyFlag                INTEGER
             }

rcCfmL2IpTraceReplyIpAddrType OBJECT-TYPE
        SYNTAX        InetAddressType
        MAX-ACCESS    not-accessible
        STATUS        current
        DESCRIPTION   "The address type of destination IP Address "
        ::= { rcCfmL2IpTraceReplyEntry 1 }

rcCfmL2IpTraceReplyIpAddr OBJECT-TYPE
        SYNTAX        InetAddress 
        MAX-ACCESS    not-accessible
        STATUS        current
        DESCRIPTION   "Destination IP Address. Support ipv4 at this time"
        ::= { rcCfmL2IpTraceReplyEntry 2 }

rcCfmL2IpTraceReplySendOrder OBJECT-TYPE
        SYNTAX          Integer32 (0..2147483647)
        MAX-ACCESS      not-accessible
        STATUS          current
        DESCRIPTION     
                "An index to distinguish among multiple L2Trace sessions 
                This value is assigned sequentially from 1. It denotes
                order that sessions were sent. It correlates to the number
                of paths found and stored in the rcCfmTransmitL2IpTraceEntry."
        ::= { rcCfmL2IpTraceReplyEntry 3}

rcCfmL2IpTraceReplyHop     OBJECT-TYPE
        SYNTAX          Integer32 (0..255)
        MAX-ACCESS      not-accessible
        STATUS          current
        DESCRIPTION     "The number of L2 hops away from L2Trace initiator."
        ::= { rcCfmL2IpTraceReplyEntry 4}

rcCfmL2IpTraceReplyReceiveOrder OBJECT-TYPE
        SYNTAX          Integer32 (0..2147483647)
        MAX-ACCESS      not-accessible
        STATUS          current
        DESCRIPTION     
                "An index to distinguish among multiple L2Trace responses 
                with the same Send Transaction Identifier field  value. 
                This value is assigned sequentially from 1, in the order 
                that the Linktrace Initiator received the responses. A
                zero value may be seen in error conditions"
        ::= { rcCfmL2IpTraceReplyEntry 5}

rcCfmL2IpTraceReplyTtl     OBJECT-TYPE
        SYNTAX          Integer32 (0..255)
        MAX-ACCESS      read-only
        STATUS          current
        DESCRIPTION     "Ttl field value for a returned L2Trace response."
        ::= { rcCfmL2IpTraceReplyEntry 6}

rcCfmL2IpTraceReplyVrfId OBJECT-TYPE
        SYNTAX        Integer32
        MAX-ACCESS    read-only
        STATUS        current
        DESCRIPTION   "VRF ID "
        ::= { rcCfmL2IpTraceReplyEntry 7}

rcCfmL2IpTraceReplyVlanId OBJECT-TYPE
	SYNTAX		Integer32 (1..4084)
	MAX-ACCESS	read-only
	STATUS		current
	DESCRIPTION	"Vlan found from L3 lookup and used for transmission"
	::= {rcCfmL2IpTraceReplyEntry 8}

rcCfmL2IpTraceReplyDestMacAddress OBJECT-TYPE
	SYNTAX		MacAddress
	MAX-ACCESS	read-only
	STATUS		current
	DESCRIPTION	"An indication of the target MAC Address transmitted"
	::= { rcCfmL2IpTraceReplyEntry 9}

rcCfmL2IpTraceReplySeqNumber OBJECT-TYPE
        SYNTAX          Integer32 (0..2147483647)  
        MAX-ACCESS      read-only
        STATUS          current
        DESCRIPTION     
                "The transaction identifier/sequence number used in  
                linktrace message packet"
        DEFVAL {0}
        ::= { rcCfmL2IpTraceReplyEntry 10}

rcCfmL2IpTraceReplyPortNum OBJECT-TYPE
        SYNTAX          InterfaceIndex
        MAX-ACCESS      read-only
        STATUS          current
        DESCRIPTION     "Either the value '0', or the port number of the
                        port used for the l2trace.  "
        ::= { rcCfmL2IpTraceReplyEntry 11 }

rcCfmL2IpTraceReplySrcMac OBJECT-TYPE
        SYNTAX          MacAddress
        MAX-ACCESS      read-only
        STATUS          current
        DESCRIPTION     
                "Mac address of the MP that responded to L2Trace request for 
                this L2traceReply"  
        ::= { rcCfmL2IpTraceReplyEntry 12}

rcCfmL2IpTraceReplyHostName OBJECT-TYPE
	SYNTAX    OCTET STRING (SIZE (0..255))
	MAX-ACCESS      read-only
        STATUS          current
        DESCRIPTION     
                "The host name of the replying node"
	::= { rcCfmL2IpTraceReplyEntry 13}

rcCfmL2IpTraceReplyLastSrcMac OBJECT-TYPE
	SYNTAX          MacAddress
        MAX-ACCESS      read-only
        STATUS          current
        DESCRIPTION     
                "The MAC address of the node that forwarded the 
                L2Trace to the responding node"
	::= { rcCfmL2IpTraceReplyEntry 14}
	
rcCfmL2IpTraceReplyLastHostName OBJECT-TYPE
	SYNTAX    OCTET STRING (SIZE (0..255))
	MAX-ACCESS      read-only
        STATUS          current
        DESCRIPTION     
                "The host name of the node that forwarded the L2Trace 
                to the responding node"
	::= { rcCfmL2IpTraceReplyEntry 15}

rcCfmL2IpTraceReplyFlag    OBJECT-TYPE
	SYNTAX 		INTEGER {
				none(1),
				internalError(2),
                                invalidMac(3),
                                mepDisabled(4), 
                                noL2TraceResponse(5),
                                l2TraceToOwnMepMac(6),
                                l2TraceComplete(7),
			        l2TraceLookupFailure(8)
			}
	MAX-ACCESS	read-only
	STATUS	        current 	
	DESCRIPTION	"L2Trace result flag indicating status or error code. 
                         Each enum value represents a status or error case.  
                         1 - No error  
                         2 - L2Trace Internal Error
                         3 - Invalid Mac Address
                         4 - Mep must be enabled in order to perform L2Trace
                         5 - No L2Trace response received
                         6 - L2Trace to own Mep MAC is not sent
                         7 - L2Trace completed
			 8 - Lookup failure for L2Trace"

	::= { rcCfmL2IpTraceReplyEntry 16}	 

END
