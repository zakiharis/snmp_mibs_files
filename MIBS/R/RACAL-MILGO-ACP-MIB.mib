RACAL-MILGO-ACP-MIB

DEFINITIONS ::= BEGIN
IMPORTS
	OBJECT-TYPE, NetworkAddress, IpAddress,
	Counter, Gauge, TimeTicks
		FROM RFC1155-SMI;


internet        OBJECT IDENTIFIER ::= { iso org(3) dod(6) 1 }
experimental    OBJECT IDENTIFIER ::= { internet 3 }
private         OBJECT IDENTIFIER ::= { internet 4 }

enterprises     OBJECT IDENTIFIER ::= { private 1 }


     mib-racal-milgo        OBJECT IDENTIFIER ::= { enterprises 124 }

     rmAcp                  OBJECT IDENTIFIER ::= { mib-racal-milgo 2 }

     acpSys                 OBJECT IDENTIFIER ::= { rmAcp 1 }
     acpComPort             OBJECT IDENTIFIER ::= { rmAcp 2 }
     acpEnetPort            OBJECT IDENTIFIER ::= { rmAcp 3 }
     acpWanPort             OBJECT IDENTIFIER ::= { rmAcp 4 }
     acpMesh                OBJECT IDENTIFIER ::= { rmAcp 5 }
     acpTb                  OBJECT IDENTIFIER ::= { rmAcp 6 }



     -- The ACP System Group

     acpSysNodeId OBJECT-TYPE 
          SYNTAX  OCTET STRING
          ACCESS  read-only
          STATUS  mandatory
DESCRIPTION ""
		--% GROUP acpSys
          ::= { acpSys 1 }


     acpSysAlarm OBJECT-TYPE 
          SYNTAX  OCTET STRING
          ACCESS  read-only
          STATUS  mandatory
DESCRIPTION ""
		--% GROUP acpSys
          ::= { acpSys 2 }


     acpSysModTable OBJECT-TYPE 
          SYNTAX  SEQUENCE OF AcpSysModEntry
          ACCESS  not-accessible
          STATUS  mandatory
DESCRIPTION ""
          ::= { acpSys 3 }


     acpSysModEntry OBJECT-TYPE 
          SYNTAX  AcpSysModEntry
          ACCESS  not-accessible
          STATUS  mandatory
DESCRIPTION ""
	  INDEX { acpSysModType }
          ::= { acpSysModTable 1 }


     AcpSysModEntry ::= SEQUENCE {
          acpSysModType
               INTEGER,
          acpSysModStatus
               INTEGER,
          acpSysModSwVersion
               OCTET STRING,
          acpSysModSwDate
               OCTET STRING,
          acpSysModSwComment
               OCTET STRING,
          acpSysModFrontIdProm
               OCTET STRING,
          acpSysModRearIdProm
               OCTET STRING
     }



     acpSysModType OBJECT-TYPE 
          SYNTAX  INTEGER {
                      none(1),
                      iopLan(2),
                      iopWan(3),
                      iopHyb(4),
                      iop(5), 
                      me(6),    
                      nam(7)  
                  }
          ACCESS  read-only
          STATUS  mandatory
DESCRIPTION ""
		--% GROUP acpSysModEntry
          ::= { acpSysModEntry 1 }

     acpSysModStatus OBJECT-TYPE 
          SYNTAX  INTEGER {
                      reset(1),
                      noHardware(2),
                      diag(3),
                      failed(4),
                      loading(5),
                      loaded(6),
                      config(7),
                      onLine(8),
                      disabled(9)
                  }
          ACCESS  read-only
          STATUS  mandatory
DESCRIPTION ""
		--% GROUP acpSysModEntry
          ::= { acpSysModEntry 2 }

     acpSysModSwVersion OBJECT-TYPE 
          SYNTAX  OCTET STRING
          ACCESS  read-only
          STATUS  mandatory
DESCRIPTION ""
		--% GROUP acpSysModEntry
          ::= { acpSysModEntry 3 }

     acpSysModSwDate OBJECT-TYPE 
          SYNTAX  OCTET STRING
          ACCESS  read-only
          STATUS  mandatory
DESCRIPTION ""
		--% GROUP acpSysModEntry
          ::= { acpSysModEntry 4 }

     acpSysModSwComment OBJECT-TYPE 
          SYNTAX  OCTET STRING
          ACCESS  read-only
          STATUS  mandatory
DESCRIPTION ""
		--% GROUP acpSysModEntry
          ::= { acpSysModEntry 5 }

     acpSysModFrontIdProm OBJECT-TYPE 
          SYNTAX  OCTET STRING
          ACCESS  read-only
          STATUS  mandatory
DESCRIPTION ""
		--% GROUP acpSysModEntry
          ::= { acpSysModEntry 6 }

     acpSysModRearIdProm OBJECT-TYPE 
          SYNTAX  OCTET STRING
          ACCESS  read-only
          STATUS  mandatory
DESCRIPTION ""
		--% GROUP acpSysModEntry
          ::= { acpSysModEntry 7 }


     -- The ACP Common Port Group


     acpComPortTable OBJECT-TYPE 
          SYNTAX  SEQUENCE OF AcpComPortEntry
          ACCESS  not-accessible
          STATUS  mandatory
DESCRIPTION ""
          ::= { acpComPort 1 }


     acpComPortEntry OBJECT-TYPE 
          SYNTAX  AcpComPortEntry
          ACCESS  not-accessible
          STATUS  mandatory
	  DESCRIPTION " "
	  INDEX	{ ifIndex }
          ::= { acpComPortTable 1 }


      AcpComPortEntry ::= SEQUENCE {
          acpComQtimer
               INTEGER,
          acpComCongTimer
               INTEGER,
          acpComErrMax
               INTEGER,
          acpComPortRxPktsAcp
               Counter,
          acpComPortRxPktsKnown
               Counter,
          acpComPortRxPktsUnk
               Counter,
          acpComPortRxOutcomeFilIop
               Counter,
          acpComPortTxPktsAcp
               Counter,
          acpComPortTxPktsKnown
               Counter,
          acpComPortTxPktsUnk
               Counter,
          acpComPortRxOutcomeFwd
               Counter,
          acpComPortRxOutcomeFilLcl
               Counter,
          acpComPortRxOutcomeFilNf
               Counter,
          acpComPortRxOutcomeFilSrc
               Counter,
          acpComPortRxOutcomeFilDest
               Counter,
          acpComPortRxFilterChars
               Counter,
          acpComPortRxSizeErr
               Counter,
          acpComPortRxCrcErr
               Counter,
          acpComPortRxFrmErr
               Counter,
          acpComPortNzRxUtil
               Counter,
          acpComPortNzTxUtil
               Counter
     }



     acpComPortQtimer OBJECT-TYPE 
          SYNTAX  INTEGER
          ACCESS  read-only
          STATUS  mandatory
DESCRIPTION ""
		--% GROUP acpComPortEntry
          ::= { acpComPortEntry 1 }


     acpComPortCongTimer OBJECT-TYPE 
          SYNTAX  INTEGER
          ACCESS  read-only
          STATUS  mandatory
DESCRIPTION ""
		--% GROUP acpComPortEntry
          ::= { acpComPortEntry 2 }


     acpComPortErrMax OBJECT-TYPE 
          SYNTAX  INTEGER
          ACCESS  read-only
          STATUS  mandatory
DESCRIPTION ""
		--% GROUP acpComPortEntry
          ::= { acpComPortEntry 3 }


     acpComPortRxPktsAcp OBJECT-TYPE 
          SYNTAX  Counter
          ACCESS  read-only
          STATUS  mandatory
DESCRIPTION ""
		--% GROUP acpComPortEntry
          ::= { acpComPortEntry 4 }


     acpComPortRxPktsKnown OBJECT-TYPE 
          SYNTAX  Counter
          ACCESS  read-only
          STATUS  mandatory
DESCRIPTION ""
		--% GROUP acpComPortEntry
          ::= { acpComPortEntry 5 }


     acpComPortRxPktsUnk OBJECT-TYPE 
          SYNTAX  Counter
          ACCESS  read-only
          STATUS  mandatory
DESCRIPTION ""
		--% GROUP acpComPortEntry
          ::= { acpComPortEntry 6 }


     acpComPortRxOutcomeFilIop OBJECT-TYPE 
          SYNTAX  Counter
          ACCESS  read-only
          STATUS  mandatory
DESCRIPTION ""
		--% GROUP acpComPortEntry
          ::= { acpComPortEntry 7 }

     acpComPortTxPktsAcp OBJECT-TYPE 
          SYNTAX  Counter
          ACCESS  read-only
          STATUS  mandatory
DESCRIPTION ""
		--% GROUP acpComPortEntry
          ::= { acpComPortEntry 8 }


     acpComPortTxPktsKnown OBJECT-TYPE 
          SYNTAX  Counter
          ACCESS  read-only
          STATUS  mandatory
DESCRIPTION ""
		--% GROUP acpComPortEntry
          ::= { acpComPortEntry 9 }


     acpComPortTxPktsUnk OBJECT-TYPE 
          SYNTAX  Counter
          ACCESS  read-only
          STATUS  mandatory
DESCRIPTION ""
		--% GROUP acpComPortEntry
          ::= { acpComPortEntry 10 }


     acpComPortRxOutcomeFwd OBJECT-TYPE 
          SYNTAX  Counter
          ACCESS  read-only
          STATUS  mandatory
DESCRIPTION ""
		--% GROUP acpComPortEntry
          ::= { acpComPortEntry 11 }


     acpComPortRxOutcomeFilLcl OBJECT-TYPE 
          SYNTAX  Counter
          ACCESS  read-only
          STATUS  mandatory
DESCRIPTION ""
		--% GROUP acpComPortEntry
          ::= { acpComPortEntry 12 }


     acpComPortRxOutcomeFilNf OBJECT-TYPE 
          SYNTAX  Counter
          ACCESS  read-only
          STATUS  mandatory
DESCRIPTION ""
		--% GROUP acpComPortEntry
          ::= { acpComPortEntry 13 }


     acpComPortRxOutcomeFilSrc OBJECT-TYPE 
          SYNTAX  Counter
          ACCESS  read-only
          STATUS  mandatory
DESCRIPTION ""
		--% GROUP acpComPortEntry
          ::= { acpComPortEntry 14 }


     acpComPortRxOutcomeFilDest OBJECT-TYPE 
          SYNTAX  Counter
          ACCESS  read-only
          STATUS  mandatory
DESCRIPTION ""
		--% GROUP acpComPortEntry
          ::= { acpComPortEntry 15 }


     acpComPortRxFilterChars OBJECT-TYPE 
          SYNTAX  Counter
          ACCESS  read-only
          STATUS  mandatory
DESCRIPTION ""
		--% GROUP acpComPortEntry
          ::= { acpComPortEntry 16 }


     acpComPortRxSizeErr OBJECT-TYPE 
          SYNTAX  Counter
          ACCESS  read-only
          STATUS  mandatory
DESCRIPTION ""
		--% GROUP acpComPortEntry
          ::= { acpComPortEntry 17 }


     acpComPortRxCrcErr OBJECT-TYPE 
          SYNTAX  Counter
          ACCESS  read-only
          STATUS  mandatory
DESCRIPTION ""
		--% GROUP acpComPortEntry
          ::= { acpComPortEntry 18 }


     acpComPortRxFrmErr OBJECT-TYPE 
          SYNTAX  Counter
          ACCESS  read-only
          STATUS  mandatory
DESCRIPTION ""
		--% GROUP acpComPortEntry
          ::= { acpComPortEntry 19 }


     acpComPortNzRxUtil OBJECT-TYPE 
          SYNTAX  Counter
          ACCESS  read-only
          STATUS  mandatory
DESCRIPTION ""
		--% GROUP acpComPortEntry
          ::= { acpComPortEntry 20 }


     acpComPortNzTxUtil OBJECT-TYPE 
          SYNTAX  Counter
          ACCESS  read-only
          STATUS  mandatory
DESCRIPTION ""
		--% GROUP acpComPortEntry
          ::= { acpComPortEntry 21 }


     -- The ACP Ethernet Port Group

     acpEnetPortTable OBJECT-TYPE 
          SYNTAX  SEQUENCE OF AcpEnetPortEntry
          ACCESS  not-accessible
          STATUS  mandatory
DESCRIPTION ""
          ::= { acpEnetPort 1 }


     acpEnetPortEntry OBJECT-TYPE 
          SYNTAX  AcpEnetPortEntry
          ACCESS  not-accessible
          STATUS  mandatory
DESCRIPTION ""
	  INDEX { acpEnetPortIgnoreHeartbeat }
          ::= { acpEnetPortTable 1 }


     AcpEnetPortEntry ::= SEQUENCE {
          acpEnetPortIgnoreHeartbeat
               INTEGER,
          acpEnetPortRxFewDescr
               Counter,
          acpEnetPortRxNoDescr
               Counter,
          acpEnetPortRxOflo
               Counter,
          acpEnetPortTxDevMem
               Counter,
          acpEnetPortTxEnp
               Counter,
          acpEnetPortTxDevInvRead
               Counter,
          acpEnetPortTx16Coll
               Counter,
          acpEnetPortTxMissHeart
               Counter,
          acpEnetPortTxDfr
               Counter,
          acpEnetPortTxOneColl
               Counter,
          acpEnetPortTxMulColl
               Counter,
          acpEnetPortTxLate
               Counter,
          acpEnetPortTxTdr
               Counter,
          acpEnetPortLanUtil
               Counter,
          acpEnetPortRxBrRat
               Counter,
          acpEnetPortTxBrRat
               Counter
     }


     acpEnetPortIgnoreHeartbeat OBJECT-TYPE 
          SYNTAX  INTEGER {
                      no(1),
                      yes(2)
                  }
          ACCESS  read-only
          STATUS  mandatory
DESCRIPTION ""
		--% GROUP acpEnetPortEntry
          ::= { acpEnetPortEntry 1 }


     acpEnetPortRxFewDescr OBJECT-TYPE 
          SYNTAX  Counter
          ACCESS  read-only
          STATUS  mandatory
DESCRIPTION ""
		--% GROUP acpEnetPortEntry
          ::= { acpEnetPortEntry 2 }


     acpEnetPortRxNoDescr OBJECT-TYPE 
          SYNTAX  Counter
          ACCESS  read-only
          STATUS  mandatory
DESCRIPTION ""
		--% GROUP acpEnetPortEntry
          ::= { acpEnetPortEntry 3 }


     acpEnetPortRxOflo OBJECT-TYPE 
          SYNTAX  Counter
          ACCESS  read-only
          STATUS  mandatory
DESCRIPTION ""
		--% GROUP acpEnetPortEntry
          ::= { acpEnetPortEntry 4 }


     acpEnetPortTxDevMem OBJECT-TYPE 
          SYNTAX  Counter
          ACCESS  read-only
          STATUS  mandatory
DESCRIPTION ""
		--% GROUP acpEnetPortEntry
          ::= { acpEnetPortEntry 5 }


     acpEnetPortTxEnp OBJECT-TYPE 
          SYNTAX  Counter
          ACCESS  read-only
          STATUS  mandatory
DESCRIPTION ""
		--% GROUP acpEnetPortEntry
          ::= { acpEnetPortEntry 6 }


     acpEnetPortTxDevInvRead OBJECT-TYPE 
          SYNTAX  Counter
          ACCESS  read-only
          STATUS  mandatory
DESCRIPTION ""
		--% GROUP acpEnetPortEntry
          ::= { acpEnetPortEntry 7 }


     acpEnetPortTx16Coll OBJECT-TYPE 
          SYNTAX  Counter
          ACCESS  read-only
          STATUS  mandatory
DESCRIPTION ""
		--% GROUP acpEnetPortEntry
          ::= { acpEnetPortEntry 8 }


     acpEnetPortTxMissHeart OBJECT-TYPE 
          SYNTAX  Counter
          ACCESS  read-only
          STATUS  mandatory
DESCRIPTION ""
		--% GROUP acpEnetPortEntry
          ::= { acpEnetPortEntry 9 }


     acpEnetPortTxDfr OBJECT-TYPE 
          SYNTAX  Counter
          ACCESS  read-only
          STATUS  mandatory
DESCRIPTION ""
		--% GROUP acpEnetPortEntry
          ::= { acpEnetPortEntry 10 }


     acpEnetPortTxOneColl OBJECT-TYPE 
          SYNTAX  Counter
          ACCESS  read-only
          STATUS  mandatory
DESCRIPTION ""
		--% GROUP acpEnetPortEntry
          ::= { acpEnetPortEntry 11 }


     acpEnetPortTxMulColl OBJECT-TYPE 
          SYNTAX  Counter
          ACCESS  read-only
          STATUS  mandatory
DESCRIPTION ""
		--% GROUP acpEnetPortEntry
          ::= { acpEnetPortEntry 12 }


     acpEnetPortTxLate OBJECT-TYPE 
          SYNTAX  Counter
          ACCESS  read-only
          STATUS  mandatory
DESCRIPTION ""
		--% GROUP acpEnetPortEntry
          ::= { acpEnetPortEntry 13 }


     acpEnetPortTxTdr OBJECT-TYPE 
          SYNTAX  Counter
          ACCESS  read-only
          STATUS  mandatory
DESCRIPTION ""
		--% GROUP acpEnetPortEntry
          ::= { acpEnetPortEntry 14 }


     acpEnetPortLanUtil OBJECT-TYPE 
          SYNTAX  Counter
          ACCESS  read-only
          STATUS  mandatory
DESCRIPTION ""
		--% GROUP acpEnetPortEntry
          ::= { acpEnetPortEntry 15 }


     acpEnetPortRxBrRat OBJECT-TYPE 
          SYNTAX  Counter
          ACCESS  read-only
          STATUS  mandatory
DESCRIPTION ""
		--% GROUP acpEnetPortEntry
          ::= { acpEnetPortEntry 16 }


     acpEnetPortTxBrRat OBJECT-TYPE 
          SYNTAX  Counter
          ACCESS  read-only
          STATUS  mandatory
DESCRIPTION ""
		--% GROUP acpEnetPortEntry
          ::= { acpEnetPortEntry 17 }


     -- The ACP WAN Port Group


     acpWanPortTable OBJECT-TYPE 
          SYNTAX  SEQUENCE OF AcpWanPortEntry
          ACCESS  not-accessible
          STATUS  mandatory
DESCRIPTION ""
          ::= { acpWanPort 1 }


     acpWanPortEntry OBJECT-TYPE 
          SYNTAX  AcpWanPortEntry
          ACCESS  not-accessible
          STATUS  mandatory
DESCRIPTION ""
	  INDEX { acpWanPortInvert }
          ::= { acpWanPortTable 1 }


      AcpWanPortEntry ::= SEQUENCE {
          acpWanPortInvert
               INTEGER,
          acpWanPortRxQOflo
               Counter,
          acpWanPortRxUtil
               Counter,
          acpWanPortTxUtil
               Counter,
          acpWanPortClock
               INTEGER
     }


     acpWanPortInvert OBJECT-TYPE 
          SYNTAX  INTEGER {
                      no(1),
                      yes(2)
                  }
          ACCESS  read-only
          STATUS  mandatory
DESCRIPTION ""
		--% GROUP acpWanPortEntry
          ::= { acpWanPortEntry 1 }

     acpWanPortRxQOflo OBJECT-TYPE 
          SYNTAX  Counter
          ACCESS  read-only
          STATUS  mandatory
DESCRIPTION ""
		--% GROUP acpWanPortEntry
          ::= { acpWanPortEntry 2 }


     acpWanPortRxUtil OBJECT-TYPE 
          SYNTAX  Counter
          ACCESS  read-only
          STATUS  mandatory
DESCRIPTION ""
		--% GROUP acpWanPortEntry
          ::= { acpWanPortEntry 3 }


     acpWanPortTxUtil OBJECT-TYPE 
          SYNTAX  Counter
          ACCESS  read-only
          STATUS  mandatory
DESCRIPTION ""
		--% GROUP acpWanPortEntry
          ::= { acpWanPortEntry 4 }

     acpWanPortClock OBJECT-TYPE 
          SYNTAX  INTEGER
          ACCESS  read-only
          STATUS  mandatory
DESCRIPTION ""
		--% GROUP acpWanPortEntry
          ::= { acpWanPortEntry 5 }

     -- The ACP Enhanced Mesh Bridge Group

     acpMeshProtocol OBJECT-TYPE 
          SYNTAX INTEGER {
                     spanningTree(1),
                     enhancedMesh(2)
                 }
          ACCESS  read-only
          STATUS  mandatory
DESCRIPTION ""
		--% GROUP acpMesh
          ::= { acpMesh 1 }


     acpMeshBridgeCost OBJECT-TYPE 
          SYNTAX  INTEGER
          ACCESS  read-only
          STATUS  mandatory
DESCRIPTION ""
		--% GROUP acpMesh
          ::= { acpMesh 2 }


     acpMeshCostTabChanges OBJECT-TYPE 
          SYNTAX  Counter
          ACCESS  read-only
          STATUS  mandatory
DESCRIPTION ""
		--% GROUP acpMesh
          ::= { acpMesh 3 }


     acpMeshLastCostTabChange OBJECT-TYPE 
          SYNTAX  Counter
          ACCESS  read-only
          STATUS  mandatory
DESCRIPTION ""
		--% GROUP acpMesh
          ::= { acpMesh 4 }


     acpMeshSubRootAddr OBJECT-TYPE 
          SYNTAX  OCTET STRING
          ACCESS  read-only
          STATUS  mandatory
DESCRIPTION ""
		--% GROUP acpMesh
          ::= { acpMesh 5 }


     acpMeshCostInfoLost OBJECT-TYPE 
          SYNTAX  Counter
          ACCESS  read-only
          STATUS  mandatory
DESCRIPTION ""
		--% GROUP acpMesh
          ::= { acpMesh 6 }


     acpMeshNodeAddrTabSize OBJECT-TYPE 
          SYNTAX  Gauge
          ACCESS  read-only
          STATUS  mandatory
DESCRIPTION ""
		--% GROUP acpMesh
          ::= { acpMesh 7 }


     acpMeshNodeAddrTabSizePeak OBJECT-TYPE 
          SYNTAX  Counter
          ACCESS  read-only
          STATUS  mandatory
DESCRIPTION ""
		--% GROUP acpMesh
          ::= { acpMesh 8 }


     acpMeshPortTable OBJECT-TYPE 
          SYNTAX  SEQUENCE OF AcpMeshPortEntry
          ACCESS  not-accessible
          STATUS  mandatory
DESCRIPTION ""
          ::= { acpMesh 9 }


     acpMeshPortEntry OBJECT-TYPE 
          SYNTAX  AcpMeshPortEntry
          ACCESS  not-accessible
          STATUS  mandatory
DESCRIPTION ""
	  INDEX { acpMeshPortRemoteNodeIfIdx }
          ::= { acpMeshPortTable 1 }


      AcpMeshPortEntry ::= SEQUENCE {
          acpMeshPortDisabledReason
               INTEGER,
          acpMeshPortBlockingSubstate
               INTEGER,
          acpMeshPortLinkCost
               INTEGER,
          acpMeshPortRemoteNodeAddr
               OCTET STRING,
          acpMeshPortSubnetAddr
               OCTET STRING,
          acpMeshPortRemoteNodeIfIdx
               INTEGER
     }


     acpMeshPortDisabledReason OBJECT-TYPE 
          SYNTAX INTEGER {
                     broken(1),
                     looped(2),
                     stopped(3),
                     notCommunicating(4)
                 }
          ACCESS  read-only
          STATUS  mandatory
DESCRIPTION ""
		--% GROUP acpMeshPortEntry
          ::= { acpMeshPortEntry 1 }


     acpMeshPortBlockingSubstate OBJECT-TYPE 
          SYNTAX  INTEGER {
                      blocking(1),
                      forwarding(2)
                  }
          ACCESS  read-only
          STATUS  mandatory
DESCRIPTION ""
		--% GROUP acpMeshPortEntry
          ::= { acpMeshPortEntry 2 }


     acpMeshPortLinkCost OBJECT-TYPE 
          SYNTAX  INTEGER
          ACCESS  read-only
          STATUS  mandatory
DESCRIPTION ""
		--% GROUP acpMeshPortEntry
          ::= { acpMeshPortEntry 3 }

     acpMeshPortRemoteNodeAddr OBJECT-TYPE 
          SYNTAX  OCTET STRING
          ACCESS  read-only
          STATUS  mandatory
DESCRIPTION ""
		--% GROUP acpMeshPortEntry
          ::= { acpMeshPortEntry 4 }


     acpMeshPortSubnetAddr OBJECT-TYPE 
          SYNTAX  OCTET STRING
          ACCESS  read-only
          STATUS  mandatory
DESCRIPTION ""
		--% GROUP acpMeshPortEntry
          ::= { acpMeshPortEntry 5 }


     acpMeshPortRemoteNodeIfIdx OBJECT-TYPE 
          SYNTAX  INTEGER
          ACCESS  read-only
          STATUS  mandatory
DESCRIPTION ""
		--% GROUP acpMeshPortEntry
          ::= { acpMeshPortEntry 6 }


     -- The ACP Transparent Bridge Group

     acpTbAddrTabFree OBJECT-TYPE 
          SYNTAX  Gauge
          ACCESS  read-only
          STATUS  mandatory
DESCRIPTION ""
		--% GROUP acpTb
          ::= { acpTb 1 }


     acpTbAddrTabFreePeak OBJECT-TYPE 
          SYNTAX  Gauge
          ACCESS  read-only
          STATUS  mandatory
DESCRIPTION ""
		--% GROUP acpTb
          ::= { acpTb 2 }


     acpTbDynAddrTabSize OBJECT-TYPE 
          SYNTAX  Gauge
          ACCESS  read-only
          STATUS  mandatory
DESCRIPTION ""
		--% GROUP acpTb
          ::= { acpTb 3 }


     acpTbDynAddrTabSizePeak OBJECT-TYPE 
          SYNTAX  Gauge
          ACCESS  read-only
          STATUS  mandatory
DESCRIPTION ""
		--% GROUP acpTb
          ::= { acpTb 4 }


     acpTbStatAddrTabSize OBJECT-TYPE 
          SYNTAX  Gauge
          ACCESS  read-only
          STATUS  mandatory
DESCRIPTION ""
		--% GROUP acpTb
          ::= { acpTb 5 }


     acpTbStatAddrTabSizePeak OBJECT-TYPE 
          SYNTAX  Gauge
          ACCESS  read-only
          STATUS  mandatory
DESCRIPTION ""
		--% GROUP acpTb
          ::= { acpTb 6 }


     acpTbPortTable OBJECT-TYPE 
          SYNTAX  SEQUENCE OF AcpTbPortEntry
          ACCESS  not-accessible
          STATUS  mandatory
DESCRIPTION ""
          ::= { acpTb 7 }


     acpTbPortEntry OBJECT-TYPE 
          SYNTAX  AcpTbPortEntry
          ACCESS  not-accessible
          STATUS  mandatory
DESCRIPTION ""
	  INDEX { acpTbPortStn }
          ::= { acpTbPortTable 1  }


     AcpTbPortEntry ::= SEQUENCE {
          acpTbPortStn
               INTEGER,
          acpTbPortTimeForwarding
               INTEGER,
          acpTbPortTimeNotForwarding
               INTEGER
     }



     acpTbPortStn OBJECT-TYPE 
          SYNTAX  INTEGER
          ACCESS  read-only
          STATUS  mandatory
DESCRIPTION ""
		--% GROUP acpTbPortEntry
          ::= { acpTbPortEntry 1 }


     acpTbPortTimeForwarding OBJECT-TYPE 
          SYNTAX  INTEGER
          ACCESS  read-only
          STATUS  mandatory
DESCRIPTION ""
		--% GROUP acpTbPortEntry
          ::= { acpTbPortEntry 2 }


     acpTbPortTimeNotForwarding OBJECT-TYPE 
          SYNTAX  INTEGER
          ACCESS  read-only
          STATUS  mandatory
DESCRIPTION ""
		--% GROUP acpTbPortEntry
          ::= { acpTbPortEntry 3 }



     END
