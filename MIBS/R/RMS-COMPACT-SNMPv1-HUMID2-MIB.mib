-- ----------------------------------------------------------------------
--
--					Copyright (c) 2006 by Sinetica Corporation Ltd.
--
-- Filename:        RMS-C_SNMPv1_humid2.mib
--
-- Author:          Adrian Moruz
--
-- Description:     SNMPv1 MIB definition for the RMS Compact Humidity 2 notifications
--
-- $Id: RMS-C_SNMPv1_humid2.mib,v 1.1 2006/10/11 11:22:50 adrian.moruz Exp $
--
-- $Name:  $
--
-- $Log: RMS-C_SNMPv1_humid2.mib,v $
-- Revision 1.1  2006/10/11 11:22:50  adrian.moruz
-- Created from RMS-C_SNMPv1.mib v1.2 to separate the different trap enterprise groups into separate MIBs
--
--
-- ----------------------------------------------------------------------

RMS-COMPACT-SNMPv1-HUMID2-MIB DEFINITIONS ::= BEGIN

-- {{{ Imports
--	OBJECT-TYPE, Counter32, Unsigned32,

IMPORTS
        TRAP-TYPE
                FROM RFC-1215
        sysDescr, sysName, DisplayString
                FROM RFC1213-MIB
        OBJECT-TYPE
                FROM RFC-1212
        enterprises 
                FROM RFC1155-SMI
	;

-- }}}



sinetica   OBJECT IDENTIFIER ::= { enterprises 3711 }



rms-compact          OBJECT IDENTIFIER ::= { sinetica 15 }
rms-compact1         OBJECT IDENTIFIER ::= { rms-compact 1 }
rms-cObjects   OBJECT IDENTIFIER ::= { rms-compact1 1 }


-- {{{ rms-cObjects  

rms-cEnviroment   OBJECT IDENTIFIER ::= { rms-cObjects 1  }

-- }}}
-- {{{ rms-cTemp group    

rms-cHumid2          OBJECT IDENTIFIER ::= { rms-cEnviroment 4 }

-- }}}

rms-cHumid2LowControlLimitAlarm            TRAP-TYPE
    ENTERPRISE rms-cHumid2
    VARIABLES { 
    			sysDescr,
    			sysName,
    			rms-cHumid2Name,
    			rms-cHumid2LowerControlLevel
    			}
    DESCRIPTION
        "Humidity is below the low control limit."
	--#TYPE		"Humidity 2 below low control limit"
	--#SUMMARY	"Humidity %s below %d in %s at %s"
	--#ARGUMENTS	{2,3,0,1}
	--#SEVERITY 	MAJOR
	--#TIMEINDEX	4
	--#STATE		NONOPERATIONAL
    ::= 131

rms-cHumid2LowWarningLimitAlarm           TRAP-TYPE
    ENTERPRISE rms-cHumid2
    VARIABLES { 
    			sysDescr,
    			sysName,
    			rms-cHumid2Name,
    			rms-cHumid2LowerWarningLevel
    			}
    DESCRIPTION
        "Humidity is below the low warning limit."
	--#TYPE		"Humidity 2 below low warning limit"
	--#SUMMARY	"Humidity %s below %d in %s at %s"
	--#ARGUMENTS	{2,3,0,1}
	--#SEVERITY 	MINOR
	--#TIMEINDEX	4
	--#STATE		NONOPERATIONAL
    ::= 132

rms-cHumid2HighWarningLimitAlarm            TRAP-TYPE
    ENTERPRISE rms-cHumid2
    VARIABLES { 
    			sysDescr,
    			sysName,
    			rms-cHumid2Name,
    			rms-cHumid2UpperWarningLevel
    			}
    DESCRIPTION
        "Humidity is over the high warning limit."
	--#TYPE		"Humidity 2 above high warning limit"
	--#SUMMARY	"Humidity %s above %d in %s at %s"
	--#ARGUMENTS	{2,3,0,1}
	--#SEVERITY 	MINOR
	--#TIMEINDEX	4
	--#STATE		NONOPERATIONAL
    ::= 133

rms-cHumid2HighControlLimitAlarm           TRAP-TYPE
    ENTERPRISE rms-cHumid2
    VARIABLES { 
    			sysDescr,
    			sysName,
    			rms-cHumid2Name,
    			rms-cHumid2UpperControlLevel
    			}
    DESCRIPTION
        "Humidity is over the high control limit."
	--#TYPE		"Humidity 2 above high control limit"
	--#SUMMARY	"Humidity %s above %d in %s at %s"
	--#ARGUMENTS	{2,3,0,1}
	--#SEVERITY 	MAJOR
	--#TIMEINDEX	4
	--#STATE		NONOPERATIONAL
    ::= 134

rms-cHumid2LowControlLimitNormal            TRAP-TYPE
    ENTERPRISE rms-cHumid2
    VARIABLES { 
    			sysDescr,
    			sysName,
    			rms-cHumid2Name,
    			rms-cHumid2LowerControlLevel
    			}
    DESCRIPTION
        "Humidity is inside the low control limit."
	--#TYPE		"Humidity 2 above low control limit"
	--#SUMMARY	"Humidity %s above %d in %s at %s"
	--#ARGUMENTS	{2,3,0,1}
	--#SEVERITY 	INFORMATIONAL
	--#TIMEINDEX	4
	--#STATE		NONOPERATIONAL
    ::= 135

rms-cHumid2LowWarningLimitNormal           TRAP-TYPE
    ENTERPRISE rms-cHumid2
    VARIABLES { 
    			sysDescr,
    			sysName,
    			rms-cHumid2Name,
    			rms-cHumid2LowerWarningLevel
    			}
    DESCRIPTION
        "Humidity is inside the low warning limit."
	--#TYPE		"Humidity 2 above low warning limit"
	--#SUMMARY	"Humidity %s above %d in %s at %s"
	--#ARGUMENTS	{2,3,0,1}
	--#SEVERITY 	INFORMATIONAL
	--#TIMEINDEX	4
	--#STATE		NONOPERATIONAL
    ::= 136

rms-cHumid2HighWarningLimitNormal            TRAP-TYPE
    ENTERPRISE rms-cHumid2
    VARIABLES { 
    			sysDescr,
    			sysName,
    			rms-cHumid2Name,
    			rms-cHumid2UpperWarningLevel
    			}
    DESCRIPTION
        "Humidity is inside the high warning limit."
	--#TYPE		"Humidity 2 below high warning limit"
	--#SUMMARY	"Humidity %s below %d in %s at %s"
	--#ARGUMENTS	{2,3,0,1}
	--#SEVERITY 	INFORMATIONAL
	--#TIMEINDEX	4
	--#STATE		NONOPERATIONAL
    ::= 137

rms-cHumid2HighControlLimitNormal           TRAP-TYPE
    ENTERPRISE rms-cHumid2
    VARIABLES { 
    			sysDescr,
    			sysName,
    			rms-cHumid2Name,
    			rms-cHumid2UpperControlLevel
    			}
    DESCRIPTION
        "Humidity is inside the high control limit."
	--#TYPE		"Humidity 2 below high control limit"
	--#SUMMARY	"Humidity %s below %d in %s at %s"
	--#ARGUMENTS	{2,3,0,1}
	--#SEVERITY 	INFORMATIONAL
	--#TIMEINDEX	4
	--#STATE		NONOPERATIONAL
    ::= 138

-- }}}

END
