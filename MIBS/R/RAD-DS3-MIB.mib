RAD-DS3-MIB DEFINITIONS ::= BEGIN
--Title:    RAD-DS3   MIB
--
-- Copyright 1993 RAD Data Communications, Ltd.
-- All Rights Reserved.  
-- It is RAD's intent to encourage the widespread use of
-- this Specification in connection with the management of
-- RAD products. RAD grants vendors, end-users,
-- and other interested parties a non-exclusive license to
-- use this Specification in connection with the management
-- of RAD products.
-- This Specification is supplied "as is," and RAD makes
-- no warranty, either express or implied, as to the use,
-- operation, condition, or performance of the Specification.
 IMPORTS diverseIfWanGen FROM RAD-MIB
			OBJECT-TYPE, Integer32, Gauge32 FROM SNMPv2-SMI
		;

-- IMPORTS
--      Gauge32                           FROM SNMPv2-SMI
--      ifIndex                         FROM SNMPv2-TC
--      OBJECT-TYPE                     FROM SNMPv2-SMI
 --     radWan                          FROM RAD-GEN-MIB;
--                RAD-DS3 MIB   
--Title:     RAD's DS3 INTERFACE MIB
--Version:   1.0
--Date:      13.10.96
--By:        Yair Arian
--File:      ds3.mib
--
--Last update: 15 Oct 03 by Shlomo Shoham
ds3Interface  OBJECT IDENTIFIER  ::=  {diverseIfWanGen 3}
prtDs3PerfHistory  OBJECT IDENTIFIER  ::=  {ds3Interface 1}
          -- The DS3 Interface Table
          prtSDs3IfTable OBJECT-TYPE
              SYNTAX  SEQUENCE OF PrtDs3IfEntry
              MAX-ACCESS  not-accessible
              STATUS  current
              DESCRIPTION
                      "The DS3 interface table."
              ::= { prtDs3PerfHistory 1 }
          prtDs3IfEntry OBJECT-TYPE
              SYNTAX  PrtDs3IfEntry
              MAX-ACCESS  not-accessible
              STATUS  current
              DESCRIPTION
                      "An entry in the DS3 interface table."
              INDEX   { ifIndex }
              ::= { prtSDs3IfTable 1 }
          PrtDs3IfEntry ::=
              SEQUENCE {
                  prtDs3IfTimeElapsed
                      Integer32,
                  prtDs3IfValidIntervals
                      Integer32
                                           }
           prtDs3IfTimeElapsed OBJECT-TYPE
               SYNTAX  Integer32 (0..899)
               MAX-ACCESS  read-only
               STATUS  current
               DESCRIPTION
                       "The number of seconds that have elapsed since
                       the beginning of the near end current error-
                       measurement period."
              ::= { prtDs3IfEntry 1 }
          prtDs3IfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { prtDs3IfEntry 2 }
          -- The DS3 Current Table
          -- The DS3 Current table contains various statistics being
          -- collected for the current 15 minute interval.
          prtDs3CurrentTable OBJECT-TYPE
              SYNTAX  SEQUENCE OF PrtDs3CurrentEntry
              MAX-ACCESS  not-accessible
              STATUS  current
              DESCRIPTION
                      "The DS3 Current table."
              ::= { prtDs3PerfHistory 2 }
          prtDs3CurrentEntry OBJECT-TYPE
              SYNTAX  PrtDs3CurrentEntry
              MAX-ACCESS  not-accessible
              STATUS  current
              DESCRIPTION
                      "An entry in the DS3 Current table."
              INDEX   { ifIndex }
              ::= { prtDs3CurrentTable 1 }
          PrtDs3CurrentEntry ::=
              SEQUENCE {
                  prtDs3CurrentLOS
                      Gauge32,
                  prtDs3CurrentOOF
                      Gauge32,
                  prtDs3CurrentLOC
                      Gauge32,
                  prtDs3CurrentAIS
                      Gauge32,
                  prtDs3CurrentRDI
                      Gauge32,
                  prtDs3CurrentUAS
                      Gauge32,
	              prtDs3CurrentBIP
                      Gauge32,
                  prtDs3CurrentFEBE
	                  Gauge32,
	              prtDs3CurrentSLM
	                  Gauge32,
                  prtDs3CurrentSES
                      Gauge32,
                  prtDs3CurrentES 
                      Gauge32,
                  prtDs3CurrentBitParity
                      Gauge32,
                  prtDs3CurrentPlcpLOF
                      Gauge32,
                  prtDs3CurrentPlcpRAI
                       Gauge32,
	              prtDs3CurrentPlcpBIP
                       Gauge32,
                  prtDs3CurrentPlcpFEBE
	                   Gauge32,
				 prtDs3CurrentBPV
				       Gauge32,
				 prtDs3CurrentLCE
				       Gauge32,
				  prtDs3CurrentStatus
				       OCTET STRING
}
          prtDs3CurrentLOS OBJECT-TYPE
              SYNTAX  Gauge32
              MAX-ACCESS  read-only
              STATUS  current
              DESCRIPTION
                      "The counter associated with the number of LOS
                       seconds, encountered by a DS3 interface in
                      the current 15 minute interval."
              ::= { prtDs3CurrentEntry 1 }
          prtDs3CurrentOOF OBJECT-TYPE
              SYNTAX  Gauge32
              MAX-ACCESS  read-only
              STATUS  current
              DESCRIPTION
                      "The counter associated with the number of OOF
                       seconds, encountered by a DS3
                       interface in the current 15 minute interval."
              ::= { prtDs3CurrentEntry 2 }
          prtDs3CurrentLOC OBJECT-TYPE
              SYNTAX  Gauge32
              MAX-ACCESS  read-only
              STATUS  current
              DESCRIPTION
                      "The counter associated with the number of LOC
                      seconds, encountered by a DS3
                      interface in the current 15 minute interval."
              ::= { prtDs3CurrentEntry 3 }
          prtDs3CurrentAIS OBJECT-TYPE
              SYNTAX  Gauge32
              MAX-ACCESS  read-only
              STATUS  current
              DESCRIPTION
                      "The counter associated with the number of AIS
                      seconds, encountered by a DS3
                      interface in the current 15 minute interval."
              ::= { prtDs3CurrentEntry 4 }
          prtDs3CurrentRDI OBJECT-TYPE
              SYNTAX  Gauge32
              MAX-ACCESS  read-only
              STATUS  current
              DESCRIPTION
                      "The counter associated with the number of RDI
                      seconds, encountered by a DS3
                      interface."
              ::= { prtDs3CurrentEntry 5 }
          prtDs3CurrentUAS OBJECT-TYPE
              SYNTAX  Gauge32
              MAX-ACCESS  read-only
              STATUS  current
              DESCRIPTION
                      "The counter associated with the number of UAS, 
                      encountered by a SONET interface."
              ::= { prtDs3CurrentEntry 6 }
        prtDs3CurrentBIP OBJECT-TYPE
              SYNTAX  Gauge32
              MAX-ACCESS  read-only
              STATUS  current
              DESCRIPTION
                      "The counter associated with the number of 
                      BIP errors, encountered by a DS3
                      interface in the current 15 minute interval."
              ::= { prtDs3CurrentEntry 7 }
          prtDs3CurrentFEBE OBJECT-TYPE
              SYNTAX  Gauge32
              MAX-ACCESS  read-only
              STATUS  current
              DESCRIPTION
                      "The counter associated with the number of 
                      FEBE errors, encountered by a DS3
                      interface in the current 15 minute interval."
              ::= { prtDs3CurrentEntry 8 }
          prtDs3CurrentSLM OBJECT-TYPE
              SYNTAX  Gauge32
              MAX-ACCESS  read-only
              STATUS  current
              DESCRIPTION
                      "The counter associated with the number of SLM
                       seconds, encountered by an E3 (only )
                       interface in the current 15 minute interval."
              ::= { prtDs3CurrentEntry 9 }
        prtDs3CurrentSES OBJECT-TYPE
              SYNTAX  Gauge32
              MAX-ACCESS  read-only
              STATUS  current
              DESCRIPTION
                      "The counter associated with the number of SES
                       encountered by a E3
                       interface in the current 15 minute interval."
	     ::= { prtDs3CurrentEntry 10 }
	  prtDs3CurrentES OBJECT-TYPE
	SYNTAX Gauge32 
              MAX-ACCESS  read-only
              STATUS  current
              DESCRIPTION
                      " The number of Errored Seconds, encountered  by a
                      DS3 interface in the current 15 minute interval."
	::= { prtDs3CurrentEntry 11 }
     prtDs3CurrentBitParity OBJECT-TYPE
              SYNTAX  Gauge32
              MAX-ACCESS  read-only
              STATUS  current
              DESCRIPTION
                      "Bit Parity Error counter. Relevant to T3 only."
              ::= { prtDs3CurrentEntry 12 }
        prtDs3CurrentPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3CurrentEntry 13 }
prtDs3CurrentPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3CurrentEntry 14 }
      prtDs3CurrentPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3CurrentEntry 15 }
      prtDs3CurrentPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3CurrentEntry 16 }
      prtDs3CurrentBPV OBJECT-TYPE
              SYNTAX  Gauge32
              MAX-ACCESS  read-only
              STATUS  current
              DESCRIPTION
                    " Number of BPVs (Bi-Polar Violations) , encountered by a 
                      DS3 interface in the current 15 minute interval. 
                      This object is relevant only for Electrical Line
                      of Fomi-E3/T3."
              ::= { prtDs3CurrentEntry 17 }
      prtDs3CurrentLCE OBJECT-TYPE
              SYNTAX  Gauge32
              MAX-ACCESS  read-only
              STATUS  current
              DESCRIPTION
                    " Number of LCE (Link Code Errors)  encountered 
                      by a DS3 interface in the current 15 minute interval. 
                      This object is relevant only for Optical Links
                      of Fomi-E3/T3."
              ::= { prtDs3CurrentEntry 18 }
     prtDs3CurrentStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3CurrentEntry 19 }
         -- The DS3 interface Interval
          -- The DS3 Interval Table contains various statistics
          -- collected by the Interface over the previous 24
          -- hours of operation.  The past 24 hours are broken into 96
          -- completed 15 minute intervals.
          prtDs3IntervalTable OBJECT-TYPE
              SYNTAX  SEQUENCE OF PrtDs3IntervalEntry
              MAX-ACCESS  not-accessible
              STATUS  current
              DESCRIPTION
                      "The DS3 Interval table."
              ::= { prtDs3PerfHistory 3 }
          prtDs3IntervalEntry OBJECT-TYPE
              SYNTAX  PrtDs3IntervalEntry
              MAX-ACCESS  not-accessible
              STATUS  current
              DESCRIPTION
                      "An entry in the DS3 Interval table."
              INDEX   { ifIndex, prtDs3IntervalNumber }
              ::= { prtDs3IntervalTable 1 }
          PrtDs3IntervalEntry ::=
              SEQUENCE {
                  prtDs3IntervalNumber
                      Integer32,
                  prtDs3IntervalLOS
                      Gauge32,
                  prtDs3IntervalOOF
                      Gauge32,
                  prtDs3IntervalLOC
                      Gauge32,
                  prtDs3IntervalAIS
                      Gauge32,
                  prtDs3IntervalRDI
                      Gauge32,
                  prtDs3IntervalUAS
                      Gauge32,
	              prtDs3IntervalBIP
                      Gauge32,
                  prtDs3IntervalFEBE
                      Gauge32,
	              prtDs3IntervalSLM
                      Gauge32,
                  prtDs3IntervalSES 
                      Gauge32,
	              prtDs3IntervalES
                      Gauge32,
                  prtDs3IntervalBitParity
                      Gauge32,
                  prtDs3IntervalPlcpLOF
                      Gauge32,
                  prtDs3IntervalPlcpRAI
                      Gauge32,
	              prtDs3IntervalPlcpBIP
                      Gauge32,
                  prtDs3IntervalPlcpFEBE
	                  Gauge32,
				  prtDs3IntervalBPV
				       Gauge32,
				  prtDs3IntervalLCE
				       Gauge32,
				  prtDs3IntervalStatus 
	                  OCTET STRING
}
          prtDs3IntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtDs3IntervalEntry 1 }
          prtDs3IntervalLOS OBJECT-TYPE
              SYNTAX  Gauge32
              MAX-ACCESS  read-only
              STATUS  current
              DESCRIPTION
                      "The counter associated with the number of LOS
                      seconds , encountered by a DS3 interface in
                      one of the previous 96, individual 15 minute,
                      intervals."
              ::= { prtDs3IntervalEntry 2 }
          prtDs3IntervalOOF OBJECT-TYPE
              SYNTAX  Gauge32
              MAX-ACCESS  read-only
              STATUS  current
              DESCRIPTION
                      "The counter associated with the number of OOF
                      seconds, encountered by a DS3
                      interface in one of the previous 96, individual 15
                      minute, intervals."
              ::= { prtDs3IntervalEntry 3 }
          prtDs3IntervalLOC OBJECT-TYPE
              SYNTAX  Gauge32
              MAX-ACCESS  read-only
              STATUS  current
              DESCRIPTION
                      "The counter associated with the number of LOC
                      seconds, encountered by a DS3
                      interface in one of the previous 96,
                      individual 15 minute, intervals."
              ::= { prtDs3IntervalEntry 4 }
          prtDs3IntervalAIS OBJECT-TYPE
              SYNTAX  Gauge32
              MAX-ACCESS  read-only
              STATUS  current
              DESCRIPTION
                      "The counter associated with the number of AIS
                      seconds, encountered by a SONET
                      interface in one of the previous 96, individual 15
                      minute, intervals."
              ::= { prtDs3IntervalEntry 5 }
          prtDs3IntervalRDI OBJECT-TYPE
              SYNTAX  Gauge32
              MAX-ACCESS  read-only
              STATUS  current
              DESCRIPTION
                      "The counter associated with the number of RDI
                      seconds, encountered by a DS3
                      interface in one of the previous 96, individual 15
                      minute, intervals."
              ::= { prtDs3IntervalEntry 6 }
          prtDs3IntervalUAS OBJECT-TYPE
              SYNTAX  Gauge32
              MAX-ACCESS  read-only
              STATUS  current
              DESCRIPTION
                      "The counter associated with the number of UAS,
                      encountered by a DS3
                      interface in one of the previous 96, individual 15
                      minute, intervals."
              ::= { prtDs3IntervalEntry 7 }
          prtDs3IntervalBIP OBJECT-TYPE
              SYNTAX  Gauge32
              MAX-ACCESS  read-only
              STATUS  current
              DESCRIPTION
                      "The counter associated with the number of 
                      BIP errors, encountered by a DS3 
                      interface in one of the previous 96, individual 15
                      minute, intervals."
              ::= { prtDs3IntervalEntry 8 }
          prtDs3IntervalFEBE OBJECT-TYPE
              SYNTAX  Gauge32
              MAX-ACCESS  read-only
              STATUS  current
              DESCRIPTION
                      "The counter associated with the number of 
                      FEBE errors, encountered by a DS3
                      interface in one of the previous 96, individual 15
                      minute, intervals."
              ::= { prtDs3IntervalEntry 9 }
          prtDs3IntervalSLM OBJECT-TYPE
              SYNTAX  Gauge32
              MAX-ACCESS  read-only
              STATUS  current
              DESCRIPTION
                      "The counter associated with the number of SLM
                      seconds, encountered by an E3
                      interface in one of the previous 96, individual 15
                      minute, intervals."
              ::= { prtDs3IntervalEntry 10 }
	 prtDs3IntervalSES OBJECT-TYPE
              SYNTAX  Gauge32
              MAX-ACCESS  read-only
              STATUS  current
              DESCRIPTION
                      "The counter associated with the number of SES
                      encountered by a E3
                      interface in one of the previous 96, individual 15
                      minute, intervals."
	      ::= { prtDs3IntervalEntry 11 }
	 prtDs3IntervalES OBJECT-TYPE
	SYNTAX Gauge32
              MAX-ACCESS  read-only
              STATUS  current
              DESCRIPTION
                      " The number of Errored Seconds, encountered  by a
                      DS3 interface in one of the previous 96, individual 15
                      minute, intervals."
	::= { prtDs3IntervalEntry 12 }
prtDs3IntervalBitParity OBJECT-TYPE
              SYNTAX  Gauge32
              MAX-ACCESS  read-only
              STATUS  current
              DESCRIPTION
                      "Bit Parity Error counter. Relevant to T3 only."
              ::= { prtDs3IntervalEntry 13 }
        prtDs3IntervalPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3IntervalEntry 14 }
prtDs3IntervalPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3IntervalEntry 15 }
      prtDs3IntervalPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3IntervalEntry 16 }
      prtDs3IntervalPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3IntervalEntry 17 }
      prtDs3IntervalBPV OBJECT-TYPE
              SYNTAX  Gauge32
              MAX-ACCESS  read-only
              STATUS  current
              DESCRIPTION
                    " Number of BPVs (Bi-Polar Violations) , encountered by a 
                      DS3 interface in the specified 15 minute interval. 
                      This object is relevant only for Electrical Line
                      of Fomi-E3/T3."
              ::= { prtDs3IntervalEntry 18 }
      prtDs3IntervalLCE OBJECT-TYPE
              SYNTAX  Gauge32
              MAX-ACCESS  read-only
              STATUS  current
              DESCRIPTION
                    " Number of LCE (Link Code Errors) encountered 
                      by a DS3 interface in the specified 15 minute interval. 
                      This object is relevant only for Optical Links
                      of Fomi-E3/T3."
              ::= { prtDs3IntervalEntry 19 }
     prtDs3IntervalStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3IntervalEntry 20 }
-- the DS3 Total table
prtDs3TotalTable OBJECT-TYPE
              SYNTAX  SEQUENCE OF PrtDs3TotalEntry
              MAX-ACCESS  not-accessible
              STATUS  current
              DESCRIPTION
              " A list of Total entries."
              ::= { prtDs3PerfHistory 4 }
prtDs3TotalEntry OBJECT-TYPE
              SYNTAX  PrtDs3TotalEntry
              MAX-ACCESS  not-accessible
              STATUS  current
              DESCRIPTION
              "An entry of Total table."
              INDEX   { ifIndex }
              ::= { prtDs3TotalTable 1 }
PrtDs3TotalEntry     ::=
          SEQUENCE {
       	    prtDs3TotalUAS	Gauge32,
        	prtDs3TotalBPV	Gauge32,
            prtDs3TotalLCE  Gauge32,
			prtDs3TotalSES  Gauge32
            }
prtDs3TotalUAS OBJECT-TYPE
              SYNTAX  Gauge32
              MAX-ACCESS  read-only
              STATUS  current
              DESCRIPTION
              "Number of UASs (Unavailable Seconds) , encountered by a 
               DS3 interface in the previous 96 intervals.
               Invalid 15 minute intervals count as 0."
              ::= { prtDs3TotalEntry 6 }
prtDs3TotalBPV OBJECT-TYPE
              SYNTAX  Gauge32
              MAX-ACCESS  read-only
              STATUS  current
              DESCRIPTION
              "Number of BPVs (Bi-Polar Violations) , encountered by a 
               DS3 interface in the previous 96 intervals.
               Invalid 15 minute intervals count as 0."
              ::= { prtDs3TotalEntry 17 }
prtDs3TotalLCE OBJECT-TYPE
              SYNTAX  Gauge32
              MAX-ACCESS  read-only
              STATUS  current
              DESCRIPTION
              "Number of LCE (Link Code Errors) encountered 
               by a DS3 interface in the previous 96 intervals.
               Invalid 15 minute intervals count as 0."
              ::= { prtDs3TotalEntry 18 }
prtDs3TotalSES OBJECT-TYPE
              SYNTAX  Gauge32
              MAX-ACCESS  read-only
              STATUS  current
              DESCRIPTION
              "Number of SES (Severely Errored Seconds) encountered 
               by a DS3 interface in the previous 96 intervals.
               Invalid 15 minute intervals count as 0."
              ::= { prtDs3TotalEntry 19 } 
dsx3XConfigTable  OBJECT-TYPE
       SYNTAX      SEQUENCE OF Dsx3XConfigEntry
       MAX-ACCESS  not-accessible
       STATUS      current
       DESCRIPTION
       "An extension to the DS3 Configuration table."
       ::= { ds3Interface 2 }
dsx3XConfigEntry OBJECT-TYPE
       SYNTAX  Dsx3XConfigEntry 
       MAX-ACCESS  not-accessible
       STATUS      current
       DESCRIPTION
       "An entry containing additional configuration
        parameters."
       AUGMENTS    { dsx3ConfigEntry }
      --  INDEX   {dsx3LineIndex }
       ::= { dsx3XConfigTable 1 }
Dsx3XConfigEntry      ::=
       SEQUENCE {
         dsx3AisEnable				INTEGER
		        }
dsx3AisEnable  OBJECT-TYPE
       SYNTAX  INTEGER {
	   notApplicable(1),
       disable(2),
	   enable(3)
       }
	   MAX-ACCESS  read-write
	   STATUS  current
	   DESCRIPTION
	   "Enable/ disable AIS transmit when Ethernet (for TDMoIP) line is disconnected."
	   ::= { dsx3XConfigEntry 1 }
END
