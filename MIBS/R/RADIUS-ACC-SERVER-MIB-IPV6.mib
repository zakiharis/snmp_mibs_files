-- extracted from draft-nelson-rfc2621bis-00.txt
-- at Thu Feb 10 06:24:09 2005

     RADIUS-ACC-SERVER-MIB-IPV6 DEFINITIONS ::= BEGIN

   IMPORTS
          MODULE-IDENTITY, OBJECT-TYPE, OBJECT-IDENTITY,
          mib-2 FROM SNMPv2-SMI
          InetAddressType, InetAddress, InetPortNumber
          FROM INET-ADDRESS-MIB
          MODULE-COMPLIANCE, OBJECT-GROUP  FROM SNMPv2-CONF
          radiusAccClientEntry FROM RADIUS-ACC-SERVER-MIB;

   radiusAccServerExtMIB MODULE-IDENTITY
          LAST-UPDATED "200502072051Z"  -- Mon Feb  7 20:51 GMT 2005
          ORGANIZATION "IETF RADIUS Extensions Working Group."
          CONTACT-INFO
                 " David B. Nelson
                   Enterasys Networks
                   50 Minutemann Road
                   Andover, MA 01810
                   US

                   Phone: +1 978 684 1000
                   EMail: dnelson@eterasys.com"
          DESCRIPTION
                "An extension to the MIB module for entities
                 implementing the server side of the Remote Access
                 Dialin User Service (RADIUS) accounting protocol,
                 using IPv6 addressing formats. Updates RFC 2621."
          REVISION "200502072051Z"  -- Mon Feb  7 20:51 GMT 2005
          DESCRIPTION "Initial version, published as RFC xxxx."

   -- RFC Editor: replace xxx with actual RFC number at the time of
   -- publication, and remove this note.

          ::= { mib-2 1 }

   -- RFC Editor: replace TBA with IANA assigned OID value, and
   -- remove this note.

   radiusAccServerExtMIBNotifications  OBJECT IDENTIFIER
               ::= { radiusAccServerExtMIB 0 }

   radiusAccServerExtMIBObjects        OBJECT IDENTIFIER
               ::= { radiusAccServerExtMIB 1 }

   radiusAccServerExtMIBConformance    OBJECT IDENTIFIER
               ::= { radiusAccServerExtMIB 2 }

   -- MIB objects

   radiusAccClientExtTable OBJECT-TYPE
         SYNTAX      SEQUENCE OF RadiusAccClientExtEntry
         MAX-ACCESS  not-accessible
         STATUS      current
         DESCRIPTION
              "The (conceptual) table listing the RADIUS
               accounting clients with which the server
               shares a secret."
         ::= { radiusAccServerExtMIBObjects 1 }

   radiusAccClientExtEntry OBJECT-TYPE
         SYNTAX     RadiusAccClientExtEntry
         MAX-ACCESS not-accessible
         STATUS     current
         DESCRIPTION
               "An entry (conceptual row) representing a RADIUS
                accounting client with which the server shares
                a secret."
         AUGMENTS      { radiusAccClientEntry }
         ::= { radiusAccClientExtTable 1 }

   RadiusAccClientExtEntry ::= SEQUENCE {
         radiusAccClientInetAddressType      InetAddressType,
         radiusAccClientInetAddress          InetAddress
   }

   radiusAccClientInetAddressType OBJECT-TYPE
         SYNTAX     InetAddressType
         MAX-ACCESS read-only
         STATUS     current
         DESCRIPTION
               "The type of address format used for the
                radiusAccClientInetAddress object."
         ::= { radiusAccClientExtEntry 1 }

   radiusAccClientInetAddress OBJECT-TYPE
         SYNTAX     InetAddress
         MAX-ACCESS read-only
         STATUS     current
         DESCRIPTION
               "The IP address of the RADIUS accounting
                client referred to in this table entry, using
                the IPv6 adddess format."
         ::= { radiusAccClientExtEntry 2 }

   -- conformance information

   radiusAccServerExtMIBCompliances OBJECT IDENTIFIER
         ::= { radiusAccServerExtMIBConformance 1 }

   radiusAccServerExtMIBGroups      OBJECT IDENTIFIER
         ::= { radiusAccServerExtMIBConformance 2 }

   -- compliance statements

   radiusAccServerExtMIBCompliance MODULE-COMPLIANCE
        STATUS  current
        DESCRIPTION
              "The compliance statement for accounting
               servers implementing the RADIUS Accounting
               Server IPv6 Extensions MIB."
        MODULE  -- this module
               MANDATORY-GROUPS { radiusAccServerExtMIBGroup }

        ::= { radiusAccServerExtMIBCompliances 1 }

   -- units of conformance

   radiusAccServerExtMIBGroup OBJECT-GROUP
        OBJECTS { radiusAccClientInetAddressType,
                  radiusAccClientInetAddress
               }
        STATUS  current
        DESCRIPTION
              "The collection of extended objects providing
               management of RADIUS Accounting Servers
               using IPv6 address format."
        ::= { radiusAccServerExtMIBGroups 1 }

   END

-- 
--    Copyright (C) The Internet Society (2005).  This document is subject
--    to the rights, licenses and restrictions contained in BCP 78, and
--    except as set forth therein, the authors retain all their rights.
-- 
-- 
-- Acknowledgment
-- 
--    Funding for the RFC Editor function is currently provided by the
--    Internet Society.
