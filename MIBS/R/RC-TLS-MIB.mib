RC-TLS-MIB DEFINITIONS ::= BEGIN

IMPORTS
    MODULE-IDENTITY, OBJECT-TYPE, Integer32, IpAddress, Counter64, Counter32, Gauge32, 
    NOTIFICATION-TYPE
        FROM SNMPv2-SMI
    DisplayString, TruthValue, MacAddress, RowStatus, DateAndTime, TimeStamp
        FROM SNMPv2-TC
    InterfaceIndex, InterfaceIndexOrZero
        FROM IF-MIB
    rcTls, rcCos, rcBanRing, rcRing, rcTdc, IdList, EnableValue, rc8021ah, rcPwe3
        FROM RAPID-CITY;

rcTlsMib MODULE-IDENTITY
       LAST-UPDATED     "201310100000Z"
       ORGANIZATION     "Bay Networks, Rapid-City Group"
       CONTACT-INFO     "
                                        Edwin Tsang
                         Postal:        Bay Networks, Inc.
                                        4401 Great America Parkway
                                        Santa Clara, CA 95052-8185

                         Tel:           408-495-6159
                         Fax:           408-495-5215
                         E-mail:        edwin_tsang@baynetworks.com
                        "
       DESCRIPTION      "Enterprise MIB for the Accelar product family."

       REVISION "201310100000Z" -- 10 October 2013
       DESCRIPTION "Version 33 :  Corrected syntax definitions."

       REVISION "200907020000Z" -- 07 July 2009
       DESCRIPTION "Version 32 :  Added rcIsidDHUni."

       REVISION "200903250000Z" -- 25 March 2009
       DESCRIPTION "Version 31 :  Added rcIsidEndptCfmIngRateLmtAction 
                                                              and rcIsidEndptCfmIngRateLmtAction under RcIsidEndptEntry.
                                                              Modified range for rcRingBcastGroupIpVlan ."

       REVISION "200903160000Z" -- 16 March 2009
       DESCRIPTION "Version 30: Updated: rcTlsTdiStatsTable, rcTlsEndptStatsTable, 
                                                             rcTlsUniIpServiceStatsTable,rcTlsIpServiceStatsTable, 
                                                             rcCosProfileTable, rcIsidEndptTable, 
                                                             rcIsidStatsTable, rcIsidEndptStatsTable."                                                             

       REVISION "200811060000Z" -- 06 November 2008
       DESCRIPTION "Version 29: modified rcBanRingId MAX-ACCESS from non-accessible to read only, 
                                                         removed size form declaration rcIsidBmacAddr "

       REVISION "200810240000Z" -- 24 October 2008
       DESCRIPTION "Version 28: modified: RcTlsTdiEndptEntry, RcRingEntry, RcIsidEntry, RcIsidEndptEntry 
                                                         added: rcRingBcastGroupTable, rcRingESUTable , rcL2cpMacBlockTable, 
                                                         rcL2cpProfileTable,rcL2cpProfileRuleTable,rcIsidMgmtEndptTable,
                                                         rcL2cpProfileTableSize . Removed : rcIsidIgmpTable, rcRingBcastMappingTable,
                                                          rcRingIgmpSnoopOnEsuEvpn "

       REVISION "200809160000Z" -- 16 Sept 2008
       DESCRIPTION "Version 27: Modified rcTlsTestTdcErrorMask 
	                                 rcTlsTestTdcHistoryErrorMask"

       REVISION "200807230000Z" -- 23 July 2008
       DESCRIPTION "Version 26: Modified rcTlsTdiEndptTdid,
	                                 rcTlsTdiEndptUniAddr"

       REVISION "200807140000Z" -- 14 July 2008
       DESCRIPTION "Version 25: Modified rcTlsRmodLane
	                        Added rcBanRingSaRbsEsuIp,
				rcIsidEsuIgmpSnoop,
				rcIsidPlsb, rcIsidPlsbEnable"	   

       REVISION "200805220000Z" -- 22 May 2008
       DESCRIPTION "Version 24: Added rcEsuStandaloneTopoTable"

       REVISION "200805100000Z" -- 10 May 2008
       DESCRIPTION "Version 23: Fixed smilint errors."

       REVISION "200803140000Z" -- 14 March 2008
       DESCRIPTION "Version 22: Modified rcRingRrpHello,
   	                                 rcRingRrpHelloInterval,
					 rcRingClearRrpStats,
					 rcRingStatsRingPortTxRrpHello,
					 rcRingStatsRingPortRxRrpHello,
					 rcRingStatsRingPortMissingRrpHello,
					 RcTlsTdiEndptEntry,
					 RcIsidEndptEntry,
					 RcIsidEndptCvidClientMepEntry.
					 rcIsidEndptDEDecodeScheme,
					 rcPwEndptPriOverrideType,
					 rcIsidEndptPriOverrideType,
					 rcTlsTdiEndptPriOverrideType,
			        Added    rcIsidEndptCvidClientMipTable,
				         rcBanRingCopyBtagPbits,
					 rcBanRingSaRbsCopyBtagPbits,
					 rcIsidEndptCopyItagPcpDeiToStag,
					 rcIsidIgmpTable,
					 rcIsidEndptDhcpL2Relay,
					 rcIsidEndptIgmpAclName,
					 rcIsidEndptIgmpStaticEntriesName,
					 rcRingBcastMappingTable,
					 rcIsidEndptCvidClientDownMepMepList,
					 rcIsidEndptCvidClientDownMepNumOfMep
				Removed  rcBanRingIgmpSnoopOnEsuEvpn,
				         rcBanRingSaIgmpSnoopOnEsuEvpn,
					 rcBanDhRingIgmpSnoopOnEsuEvpn"

       REVISION "200712050000Z" -- 05 Dec 2007
       DESCRIPTION "Version 21: Added rcIsidNumDestBmacAddr,
				      rcIsidBmacAddr,
				      rcIsidDirectedMcast,
				      rcIsidVideoType,
				      rcIsidEndptEndPointId,
				      rcIsidEndptDirectedMcast,
				      rcTlsIsidUserMacTable,
				      rcRingModuleTable,
				      rcRingTable,
				      rcRingStatsTable,
                                      rcBanRingIgmpSnoopOnEsuEvpn,
				      rcRingClearRctStats,
				      rcBanRingSaIgmpSnoopOnEsuEvpn,
				      rcBanDhRingIgmpSnoopOnEsuEvpn,
				      rcIsidVideoMrgPtAclTable,
				      rcRingIgmpSnoopOnEsuEvpn,
				Modified rcTlsUniRbsId,
				         rcTlsUniStandaloneRbsId,
					 rcTlsIpServiceModId,
					 rcBanRingTopoRbsId,
					 rcRingModuleModId,
					 rcRingPrimaryEsuModIds,
					 rcRingSecondaryEsuModIds,
					 rcIsidEndptModId,
					 rcRingRrpHello,
					 rcRingRrpHelloInterval,
					 rcRingStatsRingPortTxRrpHello,
					 rcRingStatsRingPortRxRrpHello,
					 rcRingStatsRingPortMissingRrpHello,
					 rcTlsTdiPbtEnable,
					 rcTlsTdiEndptTrunkGroup,
			        Removed  rcRingClearRrpStats"		 
					  

       REVISION "200710050000Z" -- 05 Oct 2007
       DESCRIPTION "Version 20: Added description for rcBanRing 3, rcBanRing 4 and rcBanRingSaRbsStatsTable 1"
                                     

       REVISION "200708230000Z" -- 23 Aug 2007
       DESCRIPTION "Version 19: Added    rcBanRingSaRbsClearRdpStats,
	                                 rcBanRingSaRbsStatsTable
	                        Modified rcTlsTdiEndptDropRedColorPackets,
				         rcTlsUniIpServiceDropRedColorPackets,
					 rcTlsIpServiceDropRedColorPackets,
				 	 rcIsidEndptDropRedColorPackets,
					 rcPwEndptDropRedColorPackets,
					 rcIsidStatsName"

       REVISION "200704180000Z" -- 18 Apr 2007
       DESCRIPTION "Version 18: Added   rcTlsTdiClearVboStats,rcTlsTdiEndptPolicingOption,
                			rcTlsTdiEndptPriOverrideType, rcTlsTdiEndptColorBasedRemarking,
 	 	 	             	rcTlsTdiEndptDropRedColorPackets,rcTlsTdiEndptDefaultTdi,
					rcTlsTdiEndptUserLabel1,rcTlsTdiEndptUserLabel2,
        	        		rcTlsTdiEndptL2ptMacSwapCdp,rcTlsTdiEndptL2ptMacSwapVtp, 									rcTlsTdiEndptL2ptMacSwapStp
				Added   Attributes 54-103 to rcTlsTdiStatsTable
				Added   Attributes 55-104 to rcTlsEndptStatsTable
				Added   rcTlsIpCustIpWatermarkIndication, rcTlsIpCustIpVlan, rcTlsRmodLane
				Added   rcTlsUniIpServiceIngressMirrorState, rcTlsUniIpServiceEgressMirrorState,
					rcTlsUniIpServicePriOverrideType, rcTlsUniIpServiceColorBasedRemarking,
 					rcTlsUniIpServiceDropRedColorPacket
				Added   Attribute 55-104 to rcTlsUniIpServiceStatsTable
				Added   Attribute 21-26 to rcTlsIpServiceTabe
				Added   Attribute 55-104 to rcTlsIpServiceStatsTable
				Added   rcOeRecordCountTable, rcTlsIpServiceRmodTable, 										        rcTlsTdiBroadcastOptimizationStatsTable,
					rcTlsIsidBroadcastOptimizationStatsTable,
				Added   rcIsidVboEnable, rcIsidClearVboStats and rcIsidMuxMode
				Added   Attribute 53-102 to rcIsidStatsTable
				Added   Attribute 55-104 to rcIsidEndptStatsTable
                                Added   rcIsidNniRateLimiterTable,rcIsidNniRateLimiterStatsTable
				Added   Attribute 33 - 41 to rcPwEndptTable
				Added   Attribute 55 - 104 to rcPwEndptStatsTable"


       REVISION "200701020000Z" -- 02 Jan 2007
       DESCRIPTION "Version 17: Added  rcTlsTdiMacTblSize, rcTlsTdiMacTblWaterMk, rcTlsTdiMacAgeTimer,
				       rcTlsTdiForceDelete to rcTlsTdiTable.
				Added  rcTlsUniMltId and rcTlsUniForceDelete to rcTlsUniTable.
				Added  rcTlsTdiEndptTrunkGroup to rcTlsTdiEndptTable.
 				Added  rcTlsSlot and rcTlsIsidId to rcTlsTrap.
				Added  rcEsmPortPolicerStatsTable, rcTlsIpServiceTable,
				       rcTlsIpServiceStatsTable
                                Added  rcOePortMplsUniCount to rcOePortTable
   				Added  rcTlsTdcTestResultDescription to rcTlsTestTdc group
				Added  rcIsidTable rcIsidEndptTable, rcIsidStatsTable, 
                                       rcIsidEndptStatsTable and rcIsidEndptCvidClientMepTable
  				Added  rcPwEndptTable, rcPwEndptStatsTable and rcPwEndptCvidClientMepTable
				Modified the rcTlsTdiAdminState"
	

       REVISION "200602030000Z" -- 03 February 2006
       DESCRIPTION "Version 16: Added  rcTlsTdiEncapsulation, rcTlsTdiMdName, rcTlsTdiMaName,
				rcTlsTdiPbtEnable and rcTlsTdiVboEnable to rcTlsTdiTable.
				Added rcTlsTdiEndptMepId,rcTlsTdiEndptServiceGroup,
				rcTlsTdiEndptCcmOperStatus,rcTlsTdiEndptIngressMirrorState 
				and rcTlsTdiEndptEgressMirrorState to rcTlsTdiEndptTable.
				Added rcTlsGlobals and rcOePortTable"
	
       REVISION "200507280000Z" -- 28 July 2005
       DESCRIPTION "Version 15: Added rcBanRingNumOfUni to rcBanRingTable. 
			        Added rcBanDhRingNumOfUni to rcBanDhRingEntry"

       REVISION "200507190000Z" -- 19 July 2005
       DESCRIPTION "Version 14: Changed rcTlsUniAdminState  syntax to INTEGER enum"

       REVISION "200506140000Z" -- 14 June 2005 
       DESCRIPTION "Version 13:  Correct the range for rcTlsTdcPeriodicRate"
       
       REVISION "200505020000Z" -- 2 May 2005 
       DESCRIPTION "Version 12:  Depricated rcTlsUniQinqEtherType amd added rcTlsUniQinQEtherType 
				 Added new attributes: rcBanRingRrpHello,rcBanRingRrpHelloInterval,
					rcBanRingClearRrpStats and rcBanRingClearRdpStats to 
					rcBanRingTable.
				 Added new attributes: rcBanDhRingRrpHello, rcBanDhRingRrpHelloInterval, 
					rcBanDhRingClearRrpStats and rcBanDhRingClearRdpStats to 
					rcBanDhRingTable.
				 Added new tabels: rcBanRingStatsTable and rcBanDhRingStatsTable"			 
       
       REVISION "200504140000Z" -- 14 April 2005 
       DESCRIPTION "Version 11:  Obsolete rcTlsTestTdcHistoryMax and rcTlsTestTdcHistoryRemaining"

       REVISION "200503280000Z" -- 28 March 2005 
       DESCRIPTION "Version 10:  Added new attributes to rcTlsTdiStatsTable,rcCosProfileTable,
			   	rcTlsEndptStatsTable and rcTlsUniIpServiceStatsTable"

       REVISION "200503080000Z" -- 08 March 2005 
       DESCRIPTION "Version 9:  Added rcTlsUniIpServiceWatermarkIndication"
     
       REVISION "200502210000Z" -- 21 February 2005 
       DESCRIPTION "Version 8:  Added correct range for rcBanRingSaRbsBanPort"
      
       REVISION "200412220000Z" -- 22 December 2004 
       DESCRIPTION "Version 7:  Increased rcCosProfileTblIndex range for feature enhancement"
 	
       REVISION "200412020000Z" -- 02 December 2004 
       DESCRIPTION "Version 6:  Changed rcEsmPortStatsLastSample range to fix CR"

       REVISION "200411110000Z" -- 11 November 2004 
       DESCRIPTION "Version 5:  Cleaned up REVISIONs and fixed typo"

       REVISION "200410200000Z" -- 20 October 2004 
       DESCRIPTION "Version 4:  Updated rcTlsUniIpServiceTable for OE
                                Added rcTlsUniIpServiceStatsTable for OE
                                Added rcBanDhRingTablefor ESU Dual Homing Ring"

       REVISION "200410040000Z" -- 04 October 2004 
       DESCRIPTION "Version 3:  Added rorc1000BaseTX, rc100BaseTXPOE, rcGbicBx
                                to rcTlsEsmGroupLegacyType"  

       REVISION "200406250000Z" -- 25 June 2004 
       DESCRIPTION "Version 2:  Added rcTlsTdiSecMappedVlan, 
                                Added Egress attributes to rcTlsTdiEndptTable
                                Added TDI and Endpt stats attributes to
                                      rcTlsTdiStatsTable and rcTlsEndptStatsTable,
                                Added new MIB table rcTlsUniIpServiceTable for
                                      Ip Mcast feaure
                                Added new attributes to rcCosProfileTable"
       ::= { rcTls 0 }


-- TLSTDI Table

rcTlsTdiTable OBJECT-TYPE
        SYNTAX        SEQUENCE OF RcTlsTdiEntry
        MAX-ACCESS    not-accessible
        STATUS        current
        DESCRIPTION   ""
        ::= { rcTls 1 }
 
rcTlsTdiEntry OBJECT-TYPE
        SYNTAX        RcTlsTdiEntry
        MAX-ACCESS    not-accessible
        STATUS        current
        DESCRIPTION   "A TlsTdi (IPLT) table entry."
        INDEX         {  rcTlsTdiId }
        ::= { rcTlsTdiTable 1 }
 
RcTlsTdiEntry ::=
        SEQUENCE {
                rcTlsTdiId                    INTEGER,
                rcTlsTdiName                  DisplayString,
                rcTlsTdiMappedVlan            INTEGER,
                rcTlsTdiMuxMode               INTEGER,	
                rcTlsTdiADMEnabled            EnableValue,
                rcTlsTdiAction                INTEGER,
                rcTlsTdiAdminState            INTEGER,
                rcTlsTdiRowStatus             RowStatus,
                rcTlsTdiNumDestUniAddr        Integer32,
		rcTlsTdiDestUniAddr           OCTET STRING,
		rcTlsTdiMgmt                  EnableValue,
		rcTlsTdiSecMappedVlan         INTEGER,
		rcTlsTdiEncapsulation	      INTEGER,
                rcTlsTdiMdName		      DisplayString,
                rcTlsTdiMaName		      DisplayString,
                rcTlsTdiPbtEnable	      EnableValue,
                rcTlsTdiVboEnable	      EnableValue,
		rcTlsTdiMacTblSize            INTEGER,
                rcTlsTdiMacTblWaterMk         INTEGER,
                rcTlsTdiMacAgeTimer           INTEGER,
                rcTlsTdiForceDelete           TruthValue,
		rcTlsTdiClearVboStats	      TruthValue
       }

rcTlsTdiId OBJECT-TYPE
        SYNTAX        INTEGER (1..16777215)
        MAX-ACCESS    read-only
        STATUS        current
        DESCRIPTION   "Transparent Domaine Identifier."
        ::= { rcTlsTdiEntry 1 }
 
rcTlsTdiName OBJECT-TYPE
        SYNTAX        DisplayString (SIZE (0..25)) 
        MAX-ACCESS    read-write
        STATUS        current
        DESCRIPTION   "Name of Transparent Domaine."
        ::= { rcTlsTdiEntry 2 }
 
rcTlsTdiMappedVlan OBJECT-TYPE
        SYNTAX        INTEGER (1..4094)
        MAX-ACCESS    read-write
        STATUS        current
        DESCRIPTION   "Vlan Tag used to distribute IPLT packets."
	DEFVAL        { 1 }	
        ::= { rcTlsTdiEntry 3 }

rcTlsTdiMuxMode  OBJECT-TYPE 
	 SYNTAX        INTEGER {
                         oneToone(1),       -- Only one qtag as member
                         manyToOne(2)       -- Many qtags as member
                        }
        MAX-ACCESS    read-write
        STATUS        current
        DESCRIPTION   "An end point for this TDI can have many qtags mapped to it 
		       only if the MuxMode is set to manyToOne.For a mantToOne Tdi
	               there will not be any remapping og qtags at the local egress."
        DEFVAL        { oneToone }
        ::= { rcTlsTdiEntry 4 }

rcTlsTdiADMEnabled OBJECT-TYPE
        SYNTAX        EnableValue
        MAX-ACCESS    read-write
        STATUS        current
        DESCRIPTION   "This Tdi will be included in the ADM message
                       only if this attribute is set."
	DEFVAL        { enable }
        ::= { rcTlsTdiEntry 5 }

rcTlsTdiAction  OBJECT-TYPE 
	 SYNTAX        INTEGER {
                         none(1),            -- none of the following
                         flushMacFdb(2)     -- flush MAC forwarding table
                        }
        MAX-ACCESS    read-write
        STATUS        current
        DESCRIPTION   "TDI related action- Flush Learned MAC addresses."
        DEFVAL        { none }
        ::= { rcTlsTdiEntry 6 }

rcTlsTdiAdminState OBJECT-TYPE
        SYNTAX        INTEGER{
                         enable(1),
                         disable(2),
                         forceDisable(3)
                      }
        MAX-ACCESS    read-write
        STATUS        current
        DESCRIPTION   "Administratively enable or disable a TDI."
	DEFVAL        { disable }
        ::= { rcTlsTdiEntry 7 }

rcTlsTdiRowStatus OBJECT-TYPE
        SYNTAX        RowStatus
        MAX-ACCESS    read-write
        STATUS        current
        DESCRIPTION   "Uses for controlling the creation and
                       deletion of this row."
        ::= { rcTlsTdiEntry 8 }

rcTlsTdiNumDestUniAddr   OBJECT-TYPE
	SYNTAX        Integer32	
	MAX-ACCESS    read-only
        STATUS        current
        DESCRIPTION   "number of Destination Uni Addreess in TDI"
        ::= { rcTlsTdiEntry 9 }

rcTlsTdiDestUniAddr   OBJECT-TYPE
	SYNTAX        OCTET STRING (SIZE(320))	
	MAX-ACCESS    read-write
        STATUS        current
        DESCRIPTION   "A list of Destination Uni Addreess, 4 byte per uni 
		       address. Up to 80 destination uni"
        ::= { rcTlsTdiEntry 10 }

rcTlsTdiMgmt OBJECT-TYPE
        SYNTAX        EnableValue
        MAX-ACCESS    read-write
        STATUS        current
        DESCRIPTION   "Enable/Disable TDI to a Mgmt TDI"
	DEFVAL        { disable }
        ::= { rcTlsTdiEntry 11 }

rcTlsTdiSecMappedVlan OBJECT-TYPE
        SYNTAX        INTEGER (1..4094)
        MAX-ACCESS    read-write
        STATUS        current
        DESCRIPTION   "Secondary Vlan Tag used to distribute IPLT packets."
	DEFVAL        { 1 }	
        ::= { rcTlsTdiEntry 12 }

rcTlsTdiEncapsulation  OBJECT-TYPE 
	 SYNTAX        INTEGER {
                         oel2(1),       -- OEL2
                         mim(2)         -- MAC in MAC
                        }
        MAX-ACCESS    read-write
        STATUS        current
        DESCRIPTION   "Encapsulation to specify the use of TDI is for eith oel2 or 
                       mim (Mac In Mac) feature"
        DEFVAL        { oel2 }
        ::= { rcTlsTdiEntry 13 }

rcTlsTdiMdName OBJECT-TYPE
        SYNTAX        DisplayString (SIZE (0..255)) 
        MAX-ACCESS    read-write
        STATUS        current
        DESCRIPTION   "Maintenance Domain Name if it is used for the PBT purpose"
        ::= { rcTlsTdiEntry 14 }

rcTlsTdiMaName OBJECT-TYPE
        SYNTAX        DisplayString (SIZE (0..255)) 
        MAX-ACCESS    read-write
        STATUS        current
        DESCRIPTION   "Maintenance Association Name if it is used for the PBT purpose"
        ::= { rcTlsTdiEntry 15 }

rcTlsTdiPbtEnable OBJECT-TYPE
        SYNTAX        EnableValue
        MAX-ACCESS    read-write
        STATUS        obsolete
        DESCRIPTION   "PBT functionality enable on this TDI"
	DEFVAL        { disable }
        ::= { rcTlsTdiEntry 16 }

rcTlsTdiVboEnable OBJECT-TYPE
        SYNTAX        EnableValue
        MAX-ACCESS    read-write
        STATUS        current
        DESCRIPTION   "enable/disable Vpls Broadcast Optimization on this TDI"
	DEFVAL        { disable }
        ::= { rcTlsTdiEntry 17 }

rcTlsTdiMacTblSize OBJECT-TYPE
        SYNTAX        INTEGER (0..16384)
        MAX-ACCESS    read-write
        STATUS        current
        DESCRIPTION   "The maximum size of the MAC table. No limit if
                       it's set to 0."
        DEFVAL       { 0 }
        ::= { rcTlsTdiEntry 18 }

rcTlsTdiMacTblWaterMk OBJECT-TYPE
        SYNTAX        INTEGER (0..90)
        MAX-ACCESS    read-write
        STATUS        current
        DESCRIPTION   "The Low Water Mark for MAC table size. Set to 90%
                       of the table size, can be over-written."
        DEFVAL       { 0 }
        ::= { rcTlsTdiEntry 19 }

rcTlsTdiMacAgeTimer OBJECT-TYPE
        SYNTAX        INTEGER (1..65535)
        MAX-ACCESS    read-write
        STATUS        current
        DESCRIPTION   "Remote MAC address ageout timer in seconds."
        DEFVAL        { 300 }
        ::= { rcTlsTdiEntry 20 }

rcTlsTdiForceDelete   OBJECT-TYPE
        SYNTAX        TruthValue
        MAX-ACCESS    read-write
        STATUS        current
        DESCRIPTION   "Action to delete the TDI and all its
                       associated end-points"
        DEFVAL        { false }
        ::= { rcTlsTdiEntry 21 }

rcTlsTdiClearVboStats OBJECT-TYPE
        SYNTAX        TruthValue
        MAX-ACCESS    read-write
        STATUS        current
        DESCRIPTION   "Clear the Statistics of VPN broadcast optimization."
        DEFVAL        { false }
        ::= { rcTlsTdiEntry 22 }
	
-- TLS UNI Table  

rcTlsUniTable OBJECT-TYPE
        SYNTAX        SEQUENCE OF RcTlsUniEntry
        MAX-ACCESS    not-accessible
        STATUS        current
        DESCRIPTION   ""
        ::= { rcTls 2 }

rcTlsUniEntry OBJECT-TYPE
        SYNTAX        RcTlsUniEntry
        MAX-ACCESS    not-accessible
        STATUS        current
        DESCRIPTION   "LPE UNI table entry."
        INDEX         { rcTlsUniAddr }
        ::= { rcTlsUniTable 1 }

RcTlsUniEntry ::=
        SEQUENCE {
                rcTlsUniAddr              IpAddress,
                rcTlsUniPort              InterfaceIndex,
                rcTlsUniServiceType       INTEGER,
                rcTlsUniRingId            INTEGER,
                rcTlsUniRbsId             Integer32,
                rcTlsUniRbsPort           INTEGER,
                rcTlsUniQinqEtherType     OCTET STRING,
		rcTlsUniServerPort	  InterfaceIndex,
                rcTlsUniAdminState        INTEGER,
                rcTlsUniOperState         INTEGER,
                rcTlsUniRowStatus         RowStatus,
		rcTlsUniName              DisplayString,
		rcTlsUniStandaloneRbsId   Integer32,
		rcTlsUniStandaloneRbsPort INTEGER,
                rcTlsUniMltId             INTEGER,
                rcTlsUniForceDelete       TruthValue
        }

rcTlsUniAddr OBJECT-TYPE
        SYNTAX        IpAddress 
        MAX-ACCESS    read-only
        STATUS        current
        DESCRIPTION   "Address of this Uni Instance, it should be no 
                       more than 24 bits."
        ::= { rcTlsUniEntry 1 }

rcTlsUniPort OBJECT-TYPE
        SYNTAX        InterfaceIndex
        MAX-ACCESS    read-write
        STATUS        current
        DESCRIPTION   "BAN port where the UNI is a member."
        ::= { rcTlsUniEntry 2 }

rcTlsUniServiceType  OBJECT-TYPE
        SYNTAX         INTEGER {
                          tlstransparent (1),
                          tlsswitched(2),
		          ipmcuni(3),
			  ipmcbi(4),
			  qnq1(5),
			  qnq2(6)
                         } 
        MAX-ACCESS     read-write 
        STATUS         current
        DESCRIPTION    "Uni service type for the end-point. It is also
			releated with rcPortServiceType ."
        DEFVAL         { tlsswitched }
        ::= { rcTlsUniEntry 3 }

rcTlsUniRingId OBJECT-TYPE
        SYNTAX        INTEGER(0..254)
        MAX-ACCESS    read-write
        STATUS        current
        DESCRIPTION   "Ring ID where the UNI is a member."
	DEFVAL       { 0 }	
        ::= { rcTlsUniEntry 4 }

rcTlsUniRbsId OBJECT-TYPE
        SYNTAX        Integer32 (0..30)
        MAX-ACCESS    read-write
        STATUS        current
        DESCRIPTION   "RBS Module ID where the UNI is a member. 
                       Applicable only if rcTlsUniPort is part of an
                       RBS ring."
	DEFVAL       { 0 }
        ::= { rcTlsUniEntry 5 }

rcTlsUniRbsPort OBJECT-TYPE
        SYNTAX        INTEGER (0..28)
        MAX-ACCESS    read-write
        STATUS        current
        DESCRIPTION   "RBS port number where the UNI is a member.
                       Applicable only if rcTlsUniPort is part of an
                       RBS ring."
	DEFVAL        { 0 }
        ::= { rcTlsUniEntry 6 }


rcTlsUniQinqEtherType OBJECT-TYPE
        SYNTAX        OCTET STRING (SIZE(4))
        MAX-ACCESS    read-write
        STATUS        current
        DESCRIPTION   "The qinq ether type value. The string represents the hex value of ethert ype, e.g. 8600"
        DEFVAL       { "00:00:80:20"  }
        ::= { rcTlsUniEntry 7 }

rcTlsUniServerPort OBJECT-TYPE
        SYNTAX        InterfaceIndex
        MAX-ACCESS    read-write
        STATUS        current
        DESCRIPTION   "Server port associated with the legacy  UNI. 
			Valid only if rcTlsUniPort is an OPM server port."
        ::= { rcTlsUniEntry 8 }

rcTlsUniAdminState OBJECT-TYPE
        SYNTAX        INTEGER {
                         enable(1), 
                         disable(2),
                         forcedisable(3)
                      }
        MAX-ACCESS    read-write
        STATUS        current
        DESCRIPTION   "Value indicating whether the UNI is enabled"
        DEFVAL        { disable }
        ::= { rcTlsUniEntry 9 }

rcTlsUniOperState OBJECT-TYPE
        SYNTAX        INTEGER { 
                          up(1), 
                          down(2) 
                       }
        MAX-ACCESS    read-only
        STATUS        current
        DESCRIPTION   "The current operational state of this UNI."
        ::= { rcTlsUniEntry 10 }

rcTlsUniRowStatus   OBJECT-TYPE
        SYNTAX        RowStatus
        MAX-ACCESS    read-write
        STATUS        current
        DESCRIPTION   "Used for controlling the creation and deletion
                       of this row."
        ::= { rcTlsUniEntry 11}

rcTlsUniName OBJECT-TYPE
        SYNTAX        DisplayString (SIZE (0..25)) 
        MAX-ACCESS    read-write
        STATUS        current
        DESCRIPTION   "Name of UNI. By default, It is UNI-<uni id>"
        ::= { rcTlsUniEntry 12 }

rcTlsUniStandaloneRbsId OBJECT-TYPE
        SYNTAX        Integer32 (0..30)
        MAX-ACCESS    read-write
        STATUS        current
        DESCRIPTION   "Standalone Module ID where the UNI is a member. 
                       Applicable only if rcTlsUniPort is part of the UNI."
	DEFVAL       { 0 }
        ::= { rcTlsUniEntry 13 }

rcTlsUniStandaloneRbsPort OBJECT-TYPE
        SYNTAX        INTEGER (0..28)
        MAX-ACCESS    read-write
        STATUS        current
        DESCRIPTION   "RBS port number where the UNI is a member.
                       Applicable only if rcTlsUniPort is part of the UNI"
	DEFVAL        { 0 }
        ::= { rcTlsUniEntry 14 } 
rcTlsUniMltId OBJECT-TYPE
        SYNTAX        INTEGER (0..256)
        MAX-ACCESS    read-write
        STATUS        current
        DESCRIPTION   "MLT Id of the UNI"
        DEFVAL        { 0 }
        ::= { rcTlsUniEntry 15 } 

rcTlsUniForceDelete   OBJECT-TYPE
        SYNTAX        TruthValue
        MAX-ACCESS    read-write
        STATUS        current
        DESCRIPTION   "Action to delete the UNI, and all its
                       associated end-points"
        DEFVAL        { false }
        ::= { rcTlsUniEntry 16 }


-- TLSTDI EndPoint Table

rcTlsTdiEndptTable OBJECT-TYPE
        SYNTAX        SEQUENCE OF RcTlsTdiEndptEntry
        MAX-ACCESS    not-accessible
        STATUS        current
        DESCRIPTION   ""
        ::= { rcTls 3 }
 
rcTlsTdiEndptEntry OBJECT-TYPE
        SYNTAX        RcTlsTdiEndptEntry
        MAX-ACCESS    not-accessible
        STATUS        current
        DESCRIPTION   "A TlsTdiEndpt (IPLT) table entry."
        INDEX         { rcTlsTdiEndptTdId, rcTlsTdiEndptUniAddr }
        ::= { rcTlsTdiEndptTable 1 }
 
RcTlsTdiEndptEntry ::=
        SEQUENCE {
                rcTlsTdiEndptTdId                  Integer32,
                rcTlsTdiEndptUniAddr               IpAddress,	
		rcTlsTdiEndptQtags                 OCTET STRING,
                rcTlsTdiEndptAdminState            EnableValue,
                rcTlsTdiEndptConMode               INTEGER,
                rcTlsTdiEndptHubUniAddr            IpAddress,
                rcTlsTdiEndptMacAddr               MacAddress,
                rcTlsTdiEndptCosProfileName        DisplayString,
                rcTlsTdiEndptPriMapping            OCTET STRING,
		rcTlsTdiEndptName 		   DisplayString,
                rcTlsTdiEndptMacTblSize            Integer32,
                rcTlsTdiEndptMacTblWaterMk         Integer32,
                rcTlsTdiEndptRemoteMacAgeTimer     Integer32,
                rcTlsTdiEndptLocalMacAgeTimer      Integer32,
                rcTlsTdiEndptOperState             INTEGER,
                rcTlsTdiEndptPriOverride           TruthValue,
              	rcTlsTdiEndptBpduTraffic           INTEGER,
                rcTlsTdiEndptAction                INTEGER,
                rcTlsTdiEndptRowStatus             RowStatus,
                rcTlsTdiEndptOuterQtag              Integer32,
		rcTlsTdiEndptNumQtagIds            Integer32,
		rcTlsTdiEndptEgressCosProfileName  DisplayString,
		rcTlsTdiEndptIngressPolicer        EnableValue,
		rcTlsTdiEndptEgressPolicer         EnableValue,
                rcTlsTdiEndptMepId                  Integer32,
                rcTlsTdiEndptServiceGroup          DisplayString,
                rcTlsTdiEndptCcmOperStatus         INTEGER,
                rcTlsTdiEndptIngressMirrorState    EnableValue,
                rcTlsTdiEndptEgressMirrorState     EnableValue,
                rcTlsTdiEndptTrunkGroup            DisplayString,
		rcTlsTdiEndptPolicingOption	   INTEGER,
                rcTlsTdiEndptPriOverrideType       INTEGER,
                rcTlsTdiEndptColorBasedRemarking   EnableValue,
                rcTlsTdiEndptDropRedColorPackets   TruthValue,
                rcTlsTdiEndptDefaultTdi            EnableValue,
		rcTlsTdiEndptUserLabel1	         OCTET STRING,
	        rcTlsTdiEndptUserLabel2	         OCTET STRING,
                rcTlsTdiEndptL2ptMacSwapCdp        EnableValue,
                rcTlsTdiEndptL2ptMacSwapVtp        EnableValue,
                rcTlsTdiEndptL2ptMacSwapStp        EnableValue,
		rcTlsTdiEndptDEDecodeScheme	   INTEGER,
		rcTlsTdiEndptPcpDecodeMap	   OCTET STRING,
                                    rcTlsTdiEndptL2cpProfile           DisplayString
       }

 rcTlsTdiEndptTdId OBJECT-TYPE
        SYNTAX        Integer32 (1..16777215)
        MAX-ACCESS    read-only
        STATUS        current
        DESCRIPTION   "Tdi that the end-point is a member of."
        ::= { rcTlsTdiEndptEntry 1 }

rcTlsTdiEndptUniAddr OBJECT-TYPE
        SYNTAX        IpAddress
        MAX-ACCESS    read-only
        STATUS        current
        DESCRIPTION   "Uni Address of the end-point."
        ::= { rcTlsTdiEndptEntry 2 }

rcTlsTdiEndptQtags  OBJECT-TYPE
        SYNTAX        OCTET STRING (SIZE(512))
        MAX-ACCESS    read-write  
        STATUS        current
        DESCRIPTION  "A bitfield used to identify which QTAG is 
		      includes in this end point.	
		      The Most significant Bit field (bit 0) set represents 
		      the Qtag 1; The Less significant Bit field (bit 4095) 
		      set repesents the Qtag 4096,"
        ::= { rcTlsTdiEndptEntry 3 }

rcTlsTdiEndptAdminState OBJECT-TYPE
        SYNTAX        EnableValue
        MAX-ACCESS    read-write
        STATUS        current
        DESCRIPTION   "Admin control of the end-point state."
	DEFVAL        { disable }
        ::= { rcTlsTdiEndptEntry 4 }
 
rcTlsTdiEndptConMode OBJECT-TYPE
        SYNTAX        INTEGER {
                          any2any (0),
                          hub     (1),
                          spoke   (2),
                          pt2pt   (3)
                         } 
        MAX-ACCESS    read-write
        STATUS        current
        DESCRIPTION   "Type of end-point"
        DEFVAL       { any2any }
        ::= { rcTlsTdiEndptEntry 5 }
 
rcTlsTdiEndptHubUniAddr OBJECT-TYPE
        SYNTAX        IpAddress
        MAX-ACCESS    read-write
        STATUS        current
        DESCRIPTION   "Hub Uni address if connection mode (ConnMode) is
                       spoke. If the connection mode is pt2pt then this
                       is the Uni address of the other end-point."
        ::= { rcTlsTdiEndptEntry 6 }
 
rcTlsTdiEndptMacAddr OBJECT-TYPE
        SYNTAX        MacAddress
        MAX-ACCESS    read-write
        STATUS        current
        DESCRIPTION   "Hub OPM Mac address if connectio mode is spoke.
                       if the connection mode is pt2pt theb this is 
                       the OPM Mac address of the other end-point."
        ::= { rcTlsTdiEndptEntry 7 }
 
rcTlsTdiEndptCosProfileName OBJECT-TYPE
        SYNTAX        DisplayString (SIZE (0..20)) 
        MAX-ACCESS    read-write
        STATUS        current
        DESCRIPTION   "COS Profile Table Name."
        DEFVAL       { "DEFAULT_PROFILE"  } 
        ::= { rcTlsTdiEndptEntry 8 }
 
rcTlsTdiEndptPriMapping OBJECT-TYPE
        SYNTAX        OCTET STRING (SIZE(8))
        MAX-ACCESS    read-write
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcTlsTdiEndptEntry 9 }

rcTlsTdiEndptName OBJECT-TYPE
        SYNTAX        DisplayString (SIZE (0..30)) 
        MAX-ACCESS    read-write
        STATUS        current
        DESCRIPTION   "Name of Endpoint, By default, it would be EP-<tdi>.<uni>.
		       Example: tdi = 1, uni = 0.0.0.1, rcTlsTdiEndptName would
		       be EP-1.0.0.0.1"
        ::= { rcTlsTdiEndptEntry 10 }

rcTlsTdiEndptMacTblSize OBJECT-TYPE
        SYNTAX        Integer32 (0..97000) 
        MAX-ACCESS    read-write
        STATUS        current
        DESCRIPTION   "The maximum size of the MAC table. No limit if
                       it's set to 0."
        DEFVAL       { 0 }
        ::= { rcTlsTdiEndptEntry 11 }
 
rcTlsTdiEndptMacTblWaterMk OBJECT-TYPE
        SYNTAX        Integer32 (0..90)
        MAX-ACCESS    read-write
        STATUS        current
        DESCRIPTION   "The Low Water Mark for MAC table size. Set to 90%
                       of the table size, can be over-written."
        DEFVAL       { 0 }
        ::= { rcTlsTdiEndptEntry 12 }
 
rcTlsTdiEndptRemoteMacAgeTimer OBJECT-TYPE
        SYNTAX        Integer32(1..65535)
        MAX-ACCESS    read-write
        STATUS        current
        DESCRIPTION   "Remote MAC address ageout timer in seconds."
	DEFVAL        { 300 }
        ::= { rcTlsTdiEndptEntry 13 }
 
rcTlsTdiEndptLocalMacAgeTimer OBJECT-TYPE
        SYNTAX        Integer32 (1..65535)
        MAX-ACCESS    read-write
        STATUS        current
        DESCRIPTION   "Local MAC address ageout timer in seconds."
	DEFVAL        { 300 }
        ::= { rcTlsTdiEndptEntry 14 }
 
rcTlsTdiEndptOperState OBJECT-TYPE
        SYNTAX        INTEGER { 
                          up(1), 
                          down(2),
                          transport-down(3) 
                       }
        MAX-ACCESS    read-only
        STATUS        current
        DESCRIPTION   "The current operational state of this ENDPOINT."
        ::= { rcTlsTdiEndptEntry 15 }

rcTlsTdiEndptPriOverride  OBJECT-TYPE
        SYNTAX          TruthValue
        MAX-ACCESS      read-write
        STATUS          current
        DESCRIPTION     "Enable or disable to override the Priority Mapping."
        DEFVAL          { false }
        ::= { rcTlsTdiEndptEntry 16 }

rcTlsTdiEndptBpduTraffic  OBJECT-TYPE
        SYNTAX          INTEGER {
			normal(1),
			expedite(2),
			drop(3)
			}
        MAX-ACCESS      read-write
        STATUS          current
        DESCRIPTION     "Bpdu traffic control."
        DEFVAL          { normal }
        ::= { rcTlsTdiEndptEntry 17 }

rcTlsTdiEndptAction  OBJECT-TYPE 
	 SYNTAX        INTEGER {
                         none(1),            -- none of the following
                         flushMacFdb(2)     -- flush MAC forwarding table
                        }
        MAX-ACCESS    read-write
        STATUS        current
        DESCRIPTION   "EndPt  related action- Flush Learned MAC addresses."
        DEFVAL        { none }
        ::= { rcTlsTdiEndptEntry 18 }

rcTlsTdiEndptRowStatus OBJECT-TYPE
        SYNTAX        RowStatus
        MAX-ACCESS    read-write
        STATUS        current
        DESCRIPTION   "Uses for controlling the creation and
                       deletion of this row."
        ::= { rcTlsTdiEndptEntry 19 }

rcTlsTdiEndptOuterQtag OBJECT-TYPE
        SYNTAX        Integer32 (0..4094) 
        MAX-ACCESS    read-write
        STATUS        current
        DESCRIPTION   "Outer qtag for QingQ"
	DEFVAL        { 0 }
        ::= { rcTlsTdiEndptEntry 20 }

rcTlsTdiEndptNumQtagIds OBJECT-TYPE
        SYNTAX        	Integer32
        MAX-ACCESS      read-only
        STATUS        	current
        DESCRIPTION   	"Used to indicate the number of Qtag IDs that
                      	are stored in the rcTlsTdiEndptQtags variable."
        ::= { rcTlsTdiEndptEntry 21 }

rcTlsTdiEndptEgressCosProfileName OBJECT-TYPE
        SYNTAX        DisplayString (SIZE (0..20)) 
        MAX-ACCESS    read-write
        STATUS        current
        DESCRIPTION   "Egress COS Profile Table Name."
        DEFVAL       { "DEFAULT_PROFILE"  } 
        ::= { rcTlsTdiEndptEntry 22 }

rcTlsTdiEndptIngressPolicer OBJECT-TYPE
        SYNTAX        EnableValue
        MAX-ACCESS    read-write
        STATUS        current
        DESCRIPTION   "Enable/disable to use Ingress Cos Profile table 
			(rcTlsTdiEndptCosProfileName) "
	DEFVAL        { enable }
        ::= { rcTlsTdiEndptEntry 23 }

rcTlsTdiEndptEgressPolicer OBJECT-TYPE
        SYNTAX        EnableValue
        MAX-ACCESS    read-write
        STATUS        current
        DESCRIPTION   "Enable/disable to use Egress Cos Profile table 
			(rcTlsTdiEndptEgressCosProfileName) "
	DEFVAL        { enable }
        ::= { rcTlsTdiEndptEntry 24 }

rcTlsTdiEndptMepId OBJECT-TYPE
        SYNTAX        Integer32 (0..8191)
        MAX-ACCESS    read-write
        STATUS        current
        DESCRIPTION   "Maintenance Endpoint ID, range 1-8191 is valid MepId
			to be assigned to the Tdi Endpoint. '0' means 
			unassigned Med ID from Tdi Endpoint"
        ::= { rcTlsTdiEndptEntry 25 }

rcTlsTdiEndptServiceGroup OBJECT-TYPE
        SYNTAX        DisplayString (SIZE (0..20)) 
        MAX-ACCESS    read-write
        STATUS        current
        DESCRIPTION   "service group name"
        ::= { rcTlsTdiEndptEntry 26 }

rcTlsTdiEndptCcmOperStatus OBJECT-TYPE
        SYNTAX        INTEGER { 
                          up(1), 
                          down(2)
                       }
        MAX-ACCESS    read-only
        STATUS        current
        DESCRIPTION   "The current CCM operational status of this endpoint."
        ::= { rcTlsTdiEndptEntry 27 }

rcTlsTdiEndptIngressMirrorState OBJECT-TYPE
        SYNTAX        EnableValue
        MAX-ACCESS    read-write
        STATUS        current
        DESCRIPTION    "disable/enable ingress mirroring on this end-point."
        DEFVAL        { disable }
        ::= { rcTlsTdiEndptEntry 28 }

rcTlsTdiEndptEgressMirrorState OBJECT-TYPE
        SYNTAX        EnableValue
        MAX-ACCESS    read-write
        STATUS        current
        DESCRIPTION    "disable/enable egress mirroring on this end-point."
        DEFVAL        { disable }
        ::= { rcTlsTdiEndptEntry 29 }

rcTlsTdiEndptTrunkGroup OBJECT-TYPE
        SYNTAX        DisplayString (SIZE (0..32)) 
        MAX-ACCESS    read-write
        STATUS        obsolete
        DESCRIPTION   "trunk group name"
        ::= { rcTlsTdiEndptEntry 30 }

rcTlsTdiEndptPolicingOption OBJECT-TYPE
	SYNTAX    INTEGER { 
		    preEncap(1), 
		    postEncap(2)
		  }
	MAX-ACCESS   	 read-write
	STATUS       	 current
	DESCRIPTION	"Specify whether the policing is 
			 pre-encapsulation or post-encapsulation 
			 for TDI Endpoints."
      ::= { rcTlsTdiEndptEntry 31 }

rcTlsTdiEndptPriOverrideType OBJECT-TYPE
        SYNTAX        INTEGER
                      {
                         tos(1),
                         dscp(2),
			 mplsexp(3)
                      }
        MAX-ACCESS    read-write
        STATUS        current
        DESCRIPTION   "This field indicated whether ToS or DSCP should be
                       used to override P bit when override is enabled."
        DEFVAL        { tos }
        ::= { rcTlsTdiEndptEntry 32 }

rcTlsTdiEndptColorBasedRemarking OBJECT-TYPE
        SYNTAX        EnableValue
        MAX-ACCESS    read-write
        STATUS        current
        DESCRIPTION   "disable/enable color-based egress mapping for this
                      end-point."
        DEFVAL        { disable }
        ::= { rcTlsTdiEndptEntry 33 }

rcTlsTdiEndptDropRedColorPackets OBJECT-TYPE
        SYNTAX        TruthValue
        MAX-ACCESS    read-write
        STATUS        current
        DESCRIPTION   "disable/enable dropping of red-colored packets for
                      this end-point if color-based mapping is used."
        DEFVAL        { true }
        ::= { rcTlsTdiEndptEntry 34}

rcTlsTdiEndptDefaultTdi OBJECT-TYPE
        SYNTAX        EnableValue
        MAX-ACCESS    read-write
        STATUS        current
        DESCRIPTION    "disable/enable default Tdi."
        DEFVAL        { disable }
        ::= { rcTlsTdiEndptEntry 35 }

rcTlsTdiEndptUserLabel1  OBJECT-TYPE
        SYNTAX          OCTET STRING (SIZE(0..89))
        MAX-ACCESS      read-write
        STATUS          current
        DESCRIPTION     "User provided field. Used to give extra management information/data "
        ::= { rcTlsTdiEndptEntry 36 }

rcTlsTdiEndptUserLabel2  OBJECT-TYPE
 	SYNTAX          OCTET STRING (SIZE(0..89))
        MAX-ACCESS      read-write
        STATUS          current
        DESCRIPTION     "User provided additional field. Used to give extra management information/data "
        ::= { rcTlsTdiEndptEntry 37 }


rcTlsTdiEndptL2ptMacSwapCdp OBJECT-TYPE
        SYNTAX        EnableValue
        MAX-ACCESS    read-write
        STATUS        current
        DESCRIPTION    "disable/enable mac swapping on tdi end-point for CDP protocol"
        DEFVAL        { disable }
        ::= { rcTlsTdiEndptEntry 38 }

rcTlsTdiEndptL2ptMacSwapVtp OBJECT-TYPE
        SYNTAX        EnableValue
        MAX-ACCESS    read-write
        STATUS        current
        DESCRIPTION    "disable/enable mac swapping on tdi end-point for VTP protocol"
        DEFVAL        { disable }
        ::= { rcTlsTdiEndptEntry 39 }

rcTlsTdiEndptL2ptMacSwapStp OBJECT-TYPE
        SYNTAX        EnableValue
        MAX-ACCESS    read-write
        STATUS        current
        DESCRIPTION    "disable/enable mac swapping on tdi end-point for STP protocol"
        DEFVAL        { disable }
        ::= { rcTlsTdiEndptEntry 40 }

rcTlsTdiEndptDEDecodeScheme OBJECT-TYPE
        SYNTAX        INTEGER
		      {
			ad8p0d(1),
			ad7p1d(2),
			ad6p2d(3),
			m7p1d(4),
			m6p2d(5),
			m5p3d(6),
			customPcp(7)
		      }
        MAX-ACCESS    read-write
        STATUS        current
        DESCRIPTION    "This indicates the DE decode 
			scheme that should be used"
        DEFVAL        { ad8p0d }
        ::= { rcTlsTdiEndptEntry 41 }

rcTlsTdiEndptPcpDecodeMap OBJECT-TYPE
        SYNTAX        OCTET STRING (SIZE (8))
        MAX-ACCESS    read-write
        STATUS        current
        DESCRIPTION    "This indicates the Drop Eligibility  
			bit for each priority. The first byte 
			represents the drop eligibility for 
			priority 0. Subsequent bytes represent 
			the drop eligibility of the remaining 
			802.1p priorities. Format is a:b:c:d:e:f:g:h, 
			where 0 <= a, b, c, d, e, f, g, h <=1"
        DEFVAL        { "00:00:00:00:00:00:00:00" }
        ::= { rcTlsTdiEndptEntry 42 }

rcTlsTdiEndptL2cpProfile OBJECT-TYPE    
        SYNTAX        DisplayString (SIZE (0..20))
        MAX-ACCESS    read-write
        STATUS        current
        DESCRIPTION   "l2cp profile associated with this end-point.
                      By default NULL L2CP profile will be associated."
        DEFVAL        { "NULL_L2CP_PROFILE" }
        ::= { rcTlsTdiEndptEntry  43 }

-- TLS REMOTE UNI MAC Table

rcTlsRemoteUniMacTable OBJECT-TYPE
        SYNTAX        SEQUENCE OF RcTlsRemoteUniMacEntry
        MAX-ACCESS    not-accessible
        STATUS        current
        DESCRIPTION   ""
        ::= { rcTls 4 }

rcTlsRemoteUniMacEntry OBJECT-TYPE
        SYNTAX        RcTlsRemoteUniMacEntry
        MAX-ACCESS    not-accessible
        STATUS        current
        DESCRIPTION   " UNI Mac table entry."
        INDEX         { rcTlsRemoteUniAddr }
        ::= { rcTlsRemoteUniMacTable 1 }

RcTlsRemoteUniMacEntry ::=
        SEQUENCE {
                rcTlsRemoteUniAddr           IpAddress,
                rcTlsRemoteUniMacOpm         MacAddress,
                rcTlsRemoteUniMacRowStatus   RowStatus
        }

rcTlsRemoteUniAddr OBJECT-TYPE
        SYNTAX        IpAddress
        MAX-ACCESS    read-only
        STATUS        current
        DESCRIPTION   "Uni address of this instance."
        ::= { rcTlsRemoteUniMacEntry 1 }

rcTlsRemoteUniMacOpm OBJECT-TYPE
        SYNTAX        MacAddress
        MAX-ACCESS    read-write
        STATUS        current
        DESCRIPTION   "Mac address of the OPM port associated with
                       this UNI address."
        ::= { rcTlsRemoteUniMacEntry 2 }

rcTlsRemoteUniMacRowStatus   OBJECT-TYPE
        SYNTAX        RowStatus
        MAX-ACCESS    read-write
        STATUS        current
        DESCRIPTION   "Used for controlling the creation and deletion
                       of this row."
        ::= { rcTlsRemoteUniMacEntry 3 }


-- TLSTDI USER MAC Table

rcTlsTdiUserMacTable OBJECT-TYPE
        SYNTAX        SEQUENCE OF RcTlsTdiUserMacEntry
        MAX-ACCESS    not-accessible
        STATUS        current
        DESCRIPTION   ""
        ::= { rcTls 5 }
 
rcTlsTdiUserMacEntry OBJECT-TYPE
        SYNTAX        RcTlsTdiUserMacEntry
        MAX-ACCESS    not-accessible
        STATUS        current
        DESCRIPTION   "A TlsTdiUserMac table entry."
        INDEX         { rcTlsTdiUserMacTdId, rcTlsTdiUserMacAddr  }
        ::= { rcTlsTdiUserMacTable 1 }
 
RcTlsTdiUserMacEntry ::=
        SEQUENCE {
                rcTlsTdiUserMacTdId       INTEGER,
                rcTlsTdiUserMacAddr       MacAddress,
                rcTlsTdiUserUniAddr       IpAddress,
                rcTlsTdiUserMacRowStatus  RowStatus
       }

rcTlsTdiUserMacTdId OBJECT-TYPE
        SYNTAX        INTEGER (1..16777215)
        MAX-ACCESS    read-only
        STATUS        current
        DESCRIPTION   "TDI Id associated with this user Mac."
        ::= { rcTlsTdiUserMacEntry 1 }
 
rcTlsTdiUserMacAddr OBJECT-TYPE
        SYNTAX        MacAddress
        MAX-ACCESS    read-only
        STATUS        current
        DESCRIPTION   "User Mac address of this instaance."
        ::= { rcTlsTdiUserMacEntry 2 }

rcTlsTdiUserUniAddr OBJECT-TYPE
        SYNTAX        IpAddress
        MAX-ACCESS    read-write
        STATUS        current
        DESCRIPTION   "Uni address associated with this user
                       Mac address."
        ::= { rcTlsTdiUserMacEntry 3 }

rcTlsTdiUserMacRowStatus OBJECT-TYPE
        SYNTAX        RowStatus
        MAX-ACCESS    read-write
        STATUS        current
        DESCRIPTION   "Used for controlling the creation and
                       deletion of this row."
        ::= { rcTlsTdiUserMacEntry 4 }

-- TLSTDI MEMBER UNI Table 

rcTlsTdiMemberUniTable OBJECT-TYPE
        SYNTAX        SEQUENCE OF RcTlsTdiMemberUniEntry
        MAX-ACCESS    not-accessible
        STATUS        current
        DESCRIPTION   ""
        ::= { rcTls 6 }
 
rcTlsTdiMemberUniEntry OBJECT-TYPE
        SYNTAX        RcTlsTdiMemberUniEntry
        MAX-ACCESS    not-accessible
        STATUS        current
        DESCRIPTION   "A TlsTdiMemberUni table entry."
        INDEX         { rcTlsTdiMemberUniTdId, rcTlsTdiMemberUniAddr  }
        ::= { rcTlsTdiMemberUniTable 1 }
 
RcTlsTdiMemberUniEntry ::=
        SEQUENCE {
                rcTlsTdiMemberUniTdId       INTEGER,
                rcTlsTdiMemberUniAddr       IpAddress,
                rcTlsTdiMemberUniRowStatus  RowStatus
       }

rcTlsTdiMemberUniTdId OBJECT-TYPE
        SYNTAX        INTEGER (1..16777215)
        MAX-ACCESS    read-only
        STATUS        current
        DESCRIPTION   "TDI Id associated with this user Mac."
        ::= { rcTlsTdiMemberUniEntry 1 }
 
rcTlsTdiMemberUniAddr OBJECT-TYPE
        SYNTAX        IpAddress
        MAX-ACCESS    read-only
        STATUS        current
        DESCRIPTION   "Uni address associated with this Tdi Member."
        ::= { rcTlsTdiMemberUniEntry 2 }

rcTlsTdiMemberUniRowStatus OBJECT-TYPE
        SYNTAX        RowStatus
        MAX-ACCESS    read-write
        STATUS        current
        DESCRIPTION   "Used for controlling the creation and
                       deletion of this row."
        ::= { rcTlsTdiMemberUniEntry 3 }


--TLSTDI STATS TABLE

rcTlsTdiStatsTable OBJECT-TYPE
        SYNTAX        SEQUENCE OF RcTlsTdiStatsEntry
        MAX-ACCESS    not-accessible
        STATUS        current
        DESCRIPTION   ""
        ::= { rcTls 7 }
 
rcTlsTdiStatsEntry OBJECT-TYPE
        SYNTAX        RcTlsTdiStatsEntry
        MAX-ACCESS    not-accessible
        STATUS        current
        DESCRIPTION   "A TlsTdi Statistics  table entry."
        INDEX         {  rcTlsTdiStatsId }
        ::= { rcTlsTdiStatsTable 1 }
 
RcTlsTdiStatsEntry ::=
        SEQUENCE {
                rcTlsTdiStatsId               INTEGER,
                rcTlsTdiStatsName             DisplayString,
                rcTlsTdiPremRxOctets	       Counter64,	
                rcTlsTdiPremRxDroppedOctets   Counter64,
	        rcTlsTdiGoldRxOctets	       Counter64,	
	        rcTlsTdiGoldRxDroppedOctets   Counter64,
	        rcTlsTdiSilverRxOctets	       Counter64,	
	        rcTlsTdiSilverRxDroppedOctets Counter64,
	        rcTlsTdiStndRxOctets	       Counter64,	
	        rcTlsTdiStndRxDroppedOctets   Counter64,
	        rcTlsTdiPremTxOctets	       Counter64,	
	        rcTlsTdiGoldTxOctets	       Counter64,	
	        rcTlsTdiSilverTxOctets	       Counter64,
	        rcTlsTdiStndTxOctets	       Counter64,	
	        rcTlsTdiPremTxMcastOctets     Counter64,	
                rcTlsTdiGoldTxMcastOctets     Counter64,	
	        rcTlsTdiSilverTxMcastOctets   Counter64,
	        rcTlsTdiStndTxMcastOctets     Counter64,
                rcTlsTdiStatsClear            TruthValue,
		rcTlsTdiPremCongestionDropOctets Counter64,
		rcTlsTdiGoldCongestionDropOctets Counter64,
		rcTlsTdiSilverCongestionDropOctets Counter64,	
		rcTlsTdiStndCongestionDropOctets Counter64,	
		rcTlsTdiPremCirDroppedOctets   Counter64,
		rcTlsTdiPremPirDroppedOctets   Counter64,
		rcTlsTdiGoldCirDroppedOctets   Counter64,
		rcTlsTdiGoldPirDroppedOctets   Counter64,
		rcTlsTdiSilverCirDroppedOctets   Counter64,
		rcTlsTdiSilverPirDroppedOctets   Counter64,
		rcTlsTdiStndCirDroppedOctets   Counter64,
		rcTlsTdiStndPirDroppedOctets   Counter64,
		rcTlsTdiPremTxDroppedOctets	       Counter64,	
	        rcTlsTdiGoldTxDroppedOctets	       Counter64,	
	        rcTlsTdiSilverTxDroppedOctets	       Counter64,
	        rcTlsTdiStndTxDroppedOctets	       Counter64,	
		rcTlsTdiPremTxCongestionDropOctets    Counter64,
		rcTlsTdiGoldTxCongestionDropOctets    Counter64,
		rcTlsTdiSilverTxCongestionDropOctets  Counter64,	
		rcTlsTdiStndTxCongestionDropOctets    Counter64,	
		rcTlsTdiPremTxCirDroppedOctets        Counter64,
		rcTlsTdiPremTxPirDroppedOctets        Counter64,
		rcTlsTdiGoldTxCirDroppedOctets        Counter64,
		rcTlsTdiGoldTxPirDroppedOctets        Counter64,
		rcTlsTdiSilverTxCirDroppedOctets      Counter64,
		rcTlsTdiSilverTxPirDroppedOctets      Counter64,
		rcTlsTdiStndTxCirDroppedOctets        Counter64,
		rcTlsTdiStndTxPirDroppedOctets        Counter64,
		rcTlsTdiRxMcastTotalOctets   	      Counter64,
		rcTlsTdiTxMcastTotalOctets   	      Counter64,
		rcTlsTdiPremRxMcastDroppedOctets      Counter64,
		rcTlsTdiGoldRxMcastDroppedOctets      Counter64,
		rcTlsTdiSilverRxMcastDroppedOctets    Counter64,
		rcTlsTdiStndRxMcastDroppedOctets      Counter64,
		rcTlsTdiPremRxFrames	              Counter64,
                rcTlsTdiPremRxDroppedFrames           Counter64,
                rcTlsTdiGoldRxFrames	              Counter64,
                rcTlsTdiGoldRxDroppedFrames           Counter64,
                rcTlsTdiSilverRxFrames	              Counter64,
                rcTlsTdiSilverRxDroppedFrames         Counter64,
	        rcTlsTdiStndRxFrames	              Counter64,
	        rcTlsTdiStndRxDroppedFrames           Counter64,
	        rcTlsTdiPremTxFrames	              Counter64,
	        rcTlsTdiGoldTxFrames	              Counter64,
	        rcTlsTdiSilverTxFrames	              Counter64,
	        rcTlsTdiStndTxFrames	              Counter64,
	        rcTlsTdiPremTxMcastFrames             Counter64,
                rcTlsTdiGoldTxMcastFrames             Counter64,
                rcTlsTdiSilverTxMcastFrames           Counter64,
	        rcTlsTdiStndTxMcastFrames             Counter64,
                rcTlsTdiPremCongestionDropFrames      Counter64,
		rcTlsTdiGoldCongestionDropFrames      Counter64,
		rcTlsTdiSilverCongestionDropFrames    Counter64,
		rcTlsTdiStndCongestionDropFrames      Counter64,
		rcTlsTdiPremCirDroppedFrames          Counter64,
		rcTlsTdiPremPirDroppedFrames          Counter64,
		rcTlsTdiGoldCirDroppedFrames          Counter64,
		rcTlsTdiGoldPirDroppedFrames          Counter64,
		rcTlsTdiSilverCirDroppedFrames        Counter64,
		rcTlsTdiSilverPirDroppedFrames        Counter64,
		rcTlsTdiStndCirDroppedFrames          Counter64,
		rcTlsTdiStndPirDroppedFrames          Counter64,
	   	rcTlsTdiPremTxDroppedFrames	      Counter64,
	        rcTlsTdiGoldTxDroppedFrames	      Counter64,
	        rcTlsTdiSilverTxDroppedFrames	      Counter64,
	        rcTlsTdiStndTxDroppedFrames	      Counter64,
		rcTlsTdiPremTxCongestionDropFrames    Counter64,
		rcTlsTdiGoldTxCongestionDropFrames    Counter64,
		rcTlsTdiSilverTxCongestionDropFrames  Counter64,
		rcTlsTdiStndTxCongestionDropFrames    Counter64,
		rcTlsTdiPremTxCirDroppedFrames        Counter64,
		rcTlsTdiPremTxPirDroppedFrames        Counter64,
		rcTlsTdiGoldTxCirDroppedFrames        Counter64,
		rcTlsTdiGoldTxPirDroppedFrames        Counter64,
		rcTlsTdiSilverTxCirDroppedFrames      Counter64,
		rcTlsTdiSilverTxPirDroppedFrames      Counter64,
		rcTlsTdiStndTxCirDroppedFrames        Counter64,
		rcTlsTdiStndTxPirDroppedFrames        Counter64,
		rcTlsTdiRxMcastTotalFrames   	      Counter64,
		rcTlsTdiTxMcastTotalFrames   	      Counter64,
		rcTlsTdiPremRxMcastDroppedFrames      Counter64,
		rcTlsTdiGoldRxMcastDroppedFrames      Counter64,
		rcTlsTdiSilverRxMcastDroppedFrames    Counter64,
		rcTlsTdiStndRxMcastDroppedFrames      Counter64,
		rcTlsTdiPremRxCirOctets			Counter64,
		rcTlsTdiPremRxCirOopOctets			Counter64,
		rcTlsTdiPremRxEirOctets			Counter64,
		rcTlsTdiPremRxEirOopOctets			Counter64,
		rcTlsTdiPremRxEirDroppedOctets		Counter64,
		rcTlsTdiPremRxPirOctets			Counter64,
		rcTlsTdiPremRxPirOopOctets			Counter64,
		rcTlsTdiPremRxGreenOctets			Counter64,
		rcTlsTdiPremRxYellowOctets			Counter64,
		rcTlsTdiPremRxRedOctets			Counter64,
		rcTlsTdiGoldRxCirOctets			Counter64,
		rcTlsTdiGoldRxCirOopOctets			Counter64,
		rcTlsTdiGoldRxEirOctets			Counter64,
		rcTlsTdiGoldRxEirOopOctets			Counter64,
		rcTlsTdiGoldRxEirDroppedOctets		Counter64,
		rcTlsTdiGoldRxPirOctets			Counter64,
		rcTlsTdiGoldRxPirOopOctets			Counter64,
		rcTlsTdiGoldRxGreenOctets			Counter64,
		rcTlsTdiGoldRxYellowOctets			Counter64,
		rcTlsTdiGoldRxRedOctets			Counter64,
		rcTlsTdiSilverRxCirOctets			Counter64,
		rcTlsTdiSilverRxCirOopOctets			Counter64,
		rcTlsTdiSilverRxEirOctets			Counter64,
		rcTlsTdiSilverRxEirOopOctets			Counter64,
		rcTlsTdiSilverRxEirDroppedOctets		Counter64,
		rcTlsTdiSilverRxPirOctets			Counter64,
		rcTlsTdiSilverRxPirOopOctets			Counter64,
		rcTlsTdiSilverRxGreenOctets			Counter64,
		rcTlsTdiSilverRxYellowOctets			Counter64,
		rcTlsTdiSilverRxRedOctets			Counter64,
		rcTlsTdiStndRxCirOctets			Counter64,
		rcTlsTdiStndRxCirOopOctets			Counter64,
		rcTlsTdiStndRxEirOctets			Counter64,
		rcTlsTdiStndRxEirOopOctets			Counter64,
		rcTlsTdiStndRxEirDroppedOctets		Counter64,
		rcTlsTdiStndRxPirOctets			Counter64,
		rcTlsTdiStndRxPirOopOctets			Counter64,
		rcTlsTdiStndRxGreenOctets			Counter64,
		rcTlsTdiStndRxYellowOctets			Counter64,
		rcTlsTdiStndRxRedOctets			Counter64,
		rcTlsTdiMcastRxDroppedOctets		Counter64,
		rcTlsTdiBcastUUcastRxTotalOctets		Counter64,
		rcTlsTdiBcastUUcastRxDroppedOctets		Counter64,
		rcTlsTdiPremRxCirFrames			Counter64,
		rcTlsTdiPremRxCirOopFrames			Counter64,
		rcTlsTdiPremRxEirFrames			Counter64,
		rcTlsTdiPremRxEirOopFrames			Counter64,
		rcTlsTdiPremRxEirDroppedFrames		Counter64,
		rcTlsTdiPremRxPirFrames			Counter64,
		rcTlsTdiPremRxPirOopFrames			Counter64,
		rcTlsTdiPremRxGreenFrames			Counter64,
		rcTlsTdiPremRxYellowFrames			Counter64,
		rcTlsTdiPremRxRedFrames			Counter64,
		rcTlsTdiGoldRxCirFrames			Counter64,
		rcTlsTdiGoldRxCirOopFrames			Counter64,
		rcTlsTdiGoldRxEirFrames			Counter64,
		rcTlsTdiGoldRxEirOopFrames			Counter64,
		rcTlsTdiGoldRxEirDroppedFrames		Counter64,
		rcTlsTdiGoldRxPirFrames			Counter64,
		rcTlsTdiGoldRxPirOopFrames			Counter64,
		rcTlsTdiGoldRxGreenFrames			Counter64,
		rcTlsTdiGoldRxYellowFrames			Counter64,
		rcTlsTdiGoldRxRedFrames			Counter64,
		rcTlsTdiSilverRxCirFrames			Counter64,
		rcTlsTdiSilverRxCirOopFrames			Counter64,
		rcTlsTdiSilverRxEirFrames			Counter64,
		rcTlsTdiSilverRxEirOopFrames			Counter64,
		rcTlsTdiSilverRxEirDroppedFrames		Counter64,
		rcTlsTdiSilverRxPirFrames			Counter64,
		rcTlsTdiSilverRxPirOopFrames			Counter64,
		rcTlsTdiSilverRxGreenFrames			Counter64,
		rcTlsTdiSilverRxYellowFrames			Counter64,
		rcTlsTdiSilverRxRedFrames			Counter64,
		rcTlsTdiStndRxCirFrames			Counter64,
		rcTlsTdiStndRxCirOopFrames			Counter64,
		rcTlsTdiStndRxEirFrames			Counter64,
		rcTlsTdiStndRxEirOopFrames			Counter64,
		rcTlsTdiStndRxEirDroppedFrames		Counter64,
		rcTlsTdiStndRxPirFrames			Counter64,
		rcTlsTdiStndRxPirOopFrames			Counter64,
		rcTlsTdiStndRxGreenFrames			Counter64,
		rcTlsTdiStndRxYellowFrames			Counter64,
		rcTlsTdiStndRxRedFrames			Counter64,
		rcTlsTdiMcastRxDroppedFrames		Counter64,
		rcTlsTdiBcastUUcastRxTotalFrames		Counter64,
		rcTlsTdiBcastUUcastRxDroppedFrames		Counter64,
		rcTlsTdiPremTxCirOctets			Counter64,
		rcTlsTdiPremTxCirOopOctets			Counter64,
		rcTlsTdiPremTxEirOctets			Counter64,
		rcTlsTdiPremTxEirOopOctets			Counter64,
		rcTlsTdiPremTxEirDroppedOctets		Counter64,
		rcTlsTdiPremTxPirOctets			Counter64,
		rcTlsTdiPremTxPirOopOctets			Counter64,
		rcTlsTdiPremTxGreenOctets			Counter64,
		rcTlsTdiPremTxYellowOctets			Counter64,
		rcTlsTdiPremTxRedOctets			Counter64,
		rcTlsTdiGoldTxCirOctets			Counter64,
		rcTlsTdiGoldTxCirOopOctets			Counter64,
		rcTlsTdiGoldTxEirOctets			Counter64,
		rcTlsTdiGoldTxEirOopOctets			Counter64,
		rcTlsTdiGoldTxEirDroppedOctets		Counter64,
		rcTlsTdiGoldTxPirOctets			Counter64,
		rcTlsTdiGoldTxPirOopOctets			Counter64,
		rcTlsTdiGoldTxGreenOctets			Counter64,
		rcTlsTdiGoldTxYellowOctets			Counter64,
		rcTlsTdiGoldTxRedOctets			Counter64,
		rcTlsTdiSilverTxCirOctets			Counter64,
		rcTlsTdiSilverTxCirOopOctets			Counter64,
		rcTlsTdiSilverTxEirOctets			Counter64,
		rcTlsTdiSilverTxEirOopOctets			Counter64,
		rcTlsTdiSilverTxEirDroppedOctets		Counter64,
		rcTlsTdiSilverTxPirOctets			Counter64,
		rcTlsTdiSilverTxPirOopOctets			Counter64,
		rcTlsTdiSilverTxGreenOctets			Counter64,
		rcTlsTdiSilverTxYellowOctets			Counter64,
		rcTlsTdiSilverTxRedOctets			Counter64,
		rcTlsTdiStndTxCirOctets			Counter64,
		rcTlsTdiStndTxCirOopOctets			Counter64,
		rcTlsTdiStndTxEirOctets			Counter64,
		rcTlsTdiStndTxEirOopOctets			Counter64,
		rcTlsTdiStndTxEirDroppedOctets		Counter64,
		rcTlsTdiStndTxPirOctets			Counter64,
		rcTlsTdiStndTxPirOopOctets			Counter64,
		rcTlsTdiStndTxGreenOctets			Counter64,
		rcTlsTdiStndTxYellowOctets			Counter64,
		rcTlsTdiStndTxRedOctets			Counter64,
		rcTlsTdiMcastTxDroppedOctets		Counter64,
		rcTlsTdiBcastUUcastTxTotalOctets		Counter64,
		rcTlsTdiBcastUUcastTxDroppedOctets		Counter64,
		rcTlsTdiPremTxCirFrames			Counter64,
		rcTlsTdiPremTxCirOopFrames			Counter64,
		rcTlsTdiPremTxEirFrames			Counter64,
		rcTlsTdiPremTxEirOopFrames			Counter64,
		rcTlsTdiPremTxEirDroppedFrames		Counter64,
		rcTlsTdiPremTxPirFrames			Counter64,
		rcTlsTdiPremTxPirOopFrames			Counter64,
		rcTlsTdiPremTxGreenFrames			Counter64,
		rcTlsTdiPremTxYellowFrames			Counter64,
		rcTlsTdiPremTxRedFrames			Counter64,
		rcTlsTdiGoldTxCirFrames			Counter64,
		rcTlsTdiGoldTxCirOopFrames			Counter64,
		rcTlsTdiGoldTxEirFrames			Counter64,
		rcTlsTdiGoldTxEirOopFrames			Counter64,
		rcTlsTdiGoldTxEirDroppedFrames		Counter64,
		rcTlsTdiGoldTxPirFrames			Counter64,
		rcTlsTdiGoldTxPirOopFrames			Counter64,
		rcTlsTdiGoldTxGreenFrames			Counter64,
		rcTlsTdiGoldTxYellowFrames			Counter64,
		rcTlsTdiGoldTxRedFrames			Counter64,
		rcTlsTdiSilverTxCirFrames			Counter64,
		rcTlsTdiSilverTxCirOopFrames			Counter64,
		rcTlsTdiSilverTxEirFrames			Counter64,
		rcTlsTdiSilverTxEirOopFrames			Counter64,
		rcTlsTdiSilverTxEirDroppedFrames		Counter64,
		rcTlsTdiSilverTxPirFrames			Counter64,
		rcTlsTdiSilverTxPirOopFrames			Counter64,
		rcTlsTdiSilverTxGreenFrames			Counter64,
		rcTlsTdiSilverTxYellowFrames			Counter64,
		rcTlsTdiSilverTxRedFrames			Counter64,
		rcTlsTdiStndTxCirFrames			Counter64,
		rcTlsTdiStndTxCirOopFrames			Counter64,
		rcTlsTdiStndTxEirFrames			Counter64,
		rcTlsTdiStndTxEirOopFrames			Counter64,
		rcTlsTdiStndTxEirDroppedFrames		Counter64,
		rcTlsTdiStndTxPirFrames			Counter64,
		rcTlsTdiStndTxPirOopFrames			Counter64,
		rcTlsTdiStndTxGreenFrames			Counter64,
		rcTlsTdiStndTxYellowFrames			Counter64,
		rcTlsTdiStndTxRedFrames			Counter64,
		rcTlsTdiMcastTxDroppedFrames		Counter64,
		rcTlsTdiBcastUUcastTxTotalFrames		Counter64,
		rcTlsTdiBcastUUcastTxDroppedFrames		Counter64,
		rcTlsTdiDropClassRxDroppedOctets  		Counter64,
		rcTlsTdiDropClassRxDroppedFrames  		Counter64,
		rcTlsTdiDropClassTxDroppedOctets  		Counter64,
		rcTlsTdiDropClassTxDroppedFrames  		Counter64
   	}  

rcTlsTdiStatsId OBJECT-TYPE
        SYNTAX        INTEGER (1..16777215)
        MAX-ACCESS    read-only
        STATUS        current
        DESCRIPTION   "Transparent Domaine Identifier."
        ::= { rcTlsTdiStatsEntry 1 }
 
rcTlsTdiStatsName OBJECT-TYPE
        SYNTAX        DisplayString (SIZE (0..15)) 
        MAX-ACCESS    read-write
        STATUS        current
        DESCRIPTION   "Name of Transparent Domaine."
        ::= { rcTlsTdiStatsEntry 2 }
 
 rcTlsTdiPremRxOctets	OBJECT-TYPE
        SYNTAX        Counter64
        MAX-ACCESS    read-only
        STATUS        current
        DESCRIPTION  "Number of Premium Service Octets received from This End-Point."
        ::= { rcTlsTdiStatsEntry 3 } 

 rcTlsTdiPremRxDroppedOctets	OBJECT-TYPE
        SYNTAX        Counter64
        MAX-ACCESS    read-only
        STATUS        current
        DESCRIPTION  "Number of Premium Service Octets dropped from This End-Point."
        ::= { rcTlsTdiStatsEntry 4 } 
       
 rcTlsTdiGoldRxOctets	OBJECT-TYPE
        SYNTAX        Counter64
        MAX-ACCESS    read-only
        STATUS        current
        DESCRIPTION  "Number of Gold Service Octets received from This End-Point."
        ::= { rcTlsTdiStatsEntry 5 } 

 rcTlsTdiGoldRxDroppedOctets	OBJECT-TYPE
        SYNTAX        Counter64
        MAX-ACCESS    read-only
        STATUS        current
        DESCRIPTION  "Number of Gold Service Octets dropped from This End-Point."
        ::= { rcTlsTdiStatsEntry 6 } 
       

 rcTlsTdiSilverRxOctets	OBJECT-TYPE
        SYNTAX        Counter64
        MAX-ACCESS    read-only
        STATUS        current
        DESCRIPTION  "Number of Silver Service Octets received from This End-Point."
        ::= { rcTlsTdiStatsEntry 7 } 

 rcTlsTdiSilverRxDroppedOctets	OBJECT-TYPE
        SYNTAX        Counter64
        MAX-ACCESS    read-only
        STATUS        current
        DESCRIPTION  "Number of Silver Service Octets dropped from This End-Point."
        ::= { rcTlsTdiStatsEntry 8 } 
       
 rcTlsTdiStndRxOctets	OBJECT-TYPE
        SYNTAX        Counter64
        MAX-ACCESS    read-only
        STATUS        current
        DESCRIPTION  "Number of Standard (Best Effort) Service Octets received from This End-Point."
        ::= { rcTlsTdiStatsEntry 9 } 

 rcTlsTdiStndRxDroppedOctets	OBJECT-TYPE
        SYNTAX        Counter64
        MAX-ACCESS    read-only
        STATUS        current
        DESCRIPTION  "Number of Standard(BestEffort) Service Octets dropped from this End-Point."
        ::= { rcTlsTdiStatsEntry 10 } 
       
 rcTlsTdiPremTxOctets	OBJECT-TYPE
        SYNTAX        Counter64
        MAX-ACCESS    read-only
        STATUS        current
        DESCRIPTION  "Number of Premium Service Octets sent to his End-Point."
        ::= { rcTlsTdiStatsEntry 11 } 

 rcTlsTdiGoldTxOctets	OBJECT-TYPE
        SYNTAX        Counter64
        MAX-ACCESS    read-only
        STATUS        current
        DESCRIPTION  "Number of Gold Service Octets sent to his End-Point."
        ::= { rcTlsTdiStatsEntry 12 } 

 rcTlsTdiSilverTxOctets	OBJECT-TYPE
        SYNTAX        Counter64
        MAX-ACCESS    read-only
        STATUS        current
        DESCRIPTION  "Number of Silver Service Octets sent to his End-Point."
        ::= { rcTlsTdiStatsEntry 13 } 

 rcTlsTdiStndTxOctets	OBJECT-TYPE
        SYNTAX        Counter64
        MAX-ACCESS    read-only
        STATUS        current
        DESCRIPTION  "Number of Standard Service Octets sent to his End-Point."
        ::= { rcTlsTdiStatsEntry 14 } 
		

 rcTlsTdiPremTxMcastOctets	OBJECT-TYPE
        SYNTAX        Counter64
        MAX-ACCESS    read-only
        STATUS        current
        DESCRIPTION  "Number of Premium Service Multicast sent to his End-Point."
        ::= { rcTlsTdiStatsEntry 15 } 

rcTlsTdiGoldTxMcastOctets	OBJECT-TYPE
        SYNTAX        Counter64
        MAX-ACCESS    read-only
        STATUS        current
        DESCRIPTION  "Number of GoldService Multicast sent to his End-Point."
        ::= { rcTlsTdiStatsEntry 16 } 
		

rcTlsTdiSilverTxMcastOctets	OBJECT-TYPE
        SYNTAX        Counter64
        MAX-ACCESS    read-only
        STATUS        current
        DESCRIPTION  "Number of SilverService Multicast sent to his End-Point."
        ::= { rcTlsTdiStatsEntry 17 } 

rcTlsTdiStndTxMcastOctets	OBJECT-TYPE
        SYNTAX        Counter64
        MAX-ACCESS    read-only
        STATUS        current
        DESCRIPTION  "Number of Premium Service Multicast sent to his End-Point."
        ::= { rcTlsTdiStatsEntry 18 } 

rcTlsTdiStatsClear 	OBJECT-TYPE
        SYNTAX        TruthValue
        MAX-ACCESS    read-write
        STATUS        current
        DESCRIPTION   "Clear statistic."
        ::= { rcTlsTdiStatsEntry 19 }

rcTlsTdiPremCongestionDropOctets	OBJECT-TYPE
        SYNTAX        Counter64
        MAX-ACCESS    read-only
        STATUS        current
        DESCRIPTION  "Number of Prem Service Octets congestion drop"
        ::= { rcTlsTdiStatsEntry 20 } 
       
rcTlsTdiGoldCongestionDropOctets	OBJECT-TYPE
        SYNTAX        Counter64
        MAX-ACCESS    read-only
        STATUS        current
        DESCRIPTION  "Number of Gold Service Octets congestion drop"
        ::= { rcTlsTdiStatsEntry 21 } 

rcTlsTdiSilverCongestionDropOctets	OBJECT-TYPE
        SYNTAX        Counter64
        MAX-ACCESS    read-only
        STATUS        current
        DESCRIPTION  "Number of Silver Service Octets congestion drop"
        ::= { rcTlsTdiStatsEntry 22 } 

rcTlsTdiStndCongestionDropOctets	OBJECT-TYPE
        SYNTAX        Counter64
        MAX-ACCESS    read-only
        STATUS        current
        DESCRIPTION  "Number of Standard Service Octets congestion drop"
        ::= { rcTlsTdiStatsEntry 23 }

rcTlsTdiPremCirDroppedOctets	OBJECT-TYPE
        SYNTAX        Counter64
        MAX-ACCESS    read-only
        STATUS        current
        DESCRIPTION  "Number of Prem Service Octets CIR drop"
        ::= { rcTlsTdiStatsEntry 24 }

rcTlsTdiPremPirDroppedOctets	OBJECT-TYPE
        SYNTAX        Counter64
        MAX-ACCESS    read-only
        STATUS        current
        DESCRIPTION  "Number of Prem Service Octets PIR drop"
        ::= { rcTlsTdiStatsEntry 25 }
  
rcTlsTdiGoldCirDroppedOctets	OBJECT-TYPE
        SYNTAX        Counter64
        MAX-ACCESS    read-only
        STATUS        current
        DESCRIPTION  "Number of Gold Service Octets CIR drop"
        ::= { rcTlsTdiStatsEntry 26 }

rcTlsTdiGoldPirDroppedOctets	OBJECT-TYPE
        SYNTAX        Counter64
        MAX-ACCESS    read-only
        STATUS        current
        DESCRIPTION  "Number of Gold Service Octets PIR drop"
        ::= { rcTlsTdiStatsEntry 27 }

rcTlsTdiSilverCirDroppedOctets	OBJECT-TYPE
        SYNTAX        Counter64
        MAX-ACCESS    read-only
        STATUS        current
        DESCRIPTION  "Number of Silver Service Octets CIR drop"
        ::= { rcTlsTdiStatsEntry 28 }

rcTlsTdiSilverPirDroppedOctets	OBJECT-TYPE
        SYNTAX        Counter64
        MAX-ACCESS    read-only
        STATUS        current
        DESCRIPTION  "Number of Silver Service Octets PIR drop"
        ::= { rcTlsTdiStatsEntry 29 }

rcTlsTdiStndCirDroppedOctets	OBJECT-TYPE
        SYNTAX        Counter64
        MAX-ACCESS    read-only
        STATUS        current
        DESCRIPTION  "Number of Standard Service Octets CIR drop"
        ::= { rcTlsTdiStatsEntry 30 }  

rcTlsTdiStndPirDroppedOctets	OBJECT-TYPE
        SYNTAX        Counter64
        MAX-ACCESS    read-only
        STATUS        current
        DESCRIPTION  "Number of Standard Service Octets PIR drop"
        ::= { rcTlsTdiStatsEntry 31 } 

rcTlsTdiPremTxDroppedOctets	OBJECT-TYPE
        SYNTAX        Counter64
        MAX-ACCESS    read-only
        STATUS        current
        DESCRIPTION  "Tx Number of Premium Service Octets dropped from This End-Point."
        ::= { rcTlsTdiStatsEntry 32 } 
       
rcTlsTdiGoldTxDroppedOctets	OBJECT-TYPE
        SYNTAX        Counter64
        MAX-ACCESS    read-only
        STATUS        current
        DESCRIPTION  "Tx Number of Gold Service Octets dropped from This End-Point."
        ::= { rcTlsTdiStatsEntry 33 } 
       
rcTlsTdiSilverTxDroppedOctets	OBJECT-TYPE
        SYNTAX        Counter64
        MAX-ACCESS    read-only
        STATUS        current
        DESCRIPTION  "Tx Number of Silver Service Octets dropped from This End-Point."
        ::= { rcTlsTdiStatsEntry 34 } 
       
rcTlsTdiStndTxDroppedOctets	OBJECT-TYPE
        SYNTAX        Counter64
        MAX-ACCESS    read-only
        STATUS        current
        DESCRIPTION  "Tx Number of Standard(BestEffort) Service Octets dropped from this End-Point."
        ::= { rcTlsTdiStatsEntry 35 } 

rcTlsTdiPremTxCongestionDropOctets	OBJECT-TYPE
        SYNTAX        Counter64
        MAX-ACCESS    read-only
        STATUS        current
        DESCRIPTION  "Number of Prem Service Octets congestion drop"
        ::= { rcTlsTdiStatsEntry 36} 
       
rcTlsTdiGoldTxCongestionDropOctets	OBJECT-TYPE
        SYNTAX        Counter64
        MAX-ACCESS    read-only
        STATUS        current
        DESCRIPTION  "Number of Gold Service Octets congestion drop"
        ::= { rcTlsTdiStatsEntry 37 } 

rcTlsTdiSilverTxCongestionDropOctets	OBJECT-TYPE
        SYNTAX        Counter64
        MAX-ACCESS    read-only
        STATUS        current
        DESCRIPTION  "Number of Silver Service Octets congestion drop"
        ::= { rcTlsTdiStatsEntry 38 } 

rcTlsTdiStndTxCongestionDropOctets	OBJECT-TYPE
        SYNTAX        Counter64
        MAX-ACCESS    read-only
        STATUS        current
        DESCRIPTION  "Number of Standard Service Octets congestion drop"
        ::= { rcTlsTdiStatsEntry 39 }

rcTlsTdiPremTxCirDroppedOctets	OBJECT-TYPE
        SYNTAX        Counter64
        MAX-ACCESS    read-only
        STATUS        current
        DESCRIPTION  "Number of Prem Service Octets CIR drop"
        ::= { rcTlsTdiStatsEntry 40 }

rcTlsTdiPremTxPirDroppedOctets	OBJECT-TYPE
        SYNTAX        Counter64
        MAX-ACCESS    read-only
        STATUS        current
        DESCRIPTION  "Number of Prem Service Octets PIR drop"
        ::= { rcTlsTdiStatsEntry 41 }
  
rcTlsTdiGoldTxCirDroppedOctets	OBJECT-TYPE
        SYNTAX        Counter64
        MAX-ACCESS    read-only
        STATUS        current
        DESCRIPTION  "Number of Gold Service Octets CIR drop"
        ::= { rcTlsTdiStatsEntry 42 }

rcTlsTdiGoldTxPirDroppedOctets	OBJECT-TYPE
        SYNTAX        Counter64
        MAX-ACCESS    read-only
        STATUS        current
        DESCRIPTION  "Number of Gold Service Octets PIR drop"
        ::= { rcTlsTdiStatsEntry 43 }

rcTlsTdiSilverTxCirDroppedOctets	OBJECT-TYPE
        SYNTAX        Counter64
        MAX-ACCESS    read-only
        STATUS        current
        DESCRIPTION  "Number of Silver Service Octets CIR drop"
        ::= { rcTlsTdiStatsEntry 44 }

rcTlsTdiSilverTxPirDroppedOctets	OBJECT-TYPE
        SYNTAX        Counter64
        MAX-ACCESS    read-only
        STATUS        current
        DESCRIPTION  "Number of Silver Service Octets PIR drop"
        ::= { rcTlsTdiStatsEntry 45 }

rcTlsTdiStndTxCirDroppedOctets	OBJECT-TYPE
        SYNTAX        Counter64
        MAX-ACCESS    read-only
        STATUS        current
        DESCRIPTION  "Number of Standard Service Octets CIR drop"
        ::= { rcTlsTdiStatsEntry 46 }  

rcTlsTdiStndTxPirDroppedOctets	OBJECT-TYPE
        SYNTAX        Counter64
        MAX-ACCESS    read-only
        STATUS        current
        DESCRIPTION  "Number of Standard Service Octets PIR drop"
        ::= { rcTlsTdiStatsEntry 47 }  

rcTlsTdiRxMcastTotalOctets   OBJECT-TYPE
        SYNTAX        Counter64
        MAX-ACCESS    read-only
        STATUS        current
        DESCRIPTION  "Rx total Number of Mcast Octet"
        ::= { rcTlsTdiStatsEntry 48 }
  
rcTlsTdiTxMcastTotalOctets  OBJECT-TYPE
        SYNTAX        Counter64
        MAX-ACCESS    read-only
        STATUS        current
        DESCRIPTION  "Tx total Number of Mcast Octet"
        ::= { rcTlsTdiStatsEntry 49 }

rcTlsTdiPremRxMcastDroppedOctets	OBJECT-TYPE
        SYNTAX        Counter64
        MAX-ACCESS    read-only
        STATUS        current
        DESCRIPTION  "Number of Premium Service Rx Mcast Octets dropped from 
		      This TDI."
        ::= { rcTlsTdiStatsEntry 50 } 

rcTlsTdiGoldRxMcastDroppedOctets	OBJECT-TYPE
        SYNTAX        Counter64
        MAX-ACCESS    read-only
        STATUS        current
        DESCRIPTION  "Number of Gold Service Rx Mcast Octets dropped from 
		      This TDI."
        ::= { rcTlsTdiStatsEntry 51 } 

rcTlsTdiSilverRxMcastDroppedOctets	OBJECT-TYPE
        SYNTAX        Counter64
        MAX-ACCESS    read-only
        STATUS        current
        DESCRIPTION  "Number of Silver Service Rx Mcast Octets dropped from 
		      This TDI."
        ::= { rcTlsTdiStatsEntry 52 } 
                            
rcTlsTdiStndRxMcastDroppedOctets	OBJECT-TYPE
        SYNTAX        Counter64
        MAX-ACCESS    read-only
        STATUS        current
        DESCRIPTION  "Number of Standard Service Rx Mcast Octets dropped from 
		      This TDI."
        ::= { rcTlsTdiStatsEntry 53 } 

rcTlsTdiPremRxFrames	OBJECT-TYPE
        SYNTAX        Counter64
        MAX-ACCESS    read-only
        STATUS        current
        DESCRIPTION  "Number of Premium Service Frames received from This End-Point."
        ::= { rcTlsTdiStatsEntry 54 }

rcTlsTdiPremRxDroppedFrames	OBJECT-TYPE
        SYNTAX        Counter64
        MAX-ACCESS    read-only
        STATUS        current
        DESCRIPTION  "Number of Premium Service Frames dropped from This End-Point."
        ::= { rcTlsTdiStatsEntry 55 }

rcTlsTdiGoldRxFrames	OBJECT-TYPE
        SYNTAX        Counter64
        MAX-ACCESS    read-only
        STATUS        current
        DESCRIPTION  "Number of Gold Service Frames received from This End-Point."
        ::= { rcTlsTdiStatsEntry 56 }

rcTlsTdiGoldRxDroppedFrames	OBJECT-TYPE
        SYNTAX        Counter64
        MAX-ACCESS    read-only
        STATUS        current
        DESCRIPTION  "Number of Gold Service Frames dropped from This End-Point."
        ::= { rcTlsTdiStatsEntry 57 }

rcTlsTdiSilverRxFrames	OBJECT-TYPE
        SYNTAX        Counter64
        MAX-ACCESS    read-only
        STATUS        current
        DESCRIPTION  "Number of Silver Service Frames received from This End-Point."
        ::= { rcTlsTdiStatsEntry 58 }

rcTlsTdiSilverRxDroppedFrames	OBJECT-TYPE
        SYNTAX        Counter64
        MAX-ACCESS    read-only
        STATUS        current
        DESCRIPTION  "Number of Silver Service Frames dropped from This End-Point."
        ::= { rcTlsTdiStatsEntry 59 }

rcTlsTdiStndRxFrames	OBJECT-TYPE
        SYNTAX        Counter64
        MAX-ACCESS    read-only
        STATUS        current
        DESCRIPTION  "Number of Standard (Best Effort) Service Frames received from This End-Point."
        ::= { rcTlsTdiStatsEntry 60 }

rcTlsTdiStndRxDroppedFrames	OBJECT-TYPE
        SYNTAX        Counter64
        MAX-ACCESS    read-only
        STATUS        current
        DESCRIPTION  "Number of Standard(BestEffort) Service Frames dropped from this End-Point."
        ::= { rcTlsTdiStatsEntry 61 }

rcTlsTdiPremTxFrames	OBJECT-TYPE
        SYNTAX        Counter64
        MAX-ACCESS    read-only
        STATUS        current
        DESCRIPTION  "Number of Premium Service Frames sent to his End-Point."
        ::= { rcTlsTdiStatsEntry 62 }

rcTlsTdiGoldTxFrames	OBJECT-TYPE
        SYNTAX        Counter64
        MAX-ACCESS    read-only
        STATUS        current
        DESCRIPTION  "Number of Gold Service Frames sent to his End-Point."
        ::= { rcTlsTdiStatsEntry 63 }

rcTlsTdiSilverTxFrames	OBJECT-TYPE
        SYNTAX        Counter64
        MAX-ACCESS    read-only
        STATUS        current
        DESCRIPTION  "Number of Silver Service Frames sent to his End-Point."
        ::= { rcTlsTdiStatsEntry 64 }

rcTlsTdiStndTxFrames	OBJECT-TYPE
        SYNTAX        Counter64
        MAX-ACCESS    read-only
        STATUS        current
        DESCRIPTION  "Number of Standard Service Frames sent to his End-Point."
        ::= { rcTlsTdiStatsEntry 65 }

rcTlsTdiPremTxMcastFrames	OBJECT-TYPE
        SYNTAX        Counter64
        MAX-ACCESS    read-only
        STATUS        current
        DESCRIPTION  "Number of Premium Service Multicast sent to his End-Point."
        ::= { rcTlsTdiStatsEntry 66 }

rcTlsTdiGoldTxMcastFrames	OBJECT-TYPE
        SYNTAX        Counter64
        MAX-ACCESS    read-only
        STATUS        current
        DESCRIPTION  "Number of GoldService Multicast sent to his End-Point."
        ::= { rcTlsTdiStatsEntry 67 }

rcTlsTdiSilverTxMcastFrames	OBJECT-TYPE
        SYNTAX        Counter64
        MAX-ACCESS    read-only
        STATUS        current
        DESCRIPTION  "Number of SilverService Multicast sent to his End-Point."
        ::= { rcTlsTdiStatsEntry 68 }

rcTlsTdiStndTxMcastFrames	OBJECT-TYPE
        SYNTAX        Counter64
        MAX-ACCESS    read-only
        STATUS        current
        DESCRIPTION  "Number of Premium Service Multicast sent to his End-Point."
        ::= { rcTlsTdiStatsEntry 69 }

rcTlsTdiPremCongestionDropFrames	OBJECT-TYPE
        SYNTAX        Counter64
        MAX-ACCESS    read-only
        STATUS        current
        DESCRIPTION  "Number of Prem Service Frames congestion drop"
        ::= { rcTlsTdiStatsEntry 70 }

rcTlsTdiGoldCongestionDropFrames	OBJECT-TYPE
        SYNTAX        Counter64
        MAX-ACCESS    read-only
        STATUS        current
        DESCRIPTION  "Number of Gold Service Frames congestion drop"
        ::= { rcTlsTdiStatsEntry 71 }

rcTlsTdiSilverCongestionDropFrames	OBJECT-TYPE
        SYNTAX        Counter64
        MAX-ACCESS    read-only
        STATUS        current
        DESCRIPTION  "Number of Silver Service Frames congestion drop"
        ::= { rcTlsTdiStatsEntry 72 }

rcTlsTdiStndCongestionDropFrames	OBJECT-TYPE
        SYNTAX        Counter64
        MAX-ACCESS    read-only
        STATUS        current
        DESCRIPTION  "Number of Standard Service Frames congestion drop"
        ::= { rcTlsTdiStatsEntry 73 }

rcTlsTdiPremCirDroppedFrames	OBJECT-TYPE
        SYNTAX        Counter64
        MAX-ACCESS    read-only
        STATUS        current
        DESCRIPTION  "Number of Prem Service Frames CIR drop"
        ::= { rcTlsTdiStatsEntry 74 }

rcTlsTdiPremPirDroppedFrames	OBJECT-TYPE
        SYNTAX        Counter64
        MAX-ACCESS    read-only
        STATUS        current
        DESCRIPTION  "Number of Prem Service Frames PIR drop"
        ::= { rcTlsTdiStatsEntry 75 }

rcTlsTdiGoldCirDroppedFrames	OBJECT-TYPE
        SYNTAX        Counter64
        MAX-ACCESS    read-only
        STATUS        current
        DESCRIPTION  "Number of Gold Service Frames CIR drop"
        ::= { rcTlsTdiStatsEntry 76 }

rcTlsTdiGoldPirDroppedFrames	OBJECT-TYPE
        SYNTAX        Counter64
        MAX-ACCESS    read-only
        STATUS        current
        DESCRIPTION  "Number of Gold Service Frames PIR drop"
        ::= { rcTlsTdiStatsEntry 77 }

rcTlsTdiSilverCirDroppedFrames	OBJECT-TYPE
        SYNTAX        Counter64
        MAX-ACCESS    read-only
        STATUS        current
        DESCRIPTION  "Number of Silver Service Frames CIR drop"
        ::= { rcTlsTdiStatsEntry 78 }

rcTlsTdiSilverPirDroppedFrames	OBJECT-TYPE
        SYNTAX        Counter64
        MAX-ACCESS    read-only
        STATUS        current
        DESCRIPTION  "Number of Silver Service Frames PIR drop"
        ::= { rcTlsTdiStatsEntry 79 }

rcTlsTdiStndCirDroppedFrames	OBJECT-TYPE
        SYNTAX        Counter64
        MAX-ACCESS    read-only
        STATUS        current
        DESCRIPTION  "Number of Standard Service Frames CIR drop"
        ::= { rcTlsTdiStatsEntry 80 }

rcTlsTdiStndPirDroppedFrames	OBJECT-TYPE
        SYNTAX        Counter64
        MAX-ACCESS    read-only
        STATUS        current
        DESCRIPTION  "Number of Standard Service Frames PIR drop"
        ::= { rcTlsTdiStatsEntry 81 }

rcTlsTdiPremTxDroppedFrames	OBJECT-TYPE
        SYNTAX        Counter64
        MAX-ACCESS    read-only
        STATUS        current
        DESCRIPTION  "Tx Number of Premium Service Frames dropped from This End-Point."
        ::= { rcTlsTdiStatsEntry 82 }

rcTlsTdiGoldTxDroppedFrames	OBJECT-TYPE
        SYNTAX        Counter64
        MAX-ACCESS    read-only
        STATUS        current
        DESCRIPTION  "Tx Number of Gold Service Frames dropped from This End-Point."
        ::= { rcTlsTdiStatsEntry 83 }

rcTlsTdiSilverTxDroppedFrames	OBJECT-TYPE
        SYNTAX        Counter64
        MAX-ACCESS    read-only
        STATUS        current
        DESCRIPTION  "Tx Number of Silver Service Frames dropped from This End-Point."
        ::= { rcTlsTdiStatsEntry 84 }

rcTlsTdiStndTxDroppedFrames	OBJECT-TYPE
        SYNTAX        Counter64
        MAX-ACCESS    read-only
        STATUS        current
        DESCRIPTION  "Tx Number of Standard(BestEffort) Service Frames dropped from this End-Point."
        ::= { rcTlsTdiStatsEntry 85 }

rcTlsTdiPremTxCongestionDropFrames	OBJECT-TYPE
        SYNTAX        Counter64
        MAX-ACCESS    read-only
        STATUS        current
        DESCRIPTION  "Number of Prem Service Frames congestion drop"
        ::= { rcTlsTdiStatsEntry 86}

rcTlsTdiGoldTxCongestionDropFrames	OBJECT-TYPE
        SYNTAX        Counter64
        MAX-ACCESS    read-only
        STATUS        current
        DESCRIPTION  "Number of Gold Service Frames congestion drop"
        ::= { rcTlsTdiStatsEntry 87 }

rcTlsTdiSilverTxCongestionDropFrames	OBJECT-TYPE
        SYNTAX        Counter64
        MAX-ACCESS    read-only
        STATUS        current
        DESCRIPTION  "Number of Silver Service Frames congestion drop"
        ::= { rcTlsTdiStatsEntry 88 }

rcTlsTdiStndTxCongestionDropFrames	OBJECT-TYPE
        SYNTAX        Counter64
        MAX-ACCESS    read-only
        STATUS        current
        DESCRIPTION  "Number of Standard Service Frames congestion drop"
        ::= { rcTlsTdiStatsEntry 89 }

rcTlsTdiPremTxCirDroppedFrames	OBJECT-TYPE
        SYNTAX        Counter64
        MAX-ACCESS    read-only
        STATUS        current
        DESCRIPTION  "Number of Prem Service Frames CIR drop"
        ::= { rcTlsTdiStatsEntry 90 }

rcTlsTdiPremTxPirDroppedFrames	OBJECT-TYPE
        SYNTAX        Counter64
        MAX-ACCESS    read-only
        STATUS        current
        DESCRIPTION  "Number of Prem Service Frames PIR drop"
        ::= { rcTlsTdiStatsEntry 91 }

rcTlsTdiGoldTxCirDroppedFrames	OBJECT-TYPE
        SYNTAX        Counter64
        MAX-ACCESS    read-only
        STATUS        current
        DESCRIPTION  "Number of Gold Service Frames CIR drop"
        ::= { rcTlsTdiStatsEntry 92 }

rcTlsTdiGoldTxPirDroppedFrames	OBJECT-TYPE
        SYNTAX        Counter64
        MAX-ACCESS    read-only
        STATUS        current
        DESCRIPTION  "Number of Gold Service Frames PIR drop"
        ::= { rcTlsTdiStatsEntry 93 }

rcTlsTdiSilverTxCirDroppedFrames	OBJECT-TYPE
        SYNTAX        Counter64
        MAX-ACCESS    read-only
        STATUS        current
        DESCRIPTION  "Number of Silver Service Frames CIR drop"
        ::= { rcTlsTdiStatsEntry 94 }

rcTlsTdiSilverTxPirDroppedFrames	OBJECT-TYPE
        SYNTAX        Counter64
        MAX-ACCESS    read-only
        STATUS        current
        DESCRIPTION  "Number of Silver Service Frames PIR drop"
        ::= { rcTlsTdiStatsEntry 95 }

rcTlsTdiStndTxCirDroppedFrames	OBJECT-TYPE
        SYNTAX        Counter64
        MAX-ACCESS    read-only
        STATUS        current
        DESCRIPTION  "Number of Standard Service Frames CIR drop"
        ::= { rcTlsTdiStatsEntry 96 }

rcTlsTdiStndTxPirDroppedFrames	OBJECT-TYPE
        SYNTAX        Counter64
        MAX-ACCESS    read-only
        STATUS        current
        DESCRIPTION  "Number of Standard Service Frames PIR drop"
        ::= { rcTlsTdiStatsEntry 97 }

rcTlsTdiRxMcastTotalFrames   OBJECT-TYPE
        SYNTAX        Counter64
        MAX-ACCESS    read-only
        STATUS        current
        DESCRIPTION  "Rx total Number of Mcast Octet"
        ::= { rcTlsTdiStatsEntry 98 }

rcTlsTdiTxMcastTotalFrames  OBJECT-TYPE
        SYNTAX        Counter64
        MAX-ACCESS    read-only
        STATUS        current
        DESCRIPTION  "Tx total Number of Mcast Octet"
        ::= { rcTlsTdiStatsEntry 99 }

rcTlsTdiPremRxMcastDroppedFrames	OBJECT-TYPE
        SYNTAX        Counter64
        MAX-ACCESS    read-only
        STATUS        current
        DESCRIPTION  "Number of Premium Service Rx Mcast Frames dropped from
		      This TDI."
        ::= { rcTlsTdiStatsEntry 100 }

rcTlsTdiGoldRxMcastDroppedFrames	OBJECT-TYPE
        SYNTAX        Counter64
        MAX-ACCESS    read-only
        STATUS        current
        DESCRIPTION  "Number of Gold Service Rx Mcast Frames dropped from
		      This TDI."
        ::= { rcTlsTdiStatsEntry 101 }

rcTlsTdiSilverRxMcastDroppedFrames	OBJECT-TYPE
        SYNTAX        Counter64
        MAX-ACCESS    read-only
        STATUS        current
        DESCRIPTION  "Number of Silver Service Rx Mcast Frames dropped from
		      This TDI."
        ::= { rcTlsTdiStatsEntry 102 }

rcTlsTdiStndRxMcastDroppedFrames	OBJECT-TYPE
        SYNTAX        Counter64
        MAX-ACCESS    read-only
        STATUS        current
        DESCRIPTION  "Number of Standard Service Rx Mcast Frames dropped from
		      This TDI."
        ::= { rcTlsTdiStatsEntry 103 }

rcTlsTdiPremRxCirOctets     OBJECT-TYPE
        SYNTAX        Counter64
        MAX-ACCESS    read-only
        STATUS        current
        DESCRIPTION  "Number of Premium Service Rx CIR Octets received."
        ::= { rcTlsTdiStatsEntry 104 }

rcTlsTdiPremRxCirOopOctets     OBJECT-TYPE
        SYNTAX        Counter64
        MAX-ACCESS    read-only
        STATUS        current
        DESCRIPTION  "Number of Premium Service Rx Octets received that 
		      were CIR OOP."
        ::= { rcTlsTdiStatsEntry 105 }

rcTlsTdiPremRxEirOctets     OBJECT-TYPE
        SYNTAX        Counter64
        MAX-ACCESS    read-only
        STATUS        current
        DESCRIPTION  "Number of Premium Service Rx EIR Octets received."
        ::= { rcTlsTdiStatsEntry 106 }

rcTlsTdiPremRxEirOopOctets     OBJECT-TYPE
        SYNTAX        Counter64
        MAX-ACCESS    read-only
        STATUS        current
        DESCRIPTION  "Number of Premium Service Rx Octets received that 
		      were EIR OOP."
        ::= { rcTlsTdiStatsEntry 107 }

rcTlsTdiPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcTlsTdiStatsEntry 108 }

rcTlsTdiPremRxPirOctets     OBJECT-TYPE
        SYNTAX        Counter64
        MAX-ACCESS    read-only
        STATUS        current
        DESCRIPTION  "Number of Premium Service Rx PIR Octets received."
        ::= { rcTlsTdiStatsEntry 109 }

rcTlsTdiPremRxPirOopOctets     OBJECT-TYPE
        SYNTAX        Counter64
        MAX-ACCESS    read-only
        STATUS        current
        DESCRIPTION  "Number of Premium Service Rx Octets received that 
		      were PIR OOP."
        ::= { rcTlsTdiStatsEntry 110 }

rcTlsTdiPremRxGreenOctets     OBJECT-TYPE
        SYNTAX        Counter64
        MAX-ACCESS    read-only
        STATUS        current
        DESCRIPTION  "Number of Premium Service Rx Octets received that 
		      were marked 'Green' by the policer."
        ::= { rcTlsTdiStatsEntry 111 }

rcTlsTdiPremRxYellowOctets     OBJECT-TYPE
        SYNTAX        Counter64
        MAX-ACCESS    read-only
        STATUS        current
        DESCRIPTION  "Number of Premium Service Rx Octets received that 
		      were marked 'Yellow' by the policer."
        ::= { rcTlsTdiStatsEntry 112 }

rcTlsTdiPremRxRedOctets     OBJECT-TYPE
        SYNTAX        Counter64
        MAX-ACCESS    read-only
        STATUS        current
        DESCRIPTION  "Number of Premium Service Rx Octets received that 
		      were marked 'Red' by the policer."
        ::= { rcTlsTdiStatsEntry 113 }

rcTlsTdiGoldRxCirOctets     OBJECT-TYPE
        SYNTAX        Counter64
        MAX-ACCESS    read-only
        STATUS        current
        DESCRIPTION  "Number of Gold Service Rx CIR Octets received."
        ::= { rcTlsTdiStatsEntry 114 }

rcTlsTdiGoldRxCirOopOctets     OBJECT-TYPE
        SYNTAX        Counter64
        MAX-ACCESS    read-only
        STATUS        current
        DESCRIPTION  "Number of Gold Service Rx Octets received that 
		      were CIR OOP."
        ::= { rcTlsTdiStatsEntry 115 }

rcTlsTdiGoldRxEirOctets     OBJECT-TYPE
        SYNTAX        Counter64
        MAX-ACCESS    read-only
        STATUS        current
        DESCRIPTION  "Number of Gold Service Rx EIR Octets received."
        ::= { rcTlsTdiStatsEntry 116 }

rcTlsTdiGoldRxEirOopOctets     OBJECT-TYPE
        SYNTAX        Counter64
        MAX-ACCESS    read-only
        STATUS        current
        DESCRIPTION  "Number of Gold Service Rx Octets received that 
		      were EIR OOP."
        ::= { rcTlsTdiStatsEntry 117 }

rcTlsTdiGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcTlsTdiStatsEntry 118 }

rcTlsTdiGoldRxPirOctets     OBJECT-TYPE
        SYNTAX        Counter64
        MAX-ACCESS    read-only
        STATUS        current
        DESCRIPTION  "Number of Gold Service Rx PIR Octets received."
        ::= { rcTlsTdiStatsEntry 119 }

rcTlsTdiGoldRxPirOopOctets     OBJECT-TYPE
        SYNTAX        Counter64
        MAX-ACCESS    read-only
        STATUS        current
        DESCRIPTION  "Number of Gold Service Rx Octets received that 
		      were PIR OOP."
        ::= { rcTlsTdiStatsEntry 120 }

rcTlsTdiGoldRxGreenOctets     OBJECT-TYPE
        SYNTAX        Counter64
        MAX-ACCESS    read-only
        STATUS        current
        DESCRIPTION  "Number of Gold Service Rx Octets received that 
		      were marked 'Green' by the policer."
        ::= { rcTlsTdiStatsEntry 121 }

rcTlsTdiGoldRxYellowOctets     OBJECT-TYPE
        SYNTAX        Counter64
        MAX-ACCESS    read-only
        STATUS        current
        DESCRIPTION  "Number of Gold Service Rx Octets received that 
		      were marked 'Yellow' by the policer."
        ::= { rcTlsTdiStatsEntry 122 }

rcTlsTdiGoldRxRedOctets     OBJECT-TYPE
        SYNTAX        Counter64
        MAX-ACCESS    read-only
        STATUS        current
        DESCRIPTION  "Number of Gold Service Rx Octets received that 
		      were marked 'Red' by the policer."
        ::= { rcTlsTdiStatsEntry 123 }

rcTlsTdiSilverRxCirOctets     OBJECT-TYPE
        SYNTAX        Counter64
        MAX-ACCESS    read-only
        STATUS        current
        DESCRIPTION  "Number of Silver Service Rx CIR Octets received."
        ::= { rcTlsTdiStatsEntry 124 }

rcTlsTdiSilverRxCirOopOctets     OBJECT-TYPE
        SYNTAX        Counter64
        MAX-ACCESS    read-only
        STATUS        current
        DESCRIPTION  "Number of Silver Service Rx Octets received that 
		      were CIR OOP."
        ::= { rcTlsTdiStatsEntry 125 }

rcTlsTdiSilverRxEirOctets     OBJECT-TYPE
        SYNTAX        Counter64
        MAX-ACCESS    read-only
        STATUS        current
        DESCRIPTION  "Number of Silver Service Rx EIR Octets received."
        ::= { rcTlsTdiStatsEntry 126 }

rcTlsTdiSilverRxEirOopOctets     OBJECT-TYPE
        SYNTAX        Counter64
        MAX-ACCESS    read-only
        STATUS        current
        DESCRIPTION  "Number of Silver Service Rx Octets received that 
		      were EIR OOP."
        ::= { rcTlsTdiStatsEntry 127 }

rcTlsTdiSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcTlsTdiStatsEntry 128 }

rcTlsTdiSilverRxPirOctets     OBJECT-TYPE
        SYNTAX        Counter64
        MAX-ACCESS    read-only
        STATUS        current
        DESCRIPTION  "Number of Silver Service Rx PIR Octets received."
        ::= { rcTlsTdiStatsEntry 129 }

rcTlsTdiSilverRxPirOopOctets     OBJECT-TYPE
        SYNTAX        Counter64
        MAX-ACCESS    read-only
        STATUS        current
        DESCRIPTION  "Number of Silver Service Rx Octets received that 
		      were PIR OOP."
        ::= { rcTlsTdiStatsEntry 130 }

rcTlsTdiSilverRxGreenOctets     OBJECT-TYPE
        SYNTAX        Counter64
        MAX-ACCESS    read-only
        STATUS        current
        DESCRIPTION  "Number of Silver Service Rx Octets received that 
		      were marked 'Green' by the policer."
        ::= { rcTlsTdiStatsEntry 131 }

rcTlsTdiSilverRxYellowOctets     OBJECT-TYPE
        SYNTAX        Counter64
        MAX-ACCESS    read-only
        STATUS        current
        DESCRIPTION  "Number of Silver Service Rx Octets received that 
		      were marked 'Yellow' by the policer."
        ::= { rcTlsTdiStatsEntry 132 }

rcTlsTdiSilverRxRedOctets     OBJECT-TYPE
        SYNTAX        Counter64
        MAX-ACCESS    read-only
        STATUS        current
        DESCRIPTION  "Number of Silver Service Rx Octets received that 
		      were marked 'Red' by the policer."
        ::= { rcTlsTdiStatsEntry 133 }

rcTlsTdiStndRxCirOctets     OBJECT-TYPE
        SYNTAX        Counter64
        MAX-ACCESS    read-only
        STATUS        current
        DESCRIPTION  "Number of Standard Service Rx CIR Octets received."
        ::= { rcTlsTdiStatsEntry 134 }

rcTlsTdiStndRxCirOopOctets     OBJECT-TYPE
        SYNTAX        Counter64
        MAX-ACCESS    read-only
        STATUS        current
        DESCRIPTION  "Number of Standard Service Rx Octets received that 
		      were CIR OOP."
        ::= { rcTlsTdiStatsEntry 135 }

rcTlsTdiStndRxEirOctets     OBJECT-TYPE
        SYNTAX        Counter64
        MAX-ACCESS    read-only
        STATUS        current
        DESCRIPTION  "Number of Standard Service Rx EIR Octets received."
        ::= { rcTlsTdiStatsEntry 136 }

rcTlsTdiStndRxEirOopOctets     OBJECT-TYPE
        SYNTAX        Counter64
        MAX-ACCESS    read-only
        STATUS        current
        DESCRIPTION  "Number of Standard Service Rx Octets received that 
		      were EIR OOP."
        ::= { rcTlsTdiStatsEntry 137 }

rcTlsTdiStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcTlsTdiStatsEntry 138 }

rcTlsTdiStndRxPirOctets     OBJECT-TYPE
        SYNTAX        Counter64
        MAX-ACCESS    read-only
        STATUS        current
        DESCRIPTION  "Number of Standard Service Rx PIR Octets received."
        ::= { rcTlsTdiStatsEntry 139 }

rcTlsTdiStndRxPirOopOctets     OBJECT-TYPE
        SYNTAX        Counter64
        MAX-ACCESS    read-only
        STATUS        current
        DESCRIPTION  "Number of Standard Service Rx Octets received that 
		      were PIR OOP."
        ::= { rcTlsTdiStatsEntry 140 }

rcTlsTdiStndRxGreenOctets     OBJECT-TYPE
        SYNTAX        Counter64
        MAX-ACCESS    read-only
        STATUS        current
        DESCRIPTION  "Number of Standard Service Rx Octets received that 
		      were marked 'Green' by the policer."
        ::= { rcTlsTdiStatsEntry 141 }

rcTlsTdiStndRxYellowOctets     OBJECT-TYPE
        SYNTAX        Counter64
        MAX-ACCESS    read-only
        STATUS        current
        DESCRIPTION  "Number of Standard Service Rx Octets received that 
		      were marked 'Yellow' by the policer."
        ::= { rcTlsTdiStatsEntry 142 }

rcTlsTdiStndRxRedOctets     OBJECT-TYPE
        SYNTAX        Counter64
        MAX-ACCESS    read-only
        STATUS        current
        DESCRIPTION  "Number of Standard Service Rx Octets received that 
		      were marked 'Red' by the policer."
        ::= { rcTlsTdiStatsEntry 143 }

rcTlsTdiMcastRxDroppedOctets     OBJECT-TYPE
        SYNTAX        Counter64
        MAX-ACCESS    read-only
        STATUS        current
        DESCRIPTION  "Number of Multicast Rx Octets dropped."
        ::= { rcTlsTdiStatsEntry 144 }

rcTlsTdiBcastUUcastRxTotalOctets     OBJECT-TYPE
        SYNTAX        Counter64
        MAX-ACCESS    read-only
        STATUS        current
        DESCRIPTION  "Number of Broadcast/Unknown Unicast Rx total Octets."
        ::= { rcTlsTdiStatsEntry 145 }

rcTlsTdiBcastUUcastRxDroppedOctets     OBJECT-TYPE
        SYNTAX        Counter64
        MAX-ACCESS    read-only
        STATUS        current
        DESCRIPTION  "Number of Broadcast/Unknown Rx Octets dropped."
        ::= { rcTlsTdiStatsEntry 146 }

rcTlsTdiPremRxCirFrames     OBJECT-TYPE
        SYNTAX        Counter64
        MAX-ACCESS    read-only
        STATUS        current
        DESCRIPTION  "Number of Premium Service Rx CIR Frames received."
        ::= { rcTlsTdiStatsEntry 147 }

rcTlsTdiPremRxCirOopFrames     OBJECT-TYPE
        SYNTAX        Counter64
        MAX-ACCESS    read-only
        STATUS        current
        DESCRIPTION  "Number of Premium Service Rx Frames received that 
		      were CIR OOP."
        ::= { rcTlsTdiStatsEntry 148 }

rcTlsTdiPremRxEirFrames     OBJECT-TYPE
        SYNTAX        Counter64
        MAX-ACCESS    read-only
        STATUS        current
        DESCRIPTION  "Number of Premium Service Rx EIR Frames received."
        ::= { rcTlsTdiStatsEntry 149 }

rcTlsTdiPremRxEirOopFrames     OBJECT-TYPE
        SYNTAX        Counter64
        MAX-ACCESS    read-only
        STATUS        current
        DESCRIPTION  "Number of Premium Service Rx Frames received that 
		      were EIR OOP."
        ::= { rcTlsTdiStatsEntry 150 }

rcTlsTdiPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcTlsTdiStatsEntry 151 }

rcTlsTdiPremRxPirFrames     OBJECT-TYPE
        SYNTAX        Counter64
        MAX-ACCESS    read-only
        STATUS        current
        DESCRIPTION  "Number of Premium Service Rx PIR Frames received."
        ::= { rcTlsTdiStatsEntry 152 }

rcTlsTdiPremRxPirOopFrames     OBJECT-TYPE
        SYNTAX        Counter64
        MAX-ACCESS    read-only
        STATUS        current
        DESCRIPTION  "Number of Premium Service Rx Frames received that 
		      were PIR OOP."
        ::= { rcTlsTdiStatsEntry 153 }

rcTlsTdiPremRxGreenFrames     OBJECT-TYPE
        SYNTAX        Counter64
        MAX-ACCESS    read-only
        STATUS        current
        DESCRIPTION  "Number of Premium Service Rx Frames received that 
		      were marked 'Green' by the policer."
        ::= { rcTlsTdiStatsEntry 154 }

rcTlsTdiPremRxYellowFrames     OBJECT-TYPE
        SYNTAX        Counter64
        MAX-ACCESS    read-only
        STATUS        current
        DESCRIPTION  "Number of Premium Service Rx Frames received that 
		      were marked 'Yellow' by the policer."
        ::= { rcTlsTdiStatsEntry 155 }

rcTlsTdiPremRxRedFrames     OBJECT-TYPE
        SYNTAX        Counter64
        MAX-ACCESS    read-only
        STATUS        current
        DESCRIPTION  "Number of Premium Service Rx Frames received that 
		      were marked 'Red' by the policer."
        ::= { rcTlsTdiStatsEntry 156 }

rcTlsTdiGoldRxCirFrames     OBJECT-TYPE
        SYNTAX        Counter64
        MAX-ACCESS    read-only
        STATUS        current
        DESCRIPTION  "Number of Gold Service Rx CIR Frames received."
        ::= { rcTlsTdiStatsEntry 157 }

rcTlsTdiGoldRxCirOopFrames     OBJECT-TYPE
        SYNTAX        Counter64
        MAX-ACCESS    read-only
        STATUS        current
        DESCRIPTION  "Number of Gold Service Rx Frames received that 
		      were CIR OOP."
        ::= { rcTlsTdiStatsEntry 158 }

rcTlsTdiGoldRxEirFrames     OBJECT-TYPE
        SYNTAX        Counter64
        MAX-ACCESS    read-only
        STATUS        current
        DESCRIPTION  "Number of Gold Service Rx EIR Frames received."
        ::= { rcTlsTdiStatsEntry 159 }

rcTlsTdiGoldRxEirOopFrames     OBJECT-TYPE
        SYNTAX        Counter64
        MAX-ACCESS    read-only
        STATUS        current
        DESCRIPTION  "Number of Gold Service Rx Frames received that 
		      were EIR OOP."
        ::= { rcTlsTdiStatsEntry 160 }

rcTlsTdiGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcTlsTdiStatsEntry 161 }

rcTlsTdiGoldRxPirFrames     OBJECT-TYPE
        SYNTAX        Counter64
        MAX-ACCESS    read-only
        STATUS        current
        DESCRIPTION  "Number of Gold Service Rx PIR Frames received."
        ::= { rcTlsTdiStatsEntry 162 }

rcTlsTdiGoldRxPirOopFrames     OBJECT-TYPE
        SYNTAX        Counter64
        MAX-ACCESS    read-only
        STATUS        current
        DESCRIPTION  "Number of Gold Service Rx Frames received that 
		      were PIR OOP."
        ::= { rcTlsTdiStatsEntry 163 }

rcTlsTdiGoldRxGreenFrames     OBJECT-TYPE
        SYNTAX        Counter64
        MAX-ACCESS    read-only
        STATUS        current
        DESCRIPTION  "Number of Gold Service Rx Frames received that 
		      were marked 'Green' by the policer."
        ::= { rcTlsTdiStatsEntry 164 }

rcTlsTdiGoldRxYellowFrames     OBJECT-TYPE
        SYNTAX        Counter64
        MAX-ACCESS    read-only
        STATUS        current
        DESCRIPTION  "Number of Gold Service Rx Frames received that 
		      were marked 'Yellow' by the policer."
        ::= { rcTlsTdiStatsEntry 165 }

rcTlsTdiGoldRxRedFrames     OBJECT-TYPE
        SYNTAX        Counter64
        MAX-ACCESS    read-only
        STATUS        current
        DESCRIPTION  "Number of Gold Service Rx Frames received that 
		      were marked 'Red' by the policer."
        ::= { rcTlsTdiStatsEntry 166 }

rcTlsTdiSilverRxCirFrames     OBJECT-TYPE
        SYNTAX        Counter64
        MAX-ACCESS    read-only
        STATUS        current
        DESCRIPTION  "Number of Silver Service Rx CIR Frames received."
        ::= { rcTlsTdiStatsEntry 167 }

rcTlsTdiSilverRxCirOopFrames     OBJECT-TYPE
        SYNTAX        Counter64
        MAX-ACCESS    read-only
        STATUS        current
        DESCRIPTION  "Number of Silver Service Rx Frames received that 
		      were CIR OOP."
        ::= { rcTlsTdiStatsEntry 168 }

rcTlsTdiSilverRxEirFrames     OBJECT-TYPE
        SYNTAX        Counter64
        MAX-ACCESS    read-only
        STATUS        current
        DESCRIPTION  "Number of Silver Service Rx EIR Frames received."
        ::= { rcTlsTdiStatsEntry 169 }

rcTlsTdiSilverRxEirOopFrames     OBJECT-TYPE
        SYNTAX        Counter64
        MAX-ACCESS    read-only
        STATUS        current
        DESCRIPTION  "Number of Silver Service Rx Frames received that 
		      were EIR OOP."
        ::= { rcTlsTdiStatsEntry 170 }

rcTlsTdiSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcTlsTdiStatsEntry 171 }

rcTlsTdiSilverRxPirFrames     OBJECT-TYPE
        SYNTAX        Counter64
        MAX-ACCESS    read-only
        STATUS        current
        DESCRIPTION  "Number of Silver Service Rx PIR Frames received."
        ::= { rcTlsTdiStatsEntry 172 }

rcTlsTdiSilverRxPirOopFrames     OBJECT-TYPE
        SYNTAX        Counter64
        MAX-ACCESS    read-only
        STATUS        current
        DESCRIPTION  "Number of Silver Service Rx Frames received that 
		      were PIR OOP."
        ::= { rcTlsTdiStatsEntry 173 }

rcTlsTdiSilverRxGreenFrames     OBJECT-TYPE
        SYNTAX        Counter64
        MAX-ACCESS    read-only
        STATUS        current
        DESCRIPTION  "Number of Silver Service Rx Frames received that 
		      were marked 'Green' by the policer."
        ::= { rcTlsTdiStatsEntry 174 }

rcTlsTdiSilverRxYellowFrames     OBJECT-TYPE
        SYNTAX        Counter64
        MAX-ACCESS    read-only
        STATUS        current
        DESCRIPTION  "Number of Silver Service Rx Frames received that 
		      were marked 'Yellow' by the policer."
        ::= { rcTlsTdiStatsEntry 175 }

rcTlsTdiSilverRxRedFrames     OBJECT-TYPE
        SYNTAX        Counter64
        MAX-ACCESS    read-only
        STATUS        current
        DESCRIPTION  "Number of Silver Service Rx Frames received that 
		      were marked 'Red' by the policer."
        ::= { rcTlsTdiStatsEntry 176 }

rcTlsTdiStndRxCirFrames     OBJECT-TYPE
        SYNTAX        Counter64
        MAX-ACCESS    read-only
        STATUS        current
        DESCRIPTION  "Number of Standard Service Rx CIR Frames received."
        ::= { rcTlsTdiStatsEntry 177 }

rcTlsTdiStndRxCirOopFrames     OBJECT-TYPE
        SYNTAX        Counter64
        MAX-ACCESS    read-only
        STATUS        current
        DESCRIPTION  "Number of Standard Service Rx Frames received that 
		      were CIR OOP."
        ::= { rcTlsTdiStatsEntry 178 }

rcTlsTdiStndRxEirFrames     OBJECT-TYPE
        SYNTAX        Counter64
        MAX-ACCESS    read-only
        STATUS        current
        DESCRIPTION  "Number of Standard Service Rx EIR Frames received."
        ::= { rcTlsTdiStatsEntry 179 }

rcTlsTdiStndRxEirOopFrames     OBJECT-TYPE
        SYNTAX        Counter64
        MAX-ACCESS    read-only
        STATUS        current
        DESCRIPTION  "Number of Standard Service Rx Frames received that 
		      were EIR OOP."
        ::= { rcTlsTdiStatsEntry 180 }

rcTlsTdiStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcTlsTdiStatsEntry 181 }

rcTlsTdiStndRxPirFrames     OBJECT-TYPE
        SYNTAX        Counter64
        MAX-ACCESS    read-only
        STATUS        current
        DESCRIPTION  "Number of Standard Service Rx PIR Frames received."
        ::= { rcTlsTdiStatsEntry 182 }

rcTlsTdiStndRxPirOopFrames     OBJECT-TYPE
        SYNTAX        Counter64
        MAX-ACCESS    read-only
        STATUS        current
        DESCRIPTION  "Number of Standard Service Rx Frames received that 
		      were PIR OOP."
        ::= { rcTlsTdiStatsEntry 183 }

rcTlsTdiStndRxGreenFrames     OBJECT-TYPE
        SYNTAX        Counter64
        MAX-ACCESS    read-only
        STATUS        current
        DESCRIPTION  "Number of Standard Service Rx Frames received that 
		      were marked 'Green' by the policer."
        ::= { rcTlsTdiStatsEntry 184 }

rcTlsTdiStndRxYellowFrames     OBJECT-TYPE
        SYNTAX        Counter64
        MAX-ACCESS    read-only
        STATUS        current
        DESCRIPTION  "Number of Standard Service Rx Frames received that 
		      were marked 'Yellow' by the policer."
        ::= { rcTlsTdiStatsEntry 185 }

rcTlsTdiStndRxRedFrames     OBJECT-TYPE
        SYNTAX        Counter64
        MAX-ACCESS    read-only
        STATUS        current
        DESCRIPTION  "Number of Standard Service Rx Frames received that 
		      were marked 'Red' by the policer."
        ::= { rcTlsTdiStatsEntry 186 }

rcTlsTdiMcastRxDroppedFrames     OBJECT-TYPE
        SYNTAX        Counter64
        MAX-ACCESS    read-only
        STATUS        current
        DESCRIPTION  "Number of Multicast Rx Frames dropped."
        ::= { rcTlsTdiStatsEntry 187 }

rcTlsTdiBcastUUcastRxTotalFrames     OBJECT-TYPE
        SYNTAX        Counter64
        MAX-ACCESS    read-only
        STATUS        current
        DESCRIPTION  "Number of Broadcast/Unknown Unicast Rx total Frames."
        ::= { rcTlsTdiStatsEntry 188 }

rcTlsTdiBcastUUcastRxDroppedFrames     OBJECT-TYPE
        SYNTAX        Counter64
        MAX-ACCESS    read-only
        STATUS        current
        DESCRIPTION  "Number of Broadcast/Unknown Rx Frames dropped."
        ::= { rcTlsTdiStatsEntry 189 }

rcTlsTdiPremTxCirOctets     OBJECT-TYPE
        SYNTAX        Counter64
        MAX-ACCESS    read-only
        STATUS        current
        DESCRIPTION  "Number of Premium Service Tx CIR Octets received."
        ::= { rcTlsTdiStatsEntry 190 }

rcTlsTdiPremTxCirOopOctets     OBJECT-TYPE
        SYNTAX        Counter64
        MAX-ACCESS    read-only
        STATUS        current
        DESCRIPTION  "Number of Premium Service Tx Octets received that 
		      were CIR OOP."
        ::= { rcTlsTdiStatsEntry 191 }

rcTlsTdiPremTxEirOctets     OBJECT-TYPE
        SYNTAX        Counter64
        MAX-ACCESS    read-only
        STATUS        current
        DESCRIPTION  "Number of Premium Service Tx EIR Octets received."
        ::= { rcTlsTdiStatsEntry 192 }

rcTlsTdiPremTxEirOopOctets     OBJECT-TYPE
        SYNTAX        Counter64
        MAX-ACCESS    read-only
        STATUS        current
        DESCRIPTION  "Number of Premium Service Tx Octets received that 
		      were EIR OOP."
        ::= { rcTlsTdiStatsEntry 193 }

rcTlsTdiPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcTlsTdiStatsEntry 194 }

rcTlsTdiPremTxPirOctets     OBJECT-TYPE
        SYNTAX        Counter64
        MAX-ACCESS    read-only
        STATUS        current
        DESCRIPTION  "Number of Premium Service Tx PIR Octets received."
        ::= { rcTlsTdiStatsEntry 195 }

rcTlsTdiPremTxPirOopOctets     OBJECT-TYPE
        SYNTAX        Counter64
        MAX-ACCESS    read-only
        STATUS        current
        DESCRIPTION  "Number of Premium Service Tx Octets received that 
		      were PIR OOP."
        ::= { rcTlsTdiStatsEntry 196 }

rcTlsTdiPremTxGreenOctets     OBJECT-TYPE
        SYNTAX        Counter64
        MAX-ACCESS    read-only
        STATUS        current
        DESCRIPTION  "Number of Premium Service Tx Octets received that 
		      were marked 'Green' by the policer."
        ::= { rcTlsTdiStatsEntry 197 }

rcTlsTdiPremTxYellowOctets     OBJECT-TYPE
        SYNTAX        Counter64
        MAX-ACCESS    read-only
        STATUS        current
        DESCRIPTION  "Number of Premium Service Tx Octets received that 
		      were marked 'Yellow' by the policer."
        ::= { rcTlsTdiStatsEntry 198 }

rcTlsTdiPremTxRedOctets     OBJECT-TYPE
        SYNTAX        Counter64
        MAX-ACCESS    read-only
        STATUS        current
        DESCRIPTION  "Number of Premium Service Tx Octets received that 
		      were marked 'Red' by the policer."
        ::= { rcTlsTdiStatsEntry 199 }

rcTlsTdiGoldTxCirOctets     OBJECT-TYPE
        SYNTAX        Counter64
        MAX-ACCESS    read-only
        STATUS        current
        DESCRIPTION  "Number of Gold Service Tx CIR Octets received."
        ::= { rcTlsTdiStatsEntry 200 }

rcTlsTdiGoldTxCirOopOctets     OBJECT-TYPE
        SYNTAX        Counter64
        MAX-ACCESS    read-only
        STATUS        current
        DESCRIPTION  "Number of Gold Service Tx Octets received that 
		      were CIR OOP."
        ::= { rcTlsTdiStatsEntry 201 }

rcTlsTdiGoldTxEirOctets     OBJECT-TYPE
        SYNTAX        Counter64
        MAX-ACCESS    read-only
        STATUS        current
        DESCRIPTION  "Number of Gold Service Tx EIR Octets received."
        ::= { rcTlsTdiStatsEntry 202 }

rcTlsTdiGoldTxEirOopOctets     OBJECT-TYPE
        SYNTAX        Counter64
        MAX-ACCESS    read-only
        STATUS        current
        DESCRIPTION  "Number of Gold Service Tx Octets received that 
		      were EIR OOP."
        ::= { rcTlsTdiStatsEntry 203 }

rcTlsTdiGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcTlsTdiStatsEntry 204 }

rcTlsTdiGoldTxPirOctets     OBJECT-TYPE
        SYNTAX        Counter64
        MAX-ACCESS    read-only
        STATUS        current
        DESCRIPTION  "Number of Gold Service Tx PIR Octets received."
        ::= { rcTlsTdiStatsEntry 205 }

rcTlsTdiGoldTxPirOopOctets     OBJECT-TYPE
        SYNTAX        Counter64
        MAX-ACCESS    read-only
        STATUS        current
        DESCRIPTION  "Number of Gold Service Tx Octets received that 
		      were PIR OOP."
        ::= { rcTlsTdiStatsEntry 206 }

rcTlsTdiGoldTxGreenOctets     OBJECT-TYPE
        SYNTAX        Counter64
        MAX-ACCESS    read-only
        STATUS        current
        DESCRIPTION  "Number of Gold Service Tx Octets received that 
		      were marked 'Green' by the policer."
        ::= { rcTlsTdiStatsEntry 207 }

rcTlsTdiGoldTxYellowOctets     OBJECT-TYPE
        SYNTAX        Counter64
        MAX-ACCESS    read-only
        STATUS        current
        DESCRIPTION  "Number of Gold Service Tx Octets received that 
		      were marked 'Yellow' by the policer."
        ::= { rcTlsTdiStatsEntry 208 }

rcTlsTdiGoldTxRedOctets     OBJECT-TYPE
        SYNTAX        Counter64
        MAX-ACCESS    read-only
        STATUS        current
        DESCRIPTION  "Number of Gold Service Tx Octets received that 
		      were marked 'Red' by the policer."
        ::= { rcTlsTdiStatsEntry 209 }

rcTlsTdiSilverTxCirOctets     OBJECT-TYPE
        SYNTAX        Counter64
        MAX-ACCESS    read-only
        STATUS        current
        DESCRIPTION  "Number of Silver Service Tx CIR Octets received."
        ::= { rcTlsTdiStatsEntry 210 }

rcTlsTdiSilverTxCirOopOctets     OBJECT-TYPE
        SYNTAX        Counter64
        MAX-ACCESS    read-only
        STATUS        current
        DESCRIPTION  "Number of Silver Service Tx Octets received that 
		      were CIR OOP."
        ::= { rcTlsTdiStatsEntry 211 }

rcTlsTdiSilverTxEirOctets     OBJECT-TYPE
        SYNTAX        Counter64
        MAX-ACCESS    read-only
        STATUS        current
        DESCRIPTION  "Number of Silver Service Tx EIR Octets received."
        ::= { rcTlsTdiStatsEntry 212 }

rcTlsTdiSilverTxEirOopOctets     OBJECT-TYPE
        SYNTAX        Counter64
        MAX-ACCESS    read-only
        STATUS        current
        DESCRIPTION  "Number of Silver Service Tx Octets received that 
		      were EIR OOP."
        ::= { rcTlsTdiStatsEntry 213 }

rcTlsTdiSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcTlsTdiStatsEntry 214 }

rcTlsTdiSilverTxPirOctets     OBJECT-TYPE
        SYNTAX        Counter64
        MAX-ACCESS    read-only
        STATUS        current
        DESCRIPTION  "Number of Silver Service Tx PIR Octets received."
        ::= { rcTlsTdiStatsEntry 215 }

rcTlsTdiSilverTxPirOopOctets     OBJECT-TYPE
        SYNTAX        Counter64
        MAX-ACCESS    read-only
        STATUS        current
        DESCRIPTION  "Number of Silver Service Tx Octets received that 
		      were PIR OOP."
        ::= { rcTlsTdiStatsEntry 216 }

rcTlsTdiSilverTxGreenOctets     OBJECT-TYPE
        SYNTAX        Counter64
        MAX-ACCESS    read-only
        STATUS        current
        DESCRIPTION  "Number of Silver Service Tx Octets received that 
		      were marked 'Green' by the policer."
        ::= { rcTlsTdiStatsEntry 217 }

rcTlsTdiSilverTxYellowOctets     OBJECT-TYPE
        SYNTAX        Counter64
        MAX-ACCESS    read-only
        STATUS        current
        DESCRIPTION  "Number of Silver Service Tx Octets received that 
		      were marked 'Yellow' by the policer."
        ::= { rcTlsTdiStatsEntry 218 }

rcTlsTdiSilverTxRedOctets     OBJECT-TYPE
        SYNTAX        Counter64
        MAX-ACCESS    read-only
        STATUS        current
        DESCRIPTION  "Number of Silver Service Tx Octets received that 
		      were marked 'Red' by the policer."
        ::= { rcTlsTdiStatsEntry 219 }

rcTlsTdiStndTxCirOctets     OBJECT-TYPE
        SYNTAX        Counter64
        MAX-ACCESS    read-only
        STATUS        current
        DESCRIPTION  "Number of Standard Service Tx CIR Octets received."
        ::= { rcTlsTdiStatsEntry 220 }

rcTlsTdiStndTxCirOopOctets     OBJECT-TYPE
        SYNTAX        Counter64
        MAX-ACCESS    read-only
        STATUS        current
        DESCRIPTION  "Number of Standard Service Tx Octets received that 
		      were CIR OOP."
        ::= { rcTlsTdiStatsEntry 221 }

rcTlsTdiStndTxEirOctets     OBJECT-TYPE
        SYNTAX        Counter64
        MAX-ACCESS    read-only
        STATUS        current
        DESCRIPTION  "Number of Standard Service Tx EIR Octets received."
        ::= { rcTlsTdiStatsEntry 222 }

rcTlsTdiStndTxEirOopOctets     OBJECT-TYPE
        SYNTAX        Counter64
        MAX-ACCESS    read-only
        STATUS        current
        DESCRIPTION  "Number of Standard Service Tx Octets received that 
		      were EIR OOP."
        ::= { rcTlsTdiStatsEntry 223 }

rcTlsTdiStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcTlsTdiStatsEntry 224 }

rcTlsTdiStndTxPirOctets     OBJECT-TYPE
        SYNTAX        Counter64
        MAX-ACCESS    read-only
        STATUS        current
        DESCRIPTION  "Number of Standard Service Tx PIR Octets received."
        ::= { rcTlsTdiStatsEntry 225 }

rcTlsTdiStndTxPirOopOctets     OBJECT-TYPE
        SYNTAX        Counter64
        MAX-ACCESS    read-only
        STATUS        current
        DESCRIPTION  "Number of Standard Service Tx Octets received that 
		      were PIR OOP."
        ::= { rcTlsTdiStatsEntry 226 }

rcTlsTdiStndTxGreenOctets     OBJECT-TYPE
        SYNTAX        Counter64
        MAX-ACCESS    read-only
        STATUS        current
        DESCRIPTION  "Number of Standard Service Tx Octets received that 
		      were marked 'Green' by the policer."
        ::= { rcTlsTdiStatsEntry 227 }

rcTlsTdiStndTxYellowOctets     OBJECT-TYPE
        SYNTAX        Counter64
        MAX-ACCESS    read-only
        STATUS        current
        DESCRIPTION  "Number of Standard Service Tx Octets received that 
		      were marked 'Yellow' by the policer."
        ::= { rcTlsTdiStatsEntry 228 }

rcTlsTdiStndTxRedOctets     OBJECT-TYPE
        SYNTAX        Counter64
        MAX-ACCESS    read-only
        STATUS        current
        DESCRIPTION  "Number of Standard Service Tx Octets received that 
		      were marked 'Red' by the policer."
        ::= { rcTlsTdiStatsEntry 229 }

rcTlsTdiMcastTxDroppedOctets     OBJECT-TYPE
        SYNTAX        Counter64
        MAX-ACCESS    read-only
        STATUS        current
        DESCRIPTION  "Number of Multicast Tx Octets dropped."
        ::= { rcTlsTdiStatsEntry 230 }

rcTlsTdiBcastUUcastTxTotalOctets     OBJECT-TYPE
        SYNTAX        Counter64
        MAX-ACCESS    read-only
        STATUS        current
        DESCRIPTION  "Number of Broadcast/Unknown Unicast Tx total Octets."
        ::= { rcTlsTdiStatsEntry 231 }

rcTlsTdiBcastUUcastTxDroppedOctets     OBJECT-TYPE
        SYNTAX        Counter64
        MAX-ACCESS    read-only
        STATUS        current
        DESCRIPTION  "Number of Broadcast/Unknown Tx Octets dropped."
        ::= { rcTlsTdiStatsEntry 232 }

rcTlsTdiPremTxCirFrames     OBJECT-TYPE
        SYNTAX        Counter64
        MAX-ACCESS    read-only
        STATUS        current
        DESCRIPTION  "Number of Premium Service Tx CIR Frames received."
        ::= { rcTlsTdiStatsEntry 233 }

rcTlsTdiPremTxCirOopFrames     OBJECT-TYPE
        SYNTAX        Counter64
        MAX-ACCESS    read-only
        STATUS        current
        DESCRIPTION  "Number of Premium Service Tx Frames received that 
		      were CIR OOP."
        ::= { rcTlsTdiStatsEntry 234 }

rcTlsTdiPremTxEirFrames     OBJECT-TYPE
        SYNTAX        Counter64
        MAX-ACCESS    read-only
        STATUS        current
        DESCRIPTION  "Number of Premium Service Tx EIR Frames received."
        ::= { rcTlsTdiStatsEntry 235 }

rcTlsTdiPremTxEirOopFrames     OBJECT-TYPE
        SYNTAX        Counter64
        MAX-ACCESS    read-only
        STATUS        current
        DESCRIPTION  "Number of Premium Service Tx Frames received that 
		      were EIR OOP."
        ::= { rcTlsTdiStatsEntry 236 }

rcTlsTdiPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcTlsTdiStatsEntry 237 }

rcTlsTdiPremTxPirFrames     OBJECT-TYPE
        SYNTAX        Counter64
        MAX-ACCESS    read-only
        STATUS        current
        DESCRIPTION  "Number of Premium Service Tx PIR Frames received."
        ::= { rcTlsTdiStatsEntry 238 }

rcTlsTdiPremTxPirOopFrames     OBJECT-TYPE
        SYNTAX        Counter64
        MAX-ACCESS    read-only
        STATUS        current
        DESCRIPTION  "Number of Premium Service Tx Frames received that 
		      were PIR OOP."
        ::= { rcTlsTdiStatsEntry 239 }

rcTlsTdiPremTxGreenFrames     OBJECT-TYPE
        SYNTAX        Counter64
        MAX-ACCESS    read-only
        STATUS        current
        DESCRIPTION  "Number of Premium Service Tx Frames received that 
		      were marked 'Green' by the policer."
        ::= { rcTlsTdiStatsEntry 240 }

rcTlsTdiPremTxYellowFrames     OBJECT-TYPE
        SYNTAX        Counter64
        MAX-ACCESS    read-only
        STATUS        current
        DESCRIPTION  "Number of Premium Service Tx Frames received that 
		      were marked 'Yellow' by the policer."
        ::= { rcTlsTdiStatsEntry 241 }

rcTlsTdiPremTxRedFrames     OBJECT-TYPE
        SYNTAX        Counter64
        MAX-ACCESS    read-only
        STATUS        current
        DESCRIPTION  "Number of Premium Service Tx Frames received that 
		      were marked 'Red' by the policer."
        ::= { rcTlsTdiStatsEntry 242 }

rcTlsTdiGoldTxCirFrames     OBJECT-TYPE
        SYNTAX        Counter64
        MAX-ACCESS    read-only
        STATUS        current
        DESCRIPTION  "Number of Gold Service Tx CIR Frames received."
        ::= { rcTlsTdiStatsEntry 243 }

rcTlsTdiGoldTxCirOopFrames     OBJECT-TYPE
        SYNTAX        Counter64
        MAX-ACCESS    read-only
        STATUS        current
        DESCRIPTION  "Number of Gold Service Tx Frames received that 
		      were CIR OOP."
        ::= { rcTlsTdiStatsEntry 244 }

rcTlsTdiGoldTxEirFrames     OBJECT-TYPE
        SYNTAX        Counter64
        MAX-ACCESS    read-only
        STATUS        current
        DESCRIPTION  "Number of Gold Service Tx EIR Frames received."
        ::= { rcTlsTdiStatsEntry 245 }

rcTlsTdiGoldTxEirOopFrames     OBJECT-TYPE
        SYNTAX        Counter64
        MAX-ACCESS    read-only
        STATUS        current
        DESCRIPTION  "Number of Gold Service Tx Frames received that 
		      were EIR OOP."
        ::= { rcTlsTdiStatsEntry 246 }

rcTlsTdiGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcTlsTdiStatsEntry 247 }

rcTlsTdiGoldTxPirFrames     OBJECT-TYPE
        SYNTAX        Counter64
        MAX-ACCESS    read-only
        STATUS        current
        DESCRIPTION  "Number of Gold Service Tx PIR Frames received."
        ::= { rcTlsTdiStatsEntry 248 }

rcTlsTdiGoldTxPirOopFrames     OBJECT-TYPE
        SYNTAX        Counter64
        MAX-ACCESS    read-only
        STATUS        current
        DESCRIPTION  "Number of Gold Service Tx Frames received that 
		      were PIR OOP."
        ::= { rcTlsTdiStatsEntry 249 }

rcTlsTdiGoldTxGreenFrames     OBJECT-TYPE
        SYNTAX        Counter64
        MAX-ACCESS    read-only
        STATUS        current
        DESCRIPTION  "Number of Gold Service Tx Frames received that 
		      were marked 'Green' by the policer."
        ::= { rcTlsTdiStatsEntry 250 }

rcTlsTdiGoldTxYellowFrames     OBJECT-TYPE
        SYNTAX        Counter64
        MAX-ACCESS    read-only
        STATUS        current
        DESCRIPTION  "Number of Gold Service Tx Frames received that 
		      were marked 'Yellow' by the policer."
        ::= { rcTlsTdiStatsEntry 251 }

rcTlsTdiGoldTxRedFrames     OBJECT-TYPE
        SYNTAX        Counter64
        MAX-ACCESS    read-only
        STATUS        current
        DESCRIPTION  "Number of Gold Service Tx Frames received that 
		      were marked 'Red' by the policer."
        ::= { rcTlsTdiStatsEntry 252 }

rcTlsTdiSilverTxCirFrames     OBJECT-TYPE
        SYNTAX        Counter64
        MAX-ACCESS    read-only
        STATUS        current
        DESCRIPTION  "Number of Silver Service Tx CIR Frames received."
        ::= { rcTlsTdiStatsEntry 253 }

rcTlsTdiSilverTxCirOopFrames     OBJECT-TYPE
        SYNTAX        Counter64
        MAX-ACCESS    read-only
        STATUS        current
        DESCRIPTION  "Number of Silver Service Tx Frames received that 
		      were CIR OOP."
        ::= { rcTlsTdiStatsEntry 254 }

rcTlsTdiSilverTxEirFrames     OBJECT-TYPE
        SYNTAX        Counter64
        MAX-ACCESS    read-only
        STATUS        current
        DESCRIPTION  "Number of Silver Service Tx EIR Frames received."
        ::= { rcTlsTdiStatsEntry 255 }

rcTlsTdiSilverTxEirOopFrames     OBJECT-TYPE
        SYNTAX        Counter64
        MAX-ACCESS    read-only
        STATUS        current
        DESCRIPTION  "Number of Silver Service Tx Frames received that 
		      were EIR OOP."
        ::= { rcTlsTdiStatsEntry 256 }

rcTlsTdiSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcTlsTdiStatsEntry 257 }

rcTlsTdiSilverTxPirFrames     OBJECT-TYPE
        SYNTAX        Counter64
        MAX-ACCESS    read-only
        STATUS        current
        DESCRIPTION  "Number of Silver Service Tx PIR Frames received."
        ::= { rcTlsTdiStatsEntry 258 }

rcTlsTdiSilverTxPirOopFrames     OBJECT-TYPE
        SYNTAX        Counter64
        MAX-ACCESS    read-only
        STATUS        current
        DESCRIPTION  "Number of Silver Service Tx Frames received that 
		      were PIR OOP."
        ::= { rcTlsTdiStatsEntry 259 }

rcTlsTdiSilverTxGreenFrames     OBJECT-TYPE
        SYNTAX        Counter64
        MAX-ACCESS    read-only
        STATUS        current
        DESCRIPTION  "Number of Silver Service Tx Frames received that 
		      were marked 'Green' by the policer."
        ::= { rcTlsTdiStatsEntry 260 }

rcTlsTdiSilverTxYellowFrames     OBJECT-TYPE
        SYNTAX        Counter64
        MAX-ACCESS    read-only
        STATUS        current
        DESCRIPTION  "Number of Silver Service Tx Frames received that 
		      were marked 'Yellow' by the policer."
        ::= { rcTlsTdiStatsEntry 261 }

rcTlsTdiSilverTxRedFrames     OBJECT-TYPE
        SYNTAX        Counter64
        MAX-ACCESS    read-only
        STATUS        current
        DESCRIPTION  "Number of Silver Service Tx Frames received that 
		      were marked 'Red' by the policer."
        ::= { rcTlsTdiStatsEntry 262 }

rcTlsTdiStndTxCirFrames     OBJECT-TYPE
        SYNTAX        Counter64
        MAX-ACCESS    read-only
        STATUS        current
        DESCRIPTION  "Number of Standard Service Tx CIR Frames received."
        ::= { rcTlsTdiStatsEntry 263 }

rcTlsTdiStndTxCirOopFrames     OBJECT-TYPE
        SYNTAX        Counter64
        MAX-ACCESS    read-only
        STATUS        current
        DESCRIPTION  "Number of Standard Service Tx Frames received that 
		      were CIR OOP."
        ::= { rcTlsTdiStatsEntry 264 }

rcTlsTdiStndTxEirFrames     OBJECT-TYPE
        SYNTAX        Counter64
        MAX-ACCESS    read-only
        STATUS        current
        DESCRIPTION  "Number of Standard Service Tx EIR Frames received."
        ::= { rcTlsTdiStatsEntry 265 }

rcTlsTdiStndTxEirOopFrames     OBJECT-TYPE
        SYNTAX        Counter64
        MAX-ACCESS    read-only
        STATUS        current
        DESCRIPTION  "Number of Standard Service Tx Frames received that 
		      were EIR OOP."
        ::= { rcTlsTdiStatsEntry 266 }

rcTlsTdiStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcTlsTdiStatsEntry 267 }

rcTlsTdiStndTxPirFrames     OBJECT-TYPE
        SYNTAX        Counter64
        MAX-ACCESS    read-only
        STATUS        current
        DESCRIPTION  "Number of Standard Service Tx PIR Frames received."
        ::= { rcTlsTdiStatsEntry 268 }

rcTlsTdiStndTxPirOopFrames     OBJECT-TYPE
        SYNTAX        Counter64
        MAX-ACCESS    read-only
        STATUS        current
        DESCRIPTION  "Number of Standard Service Tx Frames received that 
		      were PIR OOP."
        ::= { rcTlsTdiStatsEntry 269 }

rcTlsTdiStndTxGreenFrames     OBJECT-TYPE
        SYNTAX        Counter64
        MAX-ACCESS    read-only
        STATUS        current
        DESCRIPTION  "Number of Standard Service Tx Frames received that 
		      were marked 'Green' by the policer."
        ::= { rcTlsTdiStatsEntry 270 }

rcTlsTdiStndTxYellowFrames     OBJECT-TYPE
        SYNTAX        Counter64
        MAX-ACCESS    read-only
        STATUS        current
        DESCRIPTION  "Number of Standard Service Tx Frames received that 
		      were marked 'Yellow' by the policer."
        ::= { rcTlsTdiStatsEntry 271 }

rcTlsTdiStndTxRedFrames     OBJECT-TYPE
        SYNTAX        Counter64
        MAX-ACCESS    read-only
        STATUS        current
        DESCRIPTION  "Number of Standard Service Tx Frames received that 
		      were marked 'Red' by the policer."
        ::= { rcTlsTdiStatsEntry 272 }

rcTlsTdiMcastTxDroppedFrames     OBJECT-TYPE
        SYNTAX        Counter64
        MAX-ACCESS    read-only
        STATUS        current
        DESCRIPTION  "Number of Multicast Tx Frames dropped."
        ::= { rcTlsTdiStatsEntry 273 }

rcTlsTdiBcastUUcastTxTotalFrames     OBJECT-TYPE
        SYNTAX        Counter64
        MAX-ACCESS    read-only
        STATUS        current
        DESCRIPTION  "Number of Broadcast/Unknown Unicast Tx total Frames."
        ::= { rcTlsTdiStatsEntry 274 }

rcTlsTdiBcastUUcastTxDroppedFrames     OBJECT-TYPE
        SYNTAX        Counter64
        MAX-ACCESS    read-only
        STATUS        current
        DESCRIPTION  "Number of Broadcast/Unknown Tx Frames dropped."
        ::= { rcTlsTdiStatsEntry 275 }

rcTlsTdiDropClassRxDroppedOctets     OBJECT-TYPE
        SYNTAX        Counter64
        MAX-ACCESS    read-only
        STATUS        current
        DESCRIPTION  "Number of Drop Class Rx Octets dropped."
        ::= { rcTlsTdiStatsEntry 276 }

rcTlsTdiDropClassRxDroppedFrames     OBJECT-TYPE
        SYNTAX        Counter64
        MAX-ACCESS    read-only
        STATUS        current
        DESCRIPTION  "Number of Drop Class Rx Frames dropped."
        ::= { rcTlsTdiStatsEntry 277 }

rcTlsTdiDropClassTxDroppedOctets	OBJECT-TYPE
        SYNTAX        Counter64
        MAX-ACCESS    read-only
        STATUS        current
        DESCRIPTION  "Number of Drop Class Tx Octets dropped."
        ::= { rcTlsTdiStatsEntry 278 }

rcTlsTdiDropClassTxDroppedFrames     OBJECT-TYPE
        SYNTAX        Counter64
        MAX-ACCESS    read-only
        STATUS        current
        DESCRIPTION  "Number of Drop Class Tx Frames dropped."
        ::= { rcTlsTdiStatsEntry 279 }


  
-- TLS ENDPT STATS TABLE

rcTlsEndptStatsTable OBJECT-TYPE
        SYNTAX        SEQUENCE OF RcTlsEndptStatsEntry
        MAX-ACCESS    not-accessible
        STATUS        current
        DESCRIPTION   ""
        ::= { rcTls 8 }
 
rcTlsEndptStatsEntry OBJECT-TYPE
        SYNTAX        RcTlsEndptStatsEntry
        MAX-ACCESS    not-accessible
        STATUS        current
        DESCRIPTION   "A Tls End-Point Statistics  table entry."
        INDEX         { rcTlsEndptStatsTdId,rcTlsEndptStatsUniAddr }
        ::= { rcTlsEndptStatsTable 1 }
 
RcTlsEndptStatsEntry ::=
        SEQUENCE {
                rcTlsEndptStatsTdId		INTEGER, 
 		rcTlsEndptStatsUniAddr          INTEGER,	
                rcTlsEndptPremRxOctets		      Counter64,	
       		rcTlsEndptPremRxDroppedOctets   Counter64,
		rcTlsEndptGoldRxOctets		      Counter64,	
		rcTlsEndptGoldRxDroppedOctets   Counter64,
		rcTlsEndptSilverRxOctets	      Counter64,	
		rcTlsEndptSilverRxDroppedOctets Counter64,
		rcTlsEndptStndRxOctets	      	Counter64,	
		rcTlsEndptStndRxDroppedOctets   Counter64,
		rcTlsEndptPremTxOctets	      	Counter64,	
		rcTlsEndptGoldTxOctets	      	Counter64,	
		rcTlsEndptSilverTxOctets	      Counter64,
		rcTlsEndptStndTxOctets	      	Counter64,	
		rcTlsEndptPremTxMcastOctets     Counter64,	
		rcTlsEndptGoldTxMcastOctets     Counter64,	
		rcTlsEndptSilverTxMcastOctets   Counter64,
		rcTlsEndptStndTxMcastOctets     Counter64,
                rcTlsEndptStatsClear            TruthValue,
		rcTlsEndptPremCongestionDropOctets Counter64,
		rcTlsEndptGoldCongestionDropOctets Counter64,
		rcTlsEndptSilverCongestionDropOctets Counter64,	
		rcTlsEndptStndCongestionDropOctets Counter64,	
		rcTlsEndptPremCirDroppedOctets   Counter64,
		rcTlsEndptPremPirDroppedOctets   Counter64,
		rcTlsEndptGoldCirDroppedOctets   Counter64,
		rcTlsEndptGoldPirDroppedOctets   Counter64,
		rcTlsEndptSilverCirDroppedOctets   Counter64,
		rcTlsEndptSilverPirDroppedOctets   Counter64,
		rcTlsEndptStndCirDroppedOctets   Counter64,
		rcTlsEndptStndPirDroppedOctets   Counter64,
		rcTlsEndptName                   DisplayString,
		rcTlsEndptPremTxDroppedOctets	       Counter64,	
		rcTlsEndptGoldTxDroppedOctets	       Counter64,	
		rcTlsEndptSilverTxDroppedOctets	       Counter64,
		rcTlsEndptStndTxDroppedOctets	       Counter64,	
		rcTlsEndptPremTxCongestionDropOctets   Counter64,
		rcTlsEndptGoldTxCongestionDropOctets   Counter64,
		rcTlsEndptSilverTxCongestionDropOctets Counter64,	
		rcTlsEndptStndTxCongestionDropOctets   Counter64,	
		rcTlsEndptPremTxCirDroppedOctets       Counter64,
		rcTlsEndptPremTxPirDroppedOctets       Counter64,
		rcTlsEndptGoldTxCirDroppedOctets       Counter64,
		rcTlsEndptGoldTxPirDroppedOctets       Counter64,
		rcTlsEndptSilverTxCirDroppedOctets     Counter64,
		rcTlsEndptSilverTxPirDroppedOctets     Counter64,
		rcTlsEndptStndTxCirDroppedOctets       Counter64,
		rcTlsEndptStndTxPirDroppedOctets       Counter64,
		rcTlsEndptRxMcastTotalOctets           Counter64,
		rcTlsEndptTxMcastTotalOctets           Counter64,
		rcTlsEndptPremRxMcastDroppedOctets     Counter64,
		rcTlsEndptGoldRxMcastDroppedOctets     Counter64,
		rcTlsEndptSilverRxMcastDroppedOctets   Counter64,
		rcTlsEndptStndRxMcastDroppedOctets     Counter64,
		rcTlsEndptPremRxFrames                 Counter64,
       		rcTlsEndptPremRxDroppedFrames          Counter64,
		rcTlsEndptGoldRxFrames	               Counter64,
		rcTlsEndptGoldRxDroppedFrames          Counter64,
		rcTlsEndptSilverRxFrames               Counter64,
		rcTlsEndptSilverRxDroppedFrames        Counter64,
		rcTlsEndptStndRxFrames                 Counter64,
		rcTlsEndptStndRxDroppedFrames          Counter64,
		rcTlsEndptPremTxFrames                 Counter64,
		rcTlsEndptGoldTxFrames                 Counter64,
		rcTlsEndptSilverTxFrames               Counter64,
		rcTlsEndptStndTxFrames                 Counter64,
		rcTlsEndptPremTxMcastFrames            Counter64,
		rcTlsEndptGoldTxMcastFrames            Counter64,
		rcTlsEndptSilverTxMcastFrames          Counter64,
		rcTlsEndptStndTxMcastFrames            Counter64,
		rcTlsEndptPremCongestionDropFrames     Counter64,
		rcTlsEndptGoldCongestionDropFrames     Counter64,
		rcTlsEndptSilverCongestionDropFrames   Counter64,
		rcTlsEndptStndCongestionDropFrames     Counter64,
		rcTlsEndptPremCirDroppedFrames         Counter64,
		rcTlsEndptPremPirDroppedFrames         Counter64,
		rcTlsEndptGoldCirDroppedFrames         Counter64,
		rcTlsEndptGoldPirDroppedFrames         Counter64,
		rcTlsEndptSilverCirDroppedFrames       Counter64,
		rcTlsEndptSilverPirDroppedFrames       Counter64,
		rcTlsEndptStndCirDroppedFrames         Counter64,
		rcTlsEndptStndPirDroppedFrames         Counter64,
		rcTlsEndptPremTxDroppedFrames	       Counter64,
		rcTlsEndptGoldTxDroppedFrames	       Counter64,
		rcTlsEndptSilverTxDroppedFrames	       Counter64,
		rcTlsEndptStndTxDroppedFrames	       Counter64,
		rcTlsEndptPremTxCongestionDropFrames   Counter64,
		rcTlsEndptGoldTxCongestionDropFrames   Counter64,
		rcTlsEndptSilverTxCongestionDropFrames Counter64,
		rcTlsEndptStndTxCongestionDropFrames   Counter64,
		rcTlsEndptPremTxCirDroppedFrames       Counter64,
		rcTlsEndptPremTxPirDroppedFrames       Counter64,
		rcTlsEndptGoldTxCirDroppedFrames       Counter64,
		rcTlsEndptGoldTxPirDroppedFrames       Counter64,
		rcTlsEndptSilverTxCirDroppedFrames     Counter64,
		rcTlsEndptSilverTxPirDroppedFrames     Counter64,
		rcTlsEndptStndTxCirDroppedFrames       Counter64,
		rcTlsEndptStndTxPirDroppedFrames       Counter64,
		rcTlsEndptRxMcastTotalFrames           Counter64,
		rcTlsEndptTxMcastTotalFrames           Counter64,
		rcTlsEndptPremRxMcastDroppedFrames     Counter64,
		rcTlsEndptGoldRxMcastDroppedFrames     Counter64,
		rcTlsEndptSilverRxMcastDroppedFrames   Counter64,
		rcTlsEndptStndRxMcastDroppedFrames     Counter64,
		rcTlsEndptPremRxCirOctets			Counter64,
		rcTlsEndptPremRxCirOopOctets		Counter64,
		rcTlsEndptPremRxEirOctets			Counter64,
		rcTlsEndptPremRxEirOopOctets		Counter64,
		rcTlsEndptPremRxEirDroppedOctets		Counter64,
		rcTlsEndptPremRxPirOctets			Counter64,
		rcTlsEndptPremRxPirOopOctets		Counter64,
		rcTlsEndptPremRxGreenOctets		Counter64,
		rcTlsEndptPremRxYellowOctets		Counter64,
		rcTlsEndptPremRxRedOctets			Counter64,
		rcTlsEndptGoldRxCirOctets			Counter64,
		rcTlsEndptGoldRxCirOopOctets		Counter64,
		rcTlsEndptGoldRxEirOctets			Counter64,
		rcTlsEndptGoldRxEirOopOctets		Counter64,
		rcTlsEndptGoldRxEirDroppedOctets		Counter64,
		rcTlsEndptGoldRxPirOctets			Counter64,
		rcTlsEndptGoldRxPirOopOctets		Counter64,
		rcTlsEndptGoldRxGreenOctets			Counter64,
		rcTlsEndptGoldRxYellowOctets		Counter64,
		rcTlsEndptGoldRxRedOctets			Counter64,
		rcTlsEndptSilverRxCirOctets			Counter64,
		rcTlsEndptSilverRxCirOopOctets		Counter64,
		rcTlsEndptSilverRxEirOctets			Counter64,
		rcTlsEndptSilverRxEirOopOctets		Counter64,
		rcTlsEndptSilverRxEirDroppedOctets		Counter64,
		rcTlsEndptSilverRxPirOctets			Counter64,
		rcTlsEndptSilverRxPirOopOctets		Counter64,
		rcTlsEndptSilverRxGreenOctets		Counter64,
		rcTlsEndptSilverRxYellowOctets		Counter64,
		rcTlsEndptSilverRxRedOctets			Counter64,
		rcTlsEndptStndRxCirOctets			Counter64,
		rcTlsEndptStndRxCirOopOctets		Counter64,
		rcTlsEndptStndRxEirOctets			Counter64,
		rcTlsEndptStndRxEirOopOctets		Counter64,
		rcTlsEndptStndRxEirDroppedOctets		Counter64,
		rcTlsEndptStndRxPirOctets			Counter64,
		rcTlsEndptStndRxPirOopOctets		Counter64,
		rcTlsEndptStndRxGreenOctets			Counter64,
		rcTlsEndptStndRxYellowOctets		Counter64,
		rcTlsEndptStndRxRedOctets			Counter64,
		rcTlsEndptMcastRxDroppedOctets		Counter64,
		rcTlsEndptBcastUUcastRxTotalOctets		Counter64,
		rcTlsEndptBcastUUcastRxDroppedOctets	Counter64,
		rcTlsEndptPremRxCirFrames			Counter64,
		rcTlsEndptPremRxCirOopFrames		Counter64,
		rcTlsEndptPremRxEirFrames			Counter64,
		rcTlsEndptPremRxEirOopFrames		Counter64,
		rcTlsEndptPremRxEirDroppedFrames		Counter64,
		rcTlsEndptPremRxPirFrames			Counter64,
		rcTlsEndptPremRxPirOopFrames		Counter64,
		rcTlsEndptPremRxGreenFrames		Counter64,
		rcTlsEndptPremRxYellowFrames		Counter64,
		rcTlsEndptPremRxRedFrames			Counter64,
		rcTlsEndptGoldRxCirFrames			Counter64,
		rcTlsEndptGoldRxCirOopFrames		Counter64,
		rcTlsEndptGoldRxEirFrames			Counter64,
		rcTlsEndptGoldRxEirOopFrames		Counter64,
		rcTlsEndptGoldRxEirDroppedFrames		Counter64,
		rcTlsEndptGoldRxPirFrames			Counter64,
		rcTlsEndptGoldRxPirOopFrames		Counter64,
		rcTlsEndptGoldRxGreenFrames		Counter64,
		rcTlsEndptGoldRxYellowFrames		Counter64,
		rcTlsEndptGoldRxRedFrames			Counter64,
		rcTlsEndptSilverRxCirFrames			Counter64,
		rcTlsEndptSilverRxCirOopFrames		Counter64,
		rcTlsEndptSilverRxEirFrames			Counter64,
		rcTlsEndptSilverRxEirOopFrames		Counter64,
		rcTlsEndptSilverRxEirDroppedFrames		Counter64,
		rcTlsEndptSilverRxPirFrames			Counter64,
		rcTlsEndptSilverRxPirOopFrames		Counter64,
		rcTlsEndptSilverRxGreenFrames		Counter64,
		rcTlsEndptSilverRxYellowFrames		Counter64,
		rcTlsEndptSilverRxRedFrames			Counter64,
		rcTlsEndptStndRxCirFrames			Counter64,
		rcTlsEndptStndRxCirOopFrames		Counter64,
		rcTlsEndptStndRxEirFrames			Counter64,
		rcTlsEndptStndRxEirOopFrames		Counter64,
		rcTlsEndptStndRxEirDroppedFrames		Counter64,
		rcTlsEndptStndRxPirFrames			Counter64,
		rcTlsEndptStndRxPirOopFrames		Counter64,
		rcTlsEndptStndRxGreenFrames		Counter64,
		rcTlsEndptStndRxYellowFrames		Counter64,
		rcTlsEndptStndRxRedFrames			Counter64,
		rcTlsEndptMcastRxDroppedFrames		Counter64,
		rcTlsEndptBcastUUcastRxTotalFrames		Counter64,
		rcTlsEndptBcastUUcastRxDroppedFrames	Counter64,
		rcTlsEndptPremTxCirOctets			Counter64,
		rcTlsEndptPremTxCirOopOctets		Counter64,
		rcTlsEndptPremTxEirOctets			Counter64,
		rcTlsEndptPremTxEirOopOctets		Counter64,
		rcTlsEndptPremTxEirDroppedOctets		Counter64,
		rcTlsEndptPremTxPirOctets			Counter64,
		rcTlsEndptPremTxPirOopOctets		Counter64,
		rcTlsEndptPremTxGreenOctets			Counter64,
		rcTlsEndptPremTxYellowOctets		Counter64,
		rcTlsEndptPremTxRedOctets			Counter64,
		rcTlsEndptGoldTxCirOctets			Counter64,
		rcTlsEndptGoldTxCirOopOctets		Counter64,
		rcTlsEndptGoldTxEirOctets			Counter64,
		rcTlsEndptGoldTxEirOopOctets		Counter64,
		rcTlsEndptGoldTxEirDroppedOctets		Counter64,
		rcTlsEndptGoldTxPirOctets			Counter64,
		rcTlsEndptGoldTxPirOopOctets		Counter64,
		rcTlsEndptGoldTxGreenOctets			Counter64,
		rcTlsEndptGoldTxYellowOctets			Counter64,
		rcTlsEndptGoldTxRedOctets			Counter64,
		rcTlsEndptSilverTxCirOctets			Counter64,
		rcTlsEndptSilverTxCirOopOctets		Counter64,
		rcTlsEndptSilverTxEirOctets			Counter64,
		rcTlsEndptSilverTxEirOopOctets		Counter64,
		rcTlsEndptSilverTxEirDroppedOctets		Counter64,
		rcTlsEndptSilverTxPirOctets			Counter64,
		rcTlsEndptSilverTxPirOopOctets		Counter64,
		rcTlsEndptSilverTxGreenOctets		Counter64,
		rcTlsEndptSilverTxYellowOctets		Counter64,
		rcTlsEndptSilverTxRedOctets			Counter64,
		rcTlsEndptStndTxCirOctets			Counter64,
		rcTlsEndptStndTxCirOopOctets		Counter64,
		rcTlsEndptStndTxEirOctets			Counter64,
		rcTlsEndptStndTxEirOopOctets		Counter64,
		rcTlsEndptStndTxEirDroppedOctets		Counter64,
		rcTlsEndptStndTxPirOctets			Counter64,
		rcTlsEndptStndTxPirOopOctets		Counter64,
		rcTlsEndptStndTxGreenOctets			Counter64,
		rcTlsEndptStndTxYellowOctets			Counter64,
		rcTlsEndptStndTxRedOctets			Counter64,
		rcTlsEndptMcastTxDroppedOctets		Counter64,
		rcTlsEndptBcastUUcastTxTotalOctets		Counter64,
		rcTlsEndptBcastUUcastTxDroppedOctets		Counter64,
		rcTlsEndptPremTxCirFrames			Counter64,
		rcTlsEndptPremTxCirOopFrames		Counter64,
		rcTlsEndptPremTxEirFrames			Counter64,
		rcTlsEndptPremTxEirOopFrames		Counter64,
		rcTlsEndptPremTxEirDroppedFrames		Counter64,
		rcTlsEndptPremTxPirFrames			Counter64,
		rcTlsEndptPremTxPirOopFrames		Counter64,
		rcTlsEndptPremTxGreenFrames		Counter64,
		rcTlsEndptPremTxYellowFrames		Counter64,
		rcTlsEndptPremTxRedFrames			Counter64,
		rcTlsEndptGoldTxCirFrames			Counter64,
		rcTlsEndptGoldTxCirOopFrames		Counter64,
		rcTlsEndptGoldTxEirFrames			Counter64,
		rcTlsEndptGoldTxEirOopFrames		Counter64,
		rcTlsEndptGoldTxEirDroppedFrames		Counter64,
		rcTlsEndptGoldTxPirFrames			Counter64,
		rcTlsEndptGoldTxPirOopFrames		Counter64,
		rcTlsEndptGoldTxGreenFrames		Counter64,
		rcTlsEndptGoldTxYellowFrames		Counter64,
		rcTlsEndptGoldTxRedFrames			Counter64,
		rcTlsEndptSilverTxCirFrames			Counter64,
		rcTlsEndptSilverTxCirOopFrames		Counter64,
		rcTlsEndptSilverTxEirFrames			Counter64,
		rcTlsEndptSilverTxEirOopFrames		Counter64,
		rcTlsEndptSilverTxEirDroppedFrames		Counter64,
		rcTlsEndptSilverTxPirFrames			Counter64,
		rcTlsEndptSilverTxPirOopFrames		Counter64,
		rcTlsEndptSilverTxGreenFrames		Counter64,
		rcTlsEndptSilverTxYellowFrames		Counter64,
		rcTlsEndptSilverTxRedFrames			Counter64,
		rcTlsEndptStndTxCirFrames			Counter64,
		rcTlsEndptStndTxCirOopFrames		Counter64,
		rcTlsEndptStndTxEirFrames			Counter64,
		rcTlsEndptStndTxEirOopFrames		Counter64,
		rcTlsEndptStndTxEirDroppedFrames		Counter64,
		rcTlsEndptStndTxPirFrames			Counter64,
		rcTlsEndptStndTxPirOopFrames		Counter64,
		rcTlsEndptStndTxGreenFrames		Counter64,
		rcTlsEndptStndTxYellowFrames		Counter64,
		rcTlsEndptStndTxRedFrames			Counter64,
		rcTlsEndptMcastTxDroppedFrames		Counter64,
		rcTlsEndptBcastUUcastTxTotalFrames		Counter64,
		rcTlsEndptBcastUUcastTxDroppedFrames	Counter64,
		rcTlsEndptDropClassRxDroppedOctets  		Counter64,
		rcTlsEndptDropClassRxDroppedFrames  		Counter64,
		rcTlsEndptDropClassTxDroppedOctets  		Counter64,
		rcTlsEndptDropClassTxDroppedFrames  		Counter64

      }

rcTlsEndptStatsTdId OBJECT-TYPE
        SYNTAX        INTEGER (1..16777215)
        MAX-ACCESS    read-only
        STATUS        current
        DESCRIPTION   "Tdi that the end-point is a member of."
        ::= { rcTlsEndptStatsEntry 1 }

 rcTlsEndptStatsUniAddr OBJECT-TYPE
        SYNTAX        INTEGER (1..16777215)
        MAX-ACCESS    read-only
        STATUS        current
        DESCRIPTION   "Transparent Domaine Identifier."
        ::= { rcTlsEndptStatsEntry 2 }
 
 rcTlsEndptPremRxOctets	OBJECT-TYPE
        SYNTAX        Counter64
        MAX-ACCESS    read-only
        STATUS        current
        DESCRIPTION  "Number of Premium Service Octets received from This End-Point."
        ::= { rcTlsEndptStatsEntry 3 } 

 rcTlsEndptPremRxDroppedOctets	OBJECT-TYPE
        SYNTAX        Counter64
        MAX-ACCESS    read-only
        STATUS        current
        DESCRIPTION  "Number of Premium Service Octets dropped from This End-Point."
        ::= { rcTlsEndptStatsEntry 4 } 
       
 rcTlsEndptGoldRxOctets	OBJECT-TYPE
        SYNTAX        Counter64
        MAX-ACCESS    read-only
        STATUS        current
        DESCRIPTION  "Number of Gold Service Octets received from This End-Point."
        ::= { rcTlsEndptStatsEntry 5 } 

 rcTlsEndptGoldRxDroppedOctets	OBJECT-TYPE
        SYNTAX        Counter64
        MAX-ACCESS    read-only
        STATUS        current
        DESCRIPTION  "Number of Gold Service Octets dropped from This End-Point."
        ::= { rcTlsEndptStatsEntry 6 } 
       

 rcTlsEndptSilverRxOctets	OBJECT-TYPE
        SYNTAX        Counter64
        MAX-ACCESS    read-only
        STATUS        current
        DESCRIPTION  "Number of Silver Service Octets received from This End-Point."
        ::= { rcTlsEndptStatsEntry 7 } 

 rcTlsEndptSilverRxDroppedOctets	OBJECT-TYPE
        SYNTAX        Counter64
        MAX-ACCESS    read-only
        STATUS        current
        DESCRIPTION  "Number of Silver Service Octets dropped from This End-Point."
        ::= { rcTlsEndptStatsEntry 8 } 
       
 rcTlsEndptStndRxOctets	OBJECT-TYPE
        SYNTAX        Counter64
        MAX-ACCESS    read-only
        STATUS        current
        DESCRIPTION  "Number of Standard (Best Effort) Service Octets received from This End-Point."
        ::= { rcTlsEndptStatsEntry 9 } 

 rcTlsEndptStndRxDroppedOctets	OBJECT-TYPE
        SYNTAX        Counter64
        MAX-ACCESS    read-only
        STATUS        current
        DESCRIPTION  "Number of Standard(BestEffort) Service Octets dropped from this End-Point."
        ::= { rcTlsEndptStatsEntry 10 } 
       
 rcTlsEndptPremTxOctets	OBJECT-TYPE
        SYNTAX        Counter64
        MAX-ACCESS    read-only
        STATUS        current
        DESCRIPTION  "Number of Premium Service Octets sent to his End-Point."
        ::= { rcTlsEndptStatsEntry 11 } 

 rcTlsEndptGoldTxOctets	OBJECT-TYPE
        SYNTAX        Counter64
        MAX-ACCESS    read-only
        STATUS        current
        DESCRIPTION  "Number of Gold Service Octets sent to his End-Point."
        ::= { rcTlsEndptStatsEntry 12 } 

 rcTlsEndptSilverTxOctets	OBJECT-TYPE
        SYNTAX        Counter64
        MAX-ACCESS    read-only
        STATUS        current
        DESCRIPTION  "Number of Silver Service Octets sent to his End-Point."
        ::= { rcTlsEndptStatsEntry 13 } 

 rcTlsEndptStndTxOctets	OBJECT-TYPE
        SYNTAX        Counter64
        MAX-ACCESS    read-only
        STATUS        current
        DESCRIPTION  "Number of Standard Service Octets sent to his End-Point."
        ::= { rcTlsEndptStatsEntry 14 } 
		

 rcTlsEndptPremTxMcastOctets	OBJECT-TYPE
        SYNTAX        Counter64
        MAX-ACCESS    read-only
        STATUS        current
        DESCRIPTION  "Number of Premium Service Multicast sent to his End-Point."
        ::= { rcTlsEndptStatsEntry 15 } 

rcTlsEndptGoldTxMcastOctets	OBJECT-TYPE
        SYNTAX        Counter64
        MAX-ACCESS    read-only
        STATUS        current
        DESCRIPTION  "Number of GoldService Multicast sent to his End-Point."
        ::= { rcTlsEndptStatsEntry 16 } 
		

rcTlsEndptSilverTxMcastOctets	OBJECT-TYPE
        SYNTAX        Counter64
        MAX-ACCESS    read-only
        STATUS        current
        DESCRIPTION  "Number of SilverService Multicast sent to his End-Point."
        ::= { rcTlsEndptStatsEntry 17 } 

rcTlsEndptStndTxMcastOctets	OBJECT-TYPE
        SYNTAX        Counter64
        MAX-ACCESS    read-only
        STATUS        current 
        DESCRIPTION  "Number of Premium Service Multicast sent to his End-Point."
        ::= { rcTlsEndptStatsEntry 18     } 

rcTlsEndptStatsClear      OBJECT-TYPE
        SYNTAX        TruthValue
        MAX-ACCESS    read-write
        STATUS        current
        DESCRIPTION   "Clear statistic."
        ::= { rcTlsEndptStatsEntry 19 }

rcTlsEndptPremCongestionDropOctets	OBJECT-TYPE
        SYNTAX        Counter64
        MAX-ACCESS    read-only
        STATUS        current
        DESCRIPTION  "Number of Prem Service Octets congestion drop"
        ::= { rcTlsEndptStatsEntry 20 } 
       
rcTlsEndptGoldCongestionDropOctets	OBJECT-TYPE
        SYNTAX        Counter64
        MAX-ACCESS    read-only
        STATUS        current
        DESCRIPTION  "Number of Gold Service Octets congestion drop"
        ::= { rcTlsEndptStatsEntry 21 } 

rcTlsEndptSilverCongestionDropOctets	OBJECT-TYPE
        SYNTAX        Counter64
        MAX-ACCESS    read-only
        STATUS        current
        DESCRIPTION  "Number of Silver Service Octets congestion drop"
        ::= { rcTlsEndptStatsEntry 22 } 

rcTlsEndptStndCongestionDropOctets	OBJECT-TYPE
        SYNTAX        Counter64
        MAX-ACCESS    read-only
        STATUS        current
        DESCRIPTION  "Number of Standard Service Octets congestion drop"
        ::= { rcTlsEndptStatsEntry 23 }

rcTlsEndptPremCirDroppedOctets	OBJECT-TYPE
        SYNTAX        Counter64
        MAX-ACCESS    read-only
        STATUS        current
        DESCRIPTION  "Number of Prem Service Octets CIR drop"
        ::= { rcTlsEndptStatsEntry 24 }

rcTlsEndptPremPirDroppedOctets	OBJECT-TYPE
        SYNTAX        Counter64
        MAX-ACCESS    read-only
        STATUS        current
        DESCRIPTION  "Number of Prem Service Octets PIR drop"
        ::= { rcTlsEndptStatsEntry 25 }
  
rcTlsEndptGoldCirDroppedOctets	OBJECT-TYPE
        SYNTAX        Counter64
        MAX-ACCESS    read-only
        STATUS        current
        DESCRIPTION  "Number of Gold Service Octets CIR drop"
        ::= { rcTlsEndptStatsEntry 26 }

rcTlsEndptGoldPirDroppedOctets	OBJECT-TYPE
        SYNTAX        Counter64
        MAX-ACCESS    read-only
        STATUS        current
        DESCRIPTION  "Number of Gold Service Octets PIR drop"
        ::= { rcTlsEndptStatsEntry 27 }

rcTlsEndptSilverCirDroppedOctets	OBJECT-TYPE
        SYNTAX        Counter64
        MAX-ACCESS    read-only
        STATUS        current
        DESCRIPTION  "Number of Silver Service Octets CIR drop"
        ::= { rcTlsEndptStatsEntry 28 }

rcTlsEndptSilverPirDroppedOctets	OBJECT-TYPE
        SYNTAX        Counter64
        MAX-ACCESS    read-only
        STATUS        current
        DESCRIPTION  "Number of Silver Service Octets PIR drop"
        ::= { rcTlsEndptStatsEntry 29 }

rcTlsEndptStndCirDroppedOctets	OBJECT-TYPE
        SYNTAX        Counter64
        MAX-ACCESS    read-only
        STATUS        current
        DESCRIPTION  "Number of Standard Service Octets CIR drop"
        ::= { rcTlsEndptStatsEntry 30 }  

rcTlsEndptStndPirDroppedOctets	OBJECT-TYPE
        SYNTAX        Counter64
        MAX-ACCESS    read-only
        STATUS        current
        DESCRIPTION  "Number of Standard Service Octets PIR drop"
        ::= { rcTlsEndptStatsEntry 31 } 
 
rcTlsEndptName OBJECT-TYPE
        SYNTAX        DisplayString (SIZE (0..30)) 
        MAX-ACCESS    read-only
        STATUS        current
        DESCRIPTION   "Name of Endpoint, By default, it would be EP-<tdi>.<uni>.
		       Example: tdi = 1, uni = 0.0.0.1, rcTlsTdiEndptName would
		       be EP-1.0.0.0.1"
        ::= { rcTlsEndptStatsEntry 32 }

rcTlsEndptPremTxDroppedOctets	OBJECT-TYPE
        SYNTAX        Counter64
        MAX-ACCESS    read-only
        STATUS        current
        DESCRIPTION  "Tx Number of Premium Service Octets dropped from This End-Point."
        ::= { rcTlsEndptStatsEntry 33 } 

rcTlsEndptGoldTxDroppedOctets	OBJECT-TYPE
        SYNTAX        Counter64
        MAX-ACCESS    read-only
        STATUS        current
        DESCRIPTION  "Tx Number of Gold Service Octets dropped from This End-Point."
        ::= { rcTlsEndptStatsEntry 34 } 
       
rcTlsEndptSilverTxDroppedOctets	OBJECT-TYPE
        SYNTAX        Counter64
        MAX-ACCESS    read-only
        STATUS        current
        DESCRIPTION  "Tx Number of Silver Service Octets dropped from This End-Point."
        ::= { rcTlsEndptStatsEntry 35 } 
       
rcTlsEndptStndTxDroppedOctets	OBJECT-TYPE
        SYNTAX        Counter64
        MAX-ACCESS    read-only
        STATUS        current
        DESCRIPTION  "Tx Number of Standard(BestEffort) Service Octets dropped from this End-Point."
        ::= { rcTlsEndptStatsEntry 36 } 

rcTlsEndptPremTxCongestionDropOctets	OBJECT-TYPE
        SYNTAX        Counter64
        MAX-ACCESS    read-only
        STATUS        current
        DESCRIPTION  "Tx Number of Prem Service Octets congestion drop"
        ::= { rcTlsEndptStatsEntry 37 } 
       
rcTlsEndptGoldTxCongestionDropOctets	OBJECT-TYPE
        SYNTAX        Counter64
        MAX-ACCESS    read-only
        STATUS        current
        DESCRIPTION  "Tx Number of Gold Service Octets congestion drop"
        ::= { rcTlsEndptStatsEntry 38 } 

rcTlsEndptSilverTxCongestionDropOctets	OBJECT-TYPE
        SYNTAX        Counter64
        MAX-ACCESS    read-only
        STATUS        current
        DESCRIPTION  "Tx Number of Silver Service Octets congestion drop"
        ::= { rcTlsEndptStatsEntry 39 } 

rcTlsEndptStndTxCongestionDropOctets	OBJECT-TYPE
        SYNTAX        Counter64
        MAX-ACCESS    read-only
        STATUS        current
        DESCRIPTION  "Tx Number of Standard Service Octets congestion drop"
        ::= { rcTlsEndptStatsEntry 40 }

rcTlsEndptPremTxCirDroppedOctets	OBJECT-TYPE
        SYNTAX        Counter64
        MAX-ACCESS    read-only
        STATUS        current
        DESCRIPTION  "Tx Number of Prem Service Octets CIR drop"
        ::= { rcTlsEndptStatsEntry 41 }

rcTlsEndptPremTxPirDroppedOctets	OBJECT-TYPE
        SYNTAX        Counter64
        MAX-ACCESS    read-only
        STATUS        current
        DESCRIPTION  "Tx Number of Prem Service Octets PIR drop"
        ::= { rcTlsEndptStatsEntry 42 }
  
rcTlsEndptGoldTxCirDroppedOctets	OBJECT-TYPE
        SYNTAX        Counter64
        MAX-ACCESS    read-only
        STATUS        current
        DESCRIPTION  "Tx Number of Gold Service Octets CIR drop"
        ::= { rcTlsEndptStatsEntry 43 }

rcTlsEndptGoldTxPirDroppedOctets	OBJECT-TYPE
        SYNTAX        Counter64
        MAX-ACCESS    read-only
        STATUS        current
        DESCRIPTION  "Tx Number of Gold Service Octets PIR drop"
        ::= { rcTlsEndptStatsEntry 44 }

rcTlsEndptSilverTxCirDroppedOctets	OBJECT-TYPE
        SYNTAX        Counter64
        MAX-ACCESS    read-only
        STATUS        current
        DESCRIPTION  "Tx Number of Silver Service Octets CIR drop"
        ::= { rcTlsEndptStatsEntry 45 }

rcTlsEndptSilverTxPirDroppedOctets	OBJECT-TYPE
        SYNTAX        Counter64
        MAX-ACCESS    read-only
        STATUS        current
        DESCRIPTION  "Tx Number of Silver Service Octets PIR drop"
        ::= { rcTlsEndptStatsEntry 46 }

rcTlsEndptStndTxCirDroppedOctets	OBJECT-TYPE
        SYNTAX        Counter64
        MAX-ACCESS    read-only
        STATUS        current
        DESCRIPTION  "Tx Number of Standard Service Octets CIR drop"
        ::= { rcTlsEndptStatsEntry 47 }  

rcTlsEndptStndTxPirDroppedOctets	OBJECT-TYPE
        SYNTAX        Counter64
        MAX-ACCESS    read-only
        STATUS        current
        DESCRIPTION  "TX Number of Standard Service Octets PIR drop"
        ::= { rcTlsEndptStatsEntry 48 }
 
rcTlsEndptRxMcastTotalOctets	OBJECT-TYPE
        SYNTAX        Counter64
        MAX-ACCESS    read-only
        STATUS        current
        DESCRIPTION  "Rx Total Number of Mcast Octets"
        ::= { rcTlsEndptStatsEntry 49 }
 
rcTlsEndptTxMcastTotalOctets	OBJECT-TYPE
        SYNTAX        Counter64
        MAX-ACCESS    read-only
        STATUS        current
        DESCRIPTION  "TX total Number of Mcast Octets"
        ::= { rcTlsEndptStatsEntry 50 }  

rcTlsEndptPremRxMcastDroppedOctets	OBJECT-TYPE
        SYNTAX        Counter64
        MAX-ACCESS    read-only
        STATUS        current
        DESCRIPTION  "Number of Premium Service Rx Mcast Octets dropped from 
		      This Endpoint."
        ::= { rcTlsEndptStatsEntry 51 } 

rcTlsEndptGoldRxMcastDroppedOctets	OBJECT-TYPE
        SYNTAX        Counter64
        MAX-ACCESS    read-only
        STATUS        current
        DESCRIPTION  "Number of Gold Service Rx Mcast Octets dropped from 
		      This Endpoint."
        ::= { rcTlsEndptStatsEntry 52 } 

rcTlsEndptSilverRxMcastDroppedOctets	OBJECT-TYPE
        SYNTAX        Counter64
        MAX-ACCESS    read-only
        STATUS        current
        DESCRIPTION  "Number of Silver Service Rx Mcast Octets dropped from 
		      This Endpoint."
        ::= { rcTlsEndptStatsEntry 53 } 
                            
rcTlsEndptStndRxMcastDroppedOctets	OBJECT-TYPE
        SYNTAX        Counter64
        MAX-ACCESS    read-only
        STATUS        current
        DESCRIPTION  "Number of Standard Service Rx Mcast Octets dropped from 
		      This Endpoint."
        ::= { rcTlsEndptStatsEntry 54 } 

rcTlsEndptPremRxFrames	OBJECT-TYPE
        SYNTAX        Counter64
        MAX-ACCESS    read-only
        STATUS        current
        DESCRIPTION  "Number of Premium Service Frames received from This End-Point."
        ::= { rcTlsEndptStatsEntry 55 }

rcTlsEndptPremRxDroppedFrames	OBJECT-TYPE
        SYNTAX        Counter64
        MAX-ACCESS    read-only
        STATUS        current
        DESCRIPTION  "Number of Premium Service Frames dropped from This End-Point."
        ::= { rcTlsEndptStatsEntry 56 }

rcTlsEndptGoldRxFrames	OBJECT-TYPE
        SYNTAX        Counter64
        MAX-ACCESS    read-only
        STATUS        current
        DESCRIPTION  "Number of Gold Service Frames received from This End-Point."
        ::= { rcTlsEndptStatsEntry 57 }

rcTlsEndptGoldRxDroppedFrames	OBJECT-TYPE
        SYNTAX        Counter64
        MAX-ACCESS    read-only
        STATUS        current
        DESCRIPTION  "Number of Gold Service Frames dropped from This End-Point."
        ::= { rcTlsEndptStatsEntry 58 }

rcTlsEndptSilverRxFrames	OBJECT-TYPE
        SYNTAX        Counter64
        MAX-ACCESS    read-only
        STATUS        current
        DESCRIPTION  "Number of Silver Service Frames received from This End-Point."
        ::= { rcTlsEndptStatsEntry 59 }

rcTlsEndptSilverRxDroppedFrames	OBJECT-TYPE
        SYNTAX        Counter64
        MAX-ACCESS    read-only
        STATUS        current
        DESCRIPTION  "Number of Silver Service Frames dropped from This End-Point."
        ::= { rcTlsEndptStatsEntry 60 }

rcTlsEndptStndRxFrames	OBJECT-TYPE
        SYNTAX        Counter64
        MAX-ACCESS    read-only
        STATUS        current
        DESCRIPTION  "Number of Standard (Best Effort) Service Frames received from This End-Point."
        ::= { rcTlsEndptStatsEntry 61 }

rcTlsEndptStndRxDroppedFrames	OBJECT-TYPE
        SYNTAX        Counter64
        MAX-ACCESS    read-only
        STATUS        current
        DESCRIPTION  "Number of Standard(BestEffort) Service Frames dropped from this End-Point."
        ::= { rcTlsEndptStatsEntry 62 }

rcTlsEndptPremTxFrames	OBJECT-TYPE
        SYNTAX        Counter64
        MAX-ACCESS    read-only
        STATUS        current
        DESCRIPTION  "Number of Premium Service Frames sent to his End-Point."
        ::= { rcTlsEndptStatsEntry 63 }

rcTlsEndptGoldTxFrames	OBJECT-TYPE
        SYNTAX        Counter64
        MAX-ACCESS    read-only
        STATUS        current
        DESCRIPTION  "Number of Gold Service Frames sent to his End-Point."
        ::= { rcTlsEndptStatsEntry 64 }

rcTlsEndptSilverTxFrames	OBJECT-TYPE
        SYNTAX        Counter64
        MAX-ACCESS    read-only
        STATUS        current
        DESCRIPTION  "Number of Silver Service Frames sent to his End-Point."
        ::= { rcTlsEndptStatsEntry 65 }

rcTlsEndptStndTxFrames	OBJECT-TYPE
        SYNTAX        Counter64
        MAX-ACCESS    read-only
        STATUS        current
        DESCRIPTION  "Number of Standard Service Frames sent to his End-Point."
        ::= { rcTlsEndptStatsEntry 66 }

rcTlsEndptPremTxMcastFrames	OBJECT-TYPE
        SYNTAX        Counter64
        MAX-ACCESS    read-only
        STATUS        current
        DESCRIPTION  "Number of Premium Service Multicast sent to his End-Point."
        ::= { rcTlsEndptStatsEntry 67 }

rcTlsEndptGoldTxMcastFrames	OBJECT-TYPE
        SYNTAX        Counter64
        MAX-ACCESS    read-only
        STATUS        current
        DESCRIPTION  "Number of GoldService Multicast sent to his End-Point."
        ::= { rcTlsEndptStatsEntry 68 }

rcTlsEndptSilverTxMcastFrames	OBJECT-TYPE
        SYNTAX        Counter64
        MAX-ACCESS    read-only
        STATUS        current
        DESCRIPTION  "Number of SilverService Multicast sent to his End-Point."
        ::= { rcTlsEndptStatsEntry 69 }

rcTlsEndptStndTxMcastFrames	OBJECT-TYPE
        SYNTAX        Counter64
        MAX-ACCESS    read-only
        STATUS        current 
        DESCRIPTION  "Number of Premium Service Multicast sent to his End-Point."
        ::= { rcTlsEndptStatsEntry 70 }

rcTlsEndptPremCongestionDropFrames	OBJECT-TYPE
        SYNTAX        Counter64
        MAX-ACCESS    read-only
        STATUS        current
        DESCRIPTION  "Number of Prem Service Frames congestion drop"
        ::= { rcTlsEndptStatsEntry 71 }

rcTlsEndptGoldCongestionDropFrames	OBJECT-TYPE
        SYNTAX        Counter64
        MAX-ACCESS    read-only
        STATUS        current
        DESCRIPTION  "Number of Gold Service Frames congestion drop"
        ::= { rcTlsEndptStatsEntry 72 }

rcTlsEndptSilverCongestionDropFrames	OBJECT-TYPE
        SYNTAX        Counter64
        MAX-ACCESS    read-only
        STATUS        current
        DESCRIPTION  "Number of Silver Service Frames congestion drop"
        ::= { rcTlsEndptStatsEntry 73 }

rcTlsEndptStndCongestionDropFrames	OBJECT-TYPE
        SYNTAX        Counter64
        MAX-ACCESS    read-only
        STATUS        current
        DESCRIPTION  "Number of Standard Service Frames congestion drop"
        ::= { rcTlsEndptStatsEntry 74 }

rcTlsEndptPremCirDroppedFrames	OBJECT-TYPE
        SYNTAX        Counter64
        MAX-ACCESS    read-only
        STATUS        current
        DESCRIPTION  "Number of Prem Service Frames CIR drop"
        ::= { rcTlsEndptStatsEntry 75 }

rcTlsEndptPremPirDroppedFrames	OBJECT-TYPE
        SYNTAX        Counter64
        MAX-ACCESS    read-only
        STATUS        current
        DESCRIPTION  "Number of Prem Service Frames PIR drop"
        ::= { rcTlsEndptStatsEntry 76 }

rcTlsEndptGoldCirDroppedFrames	OBJECT-TYPE
        SYNTAX        Counter64
        MAX-ACCESS    read-only
        STATUS        current
        DESCRIPTION  "Number of Gold Service Frames CIR drop"
        ::= { rcTlsEndptStatsEntry 77 }

rcTlsEndptGoldPirDroppedFrames	OBJECT-TYPE
        SYNTAX        Counter64
        MAX-ACCESS    read-only
        STATUS        current
        DESCRIPTION  "Number of Gold Service Frames PIR drop"
        ::= { rcTlsEndptStatsEntry 78 }

rcTlsEndptSilverCirDroppedFrames	OBJECT-TYPE
        SYNTAX        Counter64
        MAX-ACCESS    read-only
        STATUS        current
        DESCRIPTION  "Number of Silver Service Frames CIR drop"
        ::= { rcTlsEndptStatsEntry 79 }

rcTlsEndptSilverPirDroppedFrames	OBJECT-TYPE
        SYNTAX        Counter64
        MAX-ACCESS    read-only
        STATUS        current
        DESCRIPTION  "Number of Silver Service Frames PIR drop"
        ::= { rcTlsEndptStatsEntry 80 }

rcTlsEndptStndCirDroppedFrames	OBJECT-TYPE
        SYNTAX        Counter64
        MAX-ACCESS    read-only
        STATUS        current
        DESCRIPTION  "Number of Standard Service Frames CIR drop"
        ::= { rcTlsEndptStatsEntry 81 }

rcTlsEndptStndPirDroppedFrames	OBJECT-TYPE
        SYNTAX        Counter64
        MAX-ACCESS    read-only
        STATUS        current
        DESCRIPTION  "Number of Standard Service Frames PIR drop"
        ::= { rcTlsEndptStatsEntry 82 }

rcTlsEndptPremTxDroppedFrames	OBJECT-TYPE
        SYNTAX        Counter64
        MAX-ACCESS    read-only
        STATUS        current
        DESCRIPTION  "Tx Number of Premium Service Frames dropped from This End-Point."
        ::= { rcTlsEndptStatsEntry 83 }

rcTlsEndptGoldTxDroppedFrames	OBJECT-TYPE
        SYNTAX        Counter64
        MAX-ACCESS    read-only
        STATUS        current
        DESCRIPTION  "Tx Number of Gold Service Frames dropped from This End-Point."
        ::= { rcTlsEndptStatsEntry 84 }

rcTlsEndptSilverTxDroppedFrames	OBJECT-TYPE
        SYNTAX        Counter64
        MAX-ACCESS    read-only
        STATUS        current
        DESCRIPTION  "Tx Number of Silver Service Frames dropped from This End-Point."
        ::= { rcTlsEndptStatsEntry 85 }

rcTlsEndptStndTxDroppedFrames	OBJECT-TYPE
        SYNTAX        Counter64
        MAX-ACCESS    read-only
        STATUS        current
        DESCRIPTION  "Tx Number of Standard(BestEffort) Service Frames dropped from this End-Point."
        ::= { rcTlsEndptStatsEntry 86 }

rcTlsEndptPremTxCongestionDropFrames	OBJECT-TYPE
        SYNTAX        Counter64
        MAX-ACCESS    read-only
        STATUS        current
        DESCRIPTION  "Tx Number of Prem Service Frames congestion drop"
        ::= { rcTlsEndptStatsEntry 87 }

rcTlsEndptGoldTxCongestionDropFrames	OBJECT-TYPE
        SYNTAX        Counter64
        MAX-ACCESS    read-only
        STATUS        current
        DESCRIPTION  "Tx Number of Gold Service Frames congestion drop"
        ::= { rcTlsEndptStatsEntry 88 }

rcTlsEndptSilverTxCongestionDropFrames	OBJECT-TYPE
        SYNTAX        Counter64
        MAX-ACCESS    read-only
        STATUS        current
        DESCRIPTION  "Tx Number of Silver Service Frames congestion drop"
        ::= { rcTlsEndptStatsEntry 89 }

rcTlsEndptStndTxCongestionDropFrames	OBJECT-TYPE
        SYNTAX        Counter64
        MAX-ACCESS    read-only
        STATUS        current
        DESCRIPTION  "Tx Number of Standard Service Frames congestion drop"
        ::= { rcTlsEndptStatsEntry 90 }

rcTlsEndptPremTxCirDroppedFrames	OBJECT-TYPE
        SYNTAX        Counter64
        MAX-ACCESS    read-only
        STATUS        current
        DESCRIPTION  "Tx Number of Prem Service Frames CIR drop"
        ::= { rcTlsEndptStatsEntry 91 }

rcTlsEndptPremTxPirDroppedFrames	OBJECT-TYPE
        SYNTAX        Counter64
        MAX-ACCESS    read-only
        STATUS        current
        DESCRIPTION  "Tx Number of Prem Service Frames PIR drop"
        ::= { rcTlsEndptStatsEntry 92 }

rcTlsEndptGoldTxCirDroppedFrames	OBJECT-TYPE
        SYNTAX        Counter64
        MAX-ACCESS    read-only
        STATUS        current
        DESCRIPTION  "Tx Number of Gold Service Frames CIR drop"
        ::= { rcTlsEndptStatsEntry 93 }

rcTlsEndptGoldTxPirDroppedFrames	OBJECT-TYPE
        SYNTAX        Counter64
        MAX-ACCESS    read-only
        STATUS        current
        DESCRIPTION  "Tx Number of Gold Service Frames PIR drop"
        ::= { rcTlsEndptStatsEntry 94 }

rcTlsEndptSilverTxCirDroppedFrames	OBJECT-TYPE
        SYNTAX        Counter64
        MAX-ACCESS    read-only
        STATUS        current
        DESCRIPTION  "Tx Number of Silver Service Frames CIR drop"
        ::= { rcTlsEndptStatsEntry 95 }

rcTlsEndptSilverTxPirDroppedFrames	OBJECT-TYPE
        SYNTAX        Counter64
        MAX-ACCESS    read-only
        STATUS        current
        DESCRIPTION  "Tx Number of Silver Service Frames PIR drop"
        ::= { rcTlsEndptStatsEntry 96 }

rcTlsEndptStndTxCirDroppedFrames	OBJECT-TYPE
        SYNTAX        Counter64
        MAX-ACCESS    read-only
        STATUS        current
        DESCRIPTION  "Tx Number of Standard Service Frames CIR drop"
        ::= { rcTlsEndptStatsEntry 97 }

rcTlsEndptStndTxPirDroppedFrames	OBJECT-TYPE
        SYNTAX        Counter64
        MAX-ACCESS    read-only
        STATUS        current
        DESCRIPTION  "TX Number of Standard Service Frames PIR drop"
        ::= { rcTlsEndptStatsEntry 98 }

rcTlsEndptRxMcastTotalFrames	OBJECT-TYPE
        SYNTAX        Counter64
        MAX-ACCESS    read-only
        STATUS        current
        DESCRIPTION  "Rx Total Number of Mcast Frames"
        ::= { rcTlsEndptStatsEntry 99 }

rcTlsEndptTxMcastTotalFrames	OBJECT-TYPE
        SYNTAX        Counter64
        MAX-ACCESS    read-only
        STATUS        current
        DESCRIPTION  "TX total Number of Mcast Frames"
        ::= { rcTlsEndptStatsEntry 100 }

rcTlsEndptPremRxMcastDroppedFrames	OBJECT-TYPE
        SYNTAX        Counter64
        MAX-ACCESS    read-only
        STATUS        current
        DESCRIPTION  "Number of Premium Service Rx Mcast Frames dropped from
		      This Endpoint."
        ::= { rcTlsEndptStatsEntry 101 }

rcTlsEndptGoldRxMcastDroppedFrames	OBJECT-TYPE
        SYNTAX        Counter64
        MAX-ACCESS    read-only
        STATUS        current
        DESCRIPTION  "Number of Gold Service Rx Mcast Frames dropped from
		      This Endpoint."
        ::= { rcTlsEndptStatsEntry 102 }

rcTlsEndptSilverRxMcastDroppedFrames	OBJECT-TYPE
        SYNTAX        Counter64
        MAX-ACCESS    read-only
        STATUS        current
        DESCRIPTION  "Number of Silver Service Rx Mcast Frames dropped from
		      This Endpoint."
        ::= { rcTlsEndptStatsEntry 103 }

rcTlsEndptStndRxMcastDroppedFrames	OBJECT-TYPE
        SYNTAX        Counter64
        MAX-ACCESS    read-only
        STATUS        current
        DESCRIPTION  "Number of Standard Service Rx Mcast Frames dropped from
		      This Endpoint."
        ::= { rcTlsEndptStatsEntry 104 }

rcTlsEndptPremRxCirOctets     OBJECT-TYPE
        SYNTAX        Counter64
        MAX-ACCESS    read-only
        STATUS        current
        DESCRIPTION  "Number of Premium Service Rx CIR Octets received."
        ::= { rcTlsEndptStatsEntry 105 }

rcTlsEndptPremRxCirOopOctets     OBJECT-TYPE
        SYNTAX        Counter64
        MAX-ACCESS    read-only
        STATUS        current
        DESCRIPTION  "Number of Premium Service Rx Octets received that 
		      were CIR OOP."
        ::= { rcTlsEndptStatsEntry 106 }

rcTlsEndptPremRxEirOctets     OBJECT-TYPE
        SYNTAX        Counter64
        MAX-ACCESS    read-only
        STATUS        current
        DESCRIPTION  "Number of Premium Service Rx EIR Octets received."
        ::= { rcTlsEndptStatsEntry 107 }

rcTlsEndptPremRxEirOopOctets     OBJECT-TYPE
        SYNTAX        Counter64
        MAX-ACCESS    read-only
        STATUS        current
        DESCRIPTION  "Number of Premium Service Rx Octets received that 
		      were EIR OOP."
        ::= { rcTlsEndptStatsEntry 108 }

rcTlsEndptPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcTlsEndptStatsEntry 109 }

rcTlsEndptPremRxPirOctets     OBJECT-TYPE
        SYNTAX        Counter64
        MAX-ACCESS    read-only
        STATUS        current
        DESCRIPTION  "Number of Premium Service Rx PIR Octets received."
        ::= { rcTlsEndptStatsEntry 110 }

rcTlsEndptPremRxPirOopOctets     OBJECT-TYPE
        SYNTAX        Counter64
        MAX-ACCESS    read-only
        STATUS        current
        DESCRIPTION  "Number of Premium Service Rx Octets received that 
		      were PIR OOP."
        ::= { rcTlsEndptStatsEntry 111 }

rcTlsEndptPremRxGreenOctets     OBJECT-TYPE
        SYNTAX        Counter64
        MAX-ACCESS    read-only
        STATUS        current
        DESCRIPTION  "Number of Premium Service Rx Octets received that 
		      were marked 'Green' by the policer."
        ::= { rcTlsEndptStatsEntry 112 }

rcTlsEndptPremRxYellowOctets     OBJECT-TYPE
        SYNTAX        Counter64
        MAX-ACCESS    read-only
        STATUS        current
        DESCRIPTION  "Number of Premium Service Rx Octets received that 
		      were marked 'Yellow' by the policer."
        ::= { rcTlsEndptStatsEntry 113 }

rcTlsEndptPremRxRedOctets     OBJECT-TYPE
        SYNTAX        Counter64
        MAX-ACCESS    read-only
        STATUS        current
        DESCRIPTION  "Number of Premium Service Rx Octets received that 
		      were marked 'Red' by the policer."
        ::= { rcTlsEndptStatsEntry 114 }

rcTlsEndptGoldRxCirOctets     OBJECT-TYPE
        SYNTAX        Counter64
        MAX-ACCESS    read-only
        STATUS        current
        DESCRIPTION  "Number of Gold Service Rx CIR Octets received."
        ::= { rcTlsEndptStatsEntry 115 }

rcTlsEndptGoldRxCirOopOctets     OBJECT-TYPE
        SYNTAX        Counter64
        MAX-ACCESS    read-only
        STATUS        current
        DESCRIPTION  "Number of Gold Service Rx Octets received that 
		      were CIR OOP."
        ::= { rcTlsEndptStatsEntry 116 }

rcTlsEndptGoldRxEirOctets     OBJECT-TYPE
        SYNTAX        Counter64
        MAX-ACCESS    read-only
        STATUS        current
        DESCRIPTION  "Number of Gold Service Rx EIR Octets received."
        ::= { rcTlsEndptStatsEntry 117 }

rcTlsEndptGoldRxEirOopOctets     OBJECT-TYPE
        SYNTAX        Counter64
        MAX-ACCESS    read-only
        STATUS        current
        DESCRIPTION  "Number of Gold Service Rx Octets received that 
		      were EIR OOP."
        ::= { rcTlsEndptStatsEntry 118 }

rcTlsEndptGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcTlsEndptStatsEntry 119 }

rcTlsEndptGoldRxPirOctets     OBJECT-TYPE
        SYNTAX        Counter64
        MAX-ACCESS    read-only
        STATUS        current
        DESCRIPTION  "Number of Gold Service Rx PIR Octets received."
        ::= { rcTlsEndptStatsEntry 120 }

rcTlsEndptGoldRxPirOopOctets     OBJECT-TYPE
        SYNTAX        Counter64
        MAX-ACCESS    read-only
        STATUS        current
        DESCRIPTION  "Number of Gold Service Rx Octets received that 
		      were PIR OOP."
        ::= { rcTlsEndptStatsEntry 121 }

rcTlsEndptGoldRxGreenOctets     OBJECT-TYPE
        SYNTAX        Counter64
        MAX-ACCESS    read-only
        STATUS        current
        DESCRIPTION  "Number of Gold Service Rx Octets received that 
		      were marked 'Green' by the policer."
        ::= { rcTlsEndptStatsEntry 122 }

rcTlsEndptGoldRxYellowOctets     OBJECT-TYPE
        SYNTAX        Counter64
        MAX-ACCESS    read-only
        STATUS        current
        DESCRIPTION  "Number of Gold Service Rx Octets received that 
		      were marked 'Yellow' by the policer."
        ::= { rcTlsEndptStatsEntry 123 }

rcTlsEndptGoldRxRedOctets     OBJECT-TYPE
        SYNTAX        Counter64
        MAX-ACCESS    read-only
        STATUS        current
        DESCRIPTION  "Number of Gold Service Rx Octets received that 
		      were marked 'Red' by the policer."
        ::= { rcTlsEndptStatsEntry 124 }

rcTlsEndptSilverRxCirOctets     OBJECT-TYPE
        SYNTAX        Counter64
        MAX-ACCESS    read-only
        STATUS        current
        DESCRIPTION  "Number of Silver Service Rx CIR Octets received."
        ::= { rcTlsEndptStatsEntry 125 }

rcTlsEndptSilverRxCirOopOctets     OBJECT-TYPE
        SYNTAX        Counter64
        MAX-ACCESS    read-only
        STATUS        current
        DESCRIPTION  "Number of Silver Service Rx Octets received that 
		      were CIR OOP."
        ::= { rcTlsEndptStatsEntry 126 }

rcTlsEndptSilverRxEirOctets     OBJECT-TYPE
        SYNTAX        Counter64
        MAX-ACCESS    read-only
        STATUS        current
        DESCRIPTION  "Number of Silver Service Rx EIR Octets received."
        ::= { rcTlsEndptStatsEntry 127 }

rcTlsEndptSilverRxEirOopOctets     OBJECT-TYPE
        SYNTAX        Counter64
        MAX-ACCESS    read-only
        STATUS        current
        DESCRIPTION  "Number of Silver Service Rx Octets received that 
		      were EIR OOP."
        ::= { rcTlsEndptStatsEntry 128 }

rcTlsEndptSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcTlsEndptStatsEntry 129 }

rcTlsEndptSilverRxPirOctets     OBJECT-TYPE
        SYNTAX        Counter64
        MAX-ACCESS    read-only
        STATUS        current
        DESCRIPTION  "Number of Silver Service Rx PIR Octets received."
        ::= { rcTlsEndptStatsEntry 130 }

rcTlsEndptSilverRxPirOopOctets     OBJECT-TYPE
        SYNTAX        Counter64
        MAX-ACCESS    read-only
        STATUS        current
        DESCRIPTION  "Number of Silver Service Rx Octets received that 
		      were PIR OOP."
        ::= { rcTlsEndptStatsEntry 131 }

rcTlsEndptSilverRxGreenOctets     OBJECT-TYPE
        SYNTAX        Counter64
        MAX-ACCESS    read-only
        STATUS        current
        DESCRIPTION  "Number of Silver Service Rx Octets received that 
		      were marked 'Green' by the policer."
        ::= { rcTlsEndptStatsEntry 132 }

rcTlsEndptSilverRxYellowOctets     OBJECT-TYPE
        SYNTAX        Counter64
        MAX-ACCESS    read-only
        STATUS        current
        DESCRIPTION  "Number of Silver Service Rx Octets received that 
		      were marked 'Yellow' by the policer."
        ::= { rcTlsEndptStatsEntry 133 }

rcTlsEndptSilverRxRedOctets     OBJECT-TYPE
        SYNTAX        Counter64
        MAX-ACCESS    read-only
        STATUS        current
        DESCRIPTION  "Number of Silver Service Rx Octets received that 
		      were marked 'Red' by the policer."
        ::= { rcTlsEndptStatsEntry 134 }

rcTlsEndptStndRxCirOctets     OBJECT-TYPE
        SYNTAX        Counter64
        MAX-ACCESS    read-only
        STATUS        current
        DESCRIPTION  "Number of Standard Service Rx CIR Octets received."
        ::= { rcTlsEndptStatsEntry 135 }

rcTlsEndptStndRxCirOopOctets     OBJECT-TYPE
        SYNTAX        Counter64
        MAX-ACCESS    read-only
        STATUS        current
        DESCRIPTION  "Number of Standard Service Rx Octets received that 
		      were CIR OOP."
        ::= { rcTlsEndptStatsEntry 136 }

rcTlsEndptStndRxEirOctets     OBJECT-TYPE
        SYNTAX        Counter64
        MAX-ACCESS    read-only
        STATUS        current
        DESCRIPTION  "Number of Standard Service Rx EIR Octets received."
        ::= { rcTlsEndptStatsEntry 137 }

rcTlsEndptStndRxEirOopOctets     OBJECT-TYPE
        SYNTAX        Counter64
        MAX-ACCESS    read-only
        STATUS        current
        DESCRIPTION  "Number of Standard Service Rx Octets received that 
		      were EIR OOP."
        ::= { rcTlsEndptStatsEntry 138 }

rcTlsEndptStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcTlsEndptStatsEntry 139 }

rcTlsEndptStndRxPirOctets     OBJECT-TYPE
        SYNTAX        Counter64
        MAX-ACCESS    read-only
        STATUS        current
        DESCRIPTION  "Number of Standard Service Rx PIR Octets received."
        ::= { rcTlsEndptStatsEntry 140 }

rcTlsEndptStndRxPirOopOctets     OBJECT-TYPE
        SYNTAX        Counter64
        MAX-ACCESS    read-only
        STATUS        current
        DESCRIPTION  "Number of Standard Service Rx Octets received that 
		      were PIR OOP."
        ::= { rcTlsEndptStatsEntry 141 }

rcTlsEndptStndRxGreenOctets     OBJECT-TYPE
        SYNTAX        Counter64
        MAX-ACCESS    read-only
        STATUS        current
        DESCRIPTION  "Number of Standard Service Rx Octets received that 
		      were marked 'Green' by the policer."
        ::= { rcTlsEndptStatsEntry 142 }

rcTlsEndptStndRxYellowOctets     OBJECT-TYPE
        SYNTAX        Counter64
        MAX-ACCESS    read-only
        STATUS        current
        DESCRIPTION  "Number of Standard Service Rx Octets received that 
		      were marked 'Yellow' by the policer."
        ::= { rcTlsEndptStatsEntry 143 }

rcTlsEndptStndRxRedOctets     OBJECT-TYPE
        SYNTAX        Counter64
        MAX-ACCESS    read-only
        STATUS        current
        DESCRIPTION  "Number of Standard Service Rx Octets received that 
		      were marked 'Red' by the policer."
        ::= { rcTlsEndptStatsEntry 144 }

rcTlsEndptMcastRxDroppedOctets     OBJECT-TYPE
        SYNTAX        Counter64
        MAX-ACCESS    read-only
        STATUS        current
        DESCRIPTION  "Number of Multicast Rx Octets dropped."
        ::= { rcTlsEndptStatsEntry 145 }

rcTlsEndptBcastUUcastRxTotalOctets     OBJECT-TYPE
        SYNTAX        Counter64
        MAX-ACCESS    read-only
        STATUS        current
        DESCRIPTION  "Number of Broadcast/Unknown Unicast Rx total Octets."
        ::= { rcTlsEndptStatsEntry 146 }

rcTlsEndptBcastUUcastRxDroppedOctets     OBJECT-TYPE
        SYNTAX        Counter64
        MAX-ACCESS    read-only
        STATUS        current
        DESCRIPTION  "Number of Broadcast/Unknown Rx Octets dropped."
        ::= { rcTlsEndptStatsEntry 147 }

rcTlsEndptPremRxCirFrames     OBJECT-TYPE
        SYNTAX        Counter64
        MAX-ACCESS    read-only
        STATUS        current
        DESCRIPTION  "Number of Premium Service Rx CIR Frames received."
        ::= { rcTlsEndptStatsEntry 148 }

rcTlsEndptPremRxCirOopFrames     OBJECT-TYPE
        SYNTAX        Counter64
        MAX-ACCESS    read-only
        STATUS        current
        DESCRIPTION  "Number of Premium Service Rx Frames received that 
		      were CIR OOP."
        ::= { rcTlsEndptStatsEntry 149 }

rcTlsEndptPremRxEirFrames     OBJECT-TYPE
        SYNTAX        Counter64
        MAX-ACCESS    read-only
        STATUS        current
        DESCRIPTION  "Number of Premium Service Rx EIR Frames received."
        ::= { rcTlsEndptStatsEntry 150 }

rcTlsEndptPremRxEirOopFrames     OBJECT-TYPE
        SYNTAX        Counter64
        MAX-ACCESS    read-only
        STATUS        current
        DESCRIPTION  "Number of Premium Service Rx Frames received that 
		      were EIR OOP."
        ::= { rcTlsEndptStatsEntry 151 }

rcTlsEndptPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcTlsEndptStatsEntry 152 }

rcTlsEndptPremRxPirFrames     OBJECT-TYPE
        SYNTAX        Counter64
        MAX-ACCESS    read-only
        STATUS        current
        DESCRIPTION  "Number of Premium Service Rx PIR Frames received."
        ::= { rcTlsEndptStatsEntry 153 }

rcTlsEndptPremRxPirOopFrames     OBJECT-TYPE
        SYNTAX        Counter64
        MAX-ACCESS    read-only
        STATUS        current
        DESCRIPTION  "Number of Premium Service Rx Frames received that 
		      were PIR OOP."
        ::= { rcTlsEndptStatsEntry 154 }

rcTlsEndptPremRxGreenFrames     OBJECT-TYPE
        SYNTAX        Counter64
        MAX-ACCESS    read-only
        STATUS        current
        DESCRIPTION  "Number of Premium Service Rx Frames received that 
		      were marked 'Green' by the policer."
        ::= { rcTlsEndptStatsEntry 155 }

rcTlsEndptPremRxYellowFrames     OBJECT-TYPE
        SYNTAX        Counter64
        MAX-ACCESS    read-only
        STATUS        current
        DESCRIPTION  "Number of Premium Service Rx Frames received that 
		      were marked 'Yellow' by the policer."
        ::= { rcTlsEndptStatsEntry 156 }

rcTlsEndptPremRxRedFrames     OBJECT-TYPE
        SYNTAX        Counter64
        MAX-ACCESS    read-only
        STATUS        current
        DESCRIPTION  "Number of Premium Service Rx Frames received that 
		      were marked 'Red' by the policer."
        ::= { rcTlsEndptStatsEntry 157 }

rcTlsEndptGoldRxCirFrames     OBJECT-TYPE
        SYNTAX        Counter64
        MAX-ACCESS    read-only
        STATUS        current
        DESCRIPTION  "Number of Gold Service Rx CIR Frames received."
        ::= { rcTlsEndptStatsEntry 158 }

rcTlsEndptGoldRxCirOopFrames     OBJECT-TYPE
        SYNTAX        Counter64
        MAX-ACCESS    read-only
        STATUS        current
        DESCRIPTION  "Number of Gold Service Rx Frames received that 
		      were CIR OOP."
        ::= { rcTlsEndptStatsEntry 159 }

rcTlsEndptGoldRxEirFrames     OBJECT-TYPE
        SYNTAX        Counter64
        MAX-ACCESS    read-only
        STATUS        current
        DESCRIPTION  "Number of Gold Service Rx EIR Frames received."
        ::= { rcTlsEndptStatsEntry 160 }

rcTlsEndptGoldRxEirOopFrames     OBJECT-TYPE
        SYNTAX        Counter64
        MAX-ACCESS    read-only
        STATUS        current
        DESCRIPTION  "Number of Gold Service Rx Frames received that 
		      were EIR OOP."
        ::= { rcTlsEndptStatsEntry 161 }

rcTlsEndptGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcTlsEndptStatsEntry 162 }

rcTlsEndptGoldRxPirFrames     OBJECT-TYPE
        SYNTAX        Counter64
        MAX-ACCESS    read-only
        STATUS        current
        DESCRIPTION  "Number of Gold Service Rx PIR Frames received."
        ::= { rcTlsEndptStatsEntry 163 }

rcTlsEndptGoldRxPirOopFrames     OBJECT-TYPE
        SYNTAX        Counter64
        MAX-ACCESS    read-only
        STATUS        current
        DESCRIPTION  "Number of Gold Service Rx Frames received that 
		      were PIR OOP."
        ::= { rcTlsEndptStatsEntry 164 }

rcTlsEndptGoldRxGreenFrames     OBJECT-TYPE
        SYNTAX        Counter64
        MAX-ACCESS    read-only
        STATUS        current
        DESCRIPTION  "Number of Gold Service Rx Frames received that 
		      were marked 'Green' by the policer."
        ::= { rcTlsEndptStatsEntry 165 }

rcTlsEndptGoldRxYellowFrames     OBJECT-TYPE
        SYNTAX        Counter64
        MAX-ACCESS    read-only
        STATUS        current
        DESCRIPTION  "Number of Gold Service Rx Frames received that 
		      were marked 'Yellow' by the policer."
        ::= { rcTlsEndptStatsEntry 166 }

rcTlsEndptGoldRxRedFrames     OBJECT-TYPE
        SYNTAX        Counter64
        MAX-ACCESS    read-only
        STATUS        current
        DESCRIPTION  "Number of Gold Service Rx Frames received that 
		      were marked 'Red' by the policer."
        ::= { rcTlsEndptStatsEntry 167 }

rcTlsEndptSilverRxCirFrames     OBJECT-TYPE
        SYNTAX        Counter64
        MAX-ACCESS    read-only
        STATUS        current
        DESCRIPTION  "Number of Silver Service Rx CIR Frames received."
        ::= { rcTlsEndptStatsEntry 168 }

rcTlsEndptSilverRxCirOopFrames     OBJECT-TYPE
        SYNTAX        Counter64
        MAX-ACCESS    read-only
        STATUS        current
        DESCRIPTION  "Number of Silver Service Rx Frames received that 
		      were CIR OOP."
        ::= { rcTlsEndptStatsEntry 169 }

rcTlsEndptSilverRxEirFrames     OBJECT-TYPE
        SYNTAX        Counter64
        MAX-ACCESS    read-only
        STATUS        current
        DESCRIPTION  "Number of Silver Service Rx EIR Frames received."
        ::= { rcTlsEndptStatsEntry 170 }

rcTlsEndptSilverRxEirOopFrames     OBJECT-TYPE
        SYNTAX        Counter64
        MAX-ACCESS    read-only
        STATUS        current
        DESCRIPTION  "Number of Silver Service Rx Frames received that 
		      were EIR OOP."
        ::= { rcTlsEndptStatsEntry 171 }

rcTlsEndptSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcTlsEndptStatsEntry 172 }

rcTlsEndptSilverRxPirFrames     OBJECT-TYPE
        SYNTAX        Counter64
        MAX-ACCESS    read-only
        STATUS        current
        DESCRIPTION  "Number of Silver Service Rx PIR Frames received."
        ::= { rcTlsEndptStatsEntry 173 }

rcTlsEndptSilverRxPirOopFrames     OBJECT-TYPE
        SYNTAX        Counter64
        MAX-ACCESS    read-only
        STATUS        current
        DESCRIPTION  "Number of Silver Service Rx Frames received that 
		      were PIR OOP."
        ::= { rcTlsEndptStatsEntry 174 }

rcTlsEndptSilverRxGreenFrames     OBJECT-TYPE
        SYNTAX        Counter64
        MAX-ACCESS    read-only
        STATUS        current
        DESCRIPTION  "Number of Silver Service Rx Frames received that 
		      were marked 'Green' by the policer."
        ::= { rcTlsEndptStatsEntry 175 }

rcTlsEndptSilverRxYellowFrames     OBJECT-TYPE
        SYNTAX        Counter64
        MAX-ACCESS    read-only
        STATUS        current
        DESCRIPTION  "Number of Silver Service Rx Frames received that 
		      were marked 'Yellow' by the policer."
        ::= { rcTlsEndptStatsEntry 176 }

rcTlsEndptSilverRxRedFrames     OBJECT-TYPE
        SYNTAX        Counter64
        MAX-ACCESS    read-only
        STATUS        current
        DESCRIPTION  "Number of Silver Service Rx Frames received that 
		      were marked 'Red' by the policer."
        ::= { rcTlsEndptStatsEntry 177 }

rcTlsEndptStndRxCirFrames     OBJECT-TYPE
        SYNTAX        Counter64
        MAX-ACCESS    read-only
        STATUS        current
        DESCRIPTION  "Number of Standard Service Rx CIR Frames received."
        ::= { rcTlsEndptStatsEntry 178 }

rcTlsEndptStndRxCirOopFrames     OBJECT-TYPE
        SYNTAX        Counter64
        MAX-ACCESS    read-only
        STATUS        current
        DESCRIPTION  "Number of Standard Service Rx Frames received that 
		      were CIR OOP."
        ::= { rcTlsEndptStatsEntry 179 }

rcTlsEndptStndRxEirFrames     OBJECT-TYPE
        SYNTAX        Counter64
        MAX-ACCESS    read-only
        STATUS        current
        DESCRIPTION  "Number of Standard Service Rx EIR Frames received."
        ::= { rcTlsEndptStatsEntry 180 }

rcTlsEndptStndRxEirOopFrames     OBJECT-TYPE
        SYNTAX        Counter64
        MAX-ACCESS    read-only
        STATUS        current
        DESCRIPTION  "Number of Standard Service Rx Frames received that 
		      were EIR OOP."
        ::= { rcTlsEndptStatsEntry 181 }

rcTlsEndptStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcTlsEndptStatsEntry 182 }

rcTlsEndptStndRxPirFrames     OBJECT-TYPE
        SYNTAX        Counter64
        MAX-ACCESS    read-only
        STATUS        current
        DESCRIPTION  "Number of Standard Service Rx PIR Frames received."
        ::= { rcTlsEndptStatsEntry 183 }

rcTlsEndptStndRxPirOopFrames     OBJECT-TYPE
        SYNTAX        Counter64
        MAX-ACCESS    read-only
        STATUS        current
        DESCRIPTION  "Number of Standard Service Rx Frames received that 
		      were PIR OOP."
        ::= { rcTlsEndptStatsEntry 184 }

rcTlsEndptStndRxGreenFrames     OBJECT-TYPE
        SYNTAX        Counter64
        MAX-ACCESS    read-only
        STATUS        current
        DESCRIPTION  "Number of Standard Service Rx Frames received that 
		      were marked 'Green' by the policer."
        ::= { rcTlsEndptStatsEntry 185 }

rcTlsEndptStndRxYellowFrames     OBJECT-TYPE
        SYNTAX        Counter64
        MAX-ACCESS    read-only
        STATUS        current
        DESCRIPTION  "Number of Standard Service Rx Frames received that 
		      were marked 'Yellow' by the policer."
        ::= { rcTlsEndptStatsEntry 186 }

rcTlsEndptStndRxRedFrames     OBJECT-TYPE
        SYNTAX        Counter64
        MAX-ACCESS    read-only
        STATUS        current
        DESCRIPTION  "Number of Standard Service Rx Frames received that 
		      were marked 'Red' by the policer."
        ::= { rcTlsEndptStatsEntry 187 }

rcTlsEndptMcastRxDroppedFrames     OBJECT-TYPE
        SYNTAX        Counter64
        MAX-ACCESS    read-only
        STATUS        current
        DESCRIPTION  "Number of Multicast Rx Frames dropped."
        ::= { rcTlsEndptStatsEntry 188 }

rcTlsEndptBcastUUcastRxTotalFrames     OBJECT-TYPE
        SYNTAX        Counter64
        MAX-ACCESS    read-only
        STATUS        current
        DESCRIPTION  "Number of Broadcast/Unknown Unicast Rx total Frames."
        ::= { rcTlsEndptStatsEntry 189 }

rcTlsEndptBcastUUcastRxDroppedFrames     OBJECT-TYPE
        SYNTAX        Counter64
        MAX-ACCESS    read-only
        STATUS        current
        DESCRIPTION  "Number of Broadcast/Unknown Rx Frames dropped."
        ::= { rcTlsEndptStatsEntry 190 }

rcTlsEndptPremTxCirOctets     OBJECT-TYPE
        SYNTAX        Counter64
        MAX-ACCESS    read-only
        STATUS        current
        DESCRIPTION  "Number of Premium Service Tx CIR Octets received."
        ::= { rcTlsEndptStatsEntry 191 }

rcTlsEndptPremTxCirOopOctets     OBJECT-TYPE
        SYNTAX        Counter64
        MAX-ACCESS    read-only
        STATUS        current
        DESCRIPTION  "Number of Premium Service Tx Octets received that 
		      were CIR OOP."
        ::= { rcTlsEndptStatsEntry 192 }

rcTlsEndptPremTxEirOctets     OBJECT-TYPE
        SYNTAX        Counter64
        MAX-ACCESS    read-only
        STATUS        current
        DESCRIPTION  "Number of Premium Service Tx EIR Octets received."
        ::= { rcTlsEndptStatsEntry 193 }

rcTlsEndptPremTxEirOopOctets     OBJECT-TYPE
        SYNTAX        Counter64
        MAX-ACCESS    read-only
        STATUS        current
        DESCRIPTION  "Number of Premium Service Tx Octets received that 
		      were EIR OOP."
        ::= { rcTlsEndptStatsEntry 194 }

rcTlsEndptPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcTlsEndptStatsEntry 195 }

rcTlsEndptPremTxPirOctets     OBJECT-TYPE
        SYNTAX        Counter64
        MAX-ACCESS    read-only
        STATUS        current
        DESCRIPTION  "Number of Premium Service Tx PIR Octets received."
        ::= { rcTlsEndptStatsEntry 196 }

rcTlsEndptPremTxPirOopOctets     OBJECT-TYPE
        SYNTAX        Counter64
        MAX-ACCESS    read-only
        STATUS        current
        DESCRIPTION  "Number of Premium Service Tx Octets received that 
		      were PIR OOP."
        ::= { rcTlsEndptStatsEntry 197 }

rcTlsEndptPremTxGreenOctets     OBJECT-TYPE
        SYNTAX        Counter64
        MAX-ACCESS    read-only
        STATUS        current
        DESCRIPTION  "Number of Premium Service Tx Octets received that 
		      were marked 'Green' by the policer."
        ::= { rcTlsEndptStatsEntry 198 }

rcTlsEndptPremTxYellowOctets     OBJECT-TYPE
        SYNTAX        Counter64
        MAX-ACCESS    read-only
        STATUS        current
        DESCRIPTION  "Number of Premium Service Tx Octets received that 
		      were marked 'Yellow' by the policer."
        ::= { rcTlsEndptStatsEntry 199 }

rcTlsEndptPremTxRedOctets     OBJECT-TYPE
        SYNTAX        Counter64
        MAX-ACCESS    read-only
        STATUS        current
        DESCRIPTION  "Number of Premium Service Tx Octets received that 
		      were marked 'Red' by the policer."
        ::= { rcTlsEndptStatsEntry 200 }

rcTlsEndptGoldTxCirOctets     OBJECT-TYPE
        SYNTAX        Counter64
        MAX-ACCESS    read-only
        STATUS        current
        DESCRIPTION  "Number of Gold Service Tx CIR Octets received."
        ::= { rcTlsEndptStatsEntry 201 }

rcTlsEndptGoldTxCirOopOctets     OBJECT-TYPE
        SYNTAX        Counter64
        MAX-ACCESS    read-only
        STATUS        current
        DESCRIPTION  "Number of Gold Service Tx Octets received that 
		      were CIR OOP."
        ::= { rcTlsEndptStatsEntry 202 }

rcTlsEndptGoldTxEirOctets     OBJECT-TYPE
        SYNTAX        Counter64
        MAX-ACCESS    read-only
        STATUS        current
        DESCRIPTION  "Number of Gold Service Tx EIR Octets received."
        ::= { rcTlsEndptStatsEntry 203 }

rcTlsEndptGoldTxEirOopOctets     OBJECT-TYPE
        SYNTAX        Counter64
        MAX-ACCESS    read-only
        STATUS        current
        DESCRIPTION  "Number of Gold Service Tx Octets received that 
		      were EIR OOP."
        ::= { rcTlsEndptStatsEntry 204 }

rcTlsEndptGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcTlsEndptStatsEntry 205 }

rcTlsEndptGoldTxPirOctets     OBJECT-TYPE
        SYNTAX        Counter64
        MAX-ACCESS    read-only
        STATUS        current
        DESCRIPTION  "Number of Gold Service Tx PIR Octets received."
        ::= { rcTlsEndptStatsEntry 206 }

rcTlsEndptGoldTxPirOopOctets     OBJECT-TYPE
        SYNTAX        Counter64
        MAX-ACCESS    read-only
        STATUS        current
        DESCRIPTION  "Number of Gold Service Tx Octets received that 
		      were PIR OOP."
        ::= { rcTlsEndptStatsEntry 207 }

rcTlsEndptGoldTxGreenOctets     OBJECT-TYPE
        SYNTAX        Counter64
        MAX-ACCESS    read-only
        STATUS        current
        DESCRIPTION  "Number of Gold Service Tx Octets received that 
		      were marked 'Green' by the policer."
        ::= { rcTlsEndptStatsEntry 208 }

rcTlsEndptGoldTxYellowOctets     OBJECT-TYPE
        SYNTAX        Counter64
        MAX-ACCESS    read-only
        STATUS        current
        DESCRIPTION  "Number of Gold Service Tx Octets received that 
		      were marked 'Yellow' by the policer."
        ::= { rcTlsEndptStatsEntry 209 }

rcTlsEndptGoldTxRedOctets     OBJECT-TYPE
        SYNTAX        Counter64
        MAX-ACCESS    read-only
        STATUS        current
        DESCRIPTION  "Number of Gold Service Tx Octets received that 
		      were marked 'Red' by the policer."
        ::= { rcTlsEndptStatsEntry 210 }

rcTlsEndptSilverTxCirOctets     OBJECT-TYPE
        SYNTAX        Counter64
        MAX-ACCESS    read-only
        STATUS        current
        DESCRIPTION  "Number of Silver Service Tx CIR Octets received."
        ::= { rcTlsEndptStatsEntry 211 }

rcTlsEndptSilverTxCirOopOctets     OBJECT-TYPE
        SYNTAX        Counter64
        MAX-ACCESS    read-only
        STATUS        current
        DESCRIPTION  "Number of Silver Service Tx Octets received that 
		      were CIR OOP."
        ::= { rcTlsEndptStatsEntry 212 }

rcTlsEndptSilverTxEirOctets     OBJECT-TYPE
        SYNTAX        Counter64
        MAX-ACCESS    read-only
        STATUS        current
        DESCRIPTION  "Number of Silver Service Tx EIR Octets received."
        ::= { rcTlsEndptStatsEntry 213 }

rcTlsEndptSilverTxEirOopOctets     OBJECT-TYPE
        SYNTAX        Counter64
        MAX-ACCESS    read-only
        STATUS        current
        DESCRIPTION  "Number of Silver Service Tx Octets received that 
		      were EIR OOP."
        ::= { rcTlsEndptStatsEntry 214 }

rcTlsEndptSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcTlsEndptStatsEntry 215 }

rcTlsEndptSilverTxPirOctets     OBJECT-TYPE
        SYNTAX        Counter64
        MAX-ACCESS    read-only
        STATUS        current
        DESCRIPTION  "Number of Silver Service Tx PIR Octets received."
        ::= { rcTlsEndptStatsEntry 216 }

rcTlsEndptSilverTxPirOopOctets     OBJECT-TYPE
        SYNTAX        Counter64
        MAX-ACCESS    read-only
        STATUS        current
        DESCRIPTION  "Number of Silver Service Tx Octets received that 
		      were PIR OOP."
        ::= { rcTlsEndptStatsEntry 217 }

rcTlsEndptSilverTxGreenOctets     OBJECT-TYPE
        SYNTAX        Counter64
        MAX-ACCESS    read-only
        STATUS        current
        DESCRIPTION  "Number of Silver Service Tx Octets received that 
		      were marked 'Green' by the policer."
        ::= { rcTlsEndptStatsEntry 218 }

rcTlsEndptSilverTxYellowOctets     OBJECT-TYPE
        SYNTAX        Counter64
        MAX-ACCESS    read-only
        STATUS        current
        DESCRIPTION  "Number of Silver Service Tx Octets received that 
		      were marked 'Yellow' by the policer."
        ::= { rcTlsEndptStatsEntry 219 }

rcTlsEndptSilverTxRedOctets     OBJECT-TYPE
        SYNTAX        Counter64
        MAX-ACCESS    read-only
        STATUS        current
        DESCRIPTION  "Number of Silver Service Tx Octets received that 
		      were marked 'Red' by the policer."
        ::= { rcTlsEndptStatsEntry 220 }

rcTlsEndptStndTxCirOctets     OBJECT-TYPE
        SYNTAX        Counter64
        MAX-ACCESS    read-only
        STATUS        current
        DESCRIPTION  "Number of Standard Service Tx CIR Octets received."
        ::= { rcTlsEndptStatsEntry 221 }

rcTlsEndptStndTxCirOopOctets     OBJECT-TYPE
        SYNTAX        Counter64
        MAX-ACCESS    read-only
        STATUS        current
        DESCRIPTION  "Number of Standard Service Tx Octets received that 
		      were CIR OOP."
        ::= { rcTlsEndptStatsEntry 222 }

rcTlsEndptStndTxEirOctets     OBJECT-TYPE
        SYNTAX        Counter64
        MAX-ACCESS    read-only
        STATUS        current
        DESCRIPTION  "Number of Standard Service Tx EIR Octets received."
        ::= { rcTlsEndptStatsEntry 223 }

rcTlsEndptStndTxEirOopOctets     OBJECT-TYPE
        SYNTAX        Counter64
        MAX-ACCESS    read-only
        STATUS        current
        DESCRIPTION  "Number of Standard Service Tx Octets received that 
		      were EIR OOP."
        ::= { rcTlsEndptStatsEntry 224 }

rcTlsEndptStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcTlsEndptStatsEntry 225 }

rcTlsEndptStndTxPirOctets     OBJECT-TYPE
        SYNTAX        Counter64
        MAX-ACCESS    read-only
        STATUS        current
        DESCRIPTION  "Number of Standard Service Tx PIR Octets received."
        ::= { rcTlsEndptStatsEntry 226 }

rcTlsEndptStndTxPirOopOctets     OBJECT-TYPE
        SYNTAX        Counter64
        MAX-ACCESS    read-only
        STATUS        current
        DESCRIPTION  "Number of Standard Service Tx Octets received that 
		      were PIR OOP."
        ::= { rcTlsEndptStatsEntry 227 }

rcTlsEndptStndTxGreenOctets     OBJECT-TYPE
        SYNTAX        Counter64
        MAX-ACCESS    read-only
        STATUS        current
        DESCRIPTION  "Number of Standard Service Tx Octets received that 
		      were marked 'Green' by the policer."
        ::= { rcTlsEndptStatsEntry 228 }

rcTlsEndptStndTxYellowOctets     OBJECT-TYPE
        SYNTAX        Counter64
        MAX-ACCESS    read-only
        STATUS        current
        DESCRIPTION  "Number of Standard Service Tx Octets received that 
		      were marked 'Yellow' by the policer."
        ::= { rcTlsEndptStatsEntry 229 }

rcTlsEndptStndTxRedOctets     OBJECT-TYPE
        SYNTAX        Counter64
        MAX-ACCESS    read-only
        STATUS        current
        DESCRIPTION  "Number of Standard Service Tx Octets received that 
		      were marked 'Red' by the policer."
        ::= { rcTlsEndptStatsEntry 230 }

rcTlsEndptMcastTxDroppedOctets     OBJECT-TYPE
        SYNTAX        Counter64
        MAX-ACCESS    read-only
        STATUS        current
        DESCRIPTION  "Number of Multicast Tx Octets dropped."
        ::= { rcTlsEndptStatsEntry 231 }

rcTlsEndptBcastUUcastTxTotalOctets     OBJECT-TYPE
        SYNTAX        Counter64
        MAX-ACCESS    read-only
        STATUS        current
        DESCRIPTION  "Number of Broadcast/Unknown Unicast Tx total Octets."
        ::= { rcTlsEndptStatsEntry 232 }

rcTlsEndptBcastUUcastTxDroppedOctets     OBJECT-TYPE
        SYNTAX        Counter64
        MAX-ACCESS    read-only
        STATUS        current
        DESCRIPTION  "Number of Broadcast/Unknown Tx Octets dropped."
        ::= { rcTlsEndptStatsEntry 233 }

rcTlsEndptPremTxCirFrames     OBJECT-TYPE
        SYNTAX        Counter64
        MAX-ACCESS    read-only
        STATUS        current
        DESCRIPTION  "Number of Premium Service Tx CIR Frames received."
        ::= { rcTlsEndptStatsEntry 234 }

rcTlsEndptPremTxCirOopFrames     OBJECT-TYPE
        SYNTAX        Counter64
        MAX-ACCESS    read-only
        STATUS        current
        DESCRIPTION  "Number of Premium Service Tx Frames received that 
		      were CIR OOP."
        ::= { rcTlsEndptStatsEntry 235 }

rcTlsEndptPremTxEirFrames     OBJECT-TYPE
        SYNTAX        Counter64
        MAX-ACCESS    read-only
        STATUS        current
        DESCRIPTION  "Number of Premium Service Tx EIR Frames received."
        ::= { rcTlsEndptStatsEntry 236 }

rcTlsEndptPremTxEirOopFrames     OBJECT-TYPE
        SYNTAX        Counter64
        MAX-ACCESS    read-only
        STATUS        current
        DESCRIPTION  "Number of Premium Service Tx Frames received that 
		      were EIR OOP."
        ::= { rcTlsEndptStatsEntry 237 }

rcTlsEndptPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcTlsEndptStatsEntry 238 }

rcTlsEndptPremTxPirFrames     OBJECT-TYPE
        SYNTAX        Counter64
        MAX-ACCESS    read-only
        STATUS        current
        DESCRIPTION  "Number of Premium Service Tx PIR Frames received."
        ::= { rcTlsEndptStatsEntry 239 }

rcTlsEndptPremTxPirOopFrames     OBJECT-TYPE
        SYNTAX        Counter64
        MAX-ACCESS    read-only
        STATUS        current
        DESCRIPTION  "Number of Premium Service Tx Frames received that 
		      were PIR OOP."
        ::= { rcTlsEndptStatsEntry 240 }

rcTlsEndptPremTxGreenFrames     OBJECT-TYPE
        SYNTAX        Counter64
        MAX-ACCESS    read-only
        STATUS        current
        DESCRIPTION  "Number of Premium Service Tx Frames received that 
		      were marked 'Green' by the policer."
        ::= { rcTlsEndptStatsEntry 241 }

rcTlsEndptPremTxYellowFrames     OBJECT-TYPE
        SYNTAX        Counter64
        MAX-ACCESS    read-only
        STATUS        current
        DESCRIPTION  "Number of Premium Service Tx Frames received that 
		      were marked 'Yellow' by the policer."
        ::= { rcTlsEndptStatsEntry 242 }

rcTlsEndptPremTxRedFrames     OBJECT-TYPE
        SYNTAX        Counter64
        MAX-ACCESS    read-only
        STATUS        current
        DESCRIPTION  "Number of Premium Service Tx Frames received that 
		      were marked 'Red' by the policer."
        ::= { rcTlsEndptStatsEntry 243 }

rcTlsEndptGoldTxCirFrames     OBJECT-TYPE
        SYNTAX        Counter64
        MAX-ACCESS    read-only
        STATUS        current
        DESCRIPTION  "Number of Gold Service Tx CIR Frames received."
        ::= { rcTlsEndptStatsEntry 244 }

rcTlsEndptGoldTxCirOopFrames     OBJECT-TYPE
        SYNTAX        Counter64
        MAX-ACCESS    read-only
        STATUS        current
        DESCRIPTION  "Number of Gold Service Tx Frames received that 
		      were CIR OOP."
        ::= { rcTlsEndptStatsEntry 245 }

rcTlsEndptGoldTxEirFrames     OBJECT-TYPE
        SYNTAX        Counter64
        MAX-ACCESS    read-only
        STATUS        current
        DESCRIPTION  "Number of Gold Service Tx EIR Frames received."
        ::= { rcTlsEndptStatsEntry 246 }

rcTlsEndptGoldTxEirOopFrames     OBJECT-TYPE
        SYNTAX        Counter64
        MAX-ACCESS    read-only
        STATUS        current
        DESCRIPTION  "Number of Gold Service Tx Frames received that 
		      were EIR OOP."
        ::= { rcTlsEndptStatsEntry 247 }

rcTlsEndptGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcTlsEndptStatsEntry 248 }

rcTlsEndptGoldTxPirFrames     OBJECT-TYPE
        SYNTAX        Counter64
        MAX-ACCESS    read-only
        STATUS        current
        DESCRIPTION  "Number of Gold Service Tx PIR Frames received."
        ::= { rcTlsEndptStatsEntry 249 }

rcTlsEndptGoldTxPirOopFrames     OBJECT-TYPE
        SYNTAX        Counter64
        MAX-ACCESS    read-only
        STATUS        current
        DESCRIPTION  "Number of Gold Service Tx Frames received that 
		      were PIR OOP."
        ::= { rcTlsEndptStatsEntry 250 }

rcTlsEndptGoldTxGreenFrames     OBJECT-TYPE
        SYNTAX        Counter64
        MAX-ACCESS    read-only
        STATUS        current
        DESCRIPTION  "Number of Gold Service Tx Frames received that 
		      were marked 'Green' by the policer."
        ::= { rcTlsEndptStatsEntry 251 }

rcTlsEndptGoldTxYellowFrames     OBJECT-TYPE
        SYNTAX        Counter64
        MAX-ACCESS    read-only
        STATUS        current
        DESCRIPTION  "Number of Gold Service Tx Frames received that 
		      were marked 'Yellow' by the policer."
        ::= { rcTlsEndptStatsEntry 252 }

rcTlsEndptGoldTxRedFrames     OBJECT-TYPE
        SYNTAX        Counter64
        MAX-ACCESS    read-only
        STATUS        current
        DESCRIPTION  "Number of Gold Service Tx Frames received that 
		      were marked 'Red' by the policer."
        ::= { rcTlsEndptStatsEntry 253 }

rcTlsEndptSilverTxCirFrames     OBJECT-TYPE
        SYNTAX        Counter64
        MAX-ACCESS    read-only
        STATUS        current
        DESCRIPTION  "Number of Silver Service Tx CIR Frames received."
        ::= { rcTlsEndptStatsEntry 254 }

rcTlsEndptSilverTxCirOopFrames     OBJECT-TYPE
        SYNTAX        Counter64
        MAX-ACCESS    read-only
        STATUS        current
        DESCRIPTION  "Number of Silver Service Tx Frames received that 
		      were CIR OOP."
        ::= { rcTlsEndptStatsEntry 255 }

rcTlsEndptSilverTxEirFrames     OBJECT-TYPE
        SYNTAX        Counter64
        MAX-ACCESS    read-only
        STATUS        current
        DESCRIPTION  "Number of Silver Service Tx EIR Frames received."
        ::= { rcTlsEndptStatsEntry 256 }

rcTlsEndptSilverTxEirOopFrames     OBJECT-TYPE
        SYNTAX        Counter64
        MAX-ACCESS    read-only
        STATUS        current
        DESCRIPTION  "Number of Silver Service Tx Frames received that 
		      were EIR OOP."
        ::= { rcTlsEndptStatsEntry 257 }

rcTlsEndptSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcTlsEndptStatsEntry 258 }

rcTlsEndptSilverTxPirFrames     OBJECT-TYPE
        SYNTAX        Counter64
        MAX-ACCESS    read-only
        STATUS        current
        DESCRIPTION  "Number of Silver Service Tx PIR Frames received."
        ::= { rcTlsEndptStatsEntry 259 }

rcTlsEndptSilverTxPirOopFrames     OBJECT-TYPE
        SYNTAX        Counter64
        MAX-ACCESS    read-only
        STATUS        current
        DESCRIPTION  "Number of Silver Service Tx Frames received that 
		      were PIR OOP."
        ::= { rcTlsEndptStatsEntry 260 }

rcTlsEndptSilverTxGreenFrames     OBJECT-TYPE
        SYNTAX        Counter64
        MAX-ACCESS    read-only
        STATUS        current
        DESCRIPTION  "Number of Silver Service Tx Frames received that 
		      were marked 'Green' by the policer."
        ::= { rcTlsEndptStatsEntry 261 }

rcTlsEndptSilverTxYellowFrames     OBJECT-TYPE
        SYNTAX        Counter64
        MAX-ACCESS    read-only
        STATUS        current
        DESCRIPTION  "Number of Silver Service Tx Frames received that 
		      were marked 'Yellow' by the policer."
        ::= { rcTlsEndptStatsEntry 262 }

rcTlsEndptSilverTxRedFrames     OBJECT-TYPE
        SYNTAX        Counter64
        MAX-ACCESS    read-only
        STATUS        current
        DESCRIPTION  "Number of Silver Service Tx Frames received that 
		      were marked 'Red' by the policer."
        ::= { rcTlsEndptStatsEntry 263 }

rcTlsEndptStndTxCirFrames     OBJECT-TYPE
        SYNTAX        Counter64
        MAX-ACCESS    read-only
        STATUS        current
        DESCRIPTION  "Number of Standard Service Tx CIR Frames received."
        ::= { rcTlsEndptStatsEntry 264 }

rcTlsEndptStndTxCirOopFrames     OBJECT-TYPE
        SYNTAX        Counter64
        MAX-ACCESS    read-only
        STATUS        current
        DESCRIPTION  "Number of Standard Service Tx Frames received that 
		      were CIR OOP."
        ::= { rcTlsEndptStatsEntry 265 }

rcTlsEndptStndTxEirFrames     OBJECT-TYPE
        SYNTAX        Counter64
        MAX-ACCESS    read-only
        STATUS        current
        DESCRIPTION  "Number of Standard Service Tx EIR Frames received."
        ::= { rcTlsEndptStatsEntry 266 }

rcTlsEndptStndTxEirOopFrames     OBJECT-TYPE
        SYNTAX        Counter64
        MAX-ACCESS    read-only
        STATUS        current
        DESCRIPTION  "Number of Standard Service Tx Frames received that 
		      were EIR OOP."
        ::= { rcTlsEndptStatsEntry 267 }

rcTlsEndptStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcTlsEndptStatsEntry 268 }

rcTlsEndptStndTxPirFrames     OBJECT-TYPE
        SYNTAX        Counter64
        MAX-ACCESS    read-only
        STATUS        current
        DESCRIPTION  "Number of Standard Service Tx PIR Frames received."
        ::= { rcTlsEndptStatsEntry 269 }

rcTlsEndptStndTxPirOopFrames     OBJECT-TYPE
        SYNTAX        Counter64
        MAX-ACCESS    read-only
        STATUS        current
        DESCRIPTION  "Number of Standard Service Tx Frames received that 
		      were PIR OOP."
        ::= { rcTlsEndptStatsEntry 270 }

rcTlsEndptStndTxGreenFrames     OBJECT-TYPE
        SYNTAX        Counter64
        MAX-ACCESS    read-only
        STATUS        current
        DESCRIPTION  "Number of Standard Service Tx Frames received that 
		      were marked 'Green' by the policer."
        ::= { rcTlsEndptStatsEntry 271 }

rcTlsEndptStndTxYellowFrames     OBJECT-TYPE
        SYNTAX        Counter64
        MAX-ACCESS    read-only
        STATUS        current
        DESCRIPTION  "Number of Standard Service Tx Frames received that 
		      were marked 'Yellow' by the policer."
        ::= { rcTlsEndptStatsEntry 272 }

rcTlsEndptStndTxRedFrames     OBJECT-TYPE
        SYNTAX        Counter64
        MAX-ACCESS    read-only
        STATUS        current
        DESCRIPTION  "Number of Standard Service Tx Frames received that 
		      were marked 'Red' by the policer."
        ::= { rcTlsEndptStatsEntry 273 }

rcTlsEndptMcastTxDroppedFrames     OBJECT-TYPE
        SYNTAX        Counter64
        MAX-ACCESS    read-only
        STATUS        current
        DESCRIPTION  "Number of Multicast Tx Frames dropped."
        ::= { rcTlsEndptStatsEntry 274 }

rcTlsEndptBcastUUcastTxTotalFrames     OBJECT-TYPE
        SYNTAX        Counter64
        MAX-ACCESS    read-only
        STATUS        current
        DESCRIPTION  "Number of Broadcast/Unknown Unicast Tx total Frames."
        ::= { rcTlsEndptStatsEntry 275 }

rcTlsEndptBcastUUcastTxDroppedFrames     OBJECT-TYPE
        SYNTAX        Counter64
        MAX-ACCESS    read-only
        STATUS        current
        DESCRIPTION  "Number of Broadcast/Unknown Tx Frames dropped."
        ::= { rcTlsEndptStatsEntry 276 }

rcTlsEndptDropClassRxDroppedOctets     OBJECT-TYPE
        SYNTAX        Counter64
        MAX-ACCESS    read-only
        STATUS        current
        DESCRIPTION  "Number of Drop Class Rx Octets dropped."
        ::= { rcTlsEndptStatsEntry 277 }

rcTlsEndptDropClassRxDroppedFrames     OBJECT-TYPE
        SYNTAX        Counter64
        MAX-ACCESS    read-only
        STATUS        current
        DESCRIPTION  "Number of Drop Class Rx Frames dropped."
        ::= { rcTlsEndptStatsEntry 278 }

rcTlsEndptDropClassTxDroppedOctets	OBJECT-TYPE
        SYNTAX        Counter64
        MAX-ACCESS    read-only
        STATUS        current
        DESCRIPTION  "Number of Drop Class Tx Octets dropped."
        ::= { rcTlsEndptStatsEntry 279 }

rcTlsEndptDropClassTxDroppedFrames     OBJECT-TYPE
        SYNTAX        Counter64
        MAX-ACCESS    read-only
        STATUS        current
        DESCRIPTION  "Number of Drop Class Tx Frames dropped."
        ::= { rcTlsEndptStatsEntry 280 }



-- Watermark type
rcTlsTrap OBJECT IDENTIFIER ::= { rcTls 9 } 

rcTlsEndptWatermarkIndication	OBJECT-TYPE
        SYNTAX        INTEGER { 
       			threasholdReached(1),
			tableFull(2)
       	   	      }	
        MAX-ACCESS    read-only
        STATUS        current 
        DESCRIPTION  " A Watermark indication signifies that the
                       Mac Table for the endpoint has reached its high watermark or already full "
        ::= { rcTlsTrap 1 } 

rcTlsUniIpServiceWatermarkIndication	OBJECT-TYPE
        SYNTAX        INTEGER { 
       			threasholdReached(1),
			tableFull(2)
       	   	      }	
        MAX-ACCESS    read-only
        STATUS        current 
        DESCRIPTION  " A Watermark indication signifies that the
                       Ip Table for the Uni Ip (Cust Ip) has reached its 
		       high watermark or already full "
        ::= { rcTlsTrap 2 } 

rcTlsSlot OBJECT-TYPE
        SYNTAX        INTEGER (1..10)
        MAX-ACCESS    read-only
        STATUS        current
        DESCRIPTION   "Slot Number"
        ::= { rcTlsTrap 3 }

rcTlsIsidId OBJECT-TYPE
        SYNTAX        INTEGER (1..16777215)
        MAX-ACCESS    read-only
        STATUS        current
        DESCRIPTION   "I-SID Identifier"
        ::= { rcTlsTrap 4 }

rcTlsIpCustIpWatermarkIndication   OBJECT-TYPE
        SYNTAX        INTEGER {
                                thresholdReached(1),
                                    tableFull(2)
        }
        MAX-ACCESS    read-only
        STATUS        current
        DESCRIPTION  " A Watermark indication signifies that the
        IP Table for the Cust Ip has reached its high watermark
        or already full "
        ::= { rcTlsTrap 5}

rcTlsIpCustIpVlan OBJECT-TYPE
        SYNTAX        INTEGER (1..4096)
        MAX-ACCESS    read-only
        STATUS        current
        DESCRIPTION   "Customer IP Vlan for the Ip Table which has 
                        reached its high watermark or is already full"
        ::= { rcTlsTrap 6}

rcTlsRmodLane  OBJECT-TYPE
        SYNTAX        INTEGER (0..2)
        MAX-ACCESS    read-only
        STATUS        current
        DESCRIPTION   "The Rmod Lane on which the Ip Table/Mac Table has reached
                       its high watermark or is already full"
        ::= { rcTlsTrap 7}

-- tlsEsmPort

rcTlsEsmGroupTable OBJECT-TYPE
        SYNTAX        SEQUENCE OF RcTlsEsmGroupEntry
        MAX-ACCESS    not-accessible
        STATUS        current
        DESCRIPTION   "Tls ESM port group table"
        ::= { rcTls 10 }

rcTlsEsmGroupEntry OBJECT-TYPE
        SYNTAX        RcTlsEsmGroupEntry
        MAX-ACCESS    not-accessible
        STATUS        current
        DESCRIPTION   "Entry containing info. for a particular group"
        INDEX         { rcTlsEsmGroupEsmPort, rcTlsEsmGroupLegacyPort, rcTlsEsmGroupUniAddr}
        ::= { rcTlsEsmGroupTable 1 }

RcTlsEsmGroupEntry ::= SEQUENCE {
	rcTlsEsmGroupEsmPort          InterfaceIndex,
	rcTlsEsmGroupLegacyPort       InterfaceIndex,
	rcTlsEsmGroupUniAddr	      IpAddress,
	rcTlsEsmGroupLegacyType       INTEGER,
	rcTlsEsmGroupTlsOverride      EnableValue,
	rcTlsEsmGroupVlanIds          IdList,	   
	rcTlsEsmGroupNumVlanIds       Integer32   	
	}

rcTlsEsmGroupEsmPort OBJECT-TYPE
        SYNTAX        InterfaceIndex	 
        MAX-ACCESS    not-accessible	
        STATUS        current
        DESCRIPTION   "ESM server port"
        ::= { rcTlsEsmGroupEntry 1}

rcTlsEsmGroupLegacyPort OBJECT-TYPE
        SYNTAX        InterfaceIndex	 
        MAX-ACCESS    not-accessible		
        STATUS        current
        DESCRIPTION   "ESM legacy port"
        ::= { rcTlsEsmGroupEntry 2}

rcTlsEsmGroupUniAddr OBJECT-TYPE
        SYNTAX        IpAddress 
        MAX-ACCESS    not-accessible
        STATUS        current
        DESCRIPTION   "Address of this Uni Instance, it should be no 
                       more than 24 bits."
        ::= { rcTlsEsmGroupEntry 3 }

rcTlsEsmGroupLegacyType OBJECT-TYPE
        SYNTAX        INTEGER {
			 other(0),           -- no port installed
                         rc100BaseTX(1),     -- (cat 5)
                         rc100BaseT2(2),     -- (cat 3)
                         rc100BaseF(3),      -- (100 mbps fiber)
                         rc1000BaseF(4),     -- (1000 mbps fiber)
                         rc1000BaseDualF(5), -- (fiber - dual connector)
                         rc10BaseF(6),       -- (10 mbps fiber)
                         rcPosMMF(7),        -- (multi mode fiber)
                         rcPosSMF(8),        -- (single mode fiber)
                         rcAtm(9),           -- (oc3, oc12, ds3, e3)
                         rcGbicLx(10),       -- (gigabit long haul)
                         rcGbicSx(11),       -- (gigabit short haul)
                         rcGbicXd(12),       -- (gigabit extended distance)
                         rcGbicCu(13),       -- (gigabit copper)
                         rcGbicOther(14),    -- (gigabit other)
                         rcOc3cSM(15),       -- (OC-3c SM)
                         rcOc3cMM(16),       -- (OC-3c MM)
                         rcOc3cCOPPER(17),   -- (OC-3c COPPER)
                         rcOc12cSM(18),      -- (OC-12c SM)
                         rcOc12cMM(19),      -- (OC-12c MM)
                         rcDs3(20),          -- (Ds3)
                         rcE3(21),           -- (E3)
                         rcGbicNone(22),     -- (Gbic card feature)
                         rc1000BaseT(23),    -- (1000 base copper)
                         rcGbicZx(24),       -- (gigabit very extended distance)
                         rcOc3cAtmSM(25),    -- (Atm OC-3c SM)
                         rcOc3cAtmMM(26),    -- (Atm OC-3c MM)
                         rcOc12cAtmSM(27),   -- (Atm OC-12c SM)
                         rcOc12cAtmMM(28),   -- (Atm OC-12c MM)
                         rcOc3cPosSM(29),    -- (Pos OC-3c SM)
                         rcOc3cPosMM(30),    -- (Pos OC-3c MM)
                         rcOc12cPosSM(31),   -- (Pos OC-12c SM)
                         rcOc12cPosMM(32),   -- (Pos OC-12c MM)
                         rcGbic1470(33),     -- (gigabit wavelength 1470)
                         rcGbic1490(34),     -- (gigabit wavelength 1490)
                         rcGbic1510(35),     -- (gigabit wavelength 1510)
                         rcGbic1530(36),     -- (gigabit wavelength 1530)
                         rcGbic1550(37),     -- (gigabit wavelength 1550)
                         rcGbic1570(38),     -- (gigabit wavelength 1570)
                         rcGbic1590(39),     -- (gigabit wavelength 1590)
                         rcGbic1610(40),     -- (gigabit wavelength 1610)
                         rcRmon(41),         -- (1000 base TProbe)
                         rcGbic1470APD(42),  -- (gigabit wavelength 1470-APD)
                         rcGbic1490APD(43),  -- (gigabit wavelength 1490-APD)
                         rcGbic1510APD(44),  -- (gigabit wavelength 1510-APD)
                         rcGbic1530APD(45),  -- (gigabit wavelength 1530-APD)
                         rcGbic1550APD(46),  -- (gigabit wavelength 1550-APD)
                         rcGbic1570APD(47),  -- (gigabit wavelength 1570-APD)
                         rcGbic1590APD(48),  -- (gigabit wavelength 1590-APD)
                         rcGbic1610APD(49),  -- (gigabit wavelength 1610-APD)
			 rc10GbLW(50),       -- (10 Gig Ethernet LW)
			 rc10GbLR(51),       -- (10 Gig Ethernet LR) 
                         rcLogicalServerPort(52), -- opm Prism used as a server for MPLS
			 rc1000BaseTX(53),   -- (tripple speed)
                         rc100BaseTXPOE(54), -- (tripple speed with POE support)
                         rcGbicBx(55),       -- (gigabit medium haul)
			 rcGbicEx(56)        -- (gigabit wavelength 1550)
	
		}	
        MAX-ACCESS    read-only
        STATUS        current
        DESCRIPTION   "Address of this Uni Instance, it should be no 
                       more than 24 bits."
        ::= { rcTlsEsmGroupEntry 4 }

rcTlsEsmGroupTlsOverride OBJECT-TYPE
        SYNTAX        EnableValue
        MAX-ACCESS    read-only
        STATUS        current
        DESCRIPTION   "Indicate the legacy port prority bit setting" 
        ::= { rcTlsEsmGroupEntry 5 }

rcTlsEsmGroupVlanIds OBJECT-TYPE
        SYNTAX        IdList (SIZE (4096))
        MAX-ACCESS    read-only  
        STATUS        current
        DESCRIPTION   "An array used to identify which VLANs this ESM port 
                      is assigned to.  Each VLAN ID is stored as a two
                      octet value. The first octet in the pair holds
                      bits 15-8 of the VLAN ID, while the second octet
                      holds bits 7-0 of the VLAN ID."
        ::= { rcTlsEsmGroupEntry 6 }

rcTlsEsmGroupNumVlanIds OBJECT-TYPE
        SYNTAX        Integer32
        MAX-ACCESS    read-only
        STATUS        current
        DESCRIPTION   "Used to indicate the number of VLAN IDs that
                      are stored in the rcTlsEsmGroupVlanIds variable."
        ::= { rcTlsEsmGroupEntry 7 }

-- ESM port stats

rcTlsEsmPortStatsTable OBJECT-TYPE
        SYNTAX        SEQUENCE OF RcTlsEsmPortStatsEntry
        MAX-ACCESS    not-accessible
        STATUS        current
        DESCRIPTION   "Tls Ethernet Service Module(ESM) port Traffic rate Stats table. 
	               Which contains maximum 1440 samples for each ESM port for 
		       24 hours. Each entry contains the minimum traffic rate, 
		       the maximum traffic rate and the average traffic rate 
		       within this particular minute for this port"
        ::= { rcTls 11 }

rcTlsEsmPortStatsEntry OBJECT-TYPE
        SYNTAX        RcTlsEsmPortStatsEntry
        MAX-ACCESS    not-accessible
        STATUS        current
        DESCRIPTION   "Entry contains maximum 1440 samples (24 hours) traffice rate stats
	               for a particular port. Each entry is 1 mintue traffic rate stats.
		       Contains the minimum traffic rate, the maximum traffic rate and 
		       average traffic rate within this particular minute for this port"
	INDEX         { rcTlsEsmPortStatsPort, rcTlsEsmPortStatsSample}
        ::= { rcTlsEsmPortStatsTable 1 }

RcTlsEsmPortStatsEntry ::= SEQUENCE {
	rcTlsEsmPortStatsPort         InterfaceIndex,
	rcTlsEsmPortStatsSample       INTEGER,
	rcTlsEsmPortStatsTimestamp    OCTET STRING,
	rcTlsEsmPortStatsMin          Gauge32,
	rcTlsEsmPortStatsMax          Gauge32,
	rcTlsEsmPortStatsAve          Gauge32	
	}

rcTlsEsmPortStatsPort OBJECT-TYPE
        SYNTAX        InterfaceIndex	 
        MAX-ACCESS    not-accessible
        STATUS        current
        DESCRIPTION   "ESM server port interface"
        ::= { rcTlsEsmPortStatsEntry 1}

rcTlsEsmPortStatsSample OBJECT-TYPE
        SYNTAX        INTEGER (1..1440)	 
        MAX-ACCESS    not-accessible
        STATUS        current
        DESCRIPTION   "Sample of the time as minute over 24 houre. The maximum 
	               samples is 1440 for each port since the data is collected.
		       (60 minute * 24 hours)."
        ::= { rcTlsEsmPortStatsEntry 2}

rcTlsEsmPortStatsTimestamp OBJECT-TYPE
        SYNTAX        OCTET STRING (SIZE (17)) 	 
        MAX-ACCESS    read-only	
        STATUS        current
        DESCRIPTION   "Date and time string of the sampling time, 
		       Format:DD:MM:YY|HH:MM:SS (10:02:04|11:00:00)"
        ::= { rcTlsEsmPortStatsEntry 3}

rcTlsEsmPortStatsMin  OBJECT-TYPE
        SYNTAX        Gauge32 	 
        MAX-ACCESS    read-only	
        STATUS        current
        DESCRIPTION   "Minimum traffic rate within this minute interval. 
	               unit: byte per second"
        ::= { rcTlsEsmPortStatsEntry 4}

rcTlsEsmPortStatsMax  OBJECT-TYPE
        SYNTAX        Gauge32 	 
        MAX-ACCESS    read-only	
        STATUS        current
        DESCRIPTION   "Maximum traffic rate within this minute interval.
	               unit: byte per second"
        ::= { rcTlsEsmPortStatsEntry 5}

rcTlsEsmPortStatsAve  OBJECT-TYPE
        SYNTAX        Gauge32 	 
        MAX-ACCESS    read-only	
        STATUS        current
        DESCRIPTION   "Average traffic rate within this minute interval.
	               unit: byte per second"
        ::= { rcTlsEsmPortStatsEntry 6}

-- ESM port last 15 minutes stats 

rcEsmPortStatsLastTable OBJECT-TYPE
        SYNTAX        SEQUENCE OF RcEsmPortStatsLastEntry
        MAX-ACCESS    not-accessible
        STATUS        current
        DESCRIPTION   "Tls Ethernet Service Module (ESM) port last 15 samples traffic 
	               rate Stats table. Contains the last 15 samples for each ESM port. 
		       Each entry contains the minimum traffic rate, the maximum traffic 
		       rate and the average traffic rate within this particular minute 
		       for this port. This table provide the capability to the SNMP 
		       agent call to get the last 15 minute stats efficently."
        ::= { rcTls 12 }

rcEsmPortStatsLastEntry OBJECT-TYPE
        SYNTAX        RcEsmPortStatsLastEntry
        MAX-ACCESS    not-accessible
        STATUS        current
        DESCRIPTION   "Entry contains the minimum traffic rate, the maximum traffic 
		       rate and the average traffic rate within this particular minute 
		       for this port."
        INDEX         { rcEsmPortStatsLastPort, rcEsmPortStatsLastSample}
        ::= { rcEsmPortStatsLastTable 1 }

RcEsmPortStatsLastEntry ::= SEQUENCE {
	rcEsmPortStatsLastPort         InterfaceIndex,
	rcEsmPortStatsLastSample       INTEGER,
	rcEsmPortStatsLastTimestamp    OCTET STRING,
	rcEsmPortStatsLastMin          Gauge32,
	rcEsmPortStatsLastMax          Gauge32,
	rcEsmPortStatsLastAve          Gauge32 	
	}

rcEsmPortStatsLastPort OBJECT-TYPE
        SYNTAX        InterfaceIndex	 
        MAX-ACCESS    not-accessible	
        STATUS        current
        DESCRIPTION   "ESM server port interface"
        ::= { rcEsmPortStatsLastEntry 1}

rcEsmPortStatsLastSample OBJECT-TYPE
        SYNTAX        INTEGER (1..15)	 
        MAX-ACCESS    not-accessible	
        STATUS        current
        DESCRIPTION   "The last 15 minute-sample of rcTlsEsmPortStatsEntry"
        ::= { rcEsmPortStatsLastEntry 2}

rcEsmPortStatsLastTimestamp OBJECT-TYPE
        SYNTAX        OCTET STRING (SIZE (17)) 	 
        MAX-ACCESS    read-only	
        STATUS        current
        DESCRIPTION   "Date and time string of the sampling time, 
		       Format:DD:MM:YY|HH:MM:SS (10:02:04|11:00:00AM)"
        ::= { rcEsmPortStatsLastEntry 3}

rcEsmPortStatsLastMin  OBJECT-TYPE
        SYNTAX        Gauge32 	 
        MAX-ACCESS    read-only	
        STATUS        current
        DESCRIPTION   "Minimum traffic rate within this minute interval. 
	               unit: byte per second"
        ::= { rcEsmPortStatsLastEntry 4}

rcEsmPortStatsLastMax  OBJECT-TYPE
        SYNTAX        Gauge32 	 
        MAX-ACCESS    read-only	
        STATUS        current
        DESCRIPTION   "Maximum traffic rate within this minute interval.
	               unit: byte per second"
        ::= { rcEsmPortStatsLastEntry 5}

rcEsmPortStatsLastAve  OBJECT-TYPE
        SYNTAX        Gauge32 	 
        MAX-ACCESS    read-only	
        STATUS        current
        DESCRIPTION   "Average traffic rate within this minute interval.
	               unit: byte per second"
        ::= { rcEsmPortStatsLastEntry 6}

-- ESM port 60 sample average stats 

rcEsmPortStatsHourTable OBJECT-TYPE
        SYNTAX        SEQUENCE OF RcEsmPortStatsHourEntry
        MAX-ACCESS    not-accessible
        STATUS        current
        DESCRIPTION   "Tls Ethernet Service Module (ESM) port Hour traffic rate Stats table,
	               Contains maximum 24 entries for each port . Each entry represent one hour 
		       average traffic rate. Which is average of 60 samples rcTlsEsmPortStatsAve 
		       of the rcTlsEsmPortStatsTable for that particular hour"
        ::= { rcTls 13 }

rcEsmPortStatsHourEntry OBJECT-TYPE
        SYNTAX        RcEsmPortStatsHourEntry
        MAX-ACCESS    not-accessible
        STATUS        current
        DESCRIPTION   "Contains maximum 24 entries for each port . Each entry represent one hour 
		       average traffic rate. Which is average of 60 samples rcTlsEsmPortStatsAve 
		       of the rcTlsEsmPortStatsTable for that particular hour"
        INDEX         { rcEsmPortStatsHourPort, rcEsmPortStatsHourHour}
        ::= { rcEsmPortStatsHourTable 1 }

RcEsmPortStatsHourEntry ::= SEQUENCE {
	rcEsmPortStatsHourPort          InterfaceIndex,
	rcEsmPortStatsHourHour          INTEGER,
	rcEsmPortStatsHourFromTimestamp OCTET STRING,
	rcEsmPortStatsHourToTimestamp   OCTET STRING,
	rcEsmPortStatsHourAve           Gauge32 	
	}

rcEsmPortStatsHourPort OBJECT-TYPE
        SYNTAX        InterfaceIndex	 
        MAX-ACCESS    not-accessible	
        STATUS        current
        DESCRIPTION   "ESM server port interface"
        ::= { rcEsmPortStatsHourEntry 1}

rcEsmPortStatsHourHour OBJECT-TYPE
        SYNTAX        INTEGER (1..24)	 
        MAX-ACCESS    not-accessible	
        STATUS        current
        DESCRIPTION   "Hour index of the 24 hours sampling"
        ::= { rcEsmPortStatsHourEntry 2}

rcEsmPortStatsHourFromTimestamp OBJECT-TYPE
        SYNTAX        OCTET STRING (SIZE (17)) 	 
        MAX-ACCESS    read-only	
        STATUS        current
        DESCRIPTION   "Time stamp of starting time for the hour average traffic 
	               rate calculation.  
		       Format:DD:MM:YY|HH:MM:SS (10:02:04|11:00:00)"
        ::= { rcEsmPortStatsHourEntry 3}

rcEsmPortStatsHourToTimestamp OBJECT-TYPE
        SYNTAX        OCTET STRING (SIZE (17)) 	 
        MAX-ACCESS    read-only	
        STATUS        current
        DESCRIPTION   "Time stamp of ending time for the hour average traffic 
	               rate calculation.  
		       Format:DD:MM:YY|HH:MM:SS (10:02:04|11:00:00)" 
        ::= { rcEsmPortStatsHourEntry 4}

rcEsmPortStatsHourAve  OBJECT-TYPE
        SYNTAX        Gauge32 	 
        MAX-ACCESS    read-only	
        STATUS        current
        DESCRIPTION   "Average traffic rate for this hour interval. 
	               unit: byte per second"
        ::= { rcEsmPortStatsHourEntry 5}

-- Esm Port Stats daily static

rcEsmPortStatsDailyTable OBJECT-TYPE
        SYNTAX        SEQUENCE OF RcEsmPortStatsDailyEntry
        MAX-ACCESS    not-accessible
        STATUS        current
        DESCRIPTION   "Tls Ethernet Service Module(ESM) port daily Stats table contains 
	               24 hours sample stats for each port. Each entry contain 24 hours 
		       average traffic rate. WHich is average of all 1440 samples 
		       rcTlsEsmPortStatsAve of the rcTlsEsmPortStatsTable"
        ::= { rcTls 14 }

rcEsmPortStatsDailyEntry OBJECT-TYPE
        SYNTAX        RcEsmPortStatsDailyEntry
        MAX-ACCESS    not-accessible
        STATUS        current
        DESCRIPTION   "Entry contains average of all 1440 samples 
		       rcTlsEsmPortStatsAve of the rcTlsEsmPortStatsTable"
        INDEX         { rcEsmPortStatsDailyPort}
        ::= { rcEsmPortStatsDailyTable 1 }

RcEsmPortStatsDailyEntry ::= SEQUENCE {
	rcEsmPortStatsDailyPort          InterfaceIndex,
	rcEsmPortStatsDailyFromTimestamp OCTET STRING,
	rcEsmPortStatsDailyToTimestamp   OCTET STRING,
	rcEsmPortStatsDailyAve           Gauge32 	
	}

rcEsmPortStatsDailyPort OBJECT-TYPE
        SYNTAX        InterfaceIndex	 
        MAX-ACCESS    not-accessible	
        STATUS        current
        DESCRIPTION   "ESM server port interface"
        ::= { rcEsmPortStatsDailyEntry 1}

rcEsmPortStatsDailyFromTimestamp OBJECT-TYPE
        SYNTAX        OCTET STRING (SIZE (17)) 	 
        MAX-ACCESS    read-only	
        STATUS        current
        DESCRIPTION   "Time stamp of starting time for the daily average traffic 
	               rate calculation.  
		       Format:DD:MM:YY|HH:MM:SS (10:02:04|11:00:00)"
        ::= { rcEsmPortStatsDailyEntry 2}

rcEsmPortStatsDailyToTimestamp OBJECT-TYPE
        SYNTAX        OCTET STRING (SIZE (17)) 	 
        MAX-ACCESS    read-only	
        STATUS        current
        DESCRIPTION   "Time stamp of ending time for the daily average traffic 
	               rate calculation.  
		       Format:DD:MM:YY|HH:MM:SS (10:02:04|11:00:00)"
        ::= { rcEsmPortStatsDailyEntry 3}

rcEsmPortStatsDailyAve  OBJECT-TYPE
        SYNTAX        Gauge32 	 
        MAX-ACCESS    read-only	
        STATUS        current
        DESCRIPTION   "Average daily traffic rate for last 24 hours, unit: byte per second"
        ::= { rcEsmPortStatsDailyEntry 4}

-- Esm Port Stats total sample

rcEsmPortStatsSizeTable OBJECT-TYPE
        SYNTAX        SEQUENCE OF RcEsmPortStatsSizeEntry
        MAX-ACCESS    not-accessible
        STATUS        current
        DESCRIPTION   "Tls ESM port Stats total sample size for each port table"
        ::= { rcTls 15 }

rcEsmPortStatsSizeEntry OBJECT-TYPE
        SYNTAX        RcEsmPortStatsSizeEntry
        MAX-ACCESS    not-accessible
        STATUS        current
        DESCRIPTION   "Entry contain total samples size for a particular port"
        INDEX         { rcEsmPortStatsSizePort}
        ::= { rcEsmPortStatsSizeTable 1 }

RcEsmPortStatsSizeEntry ::= SEQUENCE {
	rcEsmPortStatsSizePort         InterfaceIndex,
	rcEsmPortStatsSizeTotal        Integer32
	}

rcEsmPortStatsSizePort OBJECT-TYPE
        SYNTAX        InterfaceIndex	 
        MAX-ACCESS    not-accessible	
        STATUS        current
        DESCRIPTION   "ESM server port"
        ::= { rcEsmPortStatsSizeEntry 1}

rcEsmPortStatsSizeTotal OBJECT-TYPE
        SYNTAX        Integer32 
        MAX-ACCESS    read-only	
        STATUS        current
        DESCRIPTION   "Times of the sample"
        ::= { rcEsmPortStatsSizeEntry 2}

-- ESM port stats clear
rcTlsEsmPortTable OBJECT-TYPE
        SYNTAX        SEQUENCE OF RcTlsEsmPortEntry
        MAX-ACCESS    not-accessible
        STATUS        current
        DESCRIPTION   "Tls ESM port table, which is used for reset the stats 
	               counter for each port"
        ::= { rcTls 16 }

rcTlsEsmPortEntry OBJECT-TYPE
        SYNTAX        RcTlsEsmPortEntry
        MAX-ACCESS    not-accessible
        STATUS        current
        DESCRIPTION   "Entry contain attribute for reset the stats counter 
	               for a particular port"
        INDEX         { rcTlsEsmPortPort}
        ::= { rcTlsEsmPortTable 1 }

RcTlsEsmPortEntry ::= SEQUENCE {
	rcTlsEsmPortPort             InterfaceIndex,
	rcTlsEsmPortClearStats       TruthValue
	}

rcTlsEsmPortPort OBJECT-TYPE
        SYNTAX        InterfaceIndex	 
        MAX-ACCESS    not-accessible	
        STATUS        current
        DESCRIPTION   "ESM server port"
        ::= { rcTlsEsmPortEntry 1}

rcTlsEsmPortClearStats OBJECT-TYPE
       SYNTAX        TruthValue
       MAX-ACCESS    read-write
       STATUS        current
       DESCRIPTION   "Clear Esm port Statistics"
       ::= {rcTlsEsmPortEntry 2 }  


-- rcTlsUniIpServiceTable 

rcTlsUniIpServiceTable OBJECT-TYPE
        SYNTAX        SEQUENCE OF RcTlsUniIpServiceEntry
        MAX-ACCESS    not-accessible
        STATUS        current
        DESCRIPTION   "Table contains a customer IP Vlan and the local IP 
		       Vlan for IP Mcast service over UNI in the BAN box "
        ::= { rcTls 17 }

rcTlsUniIpServiceEntry OBJECT-TYPE
        SYNTAX        RcTlsUniIpServiceEntry
        MAX-ACCESS    not-accessible
        STATUS        current
        DESCRIPTION   "Entry contains the customer IP Vlan and the Local 
		       Vlan for for the IP Mcast service over UNI in the BAN box"
        INDEX         { rcTlsUniIpServiceAddr, rcTlsUniIpServiceCustIpVlan }
        ::= { rcTlsUniIpServiceTable 1 }

RcTlsUniIpServiceEntry ::=
        SEQUENCE {
                rcTlsUniIpServiceAddr                       IpAddress,
                rcTlsUniIpServiceCustIpVlan                 INTEGER,
                rcTlsUniIpServiceServiceProviderIpVlan      INTEGER,
                rcTlsUniIpServiceRowStatus                  RowStatus,
		rcTlsUniIpServiceName                       DisplayString,
		rcTlsUniIpServiceAgeTimer                   INTEGER,
		rcTlsUniIpServiceIngressCosProfileName      DisplayString,
		rcTlsUniIpServiceIngressPolicer             EnableValue,
		rcTlsUniIpServiceEgressCosProfileName       DisplayString,
		rcTlsUniIpServiceEgressPolicer              EnableValue,
		rcTlsUniIpServiceAction                     INTEGER,
		rcTlsUniIpServiceAdminState                 EnableValue,
                rcTlsUniIpServiceOperState                  INTEGER,
	        rcTlsUniIpServicePriMapping                 OCTET STRING,
	        rcTlsUniIpServicePriOverride                TruthValue,
		rcTlsUniIpServiceIpTblSize                  INTEGER,	
		rcTlsUniIpServiceIpTblWaterMk               INTEGER,	
		rcTlsUniIpServiceIngressMirrorState         EnableValue,
        	rcTlsUniIpServiceEgressMirrorState          EnableValue,
                rcTlsUniIpServicePriOverrideType            INTEGER,
                rcTlsUniIpServiceColorBasedRemarking        EnableValue,
                rcTlsUniIpServiceDropRedColorPackets        TruthValue
        }

rcTlsUniIpServiceAddr OBJECT-TYPE
        SYNTAX        IpAddress 
        MAX-ACCESS    not-accessible
        STATUS        current
        DESCRIPTION   "Address of the Uni Instance - rcTlsUniAddr"
        ::= { rcTlsUniIpServiceEntry 1 }

rcTlsUniIpServiceCustIpVlan OBJECT-TYPE
        SYNTAX        INTEGER (1..4096)
        MAX-ACCESS    not-accessible
        STATUS        current
        DESCRIPTION   "Customer IP Vlan for UNI IP Mcast Vlan mapping"
        ::= { rcTlsUniIpServiceEntry 2 }

rcTlsUniIpServiceServiceProviderIpVlan OBJECT-TYPE
        SYNTAX        INTEGER (1..4096)
        MAX-ACCESS    read-create
        STATUS        current
        DESCRIPTION   "Service Provider IP Vlan for UNI IP Mcast Vlan mapping"
        ::= { rcTlsUniIpServiceEntry 3 }

rcTlsUniIpServiceName  OBJECT-TYPE
        SYNTAX        DisplayString (SIZE (0..30)) 
        MAX-ACCESS    read-create
        STATUS        current
        DESCRIPTION   "Name of UNI IP Service Vlan Entry. By default, It is 
		       VLAN-<uni id>-<cust ip vlan>"
        ::= { rcTlsUniIpServiceEntry 4 } 

rcTlsUniIpServiceRowStatus  OBJECT-TYPE
        SYNTAX        RowStatus
        MAX-ACCESS    read-create
        STATUS        current
        DESCRIPTION   "Used to create/delete entries in the rcTlsUniIpServiceEntry."
        ::= { rcTlsUniIpServiceEntry 5 }

rcTlsUniIpServiceAgeTimer  OBJECT-TYPE
        SYNTAX        INTEGER (1..1966020)
        MAX-ACCESS    read-create
        STATUS        current
        DESCRIPTION   "Mac address ageout timer in seconds.
		       Valid only if rcTlsUniIpService is Enabled"
	DEFVAL        { 300 }
        ::= { rcTlsUniIpServiceEntry 6 }

rcTlsUniIpServiceIngressCosProfileName OBJECT-TYPE
        SYNTAX        DisplayString (SIZE (1..20)) 
        MAX-ACCESS    read-write
        STATUS        current
        DESCRIPTION   "Ingress COS Profile Table Name for Customer Ip Service"
        DEFVAL       { "DEFAULT_PROFILE"  } 
        ::= { rcTlsUniIpServiceEntry 7 }

rcTlsUniIpServiceIngressPolicer OBJECT-TYPE
        SYNTAX        EnableValue
        MAX-ACCESS    read-create
        STATUS        current
        DESCRIPTION   "Enable/disable to use Ingress Cos Profile table 
			(rcTlsUniIpServiceIngressCosProfileName) for this 
			customer IP service"
	DEFVAL        { enable }
        ::= { rcTlsUniIpServiceEntry 8 }

rcTlsUniIpServiceEgressCosProfileName OBJECT-TYPE
        SYNTAX        DisplayString (SIZE (0..20)) 
        MAX-ACCESS    read-create
        STATUS        current
        DESCRIPTION   "Egress COS Profile Table Name for this customer IP
			Service."
        DEFVAL       { "DEFAULT_PROFILE"  } 
        ::= { rcTlsUniIpServiceEntry 9 }

rcTlsUniIpServiceEgressPolicer OBJECT-TYPE
        SYNTAX        EnableValue
        MAX-ACCESS    read-create
        STATUS        current
        DESCRIPTION   "Enable/disable to use Egress Cos Profile table 
			(rcTlsUniIpServiceEgressCosProfileName) for this 
			customer Ip Service"
	DEFVAL        { disable }
        ::= { rcTlsUniIpServiceEntry 10 }

rcTlsUniIpServiceAction  OBJECT-TYPE 
	SYNTAX        INTEGER {
                         none(1),       -- none of the following
                         flushIp(2)     -- flush Ip forwarding table
                      }
        MAX-ACCESS    read-create
        STATUS        current
        DESCRIPTION   "Mcast UNI related action- Flush learningMac addresse"
        DEFVAL        { none }
	::= { rcTlsUniIpServiceEntry 11 }

rcTlsUniIpServiceAdminState OBJECT-TYPE
        SYNTAX        EnableValue
        MAX-ACCESS    read-create
        STATUS        current
        DESCRIPTION   "Value indicating whether the Ip Service is enabled"
        DEFVAL        { disable }
        ::= { rcTlsUniIpServiceEntry 12 }

rcTlsUniIpServiceOperState OBJECT-TYPE
        SYNTAX        INTEGER { 
                          up(1), 
                          down(2) 
                       }
        MAX-ACCESS    read-only
        STATUS        current
        DESCRIPTION   "The current operational state of this Customer IP Vlan."
        ::= { rcTlsUniIpServiceEntry 13 }

rcTlsUniIpServicePriMapping OBJECT-TYPE
        SYNTAX        OCTET STRING (SIZE(8))
        MAX-ACCESS    read-create
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcTlsUniIpServiceEntry 14 }

rcTlsUniIpServicePriOverride  OBJECT-TYPE
        SYNTAX          TruthValue
        MAX-ACCESS      read-create
        STATUS          current
        DESCRIPTION     "Enable or disable to override the Priority Mapping."
        DEFVAL          { false }
        ::= {rcTlsUniIpServiceEntry 15 }

rcTlsUniIpServiceIpTblSize OBJECT-TYPE
        SYNTAX        INTEGER (0..97000) 
        MAX-ACCESS    read-create
        STATUS        current
        DESCRIPTION   "The maximum size of the IP table. No limit if
                       it's set to 0."
        DEFVAL       { 0 }
        ::= { rcTlsUniIpServiceEntry 16 }

rcTlsUniIpServiceIpTblWaterMk OBJECT-TYPE
        SYNTAX        INTEGER (0..90)
        MAX-ACCESS    read-create
        STATUS        current
        DESCRIPTION   "The Low Water Mark for Ip table size. Set to 90%
                       of the table size, can be over-written."
        DEFVAL       { 0 }
        ::= { rcTlsUniIpServiceEntry 17 }
rcTlsUniIpServiceIngressMirrorState OBJECT-TYPE
        SYNTAX        EnableValue
        MAX-ACCESS    read-write
        STATUS        current
        DESCRIPTION   "disable/enable ingress mirroring on this cust-ip-vlan."
        DEFVAL        { disable }
        ::= { rcTlsUniIpServiceEntry 18 }

rcTlsUniIpServiceEgressMirrorState OBJECT-TYPE
        SYNTAX        EnableValue
        MAX-ACCESS    read-write
        STATUS        current
        DESCRIPTION   "disable/enable egress mirroring on this cust-ip-vlan."
        DEFVAL        { disable }
        ::= { rcTlsUniIpServiceEntry 19 }

rcTlsUniIpServicePriOverrideType OBJECT-TYPE
        SYNTAX        INTEGER
                      {
                         tos(1),
                         dscp(2)
                      }
        MAX-ACCESS    read-write
        STATUS        current
        DESCRIPTION   "This field indicated whether ToS or DSCP should be
                       used to override P bit when override is enabled."
        DEFVAL        { tos }
        ::= { rcTlsUniIpServiceEntry 20 }

rcTlsUniIpServiceColorBasedRemarking OBJECT-TYPE
        SYNTAX        EnableValue
        MAX-ACCESS    read-write
        STATUS        current
        DESCRIPTION   "disable/enable color-based egress mapping for this
                      end-point."
        DEFVAL        { disable }
        ::= { rcTlsUniIpServiceEntry 21 }

rcTlsUniIpServiceDropRedColorPackets OBJECT-TYPE
        SYNTAX        TruthValue
        MAX-ACCESS    read-write
        STATUS        current
        DESCRIPTION   "disable/enable dropping of red-colored packets for
                      this end-point if color-based mapping is used."
        DEFVAL        { true }
        ::= { rcTlsUniIpServiceEntry 22 }

-- Tls Uni Ip Service  STATS TABLE

rcTlsUniIpServiceStatsTable OBJECT-TYPE
        SYNTAX        SEQUENCE OF RcTlsUniIpServiceStatsEntry
        MAX-ACCESS    not-accessible
        STATUS        current
        DESCRIPTION   "Tls Uni Ip service statistics table. Which is used to represent
			the Customer Ip vlan service statistics for Uni Ip Service"
        ::= { rcTls 18 }
 
rcTlsUniIpServiceStatsEntry OBJECT-TYPE
        SYNTAX        RcTlsUniIpServiceStatsEntry
        MAX-ACCESS    not-accessible
        STATUS        current
        DESCRIPTION   "A Tls Uni Ip Service Statistics table entry. Which is used
                       for customer Ip Vlan"
        INDEX         { rcTlsUniIpServiceStatsAddr,rcTlsUniIpServiceStatsCustIpVlan}
        ::= { rcTlsUniIpServiceStatsTable 1 }
 
RcTlsUniIpServiceStatsEntry ::=
        SEQUENCE { 
 		rcTlsUniIpServiceStatsAddr          			IpAddress,	
                rcTlsUniIpServiceStatsCustIpVlan       			INTEGER, 
                rcTlsUniIpServiceStatsPremRxOctets	       		Counter64,	
       		rcTlsUniIpServiceStatsPremRxDroppedOctets   		Counter64,
		rcTlsUniIpServiceStatsGoldRxOctets			Counter64,	
		rcTlsUniIpServiceStatsGoldRxDroppedOctets   		Counter64,
		rcTlsUniIpServiceStatsSilverRxOctets	      		Counter64,	
		rcTlsUniIpServiceStatsSilverRxDroppedOctets 		Counter64,
		rcTlsUniIpServiceStatsStndRxOctets	      		Counter64,	
		rcTlsUniIpServiceStatsStndRxDroppedOctets   		Counter64,
		rcTlsUniIpServiceStatsPremTxOctets	      		Counter64,	
		rcTlsUniIpServiceStatsGoldTxOctets	      		Counter64,	
		rcTlsUniIpServiceStatsSilverTxOctets	      		Counter64,
		rcTlsUniIpServiceStatsStndTxOctets	      		Counter64,	
		rcTlsUniIpServiceStatsPremTxMcastOctets     		Counter64,	
		rcTlsUniIpServiceStatsGoldTxMcastOctets     		Counter64,	
		rcTlsUniIpServiceStatsSilverTxMcastOctets   		Counter64,
		rcTlsUniIpServiceStatsStndTxMcastOctets     		Counter64,
                rcTlsUniIpServiceStatsClear            			TruthValue,
		rcTlsUniIpServiceStatsPremCongestionDropOctets 		Counter64,
		rcTlsUniIpServiceStatsGoldCongestionDropOctets 		Counter64,
		rcTlsUniIpServiceStatsSilverCongestionDropOctets 	Counter64,	
		rcTlsUniIpServiceStatsStndCongestionDropOctets 		Counter64,	
		rcTlsUniIpServiceStatsPremCirDroppedOctets   		Counter64,
		rcTlsUniIpServiceStatsPremPirDroppedOctets   		Counter64,
		rcTlsUniIpServiceStatsGoldCirDroppedOctets   		Counter64,
		rcTlsUniIpServiceStatsGoldPirDroppedOctets   		Counter64,
		rcTlsUniIpServiceStatsSilverCirDroppedOctets   		Counter64,
		rcTlsUniIpServiceStatsSilverPirDroppedOctets   		Counter64,
		rcTlsUniIpServiceStatsStndCirDroppedOctets   		Counter64,
		rcTlsUniIpServiceStatsStndPirDroppedOctets   		Counter64,
		rcTlsUniIpServiceStatsName                   		DisplayString,
		rcTlsUniIpServiceStatsPremTxDroppedOctets	       	Counter64,	
		rcTlsUniIpServiceStatsGoldTxDroppedOctets	       	Counter64,	
		rcTlsUniIpServiceStatsSilverTxDroppedOctets	       	Counter64,
		rcTlsUniIpServiceStatsStndTxDroppedOctets	       	Counter64,	
		rcTlsUniIpServiceStatsPremTxCongestionDropOctets   	Counter64,
		rcTlsUniIpServiceStatsGoldTxCongestionDropOctets   	Counter64,
		rcTlsUniIpServiceStatsSilverTxCongestionDropOctets 	Counter64,	
		rcTlsUniIpServiceStatsStndTxCongestionDropOctets   	Counter64,	
		rcTlsUniIpServiceStatsPremTxCirDroppedOctets       	Counter64,
		rcTlsUniIpServiceStatsPremTxPirDroppedOctets       	Counter64,
		rcTlsUniIpServiceStatsGoldTxCirDroppedOctets       	Counter64,
		rcTlsUniIpServiceStatsGoldTxPirDroppedOctets       	Counter64,
		rcTlsUniIpServiceStatsSilverTxCirDroppedOctets     	Counter64,
		rcTlsUniIpServiceStatsSilverTxPirDroppedOctets     	Counter64,
		rcTlsUniIpServiceStatsStndTxCirDroppedOctets       	Counter64,
		rcTlsUniIpServiceStatsStndTxPirDroppedOctets       	Counter64,
		rcTlsUniIpServiceStatsRxMcastTotalOctets           	Counter64,
		rcTlsUniIpServiceStatsTxMcastTotalOctets           	Counter64,
		rcTlsUniIpServiceStatsPremRxMcastDroppedOctets          Counter64,
		rcTlsUniIpServiceStatsGoldRxMcastDroppedOctets          Counter64,
		rcTlsUniIpServiceStatsSilverRxMcastDroppedOctets        Counter64,
		rcTlsUniIpServiceStatsStndRxMcastDroppedOctets          Counter64,
		rcTlsUniIpServiceStatsPremRxFrames	           Counter64,
       		rcTlsUniIpServiceStatsPremRxDroppedFrames          Counter64,
		rcTlsUniIpServiceStatsGoldRxFrames		   Counter64,
		rcTlsUniIpServiceStatsGoldRxDroppedFrames          Counter64,
		rcTlsUniIpServiceStatsSilverRxFrames	           Counter64,
		rcTlsUniIpServiceStatsSilverRxDroppedFrames        Counter64,
		rcTlsUniIpServiceStatsStndRxFrames	      	   Counter64,
		rcTlsUniIpServiceStatsStndRxDroppedFrames          Counter64,
		rcTlsUniIpServiceStatsPremTxFrames	           Counter64,
		rcTlsUniIpServiceStatsGoldTxFrames	           Counter64,
		rcTlsUniIpServiceStatsSilverTxFrames	           Counter64,
		rcTlsUniIpServiceStatsStndTxFrames	           Counter64,
		rcTlsUniIpServiceStatsPremTxMcastFrames            Counter64,
		rcTlsUniIpServiceStatsGoldTxMcastFrames            Counter64,
		rcTlsUniIpServiceStatsSilverTxMcastFrames          Counter64,
		rcTlsUniIpServiceStatsStndTxMcastFrames            Counter64,
		rcTlsUniIpServiceStatsPremCongestionDropFrames     Counter64,
		rcTlsUniIpServiceStatsGoldCongestionDropFrames     Counter64,
		rcTlsUniIpServiceStatsSilverCongestionDropFrames   Counter64,
		rcTlsUniIpServiceStatsStndCongestionDropFrames     Counter64,
		rcTlsUniIpServiceStatsPremCirDroppedFrames         Counter64,
		rcTlsUniIpServiceStatsPremPirDroppedFrames         Counter64,
		rcTlsUniIpServiceStatsGoldCirDroppedFrames         Counter64,
		rcTlsUniIpServiceStatsGoldPirDroppedFrames         Counter64,
		rcTlsUniIpServiceStatsSilverCirDroppedFrames       Counter64,
		rcTlsUniIpServiceStatsSilverPirDroppedFrames       Counter64,
		rcTlsUniIpServiceStatsStndCirDroppedFrames         Counter64,
		rcTlsUniIpServiceStatsStndPirDroppedFrames         Counter64,
		rcTlsUniIpServiceStatsPremTxDroppedFrames	   Counter64,
		rcTlsUniIpServiceStatsGoldTxDroppedFrames	   Counter64,
		rcTlsUniIpServiceStatsSilverTxDroppedFrames	   Counter64,
		rcTlsUniIpServiceStatsStndTxDroppedFrames	   Counter64,
		rcTlsUniIpServiceStatsPremTxCongestionDropFrames   Counter64,
		rcTlsUniIpServiceStatsGoldTxCongestionDropFrames   Counter64,
		rcTlsUniIpServiceStatsSilverTxCongestionDropFrames Counter64,
		rcTlsUniIpServiceStatsStndTxCongestionDropFrames   Counter64,
		rcTlsUniIpServiceStatsPremTxCirDroppedFrames       Counter64,
		rcTlsUniIpServiceStatsPremTxPirDroppedFrames       Counter64,
		rcTlsUniIpServiceStatsGoldTxCirDroppedFrames       Counter64,
		rcTlsUniIpServiceStatsGoldTxPirDroppedFrames       Counter64,
		rcTlsUniIpServiceStatsSilverTxCirDroppedFrames     Counter64,
		rcTlsUniIpServiceStatsSilverTxPirDroppedFrames     Counter64,
		rcTlsUniIpServiceStatsStndTxCirDroppedFrames       Counter64,
		rcTlsUniIpServiceStatsStndTxPirDroppedFrames       Counter64,
		rcTlsUniIpServiceStatsRxMcastTotalFrames           Counter64,
		rcTlsUniIpServiceStatsTxMcastTotalFrames           Counter64,
		rcTlsUniIpServiceStatsPremRxMcastDroppedFrames     Counter64,
		rcTlsUniIpServiceStatsGoldRxMcastDroppedFrames     Counter64,
		rcTlsUniIpServiceStatsSilverRxMcastDroppedFrames   Counter64,
		rcTlsUniIpServiceStatsStndRxMcastDroppedFrames     Counter64,
	rcTlsUniIpServiceStatsPremRxCirOctets			Counter64,
	rcTlsUniIpServiceStatsPremRxCirOopOctets		Counter64,
	rcTlsUniIpServiceStatsPremRxEirOctets			Counter64,
	rcTlsUniIpServiceStatsPremRxEirOopOctets		Counter64,
	rcTlsUniIpServiceStatsPremRxEirDroppedOctets		Counter64,
	rcTlsUniIpServiceStatsPremRxPirOctets			Counter64,
	rcTlsUniIpServiceStatsPremRxPirOopOctets		Counter64,
	rcTlsUniIpServiceStatsPremRxGreenOctets		Counter64,
	rcTlsUniIpServiceStatsPremRxYellowOctets		Counter64,
	rcTlsUniIpServiceStatsPremRxRedOctets			Counter64,
	rcTlsUniIpServiceStatsGoldRxCirOctets			Counter64,
	rcTlsUniIpServiceStatsGoldRxCirOopOctets		Counter64,
	rcTlsUniIpServiceStatsGoldRxEirOctets			Counter64,
	rcTlsUniIpServiceStatsGoldRxEirOopOctets		Counter64,
	rcTlsUniIpServiceStatsGoldRxEirDroppedOctets		Counter64,
	rcTlsUniIpServiceStatsGoldRxPirOctets			Counter64,
	rcTlsUniIpServiceStatsGoldRxPirOopOctets		Counter64,
	rcTlsUniIpServiceStatsGoldRxGreenOctets		Counter64,
	rcTlsUniIpServiceStatsGoldRxYellowOctets		Counter64,
	rcTlsUniIpServiceStatsGoldRxRedOctets			Counter64,
	rcTlsUniIpServiceStatsSilverRxCirOctets			Counter64,
	rcTlsUniIpServiceStatsSilverRxCirOopOctets		Counter64,
	rcTlsUniIpServiceStatsSilverRxEirOctets			Counter64,
	rcTlsUniIpServiceStatsSilverRxEirOopOctets		Counter64,
	rcTlsUniIpServiceStatsSilverRxEirDroppedOctets		Counter64,
	rcTlsUniIpServiceStatsSilverRxPirOctets			Counter64,
	rcTlsUniIpServiceStatsSilverRxPirOopOctets		Counter64,
	rcTlsUniIpServiceStatsSilverRxGreenOctets		Counter64,
	rcTlsUniIpServiceStatsSilverRxYellowOctets		Counter64,
	rcTlsUniIpServiceStatsSilverRxRedOctets			Counter64,
	rcTlsUniIpServiceStatsStndRxCirOctets			Counter64,
	rcTlsUniIpServiceStatsStndRxCirOopOctets		Counter64,
	rcTlsUniIpServiceStatsStndRxEirOctets			Counter64,
	rcTlsUniIpServiceStatsStndRxEirOopOctets		Counter64,
	rcTlsUniIpServiceStatsStndRxEirDroppedOctets		Counter64,
	rcTlsUniIpServiceStatsStndRxPirOctets			Counter64,
	rcTlsUniIpServiceStatsStndRxPirOopOctets		Counter64,
	rcTlsUniIpServiceStatsStndRxGreenOctets		Counter64,
	rcTlsUniIpServiceStatsStndRxYellowOctets		Counter64,
	rcTlsUniIpServiceStatsStndRxRedOctets			Counter64,
	rcTlsUniIpServiceStatsMcastRxDroppedOctets		Counter64,
	rcTlsUniIpServiceStatsBcastUUcastRxTotalOctets		Counter64,
	rcTlsUniIpServiceStatsBcastUUcastRxDroppedOctets	Counter64,
	rcTlsUniIpServiceStatsPremRxCirFrames			Counter64,
	rcTlsUniIpServiceStatsPremRxCirOopFrames		Counter64,
	rcTlsUniIpServiceStatsPremRxEirFrames			Counter64,
	rcTlsUniIpServiceStatsPremRxEirOopFrames		Counter64,
	rcTlsUniIpServiceStatsPremRxEirDroppedFrames		Counter64,
	rcTlsUniIpServiceStatsPremRxPirFrames			Counter64,
	rcTlsUniIpServiceStatsPremRxPirOopFrames		Counter64,
	rcTlsUniIpServiceStatsPremRxGreenFrames		Counter64,
	rcTlsUniIpServiceStatsPremRxYellowFrames		Counter64,
	rcTlsUniIpServiceStatsPremRxRedFrames		Counter64,
	rcTlsUniIpServiceStatsGoldRxCirFrames			Counter64,
	rcTlsUniIpServiceStatsGoldRxCirOopFrames		Counter64,
	rcTlsUniIpServiceStatsGoldRxEirFrames			Counter64,
	rcTlsUniIpServiceStatsGoldRxEirOopFrames		Counter64,
	rcTlsUniIpServiceStatsGoldRxEirDroppedFrames		Counter64,
	rcTlsUniIpServiceStatsGoldRxPirFrames			Counter64,
	rcTlsUniIpServiceStatsGoldRxPirOopFrames		Counter64,
	rcTlsUniIpServiceStatsGoldRxGreenFrames		Counter64,
	rcTlsUniIpServiceStatsGoldRxYellowFrames		Counter64,
	rcTlsUniIpServiceStatsGoldRxRedFrames			Counter64,
	rcTlsUniIpServiceStatsSilverRxCirFrames			Counter64,
	rcTlsUniIpServiceStatsSilverRxCirOopFrames		Counter64,
	rcTlsUniIpServiceStatsSilverRxEirFrames			Counter64,
	rcTlsUniIpServiceStatsSilverRxEirOopFrames		Counter64,
	rcTlsUniIpServiceStatsSilverRxEirDroppedFrames		Counter64,
	rcTlsUniIpServiceStatsSilverRxPirFrames			Counter64,
	rcTlsUniIpServiceStatsSilverRxPirOopFrames		Counter64,
	rcTlsUniIpServiceStatsSilverRxGreenFrames		Counter64,
	rcTlsUniIpServiceStatsSilverRxYellowFrames		Counter64,
	rcTlsUniIpServiceStatsSilverRxRedFrames		Counter64,
	rcTlsUniIpServiceStatsStndRxCirFrames			Counter64,
	rcTlsUniIpServiceStatsStndRxCirOopFrames		Counter64,
	rcTlsUniIpServiceStatsStndRxEirFrames			Counter64,
	rcTlsUniIpServiceStatsStndRxEirOopFrames		Counter64,
	rcTlsUniIpServiceStatsStndRxEirDroppedFrames		Counter64,
	rcTlsUniIpServiceStatsStndRxPirFrames			Counter64,
	rcTlsUniIpServiceStatsStndRxPirOopFrames		Counter64,
	rcTlsUniIpServiceStatsStndRxGreenFrames		Counter64,
	rcTlsUniIpServiceStatsStndRxYellowFrames		Counter64,
	rcTlsUniIpServiceStatsStndRxRedFrames			Counter64,
	rcTlsUniIpServiceStatsMcastRxDroppedFrames		Counter64,
	rcTlsUniIpServiceStatsBcastUUcastRxTotalFrames		Counter64,
	rcTlsUniIpServiceStatsBcastUUcastRxDroppedFrames	Counter64,
	rcTlsUniIpServiceStatsPremTxCirOctets			Counter64,
	rcTlsUniIpServiceStatsPremTxCirOopOctets		Counter64,
	rcTlsUniIpServiceStatsPremTxEirOctets			Counter64,
	rcTlsUniIpServiceStatsPremTxEirOopOctets		Counter64,
	rcTlsUniIpServiceStatsPremTxEirDroppedOctets		Counter64,
	rcTlsUniIpServiceStatsPremTxPirOctets			Counter64,
	rcTlsUniIpServiceStatsPremTxPirOopOctets		Counter64,
	rcTlsUniIpServiceStatsPremTxGreenOctets		Counter64,
	rcTlsUniIpServiceStatsPremTxYellowOctets		Counter64,
	rcTlsUniIpServiceStatsPremTxRedOctets			Counter64,
	rcTlsUniIpServiceStatsGoldTxCirOctets			Counter64,
	rcTlsUniIpServiceStatsGoldTxCirOopOctets		Counter64,
	rcTlsUniIpServiceStatsGoldTxEirOctets			Counter64,
	rcTlsUniIpServiceStatsGoldTxEirOopOctets		Counter64,
	rcTlsUniIpServiceStatsGoldTxEirDroppedOctets		Counter64,
	rcTlsUniIpServiceStatsGoldTxPirOctets			Counter64,
	rcTlsUniIpServiceStatsGoldTxPirOopOctets		Counter64,
	rcTlsUniIpServiceStatsGoldTxGreenOctets		Counter64,
	rcTlsUniIpServiceStatsGoldTxYellowOctets		Counter64,
	rcTlsUniIpServiceStatsGoldTxRedOctets			Counter64,
	rcTlsUniIpServiceStatsSilverTxCirOctets			Counter64,
	rcTlsUniIpServiceStatsSilverTxCirOopOctets		Counter64,
	rcTlsUniIpServiceStatsSilverTxEirOctets			Counter64,
	rcTlsUniIpServiceStatsSilverTxEirOopOctets		Counter64,
	rcTlsUniIpServiceStatsSilverTxEirDroppedOctets		Counter64,
	rcTlsUniIpServiceStatsSilverTxPirOctets			Counter64,
	rcTlsUniIpServiceStatsSilverTxPirOopOctets		Counter64,
	rcTlsUniIpServiceStatsSilverTxGreenOctets		Counter64,
	rcTlsUniIpServiceStatsSilverTxYellowOctets		Counter64,
	rcTlsUniIpServiceStatsSilverTxRedOctets			Counter64,
	rcTlsUniIpServiceStatsStndTxCirOctets			Counter64,
	rcTlsUniIpServiceStatsStndTxCirOopOctets		Counter64,
	rcTlsUniIpServiceStatsStndTxEirOctets			Counter64,
	rcTlsUniIpServiceStatsStndTxEirOopOctets		Counter64,
	rcTlsUniIpServiceStatsStndTxEirDroppedOctets		Counter64,
	rcTlsUniIpServiceStatsStndTxPirOctets			Counter64,
	rcTlsUniIpServiceStatsStndTxPirOopOctets		Counter64,
	rcTlsUniIpServiceStatsStndTxGreenOctets		Counter64,
	rcTlsUniIpServiceStatsStndTxYellowOctets		Counter64,
	rcTlsUniIpServiceStatsStndTxRedOctets			Counter64,
	rcTlsUniIpServiceStatsMcastTxDroppedOctets		Counter64,
	rcTlsUniIpServiceStatsBcastUUcastTxTotalOctets		Counter64,
	rcTlsUniIpServiceStatsBcastUUcastTxDroppedOctets	Counter64,
	rcTlsUniIpServiceStatsPremTxCirFrames			Counter64,
	rcTlsUniIpServiceStatsPremTxCirOopFrames		Counter64,
	rcTlsUniIpServiceStatsPremTxEirFrames			Counter64,
	rcTlsUniIpServiceStatsPremTxEirOopFrames		Counter64,
	rcTlsUniIpServiceStatsPremTxEirDroppedFrames		Counter64,
	rcTlsUniIpServiceStatsPremTxPirFrames			Counter64,
	rcTlsUniIpServiceStatsPremTxPirOopFrames		Counter64,
	rcTlsUniIpServiceStatsPremTxGreenFrames		Counter64,
	rcTlsUniIpServiceStatsPremTxYellowFrames		Counter64,
	rcTlsUniIpServiceStatsPremTxRedFrames		Counter64,
	rcTlsUniIpServiceStatsGoldTxCirFrames			Counter64,
	rcTlsUniIpServiceStatsGoldTxCirOopFrames		Counter64,
	rcTlsUniIpServiceStatsGoldTxEirFrames			Counter64,
	rcTlsUniIpServiceStatsGoldTxEirOopFrames		Counter64,
	rcTlsUniIpServiceStatsGoldTxEirDroppedFrames		Counter64,
	rcTlsUniIpServiceStatsGoldTxPirFrames			Counter64,
	rcTlsUniIpServiceStatsGoldTxPirOopFrames		Counter64,
	rcTlsUniIpServiceStatsGoldTxGreenFrames		Counter64,
	rcTlsUniIpServiceStatsGoldTxYellowFrames		Counter64,
	rcTlsUniIpServiceStatsGoldTxRedFrames			Counter64,
	rcTlsUniIpServiceStatsSilverTxCirFrames			Counter64,
	rcTlsUniIpServiceStatsSilverTxCirOopFrames		Counter64,
	rcTlsUniIpServiceStatsSilverTxEirFrames			Counter64,
	rcTlsUniIpServiceStatsSilverTxEirOopFrames		Counter64,
	rcTlsUniIpServiceStatsSilverTxEirDroppedFrames		Counter64,
	rcTlsUniIpServiceStatsSilverTxPirFrames			Counter64,
	rcTlsUniIpServiceStatsSilverTxPirOopFrames		Counter64,
	rcTlsUniIpServiceStatsSilverTxGreenFrames		Counter64,
	rcTlsUniIpServiceStatsSilverTxYellowFrames		Counter64,
	rcTlsUniIpServiceStatsSilverTxRedFrames		Counter64,
	rcTlsUniIpServiceStatsStndTxCirFrames			Counter64,
	rcTlsUniIpServiceStatsStndTxCirOopFrames		Counter64,
	rcTlsUniIpServiceStatsStndTxEirFrames			Counter64,
	rcTlsUniIpServiceStatsStndTxEirOopFrames		Counter64,
	rcTlsUniIpServiceStatsStndTxEirDroppedFrames		Counter64,
	rcTlsUniIpServiceStatsStndTxPirFrames			Counter64,
	rcTlsUniIpServiceStatsStndTxPirOopFrames		Counter64,
	rcTlsUniIpServiceStatsStndTxGreenFrames		Counter64,
	rcTlsUniIpServiceStatsStndTxYellowFrames		Counter64,
	rcTlsUniIpServiceStatsStndTxRedFrames			Counter64,
	rcTlsUniIpServiceStatsMcastTxDroppedFrames		Counter64,
	rcTlsUniIpServiceStatsBcastUUcastTxTotalFrames		Counter64,
	rcTlsUniIpServiceStatsBcastUUcastTxDroppedFrames	Counter64,
	rcTlsUniIpServiceStatsDropClassRxDroppedOctets  	Counter64,
	rcTlsUniIpServiceStatsDropClassRxDroppedFrames  	Counter64,
	rcTlsUniIpServiceStatsDropClassTxDroppedOctets  		Counter64,
	rcTlsUniIpServiceStatsDropClassTxDroppedFrames  	Counter64
      }

rcTlsUniIpServiceStatsAddr OBJECT-TYPE
        SYNTAX        IpAddress
        MAX-ACCESS    not-accessible
        STATUS        current
        DESCRIPTION   "Tls Uni Ip Service Uni Address"
        ::= { rcTlsUniIpServiceStatsEntry 1}

rcTlsUniIpServiceStatsCustIpVlan OBJECT-TYPE
        SYNTAX        INTEGER (1..4096)
        MAX-ACCESS    not-accessible
        STATUS        current
        DESCRIPTION   "Customer IP Vlan for UNI IP Vlan mapping"
        ::= { rcTlsUniIpServiceStatsEntry 2 }
 
rcTlsUniIpServiceStatsPremRxOctets	OBJECT-TYPE
        SYNTAX        Counter64
        MAX-ACCESS    read-only
        STATUS        current
        DESCRIPTION  "Number of Premium ServiceStats Octets received from This Customer Ip Service."
        ::= { rcTlsUniIpServiceStatsEntry 3 } 

rcTlsUniIpServiceStatsPremRxDroppedOctets	OBJECT-TYPE
        SYNTAX        Counter64
        MAX-ACCESS    read-only
        STATUS        current
        DESCRIPTION  "Number of Premium ServiceStats Octets dropped from This Customer Ip Service."
        ::= { rcTlsUniIpServiceStatsEntry 4 } 
       
rcTlsUniIpServiceStatsGoldRxOctets	OBJECT-TYPE
        SYNTAX        Counter64
        MAX-ACCESS    read-only
        STATUS        current
        DESCRIPTION  "Number of Gold ServiceStats Octets received from This Customer Ip Service."
        ::= { rcTlsUniIpServiceStatsEntry 5 } 

rcTlsUniIpServiceStatsGoldRxDroppedOctets	OBJECT-TYPE
        SYNTAX        Counter64
        MAX-ACCESS    read-only
        STATUS        current
        DESCRIPTION  "Number of Gold ServiceStats Octets dropped from This Customer Ip Service."
        ::= { rcTlsUniIpServiceStatsEntry 6 } 
       
rcTlsUniIpServiceStatsSilverRxOctets	OBJECT-TYPE
        SYNTAX        Counter64
        MAX-ACCESS    read-only
        STATUS        current
        DESCRIPTION  "Number of Silver ServiceStats Octets received from This Customer Ip Service."
        ::= { rcTlsUniIpServiceStatsEntry 7 } 

rcTlsUniIpServiceStatsSilverRxDroppedOctets	OBJECT-TYPE
        SYNTAX        Counter64
        MAX-ACCESS    read-only
        STATUS        current
        DESCRIPTION  "Number of Silver ServiceStats Octets dropped from This Customer Ip Service."
        ::= { rcTlsUniIpServiceStatsEntry 8 } 
       
rcTlsUniIpServiceStatsStndRxOctets	OBJECT-TYPE
        SYNTAX        Counter64
        MAX-ACCESS    read-only
        STATUS        current
        DESCRIPTION  "Number of Standard (Best Effort) ServiceStats Octets received from This Customer Ip Service."
        ::= { rcTlsUniIpServiceStatsEntry 9 } 

rcTlsUniIpServiceStatsStndRxDroppedOctets	OBJECT-TYPE
        SYNTAX        Counter64
        MAX-ACCESS    read-only
        STATUS        current
        DESCRIPTION  "Number of Standard(BestEffort) ServiceStats Octets dropped from this Customer Ip Service."
        ::= { rcTlsUniIpServiceStatsEntry 10 } 
       
rcTlsUniIpServiceStatsPremTxOctets	OBJECT-TYPE
        SYNTAX        Counter64
        MAX-ACCESS    read-only
        STATUS        current
        DESCRIPTION  "Number of Premium ServiceStats Octets sent to his Customer Ip Service."
        ::= { rcTlsUniIpServiceStatsEntry 11 } 

rcTlsUniIpServiceStatsGoldTxOctets	OBJECT-TYPE
        SYNTAX        Counter64
        MAX-ACCESS    read-only
        STATUS        current
        DESCRIPTION  "Number of Gold ServiceStats Octets sent to his Customer Ip Service."
        ::= { rcTlsUniIpServiceStatsEntry 12 } 

rcTlsUniIpServiceStatsSilverTxOctets	OBJECT-TYPE
        SYNTAX        Counter64
        MAX-ACCESS    read-only
        STATUS        current
        DESCRIPTION  "Number of Silver ServiceStats Octets sent to his Customer Ip Service."
        ::= { rcTlsUniIpServiceStatsEntry 13 } 

rcTlsUniIpServiceStatsStndTxOctets	OBJECT-TYPE
        SYNTAX        Counter64
        MAX-ACCESS    read-only
        STATUS        current
        DESCRIPTION  "Number of Standard ServiceStats Octets sent to his Customer Ip Service."
        ::= { rcTlsUniIpServiceStatsEntry 14 } 
		

rcTlsUniIpServiceStatsPremTxMcastOctets	OBJECT-TYPE
        SYNTAX        Counter64
        MAX-ACCESS    read-only
        STATUS        current
        DESCRIPTION  "Number of Premium ServiceStats Multicast sent to his Customer Ip Service."
        ::= { rcTlsUniIpServiceStatsEntry 15 } 

rcTlsUniIpServiceStatsGoldTxMcastOctets	OBJECT-TYPE
        SYNTAX        Counter64
        MAX-ACCESS    read-only
        STATUS        current
        DESCRIPTION  "Number of GoldServiceStats Multicast sent to his Customer Ip Service."
        ::= { rcTlsUniIpServiceStatsEntry 16 } 
		
rcTlsUniIpServiceStatsSilverTxMcastOctets	OBJECT-TYPE
        SYNTAX        Counter64
        MAX-ACCESS    read-only
        STATUS        current
        DESCRIPTION  "Number of SilverServiceStats Multicast sent to his Customer Ip Service."
        ::= { rcTlsUniIpServiceStatsEntry 17 } 

rcTlsUniIpServiceStatsStndTxMcastOctets	OBJECT-TYPE
        SYNTAX        Counter64
        MAX-ACCESS    read-only
        STATUS        current 
        DESCRIPTION  "Number of Premium ServiceStats Multicast sent to his Customer Ip Service."
        ::= { rcTlsUniIpServiceStatsEntry 18     } 

rcTlsUniIpServiceStatsClear      OBJECT-TYPE
        SYNTAX        TruthValue
        MAX-ACCESS    read-write
        STATUS        current
        DESCRIPTION   "Clear statistic."
        ::= { rcTlsUniIpServiceStatsEntry 19 }

rcTlsUniIpServiceStatsPremCongestionDropOctets	OBJECT-TYPE
        SYNTAX        Counter64
        MAX-ACCESS    read-only
        STATUS        current
        DESCRIPTION  "Number of Prem ServiceStats Octets congestion drop"
        ::= { rcTlsUniIpServiceStatsEntry 20 } 
       
rcTlsUniIpServiceStatsGoldCongestionDropOctets	OBJECT-TYPE
        SYNTAX        Counter64
        MAX-ACCESS    read-only
        STATUS        current
        DESCRIPTION  "Number of Gold ServiceStats Octets congestion drop"
        ::= { rcTlsUniIpServiceStatsEntry 21 } 

rcTlsUniIpServiceStatsSilverCongestionDropOctets	OBJECT-TYPE
        SYNTAX        Counter64
        MAX-ACCESS    read-only
        STATUS        current
        DESCRIPTION  "Number of Silver ServiceStats Octets congestion drop"
        ::= { rcTlsUniIpServiceStatsEntry 22 } 

rcTlsUniIpServiceStatsStndCongestionDropOctets	OBJECT-TYPE
        SYNTAX        Counter64
        MAX-ACCESS    read-only
        STATUS        current
        DESCRIPTION  "Number of Standard ServiceStats Octets congestion drop"
        ::= { rcTlsUniIpServiceStatsEntry 23 }

rcTlsUniIpServiceStatsPremCirDroppedOctets	OBJECT-TYPE
        SYNTAX        Counter64
        MAX-ACCESS    read-only
        STATUS        current
        DESCRIPTION  "Number of Prem ServiceStats Octets CIR drop"
        ::= { rcTlsUniIpServiceStatsEntry 24 }

rcTlsUniIpServiceStatsPremPirDroppedOctets	OBJECT-TYPE
        SYNTAX        Counter64
        MAX-ACCESS    read-only
        STATUS        current
        DESCRIPTION  "Number of Prem ServiceStats Octets PIR drop"
        ::= { rcTlsUniIpServiceStatsEntry 25 }
  
rcTlsUniIpServiceStatsGoldCirDroppedOctets	OBJECT-TYPE
        SYNTAX        Counter64
        MAX-ACCESS    read-only
        STATUS        current
        DESCRIPTION  "Number of Gold ServiceStats Octets CIR drop"
        ::= { rcTlsUniIpServiceStatsEntry 26 }

rcTlsUniIpServiceStatsGoldPirDroppedOctets	OBJECT-TYPE
        SYNTAX        Counter64
        MAX-ACCESS    read-only
        STATUS        current
        DESCRIPTION  "Number of Gold ServiceStats Octets PIR drop"
        ::= { rcTlsUniIpServiceStatsEntry 27 }

rcTlsUniIpServiceStatsSilverCirDroppedOctets	OBJECT-TYPE
        SYNTAX        Counter64
        MAX-ACCESS    read-only
        STATUS        current
        DESCRIPTION  "Number of Silver ServiceStats Octets CIR drop"
        ::= { rcTlsUniIpServiceStatsEntry 28 }

rcTlsUniIpServiceStatsSilverPirDroppedOctets	OBJECT-TYPE
        SYNTAX        Counter64
        MAX-ACCESS    read-only
        STATUS        current
        DESCRIPTION  "Number of Silver ServiceStats Octets PIR drop"
        ::= { rcTlsUniIpServiceStatsEntry 29 }

rcTlsUniIpServiceStatsStndCirDroppedOctets	OBJECT-TYPE
        SYNTAX        Counter64
        MAX-ACCESS    read-only
        STATUS        current
        DESCRIPTION  "Number of Standard ServiceStats Octets CIR drop"
        ::= { rcTlsUniIpServiceStatsEntry 30 }  

rcTlsUniIpServiceStatsStndPirDroppedOctets	OBJECT-TYPE
        SYNTAX        Counter64
        MAX-ACCESS    read-only
        STATUS        current
        DESCRIPTION  "Number of Standard ServiceStats Octets PIR drop"
        ::= { rcTlsUniIpServiceStatsEntry 31 } 
 
rcTlsUniIpServiceStatsName OBJECT-TYPE
        SYNTAX        DisplayString (SIZE (0..30)) 
        MAX-ACCESS    read-only
        STATUS        current
        DESCRIPTION   "Name of UNI IP Service Vlan Entry. By default, It is 
		       VLAN-<uni id>-<cust ip vlan>"
        ::= { rcTlsUniIpServiceStatsEntry 32 }

rcTlsUniIpServiceStatsPremTxDroppedOctets	OBJECT-TYPE
        SYNTAX        Counter64
        MAX-ACCESS    read-only
        STATUS        current
        DESCRIPTION  "Tx Number of Premium ServiceStats Octets dropped from This Customer Ip Service."
        ::= { rcTlsUniIpServiceStatsEntry 33 } 

rcTlsUniIpServiceStatsGoldTxDroppedOctets	OBJECT-TYPE
        SYNTAX        Counter64
        MAX-ACCESS    read-only
        STATUS        current
        DESCRIPTION  "Tx Number of Gold ServiceStats Octets dropped from This Customer Ip Service."
        ::= { rcTlsUniIpServiceStatsEntry 34 } 
       
rcTlsUniIpServiceStatsSilverTxDroppedOctets	OBJECT-TYPE
        SYNTAX        Counter64
        MAX-ACCESS    read-only
        STATUS        current
        DESCRIPTION  "Tx Number of Silver ServiceStats Octets dropped from This Customer Ip Service."
        ::= { rcTlsUniIpServiceStatsEntry 35 } 
       
rcTlsUniIpServiceStatsStndTxDroppedOctets	OBJECT-TYPE
        SYNTAX        Counter64
        MAX-ACCESS    read-only
        STATUS        current
        DESCRIPTION  "Tx Number of Standard(BestEffort) ServiceStats Octets dropped from this Customer Ip Service."
        ::= { rcTlsUniIpServiceStatsEntry 36 } 

rcTlsUniIpServiceStatsPremTxCongestionDropOctets	OBJECT-TYPE
        SYNTAX        Counter64
        MAX-ACCESS    read-only
        STATUS        current
        DESCRIPTION  "Tx Number of Prem ServiceStats Octets congestion drop"
        ::= { rcTlsUniIpServiceStatsEntry 37 } 
       
rcTlsUniIpServiceStatsGoldTxCongestionDropOctets	OBJECT-TYPE
        SYNTAX        Counter64
        MAX-ACCESS    read-only
        STATUS        current
        DESCRIPTION  "Tx Number of Gold ServiceStats Octets congestion drop"
        ::= { rcTlsUniIpServiceStatsEntry 38 } 

rcTlsUniIpServiceStatsSilverTxCongestionDropOctets	OBJECT-TYPE
        SYNTAX        Counter64
        MAX-ACCESS    read-only
        STATUS        current
        DESCRIPTION  "Tx Number of Silver ServiceStats Octets congestion drop"
        ::= { rcTlsUniIpServiceStatsEntry 39 } 

rcTlsUniIpServiceStatsStndTxCongestionDropOctets	OBJECT-TYPE
        SYNTAX        Counter64
        MAX-ACCESS    read-only
        STATUS        current
        DESCRIPTION  "Tx Number of Standard ServiceStats Octets congestion drop"
        ::= { rcTlsUniIpServiceStatsEntry 40 }

rcTlsUniIpServiceStatsPremTxCirDroppedOctets	OBJECT-TYPE
        SYNTAX        Counter64
        MAX-ACCESS    read-only
        STATUS        current
        DESCRIPTION  "Tx Number of Prem ServiceStats Octets CIR drop"
        ::= { rcTlsUniIpServiceStatsEntry 41 }

rcTlsUniIpServiceStatsPremTxPirDroppedOctets	OBJECT-TYPE
        SYNTAX        Counter64
        MAX-ACCESS    read-only
        STATUS        current
        DESCRIPTION  "Tx Number of Prem ServiceStats Octets PIR drop"
        ::= { rcTlsUniIpServiceStatsEntry 42 }
  
rcTlsUniIpServiceStatsGoldTxCirDroppedOctets	OBJECT-TYPE
        SYNTAX        Counter64
        MAX-ACCESS    read-only
        STATUS        current
        DESCRIPTION  "Tx Number of Gold ServiceStats Octets CIR drop"
        ::= { rcTlsUniIpServiceStatsEntry 43 }

rcTlsUniIpServiceStatsGoldTxPirDroppedOctets	OBJECT-TYPE
        SYNTAX        Counter64
        MAX-ACCESS    read-only
        STATUS        current
        DESCRIPTION  "Tx Number of Gold ServiceStats Octets PIR drop"
        ::= { rcTlsUniIpServiceStatsEntry 44 }

rcTlsUniIpServiceStatsSilverTxCirDroppedOctets	OBJECT-TYPE
        SYNTAX        Counter64
        MAX-ACCESS    read-only
        STATUS        current
        DESCRIPTION  "Tx Number of Silver ServiceStats Octets CIR drop"
        ::= { rcTlsUniIpServiceStatsEntry 45 }

rcTlsUniIpServiceStatsSilverTxPirDroppedOctets	OBJECT-TYPE
        SYNTAX        Counter64
        MAX-ACCESS    read-only
        STATUS        current
        DESCRIPTION  "Tx Number of Silver ServiceStats Octets PIR drop"
        ::= { rcTlsUniIpServiceStatsEntry 46 }

rcTlsUniIpServiceStatsStndTxCirDroppedOctets	OBJECT-TYPE
        SYNTAX        Counter64
        MAX-ACCESS    read-only
        STATUS        current
        DESCRIPTION  "Tx Number of Standard ServiceStats Octets CIR drop"
        ::= { rcTlsUniIpServiceStatsEntry 47 }  

rcTlsUniIpServiceStatsStndTxPirDroppedOctets	OBJECT-TYPE
        SYNTAX        Counter64
        MAX-ACCESS    read-only
        STATUS        current
        DESCRIPTION  "TX Number of Standard ServiceStats Octets PIR drop"
        ::= { rcTlsUniIpServiceStatsEntry 48 }
 
rcTlsUniIpServiceStatsRxMcastTotalOctets	OBJECT-TYPE
        SYNTAX        Counter64
        MAX-ACCESS    read-only
        STATUS        current
        DESCRIPTION  "Rx Total Number of Mcast Octets"
        ::= { rcTlsUniIpServiceStatsEntry 49 }
 
rcTlsUniIpServiceStatsTxMcastTotalOctets	OBJECT-TYPE
        SYNTAX        Counter64
        MAX-ACCESS    read-only
        STATUS        current
        DESCRIPTION  "TX total Number of Mcast Octets"
        ::= { rcTlsUniIpServiceStatsEntry 50 } 

rcTlsUniIpServiceStatsPremRxMcastDroppedOctets	OBJECT-TYPE
        SYNTAX        Counter64
        MAX-ACCESS    read-only
        STATUS        current
        DESCRIPTION  "Number of Premium Service Rx Mcast Octets dropped from 
		      This Customer Ip Service."
        ::= { rcTlsUniIpServiceStatsEntry 51 } 

rcTlsUniIpServiceStatsGoldRxMcastDroppedOctets	OBJECT-TYPE
        SYNTAX        Counter64
        MAX-ACCESS    read-only
        STATUS        current
        DESCRIPTION  "Number of Gold Service Rx Mcast Octets dropped from 
		      This Customer Ip Service."
        ::= { rcTlsUniIpServiceStatsEntry 52 } 

rcTlsUniIpServiceStatsSilverRxMcastDroppedOctets	OBJECT-TYPE
        SYNTAX        Counter64
        MAX-ACCESS    read-only
        STATUS        current
        DESCRIPTION  "Number of Silver Service Rx Mcast Octets dropped from 
		      This Customer Ip Service."
        ::= { rcTlsUniIpServiceStatsEntry 53 } 
                            
rcTlsUniIpServiceStatsStndRxMcastDroppedOctets	OBJECT-TYPE
        SYNTAX        Counter64
        MAX-ACCESS    read-only
        STATUS        current
        DESCRIPTION  "Number of Standard Service Rx Mcast Octets dropped from 
		      This Customer Ip Service."
        ::= { rcTlsUniIpServiceStatsEntry 54 } 

rcTlsUniIpServiceStatsPremRxFrames	OBJECT-TYPE
        SYNTAX        Counter64
        MAX-ACCESS    read-only
        STATUS        current
        DESCRIPTION  "Number of Premium ServiceStats Frames received from This Customer Ip Service."
        ::= { rcTlsUniIpServiceStatsEntry 55 }

rcTlsUniIpServiceStatsPremRxDroppedFrames	OBJECT-TYPE
        SYNTAX        Counter64
        MAX-ACCESS    read-only
        STATUS        current
        DESCRIPTION  "Number of Premium ServiceStats Frames dropped from This Customer Ip Service."
        ::= { rcTlsUniIpServiceStatsEntry 56 }

rcTlsUniIpServiceStatsGoldRxFrames	OBJECT-TYPE
        SYNTAX        Counter64
        MAX-ACCESS    read-only
        STATUS        current
        DESCRIPTION  "Number of Gold ServiceStats Frames received from This Customer Ip Service."
        ::= { rcTlsUniIpServiceStatsEntry 57 }

rcTlsUniIpServiceStatsGoldRxDroppedFrames	OBJECT-TYPE
        SYNTAX        Counter64
        MAX-ACCESS    read-only
        STATUS        current
        DESCRIPTION  "Number of Gold ServiceStats Frames dropped from This Customer Ip Service."
        ::= { rcTlsUniIpServiceStatsEntry 58 }

rcTlsUniIpServiceStatsSilverRxFrames	OBJECT-TYPE
        SYNTAX        Counter64
        MAX-ACCESS    read-only
        STATUS        current
        DESCRIPTION  "Number of Silver ServiceStats Frames received from This Customer Ip Service."
        ::= { rcTlsUniIpServiceStatsEntry 59 }

rcTlsUniIpServiceStatsSilverRxDroppedFrames	OBJECT-TYPE
        SYNTAX        Counter64
        MAX-ACCESS    read-only
        STATUS        current
        DESCRIPTION  "Number of Silver ServiceStats Frames dropped from This Customer Ip Service."
        ::= { rcTlsUniIpServiceStatsEntry 60 }

rcTlsUniIpServiceStatsStndRxFrames	OBJECT-TYPE
        SYNTAX        Counter64
        MAX-ACCESS    read-only
        STATUS        current
        DESCRIPTION  "Number of Standard (Best Effort) ServiceStats Frames received from This Customer Ip Service."
        ::= { rcTlsUniIpServiceStatsEntry 61 }

rcTlsUniIpServiceStatsStndRxDroppedFrames	OBJECT-TYPE
        SYNTAX        Counter64
        MAX-ACCESS    read-only
        STATUS        current
        DESCRIPTION  "Number of Standard(BestEffort) ServiceStats Frames dropped from this Customer Ip Service."
        ::= { rcTlsUniIpServiceStatsEntry 62 }

rcTlsUniIpServiceStatsPremTxFrames	OBJECT-TYPE
        SYNTAX        Counter64
        MAX-ACCESS    read-only
        STATUS        current
        DESCRIPTION  "Number of Premium ServiceStats Frames sent to his Customer Ip Service."
        ::= { rcTlsUniIpServiceStatsEntry 63 }

rcTlsUniIpServiceStatsGoldTxFrames	OBJECT-TYPE
        SYNTAX        Counter64
        MAX-ACCESS    read-only
        STATUS        current
        DESCRIPTION  "Number of Gold ServiceStats Frames sent to his Customer Ip Service."
        ::= { rcTlsUniIpServiceStatsEntry 64 }

rcTlsUniIpServiceStatsSilverTxFrames	OBJECT-TYPE
        SYNTAX        Counter64
        MAX-ACCESS    read-only
        STATUS        current
        DESCRIPTION  "Number of Silver ServiceStats Frames sent to his Customer Ip Service."
        ::= { rcTlsUniIpServiceStatsEntry 65 }

rcTlsUniIpServiceStatsStndTxFrames	OBJECT-TYPE
        SYNTAX        Counter64
        MAX-ACCESS    read-only
        STATUS        current
        DESCRIPTION  "Number of Standard ServiceStats Frames sent to his Customer Ip Service."
        ::= { rcTlsUniIpServiceStatsEntry 66 }

rcTlsUniIpServiceStatsPremTxMcastFrames	OBJECT-TYPE
        SYNTAX        Counter64
        MAX-ACCESS    read-only
        STATUS        current
        DESCRIPTION  "Number of Premium ServiceStats Multicast sent to his Customer Ip Service."
        ::= { rcTlsUniIpServiceStatsEntry 67 }

rcTlsUniIpServiceStatsGoldTxMcastFrames	OBJECT-TYPE
        SYNTAX        Counter64
        MAX-ACCESS    read-only
        STATUS        current
        DESCRIPTION  "Number of GoldServiceStats Multicast sent to his Customer Ip Service."
        ::= { rcTlsUniIpServiceStatsEntry 68 }

rcTlsUniIpServiceStatsSilverTxMcastFrames	OBJECT-TYPE
        SYNTAX        Counter64
        MAX-ACCESS    read-only
        STATUS        current
        DESCRIPTION  "Number of SilverServiceStats Multicast sent to his Customer Ip Service."
        ::= { rcTlsUniIpServiceStatsEntry 69 }

rcTlsUniIpServiceStatsStndTxMcastFrames	OBJECT-TYPE
        SYNTAX        Counter64
        MAX-ACCESS    read-only
        STATUS        current
        DESCRIPTION  "Number of Premium ServiceStats Multicast sent to his Customer Ip Service."
        ::= { rcTlsUniIpServiceStatsEntry 70 }

rcTlsUniIpServiceStatsPremCongestionDropFrames	OBJECT-TYPE
        SYNTAX        Counter64
        MAX-ACCESS    read-only
        STATUS        current
        DESCRIPTION  "Number of Prem ServiceStats Frames congestion drop"
        ::= { rcTlsUniIpServiceStatsEntry 71 }

rcTlsUniIpServiceStatsGoldCongestionDropFrames	OBJECT-TYPE
        SYNTAX        Counter64
        MAX-ACCESS    read-only
        STATUS        current
        DESCRIPTION  "Number of Gold ServiceStats Frames congestion drop"
        ::= { rcTlsUniIpServiceStatsEntry 72 }

rcTlsUniIpServiceStatsSilverCongestionDropFrames	OBJECT-TYPE
        SYNTAX        Counter64
        MAX-ACCESS    read-only
        STATUS        current
        DESCRIPTION  "Number of Silver ServiceStats Frames congestion drop"
        ::= { rcTlsUniIpServiceStatsEntry 73 }

rcTlsUniIpServiceStatsStndCongestionDropFrames	OBJECT-TYPE
        SYNTAX        Counter64
        MAX-ACCESS    read-only
        STATUS        current
        DESCRIPTION  "Number of Standard ServiceStats Frames congestion drop"
        ::= { rcTlsUniIpServiceStatsEntry 74 }

rcTlsUniIpServiceStatsPremCirDroppedFrames	OBJECT-TYPE
        SYNTAX        Counter64
        MAX-ACCESS    read-only
        STATUS        current
        DESCRIPTION  "Number of Prem ServiceStats Frames CIR drop"
        ::= { rcTlsUniIpServiceStatsEntry 75 }

rcTlsUniIpServiceStatsPremPirDroppedFrames	OBJECT-TYPE
        SYNTAX        Counter64
        MAX-ACCESS    read-only
        STATUS        current
        DESCRIPTION  "Number of Prem ServiceStats Frames PIR drop"
        ::= { rcTlsUniIpServiceStatsEntry 76 }

rcTlsUniIpServiceStatsGoldCirDroppedFrames	OBJECT-TYPE
        SYNTAX        Counter64
        MAX-ACCESS    read-only
        STATUS        current
        DESCRIPTION  "Number of Gold ServiceStats Frames CIR drop"
        ::= { rcTlsUniIpServiceStatsEntry 77 }

rcTlsUniIpServiceStatsGoldPirDroppedFrames	OBJECT-TYPE
        SYNTAX        Counter64
        MAX-ACCESS    read-only
        STATUS        current
        DESCRIPTION  "Number of Gold ServiceStats Frames PIR drop"
        ::= { rcTlsUniIpServiceStatsEntry 78 }

rcTlsUniIpServiceStatsSilverCirDroppedFrames	OBJECT-TYPE
        SYNTAX        Counter64
        MAX-ACCESS    read-only
        STATUS        current
        DESCRIPTION  "Number of Silver ServiceStats Frames CIR drop"
        ::= { rcTlsUniIpServiceStatsEntry 79 }

rcTlsUniIpServiceStatsSilverPirDroppedFrames	OBJECT-TYPE
        SYNTAX        Counter64
        MAX-ACCESS    read-only
        STATUS        current
        DESCRIPTION  "Number of Silver ServiceStats Frames PIR drop"
        ::= { rcTlsUniIpServiceStatsEntry 80 }

rcTlsUniIpServiceStatsStndCirDroppedFrames	OBJECT-TYPE
        SYNTAX        Counter64
        MAX-ACCESS    read-only
        STATUS        current
        DESCRIPTION  "Number of Standard ServiceStats Frames CIR drop"
        ::= { rcTlsUniIpServiceStatsEntry 81 }

rcTlsUniIpServiceStatsStndPirDroppedFrames	OBJECT-TYPE
        SYNTAX        Counter64
        MAX-ACCESS    read-only
        STATUS        current
        DESCRIPTION  "Number of Standard ServiceStats Frames PIR drop"
        ::= { rcTlsUniIpServiceStatsEntry 82 }

rcTlsUniIpServiceStatsPremTxDroppedFrames	OBJECT-TYPE
        SYNTAX        Counter64
        MAX-ACCESS    read-only
        STATUS        current
        DESCRIPTION  "Tx Number of Premium ServiceStats Frames dropped from This Customer Ip Service."
        ::= { rcTlsUniIpServiceStatsEntry 83 }

rcTlsUniIpServiceStatsGoldTxDroppedFrames	OBJECT-TYPE
        SYNTAX        Counter64
        MAX-ACCESS    read-only
        STATUS        current
        DESCRIPTION  "Tx Number of Gold ServiceStats Frames dropped from This Customer Ip Service."
        ::= { rcTlsUniIpServiceStatsEntry 84 }

rcTlsUniIpServiceStatsSilverTxDroppedFrames	OBJECT-TYPE
        SYNTAX        Counter64
        MAX-ACCESS    read-only
        STATUS        current
        DESCRIPTION  "Tx Number of Silver ServiceStats Frames dropped from This Customer Ip Service."
        ::= { rcTlsUniIpServiceStatsEntry 85 }

rcTlsUniIpServiceStatsStndTxDroppedFrames	OBJECT-TYPE
        SYNTAX        Counter64
        MAX-ACCESS    read-only
        STATUS        current
        DESCRIPTION  "Tx Number of Standard(BestEffort) ServiceStats Frames dropped from this Customer Ip Service."
        ::= { rcTlsUniIpServiceStatsEntry 86 }

rcTlsUniIpServiceStatsPremTxCongestionDropFrames	OBJECT-TYPE
        SYNTAX        Counter64
        MAX-ACCESS    read-only
        STATUS        current
        DESCRIPTION  "Tx Number of Prem ServiceStats Frames congestion drop"
        ::= { rcTlsUniIpServiceStatsEntry 87 }

rcTlsUniIpServiceStatsGoldTxCongestionDropFrames	OBJECT-TYPE
        SYNTAX        Counter64
        MAX-ACCESS    read-only
        STATUS        current
        DESCRIPTION  "Tx Number of Gold ServiceStats Frames congestion drop"
        ::= { rcTlsUniIpServiceStatsEntry 88 }

rcTlsUniIpServiceStatsSilverTxCongestionDropFrames	OBJECT-TYPE
        SYNTAX        Counter64
        MAX-ACCESS    read-only
        STATUS        current
        DESCRIPTION  "Tx Number of Silver ServiceStats Frames congestion drop"
        ::= { rcTlsUniIpServiceStatsEntry 89 }

rcTlsUniIpServiceStatsStndTxCongestionDropFrames	OBJECT-TYPE
        SYNTAX        Counter64
        MAX-ACCESS    read-only
        STATUS        current
        DESCRIPTION  "Tx Number of Standard ServiceStats Frames congestion drop"
        ::= { rcTlsUniIpServiceStatsEntry 90 }

rcTlsUniIpServiceStatsPremTxCirDroppedFrames	OBJECT-TYPE
        SYNTAX        Counter64
        MAX-ACCESS    read-only
        STATUS        current
        DESCRIPTION  "Tx Number of Prem ServiceStats Frames CIR drop"
        ::= { rcTlsUniIpServiceStatsEntry 91 }

rcTlsUniIpServiceStatsPremTxPirDroppedFrames	OBJECT-TYPE
        SYNTAX        Counter64
        MAX-ACCESS    read-only
        STATUS        current
        DESCRIPTION  "Tx Number of Prem ServiceStats Frames PIR drop"
        ::= { rcTlsUniIpServiceStatsEntry 92 }

rcTlsUniIpServiceStatsGoldTxCirDroppedFrames	OBJECT-TYPE
        SYNTAX        Counter64
        MAX-ACCESS    read-only
        STATUS        current
        DESCRIPTION  "Tx Number of Gold ServiceStats Frames CIR drop"
        ::= { rcTlsUniIpServiceStatsEntry 93 }

rcTlsUniIpServiceStatsGoldTxPirDroppedFrames	OBJECT-TYPE
        SYNTAX        Counter64
        MAX-ACCESS    read-only
        STATUS        current
        DESCRIPTION  "Tx Number of Gold ServiceStats Frames PIR drop"
        ::= { rcTlsUniIpServiceStatsEntry 94 }

rcTlsUniIpServiceStatsSilverTxCirDroppedFrames	OBJECT-TYPE
        SYNTAX        Counter64
        MAX-ACCESS    read-only
        STATUS        current
        DESCRIPTION  "Tx Number of Silver ServiceStats Frames CIR drop"
        ::= { rcTlsUniIpServiceStatsEntry 95 }

rcTlsUniIpServiceStatsSilverTxPirDroppedFrames	OBJECT-TYPE
        SYNTAX        Counter64
        MAX-ACCESS    read-only
        STATUS        current
        DESCRIPTION  "Tx Number of Silver ServiceStats Frames PIR drop"
        ::= { rcTlsUniIpServiceStatsEntry 96 }

rcTlsUniIpServiceStatsStndTxCirDroppedFrames	OBJECT-TYPE
        SYNTAX        Counter64
        MAX-ACCESS    read-only
        STATUS        current
        DESCRIPTION  "Tx Number of Standard ServiceStats Frames CIR drop"
        ::= { rcTlsUniIpServiceStatsEntry 97 }

rcTlsUniIpServiceStatsStndTxPirDroppedFrames	OBJECT-TYPE
        SYNTAX        Counter64
        MAX-ACCESS    read-only
        STATUS        current
        DESCRIPTION  "TX Number of Standard ServiceStats Frames PIR drop"
        ::= { rcTlsUniIpServiceStatsEntry 98 }

rcTlsUniIpServiceStatsRxMcastTotalFrames	OBJECT-TYPE
        SYNTAX        Counter64
        MAX-ACCESS    read-only
        STATUS        current
        DESCRIPTION  "Rx Total Number of Mcast Frames"
        ::= { rcTlsUniIpServiceStatsEntry 99 }

rcTlsUniIpServiceStatsTxMcastTotalFrames	OBJECT-TYPE
        SYNTAX        Counter64
        MAX-ACCESS    read-only
        STATUS        current
        DESCRIPTION  "TX total Number of Mcast Frames"
        ::= { rcTlsUniIpServiceStatsEntry 100 }

rcTlsUniIpServiceStatsPremRxMcastDroppedFrames	OBJECT-TYPE
        SYNTAX        Counter64
        MAX-ACCESS    read-only
        STATUS        current
        DESCRIPTION  "Number of Premium Service Rx Mcast Frames dropped from
		      This Customer Ip Service."
        ::= { rcTlsUniIpServiceStatsEntry 101 }

rcTlsUniIpServiceStatsGoldRxMcastDroppedFrames	OBJECT-TYPE
        SYNTAX        Counter64
        MAX-ACCESS    read-only
        STATUS        current
        DESCRIPTION  "Number of Gold Service Rx Mcast Frames dropped from
		      This Customer Ip Service."
        ::= { rcTlsUniIpServiceStatsEntry 102 }

rcTlsUniIpServiceStatsSilverRxMcastDroppedFrames	OBJECT-TYPE
        SYNTAX        Counter64
        MAX-ACCESS    read-only
        STATUS        current
        DESCRIPTION  "Number of Silver Service Rx Mcast Frames dropped from
		      This Customer Ip Service."
        ::= { rcTlsUniIpServiceStatsEntry 103 }

rcTlsUniIpServiceStatsStndRxMcastDroppedFrames	OBJECT-TYPE
        SYNTAX        Counter64
        MAX-ACCESS    read-only
        STATUS        current
        DESCRIPTION  "Number of Standard Service Rx Mcast Frames dropped from
		      This Customer Ip Service."
        ::= { rcTlsUniIpServiceStatsEntry 104 }

rcTlsUniIpServiceStatsPremRxCirOctets     OBJECT-TYPE
        SYNTAX        Counter64
        MAX-ACCESS    read-only
        STATUS        current
        DESCRIPTION  "Number of Premium Service Rx CIR Octets received."
        ::= { rcTlsUniIpServiceStatsEntry 105 }

rcTlsUniIpServiceStatsPremRxCirOopOctets     OBJECT-TYPE
        SYNTAX        Counter64
        MAX-ACCESS    read-only
        STATUS        current
        DESCRIPTION  "Number of Premium Service Rx Octets received that 
		      were CIR OOP."
        ::= { rcTlsUniIpServiceStatsEntry 106 }

rcTlsUniIpServiceStatsPremRxEirOctets     OBJECT-TYPE
        SYNTAX        Counter64
        MAX-ACCESS    read-only
        STATUS        current
        DESCRIPTION  "Number of Premium Service Rx EIR Octets received."
        ::= { rcTlsUniIpServiceStatsEntry 107 }

rcTlsUniIpServiceStatsPremRxEirOopOctets     OBJECT-TYPE
        SYNTAX        Counter64
        MAX-ACCESS    read-only
        STATUS        current
        DESCRIPTION  "Number of Premium Service Rx Octets received that 
		      were EIR OOP."
        ::= { rcTlsUniIpServiceStatsEntry 108 }

rcTlsUniIpServiceStatsPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcTlsUniIpServiceStatsEntry 109 }

rcTlsUniIpServiceStatsPremRxPirOctets     OBJECT-TYPE
        SYNTAX        Counter64
        MAX-ACCESS    read-only
        STATUS        current
        DESCRIPTION  "Number of Premium Service Rx PIR Octets received."
        ::= { rcTlsUniIpServiceStatsEntry 110 }

rcTlsUniIpServiceStatsPremRxPirOopOctets     OBJECT-TYPE
        SYNTAX        Counter64
        MAX-ACCESS    read-only
        STATUS        current
        DESCRIPTION  "Number of Premium Service Rx Octets received that 
		      were PIR OOP."
        ::= { rcTlsUniIpServiceStatsEntry 111 }

rcTlsUniIpServiceStatsPremRxGreenOctets     OBJECT-TYPE
        SYNTAX        Counter64
        MAX-ACCESS    read-only
        STATUS        current
        DESCRIPTION  "Number of Premium Service Rx Octets received that 
		      were marked 'Green' by the policer."
        ::= { rcTlsUniIpServiceStatsEntry 112 }

rcTlsUniIpServiceStatsPremRxYellowOctets     OBJECT-TYPE
        SYNTAX        Counter64
        MAX-ACCESS    read-only
        STATUS        current
        DESCRIPTION  "Number of Premium Service Rx Octets received that 
		      were marked 'Yellow' by the policer."
        ::= { rcTlsUniIpServiceStatsEntry 113 }

rcTlsUniIpServiceStatsPremRxRedOctets     OBJECT-TYPE
        SYNTAX        Counter64
        MAX-ACCESS    read-only
        STATUS        current
        DESCRIPTION  "Number of Premium Service Rx Octets received that 
		      were marked 'Red' by the policer."
        ::= { rcTlsUniIpServiceStatsEntry 114 }

rcTlsUniIpServiceStatsGoldRxCirOctets     OBJECT-TYPE
        SYNTAX        Counter64
        MAX-ACCESS    read-only
        STATUS        current
        DESCRIPTION  "Number of Gold Service Rx CIR Octets received."
        ::= { rcTlsUniIpServiceStatsEntry 115 }

rcTlsUniIpServiceStatsGoldRxCirOopOctets     OBJECT-TYPE
        SYNTAX        Counter64
        MAX-ACCESS    read-only
        STATUS        current
        DESCRIPTION  "Number of Gold Service Rx Octets received that 
		      were CIR OOP."
        ::= { rcTlsUniIpServiceStatsEntry 116 }

rcTlsUniIpServiceStatsGoldRxEirOctets     OBJECT-TYPE
        SYNTAX        Counter64
        MAX-ACCESS    read-only
        STATUS        current
        DESCRIPTION  "Number of Gold Service Rx EIR Octets received."
        ::= { rcTlsUniIpServiceStatsEntry 117 }

rcTlsUniIpServiceStatsGoldRxEirOopOctets     OBJECT-TYPE
        SYNTAX        Counter64
        MAX-ACCESS    read-only
        STATUS        current
        DESCRIPTION  "Number of Gold Service Rx Octets received that 
		      were EIR OOP."
        ::= { rcTlsUniIpServiceStatsEntry 118 }

rcTlsUniIpServiceStatsGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcTlsUniIpServiceStatsEntry 119 }

rcTlsUniIpServiceStatsGoldRxPirOctets     OBJECT-TYPE
        SYNTAX        Counter64
        MAX-ACCESS    read-only
        STATUS        current
        DESCRIPTION  "Number of Gold Service Rx PIR Octets received."
        ::= { rcTlsUniIpServiceStatsEntry 120 }

rcTlsUniIpServiceStatsGoldRxPirOopOctets     OBJECT-TYPE
        SYNTAX        Counter64
        MAX-ACCESS    read-only
        STATUS        current
        DESCRIPTION  "Number of Gold Service Rx Octets received that 
		      were PIR OOP."
        ::= { rcTlsUniIpServiceStatsEntry 121 }

rcTlsUniIpServiceStatsGoldRxGreenOctets     OBJECT-TYPE
        SYNTAX        Counter64
        MAX-ACCESS    read-only
        STATUS        current
        DESCRIPTION  "Number of Gold Service Rx Octets received that 
		      were marked 'Green' by the policer."
        ::= { rcTlsUniIpServiceStatsEntry 122 }

rcTlsUniIpServiceStatsGoldRxYellowOctets     OBJECT-TYPE
        SYNTAX        Counter64
        MAX-ACCESS    read-only
        STATUS        current
        DESCRIPTION  "Number of Gold Service Rx Octets received that 
		      were marked 'Yellow' by the policer."
        ::= { rcTlsUniIpServiceStatsEntry 123 }

rcTlsUniIpServiceStatsGoldRxRedOctets     OBJECT-TYPE
        SYNTAX        Counter64
        MAX-ACCESS    read-only
        STATUS        current
        DESCRIPTION  "Number of Gold Service Rx Octets received that 
		      were marked 'Red' by the policer."
        ::= { rcTlsUniIpServiceStatsEntry 124 }

rcTlsUniIpServiceStatsSilverRxCirOctets     OBJECT-TYPE
        SYNTAX        Counter64
        MAX-ACCESS    read-only
        STATUS        current
        DESCRIPTION  "Number of Silver Service Rx CIR Octets received."
        ::= { rcTlsUniIpServiceStatsEntry 125 }

rcTlsUniIpServiceStatsSilverRxCirOopOctets     OBJECT-TYPE
        SYNTAX        Counter64
        MAX-ACCESS    read-only
        STATUS        current
        DESCRIPTION  "Number of Silver Service Rx Octets received that 
		      were CIR OOP."
        ::= { rcTlsUniIpServiceStatsEntry 126 }

rcTlsUniIpServiceStatsSilverRxEirOctets     OBJECT-TYPE
        SYNTAX        Counter64
        MAX-ACCESS    read-only
        STATUS        current
        DESCRIPTION  "Number of Silver Service Rx EIR Octets received."
        ::= { rcTlsUniIpServiceStatsEntry 127 }

rcTlsUniIpServiceStatsSilverRxEirOopOctets     OBJECT-TYPE
        SYNTAX        Counter64
        MAX-ACCESS    read-only
        STATUS        current
        DESCRIPTION  "Number of Silver Service Rx Octets received that 
		      were EIR OOP."
        ::= { rcTlsUniIpServiceStatsEntry 128 }

rcTlsUniIpServiceStatsSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcTlsUniIpServiceStatsEntry 129 }

rcTlsUniIpServiceStatsSilverRxPirOctets     OBJECT-TYPE
        SYNTAX        Counter64
        MAX-ACCESS    read-only
        STATUS        current
        DESCRIPTION  "Number of Silver Service Rx PIR Octets received."
        ::= { rcTlsUniIpServiceStatsEntry 130 }

rcTlsUniIpServiceStatsSilverRxPirOopOctets     OBJECT-TYPE
        SYNTAX        Counter64
        MAX-ACCESS    read-only
        STATUS        current
        DESCRIPTION  "Number of Silver Service Rx Octets received that 
		      were PIR OOP."
        ::= { rcTlsUniIpServiceStatsEntry 131 }

rcTlsUniIpServiceStatsSilverRxGreenOctets     OBJECT-TYPE
        SYNTAX        Counter64
        MAX-ACCESS    read-only
        STATUS        current
        DESCRIPTION  "Number of Silver Service Rx Octets received that 
		      were marked 'Green' by the policer."
        ::= { rcTlsUniIpServiceStatsEntry 132 }

rcTlsUniIpServiceStatsSilverRxYellowOctets     OBJECT-TYPE
        SYNTAX        Counter64
        MAX-ACCESS    read-only
        STATUS        current
        DESCRIPTION  "Number of Silver Service Rx Octets received that 
		      were marked 'Yellow' by the policer."
        ::= { rcTlsUniIpServiceStatsEntry 133 }

rcTlsUniIpServiceStatsSilverRxRedOctets     OBJECT-TYPE
        SYNTAX        Counter64
        MAX-ACCESS    read-only
        STATUS        current
        DESCRIPTION  "Number of Silver Service Rx Octets received that 
		      were marked 'Red' by the policer."
        ::= { rcTlsUniIpServiceStatsEntry 134 }

rcTlsUniIpServiceStatsStndRxCirOctets     OBJECT-TYPE
        SYNTAX        Counter64
        MAX-ACCESS    read-only
        STATUS        current
        DESCRIPTION  "Number of Standard Service Rx CIR Octets received."
        ::= { rcTlsUniIpServiceStatsEntry 135 }

rcTlsUniIpServiceStatsStndRxCirOopOctets     OBJECT-TYPE
        SYNTAX        Counter64
        MAX-ACCESS    read-only
        STATUS        current
        DESCRIPTION  "Number of Standard Service Rx Octets received that 
		      were CIR OOP."
        ::= { rcTlsUniIpServiceStatsEntry 136 }

rcTlsUniIpServiceStatsStndRxEirOctets     OBJECT-TYPE
        SYNTAX        Counter64
        MAX-ACCESS    read-only
        STATUS        current
        DESCRIPTION  "Number of Standard Service Rx EIR Octets received."
        ::= { rcTlsUniIpServiceStatsEntry 137 }

rcTlsUniIpServiceStatsStndRxEirOopOctets     OBJECT-TYPE
        SYNTAX        Counter64
        MAX-ACCESS    read-only
        STATUS        current
        DESCRIPTION  "Number of Standard Service Rx Octets received that 
		      were EIR OOP."
        ::= { rcTlsUniIpServiceStatsEntry 138 }

rcTlsUniIpServiceStatsStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcTlsUniIpServiceStatsEntry 139 }

rcTlsUniIpServiceStatsStndRxPirOctets     OBJECT-TYPE
        SYNTAX        Counter64
        MAX-ACCESS    read-only
        STATUS        current
        DESCRIPTION  "Number of Standard Service Rx PIR Octets received."
        ::= { rcTlsUniIpServiceStatsEntry 140 }

rcTlsUniIpServiceStatsStndRxPirOopOctets     OBJECT-TYPE
        SYNTAX        Counter64
        MAX-ACCESS    read-only
        STATUS        current
        DESCRIPTION  "Number of Standard Service Rx Octets received that 
		      were PIR OOP."
        ::= { rcTlsUniIpServiceStatsEntry 141 }

rcTlsUniIpServiceStatsStndRxGreenOctets     OBJECT-TYPE
        SYNTAX        Counter64
        MAX-ACCESS    read-only
        STATUS        current
        DESCRIPTION  "Number of Standard Service Rx Octets received that 
		      were marked 'Green' by the policer."
        ::= { rcTlsUniIpServiceStatsEntry 142 }

rcTlsUniIpServiceStatsStndRxYellowOctets     OBJECT-TYPE
        SYNTAX        Counter64
        MAX-ACCESS    read-only
        STATUS        current
        DESCRIPTION  "Number of Standard Service Rx Octets received that 
		      were marked 'Yellow' by the policer."
        ::= { rcTlsUniIpServiceStatsEntry 143 }

rcTlsUniIpServiceStatsStndRxRedOctets     OBJECT-TYPE
        SYNTAX        Counter64
        MAX-ACCESS    read-only
        STATUS        current
        DESCRIPTION  "Number of Standard Service Rx Octets received that 
		      were marked 'Red' by the policer."
        ::= { rcTlsUniIpServiceStatsEntry 144 }

rcTlsUniIpServiceStatsMcastRxDroppedOctets     OBJECT-TYPE
        SYNTAX        Counter64
        MAX-ACCESS    read-only
        STATUS        current
        DESCRIPTION  "Number of Multicast Rx Octets dropped."
        ::= { rcTlsUniIpServiceStatsEntry 145 }

rcTlsUniIpServiceStatsBcastUUcastRxTotalOctets     OBJECT-TYPE
        SYNTAX        Counter64
        MAX-ACCESS    read-only
        STATUS        current
        DESCRIPTION  "Number of Broadcast/Unknown Unicast Rx total Octets."
        ::= { rcTlsUniIpServiceStatsEntry 146 }

rcTlsUniIpServiceStatsBcastUUcastRxDroppedOctets     OBJECT-TYPE
        SYNTAX        Counter64
        MAX-ACCESS    read-only
        STATUS        current
        DESCRIPTION  "Number of Broadcast/Unknown Rx Octets dropped."
        ::= { rcTlsUniIpServiceStatsEntry 147 }

rcTlsUniIpServiceStatsPremRxCirFrames     OBJECT-TYPE
        SYNTAX        Counter64
        MAX-ACCESS    read-only
        STATUS        current
        DESCRIPTION  "Number of Premium Service Rx CIR Frames received."
        ::= { rcTlsUniIpServiceStatsEntry 148 }

rcTlsUniIpServiceStatsPremRxCirOopFrames     OBJECT-TYPE
        SYNTAX        Counter64
        MAX-ACCESS    read-only
        STATUS        current
        DESCRIPTION  "Number of Premium Service Rx Frames received that 
		      were CIR OOP."
        ::= { rcTlsUniIpServiceStatsEntry 149 }

rcTlsUniIpServiceStatsPremRxEirFrames     OBJECT-TYPE
        SYNTAX        Counter64
        MAX-ACCESS    read-only
        STATUS        current
        DESCRIPTION  "Number of Premium Service Rx EIR Frames received."
        ::= { rcTlsUniIpServiceStatsEntry 150 }

rcTlsUniIpServiceStatsPremRxEirOopFrames     OBJECT-TYPE
        SYNTAX        Counter64
        MAX-ACCESS    read-only
        STATUS        current
        DESCRIPTION  "Number of Premium Service Rx Frames received that 
		      were EIR OOP."
        ::= { rcTlsUniIpServiceStatsEntry 151 }

rcTlsUniIpServiceStatsPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcTlsUniIpServiceStatsEntry 152 }

rcTlsUniIpServiceStatsPremRxPirFrames     OBJECT-TYPE
        SYNTAX        Counter64
        MAX-ACCESS    read-only
        STATUS        current
        DESCRIPTION  "Number of Premium Service Rx PIR Frames received."
        ::= { rcTlsUniIpServiceStatsEntry 153 }

rcTlsUniIpServiceStatsPremRxPirOopFrames     OBJECT-TYPE
        SYNTAX        Counter64
        MAX-ACCESS    read-only
        STATUS        current
        DESCRIPTION  "Number of Premium Service Rx Frames received that 
		      were PIR OOP."
        ::= { rcTlsUniIpServiceStatsEntry 154 }

rcTlsUniIpServiceStatsPremRxGreenFrames     OBJECT-TYPE
        SYNTAX        Counter64
        MAX-ACCESS    read-only
        STATUS        current
        DESCRIPTION  "Number of Premium Service Rx Frames received that 
		      were marked 'Green' by the policer."
        ::= { rcTlsUniIpServiceStatsEntry 155 }

rcTlsUniIpServiceStatsPremRxYellowFrames     OBJECT-TYPE
        SYNTAX        Counter64
        MAX-ACCESS    read-only
        STATUS        current
        DESCRIPTION  "Number of Premium Service Rx Frames received that 
		      were marked 'Yellow' by the policer."
        ::= { rcTlsUniIpServiceStatsEntry 156 }

rcTlsUniIpServiceStatsPremRxRedFrames     OBJECT-TYPE
        SYNTAX        Counter64
        MAX-ACCESS    read-only
        STATUS        current
        DESCRIPTION  "Number of Premium Service Rx Frames received that 
		      were marked 'Red' by the policer."
        ::= { rcTlsUniIpServiceStatsEntry 157 }

rcTlsUniIpServiceStatsGoldRxCirFrames     OBJECT-TYPE
        SYNTAX        Counter64
        MAX-ACCESS    read-only
        STATUS        current
        DESCRIPTION  "Number of Gold Service Rx CIR Frames received."
        ::= { rcTlsUniIpServiceStatsEntry 158 }

rcTlsUniIpServiceStatsGoldRxCirOopFrames     OBJECT-TYPE
        SYNTAX        Counter64
        MAX-ACCESS    read-only
        STATUS        current
        DESCRIPTION  "Number of Gold Service Rx Frames received that 
		      were CIR OOP."
        ::= { rcTlsUniIpServiceStatsEntry 159 }

rcTlsUniIpServiceStatsGoldRxEirFrames     OBJECT-TYPE
        SYNTAX        Counter64
        MAX-ACCESS    read-only
        STATUS        current
        DESCRIPTION  "Number of Gold Service Rx EIR Frames received."
        ::= { rcTlsUniIpServiceStatsEntry 160 }

rcTlsUniIpServiceStatsGoldRxEirOopFrames     OBJECT-TYPE
        SYNTAX        Counter64
        MAX-ACCESS    read-only
        STATUS        current
        DESCRIPTION  "Number of Gold Service Rx Frames received that 
		      were EIR OOP."
        ::= { rcTlsUniIpServiceStatsEntry 161 }

rcTlsUniIpServiceStatsGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcTlsUniIpServiceStatsEntry 162 }

rcTlsUniIpServiceStatsGoldRxPirFrames     OBJECT-TYPE
        SYNTAX        Counter64
        MAX-ACCESS    read-only
        STATUS        current
        DESCRIPTION  "Number of Gold Service Rx PIR Frames received."
        ::= { rcTlsUniIpServiceStatsEntry 163 }

rcTlsUniIpServiceStatsGoldRxPirOopFrames     OBJECT-TYPE
        SYNTAX        Counter64
        MAX-ACCESS    read-only
        STATUS        current
        DESCRIPTION  "Number of Gold Service Rx Frames received that 
		      were PIR OOP."
        ::= { rcTlsUniIpServiceStatsEntry 164 }

rcTlsUniIpServiceStatsGoldRxGreenFrames     OBJECT-TYPE
        SYNTAX        Counter64
        MAX-ACCESS    read-only
        STATUS        current
        DESCRIPTION  "Number of Gold Service Rx Frames received that 
		      were marked 'Green' by the policer."
        ::= { rcTlsUniIpServiceStatsEntry 165 }

rcTlsUniIpServiceStatsGoldRxYellowFrames     OBJECT-TYPE
        SYNTAX        Counter64
        MAX-ACCESS    read-only
        STATUS        current
        DESCRIPTION  "Number of Gold Service Rx Frames received that 
		      were marked 'Yellow' by the policer."
        ::= { rcTlsUniIpServiceStatsEntry 166 }

rcTlsUniIpServiceStatsGoldRxRedFrames     OBJECT-TYPE
        SYNTAX        Counter64
        MAX-ACCESS    read-only
        STATUS        current
        DESCRIPTION  "Number of Gold Service Rx Frames received that 
		      were marked 'Red' by the policer."
        ::= { rcTlsUniIpServiceStatsEntry 167 }

rcTlsUniIpServiceStatsSilverRxCirFrames     OBJECT-TYPE
        SYNTAX        Counter64
        MAX-ACCESS    read-only
        STATUS        current
        DESCRIPTION  "Number of Silver Service Rx CIR Frames received."
        ::= { rcTlsUniIpServiceStatsEntry 168 }

rcTlsUniIpServiceStatsSilverRxCirOopFrames     OBJECT-TYPE
        SYNTAX        Counter64
        MAX-ACCESS    read-only
        STATUS        current
        DESCRIPTION  "Number of Silver Service Rx Frames received that 
		      were CIR OOP."
        ::= { rcTlsUniIpServiceStatsEntry 169 }

rcTlsUniIpServiceStatsSilverRxEirFrames     OBJECT-TYPE
        SYNTAX        Counter64
        MAX-ACCESS    read-only
        STATUS        current
        DESCRIPTION  "Number of Silver Service Rx EIR Frames received."
        ::= { rcTlsUniIpServiceStatsEntry 170 }

rcTlsUniIpServiceStatsSilverRxEirOopFrames     OBJECT-TYPE
        SYNTAX        Counter64
        MAX-ACCESS    read-only
        STATUS        current
        DESCRIPTION  "Number of Silver Service Rx Frames received that 
		      were EIR OOP."
        ::= { rcTlsUniIpServiceStatsEntry 171 }

rcTlsUniIpServiceStatsSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcTlsUniIpServiceStatsEntry 172 }

rcTlsUniIpServiceStatsSilverRxPirFrames     OBJECT-TYPE
        SYNTAX        Counter64
        MAX-ACCESS    read-only
        STATUS        current
        DESCRIPTION  "Number of Silver Service Rx PIR Frames received."
        ::= { rcTlsUniIpServiceStatsEntry 173 }

rcTlsUniIpServiceStatsSilverRxPirOopFrames     OBJECT-TYPE
        SYNTAX        Counter64
        MAX-ACCESS    read-only
        STATUS        current
        DESCRIPTION  "Number of Silver Service Rx Frames received that 
		      were PIR OOP."
        ::= { rcTlsUniIpServiceStatsEntry 174 }

rcTlsUniIpServiceStatsSilverRxGreenFrames     OBJECT-TYPE
        SYNTAX        Counter64
        MAX-ACCESS    read-only
        STATUS        current
        DESCRIPTION  "Number of Silver Service Rx Frames received that 
		      were marked 'Green' by the policer."
        ::= { rcTlsUniIpServiceStatsEntry 175 }

rcTlsUniIpServiceStatsSilverRxYellowFrames     OBJECT-TYPE
        SYNTAX        Counter64
        MAX-ACCESS    read-only
        STATUS        current
        DESCRIPTION  "Number of Silver Service Rx Frames received that 
		      were marked 'Yellow' by the policer."
        ::= { rcTlsUniIpServiceStatsEntry 176 }

rcTlsUniIpServiceStatsSilverRxRedFrames     OBJECT-TYPE
        SYNTAX        Counter64
        MAX-ACCESS    read-only
        STATUS        current
        DESCRIPTION  "Number of Silver Service Rx Frames received that 
		      were marked 'Red' by the policer."
        ::= { rcTlsUniIpServiceStatsEntry 177 }

rcTlsUniIpServiceStatsStndRxCirFrames     OBJECT-TYPE
        SYNTAX        Counter64
        MAX-ACCESS    read-only
        STATUS        current
        DESCRIPTION  "Number of Standard Service Rx CIR Frames received."
        ::= { rcTlsUniIpServiceStatsEntry 178 }

rcTlsUniIpServiceStatsStndRxCirOopFrames     OBJECT-TYPE
        SYNTAX        Counter64
        MAX-ACCESS    read-only
        STATUS        current
        DESCRIPTION  "Number of Standard Service Rx Frames received that 
		      were CIR OOP."
        ::= { rcTlsUniIpServiceStatsEntry 179 }

rcTlsUniIpServiceStatsStndRxEirFrames     OBJECT-TYPE
        SYNTAX        Counter64
        MAX-ACCESS    read-only
        STATUS        current
        DESCRIPTION  "Number of Standard Service Rx EIR Frames received."
        ::= { rcTlsUniIpServiceStatsEntry 180 }

rcTlsUniIpServiceStatsStndRxEirOopFrames     OBJECT-TYPE
        SYNTAX        Counter64
        MAX-ACCESS    read-only
        STATUS        current
        DESCRIPTION  "Number of Standard Service Rx Frames received that 
		      were EIR OOP."
        ::= { rcTlsUniIpServiceStatsEntry 181 }

rcTlsUniIpServiceStatsStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcTlsUniIpServiceStatsEntry 182 }

rcTlsUniIpServiceStatsStndRxPirFrames     OBJECT-TYPE
        SYNTAX        Counter64
        MAX-ACCESS    read-only
        STATUS        current
        DESCRIPTION  "Number of Standard Service Rx PIR Frames received."
        ::= { rcTlsUniIpServiceStatsEntry 183 }

rcTlsUniIpServiceStatsStndRxPirOopFrames     OBJECT-TYPE
        SYNTAX        Counter64
        MAX-ACCESS    read-only
        STATUS        current
        DESCRIPTION  "Number of Standard Service Rx Frames received that 
		      were PIR OOP."
        ::= { rcTlsUniIpServiceStatsEntry 184 }

rcTlsUniIpServiceStatsStndRxGreenFrames     OBJECT-TYPE
        SYNTAX        Counter64
        MAX-ACCESS    read-only
        STATUS        current
        DESCRIPTION  "Number of Standard Service Rx Frames received that 
		      were marked 'Green' by the policer."
        ::= { rcTlsUniIpServiceStatsEntry 185 }

rcTlsUniIpServiceStatsStndRxYellowFrames     OBJECT-TYPE
        SYNTAX        Counter64
        MAX-ACCESS    read-only
        STATUS        current
        DESCRIPTION  "Number of Standard Service Rx Frames received that 
		      were marked 'Yellow' by the policer."
        ::= { rcTlsUniIpServiceStatsEntry 186 }

rcTlsUniIpServiceStatsStndRxRedFrames     OBJECT-TYPE
        SYNTAX        Counter64
        MAX-ACCESS    read-only
        STATUS        current
        DESCRIPTION  "Number of Standard Service Rx Frames received that 
		      were marked 'Red' by the policer."
        ::= { rcTlsUniIpServiceStatsEntry 187 }

rcTlsUniIpServiceStatsMcastRxDroppedFrames     OBJECT-TYPE
        SYNTAX        Counter64
        MAX-ACCESS    read-only
        STATUS        current
        DESCRIPTION  "Number of Multicast Rx Frames dropped."
        ::= { rcTlsUniIpServiceStatsEntry 188 }

rcTlsUniIpServiceStatsBcastUUcastRxTotalFrames     OBJECT-TYPE
        SYNTAX        Counter64
        MAX-ACCESS    read-only
        STATUS        current
        DESCRIPTION  "Number of Broadcast/Unknown Unicast Rx total Frames."
        ::= { rcTlsUniIpServiceStatsEntry 189 }

rcTlsUniIpServiceStatsBcastUUcastRxDroppedFrames     OBJECT-TYPE
        SYNTAX        Counter64
        MAX-ACCESS    read-only
        STATUS        current
        DESCRIPTION  "Number of Broadcast/Unknown Rx Frames dropped."
        ::= { rcTlsUniIpServiceStatsEntry 190 }

rcTlsUniIpServiceStatsPremTxCirOctets     OBJECT-TYPE
        SYNTAX        Counter64
        MAX-ACCESS    read-only
        STATUS        current
        DESCRIPTION  "Number of Premium Service Tx CIR Octets received."
        ::= { rcTlsUniIpServiceStatsEntry 191 }

rcTlsUniIpServiceStatsPremTxCirOopOctets     OBJECT-TYPE
        SYNTAX        Counter64
        MAX-ACCESS    read-only
        STATUS        current
        DESCRIPTION  "Number of Premium Service Tx Octets received that 
		      were CIR OOP."
        ::= { rcTlsUniIpServiceStatsEntry 192 }

rcTlsUniIpServiceStatsPremTxEirOctets     OBJECT-TYPE
        SYNTAX        Counter64
        MAX-ACCESS    read-only
        STATUS        current
        DESCRIPTION  "Number of Premium Service Tx EIR Octets received."
        ::= { rcTlsUniIpServiceStatsEntry 193 }

rcTlsUniIpServiceStatsPremTxEirOopOctets     OBJECT-TYPE
        SYNTAX        Counter64
        MAX-ACCESS    read-only
        STATUS        current
        DESCRIPTION  "Number of Premium Service Tx Octets received that 
		      were EIR OOP."
        ::= { rcTlsUniIpServiceStatsEntry 194 }

rcTlsUniIpServiceStatsPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcTlsUniIpServiceStatsEntry 195 }

rcTlsUniIpServiceStatsPremTxPirOctets     OBJECT-TYPE
        SYNTAX        Counter64
        MAX-ACCESS    read-only
        STATUS        current
        DESCRIPTION  "Number of Premium Service Tx PIR Octets received."
        ::= { rcTlsUniIpServiceStatsEntry 196 }

rcTlsUniIpServiceStatsPremTxPirOopOctets     OBJECT-TYPE
        SYNTAX        Counter64
        MAX-ACCESS    read-only
        STATUS        current
        DESCRIPTION  "Number of Premium Service Tx Octets received that 
		      were PIR OOP."
        ::= { rcTlsUniIpServiceStatsEntry 197 }

rcTlsUniIpServiceStatsPremTxGreenOctets     OBJECT-TYPE
        SYNTAX        Counter64
        MAX-ACCESS    read-only
        STATUS        current
        DESCRIPTION  "Number of Premium Service Tx Octets received that 
		      were marked 'Green' by the policer."
        ::= { rcTlsUniIpServiceStatsEntry 198 }

rcTlsUniIpServiceStatsPremTxYellowOctets     OBJECT-TYPE
        SYNTAX        Counter64
        MAX-ACCESS    read-only
        STATUS        current
        DESCRIPTION  "Number of Premium Service Tx Octets received that 
		      were marked 'Yellow' by the policer."
        ::= { rcTlsUniIpServiceStatsEntry 199 }

rcTlsUniIpServiceStatsPremTxRedOctets     OBJECT-TYPE
        SYNTAX        Counter64
        MAX-ACCESS    read-only
        STATUS        current
        DESCRIPTION  "Number of Premium Service Tx Octets received that 
		      were marked 'Red' by the policer."
        ::= { rcTlsUniIpServiceStatsEntry 200 }

rcTlsUniIpServiceStatsGoldTxCirOctets     OBJECT-TYPE
        SYNTAX        Counter64
        MAX-ACCESS    read-only
        STATUS        current
        DESCRIPTION  "Number of Gold Service Tx CIR Octets received."
        ::= { rcTlsUniIpServiceStatsEntry 201 }

rcTlsUniIpServiceStatsGoldTxCirOopOctets     OBJECT-TYPE
        SYNTAX        Counter64
        MAX-ACCESS    read-only
        STATUS        current
        DESCRIPTION  "Number of Gold Service Tx Octets received that 
		      were CIR OOP."
        ::= { rcTlsUniIpServiceStatsEntry 202 }

rcTlsUniIpServiceStatsGoldTxEirOctets     OBJECT-TYPE
        SYNTAX        Counter64
        MAX-ACCESS    read-only
        STATUS        current
        DESCRIPTION  "Number of Gold Service Tx EIR Octets received."
        ::= { rcTlsUniIpServiceStatsEntry 203 }

rcTlsUniIpServiceStatsGoldTxEirOopOctets     OBJECT-TYPE
        SYNTAX        Counter64
        MAX-ACCESS    read-only
        STATUS        current
        DESCRIPTION  "Number of Gold Service Tx Octets received that 
		      were EIR OOP."
        ::= { rcTlsUniIpServiceStatsEntry 204 }

rcTlsUniIpServiceStatsGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcTlsUniIpServiceStatsEntry 205 }

rcTlsUniIpServiceStatsGoldTxPirOctets     OBJECT-TYPE
        SYNTAX        Counter64
        MAX-ACCESS    read-only
        STATUS        current
        DESCRIPTION  "Number of Gold Service Tx PIR Octets received."
        ::= { rcTlsUniIpServiceStatsEntry 206 }

rcTlsUniIpServiceStatsGoldTxPirOopOctets     OBJECT-TYPE
        SYNTAX        Counter64
        MAX-ACCESS    read-only
        STATUS        current
        DESCRIPTION  "Number of Gold Service Tx Octets received that 
		      were PIR OOP."
        ::= { rcTlsUniIpServiceStatsEntry 207 }

rcTlsUniIpServiceStatsGoldTxGreenOctets     OBJECT-TYPE
        SYNTAX        Counter64
        MAX-ACCESS    read-only
        STATUS        current
        DESCRIPTION  "Number of Gold Service Tx Octets received that 
		      were marked 'Green' by the policer."
        ::= { rcTlsUniIpServiceStatsEntry 208 }

rcTlsUniIpServiceStatsGoldTxYellowOctets     OBJECT-TYPE
        SYNTAX        Counter64
        MAX-ACCESS    read-only
        STATUS        current
        DESCRIPTION  "Number of Gold Service Tx Octets received that 
		      were marked 'Yellow' by the policer."
        ::= { rcTlsUniIpServiceStatsEntry 209 }

rcTlsUniIpServiceStatsGoldTxRedOctets     OBJECT-TYPE
        SYNTAX        Counter64
        MAX-ACCESS    read-only
        STATUS        current
        DESCRIPTION  "Number of Gold Service Tx Octets received that 
		      were marked 'Red' by the policer."
        ::= { rcTlsUniIpServiceStatsEntry 210 }

rcTlsUniIpServiceStatsSilverTxCirOctets     OBJECT-TYPE
        SYNTAX        Counter64
        MAX-ACCESS    read-only
        STATUS        current
        DESCRIPTION  "Number of Silver Service Tx CIR Octets received."
        ::= { rcTlsUniIpServiceStatsEntry 211 }

rcTlsUniIpServiceStatsSilverTxCirOopOctets     OBJECT-TYPE
        SYNTAX        Counter64
        MAX-ACCESS    read-only
        STATUS        current
        DESCRIPTION  "Number of Silver Service Tx Octets received that 
		      were CIR OOP."
        ::= { rcTlsUniIpServiceStatsEntry 212 }

rcTlsUniIpServiceStatsSilverTxEirOctets     OBJECT-TYPE
        SYNTAX        Counter64
        MAX-ACCESS    read-only
        STATUS        current
        DESCRIPTION  "Number of Silver Service Tx EIR Octets received."
        ::= { rcTlsUniIpServiceStatsEntry 213 }

rcTlsUniIpServiceStatsSilverTxEirOopOctets     OBJECT-TYPE
        SYNTAX        Counter64
        MAX-ACCESS    read-only
        STATUS        current
        DESCRIPTION  "Number of Silver Service Tx Octets received that 
		      were EIR OOP."
        ::= { rcTlsUniIpServiceStatsEntry 214 }

rcTlsUniIpServiceStatsSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcTlsUniIpServiceStatsEntry 215 }

rcTlsUniIpServiceStatsSilverTxPirOctets     OBJECT-TYPE
        SYNTAX        Counter64
        MAX-ACCESS    read-only
        STATUS        current
        DESCRIPTION  "Number of Silver Service Tx PIR Octets received."
        ::= { rcTlsUniIpServiceStatsEntry 216 }

rcTlsUniIpServiceStatsSilverTxPirOopOctets     OBJECT-TYPE
        SYNTAX        Counter64
        MAX-ACCESS    read-only
        STATUS        current
        DESCRIPTION  "Number of Silver Service Tx Octets received that 
		      were PIR OOP."
        ::= { rcTlsUniIpServiceStatsEntry 217 }

rcTlsUniIpServiceStatsSilverTxGreenOctets     OBJECT-TYPE
        SYNTAX        Counter64
        MAX-ACCESS    read-only
        STATUS        current
        DESCRIPTION  "Number of Silver Service Tx Octets received that 
		      were marked 'Green' by the policer."
        ::= { rcTlsUniIpServiceStatsEntry 218 }

rcTlsUniIpServiceStatsSilverTxYellowOctets     OBJECT-TYPE
        SYNTAX        Counter64
        MAX-ACCESS    read-only
        STATUS        current
        DESCRIPTION  "Number of Silver Service Tx Octets received that 
		      were marked 'Yellow' by the policer."
        ::= { rcTlsUniIpServiceStatsEntry 219 }

rcTlsUniIpServiceStatsSilverTxRedOctets     OBJECT-TYPE
        SYNTAX        Counter64
        MAX-ACCESS    read-only
        STATUS        current
        DESCRIPTION  "Number of Silver Service Tx Octets received that 
		      were marked 'Red' by the policer."
        ::= { rcTlsUniIpServiceStatsEntry 220 }

rcTlsUniIpServiceStatsStndTxCirOctets     OBJECT-TYPE
        SYNTAX        Counter64
        MAX-ACCESS    read-only
        STATUS        current
        DESCRIPTION  "Number of Standard Service Tx CIR Octets received."
        ::= { rcTlsUniIpServiceStatsEntry 221 }

rcTlsUniIpServiceStatsStndTxCirOopOctets     OBJECT-TYPE
        SYNTAX        Counter64
        MAX-ACCESS    read-only
        STATUS        current
        DESCRIPTION  "Number of Standard Service Tx Octets received that 
		      were CIR OOP."
        ::= { rcTlsUniIpServiceStatsEntry 222 }

rcTlsUniIpServiceStatsStndTxEirOctets     OBJECT-TYPE
        SYNTAX        Counter64
        MAX-ACCESS    read-only
        STATUS        current
        DESCRIPTION  "Number of Standard Service Tx EIR Octets received."
        ::= { rcTlsUniIpServiceStatsEntry 223 }

rcTlsUniIpServiceStatsStndTxEirOopOctets     OBJECT-TYPE
        SYNTAX        Counter64
        MAX-ACCESS    read-only
        STATUS        current
        DESCRIPTION  "Number of Standard Service Tx Octets received that 
		      were EIR OOP."
        ::= { rcTlsUniIpServiceStatsEntry 224 }

rcTlsUniIpServiceStatsStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcTlsUniIpServiceStatsEntry 225 }

rcTlsUniIpServiceStatsStndTxPirOctets     OBJECT-TYPE
        SYNTAX        Counter64
        MAX-ACCESS    read-only
        STATUS        current
        DESCRIPTION  "Number of Standard Service Tx PIR Octets received."
        ::= { rcTlsUniIpServiceStatsEntry 226 }

rcTlsUniIpServiceStatsStndTxPirOopOctets     OBJECT-TYPE
        SYNTAX        Counter64
        MAX-ACCESS    read-only
        STATUS        current
        DESCRIPTION  "Number of Standard Service Tx Octets received that 
		      were PIR OOP."
        ::= { rcTlsUniIpServiceStatsEntry 227 }

rcTlsUniIpServiceStatsStndTxGreenOctets     OBJECT-TYPE
        SYNTAX        Counter64
        MAX-ACCESS    read-only
        STATUS        current
        DESCRIPTION  "Number of Standard Service Tx Octets received that 
		      were marked 'Green' by the policer."
        ::= { rcTlsUniIpServiceStatsEntry 228 }

rcTlsUniIpServiceStatsStndTxYellowOctets     OBJECT-TYPE
        SYNTAX        Counter64
        MAX-ACCESS    read-only
        STATUS        current
        DESCRIPTION  "Number of Standard Service Tx Octets received that 
		      were marked 'Yellow' by the policer."
        ::= { rcTlsUniIpServiceStatsEntry 229 }

rcTlsUniIpServiceStatsStndTxRedOctets     OBJECT-TYPE
        SYNTAX        Counter64
        MAX-ACCESS    read-only
        STATUS        current
        DESCRIPTION  "Number of Standard Service Tx Octets received that 
		      were marked 'Red' by the policer."
        ::= { rcTlsUniIpServiceStatsEntry 230 }

rcTlsUniIpServiceStatsMcastTxDroppedOctets     OBJECT-TYPE
        SYNTAX        Counter64
        MAX-ACCESS    read-only
        STATUS        current
        DESCRIPTION  "Number of Multicast Tx Octets dropped."
        ::= { rcTlsUniIpServiceStatsEntry 231 }

rcTlsUniIpServiceStatsBcastUUcastTxTotalOctets     OBJECT-TYPE
        SYNTAX        Counter64
        MAX-ACCESS    read-only
        STATUS        current
        DESCRIPTION  "Number of Broadcast/Unknown Unicast Tx total Octets."
        ::= { rcTlsUniIpServiceStatsEntry 232 }

rcTlsUniIpServiceStatsBcastUUcastTxDroppedOctets     OBJECT-TYPE
        SYNTAX        Counter64
        MAX-ACCESS    read-only
        STATUS        current
        DESCRIPTION  "Number of Broadcast/Unknown Tx Octets dropped."
        ::= { rcTlsUniIpServiceStatsEntry 233 }

rcTlsUniIpServiceStatsPremTxCirFrames     OBJECT-TYPE
        SYNTAX        Counter64
        MAX-ACCESS    read-only
        STATUS        current
        DESCRIPTION  "Number of Premium Service Tx CIR Frames received."
        ::= { rcTlsUniIpServiceStatsEntry 234 }

rcTlsUniIpServiceStatsPremTxCirOopFrames     OBJECT-TYPE
        SYNTAX        Counter64
        MAX-ACCESS    read-only
        STATUS        current
        DESCRIPTION  "Number of Premium Service Tx Frames received that 
		      were CIR OOP."
        ::= { rcTlsUniIpServiceStatsEntry 235 }

rcTlsUniIpServiceStatsPremTxEirFrames     OBJECT-TYPE
        SYNTAX        Counter64
        MAX-ACCESS    read-only
        STATUS        current
        DESCRIPTION  "Number of Premium Service Tx EIR Frames received."
        ::= { rcTlsUniIpServiceStatsEntry 236 }

rcTlsUniIpServiceStatsPremTxEirOopFrames     OBJECT-TYPE
        SYNTAX        Counter64
        MAX-ACCESS    read-only
        STATUS        current
        DESCRIPTION  "Number of Premium Service Tx Frames received that 
		      were EIR OOP."
        ::= { rcTlsUniIpServiceStatsEntry 237 }

rcTlsUniIpServiceStatsPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcTlsUniIpServiceStatsEntry 238 }

rcTlsUniIpServiceStatsPremTxPirFrames     OBJECT-TYPE
        SYNTAX        Counter64
        MAX-ACCESS    read-only
        STATUS        current
        DESCRIPTION  "Number of Premium Service Tx PIR Frames received."
        ::= { rcTlsUniIpServiceStatsEntry 239 }

rcTlsUniIpServiceStatsPremTxPirOopFrames     OBJECT-TYPE
        SYNTAX        Counter64
        MAX-ACCESS    read-only
        STATUS        current
        DESCRIPTION  "Number of Premium Service Tx Frames received that 
		      were PIR OOP."
        ::= { rcTlsUniIpServiceStatsEntry 240 }

rcTlsUniIpServiceStatsPremTxGreenFrames     OBJECT-TYPE
        SYNTAX        Counter64
        MAX-ACCESS    read-only
        STATUS        current
        DESCRIPTION  "Number of Premium Service Tx Frames received that 
		      were marked 'Green' by the policer."
        ::= { rcTlsUniIpServiceStatsEntry 241 }

rcTlsUniIpServiceStatsPremTxYellowFrames     OBJECT-TYPE
        SYNTAX        Counter64
        MAX-ACCESS    read-only
        STATUS        current
        DESCRIPTION  "Number of Premium Service Tx Frames received that 
		      were marked 'Yellow' by the policer."
        ::= { rcTlsUniIpServiceStatsEntry 242 }

rcTlsUniIpServiceStatsPremTxRedFrames     OBJECT-TYPE
        SYNTAX        Counter64
        MAX-ACCESS    read-only
        STATUS        current
        DESCRIPTION  "Number of Premium Service Tx Frames received that 
		      were marked 'Red' by the policer."
        ::= { rcTlsUniIpServiceStatsEntry 243 }

rcTlsUniIpServiceStatsGoldTxCirFrames     OBJECT-TYPE
        SYNTAX        Counter64
        MAX-ACCESS    read-only
        STATUS        current
        DESCRIPTION  "Number of Gold Service Tx CIR Frames received."
        ::= { rcTlsUniIpServiceStatsEntry 244 }

rcTlsUniIpServiceStatsGoldTxCirOopFrames     OBJECT-TYPE
        SYNTAX        Counter64
        MAX-ACCESS    read-only
        STATUS        current
        DESCRIPTION  "Number of Gold Service Tx Frames received that 
		      were CIR OOP."
        ::= { rcTlsUniIpServiceStatsEntry 245 }

rcTlsUniIpServiceStatsGoldTxEirFrames     OBJECT-TYPE
        SYNTAX        Counter64
        MAX-ACCESS    read-only
        STATUS        current
        DESCRIPTION  "Number of Gold Service Tx EIR Frames received."
        ::= { rcTlsUniIpServiceStatsEntry 246 }

rcTlsUniIpServiceStatsGoldTxEirOopFrames     OBJECT-TYPE
        SYNTAX        Counter64
        MAX-ACCESS    read-only
        STATUS        current
        DESCRIPTION  "Number of Gold Service Tx Frames received that 
		      were EIR OOP."
        ::= { rcTlsUniIpServiceStatsEntry 247 }

rcTlsUniIpServiceStatsGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcTlsUniIpServiceStatsEntry 248 }

rcTlsUniIpServiceStatsGoldTxPirFrames     OBJECT-TYPE
        SYNTAX        Counter64
        MAX-ACCESS    read-only
        STATUS        current
        DESCRIPTION  "Number of Gold Service Tx PIR Frames received."
        ::= { rcTlsUniIpServiceStatsEntry 249 }

rcTlsUniIpServiceStatsGoldTxPirOopFrames     OBJECT-TYPE
        SYNTAX        Counter64
        MAX-ACCESS    read-only
        STATUS        current
        DESCRIPTION  "Number of Gold Service Tx Frames received that 
		      were PIR OOP."
        ::= { rcTlsUniIpServiceStatsEntry 250 }

rcTlsUniIpServiceStatsGoldTxGreenFrames     OBJECT-TYPE
        SYNTAX        Counter64
        MAX-ACCESS    read-only
        STATUS        current
        DESCRIPTION  "Number of Gold Service Tx Frames received that 
		      were marked 'Green' by the policer."
        ::= { rcTlsUniIpServiceStatsEntry 251 }

rcTlsUniIpServiceStatsGoldTxYellowFrames     OBJECT-TYPE
        SYNTAX        Counter64
        MAX-ACCESS    read-only
        STATUS        current
        DESCRIPTION  "Number of Gold Service Tx Frames received that 
		      were marked 'Yellow' by the policer."
        ::= { rcTlsUniIpServiceStatsEntry 252 }

rcTlsUniIpServiceStatsGoldTxRedFrames     OBJECT-TYPE
        SYNTAX        Counter64
        MAX-ACCESS    read-only
        STATUS        current
        DESCRIPTION  "Number of Gold Service Tx Frames received that 
		      were marked 'Red' by the policer."
        ::= { rcTlsUniIpServiceStatsEntry 253 }

rcTlsUniIpServiceStatsSilverTxCirFrames     OBJECT-TYPE
        SYNTAX        Counter64
        MAX-ACCESS    read-only
        STATUS        current
        DESCRIPTION  "Number of Silver Service Tx CIR Frames received."
        ::= { rcTlsUniIpServiceStatsEntry 254 }

rcTlsUniIpServiceStatsSilverTxCirOopFrames     OBJECT-TYPE
        SYNTAX        Counter64
        MAX-ACCESS    read-only
        STATUS        current
        DESCRIPTION  "Number of Silver Service Tx Frames received that 
		      were CIR OOP."
        ::= { rcTlsUniIpServiceStatsEntry 255 }

rcTlsUniIpServiceStatsSilverTxEirFrames     OBJECT-TYPE
        SYNTAX        Counter64
        MAX-ACCESS    read-only
        STATUS        current
        DESCRIPTION  "Number of Silver Service Tx EIR Frames received."
        ::= { rcTlsUniIpServiceStatsEntry 256 }

rcTlsUniIpServiceStatsSilverTxEirOopFrames     OBJECT-TYPE
        SYNTAX        Counter64
        MAX-ACCESS    read-only
        STATUS        current
        DESCRIPTION  "Number of Silver Service Tx Frames received that 
		      were EIR OOP."
        ::= { rcTlsUniIpServiceStatsEntry 257 }

rcTlsUniIpServiceStatsSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcTlsUniIpServiceStatsEntry 258 }

rcTlsUniIpServiceStatsSilverTxPirFrames     OBJECT-TYPE
        SYNTAX        Counter64
        MAX-ACCESS    read-only
        STATUS        current
        DESCRIPTION  "Number of Silver Service Tx PIR Frames received."
        ::= { rcTlsUniIpServiceStatsEntry 259 }

rcTlsUniIpServiceStatsSilverTxPirOopFrames     OBJECT-TYPE
        SYNTAX        Counter64
        MAX-ACCESS    read-only
        STATUS        current
        DESCRIPTION  "Number of Silver Service Tx Frames received that 
		      were PIR OOP."
        ::= { rcTlsUniIpServiceStatsEntry 260 }

rcTlsUniIpServiceStatsSilverTxGreenFrames     OBJECT-TYPE
        SYNTAX        Counter64
        MAX-ACCESS    read-only
        STATUS        current
        DESCRIPTION  "Number of Silver Service Tx Frames received that 
		      were marked 'Green' by the policer."
        ::= { rcTlsUniIpServiceStatsEntry 261 }

rcTlsUniIpServiceStatsSilverTxYellowFrames     OBJECT-TYPE
        SYNTAX        Counter64
        MAX-ACCESS    read-only
        STATUS        current
        DESCRIPTION  "Number of Silver Service Tx Frames received that 
		      were marked 'Yellow' by the policer."
        ::= { rcTlsUniIpServiceStatsEntry 262 }

rcTlsUniIpServiceStatsSilverTxRedFrames     OBJECT-TYPE
        SYNTAX        Counter64
        MAX-ACCESS    read-only
        STATUS        current
        DESCRIPTION  "Number of Silver Service Tx Frames received that 
		      were marked 'Red' by the policer."
        ::= { rcTlsUniIpServiceStatsEntry 263 }

rcTlsUniIpServiceStatsStndTxCirFrames     OBJECT-TYPE
        SYNTAX        Counter64
        MAX-ACCESS    read-only
        STATUS        current
        DESCRIPTION  "Number of Standard Service Tx CIR Frames received."
        ::= { rcTlsUniIpServiceStatsEntry 264 }

rcTlsUniIpServiceStatsStndTxCirOopFrames     OBJECT-TYPE
        SYNTAX        Counter64
        MAX-ACCESS    read-only
        STATUS        current
        DESCRIPTION  "Number of Standard Service Tx Frames received that 
		      were CIR OOP."
        ::= { rcTlsUniIpServiceStatsEntry 265 }

rcTlsUniIpServiceStatsStndTxEirFrames     OBJECT-TYPE
        SYNTAX        Counter64
        MAX-ACCESS    read-only
        STATUS        current
        DESCRIPTION  "Number of Standard Service Tx EIR Frames received."
        ::= { rcTlsUniIpServiceStatsEntry 266 }

rcTlsUniIpServiceStatsStndTxEirOopFrames     OBJECT-TYPE
        SYNTAX        Counter64
        MAX-ACCESS    read-only
        STATUS        current
        DESCRIPTION  "Number of Standard Service Tx Frames received that 
		      were EIR OOP."
        ::= { rcTlsUniIpServiceStatsEntry 267 }

rcTlsUniIpServiceStatsStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcTlsUniIpServiceStatsEntry 268 }

rcTlsUniIpServiceStatsStndTxPirFrames     OBJECT-TYPE
        SYNTAX        Counter64
        MAX-ACCESS    read-only
        STATUS        current
        DESCRIPTION  "Number of Standard Service Tx PIR Frames received."
        ::= { rcTlsUniIpServiceStatsEntry 269 }

rcTlsUniIpServiceStatsStndTxPirOopFrames     OBJECT-TYPE
        SYNTAX        Counter64
        MAX-ACCESS    read-only
        STATUS        current
        DESCRIPTION  "Number of Standard Service Tx Frames received that 
		      were PIR OOP."
        ::= { rcTlsUniIpServiceStatsEntry 270 }

rcTlsUniIpServiceStatsStndTxGreenFrames     OBJECT-TYPE
        SYNTAX        Counter64
        MAX-ACCESS    read-only
        STATUS        current
        DESCRIPTION  "Number of Standard Service Tx Frames received that 
		      were marked 'Green' by the policer."
        ::= { rcTlsUniIpServiceStatsEntry 271 }

rcTlsUniIpServiceStatsStndTxYellowFrames     OBJECT-TYPE
        SYNTAX        Counter64
        MAX-ACCESS    read-only
        STATUS        current
        DESCRIPTION  "Number of Standard Service Tx Frames received that 
		      were marked 'Yellow' by the policer."
        ::= { rcTlsUniIpServiceStatsEntry 272 }

rcTlsUniIpServiceStatsStndTxRedFrames     OBJECT-TYPE
        SYNTAX        Counter64
        MAX-ACCESS    read-only
        STATUS        current
        DESCRIPTION  "Number of Standard Service Tx Frames received that 
		      were marked 'Red' by the policer."
        ::= { rcTlsUniIpServiceStatsEntry 273 }

rcTlsUniIpServiceStatsMcastTxDroppedFrames     OBJECT-TYPE
        SYNTAX        Counter64
        MAX-ACCESS    read-only
        STATUS        current
        DESCRIPTION  "Number of Multicast Tx Frames dropped."
        ::= { rcTlsUniIpServiceStatsEntry 274 }

rcTlsUniIpServiceStatsBcastUUcastTxTotalFrames     OBJECT-TYPE
        SYNTAX        Counter64
        MAX-ACCESS    read-only
        STATUS        current
        DESCRIPTION  "Number of Broadcast/Unknown Unicast Tx total Frames."
        ::= { rcTlsUniIpServiceStatsEntry 275 }

rcTlsUniIpServiceStatsBcastUUcastTxDroppedFrames     OBJECT-TYPE
        SYNTAX        Counter64
        MAX-ACCESS    read-only
        STATUS        current
        DESCRIPTION  "Number of Broadcast/Unknown Tx Frames dropped."
        ::= { rcTlsUniIpServiceStatsEntry 276 }

rcTlsUniIpServiceStatsDropClassRxDroppedOctets     OBJECT-TYPE
        SYNTAX        Counter64
        MAX-ACCESS    read-only
        STATUS        current
        DESCRIPTION  "Number of Drop Class Rx Octets dropped."
        ::= { rcTlsUniIpServiceStatsEntry 277 }

rcTlsUniIpServiceStatsDropClassRxDroppedFrames     OBJECT-TYPE
        SYNTAX        Counter64
        MAX-ACCESS    read-only
        STATUS        current
        DESCRIPTION  "Number of Drop Class Rx Frames dropped."
        ::= { rcTlsUniIpServiceStatsEntry 278 }

rcTlsUniIpServiceStatsDropClassTxDroppedOctets	OBJECT-TYPE
        SYNTAX        Counter64
        MAX-ACCESS    read-only
        STATUS        current
        DESCRIPTION  "Number of Drop Class Tx Octets dropped."
        ::= { rcTlsUniIpServiceStatsEntry 279 }

rcTlsUniIpServiceStatsDropClassTxDroppedFrames     OBJECT-TYPE
        SYNTAX        Counter64
        MAX-ACCESS    read-only
        STATUS        current
        DESCRIPTION  "Number of Drop Class Tx Frames dropped."
        ::= { rcTlsUniIpServiceStatsEntry 280 }




-- ESM Port Policer Stats

rcEsmPortPolicerStatsTable OBJECT-TYPE
        SYNTAX        SEQUENCE OF RcEsmPortPolicerStatsEntry
        MAX-ACCESS    not-accessible
        STATUS        current
        DESCRIPTION   "ESM (Ethernet Service Module) port Policer Out of 
		       Profile dropped statistic Table. It is used for TLS 
		       feature. Only applicable to port interface which 
		       support TLS feature. The CoS Profile is defined by 
		       rcCosProfileTable."
        ::= { rcTls 19 }

rcEsmPortPolicerStatsEntry  OBJECT-TYPE
        SYNTAX        RcEsmPortPolicerStatsEntry
        MAX-ACCESS    not-accessible
        STATUS        current
        DESCRIPTION   "Entry contains out-of-profile (dropped) octet counts"
        INDEX         { rcEsmPortPolicerStatsPort  }
        ::= { rcEsmPortPolicerStatsTable 1 }
 
RcEsmPortPolicerStatsEntry ::=
	SEQUENCE {	 
		rcEsmPortPolicerStatsPort               InterfaceIndex,
		rcEsmPortPolicerStatsTxPremDropOctets   Counter64,
		rcEsmPortPolicerStatsTxGoldDropOctets   Counter64,
		rcEsmPortPolicerStatsTxSilverDropOctets Counter64,	
      		rcEsmPortPolicerStatsTxStndDropOctets   Counter64
	}
rcEsmPortPolicerStatsPort OBJECT-TYPE
        SYNTAX        InterfaceIndex
        MAX-ACCESS    not-accessible
        STATUS        current
        DESCRIPTION   "Port interface Index"
        ::= { rcEsmPortPolicerStatsEntry 1}

rcEsmPortPolicerStatsTxPremDropOctets	OBJECT-TYPE
        SYNTAX        Counter64
        MAX-ACCESS    read-only
        STATUS        current
        DESCRIPTION  "Port Egress policer, count of premium octets dropped"
	::= { rcEsmPortPolicerStatsEntry 2}

rcEsmPortPolicerStatsTxGoldDropOctets	OBJECT-TYPE
        SYNTAX        Counter64
        MAX-ACCESS    read-only
        STATUS        current
        DESCRIPTION  "Port Egress policer, count of Gold octets dropped"
	::= { rcEsmPortPolicerStatsEntry 3}

rcEsmPortPolicerStatsTxSilverDropOctets	OBJECT-TYPE
        SYNTAX        Counter64
        MAX-ACCESS    read-only
        STATUS        current
        DESCRIPTION  "Port Egress policer, count of Silver octets dropped"
	::= { rcEsmPortPolicerStatsEntry 4}

rcEsmPortPolicerStatsTxStndDropOctets	OBJECT-TYPE
        SYNTAX        Counter64
        MAX-ACCESS    read-only
        STATUS        current
        DESCRIPTION  "Port Egress policer, count of Standard octets dropped"
	::= { rcEsmPortPolicerStatsEntry 5}


-- rcTlsIpServiceTable 

rcTlsIpServiceTable OBJECT-TYPE
        SYNTAX        SEQUENCE OF RcTlsIpServiceEntry
        MAX-ACCESS    not-accessible
        STATUS        current
        DESCRIPTION   "Table contains a customer IP Vlan and the local IP 
		       Vlan for IP Mcast service"
        ::= { rcTls 20 }

rcTlsIpServiceEntry OBJECT-TYPE
        SYNTAX        RcTlsIpServiceEntry
        MAX-ACCESS    not-accessible
        STATUS        current
        DESCRIPTION   "Entry contains the customer IP Vlan and the Local 
		       Vlan for for the IP Mcast service"
        INDEX         { rcTlsIpServiceTlsIndex, rcTlsIpServiceCustIpVlan }
        ::= { rcTlsIpServiceTable 1 }

RcTlsIpServiceEntry ::=
        SEQUENCE {
                rcTlsIpServiceTlsIndex                   INTEGER,
                rcTlsIpServiceCustIpVlan                 INTEGER,
                rcTlsIpServicePort                       InterfaceIndex,
                rcTlsIpServiceClearStats                 TruthValue,
                rcTlsIpServiceServiceProviderIpVlan      INTEGER,
                rcTlsIpServiceRowStatus                  RowStatus,
		rcTlsIpServiceName                       DisplayString,
		rcTlsIpServiceAgeTimer                   INTEGER,
		rcTlsIpServiceIngressCosProfileName      DisplayString,
		rcTlsIpServiceIngressPolicer             EnableValue,
		rcTlsIpServiceEgressCosProfileName       DisplayString,
		rcTlsIpServiceEgressPolicer              EnableValue,
		rcTlsIpServiceAction                     INTEGER,
		rcTlsIpServiceAdminState                 EnableValue,
		rcTlsIpServiceOperState                  INTEGER,
	        rcTlsIpServicePriMapping                 OCTET STRING,
	        rcTlsIpServicePriOverride                TruthValue,
		rcTlsIpServiceIpTblSize                  INTEGER,	
		rcTlsIpServiceIpTblWaterMk               INTEGER,
		rcTlsIpServiceIpTblMltId                 INTEGER,
		rcTlsIpServicePriOverrideType            INTEGER,
                rcTlsIpServiceColorBasedRemarking        EnableValue,
                rcTlsIpServiceDropRedColorPackets        TruthValue,
		rcTlsIpServiceRingId	                 INTEGER,
		rcTlsIpServiceModId	        	 Integer32,
		rcTlsIpServiceEsuPort                    INTEGER
        }

rcTlsIpServiceTlsIndex OBJECT-TYPE
        SYNTAX        INTEGER (1..2147483647)
        MAX-ACCESS    not-accessible
        STATUS        current
        DESCRIPTION   "TLS Index"
        ::= { rcTlsIpServiceEntry 1 }

rcTlsIpServiceCustIpVlan OBJECT-TYPE
        SYNTAX        INTEGER (1..4096)
        MAX-ACCESS    not-accessible
        STATUS        current
        DESCRIPTION   "Customer IP Vlan for IP Mcast Vlan mapping"
        ::= { rcTlsIpServiceEntry 2 }

rcTlsIpServicePort OBJECT-TYPE
        SYNTAX        InterfaceIndex
        MAX-ACCESS    read-create
        STATUS        current
        DESCRIPTION   "Customer IP Vlan for IP Mcast Vlan mapping"
        DEFVAL        { 1 }
        ::= { rcTlsIpServiceEntry 3 }

rcTlsIpServiceClearStats OBJECT-TYPE
        SYNTAX        TruthValue 
        MAX-ACCESS    read-create
        STATUS        current
        DESCRIPTION   "Clear Ip Service Statistics"
        ::= { rcTlsIpServiceEntry 4 }

rcTlsIpServiceServiceProviderIpVlan OBJECT-TYPE
        SYNTAX        INTEGER (1..4094)
        MAX-ACCESS    read-create
        STATUS        current
        DESCRIPTION   "Service Provider IP Vlan for UNI IP Mcast Vlan mapping"
        ::= { rcTlsIpServiceEntry 5 }

rcTlsIpServiceName  OBJECT-TYPE
        SYNTAX        DisplayString (SIZE (0..30)) 
        MAX-ACCESS    read-create
        STATUS        current
        DESCRIPTION   "Name of IP Service Vlan Entry. By default, It is 
		       VLAN-<uni id>-<cust ip vlan>"
        ::= { rcTlsIpServiceEntry 6 } 

rcTlsIpServiceRowStatus  OBJECT-TYPE
        SYNTAX        RowStatus
        MAX-ACCESS    read-create
        STATUS        current
        DESCRIPTION   "Used to create/delete entries"
        ::= { rcTlsIpServiceEntry 7 }

rcTlsIpServiceAgeTimer  OBJECT-TYPE
        SYNTAX        INTEGER (1..1966020)
        MAX-ACCESS    read-create
        STATUS        obsolete
        DESCRIPTION   "Mac address ageout timer in seconds.
		       Valid only if rcTlsIpService is Enabled"
	DEFVAL        { 300 }
        ::= { rcTlsIpServiceEntry 8 }

rcTlsIpServiceIngressCosProfileName OBJECT-TYPE
        SYNTAX        DisplayString (SIZE (1..20)) 
        MAX-ACCESS    read-create
        STATUS        current
        DESCRIPTION   "Ingress COS Profile Table Name for Customer Ip Service"
        DEFVAL       { "DEFAULT_MGT_PROFILE"  } 
        ::= { rcTlsIpServiceEntry 9 }

rcTlsIpServiceIngressPolicer OBJECT-TYPE
        SYNTAX        EnableValue
        MAX-ACCESS    read-create
        STATUS        current
        DESCRIPTION   "Enable/disable to use Ingress Cos Profile table 
			(rcTlsIpServiceIngressCosProfileName) for this 
			customer IP service"
	DEFVAL        { enable }
        ::= { rcTlsIpServiceEntry 10 }

rcTlsIpServiceEgressCosProfileName OBJECT-TYPE
        SYNTAX        DisplayString (SIZE (0..20)) 
        MAX-ACCESS    read-create
        STATUS        current
        DESCRIPTION   "Egress COS Profile Table Name for this customer IP
			Service."
        DEFVAL       { "DEFAULT_MGT_PROFILE"  } 
        ::= { rcTlsIpServiceEntry 11 }

rcTlsIpServiceEgressPolicer OBJECT-TYPE
        SYNTAX        EnableValue
        MAX-ACCESS    read-create
        STATUS        current
        DESCRIPTION   "Enable/disable to use Egress Cos Profile table 
			(rcTlsIpServiceEgressCosProfileName) for this 
			customer Ip Service"
	DEFVAL        { disable }
        ::= { rcTlsIpServiceEntry 12 }

rcTlsIpServiceAction  OBJECT-TYPE 
	SYNTAX        INTEGER {
                         none(1),       -- none of the following
                         flushIp(2)     -- flush Ip forwarding table
                      }
        MAX-ACCESS    read-create
        STATUS        current
        DESCRIPTION   "Mcast related action- Flush learningMac addresse"
        DEFVAL        { none }
	::= { rcTlsIpServiceEntry 13 }

rcTlsIpServiceAdminState OBJECT-TYPE
        SYNTAX        EnableValue
        MAX-ACCESS    read-create
        STATUS        current
        DESCRIPTION   "Value indicating whether the Ip Service is enabled"
        DEFVAL        { disable }
        ::= { rcTlsIpServiceEntry 14 }

rcTlsIpServiceOperState OBJECT-TYPE
        SYNTAX        INTEGER { 
                          up(1), 
                          down(2) 
                       }
        MAX-ACCESS    read-only
        STATUS        current
        DESCRIPTION   "The current operational state of this Customer IP Vlan."
        ::= { rcTlsIpServiceEntry 15 }

rcTlsIpServicePriMapping OBJECT-TYPE
        SYNTAX        OCTET STRING (SIZE(8))
        MAX-ACCESS    read-create
        STATUS        current
        DESCRIPTION   "Maps 802.1p priorities (0-7) to Optical Ethernet
                       Class of Service (COS) values (0-7) for packets.
                       The first bytes represent the COS for 802.1p
                       priority 0. Subsequent bytes represent the
                       mappings of the remaining 802.1p priorities."
        DEFVAL       { "00:00:02:04:00:06:06:07"  }
        ::= { rcTlsIpServiceEntry 16 }

rcTlsIpServicePriOverride  OBJECT-TYPE
        SYNTAX          TruthValue
        MAX-ACCESS      read-create
        STATUS          current
        DESCRIPTION     "Enable or disable to override the Priority Mapping."
        DEFVAL          { false }
        ::= { rcTlsIpServiceEntry 17 }

rcTlsIpServiceIpTblSize OBJECT-TYPE
        SYNTAX        INTEGER (0..97000) 
        MAX-ACCESS    read-create
        STATUS        obsolete
        DESCRIPTION   "The maximum size of the IP table. No limit if
                       it's set to 0."
        DEFVAL       { 0 }
        ::= { rcTlsIpServiceEntry 18 }

rcTlsIpServiceIpTblWaterMk OBJECT-TYPE
        SYNTAX        INTEGER (0..90)
        MAX-ACCESS    read-create
        STATUS        obsolete
        DESCRIPTION   "The Low Water Mark for Ip table size. Set to 90%
                       of the table size, can be over-written."
        DEFVAL       { 0 }
        ::= { rcTlsIpServiceEntry 19 }

rcTlsIpServiceIpTblMltId OBJECT-TYPE
        SYNTAX        INTEGER (0..256)
        MAX-ACCESS    read-create
        STATUS        current
        DESCRIPTION   "Mlt Id of the Ip Table"
        DEFVAL       { 0 }
        ::= { rcTlsIpServiceEntry 20 }
rcTlsIpServicePriOverrideType OBJECT-TYPE
        SYNTAX        INTEGER
                      {
                         tos(1),
                         dscp(2)
                      }
        MAX-ACCESS    read-create
        STATUS        current
        DESCRIPTION   "This field indicated whether ToS or DSCP should be
                       used to override P bit when override is enabled."
        DEFVAL        { tos }
        ::= { rcTlsIpServiceEntry 21 }

rcTlsIpServiceColorBasedRemarking OBJECT-TYPE
        SYNTAX        EnableValue
        MAX-ACCESS    read-create
        STATUS        current
        DESCRIPTION   "disable/enable color-based egress mapping for this
                      end-point."
        DEFVAL        { disable }
        ::= { rcTlsIpServiceEntry 22 }

rcTlsIpServiceDropRedColorPackets OBJECT-TYPE
        SYNTAX        TruthValue
        MAX-ACCESS    read-create
        STATUS        current
        DESCRIPTION   "disable/enable dropping of red-colored packets for
                      this end-point if color-based mapping is used."
        DEFVAL        { true }
        ::= { rcTlsIpServiceEntry 23 }

rcTlsIpServiceRingId OBJECT-TYPE
        SYNTAX      	INTEGER (0..254)
        MAX-ACCESS    	read-create
        STATUS        	current
        DESCRIPTION   	"Ring Id of the Ip table."
        ::= { rcTlsIpServiceEntry 24 }		    

rcTlsIpServiceModId OBJECT-TYPE
        SYNTAX      	Integer32 (0..30)
        MAX-ACCESS    	read-create
        STATUS        	current
        DESCRIPTION   	"RBS Module ID of the Ip table."
        ::= { rcTlsIpServiceEntry 25 }

rcTlsIpServiceEsuPort OBJECT-TYPE
        SYNTAX    	INTEGER (0..28)
        MAX-ACCESS    	read-create
        STATUS        	current
        DESCRIPTION   	"RBS port number of the Ip table."
        ::= { rcTlsIpServiceEntry 26 }	




-- rcTlsIpServiceStatsTable

rcTlsIpServiceStatsTable OBJECT-TYPE
        SYNTAX        SEQUENCE OF RcTlsIpServiceStatsEntry
        MAX-ACCESS    not-accessible
        STATUS        current
        DESCRIPTION   "Tls Ip service statistics table."
        ::= { rcTls 21 }
 
rcTlsIpServiceStatsEntry OBJECT-TYPE
        SYNTAX        RcTlsIpServiceStatsEntry
        MAX-ACCESS    not-accessible
        STATUS        current
        DESCRIPTION   "A Tls Ip Service Statistics table entry, which is used
                       for customer Ip Vlan Statistics"
        INDEX         { rcTlsIpServiceStatsTlsIndex, rcTlsIpServiceStatsCustIpVlan }
        ::= { rcTlsIpServiceStatsTable 1 }
 
RcTlsIpServiceStatsEntry ::=
        SEQUENCE { 
                rcTlsIpServiceStatsTlsIndex                     INTEGER,
                rcTlsIpServiceStatsCustIpVlan                   INTEGER,
                rcTlsIpServiceStatsPort                    InterfaceIndex,
                rcTlsIpServiceStatsPremRxOctets                 Counter64,    
                rcTlsIpServiceStatsPremRxDroppedOctets          Counter64,
                rcTlsIpServiceStatsGoldRxOctets                 Counter64,    
                rcTlsIpServiceStatsGoldRxDroppedOctets          Counter64,
                rcTlsIpServiceStatsSilverRxOctets               Counter64,    
                rcTlsIpServiceStatsSilverRxDroppedOctets        Counter64,
                rcTlsIpServiceStatsStndRxOctets                 Counter64,    
                rcTlsIpServiceStatsStndRxDroppedOctets          Counter64,
                rcTlsIpServiceStatsPremTxOctets                 Counter64,    
                rcTlsIpServiceStatsGoldTxOctets                 Counter64,  
                rcTlsIpServiceStatsSilverTxOctets               Counter64,
                rcTlsIpServiceStatsStndTxOctets                 Counter64,    
                rcTlsIpServiceStatsPremTxMcastOctets            Counter64,  
                rcTlsIpServiceStatsGoldTxMcastOctets            Counter64,  
                rcTlsIpServiceStatsSilverTxMcastOctets          Counter64,
                rcTlsIpServiceStatsStndTxMcastOctets            Counter64,
                rcTlsIpServiceStatsPremCongestionDropOctets     Counter64,
                rcTlsIpServiceStatsGoldCongestionDropOctets     Counter64,
                rcTlsIpServiceStatsSilverCongestionDropOctets   Counter64,    
                rcTlsIpServiceStatsStndCongestionDropOctets     Counter64,    
                rcTlsIpServiceStatsPremCirDroppedOctets         Counter64,
                rcTlsIpServiceStatsPremPirDroppedOctets         Counter64,
                rcTlsIpServiceStatsGoldCirDroppedOctets         Counter64,
                rcTlsIpServiceStatsGoldPirDroppedOctets         Counter64,
                rcTlsIpServiceStatsSilverCirDroppedOctets       Counter64,
                rcTlsIpServiceStatsSilverPirDroppedOctets       Counter64,
                rcTlsIpServiceStatsStndCirDroppedOctets         Counter64,
                rcTlsIpServiceStatsStndPirDroppedOctets         Counter64,
                rcTlsIpServiceStatsName                         DisplayString,
                rcTlsIpServiceStatsPremTxDroppedOctets          Counter64,    
                rcTlsIpServiceStatsGoldTxDroppedOctets          Counter64,   
                rcTlsIpServiceStatsSilverTxDroppedOctets        Counter64,
                rcTlsIpServiceStatsStndTxDroppedOctets          Counter64,    
                rcTlsIpServiceStatsPremTxCongestionDropOctets   Counter64,
                rcTlsIpServiceStatsGoldTxCongestionDropOctets   Counter64,
                rcTlsIpServiceStatsSilverTxCongestionDropOctets Counter64,   
                rcTlsIpServiceStatsStndTxCongestionDropOctets   Counter64,   
                rcTlsIpServiceStatsPremTxCirDroppedOctets       Counter64,
                rcTlsIpServiceStatsPremTxPirDroppedOctets       Counter64,
                rcTlsIpServiceStatsGoldTxCirDroppedOctets       Counter64,
                rcTlsIpServiceStatsGoldTxPirDroppedOctets       Counter64,
                rcTlsIpServiceStatsSilverTxCirDroppedOctets     Counter64,
                rcTlsIpServiceStatsSilverTxPirDroppedOctets     Counter64,
                rcTlsIpServiceStatsStndTxCirDroppedOctets       Counter64,
                rcTlsIpServiceStatsStndTxPirDroppedOctets       Counter64,
                rcTlsIpServiceStatsRxMcastTotalOctets           Counter64,
                rcTlsIpServiceStatsTxMcastTotalOctets           Counter64,
                rcTlsIpServiceStatsPremRxMcastDroppedOctets     Counter64,
                rcTlsIpServiceStatsGoldRxMcastDroppedOctets     Counter64,
                rcTlsIpServiceStatsSilverRxMcastDroppedOctets   Counter64,
                rcTlsIpServiceStatsStndRxMcastDroppedOctets     Counter64,
rcTlsIpServiceStatsPremRxFrames                 Counter64,
                rcTlsIpServiceStatsPremRxDroppedFrames          Counter64,
                rcTlsIpServiceStatsGoldRxFrames                 Counter64,
                rcTlsIpServiceStatsGoldRxDroppedFrames          Counter64,
                rcTlsIpServiceStatsSilverRxFrames               Counter64,
                rcTlsIpServiceStatsSilverRxDroppedFrames        Counter64,
                rcTlsIpServiceStatsStndRxFrames                 Counter64,
                rcTlsIpServiceStatsStndRxDroppedFrames          Counter64,
                rcTlsIpServiceStatsPremTxFrames                 Counter64,
                rcTlsIpServiceStatsGoldTxFrames                 Counter64,
                rcTlsIpServiceStatsSilverTxFrames               Counter64,
                rcTlsIpServiceStatsStndTxFrames                 Counter64,
                rcTlsIpServiceStatsPremTxMcastFrames            Counter64,
                rcTlsIpServiceStatsGoldTxMcastFrames            Counter64,
                rcTlsIpServiceStatsSilverTxMcastFrames          Counter64,
                rcTlsIpServiceStatsStndTxMcastFrames            Counter64,
                rcTlsIpServiceStatsPremCongestionDropFrames     Counter64,
                rcTlsIpServiceStatsGoldCongestionDropFrames     Counter64,
                rcTlsIpServiceStatsSilverCongestionDropFrames   Counter64,
                rcTlsIpServiceStatsStndCongestionDropFrames     Counter64,
                rcTlsIpServiceStatsPremCirDroppedFrames         Counter64,
                rcTlsIpServiceStatsPremPirDroppedFrames         Counter64,
                rcTlsIpServiceStatsGoldCirDroppedFrames         Counter64,
                rcTlsIpServiceStatsGoldPirDroppedFrames         Counter64,
                rcTlsIpServiceStatsSilverCirDroppedFrames       Counter64,
                rcTlsIpServiceStatsSilverPirDroppedFrames       Counter64,
                rcTlsIpServiceStatsStndCirDroppedFrames         Counter64,
                rcTlsIpServiceStatsStndPirDroppedFrames         Counter64,
                rcTlsIpServiceStatsPremTxDroppedFrames          Counter64,
                rcTlsIpServiceStatsGoldTxDroppedFrames          Counter64,
                rcTlsIpServiceStatsSilverTxDroppedFrames        Counter64,
                rcTlsIpServiceStatsStndTxDroppedFrames          Counter64,
                rcTlsIpServiceStatsPremTxCongestionDropFrames   Counter64,
                rcTlsIpServiceStatsGoldTxCongestionDropFrames   Counter64,
                rcTlsIpServiceStatsSilverTxCongestionDropFrames Counter64,
                rcTlsIpServiceStatsStndTxCongestionDropFrames   Counter64,
                rcTlsIpServiceStatsPremTxCirDroppedFrames       Counter64,
                rcTlsIpServiceStatsPremTxPirDroppedFrames       Counter64,
                rcTlsIpServiceStatsGoldTxCirDroppedFrames       Counter64,
                rcTlsIpServiceStatsGoldTxPirDroppedFrames       Counter64,
                rcTlsIpServiceStatsSilverTxCirDroppedFrames     Counter64,
                rcTlsIpServiceStatsSilverTxPirDroppedFrames     Counter64,
                rcTlsIpServiceStatsStndTxCirDroppedFrames       Counter64,
                rcTlsIpServiceStatsStndTxPirDroppedFrames       Counter64,
                rcTlsIpServiceStatsRxMcastTotalFrames           Counter64,
                rcTlsIpServiceStatsTxMcastTotalFrames           Counter64,
                rcTlsIpServiceStatsPremRxMcastDroppedFrames     Counter64,
                rcTlsIpServiceStatsGoldRxMcastDroppedFrames     Counter64,
                rcTlsIpServiceStatsSilverRxMcastDroppedFrames   Counter64,
                rcTlsIpServiceStatsStndRxMcastDroppedFrames     Counter64,
	rcTlsIpServiceStatsPremRxCirOctets			Counter64,
	rcTlsIpServiceStatsPremRxCirOopOctets			Counter64,
	rcTlsIpServiceStatsPremRxEirOctets			Counter64,
	rcTlsIpServiceStatsPremRxEirOopOctets			Counter64,
	rcTlsIpServiceStatsPremRxEirDroppedOctets		Counter64,
	rcTlsIpServiceStatsPremRxPirOctets			Counter64,
	rcTlsIpServiceStatsPremRxPirOopOctets			Counter64,
	rcTlsIpServiceStatsPremRxGreenOctets			Counter64,
	rcTlsIpServiceStatsPremRxYellowOctets			Counter64,
	rcTlsIpServiceStatsPremRxRedOctets			Counter64,
	rcTlsIpServiceStatsGoldRxCirOctets			Counter64,
	rcTlsIpServiceStatsGoldRxCirOopOctets			Counter64,
	rcTlsIpServiceStatsGoldRxEirOctets			Counter64,
	rcTlsIpServiceStatsGoldRxEirOopOctets			Counter64,
	rcTlsIpServiceStatsGoldRxEirDroppedOctets		Counter64,
	rcTlsIpServiceStatsGoldRxPirOctets			Counter64,
	rcTlsIpServiceStatsGoldRxPirOopOctets			Counter64,
	rcTlsIpServiceStatsGoldRxGreenOctets			Counter64,
	rcTlsIpServiceStatsGoldRxYellowOctets			Counter64,
	rcTlsIpServiceStatsGoldRxRedOctets			Counter64,
	rcTlsIpServiceStatsSilverRxCirOctets			Counter64,
	rcTlsIpServiceStatsSilverRxCirOopOctets			Counter64,
	rcTlsIpServiceStatsSilverRxEirOctets			Counter64,
	rcTlsIpServiceStatsSilverRxEirOopOctets			Counter64,
	rcTlsIpServiceStatsSilverRxEirDroppedOctets		Counter64,
	rcTlsIpServiceStatsSilverRxPirOctets			Counter64,
	rcTlsIpServiceStatsSilverRxPirOopOctets			Counter64,
	rcTlsIpServiceStatsSilverRxGreenOctets			Counter64,
	rcTlsIpServiceStatsSilverRxYellowOctets			Counter64,
	rcTlsIpServiceStatsSilverRxRedOctets			Counter64,
	rcTlsIpServiceStatsStndRxCirOctets			Counter64,
	rcTlsIpServiceStatsStndRxCirOopOctets			Counter64,
	rcTlsIpServiceStatsStndRxEirOctets			Counter64,
	rcTlsIpServiceStatsStndRxEirOopOctets			Counter64,
	rcTlsIpServiceStatsStndRxEirDroppedOctets		Counter64,
	rcTlsIpServiceStatsStndRxPirOctets			Counter64,
	rcTlsIpServiceStatsStndRxPirOopOctets			Counter64,
	rcTlsIpServiceStatsStndRxGreenOctets			Counter64,
	rcTlsIpServiceStatsStndRxYellowOctets			Counter64,
	rcTlsIpServiceStatsStndRxRedOctets			Counter64,
	rcTlsIpServiceStatsMcastRxDroppedOctets		Counter64,
	rcTlsIpServiceStatsBcastUUcastRxTotalOctets		Counter64,
	rcTlsIpServiceStatsBcastUUcastRxDroppedOctets		Counter64,
	rcTlsIpServiceStatsPremRxCirFrames			Counter64,
	rcTlsIpServiceStatsPremRxCirOopFrames		Counter64,
	rcTlsIpServiceStatsPremRxEirFrames			Counter64,
	rcTlsIpServiceStatsPremRxEirOopFrames			Counter64,
	rcTlsIpServiceStatsPremRxEirDroppedFrames		Counter64,
	rcTlsIpServiceStatsPremRxPirFrames			Counter64,
	rcTlsIpServiceStatsPremRxPirOopFrames			Counter64,
	rcTlsIpServiceStatsPremRxGreenFrames			Counter64,
	rcTlsIpServiceStatsPremRxYellowFrames			Counter64,
	rcTlsIpServiceStatsPremRxRedFrames			Counter64,
	rcTlsIpServiceStatsGoldRxCirFrames			Counter64,
	rcTlsIpServiceStatsGoldRxCirOopFrames			Counter64,
	rcTlsIpServiceStatsGoldRxEirFrames			Counter64,
	rcTlsIpServiceStatsGoldRxEirOopFrames			Counter64,
	rcTlsIpServiceStatsGoldRxEirDroppedFrames		Counter64,
	rcTlsIpServiceStatsGoldRxPirFrames			Counter64,
	rcTlsIpServiceStatsGoldRxPirOopFrames			Counter64,
	rcTlsIpServiceStatsGoldRxGreenFrames			Counter64,
	rcTlsIpServiceStatsGoldRxYellowFrames			Counter64,
	rcTlsIpServiceStatsGoldRxRedFrames			Counter64,
	rcTlsIpServiceStatsSilverRxCirFrames			Counter64,
	rcTlsIpServiceStatsSilverRxCirOopFrames		Counter64,
	rcTlsIpServiceStatsSilverRxEirFrames			Counter64,
	rcTlsIpServiceStatsSilverRxEirOopFrames		Counter64,
	rcTlsIpServiceStatsSilverRxEirDroppedFrames		Counter64,
	rcTlsIpServiceStatsSilverRxPirFrames			Counter64,
	rcTlsIpServiceStatsSilverRxPirOopFrames		Counter64,
	rcTlsIpServiceStatsSilverRxGreenFrames			Counter64,
	rcTlsIpServiceStatsSilverRxYellowFrames			Counter64,
	rcTlsIpServiceStatsSilverRxRedFrames			Counter64,
	rcTlsIpServiceStatsStndRxCirFrames			Counter64,
	rcTlsIpServiceStatsStndRxCirOopFrames			Counter64,
	rcTlsIpServiceStatsStndRxEirFrames			Counter64,
	rcTlsIpServiceStatsStndRxEirOopFrames			Counter64,
	rcTlsIpServiceStatsStndRxEirDroppedFrames		Counter64,
	rcTlsIpServiceStatsStndRxPirFrames			Counter64,
	rcTlsIpServiceStatsStndRxPirOopFrames			Counter64,
	rcTlsIpServiceStatsStndRxGreenFrames			Counter64,
	rcTlsIpServiceStatsStndRxYellowFrames			Counter64,
	rcTlsIpServiceStatsStndRxRedFrames			Counter64,
	rcTlsIpServiceStatsMcastRxDroppedFrames		Counter64,
	rcTlsIpServiceStatsBcastUUcastRxTotalFrames		Counter64,
	rcTlsIpServiceStatsBcastUUcastRxDroppedFrames		Counter64,
	rcTlsIpServiceStatsPremTxCirOctets			Counter64,
	rcTlsIpServiceStatsPremTxCirOopOctets			Counter64,
	rcTlsIpServiceStatsPremTxEirOctets			Counter64,
	rcTlsIpServiceStatsPremTxEirOopOctets			Counter64,
	rcTlsIpServiceStatsPremTxEirDroppedOctets		Counter64,
	rcTlsIpServiceStatsPremTxPirOctets			Counter64,
	rcTlsIpServiceStatsPremTxPirOopOctets			Counter64,
	rcTlsIpServiceStatsPremTxGreenOctets			Counter64,
	rcTlsIpServiceStatsPremTxYellowOctets			Counter64,
	rcTlsIpServiceStatsPremTxRedOctets			Counter64,
	rcTlsIpServiceStatsGoldTxCirOctets			Counter64,
	rcTlsIpServiceStatsGoldTxCirOopOctets			Counter64,
	rcTlsIpServiceStatsGoldTxEirOctets			Counter64,
	rcTlsIpServiceStatsGoldTxEirOopOctets			Counter64,
	rcTlsIpServiceStatsGoldTxEirDroppedOctets		Counter64,
	rcTlsIpServiceStatsGoldTxPirOctets			Counter64,
	rcTlsIpServiceStatsGoldTxPirOopOctets			Counter64,
	rcTlsIpServiceStatsGoldTxGreenOctets			Counter64,
	rcTlsIpServiceStatsGoldTxYellowOctets			Counter64,
	rcTlsIpServiceStatsGoldTxRedOctets			Counter64,
	rcTlsIpServiceStatsSilverTxCirOctets			Counter64,
	rcTlsIpServiceStatsSilverTxCirOopOctets			Counter64,
	rcTlsIpServiceStatsSilverTxEirOctets			Counter64,
	rcTlsIpServiceStatsSilverTxEirOopOctets			Counter64,
	rcTlsIpServiceStatsSilverTxEirDroppedOctets		Counter64,
	rcTlsIpServiceStatsSilverTxPirOctets			Counter64,
	rcTlsIpServiceStatsSilverTxPirOopOctets			Counter64,
	rcTlsIpServiceStatsSilverTxGreenOctets			Counter64,
	rcTlsIpServiceStatsSilverTxYellowOctets			Counter64,
	rcTlsIpServiceStatsSilverTxRedOctets			Counter64,
	rcTlsIpServiceStatsStndTxCirOctets			Counter64,
	rcTlsIpServiceStatsStndTxCirOopOctets			Counter64,
	rcTlsIpServiceStatsStndTxEirOctets			Counter64,
	rcTlsIpServiceStatsStndTxEirOopOctets			Counter64,
	rcTlsIpServiceStatsStndTxEirDroppedOctets		Counter64,
	rcTlsIpServiceStatsStndTxPirOctets			Counter64,
	rcTlsIpServiceStatsStndTxPirOopOctets			Counter64,
	rcTlsIpServiceStatsStndTxGreenOctets			Counter64,
	rcTlsIpServiceStatsStndTxYellowOctets			Counter64,
	rcTlsIpServiceStatsStndTxRedOctets			Counter64,
	rcTlsIpServiceStatsMcastTxDroppedOctets		Counter64,
	rcTlsIpServiceStatsBcastUUcastTxTotalOctets		Counter64,
	rcTlsIpServiceStatsBcastUUcastTxDroppedOctets		Counter64,
	rcTlsIpServiceStatsPremTxCirFrames			Counter64,
	rcTlsIpServiceStatsPremTxCirOopFrames			Counter64,
	rcTlsIpServiceStatsPremTxEirFrames			Counter64,
	rcTlsIpServiceStatsPremTxEirOopFrames			Counter64,
	rcTlsIpServiceStatsPremTxEirDroppedFrames		Counter64,
	rcTlsIpServiceStatsPremTxPirFrames			Counter64,
	rcTlsIpServiceStatsPremTxPirOopFrames			Counter64,
	rcTlsIpServiceStatsPremTxGreenFrames			Counter64,
	rcTlsIpServiceStatsPremTxYellowFrames			Counter64,
	rcTlsIpServiceStatsPremTxRedFrames			Counter64,
	rcTlsIpServiceStatsGoldTxCirFrames			Counter64,
	rcTlsIpServiceStatsGoldTxCirOopFrames			Counter64,
	rcTlsIpServiceStatsGoldTxEirFrames			Counter64,
	rcTlsIpServiceStatsGoldTxEirOopFrames			Counter64,
	rcTlsIpServiceStatsGoldTxEirDroppedFrames		Counter64,
	rcTlsIpServiceStatsGoldTxPirFrames			Counter64,
	rcTlsIpServiceStatsGoldTxPirOopFrames			Counter64,
	rcTlsIpServiceStatsGoldTxGreenFrames			Counter64,
	rcTlsIpServiceStatsGoldTxYellowFrames			Counter64,
	rcTlsIpServiceStatsGoldTxRedFrames			Counter64,
	rcTlsIpServiceStatsSilverTxCirFrames			Counter64,
	rcTlsIpServiceStatsSilverTxCirOopFrames		Counter64,
	rcTlsIpServiceStatsSilverTxEirFrames			Counter64,
	rcTlsIpServiceStatsSilverTxEirOopFrames		Counter64,
	rcTlsIpServiceStatsSilverTxEirDroppedFrames		Counter64,
	rcTlsIpServiceStatsSilverTxPirFrames			Counter64,
	rcTlsIpServiceStatsSilverTxPirOopFrames		Counter64,
	rcTlsIpServiceStatsSilverTxGreenFrames			Counter64,
	rcTlsIpServiceStatsSilverTxYellowFrames			Counter64,
	rcTlsIpServiceStatsSilverTxRedFrames			Counter64,
	rcTlsIpServiceStatsStndTxCirFrames			Counter64,
	rcTlsIpServiceStatsStndTxCirOopFrames			Counter64,
	rcTlsIpServiceStatsStndTxEirFrames			Counter64,
	rcTlsIpServiceStatsStndTxEirOopFrames			Counter64,
	rcTlsIpServiceStatsStndTxEirDroppedFrames		Counter64,
	rcTlsIpServiceStatsStndTxPirFrames			Counter64,
	rcTlsIpServiceStatsStndTxPirOopFrames			Counter64,
	rcTlsIpServiceStatsStndTxGreenFrames			Counter64,
	rcTlsIpServiceStatsStndTxYellowFrames			Counter64,
	rcTlsIpServiceStatsStndTxRedFrames			Counter64,
	rcTlsIpServiceStatsMcastTxDroppedFrames		Counter64,
	rcTlsIpServiceStatsBcastUUcastTxTotalFrames		Counter64,
	rcTlsIpServiceStatsBcastUUcastTxDroppedFrames		Counter64,
	rcTlsIpServiceStatsDropClassRxDroppedOctets  		Counter64,
	rcTlsIpServiceStatsDropClassRxDroppedFrames  		Counter64,
	rcTlsIpServiceStatsDropClassTxDroppedOctets  		Counter64,
	rcTlsIpServiceStatsDropClassTxDroppedFrames  		Counter64
      }

rcTlsIpServiceStatsTlsIndex OBJECT-TYPE
        SYNTAX        INTEGER (1..2147483647)
        MAX-ACCESS    not-accessible
        STATUS        current
        DESCRIPTION   "TLS Index"
        ::= { rcTlsIpServiceStatsEntry 1}

rcTlsIpServiceStatsCustIpVlan OBJECT-TYPE
        SYNTAX        INTEGER (1..4096)
        MAX-ACCESS    not-accessible
        STATUS        current
        DESCRIPTION   "Customer IP Vlan for IP Vlan mapping"
        ::= { rcTlsIpServiceStatsEntry 2 }
 
rcTlsIpServiceStatsPort OBJECT-TYPE
        SYNTAX        InterfaceIndex
        MAX-ACCESS    read-only
        STATUS        current
        DESCRIPTION   "Customer IP Vlan Port"
        ::= { rcTlsIpServiceStatsEntry 3 }

rcTlsIpServiceStatsPremRxOctets      OBJECT-TYPE
        SYNTAX        Counter64
        MAX-ACCESS    read-only
        STATUS        current
        DESCRIPTION  "Number of Premium ServiceStats Octets received."
        ::= { rcTlsIpServiceStatsEntry 4 } 

rcTlsIpServiceStatsPremRxDroppedOctets       OBJECT-TYPE
        SYNTAX        Counter64
        MAX-ACCESS    read-only
        STATUS        current
        DESCRIPTION  "Number of Premium ServiceStats Octets dropped."
        ::= { rcTlsIpServiceStatsEntry 5 } 
       
rcTlsIpServiceStatsGoldRxOctets      OBJECT-TYPE
        SYNTAX        Counter64
        MAX-ACCESS    read-only
        STATUS        current
        DESCRIPTION  "Number of Gold ServiceStats Octets received."
        ::= { rcTlsIpServiceStatsEntry 6 } 

rcTlsIpServiceStatsGoldRxDroppedOctets       OBJECT-TYPE
        SYNTAX        Counter64
        MAX-ACCESS    read-only
        STATUS        current
        DESCRIPTION  "Number of Gold ServiceStats Octets dropped."
        ::= { rcTlsIpServiceStatsEntry 7 } 
       
rcTlsIpServiceStatsSilverRxOctets    OBJECT-TYPE
        SYNTAX        Counter64
        MAX-ACCESS    read-only
        STATUS        current
        DESCRIPTION  "Number of Silver ServiceStats Octets received."
        ::= { rcTlsIpServiceStatsEntry 8 } 

rcTlsIpServiceStatsSilverRxDroppedOctets     OBJECT-TYPE
        SYNTAX        Counter64
        MAX-ACCESS    read-only
        STATUS        current
        DESCRIPTION  "Number of Silver ServiceStats Octets dropped."
        ::= { rcTlsIpServiceStatsEntry 9 } 
       
rcTlsIpServiceStatsStndRxOctets      OBJECT-TYPE
        SYNTAX        Counter64
        MAX-ACCESS    read-only
        STATUS        current
        DESCRIPTION  "Number of Standard ServiceStats Octets received."
        ::= { rcTlsIpServiceStatsEntry 10 } 

rcTlsIpServiceStatsStndRxDroppedOctets       OBJECT-TYPE
        SYNTAX        Counter64
        MAX-ACCESS    read-only
        STATUS        current
        DESCRIPTION  "Number of Standard ServiceStats Octets dropped."
        ::= { rcTlsIpServiceStatsEntry 11 } 
       
rcTlsIpServiceStatsPremTxOctets      OBJECT-TYPE
        SYNTAX        Counter64
        MAX-ACCESS    read-only
        STATUS        current
        DESCRIPTION  "Number of Premium ServiceStats Octets sent."
        ::= { rcTlsIpServiceStatsEntry 12 } 

rcTlsIpServiceStatsGoldTxOctets      OBJECT-TYPE
        SYNTAX        Counter64
        MAX-ACCESS    read-only
        STATUS        current
        DESCRIPTION  "Number of Gold ServiceStats Octets sent."
        ::= { rcTlsIpServiceStatsEntry 13 } 

rcTlsIpServiceStatsSilverTxOctets    OBJECT-TYPE
        SYNTAX        Counter64
        MAX-ACCESS    read-only
        STATUS        current
        DESCRIPTION  "Number of Silver ServiceStats Octets sent."
        ::= { rcTlsIpServiceStatsEntry 14 } 

rcTlsIpServiceStatsStndTxOctets      OBJECT-TYPE
        SYNTAX        Counter64
        MAX-ACCESS    read-only
        STATUS        current
        DESCRIPTION  "Number of Standard ServiceStats Octets sent."
        ::= { rcTlsIpServiceStatsEntry 15 }
                

rcTlsIpServiceStatsPremTxMcastOctets OBJECT-TYPE
        SYNTAX        Counter64
        MAX-ACCESS    read-only
        STATUS        current
        DESCRIPTION  "Number of Premium ServiceStats Multicast sent."
        ::= { rcTlsIpServiceStatsEntry 16 } 

rcTlsIpServiceStatsGoldTxMcastOctets OBJECT-TYPE
        SYNTAX        Counter64
        MAX-ACCESS    read-only
        STATUS        current
        DESCRIPTION  "Number of GoldServiceStats Multicast sent."
        ::= { rcTlsIpServiceStatsEntry 17 } 
                
rcTlsIpServiceStatsSilverTxMcastOctets       OBJECT-TYPE
        SYNTAX        Counter64
        MAX-ACCESS    read-only
        STATUS        current
        DESCRIPTION  "Number of SilverServiceStats Multicast sent."
        ::= { rcTlsIpServiceStatsEntry 18 } 

rcTlsIpServiceStatsStndTxMcastOctets OBJECT-TYPE
        SYNTAX        Counter64
        MAX-ACCESS    read-only
        STATUS        current 
        DESCRIPTION  "Number of Premium ServiceStats Multicast sent.."
        ::= { rcTlsIpServiceStatsEntry 19 }

rcTlsIpServiceStatsPremCongestionDropOctets  OBJECT-TYPE
        SYNTAX        Counter64
        MAX-ACCESS    read-only
        STATUS        current
        DESCRIPTION  "Number of Prem ServiceStats Octets congestion dropped"
        ::= { rcTlsIpServiceStatsEntry 20 } 
       
rcTlsIpServiceStatsGoldCongestionDropOctets  OBJECT-TYPE
        SYNTAX        Counter64
        MAX-ACCESS    read-only
        STATUS        current
        DESCRIPTION  "Number of Gold ServiceStats Octets congestion dropped"
        ::= { rcTlsIpServiceStatsEntry 21 } 

rcTlsIpServiceStatsSilverCongestionDropOctets        OBJECT-TYPE
        SYNTAX        Counter64
        MAX-ACCESS    read-only
        STATUS        current
        DESCRIPTION  "Number of Silver ServiceStats Octets congestion dropped"
        ::= { rcTlsIpServiceStatsEntry 22 } 

rcTlsIpServiceStatsStndCongestionDropOctets  OBJECT-TYPE
        SYNTAX        Counter64
        MAX-ACCESS    read-only
        STATUS        current
        DESCRIPTION  "Number of Stnd ServiceStats congestion Octets dropped"
        ::= { rcTlsIpServiceStatsEntry 23 }

rcTlsIpServiceStatsPremCirDroppedOctets      OBJECT-TYPE
        SYNTAX        Counter64
        MAX-ACCESS    read-only
        STATUS        current
        DESCRIPTION  "Number of Prem ServiceStats CIR Octets dropped"
        ::= { rcTlsIpServiceStatsEntry 24 }

rcTlsIpServiceStatsPremPirDroppedOctets      OBJECT-TYPE
        SYNTAX        Counter64
        MAX-ACCESS    read-only
        STATUS        current
        DESCRIPTION  "Number of Prem ServiceStats PIR Octets dropped"
        ::= { rcTlsIpServiceStatsEntry 25 }
  
rcTlsIpServiceStatsGoldCirDroppedOctets      OBJECT-TYPE
        SYNTAX        Counter64
        MAX-ACCESS    read-only
        STATUS        current
        DESCRIPTION  "Number of Gold ServiceStats CIR Octets dropped"
        ::= { rcTlsIpServiceStatsEntry 26 }

rcTlsIpServiceStatsGoldPirDroppedOctets      OBJECT-TYPE
        SYNTAX        Counter64
        MAX-ACCESS    read-only
        STATUS        current
        DESCRIPTION  "Number of Gold ServiceStats PIR Octets dropped"
        ::= { rcTlsIpServiceStatsEntry 27 }

rcTlsIpServiceStatsSilverCirDroppedOctets    OBJECT-TYPE
        SYNTAX        Counter64
        MAX-ACCESS    read-only
        STATUS        current
        DESCRIPTION  "Number of Silver ServiceStats CIR Octets dropped."
        ::= { rcTlsIpServiceStatsEntry 28 }

rcTlsIpServiceStatsSilverPirDroppedOctets    OBJECT-TYPE
        SYNTAX        Counter64
        MAX-ACCESS    read-only
        STATUS        current
        DESCRIPTION  "Number of Silver ServiceStats PIR Octets dropped"
        ::= { rcTlsIpServiceStatsEntry 29 }

rcTlsIpServiceStatsStndCirDroppedOctets      OBJECT-TYPE
        SYNTAX        Counter64
        MAX-ACCESS    read-only
        STATUS        current
        DESCRIPTION  "Number of Standard ServiceStats CIR Octets dropped"
        ::= { rcTlsIpServiceStatsEntry 30 }  

rcTlsIpServiceStatsStndPirDroppedOctets      OBJECT-TYPE
        SYNTAX        Counter64
        MAX-ACCESS    read-only
        STATUS        current
        DESCRIPTION  "Number of Standard ServiceStats PIR Octets dropped"
        ::= { rcTlsIpServiceStatsEntry 31 } 
 
rcTlsIpServiceStatsName OBJECT-TYPE
        SYNTAX        DisplayString (SIZE (0..30)) 
        MAX-ACCESS    read-only
        STATUS        current
        DESCRIPTION   "Name of IP Service Vlan Entry."
        ::= { rcTlsIpServiceStatsEntry 32 }

rcTlsIpServiceStatsPremTxDroppedOctets       OBJECT-TYPE
        SYNTAX        Counter64
        MAX-ACCESS    read-only
        STATUS        current
        DESCRIPTION  "Tx Number of Premium ServiceStats Octets dropped."
        ::= { rcTlsIpServiceStatsEntry 33 } 

rcTlsIpServiceStatsGoldTxDroppedOctets       OBJECT-TYPE
        SYNTAX        Counter64
        MAX-ACCESS    read-only
        STATUS        current
        DESCRIPTION  "Tx Number of Gold ServiceStats Octets dropped."
        ::= { rcTlsIpServiceStatsEntry 34 } 
       
rcTlsIpServiceStatsSilverTxDroppedOctets     OBJECT-TYPE
        SYNTAX        Counter64
        MAX-ACCESS    read-only
        STATUS        current
        DESCRIPTION  "Tx Number of Silver ServiceStats Octets dropped."
        ::= { rcTlsIpServiceStatsEntry 35 }
       
rcTlsIpServiceStatsStndTxDroppedOctets       OBJECT-TYPE
        SYNTAX        Counter64
        MAX-ACCESS    read-only
        STATUS        current
        DESCRIPTION  "Tx Number of Standard ServiceStats Octets dropped."
        ::= { rcTlsIpServiceStatsEntry 36 } 

rcTlsIpServiceStatsPremTxCongestionDropOctets        OBJECT-TYPE
        SYNTAX        Counter64
        MAX-ACCESS    read-only
        STATUS        current
        DESCRIPTION  "Tx Nbr of Prem ServiceStats Octets congestion dropped."
        ::= { rcTlsIpServiceStatsEntry 37 } 
       
rcTlsIpServiceStatsGoldTxCongestionDropOctets        OBJECT-TYPE
        SYNTAX        Counter64
        MAX-ACCESS    read-only
        STATUS        current
        DESCRIPTION  "Tx Nbr of Gold ServiceStats Octets congestion dropped."
        ::= { rcTlsIpServiceStatsEntry 38 } 

rcTlsIpServiceStatsSilverTxCongestionDropOctets      OBJECT-TYPE
        SYNTAX        Counter64
        MAX-ACCESS    read-only
        STATUS        current
        DESCRIPTION  "Tx Nbr Silver ServiceStats Octets congestion dropped."
        ::= { rcTlsIpServiceStatsEntry 39 } 

rcTlsIpServiceStatsStndTxCongestionDropOctets        OBJECT-TYPE
        SYNTAX        Counter64
        MAX-ACCESS    read-only
        STATUS        current
        DESCRIPTION  "Tx Nbr Standard ServiceStats Octets congestion dropped."
        ::= { rcTlsIpServiceStatsEntry 40 }

rcTlsIpServiceStatsPremTxCirDroppedOctets    OBJECT-TYPE
        SYNTAX        Counter64
        MAX-ACCESS    read-only
        STATUS        current
        DESCRIPTION  "Tx Number of Prem ServiceStats CIR Octets dropped."
        ::= { rcTlsIpServiceStatsEntry 41 }

rcTlsIpServiceStatsPremTxPirDroppedOctets    OBJECT-TYPE
        SYNTAX        Counter64
        MAX-ACCESS    read-only
        STATUS        current
        DESCRIPTION  "Tx Number of Prem ServiceStats PIR Octets dropped."
        ::= { rcTlsIpServiceStatsEntry 42 }
  
rcTlsIpServiceStatsGoldTxCirDroppedOctets    OBJECT-TYPE
        SYNTAX        Counter64
        MAX-ACCESS    read-only
        STATUS        current
        DESCRIPTION  "Tx Number of Gold ServiceStats CIR Octets dropped."
        ::= { rcTlsIpServiceStatsEntry 43 }

rcTlsIpServiceStatsGoldTxPirDroppedOctets    OBJECT-TYPE
        SYNTAX        Counter64
        MAX-ACCESS    read-only
        STATUS        current
        DESCRIPTION  "Tx Number of Gold ServiceStats PIR Octets dropped."
        ::= { rcTlsIpServiceStatsEntry 44 }

rcTlsIpServiceStatsSilverTxCirDroppedOctets  OBJECT-TYPE
        SYNTAX        Counter64
        MAX-ACCESS    read-only
        STATUS        current
        DESCRIPTION  "Tx Number of Silver ServiceStats CIR Octets dropped"
        ::= { rcTlsIpServiceStatsEntry 45 }

rcTlsIpServiceStatsSilverTxPirDroppedOctets  OBJECT-TYPE
        SYNTAX        Counter64
        MAX-ACCESS    read-only
        STATUS        current   
        DESCRIPTION  "Tx Number of Silver ServiceStats PIR Octets dropped."
        ::= { rcTlsIpServiceStatsEntry 46 }

rcTlsIpServiceStatsStndTxCirDroppedOctets    OBJECT-TYPE
        SYNTAX        Counter64
        MAX-ACCESS    read-only
        STATUS        current
        DESCRIPTION  "Tx Number of Standard ServiceStats CIR Octets dropped."
        ::= { rcTlsIpServiceStatsEntry 47 }  

rcTlsIpServiceStatsStndTxPirDroppedOctets    OBJECT-TYPE
        SYNTAX        Counter64
        MAX-ACCESS    read-only
        STATUS        current
        DESCRIPTION  "TX Number of Standard ServiceStats PIR Octets dropped."
        ::= { rcTlsIpServiceStatsEntry 48 }
 
rcTlsIpServiceStatsRxMcastTotalOctets        OBJECT-TYPE
        SYNTAX        Counter64
        MAX-ACCESS    read-only
        STATUS        current
        DESCRIPTION  "Rx Total Number of Mcast Octets"
        ::= { rcTlsIpServiceStatsEntry 49 }
 
rcTlsIpServiceStatsTxMcastTotalOctets        OBJECT-TYPE
        SYNTAX        Counter64
        MAX-ACCESS    read-only
        STATUS        current
        DESCRIPTION  "Tx total Number of Mcast Octets"
        ::= { rcTlsIpServiceStatsEntry 50 } 

rcTlsIpServiceStatsPremRxMcastDroppedOctets  OBJECT-TYPE
        SYNTAX        Counter64
        MAX-ACCESS    read-only
        STATUS        current
        DESCRIPTION  "Number of Premium Service Rx Mcast Octets dropped."
        ::= { rcTlsIpServiceStatsEntry 51 } 

rcTlsIpServiceStatsGoldRxMcastDroppedOctets  OBJECT-TYPE
        SYNTAX        Counter64
        MAX-ACCESS    read-only
        STATUS        current
        DESCRIPTION  "Number of Gold Service Rx Mcast Octets dropped."
        ::= { rcTlsIpServiceStatsEntry 52 } 

rcTlsIpServiceStatsSilverRxMcastDroppedOctets        OBJECT-TYPE
        SYNTAX        Counter64
        MAX-ACCESS    read-only
        STATUS        current
        DESCRIPTION  "Number of Silver Service Rx Mcast Octets dropped."
        ::= { rcTlsIpServiceStatsEntry 53 } 
                            
rcTlsIpServiceStatsStndRxMcastDroppedOctets  OBJECT-TYPE
        SYNTAX        Counter64
        MAX-ACCESS    read-only
        STATUS        current
        DESCRIPTION  "Number of Standard Service Rx Mcast Octets dropped."
        ::= { rcTlsIpServiceStatsEntry 54 } 

rcTlsIpServiceStatsPremRxFrames      OBJECT-TYPE
        SYNTAX        Counter64
        MAX-ACCESS    read-only
        STATUS        current
        DESCRIPTION  "Number of Premium ServiceStats Frames received."
        ::= { rcTlsIpServiceStatsEntry 55 }

rcTlsIpServiceStatsPremRxDroppedFrames       OBJECT-TYPE
        SYNTAX        Counter64
        MAX-ACCESS    read-only
        STATUS        current
        DESCRIPTION  "Number of Premium ServiceStats Frames dropped."
        ::= { rcTlsIpServiceStatsEntry 56 }

rcTlsIpServiceStatsGoldRxFrames      OBJECT-TYPE
        SYNTAX        Counter64
        MAX-ACCESS    read-only
        STATUS        current
        DESCRIPTION  "Number of Gold ServiceStats Frames received."
        ::= { rcTlsIpServiceStatsEntry 57 }

rcTlsIpServiceStatsGoldRxDroppedFrames       OBJECT-TYPE
        SYNTAX        Counter64
        MAX-ACCESS    read-only
        STATUS        current
        DESCRIPTION  "Number of Gold ServiceStats Frames dropped."
        ::= { rcTlsIpServiceStatsEntry 58 }

rcTlsIpServiceStatsSilverRxFrames    OBJECT-TYPE
        SYNTAX        Counter64
        MAX-ACCESS    read-only
        STATUS        current
        DESCRIPTION  "Number of Silver ServiceStats Frames received."
        ::= { rcTlsIpServiceStatsEntry 59 }

rcTlsIpServiceStatsSilverRxDroppedFrames     OBJECT-TYPE
        SYNTAX        Counter64
        MAX-ACCESS    read-only
        STATUS        current
        DESCRIPTION  "Number of Silver ServiceStats Frames dropped."
        ::= { rcTlsIpServiceStatsEntry 60 }

rcTlsIpServiceStatsStndRxFrames      OBJECT-TYPE
        SYNTAX        Counter64
        MAX-ACCESS    read-only
        STATUS        current
        DESCRIPTION  "Number of Standard ServiceStats Frames received."
        ::= { rcTlsIpServiceStatsEntry 61 }

rcTlsIpServiceStatsStndRxDroppedFrames       OBJECT-TYPE
        SYNTAX        Counter64
        MAX-ACCESS    read-only
        STATUS        current
        DESCRIPTION  "Number of Standard ServiceStats Frames dropped."
        ::= { rcTlsIpServiceStatsEntry 62 }

rcTlsIpServiceStatsPremTxFrames      OBJECT-TYPE
        SYNTAX        Counter64
        MAX-ACCESS    read-only
        STATUS        current
        DESCRIPTION  "Number of Premium ServiceStats Frames sent."
        ::= { rcTlsIpServiceStatsEntry 63 }

rcTlsIpServiceStatsGoldTxFrames      OBJECT-TYPE
        SYNTAX        Counter64
        MAX-ACCESS    read-only
        STATUS        current
        DESCRIPTION  "Number of Gold ServiceStats Frames sent."
        ::= { rcTlsIpServiceStatsEntry 64 }

rcTlsIpServiceStatsSilverTxFrames    OBJECT-TYPE
        SYNTAX        Counter64
        MAX-ACCESS    read-only
        STATUS        current
        DESCRIPTION  "Number of Silver ServiceStats Frames sent."
        ::= { rcTlsIpServiceStatsEntry 65 }

rcTlsIpServiceStatsStndTxFrames      OBJECT-TYPE
        SYNTAX        Counter64
        MAX-ACCESS    read-only
        STATUS        current
        DESCRIPTION  "Number of Standard ServiceStats Frames sent."
        ::= { rcTlsIpServiceStatsEntry 66 }

rcTlsIpServiceStatsPremTxMcastFrames OBJECT-TYPE
        SYNTAX        Counter64
        MAX-ACCESS    read-only
        STATUS        current
        DESCRIPTION  "Number of Premium ServiceStats Multicast sent."
        ::= { rcTlsIpServiceStatsEntry 67 }

rcTlsIpServiceStatsGoldTxMcastFrames OBJECT-TYPE
        SYNTAX        Counter64
        MAX-ACCESS    read-only
        STATUS        current
        DESCRIPTION  "Number of GoldServiceStats Multicast sent."
        ::= { rcTlsIpServiceStatsEntry 68 }

rcTlsIpServiceStatsSilverTxMcastFrames       OBJECT-TYPE
        SYNTAX        Counter64
        MAX-ACCESS    read-only
        STATUS        current
        DESCRIPTION  "Number of SilverServiceStats Multicast sent."
        ::= { rcTlsIpServiceStatsEntry 69 }

rcTlsIpServiceStatsStndTxMcastFrames OBJECT-TYPE
        SYNTAX        Counter64
        MAX-ACCESS    read-only
        STATUS        current 
        DESCRIPTION  "Number of Premium ServiceStats Multicast sent.."
        ::= { rcTlsIpServiceStatsEntry 70 }

rcTlsIpServiceStatsPremCongestionDropFrames  OBJECT-TYPE
        SYNTAX        Counter64
        MAX-ACCESS    read-only
        STATUS        current
        DESCRIPTION  "Number of Prem ServiceStats Frames congestion dropped"
        ::= { rcTlsIpServiceStatsEntry 71 }

rcTlsIpServiceStatsGoldCongestionDropFrames  OBJECT-TYPE
        SYNTAX        Counter64
        MAX-ACCESS    read-only
        STATUS        current
        DESCRIPTION  "Number of Gold ServiceStats Frames congestion dropped"
        ::= { rcTlsIpServiceStatsEntry 72 }

rcTlsIpServiceStatsSilverCongestionDropFrames        OBJECT-TYPE
        SYNTAX        Counter64
        MAX-ACCESS    read-only
        STATUS        current
        DESCRIPTION  "Number of Silver ServiceStats Frames congestion dropped"
        ::= { rcTlsIpServiceStatsEntry 73 }

rcTlsIpServiceStatsStndCongestionDropFrames  OBJECT-TYPE
        SYNTAX        Counter64
        MAX-ACCESS    read-only
        STATUS        current
        DESCRIPTION  "Number of Stnd ServiceStats congestion Frames dropped"
        ::= { rcTlsIpServiceStatsEntry 74 }

rcTlsIpServiceStatsPremCirDroppedFrames      OBJECT-TYPE
        SYNTAX        Counter64
        MAX-ACCESS    read-only
        STATUS        current
        DESCRIPTION  "Number of Prem ServiceStats CIR Frames dropped"
        ::= { rcTlsIpServiceStatsEntry 75 }

rcTlsIpServiceStatsPremPirDroppedFrames      OBJECT-TYPE
        SYNTAX        Counter64
        MAX-ACCESS    read-only
        STATUS        current
        DESCRIPTION  "Number of Prem ServiceStats PIR Frames dropped"
        ::= { rcTlsIpServiceStatsEntry 76 }

rcTlsIpServiceStatsGoldCirDroppedFrames      OBJECT-TYPE
        SYNTAX        Counter64
        MAX-ACCESS    read-only
        STATUS        current
        DESCRIPTION  "Number of Gold ServiceStats CIR Frames dropped"
        ::= { rcTlsIpServiceStatsEntry 77 }

rcTlsIpServiceStatsGoldPirDroppedFrames      OBJECT-TYPE
        SYNTAX        Counter64
        MAX-ACCESS    read-only
        STATUS        current
        DESCRIPTION  "Number of Gold ServiceStats PIR Frames dropped"
        ::= { rcTlsIpServiceStatsEntry 78 }

rcTlsIpServiceStatsSilverCirDroppedFrames    OBJECT-TYPE
        SYNTAX        Counter64
        MAX-ACCESS    read-only
        STATUS        current
        DESCRIPTION  "Number of Silver ServiceStats CIR Frames dropped."
        ::= { rcTlsIpServiceStatsEntry 79 }

rcTlsIpServiceStatsSilverPirDroppedFrames    OBJECT-TYPE
        SYNTAX        Counter64
        MAX-ACCESS    read-only
        STATUS        current
        DESCRIPTION  "Number of Silver ServiceStats PIR Frames dropped"
        ::= { rcTlsIpServiceStatsEntry 80 }

rcTlsIpServiceStatsStndCirDroppedFrames      OBJECT-TYPE
        SYNTAX        Counter64
        MAX-ACCESS    read-only
        STATUS        current
        DESCRIPTION  "Number of Standard ServiceStats CIR Frames dropped"
        ::= { rcTlsIpServiceStatsEntry 81 }

rcTlsIpServiceStatsStndPirDroppedFrames      OBJECT-TYPE
        SYNTAX        Counter64
        MAX-ACCESS    read-only
        STATUS        current
        DESCRIPTION  "Number of Standard ServiceStats PIR Frames dropped"
        ::= { rcTlsIpServiceStatsEntry 82 }

rcTlsIpServiceStatsPremTxDroppedFrames       OBJECT-TYPE
        SYNTAX        Counter64
        MAX-ACCESS    read-only
        STATUS        current
        DESCRIPTION  "Tx Number of Premium ServiceStats Frames dropped."
        ::= { rcTlsIpServiceStatsEntry 83 }

rcTlsIpServiceStatsGoldTxDroppedFrames       OBJECT-TYPE
        SYNTAX        Counter64
        MAX-ACCESS    read-only
        STATUS        current
        DESCRIPTION  "Tx Number of Gold ServiceStats Frames dropped."
        ::= { rcTlsIpServiceStatsEntry 84 }

rcTlsIpServiceStatsSilverTxDroppedFrames     OBJECT-TYPE
        SYNTAX        Counter64
        MAX-ACCESS    read-only
        STATUS        current
        DESCRIPTION  "Tx Number of Silver ServiceStats Frames dropped."
        ::= { rcTlsIpServiceStatsEntry 85 }

rcTlsIpServiceStatsStndTxDroppedFrames       OBJECT-TYPE
        SYNTAX        Counter64
        MAX-ACCESS    read-only
        STATUS        current
        DESCRIPTION  "Tx Number of Standard ServiceStats Frames dropped."
        ::= { rcTlsIpServiceStatsEntry 86 }

rcTlsIpServiceStatsPremTxCongestionDropFrames        OBJECT-TYPE
        SYNTAX        Counter64
        MAX-ACCESS    read-only
        STATUS        current
        DESCRIPTION  "Tx Nbr of Prem ServiceStats Frames congestion dropped."
        ::= { rcTlsIpServiceStatsEntry 87 }

rcTlsIpServiceStatsGoldTxCongestionDropFrames        OBJECT-TYPE
        SYNTAX        Counter64
        MAX-ACCESS    read-only
        STATUS        current
        DESCRIPTION  "Tx Nbr of Gold ServiceStats Frames congestion dropped."
        ::= { rcTlsIpServiceStatsEntry 88 }

rcTlsIpServiceStatsSilverTxCongestionDropFrames      OBJECT-TYPE
        SYNTAX        Counter64
        MAX-ACCESS    read-only
        STATUS        current
        DESCRIPTION  "Tx Nbr Silver ServiceStats Frames congestion dropped."
        ::= { rcTlsIpServiceStatsEntry 89 }

rcTlsIpServiceStatsStndTxCongestionDropFrames        OBJECT-TYPE
        SYNTAX        Counter64
        MAX-ACCESS    read-only
        STATUS        current
        DESCRIPTION  "Tx Nbr Standard ServiceStats Frames congestion dropped."
        ::= { rcTlsIpServiceStatsEntry 90 }

rcTlsIpServiceStatsPremTxCirDroppedFrames    OBJECT-TYPE
        SYNTAX        Counter64
        MAX-ACCESS    read-only
        STATUS        current
        DESCRIPTION  "Tx Number of Prem ServiceStats CIR Frames dropped."
        ::= { rcTlsIpServiceStatsEntry 91 }

rcTlsIpServiceStatsPremTxPirDroppedFrames    OBJECT-TYPE
        SYNTAX        Counter64
        MAX-ACCESS    read-only
        STATUS        current
        DESCRIPTION  "Tx Number of Prem ServiceStats PIR Frames dropped."
        ::= { rcTlsIpServiceStatsEntry 92 }

rcTlsIpServiceStatsGoldTxCirDroppedFrames    OBJECT-TYPE
        SYNTAX        Counter64
        MAX-ACCESS    read-only
        STATUS        current
        DESCRIPTION  "Tx Number of Gold ServiceStats CIR Frames dropped."
        ::= { rcTlsIpServiceStatsEntry 93 }

rcTlsIpServiceStatsGoldTxPirDroppedFrames    OBJECT-TYPE
        SYNTAX        Counter64
        MAX-ACCESS    read-only
        STATUS        current
        DESCRIPTION  "Tx Number of Gold ServiceStats PIR Frames dropped."
        ::= { rcTlsIpServiceStatsEntry 94 }

rcTlsIpServiceStatsSilverTxCirDroppedFrames  OBJECT-TYPE
        SYNTAX        Counter64
        MAX-ACCESS    read-only
        STATUS        current
        DESCRIPTION  "Tx Number of Silver ServiceStats CIR Frames dropped"
        ::= { rcTlsIpServiceStatsEntry 95 }

rcTlsIpServiceStatsSilverTxPirDroppedFrames  OBJECT-TYPE
        SYNTAX        Counter64
        MAX-ACCESS    read-only
        STATUS        current
        DESCRIPTION  "Tx Number of Silver ServiceStats PIR Frames dropped."
        ::= { rcTlsIpServiceStatsEntry 96 }

rcTlsIpServiceStatsStndTxCirDroppedFrames    OBJECT-TYPE
        SYNTAX        Counter64
        MAX-ACCESS    read-only
        STATUS        current
        DESCRIPTION  "Tx Number of Standard ServiceStats CIR Frames dropped."
        ::= { rcTlsIpServiceStatsEntry 97 }

rcTlsIpServiceStatsStndTxPirDroppedFrames    OBJECT-TYPE
        SYNTAX        Counter64
        MAX-ACCESS    read-only
        STATUS        current
        DESCRIPTION  "TX Number of Standard ServiceStats PIR Frames dropped."
        ::= { rcTlsIpServiceStatsEntry 98 }

rcTlsIpServiceStatsRxMcastTotalFrames        OBJECT-TYPE
        SYNTAX        Counter64
        MAX-ACCESS    read-only
        STATUS        current
        DESCRIPTION  "Rx Total Number of Mcast Frames"
        ::= { rcTlsIpServiceStatsEntry 99 }
 
rcTlsIpServiceStatsTxMcastTotalFrames        OBJECT-TYPE
        SYNTAX        Counter64
        MAX-ACCESS    read-only
        STATUS        current
        DESCRIPTION  "Tx total Number of Mcast Frames"
        ::= { rcTlsIpServiceStatsEntry 100 }

rcTlsIpServiceStatsPremRxMcastDroppedFrames  OBJECT-TYPE
        SYNTAX        Counter64
        MAX-ACCESS    read-only
        STATUS        current
        DESCRIPTION  "Number of Premium Service Rx Mcast Frames dropped."
        ::= { rcTlsIpServiceStatsEntry 101 }

rcTlsIpServiceStatsGoldRxMcastDroppedFrames  OBJECT-TYPE
        SYNTAX        Counter64
        MAX-ACCESS    read-only
        STATUS        current
        DESCRIPTION  "Number of Gold Service Rx Mcast Frames dropped."
        ::= { rcTlsIpServiceStatsEntry 102 }

rcTlsIpServiceStatsSilverRxMcastDroppedFrames        OBJECT-TYPE
        SYNTAX        Counter64
        MAX-ACCESS    read-only
        STATUS        current
        DESCRIPTION  "Number of Silver Service Rx Mcast Frames dropped."
        ::= { rcTlsIpServiceStatsEntry 103 }

rcTlsIpServiceStatsStndRxMcastDroppedFrames  OBJECT-TYPE
        SYNTAX        Counter64
        MAX-ACCESS    read-only
        STATUS        current
        DESCRIPTION  "Number of Standard Service Rx Mcast Frames dropped."
        ::= { rcTlsIpServiceStatsEntry 104 }

rcTlsIpServiceStatsPremRxCirOctets     OBJECT-TYPE
        SYNTAX        Counter64
        MAX-ACCESS    read-only
        STATUS        current
        DESCRIPTION  "Number of Premium Service Rx CIR Octets received."
        ::= { rcTlsIpServiceStatsEntry 105 }

rcTlsIpServiceStatsPremRxCirOopOctets     OBJECT-TYPE
        SYNTAX        Counter64
        MAX-ACCESS    read-only
        STATUS        current
        DESCRIPTION  "Number of Premium Service Rx Octets received that 
		      were CIR OOP."
        ::= { rcTlsIpServiceStatsEntry 106 }

rcTlsIpServiceStatsPremRxEirOctets     OBJECT-TYPE
        SYNTAX        Counter64
        MAX-ACCESS    read-only
        STATUS        current
        DESCRIPTION  "Number of Premium Service Rx EIR Octets received."
        ::= { rcTlsIpServiceStatsEntry 107 }

rcTlsIpServiceStatsPremRxEirOopOctets     OBJECT-TYPE
        SYNTAX        Counter64
        MAX-ACCESS    read-only
        STATUS        current
        DESCRIPTION  "Number of Premium Service Rx Octets received that 
		      were EIR OOP."
        ::= { rcTlsIpServiceStatsEntry 108 }

rcTlsIpServiceStatsPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcTlsIpServiceStatsEntry 109 }

rcTlsIpServiceStatsPremRxPirOctets     OBJECT-TYPE
        SYNTAX        Counter64
        MAX-ACCESS    read-only
        STATUS        current
        DESCRIPTION  "Number of Premium Service Rx PIR Octets received."
        ::= { rcTlsIpServiceStatsEntry 110 }

rcTlsIpServiceStatsPremRxPirOopOctets     OBJECT-TYPE
        SYNTAX        Counter64
        MAX-ACCESS    read-only
        STATUS        current
        DESCRIPTION  "Number of Premium Service Rx Octets received that 
		      were PIR OOP."
        ::= { rcTlsIpServiceStatsEntry 111 }

rcTlsIpServiceStatsPremRxGreenOctets     OBJECT-TYPE
        SYNTAX        Counter64
        MAX-ACCESS    read-only
        STATUS        current
        DESCRIPTION  "Number of Premium Service Rx Octets received that 
		      were marked 'Green' by the policer."
        ::= { rcTlsIpServiceStatsEntry 112 }

rcTlsIpServiceStatsPremRxYellowOctets     OBJECT-TYPE
        SYNTAX        Counter64
        MAX-ACCESS    read-only
        STATUS        current
        DESCRIPTION  "Number of Premium Service Rx Octets received that 
		      were marked 'Yellow' by the policer."
        ::= { rcTlsIpServiceStatsEntry 113 }

rcTlsIpServiceStatsPremRxRedOctets     OBJECT-TYPE
        SYNTAX        Counter64
        MAX-ACCESS    read-only
        STATUS        current
        DESCRIPTION  "Number of Premium Service Rx Octets received that 
		      were marked 'Red' by the policer."
        ::= { rcTlsIpServiceStatsEntry 114 }

rcTlsIpServiceStatsGoldRxCirOctets     OBJECT-TYPE
        SYNTAX        Counter64
        MAX-ACCESS    read-only
        STATUS        current
        DESCRIPTION  "Number of Gold Service Rx CIR Octets received."
        ::= { rcTlsIpServiceStatsEntry 115 }

rcTlsIpServiceStatsGoldRxCirOopOctets     OBJECT-TYPE
        SYNTAX        Counter64
        MAX-ACCESS    read-only
        STATUS        current
        DESCRIPTION  "Number of Gold Service Rx Octets received that 
		      were CIR OOP."
        ::= { rcTlsIpServiceStatsEntry 116 }

rcTlsIpServiceStatsGoldRxEirOctets     OBJECT-TYPE
        SYNTAX        Counter64
        MAX-ACCESS    read-only
        STATUS        current
        DESCRIPTION  "Number of Gold Service Rx EIR Octets received."
        ::= { rcTlsIpServiceStatsEntry 117 }

rcTlsIpServiceStatsGoldRxEirOopOctets     OBJECT-TYPE
        SYNTAX        Counter64
        MAX-ACCESS    read-only
        STATUS        current
        DESCRIPTION  "Number of Gold Service Rx Octets received that 
		      were EIR OOP."
        ::= { rcTlsIpServiceStatsEntry 118 }

rcTlsIpServiceStatsGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcTlsIpServiceStatsEntry 119 }

rcTlsIpServiceStatsGoldRxPirOctets     OBJECT-TYPE
        SYNTAX        Counter64
        MAX-ACCESS    read-only
        STATUS        current
        DESCRIPTION  "Number of Gold Service Rx PIR Octets received."
        ::= { rcTlsIpServiceStatsEntry 120 }

rcTlsIpServiceStatsGoldRxPirOopOctets     OBJECT-TYPE
        SYNTAX        Counter64
        MAX-ACCESS    read-only
        STATUS        current
        DESCRIPTION  "Number of Gold Service Rx Octets received that 
		      were PIR OOP."
        ::= { rcTlsIpServiceStatsEntry 121 }

rcTlsIpServiceStatsGoldRxGreenOctets     OBJECT-TYPE
        SYNTAX        Counter64
        MAX-ACCESS    read-only
        STATUS        current
        DESCRIPTION  "Number of Gold Service Rx Octets received that 
		      were marked 'Green' by the policer."
        ::= { rcTlsIpServiceStatsEntry 122 }

rcTlsIpServiceStatsGoldRxYellowOctets     OBJECT-TYPE
        SYNTAX        Counter64
        MAX-ACCESS    read-only
        STATUS        current
        DESCRIPTION  "Number of Gold Service Rx Octets received that 
		      were marked 'Yellow' by the policer."
        ::= { rcTlsIpServiceStatsEntry 123 }

rcTlsIpServiceStatsGoldRxRedOctets     OBJECT-TYPE
        SYNTAX        Counter64
        MAX-ACCESS    read-only
        STATUS        current
        DESCRIPTION  "Number of Gold Service Rx Octets received that 
		      were marked 'Red' by the policer."
        ::= { rcTlsIpServiceStatsEntry 124 }

rcTlsIpServiceStatsSilverRxCirOctets     OBJECT-TYPE
        SYNTAX        Counter64
        MAX-ACCESS    read-only
        STATUS        current
        DESCRIPTION  "Number of Silver Service Rx CIR Octets received."
        ::= { rcTlsIpServiceStatsEntry 125 }

rcTlsIpServiceStatsSilverRxCirOopOctets     OBJECT-TYPE
        SYNTAX        Counter64
        MAX-ACCESS    read-only
        STATUS        current
        DESCRIPTION  "Number of Silver Service Rx Octets received that 
		      were CIR OOP."
        ::= { rcTlsIpServiceStatsEntry 126 }

rcTlsIpServiceStatsSilverRxEirOctets     OBJECT-TYPE
        SYNTAX        Counter64
        MAX-ACCESS    read-only
        STATUS        current
        DESCRIPTION  "Number of Silver Service Rx EIR Octets received."
        ::= { rcTlsIpServiceStatsEntry 127 }

rcTlsIpServiceStatsSilverRxEirOopOctets     OBJECT-TYPE
        SYNTAX        Counter64
        MAX-ACCESS    read-only
        STATUS        current
        DESCRIPTION  "Number of Silver Service Rx Octets received that 
		      were EIR OOP."
        ::= { rcTlsIpServiceStatsEntry 128 }

rcTlsIpServiceStatsSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcTlsIpServiceStatsEntry 129 }

rcTlsIpServiceStatsSilverRxPirOctets     OBJECT-TYPE
        SYNTAX        Counter64
        MAX-ACCESS    read-only
        STATUS        current
        DESCRIPTION  "Number of Silver Service Rx PIR Octets received."
        ::= { rcTlsIpServiceStatsEntry 130 }

rcTlsIpServiceStatsSilverRxPirOopOctets     OBJECT-TYPE
        SYNTAX        Counter64
        MAX-ACCESS    read-only
        STATUS        current
        DESCRIPTION  "Number of Silver Service Rx Octets received that 
		      were PIR OOP."
        ::= { rcTlsIpServiceStatsEntry 131 }

rcTlsIpServiceStatsSilverRxGreenOctets     OBJECT-TYPE
        SYNTAX        Counter64
        MAX-ACCESS    read-only
        STATUS        current
        DESCRIPTION  "Number of Silver Service Rx Octets received that 
		      were marked 'Green' by the policer."
        ::= { rcTlsIpServiceStatsEntry 132 }

rcTlsIpServiceStatsSilverRxYellowOctets     OBJECT-TYPE
        SYNTAX        Counter64
        MAX-ACCESS    read-only
        STATUS        current
        DESCRIPTION  "Number of Silver Service Rx Octets received that 
		      were marked 'Yellow' by the policer."
        ::= { rcTlsIpServiceStatsEntry 133 }

rcTlsIpServiceStatsSilverRxRedOctets     OBJECT-TYPE
        SYNTAX        Counter64
        MAX-ACCESS    read-only
        STATUS        current
        DESCRIPTION  "Number of Silver Service Rx Octets received that 
		      were marked 'Red' by the policer."
        ::= { rcTlsIpServiceStatsEntry 134 }

rcTlsIpServiceStatsStndRxCirOctets     OBJECT-TYPE
        SYNTAX        Counter64
        MAX-ACCESS    read-only
        STATUS        current
        DESCRIPTION  "Number of Standard Service Rx CIR Octets received."
        ::= { rcTlsIpServiceStatsEntry 135 }

rcTlsIpServiceStatsStndRxCirOopOctets     OBJECT-TYPE
        SYNTAX        Counter64
        MAX-ACCESS    read-only
        STATUS        current
        DESCRIPTION  "Number of Standard Service Rx Octets received that 
		      were CIR OOP."
        ::= { rcTlsIpServiceStatsEntry 136 }

rcTlsIpServiceStatsStndRxEirOctets     OBJECT-TYPE
        SYNTAX        Counter64
        MAX-ACCESS    read-only
        STATUS        current
        DESCRIPTION  "Number of Standard Service Rx EIR Octets received."
        ::= { rcTlsIpServiceStatsEntry 137 }

rcTlsIpServiceStatsStndRxEirOopOctets     OBJECT-TYPE
        SYNTAX        Counter64
        MAX-ACCESS    read-only
        STATUS        current
        DESCRIPTION  "Number of Standard Service Rx Octets received that 
		      were EIR OOP."
        ::= { rcTlsIpServiceStatsEntry 138 }

rcTlsIpServiceStatsStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcTlsIpServiceStatsEntry 139 }

rcTlsIpServiceStatsStndRxPirOctets     OBJECT-TYPE
        SYNTAX        Counter64
        MAX-ACCESS    read-only
        STATUS        current
        DESCRIPTION  "Number of Standard Service Rx PIR Octets received."
        ::= { rcTlsIpServiceStatsEntry 140 }

rcTlsIpServiceStatsStndRxPirOopOctets     OBJECT-TYPE
        SYNTAX        Counter64
        MAX-ACCESS    read-only
        STATUS        current
        DESCRIPTION  "Number of Standard Service Rx Octets received that 
		      were PIR OOP."
        ::= { rcTlsIpServiceStatsEntry 141 }

rcTlsIpServiceStatsStndRxGreenOctets     OBJECT-TYPE
        SYNTAX        Counter64
        MAX-ACCESS    read-only
        STATUS        current
        DESCRIPTION  "Number of Standard Service Rx Octets received that 
		      were marked 'Green' by the policer."
        ::= { rcTlsIpServiceStatsEntry 142 }

rcTlsIpServiceStatsStndRxYellowOctets     OBJECT-TYPE
        SYNTAX        Counter64
        MAX-ACCESS    read-only
        STATUS        current
        DESCRIPTION  "Number of Standard Service Rx Octets received that 
		      were marked 'Yellow' by the policer."
        ::= { rcTlsIpServiceStatsEntry 143 }

rcTlsIpServiceStatsStndRxRedOctets     OBJECT-TYPE
        SYNTAX        Counter64
        MAX-ACCESS    read-only
        STATUS        current
        DESCRIPTION  "Number of Standard Service Rx Octets received that 
		      were marked 'Red' by the policer."
        ::= { rcTlsIpServiceStatsEntry 144 }

rcTlsIpServiceStatsMcastRxDroppedOctets     OBJECT-TYPE
        SYNTAX        Counter64
        MAX-ACCESS    read-only
        STATUS        current
        DESCRIPTION  "Number of Multicast Rx Octets dropped."
        ::= { rcTlsIpServiceStatsEntry 145 }

rcTlsIpServiceStatsBcastUUcastRxTotalOctets     OBJECT-TYPE
        SYNTAX        Counter64
        MAX-ACCESS    read-only
        STATUS        current
        DESCRIPTION  "Number of Broadcast/Unknown Unicast Rx total Octets."
        ::= { rcTlsIpServiceStatsEntry 146 }

rcTlsIpServiceStatsBcastUUcastRxDroppedOctets     OBJECT-TYPE
        SYNTAX        Counter64
        MAX-ACCESS    read-only
        STATUS        current
        DESCRIPTION  "Number of Broadcast/Unknown Rx Octets dropped."
        ::= { rcTlsIpServiceStatsEntry 147 }

rcTlsIpServiceStatsPremRxCirFrames     OBJECT-TYPE
        SYNTAX        Counter64
        MAX-ACCESS    read-only
        STATUS        current
        DESCRIPTION  "Number of Premium Service Rx CIR Frames received."
        ::= { rcTlsIpServiceStatsEntry 148 }

rcTlsIpServiceStatsPremRxCirOopFrames     OBJECT-TYPE
        SYNTAX        Counter64
        MAX-ACCESS    read-only
        STATUS        current
        DESCRIPTION  "Number of Premium Service Rx Frames received that 
		      were CIR OOP."
        ::= { rcTlsIpServiceStatsEntry 149 }

rcTlsIpServiceStatsPremRxEirFrames     OBJECT-TYPE
        SYNTAX        Counter64
        MAX-ACCESS    read-only
        STATUS        current
        DESCRIPTION  "Number of Premium Service Rx EIR Frames received."
        ::= { rcTlsIpServiceStatsEntry 150 }

rcTlsIpServiceStatsPremRxEirOopFrames     OBJECT-TYPE
        SYNTAX        Counter64
        MAX-ACCESS    read-only
        STATUS        current
        DESCRIPTION  "Number of Premium Service Rx Frames received that 
		      were EIR OOP."
        ::= { rcTlsIpServiceStatsEntry 151 }

rcTlsIpServiceStatsPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcTlsIpServiceStatsEntry 152 }

rcTlsIpServiceStatsPremRxPirFrames     OBJECT-TYPE
        SYNTAX        Counter64
        MAX-ACCESS    read-only
        STATUS        current
        DESCRIPTION  "Number of Premium Service Rx PIR Frames received."
        ::= { rcTlsIpServiceStatsEntry 153 }

rcTlsIpServiceStatsPremRxPirOopFrames     OBJECT-TYPE
        SYNTAX        Counter64
        MAX-ACCESS    read-only
        STATUS        current
        DESCRIPTION  "Number of Premium Service Rx Frames received that 
		      were PIR OOP."
        ::= { rcTlsIpServiceStatsEntry 154 }

rcTlsIpServiceStatsPremRxGreenFrames     OBJECT-TYPE
        SYNTAX        Counter64
        MAX-ACCESS    read-only
        STATUS        current
        DESCRIPTION  "Number of Premium Service Rx Frames received that 
		      were marked 'Green' by the policer."
        ::= { rcTlsIpServiceStatsEntry 155 }

rcTlsIpServiceStatsPremRxYellowFrames     OBJECT-TYPE
        SYNTAX        Counter64
        MAX-ACCESS    read-only
        STATUS        current
        DESCRIPTION  "Number of Premium Service Rx Frames received that 
		      were marked 'Yellow' by the policer."
        ::= { rcTlsIpServiceStatsEntry 156 }

rcTlsIpServiceStatsPremRxRedFrames     OBJECT-TYPE
        SYNTAX        Counter64
        MAX-ACCESS    read-only
        STATUS        current
        DESCRIPTION  "Number of Premium Service Rx Frames received that 
		      were marked 'Red' by the policer."
        ::= { rcTlsIpServiceStatsEntry 157 }

rcTlsIpServiceStatsGoldRxCirFrames     OBJECT-TYPE
        SYNTAX        Counter64
        MAX-ACCESS    read-only
        STATUS        current
        DESCRIPTION  "Number of Gold Service Rx CIR Frames received."
        ::= { rcTlsIpServiceStatsEntry 158 }

rcTlsIpServiceStatsGoldRxCirOopFrames     OBJECT-TYPE
        SYNTAX        Counter64
        MAX-ACCESS    read-only
        STATUS        current
        DESCRIPTION  "Number of Gold Service Rx Frames received that 
		      were CIR OOP."
        ::= { rcTlsIpServiceStatsEntry 159 }

rcTlsIpServiceStatsGoldRxEirFrames     OBJECT-TYPE
        SYNTAX        Counter64
        MAX-ACCESS    read-only
        STATUS        current
        DESCRIPTION  "Number of Gold Service Rx EIR Frames received."
        ::= { rcTlsIpServiceStatsEntry 160 }

rcTlsIpServiceStatsGoldRxEirOopFrames     OBJECT-TYPE
        SYNTAX        Counter64
        MAX-ACCESS    read-only
        STATUS        current
        DESCRIPTION  "Number of Gold Service Rx Frames received that 
		      were EIR OOP."
        ::= { rcTlsIpServiceStatsEntry 161 }

rcTlsIpServiceStatsGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcTlsIpServiceStatsEntry 162 }

rcTlsIpServiceStatsGoldRxPirFrames     OBJECT-TYPE
        SYNTAX        Counter64
        MAX-ACCESS    read-only
        STATUS        current
        DESCRIPTION  "Number of Gold Service Rx PIR Frames received."
        ::= { rcTlsIpServiceStatsEntry 163 }

rcTlsIpServiceStatsGoldRxPirOopFrames     OBJECT-TYPE
        SYNTAX        Counter64
        MAX-ACCESS    read-only
        STATUS        current
        DESCRIPTION  "Number of Gold Service Rx Frames received that 
		      were PIR OOP."
        ::= { rcTlsIpServiceStatsEntry 164 }

rcTlsIpServiceStatsGoldRxGreenFrames     OBJECT-TYPE
        SYNTAX        Counter64
        MAX-ACCESS    read-only
        STATUS        current
        DESCRIPTION  "Number of Gold Service Rx Frames received that 
		      were marked 'Green' by the policer."
        ::= { rcTlsIpServiceStatsEntry 165 }

rcTlsIpServiceStatsGoldRxYellowFrames     OBJECT-TYPE
        SYNTAX        Counter64
        MAX-ACCESS    read-only
        STATUS        current
        DESCRIPTION  "Number of Gold Service Rx Frames received that 
		      were marked 'Yellow' by the policer."
        ::= { rcTlsIpServiceStatsEntry 166 }

rcTlsIpServiceStatsGoldRxRedFrames     OBJECT-TYPE
        SYNTAX        Counter64
        MAX-ACCESS    read-only
        STATUS        current
        DESCRIPTION  "Number of Gold Service Rx Frames received that 
		      were marked 'Red' by the policer."
        ::= { rcTlsIpServiceStatsEntry 167 }

rcTlsIpServiceStatsSilverRxCirFrames     OBJECT-TYPE
        SYNTAX        Counter64
        MAX-ACCESS    read-only
        STATUS        current
        DESCRIPTION  "Number of Silver Service Rx CIR Frames received."
        ::= { rcTlsIpServiceStatsEntry 168 }

rcTlsIpServiceStatsSilverRxCirOopFrames     OBJECT-TYPE
        SYNTAX        Counter64
        MAX-ACCESS    read-only
        STATUS        current
        DESCRIPTION  "Number of Silver Service Rx Frames received that 
		      were CIR OOP."
        ::= { rcTlsIpServiceStatsEntry 169 }

rcTlsIpServiceStatsSilverRxEirFrames     OBJECT-TYPE
        SYNTAX        Counter64
        MAX-ACCESS    read-only
        STATUS        current
        DESCRIPTION  "Number of Silver Service Rx EIR Frames received."
        ::= { rcTlsIpServiceStatsEntry 170 }

rcTlsIpServiceStatsSilverRxEirOopFrames     OBJECT-TYPE
        SYNTAX        Counter64
        MAX-ACCESS    read-only
        STATUS        current
        DESCRIPTION  "Number of Silver Service Rx Frames received that 
		      were EIR OOP."
        ::= { rcTlsIpServiceStatsEntry 171 }

rcTlsIpServiceStatsSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcTlsIpServiceStatsEntry 172 }

rcTlsIpServiceStatsSilverRxPirFrames     OBJECT-TYPE
        SYNTAX        Counter64
        MAX-ACCESS    read-only
        STATUS        current
        DESCRIPTION  "Number of Silver Service Rx PIR Frames received."
        ::= { rcTlsIpServiceStatsEntry 173 }

rcTlsIpServiceStatsSilverRxPirOopFrames     OBJECT-TYPE
        SYNTAX        Counter64
        MAX-ACCESS    read-only
        STATUS        current
        DESCRIPTION  "Number of Silver Service Rx Frames received that 
		      were PIR OOP."
        ::= { rcTlsIpServiceStatsEntry 174 }

rcTlsIpServiceStatsSilverRxGreenFrames     OBJECT-TYPE
        SYNTAX        Counter64
        MAX-ACCESS    read-only
        STATUS        current
        DESCRIPTION  "Number of Silver Service Rx Frames received that 
		      were marked 'Green' by the policer."
        ::= { rcTlsIpServiceStatsEntry 175 }

rcTlsIpServiceStatsSilverRxYellowFrames     OBJECT-TYPE
        SYNTAX        Counter64
        MAX-ACCESS    read-only
        STATUS        current
        DESCRIPTION  "Number of Silver Service Rx Frames received that 
		      were marked 'Yellow' by the policer."
        ::= { rcTlsIpServiceStatsEntry 176 }

rcTlsIpServiceStatsSilverRxRedFrames     OBJECT-TYPE
        SYNTAX        Counter64
        MAX-ACCESS    read-only
        STATUS        current
        DESCRIPTION  "Number of Silver Service Rx Frames received that 
		      were marked 'Red' by the policer."
        ::= { rcTlsIpServiceStatsEntry 177 }

rcTlsIpServiceStatsStndRxCirFrames     OBJECT-TYPE
        SYNTAX        Counter64
        MAX-ACCESS    read-only
        STATUS        current
        DESCRIPTION  "Number of Standard Service Rx CIR Frames received."
        ::= { rcTlsIpServiceStatsEntry 178 }

rcTlsIpServiceStatsStndRxCirOopFrames     OBJECT-TYPE
        SYNTAX        Counter64
        MAX-ACCESS    read-only
        STATUS        current
        DESCRIPTION  "Number of Standard Service Rx Frames received that 
		      were CIR OOP."
        ::= { rcTlsIpServiceStatsEntry 179 }

rcTlsIpServiceStatsStndRxEirFrames     OBJECT-TYPE
        SYNTAX        Counter64
        MAX-ACCESS    read-only
        STATUS        current
        DESCRIPTION  "Number of Standard Service Rx EIR Frames received."
        ::= { rcTlsIpServiceStatsEntry 180 }

rcTlsIpServiceStatsStndRxEirOopFrames     OBJECT-TYPE
        SYNTAX        Counter64
        MAX-ACCESS    read-only
        STATUS        current
        DESCRIPTION  "Number of Standard Service Rx Frames received that 
		      were EIR OOP."
        ::= { rcTlsIpServiceStatsEntry 181 }

rcTlsIpServiceStatsStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcTlsIpServiceStatsEntry 182 }

rcTlsIpServiceStatsStndRxPirFrames     OBJECT-TYPE
        SYNTAX        Counter64
        MAX-ACCESS    read-only
        STATUS        current
        DESCRIPTION  "Number of Standard Service Rx PIR Frames received."
        ::= { rcTlsIpServiceStatsEntry 183 }

rcTlsIpServiceStatsStndRxPirOopFrames     OBJECT-TYPE
        SYNTAX        Counter64
        MAX-ACCESS    read-only
        STATUS        current
        DESCRIPTION  "Number of Standard Service Rx Frames received that 
		      were PIR OOP."
        ::= { rcTlsIpServiceStatsEntry 184 }

rcTlsIpServiceStatsStndRxGreenFrames     OBJECT-TYPE
        SYNTAX        Counter64
        MAX-ACCESS    read-only
        STATUS        current
        DESCRIPTION  "Number of Standard Service Rx Frames received that 
		      were marked 'Green' by the policer."
        ::= { rcTlsIpServiceStatsEntry 185 }

rcTlsIpServiceStatsStndRxYellowFrames     OBJECT-TYPE
        SYNTAX        Counter64
        MAX-ACCESS    read-only
        STATUS        current
        DESCRIPTION  "Number of Standard Service Rx Frames received that 
		      were marked 'Yellow' by the policer."
        ::= { rcTlsIpServiceStatsEntry 186 }

rcTlsIpServiceStatsStndRxRedFrames     OBJECT-TYPE
        SYNTAX        Counter64
        MAX-ACCESS    read-only
        STATUS        current
        DESCRIPTION  "Number of Standard Service Rx Frames received that 
		      were marked 'Red' by the policer."
        ::= { rcTlsIpServiceStatsEntry 187 }

rcTlsIpServiceStatsMcastRxDroppedFrames     OBJECT-TYPE
        SYNTAX        Counter64
        MAX-ACCESS    read-only
        STATUS        current
        DESCRIPTION  "Number of Multicast Rx Frames dropped."
        ::= { rcTlsIpServiceStatsEntry 188 }

rcTlsIpServiceStatsBcastUUcastRxTotalFrames     OBJECT-TYPE
        SYNTAX        Counter64
        MAX-ACCESS    read-only
        STATUS        current
        DESCRIPTION  "Number of Broadcast/Unknown Unicast Rx total Frames."
        ::= { rcTlsIpServiceStatsEntry 189 }

rcTlsIpServiceStatsBcastUUcastRxDroppedFrames     OBJECT-TYPE
        SYNTAX        Counter64
        MAX-ACCESS    read-only
        STATUS        current
        DESCRIPTION  "Number of Broadcast/Unknown Rx Frames dropped."
        ::= { rcTlsIpServiceStatsEntry 190 }

rcTlsIpServiceStatsPremTxCirOctets     OBJECT-TYPE
        SYNTAX        Counter64
        MAX-ACCESS    read-only
        STATUS        current
        DESCRIPTION  "Number of Premium Service Tx CIR Octets received."
        ::= { rcTlsIpServiceStatsEntry 191 }

rcTlsIpServiceStatsPremTxCirOopOctets     OBJECT-TYPE
        SYNTAX        Counter64
        MAX-ACCESS    read-only
        STATUS        current
        DESCRIPTION  "Number of Premium Service Tx Octets received that 
		      were CIR OOP."
        ::= { rcTlsIpServiceStatsEntry 192 }

rcTlsIpServiceStatsPremTxEirOctets     OBJECT-TYPE
        SYNTAX        Counter64
        MAX-ACCESS    read-only
        STATUS        current
        DESCRIPTION  "Number of Premium Service Tx EIR Octets received."
        ::= { rcTlsIpServiceStatsEntry 193 }

rcTlsIpServiceStatsPremTxEirOopOctets     OBJECT-TYPE
        SYNTAX        Counter64
        MAX-ACCESS    read-only
        STATUS        current
        DESCRIPTION  "Number of Premium Service Tx Octets received that 
		      were EIR OOP."
        ::= { rcTlsIpServiceStatsEntry 194 }

rcTlsIpServiceStatsPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcTlsIpServiceStatsEntry 195 }

rcTlsIpServiceStatsPremTxPirOctets     OBJECT-TYPE
        SYNTAX        Counter64
        MAX-ACCESS    read-only
        STATUS        current
        DESCRIPTION  "Number of Premium Service Tx PIR Octets received."
        ::= { rcTlsIpServiceStatsEntry 196 }

rcTlsIpServiceStatsPremTxPirOopOctets     OBJECT-TYPE
        SYNTAX        Counter64
        MAX-ACCESS    read-only
        STATUS        current
        DESCRIPTION  "Number of Premium Service Tx Octets received that 
		      were PIR OOP."
        ::= { rcTlsIpServiceStatsEntry 197 }

rcTlsIpServiceStatsPremTxGreenOctets     OBJECT-TYPE
        SYNTAX        Counter64
        MAX-ACCESS    read-only
        STATUS        current
        DESCRIPTION  "Number of Premium Service Tx Octets received that 
		      were marked 'Green' by the policer."
        ::= { rcTlsIpServiceStatsEntry 198 }

rcTlsIpServiceStatsPremTxYellowOctets     OBJECT-TYPE
        SYNTAX        Counter64
        MAX-ACCESS    read-only
        STATUS        current
        DESCRIPTION  "Number of Premium Service Tx Octets received that 
		      were marked 'Yellow' by the policer."
        ::= { rcTlsIpServiceStatsEntry 199 }

rcTlsIpServiceStatsPremTxRedOctets     OBJECT-TYPE
        SYNTAX        Counter64
        MAX-ACCESS    read-only
        STATUS        current
        DESCRIPTION  "Number of Premium Service Tx Octets received that 
		      were marked 'Red' by the policer."
        ::= { rcTlsIpServiceStatsEntry 200 }

rcTlsIpServiceStatsGoldTxCirOctets     OBJECT-TYPE
        SYNTAX        Counter64
        MAX-ACCESS    read-only
        STATUS        current
        DESCRIPTION  "Number of Gold Service Tx CIR Octets received."
        ::= { rcTlsIpServiceStatsEntry 201 }

rcTlsIpServiceStatsGoldTxCirOopOctets     OBJECT-TYPE
        SYNTAX        Counter64
        MAX-ACCESS    read-only
        STATUS        current
        DESCRIPTION  "Number of Gold Service Tx Octets received that 
		      were CIR OOP."
        ::= { rcTlsIpServiceStatsEntry 202 }

rcTlsIpServiceStatsGoldTxEirOctets     OBJECT-TYPE
        SYNTAX        Counter64
        MAX-ACCESS    read-only
        STATUS        current
        DESCRIPTION  "Number of Gold Service Tx EIR Octets received."
        ::= { rcTlsIpServiceStatsEntry 203 }

rcTlsIpServiceStatsGoldTxEirOopOctets     OBJECT-TYPE
        SYNTAX        Counter64
        MAX-ACCESS    read-only
        STATUS        current
        DESCRIPTION  "Number of Gold Service Tx Octets received that 
		      were EIR OOP."
        ::= { rcTlsIpServiceStatsEntry 204 }

rcTlsIpServiceStatsGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcTlsIpServiceStatsEntry 205 }

rcTlsIpServiceStatsGoldTxPirOctets     OBJECT-TYPE
        SYNTAX        Counter64
        MAX-ACCESS    read-only
        STATUS        current
        DESCRIPTION  "Number of Gold Service Tx PIR Octets received."
        ::= { rcTlsIpServiceStatsEntry 206 }

rcTlsIpServiceStatsGoldTxPirOopOctets     OBJECT-TYPE
        SYNTAX        Counter64
        MAX-ACCESS    read-only
        STATUS        current
        DESCRIPTION  "Number of Gold Service Tx Octets received that 
		      were PIR OOP."
        ::= { rcTlsIpServiceStatsEntry 207 }

rcTlsIpServiceStatsGoldTxGreenOctets     OBJECT-TYPE
        SYNTAX        Counter64
        MAX-ACCESS    read-only
        STATUS        current
        DESCRIPTION  "Number of Gold Service Tx Octets received that 
		      were marked 'Green' by the policer."
        ::= { rcTlsIpServiceStatsEntry 208 }

rcTlsIpServiceStatsGoldTxYellowOctets     OBJECT-TYPE
        SYNTAX        Counter64
        MAX-ACCESS    read-only
        STATUS        current
        DESCRIPTION  "Number of Gold Service Tx Octets received that 
		      were marked 'Yellow' by the policer."
        ::= { rcTlsIpServiceStatsEntry 209 }

rcTlsIpServiceStatsGoldTxRedOctets     OBJECT-TYPE
        SYNTAX        Counter64
        MAX-ACCESS    read-only
        STATUS        current
        DESCRIPTION  "Number of Gold Service Tx Octets received that 
		      were marked 'Red' by the policer."
        ::= { rcTlsIpServiceStatsEntry 210 }

rcTlsIpServiceStatsSilverTxCirOctets     OBJECT-TYPE
        SYNTAX        Counter64
        MAX-ACCESS    read-only
        STATUS        current
        DESCRIPTION  "Number of Silver Service Tx CIR Octets received."
        ::= { rcTlsIpServiceStatsEntry 211 }

rcTlsIpServiceStatsSilverTxCirOopOctets     OBJECT-TYPE
        SYNTAX        Counter64
        MAX-ACCESS    read-only
        STATUS        current
        DESCRIPTION  "Number of Silver Service Tx Octets received that 
		      were CIR OOP."
        ::= { rcTlsIpServiceStatsEntry 212 }

rcTlsIpServiceStatsSilverTxEirOctets     OBJECT-TYPE
        SYNTAX        Counter64
        MAX-ACCESS    read-only
        STATUS        current
        DESCRIPTION  "Number of Silver Service Tx EIR Octets received."
        ::= { rcTlsIpServiceStatsEntry 213 }

rcTlsIpServiceStatsSilverTxEirOopOctets     OBJECT-TYPE
        SYNTAX        Counter64
        MAX-ACCESS    read-only
        STATUS        current
        DESCRIPTION  "Number of Silver Service Tx Octets received that 
		      were EIR OOP."
        ::= { rcTlsIpServiceStatsEntry 214 }

rcTlsIpServiceStatsSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcTlsIpServiceStatsEntry 215 }

rcTlsIpServiceStatsSilverTxPirOctets     OBJECT-TYPE
        SYNTAX        Counter64
        MAX-ACCESS    read-only
        STATUS        current
        DESCRIPTION  "Number of Silver Service Tx PIR Octets received."
        ::= { rcTlsIpServiceStatsEntry 216 }

rcTlsIpServiceStatsSilverTxPirOopOctets     OBJECT-TYPE
        SYNTAX        Counter64
        MAX-ACCESS    read-only
        STATUS        current
        DESCRIPTION  "Number of Silver Service Tx Octets received that 
		      were PIR OOP."
        ::= { rcTlsIpServiceStatsEntry 217 }

rcTlsIpServiceStatsSilverTxGreenOctets     OBJECT-TYPE
        SYNTAX        Counter64
        MAX-ACCESS    read-only
        STATUS        current
        DESCRIPTION  "Number of Silver Service Tx Octets received that 
		      were marked 'Green' by the policer."
        ::= { rcTlsIpServiceStatsEntry 218 }

rcTlsIpServiceStatsSilverTxYellowOctets     OBJECT-TYPE
        SYNTAX        Counter64
        MAX-ACCESS    read-only
        STATUS        current
        DESCRIPTION  "Number of Silver Service Tx Octets received that 
		      were marked 'Yellow' by the policer."
        ::= { rcTlsIpServiceStatsEntry 219 }

rcTlsIpServiceStatsSilverTxRedOctets     OBJECT-TYPE
        SYNTAX        Counter64
        MAX-ACCESS    read-only
        STATUS        current
        DESCRIPTION  "Number of Silver Service Tx Octets received that 
		      were marked 'Red' by the policer."
        ::= { rcTlsIpServiceStatsEntry 220 }

rcTlsIpServiceStatsStndTxCirOctets     OBJECT-TYPE
        SYNTAX        Counter64
        MAX-ACCESS    read-only
        STATUS        current
        DESCRIPTION  "Number of Standard Service Tx CIR Octets received."
        ::= { rcTlsIpServiceStatsEntry 221 }

rcTlsIpServiceStatsStndTxCirOopOctets     OBJECT-TYPE
        SYNTAX        Counter64
        MAX-ACCESS    read-only
        STATUS        current
        DESCRIPTION  "Number of Standard Service Tx Octets received that 
		      were CIR OOP."
        ::= { rcTlsIpServiceStatsEntry 222 }

rcTlsIpServiceStatsStndTxEirOctets     OBJECT-TYPE
        SYNTAX        Counter64
        MAX-ACCESS    read-only
        STATUS        current
        DESCRIPTION  "Number of Standard Service Tx EIR Octets received."
        ::= { rcTlsIpServiceStatsEntry 223 }

rcTlsIpServiceStatsStndTxEirOopOctets     OBJECT-TYPE
        SYNTAX        Counter64
        MAX-ACCESS    read-only
        STATUS        current
        DESCRIPTION  "Number of Standard Service Tx Octets received that 
		      were EIR OOP."
        ::= { rcTlsIpServiceStatsEntry 224 }

rcTlsIpServiceStatsStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcTlsIpServiceStatsEntry 225 }

rcTlsIpServiceStatsStndTxPirOctets     OBJECT-TYPE
        SYNTAX        Counter64
        MAX-ACCESS    read-only
        STATUS        current
        DESCRIPTION  "Number of Standard Service Tx PIR Octets received."
        ::= { rcTlsIpServiceStatsEntry 226 }

rcTlsIpServiceStatsStndTxPirOopOctets     OBJECT-TYPE
        SYNTAX        Counter64
        MAX-ACCESS    read-only
        STATUS        current
        DESCRIPTION  "Number of Standard Service Tx Octets received that 
		      were PIR OOP."
        ::= { rcTlsIpServiceStatsEntry 227 }

rcTlsIpServiceStatsStndTxGreenOctets     OBJECT-TYPE
        SYNTAX        Counter64
        MAX-ACCESS    read-only
        STATUS        current
        DESCRIPTION  "Number of Standard Service Tx Octets received that 
		      were marked 'Green' by the policer."
        ::= { rcTlsIpServiceStatsEntry 228 }

rcTlsIpServiceStatsStndTxYellowOctets     OBJECT-TYPE
        SYNTAX        Counter64
        MAX-ACCESS    read-only
        STATUS        current
        DESCRIPTION  "Number of Standard Service Tx Octets received that 
		      were marked 'Yellow' by the policer."
        ::= { rcTlsIpServiceStatsEntry 229 }

rcTlsIpServiceStatsStndTxRedOctets     OBJECT-TYPE
        SYNTAX        Counter64
        MAX-ACCESS    read-only
        STATUS        current
        DESCRIPTION  "Number of Standard Service Tx Octets received that 
		      were marked 'Red' by the policer."
        ::= { rcTlsIpServiceStatsEntry 230 }

rcTlsIpServiceStatsMcastTxDroppedOctets     OBJECT-TYPE
        SYNTAX        Counter64
        MAX-ACCESS    read-only
        STATUS        current
        DESCRIPTION  "Number of Multicast Tx Octets dropped."
        ::= { rcTlsIpServiceStatsEntry 231 }

rcTlsIpServiceStatsBcastUUcastTxTotalOctets     OBJECT-TYPE
        SYNTAX        Counter64
        MAX-ACCESS    read-only
        STATUS        current
        DESCRIPTION  "Number of Broadcast/Unknown Unicast Tx total Octets."
        ::= { rcTlsIpServiceStatsEntry 232 }

rcTlsIpServiceStatsBcastUUcastTxDroppedOctets     OBJECT-TYPE
        SYNTAX        Counter64
        MAX-ACCESS    read-only
        STATUS        current
        DESCRIPTION  "Number of Broadcast/Unknown Tx Octets dropped."
        ::= { rcTlsIpServiceStatsEntry 233 }

rcTlsIpServiceStatsPremTxCirFrames     OBJECT-TYPE
        SYNTAX        Counter64
        MAX-ACCESS    read-only
        STATUS        current
        DESCRIPTION  "Number of Premium Service Tx CIR Frames received."
        ::= { rcTlsIpServiceStatsEntry 234 }

rcTlsIpServiceStatsPremTxCirOopFrames     OBJECT-TYPE
        SYNTAX        Counter64
        MAX-ACCESS    read-only
        STATUS        current
        DESCRIPTION  "Number of Premium Service Tx Frames received that 
		      were CIR OOP."
        ::= { rcTlsIpServiceStatsEntry 235 }

rcTlsIpServiceStatsPremTxEirFrames     OBJECT-TYPE
        SYNTAX        Counter64
        MAX-ACCESS    read-only
        STATUS        current
        DESCRIPTION  "Number of Premium Service Tx EIR Frames received."
        ::= { rcTlsIpServiceStatsEntry 236 }

rcTlsIpServiceStatsPremTxEirOopFrames     OBJECT-TYPE
        SYNTAX        Counter64
        MAX-ACCESS    read-only
        STATUS        current
        DESCRIPTION  "Number of Premium Service Tx Frames received that 
		      were EIR OOP."
        ::= { rcTlsIpServiceStatsEntry 237 }

rcTlsIpServiceStatsPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcTlsIpServiceStatsEntry 238 }

rcTlsIpServiceStatsPremTxPirFrames     OBJECT-TYPE
        SYNTAX        Counter64
        MAX-ACCESS    read-only
        STATUS        current
        DESCRIPTION  "Number of Premium Service Tx PIR Frames received."
        ::= { rcTlsIpServiceStatsEntry 239 }

rcTlsIpServiceStatsPremTxPirOopFrames     OBJECT-TYPE
        SYNTAX        Counter64
        MAX-ACCESS    read-only
        STATUS        current
        DESCRIPTION  "Number of Premium Service Tx Frames received that 
		      were PIR OOP."
        ::= { rcTlsIpServiceStatsEntry 240 }

rcTlsIpServiceStatsPremTxGreenFrames     OBJECT-TYPE
        SYNTAX        Counter64
        MAX-ACCESS    read-only
        STATUS        current
        DESCRIPTION  "Number of Premium Service Tx Frames received that 
		      were marked 'Green' by the policer."
        ::= { rcTlsIpServiceStatsEntry 241 }

rcTlsIpServiceStatsPremTxYellowFrames     OBJECT-TYPE
        SYNTAX        Counter64
        MAX-ACCESS    read-only
        STATUS        current
        DESCRIPTION  "Number of Premium Service Tx Frames received that 
		      were marked 'Yellow' by the policer."
        ::= { rcTlsIpServiceStatsEntry 242 }

rcTlsIpServiceStatsPremTxRedFrames     OBJECT-TYPE
        SYNTAX        Counter64
        MAX-ACCESS    read-only
        STATUS        current
        DESCRIPTION  "Number of Premium Service Tx Frames received that 
		      were marked 'Red' by the policer."
        ::= { rcTlsIpServiceStatsEntry 243 }

rcTlsIpServiceStatsGoldTxCirFrames     OBJECT-TYPE
        SYNTAX        Counter64
        MAX-ACCESS    read-only
        STATUS        current
        DESCRIPTION  "Number of Gold Service Tx CIR Frames received."
        ::= { rcTlsIpServiceStatsEntry 244 }

rcTlsIpServiceStatsGoldTxCirOopFrames     OBJECT-TYPE
        SYNTAX        Counter64
        MAX-ACCESS    read-only
        STATUS        current
        DESCRIPTION  "Number of Gold Service Tx Frames received that 
		      were CIR OOP."
        ::= { rcTlsIpServiceStatsEntry 245 }

rcTlsIpServiceStatsGoldTxEirFrames     OBJECT-TYPE
        SYNTAX        Counter64
        MAX-ACCESS    read-only
        STATUS        current
        DESCRIPTION  "Number of Gold Service Tx EIR Frames received."
        ::= { rcTlsIpServiceStatsEntry 246 }

rcTlsIpServiceStatsGoldTxEirOopFrames     OBJECT-TYPE
        SYNTAX        Counter64
        MAX-ACCESS    read-only
        STATUS        current
        DESCRIPTION  "Number of Gold Service Tx Frames received that 
		      were EIR OOP."
        ::= { rcTlsIpServiceStatsEntry 247 }

rcTlsIpServiceStatsGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcTlsIpServiceStatsEntry 248 }

rcTlsIpServiceStatsGoldTxPirFrames     OBJECT-TYPE
        SYNTAX        Counter64
        MAX-ACCESS    read-only
        STATUS        current
        DESCRIPTION  "Number of Gold Service Tx PIR Frames received."
        ::= { rcTlsIpServiceStatsEntry 249 }

rcTlsIpServiceStatsGoldTxPirOopFrames     OBJECT-TYPE
        SYNTAX        Counter64
        MAX-ACCESS    read-only
        STATUS        current
        DESCRIPTION  "Number of Gold Service Tx Frames received that 
		      were PIR OOP."
        ::= { rcTlsIpServiceStatsEntry 250 }

rcTlsIpServiceStatsGoldTxGreenFrames     OBJECT-TYPE
        SYNTAX        Counter64
        MAX-ACCESS    read-only
        STATUS        current
        DESCRIPTION  "Number of Gold Service Tx Frames received that 
		      were marked 'Green' by the policer."
        ::= { rcTlsIpServiceStatsEntry 251 }

rcTlsIpServiceStatsGoldTxYellowFrames     OBJECT-TYPE
        SYNTAX        Counter64
        MAX-ACCESS    read-only
        STATUS        current
        DESCRIPTION  "Number of Gold Service Tx Frames received that 
		      were marked 'Yellow' by the policer."
        ::= { rcTlsIpServiceStatsEntry 252 }

rcTlsIpServiceStatsGoldTxRedFrames     OBJECT-TYPE
        SYNTAX        Counter64
        MAX-ACCESS    read-only
        STATUS        current
        DESCRIPTION  "Number of Gold Service Tx Frames received that 
		      were marked 'Red' by the policer."
        ::= { rcTlsIpServiceStatsEntry 253 }

rcTlsIpServiceStatsSilverTxCirFrames     OBJECT-TYPE
        SYNTAX        Counter64
        MAX-ACCESS    read-only
        STATUS        current
        DESCRIPTION  "Number of Silver Service Tx CIR Frames received."
        ::= { rcTlsIpServiceStatsEntry 254 }

rcTlsIpServiceStatsSilverTxCirOopFrames     OBJECT-TYPE
        SYNTAX        Counter64
        MAX-ACCESS    read-only
        STATUS        current
        DESCRIPTION  "Number of Silver Service Tx Frames received that 
		      were CIR OOP."
        ::= { rcTlsIpServiceStatsEntry 255 }

rcTlsIpServiceStatsSilverTxEirFrames     OBJECT-TYPE
        SYNTAX        Counter64
        MAX-ACCESS    read-only
        STATUS        current
        DESCRIPTION  "Number of Silver Service Tx EIR Frames received."
        ::= { rcTlsIpServiceStatsEntry 256 }

rcTlsIpServiceStatsSilverTxEirOopFrames     OBJECT-TYPE
        SYNTAX        Counter64
        MAX-ACCESS    read-only
        STATUS        current
        DESCRIPTION  "Number of Silver Service Tx Frames received that 
		      were EIR OOP."
        ::= { rcTlsIpServiceStatsEntry 257 }

rcTlsIpServiceStatsSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcTlsIpServiceStatsEntry 258 }

rcTlsIpServiceStatsSilverTxPirFrames     OBJECT-TYPE
        SYNTAX        Counter64
        MAX-ACCESS    read-only
        STATUS        current
        DESCRIPTION  "Number of Silver Service Tx PIR Frames received."
        ::= { rcTlsIpServiceStatsEntry 259 }

rcTlsIpServiceStatsSilverTxPirOopFrames     OBJECT-TYPE
        SYNTAX        Counter64
        MAX-ACCESS    read-only
        STATUS        current
        DESCRIPTION  "Number of Silver Service Tx Frames received that 
		      were PIR OOP."
        ::= { rcTlsIpServiceStatsEntry 260 }

rcTlsIpServiceStatsSilverTxGreenFrames     OBJECT-TYPE
        SYNTAX        Counter64
        MAX-ACCESS    read-only
        STATUS        current
        DESCRIPTION  "Number of Silver Service Tx Frames received that 
		      were marked 'Green' by the policer."
        ::= { rcTlsIpServiceStatsEntry 261 }

rcTlsIpServiceStatsSilverTxYellowFrames     OBJECT-TYPE
        SYNTAX        Counter64
        MAX-ACCESS    read-only
        STATUS        current
        DESCRIPTION  "Number of Silver Service Tx Frames received that 
		      were marked 'Yellow' by the policer."
        ::= { rcTlsIpServiceStatsEntry 262 }

rcTlsIpServiceStatsSilverTxRedFrames     OBJECT-TYPE
        SYNTAX        Counter64
        MAX-ACCESS    read-only
        STATUS        current
        DESCRIPTION  "Number of Silver Service Tx Frames received that 
		      were marked 'Red' by the policer."
        ::= { rcTlsIpServiceStatsEntry 263 }

rcTlsIpServiceStatsStndTxCirFrames     OBJECT-TYPE
        SYNTAX        Counter64
        MAX-ACCESS    read-only
        STATUS        current
        DESCRIPTION  "Number of Standard Service Tx CIR Frames received."
        ::= { rcTlsIpServiceStatsEntry 264 }

rcTlsIpServiceStatsStndTxCirOopFrames     OBJECT-TYPE
        SYNTAX        Counter64
        MAX-ACCESS    read-only
        STATUS        current
        DESCRIPTION  "Number of Standard Service Tx Frames received that 
		      were CIR OOP."
        ::= { rcTlsIpServiceStatsEntry 265 }

rcTlsIpServiceStatsStndTxEirFrames     OBJECT-TYPE
        SYNTAX        Counter64
        MAX-ACCESS    read-only
        STATUS        current
        DESCRIPTION  "Number of Standard Service Tx EIR Frames received."
        ::= { rcTlsIpServiceStatsEntry 266 }

rcTlsIpServiceStatsStndTxEirOopFrames     OBJECT-TYPE
        SYNTAX        Counter64
        MAX-ACCESS    read-only
        STATUS        current
        DESCRIPTION  "Number of Standard Service Tx Frames received that 
		      were EIR OOP."
        ::= { rcTlsIpServiceStatsEntry 267 }

rcTlsIpServiceStatsStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcTlsIpServiceStatsEntry 268 }

rcTlsIpServiceStatsStndTxPirFrames     OBJECT-TYPE
        SYNTAX        Counter64
        MAX-ACCESS    read-only
        STATUS        current
        DESCRIPTION  "Number of Standard Service Tx PIR Frames received."
        ::= { rcTlsIpServiceStatsEntry 269 }

rcTlsIpServiceStatsStndTxPirOopFrames     OBJECT-TYPE
        SYNTAX        Counter64
        MAX-ACCESS    read-only
        STATUS        current
        DESCRIPTION  "Number of Standard Service Tx Frames received that 
		      were PIR OOP."
        ::= { rcTlsIpServiceStatsEntry 270 }

rcTlsIpServiceStatsStndTxGreenFrames     OBJECT-TYPE
        SYNTAX        Counter64
        MAX-ACCESS    read-only
        STATUS        current
        DESCRIPTION  "Number of Standard Service Tx Frames received that 
		      were marked 'Green' by the policer."
        ::= { rcTlsIpServiceStatsEntry 271 }

rcTlsIpServiceStatsStndTxYellowFrames     OBJECT-TYPE
        SYNTAX        Counter64
        MAX-ACCESS    read-only
        STATUS        current
        DESCRIPTION  "Number of Standard Service Tx Frames received that 
		      were marked 'Yellow' by the policer."
        ::= { rcTlsIpServiceStatsEntry 272 }

rcTlsIpServiceStatsStndTxRedFrames     OBJECT-TYPE
        SYNTAX        Counter64
        MAX-ACCESS    read-only
        STATUS        current
        DESCRIPTION  "Number of Standard Service Tx Frames received that 
		      were marked 'Red' by the policer."
        ::= { rcTlsIpServiceStatsEntry 273 }

rcTlsIpServiceStatsMcastTxDroppedFrames     OBJECT-TYPE
        SYNTAX        Counter64
        MAX-ACCESS    read-only
        STATUS        current
        DESCRIPTION  "Number of Multicast Tx Frames dropped."
        ::= { rcTlsIpServiceStatsEntry 274 }

rcTlsIpServiceStatsBcastUUcastTxTotalFrames     OBJECT-TYPE
        SYNTAX        Counter64
        MAX-ACCESS    read-only
        STATUS        current
        DESCRIPTION  "Number of Broadcast/Unknown Unicast Tx total Frames."
        ::= { rcTlsIpServiceStatsEntry 275 }

rcTlsIpServiceStatsBcastUUcastTxDroppedFrames     OBJECT-TYPE
        SYNTAX        Counter64
        MAX-ACCESS    read-only
        STATUS        current
        DESCRIPTION  "Number of Broadcast/Unknown Tx Frames dropped."
        ::= { rcTlsIpServiceStatsEntry 276 }

rcTlsIpServiceStatsDropClassRxDroppedOctets     OBJECT-TYPE
        SYNTAX        Counter64
        MAX-ACCESS    read-only
        STATUS        current
        DESCRIPTION  "Number of Drop Class Rx Octets dropped."
        ::= { rcTlsIpServiceStatsEntry 277 }

rcTlsIpServiceStatsDropClassRxDroppedFrames     OBJECT-TYPE
        SYNTAX        Counter64
        MAX-ACCESS    read-only
        STATUS        current
        DESCRIPTION  "Number of Drop Class Rx Frames dropped."
        ::= { rcTlsIpServiceStatsEntry 278 }

rcTlsIpServiceStatsDropClassTxDroppedOctets	OBJECT-TYPE
        SYNTAX        Counter64
        MAX-ACCESS    read-only
        STATUS        current
        DESCRIPTION  "Number of Drop Class Tx Octets dropped."
        ::= { rcTlsIpServiceStatsEntry 279 }

rcTlsIpServiceStatsDropClassTxDroppedFrames     OBJECT-TYPE
        SYNTAX        Counter64
        MAX-ACCESS    read-only
        STATUS        current
        DESCRIPTION  "Number of Drop Class Tx Frames dropped."
        ::= { rcTlsIpServiceStatsEntry 280 }




-- rcTlsGlobals

rcTlsGlobals OBJECT IDENTIFIER ::= { rcTls 22 } 

rcTlsGlobalsMimEtherType OBJECT-TYPE
        SYNTAX        INTEGER (1..'FFFF'h)
        MAX-ACCESS    read-write
        STATUS        current
        DESCRIPTION   "Mac in Mac Ethertype"
        DEFVAL        { '8889'h }
        ::= { rcTlsGlobals 1 }

-- rcOePortTable

rcOePortTable OBJECT-TYPE
        SYNTAX	      SEQUENCE OF RcOePortEntry
        MAX-ACCESS    not-accessible
        STATUS        current
        DESCRIPTION   "Optical Ethernet Port table, contains OE supported 
		       port and OE Tls port information"
        ::= { rcTls 23 }

rcOePortEntry OBJECT-TYPE
        SYNTAX        RcOePortEntry
        MAX-ACCESS    not-accessible
        STATUS        current
        DESCRIPTION   "Entry containing port information for a particular 
		       OE supported port"
        INDEX         { rcOePortIndex }
        ::= { rcOePortTable 1 }

RcOePortEntry ::= SEQUENCE {
        rcOePortIndex                           InterfaceIndex,
	rcOePortType                            INTEGER,
        rcOePortServiceType                     INTEGER,
	rcOePortSwitchedUniCount  	        Counter32,
	rcOePortTransparentUniCount             Counter32,
	rcOePortQinQ1UniCount                   Counter32,
	rcOePortQinQ2UniCount                   Counter32,
	rcOePortQinQEtherType                   INTEGER,
	rcOePortMplsUniCount                    Counter32 
        }
	
rcOePortIndex OBJECT-TYPE
        SYNTAX        InterfaceIndex
        MAX-ACCESS    not-accessible
        STATUS        current
        DESCRIPTION   "An index value that uniquely identifies a OE 
	               supported port.
                       This value is similar to ifIndex in MIB2."
        ::= { rcOePortEntry 1 }

rcOePortType OBJECT-TYPE
	SYNTAX        INTEGER {
			 esm8x1000Base(1),
			 pr48x1000BaseTX(2),
                         pr30x1000BaseSXBB(3),
			 pr3x10GBaseGbic(4),
			 pr3x10GBaseXZW(5)
	              }
	MAX-ACCESS    read-only
	STATUS        current
	DESCRIPTION   "Port Hardware type, which include PowerRange and 
	               ESM port"
	::= { rcOePortEntry 2 }

rcOePortServiceType OBJECT-TYPE
	SYNTAX        INTEGER {
                         none(1),
			 server(2), 
		         ringPrimary(3),
			 ringSecondary(4),
			 standalone(5),
			 transparent(6),
			 multiService(7)
	              }
	MAX-ACCESS    read-only
	STATUS        current
	DESCRIPTION   "Port OE service type which is assigned"
	::= { rcOePortEntry 3 }

rcOePortSwitchedUniCount OBJECT-TYPE
        SYNTAX        Counter32
        MAX-ACCESS    read-only
        STATUS        current
        DESCRIPTION   "Number of Switched UNI this port belongs to"
        ::= { rcOePortEntry 4 }

rcOePortTransparentUniCount OBJECT-TYPE
        SYNTAX        Counter32
        MAX-ACCESS    read-only
        STATUS        current
        DESCRIPTION   "Number of Transparent UNI this port belongs to"
        ::= { rcOePortEntry 5 }

rcOePortQinQ1UniCount OBJECT-TYPE
        SYNTAX        Counter32
        MAX-ACCESS    read-only
        STATUS        current
        DESCRIPTION   "Number of QinQ1 UNI this port belongs to"
        ::= { rcOePortEntry 6 }

rcOePortQinQ2UniCount OBJECT-TYPE
        SYNTAX        Counter32
        MAX-ACCESS    read-only
        STATUS        current
        DESCRIPTION   "Number of QinQ2 UNI this port belongs to"
        ::= { rcOePortEntry 7 }

rcOePortQinQEtherType   OBJECT-TYPE
        SYNTAX        INTEGER (1..'FFFF'h) 
        MAX-ACCESS    read-only
        STATUS        current
        DESCRIPTION   "The QinQ ether type value. It is hex value. 
                       It should be displayed as Hex value. It is 
		       only be used when port is associated with 
		       QinQ service. Otherwise, it would be ignored"
        ::= { rcOePortEntry 8 }

rcOePortMplsUniCount OBJECT-TYPE
        SYNTAX        Counter32
        MAX-ACCESS    read-only
        STATUS        current
        DESCRIPTION   "Number of MPLS (vc-label)UNI  this port belongs to"
        ::= { rcOePortEntry 9 }     
-- OE MAC Count Table

rcOeRecordCountTable  OBJECT-TYPE
SYNTAX          SEQUENCE OF RcOeRecordCountEntry
MAX-ACCESS      not-accessible
STATUS          current
DESCRIPTION     "OE port Record Count (MAC/IP count) table."
        ::= { rcTls 24 }

rcOeRecordCountEntry   OBJECT-TYPE
SYNTAX          RcOeRecordCountEntry
MAX-ACCESS      not-accessible
STATUS          current
DESCRIPTION     "Entry containing information about MAC/IP entries learnt 
                 on each ESM port or R-Mod lane."
INDEX           {rcOeRecordCountSlot, rcOeRecordCountIndex}
::= { rcOeRecordCountTable  1 }

RcOeRecordCountEntry   ::= SEQUENCE {
                rcOeRecordCountSlot                 Integer32,
                rcOeRecordCountIndex               Integer32,
                rcOeRecordCountPort                DisplayString,
                rcOeRecordCountIngress             Integer32,
                rcOeRecordCountEgress              Integer32,
                rcOeRecordCountIp                  Integer32,
                rcOeRecordCountRecRemaining        Integer32,
                rcOeRecordCountRecTotal            Integer32
                }

rcOeRecordCountSlot      OBJECT-TYPE
        SYNTAX        Integer32 (1..10)
        MAX-ACCESS    not-accessible
        STATUS        current
        DESCRIPTION   "An index value that uniquely identifies a 
                       slot with an ESM/R-Mod card"
        ::= { rcOeRecordCountEntry   1}

rcOeRecordCountIndex     OBJECT-TYPE
        SYNTAX        Integer32 (0..7)
        MAX-ACCESS    not-accessible
        STATUS        current
        DESCRIPTION   "An index value that uniquely identifies an ESM
                       port or R-Mod lane. In the case of a slot which 
                       has ESM card, the index can go from 0..7. Index 0
                       corresponds to port 0, index 1 corresponds to port
                       1 and so on. For an R-Mod card, the index goes
                       from 0 to 2 or 0 to 1 depending on the card type.
                       Index 0 refers to left lane, Index 1 refers to
                       center lane and so on."
        ::= { rcOeRecordCountEntry   2}

rcOeRecordCountPort      OBJECT-TYPE
        SYNTAX        DisplayString (SIZE (1..15))
        MAX-ACCESS    read-only
        STATUS        current
        DESCRIPTION   "ESM port or range of ports in an R-Mod lane"
        ::= { rcOeRecordCountEntry   3}

rcOeRecordCountIngress   OBJECT-TYPE
        SYNTAX        Integer32
        MAX-ACCESS    read-only
        STATUS        current
        DESCRIPTION   "Number of ingress MAC addresses learnt on an ESM
                       port or R-Mod lane."
        ::= { rcOeRecordCountEntry   4}

rcOeRecordCountEgress    OBJECT-TYPE
        SYNTAX        Integer32
        MAX-ACCESS    read-only
        STATUS        current
        DESCRIPTION   "Number of egress MAC addresses learnt on an ESM
                       port or R-Mod lane."
        ::= { rcOeRecordCountEntry   5}

rcOeRecordCountIp        OBJECT-TYPE
        SYNTAX        Integer32
        MAX-ACCESS    read-only
        STATUS        current
        DESCRIPTION   "Number of IP addresses learnt against Cust-IP-Vlans
                       on an ESM port or R-Mod lane."
        ::= { rcOeRecordCountEntry   6}

rcOeRecordCountRecRemaining    OBJECT-TYPE
        SYNTAX              Integer32
        MAX-ACCESS          read-only
        STATUS              current
        DESCRIPTION   "Number of MAC table records that are unused on an
                       ESM port or R-Mod lane. These records are used for
                       storing learnt MAC/IP addresses."
        ::= { rcOeRecordCountEntry   7}

rcOeRecordCountRecTotal  OBJECT-TYPE
        SYNTAX        Integer32
        MAX-ACCESS    read-only
        STATUS        current
        DESCRIPTION   "The total number of MAC table records that are available
                       on an ESM port or R-Mod lane. These records are used
                       for storing learnt MAC/IP addresses."
        ::= { rcOeRecordCountEntry   8}

-- rcTlsIpServiceRmodTable

rcTlsIpServiceRmodTable OBJECT-TYPE
        SYNTAX        SEQUENCE OF RcTlsIpServiceRmodEntry
        MAX-ACCESS    not-accessible
        STATUS        current
        DESCRIPTION   "Table contains Rmod values for customer IP Vlan.Table entry
                       for cust-ip-vlan is created internally when the cust-ip-vlan
                       is configured on a port.The entry will be deleted only after
                       the last cust-ip-vlan end-point is deleted. "
        ::= { rcTls 25}

rcTlsIpServiceRmodEntry OBJECT-TYPE
        SYNTAX        RcTlsIpServiceRmodEntry
        MAX-ACCESS    not-accessible
        STATUS        current
        DESCRIPTION   "Entry contains Rmod values for customer IP Vlan."
        INDEX         { rcTlsIpServiceRmodCustIpVlan}
        ::= { rcTlsIpServiceRmodTable 1}

RcTlsIpServiceRmodEntry ::=
        SEQUENCE {
            rcTlsIpServiceRmodCustIpVlan                 INTEGER,
            rcTlsIpServiceRmodIpTblSize                  INTEGER,
            rcTlsIpServiceRmodIpTblWaterMk               INTEGER,
            rcTlsIpServiceRmodAgeTimer                   INTEGER
        }

rcTlsIpServiceRmodCustIpVlan OBJECT-TYPE
        SYNTAX        INTEGER (1..4096)
        MAX-ACCESS    not-accessible
        STATUS        current
        DESCRIPTION   "Customer IP Vlan for IP Mcast Vlan mapping"
        ::= { rcTlsIpServiceRmodEntry 1}


rcTlsIpServiceRmodIpTblSize OBJECT-TYPE
        SYNTAX        INTEGER (0..16384)
        MAX-ACCESS    read-write
        STATUS        current
        DESCRIPTION   "The size of the IP table. No table entries if
                       it's set to 0."
        DEFVAL       { 0 }
        ::= { rcTlsIpServiceRmodEntry 2 }

rcTlsIpServiceRmodIpTblWaterMk OBJECT-TYPE
        SYNTAX        INTEGER (0..90)
        MAX-ACCESS    read-write
        STATUS        current
        DESCRIPTION   "The Low Water Mark for Ip table size. Set to 90%
                       of the table size, can be over-written."
        DEFVAL       { 0 }
        ::= { rcTlsIpServiceRmodEntry 3}

rcTlsIpServiceRmodAgeTimer OBJECT-TYPE
        SYNTAX        INTEGER (1..1966020)
        MAX-ACCESS    read-write
        STATUS        current
        DESCRIPTION   "IP address ageout timer in seconds.
                       Valid only if rcTlsIpService is Enabled"
        DEFVAL        { 300 }
        ::= {  rcTlsIpServiceRmodEntry 4 }


-- rcTlsTdiBroadcastOptimizationStatsTable

rcTlsTdiBroadcastOptimizationStatsTable OBJECT-TYPE
        SYNTAX        SEQUENCE OF RcTlsTdiBroadcastOptimizationStatsEntry
        MAX-ACCESS    not-accessible
        STATUS        current
        DESCRIPTION   "Tls BroadcastOptimization statistics table."
        ::= { rcTls 26 }	
 
rcTlsTdiBroadcastOptimizationStatsEntry OBJECT-TYPE
        SYNTAX        RcTlsTdiBroadcastOptimizationStatsEntry
        MAX-ACCESS    not-accessible
        STATUS        current
        DESCRIPTION   "A Tls Broadcast Optimization Statistics table entry, 
		      which is used for TDI Broadcast Optimization 
		      Statistics."
      	INDEX         { rcTlsTdiBroadcastOptimizationStatsTdiId, 
			rcTlsTdiBroadcastOptimizationStatsPortIndex}
        ::= { rcTlsTdiBroadcastOptimizationStatsTable 1 }
 
RcTlsTdiBroadcastOptimizationStatsEntry ::=
        SEQUENCE { 
                rcTlsTdiBroadcastOptimizationStatsTdiId            INTEGER,
                rcTlsTdiBroadcastOptimizationStatsPortIndex        InterfaceIndex,
		rcTlsTdiBroadcastOptimizationStatsFrames           Counter64,
		rcTlsTdiBroadcastOptimizationStatsOctets           Counter64,
		rcTlsTdiBroadcastOptimizationStatsName             DisplayString,	
		rcTlsTdiBroadcastOptimizationStatsPortType         INTEGER, 
		rcTlsTdiBroadcastOptimizationStatsRingId           INTEGER
	}	

rcTlsTdiBroadcastOptimizationStatsTdiId OBJECT-TYPE
    		SYNTAX        INTEGER (1..16777215)
       		MAX-ACCESS    not-accessible
         	STATUS        current
        	DESCRIPTION   "Transparent Domaine Identifier."
        	::= { rcTlsTdiBroadcastOptimizationStatsEntry 1 }

rcTlsTdiBroadcastOptimizationStatsPortIndex OBJECT-TYPE
       		SYNTAX        InterfaceIndex
       	 	MAX-ACCESS    not-accessible
        	STATUS        current
        	DESCRIPTION   "An index value that uniquely identifies a OE 
	               	      supported port."
               	::= { rcTlsTdiBroadcastOptimizationStatsEntry 2}

rcTlsTdiBroadcastOptimizationStatsFrames OBJECT-TYPE
    		SYNTAX        Counter64 
       		MAX-ACCESS    read-only
         	STATUS        current
        	DESCRIPTION   "Frames transmitted from the port."
        	::= { rcTlsTdiBroadcastOptimizationStatsEntry 3 }

rcTlsTdiBroadcastOptimizationStatsOctets OBJECT-TYPE
    		SYNTAX        Counter64 
       		MAX-ACCESS    read-only
         	STATUS        current
        	DESCRIPTION   "Octets transmitted from the port."
        	::= { rcTlsTdiBroadcastOptimizationStatsEntry 4 }

rcTlsTdiBroadcastOptimizationStatsName OBJECT-TYPE
       		SYNTAX        DisplayString (SIZE (0..25)) 
        	MAX-ACCESS    read-only
        	STATUS        current
        	DESCRIPTION   "Name of TDI "
        	::= { rcTlsTdiBroadcastOptimizationStatsEntry 5 }

rcTlsTdiBroadcastOptimizationStatsPortType OBJECT-TYPE
        	SYNTAX        INTEGER {
                	          primary(1),
                        	  secondary(2),
                         	  standalone(3)
                        	}
        	MAX-ACCESS    read-only
        	STATUS        current
       		DESCRIPTION   "ring/standalone port type."
        	::= { rcTlsTdiBroadcastOptimizationStatsEntry 6 }

rcTlsTdiBroadcastOptimizationStatsRingId OBJECT-TYPE
        	SYNTAX        INTEGER (1..254)
        	MAX-ACCESS    read-only
        	STATUS        current
        	DESCRIPTION   "Ring ID."
        	::= { rcTlsTdiBroadcastOptimizationStatsEntry 7 }

-- rcTlsIsidBroadcastOptimizationStatsTable

rcTlsIsidBroadcastOptimizationStatsTable OBJECT-TYPE
        SYNTAX        SEQUENCE OF RcTlsIsidBroadcastOptimizationStatsEntry
        MAX-ACCESS    not-accessible
        STATUS        current
        DESCRIPTION   "Tls Isid BroadcastOptimization statistics table."
        ::= { rcTls 27 }	
 
rcTlsIsidBroadcastOptimizationStatsEntry OBJECT-TYPE
        SYNTAX        RcTlsIsidBroadcastOptimizationStatsEntry
        MAX-ACCESS    not-accessible
        STATUS        current
        DESCRIPTION   "A Tls Broadcast Optimization Statistics table entry, 
		      which is used for I-SID Broadcast Optimization 
		      Statistics."
      	INDEX         { rcTlsIsidBroadcastOptimizationStatsIsidId, 
			rcTlsIsidBroadcastOptimizationStatsPortIndex}
        ::= { rcTlsIsidBroadcastOptimizationStatsTable 1 }
 
RcTlsIsidBroadcastOptimizationStatsEntry ::=
        SEQUENCE { 
                rcTlsIsidBroadcastOptimizationStatsIsidId           INTEGER,
                rcTlsIsidBroadcastOptimizationStatsPortIndex        InterfaceIndex,
		rcTlsIsidBroadcastOptimizationStatsFrames           Counter64,
		rcTlsIsidBroadcastOptimizationStatsOctets           Counter64,
		rcTlsIsidBroadcastOptimizationStatsName             DisplayString,	
		rcTlsIsidBroadcastOptimizationStatsPortType         INTEGER, 
		rcTlsIsidBroadcastOptimizationStatsRingId           INTEGER
	}	

rcTlsIsidBroadcastOptimizationStatsIsidId OBJECT-TYPE
    		SYNTAX        INTEGER (1..16777215)
       		MAX-ACCESS    not-accessible
         	STATUS        current
        	DESCRIPTION   "I-SID Identifier"
        	::= { rcTlsIsidBroadcastOptimizationStatsEntry 1 }

rcTlsIsidBroadcastOptimizationStatsPortIndex OBJECT-TYPE
       		SYNTAX        InterfaceIndex
       	 	MAX-ACCESS    not-accessible
        	STATUS        current
        	DESCRIPTION   "An index value that uniquely identifies a OE 
	               	      supported port."
               	::= { rcTlsIsidBroadcastOptimizationStatsEntry 2}

rcTlsIsidBroadcastOptimizationStatsFrames OBJECT-TYPE
    		SYNTAX        Counter64 
       		MAX-ACCESS    read-only
         	STATUS        current
        	DESCRIPTION   "Frames transmitted from the port."
        	::= { rcTlsIsidBroadcastOptimizationStatsEntry 3 }

rcTlsIsidBroadcastOptimizationStatsOctets OBJECT-TYPE
    		SYNTAX        Counter64 
       		MAX-ACCESS    read-only
         	STATUS        current
        	DESCRIPTION   "Octets transmitted from the port."
        	::= { rcTlsIsidBroadcastOptimizationStatsEntry 4 }

rcTlsIsidBroadcastOptimizationStatsName OBJECT-TYPE
       		SYNTAX        DisplayString (SIZE (0..25)) 
        	MAX-ACCESS    read-only
        	STATUS        current
        	DESCRIPTION   "Name of I-SID "
        	::= { rcTlsIsidBroadcastOptimizationStatsEntry 5 }

rcTlsIsidBroadcastOptimizationStatsPortType OBJECT-TYPE
        	SYNTAX        INTEGER {
                	          primary(1),
                        	  secondary(2),
                         	  standalone(3)
                        	}
        	MAX-ACCESS    read-only
        	STATUS        current
       		DESCRIPTION   "ring/standalone port type."
        	::= { rcTlsIsidBroadcastOptimizationStatsEntry 6 }

rcTlsIsidBroadcastOptimizationStatsRingId OBJECT-TYPE
        	SYNTAX        INTEGER (1..254)
        	MAX-ACCESS    read-only
        	STATUS        current
        	DESCRIPTION   "Ring ID."
        	::= { rcTlsIsidBroadcastOptimizationStatsEntry 7 }


-- Rate Policer Profile Table 

-- The default values represent a best effort class of service, no CIR
-- and a minimal (64Kbps) PIR

-- The sum of the 3 CIRs must be less than or equal to the PIR

rcCosProfileTable OBJECT-TYPE
        SYNTAX        SEQUENCE OF RcCosProfileEntry
        MAX-ACCESS    not-accessible
        STATUS        current
        DESCRIPTION   "A list of CoS Profiles. A Rate Policer is used
                       to configure the rate policers (CIR & PIR) for
                       up to four classes of service for a UNI end-point."
        ::= { rcCos 1 }
 
rcCosProfileEntry OBJECT-TYPE
        SYNTAX        RcCosProfileEntry
        MAX-ACCESS    not-accessible
        STATUS        current
        DESCRIPTION   "A CoS Profile Table Entry."
        INDEX         { rcCosProfileTblIndex  }
        ::= { rcCosProfileTable 1 }
 
RcCosProfileEntry ::=
        SEQUENCE {
                rcCosProfileTblIndex              INTEGER,
                rcCosProfileName                  DisplayString,
                rcCosProfilePremiumCirUnits       INTEGER,
                rcCosProfilePremiumCir            INTEGER,
                rcCosProfileGoldCirUnits          INTEGER,
                rcCosProfileGoldCir               INTEGER,
                rcCosProfileSilverCirUnits        INTEGER,
                rcCosProfileSilverCir             INTEGER,
                rcCosProfileStandardPirUnits      INTEGER,
                rcCosProfileStandardPir           INTEGER,
                rcCosProfileRowStatus             RowStatus,
		rcCosProfilePremiumPirUsage       EnableValue,
		rcCosProfileGoldPirUsage          EnableValue,
	  	rcCosProfileSilverPirUsage        EnableValue,
		rcCosProfilePremiumTBMaxSize      INTEGER,
		rcCosProfilePremiumTBMaxCtl 	  INTEGER,
		rcCosProfileGoldTBMaxSize         INTEGER,
		rcCosProfileGoldTBMaxCtl          INTEGER,
		rcCosProfileSilverTBMaxSize       INTEGER,
		rcCosProfileSilverTBMaxCtl        INTEGER,
		rcCosProfileStandardTBMaxSize     INTEGER,
		rcCosProfileStandardTBMaxCtl      INTEGER,
		rcCosProfileMcastLimitUnits	  INTEGER,
		rcCosProfileMcastLimitRate	  INTEGER,	
		rcCosProfileMcastLimitUsage	  EnableValue,
		rcCosProfileMcastLimitTBMaxCtl    INTEGER,
		rcCosProfileMcastLimitTBMaxSize   INTEGER,
		rcCosProfileCosMap			OCTET STRING,  
		rcCosProfilePremiumEirUsage		EnableValue,
		rcCosProfilePremiumEirUnits		INTEGER,
		rcCosProfilePremiumEir		INTEGER,
		rcCosProfilePremiumEirTBMaxCtl	INTEGER,
		rcCosProfilePremiumEirTBMaxSize	INTEGER,
		rcCosProfilePremiumCouplingFlag	EnableValue,
		rcCosProfileGoldEirUsage		EnableValue,
		rcCosProfileGoldEirUnits		INTEGER,
		rcCosProfileGoldEir			INTEGER,
		rcCosProfileGoldEirTBMaxCtl		INTEGER,
		rcCosProfileGoldEirTBMaxSize		INTEGER,
		rcCosProfileGoldCouplingFlag		EnableValue,
		rcCosProfileSilverEirUsage		EnableValue,
		rcCosProfileSilverEirUnits		INTEGER,
		rcCosProfileSilverEir			INTEGER,
		rcCosProfileSilverEirTBMaxCtl		INTEGER,
		rcCosProfileSilverEirTBMaxSize	INTEGER,
		rcCosProfileSilverCouplingFlag	EnableValue,
		rcCosProfileStandardCirUnits            	INTEGER,
		rcCosProfileStandardCir                 	INTEGER,
		rcCosProfileStandardCirTBMaxCtl         	INTEGER,
		rcCosProfileStandardCirTBMaxSize        	INTEGER,
		rcCosProfileStandardEirUsage            	EnableValue,
		rcCosProfileStandardEirUnits		INTEGER,
		rcCosProfileStandardEir		INTEGER,
		rcCosProfileStandardEirTBMaxCtl	INTEGER,
		rcCosProfileStandardEirTBMaxSize	INTEGER,
		rcCosProfileStandardCouplingFlag        	EnableValue,
		rcCosProfileStandardPirUsage            	EnableValue,
		rcCosProfileBcastUUcastLimitUsage	EnableValue,
		rcCosProfileBcastUUcastLimitUnits	INTEGER,
		rcCosProfileBcastUUcastLimitRate	INTEGER,
		rcCosProfileBcastUUcastLimitTBMaxCtl	INTEGER,
		rcCosProfileBcastUUcastLimitTBMaxSize	INTEGER
  
       }

rcCosProfileTblIndex OBJECT-TYPE
        SYNTAX        INTEGER (1..2000)
        MAX-ACCESS    read-only
        STATUS        current
        DESCRIPTION   "The value of this object uniquely identifies an
                       instance of a rcCosProfileEntry."
        ::= { rcCosProfileEntry 1 }
 
rcCosProfileName OBJECT-TYPE
        SYNTAX        DisplayString (SIZE (1..20)) 
        MAX-ACCESS    read-write
        STATUS        current
        DESCRIPTION   "A plain text name describing this rcCosProfile."
        ::= { rcCosProfileEntry 2 }
 
rcCosProfilePremiumCirUnits OBJECT-TYPE
        SYNTAX        INTEGER { 
                          unitsOf64Kbps (1), 
                          unitsOf1Mbps (2),
                          unitsOf100Kbps (3) 
                       }
        MAX-ACCESS    read-write
        STATUS        current
        DESCRIPTION   "Indicates whether the rcCosProfilePremiumCir value
                       is measured in units of 64Kbps or 100Kbps or 1Mbps."  
        DEFVAL { 1 }
        ::= { rcCosProfileEntry 3 }
 
rcCosProfilePremiumCir OBJECT-TYPE
        SYNTAX        INTEGER (0..1000)
        MAX-ACCESS    read-write
        STATUS        current
        DESCRIPTION   "The value of this object indicates the CIR rate
                       for traffic that has been classified as Premium,
                       a NNSC classification that is analogous to DSCP
                       EF, ToS Critical, or 802.1p user priority 6. This
                       attribute reflects a guaranteed data rate. Traffic
                       in excess of this data rate is discarded.
                       If rcCosProfilePremiumCirUnits is set to 1, this
                       value may not exceed 15.If rcCosProfilePremiumCirUnits 
	               is set to 3, this value may not exceed 200."

        DEFVAL { 0 }
        ::= { rcCosProfileEntry 4 }
 
rcCosProfileGoldCirUnits OBJECT-TYPE
        SYNTAX        INTEGER { 
                          unitsOf64Kbps (1), 
                          unitsOf1Mbps (2),
                          unitsOf100Kbps (3)
                       }
        MAX-ACCESS    read-write
        STATUS        current
        DESCRIPTION   "Indicates whether the rcCosProfileGoldCir value
                       is measured in units of 64Kbps or 100 Kbps or 1Mbps."  
        DEFVAL { 1 }
        ::= { rcCosProfileEntry 5 }
 
rcCosProfileGoldCir OBJECT-TYPE
        SYNTAX        INTEGER (0..1000)
        MAX-ACCESS    read-write
        STATUS        current
        DESCRIPTION   "The value of this object indicates the CIR rate
                       for traffic that has been classified as Gold,
                       a NNSC classification that is analogous to DSCP
                       AF3, ToS Flash, or 802.1p user priority 4. This
                       attribute reflects a guaranteed data rate. Traffic
                       in excess of this data rate is marked yellow.
                       If rcCosProfileGoldCirUnits is set to 1, this
                       value may not exceed 15.If rcCosProfileGoldCirUnits 
	           is set to 3, this value may not exceed 200."
        DEFVAL { 0 }
        ::= { rcCosProfileEntry 6 }
 
rcCosProfileSilverCirUnits OBJECT-TYPE
        SYNTAX        INTEGER { 
                          unitsOf64Kbps (1), 
                         unitsOf1Mbps (2),
                         unitsOf100Kbps (3) 
                       }
        MAX-ACCESS    read-write
        STATUS        current
        DESCRIPTION   "Indicates whether the rcCosProfileSilverCir value
                       is measured in units of 64Kbps or 100 Kbps  or 1Mbps."  
        DEFVAL { 1 }
        ::= { rcCosProfileEntry 7 }
 
rcCosProfileSilverCir OBJECT-TYPE
        SYNTAX        INTEGER (0..1000)
        MAX-ACCESS    read-write
        STATUS        current
        DESCRIPTION   "The value of this object indicates the CIR rate
                       for traffic that has been classified as Silver,
                       a NNSC classification that is analogous to DSCP
                       AF2, ToS Immediate, or 802.1p user priority 3. This
                       attribute reflects a guaranteed data rate. Traffic
                       in excess of this data rate is marked yellow.
                       If rcCosProfileSilverCirUnits is set to 1, this
                       value may not exceed 15.If rcCosProfileSilverCirUnits 
		       is set to 3, this value may not exceed 200."
        DEFVAL { 0 }
        ::= { rcCosProfileEntry 8 }
 
rcCosProfileStandardPirUnits OBJECT-TYPE
        SYNTAX        INTEGER { 
                          unitsOf64Kbps (1), 
                          unitsOf1Mbps (2),
                          unitsOf100Kbps (3)
                       }
        MAX-ACCESS    read-write
        STATUS        current
        DESCRIPTION   "Indicates whether the rcCosProfileStandardPir value
                       is measured in units of 64Kbps or 100 Kbps or 1Mbps."  
        DEFVAL { 1 }
        ::= { rcCosProfileEntry 9 }
 
rcCosProfileStandardPir OBJECT-TYPE
        SYNTAX        INTEGER (1..1000)
        MAX-ACCESS    read-write
        STATUS        current
        DESCRIPTION   "The value of this object indicates the PIR rate
                       for traffic that has been classified as Standard
                       traffic. This attribute reflects a best effort
                       peak data rate. If rcCosProfileStandardPirUnits
                       is set to 1, this value may not exceed 15.If
	     rcCosProfileStandardPirUnits is set to 3, this
	     value may not exceed 200.Traffic that has been 
                       colored yellow as a result of exceeding a Gold or 
                       Silver CIR and exceeds this data rate is discarded.
                       Any traffic classified as Standard, a NNSC 
                       classification that is analogous to DSCP Standard,
                       ToS Routine, or 802.1p user priority 0, that exceeds 
                       this data rate will be discarded. Traffic that has
                       been classified as Premium, and traffic hat has been
                       classified as Gold or Silver that has not exceeded 
                       their CIR, will not be discarded if the data rate 
                       exceeds this PIR. That traffic may, however, force 
                       this PIR to a value less than or equal than zero."
        DEFVAL { 15 }
        ::= { rcCosProfileEntry 10 }

rcCosProfileRowStatus OBJECT-TYPE
        SYNTAX        RowStatus
        MAX-ACCESS    read-write
        STATUS        current
        DESCRIPTION   "Uses for controlling the creation and
                       deletion of this row."
        ::= { rcCosProfileEntry 11 }


rcCosProfilePremiumPirUsage OBJECT-TYPE
        SYNTAX        EnableValue
        MAX-ACCESS    read-write
        STATUS        current
        DESCRIPTION   "Administratively enable or disable Premium PIR usage."
	DEFVAL        { enable }
        ::= { rcCosProfileEntry 12 }

rcCosProfileGoldPirUsage OBJECT-TYPE
        SYNTAX        EnableValue
        MAX-ACCESS    read-write
        STATUS        current
        DESCRIPTION   "Administratively enable or disable Gold PIR usage."
	DEFVAL        { enable }
        ::= { rcCosProfileEntry 13 }

rcCosProfileSilverPirUsage OBJECT-TYPE
        SYNTAX        EnableValue
        MAX-ACCESS    read-write
        STATUS        current
        DESCRIPTION   "Administratively enable or disable Silver PIR usage."
	DEFVAL        { enable }
        ::= { rcCosProfileEntry 14 }

rcCosProfilePremiumTBMaxSize   OBJECT-TYPE
        SYNTAX        INTEGER (1..8000) 
        MAX-ACCESS    read-write
        STATUS        current
        DESCRIPTION   "Specifies the Max. Token Bucket size limit for 
		       the Premium bucket, in kilobytes"  
        DEFVAL { 1 }
        ::= { rcCosProfileEntry 15 }

rcCosProfilePremiumTBMaxCtl  OBJECT-TYPE
        SYNTAX        INTEGER { 
                          automatic (1), 
                          manual (2) 
                       }
        MAX-ACCESS    read-write
        STATUS        current
        DESCRIPTION   "Specifies whether the Max. Token Bucket size attribute 
		       rcCosProfilePremiumTBMaxSize is being used to control 
		       the Premium bucket or not. automatic -- does not 
		       use it. manual -- uses it"  
        DEFVAL { automatic }
	::= { rcCosProfileEntry 16 }

rcCosProfileGoldTBMaxSize  OBJECT-TYPE
        SYNTAX        INTEGER (1..8000) 
        MAX-ACCESS    read-write
        STATUS        current
        DESCRIPTION   "Specifies the Max. Token Bucket size limit for 
		       the Gold bucket, in kilobytes"  
        DEFVAL { 1 }
        ::= { rcCosProfileEntry 17 }

rcCosProfileGoldTBMaxCtl  OBJECT-TYPE
        SYNTAX        INTEGER { 
                          automatic (1), 
                          manual (2) 
                       }
        MAX-ACCESS    read-write
        STATUS        current
        DESCRIPTION   "Specifies whether the Max. Token Bucket size attribute 
		       rcCosProfileGoldTBMaxSize is being used to control 
		       the Gold bucket or not. automatic -- does not 
		       use it. manual -- uses it"  
        DEFVAL { automatic }
	::= { rcCosProfileEntry 18 }

rcCosProfileSilverTBMaxSize  OBJECT-TYPE
        SYNTAX        INTEGER (1..8000) 
        MAX-ACCESS    read-write
        STATUS        current
        DESCRIPTION   "Specifies the Max. Token Bucket size limit for 
		       the Silver bucket, in kilobytes"  
        DEFVAL { 1 }
        ::= { rcCosProfileEntry 19 }

rcCosProfileSilverTBMaxCtl  OBJECT-TYPE
        SYNTAX        INTEGER { 
                          automatic (1), 
                          manual (2) 
                       }
        MAX-ACCESS    read-write
        STATUS        current
        DESCRIPTION   "Specifies whether the Max. Token Bucket size attribute 
		       rcCosProfileSilverTBMaxSize is being used to control 
		       the Silver bucket or not. automatic -- does not 
		       use it. manual -- uses it"  
        DEFVAL { automatic }
	::= { rcCosProfileEntry 20 }

rcCosProfileStandardTBMaxSize  OBJECT-TYPE
        SYNTAX        INTEGER (1..8000) 
        MAX-ACCESS    read-write
        STATUS        current
        DESCRIPTION   "Specifies the Max. Token Bucket size limit for 
		       the Standard bucket, in kilobytes"  
        DEFVAL { 1 }
        ::= { rcCosProfileEntry 21 }

rcCosProfileStandardTBMaxCtl  OBJECT-TYPE
        SYNTAX        INTEGER { 
                          automatic (1), 
                          manual (2) 
                       }
        MAX-ACCESS    read-write
        STATUS        current
        DESCRIPTION   "Specifies whether the Max. Token Bucket size attribute 
		       rcCosProfileStandardTBMaxSize is being used to control 
		       the Standard bucket or not. automatic -- does not 
		       use it. manual -- uses it"  
        DEFVAL { automatic }
	::= { rcCosProfileEntry 22 }
rcCosProfileMcastLimitUnits OBJECT-TYPE
        SYNTAX        INTEGER { 
                          unitsOf64Kbps (1), 
                          unitsOf1Mbps (2),
                          unitsOf100Kbps (3)
                       }
        MAX-ACCESS    read-write
        STATUS        current
        DESCRIPTION   "Indicates whether the rcCosProfileMcastLimitRate
		       value is measured in units of 64Kbps or 100Kbps or 1Mbps."  
        DEFVAL { unitsOf64Kbps }
        ::= { rcCosProfileEntry 24 }

rcCosProfileMcastLimitRate OBJECT-TYPE
        SYNTAX        INTEGER (0..1000)
        MAX-ACCESS    read-write
        STATUS        current
        DESCRIPTION   "The value of this object indicates the rate
                       for traffic that has been classified as Mcast.
	               This attribute reflects a maximum data rate.
		       Traffic in excess of this data rate is discarded.
                       If rcCosProfileMcastLimitUnits is set to 1, this
                       value may not exceed 15.If 
		       rcCosProfileMcastLimitUnits is set to 3, this value
		       may not exceed 200."

        DEFVAL { 15 }
        ::= { rcCosProfileEntry 25 }

rcCosProfileMcastLimitUsage OBJECT-TYPE
        SYNTAX        EnableValue
        MAX-ACCESS    read-write
        STATUS        current
        DESCRIPTION   "Administratively enable or disable Macast 
		       rate usage."
	DEFVAL { disable }
        ::= { rcCosProfileEntry 26 }

rcCosProfileMcastLimitTBMaxCtl  OBJECT-TYPE
        SYNTAX        INTEGER { 
                          automatic (1), 
                          manual (2) 
                       }
        MAX-ACCESS    read-write
        STATUS        current
        DESCRIPTION   "Specifies whether the Max. Token Bucket size
		       attribute rcCosProfileMcastLimitTBMaxSize can 
		       be modified by the user or is set internally.
		       automatic -- set internally, manual -- modifiable"  
        DEFVAL { automatic }
	::= { rcCosProfileEntry 27 }

rcCosProfileMcastLimitTBMaxSize  OBJECT-TYPE
        SYNTAX        INTEGER (1..8000) 
        MAX-ACCESS    read-write
        STATUS        current
        DESCRIPTION   "Specifies the Max. Token Bucket size limit for 
		       the Mcast bucket, in kilobytes"  
        DEFVAL { 1 }
        ::= { rcCosProfileEntry 28 }

rcCosProfileCosMap  OBJECT-TYPE
        SYNTAX        OCTET STRING (SIZE (8))
        MAX-ACCESS    read-create
        STATUS        current
        DESCRIPTION   "This indicates the priorit to CoS mapping.
		       The first byte represents the CoS for priority 
		       0 and subsequent bytes represent the CoS for 
		       the remaining 802.1p priorities. Format is 
		       a:b:c:d:e:f:g:h, where 0 <= a,b,c,d,e,f,g,h <= 4.
		       0 represents drop-class, 1 represents best-effort, 
		       2 represents silver, 3 represents gold and 4 
		       represents premium traffic."
        DEFVAL { "1:1:2:2:3:3:4:4" }
        ::= { rcCosProfileEntry 29 }

rcCosProfilePremiumEirUsage  OBJECT-TYPE
        SYNTAX        EnableValue
        MAX-ACCESS    read-create
        STATUS        current
        DESCRIPTION   "Administratively enable or disable Premium EIR usage."
        DEFVAL { disable }
        ::= { rcCosProfileEntry 30 }

rcCosProfilePremiumEirUnits  OBJECT-TYPE
        SYNTAX        INTEGER { 
                          unitsOf64Kbps (1), 
                          unitsOf1Mbps (2),
			  unitsOf100Kbps (3)
                      }
        MAX-ACCESS    read-create
        STATUS        current
        DESCRIPTION   "Indicates whether the Premium EIR value is measured 
		       in units of 64Kbps or 100Kbps or 1Mbps."
        DEFVAL { unitsOf64Kbps }
        ::= { rcCosProfileEntry 31 }

rcCosProfilePremiumEir OBJECT-TYPE
        SYNTAX        INTEGER (0..10000)
        MAX-ACCESS    read-create
        STATUS        current
        DESCRIPTION   "The value of this object indicates the EIR rate
                       for traffic that has been classified as Premium,
                       a NNSC classification that is analogous to DSCP
                       EF, ToS Critical, or 802.1p user priority 6. This
                       attribute reflects the excess rate for Premium 
		       traffic. The excess rate provides per-class control 
		       over the volume of frames marked yellow. If eir 
		       usage is disabled, traffic that goes over the eir 
		       is immediately marked red and dropped. If eir 
		       usage is enabled, traffic that conforms to eir is
		       marked yellow and is passed through the pir token 
		       bucket and all traffic that is over the eir is 
		       marked red and dropped. If Premium EIR units is set 
		       to 64Kbps, this value cannot exceed 15. If it is 
		       set to 100Kbps, this value cannot exceed 200."
        DEFVAL { 0 }
        ::= { rcCosProfileEntry 32 }


rcCosProfilePremiumEirTBMaxCtl  OBJECT-TYPE
        SYNTAX        INTEGER { 
                          automatic (1), 
                          manual (2) 
                      }
        MAX-ACCESS    read-create
        STATUS        current
        DESCRIPTION   "Specifies whether the Max. Token Bucket size 
		       attribute rcCosProfilePremiumEirTBMaxSize can 
		       be modified by the user or is set internally.
		       automatic -- set internally, manual -- modifiable" 
        DEFVAL { automatic }
	::= { rcCosProfileEntry 33 }

rcCosProfilePremiumEirTBMaxSize   OBJECT-TYPE
        SYNTAX        INTEGER (1..8000) 
        MAX-ACCESS    read-create
        STATUS        current
        DESCRIPTION   "Specifies the Max. Token Bucket size limit for 
		       the Premium EIR bucket, in Kilobytes."  
        DEFVAL { 1 }
        ::= { rcCosProfileEntry 34 }

rcCosProfilePremiumCouplingFlag  OBJECT-TYPE
        SYNTAX        EnableValue
        MAX-ACCESS    read-create
        STATUS        current
        DESCRIPTION   "Administratively enable or disable Premium 
		       Coupling Flag."
        DEFVAL { disable }
	::= { rcCosProfileEntry 35 }

rcCosProfileGoldEirUsage  OBJECT-TYPE
        SYNTAX        EnableValue
        MAX-ACCESS    read-create
        STATUS        current
        DESCRIPTION   "Administratively enable or disable Gold EIR usage."
        DEFVAL { disable }
        ::= { rcCosProfileEntry 36 }

rcCosProfileGoldEirUnits  OBJECT-TYPE
        SYNTAX        INTEGER { 
                          unitsOf64Kbps (1), 
                          unitsOf1Mbps (2),
			  unitsOf100Kbps (3)
                      }
        MAX-ACCESS    read-create
        STATUS        current
        DESCRIPTION   "Indicates whether the Gold EIR value is measured 
		       in units of 64Kbps or 100Kbps or 1Mbps."
        DEFVAL { unitsOf64Kbps }
        ::= { rcCosProfileEntry 37 }
 
rcCosProfileGoldEir OBJECT-TYPE
        SYNTAX        INTEGER (0..10000)
        MAX-ACCESS    read-create
        STATUS        current
        DESCRIPTION   "The value of this object indicates the EIR rate
                       for traffic that has been classified as Gold,
                       a NNSC classification that is analogous to DSCP
                       AF3, ToS Flash, or 802.1p user priority 4. This
                       attribute reflects the excess rate for Gold 
		       traffic. The excess rate provides per-class control 
		       over the volume of frames marked yellow. If eir 
		       usage is disabled, traffic that goes over the eir 
		       is immediately marked red and dropped. If eir 
		       usage is enabled, traffic that conforms to eir is
		       marked yellow and is passed through the pir token 
		       bucket and all traffic that is over the eir is 
		       marked red and dropped. If Gold EIR units is set 
		       to 64Kbps, this value cannot exceed 15. If it is 
		       set to 100Kbps, this value cannot exceed 200."
        DEFVAL { 0 }
        ::= { rcCosProfileEntry 38 }

rcCosProfileGoldEirTBMaxCtl  OBJECT-TYPE
        SYNTAX        INTEGER { 
                          automatic (1), 
                          manual (2) 
                      }
        MAX-ACCESS    read-create
        STATUS        current
        DESCRIPTION   "Specifies whether the Max. Token Bucket size 
		       attribute rcCosProfileGoldEirTBMaxSize can 
		       be modified by the user or is set internally.
		       automatic -- set internally, manual -- modifiable" 
        DEFVAL { automatic }
	::= { rcCosProfileEntry 39 }

rcCosProfileGoldEirTBMaxSize   OBJECT-TYPE
        SYNTAX        INTEGER (1..8000) 
        MAX-ACCESS    read-create
        STATUS        current
        DESCRIPTION   "Specifies the Max. Token Bucket size limit for 
		       the Gold EIR bucket, in Kilobytes."  
        DEFVAL { 1 }
        ::= { rcCosProfileEntry 40 }

rcCosProfileGoldCouplingFlag  OBJECT-TYPE
        SYNTAX        EnableValue
        MAX-ACCESS    read-create
        STATUS        current
        DESCRIPTION   "Administratively enable or disable Gold 
		       Coupling Flag."
        DEFVAL { disable }
	::= { rcCosProfileEntry 41 }

rcCosProfileSilverEirUsage  OBJECT-TYPE
        SYNTAX        EnableValue
        MAX-ACCESS    read-create
        STATUS        current
        DESCRIPTION   "Administratively enable or disable Silver EIR usage."
        DEFVAL { disable }
        ::= { rcCosProfileEntry 42 }

rcCosProfileSilverEirUnits  OBJECT-TYPE
        SYNTAX        INTEGER { 
                          unitsOf64Kbps (1), 
                          unitsOf1Mbps (2),
			  unitsOf100Kbps (3)
                      }
        MAX-ACCESS    read-create
        STATUS        current
        DESCRIPTION   "Indicates whether the Silver EIR value is measured 
		       in units of 64Kbps or 100Kbps or 1Mbps."
        DEFVAL { unitsOf64Kbps }
        ::= { rcCosProfileEntry 43 }
 
rcCosProfileSilverEir OBJECT-TYPE
        SYNTAX        INTEGER (0..10000)
        MAX-ACCESS    read-create
        STATUS        current
        DESCRIPTION   "The value of this object indicates the EIR rate
                       for traffic that has been classified as Silver,
                       a NNSC classification that is analogous to DSCP
                       AF2, ToS Immediate, or 802.1p user priority 3. This
                       attribute reflects the excess rate for Silver 
		       traffic. The excess rate provides per-class control 
		       over the volume of frames marked yellow. If eir 
		       usage is disabled, traffic that goes over the eir 
		       is immediately marked red and dropped. If eir 
		       usage is enabled, traffic that conforms to eir is
		       marked yellow and is passed through the pir token 
		       bucket and all traffic that is over the eir is 
		       marked red and dropped. If Silver EIR units is set 
		       to 64Kbps, this value cannot exceed 15. If it is 
		       set to 100Kbps, this value cannot exceed 200."
        DEFVAL { 0 }
        ::= { rcCosProfileEntry 44 }

rcCosProfileSilverEirTBMaxCtl  OBJECT-TYPE
        SYNTAX        INTEGER { 
                          automatic (1), 
                          manual (2) 
                      }
        MAX-ACCESS    read-create
        STATUS        current
        DESCRIPTION   "Specifies whether the Max. Token Bucket size 
		       attribute rcCosProfileSilverEirTBMaxSize can 
		       be modified by the user or is set internally.
		       automatic -- set internally, manual -- modifiable" 
        DEFVAL { automatic }
	::= { rcCosProfileEntry 45 }

rcCosProfileSilverEirTBMaxSize   OBJECT-TYPE
        SYNTAX        INTEGER (1..8000) 
        MAX-ACCESS    read-create
        STATUS        current
        DESCRIPTION   "Specifies the Max. Token Bucket size limit for 
		       the Silver EIR bucket, in Kilobytes."  
        DEFVAL { 1 }
        ::= { rcCosProfileEntry 46 }

rcCosProfileSilverCouplingFlag  OBJECT-TYPE
        SYNTAX        EnableValue
        MAX-ACCESS    read-create
        STATUS        current
        DESCRIPTION   "Administratively enable or disable Silver 
		       Coupling Flag."
        DEFVAL { disable }
	::= { rcCosProfileEntry 47 }
 
rcCosProfileStandardCirUnits OBJECT-TYPE
        SYNTAX        INTEGER { 
                          unitsOf64Kbps (1), 
                          unitsOf1Mbps (2),
			  unitsOf100Kbps (3)
                       }
        MAX-ACCESS    read-create
        STATUS        current
        DESCRIPTION   "Indicates whether the rcCosProfileStandardCir value
                       is measured in units of 64Kbps or 100 Kbps or 1Mbps."  
        DEFVAL { 1 }
        ::= { rcCosProfileEntry 48 }
 
rcCosProfileStandardCir OBJECT-TYPE
        SYNTAX        INTEGER (0..10000)
        MAX-ACCESS    read-create
        STATUS        current
        DESCRIPTION   "The value of this object indicates the CIR rate
                       for traffic that has been classified as Standard,
                       a NNSC classification that is analogous to DSCP
                       Standard, ToS Routine, or 802.1p user priority 0. 
                       This attribute reflects a guaranteed data rate 
		       for Standard (best effort) traffic. Traffic that 
		       conforms to cir is marked green and the rest of 
                       the traffic either marked yellow or red based on 
		       eir/pir usage and passed through the EIR and PIR 
		       token buckets. If rcCosProfileStandardCirUnits is 
		       set to 64kbps, this value cannot not exceed 15. 
		       If rcCosProfileStandardCirUnits is set to 100kbps, 
		       this value cannot not exceed 200."
        DEFVAL { 0 }
        ::= { rcCosProfileEntry 49 }

rcCosProfileStandardCirTBMaxCtl  OBJECT-TYPE
        SYNTAX        INTEGER { 
                          automatic (1), 
                          manual (2) 
                      }
        MAX-ACCESS    read-create
        STATUS        current
        DESCRIPTION   "Specifies whether the Max. Token Bucket size 
		       attribute rcCosProfileStandardCirTBMaxSize can 
		       be modified by the user or is set internally.
		       automatic -- set internally, manual -- modifiable" 
        DEFVAL { automatic }
	::= { rcCosProfileEntry 50 }

rcCosProfileStandardCirTBMaxSize   OBJECT-TYPE
        SYNTAX        INTEGER (1..8000) 
        MAX-ACCESS    read-create
        STATUS        current
        DESCRIPTION   "Specifies the Max. Token Bucket size limit for 
		       the Standard CIR bucket, in Kilobytes."  
        DEFVAL { 1 }
        ::= { rcCosProfileEntry 51 }

rcCosProfileStandardEirUsage  OBJECT-TYPE
        SYNTAX        EnableValue
        MAX-ACCESS    read-create
        STATUS        current
        DESCRIPTION   "Administratively enable or disable Standard EIR usage."
        DEFVAL { disable }
        ::= { rcCosProfileEntry 52 }

rcCosProfileStandardEirUnits  OBJECT-TYPE
        SYNTAX        INTEGER { 
                          unitsOf64Kbps (1), 
                          unitsOf1Mbps (2),
			  unitsOf100Kbps (3)
                      }
        MAX-ACCESS    read-create
        STATUS        current
        DESCRIPTION   "Indicates whether the Standard EIR value is measured 
		       in units of 64Kbps or 100Kbps or 1Mbps."
        DEFVAL { unitsOf64Kbps }
        ::= { rcCosProfileEntry 53 }
 
rcCosProfileStandardEir OBJECT-TYPE
        SYNTAX        INTEGER (0..10000)
        MAX-ACCESS    read-create
        STATUS        current
        DESCRIPTION   "The value of this object indicates the EIR rate
                       for traffic that has been classified as Standard,
                       a NNSC classification that is analogous to DSCP
                       Standard, ToS Routine, or 802.1p user priority 0. 
                       This attribute reflects the excess rate for Standard 
		       (best-effort) traffic. The excess rate provides 
		       per-class control over the volume of frames marked 
		       yellow. Traffic that conforms to eir is marked 
		       yellow and is passed through the pir token bucket 
		       and all traffic that is over the eir is marked red 
		       and dropped. If Standard EIR units is set to 64Kbps, 
		       this value cannot exceed 15. If it is set to 100Kbps, 
		       this value cannot exceed 200."
        DEFVAL { 0 }
        ::= { rcCosProfileEntry 54 }

rcCosProfileStandardEirTBMaxCtl  OBJECT-TYPE
        SYNTAX        INTEGER { 
                          automatic (1), 
                          manual (2) 
                      }
        MAX-ACCESS    read-create
        STATUS        current
        DESCRIPTION   "Specifies whether the Max. Token Bucket size 
		       attribute rcCosProfileStandardEirTBMaxSize can 
		       be modified by the user or is set internally.
		       automatic -- set internally, manual -- modifiable" 
        DEFVAL { automatic }
	::= { rcCosProfileEntry 55 }

rcCosProfileStandardEirTBMaxSize   OBJECT-TYPE
        SYNTAX        INTEGER (1..8000) 
        MAX-ACCESS    read-create
        STATUS        current
        DESCRIPTION   "Specifies the Max. Token Bucket size limit for 
		       the Standard EIR bucket, in Kilobytes."  
        DEFVAL { 1 }
        ::= { rcCosProfileEntry 56 }

rcCosProfileStandardCouplingFlag  OBJECT-TYPE
        SYNTAX        EnableValue
        MAX-ACCESS    read-create
        STATUS        current
        DESCRIPTION   "Administratively enable or disable Standard 
		       Coupling Flag."
        DEFVAL { disable }
	::= { rcCosProfileEntry 57 }

rcCosProfileStandardPirUsage OBJECT-TYPE
        SYNTAX        EnableValue
        MAX-ACCESS    read-create
        STATUS        current
        DESCRIPTION   "Administratively enable or disable Standard PIR usage."
	DEFVAL        { enable }
        ::= { rcCosProfileEntry 58 }

rcCosProfileBcastUUcastLimitUsage  OBJECT-TYPE
        SYNTAX        EnableValue
        MAX-ACCESS    read-create
        STATUS        current
        DESCRIPTION   "Administratively enable or disable Broadcast/
		       Unknown Unicast rate usage."
        DEFVAL { disable }
        ::= { rcCosProfileEntry 59 }

rcCosProfileBcastUUcastLimitUnits  OBJECT-TYPE
        SYNTAX        INTEGER { 
                          unitsOf64Kbps (1), 
                          unitsOf1Mbps (2),
			  unitsOf100Kbps (3)
                      }
        MAX-ACCESS    read-create
        STATUS        current
        DESCRIPTION   "Indicates whether the Broadcast/Unknown 
		       Unicast rate is measured in units of 64Kbps 
		       or 100Kbps or 1Mbps."
        DEFVAL { unitsOf1Mbps }
        ::= { rcCosProfileEntry 60 }
 
rcCosProfileBcastUUcastLimitRate OBJECT-TYPE
        SYNTAX        INTEGER (0..10000)
        MAX-ACCESS    read-create
        STATUS        current
        DESCRIPTION   "The value of this object indicates the rate 
                       for the traffic that has been classified as 
                       Broadcast/Unknown Unicast. This attribute 
                       reflects a maximum data rate. Traffic in 
                       excess of this data rate is discarded. If 
		       Broadcast/Unknown Unicast Limit units is set 
		       to 64Kbps, this value cannot exceed 15. If it is 
		       set to 100Kbps, this value cannot exceed 200."
        DEFVAL { 1000 }
        ::= { rcCosProfileEntry 61 }

rcCosProfileBcastUUcastLimitTBMaxCtl  OBJECT-TYPE
        SYNTAX        INTEGER { 
                          automatic (1), 
                          manual (2) 
                      }
        MAX-ACCESS    read-create
        STATUS        current
        DESCRIPTION   "Specifies whether the Max. Token Bucket size 
		       attribute rcCosProfileBcastUUcastLimitTBMaxSize can 
		       be modified by the user or is set internally.
		       automatic -- set internally, manual -- modifiable" 
        DEFVAL { automatic }
	::= { rcCosProfileEntry 62 }

rcCosProfileBcastUUcastLimitTBMaxSize   OBJECT-TYPE
        SYNTAX        INTEGER (1..8000) 
        MAX-ACCESS    read-create
        STATUS        current
        DESCRIPTION   "Specifies the Max. Token Bucket size limit for 
		       the Broadcast/Unknown Unicast limit bucket, in 
		       Kilobytes."  
        DEFVAL { 1 }
        ::= { rcCosProfileEntry 63 }



-- rcCosProfileTableSize

rcCosProfileTableSize OBJECT-TYPE
        SYNTAX        Integer32
        MAX-ACCESS    read-only
        STATUS        current
        DESCRIPTION   "Used to indicate the number of entries in the
                       rcCosProfileTable"
        ::= { rcCos 2 }

-- BAN RING Table 

rcBanRingTable OBJECT-TYPE
        SYNTAX        SEQUENCE OF RcBanRingEntry
        MAX-ACCESS    not-accessible
        STATUS        current
        DESCRIPTION   ""
        ::= { rcBanRing 1 }
 
rcBanRingEntry OBJECT-TYPE
        SYNTAX        RcBanRingEntry
        MAX-ACCESS    not-accessible
        STATUS        current
        DESCRIPTION   "BAN ring table entry."
        INDEX         { rcBanRingId }
        ::= { rcBanRingTable 1 }
 
RcBanRingEntry ::=
        SEQUENCE {
                rcBanRingId                    Integer32,
                rcBanRingPrimaryPort           InterfaceIndex,
                rcBanRingSecondaryPort         InterfaceIndex,
                rcBanRingAdminState            EnableValue,
                rcBanRingTxTimer               Integer32,
                rcBanRingOperState             INTEGER,
                rcBanRingName                  DisplayString,
                rcBanRingDiscoverInterval      Integer32,
                rcBanRingRowStatus             RowStatus,
                rcBanRingNumVlanIds            Integer32,
                rcBanRingVlanIds               IdList,
		rcBanRingRrpHello              EnableValue,
                rcBanRingRrpHelloInterval      Integer32,
		rcBanRingClearRrpStats         TruthValue,
		rcBanRingClearRdpStats         TruthValue,
		rcBanRingNumOfUni              Integer32,
		rcBanRingCopyBtagPbits         EnableValue
       }

rcBanRingId OBJECT-TYPE
        SYNTAX        Integer32 (1..254)
        MAX-ACCESS    read-only
        STATUS        current
        DESCRIPTION   "BAN Ring ID."
        ::= { rcBanRingEntry 1 }
 
rcBanRingPrimaryPort OBJECT-TYPE
        SYNTAX        InterfaceIndex
        MAX-ACCESS    read-write
        STATUS        current
        DESCRIPTION   "BAN Ring primaray port number."
        ::= { rcBanRingEntry 2 }
 
rcBanRingSecondaryPort OBJECT-TYPE
        SYNTAX        InterfaceIndex
        MAX-ACCESS    read-write
        STATUS        current
        DESCRIPTION   "BAN Ring secondary port number."
        ::= { rcBanRingEntry 3 }
 
rcBanRingAdminState OBJECT-TYPE
        SYNTAX        EnableValue
        MAX-ACCESS    read-write
        STATUS        current
        DESCRIPTION   "Administratively enable or disable a BAN Ring."
	DEFVAL        { disable }
        ::= { rcBanRingEntry 4 }

rcBanRingTxTimer OBJECT-TYPE
        SYNTAX        Integer32
        MAX-ACCESS    read-write
        STATUS        current
        DESCRIPTION   "BAN Ring TX timer value."
        ::= { rcBanRingEntry 5 }
 
rcBanRingOperState OBJECT-TYPE
        SYNTAX        INTEGER { 
			  down(0),
                          normal(1), 
                          cut(2), 
                          recover(3) 
                       }
        MAX-ACCESS    read-only
        STATUS        current
        DESCRIPTION   "BAN Ring operation status."
        ::= { rcBanRingEntry 6 }

rcBanRingName OBJECT-TYPE
        SYNTAX        DisplayString (SIZE (0..32)) 
        MAX-ACCESS    read-write
        STATUS        current
        DESCRIPTION   "Modification of this field is allowed only
                       when the admin state is disabled."
        ::= { rcBanRingEntry 7 }

rcBanRingDiscoverInterval OBJECT-TYPE
        SYNTAX          Integer32 (1..255)
        UNITS           "seconds"
        MAX-ACCESS      read-write
        STATUS          current
        DESCRIPTION     "The time interval between discovery messages that are
                         generated to check for ring module existence."
        DEFVAL          { 30 }
        ::= { rcBanRingEntry 8 }

rcBanRingRowStatus OBJECT-TYPE
        SYNTAX        RowStatus
        MAX-ACCESS    read-write
        STATUS        current
        DESCRIPTION   "Uses for controlling the creation and
                       deletion of this row."
        ::= { rcBanRingEntry 9 }

rcBanRingNumVlanIds OBJECT-TYPE
        SYNTAX        	Integer32
        MAX-ACCESS      read-only
        STATUS        	current
        DESCRIPTION   	"Used to indicate the number of VLAN IDs that
                      	are stored in the rcBanRingVlanIds variable."
        ::= { rcBanRingEntry 10 }

rcBanRingVlanIds OBJECT-TYPE
        SYNTAX        	IdList (SIZE (4096))
        MAX-ACCESS      read-write
        STATUS        	current
        DESCRIPTION   	"An array used to identify which VLANs this Ring 
                      	is associated with.  Each VLAN ID is stored as a 
		      	two octet value. The first octet in the pair holds
                      	bits 15-8 of the VLAN ID, while the second octet
                      	holds bits 7-0 of the VLAN ID."
        ::= { rcBanRingEntry 11 }

rcBanRingRrpHello OBJECT-TYPE
        SYNTAX        EnableValue
        MAX-ACCESS    read-write
        STATUS        current
        DESCRIPTION   "RRP hello enable or disable a BAN Ring."
	DEFVAL        { disable }
        ::= { rcBanRingEntry 12 }

rcBanRingRrpHelloInterval OBJECT-TYPE
        SYNTAX          Integer32 (1000..60000)
        UNITS           "milliseconds"
        MAX-ACCESS      read-write
        STATUS          current
        DESCRIPTION     "The time interval between hello messages that are
                         generated to the ESU."
        DEFVAL          { 1000 }
        ::= { rcBanRingEntry 13 }

rcBanRingClearRrpStats   OBJECT-TYPE
        SYNTAX          TruthValue
        MAX-ACCESS      read-write
        STATUS          current
        DESCRIPTION     "To clear the RRP sending/receiving and missing 
			 hello message counter"
        DEFVAL          { false }
        ::= { rcBanRingEntry 14 }

rcBanRingClearRdpStats   OBJECT-TYPE
        SYNTAX          TruthValue
        MAX-ACCESS      read-write
        STATUS          current
        DESCRIPTION     "To clear the RDP sending/receiving 
			 message counter"
        DEFVAL          { false }
        ::= { rcBanRingEntry 15 }

rcBanRingNumOfUni OBJECT-TYPE
        SYNTAX        	Integer32
        MAX-ACCESS      read-only
        STATUS        	current
        DESCRIPTION   	"Used to indicate the number of UNIs this ring
                      	is assigned to"
        ::= { rcBanRingEntry 16 }

rcBanRingCopyBtagPbits  OBJECT-TYPE
        SYNTAX        EnableValue
        MAX-ACCESS    read-write
        STATUS        current
        DESCRIPTION   "Administratively enable or disable Copying of Btag Pbits on Ring."
        DEFVAL        { enable }
        ::= { rcBanRingEntry 17 }


-- RBS TOPOLOGY Table 

rcBanRingTopoTable OBJECT-TYPE

        SYNTAX        SEQUENCE OF RcBanRingTopoEntry
        MAX-ACCESS    not-accessible
        STATUS        current
        DESCRIPTION   ""
        ::= { rcBanRing 2 }
 
rcBanRingTopoEntry OBJECT-TYPE
        SYNTAX        RcBanRingTopoEntry
        MAX-ACCESS    not-accessible
        STATUS        current
        DESCRIPTION   "BAN ring topology entry."
        INDEX         { rcBanRingTopoRingId,rcBanRingTopoRbsId }
        ::= { rcBanRingTopoTable 1 }
 
RcBanRingTopoEntry ::=
        SEQUENCE {
                rcBanRingTopoRingId                INTEGER,
                rcBanRingTopoRbsId                 Integer32,
                rcBanRingTopoRbsMac                MacAddress,
                rcBanRingTopoRbsIp                 IpAddress,
                rcBanRingTopoRbsState              INTEGER,
                rcBanRingTopoRbsPortMask           Integer32,
                rcBanRingTopoRbsPortState          Integer32,
		rcBanRingTopoRbsPosition           Integer32,
		rcBanRingTopoRingBreakType         INTEGER,
		rcBanRingTopoRingName              DisplayString
       }

rcBanRingTopoRingId OBJECT-TYPE
        SYNTAX        INTEGER (1..255)
        MAX-ACCESS    read-only
        STATUS        current
        DESCRIPTION   "BAN Ring ID."
        ::= { rcBanRingTopoEntry 1 }
 
rcBanRingTopoRbsId OBJECT-TYPE
        SYNTAX       Integer32 (1..30)
        MAX-ACCESS    read-only
        STATUS        current

        DESCRIPTION   "BAN Ring RBS ID."
        ::= { rcBanRingTopoEntry 2 }
 
rcBanRingTopoRbsMac OBJECT-TYPE
        SYNTAX        MacAddress
        MAX-ACCESS    read-only
        STATUS        current
        DESCRIPTION   "BAN Ring RBS Mac address."
        ::= { rcBanRingTopoEntry 3 }
 
rcBanRingTopoRbsIp OBJECT-TYPE
        SYNTAX        IpAddress
        MAX-ACCESS    read-only
        STATUS        current
        DESCRIPTION   "BAN Ring RBS Ip address."
        ::= { rcBanRingTopoEntry 4 }
 
rcBanRingTopoRbsState OBJECT-TYPE
        SYNTAX        INTEGER { 
                          up(1), 
                          down(2) 
                       }
        MAX-ACCESS    read-only
        STATUS        current
        DESCRIPTION   "BAN Ring RBS operation status."
        ::= { rcBanRingTopoEntry 5 }

rcBanRingTopoRbsPortMask OBJECT-TYPE
        SYNTAX        Integer32
        MAX-ACCESS    read-only
        STATUS        current
        DESCRIPTION   "BAN Ring RBS ports configured mask. Bit Set representation,
		       From less significant bit to the most significant bit.
		       Less significant bit 0 represents to the first port, Less 
		       significant bit 1 represents second port on module. 
		       So on so for ... 
		       Bit clear (0) means port is not configured, 
		       Bit Set(1) means port is configured "
        ::= { rcBanRingTopoEntry 6 }
 
rcBanRingTopoRbsPortState OBJECT-TYPE
        SYNTAX        Integer32
        MAX-ACCESS    read-only
        STATUS        current
        DESCRIPTION   "BAN Ring RBS port state mask. Bit Set representation,
		       From less significant bit to the most significant bit.
		       Less significant bit 0 represents to the first port, Less 
		       significant bit 1 represents second port switch. 
		       So on so for ... 
		       Bit clear (0) means state down, Bit Set(1) means state up"
        ::= { rcBanRingTopoEntry 7 }

rcBanRingTopoRbsPosition  OBJECT-TYPE
        SYNTAX        Integer32
        MAX-ACCESS    read-only
        STATUS        current
        DESCRIPTION   "Postion of the RBS switch in the BAN ring"
        ::= { rcBanRingTopoEntry 8 }       

rcBanRingTopoRingBreakType  OBJECT-TYPE
        SYNTAX        INTEGER {
			normalRing (1),
			primaryHalf(2),
			secondaryHalf(3)
			}
        MAX-ACCESS    read-only
        STATUS        current
        DESCRIPTION   "Represent the RBS switch ring status, `normalRing (1) means ring is 
		       not broken. 'primaryHalf'(2) means ring is broken and this switch is 
		       on the primary half broken ring. 'secondaryHalf'(3) means ring is 
		       broken and this switch is on secondary half ring"
        ::= { rcBanRingTopoEntry 9 }       

rcBanRingTopoRingName OBJECT-TYPE
        SYNTAX        DisplayString (SIZE (1..32)) 
        MAX-ACCESS    read-only
        STATUS        current
        DESCRIPTION   "Ring Name"
        ::= { rcBanRingTopoEntry 10 }

-- Standalone RBS Table 

rcBanRingSaRbsTable OBJECT-TYPE

        SYNTAX        SEQUENCE OF RcBanRingSaRbsEntry
        MAX-ACCESS    not-accessible
        STATUS        current
        DESCRIPTION   "Standalone table contains all entries"
        ::= { rcBanRing 3 }
 
rcBanRingSaRbsEntry OBJECT-TYPE
        SYNTAX        RcBanRingSaRbsEntry
        MAX-ACCESS    not-accessible
        STATUS        current
        DESCRIPTION   "BAN ring table entry."
        INDEX         { rcBanRingSaRbsBanPort }
        ::= { rcBanRingSaRbsTable 1 }
 
RcBanRingSaRbsEntry ::=
        SEQUENCE {
                rcBanRingSaRbsBanPort               InterfaceIndex,
                rcBanRingSaRbsAdminState            EnableValue,
                rcBanRingSaRbsTxTimer               Integer32,
                rcBanRingSaRbsOperState             INTEGER,
                rcBanRingSaRbsDiscoverInterval      Integer32,
                rcBanRingSaRbsRowStatus             RowStatus,
		rcBanRingSaRbsClearRdpStats         TruthValue,
		rcBanRingSaRbsCopyBtagPbits         EnableValue,
		rcBanRingSaRbsEsuIp                 IpAddress  
          }

rcBanRingSaRbsBanPort OBJECT-TYPE
        SYNTAX        InterfaceIndex (64..687)
        MAX-ACCESS    not-accessible
        STATUS        current
        DESCRIPTION   "Standalone RBS BAN port number."
        ::= { rcBanRingSaRbsEntry 1 }
 
rcBanRingSaRbsAdminState OBJECT-TYPE
        SYNTAX        EnableValue
        MAX-ACCESS    read-create
        STATUS        current
        DESCRIPTION   "Administratively enable or disable a Standalone RBS."
	DEFVAL        { disable }
        ::= { rcBanRingSaRbsEntry 2 }

rcBanRingSaRbsTxTimer OBJECT-TYPE
        SYNTAX        Integer32
        MAX-ACCESS    read-create
        STATUS        current
        DESCRIPTION   "Standalone RBS TX timer value."
        ::= { rcBanRingSaRbsEntry 3 }
 
rcBanRingSaRbsOperState OBJECT-TYPE
        SYNTAX        INTEGER {
			  down(0), 
                          normal(1), 
                          cut(2), 
                          recover(3) 
                       }
        MAX-ACCESS    read-only
        STATUS        current
        DESCRIPTION   "Standalone RBS operation status."
        ::= { rcBanRingSaRbsEntry 4 }

rcBanRingSaRbsDiscoverInterval OBJECT-TYPE
        SYNTAX          Integer32 (1..255)
        UNITS           "seconds"
        MAX-ACCESS      read-create
        STATUS          current
        DESCRIPTION     "The time interval between discovery messages that are
                         generated to check for Standalone RBS module existence."
        DEFVAL          { 30 }
        ::= { rcBanRingSaRbsEntry 5 }

rcBanRingSaRbsRowStatus OBJECT-TYPE
        SYNTAX        RowStatus
        MAX-ACCESS    read-create
        STATUS        current
        DESCRIPTION   "Uses for controlling the creation and
                       deletion of this row."
        ::= { rcBanRingSaRbsEntry 6 }

rcBanRingSaRbsClearRdpStats   OBJECT-TYPE
        SYNTAX          TruthValue
        MAX-ACCESS      read-create
        STATUS          current
        DESCRIPTION     "To clear the RDP sending/receiving message counters."
        DEFVAL          { false }
        ::= { rcBanRingSaRbsEntry 7 }

rcBanRingSaRbsCopyBtagPbits   OBJECT-TYPE
        SYNTAX        EnableValue
        MAX-ACCESS    read-create
        STATUS        current
        DESCRIPTION   "Administratively enable or disable of Copying of Btag Pbits on Standalone RBS."
        DEFVAL        { enable }
        ::= { rcBanRingSaRbsEntry 8 }

rcBanRingSaRbsEsuIp   OBJECT-TYPE
        SYNTAX        IpAddress
        MAX-ACCESS    read-only
        STATUS        current
        DESCRIPTION   "Mgmt IP address of the ESU Module. Which is set by 
	               RDP topology"
        ::= { rcBanRingSaRbsEntry 9 }


-- Ban Ring Dual-homing Ring

rcBanDhRingTable OBJECT-TYPE

        SYNTAX        SEQUENCE OF RcBanDhRingEntry
        MAX-ACCESS    not-accessible
        STATUS        current
        DESCRIPTION   "Dual Ring table"
        ::= { rcBanRing 4 }
 
rcBanDhRingEntry OBJECT-TYPE
        SYNTAX        RcBanDhRingEntry
        MAX-ACCESS    not-accessible
        STATUS        current
        DESCRIPTION   "BAN Dual Home ring table entry."
        INDEX         { rcBanDhRingId }
        ::= { rcBanDhRingTable 1 }

RcBanDhRingEntry ::=
        SEQUENCE {
                rcBanDhRingId                    INTEGER,
                rcBanDhRingBanPortType           INTEGER,
                rcBanDhRingPort                  InterfaceIndex,
                rcBanDhRingPartnerPortMac        MacAddress,
		rcBanDhRingIbtPort               InterfaceIndex,
                rcBanDhRingIbtMlt                INTEGER,
                rcBanDhRingIbtVid                INTEGER,
                rcBanDhRingAdminState            EnableValue,
                rcBanDhRingTxTimer               Integer32,
                rcBanDhRingOperState             INTEGER,
                rcBanDhRingName                  DisplayString,
                rcBanDhRingDiscoverInterval      INTEGER,
                rcBanDhRingRowStatus             RowStatus,
                rcBanDhRingNumVlanIds            Integer32,
                rcBanDhRingVlanIds               IdList,
		rcBanDhRingRrpHello              EnableValue,
                rcBanDhRingRrpHelloInterval      INTEGER,
		rcBanDhRingClearRrpStats         TruthValue,
		rcBanDhRingClearRdpStats         TruthValue,
		rcBanDhRingNumOfUni              Integer32
       }

rcBanDhRingId OBJECT-TYPE
        SYNTAX        INTEGER (1..254)
        MAX-ACCESS    not-accessible
        STATUS        current
        DESCRIPTION   "BAN Dual Home Ring ID."
        ::= { rcBanDhRingEntry 1 }

rcBanDhRingBanPortType  OBJECT-TYPE
        SYNTAX          INTEGER {
            primary(1),
            secondary(2)
            }
        MAX-ACCESS      read-create
        STATUS          current
        DESCRIPTION     "Primary/Secondary BAN port type"
        DEFVAL          { primary }
        ::= { rcBanDhRingEntry 2 }

rcBanDhRingPort OBJECT-TYPE
        SYNTAX        InterfaceIndex
        MAX-ACCESS    read-create
        STATUS        current
        DESCRIPTION   "BAN  Dual Home Ring primaray port number."
        ::= { rcBanDhRingEntry 3 }
 
rcBanDhRingPartnerPortMac OBJECT-TYPE
        SYNTAX        MacAddress
        MAX-ACCESS    read-create
        STATUS        current
        DESCRIPTION   "BAN  Dual Home Ring Partner/other port MAC address."
        ::= { rcBanDhRingEntry 4 }

rcBanDhRingIbtPort OBJECT-TYPE
        SYNTAX        InterfaceIndex
        MAX-ACCESS    read-create
        STATUS        current
        DESCRIPTION   "Single link Inter BAN Trunk port number."
        ::= { rcBanDhRingEntry 5 }

rcBanDhRingIbtMlt OBJECT-TYPE
        SYNTAX        INTEGER (0..32)
        MAX-ACCESS    read-create
        STATUS        current
        DESCRIPTION   "Multi-link Inter BAN Trunk MLT interface ID"
        ::= { rcBanDhRingEntry 6 }
 
rcBanDhRingIbtVid OBJECT-TYPE
        SYNTAX        INTEGER (0..4094) 
        MAX-ACCESS    read-create
        STATUS        current
        DESCRIPTION   "BAN Dual Home Ring IBT port VID number."
        ::= { rcBanDhRingEntry 7 }

rcBanDhRingAdminState OBJECT-TYPE
        SYNTAX        EnableValue
        MAX-ACCESS    read-create
        STATUS        current
        DESCRIPTION   "Administratively enable or disable a BAN Dual Home Ring."
	DEFVAL        { disable }
        ::= { rcBanDhRingEntry 8 }

rcBanDhRingTxTimer OBJECT-TYPE
        SYNTAX        Integer32
        MAX-ACCESS    read-create
        STATUS        current
        DESCRIPTION   "BAN Dual Home Ring TX timer value."
        ::= { rcBanDhRingEntry 9 }
 
rcBanDhRingOperState OBJECT-TYPE
        SYNTAX        INTEGER { 
			  down(0),
                          normal(1), 
                          cut(2), 
                          recover(3) 
                       }
        MAX-ACCESS    read-only
        STATUS        current
        DESCRIPTION   "BAN Dual Home Ring operation status."
        ::= { rcBanDhRingEntry 10 }

rcBanDhRingName OBJECT-TYPE
        SYNTAX        DisplayString (SIZE (0..32)) 
        MAX-ACCESS    read-create
        STATUS        current
        DESCRIPTION   "Modification of this field is allowed only
                       when the admin state is disabled."
        ::= { rcBanDhRingEntry 11 }

rcBanDhRingDiscoverInterval OBJECT-TYPE
        SYNTAX          INTEGER (1..255)
        UNITS           "seconds"
        MAX-ACCESS      read-create
        STATUS          current
        DESCRIPTION     "The time interval between discovery messages that are
                         generated to check for ring module existence."
        DEFVAL          { 30 }
        ::= { rcBanDhRingEntry 12 }

rcBanDhRingRowStatus OBJECT-TYPE
        SYNTAX        RowStatus
        MAX-ACCESS    read-create
        STATUS        current
        DESCRIPTION   "Uses for controlling the creation and
                       deletion of this row."
        ::= { rcBanDhRingEntry 13 }

rcBanDhRingNumVlanIds OBJECT-TYPE
        SYNTAX        	Integer32
        MAX-ACCESS      read-only
        STATUS        	current
        DESCRIPTION   	"Used to indicate the number of VLAN IDs that
                      	are stored in the rcBanRingVlanIds variable."
        ::= { rcBanDhRingEntry 14 }

rcBanDhRingVlanIds OBJECT-TYPE
        SYNTAX        	IdList (SIZE (4096))
        MAX-ACCESS      read-create
        STATUS        	current
        DESCRIPTION   	"An array used to identify which VLANs this Ring 
                      	is associated with.  Each VLAN ID is stored as a 
		      	two octet value. The first octet in the pair holds
                      	bits 15-8 of the VLAN ID, while the second octet
                      	holds bits 7-0 of the VLAN ID."
        ::= { rcBanDhRingEntry 15 }

rcBanDhRingRrpHello OBJECT-TYPE
        SYNTAX        EnableValue
        MAX-ACCESS    read-create
        STATUS        current
        DESCRIPTION   "RRP hello enable or disable a BAN Ring."
	DEFVAL        { disable }
        ::= { rcBanDhRingEntry 16 }

rcBanDhRingRrpHelloInterval OBJECT-TYPE
        SYNTAX          INTEGER (1000..60000)
        UNITS           "milliseconds"
        MAX-ACCESS      read-create
        STATUS          current
        DESCRIPTION     "The time interval between hello messages that are
                         generated to the ESU."
        DEFVAL          { 1000 }
        ::= { rcBanDhRingEntry 17 }

rcBanDhRingClearRrpStats   OBJECT-TYPE
        SYNTAX          TruthValue
        MAX-ACCESS      read-create
        STATUS          current
        DESCRIPTION     "To clear the RRP sending/receiving and missing 
			 hello message counter"
	DEFVAL          { false }
        ::= { rcBanDhRingEntry 18 }

rcBanDhRingClearRdpStats   OBJECT-TYPE
        SYNTAX          TruthValue
        MAX-ACCESS      read-create
        STATUS          current
        DESCRIPTION     "To clear the RDP sending/receiving message counter"
	DEFVAL          { false }
        ::= { rcBanDhRingEntry 19 }

rcBanDhRingNumOfUni OBJECT-TYPE
        SYNTAX        	Integer32
        MAX-ACCESS      read-only
        STATUS        	current
        DESCRIPTION   	"Used to indicate the number of UNIs this ring
                      	is assigned to"
        ::= { rcBanDhRingEntry 20 } 

-- rcBanRingStatsTable 

rcBanRingStatsTable OBJECT-TYPE

        SYNTAX        SEQUENCE OF RcBanRingStatsEntry
        MAX-ACCESS    not-accessible
        STATUS        current
        DESCRIPTION   "Ban Ring stats table"
        ::= { rcBanRing 5 }
 
rcBanRingStatsEntry OBJECT-TYPE
        SYNTAX        RcBanRingStatsEntry
        MAX-ACCESS    not-accessible
        STATUS        current
        DESCRIPTION   "BAN ring table entry. Contain RRP and Rdp Message
                      sending/receiving and missing counter"
        INDEX         { rcBanRingStatsId }
        ::= { rcBanRingStatsTable 1 }
 
RcBanRingStatsEntry ::= 
        SEQUENCE {
                rcBanRingStatsId                            INTEGER,
                rcBanRingStatsRingOperState                 INTEGER,
                rcBanRingStatsRingName                      DisplayString,
                rcBanRingStatsPrimaryPortTxRrpHello         Counter32,
                rcBanRingStatsPrimaryPortRxRrpHello         Counter32,
                rcBanRingStatsSecondaryPortTxRrpHello       Counter32,  
                rcBanRingStatsSecondaryPortRxRrpHello       Counter32,
                rcBanRingStatsPrimaryPortMissingRrpHello    Counter32,
                rcBanRingStatsSecondaryPortMissingRrpHello  Counter32,
                rcBanRingStatsPrimaryPortTxRdp              Counter32,     
                rcBanRingStatsPrimaryPortRxRdp              Counter32,
                rcBanRingStatsSecondaryPortTxRdp            Counter32,     
                rcBanRingStatsSecondaryPortRxRdp            Counter32
       }

rcBanRingStatsId      OBJECT-TYPE
        SYNTAX        INTEGER (1..254)
        MAX-ACCESS    not-accessible
        STATUS        current
        DESCRIPTION   "BAN Ring ID."
        ::= { rcBanRingStatsEntry 1 }

rcBanRingStatsRingOperState    OBJECT-TYPE
        SYNTAX        INTEGER { 
			  down(0),
                          normal(1), 
                          cut(2), 
                          recover(3) 
                       }
        MAX-ACCESS    read-only
        STATUS        current
        DESCRIPTION   "BAN Ring operation status."
        ::= { rcBanRingStatsEntry 2 }

rcBanRingStatsRingName   OBJECT-TYPE
        SYNTAX        DisplayString (SIZE (0..32)) 
        MAX-ACCESS    read-only
        STATUS        current
        DESCRIPTION   "Name fo the Ban ring"
        ::= { rcBanRingStatsEntry 3 }


rcBanRingStatsPrimaryPortTxRrpHello  OBJECT-TYPE
        SYNTAX         Counter32
        MAX-ACCESS     read-only
        STATUS         current
        DESCRIPTION    "The total Number of RRP Hello messages are 
                       transmitted by primary port"
        ::= { rcBanRingStatsEntry 4 }
                                            
rcBanRingStatsPrimaryPortRxRrpHello  OBJECT-TYPE
        SYNTAX         Counter32
        MAX-ACCESS     read-only
        STATUS         current
        DESCRIPTION    "The total Number of RRP Hello messages are 
                       received on primary port. Every RRP hello message
                       is transmitted by Primary port, is expected to be 
                       responsed by a Connected Port (ESU Port). The
                       respose is a receiving count"
        ::= { rcBanRingStatsEntry 5 }
                          
rcBanRingStatsSecondaryPortTxRrpHello   OBJECT-TYPE 
        SYNTAX         Counter32
        MAX-ACCESS     read-only
        STATUS         current
        DESCRIPTION    "The total Number of RRP Hello messages are 
                       transmitted by Seondary port"
        ::= { rcBanRingStatsEntry 6 }            
                                            
rcBanRingStatsSecondaryPortRxRrpHello   OBJECT-TYPE    
        SYNTAX         Counter32
        MAX-ACCESS     read-only
        STATUS         current
        DESCRIPTION    "The total Number of RRP Hello messages are 
                       received on Secondary port. Every RRP hello message
                       is transmitted by Secondary port, is expected to be 
                       responsed by a Connected Port (ESU Port). The
                       respose is a receiving count"
        ::= { rcBanRingStatsEntry 7 }

rcBanRingStatsPrimaryPortMissingRrpHello  OBJECT-TYPE
        SYNTAX         Counter32
        MAX-ACCESS     read-only
        STATUS         current
        DESCRIPTION    "The total Number of RRP Hello messages responses
                       are missing on Primary port. Each RRP hello
                       message is transmitted by Primary port, 
                       is expected to be responded by a Connected Port
                       (ESU Port). Otherwise, it is a missing count"
        ::= { rcBanRingStatsEntry 8 }                                            
rcBanRingStatsSecondaryPortMissingRrpHello  OBJECT-TYPE
        SYNTAX         Counter32
        MAX-ACCESS     read-only
        STATUS         current
        DESCRIPTION    "The total Number of RRP Hello messages responses
                       are missing on Secondary port. Each RRP hello
                       message is transmitted by Secondary port, 
                       is expected to be respondsed by a Connected Port
                       (ESU Port). Otherwise, it is a missing count"
        ::= { rcBanRingStatsEntry 9 }
                     
rcBanRingStatsPrimaryPortTxRdp   OBJECT-TYPE
        SYNTAX         Counter32
        MAX-ACCESS     read-only
        STATUS         current
        DESCRIPTION    "The total Number of RDP messages are transmitted 
                       by Primary Port." 
        ::= { rcBanRingStatsEntry 10 }

rcBanRingStatsPrimaryPortRxRdp     OBJECT-TYPE
        SYNTAX         Counter32
        MAX-ACCESS     read-only
        STATUS         current
        DESCRIPTION    "The total Number of RDP messages are received 
                       on Primary Port. No RDP Message received on
                       Primary Port if rcBanRingStatsRingOperState is 
                       'normal'."
        ::= { rcBanRingStatsEntry 11 }

rcBanRingStatsSecondaryPortTxRdp   OBJECT-TYPE        
        SYNTAX         Counter32
        MAX-ACCESS     read-only
        STATUS         current
        DESCRIPTION    "The total Number of RDP messages are transmitted 
                       by Secondary Port when rcBanRingStatsRingOperState
                       is in 'cut'. No RDP Tx when it is 'normal'" 
        ::= { rcBanRingStatsEntry 12 }

rcBanRingStatsSecondaryPortRxRdp  OBJECT-TYPE  
       SYNTAX         Counter32
        MAX-ACCESS     read-only
        STATUS         current
        DESCRIPTION    "The total Number of RDP messages received 
                       on Secondary Port." 
        ::= { rcBanRingStatsEntry 13 }

-- rcBanDhRingStatsTable 
rcBanDhRingStatsTable OBJECT-TYPE

        SYNTAX        SEQUENCE OF RcBanDhRingStatsEntry
        MAX-ACCESS    not-accessible
        STATUS        current
        DESCRIPTION   "Ban Ring stats table"
        ::= { rcBanRing 6  }

rcBanDhRingStatsEntry OBJECT-TYPE
        SYNTAX        RcBanDhRingStatsEntry
        MAX-ACCESS    not-accessible
        STATUS        current
        DESCRIPTION   "BAN ring table entry. Contain RRP and Rdp Message
                      sending/receiving and missing counter"
        INDEX         { rcBanDhRingStatsId }
        ::= { rcBanDhRingStatsTable 1 }

RcBanDhRingStatsEntry ::=
        SEQUENCE {
                rcBanDhRingStatsId                         INTEGER,
                rcBanDhRingStatsRingOperState              INTEGER,
                rcBanDhRingStatsRingName                   DisplayString,
                rcBanDhRingStatsRingPortTxRrpHello         Counter32,
                rcBanDhRingStatsRingPortRxRrpHello         Counter32,
                rcBanDhRingStatsIbtPortTxRrpHello          Counter32,
                rcBanDhRingStatsIbtPortRxRrpHello          Counter32,
                rcBanDhRingStatsRingPortMissingRrpHello    Counter32,
                rcBanDhRingStatsIbtPortMissingRrpHello     Counter32,
                rcBanDhRingStatsRingPortTxRdp              Counter32,
                rcBanDhRingStatsRingPortRxRdp              Counter32,
                rcBanDhRingStatsIbtPortRxRdp               Counter32

       }

rcBanDhRingStatsId      OBJECT-TYPE
        SYNTAX        INTEGER (1..254)
        MAX-ACCESS    not-accessible
        STATUS        current
        DESCRIPTION   "BAN Ring ID."
        ::= { rcBanDhRingStatsEntry 1 }

rcBanDhRingStatsRingOperState    OBJECT-TYPE
        SYNTAX        INTEGER {
                          down(0),
                          normal(1),
                          cut(2),
                          recover(3)
                       }
        MAX-ACCESS    read-only
        STATUS        current
        DESCRIPTION   "BAN Ring operation status."
        ::= { rcBanDhRingStatsEntry 2 }

rcBanDhRingStatsRingName   OBJECT-TYPE
        SYNTAX        DisplayString (SIZE (0..32))
        MAX-ACCESS    read-only
        STATUS        current
        DESCRIPTION   "Name fo the Ban ring"
        ::= { rcBanDhRingStatsEntry 3 }


rcBanDhRingStatsRingPortTxRrpHello  OBJECT-TYPE
        SYNTAX         Counter32
        MAX-ACCESS     read-only
        STATUS         current
        DESCRIPTION    "The total Number of RRP Hello messages are
                       transmitted by primary port"
        ::= { rcBanDhRingStatsEntry 4 }

rcBanDhRingStatsRingPortRxRrpHello  OBJECT-TYPE
        SYNTAX         Counter32
        MAX-ACCESS     read-only
        STATUS         current
        DESCRIPTION    "The total Number of RRP Hello messages are
                       received on primary port. Every RRP hello message
                       is transmitted by Ring port, is expected to be
                       responsed by a Connected Port (ESU Port). The
                       respose is a receiving count"
        ::= { rcBanDhRingStatsEntry 5 }

rcBanDhRingStatsIbtPortTxRrpHello   OBJECT-TYPE
        SYNTAX         Counter32
        MAX-ACCESS     read-only
        STATUS         current
        DESCRIPTION    "The total Number of RRP Hello messages are
                       transmitted by Seondary port"
        ::= { rcBanDhRingStatsEntry 6 }

rcBanDhRingStatsIbtPortRxRrpHello   OBJECT-TYPE
        SYNTAX         Counter32
        MAX-ACCESS     read-only
        STATUS         current
        DESCRIPTION    "The total Number of RRP Hello messages are
                       received on Ibt port. Every RRP hello message
                       is transmitted by Ibt port, is expected to be
                       responsed by a Connected Port (ESU Port). The
                       respose is a receiving count"
        ::= { rcBanDhRingStatsEntry 7 }

rcBanDhRingStatsRingPortMissingRrpHello  OBJECT-TYPE
        SYNTAX         Counter32
        MAX-ACCESS     read-only
        STATUS         current
        DESCRIPTION    "The total Number of RRP Hello messages responses
                       are missing on Ring port. Each RRP hello
                       message is transmitted by Ring port,
                       is expected to be responded by a Connected Port
                       (ESU Port). Otherwise, it is a missing count"
        ::= { rcBanDhRingStatsEntry 8 }

rcBanDhRingStatsIbtPortMissingRrpHello  OBJECT-TYPE
        SYNTAX         Counter32
        MAX-ACCESS     read-only
        STATUS         current
        DESCRIPTION    "The total Number of RRP Hello messages responses
                       are missing on Ibt port. Each RRP hello
                       message is transmitted by Ibt port,
                       is expected to be respondsed by a Connected Port
                       (ESU Port). Otherwise, it is a missing count"
        ::= { rcBanDhRingStatsEntry 9 }

rcBanDhRingStatsRingPortTxRdp   OBJECT-TYPE
        SYNTAX         Counter32
        MAX-ACCESS     read-only
        STATUS         current
        DESCRIPTION    "The total Number of RDP messages are transmitted
                       by Ring Port."
        ::= { rcBanDhRingStatsEntry 10 }

rcBanDhRingStatsRingPortRxRdp     OBJECT-TYPE
        SYNTAX         Counter32
        MAX-ACCESS     read-only
        STATUS         current
        DESCRIPTION    "The total Number of RDP messages are received
                       on Ring Port."
        ::= { rcBanDhRingStatsEntry 11 }

rcBanDhRingStatsIbtPortRxRdp  OBJECT-TYPE
       SYNTAX         Counter32
        MAX-ACCESS     read-only
        STATUS         current
        DESCRIPTION    "The total Number of RDP messages received
                       on Ibt Port."
        ::= { rcBanDhRingStatsEntry 12 }

rcBanRingTrapObjects OBJECT IDENTIFIER ::= { rcBanRing 7 }

rcBanRingTrapIndication OBJECT-TYPE
        SYNTAX        INTEGER  {
                                 normal(1),
                                 cut(2),
                                 down(3),
                                 adminDisable(4)
                                }
        MAX-ACCESS    read-only
        STATUS        current
        DESCRIPTION   "The type of trap send is represented"
        ::= { rcBanRingTrapObjects 1 }

rcBanRingTrapReason     OBJECT-TYPE
        SYNTAX          OCTET STRING (SIZE (256))
        MAX-ACCESS      read-only
        STATUS          current
        DESCRIPTION     "The Reason for a Ring Cut situation."
        ::= { rcBanRingTrapObjects 2 }

-- Standalone RBS Stats Table 

rcBanRingSaRbsStatsTable OBJECT-TYPE
        SYNTAX        SEQUENCE OF RcBanRingSaRbsStatsEntry
        MAX-ACCESS    not-accessible
        STATUS        current
        DESCRIPTION   "Standalone stats table"
        ::= { rcBanRing 8 }
 
rcBanRingSaRbsStatsEntry OBJECT-TYPE
        SYNTAX        RcBanRingSaRbsStatsEntry
        MAX-ACCESS    not-accessible
        STATUS        current
        DESCRIPTION   "Standalone RBS statistics entry. Which contains
                       operational state and Rdp rx and tx counter"
        INDEX         { rcBanRingSaRbsStatsBanPort }
        ::= { rcBanRingSaRbsStatsTable 1 }
 
RcBanRingSaRbsStatsEntry ::=
        SEQUENCE {
                rcBanRingSaRbsStatsBanPort            InterfaceIndex,
                rcBanRingSaRbsStatsOperState          INTEGER,
                rcBanRingSaRbsStatsTxRdp              Counter32,     
                rcBanRingSaRbsStatsRxRdp              Counter32
          }

rcBanRingSaRbsStatsBanPort OBJECT-TYPE
        SYNTAX        InterfaceIndex(64..687)
        MAX-ACCESS    not-accessible
        STATUS        current
        DESCRIPTION   "Standalone RBS BAN port number."
        ::= { rcBanRingSaRbsStatsEntry 1 }
 
rcBanRingSaRbsStatsOperState OBJECT-TYPE
        SYNTAX        INTEGER {
			  down(1), 
                          normal(2), 
                          cut(3), 
                          recover(4) 
                       }
        MAX-ACCESS    read-only
        STATUS        current
        DESCRIPTION   "Standalone RBS operation status."
        ::= { rcBanRingSaRbsStatsEntry 2 }

rcBanRingSaRbsStatsTxRdp   OBJECT-TYPE
        SYNTAX         Counter32
        MAX-ACCESS     read-only
        STATUS         current
        DESCRIPTION    "The total number of RDP messages transmitted 
                       by standalone RBS BAN port." 
        ::= { rcBanRingSaRbsStatsEntry 3 }

rcBanRingSaRbsStatsRxRdp     OBJECT-TYPE
        SYNTAX         Counter32
        MAX-ACCESS     read-only
        STATUS         current
        DESCRIPTION    "The total number of RDP messages received 
                       on standalone RBS BAN port."
        ::= { rcBanRingSaRbsStatsEntry 4 }

-- Standalone ESU Topology Table
 
rcEsuStandaloneTopoTable OBJECT-TYPE

        SYNTAX        SEQUENCE OF RcEsuStandaloneTopoEntry
        MAX-ACCESS    not-accessible
        STATUS        current
        DESCRIPTION   "Table contains entrires of topology information
	              of ESU Standalone"
        ::= { rcBanRing 9 }
 
rcEsuStandaloneTopoEntry OBJECT-TYPE
        SYNTAX        RcEsuStandaloneTopoEntry
        MAX-ACCESS    not-accessible
        STATUS        current
        DESCRIPTION   "Entry contains ESU Standalone real time topology information. 
		       If Standalone interface is down or Standalone is disabled, 
		       Topology entry will not exist."
        INDEX         { rcEsuStandaloneTopoPort}
        ::= { rcEsuStandaloneTopoTable 1 }
 
RcEsuStandaloneTopoEntry ::=
        SEQUENCE {
                rcEsuStandaloneTopoPort               InterfaceIndex,
                rcEsuStandaloneTopoEsuId              Integer32,
                rcEsuStandaloneTopoEsuMac             MacAddress,
                rcEsuStandaloneTopoEsuIp              IpAddress,
                rcEsuStandaloneTopoEsuPortMask        Integer32,
                rcEsuStandaloneTopoEsuPortState       Integer32
       }

rcEsuStandaloneTopoPort OBJECT-TYPE
        SYNTAX        InterfaceIndex
        MAX-ACCESS    not-accessible
        STATUS        current
        DESCRIPTION   "ESU Stanalone port interface, which is configured on the 
		       MERS8600"
        ::= { rcEsuStandaloneTopoEntry 1 }
 
rcEsuStandaloneTopoEsuId OBJECT-TYPE
        SYNTAX        Integer32
        MAX-ACCESS    read-only
        STATUS        current

        DESCRIPTION   "Module ID of ESU device which is being connected to the 
		       Standalone interface."
        ::= { rcEsuStandaloneTopoEntry 2 }
 
rcEsuStandaloneTopoEsuMac OBJECT-TYPE
        SYNTAX        MacAddress
        MAX-ACCESS    read-only
        STATUS        current
        DESCRIPTION   "Mgmt Mac address of ESU device which is being connected 
                       to the Standalone interface"
        ::= { rcEsuStandaloneTopoEntry 3 }
 
rcEsuStandaloneTopoEsuIp OBJECT-TYPE
        SYNTAX        IpAddress
        MAX-ACCESS    read-only
        STATUS        current
        DESCRIPTION   "IP address of ESU device which is being connected 
                       to the Standalone interface"
        ::= { rcEsuStandaloneTopoEntry 4 }

rcEsuStandaloneTopoEsuPortMask OBJECT-TYPE
        SYNTAX        Integer32
        MAX-ACCESS    read-only
        STATUS        current
        DESCRIPTION   "ESU device's ports configured mask. Bit Set representation,
		       From less significant bit to the most significant bit.
		       Less significant bit 0 represents to the first port, Less 
		       significant bit 1 represents second port on module. 
		       So on so for ... 
		       Bit clear (0) means port is not configured, 
		       Bit Set(1) means port is configured "
        ::= { rcEsuStandaloneTopoEntry 5 }
 
rcEsuStandaloneTopoEsuPortState OBJECT-TYPE
        SYNTAX        Integer32
        MAX-ACCESS    read-only
        STATUS        current
        DESCRIPTION   "ESU device's port state mask. Bit Set representation,
		       From less significant bit to the most significant bit.
		       Less significant bit 0 represents to the first port, Less 
		       significant bit 1 represents second port switch. 
		       So on so for ... 
		       Bit clear (0) means state down, Bit Set(1) means state up"
        ::= { rcEsuStandaloneTopoEntry 6 }

-- Ring module table

rcRingModuleTable OBJECT-TYPE

        SYNTAX        SEQUENCE OF RcRingModuleEntry
        MAX-ACCESS    not-accessible
        STATUS        current
        DESCRIPTION   "Ring module table"
        ::= { rcRing 1 }

rcRingModuleEntry     OBJECT-TYPE
        SYNTAX        RcRingModuleEntry
        MAX-ACCESS    not-accessible
        STATUS        current
        DESCRIPTION   "Ring module entry."
        INDEX         { rcRingModuleRingId, rcRingModuleModId }
        ::= { rcRingModuleTable 1 }
 
RcRingModuleEntry ::=
        SEQUENCE {
                rcRingModuleRingId                Integer32,
                rcRingModuleModId                 Integer32,
                rcRingModuleOperStatus            INTEGER,
                rcRingModuleAdminState            INTEGER,
		rcRingModuleRingName              DisplayString,
		rcRingModuleUniEndptAction        INTEGER
       }

rcRingModuleRingId    OBJECT-TYPE
        SYNTAX        Integer32 (0..254)
        MAX-ACCESS    not-accessible
        STATUS        current
        DESCRIPTION   "BAN Ring ID."
        ::= { rcRingModuleEntry 1 }
 
rcRingModuleModId     OBJECT-TYPE
        SYNTAX        Integer32 (1..30)
        MAX-ACCESS    not-accessible
        STATUS        current
        DESCRIPTION   "BAN Ring RBS ID."
        ::= { rcRingModuleEntry 2 }
 
rcRingModuleOperStatus  OBJECT-TYPE
        SYNTAX          INTEGER { 
                          up(1), 
                          disabled(2),
                          notpresent(3)
                        }
        MAX-ACCESS      read-only
        STATUS          current
        DESCRIPTION     "BAN Ring RBS operation status."
        ::= { rcRingModuleEntry 3 }

rcRingModuleAdminState OBJECT-TYPE
        SYNTAX         INTEGER { 
			  enabled (1), 
			  disabled(0)
                       }
        MAX-ACCESS     read-write
        STATUS         current
        DESCRIPTION    "BAN Ring RBS administration status."
        ::= { rcRingModuleEntry 4 }

rcRingModuleRingName  OBJECT-TYPE
        SYNTAX        DisplayString (SIZE (1..32)) 
        MAX-ACCESS    read-only
        STATUS        current
        DESCRIPTION   "Ring Name"
        ::= { rcRingModuleEntry 5 }

rcRingModuleUniEndptAction  OBJECT-TYPE
        SYNTAX              INTEGER {
			      disable (0),
		              enable  (1),
			      delete  (2)
			    }
        MAX-ACCESS          read-write
        STATUS              current
        DESCRIPTION         "Delete, disable or enable all of the UNIs and end-points on
                             the ESU"
        ::= { rcRingModuleEntry 6 }       


-- Bidirectional Ring based on R/RS module
rcRingTable OBJECT-TYPE

        SYNTAX        SEQUENCE OF RcRingEntry
        MAX-ACCESS    not-accessible
        STATUS        current
        DESCRIPTION   "Bidirectional ring table"
        ::= { rcRing 2 }

rcRingEntry OBJECT-TYPE
        SYNTAX        RcRingEntry
        MAX-ACCESS    not-accessible
        STATUS        current
        DESCRIPTION   "Bidirectional ring table entry."
        INDEX         { rcRingId }
        ::= { rcRingTable 1 }

RcRingEntry ::=
        SEQUENCE {
                rcRingId                    Integer32,
                rcRingPortType              INTEGER,
                rcRingPort                  InterfaceIndex,
                rcRingPartnerPortMac        MacAddress,
                rcRingRctType               INTEGER,
                rcRingRctPort               InterfaceIndex,
                rcRingRctVid                Integer32,
                rcRingRctMlt                Integer32,
                rcRingRctPbtTg              DisplayString,
                rcRingAdminState            EnableValue,
                rcRingRctHello              EnableValue,
                rcRingRctHelloTimer         Integer32,
                rcRingOperState             INTEGER,
                rcRingName                  DisplayString,
                rcRingDiscoverInterval      Integer32,
                rcRingRowStatus             RowStatus,
                rcRingNumVlanIds            Integer32,
                rcRingVlanIds               IdList,
                rcRingRrpHello              EnableValue, 
                rcRingRrpHelloInterval      Integer32,
                rcRingClearRrpStats         TruthValue,
                rcRingClearRdpStats         TruthValue,
                rcRingPrimaryEsuModIds      IdList,
                rcRingSecondaryEsuModIds    IdList,
                rcRingType                  INTEGER,
                rcRingRctOperState          INTEGER,
                rcRingCopyBtagPbits         EnableValue
       }

rcRingId OBJECT-TYPE
        SYNTAX        Integer32 (1..254)
        MAX-ACCESS    not-accessible
        STATUS        current
        DESCRIPTION   "Bidirectional Ring ID."
        ::= { rcRingEntry 1 }

rcRingPortType  OBJECT-TYPE
        SYNTAX          INTEGER {
            primary(1),
            secondary(2)
            }
        MAX-ACCESS      read-create
        STATUS          current
        DESCRIPTION     "Primary/Secondary Ring Port"
        DEFVAL          { primary }
        ::= { rcRingEntry 2 }

rcRingPort OBJECT-TYPE
        SYNTAX        InterfaceIndex
        MAX-ACCESS    read-create
        STATUS        current
        DESCRIPTION   "Home Ring port number."
        ::= { rcRingEntry 3 }

rcRingPartnerPortMac OBJECT-TYPE
        SYNTAX        MacAddress
        MAX-ACCESS    read-create
        STATUS        current
        DESCRIPTION   "Home Ring Partner's Ring port MAC address."
        ::= { rcRingEntry 4 }

rcRingRctType  OBJECT-TYPE
        SYNTAX          INTEGER {
            none(1),
            vlan(2),
            pbt(3),
            pbb(4)
            }
        MAX-ACCESS      read-create
        STATUS          current
        DESCRIPTION     "Bidirectional Ring Ring Closing Trunk Type"
        DEFVAL          { none }
        ::= { rcRingEntry 5 }

rcRingRctPort OBJECT-TYPE
        SYNTAX        InterfaceIndex
        MAX-ACCESS    read-create
        STATUS        current
        DESCRIPTION   "Single link port number used for RCT."
        ::= { rcRingEntry 6 }

rcRingRctVid OBJECT-TYPE
        SYNTAX        Integer32 (0..4094)
        MAX-ACCESS    read-create
        STATUS        current
        DESCRIPTION   "Bidirectional Ring RCT Vlan Id."
        ::= { rcRingEntry 7 }

rcRingRctMlt OBJECT-TYPE
        SYNTAX        Integer32 (0..256)
        MAX-ACCESS    read-create
        STATUS        current
        DESCRIPTION   "Multi-link Trunk MLT Interface ID used for RCT."
        ::= { rcRingEntry 8 }

rcRingRctPbtTg OBJECT-TYPE
        SYNTAX        DisplayString (SIZE (0..32))
        MAX-ACCESS    read-create
        STATUS        current
        DESCRIPTION   "PBT Trunk group name that is used for RCT."
        ::= { rcRingEntry 9 }

rcRingAdminState OBJECT-TYPE
        SYNTAX        EnableValue
        MAX-ACCESS    read-create
        STATUS        current
        DESCRIPTION   "Administratively enable or disable Bidirectional Ring."
        DEFVAL        { disable }
        ::= { rcRingEntry 10 }

rcRingRctHello OBJECT-TYPE
        SYNTAX        EnableValue
        MAX-ACCESS    read-create
        STATUS        current
        DESCRIPTION   "RCT hello enable or disable."
        DEFVAL        { disable }
        ::= { rcRingEntry 11 }

rcRingRctHelloTimer OBJECT-TYPE
        SYNTAX        Integer32 (1..255)
        UNITS         "seconds"
        MAX-ACCESS    read-create
        STATUS        current
        DESCRIPTION   "Bidirectional Ring RCT Hello timer value in Seconds."
        DEFVAL          { 10 }
        ::= { rcRingEntry 12 }

rcRingOperState OBJECT-TYPE
        SYNTAX        INTEGER {
                          down(1),
                          normal(2),
                          cut(3),
                          rct-cut(4),
                          partner-ring-port-down(5),
                          partner-down(6),
                          recover(7)
                       }
        MAX-ACCESS    read-only
        STATUS        current
        DESCRIPTION   "Bidirectional Ring operation status."
        DEFVAL        { down }
        ::= { rcRingEntry 13 }

rcRingName OBJECT-TYPE
        SYNTAX        DisplayString (SIZE (0..32))
        MAX-ACCESS    read-create
        STATUS        current
        DESCRIPTION   "Modification of this field is allowed only
                       when the admin state is disabled."
        ::= { rcRingEntry 14 }

rcRingDiscoverInterval OBJECT-TYPE
        SYNTAX          Integer32 (1..255)
        UNITS           "seconds"
        MAX-ACCESS      read-create
        STATUS          current
        DESCRIPTION     "The time interval between discovery messages that
                         are generated to check for ring module existence."
        DEFVAL          { 30 }
        ::= { rcRingEntry 15 }

rcRingRowStatus OBJECT-TYPE
        SYNTAX        RowStatus
        MAX-ACCESS    read-create
        STATUS        current
        DESCRIPTION   "Uses for controlling the creation and
                       deletion of this row."
        ::= { rcRingEntry 16 }

rcRingNumVlanIds OBJECT-TYPE
        SYNTAX          Integer32
        MAX-ACCESS      read-only
        STATUS          current
        DESCRIPTION     "Used to indicate the number of VLAN IDs that
                        are stored in the rcBanRingVlanIds variable."
        ::= { rcRingEntry 17 }

rcRingVlanIds OBJECT-TYPE
        SYNTAX          IdList (SIZE (4096))
        MAX-ACCESS      read-create
        STATUS          current
        DESCRIPTION     "An array used to identify which VLANs this
                         Ring is associated with.  Each VLAN ID is 
                         stored as a two octet value. The first octet
                         in the pair holds bits 15-8 of the VLAN ID,
                         while the second octet holds bits 7-0 of the
                         VLAN ID."
        ::= { rcRingEntry 18 }

rcRingRrpHello OBJECT-TYPE
        SYNTAX        EnableValue
        MAX-ACCESS    read-create
        STATUS        current
        DESCRIPTION   "RRP hello enable or disable."
        DEFVAL        { disable }
        ::= { rcRingEntry 19 }

rcRingRrpHelloInterval OBJECT-TYPE
        SYNTAX          Integer32 (1000..10000)
        UNITS           "milliseconds"
        MAX-ACCESS      read-create
        STATUS          current
        DESCRIPTION     "The time interval between hello messages that
                         are generated to the ESU."
        DEFVAL          { 1000 }
        ::= { rcRingEntry 20 }

rcRingClearRrpStats     OBJECT-TYPE
        SYNTAX          TruthValue
        MAX-ACCESS      read-create
        STATUS          current
        DESCRIPTION     "To clear the RRP sending/receiving and missing
                         hello message counter"
        DEFVAL          { false }
        ::= { rcRingEntry 21 }

rcRingClearRdpStats   OBJECT-TYPE
        SYNTAX          TruthValue
        MAX-ACCESS      read-create
        STATUS          current
        DESCRIPTION     "To clear the RDP sending/receiving message counter"
        DEFVAL          { false }
        ::= { rcRingEntry 22 }

rcRingPrimaryEsuModIds OBJECT-TYPE
        SYNTAX          IdList (SIZE (31))
        MAX-ACCESS      read-create
        STATUS          current
        DESCRIPTION     "Each octet represents the module id homed on primary "
        ::= { rcRingEntry 23 }

rcRingSecondaryEsuModIds OBJECT-TYPE
        SYNTAX          IdList (SIZE (31))
        MAX-ACCESS      read-create
        STATUS          current
        DESCRIPTION     " octet represents the module id homed on secondary "
        ::= { rcRingEntry 24 }

rcRingType  OBJECT-TYPE
        SYNTAX          INTEGER {
            single-home(1),
            dual-home(2)
            }
        MAX-ACCESS      read-create
        STATUS          current
        DESCRIPTION     "Primary/Secondary Ring Port"
        DEFVAL          { single-home }
        ::= { rcRingEntry 25 }

rcRingRctOperState OBJECT-TYPE
        SYNTAX        INTEGER {
                          up(1),
                          down(2)
                       }
        MAX-ACCESS    read-only
        STATUS        current
        DESCRIPTION   "Bidirectional Ring Ring Closing Trunk operation status."
        DEFVAL        { down }
        ::= { rcRingEntry 26 }

rcRingCopyBtagPbits OBJECT-TYPE
        SYNTAX        EnableValue
        MAX-ACCESS    read-create
        STATUS        current
        DESCRIPTION   "Administratively enable or disable Copying of Btag Pbits on Ring."
        DEFVAL        { enable }
        ::= { rcRingEntry 27 }

rcRingStatsTable OBJECT-TYPE

        SYNTAX        SEQUENCE OF RcRingStatsEntry
        MAX-ACCESS    not-accessible
        STATUS        current
        DESCRIPTION   "Bidirectional Ring stats table"
        ::= { rcRing 3 }

rcRingStatsEntry OBJECT-TYPE
        SYNTAX        RcRingStatsEntry
        MAX-ACCESS    not-accessible
        STATUS        current
        DESCRIPTION   "Bidirectional Ring table entry. Contain RRP and Rdp Message
                      sending/receiving and missing counter"
        INDEX         { rcRingStatsId }
        ::= { rcRingStatsTable 1 }

RcRingStatsEntry ::=
        SEQUENCE {
                rcRingStatsId                         Integer32,
                rcRingStatsRingOperState              INTEGER,
                rcRingStatsRingName                   DisplayString,
                rcRingStatsRingPortTxRrpHello         Counter32, 
                rcRingStatsRingPortRxRrpHello         Counter32, 
                rcRingStatsRctTxHello                 Counter32,
                rcRingStatsRctRxHello                 Counter32,
                rcRingStatsRingPortMissingRrpHello    Counter32, 
                rcRingStatsRctMissingHello            Counter32,
                rcRingStatsRingPortTxRdp              Counter32,
                rcRingStatsRingPortRxRdp              Counter32,
                rcRingStatsRctRxRdp                   Counter32
       }

rcRingStatsId      OBJECT-TYPE
        SYNTAX        Integer32 (1..254)
        MAX-ACCESS    not-accessible
        STATUS        current
        DESCRIPTION   "Bidirectional Ring ID."
        ::= { rcRingStatsEntry 1 }

rcRingStatsRingOperState    OBJECT-TYPE
        SYNTAX        INTEGER {
                          down(1),
                          normal(2),
                          cut(3),
				  rct-cut(4),
		              partner-ring-port-down(5),
		              partner-down(6),
                          recover(7)
                       }
        MAX-ACCESS    read-only
        STATUS        current
        DESCRIPTION   "Bidirectional Ring operation status."
        ::= { rcRingStatsEntry 2 }

rcRingStatsRingName   OBJECT-TYPE
        SYNTAX        DisplayString (SIZE (0..32))
        MAX-ACCESS    read-only
        STATUS        current
        DESCRIPTION   "Name of the Bidirectional ring"
        ::= { rcRingStatsEntry 3 }


rcRingStatsRingPortTxRrpHello  OBJECT-TYPE
        SYNTAX         Counter32
        MAX-ACCESS     read-only
        STATUS         current
        DESCRIPTION    "The total Number of RRP Hello messages are
                       transmitted by primary port"
        ::= { rcRingStatsEntry 4 }

rcRingStatsRingPortRxRrpHello  OBJECT-TYPE
        SYNTAX         Counter32
        MAX-ACCESS     read-only
        STATUS         current
        DESCRIPTION    "The total Number of RRP Hello messages are
                       received on primary port. Every RRP hello message
                       is transmitted by Ring port, is expected to be
                       responsed by a Connected Port (ESU Port). The
                       respose is a receiving count"
        ::= { rcRingStatsEntry 5 }

rcRingStatsRctTxHello   OBJECT-TYPE
        SYNTAX         Counter32
        MAX-ACCESS     read-only
        STATUS         current
        DESCRIPTION    "The total Number of RRP Hello messages are
                       transmitted by Seondary port"
        ::= { rcRingStatsEntry 6 }

rcRingStatsRctRxHello   OBJECT-TYPE
        SYNTAX         Counter32
        MAX-ACCESS     read-only
        STATUS         current
        DESCRIPTION    "The total Number of RRP Hello messages are
                       received on Ibt port. Every RRP hello message
                       is transmitted by Ibt port, is expected to be
                       responsed by a Connected Port (ESU Port). The
                       respose is a receiving count"
        ::= { rcRingStatsEntry 7 }

rcRingStatsRingPortMissingRrpHello  OBJECT-TYPE
        SYNTAX         Counter32
        MAX-ACCESS     read-only
        STATUS         current
        DESCRIPTION    "The total Number of RRP Hello messages responses
                       are missing on Ring port. Each RRP hello
                       message is transmitted by Ring port,
                       is expected to be responded by a Connected Port
                       (ESU Port). Otherwise, it is a missing count"
        ::= { rcRingStatsEntry 8 }

rcRingStatsRctMissingHello  OBJECT-TYPE
        SYNTAX         Counter32
        MAX-ACCESS     read-only
        STATUS         current
        DESCRIPTION    "The total Number of RRP Hello messages responses
                       are missing on Ibt port. Each RRP hello
                       message is transmitted by Ibt port,
                       is expected to be respondsed by a Connected Port
                       (ESU Port). Otherwise, it is a missing count"
        ::= { rcRingStatsEntry 9 }

rcRingStatsRingPortTxRdp   OBJECT-TYPE
        SYNTAX         Counter32
        MAX-ACCESS     read-only
        STATUS         current
        DESCRIPTION    "The total Number of RDP messages are transmitted
                       by Ring Port."
        ::= { rcRingStatsEntry 10 }

rcRingStatsRingPortRxRdp     OBJECT-TYPE
        SYNTAX         Counter32
        MAX-ACCESS     read-only
        STATUS         current
        DESCRIPTION    "The total Number of RDP messages are received
                       on Ring Port."
        ::= { rcRingStatsEntry 11 }

rcRingStatsRctRxRdp  OBJECT-TYPE
       SYNTAX         Counter32
        MAX-ACCESS     read-only
        STATUS         current
        DESCRIPTION    "The total Number of RDP messages received
                       on Rct."
        ::= { rcRingStatsEntry 12 }

-- Ring Broadcast Group Table

rcRingBcastGroupTable OBJECT-TYPE
        SYNTAX        SEQUENCE OF RcRingBcastGroupEntry
        MAX-ACCESS    not-accessible
        STATUS        current
        DESCRIPTION   ""
        ::= { rcRing 4 }

rcRingBcastGroupEntry OBJECT-TYPE
 	SYNTAX         RcRingBcastGroupEntry
        MAX-ACCESS     not-accessible
        STATUS         current
        DESCRIPTION    "Ring isid mapping entry."
        INDEX         { rcRingBcastGroupRingId, rcRingBcastGroupId}
        ::= { rcRingBcastGroupTable  1 }

RcRingBcastGroupEntry ::=
	SEQUENCE {
		rcRingBcastGroupRingId     	Integer32,
		rcRingBcastGroupId		Integer32,
		rcRingBcastGroupIsidId		Integer32,
		rcRingBcastGroupIpVlan		Integer32,
		rcRingBcastGroupRowStatus       RowStatus
}
	

rcRingBcastGroupRingId  OBJECT-TYPE
        SYNTAX         Integer32 (1..254)
        MAX-ACCESS    not-accessible
        STATUS        current
        DESCRIPTION   "Ring ID."
        ::= {rcRingBcastGroupEntry  1 }

rcRingBcastGroupId OBJECT-TYPE
        SYNTAX         Integer32 (1..250)
        MAX-ACCESS    not-accessible
        STATUS        current
        DESCRIPTION   "Broadcast Group ring."
        ::= {rcRingBcastGroupEntry  2 }

rcRingBcastGroupIsidId OBJECT-TYPE
        SYNTAX        Integer32 (0..16777215)
        MAX-ACCESS    read-create
        STATUS        current
        DESCRIPTION   "Isid Id that mapped to the groupId."
        ::= {rcRingBcastGroupEntry  3 }

rcRingBcastGroupIpVlan OBJECT-TYPE
        SYNTAX        Integer32 (0..4090)
        MAX-ACCESS    read-create
        STATUS        current
        DESCRIPTION   "IpValn Id that mapped to the groupId."
        ::= {rcRingBcastGroupEntry  4 }

rcRingBcastGroupRowStatus OBJECT-TYPE
        SYNTAX        RowStatus
        MAX-ACCESS    read-create
        STATUS        current
        DESCRIPTION   "Uses for controlling the creation and
                       deletion of this row."
        ::= {rcRingBcastGroupEntry  5 }

-- Ring ESU Table

rcRingESUTable OBJECT-TYPE   
        SYNTAX      SEQUENCE OF RcRingESUEntry
        MAX-ACCESS  not-accessible
        STATUS      current
        DESCRIPTION "Dual home ring ESU table with pre-allocated 30 rows"
        ::= { rcRing 5 }

rcRingESUEntry OBJECT-TYPE
        SYNTAX      RcRingESUEntry
        MAX-ACCESS  not-accessible
        STATUS      current
        DESCRIPTION "Ring ESU entry"
        INDEX       { rcRingESURingId, rcRingESUESUId }
        ::= { rcRingESUTable 1 }

RcRingESUEntry ::=
        SEQUENCE {
            rcRingESURingId            Integer32,
            rcRingESUESUId             Integer32,
            rcRingESUQnQEtherType      INTEGER,
            rcRingESUQnQEtherTypeValue Integer32,
	    rcRingESUHomeAssignment    INTEGER,
	    rcRingESUOnRingState       INTEGER
        }

rcRingESURingId OBJECT-TYPE
        SYNTAX      Integer32 (1..254)
        MAX-ACCESS  not-accessible
        STATUS      current
        DESCRIPTION "Ring ID"
        ::= { rcRingESUEntry 1 }

rcRingESUESUId OBJECT-TYPE
        SYNTAX      Integer32 (1..30)
        MAX-ACCESS  not-accessible
        STATUS      current
        DESCRIPTION "ESU ID"
        ::= { rcRingESUEntry 2 }

rcRingESUQnQEtherType OBJECT-TYPE
        SYNTAX      INTEGER {
                        portEtherType(1),
                        dot1q(2),
                        dot1ad(3),
                        et9100(4),
                        et8020(5)
                    }
        MAX-ACCESS  read-create
        STATUS      current
        DESCRIPTION "Meaningful QinQ ethernet Type: dot1aq: 802.1q; dot1ad:
                     802.1ad; et_9100: Other vendor ethernet type; et_8020
                     Nortel MERS/ESU ethernet type; portEtherType: use ring
                     ethernet type"
        ::= { rcRingESUEntry 3 }

rcRingESUQnQEtherTypeValue OBJECT-TYPE
        SYNTAX      Integer32 (1..16777215)
        MAX-ACCESS  read-only
        STATUS      current
        DESCRIPTION "QinQ ethernet type real value: dot1q: 0x8100; dot1ad:
                     0x88a8; 8020: 0x8020; 9100: 0x9100"
        ::= { rcRingESUEntry 4 }

rcRingESUHomeAssignment OBJECT-TYPE
        SYNTAX      INTEGER {
                 	homeOnPrimary(1),
			homeOnSecondary(2),
		        homeNone(3)
                    }
        MAX-ACCESS  read-only
        STATUS      current
        DESCRIPTION "tell if the home of the ESU is provisioned."
        ::= { rcRingESUEntry 5 }

rcRingESUOnRingState OBJECT-TYPE
        SYNTAX      INTEGER {
			presentAndUp(1),
			presentAndDown(2),
			notPresent(3)
		    }	
        MAX-ACCESS  read-only
        STATUS      current
        DESCRIPTION "tell if the ESU is on the ring or not and the ESU state(UP or DOWN)."
        ::= { rcRingESUEntry 6 }


-- TD Connectivity

rcTlsTest		OBJECT IDENTIFIER ::= { rcTdc 1 }

rcTlsTestTdc      OBJECT IDENTIFIER ::= { rcTlsTest 1 }

--
-- rcTlsTestTdc - TD Connectivity Test
--
rcTlsTestTdcTable  OBJECT-TYPE
        SYNTAX          SEQUENCE OF RcTlsTestTdcEntry
        MAX-ACCESS      not-accessible
        STATUS          current
        DESCRIPTION     "Provisioning information for all TD Connectivity
                        tests and each tests' results."
        ::= { rcTlsTestTdc 1 }

rcTlsTestTdcEntry  OBJECT-TYPE
        SYNTAX          RcTlsTestTdcEntry
        MAX-ACCESS      not-accessible
        STATUS          current
        DESCRIPTION     "Provisioning information for a particular TD
                        Connectivity test and the test results."
        INDEX           { rcTlsTestTdcTestId }
        ::= { rcTlsTestTdcTable 1 }

RcTlsTestTdcEntry ::=
        SEQUENCE {
                rcTlsTestTdcTestId        INTEGER,
                rcTlsTestTdcTDI           INTEGER,
                rcTlsTestTdcSrcPortNum    Integer32,
                rcTlsTestTdcDstPortNum    Integer32,
                rcTlsTestTdcSrcPortIP     IpAddress,
                rcTlsTestTdcDstPortIP     IpAddress,
                rcTlsTestTdcPktPriority   INTEGER,
                rcTlsTestTdcPktTimeout    INTEGER,
                rcTlsTestTdcProtocol      INTEGER,
                rcTlsTestTdcTestType      INTEGER,
                rcTlsTestTdcTimeTrace     INTEGER,
                rcTlsTestTdcPriority      TruthValue,
                rcTlsTestTdcPktsSent        Integer32,
                rcTlsTestTdcPktsReceived    Integer32,
                rcTlsTestTdcRttBroadcast    Integer32,
                rcTlsTestTdcRttUnicast      Integer32,
                rcTlsTestTdcPriOpePkt       OCTET STRING,
                rcTlsTestTdcTestDate        OCTET STRING,
                rcTlsTestTdcTestTime        OCTET STRING,
                rcTlsTestTdcTraceInfo       TruthValue,
                rcTlsTestTdcRowStatus       RowStatus,
                rcTlsTestTdcAction          INTEGER,
                rcTlsTestTdcResult          INTEGER,
                rcTlsTestTdcErrorMask       BITS,
                rcTlsTestTdcName          DisplayString,
                rcTlsTestTdcMulticastCnt  INTEGER,
                rcTlsTestTdcUnicastCnt    INTEGER,
                rcTlsTestTdcRepeatCnt     INTEGER,
                rcTlsTestTdcPeriodicRate  INTEGER,
                rcTlsTestTdcPeriodicCount INTEGER,
                rcTlsTestTdcHistoryCnt    INTEGER,
                rcTlsTestTdcRttThreshold  INTEGER,
                rcTlsTestTdcSnmpTrapControl TruthValue,
                rcTlsTestTdcRttBroadcastMin Integer32,
                rcTlsTestTdcRttBroadcastMax Integer32,
                rcTlsTestTdcRttBroadcastAvg Integer32,
                rcTlsTestTdcRttUnicastMin   Integer32,
                rcTlsTestTdcRttUnicastMax   Integer32,
                rcTlsTestTdcRttUnicastAvg   Integer32,
                rcTlsTestTdcHopCountMin     Integer32,
                rcTlsTestTdcHopCountMax     Integer32,
                rcTlsTestTdcHopCountAvg     Integer32,
                rcTlsTestTdcClearHistoryAction INTEGER,
                rcTlsTestTdcScheduled       TruthValue,
                rcTlsTestTdcCurrentPeriodicCount Integer32,
	        rcTlsTestTdcQtag            INTEGER
                }

rcTlsTestTdcTestId  OBJECT-TYPE
        SYNTAX          INTEGER (1..9999)
        MAX-ACCESS      read-only
        STATUS          current
        DESCRIPTION     "The unique TDC test ID for this entry."
        ::= { rcTlsTestTdcEntry 1 }

rcTlsTestTdcTDI  OBJECT-TYPE
        SYNTAX          INTEGER (1..16777215)
        MAX-ACCESS      read-write
        STATUS          current
        DESCRIPTION     "The customer TD on which this test is executed."
        ::= { rcTlsTestTdcEntry 2 }

rcTlsTestTdcSrcPortNum  OBJECT-TYPE
        SYNTAX          Integer32
        MAX-ACCESS      read-write
        STATUS          current
        DESCRIPTION     "An index value that uniquely identifies the TLS
                        interface (UNI port) at the source of the test."
        ::= { rcTlsTestTdcEntry 3 }

rcTlsTestTdcDstPortNum  OBJECT-TYPE
        SYNTAX          Integer32
        MAX-ACCESS      read-write
        STATUS          current
        DESCRIPTION     "An index value that uniquely identifies the
                        destination TLS interface (LAN port)."
        ::= { rcTlsTestTdcEntry 4 }

rcTlsTestTdcSrcPortIP  OBJECT-TYPE
        SYNTAX          IpAddress
        MAX-ACCESS      read-write
        STATUS          current
        DESCRIPTION     "The IP address of the source port or CPU."
        ::= { rcTlsTestTdcEntry 5 }

rcTlsTestTdcDstPortIP  OBJECT-TYPE
        SYNTAX          IpAddress
        MAX-ACCESS      read-write
        STATUS          current
        DESCRIPTION     "The IP address of the destination port or CPU."
        ::= { rcTlsTestTdcEntry 6 }

rcTlsTestTdcPktPriority  OBJECT-TYPE
        SYNTAX          INTEGER (0..7)
        MAX-ACCESS      read-write
        STATUS          current
        DESCRIPTION     "Optional 802.1 network priority to be used for
                        this test. If not specified by the user, the port
                        default priority is assumed."
        ::= { rcTlsTestTdcEntry 7 }

rcTlsTestTdcPktTimeout  OBJECT-TYPE
        SYNTAX          INTEGER (1..120)
        MAX-ACCESS      read-write
        STATUS          current
        DESCRIPTION     "Optional timeout period for the TDC test in seconds.
                        If not specified, a default value of 10 seconds will
                        be used."
        DEFVAL          { 10 }
        ::= { rcTlsTestTdcEntry 8 }

rcTlsTestTdcProtocol  OBJECT-TYPE
        SYNTAX          INTEGER {
                                  l2(1), -- tls/l2
                                  oel2(2),  -- oel2
                                  l2forcedOel2(3)  -- l2 port to send oel2
                        }
        MAX-ACCESS      read-write
        STATUS          current
        DESCRIPTION     "The protocol to use for the TDC test. If not
                        specified by the user, the mode (protocol) of the
                        source UNI port will be assumed."
        ::= { rcTlsTestTdcEntry 9 }

rcTlsTestTdcTestType  OBJECT-TYPE
        SYNTAX          INTEGER {
                                broadcastandunicast(1), -- both (tlsl2)
                                broadcast(2),  -- broadcast only (tlsl2)
                                unicast(3),  -- unicast only
                                multicastandunicast(4),  -- both (oel2)
                                multicast(5)  -- multicast only (oel2)
                        }
        MAX-ACCESS      read-write
        STATUS          current
        DESCRIPTION     "Optional target address of the TDC test. For tlsl2
                        protocol, the options are broadcast and unicast,
                        broadcast only and unicast only. For oel2 protocol,
                        the options are multicast and unicast, multicast only
                        and unicast only. By default, tlsl2 tests use broadcast
                        and unicast while oel2 tests use multicast and uni-cast."
        ::= { rcTlsTestTdcEntry 10 }

rcTlsTestTdcTimeTrace OBJECT-TYPE
        SYNTAX          INTEGER {
                                  none(1), -- basic test
                                  time(2),  -- time info test
                                  trace(3)  -- trace info test
                        }
        MAX-ACCESS      read-write
        STATUS          current
        DESCRIPTION     "Optional data associated with the TDC test. The
                        basic test validates the provisioning associated with
                        the source ports, destination ports and TDs configured
                        in the test. The time test collects the round-trip-time
                        of the packet between source and destination. The trace
                        test collects the IP address, machine adress and port
                        information for nodes along the source to destination
                        path (and back again). If not specified, the basic test
                        is assumed."
        DEFVAL          { 1 }
        ::= { rcTlsTestTdcEntry 11 }

rcTlsTestTdcPriority  OBJECT-TYPE
        SYNTAX          TruthValue
        MAX-ACCESS      read-only
        STATUS          current
        DESCRIPTION     "Boolean value indicating whether the user
                        specified the packet priority or not."
        ::= { rcTlsTestTdcEntry 12 }

rcTlsTestTdcPktsSent  OBJECT-TYPE
        SYNTAX          Integer32
        MAX-ACCESS      read-only
        STATUS          current
        DESCRIPTION     "The number of test packets sent."
        ::= { rcTlsTestTdcEntry 13 }

rcTlsTestTdcPktsReceived  OBJECT-TYPE
        SYNTAX          Integer32
        MAX-ACCESS      read-only
        STATUS          current
        DESCRIPTION     "The number of test packets received."
        ::= { rcTlsTestTdcEntry 14 }

rcTlsTestTdcRttBroadcast  OBJECT-TYPE
        SYNTAX          Integer32
        MAX-ACCESS      read-only
        STATUS          current
        DESCRIPTION     "The round-trip-time of the last broadcast test
                        packet in microseconds."
        ::= { rcTlsTestTdcEntry 15 }

rcTlsTestTdcRttUnicast  OBJECT-TYPE
        SYNTAX          Integer32
        MAX-ACCESS      read-only
        STATUS          current
        DESCRIPTION     "The round-trip-time of the last unicast test
                        packet in microseconds."
        ::= { rcTlsTestTdcEntry 16 }

rcTlsTestTdcPriOpePkt  OBJECT-TYPE
        SYNTAX          OCTET STRING (SIZE (8))
        MAX-ACCESS      read-only
        STATUS          current
        DESCRIPTION     "The OPE network priority. (ie. Customer priority
                        mapped into an OPE priority. Same as tlsTDPriority-Map.)"
        ::= { rcTlsTestTdcEntry 17 }

rcTlsTestTdcTestDate  OBJECT-TYPE
        SYNTAX          OCTET STRING (SIZE (6))
        MAX-ACCESS      read-only
        STATUS          current
        DESCRIPTION     "The local date stamp for the test (DD/MM)."
        ::= { rcTlsTestTdcEntry 18 }

rcTlsTestTdcTestTime  OBJECT-TYPE
        SYNTAX          OCTET STRING (SIZE (9))
        MAX-ACCESS      read-only
        STATUS          current
        DESCRIPTION     "The local time-of-day stamp for the test (HH:MM:SS)."
        ::= { rcTlsTestTdcEntry 19 }

rcTlsTestTdcTraceInfo  OBJECT-TYPE
        SYNTAX          TruthValue
        MAX-ACCESS      read-only
        STATUS          current
        DESCRIPTION     "Boolean value indicating whether the trace info
                        exists for this entry."
        ::= { rcTlsTestTdcEntry 20 }

rcTlsTestTdcRowStatus  OBJECT-TYPE
        SYNTAX          RowStatus
        MAX-ACCESS      read-write
        STATUS          current
        DESCRIPTION     "Used to create/delete an entry in this table"
        ::= { rcTlsTestTdcEntry 21 }

rcTlsTestTdcAction  OBJECT-TYPE
        SYNTAX          INTEGER {
                                none(1), -- no action taken
                                start(2), -- run the specified TDC test one time
                                startPeriodic(3), -- start the specified TDC test for periodic execution
                                abort (4), -- abort the execution of the cur-rent test
                                abortPeriodic(5) -- abort future executions of test (does not halt current test)
        }
        MAX-ACCESS      read-write
        STATUS          current
        DESCRIPTION     "This action controls test execution:  start will exe-cute the test one time; 
			startPeriodic will begin periodic execution of a test;
                        abort termi-nates the test if it is currently executing;
                        abortPeriodic will cancel future executions of a peri-odic test 
			(will not halt a current test).
                        No test results are collected for an aborted test.  
			abort and abortPeriodic have no affect
                        if a test is not running."
        DEFVAL          { none }
        ::= { rcTlsTestTdcEntry 22 }

rcTlsTestTdcResult  OBJECT-TYPE
        SYNTAX          INTEGER {
                                 none(1), -- none of these
                                 inProgress(2), -- action still in progress
                                 success(3), -- action successful
                                 fail(4) -- action failed
                        }
        MAX-ACCESS      read-only
        STATUS          current
        DESCRIPTION     "Result from the last TDC action"
        DEFVAL          { none }
        ::= { rcTlsTestTdcEntry 23 }


rcTlsTestTdcErrorMask  OBJECT-TYPE
        SYNTAX          BITS {
                          unused0(0),
                          bit1(1),
                          bit2(2),
                          bit3(3),
                          bit4(4),
                          bit5(5),
                          bit6(6),
                          bit7(7),
                          bit8(8),
                          bit9(9),
                          bit10(10),
                          bit11(11),
                          bit12(12),
                          bit13(13),
                          bit14(14),
                          bit15(15),
                          bit16(16),
                          bit17(17),
                          bit18(18),
                          bit19(19),
                          bit20(20),
                          bit21(21),
                          bit22(22),
                          unused23(23),
                          unused24(24),
                          bit25(25),
                          bit26(26),
                          bit27(27),
                          unused28(28),
                          unused29(29),
                          unused30(30),
                          unused31(31),
                          unused32(32),
                          bit33(33),
                          bit34(34),
                          bit35(35),
                          bit36(36),
                          bit37(37),
                          bit38(38),
                          bit39(39),
                          bit40(40),
                          bit41(41),
                          bit42(42),
                          bit43(43),
                          bit44(44),
                          bit45(45),
                          bit46(46),
                          bit47(47),
                          bit48(48),
                          bit49(49),
                              bit50(50)
                        }
        MAX-ACCESS      read-only
        STATUS          current
        DESCRIPTION     "The error mask associated with the TDC test. Each bit
                        in the mask represents a specific error. The errors
                        from least significant bit to highest significant bit
                        are:
                        bit  1 - TD nonexistent on destination port
                        bit  2 - TD disabled on destination port
                        bit  3 - TD not assigned to destination port
                        bit  4 - TD filtered on destination NNI port
                        bit  5 - destination port is NNI
                        bit  6 - destination port is craft
                        bit  7 - destination FDB test failed
                        bit  8 - destination administrative state down
                        bit  9 - destination operational state down
                        bit 10 - destination port connectivity mismatch error
                        bit 11 - destination port type mismatch
                        bit 12 - destination port mode mismatch error
                        bit 13 - destination MIB query failed
                        bit 14 - destination system error
                        bit 15 - invalid destination port
                        bit 16 - destination port is CPU
                        bit 17 - destination port mode mismatch warning
                        bit 18 - destination port connectivity mismatch warning
                        bit 19 - default priority used on destination
                        bit 20 - IP not assigned on destination oel2 port
                        bit 21 - static entry exists on destination port
                        bit 22 - destination FDB table full warning
                        bit 25 - Source Uni Not configured for TDC test.
                        bit 26 - Source Uni Endpoint Admin State Disable for TDC test.
                        bit 27 - Source Uni endpoint or TDI not configured for TDC test.
                        bit 33 - TD nonexistent on source port
                        bit 34 - TD not assigned to source port
                        bit 35 - source FDB test failed
                        bit 36 - source administrative state down
                        bit 37 - source operational state down
                        bit 38 - source system error
                        bit 39 - no response
                        bit 40 - could not get trace information
                        bit 41 - could not get time information
                        bit 42 - source MIB query failed
                        bit 43 - TD disabled on source port
                        bit 44 - invalid source port
                        bit 45 - all ports down on the source node
                        bit 46 - unknown error
                        bit 47 - source FDB test failed
                        bit 48 - static entry exists on source port
                        bit 49 - no FDB entry for destination MAC, unicast aborted
                        bit 50 \226 RTT threshold exceeded"
        ::= { rcTlsTestTdcEntry 24 }


rcTlsTestTdcName  OBJECT-TYPE
        SYNTAX          DisplayString(SIZE (0 .. 20))
        MAX-ACCESS      read-write
        STATUS          current
        DESCRIPTION     "An optional user-defined name for this test.  A TDC
                        test name must be unique for each test."
        ::= { rcTlsTestTdcEntry 25 }

rcTlsTestTdcMulticastCnt  OBJECT-TYPE
        SYNTAX          INTEGER (0 .. 100)
        MAX-ACCESS      read-write
        STATUS          current
        DESCRIPTION     "The number of multicast messages sent with each test.
                        A value of zero(0) means the test will look at the FDB
                        for a valid entry, and if one exists a multicast packet
                        will not be sent."
        DEFVAL          { 1 }
        ::= { rcTlsTestTdcEntry 26 }

rcTlsTestTdcUnicastCnt  OBJECT-TYPE
        SYNTAX          INTEGER (0 .. 100)
        MAX-ACCESS      read-write
        STATUS          current
        DESCRIPTION     "The number of unicast messages sent with each test."
        DEFVAL          { 1 }
        ::= { rcTlsTestTdcEntry 27 }

rcTlsTestTdcRepeatCnt  OBJECT-TYPE
        SYNTAX          INTEGER (1 .. 100)
        MAX-ACCESS      read-write
        STATUS          current
        DESCRIPTION     "The number of times a message sequence is executed per
                        test."
        DEFVAL          { 1 }
        ::= { rcTlsTestTdcEntry 28 }


rcTlsTestTdcPeriodicRate  OBJECT-TYPE
        SYNTAX          INTEGER (1..1440)  -- time in minutes
        MAX-ACCESS      read-write
        STATUS          current
        DESCRIPTION     "Used to set a periodic test rate.  The time is
                        in minutes.  The time period ranges from once-a-minute (1) to once-a-day (1440).  A time
                        of zero will cause an error indication if a periodic test is initiated.
                        The test will run at the set rate up to the number of times 
			set via rcTlsTestTdcPeriodicCount.
                        This value can not be changed if a test is currently running periodically.
                        Periodic testing can be halted via rcTlsTestTdcPeriodic-Control."
        DEFVAL          { 1 }
        ::= { rcTlsTestTdcEntry 29 }

rcTlsTestTdcPeriodicCount  OBJECT-TYPE
        SYNTAX          INTEGER (0 .. 1440)
        MAX-ACCESS      read-write
        STATUS          current
        DESCRIPTION     "This object allows the user to place a limit on the number of times 
			 a test running periodically shall run.
                        - 0 : Run indefinitely at the periodic rate set via rcTlsTestTdcPeriodicRate.
                        -  1 .. 1440 : Run this number of times at the periodic rate set via 
			   rcTlsTestTdcPeriodicRate.
                        The maximum allowable value of 1440 allows the user to run at the maximum 
			periodic rate of once-per-minute for a 24-hour period.
                        Beware of the maximum number of samples which may be saved via the 

			TDC history table if you wish to save all the results of a peri-odic TDC test.
                        This value cannot be changed if a test is currently running periodically.  
			Periodic testing can be halted via rcTlsTestTdcPeriodic-Control."
        DEFVAL          { 0 }
        ::= { rcTlsTestTdcEntry 30 }

rcTlsTestTdcHistoryCnt  OBJECT-TYPE
        SYNTAX          INTEGER (1 .. 9999)
        MAX-ACCESS      read-write
        STATUS          current
        DESCRIPTION     "The number of results to be saved for a given TDC test.  The 
			 maximum number of results which may be saved by a given device is
			 obtainable via rcTlsTestTdcHistoryMax.
                         The total amount of storage allocated for all tests cannot exceed 
			 rcTlsTestTdcHistoryMax."
        DEFVAL          { 1 }
        ::= { rcTlsTestTdcEntry 31 }

rcTlsTestTdcRttThreshold  OBJECT-TYPE
        SYNTAX          INTEGER (0 .. 10000)
        MAX-ACCESS      read-write
        STATUS          current
        DESCRIPTION     "The number of milliseconds allowed for a message to
                        make a round trip journey. Exceeding this threshold can
                        cause the generation of an SNMP rcTlsTestTdcTestFailure
                        event, but will not affect continued execution of the
                        test.  A value of 0 indicates the threshold is
                        disabled."
        DEFVAL          { 0 }
        ::= { rcTlsTestTdcEntry 32 }

rcTlsTestTdcSnmpTrapControl  OBJECT-TYPE
        SYNTAX          TruthValue
        MAX-ACCESS      read-write
        STATUS          current
        DESCRIPTION     "Enable or disable the generation of the
                        rcTlsTestTdcTestFailure SNMP trap for this test."
        DEFVAL          { false }
        ::= { rcTlsTestTdcEntry 33 }

rcTlsTestTdcRttBroadcastMin  OBJECT-TYPE
        SYNTAX          Integer32
        MAX-ACCESS      read-only
        STATUS          current
        DESCRIPTION     "The minimum round-trip-time, in microseconds,
                        required by a broadcast test packet over for all
                        executions of this test."
        ::= { rcTlsTestTdcEntry 34 }

rcTlsTestTdcRttBroadcastMax  OBJECT-TYPE
        SYNTAX          Integer32
        MAX-ACCESS      read-only
        STATUS          current
        DESCRIPTION     "The maximum round-trip-time, in microseconds,
                        required by a broadcast test packet for all
                        executions of this test."
        ::= { rcTlsTestTdcEntry 35 }

rcTlsTestTdcRttBroadcastAvg  OBJECT-TYPE
        SYNTAX          Integer32
        MAX-ACCESS      read-only
        STATUS          current
        DESCRIPTION     "The average round-trip-time for a broadcast test
                        packet in microseconds for all executions of this test."
        ::= { rcTlsTestTdcEntry 36 }

rcTlsTestTdcRttUnicastMin  OBJECT-TYPE
        SYNTAX          Integer32
        MAX-ACCESS      read-only
        STATUS          current
        DESCRIPTION     " The minimum round-trip-time, in microseconds,
                        required by a unicast test packet for all
                        executions of this test."
        ::= { rcTlsTestTdcEntry 37 }

rcTlsTestTdcRttUnicastMax  OBJECT-TYPE
        SYNTAX          Integer32
        MAX-ACCESS      read-only
        STATUS          current
        DESCRIPTION     " The maximum round-trip-time, in microseconds,
                        required by a unicast test packet for all
                        executions of this test."
        ::= { rcTlsTestTdcEntry 38 }

rcTlsTestTdcRttUnicastAvg  OBJECT-TYPE
        SYNTAX          Integer32
        MAX-ACCESS      read-only
        STATUS          current
        DESCRIPTION     "The average round-trip-time for a unicast test
                        packet in microseconds for all executions of this test."
        ::= { rcTlsTestTdcEntry 39 }

rcTlsTestTdcHopCountMin  OBJECT-TYPE
        SYNTAX          Integer32
        MAX-ACCESS      read-only
        STATUS          current
        DESCRIPTION     "The minimum hop count for all executions of this test."
        ::= { rcTlsTestTdcEntry 40 }

rcTlsTestTdcHopCountMax  OBJECT-TYPE
        SYNTAX          Integer32
        MAX-ACCESS      read-only
        STATUS          current
        DESCRIPTION     "The maximum hop count for all executions of this test."
        ::= { rcTlsTestTdcEntry 41 }

rcTlsTestTdcHopCountAvg  OBJECT-TYPE
        SYNTAX          Integer32
        MAX-ACCESS      read-only
        STATUS          current
        DESCRIPTION     "The average hop count all executions of this test."
        ::= { rcTlsTestTdcEntry 42 }

rcTlsTestTdcClearHistoryAction OBJECT-TYPE
        SYNTAX          INTEGER {
                                  none(1), -- none of these
                                  clear(2) -- clear history for this test
        }
        MAX-ACCESS      read-write
        STATUS          current
        DESCRIPTION     "The clear option removes all stored test results for
                        this test including the most recent test result.  The clear option has no
                        affect if there are no stored results. A query of this object shall return none(1)."
        DEFVAL          { none }
        ::= { rcTlsTestTdcEntry 43 }

rcTlsTestTdcScheduled  OBJECT-TYPE
        SYNTAX          TruthValue
        MAX-ACCESS      read-only
        STATUS          current
        DESCRIPTION     "Indicates whether this test is currently scheduled to execute in periodic mode.
                        A TRUE response indicates the test is scheduled to run at some future time, and will
                        execute as scheduled unless manually aborted."
        ::= { rcTlsTestTdcEntry 44 }

rcTlsTestTdcCurrentPeriodicCount  OBJECT-TYPE
        SYNTAX          Integer32
        MAX-ACCESS      read-only
        STATUS          current
        DESCRIPTION     "This object returns the current value of the periodic counter.  If the value had been
                        set greater than zero and the test is currently running periodically, then this object
                        is decremented each time the the test runs until a value of zero is reached."
        ::= { rcTlsTestTdcEntry 45 }

rcTlsTestTdcQtag  OBJECT-TYPE
        SYNTAX        INTEGER (0..4096) 
        MAX-ACCESS    read-write
        STATUS        current
        DESCRIPTION   "TDC test Qtag, it is 0 by default. It means the first 
	               Qtag of the Tls Endpoint"
	DEFVAL        { 0 }
        ::= {rcTlsTestTdcEntry 46  }

--
-- Trace Information related to the TDC Test.
-- If rcTlsTestTdcTraceInfo == True, the trace info for the rcTlsTestTdcTestId
-- can be found in this table
--
rcTlsTestTdcTraceTable  OBJECT-TYPE
        SYNTAX          SEQUENCE OF RcTlsTestTdcTraceEntry
        MAX-ACCESS      not-accessible
        STATUS          current
        DESCRIPTION     "Trace information for a TD Connectivity test."
        ::= { rcTlsTestTdc 2}

rcTlsTestTdcTraceEntry  OBJECT-TYPE
        SYNTAX          RcTlsTestTdcTraceEntry
        MAX-ACCESS      not-accessible
        STATUS          current
        DESCRIPTION     "Trace information for the last TD Connectivity test
                        that had the trace functionality enabled."
        INDEX           { rcTlsTestTraceTestId,
                          rcTlsTestTraceTraceType,
                          rcTlsTestTraceTraceSeq }
        ::= { rcTlsTestTdcTraceTable 1 }

RcTlsTestTdcTraceEntry ::=
        SEQUENCE {
                -- index
                rcTlsTestTraceTestId              INTEGER,
                rcTlsTestTraceTraceType           INTEGER,
                rcTlsTestTraceTraceSeq            Integer32,

                -- node info
                rcTlsTestTraceNodeEthAddr         MacAddress,
                rcTlsTestTraceNodeIPAddr          IpAddress,
                rcTlsTestTracePortOut             Integer32,
                rcTlsTestTracePortIn              Integer32
                }

rcTlsTestTraceTestId  OBJECT-TYPE
        SYNTAX          INTEGER (1..9999)
        MAX-ACCESS      read-only
        STATUS          current
        DESCRIPTION     "The unique TDC test ID to which these results
                        correspond."
        ::= { rcTlsTestTdcTraceEntry 1 }

rcTlsTestTraceTraceType  OBJECT-TYPE
        SYNTAX          INTEGER {
                                broadcast(1),
                                multicast(2),
                                unicast(3)
                        }
        MAX-ACCESS      read-only
        STATUS          current
        DESCRIPTION     "Type of TDC test packet for which these results
                        apply."
        ::= { rcTlsTestTdcTraceEntry 2 }

rcTlsTestTraceTraceSeq  OBJECT-TYPE
        SYNTAX          Integer32 (-2147483648..2147483647)
        MAX-ACCESS      read-only
        STATUS          current
        DESCRIPTION     "The trace sequence number associated with this
                        entry."
        ::= { rcTlsTestTdcTraceEntry 3 }

rcTlsTestTraceNodeEthAddr  OBJECT-TYPE
        SYNTAX          MacAddress
        MAX-ACCESS      read-only
        STATUS          current
        DESCRIPTION     "The MAC address of the node by which this sequence
                        entry was generated."
        ::= { rcTlsTestTdcTraceEntry 4 }

rcTlsTestTraceNodeIPAddr  OBJECT-TYPE
        SYNTAX          IpAddress
        MAX-ACCESS      read-only
        STATUS          current
        DESCRIPTION     "The IP address of the node by which this sequence
                        entry was generated."
        ::= { rcTlsTestTdcTraceEntry 5 }

rcTlsTestTracePortOut  OBJECT-TYPE
        SYNTAX          Integer32
        MAX-ACCESS      read-only
        STATUS          current
        DESCRIPTION     "The port number on which this node sent the outbound
                        test packet."
        ::= { rcTlsTestTdcTraceEntry 6 }

rcTlsTestTracePortIn  OBJECT-TYPE
        SYNTAX          Integer32
        MAX-ACCESS      read-only
        STATUS          current
        DESCRIPTION     "The port number on which this node received the
                        inbound test packet."
        ::= { rcTlsTestTdcTraceEntry 7 }

--
-- History Information related to the TDC Test History.
--
rcTlsTestTdcHistoryTable  OBJECT-TYPE
        SYNTAX          SEQUENCE OF RcTlsTestTdcHistoryEntry
        MAX-ACCESS      not-accessible
        STATUS          current
        DESCRIPTION     "History for a TD Connectivity test."
        ::= { rcTlsTestTdc 3}

rcTlsTestTdcHistoryEntry  OBJECT-TYPE
        SYNTAX          RcTlsTestTdcHistoryEntry
        MAX-ACCESS      not-accessible
        STATUS          current
        DESCRIPTION     "History information for the TD Connectivity tests."
        INDEX           { rcTlsTestTdcHistoryTestHId,
                          rcTlsTestTdcHistoryId }
        ::= { rcTlsTestTdcHistoryTable 1 }

RcTlsTestTdcHistoryEntry ::=
        SEQUENCE {
                -- index
                rcTlsTestTdcHistoryTestHId       INTEGER,
                rcTlsTestTdcHistoryId     INTEGER,

                -- history data
                rcTlsTestTdcHistoryPktsSent         Integer32,
                rcTlsTestTdcHistoryPktsReceived     Integer32,
                rcTlsTestTdcHistoryRttBroadcastMin  Integer32,
                rcTlsTestTdcHistoryRttBroadcastMax  Integer32,
                rcTlsTestTdcHistoryRttBroadcastAvg  Integer32,
                rcTlsTestTdcHistoryRttUnicastMin    Integer32,
                rcTlsTestTdcHistoryRttUnicastMax    Integer32,
                rcTlsTestTdcHistoryRttUnicastAvg    Integer32,
                rcTlsTestTdcHistoryRttAvg           Integer32,
                rcTlsTestTdcHistoryHopCountMin      Integer32,
                rcTlsTestTdcHistoryHopCountMax      Integer32,
                rcTlsTestTdcHistoryHopCountAvg      Integer32,
                rcTlsTestTdcHistoryTestDateandTime  DateAndTime,
                rcTlsTestTdcHistoryTimeStamp        TimeStamp,
                rcTlsTestTdcHistoryResult           INTEGER,
                rcTlsTestTdcHistoryErrorMask        BITS
                }

rcTlsTestTdcHistoryTestHId  OBJECT-TYPE
        SYNTAX          INTEGER (1..9999)
        MAX-ACCESS      not-accessible
        STATUS          current
        DESCRIPTION     "The unique TDC test ID for this entry."
        ::= { rcTlsTestTdcHistoryEntry 1 }

rcTlsTestTdcHistoryId  OBJECT-TYPE
        SYNTAX          INTEGER (1 .. 9999)
        MAX-ACCESS      not-accessible
        STATUS          current
        DESCRIPTION     "The history id for this entry.  The device will save up to rcTlsTestTdcHistoryCnt
                        entries per test.  Test results are stored in the next available row, and if more than
                        rcTlsTestTdcHistoryCnt are present the oldest stored re-sult will be removed.
                        Once the maximum row id is reached the index will wrap-around."
        ::= { rcTlsTestTdcHistoryEntry 2 }

rcTlsTestTdcHistoryPktsSent  OBJECT-TYPE
        SYNTAX          Integer32
        MAX-ACCESS      read-only
        STATUS          current
        DESCRIPTION     "The number of packets sent during this test."
        ::= { rcTlsTestTdcHistoryEntry 3 }

rcTlsTestTdcHistoryPktsReceived  OBJECT-TYPE
        SYNTAX          Integer32
        MAX-ACCESS      read-only
        STATUS          current
        DESCRIPTION     "The number of packets received during this test."
        ::= { rcTlsTestTdcHistoryEntry 4 }

rcTlsTestTdcHistoryRttBroadcastMin  OBJECT-TYPE
        SYNTAX          Integer32
        MAX-ACCESS      read-only
        STATUS          current
        DESCRIPTION     "The average broadcast RTT during this test."
        ::= { rcTlsTestTdcHistoryEntry 5 }

rcTlsTestTdcHistoryRttBroadcastMax  OBJECT-TYPE
        SYNTAX          Integer32
        MAX-ACCESS      read-only
        STATUS          current
        DESCRIPTION     "The average broadcast RTT during this test."
        ::= { rcTlsTestTdcHistoryEntry 6 }

rcTlsTestTdcHistoryRttBroadcastAvg  OBJECT-TYPE
        SYNTAX          Integer32
        MAX-ACCESS      read-only
        STATUS          current
        DESCRIPTION     "The average broadcast RTT during this test."
        ::= { rcTlsTestTdcHistoryEntry 7 }

rcTlsTestTdcHistoryRttUnicastMin  OBJECT-TYPE
        SYNTAX          Integer32
        MAX-ACCESS      read-only
        STATUS          current
        DESCRIPTION     "The average unicast RTT during this test."
        ::= { rcTlsTestTdcHistoryEntry 8 }

rcTlsTestTdcHistoryRttUnicastMax  OBJECT-TYPE
        SYNTAX          Integer32
        MAX-ACCESS      read-only
        STATUS          current
        DESCRIPTION     "The average unicast RTT during this test."
        ::= { rcTlsTestTdcHistoryEntry 9 }

rcTlsTestTdcHistoryRttUnicastAvg  OBJECT-TYPE
        SYNTAX          Integer32
        MAX-ACCESS      read-only
        STATUS          current
        DESCRIPTION     "The average unicast RTT during this test."
        ::= { rcTlsTestTdcHistoryEntry 10 }

rcTlsTestTdcHistoryRttAvg  OBJECT-TYPE
        SYNTAX          Integer32
        MAX-ACCESS      read-only
        STATUS          current
        DESCRIPTION     "The average RTT during this test."
        ::= { rcTlsTestTdcHistoryEntry 11 }

rcTlsTestTdcHistoryHopCountMin  OBJECT-TYPE
        SYNTAX          Integer32
        MAX-ACCESS      read-only
        STATUS          current
        DESCRIPTION     "The minimum hop count during this test.  May be
                        invalid if test trace is disabled."
        ::= { rcTlsTestTdcHistoryEntry 12 }

rcTlsTestTdcHistoryHopCountMax  OBJECT-TYPE
        SYNTAX          Integer32
        MAX-ACCESS      read-only
        STATUS          current
        DESCRIPTION     "The maximum hop count during this test.  May be
                        invalid if test trace is disabled."
        ::= { rcTlsTestTdcHistoryEntry 13 }

rcTlsTestTdcHistoryHopCountAvg  OBJECT-TYPE
        SYNTAX          Integer32
        MAX-ACCESS      read-only
        STATUS          current
        DESCRIPTION     "The average hop count during this test.  May be
                        invalid if test trace is disabled."
        ::= { rcTlsTestTdcHistoryEntry 14 }

rcTlsTestTdcHistoryTestDateandTime  OBJECT-TYPE
        SYNTAX          DateAndTime
        MAX-ACCESS      read-only
        STATUS          current
        DESCRIPTION     "The date the test was run."
        ::= { rcTlsTestTdcHistoryEntry 15 }


rcTlsTestTdcHistoryTimeStamp  OBJECT-TYPE
        SYNTAX          TimeStamp
        MAX-ACCESS      read-only
        STATUS          current
        DESCRIPTION     "The value of sysUpTime at which the test began
                        execution."
        ::= { rcTlsTestTdcHistoryEntry 16 }


rcTlsTestTdcHistoryResult  OBJECT-TYPE
        SYNTAX          INTEGER {
                                 none(1), -- none of these
                                 success(3), -- action successful
                                 fail(4) -- action failed
                        }
        MAX-ACCESS      read-only
        STATUS          current
        DESCRIPTION     "Result from the TDC action"
        DEFVAL          { none }
        ::= { rcTlsTestTdcHistoryEntry 17 }

rcTlsTestTdcHistoryErrorMask  OBJECT-TYPE
        SYNTAX          BITS {
                          unused0(0),
                          bit1(1),
                          bit2(2),
                          bit3(3),
                          bit4(4),
                          bit5(5),
                          bit6(6),
                          bit7(7),
                          bit8(8),
                          bit9(9),
                          bit10(10),
                          bit11(11),
                          bit12(12),
                          bit13(13),
                          bit14(14),
                          bit15(15),
                          bit16(16),
                          bit17(17),
                          bit18(18),
                          bit19(19),
                          bit20(20),
                          bit21(21),
                          bit22(22),
                          unused23(23),
                          unused24(24),
                          bit25(25),
                          bit26(26),
                          bit27(27),
                          unused28(28),
                          unused29(29),
                          unused30(30),
                          unused31(31),
                          unused32(32),
                          bit33(33),
                          bit34(34),
                          bit35(35),
                          bit36(36),
                          bit37(37),
                          bit38(38),
                          bit39(39),
                          bit40(40),
                          bit41(41),
                          bit42(42),
                          bit43(43),
                          bit44(44),
                          bit45(45),
                          bit46(46),
                          bit47(47),
                          bit48(48),
                          bit49(49),
                          bit50(50)
                        }
        MAX-ACCESS      read-only
        STATUS          current
        DESCRIPTION     "The error mask associated with the TDC test. Each bit
                        in the mask represents a specific error. The errors
                        from least significant bit to highest significant bit
                        are:
                        bit  1 - TD nonexistent on destination port
                        bit  2 - TD disabled on destination port
                        bit  3 - TD not assigned to destination port
                        bit  4 - TD filtered on destination NNI port
                        bit  5 - destination port is NNI
                        bit  6 - destination port is craft
                        bit  7 - destination FDB test failed
                        bit  8 - destination administrative state down
                        bit  9 - destination operational state down
                        bit 10 - destination port connectivity mismatch error
                        bit 11 - destination port type mismatch
                        bit 12 - destination port mode mismatch error
                        bit 13 - destination MIB query failed
                        bit 14 - destination system error
                        bit 15 - invalid destination port
                        bit 16 - destination port is CPU
                        bit 17 - destination port mode mismatch warning
                        bit 18 - destination port connectivity mismatch warning
                        bit 19 - default priority used on destination
                        bit 20 - IP not assigned on destination oel2 port
                        bit 21 - static entry exists on destination port
                        bit 22 - destination FDB table full warning
                        bit 25 - Source Uni Not configured for TDC test.
                        bit 26 - Source Uni Endpoint Admin State Disable for TDC test.
                        bit 27 - Source Uni endpoint or TDI not configured for TDC test.
                        bit 33 - TD nonexistent on source port
                        bit 34 - TD not assigned to source port
                        bit 35 - source FDB test failed
                        bit 36 - source administrative state down
                        bit 37 - source operational state down
                        bit 38 - source system error
                        bit 39 - no response
                        bit 40 - could not get trace information
                        bit 41 - could not get time information
                        bit 42 - source MIB query failed
                        bit 43 - TD disabled on source port
                        bit 44 - invalid source port
                        bit 45 - all ports down on the source node
                        bit 46 - unknown error
                        bit 47 - source FDB test failed
                        bit 48 - static entry exists on source port
                        bit 49 - no FDB entry for destination MAC, unicast aborted
                        bit 50 \226 RTT threshold exceeded"
        ::= { rcTlsTestTdcHistoryEntry 18 }


rcTlsTestTdcHistoryMax  OBJECT-TYPE
        SYNTAX          INTEGER (1..9999)
        MAX-ACCESS      read-only
        STATUS          obsolete
        DESCRIPTION     "The maximum amount of test history storage available on this device."
        ::= { rcTlsTestTdc 4}

rcTlsTestTdcHistoryRemaining  OBJECT-TYPE
        SYNTAX          INTEGER (1..9999)
        MAX-ACCESS      read-only
        STATUS          obsolete
        DESCRIPTION     "The amount of test history storage remaining unused
                        on this device."
        ::= { rcTlsTestTdc 5}

-- Tdc test result trap type
rcTlsTdcTestResultIndication   OBJECT-TYPE
        SYNTAX        INTEGER {
                tdcTestPass(1),
                tdcTestFail(2)
                  }
        MAX-ACCESS    read-only
        STATUS        current
        DESCRIPTION  " The Tdc Test has passed or failed "
        ::= { rcTlsTestTdc 6 }

rcTlsTdcTestRttExceedIndication   OBJECT-TYPE
        SYNTAX        INTEGER {
                tdcTestRttOK(1),
                tdcTestRttExceed(2)
                  }
        MAX-ACCESS    read-only
        STATUS        current
        DESCRIPTION  " The Tdc Test RTT has exceeded the preset threshold or not"
        ::= { rcTlsTestTdc 7 }

rcTlsTdcTestResultDescription   OBJECT-TYPE
        SYNTAX        OCTET STRING (SIZE(0..255))
        MAX-ACCESS    read-only
        STATUS        current
        DESCRIPTION  " The description of test case result "
        ::= { rcTlsTestTdc 8 }

-- 802.1ah

rcIsidTable OBJECT-TYPE
        SYNTAX        SEQUENCE OF RcIsidEntry
        MAX-ACCESS    not-accessible
        STATUS        current
        DESCRIPTION   "802.1ah Service Identifier table"
        ::= { rc8021ah 1}

rcIsidEntry OBJECT-TYPE
        SYNTAX        RcIsidEntry
        MAX-ACCESS    not-accessible
        STATUS        current
        DESCRIPTION   ""
        INDEX         { rcIsidId }
        ::= { rcIsidTable 1 }

RcIsidEntry ::=
        SEQUENCE {
                    rcIsidId                    INTEGER,
                    rcIsidName                  DisplayString,
                    rcIsidBackboneVlan          INTEGER,
                    rcIsidAdminState            INTEGER,
                    rcIsidRowStatus             RowStatus,
                    rcIsidClearStats            TruthValue,
                    rcIsidAction                INTEGER,
                    rcIsidMacTblSize            INTEGER,
                    rcIsidMacTblWaterMk         INTEGER,
                    rcIsidMacAgeTimer           INTEGER,
                    rcIsidPbtEnable	        EnableValue,
                    rcIsidForceDelete           TruthValue,
		    rcIsidVboEnable	        EnableValue,
		    rcIsidClearVboStats         TruthValue,
                    rcIsidMuxMode               INTEGER,
                    rcIsidNumDestBmacAddr       Integer32,
                    rcIsidBmacAddr              OCTET STRING,
                    rcIsidDirectedMcast		EnableValue,
                    rcIsidVideoType             INTEGER,
		    rcIsidEsuIgmpSnoop          EnableValue,
                    rcIsidPlsb	                INTEGER,
                    rcIsidPlsbEnable	        EnableValue,
                    rcIsidIgmpSnoop             EnableValue,
                    rcIsidIgmpSnoopAndDrop      EnableValue,
                    rcIsidIgmpProxy             EnableValue,
                    rcIsidIgmpFastLeave         EnableValue,
                    rcIsidIgmpMrouterBmacAddr   OCTET STRING,
                    rcIsidNumMrouterBmacAddr    Integer32,
                    rcIsidIgmpHostTimeOut       Integer32,
		    rcIsidDHUni                 INTEGER
                 }

rcIsidId OBJECT-TYPE
        SYNTAX        INTEGER (1..16777215)
        MAX-ACCESS    not-accessible
        STATUS        current
        DESCRIPTION   "Service Instance ID of the I component"
        ::= { rcIsidEntry 1 }
 
rcIsidName OBJECT-TYPE
        SYNTAX        DisplayString (SIZE (0..25)) 
        MAX-ACCESS    read-create
        STATUS        current
        DESCRIPTION   "Name of Service Instance of the I component "
        ::= { rcIsidEntry 2 }

rcIsidBackboneVlan OBJECT-TYPE
        SYNTAX        INTEGER (1..4094)
        MAX-ACCESS    read-create
        STATUS        current
        DESCRIPTION   "Backbone Vlan which is used to carry Service 
                       Instance Over a Provider Backbone network"
        DEFVAL        { 1 }     
        ::= { rcIsidEntry 3 }

rcIsidAdminState OBJECT-TYPE
        SYNTAX        INTEGER {
                         enable(1),
                         disable(2),
                         forceDisable(3)
                      }
        MAX-ACCESS    read-create
        STATUS        current
        DESCRIPTION   "Administratively enable or disable this I Service 
                       Identifier entry."
        DEFVAL        { disable }
        ::= { rcIsidEntry 4 } 

rcIsidRowStatus OBJECT-TYPE
        SYNTAX        RowStatus
        MAX-ACCESS    read-create
        STATUS        current
        DESCRIPTION   "Uses for controlling the creation and
                       deletion of this entry"
        ::= { rcIsidEntry 5 }

rcIsidClearStats OBJECT-TYPE
        SYNTAX        TruthValue
        MAX-ACCESS    read-create
        STATUS        current
        DESCRIPTION   "Action to clear the stats for all endpoint which
                       are associated with this Service Identifier"
        DEFVAL        { false }
        ::= { rcIsidEntry 6 }

rcIsidAction  OBJECT-TYPE
         SYNTAX        INTEGER {
                         none(1),           -- none of the following
                         flushMacFdb(2)     -- flush MAC forwarding table
                        }
        MAX-ACCESS    read-create
        STATUS        current
        DESCRIPTION   "Flush Learned MAC addresses."
        DEFVAL        { none }
        ::= { rcIsidEntry 7 }

rcIsidMacTblSize OBJECT-TYPE
        SYNTAX        INTEGER (0..16384)
        MAX-ACCESS    read-create
        STATUS        current
        DESCRIPTION   "The maximum size of the MAC table. No limit if
                       it's set to 0."
        DEFVAL       { 0 }
        ::= { rcIsidEntry 8 }

rcIsidMacTblWaterMk OBJECT-TYPE
        SYNTAX        INTEGER (0..90)
        MAX-ACCESS    read-create
        STATUS        current
        DESCRIPTION   "The Low Water Mark for MAC table size. Set to 90%
                       of the table size, can be over-written."
        DEFVAL       { 0 }
        ::= { rcIsidEntry 9 }

rcIsidMacAgeTimer OBJECT-TYPE
        SYNTAX        INTEGER (1..65535)
        MAX-ACCESS    read-create
        STATUS        current
        DESCRIPTION   "Remote MAC address ageout timer in seconds."
        DEFVAL        { 300 }
        ::= { rcIsidEntry 10 }

rcIsidPbtEnable OBJECT-TYPE
        SYNTAX        EnableValue
        MAX-ACCESS    read-create
        STATUS        current
        DESCRIPTION   "PBT functionality enable on this ISID"
	DEFVAL        { disable }
        ::= { rcIsidEntry 11 }

rcIsidForceDelete     OBJECT-TYPE
        SYNTAX        TruthValue
        MAX-ACCESS    read-create
        STATUS        current
        DESCRIPTION   "Action to delete the ISID and all its
                       associated end-points"
        DEFVAL        { false }
        ::= { rcIsidEntry 12 }
rcIsidVboEnable OBJECT-TYPE
        SYNTAX        EnableValue
        MAX-ACCESS    read-create
        STATUS        current
        DESCRIPTION   "enable/disable Evpn Broadcast Optimization on this ISID"
	DEFVAL        { disable }
        ::= { rcIsidEntry 13 }

rcIsidClearVboStats OBJECT-TYPE
        SYNTAX        TruthValue
        MAX-ACCESS    read-create
        STATUS        current
        DESCRIPTION   "Clear the Statistics of VPN broadcast optimization."
        DEFVAL        { false }
        ::= { rcIsidEntry 14 }
rcIsidMuxMode OBJECT-TYPE
	SYNTAX INTEGER{
               oneToone(1),    --Only one qtag as member
               manyToOne(2)    --Many qtags as member
              }
	MAX-ACCESS      read-create 
	STATUS          current
 	DESCRIPTION "An end point for thid Isid can have many qtags mapped to 
		     it only if the muxmode is set to manyToOne.For a 		     manyToOne Isid there will not be any remapping of qtags at 
		     the lacal egress"
	DEFVAL     { oneToone }
	::={ rcIsidEntry 15 }

rcIsidNumDestBmacAddr OBJECT-TYPE
        SYNTAX        Integer32
        MAX-ACCESS    read-only
        STATUS        current
        DESCRIPTION   "Stores the number of Destination Bmacs 
                      configured for the I-Sid."
        ::= { rcIsidEntry 16 }

rcIsidBmacAddr OBJECT-TYPE
        SYNTAX        OCTET STRING(SIZE(320))
        MAX-ACCESS    read-create
        STATUS        current
        DESCRIPTION   "A list of Destination Bmac Addresses 
                      configured for this I-SID. There can be 
                      a maximum of 4 B-MAC addresses per I-SID."
        ::= { rcIsidEntry 17 }

rcIsidDirectedMcast OBJECT-TYPE
        SYNTAX        EnableValue
        MAX-ACCESS    read-create
        STATUS        current
        DESCRIPTION   "Disable/Enable directed multicasting on 
                      this I-SID. This will enable directed 
                      multicasting on all the end-points of this I-SID."
        DEFVAL        { disable }
        ::= { rcIsidEntry 18 }

rcIsidVideoType OBJECT-TYPE
        SYNTAX INTEGER{
			none(1),
			targetIsid(2),
			videoIsid(3)
                      }
        MAX-ACCESS      read-create
        STATUS          current
        DESCRIPTION     "The Video service type that this i-sid provides.
                         Target-ISID for delivering IPTV channels to end-points and connecting to VoD servers.
                         Video-ISID for efficient mcast delivery from video head-end to edge MERS"
        DEFVAL        { none }
        ::= { rcIsidEntry 19 }

rcIsidEsuIgmpSnoop              OBJECT-TYPE
        SYNTAX        EnableValue
        MAX-ACCESS    read-create
        STATUS        current
        DESCRIPTION   "Specifies if IGMP snooping is enabled/disabled on the broadcast optimized EVPN VLAN on the ESU"
        DEFVAL        { disable }
        ::= { rcIsidEntry 20 }

rcIsidPlsb       OBJECT-TYPE
        SYNTAX        INTEGER(0..100)
        MAX-ACCESS    read-create
        STATUS        current
        DESCRIPTION   "PLSB instance ID this isid associated to" 
        DEFVAL        { 0 }
        ::= { rcIsidEntry 21 }

rcIsidPlsbEnable OBJECT-TYPE
        SYNTAX        EnableValue
        MAX-ACCESS    read-create
        STATUS        current
        DESCRIPTION   "PLSB functionality enable on this ISID"
	DEFVAL        { disable }
        ::= { rcIsidEntry 22 }

rcIsidIgmpSnoop             OBJECT-TYPE
        SYNTAX        EnableValue
        MAX-ACCESS    read-create
        STATUS        current
        DESCRIPTION   " Enable/Disable snooping of IGMP control frames."
        DEFVAL        { disable }
        ::= { rcIsidEntry  23 }

rcIsidIgmpSnoopAndDrop      OBJECT-TYPE
        SYNTAX        EnableValue
        MAX-ACCESS    read-create
        STATUS        current
        DESCRIPTION  "Enable/Disable snoop and drop of IGMP control frames"
        DEFVAL        { disable }
        ::= { rcIsidEntry  24 }

rcIsidIgmpProxy             OBJECT-TYPE
        SYNTAX        EnableValue
        MAX-ACCESS    read-create
        STATUS        current
        DESCRIPTION  "Enable/Disable proxy of  IGMP control frames"
        DEFVAL        { disable }
        ::= { rcIsidEntry  25 }

rcIsidIgmpFastLeave         OBJECT-TYPE
        SYNTAX        EnableValue
        MAX-ACCESS    read-create
        STATUS        current
        DESCRIPTION  "Enable/Disable fast-leave of IGMP control frames"
        DEFVAL        { enable }
        ::= { rcIsidEntry  26 }

rcIsidIgmpMrouterBmacAddr         OBJECT-TYPE
        SYNTAX        OCTET STRING(SIZE(320))
        MAX-ACCESS    read-create
        STATUS        current
        DESCRIPTION   "A list of uni MAC addresses, to which
                       the Multicast router is connected.
                       A max of 8 mrouter-bmacs may be configured per I-SID"
        ::= { rcIsidEntry  27 }

rcIsidNumMrouterBmacAddr OBJECT-TYPE
        SYNTAX        Integer32
        MAX-ACCESS    read-only
        STATUS        current
        DESCRIPTION   "Stores the number of Mrouter-BMAC addresses
                       configured for the I-Sid."
        ::= { rcIsidEntry 28 }

rcIsidIgmpHostTimeOut OBJECT-TYPE
        SYNTAX        Integer32(60..16777215)
        MAX-ACCESS    read-create
        STATUS        current
        DESCRIPTION   "The time interval in seconds before the snoop
                       records for the I-Sid expire."
        DEFVAL        { 260 }
        ::= { rcIsidEntry 29 }

rcIsidDHUni OBJECT-TYPE
        SYNTAX        INTEGER (0..254)
        MAX-ACCESS    read-create
        STATUS        current
        DESCRIPTION   "Unique dual home UNI Id associated with PLSB Isid."
        DEFVAL        { 0 }  
        ::= { rcIsidEntry 30 }         

-- Isid endpoint table

rcIsidEndptTable OBJECT-TYPE
        SYNTAX        SEQUENCE OF RcIsidEndptEntry
        MAX-ACCESS    not-accessible
        STATUS        current
        DESCRIPTION   ""
        ::= { rc8021ah 2 }
 
rcIsidEndptEntry OBJECT-TYPE
        SYNTAX        RcIsidEndptEntry
        MAX-ACCESS    not-accessible
        STATUS        current
        DESCRIPTION   "A Customer Endpoint table entry."
        INDEX         { rcIsidEndptIsidId, rcIsidEndptTlsIndex }
        ::= { rcIsidEndptTable 1 }
 
RcIsidEndptEntry ::=
        SEQUENCE {
                 rcIsidEndptIsidId                   Integer32,
                 rcIsidEndptTlsIndex                 Integer32,
                 rcIsidEndptPort                     InterfaceIndex,
                 rcIsidEndptQtags                    OCTET STRING,
                 rcIsidEndptNumQtagIds               Integer32,      
                 rcIsidEndptOuterQtag                Integer32,
                 rcIsidEndptConnectType              INTEGER,
                 rcIsidEndptAdminState               EnableValue,
                 rcIsidEndptRemoteMacAddr            MacAddress,
                 rcIsidEndptIngressCosProfileName    DisplayString,
                 rcIsidEndptEgressCosProfileName     DisplayString,
                 rcIsidEndptIngressPolicer           EnableValue,
                 rcIsidEndptEgressPolicer            EnableValue,
                 rcIsidEndptPriMapping               OCTET STRING,
                 rcIsidEndptName                     DisplayString,
                 rcIsidEndptOperState                INTEGER,
                 rcIsidEndptPriOverride              TruthValue,
                 rcIsidEndptBpduTraffic              INTEGER,        
                 rcIsidEndptRowStatus                RowStatus,
                 rcIsidEndptClearStats               TruthValue,
                 rcIsidEndptServiceType              INTEGER,
                 rcIsidEndptMuxMode                  INTEGER,
                 rcIsidEndptMltId                    Integer32,
                 rcIsidEndptTrunkGroup               DisplayString,
		 rcIsidEndptMepList   		     OCTET STRING,
		 rcIsidEndptNumOfMep  		     Integer32,
		 rcIsidEndptClientMepList   	     OCTET STRING,
		 rcIsidEndptNumOfClientMep  	     Integer32,
                 rcIsidEndptRingId		     Integer32,
		 rcIsidEndptModId		     Integer32,
		 rcIsidEndptEsuPort                  Integer32,
		 rcIsidEndptPolicingOption	     INTEGER,
                 rcIsidEndptPriOverrideType          INTEGER,
                 rcIsidEndptColorBasedRemarking      EnableValue,
                 rcIsidEndptDropRedColorPackets      TruthValue,
 	         rcIsidEndptUserLabel1	             OCTET STRING,
	         rcIsidEndptUserLabel2	             OCTET STRING,
		 rcIsidEndptIngressMirrorState       EnableValue,
		 rcIsidEndptEgressMirrorState        EnableValue,
                 rcIsidEndptDefaultIsid              EnableValue,
                 rcIsidEndptL2ptMacSwapCdp           EnableValue,
                 rcIsidEndptL2ptMacSwapVtp           EnableValue,
                 rcIsidEndptL2ptMacSwapStp           EnableValue,
		 rcIsidEndptEndPointId		     Integer32,
                 rcIsidEndptDirectedMcast            EnableValue,
		 rcIsidEndptDEDecodeScheme	     INTEGER,
		 rcIsidEndptPcpDecodeMap	     OCTET STRING,
		 rcIsidEndptCopyItagPcpDeiToStag     EnableValue,
		 rcIsidEndptDhcpL2Relay              EnableValue,
		 rcIsidEndptIgmpAclName              DisplayString,
		 rcIsidEndptIgmpStaticEntriesName    DisplayString,
                 rcIsidEndptL2cpProfile              DisplayString,
                 rcIsidEndptNidMgmtSrcMacState       EnableValue,
                 rcIsidEndptNidMgmtSrcMac            MacAddress,
                 rcIsidEndptNidMgmtSrcIpAddress      IpAddress,
                 rcIsidEndptNidMgmtSrcIpMask         IpAddress,
                 rcIsidEndptCfmIngRateLimitSt        	EnableValue, 
                 rcIsidEndptCfmIngRateLimit          	INTEGER,
                 rcIsidEndptCfmEgrRateLimitSt       	EnableValue,
                 rcIsidEndptCfmEgrRateLimit          	INTEGER,
                 rcIsidEndptDHUId                    		INTEGER,
                 rcIsidEndptDHUOperState            		INTEGER,
                 rcIsidEndptDHUHomeOnMe            	TruthValue,
                 rcIsidEndptCfmIngRateLmtAction      INTEGER,
                 rcIsidEndptCfmEgrRateLmtAction      INTEGER
                 }

rcIsidEndptIsidId OBJECT-TYPE
        SYNTAX        Integer32 (1..16777215)
        MAX-ACCESS    not-accessible
        STATUS        current
        DESCRIPTION   "Service Instance ID of the I component"
        ::= { rcIsidEndptEntry 1 }

rcIsidEndptTlsIndex OBJECT-TYPE
        SYNTAX        Integer32 (1..2147483647)
        MAX-ACCESS    not-accessible
        STATUS        current
        DESCRIPTION   "TLS Index"
        ::= { rcIsidEndptEntry 2 }

rcIsidEndptPort  OBJECT-TYPE
        SYNTAX        InterfaceIndex
        MAX-ACCESS    read-create
        STATUS        current
        DESCRIPTION   "An index value that uniquely identifies a port."
        DEFVAL        { 1 }
        ::= { rcIsidEndptEntry 3 }

rcIsidEndptQtags  OBJECT-TYPE
        SYNTAX        OCTET STRING (SIZE(512))
        MAX-ACCESS    read-create  
        STATUS        current
        DESCRIPTION   "This bitfield indicates which Qtags (in the range
		      1 to 4096) are associated with this end-point. 
		      The Most Significant (left-most) Bit represents Qtag 1.
		      The Least Significant Bit represents Qtag 4096."
        ::= { rcIsidEndptEntry 4 }

rcIsidEndptNumQtagIds  OBJECT-TYPE
        SYNTAX          Integer32
        MAX-ACCESS      read-only
        STATUS          current
        DESCRIPTION     "Used to indicate the number of Qtag IDs that
                        are stored in the rcIsidEndptQtags variable."
        ::= { rcIsidEndptEntry 5 }

rcIsidEndptOuterQtag OBJECT-TYPE
        SYNTAX        Integer32 (0..4094) 
        MAX-ACCESS    read-create
        STATUS        current
        DESCRIPTION   "Outer qtag for QinQ ISID endpoint"
        DEFVAL        { 0 }
        ::= { rcIsidEndptEntry 6 }

rcIsidEndptConnectType OBJECT-TYPE
        SYNTAX        INTEGER {
                          any2any (1),
                          pt2pt   (4)
                         } 
        MAX-ACCESS    read-create
        STATUS        current
        DESCRIPTION   "Type of end-point"
        DEFVAL       { any2any }
        ::= { rcIsidEndptEntry 7 }

rcIsidEndptAdminState OBJECT-TYPE
        SYNTAX        EnableValue
        MAX-ACCESS    read-create
        STATUS        current
        DESCRIPTION   "Admin control of the end-point state."
        DEFVAL        { disable }
        ::= { rcIsidEndptEntry 8 }

rcIsidEndptRemoteMacAddr OBJECT-TYPE
        SYNTAX        MacAddress
        MAX-ACCESS    read-create
        STATUS        current
        DESCRIPTION   "A remote MAC address of other endpoint "
        ::= { rcIsidEndptEntry 9 }

rcIsidEndptIngressCosProfileName OBJECT-TYPE
        SYNTAX        DisplayString (SIZE (0..20)) 
        MAX-ACCESS    read-create
        STATUS        current
        DESCRIPTION   "COS Profile Table Name which is used by
                       this endpoint as ingress policer"
        DEFVAL       { "DEFAULT_PROFILE"  } 
        ::= { rcIsidEndptEntry 10 }

rcIsidEndptEgressCosProfileName OBJECT-TYPE
        SYNTAX        DisplayString (SIZE (0..20)) 
        MAX-ACCESS    read-create
        STATUS        current
        DESCRIPTION   "COS Profile Table Name which is used by 
                       this endpoint as egress policer"
        DEFVAL       { "DEFAULT_PROFILE"  } 
        ::= { rcIsidEndptEntry 11 }

rcIsidEndptIngressPolicer OBJECT-TYPE
        SYNTAX        EnableValue
        MAX-ACCESS    read-create
        STATUS        current
        DESCRIPTION   "Enable/disable to use Ingress Cos Profile table 
                        (rcIsidEndptCosProfileName) "
        DEFVAL        { enable }
        ::= { rcIsidEndptEntry 12 }

rcIsidEndptEgressPolicer OBJECT-TYPE
        SYNTAX        EnableValue
        MAX-ACCESS    read-create
        STATUS        current
        DESCRIPTION   "Enable/disable to use Egress Cos Profile table 
                        (rcIsidEndptEgressCosProfileName) "
        DEFVAL        { disable }
        ::= { rcIsidEndptEntry 13 }

rcIsidEndptPriMapping OBJECT-TYPE
        SYNTAX        OCTET STRING (SIZE(8))
        MAX-ACCESS    read-create
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcIsidEndptEntry 14 }

rcIsidEndptName       OBJECT-TYPE
        SYNTAX        DisplayString (SIZE (0..30)) 
        MAX-ACCESS    read-create
        STATUS        current
        DESCRIPTION   "Name of Endpoint, By default, it would be 
                       'EP-<sid> Port <PortNum>'.
                       Example: sid = 1, port = 1/2, rcIsidEndptName would
                       be 'EP-1 PORT 1/2'"
        ::= { rcIsidEndptEntry 15 }

rcIsidEndptOperState  OBJECT-TYPE
        SYNTAX        INTEGER { 
                          up(1), 
                          down(2),
			  transport-down(3)   
                       }
        MAX-ACCESS    read-only
        STATUS        current
        DESCRIPTION   "The current operational state of this ENDPOINT."
        ::= { rcIsidEndptEntry 16 }

rcIsidEndptPriOverride OBJECT-TYPE
        SYNTAX          TruthValue
        MAX-ACCESS      read-create
        STATUS          current
        DESCRIPTION     "Enable or disable to override the Priority Mapping."
        DEFVAL          { false }
        ::= { rcIsidEndptEntry 17 }

rcIsidEndptBpduTraffic OBJECT-TYPE
        SYNTAX          INTEGER {
                        normal(1),
                        expedite(2),
                        drop(3)
                        }
        MAX-ACCESS      read-create
        STATUS          current
        DESCRIPTION     "Bpdu traffic control."
        DEFVAL          { normal }
        ::= { rcIsidEndptEntry 18 }

rcIsidEndptRowStatus  OBJECT-TYPE
        SYNTAX        RowStatus
        MAX-ACCESS    read-create
        STATUS        current
        DESCRIPTION   "Uses for controlling the creation and
                       deletion of this row."
        ::= { rcIsidEndptEntry 19 }

rcIsidEndptClearStats OBJECT-TYPE
        SYNTAX        TruthValue
        MAX-ACCESS    read-create
        STATUS        current
        DESCRIPTION   "Clear Endpoint statistics."
        DEFVAL        { false }
        ::= { rcIsidEndptEntry 20 } 

rcIsidEndptServiceType OBJECT-TYPE
        SYNTAX         INTEGER {
                          transparent (1),
                          switched(2),
                          qnq1(3),
                          qnq2(4)
                         } 
        MAX-ACCESS     read-create 
        STATUS         current
        DESCRIPTION    "service type of the end-point. It is also
                        releated with."
        DEFVAL         { switched }
        ::= { rcIsidEndptEntry 21 }

rcIsidEndptMuxMode  OBJECT-TYPE 
        SYNTAX      INTEGER {
                       oneToone(1),       -- Only one qtag as member
                       manyToOne(2)       -- Many qtags as member
                      }
        MAX-ACCESS    read-create
        STATUS        obsolete
        DESCRIPTION   "An endpoint can have many qtags mapped to it
                       only if the MuxMode is set to manyToOne. For
                       a manyToOne i-sid there will not be any
                       remapping of qtags at the local egress."
        DEFVAL        { oneToone }
        ::= { rcIsidEndptEntry 22 }

rcIsidEndptMltId  OBJECT-TYPE
        SYNTAX      Integer32 (0..256)
        MAX-ACCESS    read-create
        STATUS        current
        DESCRIPTION   "MLT Id of the ISID"
        DEFVAL        { 0 }
        ::= { rcIsidEndptEntry 23 }

rcIsidEndptTrunkGroup OBJECT-TYPE
        SYNTAX        DisplayString (SIZE (0..32)) 
        MAX-ACCESS    read-create
        STATUS        current
        DESCRIPTION   "trunk group name"
        ::= { rcIsidEndptEntry 24 }


rcIsidEndptMepList OBJECT-TYPE
        SYNTAX        OCTET STRING (SIZE(0..408))
        MAX-ACCESS    read-create
        STATUS        current
        DESCRIPTION   "List of Meps assigned to this entry. 
		       A mep is consist of <md>.<ma>.<mep_id>. Domain
		       Name, Association and Mep Id is separated by '.' 
		       A list of mep is consist of 
		       <md1>.<ma1>.<mepid1>,<md2>.<ma2>.<mepid2>,... 
		       Each mep is separated by ','. Maximum up 8 meps"
        ::= { rcIsidEndptEntry 25 }

rcIsidEndptNumOfMep OBJECT-TYPE
        SYNTAX        	Integer32
        MAX-ACCESS      read-only
        STATUS        	current
        DESCRIPTION   	"Used to indicate the number of Meps
                      	is assigned to this entry"
        ::= { rcIsidEndptEntry 26 }

rcIsidEndptClientMepList OBJECT-TYPE
        SYNTAX        OCTET STRING (SIZE(0..408))
        MAX-ACCESS    read-create
        STATUS        deprecated
        DESCRIPTION   "List of Client Meps assigned to this entry. 
		       A client mep is consist of <md>.<ma>.<mep_id>. Domain
		       Name, Association and Mep Id is separated by '.' 
		       A list of client meps is consist of 
		       <md1>.<ma1>.<mepid1>,<md2>.<ma2>.<mepid2>,... 
		       Each mep is separated by ','. Maximum up 8 meps"
        ::= { rcIsidEndptEntry 27 }

rcIsidEndptNumOfClientMep OBJECT-TYPE
        SYNTAX        	Integer32
        MAX-ACCESS      read-only
        STATUS        	deprecated
        DESCRIPTION   	"Used to indicate the number of Client Meps
                      	is assigned to this entry"
        ::= { rcIsidEndptEntry 28 }

rcIsidEndptRingId	OBJECT-TYPE
        SYNTAX      	Integer32 (0..254)
        MAX-ACCESS    	read-create
        STATUS        	current
        DESCRIPTION   	"Ring Id where the end-point is a member."
        ::= { rcIsidEndptEntry 29 }		    

rcIsidEndptModId	OBJECT-TYPE
        SYNTAX      	Integer32 (0..30)
        MAX-ACCESS    	read-create
        STATUS        	current
        DESCRIPTION   	"RBS Module ID where the end-point is a member."
        ::= { rcIsidEndptEntry 30 }

rcIsidEndptEsuPort	OBJECT-TYPE
        SYNTAX    	Integer32 (0..28)
        MAX-ACCESS    	read-create
        STATUS        	current
        DESCRIPTION   	"RBS port number where the end-point is a member."
        ::= { rcIsidEndptEntry 31 }		  

rcIsidEndptPolicingOption OBJECT-TYPE
	SYNTAX	INTEGER { 
		  preEncap(1), 
		  postEncap(2)
		}
	MAX-ACCESS	read-create
	STATUS		current
	DESCRIPTION	"Specify whether the policing is 
			 pre-encapsulation or post-encapsulation for 
			 Isid Endpoints."
	::= { rcIsidEndptEntry 32 }


rcIsidEndptPriOverrideType OBJECT-TYPE
        SYNTAX        INTEGER
                      {
                         tos(1),
                         dscp(2),
			 mplsexp(3)
                      }
        MAX-ACCESS    read-create
        STATUS        current
        DESCRIPTION   "This field indicated whether ToS or DSCP should be
                       used to override P bit when override is enabled."
        DEFVAL        { tos }
        ::= { rcIsidEndptEntry 33 }

rcIsidEndptColorBasedRemarking OBJECT-TYPE
        SYNTAX        EnableValue
        MAX-ACCESS    read-create
        STATUS        current
        DESCRIPTION   "disable/enable color-based egress mapping for this
                      end-point."
        DEFVAL        { disable }
        ::= { rcIsidEndptEntry 34 }

rcIsidEndptDropRedColorPackets OBJECT-TYPE
        SYNTAX        TruthValue
        MAX-ACCESS    read-create
        STATUS        current
        DESCRIPTION   "disable/enable dropping of red-colored packets for
                      this end-point if color-based mapping is used."
        DEFVAL        { true }
        ::= { rcIsidEndptEntry 35 }		  


rcIsidEndptUserLabel1  OBJECT-TYPE
 	SYNTAX          OCTET STRING (SIZE(0..89))
        MAX-ACCESS      read-create
        STATUS          current
        DESCRIPTION     "User provided field. Used to give extra management information/data "
        ::= { rcIsidEndptEntry 36 }

rcIsidEndptUserLabel2  OBJECT-TYPE
 	SYNTAX          OCTET STRING (SIZE(0..89))
        MAX-ACCESS      read-create
        STATUS          current
        DESCRIPTION     "User provided additional field. Used to give extra management information/data "
        ::= { rcIsidEndptEntry 37 }

rcIsidEndptIngressMirrorState OBJECT-TYPE
        SYNTAX        EnableValue
        MAX-ACCESS    read-create
        STATUS        current
        DESCRIPTION   "Disable/Enable Ingress Mirroring on this endpoint."
        DEFVAL        { disable }
        ::= { rcIsidEndptEntry 38 }

rcIsidEndptEgressMirrorState OBJECT-TYPE
        SYNTAX        EnableValue
        MAX-ACCESS    read-create
        STATUS        current
        DESCRIPTION   "Disable/Enable Egress Mirroring on this endpoint."
        DEFVAL        { disable }
        ::= { rcIsidEndptEntry 39 }

rcIsidEndptDefaultIsid OBJECT-TYPE
        SYNTAX      	EnableValue
        MAX-ACCESS      read-create
        STATUS          current
        DESCRIPTION     "disable/enable default Isid."
        DEFVAL  { disable }
        ::= { rcIsidEndptEntry 40 }

rcIsidEndptL2ptMacSwapCdp OBJECT-TYPE
        SYNTAX          EnableValue
        MAX-ACCESS      read-create
        STATUS          current
        DESCRIPTION     "disable/enable mac swapping on isid end-point for CDP protocol"
        DEFVAL          { disable }
        ::= { rcIsidEndptEntry 42 }

rcIsidEndptL2ptMacSwapVtp OBJECT-TYPE
        SYNTAX          EnableValue
        MAX-ACCESS      read-create
        STATUS          current
        DESCRIPTION     "disable/enable mac swapping on isid end-point for VTP protocol"
        DEFVAL          { disable }
        ::= { rcIsidEndptEntry 43 }

rcIsidEndptL2ptMacSwapStp OBJECT-TYPE
        SYNTAX          EnableValue
        MAX-ACCESS      read-create
        STATUS          current
        DESCRIPTION     "disable/enable mac swapping on isid end-point for STP protocol"
        DEFVAL          { disable }
        ::= { rcIsidEndptEntry 44 }

rcIsidEndptEndPointId  OBJECT-TYPE
	SYNTAX		Integer32 (0..49)
	MAX-ACCESS	read-create
	STATUS		current
	DESCRIPTION 	"End-point ID where the end-point is a member. The maximum 
			number of endpoints per port on an I-SID is 10 and per MLT 
			per I-SID is 10 on R-Module. On RC-Modules, the maximum 
                        number of port based endpoints supported per port per I-SID                                 is 50 and the of maximum number of MLT Based end-points 
                        supported per MLT per I-SID is 16"
	DEFVAL		{ 0 }
	::= { rcIsidEndptEntry 45 }

rcIsidEndptDirectedMcast       OBJECT-TYPE
        SYNTAX        EnableValue
        MAX-ACCESS    read-create
        STATUS        current
        DESCRIPTION   "Disable/Enable directed multicasting on this endpoint."
        DEFVAL        { disable }
        ::= { rcIsidEndptEntry 46 }

rcIsidEndptDEDecodeScheme   OBJECT-TYPE
        SYNTAX        INTEGER
		      {
			ad8p0d(1),
			ad7p1d(2),
			ad6p2d(3),
			m7p1d(4),
			m6p2d(5),
			m5p3d(6),
			customPcp(7),
			dei(8)
		      }
        MAX-ACCESS    read-create
        STATUS        current
        DESCRIPTION   "This indicated the DE decoding 
		       scheme that should be used"
        DEFVAL        { ad8p0d }
        ::= { rcIsidEndptEntry 47 }

rcIsidEndptPcpDecodeMap   OBJECT-TYPE
        SYNTAX        OCTET STRING (SIZE (8))
        MAX-ACCESS    read-create
        STATUS        current
        DESCRIPTION   "This indicated the Drop Eligibility 
		      bit for each priority. The first byte 
		      represents the drop eligibility for 
		      priority 0. Subsequent bytes represent 
		      the drop eligibility of the remaining 
		      802.1p priorities. Format is a:b:c:d:e:f:g:h, 
		      where 0 <= a, b, c, d, e, f, g, h <=1"
        DEFVAL        { "00:00:00:00:00:00:00:00" }
        ::= { rcIsidEndptEntry 48 }

rcIsidEndptCopyItagPcpDeiToStag OBJECT-TYPE
        SYNTAX          EnableValue
        MAX-ACCESS      read-create
        STATUS          current
        DESCRIPTION     "Disable/Enable copying of I-Tag PCP/DEI bits to S-Tag p-bits and DEI at the egress"
        DEFVAL          { disable }
        ::= { rcIsidEndptEntry 49 }

rcIsidEndptDhcpL2Relay      OBJECT-TYPE
        SYNTAX        EnableValue
        MAX-ACCESS    read-create
        STATUS        current
        DESCRIPTION   "Disable/Enable DhcpL2Relay on this endpoint."
        DEFVAL        { disable }
        ::= { rcIsidEndptEntry 50 }

rcIsidEndptIgmpAclName      OBJECT-TYPE
        SYNTAX        DisplayString (SIZE(0..64))
        MAX-ACCESS    read-create
        STATUS        current
        DESCRIPTION   "Name of the IP prefix-list containing allowed multicast
                       groups for this end-point"
        ::= { rcIsidEndptEntry 51 }

rcIsidEndptIgmpStaticEntriesName     OBJECT-TYPE
        SYNTAX        DisplayString (SIZE(0..64))
        MAX-ACCESS    read-create
        STATUS        current
        DESCRIPTION   "Name of the IP prefix-list containing statically 
                       forwarded multicast groups for this end-point"
        ::= { rcIsidEndptEntry 52 }

rcIsidEndptL2cpProfile OBJECT-TYPE
        SYNTAX          DisplayString (SIZE (0..20))
        MAX-ACCESS      read-create
        STATUS          current
        DESCRIPTION     "l2cp-profile associated with this end-point.
                         By default NULL L2CP profile will be associated."
        DEFVAL          { "NULL_L2CP_PROFILE" }
        ::= { rcIsidEndptEntry 53 }

rcIsidEndptNidMgmtSrcMacState OBJECT-TYPE
         SYNTAX          EnableValue
         MAX-ACCESS      read-create
         STATUS          current
         DESCRIPTION     "Disable/Enable configuration of management 
	                  source C-MAC on I-SID"
         DEFVAL          { disable }
         ::= { rcIsidEndptEntry 54 }
 
rcIsidEndptNidMgmtSrcMac OBJECT-TYPE
         SYNTAX        MacAddress
         MAX-ACCESS    read-create
         STATUS        current
         DESCRIPTION   "The customer source MAC address that has to 
	                go over the management I-SID"
         ::= { rcIsidEndptEntry 55 }
 
rcIsidEndptNidMgmtSrcIpAddress      OBJECT-TYPE
         SYNTAX        IpAddress
         MAX-ACCESS    read-create
         STATUS        current
         DESCRIPTION   "NID IP address that has to go over management I-SID"
         ::= { rcIsidEndptEntry 56 }
 
rcIsidEndptNidMgmtSrcIpMask  OBJECT-TYPE
         SYNTAX        IpAddress
         MAX-ACCESS    read-create
         STATUS        current
         DESCRIPTION   "The NID management IP address mask"
         ::= { rcIsidEndptEntry 57 }

rcIsidEndptCfmIngRateLimitSt OBJECT-TYPE
        SYNTAX          EnableValue
        MAX-ACCESS      read-create
        STATUS          current
        DESCRIPTION     "Disable/enable the end-point Rate Limiter 
                         for CFM frames, in the ingress direction."
        DEFVAL          { disable }
        ::= { rcIsidEndptEntry 58 }

rcIsidEndptCfmIngRateLimit OBJECT-TYPE
        SYNTAX          INTEGER (0 | 20..1000)
        MAX-ACCESS      read-create
        STATUS          current
        DESCRIPTION     "Rate Limit value for CFM ingress rate limiter
                         on this end-point.(in packets per second)"
        DEFVAL          { 20 }
        ::= { rcIsidEndptEntry 59 }

rcIsidEndptCfmEgrRateLimitSt OBJECT-TYPE
        SYNTAX          EnableValue
        MAX-ACCESS      read-create
        STATUS          current
        DESCRIPTION     "Disable/enable the end-point Rate Limiter
                         for CFM frames, in the egress direction."
        DEFVAL          { disable }
        ::= { rcIsidEndptEntry 60 }

rcIsidEndptCfmEgrRateLimit OBJECT-TYPE
        SYNTAX          INTEGER (0 | 20..1000)
        MAX-ACCESS      read-create
        STATUS          current
        DESCRIPTION     "Rate Limit value for CFM egress rate limiter
                         on this end-point.(in packets per second)"
        DEFVAL          { 20 }
        ::= { rcIsidEndptEntry 61 }

rcIsidEndptDHUId OBJECT-TYPE
        SYNTAX          INTEGER (0..254)
        MAX-ACCESS      read-create
        STATUS          current
        DESCRIPTION     "DHU Id where the end-point is a member."
        ::= { rcIsidEndptEntry 62 }

rcIsidEndptDHUOperState OBJECT-TYPE
        SYNTAX        INTEGER {
                          down(1),
                          normal(2),
                          partnerportdown(3),
                          partnernodedown(4)
                      }
        MAX-ACCESS    read-only
        STATUS        current
        DESCRIPTION   "The current operational state of DHU
                       where the end-point is a member."
        ::= { rcIsidEndptEntry 63 }

rcIsidEndptDHUHomeOnMe OBJECT-TYPE
        SYNTAX        TruthValue
        MAX-ACCESS    read-only
        STATUS        current
        DESCRIPTION   "Home direction to the DHU where the end-point is a member."
        DEFVAL        { false }
        ::= { rcIsidEndptEntry 64 }

rcIsidEndptCfmIngRateLmtAction OBJECT-TYPE
        SYNTAX        INTEGER {
                         drop(1),
                         downgrade(2)
                      }
        MAX-ACCESS    read-create
        STATUS        current
        DESCRIPTION   "On ingress, to mark the rate limited packets to yellow using 
                      downgrade option or to drop them using drop option."
        DEFVAL        { drop }
        ::= { rcIsidEndptEntry 65 }

rcIsidEndptCfmEgrRateLmtAction OBJECT-TYPE
        SYNTAX        INTEGER {
                         drop(1),
                         downgrade(2)
                      }
        MAX-ACCESS    read-create
        STATUS        current
        DESCRIPTION   "On egress, to mark the rate limited packets to yellow using 
                      downgrade option or to drop them using drop option."
        DEFVAL        { drop }
        ::= { rcIsidEndptEntry 66 }



-- Isid stats table

rcIsidStatsTable OBJECT-TYPE
        SYNTAX        SEQUENCE OF RcIsidStatsEntry
        MAX-ACCESS    not-accessible
        STATUS        current
        DESCRIPTION   ""
        ::= { rc8021ah 3 }
 
rcIsidStatsEntry OBJECT-TYPE
        SYNTAX        RcIsidStatsEntry
        MAX-ACCESS    not-accessible
        STATUS        current
        DESCRIPTION   "A Isid Statistics table entry."
        INDEX         {  rcIsidStatsId }
        ::= { rcIsidStatsTable 1 }
 
RcIsidStatsEntry ::=
        SEQUENCE {
                rcIsidStatsId                            INTEGER,
                rcIsidStatsName                          DisplayString,
                rcIsidStatsPremRxOctets                  Counter64,     
                rcIsidStatsPremRxDroppedOctets           Counter64,
                rcIsidStatsGoldRxOctets                  Counter64,       
                rcIsidStatsGoldRxDroppedOctets           Counter64,
                rcIsidStatsSilverRxOctets                Counter64,       
                rcIsidStatsSilverRxDroppedOctets         Counter64,
                rcIsidStatsStndRxOctets                  Counter64,       
                rcIsidStatsStndRxDroppedOctets           Counter64,
                rcIsidStatsPremTxOctets                  Counter64,       
                rcIsidStatsGoldTxOctets                  Counter64,       
                rcIsidStatsSilverTxOctets                Counter64,
                rcIsidStatsStndTxOctets                  Counter64,       
                rcIsidStatsPremTxMcastOctets             Counter64,  
                rcIsidStatsGoldTxMcastOctets             Counter64,  
                rcIsidStatsSilverTxMcastOctets           Counter64,
                rcIsidStatsStndTxMcastOctets             Counter64,
                rcIsidStatsPremCongestionDropOctets      Counter64,
                rcIsidStatsGoldCongestionDropOctets      Counter64,
                rcIsidStatsSilverCongestionDropOctets    Counter64,     
                rcIsidStatsStndCongestionDropOctets      Counter64,       
                rcIsidStatsPremCirDroppedOctets          Counter64,
                rcIsidStatsPremPirDroppedOctets          Counter64,
                rcIsidStatsGoldCirDroppedOctets          Counter64,
                rcIsidStatsGoldPirDroppedOctets          Counter64,
                rcIsidStatsSilverCirDroppedOctets        Counter64,
                rcIsidStatsSilverPirDroppedOctets        Counter64,
                rcIsidStatsStndCirDroppedOctets          Counter64,
                rcIsidStatsStndPirDroppedOctets          Counter64,
                rcIsidStatsPremTxDroppedOctets           Counter64,       
                rcIsidStatsGoldTxDroppedOctets           Counter64,       
                rcIsidStatsSilverTxDroppedOctets         Counter64,
                rcIsidStatsStndTxDroppedOctets           Counter64,       
                rcIsidStatsPremTxCongestionDropOctets    Counter64,
                rcIsidStatsGoldTxCongestionDropOctets    Counter64,
                rcIsidStatsSilverTxCongestionDropOctets  Counter64,  
                rcIsidStatsStndTxCongestionDropOctets    Counter64,  
                rcIsidStatsPremTxCirDroppedOctets        Counter64,
                rcIsidStatsPremTxPirDroppedOctets        Counter64,
                rcIsidStatsGoldTxCirDroppedOctets        Counter64,
                rcIsidStatsGoldTxPirDroppedOctets        Counter64,
                rcIsidStatsSilverTxCirDroppedOctets      Counter64,
                rcIsidStatsSilverTxPirDroppedOctets      Counter64,
                rcIsidStatsStndTxCirDroppedOctets        Counter64,
                rcIsidStatsStndTxPirDroppedOctets        Counter64,
                rcIsidStatsRxMcastTotalOctets            Counter64,
                rcIsidStatsTxMcastTotalOctets            Counter64,
                rcIsidStatsPremRxMcastDroppedOctets      Counter64,
                rcIsidStatsGoldRxMcastDroppedOctets      Counter64,
                rcIsidStatsSilverRxMcastDroppedOctets    Counter64,
                rcIsidStatsStndRxMcastDroppedOctets      Counter64,
 rcIsidStatsPremRxFrames                  Counter64,     
                rcIsidStatsPremRxDroppedFrames           Counter64,
                rcIsidStatsGoldRxFrames                  Counter64,
                rcIsidStatsGoldRxDroppedFrames           Counter64,
                rcIsidStatsSilverRxFrames                Counter64,
                rcIsidStatsSilverRxDroppedFrames         Counter64,
                rcIsidStatsStndRxFrames                  Counter64,
                rcIsidStatsStndRxDroppedFrames           Counter64,
                rcIsidStatsPremTxFrames                  Counter64,
                rcIsidStatsGoldTxFrames                  Counter64,
                rcIsidStatsSilverTxFrames                Counter64,
                rcIsidStatsStndTxFrames                  Counter64,
                rcIsidStatsPremTxMcastFrames             Counter64,
                rcIsidStatsGoldTxMcastFrames             Counter64,
                rcIsidStatsSilverTxMcastFrames           Counter64,
                rcIsidStatsStndTxMcastFrames             Counter64,
                rcIsidStatsPremCongestionDropFrames      Counter64,
                rcIsidStatsGoldCongestionDropFrames      Counter64,
                rcIsidStatsSilverCongestionDropFrames    Counter64,
                rcIsidStatsStndCongestionDropFrames      Counter64,
                rcIsidStatsPremCirDroppedFrames          Counter64,
                rcIsidStatsPremPirDroppedFrames          Counter64,
                rcIsidStatsGoldCirDroppedFrames          Counter64,
                rcIsidStatsGoldPirDroppedFrames          Counter64,
                rcIsidStatsSilverCirDroppedFrames        Counter64,
                rcIsidStatsSilverPirDroppedFrames        Counter64,
                rcIsidStatsStndCirDroppedFrames          Counter64,
                rcIsidStatsStndPirDroppedFrames          Counter64,
                rcIsidStatsPremTxDroppedFrames           Counter64,
                rcIsidStatsGoldTxDroppedFrames           Counter64,
                rcIsidStatsSilverTxDroppedFrames         Counter64,
                rcIsidStatsStndTxDroppedFrames           Counter64,
                rcIsidStatsPremTxCongestionDropFrames    Counter64,
                rcIsidStatsGoldTxCongestionDropFrames    Counter64,
                rcIsidStatsSilverTxCongestionDropFrames  Counter64,
                rcIsidStatsStndTxCongestionDropFrames    Counter64,
                rcIsidStatsPremTxCirDroppedFrames        Counter64,
                rcIsidStatsPremTxPirDroppedFrames        Counter64,
                rcIsidStatsGoldTxCirDroppedFrames        Counter64,
                rcIsidStatsGoldTxPirDroppedFrames        Counter64,
                rcIsidStatsSilverTxCirDroppedFrames      Counter64,
                rcIsidStatsSilverTxPirDroppedFrames      Counter64,
                rcIsidStatsStndTxCirDroppedFrames        Counter64,
                rcIsidStatsStndTxPirDroppedFrames        Counter64,
                rcIsidStatsRxMcastTotalFrames            Counter64,
                rcIsidStatsTxMcastTotalFrames            Counter64,
                rcIsidStatsPremRxMcastDroppedFrames      Counter64,
                rcIsidStatsGoldRxMcastDroppedFrames      Counter64,
                rcIsidStatsSilverRxMcastDroppedFrames    Counter64,
                rcIsidStatsStndRxMcastDroppedFrames      Counter64,
		rcIsidStatsPremRxCirOctets			Counter64,   
		rcIsidStatsPremRxCirOopOctets		Counter64,
		rcIsidStatsPremRxEirOctets			Counter64,
		rcIsidStatsPremRxEirOopOctets		Counter64,
		rcIsidStatsPremRxEirDroppedOctets		Counter64,
		rcIsidStatsPremRxPirOctets			Counter64,
		rcIsidStatsPremRxPirOopOctets		Counter64,
		rcIsidStatsPremRxGreenOctets			Counter64,
		rcIsidStatsPremRxYellowOctets		Counter64,
		rcIsidStatsPremRxRedOctets			Counter64,
		rcIsidStatsGoldRxCirOctets			Counter64,
		rcIsidStatsGoldRxCirOopOctets		Counter64,
		rcIsidStatsGoldRxEirOctets			Counter64,
		rcIsidStatsGoldRxEirOopOctets		Counter64,
		rcIsidStatsGoldRxEirDroppedOctets		Counter64,
		rcIsidStatsGoldRxPirOctets			Counter64,
		rcIsidStatsGoldRxPirOopOctets		Counter64,
		rcIsidStatsGoldRxGreenOctets			Counter64,
		rcIsidStatsGoldRxYellowOctets			Counter64,
		rcIsidStatsGoldRxRedOctets			Counter64,
		rcIsidStatsSilverRxCirOctets			Counter64,
		rcIsidStatsSilverRxCirOopOctets		Counter64,
		rcIsidStatsSilverRxEirOctets			Counter64,
		rcIsidStatsSilverRxEirOopOctets		Counter64,
		rcIsidStatsSilverRxEirDroppedOctets		Counter64,
		rcIsidStatsSilverRxPirOctets			Counter64,
		rcIsidStatsSilverRxPirOopOctets		Counter64,
		rcIsidStatsSilverRxGreenOctets		Counter64,
		rcIsidStatsSilverRxYellowOctets		Counter64,
		rcIsidStatsSilverRxRedOctets			Counter64,
		rcIsidStatsStndRxCirOctets			Counter64,
		rcIsidStatsStndRxCirOopOctets		Counter64,
		rcIsidStatsStndRxEirOctets			Counter64,
		rcIsidStatsStndRxEirOopOctets		Counter64,
		rcIsidStatsStndRxEirDroppedOctets		Counter64,
		rcIsidStatsStndRxPirOctets			Counter64,
		rcIsidStatsStndRxPirOopOctets		Counter64,
		rcIsidStatsStndRxGreenOctets			Counter64,
		rcIsidStatsStndRxYellowOctets			Counter64,
		rcIsidStatsStndRxRedOctets			Counter64,
		rcIsidStatsMcastRxDroppedOctets		Counter64,
		rcIsidStatsBcastUUcastRxTotalOctets		Counter64,
		rcIsidStatsBcastUUcastRxDroppedOctets		Counter64,
		rcIsidStatsPremRxCirFrames			Counter64,
		rcIsidStatsPremRxCirOopFrames		Counter64,
		rcIsidStatsPremRxEirFrames			Counter64,
		rcIsidStatsPremRxEirOopFrames		Counter64,
		rcIsidStatsPremRxEirDroppedFrames		Counter64,
		rcIsidStatsPremRxPirFrames			Counter64,
		rcIsidStatsPremRxPirOopFrames		Counter64,
		rcIsidStatsPremRxGreenFrames		Counter64,
		rcIsidStatsPremRxYellowFrames		Counter64,
		rcIsidStatsPremRxRedFrames			Counter64,
		rcIsidStatsGoldRxCirFrames			Counter64,
		rcIsidStatsGoldRxCirOopFrames		Counter64,
		rcIsidStatsGoldRxEirFrames			Counter64,
		rcIsidStatsGoldRxEirOopFrames		Counter64,
		rcIsidStatsGoldRxEirDroppedFrames		Counter64,
		rcIsidStatsGoldRxPirFrames			Counter64,
		rcIsidStatsGoldRxPirOopFrames		Counter64,
		rcIsidStatsGoldRxGreenFrames		Counter64,
		rcIsidStatsGoldRxYellowFrames		Counter64,
		rcIsidStatsGoldRxRedFrames			Counter64,
		rcIsidStatsSilverRxCirFrames			Counter64,
		rcIsidStatsSilverRxCirOopFrames		Counter64,
		rcIsidStatsSilverRxEirFrames			Counter64,
		rcIsidStatsSilverRxEirOopFrames		Counter64,
		rcIsidStatsSilverRxEirDroppedFrames		Counter64,
		rcIsidStatsSilverRxPirFrames			Counter64,
		rcIsidStatsSilverRxPirOopFrames		Counter64,
		rcIsidStatsSilverRxGreenFrames		Counter64,
		rcIsidStatsSilverRxYellowFrames		Counter64,
		rcIsidStatsSilverRxRedFrames			Counter64,
		rcIsidStatsStndRxCirFrames			Counter64,
		rcIsidStatsStndRxCirOopFrames		Counter64,
		rcIsidStatsStndRxEirFrames			Counter64,
		rcIsidStatsStndRxEirOopFrames		Counter64,
		rcIsidStatsStndRxEirDroppedFrames		Counter64,
		rcIsidStatsStndRxPirFrames			Counter64,
		rcIsidStatsStndRxPirOopFrames		Counter64,
		rcIsidStatsStndRxGreenFrames		Counter64,
		rcIsidStatsStndRxYellowFrames		Counter64,
		rcIsidStatsStndRxRedFrames			Counter64,
		rcIsidStatsMcastRxDroppedFrames		Counter64,
		rcIsidStatsBcastUUcastRxTotalFrames		Counter64,
		rcIsidStatsBcastUUcastRxDroppedFrames	Counter64,
		rcIsidStatsPremTxCirOctets			Counter64,
		rcIsidStatsPremTxCirOopOctets		Counter64,
		rcIsidStatsPremTxEirOctets			Counter64,
		rcIsidStatsPremTxEirOopOctets		Counter64,
		rcIsidStatsPremTxEirDroppedOctets		Counter64,
		rcIsidStatsPremTxPirOctets			Counter64,
		rcIsidStatsPremTxPirOopOctets		Counter64,
		rcIsidStatsPremTxGreenOctets			Counter64,
		rcIsidStatsPremTxYellowOctets			Counter64,
		rcIsidStatsPremTxRedOctets			Counter64,
		rcIsidStatsGoldTxCirOctets			Counter64,
		rcIsidStatsGoldTxCirOopOctets			Counter64,
		rcIsidStatsGoldTxEirOctets			Counter64,
		rcIsidStatsGoldTxEirOopOctets			Counter64,
		rcIsidStatsGoldTxEirDroppedOctets		Counter64,
		rcIsidStatsGoldTxPirOctets			Counter64,
		rcIsidStatsGoldTxPirOopOctets			Counter64,
		rcIsidStatsGoldTxGreenOctets			Counter64,
		rcIsidStatsGoldTxYellowOctets			Counter64,
		rcIsidStatsGoldTxRedOctets			Counter64,
		rcIsidStatsSilverTxCirOctets			Counter64,
		rcIsidStatsSilverTxCirOopOctets		Counter64,
		rcIsidStatsSilverTxEirOctets			Counter64,
		rcIsidStatsSilverTxEirOopOctets		Counter64,
		rcIsidStatsSilverTxEirDroppedOctets		Counter64,
		rcIsidStatsSilverTxPirOctets			Counter64,
		rcIsidStatsSilverTxPirOopOctets		Counter64,
		rcIsidStatsSilverTxGreenOctets			Counter64,
		rcIsidStatsSilverTxYellowOctets		Counter64,
		rcIsidStatsSilverTxRedOctets			Counter64,
		rcIsidStatsStndTxCirOctets			Counter64,
		rcIsidStatsStndTxCirOopOctets			Counter64,
		rcIsidStatsStndTxEirOctets			Counter64,
		rcIsidStatsStndTxEirOopOctets			Counter64,
		rcIsidStatsStndTxEirDroppedOctets		Counter64,
		rcIsidStatsStndTxPirOctets			Counter64,
		rcIsidStatsStndTxPirOopOctets			Counter64,
		rcIsidStatsStndTxGreenOctets			Counter64,
		rcIsidStatsStndTxYellowOctets			Counter64,
		rcIsidStatsStndTxRedOctets			Counter64,
		rcIsidStatsMcastTxDroppedOctets		Counter64,
		rcIsidStatsBcastUUcastTxTotalOctets		Counter64,
		rcIsidStatsBcastUUcastTxDroppedOctets		Counter64,
		rcIsidStatsPremTxCirFrames			Counter64,
		rcIsidStatsPremTxCirOopFrames		Counter64,
		rcIsidStatsPremTxEirFrames			Counter64,
		rcIsidStatsPremTxEirOopFrames		Counter64,
		rcIsidStatsPremTxEirDroppedFrames		Counter64,
		rcIsidStatsPremTxPirFrames			Counter64,
		rcIsidStatsPremTxPirOopFrames		Counter64,
		rcIsidStatsPremTxGreenFrames		Counter64,
		rcIsidStatsPremTxYellowFrames		Counter64,
		rcIsidStatsPremTxRedFrames			Counter64,
		rcIsidStatsGoldTxCirFrames			Counter64,
		rcIsidStatsGoldTxCirOopFrames		Counter64,
		rcIsidStatsGoldTxEirFrames			Counter64,
		rcIsidStatsGoldTxEirOopFrames		Counter64,
		rcIsidStatsGoldTxEirDroppedFrames		Counter64,
		rcIsidStatsGoldTxPirFrames			Counter64,
		rcIsidStatsGoldTxPirOopFrames		Counter64,
		rcIsidStatsGoldTxGreenFrames			Counter64,
		rcIsidStatsGoldTxYellowFrames		Counter64,
		rcIsidStatsGoldTxRedFrames			Counter64,
		rcIsidStatsSilverTxCirFrames			Counter64,
		rcIsidStatsSilverTxCirOopFrames		Counter64,
		rcIsidStatsSilverTxEirFrames			Counter64,
		rcIsidStatsSilverTxEirOopFrames		Counter64,
		rcIsidStatsSilverTxEirDroppedFrames		Counter64,
		rcIsidStatsSilverTxPirFrames			Counter64,
		rcIsidStatsSilverTxPirOopFrames		Counter64,
		rcIsidStatsSilverTxGreenFrames		Counter64,
		rcIsidStatsSilverTxYellowFrames		Counter64,
		rcIsidStatsSilverTxRedFrames			Counter64,
		rcIsidStatsStndTxCirFrames			Counter64,
		rcIsidStatsStndTxCirOopFrames		Counter64,
		rcIsidStatsStndTxEirFrames			Counter64,
		rcIsidStatsStndTxEirOopFrames		Counter64,
		rcIsidStatsStndTxEirDroppedFrames		Counter64,
		rcIsidStatsStndTxPirFrames			Counter64,
		rcIsidStatsStndTxPirOopFrames		Counter64,
		rcIsidStatsStndTxGreenFrames			Counter64,
		rcIsidStatsStndTxYellowFrames		Counter64,
		rcIsidStatsStndTxRedFrames			Counter64,
		rcIsidStatsMcastTxDroppedFrames		Counter64,
		rcIsidStatsBcastUUcastTxTotalFrames		Counter64,
		rcIsidStatsBcastUUcastTxDroppedFrames	Counter64,
		rcIsidStatsDropClassRxDroppedOctets  		Counter64,
		rcIsidStatsDropClassRxDroppedFrames  		Counter64,
		rcIsidStatsDropClassTxDroppedOctets  		Counter64,
		rcIsidStatsDropClassTxDroppedFrames  		Counter64        
        }  

rcIsidStatsId OBJECT-TYPE
        SYNTAX        INTEGER (1..16777215)
        MAX-ACCESS    not-accessible
        STATUS        current
        DESCRIPTION   "ISID Identifier."
        ::= { rcIsidStatsEntry 1 }
 
rcIsidStatsName OBJECT-TYPE
        SYNTAX        DisplayString (SIZE (0..25)) 
        MAX-ACCESS    read-only
        STATUS        current
        DESCRIPTION   "Name of ISID."
        ::= { rcIsidStatsEntry 2 }
 
rcIsidStatsPremRxOctets      OBJECT-TYPE
        SYNTAX        Counter64
        MAX-ACCESS    read-only
        STATUS        current
        DESCRIPTION  "Number of Premium Service Octets received."
        ::= { rcIsidStatsEntry 3 } 

rcIsidStatsPremRxDroppedOctets       OBJECT-TYPE
        SYNTAX        Counter64
        MAX-ACCESS    read-only
        STATUS        current
        DESCRIPTION  "Number of Premium Service Octets dropped."
        ::= { rcIsidStatsEntry 4 } 
       
rcIsidStatsGoldRxOctets      OBJECT-TYPE
        SYNTAX        Counter64
        MAX-ACCESS    read-only
        STATUS        current
        DESCRIPTION  "Number of Gold Service Octets received."
        ::= { rcIsidStatsEntry 5 } 

rcIsidStatsGoldRxDroppedOctets       OBJECT-TYPE
        SYNTAX        Counter64
        MAX-ACCESS    read-only
        STATUS        current
        DESCRIPTION  "Number of Gold Service Octets dropped."
        ::= { rcIsidStatsEntry 6 } 
       

rcIsidStatsSilverRxOctets    OBJECT-TYPE
        SYNTAX        Counter64
        MAX-ACCESS    read-only
        STATUS        current
        DESCRIPTION  "Number of Silver Service Octets received."
        ::= { rcIsidStatsEntry 7 } 

rcIsidStatsSilverRxDroppedOctets     OBJECT-TYPE
        SYNTAX        Counter64
        MAX-ACCESS    read-only
        STATUS        current
        DESCRIPTION  "Number of Silver Service Octets dropped."
        ::= {rcIsidStatsEntry 8 } 
       
rcIsidStatsStndRxOctets      OBJECT-TYPE
        SYNTAX        Counter64
        MAX-ACCESS    read-only
        STATUS        current
        DESCRIPTION  "Number of Standard Service Octets received."
        ::= {rcIsidStatsEntry 9 } 

rcIsidStatsStndRxDroppedOctets       OBJECT-TYPE
        SYNTAX        Counter64
        MAX-ACCESS    read-only
        STATUS        current
        DESCRIPTION  "Number of Standard Service Octets dropped."
        ::= {rcIsidStatsEntry 10 } 
       
rcIsidStatsPremTxOctets      OBJECT-TYPE
        SYNTAX        Counter64
        MAX-ACCESS    read-only
        STATUS        current
        DESCRIPTION  "Number of Premium Service Octets sent."
        ::= {rcIsidStatsEntry 11 } 

rcIsidStatsGoldTxOctets      OBJECT-TYPE
        SYNTAX        Counter64
        MAX-ACCESS    read-only
        STATUS        current
        DESCRIPTION  "Number of Gold Service Octets sent."
        ::= {rcIsidStatsEntry 12 } 

rcIsidStatsSilverTxOctets    OBJECT-TYPE
        SYNTAX        Counter64
        MAX-ACCESS    read-only
        STATUS        current
        DESCRIPTION  "Number of Silver Service Octets sent."
        ::= {rcIsidStatsEntry 13 } 

rcIsidStatsStndTxOctets      OBJECT-TYPE
        SYNTAX        Counter64
        MAX-ACCESS    read-only
        STATUS        current
        DESCRIPTION  "Number of Standard Service Octets sent."
        ::= {rcIsidStatsEntry 14 } 
                

rcIsidStatsPremTxMcastOctets OBJECT-TYPE
        SYNTAX        Counter64
        MAX-ACCESS    read-only
        STATUS        current
        DESCRIPTION  "Number of Premium Service Multicast sent."
        ::= {rcIsidStatsEntry 15 } 

rcIsidStatsGoldTxMcastOctets OBJECT-TYPE
        SYNTAX        Counter64
        MAX-ACCESS    read-only
        STATUS        current
        DESCRIPTION  "Number of GoldService Multicast sent."
        ::= {rcIsidStatsEntry 16 } 
                

rcIsidStatsSilverTxMcastOctets       OBJECT-TYPE
        SYNTAX        Counter64
        MAX-ACCESS    read-only
        STATUS        current
        DESCRIPTION  "Number of SilverService Multicast sent."
        ::= {rcIsidStatsEntry 17 } 

rcIsidStatsStndTxMcastOctets OBJECT-TYPE
        SYNTAX        Counter64
        MAX-ACCESS    read-only
        STATUS        current
        DESCRIPTION  "Number of Premium Service Multicast sent."
        ::= {rcIsidStatsEntry 18 } 

rcIsidStatsPremCongestionDropOctets  OBJECT-TYPE
        SYNTAX        Counter64
        MAX-ACCESS    read-only
        STATUS        current
        DESCRIPTION  "Number of Prem Service Octets congestion drop"
        ::= {rcIsidStatsEntry 19 } 
       
rcIsidStatsGoldCongestionDropOctets  OBJECT-TYPE
        SYNTAX        Counter64
        MAX-ACCESS    read-only
        STATUS        current
        DESCRIPTION  "Number of Gold Service Octets congestion drop"
        ::= {rcIsidStatsEntry 20 } 

rcIsidStatsSilverCongestionDropOctets        OBJECT-TYPE
        SYNTAX        Counter64
        MAX-ACCESS    read-only
        STATUS        current
        DESCRIPTION  "Number of Silver Service Octets congestion drop"
        ::= {rcIsidStatsEntry 21 } 

rcIsidStatsStndCongestionDropOctets  OBJECT-TYPE
        SYNTAX        Counter64
        MAX-ACCESS    read-only
        STATUS        current
        DESCRIPTION  "Number of Standard Service Octets congestion drop"
        ::= {rcIsidStatsEntry 22 }

rcIsidStatsPremCirDroppedOctets      OBJECT-TYPE
        SYNTAX        Counter64
        MAX-ACCESS    read-only
        STATUS        current
        DESCRIPTION  "Number of Prem Service Octets CIR drop"
        ::= {rcIsidStatsEntry 23 }

rcIsidStatsPremPirDroppedOctets      OBJECT-TYPE
        SYNTAX        Counter64
        MAX-ACCESS    read-only
        STATUS        current
        DESCRIPTION  "Number of Prem Service Octets PIR drop"
        ::= {rcIsidStatsEntry 24 }
  
rcIsidStatsGoldCirDroppedOctets      OBJECT-TYPE
        SYNTAX        Counter64
        MAX-ACCESS    read-only
        STATUS        current
        DESCRIPTION  "Number of Gold Service Octets CIR drop"
        ::= {rcIsidStatsEntry 25 }

rcIsidStatsGoldPirDroppedOctets      OBJECT-TYPE
        SYNTAX        Counter64
        MAX-ACCESS    read-only
        STATUS        current
        DESCRIPTION  "Number of Gold Service Octets PIR drop"
        ::= {rcIsidStatsEntry 26 }

rcIsidStatsSilverCirDroppedOctets    OBJECT-TYPE
        SYNTAX        Counter64
        MAX-ACCESS    read-only
        STATUS        current
        DESCRIPTION  "Number of Silver Service Octets CIR drop"
        ::= {rcIsidStatsEntry 27 }

rcIsidStatsSilverPirDroppedOctets    OBJECT-TYPE
        SYNTAX        Counter64
        MAX-ACCESS    read-only
        STATUS        current
        DESCRIPTION  "Number of Silver Service Octets PIR drop"
        ::= {rcIsidStatsEntry 28 }

rcIsidStatsStndCirDroppedOctets      OBJECT-TYPE
        SYNTAX        Counter64
        MAX-ACCESS    read-only
        STATUS        current
        DESCRIPTION  "Number of Standard Service Octets CIR drop"
        ::= {rcIsidStatsEntry 29 }  

rcIsidStatsStndPirDroppedOctets      OBJECT-TYPE
        SYNTAX        Counter64
        MAX-ACCESS    read-only
        STATUS        current
        DESCRIPTION  "Number of Standard Service Octets PIR drop"
        ::= {rcIsidStatsEntry 30 }  

rcIsidStatsPremTxDroppedOctets       OBJECT-TYPE
        SYNTAX        Counter64
        MAX-ACCESS    read-only
        STATUS        current
        DESCRIPTION  "Tx Number of Premium Service Octets dropped."
        ::= {rcIsidStatsEntry 31 } 
       
rcIsidStatsGoldTxDroppedOctets       OBJECT-TYPE
        SYNTAX        Counter64
        MAX-ACCESS    read-only
        STATUS        current
        DESCRIPTION  "Tx Number of Gold Service Octets dropped."
        ::= {rcIsidStatsEntry 32 } 
       
rcIsidStatsSilverTxDroppedOctets     OBJECT-TYPE
        SYNTAX        Counter64
        MAX-ACCESS    read-only
        STATUS        current
        DESCRIPTION  "Tx Number of Silver Service Octets dropped."
        ::= {rcIsidStatsEntry 33 } 
       
rcIsidStatsStndTxDroppedOctets       OBJECT-TYPE
        SYNTAX        Counter64
        MAX-ACCESS    read-only
        STATUS        current
        DESCRIPTION  "Tx Number of Standard Service Octets dropped."
        ::= {rcIsidStatsEntry 34 } 

rcIsidStatsPremTxCongestionDropOctets        OBJECT-TYPE
        SYNTAX        Counter64
        MAX-ACCESS    read-only
        STATUS        current
        DESCRIPTION  "Number of Prem Service Octets congestion dropped."
        ::= {rcIsidStatsEntry 35 } 
       
rcIsidStatsGoldTxCongestionDropOctets        OBJECT-TYPE
        SYNTAX        Counter64
        MAX-ACCESS    read-only
        STATUS        current
        DESCRIPTION  "Number of Gold Service Octets congestion dropped."
        ::= {rcIsidStatsEntry 36 } 

rcIsidStatsSilverTxCongestionDropOctets      OBJECT-TYPE
        SYNTAX        Counter64
        MAX-ACCESS    read-only
        STATUS        current
        DESCRIPTION  "Number of Silver Service Octets congestion dropped."
        ::= {rcIsidStatsEntry 37 } 

rcIsidStatsStndTxCongestionDropOctets        OBJECT-TYPE
        SYNTAX        Counter64
        MAX-ACCESS    read-only
        STATUS        current
        DESCRIPTION  "Number of Standard Service Octets congestion dropped."
        ::= {rcIsidStatsEntry 38 }

rcIsidStatsPremTxCirDroppedOctets    OBJECT-TYPE
        SYNTAX        Counter64
        MAX-ACCESS    read-only
        STATUS        current
        DESCRIPTION  "Number of Prem Service Octets CIR dropped."
        ::= {rcIsidStatsEntry 39 }

rcIsidStatsPremTxPirDroppedOctets    OBJECT-TYPE
        SYNTAX        Counter64
        MAX-ACCESS    read-only
        STATUS        current
        DESCRIPTION  "Number of Prem Service Octets PIR dropped."
        ::= {rcIsidStatsEntry 40 }
  
rcIsidStatsGoldTxCirDroppedOctets    OBJECT-TYPE
        SYNTAX        Counter64
        MAX-ACCESS    read-only
        STATUS        current
        DESCRIPTION  "Number of Gold Service Octets CIR dropped."
        ::= {rcIsidStatsEntry 41 }

rcIsidStatsGoldTxPirDroppedOctets    OBJECT-TYPE
        SYNTAX        Counter64
        MAX-ACCESS    read-only
        STATUS        current
        DESCRIPTION  "Number of Gold Service Octets PIR dropped."
        ::= {rcIsidStatsEntry 42 }

rcIsidStatsSilverTxCirDroppedOctets  OBJECT-TYPE
        SYNTAX        Counter64
        MAX-ACCESS    read-only
        STATUS        current
        DESCRIPTION  "Number of Silver Service Octets CIR dropped."
        ::= {rcIsidStatsEntry 43 }

rcIsidStatsSilverTxPirDroppedOctets  OBJECT-TYPE
        SYNTAX        Counter64
        MAX-ACCESS    read-only
        STATUS        current
        DESCRIPTION  "Number of Silver Service Octets PIR dropped."
        ::= {rcIsidStatsEntry 44 }

rcIsidStatsStndTxCirDroppedOctets    OBJECT-TYPE
        SYNTAX        Counter64
        MAX-ACCESS    read-only
        STATUS        current
        DESCRIPTION  "Number of Standard Service Octets CIR dropped."
        ::= {rcIsidStatsEntry 45 }  

rcIsidStatsStndTxPirDroppedOctets    OBJECT-TYPE
        SYNTAX        Counter64
        MAX-ACCESS    read-only
        STATUS        current
        DESCRIPTION  "Number of Standard Service Octets PIR dropped."
        ::= {rcIsidStatsEntry 46 }  

rcIsidStatsRxMcastTotalOctets   OBJECT-TYPE
        SYNTAX        Counter64
        MAX-ACCESS    read-only
        STATUS        current
        DESCRIPTION  "Rx total Number of Mcast Octet"
        ::= {rcIsidStatsEntry 47 }
  
rcIsidStatsTxMcastTotalOctets  OBJECT-TYPE
        SYNTAX        Counter64
        MAX-ACCESS    read-only
        STATUS        current
        DESCRIPTION  "Tx total Number of Mcast Octet"
        ::= {rcIsidStatsEntry 48 }

rcIsidStatsPremRxMcastDroppedOctets  OBJECT-TYPE
        SYNTAX        Counter64
        MAX-ACCESS    read-only
        STATUS        current
        DESCRIPTION  "Number of Premium Service Rx Mcast Octets dropped."
        ::= {rcIsidStatsEntry 49 } 

rcIsidStatsGoldRxMcastDroppedOctets  OBJECT-TYPE
        SYNTAX        Counter64
        MAX-ACCESS    read-only
        STATUS        current
        DESCRIPTION  "Number of Gold Service Rx Mcast Octets dropped."
        ::= {rcIsidStatsEntry 50 } 

rcIsidStatsSilverRxMcastDroppedOctets        OBJECT-TYPE
        SYNTAX        Counter64
        MAX-ACCESS    read-only
        STATUS        current
        DESCRIPTION  "Number of Silver Service Rx Mcast Octets dropped."
        ::= {rcIsidStatsEntry 51 } 
                            
rcIsidStatsStndRxMcastDroppedOctets  OBJECT-TYPE
        SYNTAX        Counter64
        MAX-ACCESS    read-only
        STATUS        current
        DESCRIPTION  "Number of Standard Service Rx Mcast Octets dropped."
        ::= {rcIsidStatsEntry 52 } 
rcIsidStatsPremRxFrames      OBJECT-TYPE
        SYNTAX        Counter64
        MAX-ACCESS    read-only
        STATUS        current
        DESCRIPTION  "Number of Premium Service Frames received."
        ::= { rcIsidStatsEntry 53 }

rcIsidStatsPremRxDroppedFrames       OBJECT-TYPE
        SYNTAX        Counter64
        MAX-ACCESS    read-only
        STATUS        current
        DESCRIPTION  "Number of Premium Service Frames dropped."
        ::= { rcIsidStatsEntry 54 }

rcIsidStatsGoldRxFrames      OBJECT-TYPE
        SYNTAX        Counter64
        MAX-ACCESS    read-only
        STATUS        current
        DESCRIPTION  "Number of Gold Service Frames received."
        ::= { rcIsidStatsEntry 55 }

rcIsidStatsGoldRxDroppedFrames       OBJECT-TYPE
        SYNTAX        Counter64
        MAX-ACCESS    read-only
        STATUS        current
        DESCRIPTION  "Number of Gold Service Frames dropped."
        ::= { rcIsidStatsEntry 56 }

rcIsidStatsSilverRxFrames    OBJECT-TYPE
        SYNTAX        Counter64
        MAX-ACCESS    read-only
        STATUS        current
        DESCRIPTION  "Number of Silver Service Frames received."
        ::= { rcIsidStatsEntry 57 }

rcIsidStatsSilverRxDroppedFrames     OBJECT-TYPE
        SYNTAX        Counter64
        MAX-ACCESS    read-only
        STATUS        current
        DESCRIPTION  "Number of Silver Service Frames dropped."
        ::= {rcIsidStatsEntry 58 }

rcIsidStatsStndRxFrames      OBJECT-TYPE
        SYNTAX        Counter64
        MAX-ACCESS    read-only
        STATUS        current
        DESCRIPTION  "Number of Standard Service Frames received."
        ::= {rcIsidStatsEntry 59 }

rcIsidStatsStndRxDroppedFrames       OBJECT-TYPE
        SYNTAX        Counter64
        MAX-ACCESS    read-only
        STATUS        current
        DESCRIPTION  "Number of Standard Service Frames dropped."
        ::= {rcIsidStatsEntry 60 }

rcIsidStatsPremTxFrames      OBJECT-TYPE
        SYNTAX        Counter64
        MAX-ACCESS    read-only
        STATUS        current
        DESCRIPTION  "Number of Premium Service Frames sent."
        ::= {rcIsidStatsEntry 61 }

rcIsidStatsGoldTxFrames      OBJECT-TYPE
        SYNTAX        Counter64
        MAX-ACCESS    read-only
        STATUS        current
        DESCRIPTION  "Number of Gold Service Frames sent."
        ::= {rcIsidStatsEntry 62 }

rcIsidStatsSilverTxFrames    OBJECT-TYPE
        SYNTAX        Counter64
        MAX-ACCESS    read-only
        STATUS        current
        DESCRIPTION  "Number of Silver Service Frames sent."
        ::= {rcIsidStatsEntry 63 }

rcIsidStatsStndTxFrames      OBJECT-TYPE
        SYNTAX        Counter64
        MAX-ACCESS    read-only
        STATUS        current
        DESCRIPTION  "Number of Standard Service Frames sent."
        ::= {rcIsidStatsEntry 64 }

rcIsidStatsPremTxMcastFrames OBJECT-TYPE
        SYNTAX        Counter64
        MAX-ACCESS    read-only
        STATUS        current
        DESCRIPTION  "Number of Premium Service Multicast sent."
        ::= {rcIsidStatsEntry 65 }

rcIsidStatsGoldTxMcastFrames OBJECT-TYPE
        SYNTAX        Counter64
        MAX-ACCESS    read-only
        STATUS        current
        DESCRIPTION  "Number of GoldService Multicast sent."
        ::= {rcIsidStatsEntry 66 }

rcIsidStatsSilverTxMcastFrames       OBJECT-TYPE
        SYNTAX        Counter64
        MAX-ACCESS    read-only
        STATUS        current
        DESCRIPTION  "Number of SilverService Multicast sent."
        ::= {rcIsidStatsEntry 67 }

rcIsidStatsStndTxMcastFrames OBJECT-TYPE
        SYNTAX        Counter64
        MAX-ACCESS    read-only
        STATUS        current
        DESCRIPTION  "Number of Premium Service Multicast sent."
        ::= {rcIsidStatsEntry 68 }

rcIsidStatsPremCongestionDropFrames  OBJECT-TYPE
        SYNTAX        Counter64
        MAX-ACCESS    read-only
        STATUS        current
        DESCRIPTION  "Number of Prem Service Frames congestion drop"
        ::= {rcIsidStatsEntry 69 }

rcIsidStatsGoldCongestionDropFrames  OBJECT-TYPE
        SYNTAX        Counter64
        MAX-ACCESS    read-only
        STATUS        current
        DESCRIPTION  "Number of Gold Service Frames congestion drop"
        ::= {rcIsidStatsEntry 70 }

rcIsidStatsSilverCongestionDropFrames        OBJECT-TYPE
        SYNTAX        Counter64
        MAX-ACCESS    read-only
        STATUS        current
        DESCRIPTION  "Number of Silver Service Frames congestion drop"
        ::= {rcIsidStatsEntry 71 }

rcIsidStatsStndCongestionDropFrames  OBJECT-TYPE
        SYNTAX        Counter64
        MAX-ACCESS    read-only
        STATUS        current
        DESCRIPTION  "Number of Standard Service Frames congestion drop"
        ::= {rcIsidStatsEntry 72 }

rcIsidStatsPremCirDroppedFrames      OBJECT-TYPE
        SYNTAX        Counter64
        MAX-ACCESS    read-only
        STATUS        current
        DESCRIPTION  "Number of Prem Service Frames CIR drop"
        ::= {rcIsidStatsEntry 73 }

rcIsidStatsPremPirDroppedFrames      OBJECT-TYPE
        SYNTAX        Counter64
        MAX-ACCESS    read-only
        STATUS        current
        DESCRIPTION  "Number of Prem Service Frames PIR drop"
        ::= {rcIsidStatsEntry 74 }

rcIsidStatsGoldCirDroppedFrames      OBJECT-TYPE
        SYNTAX        Counter64
        MAX-ACCESS    read-only
        STATUS        current
        DESCRIPTION  "Number of Gold Service Frames CIR drop"
        ::= {rcIsidStatsEntry 75 }

rcIsidStatsGoldPirDroppedFrames      OBJECT-TYPE
        SYNTAX        Counter64
        MAX-ACCESS    read-only
        STATUS        current
        DESCRIPTION  "Number of Gold Service Frames PIR drop"
        ::= {rcIsidStatsEntry 76 }

rcIsidStatsSilverCirDroppedFrames    OBJECT-TYPE
        SYNTAX        Counter64
        MAX-ACCESS    read-only
        STATUS        current
        DESCRIPTION  "Number of Silver Service Frames CIR drop"
        ::= {rcIsidStatsEntry 77 }

rcIsidStatsSilverPirDroppedFrames    OBJECT-TYPE
        SYNTAX        Counter64
        MAX-ACCESS    read-only
        STATUS        current
        DESCRIPTION  "Number of Silver Service Frames PIR drop"
        ::= {rcIsidStatsEntry 78 }

rcIsidStatsStndCirDroppedFrames      OBJECT-TYPE
        SYNTAX        Counter64
        MAX-ACCESS    read-only
        STATUS        current
        DESCRIPTION  "Number of Standard Service Frames CIR drop"
        ::= {rcIsidStatsEntry 79 }

rcIsidStatsStndPirDroppedFrames      OBJECT-TYPE
        SYNTAX        Counter64
        MAX-ACCESS    read-only
        STATUS        current
        DESCRIPTION  "Number of Standard Service Frames PIR drop"
        ::= {rcIsidStatsEntry 80 }

rcIsidStatsPremTxDroppedFrames       OBJECT-TYPE
        SYNTAX        Counter64
        MAX-ACCESS    read-only
        STATUS        current
        DESCRIPTION  "Tx Number of Premium Service Frames dropped."
        ::= {rcIsidStatsEntry 81 }

rcIsidStatsGoldTxDroppedFrames       OBJECT-TYPE
        SYNTAX        Counter64
        MAX-ACCESS    read-only
        STATUS        current
        DESCRIPTION  "Tx Number of Gold Service Frames dropped."
        ::= {rcIsidStatsEntry 82 }

rcIsidStatsSilverTxDroppedFrames     OBJECT-TYPE
        SYNTAX        Counter64
        MAX-ACCESS    read-only
        STATUS        current
        DESCRIPTION  "Tx Number of Silver Service Frames dropped."
        ::= {rcIsidStatsEntry 83 }

rcIsidStatsStndTxDroppedFrames       OBJECT-TYPE
        SYNTAX        Counter64
        MAX-ACCESS    read-only
        STATUS        current
        DESCRIPTION  "Tx Number of Standard Service Frames dropped."
        ::= {rcIsidStatsEntry 84 }

rcIsidStatsPremTxCongestionDropFrames        OBJECT-TYPE
        SYNTAX        Counter64
        MAX-ACCESS    read-only
        STATUS        current
        DESCRIPTION  "Number of Prem Service Frames congestion dropped."
        ::= {rcIsidStatsEntry 85 }

rcIsidStatsGoldTxCongestionDropFrames        OBJECT-TYPE
        SYNTAX        Counter64
        MAX-ACCESS    read-only
        STATUS        current
        DESCRIPTION  "Number of Gold Service Frames congestion dropped."
        ::= {rcIsidStatsEntry 86 }

rcIsidStatsSilverTxCongestionDropFrames      OBJECT-TYPE
        SYNTAX        Counter64
        MAX-ACCESS    read-only
        STATUS        current
        DESCRIPTION  "Number of Silver Service Frames congestion dropped."
        ::= {rcIsidStatsEntry 87 }

rcIsidStatsStndTxCongestionDropFrames        OBJECT-TYPE
        SYNTAX        Counter64
        MAX-ACCESS    read-only
        STATUS        current
        DESCRIPTION  "Number of Standard Service Frames congestion dropped."
        ::= {rcIsidStatsEntry 88 }

rcIsidStatsPremTxCirDroppedFrames    OBJECT-TYPE
        SYNTAX        Counter64
        MAX-ACCESS    read-only
        STATUS        current
        DESCRIPTION  "Number of Prem Service Frames CIR dropped."
        ::= {rcIsidStatsEntry 89 }

rcIsidStatsPremTxPirDroppedFrames    OBJECT-TYPE
        SYNTAX        Counter64
        MAX-ACCESS    read-only
        STATUS        current
        DESCRIPTION  "Number of Prem Service Frames PIR dropped."
        ::= {rcIsidStatsEntry 90 }

rcIsidStatsGoldTxCirDroppedFrames    OBJECT-TYPE
        SYNTAX        Counter64
        MAX-ACCESS    read-only
        STATUS        current
        DESCRIPTION  "Number of Gold Service Frames CIR dropped."
        ::= {rcIsidStatsEntry 91 }

rcIsidStatsGoldTxPirDroppedFrames    OBJECT-TYPE
        SYNTAX        Counter64
        MAX-ACCESS    read-only
        STATUS        current
        DESCRIPTION  "Number of Gold Service Frames PIR dropped."
        ::= {rcIsidStatsEntry 92 }

rcIsidStatsSilverTxCirDroppedFrames  OBJECT-TYPE
        SYNTAX        Counter64
        MAX-ACCESS    read-only
        STATUS        current
        DESCRIPTION  "Number of Silver Service Frames CIR dropped."
        ::= {rcIsidStatsEntry 93 }

rcIsidStatsSilverTxPirDroppedFrames  OBJECT-TYPE
        SYNTAX        Counter64
        MAX-ACCESS    read-only
        STATUS        current
        DESCRIPTION  "Number of Silver Service Frames PIR dropped."
        ::= {rcIsidStatsEntry 94 }

rcIsidStatsStndTxCirDroppedFrames    OBJECT-TYPE
        SYNTAX        Counter64
        MAX-ACCESS    read-only
        STATUS        current
        DESCRIPTION  "Number of Standard Service Frames CIR dropped."
        ::= {rcIsidStatsEntry 95 }

rcIsidStatsStndTxPirDroppedFrames    OBJECT-TYPE
        SYNTAX        Counter64
        MAX-ACCESS    read-only
        STATUS        current
        DESCRIPTION  "Number of Standard Service Frames PIR dropped."
        ::= {rcIsidStatsEntry 96 }

rcIsidStatsRxMcastTotalFrames   OBJECT-TYPE
        SYNTAX        Counter64
        MAX-ACCESS    read-only
        STATUS        current
        DESCRIPTION  "Rx total Number of Mcast Octet"
        ::= {rcIsidStatsEntry 97 }

rcIsidStatsTxMcastTotalFrames  OBJECT-TYPE
        SYNTAX        Counter64
        MAX-ACCESS    read-only
        STATUS        current
        DESCRIPTION  "Tx total Number of Mcast Octet"
        ::= {rcIsidStatsEntry 98 }

rcIsidStatsPremRxMcastDroppedFrames  OBJECT-TYPE
        SYNTAX        Counter64
        MAX-ACCESS    read-only
        STATUS        current
        DESCRIPTION  "Number of Premium Service Rx Mcast Frames dropped."
        ::= {rcIsidStatsEntry 99 }

rcIsidStatsGoldRxMcastDroppedFrames  OBJECT-TYPE
        SYNTAX        Counter64
        MAX-ACCESS    read-only
        STATUS        current
        DESCRIPTION  "Number of Gold Service Rx Mcast Frames dropped."
        ::= {rcIsidStatsEntry 100 }

rcIsidStatsSilverRxMcastDroppedFrames        OBJECT-TYPE
        SYNTAX        Counter64
        MAX-ACCESS    read-only
        STATUS        current
        DESCRIPTION  "Number of Silver Service Rx Mcast Frames dropped."
        ::= {rcIsidStatsEntry 101 }

rcIsidStatsStndRxMcastDroppedFrames  OBJECT-TYPE
        SYNTAX        Counter64
        MAX-ACCESS    read-only
        STATUS        current
        DESCRIPTION  "Number of Standard Service Rx Mcast Frames dropped."
        ::= {rcIsidStatsEntry 102 }

rcIsidStatsPremRxCirOctets     OBJECT-TYPE
        SYNTAX        Counter64
        MAX-ACCESS    read-only
        STATUS        current
        DESCRIPTION  "Number of Premium Service Rx CIR Octets received."
        ::= { rcIsidStatsEntry 103}

rcIsidStatsPremRxCirOopOctets     OBJECT-TYPE
        SYNTAX        Counter64
        MAX-ACCESS    read-only
        STATUS        current
        DESCRIPTION  "Number of Premium Service Rx Octets received that 
		      were CIR OOP."
        ::= { rcIsidStatsEntry 104 }

rcIsidStatsPremRxEirOctets     OBJECT-TYPE
        SYNTAX        Counter64
        MAX-ACCESS    read-only
        STATUS        current
        DESCRIPTION  "Number of Premium Service Rx EIR Octets received."
        ::= { rcIsidStatsEntry 105 }

rcIsidStatsPremRxEirOopOctets     OBJECT-TYPE
        SYNTAX        Counter64
        MAX-ACCESS    read-only
        STATUS        current
        DESCRIPTION  "Number of Premium Service Rx Octets received that 
		      were EIR OOP."
        ::= { rcIsidStatsEntry 106 }

rcIsidStatsPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcIsidStatsEntry 107 }

rcIsidStatsPremRxPirOctets     OBJECT-TYPE
        SYNTAX        Counter64
        MAX-ACCESS    read-only
        STATUS        current
        DESCRIPTION  "Number of Premium Service Rx PIR Octets received."
        ::= { rcIsidStatsEntry 108 }

rcIsidStatsPremRxPirOopOctets     OBJECT-TYPE
        SYNTAX        Counter64
        MAX-ACCESS    read-only
        STATUS        current
        DESCRIPTION  "Number of Premium Service Rx Octets received that 
		      were PIR OOP."
        ::= { rcIsidStatsEntry 109 }

rcIsidStatsPremRxGreenOctets     OBJECT-TYPE
        SYNTAX        Counter64
        MAX-ACCESS    read-only
        STATUS        current
        DESCRIPTION  "Number of Premium Service Rx Octets received that 
		      were marked 'Green' by the policer."
        ::= { rcIsidStatsEntry 110 }

rcIsidStatsPremRxYellowOctets     OBJECT-TYPE
        SYNTAX        Counter64
        MAX-ACCESS    read-only
        STATUS        current
        DESCRIPTION  "Number of Premium Service Rx Octets received that 
		      were marked 'Yellow' by the policer."
        ::= { rcIsidStatsEntry 111 }

rcIsidStatsPremRxRedOctets     OBJECT-TYPE
        SYNTAX        Counter64
        MAX-ACCESS    read-only
        STATUS        current
        DESCRIPTION  "Number of Premium Service Rx Octets received that 
		      were marked 'Red' by the policer."
        ::= { rcIsidStatsEntry 112 }

rcIsidStatsGoldRxCirOctets     OBJECT-TYPE
        SYNTAX        Counter64
        MAX-ACCESS    read-only
        STATUS        current
        DESCRIPTION  "Number of Gold Service Rx CIR Octets received."
        ::= { rcIsidStatsEntry 113 }

rcIsidStatsGoldRxCirOopOctets     OBJECT-TYPE
        SYNTAX        Counter64
        MAX-ACCESS    read-only
        STATUS        current
        DESCRIPTION  "Number of Gold Service Rx Octets received that 
		      were CIR OOP."
        ::= { rcIsidStatsEntry 114 }

rcIsidStatsGoldRxEirOctets     OBJECT-TYPE
        SYNTAX        Counter64
        MAX-ACCESS    read-only
        STATUS        current
        DESCRIPTION  "Number of Gold Service Rx EIR Octets received."
        ::= { rcIsidStatsEntry 115 }

rcIsidStatsGoldRxEirOopOctets     OBJECT-TYPE
        SYNTAX        Counter64
        MAX-ACCESS    read-only
        STATUS        current
        DESCRIPTION  "Number of Gold Service Rx Octets received that 
		      were EIR OOP."
        ::= { rcIsidStatsEntry 116 }

rcIsidStatsGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcIsidStatsEntry 117 }

rcIsidStatsGoldRxPirOctets     OBJECT-TYPE
        SYNTAX        Counter64
        MAX-ACCESS    read-only
        STATUS        current
        DESCRIPTION  "Number of Gold Service Rx PIR Octets received."
        ::= { rcIsidStatsEntry 118 }

rcIsidStatsGoldRxPirOopOctets     OBJECT-TYPE
        SYNTAX        Counter64
        MAX-ACCESS    read-only
        STATUS        current
        DESCRIPTION  "Number of Gold Service Rx Octets received that 
		      were PIR OOP."
        ::= { rcIsidStatsEntry 119 }

rcIsidStatsGoldRxGreenOctets     OBJECT-TYPE
        SYNTAX        Counter64
        MAX-ACCESS    read-only
        STATUS        current
        DESCRIPTION  "Number of Gold Service Rx Octets received that 
		      were marked 'Green' by the policer."
        ::= { rcIsidStatsEntry 120 }

rcIsidStatsGoldRxYellowOctets     OBJECT-TYPE
        SYNTAX        Counter64
        MAX-ACCESS    read-only
        STATUS        current
        DESCRIPTION  "Number of Gold Service Rx Octets received that 
		      were marked 'Yellow' by the policer."
        ::= { rcIsidStatsEntry 121 }

rcIsidStatsGoldRxRedOctets     OBJECT-TYPE
        SYNTAX        Counter64
        MAX-ACCESS    read-only
        STATUS        current
        DESCRIPTION  "Number of Gold Service Rx Octets received that 
		      were marked 'Red' by the policer."
        ::= { rcIsidStatsEntry 122 }

rcIsidStatsSilverRxCirOctets     OBJECT-TYPE
        SYNTAX        Counter64
        MAX-ACCESS    read-only
        STATUS        current
        DESCRIPTION  "Number of Silver Service Rx CIR Octets received."
        ::= { rcIsidStatsEntry 123 }

rcIsidStatsSilverRxCirOopOctets     OBJECT-TYPE
        SYNTAX        Counter64
        MAX-ACCESS    read-only
        STATUS        current
        DESCRIPTION  "Number of Silver Service Rx Octets received that 
		      were CIR OOP."
        ::= { rcIsidStatsEntry 124 }

rcIsidStatsSilverRxEirOctets     OBJECT-TYPE
        SYNTAX        Counter64
        MAX-ACCESS    read-only
        STATUS        current
        DESCRIPTION  "Number of Silver Service Rx EIR Octets received."
        ::= { rcIsidStatsEntry 125 }

rcIsidStatsSilverRxEirOopOctets     OBJECT-TYPE
        SYNTAX        Counter64
        MAX-ACCESS    read-only
        STATUS        current
        DESCRIPTION  "Number of Silver Service Rx Octets received that 
		      were EIR OOP."
        ::= { rcIsidStatsEntry 126 }

rcIsidStatsSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcIsidStatsEntry 127 }

rcIsidStatsSilverRxPirOctets     OBJECT-TYPE
        SYNTAX        Counter64
        MAX-ACCESS    read-only
        STATUS        current
        DESCRIPTION  "Number of Silver Service Rx PIR Octets received."
        ::= { rcIsidStatsEntry 128 }

rcIsidStatsSilverRxPirOopOctets     OBJECT-TYPE
        SYNTAX        Counter64
        MAX-ACCESS    read-only
        STATUS        current
        DESCRIPTION  "Number of Silver Service Rx Octets received that 
		      were PIR OOP."
        ::= { rcIsidStatsEntry 129 }

rcIsidStatsSilverRxGreenOctets     OBJECT-TYPE
        SYNTAX        Counter64
        MAX-ACCESS    read-only
        STATUS        current
        DESCRIPTION  "Number of Silver Service Rx Octets received that 
		      were marked 'Green' by the policer."
        ::= { rcIsidStatsEntry 130 }

rcIsidStatsSilverRxYellowOctets     OBJECT-TYPE
        SYNTAX        Counter64
        MAX-ACCESS    read-only
        STATUS        current
        DESCRIPTION  "Number of Silver Service Rx Octets received that 
		      were marked 'Yellow' by the policer."
        ::= { rcIsidStatsEntry 131 }

rcIsidStatsSilverRxRedOctets     OBJECT-TYPE
        SYNTAX        Counter64
        MAX-ACCESS    read-only
        STATUS        current
        DESCRIPTION  "Number of Silver Service Rx Octets received that 
		      were marked 'Red' by the policer."
        ::= { rcIsidStatsEntry 132 }

rcIsidStatsStndRxCirOctets     OBJECT-TYPE
        SYNTAX        Counter64
        MAX-ACCESS    read-only
        STATUS        current
        DESCRIPTION  "Number of Standard Service Rx CIR Octets received."
        ::= { rcIsidStatsEntry 133 }

rcIsidStatsStndRxCirOopOctets     OBJECT-TYPE
        SYNTAX        Counter64
        MAX-ACCESS    read-only
        STATUS        current
        DESCRIPTION  "Number of Standard Service Rx Octets received that 
		      were CIR OOP."
        ::= { rcIsidStatsEntry 134 }

rcIsidStatsStndRxEirOctets     OBJECT-TYPE
        SYNTAX        Counter64
        MAX-ACCESS    read-only
        STATUS        current
        DESCRIPTION  "Number of Standard Service Rx EIR Octets received."
        ::= { rcIsidStatsEntry 135 }

rcIsidStatsStndRxEirOopOctets     OBJECT-TYPE
        SYNTAX        Counter64
        MAX-ACCESS    read-only
        STATUS        current
        DESCRIPTION  "Number of Standard Service Rx Octets received that 
		      were EIR OOP."
        ::= { rcIsidStatsEntry 136 }

rcIsidStatsStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcIsidStatsEntry 137 }

rcIsidStatsStndRxPirOctets     OBJECT-TYPE
        SYNTAX        Counter64
        MAX-ACCESS    read-only
        STATUS        current
        DESCRIPTION  "Number of Standard Service Rx PIR Octets received."
        ::= { rcIsidStatsEntry 138 }

rcIsidStatsStndRxPirOopOctets     OBJECT-TYPE
        SYNTAX        Counter64
        MAX-ACCESS    read-only
        STATUS        current
        DESCRIPTION  "Number of Standard Service Rx Octets received that 
		      were PIR OOP."
        ::= { rcIsidStatsEntry 139 }

rcIsidStatsStndRxGreenOctets     OBJECT-TYPE
        SYNTAX        Counter64
        MAX-ACCESS    read-only
        STATUS        current
        DESCRIPTION  "Number of Standard Service Rx Octets received that 
		      were marked 'Green' by the policer."
        ::= { rcIsidStatsEntry 140 }

rcIsidStatsStndRxYellowOctets     OBJECT-TYPE
        SYNTAX        Counter64
        MAX-ACCESS    read-only
        STATUS        current
        DESCRIPTION  "Number of Standard Service Rx Octets received that 
		      were marked 'Yellow' by the policer."
        ::= { rcIsidStatsEntry 141 }

rcIsidStatsStndRxRedOctets     OBJECT-TYPE
        SYNTAX        Counter64
        MAX-ACCESS    read-only
        STATUS        current
        DESCRIPTION  "Number of Standard Service Rx Octets received that 
		      were marked 'Red' by the policer."
        ::= { rcIsidStatsEntry 142 }

rcIsidStatsMcastRxDroppedOctets     OBJECT-TYPE
        SYNTAX        Counter64
        MAX-ACCESS    read-only
        STATUS        current
        DESCRIPTION  "Number of Multicast Rx Octets dropped."
        ::= { rcIsidStatsEntry 143 }

rcIsidStatsBcastUUcastRxTotalOctets     OBJECT-TYPE
        SYNTAX        Counter64
        MAX-ACCESS    read-only
        STATUS        current
        DESCRIPTION  "Number of Broadcast/Unknown Unicast Rx total Octets."
        ::= { rcIsidStatsEntry 144 }

rcIsidStatsBcastUUcastRxDroppedOctets     OBJECT-TYPE
        SYNTAX        Counter64
        MAX-ACCESS    read-only
        STATUS        current
        DESCRIPTION  "Number of Broadcast/Unknown Rx Octets dropped."
        ::= { rcIsidStatsEntry 145 }

rcIsidStatsPremRxCirFrames     OBJECT-TYPE
        SYNTAX        Counter64
        MAX-ACCESS    read-only
        STATUS        current
        DESCRIPTION  "Number of Premium Service Rx CIR Frames received."
        ::= { rcIsidStatsEntry 146 }

rcIsidStatsPremRxCirOopFrames     OBJECT-TYPE
        SYNTAX        Counter64
        MAX-ACCESS    read-only
        STATUS        current
        DESCRIPTION  "Number of Premium Service Rx Frames received that 
		      were CIR OOP."
        ::= { rcIsidStatsEntry 147 }

rcIsidStatsPremRxEirFrames     OBJECT-TYPE
        SYNTAX        Counter64
        MAX-ACCESS    read-only
        STATUS        current
        DESCRIPTION  "Number of Premium Service Rx EIR Frames received."
        ::= { rcIsidStatsEntry 148 }

rcIsidStatsPremRxEirOopFrames     OBJECT-TYPE
        SYNTAX        Counter64
        MAX-ACCESS    read-only
        STATUS        current
        DESCRIPTION  "Number of Premium Service Rx Frames received that 
		      were EIR OOP."
        ::= { rcIsidStatsEntry 149 }

rcIsidStatsPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcIsidStatsEntry 150 }

rcIsidStatsPremRxPirFrames     OBJECT-TYPE
        SYNTAX        Counter64
        MAX-ACCESS    read-only
        STATUS        current
        DESCRIPTION  "Number of Premium Service Rx PIR Frames received."
        ::= { rcIsidStatsEntry 151 }

rcIsidStatsPremRxPirOopFrames     OBJECT-TYPE
        SYNTAX        Counter64
        MAX-ACCESS    read-only
        STATUS        current
        DESCRIPTION  "Number of Premium Service Rx Frames received that 
		      were PIR OOP."
        ::= { rcIsidStatsEntry 152 }

rcIsidStatsPremRxGreenFrames     OBJECT-TYPE
        SYNTAX        Counter64
        MAX-ACCESS    read-only
        STATUS        current
        DESCRIPTION  "Number of Premium Service Rx Frames received that 
		      were marked 'Green' by the policer."
        ::= { rcIsidStatsEntry 153 }

rcIsidStatsPremRxYellowFrames     OBJECT-TYPE
        SYNTAX        Counter64
        MAX-ACCESS    read-only
        STATUS        current
        DESCRIPTION  "Number of Premium Service Rx Frames received that 
		      were marked 'Yellow' by the policer."
        ::= { rcIsidStatsEntry 154 }

rcIsidStatsPremRxRedFrames     OBJECT-TYPE
        SYNTAX        Counter64
        MAX-ACCESS    read-only
        STATUS        current
        DESCRIPTION  "Number of Premium Service Rx Frames received that 
		      were marked 'Red' by the policer."
        ::= { rcIsidStatsEntry 155 }

rcIsidStatsGoldRxCirFrames     OBJECT-TYPE
        SYNTAX        Counter64
        MAX-ACCESS    read-only
        STATUS        current
        DESCRIPTION  "Number of Gold Service Rx CIR Frames received."
        ::= { rcIsidStatsEntry 156 }

rcIsidStatsGoldRxCirOopFrames     OBJECT-TYPE
        SYNTAX        Counter64
        MAX-ACCESS    read-only
        STATUS        current
        DESCRIPTION  "Number of Gold Service Rx Frames received that 
		      were CIR OOP."
        ::= { rcIsidStatsEntry 157 }

rcIsidStatsGoldRxEirFrames     OBJECT-TYPE
        SYNTAX        Counter64
        MAX-ACCESS    read-only
        STATUS        current
        DESCRIPTION  "Number of Gold Service Rx EIR Frames received."
        ::= { rcIsidStatsEntry 158 }

rcIsidStatsGoldRxEirOopFrames     OBJECT-TYPE
        SYNTAX        Counter64
        MAX-ACCESS    read-only
        STATUS        current
        DESCRIPTION  "Number of Gold Service Rx Frames received that 
		      were EIR OOP."
        ::= { rcIsidStatsEntry 159 }

rcIsidStatsGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcIsidStatsEntry 160 }

rcIsidStatsGoldRxPirFrames     OBJECT-TYPE
        SYNTAX        Counter64
        MAX-ACCESS    read-only
        STATUS        current
        DESCRIPTION  "Number of Gold Service Rx PIR Frames received."
        ::= { rcIsidStatsEntry 161 }

rcIsidStatsGoldRxPirOopFrames     OBJECT-TYPE
        SYNTAX        Counter64
        MAX-ACCESS    read-only
        STATUS        current
        DESCRIPTION  "Number of Gold Service Rx Frames received that 
		      were PIR OOP."
        ::= { rcIsidStatsEntry 162 }

rcIsidStatsGoldRxGreenFrames     OBJECT-TYPE
        SYNTAX        Counter64
        MAX-ACCESS    read-only
        STATUS        current
        DESCRIPTION  "Number of Gold Service Rx Frames received that 
		      were marked 'Green' by the policer."
        ::= { rcIsidStatsEntry 163 }

rcIsidStatsGoldRxYellowFrames     OBJECT-TYPE
        SYNTAX        Counter64
        MAX-ACCESS    read-only
        STATUS        current
        DESCRIPTION  "Number of Gold Service Rx Frames received that 
		      were marked 'Yellow' by the policer."
        ::= { rcIsidStatsEntry 164 }

rcIsidStatsGoldRxRedFrames     OBJECT-TYPE
        SYNTAX        Counter64
        MAX-ACCESS    read-only
        STATUS        current
        DESCRIPTION  "Number of Gold Service Rx Frames received that 
		      were marked 'Red' by the policer."
        ::= { rcIsidStatsEntry 165 }

rcIsidStatsSilverRxCirFrames     OBJECT-TYPE
        SYNTAX        Counter64
        MAX-ACCESS    read-only
        STATUS        current
        DESCRIPTION  "Number of Silver Service Rx CIR Frames received."
        ::= { rcIsidStatsEntry 166 }

rcIsidStatsSilverRxCirOopFrames     OBJECT-TYPE
        SYNTAX        Counter64
        MAX-ACCESS    read-only
        STATUS        current
        DESCRIPTION  "Number of Silver Service Rx Frames received that 
		      were CIR OOP."
        ::= { rcIsidStatsEntry 167 }

rcIsidStatsSilverRxEirFrames     OBJECT-TYPE
        SYNTAX        Counter64
        MAX-ACCESS    read-only
        STATUS        current
        DESCRIPTION  "Number of Silver Service Rx EIR Frames received."
        ::= { rcIsidStatsEntry 168 }

rcIsidStatsSilverRxEirOopFrames     OBJECT-TYPE
        SYNTAX        Counter64
        MAX-ACCESS    read-only
        STATUS        current
        DESCRIPTION  "Number of Silver Service Rx Frames received that 
		      were EIR OOP."
        ::= { rcIsidStatsEntry 169 }

rcIsidStatsSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcIsidStatsEntry 170 }

rcIsidStatsSilverRxPirFrames     OBJECT-TYPE
        SYNTAX        Counter64
        MAX-ACCESS    read-only
        STATUS        current
        DESCRIPTION  "Number of Silver Service Rx PIR Frames received."
        ::= { rcIsidStatsEntry 171 }

rcIsidStatsSilverRxPirOopFrames     OBJECT-TYPE
        SYNTAX        Counter64
        MAX-ACCESS    read-only
        STATUS        current
        DESCRIPTION  "Number of Silver Service Rx Frames received that 
		      were PIR OOP."
        ::= { rcIsidStatsEntry 172 }

rcIsidStatsSilverRxGreenFrames     OBJECT-TYPE
        SYNTAX        Counter64
        MAX-ACCESS    read-only
        STATUS        current
        DESCRIPTION  "Number of Silver Service Rx Frames received that 
		      were marked 'Green' by the policer."
        ::= { rcIsidStatsEntry 173 }

rcIsidStatsSilverRxYellowFrames     OBJECT-TYPE
        SYNTAX        Counter64
        MAX-ACCESS    read-only
        STATUS        current
        DESCRIPTION  "Number of Silver Service Rx Frames received that 
		      were marked 'Yellow' by the policer."
        ::= { rcIsidStatsEntry 174 }

rcIsidStatsSilverRxRedFrames     OBJECT-TYPE
        SYNTAX        Counter64
        MAX-ACCESS    read-only
        STATUS        current
        DESCRIPTION  "Number of Silver Service Rx Frames received that 
		      were marked 'Red' by the policer."
        ::= { rcIsidStatsEntry 175 }

rcIsidStatsStndRxCirFrames     OBJECT-TYPE
        SYNTAX        Counter64
        MAX-ACCESS    read-only
        STATUS        current
        DESCRIPTION  "Number of Standard Service Rx CIR Frames received."
        ::= { rcIsidStatsEntry 176 }

rcIsidStatsStndRxCirOopFrames     OBJECT-TYPE
        SYNTAX        Counter64
        MAX-ACCESS    read-only
        STATUS        current
        DESCRIPTION  "Number of Standard Service Rx Frames received that 
		      were CIR OOP."
        ::= { rcIsidStatsEntry 177 }

rcIsidStatsStndRxEirFrames     OBJECT-TYPE
        SYNTAX        Counter64
        MAX-ACCESS    read-only
        STATUS        current
        DESCRIPTION  "Number of Standard Service Rx EIR Frames received."
        ::= { rcIsidStatsEntry 178 }

rcIsidStatsStndRxEirOopFrames     OBJECT-TYPE
        SYNTAX        Counter64
        MAX-ACCESS    read-only
        STATUS        current
        DESCRIPTION  "Number of Standard Service Rx Frames received that 
		      were EIR OOP."
        ::= { rcIsidStatsEntry 179 }

rcIsidStatsStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcIsidStatsEntry 180 }

rcIsidStatsStndRxPirFrames     OBJECT-TYPE
        SYNTAX        Counter64
        MAX-ACCESS    read-only
        STATUS        current
        DESCRIPTION  "Number of Standard Service Rx PIR Frames received."
        ::= { rcIsidStatsEntry 181 }

rcIsidStatsStndRxPirOopFrames     OBJECT-TYPE
        SYNTAX        Counter64
        MAX-ACCESS    read-only
        STATUS        current
        DESCRIPTION  "Number of Standard Service Rx Frames received that 
		      were PIR OOP."
        ::= { rcIsidStatsEntry 182 }

rcIsidStatsStndRxGreenFrames     OBJECT-TYPE
        SYNTAX        Counter64
        MAX-ACCESS    read-only
        STATUS        current
        DESCRIPTION  "Number of Standard Service Rx Frames received that 
		      were marked 'Green' by the policer."
        ::= { rcIsidStatsEntry 183 }

rcIsidStatsStndRxYellowFrames     OBJECT-TYPE
        SYNTAX        Counter64
        MAX-ACCESS    read-only
        STATUS        current
        DESCRIPTION  "Number of Standard Service Rx Frames received that 
		      were marked 'Yellow' by the policer."
        ::= { rcIsidStatsEntry 184 }

rcIsidStatsStndRxRedFrames     OBJECT-TYPE
        SYNTAX        Counter64
        MAX-ACCESS    read-only
        STATUS        current
        DESCRIPTION  "Number of Standard Service Rx Frames received that 
		      were marked 'Red' by the policer."
        ::= { rcIsidStatsEntry 185 }

rcIsidStatsMcastRxDroppedFrames     OBJECT-TYPE
        SYNTAX        Counter64
        MAX-ACCESS    read-only
        STATUS        current
        DESCRIPTION  "Number of Multicast Rx Frames dropped."
        ::= { rcIsidStatsEntry 186 }

rcIsidStatsBcastUUcastRxTotalFrames     OBJECT-TYPE
        SYNTAX        Counter64
        MAX-ACCESS    read-only
        STATUS        current
        DESCRIPTION  "Number of Broadcast/Unknown Unicast Rx total Frames."
        ::= { rcIsidStatsEntry 187 }

rcIsidStatsBcastUUcastRxDroppedFrames     OBJECT-TYPE
        SYNTAX        Counter64
        MAX-ACCESS    read-only
        STATUS        current
        DESCRIPTION  "Number of Broadcast/Unknown Rx Frames dropped."
        ::= { rcIsidStatsEntry 188 }

rcIsidStatsPremTxCirOctets     OBJECT-TYPE
        SYNTAX        Counter64
        MAX-ACCESS    read-only
        STATUS        current
        DESCRIPTION  "Number of Premium Service Tx CIR Octets received."
        ::= { rcIsidStatsEntry 189 }

rcIsidStatsPremTxCirOopOctets     OBJECT-TYPE
        SYNTAX        Counter64
        MAX-ACCESS    read-only
        STATUS        current
        DESCRIPTION  "Number of Premium Service Tx Octets received that 
		      were CIR OOP."
        ::= { rcIsidStatsEntry 190 }

rcIsidStatsPremTxEirOctets     OBJECT-TYPE
        SYNTAX        Counter64
        MAX-ACCESS    read-only
        STATUS        current
        DESCRIPTION  "Number of Premium Service Tx EIR Octets received."
        ::= { rcIsidStatsEntry 191 }

rcIsidStatsPremTxEirOopOctets     OBJECT-TYPE
        SYNTAX        Counter64
        MAX-ACCESS    read-only
        STATUS        current
        DESCRIPTION  "Number of Premium Service Tx Octets received that 
		      were EIR OOP."
        ::= { rcIsidStatsEntry 192 }

rcIsidStatsPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcIsidStatsEntry 193 }

rcIsidStatsPremTxPirOctets     OBJECT-TYPE
        SYNTAX        Counter64
        MAX-ACCESS    read-only
        STATUS        current
        DESCRIPTION  "Number of Premium Service Tx PIR Octets received."
        ::= { rcIsidStatsEntry 194 }

rcIsidStatsPremTxPirOopOctets     OBJECT-TYPE
        SYNTAX        Counter64
        MAX-ACCESS    read-only
        STATUS        current
        DESCRIPTION  "Number of Premium Service Tx Octets received that 
		      were PIR OOP."
        ::= { rcIsidStatsEntry 195 }

rcIsidStatsPremTxGreenOctets     OBJECT-TYPE
        SYNTAX        Counter64
        MAX-ACCESS    read-only
        STATUS        current
        DESCRIPTION  "Number of Premium Service Tx Octets received that 
		      were marked 'Green' by the policer."
        ::= { rcIsidStatsEntry 196 }

rcIsidStatsPremTxYellowOctets     OBJECT-TYPE
        SYNTAX        Counter64
        MAX-ACCESS    read-only
        STATUS        current
        DESCRIPTION  "Number of Premium Service Tx Octets received that 
		      were marked 'Yellow' by the policer."
        ::= { rcIsidStatsEntry 197 }

rcIsidStatsPremTxRedOctets     OBJECT-TYPE
        SYNTAX        Counter64
        MAX-ACCESS    read-only
        STATUS        current
        DESCRIPTION  "Number of Premium Service Tx Octets received that 
		      were marked 'Red' by the policer."
        ::= { rcIsidStatsEntry 198 }

rcIsidStatsGoldTxCirOctets     OBJECT-TYPE
        SYNTAX        Counter64
        MAX-ACCESS    read-only
        STATUS        current
        DESCRIPTION  "Number of Gold Service Tx CIR Octets received."
        ::= { rcIsidStatsEntry 199 }

rcIsidStatsGoldTxCirOopOctets     OBJECT-TYPE
        SYNTAX        Counter64
        MAX-ACCESS    read-only
        STATUS        current
        DESCRIPTION  "Number of Gold Service Tx Octets received that 
		      were CIR OOP."
        ::= { rcIsidStatsEntry 200 }

rcIsidStatsGoldTxEirOctets     OBJECT-TYPE
        SYNTAX        Counter64
        MAX-ACCESS    read-only
        STATUS        current
        DESCRIPTION  "Number of Gold Service Tx EIR Octets received."
        ::= { rcIsidStatsEntry 201 }

rcIsidStatsGoldTxEirOopOctets     OBJECT-TYPE
        SYNTAX        Counter64
        MAX-ACCESS    read-only
        STATUS        current
        DESCRIPTION  "Number of Gold Service Tx Octets received that 
		      were EIR OOP."
        ::= { rcIsidStatsEntry 202 }

rcIsidStatsGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcIsidStatsEntry 203 }

rcIsidStatsGoldTxPirOctets     OBJECT-TYPE
        SYNTAX        Counter64
        MAX-ACCESS    read-only
        STATUS        current
        DESCRIPTION  "Number of Gold Service Tx PIR Octets received."
        ::= { rcIsidStatsEntry 204 }

rcIsidStatsGoldTxPirOopOctets     OBJECT-TYPE
        SYNTAX        Counter64
        MAX-ACCESS    read-only
        STATUS        current
        DESCRIPTION  "Number of Gold Service Tx Octets received that 
		      were PIR OOP."
        ::= { rcIsidStatsEntry 205 }

rcIsidStatsGoldTxGreenOctets     OBJECT-TYPE
        SYNTAX        Counter64
        MAX-ACCESS    read-only
        STATUS        current
        DESCRIPTION  "Number of Gold Service Tx Octets received that 
		      were marked 'Green' by the policer."
        ::= { rcIsidStatsEntry 206 }

rcIsidStatsGoldTxYellowOctets     OBJECT-TYPE
        SYNTAX        Counter64
        MAX-ACCESS    read-only
        STATUS        current
        DESCRIPTION  "Number of Gold Service Tx Octets received that 
		      were marked 'Yellow' by the policer."
        ::= { rcIsidStatsEntry 207 }

rcIsidStatsGoldTxRedOctets     OBJECT-TYPE
        SYNTAX        Counter64
        MAX-ACCESS    read-only
        STATUS        current
        DESCRIPTION  "Number of Gold Service Tx Octets received that 
		      were marked 'Red' by the policer."
        ::= { rcIsidStatsEntry 208 }

rcIsidStatsSilverTxCirOctets     OBJECT-TYPE
        SYNTAX        Counter64
        MAX-ACCESS    read-only
        STATUS        current
        DESCRIPTION  "Number of Silver Service Tx CIR Octets received."
        ::= { rcIsidStatsEntry 209 }

rcIsidStatsSilverTxCirOopOctets     OBJECT-TYPE
        SYNTAX        Counter64
        MAX-ACCESS    read-only
        STATUS        current
        DESCRIPTION  "Number of Silver Service Tx Octets received that 
		      were CIR OOP."
        ::= { rcIsidStatsEntry 210 }

rcIsidStatsSilverTxEirOctets     OBJECT-TYPE
        SYNTAX        Counter64
        MAX-ACCESS    read-only
        STATUS        current
        DESCRIPTION  "Number of Silver Service Tx EIR Octets received."
        ::= { rcIsidStatsEntry 211 }

rcIsidStatsSilverTxEirOopOctets     OBJECT-TYPE
        SYNTAX        Counter64
        MAX-ACCESS    read-only
        STATUS        current
        DESCRIPTION  "Number of Silver Service Tx Octets received that 
		      were EIR OOP."
        ::= { rcIsidStatsEntry 212 }

rcIsidStatsSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcIsidStatsEntry 213 }

rcIsidStatsSilverTxPirOctets     OBJECT-TYPE
        SYNTAX        Counter64
        MAX-ACCESS    read-only
        STATUS        current
        DESCRIPTION  "Number of Silver Service Tx PIR Octets received."
        ::= { rcIsidStatsEntry 214 }

rcIsidStatsSilverTxPirOopOctets     OBJECT-TYPE
        SYNTAX        Counter64
        MAX-ACCESS    read-only
        STATUS        current
        DESCRIPTION  "Number of Silver Service Tx Octets received that 
		      were PIR OOP."
        ::= { rcIsidStatsEntry 215 }

rcIsidStatsSilverTxGreenOctets     OBJECT-TYPE
        SYNTAX        Counter64
        MAX-ACCESS    read-only
        STATUS        current
        DESCRIPTION  "Number of Silver Service Tx Octets received that 
		      were marked 'Green' by the policer."
        ::= { rcIsidStatsEntry 216 }

rcIsidStatsSilverTxYellowOctets     OBJECT-TYPE
        SYNTAX        Counter64
        MAX-ACCESS    read-only
        STATUS        current
        DESCRIPTION  "Number of Silver Service Tx Octets received that 
		      were marked 'Yellow' by the policer."
        ::= { rcIsidStatsEntry 217 }

rcIsidStatsSilverTxRedOctets     OBJECT-TYPE
        SYNTAX        Counter64
        MAX-ACCESS    read-only
        STATUS        current
        DESCRIPTION  "Number of Silver Service Tx Octets received that 
		      were marked 'Red' by the policer."
        ::= { rcIsidStatsEntry 218 }

rcIsidStatsStndTxCirOctets     OBJECT-TYPE
        SYNTAX        Counter64
        MAX-ACCESS    read-only
        STATUS        current
        DESCRIPTION  "Number of Standard Service Tx CIR Octets received."
        ::= { rcIsidStatsEntry 219 }

rcIsidStatsStndTxCirOopOctets     OBJECT-TYPE
        SYNTAX        Counter64
        MAX-ACCESS    read-only
        STATUS        current
        DESCRIPTION  "Number of Standard Service Tx Octets received that 
		      were CIR OOP."
        ::= { rcIsidStatsEntry 220 }

rcIsidStatsStndTxEirOctets     OBJECT-TYPE
        SYNTAX        Counter64
        MAX-ACCESS    read-only
        STATUS        current
        DESCRIPTION  "Number of Standard Service Tx EIR Octets received."
        ::= { rcIsidStatsEntry 221 }

rcIsidStatsStndTxEirOopOctets     OBJECT-TYPE
        SYNTAX        Counter64
        MAX-ACCESS    read-only
        STATUS        current
        DESCRIPTION  "Number of Standard Service Tx Octets received that 
		      were EIR OOP."
        ::= { rcIsidStatsEntry 222 }

rcIsidStatsStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcIsidStatsEntry 223 }

rcIsidStatsStndTxPirOctets     OBJECT-TYPE
        SYNTAX        Counter64
        MAX-ACCESS    read-only
        STATUS        current
        DESCRIPTION  "Number of Standard Service Tx PIR Octets received."
        ::= { rcIsidStatsEntry 224 }

rcIsidStatsStndTxPirOopOctets     OBJECT-TYPE
        SYNTAX        Counter64
        MAX-ACCESS    read-only
        STATUS        current
        DESCRIPTION  "Number of Standard Service Tx Octets received that 
		      were PIR OOP."
        ::= { rcIsidStatsEntry 225 }

rcIsidStatsStndTxGreenOctets     OBJECT-TYPE
        SYNTAX        Counter64
        MAX-ACCESS    read-only
        STATUS        current
        DESCRIPTION  "Number of Standard Service Tx Octets received that 
		      were marked 'Green' by the policer."
        ::= { rcIsidStatsEntry 226 }

rcIsidStatsStndTxYellowOctets     OBJECT-TYPE
        SYNTAX        Counter64
        MAX-ACCESS    read-only
        STATUS        current
        DESCRIPTION  "Number of Standard Service Tx Octets received that 
		      were marked 'Yellow' by the policer."
        ::= { rcIsidStatsEntry 227 }

rcIsidStatsStndTxRedOctets     OBJECT-TYPE
        SYNTAX        Counter64
        MAX-ACCESS    read-only
        STATUS        current
        DESCRIPTION  "Number of Standard Service Tx Octets received that 
		      were marked 'Red' by the policer."
        ::= { rcIsidStatsEntry 228 }

rcIsidStatsMcastTxDroppedOctets     OBJECT-TYPE
        SYNTAX        Counter64
        MAX-ACCESS    read-only
        STATUS        current
        DESCRIPTION  "Number of Multicast Tx Octets dropped."
        ::= { rcIsidStatsEntry 229 }

rcIsidStatsBcastUUcastTxTotalOctets     OBJECT-TYPE
        SYNTAX        Counter64
        MAX-ACCESS    read-only
        STATUS        current
        DESCRIPTION  "Number of Broadcast/Unknown Unicast Tx total Octets."
        ::= { rcIsidStatsEntry 230 }

rcIsidStatsBcastUUcastTxDroppedOctets     OBJECT-TYPE
        SYNTAX        Counter64
        MAX-ACCESS    read-only
        STATUS        current
        DESCRIPTION  "Number of Broadcast/Unknown Tx Octets dropped."
        ::= { rcIsidStatsEntry 231 }

rcIsidStatsPremTxCirFrames     OBJECT-TYPE
        SYNTAX        Counter64
        MAX-ACCESS    read-only
        STATUS        current
        DESCRIPTION  "Number of Premium Service Tx CIR Frames received."
        ::= { rcIsidStatsEntry 232 }

rcIsidStatsPremTxCirOopFrames     OBJECT-TYPE
        SYNTAX        Counter64
        MAX-ACCESS    read-only
        STATUS        current
        DESCRIPTION  "Number of Premium Service Tx Frames received that 
		      were CIR OOP."
        ::= { rcIsidStatsEntry 233 }

rcIsidStatsPremTxEirFrames     OBJECT-TYPE
        SYNTAX        Counter64
        MAX-ACCESS    read-only
        STATUS        current
        DESCRIPTION  "Number of Premium Service Tx EIR Frames received."
        ::= { rcIsidStatsEntry 234 }

rcIsidStatsPremTxEirOopFrames     OBJECT-TYPE
        SYNTAX        Counter64
        MAX-ACCESS    read-only
        STATUS        current
        DESCRIPTION  "Number of Premium Service Tx Frames received that 
		      were EIR OOP."
        ::= { rcIsidStatsEntry 235 }

rcIsidStatsPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcIsidStatsEntry 236 }

rcIsidStatsPremTxPirFrames     OBJECT-TYPE
        SYNTAX        Counter64
        MAX-ACCESS    read-only
        STATUS        current
        DESCRIPTION  "Number of Premium Service Tx PIR Frames received."
        ::= { rcIsidStatsEntry 237 }

rcIsidStatsPremTxPirOopFrames     OBJECT-TYPE
        SYNTAX        Counter64
        MAX-ACCESS    read-only
        STATUS        current
        DESCRIPTION  "Number of Premium Service Tx Frames received that 
		      were PIR OOP."
        ::= { rcIsidStatsEntry 238 }

rcIsidStatsPremTxGreenFrames     OBJECT-TYPE
        SYNTAX        Counter64
        MAX-ACCESS    read-only
        STATUS        current
        DESCRIPTION  "Number of Premium Service Tx Frames received that 
		      were marked 'Green' by the policer."
        ::= { rcIsidStatsEntry 239 }

rcIsidStatsPremTxYellowFrames     OBJECT-TYPE
        SYNTAX        Counter64
        MAX-ACCESS    read-only
        STATUS        current
        DESCRIPTION  "Number of Premium Service Tx Frames received that 
		      were marked 'Yellow' by the policer."
        ::= { rcIsidStatsEntry 240 }

rcIsidStatsPremTxRedFrames     OBJECT-TYPE
        SYNTAX        Counter64
        MAX-ACCESS    read-only
        STATUS        current
        DESCRIPTION  "Number of Premium Service Tx Frames received that 
		      were marked 'Red' by the policer."
        ::= { rcIsidStatsEntry 241 }

rcIsidStatsGoldTxCirFrames     OBJECT-TYPE
        SYNTAX        Counter64
        MAX-ACCESS    read-only
        STATUS        current
        DESCRIPTION  "Number of Gold Service Tx CIR Frames received."
        ::= { rcIsidStatsEntry 242 }

rcIsidStatsGoldTxCirOopFrames     OBJECT-TYPE
        SYNTAX        Counter64
        MAX-ACCESS    read-only
        STATUS        current
        DESCRIPTION  "Number of Gold Service Tx Frames received that 
		      were CIR OOP."
        ::= { rcIsidStatsEntry 243 }

rcIsidStatsGoldTxEirFrames     OBJECT-TYPE
        SYNTAX        Counter64
        MAX-ACCESS    read-only
        STATUS        current
        DESCRIPTION  "Number of Gold Service Tx EIR Frames received."
        ::= { rcIsidStatsEntry 244 }

rcIsidStatsGoldTxEirOopFrames     OBJECT-TYPE
        SYNTAX        Counter64
        MAX-ACCESS    read-only
        STATUS        current
        DESCRIPTION  "Number of Gold Service Tx Frames received that 
		      were EIR OOP."
        ::= { rcIsidStatsEntry 245 }

rcIsidStatsGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcIsidStatsEntry 246 }

rcIsidStatsGoldTxPirFrames     OBJECT-TYPE
        SYNTAX        Counter64
        MAX-ACCESS    read-only
        STATUS        current
        DESCRIPTION  "Number of Gold Service Tx PIR Frames received."
        ::= { rcIsidStatsEntry 247 }

rcIsidStatsGoldTxPirOopFrames     OBJECT-TYPE
        SYNTAX        Counter64
        MAX-ACCESS    read-only
        STATUS        current
        DESCRIPTION  "Number of Gold Service Tx Frames received that 
		      were PIR OOP."
        ::= { rcIsidStatsEntry 248 }

rcIsidStatsGoldTxGreenFrames     OBJECT-TYPE
        SYNTAX        Counter64
        MAX-ACCESS    read-only
        STATUS        current
        DESCRIPTION  "Number of Gold Service Tx Frames received that 
		      were marked 'Green' by the policer."
        ::= { rcIsidStatsEntry 249 }

rcIsidStatsGoldTxYellowFrames     OBJECT-TYPE
        SYNTAX        Counter64
        MAX-ACCESS    read-only
        STATUS        current
        DESCRIPTION  "Number of Gold Service Tx Frames received that 
		      were marked 'Yellow' by the policer."
        ::= { rcIsidStatsEntry 250 }

rcIsidStatsGoldTxRedFrames     OBJECT-TYPE
        SYNTAX        Counter64
        MAX-ACCESS    read-only
        STATUS        current
        DESCRIPTION  "Number of Gold Service Tx Frames received that 
		      were marked 'Red' by the policer."
        ::= { rcIsidStatsEntry 251 }

rcIsidStatsSilverTxCirFrames     OBJECT-TYPE
        SYNTAX        Counter64
        MAX-ACCESS    read-only
        STATUS        current
        DESCRIPTION  "Number of Silver Service Tx CIR Frames received."
        ::= { rcIsidStatsEntry 252 }

rcIsidStatsSilverTxCirOopFrames     OBJECT-TYPE
        SYNTAX        Counter64
        MAX-ACCESS    read-only
        STATUS        current
        DESCRIPTION  "Number of Silver Service Tx Frames received that 
		      were CIR OOP."
        ::= { rcIsidStatsEntry 253 }

rcIsidStatsSilverTxEirFrames     OBJECT-TYPE
        SYNTAX        Counter64
        MAX-ACCESS    read-only
        STATUS        current
        DESCRIPTION  "Number of Silver Service Tx EIR Frames received."
        ::= { rcIsidStatsEntry 254 }

rcIsidStatsSilverTxEirOopFrames     OBJECT-TYPE
        SYNTAX        Counter64
        MAX-ACCESS    read-only
        STATUS        current
        DESCRIPTION  "Number of Silver Service Tx Frames received that 
		      were EIR OOP."
        ::= { rcIsidStatsEntry 255 }

rcIsidStatsSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcIsidStatsEntry 256 }

rcIsidStatsSilverTxPirFrames     OBJECT-TYPE
        SYNTAX        Counter64
        MAX-ACCESS    read-only
        STATUS        current
        DESCRIPTION  "Number of Silver Service Tx PIR Frames received."
        ::= { rcIsidStatsEntry 257 }

rcIsidStatsSilverTxPirOopFrames     OBJECT-TYPE
        SYNTAX        Counter64
        MAX-ACCESS    read-only
        STATUS        current
        DESCRIPTION  "Number of Silver Service Tx Frames received that 
		      were PIR OOP."
        ::= { rcIsidStatsEntry 258 }

rcIsidStatsSilverTxGreenFrames     OBJECT-TYPE
        SYNTAX        Counter64
        MAX-ACCESS    read-only
        STATUS        current
        DESCRIPTION  "Number of Silver Service Tx Frames received that 
		      were marked 'Green' by the policer."
        ::= { rcIsidStatsEntry 259 }

rcIsidStatsSilverTxYellowFrames     OBJECT-TYPE
        SYNTAX        Counter64
        MAX-ACCESS    read-only
        STATUS        current
        DESCRIPTION  "Number of Silver Service Tx Frames received that 
		      were marked 'Yellow' by the policer."
        ::= { rcIsidStatsEntry 260 }

rcIsidStatsSilverTxRedFrames     OBJECT-TYPE
        SYNTAX        Counter64
        MAX-ACCESS    read-only
        STATUS        current
        DESCRIPTION  "Number of Silver Service Tx Frames received that 
		      were marked 'Red' by the policer."
        ::= { rcIsidStatsEntry 261 }

rcIsidStatsStndTxCirFrames     OBJECT-TYPE
        SYNTAX        Counter64
        MAX-ACCESS    read-only
        STATUS        current
        DESCRIPTION  "Number of Standard Service Tx CIR Frames received."
        ::= { rcIsidStatsEntry 262 }

rcIsidStatsStndTxCirOopFrames     OBJECT-TYPE
        SYNTAX        Counter64
        MAX-ACCESS    read-only
        STATUS        current
        DESCRIPTION  "Number of Standard Service Tx Frames received that 
		      were CIR OOP."
        ::= { rcIsidStatsEntry 263 }

rcIsidStatsStndTxEirFrames     OBJECT-TYPE
        SYNTAX        Counter64
        MAX-ACCESS    read-only
        STATUS        current
        DESCRIPTION  "Number of Standard Service Tx EIR Frames received."
        ::= { rcIsidStatsEntry 264 }

rcIsidStatsStndTxEirOopFrames     OBJECT-TYPE
        SYNTAX        Counter64
        MAX-ACCESS    read-only
        STATUS        current
        DESCRIPTION  "Number of Standard Service Tx Frames received that 
		      were EIR OOP."
        ::= { rcIsidStatsEntry 265 }

rcIsidStatsStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcIsidStatsEntry 266 }

rcIsidStatsStndTxPirFrames     OBJECT-TYPE
        SYNTAX        Counter64
        MAX-ACCESS    read-only
        STATUS        current
        DESCRIPTION  "Number of Standard Service Tx PIR Frames received."
        ::= { rcIsidStatsEntry 267 }

rcIsidStatsStndTxPirOopFrames     OBJECT-TYPE
        SYNTAX        Counter64
        MAX-ACCESS    read-only
        STATUS        current
        DESCRIPTION  "Number of Standard Service Tx Frames received that 
		      were PIR OOP."
        ::= { rcIsidStatsEntry 268 }

rcIsidStatsStndTxGreenFrames     OBJECT-TYPE
        SYNTAX        Counter64
        MAX-ACCESS    read-only
        STATUS        current
        DESCRIPTION  "Number of Standard Service Tx Frames received that 
		      were marked 'Green' by the policer."
        ::= { rcIsidStatsEntry 269 }

rcIsidStatsStndTxYellowFrames     OBJECT-TYPE
        SYNTAX        Counter64
        MAX-ACCESS    read-only
        STATUS        current
        DESCRIPTION  "Number of Standard Service Tx Frames received that 
		      were marked 'Yellow' by the policer."
        ::= { rcIsidStatsEntry 270 }

rcIsidStatsStndTxRedFrames     OBJECT-TYPE
        SYNTAX        Counter64
        MAX-ACCESS    read-only
        STATUS        current
        DESCRIPTION  "Number of Standard Service Tx Frames received that 
		      were marked 'Red' by the policer."
        ::= { rcIsidStatsEntry 271 }

rcIsidStatsMcastTxDroppedFrames     OBJECT-TYPE
        SYNTAX        Counter64
        MAX-ACCESS    read-only
        STATUS        current
        DESCRIPTION  "Number of Multicast Tx Frames dropped."
        ::= { rcIsidStatsEntry 272 }

rcIsidStatsBcastUUcastTxTotalFrames     OBJECT-TYPE
        SYNTAX        Counter64
        MAX-ACCESS    read-only
        STATUS        current
        DESCRIPTION  "Number of Broadcast/Unknown Unicast Tx total Frames."
        ::= { rcIsidStatsEntry 273 }

rcIsidStatsBcastUUcastTxDroppedFrames     OBJECT-TYPE
        SYNTAX        Counter64
        MAX-ACCESS    read-only
        STATUS        current
        DESCRIPTION  "Number of Broadcast/Unknown Tx Frames dropped."
        ::= { rcIsidStatsEntry 274 }

rcIsidStatsDropClassRxDroppedOctets     OBJECT-TYPE
        SYNTAX        Counter64
        MAX-ACCESS    read-only
        STATUS        current
        DESCRIPTION  "Number of Drop Class Rx Octets dropped."
        ::= { rcIsidStatsEntry 276 }

rcIsidStatsDropClassRxDroppedFrames     OBJECT-TYPE
        SYNTAX        Counter64
        MAX-ACCESS    read-only
        STATUS        current
        DESCRIPTION  "Number of Drop Class Rx Frames dropped."
        ::= { rcIsidStatsEntry 277 }

rcIsidStatsDropClassTxDroppedOctets	OBJECT-TYPE
        SYNTAX        Counter64
        MAX-ACCESS    read-only
        STATUS        current
        DESCRIPTION  "Number of Drop Class Tx Octets dropped."
        ::= { rcIsidStatsEntry 278 }

rcIsidStatsDropClassTxDroppedFrames     OBJECT-TYPE
        SYNTAX        Counter64
        MAX-ACCESS    read-only
        STATUS        current
        DESCRIPTION  "Number of Drop Class Tx Frames dropped."
        ::= { rcIsidStatsEntry 279 }



-- Isid endpoint stats table

rcIsidEndptStatsTable OBJECT-TYPE
        SYNTAX        SEQUENCE OF RcIsidEndptStatsEntry
        MAX-ACCESS    not-accessible
        STATUS        current
        DESCRIPTION   ""
        ::= { rc8021ah 4 }
 
rcIsidEndptStatsEntry OBJECT-TYPE
        SYNTAX        RcIsidEndptStatsEntry
        MAX-ACCESS    not-accessible
        STATUS        current
        DESCRIPTION   "A Isid End-Point Statistics  table entry."
        INDEX         { rcIsidEndptStatsIsidId, rcIsidEndptStatsTlsIndex }
        ::= { rcIsidEndptStatsTable 1 }
 
RcIsidEndptStatsEntry ::=
        SEQUENCE {
                rcIsidEndptStatsIsidId                       INTEGER,
                rcIsidEndptStatsTlsIndex                     INTEGER,
                rcIsidEndptStatsPort                         InterfaceIndex,
                rcIsidEndptStatsPremRxOctets                 Counter64, 
                rcIsidEndptStatsPremRxDroppedOctets          Counter64,
                rcIsidEndptStatsGoldRxOctets                 Counter64,       
                rcIsidEndptStatsGoldRxDroppedOctets          Counter64,
                rcIsidEndptStatsSilverRxOctets               Counter64,       
                rcIsidEndptStatsSilverRxDroppedOctets        Counter64,
                rcIsidEndptStatsStndRxOctets                 Counter64,      
                rcIsidEndptStatsStndRxDroppedOctets          Counter64,
                rcIsidEndptStatsPremTxOctets                 Counter64,      
                rcIsidEndptStatsGoldTxOctets                 Counter64,      
                rcIsidEndptStatsSilverTxOctets               Counter64,
                rcIsidEndptStatsStndTxOctets                 Counter64,      
                rcIsidEndptStatsPremTxMcastOctets            Counter64,     
                rcIsidEndptStatsGoldTxMcastOctets            Counter64,     
                rcIsidEndptStatsSilverTxMcastOctets          Counter64,
                rcIsidEndptStatsStndTxMcastOctets            Counter64,
                rcIsidEndptStatsPremCongestionDropOctets     Counter64,
                rcIsidEndptStatsGoldCongestionDropOctets     Counter64,
                rcIsidEndptStatsSilverCongestionDropOctets   Counter64,       
                rcIsidEndptStatsStndCongestionDropOctets     Counter64,  
                rcIsidEndptStatsPremCirDroppedOctets         Counter64,
                rcIsidEndptStatsPremPirDroppedOctets         Counter64,
                rcIsidEndptStatsGoldCirDroppedOctets         Counter64,
                rcIsidEndptStatsGoldPirDroppedOctets         Counter64,
                rcIsidEndptStatsSilverCirDroppedOctets       Counter64,
                rcIsidEndptStatsSilverPirDroppedOctets       Counter64,
                rcIsidEndptStatsStndCirDroppedOctets         Counter64,
                rcIsidEndptStatsStndPirDroppedOctets         Counter64,
                rcIsidEndptStatsName                         DisplayString,
                rcIsidEndptStatsPremTxDroppedOctets          Counter64,       
                rcIsidEndptStatsGoldTxDroppedOctets          Counter64,       
                rcIsidEndptStatsSilverTxDroppedOctets        Counter64,
                rcIsidEndptStatsStndTxDroppedOctets          Counter64,       
                rcIsidEndptStatsPremTxCongestionDropOctets   Counter64,
                rcIsidEndptStatsGoldTxCongestionDropOctets   Counter64,
                rcIsidEndptStatsSilverTxCongestionDropOctets Counter64,      
                rcIsidEndptStatsStndTxCongestionDropOctets   Counter64,      
                rcIsidEndptStatsPremTxCirDroppedOctets       Counter64,
                rcIsidEndptStatsPremTxPirDroppedOctets       Counter64,
                rcIsidEndptStatsGoldTxCirDroppedOctets       Counter64,
                rcIsidEndptStatsGoldTxPirDroppedOctets       Counter64,
                rcIsidEndptStatsSilverTxCirDroppedOctets     Counter64,
                rcIsidEndptStatsSilverTxPirDroppedOctets     Counter64,
                rcIsidEndptStatsStndTxCirDroppedOctets       Counter64,
                rcIsidEndptStatsStndTxPirDroppedOctets       Counter64,
                rcIsidEndptStatsRxMcastTotalOctets           Counter64,
                rcIsidEndptStatsTxMcastTotalOctets           Counter64,
                rcIsidEndptStatsPremRxMcastDroppedOctets     Counter64,
                rcIsidEndptStatsGoldRxMcastDroppedOctets     Counter64,
                rcIsidEndptStatsSilverRxMcastDroppedOctets   Counter64,
                rcIsidEndptStatsStndRxMcastDroppedOctets     Counter64,
		rcIsidEndptStatsPremRxFrames                 Counter64,
                rcIsidEndptStatsPremRxDroppedFrames          Counter64,
                rcIsidEndptStatsGoldRxFrames                 Counter64,
                rcIsidEndptStatsGoldRxDroppedFrames          Counter64,
                rcIsidEndptStatsSilverRxFrames               Counter64,
                rcIsidEndptStatsSilverRxDroppedFrames        Counter64,
                rcIsidEndptStatsStndRxFrames                 Counter64,
                rcIsidEndptStatsStndRxDroppedFrames          Counter64,
                rcIsidEndptStatsPremTxFrames                 Counter64,
                rcIsidEndptStatsGoldTxFrames                 Counter64,
                rcIsidEndptStatsSilverTxFrames               Counter64,
                rcIsidEndptStatsStndTxFrames                 Counter64,
                rcIsidEndptStatsPremTxMcastFrames            Counter64,
                rcIsidEndptStatsGoldTxMcastFrames            Counter64,
                rcIsidEndptStatsSilverTxMcastFrames          Counter64,
                rcIsidEndptStatsStndTxMcastFrames            Counter64,
                rcIsidEndptStatsPremCongestionDropFrames     Counter64,
                rcIsidEndptStatsGoldCongestionDropFrames     Counter64,
                rcIsidEndptStatsSilverCongestionDropFrames   Counter64,
                rcIsidEndptStatsStndCongestionDropFrames     Counter64,
                rcIsidEndptStatsPremCirDroppedFrames         Counter64,
                rcIsidEndptStatsPremPirDroppedFrames         Counter64,
                rcIsidEndptStatsGoldCirDroppedFrames         Counter64,
                rcIsidEndptStatsGoldPirDroppedFrames         Counter64,
                rcIsidEndptStatsSilverCirDroppedFrames       Counter64,
                rcIsidEndptStatsSilverPirDroppedFrames       Counter64,
                rcIsidEndptStatsStndCirDroppedFrames         Counter64,
                rcIsidEndptStatsStndPirDroppedFrames         Counter64,
                rcIsidEndptStatsPremTxDroppedFrames          Counter64,
                rcIsidEndptStatsGoldTxDroppedFrames          Counter64,
                rcIsidEndptStatsSilverTxDroppedFrames        Counter64,
                rcIsidEndptStatsStndTxDroppedFrames          Counter64,
                rcIsidEndptStatsPremTxCongestionDropFrames   Counter64,
                rcIsidEndptStatsGoldTxCongestionDropFrames   Counter64,
                rcIsidEndptStatsSilverTxCongestionDropFrames Counter64,
                rcIsidEndptStatsStndTxCongestionDropFrames   Counter64,
                rcIsidEndptStatsPremTxCirDroppedFrames       Counter64,
                rcIsidEndptStatsPremTxPirDroppedFrames       Counter64,
                rcIsidEndptStatsGoldTxCirDroppedFrames       Counter64,
                rcIsidEndptStatsGoldTxPirDroppedFrames       Counter64,
                rcIsidEndptStatsSilverTxCirDroppedFrames     Counter64,
                rcIsidEndptStatsSilverTxPirDroppedFrames     Counter64,
                rcIsidEndptStatsStndTxCirDroppedFrames       Counter64,
                rcIsidEndptStatsStndTxPirDroppedFrames       Counter64,
                rcIsidEndptStatsRxMcastTotalFrames           Counter64,
                rcIsidEndptStatsTxMcastTotalFrames           Counter64,
                rcIsidEndptStatsPremRxMcastDroppedFrames     Counter64,
                rcIsidEndptStatsGoldRxMcastDroppedFrames     Counter64,
                rcIsidEndptStatsSilverRxMcastDroppedFrames   Counter64,
                rcIsidEndptStatsStndRxMcastDroppedFrames     Counter64,
	rcIsidEndptStatsPremRxCirOctets			Counter64,
	rcIsidEndptStatsPremRxCirOopOctets			Counter64,
	rcIsidEndptStatsPremRxEirOctets			Counter64,
	rcIsidEndptStatsPremRxEirOopOctets			Counter64,
	rcIsidEndptStatsPremRxEirDroppedOctets		Counter64,
	rcIsidEndptStatsPremRxPirOctets			Counter64,
	rcIsidEndptStatsPremRxPirOopOctets			Counter64,
	rcIsidEndptStatsPremRxGreenOctets			Counter64,
	rcIsidEndptStatsPremRxYellowOctets			Counter64,
	rcIsidEndptStatsPremRxRedOctets			Counter64,
	rcIsidEndptStatsGoldRxCirOctets			Counter64,
	rcIsidEndptStatsGoldRxCirOopOctets			Counter64,
	rcIsidEndptStatsGoldRxEirOctets			Counter64,
	rcIsidEndptStatsGoldRxEirOopOctets			Counter64,
	rcIsidEndptStatsGoldRxEirDroppedOctets		Counter64,
	rcIsidEndptStatsGoldRxPirOctets			Counter64,
	rcIsidEndptStatsGoldRxPirOopOctets			Counter64,
	rcIsidEndptStatsGoldRxGreenOctets			Counter64,
	rcIsidEndptStatsGoldRxYellowOctets			Counter64,
	rcIsidEndptStatsGoldRxRedOctets			Counter64,
	rcIsidEndptStatsSilverRxCirOctets			Counter64,
	rcIsidEndptStatsSilverRxCirOopOctets			Counter64,
	rcIsidEndptStatsSilverRxEirOctets			Counter64,
	rcIsidEndptStatsSilverRxEirOopOctets			Counter64,
	rcIsidEndptStatsSilverRxEirDroppedOctets		Counter64,
	rcIsidEndptStatsSilverRxPirOctets			Counter64,
	rcIsidEndptStatsSilverRxPirOopOctets			Counter64,
	rcIsidEndptStatsSilverRxGreenOctets			Counter64,
	rcIsidEndptStatsSilverRxYellowOctets			Counter64,
	rcIsidEndptStatsSilverRxRedOctets			Counter64,
	rcIsidEndptStatsStndRxCirOctets			Counter64,
	rcIsidEndptStatsStndRxCirOopOctets			Counter64,
	rcIsidEndptStatsStndRxEirOctets			Counter64,
	rcIsidEndptStatsStndRxEirOopOctets			Counter64,
	rcIsidEndptStatsStndRxEirDroppedOctets		Counter64,
	rcIsidEndptStatsStndRxPirOctets			Counter64,
	rcIsidEndptStatsStndRxPirOopOctets			Counter64,
	rcIsidEndptStatsStndRxGreenOctets			Counter64,
	rcIsidEndptStatsStndRxYellowOctets			Counter64,
	rcIsidEndptStatsStndRxRedOctets			Counter64,
	rcIsidEndptStatsMcastRxDroppedOctets			Counter64,
	rcIsidEndptStatsBcastUUcastRxTotalOctets		Counter64,
	rcIsidEndptStatsBcastUUcastRxDroppedOctets		Counter64,
	rcIsidEndptStatsPremRxCirFrames			Counter64,
	rcIsidEndptStatsPremRxCirOopFrames			Counter64,
	rcIsidEndptStatsPremRxEirFrames			Counter64,
	rcIsidEndptStatsPremRxEirOopFrames			Counter64,
	rcIsidEndptStatsPremRxEirDroppedFrames		Counter64,
	rcIsidEndptStatsPremRxPirFrames			Counter64,
	rcIsidEndptStatsPremRxPirOopFrames			Counter64,
	rcIsidEndptStatsPremRxGreenFrames			Counter64,
	rcIsidEndptStatsPremRxYellowFrames			Counter64,
	rcIsidEndptStatsPremRxRedFrames			Counter64,
	rcIsidEndptStatsGoldRxCirFrames			Counter64,
	rcIsidEndptStatsGoldRxCirOopFrames			Counter64,
	rcIsidEndptStatsGoldRxEirFrames			Counter64,
	rcIsidEndptStatsGoldRxEirOopFrames			Counter64,
	rcIsidEndptStatsGoldRxEirDroppedFrames		Counter64,
	rcIsidEndptStatsGoldRxPirFrames			Counter64,
	rcIsidEndptStatsGoldRxPirOopFrames			Counter64,
	rcIsidEndptStatsGoldRxGreenFrames			Counter64,
	rcIsidEndptStatsGoldRxYellowFrames			Counter64,
	rcIsidEndptStatsGoldRxRedFrames			Counter64,
	rcIsidEndptStatsSilverRxCirFrames			Counter64,
	rcIsidEndptStatsSilverRxCirOopFrames			Counter64,
	rcIsidEndptStatsSilverRxEirFrames			Counter64,
	rcIsidEndptStatsSilverRxEirOopFrames			Counter64,
	rcIsidEndptStatsSilverRxEirDroppedFrames		Counter64,
	rcIsidEndptStatsSilverRxPirFrames			Counter64,
	rcIsidEndptStatsSilverRxPirOopFrames			Counter64,
	rcIsidEndptStatsSilverRxGreenFrames			Counter64,
	rcIsidEndptStatsSilverRxYellowFrames			Counter64,
	rcIsidEndptStatsSilverRxRedFrames			Counter64,
	rcIsidEndptStatsStndRxCirFrames			Counter64,
	rcIsidEndptStatsStndRxCirOopFrames			Counter64,
	rcIsidEndptStatsStndRxEirFrames			Counter64,
	rcIsidEndptStatsStndRxEirOopFrames			Counter64,
	rcIsidEndptStatsStndRxEirDroppedFrames		Counter64,
	rcIsidEndptStatsStndRxPirFrames			Counter64,
	rcIsidEndptStatsStndRxPirOopFrames			Counter64,
	rcIsidEndptStatsStndRxGreenFrames			Counter64,
	rcIsidEndptStatsStndRxYellowFrames			Counter64,
	rcIsidEndptStatsStndRxRedFrames			Counter64,
	rcIsidEndptStatsMcastRxDroppedFrames			Counter64,
	rcIsidEndptStatsBcastUUcastRxTotalFrames		Counter64,
	rcIsidEndptStatsBcastUUcastRxDroppedFrames		Counter64,
	rcIsidEndptStatsPremTxCirOctets			Counter64,
	rcIsidEndptStatsPremTxCirOopOctets			Counter64,
	rcIsidEndptStatsPremTxEirOctets			Counter64,
	rcIsidEndptStatsPremTxEirOopOctets			Counter64,
	rcIsidEndptStatsPremTxEirDroppedOctets		Counter64,
	rcIsidEndptStatsPremTxPirOctets			Counter64,
	rcIsidEndptStatsPremTxPirOopOctets			Counter64,
	rcIsidEndptStatsPremTxGreenOctets			Counter64,
	rcIsidEndptStatsPremTxYellowOctets			Counter64,
	rcIsidEndptStatsPremTxRedOctets			Counter64,
	rcIsidEndptStatsGoldTxCirOctets			Counter64,
	rcIsidEndptStatsGoldTxCirOopOctets			Counter64,
	rcIsidEndptStatsGoldTxEirOctets			Counter64,
	rcIsidEndptStatsGoldTxEirOopOctets			Counter64,
	rcIsidEndptStatsGoldTxEirDroppedOctets			Counter64,
	rcIsidEndptStatsGoldTxPirOctets			Counter64,
	rcIsidEndptStatsGoldTxPirOopOctets			Counter64,
	rcIsidEndptStatsGoldTxGreenOctets			Counter64,
	rcIsidEndptStatsGoldTxYellowOctets			Counter64,
	rcIsidEndptStatsGoldTxRedOctets			Counter64,
	rcIsidEndptStatsSilverTxCirOctets			Counter64,
	rcIsidEndptStatsSilverTxCirOopOctets			Counter64,
	rcIsidEndptStatsSilverTxEirOctets			Counter64,
	rcIsidEndptStatsSilverTxEirOopOctets			Counter64,
	rcIsidEndptStatsSilverTxEirDroppedOctets		Counter64,
	rcIsidEndptStatsSilverTxPirOctets			Counter64,
	rcIsidEndptStatsSilverTxPirOopOctets			Counter64,
	rcIsidEndptStatsSilverTxGreenOctets			Counter64,
	rcIsidEndptStatsSilverTxYellowOctets			Counter64,
	rcIsidEndptStatsSilverTxRedOctets			Counter64,
	rcIsidEndptStatsStndTxCirOctets			Counter64,
	rcIsidEndptStatsStndTxCirOopOctets			Counter64,
	rcIsidEndptStatsStndTxEirOctets			Counter64,
	rcIsidEndptStatsStndTxEirOopOctets			Counter64,
	rcIsidEndptStatsStndTxEirDroppedOctets			Counter64,
	rcIsidEndptStatsStndTxPirOctets			Counter64,
	rcIsidEndptStatsStndTxPirOopOctets			Counter64,
	rcIsidEndptStatsStndTxGreenOctets			Counter64,
	rcIsidEndptStatsStndTxYellowOctets			Counter64,
	rcIsidEndptStatsStndTxRedOctets			Counter64,
	rcIsidEndptStatsMcastTxDroppedOctets			Counter64,
	rcIsidEndptStatsBcastUUcastTxTotalOctets		Counter64,
	rcIsidEndptStatsBcastUUcastTxDroppedOctets		Counter64,
	rcIsidEndptStatsPremTxCirFrames			Counter64,
	rcIsidEndptStatsPremTxCirOopFrames			Counter64,
	rcIsidEndptStatsPremTxEirFrames			Counter64,
	rcIsidEndptStatsPremTxEirOopFrames			Counter64,
	rcIsidEndptStatsPremTxEirDroppedFrames		Counter64,
	rcIsidEndptStatsPremTxPirFrames			Counter64,
	rcIsidEndptStatsPremTxPirOopFrames			Counter64,
	rcIsidEndptStatsPremTxGreenFrames			Counter64,
	rcIsidEndptStatsPremTxYellowFrames			Counter64,
	rcIsidEndptStatsPremTxRedFrames			Counter64,
	rcIsidEndptStatsGoldTxCirFrames			Counter64,
	rcIsidEndptStatsGoldTxCirOopFrames			Counter64,
	rcIsidEndptStatsGoldTxEirFrames			Counter64,
	rcIsidEndptStatsGoldTxEirOopFrames			Counter64,
	rcIsidEndptStatsGoldTxEirDroppedFrames		Counter64,
	rcIsidEndptStatsGoldTxPirFrames			Counter64,
	rcIsidEndptStatsGoldTxPirOopFrames			Counter64,
	rcIsidEndptStatsGoldTxGreenFrames			Counter64,
	rcIsidEndptStatsGoldTxYellowFrames			Counter64,
	rcIsidEndptStatsGoldTxRedFrames			Counter64,
	rcIsidEndptStatsSilverTxCirFrames			Counter64,
	rcIsidEndptStatsSilverTxCirOopFrames			Counter64,
	rcIsidEndptStatsSilverTxEirFrames			Counter64,
	rcIsidEndptStatsSilverTxEirOopFrames			Counter64,
	rcIsidEndptStatsSilverTxEirDroppedFrames		Counter64,
	rcIsidEndptStatsSilverTxPirFrames			Counter64,
	rcIsidEndptStatsSilverTxPirOopFrames			Counter64,
	rcIsidEndptStatsSilverTxGreenFrames			Counter64,
	rcIsidEndptStatsSilverTxYellowFrames			Counter64,
	rcIsidEndptStatsSilverTxRedFrames			Counter64,
	rcIsidEndptStatsStndTxCirFrames			Counter64,
	rcIsidEndptStatsStndTxCirOopFrames			Counter64,
	rcIsidEndptStatsStndTxEirFrames			Counter64,
	rcIsidEndptStatsStndTxEirOopFrames			Counter64,
	rcIsidEndptStatsStndTxEirDroppedFrames		Counter64,
	rcIsidEndptStatsStndTxPirFrames			Counter64,
	rcIsidEndptStatsStndTxPirOopFrames			Counter64,
	rcIsidEndptStatsStndTxGreenFrames			Counter64,
	rcIsidEndptStatsStndTxYellowFrames			Counter64,
	rcIsidEndptStatsStndTxRedFrames			Counter64,
	rcIsidEndptStatsMcastTxDroppedFrames			Counter64,
	rcIsidEndptStatsBcastUUcastTxTotalFrames		Counter64,
	rcIsidEndptStatsBcastUUcastTxDroppedFrames		Counter64,
       	 rcIsidEndptStatsCfmIngRtLimitPassedFrames              	Counter64,
       	 rcIsidEndptStatsCfmIngRtLimitDroppedFrames             	Counter64,
        	rcIsidEndptStatsCfmEgrRtLimitPassedFrames               	Counter64,
       	 rcIsidEndptStatsCfmEgrRtLimitDroppedFrames             	Counter64,
	rcIsidEndptStatsDropClassRxDroppedOctets  		Counter64,
	rcIsidEndptStatsDropClassRxDroppedFrames  		Counter64,
	rcIsidEndptStatsDropClassTxDroppedOctets  		Counter64,
	rcIsidEndptStatsDropClassTxDroppedFrames  		Counter64
      }

rcIsidEndptStatsIsidId OBJECT-TYPE
        SYNTAX        INTEGER (1..16777215)
        MAX-ACCESS    not-accessible
        STATUS        current
        DESCRIPTION   "Isid that the end-point is a member of."
        ::= { rcIsidEndptStatsEntry 1 }

rcIsidEndptStatsTlsIndex OBJECT-TYPE
        SYNTAX        INTEGER (1..2147483647)
        MAX-ACCESS    not-accessible
        STATUS        current
        DESCRIPTION   "TLS Index"
        ::= { rcIsidEndptStatsEntry 2 }

rcIsidEndptStatsPort OBJECT-TYPE
        SYNTAX        InterfaceIndex
        MAX-ACCESS    read-only
        STATUS        current
        DESCRIPTION   "Port Identifier."
        ::= { rcIsidEndptStatsEntry 3 }
 
rcIsidEndptStatsPremRxOctets        OBJECT-TYPE
        SYNTAX        Counter64
        MAX-ACCESS    read-only
        STATUS        current
        DESCRIPTION  "Number of Premium Service Octets received."
        ::= { rcIsidEndptStatsEntry 4 } 

rcIsidEndptStatsPremRxDroppedOctets OBJECT-TYPE
        SYNTAX        Counter64
        MAX-ACCESS    read-only
        STATUS        current
        DESCRIPTION  "Number of Premium Service Octets dropped."
        ::= { rcIsidEndptStatsEntry 5 } 
       
rcIsidEndptStatsGoldRxOctets        OBJECT-TYPE
        SYNTAX        Counter64
        MAX-ACCESS    read-only
        STATUS        current
        DESCRIPTION  "Number of Gold Service Octets received."
        ::= { rcIsidEndptStatsEntry 6 } 

rcIsidEndptStatsGoldRxDroppedOctets OBJECT-TYPE
        SYNTAX        Counter64
        MAX-ACCESS    read-only
        STATUS        current
        DESCRIPTION  "Number of Gold Service Octets dropped."
        ::= { rcIsidEndptStatsEntry 7 } 
       
rcIsidEndptStatsSilverRxOctets      OBJECT-TYPE
        SYNTAX        Counter64
        MAX-ACCESS    read-only
        STATUS        current
        DESCRIPTION  "Number of Silver Service Octets received."
        ::= { rcIsidEndptStatsEntry 8 } 

rcIsidEndptStatsSilverRxDroppedOctets       OBJECT-TYPE
        SYNTAX        Counter64
        MAX-ACCESS    read-only
        STATUS        current
        DESCRIPTION  "Number of Silver Service Octets dropped."
        ::= { rcIsidEndptStatsEntry 9 } 
       
rcIsidEndptStatsStndRxOctets        OBJECT-TYPE
        SYNTAX        Counter64
        MAX-ACCESS    read-only
        STATUS        current
        DESCRIPTION  "Number of Standard Service Octets received."
        ::= { rcIsidEndptStatsEntry 10 } 

rcIsidEndptStatsStndRxDroppedOctets OBJECT-TYPE
        SYNTAX        Counter64
        MAX-ACCESS    read-only
        STATUS        current
        DESCRIPTION  "Number of Standard Service Octets dropped."
        ::= { rcIsidEndptStatsEntry 11 } 
       
rcIsidEndptStatsPremTxOctets        OBJECT-TYPE
        SYNTAX        Counter64
        MAX-ACCESS    read-only
        STATUS        current
        DESCRIPTION  "Number of Premium Service Octets sent."
        ::= { rcIsidEndptStatsEntry 12 } 

rcIsidEndptStatsGoldTxOctets        OBJECT-TYPE
        SYNTAX        Counter64
        MAX-ACCESS    read-only
        STATUS        current
        DESCRIPTION  "Number of Gold Service Octets sent."
        ::= { rcIsidEndptStatsEntry 13 } 

rcIsidEndptStatsSilverTxOctets      OBJECT-TYPE
        SYNTAX        Counter64
        MAX-ACCESS    read-only
        STATUS        current
        DESCRIPTION  "Number of Silver Service Octets sent."
        ::= { rcIsidEndptStatsEntry 14 } 

rcIsidEndptStatsStndTxOctets        OBJECT-TYPE
        SYNTAX        Counter64
        MAX-ACCESS    read-only
        STATUS        current
        DESCRIPTION  "Number of Standard Service Octets sent."
        ::= { rcIsidEndptStatsEntry 15 } 
                

rcIsidEndptStatsPremTxMcastOctets   OBJECT-TYPE
        SYNTAX        Counter64
        MAX-ACCESS    read-only
        STATUS        current
        DESCRIPTION  "Number of Premium Service Multicast sent."
        ::= { rcIsidEndptStatsEntry 16 } 

rcIsidEndptStatsGoldTxMcastOctets    OBJECT-TYPE
        SYNTAX        Counter64
        MAX-ACCESS    read-only
        STATUS        current
        DESCRIPTION  "Number of GoldService Multicast sent."
        ::= { rcIsidEndptStatsEntry 17 } 
                
rcIsidEndptStatsSilverTxMcastOctets  OBJECT-TYPE
        SYNTAX        Counter64
        MAX-ACCESS    read-only
        STATUS        current
        DESCRIPTION  "Number of SilverService Multicast sent."
        ::= { rcIsidEndptStatsEntry 18 } 

rcIsidEndptStatsStndTxMcastOctets    OBJECT-TYPE
        SYNTAX        Counter64
        MAX-ACCESS    read-only
        STATUS        current 
        DESCRIPTION  "Number of Premium Service Multicast sent."
        ::= { rcIsidEndptStatsEntry 19     } 

rcIsidEndptStatsPremCongestionDropOctets     OBJECT-TYPE
        SYNTAX        Counter64
        MAX-ACCESS    read-only
        STATUS        current
        DESCRIPTION  "Number of Prem Service Octets congestion dropped."
        ::= { rcIsidEndptStatsEntry 20 } 
       
rcIsidEndptStatsGoldCongestionDropOctets     OBJECT-TYPE
        SYNTAX        Counter64
        MAX-ACCESS    read-only
        STATUS        current
        DESCRIPTION  "Number of Gold Service Octets congestion dropped."
        ::= { rcIsidEndptStatsEntry 21 } 

rcIsidEndptStatsSilverCongestionDropOctets   OBJECT-TYPE
        SYNTAX        Counter64
        MAX-ACCESS    read-only
        STATUS        current
        DESCRIPTION  "Number of Silver Service Octets congestion dropped."
        ::= { rcIsidEndptStatsEntry 22 } 

rcIsidEndptStatsStndCongestionDropOctets     OBJECT-TYPE
        SYNTAX        Counter64
        MAX-ACCESS    read-only
        STATUS        current
        DESCRIPTION  "Number of Standard Service Octets congestion dropped."
        ::= { rcIsidEndptStatsEntry 23 }

rcIsidEndptStatsPremCirDroppedOctets OBJECT-TYPE
        SYNTAX        Counter64
        MAX-ACCESS    read-only
        STATUS        current
        DESCRIPTION  "Number of Prem Service Octets CIR dropped."
        ::= { rcIsidEndptStatsEntry 24 }

rcIsidEndptStatsPremPirDroppedOctets OBJECT-TYPE
        SYNTAX        Counter64
        MAX-ACCESS    read-only
        STATUS        current
        DESCRIPTION  "Number of Prem Service Octets PIR dropped."
        ::= { rcIsidEndptStatsEntry 25 }
  
rcIsidEndptStatsGoldCirDroppedOctets OBJECT-TYPE
        SYNTAX        Counter64
        MAX-ACCESS    read-only
        STATUS        current
        DESCRIPTION  "Number of Gold Service Octets CIR dropped."
        ::= { rcIsidEndptStatsEntry 26 }

rcIsidEndptStatsGoldPirDroppedOctets OBJECT-TYPE
        SYNTAX        Counter64
        MAX-ACCESS    read-only
        STATUS        current
        DESCRIPTION  "Number of Gold Service Octets PIR dropped."
        ::= { rcIsidEndptStatsEntry 27 }

rcIsidEndptStatsSilverCirDroppedOctets       OBJECT-TYPE
        SYNTAX        Counter64
        MAX-ACCESS    read-only
        STATUS        current
        DESCRIPTION  "Number of Silver Service Octets CIR dropped."
        ::= { rcIsidEndptStatsEntry 28 }

rcIsidEndptStatsSilverPirDroppedOctets       OBJECT-TYPE
        SYNTAX        Counter64
        MAX-ACCESS    read-only
        STATUS        current
        DESCRIPTION  "Number of Silver Service Octets PIR dropped."
        ::= { rcIsidEndptStatsEntry 29 }

rcIsidEndptStatsStndCirDroppedOctets OBJECT-TYPE
        SYNTAX        Counter64
        MAX-ACCESS    read-only
        STATUS        current
        DESCRIPTION  "Number of Standard Service Octets CIR dropped."
        ::= { rcIsidEndptStatsEntry 30 }  

rcIsidEndptStatsStndPirDroppedOctets OBJECT-TYPE
        SYNTAX        Counter64
        MAX-ACCESS    read-only
        STATUS        current
        DESCRIPTION  "Number of Standard Service Octets PIR dropped."
        ::= { rcIsidEndptStatsEntry 31 } 
 
rcIsidEndptStatsName OBJECT-TYPE
        SYNTAX        DisplayString (SIZE (0..30)) 
        MAX-ACCESS    read-only
        STATUS        current
        DESCRIPTION   "Name of Endpoint."
        ::= { rcIsidEndptStatsEntry 32 }

rcIsidEndptStatsPremTxDroppedOctets  OBJECT-TYPE
        SYNTAX        Counter64
        MAX-ACCESS    read-only
        STATUS        current
        DESCRIPTION  "Tx Number of Premium Service Octets dropped."
        ::= { rcIsidEndptStatsEntry 33 } 

rcIsidEndptStatsGoldTxDroppedOctets  OBJECT-TYPE
        SYNTAX        Counter64
        MAX-ACCESS    read-only
        STATUS        current
        DESCRIPTION  "Tx Number of Gold Service Octets dropped."
        ::= { rcIsidEndptStatsEntry 34 } 
       
rcIsidEndptStatsSilverTxDroppedOctets        OBJECT-TYPE
        SYNTAX        Counter64
        MAX-ACCESS    read-only
        STATUS        current
        DESCRIPTION  "Tx Number of Silver Service Octets dropped."
        ::= { rcIsidEndptStatsEntry 35 } 
       
rcIsidEndptStatsStndTxDroppedOctets  OBJECT-TYPE
        SYNTAX        Counter64
        MAX-ACCESS    read-only
        STATUS        current
        DESCRIPTION  "Tx Number of Standard Service Octets dropped."
        ::= { rcIsidEndptStatsEntry 36 } 

rcIsidEndptStatsPremTxCongestionDropOctets   OBJECT-TYPE
        SYNTAX        Counter64
        MAX-ACCESS    read-only
        STATUS        current
        DESCRIPTION  "Tx Number of Prem Service Octets congestion dropped."
        ::= { rcIsidEndptStatsEntry 37 } 
       
rcIsidEndptStatsGoldTxCongestionDropOctets   OBJECT-TYPE
        SYNTAX        Counter64
        MAX-ACCESS    read-only
        STATUS        current
        DESCRIPTION  "Tx Number of Gold Service Octets congestion dropped."
        ::= { rcIsidEndptStatsEntry 38 } 

rcIsidEndptStatsSilverTxCongestionDropOctets OBJECT-TYPE
        SYNTAX        Counter64
        MAX-ACCESS    read-only
        STATUS        current
        DESCRIPTION  "Tx Number of Silver Service Octets congestion dropped."
        ::= { rcIsidEndptStatsEntry 39 } 

rcIsidEndptStatsStndTxCongestionDropOctets   OBJECT-TYPE
        SYNTAX        Counter64
        MAX-ACCESS    read-only
        STATUS        current
        DESCRIPTION  "Tx Number of Standard Service Octets congestion dropped."
        ::= { rcIsidEndptStatsEntry 40 }

rcIsidEndptStatsPremTxCirDroppedOctets       OBJECT-TYPE
        SYNTAX        Counter64
        MAX-ACCESS    read-only
        STATUS        current
        DESCRIPTION  "Tx Number of Prem Service Octets CIR dropped."
        ::= { rcIsidEndptStatsEntry 41 }

rcIsidEndptStatsPremTxPirDroppedOctets       OBJECT-TYPE
        SYNTAX        Counter64
        MAX-ACCESS    read-only
        STATUS        current
        DESCRIPTION  "Tx Number of Prem Service Octets PIR dropped."
        ::= { rcIsidEndptStatsEntry 42 }
  
rcIsidEndptStatsGoldTxCirDroppedOctets       OBJECT-TYPE
        SYNTAX        Counter64
        MAX-ACCESS    read-only
        STATUS        current
        DESCRIPTION  "Tx Number of Gold Service Octets CIR dropped."
        ::= { rcIsidEndptStatsEntry 43 }

rcIsidEndptStatsGoldTxPirDroppedOctets       OBJECT-TYPE
        SYNTAX        Counter64
        MAX-ACCESS    read-only
        STATUS        current
        DESCRIPTION  "Tx Number of Gold Service Octets PIR dropped."
        ::= { rcIsidEndptStatsEntry 44 }

rcIsidEndptStatsSilverTxCirDroppedOctets     OBJECT-TYPE
        SYNTAX        Counter64
        MAX-ACCESS    read-only
        STATUS        current
        DESCRIPTION  "Tx Number of Silver Service Octets CIR dropped."
        ::= { rcIsidEndptStatsEntry 45 }

rcIsidEndptStatsSilverTxPirDroppedOctets     OBJECT-TYPE
        SYNTAX        Counter64
        MAX-ACCESS    read-only
        STATUS        current
        DESCRIPTION  "Tx Number of Silver Service Octets PIR dropped."
        ::= { rcIsidEndptStatsEntry 46 }

rcIsidEndptStatsStndTxCirDroppedOctets       OBJECT-TYPE
        SYNTAX        Counter64
        MAX-ACCESS    read-only
        STATUS        current
        DESCRIPTION  "Tx Number of Standard Service Octets CIR dropped."
        ::= { rcIsidEndptStatsEntry 47 }  

rcIsidEndptStatsStndTxPirDroppedOctets       OBJECT-TYPE
        SYNTAX        Counter64
        MAX-ACCESS    read-only
        STATUS        current
        DESCRIPTION  "TX Number of Standard Service Octets PIR dropped."
        ::= { rcIsidEndptStatsEntry 48 }
 
rcIsidEndptStatsRxMcastTotalOctets   OBJECT-TYPE
        SYNTAX        Counter64
        MAX-ACCESS    read-only
        STATUS        current
        DESCRIPTION  "Rx Total Number of Mcast Octets"
        ::= { rcIsidEndptStatsEntry 49 }
 
rcIsidEndptStatsTxMcastTotalOctets   OBJECT-TYPE
        SYNTAX        Counter64
        MAX-ACCESS    read-only
        STATUS        current
        DESCRIPTION  "TX total Number of Mcast Octets"
        ::= { rcIsidEndptStatsEntry 50 } 
rcIsidEndptStatsPremRxMcastDroppedOctets     OBJECT-TYPE
        SYNTAX        Counter64
        MAX-ACCESS    read-only
        STATUS        current
        DESCRIPTION  "Number of Premium Service Rx Mcast Octets dropped."
        ::= { rcIsidEndptStatsEntry 51 } 

rcIsidEndptStatsGoldRxMcastDroppedOctets     OBJECT-TYPE
        SYNTAX        Counter64
        MAX-ACCESS    read-only
        STATUS        current
        DESCRIPTION  "Number of Gold Service Rx Mcast Octets dropped."
        ::= { rcIsidEndptStatsEntry 52 } 

rcIsidEndptStatsSilverRxMcastDroppedOctets   OBJECT-TYPE
        SYNTAX        Counter64
        MAX-ACCESS    read-only
        STATUS        current
        DESCRIPTION  "Number of Silver Service Rx Mcast Octets dropped."
        ::= { rcIsidEndptStatsEntry 53 } 
                            
rcIsidEndptStatsStndRxMcastDroppedOctets     OBJECT-TYPE
        SYNTAX        Counter64
        MAX-ACCESS    read-only
        STATUS        current
        DESCRIPTION  "Number of Standard Service Rx Mcast Octets dropped."
        ::= { rcIsidEndptStatsEntry 54 } 
rcIsidEndptStatsPremRxFrames        OBJECT-TYPE
        SYNTAX        Counter64
        MAX-ACCESS    read-only
        STATUS        current
        DESCRIPTION  "Number of Premium Service Frames received."
        ::= { rcIsidEndptStatsEntry 55 }

rcIsidEndptStatsPremRxDroppedFrames OBJECT-TYPE
        SYNTAX        Counter64
        MAX-ACCESS    read-only
        STATUS        current
        DESCRIPTION  "Number of Premium Service Frames dropped."
        ::= { rcIsidEndptStatsEntry 56 }

rcIsidEndptStatsGoldRxFrames        OBJECT-TYPE
        SYNTAX        Counter64
        MAX-ACCESS    read-only
        STATUS        current
        DESCRIPTION  "Number of Gold Service Frames received."
        ::= { rcIsidEndptStatsEntry 57 }

rcIsidEndptStatsGoldRxDroppedFrames OBJECT-TYPE
        SYNTAX        Counter64
        MAX-ACCESS    read-only
        STATUS        current
        DESCRIPTION  "Number of Gold Service Frames dropped."
        ::= { rcIsidEndptStatsEntry 58 }

rcIsidEndptStatsSilverRxFrames      OBJECT-TYPE
        SYNTAX        Counter64
        MAX-ACCESS    read-only
        STATUS        current
        DESCRIPTION  "Number of Silver Service Frames received."
        ::= { rcIsidEndptStatsEntry 59 }

rcIsidEndptStatsSilverRxDroppedFrames       OBJECT-TYPE
        SYNTAX        Counter64
        MAX-ACCESS    read-only
        STATUS        current
        DESCRIPTION  "Number of Silver Service Frames dropped."
        ::= { rcIsidEndptStatsEntry 60 }

rcIsidEndptStatsStndRxFrames        OBJECT-TYPE
        SYNTAX        Counter64
        MAX-ACCESS    read-only
        STATUS        current
        DESCRIPTION  "Number of Standard Service Frames received."
        ::= { rcIsidEndptStatsEntry 61 }

rcIsidEndptStatsStndRxDroppedFrames OBJECT-TYPE
        SYNTAX        Counter64
        MAX-ACCESS    read-only
        STATUS        current
        DESCRIPTION  "Number of Standard Service Frames dropped."
        ::= { rcIsidEndptStatsEntry 62 }

rcIsidEndptStatsPremTxFrames        OBJECT-TYPE
        SYNTAX        Counter64
        MAX-ACCESS    read-only
        STATUS        current
        DESCRIPTION  "Number of Premium Service Frames sent."
        ::= { rcIsidEndptStatsEntry 63 }

rcIsidEndptStatsGoldTxFrames        OBJECT-TYPE
        SYNTAX        Counter64
        MAX-ACCESS    read-only
        STATUS        current
        DESCRIPTION  "Number of Gold Service Frames sent."
        ::= { rcIsidEndptStatsEntry 64 }

rcIsidEndptStatsSilverTxFrames      OBJECT-TYPE
        SYNTAX        Counter64
        MAX-ACCESS    read-only
        STATUS        current
        DESCRIPTION  "Number of Silver Service Frames sent."
        ::= { rcIsidEndptStatsEntry 65 }

rcIsidEndptStatsStndTxFrames        OBJECT-TYPE
        SYNTAX        Counter64
        MAX-ACCESS    read-only
        STATUS        current
        DESCRIPTION  "Number of Standard Service Frames sent."
        ::= { rcIsidEndptStatsEntry 66 }

rcIsidEndptStatsPremTxMcastFrames   OBJECT-TYPE
        SYNTAX        Counter64
        MAX-ACCESS    read-only
        STATUS        current
        DESCRIPTION  "Number of Premium Service Multicast sent."
        ::= { rcIsidEndptStatsEntry 67 }

rcIsidEndptStatsGoldTxMcastFrames    OBJECT-TYPE
        SYNTAX        Counter64
        MAX-ACCESS    read-only
        STATUS        current
        DESCRIPTION  "Number of GoldService Multicast sent."
        ::= { rcIsidEndptStatsEntry 68 }

rcIsidEndptStatsSilverTxMcastFrames  OBJECT-TYPE
        SYNTAX        Counter64
        MAX-ACCESS    read-only
        STATUS        current
        DESCRIPTION  "Number of SilverService Multicast sent."
        ::= { rcIsidEndptStatsEntry 69 }

rcIsidEndptStatsStndTxMcastFrames    OBJECT-TYPE
        SYNTAX        Counter64
        MAX-ACCESS    read-only
        STATUS        current
        DESCRIPTION  "Number of Premium Service Multicast sent."
        ::= { rcIsidEndptStatsEntry 70 }

rcIsidEndptStatsPremCongestionDropFrames     OBJECT-TYPE
        SYNTAX        Counter64
        MAX-ACCESS    read-only
        STATUS        current
        DESCRIPTION  "Number of Prem Service Frames congestion dropped."
        ::= { rcIsidEndptStatsEntry 71 }

rcIsidEndptStatsGoldCongestionDropFrames     OBJECT-TYPE
        SYNTAX        Counter64
        MAX-ACCESS    read-only
        STATUS        current
        DESCRIPTION  "Number of Gold Service Frames congestion dropped."
        ::= { rcIsidEndptStatsEntry 72 }

rcIsidEndptStatsSilverCongestionDropFrames   OBJECT-TYPE
        SYNTAX        Counter64
        MAX-ACCESS    read-only
        STATUS        current
        DESCRIPTION  "Number of Silver Service Frames congestion dropped."
        ::= { rcIsidEndptStatsEntry 73 }

rcIsidEndptStatsStndCongestionDropFrames     OBJECT-TYPE
        SYNTAX        Counter64
        MAX-ACCESS    read-only
        STATUS        current
        DESCRIPTION  "Number of Standard Service Frames congestion dropped."
        ::= { rcIsidEndptStatsEntry 74 }

rcIsidEndptStatsPremCirDroppedFrames OBJECT-TYPE
        SYNTAX        Counter64
        MAX-ACCESS    read-only
        STATUS        current
        DESCRIPTION  "Number of Prem Service Frames CIR dropped."
        ::= { rcIsidEndptStatsEntry 75 }

rcIsidEndptStatsPremPirDroppedFrames OBJECT-TYPE
        SYNTAX        Counter64
        MAX-ACCESS    read-only
        STATUS        current
        DESCRIPTION  "Number of Prem Service Frames PIR dropped."
        ::= { rcIsidEndptStatsEntry 76 }

rcIsidEndptStatsGoldCirDroppedFrames OBJECT-TYPE
        SYNTAX        Counter64
        MAX-ACCESS    read-only
        STATUS        current
        DESCRIPTION  "Number of Gold Service Frames CIR dropped."
        ::= { rcIsidEndptStatsEntry 77 }

rcIsidEndptStatsGoldPirDroppedFrames OBJECT-TYPE
        SYNTAX        Counter64
        MAX-ACCESS    read-only
        STATUS        current
        DESCRIPTION  "Number of Gold Service Frames PIR dropped."
        ::= { rcIsidEndptStatsEntry 78 }

rcIsidEndptStatsSilverCirDroppedFrames       OBJECT-TYPE
        SYNTAX        Counter64
        MAX-ACCESS    read-only
        STATUS        current
        DESCRIPTION  "Number of Silver Service Frames CIR dropped."
        ::= { rcIsidEndptStatsEntry 79 }

rcIsidEndptStatsSilverPirDroppedFrames       OBJECT-TYPE
        SYNTAX        Counter64
        MAX-ACCESS    read-only
        STATUS        current
        DESCRIPTION  "Number of Silver Service Frames PIR dropped."
        ::= { rcIsidEndptStatsEntry 80 }

rcIsidEndptStatsStndCirDroppedFrames OBJECT-TYPE
        SYNTAX        Counter64
        MAX-ACCESS    read-only
        STATUS        current
        DESCRIPTION  "Number of Standard Service Frames CIR dropped."
        ::= { rcIsidEndptStatsEntry 81 }

rcIsidEndptStatsStndPirDroppedFrames OBJECT-TYPE
        SYNTAX        Counter64
        MAX-ACCESS    read-only
        STATUS        current
        DESCRIPTION  "Number of Standard Service Frames PIR dropped."
        ::= { rcIsidEndptStatsEntry 82 }

rcIsidEndptStatsPremTxDroppedFrames  OBJECT-TYPE
        SYNTAX        Counter64
        MAX-ACCESS    read-only
        STATUS        current
        DESCRIPTION  "Tx Number of Premium Service Frames dropped."
        ::= { rcIsidEndptStatsEntry 83 }

rcIsidEndptStatsGoldTxDroppedFrames  OBJECT-TYPE
        SYNTAX        Counter64
        MAX-ACCESS    read-only
        STATUS        current
        DESCRIPTION  "Tx Number of Gold Service Frames dropped."
        ::= { rcIsidEndptStatsEntry 84 }

rcIsidEndptStatsSilverTxDroppedFrames        OBJECT-TYPE
        SYNTAX        Counter64
        MAX-ACCESS    read-only
        STATUS        current
        DESCRIPTION  "Tx Number of Silver Service Frames dropped."
        ::= { rcIsidEndptStatsEntry 85 }

rcIsidEndptStatsStndTxDroppedFrames  OBJECT-TYPE
        SYNTAX        Counter64
        MAX-ACCESS    read-only
        STATUS        current
        DESCRIPTION  "Tx Number of Standard Service Frames dropped."
        ::= { rcIsidEndptStatsEntry 86 }

rcIsidEndptStatsPremTxCongestionDropFrames   OBJECT-TYPE
        SYNTAX        Counter64
        MAX-ACCESS    read-only
        STATUS        current
        DESCRIPTION  "Tx Number of Prem Service Frames congestion dropped."
        ::= { rcIsidEndptStatsEntry 87 }

rcIsidEndptStatsGoldTxCongestionDropFrames   OBJECT-TYPE
        SYNTAX        Counter64
        MAX-ACCESS    read-only
        STATUS        current
        DESCRIPTION  "Tx Number of Gold Service Frames congestion dropped."
        ::= { rcIsidEndptStatsEntry 88 }

rcIsidEndptStatsSilverTxCongestionDropFrames OBJECT-TYPE
        SYNTAX        Counter64
        MAX-ACCESS    read-only
        STATUS        current
        DESCRIPTION  "Tx Number of Silver Service Frames congestion dropped."
        ::= { rcIsidEndptStatsEntry 89 }

rcIsidEndptStatsStndTxCongestionDropFrames   OBJECT-TYPE
        SYNTAX        Counter64
        MAX-ACCESS    read-only
        STATUS        current
        DESCRIPTION  "Tx Number of Standard Service Frames congestion dropped."
        ::= { rcIsidEndptStatsEntry 90 }

rcIsidEndptStatsPremTxCirDroppedFrames       OBJECT-TYPE
        SYNTAX        Counter64
        MAX-ACCESS    read-only
        STATUS        current
        DESCRIPTION  "Tx Number of Prem Service Frames CIR dropped."
        ::= { rcIsidEndptStatsEntry 91 }

rcIsidEndptStatsPremTxPirDroppedFrames       OBJECT-TYPE
        SYNTAX        Counter64
        MAX-ACCESS    read-only
        STATUS        current
        DESCRIPTION  "Tx Number of Prem Service Frames PIR dropped."
        ::= { rcIsidEndptStatsEntry 92 }

rcIsidEndptStatsGoldTxCirDroppedFrames       OBJECT-TYPE
        SYNTAX        Counter64
        MAX-ACCESS    read-only
        STATUS        current
        DESCRIPTION  "Tx Number of Gold Service Frames CIR dropped."
        ::= { rcIsidEndptStatsEntry 93 }

rcIsidEndptStatsGoldTxPirDroppedFrames       OBJECT-TYPE
        SYNTAX        Counter64
        MAX-ACCESS    read-only
        STATUS        current
        DESCRIPTION  "Tx Number of Gold Service Frames PIR dropped."
        ::= { rcIsidEndptStatsEntry 94 }

rcIsidEndptStatsSilverTxCirDroppedFrames     OBJECT-TYPE
        SYNTAX        Counter64
        MAX-ACCESS    read-only
        STATUS        current
        DESCRIPTION  "Tx Number of Silver Service Frames CIR dropped."
        ::= { rcIsidEndptStatsEntry 95 }

rcIsidEndptStatsSilverTxPirDroppedFrames     OBJECT-TYPE
        SYNTAX        Counter64
        MAX-ACCESS    read-only
        STATUS        current
        DESCRIPTION  "Tx Number of Silver Service Frames PIR dropped."
        ::= { rcIsidEndptStatsEntry 96 }

rcIsidEndptStatsStndTxCirDroppedFrames       OBJECT-TYPE
        SYNTAX        Counter64
        MAX-ACCESS    read-only
        STATUS        current
        DESCRIPTION  "Tx Number of Standard Service Frames CIR dropped."
        ::= { rcIsidEndptStatsEntry 97 }

rcIsidEndptStatsStndTxPirDroppedFrames       OBJECT-TYPE
        SYNTAX        Counter64
        MAX-ACCESS    read-only
        STATUS        current
        DESCRIPTION  "TX Number of Standard Service Frames PIR dropped."
        ::= { rcIsidEndptStatsEntry 98 }

rcIsidEndptStatsRxMcastTotalFrames   OBJECT-TYPE
        SYNTAX        Counter64
        MAX-ACCESS    read-only
        STATUS        current
        DESCRIPTION  "Rx Total Number of Mcast Frames"
        ::= { rcIsidEndptStatsEntry 99 }

rcIsidEndptStatsTxMcastTotalFrames   OBJECT-TYPE
        SYNTAX        Counter64
        MAX-ACCESS    read-only
        STATUS        current
        DESCRIPTION  "TX total Number of Mcast Frames"
        ::= { rcIsidEndptStatsEntry 100 }

rcIsidEndptStatsPremRxMcastDroppedFrames     OBJECT-TYPE
        SYNTAX        Counter64
        MAX-ACCESS    read-only
        STATUS        current
        DESCRIPTION  "Number of Premium Service Rx Mcast Frames dropped."
        ::= { rcIsidEndptStatsEntry 101 }

rcIsidEndptStatsGoldRxMcastDroppedFrames     OBJECT-TYPE
        SYNTAX        Counter64
        MAX-ACCESS    read-only
        STATUS        current
        DESCRIPTION  "Number of Gold Service Rx Mcast Frames dropped."
        ::= { rcIsidEndptStatsEntry 102 }

rcIsidEndptStatsSilverRxMcastDroppedFrames   OBJECT-TYPE
        SYNTAX        Counter64
        MAX-ACCESS    read-only
        STATUS        current
        DESCRIPTION  "Number of Silver Service Rx Mcast Frames dropped."
        ::= { rcIsidEndptStatsEntry 103 }

rcIsidEndptStatsStndRxMcastDroppedFrames     OBJECT-TYPE
        SYNTAX        Counter64
        MAX-ACCESS    read-only
        STATUS        current
        DESCRIPTION  "Number of Standard Service Rx Mcast Frames dropped."
        ::= { rcIsidEndptStatsEntry 104 }

rcIsidEndptStatsPremRxCirOctets     OBJECT-TYPE
        SYNTAX        Counter64
        MAX-ACCESS    read-only
        STATUS        current
        DESCRIPTION  "Number of Premium Service Rx CIR Octets received."
        ::= { rcIsidEndptStatsEntry 105 }

rcIsidEndptStatsPremRxCirOopOctets     OBJECT-TYPE
        SYNTAX        Counter64
        MAX-ACCESS    read-only
        STATUS        current
        DESCRIPTION  "Number of Premium Service Rx Octets received that 
		      were CIR OOP."
        ::= { rcIsidEndptStatsEntry 106 }

rcIsidEndptStatsPremRxEirOctets     OBJECT-TYPE
        SYNTAX        Counter64
        MAX-ACCESS    read-only
        STATUS        current
        DESCRIPTION  "Number of Premium Service Rx EIR Octets received."
        ::= { rcIsidEndptStatsEntry 107 }

rcIsidEndptStatsPremRxEirOopOctets     OBJECT-TYPE
        SYNTAX        Counter64
        MAX-ACCESS    read-only
        STATUS        current
        DESCRIPTION  "Number of Premium Service Rx Octets received that 
		      were EIR OOP."
        ::= { rcIsidEndptStatsEntry 108 }

rcIsidEndptStatsPremRxEirDroppedOctets     OBJECT-TYPE
        SYNTAX        Counter64
        MAX-ACCESS    read-only
        STATUS        current
        DESCRIPTION  "Number of Premium Service Rx Octets dropped by the 
		      EIR bucket This count would be the same as the EIR 
		      OOP octets as long as the 'drop-red' flag on the 
		      end-point is set to TRUE."
        ::= { rcIsidEndptStatsEntry 109 }

rcIsidEndptStatsPremRxPirOctets     OBJECT-TYPE
        SYNTAX        Counter64
        MAX-ACCESS    read-only
        STATUS        current
        DESCRIPTION  "Number of Premium Service Rx PIR Octets received."
        ::= { rcIsidEndptStatsEntry 110 }

rcIsidEndptStatsPremRxPirOopOctets     OBJECT-TYPE
        SYNTAX        Counter64
        MAX-ACCESS    read-only
        STATUS        current
        DESCRIPTION  "Number of Premium Service Rx Octets received that 
		      were PIR OOP."
        ::= { rcIsidEndptStatsEntry 111 }

rcIsidEndptStatsPremRxGreenOctets     OBJECT-TYPE
        SYNTAX        Counter64
        MAX-ACCESS    read-only
        STATUS        current
        DESCRIPTION  "Number of Premium Service Rx Octets received that 
		      were marked 'Green' by the policer."
        ::= { rcIsidEndptStatsEntry 112 }

rcIsidEndptStatsPremRxYellowOctets     OBJECT-TYPE
        SYNTAX        Counter64
        MAX-ACCESS    read-only
        STATUS        current
        DESCRIPTION  "Number of Premium Service Rx Octets received that 
		      were marked 'Yellow' by the policer."
        ::= { rcIsidEndptStatsEntry 113 }

rcIsidEndptStatsPremRxRedOctets     OBJECT-TYPE
        SYNTAX        Counter64
        MAX-ACCESS    read-only
        STATUS        current
        DESCRIPTION  "Number of Premium Service Rx Octets received that 
		      were marked 'Red' by the policer."
        ::= { rcIsidEndptStatsEntry 114 }

rcIsidEndptStatsGoldRxCirOctets     OBJECT-TYPE
        SYNTAX        Counter64
        MAX-ACCESS    read-only
        STATUS        current
        DESCRIPTION  "Number of Gold Service Rx CIR Octets received."
        ::= { rcIsidEndptStatsEntry 115 }

rcIsidEndptStatsGoldRxCirOopOctets     OBJECT-TYPE
        SYNTAX        Counter64
        MAX-ACCESS    read-only
        STATUS        current
        DESCRIPTION  "Number of Gold Service Rx Octets received that 
		      were CIR OOP."
        ::= { rcIsidEndptStatsEntry 116 }

rcIsidEndptStatsGoldRxEirOctets     OBJECT-TYPE
        SYNTAX        Counter64
        MAX-ACCESS    read-only
        STATUS        current
        DESCRIPTION  "Number of Gold Service Rx EIR Octets received."
        ::= { rcIsidEndptStatsEntry 117 }

rcIsidEndptStatsGoldRxEirOopOctets     OBJECT-TYPE
        SYNTAX        Counter64
        MAX-ACCESS    read-only
        STATUS        current
        DESCRIPTION  "Number of Gold Service Rx Octets received that 
		      were EIR OOP."
        ::= { rcIsidEndptStatsEntry 118 }

rcIsidEndptStatsGoldRxEirDroppedOctets     OBJECT-TYPE
        SYNTAX        Counter64
        MAX-ACCESS    read-only
        STATUS        current
        DESCRIPTION  "Number of Gold Service Rx Octets dropped by the 
		      EIR bucket This count would be the same as the EIR 
		      OOP octets as long as the 'drop-red' flag on the 
		      end-point is set to TRUE."
        ::= { rcIsidEndptStatsEntry 119 }

rcIsidEndptStatsGoldRxPirOctets     OBJECT-TYPE
        SYNTAX        Counter64
        MAX-ACCESS    read-only
        STATUS        current
        DESCRIPTION  "Number of Gold Service Rx PIR Octets received."
        ::= { rcIsidEndptStatsEntry 120 }

rcIsidEndptStatsGoldRxPirOopOctets     OBJECT-TYPE
        SYNTAX        Counter64
        MAX-ACCESS    read-only
        STATUS        current
        DESCRIPTION  "Number of Gold Service Rx Octets received that 
		      were PIR OOP."
        ::= { rcIsidEndptStatsEntry 121 }

rcIsidEndptStatsGoldRxGreenOctets     OBJECT-TYPE
        SYNTAX        Counter64
        MAX-ACCESS    read-only
        STATUS        current
        DESCRIPTION  "Number of Gold Service Rx Octets received that 
		      were marked 'Green' by the policer."
        ::= { rcIsidEndptStatsEntry 122 }

rcIsidEndptStatsGoldRxYellowOctets     OBJECT-TYPE
        SYNTAX        Counter64
        MAX-ACCESS    read-only
        STATUS        current
        DESCRIPTION  "Number of Gold Service Rx Octets received that 
		      were marked 'Yellow' by the policer."
        ::= { rcIsidEndptStatsEntry 123 }

rcIsidEndptStatsGoldRxRedOctets     OBJECT-TYPE
        SYNTAX        Counter64
        MAX-ACCESS    read-only
        STATUS        current
        DESCRIPTION  "Number of Gold Service Rx Octets received that 
		      were marked 'Red' by the policer."
        ::= { rcIsidEndptStatsEntry 124 }

rcIsidEndptStatsSilverRxCirOctets     OBJECT-TYPE
        SYNTAX        Counter64
        MAX-ACCESS    read-only
        STATUS        current
        DESCRIPTION  "Number of Silver Service Rx CIR Octets received."
        ::= { rcIsidEndptStatsEntry 125 }

rcIsidEndptStatsSilverRxCirOopOctets     OBJECT-TYPE
        SYNTAX        Counter64
        MAX-ACCESS    read-only
        STATUS        current
        DESCRIPTION  "Number of Silver Service Rx Octets received that 
		      were CIR OOP."
        ::= { rcIsidEndptStatsEntry 126 }

rcIsidEndptStatsSilverRxEirOctets     OBJECT-TYPE
        SYNTAX        Counter64
        MAX-ACCESS    read-only
        STATUS        current
        DESCRIPTION  "Number of Silver Service Rx EIR Octets received."
        ::= { rcIsidEndptStatsEntry 127 }

rcIsidEndptStatsSilverRxEirOopOctets     OBJECT-TYPE
        SYNTAX        Counter64
        MAX-ACCESS    read-only
        STATUS        current
        DESCRIPTION  "Number of Silver Service Rx Octets received that 
		      were EIR OOP."
        ::= { rcIsidEndptStatsEntry 128 }

rcIsidEndptStatsSilverRxEirDroppedOctets     OBJECT-TYPE
        SYNTAX        Counter64
        MAX-ACCESS    read-only
        STATUS        current
        DESCRIPTION  "Number of Silver Service Rx Octets dropped by the 
		      EIR bucket This count would be the same as the EIR 
		      OOP octets as long as the 'drop-red' flag on the 
		      end-point is set to TRUE."
        ::= { rcIsidEndptStatsEntry 129 }

rcIsidEndptStatsSilverRxPirOctets     OBJECT-TYPE
        SYNTAX        Counter64
        MAX-ACCESS    read-only
        STATUS        current
        DESCRIPTION  "Number of Silver Service Rx PIR Octets received."
        ::= { rcIsidEndptStatsEntry 130 }

rcIsidEndptStatsSilverRxPirOopOctets     OBJECT-TYPE
        SYNTAX        Counter64
        MAX-ACCESS    read-only
        STATUS        current
        DESCRIPTION  "Number of Silver Service Rx Octets received that 
		      were PIR OOP."
        ::= { rcIsidEndptStatsEntry 131 }

rcIsidEndptStatsSilverRxGreenOctets     OBJECT-TYPE
        SYNTAX        Counter64
        MAX-ACCESS    read-only
        STATUS        current
        DESCRIPTION  "Number of Silver Service Rx Octets received that 
		      were marked 'Green' by the policer."
        ::= { rcIsidEndptStatsEntry 132 }

rcIsidEndptStatsSilverRxYellowOctets     OBJECT-TYPE
        SYNTAX        Counter64
        MAX-ACCESS    read-only
        STATUS        current
        DESCRIPTION  "Number of Silver Service Rx Octets received that 
		      were marked 'Yellow' by the policer."
        ::= { rcIsidEndptStatsEntry 133 }

rcIsidEndptStatsSilverRxRedOctets     OBJECT-TYPE
        SYNTAX        Counter64
        MAX-ACCESS    read-only
        STATUS        current
        DESCRIPTION  "Number of Silver Service Rx Octets received that 
		      were marked 'Red' by the policer."
        ::= { rcIsidEndptStatsEntry 134 }

rcIsidEndptStatsStndRxCirOctets     OBJECT-TYPE
        SYNTAX        Counter64
        MAX-ACCESS    read-only
        STATUS        current
        DESCRIPTION  "Number of Standard Service Rx CIR Octets received."
        ::= { rcIsidEndptStatsEntry 135 }

rcIsidEndptStatsStndRxCirOopOctets     OBJECT-TYPE
        SYNTAX        Counter64
        MAX-ACCESS    read-only
        STATUS        current
        DESCRIPTION  "Number of Standard Service Rx Octets received that 
		      were CIR OOP."
        ::= { rcIsidEndptStatsEntry 136 }

rcIsidEndptStatsStndRxEirOctets     OBJECT-TYPE
        SYNTAX        Counter64
        MAX-ACCESS    read-only
        STATUS        current
        DESCRIPTION  "Number of Standard Service Rx EIR Octets received."
        ::= { rcIsidEndptStatsEntry 137 }

rcIsidEndptStatsStndRxEirOopOctets     OBJECT-TYPE
        SYNTAX        Counter64
        MAX-ACCESS    read-only
        STATUS        current
        DESCRIPTION  "Number of Standard Service Rx Octets received that 
		      were EIR OOP."
        ::= { rcIsidEndptStatsEntry 138 }

rcIsidEndptStatsStndRxEirDroppedOctets     OBJECT-TYPE
        SYNTAX        Counter64
        MAX-ACCESS    read-only
        STATUS        current
        DESCRIPTION  "Number of Standard Service Rx Octets dropped by the 
		      EIR bucket This count would be the same as the EIR 
		      OOP octets as long as the 'drop-red' flag on the 
		      end-point is set to TRUE."
        ::= { rcIsidEndptStatsEntry 139 }

rcIsidEndptStatsStndRxPirOctets     OBJECT-TYPE
        SYNTAX        Counter64
        MAX-ACCESS    read-only
        STATUS        current
        DESCRIPTION  "Number of Standard Service Rx PIR Octets received."
        ::= { rcIsidEndptStatsEntry 140 }

rcIsidEndptStatsStndRxPirOopOctets     OBJECT-TYPE
        SYNTAX        Counter64
        MAX-ACCESS    read-only
        STATUS        current
        DESCRIPTION  "Number of Standard Service Rx Octets received that 
		      were PIR OOP."
        ::= { rcIsidEndptStatsEntry 141 }

rcIsidEndptStatsStndRxGreenOctets     OBJECT-TYPE
        SYNTAX        Counter64
        MAX-ACCESS    read-only
        STATUS        current
        DESCRIPTION  "Number of Standard Service Rx Octets received that 
		      were marked 'Green' by the policer."
        ::= { rcIsidEndptStatsEntry 142 }

rcIsidEndptStatsStndRxYellowOctets     OBJECT-TYPE
        SYNTAX        Counter64
        MAX-ACCESS    read-only
        STATUS        current
        DESCRIPTION  "Number of Standard Service Rx Octets received that 
		      were marked 'Yellow' by the policer."
        ::= { rcIsidEndptStatsEntry 143 }

rcIsidEndptStatsStndRxRedOctets     OBJECT-TYPE
        SYNTAX        Counter64
        MAX-ACCESS    read-only
        STATUS        current
        DESCRIPTION  "Number of Standard Service Rx Octets received that 
		      were marked 'Red' by the policer."
        ::= { rcIsidEndptStatsEntry 144 }

rcIsidEndptStatsMcastRxDroppedOctets     OBJECT-TYPE
        SYNTAX        Counter64
        MAX-ACCESS    read-only
        STATUS        current
        DESCRIPTION  "Number of Multicast Rx Octets dropped."
        ::= { rcIsidEndptStatsEntry 145 }

rcIsidEndptStatsBcastUUcastRxTotalOctets     OBJECT-TYPE
        SYNTAX        Counter64
        MAX-ACCESS    read-only
        STATUS        current
        DESCRIPTION  "Number of Broadcast/Unknown Unicast Rx total Octets."
        ::= { rcIsidEndptStatsEntry 146 }

rcIsidEndptStatsBcastUUcastRxDroppedOctets     OBJECT-TYPE
        SYNTAX        Counter64
        MAX-ACCESS    read-only
        STATUS        current
        DESCRIPTION  "Number of Broadcast/Unknown Rx Octets dropped."
        ::= { rcIsidEndptStatsEntry 147 }

rcIsidEndptStatsPremRxCirFrames     OBJECT-TYPE
        SYNTAX        Counter64
        MAX-ACCESS    read-only
        STATUS        current
        DESCRIPTION  "Number of Premium Service Rx CIR Frames received."
        ::= { rcIsidEndptStatsEntry 148 }

rcIsidEndptStatsPremRxCirOopFrames     OBJECT-TYPE
        SYNTAX        Counter64
        MAX-ACCESS    read-only
        STATUS        current
        DESCRIPTION  "Number of Premium Service Rx Frames received that 
		      were CIR OOP."
        ::= { rcIsidEndptStatsEntry 149 }

rcIsidEndptStatsPremRxEirFrames     OBJECT-TYPE
        SYNTAX        Counter64
        MAX-ACCESS    read-only
        STATUS        current
        DESCRIPTION  "Number of Premium Service Rx EIR Frames received."
        ::= { rcIsidEndptStatsEntry 150 }

rcIsidEndptStatsPremRxEirOopFrames     OBJECT-TYPE
        SYNTAX        Counter64
        MAX-ACCESS    read-only
        STATUS        current
        DESCRIPTION  "Number of Premium Service Rx Frames received that 
		      were EIR OOP."
        ::= { rcIsidEndptStatsEntry 151 }

rcIsidEndptStatsPremRxEirDroppedFrames     OBJECT-TYPE
        SYNTAX        Counter64
        MAX-ACCESS    read-only
        STATUS        current
        DESCRIPTION  "Number of Premium Service Rx Frames dropped by the 
		      EIR bucket This count would be the same as the EIR 
		      OOP octets as long as the 'drop-red' flag on the 
		      end-point is set to TRUE."
        ::= { rcIsidEndptStatsEntry 152 }

rcIsidEndptStatsPremRxPirFrames     OBJECT-TYPE
        SYNTAX        Counter64
        MAX-ACCESS    read-only
        STATUS        current
        DESCRIPTION  "Number of Premium Service Rx PIR Frames received."
        ::= { rcIsidEndptStatsEntry 153 }

rcIsidEndptStatsPremRxPirOopFrames     OBJECT-TYPE
        SYNTAX        Counter64
        MAX-ACCESS    read-only
        STATUS        current
        DESCRIPTION  "Number of Premium Service Rx Frames received that 
		      were PIR OOP."
        ::= { rcIsidEndptStatsEntry 154 }

rcIsidEndptStatsPremRxGreenFrames     OBJECT-TYPE
        SYNTAX        Counter64
        MAX-ACCESS    read-only
        STATUS        current
        DESCRIPTION  "Number of Premium Service Rx Frames received that 
		      were marked 'Green' by the policer."
        ::= { rcIsidEndptStatsEntry 155 }

rcIsidEndptStatsPremRxYellowFrames     OBJECT-TYPE
        SYNTAX        Counter64
        MAX-ACCESS    read-only
        STATUS        current
        DESCRIPTION  "Number of Premium Service Rx Frames received that 
		      were marked 'Yellow' by the policer."
        ::= { rcIsidEndptStatsEntry 156 }

rcIsidEndptStatsPremRxRedFrames     OBJECT-TYPE
        SYNTAX        Counter64
        MAX-ACCESS    read-only
        STATUS        current
        DESCRIPTION  "Number of Premium Service Rx Frames received that 
		      were marked 'Red' by the policer."
        ::= { rcIsidEndptStatsEntry 157 }

rcIsidEndptStatsGoldRxCirFrames     OBJECT-TYPE
        SYNTAX        Counter64
        MAX-ACCESS    read-only
        STATUS        current
        DESCRIPTION  "Number of Gold Service Rx CIR Frames received."
        ::= { rcIsidEndptStatsEntry 158 }

rcIsidEndptStatsGoldRxCirOopFrames     OBJECT-TYPE
        SYNTAX        Counter64
        MAX-ACCESS    read-only
        STATUS        current
        DESCRIPTION  "Number of Gold Service Rx Frames received that 
		      were CIR OOP."
        ::= { rcIsidEndptStatsEntry 159 }

rcIsidEndptStatsGoldRxEirFrames     OBJECT-TYPE
        SYNTAX        Counter64
        MAX-ACCESS    read-only
        STATUS        current
        DESCRIPTION  "Number of Gold Service Rx EIR Frames received."
        ::= { rcIsidEndptStatsEntry 160 }

rcIsidEndptStatsGoldRxEirOopFrames     OBJECT-TYPE
        SYNTAX        Counter64
        MAX-ACCESS    read-only
        STATUS        current
        DESCRIPTION  "Number of Gold Service Rx Frames received that 
		      were EIR OOP."
        ::= { rcIsidEndptStatsEntry 161 }

rcIsidEndptStatsGoldRxEirDroppedFrames     OBJECT-TYPE
        SYNTAX        Counter64
        MAX-ACCESS    read-only
        STATUS        current
        DESCRIPTION  "Number of Gold Service Rx Frames dropped by the 
		      EIR bucket This count would be the same as the EIR 
		      OOP octets as long as the 'drop-red' flag on the 
		      end-point is set to TRUE."
        ::= { rcIsidEndptStatsEntry 162 }

rcIsidEndptStatsGoldRxPirFrames     OBJECT-TYPE
        SYNTAX        Counter64
        MAX-ACCESS    read-only
        STATUS        current
        DESCRIPTION  "Number of Gold Service Rx PIR Frames received."
        ::= { rcIsidEndptStatsEntry 163 }

rcIsidEndptStatsGoldRxPirOopFrames     OBJECT-TYPE
        SYNTAX        Counter64
        MAX-ACCESS    read-only
        STATUS        current
        DESCRIPTION  "Number of Gold Service Rx Frames received that 
		      were PIR OOP."
        ::= { rcIsidEndptStatsEntry 164 }

rcIsidEndptStatsGoldRxGreenFrames     OBJECT-TYPE
        SYNTAX        Counter64
        MAX-ACCESS    read-only
        STATUS        current
        DESCRIPTION  "Number of Gold Service Rx Frames received that 
		      were marked 'Green' by the policer."
        ::= { rcIsidEndptStatsEntry 165 }

rcIsidEndptStatsGoldRxYellowFrames     OBJECT-TYPE
        SYNTAX        Counter64
        MAX-ACCESS    read-only
        STATUS        current
        DESCRIPTION  "Number of Gold Service Rx Frames received that 
		      were marked 'Yellow' by the policer."
        ::= { rcIsidEndptStatsEntry 166 }

rcIsidEndptStatsGoldRxRedFrames     OBJECT-TYPE
        SYNTAX        Counter64
        MAX-ACCESS    read-only
        STATUS        current
        DESCRIPTION  "Number of Gold Service Rx Frames received that 
		      were marked 'Red' by the policer."
        ::= { rcIsidEndptStatsEntry 167 }

rcIsidEndptStatsSilverRxCirFrames     OBJECT-TYPE
        SYNTAX        Counter64
        MAX-ACCESS    read-only
        STATUS        current
        DESCRIPTION  "Number of Silver Service Rx CIR Frames received."
        ::= { rcIsidEndptStatsEntry 168 }

rcIsidEndptStatsSilverRxCirOopFrames     OBJECT-TYPE
        SYNTAX        Counter64
        MAX-ACCESS    read-only
        STATUS        current
        DESCRIPTION  "Number of Silver Service Rx Frames received that 
		      were CIR OOP."
        ::= { rcIsidEndptStatsEntry 169 }

rcIsidEndptStatsSilverRxEirFrames     OBJECT-TYPE
        SYNTAX        Counter64
        MAX-ACCESS    read-only
        STATUS        current
        DESCRIPTION  "Number of Silver Service Rx EIR Frames received."
        ::= { rcIsidEndptStatsEntry 170 }

rcIsidEndptStatsSilverRxEirOopFrames     OBJECT-TYPE
        SYNTAX        Counter64
        MAX-ACCESS    read-only
        STATUS        current
        DESCRIPTION  "Number of Silver Service Rx Frames received that 
		      were EIR OOP."
        ::= { rcIsidEndptStatsEntry 171 }

rcIsidEndptStatsSilverRxEirDroppedFrames     OBJECT-TYPE
        SYNTAX        Counter64
        MAX-ACCESS    read-only
        STATUS        current
        DESCRIPTION  "Number of Silver Service Rx Frames dropped by the 
		      EIR bucket This count would be the same as the EIR 
		      OOP octets as long as the 'drop-red' flag on the 
		      end-point is set to TRUE."
        ::= { rcIsidEndptStatsEntry 172 }

rcIsidEndptStatsSilverRxPirFrames     OBJECT-TYPE
        SYNTAX        Counter64
        MAX-ACCESS    read-only
        STATUS        current
        DESCRIPTION  "Number of Silver Service Rx PIR Frames received."
        ::= { rcIsidEndptStatsEntry 173 }

rcIsidEndptStatsSilverRxPirOopFrames     OBJECT-TYPE
        SYNTAX        Counter64
        MAX-ACCESS    read-only
        STATUS        current
        DESCRIPTION  "Number of Silver Service Rx Frames received that 
		      were PIR OOP."
        ::= { rcIsidEndptStatsEntry 174 }

rcIsidEndptStatsSilverRxGreenFrames     OBJECT-TYPE
        SYNTAX        Counter64
        MAX-ACCESS    read-only
        STATUS        current
        DESCRIPTION  "Number of Silver Service Rx Frames received that 
		      were marked 'Green' by the policer."
        ::= { rcIsidEndptStatsEntry 175 }

rcIsidEndptStatsSilverRxYellowFrames     OBJECT-TYPE
        SYNTAX        Counter64
        MAX-ACCESS    read-only
        STATUS        current
        DESCRIPTION  "Number of Silver Service Rx Frames received that 
		      were marked 'Yellow' by the policer."
        ::= { rcIsidEndptStatsEntry 176 }

rcIsidEndptStatsSilverRxRedFrames     OBJECT-TYPE
        SYNTAX        Counter64
        MAX-ACCESS    read-only
        STATUS        current
        DESCRIPTION  "Number of Silver Service Rx Frames received that 
		      were marked 'Red' by the policer."
        ::= { rcIsidEndptStatsEntry 177 }

rcIsidEndptStatsStndRxCirFrames     OBJECT-TYPE
        SYNTAX        Counter64
        MAX-ACCESS    read-only
        STATUS        current
        DESCRIPTION  "Number of Standard Service Rx CIR Frames received."
        ::= { rcIsidEndptStatsEntry 178 }

rcIsidEndptStatsStndRxCirOopFrames     OBJECT-TYPE
        SYNTAX        Counter64
        MAX-ACCESS    read-only
        STATUS        current
        DESCRIPTION  "Number of Standard Service Rx Frames received that 
		      were CIR OOP."
        ::= { rcIsidEndptStatsEntry 179 }

rcIsidEndptStatsStndRxEirFrames     OBJECT-TYPE
        SYNTAX        Counter64
        MAX-ACCESS    read-only
        STATUS        current
        DESCRIPTION  "Number of Standard Service Rx EIR Frames received."
        ::= { rcIsidEndptStatsEntry 180 }

rcIsidEndptStatsStndRxEirOopFrames     OBJECT-TYPE
        SYNTAX        Counter64
        MAX-ACCESS    read-only
        STATUS        current
        DESCRIPTION  "Number of Standard Service Rx Frames received that 
		      were EIR OOP."
        ::= { rcIsidEndptStatsEntry 181 }

rcIsidEndptStatsStndRxEirDroppedFrames     OBJECT-TYPE
        SYNTAX        Counter64
        MAX-ACCESS    read-only
        STATUS        current
        DESCRIPTION  "Number of Standard Service Rx Frames dropped by the 
		      EIR bucket This count would be the same as the EIR 
		      OOP octets as long as the 'drop-red' flag on the 
		      end-point is set to TRUE."
        ::= { rcIsidEndptStatsEntry 182 }

rcIsidEndptStatsStndRxPirFrames     OBJECT-TYPE
        SYNTAX        Counter64
        MAX-ACCESS    read-only
        STATUS        current
        DESCRIPTION  "Number of Standard Service Rx PIR Frames received."
        ::= { rcIsidEndptStatsEntry 183 }

rcIsidEndptStatsStndRxPirOopFrames     OBJECT-TYPE
        SYNTAX        Counter64
        MAX-ACCESS    read-only
        STATUS        current
        DESCRIPTION  "Number of Standard Service Rx Frames received that 
		      were PIR OOP."
        ::= { rcIsidEndptStatsEntry 184 }

rcIsidEndptStatsStndRxGreenFrames     OBJECT-TYPE
        SYNTAX        Counter64
        MAX-ACCESS    read-only
        STATUS        current
        DESCRIPTION  "Number of Standard Service Rx Frames received that 
		      were marked 'Green' by the policer."
        ::= { rcIsidEndptStatsEntry 185 }

rcIsidEndptStatsStndRxYellowFrames     OBJECT-TYPE
        SYNTAX        Counter64
        MAX-ACCESS    read-only
        STATUS        current
        DESCRIPTION  "Number of Standard Service Rx Frames received that 
		      were marked 'Yellow' by the policer."
        ::= { rcIsidEndptStatsEntry 186 }

rcIsidEndptStatsStndRxRedFrames     OBJECT-TYPE
        SYNTAX        Counter64
        MAX-ACCESS    read-only
        STATUS        current
        DESCRIPTION  "Number of Standard Service Rx Frames received that 
		      were marked 'Red' by the policer."
        ::= { rcIsidEndptStatsEntry 187 }

rcIsidEndptStatsMcastRxDroppedFrames     OBJECT-TYPE
        SYNTAX        Counter64
        MAX-ACCESS    read-only
        STATUS        current
        DESCRIPTION  "Number of Multicast Rx Frames dropped."
        ::= { rcIsidEndptStatsEntry 188 }

rcIsidEndptStatsBcastUUcastRxTotalFrames     OBJECT-TYPE
        SYNTAX        Counter64
        MAX-ACCESS    read-only
        STATUS        current
        DESCRIPTION  "Number of Broadcast/Unknown Unicast Rx total Frames."
        ::= { rcIsidEndptStatsEntry 189 }

rcIsidEndptStatsBcastUUcastRxDroppedFrames     OBJECT-TYPE
        SYNTAX        Counter64
        MAX-ACCESS    read-only
        STATUS        current
        DESCRIPTION  "Number of Broadcast/Unknown Rx Frames dropped."
        ::= { rcIsidEndptStatsEntry 190 }

rcIsidEndptStatsPremTxCirOctets     OBJECT-TYPE
        SYNTAX        Counter64
        MAX-ACCESS    read-only
        STATUS        current
        DESCRIPTION  "Number of Premium Service Tx CIR Octets received."
        ::= { rcIsidEndptStatsEntry 191 }

rcIsidEndptStatsPremTxCirOopOctets     OBJECT-TYPE
        SYNTAX        Counter64
        MAX-ACCESS    read-only
        STATUS        current
        DESCRIPTION  "Number of Premium Service Tx Octets received that 
		      were CIR OOP."
        ::= { rcIsidEndptStatsEntry 192 }

rcIsidEndptStatsPremTxEirOctets     OBJECT-TYPE
        SYNTAX        Counter64
        MAX-ACCESS    read-only
        STATUS        current
        DESCRIPTION  "Number of Premium Service Tx EIR Octets received."
        ::= { rcIsidEndptStatsEntry 193 }

rcIsidEndptStatsPremTxEirOopOctets     OBJECT-TYPE
        SYNTAX        Counter64
        MAX-ACCESS    read-only
        STATUS        current
        DESCRIPTION  "Number of Premium Service Tx Octets received that 
		      were EIR OOP."
        ::= { rcIsidEndptStatsEntry 194 }

rcIsidEndptStatsPremTxEirDroppedOctets     OBJECT-TYPE
        SYNTAX        Counter64
        MAX-ACCESS    read-only
        STATUS        current
        DESCRIPTION  "Number of Premium Service Tx Octets dropped by the 
		      EIR bucket This count would be the same as the EIR 
		      OOP octets as long as the 'drop-red' flag on the 
		      end-point is set to TRUE."
        ::= { rcIsidEndptStatsEntry 195 }

rcIsidEndptStatsPremTxPirOctets     OBJECT-TYPE
        SYNTAX        Counter64
        MAX-ACCESS    read-only
        STATUS        current
        DESCRIPTION  "Number of Premium Service Tx PIR Octets received."
        ::= { rcIsidEndptStatsEntry 196 }

rcIsidEndptStatsPremTxPirOopOctets     OBJECT-TYPE
        SYNTAX        Counter64
        MAX-ACCESS    read-only
        STATUS        current
        DESCRIPTION  "Number of Premium Service Tx Octets received that 
		      were PIR OOP."
        ::= { rcIsidEndptStatsEntry 197 }

rcIsidEndptStatsPremTxGreenOctets     OBJECT-TYPE
        SYNTAX        Counter64
        MAX-ACCESS    read-only
        STATUS        current
        DESCRIPTION  "Number of Premium Service Tx Octets received that 
		      were marked 'Green' by the policer."
        ::= { rcIsidEndptStatsEntry 198 }

rcIsidEndptStatsPremTxYellowOctets     OBJECT-TYPE
        SYNTAX        Counter64
        MAX-ACCESS    read-only
        STATUS        current
        DESCRIPTION  "Number of Premium Service Tx Octets received that 
		      were marked 'Yellow' by the policer."
        ::= { rcIsidEndptStatsEntry 199 }

rcIsidEndptStatsPremTxRedOctets     OBJECT-TYPE
        SYNTAX        Counter64
        MAX-ACCESS    read-only
        STATUS        current
        DESCRIPTION  "Number of Premium Service Tx Octets received that 
		      were marked 'Red' by the policer."
        ::= { rcIsidEndptStatsEntry 200 }

rcIsidEndptStatsGoldTxCirOctets     OBJECT-TYPE
        SYNTAX        Counter64
        MAX-ACCESS    read-only
        STATUS        current
        DESCRIPTION  "Number of Gold Service Tx CIR Octets received."
        ::= { rcIsidEndptStatsEntry 201 }

rcIsidEndptStatsGoldTxCirOopOctets     OBJECT-TYPE
        SYNTAX        Counter64
        MAX-ACCESS    read-only
        STATUS        current
        DESCRIPTION  "Number of Gold Service Tx Octets received that 
		      were CIR OOP."
        ::= { rcIsidEndptStatsEntry 202 }

rcIsidEndptStatsGoldTxEirOctets     OBJECT-TYPE
        SYNTAX        Counter64
        MAX-ACCESS    read-only
        STATUS        current
        DESCRIPTION  "Number of Gold Service Tx EIR Octets received."
        ::= { rcIsidEndptStatsEntry 203 }

rcIsidEndptStatsGoldTxEirOopOctets     OBJECT-TYPE
        SYNTAX        Counter64
        MAX-ACCESS    read-only
        STATUS        current
        DESCRIPTION  "Number of Gold Service Tx Octets received that 
		      were EIR OOP."
        ::= { rcIsidEndptStatsEntry 204 }

rcIsidEndptStatsGoldTxEirDroppedOctets     OBJECT-TYPE
        SYNTAX        Counter64
        MAX-ACCESS    read-only
        STATUS        current
        DESCRIPTION  "Number of Gold Service Tx Octets dropped by the 
		      EIR bucket This count would be the same as the EIR 
		      OOP octets as long as the 'drop-red' flag on the 
		      end-point is set to TRUE."
        ::= { rcIsidEndptStatsEntry 205 }

rcIsidEndptStatsGoldTxPirOctets     OBJECT-TYPE
        SYNTAX        Counter64
        MAX-ACCESS    read-only
        STATUS        current
        DESCRIPTION  "Number of Gold Service Tx PIR Octets received."
        ::= { rcIsidEndptStatsEntry 206 }

rcIsidEndptStatsGoldTxPirOopOctets     OBJECT-TYPE
        SYNTAX        Counter64
        MAX-ACCESS    read-only
        STATUS        current
        DESCRIPTION  "Number of Gold Service Tx Octets received that 
		      were PIR OOP."
        ::= { rcIsidEndptStatsEntry 207 }

rcIsidEndptStatsGoldTxGreenOctets     OBJECT-TYPE
        SYNTAX        Counter64
        MAX-ACCESS    read-only
        STATUS        current
        DESCRIPTION  "Number of Gold Service Tx Octets received that 
		      were marked 'Green' by the policer."
        ::= { rcIsidEndptStatsEntry 208 }

rcIsidEndptStatsGoldTxYellowOctets     OBJECT-TYPE
        SYNTAX        Counter64
        MAX-ACCESS    read-only
        STATUS        current
        DESCRIPTION  "Number of Gold Service Tx Octets received that 
		      were marked 'Yellow' by the policer."
        ::= { rcIsidEndptStatsEntry 209 }

rcIsidEndptStatsGoldTxRedOctets     OBJECT-TYPE
        SYNTAX        Counter64
        MAX-ACCESS    read-only
        STATUS        current
        DESCRIPTION  "Number of Gold Service Tx Octets received that 
		      were marked 'Red' by the policer."
        ::= { rcIsidEndptStatsEntry 210 }

rcIsidEndptStatsSilverTxCirOctets     OBJECT-TYPE
        SYNTAX        Counter64
        MAX-ACCESS    read-only
        STATUS        current
        DESCRIPTION  "Number of Silver Service Tx CIR Octets received."
        ::= { rcIsidEndptStatsEntry 211 }

rcIsidEndptStatsSilverTxCirOopOctets     OBJECT-TYPE
        SYNTAX        Counter64
        MAX-ACCESS    read-only
        STATUS        current
        DESCRIPTION  "Number of Silver Service Tx Octets received that 
		      were CIR OOP."
        ::= { rcIsidEndptStatsEntry 212 }

rcIsidEndptStatsSilverTxEirOctets     OBJECT-TYPE
        SYNTAX        Counter64
        MAX-ACCESS    read-only
        STATUS        current
        DESCRIPTION  "Number of Silver Service Tx EIR Octets received."
        ::= { rcIsidEndptStatsEntry 213 }

rcIsidEndptStatsSilverTxEirOopOctets     OBJECT-TYPE
        SYNTAX        Counter64
        MAX-ACCESS    read-only
        STATUS        current
        DESCRIPTION  "Number of Silver Service Tx Octets received that 
		      were EIR OOP."
        ::= { rcIsidEndptStatsEntry 214 }

rcIsidEndptStatsSilverTxEirDroppedOctets     OBJECT-TYPE
        SYNTAX        Counter64
        MAX-ACCESS    read-only
        STATUS        current
        DESCRIPTION  "Number of Silver Service Tx Octets dropped by the 
		      EIR bucket This count would be the same as the EIR 
		      OOP octets as long as the 'drop-red' flag on the 
		      end-point is set to TRUE."
        ::= { rcIsidEndptStatsEntry 215 }

rcIsidEndptStatsSilverTxPirOctets     OBJECT-TYPE
        SYNTAX        Counter64
        MAX-ACCESS    read-only
        STATUS        current
        DESCRIPTION  "Number of Silver Service Tx PIR Octets received."
        ::= { rcIsidEndptStatsEntry 216 }

rcIsidEndptStatsSilverTxPirOopOctets     OBJECT-TYPE
        SYNTAX        Counter64
        MAX-ACCESS    read-only
        STATUS        current
        DESCRIPTION  "Number of Silver Service Tx Octets received that 
		      were PIR OOP."
        ::= { rcIsidEndptStatsEntry 217 }

rcIsidEndptStatsSilverTxGreenOctets     OBJECT-TYPE
        SYNTAX        Counter64
        MAX-ACCESS    read-only
        STATUS        current
        DESCRIPTION  "Number of Silver Service Tx Octets received that 
		      were marked 'Green' by the policer."
        ::= { rcIsidEndptStatsEntry 218 }

rcIsidEndptStatsSilverTxYellowOctets     OBJECT-TYPE
        SYNTAX        Counter64
        MAX-ACCESS    read-only
        STATUS        current
        DESCRIPTION  "Number of Silver Service Tx Octets received that 
		      were marked 'Yellow' by the policer."
        ::= { rcIsidEndptStatsEntry 219 }

rcIsidEndptStatsSilverTxRedOctets     OBJECT-TYPE
        SYNTAX        Counter64
        MAX-ACCESS    read-only
        STATUS        current
        DESCRIPTION  "Number of Silver Service Tx Octets received that 
		      were marked 'Red' by the policer."
        ::= { rcIsidEndptStatsEntry 220 }

rcIsidEndptStatsStndTxCirOctets     OBJECT-TYPE
        SYNTAX        Counter64
        MAX-ACCESS    read-only
        STATUS        current
        DESCRIPTION  "Number of Standard Service Tx CIR Octets received."
        ::= { rcIsidEndptStatsEntry 221 }

rcIsidEndptStatsStndTxCirOopOctets     OBJECT-TYPE
        SYNTAX        Counter64
        MAX-ACCESS    read-only
        STATUS        current
        DESCRIPTION  "Number of Standard Service Tx Octets received that 
		      were CIR OOP."
        ::= { rcIsidEndptStatsEntry 222 }

rcIsidEndptStatsStndTxEirOctets     OBJECT-TYPE
        SYNTAX        Counter64
        MAX-ACCESS    read-only
        STATUS        current
        DESCRIPTION  "Number of Standard Service Tx EIR Octets received."
        ::= { rcIsidEndptStatsEntry 223 }

rcIsidEndptStatsStndTxEirOopOctets     OBJECT-TYPE
        SYNTAX        Counter64
        MAX-ACCESS    read-only
        STATUS        current
        DESCRIPTION  "Number of Standard Service Tx Octets received that 
		      were EIR OOP."
        ::= { rcIsidEndptStatsEntry 224 }

rcIsidEndptStatsStndTxEirDroppedOctets     OBJECT-TYPE
        SYNTAX        Counter64
        MAX-ACCESS    read-only
        STATUS        current
        DESCRIPTION  "Number of Standard Service Tx Octets dropped by the 
		      EIR bucket This count would be the same as the EIR 
		      OOP octets as long as the 'drop-red' flag on the 
		      end-point is set to TRUE."
        ::= { rcIsidEndptStatsEntry 225 }

rcIsidEndptStatsStndTxPirOctets     OBJECT-TYPE
        SYNTAX        Counter64
        MAX-ACCESS    read-only
        STATUS        current
        DESCRIPTION  "Number of Standard Service Tx PIR Octets received."
        ::= { rcIsidEndptStatsEntry 226 }

rcIsidEndptStatsStndTxPirOopOctets     OBJECT-TYPE
        SYNTAX        Counter64
        MAX-ACCESS    read-only
        STATUS        current
        DESCRIPTION  "Number of Standard Service Tx Octets received that 
		      were PIR OOP."
        ::= { rcIsidEndptStatsEntry 227 }

rcIsidEndptStatsStndTxGreenOctets     OBJECT-TYPE
        SYNTAX        Counter64
        MAX-ACCESS    read-only
        STATUS        current
        DESCRIPTION  "Number of Standard Service Tx Octets received that 
		      were marked 'Green' by the policer."
        ::= { rcIsidEndptStatsEntry 228 }

rcIsidEndptStatsStndTxYellowOctets     OBJECT-TYPE
        SYNTAX        Counter64
        MAX-ACCESS    read-only
        STATUS        current
        DESCRIPTION  "Number of Standard Service Tx Octets received that 
		      were marked 'Yellow' by the policer."
        ::= { rcIsidEndptStatsEntry 229 }

rcIsidEndptStatsStndTxRedOctets     OBJECT-TYPE
        SYNTAX        Counter64
        MAX-ACCESS    read-only
        STATUS        current
        DESCRIPTION  "Number of Standard Service Tx Octets received that 
		      were marked 'Red' by the policer."
        ::= { rcIsidEndptStatsEntry 230 }

rcIsidEndptStatsMcastTxDroppedOctets     OBJECT-TYPE
        SYNTAX        Counter64
        MAX-ACCESS    read-only
        STATUS        current
        DESCRIPTION  "Number of Multicast Tx Octets dropped."
        ::= { rcIsidEndptStatsEntry 231 }

rcIsidEndptStatsBcastUUcastTxTotalOctets     OBJECT-TYPE
        SYNTAX        Counter64
        MAX-ACCESS    read-only
        STATUS        current
        DESCRIPTION  "Number of Broadcast/Unknown Unicast Tx total Octets."
        ::= { rcIsidEndptStatsEntry 232 }

rcIsidEndptStatsBcastUUcastTxDroppedOctets     OBJECT-TYPE
        SYNTAX        Counter64
        MAX-ACCESS    read-only
        STATUS        current
        DESCRIPTION  "Number of Broadcast/Unknown Tx Octets dropped."
        ::= { rcIsidEndptStatsEntry 233 }

rcIsidEndptStatsPremTxCirFrames     OBJECT-TYPE
        SYNTAX        Counter64
        MAX-ACCESS    read-only
        STATUS        current
        DESCRIPTION  "Number of Premium Service Tx CIR Frames received."
        ::= { rcIsidEndptStatsEntry 234 }

rcIsidEndptStatsPremTxCirOopFrames     OBJECT-TYPE
        SYNTAX        Counter64
        MAX-ACCESS    read-only
        STATUS        current
        DESCRIPTION  "Number of Premium Service Tx Frames received that 
		      were CIR OOP."
        ::= { rcIsidEndptStatsEntry 235 }

rcIsidEndptStatsPremTxEirFrames     OBJECT-TYPE
        SYNTAX        Counter64
        MAX-ACCESS    read-only
        STATUS        current
        DESCRIPTION  "Number of Premium Service Tx EIR Frames received."
        ::= { rcIsidEndptStatsEntry 236 }

rcIsidEndptStatsPremTxEirOopFrames     OBJECT-TYPE
        SYNTAX        Counter64
        MAX-ACCESS    read-only
        STATUS        current
        DESCRIPTION  "Number of Premium Service Tx Frames received that 
		      were EIR OOP."
        ::= { rcIsidEndptStatsEntry 237 }

rcIsidEndptStatsPremTxEirDroppedFrames     OBJECT-TYPE
        SYNTAX        Counter64
        MAX-ACCESS    read-only
        STATUS        current
        DESCRIPTION  "Number of Premium Service Tx Frames dropped by the 
		      EIR bucket This count would be the same as the EIR 
		      OOP octets as long as the 'drop-red' flag on the 
		      end-point is set to TRUE."
        ::= { rcIsidEndptStatsEntry 238 }

rcIsidEndptStatsPremTxPirFrames     OBJECT-TYPE
        SYNTAX        Counter64
        MAX-ACCESS    read-only
        STATUS        current
        DESCRIPTION  "Number of Premium Service Tx PIR Frames received."
        ::= { rcIsidEndptStatsEntry 239 }

rcIsidEndptStatsPremTxPirOopFrames     OBJECT-TYPE
        SYNTAX        Counter64
        MAX-ACCESS    read-only
        STATUS        current
        DESCRIPTION  "Number of Premium Service Tx Frames received that 
		      were PIR OOP."
        ::= { rcIsidEndptStatsEntry 240 }

rcIsidEndptStatsPremTxGreenFrames     OBJECT-TYPE
        SYNTAX        Counter64
        MAX-ACCESS    read-only
        STATUS        current
        DESCRIPTION  "Number of Premium Service Tx Frames received that 
		      were marked 'Green' by the policer."
        ::= { rcIsidEndptStatsEntry 241 }

rcIsidEndptStatsPremTxYellowFrames     OBJECT-TYPE
        SYNTAX        Counter64
        MAX-ACCESS    read-only
        STATUS        current
        DESCRIPTION  "Number of Premium Service Tx Frames received that 
		      were marked 'Yellow' by the policer."
        ::= { rcIsidEndptStatsEntry 242 }

rcIsidEndptStatsPremTxRedFrames     OBJECT-TYPE
        SYNTAX        Counter64
        MAX-ACCESS    read-only
        STATUS        current
        DESCRIPTION  "Number of Premium Service Tx Frames received that 
		      were marked 'Red' by the policer."
        ::= { rcIsidEndptStatsEntry 243 }

rcIsidEndptStatsGoldTxCirFrames     OBJECT-TYPE
        SYNTAX        Counter64
        MAX-ACCESS    read-only
        STATUS        current
        DESCRIPTION  "Number of Gold Service Tx CIR Frames received."
        ::= { rcIsidEndptStatsEntry 244 }

rcIsidEndptStatsGoldTxCirOopFrames     OBJECT-TYPE
        SYNTAX        Counter64
        MAX-ACCESS    read-only
        STATUS        current
        DESCRIPTION  "Number of Gold Service Tx Frames received that 
		      were CIR OOP."
        ::= { rcIsidEndptStatsEntry 245 }

rcIsidEndptStatsGoldTxEirFrames     OBJECT-TYPE
        SYNTAX        Counter64
        MAX-ACCESS    read-only
        STATUS        current
        DESCRIPTION  "Number of Gold Service Tx EIR Frames received."
        ::= { rcIsidEndptStatsEntry 246 }

rcIsidEndptStatsGoldTxEirOopFrames     OBJECT-TYPE
        SYNTAX        Counter64
        MAX-ACCESS    read-only
        STATUS        current
        DESCRIPTION  "Number of Gold Service Tx Frames received that 
		      were EIR OOP."
        ::= { rcIsidEndptStatsEntry 247 }

rcIsidEndptStatsGoldTxEirDroppedFrames     OBJECT-TYPE
        SYNTAX        Counter64
        MAX-ACCESS    read-only
        STATUS        current
        DESCRIPTION  "Number of Gold Service Tx Frames dropped by the 
		      EIR bucket This count would be the same as the EIR 
		      OOP octets as long as the 'drop-red' flag on the 
		      end-point is set to TRUE."
        ::= { rcIsidEndptStatsEntry 248 }

rcIsidEndptStatsGoldTxPirFrames     OBJECT-TYPE
        SYNTAX        Counter64
        MAX-ACCESS    read-only
        STATUS        current
        DESCRIPTION  "Number of Gold Service Tx PIR Frames received."
        ::= { rcIsidEndptStatsEntry 249 }

rcIsidEndptStatsGoldTxPirOopFrames     OBJECT-TYPE
        SYNTAX        Counter64
        MAX-ACCESS    read-only
        STATUS        current
        DESCRIPTION  "Number of Gold Service Tx Frames received that 
		      were PIR OOP."
        ::= { rcIsidEndptStatsEntry 250 }

rcIsidEndptStatsGoldTxGreenFrames     OBJECT-TYPE
        SYNTAX        Counter64
        MAX-ACCESS    read-only
        STATUS        current
        DESCRIPTION  "Number of Gold Service Tx Frames received that 
		      were marked 'Green' by the policer."
        ::= { rcIsidEndptStatsEntry 251 }

rcIsidEndptStatsGoldTxYellowFrames     OBJECT-TYPE
        SYNTAX        Counter64
        MAX-ACCESS    read-only
        STATUS        current
        DESCRIPTION  "Number of Gold Service Tx Frames received that 
		      were marked 'Yellow' by the policer."
        ::= { rcIsidEndptStatsEntry 252 }

rcIsidEndptStatsGoldTxRedFrames     OBJECT-TYPE
        SYNTAX        Counter64
        MAX-ACCESS    read-only
        STATUS        current
        DESCRIPTION  "Number of Gold Service Tx Frames received that 
		      were marked 'Red' by the policer."
        ::= { rcIsidEndptStatsEntry 253 }

rcIsidEndptStatsSilverTxCirFrames     OBJECT-TYPE
        SYNTAX        Counter64
        MAX-ACCESS    read-only
        STATUS        current
        DESCRIPTION  "Number of Silver Service Tx CIR Frames received."
        ::= { rcIsidEndptStatsEntry 254 }

rcIsidEndptStatsSilverTxCirOopFrames     OBJECT-TYPE
        SYNTAX        Counter64
        MAX-ACCESS    read-only
        STATUS        current
        DESCRIPTION  "Number of Silver Service Tx Frames received that 
		      were CIR OOP."
        ::= { rcIsidEndptStatsEntry 255 }

rcIsidEndptStatsSilverTxEirFrames     OBJECT-TYPE
        SYNTAX        Counter64
        MAX-ACCESS    read-only
        STATUS        current
        DESCRIPTION  "Number of Silver Service Tx EIR Frames received."
        ::= { rcIsidEndptStatsEntry 256 }

rcIsidEndptStatsSilverTxEirOopFrames     OBJECT-TYPE
        SYNTAX        Counter64
        MAX-ACCESS    read-only
        STATUS        current
        DESCRIPTION  "Number of Silver Service Tx Frames received that 
		      were EIR OOP."
        ::= { rcIsidEndptStatsEntry 257 }

rcIsidEndptStatsSilverTxEirDroppedFrames     OBJECT-TYPE
        SYNTAX        Counter64
        MAX-ACCESS    read-only
        STATUS        current
        DESCRIPTION  "Number of Silver Service Tx Frames dropped by the 
		      EIR bucket This count would be the same as the EIR 
		      OOP octets as long as the 'drop-red' flag on the 
		      end-point is set to TRUE."
        ::= { rcIsidEndptStatsEntry 258 }

rcIsidEndptStatsSilverTxPirFrames     OBJECT-TYPE
        SYNTAX        Counter64
        MAX-ACCESS    read-only
        STATUS        current
        DESCRIPTION  "Number of Silver Service Tx PIR Frames received."
        ::= { rcIsidEndptStatsEntry 259 }

rcIsidEndptStatsSilverTxPirOopFrames     OBJECT-TYPE
        SYNTAX        Counter64
        MAX-ACCESS    read-only
        STATUS        current
        DESCRIPTION  "Number of Silver Service Tx Frames received that 
		      were PIR OOP."
        ::= { rcIsidEndptStatsEntry 260 }

rcIsidEndptStatsSilverTxGreenFrames     OBJECT-TYPE
        SYNTAX        Counter64
        MAX-ACCESS    read-only
        STATUS        current
        DESCRIPTION  "Number of Silver Service Tx Frames received that 
		      were marked 'Green' by the policer."
        ::= { rcIsidEndptStatsEntry 261 }

rcIsidEndptStatsSilverTxYellowFrames     OBJECT-TYPE
        SYNTAX        Counter64
        MAX-ACCESS    read-only
        STATUS        current
        DESCRIPTION  "Number of Silver Service Tx Frames received that 
		      were marked 'Yellow' by the policer."
        ::= { rcIsidEndptStatsEntry 262 }

rcIsidEndptStatsSilverTxRedFrames     OBJECT-TYPE
        SYNTAX        Counter64
        MAX-ACCESS    read-only
        STATUS        current
        DESCRIPTION  "Number of Silver Service Tx Frames received that 
		      were marked 'Red' by the policer."
        ::= { rcIsidEndptStatsEntry 263 }

rcIsidEndptStatsStndTxCirFrames     OBJECT-TYPE
        SYNTAX        Counter64
        MAX-ACCESS    read-only
        STATUS        current
        DESCRIPTION  "Number of Standard Service Tx CIR Frames received."
        ::= { rcIsidEndptStatsEntry 264 }

rcIsidEndptStatsStndTxCirOopFrames     OBJECT-TYPE
        SYNTAX        Counter64
        MAX-ACCESS    read-only
        STATUS        current
        DESCRIPTION  "Number of Standard Service Tx Frames received that 
		      were CIR OOP."
        ::= { rcIsidEndptStatsEntry 265 }

rcIsidEndptStatsStndTxEirFrames     OBJECT-TYPE
        SYNTAX        Counter64
        MAX-ACCESS    read-only
        STATUS        current
        DESCRIPTION  "Number of Standard Service Tx EIR Frames received."
        ::= { rcIsidEndptStatsEntry 266 }

rcIsidEndptStatsStndTxEirOopFrames     OBJECT-TYPE
        SYNTAX        Counter64
        MAX-ACCESS    read-only
        STATUS        current
        DESCRIPTION  "Number of Standard Service Tx Frames received that 
		      were EIR OOP."
        ::= { rcIsidEndptStatsEntry 267 }

rcIsidEndptStatsStndTxEirDroppedFrames     OBJECT-TYPE
        SYNTAX        Counter64
        MAX-ACCESS    read-only
        STATUS        current
        DESCRIPTION  "Number of Standard Service Tx Frames dropped by the 
		      EIR bucket This count would be the same as the EIR 
		      OOP octets as long as the 'drop-red' flag on the 
		      end-point is set to TRUE."
        ::= { rcIsidEndptStatsEntry 268 }

rcIsidEndptStatsStndTxPirFrames     OBJECT-TYPE
        SYNTAX        Counter64
        MAX-ACCESS    read-only
        STATUS        current
        DESCRIPTION  "Number of Standard Service Tx PIR Frames received."
        ::= { rcIsidEndptStatsEntry 269 }

rcIsidEndptStatsStndTxPirOopFrames     OBJECT-TYPE
        SYNTAX        Counter64
        MAX-ACCESS    read-only
        STATUS        current
        DESCRIPTION  "Number of Standard Service Tx Frames received that 
		      were PIR OOP."
        ::= { rcIsidEndptStatsEntry 270 }

rcIsidEndptStatsStndTxGreenFrames     OBJECT-TYPE
        SYNTAX        Counter64
        MAX-ACCESS    read-only
        STATUS        current
        DESCRIPTION  "Number of Standard Service Tx Frames received that 
		      were marked 'Green' by the policer."
        ::= { rcIsidEndptStatsEntry 271 }

rcIsidEndptStatsStndTxYellowFrames     OBJECT-TYPE
        SYNTAX        Counter64
        MAX-ACCESS    read-only
        STATUS        current
        DESCRIPTION  "Number of Standard Service Tx Frames received that 
		      were marked 'Yellow' by the policer."
        ::= { rcIsidEndptStatsEntry 272 }

rcIsidEndptStatsStndTxRedFrames     OBJECT-TYPE
        SYNTAX        Counter64
        MAX-ACCESS    read-only
        STATUS        current
        DESCRIPTION  "Number of Standard Service Tx Frames received that 
		      were marked 'Red' by the policer."
        ::= { rcIsidEndptStatsEntry 273 }

rcIsidEndptStatsMcastTxDroppedFrames     OBJECT-TYPE
        SYNTAX        Counter64
        MAX-ACCESS    read-only
        STATUS        current
        DESCRIPTION  "Number of Multicast Tx Frames dropped."
        ::= { rcIsidEndptStatsEntry 274 }

rcIsidEndptStatsBcastUUcastTxTotalFrames     OBJECT-TYPE
        SYNTAX        Counter64
        MAX-ACCESS    read-only
        STATUS        current
        DESCRIPTION  "Number of Broadcast/Unknown Unicast Tx total Frames."
        ::= { rcIsidEndptStatsEntry 275 }

rcIsidEndptStatsBcastUUcastTxDroppedFrames     OBJECT-TYPE
        SYNTAX        Counter64
        MAX-ACCESS    read-only
        STATUS        current
        DESCRIPTION  "Number of Broadcast/Unknown Tx Frames dropped."
        ::= { rcIsidEndptStatsEntry 276 }

rcIsidEndptStatsCfmIngRtLimitPassedFrames OBJECT-TYPE
        SYNTAX        Counter64
        MAX-ACCESS    read-only
        STATUS        current
        DESCRIPTION  "Number of Ingress CFM Frames passed after rate limiting."
        ::= { rcIsidEndptStatsEntry 277 }

rcIsidEndptStatsCfmIngRtLimitDroppedFrames OBJECT-TYPE
        SYNTAX        Counter64
        MAX-ACCESS    read-only
        STATUS        current
        DESCRIPTION  "Number of Ingress CFM Frames dropped after rate limiting."
        ::= { rcIsidEndptStatsEntry 278 }

rcIsidEndptStatsCfmEgrRtLimitPassedFrames OBJECT-TYPE
        SYNTAX        Counter64
        MAX-ACCESS    read-only
        STATUS        current
        DESCRIPTION  "Number of Egress CFM frames passed after rate limiting."
        ::= { rcIsidEndptStatsEntry 279 }

rcIsidEndptStatsCfmEgrRtLimitDroppedFrames  OBJECT-TYPE
        SYNTAX        Counter64
        MAX-ACCESS    read-only
        STATUS        current
        DESCRIPTION  "Number of Egress CFM frames dropped after rate limiting."
        ::= { rcIsidEndptStatsEntry 280 }

rcIsidEndptStatsDropClassRxDroppedOctets     OBJECT-TYPE
        SYNTAX        Counter64
        MAX-ACCESS    read-only
        STATUS        current
        DESCRIPTION  "Number of Drop Class Rx Octets dropped."
        ::= { rcIsidEndptStatsEntry 281 }

rcIsidEndptStatsDropClassRxDroppedFrames     OBJECT-TYPE
        SYNTAX        Counter64
        MAX-ACCESS    read-only
        STATUS        current
        DESCRIPTION  "Number of Drop Class Rx Frames dropped."
        ::= { rcIsidEndptStatsEntry 282 }

rcIsidEndptStatsDropClassTxDroppedOctets	OBJECT-TYPE
        SYNTAX        Counter64
        MAX-ACCESS    read-only
        STATUS        current
        DESCRIPTION  "Number of Drop Class Tx Octets dropped."
        ::= { rcIsidEndptStatsEntry 283 }

rcIsidEndptStatsDropClassTxDroppedFrames     OBJECT-TYPE
        SYNTAX        Counter64
        MAX-ACCESS    read-only
        STATUS        current
        DESCRIPTION  "Number of Drop Class Tx Frames dropped."
        ::= { rcIsidEndptStatsEntry 284 }



-- Isid Endpoint Cvid Client Mep

rcIsidEndptCvidClientMepTable OBJECT-TYPE
        SYNTAX        SEQUENCE OF RcIsidEndptCvidClientMepEntry
        MAX-ACCESS    not-accessible
        STATUS        current
        DESCRIPTION   "A table used to maintain CFM Client MEP 
                       assigned to the Isid Endpoint with Cvid"
        ::= { rc8021ah 5 }

rcIsidEndptCvidClientMepEntry OBJECT-TYPE
        SYNTAX        RcIsidEndptCvidClientMepEntry
        MAX-ACCESS    not-accessible
        STATUS        current
        DESCRIPTION   "An entry in the rcIsidEndptCvidClientMep table."
        INDEX         { rcIsidEndptCvidClientMepIsidId, rcIsidEndptCvidClientMepTlsIndex, rcIsidEndptCvidClientMepCvid}
        ::= { rcIsidEndptCvidClientMepTable 1 }

RcIsidEndptCvidClientMepEntry ::= SEQUENCE {
        rcIsidEndptCvidClientMepIsidId    Integer32,
        rcIsidEndptCvidClientMepTlsIndex  Integer32,
        rcIsidEndptCvidClientMepCvid      Integer32,
        rcIsidEndptCvidClientMepMepList   OCTET STRING,
	rcIsidEndptCvidClientMepNumOfMep  Integer32,
	rcIsidEndptCvidClientMepRowStatus RowStatus,
	rcIsidEndptCvidClientMepPort      InterfaceIndex,
	rcIsidEndptCvidClientDownMepMepList     OCTET STRING,
	rcIsidEndptCvidClientDownMepNumOfMep    Integer32
        }

rcIsidEndptCvidClientMepIsidId OBJECT-TYPE
        SYNTAX        Integer32 (1..16777215) 
        MAX-ACCESS    not-accessible
        STATUS        current
        DESCRIPTION   "Service Instance ID of the I component"
        ::= { rcIsidEndptCvidClientMepEntry 1 }

rcIsidEndptCvidClientMepTlsIndex OBJECT-TYPE
        SYNTAX        Integer32 (1..2147483647)
        MAX-ACCESS    not-accessible
        STATUS        current
        DESCRIPTION   "Tls Index of an Isid Endpoint."
        ::= { rcIsidEndptCvidClientMepEntry 2 }

rcIsidEndptCvidClientMepCvid OBJECT-TYPE
        SYNTAX        Integer32 (1..4096) 
        MAX-ACCESS    not-accessible
        STATUS        current
        DESCRIPTION   "C-Vlan Id associate with the Isid Endpoint"
        ::= { rcIsidEndptCvidClientMepEntry 3 }

rcIsidEndptCvidClientMepMepList OBJECT-TYPE
        SYNTAX        OCTET STRING (SIZE(0..408))
        MAX-ACCESS    read-create
        STATUS        current
        DESCRIPTION   "List of Client Meps assigned to this entry. 
		       A client mep is consist of <md>.<ma>.<mep_id>. Domain
		       Name, Association and Mep Id is separated by '.' 
		       A list of mep is consist of 
		       <md1>.<ma1>.<mepid1>,<md2>.<ma2>.<mepid2>,... 
		       Each mep is separated by ','. Maximum up 8 meps"
        ::= { rcIsidEndptCvidClientMepEntry 4 }

rcIsidEndptCvidClientMepNumOfMep OBJECT-TYPE
        SYNTAX        	Integer32
        MAX-ACCESS      read-only
        STATUS        	current
        DESCRIPTION   	"Used to indicate the number of Client Meps
                      	is assigned to this entry"
        ::= { rcIsidEndptCvidClientMepEntry 5 }

rcIsidEndptCvidClientMepRowStatus OBJECT-TYPE
        SYNTAX          RowStatus
        MAX-ACCESS      read-create
        STATUS          current
        DESCRIPTION     "Row Create attibute. For perfomace and efficience, 
                         rcIsidEndptCvidClientMepMepList is required for creation.
			 If any Mip is added, entry would be created.
			 If all Mip are removed, entry would be deleted"
        ::= { rcIsidEndptCvidClientMepEntry 6 }

rcIsidEndptCvidClientMepPort  OBJECT-TYPE
        SYNTAX        InterfaceIndex
        MAX-ACCESS    read-create
        STATUS        current
        DESCRIPTION   "An index value that uniquely identifies a port."
        DEFVAL        { 1 }
        ::= { rcIsidEndptCvidClientMepEntry 7 }

rcIsidEndptCvidClientDownMepMepList OBJECT-TYPE
        SYNTAX        OCTET STRING (SIZE(0..408))
        MAX-ACCESS    read-create
        STATUS        current
        DESCRIPTION   "List of Client Down Meps assigned to this entry. 
		       A client mep is consist of <md>.<ma>.<mep_id>. Domain
		       Name, Association and Mep Id is separated by '.' 
		       A list of mep is consist of 
		       <md1>.<ma1>.<mepid1>,<md2>.<ma2>.<mepid2>,... 
		       Each mep is separated by ','. Maximum up 8 meps"
        ::= { rcIsidEndptCvidClientMepEntry 8 }

rcIsidEndptCvidClientDownMepNumOfMep OBJECT-TYPE
        SYNTAX        	Integer32
        MAX-ACCESS      read-only
        STATUS        	current
        DESCRIPTION   	"Used to indicate the number of Client Down Meps
                      	is assigned to this entry"
        ::= { rcIsidEndptCvidClientMepEntry 9 }

--
-- ISID NNI RATE LIMIT TABLE
--

rcIsidNniRateLimiterTable OBJECT-TYPE
        SYNTAX        SEQUENCE OF RcIsidNniRateLimiterEntry
        MAX-ACCESS    not-accessible
        STATUS        current
        DESCRIPTION   "802.1ah Service Identifier NNI Rate Limiter table"
        ::= { rc8021ah 6}

rcIsidNniRateLimiterEntry OBJECT-TYPE
        SYNTAX        RcIsidNniRateLimiterEntry
        MAX-ACCESS    not-accessible
        STATUS        current
        DESCRIPTION   ""
        INDEX         { rcIsidNniRateLimiterIsidId, 
			rcIsidNniRateLimiterSlotNumber, 
			rcIsidNniRateLimiterLaneNumber }
        ::= { rcIsidNniRateLimiterTable 1 }

RcIsidNniRateLimiterEntry ::=
        SEQUENCE {
                    rcIsidNniRateLimiterIsidId		INTEGER,
                    rcIsidNniRateLimiterSlotNumber	INTEGER,
                    rcIsidNniRateLimiterLaneNumber	INTEGER,
                    rcIsidNniRateLimiterRateLimit	INTEGER,
                    rcIsidNniRateLimiterRowStatus	RowStatus,
		    rcIsidNniRateLimiterClearStats	TruthValue
                 }

rcIsidNniRateLimiterIsidId 	OBJECT-TYPE
        SYNTAX        INTEGER (1..16777215)
        MAX-ACCESS    not-accessible
        STATUS        current
        DESCRIPTION   "Service Instance ID of the I component"
        ::= { rcIsidNniRateLimiterEntry 1 }

rcIsidNniRateLimiterSlotNumber	OBJECT-TYPE
	SYNTAX		INTEGER (1..10)
	MAX-ACCESS	not-accessible
	STATUS		current
	DESCRIPTION	"Slot number."
	::= { rcIsidNniRateLimiterEntry 2 }

rcIsidNniRateLimiterLaneNumber	OBJECT-TYPE
	SYNTAX		INTEGER (1..3)
	MAX-ACCESS	not-accessible
	STATUS		current
	DESCRIPTION	"Lane number. On a 30 Port 1G card (8630GBR),
			 Ports 1 to 10 are grouped under Lane 1, Ports
			 11 to 20 are grouped under Lane 2 and Ports 21
			 to 30 are grouped under Lane 3. For a 3 Port
			 10G card (8683XLR), Port 1 comes under Lane 1,
			 Port 2 comes under Lane 2 and Port 3 comes 
			 under Lane 3. For a 48 Port 1G card (8648GTR),
			 Ports 1 to 24 are grouped under Lane 1 and Ports
			 25 to 48 are grouped under Lane 2."
	::= { rcIsidNniRateLimiterEntry 3 }

rcIsidNniRateLimiterRateLimit	OBJECT-TYPE
	SYNTAX		INTEGER (1..10000)
	MAX-ACCESS	read-create
	STATUS		current
	DESCRIPTION	"Rate Limit in Mbps."
        DEFVAL          { 1 }
	::= { rcIsidNniRateLimiterEntry 4 }

rcIsidNniRateLimiterRowStatus	OBJECT-TYPE
	SYNTAX		RowStatus
	MAX-ACCESS	read-create
	STATUS		current
	DESCRIPTION	"Create/delete operations for this entry."
	::= { rcIsidNniRateLimiterEntry 5 }

rcIsidNniRateLimiterClearStats OBJECT-TYPE
        SYNTAX        TruthValue
        MAX-ACCESS    read-create
        STATUS        current
        DESCRIPTION   "Action to clear stats for
		      this Isid NNI Rate Limiter"
        DEFVAL        { false }
        ::= { rcIsidNniRateLimiterEntry 6 }

--
-- Isid NNI Rate Limiter Stats table
--

rcIsidNniRateLimiterStatsTable OBJECT-TYPE
        SYNTAX        SEQUENCE OF RcIsidNniRateLimiterStatsEntry
        MAX-ACCESS    not-accessible
        STATUS        current
        DESCRIPTION   "Isid Nni Rate Limiter statistics table."
        ::= { rc8021ah 7 }
 
rcIsidNniRateLimiterStatsEntry OBJECT-TYPE
        SYNTAX        RcIsidNniRateLimiterStatsEntry
        MAX-ACCESS    not-accessible
        STATUS        current
        DESCRIPTION   "A Isid Nni Rate Limiter Statistics table entry."
        INDEX         { rcIsidNniRateLimiterStatsIsidId, 
			rcIsidNniRateLimiterStatsSlotNumber, 
			rcIsidNniRateLimiterStatsLaneNumber }
        ::= { rcIsidNniRateLimiterStatsTable 1 }
 
RcIsidNniRateLimiterStatsEntry ::=
        SEQUENCE {
                rcIsidNniRateLimiterStatsIsidId			INTEGER,
                rcIsidNniRateLimiterStatsSlotNumber		INTEGER,
                rcIsidNniRateLimiterStatsLaneNumber		INTEGER,
                rcIsidNniRateLimiterStatsTotalRxOctets		Counter64,
                rcIsidNniRateLimiterStatsTotalRxDroppedOctets	Counter64,
                rcIsidNniRateLimiterStatsTotalRxPackets		Counter64,
                rcIsidNniRateLimiterStatsTotalRxDroppedPackets	Counter64
        }

rcIsidNniRateLimiterStatsIsidId		OBJECT-TYPE
        SYNTAX        INTEGER (1..16777215)
        MAX-ACCESS    not-accessible
        STATUS        current
        DESCRIPTION   "ISID Identifier."
        ::= { rcIsidNniRateLimiterStatsEntry 1 }
 
rcIsidNniRateLimiterStatsSlotNumber	OBJECT-TYPE
        SYNTAX        INTEGER (1..10) 
        MAX-ACCESS    not-accessible
        STATUS        current
        DESCRIPTION   "Slot Number."
        ::= { rcIsidNniRateLimiterStatsEntry 2 }
 
rcIsidNniRateLimiterStatsLaneNumber	OBJECT-TYPE
        SYNTAX        INTEGER (1..3)
        MAX-ACCESS    not-accessible
        STATUS        current
        DESCRIPTION   "Lane Number. On a 30 Port 1G card (8630GBR),
		      Ports 1 to 10 are grouped under Lane 1, Ports
		      11 to 20 are grouped under Lane 2 and Ports 21
		      to 30 are grouped under Lane 3. For a 3 Port
		      10G card (8683XLR), Port 1 comes under Lane 1,
		      Port 2 comes under Lane 2 and Port 3 comes 
		      under Lane 3. For a 48 Port 1G card (8648GTR),
		      Ports 1 to 24 are grouped under Lane 1 and Ports
		      25 to 48 are grouped under Lane 2."
        ::= { rcIsidNniRateLimiterStatsEntry 3 } 

rcIsidNniRateLimiterStatsTotalRxOctets	OBJECT-TYPE
        SYNTAX        Counter64
        MAX-ACCESS    read-only
        STATUS        current
        DESCRIPTION   "Total number of Octets received."
        ::= { rcIsidNniRateLimiterStatsEntry 4 } 
       
rcIsidNniRateLimiterStatsTotalRxDroppedOctets	OBJECT-TYPE
        SYNTAX        Counter64
        MAX-ACCESS    read-only
        STATUS        current
        DESCRIPTION   "Total number of Octets dropped."
        ::= { rcIsidNniRateLimiterStatsEntry 5 } 

rcIsidNniRateLimiterStatsTotalRxPackets		OBJECT-TYPE
        SYNTAX        Counter64
        MAX-ACCESS    read-only
        STATUS        current
        DESCRIPTION   "Total number of Packets received."
        ::= { rcIsidNniRateLimiterStatsEntry 6 } 
       

rcIsidNniRateLimiterStatsTotalRxDroppedPackets	OBJECT-TYPE
        SYNTAX        Counter64
        MAX-ACCESS    read-only
        STATUS        current
        DESCRIPTION   "Total number of Packets dropped."
        ::= { rcIsidNniRateLimiterStatsEntry 7 } 

-- TLSISID USER MAC Table

rcTlsIsidUserMacTable OBJECT-TYPE
        SYNTAX        SEQUENCE OF RcTlsIsidUserMacEntry
        MAX-ACCESS    not-accessible
        STATUS        current
        DESCRIPTION   "TLS ISID user mac table"
        ::= { rc8021ah 8 }

rcTlsIsidUserMacEntry OBJECT-TYPE
        SYNTAX        RcTlsIsidUserMacEntry
        MAX-ACCESS    not-accessible
        STATUS        current
        DESCRIPTION   "A TlsIsidUserMac table entry."
        INDEX         { rcTlsIsidUserMacIsidId, rcTlsIsidUserMacAddr  }
        ::= { rcTlsIsidUserMacTable 1 }

RcTlsIsidUserMacEntry ::=
        SEQUENCE {
                rcTlsIsidUserMacIsidId     Integer32,
                rcTlsIsidUserMacAddr       MacAddress,
                rcTlsIsidUserMacBmac       MacAddress,
                rcTlsIsidUserMacRowStatus  RowStatus
       }

rcTlsIsidUserMacIsidId OBJECT-TYPE
        SYNTAX        Integer32 (1..16777215)
        MAX-ACCESS    not-accessible
        STATUS        current
        DESCRIPTION   "Isid Id associated with this user Mac."
        ::= { rcTlsIsidUserMacEntry 1 }

rcTlsIsidUserMacAddr OBJECT-TYPE
        SYNTAX        MacAddress
        MAX-ACCESS    not-accessible
        STATUS        current
        DESCRIPTION   "User Mac address of this instance."
        ::= { rcTlsIsidUserMacEntry 2 }

rcTlsIsidUserMacBmac OBJECT-TYPE
        SYNTAX        MacAddress
        MAX-ACCESS    read-create
        STATUS        current
        DESCRIPTION   "BMAC of this instance mapped to the User Mac."
        ::= { rcTlsIsidUserMacEntry 3}

rcTlsIsidUserMacRowStatus OBJECT-TYPE
        SYNTAX        RowStatus
        MAX-ACCESS    read-create
        STATUS        current
        DESCRIPTION   "Used for controlling the creation and
                       deletion of this row."
        ::= { rcTlsIsidUserMacEntry 4 }

-- END OF TLS ISID USER MAC TABLE

---
--- Isid Video Merge-Point ACL table
---

rcIsidVideoMrgPtAclTable OBJECT-TYPE
        SYNTAX         SEQUENCE OF RcIsidVideoMrgPtAclEntry
        MAX-ACCESS     not-accessible
        STATUS         current
        DESCRIPTION    "Access control list at the merge point of Video and Target ISIDs"
        ::= { rc8021ah 9 }

rcIsidVideoMrgPtAclEntry OBJECT-TYPE
        SYNTAX         RcIsidVideoMrgPtAclEntry
        MAX-ACCESS     not-accessible
        STATUS         current
        DESCRIPTION    "Video merge point acl table entry for iptv support."
        INDEX           { rcIsidVideoMrgPtAclVideoIsidId,rcIsidVideoMrgPtAclTargetIsidId }
        ::= { rcIsidVideoMrgPtAclTable 1}

RcIsidVideoMrgPtAclEntry ::=
        SEQUENCE {
                 rcIsidVideoMrgPtAclVideoIsidId           Integer32,
                 rcIsidVideoMrgPtAclTargetIsidId          Integer32,
                 rcIsidVideoMrgPtAclAllowedGrpsListName   DisplayString,
                 rcIsidVideoMrgPtAclRowStatus             RowStatus
                 }

rcIsidVideoMrgPtAclVideoIsidId     OBJECT-TYPE
        SYNTAX        Integer32 (1..6777215)
        MAX-ACCESS    not-accessible
        STATUS        current
        DESCRIPTION   "Video Isid ID for video merge point acl"
        ::= { rcIsidVideoMrgPtAclEntry 1 }

rcIsidVideoMrgPtAclTargetIsidId    OBJECT-TYPE
        SYNTAX          Integer32 (1..16777215)
        MAX-ACCESS      not-accessible
        STATUS          current
        DESCRIPTION     "Target Isid ID for video merge point acl"
        ::= { rcIsidVideoMrgPtAclEntry 2 }

rcIsidVideoMrgPtAclAllowedGrpsListName       OBJECT-TYPE
       SYNTAX             DisplayString (SIZE(0..64))
       MAX-ACCESS         read-create
       STATUS             current
       DESCRIPTION        "Name of the IP prefix-list containing allowed multicast groups
                           for Video ISID/Target ISID pair"

       ::= {rcIsidVideoMrgPtAclEntry 3 }

rcIsidVideoMrgPtAclRowStatus   OBJECT-TYPE
        SYNTAX       RowStatus
        MAX-ACCESS   read-create
        STATUS       current
        DESCRIPTION   "Used for controlling the creation and
                       deletion of this row."
        ::= { rcIsidVideoMrgPtAclEntry 4 }

-- Isid Endpoint Cvid Client Mip

rcIsidEndptCvidClientMipTable OBJECT-TYPE
        SYNTAX        SEQUENCE OF RcIsidEndptCvidClientMipEntry
        MAX-ACCESS    not-accessible
        STATUS        current
        DESCRIPTION   "A table used to maintain CFM Client MIP 
                       assigned to the Isid Endpoint with Cvid"
        ::= { rc8021ah 10 }

rcIsidEndptCvidClientMipEntry OBJECT-TYPE
        SYNTAX        RcIsidEndptCvidClientMipEntry
        MAX-ACCESS    not-accessible
        STATUS        current
        DESCRIPTION   "An entry in the rcIsidEndptCvidClientMip table."
        INDEX         { rcIsidEndptCvidClientMipIsidId, rcIsidEndptCvidClientMipTlsIndex, rcIsidEndptCvidClientMipCvid}
        ::= { rcIsidEndptCvidClientMipTable 1 }

RcIsidEndptCvidClientMipEntry ::= SEQUENCE {
        rcIsidEndptCvidClientMipIsidId    Integer32,
        rcIsidEndptCvidClientMipTlsIndex  Integer32,
        rcIsidEndptCvidClientMipCvid      Integer32,
        rcIsidEndptCvidClientMipMipList   OCTET STRING,
        rcIsidEndptCvidClientMipNumOfMip  Integer32,
        rcIsidEndptCvidClientMipRowStatus RowStatus	
        }

rcIsidEndptCvidClientMipIsidId OBJECT-TYPE
        SYNTAX        Integer32 (1..16777215) 
        MAX-ACCESS    not-accessible
        STATUS        current
        DESCRIPTION   "Service Instance ID of the I component"
        ::= { rcIsidEndptCvidClientMipEntry 1 }

rcIsidEndptCvidClientMipTlsIndex OBJECT-TYPE
        SYNTAX        Integer32 (1..2147483647)
        MAX-ACCESS    not-accessible
        STATUS        current
        DESCRIPTION   "Tls Index of an Isid Endpoint."
        ::= { rcIsidEndptCvidClientMipEntry 2 }

rcIsidEndptCvidClientMipCvid OBJECT-TYPE
        SYNTAX        Integer32 (1..4096) 
        MAX-ACCESS    not-accessible
        STATUS        current
        DESCRIPTION   "C-Vlan Id associate with the Isid Endpoint"
        ::= { rcIsidEndptCvidClientMipEntry 3 }

rcIsidEndptCvidClientMipMipList OBJECT-TYPE
        SYNTAX        OCTET STRING (SIZE(0..408))
        MAX-ACCESS    read-create
        STATUS        current
        DESCRIPTION   "List of Client Mips assigned to this entry. 
		       A client mip is consist of <md>.<mip_id>. Domain
		       Name, Association and Mip Id is separated by '.' 
		       A list of mip is consist of 
		       <md1>.<mipid1>,<md2>.<mipid2>,... 
		       Each mip is separated by ','. Maximum up 8 mips"
        ::= { rcIsidEndptCvidClientMipEntry 4 }

rcIsidEndptCvidClientMipNumOfMip OBJECT-TYPE
        SYNTAX        	Integer32
        MAX-ACCESS      read-only
        STATUS        	current
        DESCRIPTION   	"Used to indicate the number of Client Mips
                      	is assigned to this entry"
        ::= { rcIsidEndptCvidClientMipEntry 5 }

rcIsidEndptCvidClientMipRowStatus OBJECT-TYPE
        SYNTAX          RowStatus
        MAX-ACCESS      read-create
        STATUS          current
        DESCRIPTION     "Row Create attibute. For perfomace and efficience, 
                         rcIsidEndptCvidClientMipMipList is required for creation.
			 If any Mip is added, entry would be created.
			 If all Mip are removed, entry would be deleted"
        ::= { rcIsidEndptCvidClientMipEntry 6 }

-- L2CP MIB section

rcL2cpMacBlockTable OBJECT-TYPE
		SYNTAX         SEQUENCE OF RcL2cpMacBlockEntry
		MAX-ACCESS     not-accessible
		STATUS         current
		DESCRIPTION    "L2CP MAC block table"
		::= { rc8021ah 11 }   

rcL2cpMacBlockEntry OBJECT-TYPE
		SYNTAX         RcL2cpMacBlockEntry
		MAX-ACCESS     not-accessible
		STATUS         current
		DESCRIPTION    "L2cp Mac Block Table Entry"
		INDEX          { rcL2cpMacBlockId }
		::= { rcL2cpMacBlockTable 1 }

RcL2cpMacBlockEntry ::=
        SEQUENCE {
                 rcL2cpMacBlockId               Integer32,
                 rcL2cpMacBlockName             DisplayString,
                 rcL2cpMacBlockStartMacAddr     MacAddress,
                 rcL2cpMacBlockEndMacAddr       MacAddress,
                 rcL2cpMacBlockRowStatus        RowStatus
                }

rcL2cpMacBlockId OBJECT-TYPE
		SYNTAX         Integer32 (1..8)
		MAX-ACCESS     not-accessible 
		STATUS         current
		DESCRIPTION    "L2cp Mac Block ID."
		::= { rcL2cpMacBlockEntry 1 }

rcL2cpMacBlockName  OBJECT-TYPE
                SYNTAX          DisplayString (SIZE (0..20))
                MAX-ACCESS      read-create
                STATUS          current
                DESCRIPTION     "L2CP MAC block name, by default it would
                                be 'MAC-BLOCK-<mac-block-ID>'"
                ::= { rcL2cpMacBlockEntry  2 }

rcL2cpMacBlockStartMacAddr OBJECT-TYPE
		SYNTAX          MacAddress
		MAX-ACCESS      read-create
		STATUS          current
		DESCRIPTION     "Start Mac Address of the L2cp Mac Block
				It must be a multicast MAC address."
		DEFVAL          { "00:00:00:00:00:00:00:00" }
		::= { rcL2cpMacBlockEntry  3 }

rcL2cpMacBlockEndMacAddr OBJECT-TYPE
		SYNTAX          MacAddress
		MAX-ACCESS      read-create
		STATUS          current
		DESCRIPTION     "End Mac Address of the L2cp Mac Block
				It must be a multicast MAC address."
		DEFVAL          { "00:00:00:00:00:00:00:00" }
		::= { rcL2cpMacBlockEntry  4 }

rcL2cpMacBlockRowStatus OBJECT-TYPE
                SYNTAX          RowStatus
                MAX-ACCESS      read-create
                STATUS          current
                DESCRIPTION     "Used for controlling the creation and
                                deletion of the MAC Block."
                ::= { rcL2cpMacBlockEntry 5 }

rcL2cpProfileTable OBJECT-TYPE       
		SYNTAX         SEQUENCE OF RcL2cpProfileEntry
		MAX-ACCESS     not-accessible
		STATUS         current
		DESCRIPTION    "L2CP Profile table."
		::= { rc8021ah 12 }
 
rcL2cpProfileEntry OBJECT-TYPE
		SYNTAX         RcL2cpProfileEntry
		MAX-ACCESS     not-accessible
		STATUS         current
		DESCRIPTION    "L2cp Profile Table Entry"
		INDEX          { rcL2cpProfileId }
		::= { rcL2cpProfileTable 1 }

RcL2cpProfileEntry ::=
        SEQUENCE {
                 rcL2cpProfileId               Integer32,
                 rcL2cpProfileName             DisplayString,
                 rcL2cpProfileApplyProfile     TruthValue, 
                 rcL2cpProfileForceDelete      TruthValue,
                 rcL2cpProfileRowStatus        RowStatus  
                }

rcL2cpProfileId OBJECT-TYPE
		SYNTAX         Integer32 (1..128)
		MAX-ACCESS     not-accessible
		STATUS         current
		DESCRIPTION    "L2CP Profile Id."
		::= { rcL2cpProfileEntry 1 }

rcL2cpProfileName OBJECT-TYPE
		SYNTAX         DisplayString (SIZE (0..20))
		MAX-ACCESS     read-create 
		STATUS         current
		DESCRIPTION    "L2CP Profile name."
		::= { rcL2cpProfileEntry 2 }

rcL2cpProfileApplyProfile OBJECT-TYPE
		SYNTAX         TruthValue
		MAX-ACCESS     read-create
		STATUS         current
		DESCRIPTION    " When apply is issued by the administrator, 
				all the changes made to the l2cp-profile will be
				reflected at the end-point and l2cp-profile 
				will be in Applied(true) state. Whenever any
				changes have been made to the profile, the state
				is changed to the Not Applied(false) state.If
				want these changes reflected at the end-point, 
				again issue the apply command."
		DEFVAL         { false }
		::= { rcL2cpProfileEntry 3 }

rcL2cpProfileForceDelete OBJECT-TYPE
		SYNTAX          TruthValue
		MAX-ACCESS      read-create
		STATUS          current
		DESCRIPTION     "Action to delete the L2cp-profile and change 
				the profile on all its associated end-points 
				to NULL_PROFILE"
		DEFVAL          {false}
		::= { rcL2cpProfileEntry 4 }

rcL2cpProfileRowStatus OBJECT-TYPE
                SYNTAX          RowStatus
                MAX-ACCESS      read-create
                STATUS          current
                DESCRIPTION     "Used for controlling the creation and deletion
                                of the row."
                ::= {  rcL2cpProfileEntry 5 }

rcL2cpProfileRuleTable OBJECT-TYPE  
		SYNTAX          SEQUENCE OF RcL2cpProfileRuleEntry
		MAX-ACCESS      not-accessible
		STATUS          current
		DESCRIPTION     "L2CP profile rule table"
		::= { rc8021ah 13  }

rcL2cpProfileRuleEntry OBJECT-TYPE
		SYNTAX          RcL2cpProfileRuleEntry
		MAX-ACCESS      not-accessible
		STATUS          current
		DESCRIPTION     "L2cp Profile Rule Table Entry"
		INDEX           { rcL2cpProfileRuleProfileId, rcL2cpProfileRuleId }
		::= { rcL2cpProfileRuleTable 1 }

RcL2cpProfileRuleEntry ::=
        SEQUENCE {
                 rcL2cpProfileRuleProfileId      Integer32,
                 rcL2cpProfileRuleId             Integer32,
                 rcL2cpProfileRuleProfileName    DisplayString,
                 rcL2cpProfileRuleMacBlockId     Integer32,
                 rcL2cpProfileRuleAction         INTEGER,
                 rcL2cpProfileRulePriority       Integer32,
                 rcL2cpProfileRuleRowStatus      RowStatus
                }

rcL2cpProfileRuleProfileId OBJECT-TYPE
		SYNTAX          Integer32 (1..128)
		MAX-ACCESS      not-accessible
		STATUS          current
		DESCRIPTION     "L2CP Profile ID."
		::=  { rcL2cpProfileRuleEntry 1 }

rcL2cpProfileRuleId  OBJECT-TYPE
		SYNTAX          Integer32 (1..8)
		MAX-ACCESS      not-accessible
		STATUS          current
		DESCRIPTION     "Rule Id added to the profile."
		::= { rcL2cpProfileRuleEntry 2 }

rcL2cpProfileRuleProfileName OBJECT-TYPE
		SYNTAX          DisplayString (SIZE (0..20)) 
		MAX-ACCESS      read-create 
		STATUS          current
		DESCRIPTION     "L2CP Profile name."
		::=  { rcL2cpProfileRuleEntry 3 }

rcL2cpProfileRuleMacBlockId OBJECT-TYPE
		SYNTAX          Integer32 (1..8)
		MAX-ACCESS      read-create
		STATUS          current
		DESCRIPTION     "L2cp-Mac-Block Id added to the rule. 
				Rule will define what action has to be applied
				to the L2CP packet having MAC address in the
				MAC Block range."
		::= { rcL2cpProfileRuleEntry 4 }

rcL2cpProfileRuleAction OBJECT-TYPE
		SYNTAX          INTEGER{
                                  normal(1),
                                  expedite(2),
                                  drop(3)
                                }
		MAX-ACCESS      read-create
		STATUS          current
		DESCRIPTION     "Action applied to L2CP packet. One of the 
				defined actions normal, expedite or drop can
				can be applied to the L2CP packet."
		DEFVAL          { normal }
		::= { rcL2cpProfileRuleEntry 5 }

rcL2cpProfileRulePriority OBJECT-TYPE
		SYNTAX          Integer32 (0..7)
		MAX-ACCESS      read-create
		STATUS          current
		DESCRIPTION     "l2cp mac block priority can be set only incase
				of expedite action."
		::= { rcL2cpProfileRuleEntry 6 }
                 
rcL2cpProfileRuleRowStatus OBJECT-TYPE
                SYNTAX          RowStatus
                MAX-ACCESS      read-create
                STATUS          current
                DESCRIPTION     "Used for controlling the creation and
                                deletion of the row."
                ::= { rcL2cpProfileRuleEntry 7 }

-- Isid Management isid endpoint table

rcIsidMgmtEndptTable OBJECT-TYPE
        SYNTAX        SEQUENCE OF RcIsidMgmtEndptEntry
        MAX-ACCESS    not-accessible
        STATUS        current
        DESCRIPTION   "Table of Management-endpoint entries."
        ::= { rc8021ah 14 }

rcIsidMgmtEndptEntry OBJECT-TYPE
        SYNTAX        RcIsidMgmtEndptEntry
        MAX-ACCESS    not-accessible
        STATUS        current
        DESCRIPTION   "Management Endpoint table entry."
        INDEX         { rcIsidMgmtEndptIsidId,rcIsidMgmtEndptTlsIndex }
        ::= { rcIsidMgmtEndptTable 1 }

RcIsidMgmtEndptEntry ::=
        SEQUENCE {
                  rcIsidMgmtEndptIsidId            Integer32,
                  rcIsidMgmtEndptTlsIndex          Integer32,
                  rcIsidMgmtEndptPort              InterfaceIndexOrZero,
                  rcIsidMgmtEndptMltId             Integer32,
                  rcIsidMgmtEndptServiceType       INTEGER,
                  rcIsidMgmtEndptOuterQtag         Integer32,
                  rcIsidMgmtEndptDataIsid          Integer32
                  }

rcIsidMgmtEndptIsidId OBJECT-TYPE
        SYNTAX        Integer32 (1..16777215)
        MAX-ACCESS    not-accessible
        STATUS        current
        DESCRIPTION   "The management isid on which endpoint is configured"
        ::= { rcIsidMgmtEndptEntry 1 }


rcIsidMgmtEndptTlsIndex OBJECT-TYPE
        SYNTAX        Integer32 (1..2147483647)
        MAX-ACCESS    not-accessible
        STATUS        current
        DESCRIPTION   "TLS Index for Isid Endpoint, the NID 
	               functionality is supported only on Port and MLT endpoints
		       The port and MLT-Id can be derived from 32 bits in TlsIndex"
        ::= { rcIsidMgmtEndptEntry 2 }

rcIsidMgmtEndptPort OBJECT-TYPE
        SYNTAX        InterfaceIndexOrZero
        MAX-ACCESS    read-only
        STATUS        current
        DESCRIPTION   "The port on which management endpoint is configured. The value is zero for MLT based endpoint."
        DEFVAL        { 0 }
        ::= { rcIsidMgmtEndptEntry 3 }

rcIsidMgmtEndptMltId  OBJECT-TYPE
        SYNTAX      Integer32 (0..256)
        MAX-ACCESS    read-only
        STATUS        current
        DESCRIPTION   "MLT Id of the ISID, the value is zero for port based endpoint"
        DEFVAL        { 0 }
        ::= { rcIsidMgmtEndptEntry 4 }

rcIsidMgmtEndptOuterQtag OBJECT-TYPE
        SYNTAX        Integer32 (0..4094)
        MAX-ACCESS    read-only
        STATUS        current
        DESCRIPTION   "S-vlan (outer-qtag) of management endpoint configured in case of endpoint service type qnq1"
        ::= { rcIsidMgmtEndptEntry 5 }

rcIsidMgmtEndptServiceType OBJECT-TYPE
        SYNTAX        INTEGER {
                          transparent (1),
                          qnq1(2)
                          }
        MAX-ACCESS    read-only
        STATUS        current
        DESCRIPTION   "Service type of management isid endpoint"
        ::= { rcIsidMgmtEndptEntry 6 }


rcIsidMgmtEndptDataIsid OBJECT-TYPE
        SYNTAX        Integer32 (0..16777215)
        MAX-ACCESS    read-only
        STATUS        current
        DESCRIPTION   "Data isid corresponding to management isid on which management isid endpoint is configured. Data Isid of value 0 indicates that there is no corresponding Data Isid present for management Isid."
        ::= { rcIsidMgmtEndptEntry 7 }

rcL2cpProfileTableSize OBJECT-TYPE
                SYNTAX        Integer32   
                MAX-ACCESS    read-only
                STATUS        current
                DESCRIPTION   "Used to indicate the number of entries in the
                               rcL2cpProfileTable"
                ::= { rc8021ah 15 }

-- Pwe3 endpoint table

rcPwEndptTable OBJECT-TYPE
        SYNTAX        SEQUENCE OF RcPwEndptEntry
        MAX-ACCESS    not-accessible
        STATUS        current
        DESCRIPTION   ""
        ::= { rcPwe3 1 }
 
rcPwEndptEntry OBJECT-TYPE
        SYNTAX        RcPwEndptEntry
        MAX-ACCESS    not-accessible
        STATUS        current
        DESCRIPTION   "A Customer Endpoint table entry."
        INDEX         { rcPwEndptPwIndex, rcPwEndptTlsIndex }
        ::= { rcPwEndptTable 1 }
 
RcPwEndptEntry ::=
        SEQUENCE {
                 rcPwEndptPwIndex                  INTEGER,
                 rcPwEndptTlsIndex                 INTEGER,
                 rcPwEndptPort                     InterfaceIndex,
                 rcPwEndptQtags                    OCTET STRING,
                 rcPwEndptNumQtagIds               Integer32,      
                 rcPwEndptOuterQtag                INTEGER,
                 rcPwEndptConnectType              INTEGER,
                 rcPwEndptAdminState               EnableValue,
                 rcPwEndptRemoteMacAddr            MacAddress,
                 rcPwEndptIngressCosProfileName    DisplayString,
                 rcPwEndptEgressCosProfileName     DisplayString,
                 rcPwEndptIngressPolicer           EnableValue,
                 rcPwEndptEgressPolicer            EnableValue,
                 rcPwEndptPriMapping               OCTET STRING,
                 rcPwEndptName                     DisplayString,
                 rcPwEndptOperState                INTEGER,
                 rcPwEndptPriOverride              TruthValue,
                 rcPwEndptBpduTraffic              INTEGER,        
                 rcPwEndptRowStatus                RowStatus,
                 rcPwEndptClearStats               TruthValue,
                 rcPwEndptServiceType              INTEGER,
                 rcPwEndptMuxMode                  INTEGER,
                 rcPwEndptInVcLabel                INTEGER,
                 rcPwEndptOutVcLabel               INTEGER,
                 rcPwEndptCwPreference             TruthValue,
                 rcPwEndptNextHopMac               MacAddress,
                 rcPwEndptTrunkGroupName           DisplayString,
		 rcPwEndptMepList   		   OCTET STRING,
		 rcPwEndptNumOfMep  		   Integer32,
		 rcPwEndptClientMepList   	   OCTET STRING,
		 rcPwEndptNumOfClientMep  	   Integer32,
                 rcPwEndptCcmOperStatus            INTEGER,
		 rcPwEndptPolicingOption	   INTEGER,
                 rcPwEndptPriOverrideType          INTEGER,
                 rcPwEndptColorBasedRemarking      EnableValue,
                 rcPwEndptDropRedColorPackets      TruthValue,
		 rcPwEndptUserLabel1 	           OCTET STRING,
 		 rcPwEndptUserLabel2 	           OCTET STRING,
		 rcPwEndptIngressMirrorState       EnableValue,
                 rcPwEndptEgressMirrorState        EnableValue,
                 rcPwEndptMltId                    INTEGER
                 }

rcPwEndptPwIndex    OBJECT-TYPE 
        SYNTAX        INTEGER (1..16777215)
        MAX-ACCESS    not-accessible
        STATUS        current
        DESCRIPTION   "PW table index number."
        ::= { rcPwEndptEntry 1 }

rcPwEndptTlsIndex OBJECT-TYPE
        SYNTAX        INTEGER (1..2147483647)
        MAX-ACCESS    not-accessible
        STATUS        current
        DESCRIPTION   "TLS Index"
        ::= { rcPwEndptEntry 2 }

rcPwEndptPort  OBJECT-TYPE
        SYNTAX        InterfaceIndex
        MAX-ACCESS    read-create
        STATUS        current
        DESCRIPTION   "An index value that uniquely identifies a port."
        DEFVAL        { 1 }
        ::= { rcPwEndptEntry 3 }

rcPwEndptQtags  OBJECT-TYPE
        SYNTAX        OCTET STRING (SIZE(512))
        MAX-ACCESS    read-create
        STATUS        current
        DESCRIPTION   "This bitfield indicates which Qtags (in the range
		      1 to 4096) are associated with this end-point. 
		      The Most Significant (left-most) Bit represents Qtag 1.
		      The Least Significant Bit represents Qtag 4096."
        ::= { rcPwEndptEntry 4 }

rcPwEndptNumQtagIds  OBJECT-TYPE
        SYNTAX          Integer32
        MAX-ACCESS      read-only
        STATUS          current
        DESCRIPTION     "Used to indicate the number of Qtag IDs that
                        are stored in the rcPwEndptQtags variable."
        ::= { rcPwEndptEntry 5 }

rcPwEndptOuterQtag OBJECT-TYPE
        SYNTAX        INTEGER (0..4094) 
        MAX-ACCESS    read-create
        STATUS        current
        DESCRIPTION   "Outer qtag for QinQ ISID endpoint"
        DEFVAL        { 0 }
        ::= { rcPwEndptEntry 6 }

rcPwEndptConnectType OBJECT-TYPE
        SYNTAX        INTEGER {
                          any2any (1),
                          hub     (2),
                          spoke   (3),
                          pt2pt   (4)
                         }
        MAX-ACCESS    read-create
        STATUS        current
        DESCRIPTION   "Type of end-point"
        DEFVAL       { pt2pt }
        ::= { rcPwEndptEntry 7 }

rcPwEndptAdminState OBJECT-TYPE
        SYNTAX        EnableValue
        MAX-ACCESS    read-create
        STATUS        current
        DESCRIPTION   "Admin control of the end-point state."
        DEFVAL        { disable }
        ::= { rcPwEndptEntry 8 }

rcPwEndptRemoteMacAddr OBJECT-TYPE
        SYNTAX        MacAddress
        MAX-ACCESS    read-create
        STATUS        current
        DESCRIPTION   "A remote MAC address of other endpoint "
        ::= { rcPwEndptEntry 9 }

rcPwEndptIngressCosProfileName OBJECT-TYPE
        SYNTAX        DisplayString (SIZE (0..20)) 
        MAX-ACCESS    read-create
        STATUS        current
        DESCRIPTION   "COS Profile Table Name which is used by
                       this endpoint as ingress policer"
        DEFVAL       { "DEFAULT_PROFILE"  } 
        ::= { rcPwEndptEntry 10 }

rcPwEndptEgressCosProfileName OBJECT-TYPE
        SYNTAX        DisplayString (SIZE (0..20)) 
        MAX-ACCESS    read-create
        STATUS        current
        DESCRIPTION   "COS Profile Table Name which is used by 
                       this endpoint as egress policer"
        DEFVAL       { "DEFAULT_PROFILE"  } 
        ::= { rcPwEndptEntry 11 }

rcPwEndptIngressPolicer OBJECT-TYPE
        SYNTAX        EnableValue
        MAX-ACCESS    read-create
        STATUS        current
        DESCRIPTION   "Enable/disable to use Ingress Cos Profile table 
                        (rcPwEndptCosProfileName) "
        DEFVAL        { enable }
        ::= { rcPwEndptEntry 12 }

rcPwEndptEgressPolicer OBJECT-TYPE
        SYNTAX        EnableValue
        MAX-ACCESS    read-create
        STATUS        current
        DESCRIPTION   "Enable/disable to use Egress Cos Profile table 
                        (rcPwEndptEgressCosProfileName) "
        DEFVAL        { disable }
        ::= { rcPwEndptEntry 13 }

rcPwEndptPriMapping OBJECT-TYPE
        SYNTAX        OCTET STRING (SIZE(8))
        MAX-ACCESS    read-create
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcPwEndptEntry 14 }

rcPwEndptName       OBJECT-TYPE
        SYNTAX        DisplayString (SIZE (0..30)) 
        MAX-ACCESS    read-create
        STATUS        current
        DESCRIPTION   "Name of Endpoint, By default, it would be 
                       'EP-<sid> Port <PortNum>'.
                       Example: sid = 1, port = 1/2, rcPwEndptName would
                       be 'EP-1 PORT 1/2'"
        ::= { rcPwEndptEntry 15 }

rcPwEndptOperState  OBJECT-TYPE
        SYNTAX        INTEGER { 
                          up(1), 
                          down(2),
			  transport-down(3) 
                       }
        MAX-ACCESS    read-only
        STATUS        current
        DESCRIPTION   "The current operational state of this ENDPOINT."
        ::= { rcPwEndptEntry 16 }

rcPwEndptPriOverride OBJECT-TYPE
        SYNTAX          TruthValue
        MAX-ACCESS      read-create
        STATUS          current
        DESCRIPTION     "Enable or disable to override the Priority Mapping."
        DEFVAL          { false }
        ::= { rcPwEndptEntry 17 }

rcPwEndptBpduTraffic OBJECT-TYPE
        SYNTAX          INTEGER {
                        normal(1),
                        expedite(2),
                        drop(3)
                        }
        MAX-ACCESS      read-create
        STATUS          current
        DESCRIPTION     "Bpdu traffic control."
        DEFVAL          { normal }
        ::= { rcPwEndptEntry 18 }

rcPwEndptRowStatus  OBJECT-TYPE
        SYNTAX        RowStatus
        MAX-ACCESS    read-create
        STATUS        current
        DESCRIPTION   "Uses for controlling the creation and
                       deletion of this row."
        ::= { rcPwEndptEntry 19 }

rcPwEndptClearStats OBJECT-TYPE
        SYNTAX        TruthValue
        MAX-ACCESS    read-create
        STATUS        current
        DESCRIPTION   "Clear Endpoint statistics."
        DEFVAL        { false }
        ::= { rcPwEndptEntry 20 } 

rcPwEndptServiceType OBJECT-TYPE
        SYNTAX         INTEGER {
                          transparent (1),
                          switched(2),
                          qnq1(3),
                          qnq2(4),
                          mpls(5)
                         } 
        MAX-ACCESS     read-create 
        STATUS         current
        DESCRIPTION    "service type of the end-point. It is also
                        releated with."
        DEFVAL         { switched }
        ::= { rcPwEndptEntry 21 }

rcPwEndptMuxMode  OBJECT-TYPE 
        SYNTAX      INTEGER {
                       oneToone(1),       -- Only one qtag as member
                       manyToOne(2)       -- Many qtags as member
                      }
        MAX-ACCESS    read-create
        STATUS        current
        DESCRIPTION   "An endpoint can have many qtags mapped to it
                       only if the MuxMode is set to manyToOne. For
                       a manyToOne i-sid there will not be any
                       remapping of qtags at the local egress."
        DEFVAL        { oneToone }
        ::= { rcPwEndptEntry 22 }

rcPwEndptInVcLabel  OBJECT-TYPE
        SYNTAX        INTEGER (0..1048575)
        MAX-ACCESS    read-create
        STATUS        current
        DESCRIPTION   "Incoming vc label."
        DEFVAL        { 0 }
        ::= { rcPwEndptEntry 23 }

rcPwEndptOutVcLabel OBJECT-TYPE
        SYNTAX        INTEGER (0..1048575)
        MAX-ACCESS    read-create
        STATUS        current
        DESCRIPTION   "Outgoing vc label."
        DEFVAL        { 0 }
        ::= { rcPwEndptEntry 24 }

rcPwEndptCwPreference OBJECT-TYPE
        SYNTAX        TruthValue
        MAX-ACCESS    read-create
        STATUS        current
        DESCRIPTION   "Control word supported or unsupported."
        DEFVAL        { true }
        ::= { rcPwEndptEntry 25 }

rcPwEndptNextHopMac OBJECT-TYPE
        SYNTAX        MacAddress
        MAX-ACCESS    read-create
        STATUS        current
        DESCRIPTION   "Nexthop Mac address."
        ::= { rcPwEndptEntry 26 }

rcPwEndptTrunkGroupName OBJECT-TYPE
        SYNTAX	      DisplayString (SIZE (0..32))
        MAX-ACCESS    read-create
        STATUS        current
        DESCRIPTION   "PBT Trunk Group Name."
        ::= { rcPwEndptEntry 27 }

rcPwEndptMepList OBJECT-TYPE
        SYNTAX        OCTET STRING (SIZE (0..408))
        MAX-ACCESS    read-create
        STATUS        current
        DESCRIPTION   "List of Meps assigned to this entry. 
                       A mep is consist of <md>.<ma>.<mep_id>. Domain
                       Name, Association and Mep Id is separated by '.' 
                       A list of mep is consist of 
                       <md1>.<ma1>.<mepid1>,<md2>.<ma2>.<mepid2>,... 
                       Each mep is separated by ','. Maximum up 8 meps"
        ::= { rcPwEndptEntry 28 }

rcPwEndptNumOfMep OBJECT-TYPE
        SYNTAX        Integer32
        MAX-ACCESS    read-only
        STATUS        current
        DESCRIPTION   "Used to indicate the number of Meps
                       is assigned to this entry"
        ::= { rcPwEndptEntry 29 }

rcPwEndptClientMepList OBJECT-TYPE
        SYNTAX        OCTET STRING (SIZE (0..408))
        MAX-ACCESS    read-create
        STATUS        current
        DESCRIPTION   "List of Client Meps assigned to this entry. 
                       A client mep is consist of <md>.<ma>.<mep_id>. Domain
                       Name, Association and Mep Id is separated by '.' 
                       A list of client meps is consist of 
                       <md1>.<ma1>.<mepid1>,<md2>.<ma2>.<mepid2>,... 
                       Each mep is separated by ','. Maximum up 8 meps"
        ::= { rcPwEndptEntry 30 }

rcPwEndptNumOfClientMep OBJECT-TYPE
        SYNTAX        Integer32
        MAX-ACCESS    read-only
        STATUS        current
        DESCRIPTION   "Used to indicate the number of Client Meps
                       is assigned to this entry"
        ::= { rcPwEndptEntry 31 }

rcPwEndptCcmOperStatus OBJECT-TYPE
        SYNTAX        INTEGER { 
                          up(1), 
                          down(2)
                      }
        MAX-ACCESS    read-only
        STATUS        current
        DESCRIPTION   "The current CCM operational status of this endpoint."
        ::= { rcPwEndptEntry 32 }
rcPwEndptPolicingOption	OBJECT-TYPE
	SYNTAX	      INTEGER { 
			preEncap(1), 
			postEncap(2)
		      }
	MAX-ACCESS    read-create
	STATUS	      current
	DESCRIPTION   "Specify whether the policing is pre-encapsulation 
		       or post-encapsulation for Pseudo Wire Endpoints."
	::= { rcPwEndptEntry 33 }


rcPwEndptPriOverrideType OBJECT-TYPE
        SYNTAX        INTEGER
                      {
                         tos(1),
                         dscp(2),
			 mplsexp(3)
                      }
        MAX-ACCESS    read-create
        STATUS        current
        DESCRIPTION   "This field indicated whether ToS or DSCP should be
                       used to override P bit when override is enabled."
        DEFVAL        { tos }
        ::= { rcPwEndptEntry 34 }

rcPwEndptColorBasedRemarking OBJECT-TYPE
        SYNTAX        EnableValue
        MAX-ACCESS    read-create
        STATUS        current
        DESCRIPTION   "disable/enable color-based egress mapping for this
                      end-point."
        DEFVAL        { disable }
        ::= { rcPwEndptEntry 35 }

rcPwEndptDropRedColorPackets OBJECT-TYPE
        SYNTAX        TruthValue
        MAX-ACCESS    read-create
        STATUS        current
        DESCRIPTION   "disable/enable dropping of red-colored packets for
                      this end-point if color-based mapping is used."
        DEFVAL        { true }
        ::= { rcPwEndptEntry 36}

rcPwEndptUserLabel1 OBJECT-TYPE
 	SYNTAX          OCTET STRING (SIZE(0..89))
        MAX-ACCESS      read-create
        STATUS          current
        DESCRIPTION     "User provided field. Used to give extra management information/data "
        ::= { rcPwEndptEntry 37 }

rcPwEndptUserLabel2 OBJECT-TYPE
 	SYNTAX          OCTET STRING (SIZE(0..89))
        MAX-ACCESS      read-create
        STATUS          current
        DESCRIPTION     "User provided additional field. Used to give extra management information/data "
        ::= { rcPwEndptEntry 38 }

rcPwEndptIngressMirrorState OBJECT-TYPE
        SYNTAX        EnableValue
        MAX-ACCESS    read-create
        STATUS        current
        DESCRIPTION   "Disable/enable ingress mirroring on this end-point."
        DEFVAL        { disable }
        ::= { rcPwEndptEntry 39 }

rcPwEndptEgressMirrorState OBJECT-TYPE
        SYNTAX        EnableValue
        MAX-ACCESS    read-create
        STATUS        current
        DESCRIPTION   "Disable/enable egress mirroring on this end-point."
        DEFVAL        { disable }
        ::= { rcPwEndptEntry 40 }

rcPwEndptMltId  OBJECT-TYPE
        SYNTAX      INTEGER (0..256)
        MAX-ACCESS    read-create
        STATUS        current
        DESCRIPTION   "MLT Id of this endpoint"
        DEFVAL        { 0 }
        ::= { rcPwEndptEntry 41 }


-- Pwe3 endpoint stats table

rcPwEndptStatsTable OBJECT-TYPE
        SYNTAX        SEQUENCE OF RcPwEndptStatsEntry
        MAX-ACCESS    not-accessible
        STATUS        current
        DESCRIPTION   ""
        ::= { rcPwe3 2 }

rcPwEndptStatsEntry OBJECT-TYPE
        SYNTAX        RcPwEndptStatsEntry
        MAX-ACCESS    not-accessible
        STATUS        current
        DESCRIPTION   "A Pw End-Point Statistics  table entry."
        INDEX         { rcPwEndptStatsPwIndex, rcPwEndptStatsTlsIndex }
        ::= { rcPwEndptStatsTable 1 }

RcPwEndptStatsEntry ::=
        SEQUENCE {
                rcPwEndptStatsPwIndex                      INTEGER,
                rcPwEndptStatsTlsIndex                     INTEGER,
                rcPwEndptStatsPort                         InterfaceIndex,
                rcPwEndptStatsPremRxOctets                 Counter64,
                rcPwEndptStatsPremRxDroppedOctets          Counter64,
                rcPwEndptStatsGoldRxOctets                 Counter64,
                rcPwEndptStatsGoldRxDroppedOctets          Counter64,
                rcPwEndptStatsSilverRxOctets               Counter64,
                rcPwEndptStatsSilverRxDroppedOctets        Counter64,
                rcPwEndptStatsStndRxOctets                 Counter64,
                rcPwEndptStatsStndRxDroppedOctets          Counter64,
                rcPwEndptStatsPremTxOctets                 Counter64,
                rcPwEndptStatsGoldTxOctets                 Counter64,
                rcPwEndptStatsSilverTxOctets               Counter64,
                rcPwEndptStatsStndTxOctets                 Counter64,
                rcPwEndptStatsPremTxMcastOctets            Counter64,
                rcPwEndptStatsGoldTxMcastOctets            Counter64,
                rcPwEndptStatsSilverTxMcastOctets          Counter64,
                rcPwEndptStatsStndTxMcastOctets            Counter64,
                rcPwEndptStatsPremCongestionDropOctets     Counter64,
                rcPwEndptStatsGoldCongestionDropOctets     Counter64,
                rcPwEndptStatsSilverCongestionDropOctets   Counter64,
                rcPwEndptStatsStndCongestionDropOctets     Counter64,
                rcPwEndptStatsPremCirDroppedOctets         Counter64,
                rcPwEndptStatsPremPirDroppedOctets         Counter64,
                rcPwEndptStatsGoldCirDroppedOctets         Counter64,
                rcPwEndptStatsGoldPirDroppedOctets         Counter64,
                rcPwEndptStatsSilverCirDroppedOctets       Counter64,
                rcPwEndptStatsSilverPirDroppedOctets       Counter64,
                rcPwEndptStatsStndCirDroppedOctets         Counter64,
                rcPwEndptStatsStndPirDroppedOctets         Counter64,
                rcPwEndptStatsName                         DisplayString,
                rcPwEndptStatsPremTxDroppedOctets          Counter64,
                rcPwEndptStatsGoldTxDroppedOctets          Counter64,
                rcPwEndptStatsSilverTxDroppedOctets        Counter64,
                rcPwEndptStatsStndTxDroppedOctets          Counter64,
                rcPwEndptStatsPremTxCongestionDropOctets   Counter64,
                rcPwEndptStatsGoldTxCongestionDropOctets   Counter64,
                rcPwEndptStatsSilverTxCongestionDropOctets Counter64,
                rcPwEndptStatsStndTxCongestionDropOctets   Counter64,
                rcPwEndptStatsPremTxCirDroppedOctets       Counter64,
                rcPwEndptStatsPremTxPirDroppedOctets       Counter64,
                rcPwEndptStatsGoldTxCirDroppedOctets       Counter64,
                rcPwEndptStatsGoldTxPirDroppedOctets       Counter64,
                rcPwEndptStatsSilverTxCirDroppedOctets     Counter64,
                rcPwEndptStatsSilverTxPirDroppedOctets     Counter64,
                rcPwEndptStatsStndTxCirDroppedOctets       Counter64,
                rcPwEndptStatsStndTxPirDroppedOctets       Counter64,
                rcPwEndptStatsRxMcastTotalOctets           Counter64,
                rcPwEndptStatsTxMcastTotalOctets           Counter64,
                rcPwEndptStatsPremRxMcastDroppedOctets     Counter64,
                rcPwEndptStatsGoldRxMcastDroppedOctets     Counter64,
                rcPwEndptStatsSilverRxMcastDroppedOctets   Counter64,
                rcPwEndptStatsStndRxMcastDroppedOctets     Counter64,
rcPwEndptStatsPremRxFrames                 Counter64,
                rcPwEndptStatsPremRxDroppedFrames          Counter64,
                rcPwEndptStatsGoldRxFrames                 Counter64,
                rcPwEndptStatsGoldRxDroppedFrames          Counter64,
                rcPwEndptStatsSilverRxFrames               Counter64,
                rcPwEndptStatsSilverRxDroppedFrames        Counter64,
                rcPwEndptStatsStndRxFrames                 Counter64,
                rcPwEndptStatsStndRxDroppedFrames          Counter64,
                rcPwEndptStatsPremTxFrames                 Counter64,
                rcPwEndptStatsGoldTxFrames                 Counter64,
                rcPwEndptStatsSilverTxFrames               Counter64,
                rcPwEndptStatsStndTxFrames                 Counter64,
                rcPwEndptStatsPremTxMcastFrames            Counter64,
                rcPwEndptStatsGoldTxMcastFrames            Counter64,
                rcPwEndptStatsSilverTxMcastFrames          Counter64,
                rcPwEndptStatsStndTxMcastFrames            Counter64,
                rcPwEndptStatsPremCongestionDropFrames     Counter64,
                rcPwEndptStatsGoldCongestionDropFrames     Counter64,
                rcPwEndptStatsSilverCongestionDropFrames   Counter64,
                rcPwEndptStatsStndCongestionDropFrames     Counter64,
                rcPwEndptStatsPremCirDroppedFrames         Counter64,
                rcPwEndptStatsPremPirDroppedFrames         Counter64,
                rcPwEndptStatsGoldCirDroppedFrames         Counter64,
                rcPwEndptStatsGoldPirDroppedFrames         Counter64,
                rcPwEndptStatsSilverCirDroppedFrames       Counter64,
                rcPwEndptStatsSilverPirDroppedFrames       Counter64,
                rcPwEndptStatsStndCirDroppedFrames         Counter64,
                rcPwEndptStatsStndPirDroppedFrames         Counter64,
                rcPwEndptStatsPremTxDroppedFrames          Counter64,
                rcPwEndptStatsGoldTxDroppedFrames          Counter64,
                rcPwEndptStatsSilverTxDroppedFrames        Counter64,
                rcPwEndptStatsStndTxDroppedFrames          Counter64,
                rcPwEndptStatsPremTxCongestionDropFrames   Counter64,
                rcPwEndptStatsGoldTxCongestionDropFrames   Counter64,
                rcPwEndptStatsSilverTxCongestionDropFrames Counter64,
                rcPwEndptStatsStndTxCongestionDropFrames   Counter64,
                rcPwEndptStatsPremTxCirDroppedFrames       Counter64,
                rcPwEndptStatsPremTxPirDroppedFrames       Counter64,
                rcPwEndptStatsGoldTxCirDroppedFrames       Counter64,
                rcPwEndptStatsGoldTxPirDroppedFrames       Counter64,
                rcPwEndptStatsSilverTxCirDroppedFrames     Counter64,
                rcPwEndptStatsSilverTxPirDroppedFrames     Counter64,
                rcPwEndptStatsStndTxCirDroppedFrames       Counter64,
                rcPwEndptStatsStndTxPirDroppedFrames       Counter64,
                rcPwEndptStatsRxMcastTotalFrames           Counter64,
                rcPwEndptStatsTxMcastTotalFrames           Counter64,
                rcPwEndptStatsPremRxMcastDroppedFrames     Counter64,
                rcPwEndptStatsGoldRxMcastDroppedFrames     Counter64,
                rcPwEndptStatsSilverRxMcastDroppedFrames   Counter64,
                rcPwEndptStatsStndRxMcastDroppedFrames     Counter64
      }

rcPwEndptStatsPwIndex OBJECT-TYPE
        SYNTAX        INTEGER (1..16777215)
        MAX-ACCESS    not-accessible
        STATUS        current
        DESCRIPTION   "Pw that the end-point is a member of."
        ::= { rcPwEndptStatsEntry 1 }

rcPwEndptStatsTlsIndex OBJECT-TYPE
        SYNTAX        INTEGER (1..2147483647)
        MAX-ACCESS    not-accessible
        STATUS        current
        DESCRIPTION   "TLS Index"
        ::= { rcPwEndptStatsEntry 2 }

rcPwEndptStatsPort OBJECT-TYPE
        SYNTAX        InterfaceIndex
        MAX-ACCESS    read-only
        STATUS        current
        DESCRIPTION   "Port Identifier."
        ::= { rcPwEndptStatsEntry 3 }

rcPwEndptStatsPremRxOctets OBJECT-TYPE
        SYNTAX        Counter64
        MAX-ACCESS    read-only
        STATUS        current
        DESCRIPTION  "Number of Premium Service Octets received."
        ::= { rcPwEndptStatsEntry 4 }

rcPwEndptStatsPremRxDroppedOctets OBJECT-TYPE
        SYNTAX        Counter64
        MAX-ACCESS    read-only
        STATUS        current
        DESCRIPTION  "Number of Premium Service Octets dropped."
        ::= { rcPwEndptStatsEntry 5 }

rcPwEndptStatsGoldRxOctets OBJECT-TYPE
        SYNTAX        Counter64
        MAX-ACCESS    read-only
        STATUS        current
        DESCRIPTION  "Number of Gold Service Octets received."
        ::= { rcPwEndptStatsEntry 6 }

rcPwEndptStatsGoldRxDroppedOctets OBJECT-TYPE
        SYNTAX        Counter64
        MAX-ACCESS    read-only
        STATUS        current
        DESCRIPTION  "Number of Gold Service Octets dropped."
        ::= { rcPwEndptStatsEntry 7 }

rcPwEndptStatsSilverRxOctets OBJECT-TYPE
        SYNTAX        Counter64
        MAX-ACCESS    read-only
        STATUS        current
        DESCRIPTION  "Number of Silver Service Octets received."
        ::= { rcPwEndptStatsEntry 8 }

rcPwEndptStatsSilverRxDroppedOctets OBJECT-TYPE
        SYNTAX        Counter64
        MAX-ACCESS    read-only
        STATUS        current
        DESCRIPTION  "Number of Silver Service Octets dropped."
        ::= { rcPwEndptStatsEntry 9 }

rcPwEndptStatsStndRxOctets OBJECT-TYPE
        SYNTAX        Counter64
        MAX-ACCESS    read-only
        STATUS        current
        DESCRIPTION  "Number of Standard Service Octets received."
        ::= { rcPwEndptStatsEntry 10 }

rcPwEndptStatsStndRxDroppedOctets OBJECT-TYPE
        SYNTAX        Counter64
        MAX-ACCESS    read-only
        STATUS        current
        DESCRIPTION  "Number of Standard Service Octets dropped."
        ::= { rcPwEndptStatsEntry 11 }

rcPwEndptStatsPremTxOctets OBJECT-TYPE
        SYNTAX        Counter64
        MAX-ACCESS    read-only
        STATUS        current
        DESCRIPTION  "Number of Premium Service Octets sent."
        ::= { rcPwEndptStatsEntry 12 }

rcPwEndptStatsGoldTxOctets OBJECT-TYPE
        SYNTAX        Counter64
        MAX-ACCESS    read-only
        STATUS        current
        DESCRIPTION  "Number of Gold Service Octets sent."
        ::= { rcPwEndptStatsEntry 13 }

rcPwEndptStatsSilverTxOctets OBJECT-TYPE
        SYNTAX        Counter64
        MAX-ACCESS    read-only
        STATUS        current
        DESCRIPTION  "Number of Silver Service Octets sent."
        ::= { rcPwEndptStatsEntry 14 }

rcPwEndptStatsStndTxOctets OBJECT-TYPE
        SYNTAX        Counter64
        MAX-ACCESS    read-only
        STATUS        current
        DESCRIPTION  "Number of Standard Service Octets sent."
        ::= { rcPwEndptStatsEntry 15 }

rcPwEndptStatsPremTxMcastOctets OBJECT-TYPE
        SYNTAX        Counter64
        MAX-ACCESS    read-only
        STATUS        current
        DESCRIPTION  "Number of Premium Service Multicast sent."
        ::= { rcPwEndptStatsEntry 16 }

rcPwEndptStatsGoldTxMcastOctets OBJECT-TYPE
        SYNTAX        Counter64
        MAX-ACCESS    read-only
        STATUS        current
        DESCRIPTION  "Number of GoldService Multicast sent."
        ::= { rcPwEndptStatsEntry 17 }

rcPwEndptStatsSilverTxMcastOctets OBJECT-TYPE
        SYNTAX        Counter64
        MAX-ACCESS    read-only
        STATUS        current
        DESCRIPTION  "Number of SilverService Multicast sent."
        ::= { rcPwEndptStatsEntry 18 }

rcPwEndptStatsStndTxMcastOctets OBJECT-TYPE
        SYNTAX        Counter64
        MAX-ACCESS    read-only
        STATUS        current
        DESCRIPTION  "Number of Premium Service Multicast sent."
        ::= { rcPwEndptStatsEntry 19 }

rcPwEndptStatsPremCongestionDropOctets OBJECT-TYPE
        SYNTAX        Counter64
        MAX-ACCESS    read-only
        STATUS        current
        DESCRIPTION  "Number of Prem Service Octets congestion dropped."
        ::= { rcPwEndptStatsEntry 20 }

rcPwEndptStatsGoldCongestionDropOctets OBJECT-TYPE
        SYNTAX        Counter64
        MAX-ACCESS    read-only
        STATUS        current
        DESCRIPTION  "Number of Gold Service Octets congestion dropped."
        ::= { rcPwEndptStatsEntry 21 }

rcPwEndptStatsSilverCongestionDropOctets OBJECT-TYPE
        SYNTAX        Counter64
        MAX-ACCESS    read-only
        STATUS        current
        DESCRIPTION  "Number of Silver Service Octets congestion dropped."
        ::= { rcPwEndptStatsEntry 22 }

rcPwEndptStatsStndCongestionDropOctets OBJECT-TYPE
        SYNTAX        Counter64
        MAX-ACCESS    read-only
        STATUS        current
        DESCRIPTION  "Number of Standard Service Octets congestion dropped."
        ::= { rcPwEndptStatsEntry 23 }

rcPwEndptStatsPremCirDroppedOctets OBJECT-TYPE
        SYNTAX        Counter64
        MAX-ACCESS    read-only
        STATUS        current
        DESCRIPTION  "Number of Prem Service Octets CIR dropped."
        ::= { rcPwEndptStatsEntry 24 }

rcPwEndptStatsPremPirDroppedOctets OBJECT-TYPE
        SYNTAX        Counter64
        MAX-ACCESS    read-only
        STATUS        current
        DESCRIPTION  "Number of Prem Service Octets PIR dropped."
        ::= { rcPwEndptStatsEntry 25 }

rcPwEndptStatsGoldCirDroppedOctets OBJECT-TYPE
        SYNTAX        Counter64
        MAX-ACCESS    read-only
        STATUS        current
        DESCRIPTION  "Number of Gold Service Octets CIR dropped."
        ::= { rcPwEndptStatsEntry 26 }

rcPwEndptStatsGoldPirDroppedOctets OBJECT-TYPE
        SYNTAX        Counter64
        MAX-ACCESS    read-only
        STATUS        current
        DESCRIPTION  "Number of Gold Service Octets PIR dropped."
        ::= { rcPwEndptStatsEntry 27 }

rcPwEndptStatsSilverCirDroppedOctets OBJECT-TYPE
        SYNTAX        Counter64
        MAX-ACCESS    read-only
        STATUS        current
        DESCRIPTION  "Number of Silver Service Octets CIR dropped."
        ::= { rcPwEndptStatsEntry 28 }

rcPwEndptStatsSilverPirDroppedOctets OBJECT-TYPE
        SYNTAX        Counter64
        MAX-ACCESS    read-only
        STATUS        current
        DESCRIPTION  "Number of Silver Service Octets PIR dropped."
        ::= { rcPwEndptStatsEntry 29 }

rcPwEndptStatsStndCirDroppedOctets OBJECT-TYPE
        SYNTAX        Counter64
        MAX-ACCESS    read-only
        STATUS        current
        DESCRIPTION  "Number of Standard Service Octets CIR dropped."
        ::= { rcPwEndptStatsEntry 30 }

rcPwEndptStatsStndPirDroppedOctets OBJECT-TYPE
        SYNTAX        Counter64
        MAX-ACCESS    read-only
        STATUS        current
        DESCRIPTION  "Number of Standard Service Octets PIR dropped."
        ::= { rcPwEndptStatsEntry 31 }

rcPwEndptStatsName OBJECT-TYPE
        SYNTAX        DisplayString (SIZE (0..30))
        MAX-ACCESS    read-only
        STATUS        current
        DESCRIPTION   "Name of Endpoint."
        ::= { rcPwEndptStatsEntry 32 }

rcPwEndptStatsPremTxDroppedOctets OBJECT-TYPE
        SYNTAX        Counter64
        MAX-ACCESS    read-only
        STATUS        current
        DESCRIPTION  "Tx Number of Premium Service Octets dropped."
        ::= { rcPwEndptStatsEntry 33 }

rcPwEndptStatsGoldTxDroppedOctets OBJECT-TYPE
        SYNTAX        Counter64
        MAX-ACCESS    read-only
        STATUS        current
        DESCRIPTION  "Tx Number of Gold Service Octets dropped."
        ::= { rcPwEndptStatsEntry 34 }

rcPwEndptStatsSilverTxDroppedOctets OBJECT-TYPE
        SYNTAX        Counter64
        MAX-ACCESS    read-only
        STATUS        current
        DESCRIPTION  "Tx Number of Silver Service Octets dropped."
        ::= { rcPwEndptStatsEntry 35 }

rcPwEndptStatsStndTxDroppedOctets OBJECT-TYPE
        SYNTAX        Counter64
        MAX-ACCESS    read-only
        STATUS        current
        DESCRIPTION  "Tx Number of Standard Service Octets dropped."
        ::= { rcPwEndptStatsEntry 36 }

rcPwEndptStatsPremTxCongestionDropOctets OBJECT-TYPE
        SYNTAX        Counter64
        MAX-ACCESS    read-only
        STATUS        current
        DESCRIPTION  "Tx Number of Prem Service Octets congestion dropped."
        ::= { rcPwEndptStatsEntry 37 }

rcPwEndptStatsGoldTxCongestionDropOctets OBJECT-TYPE
        SYNTAX        Counter64
        MAX-ACCESS    read-only
        STATUS        current
        DESCRIPTION  "Tx Number of Gold Service Octets congestion dropped."
        ::= { rcPwEndptStatsEntry 38 }

rcPwEndptStatsSilverTxCongestionDropOctets OBJECT-TYPE
        SYNTAX        Counter64
        MAX-ACCESS    read-only
        STATUS        current
        DESCRIPTION  "Tx Number of Silver Service Octets congestion dropped."
        ::= { rcPwEndptStatsEntry 39 }

rcPwEndptStatsStndTxCongestionDropOctets OBJECT-TYPE
        SYNTAX        Counter64
        MAX-ACCESS    read-only
        STATUS        current
        DESCRIPTION  "Tx Number of Standard Service Octets congestion dropped."
        ::= { rcPwEndptStatsEntry 40 }

rcPwEndptStatsPremTxCirDroppedOctets OBJECT-TYPE
        SYNTAX        Counter64
        MAX-ACCESS    read-only
        STATUS        current
        DESCRIPTION  "Tx Number of Prem Service Octets CIR dropped."
        ::= { rcPwEndptStatsEntry 41 }

rcPwEndptStatsPremTxPirDroppedOctets OBJECT-TYPE
        SYNTAX        Counter64
        MAX-ACCESS    read-only
        STATUS        current
        DESCRIPTION  "Tx Number of Prem Service Octets PIR dropped."
        ::= { rcPwEndptStatsEntry 42 }

rcPwEndptStatsGoldTxCirDroppedOctets OBJECT-TYPE
        SYNTAX        Counter64
        MAX-ACCESS    read-only
        STATUS        current
        DESCRIPTION  "Tx Number of Gold Service Octets CIR dropped."
        ::= { rcPwEndptStatsEntry 43 }

rcPwEndptStatsGoldTxPirDroppedOctets OBJECT-TYPE
        SYNTAX        Counter64
        MAX-ACCESS    read-only
        STATUS        current
        DESCRIPTION  "Tx Number of Gold Service Octets PIR dropped."
        ::= { rcPwEndptStatsEntry 44 }

rcPwEndptStatsSilverTxCirDroppedOctets OBJECT-TYPE
        SYNTAX        Counter64
        MAX-ACCESS    read-only
        STATUS        current
        DESCRIPTION  "Tx Number of Silver Service Octets CIR dropped."
        ::= { rcPwEndptStatsEntry 45 }

rcPwEndptStatsSilverTxPirDroppedOctets OBJECT-TYPE
        SYNTAX        Counter64
        MAX-ACCESS    read-only
        STATUS        current
        DESCRIPTION  "Tx Number of Silver Service Octets PIR dropped."
        ::= { rcPwEndptStatsEntry 46 }

rcPwEndptStatsStndTxCirDroppedOctets OBJECT-TYPE
        SYNTAX        Counter64
        MAX-ACCESS    read-only
        STATUS        current
        DESCRIPTION  "Tx Number of Standard Service Octets CIR dropped."
        ::= { rcPwEndptStatsEntry 47 }

rcPwEndptStatsStndTxPirDroppedOctets OBJECT-TYPE
        SYNTAX        Counter64
        MAX-ACCESS    read-only
        STATUS        current
        DESCRIPTION  "TX Number of Standard Service Octets PIR dropped."
        ::= { rcPwEndptStatsEntry 48 }

rcPwEndptStatsRxMcastTotalOctets OBJECT-TYPE
        SYNTAX        Counter64
        MAX-ACCESS    read-only
        STATUS        current
        DESCRIPTION  "Rx Total Number of Mcast Octets"
        ::= { rcPwEndptStatsEntry 49 }

rcPwEndptStatsTxMcastTotalOctets OBJECT-TYPE
        SYNTAX        Counter64
        MAX-ACCESS    read-only
        STATUS        current
        DESCRIPTION  "TX total Number of Mcast Octets"
        ::= { rcPwEndptStatsEntry 50 }
rcPwEndptStatsPremRxMcastDroppedOctets OBJECT-TYPE
        SYNTAX        Counter64
        MAX-ACCESS    read-only
        STATUS        current
        DESCRIPTION  "Number of Premium Service Rx Mcast Octets dropped."
        ::= { rcPwEndptStatsEntry 51 }

rcPwEndptStatsGoldRxMcastDroppedOctets OBJECT-TYPE
        SYNTAX        Counter64
        MAX-ACCESS    read-only
        STATUS        current
        DESCRIPTION  "Number of Gold Service Rx Mcast Octets dropped."
        ::= { rcPwEndptStatsEntry 52 }

rcPwEndptStatsSilverRxMcastDroppedOctets OBJECT-TYPE
        SYNTAX        Counter64
        MAX-ACCESS    read-only
        STATUS        current
        DESCRIPTION  "Number of Silver Service Rx Mcast Octets dropped."
        ::= { rcPwEndptStatsEntry 53 }

rcPwEndptStatsStndRxMcastDroppedOctets OBJECT-TYPE
        SYNTAX        Counter64
        MAX-ACCESS    read-only
        STATUS        current
        DESCRIPTION  "Number of Standard Service Rx Mcast Octets dropped."
        ::= { rcPwEndptStatsEntry 54 } 

rcPwEndptStatsPremRxFrames OBJECT-TYPE
        SYNTAX        Counter64
        MAX-ACCESS    read-only
        STATUS        current
        DESCRIPTION  "Number of Premium Service Frames received."
        ::= { rcPwEndptStatsEntry 55 }

rcPwEndptStatsPremRxDroppedFrames OBJECT-TYPE
        SYNTAX        Counter64
        MAX-ACCESS    read-only
        STATUS        current
        DESCRIPTION  "Number of Premium Service Frames dropped."
        ::= { rcPwEndptStatsEntry 56 }

rcPwEndptStatsGoldRxFrames OBJECT-TYPE
        SYNTAX        Counter64
        MAX-ACCESS    read-only
        STATUS        current
        DESCRIPTION  "Number of Gold Service Frames received."
        ::= { rcPwEndptStatsEntry 57 }

rcPwEndptStatsGoldRxDroppedFrames OBJECT-TYPE
        SYNTAX        Counter64
        MAX-ACCESS    read-only
        STATUS        current
        DESCRIPTION  "Number of Gold Service Frames dropped."
        ::= { rcPwEndptStatsEntry 58 }

rcPwEndptStatsSilverRxFrames OBJECT-TYPE
        SYNTAX        Counter64
        MAX-ACCESS    read-only
        STATUS        current
        DESCRIPTION  "Number of Silver Service Frames received."
        ::= { rcPwEndptStatsEntry 59 }

rcPwEndptStatsSilverRxDroppedFrames OBJECT-TYPE
        SYNTAX        Counter64
        MAX-ACCESS    read-only
        STATUS        current
        DESCRIPTION  "Number of Silver Service Frames dropped."
        ::= { rcPwEndptStatsEntry 60 }

rcPwEndptStatsStndRxFrames OBJECT-TYPE
        SYNTAX        Counter64
        MAX-ACCESS    read-only
        STATUS        current
        DESCRIPTION  "Number of Standard Service Frames received."
        ::= { rcPwEndptStatsEntry 61 }

rcPwEndptStatsStndRxDroppedFrames OBJECT-TYPE
        SYNTAX        Counter64
        MAX-ACCESS    read-only
        STATUS        current
        DESCRIPTION  "Number of Standard Service Frames dropped."
        ::= { rcPwEndptStatsEntry 62 }

rcPwEndptStatsPremTxFrames OBJECT-TYPE
        SYNTAX        Counter64
        MAX-ACCESS    read-only
        STATUS        current
        DESCRIPTION  "Number of Premium Service Frames sent."
        ::= { rcPwEndptStatsEntry 63 }

rcPwEndptStatsGoldTxFrames OBJECT-TYPE
        SYNTAX        Counter64
        MAX-ACCESS    read-only
        STATUS        current
        DESCRIPTION  "Number of Gold Service Frames sent."
        ::= { rcPwEndptStatsEntry 64 }

rcPwEndptStatsSilverTxFrames OBJECT-TYPE
        SYNTAX        Counter64
        MAX-ACCESS    read-only
        STATUS        current
        DESCRIPTION  "Number of Silver Service Frames sent."
        ::= { rcPwEndptStatsEntry 65 }

rcPwEndptStatsStndTxFrames OBJECT-TYPE
        SYNTAX        Counter64
        MAX-ACCESS    read-only
        STATUS        current
        DESCRIPTION  "Number of Standard Service Frames sent."
        ::= { rcPwEndptStatsEntry 66 }

rcPwEndptStatsPremTxMcastFrames OBJECT-TYPE
        SYNTAX        Counter64
        MAX-ACCESS    read-only
        STATUS        current
        DESCRIPTION  "Number of Premium Service Multicast sent."
        ::= { rcPwEndptStatsEntry 67 }

rcPwEndptStatsGoldTxMcastFrames OBJECT-TYPE
        SYNTAX        Counter64
        MAX-ACCESS    read-only
        STATUS        current
        DESCRIPTION  "Number of GoldService Multicast sent."
        ::= { rcPwEndptStatsEntry 68 }

rcPwEndptStatsSilverTxMcastFrames OBJECT-TYPE
        SYNTAX        Counter64
        MAX-ACCESS    read-only
        STATUS        current
        DESCRIPTION  "Number of SilverService Multicast sent."
        ::= { rcPwEndptStatsEntry 69 }

rcPwEndptStatsStndTxMcastFrames OBJECT-TYPE
        SYNTAX        Counter64
        MAX-ACCESS    read-only
        STATUS        current
        DESCRIPTION  "Number of Premium Service Multicast sent."
        ::= { rcPwEndptStatsEntry 70 }

rcPwEndptStatsPremCongestionDropFrames OBJECT-TYPE
        SYNTAX        Counter64
        MAX-ACCESS    read-only
        STATUS        current
        DESCRIPTION  "Number of Prem Service Frames congestion dropped."
        ::= { rcPwEndptStatsEntry 71 }

rcPwEndptStatsGoldCongestionDropFrames OBJECT-TYPE
        SYNTAX        Counter64
        MAX-ACCESS    read-only
        STATUS        current
        DESCRIPTION  "Number of Gold Service Frames congestion dropped."
        ::= { rcPwEndptStatsEntry 72 }

rcPwEndptStatsSilverCongestionDropFrames OBJECT-TYPE
        SYNTAX        Counter64
        MAX-ACCESS    read-only
        STATUS        current
        DESCRIPTION  "Number of Silver Service Frames congestion dropped."
        ::= { rcPwEndptStatsEntry 73 }

rcPwEndptStatsStndCongestionDropFrames OBJECT-TYPE
        SYNTAX        Counter64
        MAX-ACCESS    read-only
        STATUS        current
        DESCRIPTION  "Number of Standard Service Frames congestion dropped."
        ::= { rcPwEndptStatsEntry 74 }

rcPwEndptStatsPremCirDroppedFrames OBJECT-TYPE
        SYNTAX        Counter64
        MAX-ACCESS    read-only
        STATUS        current
        DESCRIPTION  "Number of Prem Service Frames CIR dropped."
        ::= { rcPwEndptStatsEntry 75 }

rcPwEndptStatsPremPirDroppedFrames OBJECT-TYPE
        SYNTAX        Counter64
        MAX-ACCESS    read-only
        STATUS        current
        DESCRIPTION  "Number of Prem Service Frames PIR dropped."
        ::= { rcPwEndptStatsEntry 76 }

rcPwEndptStatsGoldCirDroppedFrames OBJECT-TYPE
        SYNTAX        Counter64
        MAX-ACCESS    read-only
        STATUS        current
        DESCRIPTION  "Number of Gold Service Frames CIR dropped."
        ::= { rcPwEndptStatsEntry 77 }

rcPwEndptStatsGoldPirDroppedFrames OBJECT-TYPE
        SYNTAX        Counter64
        MAX-ACCESS    read-only
        STATUS        current
        DESCRIPTION  "Number of Gold Service Frames PIR dropped."
        ::= { rcPwEndptStatsEntry 78 }

rcPwEndptStatsSilverCirDroppedFrames OBJECT-TYPE
        SYNTAX        Counter64
        MAX-ACCESS    read-only
        STATUS        current
        DESCRIPTION  "Number of Silver Service Frames CIR dropped."
        ::= { rcPwEndptStatsEntry 79 }

rcPwEndptStatsSilverPirDroppedFrames OBJECT-TYPE
        SYNTAX        Counter64
        MAX-ACCESS    read-only
        STATUS        current
        DESCRIPTION  "Number of Silver Service Frames PIR dropped."
        ::= { rcPwEndptStatsEntry 80 }

rcPwEndptStatsStndCirDroppedFrames OBJECT-TYPE
        SYNTAX        Counter64
        MAX-ACCESS    read-only
        STATUS        current
        DESCRIPTION  "Number of Standard Service Frames CIR dropped."
        ::= { rcPwEndptStatsEntry 81 }

rcPwEndptStatsStndPirDroppedFrames OBJECT-TYPE
        SYNTAX        Counter64
        MAX-ACCESS    read-only
        STATUS        current
        DESCRIPTION  "Number of Standard Service Frames PIR dropped."
        ::= { rcPwEndptStatsEntry 82 }

rcPwEndptStatsPremTxDroppedFrames OBJECT-TYPE
        SYNTAX        Counter64
        MAX-ACCESS    read-only
        STATUS        current
        DESCRIPTION  "Tx Number of Premium Service Frames dropped."
        ::= { rcPwEndptStatsEntry 83 }

rcPwEndptStatsGoldTxDroppedFrames OBJECT-TYPE
        SYNTAX        Counter64
        MAX-ACCESS    read-only
        STATUS        current
        DESCRIPTION  "Tx Number of Gold Service Frames dropped."
        ::= { rcPwEndptStatsEntry 84 }

rcPwEndptStatsSilverTxDroppedFrames OBJECT-TYPE
        SYNTAX        Counter64
        MAX-ACCESS    read-only
        STATUS        current
        DESCRIPTION  "Tx Number of Silver Service Frames dropped."
        ::= { rcPwEndptStatsEntry 85 }

rcPwEndptStatsStndTxDroppedFrames OBJECT-TYPE
        SYNTAX        Counter64
        MAX-ACCESS    read-only
        STATUS        current
        DESCRIPTION  "Tx Number of Standard Service Frames dropped."
        ::= { rcPwEndptStatsEntry 86 }

rcPwEndptStatsPremTxCongestionDropFrames OBJECT-TYPE
        SYNTAX        Counter64
        MAX-ACCESS    read-only
        STATUS        current
        DESCRIPTION  "Tx Number of Prem Service Frames congestion dropped."
        ::= { rcPwEndptStatsEntry 87 }

rcPwEndptStatsGoldTxCongestionDropFrames OBJECT-TYPE
        SYNTAX        Counter64
        MAX-ACCESS    read-only
        STATUS        current
        DESCRIPTION  "Tx Number of Gold Service Frames congestion dropped."
        ::= { rcPwEndptStatsEntry 88 }

rcPwEndptStatsSilverTxCongestionDropFrames OBJECT-TYPE
        SYNTAX        Counter64
        MAX-ACCESS    read-only
        STATUS        current
        DESCRIPTION  "Tx Number of Silver Service Frames congestion dropped."
        ::= { rcPwEndptStatsEntry 89 }

rcPwEndptStatsStndTxCongestionDropFrames OBJECT-TYPE
        SYNTAX        Counter64
        MAX-ACCESS    read-only
        STATUS        current
        DESCRIPTION  "Tx Number of Standard Service Frames congestion dropped."
        ::= { rcPwEndptStatsEntry 90 }

rcPwEndptStatsPremTxCirDroppedFrames OBJECT-TYPE
        SYNTAX        Counter64
        MAX-ACCESS    read-only
        STATUS        current
        DESCRIPTION  "Tx Number of Prem Service Frames CIR dropped."
        ::= { rcPwEndptStatsEntry 91 }

rcPwEndptStatsPremTxPirDroppedFrames OBJECT-TYPE
        SYNTAX        Counter64
        MAX-ACCESS    read-only
        STATUS        current
        DESCRIPTION  "Tx Number of Prem Service Frames PIR dropped."
        ::= { rcPwEndptStatsEntry 92 }

rcPwEndptStatsGoldTxCirDroppedFrames OBJECT-TYPE
        SYNTAX        Counter64
        MAX-ACCESS    read-only
        STATUS        current
        DESCRIPTION  "Tx Number of Gold Service Frames CIR dropped."
        ::= { rcPwEndptStatsEntry 93 }

rcPwEndptStatsGoldTxPirDroppedFrames OBJECT-TYPE
        SYNTAX        Counter64
        MAX-ACCESS    read-only
        STATUS        current
        DESCRIPTION  "Tx Number of Gold Service Frames PIR dropped."
        ::= { rcPwEndptStatsEntry 94 }

rcPwEndptStatsSilverTxCirDroppedFrames OBJECT-TYPE
        SYNTAX        Counter64
        MAX-ACCESS    read-only
        STATUS        current
        DESCRIPTION  "Tx Number of Silver Service Frames CIR dropped."
        ::= { rcPwEndptStatsEntry 95 }

rcPwEndptStatsSilverTxPirDroppedFrames OBJECT-TYPE
        SYNTAX        Counter64
        MAX-ACCESS    read-only
        STATUS        current
        DESCRIPTION  "Tx Number of Silver Service Frames PIR dropped."
        ::= { rcPwEndptStatsEntry 96 }

rcPwEndptStatsStndTxCirDroppedFrames OBJECT-TYPE
        SYNTAX        Counter64
        MAX-ACCESS    read-only
        STATUS        current
        DESCRIPTION  "Tx Number of Standard Service Frames CIR dropped."
        ::= { rcPwEndptStatsEntry 97 }

rcPwEndptStatsStndTxPirDroppedFrames OBJECT-TYPE
        SYNTAX        Counter64
        MAX-ACCESS    read-only
        STATUS        current
        DESCRIPTION  "TX Number of Standard Service Frames PIR dropped."
        ::= { rcPwEndptStatsEntry 98 }

rcPwEndptStatsRxMcastTotalFrames OBJECT-TYPE
        SYNTAX        Counter64
        MAX-ACCESS    read-only
        STATUS        current
        DESCRIPTION  "Rx Total Number of Mcast Frames"
        ::= { rcPwEndptStatsEntry 99 }

rcPwEndptStatsTxMcastTotalFrames OBJECT-TYPE
        SYNTAX        Counter64
        MAX-ACCESS    read-only
        STATUS        current
        DESCRIPTION  "TX total Number of Mcast Frames"
        ::= { rcPwEndptStatsEntry 100 }

rcPwEndptStatsPremRxMcastDroppedFrames OBJECT-TYPE
        SYNTAX        Counter64
        MAX-ACCESS    read-only
        STATUS        current
        DESCRIPTION  "Number of Premium Service Rx Mcast Frames dropped."
        ::= { rcPwEndptStatsEntry 101 }

rcPwEndptStatsGoldRxMcastDroppedFrames OBJECT-TYPE
        SYNTAX        Counter64
        MAX-ACCESS    read-only
        STATUS        current
        DESCRIPTION  "Number of Gold Service Rx Mcast Frames dropped."
        ::= { rcPwEndptStatsEntry 102 }

rcPwEndptStatsSilverRxMcastDroppedFrames OBJECT-TYPE
        SYNTAX        Counter64
        MAX-ACCESS    read-only
        STATUS        current
        DESCRIPTION  "Number of Silver Service Rx Mcast Frames dropped."
        ::= { rcPwEndptStatsEntry 103 }

rcPwEndptStatsStndRxMcastDroppedFrames OBJECT-TYPE
        SYNTAX        Counter64
        MAX-ACCESS    read-only
        STATUS        current
        DESCRIPTION  "Number of Standard Service Rx Mcast Frames dropped."
        ::= { rcPwEndptStatsEntry 104 }

-- Pwe3 Endpoint Cvid Client Mep

rcPwEndptCvidClientMepTable OBJECT-TYPE
        SYNTAX        SEQUENCE OF RcPwEndptCvidClientMepEntry
        MAX-ACCESS    not-accessible
        STATUS        current
        DESCRIPTION   "A table used to maintain CFM Client MEP 
                       assigned to the Isid Endpoint with Cvid"
        ::= { rcPwe3 3 }

rcPwEndptCvidClientMepEntry OBJECT-TYPE
        SYNTAX        RcPwEndptCvidClientMepEntry
        MAX-ACCESS    not-accessible
        STATUS        current
        DESCRIPTION   "An entry in the rcIsidEndptCvidClientMep table."
        INDEX         { rcPwEndptCvidClientMepPwIndex, rcPwEndptCvidClientMepTlsIndex, rcPwEndptCvidClientMepCvid}
        ::= { rcPwEndptCvidClientMepTable 1 }

RcPwEndptCvidClientMepEntry ::= SEQUENCE {
        rcPwEndptCvidClientMepPwIndex   INTEGER,
        rcPwEndptCvidClientMepTlsIndex  INTEGER,
        rcPwEndptCvidClientMepCvid      INTEGER,
        rcPwEndptCvidClientMepMepList   OCTET STRING,
	rcPwEndptCvidClientMepNumOfMep  Integer32
        }

rcPwEndptCvidClientMepPwIndex OBJECT-TYPE
        SYNTAX        INTEGER (1..16777215) 
        MAX-ACCESS    not-accessible
        STATUS        current
        DESCRIPTION   "Service Instance ID of the I component"
        ::= { rcPwEndptCvidClientMepEntry 1 }

rcPwEndptCvidClientMepTlsIndex OBJECT-TYPE
        SYNTAX        INTEGER (1..2147483647)
        MAX-ACCESS    not-accessible
        STATUS        current
        DESCRIPTION   "Tls Index of an PW Endpoint."
        ::= { rcPwEndptCvidClientMepEntry 2 }

rcPwEndptCvidClientMepCvid OBJECT-TYPE
        SYNTAX        INTEGER (1..4094) 
        MAX-ACCESS    not-accessible
        STATUS        current
        DESCRIPTION   "C-Vlan Id associate with the PW Endpoint"
        ::= { rcPwEndptCvidClientMepEntry 3 }

rcPwEndptCvidClientMepMepList OBJECT-TYPE
        SYNTAX        OCTET STRING (SIZE(0..408))
        MAX-ACCESS    read-create
        STATUS        current
        DESCRIPTION   "List of Client Meps assigned to this entry. 
		       A client mep is consist of <md>.<ma>.<mep_id>. Domain
		       Name, Association and Mep Id is separated by '.' 
		       A list of mep is consist of 
		       <md1>.<ma1>.<mepid1>,<md2>.<ma2>.<mepid2>,... 
		       Each mep is separated by ','. Maximum up 8 meps"
        ::= { rcPwEndptCvidClientMepEntry 4 }

rcPwEndptCvidClientMepNumOfMep OBJECT-TYPE
        SYNTAX        	Integer32
        MAX-ACCESS      read-only
        STATUS        	current
        DESCRIPTION   	"Used to indicate the number of Client Meps
                      	is assigned to this entry"
        ::= { rcPwEndptCvidClientMepEntry 5 }

END
