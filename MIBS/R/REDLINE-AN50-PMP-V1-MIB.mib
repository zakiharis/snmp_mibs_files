-- **************************************************************
-- Redline AN50-PMP MIB
-- ECO Rev 1.00
-- Copyright (c) 2006 by Redline Communications, Inc
-- All rights reserved
-- **************************************************************

REDLINE-AN50-PMP-V1-MIB DEFINITIONS ::= BEGIN
IMPORTS

 	OBJECT-TYPE, IpAddress, enterprises,TimeTicks 	FROM RFC1155-SMI
	RowStatus							FROM SNMPv2-TC;
--      ORGANIZATION "Redline Communications, Inc."

--      postal:  Redline Communications Inc.
--              302 Town Centre Blvd Suite 100
--              Markham Ontario L3R 0E8
--              Canada
--      phone:     +1 905 479-8344

--      DESCRIPTION "This MIB contains Redline-defined attributes for 
--		     AN-50 PMP switched device based on V1 processor. The device can
--		     connect multiple subscriber stations to a central
--		     base station."

--      LAST-UPDATED "200304050930Z"
--      Author: Bogdan Moldoveanu
--      DESCRIPTION "MIB module for AN50PMP V1 Processor."

--      LAST-UPDATED "200308200000Z"
--      Author: Bogdan Moldoveanu
--      DESCRIPTION "Added an50pmpLastModifiedCID"

--      LAST-UPDATED "200401070000Z"
--      Author: Bogdan Moldoveanu
--      DESCRIPTION "Added an50pmpLastMissedSsMacAddress"

--      LAST-UPDATED "200401080000Z"
--      Author: Bogdan Moldoveanu
--      DESCRIPTION "Added an50pmpLastRegisteredSsMacAddress"

--      LAST-UPDATED "200408040000Z"
--      Author: Ioan Cautil
--      DESCRIPTION "Completed descriptions of mib nodes" 

--      LAST-UPDATED "200601160000Z"
--      Author: Mark Fairclough
--      DESCRIPTION "spelling and update to Redline address"

--textual convention

-- Registration of object identifiers
redline         		OBJECT IDENTIFIER ::= { enterprises 10728 }
redlineProducts 		OBJECT IDENTIFIER ::= { redline 1 }
redlineMgmt     		OBJECT IDENTIFIER ::= { redline 2 }
redlineAN50 		OBJECT IDENTIFIER ::= { redlineProducts 1 }
redlineAN50PMPV1	 	OBJECT IDENTIFIER ::= {redlineMgmt 51}


-- -----------------------------
-- Link and Connections Table
-- -----------------------------

an50pmpLinkTable	 	OBJECT-TYPE
	SYNTAX		SEQUENCE OF An50pmpLinkEntry
	ACCESS		not-accessible
	STATUS		mandatory
	DESCRIPTION	
		"Table with Wireless links and connections
		information configured into AN50 PMP device
		based on V1 processor."
	::= {redlineAN50PMPV1 1}

an50pmpLinkEntry		OBJECT-TYPE
	SYNTAX		An50pmpLinkEntry
	ACCESS		not-accessible
	STATUS		mandatory
	DESCRIPTION
		"A unique set of link parameters."
	INDEX	{an50pmpLinkID}
	
	::= {an50pmpLinkTable 1}

An50pmpLinkEntry ::=
	SEQUENCE  {
		an50pmpLinkID			INTEGER,
		an50pmpLinkName			OCTET STRING,
		an50pmpLinkGroupID		INTEGER,
		an50pmpLinkPeerMac		OCTET STRING,
		an50pmpLinkMaxDLBurstRate	INTEGER,
		an50pmpLinkMaxULBurstRate	INTEGER,
		an50pmpLinkMaxHost		INTEGER,
		an50pmpLinkCIDDLCIR		INTEGER,
		an50pmpLinkCIDDLPIR		INTEGER,
		an50pmpLinkCIDULCIR		INTEGER,
		an50pmpLinkCIDULPIR		INTEGER,
		an50pmpLinkDLQoS			INTEGER,
		an50pmpLinkULQoS			INTEGER,
		an50pmpLinkRowStatus		RowStatus
	}

an50pmpLinkID	OBJECT-TYPE
	SYNTAX		INTEGER (1 .. 1024)
	ACCESS		read-only
	STATUS		mandatory
	DESCRIPTION
		"Link ID, a unique number between 1 and 1024 that 
		 identifies a particular link."
	::= {an50pmpLinkEntry 1}

an50pmpLinkName		OBJECT-TYPE
	SYNTAX		OCTET STRING(SIZE(1..8))
	ACCESS		read-write
	STATUS		mandatory
	DESCRIPTION
		"The name of the Link/Connection "
	::= {an50pmpLinkEntry 2}

an50pmpLinkGroupID	OBJECT-TYPE
	SYNTAX		INTEGER(1 .. 1024)
	ACCESS		read-write
	STATUS		mandatory
	DESCRIPTION
		"Group assigned to this link."
	::= {an50pmpLinkEntry 3}


an50pmpLinkPeerMac	OBJECT-TYPE
	SYNTAX		OCTET STRING
	ACCESS		read-write
	STATUS		mandatory
	DESCRIPTION
		"Link Destination MAC address."
	::= {an50pmpLinkEntry 4}

an50pmpLinkMaxDLBurstRate	OBJECT-TYPE
	SYNTAX		INTEGER (1..8)
	ACCESS		read-write
	STATUS		mandatory
	DESCRIPTION
		"Maximum downlink rate for this link.
		Rate range: 6Mb/s=1, 9Mb/s=2, 12Mb/s=3, 18Mb/s=4, 
		24Mb/s=5, 36Mb/s=6, 48Mb/s=7, 54Mbs=8."
	::= {an50pmpLinkEntry 5}

an50pmpLinkMaxULBurstRate	OBJECT-TYPE
	SYNTAX		INTEGER (1..8)
	ACCESS		read-write
	STATUS		mandatory
	DESCRIPTION
		"Maximum uplink rate for this link.
		Rate range: 6Mb/s=1, 9Mb/s=2, 12Mb/s=3, 18Mb/s=4, 
		24Mb/s=5, 36Mb/s=6, 48Mb/s=7, 54Mbs=8."
	::= {an50pmpLinkEntry 6}

an50pmpLinkMaxHost	OBJECT-TYPE
	SYNTAX		INTEGER
	ACCESS		read-write
	STATUS		mandatory
	DESCRIPTION
		"Maximum number of hosts for this link."
	::= {an50pmpLinkEntry 7}

an50pmpLinkCIDDLCIR	OBJECT-TYPE
	SYNTAX		INTEGER (0 .. 65535)
	ACCESS		read-write
	STATUS		mandatory
	DESCRIPTION
		"The downlink commited rate for this connection in kb/s."
	::= {an50pmpLinkEntry 8}

an50pmpLinkCIDDLPIR	OBJECT-TYPE
	SYNTAX		INTEGER (0 .. 65535)
	ACCESS		read-write
	STATUS		mandatory
	DESCRIPTION
		"The downlink peak rate for this connection in kb/s."
	::= {an50pmpLinkEntry 9}

an50pmpLinkCIDULCIR	OBJECT-TYPE
	SYNTAX		INTEGER (0 .. 65535)
	ACCESS		read-write
	STATUS		mandatory
	DESCRIPTION
		"The uplink commited rate for this connection in kb/s."
	::= {an50pmpLinkEntry 10}

an50pmpLinkCIDULPIR	OBJECT-TYPE
	SYNTAX		INTEGER (0 .. 65535)
	ACCESS		read-write
	STATUS		mandatory
	DESCRIPTION
		"The uplink peak rate for this connection in kb/s."
	::= {an50pmpLinkEntry 11}

an50pmpLinkDLQoS		OBJECT-TYPE
	SYNTAX		INTEGER (1..54)
	ACCESS		read-write
	STATUS		mandatory
	DESCRIPTION
		"The downlink  QoS level."
	::= {an50pmpLinkEntry 12}

an50pmpLinkULQoS		OBJECT-TYPE
	SYNTAX		INTEGER (1..54)
	ACCESS		read-write
	STATUS		mandatory
	DESCRIPTION
		"The uplink QoS level."
	::= {an50pmpLinkEntry 13}

an50pmpLinkRowStatus	OBJECT-TYPE
	SYNTAX		RowStatus
	ACCESS		read-write
	STATUS		mandatory
	DESCRIPTION
		"Status of the row"
	::= {an50pmpLinkEntry 14}

an50pmpLinkStatusTable	OBJECT-TYPE
	SYNTAX		SEQUENCE OF An50pmpLinkStatusEntry
	ACCESS		not-accessible
	STATUS		mandatory
	DESCRIPTION
		"Statistics per uplink connections."	
	::= {redlineAN50PMPV1 2}

an50pmpLinkStatusEntry	OBJECT-TYPE
	SYNTAX		An50pmpLinkStatusEntry
	ACCESS		not-accessible
	STATUS		mandatory
	DESCRIPTION
		"Statistics for a link connection."
	INDEX		{an50pmpLinkID}
	::= {an50pmpLinkStatusTable 1}

An50pmpLinkStatusEntry  ::=
	SEQUENCE {
		an50pmpLinkStatusID			INTEGER,
		an50pmpLinkStatus				INTEGER,
		an50pmpLinkStatusCode			INTEGER,
		an50pmpLinkRegConn			INTEGER,
		an50pmpLinkDLBurstRate			INTEGER,
		an50pmpLinkDLRSSI				INTEGER,
		an50pmpLinkDLSINADR			INTEGER,
		an50pmpLinkDLStatLostFrm		INTEGER,
		an50pmpLinkDLStatBlksTot		INTEGER,
		an50pmpLinkDLStatBlksRetr		INTEGER,
		an50pmpLinkDLStatBlksDisc		INTEGER,
		an50pmpLinkDLCIDStatPktDisc		INTEGER,
		an50pmpLinkDLCIDStatPktTran		INTEGER,
		an50pmpLinkDLCIDStatPktRecv		INTEGER,
		an50pmpLinkULBurstRate			INTEGER,
		an50pmpLinkULRSSI				INTEGER,
		an50pmpLinkULSINADR			INTEGER,
		an50pmpLinkULStatLostFrm		INTEGER,
		an50pmpLinkULStatBlksTot		INTEGER,
		an50pmpLinkULStatBlksRetr		INTEGER,
		an50pmpLinkULStatBlksDisc		INTEGER,
		an50pmpLinkULCIDStatPktDisc		INTEGER,
		an50pmpLinkULCIDStatPktTran		INTEGER,
		an50pmpLinkULCIDStatPktRecv		INTEGER,
		an50pmpLinkUpTime				TimeTicks,
		an50pmpLinkLostCount			INTEGER
	}

an50pmpLinkStatusID	OBJECT-TYPE
	SYNTAX		INTEGER (1 .. 1024)
	ACCESS		read-only
	STATUS		mandatory
	DESCRIPTION
		"Index for an50pmpLinkStatusTable table"
	::= {an50pmpLinkStatusEntry 1}

an50pmpLinkStatus		OBJECT-TYPE
	SYNTAX		INTEGER {
					up(1),
					down(2)
				}
	ACCESS		read-only
	STATUS		mandatory
	DESCRIPTION
		"Status of the Link."
	::= {an50pmpLinkStatusEntry 2}

an50pmpLinkStatusCode	OBJECT-TYPE
	SYNTAX		INTEGER
	ACCESS		read-only
	STATUS		mandatory
	DESCRIPTION
		"Alarm bits shown as a hex number."
	::= {an50pmpLinkStatusEntry 3}
				
an50pmpLinkRegConn	OBJECT-TYPE
	SYNTAX		INTEGER (1 .. 1024)
	ACCESS		read-only
	STATUS		mandatory
	DESCRIPTION
		"Number of connections configured for this link."
	::= {an50pmpLinkStatusEntry 4}

an50pmpLinkDLBurstRate	OBJECT-TYPE
	SYNTAX		INTEGER (1..8)
	ACCESS		read-only
	STATUS		mandatory
	DESCRIPTION
		"Current master Tx burst rate.
		Rate range: 6Mb/s=1, 9Mb/s=2, 12Mb/s=3, 18Mb/s=4, 
		24Mb/s=5, 36Mb/s=6, 48Mb/s=7, 54Mbs=8. "
	::= {an50pmpLinkStatusEntry 5}

an50pmpLinkDLRSSI		OBJECT-TYPE
	SYNTAX		INTEGER 
	ACCESS		read-only
	STATUS		mandatory
	DESCRIPTION
		"RSSI (Received Signal Strength Indicator) at slave."
	::= {an50pmpLinkStatusEntry 6}

an50pmpLinkDLSINADR	OBJECT-TYPE
	SYNTAX		INTEGER 
	ACCESS		read-only
	STATUS		mandatory
	DESCRIPTION
		"SINADR (Signal Interference and Noise Distorsion Ratio) at slave."
	::= {an50pmpLinkStatusEntry 7}

an50pmpLinkDLStatLostFrm OBJECT-TYPE
	SYNTAX		INTEGER 
	ACCESS		read-only
	STATUS		mandatory
	DESCRIPTION
		"SINADR at slave."
	::= {an50pmpLinkStatusEntry 8}

an50pmpLinkDLStatBlksTot OBJECT-TYPE
	SYNTAX		INTEGER 
	ACCESS		read-only
	STATUS		mandatory
	DESCRIPTION
		"Blocks transmitted from master to slave."
	::= {an50pmpLinkStatusEntry 9}

an50pmpLinkDLStatBlksRetr OBJECT-TYPE
	SYNTAX		INTEGER 
	ACCESS		read-only
	STATUS		mandatory
	DESCRIPTION
		"Block re-transmitted from master to slave."
	::= {an50pmpLinkStatusEntry 10}

an50pmpLinkDLStatBlksDisc OBJECT-TYPE
	SYNTAX		INTEGER 
	ACCESS		read-only
	STATUS		mandatory
	DESCRIPTION
		"Blocks lost from master to slave"
	::= {an50pmpLinkStatusEntry 11}

an50pmpLinkDLCIDStatPktDisc OBJECT-TYPE
	SYNTAX		INTEGER 
	ACCESS		read-only
	STATUS		mandatory
	DESCRIPTION
		"Packets discarded by master due to buffer full."
	::= {an50pmpLinkStatusEntry 12}

an50pmpLinkDLCIDStatPktTran OBJECT-TYPE
	SYNTAX		INTEGER 
	ACCESS		read-only
	STATUS		mandatory
	DESCRIPTION
		"Packets transmitted from master to slave."
	::= {an50pmpLinkStatusEntry 13}

an50pmpLinkDLCIDStatPktRecv OBJECT-TYPE
	SYNTAX		INTEGER 
	ACCESS		read-only
	STATUS		mandatory
	DESCRIPTION
		"Packets received by slave"
	::= {an50pmpLinkStatusEntry 14}

an50pmpLinkULBurstRate  OBJECT-TYPE
	SYNTAX		INTEGER (1..8)
	ACCESS		read-only
	STATUS		mandatory
	DESCRIPTION
		"Current Slave Tx Burst Rate.
		Rate range: 6Mb/s=1, 9Mb/s=2, 12Mb/s=3, 18Mb/s=4, 
		24Mb/s=5, 36Mb/s=6, 48Mb/s=7, 54Mbs=8."
	::= {an50pmpLinkStatusEntry 15}

an50pmpLinkULRSSI		OBJECT-TYPE
	SYNTAX		INTEGER 
	ACCESS		read-only
	STATUS		mandatory
	DESCRIPTION
		"RSSI at master."
	::= {an50pmpLinkStatusEntry 16}

an50pmpLinkULSINADR	OBJECT-TYPE
	SYNTAX		INTEGER 
	ACCESS		read-only
	STATUS		mandatory
	DESCRIPTION
		"SINADR at master."
	::= {an50pmpLinkStatusEntry 17}

an50pmpLinkULStatLostFrm OBJECT-TYPE
	SYNTAX		INTEGER 
	ACCESS		read-only
	STATUS		mandatory
	DESCRIPTION
		"Frames lost from slave to master"
	::= {an50pmpLinkStatusEntry 18}

an50pmpLinkULStatBlksTot OBJECT-TYPE
	SYNTAX		INTEGER 
	ACCESS		read-only
	STATUS		mandatory
	DESCRIPTION
		"Blocks transmitted slave to master."
	::= {an50pmpLinkStatusEntry 19}

an50pmpLinkULStatBlksRetr OBJECT-TYPE
	SYNTAX		INTEGER 
	ACCESS		read-only
	STATUS		mandatory
	DESCRIPTION
		"Block re-transmitted slave to master."
	::= {an50pmpLinkStatusEntry 20}

an50pmpLinkULStatBlksDisc OBJECT-TYPE
	SYNTAX		INTEGER 
	ACCESS		read-only
	STATUS		mandatory
	DESCRIPTION
		"Blocks lost from slave to master."
	::= {an50pmpLinkStatusEntry 21}

an50pmpLinkULCIDStatPktDisc OBJECT-TYPE
	SYNTAX		INTEGER 
	ACCESS		read-only
	STATUS		mandatory
	DESCRIPTION
		"Packets discarded by slave due to buffer full."
	::= {an50pmpLinkStatusEntry 22}

an50pmpLinkULCIDStatPktTran OBJECT-TYPE
	SYNTAX		INTEGER 
	ACCESS		read-only
	STATUS		mandatory
	DESCRIPTION
		"Packets transmitted from slave to master."
	::= {an50pmpLinkStatusEntry 23}

an50pmpLinkULCIDStatPktRecv OBJECT-TYPE
	SYNTAX		INTEGER 
	ACCESS		read-only
	STATUS		mandatory
	DESCRIPTION
		"Packets received by master from slave."
	::= {an50pmpLinkStatusEntry 24}

an50pmpLinkUpTime		OBJECT-TYPE
	SYNTAX		TimeTicks 
	ACCESS		read-only
	STATUS		mandatory
	DESCRIPTION
		"Time since the link is UP (in hundreth a of second)."
	::= {an50pmpLinkStatusEntry 25}

an50pmpLinkLostCount	OBJECT-TYPE
	SYNTAX		INTEGER
	ACCESS		read-only
	STATUS		mandatory
	DESCRIPTION
		"Number of times the link has been lost."
	::= {an50pmpLinkStatusEntry 26}

an50pmpCIDSaveConfig OBJECT-TYPE
        SYNTAX  INTEGER { 
			donothing(1), -- do not save configuration
			saveConfig(2)  -- save configuration
			}
        ACCESS  read-write
        STATUS  mandatory
        DESCRIPTION
            "The attribute saves the entire config set of the AN50 PMP."
        ::= { redlineAN50PMPV1 3}

an50pmpLastModifiedCID OBJECT-TYPE
        SYNTAX  INTEGER (4..1023)
        ACCESS  read-only
        STATUS  mandatory
        DESCRIPTION
            "The attribute represents the last modified CID."
        ::= { redlineAN50PMPV1 4}

an50pmpLastMissedSsMacAddress	OBJECT-TYPE
	SYNTAX		OCTET STRING
	ACCESS		read-only
	STATUS		mandatory
	DESCRIPTION
		"MAC address of the SS that missed the registration with the BS."
        ::= { redlineAN50PMPV1 5}

an50pmpLastRegisteredSsMacAddress	OBJECT-TYPE
	SYNTAX		OCTET STRING
	ACCESS		read-only
	STATUS		mandatory
	DESCRIPTION
		"MAC address of the last SS that successfuly registered with the BS."
        ::= { redlineAN50PMPV1 6}

an50pmpLastSuccessfulID	OBJECT-TYPE
	SYNTAX		INTEGER (4..1023)
	ACCESS		read-only
	STATUS		mandatory
	DESCRIPTION
		"The ID of the Link registered in BS table that is sent through 
		LastSuccessfulRegisteredSS Trap(number10)."
        ::= { redlineAN50PMPV1 7}

an50pmpLastDeniedSsMacAddress	OBJECT-TYPE
	SYNTAX		OCTET STRING
	ACCESS		read-write
	STATUS		mandatory
	DESCRIPTION
		"MAC address of the SS that will be denied by thisBS."
        ::= { redlineAN50PMPV1 8}


END
