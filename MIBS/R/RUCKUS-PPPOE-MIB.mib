--
-- Copyright (c) 2010 by Ruckus Wireless, Inc.
-- All Rights Reserved
--

RUCKUS-PPPOE-MIB DEFINITIONS ::= BEGIN

IMPORTS
    ruckusCommonPPPOEModule
        FROM RUCKUS-ROOT-MIB
    MODULE-IDENTITY,
    OBJECT-TYPE
        FROM SNMPv2-SMI
    OBJECT-GROUP,
    MODULE-COMPLIANCE
        FROM SNMPv2-CONF
    DisplayString
        FROM SNMPv2-TC
    InterfaceIndex
        FROM IF-MIB;

ruckusPPPOEMIB MODULE-IDENTITY
    LAST-UPDATED "201010150800Z"
    ORGANIZATION "Ruckus Wireless, Inc"
    CONTACT-INFO
        "Ruckus Wireless Inc.

        Postal:
        350 West Java Dr.
        Sunnyvale, CA 94089
        USA

        EMail: support@ruckuswireless.com

        Phone: +1-650-265-4200."
    DESCRIPTION
        "Ruckus PPPoE mib objects."
    ::= { ruckusCommonPPPOEModule 1 }


-- Groups
--

ruckusPPPOEObjects OBJECT IDENTIFIER    ::= { ruckusPPPOEMIB 1 }

ruckusPPPOEInfo OBJECT IDENTIFIER   ::= { ruckusPPPOEObjects 1 }

ruckusPPPOEEvents OBJECT IDENTIFIER     ::= { ruckusPPPOEMIB 2 }

-- PPPoE Information
--

ruckusPPPOEUserName OBJECT-TYPE
    SYNTAX  DisplayString (SIZE (1..64))
    MAX-ACCESS read-write
    STATUS current
    DESCRIPTION
        "Specifies PPPoE user name. But it will not be effective unless you set apply(1) to ruckusPPPOEApply."
    ::= { ruckusPPPOEInfo 1 }


ruckusPPPOEPassword OBJECT-TYPE
    SYNTAX  OCTET STRING (SIZE (1..64))
    MAX-ACCESS read-write
    STATUS current
    DESCRIPTION
        "Specifies PPPoE password. But it will not be effective unless you set apply(1) to ruckusPPPOEApply."
    ::= { ruckusPPPOEInfo 2 }


ruckusPPPOEConnectionStatus OBJECT-TYPE
    SYNTAX  INTEGER {
            connected(1),
            notConnected(2) }
    MAX-ACCESS read-only
    STATUS current
    DESCRIPTION
        "Specifies PPPoE connection status.  Return up(1) if connection is 
        up, down(2) if connection is down, disabled(3) if PPPoE is disabled."
    ::= { ruckusPPPOEInfo 3 }


ruckusPPPOEConnection OBJECT-TYPE
    SYNTAX  INTEGER {
            connect(1),
            disConnect(2),
            ok(3) ,
            disabled(4)}
    MAX-ACCESS read-write
    STATUS current
    DESCRIPTION
        "Set connect(1) to connect or re-connect and disConnect(2)
        to PPPoE server.  On read, return enabled(3) if PPPoE is enabled, or
        disabled(4) if PPPoE is disabled."
    ::= { ruckusPPPOEInfo 4 }


ruckusPPPOEIfindex OBJECT-TYPE
    SYNTAX  InterfaceIndex
    MAX-ACCESS read-only
    STATUS current
    DESCRIPTION
        "Specifies the interface index, in the ifTable."
    ::= { ruckusPPPOEInfo 5 }

ruckusPPPOEApply OBJECT-TYPE
    SYNTAX  INTEGER { apply(1)}
    MAX-ACCESS read-write
    STATUS current
    DESCRIPTION
        "Set apply(1) to apply the change of username and password for PPPoE .
         Firstly, set the mib nodes : ruckusPPPOEUserName and ruckusPPPOEPassword .
         Secondly, set apply(1) to enable this PPPOE's username and password .
         For read, only return 0."
    ::= { ruckusPPPOEInfo 6 }


-- Conformance & Compliance
--

END
