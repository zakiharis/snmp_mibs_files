--
-- Copyright (c) 2010 by Ruckus Wireless, Inc.
-- All Rights Reserved
--

RUCKUS-ADAPTER-MIB DEFINITIONS ::= BEGIN

IMPORTS
    ruckusCommonAdapterModule
        FROM RUCKUS-ROOT-MIB
    MODULE-IDENTITY,
    OBJECT-TYPE,
    Counter32
        FROM SNMPv2-SMI
    TruthValue,
    MacAddress
        FROM SNMPv2-TC
    OBJECT-GROUP,
    MODULE-COMPLIANCE
        FROM SNMPv2-CONF
    ifIndex
        FROM IF-MIB
    RuckusdB,
    RuckusSSID
        FROM RUCKUS-TC-MIB;

ruckusAdapterMIB MODULE-IDENTITY
    LAST-UPDATED "201010150800Z"
    ORGANIZATION "Ruckus Wireless, Inc."
    CONTACT-INFO
        "Ruckus Wireless Inc.

        Postal:
        350 West Java Dr.
        Sunnyvale, CA 94089
        USA

        EMail: support@ruckuswireless.com

        Phone: +1-650-265-4200"
    DESCRIPTION
        "Ruckus adapter mib module."
    ::= { ruckusCommonAdapterModule 1 }


-- Groups
--

ruckusAdapterObjects OBJECT IDENTIFIER  ::= { ruckusAdapterMIB 1 }

ruckusAdapterInfo OBJECT IDENTIFIER     ::= { ruckusAdapterObjects 1 }

ruckusAdapterEvents OBJECT IDENTIFIER   ::= { ruckusAdapterMIB 2 }

--
--

ruckusAdapterTable OBJECT-TYPE
    SYNTAX  SEQUENCE OF RuckusAdapterEntry
    MAX-ACCESS not-accessible
    STATUS current
    DESCRIPTION
        "Specifies adapter table."
    ::= { ruckusAdapterInfo 1 }


ruckusAdapterEntry OBJECT-TYPE
    SYNTAX  RuckusAdapterEntry
    MAX-ACCESS not-accessible
    STATUS current
    DESCRIPTION
        "Specifies each adapter entry."
    INDEX {
        ifIndex,
        ruckusAdapterMacAddress }
    ::= { ruckusAdapterTable 1 }


RuckusAdapterEntry ::= SEQUENCE {

    ruckusAdapterMacAddress MacAddress,
    ruckusAdapterReboot     TruthValue }


ruckusAdapterMacAddress OBJECT-TYPE
    SYNTAX  MacAddress
    MAX-ACCESS not-accessible
    STATUS current
    DESCRIPTION
        "Specifies adapter hardware address.
        An index into the table."
    ::= { ruckusAdapterEntry 1 }


ruckusAdapterReboot OBJECT-TYPE
    SYNTAX  TruthValue
    MAX-ACCESS read-write
    STATUS current
    DESCRIPTION
        "Setting to true(1) would cause to reboot the adapter.
        Always returns false(2)"
    DEFVAL { false }
    ::= { ruckusAdapterEntry 2 }


-- Ruckus Adapter Information
--

ruckusAdapterInfoTable OBJECT-TYPE
    SYNTAX  SEQUENCE OF RuckusAdapterInfoEntry
    MAX-ACCESS not-accessible
    STATUS current
    DESCRIPTION
        "Specifies each adapter table."
    ::= { ruckusAdapterInfo 2 }


ruckusAdapterInfoEntry OBJECT-TYPE
    SYNTAX  RuckusAdapterInfoEntry
    MAX-ACCESS not-accessible
    STATUS current
    DESCRIPTION
        "Specifies each adapter entry."
    INDEX {
        ifIndex,
        ruckusAdapterInfoMacAddr }
    ::= { ruckusAdapterInfoTable 1 }


RuckusAdapterInfoEntry ::= SEQUENCE {

    ruckusAdapterInfoMacAddr MacAddress,
    ruckusAdapterInfoSSID    RuckusSSID,
    ruckusAdapterInfoBSSID   MacAddress,
    ruckusAdapterRssi        RuckusdB }


ruckusAdapterInfoMacAddr OBJECT-TYPE
    SYNTAX  MacAddress
    MAX-ACCESS not-accessible
    STATUS current
    DESCRIPTION
        "Adapter mac address, an index into the table."
    ::= { ruckusAdapterInfoEntry 1 }


ruckusAdapterInfoSSID OBJECT-TYPE
    SYNTAX  RuckusSSID
    MAX-ACCESS read-only
    STATUS current
    DESCRIPTION
        "Specifies the SSID."
    ::= { ruckusAdapterInfoEntry 2 }


ruckusAdapterInfoBSSID OBJECT-TYPE
    SYNTAX  MacAddress
    MAX-ACCESS read-only
    STATUS current
    DESCRIPTION
        "Specifies the BSS ID."
    ::= { ruckusAdapterInfoEntry 3 }


ruckusAdapterRssi OBJECT-TYPE
    SYNTAX  RuckusdB
    MAX-ACCESS read-only
    STATUS current
    DESCRIPTION
        "Specifies the RSSI."
    ::= { ruckusAdapterInfoEntry 4 }


-- Ruckus Adapter Statistics
--

ruckusAdapterStatTable OBJECT-TYPE
    SYNTAX  SEQUENCE OF RuckusAdapterStatEntry
    MAX-ACCESS not-accessible
    STATUS current
    DESCRIPTION
        "Specifies adapter table."
    ::= { ruckusAdapterInfo 3 }


ruckusAdapterStatEntry OBJECT-TYPE
    SYNTAX  RuckusAdapterStatEntry
    MAX-ACCESS not-accessible
    STATUS current
    DESCRIPTION
        "Specifies each adapter entry."
    INDEX {
        ifIndex,
        ruckusAdapterStatMacAddr }
    ::= { ruckusAdapterStatTable 1 }


RuckusAdapterStatEntry ::= SEQUENCE {

    ruckusAdapterStatMacAddr       MacAddress,
    ruckusAdapterStatRxDataFrames  Counter32,
    ruckusAdapterStatRxMgmtFrames  Counter32,
    ruckusAdapterStatRxCtrlFrames  Counter32,
    ruckusAdapterStatRxUcastFrames Counter32,
    ruckusAdapterStatRxMcastFrames Counter32,
    ruckusAdapterStatRxBytes       Counter32,
    ruckusAdapterStatRxDup         Counter32,
    ruckusAdapterStatRxNoPrivacy   Counter32,
    ruckusAdapterStatRxWEPFail     Counter32,
    ruckusAdapterStatRxDemicFail   Counter32,
    ruckusAdapterStatRxDecap       Counter32,
    ruckusAdapterStatRxDeFrag      Counter32,
    ruckusAdapterStatRxDisAssoc    Counter32,
    ruckusAdapterStatRxDeAuth      Counter32,
    ruckusAdapterStatRxUnAuth      Counter32,
    ruckusAdapterStatRxUnEncrypted Counter32,
    ruckusAdapterStatRxBeacons     Counter32,
    ruckusAdapterStatTxDataFrames  Counter32,
    ruckusAdapterStatTxMgmtFrames  Counter32,
    ruckusAdapterStatTxUcastFrames Counter32,
    ruckusAdapterStatTxMcastFrames Counter32,
    ruckusAdapterStatTxBytes       Counter32,
    ruckusAdapterStatTxAssoc       Counter32,
    ruckusAdapterStatTxAssocFail   Counter32,
    ruckusAdapterStatTxAuth        Counter32,
    ruckusAdapterStatTxAuthFail    Counter32,
    ruckusAdapterStatTxDeAuth      Counter32,
    ruckusAdapterStatTxDisAssoc    Counter32,
    ruckusAdapterStatTxProbeReq    Counter32,
    ruckusAdapterStatTxProbeResp   Counter32 }


ruckusAdapterStatMacAddr OBJECT-TYPE
    SYNTAX  MacAddress
    MAX-ACCESS not-accessible
    STATUS current
    DESCRIPTION
        "Adapter mac address, an index into the table."
    ::= { ruckusAdapterStatEntry 1 }


ruckusAdapterStatRxDataFrames OBJECT-TYPE
    SYNTAX  Counter32
    MAX-ACCESS read-only
    STATUS current
    DESCRIPTION
        "Rx data frames."
    ::= { ruckusAdapterStatEntry 2 }


ruckusAdapterStatRxMgmtFrames OBJECT-TYPE
    SYNTAX  Counter32
    MAX-ACCESS read-only
    STATUS current
    DESCRIPTION
        "Rx management frames."
    ::= { ruckusAdapterStatEntry 3 }


ruckusAdapterStatRxCtrlFrames OBJECT-TYPE
    SYNTAX  Counter32
    MAX-ACCESS read-only
    STATUS current
    DESCRIPTION
        "Rx control frames."
    ::= { ruckusAdapterStatEntry 4 }


ruckusAdapterStatRxUcastFrames OBJECT-TYPE
    SYNTAX  Counter32
    MAX-ACCESS read-only
    STATUS current
    DESCRIPTION
        "Rx unicast frames."
    ::= { ruckusAdapterStatEntry 5 }


ruckusAdapterStatRxMcastFrames OBJECT-TYPE
    SYNTAX  Counter32
    MAX-ACCESS read-only
    STATUS current
    DESCRIPTION
        "Rx multicast/broadcast frames."
    ::= { ruckusAdapterStatEntry 6 }


ruckusAdapterStatRxBytes OBJECT-TYPE
    SYNTAX  Counter32
    MAX-ACCESS read-only
    STATUS current
    DESCRIPTION
        "Rx data count (bytes)"
    ::= { ruckusAdapterStatEntry 7 }


ruckusAdapterStatRxDup OBJECT-TYPE
    SYNTAX  Counter32
    MAX-ACCESS read-only
    STATUS current
    DESCRIPTION
        "Rx discard because of duplicates."
    ::= { ruckusAdapterStatEntry 8 }


ruckusAdapterStatRxNoPrivacy OBJECT-TYPE
    SYNTAX  Counter32
    MAX-ACCESS read-only
    STATUS current
    DESCRIPTION
        "Rx w/ wep but privacy off."
    ::= { ruckusAdapterStatEntry 9 }


ruckusAdapterStatRxWEPFail OBJECT-TYPE
    SYNTAX  Counter32
    MAX-ACCESS read-only
    STATUS current
    DESCRIPTION
        "Rx wep processing failed."
    ::= { ruckusAdapterStatEntry 10 }


ruckusAdapterStatRxDemicFail OBJECT-TYPE
    SYNTAX  Counter32
    MAX-ACCESS read-only
    STATUS current
    DESCRIPTION
        "Rx demic failed."
    ::= { ruckusAdapterStatEntry 11 }


ruckusAdapterStatRxDecap OBJECT-TYPE
    SYNTAX  Counter32
    MAX-ACCESS read-only
    STATUS current
    DESCRIPTION
        "Rx decapsulation failed."
    ::= { ruckusAdapterStatEntry 12 }


ruckusAdapterStatRxDeFrag OBJECT-TYPE
    SYNTAX  Counter32
    MAX-ACCESS read-only
    STATUS current
    DESCRIPTION
        "Rx defragmentation failed."
    ::= { ruckusAdapterStatEntry 13 }


ruckusAdapterStatRxDisAssoc OBJECT-TYPE
    SYNTAX  Counter32
    MAX-ACCESS read-only
    STATUS current
    DESCRIPTION
        "Rx dis associations."
    ::= { ruckusAdapterStatEntry 14 }


ruckusAdapterStatRxDeAuth OBJECT-TYPE
    SYNTAX  Counter32
    MAX-ACCESS read-only
    STATUS current
    DESCRIPTION
        "Rx de authentication."
    ::= { ruckusAdapterStatEntry 15 }


ruckusAdapterStatRxUnAuth OBJECT-TYPE
    SYNTAX  Counter32
    MAX-ACCESS read-only
    STATUS current
    DESCRIPTION
        "Rx un authenticated."
    ::= { ruckusAdapterStatEntry 16 }


ruckusAdapterStatRxUnEncrypted OBJECT-TYPE
    SYNTAX  Counter32
    MAX-ACCESS read-only
    STATUS current
    DESCRIPTION
        "Rx un encrypted."
    ::= { ruckusAdapterStatEntry 17 }


ruckusAdapterStatRxBeacons OBJECT-TYPE
    SYNTAX  Counter32
    MAX-ACCESS read-only
    STATUS current
    DESCRIPTION
        "Rx beacons."
    ::= { ruckusAdapterStatEntry 18 }


ruckusAdapterStatTxDataFrames OBJECT-TYPE
    SYNTAX  Counter32
    MAX-ACCESS read-only
    STATUS current
    DESCRIPTION
        "Rx data frames."
    ::= { ruckusAdapterStatEntry 19 }


ruckusAdapterStatTxMgmtFrames OBJECT-TYPE
    SYNTAX  Counter32
    MAX-ACCESS read-only
    STATUS current
    DESCRIPTION
        "Tx management frames."
    ::= { ruckusAdapterStatEntry 20 }


ruckusAdapterStatTxUcastFrames OBJECT-TYPE
    SYNTAX  Counter32
    MAX-ACCESS read-only
    STATUS current
    DESCRIPTION
        "Tx unicast frames."
    ::= { ruckusAdapterStatEntry 21 }


ruckusAdapterStatTxMcastFrames OBJECT-TYPE
    SYNTAX  Counter32
    MAX-ACCESS read-only
    STATUS current
    DESCRIPTION
        "Tx multicast"
    ::= { ruckusAdapterStatEntry 22 }


ruckusAdapterStatTxBytes OBJECT-TYPE
    SYNTAX  Counter32
    MAX-ACCESS read-only
    STATUS current
    DESCRIPTION
        "Tx data count (bytes)."
    ::= { ruckusAdapterStatEntry 23 }


ruckusAdapterStatTxAssoc OBJECT-TYPE
    SYNTAX  Counter32
    MAX-ACCESS read-only
    STATUS current
    DESCRIPTION
        "[re]associations."
    ::= { ruckusAdapterStatEntry 24 }


ruckusAdapterStatTxAssocFail OBJECT-TYPE
    SYNTAX  Counter32
    MAX-ACCESS read-only
    STATUS current
    DESCRIPTION
        "[re]association failures."
    ::= { ruckusAdapterStatEntry 25 }


ruckusAdapterStatTxAuth OBJECT-TYPE
    SYNTAX  Counter32
    MAX-ACCESS read-only
    STATUS current
    DESCRIPTION
        "[re]authentications."
    ::= { ruckusAdapterStatEntry 26 }


ruckusAdapterStatTxAuthFail OBJECT-TYPE
    SYNTAX  Counter32
    MAX-ACCESS read-only
    STATUS current
    DESCRIPTION
        "[re]authentication failures."
    ::= { ruckusAdapterStatEntry 27 }


ruckusAdapterStatTxDeAuth OBJECT-TYPE
    SYNTAX  Counter32
    MAX-ACCESS read-only
    STATUS current
    DESCRIPTION
        "Tx de auth."
    ::= { ruckusAdapterStatEntry 28 }


ruckusAdapterStatTxDisAssoc OBJECT-TYPE
    SYNTAX  Counter32
    MAX-ACCESS read-only
    STATUS current
    DESCRIPTION
        "Tx dis associations."
    ::= { ruckusAdapterStatEntry 29 }


ruckusAdapterStatTxProbeReq OBJECT-TYPE
    SYNTAX  Counter32
    MAX-ACCESS read-only
    STATUS current
    DESCRIPTION
        "Tx probe requests."
    ::= { ruckusAdapterStatEntry 30 }


ruckusAdapterStatTxProbeResp OBJECT-TYPE
    SYNTAX  Counter32
    MAX-ACCESS read-only
    STATUS current
    DESCRIPTION
        "Tx probe responses."
    ::= { ruckusAdapterStatEntry 31 }


END
