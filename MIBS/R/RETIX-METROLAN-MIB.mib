-- Title:     Retix MetroLAN 5000 MIB definition in concise format
          -- Date:      3 October, 1996
          -- Version:   1.00
          -- By:        Ning Zhong

          RETIX-METROLAN-MIB DEFINITIONS ::= BEGIN

          IMPORTS
                     Counter, TimeTicks
                             FROM RFC1155-SMI
                     mib-2
                             FROM RFC1213-MIB
                     OBJECT-TYPE
                             FROM RFC-1212
                     TRAP-TYPE
                             FROM RFC-1215
                     enterprises, NetworkAddress, IpAddress,
                     Counter, Gauge, TimeTicks, DisplayString
                             FROM RFC1155-SMI;

          -- enterprises  OBJECT IDENTIFIER ::=
          --             { iso org(3) dod(6) internet(1) private(4) 1 }

          --
          --  Defined Groups
          --
          retix            OBJECT IDENTIFIER ::= { enterprises 72 }


          -- This MIB definition file is divided into two parts: 
          -- 1) MetroLanDS3ATM  and  2) MetroLanSS.
          -- MetroLanDS3ATM being the objects to configure DS3/ATM board, while
          -- MetroLanSS are the Retix specific objects for stackbus, VLAN, SLIP.

          metroLanDS3ATM   OBJECT IDENTIFIER ::= { mib-2 37 }
          metroLanSS       OBJECT IDENTIFIER ::= { enterprises 72 20 }



          -- groups in MetroLanDS3ATM

          atmBandwithGroup OBJECT IDENTIFIER ::= { metroLanDS3ATM 1 }
          atmLogicalPort   OBJECT IDENTIFIER ::= { metroLanDS3ATM 2 }
          ds3FrameDevice   OBJECT IDENTIFIER ::= { metroLanDS3ATM 3 }

          -- groups in metroLanSS

          ssUnitProfile    OBJECT IDENTIFIER ::= { metroLanSS 1 }
          ssBaseUnit       OBJECT IDENTIFIER ::= { metroLanSS 2 }
          ssStakBus        OBJECT IDENTIFIER ::= { metroLanSS 3 }
          ssVirtualLan     OBJECT IDENTIFIER ::= { metroLanSS 4 }
          ssSlip           OBJECT IDENTIFIER ::= { metroLanSS 5 }


          -- the atmBandwithGroup group

          -- up to eight ATM Bandwidth Group can be configured. with instance
          -- range from 1 to 8. 

          atmBWGBandwidth OBJECT-TYPE
              SYNTAX  INTEGER (1..8)
              ACCESS  read-write
              STATUS  mandatory
              DESCRIPTION
                      "The bandwidth amount (in Kbps) assigned to a 
                       specific bandwidth group. Total bandwidth for all
                       eight groups can not exceed the maximum, which is 36880."
              ::= { atmBandwithGroup 1 }

          atmBWGConfig OBJECT-TYPE
              SYNTAX  INTEGER {
                         go (1)       -- go! action! set!
                      }
              ACCESS  write-only
              STATUS  mandatory
              DESCRIPTION
                      "this carry out the actual SET of the bandwidth group.  
                       a SYSTEM RESET will be executed for the changes in
                       bandwidth group to take effect."
              ::= { atmBandwithGroup 2 }



          -- the atmLogicalPort group

          -- up to 128 ATM Logical Ports can be configured. with instance
          -- range from 17 to 17+127

          atmRX-VCI OBJECT-TYPE
              SYNTAX  INTEGER (35..1023)
              ACCESS  read-write
              STATUS  mandatory
              DESCRIPTION
                      "Receive VCI #. can be set as the same as atmTX-VCI"
              ::= { atmLogicalPort 1 }

          atmRX-VPI OBJECT-TYPE
              SYNTAX  INTEGER (0..255)
              ACCESS  read-write
              STATUS  mandatory
              DESCRIPTION
                      "Receive VPI #. can be set as the same as atmTX-VPI"
              ::= { atmLogicalPort 2 }

          atmTX-VCI OBJECT-TYPE
              SYNTAX  INTEGER (35..1023)
              ACCESS  read-write
              STATUS  mandatory
              DESCRIPTION
                      "Transmit VCI #. choose a unique number for each ATM
                       logical port."
              ::= { atmLogicalPort 3 }

          atmTX-VPI OBJECT-TYPE
              SYNTAX  INTEGER (0..255)
              ACCESS  read-write 
              STATUS  mandatory
              DESCRIPTION
                      "Transmit VPI #."
              ::= { atmLogicalPort 4 }

          atmBWG OBJECT-TYPE
              SYNTAX  INTEGER (1..8)
              ACCESS  read-write
              STATUS  mandatory
              DESCRIPTION
                      "Bandwidth group number. That paticular bandwidthgroup
                       must be configured with a positive bandwidth"
              ::= { atmLogicalPort 5 }

          atmEncaps OBJECT-TYPE
              SYNTAX  INTEGER {
                         vcBridged8023 (2),
                         llcEncaps (7)
                      }
              ACCESS  read-write
              STATUS  mandatory
              DESCRIPTION
                      "Encapsulation"
              ::= { atmLogicalPort 6 }

          atmPortConfig OBJECT-TYPE
              SYNTAX  INTEGER (0..1)
              ACCESS  read-write
              STATUS  mandatory
              DESCRIPTION
                      "this carry out the actual SET of the logical port.
                       0 deletes the existing port,
                       1 creates a new logical port"
              ::= { atmLogicalPort 7 }



          -- the ds3FrameDevice group

          ds3NoSignalCntr OBJECT-TYPE
              SYNTAX  INTEGER
              ACCESS  read-only
              STATUS  mandatory
              DESCRIPTION
                      "NoSignalCntr stat"
              ::= { ds3FrameDevice 1 }

          ds3NoDS3FrameCntr OBJECT-TYPE
              SYNTAX  INTEGER
              ACCESS  read-only
              STATUS  mandatory
              DESCRIPTION
                      "NoDS3FrameCntr stat"
              ::= { ds3FrameDevice 2 }

          ds3AISDetectCntr OBJECT-TYPE
              SYNTAX  INTEGER
              ACCESS  read-only
              STATUS  mandatory
              DESCRIPTION
                      "AISDetectCntr stat"
              ::= { ds3FrameDevice 3 }

          ds3YellowAlarmCntr OBJECT-TYPE
              SYNTAX  INTEGER
              ACCESS  read-only
              STATUS  mandatory
              DESCRIPTION
                      "YellowAlarmCntr stat"
              ::= { ds3FrameDevice 4 }

          ds3FErrCntr OBJECT-TYPE
              SYNTAX  INTEGER
              ACCESS  read-only
              STATUS  mandatory
              DESCRIPTION
                      "FErrCntr stat"
              ::= { ds3FrameDevice 5 }

          ds3PErrCntr OBJECT-TYPE
              SYNTAX  INTEGER
              ACCESS  read-only
              STATUS  mandatory
              DESCRIPTION
                      "PErrCntr stat"
              ::= { ds3FrameDevice 6 }

          ds3CPErrCntr OBJECT-TYPE
              SYNTAX  INTEGER
              ACCESS  read-only
              STATUS  mandatory
              DESCRIPTION
                      "CPErrCntr stat"
              ::= { ds3FrameDevice 7 }

          ds3FEBlockErrCntr OBJECT-TYPE
              SYNTAX  INTEGER
              ACCESS  read-only
              STATUS  mandatory
              DESCRIPTION
                      "FEBlockErrCntr stat"
              ::= { ds3FrameDevice 8 }

          ds3BPVErrCntr OBJECT-TYPE
              SYNTAX  INTEGER
              ACCESS  read-only
              STATUS  mandatory
              DESCRIPTION
                      "BPVErrCntr stat"
              ::= { ds3FrameDevice 9 }

          ds3ATMOCD OBJECT-TYPE
              SYNTAX  INTEGER
              ACCESS  read-only
              STATUS  mandatory
              DESCRIPTION
                      "ATMOCD stat"
              ::= { ds3FrameDevice 10 }

          ds3FIFOOverflow OBJECT-TYPE
              SYNTAX  INTEGER
              ACCESS  read-only
              STATUS  mandatory
              DESCRIPTION
                      "FIFOOverflow stat"
              ::= { ds3FrameDevice 11 }

          ds3RAI OBJECT-TYPE
              SYNTAX  INTEGER
              ACCESS  read-only
              STATUS  mandatory
              DESCRIPTION
                      "RAI stat"
              ::= { ds3FrameDevice 12 }

          ds3RAICntr OBJECT-TYPE
              SYNTAX  INTEGER
              ACCESS  read-only
              STATUS  mandatory
              DESCRIPTION
                      "RAICntr stat"
              ::= { ds3FrameDevice 13 }

          ds3SignalLoss OBJECT-TYPE
              SYNTAX  INTEGER
              ACCESS  read-only
              STATUS  mandatory
              DESCRIPTION
                      "SignalLoss stat"
              ::= { ds3FrameDevice 14 }

          ds3FrameLoss OBJECT-TYPE
              SYNTAX  INTEGER
              ACCESS  read-only
              STATUS  mandatory
              DESCRIPTION
                      "FrameLoss stat"
              ::= { ds3FrameDevice 15 }

          ds3SyncLoss OBJECT-TYPE
              SYNTAX  INTEGER
              ACCESS  read-only
              STATUS  mandatory
              DESCRIPTION
                      "SyncLoss stat"
              ::= { ds3FrameDevice 16 }

          ds3YellowAlarm OBJECT-TYPE
              SYNTAX  INTEGER
              ACCESS  read-only
              STATUS  mandatory
              DESCRIPTION
                      "YellowAlarm stat"
              ::= { ds3FrameDevice 17 }

          ds3AISDetect OBJECT-TYPE
              SYNTAX  INTEGER
              ACCESS  read-only
              STATUS  mandatory
              DESCRIPTION
                      "AISDetect stat"
              ::= { ds3FrameDevice 18 }

          ds3ClearErrorCntr OBJECT-TYPE
              SYNTAX  INTEGER {
                         set (1)
                      }
              ACCESS  write-only
              STATUS  mandatory
              DESCRIPTION
                      " SET this object will clear the Error Counters."
              ::= { ds3FrameDevice 19 }

          ds3GFCInsertion OBJECT-TYPE
              SYNTAX  INTEGER 
              ACCESS  read-write
              STATUS  mandatory
              DESCRIPTION
                      "Insertion of GFC bits "
              ::= { ds3FrameDevice 20 }

          ds3BipolarSerialIO OBJECT-TYPE
              SYNTAX  INTEGER
              ACCESS  read-write
              STATUS  mandatory
              DESCRIPTION
                      "Bipolar serial IO"
              ::= { ds3FrameDevice 21 }

          ds3PayloadScrambling OBJECT-TYPE
              SYNTAX  INTEGER 
              ACCESS  read-write
              STATUS  mandatory
              DESCRIPTION
                      "Payload scrambling"
              ::= { ds3FrameDevice 22 }

          ds3PLCPOverheadProc OBJECT-TYPE
              SYNTAX  INTEGER 
              ACCESS  read-write
              STATUS  mandatory
              DESCRIPTION
                      "PLCP overhead processing"
              ::= { ds3FrameDevice 23 }

          ds3FEBEGeneration OBJECT-TYPE
              SYNTAX  INTEGER
              ACCESS  read-write
              STATUS  mandatory
              DESCRIPTION
                      "FEBE error generation"
              ::= { ds3FrameDevice 24 }

          ds3LoopBack OBJECT-TYPE
              SYNTAX  INTEGER
              ACCESS  read-write
              STATUS  mandatory
              DESCRIPTION
                      "LoopBack Mode "
              ::= { ds3FrameDevice 25 }

          ds3FEACGenNDetect OBJECT-TYPE
              SYNTAX  INTEGER
              ACCESS  read-write
              STATUS  mandatory
              DESCRIPTION
                      "FEAC generation/detection"
              ::= { ds3FrameDevice 26 }

          ds3RcvEQ OBJECT-TYPE
              SYNTAX  INTEGER
              ACCESS  read-write
              STATUS  mandatory
              DESCRIPTION
                      "Use internal receive equalizer"
              ::= { ds3FrameDevice 27 }

          ds3XmitLevel OBJECT-TYPE
              SYNTAX  INTEGER
              ACCESS  read-write
              STATUS  mandatory
              DESCRIPTION
                      " transmit level: use normal (low) or long (high) cables"
              ::= { ds3FrameDevice 28 }




          -- the metroLanSS group
          --

          -- the SSUnitProfile group
          -- Main board + I/O_1 + I/O_2 card type info

          ssBaseModule OBJECT-TYPE
              SYNTAX  INTEGER
              ACCESS  read-only
              STATUS  mandatory
              DESCRIPTION
                      "Identifies the type of main board card type"
              ::= { ssUnitProfile 1 }

          ssIO1Module OBJECT-TYPE
              SYNTAX  INTEGER {
                         vacant (1),
                         pcnet-6-card-id (2),
                         feast-card-id (3),
                         stakBus-card-id (4),
                         atm-card-id (5)
                      }
              ACCESS  read-only
              STATUS  mandatory
              DESCRIPTION
                      "I/O 1 card type"
              ::= { ssUnitProfile 2 }

          ssIO2Module OBJECT-TYPE
              SYNTAX  INTEGER {
                         vacant (1),
                         pcnet-6-card-id (2),
                         feast-card-id (3),
                         stakBus-card-id (4),
                         atm-card-id (5)
                      }
              ACCESS  read-only
              STATUS  mandatory
              DESCRIPTION
                      "I/O 2 card type"
              ::= { ssUnitProfile 3 }


          -- the ssBaseUnit group
          -- base unit. boot and software version

          ssBaseBootFWVer OBJECT-TYPE
              SYNTAX  INTEGER
              ACCESS  read-only
              STATUS  mandatory
              DESCRIPTION
                      "Version number of current boot firmware"
              ::= { ssBaseUnit 1 }

          ssBaseSoftVer OBJECT-TYPE
              SYNTAX  INTEGER
              ACCESS  read-only
              STATUS  mandatory
              DESCRIPTION
                      "Version number of current software"
              ::= { ssBaseUnit 2 }

          ssErrorLog OBJECT-TYPE
              SYNTAX  INTEGER
              ACCESS  read-write
              STATUS  mandatory
              DESCRIPTION
                      "A stored value indicating that the unit has
                       experienced a fault.  Log information is formatted
                       as a four digit hex number.  Set to zero to clear
                       the logged fault.  Record this value and call Retix
                       technical support."
              ::= { ssBaseUnit 3 }


          -- the ssStakBus group
          -- StakBus related info

          ssStkBusIOPort OBJECT-TYPE
              SYNTAX  INTEGER {
                           on-IO1 (1),
                           on-IO2 (2),
                           not-installed (3)
                      }
              ACCESS  read-only
              STATUS  mandatory
              DESCRIPTION
                      "which I/O port is StakBus installed. 
                       (only 1 stakbus per system is allowed)"
              ::= { ssStakBus 1 }

          ssStkBusSpeed OBJECT-TYPE
              SYNTAX  INTEGER
              ACCESS  read-only
              STATUS  mandatory
              DESCRIPTION
                      "StakBus speed. 175000000, or 0 if no StakBus card
                       installed"
              ::= { ssStakBus 2 }

          ssStkBusNodeAddr OBJECT-TYPE
              SYNTAX  INTEGER (0..15)
              ACCESS  read-only
              STATUS  mandatory
              DESCRIPTION
                      "Module ID for StakBus card"
              ::= { ssStakBus 3 }

          ssStkBusRingOp OBJECT-TYPE
              SYNTAX  INTEGER {
                           ringOperational(1),
                           ringNotOperational(2),
                           notInstalled(3)
                      }
              ACCESS  read-only
              STATUS  mandatory
              DESCRIPTION
                      "StakBus Ring OperationalStatus"
              ::= { ssStakBus 4 }

          -- the ssVirtualLan group

          ssVLANEnDisable OBJECT-TYPE
              SYNTAX  INTEGER
              ACCESS  read-write
              STATUS  mandatory
              DESCRIPTION
                      "Globally enable/disable VLAN for the system"
              ::= { ssVirtualLan 1 }

          portVLANTable OBJECT-TYPE
              SYNTAX  SEQUENCE OF PortVLANEntry
              ACCESS  not-accessible
              STATUS  mandatory
              DESCRIPTION
                      "Table of port based VLAN configurations.
                       Entries (rows) are added to the table by issuing a
                       SET command with the EnableAdd value for the
                       portVLANEntryEdit object.  The new row is created
                       using the instantiations."
              ::= { ssVirtualLan 2 }

          portVLANEntry OBJECT-TYPE
              SYNTAX  PortVLANEntry
              ACCESS  not-accessible
              STATUS  mandatory
              DESCRIPTION
                      "a VLAN entry containing portID, VLANID, ..."
              INDEX   { ssVLANEntryPortID, ssVLANEntryVLANID }
              ::= { portVLANTable 1 }

          PortVLANEntry ::=
              SEQUENCE {
                  ssVLANEntryPortID
                      INTEGER,
                  ssVLANEntryVLANID
                      INTEGER,
                  ssVLANEntryEdit
                      INTEGER
              }
 
          ssVLANEntryPortID OBJECT-TYPE
              SYNTAX  INTEGER
              ACCESS  read-write
              STATUS  mandatory
              DESCRIPTION
                      "Port ID"
              ::= { portVLANEntry 1 }

          ssVLANEntryVLANID OBJECT-TYPE
              SYNTAX  INTEGER 
              ACCESS  read-write
              STATUS  mandatory
              DESCRIPTION
                      "Vlan ID"
              ::= { portVLANEntry 2 }

          ssVLANEntryEdit OBJECT-TYPE
              SYNTAX  INTEGER {
                         enable-add (1),
                         disable (2),
                         delete (3)
                      }
              ACCESS  read-write
              STATUS  mandatory
              DESCRIPTION
                      "When set to enableAdd(1) the instantiations will
                       be used to create a new table entry (row).
                       Existing entries can be disabled(2) or deleted (3)."
              ::= { portVLANEntry 3 }


          -- ssSlip group

          slipEnable OBJECT-TYPE
              SYNTAX  INTEGER
              ACCESS  read-write
              STATUS  mandatory
              DESCRIPTION
                      "enable/disable SLIP"
              ::= { ssSlip 1 }

          slipHostIP OBJECT-TYPE
              SYNTAX  IpAddress
              ACCESS  read-write
              STATUS  mandatory
              DESCRIPTION
                      "SLIP Remote IP Addr"
              ::= { ssSlip 2 }

          END
