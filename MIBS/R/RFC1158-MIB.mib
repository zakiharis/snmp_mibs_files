RFC1158-MIB DEFINITIONS ::= BEGIN

IMPORTS 	IpAddress, enterprises, Gauge, TimeTicks, Counter, OBJECT-TYPE
				FROM RFC1155-SMI
			PhysAddress
				FROM SNMPv2-TC;

          ncd                           OBJECT IDENTIFIER ::= { enterprises 82 }
          ncd-mibs                      OBJECT IDENTIFIER ::= { ncd 2 }
          ncd-mibs-mib1                 OBJECT IDENTIFIER ::= { ncd-mibs 1 }
          ncd-mibs-mib2                 OBJECT IDENTIFIER ::= { ncd-mibs 2 }
          ncd-mibs-mib3                 OBJECT IDENTIFIER ::= { ncd-mibs 3 }
          ncdSystem                     OBJECT IDENTIFIER ::= { ncd-mibs-mib1 1 }
          ncdMbuf                       OBJECT IDENTIFIER ::= { ncd-mibs-mib1 2 }
          ncdEther                      OBJECT IDENTIFIER ::= { ncd-mibs-mib1 3 }
          ncdSerial                     OBJECT IDENTIFIER ::= { ncd-mibs-mib1 4 }
          ncdTcp                        OBJECT IDENTIFIER ::= { ncd-mibs-mib1 5 }
          ncdTftp                       OBJECT IDENTIFIER ::= { ncd-mibs-mib1 7 }
          ncdNfs                        OBJECT IDENTIFIER ::= { ncd-mibs-mib1 8 }
          ncdXdmcp                      OBJECT IDENTIFIER ::= { ncd-mibs-mib2 11 }
          ncdDecnet                     OBJECT IDENTIFIER ::= { ncd-mibs-mib2 12 }
          ncdLat                        OBJECT IDENTIFIER ::= { ncd-mibs-mib2 13 }
          ncdNameResolver               OBJECT IDENTIFIER ::= { ncd-mibs-mib2 14 }
          ncdFontService                OBJECT IDENTIFIER ::= { ncd-mibs-mib2 15 }
          ncdArp                        OBJECT IDENTIFIER ::= { ncd-mibs-mib2 19 }
          ncdIp                         OBJECT IDENTIFIER ::= { ncd-mibs-mib3 1 }
          ncdUdp                        OBJECT IDENTIFIER ::= { ncd-mibs-mib3 2 }
          ncdSerialDaemon               OBJECT IDENTIFIER ::= { ncd-mibs-mib3 3 }
          ncdDnetNameResolver           OBJECT IDENTIFIER ::= { ncd-mibs-mib3 4 }
          ncdBoot                       OBJECT IDENTIFIER ::= { ncd-mibs-mib3 5 }
          ncdConfig                     OBJECT IDENTIFIER ::= { ncd-mibs-mib3 6 }
          ncdXserver                    OBJECT IDENTIFIER ::= { ncd-mibs-mib3 7 }
          ncdDiag                       OBJECT IDENTIFIER ::= { ncd-mibs-mib3 8 }
          ncdDps                        OBJECT IDENTIFIER ::= { ncd-mibs-mib3 9 }
          ncdExec                       OBJECT IDENTIFIER ::= { ncd-mibs-mib3 10 }
          ncdLogin                      OBJECT IDENTIFIER ::= { ncd-mibs-mib3 11 }
          ncdPex                        OBJECT IDENTIFIER ::= { ncd-mibs-mib3 12 }
          ncdTerm                       OBJECT IDENTIFIER ::= { ncd-mibs-mib3 13 }
          ncdFile                       OBJECT IDENTIFIER ::= { ncd-mibs-mib3 14 }
          ncdPref                       OBJECT IDENTIFIER ::= { ncd-mibs-mib3 15 }
          ncdAccess                     OBJECT IDENTIFIER ::= { ncd-mibs-mib3 16 }
          ncdTokenRing                  OBJECT IDENTIFIER ::= { ncd-mibs-mib3 17 }
          ncdXremote                    OBJECT IDENTIFIER ::= { ncd-mibs-mib3 18 }
          ncdPpp                        OBJECT IDENTIFIER ::= { ncd-mibs-mib3 19 }
          ncdPrefPex                    OBJECT IDENTIFIER ::= { ncd-mibs-mib3 20 }
          ncd3270                       OBJECT IDENTIFIER ::= { ncd-mibs-mib3 21 }
          ncdParallel                   OBJECT IDENTIFIER ::= { ncd-mibs-mib3 22 }
          ncdTBD                        OBJECT IDENTIFIER ::= { ncd-mibs-mib3 99 }

          -- the ncdSystem Group

          ncdSysMemTotal OBJECT-TYPE
              SYNTAX  INTEGER
              ACCESS  read-only
              STATUS  optional
			  DESCRIPTION ""
              ::= { ncdSystem 1 }

          ncdSysMemAvail OBJECT-TYPE
              SYNTAX  Gauge
              ACCESS  read-only
              STATUS  optional
			  DESCRIPTION ""
              ::= { ncdSystem 2 }

          ncdSysMemFrags OBJECT-TYPE
              SYNTAX  Gauge
              ACCESS  read-only
              STATUS  optional
			  DESCRIPTION ""
              ::= { ncdSystem 3 }

          ncdSysIdleTime OBJECT-TYPE
              SYNTAX  TimeTicks
              ACCESS  read-only
              STATUS  optional
			  DESCRIPTION ""
              ::= { ncdSystem 4 }

          ncdSysBootPromVersion OBJECT-TYPE
              SYNTAX  OCTET STRING
              ACCESS  read-only
              STATUS  optional
			  DESCRIPTION ""
              ::= { ncdSystem 5 }

          ncdSysKeyboardControllerVersion OBJECT-TYPE
              SYNTAX  OCTET STRING
              ACCESS  read-only
              STATUS  optional
			  DESCRIPTION ""
              ::= { ncdSystem 6 }

          ncdSysAdminStatus OBJECT-TYPE
              SYNTAX  INTEGER
              ACCESS  read-write
              STATUS  optional
			  DESCRIPTION ""
              ::= { ncdSystem 7 }

          ncdSysMemCode OBJECT-TYPE
              SYNTAX  INTEGER
              ACCESS  read-only
              STATUS  optional
			  DESCRIPTION ""
              ::= { ncdSystem 8 }

          ncdSysQueryNameAtBoot OBJECT-TYPE
              SYNTAX  INTEGER
              ACCESS  read-write
              STATUS  optional
			  DESCRIPTION ""
              ::= { ncdSystem 9 }

          ncdSysLowMemWarningThreshold OBJECT-TYPE
              SYNTAX  INTEGER
              ACCESS  read-write
              STATUS  optional
			  DESCRIPTION ""
              ::= { ncdSystem 10 }

          ncdSysLicenseKey OBJECT-TYPE
              SYNTAX  OCTET STRING
              ACCESS  read-write
              STATUS  optional
			  DESCRIPTION ""
              ::= { ncdSystem 11 }

          ncdSysLicensedFeatures OBJECT-TYPE
              SYNTAX  OCTET STRING
              ACCESS  read-only
              STATUS  optional
			  DESCRIPTION ""
              ::= { ncdSystem 12 }

          ncdSysOptionalFeatures OBJECT-TYPE
              SYNTAX  OCTET STRING
              ACCESS  read-only
              STATUS  optional
			  DESCRIPTION ""
              ::= { ncdSystem 13 }


          -- the ncdMbuf Group

          ncdMbufTotal OBJECT-TYPE
              SYNTAX  INTEGER
              ACCESS  read-only
              STATUS  optional
			  DESCRIPTION ""
              ::= { ncdMbuf 1 }

          ncdMbufAvail OBJECT-TYPE
              SYNTAX  Gauge
              ACCESS  read-only
              STATUS  optional
			  DESCRIPTION ""
              ::= { ncdMbuf 2 }

          ncdMbufClusterTotal OBJECT-TYPE
              SYNTAX  INTEGER
              ACCESS  read-only
              STATUS  optional
			  DESCRIPTION ""
              ::= { ncdMbuf 3 }

          ncdMbufClusterAvail OBJECT-TYPE
              SYNTAX  Gauge
              ACCESS  read-only
              STATUS  optional
			  DESCRIPTION ""
              ::= { ncdMbuf 4 }

          ncdMbufReserved OBJECT-TYPE
              SYNTAX  Gauge
              ACCESS  read-only
              STATUS  optional
			  DESCRIPTION ""
              ::= { ncdMbuf 5 }

          ncdMbufDrops OBJECT-TYPE
              SYNTAX  Counter
              ACCESS  read-only
              STATUS  optional
			  DESCRIPTION ""
              ::= { ncdMbuf 6 }

          ncdMbufWaits OBJECT-TYPE
              SYNTAX  Counter
              ACCESS  read-only
              STATUS  optional
			  DESCRIPTION ""
              ::= { ncdMbuf 7 }

          ncdMbufPacketDatas OBJECT-TYPE
              SYNTAX  Gauge
              ACCESS  read-only
              STATUS  optional
			  DESCRIPTION ""
              ::= { ncdMbuf 8 }

          ncdMbufPacketHeaders OBJECT-TYPE
              SYNTAX  Gauge
              ACCESS  read-only
              STATUS  optional
			  DESCRIPTION ""
              ::= { ncdMbuf 9 }

          ncdMbufConnCtrlStructs OBJECT-TYPE
              SYNTAX  Gauge
              ACCESS  read-only
              STATUS  optional
			  DESCRIPTION ""
              ::= { ncdMbuf 10 }

          ncdMbufATTable OBJECT-TYPE
              SYNTAX  Gauge
              ACCESS  read-only
              STATUS  optional
			  DESCRIPTION ""
              ::= { ncdMbuf 11 }

          ncdMbufConnNames OBJECT-TYPE
              SYNTAX  Gauge
              ACCESS  read-only
              STATUS  optional
			  DESCRIPTION ""
              ::= { ncdMbuf 12 }

          ncdMbufConnOptions OBJECT-TYPE
              SYNTAX  Gauge
              ACCESS  read-only
              STATUS  optional
			  DESCRIPTION ""
              ::= { ncdMbuf 13 }

          ncdMbufFrags OBJECT-TYPE
              SYNTAX  Gauge
              ACCESS  read-only
              STATUS  optional
			  DESCRIPTION ""
              ::= { ncdMbuf 14 }

          ncdMbufInterfaceAddr OBJECT-TYPE
              SYNTAX  Gauge
              ACCESS  read-only
              STATUS  optional
			  DESCRIPTION ""
              ::= { ncdMbuf 15 }

          ncdMbufProtoCtrlStructs OBJECT-TYPE
              SYNTAX  Gauge
              ACCESS  read-only
              STATUS  optional
			  DESCRIPTION ""
              ::= { ncdMbuf 16 }


          -- the ncdEther Group

          ncdEtherTable OBJECT-TYPE
              SYNTAX  SEQUENCE OF NcdEtherEntry
              ACCESS  not-accessible
              STATUS  optional
			  DESCRIPTION ""
              ::= { ncdEther 1 }

          ncdEtherEntry OBJECT-TYPE
              SYNTAX  NcdEtherEntry
              ACCESS  not-accessible
              STATUS  optional
			  DESCRIPTION ""
              ::= { ncdEtherTable 1 }

          NcdEtherEntry ::=
              SEQUENCE {
                  ncdEtherTableIndex
                      INTEGER,
                  ncdEtherInCrcErrors
                      Counter,
                  ncdEtherInMisseds
                      Counter,
                  ncdEtherInFrameErrors
                      Counter,
                  ncdEtherSingleCollisions
                      Counter,
                  ncdEtherMultipleCollisions
                      Counter,
                  ncdEtherLateCollisions
                      Counter,
                  ncdEtherOutDeferreds
                      Counter,
                  ncdEtherOutRetryErrors
                      Counter,
                  ncdEtherLostCarriers
                      Counter,
                  ncdEtherRestarts
                      Counter
              }

          ncdEtherTableIndex OBJECT-TYPE
              SYNTAX  INTEGER
              ACCESS  read-only
              STATUS  optional
			  DESCRIPTION ""
              ::= { ncdEtherEntry 11 }

          ncdEtherInCrcErrors OBJECT-TYPE
              SYNTAX  Counter
              ACCESS  read-only
              STATUS  optional
			  DESCRIPTION ""
              ::= { ncdEtherEntry 1 }

          ncdEtherInMisseds OBJECT-TYPE
              SYNTAX  Counter
              ACCESS  read-only
              STATUS  optional
			  DESCRIPTION ""
              ::= { ncdEtherEntry 2 }

          ncdEtherInFrameErrors OBJECT-TYPE
              SYNTAX  Counter
              ACCESS  read-only
              STATUS  optional
			  DESCRIPTION ""
              ::= { ncdEtherEntry 3 }

          ncdEtherSingleCollisions OBJECT-TYPE
              SYNTAX  Counter
              ACCESS  read-only
              STATUS  optional
			  DESCRIPTION ""
              ::= { ncdEtherEntry 4 }

          ncdEtherMultipleCollisions OBJECT-TYPE
              SYNTAX  Counter
              ACCESS  read-only
              STATUS  optional
			  DESCRIPTION ""
              ::= { ncdEtherEntry 5 }

          ncdEtherLateCollisions OBJECT-TYPE
              SYNTAX  Counter
              ACCESS  read-only
              STATUS  optional
			  DESCRIPTION ""
              ::= { ncdEtherEntry 6 }

          ncdEtherOutDeferreds OBJECT-TYPE
              SYNTAX  Counter
              ACCESS  read-only
              STATUS  optional
			  DESCRIPTION ""
              ::= { ncdEtherEntry 7 }

          ncdEtherOutRetryErrors OBJECT-TYPE
              SYNTAX  Counter
              ACCESS  read-only
              STATUS  optional
			  DESCRIPTION ""
              ::= { ncdEtherEntry 8 }

          ncdEtherLostCarriers OBJECT-TYPE
              SYNTAX  Counter
              ACCESS  read-only
              STATUS  optional
			  DESCRIPTION ""
              ::= { ncdEtherEntry 9 }

          ncdEtherRestarts OBJECT-TYPE
              SYNTAX  Counter
              ACCESS  read-only
              STATUS  optional
			  DESCRIPTION ""
              ::= { ncdEtherEntry 10 }

          ncdEtherUseSNAPEncap OBJECT-TYPE
              SYNTAX  INTEGER
              ACCESS  read-write
              STATUS  optional
			  DESCRIPTION ""
              ::= { ncdEther 11 }


          -- the ncdSerial Group

          ncdSerialTable OBJECT-TYPE
              SYNTAX  SEQUENCE OF NcdSerialEntry
              ACCESS  not-accessible
              STATUS  optional
			  DESCRIPTION ""
              ::= { ncdSerial 1 }

          ncdSerialEntry OBJECT-TYPE
              SYNTAX  NcdSerialEntry
              ACCESS  not-accessible
              STATUS  optional
			  DESCRIPTION ""
              ::= { ncdSerialTable 1 }

          NcdSerialEntry ::=
              SEQUENCE {
                  ncdSerialInPortNumber
                      INTEGER,
                  ncdSerialInOverruns
                      INTEGER,
                  ncdSerialInFrameErrors
                      INTEGER,
                  ncdSerialInParityErrors
                      INTEGER,
                  ncdSerialInBreakErrors
                      INTEGER,
                  ncdSerialInTotCharXmit
                      INTEGER,
                  ncdSerialInTotXmitInt
                      INTEGER,
                  ncdSerialInTotCharRcv
                      INTEGER,
                  ncdSerialInTotRcvInt
                      INTEGER,
                  ncdSerialInTotRcvErr
                      INTEGER
              }

          ncdSerialInPortNumber OBJECT-TYPE
              SYNTAX  INTEGER
              ACCESS  read-only
              STATUS  optional
			  DESCRIPTION ""
              ::= { ncdSerialEntry 5 }

          ncdSerialInOverruns OBJECT-TYPE
              SYNTAX  INTEGER
              ACCESS  read-only
              STATUS  optional
			  DESCRIPTION ""
              ::= { ncdSerialEntry 1 }

          ncdSerialInFrameErrors OBJECT-TYPE
              SYNTAX  INTEGER
              ACCESS  read-only
              STATUS  optional
			  DESCRIPTION ""
              ::= { ncdSerialEntry 2 }

          ncdSerialInParityErrors OBJECT-TYPE
              SYNTAX  INTEGER
              ACCESS  read-only
              STATUS  optional
			  DESCRIPTION ""
              ::= { ncdSerialEntry 3 }

          ncdSerialInBreakErrors OBJECT-TYPE
              SYNTAX  INTEGER
              ACCESS  read-only
              STATUS  optional
			  DESCRIPTION ""
              ::= { ncdSerialEntry 4 }

          ncdSerialInTotCharXmit OBJECT-TYPE
              SYNTAX  INTEGER
              ACCESS  read-only
              STATUS  optional
			  DESCRIPTION ""
              ::= { ncdSerialEntry 6 }

          ncdSerialInTotXmitInt OBJECT-TYPE
              SYNTAX  INTEGER
              ACCESS  read-only
              STATUS  optional
			  DESCRIPTION ""
              ::= { ncdSerialEntry 7 }

          ncdSerialInTotCharRcv OBJECT-TYPE
              SYNTAX  INTEGER
              ACCESS  read-only
              STATUS  optional
			  DESCRIPTION ""
              ::= { ncdSerialEntry 8 }

          ncdSerialInTotRcvInt OBJECT-TYPE
              SYNTAX  INTEGER
              ACCESS  read-only
              STATUS  optional
			  DESCRIPTION ""
              ::= { ncdSerialEntry 9 }

          ncdSerialInTotRcvErr OBJECT-TYPE
              SYNTAX  INTEGER
              ACCESS  read-only
              STATUS  optional
			  DESCRIPTION ""
              ::= { ncdSerialEntry 10 }

          ncdSerialIfTable OBJECT-TYPE
              SYNTAX  SEQUENCE OF NcdSerialIfEntry
              ACCESS  not-accessible
              STATUS  optional
			  DESCRIPTION ""
              ::= { ncdSerial 2 }

          ncdSerialIfEntry OBJECT-TYPE
              SYNTAX  NcdSerialIfEntry
              ACCESS  not-accessible
              STATUS  optional
			  DESCRIPTION ""
              ::= { ncdSerialIfTable 1 }

          NcdSerialIfEntry ::=
              SEQUENCE {
                  ncdSerialIfTableIndex
                      INTEGER,
                  ncdSerialIfTablePortNumber
                      INTEGER,
                  ncdSerialIfTableMode
                      INTEGER,
                  ncdSerialIfTableCurMode
                      INTEGER,
                  ncdSerialIfTableBaudRate
                      INTEGER,
                  ncdSerialIfTableDataBits
                      INTEGER,
                  ncdSerialIfTableStopBits
                      INTEGER,
                  ncdSerialIfTableParity
                      INTEGER,
                  ncdSerialIfTableHandshake
                      INTEGER,
                  ncdSerialIfTableActionOnDiscon
                      INTEGER
              }

          ncdSerialIfTableIndex OBJECT-TYPE
              SYNTAX  INTEGER
              ACCESS  read-only
              STATUS  optional
			  DESCRIPTION ""
              ::= { ncdSerialIfEntry 1 }

          ncdSerialIfTablePortNumber OBJECT-TYPE
              SYNTAX  INTEGER
              ACCESS  read-only
              STATUS  optional
			  DESCRIPTION ""
              ::= { ncdSerialIfEntry 2 }

          ncdSerialIfTableMode OBJECT-TYPE
              SYNTAX  INTEGER
              ACCESS  read-write
              STATUS  optional
			  DESCRIPTION ""
              ::= { ncdSerialIfEntry 3 }

          ncdSerialIfTableCurMode OBJECT-TYPE
              SYNTAX  INTEGER
              ACCESS  read-write
              STATUS  optional
			  DESCRIPTION ""
              ::= { ncdSerialIfEntry 9 }

          ncdSerialIfTableBaudRate OBJECT-TYPE
              SYNTAX  INTEGER
              ACCESS  read-write
              STATUS  optional
			  DESCRIPTION ""
              ::= { ncdSerialIfEntry 4 }

          ncdSerialIfTableDataBits OBJECT-TYPE
              SYNTAX  INTEGER
              ACCESS  read-write
              STATUS  optional
			  DESCRIPTION ""
              ::= { ncdSerialIfEntry 5 }

          ncdSerialIfTableStopBits OBJECT-TYPE
              SYNTAX  INTEGER
              ACCESS  read-write
              STATUS  optional
			  DESCRIPTION ""
              ::= { ncdSerialIfEntry 6 }

          ncdSerialIfTableParity OBJECT-TYPE
              SYNTAX  INTEGER
              ACCESS  read-write
              STATUS  optional
			  DESCRIPTION ""
              ::= { ncdSerialIfEntry 7 }

          ncdSerialIfTableHandshake OBJECT-TYPE
              SYNTAX  INTEGER
              ACCESS  read-write
              STATUS  optional
			  DESCRIPTION ""
              ::= { ncdSerialIfEntry 8 }

          ncdSerialIfTableActionOnDiscon OBJECT-TYPE
              SYNTAX  INTEGER
              ACCESS  read-write
              STATUS  optional
			  DESCRIPTION ""
              ::= { ncdSerialIfEntry 10 }

          ncdSerialSDTable OBJECT-TYPE
              SYNTAX  SEQUENCE OF NcdSerialSDEntry
              ACCESS  not-accessible
              STATUS  optional
			  DESCRIPTION ""
              ::= { ncdSerial 3 }

          ncdSerialSDEntry OBJECT-TYPE
              SYNTAX  NcdSerialSDEntry
              ACCESS  not-accessible
              STATUS  optional
			  DESCRIPTION ""
              ::= { ncdSerialSDTable 1 }

          NcdSerialSDEntry ::=
              SEQUENCE {
                  ncdSerialSDTableIndex
                      INTEGER,
                  ncdSerialSDTablePortNumber
                      INTEGER,
                  ncdSerialSDTableUseSerialProt
                      INTEGER,
                  ncdSerialSDTableTCPPort
                      INTEGER,
                  ncdSerialSDTableUseNCDnetObjName
                      OCTET STRING,
                  ncdSerialSDTableEnableLAT
                      INTEGER,
                  ncdSerialSDTableLATServName
                      OCTET STRING,
                  ncdSerialSDTableLATServRating
                      INTEGER
              }

          ncdSerialSDTableIndex OBJECT-TYPE
              SYNTAX  INTEGER
              ACCESS  read-only
              STATUS  optional
			  DESCRIPTION ""
              ::= { ncdSerialSDEntry 1 }

          ncdSerialSDTablePortNumber OBJECT-TYPE
              SYNTAX  INTEGER
              ACCESS  read-only
              STATUS  optional
			  DESCRIPTION ""
              ::= { ncdSerialSDEntry 2 }

          ncdSerialSDTableUseSerialProt OBJECT-TYPE
              SYNTAX  INTEGER
              ACCESS  read-write
              STATUS  optional
			  DESCRIPTION ""
              ::= { ncdSerialSDEntry 3 }

          ncdSerialSDTableTCPPort OBJECT-TYPE
              SYNTAX  INTEGER
              ACCESS  read-write
              STATUS  optional
			  DESCRIPTION ""
              ::= { ncdSerialSDEntry 4 }

          ncdSerialSDTableUseNCDnetObjName OBJECT-TYPE
              SYNTAX  OCTET STRING
              ACCESS  read-write
              STATUS  optional
			  DESCRIPTION ""
              ::= { ncdSerialSDEntry 5 }

          ncdSerialSDTableEnableLAT OBJECT-TYPE
              SYNTAX  INTEGER
              ACCESS  read-write
              STATUS  optional
			  DESCRIPTION ""
              ::= { ncdSerialSDEntry 6 }

          ncdSerialSDTableLATServName OBJECT-TYPE
              SYNTAX  OCTET STRING
              ACCESS  read-write
              STATUS  optional
			  DESCRIPTION ""
              ::= { ncdSerialSDEntry 7 }

          ncdSerialSDTableLATServRating OBJECT-TYPE
              SYNTAX  INTEGER
              ACCESS  read-write
              STATUS  optional
			  DESCRIPTION ""
              ::= { ncdSerialSDEntry 8 }


          -- the ncdTcp Group

          ncdTcpRetransDrops OBJECT-TYPE
              SYNTAX  Counter
              ACCESS  read-only
              STATUS  optional
			  DESCRIPTION ""
              ::= { ncdTcp 1 }

          ncdTcpOutKeepAlives OBJECT-TYPE
              SYNTAX  Counter
              ACCESS  read-only
              STATUS  optional
			  DESCRIPTION ""
              ::= { ncdTcp 2 }

          ncdTcpKeepAliveDrops OBJECT-TYPE
              SYNTAX  Counter
              ACCESS  read-only
              STATUS  optional
			  DESCRIPTION ""
              ::= { ncdTcp 3 }

          ncdTcpInAcks OBJECT-TYPE
              SYNTAX  Counter
              ACCESS  read-only
              STATUS  optional
			  DESCRIPTION ""
              ::= { ncdTcp 4 }

          ncdTcpOutBareAcks OBJECT-TYPE
              SYNTAX  Counter
              ACCESS  read-only
              STATUS  optional
			  DESCRIPTION ""
              ::= { ncdTcp 5 }

          ncdTcpConnectTimeout OBJECT-TYPE
              SYNTAX  TimeTicks
              ACCESS  read-write
              STATUS  optional
			  DESCRIPTION ""
              ::= { ncdTcp 6 }

          ncdTcpMaxRxt OBJECT-TYPE
              SYNTAX  INTEGER
              ACCESS  read-write
              STATUS  optional
			  DESCRIPTION ""
              ::= { ncdTcp 7 }

          ncdTcpKeepIdle OBJECT-TYPE
              SYNTAX  TimeTicks
              ACCESS  read-write
              STATUS  optional
			  DESCRIPTION ""
              ::= { ncdTcp 8 }

          ncdTcpKeepAliveIntvl OBJECT-TYPE
              SYNTAX  TimeTicks
              ACCESS  read-write
              STATUS  optional
			  DESCRIPTION ""
              ::= { ncdTcp 9 }

          ncdTcpMaxKeepAliveIdeTime OBJECT-TYPE
              SYNTAX  TimeTicks
              ACCESS  read-write
              STATUS  optional
			  DESCRIPTION ""
              ::= { ncdTcp 10 }

          ncdTcpDfltLingerTime OBJECT-TYPE
              SYNTAX  TimeTicks
              ACCESS  read-write
              STATUS  optional
			  DESCRIPTION ""
              ::= { ncdTcp 11 }

          ncdTcpRecvBufferSize OBJECT-TYPE
              SYNTAX  INTEGER
              ACCESS  read-write
              STATUS  optional
			  DESCRIPTION ""
              ::= { ncdTcp 12 }

          ncdTcpSendBufferSize OBJECT-TYPE
              SYNTAX  INTEGER
              ACCESS  read-write
              STATUS  optional
			  DESCRIPTION ""
              ::= { ncdTcp 13 }


          -- the ncdTftp Group

          ncdTftpClientReadReqs OBJECT-TYPE
              SYNTAX  Counter
              ACCESS  read-only
              STATUS  optional
			  DESCRIPTION ""
              ::= { ncdTftp 1 }

          ncdTftpClientWriteReqs OBJECT-TYPE
              SYNTAX  Counter
              ACCESS  read-only
              STATUS  optional
			  DESCRIPTION ""
              ::= { ncdTftp 2 }

          ncdTftpClientInDataPkts OBJECT-TYPE
              SYNTAX  Counter
              ACCESS  read-only
              STATUS  optional
			  DESCRIPTION ""
              ::= { ncdTftp 3 }

          ncdTftpClientInAcks OBJECT-TYPE
              SYNTAX  Counter
              ACCESS  read-only
              STATUS  optional
			  DESCRIPTION ""
              ::= { ncdTftp 4 }

          ncdTftpClientInNoFileErrors OBJECT-TYPE
              SYNTAX  Counter
              ACCESS  read-only
              STATUS  optional
			  DESCRIPTION ""
              ::= { ncdTftp 5 }

          ncdTftpClientInAccessErrors OBJECT-TYPE
              SYNTAX  Counter
              ACCESS  read-only
              STATUS  optional
			  DESCRIPTION ""
              ::= { ncdTftp 6 }

          ncdTftpClientInDiskFullErrors OBJECT-TYPE
              SYNTAX  Counter
              ACCESS  read-only
              STATUS  optional
			  DESCRIPTION ""
              ::= { ncdTftp 7 }

          ncdTftpClientNoBufs OBJECT-TYPE
              SYNTAX  Counter
              ACCESS  read-only
              STATUS  optional
			  DESCRIPTION ""
              ::= { ncdTftp 8 }

          ncdTftpClientOutDataPkts OBJECT-TYPE
              SYNTAX  Counter
              ACCESS  read-only
              STATUS  optional
			  DESCRIPTION ""
              ::= { ncdTftp 9 }

          ncdTftpClientOutAcks OBJECT-TYPE
              SYNTAX  Counter
              ACCESS  read-only
              STATUS  optional
			  DESCRIPTION ""
              ::= { ncdTftp 10 }

          ncdTftpClientRetrans OBJECT-TYPE
              SYNTAX  Counter
              ACCESS  read-only
              STATUS  optional
			  DESCRIPTION ""
              ::= { ncdTftp 11 }


          -- the ncdNfs Group

          ncdNfsClientNulls OBJECT-TYPE
              SYNTAX  Counter
              ACCESS  read-only
              STATUS  optional
			  DESCRIPTION ""
              ::= { ncdNfs 1 }

          ncdNfsClientGetAttributes OBJECT-TYPE
              SYNTAX  Counter
              ACCESS  read-only
              STATUS  optional
			  DESCRIPTION ""
              ::= { ncdNfs 2 }

          ncdNfsClientSetAttributes OBJECT-TYPE
              SYNTAX  Counter
              ACCESS  read-only
              STATUS  optional
			  DESCRIPTION ""
              ::= { ncdNfs 3 }

          ncdNfsClientGetRoots OBJECT-TYPE
              SYNTAX  Counter
              ACCESS  read-only
              STATUS  optional
			  DESCRIPTION ""
              ::= { ncdNfs 4 }

          ncdNfsClientLookups OBJECT-TYPE
              SYNTAX  Counter
              ACCESS  read-only
              STATUS  optional
			  DESCRIPTION ""
              ::= { ncdNfs 5 }

          ncdNfsClientReadLinks OBJECT-TYPE
              SYNTAX  Counter
              ACCESS  read-only
              STATUS  optional
			  DESCRIPTION ""
              ::= { ncdNfs 6 }

          ncdNfsClientReads OBJECT-TYPE
              SYNTAX  Counter
              ACCESS  read-only
              STATUS  optional
			  DESCRIPTION ""
              ::= { ncdNfs 7 }

          ncdNfsClientWriteCaches OBJECT-TYPE
              SYNTAX  Counter
              ACCESS  read-only
              STATUS  optional
			  DESCRIPTION ""
              ::= { ncdNfs 8 }

          ncdNfsClientWrites OBJECT-TYPE
              SYNTAX  Counter
              ACCESS  read-only
              STATUS  optional
			  DESCRIPTION ""
              ::= { ncdNfs 9 }

          ncdNfsClientCreates OBJECT-TYPE
              SYNTAX  Counter
              ACCESS  read-only
              STATUS  optional
			  DESCRIPTION ""
              ::= { ncdNfs 10 }

          ncdNfsClientRemoves OBJECT-TYPE
              SYNTAX  Counter
              ACCESS  read-only
              STATUS  optional
			  DESCRIPTION ""
              ::= { ncdNfs 11 }

          ncdNfsClientRenames OBJECT-TYPE
              SYNTAX  Counter
              ACCESS  read-only
              STATUS  optional
			  DESCRIPTION ""
              ::= { ncdNfs 12 }

          ncdNfsClientCreateLinks OBJECT-TYPE
              SYNTAX  Counter
              ACCESS  read-only
              STATUS  optional
			  DESCRIPTION ""
              ::= { ncdNfs 13 }

          ncdNfsClientCreateSymlinks OBJECT-TYPE
              SYNTAX  Counter
              ACCESS  read-only
              STATUS  optional
			  DESCRIPTION ""
              ::= { ncdNfs 14 }

          ncdNfsClientMakeDirs OBJECT-TYPE
              SYNTAX  Counter
              ACCESS  read-only
              STATUS  optional
			  DESCRIPTION ""
              ::= { ncdNfs 15 }

          ncdNfsClientRemoveDirs OBJECT-TYPE
              SYNTAX  Counter
              ACCESS  read-only
              STATUS  optional
			  DESCRIPTION ""
              ::= { ncdNfs 16 }

          ncdNfsClientReadDirs OBJECT-TYPE
              SYNTAX  Counter
              ACCESS  read-only
              STATUS  optional
			  DESCRIPTION ""
              ::= { ncdNfs 17 }

          ncdNfsClientFileSysStats OBJECT-TYPE
              SYNTAX  Counter
              ACCESS  read-only
              STATUS  optional
			  DESCRIPTION ""
              ::= { ncdNfs 18 }


          -- the ncdXdmcp Group

          ncdXdmcpSendKeepAlivesTime OBJECT-TYPE
              SYNTAX  TimeTicks
              ACCESS  read-write
              STATUS  optional
			  DESCRIPTION ""
              ::= { ncdXdmcp 1 }

          ncdXdmcpKeepAlivesDeadTime OBJECT-TYPE
              SYNTAX  TimeTicks
              ACCESS  read-write
              STATUS  optional
			  DESCRIPTION ""
              ::= { ncdXdmcp 2 }

          ncdXdmcpcpDisplayClass OBJECT-TYPE
              SYNTAX  OCTET STRING
              ACCESS  read-write
              STATUS  optional
			  DESCRIPTION ""
              ::= { ncdXdmcp 3 }

          ncdXdmcpMfgDisplayId OBJECT-TYPE
              SYNTAX  OCTET STRING
              ACCESS  read-only
              STATUS  optional
			  DESCRIPTION ""
              ::= { ncdXdmcp 4 }

          ncdXdmcpBroadcastWaitTime OBJECT-TYPE
              SYNTAX  INTEGER
              ACCESS  read-write
              STATUS  optional
			  DESCRIPTION ""
              ::= { ncdXdmcp 5 }

          ncdXdmcpBroadcasts OBJECT-TYPE
              SYNTAX  INTEGER
              ACCESS  read-write
              STATUS  optional
			  DESCRIPTION ""
              ::= { ncdXdmcp 6 }

          ncdXdmcpIndirects OBJECT-TYPE
              SYNTAX  INTEGER
              ACCESS  read-write
              STATUS  optional
			  DESCRIPTION ""
              ::= { ncdXdmcp 7 }

          ncdXdmcpWhenFirstClientExits OBJECT-TYPE
              SYNTAX  INTEGER
              ACCESS  read-write
              STATUS  optional
			  DESCRIPTION ""
              ::= { ncdXdmcp 8 }


          -- the ncdDecnet Group

          ncdDecnetConnectTimeout OBJECT-TYPE
              SYNTAX  TimeTicks
              ACCESS  read-write
              STATUS  optional
			  DESCRIPTION ""
              ::= { ncdDecnet 1 }

          ncdDecnetRetransLimit OBJECT-TYPE
              SYNTAX  INTEGER
              ACCESS  read-write
              STATUS  optional
			  DESCRIPTION ""
              ::= { ncdDecnet 2 }

          ncdDecnetKeepaliveTimeout OBJECT-TYPE
              SYNTAX  TimeTicks
              ACCESS  read-write
              STATUS  optional
			  DESCRIPTION ""
              ::= { ncdDecnet 3 }

          ncdDecnetHelloTimeout OBJECT-TYPE
              SYNTAX  TimeTicks
              ACCESS  read-write
              STATUS  optional
			  DESCRIPTION ""
              ::= { ncdDecnet 4 }

          ncdDecnetRouterTimeout OBJECT-TYPE
              SYNTAX  TimeTicks
              ACCESS  read-write
              STATUS  optional
			  DESCRIPTION ""
              ::= { ncdDecnet 5 }

          ncdDecnetMopIdTimeout OBJECT-TYPE
              SYNTAX  TimeTicks
              ACCESS  read-write
              STATUS  optional
			  DESCRIPTION ""
              ::= { ncdDecnet 6 }

          ncdDecnetAddress OBJECT-TYPE
              SYNTAX  PhysAddress
              ACCESS  read-only
              STATUS  optional
			  DESCRIPTION ""
              ::= { ncdDecnet 8 }

          ncdDecnetNewAddress OBJECT-TYPE
              SYNTAX  PhysAddress
              ACCESS  read-write
              STATUS  optional
			  DESCRIPTION ""
              ::= { ncdDecnet 9 }

          ncdDecnetDesignatedRouter OBJECT-TYPE
              SYNTAX  PhysAddress
              ACCESS  read-write
              STATUS  optional
			  DESCRIPTION ""
              ::= { ncdDecnet 10 }

          ncdDecnetDnetUserName OBJECT-TYPE
              SYNTAX  OCTET STRING
              ACCESS  read-write
              STATUS  optional
			  DESCRIPTION ""
              ::= { ncdDecnet 11 }

          ncdDecnetMopResetEnabled OBJECT-TYPE
              SYNTAX  INTEGER
              ACCESS  read-write
              STATUS  optional
			  DESCRIPTION ""
              ::= { ncdDecnet 12 }

          ncdDecnetDataBlocksXmt OBJECT-TYPE
              SYNTAX  INTEGER
              ACCESS  read-only
              STATUS  optional
			  DESCRIPTION ""
              ::= { ncdDecnet 13 }

          ncdDecnetDataBlocksRcv OBJECT-TYPE
              SYNTAX  INTEGER
              ACCESS  read-only
              STATUS  optional
			  DESCRIPTION ""
              ::= { ncdDecnet 14 }

          ncdDecnetDataBytesXmt OBJECT-TYPE
              SYNTAX  INTEGER
              ACCESS  read-only
              STATUS  optional
			  DESCRIPTION ""
              ::= { ncdDecnet 15 }

          ncdDecnetDataBytesRcv OBJECT-TYPE
              SYNTAX  INTEGER
              ACCESS  read-only
              STATUS  optional
			  DESCRIPTION ""
              ::= { ncdDecnet 16 }

          ncdDecnetHelloPacketsXmt OBJECT-TYPE
              SYNTAX  INTEGER
              ACCESS  read-only
              STATUS  optional
			  DESCRIPTION ""
              ::= { ncdDecnet 17 }

          ncdDecnetHelloPacketsRcv OBJECT-TYPE
              SYNTAX  INTEGER
              ACCESS  read-only
              STATUS  optional
			  DESCRIPTION ""
              ::= { ncdDecnet 18 }

          ncdDecnetCntCircDown OBJECT-TYPE
              SYNTAX  INTEGER
              ACCESS  read-only
              STATUS  optional
			  DESCRIPTION ""
              ::= { ncdDecnet 19 }

          ncdDecnetInErrs OBJECT-TYPE
              SYNTAX  INTEGER
              ACCESS  read-only
              STATUS  optional
			  DESCRIPTION ""
              ::= { ncdDecnet 20 }

          ncdDecnetOutErrs OBJECT-TYPE
              SYNTAX  INTEGER
              ACCESS  read-only
              STATUS  optional
			  DESCRIPTION ""
              ::= { ncdDecnet 21 }

          ncdDecnetLastZeroTime OBJECT-TYPE
              SYNTAX  INTEGER
              ACCESS  read-only
              STATUS  optional
			  DESCRIPTION ""
              ::= { ncdDecnet 22 }

          ncdDecnetCurrentAddress OBJECT-TYPE
              SYNTAX  PhysAddress
              ACCESS  read-only
              STATUS  optional
			  DESCRIPTION ""
              ::= { ncdDecnet 23 }


          -- the ncdLat Group

          ncdLatConnectTimeout OBJECT-TYPE
              SYNTAX  TimeTicks
              ACCESS  read-write
              STATUS  optional
			  DESCRIPTION ""
              ::= { ncdLat 1 }

          ncdLatCircuitFlushTimeout OBJECT-TYPE
              SYNTAX  TimeTicks
              ACCESS  read-write
              STATUS  optional
			  DESCRIPTION ""
              ::= { ncdLat 2 }

          ncdLatRetransTimeout OBJECT-TYPE
              SYNTAX  TimeTicks
              ACCESS  read-write
              STATUS  optional
			  DESCRIPTION ""
              ::= { ncdLat 3 }

          ncdLatRetransLimit OBJECT-TYPE
              SYNTAX  INTEGER
              ACCESS  read-write
              STATUS  optional
			  DESCRIPTION ""
              ::= { ncdLat 4 }

          ncdLatKeepaliveTimeout OBJECT-TYPE
              SYNTAX  TimeTicks
              ACCESS  read-write
              STATUS  optional
			  DESCRIPTION ""
              ::= { ncdLat 5 }

          ncdLatGroupCodes OBJECT-TYPE
              SYNTAX  OCTET STRING
              ACCESS  read-write
              STATUS  optional
			  DESCRIPTION ""
              ::= { ncdLat 6 }

          ncdLatMaxDirEntries OBJECT-TYPE
              SYNTAX  INTEGER
              ACCESS  read-write
              STATUS  optional
			  DESCRIPTION ""
              ::= { ncdLat 7 }


          -- the ncdNameResolver Group

          ncdNameResolverTransactTimeout OBJECT-TYPE
              SYNTAX  TimeTicks
              ACCESS  read-write
              STATUS  optional
			  DESCRIPTION ""
              ::= { ncdNameResolver 1 }

          ncdNameResolverNumericalAddrs OBJECT-TYPE
              SYNTAX  INTEGER
              ACCESS  read-only
              STATUS  optional
			  DESCRIPTION ""
              ::= { ncdNameResolver 2 }

          ncdNameResolverCacheHits OBJECT-TYPE
              SYNTAX  INTEGER
              ACCESS  read-only
              STATUS  optional
			  DESCRIPTION ""
              ::= { ncdNameResolver 3 }

          ncdNameResolverServerHits OBJECT-TYPE
              SYNTAX  INTEGER
              ACCESS  read-only
              STATUS  optional
			  DESCRIPTION ""
              ::= { ncdNameResolver 4 }

          ncdNameResolverCacheOverflows OBJECT-TYPE
              SYNTAX  INTEGER
              ACCESS  read-only
              STATUS  optional
			  DESCRIPTION ""
              ::= { ncdNameResolver 5 }

          ncdNameResolverNoNameErrs OBJECT-TYPE
              SYNTAX  INTEGER
              ACCESS  read-only
              STATUS  optional
			  DESCRIPTION ""
              ::= { ncdNameResolver 6 }

          ncdNameResolverBadNameErrs OBJECT-TYPE
              SYNTAX  INTEGER
              ACCESS  read-only
              STATUS  optional
			  DESCRIPTION ""
              ::= { ncdNameResolver 7 }

          ncdNameResolverRspErrs OBJECT-TYPE
              SYNTAX  INTEGER
              ACCESS  read-only
              STATUS  optional
			  DESCRIPTION ""
              ::= { ncdNameResolver 8 }

          ncdNameResolverNoRspErrs OBJECT-TYPE
              SYNTAX  INTEGER
              ACCESS  read-only
              STATUS  optional
			  DESCRIPTION ""
              ::= { ncdNameResolver 9 }

          ncdNameResolverSysErrs OBJECT-TYPE
              SYNTAX  INTEGER
              ACCESS  read-only
              STATUS  optional
			  DESCRIPTION ""
              ::= { ncdNameResolver 10 }

          ncdNameResolverNoMemErrs OBJECT-TYPE
              SYNTAX  INTEGER
              ACCESS  read-only
              STATUS  optional
			  DESCRIPTION ""
              ::= { ncdNameResolver 11 }

          ncdNameResolverNameCacheMaxSize OBJECT-TYPE
              SYNTAX  INTEGER
              ACCESS  read-write
              STATUS  optional
			  DESCRIPTION ""
              ::= { ncdNameResolver 12 }

          ncdNameResolverNameCacheMaxTimeout OBJECT-TYPE
              SYNTAX  INTEGER
              ACCESS  read-write
              STATUS  optional
			  DESCRIPTION ""
              ::= { ncdNameResolver 13 }

          ncdNameResolverNameCacheTable OBJECT-TYPE
              SYNTAX  SEQUENCE OF NcdNameResolverNameCacheEntry
              ACCESS  not-accessible
              STATUS  optional
			  DESCRIPTION ""
              ::= { ncdNameResolver 14 }

          ncdNameResolverNameCacheEntry OBJECT-TYPE
              SYNTAX  NcdNameResolverNameCacheEntry
              ACCESS  not-accessible
              STATUS  optional
			  DESCRIPTION ""
              ::= { ncdNameResolverNameCacheTable 1 }

          NcdNameResolverNameCacheEntry ::=
              SEQUENCE {
                  ncdNameResolverTableIndex
                      INTEGER,
                  ncdNameResolverTableName
                      OCTET STRING,
                  ncdNameResolverTableAddress
                      OCTET STRING,
                  ncdNameResolverTableExpTime
                      INTEGER
              }

          ncdNameResolverTableIndex OBJECT-TYPE
              SYNTAX  INTEGER
              ACCESS  read-only
              STATUS  optional
			  DESCRIPTION ""
              ::= { ncdNameResolverNameCacheEntry 1 }

          ncdNameResolverTableName OBJECT-TYPE
              SYNTAX  OCTET STRING
              ACCESS  read-write
              STATUS  optional
			  DESCRIPTION ""
              ::= { ncdNameResolverNameCacheEntry 2 }

          ncdNameResolverTableAddress OBJECT-TYPE
              SYNTAX  OCTET STRING
              ACCESS  read-write
              STATUS  optional
			  DESCRIPTION ""
              ::= { ncdNameResolverNameCacheEntry 3 }

          ncdNameResolverTableExpTime OBJECT-TYPE
              SYNTAX  INTEGER
              ACCESS  read-write
              STATUS  optional
			  DESCRIPTION ""
              ::= { ncdNameResolverNameCacheEntry 4 }

          ncdNameResolverProtocol OBJECT-TYPE
              SYNTAX  INTEGER
              ACCESS  read-write
              STATUS  optional
			  DESCRIPTION ""
              ::= { ncdNameResolver 15 }

          ncdNameResolverRtxTimeout OBJECT-TYPE
              SYNTAX  INTEGER
              ACCESS  read-write
              STATUS  optional
			  DESCRIPTION ""
              ::= { ncdNameResolver 16 }

          ncdNameResolverRequests OBJECT-TYPE
              SYNTAX  INTEGER
              ACCESS  read-only
              STATUS  optional
			  DESCRIPTION ""
              ::= { ncdNameResolver 17 }

          ncdNameResolverNameServersTable OBJECT-TYPE
              SYNTAX  SEQUENCE OF NcdNameResolverNameServersEntry
              ACCESS  not-accessible
              STATUS  optional
			  DESCRIPTION ""
              ::= { ncdNameResolver 18 }

          ncdNameResolverNameServersEntry OBJECT-TYPE
              SYNTAX  NcdNameResolverNameServersEntry
              ACCESS  not-accessible
              STATUS  optional
			  DESCRIPTION ""
              ::= { ncdNameResolverNameServersTable 1 }

          NcdNameResolverNameServersEntry ::=
              SEQUENCE {
                  ncdInetNameServersTableIndex
                      INTEGER,
                  ncdInetNameServersTableAddress
                      IpAddress
              }

          ncdInetNameServersTableIndex OBJECT-TYPE
              SYNTAX  INTEGER
              ACCESS  read-only
              STATUS  optional
			  DESCRIPTION ""
              ::= { ncdNameResolverNameServersEntry 1 }

          ncdInetNameServersTableAddress OBJECT-TYPE
              SYNTAX  IpAddress
              ACCESS  read-write
              STATUS  optional
			  DESCRIPTION ""
              ::= { ncdNameResolverNameServersEntry 2 }

          ncdNameResolverDnsDefaultDomain OBJECT-TYPE
              SYNTAX  OCTET STRING
              ACCESS  read-write
              STATUS  optional
			  DESCRIPTION ""
              ::= { ncdNameResolver 19 }

          ncdNameResolverDnsDoNameSearch OBJECT-TYPE
              SYNTAX  INTEGER
              ACCESS  read-write
              STATUS  optional
			  DESCRIPTION ""
              ::= { ncdNameResolver 20 }


          -- the ncdFontService Group

          ncdFontServiceCacheSize OBJECT-TYPE
              SYNTAX  INTEGER
              ACCESS  read-only
              STATUS  optional
			  DESCRIPTION ""
              ::= { ncdFontService 2 }

          ncdFontServiceCacheUsed OBJECT-TYPE
              SYNTAX  Gauge
              ACCESS  read-only
              STATUS  optional
			  DESCRIPTION ""
              ::= { ncdFontService 3 }

          ncdFontServiceNumCachedFonts OBJECT-TYPE
              SYNTAX  Gauge
              ACCESS  read-only
              STATUS  optional
			  DESCRIPTION ""
              ::= { ncdFontService 4 }

          ncdFontServiceNetLoads OBJECT-TYPE
              SYNTAX  Counter
              ACCESS  read-only
              STATUS  optional
			  DESCRIPTION ""
              ::= { ncdFontService 5 }

          ncdFontServiceReferenceIncs OBJECT-TYPE
              SYNTAX  Counter
              ACCESS  read-only
              STATUS  optional
			  DESCRIPTION ""
              ::= { ncdFontService 6 }

          ncdFontServiceCacheHits OBJECT-TYPE
              SYNTAX  Counter
              ACCESS  read-only
              STATUS  optional
			  DESCRIPTION ""
              ::= { ncdFontService 7 }

          ncdFontServiceFontsInUse OBJECT-TYPE
              SYNTAX  INTEGER
              ACCESS  read-only
              STATUS  optional
			  DESCRIPTION ""
              ::= { ncdFontService 9 }


          -- the ncdArp Group

          ncdArpIncompleteEntryTimeout OBJECT-TYPE
              SYNTAX  TimeTicks
              ACCESS  read-write
              STATUS  optional
			  DESCRIPTION ""
              ::= { ncdArp 1 }

          ncdArpCompleteEntryTimeout OBJECT-TYPE
              SYNTAX  TimeTicks
              ACCESS  read-write
              STATUS  optional
			  DESCRIPTION ""
              ::= { ncdArp 2 }


          -- the ncdIp Group

          ncdIpNewAddress OBJECT-TYPE
              SYNTAX  IpAddress
              ACCESS  read-write
              STATUS  optional
			  DESCRIPTION ""
              ::= { ncdIp 1 }

          ncdIpInitDfltGatewy1 OBJECT-TYPE
              SYNTAX  IpAddress
              ACCESS  read-write
              STATUS  optional
			  DESCRIPTION ""
              ::= { ncdIp 2 }

          ncdIpInitDfltGatewy2 OBJECT-TYPE
              SYNTAX  IpAddress
              ACCESS  read-write
              STATUS  optional
			  DESCRIPTION ""
              ::= { ncdIp 3 }

          ncdIpDynamicAddressDiscovery OBJECT-TYPE
              SYNTAX  INTEGER
              ACCESS  read-write
              STATUS  optional
			  DESCRIPTION ""
              ::= { ncdIp 4 }

          ncdIpUseProxyArp OBJECT-TYPE
              SYNTAX  INTEGER
              ACCESS  read-write
              STATUS  optional
			  DESCRIPTION ""
              ::= { ncdIp 5 }

          ncdIpUseRouterDiscovery OBJECT-TYPE
              SYNTAX  INTEGER
              ACCESS  read-write
              STATUS  optional
			  DESCRIPTION ""
              ::= { ncdIp 6 }

          ncdIpUseRouterDiscoverySolicit OBJECT-TYPE
              SYNTAX  INTEGER
              ACCESS  read-write
              STATUS  optional
			  DESCRIPTION ""
              ::= { ncdIp 7 }

          ncdIpRouteExtendedDiagnostics OBJECT-TYPE
              SYNTAX  INTEGER
              ACCESS  read-write
              STATUS  optional
			  DESCRIPTION ""
              ::= { ncdIp 8 }

          ncdIpRspToBcastIcmp OBJECT-TYPE
              SYNTAX  INTEGER
              ACCESS  read-write
              STATUS  optional
			  DESCRIPTION ""
              ::= { ncdIp 9 }

          ncdIpEquivAddressesTable OBJECT-TYPE
              SYNTAX  SEQUENCE OF NcdIpEquivAddressesEntry
              ACCESS  not-accessible
              STATUS  optional
			  DESCRIPTION ""
              ::= { ncdIp 11 }

          ncdIpEquivAddressesEntry OBJECT-TYPE
              SYNTAX  NcdIpEquivAddressesEntry
              ACCESS  not-accessible
              STATUS  optional
			  DESCRIPTION ""
              ::= { ncdIpEquivAddressesTable 1 }

          NcdIpEquivAddressesEntry ::=
              SEQUENCE {
                  ncdIpEATIndex
                      INTEGER,
                  ncdIpEATAddresses
                      IpAddress
              }

          ncdIpEATIndex OBJECT-TYPE
              SYNTAX  INTEGER
              ACCESS  read-only
              STATUS  optional
			  DESCRIPTION ""
              ::= { ncdIpEquivAddressesEntry 1 }

          ncdIpEATAddresses OBJECT-TYPE
              SYNTAX  IpAddress
              ACCESS  read-write
              STATUS  optional
			  DESCRIPTION ""
              ::= { ncdIpEquivAddressesEntry 2 }


          -- the ncdSerialDaemon Group

          ncdSerialDaemonStatsTable OBJECT-TYPE
              SYNTAX  SEQUENCE OF NcdSerialDaemonStatsEntry
              ACCESS  not-accessible
              STATUS  optional
			  DESCRIPTION ""
              ::= { ncdSerialDaemon 1 }

          ncdSerialDaemonStatsEntry OBJECT-TYPE
              SYNTAX  NcdSerialDaemonStatsEntry
              ACCESS  not-accessible
              STATUS  optional
			  DESCRIPTION ""
              ::= { ncdSerialDaemonStatsTable 1 }

          NcdSerialDaemonStatsEntry ::=
              SEQUENCE {
                  ncdSerialDaemonPortNumber
                      INTEGER,
                  ncdSerialDaemonConnAccepts
                      INTEGER,
                  ncdSerialDaemonConnBadAccesses
                      INTEGER,
                  ncdSerialDaemonConnIOErrors
                      INTEGER,
                  ncdSerialDaemonConnEofCloses
                      INTEGER
              }

          ncdSerialDaemonPortNumber OBJECT-TYPE
              SYNTAX  INTEGER
              ACCESS  read-only
              STATUS  optional
			  DESCRIPTION ""
              ::= { ncdSerialDaemonStatsEntry 1 }

          ncdSerialDaemonConnAccepts OBJECT-TYPE
              SYNTAX  INTEGER
              ACCESS  read-only
              STATUS  optional
			  DESCRIPTION ""
              ::= { ncdSerialDaemonStatsEntry 2 }

          ncdSerialDaemonConnBadAccesses OBJECT-TYPE
              SYNTAX  INTEGER
              ACCESS  read-only
              STATUS  optional
			  DESCRIPTION ""
              ::= { ncdSerialDaemonStatsEntry 3 }

          ncdSerialDaemonConnIOErrors OBJECT-TYPE
              SYNTAX  INTEGER
              ACCESS  read-only
              STATUS  optional
			  DESCRIPTION ""
              ::= { ncdSerialDaemonStatsEntry 4 }

          ncdSerialDaemonConnEofCloses OBJECT-TYPE
              SYNTAX  INTEGER
              ACCESS  read-only
              STATUS  optional
			  DESCRIPTION ""
              ::= { ncdSerialDaemonStatsEntry 5 }


          -- the ncdDnetNameResolver Group

          ncdDnetNameResolverRequests OBJECT-TYPE
              SYNTAX  INTEGER
              ACCESS  read-only
              STATUS  optional
			  DESCRIPTION ""
              ::= { ncdDnetNameResolver 1 }

          ncdDnetNameResolverNumericalAddrs OBJECT-TYPE
              SYNTAX  INTEGER
              ACCESS  read-only
              STATUS  optional
			  DESCRIPTION ""
              ::= { ncdDnetNameResolver 2 }

          ncdDnetNameResolverCacheHits OBJECT-TYPE
              SYNTAX  INTEGER
              ACCESS  read-only
              STATUS  optional
			  DESCRIPTION ""
              ::= { ncdDnetNameResolver 3 }

          ncdDnetNameResolverServerHits OBJECT-TYPE
              SYNTAX  INTEGER
              ACCESS  read-only
              STATUS  optional
			  DESCRIPTION ""
              ::= { ncdDnetNameResolver 4 }

          ncdDnetNameResolverCacheOverflows OBJECT-TYPE
              SYNTAX  INTEGER
              ACCESS  read-only
              STATUS  optional
			  DESCRIPTION ""
              ::= { ncdDnetNameResolver 5 }

          ncdDnetNameResolverNoNameErrs OBJECT-TYPE
              SYNTAX  INTEGER
              ACCESS  read-only
              STATUS  optional
			  DESCRIPTION ""
              ::= { ncdDnetNameResolver 6 }

          ncdDnetNameResolverBadNameErrs OBJECT-TYPE
              SYNTAX  INTEGER
              ACCESS  read-only
              STATUS  optional
			  DESCRIPTION ""
              ::= { ncdDnetNameResolver 7 }

          ncdDnetNameResolverRspErrs OBJECT-TYPE
              SYNTAX  INTEGER
              ACCESS  read-only
              STATUS  optional
			  DESCRIPTION ""
              ::= { ncdDnetNameResolver 8 }

          ncdDnetNameResolverNoRspErrs OBJECT-TYPE
              SYNTAX  INTEGER
              ACCESS  read-only
              STATUS  optional
			  DESCRIPTION ""
              ::= { ncdDnetNameResolver 9 }

          ncdDnetNameResolverSysErrs OBJECT-TYPE
              SYNTAX  INTEGER
              ACCESS  read-only
              STATUS  optional
			  DESCRIPTION ""
              ::= { ncdDnetNameResolver 10 }

          ncdDnetNameResolverNoMemErrs OBJECT-TYPE
              SYNTAX  INTEGER
              ACCESS  read-only
              STATUS  optional
			  DESCRIPTION ""
              ::= { ncdDnetNameResolver 11 }

          ncdDnetNameResolverNameCacheMaxSize OBJECT-TYPE
              SYNTAX  INTEGER
              ACCESS  read-write
              STATUS  optional
			  DESCRIPTION ""
              ::= { ncdDnetNameResolver 12 }

          ncdDnetNameResolverNameCacheMaxTimeout OBJECT-TYPE
              SYNTAX  INTEGER
              ACCESS  read-write
              STATUS  optional
			  DESCRIPTION ""
              ::= { ncdDnetNameResolver 13 }

          ncdDnetNameResolverNameCacheTable OBJECT-TYPE
              SYNTAX  SEQUENCE OF NcdDnetNameResolverNameCacheEntry
              ACCESS  not-accessible
              STATUS  optional
			  DESCRIPTION ""
              ::= { ncdDnetNameResolver 14 }

          ncdDnetNameResolverNameCacheEntry OBJECT-TYPE
              SYNTAX  NcdDnetNameResolverNameCacheEntry
              ACCESS  not-accessible
              STATUS  optional
			  DESCRIPTION ""
              ::= { ncdDnetNameResolverNameCacheTable 1 }

          NcdDnetNameResolverNameCacheEntry ::=
              SEQUENCE {
                  ncdDnetNameResolverIndex
                      INTEGER,
                  ncdDnetNameResolverName
                      OCTET STRING,
                  ncdDnetNameResolverAddress
                      OCTET STRING,
                  ncdDnetNameResolverExpTime
                      INTEGER
              }

          ncdDnetNameResolverIndex OBJECT-TYPE
              SYNTAX  INTEGER
              ACCESS  read-only
              STATUS  optional
			  DESCRIPTION ""
              ::= { ncdDnetNameResolverNameCacheEntry 1 }

          ncdDnetNameResolverName OBJECT-TYPE
              SYNTAX  OCTET STRING
              ACCESS  read-write
              STATUS  optional
			  DESCRIPTION ""
              ::= { ncdDnetNameResolverNameCacheEntry 2 }

          ncdDnetNameResolverAddress OBJECT-TYPE
              SYNTAX  OCTET STRING
              ACCESS  read-write
              STATUS  optional
			  DESCRIPTION ""
              ::= { ncdDnetNameResolverNameCacheEntry 3 }

          ncdDnetNameResolverExpTime OBJECT-TYPE
              SYNTAX  INTEGER
              ACCESS  read-write
              STATUS  optional
			  DESCRIPTION ""
              ::= { ncdDnetNameResolverNameCacheEntry 4 }

          ncdDnetNameResolverTransactTimeout OBJECT-TYPE
              SYNTAX  INTEGER
              ACCESS  read-write
              STATUS  optional
			  DESCRIPTION ""
              ::= { ncdDnetNameResolver 15 }

          ncdDnetNameResolverServersTable OBJECT-TYPE
              SYNTAX  SEQUENCE OF NcdDnetNameResolverServersEntry
              ACCESS  not-accessible
              STATUS  optional
			  DESCRIPTION ""
              ::= { ncdDnetNameResolver 16 }

          ncdDnetNameResolverServersEntry OBJECT-TYPE
              SYNTAX  NcdDnetNameResolverServersEntry
              ACCESS  not-accessible
              STATUS  optional
			  DESCRIPTION ""
              ::= { ncdDnetNameResolverServersTable 1 }

          NcdDnetNameResolverServersEntry ::=
              SEQUENCE {
                  ncdDnetNameResolverServerIndex
                      INTEGER,
                  ncdDnetNameResolverServer
                      PhysAddress
              }

          ncdDnetNameResolverServerIndex OBJECT-TYPE
              SYNTAX  INTEGER
              ACCESS  read-only
              STATUS  optional
			  DESCRIPTION ""
              ::= { ncdDnetNameResolverServersEntry 1 }

          ncdDnetNameResolverServer OBJECT-TYPE
              SYNTAX  PhysAddress
              ACCESS  read-write
              STATUS  optional
			  DESCRIPTION ""
              ::= { ncdDnetNameResolverServersEntry 2 }


          -- the ncdBoot Group

          ncdBootServerAutomatically OBJECT-TYPE
              SYNTAX  INTEGER
              ACCESS  read-write
              STATUS  optional
			  DESCRIPTION ""
              ::= { ncdBoot 1 }

          ncdBootRamTest OBJECT-TYPE
              SYNTAX  INTEGER
              ACCESS  read-write
              STATUS  optional
			  DESCRIPTION ""
              ::= { ncdBoot 2 }

          ncdBootActualSource OBJECT-TYPE
              SYNTAX  INTEGER
              ACCESS  read-only
              STATUS  optional
			  DESCRIPTION ""
              ::= { ncdBoot 3 }

          ncdBootActualServer OBJECT-TYPE
              SYNTAX  IpAddress
              ACCESS  read-only
              STATUS  optional
			  DESCRIPTION ""
              ::= { ncdBoot 4 }

          ncdBootDesiredSource OBJECT-TYPE
              SYNTAX  INTEGER
              ACCESS  read-write
              STATUS  optional
			  DESCRIPTION ""
              ::= { ncdBoot 5 }

          ncdBootPersist OBJECT-TYPE
              SYNTAX  INTEGER
              ACCESS  read-write
              STATUS  optional
			  DESCRIPTION ""
              ::= { ncdBoot 6 }

          ncdBootDefaultServer OBJECT-TYPE
              SYNTAX  IpAddress
              ACCESS  read-write
              STATUS  optional
			  DESCRIPTION ""
              ::= { ncdBoot 7 }

          ncdBootMonitorReverseVideo OBJECT-TYPE
              SYNTAX  INTEGER
              ACCESS  read-write
              STATUS  optional
			  DESCRIPTION ""
              ::= { ncdBoot 8 }

          ncdBootDesiredInetServer OBJECT-TYPE
              SYNTAX  IpAddress
              ACCESS  read-write
              STATUS  optional
			  DESCRIPTION ""
              ::= { ncdBoot 9 }

          ncdBootUseRelativeHexFile OBJECT-TYPE
              SYNTAX  INTEGER
              ACCESS  read-write
              STATUS  optional
			  DESCRIPTION ""
              ::= { ncdBoot 10 }

          ncdBootUseAbsoluteHexFile OBJECT-TYPE
              SYNTAX  INTEGER
              ACCESS  read-write
              STATUS  optional
			  DESCRIPTION ""
              ::= { ncdBoot 11 }

          ncdBootUseRelativeMemSizeFile OBJECT-TYPE
              SYNTAX  INTEGER
              ACCESS  read-write
              STATUS  optional
			  DESCRIPTION ""
              ::= { ncdBoot 12 }

          ncdBootUseAbsoluteMemSizeFile OBJECT-TYPE
              SYNTAX  INTEGER
              ACCESS  read-write
              STATUS  optional
			  DESCRIPTION ""
              ::= { ncdBoot 13 }

          ncdBootUseRelativeProductFile OBJECT-TYPE
              SYNTAX  INTEGER
              ACCESS  read-write
              STATUS  optional
			  DESCRIPTION ""
              ::= { ncdBoot 14 }

          ncdBootUseAbsoluteProductFile OBJECT-TYPE
              SYNTAX  INTEGER
              ACCESS  read-write
              STATUS  optional
			  DESCRIPTION ""
              ::= { ncdBoot 15 }

          ncdBootEnableICMPSubnetMaskRequest OBJECT-TYPE
              SYNTAX  INTEGER
              ACCESS  read-write
              STATUS  optional
			  DESCRIPTION ""
              ::= { ncdBoot 16 }

          ncdBootBroadcastInetRequest OBJECT-TYPE
              SYNTAX  INTEGER
              ACCESS  read-write
              STATUS  optional
			  DESCRIPTION ""
              ::= { ncdBoot 17 }

          ncdBootMop OBJECT-TYPE
              SYNTAX  INTEGER
              ACCESS  read-write
              STATUS  optional
			  DESCRIPTION ""
              ::= { ncdBoot 18 }

          ncdBootMopWithFileName OBJECT-TYPE
              SYNTAX  INTEGER
              ACCESS  read-write
              STATUS  optional
			  DESCRIPTION ""
              ::= { ncdBoot 19 }

          ncdBootCustomFile OBJECT-TYPE
              SYNTAX  OCTET STRING
              ACCESS  read-write
              STATUS  optional
			  DESCRIPTION ""
              ::= { ncdBoot 20 }

          ncdBootTftpDirectory OBJECT-TYPE
              SYNTAX  OCTET STRING
              ACCESS  read-write
              STATUS  optional
			  DESCRIPTION ""
              ::= { ncdBoot 21 }

          ncdBootNfsDirectory OBJECT-TYPE
              SYNTAX  OCTET STRING
              ACCESS  read-write
              STATUS  optional
			  DESCRIPTION ""
              ::= { ncdBoot 22 }


          -- the ncdConfig Group

          ncdConfigInitFileLoad OBJECT-TYPE
              SYNTAX  INTEGER
              ACCESS  read-write
              STATUS  optional
			  DESCRIPTION ""
              ::= { ncdConfig 1 }

          ncdConfigInitPersistentFileLoad OBJECT-TYPE
              SYNTAX  INTEGER
              ACCESS  read-write
              STATUS  optional
			  DESCRIPTION ""
              ::= { ncdConfig 2 }

          ncdConfigDfltUnixDirectory OBJECT-TYPE
              SYNTAX  OCTET STRING
              ACCESS  read-write
              STATUS  optional
			  DESCRIPTION ""
              ::= { ncdConfig 3 }

          ncdConfigDfltVmsDirectory OBJECT-TYPE
              SYNTAX  OCTET STRING
              ACCESS  read-write
              STATUS  optional
			  DESCRIPTION ""
              ::= { ncdConfig 4 }

          ncdConfigInitFile OBJECT-TYPE
              SYNTAX  OCTET STRING
              ACCESS  read-write
              STATUS  optional
			  DESCRIPTION ""
              ::= { ncdConfig 5 }

          ncdConfigInitUseUnitNameFile OBJECT-TYPE
              SYNTAX  INTEGER
              ACCESS  read-write
              STATUS  optional
			  DESCRIPTION ""
              ::= { ncdConfig 6 }

          ncdConfigInitUseFQUnitName OBJECT-TYPE
              SYNTAX  INTEGER
              ACCESS  read-write
              STATUS  optional
			  DESCRIPTION ""
              ::= { ncdConfig 7 }

          ncdConfigInitUseEnetUnitAddrFile OBJECT-TYPE
              SYNTAX  INTEGER
              ACCESS  read-write
              STATUS  optional
			  DESCRIPTION ""
              ::= { ncdConfig 8 }

          ncdConfigInitUseInetUnitAddrFile OBJECT-TYPE
              SYNTAX  INTEGER
              ACCESS  read-write
              STATUS  optional
			  DESCRIPTION ""
              ::= { ncdConfig 9 }

          ncdConfigInitUseDecimalInetUnitAddr OBJECT-TYPE
              SYNTAX  INTEGER
              ACCESS  read-write
              STATUS  optional
			  DESCRIPTION ""
              ::= { ncdConfig 10 }

          ncdConfigInitUseGenericFile OBJECT-TYPE
              SYNTAX  INTEGER
              ACCESS  read-write
              STATUS  optional
			  DESCRIPTION ""
              ::= { ncdConfig 11 }

          ncdConfigTelnetPort OBJECT-TYPE
              SYNTAX  INTEGER
              ACCESS  read-write
              STATUS  optional
			  DESCRIPTION ""
              ::= { ncdConfig 12 }

          ncdConfigTcpPort OBJECT-TYPE
              SYNTAX  INTEGER
              ACCESS  read-write
              STATUS  optional
			  DESCRIPTION ""
              ::= { ncdConfig 13 }

          ncdConfigDfltFile OBJECT-TYPE
              SYNTAX  OCTET STRING
              ACCESS  read-write
              STATUS  optional
			  DESCRIPTION ""
              ::= { ncdConfig 14 }

          ncdConfigAutoSaveNvram OBJECT-TYPE
              SYNTAX  INTEGER
              ACCESS  read-write
              STATUS  optional
			  DESCRIPTION ""
              ::= { ncdConfig 15 }

          ncdConfigAutoSaveFile OBJECT-TYPE
              SYNTAX  INTEGER
              ACCESS  read-write
              STATUS  optional
			  DESCRIPTION ""
              ::= { ncdConfig 16 }

          ncdConfigAutoSaveFileName OBJECT-TYPE
              SYNTAX  OCTET STRING
              ACCESS  read-write
              STATUS  optional
			  DESCRIPTION ""
              ::= { ncdConfig 17 }

          ncdConfigAutoSaveChanges OBJECT-TYPE
              SYNTAX  INTEGER
              ACCESS  read-write
              STATUS  optional
			  DESCRIPTION ""
              ::= { ncdConfig 18 }

          ncdConfigPrefdTelnetPort OBJECT-TYPE
              SYNTAX  INTEGER
              ACCESS  read-write
              STATUS  optional
			  DESCRIPTION ""
              ::= { ncdConfig 19 }

          ncdConfigPrefdTcpPort OBJECT-TYPE
              SYNTAX  INTEGER
              ACCESS  read-write
              STATUS  optional
			  DESCRIPTION ""
              ::= { ncdConfig 20 }

          ncdConfigPrefdDnetObject OBJECT-TYPE
              SYNTAX  OCTET STRING
              ACCESS  read-write
              STATUS  optional
			  DESCRIPTION ""
              ::= { ncdConfig 21 }

          ncdConfigInitUseDnetUnitAddrFile OBJECT-TYPE
              SYNTAX  INTEGER
              ACCESS  read-write
              STATUS  optional
			  DESCRIPTION ""
              ::= { ncdConfig 22 }

          ncdConfigDnetObject OBJECT-TYPE
              SYNTAX  OCTET STRING
              ACCESS  read-write
              STATUS  optional
			  DESCRIPTION ""
              ::= { ncdConfig 23 }


          -- the ncdXserver Group

          ncdXserverCurrentKeyboard OBJECT-TYPE
              SYNTAX  INTEGER
              ACCESS  read-write
              STATUS  optional
			  DESCRIPTION ""
              ::= { ncdXserver 1 }

          ncdXserverKeyboardTypeChoices OBJECT-TYPE
              SYNTAX  SEQUENCE OF NcdXserverKeyboardTypeEntry
              ACCESS  not-accessible
              STATUS  optional
			  DESCRIPTION ""
              ::= { ncdXserver 2 }

          ncdXserverKeyboardTypeEntry OBJECT-TYPE
              SYNTAX  NcdXserverKeyboardTypeEntry
              ACCESS  not-accessible
              STATUS  optional
			  DESCRIPTION ""
              ::= { ncdXserverKeyboardTypeChoices 1 }

          NcdXserverKeyboardTypeEntry ::=
              SEQUENCE {
                  ncdXserverKeyboardChoiceIndex
                      INTEGER,
                  ncdXserverCurrentKeyboardChoice
                      OCTET STRING
              }

          ncdXserverKeyboardChoiceIndex OBJECT-TYPE
              SYNTAX  INTEGER
              ACCESS  read-only
              STATUS  optional
			  DESCRIPTION ""
              ::= { ncdXserverKeyboardTypeEntry 1 }

          ncdXserverCurrentKeyboardChoice OBJECT-TYPE
              SYNTAX  OCTET STRING
              ACCESS  read-only
              STATUS  optional
			  DESCRIPTION ""
              ::= { ncdXserverKeyboardTypeEntry 2 }

          ncdXserverNarrowKeyTable OBJECT-TYPE
              SYNTAX  INTEGER
              ACCESS  read-write
              STATUS  optional
			  DESCRIPTION ""
              ::= { ncdXserver 3 }

          ncdXserverDeadKeySupport OBJECT-TYPE
              SYNTAX  INTEGER
              ACCESS  read-write
              STATUS  optional
			  DESCRIPTION ""
              ::= { ncdXserver 4 }

          ncdXserverMouseButtons OBJECT-TYPE
              SYNTAX  INTEGER
              ACCESS  read-write
              STATUS  optional
			  DESCRIPTION ""
              ::= { ncdXserver 5 }

          ncdXserverDefaultFontPathTable OBJECT-TYPE
              SYNTAX  SEQUENCE OF NcdXserverDefaultFontPathEntry
              ACCESS  not-accessible
              STATUS  optional
			  DESCRIPTION ""
              ::= { ncdXserver 6 }

          ncdXserverDefaultFontPathEntry OBJECT-TYPE
              SYNTAX  NcdXserverDefaultFontPathEntry
              ACCESS  not-accessible
              STATUS  optional
			  DESCRIPTION ""
              ::= { ncdXserverDefaultFontPathTable 1 }

          NcdXserverDefaultFontPathEntry ::=
              SEQUENCE {
                  ncdXserverFontPathTableIndex
                      INTEGER,
                  ncdXserverFontPathTableEntry
                      OCTET STRING
              }

          ncdXserverFontPathTableIndex OBJECT-TYPE
              SYNTAX  INTEGER
              ACCESS  read-only
              STATUS  optional
			  DESCRIPTION ""
              ::= { ncdXserverDefaultFontPathEntry 1 }

          ncdXserverFontPathTableEntry OBJECT-TYPE
              SYNTAX  OCTET STRING
              ACCESS  read-write
              STATUS  optional
			  DESCRIPTION ""
              ::= { ncdXserverDefaultFontPathEntry 2 }

          ncdXserverDefaultFont OBJECT-TYPE
              SYNTAX  OCTET STRING
              ACCESS  read-write
              STATUS  optional
			  DESCRIPTION ""
              ::= { ncdXserver 7 }

          ncdXserverFontCacheSize OBJECT-TYPE
              SYNTAX  INTEGER
              ACCESS  read-write
              STATUS  optional
			  DESCRIPTION ""
              ::= { ncdXserver 8 }

          ncdXserverRetainFonts OBJECT-TYPE
              SYNTAX  INTEGER
              ACCESS  read-write
              STATUS  optional
			  DESCRIPTION ""
              ::= { ncdXserver 9 }

          ncdXserverFontDirFileName OBJECT-TYPE
              SYNTAX  OCTET STRING
              ACCESS  read-write
              STATUS  optional
			  DESCRIPTION ""
              ::= { ncdXserver 10 }

          ncdXserverFontAliasFileName OBJECT-TYPE
              SYNTAX  OCTET STRING
              ACCESS  read-write
              STATUS  optional
			  DESCRIPTION ""
              ::= { ncdXserver 11 }

          ncdXserverFontPathAliasTable OBJECT-TYPE
              SYNTAX  SEQUENCE OF NcdXserverFontPathAliasEntry
              ACCESS  not-accessible
              STATUS  optional
			  DESCRIPTION ""
              ::= { ncdXserver 12 }

          ncdXserverFontPathAliasEntry OBJECT-TYPE
              SYNTAX  NcdXserverFontPathAliasEntry
              ACCESS  not-accessible
              STATUS  optional
			  DESCRIPTION ""
              ::= { ncdXserverFontPathAliasTable 1 }

          NcdXserverFontPathAliasEntry ::=
              SEQUENCE {
                  ncdXserverAliasTableIndex
                      INTEGER,
                  ncdXserverAliasTableAlias
                      OCTET STRING,
                  ncdXserverAliasTableValue
                      OCTET STRING
              }

          ncdXserverAliasTableIndex OBJECT-TYPE
              SYNTAX  INTEGER
              ACCESS  read-only
              STATUS  optional
			  DESCRIPTION ""
              ::= { ncdXserverFontPathAliasEntry 1 }

          ncdXserverAliasTableAlias OBJECT-TYPE
              SYNTAX  OCTET STRING
              ACCESS  read-write
              STATUS  optional
			  DESCRIPTION ""
              ::= { ncdXserverFontPathAliasEntry 2 }

          ncdXserverAliasTableValue OBJECT-TYPE
              SYNTAX  OCTET STRING
              ACCESS  read-write
              STATUS  optional
			  DESCRIPTION ""
              ::= { ncdXserverFontPathAliasEntry 3 }

          ncdXserverFontserverRetryAttempts OBJECT-TYPE
              SYNTAX  INTEGER
              ACCESS  read-write
              STATUS  optional
			  DESCRIPTION ""
              ::= { ncdXserver 13 }

          ncdXserverFontserverReadTimeout OBJECT-TYPE
              SYNTAX  INTEGER
              ACCESS  read-write
              STATUS  optional
			  DESCRIPTION ""
              ::= { ncdXserver 14 }

          ncdXserverFontserverOpenTimeout OBJECT-TYPE
              SYNTAX  INTEGER
              ACCESS  read-write
              STATUS  optional
			  DESCRIPTION ""
              ::= { ncdXserver 15 }

          ncdXserverFontserverReopenTimeout OBJECT-TYPE
              SYNTAX  INTEGER
              ACCESS  read-write
              STATUS  optional
			  DESCRIPTION ""
              ::= { ncdXserver 16 }

          ncdXserverXDisabledExt OBJECT-TYPE
              SYNTAX  SEQUENCE OF NcdXserverXDisabledEntry
              ACCESS  not-accessible
              STATUS  optional
			  DESCRIPTION ""
              ::= { ncdXserver 17 }

          ncdXserverXDisabledEntry OBJECT-TYPE
              SYNTAX  NcdXserverXDisabledEntry
              ACCESS  not-accessible
              STATUS  optional
			  DESCRIPTION ""
              ::= { ncdXserverXDisabledExt 1 }

          NcdXserverXDisabledEntry ::=
              SEQUENCE {
                  ncdXserverDisExtTableIndex
                      INTEGER,
                  ncdXserverDisExtTableName
                      OCTET STRING
              }

          ncdXserverDisExtTableIndex OBJECT-TYPE
              SYNTAX  INTEGER
              ACCESS  read-only
              STATUS  optional
			  DESCRIPTION ""
              ::= { ncdXserverXDisabledEntry 1 }

          ncdXserverDisExtTableName OBJECT-TYPE
              SYNTAX  OCTET STRING
              ACCESS  read-write
              STATUS  optional
			  DESCRIPTION ""
              ::= { ncdXserverXDisabledEntry 2 }

          ncdXserverXServerRetainSettings OBJECT-TYPE
              SYNTAX  INTEGER
              ACCESS  read-write
              STATUS  optional
			  DESCRIPTION ""
              ::= { ncdXserver 18 }

          ncdXserverInitialXResources OBJECT-TYPE
              SYNTAX  OCTET STRING
              ACCESS  read-write
              STATUS  optional
			  DESCRIPTION ""
              ::= { ncdXserver 19 }

          ncdXserverArcCacheSize OBJECT-TYPE
              SYNTAX  INTEGER
              ACCESS  read-write
              STATUS  optional
			  DESCRIPTION ""
              ::= { ncdXserver 20 }

          ncdXserverRgbPath OBJECT-TYPE
              SYNTAX  OCTET STRING
              ACCESS  read-write
              STATUS  optional
			  DESCRIPTION ""
              ::= { ncdXserver 21 }

          ncdXserverXDefaultVisual OBJECT-TYPE
              SYNTAX  INTEGER
              ACCESS  read-write
              STATUS  optional
			  DESCRIPTION ""
              ::= { ncdXserver 22 }

          ncdXserverColormapTable OBJECT-TYPE
              SYNTAX  SEQUENCE OF NcdXserverColormapEntry
              ACCESS  not-accessible
              STATUS  optional
			  DESCRIPTION ""
              ::= { ncdXserver 23 }

          ncdXserverColormapEntry OBJECT-TYPE
              SYNTAX  NcdXserverColormapEntry
              ACCESS  not-accessible
              STATUS  optional
			  DESCRIPTION ""
              ::= { ncdXserverColormapTable 1 }

          NcdXserverColormapEntry ::=
              SEQUENCE {
                  ncdXserverCTIndex
                      INTEGER,
                  ncdXserverCTPixel
                      INTEGER,
                  ncdXserverCTRgb
                      OCTET STRING,
                  ncdXserverCTReadOnly
                      INTEGER
              }

          ncdXserverCTIndex OBJECT-TYPE
              SYNTAX  INTEGER
              ACCESS  read-only
              STATUS  optional
			  DESCRIPTION ""
              ::= { ncdXserverColormapEntry 1 }

          ncdXserverCTPixel OBJECT-TYPE
              SYNTAX  INTEGER
              ACCESS  read-write
              STATUS  optional
			  DESCRIPTION ""
              ::= { ncdXserverColormapEntry 2 }

          ncdXserverCTRgb OBJECT-TYPE
              SYNTAX  OCTET STRING
              ACCESS  read-write
              STATUS  optional
			  DESCRIPTION ""
              ::= { ncdXserverColormapEntry 3 }

          ncdXserverCTReadOnly OBJECT-TYPE
              SYNTAX  INTEGER
              ACCESS  read-write
              STATUS  optional
			  DESCRIPTION ""
              ::= { ncdXserverColormapEntry 4 }

          ncdXserverXBlackPixel OBJECT-TYPE
              SYNTAX  INTEGER
              ACCESS  read-write
              STATUS  optional
			  DESCRIPTION ""
              ::= { ncdXserver 24 }

          ncdXserverXWhitePixel OBJECT-TYPE
              SYNTAX  INTEGER
              ACCESS  read-write
              STATUS  optional
			  DESCRIPTION ""
              ::= { ncdXserver 25 }

          ncdXserverInputExtensionDevice OBJECT-TYPE
              SYNTAX  INTEGER
              ACCESS  read-write
              STATUS  optional
			  DESCRIPTION ""
              ::= { ncdXserver 26 }

          ncdXserverKeysymDBPath OBJECT-TYPE
              SYNTAX  OCTET STRING
              ACCESS  read-write
              STATUS  optional
			  DESCRIPTION ""
              ::= { ncdXserver 27 }

          ncdXServerTouchscreenCalibrationLimitsTable OBJECT-TYPE
              SYNTAX  SEQUENCE OF NcdXServerTouchscreenCalibrationLimitsEntry
              ACCESS  not-accessible
              STATUS  optional
			  DESCRIPTION ""
              ::= { ncdXserver 28 }

          ncdXServerTouchscreenCalibrationLimitsEntry OBJECT-TYPE
              SYNTAX  NcdXServerTouchscreenCalibrationLimitsEntry
              ACCESS  not-accessible
              STATUS  optional
			  DESCRIPTION ""
              ::= { ncdXServerTouchscreenCalibrationLimitsTable 1 }

          NcdXServerTouchscreenCalibrationLimitsEntry ::=
              SEQUENCE {
                  ncdXserverTouchscreenCalibrationLimitsIndex
                      INTEGER,
                  ncdXserverTouchscreenCalibrationLimitsXMin
                      INTEGER,
                  ncdXserverTouchscreenCalibrationLimitsYMin
                      INTEGER,
                  ncdXserverTouchscreenCalibrationLimitsXMax
                      INTEGER,
                  ncdXserverTouchscreenCalibrationLimitsYMax
                      INTEGER
              }

          ncdXserverTouchscreenCalibrationLimitsIndex OBJECT-TYPE
              SYNTAX  INTEGER
              ACCESS  read-only
              STATUS  optional
			  DESCRIPTION ""
              ::= { ncdXServerTouchscreenCalibrationLimitsEntry 1 }

          ncdXserverTouchscreenCalibrationLimitsXMin OBJECT-TYPE
              SYNTAX  INTEGER
              ACCESS  read-write
              STATUS  optional
			  DESCRIPTION ""
              ::= { ncdXServerTouchscreenCalibrationLimitsEntry 2 }

          ncdXserverTouchscreenCalibrationLimitsYMin OBJECT-TYPE
              SYNTAX  INTEGER
              ACCESS  read-write
              STATUS  optional
			  DESCRIPTION ""
              ::= { ncdXServerTouchscreenCalibrationLimitsEntry 3 }

          ncdXserverTouchscreenCalibrationLimitsXMax OBJECT-TYPE
              SYNTAX  INTEGER
              ACCESS  read-write
              STATUS  optional
			  DESCRIPTION ""
              ::= { ncdXServerTouchscreenCalibrationLimitsEntry 4 }

          ncdXserverTouchscreenCalibrationLimitsYMax OBJECT-TYPE
              SYNTAX  INTEGER
              ACCESS  read-write
              STATUS  optional
			  DESCRIPTION ""
              ::= { ncdXServerTouchscreenCalibrationLimitsEntry 5 }


          -- the ncdDiag Group

          ncdDiagTimestampEnabled OBJECT-TYPE
              SYNTAX  INTEGER
              ACCESS  read-write
              STATUS  optional
			  DESCRIPTION ""
              ::= { ncdDiag 1 }

          ncdDiagTimestampGranularity OBJECT-TYPE
              SYNTAX  INTEGER
              ACCESS  read-write
              STATUS  optional
			  DESCRIPTION ""
              ::= { ncdDiag 2 }

          ncdDiagConfiguredBufferSize OBJECT-TYPE
              SYNTAX  INTEGER
              ACCESS  read-write
              STATUS  optional
			  DESCRIPTION ""
              ::= { ncdDiag 3 }

          ncdDiagLogFile OBJECT-TYPE
              SYNTAX  OCTET STRING
              ACCESS  read-write
              STATUS  optional
			  DESCRIPTION ""
              ::= { ncdDiag 4 }

          ncdDiagTelnetPort OBJECT-TYPE
              SYNTAX  INTEGER
              ACCESS  read-write
              STATUS  optional
			  DESCRIPTION ""
              ::= { ncdDiag 5 }

          ncdDiagTcpPort OBJECT-TYPE
              SYNTAX  INTEGER
              ACCESS  read-write
              STATUS  optional
			  DESCRIPTION ""
              ::= { ncdDiag 6 }

          ncdDiagDnetObject OBJECT-TYPE
              SYNTAX  OCTET STRING
              ACCESS  read-write
              STATUS  optional
			  DESCRIPTION ""
              ::= { ncdDiag 7 }

          ncdSevereSystemErrors OBJECT-TYPE
              SYNTAX  INTEGER
              ACCESS  read-write
              STATUS  optional
			  DESCRIPTION ""
              ::= { ncdDiag 8 }


          -- the ncdDps Group

          ncdDpsResourcePath OBJECT-TYPE
              SYNTAX  OCTET STRING
              ACCESS  read-write
              STATUS  optional
			  DESCRIPTION ""
              ::= { ncdDps 1 }


          -- the ncdExec Group

          ncdExecStartupCommandsTable OBJECT-TYPE
              SYNTAX  SEQUENCE OF NcdExecStartupCommandsEntry
              ACCESS  not-accessible
              STATUS  optional
			  DESCRIPTION ""
              ::= { ncdExec 1 }

          ncdExecStartupCommandsEntry OBJECT-TYPE
              SYNTAX  NcdExecStartupCommandsEntry
              ACCESS  not-accessible
              STATUS  optional
			  DESCRIPTION ""
              ::= { ncdExecStartupCommandsTable 1 }

          NcdExecStartupCommandsEntry ::=
              SEQUENCE {
                  ncdExecSTCIndex
                      INTEGER,
                  ncdExecSTCCommands
                      OCTET STRING
              }

          ncdExecSTCIndex OBJECT-TYPE
              SYNTAX  INTEGER
              ACCESS  read-only
              STATUS  optional
			  DESCRIPTION ""
              ::= { ncdExecStartupCommandsEntry 1 }

          ncdExecSTCCommands OBJECT-TYPE
              SYNTAX  OCTET STRING
              ACCESS  read-write
              STATUS  optional
			  DESCRIPTION ""
              ::= { ncdExecStartupCommandsEntry 2 }

          ncdExecDisabledCommandsTable OBJECT-TYPE
              SYNTAX  SEQUENCE OF NcdExecDisabledCommandsEntry
              ACCESS  not-accessible
              STATUS  optional
			  DESCRIPTION ""
              ::= { ncdExec 2 }

          ncdExecDisabledCommandsEntry OBJECT-TYPE
              SYNTAX  NcdExecDisabledCommandsEntry
              ACCESS  not-accessible
              STATUS  optional
			  DESCRIPTION ""
              ::= { ncdExecDisabledCommandsTable 1 }

          NcdExecDisabledCommandsEntry ::=
              SEQUENCE {
                  ncdExecDCIndex
                      INTEGER,
                  ncdExecDCCommands
                      OCTET STRING
              }

          ncdExecDCIndex OBJECT-TYPE
              SYNTAX  INTEGER
              ACCESS  read-only
              STATUS  optional
			  DESCRIPTION ""
              ::= { ncdExecDisabledCommandsEntry 1 }

          ncdExecDCCommands OBJECT-TYPE
              SYNTAX  OCTET STRING
              ACCESS  read-write
              STATUS  optional
			  DESCRIPTION ""
              ::= { ncdExecDisabledCommandsEntry 2 }


          -- the ncdLogin Group

          ncdLoginDfltHostsTable OBJECT-TYPE
              SYNTAX  SEQUENCE OF NcdLoginDfltHostsEntry
              ACCESS  not-accessible
              STATUS  optional
			  DESCRIPTION ""
              ::= { ncdLogin 1 }

          ncdLoginDfltHostsEntry OBJECT-TYPE
              SYNTAX  NcdLoginDfltHostsEntry
              ACCESS  not-accessible
              STATUS  optional
			  DESCRIPTION ""
              ::= { ncdLoginDfltHostsTable 1 }

          NcdLoginDfltHostsEntry ::=
              SEQUENCE {
                  ncdLoginDHTIndex
                      INTEGER,
                  ncdLoginDHTNetwork
                      INTEGER,
                  ncdLoginDHTHost
                      OCTET STRING,
                  ncdLoginDHTDescription
                      OCTET STRING
              }

          ncdLoginDHTIndex OBJECT-TYPE
              SYNTAX  INTEGER
              ACCESS  read-only
              STATUS  optional
			  DESCRIPTION ""
              ::= { ncdLoginDfltHostsEntry 1 }

          ncdLoginDHTNetwork OBJECT-TYPE
              SYNTAX  INTEGER
              ACCESS  read-write
              STATUS  optional
			  DESCRIPTION ""
              ::= { ncdLoginDfltHostsEntry 2 }

          ncdLoginDHTHost OBJECT-TYPE
              SYNTAX  OCTET STRING
              ACCESS  read-write
              STATUS  optional
			  DESCRIPTION ""
              ::= { ncdLoginDfltHostsEntry 3 }

          ncdLoginDHTDescription OBJECT-TYPE
              SYNTAX  OCTET STRING
              ACCESS  read-write
              STATUS  optional
			  DESCRIPTION ""
              ::= { ncdLoginDfltHostsEntry 4 }

          ncdLoginRestrictConnectionChoices OBJECT-TYPE
              SYNTAX  INTEGER
              ACCESS  read-write
              STATUS  optional
			  DESCRIPTION ""
              ::= { ncdLogin 2 }

          ncdLoginDisabledNetTable OBJECT-TYPE
              SYNTAX  SEQUENCE OF NcdLoginDisabledNetEntry
              ACCESS  not-accessible
              STATUS  optional
			  DESCRIPTION ""
              ::= { ncdLogin 3 }

          ncdLoginDisabledNetEntry OBJECT-TYPE
              SYNTAX  NcdLoginDisabledNetEntry
              ACCESS  not-accessible
              STATUS  optional
			  DESCRIPTION ""
              ::= { ncdLoginDisabledNetTable 1 }

          NcdLoginDisabledNetEntry ::=
              SEQUENCE {
                  ncdLoginDNTIndex
                      INTEGER,
                  ncdLoginDNTName
                      OCTET STRING
              }

          ncdLoginDNTIndex OBJECT-TYPE
              SYNTAX  INTEGER
              ACCESS  read-only
              STATUS  optional
			  DESCRIPTION ""
              ::= { ncdLoginDisabledNetEntry 1 }

          ncdLoginDNTName OBJECT-TYPE
              SYNTAX  OCTET STRING
              ACCESS  read-write
              STATUS  optional
			  DESCRIPTION ""
              ::= { ncdLoginDisabledNetEntry 2 }

          ncdLoginAutoMapDelay OBJECT-TYPE
              SYNTAX  INTEGER
              ACCESS  read-write
              STATUS  optional
			  DESCRIPTION ""
              ::= { ncdLogin 4 }

          ncdLoginDwLoginAccount OBJECT-TYPE
              SYNTAX  OCTET STRING
              ACCESS  read-write
              STATUS  optional
			  DESCRIPTION ""
              ::= { ncdLogin 13 }

          ncdLoginDwPassword OBJECT-TYPE
              SYNTAX  OCTET STRING
              ACCESS  read-write
              STATUS  optional
			  DESCRIPTION ""
              ::= { ncdLogin 14 }


          -- the ncdPex Group

          ncdPexSetupMaxModelClipPlanes OBJECT-TYPE
              SYNTAX  INTEGER
              ACCESS  read-write
              STATUS  optional
			  DESCRIPTION ""
              ::= { ncdPex 1 }

          ncdPexSetupMaxNonAmbientLights OBJECT-TYPE
              SYNTAX  INTEGER
              ACCESS  read-write
              STATUS  optional
			  DESCRIPTION ""
              ::= { ncdPex 2 }

          ncdPexSetupMaxNamesetNames OBJECT-TYPE
              SYNTAX  INTEGER
              ACCESS  read-write
              STATUS  optional
			  DESCRIPTION ""
              ::= { ncdPex 3 }

          ncdPexSetupMonRefRedu OBJECT-TYPE
              SYNTAX  OCTET STRING
              ACCESS  read-write
              STATUS  optional
			  DESCRIPTION ""
              ::= { ncdPex 4 }

          ncdPexSetupMonRefRedv OBJECT-TYPE
              SYNTAX  OCTET STRING
              ACCESS  read-write
              STATUS  optional
			  DESCRIPTION ""
              ::= { ncdPex 5 }

          ncdPexSetupMonRefRedY OBJECT-TYPE
              SYNTAX  OCTET STRING
              ACCESS  read-write
              STATUS  optional
			  DESCRIPTION ""
              ::= { ncdPex 6 }

          ncdPexSetupMonRefGreenu OBJECT-TYPE
              SYNTAX  OCTET STRING
              ACCESS  read-write
              STATUS  optional
			  DESCRIPTION ""
              ::= { ncdPex 7 }

          ncdPexSetupMonRefGreenv OBJECT-TYPE
              SYNTAX  OCTET STRING
              ACCESS  read-write
              STATUS  optional
			  DESCRIPTION ""
              ::= { ncdPex 8 }

          ncdPexSetupMonRefGreenY OBJECT-TYPE
              SYNTAX  OCTET STRING
              ACCESS  read-write
              STATUS  optional
			  DESCRIPTION ""
              ::= { ncdPex 9 }

          ncdPexSetupMonRefBlueu OBJECT-TYPE
              SYNTAX  OCTET STRING
              ACCESS  read-write
              STATUS  optional
			  DESCRIPTION ""
              ::= { ncdPex 10 }

          ncdPexSetupMonRefBluev OBJECT-TYPE
              SYNTAX  OCTET STRING
              ACCESS  read-write
              STATUS  optional
			  DESCRIPTION ""
              ::= { ncdPex 11 }

          ncdPexSetupMonRefBlueY OBJECT-TYPE
              SYNTAX  OCTET STRING
              ACCESS  read-write
              STATUS  optional
			  DESCRIPTION ""
              ::= { ncdPex 12 }

          ncdPexSetupMonRefWhiteu OBJECT-TYPE
              SYNTAX  OCTET STRING
              ACCESS  read-write
              STATUS  optional
			  DESCRIPTION ""
              ::= { ncdPex 13 }

          ncdPexSetupMonRefWhitev OBJECT-TYPE
              SYNTAX  OCTET STRING
              ACCESS  read-write
              STATUS  optional
			  DESCRIPTION ""
              ::= { ncdPex 14 }

          ncdPexSetupMonRefWhiteY OBJECT-TYPE
              SYNTAX  OCTET STRING
              ACCESS  read-write
              STATUS  optional
			  DESCRIPTION ""
              ::= { ncdPex 15 }


          -- the ncdTerm Group

          ncdTermDfltConnectionTable OBJECT-TYPE
              SYNTAX  SEQUENCE OF NcdTermDfltConnectionEntry
              ACCESS  not-accessible
              STATUS  optional
			  DESCRIPTION ""
              ::= { ncdTerm 1 }

          ncdTermDfltConnectionEntry OBJECT-TYPE
              SYNTAX  NcdTermDfltConnectionEntry
              ACCESS  not-accessible
              STATUS  optional
			  DESCRIPTION ""
              ::= { ncdTermDfltConnectionTable 1 }

          NcdTermDfltConnectionEntry ::=
              SEQUENCE {
                  ncdTermDCTIndex
                      INTEGER,
                  ncdTermDCTProtocol
                      INTEGER,
                  ncdTermDCTHost
                      OCTET STRING,
                  ncdTermDCTDescription
                      OCTET STRING
              }

          ncdTermDCTIndex OBJECT-TYPE
              SYNTAX  INTEGER
              ACCESS  read-only
              STATUS  optional
			  DESCRIPTION ""
              ::= { ncdTermDfltConnectionEntry 1 }

          ncdTermDCTProtocol OBJECT-TYPE
              SYNTAX  INTEGER
              ACCESS  read-write
              STATUS  optional
			  DESCRIPTION ""
              ::= { ncdTermDfltConnectionEntry 2 }

          ncdTermDCTHost OBJECT-TYPE
              SYNTAX  OCTET STRING
              ACCESS  read-write
              STATUS  optional
			  DESCRIPTION ""
              ::= { ncdTermDfltConnectionEntry 3 }

          ncdTermDCTDescription OBJECT-TYPE
              SYNTAX  OCTET STRING
              ACCESS  read-write
              STATUS  optional
			  DESCRIPTION ""
              ::= { ncdTermDfltConnectionEntry 4 }

          ncdTermRestrictConnectionChoices OBJECT-TYPE
              SYNTAX  INTEGER
              ACCESS  read-write
              STATUS  optional
			  DESCRIPTION ""
              ::= { ncdTerm 2 }

          ncdTermAutoMapDelay OBJECT-TYPE
              SYNTAX  INTEGER
              ACCESS  read-write
              STATUS  optional
			  DESCRIPTION ""
              ::= { ncdTerm 3 }

          ncdTermDfltConnectTimeout OBJECT-TYPE
              SYNTAX  INTEGER
              ACCESS  read-write
              STATUS  optional
			  DESCRIPTION ""
              ::= { ncdTerm 4 }

          ncdTermDelayLATDisplay OBJECT-TYPE
              SYNTAX  INTEGER
              ACCESS  read-write
              STATUS  optional
			  DESCRIPTION ""
              ::= { ncdTerm 5 }


          -- the ncdFile Group

          ncdFileInitialFileServer1 OBJECT-TYPE
              SYNTAX  IpAddress
              ACCESS  read-write
              STATUS  optional
			  DESCRIPTION ""
              ::= { ncdFile 1 }

          ncdFileInitialFileServer1Protocol OBJECT-TYPE
              SYNTAX  INTEGER
              ACCESS  read-write
              STATUS  optional
			  DESCRIPTION ""
              ::= { ncdFile 2 }

          ncdFileInitialFileServer2 OBJECT-TYPE
              SYNTAX  IpAddress
              ACCESS  read-write
              STATUS  optional
			  DESCRIPTION ""
              ::= { ncdFile 3 }

          ncdFileInitialFileServer2Protocol OBJECT-TYPE
              SYNTAX  INTEGER
              ACCESS  read-write
              STATUS  optional
			  DESCRIPTION ""
              ::= { ncdFile 4 }

          ncdFileInitialFileServersUseVmsTftp OBJECT-TYPE
              SYNTAX  INTEGER
              ACCESS  read-write
              STATUS  optional
			  DESCRIPTION ""
              ::= { ncdFile 5 }

          ncdFileServiceTable OBJECT-TYPE
              SYNTAX  SEQUENCE OF NcdFileServiceEntry
              ACCESS  not-accessible
              STATUS  optional
			  DESCRIPTION ""
              ::= { ncdFile 6 }

          ncdFileServiceEntry OBJECT-TYPE
              SYNTAX  NcdFileServiceEntry
              ACCESS  not-accessible
              STATUS  optional
			  DESCRIPTION ""
              ::= { ncdFileServiceTable 1 }

          NcdFileServiceEntry ::=
              SEQUENCE {
                  ncdFileSTIndex
                      INTEGER,
                  ncdFileSTLocalUnixMountPoint
                      OCTET STRING,
                  ncdFileSTLocalVmsMountPoint
                      OCTET STRING,
                  ncdFileSTServerAddress
                      IpAddress,
                  ncdFileSTProtocol
                      INTEGER,
                  ncdFileSTServerMountPoint
                      OCTET STRING,
                  ncdFileSTFileNameType
                      INTEGER,
                  ncdFileSTRetransTimeout
                      INTEGER,
                  ncdFileSTTransTimeout
                      INTEGER,
                  ncdFileSTReadSize
                      INTEGER,
                  ncdFileSTWriteSize
                      INTEGER
              }

          ncdFileSTIndex OBJECT-TYPE
              SYNTAX  INTEGER
              ACCESS  read-only
              STATUS  optional
			  DESCRIPTION ""
              ::= { ncdFileServiceEntry 1 }

          ncdFileSTLocalUnixMountPoint OBJECT-TYPE
              SYNTAX  OCTET STRING
              ACCESS  read-write
              STATUS  optional
			  DESCRIPTION ""
              ::= { ncdFileServiceEntry 2 }

          ncdFileSTLocalVmsMountPoint OBJECT-TYPE
              SYNTAX  OCTET STRING
              ACCESS  read-write
              STATUS  optional
			  DESCRIPTION ""
              ::= { ncdFileServiceEntry 3 }

          ncdFileSTServerAddress OBJECT-TYPE
              SYNTAX  IpAddress
              ACCESS  read-write
              STATUS  optional
			  DESCRIPTION ""
              ::= { ncdFileServiceEntry 4 }

          ncdFileSTProtocol OBJECT-TYPE
              SYNTAX  INTEGER
              ACCESS  read-write
              STATUS  optional
			  DESCRIPTION ""
              ::= { ncdFileServiceEntry 5 }

          ncdFileSTServerMountPoint OBJECT-TYPE
              SYNTAX  OCTET STRING
              ACCESS  read-write
              STATUS  optional
			  DESCRIPTION ""
              ::= { ncdFileServiceEntry 6 }

          ncdFileSTFileNameType OBJECT-TYPE
              SYNTAX  INTEGER
              ACCESS  read-write
              STATUS  optional
			  DESCRIPTION ""
              ::= { ncdFileServiceEntry 7 }

          ncdFileSTRetransTimeout OBJECT-TYPE
              SYNTAX  INTEGER
              ACCESS  read-write
              STATUS  optional
			  DESCRIPTION ""
              ::= { ncdFileServiceEntry 8 }

          ncdFileSTTransTimeout OBJECT-TYPE
              SYNTAX  INTEGER
              ACCESS  read-write
              STATUS  optional
			  DESCRIPTION ""
              ::= { ncdFileServiceEntry 9 }

          ncdFileSTReadSize OBJECT-TYPE
              SYNTAX  INTEGER
              ACCESS  read-write
              STATUS  optional
			  DESCRIPTION ""
              ::= { ncdFileServiceEntry 10 }

          ncdFileSTWriteSize OBJECT-TYPE
              SYNTAX  INTEGER
              ACCESS  read-write
              STATUS  optional
			  DESCRIPTION ""
              ::= { ncdFileServiceEntry 11 }

          ncdFileExtendedDiagnostics OBJECT-TYPE
              SYNTAX  INTEGER
              ACCESS  read-write
              STATUS  optional
			  DESCRIPTION ""
              ::= { ncdFile 7 }

          ncdFileRegressiveSearch OBJECT-TYPE
              SYNTAX  INTEGER
              ACCESS  read-write
              STATUS  optional
			  DESCRIPTION ""
              ::= { ncdFile 8 }

          ncdFileServerHolddownTime OBJECT-TYPE
              SYNTAX  INTEGER
              ACCESS  read-write
              STATUS  optional
			  DESCRIPTION ""
              ::= { ncdFile 9 }

          ncdFileUnmountTime OBJECT-TYPE
              SYNTAX  INTEGER
              ACCESS  read-write
              STATUS  optional
			  DESCRIPTION ""
              ::= { ncdFile 10 }

          ncdFileDfltVmsExtension OBJECT-TYPE
              SYNTAX  OCTET STRING
              ACCESS  read-write
              STATUS  optional
			  DESCRIPTION ""
              ::= { ncdFile 11 }

          ncdFileManagerTelnetPort OBJECT-TYPE
              SYNTAX  INTEGER
              ACCESS  read-write
              STATUS  optional
			  DESCRIPTION ""
              ::= { ncdFile 12 }

          ncdFileManagerTcpPort OBJECT-TYPE
              SYNTAX  INTEGER
              ACCESS  read-write
              STATUS  optional
			  DESCRIPTION ""
              ::= { ncdFile 13 }

          ncdFileManagerDnetObject OBJECT-TYPE
              SYNTAX  OCTET STRING
              ACCESS  read-write
              STATUS  optional
			  DESCRIPTION ""
              ::= { ncdFile 14 }


          -- the ncdPref Group

          ncdPrefKbdFuncKeyMap OBJECT-TYPE
              SYNTAX  INTEGER
              ACCESS  read-write
              STATUS  optional
			  DESCRIPTION ""
              ::= { ncdPref 1 }

          ncdPrefKbdAutoRepeat OBJECT-TYPE
              SYNTAX  INTEGER
              ACCESS  read-write
              STATUS  optional
			  DESCRIPTION ""
              ::= { ncdPref 2 }

          ncdPrefKdbAutoRepeatAfter OBJECT-TYPE
              SYNTAX  TimeTicks
              ACCESS  read-write
              STATUS  optional
			  DESCRIPTION ""
              ::= { ncdPref 3 }

          ncdPrefKbdAutoRepeatRate OBJECT-TYPE
              SYNTAX  INTEGER
              ACCESS  read-write
              STATUS  optional
			  DESCRIPTION ""
              ::= { ncdPref 4 }

          ncdPrefKeyClickVolume OBJECT-TYPE
              SYNTAX  INTEGER
              ACCESS  read-write
              STATUS  optional
			  DESCRIPTION ""
              ::= { ncdPref 5 }

          ncdPrefKbdLedsTable OBJECT-TYPE
              SYNTAX  SEQUENCE OF NcdPrefKbdLedsEntry
              ACCESS  not-accessible
              STATUS  optional
			  DESCRIPTION ""
              ::= { ncdPref 6 }

          ncdPrefKbdLedsEntry OBJECT-TYPE
              SYNTAX  NcdPrefKbdLedsEntry
              ACCESS  not-accessible
              STATUS  optional
			  DESCRIPTION ""
              ::= { ncdPrefKbdLedsTable 1 }

          NcdPrefKbdLedsEntry ::=
              SEQUENCE {
                  ncdPrefLedsTableIndex
                      INTEGER,
                  ncdPrefLedsTableEntry
                      INTEGER
              }

          ncdPrefLedsTableIndex OBJECT-TYPE
              SYNTAX  INTEGER
              ACCESS  read-only
              STATUS  optional
			  DESCRIPTION ""
              ::= { ncdPrefKbdLedsEntry 1 }

          ncdPrefLedsTableEntry OBJECT-TYPE
              SYNTAX  INTEGER
              ACCESS  read-write
              STATUS  optional
			  DESCRIPTION ""
              ::= { ncdPrefKbdLedsEntry 2 }

          ncdPrefBellEnabled OBJECT-TYPE
              SYNTAX  INTEGER
              ACCESS  read-write
              STATUS  optional
			  DESCRIPTION ""
              ::= { ncdPref 7 }

          ncdPrefBellVolume OBJECT-TYPE
              SYNTAX  INTEGER
              ACCESS  read-write
              STATUS  optional
			  DESCRIPTION ""
              ::= { ncdPref 8 }

          ncdPrefBellPitch OBJECT-TYPE
              SYNTAX  INTEGER
              ACCESS  read-write
              STATUS  optional
			  DESCRIPTION ""
              ::= { ncdPref 9 }

          ncdPrefBellDuration OBJECT-TYPE
              SYNTAX  TimeTicks
              ACCESS  read-write
              STATUS  optional
			  DESCRIPTION ""
              ::= { ncdPref 10 }

          ncdPrefMouseThresholdDistance OBJECT-TYPE
              SYNTAX  INTEGER
              ACCESS  read-write
              STATUS  optional
			  DESCRIPTION ""
              ::= { ncdPref 11 }

          ncdPrefMouseAcceration OBJECT-TYPE
              SYNTAX  INTEGER
              ACCESS  read-write
              STATUS  optional
			  DESCRIPTION ""
              ::= { ncdPref 12 }

          ncdPrefMouseButtonArragement OBJECT-TYPE
              SYNTAX  INTEGER
              ACCESS  read-write
              STATUS  optional
			  DESCRIPTION ""
              ::= { ncdPref 13 }

          ncdPrefScreenBackground OBJECT-TYPE
              SYNTAX  INTEGER
              ACCESS  read-write
              STATUS  optional
			  DESCRIPTION ""
              ::= { ncdPref 14 }

          ncdPrefScreenSolidColor OBJECT-TYPE
              SYNTAX  OCTET STRING
              ACCESS  read-write
              STATUS  optional
			  DESCRIPTION ""
              ::= { ncdPref 15 }

          ncdPrefScreenBitmapFile OBJECT-TYPE
              SYNTAX  OCTET STRING
              ACCESS  read-write
              STATUS  optional
			  DESCRIPTION ""
              ::= { ncdPref 16 }

          ncdPrefScreenBackBitmapForeground OBJECT-TYPE
              SYNTAX  OCTET STRING
              ACCESS  read-write
              STATUS  optional
			  DESCRIPTION ""
              ::= { ncdPref 17 }

          ncdPrefScreenBackBitmapBackground OBJECT-TYPE
              SYNTAX  OCTET STRING
              ACCESS  read-write
              STATUS  optional
			  DESCRIPTION ""
              ::= { ncdPref 18 }

          ncdPrefScreenSaverEnabled OBJECT-TYPE
              SYNTAX  INTEGER
              ACCESS  read-write
              STATUS  optional
			  DESCRIPTION ""
              ::= { ncdPref 20 }

          ncdPrefScreenSaverAllowExposures OBJECT-TYPE
              SYNTAX  INTEGER
              ACCESS  read-write
              STATUS  optional
			  DESCRIPTION ""
              ::= { ncdPref 21 }

          ncdPrefScreenSaverAfter OBJECT-TYPE
              SYNTAX  INTEGER
              ACCESS  read-write
              STATUS  optional
			  DESCRIPTION ""
              ::= { ncdPref 22 }

          ncdPrefScreenSaverChangeAfter OBJECT-TYPE
              SYNTAX  INTEGER
              ACCESS  read-write
              STATUS  optional
			  DESCRIPTION ""
              ::= { ncdPref 23 }

          ncdPrefScreenSaverStyle OBJECT-TYPE
              SYNTAX  INTEGER
              ACCESS  read-write
              STATUS  optional
			  DESCRIPTION ""
              ::= { ncdPref 24 }

          ncdPrefScreenSaverBitmapFile OBJECT-TYPE
              SYNTAX  OCTET STRING
              ACCESS  read-write
              STATUS  optional
			  DESCRIPTION ""
              ::= { ncdPref 25 }

          ncdPrefFontExtendedDiagnostics OBJECT-TYPE
              SYNTAX  INTEGER
              ACCESS  read-write
              STATUS  optional
			  DESCRIPTION ""
              ::= { ncdPref 26 }

          ncdPrefFontPathTable OBJECT-TYPE
              SYNTAX  SEQUENCE OF NcdPrefFontPathEntry
              ACCESS  not-accessible
              STATUS  optional
			  DESCRIPTION ""
              ::= { ncdPref 27 }

          ncdPrefFontPathEntry OBJECT-TYPE
              SYNTAX  NcdPrefFontPathEntry
              ACCESS  not-accessible
              STATUS  optional
			  DESCRIPTION ""
              ::= { ncdPrefFontPathTable 1 }

          NcdPrefFontPathEntry ::=
              SEQUENCE {
                  ncdPrefFontPathTableIndex
                      INTEGER,
                  ncdPrefFontPathTableEntry
                      OCTET STRING
              }

          ncdPrefFontPathTableIndex OBJECT-TYPE
              SYNTAX  INTEGER
              ACCESS  read-only
              STATUS  optional
			  DESCRIPTION ""
              ::= { ncdPrefFontPathEntry 1 }

          ncdPrefFontPathTableEntry OBJECT-TYPE
              SYNTAX  OCTET STRING
              ACCESS  read-write
              STATUS  optional
			  DESCRIPTION ""
              ::= { ncdPrefFontPathEntry 2 }

          ncdPrefScreenRes OBJECT-TYPE
              SYNTAX  INTEGER
              ACCESS  read-write
              STATUS  optional
			  DESCRIPTION ""
              ::= { ncdPref 29 }

          ncdPrefUseBackingStore OBJECT-TYPE
              SYNTAX  INTEGER
              ACCESS  read-write
              STATUS  optional
			  DESCRIPTION ""
              ::= { ncdPref 30 }

          ncdPrefPermitOldBugs OBJECT-TYPE
              SYNTAX  INTEGER
              ACCESS  read-write
              STATUS  optional
			  DESCRIPTION ""
              ::= { ncdPref 31 }

          ncdPrefOldDwCompatibility OBJECT-TYPE
              SYNTAX  INTEGER
              ACCESS  read-write
              STATUS  optional
			  DESCRIPTION ""
              ::= { ncdPref 32 }

          ncdPrefOldDwKbdCompatibility OBJECT-TYPE
              SYNTAX  INTEGER
              ACCESS  read-write
              STATUS  optional
			  DESCRIPTION ""
              ::= { ncdPref 33 }

          ncdPrefOldDwImageCompatibility OBJECT-TYPE
              SYNTAX  INTEGER
              ACCESS  read-write
              STATUS  optional
			  DESCRIPTION ""
              ::= { ncdPref 34 }

          ncdPrefConsoleAutoLogoutIdleTime OBJECT-TYPE
              SYNTAX  INTEGER
              ACCESS  read-write
              STATUS  optional
			  DESCRIPTION ""
              ::= { ncdPref 35 }

          ncdPrefConsoleAutoLogoutCancelDelay OBJECT-TYPE
              SYNTAX  INTEGER
              ACCESS  read-write
              STATUS  optional
			  DESCRIPTION ""
              ::= { ncdPref 36 }

          ncdPrefConsoleAutoLockTime OBJECT-TYPE
              SYNTAX  INTEGER
              ACCESS  read-write
              STATUS  optional
			  DESCRIPTION ""
              ::= { ncdPref 37 }

          ncdPrefConsoleLockScreenPasswdDflt OBJECT-TYPE
              SYNTAX  OCTET STRING
              ACCESS  read-write
              STATUS  optional
			  DESCRIPTION ""
              ::= { ncdPref 38 }

          ncdPrefConsoleBlankScreenDelay OBJECT-TYPE
              SYNTAX  INTEGER
              ACCESS  read-write
              STATUS  optional
			  DESCRIPTION ""
              ::= { ncdPref 39 }

          ncdPrefConsoleShowTimestamps OBJECT-TYPE
              SYNTAX  INTEGER
              ACCESS  read-write
              STATUS  optional
			  DESCRIPTION ""
              ::= { ncdPref 40 }

          ncdPrefMaximumGain OBJECT-TYPE
              SYNTAX  INTEGER
              ACCESS  read-write
              STATUS  optional
			  DESCRIPTION ""
              ::= { ncdPref 41 }

          ncdPrefSIESamplingMethod OBJECT-TYPE
              SYNTAX  INTEGER
              ACCESS  read-write
              STATUS  optional
			  DESCRIPTION ""
              ::= { ncdPref 42 }

          ncdPrefSIEContrast OBJECT-TYPE
              SYNTAX  INTEGER
              ACCESS  read-write
              STATUS  optional
			  DESCRIPTION ""
              ::= { ncdPref 43 }

          ncdPrefConsoleKeyString OBJECT-TYPE
              SYNTAX  OCTET STRING
              ACCESS  read-write
              STATUS  optional
			  DESCRIPTION ""
              ::= { ncdPref 44 }

          ncdPrefTouchscreenButtonReleaseThreshold OBJECT-TYPE
              SYNTAX  INTEGER
              ACCESS  read-write
              STATUS  optional
			  DESCRIPTION ""
              ::= { ncdPref 45 }

          ncdPrefCurrentPointingDevice OBJECT-TYPE
              SYNTAX  INTEGER
              ACCESS  read-write
              STATUS  optional
			  DESCRIPTION ""
              ::= { ncdPref 46 }

          ncdPrefTouchscreenButtonPressThreshold OBJECT-TYPE
              SYNTAX  INTEGER
              ACCESS  read-write
              STATUS  optional
			  DESCRIPTION ""
              ::= { ncdPref 47 }

          ncdPrefPowerManageStandbyTime OBJECT-TYPE
              SYNTAX  INTEGER
              ACCESS  read-write
              STATUS  optional
			  DESCRIPTION ""
              ::= { ncdPref 50 }

          ncdPrefPowerManageSuspendTime OBJECT-TYPE
              SYNTAX  INTEGER
              ACCESS  read-write
              STATUS  optional
			  DESCRIPTION ""
              ::= { ncdPref 51 }

          ncdPrefPowerManagePowerdownTime OBJECT-TYPE
              SYNTAX  INTEGER
              ACCESS  read-write
              STATUS  optional
			  DESCRIPTION ""
              ::= { ncdPref 52 }

          ncdPrefPowerManageEnable OBJECT-TYPE
              SYNTAX  INTEGER
              ACCESS  read-write
              STATUS  optional
			  DESCRIPTION ""
              ::= { ncdPref 53 }


          -- the ncdAccess Group

          ncdAccessXdmAuthCookie OBJECT-TYPE
              SYNTAX  OCTET STRING
              ACCESS  read-write
              STATUS  optional
			  DESCRIPTION ""
              ::= { ncdAccess 1 }

          ncdAccessDfltAccessEnabled OBJECT-TYPE
              SYNTAX  INTEGER
              ACCESS  read-write
              STATUS  optional
			  DESCRIPTION ""
              ::= { ncdAccess 2 }

          ncdAccessAccessEnabled OBJECT-TYPE
              SYNTAX  INTEGER
              ACCESS  read-write
              STATUS  optional
			  DESCRIPTION ""
              ::= { ncdAccess 3 }

          ncdAccessAccessControlTable OBJECT-TYPE
              SYNTAX  SEQUENCE OF NcdAccessAccessControlEntry
              ACCESS  not-accessible
              STATUS  optional
			  DESCRIPTION ""
              ::= { ncdAccess 4 }

          ncdAccessAccessControlEntry OBJECT-TYPE
              SYNTAX  NcdAccessAccessControlEntry
              ACCESS  not-accessible
              STATUS  optional
			  DESCRIPTION ""
              ::= { ncdAccessAccessControlTable 1 }

          NcdAccessAccessControlEntry ::=
              SEQUENCE {
                  ncdAccessACTIndex
                      INTEGER,
                  ncdAccessACTAddress
                      OCTET STRING,
                  ncdAccessACTFamily
                      INTEGER
              }

          ncdAccessACTIndex OBJECT-TYPE
              SYNTAX  INTEGER
              ACCESS  read-only
              STATUS  optional
			  DESCRIPTION ""
              ::= { ncdAccessAccessControlEntry 1 }

          ncdAccessACTAddress OBJECT-TYPE
              SYNTAX  OCTET STRING
              ACCESS  read-write
              STATUS  optional
			  DESCRIPTION ""
              ::= { ncdAccessAccessControlEntry 2 }

          ncdAccessACTFamily OBJECT-TYPE
              SYNTAX  INTEGER
              ACCESS  read-write
              STATUS  optional
			  DESCRIPTION ""
              ::= { ncdAccessAccessControlEntry 3 }

          ncdAccessConfigdReadOnlyPasswd OBJECT-TYPE
              SYNTAX  OCTET STRING
              ACCESS  read-write
              STATUS  optional
			  DESCRIPTION ""
              ::= { ncdAccess 5 }

          ncdAccessConfigdReadWritePasswd OBJECT-TYPE
              SYNTAX  OCTET STRING
              ACCESS  read-write
              STATUS  optional
			  DESCRIPTION ""
              ::= { ncdAccess 6 }

          ncdAccessConfigdEnforePasswdsLocally OBJECT-TYPE
              SYNTAX  INTEGER
              ACCESS  read-write
              STATUS  optional
			  DESCRIPTION ""
              ::= { ncdAccess 7 }

          ncdAccessConfigdAccessControlEnabled OBJECT-TYPE
              SYNTAX  INTEGER
              ACCESS  read-write
              STATUS  optional
			  DESCRIPTION ""
              ::= { ncdAccess 8 }

          ncdAccessConfigdHostTable OBJECT-TYPE
              SYNTAX  SEQUENCE OF NcdAccessConfigdHostEntry
              ACCESS  not-accessible
              STATUS  optional
			  DESCRIPTION ""
              ::= { ncdAccess 9 }

          ncdAccessConfigdHostEntry OBJECT-TYPE
              SYNTAX  NcdAccessConfigdHostEntry
              ACCESS  not-accessible
              STATUS  optional
			  DESCRIPTION ""
              ::= { ncdAccessConfigdHostTable 1 }

          NcdAccessConfigdHostEntry ::=
              SEQUENCE {
                  ncdAccessCHTIndex
                      INTEGER,
                  ncdAccessCHTAddress
                      OCTET STRING,
                  ncdAccessCHTFamily
                      INTEGER
              }

          ncdAccessCHTIndex OBJECT-TYPE
              SYNTAX  INTEGER
              ACCESS  read-only
              STATUS  optional
			  DESCRIPTION ""
              ::= { ncdAccessConfigdHostEntry 1 }

          ncdAccessCHTAddress OBJECT-TYPE
              SYNTAX  OCTET STRING
              ACCESS  read-write
              STATUS  optional
			  DESCRIPTION ""
              ::= { ncdAccessConfigdHostEntry 2 }

          ncdAccessCHTFamily OBJECT-TYPE
              SYNTAX  INTEGER
              ACCESS  read-write
              STATUS  optional
			  DESCRIPTION ""
              ::= { ncdAccessConfigdHostEntry 3 }

          ncdAccessPrefdReadOnlyPasswd OBJECT-TYPE
              SYNTAX  OCTET STRING
              ACCESS  read-write
              STATUS  optional
			  DESCRIPTION ""
              ::= { ncdAccess 10 }

          ncdAccessPrefdReadWritePasswd OBJECT-TYPE
              SYNTAX  OCTET STRING
              ACCESS  read-write
              STATUS  optional
			  DESCRIPTION ""
              ::= { ncdAccess 11 }

          ncdAccessPrefdEnforcePasswdsLocally OBJECT-TYPE
              SYNTAX  INTEGER
              ACCESS  read-write
              STATUS  optional
			  DESCRIPTION ""
              ::= { ncdAccess 12 }

          ncdAccessSnmpReadOnlyCommunity1 OBJECT-TYPE
              SYNTAX  OCTET STRING
              ACCESS  read-write
              STATUS  optional
			  DESCRIPTION ""
              ::= { ncdAccess 13 }

          ncdAccessSnmpReadOnlyCommunity2 OBJECT-TYPE
              SYNTAX  OCTET STRING
              ACCESS  read-write
              STATUS  optional
			  DESCRIPTION ""
              ::= { ncdAccess 14 }

          ncdAccessSnmpReadOnlyAccessControl OBJECT-TYPE
              SYNTAX  INTEGER
              ACCESS  read-write
              STATUS  optional
			  DESCRIPTION ""
              ::= { ncdAccess 15 }

          ncdAccessSnmpReadOnlyAccessControlTable OBJECT-TYPE
              SYNTAX  SEQUENCE OF NcdAccessSnmpReadOnlyAccessControlEntry
              ACCESS  not-accessible
              STATUS  optional
			  DESCRIPTION ""
              ::= { ncdAccess 16 }

          ncdAccessSnmpReadOnlyAccessControlEntry OBJECT-TYPE
              SYNTAX  NcdAccessSnmpReadOnlyAccessControlEntry
              ACCESS  not-accessible
              STATUS  optional
			  DESCRIPTION ""
              ::= { ncdAccessSnmpReadOnlyAccessControlTable 1 }

          NcdAccessSnmpReadOnlyAccessControlEntry ::=
              SEQUENCE {
                  ncdAccessSnmpROAccessControlTableIndex
                      INTEGER,
                  ncdAccessSnmpROAccessControlTableHost
                      OCTET STRING
              }

          ncdAccessSnmpROAccessControlTableIndex OBJECT-TYPE
              SYNTAX  INTEGER
              ACCESS  read-only
              STATUS  optional
			  DESCRIPTION ""
              ::= { ncdAccessSnmpReadOnlyAccessControlEntry 1 }

          ncdAccessSnmpROAccessControlTableHost OBJECT-TYPE
              SYNTAX  OCTET STRING
              ACCESS  read-write
              STATUS  optional
			  DESCRIPTION ""
              ::= { ncdAccessSnmpReadOnlyAccessControlEntry 2 }

          ncdAccessSnmpReadWriteCommunity1 OBJECT-TYPE
              SYNTAX  OCTET STRING
              ACCESS  read-write
              STATUS  optional
			  DESCRIPTION ""
              ::= { ncdAccess 17 }

          ncdAccessSnmpReadWriteCommunity2 OBJECT-TYPE
              SYNTAX  OCTET STRING
              ACCESS  read-write
              STATUS  optional
			  DESCRIPTION ""
              ::= { ncdAccess 18 }

          ncdAccessSnmpReadWriteAccessControl OBJECT-TYPE
              SYNTAX  INTEGER
              ACCESS  read-write
              STATUS  optional
			  DESCRIPTION ""
              ::= { ncdAccess 19 }

          ncdAccessSnmpReadWriteAccessControlTable OBJECT-TYPE
              SYNTAX  SEQUENCE OF NcdAccessSnmpReadWriteAccessControlEntry
              ACCESS  not-accessible
              STATUS  optional
			  DESCRIPTION ""
              ::= { ncdAccess 20 }

          ncdAccessSnmpReadWriteAccessControlEntry OBJECT-TYPE
              SYNTAX  NcdAccessSnmpReadWriteAccessControlEntry
              ACCESS  not-accessible
              STATUS  optional
			  DESCRIPTION ""
              ::= { ncdAccessSnmpReadWriteAccessControlTable 1 }

          NcdAccessSnmpReadWriteAccessControlEntry ::=
              SEQUENCE {
                  ncdAccessSnmpRWAccessControlTableIndex
                      INTEGER,
                  ncdAccessSnmpRWAccessControlTableAddress
                      OCTET STRING
              }

          ncdAccessSnmpRWAccessControlTableIndex OBJECT-TYPE
              SYNTAX  INTEGER
              ACCESS  read-only
              STATUS  optional
			  DESCRIPTION ""
              ::= { ncdAccessSnmpReadWriteAccessControlEntry 1 }

          ncdAccessSnmpRWAccessControlTableAddress OBJECT-TYPE
              SYNTAX  OCTET STRING
              ACCESS  read-write
              STATUS  optional
			  DESCRIPTION ""
              ::= { ncdAccessSnmpReadWriteAccessControlEntry 2 }

          ncdAccessSnmpResetEnabled OBJECT-TYPE
              SYNTAX  INTEGER
              ACCESS  read-write
              STATUS  optional
			  DESCRIPTION ""
              ::= { ncdAccess 21 }

          ncdAccessSnmpTrapMonitorsTable OBJECT-TYPE
              SYNTAX  SEQUENCE OF NcdAccessSnmpTrapMonitorsEntry
              ACCESS  not-accessible
              STATUS  optional
			  DESCRIPTION ""
              ::= { ncdAccess 22 }

          ncdAccessSnmpTrapMonitorsEntry OBJECT-TYPE
              SYNTAX  NcdAccessSnmpTrapMonitorsEntry
              ACCESS  not-accessible
              STATUS  optional
			  DESCRIPTION ""
              ::= { ncdAccessSnmpTrapMonitorsTable 1 }

          NcdAccessSnmpTrapMonitorsEntry ::=
              SEQUENCE {
                  ncdAccessSnmpTMTIndex
                      INTEGER,
                  ncdAccessSnmpTMTHost
                      IpAddress,
                  ncdAccessSnmpTMTCommunity
                      OCTET STRING
              }

          ncdAccessSnmpTMTIndex OBJECT-TYPE
              SYNTAX  INTEGER
              ACCESS  read-only
              STATUS  optional
			  DESCRIPTION ""
              ::= { ncdAccessSnmpTrapMonitorsEntry 1 }

          ncdAccessSnmpTMTHost OBJECT-TYPE
              SYNTAX  IpAddress
              ACCESS  read-write
              STATUS  optional
			  DESCRIPTION ""
              ::= { ncdAccessSnmpTrapMonitorsEntry 2 }

          ncdAccessSnmpTMTCommunity OBJECT-TYPE
              SYNTAX  OCTET STRING
              ACCESS  read-write
              STATUS  optional
			  DESCRIPTION ""
              ::= { ncdAccessSnmpTrapMonitorsEntry 3 }

          ncdAccessMopResetPasswd OBJECT-TYPE
              SYNTAX  OCTET STRING
              ACCESS  read-write
              STATUS  optional
			  DESCRIPTION ""
              ::= { ncdAccess 23 }

          ncdAccessDiagdAccessControlEnabled OBJECT-TYPE
              SYNTAX  INTEGER
              ACCESS  read-write
              STATUS  optional
			  DESCRIPTION ""
              ::= { ncdAccess 24 }

          ncdAccessDiagdAccessControlTable OBJECT-TYPE
              SYNTAX  SEQUENCE OF NcdAccessDiagdAccessControlEntry
              ACCESS  not-accessible
              STATUS  optional
			  DESCRIPTION ""
              ::= { ncdAccess 25 }

          ncdAccessDiagdAccessControlEntry OBJECT-TYPE
              SYNTAX  NcdAccessDiagdAccessControlEntry
              ACCESS  not-accessible
              STATUS  optional
			  DESCRIPTION ""
              ::= { ncdAccessDiagdAccessControlTable 1 }

          NcdAccessDiagdAccessControlEntry ::=
              SEQUENCE {
                  ncdAccessDiagdACTIndex
                      INTEGER,
                  ncdAccessDiagdACTAddress
                      OCTET STRING,
                  ncdAccessDiagdACTFamily
                      INTEGER
              }

          ncdAccessDiagdACTIndex OBJECT-TYPE
              SYNTAX  INTEGER
              ACCESS  read-only
              STATUS  optional
			  DESCRIPTION ""
              ::= { ncdAccessDiagdAccessControlEntry 1 }

          ncdAccessDiagdACTAddress OBJECT-TYPE
              SYNTAX  OCTET STRING
              ACCESS  read-write
              STATUS  optional
			  DESCRIPTION ""
              ::= { ncdAccessDiagdAccessControlEntry 2 }

          ncdAccessDiagdACTFamily OBJECT-TYPE
              SYNTAX  INTEGER
              ACCESS  read-write
              STATUS  optional
			  DESCRIPTION ""
              ::= { ncdAccessDiagdAccessControlEntry 3 }

          ncdAccessNfsUserId OBJECT-TYPE
              SYNTAX  INTEGER
              ACCESS  read-write
              STATUS  optional
			  DESCRIPTION ""
              ::= { ncdAccess 26 }

          ncdAccessNfsGroupId OBJECT-TYPE
              SYNTAX  INTEGER
              ACCESS  read-write
              STATUS  optional
			  DESCRIPTION ""
              ::= { ncdAccess 27 }

          ncdAccessExecdAccessControlEnabled OBJECT-TYPE
              SYNTAX  INTEGER
              ACCESS  read-write
              STATUS  optional
			  DESCRIPTION ""
              ::= { ncdAccess 28 }

          ncdAccessExecdAccessControlTable OBJECT-TYPE
              SYNTAX  SEQUENCE OF NcdAccessExecdAccessControlEntry
              ACCESS  not-accessible
              STATUS  optional
			  DESCRIPTION ""
              ::= { ncdAccess 29 }

          ncdAccessExecdAccessControlEntry OBJECT-TYPE
              SYNTAX  NcdAccessExecdAccessControlEntry
              ACCESS  not-accessible
              STATUS  optional
			  DESCRIPTION ""
              ::= { ncdAccessExecdAccessControlTable 1 }

          NcdAccessExecdAccessControlEntry ::=
              SEQUENCE {
                  ncdAccessExecdACTIndex
                      INTEGER,
                  ncdAccessExecdACTAddress
                      OCTET STRING,
                  ncdAccessExecdACTFamily
                      INTEGER
              }

          ncdAccessExecdACTIndex OBJECT-TYPE
              SYNTAX  INTEGER
              ACCESS  read-only
              STATUS  optional
			  DESCRIPTION ""
              ::= { ncdAccessExecdAccessControlEntry 1 }

          ncdAccessExecdACTAddress OBJECT-TYPE
              SYNTAX  OCTET STRING
              ACCESS  read-write
              STATUS  optional
			  DESCRIPTION ""
              ::= { ncdAccessExecdAccessControlEntry 2 }

          ncdAccessExecdACTFamily OBJECT-TYPE
              SYNTAX  INTEGER
              ACCESS  read-write
              STATUS  optional
			  DESCRIPTION ""
              ::= { ncdAccessExecdAccessControlEntry 3 }

          ncdAccessSerialdLatPasswdTable OBJECT-TYPE
              SYNTAX  SEQUENCE OF NcdAccessSerialdLatPasswdEntry
              ACCESS  not-accessible
              STATUS  optional
			  DESCRIPTION ""
              ::= { ncdAccess 30 }

          ncdAccessSerialdLatPasswdEntry OBJECT-TYPE
              SYNTAX  NcdAccessSerialdLatPasswdEntry
              ACCESS  not-accessible
              STATUS  optional
			  DESCRIPTION ""
              ::= { ncdAccessSerialdLatPasswdTable 1 }

          NcdAccessSerialdLatPasswdEntry ::=
              SEQUENCE {
                  ncdAccessSerialdLPTIndex
                      INTEGER,
                  ncdAccessSerialdLPTPortNumber
                      INTEGER,
                  ncdAccessSerialdLPTPassword
                      OCTET STRING
              }

          ncdAccessSerialdLPTIndex OBJECT-TYPE
              SYNTAX  INTEGER
              ACCESS  read-only
              STATUS  optional
			  DESCRIPTION ""
              ::= { ncdAccessSerialdLatPasswdEntry 1 }

          ncdAccessSerialdLPTPortNumber OBJECT-TYPE
              SYNTAX  INTEGER
              ACCESS  read-only
              STATUS  optional
			  DESCRIPTION ""
              ::= { ncdAccessSerialdLatPasswdEntry 2 }

          ncdAccessSerialdLPTPassword OBJECT-TYPE
              SYNTAX  OCTET STRING
              ACCESS  read-write
              STATUS  optional
			  DESCRIPTION ""
              ::= { ncdAccessSerialdLatPasswdEntry 3 }

          ncdAccessSerialdAccessControlEnabled OBJECT-TYPE
              SYNTAX  INTEGER
              ACCESS  read-write
              STATUS  optional
			  DESCRIPTION ""
              ::= { ncdAccess 31 }

          ncdAccessSerialdAccessControlTable OBJECT-TYPE
              SYNTAX  SEQUENCE OF NcdAccessSerialdAccessControlEntry
              ACCESS  not-accessible
              STATUS  optional
			  DESCRIPTION ""
              ::= { ncdAccess 32 }

          ncdAccessSerialdAccessControlEntry OBJECT-TYPE
              SYNTAX  NcdAccessSerialdAccessControlEntry
              ACCESS  not-accessible
              STATUS  optional
			  DESCRIPTION ""
              ::= { ncdAccessSerialdAccessControlTable 1 }

          NcdAccessSerialdAccessControlEntry ::=
              SEQUENCE {
                  ncdAccessSerialdACTIndex
                      INTEGER,
                  ncdAccessSerialdACTAddress
                      OCTET STRING,
                  ncdAccessSerialdACTFamily
                      INTEGER
              }

          ncdAccessSerialdACTIndex OBJECT-TYPE
              SYNTAX  INTEGER
              ACCESS  read-only
              STATUS  optional
			  DESCRIPTION ""
              ::= { ncdAccessSerialdAccessControlEntry 1 }

          ncdAccessSerialdACTAddress OBJECT-TYPE
              SYNTAX  OCTET STRING
              ACCESS  read-write
              STATUS  optional
			  DESCRIPTION ""
              ::= { ncdAccessSerialdAccessControlEntry 2 }

          ncdAccessSerialdACTFamily OBJECT-TYPE
              SYNTAX  INTEGER
              ACCESS  read-write
              STATUS  optional
			  DESCRIPTION ""
              ::= { ncdAccessSerialdAccessControlEntry 3 }

          ncdAccessFileManagerPasswd OBJECT-TYPE
              SYNTAX  OCTET STRING
              ACCESS  read-write
              STATUS  optional
			  DESCRIPTION ""
              ::= { ncdAccess 33 }

          ncdAccessFiledAccessControlEnabled OBJECT-TYPE
              SYNTAX  INTEGER
              ACCESS  read-write
              STATUS  optional
			  DESCRIPTION ""
              ::= { ncdAccess 34 }

          ncdAccessFiledAccessControlTable OBJECT-TYPE
              SYNTAX  SEQUENCE OF NcdAccessFiledAccessControlEntry
              ACCESS  not-accessible
              STATUS  optional
			  DESCRIPTION ""
              ::= { ncdAccess 35 }

          ncdAccessFiledAccessControlEntry OBJECT-TYPE
              SYNTAX  NcdAccessFiledAccessControlEntry
              ACCESS  not-accessible
              STATUS  optional
			  DESCRIPTION ""
              ::= { ncdAccessFiledAccessControlTable 1 }

          NcdAccessFiledAccessControlEntry ::=
              SEQUENCE {
                  ncdAccessFiledACTIndex
                      INTEGER,
                  ncdAccessFiledACTAddress
                      OCTET STRING,
                  ncdAccessFiledACTFamily
                      INTEGER
              }

          ncdAccessFiledACTIndex OBJECT-TYPE
              SYNTAX  INTEGER
              ACCESS  read-only
              STATUS  optional
			  DESCRIPTION ""
              ::= { ncdAccessFiledAccessControlEntry 1 }

          ncdAccessFiledACTAddress OBJECT-TYPE
              SYNTAX  OCTET STRING
              ACCESS  read-write
              STATUS  optional
			  DESCRIPTION ""
              ::= { ncdAccessFiledAccessControlEntry 2 }

          ncdAccessFiledACTFamily OBJECT-TYPE
              SYNTAX  INTEGER
              ACCESS  read-write
              STATUS  optional
			  DESCRIPTION ""
              ::= { ncdAccessFiledAccessControlEntry 3 }

          ncdAccessParalleldLatPasswdTable OBJECT-TYPE
              SYNTAX  SEQUENCE OF NcdAccessParalleldLatPasswdEntry
              ACCESS  not-accessible
              STATUS  optional
			  DESCRIPTION ""
              ::= { ncdAccess 36 }

          ncdAccessParalleldLatPasswdEntry OBJECT-TYPE
              SYNTAX  NcdAccessParalleldLatPasswdEntry
              ACCESS  not-accessible
              STATUS  optional
			  DESCRIPTION ""
              ::= { ncdAccessParalleldLatPasswdTable 1 }

          NcdAccessParalleldLatPasswdEntry ::=
              SEQUENCE {
                  ncdAccessParalleldLPTIndex
                      INTEGER,
                  ncdAccessParalleldLPTPortNumber
                      INTEGER,
                  ncdAccessParalleldLPTPassword
                      OCTET STRING
              }

          ncdAccessParalleldLPTIndex OBJECT-TYPE
              SYNTAX  INTEGER
              ACCESS  read-only
              STATUS  optional
			  DESCRIPTION ""
              ::= { ncdAccessParalleldLatPasswdEntry 1 }

          ncdAccessParalleldLPTPortNumber OBJECT-TYPE
              SYNTAX  INTEGER
              ACCESS  read-only
              STATUS  optional
			  DESCRIPTION ""
              ::= { ncdAccessParalleldLatPasswdEntry 2 }

          ncdAccessParalleldLPTPassword OBJECT-TYPE
              SYNTAX  OCTET STRING
              ACCESS  read-write
              STATUS  optional
			  DESCRIPTION ""
              ::= { ncdAccessParalleldLatPasswdEntry 3 }

          ncdAccessGlobalPasswd OBJECT-TYPE
              SYNTAX  OCTET STRING
              ACCESS  read-write
              STATUS  optional
			  DESCRIPTION ""
              ::= { ncdAccess 38 }

          ncdAccessConsoleDisplayPassword OBJECT-TYPE
              SYNTAX  OCTET STRING
              ACCESS  read-write
              STATUS  optional
			  DESCRIPTION ""
              ::= { ncdAccess 42 }

          ncdAccessConsoleEnforcePasswordLocally OBJECT-TYPE
              SYNTAX  INTEGER
              ACCESS  read-write
              STATUS  optional
			  DESCRIPTION ""
              ::= { ncdAccess 43 }


          -- the ncdTokenRing Group

          ncdTokenRingSpeed OBJECT-TYPE
              SYNTAX  INTEGER
              ACCESS  read-write
              STATUS  optional
			  DESCRIPTION ""
              ::= { ncdTokenRing 1 }


          -- the ncdXremote Group

          ncdXremoteVersion OBJECT-TYPE
              SYNTAX  INTEGER
              ACCESS  read-only
              STATUS  optional
			  DESCRIPTION ""
              ::= { ncdXremote 1 }

          ncdXremoteState OBJECT-TYPE
              SYNTAX  OCTET STRING
              ACCESS  read-only
              STATUS  optional
			  DESCRIPTION ""
              ::= { ncdXremote 2 }

          ncdXremotePktsTransmitted OBJECT-TYPE
              SYNTAX  INTEGER
              ACCESS  read-only
              STATUS  optional
			  DESCRIPTION ""
              ::= { ncdXremote 3 }

          ncdXremotePktTransErrors OBJECT-TYPE
              SYNTAX  INTEGER
              ACCESS  read-only
              STATUS  optional
			  DESCRIPTION ""
              ::= { ncdXremote 4 }

          ncdXremotePktsRetrans OBJECT-TYPE
              SYNTAX  INTEGER
              ACCESS  read-only
              STATUS  optional
			  DESCRIPTION ""
              ::= { ncdXremote 5 }

          ncdXremotePktsReceived OBJECT-TYPE
              SYNTAX  INTEGER
              ACCESS  read-only
              STATUS  optional
			  DESCRIPTION ""
              ::= { ncdXremote 6 }

          ncdXremotePktsWithErrorsReceived OBJECT-TYPE
              SYNTAX  INTEGER
              ACCESS  read-only
              STATUS  optional
			  DESCRIPTION ""
              ::= { ncdXremote 7 }

          ncdXremotePktsOutOfSequence OBJECT-TYPE
              SYNTAX  INTEGER
              ACCESS  read-only
              STATUS  optional
			  DESCRIPTION ""
              ::= { ncdXremote 8 }

          ncdXremoteRoundTripTime OBJECT-TYPE
              SYNTAX  TimeTicks
              ACCESS  read-only
              STATUS  optional
			  DESCRIPTION ""
              ::= { ncdXremote 9 }

          ncdXremoteTimeOut OBJECT-TYPE
              SYNTAX  TimeTicks
              ACCESS  read-only
              STATUS  optional
			  DESCRIPTION ""
              ::= { ncdXremote 10 }

          ncdXremoteTransWinSize OBJECT-TYPE
              SYNTAX  INTEGER
              ACCESS  read-only
              STATUS  optional
			  DESCRIPTION ""
              ::= { ncdXremote 11 }

          ncdXremoteTransSequenceNumber OBJECT-TYPE
              SYNTAX  INTEGER
              ACCESS  read-only
              STATUS  optional
			  DESCRIPTION ""
              ::= { ncdXremote 12 }

          ncdXremoteUnackPkt OBJECT-TYPE
              SYNTAX  INTEGER
              ACCESS  read-only
              STATUS  optional
			  DESCRIPTION ""
              ::= { ncdXremote 13 }

          ncdXremoteReceiveWinSize OBJECT-TYPE
              SYNTAX  INTEGER
              ACCESS  read-only
              STATUS  optional
			  DESCRIPTION ""
              ::= { ncdXremote 14 }

          ncdXremoteNxtReceiveSequenceNumber OBJECT-TYPE
              SYNTAX  INTEGER
              ACCESS  read-only
              STATUS  optional
			  DESCRIPTION ""
              ::= { ncdXremote 15 }

          ncdXremoteCompressType OBJECT-TYPE
              SYNTAX  INTEGER
              ACCESS  read-write
              STATUS  optional
			  DESCRIPTION ""
              ::= { ncdXremote 16 }

          ncdXremoteAuthEnabled OBJECT-TYPE
              SYNTAX  INTEGER
              ACCESS  read-write
              STATUS  optional
			  DESCRIPTION ""
              ::= { ncdXremote 17 }

          ncdXremoteEscTable OBJECT-TYPE
              SYNTAX  SEQUENCE OF NcdXremoteEscEntry
              ACCESS  not-accessible
              STATUS  optional
			  DESCRIPTION ""
              ::= { ncdXremote 18 }

          ncdXremoteEscEntry OBJECT-TYPE
              SYNTAX  NcdXremoteEscEntry
              ACCESS  not-accessible
              STATUS  optional
			  DESCRIPTION ""
              ::= { ncdXremoteEscTable 1 }

          NcdXremoteEscEntry ::=
              SEQUENCE {
                  ncdXremoteEscIndex
                      INTEGER,
                  ncdXremoteEscChar
                      INTEGER
              }

          ncdXremoteEscIndex OBJECT-TYPE
              SYNTAX  INTEGER
              ACCESS  read-only
              STATUS  optional
			  DESCRIPTION ""
              ::= { ncdXremoteEscEntry 1 }

          ncdXremoteEscChar OBJECT-TYPE
              SYNTAX  INTEGER
              ACCESS  read-write
              STATUS  optional
			  DESCRIPTION ""
              ::= { ncdXremoteEscEntry 2 }

          ncdXremoteNetEnabled OBJECT-TYPE
              SYNTAX  INTEGER
              ACCESS  read-write
              STATUS  optional
			  DESCRIPTION ""
              ::= { ncdXremote 19 }

          ncdXremoteListenPort OBJECT-TYPE
              SYNTAX  INTEGER
              ACCESS  read-write
              STATUS  optional
			  DESCRIPTION ""
              ::= { ncdXremote 20 }


          -- the ncdPpp Group

          ncdPppSlipIfTable OBJECT-TYPE
              SYNTAX  SEQUENCE OF NcdPppSlipIfEntry
              ACCESS  not-accessible
              STATUS  optional
			  DESCRIPTION ""
              ::= { ncdPpp 1 }

          ncdPppSlipIfEntry OBJECT-TYPE
              SYNTAX  NcdPppSlipIfEntry
              ACCESS  not-accessible
              STATUS  optional
			  DESCRIPTION ""
              ::= { ncdPppSlipIfTable 1 }

          NcdPppSlipIfEntry ::=
              SEQUENCE {
                  ncdPppSlipIfTablePortNumber
                      INTEGER,
                  ncdPppSlipIfTableIpAddress
                      IpAddress,
                  ncdPppSlipIfTablePeerIpAddress
                      IpAddress,
                  ncdPppSlipIfTableDfltGateway
                      INTEGER,
                  ncdPppSlipIfTableVJCompression
                      INTEGER
              }

          ncdPppSlipIfTablePortNumber OBJECT-TYPE
              SYNTAX  INTEGER
              ACCESS  read-only
              STATUS  optional
			  DESCRIPTION ""
              ::= { ncdPppSlipIfEntry 1 }

          ncdPppSlipIfTableIpAddress OBJECT-TYPE
              SYNTAX  IpAddress
              ACCESS  read-write
              STATUS  optional
			  DESCRIPTION ""
              ::= { ncdPppSlipIfEntry 2 }

          ncdPppSlipIfTablePeerIpAddress OBJECT-TYPE
              SYNTAX  IpAddress
              ACCESS  read-write
              STATUS  optional
			  DESCRIPTION ""
              ::= { ncdPppSlipIfEntry 3 }

          ncdPppSlipIfTableDfltGateway OBJECT-TYPE
              SYNTAX  INTEGER
              ACCESS  read-write
              STATUS  optional
			  DESCRIPTION ""
              ::= { ncdPppSlipIfEntry 4 }

          ncdPppSlipIfTableVJCompression OBJECT-TYPE
              SYNTAX  INTEGER
              ACCESS  read-write
              STATUS  optional
			  DESCRIPTION ""
              ::= { ncdPppSlipIfEntry 5 }

          ncdPppIfTable OBJECT-TYPE
              SYNTAX  SEQUENCE OF NcdPppIfEntry
              ACCESS  not-accessible
              STATUS  optional
			  DESCRIPTION ""
              ::= { ncdPpp 2 }

          ncdPppIfEntry OBJECT-TYPE
              SYNTAX  NcdPppIfEntry
              ACCESS  not-accessible
              STATUS  optional
			  DESCRIPTION ""
              ::= { ncdPppIfTable 1 }

          NcdPppIfEntry ::=
              SEQUENCE {
                  ncdPppIfTablePortNumber
                      INTEGER,
                  ncdPppIfTableCtlCharMap
                      INTEGER,
                  ncdPppIfTableMTU
                      INTEGER,
                  ncdPppIfTableProtocolComp
                      INTEGER,
                  ncdPppIfTableACComp
                      INTEGER,
                  ncdPppIfTablePassive
                      INTEGER,
                  ncdPppIfTableOldOptions
                      INTEGER
              }

          ncdPppIfTablePortNumber OBJECT-TYPE
              SYNTAX  INTEGER
              ACCESS  read-only
              STATUS  optional
			  DESCRIPTION ""
              ::= { ncdPppIfEntry 1 }

          ncdPppIfTableCtlCharMap OBJECT-TYPE
              SYNTAX  INTEGER
              ACCESS  read-write
              STATUS  optional
			  DESCRIPTION ""
              ::= { ncdPppIfEntry 2 }

          ncdPppIfTableMTU OBJECT-TYPE
              SYNTAX  INTEGER
              ACCESS  read-write
              STATUS  optional
			  DESCRIPTION ""
              ::= { ncdPppIfEntry 3 }

          ncdPppIfTableProtocolComp OBJECT-TYPE
              SYNTAX  INTEGER
              ACCESS  read-write
              STATUS  optional
			  DESCRIPTION ""
              ::= { ncdPppIfEntry 4 }

          ncdPppIfTableACComp OBJECT-TYPE
              SYNTAX  INTEGER
              ACCESS  read-write
              STATUS  optional
			  DESCRIPTION ""
              ::= { ncdPppIfEntry 5 }

          ncdPppIfTablePassive OBJECT-TYPE
              SYNTAX  INTEGER
              ACCESS  read-write
              STATUS  optional
			  DESCRIPTION ""
              ::= { ncdPppIfEntry 6 }

          ncdPppIfTableOldOptions OBJECT-TYPE
              SYNTAX  INTEGER
              ACCESS  read-write
              STATUS  optional
			  DESCRIPTION ""
              ::= { ncdPppIfEntry 7 }


          -- the ncdPrefPex Group

          ncdPrefPexNomLinWidth OBJECT-TYPE
              SYNTAX  INTEGER
              ACCESS  read-write
              STATUS  optional
			  DESCRIPTION ""
              ::= { ncdPrefPex 1 }

          ncdPrefPexNomEdgeWidth OBJECT-TYPE
              SYNTAX  INTEGER
              ACCESS  read-write
              STATUS  optional
			  DESCRIPTION ""
              ::= { ncdPrefPex 2 }

          ncdPrefPexNomMarkSiz OBJECT-TYPE
              SYNTAX  INTEGER
              ACCESS  read-write
              STATUS  optional
			  DESCRIPTION ""
              ::= { ncdPrefPex 3 }

          ncdPrefPexDitFlatShadedSurface OBJECT-TYPE
              SYNTAX  INTEGER
              ACCESS  read-write
              STATUS  optional
			  DESCRIPTION ""
              ::= { ncdPrefPex 4 }

          ncdPrefPexDitInterpSurface OBJECT-TYPE
              SYNTAX  INTEGER
              ACCESS  read-write
              STATUS  optional
			  DESCRIPTION ""
              ::= { ncdPrefPex 5 }

          ncdPrefPexSurfaceInterStyle OBJECT-TYPE
              SYNTAX  INTEGER
              ACCESS  read-write
              STATUS  optional
			  DESCRIPTION ""
              ::= { ncdPrefPex 6 }

          ncdPrefPexSurfaceInterpMethod OBJECT-TYPE
              SYNTAX  INTEGER
              ACCESS  read-write
              STATUS  optional
			  DESCRIPTION ""
              ::= { ncdPrefPex 7 }

          ncdPrefPexSurfaceReflectModel OBJECT-TYPE
              SYNTAX  INTEGER
              ACCESS  read-write
              STATUS  optional
			  DESCRIPTION ""
              ::= { ncdPrefPex 8 }

          ncdPrefPexColorClipMethod OBJECT-TYPE
              SYNTAX  INTEGER
              ACCESS  read-write
              STATUS  optional
			  DESCRIPTION ""
              ::= { ncdPrefPex 9 }


          -- the ncd3270 Group

          ncd3270DfltConnectionTable OBJECT-TYPE
              SYNTAX  SEQUENCE OF Ncd3270DfltConnectionEntry
              ACCESS  not-accessible
              STATUS  optional
			  DESCRIPTION ""
              ::= { ncd3270 1 }

          ncd3270DfltConnectionEntry OBJECT-TYPE
              SYNTAX  Ncd3270DfltConnectionEntry
              ACCESS  not-accessible
              STATUS  optional
			  DESCRIPTION ""
              ::= { ncd3270DfltConnectionTable 1 }

          Ncd3270DfltConnectionEntry ::=
              SEQUENCE {
                  ncd3270DCTIndex
                      INTEGER,
                  ncd3270DCTProtocol
                      INTEGER,
                  ncdTermDCTHost
                      OCTET STRING,
                  ncdTermDCTPort
                      OCTET STRING,
                  ncd3270DCTModel
                      INTEGER,
                  ncdTermDCTDescription
                      OCTET STRING
              }

          ncd3270DCTIndex OBJECT-TYPE
              SYNTAX  INTEGER
              ACCESS  read-only
              STATUS  optional
			  DESCRIPTION ""
              ::= { ncd3270DfltConnectionEntry 1 }

          ncd3270DCTProtocol OBJECT-TYPE
              SYNTAX  INTEGER
              ACCESS  read-write
              STATUS  optional
			  DESCRIPTION ""
              ::= { ncd3270DfltConnectionEntry 2 }

          ncdTermDCTHost OBJECT-TYPE
              SYNTAX  OCTET STRING
              ACCESS  read-write
              STATUS  optional
			  DESCRIPTION ""
              ::= { ncd3270DfltConnectionEntry 3 }

          ncdTermDCTPort OBJECT-TYPE
              SYNTAX  OCTET STRING
              ACCESS  read-write
              STATUS  optional
			  DESCRIPTION ""
              ::= { ncd3270DfltConnectionEntry 4 }

          ncd3270DCTModel OBJECT-TYPE
              SYNTAX  INTEGER
              ACCESS  read-write
              STATUS  optional
			  DESCRIPTION ""
              ::= { ncd3270DfltConnectionEntry 5 }

          ncdTermDCTDescription OBJECT-TYPE
              SYNTAX  OCTET STRING
              ACCESS  read-write
              STATUS  optional
			  DESCRIPTION ""
              ::= { ncd3270DfltConnectionEntry 6 }

          ncd3270Enable3270Emulation OBJECT-TYPE
              SYNTAX  INTEGER
              ACCESS  read-write
              STATUS  optional
			  DESCRIPTION ""
              ::= { ncd3270 2 }


          -- the ncdParallel Group

          ncdParallelDTable OBJECT-TYPE
              SYNTAX  SEQUENCE OF NcdParallelDEntry
              ACCESS  not-accessible
              STATUS  optional
			  DESCRIPTION ""
              ::= { ncdParallel 1 }

          ncdParallelDEntry OBJECT-TYPE
              SYNTAX  NcdParallelDEntry
              ACCESS  not-accessible
              STATUS  optional
			  DESCRIPTION ""
              ::= { ncdParallelDTable 1 }

          NcdParallelDEntry ::=
              SEQUENCE {
                  ncdParallelDTableIndex
                      INTEGER,
                  ncdParallelDTablePortNumber
                      INTEGER,
                  ncdParallelDTableUseParaProt
                      INTEGER,
                  ncdParallelDTableTCPPort
                      INTEGER,
                  ncdParallelDTableNCDnetObjName
                      OCTET STRING,
                  ncdParallelDTableEnableLAT
                      INTEGER,
                  ncdParallelDTableLATServName
                      OCTET STRING,
                  ncdParallelDTableLATServRating
                      INTEGER
              }

          ncdParallelDTableIndex OBJECT-TYPE
              SYNTAX  INTEGER
              ACCESS  read-only
              STATUS  optional
			  DESCRIPTION ""
              ::= { ncdParallelDEntry 1 }

          ncdParallelDTablePortNumber OBJECT-TYPE
              SYNTAX  INTEGER
              ACCESS  read-only
              STATUS  optional
			  DESCRIPTION ""
              ::= { ncdParallelDEntry 2 }

          ncdParallelDTableUseParaProt OBJECT-TYPE
              SYNTAX  INTEGER
              ACCESS  read-write
              STATUS  optional
			  DESCRIPTION ""
              ::= { ncdParallelDEntry 3 }

          ncdParallelDTableTCPPort OBJECT-TYPE
              SYNTAX  INTEGER
              ACCESS  read-write
              STATUS  optional
			  DESCRIPTION ""
              ::= { ncdParallelDEntry 4 }

          ncdParallelDTableNCDnetObjName OBJECT-TYPE
              SYNTAX  OCTET STRING
              ACCESS  read-write
              STATUS  optional
			  DESCRIPTION ""
              ::= { ncdParallelDEntry 5 }

          ncdParallelDTableEnableLAT OBJECT-TYPE
              SYNTAX  INTEGER
              ACCESS  read-write
              STATUS  optional
			  DESCRIPTION ""
              ::= { ncdParallelDEntry 6 }

          ncdParallelDTableLATServName OBJECT-TYPE
              SYNTAX  OCTET STRING
              ACCESS  read-write
              STATUS  optional
			  DESCRIPTION ""
              ::= { ncdParallelDEntry 7 }

          ncdParallelDTableLATServRating OBJECT-TYPE
              SYNTAX  INTEGER
              ACCESS  read-write
              STATUS  optional
			  DESCRIPTION ""
              ::= { ncdParallelDEntry 8 }

          ncdParallelDStatsTbl OBJECT-TYPE
              SYNTAX  SEQUENCE OF NcdParallelDStatsEntryrvRating
              ACCESS  not-accessible
              STATUS  optional
			  DESCRIPTION ""
              ::= { ncdParallel 2 }

          ncdParallelDStatsEntryrvRating OBJECT-TYPE
              SYNTAX  NcdParallelDStatsEntryrvRating
              ACCESS  not-accessible
              STATUS  optional
			  DESCRIPTION ""
              ::= { ncdParallelDStatsTbl 1 }

          NcdParallelDStatsEntryrvRating ::=
              SEQUENCE {
                  ncdParallelDStatsTblPortNumber
                      INTEGER,
                  ncdParallelDStatsTblConnAccepts
                      INTEGER,
                  ncdParallelDStatsTblConnBadAccesses
                      INTEGER,
                  ncdParallelDStatsTblConnIOErrors
                      INTEGER,
                  ncdParallelDStatsTblConnEofCloses
                      INTEGER
              }

          ncdParallelDStatsTblPortNumber OBJECT-TYPE
              SYNTAX  INTEGER
              ACCESS  read-only
              STATUS  optional
			  DESCRIPTION ""
              ::= { ncdParallelDStatsEntryrvRating 1 }

          ncdParallelDStatsTblConnAccepts OBJECT-TYPE
              SYNTAX  INTEGER
              ACCESS  read-only
              STATUS  optional
			  DESCRIPTION ""
              ::= { ncdParallelDStatsEntryrvRating 2 }

          ncdParallelDStatsTblConnBadAccesses OBJECT-TYPE
              SYNTAX  INTEGER
              ACCESS  read-only
              STATUS  optional
			  DESCRIPTION ""
              ::= { ncdParallelDStatsEntryrvRating 3 }

          ncdParallelDStatsTblConnIOErrors OBJECT-TYPE
              SYNTAX  INTEGER
              ACCESS  read-only
              STATUS  optional
			  DESCRIPTION ""
              ::= { ncdParallelDStatsEntryrvRating 4 }

          ncdParallelDStatsTblConnEofCloses OBJECT-TYPE
              SYNTAX  INTEGER
              ACCESS  read-only
              STATUS  optional
			  DESCRIPTION ""
              ::= { ncdParallelDStatsEntryrvRating 5 }

          END
