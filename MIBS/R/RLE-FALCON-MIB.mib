--  Title:    FALCON20.MIB
--  Version:  v3.3
--  Date:     10/19/99 08:23am
--
--  Copyright @ 1998 RLE Technologies.  All rights reserved worldwide.
--
--  This MIB defines objects for the RLE Falcon SNMP Agent.
--

RLE-FALCON-MIB DEFINITIONS ::= BEGIN

IMPORTS
	TruthValue, PositiveInteger
		FROM RFC1253-MIB
	DisplayString
		FROM RFC1213-MIB
	OBJECT-TYPE
		FROM RFC-1212
	Counter, enterprises
		FROM RFC1155-SMI
		OBJECT-IDENTITY, Gauge32 FROM SNMPv2-SMI
		TRAP-TYPE FROM RFC-1215;

rle OBJECT IDENTIFIER ::= { enterprises  3184 }

products   OBJECT IDENTIFIER ::= { rle  1 }

falcon   OBJECT IDENTIFIER ::= { products  1 }

falconMIB OBJECT IDENTIFIER ::= { falcon 1 }

falconIdent OBJECT IDENTIFIER ::= { falconMIB 1 }

falconIdentManufacturer OBJECT-TYPE
    SYNTAX  DisplayString
    ACCESS  read-only
    STATUS  mandatory
    DESCRIPTION
           "The Monitor Control Unit manufacturer."
    ::= { falconIdent  1 }

falconIdentModel OBJECT-TYPE
    SYNTAX  DisplayString
    ACCESS  read-only
    STATUS  mandatory
    DESCRIPTION
           "The Monitor Control Unit Model designation."
    ::= { falconIdent  2 }

falconIdentSoftwareVersion OBJECT-TYPE
    SYNTAX  DisplayString
    ACCESS  read-only
    STATUS  mandatory
    DESCRIPTION
           "The falcon SNMP Agent software version."
    ::= { falconIdent  3 }

falconIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { falconIdent  4 }

falconSystem OBJECT IDENTIFIER ::= { falconMIB 2 }

falconClock OBJECT-TYPE
    SYNTAX  DisplayString
    ACCESS  read-write
    STATUS  mandatory
    DESCRIPTION
           "The falcon internal clock settings.
            Displayed as MM/DD/YY HH:MM:SS"
    ::= { falconSystem  1 }

falconDoorAlarmBypass OBJECT-TYPE
    SYNTAX  INTEGER (-2147483648..2147483647)
    ACCESS  read-write
    STATUS  mandatory
    DESCRIPTION
           "The falcon door alarm bypass switch.
            This allows the alarm to be bypassed upon valid keypad access.
            Zero disables this, or use 1 thru 8 for the corresponding
            falcon input."
    ::= { falconSystem  2 }

falconKeypad OBJECT IDENTIFIER ::= { falconSystem 3 }

falconKeypadCode1 OBJECT-TYPE
    SYNTAX  DisplayString
    ACCESS  read-write
    STATUS  mandatory
    DESCRIPTION
           "The falcon keypad access code for user #1.
            This can be up to six numberic characters."
    ::= { falconKeypad  1 }

falconKeypadName1 OBJECT-TYPE
    SYNTAX  DisplayString
    ACCESS  read-write
    STATUS  mandatory
    DESCRIPTION
           "The falcon keypad access name for user #1.
            This can be up to 20 characters."
    ::= { falconKeypad  2 }

falconKeypadCode2 OBJECT-TYPE
    SYNTAX  DisplayString
    ACCESS  read-write
    STATUS  mandatory
    DESCRIPTION
           "The falcon keypad access code for user #2.
            This can be up to six numberic characters."
    ::= { falconKeypad  3 }

falconKeypadName2 OBJECT-TYPE
    SYNTAX  DisplayString
    ACCESS  read-write
    STATUS  mandatory
    DESCRIPTION
           "The falcon keypad access name for user #2.
            This can be up to 20 characters."
    ::= { falconKeypad  4 }

falconKeypadCode3 OBJECT-TYPE
    SYNTAX  DisplayString
    ACCESS  read-write
    STATUS  mandatory
    DESCRIPTION
           "The falcon keypad access code for user #3.
            This can be up to six numberic characters."
    ::= { falconKeypad  5 }

falconKeypadName3 OBJECT-TYPE
    SYNTAX  DisplayString
    ACCESS  read-write
    STATUS  mandatory
    DESCRIPTION
           "The falcon keypad access name for user #3.
            This can be up to 20 characters."
    ::= { falconKeypad  6 }

falconKeypadCode4 OBJECT-TYPE
    SYNTAX  DisplayString
    ACCESS  read-write
    STATUS  mandatory
    DESCRIPTION
           "The falcon keypad access code for user #4.
            This can be up to six numberic characters."
    ::= { falconKeypad  7 }

falconKeypadName4 OBJECT-TYPE
    SYNTAX  DisplayString
    ACCESS  read-write
    STATUS  mandatory
    DESCRIPTION
           "The falcon keypad access name for user #4.
            This can be up to 20 characters."
    ::= { falconKeypad  8 }

falconKeypadCode5 OBJECT-TYPE
    SYNTAX  DisplayString
    ACCESS  read-write
    STATUS  mandatory
    DESCRIPTION
           "The falcon keypad access code for user #5.
            This can be up to six numberic characters."
    ::= { falconKeypad  9 }

falconKeypadName5 OBJECT-TYPE
    SYNTAX  DisplayString
    ACCESS  read-write
    STATUS  mandatory
    DESCRIPTION
           "The falcon keypad access name for user #5.
            This can be up to 20 characters."
    ::= { falconKeypad  10 }

falconKeypadCode6 OBJECT-TYPE
    SYNTAX  DisplayString
    ACCESS  read-write
    STATUS  mandatory
    DESCRIPTION
           "The falcon keypad access code for user #6.
            This can be up to six numberic characters."
    ::= { falconKeypad  11 }

falconKeypadName6 OBJECT-TYPE
    SYNTAX  DisplayString
    ACCESS  read-write
    STATUS  mandatory
    DESCRIPTION
           "The falcon keypad access name for user #6.
            This can be up to 20 characters."
    ::= { falconKeypad  12 }

falconKeypadCode7 OBJECT-TYPE
    SYNTAX  DisplayString
    ACCESS  read-write
    STATUS  mandatory
    DESCRIPTION
           "The falcon keypad access code for user #7.
            This can be up to six numberic characters."
    ::= { falconKeypad  13 }

falconKeypadName7 OBJECT-TYPE
    SYNTAX  DisplayString
    ACCESS  read-write
    STATUS  mandatory
    DESCRIPTION
           "The falcon keypad access name for user #7.
            This can be up to 20 characters."
    ::= { falconKeypad  14 }

falconKeypadCode8 OBJECT-TYPE
    SYNTAX  DisplayString
    ACCESS  read-write
    STATUS  mandatory
    DESCRIPTION
           "The falcon keypad access code for user #8.
            This can be up to six numberic characters."
    ::= { falconKeypad  15 }

falconKeypadName8 OBJECT-TYPE
    SYNTAX  DisplayString
    ACCESS  read-write
    STATUS  mandatory
    DESCRIPTION
           "The falcon keypad access name for user #8.
            This can be up to 20 characters."
    ::= { falconKeypad  16 }

falconKeypadCode9 OBJECT-TYPE
    SYNTAX  DisplayString
    ACCESS  read-write
    STATUS  mandatory
    DESCRIPTION
           "The falcon keypad access code for user #9.
            This can be up to six numberic characters."
    ::= { falconKeypad  17 }

falconKeypadName9 OBJECT-TYPE
    SYNTAX  DisplayString
    ACCESS  read-write
    STATUS  mandatory
    DESCRIPTION
           "The falcon keypad access name for user #9.
            This can be up to 20 characters."
    ::= { falconKeypad  18 }

falconKeypadCode10 OBJECT-TYPE
    SYNTAX  DisplayString
    ACCESS  read-write
    STATUS  mandatory
    DESCRIPTION
           "The falcon keypad access code for user #10.
            This can be up to six numberic characters."
    ::= { falconKeypad  19 }

falconKeypadName10 OBJECT-TYPE
    SYNTAX  DisplayString
    ACCESS  read-write
    STATUS  mandatory
    DESCRIPTION
           "The falcon keypad access name for user #10.
            This can be up to 20 characters."
    ::= { falconKeypad  20 }

falconKeypadCode11 OBJECT-TYPE
    SYNTAX  DisplayString
    ACCESS  read-write
    STATUS  mandatory
    DESCRIPTION
           "The falcon keypad access code for user #11.
            This can be up to six numberic characters."
    ::= { falconKeypad  21 }

falconKeypadName11 OBJECT-TYPE
    SYNTAX  DisplayString
    ACCESS  read-write
    STATUS  mandatory
    DESCRIPTION
           "The falcon keypad access name for user #11.
            This can be up to 20 characters."
    ::= { falconKeypad  22 }

falconKeypadCode12 OBJECT-TYPE
    SYNTAX  DisplayString
    ACCESS  read-write
    STATUS  mandatory
    DESCRIPTION
           "The falcon keypad access code for user #12.
            This can be up to six numberic characters."
    ::= { falconKeypad  23 }

falconKeypadName12 OBJECT-TYPE
    SYNTAX  DisplayString
    ACCESS  read-write
    STATUS  mandatory
    DESCRIPTION
           "The falcon keypad access name for user #12.
            This can be up to 20 characters."
    ::= { falconKeypad  24 }

falconKeypadCode13 OBJECT-TYPE
    SYNTAX  DisplayString
    ACCESS  read-write
    STATUS  mandatory
    DESCRIPTION
           "The falcon keypad access code for user #13.
            This can be up to six numberic characters."
    ::= { falconKeypad  25 }

falconKeypadName13 OBJECT-TYPE
    SYNTAX  DisplayString
    ACCESS  read-write
    STATUS  mandatory
    DESCRIPTION
           "The falcon keypad access name for user #13.
            This can be up to 20 characters."
    ::= { falconKeypad  26 }

falconKeypadCode14 OBJECT-TYPE
    SYNTAX  DisplayString
    ACCESS  read-write
    STATUS  mandatory
    DESCRIPTION
           "The falcon keypad access code for user #14.
            This can be up to six numberic characters."
    ::= { falconKeypad  27 }

falconKeypadName14 OBJECT-TYPE
    SYNTAX  DisplayString
    ACCESS  read-write
    STATUS  mandatory
    DESCRIPTION
           "The falcon keypad access name for user #14.
            This can be up to 20 characters."
    ::= { falconKeypad  28 }

falconKeypadCode15 OBJECT-TYPE
    SYNTAX  DisplayString
    ACCESS  read-write
    STATUS  mandatory
    DESCRIPTION
           "The falcon keypad access code for user #15.
            This can be up to six numberic characters."
    ::= { falconKeypad  29 }

falconKeypadName15 OBJECT-TYPE
    SYNTAX  DisplayString
    ACCESS  read-write
    STATUS  mandatory
    DESCRIPTION
           "The falcon keypad access name for user #15.
            This can be up to 20 characters."
    ::= { falconKeypad  30 }

falconKeypadCode16 OBJECT-TYPE
    SYNTAX  DisplayString
    ACCESS  read-write
    STATUS  mandatory
    DESCRIPTION
           "The falcon keypad access code for user #16.
            This can be up to six numberic characters."
    ::= { falconKeypad  31 }

falconKeypadName16 OBJECT-TYPE
    SYNTAX  DisplayString
    ACCESS  read-write
    STATUS  mandatory
    DESCRIPTION
           "The falcon keypad access name for user #16.
            This can be up to 20 characters."
    ::= { falconKeypad  32 }

falconKeypadCode17 OBJECT-TYPE
    SYNTAX  DisplayString
    ACCESS  read-write
    STATUS  mandatory
    DESCRIPTION
           "The falcon keypad access code for user #17.
            This can be up to six numberic characters."
    ::= { falconKeypad  33 }

falconKeypadName17 OBJECT-TYPE
    SYNTAX  DisplayString
    ACCESS  read-write
    STATUS  mandatory
    DESCRIPTION
           "The falcon keypad access name for user #17.
            This can be up to 20 characters."
    ::= { falconKeypad  34 }

falconKeypadCode18 OBJECT-TYPE
    SYNTAX  DisplayString
    ACCESS  read-write
    STATUS  mandatory
    DESCRIPTION
           "The falcon keypad access code for user #18.
            This can be up to six numberic characters."
    ::= { falconKeypad  35 }

falconKeypadName18 OBJECT-TYPE
    SYNTAX  DisplayString
    ACCESS  read-write
    STATUS  mandatory
    DESCRIPTION
           "The falcon keypad access name for user #18.
            This can be up to 20 characters."
    ::= { falconKeypad  36 }

falconKeypadCode19 OBJECT-TYPE
    SYNTAX  DisplayString
    ACCESS  read-write
    STATUS  mandatory
    DESCRIPTION
           "The falcon keypad access code for user #19.
            This can be up to six numberic characters."
    ::= { falconKeypad  37 }

falconKeypadName19 OBJECT-TYPE
    SYNTAX  DisplayString
    ACCESS  read-write
    STATUS  mandatory
    DESCRIPTION
           "The falcon keypad access name for user #19.
            This can be up to 20 characters."
    ::= { falconKeypad  38 }

falconKeypadCode20 OBJECT-TYPE
    SYNTAX  DisplayString
    ACCESS  read-write
    STATUS  mandatory
    DESCRIPTION
           "The falcon keypad access code for user #20.
            This can be up to six numberic characters."
    ::= { falconKeypad  39 }

falconKeypadName20 OBJECT-TYPE
    SYNTAX  DisplayString
    ACCESS  read-write
    STATUS  mandatory
    DESCRIPTION
           "The falcon keypad access name for user #20.
            This can be up to 20 characters."
    ::= { falconKeypad  40 }

falconInputVoltage OBJECT-TYPE
    SYNTAX  INTEGER (-2147483648..2147483647)
    ACCESS  read-only
    STATUS  mandatory
    DESCRIPTION
           "The falcon input voltage (DC Power)."
    ::= { falconSystem  4 }

falconOnBattery OBJECT-TYPE
    SYNTAX  INTEGER {
    notInstalled(0),
    installed(1)
}
    ACCESS  read-write
    STATUS  mandatory
    DESCRIPTION
           "The state of use of the On Battery Alarm. When
            the State is set to installed(1), the On Battery and
            Low Battery alarms are enabled.
            This variable is stored in non-volatile memory."
    ::= { falconSystem  5 }

falconLowBatteryThreshold OBJECT-TYPE
    SYNTAX  INTEGER (-2147483648..2147483647)
    ACCESS  read-write
    STATUS  mandatory
    DESCRIPTION
           "The low voltage trip point for the low battery alarm.
            When the input voltage goes below this voltage, the
            Low Battery alarm is set.
            This variable is stored in non-volatile memory."
    ::= { falconSystem  6 }

falconAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds.
            This variable is stored in non-volatile memory."
    ::= { falconSystem  7 }

falconInputs OBJECT IDENTIFIER ::= { falconMIB  3 }

falconInput1 OBJECT IDENTIFIER ::= { falconInputs 1 }

falconInput1State OBJECT-TYPE
    SYNTAX  INTEGER {
    notinstalled(1),
    analog-4to20-installed(2),
    digital-no-installed(3),
    digital-nc-installed(4)
}
    ACCESS  read-write
    STATUS  mandatory
    DESCRIPTION
           "The state of use of Input Number 1. When a sensor is
            connected to Input 1 set State to installed(2) to
            indicate that the value of falconReading1 is valid.
            When no sensor is connected to Input 1 set
            State to notInstalled(1) to indicate that the value of
            falconReading1 may not be valid.
            This variable is stored in non-volatile memory."
    ::= { falconInput1  1 }

falconInput1Reading OBJECT-TYPE
    SYNTAX  INTEGER (-2147483648..2147483647)
    ACCESS  read-only
    STATUS  mandatory
    DESCRIPTION
           "The reading for sensor 1.
            If the input is digital, the reading will be 1 (active) or
            0 (inactive)"
    ::= { falconInput1  2 }

falconInput1Gain OBJECT-TYPE
    SYNTAX  INTEGER (-2147483648..2147483647)
    ACCESS  read-write
    STATUS  mandatory
    DESCRIPTION
           "A correction gain associated with the sensor variable.
            The value of gain is multiplied by the value from
            Input Sensor Number 1 to obtain the value of
            the Input1 variable. The gain variable is stored in
            non-volatile memory."
    ::= { falconInput1  3 }

falconInput1Offset OBJECT-TYPE
    SYNTAX  INTEGER (-2147483648..2147483647)
    ACCESS  read-write
    STATUS  mandatory
    DESCRIPTION
           "A correction Offset associated with the sensor variable.
            The value of Offset is added to the value from
            Input Sensor Number 1 to obtain the value of
            the Input1 variable. The Offset variable is stored in
            non-volatile memory."
    ::= { falconInput1  4 }

falconInput1Label OBJECT-TYPE
    SYNTAX  DisplayString
    ACCESS  read-write
    STATUS  mandatory
    DESCRIPTION
           "A user-defined text string associated with Input Number 1.
            The text string is stored in non-volatile memory."
    ::= { falconInput1  5 }

falconInput1UOM OBJECT-TYPE
    SYNTAX  DisplayString
    ACCESS  read-write
    STATUS  mandatory
    DESCRIPTION
           "A user-defined text string associated with Input Number 1.
            The text string is stored in non-volatile memory."
    ::= { falconInput1  6 }

falconInput1HighLimit2 OBJECT-TYPE
    SYNTAX  INTEGER (-2147483648..2147483647)
    ACCESS  read-write
    STATUS  mandatory
    DESCRIPTION
           "When input 1 reaches or exceeds this value a trap will
            be generated signifying a high alarm condition at
            sensor 1.
            The HighLimit2 variable is stored in non-volatile memory."
    ::= { falconInput1  7 }

falconInput1HighLimit OBJECT-TYPE
    SYNTAX  INTEGER (-2147483648..2147483647)
    ACCESS  read-write
    STATUS  mandatory
    DESCRIPTION
           "When input 1 reaches or exceeds this value a trap will
            be generated signifying a high alarm condition at
            sensor 1.
            The HighLimit variable is stored in non-volatile memory."
    ::= { falconInput1  8 }

falconInput1LowLimit OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconInput1  9 }

falconInput1LowLimit2 OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { falconInput1  10 }

falconInput1RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput1  11 }

falconInput1Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput1  12 }

falconInput1Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput1  13 }

falconInput2 OBJECT IDENTIFIER ::= { falconInputs 2 }

falconInput2State OBJECT-TYPE
    SYNTAX  INTEGER {
    notinstalled(1),
    analog-4to20-installed(2),
    digital-no-installed(3),
    digital-nc-installed(4)
}
    ACCESS  read-write
    STATUS  mandatory
    DESCRIPTION
           "The state of use of Input Number 2. When a sensor is
            connected to Input 2 set State to installed(2) to
            indicate that the value of falconReading2 is valid.
            When no sensor is connected to Input 2 set
            State to notInstalled(1) to indicate that the value of
            falconReading2 may not be valid.
            This variable is stored in non-volatile memory."
    ::= { falconInput2  1 }

falconInput2Reading OBJECT-TYPE
    SYNTAX  INTEGER (-2147483648..2147483647)
    ACCESS  read-only
    STATUS  mandatory
    DESCRIPTION
           "The reading for sensor 2.
            If the input is digital, the reading will be 1 (active) or
            0 (inactive)"
    ::= { falconInput2  2 }

falconInput2Gain OBJECT-TYPE
    SYNTAX  INTEGER (-2147483648..2147483647)
    ACCESS  read-write
    STATUS  mandatory
    DESCRIPTION
           "A correction gain associated with the sensor variable.
            The value of gain is multiplied by the value from
            Input Sensor Number 2 to obtain the value of
            the Input2 variable. The gain variable is stored in
            non-volatile memory."
    ::= { falconInput2  3 }

falconInput2Offset OBJECT-TYPE
    SYNTAX  INTEGER (-2147483648..2147483647)
    ACCESS  read-write
    STATUS  mandatory
    DESCRIPTION
           "A correction Offset associated with the sensor variable.
            The value of Offset is added to the value from
            Input Sensor Number 2 to obtain the value of
            the Input2 variable. The Offset variable is stored in
            non-volatile memory."
    ::= { falconInput2  4 }

falconInput2Label OBJECT-TYPE
    SYNTAX  DisplayString
    ACCESS  read-write
    STATUS  mandatory
    DESCRIPTION
           "A user-defined text string associated with Input Number 2.
            The text string is stored in non-volatile memory."
    ::= { falconInput2  5 }

falconInput2UOM OBJECT-TYPE
    SYNTAX  DisplayString
    ACCESS  read-write
    STATUS  mandatory
    DESCRIPTION
           "A user-defined text string associated with Input Number 2.
            The text string is stored in non-volatile memory."
    ::= { falconInput2  6 }

falconInput2HighLimit2 OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconInput2  7 }

falconInput2HighLimit OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { falconInput2  8 }

falconInput2LowLimit OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconInput2  9 }

falconInput2LowLimit2 OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { falconInput2  10 }

falconInput2RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput2  11 }

falconInput2Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput2  12 }

falconInput2Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput2  13 }

falconInput3 OBJECT IDENTIFIER ::= { falconInputs 3 }

falconInput3State OBJECT-TYPE
    SYNTAX  INTEGER {
    notInstalled(1),
    analog-4to20-installed(2),
    digital-no-installed(3),
    digital-nc-installed(4)
}
    ACCESS  read-write
    STATUS  mandatory
    DESCRIPTION
           "The state of use of Input Number 3. When a sensor is
            connected to Input 3 set State to installed(2) to
            indicate that the value of falconReading3 is valid.
            When no sensor is connected to Input 3 set
            State to notInstalled(1) to indicate that the value of
            falconReading3 may not be valid.
            This variable is stored in non-volatile memory."
    ::= { falconInput3  1 }

falconInput3Reading OBJECT-TYPE
    SYNTAX  INTEGER (-2147483648..2147483647)
    ACCESS  read-only
    STATUS  mandatory
    DESCRIPTION
           "The reading for sensor 3.
            If the input is digital, the reading will be 1 (active) or
            0 (inactive)"
    ::= { falconInput3  2 }

falconInput3Gain OBJECT-TYPE
    SYNTAX  INTEGER (-2147483648..2147483647)
    ACCESS  read-write
    STATUS  mandatory
    DESCRIPTION
           "A correction gain associated with the sensor variable.
            The value of gain is multiplied by the value from
            Input Sensor Number 3 to obtain the value of
            the Input3 variable. The gain variable is stored in
            non-volatile memory."
    ::= { falconInput3  3 }

falconInput3Offset OBJECT-TYPE
    SYNTAX  INTEGER (-2147483648..2147483647)
    ACCESS  read-write
    STATUS  mandatory
    DESCRIPTION
           "A correction Offset associated with the sensor variable.
            The value of Offset is added to the value from
            Input Sensor Number 3 to obtain the value of
            the Input3 variable. The Offset variable is stored in
            non-volatile memory."
    ::= { falconInput3  4 }

falconInput3Label OBJECT-TYPE
    SYNTAX  DisplayString
    ACCESS  read-write
    STATUS  mandatory
    DESCRIPTION
           "A user-defined text string associated with Input Number 3.
            The text string is stored in non-volatile memory."
    ::= { falconInput3  5 }

falconInput3UOM OBJECT-TYPE
    SYNTAX  DisplayString
    ACCESS  read-write
    STATUS  mandatory
    DESCRIPTION
           "A user-defined text string associated with Input Number 3.
            The text string is stored in non-volatile memory."
    ::= { falconInput3  6 }

falconInput3HighLimit2 OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconInput3  7 }

falconInput3HighLimit OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { falconInput3  8 }

falconInput3LowLimit OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconInput3  9 }

falconInput3LowLimit2 OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { falconInput3  10 }

falconInput3RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput3  11 }

falconInput3Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput3  12 }

falconInput3Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput3  13 }

falconInput4 OBJECT IDENTIFIER ::= { falconInputs 4 }

falconInput4State OBJECT-TYPE
    SYNTAX  INTEGER {
    notInstalled(1),
    analog-4to20-installed(2),
    digital-no-installed(3),
    digital-nc-installed(4)
}
    ACCESS  read-write
    STATUS  mandatory
    DESCRIPTION
           "The state of use of Input Number 4. When a sensor is
            connected to Input 4 set State to installed(2) to
            indicate that the value of falconReading4 is valid.
            When no sensor is connected to Input 4 set
            State to notInstalled(1) to indicate that the value of
            falconReading4 may not be valid.
            This variable is stored in non-volatile memory."
    ::= { falconInput4  1 }

falconInput4Reading OBJECT-TYPE
    SYNTAX  INTEGER (-2147483648..2147483647)
    ACCESS  read-only
    STATUS  mandatory
    DESCRIPTION
           "The reading for sensor 4.
            If the input is digital, the reading will be 1 (active) or
            0 (inactive)"
    ::= { falconInput4  2 }

falconInput4Gain OBJECT-TYPE
    SYNTAX  INTEGER (-2147483648..2147483647)
    ACCESS  read-write
    STATUS  mandatory
    DESCRIPTION
           "A correction gain associated with the sensor variable.
            The value of gain is multiplied by the value from
            Input Sensor Number 4 to obtain the value of
            the Input4 variable. The gain variable is stored in
            non-volatile memory."
    ::= { falconInput4  3 }

falconInput4Offset OBJECT-TYPE
    SYNTAX  INTEGER (-2147483648..2147483647)
    ACCESS  read-write
    STATUS  mandatory
    DESCRIPTION
           "A correction Offset associated with the sensor variable.
            The value of Offset is added to the value from
            Input Sensor Number 4 to obtain the value of
            the Input4 variable. The Offset variable is stored in
            non-volatile memory."
    ::= { falconInput4  4 }

falconInput4Label OBJECT-TYPE
    SYNTAX  DisplayString
    ACCESS  read-write
    STATUS  mandatory
    DESCRIPTION
           "A user-defined text string associated with Input Number 4.
            The text string is stored in non-volatile memory."
    ::= { falconInput4  5 }

falconInput4UOM OBJECT-TYPE
    SYNTAX  DisplayString
    ACCESS  read-write
    STATUS  mandatory
    DESCRIPTION
           "A user-defined text string associated with Input Number 4.
            The text string is stored in non-volatile memory."
    ::= { falconInput4  6 }

falconInput4HighLimit2 OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconInput4  7 }

falconInput4HighLimit OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { falconInput4  8 }

falconInput4LowLimit OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconInput4  9 }

falconInput4LowLimit2 OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { falconInput4  10 }

falconInput4RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput4  11 }

falconInput4Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput4  12 }

falconInput4Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput4  13 }

falconInput5 OBJECT IDENTIFIER ::= { falconInputs 5 }

falconInput5State OBJECT-TYPE
    SYNTAX  INTEGER {
    notInstalled(1),
    analog-4to20-installed(2),
    digital-no-installed(3),
    digital-nc-installed(4)
}
    ACCESS  read-write
    STATUS  mandatory
    DESCRIPTION
           "The state of use of Input Number 5. When a sensor is
            connected to Input 5 set State to installed(2) to
            indicate that the value of falconReading4 is valid.
            When no sensor is connected to Input 5 set
            State to notInstalled(1) to indicate that the value of
            falconReading5 may not be valid.
            This variable is stored in non-volatile memory."
    ::= { falconInput5  1 }

falconInput5Reading OBJECT-TYPE
    SYNTAX  INTEGER (-2147483648..2147483647)
    ACCESS  read-only
    STATUS  mandatory
    DESCRIPTION
           "The reading for sensor 5.
            If the input is digital, the reading will be 1 (active) or
            0 (inactive)"
    ::= { falconInput5  2 }

falconInput5Gain OBJECT-TYPE
    SYNTAX  INTEGER (-2147483648..2147483647)
    ACCESS  read-write
    STATUS  mandatory
    DESCRIPTION
           "A correction gain associated with the sensor variable.
            The value of gain is multiplied by the value from
            Input Sensor Number 5 to obtain the value of
            the Input5 variable. The gain variable is stored in
            non-volatile memory."
    ::= { falconInput5  3 }

falconInput5Offset OBJECT-TYPE
    SYNTAX  INTEGER (-2147483648..2147483647)
    ACCESS  read-write
    STATUS  mandatory
    DESCRIPTION
           "A correction Offset associated with the sensor variable.
            The value of Offset is added to the value from
            Input Sensor Number 5 to obtain the value of
            the Input5 variable. The Offset variable is stored in
            non-volatile memory."
    ::= { falconInput5  4 }

falconInput5Label OBJECT-TYPE
    SYNTAX  DisplayString
    ACCESS  read-write
    STATUS  mandatory
    DESCRIPTION
           "A user-defined text string associated with Input Number 5.
            The text string is stored in non-volatile memory."
    ::= { falconInput5  5 }

falconInput5UOM OBJECT-TYPE
    SYNTAX  DisplayString
    ACCESS  read-write
    STATUS  mandatory
    DESCRIPTION
           "A user-defined text string associated with Input Number 5.
            The text string is stored in non-volatile memory."
    ::= { falconInput5  6 }

falconInput5HighLimit2 OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { falconInput5  7 }

falconInput5HighLimit OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { falconInput5  8 }

falconInput5LowLimit OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { falconInput5  9 }

falconInput5LowLimit2 OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { falconInput5  10 }

falconInput5RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput5  11 }

falconInput5Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput5  12 }

falconInput5Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput5  13 }

falconInput6 OBJECT IDENTIFIER ::= { falconInputs 6 }

falconInput6State OBJECT-TYPE
    SYNTAX  INTEGER {
    notInstalled(1),
    analog-4to20-installed(2),
    digital-no-installed(3),
    digital-nc-installed(4)
}
    ACCESS  read-write
    STATUS  mandatory
    DESCRIPTION
           "The state of use of Input Number 6. When a sensor is
            connected to Input 6 set State to installed(2) to
            indicate that the value of falconReading6 is valid.
            When no sensor is connected to Input 6 set
            State to notInstalled(1) to indicate that the value of
            falconReading6 may not be valid.
            This variable is stored in non-volatile memory."
    ::= { falconInput6  1 }

falconInput6Reading OBJECT-TYPE
    SYNTAX  INTEGER (-2147483648..2147483647)
    ACCESS  read-only
    STATUS  mandatory
    DESCRIPTION
           "The reading for sensor 6.
            If the input is digital, the reading will be 1 (active) or
            0 (inactive)"
    ::= { falconInput6  2 }

falconInput6Gain OBJECT-TYPE
    SYNTAX  INTEGER (-2147483648..2147483647)
    ACCESS  read-write
    STATUS  mandatory
    DESCRIPTION
           "A correction gain associated with the sensor variable.
            The value of gain is multiplied by the value from
            Input Sensor Number 6 to obtain the value of
            the Input6 variable. The gain variable is stored in
            non-volatile memory."
    ::= { falconInput6  3 }

falconInput6Offset OBJECT-TYPE
    SYNTAX  INTEGER (-2147483648..2147483647)
    ACCESS  read-write
    STATUS  mandatory
    DESCRIPTION
           "A correction Offset associated with the sensor variable.
            The value of Offset is added to the value from
            Input Sensor Number 6 to obtain the value of
            the Input6 variable. The Offset variable is stored in
            non-volatile memory."
    ::= { falconInput6  4 }

falconInput6Label OBJECT-TYPE
    SYNTAX  DisplayString
    ACCESS  read-write
    STATUS  mandatory
    DESCRIPTION
           "A user-defined text string associated with Input Number 6.
            The text string is stored in non-volatile memory."
    ::= { falconInput6  5 }

falconInput6UOM OBJECT-TYPE
    SYNTAX  DisplayString
    ACCESS  read-write
    STATUS  mandatory
    DESCRIPTION
           "A user-defined text string associated with Input Number 6.
            The text string is stored in non-volatile memory."
    ::= { falconInput6  6 }

falconInput6HighLimit2 OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { falconInput6  7 }

falconInput6HighLimit OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { falconInput6  8 }

falconInput6LowLimit OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { falconInput6  9 }

falconInput6LowLimit2 OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { falconInput6  10 }

falconInput6RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput6  11 }

falconInput6Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput6  12 }

falconInput6Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput6  13 }

falconInput7 OBJECT IDENTIFIER ::= { falconInputs 7 }

falconInput7State OBJECT-TYPE
    SYNTAX  INTEGER {
    notInstalled(1),
    analog-4to20-installed(2),
    digital-no-installed(3),
    digital-nc-installed(4)
}
    ACCESS  read-write
    STATUS  mandatory
    DESCRIPTION
           "The state of use of Input Number 7. When a sensor is
            connected to Input 7 set State to installed(2) to
            indicate that the value of falconReading4 is valid.
            When no sensor is connected to Input 7 set
            State to notInstalled(1) to indicate that the value of
            falconReading7 may not be valid.
            This variable is stored in non-volatile memory."
    ::= { falconInput7  1 }

falconInput7Reading OBJECT-TYPE
    SYNTAX  INTEGER (-2147483648..2147483647)
    ACCESS  read-only
    STATUS  mandatory
    DESCRIPTION
           "The reading for sensor 7.
            If the input is digital, the reading will be 1 (active) or
            0 (inactive)"
    ::= { falconInput7  2 }

falconInput7Gain OBJECT-TYPE
    SYNTAX  INTEGER (-2147483648..2147483647)
    ACCESS  read-write
    STATUS  mandatory
    DESCRIPTION
           "A correction gain associated with the sensor variable.
            The value of gain is multiplied by the value from
            Input Sensor Number 7 to obtain the value of
            the Input7 variable. The gain variable is stored in
            non-volatile memory."
    ::= { falconInput7  3 }

falconInput7Offset OBJECT-TYPE
    SYNTAX  INTEGER (-2147483648..2147483647)
    ACCESS  read-write
    STATUS  mandatory
    DESCRIPTION
           "A correction Offset associated with the sensor variable.
            The value of Offset is added to the value from
            Input Sensor Number 7 to obtain the value of
            the Input7 variable. The Offset variable is stored in
            non-volatile memory."
    ::= { falconInput7  4 }

falconInput7Label OBJECT-TYPE
    SYNTAX  DisplayString
    ACCESS  read-write
    STATUS  mandatory
    DESCRIPTION
           "A user-defined text string associated with Input Number 7.
            The text string is stored in non-volatile memory."
    ::= { falconInput7  5 }

falconInput7UOM OBJECT-TYPE
    SYNTAX  DisplayString
    ACCESS  read-write
    STATUS  mandatory
    DESCRIPTION
           "A user-defined text string associated with Input Number 7.
            The text string is stored in non-volatile memory."
    ::= { falconInput7  6 }

falconInput7HighLimit2 OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { falconInput7  7 }

falconInput7HighLimit OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { falconInput7  8 }

falconInput7LowLimit OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { falconInput7  9 }

falconInput7LowLimit2 OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { falconInput7  10 }

falconInput7RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput7  11 }

falconInput7Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput7  12 }

falconInput7Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput7  13 }

falconInput8 OBJECT IDENTIFIER ::= { falconInputs 8 }

falconInput8State OBJECT-TYPE
    SYNTAX  INTEGER {
    notInstalled(1),
    analog-4to20-installed(2),
    digital-no-installed(3),
    digital-nc-installed(4)
}
    ACCESS  read-write
    STATUS  mandatory
    DESCRIPTION
           "The state of use of Input Number 8. When a sensor is
            connected to Input 8 set State to installed(2) to
            indicate that the value of falconReading8 is valid.
            When no sensor is connected to Input 8 set
            State to notInstalled(1) to indicate that the value of
            falconReading8 may not be valid.
            This variable is stored in non-volatile memory."
    ::= { falconInput8  1 }

falconInput8Reading OBJECT-TYPE
    SYNTAX  INTEGER (-2147483648..2147483647)
    ACCESS  read-only
    STATUS  mandatory
    DESCRIPTION
           "The reading for sensor 8.
            If the input is digital, the reading will be 1 (active) or
            0 (inactive)"
    ::= { falconInput8  2 }

falconInput8Gain OBJECT-TYPE
    SYNTAX  INTEGER (-2147483648..2147483647)
    ACCESS  read-write
    STATUS  mandatory
    DESCRIPTION
           "A correction gain associated with the sensor variable.
            The value of gain is multiplied by the value from
            Input Sensor Number 8 to obtain the value of
            the Input8 variable. The gain variable is stored in
            non-volatile memory."
    ::= { falconInput8  3 }

falconInput8Offset OBJECT-TYPE
    SYNTAX  INTEGER (-2147483648..2147483647)
    ACCESS  read-write
    STATUS  mandatory
    DESCRIPTION
           "A correction Offset associated with the sensor variable.
            The value of Offset is added to the value from
            Input Sensor Number 8 to obtain the value of
            the Input8 variable. The Offset variable is stored in
            non-volatile memory."
    ::= { falconInput8  4 }

falconInput8Label OBJECT-TYPE
    SYNTAX  DisplayString
    ACCESS  read-write
    STATUS  mandatory
    DESCRIPTION
           "A user-defined text string associated with Input Number 8.
            The text string is stored in non-volatile memory."
    ::= { falconInput8  5 }

falconInput8UOM OBJECT-TYPE
    SYNTAX  DisplayString
    ACCESS  read-write
    STATUS  mandatory
    DESCRIPTION
           "A user-defined text string associated with Input Number 8.
            The text string is stored in non-volatile memory."
    ::= { falconInput8  6 }

falconInput8HighLimit2 OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { falconInput8  7 }

falconInput8HighLimit OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { falconInput8  8 }

falconInput8LowLimit OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { falconInput8  9 }

falconInput8LowLimit2 OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { falconInput8  10 }

falconInput8RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput8  9 }

falconInput8Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput8  10 }

falconInput8Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { falconInput8  11 }

falconInput9 OBJECT IDENTIFIER ::= { falconInputs 25 }

falconInput9State OBJECT-TYPE
    SYNTAX  INTEGER {
    notInstalled(1),
    digital-no-installed(3),
    digital-nc-installed(4)
}
    ACCESS  read-write
    STATUS  mandatory
    DESCRIPTION
           "The state of use of Input Number 9.
            This variable is stored in non-volatile memory."
    ::= { falconInput9  1 }

falconInput9Reading OBJECT-TYPE
    SYNTAX  INTEGER (0..1)
    ACCESS  read-only
    STATUS  mandatory
    DESCRIPTION
           "The reading for input 9.
            The reading will be 1 (active) or 0 (inactive)"
    ::= { falconInput9  2 }

falconInput9Label OBJECT-TYPE
    SYNTAX  DisplayString
    ACCESS  read-write
    STATUS  mandatory
    DESCRIPTION
           "A user-defined text string associated with Input Number 9.
            The text string is stored in non-volatile memory."
    ::= { falconInput9  3 }

falconInput9RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput9  4 }

falconInput9Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput9  5 }

falconInput10 OBJECT IDENTIFIER ::= { falconInputs 26 }

falconInput10State OBJECT-TYPE
    SYNTAX  INTEGER {
    notInstalled(1),
    digital-no-installed(3),
    digital-nc-installed(4)
}
    ACCESS  read-write
    STATUS  mandatory
    DESCRIPTION
           "The state of use of Input Number 10.
            This variable is stored in non-volatile memory."
    ::= { falconInput10  1 }

falconInput10Reading OBJECT-TYPE
    SYNTAX  INTEGER (0..1)
    ACCESS  read-only
    STATUS  mandatory
    DESCRIPTION
           "The reading for input 10.
            The reading will be 1 (active) or 0 (inactive)"
    ::= { falconInput10  2 }

falconInput10Label OBJECT-TYPE
    SYNTAX  DisplayString
    ACCESS  read-write
    STATUS  mandatory
    DESCRIPTION
           "A user-defined text string associated with Input Number 10.
            The text string is stored in non-volatile memory."
    ::= { falconInput10  3 }

falconInput10RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput10  4 }

falconInput10Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput10  5 }

falconInput11 OBJECT IDENTIFIER ::= { falconInputs 27 }

falconInput11State OBJECT-TYPE
    SYNTAX  INTEGER {
    notInstalled(1),
    digital-no-installed(3),
    digital-nc-installed(4)
}
    ACCESS  read-write
    STATUS  mandatory
    DESCRIPTION
           "The state of use of Input Number 11.
            This variable is stored in non-volatile memory."
    ::= { falconInput11  1 }

falconInput11Reading OBJECT-TYPE
    SYNTAX  INTEGER (0..1)
    ACCESS  read-only
    STATUS  mandatory
    DESCRIPTION
           "The reading for input 11.
            The reading will be 1 (active) or 0 (inactive)"
    ::= { falconInput11  2 }

falconInput11Label OBJECT-TYPE
    SYNTAX  DisplayString
    ACCESS  read-write
    STATUS  mandatory
    DESCRIPTION
           "A user-defined text string associated with Input Number 11.
            The text string is stored in non-volatile memory."
    ::= { falconInput11  3 }

falconInput11RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput11  4 }

falconInput11Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput11  5 }

falconInput12 OBJECT IDENTIFIER ::= { falconInputs 28 }

falconInput12State OBJECT-TYPE
    SYNTAX  INTEGER {
    notInstalled(1),
    digital-no-installed(3),
    digital-nc-installed(4)
}
    ACCESS  read-write
    STATUS  mandatory
    DESCRIPTION
           "The state of use of Input Number 12.
            This variable is stored in non-volatile memory."
    ::= { falconInput12  1 }

falconInput12Reading OBJECT-TYPE
    SYNTAX  INTEGER (0..1)
    ACCESS  read-only
    STATUS  mandatory
    DESCRIPTION
           "The reading for input 12.
            The reading will be 1 (active) or 0 (inactive)"
    ::= { falconInput12  2 }

falconInput12Label OBJECT-TYPE
    SYNTAX  DisplayString
    ACCESS  read-write
    STATUS  mandatory
    DESCRIPTION
           "A user-defined text string associated with Input Number 12.
            The text string is stored in non-volatile memory."
    ::= { falconInput12  3 }

falconInput12RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput12  4 }

falconInput12Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput12  5 }

falconInput13 OBJECT IDENTIFIER ::= { falconInputs 29 }

falconInput13State OBJECT-TYPE
    SYNTAX  INTEGER {
    notInstalled(1),
    digital-no-installed(3),
    digital-nc-installed(4)
}
    ACCESS  read-write
    STATUS  mandatory
    DESCRIPTION
           "The state of use of Input Number 13.
            This variable is stored in non-volatile memory."
    ::= { falconInput13  1 }

falconInput13Reading OBJECT-TYPE
    SYNTAX  INTEGER (0..1)
    ACCESS  read-only
    STATUS  mandatory
    DESCRIPTION
           "The reading for input 13.
            The reading will be 1 (active) or 0 (inactive)"
    ::= { falconInput13  2 }

falconInput13Label OBJECT-TYPE
    SYNTAX  DisplayString
    ACCESS  read-write
    STATUS  mandatory
    DESCRIPTION
           "A user-defined text string associated with Input Number 13.
            The text string is stored in non-volatile memory."
    ::= { falconInput13  3 }

falconInput13RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput13  4 }

falconInput13Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput13  5 }

falconInput14 OBJECT IDENTIFIER ::= { falconInputs 30 }

falconInput14State OBJECT-TYPE
    SYNTAX  INTEGER {
    notInstalled(1),
    digital-no-installed(3),
    digital-nc-installed(4)
}
    ACCESS  read-write
    STATUS  mandatory
    DESCRIPTION
           "The state of use of Input Number 14.
            This variable is stored in non-volatile memory."
    ::= { falconInput14  1 }

falconInput14Reading OBJECT-TYPE
    SYNTAX  INTEGER (0..1)
    ACCESS  read-only
    STATUS  mandatory
    DESCRIPTION
           "The reading for input 14.
            The reading will be 1 (active) or 0 (inactive)"
    ::= { falconInput14  2 }

falconInput14Label OBJECT-TYPE
    SYNTAX  DisplayString
    ACCESS  read-write
    STATUS  mandatory
    DESCRIPTION
           "A user-defined text string associated with Input Number 14.
            The text string is stored in non-volatile memory."
    ::= { falconInput14  3 }

falconInput14RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput14  4 }

falconInput14Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput14  5 }

falconInput15 OBJECT IDENTIFIER ::= { falconInputs 31 }

falconInput15State OBJECT-TYPE
    SYNTAX  INTEGER {
    notInstalled(1),
    digital-no-installed(3),
    digital-nc-installed(4)
}
    ACCESS  read-write
    STATUS  mandatory
    DESCRIPTION
           "The state of use of Input Number 15.
            This variable is stored in non-volatile memory."
    ::= { falconInput15  1 }

falconInput15Reading OBJECT-TYPE
    SYNTAX  INTEGER (0..1)
    ACCESS  read-only
    STATUS  mandatory
    DESCRIPTION
           "The reading for input 15.
            The reading will be 1 (active) or 0 (inactive)"
    ::= { falconInput15  2 }

falconInput15Label OBJECT-TYPE
    SYNTAX  DisplayString
    ACCESS  read-write
    STATUS  mandatory
    DESCRIPTION
           "A user-defined text string associated with Input Number 15.
            The text string is stored in non-volatile memory."
    ::= { falconInput15  3 }

falconInput15RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput15  4 }

falconInput15Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput15  50 }

falconInput16 OBJECT IDENTIFIER ::= { falconInputs 32 }

falconInput16State OBJECT-TYPE
    SYNTAX  INTEGER {
    notInstalled(1),
    digital-no-installed(3),
    digital-nc-installed(4)
}
    ACCESS  read-write
    STATUS  mandatory
    DESCRIPTION
           "The state of use of Input Number 16.
            This variable is stored in non-volatile memory."
    ::= { falconInput16  1 }

falconInput16Reading OBJECT-TYPE
    SYNTAX  INTEGER (0..1)
    ACCESS  read-only
    STATUS  mandatory
    DESCRIPTION
           "The reading for input 16.
            The reading will be 1 (active) or 0 (inactive)"
    ::= { falconInput16  2 }

falconInput16Label OBJECT-TYPE
    SYNTAX  DisplayString
    ACCESS  read-write
    STATUS  mandatory
    DESCRIPTION
           "A user-defined text string associated with Input Number 16.
            The text string is stored in non-volatile memory."
    ::= { falconInput16  3 }

falconInput16RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput16  4 }

falconInput16Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput16  5 }

falconInput17 OBJECT IDENTIFIER ::= { falconInputs 33 }

falconInput17State OBJECT-TYPE
    SYNTAX  INTEGER {
    notInstalled(1),
    digital-no-installed(3),
    digital-nc-installed(4)
}
    ACCESS  read-write
    STATUS  mandatory
    DESCRIPTION
           "The state of use of Input Number 17.
            This variable is stored in non-volatile memory."
    ::= { falconInput17  1 }

falconInput17Reading OBJECT-TYPE
    SYNTAX  INTEGER (0..1)
    ACCESS  read-only
    STATUS  mandatory
    DESCRIPTION
           "The reading for input 17.
            The reading will be 1 (active) or 0 (inactive)"
    ::= { falconInput17  2 }

falconInput17Label OBJECT-TYPE
    SYNTAX  DisplayString
    ACCESS  read-write
    STATUS  mandatory
    DESCRIPTION
           "A user-defined text string associated with Input Number 17.
            The text string is stored in non-volatile memory."
    ::= { falconInput17  3 }

falconInput17RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput17  4 }

falconInput17Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput17  5 }

falconInput18 OBJECT IDENTIFIER ::= { falconInputs 34 }

falconInput18State OBJECT-TYPE
    SYNTAX  INTEGER {
    notInstalled(1),
    digital-no-installed(3),
    digital-nc-installed(4)
}
    ACCESS  read-write
    STATUS  mandatory
    DESCRIPTION
           "The state of use of Input Number 18.
            This variable is stored in non-volatile memory."
    ::= { falconInput18  1 }

falconInput18Reading OBJECT-TYPE
    SYNTAX  INTEGER (0..1)
    ACCESS  read-only
    STATUS  mandatory
    DESCRIPTION
           "The reading for input 18.
            The reading will be 1 (active) or 0 (inactive)"
    ::= { falconInput18  2 }

falconInput18Label OBJECT-TYPE
    SYNTAX  DisplayString
    ACCESS  read-write
    STATUS  mandatory
    DESCRIPTION
           "A user-defined text string associated with Input Number 18.
            The text string is stored in non-volatile memory."
    ::= { falconInput18  3 }

falconInput18RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput18  4 }

falconInput18Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput18  5 }

falconInput19 OBJECT IDENTIFIER ::= { falconInputs 35 }

falconInput19State OBJECT-TYPE
    SYNTAX  INTEGER {
    notInstalled(1),
    digital-no-installed(3),
    digital-nc-installed(4)
}
    ACCESS  read-write
    STATUS  mandatory
    DESCRIPTION
           "The state of use of Input Number 19.
            This variable is stored in non-volatile memory."
    ::= { falconInput19  1 }

falconInput19Reading OBJECT-TYPE
    SYNTAX  INTEGER (0..1)
    ACCESS  read-only
    STATUS  mandatory
    DESCRIPTION
           "The reading for input 19.
            The reading will be 1 (active) or 0 (inactive)"
    ::= { falconInput19  2 }

falconInput19Label OBJECT-TYPE
    SYNTAX  DisplayString
    ACCESS  read-write
    STATUS  mandatory
    DESCRIPTION
           "A user-defined text string associated with Input Number 19.
            The text string is stored in non-volatile memory."
    ::= { falconInput19  3 }

falconInput19RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput19  4 }

falconInput19Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput19  5 }

falconInput20 OBJECT IDENTIFIER ::= { falconInputs 36 }

falconInput20State OBJECT-TYPE
    SYNTAX  INTEGER {
    notInstalled(1),
    digital-no-installed(3),
    digital-nc-installed(4)
}
    ACCESS  read-write
    STATUS  mandatory
    DESCRIPTION
           "The state of use of Input Number 20.
            This variable is stored in non-volatile memory."
    ::= { falconInput20  1 }

falconInput20Reading OBJECT-TYPE
    SYNTAX  INTEGER (0..1)
    ACCESS  read-only
    STATUS  mandatory
    DESCRIPTION
           "The reading for input 20.
            The reading will be 1 (active) or 0 (inactive)"
    ::= { falconInput20  2 }

falconInput20Label OBJECT-TYPE
    SYNTAX  DisplayString
    ACCESS  read-write
    STATUS  mandatory
    DESCRIPTION
           "A user-defined text string associated with Input Number 20.
            The text string is stored in non-volatile memory."
    ::= { falconInput20  3 }

falconInput20RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { falconInput20  4 }

falconInput20Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { falconInput20  5 }

falconOutputs OBJECT IDENTIFIER ::= { falconMIB  4 }

falconRelay1 OBJECT IDENTIFIER ::= { falconOutputs 1 }

falconRelay1State OBJECT-TYPE
    SYNTAX  INTEGER {
    normallyoff(1),
    normallyon(2),
    forceon(3),
    forceoff(4),
    keypadcontrolled(5)
}
    ACCESS  read-write
    STATUS  mandatory
    DESCRIPTION
           "The state of use of Relay Number 1. The relay can be
            set for normally open or closed. The relay can be forced
            to an on or off condition, or controlled by the keypad.
            This variable is stored in non-volatile memory."
    ::= { falconRelay1  1 }

falconRelay1Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 1."
    ::= { falconRelay1  2 }

falconRelay1Label OBJECT-TYPE
    SYNTAX  DisplayString
    ACCESS  read-write
    STATUS  mandatory
    DESCRIPTION
           "A user-defined text string associated with Relay Number 1.
            The text string is stored in non-volatile memory."
    ::= { falconRelay1  3 }

falconRelay1Time OBJECT-TYPE
    SYNTAX  INTEGER (-2147483648..2147483647)
    MAX-ACCESS read-write
    STATUS     mandatory
    DESCRIPTION
        "The number of seconds the relay will be activated.
         Set this to -1 for indefinitely."
    ::= { falconRelay1  4 }

falconRelay2 OBJECT IDENTIFIER ::= { falconOutputs 2 }

falconRelay2State OBJECT-TYPE
    SYNTAX  INTEGER {
    normallyoff(1),
    normallyon(2),
    forceon(3),
    forceoff(4),
    keypascontrolled(5)
}
    ACCESS  read-write
    STATUS  mandatory
    DESCRIPTION
           "The state of use of Relay Number 2. The relay can be
            set for normally open or closed. The relay can be forced
            to an on or off condition, or controlled by the keypad.
            This variable is stored in non-volatile memory."
    ::= { falconRelay2  1 }

falconRelay2Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 2."
    ::= { falconRelay2  2 }

falconRelay2Label OBJECT-TYPE
    SYNTAX  DisplayString
    ACCESS  read-write
    STATUS  mandatory
    DESCRIPTION
           "A user-defined text string associated with Relay Number 2.
            The text string is stored in non-volatile memory."
    ::= { falconRelay2  3 }

falconRelay2Time OBJECT-TYPE
    SYNTAX  INTEGER (-2147483648..2147483647)
    MAX-ACCESS read-write
    STATUS     mandatory
    DESCRIPTION
        "The number of seconds the relay will be activated.
         Set this to -1 for indefinitely."
    ::= { falconRelay2  4 }

falconRelay3 OBJECT IDENTIFIER ::= { falconOutputs 3 }

falconRelay3State OBJECT-TYPE
    SYNTAX  INTEGER {
    normallyoff(1),
    normallyon(2),
    forceon(3),
    forceoff(4),
    keypascontrolled(5)
}
    ACCESS  read-write
    STATUS  mandatory
    DESCRIPTION
           "The state of use of Relay Number 3. The relay can be
            set for normally open or closed. The relay can be forced
            to an on or off condition, or controlled by the keypad.
            This variable is stored in non-volatile memory."
    ::= { falconRelay3  1 }

falconRelay3Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 3."
    ::= { falconRelay3  2 }

falconRelay3Label OBJECT-TYPE
    SYNTAX  DisplayString
    ACCESS  read-write
    STATUS  mandatory
    DESCRIPTION
           "A user-defined text string associated with Relay Number 3.
            The text string is stored in non-volatile memory."
    ::= { falconRelay3  3 }

falconRelay3Time OBJECT-TYPE
    SYNTAX  INTEGER (-2147483648..2147483647)
    MAX-ACCESS read-write
    STATUS     mandatory
    DESCRIPTION
        "The number of seconds the relay will be activated.
         Set this to -1 for indefinitely."
    ::= { falconRelay3  4 }

falconRelay4 OBJECT IDENTIFIER ::= { falconOutputs 4 }

falconRelay4State OBJECT-TYPE
    SYNTAX  INTEGER {
    normallyoff(1),
    normallyon(2),
    forceon(3),
    forceoff(4),
    keypascontrolled(5)
}
    ACCESS  read-write
    STATUS  mandatory
    DESCRIPTION
           "The state of use of Relay Number 4. The relay can be
            set for normally open or closed. The relay can be forced
            to an on or off condition, or controlled by the keypad.
            This variable is stored in non-volatile memory."
    ::= { falconRelay4  1 }

falconRelay4Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 4."
    ::= { falconRelay4  2 }

falconRelay4Label OBJECT-TYPE
    SYNTAX  DisplayString
    ACCESS  read-write
    STATUS  mandatory
    DESCRIPTION
           "A user-defined text string associated with Relay Number 4.
            The text string is stored in non-volatile memory."
    ::= { falconRelay4  3 }

falconRelay4Time OBJECT-TYPE
    SYNTAX  INTEGER (-2147483648..2147483647)
    MAX-ACCESS read-write
    STATUS     mandatory
    DESCRIPTION
        "The number of seconds the relay will be activated.
         Set this to -1 for indefinitely."
    ::= { falconRelay4  4 }

falconRelay5 OBJECT IDENTIFIER ::= { falconOutputs 5 }

falconRelay5State OBJECT-TYPE
    SYNTAX  INTEGER {
    normallyoff(1),
    normallyon(2),
    forceon(3),
    forceoff(4),
    keypascontrolled(5)
}
    ACCESS  read-write
    STATUS  mandatory
    DESCRIPTION
           "The state of use of Relay Number 5. The relay can be
            set for normally open or closed. The relay can be forced
            to an on or off condition, or controlled by the keypad.
            This variable is stored in non-volatile memory."
    ::= { falconRelay5  1 }

falconRelay5Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 5."
    ::= { falconRelay5  2 }

falconRelay5Label OBJECT-TYPE
    SYNTAX  DisplayString
    ACCESS  read-write
    STATUS  mandatory
    DESCRIPTION
           "A user-defined text string associated with Relay Number 5.
            The text string is stored in non-volatile memory."
    ::= { falconRelay5  3 }

falconRelay5Time OBJECT-TYPE
    SYNTAX  INTEGER (-2147483648..2147483647)
    MAX-ACCESS read-write
    STATUS     mandatory
    DESCRIPTION
        "The number of seconds the relay will be activated.
         Set this to -1 for indefinitely."
    ::= { falconRelay5  4 }

falconRelay6 OBJECT IDENTIFIER ::= { falconOutputs 6 }

falconRelay6State OBJECT-TYPE
    SYNTAX  INTEGER {
    normallyoff(1),
    normallyon(2),
    forceon(3),
    forceoff(4),
    keypascontrolled(5)
}
    ACCESS  read-write
    STATUS  mandatory
    DESCRIPTION
           "The state of use of Relay Number 6. The relay can be
            set for normally open or closed. The relay can be forced
            to an on or off condition, or controlled by the keypad.
            This variable is stored in non-volatile memory."
    ::= { falconRelay6  1 }

falconRelay6Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 6."
    ::= { falconRelay6  2 }

falconRelay6Label OBJECT-TYPE
    SYNTAX  DisplayString
    ACCESS  read-write
    STATUS  mandatory
    DESCRIPTION
           "A user-defined text string associated with Relay Number 6.
            The text string is stored in non-volatile memory."
    ::= { falconRelay6  3 }

falconRelay6Time OBJECT-TYPE
    SYNTAX  INTEGER (-2147483648..2147483647)
    MAX-ACCESS read-write
    STATUS     mandatory
    DESCRIPTION
        "The number of seconds the relay will be activated.
         Set this to -1 for indefinitely."
    ::= { falconRelay6  4 }

falconAlarms OBJECT IDENTIFIER ::= { falconMIB  5 }

falconAlarmsPresent OBJECT-TYPE
    SYNTAX     Gauge32
    MAX-ACCESS read-only
    STATUS     current
    DESCRIPTION
        "The present number of active alarm conditions."
    ::= { falconAlarms 1 }

falconAlarmTable OBJECT-TYPE
    SYNTAX     SEQUENCE OF FalconAlarmEntry
    MAX-ACCESS not-accessible
    STATUS     current
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        falconAlarmId equal to 1, and increments the value of
        falconAlarmId each time a new row is created, wrapping to
        the first free value greater than or equal to 1 when
        the maximum value of falconAlarmId would otherwise be
        exceeded.  Consequently, after multiple operations,
        the table may become sparse, e.g., containing entries
        for rows 95, 100, 101, and 203 and the entries should
        not be assumed to be in chronological order because
        falconAlarmId might have wrapped.

        Alarms are named by an AutonomousType (OBJECT
        IDENTIFIER), falconAlarmDescr, to allow a single table to
        reflect well known alarms plus alarms defined by a
        particular implementation, i.e., as documented in the
        private enterprise MIB definition for the device.  No
        two rows will have the same value of falconAlarmDescr,
        since alarms define conditions.  In order to meet this
        requirement, care should be taken in the definition of
        alarm conditions to insure that a system cannot enter
        the same condition multiple times simultaneously.

        The number of rows in the table at any given time is
        reflected by the value of falconAlarmsPresent."
    ::= { falconAlarms 2 }

falconAlarmEntry OBJECT-TYPE
    SYNTAX     FalconAlarmEntry
    MAX-ACCESS not-accessible
    STATUS     current
    DESCRIPTION
         "An entry containing information applicable to a
         particular alarm."
   INDEX { falconAlarmId }
   ::= { falconAlarmTable 1 }

FalconAlarmEntry ::= SEQUENCE {
    falconAlarmId          PositiveInteger,
    falconAlarmDescr       OBJECT IDENTIFIER
}

falconAlarmId OBJECT-TYPE
    SYNTAX     PositiveInteger
    MAX-ACCESS not-accessible
    STATUS     current
    DESCRIPTION
         "A unique identifier for an alarm condition.  This
          value must remain constant."
    ::= { falconAlarmEntry 1 }

falconAlarmDescr OBJECT-TYPE
    SYNTAX     OBJECT IDENTIFIER
    MAX-ACCESS read-only
    STATUS     current
    DESCRIPTION
        "A reference to an alarm description object.  The
         object referenced should not be accessible, but rather
         be used to provide a unique description of the alarm
         condition."
    ::= { falconAlarmEntry 2 }

--
-- Well known alarm conditions.
--

falconWellKnownAlarms    OBJECT IDENTIFIER ::= { falconAlarms 3 }

falconInput1HighAlarm OBJECT-IDENTITY
    STATUS     current
    DESCRIPTION
        "The reading for sensor 1 has reached the high limit
        value."
    ::= { falconWellKnownAlarms  1 }

falconInput1LowAlarm OBJECT-IDENTITY
    STATUS     current
    DESCRIPTION
        "The reading for sensor 1 has reached the low limit
        value."
    ::= { falconWellKnownAlarms  2 }

falconInput1High2Alarm OBJECT-IDENTITY
    STATUS     current
    DESCRIPTION
        "The reading for sensor 1 has reached the high limit
        value."
    ::= { falconWellKnownAlarms  3 }

falconInput1Low2Alarm OBJECT-IDENTITY
    STATUS     current
    DESCRIPTION
        "The reading for sensor 1 has reached the low limit
        value."
    ::= { falconWellKnownAlarms  4 }

falconInput2HighAlarm OBJECT-IDENTITY
    STATUS     current
    DESCRIPTION
        "The reading for sensor 2 has reached the high limit
        value."
    ::= { falconWellKnownAlarms  5 }

falconInput2LowAlarm OBJECT-IDENTITY
    STATUS     current
    DESCRIPTION
        "The reading for sensor 2 has reached the low limit
        value."
    ::= { falconWellKnownAlarms  6 }

falconInput2High2Alarm OBJECT-IDENTITY
    STATUS     current
    DESCRIPTION
        "The reading for sensor 2 has reached the high limit
        value."
    ::= { falconWellKnownAlarms  7 }

falconInput2Low2Alarm OBJECT-IDENTITY
    STATUS     current
    DESCRIPTION
        "The reading for sensor 2 has reached the low limit
        value."
    ::= { falconWellKnownAlarms  8 }

falconInput3HighAlarm OBJECT-IDENTITY
    STATUS     current
    DESCRIPTION
        "The reading for sensor 3 has reached the high limit
        value."
    ::= { falconWellKnownAlarms  9 }

falconInput3LowAlarm OBJECT-IDENTITY
    STATUS     current
    DESCRIPTION
        "The reading for sensor 3 has reached the low limit
        value."
    ::= { falconWellKnownAlarms  10 }

falconInput3High2Alarm OBJECT-IDENTITY
    STATUS     current
    DESCRIPTION
        "The reading for sensor 3 has reached the high limit
        value."
    ::= { falconWellKnownAlarms  11 }

falconInput3Low2Alarm OBJECT-IDENTITY
    STATUS     current
    DESCRIPTION
        "The reading for sensor 3 has reached the low limit
        value."
    ::= { falconWellKnownAlarms  12 }

falconInput4HighAlarm OBJECT-IDENTITY
    STATUS     current
    DESCRIPTION
        "The reading for sensor 4 has reached the high limit
        value."
    ::= { falconWellKnownAlarms  13 }

falconInput4LowAlarm OBJECT-IDENTITY
    STATUS     current
    DESCRIPTION
        "The reading for sensor 4 has reached the low limit
        value."
    ::= { falconWellKnownAlarms  14 }

falconInput4High2Alarm OBJECT-IDENTITY
    STATUS     current
    DESCRIPTION
        "The reading for sensor 4 has reached the high limit
        value."
    ::= { falconWellKnownAlarms  15 }

falconInput4Low2Alarm OBJECT-IDENTITY
    STATUS     current
    DESCRIPTION
        "The reading for sensor 4 has reached the low limit
        value."
    ::= { falconWellKnownAlarms  16 }

falconInput5HighAlarm OBJECT-IDENTITY
    STATUS     current
    DESCRIPTION
        "The reading for sensor 5 has reached the high limit
        value."
    ::= { falconWellKnownAlarms  17 }

falconInput5LowAlarm OBJECT-IDENTITY
    STATUS     current
    DESCRIPTION
        "The reading for sensor 5 has reached the low limit
        value."
    ::= { falconWellKnownAlarms  18 }

falconInput5High2Alarm OBJECT-IDENTITY
    STATUS     current
    DESCRIPTION
        "The reading for sensor 5 has reached the high limit
        value."
    ::= { falconWellKnownAlarms  19 }

falconInput5Low2Alarm OBJECT-IDENTITY
    STATUS     current
    DESCRIPTION
        "The reading for sensor 5 has reached the low limit
        value."
    ::= { falconWellKnownAlarms  20 }

falconInput6HighAlarm OBJECT-IDENTITY
    STATUS     current
    DESCRIPTION
        "The reading for sensor 6 has reached the high limit
        value."
    ::= { falconWellKnownAlarms  21 }

falconInput6LowAlarm OBJECT-IDENTITY
    STATUS     current
    DESCRIPTION
        "The reading for sensor 6 has reached the low limit
        value."
    ::= { falconWellKnownAlarms  22 }

falconInput6High2Alarm OBJECT-IDENTITY
    STATUS     current
    DESCRIPTION
        "The reading for sensor 6 has reached the high limit
        value."
    ::= { falconWellKnownAlarms  23 }

falconInput6Low2Alarm OBJECT-IDENTITY
    STATUS     current
    DESCRIPTION
        "The reading for sensor 6 has reached the low limit
        value."
    ::= { falconWellKnownAlarms  24 }

falconInput7HighAlarm OBJECT-IDENTITY
    STATUS     current
    DESCRIPTION
        "The reading for sensor 7 has reached the high limit
        value."
    ::= { falconWellKnownAlarms  25 }

falconInput7LowAlarm OBJECT-IDENTITY
    STATUS     current
    DESCRIPTION
        "The reading for sensor 7 has reached the low limit
        value."
    ::= { falconWellKnownAlarms  26 }

falconInput7High2Alarm OBJECT-IDENTITY
    STATUS     current
    DESCRIPTION
        "The reading for sensor 7 has reached the high limit
        value."
    ::= { falconWellKnownAlarms  27 }

falconInput7Low2Alarm OBJECT-IDENTITY
    STATUS     current
    DESCRIPTION
        "The reading for sensor 7 has reached the low limit
        value."
    ::= { falconWellKnownAlarms  28 }

falconInput8HighAlarm OBJECT-IDENTITY
    STATUS     current
    DESCRIPTION
        "The reading for sensor 8 has reached the high limit
        value."
    ::= { falconWellKnownAlarms  29 }

falconInput8LowAlarm OBJECT-IDENTITY
    STATUS     current
    DESCRIPTION
        "The reading for sensor 8 has reached the low limit
        value."
    ::= { falconWellKnownAlarms  30 }

falconInput8High2Alarm OBJECT-IDENTITY
    STATUS     current
    DESCRIPTION
        "The reading for sensor 8 has reached the high limit
        value."
    ::= { falconWellKnownAlarms  31 }

falconInput8Low2Alarm OBJECT-IDENTITY
    STATUS     current
    DESCRIPTION
        "The reading for sensor 8 has reached the low limit
        value."
    ::= { falconWellKnownAlarms  32 }

falconInput1DigAlarm OBJECT-IDENTITY
    STATUS     current
    DESCRIPTION
        "The digital input 1 has been activated."
    ::= { falconWellKnownAlarms  81 }

falconInput2DigAlarm OBJECT-IDENTITY
    STATUS     current
    DESCRIPTION
        "The digital input 2 has been activated."
    ::= { falconWellKnownAlarms  82 }

falconInput3DigAlarm OBJECT-IDENTITY
    STATUS     current
    DESCRIPTION
        "The digital input 3 has been activated."
    ::= { falconWellKnownAlarms  83 }

falconInput4DigAlarm OBJECT-IDENTITY
    STATUS     current
    DESCRIPTION
        "The digital input 4 has been activated."
    ::= { falconWellKnownAlarms  84 }

falconInput5DigAlarm OBJECT-IDENTITY
    STATUS     current
    DESCRIPTION
        "The digital input 5 has been activated."
    ::= { falconWellKnownAlarms  85 }

falconInput6DigAlarm OBJECT-IDENTITY
    STATUS     current
    DESCRIPTION
        "The digital input 6 has been activated."
    ::= { falconWellKnownAlarms  86 }

falconInput7DigAlarm OBJECT-IDENTITY
    STATUS     current
    DESCRIPTION
        "The digital input 7 has been activated."
    ::= { falconWellKnownAlarms  87 }

falconInput8DigAlarm OBJECT-IDENTITY
    STATUS     current
    DESCRIPTION
        "The digital input 8 has been activated."
    ::= { falconWellKnownAlarms  88 }

falconInput9DigAlarm OBJECT-IDENTITY
    STATUS     current
    DESCRIPTION
        "The digital input 9 has been activated."
    ::= { falconWellKnownAlarms  89 }

falconInput10DigAlarm OBJECT-IDENTITY
    STATUS     current
    DESCRIPTION
        "The digital input 10 has been activated."
    ::= { falconWellKnownAlarms  90 }

falconInput11DigAlarm OBJECT-IDENTITY
    STATUS     current
    DESCRIPTION
        "The digital input 11 has been activated."
    ::= { falconWellKnownAlarms  91 }

falconInput12DigAlarm OBJECT-IDENTITY
    STATUS     current
    DESCRIPTION
        "The digital input 12 has been activated."
    ::= { falconWellKnownAlarms  92 }

falconInput13DigAlarm OBJECT-IDENTITY
    STATUS     current
    DESCRIPTION
        "The digital input 13 has been activated."
    ::= { falconWellKnownAlarms  93 }

falconInput14DigAlarm OBJECT-IDENTITY
    STATUS     current
    DESCRIPTION
        "The digital input 14 has been activated."
    ::= { falconWellKnownAlarms  94 }

falconInput15DigAlarm OBJECT-IDENTITY
    STATUS     current
    DESCRIPTION
        "The digital input 15 has been activated."
    ::= { falconWellKnownAlarms  95 }

falconInput16DigAlarm OBJECT-IDENTITY
    STATUS     current
    DESCRIPTION
        "The digital input 16 has been activated."
    ::= { falconWellKnownAlarms  96 }

falconInput17DigAlarm OBJECT-IDENTITY
    STATUS     current
    DESCRIPTION
        "The digital input 17 has been activated."
    ::= { falconWellKnownAlarms  97 }

falconInput18DigAlarm OBJECT-IDENTITY
    STATUS     current
    DESCRIPTION
        "The digital input 18 has been activated."
    ::= { falconWellKnownAlarms  98 }

falconInput19DigAlarm OBJECT-IDENTITY
    STATUS     current
    DESCRIPTION
        "The digital input 19 has been activated."
    ::= { falconWellKnownAlarms  99 }

falconInput20DigAlarm OBJECT-IDENTITY
    STATUS     current
    DESCRIPTION
        "The digital input 20 has been activated."
    ::= { falconWellKnownAlarms  100 }

falconOnBatteryAlarm OBJECT-IDENTITY
    STATUS     current
    DESCRIPTION
        "The On Battery input has been activated."
    ::= { falconWellKnownAlarms  102 }

falconLowBatteryAlarm OBJECT-IDENTITY
    STATUS     current
    DESCRIPTION
        "The Faclon has detected a low battery condition."
    ::= { falconWellKnownAlarms  103 }

falconTraps OBJECT IDENTIFIER ::= { falconMIB  6 }

falconAlarmEntryAdded TRAP-TYPE
    ENTERPRISE   falconTraps 
    DESCRIPTION
           "An AlarmEntryAdded Trap signifies that the a sensor
            reading has reached a high or low limit value."
    ::= 1

falconAlarmEntryRemoved TRAP-TYPE
    ENTERPRISE   falconTraps 
    DESCRIPTION
           "An AlarmEntryAdded Trap signifies that the a sensor
            reading has gone below the high limit value or above
            the low limit value."
    ::= 2

falconAccessGranted TRAP-TYPE
    ENTERPRISE   falconTraps 
    DESCRIPTION
           "An falconAccessGranted Trap signifies that a valid
            key code sequence was processed by the falcon."
    ::= 3

falconAccessDenied TRAP-TYPE
    ENTERPRISE   falconTraps 
    DESCRIPTION
           "An falconAccessedDenied Trap signifies that an invalid
            key code sequence was processed by the falcon."
    ::= 4

falconAlarmHistory OBJECT IDENTIFIER ::= { falconMIB  7 }

falconAlarmHistoryEntries OBJECT-TYPE
    SYNTAX     Gauge32
    MAX-ACCESS read-only
    STATUS     current
    DESCRIPTION
        "The present number of entries in the alarm history."
    ::= { falconAlarmHistory 1 }

falconAlarmHistoryClear OBJECT-TYPE
    SYNTAX  INTEGER {
    clearbuffer(1)
}
    ACCESS  read-write
    STATUS  mandatory
    DESCRIPTION
           "Setting this value to ClearBuffer(1) will clear the
            alarm history buffer. "
    ::= { falconAlarmHistory 2 }

falconAlarmHistoryTable OBJECT-TYPE
    SYNTAX     SEQUENCE OF FalconAlarmHistoryEntry
    MAX-ACCESS not-accessible
    STATUS     current
    DESCRIPTION
       "A list of alarm history table entries stored in the
        in the non-volatile memory.  The table contains zero,
        one, or many rows at any moment, depending upon the
        number of alarm conditions in effect. The falcon creates
        a row in the table each time a new alarm is detected.
        The falcon creates the first row with falconAlarmHistoryId
        equal to 1, and increments the value of falconAlarmHistoryId
        each time a new row is created, up to a maximum of 100.
        After 100 entries are created, the falcon will overwrite
        the earliest entry with the latest alarm.
        The number of rows in the table at any given time is
        reflected by the value of falconAlarmHistoryEntries."
    ::= { falconAlarmHistory 3 }

falconAlarmHistoryEntry OBJECT-TYPE
    SYNTAX     FalconAlarmHistoryEntry
    MAX-ACCESS not-accessible
    STATUS     current
    DESCRIPTION
         "An entry containing information applicable to a
         particular alarm history entry."
   INDEX { falconAlarmHistoryId }
   ::= { falconAlarmHistoryTable 1 }

FalconAlarmHistoryEntry ::= SEQUENCE {
    falconAlarmHistoryId     PositiveInteger,
    falconAlarmHistoryText   DisplayString
}

falconAlarmHistoryId OBJECT-TYPE
    SYNTAX     PositiveInteger
    MAX-ACCESS not-accessible
    STATUS     current
    DESCRIPTION
         "A unique identifier for an alarm condition.  This
          value must remain constant."
    ::= { falconAlarmHistoryEntry 1 }

falconAlarmHistoryText OBJECT-TYPE
    SYNTAX     DisplayString
    MAX-ACCESS read-only
    STATUS     current
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel
         These alarms are stored in non-volatile memory."
    ::= { falconAlarmHistoryEntry 2 }

falconTrapSettings OBJECT IDENTIFIER ::= { falconMIB  8 }

falconPersistantTraps OBJECT-TYPE
    SYNTAX  INTEGER (0..2147483647)
    MAX-ACCESS read-write
    STATUS     mandatory
    DESCRIPTION
        "The number of minutes between persistant traps.
         Set this to 0 to turn off persistant traps.
         This value is stored in non-volatile memory."
    ::= { falconTrapSettings 1 }

falconAlarmAcknowledge OBJECT-TYPE
    SYNTAX  INTEGER {
    acknowledgeAlarms(1)
}
    ACCESS  read-write
    STATUS  mandatory
    DESCRIPTION
           "Setting this value to AcknowledgeAlarms(1) will
            stop the falcon from sending persistant traps
            and dial out sequences."
    ::= { falconTrapSettings 2 }

--
-- The falcon Extension
--
        falcon8124 OBJECT IDENTIFIER ::= { falcon 3 }

END
