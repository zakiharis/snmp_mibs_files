-- MIB file(file name: melco_r2000):

-- MELNET R2000 MIB
--   
--   Copyright 1995 Mitsubishi Electric Corporation.  All rights reserved.

-- START OF MIB: r2000-MIB
        R2000-MIB DEFINITIONS ::= BEGIN

        IMPORTS
                mgmt, NetworkAddress, IpAddress, Counter, Gauge,
                        TimeTicks, enterprises
                    FROM RFC1155-SMI
                PhysAddress
                    FROM RFC1213-MIB       --MIB 2
                FddiTime, FddiResourceId, FddiSMTStationIDType, 
                        FddiMACLongAddressType
                    FROM RFC1285-MIB       --FDDI MIB
                MacAddress, BridgeId, Timeout
                    FROM RFC1286-MIB       --Bridge MIB
                OBJECT-TYPE
                        FROM RFC-1212;

        --  MELCO MIB 

	melco	 	OBJECT IDENTIFIER ::= { enterprises 409 }
	cow	 	OBJECT IDENTIFIER ::= { melco 94 }
	equipment 	OBJECT IDENTIFIER ::= { cow 2 }
	networkelement 	OBJECT IDENTIFIER ::= { equipment 2 }
	r2000	 	OBJECT IDENTIFIER ::= { networkelement 1 }

        --  MELCO R2000 MIB 

	nvl		OBJECT IDENTIFIER ::= { r2000 19 }


        -- the NOVELL group

        nvlIPX          OBJECT IDENTIFIER ::= { nvl 1 }

        -- the NOVELL IPX group

        nvlIpxForwarding OBJECT-TYPE
            SYNTAX  INTEGER { disabled(1), enabled(2) }   
            ACCESS  read-write
            STATUS  mandatory
            DESCRIPTION
                    "R2000 Specific. nvlIpxForwarding On/Off. "
            ::= { nvlIPX 1 }

        nvlIpxInReceives OBJECT-TYPE
            SYNTAX  Counter
            ACCESS  read-only
            STATUS  mandatory
            DESCRIPTION
                    "R2000 Specific"
            ::= { nvlIPX 2 }

        nvlIpxInHdrErrors OBJECT-TYPE
            SYNTAX  Counter
            ACCESS  read-only
            STATUS  mandatory
            DESCRIPTION
                    "R2000 Specific"
            ::= { nvlIPX 3 }

        nvlIpxInAddrErrors OBJECT-TYPE
            SYNTAX  Counter
            ACCESS  read-only
            STATUS  mandatory
            DESCRIPTION
                    "R2000 Specific"
            ::= { nvlIPX 4 }

        nvlIpxForwDatagrams OBJECT-TYPE
            SYNTAX  Counter
            ACCESS  read-only
            STATUS  mandatory
            DESCRIPTION
                    "R2000 Specific"
            ::= { nvlIPX 5 }

        nvlIpxInUnknownSockets OBJECT-TYPE
            SYNTAX  Counter
            ACCESS  read-only
            STATUS  mandatory
            DESCRIPTION
                    "R2000 Specific"
            ::= { nvlIPX 6 }

        nvlIpxInDiscards OBJECT-TYPE
            SYNTAX  Counter
            ACCESS  read-only
            STATUS  mandatory
            DESCRIPTION
                    "R2000 Specific"
            ::= { nvlIPX 7 }

        nvlIpxInDelivers OBJECT-TYPE
            SYNTAX  Counter
            ACCESS  read-only
            STATUS  mandatory
            DESCRIPTION
                    "R2000 Specific"
            ::= { nvlIPX 8 }

        nvlIpxOutRequests OBJECT-TYPE
            SYNTAX  Counter
            ACCESS  read-only
            STATUS  mandatory
            DESCRIPTION
                    "R2000 Specific"
            ::= { nvlIPX 9 }

        nvlIpxOutDiscards OBJECT-TYPE
            SYNTAX  Counter
            ACCESS  read-only
            STATUS  mandatory
            DESCRIPTION
                    "R2000 Specific"
            ::= { nvlIPX 10 }

        nvlIpxOutNoRoutes OBJECT-TYPE
            SYNTAX  Counter
            ACCESS  read-only
            STATUS  mandatory
            DESCRIPTION
                    "R2000 Specific"
            ::= { nvlIPX 11 }

        nvlIpxForwardingDiscards OBJECT-TYPE
            SYNTAX  Counter
            ACCESS  read-only
            STATUS  mandatory
            DESCRIPTION
                    "R2000 Specific"
            ::= { nvlIPX 12 }

        nvlIpxTrafficControlEnable OBJECT-TYPE
            SYNTAX  INTEGER { disabled(1), enabled(2) }
            ACCESS  read-write
            STATUS  mandatory
            DESCRIPTION
                    "R2000 Specific"
            ::= { nvlIPX 13 }

        nvlIpxForward OBJECT IDENTIFIER ::= { nvlIPX 14 }

         -- the NOVELL IPX Forward Table

        nvlIpxForwardTable OBJECT-TYPE
            SYNTAX  SEQUENCE OF NvlIpxForwardEntry 
            ACCESS  not-accessible
            STATUS  mandatory
            DESCRIPTION
                    "R2000 Specific"
            ::= { nvlIpxForward 3 }

        nvlIpxForwardEntry OBJECT-TYPE
            SYNTAX  NvlIpxForwardEntry
            ACCESS  not-accessible
            STATUS  mandatory
            DESCRIPTION
                    "R2000 Specific"
            INDEX   { nvlIpxForwardDest }
            ::= { nvlIpxForwardTable 1 }

        NvlIpxForwardEntry ::=
            SEQUENCE {
                nvlIpxForwardDest
                    IpAddress,
                nvlIpxForwardNextHop
                    IpAddress,
                nvlIpxForwardLpID
                    INTEGER,
                nvlIpxForwardType
                    INTEGER,
                nvlIpxForwardProto
                    Counter,
                nvlIpxForwardAge
                    INTEGER,
                nvlIpxForwardMetric1
                    INTEGER,
                nvlIpxForwardMetric2
                    INTEGER
            }

        nvlIpxForwardDest OBJECT-TYPE
            SYNTAX  IpAddress
            ACCESS  read-only
            STATUS  mandatory
            DESCRIPTION
                    "R2000 Specific"
            ::= { nvlIpxForwardEntry 1 }

        nvlIpxForwardNextHop OBJECT-TYPE
            SYNTAX  IpAddress
            ACCESS  read-only
            STATUS  mandatory
            DESCRIPTION
                    "R2000 Specific"
            ::= { nvlIpxForwardEntry 2 }

        nvlIpxForwardLpID OBJECT-TYPE
            SYNTAX  INTEGER
            ACCESS  read-only
            STATUS  mandatory
            DESCRIPTION
                    "R2000 Specific"
            ::= { nvlIpxForwardEntry 3 }

        nvlIpxForwardType OBJECT-TYPE
            SYNTAX  INTEGER { local(1), remote(2) }
            ACCESS  read-only
            STATUS  mandatory
            DESCRIPTION
                    "R2000 Specific. Local/Remote"
            ::= { nvlIpxForwardEntry 4 }

        nvlIpxForwardProto OBJECT-TYPE
            SYNTAX  Counter
            ACCESS  read-only
            STATUS  mandatory
            DESCRIPTION
                    "R2000 Specific"
            ::= { nvlIpxForwardEntry 5 }

        nvlIpxForwardAge OBJECT-TYPE
            SYNTAX  INTEGER
            ACCESS  read-only
            STATUS  mandatory
            DESCRIPTION
                    "R2000 Specific"
            ::= { nvlIpxForwardEntry 6 }

        nvlIpxForwardMetric1 OBJECT-TYPE
            SYNTAX  INTEGER
            ACCESS  read-only
            STATUS  mandatory
            DESCRIPTION
                    "R2000 Specific"
            ::= { nvlIpxForwardEntry 7 }

        nvlIpxForwardMetric2 OBJECT-TYPE
            SYNTAX  INTEGER
            ACCESS  read-only
            STATUS  mandatory
            DESCRIPTION
                    "R2000 Specific"
            ::= { nvlIpxForwardEntry 8 }

        -- Traps
        -- Generic-Traps

        coldStart TRAP-TYPE
            ENTERPRISE  snmp
            DESCRIPTION
                        "A coldStart trap signifies that the sending
                        protocol entity is reinitializing itself such
                        that the agent's configuration or the protocol
                        entity implementation may be altered."
            ::= 0

        warmStart TRAP-TYPE
            ENTERPRISE  snmp
            DESCRIPTION
                        "A warmStart trap signifies that the sending
                        protocol entity is reinitializing itself such
                        that neither the agent configuration nor the
                        protocol entity implementation is altered."
            ::= 1

        linkDown TRAP-TYPE
            ENTERPRISE  snmp
            VARIABLES   { ifIndex }
            DESCRIPTION
                        "A linkDown trap signifies that the sending
                        protocol entity recognizes a failure in one of
                        the communication links represented in the
                        agent's configuration."
            ::= 2

        linkUp TRAP-TYPE
            ENTERPRISE  snmp
            VARIABLES   { ifIndex }
            DESCRIPTION
                        "A linkUp trap signifies that the sending
                        protocol entity recognizes that one of the
                        communication links represented in the agent's
                        configuration has come up."
            ::= 3

        authenticationFailure TRAP-TYPE
            ENTERPRISE  snmp
            DESCRIPTION
                        "An authenticationFailure trap signifies that
                        the sending protocol entity is the addressee
                        of a protocol message that is not properly
                        authenticated.  While implementations of the
                        SNMP must be capable of generating this trap,
                        they must also be capable of suppressing the
                        emission of such traps via an implementation-
                        specific mechanism."
            ::= 4
        egpNeighborLoss TRAP-TYPE
            ENTERPRISE  snmp
            VARIABLES   { egpNeighAddr }
            DESCRIPTION
                        "An egpNeighborLoss trap signifies that an EGP
                        neighbor for whom the sending protocol entity
                        was an EGP peer has been marked down and the
                        peer relationship no longer obtains."
            ::= 5

        -- Enterprise-specific Trap

        fddiAlarm TRAP-TYPE
            ENTERPRISE  melco
            DESCRIPTION
                        "Selftest Error."
            ::= 1577124096

END
