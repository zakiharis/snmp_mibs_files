RBTWS-REGISTRATION-CHASSIS-MIB DEFINITIONS ::= BEGIN

IMPORTS
    MODULE-IDENTITY
        FROM SNMPv2-SMI
    rbtwsRegistration
        FROM RBTWS-ROOT-MIB;

rbtwsRegistrationChassisMib MODULE-IDENTITY
    LAST-UPDATED "200708231753Z"
    ORGANIZATION "Enterasys Networks"
    CONTACT-INFO
        "www.enterasys.com"
    DESCRIPTION
        "The MIB module for Enterasys Networks wireless switch
        chassis component OID registrations.
        These are generic OIDs: they apply to any switch model,
        if the respective chassis component is present in the switch.

        Copyright 2007 Enterasys Networks, Inc.
        All rights reserved.
        This SNMP Management Information Base
        Specification (Specification) embodies
        confidential and proprietary intellectual property.

        This Specification is supplied 'AS IS' and Enterasys Networks
        makes no warranty, either express or implied, as to the use,
        operation, condition, or performance of the Specification."

    REVISION "200708220000Z"
    DESCRIPTION "v1.0: initial version, published in 6.2 release"

    ::= { rbtwsRegistration 5 }


rbtwsChassisComponents      OBJECT IDENTIFIER ::= { rbtwsRegistration 4 }

rbtwsChasCompPowerSupplies  OBJECT IDENTIFIER ::= { rbtwsChassisComponents 1 }

rbtwsChasCompFans           OBJECT IDENTIFIER ::= { rbtwsChassisComponents 2 }

rbtwsChasCompPowerSupply1   OBJECT IDENTIFIER ::= { rbtwsChasCompPowerSupplies 1 }
rbtwsChasCompPowerSupply2   OBJECT IDENTIFIER ::= { rbtwsChasCompPowerSupplies 2 }

rbtwsChasCompFan1           OBJECT IDENTIFIER ::= { rbtwsChasCompFans 1 }
rbtwsChasCompFan2           OBJECT IDENTIFIER ::= { rbtwsChasCompFans 2 }
rbtwsChasCompFan3           OBJECT IDENTIFIER ::= { rbtwsChasCompFans 3 }

END
