-- *****************************************************************
-- RDN-EVT-NOTIFICATIONS.mib:
-- Motorola BSR's EVT Notifications MIB
--
-- Copyright (C) 2003, 2008 by Motorola, Inc.
-- All rights reserved.
-- *****************************************************************
RDN-EVT-NOTIFICATIONS  DEFINITIONS::= BEGIN

IMPORTS
    riverdelta
        FROM RDN-MIB
	
    ifPhysAddress
        FROM IF-MIB

    docsIfDocsisBaseCapability
        FROM DOCS-IF-MIB

    docsDevEvId,
    docsDevEvText,
    docsDevEvLevel
        FROM DOCS-CABLE-DEVICE-MIB
		
    NOTIFICATION-TYPE,
    MODULE-IDENTITY
	FROM SNMPv2-SMI;

rdnEvtNotifications MODULE-IDENTITY
     LAST-UPDATED "200808080000Z" -- August 8, 2008
     ORGANIZATION "Motorola"
     CONTACT-INFO "Motorola
                   Customer Service
                   101 Tournament Drive
                   Horsham, PA 19044
                   US Tel: +1 888 944 4357
                   Int Tel: +1 215 323 0044
	           Fax: +1 215 323 1502
                   Email: CPSSupport@Motorola.com"
     DESCRIPTION
	 "MIB module for EVT Notifications. The following notifications
	  are generated by EVTs. The Event Id for each event is represented 
          as the last sub identifier for each notification. 
	  
	  The DOCSIS Event Id(docsDevEvId) or last sub-identifier is 
	  calculated by adding the Motorola Event Id Base + Vendor Specific 
	  Event Base + + the EVT subsystem base + index (1-255).
	  
	  Example of DRM.56 'Spare CMTS Active' event identifier is:
	     Vendor Event Id Base                 0x80000000
	     Motorola Event Base               +  0x13750000
	     DRM Evt subsystem Base            +  0x     700
	     56 (in hex)                       +  0x      38
                                                  ----------
                                                  0x93750738 hex
						  
                                               or 2473920312 decimal

           The CLI command 'show evt' also displays the bases for the EVT
	   subsystems that are registered.
	   
	   All EVT notifications contain the same set variable-bindings:
	       docsDevEvLevel - this event's severity level. 
	       docsDevEvId - the DOSIS Event Id for this particular event,
                   and also the last sub identifier for this notification.
               docsDevEvText - The DOCSIS Event Text for this event, 
	           ASCII printable text that is displayed for this event.
               docsIfDocsisBaseCapability - The current DOCSIS capabilities of 
                   this agent.
 	       ifPhysAddress - Not used at this time.

	   This MIB just list a few of the notifications generated by EVT,
	   specifically all EVTs notification with a severity level of 
	   critical or higher.


	   Copyright (C) 2003, 2008 by Motorola, Inc.
	   All rights reserved."

     REVISION "200808080000Z"  -- 08 August 2008
     DESCRIPTION
	 "Added Copyright Statement into MIB modules's
	 description."	   	   
 
     REVISION       "200402200000Z" -- February 20, 2004
     DESCRIPTION
         "Correct the follow Object Identifiers:
	  * rdnEvtDraRxUnexpectedMsgSubType is 2473919755 (DRA.11)
	  * rdnEvtDraTmrInitFailure is 247391961 (DRA.17)
	  * rdnEvtDraInvalidFuncParam is 2473919767 (DRA.23)
	  * rdnEvtDraInvalidMsgParam is 2473919768 (DRA.24)"
     REVISION       "200311050000Z" -- November 5, 2003 
     DESCRIPTION
         "Updated the CONTACT-INFO."
     REVISION       "200307090000Z" -- July 9, 2003
     DESCRIPTION
	 "Initial creation."
     ::= { riverdelta 0 }

rdnEvtMacrtrGetQIdFailure NOTIFICATION-TYPE
     OBJECTS     { docsDevEvLevel, 
                   docsDevEvId, 
                   docsDevEvText, 
                   docsIfDocsisBaseCapability,
		   ifPhysAddress }
     STATUS      current
     DESCRIPTION
	 "This is an internal software error. 
	 The MACRTR task was unable to get the DOCSIS Redundancy Agent(DRA)
	 task main message queue id."
     ::= { rdnEvtNotifications 2473918722 }

rdnEvtMacrtrUnknownCase NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task was received 
	 an unexpected case, which is not handled."
     ::= { rdnEvtNotifications 2473918723 }

rdnEvtMacrtrMsgQReceiveFailure NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task caught an error
	 when it was receiving a message."
     ::= { rdnEvtNotifications 2473918724 }

rdnEvtMacrtrRdbDefineTableFailure NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task was unable
	 to register a table with the Redundancy Runtime Record 
	 Database(RDB) for CMTS Redundancy."
     ::= { rdnEvtNotifications 2473918726 }

rdnEvtMacrtrRxUnexpectedMsgType NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task received an 
	 unexpected message type."
     ::= { rdnEvtNotifications 2473918730 }

rdnEvtMacrtrRegTaskMonFailure NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task was unable to
	 register with the task monitor."
     ::= { rdnEvtNotifications 2473918731 }

rdnEvtMacrtrInvalidFuncParam NOTIFICATION-TYPE
     OBJECTS     { docsDevEvLevel, 
                   docsDevEvId, 
                   docsDevEvText, 
                   docsIfDocsisBaseCapability,
		   ifPhysAddress }
     STATUS      current
     DESCRIPTION
	 "This is an internal software error. The MACRTR task detected an 
	 invalid function parameter."
     ::= { rdnEvtNotifications 2473918732 }

rdnEvtMacrtrUnknownCmId NOTIFICATION-TYPE
     OBJECTS     { docsDevEvLevel, 
                   docsDevEvId, 
                   docsDevEvText, 
                   docsIfDocsisBaseCapability,
		   ifPhysAddress }
     STATUS      current
     DESCRIPTION
	 "This is an internal software error. During a CMTS Switchover,
	 the MACRTR task was unable to determine the cable modem Id when
	 loading the Cable Modem runtime record. This notification is only 
	 generated on the BSR 64000."
     ::= { rdnEvtNotifications 2473918735 }

rdnEvtBpiLoadAuthRunRecFailure NOTIFICATION-TYPE
     OBJECTS     { docsDevEvLevel, 
                   docsDevEvId, 
                   docsDevEvText, 
                   docsIfDocsisBaseCapability,
		   ifPhysAddress }
     STATUS      current
     DESCRIPTION
	 "This is an internal software error. The Baseline Privacy 
	 Interface(BPI) task was unable to load the Authorization Key
	 runtime record during a CMTS Switchover."
     ::= { rdnEvtNotifications 2473919513 }

rdnEvtBpiLoadTekRunRecFailure NOTIFICATION-TYPE
     OBJECTS     { docsDevEvLevel, 
                   docsDevEvId, 
                   docsDevEvText, 
                   docsIfDocsisBaseCapability,
		   ifPhysAddress }
     STATUS      current
     DESCRIPTION
	 "This is an internal software error. The Baseline Privacy 
	 Interface(BPI) task was unable to load the TEK runtime 
	 record during a CMTS Switchover."
     ::= { rdnEvtNotifications 2473919514 }

rdnEvtBpiLoadCmCertificateFailure NOTIFICATION-TYPE
     OBJECTS     { docsDevEvLevel, 
                   docsDevEvId, 
                   docsDevEvText, 
                   docsIfDocsisBaseCapability,
		   ifPhysAddress }
     STATUS      current
     DESCRIPTION
	 "This is an internal software error. The Baseline Privacy 
	 Interface(BPI) task was unable to load the Cable Modem 
	 Certificate during a CMTS Switchover."
     ::= { rdnEvtNotifications 2473919525 }

rdnEvtDraTaskSpawnFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to create the 
	 DOCSIS Redundancy Agent(DRA) task. This notification is only 
	 generated on the BSR 64000."
     ::= { rdnEvtNotifications 2473919745 }

rdnEvtDraMsgQCreateFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to create the DRA task's
	 message queue. This notification is only generated on the BSR 64000."
     ::= { rdnEvtNotifications 2473919746 }

rdnEvtDraMsgQReceiveFailure NOTIFICATION-TYPE
     OBJECTS     { docsDevEvLevel, 
                   docsDevEvId, 
                   docsDevEvText, 
                   docsIfDocsisBaseCapability,
		   ifPhysAddress }
     STATUS      current
     DESCRIPTION
	 "This is an internal software error. DRA task's caught an error
	 when it was receiving a message. This notification is only 
	 generated on the BSR 64000."
     ::= { rdnEvtNotifications 2473919747 }

rdnEvtDraRegTaskMonFailure NOTIFICATION-TYPE
     OBJECTS     { docsDevEvLevel, 
                   docsDevEvId, 
                   docsDevEvText, 
                   docsIfDocsisBaseCapability,
		   ifPhysAddress }
     STATUS      current
     DESCRIPTION
	 "This is an internal software error. DRA task was unable to register 
	 with the task monitor. This notification is only 
	 generated on the BSR 64000."
     ::= { rdnEvtNotifications 2473919748 }

rdnEvtDraCreateRdbFailure NOTIFICATION-TYPE
     OBJECTS     { docsDevEvLevel, 
                   docsDevEvId, 
                   docsDevEvText, 
                   docsIfDocsisBaseCapability,
		   ifPhysAddress }
     STATUS      current
     DESCRIPTION
	 "This is an internal software error. DRA task was
	 unable to create a Redundancy Runtime Database for CMTS Redundancy. 
	 This notification is only generated on the BSR 64000."
     ::= { rdnEvtNotifications 2473919749 }

rdnEvtDraRxUnexpectedMsgType NOTIFICATION-TYPE
     OBJECTS     { docsDevEvLevel, 
                   docsDevEvId, 
                   docsDevEvText, 
                   docsIfDocsisBaseCapability,
		   ifPhysAddress }
     STATUS      current
     DESCRIPTION
	 "This is an internal software error. DRA task received an unexpected
	 message type. This notification is only generated on the BSR 64000."
     ::= { rdnEvtNotifications 2473919754 }

rdnEvtDraRxUnexpectedMsgSubType NOTIFICATION-TYPE
     OBJECTS     { docsDevEvLevel, 
                   docsDevEvId, 
                   docsDevEvText, 
                   docsIfDocsisBaseCapability,
		   ifPhysAddress }
     STATUS      current
     DESCRIPTION
	 "This is an internal software error. DRA task received an unexpected
	 message sub-type. This notification is only generated on the 
	 BSR 64000."
     ::= { rdnEvtNotifications 2473919755 }

rdnEvtDraTmrInitFailure NOTIFICATION-TYPE
     OBJECTS     { docsDevEvLevel, 
                   docsDevEvId, 
                   docsDevEvText, 
                   docsIfDocsisBaseCapability,
		   ifPhysAddress }
     STATUS      current
     DESCRIPTION
	 "This is an internal software error. DRA was unable to 
	 create its timers. This notification is only generated 
	 on the BSR 64000."
     ::= { rdnEvtNotifications 2473919761 }

rdnEvtDraInvalidFuncParam NOTIFICATION-TYPE
     OBJECTS     { docsDevEvLevel, 
                   docsDevEvId, 
                   docsDevEvText, 
                   docsIfDocsisBaseCapability,
		   ifPhysAddress }
     STATUS      current
     DESCRIPTION
	 "This is an internal software error. The DRA task detected an 
	 invalid function parameter. This notification is only generated 
	 on the BSR 64000."
     ::= { rdnEvtNotifications 2473919767 }

rdnEvtDraInvalidMsgParam NOTIFICATION-TYPE
     OBJECTS     { docsDevEvLevel, 
                   docsDevEvId, 
                   docsDevEvText, 
                   docsIfDocsisBaseCapability,
		   ifPhysAddress }
     STATUS      current
     DESCRIPTION
	 "This is an internal software error. The DRA task detected an 
	 invalid message parameter. This notification is only generated 
	 on the BSR 64000."
     ::= { rdnEvtNotifications 2473919768 }

rdnEvtRdbMsgQCheckFailure NOTIFICATION-TYPE
     OBJECTS     { docsDevEvLevel, 
                   docsDevEvId, 
                   docsDevEvText, 
                   docsIfDocsisBaseCapability,
		   ifPhysAddress }
     STATUS      current
     DESCRIPTION
	 "This is an internal resource error. The is a major component 
	 failure with on of RDB's message queues, that may lead to 
	 system failures. Try correcting this problem by resetting this
	 CMTS. This notification is only generated on the BSR 64000."
     ::= { rdnEvtNotifications 2473920006 }

rdnEvtRdbCreateDatabaseFailure NOTIFICATION-TYPE
     OBJECTS     { docsDevEvLevel, 
                   docsDevEvId, 
                   docsDevEvText, 
                   docsIfDocsisBaseCapability,
		   ifPhysAddress }
     STATUS      current
     DESCRIPTION
	 "This is an internal error. There is a major component 
	 failure creating a database for CMTS redundancy, this could
	 lead to system failures. This notification is only generated 
	 on the BSR 64000."
     ::= { rdnEvtNotifications 2473920025 }

rdnEvtRdbInitDatabaseFailure NOTIFICATION-TYPE
     OBJECTS     { docsDevEvLevel, 
                   docsDevEvId, 
                   docsDevEvText, 
                   docsIfDocsisBaseCapability,
		   ifPhysAddress }
     STATUS      current
     DESCRIPTION
	 "This is an internal error. There is a major component 
	 failure initializing a database for CMTS redundancy, this could
	 lead to system failures. This notification is only generated 
	 on the BSR 64000."
     ::= { rdnEvtNotifications 2473920026 }

rdnEvtRdbSemCreateFailure NOTIFICATION-TYPE
     OBJECTS     { docsDevEvLevel, 
                   docsDevEvId, 
                   docsDevEvText, 
                   docsIfDocsisBaseCapability,
		   ifPhysAddress }
     STATUS      current
     DESCRIPTION
	 "This is an internal software error. RDB task was unable to create 
	 a semaphore for mutual exclusion. This notification is only generated 
	 on the BSR 64000."
     ::= { rdnEvtNotifications 2473920048 }

rdnEvtRdbUnknownTableFromPeer NOTIFICATION-TYPE
     OBJECTS     { docsDevEvLevel, 
                   docsDevEvId, 
                   docsDevEvText, 
                   docsIfDocsisBaseCapability,
		   ifPhysAddress }
     STATUS      current
     DESCRIPTION
	 "Software versions may not be the same on the Primary and
	 the Spare. This may cause a loss of data on replications of
	 the redundancy databases and lead to serious problem on a
	 switchover. Upgrade the software so that the Primary and Spare
	 have matching software versions."
     ::= { rdnEvtNotifications 2473920145 }

rdnEvtRdbDefineTableNotEnoughMemory NOTIFICATION-TYPE
     OBJECTS     { docsDevEvLevel, 
                   docsDevEvId, 
                   docsDevEvText, 
                   docsIfDocsisBaseCapability,
		   ifPhysAddress }
     STATUS      current
     DESCRIPTION
	 "Not Enough Memory to register a new table with RDB. This could
	 lead loss of data on replications of the redundancy databases and 
	 lead to serious problem on a switchovers."
     ::= { rdnEvtNotifications 2473920174 }

rdnEvtRdbMsgBufAllocFailure NOTIFICATION-TYPE
     OBJECTS     { docsDevEvLevel, 
                   docsDevEvId, 
                   docsDevEvText, 
                   docsIfDocsisBaseCapability,
		   ifPhysAddress }
     STATUS      current
     DESCRIPTION
	 "Not Enough Memory to create message buffers in RDB. This could
	 lead loss of data on replications of the redundancy databases and 
	 lead to serious problem on a switchovers. Reset the card 
	 reporting this problem."
     ::= { rdnEvtNotifications 2473920179 }

rdnEvtRdbMemPoolAllocFailure NOTIFICATION-TYPE
     OBJECTS     { docsDevEvLevel, 
                   docsDevEvId, 
                   docsDevEvText, 
                   docsIfDocsisBaseCapability,
		   ifPhysAddress }
     STATUS      current
     DESCRIPTION
	 "Not Enough Memory to create storage for the runtime records.
	 This could lead to loss of data on replications of the 
	 redundancy databases and lead to serious problems on a switchover."
     ::= { rdnEvtNotifications 2473920185 }

rdnEvtRdbMallocFailure NOTIFICATION-TYPE
     OBJECTS     { docsDevEvLevel, 
                   docsDevEvId, 
                   docsDevEvText, 
                   docsIfDocsisBaseCapability,
		   ifPhysAddress }
     STATUS      current
     DESCRIPTION
	 "Memory allocation for internal RDB structure reported an error.
	 This card is most like running low on memory. Reset the card 
	 reporting this problem."
     ::= { rdnEvtNotifications 2473920186 }

rdnEvtDrmSpareCmtsActive NOTIFICATION-TYPE
     OBJECTS     { docsDevEvLevel, 
                   docsDevEvId, 
                   docsDevEvText, 
                   docsIfDocsisBaseCapability,
		   ifPhysAddress }
     STATUS      current
     DESCRIPTION
	 "This is reported when a Spare CMTS becomes active
	 for a redundant primary CMTS in a BSR 64000 chassis."
     ::= { rdnEvtNotifications 2473920312 }

rdnEvtDrmFailedAutoTakeover NOTIFICATION-TYPE
     OBJECTS     { docsDevEvLevel, 
                   docsDevEvId, 
                   docsDevEvText, 
                   docsIfDocsisBaseCapability,
		   ifPhysAddress }
     STATUS      current
     DESCRIPTION
	 "This is reported when a Primary CMTS goes down, and
	  an auto-takeover fails to make Spare CMTS become the
	  active CMTS in a BSR 64000 chassis."
      ::= { rdnEvtNotifications 2473920313 }

rdnEvtDrmFailedAutoGiveback NOTIFICATION-TYPE
     OBJECTS     { docsDevEvLevel, 
                   docsDevEvId, 
                   docsDevEvText, 
                   docsIfDocsisBaseCapability,
		   ifPhysAddress }
     STATUS      current
     DESCRIPTION
	 "This is reported when a active Spare CMTS goes down, and
	  an auto-giveback fails to make Primary CMTS become the
	  active CMTS in a BSR 64000 chassis."
      ::= { rdnEvtNotifications 2473920314 }

rdnEvtDrmSpareXmittersRcvrsMismatch NOTIFICATION-TYPE
     OBJECTS     { docsDevEvLevel, 
                   docsDevEvId, 
                   docsDevEvText, 
                   docsIfDocsisBaseCapability,
		   ifPhysAddress }
     STATUS      current
     DESCRIPTION
	 "This is reported when Spare CMTS has fewer transmitters or
	  receivers than a Primary CMTS. The Spare CMTS must have at 
	  least as many transmitters and receivers as each Primary CMTS
	  in order to have successful CMTS switchovers in a 
	  BSR 64000 chassis."
      ::= { rdnEvtNotifications 2473920315 }

rdnEvtDrmSpareDtxActive NOTIFICATION-TYPE
     OBJECTS     { docsDevEvLevel, 
                   docsDevEvId, 
                   docsDevEvText, 
                   docsIfDocsisBaseCapability,
		   ifPhysAddress }
     STATUS      current
     DESCRIPTION
	 "This is reported when a Spare DTX becomes active
	  for a redundant primary DTX in a BSR 64000 chassis."
      ::= { rdnEvtNotifications 2473920431}

rdnEvtDrmFailedDtxAutoTakeover NOTIFICATION-TYPE
     OBJECTS     { docsDevEvLevel, 
                   docsDevEvId, 
                   docsDevEvText, 
                   docsIfDocsisBaseCapability,
		   ifPhysAddress }
     STATUS      current
     DESCRIPTION
         "This is reported when a Primary DTX goes down, and
          an auto-takeover fails to make Spare DTX become the
          active DTX in a BSR 64000 chassis."
      ::= { rdnEvtNotifications 2473920432}

rdnEvtDrmFailedDtxAutoGiveback NOTIFICATION-TYPE
     OBJECTS     { docsDevEvLevel, 
                   docsDevEvId, 
                   docsDevEvText, 
                   docsIfDocsisBaseCapability,
		   ifPhysAddress }
     STATUS      current
     DESCRIPTION
         "This is reported when a active Spare DTX goes down, and
          an auto-giveback fails to make Primary DTX become the
          active DTX in a BSR 64000 chassis."
      ::= { rdnEvtNotifications 2473920433}

rdnEvtDrmSpareDrxActive NOTIFICATION-TYPE
     OBJECTS     { docsDevEvLevel,
                   docsDevEvId,
                   docsDevEvText,
                   docsIfDocsisBaseCapability,
                   ifPhysAddress }
     STATUS      current
     DESCRIPTION
         "This is reported when a Spare DRX becomes active
          for a redundant primary DRX in a BSR 64000 chassis."
      ::= { rdnEvtNotifications 2473920441}

rdnEvtDrmFailedDrxAutoTakeover NOTIFICATION-TYPE
     OBJECTS     { docsDevEvLevel,
                   docsDevEvId,
                   docsDevEvText,
                   docsIfDocsisBaseCapability,
                   ifPhysAddress }
     STATUS      current
     DESCRIPTION
         "This is reported when a Primary DRX goes down, and
          an auto-takeover fails to make Spare DRX become the
          active DRX in a BSR 64000 chassis."
      ::= { rdnEvtNotifications 2473920442}

rdnEvtDrmFailedDrxAutoGiveback NOTIFICATION-TYPE
     OBJECTS     { docsDevEvLevel,
                   docsDevEvId,
                   docsDevEvText,
                   docsIfDocsisBaseCapability,
                   ifPhysAddress }
     STATUS      current
     DESCRIPTION
         "This is reported when a active Spare DRX goes down, and
          an auto-giveback fails to make Primary DRX become the
          active DRX in a BSR 64000 chassis."
      ::= { rdnEvtNotifications 2473920443}

rdnEvtAccrtrRdbDefineTableFailure NOTIFICATION-TYPE
     OBJECTS     { docsDevEvLevel, 
                   docsDevEvId, 
                   docsDevEvText, 
                   docsIfDocsisBaseCapability,
		   ifPhysAddress }
     STATUS      current
     DESCRIPTION
	 "This is an internal software error. The Accrtr task was unable
	 to register a table with the Redundancy Runtime Record 
	 Database(RDB) for CMTS Redundancy."
     ::= { rdnEvtNotifications 2473920769 }

rdnEvtAccrtrRdbNextFailure NOTIFICATION-TYPE
     OBJECTS     { docsDevEvLevel, 
                   docsDevEvId, 
                   docsDevEvText, 
                   docsIfDocsisBaseCapability,
		   ifPhysAddress }
     STATUS      current
     DESCRIPTION
	 "This is an internal software error. The Accrtr task was unable
	 retrieve the next runtime record from Redundancy Runtime Record 
	 Database(RDB) for CMTS Redundancy."
     ::= { rdnEvtNotifications 2473920775 }

rdnEvtAccrtrNotFrozenLoad NOTIFICATION-TYPE
     OBJECTS     { docsDevEvLevel, 
                   docsDevEvId, 
                   docsDevEvText, 
                   docsIfDocsisBaseCapability,
		   ifPhysAddress }
     STATUS      current
     DESCRIPTION
	 "This is an internal software error. The Accrtr task was not frozen
	 when trying to load the runtime records for a particular cable
	 modem during a CMTS Switchover."
     ::= { rdnEvtNotifications 2473920781 }

rdnEvtArdrtrRdbDefineTableFailure NOTIFICATION-TYPE
     OBJECTS     { docsDevEvLevel, 
                   docsDevEvId, 
                   docsDevEvText, 
                   docsIfDocsisBaseCapability,
		   ifPhysAddress }
     STATUS      current
     DESCRIPTION
	 "This is an internal software error. The Address Resolution 
	 Database Run Time Records(Ardrtr) task was unable
	 to register a table with the Redundancy Runtime Record 
	 Database(RDB) for CMTS Redundancy."
     ::= { rdnEvtNotifications 2473921025 }

rdnEvtArdrtrRdbNextFailure NOTIFICATION-TYPE
     OBJECTS     { docsDevEvLevel, 
                   docsDevEvId, 
                   docsDevEvText, 
                   docsIfDocsisBaseCapability,
		   ifPhysAddress }
     STATUS      current
     DESCRIPTION
	 "This is an internal software error. The Address Resolution 
	 Database Run Time Records(Ardrtr) task was unable
	 retrieve the next runtime record from Redundancy Runtime Record 
	 Database(RDB) for CMTS Redundancy."
     ::= { rdnEvtNotifications 2473921031 }

rdnEvtArdrtrNotFrozenLoad NOTIFICATION-TYPE
     OBJECTS     { docsDevEvLevel, 
                   docsDevEvId, 
                   docsDevEvText, 
                   docsIfDocsisBaseCapability,
		   ifPhysAddress }
     STATUS      current
     DESCRIPTION
	 "This is an internal software error. The Address Resolution 
	 Database Run Time Records(Ardrtr) task was not frozen
	 when trying to load the runtime records for a particular cable
	 modem during a CMTS Switchover."
     ::= { rdnEvtNotifications 2473921035 }

rdnEvtArdrtrLoadFailure NOTIFICATION-TYPE
     OBJECTS     { docsDevEvLevel, 
                   docsDevEvId, 
                   docsDevEvText, 
                   docsIfDocsisBaseCapability,
		   ifPhysAddress }
     STATUS      current
     DESCRIPTION
	 "This is an internal software error. The Address Resolution 
	 Database Run Time Records(Ardrtr) task was unable to load
	 the runtime records do to an invalid cable modem Id during a 
	 CMTS Switchover."
     ::= { rdnEvtNotifications 2473921039 }

rdnEvtMacmgrValidateCmError NOTIFICATION-TYPE
     OBJECTS     { docsDevEvLevel, 
                   docsDevEvId, 
                   docsDevEvText, 
                   docsIfDocsisBaseCapability,
		   ifPhysAddress }
     STATUS      current
     DESCRIPTION
	 "This is an internal software error. The Macmgr task received 
	 a 'Validate Cable Modem' message from BPI, which contained an 
	 invalid cable modem index."
     ::= { rdnEvtNotifications 2473921541 }

rdnEvtMacmgrInvalidateCmError NOTIFICATION-TYPE
     OBJECTS     { docsDevEvLevel, 
                   docsDevEvId, 
                   docsDevEvText, 
                   docsIfDocsisBaseCapability,
		   ifPhysAddress }
     STATUS      current
     DESCRIPTION
	 "This is an internal software error. The Macmgr task received 
	 a 'Invalidate Cable Modem' message from BPI, which contained an 
	 invalid cable modem index."
     ::= { rdnEvtNotifications 2473921568 }

rdnEvtMacmgrNullPtr NOTIFICATION-TYPE
     OBJECTS     { docsDevEvLevel, 
                   docsDevEvId, 
                   docsDevEvText, 
                   docsIfDocsisBaseCapability,
		   ifPhysAddress }
     STATUS      current
     DESCRIPTION
	 "This is an internal software error. The Macmgr task called a 
	 function with a null pointer."
     ::= { rdnEvtNotifications 2473921577 }

rdnEvtDocsifCmtsCmIndexAddFreeListFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to add
	 the docsIfCmtsCmStatusIndex to a list of indexes available to use."
     ::= { rdnEvtNotifications 2473924360 }

rdnEvtDocsifCmtsCmIndexDelFreeListFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to remove
	 the docsIfCmtsCmStatusIndex from a list of indexes available to use."
     ::= { rdnEvtNotifications 2473924362 }

rdnEvtDocsifCmtsCmIndexReloadFreeListFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to reload
	 the docsIfCmtsCmStatusIndex from a list of indexes available to use."
     ::= { rdnEvtNotifications 2473924371 }

rdnEvtUpcTaskSpawnFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to create the 
	 Up Converter(UPC) task."
     ::= { rdnEvtNotifications 2473925121 }

rdnEvtUpcMsgQCreateFailure NOTIFICATION-TYPE
     OBJECTS     { docsDevEvLevel, 
                   docsDevEvId, 
                   docsDevEvText, 
                   docsIfDocsisBaseCapability,
		   ifPhysAddress }
     STATUS      current
     DESCRIPTION
	 "This is an internal software error. Unable to create the UPC task's
	 message queue."
     ::= { rdnEvtNotifications 2473925122 }

rdnEvtUpcMsgQReceiveFailure NOTIFICATION-TYPE
     OBJECTS     { docsDevEvLevel, 
                   docsDevEvId, 
                   docsDevEvText, 
                   docsIfDocsisBaseCapability,
		   ifPhysAddress }
     STATUS      current
     DESCRIPTION
	 "This is an internal software error. UPC task's caught an error
	 when it was receiving a message."
	 ::= { rdnEvtNotifications 2473925123 }

rdnEvtUpcRegTaskMonFailure NOTIFICATION-TYPE
     OBJECTS     { docsDevEvLevel, 
                   docsDevEvId, 
                   docsDevEvText, 
                   docsIfDocsisBaseCapability,
		   ifPhysAddress }
     STATUS      current
     DESCRIPTION
	 "This is an internal software error. UPC task was unable to register 
	 with the task monitor."
     ::= { rdnEvtNotifications 2473925124 }

rdnEvtUpcRxUnexpectedMsgType NOTIFICATION-TYPE
     OBJECTS     { docsDevEvLevel, 
                   docsDevEvId, 
                   docsDevEvText, 
                   docsIfDocsisBaseCapability,
		   ifPhysAddress }
     STATUS      current
     DESCRIPTION
	 "This is an internal software error. UPC task received an unexpected
	 message type."
     ::= { rdnEvtNotifications 2473925126 }

rdnEvtUpcRxUnexpectedMsgSubType NOTIFICATION-TYPE
     OBJECTS     { docsDevEvLevel, 
                   docsDevEvId, 
                   docsDevEvText, 
                   docsIfDocsisBaseCapability,
		   ifPhysAddress }
     STATUS      current
     DESCRIPTION
	 "This is an internal software error. UPC task received an unexpected
	 message sub-type."
     ::= { rdnEvtNotifications 2473925127 }

rdnEvtUpcSemCreateFailure NOTIFICATION-TYPE
     OBJECTS     { docsDevEvLevel, 
                   docsDevEvId, 
                   docsDevEvText, 
                   docsIfDocsisBaseCapability,
		   ifPhysAddress }
     STATUS      current
     DESCRIPTION
	 "This is an internal software error. UPC task was unable to create a
	 semaphore for mutual exclusion."
     ::= { rdnEvtNotifications 2473925142 }

rdnEvtSvcfloNullPtr NOTIFICATION-TYPE
     OBJECTS     { docsDevEvLevel, 
                   docsDevEvId, 
                   docsDevEvText, 
                   docsIfDocsisBaseCapability,
		   ifPhysAddress }
     STATUS      current
     DESCRIPTION
	 "This is an internal software error. The SVCFLO task called a 
	 function will a null pointer."
     ::= { rdnEvtNotifications 2473925891 }

rdnEvtSvcfloWriteNextFlowTlvError NOTIFICATION-TYPE
     OBJECTS     { docsDevEvLevel, 
                   docsDevEvId, 
                   docsDevEvText, 
                   docsIfDocsisBaseCapability,
		   ifPhysAddress }
     STATUS      current
     DESCRIPTION
	 "This is an internal software error. The SVCFLO task
	 detected an error when trying to backup a Service Flow TLV for
	 CMTS Redundancy. This TLV is not replicated to the peer CMTS,
	 and could cause this modem to de-register on a CMTS switchover."
     ::= { rdnEvtNotifications 2473925895 }

rdnEvtSvcfloSidInsertFailure NOTIFICATION-TYPE
     OBJECTS     { docsDevEvLevel, 
                   docsDevEvId, 
                   docsDevEvText, 
                   docsIfDocsisBaseCapability,
		   ifPhysAddress }
     STATUS      current
     DESCRIPTION
	 "This is an internal software error. The SVCFLO task
	 was unable to store the cable modems Service Id (SID)."
     ::= { rdnEvtNotifications 2473925899 }

rdnEvtUbshaCollectionRspMallocError NOTIFICATION-TYPE
     OBJECTS     { docsDevEvLevel, 
                   docsDevEvId, 
                   docsDevEvText, 
                   docsIfDocsisBaseCapability,
		   ifPhysAddress }
     STATUS      current
     DESCRIPTION
	 "This is an internal software error. Failed to allocate memory during 
	 upstream channel sampling response."
     ::= { rdnEvtNotifications 2473927699 }

rdnEvtUbshaTaskSuspended NOTIFICATION-TYPE
     OBJECTS     { docsDevEvLevel, 
                   docsDevEvId, 
                   docsDevEvText, 
                   docsIfDocsisBaseCapability,
		   ifPhysAddress }
     STATUS      current
     DESCRIPTION
	 "This is an internal software error. The Upstream Bandwidth 
	 Scheduler(UBS) task suspended itself. Reset CMTS to clear the 
	 error."
     ::= { rdnEvtNotifications  2473927709 }


END
