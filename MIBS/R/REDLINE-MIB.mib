-- *****************************************************************
-- REDLINE-MIB:  Redline MIB root tree
-- ECO Rev 1.00
--
-- March 2002, Sinisa Djurkic, Claude Daniel Ndjouou
--
-- Copyright (c) 2002 by redline Communications, Inc.
-- All rights reserved.
-- 
-- *****************************************************************

REDLINE-MIB DEFINITIONS ::= BEGIN

IMPORTS
	enterprises,
	MODULE-IDENTITY,
	OBJECT-IDENTITY
		FROM SNMPv2-SMI;

redline MODULE-IDENTITY
	LAST-UPDATED "200506081750Z"
	ORGANIZATION "Redline Communications Inc."
	CONTACT-INFO
		"Editor:        Marek Koziol

		postal:        Redline Communications Inc.
		               302 Town Centre Blvd.
		               Markham, ON
		               Canada L3R 0E8

		phone:              +1 905 479-8344
		email:      mkoziol@redlinecommunications.com"
	DESCRIPTION
		"This file defines the private Redline Communications Inc. SNMP MIB extensions.

		Acknowledgements:
		Sinisa Djurkic, Claude Ndjouou  - Original Authors, Redline Communications Inc.
		Radu Salea                      - Redline Communications Inc.
		Radu Zak Savulian               - Redline Communications Inc."
	REVISION "200506081750Z"
	DESCRIPTION
		"Added redlineSystem and redlineTransmission root OIDs."
	REVISION "200111080000Z"
	DESCRIPTION
		"Author decided to split main mib module into project mibs."
	REVISION "200108120000Z"
	DESCRIPTION
		"Initial MIB definitions, snacc4j compilation passed."
	REVISION "200203130000Z"
	DESCRIPTION
		"Changed the mib oid tree"
	::= { enterprises 10728 }


redlineProducts OBJECT-IDENTITY
	STATUS current
	DESCRIPTION
		"redlineProducts is the root from  wich sysObjectID values are
		assigned.
		see REDLINE-PRODUCTS-MIB for more details"
	::= { redline 1 }

redlineMgmt OBJECT-IDENTITY
	STATUS current
	DESCRIPTION
		"The main subtree for new mib development."
	::= { redline 2 }

-- The root OID for Redline system MIBs.

redlineSystem OBJECT IDENTIFIER 	::= { redlineMgmt 1 }

-- The root OID for Redline interface MIBs.

redlineTransmission OBJECT IDENTIFIER 	::= { redlineMgmt 10 }

redlineExperiment OBJECT-IDENTITY
	STATUS current
	DESCRIPTION
		"Provides a root object identifier from which experimental mibs may
		be temporarily based"
	::= { redline 3 }

redlineAdmin OBJECT-IDENTITY
	STATUS current
	DESCRIPTION
		"redlineAdmin is for administratively assigned OBJECT-IDENTITYS,
		not associated with MIB objects"
	::= { redline 4 }

redlineModules OBJECT-IDENTITY
	STATUS current
	DESCRIPTION
		"redlineModules provides a root object identifier from which
		MODULE-IDENTITY values may be assigned."
	::= { redline 5 }

redlinePartners OBJECT-IDENTITY
	STATUS current
	DESCRIPTION
		"This is the root OBJECT-IDENTITY from which partner
		sysObjectID values may be assigned."
	::= { redline 6 }

redlineOtherEnterpises OBJECT-IDENTITY
	STATUS current
	DESCRIPTION
		"redlineOtherEnterprises provides a root object identifier
		from which mibs produced by other companies may be placed."
	::= { redline 7 }

redlineAgentCapability OBJECT-IDENTITY
	STATUS current
	DESCRIPTION
		"redlineAgentCapability provides a root object identifier
		from which AGENT-CAPABILITIES values may be assigned."
	::= { redline 8 }

END
