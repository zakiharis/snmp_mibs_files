RED-LION-RAM-MIB DEFINITIONS ::= BEGIN

-- INITIAL REQUIREMENTS:
-- RSSI /signal strength/Health of Cellular connectivity (Supported in new RED-LION-WIRELESS-MIB)
-- Health of internal components of device including:
-- power supply, (UNSUPPORTED)
-- temperature, (UNSUPPORTED)
-- Ethernet, (via MIB-II.interface.ifTable.<ifIndex>.ifAdminStatus)
-- cellular radio (via new RED-LION-WIRELESS-MIB::currentState or Activated)
-- Status of
-- VRRP, (via RED-LION-RAM-MIB::system.vrrp.*)
-- Ethernet, (via MIB-II.interface.ifTable.<ifIndex>.ifAdminStatus)
-- link state (via MIB-II.interface.ifTable.<ifIndex>.ifAdminStatus)
-- throughput information on active interfaces (MIB-II?)
-- Location information and serial numbers for inventory control (Defined in config, accessible via MIB-II)


IMPORTS
        enterprises     FROM RFC1155-SMI
        OBJECT-TYPE     FROM RFC-1212
        DisplayString   FROM RFC1213-MIB;

redlionram     OBJECT IDENTIFIER ::= {enterprises 1890}
system         OBJECT IDENTIFIER ::= {redlionram 1} -- Unit Information as Leaves. Sub-Systems (as defined in config.xml as branches)
unitInfo       OBJECT IDENTIFIER ::= {system 1}
cellular       OBJECT IDENTIFIER ::= {system 2}
trafficppp0    OBJECT IDENTIFIER ::= {system 3}
trafficwwan0   OBJECT IDENTIFIER ::= {system 4}
trafficeth0    OBJECT IDENTIFIER ::= {system 5}
trafficeth1    OBJECT IDENTIFIER ::= {system 6}
gpscurrent     OBJECT IDENTIFIER ::= {system 7}

unitDescription OBJECT-TYPE
  SYNTAX  DisplayString
  ACCESS  read-only
  STATUS  mandatory
  DESCRIPTION
          "Model Name (e.g. SN6600). DEFAULT: UNKNOWN"
  ::= {unitInfo 1}

unitSerialNumber OBJECT-TYPE
  SYNTAX  DisplayString
  ACCESS  read-only
  STATUS  mandatory
  DESCRIPTION
          "Serial Number (e.g. 6621-2517560325). DEFAULT: UNKNOWN"
  ::= {unitInfo 2}

unitFirmwareVersion OBJECT-TYPE
  SYNTAX  DisplayString
  ACCESS  read-only
  STATUS  mandatory
  DESCRIPTION
          "Firmware Version Number (e.g. v3.04rc33). DEFAULT: UNKNOWN"
  ::= {unitInfo 3}

unitName OBJECT-TYPE
  SYNTAX  DisplayString
  ACCESS  read-only
  STATUS  mandatory
  DESCRIPTION
          "Unit Name (e.g. RAM-0647e3 or User Prefered Name via GUI Access Settings). DEFAULT: UNKNOWN"
  ::= {unitInfo 4}

mdn OBJECT-TYPE -- CELLMODEM_MDN=3144973013
  SYNTAX  DisplayString
  ACCESS  read-only
  STATUS  mandatory
  DESCRIPTION
          "Cellular Mobile Directory Number (e.g. (xxx)xxx-xxxx). DEFAULT: UNKNOWN"
  ::= {cellular 1}

minIMEI OBJECT-TYPE -- CELLMODEM_MIN_IMEI=3148530409
  SYNTAX  DisplayString
  ACCESS  read-only
  STATUS  mandatory
  DESCRIPTION
          "Cellular Intl Mobile Equipment Identifier  DEFAULT: UNKNOWN"
  ::= {cellular 2}

nai OBJECT-TYPE -- CELLMODEM_NAI=redlionram05@sprintpcs.com
  SYNTAX  DisplayString
  ACCESS  read-only
  STATUS  mandatory
  DESCRIPTION
          "Cellular Network Acces Identifier. DEFAULT: UNKNOWN"
  ::= {cellular 3}

sipUser OBJECT-TYPE -- CELLMODEM_SIPUSER=0
  SYNTAX  INTEGER
  ACCESS  read-only
  STATUS  mandatory
  DESCRIPTION
          "Cellular Session Initiation Protocol User. DEFAULT: -1"
  ::= {cellular 4}

sid OBJECT-TYPE -- CELLMODEM_SID=4139
  SYNTAX  INTEGER
  ACCESS  read-only
  STATUS  mandatory

  DESCRIPTION
          "Cellular System ID. DEFAULT: -1"
  ::= {cellular 5}

nid OBJECT-TYPE -- CELLMODEM_NID=65535
  SYNTAX  INTEGER
  ACCESS  read-only
  STATUS  mandatory
  DESCRIPTION
          "Cellular Network Identifier. DEFAULT: -1"
  ::= {cellular 6}

prl OBJECT-TYPE -- CELLMODEM_PRL_VERSION=60754
  SYNTAX  INTEGER
  ACCESS  read-only
  STATUS  mandatory
  DESCRIPTION
          "Cellular Preferred Roaming List. DEFAULT: -1"
  ::= {cellular 7}

activated OBJECT-TYPE -- CELLMODEM_CARD_ACTIVATED=yes
  SYNTAX  INTEGER -- {unknown(-1), no(0), yes(1)}
  ACCESS  read-only
  STATUS  mandatory
  DESCRIPTION
          "Cellular module activation status. DEFAULT: -1"
  ::= {cellular 8}

omaSupported OBJECT-TYPE -- CELLMODEM_OMA_SUPPORTED=yes
  SYNTAX  INTEGER -- {unknown(-1), no(0), yes(1)}
  ACCESS  read-only
  STATUS  mandatory
  DESCRIPTION
          "Cellular OMA Supported status. DEFAULT: -1"
  ::= {cellular 9}

currentMipProfile OBJECT-TYPE -- CELLMODEM_CURRENT_MIP_PROFILE=1
  SYNTAX  INTEGER
  ACCESS  read-only
  STATUS  mandatory
  DESCRIPTION
          "Cellular Mobile IP Profile. DEFAULT: -1"
  ::= {cellular 10}

esn OBJECT-TYPE -- CELLMODEM_ESN=60A12A55
  SYNTAX  DisplayString
  ACCESS  read-only
  STATUS  mandatory
  DESCRIPTION
          "Cellular Module Electronic Serial Number. DEFAULT: UNKNOWN"
  ::= {cellular 11}

pesn OBJECT-TYPE -- CELLMODEM_PESN=A5CB0001
  SYNTAX  DisplayString
  ACCESS  read-only
  STATUS  mandatory
  DESCRIPTION
          "Cellular Module Pseudo ESN. DEFAULT: UNKNOWN"
  ::= {cellular 12}

meid OBJECT-TYPE -- CELLMODEM_MEID=4D7-25D280D9
  SYNTAX  DisplayString
  ACCESS  read-only
  STATUS  mandatory
  DESCRIPTION
          "Cellular Mobile Equipment Identifier. DEFAULT: UNKNOWN"
  ::= {cellular 13}

vendor OBJECT-TYPE -- CELLMODEM_MANU=Sierra Wireless
  SYNTAX  DisplayString
  ACCESS  read-only
  STATUS  mandatory
  DESCRIPTION
          "Cellular Module manufacturer. DEFAULT: UNKNOWN"
  ::= {cellular 14}

modelName OBJECT-TYPE -- CELLMODEM_MODEL=sierra598U
  SYNTAX  DisplayString
  ACCESS  read-only
  STATUS  mandatory
  DESCRIPTION
          "The vendor-provided model name of the modem/card/module (e.g. sierra598U). DEFAULT: UNKNOWN"
  ::= {cellular 15}

fwVersion OBJECT-TYPE -- CELLMODEM_FIRMWARE_V=p2511202
  SYNTAX  DisplayString
  ACCESS  read-only
  STATUS  mandatory
  DESCRIPTION
          "Cellular Module Firmware version #. DEFAULT: UNKNOWN"
  ::= {cellular 16}

hwVersion OBJECT-TYPE -- CELLMODEM_HARDWARE_V=T598 Rev 1.0
  SYNTAX  DisplayString
  ACCESS  read-only
  STATUS  mandatory
  DESCRIPTION
          "Cellular Module hardware version #. DEFAULT: UNKNOWN"
  ::= {cellular 17}

carrier OBJECT-TYPE -- CELLMODEM_CARRIER=Sprint
  SYNTAX  DisplayString
  ACCESS  read-only
  STATUS  mandatory
  DESCRIPTION
          "Cellular Service Provider. DEFAULT: UNKNOWN"
  ::= {cellular 18}

lowRssi OBJECT-TYPE -- CELLMODEM_LOWSPEED_RSSI=73
  SYNTAX  INTEGER
  ACCESS  read-only
  STATUS  mandatory
  DESCRIPTION
          "Cellular Low Speed received signal strenth indication. DEFAULT: 0"
  ::= {cellular 19}

lowEcio OBJECT-TYPE -- CELLMODEM_LOWSPEED_ECIO=9
  SYNTAX  INTEGER
  ACCESS  read-only
  STATUS  mandatory
  DESCRIPTION
          "Cellular Low Speed EC/IO. DEFAULT: 0"
  ::= {cellular 20}

highRssi OBJECT-TYPE -- CELLMODEM_HIGHSPEED_RSSI=73
  SYNTAX  INTEGER
  ACCESS  read-only
  STATUS  mandatory
  DESCRIPTION
          "Cellular High Speed received signal strenth indication. DEFAULT: 0"
  ::= {cellular 21}

highEcio OBJECT-TYPE -- CELLMODEM_HIGHSPEED_ECIO=8
  SYNTAX  INTEGER
  ACCESS  read-only
  STATUS  mandatory
  DESCRIPTION
          "Cellular High Speed EC/IO. DEFAULT: 0"
  ::= {cellular 22}

currentRssi OBJECT-TYPE -- CELLMODEM_CURRENT_RSSI=73
  SYNTAX  INTEGER
  ACCESS  read-only
  STATUS  mandatory
  DESCRIPTION
          "Cellular Current Received Signal Strenth Indication. DEFAULT: 0"
  ::= {cellular 23}

currentEcio OBJECT-TYPE -- CELLMODEM_CURRENT_ECIO=8
  SYNTAX  INTEGER
  ACCESS  read-only
  STATUS  mandatory
  DESCRIPTION
          "Cellular Current EC/IO. DEFAULT: 0"
  ::= {cellular 24}

svcType OBJECT-TYPE -- CELLMODEM_SERVICE_TYPE=EVDO REV: A
  SYNTAX  DisplayString
  ACCESS  read-only
  STATUS  mandatory
  DESCRIPTION
          "Cellular Service Type. DEFAULT: UNKNOWN"
  ::= {cellular 25}

currentChannel OBJECT-TYPE -- CELLMODEM_CURRENT_CHAN=625
  SYNTAX  INTEGER
  ACCESS  read-only
  STATUS  mandatory
  DESCRIPTION
          "Cellular Channel. DEFAULT: -1"
  ::= {cellular 29}

cdmaType OBJECT-TYPE -- CELLMODEM_CDMA_TYPE=Digital
  SYNTAX  DisplayString
  ACCESS  read-only
  STATUS  mandatory
  DESCRIPTION
          "Cellular CDMA Type (e.g. None, Analog, Digital). DEFAULT: UNKNOWN"
  ::= {cellular 30}

hdrType OBJECT-TYPE -- CELLMODEM_HDR_TYPE=RevA
  SYNTAX  DisplayString
  ACCESS  read-only
  STATUS  mandatory
  DESCRIPTION
          "Cellular HDR (e.g. Unknown, None, Rev0, RevA). DEFAULT: UNKNOWN"
  ::= {cellular 31}

cdmaRoaming OBJECT-TYPE -- CELLMODEM_CDMA_ROAMING=Home
  SYNTAX  DisplayString
  ACCESS  read-only
  STATUS  mandatory
  DESCRIPTION
          "Cellular Roaming indicator - CDMA. DEFAULT: UNKNOWN"
  ::= {cellular 32}

hdrRoaming OBJECT-TYPE -- CELLMODEM_HDR_ROAMING=None
  SYNTAX  DisplayString
  ACCESS  read-only
  STATUS  mandatory
  DESCRIPTION
          "Cellular Roaming indicator - EVDO. DEFAULT: UNKNOWN"
  ::= {cellular 33}

roaming OBJECT-TYPE -- CELLMODEM_ROAMING=0
  SYNTAX  INTEGER -- {unknown(-1), no(0), yes(1)}
  ACCESS  read-only
  STATUS  mandatory
  DESCRIPTION
          "Cellular current roaming status. DEFAULT: -1"
  ::= {cellular 34}

currentState OBJECT-TYPE -- CELLMODEM_CURRENT_STATE=Connected
  SYNTAX  INTEGER -- {unknown(-1), disconnected(0), connected(1)}
  ACCESS  read-only
  STATUS  mandatory
  DESCRIPTION
          "Cellular state (e.g. connecting, dormant, connected, disconnected, error, callincoming). DEFAULT: -1"
  ::= {cellular 35}

speedPref OBJECT-TYPE -- CELLMODEM_SPEEDPREF=Automatic
  SYNTAX  DisplayString
  ACCESS  read-only
  STATUS  mandatory
  DESCRIPTION
          "Cellular Module speed pref. DEFAULT: UNKNOWN"
  ::= {cellular 36}

roamPref OBJECT-TYPE -- CELLMODEM_ROAMPREF=HomePreferred - AUTO
  SYNTAX  DisplayString
  ACCESS  read-only
  STATUS  mandatory
  DESCRIPTION
          "Cellular Module roaming pref. DEFAULT: UNKNOWN"
  ::= {cellular 37}

devName OBJECT-TYPE -- the /dev/name
  SYNTAX  DisplayString
  ACCESS  read-only
  STATUS  mandatory
  DESCRIPTION
          "The device name as presented by the operating system (e.g. /dev/ttyUSB0). DEFAULT: UNKNOWN"
  ::= {cellular 38}

ifName OBJECT-TYPE -- the ifEntry name
  SYNTAX  DisplayString
  ACCESS  read-only
  STATUS  mandatory
  DESCRIPTION
          "The cellular interface name, if known, as presented by the operating system (e.g. ppp0). DEFAULT: UNKNOWN"
  ::= {cellular 39}

txCount OBJECT-TYPE -- transmitted bytes
  SYNTAX  INTEGER
  ACCESS  read-only
  STATUS  mandatory
  DESCRIPTION
          "Cellular Module TX Byte Count, updated every 30 mins. DEFAULT: -1"
  ::= {cellular 40}

rxCount OBJECT-TYPE -- received bytes
  SYNTAX  INTEGER
  ACCESS  read-only
  STATUS  mandatory
  DESCRIPTION
          "Cellular Module RX Byte Count, updated every 30 mins.. DEFAULT: -1"
  ::= {cellular 41}

gprsState OBJECT-TYPE -- CELLMODEM_GPRS_STATE
  SYNTAX DisplayString
  ACCESS read-only
  STATUS mandatory
  DESCRIPTION
          "Cellular GPRS State. DEFAULT: UNKNOWN"
  ::= {cellular 42}

rxLevel OBJECT-TYPE -- CELLMODEM_RX_LEVEL
  SYNTAX DisplayString
  ACCESS read-only
  STATUS mandatory
  DESCRIPTION
          "Cellular RX Level. DEFAULT: UNKNOWN"
  ::= {cellular 43}

servingCell OBJECT-TYPE -- CELLMODEM_SERVING_CELL
  SYNTAX DisplayString
  ACCESS read-only
  STATUS mandatory
  DESCRIPTION
          "Cellular Serving Cell. DEFAULT: UNKNOWN"
  ::= {cellular 44}

rccState OBJECT-TYPE -- CELLMODEM_RCC_STATE
  SYNTAX DisplayString
  ACCESS read-only
  STATUS mandatory
  DESCRIPTION
          "Cellular RCC State. DEFAULT: UNKNOWN"
  ::= {cellular 45}

gsmChannel OBJECT-TYPE -- CELLMODEM_GSM_CHANNEL
  SYNTAX DisplayString
  ACCESS read-only
  STATUS mandatory
  DESCRIPTION
          "Cellular GSM Channel. DEFAULT: UNKNOWN"
  ::= {cellular 46}

psState OBJECT-TYPE -- CELLMODEM_PS_STATE
  SYNTAX DisplayString
  ACCESS read-only
  STATUS mandatory
  DESCRIPTION
          "Cellular PS State. DEFAULT: UNKNOWN"
  ::= {cellular 47}

mode OBJECT-TYPE -- CELLMODEM_MODE
  SYNTAX DisplayString
  ACCESS read-only
  STATUS mandatory
  DESCRIPTION
          "Cellular Mode. DEFAULT: UNKNOWN"
  ::= {cellular 48}

temperature OBJECT-TYPE -- CELLMODEM_TEMPRATURE
  SYNTAX DisplayString
  ACCESS read-only
  STATUS mandatory
  DESCRIPTION
          "Cellular Module Temp (not available on all modules). DEFAULT: UNKNOWN"
  ::= {cellular 49}

simContextApn0 OBJECT-TYPE -- CELLMODEM_SIM_CONT_APN0
  SYNTAX DisplayString
  ACCESS read-only
  STATUS mandatory
  DESCRIPTION
          "Cellular SIM APN 0. DEFAULT: UNKNOWN"
  ::= {cellular 50}

simContextApn1 OBJECT-TYPE -- CELLMODEM_SIM_CONT_APN1
  SYNTAX DisplayString
  ACCESS read-only
  STATUS mandatory
  DESCRIPTION
          "Cellular SIM APN 1. DEFAULT: UNKNOWN"
  ::= {cellular 51}

simStatus OBJECT-TYPE -- CELLMODEM_SIM_STATUS
  SYNTAX DisplayString
  ACCESS read-only
  STATUS mandatory
  DESCRIPTION
          "Cellular SIM Status. DEFAULT: UNKNOWN"
  ::= {cellular 52}

serviceDomain OBJECT-TYPE -- CELLMODEM_SERVICE_DOMAIN
  SYNTAX DisplayString
  ACCESS read-only
  STATUS mandatory
  DESCRIPTION
          "Cellular Service Domain. DEFAULT: UNKNOWN"
  ::= {cellular 53}

availServiceType OBJECT-TYPE -- CELLMODEM_AVAIL_SERVICE_TYPE
  SYNTAX DisplayString
  ACCESS read-only
  STATUS mandatory
  DESCRIPTION
          "Cellular Available Service Type. DEFAULT: UNKNOWN"
  ::= {cellular 54}

wCdmaL1State OBJECT-TYPE -- CELLMODEM_WCDMA_L1_STATE
  SYNTAX DisplayString
  ACCESS read-only
  STATUS mandatory
  DESCRIPTION
          "Cellular WCDMA L1 State. DEFAULT: UNKNOWN"
  ::= {cellular 55}

mmcsState OBJECT-TYPE -- CELLMODEM_MM_CS_STATE
  SYNTAX DisplayString
  ACCESS read-only
  STATUS mandatory
  DESCRIPTION
          "Cellular MM CS State. DEFAULT: UNKNOWN"
  ::= {cellular 56}

gmmPsState OBJECT-TYPE -- CELLMODEM_GMM_PS_STATE
  SYNTAX DisplayString
  ACCESS read-only
  STATUS mandatory
  DESCRIPTION
          "Cellular GMM PS State. DEFAULT: UNKNOWN"
  ::= {cellular 57}

wCdmaChannel OBJECT-TYPE -- CELLMODEM_WCDMA_CHANNEL
  SYNTAX DisplayString
  ACCESS read-only
  STATUS mandatory
  DESCRIPTION
          "Cellular WCDMA Channel. DEFAULT: UNKNOWN"
  ::= {cellular 58}

wCdmaBand OBJECT-TYPE -- CELLMODEM_WCDMA_BAND
  SYNTAX DisplayString
  ACCESS read-only
  STATUS mandatory
  DESCRIPTION
          "Cellular WCDMA Band. DEFAULT: UNKNOWN"
  ::= {cellular 59}

systemMode OBJECT-TYPE -- CELLMODEM_SYSTEM_MODE
  SYNTAX DisplayString
  ACCESS read-only
  STATUS mandatory
  DESCRIPTION
          "Cellular System Mode. DEFAULT: UNKNOWN"
  ::= {cellular 60}

powerOnTime OBJECT-TYPE -- CELLMODEM_POWERON_TIME
  SYNTAX DisplayString
  ACCESS read-only
  STATUS mandatory
  DESCRIPTION
          "Cellular Power On Time. DEFAULT: UNKNOWN"
  ::= {cellular 61}

lowSpeedCsq OBJECT-TYPE -- CELLMODEM_LOWSPEED_CSQ
  SYNTAX DisplayString
  ACCESS read-only
  STATUS mandatory
  DESCRIPTION
          "Cellular Low Speed CSQ. DEFAULT: UNKNOWN"
  ::= {cellular 62}

highSpeedCsq OBJECT-TYPE -- CELLMODEM_HIGHSPEED_CSQ
  SYNTAX DisplayString
  ACCESS read-only
  STATUS mandatory
  DESCRIPTION
          "Cellular High Speed CSQ. DEFAULT: UNKNOWN"
  ::= {cellular 63}

band OBJECT-TYPE -- CELLMODEM_BAND
  SYNTAX DisplayString
  ACCESS read-only
  STATUS mandatory
  DESCRIPTION
          "Cellular Band. DEFAULT: UNKNOWN"
  ::= {cellular 64}

imei OBJECT-TYPE -- CELLMODEM_IMEI
  SYNTAX DisplayString
  ACCESS read-only
  STATUS mandatory
  DESCRIPTION
          "Cellular IMEI. DEFAULT: UNKNOWN"
  ::= {cellular 65}

simId OBJECT-TYPE -- CELLMODEM_SIM_ID
  SYNTAX DisplayString
  ACCESS read-only
  STATUS mandatory
  DESCRIPTION
          "Cellular SIM ID. DEFAULT: UNKNOWN"
  ::= {cellular 66}

carrPLMN OBJECT-TYPE -- CELLMODEM_CARRIER_PLMN=123456
  SYNTAX DisplayString
  ACCESS read-only
  STATUS mandatory
  DESCRIPTION
          "Carrier PLMN... DEFAULT: UNKNOWN"
  ::= {cellular 67}

rxLevelC0 OBJECT-TYPE -- CELLMODEM_RX_LEVEL_C0=:-62
  SYNTAX DisplayString
  ACCESS read-only
  STATUS mandatory
  DESCRIPTION
          "Receive Level C0... DEFAULT: UNKNOWN"
  ::= {cellular 68}

rxLevelC1 OBJECT-TYPE -- CELLMODEM_RX_LEVEL_C1=:-106
  SYNTAX DisplayString
  ACCESS read-only
  STATUS mandatory
  DESCRIPTION
          "Receive Level C1... DEFAULT: UNKNOWN"
  ::= {cellular 69}

locAreaCode OBJECT-TYPE -- CELLMODEM_LOCATION_AREA_CODE=5FB7 (24503)
  SYNTAX DisplayString
  ACCESS read-only
  STATUS mandatory
  DESCRIPTION
          "Location Area Code... DEFAULT: UNKNOWN"
  ::= {cellular 70}

lteBand OBJECT-TYPE -- CELLMODEM_LTE_BAND=B17
  SYNTAX DisplayString
  ACCESS read-only
  STATUS mandatory
  DESCRIPTION
          "LTE Band... DEFAULT: UNKNOWN"
  ::= {cellular 71}

lteRxChan OBJECT-TYPE -- CELLMODEM_LTE_RX_CHAN=5780
  SYNTAX DisplayString
  ACCESS read-only
  STATUS mandatory
  DESCRIPTION
          "LTE Receive Channel... DEFAULT: UNKNOWN"
  ::= {cellular 72}

lteTxChan OBJECT-TYPE -- CELLMODEM_LTE_TX_CHAN=65535
  SYNTAX DisplayString
  ACCESS read-only
  STATUS mandatory
  DESCRIPTION
          "LTE Transmit Channel... DEFAULT: UNKNOWN"
  ::= {cellular 73}

lteBW OBJECT-TYPE -- CELLMODEM_LTE_BW=10MHZ
  SYNTAX DisplayString
  ACCESS read-only
  STATUS mandatory
  DESCRIPTION
          "LTE Bandwidth... DEFAULT: UNKNOWN"
  ::= {cellular 74}

lteRSRP OBJECT-TYPE -- CELLMODEM_LTE_RSRP=-89
  SYNTAX DisplayString
  ACCESS read-only
  STATUS mandatory
  DESCRIPTION
          "LTE Reference Signal Received Power... DEFAULT: UNKNOWN"
  ::= {cellular 75}

lteRSRQ OBJECT-TYPE -- CELLMODEM_LTE_RSRQ=-8
  SYNTAX DisplayString
  ACCESS read-only
  STATUS mandatory
  DESCRIPTION
          "LTE Reference Signal Received Quality... DEFAULT: UNKNOWN"
  ::= {cellular 76}

lteTracAreaCode OBJECT-TYPE -- CELLMODEM_LTE_TRAC_AREA_CODE=6709 (26377)
  SYNTAX DisplayString
  ACCESS read-only
  STATUS mandatory
  DESCRIPTION
          "LTE Trac Area Code... DEFAULT: UNKNOWN"
  ::= {cellular 77}

creg OBJECT-TYPE -- CELLMODEM_CREG=Not registered, Searching
  SYNTAX DisplayString
  ACCESS read-only
  STATUS mandatory
  DESCRIPTION
          "Cellmodem CREG Not registered, Searching... DEFAULT: UNKNOWN"
  ::= {cellular 78}

cellularUpTime OBJECT-TYPE -- Cellular Up Time in Seconds
  SYNTAX INTEGER
  ACCESS read-only
  STATUS mandatory
  DESCRIPTION
          "Cellular Up Time in Seconds, DEFAULT: -1"
  ::= {cellular 79}

lteRSRPint OBJECT-TYPE -- CELLMODEM_LTE_RSRPint=-106
  SYNTAX INTEGER
  ACCESS read-only
  STATUS mandatory
  DESCRIPTION
          "LTE Reference Signal Received Power in Integer... DEFAULT: -1"
  ::= {cellular 80}

lteRSRQint OBJECT-TYPE -- CELLMODEM_LTE_RSRQint=-11
  SYNTAX INTEGER
  ACCESS read-only
  STATUS mandatory
  DESCRIPTION
          "LTE Reference Signal Received Quality in Integer... DEFAULT: -1"
  ::= {cellular 81}

lteSINRint OBJECT-TYPE -- CELLMODEM_LTE_SINRint=6
  SYNTAX INTEGER
  ACCESS read-only
  STATUS mandatory
  DESCRIPTION
          "LTE Signal to Interference Plus Noise Ratio in Integer... DEFAULT: -1"
  ::= {cellular 82}

todayRxPpp0 OBJECT-TYPE -- Vnstat Today Rx for PPP0 Interface
  SYNTAX DisplayString
  ACCESS read-only
  STATUS mandatory
  DESCRIPTION
          "Vnstat Today Rx for PPP0 Interface... DEFAULT: UNKNOWN"
  ::= {trafficppp0 1}

todayTxPpp0 OBJECT-TYPE -- Vnstat Today Tx for PPP0 Interface
  SYNTAX DisplayString
  ACCESS read-only
  STATUS mandatory
  DESCRIPTION
          "Vnstat Today Tx for PPP0 Interface... DEFAULT: UNKNOWN"
  ::= {trafficppp0 2}

todayTotalPpp0 OBJECT-TYPE -- Vnstat Today Total Rx/Tx for PPP0 Interface
  SYNTAX DisplayString
  ACCESS read-only
  STATUS mandatory
  DESCRIPTION
          "Vnstat Today Total Rx/Tx for PPP0 Interface... DEFAULT: UNKNOWN"
  ::= {trafficppp0 3}

yesterdayRxPpp0 OBJECT-TYPE -- Vnstat Yesterday Rx for PPP0 Interface
  SYNTAX DisplayString
  ACCESS read-only
  STATUS mandatory
  DESCRIPTION
          "Vnstat Yesterday Rx for PPP0 Interface... DEFAULT: UNKNOWN"
  ::= {trafficppp0 4}

yesterdayTxPpp0 OBJECT-TYPE -- Vnstat Yesterday Tx for PPP0 Interface
  SYNTAX DisplayString
  ACCESS read-only
  STATUS mandatory
  DESCRIPTION
          "Vnstat Yesterday Tx for PPP0 Interface... DEFAULT: UNKNOWN"
  ::= {trafficppp0 5}

yesterdayTotalPpp0 OBJECT-TYPE -- Vnstat Yesterday Total Rx/Tx for PPP0 Interface
  SYNTAX DisplayString
  ACCESS read-only
  STATUS mandatory
  DESCRIPTION
          "Vnstat Yesterday Total Rx/Tx for PPP0 Interface... DEFAULT: UNKNOWN"
  ::= {trafficppp0 6}

currMonthRxPpp0 OBJECT-TYPE -- Vnstat Current Month Rx for PPP0 Interface
  SYNTAX DisplayString
  ACCESS read-only
  STATUS mandatory
  DESCRIPTION
          "Vnstat Current Month Rx for PPP0 Interface... DEFAULT: UNKNOWN"
  ::= {trafficppp0 7}

currMonthTxPpp0 OBJECT-TYPE -- Vnstat Current Month Tx for PPP0 Interface
  SYNTAX DisplayString
  ACCESS read-only
  STATUS mandatory
  DESCRIPTION
          "Vnstat Current Month Tx for PPP0 Interface... DEFAULT: UNKNOWN"
  ::= {trafficppp0 8}

currMonthTotalPpp0 OBJECT-TYPE -- Vnstat Current Month Total Rx/Tx for PPP0 Interface
  SYNTAX DisplayString
  ACCESS read-only
  STATUS mandatory
  DESCRIPTION
          "Vnstat Current Month Total Rx/Tx for PPP0 Interface... DEFAULT: UNKNOWN"
  ::= {trafficppp0 9}

preMonthRxPpp0 OBJECT-TYPE -- Vnstat Previous Month Rx for PPP0 Interface
  SYNTAX DisplayString
  ACCESS read-only
  STATUS mandatory
  DESCRIPTION
          "Vnstat Previous Month Rx for PPP0 Interface... DEFAULT: UNKNOWN"
  ::= {trafficppp0 10}

preMonthTxPpp0 OBJECT-TYPE -- Vnstat Previous Month Tx for PPP0 Interface
  SYNTAX DisplayString
  ACCESS read-only
  STATUS mandatory
  DESCRIPTION
          "Vnstat Previous Month Tx for PPP0 Interface... DEFAULT: UNKNOWN"
  ::= {trafficppp0 11}

preMonthTotalPpp0 OBJECT-TYPE -- Vnstat Previous Month Total Rx/Tx for PPP0 Interface
  SYNTAX DisplayString
  ACCESS read-only
  STATUS mandatory
  DESCRIPTION
          "Vnstat Previous Month Total Rx/Tx for PPP0 Interface... DEFAULT: UNKNOWN"
  ::= {trafficppp0 12}

todayRxPpp0Kib OBJECT-TYPE -- Vnstat Today Rx for PPP0 Interface in Kib
  SYNTAX INTEGER
  ACCESS read-only
  STATUS mandatory
  DESCRIPTION
          "Vnstat Today Rx for PPP0 Interface in Kib... DEFAULT: -1"
  ::= {trafficppp0 13}

todayTxPpp0Kib OBJECT-TYPE -- Vnstat Today Tx for PPP0 Interface in Kib
  SYNTAX INTEGER
  ACCESS read-only
  STATUS mandatory
  DESCRIPTION
          "Vnstat Today Tx for PPP0 Interface in Kib... DEFAULT: -1"
  ::= {trafficppp0 14}

todayTotalPpp0Kib OBJECT-TYPE -- Vnstat Today Total Rx/Tx for PPP0 Interface in Kib
  SYNTAX INTEGER
  ACCESS read-only
  STATUS mandatory
  DESCRIPTION
          "Vnstat Today Total Rx/Tx for PPP0 Interface in Kib... DEFAULT: -1"
  ::= {trafficppp0 15}

yesterdayRxPpp0Kib OBJECT-TYPE -- Vnstat Yesterday Rx for PPP0 Interface in Kib
  SYNTAX INTEGER
  ACCESS read-only
  STATUS mandatory
  DESCRIPTION
          "Vnstat Yesterday Rx for PPP0 Interface in Kib... DEFAULT: -1"
  ::= {trafficppp0 16}

yesterdayTxPpp0Kib OBJECT-TYPE -- Vnstat Yesterday Tx for PPP0 Interface in Kib
  SYNTAX INTEGER
  ACCESS read-only
  STATUS mandatory
  DESCRIPTION
          "Vnstat Yesterday Tx for PPP0 Interface in Kib... DEFAULT: -1"
  ::= {trafficppp0 17}

yesterdayTotalPpp0Kib OBJECT-TYPE -- Vnstat Yesterday Total Rx/Tx for PPP0 Interface in Kib
  SYNTAX INTEGER
  ACCESS read-only
  STATUS mandatory
  DESCRIPTION
          "Vnstat Yesterday Total Rx/Tx for PPP0 Interface in Kib... DEFAULT: -1"
  ::= {trafficppp0 18}

currMonthRxPpp0Kib OBJECT-TYPE -- Vnstat Current Month Rx for PPP0 Interface in Kib
  SYNTAX INTEGER
  ACCESS read-only
  STATUS mandatory
  DESCRIPTION
          "Vnstat Current Month Rx for PPP0 Interface in Kib... DEFAULT: -1"
  ::= {trafficppp0 19}

currMonthTxPpp0Kib OBJECT-TYPE -- Vnstat Current Month Tx for PPP0 Interface in Kib
  SYNTAX INTEGER
  ACCESS read-only
  STATUS mandatory
  DESCRIPTION
          "Vnstat Current Month Tx for PPP0 Interface in Kib... DEFAULT: -1"
  ::= {trafficppp0 20}

currMonthTotalPpp0Kib OBJECT-TYPE -- Vnstat Current Month Total Rx/Tx for PPP0 Interface in Kib
  SYNTAX INTEGER
  ACCESS read-only
  STATUS mandatory
  DESCRIPTION
          "Vnstat Current Month Total Rx/Tx for PPP0 Interface in Kib... DEFAULT: -1"
  ::= {trafficppp0 21}

preMonthRxPpp0Kib OBJECT-TYPE -- Vnstat Previous Month Rx for PPP0 Interface in Kib
  SYNTAX INTEGER
  ACCESS read-only
  STATUS mandatory
  DESCRIPTION
          "Vnstat Previous Month Rx for PPP0 Interface in Kib... DEFAULT: -1"
  ::= {trafficppp0 22}

preMonthTxPpp0Kib OBJECT-TYPE -- Vnstat Previous Month Tx for PPP0 Interface in Kib
  SYNTAX INTEGER
  ACCESS read-only
  STATUS mandatory
  DESCRIPTION
          "Vnstat Previous Month Tx for PPP0 Interface in Kib... DEFAULT: -1"
  ::= {trafficppp0 23}

preMonthTotalPpp0Kib OBJECT-TYPE -- Vnstat Previous Month Total Rx/Tx for PPP0 Interface in Kib
  SYNTAX INTEGER
  ACCESS read-only
  STATUS mandatory
  DESCRIPTION
          "Vnstat Previous Month Total Rx/Tx for PPP0 Interface in Kib... DEFAULT: -1"
  ::= {trafficppp0 24}

todayRxWwan0 OBJECT-TYPE -- Vnstat Today Rx for WWAN0 Interface
  SYNTAX DisplayString
  ACCESS read-only
  STATUS mandatory
  DESCRIPTION
          "Vnstat Today Rx for WWAN0 Interface... DEFAULT: UNKNOWN"
  ::= {trafficwwan0 1}

todayTxWwan0 OBJECT-TYPE -- Vnstat Today Tx for WWAN0 Interface
  SYNTAX DisplayString
  ACCESS read-only
  STATUS mandatory
  DESCRIPTION
          "Vnstat Today Tx for WWAN0 Interface... DEFAULT: UNKNOWN"
  ::= {trafficwwan0 2}

todayTotalWwan0 OBJECT-TYPE -- Vnstat Today Total Rx/Tx for WWAN0 Interface
  SYNTAX DisplayString
  ACCESS read-only
  STATUS mandatory
  DESCRIPTION
          "Vnstat Today Total Rx/Tx for WWAN0 Interface... DEFAULT: UNKNOWN"
  ::= {trafficwwan0 3}

yesterdayRxWwan0 OBJECT-TYPE -- Vnstat Yesterday Rx for WWAN0 Interface
  SYNTAX DisplayString
  ACCESS read-only
  STATUS mandatory
  DESCRIPTION
          "Vnstat Yesterday Rx for WWAN0 Interface... DEFAULT: UNKNOWN"
  ::= {trafficwwan0 4}

yesterdayTxWwan0 OBJECT-TYPE -- Vnstat Yesterday Tx for WWAN0 Interface
  SYNTAX DisplayString
  ACCESS read-only
  STATUS mandatory
  DESCRIPTION
          "Vnstat Yesterday Tx for WWAN0 Interface... DEFAULT: UNKNOWN"
  ::= {trafficwwan0 5}

yesterdayTotalWwan0 OBJECT-TYPE -- Vnstat Yesterday Total Rx/Tx for WWAN0 Interface
  SYNTAX DisplayString
  ACCESS read-only
  STATUS mandatory
  DESCRIPTION
          "Vnstat Yesterday Total Rx/Tx for WWAN0 Interface... DEFAULT: UNKNOWN"
  ::= {trafficwwan0 6}

currMonthRxWwan0 OBJECT-TYPE -- Vnstat Current Month Rx for WWAN0 Interface
  SYNTAX DisplayString
  ACCESS read-only
  STATUS mandatory
  DESCRIPTION
          "Vnstat Current Month Rx for WWAN0 Interface... DEFAULT: UNKNOWN"
  ::= {trafficwwan0 7}

currMonthTxWwan0 OBJECT-TYPE -- Vnstat Current Month Tx for WWAN0 Interface
  SYNTAX DisplayString
  ACCESS read-only
  STATUS mandatory
  DESCRIPTION
          "Vnstat Current Month Tx for WWAN0 Interface... DEFAULT: UNKNOWN"
  ::= {trafficwwan0 8}

currMonthTotalWwan0 OBJECT-TYPE -- Vnstat Current Month Total Rx/Tx for WWAN0 Interface
  SYNTAX DisplayString
  ACCESS read-only
  STATUS mandatory
  DESCRIPTION
          "Vnstat Current Month Total Rx/Tx for WWAN0 Interface... DEFAULT: UNKNOWN"
  ::= {trafficwwan0 9}

preMonthRxWwan0 OBJECT-TYPE -- Vnstat Previous Month Rx for WWAN0 Interface
  SYNTAX DisplayString
  ACCESS read-only
  STATUS mandatory
  DESCRIPTION
          "Vnstat Previous Month Rx for WWAN0 Interface... DEFAULT: UNKNOWN"
  ::= {trafficwwan0 10}

preMonthTxWwan0 OBJECT-TYPE -- Vnstat Previous Month Tx for WWAN0 Interface
  SYNTAX DisplayString
  ACCESS read-only
  STATUS mandatory
  DESCRIPTION
          "Vnstat Previous Month Tx for WWAN0 Interface... DEFAULT: UNKNOWN"
  ::= {trafficwwan0 11}

preMonthTotalWwan0 OBJECT-TYPE -- Vnstat Previous Month Total Rx/Tx for WWAN0 Interface
  SYNTAX DisplayString
  ACCESS read-only
  STATUS mandatory
  DESCRIPTION
          "Vnstat Previous Month Total Rx/Tx for WWAN0 Interface... DEFAULT: UNKNOWN"
  ::= {trafficwwan0 12}

todayRxWwan0Kib OBJECT-TYPE -- Vnstat Today Rx for WWAN0 Interface in Kib
  SYNTAX INTEGER
  ACCESS read-only
  STATUS mandatory
  DESCRIPTION
          "Vnstat Today Rx for WWAN0 Interface in Kib... DEFAULT: -1"
  ::= {trafficwwan0 13}

todayTxWwan0Kib OBJECT-TYPE -- Vnstat Today Tx for WWAN0 Interface in Kib
  SYNTAX INTEGER
  ACCESS read-only
  STATUS mandatory
  DESCRIPTION
          "Vnstat Today Tx for WWAN0 Interface in Kib... DEFAULT: -1"
  ::= {trafficwwan0 14}

todayTotalWwan0Kib OBJECT-TYPE -- Vnstat Today Total Rx/Tx for WWAN0 Interface in Kib
  SYNTAX INTEGER
  ACCESS read-only
  STATUS mandatory
  DESCRIPTION
          "Vnstat Today Total Rx/Tx for WWAN0 Interface in Kib... DEFAULT: -1"
  ::= {trafficwwan0 15}

yesterdayRxWwan0Kib OBJECT-TYPE -- Vnstat Yesterday Rx for WWAN0 Interface in Kib
  SYNTAX INTEGER
  ACCESS read-only
  STATUS mandatory
  DESCRIPTION
          "Vnstat Yesterday Rx for WWAN0 Interface in Kib... DEFAULT: -1"
  ::= {trafficwwan0 16}

yesterdayTxWwan0Kib OBJECT-TYPE -- Vnstat Yesterday Tx for WWAN0 Interface in Kib
  SYNTAX INTEGER
  ACCESS read-only
  STATUS mandatory
  DESCRIPTION
          "Vnstat Yesterday Tx for WWAN0 Interface in Kib... DEFAULT: -1"
  ::= {trafficwwan0 17}

yesterdayTotalWwan0Kib OBJECT-TYPE -- Vnstat Yesterday Total Rx/Tx for WWAN0 Interface in Kib
  SYNTAX INTEGER
  ACCESS read-only
  STATUS mandatory
  DESCRIPTION
          "Vnstat Yesterday Total Rx/Tx for WWAN0 Interface in Kib... DEFAULT: -1"
  ::= {trafficwwan0 18}

currMonthRxWwan0Kib OBJECT-TYPE -- Vnstat Current Month Rx for WWAN0 Interface in Kib
  SYNTAX INTEGER
  ACCESS read-only
  STATUS mandatory
  DESCRIPTION
          "Vnstat Current Month Rx for WWAN0 Interface in Kib... DEFAULT: -1"
  ::= {trafficwwan0 19}

currMonthTxWwan0Kib OBJECT-TYPE -- Vnstat Current Month Tx for WWAN0 Interface in Kib
  SYNTAX INTEGER
  ACCESS read-only
  STATUS mandatory
  DESCRIPTION
          "Vnstat Current Month Tx for WWAN0 Interface in Kib... DEFAULT: -1"
  ::= {trafficwwan0 20}

currMonthTotalWwan0Kib OBJECT-TYPE -- Vnstat Current Month Total Rx/Tx for WWAN0 Interface in Kib
  SYNTAX INTEGER
  ACCESS read-only
  STATUS mandatory
  DESCRIPTION
          "Vnstat Current Month Total Rx/Tx for WWAN0 Interface in Kib... DEFAULT: -1"
  ::= {trafficwwan0 21}

preMonthRxWwan0Kib OBJECT-TYPE -- Vnstat Previous Month Rx for WWAN0 Interface in Kib
  SYNTAX INTEGER
  ACCESS read-only
  STATUS mandatory
  DESCRIPTION
          "Vnstat Previous Month Rx for WWAN0 Interface in Kib... DEFAULT: -1"
  ::= {trafficwwan0 22}

preMonthTxWwan0Kib OBJECT-TYPE -- Vnstat Previous Month Tx for WWAN0 Interface in Kib
  SYNTAX INTEGER
  ACCESS read-only
  STATUS mandatory
  DESCRIPTION
          "Vnstat Previous Month Tx for WWAN0 Interface in Kib... DEFAULT: -1"
  ::= {trafficwwan0 23}

preMonthTotalWwan0Kib OBJECT-TYPE -- Vnstat Previous Month Total Rx/Tx for WWAN0 Interface in Kib
  SYNTAX INTEGER
  ACCESS read-only
  STATUS mandatory
  DESCRIPTION
          "Vnstat Previous Month Total Rx/Tx for WWAN0 Interface in Kib... DEFAULT: -1"
  ::= {trafficwwan0 24}


todayRxEth0 OBJECT-TYPE -- Vnstat Today Rx for Eth0 Interface
  SYNTAX DisplayString
  ACCESS read-only
  STATUS mandatory
  DESCRIPTION
          "Vnstat Today Rx for Eth0 Interface... DEFAULT: UNKNOWN"
  ::= {trafficeth0 1}

todayTxEth0 OBJECT-TYPE -- Vnstat Today Tx for Eth0 Interface
  SYNTAX DisplayString
  ACCESS read-only
  STATUS mandatory
  DESCRIPTION
          "Vnstat Today Tx for Eth0 Interface... DEFAULT: UNKNOWN"
  ::= {trafficeth0 2}

todayTotalEth0 OBJECT-TYPE -- Vnstat Today Total Rx/Tx for Eth0 Interface
  SYNTAX DisplayString
  ACCESS read-only
  STATUS mandatory
  DESCRIPTION
          "Vnstat Today Total Rx/Tx for Eth0 Interface... DEFAULT: UNKNOWN"
  ::= {trafficeth0 3}

yesterdayRxEth0 OBJECT-TYPE -- Vnstat Yesterday Rx for Eth0 Interface
  SYNTAX DisplayString
  ACCESS read-only
  STATUS mandatory
  DESCRIPTION
          "Vnstat Yesterday Rx for Eth0 Interface... DEFAULT: UNKNOWN"
  ::= {trafficeth0 4}

yesterdayTxEth0 OBJECT-TYPE -- Vnstat Yesterday Tx for Eth0 Interface
  SYNTAX DisplayString
  ACCESS read-only
  STATUS mandatory
  DESCRIPTION
          "Vnstat Yesterday Tx for Eth0 Interface... DEFAULT: UNKNOWN"
  ::= {trafficeth0 5}

yesterdayTotalEth0 OBJECT-TYPE -- Vnstat Yesterday Total Rx/Tx for Eth0 Interface
  SYNTAX DisplayString
  ACCESS read-only
  STATUS mandatory
  DESCRIPTION
          "Vnstat Yesterday Total Rx/Tx for Eth0 Interface... DEFAULT: UNKNOWN"
  ::= {trafficeth0 6}

currMonthRxEth0 OBJECT-TYPE -- Vnstat Current Month Rx for Eth0 Interface
  SYNTAX DisplayString
  ACCESS read-only
  STATUS mandatory
  DESCRIPTION
          "Vnstat Current Month Rx for Eth0 Interface... DEFAULT: UNKNOWN"
  ::= {trafficeth0 7}

currMonthTxEth0 OBJECT-TYPE -- Vnstat Current Month Tx for Eth0 Interface
  SYNTAX DisplayString
  ACCESS read-only
  STATUS mandatory
  DESCRIPTION
          "Vnstat Current Month Tx for Eth0 Interface... DEFAULT: UNKNOWN"
  ::= {trafficeth0 8}

currMonthTotalEth0 OBJECT-TYPE -- Vnstat Current Month Total Rx/Tx for Eth0 Interface
  SYNTAX DisplayString
  ACCESS read-only
  STATUS mandatory
  DESCRIPTION
          "Vnstat Current Month Total Rx/Tx for Eth0 Interface... DEFAULT: UNKNOWN"
  ::= {trafficeth0 9}

preMonthRxEth0 OBJECT-TYPE -- Vnstat Previous Month Rx for Eth0 Interface
  SYNTAX DisplayString
  ACCESS read-only
  STATUS mandatory
  DESCRIPTION
          "Vnstat Previous Month Rx for Eth0 Interface... DEFAULT: UNKNOWN"
  ::= {trafficeth0 10}

preMonthTxEth0 OBJECT-TYPE -- Vnstat Previous Month Tx for Eth0 Interface
  SYNTAX DisplayString
  ACCESS read-only
  STATUS mandatory
  DESCRIPTION
          "Vnstat Previous Month Tx for Eth0 Interface... DEFAULT: UNKNOWN"
  ::= {trafficeth0 11}

preMonthTotalEth0 OBJECT-TYPE -- Vnstat Previous Month Total Rx/Tx for Eth0 Interface
  SYNTAX DisplayString
  ACCESS read-only
  STATUS mandatory
  DESCRIPTION
          "Vnstat Previous Month Total Rx/Tx for Eth0 Interface... DEFAULT: UNKNOWN"
  ::= {trafficeth0 12}

todayRxEth0Kib OBJECT-TYPE -- Vnstat Today Rx for ETH0 Interface in Kib
  SYNTAX INTEGER
  ACCESS read-only
  STATUS mandatory
  DESCRIPTION
          "Vnstat Today Rx for ETH0 Interface in Kib... DEFAULT: -1"
  ::= {trafficeth0 13}

todayTxEth0Kib OBJECT-TYPE -- Vnstat Today Tx for ETH0 Interface in Kib
  SYNTAX INTEGER
  ACCESS read-only
  STATUS mandatory
  DESCRIPTION
          "Vnstat Today Tx for ETH0 Interface in Kib... DEFAULT: -1"
  ::= {trafficeth0 14}

todayTotalEth0Kib OBJECT-TYPE -- Vnstat Today Total Rx/Tx for ETH0 Interface in Kib
  SYNTAX INTEGER
  ACCESS read-only
  STATUS mandatory
  DESCRIPTION
          "Vnstat Today Total Rx/Tx for ETH0 Interface in Kib... DEFAULT: -1"
  ::= {trafficeth0 15}

yesterdayRxEth0Kib OBJECT-TYPE -- Vnstat Yesterday Rx for ETH0 Interface in Kib
  SYNTAX INTEGER
  ACCESS read-only
  STATUS mandatory
  DESCRIPTION
          "Vnstat Yesterday Rx for ETH0 Interface in Kib... DEFAULT: -1"
  ::= {trafficeth0 16}

yesterdayTxEth0Kib OBJECT-TYPE -- Vnstat Yesterday Tx for ETH0 Interface in Kib
  SYNTAX INTEGER
  ACCESS read-only
  STATUS mandatory
  DESCRIPTION
          "Vnstat Yesterday Tx for ETH0 Interface in Kib... DEFAULT: -1"
  ::= {trafficeth0 17}

yesterdayTotalEth0Kib OBJECT-TYPE -- Vnstat Yesterday Total Rx/Tx for ETH0 Interface in Kib
  SYNTAX INTEGER
  ACCESS read-only
  STATUS mandatory
  DESCRIPTION
          "Vnstat Yesterday Total Rx/Tx for ETH0 Interface in Kib... DEFAULT: -1"
  ::= {trafficeth0 18}

currMonthRxEth0Kib OBJECT-TYPE -- Vnstat Current Month Rx for ETH0 Interface in Kib
  SYNTAX INTEGER
  ACCESS read-only
  STATUS mandatory
  DESCRIPTION
          "Vnstat Current Month Rx for ETH0 Interface in Kib... DEFAULT: -1"
  ::= {trafficeth0 19}

currMonthTxEth0Kib OBJECT-TYPE -- Vnstat Current Month Tx for ETH0 Interface in Kib
  SYNTAX INTEGER
  ACCESS read-only
  STATUS mandatory
  DESCRIPTION
          "Vnstat Current Month Tx for ETH0 Interface in Kib... DEFAULT: -1"
  ::= {trafficeth0 20}

currMonthTotalEth0Kib OBJECT-TYPE -- Vnstat Current Month Total Rx/Tx for ETH0 Interface in Kib
  SYNTAX INTEGER
  ACCESS read-only
  STATUS mandatory
  DESCRIPTION
          "Vnstat Current Month Total Rx/Tx for ETH0 Interface in Kib... DEFAULT: -1"
  ::= {trafficeth0 21}

preMonthRxEth0Kib OBJECT-TYPE -- Vnstat Previous Month Rx for ETH0 Interface in Kib
  SYNTAX INTEGER
  ACCESS read-only
  STATUS mandatory
  DESCRIPTION
          "Vnstat Previous Month Rx for ETH0 Interface in Kib... DEFAULT: -1"
  ::= {trafficeth0 22}

preMonthTxEth0Kib OBJECT-TYPE -- Vnstat Previous Month Tx for ETH0 Interface in Kib
  SYNTAX INTEGER
  ACCESS read-only
  STATUS mandatory
  DESCRIPTION
          "Vnstat Previous Month Tx for ETH0 Interface in Kib... DEFAULT: -1"
  ::= {trafficeth0 23}

preMonthTotalEth0Kib OBJECT-TYPE -- Vnstat Previous Month Total Rx/Tx for ETH0 Interface in Kib
  SYNTAX INTEGER
  ACCESS read-only
  STATUS mandatory
  DESCRIPTION
          "Vnstat Previous Month Total Rx/Tx for ETH0 Interface in Kib... DEFAULT: -1"
  ::= {trafficeth0 24}

todayRxEth1 OBJECT-TYPE -- Vnstat Today Rx for Eth1 Interface
  SYNTAX DisplayString
  ACCESS read-only
  STATUS mandatory
  DESCRIPTION
          "Vnstat Today Rx for Eth1 Interface... DEFAULT: UNKNOWN"
  ::= {trafficeth1 1}

todayTxEth1 OBJECT-TYPE -- Vnstat Today Tx for Eth1 Interface
  SYNTAX DisplayString
  ACCESS read-only
  STATUS mandatory
  DESCRIPTION
          "Vnstat Today Tx for Eth1 Interface... DEFAULT: UNKNOWN"
  ::= {trafficeth1 2}

todayTotalEth1 OBJECT-TYPE -- Vnstat Today Total Rx/Tx for Eth1 Interface
  SYNTAX DisplayString
  ACCESS read-only
  STATUS mandatory
  DESCRIPTION
          "Vnstat Today Total Rx/Tx for Eth1 Interface... DEFAULT: UNKNOWN"
  ::= {trafficeth1 3}

yesterdayRxEth1 OBJECT-TYPE -- Vnstat Yesterday Rx for Eth1 Interface
  SYNTAX DisplayString
  ACCESS read-only
  STATUS mandatory
  DESCRIPTION
          "Vnstat Yesterday Rx for Eth1 Interface... DEFAULT: UNKNOWN"
  ::= {trafficeth1 4}

yesterdayTxEth1 OBJECT-TYPE -- Vnstat Yesterday Tx for Eth1 Interface
  SYNTAX DisplayString
  ACCESS read-only
  STATUS mandatory
  DESCRIPTION
          "Vnstat Yesterday Tx for Eth1 Interface... DEFAULT: UNKNOWN"
  ::= {trafficeth1 5}

yesterdayTotalEth1 OBJECT-TYPE -- Vnstat Yesterday Total Rx/Tx for Eth1 Interface
  SYNTAX DisplayString
  ACCESS read-only
  STATUS mandatory
  DESCRIPTION
          "Vnstat Yesterday Total Rx/Tx for Eth1 Interface... DEFAULT: UNKNOWN"
  ::= {trafficeth1 6}

currMonthRxEth1 OBJECT-TYPE -- Vnstat Current Month Rx for Eth1 Interface
  SYNTAX DisplayString
  ACCESS read-only
  STATUS mandatory
  DESCRIPTION
          "Vnstat Current Month Rx for Eth1 Interface... DEFAULT: UNKNOWN"
  ::= {trafficeth1 7}

currMonthTxEth1 OBJECT-TYPE -- Vnstat Current Month Tx for Eth1 Interface
  SYNTAX DisplayString
  ACCESS read-only
  STATUS mandatory
  DESCRIPTION
          "Vnstat Current Month Tx for Eth1 Interface... DEFAULT: UNKNOWN"
  ::= {trafficeth1 8}

currMonthTotalEth1 OBJECT-TYPE -- Vnstat Current Month Total Rx/Tx for Eth1 Interface
  SYNTAX DisplayString
  ACCESS read-only
  STATUS mandatory
  DESCRIPTION
          "Vnstat Current Month Total Rx/Tx for Eth1 Interface... DEFAULT: UNKNOWN"
  ::= {trafficeth1 9}

preMonthRxEth1 OBJECT-TYPE -- Vnstat Previous Month Rx for Eth1 Interface
  SYNTAX DisplayString
  ACCESS read-only
  STATUS mandatory
  DESCRIPTION
          "Vnstat Previous Month Rx for Eth1 Interface... DEFAULT: UNKNOWN"
  ::= {trafficeth1 10}

preMonthTxEth1 OBJECT-TYPE -- Vnstat Previous Month Tx for Eth1 Interface
  SYNTAX DisplayString
  ACCESS read-only
  STATUS mandatory
  DESCRIPTION
          "Vnstat Previous Month Tx for Eth1 Interface... DEFAULT: UNKNOWN"
  ::= {trafficeth1 11}

preMonthTotalEth1 OBJECT-TYPE -- Vnstat Previous Month Total Rx/Tx for Eth1 Interface
  SYNTAX DisplayString
  ACCESS read-only
  STATUS mandatory
  DESCRIPTION
          "Vnstat Previous Month Total Rx/Tx for Eth1 Interface... DEFAULT: UNKNOWN"
  ::= {trafficeth1 12}

todayRxEth1Kib OBJECT-TYPE -- Vnstat Today Rx for ETH1 Interface in Kib
  SYNTAX INTEGER
  ACCESS read-only
  STATUS mandatory
  DESCRIPTION
          "Vnstat Today Rx for ETH1 Interface in Kib... DEFAULT: -1"
  ::= {trafficeth1 13}

todayTxEth1Kib OBJECT-TYPE -- Vnstat Today Tx for ETH1 Interface in Kib
  SYNTAX INTEGER
  ACCESS read-only
  STATUS mandatory
  DESCRIPTION
          "Vnstat Today Tx for ETH1 Interface in Kib... DEFAULT: -1"
  ::= {trafficeth1 14}

todayTotalEth1Kib OBJECT-TYPE -- Vnstat Today Total Rx/Tx for ETH1 Interface in Kib
  SYNTAX INTEGER
  ACCESS read-only
  STATUS mandatory
  DESCRIPTION
          "Vnstat Today Total Rx/Tx for ETH1 Interface in Kib... DEFAULT: -1"
  ::= {trafficeth1 15}

yesterdayRxEth1Kib OBJECT-TYPE -- Vnstat Yesterday Rx for ETH1 Interface in Kib
  SYNTAX INTEGER
  ACCESS read-only
  STATUS mandatory
  DESCRIPTION
          "Vnstat Yesterday Rx for ETH1 Interface in Kib... DEFAULT: -1"
  ::= {trafficeth1 16}

yesterdayTxEth1Kib OBJECT-TYPE -- Vnstat Yesterday Tx for ETH1 Interface in Kib
  SYNTAX INTEGER
  ACCESS read-only
  STATUS mandatory
  DESCRIPTION
          "Vnstat Yesterday Tx for ETH1 Interface in Kib... DEFAULT: -1"
  ::= {trafficeth1 17}

yesterdayTotalEth1Kib OBJECT-TYPE -- Vnstat Yesterday Total Rx/Tx for ETH1 Interface in Kib
  SYNTAX INTEGER
  ACCESS read-only
  STATUS mandatory
  DESCRIPTION
          "Vnstat Yesterday Total Rx/Tx for ETH1 Interface in Kib... DEFAULT: -1"
  ::= {trafficeth1 18}

currMonthRxEth1Kib OBJECT-TYPE -- Vnstat Current Month Rx for ETH1 Interface in Kib
  SYNTAX INTEGER
  ACCESS read-only
  STATUS mandatory
  DESCRIPTION
          "Vnstat Current Month Rx for ETH1 Interface in Kib... DEFAULT: -1"
  ::= {trafficeth1 19}

currMonthTxEth1Kib OBJECT-TYPE -- Vnstat Current Month Tx for ETH1 Interface in Kib
  SYNTAX INTEGER
  ACCESS read-only
  STATUS mandatory
  DESCRIPTION
          "Vnstat Current Month Tx for ETH1 Interface in Kib... DEFAULT: -1"
  ::= {trafficeth1 20}

currMonthTotalEth1Kib OBJECT-TYPE -- Vnstat Current Month Total Rx/Tx for ETH1 Interface in Kib
  SYNTAX INTEGER
  ACCESS read-only
  STATUS mandatory
  DESCRIPTION
          "Vnstat Current Month Total Rx/Tx for ETH1 Interface in Kib... DEFAULT: -1"
  ::= {trafficeth1 21}

preMonthRxEth1Kib OBJECT-TYPE -- Vnstat Previous Month Rx for ETH1 Interface in Kib
  SYNTAX INTEGER
  ACCESS read-only
  STATUS mandatory
  DESCRIPTION
          "Vnstat Previous Month Rx for ETH1 Interface in Kib... DEFAULT: -1"
  ::= {trafficeth1 22}

preMonthTxEth1Kib OBJECT-TYPE -- Vnstat Previous Month Tx for ETH1 Interface in Kib
  SYNTAX INTEGER
  ACCESS read-only
  STATUS mandatory
  DESCRIPTION
          "Vnstat Previous Month Tx for ETH1 Interface in Kib... DEFAULT: -1"
  ::= {trafficeth1 23}

preMonthTotalEth1Kib OBJECT-TYPE -- Vnstat Previous Month Total Rx/Tx for ETH1 Interface in Kib
  SYNTAX INTEGER
  ACCESS read-only
  STATUS mandatory
  DESCRIPTION
          "Vnstat Previous Month Total Rx/Tx for ETH1 Interface in Kib... DEFAULT: -1"
  ::= {trafficeth1 24}

currentGpsValid OBJECT-TYPE -- GPS Fixed Quality
  SYNTAX DisplayString
  ACCESS read-only
  STATUS mandatory
  DESCRIPTION
          "GPS Current Valid Fixed Quality (0 = Invalid, 1 = Valid)... DEFAULT: UNKNOWN"
  ::= {gpscurrent 1}

currentGpsLat OBJECT-TYPE -- GPS Latitude Degrees
  SYNTAX DisplayString
  ACCESS read-only
  STATUS mandatory
  DESCRIPTION
          "GPS Current Latitude Degrees ... DEFAULT: UNKNOWN"
  ::= {gpscurrent 2}

currentGpsLong OBJECT-TYPE -- GPS Longitude Degrees
  SYNTAX DisplayString
  ACCESS read-only
  STATUS mandatory
  DESCRIPTION
          "GPS Current Longitude Degrees ... DEFAULT: UNKNOWN"
  ::= {gpscurrent 3}

currentGpsAlt OBJECT-TYPE -- GPS Altitude Tenths of Meter
  SYNTAX DisplayString
  ACCESS read-only
  STATUS mandatory
  DESCRIPTION
          "GPS Current Altitude Tenths of Meter(280.2 = 2802) ... DEFAULT: UNKNOWN"
  ::= {gpscurrent 4}

currentGpsTimeStamp OBJECT-TYPE -- GPS Time Stamp
  SYNTAX DisplayString
  ACCESS read-only
  STATUS mandatory
  DESCRIPTION
          "GPS Current Time Stamp ... DEFAULT: UNKNOWN"
  ::= {gpscurrent 5}

currentGpsNumSat OBJECT-TYPE -- GPS Number of Satellites
  SYNTAX DisplayString
  ACCESS read-only
  STATUS mandatory
  DESCRIPTION
          "GPS Current Number of Satellites ... DEFAULT: UNKNOWN"
  ::= {gpscurrent 6}

currentGpsFtfromcp OBJECT-TYPE -- GPS Feet From Lockdown Center Point
  SYNTAX DisplayString
  ACCESS read-only
  STATUS mandatory
  DESCRIPTION
          "GPS Current Feet From Lockdown Center Point ... DEFAULT: UNKNOWN"
  ::= {gpscurrent 7}

currentGpsSpeed OBJECT-TYPE -- GPS Speed
  SYNTAX DisplayString
  ACCESS read-only
  STATUS mandatory
  DESCRIPTION
          "GPS Current Speed, SOG tenths of knots (50.1 = 501)... DEFAULT: UNKNOWN"
  ::= {gpscurrent 8}

currentGpsCourse OBJECT-TYPE -- GPS Course, Heading in tenths of degree
  SYNTAX DisplayString
  ACCESS read-only
  STATUS mandatory
  DESCRIPTION
          "GPS Current Course, Heading in tenths of degree(280.3 = 2803)... DEFAULT: UNKNOWN"
  ::= {gpscurrent 9}

gpsSource OBJECT-TYPE -- GPS Source of Data
  SYNTAX DisplayString
  ACCESS read-only
  STATUS mandatory
  DESCRIPTION
          "GPS Source of Data (1=Internal; 3=Fixed)... DEFAULT: UNKNOWN"
  ::= {gpscurrent 10}

gpsLockdownState OBJECT-TYPE -- GPS Heading in Tenths of Degree
  SYNTAX DisplayString
  ACCESS read-only
  STATUS mandatory
  DESCRIPTION
          "GPS Current Lockdown State (0 = Monitor; 5 = Lockdown; 7-9 = Violation)... DEFAULT: UNKNOWN"
  ::= {gpscurrent 11}

gpsLockdownRadius OBJECT-TYPE -- GPS Lockdown Radius (ft)
  SYNTAX DisplayString
  ACCESS read-only
  STATUS mandatory
  DESCRIPTION
          "GPS Current Lockdown Radius (ft), Units in Feet as calculated from centerpoint... DEFAULT: UNKNOWN"
  ::= {gpscurrent 12}

END
