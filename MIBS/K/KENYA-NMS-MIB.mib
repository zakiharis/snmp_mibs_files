KENYA-NMS-MIB DEFINITIONS ::= BEGIN

IMPORTS
	OBJECT-TYPE FROM RFC1155-SMI
	vlbProducts
		FROM VOLUBILL-ROOT-MIB 
	Integer32, IpAddress FROM SNMPv2-SMI;

bay OBJECT IDENTIFIER ::= { vlbProducts 1 }

bayConsolidatedStatus OBJECT-TYPE
	SYNTAX INTEGER
	{
		allUnmanaged(0),
		green(1),
		yellow(2),
		orange(3),
		red(4)
	}
	ACCESS read-only
	STATUS mandatory
	DESCRIPTION
	  "The overall status of the bay, indicated by colour."
	::= { bay 1 }

---------------------------------------
-- Bay Hardwares list Table
---------------------------------------
bayHardwares OBJECT IDENTIFIER ::= { bay 2 }

--- Hardware type 1 : Servers and Switches

bayHwCount OBJECT-TYPE
	SYNTAX INTEGER
	ACCESS read-only
	STATUS mandatory
	DESCRIPTION "The number of systems in the rack."
	::= { bayHardwares 1 }

bayHwTable OBJECT-TYPE
	SYNTAX SEQUENCE OF BayHwEntry
	MAX-ACCESS not-accessible
	STATUS current
	DESCRIPTION "Table of systems in the rack."
	::= { bayHardwares 2 }

bayHwEntry OBJECT-TYPE
	SYNTAX BayHwEntry
	MAX-ACCESS not-accessible
	STATUS current
	DESCRIPTION "Entry in the server table."
	INDEX { bayHwIndex }
	::= { bayHwTable 1  }

BayHwEntry ::= SEQUENCE {
	bayHwIndex Integer32 ,
	bayHwName OCTET STRING,
	bayHwAddress IpAddress
}

bayHwIndex OBJECT-TYPE
        SYNTAX Integer32 (1..65535)
	MAX-ACCESS read-only
	STATUS current
DESCRIPTION ""
	::= { bayHwEntry 1  }

bayHwName OBJECT-TYPE
        SYNTAX OCTET STRING (SIZE(0..20))
	MAX-ACCESS read-only
	STATUS current
	DESCRIPTION "System hardware name."
	::= { bayHwEntry 2  }

bayHwAddress OBJECT-TYPE
        SYNTAX IpAddress
	MAX-ACCESS read-only
	STATUS current
	DESCRIPTION "Main IP address of the server (used for telnet)"
	::= { bayHwEntry 3 }



-- end of hardwares tables



----------------------------------------------------------------
------------------ APPLICATIONS --------------------------------

bayApplications OBJECT IDENTIFIER ::= { bay 3 }

--
-- PROXY
--

bayProxy  OBJECT IDENTIFIER ::= { bayApplications 1 }

bayProxyGlobalStatus OBJECT-TYPE
	SYNTAX INTEGER
	{
		allUnmanaged(0),
		green(1),
		yellow(2),
		orange(3),
		red(4)
	}
	ACCESS read-only
	STATUS mandatory
	DESCRIPTION "Status of the Service Delivery system (easily reached from Node monitoring)."
	::= { bayProxy 1 }

proxyHTTPGroupStatus OBJECT-TYPE
	SYNTAX INTEGER
	{
		allUnmanaged(0),
		green(1),
		yellow(2),
		orange(3),
		red(4)
	}
	ACCESS read-only
	STATUS mandatory
DESCRIPTION ""
	::= { bayProxy 2 }

proxySSNGroupStatus OBJECT-TYPE
	SYNTAX INTEGER
	{
		allUnmanaged(0),
		green(1),
		yellow(2),
		orange(3),
		red(4)
	}
	ACCESS read-only
	STATUS mandatory
DESCRIPTION ""
	::= { bayProxy 3 }

proxyMMSGroupStatus OBJECT-TYPE
	SYNTAX INTEGER
	{
		allUnmanaged(0),
		green(1),
		yellow(2),
		orange(3),
		red(4)
	}
	ACCESS read-only
	STATUS mandatory
DESCRIPTION ""
	::= { bayProxy 4 }

proxyMAILGroupStatus OBJECT-TYPE
	SYNTAX INTEGER
	{
		allUnmanaged(0),
		green(1),
		yellow(2),
		orange(3),
		red(4)
	}
	ACCESS read-only
	STATUS mandatory
DESCRIPTION ""
	::= { bayProxy 5 }

--
--  BILLING
--

bayBilling OBJECT IDENTIFIER ::= { bayApplications 2 }

bayBillingGlobalStatus OBJECT-TYPE
	SYNTAX INTEGER
	{
		allUnmanaged(0),
		green(1),
		yellow(2),
		orange(3),
		red(4)
	}
	ACCESS read-only
	STATUS mandatory
	DESCRIPTION "Status of the Service Controller system (easily reached from Node monitoring)."
	::= { bayBilling 1 }


baySwitching OBJECT IDENTIFIER ::= { bayApplications 3 }

bayL7SwitchingGlobalStatus OBJECT-TYPE
	SYNTAX INTEGER
	{
		allUnmanaged(0),
		green(1),
		yellow(2),
		orange(3),
		red(4)
	}
	ACCESS read-only
	STATUS mandatory
	DESCRIPTION "Status of Service Filtering Switches (easily reached from Node monitoring)."
	::= { baySwitching 1 }

bayL2SwitchingGlobalStatus OBJECT-TYPE
	SYNTAX INTEGER
	{
		allUnmanaged(0),
		green(1),
		yellow(2),
		orange(3),
		red(4)
	}
	ACCESS read-only
	STATUS mandatory
	DESCRIPTION "Status of Layer 2 Switches (easily reached from Node monitoring)."
	::= { baySwitching 2 }


bayLms OBJECT IDENTIFIER ::= { bayApplications 4 }

bayLmsGlobalStatus OBJECT-TYPE
	SYNTAX INTEGER
	{
		allUnmanaged(0),
		green(1),
		yellow(2),
		orange(3),
		red(4)
	}
	ACCESS read-only
	STATUS mandatory
	DESCRIPTION "Status of Power system." 
	::= { bayLms 1 }




bayScstats OBJECT IDENTIFIER ::= { bayApplications 5 }

bscInAgentReportRequests OBJECT-TYPE
	SYNTAX INTEGER
	ACCESS read-only
	STATUS mandatory
DESCRIPTION ""
	::= { bayScstats 1 }

bscOutUpdateSessionReplies OBJECT-TYPE
	SYNTAX INTEGER
	ACCESS read-only
	STATUS mandatory
DESCRIPTION ""
	::= { bayScstats 2 }

bscOutReplies OBJECT-TYPE
	SYNTAX INTEGER
	ACCESS read-only
	STATUS mandatory
DESCRIPTION ""
	::= { bayScstats 3 }

bscCurrentServicesPendingSessions OBJECT-TYPE
	SYNTAX INTEGER
	ACCESS read-only
	STATUS mandatory
DESCRIPTION ""
	::= { bayScstats 4 }

bscUdrs OBJECT-TYPE
	SYNTAX INTEGER
	ACCESS read-only
	STATUS mandatory
	DESCRIPTION "Number of Usage Detail Records created."
	::= { bayScstats 5 }

bscInReportUsageReplies OBJECT-TYPE
	SYNTAX INTEGER
	ACCESS read-only
	STATUS mandatory
DESCRIPTION ""
	::= { bayScstats 6 }

bscClosedSessions OBJECT-TYPE
	SYNTAX INTEGER
	ACCESS read-only
	STATUS mandatory
DESCRIPTION ""
	::= { bayScstats 7 }

bscOldServicesPendingSessions OBJECT-TYPE
	SYNTAX INTEGER
	ACCESS read-only
	STATUS mandatory
	DESCRIPTION "Number of contexts opened on the previous services page." 
	::= { bayScstats 8 }

bscInRequests OBJECT-TYPE
	SYNTAX INTEGER
	ACCESS read-only
	STATUS mandatory
DESCRIPTION ""
	::= { bayScstats 9 }

bscOutAgentReportReplies OBJECT-TYPE
	SYNTAX INTEGER
	ACCESS read-only
	STATUS mandatory
DESCRIPTION ""
	::= { bayScstats 10 }

bscInCloseSessionReplies OBJECT-TYPE
	SYNTAX INTEGER
	ACCESS read-only
	STATUS mandatory
DESCRIPTION ""
	::= { bayScstats 11 }

bscInCloseSessionRequests OBJECT-TYPE
	SYNTAX INTEGER
	ACCESS read-only
	STATUS mandatory
DESCRIPTION ""
	::= { bayScstats 12 }

bscOutCloseSessionReplies OBJECT-TYPE
	SYNTAX INTEGER
	ACCESS read-only
	STATUS mandatory
DESCRIPTION ""
	::= { bayScstats 13 }

bscUdrFiles OBJECT-TYPE
	SYNTAX INTEGER
	ACCESS read-only
	STATUS mandatory
DESCRIPTION ""
	::= { bayScstats 14 }

bscOutListSessionReplies OBJECT-TYPE
	SYNTAX INTEGER
	ACCESS read-only
	STATUS mandatory
DESCRIPTION ""
	::= { bayScstats 15 }

bscOutRequests OBJECT-TYPE
	SYNTAX INTEGER
	ACCESS read-only
	STATUS mandatory
DESCRIPTION ""
	::= { bayScstats 16 }

bscOutUpdateSessionRequests OBJECT-TYPE
	SYNTAX INTEGER
	ACCESS read-only
	STATUS mandatory
DESCRIPTION ""
	::= { bayScstats 17 }

bscInUpdateSessionReplies OBJECT-TYPE
	SYNTAX INTEGER
	ACCESS read-only
	STATUS mandatory
DESCRIPTION ""
	::= { bayScstats 18 }

bscInAgentReportReplies OBJECT-TYPE
	SYNTAX INTEGER
	ACCESS read-only
	STATUS mandatory
DESCRIPTION ""
	::= { bayScstats 19 }

bscOutAgentReportRequests OBJECT-TYPE
	SYNTAX INTEGER
	ACCESS read-only
	STATUS mandatory
DESCRIPTION ""
	::= { bayScstats 20 }

bscInUpdateSessionRequests OBJECT-TYPE
	SYNTAX INTEGER
	ACCESS read-only
	STATUS mandatory
DESCRIPTION ""
	::= { bayScstats 21 }

bscInReplies OBJECT-TYPE
	SYNTAX INTEGER
	ACCESS read-only
	STATUS mandatory
DESCRIPTION ""
	::= { bayScstats 22 }

bscOutCreateSessionRequests OBJECT-TYPE
	SYNTAX INTEGER
	ACCESS read-only
	STATUS mandatory
DESCRIPTION ""
	::= { bayScstats 23 }

bscInReportUsageRequests OBJECT-TYPE
	SYNTAX INTEGER
	ACCESS read-only
	STATUS mandatory
DESCRIPTION ""
	::= { bayScstats 24 }

bscInListSessionRequests OBJECT-TYPE
	SYNTAX INTEGER
	ACCESS read-only
	STATUS mandatory
DESCRIPTION ""
	::= { bayScstats 25 }

bscOutReportUsageRequests OBJECT-TYPE
	SYNTAX INTEGER
	ACCESS read-only
	STATUS mandatory
DESCRIPTION ""
	::= { bayScstats 26 }

bscInListSessionReplies OBJECT-TYPE
	SYNTAX INTEGER
	ACCESS read-only
	STATUS mandatory
DESCRIPTION ""
	::= { bayScstats 27 }

bscInCreateSessionRequests OBJECT-TYPE
	SYNTAX INTEGER
	ACCESS read-only
	STATUS mandatory
DESCRIPTION ""
	::= { bayScstats 28 }

bscOutCloseSessionRequests OBJECT-TYPE
	SYNTAX INTEGER
	ACCESS read-only
	STATUS mandatory
DESCRIPTION ""
	::= { bayScstats 29 }

bscOutListSessionRequests OBJECT-TYPE
	SYNTAX INTEGER
	ACCESS read-only
	STATUS mandatory
DESCRIPTION ""
	::= { bayScstats 30 }

bscInCreateSessionReplies OBJECT-TYPE
	SYNTAX INTEGER
	ACCESS read-only
	STATUS mandatory
DESCRIPTION ""
	::= { bayScstats 31 }

bscCreatedSessions OBJECT-TYPE
	SYNTAX INTEGER
	ACCESS read-only
	STATUS mandatory
DESCRIPTION ""
	::= { bayScstats 32 }

bscOutReportUsageReplies OBJECT-TYPE
	SYNTAX INTEGER
	ACCESS read-only
	STATUS mandatory
DESCRIPTION ""
	::= { bayScstats 33 }

bscOutCreateSessionReplies OBJECT-TYPE
	SYNTAX INTEGER
	ACCESS read-only
	STATUS mandatory
DESCRIPTION ""
	::= { bayScstats 34 }

bscSessionsPerSecond  OBJECT-TYPE
	SYNTAX INTEGER
	ACCESS read-only
	STATUS mandatory
DESCRIPTION ""
	::= { bayScstats 35 }

bscRejectedSessions  OBJECT-TYPE
	SYNTAX INTEGER
	ACCESS read-only
	STATUS mandatory
	DESCRIPTION "Rejected service session access."
	::= { bayScstats 36 }

bscInContinueSessionRequest OBJECT-TYPE
	SYNTAX INTEGER
	ACCESS read-only
	STATUS mandatory
DESCRIPTION ""
	::= { bayScstats 37 }

bscOutContinueSessionRequest OBJECT-TYPE
	SYNTAX INTEGER
	ACCESS read-only
	STATUS mandatory
DESCRIPTION ""
	::= { bayScstats 38 }

bscInContinueSessionReplies OBJECT-TYPE
	SYNTAX INTEGER
	ACCESS read-only
	STATUS mandatory
DESCRIPTION ""
	::= { bayScstats 39 }

bscOutContinueSessionReplies OBJECT-TYPE
	SYNTAX INTEGER
	ACCESS read-only
	STATUS mandatory
DESCRIPTION ""
	::= { bayScstats 40 }

bscAuthRequests OBJECT-TYPE
	SYNTAX INTEGER
	ACCESS read-only
	STATUS mandatory
	DESCRIPTION "Number of authorize requests sent by agent since last reset." 
	::= { bayScstats 41 }

bscAuthNonRepliedRequestsPercent OBJECT-TYPE
	SYNTAX INTEGER
	ACCESS read-only
	STATUS mandatory
	DESCRIPTION "Percentage of authorize requests sent during second now-5 and still unanswered now."
	::= { bayScstats 42 }

bscAuthReplies OBJECT-TYPE
	SYNTAX INTEGER
	ACCESS read-only
	STATUS mandatory
	DESCRIPTION "Number of authorize replies received by agent since last reset." 
	::= { bayScstats 43 }

bscAcctReplies OBJECT-TYPE
	SYNTAX INTEGER
	ACCESS read-only
	STATUS mandatory
	DESCRIPTION "Number of accounting replies received by agent since last reset."
	::= { bayScstats 44 }

bscAcctRequests OBJECT-TYPE
	SYNTAX INTEGER
	ACCESS read-only
	STATUS mandatory
	DESCRIPTION "Number of accounting requests sent by agent since last reset." 
	::= { bayScstats 45 }

bscAcctRepliedRequestsPercent OBJECT-TYPE
	SYNTAX INTEGER
	ACCESS read-only
	STATUS mandatory
DESCRIPTION ""
	::= { bayScstats 46 }

bayTraps OBJECT IDENTIFIER ::= { bay 4 }

bayExternalTrapTarget OBJECT-TYPE
        SYNTAX OCTET STRING (SIZE(0..20))
	ACCESS read-only
	STATUS mandatory
	DESCRIPTION "External destination of NMS traps."
	::= { bayTraps 1 }


END
