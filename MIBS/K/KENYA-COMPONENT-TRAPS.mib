KENYA-COMPONENT-TRAPS DEFINITIONS ::= BEGIN

IMPORTS
	OBJECT-TYPE FROM RFC1155-SMI
	TRAP-TYPE
		FROM RFC-1215
	volubill, vlbComponents
		FROM VOLUBILL-ROOT-MIB	
	nmSoftwares, scSoftwares, pxSoftwares
		FROM KENYA-COMPONENT-MIB;

-------------------------------------------
--  infos for data collector messages
--  defined here to be used only in traps, 
--  no reply from snmpget to thoose oids

nmDataCollector OBJECT IDENTIFIER ::= { nmSoftwares 1 }

dcCheckedOid  OBJECT-TYPE
	SYNTAX OCTET STRING
	ACCESS read-only
	STATUS mandatory
DESCRIPTION ""
	::= { nmDataCollector 1 }

dcErrorString  OBJECT-TYPE
	SYNTAX OCTET STRING (SIZE(0..200))
	ACCESS read-only
	STATUS mandatory
DESCRIPTION ""
	::= { nmDataCollector 2 }

dcTestDescr  OBJECT-TYPE
	SYNTAX OCTET STRING	ACCESS read-only
	STATUS mandatory
DESCRIPTION ""
	::= { nmDataCollector 3 }

dcNbRepeat  OBJECT-TYPE
	SYNTAX INTEGER
	ACCESS read-only
	STATUS mandatory
DESCRIPTION ""
	::= { nmDataCollector 4 }

dcSystemRequirement OBJECT-TYPE
	SYNTAX OCTET STRING
	ACCESS read-only
	STATUS mandatory
DESCRIPTION ""
	::= { nmDataCollector 5 }

dcSystemErrorDate OBJECT-TYPE
	SYNTAX OCTET STRING
	ACCESS read-only
	STATUS mandatory
DESCRIPTION ""
	::= { nmDataCollector 6 }

trapSeverity OBJECT-TYPE
	SYNTAX INTEGER
	{
		informative(1),
		warning(2),
		serious(3),
		critical(4)
	}
	ACCESS read-only
	STATUS mandatory
DESCRIPTION ""
	::= { vlbComponents 5 }

-------------------------------------------
--  infos for process respawner  messages
--  defined here to be used only in traps, 
--  no reply form snmpget to thoose oids

procRespawner OBJECT IDENTIFIER ::= { nmSoftwares 2 }


prMissingProcName  OBJECT-TYPE
	SYNTAX OCTET STRING (SIZE(0..200))
	ACCESS read-only
	STATUS mandatory
DESCRIPTION ""
	::= { procRespawner 1 }	

prRespawnCommand  OBJECT-TYPE
	SYNTAX OCTET STRING
	ACCESS read-only
	STATUS mandatory
DESCRIPTION ""
	::= { procRespawner 2 }

-------------------------------------------
--  infos for nms component snmp error  messages
--  defined here to be used only in traps, 
--  no reply form snmpget to thoose oids

nmsGolbalStatusProcessor  OBJECT IDENTIFIER ::= { nmSoftwares 3 }

snmpFailedComponent  OBJECT-TYPE
	SYNTAX OCTET STRING
	ACCESS read-only
	STATUS mandatory
DESCRIPTION ""
	::= { nmsGolbalStatusProcessor 1 }

snmpRequestedOid  OBJECT-TYPE
	SYNTAX OCTET STRING
	ACCESS read-only
	STATUS mandatory
DESCRIPTION ""
	::= { nmsGolbalStatusProcessor 2 }

componentTrapSender  OBJECT IDENTIFIER ::= { nmSoftwares 4 }

sourceComponent  OBJECT-TYPE
	SYNTAX OCTET STRING
	ACCESS read-only
	STATUS mandatory
DESCRIPTION ""
	::= { componentTrapSender 1 }

componentInfo  OBJECT-TYPE
        SYNTAX OCTET STRING
        ACCESS read-only
        STATUS mandatory
DESCRIPTION ""
        ::= { componentTrapSender 2 }
        
alarmDescription  OBJECT-TYPE
	SYNTAX OCTET STRING
	ACCESS read-only
	STATUS mandatory
DESCRIPTION ""
	::= { componentTrapSender 3 }
	
processName  OBJECT-TYPE
	SYNTAX OCTET STRING
	ACCESS read-only
	STATUS mandatory
DESCRIPTION ""
	::= { componentTrapSender 4 }


scAgentApplication  OBJECT IDENTIFIER ::= { scSoftwares 1 }

scaSourceComponent OBJECT-TYPE
	SYNTAX OCTET STRING
	ACCESS read-only
	STATUS mandatory
DESCRIPTION ""
	::= { scAgentApplication 1 }

scaErrorMessage OBJECT-TYPE
	SYNTAX OCTET STRING
	ACCESS read-only
	STATUS mandatory
DESCRIPTION ""
	::= { scAgentApplication 2 }

udrWriterApplication OBJECT IDENTIFIER ::= { scSoftwares 2 }

uwSourceComponent OBJECT-TYPE
	SYNTAX OCTET STRING
	ACCESS read-only
	STATUS mandatory
DESCRIPTION ""
	::= { udrWriterApplication 1 }

uwInfoMessage OBJECT-TYPE
	SYNTAX OCTET STRING
	ACCESS read-only
	STATUS mandatory
DESCRIPTION ""
	::= { udrWriterApplication 2 }

proxyApplication OBJECT IDENTIFIER ::= { pxSoftwares 1 }

pxSourceComponent OBJECT-TYPE
	SYNTAX OCTET STRING
	ACCESS read-only
	STATUS mandatory
DESCRIPTION ""
	::= { proxyApplication 1 }

pxErrorMessage OBJECT-TYPE
	SYNTAX OCTET STRING
	ACCESS read-only
	STATUS mandatory
DESCRIPTION ""
	::= { proxyApplication 2 }

--------------------------------------------
---------------  TRAPS ---------------------


procMissing TRAP-TYPE
    ENTERPRISE volubill
    VARIABLES { trapSeverity, sourceComponent, prMissingProcName, prRespawnCommand}
    DESCRIPTION
        "The SNMP trap that is generated by the Process Respawner 
	when a critical required process is missing.
	Severity CRITICAL"
    ::= 1

procMissingAfterRespawn TRAP-TYPE
    ENTERPRISE volubill
    VARIABLES { trapSeverity, sourceComponent, prMissingProcName, prRespawnCommand }
    DESCRIPTION
        "The SNMP trap that is generated by the process respawner
	to inform that the process is still missing after a restart
	Reason: Critical Process Missing
	Severity CRITICAL"
    ::= 2

snmpUnreachableHost TRAP-TYPE
    ENTERPRISE volubill
    VARIABLES { trapSeverity , sourceComponent, snmpFailedComponent, snmpRequestedOid }
    DESCRIPTION
        "The SNMP trap that is generated by the LMS snmp agent 
	when a server fails to answer SNMP requests
	If the reason is Cannot reach master-switch hardware, Severity SERIOUS
	If the reason is cannot reach component, Severity WARNING"
    ::= 3

dataCollectorThresholdExceeded TRAP-TYPE
    ENTERPRISE volubill
    VARIABLES { trapSeverity, sourceComponent, dcCheckedOid, dcErrorString, dcTestDescr , dcNbRepeat}
    DESCRIPTION
        "The SNMP trap that is generated by the data collector 
	when a collected data exceed its defined thresholds
	Reason: system limitation reached
	Severity WARNING"
    ::= 4

dataCollectorSystemRequirement TRAP-TYPE
    ENTERPRISE volubill
    VARIABLES { trapSeverity, dcSystemRequirement , dcSystemErrorDate }
    DESCRIPTION
        "Generated by the data collector 
	when a system limitation is detected and should be corrected
	data collector will still work correctly
	Reason: system limitation reached
	Severity WARNING"
    ::= 5

dataCollectorSystemError TRAP-TYPE
    ENTERPRISE volubill
    VARIABLES { trapSeverity, dcSystemRequirement }
    DESCRIPTION
        "Generated by the data collector 
	when a system limitation is detected and prevents 
	data collector from running correctly"
    ::= 6

scAgentError TRAP-TYPE
    ENTERPRISE volubill
    VARIABLES { trapSeverity, scaSourceComponent, scaErrorMessage }
    DESCRIPTION
        "Generated by scagent application 
	suitable for several error types
	description included in variables
	Here are the different reasons:
	*Service catalog successfully loaded;
	*Rollback to previous service catalog successful;
	*Reaching Overload Level X: means X% of the traffic is rejected for capacity reason;
	*Percentage of non-replied authorize requests now below threshold;
	*Percentage of non-replied accounting requests now below threshold.
	Reason: system limitation reached
	Severity WARNING"
    ::= 7


healthCheckError TRAP-TYPE
    ENTERPRISE volubill
    VARIABLES { trapSeverity, sourceComponent }
    DESCRIPTION
        "The SNMP trap that is generated by snmp agent
	when health check test fails.
	Reason:  Check process health failed
	Severity WARNING"
    ::= 8


proxyError TRAP-TYPE
	ENTERPRISE volubill
	VARIABLES { trapSeverity, pxSourceComponent, pxErrorMessage }
	DESCRIPTION
		"Generated by proxy application
		suitable for several error types
		description included in variables

		Here are the different reasons:
		*Overload: 
			-Enter in the warning zone;
			-Stay in the warning zone;
			-Exit from the warning zone;
			-Enter in overload;
			-Stay in overload;
			-Exit from overload.
		*Advice of charge: URL retrieving failed '<url>' (HTTP <HTTP status code>);
		*Configuration problem (bad parameters in a configuration file):
			-Could not open document config file <filename> <error cause>
			-Missing information primitive in the configuration, include primitive name;
		*Unable to open the timing file '<filename>' (errno <error code>: <error meaning>) 
		*Could not load event-table;
		*Could not bind to service table."
	::= 9


switchProvisioningError TRAP-TYPE
        ENTERPRISE volubill
        VARIABLES { trapSeverity, sourceComponent }
        DESCRIPTION
                "L7 switch provisioning error
			Provisioning of L7 switches failed.
			Severity CRITICAL"
        ::= 10


powerFailure TRAP-TYPE
	ENTERPRISE volubill
	VARIABLES { trapSeverity }
	DESCRIPTION
		"Power failure on platform.
		SNMP command error: host <master-switch-IP-address> SNMP set failed
		Severity CRITICAL"
	::= 11

linkFailure TRAP-TYPE
        ENTERPRISE volubill
        VARIABLES { trapSeverity, sourceComponent, componentInfo}
        DESCRIPTION
                "link failure on platform.
			Reason: <NIC-reference>: AFT link failure detected.
			Severity SERIOUS"
        ::= 12

caInvalidVIPStatus TRAP-TYPE
        ENTERPRISE volubill
        VARIABLES { trapSeverity, sourceComponent, componentInfo}
        DESCRIPTION
                "ClickArray VIP statuses are not valid."
        ::= 13

caValidVIPStatus TRAP-TYPE
        ENTERPRISE volubill
        VARIABLES { trapSeverity, sourceComponent, componentInfo}
        DESCRIPTION
                "ClickArray VIP statuses are valid."
        ::= 14

successfulProvisioning TRAP-TYPE
        ENTERPRISE volubill
        VARIABLES { trapSeverity, sourceComponent, componentInfo }
        DESCRIPTION
                "Generated by the NMS after each successful
                 service provisioning"
        ::= 15

sSNModuleNotHA TRAP-TYPE
        ENTERPRISE volubill
        VARIABLES { trapSeverity, sourceComponent, componentInfo }
        DESCRIPTION
                "SSN module in HA node does not have at least 2 connections to L4 switches."
        ::= 16

successfulRollback TRAP-TYPE
        ENTERPRISE volubill
        VARIABLES { trapSeverity, sourceComponent, componentInfo }
        DESCRIPTION
                "Generated by the NMS after each successful
                 service rollback provisioning"
        ::= 17
        
procStarted TRAP-TYPE
    ENTERPRISE volubill
    VARIABLES { trapSeverity, sourceComponent, processName}
    DESCRIPTION
        "Generated by process when starting."
    ::= 18
    
rectifierAlarm TRAP-TYPE
    ENTERPRISE volubill
    VARIABLES { trapSeverity, alarmDescription}
    DESCRIPTION
        "Generated by NMS when Alarms are generated by APC rectifier."
    ::= 19    

powerOn TRAP-TYPE
        ENTERPRISE volubill
        VARIABLES { trapSeverity }
        DESCRIPTION
                "Power is back on platform."
    ::= 20
    

uwMessage TRAP-TYPE
    ENTERPRISE volubill
    VARIABLES { trapSeverity, uwSourceComponent, uwInfoMessage }
    DESCRIPTION
        "Generated by udr writer when starting, closing and writing file." 
    ::= 21

vlbProcStarted TRAP-TYPE
    ENTERPRISE volubill
    VARIABLES { trapSeverity, sourceComponent, processName, componentInfo }
    DESCRIPTION
        "Generated by process when starting."
    ::= 22

vlbProcNotStarted TRAP-TYPE
    ENTERPRISE volubill
    VARIABLES { trapSeverity, sourceComponent, processName, componentInfo }
    DESCRIPTION
        "Generated by process when process cannot be started."
    ::= 23
    
vlbProcStopped TRAP-TYPE
    ENTERPRISE volubill
    VARIABLES { trapSeverity, sourceComponent, processName, componentInfo }
    DESCRIPTION
        "Generated by process when stopping."
    ::= 24

vlbLogTrap TRAP-TYPE
    ENTERPRISE volubill
    VARIABLES { trapSeverity, sourceComponent, processName, componentInfo }
    DESCRIPTION
        "Log generated by process" 
    ::= 25

        
------------------------------------------
--  BSSG Traps  : range 30 to 49 ---------
------------------------------------------

bssgStart TRAP-TYPE
        ENTERPRISE volubill
        VARIABLES { trapSeverity, sourceComponent, componentInfo }
        DESCRIPTION
                "BSSG Start"
        ::= 30

bssgStop TRAP-TYPE
        ENTERPRISE volubill
        VARIABLES { trapSeverity, sourceComponent, componentInfo }
        DESCRIPTION
                "BSSG Stop"
        ::= 31

bssgSmiConnectFailure TRAP-TYPE
        ENTERPRISE volubill
        VARIABLES { trapSeverity, sourceComponent, componentInfo }
        DESCRIPTION
                "BSSG SMI Connection Failure"
        ::= 32

bssgQuickRulesConnectFailure TRAP-TYPE
        ENTERPRISE volubill
        VARIABLES { trapSeverity, sourceComponent, componentInfo }
        DESCRIPTION
                "BSSG QuickRules Connection Failure"
        ::= 33

bssgSCDKDisconnect TRAP-TYPE
        ENTERPRISE volubill
        VARIABLES { trapSeverity, sourceComponent, componentInfo }
        DESCRIPTION
                "BSSG SCDK Disconnect"
        ::= 34

bssgDatabaseConnectFailure TRAP-TYPE
        ENTERPRISE volubill
        VARIABLES { trapSeverity, sourceComponent, componentInfo }
        DESCRIPTION
                "BSSG Database Connection Failure"
        ::= 35

bssgReloadConfig TRAP-TYPE
        ENTERPRISE volubill
        VARIABLES { trapSeverity, sourceComponent, componentInfo }
        DESCRIPTION
                "BSSG Reloaded configuration"
        ::= 36

------------------------------------------
--  BSSG Traps End : range 30 to 49 ---------
------------------------------------------

------------------------------------------
---  DCM Traps  : range 50 to 69 ---------
------------------------------------------

------------------------------------------
---  DCM Traps End : range 50 to 69 ---------
------------------------------------------

------------------------------------------
---  SMS Traps  : range 70 to 79 ---------
------------------------------------------

start TRAP-TYPE
        ENTERPRISE volubill
        VARIABLES { trapSeverity, sourceComponent, componentInfo }
        DESCRIPTION
                "The SMSModule is started on host X.X.X.X"
        ::= 70 

stop TRAP-TYPE
        ENTERPRISE volubill
        VARIABLES { trapSeverity, sourceComponent, componentInfo }
        DESCRIPTION
                "The SMSModule is stopped on host X.X.X.X"
        ::= 71 

overloadActivatedTrap TRAP-TYPE
        ENTERPRISE volubill
        VARIABLES { trapSeverity, sourceComponent, componentInfo }
        DESCRIPTION
                "The overload mode for the SMS module is activated on host X.X.X.X"
        ::= 72

overloadDesactivated TRAP-TYPE
        ENTERPRISE volubill
        VARIABLES { trapSeverity, sourceComponent, componentInfo }
        DESCRIPTION
                "The overload mode for the SMSModule is desactivated on host X.X.X.X"
        ::= 73

sCDKConnection TRAP-TYPE
        ENTERPRISE volubill
        VARIABLES { trapSeverity, sourceComponent, componentInfo }
        DESCRIPTION
                "A SCDKBis client on host X.X.X.X is connected to SMS module"
        ::= 74

sCDKDisconnection TRAP-TYPE
        ENTERPRISE volubill
        VARIABLES { trapSeverity, sourceComponent, componentInfo }
        DESCRIPTION
                "A SCDKBis client on host X.X.X.X has been disconnected to SMS module"
        ::= 75

uDRWritingError TRAP-TYPE
        ENTERPRISE volubill
        VARIABLES { trapSeverity, sourceComponent, componentInfo }
        DESCRIPTION
                "A writing error occurred on the device where the SMSModule on host X.X.X.X is running. Maybe the disc is full... You should activate the UDRZipper to economize disc space"
        ::= 76

provisioningError TRAP-TYPE
        ENTERPRISE volubill
        VARIABLES { trapSeverity, sourceComponent, componentInfo }
        DESCRIPTION
                "An error occurred with the provisioning file into the SMS Module on host X.X.X.X"
        ::= 77
                                       
activatedUDRZipper TRAP-TYPE
        ENTERPRISE volubill
        VARIABLES { trapSeverity, sourceComponent, componentInfo }
        DESCRIPTION
                "The UDRZipper is activated on host X.X.X.X"
        ::= 78
        
desactivatedUDRZipper TRAP-TYPE
        ENTERPRISE volubill
        VARIABLES { trapSeverity, sourceComponent, componentInfo }
        DESCRIPTION
                "The UDRZipper is desactivated on host X.X.X.X"
        ::= 79
                          
------------------------------------------
---  SMS Traps End : range 70 to 79 ---------
------------------------------------------

END
