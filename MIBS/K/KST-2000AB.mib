--
-- KST-2000AB.my
-- MIB generated by MG-SOFT Visual MIB Builder Version 4.0 Build 349
-- Friday, November 04, 2005 at 14:19:38
--

	KST-2000AB DEFINITIONS ::= BEGIN
 
		IMPORTS
			comtechEFData			
				FROM ComtechEFData			
			OBJECT-GROUP, MODULE-COMPLIANCE			
				FROM SNMPv2-CONF			
			OBJECT-TYPE, MODULE-IDENTITY			
				FROM SNMPv2-SMI;
	
	
		-- 1.3.6.1.4.1.6247.30
		kst2000AB MODULE-IDENTITY 
			LAST-UPDATED "200510311629Z"		-- October 31, 2005 at 16:29 GMT
			ORGANIZATION 
				"Comtech EF Data Corp."
			CONTACT-INFO 
				"Comtech EF Data Crop.
				2114 W. 7th Street
				Tempe, AZ  85281 USA
				
				Tel: 480-333-2200
				Fax: 480-333-2540
				Web: http://www.comtechefdata.com"
			DESCRIPTION 
				"Module Identity for KST-2000A/B Transceiver."
			::= { comtechEFData 30 }

		
	
--
-- Node definitions
--
	
		-- 1.3.6.1.4.1.6247.30.1
		kst2000ABObjects OBJECT IDENTIFIER ::= { kst2000AB 1 }

		
		-- 1.3.6.1.4.1.6247.30.1.1
		kstSystemInfo OBJECT IDENTIFIER ::= { kst2000ABObjects 1 }

		
		-- 1.3.6.1.4.1.6247.30.1.1.1
		kstEquipmentType OBJECT-TYPE
			SYNTAX OCTET STRING (SIZE (18..19))
			MAX-ACCESS read-only
			STATUS current
			DESCRIPTION
				"KST Equipment Type. (RET?)"
			::= { kstSystemInfo 1 }

		
		-- 1.3.6.1.4.1.6247.30.1.1.2
		kstSerialNumbers OBJECT-TYPE
			SYNTAX OCTET STRING (SIZE (79))
			MAX-ACCESS read-only
			STATUS current
			DESCRIPTION
				"KST-2000A/B Serial Numbers. (SNM?)"
			::= { kstSystemInfo 2 }

		
		-- 1.3.6.1.4.1.6247.30.1.1.3
		kstAssemblyNumbers OBJECT-TYPE
			SYNTAX OCTET STRING (SIZE (75))
			MAX-ACCESS read-only
			STATUS current
			DESCRIPTION
				"KST-2000A/B Assembly Numbers. (ANM?)"
			::= { kstSystemInfo 3 }

		
		-- 1.3.6.1.4.1.6247.30.1.1.4
		kstFirmwareNumbers OBJECT-TYPE
			SYNTAX OCTET STRING (SIZE (111))
			MAX-ACCESS read-only
			STATUS current
			DESCRIPTION
				"KST-2000A/B Firmware Numbers and Versions. (FRM?)"
			::= { kstSystemInfo 4 }

		
		-- 1.3.6.1.4.1.6247.30.1.2
		kstUnitParameters OBJECT IDENTIFIER ::= { kst2000ABObjects 2 }

		
		-- 1.3.6.1.4.1.6247.30.1.2.1
		kstCircuitID OBJECT-TYPE
			SYNTAX OCTET STRING (SIZE (0..24))
			MAX-ACCESS read-write
			STATUS current
			DESCRIPTION
				"KST-2000A/B Unit Circuit ID. (CID?, CID=)"
			::= { kstUnitParameters 1 }

		
		-- 1.3.6.1.4.1.6247.30.1.2.2
		kstAgc OBJECT-TYPE
			SYNTAX INTEGER
				{
				off(0),
				on(1),
				burst(2)
				}
			MAX-ACCESS read-write
			STATUS current
			DESCRIPTION
				"KST-2000A/B Unit AGC. (AGC?, AGC=)"
			::= { kstUnitParameters 2 }

		
		-- 1.3.6.1.4.1.6247.30.1.2.3
		kstRefOscillatorAdjust OBJECT-TYPE
			SYNTAX INTEGER (0..255)
			MAX-ACCESS read-write
			STATUS current
			DESCRIPTION
				"KST-2000A/B Reference Oscillator Adjust. (REF?, REF=)"
			::= { kstUnitParameters 3 }

		
		-- 1.3.6.1.4.1.6247.30.1.2.4
		kstLockMode OBJECT-TYPE
			SYNTAX INTEGER
				{
				off(0),
				on(1)
				}
			MAX-ACCESS read-write
			STATUS current
			DESCRIPTION
				"KST-2000A/B Lock Mode. (LOK?, LOK=)"
			::= { kstUnitParameters 4 }

		
		-- 1.3.6.1.4.1.6247.30.1.3
		kstTxParameters OBJECT IDENTIFIER ::= { kst2000ABObjects 3 }

		
		-- 1.3.6.1.4.1.6247.30.1.3.1
		kstUpConvFrequency OBJECT-TYPE
			SYNTAX INTEGER (13750..14500)
			UNITS "MHz"
			MAX-ACCESS read-write
			STATUS current
			DESCRIPTION
				"KST-2000A/B Up Converter Frequency. (UFQ?, UFQ=)"
			::= { kstTxParameters 1 }

		
		-- 1.3.6.1.4.1.6247.30.1.3.2
		kstUpConvAttenuation OBJECT-TYPE
			SYNTAX INTEGER (0..55)
			UNITS "dB"
			MAX-ACCESS read-write
			STATUS current
			DESCRIPTION
				"KST-2000A/B Up Converter Attenuation. (UAT?, UAT=)"
			::= { kstTxParameters 2 }

		
		-- 1.3.6.1.4.1.6247.30.1.3.3
		kstUpConvOutput OBJECT-TYPE
			SYNTAX INTEGER
				{
				off(0),
				on(1),
				warm(2)
				}
			MAX-ACCESS read-write
			STATUS current
			DESCRIPTION
				"KST-2000A/B Up Converter Output. (UMU?, UMU=)"
			::= { kstTxParameters 3 }

		
		-- 1.3.6.1.4.1.6247.30.1.3.4
		kstHpaPowerEnable OBJECT-TYPE
			SYNTAX INTEGER
				{
				off(0),
				on(1)
				}
			MAX-ACCESS read-write
			STATUS current
			DESCRIPTION
				"KST-2000A/B HPA Power Enable. (AMP?, AMP=)"
			::= { kstTxParameters 4 }

		
		-- 1.3.6.1.4.1.6247.30.1.3.5
		kstHpaFaultLogic OBJECT-TYPE
			SYNTAX INTEGER
				{
				noSummary(0),
				summary(1)
				}
			MAX-ACCESS read-write
			STATUS current
			DESCRIPTION
				"KST-2000A/B HPA Fault Logic. (KFE?, KFE=)"
			::= { kstTxParameters 5 }

		
		-- 1.3.6.1.4.1.6247.30.1.4
		kstRxParameters OBJECT IDENTIFIER ::= { kst2000ABObjects 4 }

		
		-- 1.3.6.1.4.1.6247.30.1.4.1
		kstDownConvFrequency OBJECT-TYPE
			SYNTAX INTEGER (10950..12750)
			UNITS "MHz"
			MAX-ACCESS read-write
			STATUS current
			DESCRIPTION
				"KST-2000A/B Down Converter Frequency. (DFQ?, DFQ=)"
			::= { kstRxParameters 1 }

		
		-- 1.3.6.1.4.1.6247.30.1.4.2
		kstDownConvAttenuation OBJECT-TYPE
			SYNTAX INTEGER (0..20)
			UNITS "dB"
			MAX-ACCESS read-write
			STATUS current
			DESCRIPTION
				"KST-2000A/B Down Converter Attenuation. (DAT?, DAT=)"
			::= { kstRxParameters 2 }

		
		-- 1.3.6.1.4.1.6247.30.1.4.3
		kstReceiveBand OBJECT-TYPE
			SYNTAX INTEGER
				{
				bandA(0),
				bandB(1),
				bandC(2)
				}
			MAX-ACCESS read-write
			STATUS current
			DESCRIPTION
				"KST-2000B Receive Band. (SRB?, SRB=)
				SRB=x, where x is,
				A = band 10950 to 11700 MHz
				B = band 11700 to 12200 MHz
				C = band 12250 to 12750 MHz"
			::= { kstRxParameters 3 }

		
		-- 1.3.6.1.4.1.6247.30.1.4.4
		kstLnaPowerEnable OBJECT-TYPE
			SYNTAX INTEGER
				{
				off(0),
				on(1)
				}
			MAX-ACCESS read-write
			STATUS current
			DESCRIPTION
				"KST-2000A/B LNA Power Enable. (LCS?, LCS=)"
			::= { kstRxParameters 4 }

		
		-- 1.3.6.1.4.1.6247.30.1.4.5
		kstLnaFaultLogic OBJECT-TYPE
			SYNTAX INTEGER
				{
				noSummary(0),
				summary(1)
				}
			MAX-ACCESS read-write
			STATUS current
			DESCRIPTION
				"KST-2000A/B LNA Fault Logic. (LFL?, LFL=)"
			::= { kstRxParameters 5 }

		
		-- 1.3.6.1.4.1.6247.30.1.5
		kstUnitStatus OBJECT IDENTIFIER ::= { kst2000ABObjects 5 }

		
		-- 1.3.6.1.4.1.6247.30.1.5.1
		kstUnitFaultStatus OBJECT-TYPE
			SYNTAX OCTET STRING (SIZE (7))
			MAX-ACCESS read-only
			STATUS current
			DESCRIPTION
				"KST-2000A/B Unit Fault Status. (CFS?, CFS=)
				CFS=ABCDEFG, where 
				A = Common Equipment Status, 0=OK, 1=FLT
				B = Reference Status, 0=OK, 1=FLT
				C = AGC Status, 0=OK, 1=FLT
				D = Up Converter Status, 0=OK, 1=FLT
				E = Down Converter Status, 0=OK, 1=FLT
				F = HPA Status, 0=OK, 1=FLT
				G = LNA Status, 0=OK, 1=FLT"
			::= { kstUnitStatus 1 }

		
		-- 1.3.6.1.4.1.6247.30.1.5.2
		kstCommonEquipmentStatus OBJECT-TYPE
			SYNTAX OCTET STRING (SIZE (4))
			MAX-ACCESS read-only
			STATUS current
			DESCRIPTION
				"KST-2000A/B Common Equipment Status. (CES?, CES=)
				CES=ABCD, where
				A = -7V PS Status, 0=OK, 1=FLT
				B = +7V PS Status, 0=OK, 1=FLT
				C = +12V PS Status, 0=OK, 1=FLT
				D = +17V PS Status, 0=OK, 1=FLT"
			::= { kstUnitStatus 2 }

		
		-- 1.3.6.1.4.1.6247.30.1.5.3
		kstReferenceStatus OBJECT-TYPE
			SYNTAX OCTET STRING (SIZE (6))
			MAX-ACCESS read-only
			STATUS current
			DESCRIPTION
				"KST-2000A/B Reference Status. (CRS?, CRS=)
				CRS=ABCDEF, where
				A = REF Source, 0=INT, 1=EXT
				B = Oscillator State, 0=COLD, 1=WARM
				C = 72M Lock Status, 0=OK, 1=FLT
				D = EXT REF Lock Status, 0=OK, 1=FLT, 2=NA
				E = EXT REF Phase_N Status, 0=OK, 1=FLT, 2=NA
				F = EXT REF Range Status, 0=OK, 1=FLT, 2=NA"
			::= { kstUnitStatus 3 }

		
		-- 1.3.6.1.4.1.6247.30.1.5.4
		kstAgcStatus OBJECT-TYPE
			SYNTAX OCTET STRING (SIZE (3))
			MAX-ACCESS read-only
			STATUS current
			DESCRIPTION
				"KST-2000A/B AGC Status. (CAS?, CAS=)
				CAS=ABC, where
				A = Loop Convergence, 0=OK, 1=FLT
				B = Excessive Input Power (EIP), 0=OK, 1=FLT
				C = Insufficient Input Power (IIP), 0=OK, 1=FLT"
			::= { kstUnitStatus 4 }

		
		-- 1.3.6.1.4.1.6247.30.1.5.5
		kstUpConvStatus OBJECT-TYPE
			SYNTAX OCTET STRING (SIZE (4))
			MAX-ACCESS read-only
			STATUS current
			DESCRIPTION
				"KST-2000A/B Up Converter Status. (CUS?, CUS=)
				CUS=ABCD, where
				A = Overtemperature Status, 0=OK, 1=FLT
				B = L-Band Synthesizer Lock Status, 0=OK, 1=FLT
				C = Ku-Band Synthesizer Lock Status, 0=OK, 1=FLT
				D = Interprocessor Comm. Status, 0=OK, 1=FLT"
			::= { kstUnitStatus 5 }

		
		-- 1.3.6.1.4.1.6247.30.1.5.6
		kstDownConvStatus OBJECT-TYPE
			SYNTAX OCTET STRING (SIZE (4))
			MAX-ACCESS read-only
			STATUS current
			DESCRIPTION
				"KST-2000A/B Down Converter Status. (CDS?, CDS=)
				CDS=ABCD, where
				A = Overtemperature Status, 0=OK, 1=FLT
				B = L-Band Synthesizer Lock Status, 0=OK, 1=FLT
				C = Ku-Band Synthesizer Lock Status, 0=OK, 1=FLT
				D = Interprocessor Comm. Status, 0=OK, 1=FLT"
			::= { kstUnitStatus 6 }

		
		-- 1.3.6.1.4.1.6247.30.1.5.7
		kstHpaStatus OBJECT-TYPE
			SYNTAX OCTET STRING (SIZE (5))
			MAX-ACCESS read-only
			STATUS current
			DESCRIPTION
				"KST-2000A/B HPA Status. (CHS?, CHS=)
				CHS=ABCDE, where
				A = Overtemperature Status, 0=OK, 1=FLT, 2=NA
				B = +9.5V Status, 0=OK, 1=FLT, 2=NA
				C = -5V Status, 0=OK, 1=FLT, 2=NA
				D = BIAS Voltage Summary Status, 0=OK, 1=FLT, 2=NA
				E = Interprocessor Comm. Status, 0=OK, 1=FLT, 2=NA"
			::= { kstUnitStatus 7 }

		
		-- 1.3.6.1.4.1.6247.30.1.5.8
		kstLnaStatus OBJECT-TYPE
			SYNTAX OCTET STRING (SIZE (1))
			MAX-ACCESS read-only
			STATUS current
			DESCRIPTION
				"KST-2000A/B LNA Status.
				0=OK, 
				1=FLT"
			::= { kstUnitStatus 8 }

		
		-- 1.3.6.1.4.1.6247.30.2
		kst2000ABConformance OBJECT IDENTIFIER ::= { kst2000AB 2 }

		
		-- 1.3.6.1.4.1.6247.30.2.1
		kst2000ABGroups OBJECT IDENTIFIER ::= { kst2000ABConformance 1 }

		
		-- 1.3.6.1.4.1.6247.30.2.1.1
		kst2000ABObjectsGroup OBJECT-GROUP
			OBJECTS { kstLnaStatus, kstHpaStatus, kstDownConvStatus, kstUpConvStatus, kstAgcStatus, 
				kstReferenceStatus, kstCommonEquipmentStatus, kstUnitFaultStatus, kstLnaFaultLogic, kstLnaPowerEnable, 
				kstReceiveBand, kstDownConvAttenuation, kstDownConvFrequency, kstHpaFaultLogic, kstHpaPowerEnable, 
				kstUpConvOutput, kstUpConvAttenuation, kstUpConvFrequency, kstLockMode, kstRefOscillatorAdjust, 
				kstAgc, kstCircuitID, kstFirmwareNumbers, kstAssemblyNumbers, kstSerialNumbers, 
				kstEquipmentType }
			STATUS current
			DESCRIPTION 
				"KST-2000A/B Objects Group."
			::= { kst2000ABGroups 1 }

		
		-- 1.3.6.1.4.1.6247.30.2.2
		kst2000ABCompliances OBJECT IDENTIFIER ::= { kst2000ABConformance 2 }

		
		-- 1.3.6.1.4.1.6247.30.2.2.1
		kst2000ABCompliance MODULE-COMPLIANCE
			STATUS current
			DESCRIPTION 
				"KST-2000A/B Compliance."
			MODULE -- this module
				MANDATORY-GROUPS { kst2000ABObjectsGroup }
			::= { kst2000ABCompliances 1 }

		
	
	END

--
-- KST-2000AB.my
--
