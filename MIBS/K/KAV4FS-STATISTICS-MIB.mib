KAV4FS-STATISTICS-MIB DEFINITIONS ::= BEGIN

--
-- Top-level of KAV4FS statistics
--

IMPORTS
   MODULE-IDENTITY
           FROM SNMPv2-SMI
   kav4LinuxFS
           FROM KAV-FOR-LINUX-FS-MIB;

statistics MODULE-IDENTITY
   LAST-UPDATED "200904031303Z"
   ORGANIZATION "www.kaspersky.com"
   CONTACT-INFO "Kaspersky Lab"
   DESCRIPTION "Defined the MIB tree for KAV4FS statistics."
   -- revisions
   REVISION "200904031303Z"
   DESCRIPTION "Initial tree."
   ::= { kav4LinuxFS 2 }


END
