----------------------------------------------
-- NOVELSAT-COMMON.mib             --
-- MIB generated by naamab, Novelsat        --
-- Sunday, September 12, 2010 at 15:46:00   --
----------------------------------------------


NOVELSAT-COMMON-MIB DEFINITIONS ::= BEGIN

IMPORTS
        OBJECT-TYPE, IpAddress, Counter32, Unsigned32, Integer32, Counter64,   
        NOTIFICATION-TYPE, OBJECT-IDENTITY, MODULE-IDENTITY
                FROM SNMPv2-SMI
        DisplayString, DateAndTime, RowStatus
                FROM SNMPv2-TC
        CounterBasedGauge64
                FROM HCNUM-TC
        nsRoot
                FROM NOVELSAT-ROOT-MIB
        ItuPerceivedSeverity
                FROM ITU-ALARM-TC-MIB;

-- ===================================================

nsCommon MODULE-IDENTITY
        LAST-UPDATED "201009121500Z"
        ORGANIZATION
                "Novelsat"
        CONTACT-INFO
                "21 Ha'taasiya St.,
                Ra'anana 43654,Israel
                --------------------------
                Tel: +972-9-7889730
                Fax: +972-9-
                e-mail: info@novelsat.com, support@novelsat.com
                http://www.novelsat.com
                --------------------------
                "
        DESCRIPTION
                "Novelsat Common MIB"

        REVISION "201009121500Z"
        DESCRIPTION
                "Version 1.0.0.X"
::= { nsRoot 2 }

-- ===================================================

nsCommonConfig  OBJECT-IDENTITY
        STATUS current
        DESCRIPTION
              "Common MIB branch that holds all common configuration parameters."
        ::= { nsCommon 1 }

-- ===================================================

nsCommonConfigManagementIP  OBJECT-IDENTITY
        STATUS current
        DESCRIPTION
              "Common MIB branch that holds all Common management IP parameters."
        ::= { nsCommonConfig 3 }
        
nsCommonConfigMgmtHostIP  OBJECT-TYPE
        SYNTAX   IpAddress
        MAX-ACCESS  read-write
        STATUS  current
        DESCRIPTION
                "This parameter holds product IP address."
        ::= { nsCommonConfigManagementIP  1 }

nsCommonConfigMgmtHostMask  OBJECT-TYPE
        SYNTAX   IpAddress 
        MAX-ACCESS  read-write
        STATUS  current
        DESCRIPTION
                "This parameter holds product network mask address."
        ::= { nsCommonConfigManagementIP  2 }

nsCommonConfigMgmtHostGW  OBJECT-TYPE
        SYNTAX   IpAddress
        MAX-ACCESS  read-write
        STATUS  current
        DESCRIPTION
                "This parameter holds product gateway address."
        ::= { nsCommonConfigManagementIP  3 }
        
nsCommonConfigMgmtHostDHCP  OBJECT-TYPE
        SYNTAX  INTEGER {
            disable (0),
            enable (1)
        }
        MAX-ACCESS  read-write
        STATUS  current
        DESCRIPTION
                "This parameter is no longer supported"
        ::= { nsCommonConfigManagementIP  4 }

nsCommonConfigMgmtHostDNS  OBJECT-TYPE
        SYNTAX   IpAddress
        MAX-ACCESS  read-write
        STATUS  current
        DESCRIPTION
                "This parameter is no longer supported"
        ::= { nsCommonConfigManagementIP  5 }

        
-- ===================================================

nsCommonConfigManagementOta  OBJECT-IDENTITY
        STATUS current
        DESCRIPTION
              "This branch is no longer supported. OTA support is now performed using Network Interfaces table"
        ::= { nsCommonConfig 8 }
        
nsCommonConfigMgmtOtaIP  OBJECT-TYPE
        SYNTAX   IpAddress
        MAX-ACCESS  read-write
        STATUS  current
        DESCRIPTION
              "This parameter is no longer supported. OTA support is now performed using Network Interfaces table"
        ::= { nsCommonConfigManagementOta  1 }

nsCommonConfigMgmtOtaMask  OBJECT-TYPE
        SYNTAX   IpAddress 
        MAX-ACCESS  read-write
        STATUS  current
        DESCRIPTION
              "This parameter is no longer supported. OTA support is now performed using Network Interfaces table"
        ::= { nsCommonConfigManagementOta  2 }
        

-- ===================================================

nsCommonConfigManagementRollback  OBJECT-IDENTITY
        STATUS current
        DESCRIPTION
              "Common MIB branch that holds all rollback parameters."
        ::= { nsCommonConfig 9 }
        
nsCommonConfigMgmtRollbackMode  OBJECT-TYPE
        SYNTAX  INTEGER {
            disable (0),
            enable (1)
        }
        MAX-ACCESS  read-write
        STATUS  current
        DESCRIPTION
                "This parameter holds rollback mode."
        ::= { nsCommonConfigManagementRollback  1 }

nsCommonConfigMgmtRollbackTimeout  OBJECT-TYPE
        SYNTAX  Unsigned32
        MAX-ACCESS  read-write
        STATUS  current
        DESCRIPTION
                "This parameter holds rollback timeout in minutes."
        ::= { nsCommonConfigManagementRollback  2 }
        
-- ===================================================

nsCommonConfigManagementRateLimiter  OBJECT-IDENTITY
        STATUS current
        DESCRIPTION
              "Common MIB branch that holds all Common management rate limiter parameters."
        ::= { nsCommonConfig 10 }
        
nsCommonConfigMgmtRateLimit  OBJECT-TYPE
        SYNTAX   Unsigned32
        MAX-ACCESS  read-write
        STATUS  current
        DESCRIPTION
                "This parameter holds management rate limit in Kbps."
        ::= { nsCommonConfigManagementRateLimiter  1 }


-- ================== Alarm and Events
nsCommonConfigAlarmsEvents  OBJECT-IDENTITY
        STATUS current
        DESCRIPTION
              "Common MIB branch that holds all Common Alarms and Events parameters."
        ::= { nsCommonConfig 11 }    
                
nsCommonConfigAlarmsEventsTable OBJECT-TYPE
    SYNTAX SEQUENCE OF CommonConfigAlarmsEventsEntry
    MAX-ACCESS not-accessible
    STATUS current
    DESCRIPTION
        "A list of Alarms and Events parameters"
    ::= { nsCommonConfigAlarmsEvents 1 } 

nsCommonConfigAlarmsEventsEntry OBJECT-TYPE
    SYNTAX      CommonConfigAlarmsEventsEntry
    MAX-ACCESS  not-accessible
    STATUS      current
    DESCRIPTION "Conceptual row in table for each alarm or event."
    INDEX   { nsCommonConfigAlarmsEventsIndex }
    ::= { nsCommonConfigAlarmsEventsTable 1 }
        
CommonConfigAlarmsEventsEntry ::=
    SEQUENCE {
        nsCommonConfigAlarmsEventsIndex              Unsigned32,
        nsCommonConfigAlarmsEventsName               DisplayString,
        nsCommonConfigAlarmsEventsMask               INTEGER,
        nsCommonConfigAlarmsEventsRelayMask          INTEGER
    } 
    
nsCommonConfigAlarmsEventsIndex  OBJECT-TYPE
        SYNTAX  Unsigned32
        MAX-ACCESS  not-accessible
        STATUS  current
        DESCRIPTION
                "This parameter holds alarm index."
        ::= { nsCommonConfigAlarmsEventsEntry  1 }        
                 
nsCommonConfigAlarmsEventsName  OBJECT-TYPE
        SYNTAX  DisplayString (SIZE(0..255))
        MAX-ACCESS  read-only
        STATUS  current
        DESCRIPTION
                "This parameter holds alarm name."
        ::= { nsCommonConfigAlarmsEventsEntry  2 }  
        
nsCommonConfigAlarmsEventsMask  OBJECT-TYPE
        SYNTAX  INTEGER {
            disable (0) ,
            enable (1)  ,
            notApplicable (255)
        }
        MAX-ACCESS  read-create
        STATUS  current
        DESCRIPTION
                "This parameter holds alarm mask."
        ::= { nsCommonConfigAlarmsEventsEntry  3 }           

nsCommonConfigAlarmsEventsRelayMask  OBJECT-TYPE
        SYNTAX  INTEGER {
            disable (0) ,
            enable (1)  ,
            notApplicable (255)
        }
        MAX-ACCESS  read-create
        STATUS  current
        DESCRIPTION
                "This parameter holds alarm mask."
        ::= { nsCommonConfigAlarmsEventsEntry  4 }           

-- ===================================================
nsCommonConfig10MhzClock  OBJECT-IDENTITY
        STATUS current
        DESCRIPTION
              "Common MIB branch that holds all Common 10Mhz clock parameters."
        ::= { nsCommonConfig 4 }
        
nsCommonConfig10MhzClockSource  OBJECT-TYPE
        SYNTAX  INTEGER {
            internal (0),
            external (1)
        }
        MAX-ACCESS  read-write
        STATUS  current
        DESCRIPTION
                "This parameter holds clock source."
        ::= { nsCommonConfig10MhzClock  1 }

nsCommonConfig10MhzClockOut  OBJECT-TYPE
        SYNTAX  INTEGER {
            off (0),
            on (1)
        }
        MAX-ACCESS  read-write
        STATUS  current
        DESCRIPTION
                "This parameter holds clock out state."
        ::= { nsCommonConfig10MhzClock  2 }

nsCommonConfig10MhzClockTxPortClock  OBJECT-TYPE
        SYNTAX  INTEGER {
            off (0),
            lband (1),
            buc (2)
        }
        MAX-ACCESS  read-write
        STATUS  current
        DESCRIPTION
                "This parameter holds TX port clock state."
        ::= { nsCommonConfig10MhzClock  3 }

nsCommonConfig10MhzClockLnbRefClock  OBJECT-TYPE
        SYNTAX  INTEGER {
            off (0),
            on (1)
        }
        MAX-ACCESS  read-write
        STATUS  current
        DESCRIPTION
                "This parameter holds LNB reference clock state."
        ::= { nsCommonConfig10MhzClock  4 }



-- ===================================================
nsCommonConfigSerialPort  OBJECT-IDENTITY
        STATUS current
        DESCRIPTION
              "Common MIB branch that holds all Common serial port parameters."
        ::= { nsCommonConfig 5 }


nsCommonConfigSerialPortBaudRate  OBJECT-TYPE
        SYNTAX  INTEGER {
            baudRate9600 (0),
            baudRate19200 (1),
            baudRate38400 (2),
            baudRate115200 (3)
        }
        MAX-ACCESS  read-write
        STATUS  current
        DESCRIPTION
                "This parameter holds serial port baud rate."
        ::= { nsCommonConfigSerialPort  1 }

nsCommonConfigSerialPortParity  OBJECT-TYPE
        SYNTAX  INTEGER {
            odd (0),
            even (1),
            none (2)
        }
        MAX-ACCESS  read-write
        STATUS  current
        DESCRIPTION
                "This parameter holds serial port parity."
        ::= { nsCommonConfigSerialPort  2 }

nsCommonConfigSerialPortDataBits  OBJECT-TYPE
        SYNTAX  INTEGER {
            dataBits5 (0),
            dataBits6 (1),
            dataBits7 (2),
            dataBits8 (3)
        }
        MAX-ACCESS  read-write
        STATUS  current
        DESCRIPTION
                "This parameter holds serial port data bits."
        ::= { nsCommonConfigSerialPort  3 }

nsCommonConfigSerialPortStopBit  OBJECT-TYPE
        SYNTAX  INTEGER {
            stopBit1 (0),
            stopBit2 (1)
        }
        MAX-ACCESS  read-write
        STATUS  current
        DESCRIPTION
                "This parameter holds serial port stop bit."
        ::= { nsCommonConfigSerialPort  4 }
          
-- ===================================================
nsCommonConfigDateTime  OBJECT-IDENTITY
        STATUS current
        DESCRIPTION
              "Common MIB branch that holds all Common serial port parameters."
        ::= { nsCommonConfig 6 }


nsCommonConfigDateAndTime  OBJECT-TYPE
		SYNTAX DateAndTime
        MAX-ACCESS  read-write
        STATUS  current
        DESCRIPTION
                "This parameter holds system date and time."
        ::= { nsCommonConfigDateTime  1 }
        
        
-- ===================================================
nsCommonConfigNetwork  OBJECT-IDENTITY
        STATUS current
        DESCRIPTION
              "Common MIB branch that holds all Common network parameters."
        ::= { nsCommonConfig 7 }

-- ================== Network Mode

nsCommonConfigNetworkForwardingMode  OBJECT-IDENTITY
        STATUS current
        DESCRIPTION
              "Common MIB branch that holds all Common forwarding mode parameters."
        ::= { nsCommonConfigNetwork 1 } 
        
nsCommonConfigNetworkMode  OBJECT-TYPE
        SYNTAX  INTEGER {
            l2TransparentBridging (0),
            l2VlanSwitching (1),
            l3IpRouting (2),
            notApplicable (255)
        }
        MAX-ACCESS  read-write
        STATUS  current
        DESCRIPTION
                "This parameter holds networking mode."
        ::= { nsCommonConfigNetworkForwardingMode  1 } 

-- ================== Interfaces
nsCommonConfigNetworkInterfaces  OBJECT-IDENTITY
        STATUS current
        DESCRIPTION
              "Common MIB branch that holds all Common Interfaces parameters."
        ::= { nsCommonConfigNetwork 2 }    
                
nsCommonConfigNetworkInterfacesTable OBJECT-TYPE
    SYNTAX SEQUENCE OF CommonConfigDataForwardInterfacesEntry
    MAX-ACCESS not-accessible
    STATUS current
    DESCRIPTION
        "A list of Interfaces parameters"
    ::= { nsCommonConfigNetworkInterfaces 1 } 

nsCommonConfigNetworkInterfacesEntry OBJECT-TYPE
    SYNTAX      CommonConfigDataForwardInterfacesEntry
    MAX-ACCESS  not-accessible
    STATUS      current
    DESCRIPTION "Conceptual row in table for each neighbor."
    INDEX   { nsCommonConfigNetworkInterfacesIndex }
    ::= { nsCommonConfigNetworkInterfacesTable 1 }
        
CommonConfigDataForwardInterfacesEntry ::=
    SEQUENCE {
        nsCommonConfigNetworkInterfacesIndex              Unsigned32,
        nsCommonConfigNetworkInterfacesName               DisplayString,
        nsCommonConfigNetworkInterfacesAdminStatus        INTEGER,
        nsCommonConfigNetworkInterfacesPortType           INTEGER,
        nsCommonConfigNetworkInterfacesMtu                Unsigned32,
        nsCommonConfigNetworkInterfacesVlan               Unsigned32,
        nsCommonConfigNetworkInterfacesIp                 IpAddress,
        nsCommonConfigNetworkInterfacesMac                DisplayString,
        nsCommonConfigNetworkInterfacesSubnetMask         IpAddress,
        nsCommonConfigNetworkInterfacesEncapsulation      INTEGER,
        nsCommonConfigNetworkInterfacesManagementControl  INTEGER,
        nsCommonConfigNetworkInterfacesAcmControl         INTEGER,
        nsCommonConfigNetworkInterfacesNotifyRowStatus    RowStatus
    } 
    
nsCommonConfigNetworkInterfacesIndex  OBJECT-TYPE
        SYNTAX  Unsigned32
        MAX-ACCESS  not-accessible
        STATUS  current
        DESCRIPTION
                "This parameter holds interface's index."
        ::= { nsCommonConfigNetworkInterfacesEntry  1 }        
                 
nsCommonConfigNetworkInterfacesName  OBJECT-TYPE
        SYNTAX  DisplayString (SIZE(0..255))
        MAX-ACCESS  read-create
        STATUS  current
        DESCRIPTION
                "This parameter holds interface's name."
        ::= { nsCommonConfigNetworkInterfacesEntry  2 }  
        
nsCommonConfigNetworkInterfacesAdminStatus  OBJECT-TYPE
        SYNTAX  INTEGER {
            disable (0) ,
            enable (1)  ,
            notApplicable (255)
        }
        MAX-ACCESS  read-create
        STATUS  current
        DESCRIPTION
                "This parameter holds interface's administrative status."
        ::= { nsCommonConfigNetworkInterfacesEntry  3 }           
        
nsCommonConfigNetworkInterfacesPortType  OBJECT-TYPE
        SYNTAX  INTEGER {
            lan (0) ,
            wan (1)  ,
            mngmt (2) ,
            loopback (3) ,
            bridge (4) ,
            notApplicable (255)
        }
        MAX-ACCESS  read-create
        STATUS  current
        DESCRIPTION
                "This parameter holds interface's port type."
        ::= { nsCommonConfigNetworkInterfacesEntry  4 }          
        
nsCommonConfigNetworkInterfacesMtu  OBJECT-TYPE
        SYNTAX  Unsigned32
        MAX-ACCESS  read-create
        STATUS  current
        DESCRIPTION
                "This parameter holds interface's MTU."
        ::= { nsCommonConfigNetworkInterfacesEntry  6 } 
        
nsCommonConfigNetworkInterfacesVlan  OBJECT-TYPE
        SYNTAX  Unsigned32
        MAX-ACCESS  read-create
        STATUS  current
        DESCRIPTION
                "This parameter holds interface's vlan/pid."
        ::= { nsCommonConfigNetworkInterfacesEntry  7 } 
        
nsCommonConfigNetworkInterfacesIp  OBJECT-TYPE
        SYNTAX  IpAddress
        MAX-ACCESS  read-create
        STATUS  current
        DESCRIPTION
                "This parameter holds interface's IP address."
        ::= { nsCommonConfigNetworkInterfacesEntry  8 }                   

nsCommonConfigNetworkInterfacesMac  OBJECT-TYPE
        SYNTAX  DisplayString (SIZE(0..255))
        MAX-ACCESS  read-create
        STATUS  current
        DESCRIPTION
                "This parameter holds interface's MAC address."
        ::= { nsCommonConfigNetworkInterfacesEntry  9 }          
        
nsCommonConfigNetworkInterfacesSubnetMask  OBJECT-TYPE
        SYNTAX  IpAddress
        MAX-ACCESS  read-create
        STATUS  current
        DESCRIPTION
                "This parameter holds interface's subnet mask."
        ::= { nsCommonConfigNetworkInterfacesEntry  10 }         
        
nsCommonConfigNetworkInterfacesEncapsulation  OBJECT-TYPE
        SYNTAX  INTEGER {
            encapsulationEth (0)      ,
            encapsulationEth8021q (1) ,
            ule (2)   ,
            gse (3)   ,
            nspe (4)  ,
            nspe2 (5)  ,
            notApplicable (255)
        }
        MAX-ACCESS  read-create
        STATUS  current
        DESCRIPTION
                "This parameter holds interface's administrative status."
        ::= { nsCommonConfigNetworkInterfacesEntry  11 }          
        
nsCommonConfigNetworkInterfacesManagementControl  OBJECT-TYPE
        SYNTAX  INTEGER {
            disable (0) ,
            enable (1)  ,
            notApplicable (255)
        }
        MAX-ACCESS  read-create
        STATUS  current
        DESCRIPTION
                "This parameter holds interface's management control status."
        ::= { nsCommonConfigNetworkInterfacesEntry  12 }           
        
nsCommonConfigNetworkInterfacesAcmControl  OBJECT-TYPE
        SYNTAX  INTEGER {
            disable (0) ,
            enable (1)  ,
            notApplicable (255)
        }
        MAX-ACCESS  read-create
        STATUS  current
        DESCRIPTION
                "This parameter holds interface's Acm control status."
        ::= { nsCommonConfigNetworkInterfacesEntry  13 }           
        
nsCommonConfigNetworkInterfacesNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkInterfacesEntry 14 }
        
        
-- ================== Neighbors        

nsCommonConfigNetworkNeighbors  OBJECT-IDENTITY
        STATUS current
        DESCRIPTION
              "Common MIB branch that holds all Common Neighbors parameters."
        ::= { nsCommonConfigNetwork 3 }    
                
nsCommonConfigNetworkNeighborsTable OBJECT-TYPE
    SYNTAX SEQUENCE OF CommonConfigDataForwardNeighborsEntry
    MAX-ACCESS not-accessible
    STATUS current
    DESCRIPTION
        "A list of Neighbors parameters"
    ::= { nsCommonConfigNetworkNeighbors 1 } 

nsCommonConfigNetworkNeighborsEntry OBJECT-TYPE
    SYNTAX      CommonConfigDataForwardNeighborsEntry
    MAX-ACCESS  not-accessible
    STATUS      current
    DESCRIPTION "Conceptual row in table for each neighbor."
    INDEX   { nsCommonConfigNetworkNeighborsIndex }
    ::= { nsCommonConfigNetworkNeighborsTable 1 }
        
CommonConfigDataForwardNeighborsEntry ::=
    SEQUENCE {
        nsCommonConfigNetworkNeighborsIndex            Unsigned32,
        nsCommonConfigNetworkNeighborsName             DisplayString,
        nsCommonConfigNetworkNeighborsIfIndex          Unsigned32,
        nsCommonConfigNetworkNeighborsIp               IpAddress,
        nsCommonConfigNetworkNeighborsMac              DisplayString,
        nsCommonConfigNetworkNeighborsSignalingIp      IpAddress,
        nsCommonConfigNetworkNeighborsModulation       INTEGER,
        nsCommonConfigNetworkNeighborsFecRate          INTEGER,
        nsCommonConfigNetworkNeighborsNotifyRowStatus  RowStatus
    } 
    
nsCommonConfigNetworkNeighborsIndex  OBJECT-TYPE
        SYNTAX  Unsigned32
        MAX-ACCESS  not-accessible
        STATUS  current
        DESCRIPTION
                "This parameter holds neighbor's index."
        ::= { nsCommonConfigNetworkNeighborsEntry  1 }        
                 
nsCommonConfigNetworkNeighborsName  OBJECT-TYPE
        SYNTAX  DisplayString (SIZE(0..255))
        MAX-ACCESS  read-create
        STATUS  current
        DESCRIPTION
                "This parameter holds neighbor's name."
        ::= { nsCommonConfigNetworkNeighborsEntry  2 }                 
                 
nsCommonConfigNetworkNeighborsIfIndex  OBJECT-TYPE
        SYNTAX  Unsigned32
        MAX-ACCESS  read-create
        STATUS  current
        DESCRIPTION
                "This parameter holds interface's index that is directly connected to this neighbor."
        ::= { nsCommonConfigNetworkNeighborsEntry  3 }                   

nsCommonConfigNetworkNeighborsIp  OBJECT-TYPE
        SYNTAX  IpAddress
        MAX-ACCESS  read-create
        STATUS  current
        DESCRIPTION
                "This parameter holds neighbor's IP address."
        ::= { nsCommonConfigNetworkNeighborsEntry  4 }                   

nsCommonConfigNetworkNeighborsMac  OBJECT-TYPE
        SYNTAX  DisplayString (SIZE(0..255))
        MAX-ACCESS  read-create
        STATUS  current
        DESCRIPTION
                "This parameter holds neighbor's MAC address."
        ::= { nsCommonConfigNetworkNeighborsEntry  5 }                   

nsCommonConfigNetworkNeighborsSignalingIp  OBJECT-TYPE
        SYNTAX  IpAddress
        MAX-ACCESS  read-create
        STATUS  current
        DESCRIPTION
                "This parameter holds neighbor's remote IP address."
        ::= { nsCommonConfigNetworkNeighborsEntry  6 }                   

nsCommonConfigNetworkNeighborsModulation  OBJECT-TYPE
        SYNTAX  INTEGER {
            modulationBpsk   (0),
            modulationQpsk   (1),
            modulation8Psk   (2),
            modulation16Qam  (3),
            modulation16Apsk (4),
            modulation32Apsk (5),
            modulation64Apsk (6),
            notApplicable (255)
        }
        MAX-ACCESS  read-create
        STATUS  current
        DESCRIPTION
                "This parameter holds neighbor's modulation."
        ::= { nsCommonConfigNetworkNeighborsEntry  7 }                   

nsCommonConfigNetworkNeighborsFecRate  OBJECT-TYPE
        SYNTAX  INTEGER {
            fec1Div5   (0),
            fec1Div4   (1),
            fec1Div3   (2),
            fec2Div5   (3),
            fec13Div30 (4),
            fec4Div9   (5),
            fec7Div15  (6),
            fec22Div45 (7),
            fec1Div2   (8),
            fec8Div15  (9),
            fec5Div9   (10),
            fec17Div30 (11),
            fec3Div5   (12),
            fec28Div45 (13),
            fec19Div30 (14),
            fec2Div3   (15),
            fec32Div45 (16),
            fec11Div15 (17),
            fec3Div4   (18),
            fec7Div9   (19),
            fec4Div5   (20),
            fec37Div45 (21),
            fec5Div6   (22),
            fec7Div8   (23),
            fec8Div9   (24),
            fec9Div10  (25),
            notApplicable (255)
        }
        MAX-ACCESS  read-create
        STATUS  current
        DESCRIPTION
                "This parameter holds neighbor's modulation."
        ::= { nsCommonConfigNetworkNeighborsEntry  8 }                   

nsCommonConfigNetworkNeighborsNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkNeighborsEntry 9 }



-- ================== Routing        

nsCommonConfigNetworkRouting  OBJECT-IDENTITY
        STATUS current
        DESCRIPTION
              "Common MIB branch that holds all Common PolicyRoute parameters."
        ::= { nsCommonConfigNetwork 4 }    

-- ================== Routing / PolicyRoute 

nsCommonConfigNetworkPolicyRoute  OBJECT-IDENTITY
        STATUS current
        DESCRIPTION
              "Common MIB branch that holds all Common PolicyRoute parameters."
        ::= { nsCommonConfigNetworkRouting 1 }   
                
nsCommonConfigNetworkPolicyRouteTable OBJECT-TYPE
    SYNTAX SEQUENCE OF CommonConfigDataForwardPolicyRouteEntry
    MAX-ACCESS not-accessible
    STATUS current
    DESCRIPTION
        "A list of PolicyRoute parameters"
    ::= { nsCommonConfigNetworkPolicyRoute 1 } 

nsCommonConfigNetworkPolicyRouteEntry OBJECT-TYPE
    SYNTAX      CommonConfigDataForwardPolicyRouteEntry
    MAX-ACCESS  not-accessible
    STATUS      current
    DESCRIPTION "Conceptual row in table for each neighbor."
    INDEX   { nsCommonConfigNetworkPolicyRouteIndex }
    ::= { nsCommonConfigNetworkPolicyRouteTable 1 }
        
CommonConfigDataForwardPolicyRouteEntry ::=
    SEQUENCE {
        nsCommonConfigNetworkPolicyRouteIndex             Unsigned32,
        nsCommonConfigNetworkPolicyRouteInputInterfaceId  Unsigned32,
        nsCommonConfigNetworkPolicyRouteRoutingTableId    Unsigned32,
        nsCommonConfigNetworkPolicyRouteNotifyRowStatus   RowStatus
    } 
    
nsCommonConfigNetworkPolicyRouteIndex  OBJECT-TYPE
        SYNTAX  Unsigned32
        MAX-ACCESS  not-accessible
        STATUS  current
        DESCRIPTION
                "This parameter holds routing policy's index."
        ::= { nsCommonConfigNetworkPolicyRouteEntry  1 }        
                 
nsCommonConfigNetworkPolicyRouteInputInterfaceId  OBJECT-TYPE
        SYNTAX  Unsigned32
        MAX-ACCESS  read-create
        STATUS  current
        DESCRIPTION
                "This parameter holds interface's index. Must exist in Interfaces' configuration table"
        ::= { nsCommonConfigNetworkPolicyRouteEntry  2 }  

nsCommonConfigNetworkPolicyRouteRoutingTableId  OBJECT-TYPE
        SYNTAX  Unsigned32
        MAX-ACCESS  read-create
        STATUS  current
        DESCRIPTION
                "This parameter holds routing policy's table ID."
        ::= { nsCommonConfigNetworkPolicyRouteEntry  3 }

nsCommonConfigNetworkPolicyRouteNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkPolicyRouteEntry 4 }

-- ================== Routing / Routes        

nsCommonConfigNetworkRoutes  OBJECT-IDENTITY
        STATUS current
        DESCRIPTION
              "Common MIB branch that holds all Common Routes parameters."
        ::= { nsCommonConfigNetworkRouting 2 }   
                
nsCommonConfigNetworkRoutesTable OBJECT-TYPE
    SYNTAX SEQUENCE OF CommonConfigDataForwardRoutesEntry
    MAX-ACCESS not-accessible
    STATUS current
    DESCRIPTION
        "A list of Routes parameters"
    ::= { nsCommonConfigNetworkRoutes 1 } 

nsCommonConfigNetworkRoutesEntry OBJECT-TYPE
    SYNTAX      CommonConfigDataForwardRoutesEntry
    MAX-ACCESS  not-accessible
    STATUS      current
    DESCRIPTION "Conceptual row in table for each neighbor."
    INDEX   { nsCommonConfigNetworkRoutesDestIpAddress, nsCommonConfigNetworkRoutesDestSubnetMask,
              nsCommonConfigNetworkRoutesNexthopIpAddress, nsCommonConfigNetworkRoutesTableId }
    ::= { nsCommonConfigNetworkRoutesTable 1 }
        
CommonConfigDataForwardRoutesEntry ::=
    SEQUENCE {
        nsCommonConfigNetworkRoutesDestIpAddress       IpAddress,
        nsCommonConfigNetworkRoutesDestSubnetMask      IpAddress,
        nsCommonConfigNetworkRoutesNexthopIpAddress    IpAddress,
        nsCommonConfigNetworkRoutesTableId             Unsigned32,
        nsCommonConfigNetworkRoutesAdminStatus         INTEGER,
        nsCommonConfigNetworkRoutesNotifyRowStatus     RowStatus
    } 
    
nsCommonConfigNetworkRoutesDestIpAddress  OBJECT-TYPE
        SYNTAX  IpAddress
        MAX-ACCESS  not-accessible
        STATUS  current
        DESCRIPTION
                "This parameter holds routes' destination IP address."
        ::= { nsCommonConfigNetworkRoutesEntry  1 }        
                 
nsCommonConfigNetworkRoutesDestSubnetMask  OBJECT-TYPE
        SYNTAX  IpAddress
        MAX-ACCESS  not-accessible
        STATUS  current
        DESCRIPTION
                "This parameter holds routes' destination subnet mask."
        ::= { nsCommonConfigNetworkRoutesEntry  2 }  

nsCommonConfigNetworkRoutesNexthopIpAddress  OBJECT-TYPE
        SYNTAX  IpAddress
        MAX-ACCESS  not-accessible
        STATUS  current
        DESCRIPTION
                "This parameter holds routes' nexthop IP address."
        ::= { nsCommonConfigNetworkRoutesEntry  3 }

nsCommonConfigNetworkRoutesTableId  OBJECT-TYPE
        SYNTAX  Unsigned32
        MAX-ACCESS  not-accessible
        STATUS  current
        DESCRIPTION
                "This parameter holds routes' table ID."
        ::= { nsCommonConfigNetworkRoutesEntry  4 }

nsCommonConfigNetworkRoutesAdminStatus  OBJECT-TYPE
        SYNTAX  INTEGER {
            disable (0) ,
            enable (1)  ,
            notApplicable (255)
        }
        MAX-ACCESS  read-create
        STATUS  current
        DESCRIPTION
                "This parameter holds interface's administrative status."
        ::= { nsCommonConfigNetworkRoutesEntry  5 }

nsCommonConfigNetworkRoutesNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkRoutesEntry 6 }


-- ================== Vlan Switching        

nsCommonConfigNetworkVlanSwitching  OBJECT-IDENTITY
        STATUS current
        DESCRIPTION
              "Common MIB branch that holds all Common VlanSwitching parameters."
        ::= { nsCommonConfigNetwork 5 }    
                
nsCommonConfigNetworkVlanSwitchingTable OBJECT-TYPE
    SYNTAX SEQUENCE OF CommonConfigDataForwardVlanSwitchingEntry
    MAX-ACCESS not-accessible
    STATUS current
    DESCRIPTION
        "A list of VlanSwitching parameters"
    ::= { nsCommonConfigNetworkVlanSwitching 1 } 

nsCommonConfigNetworkVlanSwitchingEntry OBJECT-TYPE
    SYNTAX      CommonConfigDataForwardVlanSwitchingEntry
    MAX-ACCESS  not-accessible
    STATUS      current
    DESCRIPTION "Conceptual row in table for each neighbor."
    INDEX   { nsCommonConfigNetworkVlanSwitchingVid }
    ::= { nsCommonConfigNetworkVlanSwitchingTable 1 }
        
CommonConfigDataForwardVlanSwitchingEntry ::=
    SEQUENCE {
        nsCommonConfigNetworkVlanSwitchingVid               Unsigned32,
        nsCommonConfigNetworkVlanSwitchingNeighborIndex     Unsigned32,
        nsCommonConfigNetworkVlanSwitchingAdminStatus       INTEGER,
        nsCommonConfigNetworkVlanSwitchingNotifyRowStatus   RowStatus
    } 
    
nsCommonConfigNetworkVlanSwitchingVid  OBJECT-TYPE
        SYNTAX  Unsigned32
        MAX-ACCESS  not-accessible
        STATUS  current
        DESCRIPTION
                "This parameter holds VLAN switching's VID."
        ::= { nsCommonConfigNetworkVlanSwitchingEntry  1 }        
                 
nsCommonConfigNetworkVlanSwitchingNeighborIndex  OBJECT-TYPE
        SYNTAX  Unsigned32
        MAX-ACCESS  read-create
        STATUS  current
        DESCRIPTION
                "This parameter holds VLAN switching's neighbor's index. Must exist in Neighbors' configuration table."
        ::= { nsCommonConfigNetworkVlanSwitchingEntry  2 }  

nsCommonConfigNetworkVlanSwitchingAdminStatus  OBJECT-TYPE
        SYNTAX  INTEGER {
            disable (0) ,
            enable (1)  ,
            notApplicable (255)
        }
        MAX-ACCESS  read-create
        STATUS  current
        DESCRIPTION
                "This parameter holds VLAN switching's administrative status."
        ::= { nsCommonConfigNetworkVlanSwitchingEntry  3 }

nsCommonConfigNetworkVlanSwitchingNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkVlanSwitchingEntry 4 }


-- ================== QoS        

nsCommonConfigNetworkQoS  OBJECT-IDENTITY
        STATUS current
        DESCRIPTION
              "Common MIB branch that holds all Common QoS parameters."
        ::= { nsCommonConfigNetwork 6 } 

-- ================== QoS / Classification

nsCommonConfigNetworkClassification  OBJECT-IDENTITY
        STATUS current
        DESCRIPTION
              "Common MIB branch that holds all Common classification parameters."
        ::= { nsCommonConfigNetworkQoS 1 }  
        
nsCommonConfigNetworkClassificationMode  OBJECT-TYPE
        SYNTAX  INTEGER {
            classMode802 (0),
            classModeTos (1),
            classModeMf (2),
            notApplicable (255)
        }
        MAX-ACCESS  read-write
        STATUS  current
        DESCRIPTION
                "This parameter holds classification's method."
        ::= { nsCommonConfigNetworkClassification  1 }        

-- ================== QoS / Classification / 802

nsCommonConfigNetworkClassification802  OBJECT-IDENTITY
        STATUS current
        DESCRIPTION
              "Common MIB branch that holds all Common classification parameters."
        ::= { nsCommonConfigNetworkClassification 2 }  
        
nsCommonConfigNetworkClassification802Table OBJECT-TYPE
    SYNTAX SEQUENCE OF CommonConfigDataForwardClassification802Entry
    MAX-ACCESS not-accessible
    STATUS current
    DESCRIPTION
        "A list of Classification802 parameters"
    ::= { nsCommonConfigNetworkClassification802 1 } 

nsCommonConfigNetworkClassification802Entry OBJECT-TYPE
    SYNTAX      CommonConfigDataForwardClassification802Entry
    MAX-ACCESS  not-accessible
    STATUS      current
    DESCRIPTION "Conceptual row in table for each neighbor."
    INDEX   { nsCommonConfigNetworkClassification802Priority }
    ::= { nsCommonConfigNetworkClassification802Table 1 }
        
CommonConfigDataForwardClassification802Entry ::=
    SEQUENCE {
        nsCommonConfigNetworkClassification802Priority  Unsigned32,
        nsCommonConfigNetworkClassification802CoS       INTEGER
    } 
    
nsCommonConfigNetworkClassification802Priority  OBJECT-TYPE
        SYNTAX  Unsigned32
        MAX-ACCESS  not-accessible
        STATUS  current
        DESCRIPTION
                "This parameter holds classification 802.1p priority."
        ::= { nsCommonConfigNetworkClassification802Entry  1 }        
                 
nsCommonConfigNetworkClassification802CoS  OBJECT-TYPE
        SYNTAX  INTEGER {
            cos0 (1) ,
            cos1 (2)  ,
            cos2 (3)  ,
            cos3 (4) ,
            cos4 (5)  ,
            cos5 (6)  ,
            cos6 (7) ,
            cos7 (8)  ,
            notApplicable (255)
        }
        MAX-ACCESS  read-write
        STATUS  current
        DESCRIPTION
                "This parameter holds classification 802.1p CoS."
        ::= { nsCommonConfigNetworkClassification802Entry  2 }          
        
-- ================== QoS / Classification / TOS

nsCommonConfigNetworkClassificationTos  OBJECT-IDENTITY
        STATUS current
        DESCRIPTION
              "Common MIB branch that holds all Common classification parameters."
        ::= { nsCommonConfigNetworkClassification 3 }
        
nsCommonConfigNetworkClassificationTosTable OBJECT-TYPE
    SYNTAX SEQUENCE OF CommonConfigDataForwardClassificationTosEntry
    MAX-ACCESS not-accessible
    STATUS current
    DESCRIPTION
        "A list of Classification Tos parameters"
    ::= { nsCommonConfigNetworkClassificationTos 1 } 

nsCommonConfigNetworkClassificationTosEntry OBJECT-TYPE
    SYNTAX      CommonConfigDataForwardClassificationTosEntry
    MAX-ACCESS  not-accessible
    STATUS      current
    DESCRIPTION "Conceptual row in table for each neighbor."
    INDEX   { nsCommonConfigNetworkClassificationTosPriority }
    ::= { nsCommonConfigNetworkClassificationTosTable 1 }
        
CommonConfigDataForwardClassificationTosEntry ::=
    SEQUENCE {
        nsCommonConfigNetworkClassificationTosPriority          Unsigned32,
        nsCommonConfigNetworkClassificationTosFieldValue        Unsigned32,
        nsCommonConfigNetworkClassificationTosFieldMask         Unsigned32,
        nsCommonConfigNetworkClassificationTosCoS               INTEGER,
        nsCommonConfigNetworkClassificationTosNotifyRowStatus   RowStatus,
        nsCommonConfigNetworkClassificationTosColor             INTEGER
    } 
    
nsCommonConfigNetworkClassificationTosPriority  OBJECT-TYPE
        SYNTAX  Unsigned32
        MAX-ACCESS  not-accessible
        STATUS  current
        DESCRIPTION
                "This parameter holds classification TOS priority."
        ::= { nsCommonConfigNetworkClassificationTosEntry  1 }        
                 
nsCommonConfigNetworkClassificationTosFieldValue  OBJECT-TYPE
        SYNTAX  Unsigned32
        MAX-ACCESS  read-create
        STATUS  current
        DESCRIPTION
                "This parameter holds classification TOS field value."
        ::= { nsCommonConfigNetworkClassificationTosEntry  2 }
                 
nsCommonConfigNetworkClassificationTosFieldMask  OBJECT-TYPE
        SYNTAX  Unsigned32
        MAX-ACCESS  read-create
        STATUS  current
        DESCRIPTION
                "This parameter holds classification TOS field mask."
        ::= { nsCommonConfigNetworkClassificationTosEntry  3 }
                                 
nsCommonConfigNetworkClassificationTosCoS  OBJECT-TYPE
        SYNTAX  INTEGER {
            cos0 (1) ,
            cos1 (2)  ,
            cos2 (3)  ,
            cos3 (4) ,
            cos4 (5)  ,
            cos5 (6)  ,
            cos6 (7) ,
            cos7 (8)  ,
            notApplicable (255)
        }
        MAX-ACCESS  read-create
        STATUS  current
        DESCRIPTION
                "This parameter holds classification TOS CoS."
        ::= { nsCommonConfigNetworkClassificationTosEntry  4 }          
        
nsCommonConfigNetworkClassificationTosNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkClassificationTosEntry 5 }
        
nsCommonConfigNetworkClassificationTosColor  OBJECT-TYPE
        SYNTAX  INTEGER {
            green (0) ,
            yellow (1)  ,
            notApplicable (255)
        }
        MAX-ACCESS  read-create
        STATUS  current
        DESCRIPTION
                "This parameter holds classification TOS Color. Not yet supported."
        ::= { nsCommonConfigNetworkClassificationTosEntry  6 }          
        
        
-- ================== QoS / Classification / MF   

nsCommonConfigNetworkClassificationMf  OBJECT-IDENTITY
        STATUS current
        DESCRIPTION
              "Common MIB branch that holds all Common classification parameters."
        ::= { nsCommonConfigNetworkClassification 4 }    

nsCommonConfigNetworkClassificationMfTable OBJECT-TYPE
    SYNTAX SEQUENCE OF CommonConfigDataForwardClassificationMfEntry
    MAX-ACCESS not-accessible
    STATUS current
    DESCRIPTION
        "A list of Classification Mf parameters"
    ::= { nsCommonConfigNetworkClassificationMf 1 } 

nsCommonConfigNetworkClassificationMfEntry OBJECT-TYPE
    SYNTAX      CommonConfigDataForwardClassificationMfEntry
    MAX-ACCESS  not-accessible
    STATUS      current
    DESCRIPTION "Conceptual row in table for each neighbor."
    INDEX   { nsCommonConfigNetworkClassificationMfPriority }
    ::= { nsCommonConfigNetworkClassificationMfTable 1 }
        
CommonConfigDataForwardClassificationMfEntry ::=
    SEQUENCE {
        nsCommonConfigNetworkClassificationMfPriority          Unsigned32,
        nsCommonConfigNetworkClassificationMfName              DisplayString,
        nsCommonConfigNetworkClassificationMfAdminStatus       INTEGER,
        nsCommonConfigNetworkClassificationMfVidHigh           Unsigned32,
        nsCommonConfigNetworkClassificationMfVidLow            Unsigned32,
        nsCommonConfigNetworkClassificationMfSrcIpAddressHigh  IpAddress,
        nsCommonConfigNetworkClassificationMfSrcIpAddressLow   IpAddress,
        nsCommonConfigNetworkClassificationMfDestIpAddressHigh IpAddress,
        nsCommonConfigNetworkClassificationMfDestIpAddressLow  IpAddress,
        nsCommonConfigNetworkClassificationMfProtocolStatus    INTEGER,
        nsCommonConfigNetworkClassificationMfProtocol          Unsigned32,
        nsCommonConfigNetworkClassificationMfSrcPortHigh       Unsigned32,
        nsCommonConfigNetworkClassificationMfSrcPortLow        Unsigned32,
        nsCommonConfigNetworkClassificationMfDestPortHigh      Unsigned32,
        nsCommonConfigNetworkClassificationMfDestPortLow       Unsigned32,
        nsCommonConfigNetworkClassificationMfCoS               INTEGER,
        nsCommonConfigNetworkClassificationMfNotifyRowStatus   RowStatus
    } 
    
nsCommonConfigNetworkClassificationMfPriority  OBJECT-TYPE
        SYNTAX  Unsigned32
        MAX-ACCESS  not-accessible
        STATUS  current
        DESCRIPTION
                "This parameter holds classification MF priority."
        ::= { nsCommonConfigNetworkClassificationMfEntry  1 }        
                 
nsCommonConfigNetworkClassificationMfName  OBJECT-TYPE
        SYNTAX  DisplayString (SIZE(0..255))
        MAX-ACCESS  read-create
        STATUS  current
        DESCRIPTION
                "This parameter holds classification MF name."
        ::= { nsCommonConfigNetworkClassificationMfEntry  2 }                  
                 
nsCommonConfigNetworkClassificationMfAdminStatus  OBJECT-TYPE
        SYNTAX  INTEGER {
            disable (0) ,
            enable (1)  ,
            notApplicable (255)
        }
        MAX-ACCESS  read-create
        STATUS  current
        DESCRIPTION
                "This parameter holds classification MF's administrative status."
        ::= { nsCommonConfigNetworkClassificationMfEntry  3 }

nsCommonConfigNetworkClassificationMfVidHigh  OBJECT-TYPE
        SYNTAX  Unsigned32
        MAX-ACCESS  read-create
        STATUS  current
        DESCRIPTION
                "This parameter holds classification MF VID high."
        ::= { nsCommonConfigNetworkClassificationMfEntry  4 }

nsCommonConfigNetworkClassificationMfVidLow  OBJECT-TYPE
        SYNTAX  Unsigned32
        MAX-ACCESS  read-create
        STATUS  current
        DESCRIPTION
                "This parameter holds classification MF VID low."
        ::= { nsCommonConfigNetworkClassificationMfEntry  5 }
                 
nsCommonConfigNetworkClassificationMfSrcIpAddressHigh  OBJECT-TYPE
        SYNTAX  IpAddress
        MAX-ACCESS  read-create
        STATUS  current
        DESCRIPTION
                "This parameter holds classification MF source IP Address high."
        ::= { nsCommonConfigNetworkClassificationMfEntry  6 }

nsCommonConfigNetworkClassificationMfSrcIpAddressLow  OBJECT-TYPE
        SYNTAX  IpAddress
        MAX-ACCESS  read-create
        STATUS  current
        DESCRIPTION
                "This parameter holds classification MF source IP Address low."
        ::= { nsCommonConfigNetworkClassificationMfEntry  7 }
                 
nsCommonConfigNetworkClassificationMfDestIpAddressHigh  OBJECT-TYPE
        SYNTAX  IpAddress
        MAX-ACCESS  read-create
        STATUS  current
        DESCRIPTION
                "This parameter holds classification MF destination IP Address high."
        ::= { nsCommonConfigNetworkClassificationMfEntry  8 }

nsCommonConfigNetworkClassificationMfDestIpAddressLow  OBJECT-TYPE
        SYNTAX  IpAddress
        MAX-ACCESS  read-create
        STATUS  current
        DESCRIPTION
                "This parameter holds classification MF destination IP Address low."
        ::= { nsCommonConfigNetworkClassificationMfEntry  9 }

nsCommonConfigNetworkClassificationMfProtocolStatus  OBJECT-TYPE
        SYNTAX  INTEGER {
            disable (0) ,
            enable (1)  ,
            notApplicable (255)
        }
        MAX-ACCESS  read-create
        STATUS  current
        DESCRIPTION
                "This parameter holds classification MF's protocol status."
        ::= { nsCommonConfigNetworkClassificationMfEntry  10 }

nsCommonConfigNetworkClassificationMfProtocol  OBJECT-TYPE
        SYNTAX  Unsigned32
        MAX-ACCESS  read-create
        STATUS  current
        DESCRIPTION
                "This parameter holds classification MF protocol."
        ::= { nsCommonConfigNetworkClassificationMfEntry  11 }

nsCommonConfigNetworkClassificationMfSrcPortHigh  OBJECT-TYPE
        SYNTAX  Unsigned32
        MAX-ACCESS  read-create
        STATUS  current
        DESCRIPTION
                "This parameter holds classification MF source port high."
        ::= { nsCommonConfigNetworkClassificationMfEntry  12 }

nsCommonConfigNetworkClassificationMfSrcPortLow  OBJECT-TYPE
        SYNTAX  Unsigned32
        MAX-ACCESS  read-create
        STATUS  current
        DESCRIPTION
                "This parameter holds classification MF source port low."
        ::= { nsCommonConfigNetworkClassificationMfEntry  13 }

nsCommonConfigNetworkClassificationMfDestPortHigh  OBJECT-TYPE
        SYNTAX  Unsigned32
        MAX-ACCESS  read-create
        STATUS  current
        DESCRIPTION
                "This parameter holds classification MF destination port high."
        ::= { nsCommonConfigNetworkClassificationMfEntry  14 }

nsCommonConfigNetworkClassificationMfDestPortLow  OBJECT-TYPE
        SYNTAX  Unsigned32
        MAX-ACCESS  read-create
        STATUS  current
        DESCRIPTION
                "This parameter holds classification MF destination port low."
        ::= { nsCommonConfigNetworkClassificationMfEntry  15 }

nsCommonConfigNetworkClassificationMfCoS  OBJECT-TYPE
        SYNTAX  INTEGER {
            cos0 (1) ,
            cos1 (2)  ,
            cos2 (3)  ,
            cos3 (4) ,
            cos4 (5)  ,
            cos5 (6)  ,
            cos6 (7) ,
            cos7 (8)  ,
            notApplicable (255)
        }
        MAX-ACCESS  read-create
        STATUS  current
        DESCRIPTION
                "This parameter holds classification MF CoS."
        ::= { nsCommonConfigNetworkClassificationMfEntry  16 } 

nsCommonConfigNetworkClassificationMfNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkClassificationMfEntry 17 }



-- ================== QoS / Queues        

nsCommonConfigNetworkQueues  OBJECT-IDENTITY
        STATUS current
        DESCRIPTION
              "Common MIB branch that holds all Common Queues parameters."
        ::= { nsCommonConfigNetworkQoS 2 }    
                
nsCommonConfigNetworkQueuesTable OBJECT-TYPE
    SYNTAX SEQUENCE OF CommonConfigDataForwardQueuesEntry
    MAX-ACCESS not-accessible
    STATUS current
    DESCRIPTION
        "A list of Queues parameters"
    ::= { nsCommonConfigNetworkQueues 1 } 

nsCommonConfigNetworkQueuesEntry OBJECT-TYPE
    SYNTAX      CommonConfigDataForwardQueuesEntry
    MAX-ACCESS  not-accessible
    STATUS      current
    DESCRIPTION "Conceptual row in table for each neighbor."
    INDEX   { nsCommonConfigNetworkQueuesCos }
    ::= { nsCommonConfigNetworkQueuesTable 1 }
        
CommonConfigDataForwardQueuesEntry ::=
    SEQUENCE {
        nsCommonConfigNetworkQueuesCos               Unsigned32,
        nsCommonConfigNetworkQueuesSchedulingMethod  INTEGER,
        nsCommonConfigNetworkQueuesWeight            Unsigned32,
        nsCommonConfigNetworkQueuesQueueDepth     Unsigned32,
        nsCommonConfigNetworkQueuesDropDiscipline INTEGER
    } 
    
nsCommonConfigNetworkQueuesCos  OBJECT-TYPE
        SYNTAX  Unsigned32
        MAX-ACCESS  not-accessible
        STATUS  current
        DESCRIPTION
                "This parameter holds queue's number."
        ::= { nsCommonConfigNetworkQueuesEntry  1 }        
                 
nsCommonConfigNetworkQueuesSchedulingMethod  OBJECT-TYPE
        SYNTAX  INTEGER {
            strictPriority (0) ,
            drr (1)  ,
            notApplicable (255)
        }
        MAX-ACCESS  read-write
        STATUS  current
        DESCRIPTION
                "This parameter holds queue's scheduling method."
        ::= { nsCommonConfigNetworkQueuesEntry  2 }                 
                 
nsCommonConfigNetworkQueuesWeight  OBJECT-TYPE
        SYNTAX  Unsigned32
        MAX-ACCESS  read-write
        STATUS  current
        DESCRIPTION
                "This parameter holds queue's weight."
        ::= { nsCommonConfigNetworkQueuesEntry  3 }  

nsCommonConfigNetworkQueuesQueueDepth  OBJECT-TYPE
        SYNTAX  Unsigned32
        MAX-ACCESS  read-write
        STATUS  current
        DESCRIPTION
                "This parameter holds queue's max queue depth."
        ::= { nsCommonConfigNetworkQueuesEntry  4 } 

nsCommonConfigNetworkQueuesDropDiscipline  OBJECT-TYPE
        SYNTAX  INTEGER {
            tailDrop (0) ,
            wred (1)  ,
            notApplicable (255)
        }
        MAX-ACCESS  read-write
        STATUS  current
        DESCRIPTION
                "This parameter holds queue's scheduling method."
        ::= { nsCommonConfigNetworkQueuesEntry  5 }  

-- ================== QoS / remote scheduling        

nsCommonConfigNetworkRemoteScheduling  OBJECT-IDENTITY
        STATUS current
        DESCRIPTION
              "Common MIB branch that holds all Common neighbor scheduling parameters. Not yet supported... "
        ::= { nsCommonConfigNetworkQoS 3 } 

nsCommonConfigNetworkRemoteSchedulingMethod  OBJECT-TYPE
        SYNTAX  INTEGER {
            proprietry (0),
            drr (1),
            wrr (2),
            notApplicable (255)
        }
        MAX-ACCESS  read-write
        STATUS  current
        DESCRIPTION
                "This parameter holds neighbor scheduling's method. Not yet supported. "
        ::= { nsCommonConfigNetworkRemoteScheduling  1 }

nsCommonConfigNetworkRemoteSchedulingFrameMerging  OBJECT-TYPE
        SYNTAX  INTEGER {
            disable (0),
            enable (1),
            notApplicable (255)
        }
        MAX-ACCESS  read-write
        STATUS  current
        DESCRIPTION
                "This parameter holds neighbor scheduling's frame merging status. Not yet supported. "
        ::= { nsCommonConfigNetworkRemoteScheduling  2 }
        
nsCommonConfigNetworkRemoteSchedulingCosSignificance  OBJECT-TYPE
        SYNTAX  INTEGER {
            global (0),
            perRemote (1),
            notApplicable (255)
        }
        MAX-ACCESS  read-write
        STATUS  current
        DESCRIPTION
                "This parameter holds neighbor scheduling's COS significance. Not yet supported. "
        ::= { nsCommonConfigNetworkRemoteScheduling  3 }


-- ================== QoS / bw management        

nsCommonConfigNetworkBwManagement  OBJECT-IDENTITY
        STATUS current
        DESCRIPTION
              "Common MIB branch that holds all Common bandwidth management parameters. Not yet supported."
        ::= { nsCommonConfigNetworkQoS 4 } 

nsCommonConfigNetworkBwManagementTable OBJECT-TYPE
    SYNTAX SEQUENCE OF CommonConfigDataForwardBwManagementEntry
    MAX-ACCESS not-accessible
    STATUS current
    DESCRIPTION
        "A list of BwManagement parameters"
    ::= { nsCommonConfigNetworkBwManagement 1 } 

nsCommonConfigNetworkBwManagementEntry OBJECT-TYPE
    SYNTAX      CommonConfigDataForwardBwManagementEntry
    MAX-ACCESS  not-accessible
    STATUS      current
    DESCRIPTION "Conceptual row in table for each neighbor."
    INDEX   { nsCommonConfigNetworkBwManagementIndex }
    ::= { nsCommonConfigNetworkBwManagementTable 1 }
        
CommonConfigDataForwardBwManagementEntry ::=
    SEQUENCE {
        nsCommonConfigNetworkBwManagementIndex             Unsigned32,
        nsCommonConfigNetworkBwManagementNeighborIndex     Unsigned32,
        nsCommonConfigNetworkBwManagementAdminStatus       INTEGER,
        nsCommonConfigNetworkBwManagementCIR               Unsigned32,
        nsCommonConfigNetworkBwManagementCBS               Unsigned32,
        nsCommonConfigNetworkBwManagementEIR               Unsigned32,
        nsCommonConfigNetworkBwManagementEBS               Unsigned32,
        nsCommonConfigNetworkBwManagementRefModulation     INTEGER,
        nsCommonConfigNetworkBwManagementRefFecRate        INTEGER,
        nsCommonConfigNetworkBwManagementPercentage        Unsigned32,
        nsCommonConfigNetworkBwManagementNotifyRowStatus   RowStatus
    } 
    
nsCommonConfigNetworkBwManagementIndex  OBJECT-TYPE
        SYNTAX  Unsigned32
        MAX-ACCESS  not-accessible
        STATUS  current
        DESCRIPTION
                "This parameter holds bandwidth management's number."
        ::= { nsCommonConfigNetworkBwManagementEntry  1 }        
                 
nsCommonConfigNetworkBwManagementNeighborIndex  OBJECT-TYPE
        SYNTAX  Unsigned32
        MAX-ACCESS  read-create
        STATUS  current
        DESCRIPTION
                "This parameter holds bandwidth management's neighbor's index."
        ::= { nsCommonConfigNetworkBwManagementEntry  2 }                  

nsCommonConfigNetworkBwManagementAdminStatus  OBJECT-TYPE
        SYNTAX  INTEGER {
            disable (0) ,
            enable (1)  ,
            notApplicable (255)
        }
        MAX-ACCESS  read-create
        STATUS  current
        DESCRIPTION
                "This parameter holds bandwidth management's administrative status."
        ::= { nsCommonConfigNetworkBwManagementEntry  3 }

nsCommonConfigNetworkBwManagementCIR  OBJECT-TYPE
        SYNTAX  Unsigned32
        MAX-ACCESS  read-create
        STATUS  current
        DESCRIPTION
                "This parameter holds bandwidth management's CIR in bps."
        ::= { nsCommonConfigNetworkBwManagementEntry  4 }                  
                 
nsCommonConfigNetworkBwManagementCBS  OBJECT-TYPE
        SYNTAX  Unsigned32
        MAX-ACCESS  read-create
        STATUS  current
        DESCRIPTION
                "This parameter holds bandwidth management's CBS in bits."
        ::= { nsCommonConfigNetworkBwManagementEntry  5 }                  
                 
nsCommonConfigNetworkBwManagementEIR  OBJECT-TYPE
        SYNTAX  Unsigned32
        MAX-ACCESS  read-create
        STATUS  current
        DESCRIPTION
                "This parameter holds bandwidth management's EIR in bps."
        ::= { nsCommonConfigNetworkBwManagementEntry  6 }                  
                 
nsCommonConfigNetworkBwManagementEBS  OBJECT-TYPE
        SYNTAX  Unsigned32
        MAX-ACCESS  read-create
        STATUS  current
        DESCRIPTION
                "This parameter holds bandwidth management's EBS in bits."
        ::= { nsCommonConfigNetworkBwManagementEntry  7 }
                 
nsCommonConfigNetworkBwManagementRefModulation  OBJECT-TYPE
        SYNTAX  INTEGER {
            modulationBpsk   (0),
            modulationQpsk   (1),
            modulation8Psk   (2),
            modulation16Qam  (3),
            modulation16Apsk (4),
            modulation32Apsk (5),
            modulation64Apsk (6),
            notApplicable (255)
        }
        MAX-ACCESS  read-create
        STATUS  current
        DESCRIPTION
                "This parameter holds bandwidth management's reference modulation."
        ::= { nsCommonConfigNetworkBwManagementEntry  8 }                 
                 
nsCommonConfigNetworkBwManagementRefFecRate  OBJECT-TYPE
        SYNTAX  INTEGER {
            fec1Div5   (0),
            fec1Div4   (1),
            fec1Div3   (2),
            fec2Div5   (3),
            fec13Div30 (4),
            fec4Div9   (5),
            fec7Div15  (6),
            fec22Div45 (7),
            fec1Div2   (8),
            fec8Div15  (9),
            fec5Div9   (10),
            fec17Div30 (11),
            fec3Div5   (12),
            fec28Div45 (13),
            fec19Div30 (14),
            fec2Div3   (15),
            fec32Div45 (16),
            fec11Div15 (17),
            fec3Div4   (18),
            fec7Div9   (19),
            fec4Div5   (20),
            fec37Div45 (21),
            fec5Div6   (22),
            fec7Div8   (23),
            fec8Div9   (24),
            fec9Div10  (25),
            notApplicable (255)
        }
        MAX-ACCESS  read-create
        STATUS  current
        DESCRIPTION
                "This parameter holds bandwidth management's reference FEC rate."
        ::= { nsCommonConfigNetworkBwManagementEntry  9 } 

nsCommonConfigNetworkBwManagementPercentage  OBJECT-TYPE
        SYNTAX  Unsigned32
        MAX-ACCESS  read-only
        STATUS  current
        DESCRIPTION
                "This parameter holds bandwidth management's percentage in hundreds of percentage."
        ::= { nsCommonConfigNetworkBwManagementEntry  10 }
                 
nsCommonConfigNetworkBwManagementNotifyRowStatus  OBJECT-TYPE
        SYNTAX      RowStatus
        MAX-ACCESS  read-create
        STATUS      current
        DESCRIPTION
                "Used to create new rows or delete in the table.
                 Note that all rows are active(1) at all times, since 
                 default values are given to empty parameters. 
                 Value createAndGo(4) is used when all row parameters
                 are inserted at once, while createAndWait(5) is used
                 to create row with default values. 
                 Value destroy(6) is used to remove a row"
        ::= { nsCommonConfigNetworkBwManagementEntry 11 }



-- ===================================================
nsCommonMonitor  OBJECT-IDENTITY
        STATUS current
        DESCRIPTION
              "Common MIB branch that holds all Common status and alarms."
        ::= { nsCommon 2 }


-- ===================================================

nsCommonMonitorNotifications  OBJECT-IDENTITY
        STATUS current
        DESCRIPTION
              "Common MIB branch that holds all Common notifications."
        ::= { nsCommonMonitor 0 }

nsCommonMonitorEventNotification NOTIFICATION-TYPE
			OBJECTS { nsCommonMonitorEventsDateAndTime,
			    nsCommonMonitorEventsType,
				nsCommonMonitorEventsSeverity,
				nsCommonMonitorEventsSource,
				nsCommonMonitorEventsEvent,
				nsCommonMonitorEventsDescription }
			STATUS current
			DESCRIPTION 
				"This notification is sent by the target when an event is triggered"
			::= { nsCommonMonitorNotifications 1 }

-- ===================================================

nsCommonMonitorAlarms  OBJECT-IDENTITY
         STATUS current
        DESCRIPTION
              "Common MIB branch that holds all Common Alarms."
        ::= { nsCommonMonitor 1 }
 
nsCommonMonitorAlarmsTable OBJECT-TYPE
	SYNTAX SEQUENCE OF DemodAlarmsEntry
	MAX-ACCESS not-accessible
	STATUS current
	DESCRIPTION
		"List of Alarms occured"
	::= { nsCommonMonitorAlarms 1 } 

nsCommonMonitorAlarmsEntry OBJECT-TYPE
    SYNTAX      DemodAlarmsEntry
    MAX-ACCESS  not-accessible
    STATUS      current
    DESCRIPTION "Conceptual row in table for each event."
    INDEX   { nsCommonMonitorAlarmsUtcSecondsHigh, nsCommonMonitorAlarmsUtcSecondsLow,
     		nsCommonMonitorAlarmsUtcNanoSecondsHigh, nsCommonMonitorAlarmsUtcNanoSecondsLow }
    ::= { nsCommonMonitorAlarmsTable 1 }
        
DemodAlarmsEntry ::=
	SEQUENCE {
		nsCommonMonitorAlarmsUtcSecondsHigh		Counter32,
		nsCommonMonitorAlarmsUtcSecondsLow		Counter32,
		nsCommonMonitorAlarmsUtcNanoSecondsHigh	Counter32,
		nsCommonMonitorAlarmsUtcNanoSecondsLow	Counter32,
		nsCommonMonitorAlarmsDateAndTime 		DateAndTime,
		nsCommonMonitorAlarmsSeverity 		    ItuPerceivedSeverity,
		nsCommonMonitorAlarmsSource 			DisplayString,
		nsCommonMonitorAlarmsEvent 			    DisplayString,
		nsCommonMonitorAlarmsDescription		DisplayString
	} 
    
nsCommonMonitorAlarmsUtcSecondsHigh  OBJECT-TYPE
        SYNTAX  Counter32
        MAX-ACCESS  not-accessible
        STATUS  current
        DESCRIPTION
                "Seconds passed from EPOCH"
        ::= { nsCommonMonitorAlarmsEntry  1 }        
 
nsCommonMonitorAlarmsUtcSecondsLow  OBJECT-TYPE
        SYNTAX  Counter32
        MAX-ACCESS  not-accessible
        STATUS  current
        DESCRIPTION
                "Seconds passed from EPOCH"
        ::= { nsCommonMonitorAlarmsEntry  2 }        
 
nsCommonMonitorAlarmsUtcNanoSecondsHigh  OBJECT-TYPE
        SYNTAX  Counter32
        MAX-ACCESS  not-accessible
        STATUS  current
        DESCRIPTION
                "Seconds passed from EPOCH"
        ::= { nsCommonMonitorAlarmsEntry  3 }        
 
nsCommonMonitorAlarmsUtcNanoSecondsLow  OBJECT-TYPE
        SYNTAX  Counter32
        MAX-ACCESS  not-accessible
        STATUS  current
        DESCRIPTION
                "Seconds passed from EPOCH"
        ::= { nsCommonMonitorAlarmsEntry  4 }        

nsCommonMonitorAlarmsDateAndTime  OBJECT-TYPE
        SYNTAX  DateAndTime
        MAX-ACCESS  read-only
        STATUS  current
        DESCRIPTION
                "Date and Time of event"
        ::= { nsCommonMonitorAlarmsEntry  5 }        
 
nsCommonMonitorAlarmsSeverity  OBJECT-TYPE
        SYNTAX  ItuPerceivedSeverity
        MAX-ACCESS  read-only
        STATUS  current
        DESCRIPTION
                "Severity of event"
        ::= { nsCommonMonitorAlarmsEntry  6 }        
 
nsCommonMonitorAlarmsSource  OBJECT-TYPE
        SYNTAX  DisplayString (SIZE(0..255))
        MAX-ACCESS  read-only
        STATUS  current
        DESCRIPTION
                "Severity of event"
        ::= { nsCommonMonitorAlarmsEntry  7 }        
 
nsCommonMonitorAlarmsEvent  OBJECT-TYPE
        SYNTAX  DisplayString (SIZE(0..255))
        MAX-ACCESS  read-only
        STATUS  current
        DESCRIPTION
                "Severity of event"
        ::= { nsCommonMonitorAlarmsEntry  8 }        
 
nsCommonMonitorAlarmsDescription  OBJECT-TYPE
        SYNTAX  DisplayString (SIZE(0..255))
        MAX-ACCESS  read-only
        STATUS  current
        DESCRIPTION
                "Severity of event"
        ::= { nsCommonMonitorAlarmsEntry  9 }        

-- ===================================================

nsCommonMonitorEvents  OBJECT-IDENTITY
         STATUS current
        DESCRIPTION
              "Common MIB branch that holds all Common events."
        ::= { nsCommonMonitor 2 }
 
nsCommonMonitorEventsTable OBJECT-TYPE
	SYNTAX SEQUENCE OF DemodEventsEntry
	MAX-ACCESS not-accessible
	STATUS current
	DESCRIPTION
		"List of Events occured"
	::= { nsCommonMonitorEvents 1 } 

nsCommonMonitorEventsEntry OBJECT-TYPE
    SYNTAX      DemodEventsEntry
    MAX-ACCESS  not-accessible
    STATUS      current
    DESCRIPTION "Conceptual row in table for each event."
    INDEX   { 	nsCommonMonitorEventsUtcSecondsHigh, nsCommonMonitorEventsUtcSecondsLow,
 		nsCommonMonitorEventsUtcNanoSecondsHigh, nsCommonMonitorEventsUtcNanoSecondsLow }
    ::= { nsCommonMonitorEventsTable 1 }
        
DemodEventsEntry ::=
	SEQUENCE {
		nsCommonMonitorEventsUtcSecondsHigh		Counter32,
		nsCommonMonitorEventsUtcSecondsLow		Counter32,
		nsCommonMonitorEventsUtcNanoSecondsHigh		Counter32,
		nsCommonMonitorEventsUtcNanoSecondsLow		Counter32,
		nsCommonMonitorEventsDateAndTime 		DateAndTime,
		nsCommonMonitorEventsType    			INTEGER,
		nsCommonMonitorEventsSeverity 		        ItuPerceivedSeverity,
		nsCommonMonitorEventsSource 			DisplayString,
		nsCommonMonitorEventsEvent 			DisplayString,
		nsCommonMonitorEventsDescription		DisplayString
	} 
    
nsCommonMonitorEventsUtcSecondsHigh  OBJECT-TYPE
        SYNTAX  Counter32
        MAX-ACCESS  not-accessible
        STATUS  current
        DESCRIPTION
                "Seconds passed from EPOCH"
        ::= { nsCommonMonitorEventsEntry  1 }        
 
nsCommonMonitorEventsUtcSecondsLow  OBJECT-TYPE
        SYNTAX  Counter32
        MAX-ACCESS  not-accessible
        STATUS  current
        DESCRIPTION
                "Seconds passed from EPOCH"
        ::= { nsCommonMonitorEventsEntry  2 }        
 
nsCommonMonitorEventsUtcNanoSecondsHigh  OBJECT-TYPE
        SYNTAX  Counter32
        MAX-ACCESS  not-accessible
        STATUS  current
        DESCRIPTION
                "Seconds passed from EPOCH"
        ::= { nsCommonMonitorEventsEntry  3 }        
 
nsCommonMonitorEventsUtcNanoSecondsLow  OBJECT-TYPE
        SYNTAX  Counter32
        MAX-ACCESS  not-accessible
        STATUS  current
        DESCRIPTION
                "Seconds passed from EPOCH"
        ::= { nsCommonMonitorEventsEntry  4 }        

nsCommonMonitorEventsDateAndTime  OBJECT-TYPE
        SYNTAX  DateAndTime
        MAX-ACCESS  read-only
        STATUS  current
        DESCRIPTION
                "Date and Time of event"
        ::= { nsCommonMonitorEventsEntry  5 }        
 
nsCommonMonitorEventsType  OBJECT-TYPE
        SYNTAX  INTEGER {
            none (0),
            info (1),
            alarmOn(2),
            alarmOff(3)
        }
        MAX-ACCESS  read-only
        STATUS  current
        DESCRIPTION
                "Severity of event"
        ::= { nsCommonMonitorEventsEntry  6 }        
 
nsCommonMonitorEventsSeverity  OBJECT-TYPE
        SYNTAX  ItuPerceivedSeverity
        MAX-ACCESS  read-only
        STATUS  current
        DESCRIPTION
                "Severity of event"
        ::= { nsCommonMonitorEventsEntry  7 }        
 
nsCommonMonitorEventsSource  OBJECT-TYPE
        SYNTAX  DisplayString (SIZE(0..255))
        MAX-ACCESS  read-only
        STATUS  current
        DESCRIPTION
                "Severity of event"
        ::= { nsCommonMonitorEventsEntry  8 }        
 
nsCommonMonitorEventsEvent  OBJECT-TYPE
        SYNTAX  DisplayString (SIZE(0..255))
        MAX-ACCESS  read-only
        STATUS  current
        DESCRIPTION
                "Severity of event"
        ::= { nsCommonMonitorEventsEntry  9 }        
 
nsCommonMonitorEventsDescription  OBJECT-TYPE
        SYNTAX  DisplayString (SIZE(0..255))
        MAX-ACCESS  read-only
        STATUS  current
        DESCRIPTION
                "Severity of event"
        ::= { nsCommonMonitorEventsEntry  10 }        
 
 -- ===================================================

nsCommonMonitorVoltage  OBJECT-IDENTITY
         STATUS current
        DESCRIPTION
              "Common MIB branch that holds all Voltage status."
        ::= { nsCommonMonitor 3 }
 
nsCommonMonitorVoltageTable OBJECT-TYPE
    SYNTAX SEQUENCE OF CommonVoltageEntry
    MAX-ACCESS not-accessible
    STATUS current
    DESCRIPTION
        "List of Events occured"
    ::= { nsCommonMonitorVoltage 1 } 

nsCommonMonitorVoltageEntry OBJECT-TYPE
    SYNTAX      CommonVoltageEntry
    MAX-ACCESS  not-accessible
    STATUS      current
    DESCRIPTION "Conceptual row in table for each event."
    INDEX   {   nsCommonMonitorVoltageIndex }
    ::= { nsCommonMonitorVoltageTable 1 }
        
CommonVoltageEntry ::=
    SEQUENCE {
        nsCommonMonitorVoltageIndex     Counter32,
        nsCommonMonitorVoltageName      DisplayString,
        nsCommonMonitorVoltageValue     Integer32
    } 
    
nsCommonMonitorVoltageIndex  OBJECT-TYPE
        SYNTAX  Counter32
        MAX-ACCESS  not-accessible
        STATUS  current
        DESCRIPTION
                "Device voltage status index"
        ::= { nsCommonMonitorVoltageEntry  1 }        
 
nsCommonMonitorVoltageName  OBJECT-TYPE
        SYNTAX  DisplayString (SIZE(0..255))
        MAX-ACCESS  read-only
        STATUS  current
        DESCRIPTION
                "Name of voltage status"
        ::= { nsCommonMonitorVoltageEntry  2 }        
 
nsCommonMonitorVoltageValue  OBJECT-TYPE
        SYNTAX  Integer32
        MAX-ACCESS  read-only
        STATUS  current
        DESCRIPTION
                "Value of voltage status in mVoltage"
        ::= { nsCommonMonitorVoltageEntry  3 }        
 
 -- ===================================================

nsCommonMonitorPowerSupply  OBJECT-IDENTITY
         STATUS current
        DESCRIPTION
              "Common MIB branch that holds all power supply status."
        ::= { nsCommonMonitor 4 }
 
nsCommonMonitorPowerSupplyTable OBJECT-TYPE
    SYNTAX SEQUENCE OF CommonPowerSupplyEntry
    MAX-ACCESS not-accessible
    STATUS current
    DESCRIPTION
        "List of Events occured"
    ::= { nsCommonMonitorPowerSupply 1 } 

nsCommonMonitorPowerSupplyEntry OBJECT-TYPE
    SYNTAX      CommonPowerSupplyEntry
    MAX-ACCESS  not-accessible
    STATUS      current
    DESCRIPTION "Conceptual row in table for each event."
    INDEX   {   nsCommonMonitorPowerSupplyIndex }
    ::= { nsCommonMonitorPowerSupplyTable 1 }
        
CommonPowerSupplyEntry ::=
    SEQUENCE {
        nsCommonMonitorPowerSupplyIndex     Counter32,
        nsCommonMonitorPowerSupplyName      DisplayString,
        nsCommonMonitorPowerSupplyValue     DisplayString
    } 
    
nsCommonMonitorPowerSupplyIndex  OBJECT-TYPE
        SYNTAX  Counter32
        MAX-ACCESS  not-accessible
        STATUS  current
        DESCRIPTION
                "Device Power Supply status index"
        ::= { nsCommonMonitorPowerSupplyEntry  1 }        
 
nsCommonMonitorPowerSupplyName  OBJECT-TYPE
        SYNTAX  DisplayString (SIZE(0..255))
        MAX-ACCESS  read-only
        STATUS  current
        DESCRIPTION
                "Name of Power Supply status"
        ::= { nsCommonMonitorPowerSupplyEntry  2 }        
 
nsCommonMonitorPowerSupplyValue  OBJECT-TYPE
        SYNTAX  DisplayString (SIZE(0..255))
        MAX-ACCESS  read-only
        STATUS  current
        DESCRIPTION
                "Value of Power Supply status"
        ::= { nsCommonMonitorPowerSupplyEntry  3 }        
 
 -- ===================================================

nsCommonMonitorNetwork  OBJECT-IDENTITY
         STATUS current
        DESCRIPTION
              "Common MIB branch that holds all network statuses."
        ::= { nsCommonMonitor 5 }
        
nsCommonMonitorNetworkInterfaces  OBJECT-IDENTITY
         STATUS current
        DESCRIPTION
              "Common MIB branch that holds all network interfaces statuses."
        ::= { nsCommonMonitorNetwork 1 }        
 
-- ==== Interface / Lan table 
 
nsCommonMonitorNetworkInterfacesLanTable OBJECT-TYPE
    SYNTAX SEQUENCE OF CommonMonitorDataForwardInterfacesLanEntry
    MAX-ACCESS not-accessible
    STATUS current
    DESCRIPTION
        "List of interface statuses"
    ::= { nsCommonMonitorNetworkInterfaces 1 } 

nsCommonMonitorNetworkInterfacesLanEntry OBJECT-TYPE
    SYNTAX      CommonMonitorDataForwardInterfacesLanEntry
    MAX-ACCESS  not-accessible
    STATUS      current
    DESCRIPTION "Conceptual row in table for each event."
    INDEX   {   nsCommonMonitorNetworkInterfacesLanIndex }
    ::= { nsCommonMonitorNetworkInterfacesLanTable 1 }
        
CommonMonitorDataForwardInterfacesLanEntry ::=
    SEQUENCE {
        nsCommonMonitorNetworkInterfacesLanIndex        Counter32,
        nsCommonMonitorNetworkInterfacesLanName         DisplayString,
        nsCommonMonitorNetworkInterfacesLanAdminStatus  INTEGER,
        nsCommonMonitorNetworkInterfacesLanOperStatus   INTEGER,
        nsCommonMonitorNetworkInterfacesLanPort         Unsigned32,
        nsCommonMonitorNetworkInterfacesLanVlan         Unsigned32,
        nsCommonMonitorNetworkInterfacesLanMacAddress   DisplayString,
        nsCommonMonitorNetworkInterfacesLanIpAddress    IpAddress,
        nsCommonMonitorNetworkInterfacesLanSubnetMask   IpAddress
    } 
    
nsCommonMonitorNetworkInterfacesLanIndex  OBJECT-TYPE
        SYNTAX  Counter32
        MAX-ACCESS  not-accessible
        STATUS  current
        DESCRIPTION
                "Network LAN Interfaces status index"
        ::= { nsCommonMonitorNetworkInterfacesLanEntry  1 }        
 
nsCommonMonitorNetworkInterfacesLanName  OBJECT-TYPE
        SYNTAX  DisplayString (SIZE(0..255))
        MAX-ACCESS  read-only
        STATUS  current
        DESCRIPTION
                "Network LAN Interfaces status name"
        ::= { nsCommonMonitorNetworkInterfacesLanEntry  2 }        
 
nsCommonMonitorNetworkInterfacesLanAdminStatus  OBJECT-TYPE
        SYNTAX  INTEGER {
            disable (0) ,
            enable (1)  ,
            notApplicable (255)
        }
        MAX-ACCESS  read-only
        STATUS  current
        DESCRIPTION
                "Network LAN Interfaces administrator status"
        ::= { nsCommonMonitorNetworkInterfacesLanEntry  3 }        

nsCommonMonitorNetworkInterfacesLanOperStatus  OBJECT-TYPE
        SYNTAX  INTEGER {
            disable (0) ,
            enable (1)  ,
            notApplicable (255)
        }
        MAX-ACCESS  read-only
        STATUS  current
        DESCRIPTION
                "Network LAN Interfaces administrator status"
        ::= { nsCommonMonitorNetworkInterfacesLanEntry  4 }        
           
nsCommonMonitorNetworkInterfacesLanPort  OBJECT-TYPE
        SYNTAX  Unsigned32
        MAX-ACCESS  read-only
        STATUS  current
        DESCRIPTION
                "Network LAN Interfaces port status"
        ::= { nsCommonMonitorNetworkInterfacesLanEntry  5 }        

nsCommonMonitorNetworkInterfacesLanVlan  OBJECT-TYPE
        SYNTAX  Unsigned32
        MAX-ACCESS  read-only
        STATUS  current
        DESCRIPTION
                "Network LAN Interfaces port status"
        ::= { nsCommonMonitorNetworkInterfacesLanEntry  6 }        
  
nsCommonMonitorNetworkInterfacesLanMacAddress  OBJECT-TYPE
        SYNTAX  DisplayString (SIZE(0..255))
        MAX-ACCESS  read-only
        STATUS  current
        DESCRIPTION
                "Network LAN Interfaces port status"
        ::= { nsCommonMonitorNetworkInterfacesLanEntry  7 }        

nsCommonMonitorNetworkInterfacesLanIpAddress  OBJECT-TYPE
        SYNTAX  IpAddress
        MAX-ACCESS  read-only
        STATUS  current
        DESCRIPTION
                "Network LAN Interfaces port status"
        ::= { nsCommonMonitorNetworkInterfacesLanEntry  8 }        

nsCommonMonitorNetworkInterfacesLanSubnetMask  OBJECT-TYPE
        SYNTAX  IpAddress
        MAX-ACCESS  read-only
        STATUS  current
        DESCRIPTION
                "Network LAN Interfaces port status"
        ::= { nsCommonMonitorNetworkInterfacesLanEntry  9 }        
  
  
-- ==== Interface / Sat table 
 
nsCommonMonitorNetworkInterfacesSatTable OBJECT-TYPE
    SYNTAX SEQUENCE OF CommonMonitorDataForwardInterfacesSatEntry
    MAX-ACCESS not-accessible
    STATUS current
    DESCRIPTION
        "List of interface statuses"
    ::= { nsCommonMonitorNetworkInterfaces 2 } 

nsCommonMonitorNetworkInterfacesSatEntry OBJECT-TYPE
    SYNTAX      CommonMonitorDataForwardInterfacesSatEntry
    MAX-ACCESS  not-accessible
    STATUS      current
    DESCRIPTION "Conceptual row in table for each event."
    INDEX   {   nsCommonMonitorNetworkInterfacesSatIndex }
    ::= { nsCommonMonitorNetworkInterfacesSatTable 1 }
        
CommonMonitorDataForwardInterfacesSatEntry ::=
    SEQUENCE {
        nsCommonMonitorNetworkInterfacesSatIndex            Counter32,
        nsCommonMonitorNetworkInterfacesSatName             DisplayString,
        nsCommonMonitorNetworkInterfacesSatAdminStatus      INTEGER,
        nsCommonMonitorNetworkInterfacesSatOperStatus       INTEGER,
        nsCommonMonitorNetworkInterfacesSatPort             Unsigned32,
        nsCommonMonitorNetworkInterfacesSatPid              Unsigned32,
        nsCommonMonitorNetworkInterfacesSatMacAddress       DisplayString,
        nsCommonMonitorNetworkInterfacesSatIpAddress        IpAddress,
        nsCommonMonitorNetworkInterfacesSatSubnetMask       IpAddress,
        nsCommonMonitorNetworkInterfacesSatEncapsulation    INTEGER
    } 
    
nsCommonMonitorNetworkInterfacesSatIndex  OBJECT-TYPE
        SYNTAX  Counter32
        MAX-ACCESS  not-accessible
        STATUS  current
        DESCRIPTION
                "Network SAT Interfaces status index"
        ::= { nsCommonMonitorNetworkInterfacesSatEntry  1 }        
 
nsCommonMonitorNetworkInterfacesSatName  OBJECT-TYPE
        SYNTAX  DisplayString (SIZE(0..255))
        MAX-ACCESS  read-only
        STATUS  current
        DESCRIPTION
                "Network SAT Interfaces status name"
        ::= { nsCommonMonitorNetworkInterfacesSatEntry  2 }        
 
nsCommonMonitorNetworkInterfacesSatAdminStatus  OBJECT-TYPE
        SYNTAX  INTEGER {
            disable (0) ,
            enable (1)  ,
            notApplicable (255)
        }
        MAX-ACCESS  read-only
        STATUS  current
        DESCRIPTION
                "Network SAT Interfaces administrator status"
        ::= { nsCommonMonitorNetworkInterfacesSatEntry  3 }        

nsCommonMonitorNetworkInterfacesSatOperStatus  OBJECT-TYPE
        SYNTAX  INTEGER {
            disable (0) ,
            enable (1)  ,
            notApplicable (255)
        }
        MAX-ACCESS  read-only
        STATUS  current
        DESCRIPTION
                "Network SAT Interfaces operational status"
        ::= { nsCommonMonitorNetworkInterfacesSatEntry  4 }        
           
nsCommonMonitorNetworkInterfacesSatPort  OBJECT-TYPE
        SYNTAX  Unsigned32
        MAX-ACCESS  read-only
        STATUS  current
        DESCRIPTION
                "Network SAT Interfaces port status"
        ::= { nsCommonMonitorNetworkInterfacesSatEntry  5 }        

nsCommonMonitorNetworkInterfacesSatPid  OBJECT-TYPE
        SYNTAX  Unsigned32
        MAX-ACCESS  read-only
        STATUS  current
        DESCRIPTION
                "Network SAT Interfaces PID status"
        ::= { nsCommonMonitorNetworkInterfacesSatEntry  6 }        
  
nsCommonMonitorNetworkInterfacesSatMacAddress  OBJECT-TYPE
        SYNTAX  DisplayString (SIZE(0..255))
        MAX-ACCESS  read-only
        STATUS  current
        DESCRIPTION
                "Network SAT Interfaces mac address status"
        ::= { nsCommonMonitorNetworkInterfacesSatEntry  7 }        

nsCommonMonitorNetworkInterfacesSatIpAddress  OBJECT-TYPE
        SYNTAX  IpAddress
        MAX-ACCESS  read-only
        STATUS  current
        DESCRIPTION
                "Network SAT Interfaces ip address status"
        ::= { nsCommonMonitorNetworkInterfacesSatEntry  8 }        

nsCommonMonitorNetworkInterfacesSatSubnetMask  OBJECT-TYPE
        SYNTAX  IpAddress
        MAX-ACCESS  read-only
        STATUS  current
        DESCRIPTION
                "Network SAT Interfaces subnet mask status"
        ::= { nsCommonMonitorNetworkInterfacesSatEntry  9 }        
  
nsCommonMonitorNetworkInterfacesSatEncapsulation  OBJECT-TYPE
        SYNTAX  INTEGER {
            encapsulationEth (0)      ,
            encapsulationEth8021q (1) ,
            ule (2)   ,
            gse (3)   ,
            nspe (4)  ,
            notApplicable (255)
        }
        MAX-ACCESS  read-only
        STATUS  current
        DESCRIPTION
                "Network SAT Interfaces encapsulation status"
        ::= { nsCommonMonitorNetworkInterfacesSatEntry  10 }        
  
 -- ===================================================

nsCommonMonitorNetworkInterfaceStatisticsTable OBJECT-TYPE
    SYNTAX SEQUENCE OF CommonMonitorDataForwardInterfaceStatisticsEntry
    MAX-ACCESS not-accessible
    STATUS current
    DESCRIPTION
        "List of interface statuses"
    ::= { nsCommonMonitorNetwork 2 }        

nsCommonMonitorNetworkInterfaceStatisticsEntry OBJECT-TYPE
    SYNTAX      CommonMonitorDataForwardInterfaceStatisticsEntry
    MAX-ACCESS  not-accessible
    STATUS      current
    DESCRIPTION "Conceptual row in table for each event."
    INDEX   {   nsCommonMonitorNetworkInterfaceStatisticsIndex }
    ::= { nsCommonMonitorNetworkInterfaceStatisticsTable 1 }
        
CommonMonitorDataForwardInterfaceStatisticsEntry ::=
    SEQUENCE {
        nsCommonMonitorNetworkInterfaceStatisticsIndex           Counter32,
        nsCommonMonitorNetworkInterfaceStatisticsMtu             Unsigned32,
        nsCommonMonitorNetworkInterfaceStatisticsRxOk            CounterBasedGauge64,
        nsCommonMonitorNetworkInterfaceStatisticsRxError         CounterBasedGauge64,
        nsCommonMonitorNetworkInterfaceStatisticsRxDrop          CounterBasedGauge64,
        nsCommonMonitorNetworkInterfaceStatisticsRxOvr           CounterBasedGauge64,
        nsCommonMonitorNetworkInterfaceStatisticsTxOk            CounterBasedGauge64,
        nsCommonMonitorNetworkInterfaceStatisticsTxError         CounterBasedGauge64,
        nsCommonMonitorNetworkInterfaceStatisticsTxDrop          CounterBasedGauge64,
        nsCommonMonitorNetworkInterfaceStatisticsTxOvr           CounterBasedGauge64,
        nsCommonMonitorNetworkInterfaceStatisticsRxBytes         CounterBasedGauge64,
        nsCommonMonitorNetworkInterfaceStatisticsTxBytes         CounterBasedGauge64,
        nsCommonMonitorNetworkInterfaceStatisticsRxBps           CounterBasedGauge64,
        nsCommonMonitorNetworkInterfaceStatisticsTxBps           CounterBasedGauge64,
        nsCommonMonitorNetworkInterfaceStatisticsName            DisplayString
    } 
    
nsCommonMonitorNetworkInterfaceStatisticsIndex  OBJECT-TYPE
        SYNTAX  Counter32
        MAX-ACCESS  not-accessible
        STATUS  current
        DESCRIPTION
                "Network InterfaceStatistics interface's index"
        ::= { nsCommonMonitorNetworkInterfaceStatisticsEntry  1 }        
 
 nsCommonMonitorNetworkInterfaceStatisticsMtu  OBJECT-TYPE
        SYNTAX  Unsigned32
        MAX-ACCESS  not-accessible
        STATUS  current
        DESCRIPTION
                "Network InterfaceStatistics interface's MTU"
        ::= { nsCommonMonitorNetworkInterfaceStatisticsEntry  2 }        
 
 nsCommonMonitorNetworkInterfaceStatisticsRxOk  OBJECT-TYPE
        SYNTAX  CounterBasedGauge64
        MAX-ACCESS  read-only
        STATUS  current
        DESCRIPTION
                "Network Interface Statistics RX OK"
        ::= { nsCommonMonitorNetworkInterfaceStatisticsEntry  3 }        
 
 nsCommonMonitorNetworkInterfaceStatisticsRxError  OBJECT-TYPE
        SYNTAX  CounterBasedGauge64
        MAX-ACCESS  read-only
        STATUS  current
        DESCRIPTION
                "Network Interface Statistics RX Errors"
        ::= { nsCommonMonitorNetworkInterfaceStatisticsEntry  4 }        

 nsCommonMonitorNetworkInterfaceStatisticsRxDrop  OBJECT-TYPE
        SYNTAX  CounterBasedGauge64
        MAX-ACCESS  read-only
        STATUS  current
        DESCRIPTION
                "Network Interface Statistics RX Drop"
        ::= { nsCommonMonitorNetworkInterfaceStatisticsEntry  5 }        

 nsCommonMonitorNetworkInterfaceStatisticsRxOvr  OBJECT-TYPE
        SYNTAX  CounterBasedGauge64
        MAX-ACCESS  read-only
        STATUS  current
        DESCRIPTION
                "Network Interface Statistics RX Ovr"
        ::= { nsCommonMonitorNetworkInterfaceStatisticsEntry  6 }        
 
  nsCommonMonitorNetworkInterfaceStatisticsTxOk  OBJECT-TYPE
        SYNTAX  CounterBasedGauge64
        MAX-ACCESS  read-only
        STATUS  current
        DESCRIPTION
                "Network Interface Statistics TX OK"
        ::= { nsCommonMonitorNetworkInterfaceStatisticsEntry  7 }        
 
 nsCommonMonitorNetworkInterfaceStatisticsTxError  OBJECT-TYPE
        SYNTAX  CounterBasedGauge64
        MAX-ACCESS  read-only
        STATUS  current
        DESCRIPTION
                "Network Interface Statistics TX Errors"
        ::= { nsCommonMonitorNetworkInterfaceStatisticsEntry  8 }        

 nsCommonMonitorNetworkInterfaceStatisticsTxDrop  OBJECT-TYPE
        SYNTAX  CounterBasedGauge64
        MAX-ACCESS  read-only
        STATUS  current
        DESCRIPTION
                "Network Interface Statistics TX Drop"
        ::= { nsCommonMonitorNetworkInterfaceStatisticsEntry  9 }        

 nsCommonMonitorNetworkInterfaceStatisticsTxOvr  OBJECT-TYPE
        SYNTAX  CounterBasedGauge64
        MAX-ACCESS  read-only
        STATUS  current
        DESCRIPTION
                "Network Interface Statistics TX Ovr"
        ::= { nsCommonMonitorNetworkInterfaceStatisticsEntry  10 }        
 
 nsCommonMonitorNetworkInterfaceStatisticsRxBytes  OBJECT-TYPE
        SYNTAX  CounterBasedGauge64
        MAX-ACCESS  read-only
        STATUS  current
        DESCRIPTION
                "Network Interface Statistics RX Bytes"
        ::= { nsCommonMonitorNetworkInterfaceStatisticsEntry  11 }        

 nsCommonMonitorNetworkInterfaceStatisticsTxBytes  OBJECT-TYPE
        SYNTAX  CounterBasedGauge64
        MAX-ACCESS  read-only
        STATUS  current
        DESCRIPTION
                "Network Interface Statistics TX Bytes"
        ::= { nsCommonMonitorNetworkInterfaceStatisticsEntry  12 }        

 nsCommonMonitorNetworkInterfaceStatisticsRxBps  OBJECT-TYPE
        SYNTAX  CounterBasedGauge64
        MAX-ACCESS  read-only
        STATUS  current
        DESCRIPTION
                "Network Interface Statistics RX Bps"
        ::= { nsCommonMonitorNetworkInterfaceStatisticsEntry  13 }        

 nsCommonMonitorNetworkInterfaceStatisticsTxBps  OBJECT-TYPE
        SYNTAX  CounterBasedGauge64
        MAX-ACCESS  read-only
        STATUS  current
        DESCRIPTION
                "Network Interface Statistics TX Bps"
        ::= { nsCommonMonitorNetworkInterfaceStatisticsEntry  14 }        
 
 nsCommonMonitorNetworkInterfaceStatisticsName  OBJECT-TYPE
        SYNTAX  DisplayString (SIZE(0..255))
        MAX-ACCESS  read-only
        STATUS  current
        DESCRIPTION
                "Network Interface Name"
        ::= { nsCommonMonitorNetworkInterfaceStatisticsEntry  15 }        
 
 
  -- ===================================================

nsCommonMonitorNetworkQueuesStatisticsTable OBJECT-TYPE
    SYNTAX SEQUENCE OF CommonMonitorDataForwardQueuesStatisticsEntry
    MAX-ACCESS not-accessible
    STATUS current
    DESCRIPTION
        "List of interface statuses"
    ::= { nsCommonMonitorNetwork 3 }        

nsCommonMonitorNetworkQueuesStatisticsEntry OBJECT-TYPE
    SYNTAX      CommonMonitorDataForwardQueuesStatisticsEntry
    MAX-ACCESS  not-accessible
    STATUS      current
    DESCRIPTION "Conceptual row in table for each event."
    INDEX   {   nsCommonMonitorNetworkQueuesStatisticsNeighborIndex , nsCommonMonitorNetworkQueuesStatisticsCos }
    ::= { nsCommonMonitorNetworkQueuesStatisticsTable 1 }
        
CommonMonitorDataForwardQueuesStatisticsEntry ::=
    SEQUENCE {
        nsCommonMonitorNetworkQueuesStatisticsNeighborIndex         Counter32,
        nsCommonMonitorNetworkQueuesStatisticsCos                   INTEGER,
        nsCommonMonitorNetworkQueuesStatisticsEnqueuedBytes         Counter64,
        nsCommonMonitorNetworkQueuesStatisticsEnqueuedPackets       Counter64,
        nsCommonMonitorNetworkQueuesStatisticsBackloggedBytes       Counter64,
        nsCommonMonitorNetworkQueuesStatisticsBackloggedPackets     Counter64,
        nsCommonMonitorNetworkQueuesStatisticsDroppedYellowPackets  Counter64,
        nsCommonMonitorNetworkQueuesStatisticsDroppedGreenPackets   Counter64
    } 
    
nsCommonMonitorNetworkQueuesStatisticsNeighborIndex  OBJECT-TYPE
        SYNTAX  Counter32
        MAX-ACCESS  not-accessible
        STATUS  current
        DESCRIPTION
                "Network QueuesStatistics neighbor's index"
        ::= { nsCommonMonitorNetworkQueuesStatisticsEntry  1 }        
 
nsCommonMonitorNetworkQueuesStatisticsCos  OBJECT-TYPE
        SYNTAX  INTEGER {
            cos0 (1) ,
            cos1 (2)  ,
            cos2 (3)  ,
            cos3 (4) ,
            cos4 (5)  ,
            cos5 (6)  ,
            cos6 (7) ,
            cos7 (8)  ,
            notApplicable (255)
        }
        MAX-ACCESS  not-accessible
        STATUS  current
        DESCRIPTION
                "Network Queues Statistics TX Bytes value"
        ::= { nsCommonMonitorNetworkQueuesStatisticsEntry  2 }        
 
 nsCommonMonitorNetworkQueuesStatisticsEnqueuedBytes  OBJECT-TYPE
        SYNTAX  Counter64
        MAX-ACCESS  read-only
        STATUS  current
        DESCRIPTION
                "Network Queues Statistics enqueued bytes value"
        ::= { nsCommonMonitorNetworkQueuesStatisticsEntry  3 }
 
 nsCommonMonitorNetworkQueuesStatisticsEnqueuedPackets  OBJECT-TYPE
        SYNTAX  Counter64
        MAX-ACCESS  read-only
        STATUS  current
        DESCRIPTION
                "Network Queues Statistics enqueued packets value"
        ::= { nsCommonMonitorNetworkQueuesStatisticsEntry  4 }
 
 nsCommonMonitorNetworkQueuesStatisticsBackloggedBytes  OBJECT-TYPE
        SYNTAX  Counter64
        MAX-ACCESS  read-only
        STATUS  current
        DESCRIPTION
                "Network Queues Statistics backlogged bytes value"
        ::= { nsCommonMonitorNetworkQueuesStatisticsEntry  5 }
 
 nsCommonMonitorNetworkQueuesStatisticsBackloggedPackets  OBJECT-TYPE
        SYNTAX  Counter64
        MAX-ACCESS  read-only
        STATUS  current
        DESCRIPTION
                "Network Queues Statistics backlogged packets value"
        ::= { nsCommonMonitorNetworkQueuesStatisticsEntry  6 } 
 
 nsCommonMonitorNetworkQueuesStatisticsDroppedYellowPackets  OBJECT-TYPE
        SYNTAX  Counter64
        MAX-ACCESS  read-only
        STATUS  current
        DESCRIPTION
                "Network Queues Statistics dropped green packets bytes value"
        ::= { nsCommonMonitorNetworkQueuesStatisticsEntry  7 }
 
 nsCommonMonitorNetworkQueuesStatisticsDroppedGreenPackets  OBJECT-TYPE
        SYNTAX  Counter64
        MAX-ACCESS  read-only
        STATUS  current
        DESCRIPTION
                "Network Queues Statistics dropped yellow packets value"
        ::= { nsCommonMonitorNetworkQueuesStatisticsEntry  8 }  
 
 
 -- ===================================================

nsCommonMonitorNetworkNeighborsStatisticsTable OBJECT-TYPE
    SYNTAX SEQUENCE OF CommonMonitorDataForwardNeighborsStatisticsEntry
    MAX-ACCESS not-accessible
    STATUS current
    DESCRIPTION
        "List of Neighbors statuses"
    ::= { nsCommonMonitorNetwork 4 }        

nsCommonMonitorNetworkNeighborsStatisticsEntry OBJECT-TYPE
    SYNTAX      CommonMonitorDataForwardNeighborsStatisticsEntry
    MAX-ACCESS  not-accessible
    STATUS      current
    DESCRIPTION "Conceptual row in table for each event."
    INDEX   {   nsCommonMonitorNetworkNeighborsStatisticsIndex }
    ::= { nsCommonMonitorNetworkNeighborsStatisticsTable 1 }
        
CommonMonitorDataForwardNeighborsStatisticsEntry ::=
    SEQUENCE {
        nsCommonMonitorNetworkNeighborsStatisticsIndex               Counter32,
        nsCommonMonitorNetworkNeighborsStatisticsAverageTxRate       Counter64,
        nsCommonMonitorNetworkNeighborsStatisticsAverageTxPacketRate Counter64,
        nsCommonMonitorNetworkNeighborsStatisticsTxBytes             Counter64,
        nsCommonMonitorNetworkNeighborsStatisticsTxPackets           Counter64
    } 
    
nsCommonMonitorNetworkNeighborsStatisticsIndex  OBJECT-TYPE
        SYNTAX  Counter32
        MAX-ACCESS  not-accessible
        STATUS  current
        DESCRIPTION
                "Network Neighbors Statistics neighbor's index"
        ::= { nsCommonMonitorNetworkNeighborsStatisticsEntry  1 }        
 
nsCommonMonitorNetworkNeighborsStatisticsAverageTxRate  OBJECT-TYPE
        SYNTAX  Counter64
        MAX-ACCESS  read-only
        STATUS  current
        DESCRIPTION
                "Network Neighbors Statistics average TX rate value"
        ::= { nsCommonMonitorNetworkNeighborsStatisticsEntry  2 }        
 
 nsCommonMonitorNetworkNeighborsStatisticsAverageTxPacketRate  OBJECT-TYPE
        SYNTAX  Counter64
        MAX-ACCESS  read-only
        STATUS  current
        DESCRIPTION
                "Network Neighbors Statistics average TX packets rate value"
        ::= { nsCommonMonitorNetworkNeighborsStatisticsEntry  3 }
 
 nsCommonMonitorNetworkNeighborsStatisticsTxBytes  OBJECT-TYPE
        SYNTAX  Counter64
        MAX-ACCESS  read-only
        STATUS  current
        DESCRIPTION
                "Network Neighbors Statistics TX bytes value"
        ::= { nsCommonMonitorNetworkNeighborsStatisticsEntry  4 }        
 
 nsCommonMonitorNetworkNeighborsStatisticsTxPackets  OBJECT-TYPE
        SYNTAX  Counter64
        MAX-ACCESS  read-only
        STATUS  current
        DESCRIPTION
                "Network Neighbors Statistics TX Packets value"
        ::= { nsCommonMonitorNetworkNeighborsStatisticsEntry  5 }
 
  -- ===================================================

nsCommonMonitorNetworkBwManagementStatisticsTable OBJECT-TYPE
    SYNTAX SEQUENCE OF CommonMonitorDataForwardBwManagementStatisticsEntry
    MAX-ACCESS not-accessible
    STATUS current
    DESCRIPTION
        "List of interface statuses"
    ::= { nsCommonMonitorNetwork 5 }        

nsCommonMonitorNetworkBwManagementStatisticsEntry OBJECT-TYPE
    SYNTAX      CommonMonitorDataForwardBwManagementStatisticsEntry
    MAX-ACCESS  not-accessible
    STATUS      current
    DESCRIPTION "Conceptual row in table for each event."
    INDEX   {   nsCommonMonitorNetworkBwManagementStatisticsNeighborIndex }
    ::= { nsCommonMonitorNetworkBwManagementStatisticsTable 1 }
        
CommonMonitorDataForwardBwManagementStatisticsEntry ::=
    SEQUENCE {
        nsCommonMonitorNetworkBwManagementStatisticsNeighborIndex         Counter32,
        nsCommonMonitorNetworkBwManagementStatisticsGreenPackets          Counter64,
        nsCommonMonitorNetworkBwManagementStatisticsGreenRates            Counter64,
        nsCommonMonitorNetworkBwManagementStatisticsYellowPackets         Counter64,
        nsCommonMonitorNetworkBwManagementStatisticsYellowRates           Counter64,
        nsCommonMonitorNetworkBwManagementStatisticsRedPackets            Counter64,
        nsCommonMonitorNetworkBwManagementStatisticsRedRates              Counter64   
    } 
    
nsCommonMonitorNetworkBwManagementStatisticsNeighborIndex  OBJECT-TYPE
        SYNTAX  Counter32
        MAX-ACCESS  not-accessible
        STATUS  current
        DESCRIPTION
                "Network BwManagementStatistics neighbor's index"
        ::= { nsCommonMonitorNetworkBwManagementStatisticsEntry  1 }        
 
nsCommonMonitorNetworkBwManagementStatisticsGreenPackets  OBJECT-TYPE
        SYNTAX  Counter64
        MAX-ACCESS  read-only
        STATUS  current
        DESCRIPTION
                "Network BwManagement Statistics green packets value"
        ::= { nsCommonMonitorNetworkBwManagementStatisticsEntry  2 }        
 
 nsCommonMonitorNetworkBwManagementStatisticsGreenRates  OBJECT-TYPE
        SYNTAX  Counter64
        MAX-ACCESS  read-only
        STATUS  current
        DESCRIPTION
                "Network BwManagement Statistics green rates value"
        ::= { nsCommonMonitorNetworkBwManagementStatisticsEntry  3 }
 
 nsCommonMonitorNetworkBwManagementStatisticsYellowPackets  OBJECT-TYPE
        SYNTAX  Counter64
        MAX-ACCESS  read-only
        STATUS  current
        DESCRIPTION
                "Network BwManagement Statistics yellow packets value"
        ::= { nsCommonMonitorNetworkBwManagementStatisticsEntry  4 }
 
 nsCommonMonitorNetworkBwManagementStatisticsYellowRates  OBJECT-TYPE
        SYNTAX  Counter64
        MAX-ACCESS  read-only
        STATUS  current
        DESCRIPTION
                "Network BwManagement Statistics yellow rates value"
        ::= { nsCommonMonitorNetworkBwManagementStatisticsEntry  5 }
 
 nsCommonMonitorNetworkBwManagementStatisticsRedPackets  OBJECT-TYPE
        SYNTAX  Counter64
        MAX-ACCESS  read-only
        STATUS  current
        DESCRIPTION
                "Network BwManagement Statistics red packets value"
        ::= { nsCommonMonitorNetworkBwManagementStatisticsEntry  6 } 
 
 nsCommonMonitorNetworkBwManagementStatisticsRedRates  OBJECT-TYPE
        SYNTAX  Counter64
        MAX-ACCESS  read-only
        STATUS  current
        DESCRIPTION
                "Network BwManagement Statistics red rates value"
        ::= { nsCommonMonitorNetworkBwManagementStatisticsEntry  7 }
 
  nsCommonMonitorNetworkInterfaceClrCmd  OBJECT-TYPE
        SYNTAX  INTEGER {
            none (0),
            execute (1),
            notApplicable (255)
        }
        MAX-ACCESS  read-write
        STATUS  current
        DESCRIPTION
                "Clear interfaces statistics counters command" 
        ::= { nsCommonMonitorNetwork  6 }
 
 
 -- ===================================================
nsCommonSystem  OBJECT-IDENTITY
        STATUS current
        DESCRIPTION
              "Common MIB branch that holds all System status."
        ::= { nsCommon 3 }
        
 -- ===================================================
 
 nsCommonSystemSwVersion  OBJECT-IDENTITY
         STATUS current
        DESCRIPTION
              "Common MIB branch that holds all Common software Version."
        ::= { nsCommonSystem 1 }
 
nsCommonSystemSwVersionFirmware  OBJECT-TYPE
        SYNTAX  DisplayString (SIZE(0..255))
        MAX-ACCESS  read-only
        STATUS  current
        DESCRIPTION
                "Firmware version"
        ::= { nsCommonSystemSwVersion  1 }        
 
nsCommonSystemSwVersionOs  OBJECT-TYPE
        SYNTAX  DisplayString (SIZE(0..255))
        MAX-ACCESS  read-only
        STATUS  current
        DESCRIPTION
                "OS version"
        ::= { nsCommonSystemSwVersion  2 }        
 
nsCommonSystemSwVersionFs  OBJECT-TYPE
        SYNTAX  DisplayString (SIZE(0..255))
        MAX-ACCESS  read-only
        STATUS  current
        DESCRIPTION
                "FS version"
        ::= { nsCommonSystemSwVersion  3 }        

nsCommonSystemSwVersionDb  OBJECT-TYPE
        SYNTAX  DisplayString (SIZE(0..255))
        MAX-ACCESS  read-only
        STATUS  current
        DESCRIPTION
                "DB version"
        ::= { nsCommonSystemSwVersion  4 }        

 nsCommonSystemSwVersionAppTable OBJECT-TYPE
	SYNTAX SEQUENCE OF SwVersionAppEntry
	MAX-ACCESS not-accessible
	STATUS current
	DESCRIPTION
		"List of software Version"
	::= { nsCommonSystemSwVersion 5 } 
 
 nsCommonSystemSwVersionAppEntry OBJECT-TYPE
    SYNTAX      SwVersionAppEntry
    MAX-ACCESS  not-accessible
    STATUS      current
    DESCRIPTION "Conceptual row in table for each event."
    INDEX   { 	nsCommonSystemSwVersionAppType }
    ::= { nsCommonSystemSwVersionAppTable 1 }
 
 SwVersionAppEntry ::=
	SEQUENCE {
		nsCommonSystemSwVersionAppType		    INTEGER,
		nsCommonSystemSwVersionAppWeb 	            DisplayString,
		nsCommonSystemSwVersionAppFP                DisplayString,
		nsCommonSystemSwVersionAppCLI     	    DisplayString,
		nsCommonSystemSwVersionAppNsmd    	    DisplayString,
		nsCommonSystemSwVersionAppPIC 		    DisplayString
	} 


 nsCommonSystemSwVersionAppType  OBJECT-TYPE
        SYNTAX  INTEGER {
           active (1),
           main (2),
           backup (3)
        }
        MAX-ACCESS  not-accessible
        STATUS  current
        DESCRIPTION
                "Card ID"
        ::= { nsCommonSystemSwVersionAppEntry  1 }        

nsCommonSystemSwVersionAppWeb  OBJECT-TYPE
        SYNTAX  DisplayString (SIZE(0..255))
        MAX-ACCESS  read-only
        STATUS  current
        DESCRIPTION
                "WEB active version"
        ::= { nsCommonSystemSwVersionAppEntry  2 }        

nsCommonSystemSwVersionAppFP  OBJECT-TYPE
        SYNTAX  DisplayString (SIZE(0..255))
        MAX-ACCESS  read-only
        STATUS  current
        DESCRIPTION
                "FP active version"
        ::= { nsCommonSystemSwVersionAppEntry  3 }
        
nsCommonSystemSwVersionAppCLI  OBJECT-TYPE
        SYNTAX  DisplayString (SIZE(0..255))
        MAX-ACCESS  read-only
        STATUS  current
        DESCRIPTION
                "CLI active version"
        ::= { nsCommonSystemSwVersionAppEntry  4 }
       
 nsCommonSystemSwVersionAppNsmd  OBJECT-TYPE
        SYNTAX  DisplayString (SIZE(0..255))
        MAX-ACCESS  read-only
        STATUS  current
        DESCRIPTION
                "NSMD active version"
        ::= { nsCommonSystemSwVersionAppEntry  5 }
 
 nsCommonSystemSwVersionAppPIC  OBJECT-TYPE
        SYNTAX  DisplayString (SIZE(0..255))
        MAX-ACCESS  read-only
        STATUS  current
        DESCRIPTION
                "PIC active version"
        ::= { nsCommonSystemSwVersionAppEntry  6 }
 
 -- ===================================================
 
 nsCommonSystemHwConfig  OBJECT-IDENTITY
         STATUS current
        DESCRIPTION
              "Common MIB branch that holds all Common software Version."
        ::= { nsCommonSystem 2 }
        
 nsCommonSystemHwConfigProductType  OBJECT-TYPE
        SYNTAX  DisplayString (SIZE(0..255))
        MAX-ACCESS  read-only
        STATUS  current
        DESCRIPTION
                "Product type"
        ::= { nsCommonSystemHwConfig  1 }

 nsCommonSystemHwConfigSerialNumber  OBJECT-TYPE
        SYNTAX  DisplayString (SIZE(0..255))
        MAX-ACCESS  read-only
        STATUS  current
        DESCRIPTION
                "Product serial number"
        ::= { nsCommonSystemHwConfig  2 }

 nsCommonSystemHwConfigHardwareVersion  OBJECT-TYPE
        SYNTAX  DisplayString (SIZE(0..255))
        MAX-ACCESS  read-only
        STATUS  current
        DESCRIPTION
                "Product hardware number"
        ::= { nsCommonSystemHwConfig  3 }

 nsCommonSystemHwConfigMacAddress  OBJECT-TYPE
        SYNTAX  DisplayString (SIZE(0..255))
        MAX-ACCESS  read-only
        STATUS  current
        DESCRIPTION
                "Product management port MAC address"
        ::= { nsCommonSystemHwConfig  4 }

 nsCommonSystemHwConfigInternalClockType  OBJECT-TYPE
        SYNTAX  DisplayString (SIZE(0..255))
        MAX-ACCESS  read-only
        STATUS  current
        DESCRIPTION
                "Product internal clock type"
        ::= { nsCommonSystemHwConfig  5 }
  
 nsCommonSystemHwConfigCardTable OBJECT-TYPE
		SYNTAX SEQUENCE OF HwConfigCardEntry
		MAX-ACCESS not-accessible
		STATUS current
		DESCRIPTION
				"List of Cards"
		::= { nsCommonSystemHwConfig 6 } 
 
 nsCommonSystemHwConfigCardEntry OBJECT-TYPE
    	SYNTAX      HwConfigCardEntry
    	MAX-ACCESS  not-accessible
    	STATUS      current
    	DESCRIPTION "Conceptual row in table for each event."
    	INDEX   { nsCommonSystemHwConfigCardID	 }
    	::= { nsCommonSystemHwConfigCardTable 1 }
 
 HwConfigCardEntry ::=
	SEQUENCE {
		nsCommonSystemHwConfigCardID		    Unsigned32,
		nsCommonSystemHwConfigCardType 	        DisplayString,
		nsCommonSystemHwConfigCardSerialNumber  DisplayString,
		nsCommonSystemHwConfigCardHwVersion		DisplayString,
		nsCommonSystemHwConfigCardSwVersion     DisplayString
	} 
 
 nsCommonSystemHwConfigCardID  OBJECT-TYPE
        SYNTAX  Unsigned32
        MAX-ACCESS  not-accessible
        STATUS  current
        DESCRIPTION
                "Card ID"
        ::= { nsCommonSystemHwConfigCardEntry  1 }        
 
  nsCommonSystemHwConfigCardType  OBJECT-TYPE
        SYNTAX  DisplayString (SIZE(0..255))
        MAX-ACCESS  read-only
        STATUS  current
        DESCRIPTION
                "Card type"
        ::= { nsCommonSystemHwConfigCardEntry  2 }
 
  nsCommonSystemHwConfigCardSerialNumber  OBJECT-TYPE
        SYNTAX  DisplayString (SIZE(0..255))
        MAX-ACCESS  read-only
        STATUS  current
        DESCRIPTION
                "Card Serial number"
        ::= { nsCommonSystemHwConfigCardEntry  3 }

  nsCommonSystemHwConfigCardHwVersion   OBJECT-TYPE
        SYNTAX  DisplayString (SIZE(0..255))
        MAX-ACCESS  read-only
        STATUS  current
        DESCRIPTION
                "Card hardware version"
        ::= { nsCommonSystemHwConfigCardEntry  4 }

  nsCommonSystemHwConfigCardSwVersion   OBJECT-TYPE
        SYNTAX  DisplayString (SIZE(0..255))
        MAX-ACCESS  read-only
        STATUS  current
        DESCRIPTION
                "Card software version. Only for Gig-E card"
        ::= { nsCommonSystemHwConfigCardEntry  5 }
 
  nsCommonSystemHwConfigBUCFeeder  OBJECT-TYPE
        SYNTAX  DisplayString (SIZE(0..255))
        MAX-ACCESS  read-only
        STATUS  current
        DESCRIPTION
                "Product BUC Feeder configuration"
        ::= { nsCommonSystemHwConfig  7 }
 
 -- ===================================================
 
  nsCommonSystemSwUpdate  OBJECT-IDENTITY
         STATUS current
        DESCRIPTION
              "Common MIB branch that holds all Common software Version."
        ::= { nsCommonSystem 3 }
 
 nsCommonSystemSwUpdateServerIP  OBJECT-TYPE
        SYNTAX   IpAddress
        MAX-ACCESS  read-write
        STATUS  current
        DESCRIPTION
                "FTP Server IP address for software upgrade process"
        ::= { nsCommonSystemSwUpdate 1 }
 
 nsCommonSystemSwUpdateUserName  OBJECT-TYPE
        SYNTAX  DisplayString (SIZE(0..255))
        MAX-ACCESS  read-write
        STATUS  current
        DESCRIPTION
                "FTP Server user name for software upgrade process"
        ::= { nsCommonSystemSwUpdate 2 }
 
 nsCommonSystemSwUpdatePassword  OBJECT-TYPE
        SYNTAX  DisplayString (SIZE(0..255))
        MAX-ACCESS  read-write
        STATUS  current
        DESCRIPTION
                "FTP Server user password for software upgrade process"
        ::= { nsCommonSystemSwUpdate 3 }

 nsCommonSystemSwUpdateFileName  OBJECT-TYPE
        SYNTAX  DisplayString (SIZE(0..255))
        MAX-ACCESS  read-write
        STATUS  current
        DESCRIPTION
                "FTP Server software package file name for software upgrade process"
        ::= { nsCommonSystemSwUpdate 4 }

 nsCommonSystemSwUpdateCmd  OBJECT-TYPE
        SYNTAX  INTEGER {
            none (0),
            execute (1),
            notApplicable (255)
        }
        MAX-ACCESS  read-write
        STATUS  current
        DESCRIPTION
                "Software upgrade command"
        ::= { nsCommonSystemSwUpdate 5 }
 
  nsCommonSystemSwUpdateComplete  OBJECT-TYPE
        SYNTAX  INTEGER {
            idle (0),
            inProgress (1)
        }
        MAX-ACCESS  read-only
        STATUS  current
        DESCRIPTION
                "Software upgrade process complete"
        ::= { nsCommonSystemSwUpdate 6 }

  nsCommonSystemSwUpdateStatus  OBJECT-TYPE
        SYNTAX  INTEGER {
            ok (0),
            error (1),
            notApplicable (255)
        }
        MAX-ACCESS  read-only
        STATUS  current
        DESCRIPTION
                "Software upgrade process status"
        ::= { nsCommonSystemSwUpdate 7 }
        
 nsCommonSystemSwActivateBackupCmd  OBJECT-TYPE
        SYNTAX  INTEGER {
            none (0),
            execute (1),
            notApplicable (255)
        }
        MAX-ACCESS  read-write
        STATUS  current
        DESCRIPTION
                "Software upgrade command"
        ::= { nsCommonSystemSwUpdate 8 }
        
 -- ===================================================

  nsCommonSystemDatabase  OBJECT-IDENTITY
         STATUS current
        DESCRIPTION
              "Common MIB branch that holds all Database actions."
        ::= { nsCommonSystem 4 }

 nsCommonSystemDatabaseCmdDbName  OBJECT-TYPE
        SYNTAX  DisplayString (SIZE(0..255))
        MAX-ACCESS  read-write
        STATUS  current
        DESCRIPTION
                "Database file name for database commands"
        ::= { nsCommonSystemDatabase 1 }

 nsCommonSystemDatabaseServerIP  OBJECT-TYPE
        SYNTAX   IpAddress
        MAX-ACCESS  read-write
        STATUS  current
        DESCRIPTION
                "TFTP Server IP address for database upload/download commands"
        ::= { nsCommonSystemDatabase 2 }

 nsCommonSystemDatabaseCmd  OBJECT-TYPE
        SYNTAX  INTEGER {
            none (0),
            save (1),
            load (2),
            delete (3),
            defaults (4),
            upload (5),
            download (6),
            notApplicable (255)
        }
        MAX-ACCESS  read-write
        STATUS  current
        DESCRIPTION
                "Database command 
                 save(1) - save configuration to file
                 load(2) - load and activate configuration
                 delete(3) - delete configuration file
                 default(4) - set current configuration to factory defaults
                 upload (5) - upload database into TFTP server
                 download (6) - download database via TFTP server into the device
                 " 
        ::= { nsCommonSystemDatabase 3 }

 nsCommonSystemDatabaseTable OBJECT-TYPE
		SYNTAX SEQUENCE OF DatabaseEntry
		MAX-ACCESS not-accessible
		STATUS current
		DESCRIPTION
				"List of Databases"
 	::= { nsCommonSystemDatabase 4 } 
 
 nsCommonSystemDatabaseEntry OBJECT-TYPE
    	SYNTAX      DatabaseEntry
    	MAX-ACCESS  not-accessible
    	STATUS      current
    	DESCRIPTION "Conceptual row in table for each event."
    	INDEX   { nsCommonSystemDatabaseID	 }
    	::= { nsCommonSystemDatabaseTable 1 }
 
 DatabaseEntry ::=
	SEQUENCE {
		nsCommonSystemDatabaseID            Unsigned32,
		nsCommonSystemDatabaseName 	        DisplayString
	} 
 
  nsCommonSystemDatabaseID  OBJECT-TYPE
        SYNTAX  Unsigned32
        MAX-ACCESS  not-accessible
        STATUS  current
        DESCRIPTION
                "Database ID"
        ::= { nsCommonSystemDatabaseEntry  1 }        
 
  nsCommonSystemDatabaseName  OBJECT-TYPE
        SYNTAX  DisplayString (SIZE(0..255))
        MAX-ACCESS  read-only
        STATUS  current
        DESCRIPTION
                "Database name"
        ::= { nsCommonSystemDatabaseEntry  2 }

 -- ===================================================

 nsCommonSystemLicense  OBJECT-IDENTITY
         STATUS current
        DESCRIPTION
              "Common MIB branch that holds License."
        ::= { nsCommonSystem 5 }
        
 nsCommonSystemLicenseIssueDate  OBJECT-TYPE
        SYNTAX  DisplayString
        MAX-ACCESS  read-only
        STATUS  current
        DESCRIPTION
                "Issue Date of the License"
        ::= { nsCommonSystemLicense  1 }        
  
 nsCommonSystemLicenseID  OBJECT-TYPE
        SYNTAX  Integer32
        MAX-ACCESS  read-only
        STATUS  current
        DESCRIPTION
                "License ID"
        ::= { nsCommonSystemLicense  2 }        

 nsCommonSystemLicenseFeaturesTable OBJECT-TYPE
        SYNTAX SEQUENCE OF LicenseFeaturesEntry
        MAX-ACCESS not-accessible
        STATUS current
        DESCRIPTION
                "List of License features"
        ::= { nsCommonSystemLicense  3 }        
 
 nsCommonSystemLicenseFeaturesEntry OBJECT-TYPE
        SYNTAX      LicenseFeaturesEntry
        MAX-ACCESS  not-accessible
        STATUS      current
        DESCRIPTION "Conceptual row in table for each license feature."
        INDEX   { nsCommonSystemLicenseFeatureIndx   }
        ::= { nsCommonSystemLicenseFeaturesTable 1 }
 
 LicenseFeaturesEntry ::=
    SEQUENCE {
        nsCommonSystemLicenseFeatureIndx      Unsigned32,
        nsCommonSystemLicenseFeatureName      DisplayString,
        nsCommonSystemLicenseFeatureType      INTEGER,
        nsCommonSystemLicenseFeatureDaysLeft  INTEGER
    } 
 
  nsCommonSystemLicenseFeatureIndx  OBJECT-TYPE
        SYNTAX  Unsigned32
        MAX-ACCESS  not-accessible
        STATUS  current
        DESCRIPTION
                "License feature Index"
        ::= { nsCommonSystemLicenseFeaturesEntry  1 }        
 
  nsCommonSystemLicenseFeatureName  OBJECT-TYPE
        SYNTAX  DisplayString (SIZE(0..255))
        MAX-ACCESS  read-only
        STATUS  current
        DESCRIPTION
                "License feature name"
        ::= { nsCommonSystemLicenseFeaturesEntry  2 }

  nsCommonSystemLicenseFeatureType  OBJECT-TYPE
        SYNTAX  INTEGER {
            notExist(0),
            permanent (1),
            temporary (2)
        }
        MAX-ACCESS  read-only
        STATUS  current
        DESCRIPTION
                "License feature type"
        ::= { nsCommonSystemLicenseFeaturesEntry  3 }

  nsCommonSystemLicenseFeatureDaysLeft  OBJECT-TYPE
        SYNTAX  Integer32
        MAX-ACCESS  read-only
        STATUS  current
        DESCRIPTION
                "License feature days left - for temporary license"
        ::= { nsCommonSystemLicenseFeaturesEntry  4 }        

-- ===================================================

nsCommonProducts  OBJECT-IDENTITY
        STATUS current
        DESCRIPTION
              "Common MIB branch that holds all Novelsat Products"
        ::= { nsCommon 4 }

-- ===================================================
nsNS1000      OBJECT IDENTIFIER ::= { nsCommonProducts  1 }
nsNS2000      OBJECT IDENTIFIER ::= { nsCommonProducts  2 }
nsNS3000      OBJECT IDENTIFIER ::= { nsCommonProducts  3 }
 
END
