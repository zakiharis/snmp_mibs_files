-- MODULE-IDENTITY
--  OrgName
--    Netasq
--  ContactInfo
--     Customer Support
--     
--     3,  rue Aricheme
--     59650 Villeneuve d'Ascq
--     FRANCE
--    
--     Tel: +33 03 20 61 96 30
--     E-mail: support@netasq.com
--     Http://www.netasq.com


--
--  Last modified date: 07/30/2002
--  

NETASQ-PROPERTY-MIB DEFINITIONS ::= BEGIN
IMPORTS
    MODULE-IDENTITY,  OBJECT-TYPE,  Integer32 FROM SNMPv2-SMI
    DisplayString              FROM RFC1213-MIB 
    ntqProductProperty         FROM NETASQ-SMI-MIB;

        ntqModel OBJECT-TYPE
                SYNTAX  DisplayString (SIZE (0..255))
                MAX-ACCESS  read-only
                STATUS  current
                DESCRIPTION
                          "Netasq Firewall model "
                ::= { ntqProductProperty 1 }
                
        ntqVersion OBJECT-TYPE
                SYNTAX DisplayString (SIZE (0..255))
                MAX-ACCESS read-only
                STATUS current
                DESCRIPTION
                        "Netasq Firewal version"
                ::= { ntqProductProperty 2 }
        
        ntqSerialNumber OBJECT-TYPE
                SYNTAX  DisplayString (SIZE (0..255))
                MAX-ACCESS  read-only
                STATUS  current
                DESCRIPTION
                        "Netasq Firewall serial number"
                ::= { ntqProductProperty 3 }
                
        ntqSystemName OBJECT-TYPE
                SYNTAX  DisplayString (SIZE (0..255))
                MAX-ACCESS  read-only
                STATUS  current
                DESCRIPTION
                        "Netasq Firewall system Name"
                ::= { ntqProductProperty 4 }
        
        ntqSystemLanguage OBJECT-TYPE
                SYNTAX  DisplayString (SIZE (0..255))
                MAX-ACCESS  read-only
                STATUS  current
                DESCRIPTION
                        "Firewall language"
                ::= { ntqProductProperty 5 }
                
        ntqNbEther      OBJECT-TYPE
                SYNTAX  Integer32
                MAX-ACCESS  read-only
                STATUS  current
                DESCRIPTION
                        "Number of ethernet interface"
                ::= { ntqProductProperty 6 }
                
        ntqNbVlan       OBJECT-TYPE
                SYNTAX  Integer32
                MAX-ACCESS  read-only
                STATUS  current
                DESCRIPTION     
                        "Number of VLAN interface"
                ::= { ntqProductProperty 7 }
                
        ntqNbDialup     OBJECT-TYPE
                SYNTAX  Integer32
                MAX-ACCESS  read-only
                STATUS  current
                DESCRIPTION
                        "Number of Dialup"
                ::= { ntqProductProperty 8 }
                
        ntqNbPPTP       OBJECT-TYPE
                SYNTAX  Integer32
                MAX-ACCESS read-only
                STATUS  current
                DESCRIPTION
                        "Number of PPTP"
                ::= { ntqProductProperty 9 }
                
        ntqNbSerial     OBJECT-TYPE
                SYNTAX  Integer32
                MAX-ACCESS  read-only
                STATUS  current
                DESCRIPTION
                        "Number of serial port"
                ::= { ntqProductProperty 10 }
                
        ntqNbLoopback OBJECT-TYPE
                SYNTAX  Integer32
                MAX-ACCESS  read-only
                STATUS  current
                DESCRIPTION
                        "Number of loopback interface"
                ::= { ntqProductProperty 11 }
        ntqWatchdog OBJECT-TYPE
                SYNTAX  Integer32
                MAX-ACCESS  read-only
                STATUS  current
                DESCRIPTION
                        "Watchdog"
                ::= { ntqProductProperty 12 }
		ntqLed OBJECT-TYPE
                SYNTAX  Integer32
                MAX-ACCESS  read-only
                STATUS  current
                DESCRIPTION
                        "Firewall Led"
                ::= { ntqProductProperty 13 }
		ntqClone OBJECT-TYPE
                SYNTAX  Integer32
                MAX-ACCESS  read-only
                STATUS  current
                DESCRIPTION
                        "Firewall Led"
                ::= { ntqProductProperty 14 }			
		ntqHADialup OBJECT-TYPE
                SYNTAX  Integer32
                MAX-ACCESS  read-only
                STATUS  current
                DESCRIPTION
                        "Firewall Led"
                ::= { ntqProductProperty 15 }
END
