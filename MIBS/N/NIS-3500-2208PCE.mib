NIS-3500-2208PCE DEFINITIONS ::= BEGIN

IMPORTS
        internet,  IpAddress,  Integer32
                FROM SNMPv2-SMI
		;

private           OBJECT IDENTIFIER ::= { internet 4 }
enterprises       OBJECT IDENTIFIER ::= { private 1 }
company          OBJECT IDENTIFIER ::= { enterprises 25972 }
switches          OBJECT IDENTIFIER ::= { company 0 }
managedPoeSwitch     OBJECT IDENTIFIER ::= { switches 5 }
nis-3500-2208pce           OBJECT IDENTIFIER ::= { managedPoeSwitch 20 }

contact MODULE-IDENTITY
        LAST-UPDATED "0604200000Z"
        ORGANIZATION ""
        CONTACT-INFO
                "Tel:      Fax:

                 Business service :

                 Customer service: "

        DESCRIPTION
                "The MIB module is for Industrial Ethernet Switch
                 and compatible to firmware kernel version 2.46  or higher."
        REVISION "0604200000Z"
        DESCRIPTION
                "Initial version of this MIB."
        ::= { nis-3500-2208pce 0 }

systemInfo            OBJECT IDENTIFIER ::= { nis-3500-2208pce 1 }
basicSetting          OBJECT IDENTIFIER ::= { nis-3500-2208pce 2 }
dhcpServer            OBJECT IDENTIFIER ::= { nis-3500-2208pce 3 }
portSetting           OBJECT IDENTIFIER ::= { nis-3500-2208pce 4 }
redundancy           OBJECT IDENTIFIER ::= { nis-3500-2208pce 5 }
vlan                  OBJECT IDENTIFIER ::= { nis-3500-2208pce 6 }
snmp                  OBJECT IDENTIFIER ::= { nis-3500-2208pce 7 }
trafficPrioritization OBJECT IDENTIFIER ::= { nis-3500-2208pce 8 }
multicast             OBJECT IDENTIFIER ::= { nis-3500-2208pce 9 }
security              OBJECT IDENTIFIER ::= { nis-3500-2208pce 10 }
warning               OBJECT IDENTIFIER ::= { nis-3500-2208pce 11 }
monitorAndDiag        OBJECT IDENTIFIER ::= { nis-3500-2208pce 12 }
saveConfiguration     OBJECT IDENTIFIER ::= { nis-3500-2208pce 13 }
factoryDefault        OBJECT IDENTIFIER ::= { nis-3500-2208pce 14 }
systemReboot          OBJECT IDENTIFIER ::= { nis-3500-2208pce 15 }
misc                  OBJECT IDENTIFIER ::= { nis-3500-2208pce 24 }
powerOverEthernet     OBJECT IDENTIFIER ::= { nis-3500-2208pce 25 }

DisplayString ::= TEXTUAL-CONVENTION
    DISPLAY-HINT "255a"
    STATUS       current
    DESCRIPTION  ""
    SYNTAX       OCTET STRING (SIZE (0..255))

MacAddress ::= OCTET STRING (SIZE (6))    -- a 6 octet address
                                          -- in the
                                          -- "canonical"
                                          -- order

PortList ::= OCTET STRING

--
-- systemInfo
--

systemName OBJECT-TYPE
       SYNTAX  DisplayString (SIZE (0..64))
       ACCESS  read-only
       STATUS  current
       DESCRIPTION   "An administratively-assigned name for this
                      managed node. By convention,  this is the node's
                      fully-qualified domain name."
       ::= { systemInfo 1 }

systemLocation OBJECT-TYPE
       SYNTAX  DisplayString (SIZE (0..64))
       ACCESS  read-only
       STATUS  current
       DESCRIPTION "The physical location of this node (e.g., 
                      `telephone closet,  3rd floor')."
       ::= { systemInfo 2 }

systemContact OBJECT-TYPE
        SYNTAX      DisplayString (SIZE(0..64))
        MAX-ACCESS  read-only
        STATUS      current
        DESCRIPTION "The contact information of system."
        ::= { systemInfo 3 }

systemDescr OBJECT-TYPE
       SYNTAX  DisplayString (SIZE (0..64))
       ACCESS  read-only
       STATUS  current
       DESCRIPTION   "A textual description of the entity.  This value
                      should include the full name and version
                      identification of the system's hardware type, 
                      software operating-system,  and networking
                      software.  It is mandatory that this only contain
                      printable ASCII characters."
       ::= { systemInfo 4 }

systemFwVer OBJECT-TYPE
        SYNTAX      DisplayString (SIZE(0..20))
        MAX-ACCESS  read-only
        STATUS      current
        DESCRIPTION "Firmware version of the device."
        ::= { systemInfo 5 }

systemMacAddress OBJECT-TYPE
       SYNTAX      MacAddress
       MAX-ACCESS  read-only
       STATUS      current

       DESCRIPTION "The MAC address of switch."
       ::= { systemInfo 6 }

--
-- basicSetting
--

switchSetting         OBJECT IDENTIFIER ::= { basicSetting 1 }
adminPassword         OBJECT IDENTIFIER ::= { basicSetting 2 }
ipConfiguration       OBJECT IDENTIFIER ::= { basicSetting 3 }
sntp                  OBJECT IDENTIFIER ::= { basicSetting 4 }
lldp                  OBJECT IDENTIFIER ::= { basicSetting 5 }
autoProvision         OBJECT IDENTIFIER ::= { basicSetting 6 }
backupAndRestore      OBJECT IDENTIFIER ::= { basicSetting 7 }
upgradeFirmware       OBJECT IDENTIFIER ::= { basicSetting 8 }

--
-- switchSetting
--

switchSettingSystemName OBJECT-TYPE
       SYNTAX  DisplayString (SIZE (0..64))
       ACCESS  read-write
       STATUS  current
       DESCRIPTION   "An administratively-assigned name for this
                      managed node. By convention,  this is the node's
                      fully-qualified domain name."
       ::= { switchSetting 1 }

switchSettingSystemLocation OBJECT-TYPE
       SYNTAX  DisplayString (SIZE (0..64))
       ACCESS  read-write
       STATUS  current
       DESCRIPTION "The physical location of this node (e.g., 
                      `telephone closet,  3rd floor')."
       ::= { switchSetting 2 }

switchSettingSystemContact OBJECT-TYPE
        SYNTAX      DisplayString (SIZE(0..64))
        MAX-ACCESS  read-write
        STATUS      current
        DESCRIPTION "The contact information of system."
        ::= { switchSetting 3 }

switchSettingLocationAlert OBJECT-TYPE
        SYNTAX      INTEGER
                    {
                        enabled(1), 
                        disabled(2)
                    }
        MAX-ACCESS  read-write
        STATUS      current
        DESCRIPTION "The location alert function."
        ::= { switchSetting 4 }

--
-- adminPassword
--

adminPasswordUserName OBJECT-TYPE
        SYNTAX      DisplayString (SIZE(0..10))
        MAX-ACCESS  read-write
        STATUS      current
        DESCRIPTION "The name(ID) of security manager."
        ::= { adminPassword 1 }

adminPassword-Password OBJECT-TYPE
        SYNTAX      DisplayString (SIZE(0..10))
        MAX-ACCESS  write-only
        STATUS      current
        DESCRIPTION "The password of security manager.
                     This object can't be read. it's write-only."
        ::= { adminPassword 2 }

--
-- ipConfiguration
--

ipConfigurationTable OBJECT-TYPE
        SYNTAX      SEQUENCE OF IPconfigurationEntry
        MAX-ACCESS  not-accessible
        STATUS      current
        DESCRIPTION "Table of descriptive information and configuration about
                     IP of switche."
        ::= { ipConfiguration 1 }

ipConfigurationEntry OBJECT-TYPE
        SYNTAX      IPconfigurationEntry
        MAX-ACCESS  not-accessible
        STATUS      current
        DESCRIPTION "An entry in the table,  containing IP/DHCP-client information
                     of the switch. "
        INDEX       { ipConfigurationIndex }
        ::= { ipConfigurationTable 1 }

IPconfigurationEntry ::= SEQUENCE
{
    ipConfigurationIndex             Integer32, 
    ipConfigurationDHCPStatus        INTEGER, 
    ipConfigurationAddress           IpAddress, 
    ipConfigurationSubMask           IpAddress, 
    ipConfigurationGateway           IpAddress, 
    ipConfigurationDNS1              IpAddress, 
    ipConfigurationDNS2              IpAddress
}

ipConfigurationIndex OBJECT-TYPE
        SYNTAX      Integer32
        MAX-ACCESS  not-accessible
        STATUS      current
        DESCRIPTION "This object identifies the switch within the system
                     for which this entry contains information. This
                     value can never be greater than switchNumber."
        ::= { ipConfigurationEntry 1 }


ipConfigurationDHCPStatus OBJECT-TYPE
        SYNTAX      INTEGER
                    {
                        enabled(1), 
                        disabled(2)
                    }
        MAX-ACCESS  read-write
        STATUS      current
        DESCRIPTION "Parameter to enable or disable DHCP client function of the
                     switch. When enabled,  device will be a DHCP client and request
                     the IP configuration from DHCP server.
                     Note: Other items in this table couldn't be modified,  when
                     ipConfigurationDHCPStatus is enabled."
        ::= { ipConfigurationEntry 2 }

ipConfigurationAddress OBJECT-TYPE
        SYNTAX      IpAddress
        MAX-ACCESS  read-write
        STATUS      current
        DESCRIPTION "The IP address of switch."
        ::= { ipConfigurationEntry 3 }

ipConfigurationSubMask OBJECT-TYPE
        SYNTAX      IpAddress
        MAX-ACCESS  read-write
        STATUS      current
        DESCRIPTION "The subnet mask of switch."
        ::= { ipConfigurationEntry 4 }

ipConfigurationGateway OBJECT-TYPE
        SYNTAX      IpAddress
        MAX-ACCESS  read-write
        STATUS      current
        DESCRIPTION "The gateway address of switch."
        ::= { ipConfigurationEntry 5 }

ipConfigurationDNS1 OBJECT-TYPE
        SYNTAX      IpAddress
        MAX-ACCESS  read-write
        STATUS      current
        DESCRIPTION "The DNS1 address of switch."
        ::= { ipConfigurationEntry 6 }

ipConfigurationDNS2 OBJECT-TYPE
        SYNTAX      IpAddress
        MAX-ACCESS  read-write
        STATUS      current
        DESCRIPTION "The DNS2 address of switch."
        ::= { ipConfigurationEntry 7 }

--
-- sntp
--

sntpClientStatus OBJECT-TYPE
        SYNTAX      INTEGER
                    {
                        enabled(1), 
                        disabled(2)
                    }
        MAX-ACCESS  read-write
        STATUS      current
        DESCRIPTION "(1)Enable SNTP clinet.
                     (2)Disable SNTP clinet.
                     SNTP is simple network time protocol.
                     Use this OID to Enable/Disable SNTP client."
        ::= { sntp 1 }

sntpDaylightSavingTime OBJECT-TYPE
        SYNTAX      INTEGER
                    {
                        enabled(1), 
                        disabled(2)
                    }
        MAX-ACCESS  read-write
        STATUS      current
        DESCRIPTION "(1)Enable Daylight Saving Time.
                     (2)Disable Daylight Saving Time.
                     Daylight Saving Time:
                     Use this OID to Enable/Disable Daylight Saving Time."
        ::= { sntp 2 }

sntpUTCTimezone OBJECT-TYPE
        SYNTAX      INTEGER
                    {
                        gmt-negative-12-00-Eniwetok-Kwajalein(1), 
                        gmt-negative-11-00-Midway-Island-Samoa(2), 
                        gmt-negative-10-00-Hawaii(3), 
                        gmt-negative-09-00-Alaska(4), 
                        gmt-negative-08-00-Pacific-Time-US-and-Canada-Tijuana(5), 
                        gmt-negative-07-00-Arizona(6), 
                        gmt-negative-07-00-Mountain-Time-US-and-Canada(7), 
                        gmt-negative-06-00-Central-Time-US-and-Canada(8), 
                        gmt-negative-06-00-Mexico-City-Tegucigalpa(9), 
                        gmt-negative-06-00-Saskatchewan(10), 
                        gmt-negative-05-00-Bogota-Lima-Quito(11), 
                        gmt-negative-05-00-Eastern-Time-US-and-Canada(12), 
                        gmt-negative-05-00-Indiana-East(13), 
                        gmt-negative-04-00-Atlantic-Time-Canada(14), 
                        gmt-negative-04-00-Caracas-La-Paz(15), 
                        gmt-negative-04-00-Santiago(16), 
                        gmt-negative-03-30-Newfoundland(17), 
                        gmt-negative-03-00-Brasilia(18), 
                        gmt-negative-03-00-Buenos-Aires-Georgetown(19), 
                        gmt-negative-02-00-Mid-Atlantic(20), 
                        gmt-negative-01-00-Azores-Cape-Verde-Is(21), 
                        gmt-Casablanca-Monrovia(22), 
                        gmt-Greenwich-Mean-Time-Dublin-Edinburgh-Lisbon-London(23), 
                        gmt-positive-01-00-Amsterdam-Berlin-Bern-Rome-Stockholm-Vienna(24), 
                        gmt-positive-01-00-Belgrade-Bratislava-Budapest-Ljubljana-Prague(25), 
                        gmt-positive-01-00-Brussels-Copenhagen-Madrid-Paris-Vilnius(26), 
                        gmt-positive-01-00-Sarajevo-Skopje-Sofija-Warsaw-Zagreb(27), 
                        gmt-positive-02-00-Athens-Istanbul-Minsk(28), 
                        gmt-positive-02-00-Bucharest(29), 
                        gmt-positive-02-00-Cairo(30), 
                        gmt-positive-02-00-Harare-Pretoria(31), 
                        gmt-positive-02-00-Helsinki-Riga-Tallinn(32), 
                        gmt-positive-02-00-Jerusalem(33), 
                        gmt-positive-03-00-Baghdad-Kuwait-Riyadh(34), 
                        gmt-positive-03-00-Moscow-St-Petersburg-Volgograd(35), 
                        gmt-positive-03-00-Mairobi(36), 
                        gmt-positive-03-30-Tehran(37), 
                        gmt-positive-04-00-Abu-Dhabi-Muscat(38), 
                        gmt-positive-04-00-Baku-Tbilisi(39), 
                        gmt-positive-04-30-Kabul(40), 
                        gmt-positive-05-00-Ekaterinburg(41), 
                        gmt-positive-05-00-Islamabad-Karachi-Tashkent(42), 
                        gmt-positive-05-30-Bombay-Calcutta-Madras-New-Delhi(43), 
                        gmt-positive-06-00-Astana-Almaty-Dhaka(44), 
                        gmt-positive-06-00-Colombo(45), 
                        gmt-positive-07-00-Bangkok-Hanoi-Jakarta(46), 
                        gmt-positive-08-00-Beijing-Chongqing-Hong-Kong-Urumqi(47), 
                        gmt-positive-08-00-Perth(48), 
                        gmt-positive-08-00-Singapore(49), 
                        gmt-positive-08-00-Taipei(50), 
                        gmt-positive-09-00-Osaka-Sapporo-Tokyo(51), 
                        gmt-positive-09-00-Seoul(52), 
                        gmt-positive-09-00-Yakutsk(53), 
                        gmt-positive-09-30-Adelaide(54), 
                        gmt-positive-09-30-Darwin(55), 
                        gmt-positive-10-00-Brisbane(56), 
                        gmt-positive-10-00-Canberra-Melbourne-Sydney(57), 
                        gmt-positive-10-00-Guam-Port-Moresby(58), 
                        gmt-positive-10-00-Hobart(59), 
                        gmt-positive-10-00-Vladivostok(60), 
                        gmt-positive-11-00-Magadan-Solomon-Is-New-Caledonia(61), 
                        gmt-positive-12-00-Auckland-Wllington(62), 
                        gmt-positive-12-00-Fiji-Kamchatka-Marshall-Is(63)
                        }
        MAX-ACCESS  read-write
        STATUS      current
        DESCRIPTION "UTC Timezone."
        ::= { sntp 3 }

sntpServerAddress OBJECT-TYPE
                SYNTAX      DisplayString (SIZE(0..100))
                MAX-ACCESS  read-write
                STATUS      current
                DESCRIPTION "The address of a SNTP Server."
        ::= { sntp 4 }

sntpSwitchTimer OBJECT-TYPE
                SYNTAX      DisplayString (SIZE(0..255))
                MAX-ACCESS  read-only
                STATUS      current
                DESCRIPTION "The switch timer."
        ::= { sntp 5 }

sntpDaylightSavingPeriodStart OBJECT-TYPE
                SYNTAX      DisplayString (SIZE(0..14))
                MAX-ACCESS  read-write
                STATUS      current
                DESCRIPTION "The start-time of daylight saveing period, 
                             format: yyyymmdd hh:mm."
        ::= { sntp 6 }

sntpDaylightSavingPeriodEnd OBJECT-TYPE
                SYNTAX      DisplayString (SIZE(0..14))
                MAX-ACCESS  read-write
                STATUS      current
                DESCRIPTION "The end-time of daylight saveing period, 
                             format: yyyymmdd hh:mm."
        ::= { sntp 7 }

sntpDaylightSavingOffset OBJECT-TYPE
                SYNTAX      Integer32
                MAX-ACCESS  read-write
                STATUS      current
                DESCRIPTION "Daylight Saving Offset(Usually is 60 mins).
                             When Enable and current time at Daylight Saving Period, 
                             the current time of the switch will be offseted by
                             Daylight Saving Offset."
        ::= { sntp 8 }

--
-- lldp
--

lldpStatus OBJECT-TYPE
		SYNTAX		INTEGER
					{
						enable(1), 
						disable(2)
					}
		MAX-ACCESS	read-write
		STATUS		current
		DESCRIPTION	"LLDP Configuration.
					 (1) Enable.
					 (2) Disable."
		::= { lldp 1 }

lldpInterval OBJECT-TYPE
		SYNTAX		Integer32
        MAX-ACCESS	read-write
        STATUS		current
        DESCRIPTION	"LLDP Interval."
        ::= { lldp 2 }

--
--autoProvision
--

autoProvisionConfigurationStatus OBJECT-TYPE
		SYNTAX		INTEGER
					{
						enable(1), 
						disable(2)
					}
		MAX-ACCESS	read-write
		STATUS		current
		DESCRIPTION	"Auto Provision for Switch Configuration.
					 (1) Enable.
					 (2) Disable."
		::= { autoProvision 1 }

autoProvisionConfigurationServerip OBJECT-TYPE
        SYNTAX      IpAddress
        MAX-ACCESS  read-write
        STATUS      current
        DESCRIPTION "The IP address of TFTP server."
		::= { autoProvision 2 }

autoProvisionConfigurationFilename OBJECT-TYPE
        SYNTAX      DisplayString (SIZE(0..14))
        MAX-ACCESS  read-write
        STATUS      current
        DESCRIPTION "The filename of firmware."
		::= { autoProvision 3 }

autoProvisionImageStatus OBJECT-TYPE
		SYNTAX		INTEGER
					{
						enable(1), 
						disable(2)
					}
		MAX-ACCESS	read-write
		STATUS		current
		DESCRIPTION	"Auto Provision for firmware image.
					 (1) Enable.
					 (2) Disable."
		::= { autoProvision 4 }

autoProvisionImageServerip OBJECT-TYPE
        SYNTAX      IpAddress
        MAX-ACCESS  read-write
        STATUS      current
        DESCRIPTION "The IP address of TFTP server."
		::= { autoProvision 5 }

autoProvisionImageFilename OBJECT-TYPE
        SYNTAX      DisplayString (SIZE(0..14))
        MAX-ACCESS  read-write
        STATUS      current
        DESCRIPTION "The filename of firmware."
		::= { autoProvision 6 }

--
-- backupAndRestore
--

backupServerIP OBJECT-TYPE
                SYNTAX      IpAddress
                MAX-ACCESS  read-write
                STATUS      current
                DESCRIPTION "The IP address of a TFTP server from which a
                             firmware image can be uploaded."
        DEFVAL { '00000000'H }
        ::= { backupAndRestore  1 }

backupAgentBoardFwFileName OBJECT-TYPE
        SYNTAX      DisplayString(SIZE(0..80))
        MAX-ACCESS  read-write
        STATUS      current
        DESCRIPTION ""
        DEFVAL      { "data.bin" }
        ::= { backupAndRestore  2 }

backupStatus OBJECT-TYPE
        SYNTAX      INTEGER
                    {
                        active(1), 
                        notActive(2)
                    }
        MAX-ACCESS  read-write
        STATUS      current
        DESCRIPTION "Setting this object to active(1) triger the TFTP
                     upload action.
                     Setting this object to notActive(2) has no effect.
                     The system always returns the value notActive(2)
                     when this object is read."
        ::= { backupAndRestore  3 }

restoreServerIP OBJECT-TYPE
                SYNTAX      IpAddress
                MAX-ACCESS  read-write
                STATUS      current
                DESCRIPTION "The IP address of a TFTP server from which a
                             firmware image can be downloaded."
        DEFVAL { '00000000'H }
        ::= { backupAndRestore  4 }

restoreAgentBoardFwFileName OBJECT-TYPE
        SYNTAX      DisplayString(SIZE(0..80))
        MAX-ACCESS  read-write
        STATUS      current
        DESCRIPTION ""
        DEFVAL      { "data.bin" }
        ::= { backupAndRestore  5 }

restoreStatus OBJECT-TYPE
        SYNTAX      INTEGER
                    {
                        active(1), 
                        notActive(2)
                    }
        MAX-ACCESS  read-write
        STATUS      current
        DESCRIPTION "Setting this object to active(1) triger the TFTP
                     download action.
                     Setting this object to notActive(2) has no effect.
                     The system always returns the value notActive(2)
                     when this object is read."
        ::= { backupAndRestore  6 }

--
-- upgradeFirmware
--

tftpDownloadServerIP OBJECT-TYPE
                SYNTAX      IpAddress
                MAX-ACCESS  read-write
                STATUS      current
                DESCRIPTION "The IP address of a TFTP server from which a
                             firmware image can be downloaded."
        DEFVAL { '00000000'H }
        ::= { upgradeFirmware  1 }

tftpDownloadAgentBoardFwFileName OBJECT-TYPE
        SYNTAX      DisplayString(SIZE(0..80))
        MAX-ACCESS  read-write
        STATUS      current
        DESCRIPTION ""
        DEFVAL      { "image.bin" }
        ::= { upgradeFirmware  2 }

tftpDownloadStatus OBJECT-TYPE
        SYNTAX      INTEGER
                    {
                        active(1), 
                        notActive(2)
                    }
        MAX-ACCESS  read-write
        STATUS      current
        DESCRIPTION "Setting this object to active(1) triger the TFTP
                     download action.
                     Setting this object to notActive(2) has no effect.
                     The system always returns the value notActive(2)
                     when this object is read."
        ::= { upgradeFirmware  3 }

--
--dhcpServer
--

dhcpServerCfgTable OBJECT-TYPE
        SYNTAX      SEQUENCE OF DHCPServerCfgEntry
        MAX-ACCESS  not-accessible
        STATUS      current
        DESCRIPTION "Table of descriptive information and configuration about
                     DHCP server of the switch."
        ::= { dhcpServer 1 }

dhcpServerCfgEntry OBJECT-TYPE
        SYNTAX      DHCPServerCfgEntry
        MAX-ACCESS  not-accessible
        STATUS      current
        DESCRIPTION "An entry in the table,  containing DHCP server information
                     of the switch. "
        INDEX       { dhcpServerCfgIndex }
        ::= { dhcpServerCfgTable 1 }

DHCPServerCfgEntry ::= SEQUENCE
{
    dhcpServerCfgIndex      Integer32, 
    dhcpServerCfgStatus     INTEGER, 
    dhcpServerCfgLowIPAddr  IpAddress, 
    dhcpServerCfgHighIPAddr IpAddress, 
    dhcpServerCfgSubMask    IpAddress, 
    dhcpServerCfgGateway    IpAddress, 
    dhcpServerCfgDNS        IpAddress, 
    dhcpServerCfgLeaseTime  Integer32
}

dhcpServerCfgIndex OBJECT-TYPE
        SYNTAX      Integer32
        MAX-ACCESS  not-accessible
        STATUS      current
        DESCRIPTION "This object identifies the switch within the system
                     for which this entry contains information. This
                     value can never be greater than switchNumber."
        ::= { dhcpServerCfgEntry 1 }

dhcpServerCfgStatus OBJECT-TYPE
        SYNTAX      INTEGER
                    {
                        enabled(1), 
                        disabled(2)
                    }
        MAX-ACCESS  read-write
        STATUS      current
        DESCRIPTION "Parameter to enable or disable DHCP server function of the
                     switch. When enabled,  the device will be a DHCP server and
                     provide the IP configurations for other DHCP clients.
                     Note: Other items in this table couldn't be modified,  when
                     dhcpServerCfgStatus is disabled."
        ::= { dhcpServerCfgEntry 2 }

dhcpServerCfgLowIPAddr OBJECT-TYPE
        SYNTAX      IpAddress
        MAX-ACCESS  read-write
        STATUS      current
        DESCRIPTION "This object defines the low boundary of DHCP server IP pool."
        ::= { dhcpServerCfgEntry 3 }

dhcpServerCfgHighIPAddr OBJECT-TYPE
        SYNTAX      IpAddress
        MAX-ACCESS  read-write
        STATUS      current
        DESCRIPTION "This object defines the high boundary of DHCP server IP pool."
        ::= { dhcpServerCfgEntry 4 }

dhcpServerCfgSubMask OBJECT-TYPE
        SYNTAX      IpAddress
        MAX-ACCESS  read-write
        STATUS      current
        DESCRIPTION "The subnet mask of IP configuration for DHCP clients."
        ::= { dhcpServerCfgEntry 5 }

dhcpServerCfgGateway OBJECT-TYPE
        SYNTAX      IpAddress
        MAX-ACCESS  read-write
        STATUS      current
        DESCRIPTION "The gateway address of IP configuration for DHCP clients."
        ::= { dhcpServerCfgEntry 6 }

dhcpServerCfgDNS OBJECT-TYPE
        SYNTAX      IpAddress
        MAX-ACCESS  read-write
        STATUS      current
        DESCRIPTION "The DNS address of IP configuration for DHCP clients."
        ::= { dhcpServerCfgEntry 7 }

dhcpServerCfgLeaseTime OBJECT-TYPE
        SYNTAX      Integer32
        MAX-ACCESS  read-write
        STATUS      current
        DESCRIPTION "The lease time(in second) of DHCP clients."
        ::= { dhcpServerCfgEntry 8 }

dhcpServerClientInfoTable OBJECT-TYPE
        SYNTAX      SEQUENCE OF DHCPServerClientInfoEntry
        MAX-ACCESS  not-accessible
        STATUS      current
        DESCRIPTION "Table of descriptive information about
                     current status of each DHCP client registered."
        ::= { dhcpServer 2 }

dhcpServerClientInfoEntry OBJECT-TYPE
        SYNTAX      DHCPServerClientInfoEntry
        MAX-ACCESS  not-accessible
        STATUS      current
        DESCRIPTION "An entry in the table,  containing DHCP clients information."
        INDEX       { dhcpServerClientInfoIndex }
        ::= { dhcpServerClientInfoTable 1 }

DHCPServerClientInfoEntry ::= SEQUENCE
{
    dhcpServerClientInfoIndex      Integer32, 
    dhcpServerClientInfoIPAddr     DisplayString, 
    dhcpServerClientInfoID         DisplayString, 
    dhcpServerClientInfoType       DisplayString, 
    dhcpServerClientInfoStatus     DisplayString, 
    dhcpServerClientInfoLease      Integer32
}

dhcpServerClientInfoIndex OBJECT-TYPE
        SYNTAX      Integer32
        MAX-ACCESS  read-only
        STATUS      current
        DESCRIPTION "Index of DHCP client."
        ::= { dhcpServerClientInfoEntry 1 }

dhcpServerClientInfoIPAddr OBJECT-TYPE
        SYNTAX      DisplayString (SIZE(0..15))
        MAX-ACCESS  read-only
        STATUS      current
        DESCRIPTION "The IP address of client."
        ::= { dhcpServerClientInfoEntry 2 }

dhcpServerClientInfoID OBJECT-TYPE
        SYNTAX      DisplayString (SIZE(0..17))
        MAX-ACCESS  read-only
        STATUS      current
        DESCRIPTION "The ID(MAC address) of client."
        ::= { dhcpServerClientInfoEntry 3 }

dhcpServerClientInfoType OBJECT-TYPE
        SYNTAX      DisplayString (SIZE(0..8))
        MAX-ACCESS  read-only
        STATUS      current
        DESCRIPTION "The type of client.
                     bootptab: Entry comes from bootptab file.
                     dynamic: Entry is dynamiclly created w/defaults for dhcp offer.
                     sniffed: Entry is learned by snooping on net traffic.
                     dbase: Entry is manually entered by user."
        ::= { dhcpServerClientInfoEntry 4 }

dhcpServerClientInfoStatus OBJECT-TYPE
        SYNTAX      DisplayString (SIZE(0..10))
        MAX-ACCESS  read-only
        STATUS      current
        DESCRIPTION "The status of client.
                     Unassigned: none of the following.
                     BOOTP: Entry has been assigned via plain bootp.
                     DHCPOffer: Entry has a dhcp offer pending.
                     DHCP: Entry has been assigned via DHCP."
        ::= { dhcpServerClientInfoEntry 5 }

dhcpServerClientInfoLease OBJECT-TYPE
        SYNTAX      Integer32
        MAX-ACCESS  read-only
        STATUS      current
        DESCRIPTION "The lease time of client(in second)."
        ::= { dhcpServerClientInfoEntry 6 }


dhcpServerIPBindingTable OBJECT-TYPE
        SYNTAX      SEQUENCE OF DHCPServerIPBindingEntry
        MAX-ACCESS  not-accessible
        STATUS      current
        DESCRIPTION "Table of descriptive information and configuration about
                     IP binding of DHCP server."
        ::= { dhcpServer 3 }

dhcpServerIPBindingEntry OBJECT-TYPE
        SYNTAX      DHCPServerIPBindingEntry
        MAX-ACCESS  not-accessible
        STATUS      current
        DESCRIPTION "An entry in the table,  containing IP binding information
                     of DHCP server. "
        INDEX       { dhcpServerIPBindingPortNum }
        ::= { dhcpServerIPBindingTable 1 }

DHCPServerIPBindingEntry ::= SEQUENCE
{
    dhcpServerIPBindingPortNum   Integer32, 
    dhcpServerIPBindingAddr      IpAddress
}

dhcpServerIPBindingPortNum OBJECT-TYPE
        SYNTAX      Integer32
        MAX-ACCESS  read-only
        STATUS      current
        DESCRIPTION "The port number."
        ::= { dhcpServerIPBindingEntry 1 }

dhcpServerIPBindingAddr OBJECT-TYPE
        SYNTAX      IpAddress
        MAX-ACCESS  read-write
        STATUS      current
        DESCRIPTION "The IP binding address."
        ::= { dhcpServerIPBindingEntry 2 }

--
-- portSetting
--

portControl      OBJECT IDENTIFIER ::= { portSetting 1 }
rateLimiting     OBJECT IDENTIFIER ::= { portSetting 2 }
portTrunk     OBJECT IDENTIFIER ::= { portSetting 3 }

portCtrlTable OBJECT-TYPE
        SYNTAX      SEQUENCE OF PortCtrlEntry
        MAX-ACCESS  not-accessible
        STATUS      current
        DESCRIPTION "Table of status information and configuration about
                     each switch ports(including expansion slot)."
        ::= { portControl 1 }

portCtrlEntry OBJECT-TYPE
        SYNTAX      PortCtrlEntry
        MAX-ACCESS  not-accessible
        STATUS      current
        DESCRIPTION "An entry in the table,  containing information
                     about configuration in one switch port of the switch."
        INDEX       { portCtrlIndex }
        ::= { portCtrlTable 1 }

PortCtrlEntry ::= SEQUENCE
{
    portCtrlIndex                Integer32, 
    portCtrlPortName             DisplayString, 
    portCtrlPortStatus           INTEGER, 
    portCtrlNegotiation          INTEGER, 
    portCtrlSpeed                INTEGER, 
    portCtrlDuplex               INTEGER, 
    portCtrlFlowControl          INTEGER, 
    portCtrlSecurity             INTEGER
}

portCtrlIndex OBJECT-TYPE
        SYNTAX      Integer32
        MAX-ACCESS  not-accessible
        STATUS      current
        DESCRIPTION "Index of port management table."
        ::= { portCtrlEntry 1 }

portCtrlPortName OBJECT-TYPE
        SYNTAX      DisplayString (SIZE(0..7))
        MAX-ACCESS  read-only
        STATUS      current
        DESCRIPTION "The name of port."
        ::= { portCtrlEntry 2 }

portCtrlPortStatus OBJECT-TYPE
        SYNTAX      INTEGER
                    {
                        enabled(1), 
                        disabled(2)
                    }
        MAX-ACCESS  read-write
        STATUS      current
        DESCRIPTION "To disable (or enable) control of this port."
        ::= { portCtrlEntry 3 }

portCtrlNegotiation OBJECT-TYPE
        SYNTAX      INTEGER
                    {
                        auto(1), 
                        force(2)
                    }
        MAX-ACCESS  read-write
        STATUS      current
        DESCRIPTION "The mode of network negoticaion, 
                     (1)Automatic
                     (2)Force"
        ::= { portCtrlEntry 4 }

portCtrlSpeed OBJECT-TYPE
        SYNTAX      INTEGER
                    {
                        speed-10M(1), 
                        speed-100M(2), 
                        speed-1000M(3)
                    }
        MAX-ACCESS  read-write
        STATUS      current
        DESCRIPTION "Set the speed of the port. If portCtrlNegotiation is auto, 
                    this object can't be modified."
        ::= { portCtrlEntry 5 }

portCtrlDuplex OBJECT-TYPE
        SYNTAX      INTEGER
                    {
                        fullduplex(1), 
                        halfduplex(2)
                    }
        MAX-ACCESS  read-write
        STATUS      current
        DESCRIPTION "Set full-duplex or half-duplex mode of the port. If portCtrlNegotiation is auto, 
                    this object can't be modified."
        ::= { portCtrlEntry 6 }

portCtrlFlowControl OBJECT-TYPE
        SYNTAX      INTEGER
                    {
                        disable(1), 
                        symmetric(2), 
                        asymmetric(3)
                    }
        MAX-ACCESS  read-write
        STATUS       current
        DESCRIPTION "Set flow control."
        ::= { portCtrlEntry 7 }

portCtrlSecurity OBJECT-TYPE
        SYNTAX      INTEGER
                    {
                        enabled(1), 
                        disabled(2)
                    }
        MAX-ACCESS  read-write
        STATUS      current
        DESCRIPTION "Set port security."
        ::= { portCtrlEntry 8 }

--
-- rateLimiting
--

rateLimitingTable OBJECT-TYPE
        SYNTAX      SEQUENCE OF RateLimitingEntry
        MAX-ACCESS  not-accessible
        STATUS      current
        DESCRIPTION "Table of descriptive information and configuration about
                     port rate limiting in this system.
                     You can set up every port 3/4s bandwidth rate and packet
                     limitation type."
        ::= { rateLimiting 1 }

rateLimitingEntry OBJECT-TYPE
        SYNTAX      RateLimitingEntry
        MAX-ACCESS  not-accessible
        STATUS      current
        DESCRIPTION "An entry in the table,  containing information
                     about port rate limiting."
        INDEX       { rateLimitingPortNum }
        ::= { rateLimitingTable 1 }

RateLimitingEntry ::= SEQUENCE
{
    rateLimitingPortNum Integer32, 
    rateLimitingPortType    INTEGER, 
    rateLimitingIngressRate Integer32, 
    rateLimitingEgressRate  Integer32
}

rateLimitingPortNum OBJECT-TYPE
        SYNTAX      Integer32
        MAX-ACCESS  read-only
        STATUS      current
        DESCRIPTION "Port number."
        ::= { rateLimitingEntry 1 }

rateLimitingPortType OBJECT-TYPE
        SYNTAX      INTEGER
                    {
                        all(1), 
                        broadcast-multicast-floodedunicast (2), 
                        broadcast-multicast(3), 
                        broadcastonly(4)
                    }
        MAX-ACCESS  read-write
        STATUS      current
        DESCRIPTION "Limit Packet type: select the packet type that want to filter.
                     The packet types have all type packet,  broadcast/multicast/
                     unknown unicast packet,  broadcast/multicast packet,  and broadcast
                     packet only. The broadcast/multicast/unknown unicast packet, 
                     broadcast/multicast packet,  and broadcast packet only are only
                     for ingress packet. The egress rate only supports all type packets."
        ::= { rateLimitingEntry 2 }

rateLimitingIngressRate OBJECT-TYPE
        SYNTAX      Integer32
        MAX-ACCESS  read-write
        STATUS      current
        DESCRIPTION "Ingress rate,  the rate range is from 64 kbps to 102400 kbps
                     (or 250000 kbps for giga ports),  and zero means no limit."
        ::= { rateLimitingEntry 3 }

rateLimitingEgressRate OBJECT-TYPE
        SYNTAX      Integer32
        MAX-ACCESS  read-write
        STATUS      current
        DESCRIPTION "Egress rate,  the rate range is from 64 kbps to 102400 kbps
                     (or 250000 kbps for giga ports),  and zero means no limit."
        ::= { rateLimitingEntry 4 }

--
-- portTrunk
--

aggregatorSetting OBJECT IDENTIFIER ::= { portTrunk 1 }
aggregatorStatus  OBJECT IDENTIFIER ::= { portTrunk 2 }
stateActivity     OBJECT IDENTIFIER ::= { portTrunk 3 }

portTrunkSysPri OBJECT-TYPE
        SYNTAX      Integer32
        MAX-ACCESS  read-write
        STATUS      current
        DESCRIPTION "The system priority of trunking."
        ::= { aggregatorSetting 1 }

portTrunkAggregatorTable OBJECT-TYPE
        SYNTAX      SEQUENCE OF PortTrunkAggregatorEntry
        MAX-ACCESS  not-accessible
        STATUS      current
        DESCRIPTION "Table of descriptive information and configuration about
                     of each trunk group in this system.
                     Link aggregation lets you group up to switch-port-num
                     consecutive ports into a single dedicated connection.
                     This feature can expand bandwidth to a device on the
                     network,  such as another switch or a server."
        ::= { aggregatorSetting 2 }

portTrunkAggregatorEntry OBJECT-TYPE
        SYNTAX      PortTrunkAggregatorEntry
        MAX-ACCESS  not-accessible
        STATUS      current
        DESCRIPTION "An entry in the table,  containing information
                     about aggregator setting of the trunk."
        INDEX       { portTrunkAggregatorIndex }
        ::= { portTrunkAggregatorTable 1 }

PortTrunkAggregatorEntry ::= SEQUENCE
{
    portTrunkAggregatorIndex         Integer32, 
    portTrunkAggregatorGroupName     DisplayString, 
    portTrunkAggregatorMemberPorts   PortList, 
    portTrunkAggregatorLACPStatus    INTEGER, 
    portTrunkAggregatorWorkPorts     Integer32
}

portTrunkAggregatorIndex OBJECT-TYPE
        SYNTAX      Integer32
        MAX-ACCESS  read-only
        STATUS      current
        DESCRIPTION "Index of trunk aggregator table."
        ::= { portTrunkAggregatorEntry 1 }

portTrunkAggregatorGroupName OBJECT-TYPE
        SYNTAX      DisplayString (SIZE(0..80))
        MAX-ACCESS  read-only
        STATUS      current
        DESCRIPTION "The name of trunk group."
        ::= { portTrunkAggregatorEntry 2 }

portTrunkAggregatorMemberPorts OBJECT-TYPE
        SYNTAX      PortList
        MAX-ACCESS  read-write
        STATUS      current
        DESCRIPTION "The members of trunk group."
        ::= { portTrunkAggregatorEntry 3 }

portTrunkAggregatorInfoTable OBJECT-TYPE
        SYNTAX      SEQUENCE OF PortTrunkAggregatorInfoEntry
        MAX-ACCESS  not-accessible
        STATUS      current
        DESCRIPTION "Table of descriptive information about
                     trunk group in this system."
        ::= { aggregatorStatus 1 }

portTrunkAggregatorInfoEntry OBJECT-TYPE
        SYNTAX      PortTrunkAggregatorInfoEntry
        MAX-ACCESS  not-accessible
        STATUS      current
        DESCRIPTION "An entry in the table,  containing information
                     about the trunk group."
        INDEX       { portTrunkAggregatorInfoIndex }
        ::= { portTrunkAggregatorInfoTable 1 }

PortTrunkAggregatorInfoEntry ::= SEQUENCE
{
    portTrunkAggregatorInfoIndex       Integer32, 
    portTrunkAggregatorInfoGroupName   DisplayString, 
    portTrunkAggregatorInfoDescription DisplayString
}

portTrunkAggregatorInfoIndex OBJECT-TYPE
        SYNTAX      Integer32
        MAX-ACCESS  read-only
        STATUS      current
        DESCRIPTION "Index of trunk information table."
        ::= { portTrunkAggregatorInfoEntry 1 }

portTrunkAggregatorInfoGroupName OBJECT-TYPE
        SYNTAX      DisplayString (SIZE(0..80))
        MAX-ACCESS  read-only
        STATUS      current
        DESCRIPTION "The name of trunk group."
        ::= { portTrunkAggregatorInfoEntry 2 }

portTrunkAggregatorInfoDescription OBJECT-TYPE
        SYNTAX      DisplayString (SIZE(0..255))
        MAX-ACCESS  read-only
        STATUS      current
        DESCRIPTION "The dscription of trunk group."
        ::= { portTrunkAggregatorInfoEntry 3 }

portTrunkAggregatorLACPStatus OBJECT-TYPE
        SYNTAX      INTEGER
                    {
                        enabled(1), 
                        disabled(2)
                    }
        MAX-ACCESS  read-write
        STATUS      current
        DESCRIPTION "The LACP function of trunking.
                     (1) LACP is enabled for the group.
                     (2) LACP is disabled for the group. "
        ::= { portTrunkAggregatorEntry 4 }

portTrunkAggregatorWorkPorts OBJECT-TYPE
        SYNTAX      Integer32
        MAX-ACCESS  read-write
        STATUS      current
        DESCRIPTION "The works ports of trunked group,  the number of work ports
        should be equal to the count of members in static trunking(ie. LACP is
        disabled),  and should not greater than the count of members in static/
        dynamic trunking."
        ::= { portTrunkAggregatorEntry 5 }

portTrunkLACPStateActTable OBJECT-TYPE
        SYNTAX      SEQUENCE OF PortTrunkLACPStateActEntry
        MAX-ACCESS  not-accessible
        STATUS      current
        DESCRIPTION "Table of descriptive information and configuration about
                     of each trunk group in this system."
        ::= { stateActivity 1 }

portTrunkLACPStateActEntry OBJECT-TYPE
        SYNTAX      PortTrunkLACPStateActEntry
        MAX-ACCESS  not-accessible
        STATUS      current
        DESCRIPTION "An entry in the table,  containing information
                     about LACP state activity of the trunk."
        INDEX       { portTrunkLACPStateActPortNum }
        ::= { portTrunkLACPStateActTable 1 }

PortTrunkLACPStateActEntry ::= SEQUENCE
{
    portTrunkLACPStateActPortNum     Integer32, 
    portTrunkLACPStateActStatus      INTEGER
}

portTrunkLACPStateActPortNum OBJECT-TYPE
        SYNTAX      Integer32
        MAX-ACCESS  read-only
        STATUS      current
        DESCRIPTION "Port number."
        ::= { portTrunkLACPStateActEntry 1 }

portTrunkLACPStateActStatus OBJECT-TYPE
        SYNTAX      INTEGER
                    {
                        active(1), 
                        passtive(2), 
                        disabled(3)
                    }
        MAX-ACCESS  read-write
        STATUS      current
        DESCRIPTION "The LACP state activity of the port.
                     (1) Active.
                     (2) Passive.
                     (3) LACP doesn't be enabled."
        ::= { portTrunkLACPStateActEntry 2 }

--
-- redundancy
--

redundantRing     OBJECT IDENTIFIER ::= { redundancy 1 }
rstp              OBJECT IDENTIFIER ::= { redundancy 3 }

--
-- redundantRing
--

redundantRingStatus OBJECT-TYPE
        SYNTAX      INTEGER
                    {
                        enabled(1), 
                        disabled(2)
                    }
        MAX-ACCESS  read-write
        STATUS      current
        DESCRIPTION "redundantRing function status.
                     (1) redundantRing function is enabled.
                     (2) redundantRing function is disabled."
        ::= { redundantRing 1 }

redundantRingMasterStatus OBJECT-TYPE
        SYNTAX      INTEGER
                    {
                        enabled(1), 
                        disabled(2)
                    }
        MAX-ACCESS  read-write
        STATUS      current
        DESCRIPTION "Ring Master function status.
                     (1) Ring Master function is enabled.
                     (2) Ring Master function is disabled.
                     This item can't be modified if redundantRingStatus
                     object is set to disabled(2)
                     "
        ::= { redundantRing 2 }

redundantRingPort1 OBJECT-TYPE
        SYNTAX      Integer32
        MAX-ACCESS  read-write
        STATUS      current
        DESCRIPTION "Port Id(1~8) will be working port.
                     The system will automatically decide which port
                     is working port and which port is backup port if
                     the redundantRingStatus object is set to enabled(1)."
        ::= { redundantRing 3 }


redundantRingPort2 OBJECT-TYPE
        SYNTAX Integer32
        MAX-ACCESS  read-write
        STATUS      current
        DESCRIPTION "Port Id(1~8) will be working port.
                     The system will automatically decide which port
                     is working port and which port is backup port if
                     the redundantRingStatus object is set to enabled(1)."
        ::= { redundantRing 4 }

redundantRingCoupleRingStatus OBJECT-TYPE
        SYNTAX      INTEGER
                    {
                        enabled(1), 
                        disabled(2)
                    }
        MAX-ACCESS  read-write
        STATUS      current
        DESCRIPTION "Couple Ring function status.
                     (1) Couple Ring function is enabled.
                     (2) Couple Ring function is disabled.
                     This item can't be modified if redundantRingStatus
                     object is set to disabled(2)
                     "
        ::= { redundantRing 5 }

redundantRingCouplingPort OBJECT-TYPE
        SYNTAX      Integer32
        MAX-ACCESS  read-write
        STATUS      current
        DESCRIPTION "Coupling Port."
        ::= { redundantRing 6 }

redundantRingDualHomingStatus OBJECT-TYPE
        SYNTAX      INTEGER
                    {
                        enabled(1), 
                        disabled(2)
                    }
        MAX-ACCESS  read-write
        STATUS      current
        DESCRIPTION "Couple Ring function status.
                     (1) Dual Homing  function is enabled.
                     (2) Dual Homing  function is disabled.
                     This item can't be modified if redundantRingStatus
                     object is set to disabled(2)
                     "
        ::= { redundantRing 7 }

redundantRingHomingPort OBJECT-TYPE
        SYNTAX      Integer32
        MAX-ACCESS  read-write
        STATUS      current
        DESCRIPTION "Homing Port."
        ::= { redundantRing 8 }

redundantRingMasterHStatus OBJECT-TYPE
        SYNTAX      INTEGER
                    {
                        enabled(1), 
                        disabled(2)
                    }
        MAX-ACCESS  read-only
        STATUS      current
        DESCRIPTION "Ring Master function hardware status.
                     (1) Ring Master function is enabled.
                     (2) Ring Master function is disabled.
                     This item can't be modified if redundantRingStatus
                     object is set to disabled(2)
                     "
        ::= { redundantRing 9 }


--
-- rstp
--

rstpStatus OBJECT-TYPE
        SYNTAX      INTEGER
                    {
                        enalbed(1), 
                        disabled(2)
                    }
        MAX-ACCESS  read-write
        STATUS      current
        DESCRIPTION "Enable/Disable rapid spanning tree protocol for system."
        ::= { rstp 1 }

rstpPriority OBJECT-TYPE
        SYNTAX      Integer32
        MAX-ACCESS  read-write
        STATUS      current
        DESCRIPTION "A value used to identify the root bridge. The bridge with
                     the lowest value has the highest priority and is selected
                     as the root. Enter a number 0 through 61440 in steps of
                     4096. If you change the value,  you must restart RSTP.
                     This item can't be modified,  if rstpStatus was disabled."
        ::= { rstp 2 }

rstpMaxAge OBJECT-TYPE
        SYNTAX      Integer32
        MAX-ACCESS  read-write
        STATUS      current
        DESCRIPTION "The number of seconds a bridge waits without receiving
                     Spanning-Tree Protocol configuration messages before
                     attempting a reconfiguration. Enter a number 6 through
                     40.
                     Note: 2*(Forward Delay Time-1) should be greater than or
                     equal to the Max Age. The Max Age should be greater
                     than or equal to 2*(Hello Time + 1).
                     This item can't be modified,  if rstpStatus was disabled."
        ::= { rstp 3 }

rstpHelloTime  OBJECT-TYPE
        SYNTAX      Integer32
        MAX-ACCESS  read-write
        STATUS      current
        DESCRIPTION "The number of seconds between the transmission of
                     Spanning-Tree Protocol configuration messages.
                     Enter a number 1 through 10
                     Note: 2*(Forward Delay Time-1) should be greater than or
                     equal to the Max Age. The Max Age should be greater
                     than or equal to 2*(Hello Time + 1).
                     This item can't be modified,  if rstpStatus was disabled."
        ::= { rstp 4 }

rstpForwardDelayTime  OBJECT-TYPE
        SYNTAX      Integer32
        MAX-ACCESS  read-write
        STATUS      current
        DESCRIPTION "The number of seconds a port waits before changing
                     from its Spanning-Tree Protocol learning and listening
                     states to the forwarding state. Enter a number 4 through
                     30.
                     Note:2*(Forward Delay Time-1) should be greater than or
                     equal to the Max Age. The Max Age should be greater
                     than or equal to 2*(Hello Time + 1).
                     This item can't be modified,  if rstpStatus was disabled."
        ::= { rstp 5 }

rstpPerPortCfgTable OBJECT-TYPE
        SYNTAX      SEQUENCE OF RstpPerPortCfgEntry
        MAX-ACCESS  not-accessible
        STATUS      current
        DESCRIPTION "Table of descriptive information and configuration about
                     rapid spanning tree (Per port)."
        ::= { rstp 6 }

rstpPerPortCfgEntry OBJECT-TYPE
        SYNTAX      RstpPerPortCfgEntry
        MAX-ACCESS  not-accessible
        STATUS      current
        DESCRIPTION "An entry in the table,  containing configuration
                     about RSTP (Per port)."
        INDEX       { rstpPerPortCfgPortNum }
        ::= { rstpPerPortCfgTable 1 }

RstpPerPortCfgEntry ::= SEQUENCE
{
    rstpPerPortCfgPortNum         Integer32, 
    rstpPerPortCfgPathCost        Integer32, 
    rstpPerPortCfgPriority        Integer32, 
    rstpPerPortCfgAdminP2P        INTEGER, 
    rstpPerPortCfgAdminEdge       INTEGER, 
    rstpPerPortCfgAdminNonStp     INTEGER
}

rstpPerPortCfgPortNum OBJECT-TYPE
        SYNTAX      Integer32
        MAX-ACCESS  read-only
        STATUS      current
        DESCRIPTION "Port number."
        ::= { rstpPerPortCfgEntry 1 }

rstpPerPortCfgPathCost OBJECT-TYPE
        SYNTAX      Integer32
        MAX-ACCESS  read-write
        STATUS      current
        DESCRIPTION "The cost of the path to the other bridge from
                     this transmitting bridge at the specified port.
                     Enter a number 1 through 200000000."
        ::= { rstpPerPortCfgEntry 2 }

rstpPerPortCfgPriority OBJECT-TYPE
        SYNTAX      Integer32
        MAX-ACCESS  read-write
        STATUS      current
        DESCRIPTION "Decide which port should be blocked by priority
                     in LAN. Enter a number 0 through 240 in steps of
                     16."
        ::= { rstpPerPortCfgEntry 3 }

rstpPerPortCfgAdminP2P OBJECT-TYPE
        SYNTAX      INTEGER
                    {
                        true(1), 
                        false(2), 
                        auto(3)
                    }
        MAX-ACCESS  read-write
        STATUS      current
        DESCRIPTION "Some of the rapid state transactions that are
                     possible within RSTP are dependent upon whether
                     the Port concerned can only be connected to
                     exactly one other Bridge(ie.,  it is served by a
                     point-to-point LAN segment),  or can be connected
                     to two or more Bridges(i.e.,  it is served by a
                     shared medium LAN segment).
                     The adminPointToPointMAC allow the p2p status
                     of the link to be manipulated adminitratively."
        ::= { rstpPerPortCfgEntry 4 }

rstpPerPortCfgAdminEdge OBJECT-TYPE
        SYNTAX      INTEGER
                    {
                        true(1), 
                        false(2)
                    }
        MAX-ACCESS  read-write
        STATUS      current
        DESCRIPTION "Present in implementations that support the
                     identification of edge ports. All ports
                     directly connected to end stations cannot
                     create bridging loops in the network and can
                     thus directly transition to forwarding, 
                     skipping the listening and learning stages."
        ::= { rstpPerPortCfgEntry 5 }

rstpPerPortCfgAdminNonStp OBJECT-TYPE
        SYNTAX      INTEGER
                    {
                        true(1), 
                        false(2)
                    }
        MAX-ACCESS  read-write
        STATUS      current
        DESCRIPTION "If true,  this port will not participate in RSTP."
        ::= { rstpPerPortCfgEntry 6 }

rstpRootBridgeInformationTable OBJECT-TYPE
        SYNTAX      SEQUENCE OF RstpRootBridgeInformationEntry
        MAX-ACCESS  not-accessible
        STATUS      current
        DESCRIPTION "Table of descriptive information about root bridge
                     of rapid spanning tree in this system."
        ::= { rstp 7 }

rstpRootBridgeInformationEntry OBJECT-TYPE
        SYNTAX      RstpRootBridgeInformationEntry
        MAX-ACCESS  not-accessible
        STATUS      current
        DESCRIPTION "An entry in the table,  containing information
                     about root bridge information of the RSTP."
        INDEX       { rstpRootBridgeInformationIndex }
        ::= { rstpRootBridgeInformationTable 1 }

RstpRootBridgeInformationEntry ::= SEQUENCE
{
    rstpRootBridgeInformationIndex         Integer32, 
    rstpRootBridgeInformationBridgeID      DisplayString, 
    rstpRootBridgeInformationRootPriority  Integer32, 
    rstpRootBridgeInformationRootPort      DisplayString, 
    rstpRootBridgeInformationRootPathCost  Integer32, 
    rstpRootBridgeInformationMaxAge        Integer32, 
    rstpRootBridgeInformationHelloTime     Integer32, 
    rstpRootBridgeInformationForwardDelay  Integer32
}

rstpRootBridgeInformationIndex OBJECT-TYPE
        SYNTAX      Integer32
        MAX-ACCESS  not-accessible
        STATUS      current
        DESCRIPTION "Index of root bridge information table."
        ::= { rstpRootBridgeInformationEntry 1 }

rstpRootBridgeInformationBridgeID OBJECT-TYPE
        SYNTAX      DisplayString (SIZE(0..255))
        MAX-ACCESS  read-only
        STATUS      current
        DESCRIPTION "Bridge ID."
        ::= { rstpRootBridgeInformationEntry 2 }

rstpRootBridgeInformationRootPriority OBJECT-TYPE
        SYNTAX      Integer32
        MAX-ACCESS  read-only
        STATUS      current
        DESCRIPTION "Root Priority."
        ::= { rstpRootBridgeInformationEntry 3 }

rstpRootBridgeInformationRootPort  OBJECT-TYPE
        SYNTAX      DisplayString (SIZE(0..80))
        MAX-ACCESS  read-only
        STATUS      current
        DESCRIPTION "Root Port."
        ::= { rstpRootBridgeInformationEntry 4 }

rstpRootBridgeInformationRootPathCost OBJECT-TYPE
        SYNTAX      Integer32
        MAX-ACCESS  read-only
        STATUS      current
        DESCRIPTION "Root Path Cost."
        ::= { rstpRootBridgeInformationEntry 5 }

rstpRootBridgeInformationMaxAge  OBJECT-TYPE
        SYNTAX      Integer32
        MAX-ACCESS  read-only
        STATUS      current
        DESCRIPTION "Max Age."
        ::= { rstpRootBridgeInformationEntry 6 }

rstpRootBridgeInformationHelloTime OBJECT-TYPE
        SYNTAX      Integer32
        MAX-ACCESS  read-only
        STATUS      current
        DESCRIPTION "Hello Time."
        ::= { rstpRootBridgeInformationEntry 7 }

rstpRootBridgeInformationForwardDelay  OBJECT-TYPE
        SYNTAX      Integer32
        MAX-ACCESS  read-only
        STATUS      current
        DESCRIPTION "Forward Delay Time."
        ::= { rstpRootBridgeInformationEntry 8 }


rstpPerPortInfoTable OBJECT-TYPE
        SYNTAX      SEQUENCE OF RstpPerPortInfoEntry
        MAX-ACCESS  not-accessible
        STATUS      current
        DESCRIPTION "Table of descriptive information and configuration about
                     rapid spanning tree (Per port)."
        ::= { rstp 8 }

rstpPerPortInfoEntry OBJECT-TYPE
        SYNTAX      RstpPerPortInfoEntry
        MAX-ACCESS  not-accessible
        STATUS      current
        DESCRIPTION "An entry in the table,  containing inforamtion
                     about RSTP (Per port)."
        INDEX       { rstpPerPortInfoPortNum }
        ::= { rstpPerPortInfoTable 1 }

RstpPerPortInfoEntry ::= SEQUENCE
{
    rstpPerPortInfoPortNum         Integer32, 
    rstpPerPortInfoPathCost        Integer32, 
    rstpPerPortInfoPriority        Integer32, 
    rstpPerPortInfoAdminP2P        INTEGER, 
    rstpPerPortInfoAdminEdge       INTEGER, 
    rstpPerPortInfoStpNeighbor     INTEGER, 
    rstpPerPortInfoState           INTEGER, 
    rstpPerPortInfoRole            INTEGER
}

rstpPerPortInfoPortNum OBJECT-TYPE
        SYNTAX      Integer32
        MAX-ACCESS  read-only
        STATUS      current
        DESCRIPTION "Port number."
        ::= { rstpPerPortInfoEntry 1 }

rstpPerPortInfoPathCost OBJECT-TYPE
        SYNTAX      Integer32
        MAX-ACCESS  read-only
        STATUS      current
        DESCRIPTION "The cost of the path to the other bridge from
                     this transmitting bridge at the specified port.
                     Enter a number 1 through 200000000."
        ::= { rstpPerPortInfoEntry 2 }

rstpPerPortInfoPriority OBJECT-TYPE
        SYNTAX      Integer32
        MAX-ACCESS  read-only
        STATUS      current
        DESCRIPTION "Decide which port should be blocked by priority
                     in LAN. Enter a number 0 through 240 in steps of
                     16."
        ::= { rstpPerPortInfoEntry 3 }

rstpPerPortInfoAdminP2P OBJECT-TYPE
        SYNTAX      INTEGER
                    {
                        auto(1), 
                        true(2), 
                        false(3)
                    }
        MAX-ACCESS  read-only
        STATUS      current
        DESCRIPTION "Some of the rapid state transactions that are
                     possible within RSTP are dependent upon whether
                     the Port concerned can only be connected to
                     exactly one other Bridge(ie.,  it is served by a
                     point-to-point LAN segment),  or can be connected
                     to two or more Bridges(i.e.,  it is served by a
                     shared medium LAN segment).
                     The adminPointToPointMAC allow the p2p status
                     of the link to be manipulated adminitratively."
        ::= { rstpPerPortInfoEntry 4 }

rstpPerPortInfoAdminEdge OBJECT-TYPE
        SYNTAX      INTEGER
                    {
                        true(1), 
                        false(2)
                    }
        MAX-ACCESS  read-only
        STATUS      current
        DESCRIPTION "Present in implementations that support the
                     identification of edge ports. All ports
                     directly connected to end stations cannot
                     create bridging loops in the network and can
                     thus directly transition to forwarding, 
                     skipping the listening and learning stages."
        ::= { rstpPerPortInfoEntry 5 }

rstpPerPortInfoStpNeighbor OBJECT-TYPE
        SYNTAX      INTEGER
                    {
                        true(1), 
                        false(2)
                    }
        MAX-ACCESS  read-only
        STATUS      current
        DESCRIPTION " "
        ::= { rstpPerPortInfoEntry 6 }

rstpPerPortInfoState OBJECT-TYPE
        SYNTAX      INTEGER
                    {
                        nonStp(1), 
                        learning(2), 
                        forwarding(3), 
                        disabled(4), 
                        discarding(5), 
                        unknown(6)
                    }
        MAX-ACCESS  read-only
        STATUS      current
        DESCRIPTION " "
        ::= { rstpPerPortInfoEntry 7 }

rstpPerPortInfoRole OBJECT-TYPE
        SYNTAX      INTEGER
                    {
                        disabled(1), 
                        root(2), 
                        designated(3), 
                        alternated(4), 
                        backup(5), 
                        nonStp(6), 
                        unknown(7)
                    }
        MAX-ACCESS  read-only
        STATUS      current
        DESCRIPTION " "
        ::= { rstpPerPortInfoEntry 8 }

--
-- vlan
--

vlanOperationMode OBJECT-TYPE
        SYNTAX      INTEGER
                    {
                        ieee8021q(1), 
                        portbased(2), 
                        disabled(3)
                    }
        MAX-ACCESS  read-write
        STATUS      current
        DESCRIPTION "The operation mode of vlan.
                        (1)IEEE802.1Q VLAN, 
                        (2)Portbased VLAN, 
                        (3)VLAN is disabled."
        ::= { vlan 1 }

vlanGVRP OBJECT-TYPE
        SYNTAX      INTEGER
                    {
                        enabled(1), 
                        disabled(2)
                    }
        MAX-ACCESS  read-write
        STATUS      current
        DESCRIPTION "Enable GVRP Protocol. The item has no meaning, 
                     if the operation mode of vlan isn't IEEE802.1Q."
        ::= { vlan 2 }

vlanIEEE8021QTable OBJECT-TYPE
        SYNTAX      SEQUENCE OF VlanIEEE8021QEntry
        MAX-ACCESS  not-accessible
        STATUS      current
        DESCRIPTION "Table of descriptive information and configuration about
                     IEEE802.1Q group in this system.
                     Tag-based VLANs are based on IEEE 802.1Q
                     specifications. Traffic is forwarded to VLAN member
                     ports based on identifying VLAN tags in data packets.
                     You can also configure the switch to interoperate
                     with existing tag-based VLAN networks and legacy
                     non-tag networks."
        ::= { vlan 3 }

vlanIEEE8021QEntry OBJECT-TYPE
        SYNTAX      VlanIEEE8021QEntry
        MAX-ACCESS  not-accessible
        STATUS      current
        DESCRIPTION "An entry in the table,  containing information
                     and configuration of IEEE802.1Q vlan."
        INDEX       { vlanIEEE8021QIndex }
        ::= { vlanIEEE8021QTable 1 }

VlanIEEE8021QEntry ::= SEQUENCE
{
    vlanIEEE8021QIndex         Integer32, 
    vlanIEEE8021QPortName      DisplayString, 
    vlanIEEE8021QLinkType      INTEGER, 
    vlanIEEE8021QUntaggedVid   Integer32, 
    vlanIEEE8021QTaggedVids    DisplayString
}

vlanIEEE8021QIndex OBJECT-TYPE
        SYNTAX      Integer32
        MAX-ACCESS  read-only
        STATUS      current
        DESCRIPTION "Index of IEEE802.1Q table."
        ::= { vlanIEEE8021QEntry 1 }

vlanIEEE8021QPortName OBJECT-TYPE
        SYNTAX      DisplayString (SIZE(0..16))
        MAX-ACCESS  read-only
        STATUS      current
        DESCRIPTION "The name of port."
        ::= { vlanIEEE8021QEntry 2 }

vlanIEEE8021QLinkType OBJECT-TYPE
        SYNTAX      INTEGER
                    {
                        accesslink(1), 
                        trunklink(2), 
                        hybridlink(3)
                    }
        MAX-ACCESS  read-write
        STATUS      current
        DESCRIPTION "The type of port:
                     (1)Access Link
                     (2)Trunk Link
                     (3)Hybrid Link"
        ::= { vlanIEEE8021QEntry 3 }

vlanIEEE8021QUntaggedVid OBJECT-TYPE
        SYNTAX      Integer32
        MAX-ACCESS  read-write
        STATUS      current
        DESCRIPTION "The untagged vid of port. This item can't be
                    modified,  if link type is trunklink."
        ::= { vlanIEEE8021QEntry 4 }

vlanIEEE8021QTaggedVids OBJECT-TYPE
        SYNTAX      DisplayString (SIZE(0..255))
        MAX-ACCESS  read-write
        STATUS      current
        DESCRIPTION "The tagged vids of port. It's a descriptive statement
                     of a list of tagged vids.
                     Note: Every tagged vid is separated by a comma and
                     no space-key be allowed. This item can't be modified, 
                     if link type is accesslink."
        ::= { vlanIEEE8021QEntry 5 }

vlanIEEE8021QGroupTable OBJECT-TYPE
        SYNTAX      SEQUENCE OF VlanIEEE8021QGroupEntry
        MAX-ACCESS  not-accessible
        STATUS      current
        DESCRIPTION "Table of descriptive information and configuration of
                     each ieee802.1q group in this system.
                     Tag-based VLANs are based on IEEE 802.1Q
                     specifications. Traffic is forwarded to VLAN member
                     ports based on identifying VLAN tags in data packets.
                     You can also configure the switch to interoperate
                     with existing tag-based VLAN networks and legacy
                     non-tag networks."
        ::= { vlan 4 }

vlanIEEE8021QGroupEntry OBJECT-TYPE
        SYNTAX      VlanIEEE8021QGroupEntry
        MAX-ACCESS  not-accessible
        STATUS      current
        DESCRIPTION "An entry in the table,  containing information
                     about group name of the IEEE802.1Q vlan."
        INDEX       { vlanIEEE8021QGroupVid }
        ::= { vlanIEEE8021QGroupTable 1 }

VlanIEEE8021QGroupEntry ::= SEQUENCE
{
    vlanIEEE8021QGroupVid     Integer32, 
    vlanIEEE8021QGroupName    DisplayString, 
    vlanIEEE8021QGroupStatus  INTEGER
}

vlanIEEE8021QGroupVid OBJECT-TYPE
        SYNTAX      Integer32
        MAX-ACCESS  read-only
        STATUS      current
        DESCRIPTION "Vlan ID."
        ::= { vlanIEEE8021QGroupEntry 1 }

vlanIEEE8021QGroupName  OBJECT-TYPE
        SYNTAX      DisplayString (SIZE(0..16))
        MAX-ACCESS  read-write
        STATUS      current
        DESCRIPTION "The group name of vlan."
        ::= { vlanIEEE8021QGroupEntry 2 }

vlanIEEE8021QGroupStatus OBJECT-TYPE
        SYNTAX      INTEGER
                    {
                        valid(1), 
                        invalid(2)
                    }
        MAX-ACCESS  read-write
        STATUS      current
        DESCRIPTION "The status of this entry. If this object is not equal to valid(1),  all associated
 	    vlan entries shall be deleted by the agent."
        ::= { vlanIEEE8021QGroupEntry 3 }

vlanPortBasedTable OBJECT-TYPE
        SYNTAX      SEQUENCE OF VlanPortBasedEntry
        MAX-ACCESS  not-accessible
        STATUS      current
        DESCRIPTION "Table of descriptive information and configuration about
                     of each port based vlan group in this
                     system. Traffic is forwarded to the member ports of
                     the same vlan group. By adding ports to the VLAN you
                     have created one port-based vlan group completely"
        ::= { vlan 5 }

vlanPortBasedEntry OBJECT-TYPE
        SYNTAX      VlanPortBasedEntry
        MAX-ACCESS  not-accessible
        STATUS      current
        DESCRIPTION "An entry in the table,  containing information
                     about port based vlan."
        INDEX       { vlanPortBasedIndex }
        ::= { vlanPortBasedTable 1 }

VlanPortBasedEntry ::= SEQUENCE
{
    vlanPortBasedIndex         Integer32, 
    vlanPortBasedGroupName     DisplayString, 
    vlanPortBasedVid           Integer32, 
    vlanPortBasedMembers       PortList, 
    vlanPortBasedStatus        INTEGER
}

vlanPortBasedIndex OBJECT-TYPE
        SYNTAX      Integer32
        MAX-ACCESS  read-only
        STATUS      current
        DESCRIPTION "Index of port-based vlan table."
        ::= { vlanPortBasedEntry 1 }

vlanPortBasedGroupName OBJECT-TYPE
        SYNTAX      DisplayString (SIZE(0..16))
        MAX-ACCESS  read-create
        STATUS      current
        DESCRIPTION "The group name of vlan."
        ::= { vlanPortBasedEntry 2 }

vlanPortBasedVid OBJECT-TYPE
        SYNTAX      Integer32
        MAX-ACCESS  read-create
        STATUS      current
        DESCRIPTION "The vid of vlan. Vid should be the value between
                     1 to 4094."
        ::= { vlanPortBasedEntry 3 }

vlanPortBasedMembers OBJECT-TYPE
        SYNTAX      PortList
        MAX-ACCESS  read-create
        STATUS      current
        DESCRIPTION "The member mask of vlan.
                     Note: If there were a trunking group,  all of trunking
                     members should be in the same vlan group.
                     If some members of trunking group doesn't be included
                     in vlan group,  the SNMP agent reports error."
        ::= { vlanPortBasedEntry 4 }

vlanPortBasedStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    vlan entries shall be deleted by the agent."
        ::= { vlanPortBasedEntry 5 }

--
-- snmp
--
snmpAgentMode OBJECT-TYPE
        SYNTAX      INTEGER
                    {
                        v1-v2Conly(1), 
                        v3(2)
                    }
        MAX-ACCESS  read-write
        STATUS      current
        DESCRIPTION "The Agent mode of snmp agent.
                     (1) SNMPV1/V2C Only.
                     (2) SNMPV3.
                     (3) SNMPV1/V2C/V3"
        ::= { snmp 1 }

snmpSystemName OBJECT-TYPE
        SYNTAX      DisplayString (SIZE(0..64))
        MAX-ACCESS  read-write
        STATUS      current
        DESCRIPTION "The system name."
        ::= { snmp 2 }

snmpSystemLocation OBJECT-TYPE
        SYNTAX      DisplayString (SIZE(0..64))
        MAX-ACCESS  read-write
        STATUS      current
        DESCRIPTION "The system location."
        ::= { snmp 3 }

snmpSystemContact OBJECT-TYPE
        SYNTAX      DisplayString (SIZE(0..64))
        MAX-ACCESS  read-write
        STATUS      current
        DESCRIPTION "The contact information of system."
        ::= { snmp 4 }

snmpCommunityStringTable OBJECT-TYPE
        SYNTAX      SEQUENCE OF SnmpCommunityStringEntry
        MAX-ACCESS  not-accessible
        STATUS      current
        DESCRIPTION "Table of descriptive and information about
                     community string of SNMP agent."
        ::= { snmp 5 }

snmpCommunityStringEntry OBJECT-TYPE
        SYNTAX      SnmpCommunityStringEntry
        MAX-ACCESS  not-accessible
        STATUS      current
        DESCRIPTION "An entry in the table,  containing inforamtion
                     about community string of SNMP agent."
        INDEX       { snmpCommunityStringIndex }
        ::= { snmpCommunityStringTable 1 }

SnmpCommunityStringEntry ::= SEQUENCE
{
    snmpCommunityStringIndex      Integer32, 
    snmpCommunityStringName       DisplayString, 
    snmpCommunityStringAttribute  INTEGER, 
    snmpCommunityStringStatus     INTEGER
}

snmpCommunityStringIndex OBJECT-TYPE
        SYNTAX      Integer32
        MAX-ACCESS  not-accessible
        STATUS      current
        DESCRIPTION "Index of community string."
        ::= { snmpCommunityStringEntry 1 }

snmpCommunityStringName OBJECT-TYPE
        SYNTAX      DisplayString (SIZE(0..32))
        MAX-ACCESS  read-write
        STATUS      current
        DESCRIPTION "The community string of SNMP agent."
        ::= { snmpCommunityStringEntry 2 }

snmpCommunityStringAttribute OBJECT-TYPE
        SYNTAX      INTEGER
                    {
                        ro(1), 
                        rw(2)
                    }
        MAX-ACCESS  read-write
        STATUS      current
        DESCRIPTION "The attribute of community string."
        ::= { snmpCommunityStringEntry 3 }

snmpCommunityStringStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    snmp entries shall be deleted by the agent."
        ::= { snmpCommunityStringEntry 4 }

snmpTrapServerTable OBJECT-TYPE
        SYNTAX      SEQUENCE OF SnmpTrapServerEntry
        MAX-ACCESS  not-accessible
        STATUS      current
        DESCRIPTION "Table of descriptive and information about
                     trap server of SNMP agent."
        ::= { snmp 6 }

snmpTrapServerEntry OBJECT-TYPE
        SYNTAX      SnmpTrapServerEntry
        MAX-ACCESS  not-accessible
        STATUS      current
        DESCRIPTION "An entry in the table,  containing inforamtion
                     about trap server of SNMP agent."
        INDEX       { snmpTrapServerIndex }
        ::= { snmpTrapServerTable 1 }

SnmpTrapServerEntry ::= SEQUENCE
{
    snmpTrapServerIndex      Integer32, 
    snmpTrapServerIPAddr     IpAddress, 
    snmpTrapServerTrapComm   DisplayString, 
    snmpTrapServerTrapVer    INTEGER, 
    snmpTrapServerStatus     INTEGER
}

snmpTrapServerIndex OBJECT-TYPE
        SYNTAX      Integer32
        MAX-ACCESS  not-accessible
        STATUS      current
        DESCRIPTION "Index of trap server."
        ::= { snmpTrapServerEntry 1 }

snmpTrapServerIPAddr OBJECT-TYPE
        SYNTAX      IpAddress
        MAX-ACCESS  read-write
        STATUS      current
        DESCRIPTION "Trap Server IP Address."
        ::= { snmpTrapServerEntry 2 }

snmpTrapServerTrapComm OBJECT-TYPE
        SYNTAX      DisplayString (SIZE(0..32))
        MAX-ACCESS  read-write
        STATUS      current
        DESCRIPTION "The community string of trap server."
        ::= { snmpTrapServerEntry 3 }

snmpTrapServerTrapVer OBJECT-TYPE
        SYNTAX      INTEGER
                    {
                        v1(1), 
                        v2c(2)
                    }
        MAX-ACCESS  read-write
        STATUS      current
        DESCRIPTION "The trap version."
        ::= { snmpTrapServerEntry 4 }

snmpTrapServerStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    snmp entries shall be deleted by the agent."
        ::= { snmpTrapServerEntry 5 }

--
-- trafficPrioritization
--

qosPolicy OBJECT-TYPE
        SYNTAX      INTEGER
                    {
                        an-8-4-2-1-weighted-fair-queuing-scheme(1), 
                        a-strict-priority-scheme(2)
                    }
        MAX-ACCESS  read-write
        STATUS      current
        DESCRIPTION "(1)Using the 8, 4, 2, 1 weight fair queue scheme.
                     (2)Use the strict priority scheme.
                     Using the 8, 4, 2, 1 weight fair queue scheme: the switch will follow 8:4:2:1
                     rate to process priority queue from Hi to lowest queue. For example: the
                     system will process 8 high queue packets,  4 middle queue packets,  2 low queue
                     packets,  and the one lowest queue packets at the same time.
                     Use the strict priority scheme: Always higher queue will be process first, 
                     except higher queue is empty."
        ::= { trafficPrioritization 1 }

qosPriorityType OBJECT-TYPE
        SYNTAX      INTEGER
                    {
                        port-base(1), 
                        cos-only(2), 
                        tos-only(3), 
                        cos-first(4), 
                        tos-first(5), 
                        disabled(6)
                    }
        MAX-ACCESS  read-write
        STATUS      current
        DESCRIPTION "(1)Port Base
                     (2)COS only
                     (3)TOS only
                     (4)COS first
                     (5)TOS first
                     (6)Disabled
                     Port-base: the port priority will follow the default port priority that you have assigned - High,  middle,  low,  or lowest.
                     COS only: the port priority will only follow the COS priority that you have assigned.
                     TOS only: the port priority will only follow the TOS priority that you have assigned.
                     COS first: the port priority will follow the COS priority first,  and then other priority rule.
                     TOS first: the port priority will follow the TOS priority first,  and the other priority rule."
        ::= { trafficPrioritization 2 }

qosPortBasedPriorityTable OBJECT-TYPE
        SYNTAX      SEQUENCE OF QosPortBasedPriorityEntry
        MAX-ACCESS  not-accessible
        STATUS      current
        DESCRIPTION "Table of descriptive information and configuration about
                     PortBased QOS."
        ::= { trafficPrioritization 3 }

qosPortBasedPriorityEntry OBJECT-TYPE
        SYNTAX      QosPortBasedPriorityEntry
        MAX-ACCESS  not-accessible
        STATUS      current
        DESCRIPTION "An entry in the table,  containing inforamtion
                     about PortBased QOS."
        INDEX       { qosPortBasedPriorityPortNum }
        ::= { qosPortBasedPriorityTable 1 }

QosPortBasedPriorityEntry ::= SEQUENCE
{
    qosPortBasedPriorityPortNum    Integer32, 
    qosPortBasedPriority           INTEGER
}

qosPortBasedPriorityPortNum OBJECT-TYPE
        SYNTAX      Integer32
        MAX-ACCESS  read-only
        STATUS      current
        DESCRIPTION "Port number."
        ::= { qosPortBasedPriorityEntry 1 }

qosPortBasedPriority OBJECT-TYPE
        SYNTAX      INTEGER
                    {
                        lowest(1), 
                        low(2), 
                        middle(3), 
                        high(4)
                    }
        MAX-ACCESS  read-write
        STATUS      current
        DESCRIPTION "The port priority will follow the default port priority
                     that you have assigned - (1)lowest,  (2)low,  (3)middle, 
                     or (4)High."
        ::= { qosPortBasedPriorityEntry 2 }

qosCOSTable OBJECT-TYPE
        SYNTAX      SEQUENCE OF QosCOSEntry
        MAX-ACCESS  not-accessible
        STATUS      current
        DESCRIPTION "Table of descriptive information and configuration about
                     PortBased QOS."
        ::= { trafficPrioritization 4 }

qosCOSEntry OBJECT-TYPE
        SYNTAX      QosCOSEntry
        MAX-ACCESS  not-accessible
        STATUS      current
        DESCRIPTION "An entry in the table,  containing inforamtion
                     about COS QOS."
        INDEX       { qosCOSPriority }
        ::= { qosCOSTable 1 }

QosCOSEntry ::= SEQUENCE
{
    qosCOSPriority    Integer32, 
    qosCOS           INTEGER
}

qosCOSPriority OBJECT-TYPE
        SYNTAX      Integer32
        MAX-ACCESS  read-only
        STATUS      current
        DESCRIPTION "COS priority."
        ::= { qosCOSEntry 1 }

qosCOS OBJECT-TYPE
        SYNTAX      INTEGER
                    {
                        lowest(1), 
                        low(2), 
                        middle(3), 
                        high(4)
                    }
        MAX-ACCESS  read-write
        STATUS      current
        DESCRIPTION "The port priority will follow the COS priority that you have assigned
                     - (1)lowest,  (2)low,  (3)middle,  or (4)High."
        ::= { qosCOSEntry 2 }

qosCOSPortDefaultTable OBJECT-TYPE
        SYNTAX      SEQUENCE OF QosCOSPortDefaultEntry
        MAX-ACCESS  not-accessible
        STATUS      current
        DESCRIPTION "Table of descriptive information and configuration about
                     PortBased QOS."
        ::= { trafficPrioritization 5 }

qosCOSPortDefaultEntry OBJECT-TYPE
        SYNTAX      QosCOSPortDefaultEntry
        MAX-ACCESS  not-accessible
        STATUS      current
        DESCRIPTION "An entry in the table,  containing inforamtion
                     about COS QOS."
        INDEX       { qosCOSPriority }
        ::= { qosCOSPortDefaultTable 1 }

QosCOSPortDefaultEntry ::= SEQUENCE
{
    qosCOSPort    Integer32, 
    qosCOSPortDefault   Integer32
}

qosCOSPort OBJECT-TYPE
        SYNTAX      Integer32
        MAX-ACCESS  read-only
        STATUS      current
        DESCRIPTION "COS Default Panel Port."
        ::= { qosCOSPortDefaultEntry 1 }

qosCOSPortDefault OBJECT-TYPE
        SYNTAX      Integer32
        MAX-ACCESS  read-write
        STATUS      current
        DESCRIPTION "COS Default Panel Port Priority."
        ::= { qosCOSPortDefaultEntry 2 }

qosTOSTable OBJECT-TYPE
        SYNTAX      SEQUENCE OF QosTOSEntry
        MAX-ACCESS  not-accessible
        STATUS      current
        DESCRIPTION "Table of descriptive information and configuration about
                     PortBased QOS."
        ::= { trafficPrioritization 6 }

qosTOSEntry OBJECT-TYPE
        SYNTAX      QosTOSEntry
        MAX-ACCESS  not-accessible
        STATUS      current
        DESCRIPTION "An entry in the table,  containing inforamtion
                     about TOS QOS."
        INDEX       { qosTOSPriority }
        ::= { qosTOSTable 1 }

QosTOSEntry ::= SEQUENCE
{
    qosTOSPriority    Integer32, 
    qosTOS           INTEGER
}

qosTOSPriority OBJECT-TYPE
        SYNTAX      Integer32
        MAX-ACCESS  read-only
        STATUS      current
        DESCRIPTION "TOS priority."
        ::= { qosTOSEntry 1 }

qosTOS OBJECT-TYPE
        SYNTAX      INTEGER
                    {
                        lowest(1), 
                        low(2), 
                        middle(3), 
                        high(4)
                    }
        MAX-ACCESS  read-write
        STATUS      current
        DESCRIPTION "The port priority will follow the TOS priority that you have assigned
                     - (1)lowest,  (2)low,  (3)middle,  or (4)High."
        ::= { qosTOSEntry 2 }


--
-- multicast
--

igmp               OBJECT IDENTIFIER ::= { multicast 1 }
multicastfiltering OBJECT IDENTIFIER ::= { multicast 3 }

--
-- igmp
--

igmpStatus OBJECT-TYPE
        SYNTAX      INTEGER
                    {
                        igmpv2(1), 
                        igmpv3(2), 
                        disabled(3)
                    }
        MAX-ACCESS  read-write
        STATUS      current
        DESCRIPTION "Parameter to enable or disable IGMP snooping on the device.
                     When enabled,  the device will examine IGMP packets and set
                     up filters for IGMP ports.

                     The Internet Group Management Protocol (IGMP) is an internal
                     protocol of the Internet Protocol (IP) suite. IP manages
                     multicast traffic by using switches,  routers,  and hosts that
                     support IGMP. Enabling IGMP allows the ports to detect IGMP
                     queries and report packets and manage IP multicast traffic
                     through the switch. IGMP have three fundamental types of
                     message as follows:

                     Message     Description
                     --------------------------------------------------------------
                     Query       A message sent from the querier (IGMP router or switch)
                                 asking for a response from each host belonging to the
                                 multicast group.

                     Report      A message sent by a host to the querier to indicate
                                 that the host wants to be or is a member of a given
                                 group indicated in the report message.

                     Leave Group A message sent by a host to the querier to indicate
                                 that the host has quit to be a member of a specific
                                 multicast group.

                     You can enable IGMP protocol and IGMP Query function. You will see
                     the IGMP snooping information in this section -- difference
                     multicast group VID and member port,  and IP multicast addresses
                     range from 224.0.0.0 through 239.255.255.255."
        ::= { igmp  1 }

igmpQuery OBJECT-TYPE
        SYNTAX      INTEGER
                    {
                        auto(1), 
                        enabled(2), 
                        disabled(3)
                    }
        MAX-ACCESS  read-write
        STATUS      current
        DESCRIPTION "(1)Detect querier automatically.
                     (2)Force to be a querier.
                     (3)Be a silence snooper.
                     The mode of querier."
        ::= { igmp  2 }


igmpEntriesTable OBJECT-TYPE
        SYNTAX      SEQUENCE OF IgmpEntriesEntry
        MAX-ACCESS  not-accessible
        STATUS      current
        DESCRIPTION "Table of descriptive information about
                     IGMP entries."
        ::= { igmp  3 }

igmpEntriesEntry OBJECT-TYPE
        SYNTAX      IgmpEntriesEntry
        MAX-ACCESS  not-accessible
        STATUS      current
        DESCRIPTION "An entry in the table,  containing inforamtion
                     about IGMP."
        INDEX       { igmpEntriesEntryIndex }
        ::= { igmpEntriesTable 1 }

IgmpEntriesEntry ::= SEQUENCE
{
    igmpEntriesEntryIndex    Integer32, 
    igmpEntriesEntryIPAddr   IpAddress, 
    igmpEntriesEntryVID      Integer32, 
    igmpEntriesEntryMembers  PortList
}

igmpEntriesEntryIndex OBJECT-TYPE
        SYNTAX      Integer32
        MAX-ACCESS  read-only
        STATUS      current
        DESCRIPTION "Index of IGMP table."
        ::= { igmpEntriesEntry 1 }

igmpEntriesEntryIPAddr  OBJECT-TYPE
                SYNTAX      IpAddress
                MAX-ACCESS  read-only
                STATUS      current
                DESCRIPTION "The IP address of an IGMP entry."
        ::= { igmpEntriesEntry 2 }

igmpEntriesEntryVID OBJECT-TYPE
        SYNTAX      Integer32
        MAX-ACCESS  read-only
        STATUS      current
        DESCRIPTION "The VLAN ID of an IGMP entry."
        ::= { igmpEntriesEntry 3 }

igmpEntriesEntryMembers OBJECT-TYPE
        SYNTAX PortList
        MAX-ACCESS  read-only
        STATUS      current
    DESCRIPTION
        "The member ports mask of IGMP entry."
        ::= { igmpEntriesEntry 4 }

--
-- multicastfiltering
--

multicastfilteringEntriesTable OBJECT-TYPE
        SYNTAX      SEQUENCE OF MulticastfilteringEntriesEntry
        MAX-ACCESS  not-accessible
        STATUS      current
        DESCRIPTION "Table of descriptive information about
                     multicast filtering entries."
        ::= { multicastfiltering 1 }

multicastfilteringEntriesEntry OBJECT-TYPE
        SYNTAX      MulticastfilteringEntriesEntry
        MAX-ACCESS  not-accessible
        STATUS      current
        DESCRIPTION "An entry in the table,  containing inforamtion
                     about multicast filtering entries."
        INDEX       { multicastFilteringIndex }
        ::= { multicastfilteringEntriesTable 1 }

MulticastfilteringEntriesEntry ::= SEQUENCE
{
    multicastFilteringIndex        Integer32, 
    multicastFilteringAddr         IpAddress, 
    multicastFilteringMemberports  PortList, 
    multicastFilteringStatus       INTEGER
}

multicastFilteringIndex OBJECT-TYPE
        SYNTAX      Integer32
        MAX-ACCESS  not-accessible
        STATUS      current
        DESCRIPTION "This object identifies the switch within the system
                     for which this entry contains information."
        ::= { multicastfilteringEntriesEntry 1 }

multicastFilteringAddr OBJECT-TYPE
        SYNTAX      IpAddress
        MAX-ACCESS  read-write
        STATUS      current
        DESCRIPTION "Group IP Address."
        ::= { multicastfilteringEntriesEntry 2 }

multicastFilteringMemberports OBJECT-TYPE
        SYNTAX      PortList
        MAX-ACCESS  read-create
        STATUS      current
        DESCRIPTION "The member mask of group."
        ::= { multicastfilteringEntriesEntry 3 }

multicastFilteringStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    vlan entries shall be deleted by the agent."
        ::= { multicastfilteringEntriesEntry 4 }

--
-- security
--
ipSecurityMgt      OBJECT IDENTIFIER ::= { security 1 }
portSecurityMgt    OBJECT IDENTIFIER ::= { security 2 }
macBlacklist       OBJECT IDENTIFIER ::= { security 3 }
ieee8021x          OBJECT IDENTIFIER ::= { security 4 }

--
-- ipSecurityMgt
--

ipSecurityStatus OBJECT-TYPE
        SYNTAX      INTEGER
                    {
                        enabled(1), 
                        disabled(2)
                    }
        MAX-ACCESS  read-write
        STATUS      current
        DESCRIPTION "IP Security function status.
                     (1) IP Security function is enabled.
                     (2) IP Security function is disabled."
        ::= { ipSecurityMgt 1 }

ipSecurityHTTPServerStatus OBJECT-TYPE
        SYNTAX      INTEGER
                    {
                        enabled(1), 
                        disabled(2)
                    }
        MAX-ACCESS  read-write
        STATUS      current
        DESCRIPTION "IP Security function status.
                     (1) IP Security of HTTP server function is enabled.
                     (2) IP Security of HTTP server function is disabled."
        ::= { ipSecurityMgt 2 }

ipSecurityTelnetServerStatus OBJECT-TYPE
        SYNTAX      INTEGER
                    {
                        enabled(1), 
                        disabled(2)
                    }
        MAX-ACCESS  read-write
        STATUS      current
        DESCRIPTION "IP Security function status.
                     (1) IP Security of telnet server function is enabled.
                     (2) IP Security of telnet server function is disabled."
        ::= { ipSecurityMgt 3 }

ipSecuritySNMPServerStatus OBJECT-TYPE
        SYNTAX      INTEGER
                    {
                        enabled(1), 
                        disabled(2)
                    }
        MAX-ACCESS  read-write
        STATUS      current
        DESCRIPTION "IP Security function status.
                     (1) IP Security of SNMP server function is enabled.
                     (2) IP Security of SNMP server function is disabled."
        ::= { ipSecurityMgt 4 }

ipSecuritySecurityIP1 OBJECT-TYPE
        SYNTAX      IpAddress
        MAX-ACCESS  read-write
        STATUS      current
        DESCRIPTION "This IP address can access and manage the
                     switch through the Web browser."
        ::= { ipSecurityMgt 5 }

ipSecuritySecurityIP2 OBJECT-TYPE
        SYNTAX      IpAddress
        MAX-ACCESS  read-write
        STATUS      current
        DESCRIPTION "This IP address can access and manage the
                     switch through the Web browser."
        ::= { ipSecurityMgt 6 }

ipSecuritySecurityIP3 OBJECT-TYPE
        SYNTAX      IpAddress
        MAX-ACCESS  read-write
        STATUS      current
        DESCRIPTION "This IP address can access and manage the
                     switch through the Web browser."
        ::= { ipSecurityMgt 7 }

ipSecuritySecurityIP4 OBJECT-TYPE
        SYNTAX      IpAddress
        MAX-ACCESS  read-write
        STATUS      current
        DESCRIPTION "This IP address can access and manage the
                     switch through the Web browser."
        ::= { ipSecurityMgt 8 }

ipSecuritySecurityIP5 OBJECT-TYPE
        SYNTAX      IpAddress
        MAX-ACCESS  read-write
        STATUS      current
        DESCRIPTION "This IP address can access and manage the
                     switch through the Web browser."
        ::= { ipSecurityMgt 9 }

ipSecuritySecurityIP6 OBJECT-TYPE
        SYNTAX      IpAddress
        MAX-ACCESS  read-write
        STATUS      current
        DESCRIPTION "This IP address can access and manage the
                     switch through the Web browser."
        ::= { ipSecurityMgt 10}

ipSecuritySecurityIP7 OBJECT-TYPE
        SYNTAX      IpAddress
        MAX-ACCESS  read-write
        STATUS      current
        DESCRIPTION "This IP address can access and manage the
                     switch through the Web browser."
        ::= { ipSecurityMgt 11}

ipSecuritySecurityIP8 OBJECT-TYPE
        SYNTAX      IpAddress
        MAX-ACCESS  read-write
        STATUS      current
        DESCRIPTION "This IP address can access and manage the
                     switch through the Web browser."
        ::= { ipSecurityMgt 12}

ipSecuritySecurityIP9 OBJECT-TYPE
        SYNTAX      IpAddress
        MAX-ACCESS  read-write
        STATUS      current
        DESCRIPTION "This IP address can access and manage the
                     switch through the Web browser."
        ::= { ipSecurityMgt 13}

ipSecuritySecurityIP10 OBJECT-TYPE
       SYNTAX      IpAddress
        MAX-ACCESS  read-write
        STATUS      current
        DESCRIPTION "This IP address can access and manage the
                     switch through the Web browser."
        ::= { ipSecurityMgt 14}


--
-- portSecurityMgt
--

portSecurityTable OBJECT-TYPE
        SYNTAX      SEQUENCE OF PortSecurityEntry
        MAX-ACCESS  not-accessible
        STATUS      current
        DESCRIPTION "Table of descriptive information about
                     static MAC per port configuration.
                     When you add a static MAC address,  it remains in the
                     switch's address table,  regardless of whether the device
                     is physically connected to the switch.
                     This saves the switch from having to re-learn a device's
                     MAC address when the disconnected or powered-off device
                     is active on the network again. "
        ::= { portSecurityMgt 1}

portSecurityEntry OBJECT-TYPE
        SYNTAX      PortSecurityEntry
        MAX-ACCESS  not-accessible
        STATUS      current
        DESCRIPTION "An entry in the table,  containing inforamtion
                     about static MAC per port configuration."
        INDEX       { portSecurityIndex }
        ::= { portSecurityTable 1 }

PortSecurityEntry ::= SEQUENCE
{
    portSecurityIndex    Integer32, 
    portSecurityPortName DisplayString, 
    portSecurityAddr     MacAddress, 
    portSecurityStatus   INTEGER
}

portSecurityIndex OBJECT-TYPE
        SYNTAX      Integer32
        MAX-ACCESS  not-accessible
        STATUS      current
        DESCRIPTION "Index of MAC."
        ::= { portSecurityEntry 1 }

portSecurityPortName OBJECT-TYPE
        SYNTAX      DisplayString(SIZE(0..7))
        MAX-ACCESS  read-write
        STATUS      current
        DESCRIPTION "The port name,  if you want to insert a new MAC entry, 
                    the port name must be correct (Please refer to the
                    switchCurrentPortNameListTable) when creating a new entry."
        ::= { portSecurityEntry 2 }

portSecurityAddr OBJECT-TYPE
        SYNTAX      MacAddress
        MAX-ACCESS  read-write
        STATUS      current
        DESCRIPTION "MAC address of the entry."
        ::= { portSecurityEntry 3 }

portSecurityStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    MAC entries shall be deleted by the agent."
        ::= { portSecurityEntry 4 }

--
-- macBlacklist
--

macBlacklistTable OBJECT-TYPE
        SYNTAX      SEQUENCE OF MACBlacklistEntry
        MAX-ACCESS  not-accessible
        STATUS      current
        DESCRIPTION "Table of descriptive information about
                     MAC filter configuration.
                     MAC address filtering allows the switch to drop
                     unwanted traffic. Traffic is filtered based on
                     the destination addresses. For example,  if your
                     network is congested because of high utilization
                     from one MAC address,  you can filter all traffic
                     transmitted to that MAC address,  restoring network
                      flow while you troubleshoot the problem."
        ::= { macBlacklist 1}

macBlacklistEntry OBJECT-TYPE
        SYNTAX      MACBlacklistEntry
        MAX-ACCESS  not-accessible
        STATUS      current
        DESCRIPTION "An entry in the table,  containing inforamtion
                     about MAC filter configuration."
        INDEX       { macBlacklistIndex }
        ::= { macBlacklistTable 1 }

MACBlacklistEntry ::= SEQUENCE
{
    macBlacklistIndex    Integer32, 
    macBlacklistAddr     MacAddress, 
    macBlacklistStatus      INTEGER
}

macBlacklistIndex OBJECT-TYPE
        SYNTAX      Integer32
        MAX-ACCESS  not-accessible
        STATUS      current
        DESCRIPTION "Index of MAC."
        ::= { macBlacklistEntry 1 }

macBlacklistAddr OBJECT-TYPE
        SYNTAX      MacAddress
        MAX-ACCESS  read-write
        STATUS      current
        DESCRIPTION "MAC address of the entry."
        ::= { macBlacklistEntry 2 }

macBlacklistStatus OBJECT-TYPE
        SYNTAX      INTEGER
                    {
                        valid(1), 
                        creatrequest(2), 
                        undercreation(3), 
                        invalid(4)
                    }
        MAX-ACCESS  read-create
        STATUS      current
        DESCRIPTION "The status of this entry. If this object is not equal to valid(1),  all associated
 	    MAC entries shall be deleted by the agent."
        ::= { macBlacklistEntry 3 }

--
-- ieee8021x
--

radiusServerSetting     OBJECT IDENTIFIER ::= { ieee8021x 1 }
portAuthConfiguration   OBJECT IDENTIFIER ::= { ieee8021x 2 }

radius8021xProtocolStatus OBJECT-TYPE
        SYNTAX      INTEGER
                    {
                        enabled(1), 
                        disabled(2)
                    }
        MAX-ACCESS  read-write
        STATUS      current
        DESCRIPTION "IEEE802.1x protocol function status.
                     (1) IEEE802.1x protocol function is enabled.
                     (2) IEEE802.1x protocol function is disabled.
                     802.1x makes use of the physical access characteristics
                     of IEEE802 LAN infrastructures in order to provide a
                     means of authenticating and authorizing devices attached
                     to a LAN port that has point-to-point connection
                     characteristics,  and of preventing access to that port
                     in cases in which the authentication and authorization
                     process fails."
        ::= { radiusServerSetting 1 }

radiusServerIP OBJECT-TYPE
        SYNTAX      IpAddress
        MAX-ACCESS  read-write
        STATUS      current
        DESCRIPTION "Radius Server IP Address: the ip address of the authentication server."
        ::= { radiusServerSetting 2 }

radiusServerPort OBJECT-TYPE
        SYNTAX      Integer32
        MAX-ACCESS  read-write
        STATUS      current
        DESCRIPTION "Server Port: The UDP port number used by the authentication server to authenticate."
        ::= { radiusServerSetting 3 }

radiusAccountingPort OBJECT-TYPE
        SYNTAX      Integer32
        MAX-ACCESS  read-write
        STATUS      current
        DESCRIPTION "Accounting Port: The UDP port number used by the authentication server to retrieve
                     accounting information. "
        ::= { radiusServerSetting 4 }

radiusSharedKey OBJECT-TYPE
        SYNTAX      DisplayString (SIZE(0..30))
        MAX-ACCESS  read-write
        STATUS      current
        DESCRIPTION "Shared Key: A key shared between this switch and authentication server."
        ::= { radiusServerSetting 5 }

radiusNASIdentifier OBJECT-TYPE
        SYNTAX      DisplayString (SIZE(0..30))
        MAX-ACCESS  read-write
        STATUS      current
        DESCRIPTION "NAS Identifier: A string used to identify this switch."
        ::= { radiusServerSetting 6 }

radiusMiscQuietPeriod OBJECT-TYPE
        SYNTAX      Integer32
        MAX-ACCESS  read-write
        STATUS      current
        DESCRIPTION "Quiet Period: used to define periods of time during
                     which it will not attempt to acquire a supplicant
                     (Default time is 60 seconds)."
        ::= { radiusServerSetting 7 }

radiusMiscTxPeriod OBJECT-TYPE
        SYNTAX      Integer32
        MAX-ACCESS  read-write
        STATUS      current
        DESCRIPTION "Tx Period: used to determine when an EAPOL PDU is to
                     be transmitted(Default value is 30 seconds)."
        ::= { radiusServerSetting 8 }

radiusMiscSupplicantTimeout OBJECT-TYPE
        SYNTAX      Integer32
        MAX-ACCESS  read-write
        STATUS      current
        DESCRIPTION "Supplicant Timeout: used to determine timeout conditions
                     in the exchanges between the supplicant and
                     authentication server(Default value is 30 seconds)."
        ::= { radiusServerSetting 9 }

radiusMiscServerTimeout OBJECT-TYPE
        SYNTAX      Integer32
        MAX-ACCESS  read-write
        STATUS      current
        DESCRIPTION "Server Timeout: used to determine timeout conditions
                     in the exchanges between the authenticator and
                     authentication server(Default value is 30 seconds)."
        ::= { radiusServerSetting 10}

radiusMiscReAuthMax OBJECT-TYPE
        SYNTAX      Integer32
        MAX-ACCESS  read-write
        STATUS      current
        DESCRIPTION "ReAuthMax: used to determine the number of
                     reauthentication attempts that are permitted
                     before the specific port becomes unauthorized
                     (Default value is 2 times)."
        ::= { radiusServerSetting 11}

radiusMiscReauthPeriod OBJECT-TYPE
        SYNTAX      Integer32
        MAX-ACCESS  read-write
        STATUS      current
        DESCRIPTION "Reauth Period: used to determine a nonzero number
                     of seconds between periodic reauthentication of
                     the supplications(Default value is 3600 seconds)."
        ::= { radiusServerSetting 12}

radiusPerPortCfgTable OBJECT-TYPE
        SYNTAX      SEQUENCE OF RadiusPerPortCfgEntry
        MAX-ACCESS  not-accessible
        STATUS      current
        DESCRIPTION "Table of descriptive information and configuration about
                     Radius per port configuration."
        ::= { portAuthConfiguration 1}

radiusPerPortCfgEntry OBJECT-TYPE
        SYNTAX      RadiusPerPortCfgEntry
        MAX-ACCESS  not-accessible
        STATUS      current
        DESCRIPTION "An entry in the table,  containing inforamtion
                     about Radius per port configuration."
        INDEX       { radiusPerPortCfgIndex }
        ::= { radiusPerPortCfgTable 1 }

RadiusPerPortCfgEntry ::= SEQUENCE
{
    radiusPerPortCfgIndex    Integer32, 
    radiusPerPortCfgPortName DisplayString, 
    radiusPerPortCfgState    INTEGER
}

radiusPerPortCfgIndex OBJECT-TYPE
        SYNTAX      Integer32
        MAX-ACCESS  not-accessible
        STATUS      current
        DESCRIPTION "Index of port."
        ::= { radiusPerPortCfgEntry 1 }

radiusPerPortCfgPortName OBJECT-TYPE
        SYNTAX      DisplayString (SIZE(0..16))
        MAX-ACCESS  read-only
        STATUS      current
        DESCRIPTION "The name of port."
        ::= { radiusPerPortCfgEntry 2 }

radiusPerPortCfgState OBJECT-TYPE
        SYNTAX      INTEGER
                    {
                        reject(1), 
                        accept(2), 
                        authorize(3), 
                        disabled(4)
                    }
        MAX-ACCESS  read-write
        STATUS      current
        DESCRIPTION "You can select the specific port and configure the
                     authorization state. Each port can select four kinds
                     of authorization state :
                     Reject: force the specific port to be unauthorized.
                     Accept: force the specific port to be authorized.
                     Authorize: the state of the specific port was determinied by
                     the outcome of the authentication.
                     Disable: the specific port didn't support 802.1x function."
        ::= { radiusPerPortCfgEntry 3 }

--
-- warning
--

faultAlarm               OBJECT IDENTIFIER ::= { warning 1 }
sysLogConfiguration      OBJECT IDENTIFIER ::= { warning 2 }
smtpConfiguration        OBJECT IDENTIFIER ::= { warning 3 }
eventSelection           OBJECT IDENTIFIER ::= { warning 4 }

--
-- faultAlarm
--
faultAlarmPwr1 OBJECT-TYPE
        SYNTAX      INTEGER
                    {
                        enabled(1), 
                        disabled(2)
                    }
        MAX-ACCESS  read-write
        STATUS      current
        DESCRIPTION "State of Power1 failure alarm."
        ::= { faultAlarm 1 }

faultAlarmPwr2 OBJECT-TYPE
        SYNTAX      INTEGER
                    {
                        enabled(1), 
                        disabled(2)
                    }
        MAX-ACCESS  read-write
        STATUS      current
        DESCRIPTION "State of Power1 failure alarm."
        ::= { faultAlarm 2 }

faultAlarmPortCfgTable OBJECT-TYPE
        SYNTAX      SEQUENCE OF FaultAlarmPortCfgEntry
        MAX-ACCESS  not-accessible
        STATUS      current
        DESCRIPTION "Table of descriptive information and configuration about
                     fault alarm per port configuration."
        ::= { faultAlarm 3}

faultAlarmPortCfgEntry OBJECT-TYPE
        SYNTAX      FaultAlarmPortCfgEntry
        MAX-ACCESS  not-accessible
        STATUS      current
        DESCRIPTION "An entry in the table,  containing inforamtion
                     about falut alarm per port configuration."
        INDEX       { faultAlarmPortCfgNum }
        ::= { faultAlarmPortCfgTable 1 }

FaultAlarmPortCfgEntry ::= SEQUENCE
{
    faultAlarmPortCfgNum        Integer32, 
    faultAlarmPortLinkStatus    INTEGER
}

faultAlarmPortCfgNum OBJECT-TYPE
        SYNTAX      Integer32
        MAX-ACCESS  read-only
        STATUS      current
        DESCRIPTION "Index of port."
        ::= { faultAlarmPortCfgEntry 1 }

faultAlarmPortLinkStatus OBJECT-TYPE
        SYNTAX      INTEGER
                    {
                        enabled(1), 
                        disabled(2)
                    }
        MAX-ACCESS  read-write
        STATUS      current
        DESCRIPTION "State of Port Link Down/Broken failure alarm."
        ::= { faultAlarmPortCfgEntry 2 }

--
-- eventSelection
--

systemEventsTable OBJECT-TYPE
        SYNTAX      SEQUENCE OF SystemEventsEntry
        MAX-ACCESS  not-accessible
        STATUS      current
        DESCRIPTION "Table of descriptive information about
                     system events."
        ::= { eventSelection 1 }

systemEventsEntry OBJECT-TYPE
        SYNTAX      SystemEventsEntry
        MAX-ACCESS  read-only
        STATUS      current
        DESCRIPTION "An entry in the table,  containing type of system events."
        INDEX       { eventSystemEventsIndex }
        ::= { systemEventsTable 1 }

SystemEventsEntry ::= SEQUENCE
{
    eventSystemEventsIndex           Integer32, 
    eventDeviceRestartEvent        INTEGER, 
    eventPowerStatusEvent            INTEGER, 
    eventAuthenticationFailureEvent  INTEGER, 
    eventRingTopologyChangeEvent INTEGER

}

eventSystemEventsIndex OBJECT-TYPE
        SYNTAX      Integer32
        MAX-ACCESS  not-accessible
        STATUS      current
        DESCRIPTION "Index of events."
        ::= {systemEventsEntry 1 }

eventDeviceRestartEvent OBJECT-TYPE
        SYNTAX      INTEGER
                    {
                        log(1), 
                        smtp(2), 
                        logandsmtp(3), 
                        disabled(4)
                    }
        MAX-ACCESS  read-write
        STATUS      current
        DESCRIPTION "Parameter to indicate the event should be logged or should be
                     sent as an Email alert.
                     The value can't be log(1) or logandsmtp(3),  if syslogStatus
                     is disabled. The value can't be smtp(2) or logandsmtp(3),  if
                     eventEmailAlertStatus is disabled."
        ::= { systemEventsEntry 2 }

eventPowerStatusEvent OBJECT-TYPE
        SYNTAX      INTEGER
                    {
                        log(1), 
                        smtp(2), 
                        logandsmtp(3), 
                        disabled(4)
                    }
        MAX-ACCESS  read-write
        STATUS      current
        DESCRIPTION "Parameter to indicate the event should be logged or should be
                     sent as an Email alert.
                     The value can't be log(1) or logandsmtp(3),  if syslogStatus
                     is disabled. The value can't be smtp(2) or logandsmtp(3),  if
                     eventEmailAlertStatus is disabled."
        ::= { systemEventsEntry 3 }

eventAuthenticationFailureEvent OBJECT-TYPE
        SYNTAX      INTEGER
                    {
                        log(1), 
                        smtp(2), 
                        logandsmtp(3), 
                        disabled(4)
                    }
        MAX-ACCESS  read-write
        STATUS      current
        DESCRIPTION "Parameter to indicate the event should be logged or should be
                     sent as an Email alert.
                     The value can't be log(1) or logandsmtp(3),  if syslogStatus
                     is disabled. The value can't be smtp(2) or logandsmtp(3),  if
                     eventEmailAlertStatus is disabled."
        ::= { systemEventsEntry 4 }

eventRingTopologyChangeEvent OBJECT-TYPE
        SYNTAX      INTEGER
                    {
                        log(1), 
                        smtp(2), 
                        logandsmtp(3), 
                        disabled(4)
                    }
        MAX-ACCESS  read-write
        STATUS      current
        DESCRIPTION "Parameter to indicate the event should be logged or should be
                     sent as an Email alert.
                     The value can't be log(1) or logandsmtp(3),  if syslogStatus
                     is disabled. The value can't be smtp(2) or logandsmtp(3),  if
                     eventEmailAlertStatus is disabled."
        ::= { systemEventsEntry 5 }

portEventsTable OBJECT-TYPE
        SYNTAX      SEQUENCE OF PortEventsEntry
        MAX-ACCESS  not-accessible
        STATUS      current
        DESCRIPTION "Table of descriptive information about
                     port events."
        ::= { eventSelection 2 }

portEventsEntry OBJECT-TYPE
        SYNTAX      PortEventsEntry
        MAX-ACCESS  not-accessible
        STATUS      current
        DESCRIPTION "An entry in the table,  containing type of port events."
        INDEX       { eventPortNumber }
        ::= { portEventsTable 1 }

PortEventsEntry ::= SEQUENCE
{
    eventPortNumber          Integer32, 
    eventPortEventLog        INTEGER, 
    eventPortEventSMTP       INTEGER
}

eventPortNumber OBJECT-TYPE
        SYNTAX      Integer32
        MAX-ACCESS  read-only
        STATUS      current
        DESCRIPTION "Port number for port event table."
        ::= {portEventsEntry 1 }

eventPortEventLog OBJECT-TYPE
        SYNTAX      INTEGER
                    {
                        linkup(1), 
                        linkdown(2), 
                        linkupandlinkdown(3), 
                        disabled(4)
                    }
        MAX-ACCESS  read-write
        STATUS      current
        DESCRIPTION "Parameter to indicate the which event should be logged.
                     The value can't be modified,  if syslogStatus is
                     disabled."
        ::= { portEventsEntry 2 }

eventPortEventSMTP OBJECT-TYPE
        SYNTAX      INTEGER
                    {
                        linkup(1), 
                        linkdown(2), 
                        linkupandlinkdown(3), 
                        disabled(4)
                    }
        MAX-ACCESS  read-write
        STATUS      current
        DESCRIPTION "Parameter to indicate the which event should be
                     an Email alert. The value can't be modified,  if
                     eventEmailAlertStatus is disabled."
        ::= { portEventsEntry 3 }

syslogStatus OBJECT-TYPE
        SYNTAX      INTEGER
                    {
                        clientOnly(1), 
                        serverOnly(2), 
                        bothClientAndServer(3), 
                        disabled(4)
                    }
        MAX-ACCESS  read-write
        STATUS      current
        DESCRIPTION "Parameter to specify the log should be sent to syslog server, 
                     or the log should be kept in switch. When disabled,  the
                     switch won't send out or record any log."
        ::= { sysLogConfiguration 1 }

eventServerAddr OBJECT-TYPE
        SYNTAX      IpAddress
        MAX-ACCESS  read-write
        STATUS      current
        DESCRIPTION "The IP address of syslog server. It can't be modified
                     when syslogStatus is disabled."
        ::= { sysLogConfiguration 2 }

eventEmailAlertStatus OBJECT-TYPE
        SYNTAX      INTEGER
                    {
                        enabled(1), 
                        disabled(2)
                    }
        MAX-ACCESS  read-write
        STATUS      current
        DESCRIPTION "Parameter to enable the Email alert feature,  When enabled, 
                     the switch will send the mail to the address presented in
                     emailAlertRcptTable."
        ::= { smtpConfiguration 1 }

eventEmailAlertAddr OBJECT-TYPE
        SYNTAX      DisplayString (SIZE(0..100))
        MAX-ACCESS  read-write
        STATUS      current
        DESCRIPTION "The IP address of SMTP server. It can't be modified when
                     eventEmailAlertStatus is disabled."
        ::= { smtpConfiguration 2 }

eventEmailAlertAuthentication OBJECT-TYPE
        SYNTAX      INTEGER
                    {
                        enabled(1), 
                        disabled(2)
                    }
        MAX-ACCESS  read-write
        STATUS      current
        DESCRIPTION "Parameter to enable the authentication feature SMTP server.
                     It can't be modified when eventEmailAlertStatus is disabled."
        ::= { smtpConfiguration 3 }

eventEmailAlertAccount OBJECT-TYPE
        SYNTAX      DisplayString (SIZE(0..70))
        MAX-ACCESS  read-write
        STATUS      current
        DESCRIPTION "The Email account for SMTP server. It can't be modified when
                     eventEmailAlertAuthentication is disabled."
        ::= { smtpConfiguration 4 }

eventEmailAlertPassword OBJECT-TYPE
        SYNTAX      DisplayString (SIZE(0..36))
        MAX-ACCESS  write-only
        STATUS      current
        DESCRIPTION "The password of Email account. It can't be modified when
                     eventEmailAlertAuthentication is disabled."
        ::= { smtpConfiguration 5 }

emailAlertRcptTable OBJECT-TYPE
        SYNTAX      SEQUENCE OF EmailAlertRcptEntry
        MAX-ACCESS  not-accessible
        STATUS      current
        DESCRIPTION "Table of descriptive information
                     of recipient Email address list."
        ::= { smtpConfiguration 6 }

emailAlertRcptEntry OBJECT-TYPE
        SYNTAX      EmailAlertRcptEntry
        MAX-ACCESS  not-accessible
        STATUS      current
        DESCRIPTION "An entry in the table,  containing recipient Email addresses."
        INDEX       { eventEmailAlertRcptIndex }
        ::= { emailAlertRcptTable 1 }

EmailAlertRcptEntry ::= SEQUENCE
{
    eventEmailAlertRcptIndex     Integer32, 
    eventEmailAlertRcptEmailAddr DisplayString
}

eventEmailAlertRcptIndex OBJECT-TYPE
        SYNTAX      Integer32
        MAX-ACCESS  read-only
        STATUS      current
        DESCRIPTION "Index of recipient Email address."
        ::= { emailAlertRcptEntry 1 }

eventEmailAlertRcptEmailAddr OBJECT-TYPE
        SYNTAX      DisplayString (SIZE(0..48))
        MAX-ACCESS  read-write
        STATUS      current
        DESCRIPTION "The recipient Email address."
        ::= { emailAlertRcptEntry 2 }

--
-- monitorAndDiag
--

macAddressTable          OBJECT IDENTIFIER ::= { monitorAndDiag 1 }
portStatistic            OBJECT IDENTIFIER ::= { monitorAndDiag 2 }
portmirroring            OBJECT IDENTIFIER ::= { monitorAndDiag 3 }
eventLog                 OBJECT IDENTIFIER ::= { monitorAndDiag 4 }

--
--  macAddressTable
--
agingTimeSetting OBJECT-TYPE
       SYNTAX  Integer32
       ACCESS  read-write
       STATUS  current
       DESCRIPTION   "The MAC address table flush time."
       ::= { macAddressTable 1 }

flushMACStatus OBJECT-TYPE
       SYNTAX      INTEGER
                   {
                       enabled(1), 
                       disabled(2)
                   }
       MAX-ACCESS  read-write
       STATUS      current
       DESCRIPTION "(1)Enable Flush MAC address table when ports link down.
                    (2)Disable Flush MAC address table when ports link down."
       ::= { macAddressTable 2 }

macAddrTable OBJECT-TYPE
        SYNTAX      SEQUENCE OF MACAddrEntry
        MAX-ACCESS  not-accessible
        STATUS      current
        DESCRIPTION "Table of descriptive information about
                     MAC filter configuration."
        ::= { macAddressTable 3}

macAddrEntry OBJECT-TYPE
        SYNTAX      MACAddrEntry
        MAX-ACCESS  not-accessible
        STATUS      current
        DESCRIPTION "An entry in the table,  containing inforamtion
                     about all MAC configuration."
        INDEX       { macAddressAddr }
        ::= { macAddrTable 1 }

MACAddrEntry ::= SEQUENCE
{
    macAddressAddr     MacAddress, 
    macAddressPortName DisplayString, 
    macAddressType     INTEGER
}

macAddressAddr OBJECT-TYPE
        SYNTAX      MacAddress
        MAX-ACCESS  read-only
        STATUS      current
        DESCRIPTION "MAC address of the entry."
        ::= { macAddrEntry 1 }

macAddressPortName OBJECT-TYPE
        SYNTAX      DisplayString(SIZE(0..7))
        MAX-ACCESS  read-only
        STATUS      current
        DESCRIPTION "The port name,  if you want to insert a new MAC entry, 
                    the port name must be correct (Please refer to the
                    switchCurrentPortNameListTable) when creating a new entry."
        ::= { macAddrEntry 2 }

macAddressType OBJECT-TYPE
        SYNTAX      INTEGER
                    {
                        dynamic(1), 
                        static(2)
                    }
        MAX-ACCESS  read-only
        STATUS      current
        DESCRIPTION "The type of this entry."
        ::= { macAddrEntry 3 }


portSecurityClearMACTable OBJECT-TYPE
        SYNTAX      INTEGER
                    {
                        active(1), 
                        notActive(2)
                    }
        MAX-ACCESS  read-write
        STATUS      current
        DESCRIPTION "Set to active for cleaning all the MAC entries in MAC table."
        ::= { macAddressTable 4}

--
--  portStatistic
--

switchPortStatTable OBJECT-TYPE
        SYNTAX      SEQUENCE OF SwitchPortStatEntry
        MAX-ACCESS  not-accessible
        STATUS      current
        DESCRIPTION "Table of descriptive and statistics information about
                     each switch ports(including expansion slot)."
        ::= { portStatistic 1 }

switchPortStatEntry OBJECT-TYPE
        SYNTAX      SwitchPortStatEntry
        MAX-ACCESS  not-accessible
        STATUS      current
        DESCRIPTION "An entry in the table,  containing information
                     about statistics in one switch port of the switch."
        INDEX       { swPortStatIndex }
        ::= { switchPortStatTable 1 }

SwitchPortStatEntry ::= SEQUENCE
{
    swPortStatIndex            Integer32, 
    swPortStatType             DisplayString, 
    swPortStatLink             INTEGER, 
    swPortStatState            INTEGER, 
    swPortStatTXGoodPkt        Integer32, 
    swPortStatTXBadPkt         Integer32, 
    swPortStatRXGoodPkt        Integer32, 
    swPortStatRXBadPkt         Integer32, 
    swPortStatTXAbortPkt       Integer32, 
    swPortStatPacketCollision  Integer32
}

swPortStatIndex OBJECT-TYPE
        SYNTAX      Integer32
        MAX-ACCESS  not-accessible
        STATUS      current
        DESCRIPTION "Index of port statistic table."
        ::= { switchPortStatEntry 1 }

swPortStatType OBJECT-TYPE
        SYNTAX      DisplayString(SIZE(0..10))
        MAX-ACCESS  read-only
        STATUS      current
        DESCRIPTION "Indicates the port type."
        ::= { switchPortStatEntry 2 }

swPortStatLink OBJECT-TYPE
        SYNTAX      INTEGER
                    {
                        up(1), 
                        down(2)
                    }
        MAX-ACCESS  read-only
        STATUS      current
        DESCRIPTION "Indicates the link state."
        ::= { switchPortStatEntry 3 }

swPortStatState OBJECT-TYPE
        SYNTAX      INTEGER
                    {
                        enabled(1), 
                        disabled(2)
                    }
        MAX-ACCESS  read-only
        STATUS      current
        DESCRIPTION "Indicates the port state"
        ::= { switchPortStatEntry 4 }

swPortStatTXGoodPkt OBJECT-TYPE
        SYNTAX      Integer32
        MAX-ACCESS  read-only
        STATUS      current
        DESCRIPTION "The count of good packets of TX."
        ::= { switchPortStatEntry 5 }

swPortStatTXBadPkt OBJECT-TYPE
        SYNTAX      Integer32
        MAX-ACCESS  read-only
        STATUS      current
        DESCRIPTION "The count of bad packets of TX."
        ::= { switchPortStatEntry 6 }

swPortStatRXGoodPkt OBJECT-TYPE
        SYNTAX      Integer32
        MAX-ACCESS  read-only
        STATUS      current
        DESCRIPTION "The count of good packets of RX."
        ::= { switchPortStatEntry 7 }

swPortStatRXBadPkt OBJECT-TYPE
        SYNTAX      Integer32
        MAX-ACCESS  read-only
        STATUS      current
        DESCRIPTION "The count of bad packets of RX."
        ::= { switchPortStatEntry 8 }

swPortStatTXAbortPkt OBJECT-TYPE
        SYNTAX      Integer32
        MAX-ACCESS  read-only
        STATUS      current
        DESCRIPTION "The count of abort packets of TX."
        ::= { switchPortStatEntry 9 }

swPortStatPacketCollision OBJECT-TYPE
        SYNTAX      Integer32
        MAX-ACCESS  read-only
        STATUS      current
        DESCRIPTION "The count of collision."
        ::= { switchPortStatEntry 10 }

--
--  portmirroring
--

swPortMirrorDestinationPortTX OBJECT-TYPE
        SYNTAX      Integer32
        MAX-ACCESS  read-write
        STATUS      current
        DESCRIPTION "The TX destination port (sniffer port).
                     Destination port can be used to see all monitor port traffic.
                     You can connect sniffer port to lan analysier or netxray."
        ::= { portmirroring 1 }

swPortMirrorDestinationPortRX OBJECT-TYPE
        SYNTAX      Integer32
        MAX-ACCESS  read-write
        STATUS      current
        DESCRIPTION "The RX destination port (sniffer port).
                     Destination port can be used to see all monitor port traffic.
                     You can connect sniffer port to lan analysier or netxray."
        ::= { portmirroring 2 }

switchPortMirrorSourceTable OBJECT-TYPE
        SYNTAX      SEQUENCE OF SwitchPortMirrorSourceEntry
        MAX-ACCESS  not-accessible
        STATUS      current
        DESCRIPTION "Table of descriptive information and configuration
                     of port mirror in this system.
                     The Port Sniffer is a method for monitor traffic
                     in switched networks. Use this tabe to select
                     monitor port for this switch."
        ::= { portmirroring 3 }

switchPortMirrorSourceEntry OBJECT-TYPE
        SYNTAX      SwitchPortMirrorSourceEntry
        MAX-ACCESS  not-accessible
        STATUS      current
        DESCRIPTION "An entry in the table,  containing information
                     about port mirror."
        INDEX       { swPortMirrorPortNum }
        ::= { switchPortMirrorSourceTable 1 }

SwitchPortMirrorSourceEntry ::= SEQUENCE
{
    swPortMirrorPortNum         Integer32, 
    swPortMirrorSourcePort      INTEGER
}

swPortMirrorPortNum OBJECT-TYPE
        SYNTAX      Integer32
        MAX-ACCESS  read-only
        STATUS      current
        DESCRIPTION "Port number."
        ::= { switchPortMirrorSourceEntry 1 }

swPortMirrorSourcePort OBJECT-TYPE
        SYNTAX      INTEGER
                    {
                        txonly(1), 
                        rxonly(2), 
                        rxandtx(3), 
                        disabled(4)
                    }
        MAX-ACCESS  read-write
        STATUS      current
        DESCRIPTION "The mode of source port (monitor port).
                     (1) TX only.
                     (2) RX only.
                     (3) RX and TX.
                     (4) Source port is disabled.
                     The ports you want to monitor. All source port traffic
                     will be copied to destination port (sniffer port)."
        ::= { switchPortMirrorSourceEntry 2 }

--
-- eventLog
--

eventLogTable OBJECT-TYPE
        SYNTAX      SEQUENCE OF EventLogEntry
        MAX-ACCESS  not-accessible
        STATUS      current
        DESCRIPTION "Table of descriptive information about
                     logs."
        ::= { eventLog 1 }

eventLogEntry OBJECT-TYPE
        SYNTAX      EventLogEntry
        MAX-ACCESS  not-accessible
        STATUS      current
        DESCRIPTION "An entry in the table,  containing list of logs."
        INDEX       { eventLogIndex }
        ::= { eventLogTable 1 }

EventLogEntry ::= SEQUENCE
{
    eventLogIndex          Integer32, 
    eventLogDescription    DisplayString
}

eventLogIndex OBJECT-TYPE
        SYNTAX      Integer32
        MAX-ACCESS  read-only
        STATUS      current
        DESCRIPTION "Index of log."
        ::= {eventLogEntry 1 }

eventLogDescription OBJECT-TYPE
        SYNTAX      DisplayString (SIZE(0..100))
        MAX-ACCESS  read-only
        STATUS      current
        DESCRIPTION "The description of log."
        ::= { eventLogEntry 2 }

--
-- saveConfiguration
--

saveCfgMgtAction OBJECT-TYPE
        SYNTAX      INTEGER
                    {
                        active(1), 
                        notActive(2)
                    }
        MAX-ACCESS  read-write
        STATUS      current
        DESCRIPTION "Setting this object to active(1) triger saving
                     current configuration.
                     Setting this object to notActive(2) has no effect.
                     The system always returns the value notActive(2)
                     when this object is read."
        ::= { saveConfiguration 1 }

--
-- factoryDefault
--

factoryDefaultAction OBJECT-TYPE
        SYNTAX      INTEGER
                    {
                        keep-ip-and-username-password(1), 
                        keep-ip(2), 
                        keep-username-password(3), 
                        keep-nothing(4), 
                        notActive(5)
                    }
        MAX-ACCESS  read-write
        STATUS      current
        DESCRIPTION "Setting this object to keep-ip-and-username-password(1),  keep-ip(2),  keep-username-password(3)
                     ,  and keep-nothing(4),  triger loading facotory default configuration.
                     Setting this object to notActive(5) has no effect.
                     The system always returns the value notActive(5)
                     when this object is read."
        ::= { factoryDefault 1 }

--
-- systemReboot
--

systemRebootAction OBJECT-TYPE
        SYNTAX      INTEGER
                    {
                        active(1), 
                        notActive(2)
                    }
        MAX-ACCESS  read-write
        STATUS      current
        DESCRIPTION "Setting this object to active(1) triger the system
                     restart.
                     Setting this object to notActive(2) has no effect.
                     The system always returns the value notActive(2)
                     when this object is read."
        ::= { systemReboot 1 }

--
-- misc
--
specificTrap              OBJECT IDENTIFIER ::= { misc 1 }

--
--specificTrap
--

trapPowerStatus OBJECT-TYPE
        SYNTAX      INTEGER
                    {
                        power1On-power2On(1), 
                        power1On-power2Off(2), 
                        power1Off-power2On(3), 
                        power1Off-power2Off(4)
                    }
        MAX-ACCESS  read-only
        STATUS      current
        DESCRIPTION "Indicates the switch power status"
        ::= { specificTrap 1 }

trapTopologyChange OBJECT-TYPE
        SYNTAX      Integer32
        MAX-ACCESS  read-only
        STATUS      current
        DESCRIPTION "redundantRing topology change counter."
        ::= { specificTrap 2 }

--
-- switchCurrentPortNameList
--

switchCurrentPortNameListTable OBJECT-TYPE
        SYNTAX      SEQUENCE OF SwitchCurrentPortNameListEntry
        MAX-ACCESS  not-accessible
        STATUS      current
        DESCRIPTION "Table of descriptive and status information about
                     the logical ports in this system."
        ::= { misc 2 }

switchCurrentPortNameListEntry OBJECT-TYPE
        SYNTAX      SwitchCurrentPortNameListEntry
        MAX-ACCESS  not-accessible
        STATUS      current
        DESCRIPTION "An entry in the table,  containing information
                     about logical port name in this system. "
        INDEX       { swCurrentPortNameListIndex }
        ::= { switchCurrentPortNameListTable 1 }

SwitchCurrentPortNameListEntry ::= SEQUENCE
{
    swCurrentPortNameListIndex      Integer32, 
    swCurrentPortNameListPortName   DisplayString, 
    swCurrentPortNameListPortNumber DisplayString
}

swCurrentPortNameListIndex OBJECT-TYPE
        SYNTAX      Integer32
        MAX-ACCESS  not-accessible
        STATUS      current
        DESCRIPTION "Index of logical port."
        ::= { switchCurrentPortNameListEntry 1 }

swCurrentPortNameListPortName OBJECT-TYPE
        SYNTAX      DisplayString (SIZE(0..7))
        MAX-ACCESS  read-only
        STATUS      current
        DESCRIPTION "The name of logical port."
        ::= { switchCurrentPortNameListEntry 2 }

swCurrentPortNameListPortNumber OBJECT-TYPE
        SYNTAX      DisplayString (SIZE(0..30))
        MAX-ACCESS  read-only
        STATUS      current
        DESCRIPTION "The port number(s) that port name belong to.
                     If the logical port stood for a trunk group,  this
                     object shows the members of trunk group."
        ::= { switchCurrentPortNameListEntry 3 }

--
-- powerOverEthernet
--

poeSystemSetting            OBJECT IDENTIFIER ::= { powerOverEthernet 1 }
poePortStatus               OBJECT IDENTIFIER ::= { powerOverEthernet 2 }
poePortControl              OBJECT IDENTIFIER ::= { powerOverEthernet 3 }

--
-- poeSystemSetting
--

poeMaximumPowerAvailable OBJECT-TYPE
                SYNTAX      Integer32
                MAX-ACCESS  read-write
                STATUS      current
                DESCRIPTION ""
        ::= { poeSystemSetting 1 }

poeActualPowerConsumption OBJECT-TYPE
                SYNTAX      Integer32
                MAX-ACCESS  read-only
                STATUS      current
                DESCRIPTION ""
        ::= { poeSystemSetting 2 }

poePortKnockoffDisabled OBJECT-TYPE
                SYNTAX      INTEGER
                            {
                                enabled(1), 
                                disabled(2)
                            }
                MAX-ACCESS  read-write
                STATUS      current
                DESCRIPTION "Port Knockoff Disabled"
        ::= { poeSystemSetting 3 }

poeACDisconnect OBJECT-TYPE
                SYNTAX      INTEGER
                            {
                                enabled(1), 
                                disabled(2)
                            }
                MAX-ACCESS  read-write
                STATUS      current
                DESCRIPTION "AC Disconnect"
        ::= { poeSystemSetting 4 }

poeCapacitiveDetection OBJECT-TYPE
                SYNTAX      INTEGER
                            {
                                enabled(1), 
                                disabled(2)
                            }
                MAX-ACCESS  read-write
                STATUS      current
                DESCRIPTION "Capacitive Detection"
        ::= { poeSystemSetting 5 }

--
-- poePortStatus
--

poePortStatusTable OBJECT-TYPE
        SYNTAX      SEQUENCE OF PoePortStatusEntry
        MAX-ACCESS  not-accessible
        STATUS      current
        DESCRIPTION ""
        ::= { poePortStatus 1 }

poePortStatusEntry OBJECT-TYPE
        SYNTAX      PoePortStatusEntry
        MAX-ACCESS  not-accessible
        STATUS      current
        DESCRIPTION ""
        INDEX       { poePortStatusIndex }
        ::= { poePortStatusTable 1 }

PoePortStatusEntry ::= SEQUENCE
{
    poePortStatusIndex              Integer32, 
    poePortStatusLink               INTEGER, 
    poePortStatusState              INTEGER, 
    poePortStatusCurrent            Integer32, 
    poePortStatusVoltage            DisplayString, 
    poePortStatusPower              Integer32, 
    poePortStatusDeterminedClass    DisplayString
}

poePortStatusIndex OBJECT-TYPE
        SYNTAX      Integer32
        MAX-ACCESS  read-only
        STATUS      current
        DESCRIPTION "This object identifies the switch within the system
                     for which this entry contains information. This
                     value can never be greater than switchNumber."
        ::= { poePortStatusEntry 1 }

poePortStatusLink OBJECT-TYPE
                SYNTAX      INTEGER
                            {
                                linkup(1), 
                                linkdown(2)
                            }
                MAX-ACCESS  read-only
                STATUS      current
                DESCRIPTION ""
        ::= { poePortStatusEntry 2 }

poePortStatusState OBJECT-TYPE
                SYNTAX      INTEGER
                            {
                                disabled(1), 
                                detecting(2), 
                                power-ieee(3), 
                                inactive(4), 
                                power-managed(5), 
                                invalid-pd(6), 
                                underload(7), 
                                overload(8), 
                                error(9), 
                                not-available(10)
                            }
                MAX-ACCESS  read-only
                STATUS      current
                DESCRIPTION ""
        ::= { poePortStatusEntry 3 }

poePortStatusCurrent OBJECT-TYPE
                SYNTAX      Integer32
                MAX-ACCESS  read-only
                STATUS      current
                DESCRIPTION "Current(mA)"
        ::= { poePortStatusEntry 4 }

poePortStatusVoltage OBJECT-TYPE
                SYNTAX      DisplayString (SIZE(0..200))
                MAX-ACCESS  read-only
                STATUS      current
                DESCRIPTION "Voltage(V)"
        ::= { poePortStatusEntry 5 }

poePortStatusPower OBJECT-TYPE
                SYNTAX      Integer32
                MAX-ACCESS  read-only
                STATUS      current
                DESCRIPTION "Power(mW)"
        ::= { poePortStatusEntry 6 }

poePortStatusDeterminedClass OBJECT-TYPE
                SYNTAX      DisplayString (SIZE(0..200))
                MAX-ACCESS  read-only
                STATUS      current
                DESCRIPTION ""
        ::= { poePortStatusEntry 7 }

--
-- poePortControl
--

poePortControlTable OBJECT-TYPE
        SYNTAX      SEQUENCE OF PoePortControlEntry
        MAX-ACCESS  not-accessible
        STATUS      current
        DESCRIPTION ""
        ::= { poePortControl 1 }

poePortControlEntry OBJECT-TYPE
        SYNTAX      PoePortControlEntry
        MAX-ACCESS  not-accessible
        STATUS      current
        DESCRIPTION ""
        INDEX       { poePortControlIndex }
        ::= { poePortControlTable 1 }

PoePortControlEntry ::= SEQUENCE
{
    poePortControlIndex                         Integer32, 
    poePortControlState                         INTEGER, 
    poePortControlPowerLimitFromClassification  INTEGER, 
    poePortControlLegacy                        INTEGER, 
    poePortControlPriority                      INTEGER, 
    poePortControlPowerLimit                    Integer32
}

poePortControlIndex OBJECT-TYPE
        SYNTAX      Integer32
        MAX-ACCESS  read-only
        STATUS      current
        DESCRIPTION "This object identifies the switch within the system
                     for which this entry contains information. This
                     value can never be greater than switchNumber."
        ::= { poePortControlEntry 1 }

poePortControlState OBJECT-TYPE
                SYNTAX      INTEGER
                            {
                                enable(1), 
                                disable(2)
                            }
                MAX-ACCESS  read-write
                STATUS      current
                DESCRIPTION "State"
        ::= { poePortControlEntry 2 }

poePortControlPowerLimitFromClassification OBJECT-TYPE
                SYNTAX      INTEGER
                            {
                                enable(1), 
                                disable(2)
                            }
                MAX-ACCESS  read-write
                STATUS      current
                DESCRIPTION "Power Limit From Classification"
        ::= { poePortControlEntry 3 }

poePortControlLegacy OBJECT-TYPE
                SYNTAX      INTEGER
                            {
                                enable(1), 
                                disable(2)
                            }
                MAX-ACCESS  read-write
                STATUS      current
                DESCRIPTION "Legacy"
        ::= { poePortControlEntry 4 }

poePortControlPriority OBJECT-TYPE
                SYNTAX      INTEGER
                            {
                                critical(1), 
                                high(2), 
                                low(3)
                            }
                MAX-ACCESS  read-write
                STATUS      current
                DESCRIPTION "Priority"
        ::= { poePortControlEntry 5 }

poePortControlPowerLimit OBJECT-TYPE
                SYNTAX      Integer32
                MAX-ACCESS  read-write
                STATUS      current
                DESCRIPTION "Power Limit (<15400)mW"
        ::= { poePortControlEntry 6 }

END
