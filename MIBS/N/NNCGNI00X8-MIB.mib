-- @(#)HubExtensions.mib	9.1 10/16/98
--------------------------------------------------------------------------------
-- file: HubExtensions.mib
--
-- contents:
--	This file contains the Newbridge MIB extensions for a 10BASET Repeater
--	module.  These extensions are designed to be used in conjunction with 
--	the 'rptrBasicPackage' part of the Repeater MIB (RFC 1368).  
--
--	A PositionIndex below maps directly to the XXXgroupIndex values used in
--	RFC 1368 as there is at most one repeater group per position (this 
--	follows the "encouragement" to do so given in Section 5.1.3 of 
--	RFC 1368).  Similarly the PortIndex values map directly to the 
--	similiarly named values used in the Repeater MIB.
--
-- history:
--	0.1 / 92.08.25 / J. Watt / Creation
--	0.2 / 93.02.08 / J. Watt / Added nncExtRptrPortOperStatus
--	0.3 / 93.02.11 / J. Watt / Fix RptrPortStatus names to match 17FS0014
--	0.4 / 93.02.17 / J. Watt / Fix OID for nncExtRptrPortOperStatus
--	0.5 / 93.04.04 / J. Watt / Fix case of RptrPortStatus enum values
--	0.6 / 93.06.01 / G. Celmainis /
--        Renamed nncExtModuleStatisticsMask to nncExtRptrModuleStatisticsMask
--	0.7 / 93.08.09 / B. McEachern /
--        Added description for nncExtRptrModuleStatisticsMask
--	0.8 / 93.09.01 / B. McEachern /
--        Create nncExtRptrPortIsolate object
--
-- Copyright 1992 to 1993 Newbridge Networks Corporation.  All Rights Reserved.
--------------------------------------------------------------------------------
NNCGNI00X8-MIB	DEFINITIONS ::= BEGIN


	IMPORTS
		nncExtRptr
			FROM NNCGNI00X1-SMI

		PositionIndex
			FROM NNCGNI00X4-MIB
			
		PortIndex
			FROM NNCGNI00X7-MIB
			
		Counter, TimeTicks
			FROM RFC1155-SMI
			
		OBJECT-TYPE
			FROM RFC-1212;
			
			
	RptrPortStatus ::= INTEGER { inService(1), forcedIsolate(2),
				     busyOut(3), autoIsolate(4),
				     linkDown(5) }

	RptrIsolationStatus ::= INTEGER { noPartitioning(1), partitionedPort(2) }

	nncExtRptrModuleTable	OBJECT-TYPE
		SYNTAX	SEQUENCE OF NncExtRptrModuleEntry
		ACCESS	not-accessible
		STATUS	mandatory
		DESCRIPTION
			"Configuration information for the Rptr modules
			 in the system"
		::= { nncExtRptr 1 }
		
	
	nncExtRptrModuleEntry	OBJECT-TYPE
		SYNTAX	NncExtRptrModuleEntry
		ACCESS	not-accessible
		STATUS	mandatory
		DESCRIPTION
			"Configuration information for a Rptr module"
		INDEX { nncExtRptrModulePositionIndex }
		::= { nncExtRptrModuleTable 1 }
		
		
	NncExtRptrModuleEntry 
		::= SEQUENCE {
			nncExtRptrModulePositionIndex
				PositionIndex,
			nncExtRptrModuleAdminMode
				INTEGER,
			nncExtRptrModuleOperMode
				INTEGER,
			nncExtRptrModuleStatisticsMask
				INTEGER
		}
		
	nncExtRptrModulePositionIndex	OBJECT-TYPE
		SYNTAX	PositionIndex
		ACCESS	read-only
		STATUS	mandatory
		DESCRIPTION
			"The position index of the module of interest"
		::= { nncExtRptrModuleEntry 1 }
		
	
	nncExtRptrModuleAdminMode	OBJECT-TYPE
		SYNTAX	INTEGER { repeater(1), cascade(2) }
		ACCESS	read-write
		STATUS	mandatory
		DESCRIPTION
			"Whether the module should try to operate as a
			 repeater or cascade module.  The actual mode, 
			 which depends on the installed modules, is
			 reported in nncExtRptrModuleOperMode"
		::= { nncExtRptrModuleEntry 2 }
			 
	
	nncExtRptrModuleOperMode		OBJECT-TYPE
		SYNTAX	INTEGER { repeater(1), cascade(2),  notPresent(3) }
		ACCESS	read-only
		STATUS	mandatory
		DESCRIPTION
			"What mode the module is operating in."
		::= { nncExtRptrModuleEntry 3 }
		
	
	nncExtRptrModuleStatisticsMask	OBJECT-TYPE
		SYNTAX	INTEGER (0..65535)
		ACCESS	read-write
		STATUS	mandatory
		DESCRIPTION
			"The statistics to be collected, represented as a sum.
			 The bit positions are defined as:
			 
			 Bit    Name                       Meaning
			 ---	---------------------      ------------
			 0	Jabber Protection		
			 1	Elastic Buffer Error
			 2	Phase Lock Error
			 3	Non SFD Packet
			 4	Pygmy Packet Reception     A runt packet
			 5	Packet Reception
			 6	Partition
			 7	Bad Link
			 8	ROR
			 9	FWF
			 10	Not Used
			 11	Transmit Collision
			 12	Receive Collision
			 13	Out of Window Collosion
			 14	Not Used
			 15	Not Used
			"
		::= { nncExtRptrModuleEntry 4 }
		
		
		
	nncExtRptrPortTable	OBJECT-TYPE
		SYNTAX	SEQUENCE OF NncExtRptrPortEntry
		ACCESS	not-accessible
		STATUS	mandatory
		DESCRIPTION
			"Configuration information for the repeater ports
			 in the system"
		::= { nncExtRptr 2 }
		
	
	nncExtRptrPortEntry	OBJECT-TYPE
		SYNTAX	NncExtRptrPortEntry
		ACCESS	not-accessible
		STATUS	mandatory
		DESCRIPTION
			"Configuration information for a repeater ports"
		INDEX { nncExtRptrPortPositionIndex, nncExtRptrPortIndex }
		::= { nncExtRptrPortTable 1 }
		
		
	NncExtRptrPortEntry 
		::= SEQUENCE {
			nncExtRptrPortPositionIndex
				PositionIndex,
			nncExtRptrPortIndex
				PortIndex,
			nncExtRptrPortAlarmEnable
				INTEGER,
			nncExtRptrPortLinkIntegrityLosses
				Counter,
			nncExtRptrPortAutoPartitions
				Counter,
			nncExtRptrPortAdminDisables
				Counter,
			nncExtRptrPortEvents
				Counter,
			nncExtRptrPortLastChange
				TimeTicks,
			nncExtRptrPortOperStatus
				RptrPortStatus,
			nncExtRptrPortIsolation
			        RptrIsolationStatus
		}
		
	nncExtRptrPortPositionIndex	OBJECT-TYPE
		SYNTAX	PositionIndex
		ACCESS	read-only
		STATUS	mandatory
		DESCRIPTION
			"The position index of the Port of interest"
		::= { nncExtRptrPortEntry 1 }

		
	nncExtRptrPortIndex	OBJECT-TYPE
		SYNTAX	PortIndex
		ACCESS	read-only
		STATUS	mandatory
		DESCRIPTION
			"The port number on the position of the port
			 of interest."
		::= { nncExtRptrPortEntry 2 }
		
		
	nncExtRptrPortAlarmEnable	OBJECT-TYPE
		SYNTAX	INTEGER { enabled(1), disabled(2) }
		ACCESS	read-write
		STATUS	mandatory
		DESCRIPTION
			"Whether or not an alarm should be generated on
			 a loss of link event."
		::= { nncExtRptrPortEntry 3 }
		
		
	nncExtRptrPortLinkIntegrityLosses	OBJECT-TYPE
		SYNTAX	Counter
		ACCESS	read-only
		STATUS	mandatory
		DESCRIPTION
			"The number of times link integrity has been lost."
		::= { nncExtRptrPortEntry 4 }
		
	
	nncExtRptrPortAutoPartitions	OBJECT-TYPE
		SYNTAX	Counter
		ACCESS	read-only
		STATUS	mandatory
		DESCRIPTION
			"The number of times the port has been 
			 auto-partitioned."
		::= { nncExtRptrPortEntry 5 }
		
		
	nncExtRptrPortAdminDisables	OBJECT-TYPE
		SYNTAX	Counter
		ACCESS	read-only
		STATUS	mandatory
		DESCRIPTION
			"The number of times the port has been disabled 
			 at the request of a management entity."
		::= { nncExtRptrPortEntry 6 }


	nncExtRptrPortEvents	OBJECT-TYPE
		SYNTAX	Counter
		ACCESS	read-only
		STATUS	mandatory
		DESCRIPTION
			"The number of times an event matching any of the
			 events described by ...ModuleStatisticsMask has
			 occurred on this port"
		::= { nncExtRptrPortEntry 7 }
		
		
	nncExtRptrPortLastChange	OBJECT-TYPE
		SYNTAX	TimeTicks
		ACCESS	read-only
		STATUS	mandatory
		DESCRIPTION
			"The last time rptrPortOperStatus changed for 
			 this port."
		::= { nncExtRptrPortEntry 8 }
		
	nncExtRptrPortOperStatus	OBJECT-TYPE
		SYNTAX	INTEGER { inService(1), forcedIsolate(2),
				     busyOut(3), autoIsolate(4),
				     linkDown(5) }
		ACCESS	read-only
		STATUS	mandatory
		DESCRIPTION
			"The current state of this repeater port"
		::= { nncExtRptrPortEntry 9 }

	nncExtRptrPortIsolation	OBJECT-TYPE
		SYNTAX	INTEGER { noPartitioning(1), partitionedPort(2) }
		ACCESS	read-write
		STATUS	mandatory
DESCRIPTION ""

		::= { nncExtRptrPortEntry 10 }

	END
