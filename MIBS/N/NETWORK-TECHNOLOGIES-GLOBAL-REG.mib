NETWORK-TECHNOLOGIES-GLOBAL-REG DEFINITIONS ::= BEGIN
IMPORTS
	MODULE-IDENTITY,
	OBJECT-TYPE,
	OBJECT-IDENTITY,
	enterprises,
	Integer32
		FROM SNMPv2-SMI

	DisplayString,
	TEXTUAL-CONVENTION
		FROM SNMPv2-TC
	;
      
-- the root of the subtree for Network Technologies Inc
nti				        OBJECT IDENTIFIER ::= {enterprises 3699}

-- subtree for products
products		        OBJECT IDENTIFIER ::= {nti 1}
experimental		    OBJECT IDENTIFIER ::= {nti 2}
hardware		        OBJECT IDENTIFIER ::= {products 1}
software		        OBJECT IDENTIFIER ::= {products 2}
enviromux-MINI          OBJECT IDENTIFIER ::= {hardware 3}
otherProduct            OBJECT IDENTIFIER ::= {hardware 200}
monitoring		        OBJECT IDENTIFIER ::= {enviromux-MINI 1}
administration		    OBJECT IDENTIFIER ::= {enviromux-MINI 2}
envTraps                OBJECT IDENTIFIER ::= {enviromux-MINI 100}
temperatureSensor1      OBJECT IDENTIFIER ::= {monitoring 1}
temperatureSensor2      OBJECT IDENTIFIER ::= {monitoring 2}
humiditySensor1         OBJECT IDENTIFIER ::= {monitoring 3}
humiditySensor2         OBJECT IDENTIFIER ::= {monitoring 4}
dryContact1             OBJECT IDENTIFIER ::= {monitoring 5}
dryContact2             OBJECT IDENTIFIER ::= {monitoring 6}
dryContact3             OBJECT IDENTIFIER ::= {monitoring 7}
dryContact4             OBJECT IDENTIFIER ::= {monitoring 8}
waterSensor             OBJECT IDENTIFIER ::= {monitoring 9}
hostSystem		        OBJECT IDENTIFIER ::= {administration 1}	
temperatureSensor1Adm   OBJECT IDENTIFIER ::= {administration 2}
temperatureSensor2Adm   OBJECT IDENTIFIER ::= {administration 3}
humiditySensor1Adm      OBJECT IDENTIFIER ::= {administration 4}
humiditySensor2Adm      OBJECT IDENTIFIER ::= {administration 5}
dryContact1Adm          OBJECT IDENTIFIER ::= {administration 6}
dryContact2Adm          OBJECT IDENTIFIER ::= {administration 7}
dryContact3Adm          OBJECT IDENTIFIER ::= {administration 8}
dryContact4Adm          OBJECT IDENTIFIER ::= {administration 9}
waterSensorAdm          OBJECT IDENTIFIER ::= {administration 10}

-- textual conventions
DecimalPointValue ::= TEXTUAL-CONVENTION
    DISPLAY-HINT    "d-1"
    STATUS          mandatory
    DESCRIPTION     
        "Display integer values using a decimal point before last digit"
    SYNTAX          Integer32

-- code version
version     OBJECT-TYPE
    SYNTAX  DisplayString
    ACCESS	read-only
    STATUS  mandatory
    DESCRIPTION
        "Code version"
    ::= {enviromux-MINI 3}         

-- temperature 1   

temperatureSensor1CurrentValue  OBJECT-TYPE
    SYNTAX  DecimalPointValue
	ACCESS	read-only
    STATUS  mandatory
    DESCRIPTION
        "Current value of the temperature sensor connected to port 1 in tenths of degrees .  
        This port is the right RJ-45 sensor port.  The value is expressed in the units 
        indicated in temperatureSensor1Unit.  
        This object is only applicable if a temperature sensor is connected to port 1."
::= {temperatureSensor1 1}

temperatureSensor1Alert  OBJECT-TYPE
    SYNTAX  INTEGER {off(0), on(1)}
	ACCESS	read-only
    STATUS  mandatory
    DESCRIPTION
        "Current alert status of the temperature sensor connected to port 1.  
        This port is the right RJ-45 sensor port.  A value of 0 indicates 
        that the sensor has not crossed either of its specified thresholds, 
        while a value of 1 indicates that it has.  
        This object is only applicable if a temperature sensor is connected to port 1."
::= {temperatureSensor1 2}
    
temperatureSensor1Name  OBJECT-TYPE
    SYNTAX  DisplayString
	ACCESS	read-write
    STATUS  mandatory
    DESCRIPTION
        "Current name assigned to the temperature sensor connected to port 1.  
        This port is the right RJ-45 sensor port. This value corresponds directly 
        with the name entered in the configuration page for this sensor.  
        This object is only applicable if a temperature sensor is connected to port 1."
::= {temperatureSensor1Adm 1}           

temperatureSensor1Unit  OBJECT-TYPE
    SYNTAX  DisplayString
	ACCESS	read-write
    STATUS  mandatory
    DESCRIPTION
        "Temperature units for the value of the temperature sensor connected to port 1.  
        This port is the right RJ-45 sensor port.  The unit may either be Fahrenheit or Celsius, 
        and corresponds directly with the unit chosen on the configuration page for this sensor.  
        This object is only applicable if a temperature sensor is connected to port 1 or 2."
::= {temperatureSensor1Adm 2}

temperatureSensor1LowThreshold  OBJECT-TYPE
    SYNTAX  DisplayString
	ACCESS	read-write
    STATUS  mandatory
    DESCRIPTION
        "Low threshold assigned to the temperature sensor connected to port 1.  
        This port is the right RJ-45 sensor port. This value corresponds directly 
        with the low threshold value entered in the configuration page for this sensor.  
        This object is only applicable if a temperature sensor is connected to port 1."
::= {temperatureSensor1Adm 3}           

temperatureSensor1HighThreshold  OBJECT-TYPE
    SYNTAX  DisplayString
	ACCESS	read-write
    STATUS  mandatory
    DESCRIPTION
        "High threshold assigned to the temperature sensor connected to port 1.  
        This port is the right RJ-45 sensor port. This value corresponds directly 
        with the high threshold value entered in the configuration page for this sensor.  
        This object is only applicable if a temperature sensor is connected to port 1."
::= {temperatureSensor1Adm 4}

-- temperature 2          
    
temperatureSensor2CurrentValue  OBJECT-TYPE
    SYNTAX  DecimalPointValue
	ACCESS	read-only
    STATUS  mandatory
    DESCRIPTION
        "Current value of the temperature sensor connected to port 2 in tenths of degrees .  
        This port is the left RJ-45 sensor port.  The value is expressed in the units 
        indicated in temperatureSensor2Unit.  
        This object is only applicable if a temperature sensor is connected to port 2."
::= {temperatureSensor2 1}

temperatureSensor2Alert  OBJECT-TYPE
    SYNTAX  INTEGER { off(0), on(1) }
	ACCESS	read-only
    STATUS  mandatory
    DESCRIPTION
        "Current alert status of the temperature sensor connected to port 2.  
        This port is the left RJ-45 sensor port.  A value of 0 indicates 
        that the sensor has not crossed either of its specified thresholds, 
        while a value of 1 indicates that it has.  
        This object is only applicable if a temperature sensor is connected to port 2."
::= {temperatureSensor2 2}

temperatureSensor2Name  OBJECT-TYPE
    SYNTAX  DisplayString
	ACCESS	read-write
    STATUS  mandatory
    DESCRIPTION
        "Current name assigned to the temperature sensor connected to port 2.  
        This port is the left RJ-45 sensor port. This value corresponds directly 
        with the name entered in the configuration page for this sensor.  
        This object is only applicable if a temperature sensor is connected to port 2."
::= {temperatureSensor2Adm 1} 

temperatureSensor2Unit  OBJECT-TYPE
    SYNTAX  DisplayString
	ACCESS	read-write
    STATUS  mandatory
    DESCRIPTION
        "Temperature units for the value of the temperature sensor connected to port 2.  
        This port is the left RJ-45 sensor port.  The unit may either be Fahrenheit or Celsius, 
        and corresponds directly with the unit chosen on the configuration page for this sensor.  
        This object is only applicable if a temperature sensor is connected to port 1 or 2."
::= {temperatureSensor2Adm 2}

temperatureSensor2LowThreshold  OBJECT-TYPE
    SYNTAX  DisplayString
	ACCESS	read-write
    STATUS  mandatory
    DESCRIPTION
         "Low threshold assigned to the temperature sensor connected to port 2.  
         This port is the left RJ-45 sensor port. This value corresponds directly 
         with the low threshold value entered in the configuration page for this sensor.  
         This object is only applicable if a temperature sensor is connected to port 2."
::= {temperatureSensor2Adm 3}           

temperatureSensor2HighThreshold  OBJECT-TYPE
    SYNTAX  DisplayString
	ACCESS	read-write
    STATUS  mandatory
    DESCRIPTION
        "High threshold assigned to the temperature sensor connected to port 2.  
        This port is the left RJ-45 sensor port. This value corresponds directly 
        with the high threshold value entered in the configuration page for this sensor.  
        This object is only applicable if a temperature sensor is connected to port 2."
::= {temperatureSensor2Adm 4}  

-- humidity 1

humiditySensor1CurrentValue  OBJECT-TYPE
    SYNTAX  DecimalPointValue
	ACCESS	read-only
    STATUS  mandatory
    DESCRIPTION
        "Current integer value in tenths of percents of the humidity sensor connected to port 1.  
        This port is the right RJ-45 sensor port.  The value corresponds directly with 
        the value displayed on the summary page and the status page for this sensor.  
        This object is only applicable if a humidity sensor is connected to port 1."
::= {humiditySensor1 1}

humiditySensor1Alert  OBJECT-TYPE
    SYNTAX  INTEGER {off(0), on(1)}
	ACCESS	read-only
    STATUS  mandatory
    DESCRIPTION
        "Current alert status of the humidity sensor connected to port 1.  
        This port is the right RJ-45 sensor port.  A value of 0 indicates 
        that the sensor has not crossed either of its specified thresholds, 
        while a value of 1 indicates that it has.  
        This object is only applicable if a humidity sensor is connected to port 1."
::= {humiditySensor1 2}

humiditySensor1Name  OBJECT-TYPE
    SYNTAX  DisplayString
	ACCESS	read-write
    STATUS  mandatory
    DESCRIPTION
        "Current name assigned to the humidity sensor connected to port 1.  
        This port is the right RJ-45 sensor port. This value corresponds directly 
        with the name entered in the configuration page for this sensor.  
        This object is only applicable if a humidity sensor is connected to port 1."
::= {humiditySensor1Adm 1}            

humiditySensor1LowThreshold  OBJECT-TYPE
    SYNTAX  DisplayString
	ACCESS	read-write
    STATUS  mandatory
    DESCRIPTION
        "Low threshold assigned to the humidity sensor connected to port 1.  
        This port is the right RJ-45 sensor port. This value corresponds directly 
        with the low threshold value entered in the configuration page for this sensor.  
        This object is only applicable if a humidity sensor is connected to port 1."
::= {humiditySensor1Adm 2}           

humiditySensor1HighThreshold  OBJECT-TYPE
    SYNTAX  DisplayString
	ACCESS	read-write
    STATUS  mandatory
    DESCRIPTION
        "High threshold assigned to the humidity sensor connected to port 1.  
        This port is the right RJ-45 sensor port. This value corresponds directly 
        with the high threshold value entered in the configuration page for this sensor.  
        This object is only applicable if a humidity sensor is connected to port 1."
::= {humiditySensor1Adm 3}

-- humidity 2

humiditySensor2CurrentValue  OBJECT-TYPE
    SYNTAX  DecimalPointValue
	ACCESS	read-only
    STATUS  mandatory
    DESCRIPTION
        "Current integer value in tenths of percents of the humidity sensor connected to port 2.  
        This port is the left RJ-45 sensor port.  The value corresponds directly 
        with the value displayed on the summary page and the status page for this sensor.  
        This object is only applicable if a humidity sensor is connected to port 2."
::= {humiditySensor2 1}

humiditySensor2Alert  OBJECT-TYPE
    SYNTAX  INTEGER {off(0), on(1)}
	ACCESS	read-only
    STATUS  mandatory
    DESCRIPTION
        "Current alert status of the humidity sensor connected to port 2.  
        This port is the left RJ-45 sensor port.  A value of 0 indicates 
        that the sensor has not crossed either of its specified thresholds, 
        while a value of 1 indicates that it has.  
        his object is only applicable if a humidity sensor is connected to port 2."
::= {humiditySensor2 2}

humiditySensor2Name  OBJECT-TYPE
    SYNTAX  DisplayString
	ACCESS	read-write
    STATUS  mandatory
    DESCRIPTION
        "Current name assigned to the humidity sensor connected to port 2.  
        This port is the left RJ-45 sensor port. This value corresponds directly 
        with the name entered in the configuration page for this sensor.  
        This object is only applicable if a humidity sensor is connected to port 2."
::= {humiditySensor2Adm 1}            
    
humiditySensor2LowThreshold  OBJECT-TYPE
    SYNTAX  DisplayString
	ACCESS	read-write
    STATUS  mandatory
    DESCRIPTION
        "Low threshold assigned to the humidity sensor connected to port 2.  
        This port is the left RJ-45 sensor port. This value corresponds directly 
        with the low threshold value entered in the configuration page for this sensor.  
        This object is only applicable if a humidity sensor is connected to port 2."
::= {humiditySensor2Adm 2}           

humiditySensor2HighThreshold  OBJECT-TYPE
    SYNTAX  DisplayString
	ACCESS	read-write
    STATUS  mandatory
    DESCRIPTION
        "High threshold assigned to the humidity sensor connected to port 1.  
        This port is the right RJ-45 sensor port. This value corresponds directly 
        with the high threshold value entered in the configuration page for this sensor.  
        This object is only applicable if a humidity sensor is connected to port 1."
::= {humiditySensor2Adm 3}             

-- dry contact 1

dryContact1Status  OBJECT-TYPE
    SYNTAX  INTEGER {open(0), closed(1)}
	ACCESS	read-only
    STATUS  mandatory
    DESCRIPTION
        "Current integer value of the dry contact sensor connected to port 1.  
        A value of 0 represents OPEN, and a value of 1 represents CLOSED.  
        The value corresponds directly with the value displayed on the 
        summary page and the status page for this sensor.  
        This object is only applicable if a dry contact sensor is connected to port 1."
::= {dryContact1 1}

dryContact1Alert  OBJECT-TYPE
    SYNTAX  INTEGER {off(0), on(1)}
	ACCESS	read-only
    STATUS  mandatory
    DESCRIPTION
        "Current alert status of the dry contact sensor connected to port 1.  
        A value of 0 indicates that the sensor has not been set to its alert condition, 
        while a value of 1 indicates that it has.  
        This object is only applicable if a dry contact sensor is connected to port 1."
::= {dryContact1 2}

dryContact1Name  OBJECT-TYPE
    SYNTAX  DisplayString
	ACCESS	read-write
    STATUS  mandatory
    DESCRIPTION
        "Current name assigned to the dry contact sensor connected to port 1.  
        This value corresponds directly with the name entered in the configuration page for this sensor.  
        This object is only applicable if a dry contact sensor is connected to port 1."
::= {dryContact1Adm 1}            

dryContact1AlertStatus  OBJECT-TYPE
    SYNTAX  INTEGER {alert-when-open(0), alert-when-closed(1)}
	ACCESS	read-write
    STATUS  mandatory
    DESCRIPTION
        "Status which generates an alert condition for the dry contact sensor connected to port 1.  
        A value of 0 represents OPEN, and a value of 1 represents CLOSED.  
        This value corresponds directly with the Alert When value entered in the configuration page for this sensor.  
        This object is only applicable if a dry contact sensor is connected to port 1."
::= {dryContact1Adm 2}

-- dry contact 2

dryContact2Status  OBJECT-TYPE
    SYNTAX  INTEGER {open(0), closed(1)}
	ACCESS	read-only
    STATUS  mandatory
    DESCRIPTION
        "Current integer value of the dry contact sensor connected to port 2.  
        A value of 0 represents OPEN, and a value of 1 represents CLOSED.  
        The value corresponds directly with the value displayed on the summary page and the status page for this sensor.  
        This object is only applicable if a dry contact sensor is connected to port 2."
::= {dryContact2 1}

dryContact2Alert  OBJECT-TYPE
    SYNTAX  INTEGER {off(0), on(1)}
	ACCESS	read-only
    STATUS  mandatory
    DESCRIPTION
        "Current alert status of the dry contact sensor connected to port 2.  
         value of 0 indicates that the sensor has not been set to its alert condition, 
         while a value of 1 indicates that it has.  
         This object is only applicable if a dry contact sensor is connected to port 2."
::= {dryContact2 2}

dryContact2Name  OBJECT-TYPE
    SYNTAX  DisplayString
	ACCESS	read-write
    STATUS  mandatory
    DESCRIPTION
        "Current name assigned to the dry contact sensor connected to port 2.  
        This value corresponds directly with the name entered in the configuration page for this sensor.  
        This object is only applicable if a dry contact sensor is connected to port 2."
::= {dryContact2Adm 1}            

dryContact2AlertStatus  OBJECT-TYPE
    SYNTAX  INTEGER {alert-when-open(0), alert-when-closed(1)}
	ACCESS	read-write
    STATUS  mandatory
    DESCRIPTION
        "Status which generates an alert condition for the dry contact sensor connected to port 2.  
        A value of 0 represents OPEN, and a value of 1 represents CLOSED.  
        This value corresponds directly with the Alert When value entered in the configuration page for this sensor.  
        This object is only applicable if a dry contact sensor is connected to port 2."
::= {dryContact2Adm 2}

-- dry contact 3

dryContact3Status  OBJECT-TYPE
    SYNTAX  INTEGER {open(0), closed(1)}
	ACCESS	read-only
    STATUS  mandatory
    DESCRIPTION
        "Current integer value of the dry contact sensor connected to port 3.  
        A value of 0 represents OPEN, and a value of 1 represents CLOSED.  
        The value corresponds directly with the value displayed on the summary page and the status page for this sensor.  
        This object is only applicable if a dry contact sensor is connected to port 3."
::= {dryContact3 1}

dryContact3Alert  OBJECT-TYPE
    SYNTAX  INTEGER {off(0), on(1)}
	ACCESS	read-only
    STATUS  mandatory
    DESCRIPTION
        "Current alert status of the dry contact sensor connected to port 3.  
        A value of 0 indicates that the sensor has not been set to its alert condition, 
        while a value of 1 indicates that it has.  
        This object is only applicable if a dry contact sensor is connected to port 3."
::= {dryContact3 2}

dryContact3Name  OBJECT-TYPE
    SYNTAX  DisplayString
	ACCESS	read-write
    STATUS  mandatory
    DESCRIPTION
        "Current name assigned to the dry contact sensor connected to port 3.  
        This value corresponds directly with the name entered in the configuration page for this sensor.  
        This object is only applicable if a dry contact sensor is connected to port 3."
::= {dryContact3Adm 1}            

dryContact3AlertStatus  OBJECT-TYPE
    SYNTAX  INTEGER {alert-when-open(0), alert-when-closed(1)}
	ACCESS	read-write
    STATUS  mandatory
    DESCRIPTION
        "Status which generates an alert condition for the dry contact sensor connected to port 3.  
        A value of 0 represents OPEN, and a value of 1 represents CLOSED.  
        This value corresponds directly with the Alert When value entered in the configuration page for this sensor.  
        This object is only applicable if a dry contact sensor is connected to port 3."
::= {dryContact3Adm 2}

-- dry contact 4

dryContact4Status  OBJECT-TYPE
    SYNTAX  INTEGER {open(0), closed(1)}
	ACCESS	read-only
    STATUS  mandatory
    DESCRIPTION
        "Current integer value of the dry contact sensor connected to port 4.  
        A value of 0 represents OPEN, and a value of 1 represents CLOSED.  
        The value corresponds directly with the value displayed on the summary page and the status page for this sensor.  
        This object is only applicable if a dry contact sensor is connected to port 4."
::= {dryContact4 1}

dryContact4Alert  OBJECT-TYPE
    SYNTAX  INTEGER {off(0), on(1)}
	ACCESS	read-only
    STATUS  mandatory
    DESCRIPTION
        "Current alert status of the dry contact sensor connected to port 4.  
        A value of 0 indicates that the sensor has not been set to its alert condition, 
        while a value of 1 indicates that it has.  
        This object is only applicable if a dry contact sensor is connected to port 4."
::= {dryContact4 2}

dryContact4Name  OBJECT-TYPE
    SYNTAX  DisplayString
	ACCESS	read-write
    STATUS  mandatory
    DESCRIPTION
        "Current name assigned to the dry contact sensor connected to port 4.  
        This value corresponds directly with the name entered in the configuration page for this sensor.  
        This object is only applicable if a dry contact sensor is connected to port 4."
::= {dryContact4Adm 1}            

dryContact4AlertStatus  OBJECT-TYPE
    SYNTAX  INTEGER {alert-when-open(0), alert-when-closed(1)}
	ACCESS	read-write
    STATUS  mandatory
    DESCRIPTION
        "Status which generates an alert condition for the dry contact sensor connected to port 4.  
        A value of 0 represents OPEN, and a value of 1 represents CLOSED.  
        This value corresponds directly with the Alert When value entered in the configuration page for this sensor.  
        This object is only applicable if a dry contact sensor is connected to port 4."
::= {dryContact4Adm 2}

-- water 1

waterStatus  OBJECT-TYPE
    SYNTAX  INTEGER {open(0), closed(1)}
	ACCESS	read-only
    STATUS  mandatory
    DESCRIPTION
        "Current integer value of the water sensor.  
        A value of 0 represents OPEN, and a value of 1 represents CLOSED. 
        The value corresponds directly with the value displayed on the summary page and the status page for this sensor.  
        This object is only applicable if a water sensor is connected."
::= {waterSensor 1}

waterAlert  OBJECT-TYPE
    SYNTAX  INTEGER {off(0), on(1)}
	ACCESS	read-only
    STATUS  mandatory
    DESCRIPTION
        "Current alert status of the water sensor.  
        A value of 0 indicates that the sensor has not been set to its alert condition, 
        while a value of 1 indicates that it has.  
        This object is only applicable if a water sensor is connected."
::= {waterSensor 2}

waterName  OBJECT-TYPE
    SYNTAX  DisplayString
	ACCESS	read-write
    STATUS  mandatory
    DESCRIPTION
        "Current name assigned to the water sensor.  
        This value corresponds directly with the name entered in the configuration page for this sensor.  
        This object is only applicable if a water sensor is connected."
::= {waterSensorAdm 1}            

waterAlertStatus  OBJECT-TYPE
    SYNTAX  INTEGER {alert-when-open(0), alert-when-closed(1)}
	ACCESS	read-write
    STATUS  mandatory
    DESCRIPTION
        "Status which generates an alert condition for the water sensor.  
        A value of 0 represents OPEN, and a value of 1 represents CLOSED.  
        This value corresponds directly with the Alert When value entered in the configuration page for this sensor.  
        This object is only applicable if a water sensor is connected."
::= {waterSensorAdm 2}

-- host system

sysName OBJECT-TYPE
    SYNTAX  DisplayString
 	ACCESS	read-only
    STATUS  mandatory
    DESCRIPTION
        "System node name.  
        This value corresponds directly with the Node Name field on the General configuration page under the ADMINISTRATION menu."
::= {hostSystem 1}
 
sysLocation OBJECT-TYPE
    SYNTAX  DisplayString
 	ACCESS	read-only
    STATUS  mandatory
     DESCRIPTION
        "System node location.  
        his value corresponds directly with the Node Location field on the General configuration page under the ADMINISTRATION menu."
::= {hostSystem 2}
 
sysIP OBJECT-TYPE
    SYNTAX  DisplayString
 	ACCESS	read-only
    STATUS  mandatory
    DESCRIPTION
        "System IP address.  
        This value corresponds directly with the IP address assigned to the enviromux-MINI on the Network configuration page under the ADMINISTRATION menu."
::= {hostSystem 3}
 
sysMask OBJECT-TYPE
    SYNTAX  DisplayString
 	ACCESS	read-only
    STATUS  mandatory
    DESCRIPTION
        "System Subnet Mask.  
        This value corresponds directly with the Subnet Mask assigned to the enviromux-MINI on the Network configuration page under the ADMINISTRATION menu."
::= {hostSystem 4}
 
sysGateway OBJECT-TYPE
    SYNTAX  DisplayString
 	ACCESS	read-only
    STATUS  mandatory
    DESCRIPTION
        "System Default Gateway.  
        This value corresponds directly with the Default Gateway assigned to the enviromux-MINI on the Network configuration page under the ADMINISTRATION menu."
::= {hostSystem 5}
 
sysDNS OBJECT-TYPE
    SYNTAX  DisplayString
 	ACCESS	read-only
    STATUS  mandatory
    DESCRIPTION
        "System DNS server.  
        This value corresponds directly with the DNS server assigned to the enviromux-MINI on the Network configuration page under the ADMINISTRATION menu."
::= {hostSystem 6}
    
-- traps
temperatureSensor1Trap  NOTIFICATION-TYPE
	STATUS		current
    DESCRIPTION         "Trap for alert from temperature sensor connected to port 1. Received if this sensor is configured to send SNMP traps using the Configuration page, and SNMP is enabled on the Network configuration page under the ADMINISTRATION menu."
	::= {envTraps 1}
	
temperatureSensor2Trap  NOTIFICATION-TYPE
	STATUS		current
    DESCRIPTION         "Trap for alert from temperature sensor connected to port 2. Received if this sensor is configured to send SNMP traps using the Configuration page, and SNMP is enabled on the Network configuration page under the ADMINISTRATION menu."
	::= {envTraps 2}
	
humiditySensor1Trap   	NOTIFICATION-TYPE
	STATUS		current
    DESCRIPTION         "Trap for alert from humidity sensor connected to port 1. Received if this sensor is configured to send SNMP traps using the Configuration page, and SNMP is enabled on the Network configuration page under the ADMINISTRATION menu."
	::= {envTraps 3}
	
humiditySensor2Trap   	NOTIFICATION-TYPE
	STATUS		current
    DESCRIPTION         "Trap for alert from humidity sensor connected to port 2. Received if this sensor is configured to send SNMP traps using the Configuration page, and SNMP is enabled on the Network configuration page under the ADMINISTRATION menu."
	::= {envTraps 4}
	
dryContactSensor1Trap   NOTIFICATION-TYPE
	STATUS		current
    DESCRIPTION         "Trap for alert from dry contact sensor connected to port 1. Received if this sensor is configured to send SNMP traps using the Configuration page, and SNMP is enabled on the Network configuration page under the ADMINISTRATION menu."
	::= {envTraps 5}
	
dryContactSensor2Trap   NOTIFICATION-TYPE
	STATUS		current
    DESCRIPTION         "Trap for alert from dry contact sensor connected to port 2. Received if this sensor is configured to send SNMP traps using the Configuration page, and SNMP is enabled on the Network configuration page under the ADMINISTRATION menu."
	::= {envTraps 6}
	
dryContactSensor3Trap   NOTIFICATION-TYPE
	STATUS		current
    DESCRIPTION         "Trap for alert from dry contact sensor connected to port 3. Received if this sensor is configured to send SNMP traps using the Configuration page, and SNMP is enabled on the Network configuration page under the ADMINISTRATION menu."
	::= {envTraps 7}
	
dryContactSensor4Trap   NOTIFICATION-TYPE
	STATUS		current
    DESCRIPTION         "Trap for alert from dry contact sensor connected to port 4. Received if this sensor is configured to send SNMP traps using the Configuration page, and SNMP is enabled on the Network configuration page under the ADMINISTRATION menu."
	::= {envTraps 8}
	
waterSensor1Trap   	NOTIFICATION-TYPE
	STATUS		current
    DESCRIPTION         "Trap for alert from water sensor. Received if this sensor is configured to send SNMP traps using the Configuration page, and SNMP is enabled on the Network configuration page under the ADMINISTRATION menu."
	::= {envTraps 9}
	
logTrap 		NOTIFICATION-TYPE
	STATUS		current
    DESCRIPTION		"Trap generated when a log entry is created.  Received if log entries are configured to be sent as SNMP traps using the Log Methods page, and SNMP is enabled on the Network configuration page under the ADMINISTRATION menu."
    ::={envTraps 100}
    
overflowTrap		NOTIFICATION-TYPE
	STATUS		current
    DESCRIPTION		"Trap generated when has reached 90% capacity.  Received if log overflow alerts are enabled and are configured to be sent as SNMP traps using the Log Overflow page, and SNMP is enabled on the Network configuration page under the ADMINISTRATION menu."
    ::={envTraps 101}
    
END
