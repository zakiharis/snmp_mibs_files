--    Netasq
--  ContactInfo
--     Customer Support
--     
--     3,  rue Aricheme
--     59650 Villeneuve d'Ascq
--     FRANCE
--    
--     Tel: +33 03 20 61 96 30
--     E-mail: support@netasq.com
--     Http://www.netasq.com

--
--  Last modified date: 10/03/2003
-- 

NETASQ-IF-MIB DEFINITIONS ::= BEGIN
IMPORTS
    MODULE-IDENTITY,  OBJECT-TYPE ,  Integer32,  Counter64 FROM SNMPv2-SMI
    DisplayString               FROM RFC1213-MIB 
	SnmpAdminString 			FROM SNMP-FRAMEWORK-MIB	
    ntqif	                    FROM NETASQ-SMI-MIB;
           
	ntqifTable OBJECT-TYPE
                SYNTAX SEQUENCE OF NtqifEntry
                MAX-ACCESS  not-accessible
                STATUS  current
                DESCRIPTION 
                        "List of interface"
                ::= { ntqif 1 }
				
				
	ntqifEntry OBJECT-TYPE
        SYNTAX  NtqifEntry
        MAX-ACCESS  not-accessible
        STATUS  current
        DESCRIPTION
               "Each entry in the ntqifTable holds a set of information."
        INDEX   { ntqifIndex }
        ::= {  ntqifTable 1 }
		
		NtqifEntry ::=
                SEQUENCE {
					ntqifIndex
						INTEGER, 
					ntqifUserName
						SnmpAdminString, 
					ntqifName
						DisplayString, 
					ntqifAddr			
						DisplayString, 
					ntqifMask
						DisplayString, 
					ntqifType
						DisplayString, 
					ntqifColor
						Integer32, 
					ntqifMacThroughput
						Integer32, 
					ntqifCurThroughput
						Integer32, 
					ntqifMaxThroughput
						Integer32, 	
					ntqifPktAccepted
						Counter64, 
					ntqifPktBlocked
						Counter64, 
					ntqifPktFragmented
						Counter64, 
					ntqifPktTcp
						Counter64, 
					ntqifPktUdp
						Counter64, 
					ntqifPktIcmp
						Counter64, 
					ntqifTotalBytes
						Counter64, 
					ntqifTcpBytes
						Counter64, 
					ntqifUdpBytes
						Counter64, 
					ntqifIcmpBytes
						Counter64, 
					ntqifTcpConn
						Counter64, 
					ntqifUdpConn
						Counter64, 
					ntqifTcpConnCount
						Integer32, 
					ntqifUdpConnCount
						Integer32, 
					ntqifInCurThroughput
						Integer32, 
					ntqifOutCurThroughput
						Integer32, 
					ntqifInMaxThroughput
						Integer32, 
					ntqifOutMaxThroughput
						Integer32, 
					ntqifInTotalBytes
						Counter64, 
					ntqifOutTotalBytes
						Counter64, 
					ntqifInTcpBytes
						Counter64, 
					ntqifOutTcpBytes
						Counter64, 
					ntqifInUdpBytes
						Counter64, 
					ntqifOutUdpBytes
						Counter64, 
					ntqifInIcmpBytes
						Counter64, 
					ntqifOutIcmpBytes
						Counter64
				}

		ntqifIndex OBJECT-TYPE
        SYNTAX  INTEGER
        MAX-ACCESS  read-only
        STATUS  current
        DESCRIPTION
             "A unique value for the table.  Its value
              ranges between 1 and 65535 and may not be contigous. 
              the index has no other meaning but a pure index" 
        ::= {  ntqifEntry 1 }
					
		ntqifUserName OBJECT-TYPE
                SYNTAX SnmpAdminString
                MAX-ACCESS read-only
                STATUS current
                DESCRIPTION
                        "User interface name"
                ::= { ntqifEntry 2 }
				
		ntqifName OBJECT-TYPE
                SYNTAX DisplayString
                MAX-ACCESS read-only
                STATUS current
                DESCRIPTION
                        "System interface name"
                ::= { ntqifEntry 3 }

		ntqifAddr OBJECT-TYPE
                SYNTAX DisplayString
                MAX-ACCESS read-only
                STATUS current
                DESCRIPTION
                        "Interface Adress"
                ::= { ntqifEntry 4 }
												
		ntqifMask OBJECT-TYPE
                SYNTAX DisplayString
                MAX-ACCESS read-only
                STATUS current
                DESCRIPTION
                        "Interface mask"
                ::= { ntqifEntry 5 }

		ntqifType OBJECT-TYPE
                SYNTAX DisplayString
                MAX-ACCESS read-only
                STATUS current
                DESCRIPTION
                        "Interface type"
                ::= { ntqifEntry 6 }				

		ntqifColor OBJECT-TYPE
                SYNTAX Integer32
                MAX-ACCESS read-only
                STATUS current
                DESCRIPTION
                        ""
                ::= { ntqifEntry 7 }
				
		ntqifMacThroughput OBJECT-TYPE
                SYNTAX Integer32
                MAX-ACCESS read-only
                STATUS current
                DESCRIPTION
                        " "
                ::= { ntqifEntry 8 }
				
		ntqifCurThroughput OBJECT-TYPE
                SYNTAX Integer32
                MAX-ACCESS read-only
                STATUS current
                DESCRIPTION
                        "incoming + outgoing current throughput in b/s "
                ::= { ntqifEntry 9 }

		ntqifMaxThroughput OBJECT-TYPE
                SYNTAX Integer32
                MAX-ACCESS read-only
                STATUS current
                DESCRIPTION
                        "incoming + outgoing maximum throughput in b/s"
                ::= { ntqifEntry 10 }	
				
		ntqifPktAccepted OBJECT-TYPE
                SYNTAX Counter64
                MAX-ACCESS read-only
                STATUS current
                DESCRIPTION
                        "number of accepted packets"
                ::= { ntqifEntry 11 }

		ntqifPktBlocked OBJECT-TYPE
                SYNTAX Counter64
                MAX-ACCESS read-only
                STATUS current
                DESCRIPTION
                        "number of packets that have been blocked"
                ::= { ntqifEntry 12 }
				
		ntqifPktFragmented OBJECT-TYPE
                SYNTAX Counter64
                MAX-ACCESS read-only
                STATUS current
                DESCRIPTION
                        "number of fragmented packets"
                ::= { ntqifEntry 13 }
				
		ntqifPktTcp OBJECT-TYPE
                SYNTAX Counter64
                MAX-ACCESS read-only
                STATUS current
                DESCRIPTION
                        "TCP packet forwarded"
                ::= { ntqifEntry 14 }				
				
		ntqifPktUdp OBJECT-TYPE
                SYNTAX Counter64
                MAX-ACCESS read-only
                STATUS current
                DESCRIPTION
                        "UDP packet forwarded"
                ::= { ntqifEntry 15 }
				
		ntqifPktIcmp OBJECT-TYPE
                SYNTAX Counter64
                MAX-ACCESS read-only
                STATUS current
                DESCRIPTION
                        "ICMP packet forwarded"
                ::= { ntqifEntry 16 }				
				
		ntqifTotalBytes OBJECT-TYPE
                SYNTAX Counter64
                MAX-ACCESS read-only
                STATUS current
                DESCRIPTION
                        "data bytes forwarded"
                ::= { ntqifEntry 17 }

		ntqifTcpBytes OBJECT-TYPE
                SYNTAX Counter64
                MAX-ACCESS read-only
                STATUS current
                DESCRIPTION
                        "incoming + outgoing TCP data bytes"
                ::= { ntqifEntry 18 }				
				
		ntqifUdpBytes OBJECT-TYPE
                SYNTAX Counter64
                MAX-ACCESS read-only
                STATUS current
                DESCRIPTION
                        "incoming + outgoing UDP data bytes"
                ::= { ntqifEntry 19 }				
				
		ntqifIcmpBytes OBJECT-TYPE
                SYNTAX Counter64
                MAX-ACCESS read-only
                STATUS current
                DESCRIPTION
                        "incoming + outgoing ICMP data bytes"
                ::= { ntqifEntry 20 }

		ntqifTcpConn OBJECT-TYPE
                SYNTAX Counter64
                MAX-ACCESS read-only
                STATUS current
                DESCRIPTION
                        "TCP connection established"
                ::= { ntqifEntry 21 }

		ntqifUdpConn OBJECT-TYPE
                SYNTAX Counter64
                MAX-ACCESS read-only
                STATUS current
                DESCRIPTION
                        "UDP connection established"
                ::= { ntqifEntry 22 }

		ntqifTcpConnCount OBJECT-TYPE
                SYNTAX Integer32
                MAX-ACCESS read-only
                STATUS current
                DESCRIPTION
                        "current TCP connection count"
                ::= { ntqifEntry 23 }
		
		ntqifUdpConnCount OBJECT-TYPE
                SYNTAX Integer32
                MAX-ACCESS read-only
                STATUS current
                DESCRIPTION
                        "current UCP connection count"
                ::= { ntqifEntry 24 }
        
        ntqifInCurThroughput OBJECT-TYPE
                SYNTAX Integer32
                MAX-ACCESS read-only
                STATUS current
                DESCRIPTION
                        "Incoming Current throughput in b/s "
                ::= { ntqifEntry 25 }
        
        ntqifOutCurThroughput OBJECT-TYPE
                SYNTAX Integer32
                MAX-ACCESS read-only
                STATUS current
                DESCRIPTION
                        "Outgoing Current throughput in b/s "
                ::= { ntqifEntry 26 }

		ntqifInMaxThroughput OBJECT-TYPE
                SYNTAX Integer32
                MAX-ACCESS read-only
                STATUS current
                DESCRIPTION
                        "Incoming maximum throughput in b/s"
                ::= { ntqifEntry 27 }
                
		ntqifOutMaxThroughput OBJECT-TYPE
                SYNTAX Integer32
                MAX-ACCESS read-only
                STATUS current
                DESCRIPTION
                        "Outgoing maximum throughput in b/s"
                ::= { ntqifEntry 28 }

		ntqifInTotalBytes OBJECT-TYPE
                SYNTAX Counter64
                MAX-ACCESS read-only
                STATUS current
                DESCRIPTION
                        "Incoming data bytes"
                ::= { ntqifEntry 29 }
		
		ntqifOutTotalBytes OBJECT-TYPE
                SYNTAX Counter64
                MAX-ACCESS read-only
                STATUS current
                DESCRIPTION
                        "Outgoing data bytes"
                ::= { ntqifEntry 30 }

		ntqifInTcpBytes OBJECT-TYPE
                SYNTAX Counter64
                MAX-ACCESS read-only
                STATUS current
                DESCRIPTION
                        "Incoming TCP data bytes"
                ::= { ntqifEntry 31 }	

		ntqifOutTcpBytes OBJECT-TYPE
                SYNTAX Counter64
                MAX-ACCESS read-only
                STATUS current
                DESCRIPTION
                        "Outgoing TCP data bytes"
                ::= { ntqifEntry 32 }			
				
		ntqifInUdpBytes OBJECT-TYPE
                SYNTAX Counter64
                MAX-ACCESS read-only
                STATUS current
                DESCRIPTION
                        "Incoming UDP data bytes"
                ::= { ntqifEntry 33 }				
		
		ntqifOutUdpBytes OBJECT-TYPE
                SYNTAX Counter64
                MAX-ACCESS read-only
                STATUS current
                DESCRIPTION
                        "Outgoing UDP data bytes"
                ::= { ntqifEntry 34 }
                
		ntqifInIcmpBytes OBJECT-TYPE
                SYNTAX Counter64
                MAX-ACCESS read-only
                STATUS current
                DESCRIPTION
                        "Incoming ICMP data bytes"
                ::= { ntqifEntry 35 }

		ntqifIOutIcmpBytes OBJECT-TYPE
                SYNTAX Counter64
                MAX-ACCESS read-only
                STATUS current
                DESCRIPTION
                        "Outgoing ICMP data bytes"
                ::= { ntqifEntry 36 }

END
