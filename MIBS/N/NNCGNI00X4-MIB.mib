-- @(#)Positions.mib	9.1 10/16/98
--------------------------------------------------------------------------------
-- file: Positions.mib
--
-- contents:
--	This file contains the Newbridge MIB extensions for positions 
--	(sometimes referred to as slots) in a standalone network element.
--
-- history:
--	0.1 / 92.08.25 / J. Watt / Creation
--	0.2 / 93.04.04 / J. Watt / Removed enum for position index (varies from
--				   product to product)
--	0.3 / 93.05.12 / G. Celmainis / change nncExtPositionAdminStatus to R-W
--
-- Copyright 1992 to 1993 Newbridge Networks Corporation.  All Rights Reserved.
--------------------------------------------------------------------------------
NNCGNI00X4-MIB	DEFINITIONS ::= BEGIN

	IMPORTS	
		nncExtPosition
			FROM NNCGNI00X1-SMI
		
		OBJECT-TYPE
			FROM RFC-1212
			
		DisplayString
			FROM RFC1213-MIB;
			
			
	PositionIndex	::= INTEGER (1..'7fffffff'h)
	
	PositionCardType ::= INTEGER { noCard(1), ctlCard(46), x21Card(108), 
				       v24Card(109), v35Card(110), 
				       ethernetCard(111), 
				       hubCard(120), t1Card(6), e1Card(5) }
					      
	PositionModuleType ::= INTEGER { noModule(1), thinModule(24), 
					 tpModule(25), auiModule(26),
					 nullAUIModule(27), foirlModule(28),
					 hubModule(29) }
	
	PositionCardId 	::= INTEGER { ctlCardId(0), x21CardId(2), v24CardId(4), 
				      v35CardId(6), ethernetCardId(1), 
				      e1CoaxCardId(12), t1DsxCardId(8), 
				      t1CsuCardId(10), e1TpCardId(24), 
				      hubCardId(28) }

	PositionModuleId::= INTEGER { thinModId(1), hubModId(2), tpModId(4), 
				      foirlModId(5),
				      nullAUIModId(6), auiModId(0) }
					      
	PositionVariantId::= INTEGER (0..255)
	
	RevisionNumber	::= INTEGER (0..255)



	PositionAdminStatus ::= INTEGER { inUse(1), busiedOut(2), reset(3) }
	
	PositionOperStatus ::= INTEGER { empty(1), ok(2), fault-on-module(3), 
                                  module-dead(4), unknown-module-type(5), 
                                  module-type-mismatch(6), 
                                  sub-module-type-mismatch(7), 
                                  wrong-firmware(9), wrong-variant(12)}
				  
			
	nncExtPositionMaxPossible	OBJECT-TYPE
		SYNTAX	INTEGER (1..255)
		ACCESS	read-only
		STATUS	mandatory
		DESCRIPTION
			"The maximum possible number of positions in the unit.
			 Positions are numbered from 1 to the value of this
			 object."
		::= { nncExtPosition 1}
				
		
	nncExtPositionTable	OBJECT-TYPE
		SYNTAX	SEQUENCE OF NncExtPositionEntry
		ACCESS	not-accessible
		STATUS	mandatory
		DESCRIPTION
			"Configuration and status information for positions and
			 their contents."
		::= { nncExtPosition 2}
		
	
	nncExtPositionEntry OBJECT-TYPE
		SYNTAX	NncExtPositionEntry
		ACCESS	not-accessible
		STATUS	mandatory
		DESCRIPTION
			"Configuration and status information for positions and
			 their contents."
		INDEX { nncExtPositionIndex }
		::= { nncExtPositionTable 1}
		
		
	NncExtPositionEntry 
		::= SEQUENCE {
			nncExtPositionIndex
				PositionIndex,
			nncExtPositionProgCard
				PositionCardType,
			nncExtPositionProgModule
				PositionModuleType,
			nncExtPositionCurrentCard
				PositionCardType,
			nncExtPositionCurrentModule
				PositionModuleType,
			nncExtPositionOperStatus
				PositionOperStatus,
			nncExtPositionAdminStatus
				PositionAdminStatus,
			nncExtPositionCardId
				PositionCardId,
			nncExtPositionModuleId
				PositionModuleId,
			nncExtPositionVariantId
				PositionVariantId,
			nncExtPositionHardwareRevision
				RevisionNumber,
			nncExtPositionFirmwareRevision
				RevisionNumber,
			nncExtPositionUIName
				DisplayString,
			nncExtPositionName
				DisplayString
		}
		
		
	nncExtPositionIndex	OBJECT-TYPE
		SYNTAX	PositionIndex
		ACCESS	read-only
		STATUS	mandatory
DESCRIPTION ""

		::= { nncExtPositionEntry 1}
		
		
	nncExtPositionProgCard	OBJECT-TYPE
		SYNTAX	INTEGER { noCard(1), ctlCard(46), x21Card(108), 
				       v24Card(109), v35Card(110), 
				       ethernetCard(111), 
				       hubCard(120), t1Card(6), e1Card(5) }
		ACCESS	read-write
		STATUS	mandatory
DESCRIPTION ""

		::= { nncExtPositionEntry 2}
			 

	nncExtPositionProgModule	OBJECT-TYPE
		SYNTAX	INTEGER { noModule(1), thinModule(24), 
					 tpModule(25), auiModule(26),
					 nullAUIModule(27), foirlModule(28),
					 hubModule(29) }
		ACCESS	read-write
		STATUS	mandatory
DESCRIPTION ""

		::= { nncExtPositionEntry 3}
		
		
	nncExtPositionCurrentCard	OBJECT-TYPE
		SYNTAX	INTEGER { noCard(1), ctlCard(46), x21Card(108), 
				       v24Card(109), v35Card(110), 
				       ethernetCard(111), 
				       hubCard(120), t1Card(6), e1Card(5) }
		ACCESS	read-only
		STATUS	mandatory
DESCRIPTION ""

		::= { nncExtPositionEntry 4}
			 

	nncExtPositionCurrentModule	OBJECT-TYPE
		SYNTAX	INTEGER { noModule(1), thinModule(24), 
					 tpModule(25), auiModule(26),
					 nullAUIModule(27), foirlModule(28),
					 hubModule(29) }
		ACCESS	read-only
		STATUS	mandatory
DESCRIPTION ""

		::= { nncExtPositionEntry 5}
		

	nncExtPositionOperStatus	OBJECT-TYPE
		SYNTAX	INTEGER { empty(1), ok(2), fault-on-module(3), 
                                  module-dead(4), unknown-module-type(5), 
                                  module-type-mismatch(6), 
                                  sub-module-type-mismatch(7), 
                                  wrong-firmware(9), wrong-variant(12)}
		ACCESS	read-only
		STATUS	mandatory
DESCRIPTION ""

		::= { nncExtPositionEntry 6}
		
		
	nncExtPositionAdminStatus	OBJECT-TYPE
		SYNTAX	INTEGER { inUse(1), busiedOut(2), reset(3) }
		ACCESS	read-write
		STATUS	mandatory
DESCRIPTION ""

		::= { nncExtPositionEntry 7}
		
		
	nncExtPositionCardId	OBJECT-TYPE
		SYNTAX	INTEGER { ctlCardId(0), x21CardId(2), v24CardId(4), 
				      v35CardId(6), ethernetCardId(1), 
				      e1CoaxCardId(12), t1DsxCardId(8), 
				      t1CsuCardId(10), e1TpCardId(24), 
				      hubCardId(28) }
		ACCESS	read-only
		STATUS	mandatory
DESCRIPTION ""

		::= { nncExtPositionEntry 8}
		
		
	nncExtPositionModuleId	OBJECT-TYPE
		SYNTAX	INTEGER { thinModId(1), hubModId(2), tpModId(4), 
				      foirlModId(5),
				      nullAUIModId(6), auiModId(0) }
		ACCESS	read-only
		STATUS	mandatory
DESCRIPTION ""

		::= { nncExtPositionEntry 9}


	nncExtPositionVariantId	OBJECT-TYPE
		SYNTAX	PositionVariantId
		ACCESS	read-only
		STATUS	mandatory
DESCRIPTION ""

		::= { nncExtPositionEntry 10}
		
		
	nncExtPositionHardwareRevision	OBJECT-TYPE
		SYNTAX	RevisionNumber
		ACCESS	read-only
		STATUS	mandatory
DESCRIPTION ""

		::= { nncExtPositionEntry 11}


	nncExtPositionFirmwareRevision	OBJECT-TYPE
		SYNTAX	RevisionNumber
		ACCESS	read-only
		STATUS	mandatory
DESCRIPTION ""

		::= { nncExtPositionEntry 12}
		
		
	nncExtPositionUIName	OBJECT-TYPE
		SYNTAX	DisplayString (SIZE(2..2))
		ACCESS	read-only
		STATUS	mandatory
DESCRIPTION ""

		::= { nncExtPositionEntry 13}
		

	nncExtPositionName	OBJECT-TYPE
		SYNTAX	DisplayString (SIZE(1..8))
		ACCESS	read-write
		STATUS	mandatory
DESCRIPTION ""

		::= { nncExtPositionEntry 14}
		
			
	nncExtPositionBackplaneIdAndRev	OBJECT-TYPE
		SYNTAX	INTEGER (0..255)
		ACCESS  read-only
		STATUS  mandatory
DESCRIPTION ""

		::= { nncExtPosition 3 }
		
		
	nncExtPositionDisplayIdAndRev	OBJECT-TYPE
		SYNTAX	INTEGER (0..255)
		ACCESS  read-only
		STATUS  mandatory
DESCRIPTION ""

		::= { nncExtPosition 4 }


END
