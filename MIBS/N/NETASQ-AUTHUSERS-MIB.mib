-- MODULE-IDENTITY
--  OrgName
--    Netasq
--  ContactInfo
--     Customer Support
--     
--     3,  rue Aricheme
--     59650 Villeneuve d'Ascq
--     FRANCE
--    
--     Tel: +33 03 20 61 96 30
--     E-mail: support@netasq.com
--     Http://www.netasq.com

--
--  Last modified date: 10/03/2003
--    

NETASQ-AUTHUSERS-MIB DEFINITIONS ::= BEGIN
IMPORTS
    MODULE-IDENTITY,  OBJECT-TYPE ,  Integer32 FROM SNMPv2-SMI
    DisplayString                 FROM RFC1213-MIB 
	SnmpAdminString 			FROM SNMP-FRAMEWORK-MIB
    ntqUsers                      FROM NETASQ-SMI-MIB;
           
        ntqAuthUsersTable OBJECT-TYPE
                SYNTAX SEQUENCE OF NtqAuthUsersEntry
                MAX-ACCESS  not-accessible
                STATUS  current
                DESCRIPTION 
                        "List of authentified users"
                ::= { ntqUsers 1 }
                
        ntqAuthUsersEntry OBJECT-TYPE
        SYNTAX  NtqAuthUsersEntry
        MAX-ACCESS  not-accessible
        STATUS  current
        DESCRIPTION
               "Each entry in the ntqAuthUsersTable holds a set of information (IP,  username,  and timeout)."
        INDEX   { ntqAuthUsersIPAddr }
        ::= {  ntqAuthUsersTable 1 }
        
        NtqAuthUsersEntry ::=
                SEQUENCE {
                        ntqAuthUsersIPAddr
                                DisplayString, 
                        ntqAuthUsersTimeOut
                                Integer32, 
						ntqAuthUsersName
                                SnmpAdminString
                }
                
        ntqAuthUsersIPAddr OBJECT-TYPE
                SYNTAX DisplayString
                MAX-ACCESS read-only
                STATUS current
                DESCRIPTION
                        "IP Adress of the authentificated user"
                ::= { ntqAuthUsersEntry 1 }
                
        ntqAuthUsersTimeOut OBJECT-TYPE
                SYNTAX Integer32
                MAX-ACCESS read-only
                STATUS current
                DESCRIPTION
                        "Timeout"
                ::= { ntqAuthUsersEntry 2 }
		ntqAuthUsersName OBJECT-TYPE
                SYNTAX SnmpAdminString
                MAX-ACCESS read-only
                STATUS current
                DESCRIPTION
                        "Username"
                ::= { ntqAuthUsersEntry 3 }
 END
