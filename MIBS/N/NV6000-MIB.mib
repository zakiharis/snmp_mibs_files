NV6000-MIB DEFINITIONS ::= BEGIN

IMPORTS
          enterprises, Counter, Gauge
                  FROM RFC1155-SMI
          OBJECT-TYPE
                  FROM RFC-1212
          DisplayString
                  FROM RFC1213-MIB;


-- High-level nodes under enterprises
ibm                   OBJECT IDENTIFIER ::= { enterprises 2 }
 ibmProd              OBJECT IDENTIFIER ::= { ibm 6 }
  netView6000SubAgent OBJECT IDENTIFIER ::= { ibmProd 4 }

--  This MIB module uses the extended OBJECT-TYPE macro as
--      defined in RFC 1212.
--
--      OBJECT-TYPE
--              SYNTAX
--              ACCESS
--              STATUS
--              DESCRIPTION
--              INDEX
--              ::=

--
--  The NV6000 Subtree...
--

-- These NV6000 Extension groups follow the structure of MIB-II

nv6saTrap                       OBJECT IDENTIFIER ::= { netView6000SubAgent 2 }
nv6saIcmp                       OBJECT IDENTIFIER ::= { netView6000SubAgent 3 }
nv6saFileSystem                 OBJECT IDENTIFIER ::= { netView6000SubAgent 4 }
nv6saComputerSystem             OBJECT IDENTIFIER ::= { netView6000SubAgent 5 }

--
-- NV6000 SNMP Extensions
--              Objects containing information about enterprise
--              specific SNMP traps generated by this node.

nv6saTrapNum OBJECT-TYPE
        SYNTAX  Counter
        ACCESS  read-only
        STATUS  optional
        DESCRIPTION
                        "Number of IBM enterprise specific traps
                        generated by this node."
        ::= { nv6saTrap 1 }

nv6saTrapThrottleCount OBJECT-TYPE
        SYNTAX  Counter
        ACCESS  read-only
        STATUS  optional
        DESCRIPTION
                        "Number of traps throttled since last trap."
        ::= { nv6saTrap 2 }

nv6saTrapThrottleId OBJECT-TYPE
        SYNTAX  INTEGER
        ACCESS  read-only
        STATUS  optional
        DESCRIPTION
                        "Trap ID of throttled traps. All throttled traps counted
                        by nv6saTrapThrottleCount have this ID."
        ::= { nv6saTrap 3 }

nv6saTrapThrottleTime OBJECT-TYPE
        SYNTAX  INTEGER
        ACCESS  read-only
        STATUS  optional
        DESCRIPTION
                "Number of seconds which must separate consecutive traps
                with identical ID and resource name in order to not
                throttle them.  If the value of this object is 0, then
                trap throttling is inactive."
        ::= { nv6saTrap 4 }

nv6saIcmpEchoReq   OBJECT-TYPE
        SYNTAX  INTEGER
        ACCESS  read-only
        STATUS  mandatory
        DESCRIPTION
                "The number of milliseconds it takes for an icmp echo
                request to respond.  nv6saIcmpEchoReq is -1 if there is
                an internal error, -2 if the echo request timed out, -3
                if the echo reply is not the correct reply, -4 if the
                packet size is too large, and -5 if the timeout is invalid.

                   To request the icmp response time for ip address
                a.b.c.d with a timeout of e and a packet size of f,
                send a GET request for nv6saIcmpEchoReq.f.e.a.b.c.d.
                For example, suppose one wanted to find out the
                number of milliseconds it took to ping 15.2.112.113,
                with a timeout of 8, and packet size of 75.
                Accordingly, GET of nv6saIcmpEchoReq.75.8.15.2.112.113
                would return the number of milliseconds."
        ::= { nv6saIcmp 1 }

-- The FileSystem Group

nv6saFileSystemMounted OBJECT-TYPE
        SYNTAX  Gauge
        ACCESS  read-only
        STATUS  optional
        DESCRIPTION
                "The number of file systems mounted."
        ::= { nv6saFileSystem 1 }

-- The FileSystem Table
  -- (Commented this Table out because it is not currently implemented
  -- and smicng had problems with it )


-- nv6saFileSystemTable OBJECT-TYPE
        -- SYNTAX  SEQUENCE OF FileSystemEntry
        -- ACCESS  not-accessible
        -- STATUS  optional
        -- DESCRIPTION
                -- "File system table."
        -- ::= { nv6saFileSystem 2 }
--
-- nv6saFileSystemEntry OBJECT-TYPE
        -- SYNTAX  FileSystemEntry
        -- ACCESS  not-accessible
        -- STATUS  optional
        -- DESCRIPTION
                -- "Each entry contains objects for a particular file
                -- system."
        -- ::= { nv6saFileSystemTable 1 }
--
-- FileSystemEntry ::= SEQUENCE {
    -- nv6saFileSystemName
        -- OCTET STRING,
    -- nv6saFileSystemBlock
        -- INTEGER,
    -- nv6saFileSystemBfree
        -- INTEGER,
    -- nv6saFileSystemBavail
        -- INTEGER,
    -- nv6saFileSystemBsize
        -- INTEGER,
    -- nv6saFileSystemFiles
        -- INTEGER,
    -- nv6saFileSystemFfree
        -- INTEGER,
    -- nv6saFileSystemDir
        -- OCTET STRING
-- }
--
-- nv6saFileSystemName OBJECT-TYPE
        -- SYNTAX  OCTET STRING
        -- ACCESS  read-only
        -- STATUS  optional
        -- DESCRIPTION
                -- "Name of mounted file system."
        -- ::= { nv6saFileSystemEntry 1 }
--
-- nv6saFileSystemBlock OBJECT-TYPE
        -- SYNTAX  INTEGER
        -- ACCESS  read-only
        -- STATUS  optional
        -- DESCRIPTION
                -- "Total blocks in file system."
        -- ::= { nv6saFileSystemEntry 2 }
--
-- nv6saFileSystemBfree OBJECT-TYPE
        -- SYNTAX  INTEGER
        -- ACCESS  read-only
        -- STATUS  optional
        -- DESCRIPTION
                -- "Free blocks in file system."
        -- ::= { nv6saFileSystemEntry 3 }
--
-- nv6saFileSystemBavail OBJECT-TYPE
        -- SYNTAX  INTEGER
        -- ACCESS  read-only
        -- STATUS  optional
        -- DESCRIPTION
                -- "Free blocks avail to non-superuser."
        -- ::= { nv6saFileSystemEntry 4 }
--
-- nv6saFileSystemBsize OBJECT-TYPE
        -- SYNTAX  INTEGER
        -- ACCESS  read-only
        -- STATUS  optional
        -- DESCRIPTION
                -- "Fundamental file system block size."
        -- ::= { nv6saFileSystemEntry 5 }
--
-- nv6saFileSystemFiles OBJECT-TYPE
        -- SYNTAX  INTEGER
        -- ACCESS  read-only
        -- STATUS  optional
        -- DESCRIPTION
                -- "Total file nodes in file system."
        -- ::= { nv6saFileSystemEntry 6 }
--
-- nv6saFileSystemFfree OBJECT-TYPE
        -- SYNTAX  INTEGER
        -- ACCESS  read-only
        -- STATUS  optional
        -- DESCRIPTION
                -- "Free file nodes in file system."
        -- ::= { nv6saFileSystemEntry 7 }
--
-- nv6saFileSystemDir OBJECT-TYPE
        -- SYNTAX  OCTET STRING
        -- ACCESS  read-only
        -- STATUS  optional
        -- DESCRIPTION
                -- "File system path prefix."
        -- ::= { nv6saFileSystemEntry 8 }

-- the ComputerSystem Group

nv6saComputerSystemLoad OBJECT-TYPE
        SYNTAX  Gauge
        ACCESS  read-only
        STATUS  mandatory
        DESCRIPTION
                "The cpu load as a percentage i.e. 25% is 2500."
        ::= { nv6saComputerSystem 1 }

-- Local Variables:
-- tab-width: 4
-- case-fold-search: nil
-- End:

END
