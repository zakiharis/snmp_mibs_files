--  =======================================================================
--  File        : nbasesw.mib
--  Description : Private MIB for NBase Switch Communications
--                Ethernet Switches
--  By          : Sergiu Rotenstein
--  Version     : $Revision:   1.7  $
--  Date        : $Date:   21 Mar 1997 17:59:44  $
--  =======================================================================
--
--
-- Copyright (c) 1995 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- products. NBase grants vendor, end-users, and other interested
-- parties a non-exclusive license to use this specification in
-- connection with the management of NBase's products.
--
-- This specification is supplied "AS IS," and NBase makes no
-- warranty, either express or implied, as to the use, operation,
-- condition, or performance of the specification.
--
-- Copyright text courtesy of S. Rotenstein.
--
-- If you have any questions about this MIB, please call NBase
-- Technical Support Center at 1-800-858-7815 from inside USA or
-- 1-818-773-0900 from outside USA.
--
--
-- NBase retains the right to change this MIB without notification.
--
--
NBASE-G1-MIB DEFINITIONS ::= BEGIN

        IMPORTS
                enterprises,
                IpAddress,
--              NetworkAdress,
		TimeTicks,
                Counter                       FROM RFC1155-SMI

                OBJECT-TYPE                   FROM RFC-1212
                DisplayString                 FROM RFC1213-MIB;
--              TRAP-TYPE                     FROM RFC-1215;

          MacAddress ::=  OCTET STRING(SIZE(6))

-- ************************************************************
-- NBase Object Identifier Definition
-- ************************************************************

nbase           OBJECT IDENTIFIER ::= { enterprises 629 }
nbSwitchG1      OBJECT IDENTIFIER ::= { nbase 1 }

-- ************************************************************
-- GROUPS in NBASE-MEGASW-MIB
--
--  The following groups are generally defined for all the NBase
--  switching products:
--
--    - nbsProduct: contains the definitions of the different products
--                  sysObjectId
--
--    - nbSys     : contains the general switch system object
--                  definitions that are not specific to a
--                  certain product, but to all the NBase
--                  switching products belonging to the first generation.
--
--    - nbsPortCfg: contains the port configuration and status related
--                  object definitions, common to all the NBase
--                  switching products belonging to the first generation.
--
--    - nbsEtherInfo :
--                  contains the Ethernet Information, specific to
--                  all the NBase switching products belonging to the
--                  first generation, that are not provided by the
--                  Ethernet Mib.
--
--    - nbsSwitchPerf:
--                  contains the Performance Statistics, common to
--                  all the NBase switching products belonging to the
--                  first generation, that are not provided by the
--                  Bridge Mib and other standard MIBs
--
--    - nbsTraps:
--                  contains the specific NBase traps, common to
--                  all the NBase switching products belonging to
--                  first generation.
--
--  The following groups are generally defined for specific NBase
--  switching products:
--
--    - nbsMiniSwDb:
--                  contains the Switching Data Base Objects specific
--                  to the NH204/MiniSwitch product.
--
--    - nbsMegaSwDb:
--                  contains the Switching Data Base Objects specific
--                  to the MegaSwitch family of products.
--
-- *******************************************************************

nbsProducts     OBJECT IDENTIFIER ::= { nbSwitchG1 1 }
nbsSys          OBJECT IDENTIFIER ::= { nbSwitchG1 2 }
nbsSysSnmpCfg   OBJECT IDENTIFIER ::= { nbSwitchG1 3 }
nbsPortCfg      OBJECT IDENTIFIER ::= { nbSwitchG1 4 }
nbsEtherInfo    OBJECT IDENTIFIER ::= { nbSwitchG1 5 }
nbsSwitchPerf   OBJECT IDENTIFIER ::= { nbSwitchG1 6 }
nbsTraps        OBJECT IDENTIFIER ::= { nbSwitchG1 7 }
nbsMiniSwDb     OBJECT IDENTIFIER ::= { nbSwitchG1 8 }
nbsMegaSwDb     OBJECT IDENTIFIER ::= { nbSwitchG1 9 }
--
-- ************************************************************
-- PRODUCTS in NBASE-MIB - define the sysObjectId
--
-- Three products are defined :
--      - miniSwicth    - defining the sysObjectId for NH204-AT
--      - megaSwitch20x - defining the sysObjectId for NH208-AT
--                        and  for NH215-AT
--      - megaFastSwitch- defining the sysObjectId for NH2007
--      - megaSwitchII  - defining the sysObjectId for NH2012
-- *************************************************************

miniSwitch      OBJECT IDENTIFIER ::= { nbsProducts 1 }      --
megaSwitch208   OBJECT IDENTIFIER ::= { nbsProducts 2 }      --
megaSwitch215   OBJECT IDENTIFIER ::= { nbsProducts 3 }      --
megaFastSwitch  OBJECT IDENTIFIER ::= { nbsProducts 4 }      --
megaSwitchII    OBJECT IDENTIFIER ::= { nbsProducts 5 }      --
megaSwitch2015  OBJECT IDENTIFIER ::= { nbsProducts 6 }      --
megaSwitch2048  OBJECT IDENTIFIER ::= { nbsProducts 7 }      --

-- *************************************************************
-- Objects in the NBase System Group
--
-- These objects are general for all the NBase Ethernet Switches
-- *************************************************************


nbsSysFwVers    OBJECT-TYPE
        SYNTAX  DisplayString
        ACCESS  read-only
        STATUS  mandatory
        DESCRIPTION
                "The SNMP Agent firmware version in the form Vmajor.minor"

        ::= { nbsSys 1 }

nbsSysPortsNumber    OBJECT-TYPE
        SYNTAX  INTEGER
        ACCESS  read-only
        STATUS  mandatory
        DESCRIPTION
                "Number of Switching Ports provided by this system."

        ::= { nbsSys 2 }

nbsSysRestart       OBJECT-TYPE
        SYNTAX  INTEGER {
                running    (1),        -- system is running
                coldRestart(2),        -- execute a cold/hardware restart
                warmRestart(3)         -- execute a warm/software restart
        }
        ACCESS  read-write
        STATUS  mandatory
        DESCRIPTION
                " This object is used to reset the system.
                  Writing a coldRestart(2), causes the switching engine
                  as well as the SNMP Agent CPU to be hardware resetted,
                  similar to a power-on cycle.
                  Writing a warmRestart(3), causes only a restart of the
                  the SNMP Agent CPU operative software. The switching
                  engine continues to operate. Nevertheless, it is
                  reinitialized to the parameters value stored in the
                  system NVRAM. These paramters may be different from
                  those of the previous session."

        ::= { nbsSys 3 }

nbsSysNumRestarts    OBJECT-TYPE
        SYNTAX  Counter
        ACCESS  read-only
        STATUS  mandatory
        DESCRIPTION
                "Number of warmRestarts executed by the system, since the
                 last coldRestart or power-on cycle..
                 A warmRestart may be initiated by:
                 - writing a warmRestart value in the nbsSysRestart object.
                 - a warmRestart command from the Administrative Interface.
                 - the SNMP Agent Firmware due to certain conditions."

        ::= { nbsSys 4 }

nbsSysLastError OBJECT-TYPE
        SYNTAX  INTEGER{
		noError	(1)	-- no fatal error occured

	}
        ACCESS  read-only
        STATUS  mandatory
        DESCRIPTION
                "The error code of the last fatal error that generated a
		 warm reset."

        ::= { nbsSys 5 }

nbsSysErrUptime    OBJECT-TYPE
	SYNTAX  TimeTicks
        ACCESS  read-only
        STATUS  mandatory
        DESCRIPTION
                "The time (in hundredths of a second) since the last
		 cold reset/power cycle when a fatal error occured.
		 This variable shows the system uptime from the last
		 cold reset/power on cycle, unless a fatal error occured."

        ::= { nbsSys 6 }

nbsSysSwitchDBSize    OBJECT-TYPE
        SYNTAX  INTEGER
        ACCESS  read-only
        STATUS  mandatory
        DESCRIPTION
                "The maximum size of the Switching Data Base. It indicates
                 how many MAC Addresses may be stored in the system
                 Switching Data Base. The possible values are 1024 or 2048."

        ::= { nbsSys 7 }

nbsSysSetNvramDefaults    OBJECT-TYPE
        SYNTAX  INTEGER {
                setDefaults (1)
        }
        ACCESS  read-write
        STATUS  mandatory
        DESCRIPTION
                "Writing the value setDefaults to this objects will restore
                 the defaults in the NVRAM data base. These values will take
                 effect after a system reset"

        ::= { nbsSys 8 }

nbsSysResetSwitchStats    OBJECT-TYPE
        SYNTAX  INTEGER {
                resetStats (1)
        }
        ACCESS  read-write
        STATUS  mandatory
        DESCRIPTION
                "Writing the value resetStats to this object will reset all
                 the switching counters, for all the ports including the
                 the Ethernet, switching and the SNMP Agent computed
                 statistics"

        ::= { nbsSys 9 }

nbsSysStpEnable    OBJECT-TYPE
        SYNTAX  INTEGER {
                stpDisable(1),
                stpEnable (2)
        }
        ACCESS  read-write
        STATUS  mandatory
        DESCRIPTION
		"Writing one of the allowed values to this object will
		modify the Administrative state of the Spanning Tree.
		This value will take effect in the next session after a
		system reset.

		Writing the value StpDisable to this object will disable
		the Spanning Tree Engine.
		Writing the value StpEnable to this object will enable
		the Spanning Tree Engine."

        ::= { nbsSys 10 }

nbsSysRunStpState    OBJECT-TYPE
        SYNTAX  INTEGER {
                stpDisable(1),
                stpEnable (2)
        }
        ACCESS  read-only
        STATUS  mandatory
        DESCRIPTION
		"Running state of the Spanning Tree Engine."

        ::= { nbsSys 11 }
--
-- Selftest Level - in system group
--
nbsSysSelftestLevel    OBJECT-TYPE
        SYNTAX  INTEGER {
                ststNone(1),
                ststShort(2),
                ststLong(3),
                ststDiagnostics(4)
        }
        ACCESS  read-write
        STATUS  mandatory
        DESCRIPTION
		"NVRAM based level of the system selftest.
		 It is supported only by the MegaSwitch II family.
	         The values are :
		   ststNone - meaning that no selftest will be executed
			      upon boot-up
		   ststShort- meaning that a short  selftest, of approx 10-20
			      seconds will be executed upon boot-up
		   ststLong - meaning that a long/extensive selftest will
			      be executed upon boot-up
		   ststDiagnostics - meaning that upon boot-up the diagnostics
			      mode is entered. In this mode it is possible to
			      interactively select the test or the group of tests
	                      that will be executed. This value may not be set through
	                      an SNMP set command."

        ::= { nbsSys 13 }


-- ******************************************************************
-- The nbsSysFrmGen Subgoup
--
-- Implementation of the nbsSysFrmGen subgroup is optional for
-- Nbase products that do not implement a frame generator - like the
-- NH204.
--
-- The nbsSysFrmGen Group is used by a station to initiate an Ethernet
-- traffic flow from this agent to the address denoted by nbsSysFrmGenDa.
--
-- To start a Frame Generator session, you must set the objects:
-- nbsSysFrmGenDa, nbsSysFrmGenSa, nbsSysFrmGenPktLen, nbsSysFrmGenPktFill,
-- nbsSysFrmGenPktRate, nbsSysFrmGenDestMap & nbsSysFrmGenPktNum.
-- The defaults are:
--       nbsSysFrmGenDa = loopback address, nbsSysFrmGenSa = device address,
--       nbsSysFrmGenPktLen = 60, nbsSysFrmGenPktFill = 0,
--       nbsSysFrmGenPktRate = 1, nbsSysFrmGenPktNum = 0 ( forever )
--
-- Note: Only one Frame Generator session can be activated at a time.
--
-- *************************************************************************

nbsSysFrmGen    OBJECT IDENTIFIER  ::= { nbsSys 12 }

nbsSysFrmGenSession    OBJECT-TYPE
        SYNTAX  INTEGER{
                idleFG  (1),   -- The Frame Generator Session is idle(GET)
			       -- or stop the Frame Generator(SET).
                runFG   (2)    -- The Frame Generator Session is running(GET)
			       -- or start a Frame Generator Session(SET)
        }
        ACCESS  read-write
        STATUS  mandatory
        DESCRIPTION
                "This object controls the activity of the Frame Generator
                 process."

        ::= { nbsSysFrmGen 1 }

nbsSysFrmGenDa    OBJECT-TYPE
        SYNTAX  MacAddress
        ACCESS  read-write
        STATUS  mandatory
        DESCRIPTION
                "The Frame Generator Destination MAC Address."

	DEFVAL { '000000000000'h }

        ::= { nbsSysFrmGen 2 }

nbsSysFrmGenSa    OBJECT-TYPE
        SYNTAX  MacAddress
        ACCESS  read-write
        STATUS  mandatory
        DESCRIPTION
                "The Frame Generator Source MAC Address."

	DEFVAL { '000000000000'h }

        ::= { nbsSysFrmGen 3 }

nbsSysFrmGenPktFill    OBJECT-TYPE
        SYNTAX  INTEGER
        ACCESS  read-write
        STATUS  mandatory
        DESCRIPTION
                "The Frame Generator Packet Fill Pattern. The default is 0."

        ::= { nbsSysFrmGen 4 }

nbsSysFrmGenPktRate    OBJECT-TYPE
        SYNTAX  INTEGER
        ACCESS  read-write
        STATUS  mandatory
        DESCRIPTION
                "The Frame Generator Rate, meaning the number of packets
                 per second to be generated. Each device is able to
                 generate a certain number of packets/second.
                 Default is 1 packet/second"

        ::= { nbsSysFrmGen 5 }

nbsSysFrmGenDestMap    OBJECT-TYPE
        SYNTAX  OCTET STRING
        ACCESS  read-write
        STATUS  mandatory
        DESCRIPTION
                "The Frame Generator Destination Map = the set of ports
                 to which the generated packets are to be sent. Each octet
                 within the value of this object specifies a set of
                 eight ports, with the first octet specifying ports
                 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length."

        ::= { nbsSysFrmGen 6}

nbsSysFrmGenPktNum    OBJECT-TYPE
        SYNTAX  Counter
        ACCESS  read-write
        STATUS  mandatory
        DESCRIPTION
                "The Frame Generator Number of Packets to be generated.
                 Default is 1."

        ::= { nbsSysFrmGen 7 }

nbsSysFrmGenPktLen    OBJECT-TYPE
        SYNTAX  INTEGER
        ACCESS  read-write
        STATUS  mandatory
        DESCRIPTION
                "The Frame Generator Packet Length. Default is 60 bytes"

        ::= { nbsSysFrmGen 8 }

nbsSysFrmGenXmtPktNum    OBJECT-TYPE
        SYNTAX  Counter
        ACCESS  read-only
        STATUS  mandatory
        DESCRIPTION
                "Number of Packets transmitted by the The Frame Generator."

        ::= { nbsSysFrmGen 9 }

--
-- ******************************************************************
--
-- Objects for the SNMP Agent configuration, including all the
-- necessary IP ( in-band or out-band ) and SNMP parameters.
--
-- Implementation of the nbsSysSnmpCfg group is mandatory for all NBase
-- products.
--
-- *********************************************************************

nbsSysIpAddr    OBJECT-TYPE
        SYNTAX  IpAddress
        ACCESS  read-write
        STATUS  mandatory
        DESCRIPTION
                "The SNMP Agent Administrative value of the IP Address for the
                 in-band access.

                 This value is stored in the system NVRAM.
                 The current operational IP Adress may be obtained by
                 accessing the ipAdEntAddr entry in the ipAddrTable,
                 for ipAdEntIfIndex 1

                 If the system has no current operational IP Address, meaning
                 that, the access is done out-of-band, then this value takes
                 effect immediately. In this case the NetMask and the
                 BcastAddr will be automatically build.
                 Otherwise it will take effect after a system reset"

        ::= { nbsSysSnmpCfg 1 }

nbsSysNetMask    OBJECT-TYPE
        SYNTAX  IpAddress
        ACCESS  read-write
        STATUS  mandatory
        DESCRIPTION
                "The SNMP Agent Administrative value of the subnet mask for
                 the in-band access.

                 This value is stored in the system NVRAM.
                 The current operational IP Adress may be obtained by
                 accessing the ipAdEntNetMask entry in the ipAddrTable,
                 for ipAdEntIfIndex 1

                 If the system has no current operational IP Address, meaning
                 that, the access is done out-of-band, then this value takes
                 effect immediately.
                 Otherwise it will take effect after a system reset"

        ::= { nbsSysSnmpCfg 2 }

nbsSysBcastAddr    OBJECT-TYPE
        SYNTAX  IpAddress
        ACCESS  read-write
        STATUS  mandatory
        DESCRIPTION
                "The SNMP Agent Administrative value of the IP Broadcast
                 Address for the in-band access.

                 This value is stored in the system NVRAM.
                 The current operational IP Adress may be obtained by
                 accessing the ipAdEntBcastAddr entry in the ipAddrTable,
                 for ipAdEntIfIndex 1

                 If the system has no current operational IP Address, meaning
                 that, the access is done out-of-band, then this value takes
                 effect immediately.
                 Otherwise it will take effect after a system reset"

        ::= { nbsSysSnmpCfg 3 }

nbsSysObIpAddr    OBJECT-TYPE
        SYNTAX  IpAddress
        ACCESS  read-write
        STATUS  mandatory
        DESCRIPTION
                "The SNMP Agent Administrative value of the IP Address for the
                 out-band access.

                 This value is stored in the system NVRAM.
                 The current operational IP Adress may be obtained by
                 accessing the ipAdEntAddr entry in the ipAddrTable,
                 for ipAdEntIfIndex equal to the SLIP interface value.

                 If the system has no current operational Out-Band IP Address,
                 meaning that, the access is done in-band, then this value
                 takes effect immediately. In this case the NetMask and the
                 BcastAddr will be automatically build.
                 Otherwise it will take effect after a system reset"

        ::= { nbsSysSnmpCfg 4 }

nbsSysObNetMask    OBJECT-TYPE
        SYNTAX  IpAddress
        ACCESS  read-write
        STATUS  mandatory
        DESCRIPTION
                "The SNMP Agent Administrative value of the subnet mask for
                 the out-band access.

                 This value is stored in the system NVRAM.
                 The current operational IP Adress may be obtained by
                 accessing the ipAdEntNetMask entry in the ipAddrTable,
                 for ipAdEntIfIndex equal to the SLIP interface value.

                 If the system has no current operational Out-Band IP Address,
                 meaning that, the access is done in-band, then this value
                 takes effect immediately.
                 Otherwise it will take effect after a system reset"

        ::= { nbsSysSnmpCfg 5 }

nbsSysObBcastAddr           OBJECT-TYPE
        SYNTAX  IpAddress
        ACCESS  read-write
        STATUS  mandatory
        DESCRIPTION
                "The SNMP Agent Administrative value of the IP Broadcast
                 Address for the in-band access.

                 This value is stored in the system NVRAM.
                 The current operational IP Adress may be obtained by
                 accessing the ipAdEntBcastAddr entry in the ipAddrTable,
                 for ipAdEntIfIndex equal to the SLIP interface value.

                 If the system has no current operational Out-Band IP Address,
                 meaning that, the access is done in-band, then this value
                 takes effect immediately.
                 Otherwise it will take effect after a system reset"

        ::= { nbsSysSnmpCfg 6 }

nbsSysDefaultGateway        OBJECT-TYPE
        SYNTAX  IpAddress
        ACCESS  read-write
        STATUS  mandatory
        DESCRIPTION
                "The SNMP Agent Administrative value of the Default Gateway.

                 This value is stored in the system NVRAM.
                 The current operational Default Gateway IP Adress may be
                 obtained by accessing ipRouteNextHop object of the 0.0.0.0
                 entry in the ipRouteTable.

                 If the system has no current operational Default Gateway
                 IP Address, then this value takes effect immediately.
                 Otherwise it will take effect after a system reset"

        ::= { nbsSysSnmpCfg 7 }

nbsSysReadComunity    OBJECT-TYPE
        SYNTAX  DisplayString (SIZE (0..256))
        ACCESS  read-write
        STATUS  mandatory
        DESCRIPTION
                "The SNMP Agent Administrative value of the read community
                 string. This value is stored in the system NVRAM.
                 It will take effect after a system reset"

        ::= { nbsSysSnmpCfg 8 }

nbsSysWriteComunity         OBJECT-TYPE
        SYNTAX  DisplayString (SIZE (0..256))
        ACCESS  read-write
        STATUS  mandatory
        DESCRIPTION
                "The SNMP Agent Administrative value of the write community
                 string. This value is stored in the system NVRAM.
                 It will take effect after a system reset.
		 The object may not be read for obvious security reasons.
		 A GET request will be answered by a zero length string."

        ::= { nbsSysSnmpCfg 9 }

nbsSysBootpEnable           OBJECT-TYPE
        SYNTAX  INTEGER {
                disable(1),      -- BOOTP process is disabled
                enable (2)       -- BOOTP process is enabled
        }
        ACCESS  read-write
        STATUS  mandatory
        DESCRIPTION
                "The SNMP Agent value for the activation of the BOOTP process.
                 This value is stored in the system NVRAM also and will be
                 preserved over system resets and power cycles."

        ::= { nbsSysSnmpCfg 10 }

nbsSysTrapTblMaxSize    OBJECT-TYPE
        SYNTAX  INTEGER
        ACCESS  read-only
        STATUS  mandatory
        DESCRIPTION
                "The maximum size (number of rows) allowed in the trap table"

        ::= { nbsSysSnmpCfg 11 }

nbsSysTrapTable OBJECT-TYPE
        SYNTAX  SEQUENCE OF NbsSysTrapEntry
        ACCESS  not-accessible
        STATUS  mandatory
        DESCRIPTION
                "A table of managers to whom will the traps generated by the
                 SNMP agent will be sent.
                 It represents the current operational table as well as the
                 NVRAM saved table. The entries in the table are saved over
                 system resets and power up cycles"

        ::= { nbsSysSnmpCfg 12 }

nbsSysTrapEntry      OBJECT-TYPE
        SYNTAX  NbsSysTrapEntry
        ACCESS  not-accessible
        STATUS  mandatory
        DESCRIPTION
                "Contains the information necessary to generate a trap to be
                 sent to a particular manager.

                 The object nbsSysTrapTblEntStatus, when written is used to
                 create or delete an entry/row in nbsSysTrapTable. To create
                 a new entry a SET PDU with the nbsSysTrapTblEntIpAddr,
                 nbsSysTrapTblEntComm and nbsSysTrapTblEntStatus objects is
                 required."
        INDEX { nbsSysTrapTblEntIndex }

        ::= { nbsSysTrapTable 1 }

NbsSysTrapEntry ::= SEQUENCE {

        nbsSysTrapTblEntIndex   INTEGER,
        nbsSysTrapTblEntStatus  INTEGER,
        nbsSysTrapTblEntIpAddr  IpAddress,
        nbsSysTrapTblEntComm    DisplayString
        }

nbsSysTrapTblEntIndex   OBJECT-TYPE
        SYNTAX  INTEGER
        ACCESS  read-only
        STATUS  mandatory
        DESCRIPTION
                "The index of the entry/row in the trap table in the range
                 1 to the value of nbsSysTrapTblMaxSize."

        ::= { nbsSysTrapEntry 1 }

nbsSysTrapTblEntStatus  OBJECT-TYPE
        SYNTAX  INTEGER {
                invalid(1),     -- an invalidated entry
                active (2)      -- an active entry describing a manager
        }
        ACCESS  read-write
        STATUS  mandatory
        DESCRIPTION
                "This object is used to get/set the validity of the
                information contained by nbsSysTrapEntry row.

                Setting this object to the value invalid(1) has the effect of
                deleting the corresponding entry in the nbsSysTrapTable.
		Deleting and entry has the effect of initializing it to default
		values : IpAddr = 0.0.0.0 & Comm = null string.

                Setting this object to the value valid(2) entry has the effect of
		creating a new row/entry in the nbsSysTrapTable object, if an entry
                with the same nbsSysTrapTblEntIpAddr does not exist. If such
                an entry exists, then a 'badValue' error will be returned.

                The GET operations will receive a value of valid(2) for
                existing entries. An invalid(1) value indicates an entry that
                was deleted by a previous SET operation."

        ::= { nbsSysTrapEntry 2 }

nbsSysTrapTblEntIpAddr  OBJECT-TYPE
        SYNTAX  IpAddress
        ACCESS  read-write
        STATUS  mandatory
        DESCRIPTION
                "IP Address of a manager that is to receive the SNMP agent
                 generated traps"

        ::= { nbsSysTrapEntry 3 }

nbsSysTrapTblEntComm    OBJECT-TYPE
        SYNTAX  DisplayString
        ACCESS  read-write
        STATUS  mandatory
        DESCRIPTION
                "Community string used by the SNMP agent in the traps
                 generated"

        ::= { nbsSysTrapEntry 4 }

nbsSysTftpSwFileName         OBJECT-TYPE
        SYNTAX  DisplayString
        ACCESS  read-write
        STATUS  mandatory
        DESCRIPTION
                "The SNMP Agent Software File Name. This is the remote
                 file name string provided to the TFTP client application
                 when starting a Firmware Update process.
                 This value is stored in the system NVRAM as well as in
                 the SNMP Agent current configuration."

        ::= { nbsSysSnmpCfg 13 }

nbsSysTftpParFileName         OBJECT-TYPE
        SYNTAX  DisplayString
        ACCESS  read-write
        STATUS  mandatory
        DESCRIPTION
                "The SNMP Agent Parameters File Name. This is the remote
                 file name string provided to the TFTP server application
                 when using the BOOTP/TFTP processin order to configure the
                 SNMP Agent.
                 This value is stored in the system NVRAM as well as in
                 the SNMP Agent current configuration."

        ::= { nbsSysSnmpCfg 14 }

nbsSysSerialLineMode    OBJECT-TYPE
        SYNTAX  INTEGER{
                adminIf(1),-- serial line is in Terminal Administrative Mode
                slipIf (2) -- serial line is in SLIP mode
        }
        ACCESS  read-write
        STATUS  mandatory
        DESCRIPTION
                "The mode in which the serial line is used:
                 by the local Administrative Interface, or as a SLIP line.
                 Note that setting this object to adminIf(1) value while
                 in SLIP mode will abort the serial connection between the
                 SNMP Manager and the device.
                 Setting this object to slipIf(2) while in Administrative
                 Interface Mode will abort the local terminal connection."

        ::= { nbsSysSnmpCfg 15 }

nbsSysSerialSlipBaudRate     OBJECT-TYPE
        SYNTAX  INTEGER{
                b9600  (1),     -- baud rate is  9600
                b19200 (2),     -- baud rate is 19200
                b38400 (3)      -- baud rate is 38400
        }
        ACCESS  read-write
        STATUS  mandatory
        DESCRIPTION
                "The Serial Line Baud Rate when in SLIP Mode.
                 This value is stored in the system NVRAM as well as in
                 the SNMP Agent current configuration."

        ::= { nbsSysSnmpCfg 16 }

nbsSysTelnetSession    OBJECT-TYPE
        SYNTAX  INTEGER{
                connected   (1),-- a  TELNET session is in process
                disconnect  (2) -- no TELNET session is in process
        }
        ACCESS  read-only
        STATUS  mandatory
        DESCRIPTION
                "This object indicates if there is any TELNET session in
                 progress."

        ::= { nbsSysSnmpCfg 17 }

nbsSysTelnetHost    OBJECT-TYPE
        SYNTAX  IpAddress
        ACCESS  read-only
        STATUS  mandatory
        DESCRIPTION
                "This object indicates the remote IP host that connected
		 to the local device. It is 0.0.0.0 if there is no active
		 Telnet session"

        ::= { nbsSysSnmpCfg 19 }

nbsSysTftpRswFileName         OBJECT-TYPE
        SYNTAX  DisplayString
        ACCESS  read-write
        STATUS  mandatory
        DESCRIPTION
                "The SNMP Agent Remote Software File Name. This is the remote
                 file name string provided to the TFTP Server application
                 by the SNMP Agent TFTP client, when initiating a Firmware Update
		 process. This value is stored in the system NVRAM as well as in
                 the SNMP Agent current configuration."

        ::= { nbsSysSnmpCfg 20 }

nbsSysTftpServerIP    OBJECT-TYPE
        SYNTAX  IpAddress
        ACCESS  read-write
        STATUS  mandatory
        DESCRIPTION
		"This is the IP Address of the TFTP Server serving the
		 software/parameter download/upload process, initiated
		 by the SNMP agent.
		 It is 0.0.0.0, if there is no TFTP server is defined"

        ::= { nbsSysSnmpCfg 21 }

nbsSysInitDownload    OBJECT-TYPE
        SYNTAX  INTEGER{
                active    (1),-- a  download sesssion is activated(WRITE) or active(READ)
		inactive  (2),-- no download sesssion is active(READ)                                      // ykfix39 - 21.09.00
		activeAppl(3) -- a  download sesssion from Application is activated(WRITE) or active(READ) // ykfix39 - 21.09.00
	}
        ACCESS  read-write
        STATUS  mandatory
        DESCRIPTION
		"This is used to initiate a download session from the above
		 TFTP server.
		 Note that the only writeable value is active(1) and activeAppl(3),
		 if no session is active at this moment."
	::= { nbsSysSnmpCfg 22 }


nbsSysParDownload    OBJECT-TYPE
        SYNTAX  INTEGER{
                active    (1),-- a  download sesssion is activated(WRITE) or active(READ)
                inactive  (2) -- no download sesssion is active(READ)
	}
        ACCESS  read-write
        STATUS  mandatory
        DESCRIPTION
		"This is used to initiate a parameter download session from the above
		 TFTP server.
		 Note that the only writeable value is active(1), if no session is
		 active at this moment."

        ::= { nbsSysSnmpCfg 23 }

nbsSysParUpload    OBJECT-TYPE
        SYNTAX  INTEGER{
                active    (1),-- an upload sesssion is activated(WRITE) or active(READ)
                inactive  (2) -- no upload sesssion is active(READ)
	}
        ACCESS  read-write
        STATUS  mandatory
        DESCRIPTION
		"This is used to initiate a parameter upload session to the above
		 TFTP server.
		 Note that the only writeable value is active(1), if no session is
		 active at this moment."

        ::= { nbsSysSnmpCfg 24 }

--
-- *********************************************************************
-- The nbsPing Subgoup
--
-- Implementation of the nbsSysPing subgroup is mandatory for all Nbase
-- products.
--
-- The nbsSysPing Group is used by a station to initiate a ping from
-- this agent to the address denoted by nbsSysPingAddr.
--
-- To ping another host, you must minimally set the nbsSysPingAddr to the
-- host that you want to ping and nbsSysPingSession to startEcho(2).  The
-- other objects let you change the number of ICMP Echo request packets to
-- be transmitted. The default value is 1.
--
-- Notes:
--      1. only one Ping can be processed at a time.
-- ************************************************************************

nbsSysPing      OBJECT IDENTIFIER  ::= { nbsSysSnmpCfg 18 }

nbsSysPingSession       OBJECT-TYPE
        SYNTAX  INTEGER{
                idlePing   (1),
                runPing    (2)
        }
        ACCESS  read-write
        STATUS  mandatory
        DESCRIPTION
                "This object controls the activity of the PING process
                 progress.
		 If GET idlePing(1) shows that the ping process is inactive - idle.
		 If SET idlePing(1) stops an active ping process, if any.

		 If GET runPing(2) shows  an active ping process.
		 If SET runPing(2) starts an active ping process, if none active.
		 This has to be the last SET in order to activate the PING process"

	 ::= { nbsSysPing 1 }

nbsSysPingAddr OBJECT-TYPE
        SYNTAX IpAddress
        ACCESS read-write
        STATUS mandatory
        DESCRIPTION
                "The IP Address to which the Nbase device will ping.  Setting
                this variable initiates the ping sequence.  The default
                value is the loopback address 127.0.0.1 ."
	DEFVAL { '7F000001'h }
-- For SunNet Manager :
--	DEFVAL { '0x7F000001'h }
--
        ::= { nbsSysPing 2 }

nbsSysPingNumber OBJECT-TYPE
        SYNTAX Counter
        ACCESS read-write
        STATUS mandatory
        DESCRIPTION
                "The number of ICMP echo packets (pings) to be sent.
                The default value is 1."

        ::= { nbsSysPing 3 }

nbsSysPingRequests OBJECT-TYPE
        SYNTAX Counter
        ACCESS read-only
        STATUS mandatory
        DESCRIPTION
                "The number of ICMP echo request (pings) sent."

        ::= { nbsSysPing 4 }

nbsSysPingResps OBJECT-TYPE
        SYNTAX INTEGER
        ACCESS read-only
        STATUS mandatory
        DESCRIPTION
                "The number of ICMP echo response packets received."

        ::= { nbsSysPing 5 }

nbsSysPingOwner OBJECT-TYPE
        SYNTAX INTEGER {
		adminInterface(1),
		snmpAgent     (2)
	}
        ACCESS read-only
        STATUS mandatory
        DESCRIPTION
                "If a Ping Process is active, then the value of this
		 object shows who activated it: the Administrative
		 Interface or the SNMP Agent . This object value
		 will permit to stop the Ping Process only from the
		 interface that activated it - i.e. the owner."

        ::= { nbsSysPing 6 }
-- ************************************************************
-- End of the SNMP Agent configuration group
-- ************************************************************
-- ************************************************************
-- Objects in the NBase Port Configuration Group
--
-- These objects are general for all the NBase Ethernet Switches
-- *************************************************************

nbsPortCfgTable OBJECT-TYPE

        SYNTAX  SEQUENCE OF NbsPortCfgEntry
        ACCESS  not-accessible
        STATUS  mandatory
        DESCRIPTION
                "A list of the port configurations entries. The number of
                 entries is given by nbsSysPortsNumber"

        ::= { nbsPortCfg 1 }

nbsPortCfgEntry      OBJECT-TYPE
        SYNTAX  NbsPortCfgEntry
        ACCESS  not-accessible
        STATUS  mandatory
        DESCRIPTION
                "Contains the information necessary to configure/describe a
                 port configuration. The number of rows/entries is fixed. A
                 row/entry may not be created or deleted"

        INDEX { nbsPortCfgIndex }

        ::= { nbsPortCfgTable 1 }

NbsPortCfgEntry ::= SEQUENCE {

        nbsPortCfgIndex         INTEGER,
        nbsPortCfgLanType       INTEGER,
        nbsPortCfgIfType        INTEGER,
        nbsPortCfgPortSelect    INTEGER,
        nbsPortCfgIfLink        INTEGER,
        nbsPortCfgPortFctrl     INTEGER,
        nbsPortCfgPortDplex     INTEGER,
        nbsPortCfgPortDelay     INTEGER,
        nbsPortCfgSpeedSelect   INTEGER,
        nbsPortCfgEnable        INTEGER,
	nbsPortCfgIsvpMode	INTEGER

        }

nbsPortCfgIndex         OBJECT-TYPE
        SYNTAX  INTEGER
        ACCESS  read-only
        STATUS  mandatory
        DESCRIPTION
                "A unique value for each switched port. Its value ranges from
                 1 to the value of nbsSysPortsNumber."
        ::= { nbsPortCfgEntry 1 }

nbsPortCfgLanType    OBJECT-TYPE
        SYNTAX  INTEGER {
                none  (1),      -- no LAN interface installed
                eth10 (2),      -- Ethernet  10Mbps
                eth100(3),      -- Ethernet 100Mbps
                eth10-100(4),   -- Ethernet 10/100Mbps
                eth100B(5),     -- Ethernet 100Mbps Backbone/ISVLAN
                eth1000B(6),    -- Ethernet 1000Mbps Backbone/ISVLAN
                atmLane(7),	-- ATM Lan Emulation Module
                eth100Grp(8),   -- Ethernet 100Mbps Group Switching
-- ykfix29 - 12.05.99 - begin
		eth10-100Grp(9),-- Ethernet 10/100Mbps Group Switching
		fddi(10),       -- FDDI
-- ykfix29 - 12.05.99 - end
		eth100-1000(11) -- Ethernet 100/1000Mbps  ( ykfix33 - 1.03.00 )

	}
        ACCESS  read-only
        STATUS  mandatory
        DESCRIPTION
                "The port LAN type that is installed (if exists)"
        ::= { nbsPortCfgEntry 2 }

nbsPortCfgIfType         OBJECT-TYPE
        SYNTAX  INTEGER {
                aui   (1),      -- AUI interface - Ethernet 10 Mbps only
                tp    (2),      -- TP  interface - 10 or 100 Mbps
                auiTp (3),      -- AUI & TP interface - Ethernet 10 Mbps only
                tpfd  (4),      -- TP Full Duplex capable - 10 or 100 Mbps
                coax  (5),      -- COAX interface- Ethernet 10 Mbps only
		foMm  (6),      -- Fiber Optic MultiMode  - 10 or 100 Mbps
                foSm  (7),      -- Fiber Optic SingleMode - 10 or 100 Mbps
		none  (8),      -- no interface installed - no LAN installed
		foSxM   (9),    -- Fiber Optic MultiMode   - GigaBit          - (WaveLength=850nm)
		foLxM  (10),    -- Fiber Optic MultiMode   - GigaBit          - (WaveLength=1310nm)
		foLxS1 (11),    -- Fiber Optic SingleMode1 - GigaBit          - (WaveLength=1310nm)
		foLxS2 (12),    -- Fiber Optic SingleMode2 - GigaBit          - (WaveLength=1550nm)
		foLxS3 (13),    -- Fiber Optic SingleMode3 - GigaBit          - (WaveLength=1550nm)
		foM    (14),    -- Fiber Optic MultiMode   - FastEthernet,ATM,FDDI - (WaveLength=1310nm)
		foMX   (15),    -- Fiber Optic MultiMode   - FastEthernet          - (WaveLength=1310nm)
		foS1   (16),    -- Fiber Optic SingleMode1 - FastEthernet,ATM,FDDI - (WaveLength=1310nm)
		foS2   (17),    -- Fiber Optic SingleMode2 - FastEthernet,ATM,FDDI - (WaveLength=1310nm)
		foS3   (18),    -- Fiber Optic SingleMode3 - FastEthernet,ATM      - (WaveLength=1550nm)
		foLxS4 (19),    -- Fiber Optic SingleMode4 - GigaBit          - (WaveLength=1550nm)
		foLxS5 (20),    -- Fiber Optic SingleMode5 - GigaBit          - (WaveLength=1550nm)
		foS4   (21),    -- Fiber Optic SingleMode4 - FastEthernet          - (WaveLength=1550nm)
		foS5   (22),    -- Fiber Optic SingleMode5 - FastEthernet          - (WaveLength=1550nm)
		foM-10 (23)     -- Fiber Optic MultiMode   -     Ethernet          - (WaveLength=850nm)
	}
        ACCESS  read-only
        STATUS  mandatory
        DESCRIPTION
                "The port physical interface that is installed (if any)."
        ::= { nbsPortCfgEntry 3 }

nbsPortCfgPortSelect         OBJECT-TYPE
        SYNTAX  INTEGER {
                other (1),      -- none of the following: for the non
			        -- TP/AUI kind like FO
		aui   (2),      -- AUI   interface select(ed)
                tp    (3),      --  TP   interface select(ed)
                asel  (4)       -- Auto Select Mode employed
        }
        ACCESS  read-write
        STATUS  mandatory
	DESCRIPTION
                "The port physical interface type selection.
                 For regular 10 Mbps Ethernet Ports, the default value
                 is Auto Select.
                 100 Base-Tx ports do not support more than one type of
                 physical interface.
                 Setting a not supported type of interface will result in
                 a badValue response"
	DEFVAL { asel }

        ::= { nbsPortCfgEntry 4 }

nbsPortCfgIfLink         OBJECT-TYPE
        SYNTAX  INTEGER {
                other  (1),      -- non existing/non Ethernet ifs state
                enable (2),      -- link is  enabled - for Ethernet ifs only
                disable(3)       -- link is disabled - for Ethernet ifs only
        }
        ACCESS  read-only
        STATUS  mandatory
        DESCRIPTION
                "The link integrity status. This object is rellevant
                 for a port of type Twisted Pair or Fiber Optic,
                 10 or 100 Mbps"
        ::= { nbsPortCfgEntry 5 }

nbsPortCfgPortFctrl         OBJECT-TYPE
        SYNTAX  INTEGER {
                enable  (1),    -- enable  flow control
                disable (2)     -- disable flow control
        }
        ACCESS  read-write
        STATUS  mandatory
        DESCRIPTION
                "The port flow control mode selection: enable (default )
                 or disable"
	DEFVAL { enable }

        ::= { nbsPortCfgEntry 6 }

nbsPortCfgPortDplex         OBJECT-TYPE
        SYNTAX  INTEGER {
                halfDuplex (1),
                fullDuplex (2)
        }
        ACCESS  read-write
        STATUS  mandatory
        DESCRIPTION
                "The port dplex mode selection: halfDuplex(1) - default
                 or fullDuplex(2) "
	DEFVAL { halfDuplex }
        ::= { nbsPortCfgEntry 7 }

nbsPortCfgPortDelay         OBJECT-TYPE
        SYNTAX  INTEGER
        ACCESS  read-write
        STATUS  mandatory
        DESCRIPTION
                "The port forwarding delay expressed in bytes, with an
                 acceptable range of 6..64 bytes. The default is 64 bytes.
                 This object is supported only by the NH204-AT device"
	DEFVAL { 64 }

        ::= { nbsPortCfgEntry 8 }

nbsPortCfgSpeedSelect         OBJECT-TYPE
	SYNTAX  INTEGER {
                autoSense (1),
                force10   (2),
		force100  (3),                    -- ykfix27 - 30.05.99
		force1000 (4)                     -- ykfix27 - 30.05.99

        }
        ACCESS  read-write
        STATUS  mandatory
        DESCRIPTION
	"The Ethernet Port speed selection in the case of a
		 eth10-100(4) & eth1000B(6) nbsPortCfgLanType Ethernet port" -- ykfix27 - 30.05.99
	DEFVAL { autoSense }

        ::= { nbsPortCfgEntry 9 }

nbsPortCfgEnable         OBJECT-TYPE
        SYNTAX  INTEGER {
		portDisable(1),
		portEnable (2)
        }
        ACCESS  read-write
        STATUS  mandatory
        DESCRIPTION
                "Port Enable/Disable"
	DEFVAL { portEnable }

        ::= { nbsPortCfgEntry 10 }


nbsPortCfgIsvpMode           OBJECT-TYPE
	SYNTAX  INTEGER {
		access  (1),
		trunk   (2),
		nonIsvp (3)
	}
	ACCESS  read-write
	STATUS  mandatory
	DESCRIPTION
		"The Inter-Switch Virtual Mode of this port.  nonIsvp(3)
		means the port does not support this mode of operation.
		Access(1) means the port is in Access mode. Trunk(2) means
		the port is in Trunk mode."

        ::= { nbsPortCfgEntry 11 }

nbsPortGrpCfgNum OBJECT-TYPE
	SYNTAX  INTEGER
	ACCESS  read-only
	STATUS  mandatory
	DESCRIPTION
		"Maximum number of Switching Ports supported
		 by the system."

        ::= { nbsPortCfg 2 }


nbsPortGrpCfgTable OBJECT-TYPE

        SYNTAX  SEQUENCE OF NbsPortGrpCfgEntry
        ACCESS  not-accessible
        STATUS  mandatory
        DESCRIPTION
                "A list of the port configurations entries. The number of
                 entries is given by nbsSysPortsNumber"

        ::= { nbsPortCfg 3 }

nbsPortGrpCfgEntry      OBJECT-TYPE
        SYNTAX  NbsPortGrpCfgEntry
        ACCESS  not-accessible
        STATUS  mandatory
        DESCRIPTION
                "Contains the information necessary to configure/describe a
                 port configuration. The number of rows/entries is fixed. A
                 row/entry may not be created or deleted"

        INDEX { nbsPortGrpCfgIndex }

        ::= { nbsPortGrpCfgTable 1 }

NbsPortGrpCfgEntry ::= SEQUENCE {

        nbsPortGrpCfgIndex         INTEGER,
        nbsPortGrpCfgGrpNumber     INTEGER,
        nbsPortGrpCfgPortNumber    INTEGER,
        nbsPortGrpCfgLinkStatus    INTEGER,
        nbsPortGrpCfgActivity      INTEGER
        }

nbsPortGrpCfgIndex         OBJECT-TYPE
        SYNTAX  INTEGER
        ACCESS  read-only
        STATUS  mandatory
        DESCRIPTION
                "A unique value for each switched port. Its value ranges from
                 1  to 32."
        ::= { nbsPortGrpCfgEntry 1 }

nbsPortGrpCfgGrpNumber    OBJECT-TYPE
        SYNTAX  INTEGER
        ACCESS  read-only
        STATUS  mandatory
        DESCRIPTION
                "number of groups  "
        ::= { nbsPortGrpCfgEntry 2 }

nbsPortGrpCfgPortNumber    OBJECT-TYPE
        SYNTAX  INTEGER
        ACCESS  read-only
        STATUS  mandatory
        DESCRIPTION
                "number of ports in group "
        ::= { nbsPortGrpCfgEntry 3 }

nbsPortGrpCfgLinkStatus    OBJECT-TYPE
        SYNTAX  INTEGER{
                linkOff(1),
                linkOn (2)

	}
        ACCESS  read-only
        STATUS  mandatory
        DESCRIPTION
                "The link status of the port"
        ::= { nbsPortGrpCfgEntry 4 }

nbsPortGrpCfgActivity    OBJECT-TYPE
        SYNTAX  INTEGER{
                nonActivity(1),
                activity (2)
	}
        ACCESS  read-only
        STATUS  mandatory
        DESCRIPTION
                "The port activity"
        ::= { nbsPortGrpCfgEntry 5 }

-- ************************************************************
-- End of the NBase Port Configuration Group
-- ************************************************************
-- ************************************************************
-- Objects in the NBase Ethernet Information Group
--
-- These objects are general for all the NBase Ethernet Switches
-- The objects provide the Ethernet MAC level information &
-- statistics that are not provided by the Ethernet MIB.
-- ************************************************************

nbsEthInfoTable OBJECT-TYPE
        SYNTAX  SEQUENCE OF NbsEthInfoEntry
        ACCESS  not-accessible
        STATUS  mandatory
        DESCRIPTION
                "A list of the port NBase specific Ethernet Statistics.
                 Number of entries is given by nbsSysPortsNumber"

        ::= { nbsEtherInfo 1 }

nbsEthInfoEntry      OBJECT-TYPE
        SYNTAX  NbsEthInfoEntry
        ACCESS  not-accessible
        STATUS  mandatory
        DESCRIPTION
                "Contains the NBase specific Ethernet Statistics for a port.
                 The number of rows/entries is fixed. A row/entry may not be
                 created or deleted"

        INDEX { nbsEthInfoIndex }

        ::= { nbsEthInfoTable  1 }

NbsEthInfoEntry ::= SEQUENCE {

        nbsEthInfoIndex           INTEGER,
        nbsEthInfoCntFctrls       Counter,
        nbsEthInfoCntExcessFctrls Counter
        }

nbsEthInfoIndex OBJECT-TYPE
        SYNTAX  INTEGER
        ACCESS  read-only
        STATUS  mandatory
        DESCRIPTION
                "A unique value for each switched port. Its value ranges from
                 1 to the value of nbsSysPortsNumber."

        ::= { nbsEthInfoEntry 1 }

nbsEthInfoCntFctrls         OBJECT-TYPE
        SYNTAX  Counter
        ACCESS  read-only
        STATUS  mandatory
        DESCRIPTION
                "Number of times the flow control mechanism was activated
                 on the specified input port, due to a full buffer on the
                 output port. The number is correct if the flow control
                 mechanism is enabled"

        ::= { nbsEthInfoEntry 2 }

nbsEthInfoCntExcessFctrls         OBJECT-TYPE
        SYNTAX  Counter
        ACCESS  read-only
        STATUS  mandatory
        DESCRIPTION
                "Number of times the flow control mechanism was activated
                 unsuccessfull 15 times. The number is correct if the
                 flow control mechanism is enabled"

        ::= { nbsEthInfoEntry 3 }

-- ************************************************************
-- End of the NBase NBase Ethernet Statistics Group
-- ************************************************************
-- ************************************************************
--
-- Objects in the NBase Performance Switching Statistics Group
--
-- These objects are general for all the NBase Ethernet Switches
-- The objects provide the Switching Performance Statistics that
-- are not provided by the Bridge MIB.
-- ************************************************************
-- **********************************
-- Switching Port Statistics
-- **********************************

nbsSwitchPerfTable OBJECT-TYPE
        SYNTAX  SEQUENCE OF NbsSwitchPerfEntry
        ACCESS  not-accessible
        STATUS  mandatory
        DESCRIPTION
                "A list of NBase port specific performance statistics.
                 Number of entries is given by nbsSysPortsNumber"

        ::= { nbsSwitchPerf 1 }

nbsSwitchPerfEntry   OBJECT-TYPE
        SYNTAX  NbsSwitchPerfEntry
        ACCESS  not-accessible
        STATUS  mandatory
        DESCRIPTION
                "Contains the NBase specific Ethernet Statistics for a port.
                 The number of rows/entries is fixed. A row/entry may not be
                 created or deleted"
        INDEX { nbsSwitchPerfIndex }

        ::= { nbsSwitchPerfTable  1 }

NbsSwitchPerfEntry ::= SEQUENCE {
            nbsSwitchPerfIndex      INTEGER,
            nbsSwitchPerfMcastPkts  Counter,
            nbsSwitchPerfUnknPkts   Counter
        }

nbsSwitchPerfIndex  OBJECT-TYPE
        SYNTAX  INTEGER
        ACCESS  read-only
        STATUS  mandatory
        DESCRIPTION
                "A unique value for each switched port. Its value ranges from
                 1 to the value of nbsSysPortsNumber."

        ::= { nbsSwitchPerfEntry 1 }

nbsSwitchPerfMcastPkts  OBJECT-TYPE
        SYNTAX  Counter
        ACCESS  read-only
        STATUS  mandatory
        DESCRIPTION
                "Number of Multicast packets received by the switching entity
                 on this port"

        ::= { nbsSwitchPerfEntry 2 }

nbsSwitchPerfUnknPkts  OBJECT-TYPE
        SYNTAX  Counter
        ACCESS  read-only
        STATUS  mandatory
        DESCRIPTION
                "Number of packets received by the switching entity
                 on this port with unknown destination port. As a result
                 these packets were forwarded to all the switch other
                 ports - flooding"

        ::= { nbsSwitchPerfEntry 3 }
--
-- ****************************************************************
-- The nbsPortFwdPerfTable containes the number of packets and bytes
-- forwarded from a specific input port to another port of the
-- switch.
-- The entry <i,i> contains the filtered packets and frames.
-- *****************************************************************

nbsPortFwdPerfTable OBJECT-TYPE
        SYNTAX  SEQUENCE OF NbsPortFwdPerfEntry
        ACCESS  not-accessible
        STATUS  mandatory
        DESCRIPTION
                "A list of the NBase port specific switching performance
                 statistics. Contains the number of packets and bytes
                 forwarded from nbsPortFwdPerfInPort to all other
                 nbsPortFwdPerfOutPort, including itself.
                 Number of entries is given by nbsSysPortsNumber"

        ::= { nbsSwitchPerf 2 }

nbsPortFwdPerfEntry     OBJECT-TYPE
        SYNTAX  NbsPortFwdPerfEntry
        ACCESS  not-accessible
        STATUS  mandatory
        DESCRIPTION
                "Contains the NBase specific Switching Performance statistics
                 for a port. Contains the number of packets and bytes
                 forwarded from nbsPortFwdPerfInPort to all other
                 nbsPortFwdPerfOutPort, including itself.
                 The number of rows/entries is fixed. A row/entry may not be
                 created or deleted"

        INDEX { nbsPortFwdPerfInPort, nbsPortFwdPerfOutPort }

        ::= { nbsPortFwdPerfTable  1 }

NbsPortFwdPerfEntry ::= SEQUENCE {

        nbsPortFwdPerfInPort       INTEGER,
        nbsPortFwdPerfOutPort      INTEGER,
        nbsPortFwdPerfFwdPkts      Counter,
        nbsPortFwdPerfFwdBytes     Counter
        }

nbsPortFwdPerfInPort  OBJECT-TYPE
        SYNTAX  INTEGER
        ACCESS  read-only
        STATUS  mandatory
        DESCRIPTION
                "A unique value for each switched port. Its value ranges from
                 1 to the value of nbsSysPortsNumber."

        ::= { nbsPortFwdPerfEntry 1 }

nbsPortFwdPerfOutPort  OBJECT-TYPE
        SYNTAX  INTEGER
        ACCESS  read-only
        STATUS  mandatory
        DESCRIPTION
                "A unique value for each switched port. Its value ranges from
                 1 to the value of nbsSysPortsNumber."

        ::= { nbsPortFwdPerfEntry 2 }

nbsPortFwdPerfFwdPkts  OBJECT-TYPE
        SYNTAX  Counter
        ACCESS  read-only
        STATUS  mandatory
        DESCRIPTION
                "Number of packets forwarded by the switching entity
                 from nbsPortFwdPerfInPort to nbsPortFwdPerfoutPort"

        ::= { nbsPortFwdPerfEntry 3 }

nbsPortFwdPerfFwdBytes  OBJECT-TYPE
        SYNTAX  Counter
        ACCESS  read-only
        STATUS  mandatory
        DESCRIPTION
                "Number of packets forwarded by the switching entity
                 from nbsPortFwdPerfInPort to nbsPortFwdPerfoutPort"

        ::= { nbsPortFwdPerfEntry 4 }
--
-- ************************************
-- Management Port Statistics
-- ************************************

nbsMgmtPerfStats        OBJECT IDENTIFIER ::= { nbsSwitchPerf 3 }

nbsMgmtPerfRcvdPkts  OBJECT-TYPE
        SYNTAX  Counter
        ACCESS  read-only
        STATUS  mandatory
        DESCRIPTION
                "Number of packets received by the SNMP Agent through
                 the management port."

        ::= { nbsMgmtPerfStats 1 }


nbsMgmtPerfRcvdBytes      OBJECT-TYPE
        SYNTAX  Counter
        ACCESS  read-only
        STATUS  mandatory
        DESCRIPTION
                "Number of bytes received by the SNMP Agent through
                 the management port."

        ::= { nbsMgmtPerfStats 2 }

nbsMgmtPerfFilterdPkts  OBJECT-TYPE
        SYNTAX  Counter
        ACCESS  read-only
        STATUS  mandatory
        DESCRIPTION
                "Number of packets received by the SNMP Agent through
                 the management port, that were discarded because they
                 carried an unknown protocol"

        ::= { nbsMgmtPerfStats 3 }

nbsMgmtPerfRcvBcastPkts  OBJECT-TYPE
        SYNTAX  Counter
        ACCESS  read-only
        STATUS  mandatory
        DESCRIPTION
                "Number of broadcast packets received by the SNMP Agent
                 through the management port."

        ::= { nbsMgmtPerfStats 4 }

nbsMgmtPerfXmtPkts  OBJECT-TYPE
        SYNTAX  Counter
        ACCESS  read-only
        STATUS  mandatory
        DESCRIPTION
                "Number of packets transmitted by the SNMP Agent
                 through the management port. This counter indicates the
                 number of packets generated by the Management Software.
                 A certain packet will be transmitted once, to a single
                 switch port, or multiple times, to multiple switch ports."

        ::= { nbsMgmtPerfStats 5 }

nbsMgmtPerfXmtUcastPkts  OBJECT-TYPE
        SYNTAX  Counter
        ACCESS  read-only
        STATUS  mandatory
        DESCRIPTION
                "Number of unicast packets transmitted by the SNMP Agent
                 through the management port."

        ::= { nbsMgmtPerfStats 6 }

nbsMgmtPerfXmtMcastPkts  OBJECT-TYPE
        SYNTAX  Counter
        ACCESS  read-only
        STATUS  mandatory
        DESCRIPTION
                "Number of multicast packets transmitted by the SNMP Agent
                 through the management port.  This counter indicates the
                 number of packets generated by the Management Software.
                 A certain packet will be transmitted once, to a single
                 switch port, or multiple times, to multiple switch ports."

        ::= { nbsMgmtPerfStats 7 }

nbsMgmtPerfXmtBcastPkts  OBJECT-TYPE
        SYNTAX  Counter
        ACCESS  read-only
        STATUS  mandatory
        DESCRIPTION
                "Number of broadcast packets transmitted by the SNMP Agent
                 through the management port.  This counter indicates the
                 number of packets generated by the Management Software.
                 A certain packet will be transmitted once, to a single
                 switch port, or multiple times, to multiple switch ports."

        ::= { nbsMgmtPerfStats 8 }
--
-- ****************************************************************
-- The nbsMgmtRcvPerfTable containes the number of packets and bytes
-- forwarded to the Management Port from the other ports of the
-- switch.
-- *****************************************************************

nbsMgmtRcvPerfTable OBJECT-TYPE
        SYNTAX  SEQUENCE OF NbsMgmtRcvPerfEntry
        ACCESS  not-accessible
        STATUS  mandatory
        DESCRIPTION
                "A list of the NBase port specific switching performance
                 statistics. Contains the number of packets and bytes
                 forwarded to the Management Port from all the
                 nbsMgmtRcvPerfOutPort ports.
                 Number of entries is given by nbsSysPortsNumber"

        ::= { nbsSwitchPerf 4 }

nbsMgmtRcvPerfEntry     OBJECT-TYPE
        SYNTAX  NbsMgmtRcvPerfEntry
        ACCESS  not-accessible
        STATUS  mandatory
        DESCRIPTION
                "Contains the NBase specific Switching Performance statistics
                 for a port. Contains the number of packets and bytes
                 forwarded to the Management Port from all the
                 nbsMgmtRcvPerfOutPort ports.
                 The number of rows/entries is fixed. A row/entry may not be
                 created or deleted"

        INDEX { nbsMgmtRcvPerfInPort }

        ::= { nbsMgmtRcvPerfTable  1 }

NbsMgmtRcvPerfEntry ::= SEQUENCE {

        nbsMgmtRcvPerfInPort      INTEGER,
        nbsMgmtRcvPerfFwdPkts      Counter,
        nbsMgmtRcvPerfFwdBytes     Counter
        }

nbsMgmtRcvPerfInPort  OBJECT-TYPE
        SYNTAX  INTEGER
        ACCESS  read-only
        STATUS  mandatory
        DESCRIPTION
                "A unique value for each switched port. Its value ranges from
                 1 to the value of nbsSysPortsNumber."

        ::= { nbsMgmtRcvPerfEntry 2 }

nbsMgmtRcvPerfFwdPkts  OBJECT-TYPE
        SYNTAX  Counter
        ACCESS  read-only
        STATUS  mandatory
        DESCRIPTION
                "Number of packets forwarded by the switching entity
                 to the Managemnt Port from nbsMgmtRcvPerfOutPort."

        ::= { nbsMgmtRcvPerfEntry 3 }

nbsMgmtRcvPerfFwdBytes  OBJECT-TYPE
        SYNTAX  Counter
        ACCESS  read-only
        STATUS  mandatory
        DESCRIPTION
                "Number of bytes forwarded by the switching entity
                 to the Managemnt Port from nbsMgmtRcvPerfOutPort."

        ::= { nbsMgmtRcvPerfEntry 4 }
--
-- *******************************************************************
-- The nbsMgmtXmtPerfTable containes the number of packets and bytes
-- forwarded from the Management Port to other ports of the
-- switch.
-- *******************************************************************

nbsMgmtXmtPerfTable OBJECT-TYPE
        SYNTAX  SEQUENCE OF NbsMgmtXmtPerfEntry
        ACCESS  not-accessible
        STATUS  mandatory
        DESCRIPTION
                "A list of the NBase port specific switching performance
                 statistics. Contains the number of packets and bytes
                 forwarded from the Management Port to all the
                 nbsMgmtXmtPerfOutPort ports.
                 Number of entries is given by nbsSysPortsNumber"

        ::= { nbsSwitchPerf 5 }

nbsMgmtXmtPerfEntry     OBJECT-TYPE
        SYNTAX  NbsMgmtXmtPerfEntry
        ACCESS  not-accessible
        STATUS  mandatory
        DESCRIPTION
                "Contains the NBase specific Switching Performance statistics
                 for a port. Contains the number of packets and bytes
                 forwarded from the Management Port to all the
                 nbsMgmtXmtPerfOutPort ports.
                 The number of rows/entries is fixed. A row/entry may not be
                 created or deleted"

        INDEX { nbsMgmtXmtPerfOutPort }

        ::= { nbsMgmtXmtPerfTable  1 }

NbsMgmtXmtPerfEntry ::= SEQUENCE {

        nbsMgmtXmtPerfOutPort      INTEGER,
        nbsMgmtXmtPerfFwdPkts      Counter,
        nbsMgmtXmtPerfFwdBytes     Counter
        }

nbsMgmtXmtPerfOutPort  OBJECT-TYPE
        SYNTAX  INTEGER
        ACCESS  read-only
        STATUS  mandatory
        DESCRIPTION
                "A unique value for each switched port. Its value ranges from
                 1 to the value of nbsSysPortsNumber."

        ::= { nbsMgmtXmtPerfEntry 2 }

nbsMgmtXmtPerfFwdPkts  OBJECT-TYPE
        SYNTAX  Counter
        ACCESS  read-only
        STATUS  mandatory
        DESCRIPTION
                "Number of packets forwarded by the switching entity
                 from the Managemnt Port to nbsMgmtXmtPerfOutPort."

        ::= { nbsMgmtXmtPerfEntry 3 }

nbsMgmtXmtPerfFwdBytes  OBJECT-TYPE
        SYNTAX  Counter
        ACCESS  read-only
        STATUS  mandatory
        DESCRIPTION
                "Number of bytes forwarded by the switching entity
                 from the Managemnt Port to nbsMgmtXmtPerfOutPort."

        ::= { nbsMgmtXmtPerfEntry 4 }
-- ************************************************************
-- End of the NBase Performance Switching Statistics Group
-- ************************************************************
-- ************************************************************
--
-- Objects in the NBase Traps Group
--
-- These objects are general for all the NBase Ethernet Switches
-- The objects provide the specific traps for the NBase devices.
-- ************************************************************

-- ************************************************************
-- End of the NBase Traps Group
-- ************************************************************

-- ************************************************************
--
-- Objects in the NBase MegaSwitch Switching Data Base Group
--
-- These objects are general for all the NBase Ethernet Switches
-- The objects provide the information regarding the Switching
-- Data Base - running and permanent.
-- ************************************************************

nbsMegaSwRunDb  OBJECT IDENTIFIER ::= { nbsMegaSwDb 1 }
                        -- Current Switching Data Base
                        --
nbsMegaSwPermDb OBJECT IDENTIFIER ::= { nbsMegaSwDb 2 }
                        -- Permanent Switching Data Base
--
-- **************************************
-- The Running Forwarding Data Base
-- **************************************
-- *****************************************************************
-- The Running Forwarding Data Base accessed according to the index
-- *****************************************************************
nbsMegaSwRunDbTable OBJECT-TYPE
        SYNTAX  SEQUENCE OF NbsMegaSwRunDbEntry
        ACCESS  not-accessible
        STATUS  mandatory
        DESCRIPTION
                "A list of the current running Learn Table entries.
                 Number of entries is given by nbsSysSwitchDBSize"

        ::= { nbsMegaSwRunDb 1 }

nbsMegaSwRunDbEntry      OBJECT-TYPE
        SYNTAX  NbsMegaSwRunDbEntry
        ACCESS  not-accessible
        STATUS  mandatory
        DESCRIPTION
                "Contains the NBase specific Learn Table entry information.
                 The information is specific to a MAC Address.
                 The number of rows/entries is fixed. A row/entry may not be
                 created or deleted"

        INDEX { nbsMegaSwRunDbIndex }

        ::= { nbsMegaSwRunDbTable  1 }

NbsMegaSwRunDbEntry ::= SEQUENCE {

        nbsMegaSwRunDbIndex     INTEGER,
        nbsMegaSwRunDbStatus    INTEGER,
        nbsMegaSwRunDbAddr      MacAddress,
        nbsMegaSwRunDbType      INTEGER,
        nbsMegaSwRunDbDport     INTEGER
        }

nbsMegaSwRunDbIndex  OBJECT-TYPE
        SYNTAX  INTEGER
        ACCESS  read-only
        STATUS  mandatory
        DESCRIPTION
                "A unique value for each Current Switching Data Base Entry.
                 Its value ranges from 1 to the value of nbsSysSwitchDBSize"

        ::= { nbsMegaSwRunDbEntry 1 }

nbsMegaSwRunDbStatus  OBJECT-TYPE
        SYNTAX  INTEGER {
                invalid         (1),
                system          (2),
                permanent       (3),
                deleteOnReset   (4),
                deleteOnTimeout (5)

                }
        ACCESS  read-only
        STATUS  mandatory
        DESCRIPTION
                "This object indicates the status of this entry.
                 The default value is deleteOnTimeout(4).

                 invalid(1) - this value indicates a inactive entry.
			   The entry may receive this value either
			   through a management SET operation or by
			   being aged out.
                 system(2) - this value indicates a system entry,
			   i.e. a system address, the broadcast address
			   or the spanning tree group address.
                 permanent(3) - this entry is currently in use and will
                           remain so after the next reset of the switch.
			   This value is legal only for customFilter(2)
			   types of entries. Setting a virtualFilter(1)
			   entry to be permanent(2) will result in a
			   deleteOnReset(3) status.
		 deleteOnReset(4) - this entry is currently in use and will
                           remain so until the next reset of the switch.
                 deleteOnTimeout(5) - this entry is currently in use and will
                           remain so until it is aged out."

        ::= { nbsMegaSwRunDbEntry 2 }

nbsMegaSwRunDbAddr  OBJECT-TYPE
        SYNTAX  MacAddress
        ACCESS  read-only
        STATUS  mandatory
        DESCRIPTION
                "The destination MAC Address in a frame to which this entry
                 forwarding information applies. This object can take the
                 value of a unicast address, a group address or the
                 broadcast address."

        ::= { nbsMegaSwRunDbEntry 3 }

nbsMegaSwRunDbType  OBJECT-TYPE
        SYNTAX  INTEGER {
                virtualFilter(1),
                customFilter (2)
                }
        ACCESS  read-only
        STATUS  mandatory
        DESCRIPTION
                "This object indicates the type of the entry and its adjacent
                 filter.
                 The default value is VirtualFilter(1).

                 virtualFilter(1) - this entry was either learned by the
                           switch or was manually added through a management
                           SET command.
                           It has a set of virtual set of filters associated
                           with it. See Virtual Filters definitions.


                 customFilter (2) - this entry was manually added through a
                           management SET command. This kind of entry
                           is similar to the permanent dot1dStaticEntry.
                           It has a set of destination filters/bitmaps
                           associated with it for each input port"

        ::= { nbsMegaSwRunDbEntry 4 }

nbsMegaSwRunDbDport  OBJECT-TYPE
        SYNTAX  INTEGER
        ACCESS  read-only
        STATUS  mandatory
        DESCRIPTION
                "The port to which a frame containing the entry Mac Address
                 should be forwarded, if it is not overwritten by a Virtual
                 Filter. This object is rellevant for virtualFilter(1) type
                 of entries only"

        ::= { nbsMegaSwRunDbEntry 5 }
--
-- *********************************************************************
-- The Running Forwarding Data Base - Filters attached to MAC Addresses
--
--	The Forwarding Data Base contains a list of MAC Addresses with
--	attached additional forwarding information. Basically there are
--	two types of additional forwarding information : Virtual Filters
--	and Custom Filters. The Forwarding Data Base is organized
--	hierahically:
--	- addresses learned from the network are forwarded according to
--	  Virtual Filters that default to the incoming port.
--	- Virtual Filter Addresses that are forwarded according to a
--	  Virtual Filter defined by the FilterDport field defined.
--	- Custom Filters Addresses that are forwarded according to a
--	  Custom Filter defined per source port(FilterSport) by the
--	  FilterDmap object.
--
--	Creation of a row is done by creating an entry of type Virtual
--	Filter with the given MAC Address and the provided FilterSport
--	and a Virtual Filter according to the FilterDport value.
--	If the creation is of a Custom Filter entry, the entry is modified
--	by the following SET commands with the CustomFilter type , the
--	provided FilterStatus and the provided FilterDmap for the
--	FilterSport. Note that the FilterSport should be non zero at
--	creation/modification time, i.e. the SET access to the management
--	port filter is not allowed.
--
--	Setting a Virtual Filter Status to permanent value wiil be ignored.
--	Instead the filterStatus will receive a delelteOnReset value.
--	Creation of a permanent Virtual Filter should be done through
--	the Permanent Data Base access.
-- **********************************************************************

nbsMegaSwRunFilterTable  OBJECT-TYPE

        SYNTAX  SEQUENCE OF NbsMegaSwRunFilterEntry
        ACCESS  not-accessible
        STATUS  mandatory
        DESCRIPTION
                "The Switching Data Base :
		 a list of destination filters associated with each
                 MAC Address in the Switching Data Base. A destination
                 filter exists for every possible input port.
                 Number of entries is given by nbsSysPortsNumber plus
                 one for the management port. Legal number of entries
                 are 9 for NH208-AT , 16 for NH215-AT and 8 for NH2007"

        ::= { nbsMegaSwRunDb 2 }

nbsMegaSwRunFilterEntry     OBJECT-TYPE
        SYNTAX  NbsMegaSwRunFilterEntry
        ACCESS  not-accessible
        STATUS  mandatory
        DESCRIPTION
                "Contains the destination filter associated with a MAC Address
                 in the Switching Data Base, when the packet was inputed
                 through nbsMegaSwRunFilterSport port."

        INDEX { nbsMegaSwRunFilterAddr, nbsMegaSwRunFilterSport }

        ::= { nbsMegaSwRunFilterTable  1 }

NbsMegaSwRunFilterEntry ::= SEQUENCE {

        nbsMegaSwRunFilterStatus INTEGER,
        nbsMegaSwRunFilterAddr   MacAddress,
        nbsMegaSwRunFilterType   INTEGER,
        nbsMegaSwRunFilterDport  INTEGER,
        nbsMegaSwRunFilterSport  INTEGER,
        nbsMegaSwRunFilterDmap   OCTET STRING
        }

nbsMegaSwRunFilterStatus  OBJECT-TYPE
        SYNTAX  INTEGER {
                invalid         (1),
                system          (2),
                permanent       (3),
                deleteOnReset   (4),
                deleteOnTimeout (5)

                }
        ACCESS  read-write
        STATUS  mandatory
        DESCRIPTION
                "This object indicates the status of this entry.
                 The default value is deleteOnTimeout(4).

                 invalid(1) - this value indicates a inactive entry.
			   The entry may receive this value either
			   through a management SET operation or by
			   being aged out. Setting this value will delete
			   the entry from the forwarding database.
                 system(2) - this value indicates a system entry,
			   i.e. a system address, the broadcast address
			   or the spanning tree group address.
                 permanent(3) - this entry is currently in use and will
                           remain so after the next reset of the switch.
			   This value is allowed for entries of type
			   customFilter(2). For virtualFilter(1) type
			   setting the status to permanent will result
			   in a deleteOnReset(3) status.
                 deleteOnReset(4) - this entry is currently in use and will
                           remain so until the next reset of the switch.
                 deleteOnTimeout(5) - this entry is currently in use and will
                           remain so until it is aged out."
	DEFVAL { deleteOnReset }

        ::= { nbsMegaSwRunFilterEntry 1 }

nbsMegaSwRunFilterAddr  OBJECT-TYPE
        SYNTAX  MacAddress
        ACCESS  read-write
        STATUS  mandatory
        DESCRIPTION
                "The destination MAC Address in a frame to which this entry
                 forwarding information applies. This object can take the
                 value of a unicast address, a group address or the
                 broadcast address. This is the same as the nbsMegaSwRunDbAddr
                 field in nbsMegaSwRunDbEntry"

        ::= { nbsMegaSwRunFilterEntry 2 }

nbsMegaSwRunFilterType  OBJECT-TYPE
        SYNTAX  INTEGER {
                virtualFilter(1),
                customFilter (2)
                }
        ACCESS  read-write
        STATUS  mandatory
        DESCRIPTION
                "This object indicates the type of the entry and its adjacent
                 filter.
                 The default value is VirtualFilter(1).

                 virtualFilter(1) - this entry was either learned by the
                           switch or was manually added through a management
                           SET command.
                           It has a set of virtual set of filters associated
                           with it. See Virtual Filters definitions.


                 customFilter (2) - this entry was manually added through a
                           management SET command. This kind of entry
                           is similar to the permanent dot1dStaticEntry.
                           It has a set of destination filters/bitmaps
                           associated with it for each input port"
	DEFVAL { virtualFilter }

        ::= { nbsMegaSwRunFilterEntry 3 }

nbsMegaSwRunFilterDport  OBJECT-TYPE
        SYNTAX  INTEGER
        ACCESS  read-write
        STATUS  mandatory
        DESCRIPTION
                "The port to which a frame containing the entry Mac Address
                 would be forwarded, if it is not overwritten by a Virtual
                 Filter. This object is rellevant for virtualFilter(1) type
                 of entries only"
	DEFVAL { 0 }

        ::= { nbsMegaSwRunFilterEntry 4 }

nbsMegaSwRunFilterSport  OBJECT-TYPE
        SYNTAX  INTEGER
        ACCESS  read-write
        STATUS  mandatory
        DESCRIPTION
                "A unique value that shows for which input/source port
                 the adjacent filter/dport map should be used.
		 At creation time this object should not be given the
		 value 0. It's range should be 1 to the number of ports"

        ::= { nbsMegaSwRunFilterEntry 5 }

nbsMegaSwRunFilterDmap  OBJECT-TYPE
        SYNTAX  OCTET STRING
        ACCESS  read-write
        STATUS  mandatory
        DESCRIPTION
                "The Destination Port Bit Map = the set of ports
                 to which the incoming packet is to be forwarded.
                 Each octet within the value of this object specifies
                 a set of eight ports, with the first octet specifying
                 ports 0 through 7, the second octet specifying ports 8
                 through 15, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant). Port 0 means the SNMP agent.
		 The default value of this object is a string of
		 ones of appropriate length, except for the source port bit
		 and the SNMP agent port(port 0).
		 Modifing this fields is rellevant only for customFilter(2)
		 type of entries.
		 Deleting the filter for a specific source port
		 means writing the default value - all 1's."
	DEFVAL { '1111111111111111'b}

        ::= { nbsMegaSwRunFilterEntry 6 }

--
-- ***********************************************************
--  The Virtual Connectivity Matrix
-- ***********************************************************

nbsMegaSwSvlanConnectTable  OBJECT-TYPE
        SYNTAX  SEQUENCE OF NbsMegaSwSvlanConnectEntry
        ACCESS  not-accessible
        STATUS  mandatory
        DESCRIPTION
		"A set of octet strings/filters showing the
		 Virtual LANs Connectivity Matrix.
                 A filter exists for every possible input port.
                 Number of entries is given by nbsSysPortsNumber plus
                 one for the management port. Legal number of entries
                 are 9 for NH208-AT, 16 for NH215-AT and 8 for NH2007"

        ::= { nbsMegaSwRunDb 3 }

nbsMegaSwSvlanConnectEntry  OBJECT-TYPE
        SYNTAX  NbsMegaSwSvlanConnectEntry
        ACCESS  not-accessible
        STATUS  mandatory
        DESCRIPTION
                "Contains the destination filter associated with
                 the input port nbsMegaSwSvlanConnectSport."

        INDEX { nbsMegaSwSvlanConnectSport }

        ::= { nbsMegaSwSvlanConnectTable  1 }

NbsMegaSwSvlanConnectEntry ::= SEQUENCE {

          nbsMegaSwSvlanConnectSport	INTEGER,
          nbsMegaSwSvlanConnectDport	OCTET STRING

        }

nbsMegaSwSvlanConnectSport  OBJECT-TYPE
        SYNTAX  INTEGER
        ACCESS  read-only
        STATUS  mandatory
        DESCRIPTION
                "A unique value that shows for which input/source port
                 the adjacent filter/dport map should be used."

        ::= { nbsMegaSwSvlanConnectEntry 1 }

nbsMegaSwSvlanConnectDport  OBJECT-TYPE
        SYNTAX  OCTET STRING
        ACCESS  read-only
        STATUS  mandatory
        DESCRIPTION
                "The Destination Port Bit Map = the set of ports
                 to which the incoming packet is to be forwarded.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit.
		 Deleteing the filter for a specific source port
		 means writing the default value - all 1's."

        ::= { nbsMegaSwSvlanConnectEntry 2 }

--
-- ********************************************
-- The Running Security Virtual Lans Data Base
-- ********************************************

nbsMegaSwRunSvlanDb OBJECT IDENTIFIER  ::= { nbsMegaSwRunDb 4 }

nbsMegaSwRunSvlanMaxNum  OBJECT-TYPE
        SYNTAX  INTEGER
        ACCESS  read-only
        STATUS  mandatory
        DESCRIPTION
                "Maximum number of Security Virtual LANs that are supported"

        ::= { nbsMegaSwRunSvlanDb 1 }

nbsMegaSwRunSvlanTable OBJECT-TYPE

        SYNTAX  SEQUENCE OF NbsMegaSwRunSvlanEntry
        ACCESS  not-accessible
        STATUS  mandatory
        DESCRIPTION
                "A list of the current Security Virtual LANs defined.
                 Number of entries is given by nbsMegaSwRunSvlanMaxNum"

        ::= { nbsMegaSwRunSvlanDb 2 }

nbsMegaSwRunSvlanEntry  OBJECT-TYPE
        SYNTAX  NbsMegaSwRunSvlanEntry
        ACCESS  not-accessible
        STATUS  mandatory
        DESCRIPTION
                "Contains the descriptor of a Security Virtual LAN."

        INDEX { nbsMegaSwRunSvlanIndex }

        ::= { nbsMegaSwRunSvlanTable 1 }

NbsMegaSwRunSvlanEntry ::= SEQUENCE {

        nbsMegaSwRunSvlanIndex     INTEGER,
        nbsMegaSwRunSvlanStatus    INTEGER,
        nbsMegaSwRunSvlanList      OCTET STRING,
        nbsMegaSwRunSvlanIsvlanFlag INTEGER

        }

nbsMegaSwRunSvlanIndex  OBJECT-TYPE
        SYNTAX  INTEGER
        ACCESS  read-only
        STATUS  mandatory
        DESCRIPTION
                "The serial number of this entry in the nbsMegaSwRunSvlanTbl.
                 It may range from 1 to the value of nbsMegaSwRunSvlanMaxNum."

        ::= { nbsMegaSwRunSvlanEntry 1 }

nbsMegaSwRunSvlanStatus  OBJECT-TYPE
        SYNTAX  INTEGER {
                valid  (1),     -- the entry is valid and active
                invalid(2)      -- the entry is invalid
        }
        ACCESS  read-write
        STATUS  mandatory
        DESCRIPTION
                "The object is used to create/delete entries in the
                 nbsMegaSwRunSvlanTable table.

                 Setting this value to invalid(2) for a certain
                 nbsMegaSwRunSvlanIndex, deletes this entry.

                 To create a new entry a SET PDU with the
                 nbsMegaSwRunSvlanList and nbsMegaSwRunSvlanStatus=valid(1)
                 objects is required."

        ::= { nbsMegaSwRunSvlanEntry 2 }

nbsMegaSwRunSvlanList  OBJECT-TYPE
        SYNTAX  OCTET STRING
        ACCESS  read-write
        STATUS  mandatory
        DESCRIPTION
                "Contains the list of the ports grouped together in this
                 Security Virtual LAN. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit."
	DEFVAL { '1111111111111111'b}


        ::= { nbsMegaSwRunSvlanEntry 3 }

nbsMegaSwRunSvlanIsvlanFlag    OBJECT-TYPE
	SYNTAX  INTEGER
        ACCESS  read-only
        STATUS  mandatory
        DESCRIPTION
		"This object indicates if this 'intra-switch' VLAN
		 entry was added by defining an inter-switch VLAN.
		 The entries that have this flag TRUE may not be
		 edited using this access. "
        ::= { nbsMegaSwRunSvlanEntry 4 }

-- ************************************************************
-- The Running InterSwitch Security Virtual Lans Data Base
-- ************************************************************

nbsMegaSwRunIsvlanMaxNum  OBJECT-TYPE
        SYNTAX  INTEGER
        ACCESS  read-only
        STATUS  mandatory
        DESCRIPTION
                "Maximum number of InterSwitch Security Virtual LANs that
	          are supported"

        ::= { nbsMegaSwRunSvlanDb 3 }

nbsMegaSwRunIsvlanTable OBJECT-TYPE

        SYNTAX  SEQUENCE OF NbsMegaSwRunIsvlanEntry
        ACCESS  not-accessible
        STATUS  mandatory
        DESCRIPTION
                "A list of the current InetrSwitch Security Virtual LANs
                 defined. Number of entries is given by nbsMegaSwRunSvlanMaxNum"

        ::= { nbsMegaSwRunSvlanDb 4 }

nbsMegaSwRunIsvlanEntry  OBJECT-TYPE
        SYNTAX  NbsMegaSwRunIsvlanEntry
        ACCESS  not-accessible
        STATUS  mandatory
        DESCRIPTION
                "Contains the descriptor of a InterSwitch Security Virtual LAN."

        INDEX { nbsMegaSwRunIsvlanIndex }

        ::= { nbsMegaSwRunIsvlanTable 1 }


NbsMegaSwRunIsvlanEntry ::= SEQUENCE {

        nbsMegaSwRunIsvlanIndex     INTEGER,
        nbsMegaSwRunIsvlanStatus    INTEGER,
        nbsMegaSwRunIsvlanList      OCTET STRING,
	nbsMegaSwRunIsvlanName	    DisplayString,
	nbsMegaSwRunIsvlanTag	    INTEGER,
	nbsMegaSwRunIsvlanVlanIndex INTEGER

        }

nbsMegaSwRunIsvlanIndex  OBJECT-TYPE
        SYNTAX  INTEGER
        ACCESS  read-only
        STATUS  mandatory
        DESCRIPTION
                "The serial number of this entry in the nbsMegaSwRunIsvlanTbl.
                 It may range from 1 to the value of nbsMegaSwRunIsvlanMaxNum."

        ::= { nbsMegaSwRunIsvlanEntry 1 }

nbsMegaSwRunIsvlanStatus  OBJECT-TYPE
        SYNTAX  INTEGER {
                valid  (1),     -- the entry is valid and active
		invalid(2),     -- the entry is invalid           (ykfix33 - 1.03.00)
		mcast(3)      	-- the entry is of Multicast type (ykfix33 - 1.03.00)
	}
        ACCESS  read-write
        STATUS  mandatory
        DESCRIPTION
                "The object is used to create/delete entries in the
                 nbsMegaSwRunIsvlanTable table.

                 Setting this value to invalid(2) for a certain
                 nbsMegaSwRunIsvlanIndex, deletes this entry.

                 To create a new entry a SET PDU with the
                 nbsMegaSwRunIsvlanList and nbsMegaSwRunIsvlanStatus=valid(1)
		 objects is required.                                         -- ykfix33 - 1.03.00
		 Vlans with mcast(3) status are created by IGMP application   -- ykfix33 - 1.03.00
		 in runtime and have tags from 3001 till 4095.                -- ykfix33 - 1.03.00
		 This value is only for GET SNMP command."                    -- ykfix33 - 1.03.00

        ::= { nbsMegaSwRunIsvlanEntry 2 }

nbsMegaSwRunIsvlanList  OBJECT-TYPE
        SYNTAX  OCTET STRING
        ACCESS  read-write
        STATUS  mandatory
        DESCRIPTION
                "Contains the list of the ports grouped together in this
                 Security Virtual LAN. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit."
	DEFVAL { '1111111111111111'b}


        ::= { nbsMegaSwRunIsvlanEntry 3 }

nbsMegaSwRunIsvlanName	OBJECT-TYPE
	SYNTAX  DisplayString (SIZE(0..15))
        ACCESS  read-write
        STATUS  mandatory
        DESCRIPTION
		"Contains an optional name for the VLAN."

        ::= { nbsMegaSwRunIsvlanEntry 4 }

nbsMegaSwRunIsvlanTag    OBJECT-TYPE
	SYNTAX  INTEGER
        ACCESS  read-write
        STATUS  mandatory
        DESCRIPTION
               "A 12 bit Port VLAN Identifier for this Port.
                0 - The Null VLAN ID.used when the Tag Header contains
                    only user_priority information;  No VLAN
                    identifier is present in the frame. This number is
                    not allowed here.
                1 - The Default PVID value used for tagging frames
                    through a Bridge Port.  The PVID used for tagging
		    of frames can be changed by management.
		    MegaSwitch II ISVLAN card supports up to 8 bits, i.e.
		    values of 0..256. "
       DEFVAL  { 1 }
        ::= { nbsMegaSwRunIsvlanEntry 5 }

nbsMegaSwRunIsvlanVlanIndex   OBJECT-TYPE
	SYNTAX  INTEGER
        ACCESS  read-only
        STATUS  mandatory
        DESCRIPTION
		"Contains an index in the nbsMegaSwRunSvlanTable for this
	         InterSwitch VLAN."
        ::= { nbsMegaSwRunIsvlanEntry 6 }

--
-- **********************************************
-- The Running Virtual Broadcast Domain Data Base
-- **********************************************

nbsMegaSwRunVbcDb  OBJECT IDENTIFIER ::= { nbsMegaSwRunDb 5 }

nbsMegaSwRunVbcMaxNum  OBJECT-TYPE
        SYNTAX  INTEGER
        ACCESS  read-only
        STATUS  mandatory
        DESCRIPTION
                "Maximum number of Virtual Broadcast Domains
                 that are supported"

        ::= { nbsMegaSwRunVbcDb 1 }

nbsMegaSwRunVbcTable OBJECT-TYPE
        SYNTAX  SEQUENCE OF NbsMegaSwRunVbcEntry
        ACCESS  not-accessible
        STATUS  mandatory
        DESCRIPTION
                "A list of the current Virtual Broadcast Domains defined.
                 Number of entries is given by nbsMegaSwRunVbcMaxNum"

        ::= { nbsMegaSwRunVbcDb 2 }

nbsMegaSwRunVbcEntry  OBJECT-TYPE
        SYNTAX  NbsMegaSwRunVbcEntry
        ACCESS  not-accessible
        STATUS  mandatory
        DESCRIPTION
                "Contains the list of ports included in a Virtual Broadcast
                Domain."

        INDEX { nbsMegaSwRunVbcIndex }

        ::= { nbsMegaSwRunVbcTable 1 }

NbsMegaSwRunVbcEntry ::= SEQUENCE {

        nbsMegaSwRunVbcIndex    INTEGER,
        nbsMegaSwRunVbcStatus   INTEGER,
        nbsMegaSwRunVbcList     OCTET STRING

        }

nbsMegaSwRunVbcIndex  OBJECT-TYPE
        SYNTAX  INTEGER
        ACCESS  read-only
        STATUS  mandatory
        DESCRIPTION
                "The serial number of this entry in the nbsMegaSwRunVbcTbl.
                 It may range from 1 to the value of nbsMegaSwRunVbcMaxNum."

        ::= { nbsMegaSwRunVbcEntry 1 }

nbsMegaSwRunVbcStatus  OBJECT-TYPE
        SYNTAX  INTEGER {
                valid  (1),     -- the entry is valid and active
                invalid(2)      -- the entry is invalid
        }
        ACCESS  read-write
        STATUS  mandatory
        DESCRIPTION
                "The object is used to create/delete entries in the
                 nbsMegaSwRunVbcTable table.

                 Setting this value to invalid(2) for a certain
                 nbsMegaSwRunVbcIndex, deletes this entry.

                 To create a new entry a SET PDU with the
                 nbsMegaSwRunVbcList and nbsMegaSwRunVbcStatus=valid(1)
                 objects is required."

        ::= { nbsMegaSwRunVbcEntry 2 }

nbsMegaSwRunVbcList  OBJECT-TYPE
        SYNTAX  OCTET STRING
        ACCESS  read-write
        STATUS  mandatory
        DESCRIPTION
                "Contains the list of the ports grouped together in this
                 Virtual Broadcast Domain. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit."
	DEFVAL { '1111111111111111'b}

        ::= { nbsMegaSwRunVbcEntry 3 }

--
-- ********************************************
-- The Running Virtual Monitoring Group
-- ********************************************

nbsMegaSwVmon OBJECT IDENTIFIER  ::= { nbsMegaSwRunDb 6 }

nbsMegaSwVmonMonitorPort  OBJECT-TYPE
        SYNTAX  INTEGER
        ACCESS  read-write
        STATUS  mandatory
        DESCRIPTION
                "The port containing the Monitor Probe/Lan Analyser.
                 Its value is in the range 1 to nbsSysPortsNumber.
                 After system reset its value will be zero, signfying
                 an unitialized Virtual Monitor Capability."

        ::= { nbsMegaSwVmon 1 }

nbsMegaSwVmonMonitrdPort  OBJECT-TYPE
        SYNTAX  INTEGER
        ACCESS  read-write
        STATUS  mandatory
        DESCRIPTION
                "The port to be monitored.
                 Its value is in the range 1 to nbsSysPortsNumber.
                 After system reset its value will be zero, signfying
                 an unitialized Virtual Monitor Capability."

        ::= { nbsMegaSwVmon 2 }

nbsMegaSwVmonStatus  OBJECT-TYPE
        SYNTAX  INTEGER {
                nonInit (1),    -- the above params are not initialized
                startMon(2),    -- start the monitoring process/running
                stopMon (3)     -- stop  the monitoring process/idle
        }
        ACCESS  read-write
        STATUS  mandatory
        DESCRIPTION
                "The status of the monitoring process.
                 It allows to poll the state of the monitoring process - GET.
                 Setting this object to startMon(3) value will start the
                 monitoring process, unless the system is not initialized in
                 nonInit(1) state.
                 Setting this object to stopMon(3) value will stop the
                 monitoring process, if any active, bringing it to idle.
                 Setting this object to nonInit(3) value is illegal.
                 This value is for GET operation only."

        ::= { nbsMegaSwVmon 3 }

-- *****************************************
-- End of the Running Forwarding Data Base
-- *****************************************
--
-- **************************************
-- The Permanent Forwarding Data Base
-- **************************************
--
-- ********************************************
-- Note that permanent customFiters(2) may be
-- added by creating a permanent(2) row in the
-- nbsMegaSwRunFilterTablestatus table.
-- ********************************************
--
-- ********************************************
-- The Permanent Security Virtual Lans Data Base
-- *********************************************

nbsMegaSwPermSvlanDb OBJECT IDENTIFIER ::= { nbsMegaSwPermDb 1 }

nbsMegaSwPermSvlanMaxNum  OBJECT-TYPE
        SYNTAX  INTEGER
        ACCESS  read-only
        STATUS  mandatory
        DESCRIPTION
                "Maximum number of Security Virtual LANs that are supported"

        ::= { nbsMegaSwPermSvlanDb 1 }

nbsMegaSwPermSvlanTable OBJECT-TYPE
        SYNTAX  SEQUENCE OF NbsMegaSwPermSvlanEntry
        ACCESS  not-accessible
        STATUS  mandatory
        DESCRIPTION
                "A list of the current Security Virtual LANs defined.
                 Number of entries is given by nbsMegaSwPermSvlanMaxNum"

        ::= { nbsMegaSwPermSvlanDb 2 }

nbsMegaSwPermSvlanEntry  OBJECT-TYPE
        SYNTAX  NbsMegaSwPermSvlanEntry
        ACCESS  not-accessible
        STATUS  mandatory
        DESCRIPTION
                "Contains the list of ports included in a Virtual LAN."

        INDEX { nbsMegaSwPermSvlanIndex }

        ::= { nbsMegaSwPermSvlanTable 1 }

NbsMegaSwPermSvlanEntry ::= SEQUENCE {

        nbsMegaSwPermSvlanIndex		INTEGER,
        nbsMegaSwPermSvlanStatus        INTEGER,
        nbsMegaSwPermSvlanList		OCTET STRING
        }

nbsMegaSwPermSvlanIndex  OBJECT-TYPE
        SYNTAX  INTEGER
        ACCESS  read-only
        STATUS  mandatory
        DESCRIPTION
                "The serial number of this entry in the nbsMegaSwPermSvlanTbl.
                 It may range from 1 to the value of nbsMegaSwPermSvlanMaxNum"

        ::= { nbsMegaSwPermSvlanEntry 1 }

nbsMegaSwPermSvlanStatus  OBJECT-TYPE
        SYNTAX  INTEGER {
                valid  (1),     -- the entry is valid and active
                invalid(2)      -- the entry is invalid
        }
        ACCESS  read-write
        STATUS  mandatory
        DESCRIPTION
                "The object is used to create/delete entries in the
                 nbsMegaSwPermSvlanTable table.

                 Setting this value to invalid(2) for a certain
                 nbsMegaSwPermSvlanIndex, deletes this entry.

                 To create a new entry a SET PDU with the
                 nbsMegaSwPermSvlanList and nbsMegaSwPermSvlanStatus set
                 to valid(1) objects is required."

        ::= { nbsMegaSwPermSvlanEntry 2 }

nbsMegaSwPermSvlanList  OBJECT-TYPE
        SYNTAX  OCTET STRING
        ACCESS  read-write
        STATUS  mandatory
        DESCRIPTION
                "Contains the list of the ports grouped together in this
                 Security Virtual LAN. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit."

	DEFVAL { '1111111111111111'b}

        ::= { nbsMegaSwPermSvlanEntry 3 }


-- ************************************************************
-- The Permananet InterSwitch Security Virtual Lans Data Base
-- ************************************************************

nbsMegaSwPermIsvlanMaxNum  OBJECT-TYPE
        SYNTAX  INTEGER
        ACCESS  read-only
        STATUS  mandatory
        DESCRIPTION
                "Maximum number of InterSwitch Security Virtual LANs that
	          are supported"

        ::= { nbsMegaSwPermSvlanDb 3 }

nbsMegaSwPermIsvlanTable OBJECT-TYPE

        SYNTAX  SEQUENCE OF NbsMegaSwPermIsvlanEntry
        ACCESS  not-accessible
        STATUS  mandatory
        DESCRIPTION
                "A list of the current InetrSwitch Security Virtual LANs
                 defined. Number of entries is given by nbsMegaSwPermSvlanMaxNum"

        ::= { nbsMegaSwPermSvlanDb 4 }

nbsMegaSwPermIsvlanEntry  OBJECT-TYPE
        SYNTAX  NbsMegaSwPermIsvlanEntry
        ACCESS  not-accessible
        STATUS  mandatory
        DESCRIPTION
                "Contains the descriptor of a InterSwitch Security Virtual LAN."

        INDEX { nbsMegaSwPermIsvlanIndex }

        ::= { nbsMegaSwPermIsvlanTable 1 }


NbsMegaSwPermIsvlanEntry ::= SEQUENCE {

        nbsMegaSwPermIsvlanIndex     INTEGER,
        nbsMegaSwPermIsvlanStatus    INTEGER,
        nbsMegaSwPermIsvlanList      OCTET STRING,
	nbsMegaSwPermIsvlanName	     DisplayString,
	nbsMegaSwPermIsvlanTag	     INTEGER

        }

nbsMegaSwPermIsvlanIndex  OBJECT-TYPE
        SYNTAX  INTEGER
        ACCESS  read-only
        STATUS  mandatory
        DESCRIPTION
                "The serial number of this entry in the nbsMegaSwPermIsvlanTbl.
                 It may range from 1 to the value of nbsMegaSwPermIsvlanMaxNum."

        ::= { nbsMegaSwPermIsvlanEntry 1 }

nbsMegaSwPermIsvlanStatus  OBJECT-TYPE
        SYNTAX  INTEGER {
                valid  (1),     -- the entry is valid and active
		invalid(2),     -- the entry is invalid           (ykfix33 - 1.03.00)
		mcast(3)      	-- the entry is of Multicast type (ykfix33 - 1.03.00)
	}
        ACCESS  read-write
        STATUS  mandatory
        DESCRIPTION
                "The object is used to create/delete entries in the
                 nbsMegaSwPermIsvlanTable table.

                 Setting this value to invalid(2) for a certain
                 nbsMegaSwPermIsvlanIndex, deletes this entry.

                 To create a new entry a SET PDU with the
                 nbsMegaSwPermIsvlanList and nbsMegaSwPermIsvlanStatus=valid(1)
		 objects is required.                                         -- ykfix33 - 1.03.00
		 Vlans with mcast(3) status are created by IGMP application   -- ykfix33 - 1.03.00
		 in runtime and have tags from 3001 till 4095.                -- ykfix33 - 1.03.00
		 This value is only for GET SNMP command."                    -- ykfix33 - 1.03.00

        ::= { nbsMegaSwPermIsvlanEntry 2 }

nbsMegaSwPermIsvlanList  OBJECT-TYPE
        SYNTAX  OCTET STRING
        ACCESS  read-write
        STATUS  mandatory
        DESCRIPTION
                "Contains the list of the ports grouped together in this
                 Security Virtual LAN. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  (Note that the setting of the bit
                 corresponding to the port from which a frame is
                 received is irrelevant.)  The default value of
                 this object is a string of ones of appropriate
                 length, except for the source port bit."
	DEFVAL { '1111111111111111'b}


        ::= { nbsMegaSwPermIsvlanEntry 3 }

nbsMegaSwPermIsvlanName	OBJECT-TYPE
	SYNTAX  DisplayString (SIZE(0..15))
        ACCESS  read-write
        STATUS  mandatory
        DESCRIPTION
		"Contains an optional name for the VLAN."

        ::= { nbsMegaSwPermIsvlanEntry 4 }

nbsMegaSwPermIsvlanTag    OBJECT-TYPE
	SYNTAX  INTEGER
        ACCESS  read-write
        STATUS  mandatory
        DESCRIPTION
               "A 12 bit Port VLAN Identifier for this Port.
                0 - The Null VLAN ID.used when the Tag Header contains
                    only user_priority information;  No VLAN
                    identifier is present in the frame. This number is
                    not allowed here.
                1 - The Default PVID value used for tagging frames
                    through a Bridge Port.  The PVID used for tagging
		    of frames can be changed by management.
		    MegaSwitch II ISVLAN card supports up to 8 bits, i.e.
		    values of 0..256. "

        ::= { nbsMegaSwPermIsvlanEntry 5 }

--
-- ************************************************
-- The Permanent Virtual Broadcast Domain Data Base
-- ************************************************

nbsMegaSwPermVbcDb OBJECT IDENTIFIER   ::= { nbsMegaSwPermDb 2 }

nbsMegaSwPermVbcMaxNum  OBJECT-TYPE
        SYNTAX  INTEGER
        ACCESS  read-only
        STATUS  mandatory
        DESCRIPTION
                "Maximum number of Virtual Broadcast Domains
                 that are supported"

        ::= { nbsMegaSwPermVbcDb 1 }

nbsMegaSwPermVbcTable OBJECT-TYPE

        SYNTAX  SEQUENCE OF NbsMegaSwPermVbcEntry
        ACCESS  not-accessible
        STATUS  mandatory
        DESCRIPTION
                "A list of the current Virtual Broadcast Domains defined.
                 Number of entries is given by nbsMegaSwPermVbcMaxNum"

        ::= { nbsMegaSwPermVbcDb 2 }

nbsMegaSwPermVbcEntry  OBJECT-TYPE
        SYNTAX  NbsMegaSwPermVbcEntry
        ACCESS  not-accessible
        STATUS  mandatory
        DESCRIPTION
                "Contains the list of ports included in a Virtual Broadcast
                Domain."

        INDEX { nbsMegaSwPermVbcIndex }

        ::= { nbsMegaSwPermVbcTable 1 }

NbsMegaSwPermVbcEntry ::= SEQUENCE {

        nbsMegaSwPermVbcIndex   INTEGER,
        nbsMegaSwPermVbcStatus  INTEGER,
        nbsMegaSwPermVbcList    OCTET STRING

        }

nbsMegaSwPermVbcIndex  OBJECT-TYPE
        SYNTAX  INTEGER
        ACCESS  read-only
        STATUS  mandatory
        DESCRIPTION
                "The serial number of this entry in the nbsMegaSwPermVbcTbl.
                 It may range from 1 to the value of nbsMegaSwPermVbcMaxNum."

        ::= { nbsMegaSwPermVbcEntry 1 }

nbsMegaSwPermVbcStatus  OBJECT-TYPE
        SYNTAX  INTEGER {
                valid  (1),     -- the entry is valid and active
                invalid(2)      -- the entry is invalid
        }
        ACCESS  read-write
        STATUS  mandatory
        DESCRIPTION
                "The object is used to create/delete entries in the
                 nbsMegaSwPermVbcTable table.

                 Setting this value to invalid(2) for a certain
                 nbsMegaSwPermVbcIndex, deletes this entry.

                 To create a new entry a SET PDU with the
                 nbsMegaSwPermVbcList and nbsMegaSwPermVbcStatus set
                 to valid(1) is required."

        ::= { nbsMegaSwPermVbcEntry 2 }

nbsMegaSwPermVbcList  OBJECT-TYPE
        SYNTAX  OCTET STRING
        ACCESS  read-write
        STATUS  mandatory
        DESCRIPTION
                "Contains the list of the ports grouped together in this
                 Virtual Broadcast Domain. The representation is a bit map.
                 Each octet within the value of this object specifies
                 a set of eight ports, with the first octet specifying
                 ports 1 through 8, the second octet specifying ports 9
                 through 16, etc.  Within each octet, the most
                 significant bit represents the lowest numbered
                 port, and the least significant bit represents the
                 highest numbered port.  Thus, each port of the
                 switch is represented by a single bit within the
                 value of this object.  If that bit has a value of
                 <1> then that port is included in the set of
                 ports; the port is not included if its bit has a
                 value of <0>.  Note that the setting of the bit
                 corresponding to the port from which a frame is
                 received is irrelevant.  The default value of
                 this object is a string of ones of appropriate
                 length, except for the source port bit."

	DEFVAL { '1111111111111111'b}

        ::= { nbsMegaSwPermVbcEntry 3 }


-- ***************************
-- The Permanent Aging Time
-- ***************************

nbsTpPermAgingTime  OBJECT-TYPE
        SYNTAX  INTEGER
        ACCESS  read-write
        STATUS  mandatory
        DESCRIPTION
                "Switching Data Base Aging Time - NVRAM based.
		 Legal values are 1 to 27000."

        ::= { nbsMegaSwPermDb 3 }


END
