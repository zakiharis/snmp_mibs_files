--NextNet Inc.
--Expedience Management Information Base
--December 1999
--This management information base has been derived from:

--Network Working Group                                  M. St. Johns, Ed.
--Request for Comments: 2669                                 @Home Network
--Category: Proposed Standard                                  August 1999

--Network Working Group                                   M. St. Johns, Ed.
--Request for Comments: 2670                                  @Home Network
--Category: Proposed Standard                                   August 1999


   
--        Management Information Base for NextNet Expedience Systems

--Status of this Memo

--   This document is in the works towards first NextNet Expedience release.

--Copyright Notice

--   Copyright (C) NextNet (1999).  All Rights Reserved.

--Abstract

--   This memo defines a portion of the Management Information Base (MIB)
--   for use with network management protocols in the Internet community.
--   In particular, it defines a basic set of managed objects for SNMP-
--   based management of NextNet Expedience Systems.

--   This memo specifies a MIB module in a manner that is compliant to the
--   SNMP SMIv1.  The set of objects are consistent with the
--   SNMP framework and existing SNMP standards.

--   This memo is a product of the Network Software group within the NextNet
--   Engineering Force.

-- Table of Contents

--   1 The SNMP Management Framework ................................... 2
--   2 Glossary ........................................................ 2
--   2.1 NextNet Expedience ............................................ 2
--   2.2 Channel ....................................................... 2
--   2.3 Customer Premise Equipment (CPE) .............................. 2
--   2.4 Base Station System (BSS) ..................................... 2
--   2.5 Codeword ...................................................... 2
--   2.6 Data Packet ................................................... 2
--   2.7 dBmV .......................................................... 3
--   2.8 ............................................................... 3
--   2.9 Downstream .................................................... 3
--   2.10 Head-end router .............................................. 3
--   2.11 MAC Packet ................................................... 3
--   2.12  ............................................................. 3
--   2.13 Slot ......................................................... 3
--   2.14 QPSK ......................................................... 3
--   2.15  ............................................................. 3
--   2.16 RF ........................................................... 3
--   2.17 Symbol-times ................................................. 3
--   2.18 Upstream ..................................................... 3
--   3 Overview ........................................................ 3
--   3.1 Structure of the MIB .......................................... 3
--   4 Definitions ..................................................... 4
--   5 Security Considerations ........................................ 20
--   6 Intellectual Property .......................................... 21
--   7 Full Copyright Statement ....................................... 22

--1.  The SNMP Management Framework

--   The SNMP Management Framework presently consists of five major
--   components:

--   o   An overall architecture, described in RFC 2571 [1].

--   o   Mechanisms for describing and naming objects and events for the
--       purpose of management. The first version of this Structure of
--       Management Information (SMI) is called SMIv1 and described in STD
--       16, RFC 1155 [2], STD 16, RFC 1212 [3] and RFC 1215 [4]. The
--       second version, called SMIv2, is described in STD 58, RFC 2578
--       [5], STD 58, RFC 2579 [6] and STD 58, RFC 2580 [7].

--   o   Message protocols for transferring management information. The
--       first version of the SNMP message protocol is called SNMPv1 and
--       described in RFC 1157 [8]. A second version of the SNMP message
--       protocol, which is not an Internet standards track protocol, is
--       called SNMPv2c and described in RFC 1901 [9] and RFC 1906 [10].
--       The third version of the message protocol is called SNMPv3 and
--       described in RFC 1906 [10], RFC 2572 [11] and RFC 2574 [12].

--   o   Protocol operations for accessing management information. The
--       first set of protocol operations and associated PDU formats is
--       described in STD 15, RFC 1157 [8]. A second set of protocol
--       operations and associated PDU formats is described in RFC 1905
--       [13].

--   o   A set of fundamental applications described in RFC 2573 [14] and
--       the view-based access control mechanism described in RFC 2575
--       [15].

--   Managed objects are accessed via a virtual information store, termed
--   the Management Information Base or MIB.  Objects in the MIB are
--   defined using the mechanisms defined in the SMI.

--   This memo specifies a MIB module that is compliant with the SMIv1.

--2.  Glossary

--   The terms in this document are derived either from Expedience usage,
--   or from the documents associated with the NextNet Expedience Interface
--   Specification process.

--2.1.  NextNet Expedience

--   Two way broadband data communication in MMDS frequence band

--2.2.  Channel

--   A specific frequency allocation with an RF medium, specified by
--   channel width in Hertz (cycles per second) and by center frequency.
--   Within the US MMDS Systems, channels are generally allocated from the
--   2500-2686MHz range.  The typical channel width in the US is 6MHz.

--2.3.  CPE   Customer Premises Equipment.

--   A CPE acts as a "slave" station in a Expedience wireless data
--   system.

--2.4.  Base Station.

--   A Base Station acts as the master station in NextNet Expedience wireless
--   data system.  It is the only station that transmits downstream, and it
--   controls the scheduling of upstream transmissions by its associated
--   CPEs.

--2.5.  Codeword

--   A characteristic of the Foward Error Correction scheme used
--   above the RF media layer.

--2.6.  Data Packet

--   The payload portion of the MAC Packet.

--2.7.  dBmV

--   Decibel relative to one milli-volt. A measure of RF power.

--2.8.  


--2.9.  Downstream

--   The direction from the base station towards the subscriber.

--2.10.  Head-end router

--   The routing point to public internet.

--2.11.  MAC Packet

--   An Expedience PDU.

--2.12.  


--2.13.  Slot

--   In general, an interval of time which is allocated by the
--   base station to a given CPE for that CPE to transmit in an upstream
--   direction.

--2.14.  QPSK   Quadrature Phase Shift Keying.

--   A particular modulation scheme on an RF medium.

--2.15.  

--2.16.  RF

--   Radio Frequency.

--2.17.  Symbol-times

--   A characteristic of the RF modulation scheme.

--2.18.  Upstream

--   The direction from the CPE towards the base station.

--3.  Overview

--   This MIB provides a set of objects required for the management of
--   NextNet Expedience system RF interfaces.  The specification is derived
--   in part from the parameters and protocols described in NextNet Radio
--   Frequency Interface Specification.

--3.1.  Structure of the MIB

--   This MIB is structured as two groups:

--   o    Management information pertinent to a device (expedDevMibObjects).

--   o    Management information pertinent to interfaces (expedIfMibObjects).

--   Device management information is organaized into five groups. All five
--   groups are implemented on both Customer Premise Equipment and Base Station
--   Systems
--        expedDevBase - basic device identification group
--        expedDevSoftware - device software identification group
--        expedDevServer - device state in relation to other servers
--        expedDevEvent - event management group
--        expedDevFilter - traffic filtering group

--   Interface management information is ogranized into three groups: 
--        expedIfBaseObjects - management information pertinent to both CPE
--        and Base Stion Systems.
--        expedIfCpeObjects - management information pertinent to CPEs only.
--        expedIfBssObjects - management information pertinent to Base Station
--      Systems only.

--   Tables within each of these groups group objects functionally - e.g.
--   Channel characteristics, MAC layer management, etc.  Rows created
--   automatically (e.g. by the device according to the hardware configuration)
--   may and generally will have a mixture of configuration and status objects
--   within them.

--4.  Definitions
   
NEXTNET-MIB DEFINITIONS ::= BEGIN

    -- Title:       NextNet MIB
    -- Date:        Dec 8, 1999
    -- By:          Vladimir Kelman/NextNet 

    IMPORTS
        NetworkAddress, IpAddress, enterprises, Counter, TimeTicks, Gauge
        FROM RFC1155-SMI
        OBJECT-TYPE
        FROM RFC-1212
        DisplayString
        FROM RFC1213-MIB
        TRAP-TYPE
        FROM RFC-1215;

          PhysAddress ::=
              OCTET STRING
          -- This data type is used to model media addresses.  For many
          -- types of media, this will be in a binary representation.
          -- For example, an ethernet address would be represented as
          -- a string of 6 octets.

-- Textual Conventions

DateAndTime ::= DisplayString (SIZE(8|11))
-- A date/time specification, optionaly including time zone offset
        
TruthValue ::= INTEGER {true(1), false(0)}

   
TenthdBmV ::= INTEGER
--        DISPLAY-HINT "d-1"
--        STATUS       current
--        DESCRIPTION
--            "This data type represents power levels that are normally
--             expressed in dBmV. Units are in tenths of a dBmV;
--             for example, 5.1 dBmV will be represented as 51."

TenthdB ::= INTEGER
--        DISPLAY-HINT "d-1"
--        STATUS       current
--        DESCRIPTION
--            "This data type represents power levels that are normally
--             expressed in dB. Units are in tenths of a dB;
--             for example, 5.1 dB will be represented as 51."


nextnet        OBJECT IDENTIFIER ::= { enterprises 4743 }
expedDev    OBJECT IDENTIFIER ::= { nextnet 1 }
expedDevTrap    OBJECT IDENTIFIER ::= { nextnet 2 }
expedDevMIBObjects  OBJECT IDENTIFIER ::= { expedDev 1 }
expedDevBase OBJECT IDENTIFIER ::= { expedDevMIBObjects 1 }

ExpedDevBaseInfo ::= SEQUENCE {
    expedDevRole INTEGER,
    expedDevDateTime DateAndTime,
    expedDevSerialNumber DisplayString,
    expedDevSTPControl INTEGER,
    expedDevGpsStatus DisplayString,
    expedDevGpsMonitorState INTEGER,
    expedDevGpsClockOK TruthValue,
    expedDevPpsStatus TruthValue,
    expedDevAirlinkStatus TruthValue,
    expedDevWriteFlash INTEGER,
    expedDevRebootDevice INTEGER,
    expedDevZeroStats INTEGER,
    expedDevTemperature INTEGER,
    expedDevModelId DisplayString

}

expedDevRole OBJECT-TYPE
   SYNTAX INTEGER {
    cpe(1),
    bssActive(2),
    bssBackup(3)
    }
   ACCESS  read-only
   STATUS  mandatory
   DESCRIPTION
        "Defines the current role of this device.  cpe (1) is
        a Customer Premises Equipment, bssActive(2) is a Base Station 
        System which is controlling the system of CPE devices,
        and bssBackup(3) is a Base Station system which is currently
        connected, but not controlling the system (not currently used).
        In general, if this device is a 'cpe', its role will not
        change during operation or between reboots.  If the
        device is a 'bss' it may change between bssActive and
        bssBackup and back again during normal operation.
        At this time, the NextNet Expedience system does not support
        the concept of a backup BSS, bssBackup is included for
        completeness."
    ::= { expedDevBase 1 }

expedDevDateTime OBJECT-TYPE
    SYNTAX      DateAndTime
    ACCESS        read-only
    STATUS      mandatory
    DESCRIPTION
        "The date and time, with optional timezone information."
    ::= { expedDevBase 2 }

expedDevSerialNumber OBJECT-TYPE
    SYNTAX      DisplayString (SIZE (0..255))
    ACCESS        read-only
    STATUS      mandatory
    DESCRIPTION
        "The manufacturer's serial number for this device."
    ::= { expedDevBase 3 }

expedDevSTPControl OBJECT-TYPE
    SYNTAX INTEGER {
        stEnabled(1),
        noStFilterBpdu(2),
        noStPassBpdu(3)
    }
    ACCESS  read-only
    STATUS  mandatory
    DESCRIPTION
        "This object controls operation of the spanning tree
        protocol (as distinguished from transparent bridging).
        If set to stEnabled(1) then the spanning tree protocol
        is enabled, subject to bridging constraints. If
        noStFilterBpdu(2), then spanning tree is not active,
        and Bridge PDUs received are discarded.
        If noStPassBpdu(3) then spanning tree is not active
        and Bridge PDUs are transparently forwarded. Note that
        a device need not implement all of these options,
        but that noStFilterBpdu(2) is required."
    ::= { expedDevBase 4 }

    --
    --
expedDevGpsStatus OBJECT-TYPE
    SYNTAX      DisplayString (SIZE (0..255))
    ACCESS        read-only
    STATUS      mandatory
    DESCRIPTION
        "The status string coming from the GPS"
    ::= { expedDevBase 5 }


expedDevGpsMonitorState OBJECT-TYPE
   SYNTAX INTEGER {
                gCState-NoGps (0),
                gCState-Init (1),
                gCState-Correcting (2),
                gCState-Undetermined (3),
                gCState-Unreliable (4),
                gCState-Locked (5),
                gCState-Floating (6),
                gCState-Drifted (7)
                }

    ACCESS        read-only
    STATUS      mandatory
    DESCRIPTION
        "The state of the GPS Clock Monitor.  The following states are possible.
        gCState-NoGps (No GPS for this base station), gCState-Init (Waiting for
        init to complete), gCState-Correcting (initial time solved, needs
        correction) gCState-Undetermined (floating init time solution),
        gCState-Unreliable (init time drifted too far), gCState-Locked (full
        time solution), gCState-Floating (Floating full time solution), and
        gCState-Drifted (full time solution drifted too far."
    ::= { expedDevBase 6 }

expedDevGpsClockOK OBJECT-TYPE
    SYNTAX      TruthValue
    ACCESS        read-only
    STATUS      mandatory
    DESCRIPTION
        "Indicates whether the GPS timing pulse is considered valid.  If a
        base is operating without a GPS unit, then this element will be True."
    ::= { expedDevBase 7 }


expedDevPpsStatus OBJECT-TYPE
    SYNTAX      TruthValue
    ACCESS        read-only
    STATUS      mandatory
    DESCRIPTION
        "Indicates whether the one-second timing pulse is being delivered to
         the base station.  If a base is operating with a GPS unit, then the
         timing pulse refers to the pulse being delivered by the GPS unit."
    ::= { expedDevBase 8 }

expedDevAirlinkStatus OBJECT-TYPE
    SYNTAX      TruthValue
    ACCESS        read-only
    STATUS      mandatory
    DESCRIPTION
        "The status of the Airlink."
    ::= { expedDevBase 9 }
 
expedDevWriteFlash OBJECT-TYPE
   SYNTAX INTEGER {
                enable(1),
                disable(2)
                }

    ACCESS        read-write
    STATUS      mandatory
    DESCRIPTION
        "Setting this flag to enable will cause the configuration to be
        written to flash"
    ::= { expedDevBase 10}

expedDevRebootDevice OBJECT-TYPE
   SYNTAX INTEGER {
                enable(1),
                disable(2)
                }

    ACCESS        read-write
    STATUS      mandatory
    DESCRIPTION
        "Setting this flag to enable will cause the device to be rebooted"
    ::= { expedDevBase 11}
 
expedDevZeroStats OBJECT-TYPE
   SYNTAX INTEGER {
                none (0),
                device (1),
                airlink (2),
                ethernet (3),
                aaa (4),
                relay (5),
                throughput (6),
                all (7)
                }

    ACCESS        read-write
    STATUS      mandatory
    DESCRIPTION
        "Zeros out the appropriate stats"
    ::= { expedDevBase 12}


expedDevTemperature OBJECT-TYPE
    SYNTAX        INTEGER
    ACCESS        read-only
    STATUS      mandatory
    DESCRIPTION
        "Current temperature of the device"
    ::= { expedDevBase 13}

expedDevModelId OBJECT-TYPE
    SYNTAX        DisplayString
    ACCESS        read-only
    STATUS      mandatory
    DESCRIPTION
            "Model Identifier for the base station.  The primary hardware
             features of the base station are specified by this string
             representation of a hexidecimal, 32-bit number with a range
             of 00000000 - FFFFFFFF and a format of ABCCDDEE.
                A => Model Category
                    0 => Outdoor Base Station
                    1 => Indoor CPE
                    2 => Outdoor CPE
                    3 => Indoor Base Station
                    4 => Mobile Subscriber Unit
                B => Reserved
                    0 => Default
                CC => Board Type
                    01 => FPGA Wedge
                    02 => Dual Board ASIC Wedge, Davicom
                    03 => Single Board ASIC Wedge, SMSC, Indoor
                    04 => Single Board ASIC, SMSC, Outdoor
                    05 => Slimline, ASIC
                    12 => AMOD Dual Board, ASIC
                    15 => AMOD Slimline, ASIC
                    16 => AMOD 5407 Coldfire, ASIC
                    17 => AMOD LX CPE
                    18 => AMOD LX SoC CPE
                    22 => AMOD 5484 Coldfire, ASIC Base
                DD => Reserved
                    00 => 2.6 GHz
                    01 => 3.3 GHz
                    02 => 3.5 GHz
                    03 => 2.4 GHz
                    04 => 2.3 GHz
                    05 => 700MHz
                    06 => 3.7 GHz
                EE => Special Options
                    00 => External Antenna
                    01 => Vertical Antenna
                    02 => Horizontal Antenna"
    ::= { expedDevBase 14}


expedDevSoftware OBJECT IDENTIFIER ::= { expedDevMIBObjects 2 }


expedDevSwCurrentVers OBJECT-TYPE
                    SYNTAX       DisplayString (SIZE (0..255))
                    ACCESS  read-only
                    STATUS      mandatory
                    DESCRIPTION
                    "The software version currently operating in this device."
::= { expedDevSoftware 1 }

   --
   -- The following group describes server access and parameters.
   --

expedDevServer OBJECT IDENTIFIER ::= { expedDevMIBObjects 3 }

ExpedDevServerInfo ::= SEQUENCE {
    expedDevBootState INTEGER,
    expedDevDhcp IpAddress,
    expedDevFTPPort   INTEGER,
    expedDevFTPRemote IpAddress,
    expedDevFTPTimeout INTEGER,
    expedDevFTPState INTEGER,
    expedDevHostTraceAddress DisplayString,
    expedDevHostTraceFilter INTEGER,
    expedDevHostTraceState INTEGER,
    expedDevTelnetPort   INTEGER,
    expedDevTelnetRemote IpAddress,
    expedDevTelnetTimeout INTEGER,
    expedDevTelnetState INTEGER,
    expedDevWebPort   INTEGER,
    expedDevWebRemote IpAddress,
    expedDevWebState   INTEGER,
    expedDevSysSector DisplayString,
    expedDevSysCell   DisplayString,
    expedDevSysLocation DisplayString,
    expedDevSysName DisplayString,
    expedDevVlanPortID INTEGER,
    expedDevVlanMgmtID   INTEGER,
    expedDevVlanUntaggedID INTEGER,
    expedDevCpuUtilization INTEGER
}

expedDevBootState OBJECT-TYPE
               SYNTAX INTEGER {
                operational(1),
                airlinkdisabled(2),
                privatemode(3),
                unknown(4)
                }
                ACCESS        read-only
                STATUS      mandatory
                DESCRIPTION
                "If operational(1), the device has completed loading and
                processing of configuration parameters and the Base Station is 
                operational.  If airlinkdisabled(2) then the device was
                administratively disabled. If privatemode(3), the device is 
                operational and is in privatemode."
::= { expedDevServer 1 }

expedDevDhcp OBJECT-TYPE
               SYNTAX        IpAddress
               ACCESS        read-only
               STATUS        mandatory
               DESCRIPTION
               "The IP address of the DHCP server that assigned an IP
               address to this device. Returns 0.0.0.0 if DHCP was not
               used for IP address assignment."
::= { expedDevServer 2 }


expedDevFTPPort OBJECT-TYPE
               SYNTAX        INTEGER (1..65535)
               ACCESS        read-write
               STATUS        mandatory
               DESCRIPTION
               "The port number that FTP is listening on."

::= { expedDevServer 3 }

expedDevFTPRemote OBJECT-TYPE
               SYNTAX        IpAddress
               ACCESS        read-write
               STATUS        mandatory
               DESCRIPTION
               "The IP address mask that is allowed access to FTP.
               255.255.255.255 allows access to everyone."
::= { expedDevServer 4 }

expedDevFTPTimeout OBJECT-TYPE
               SYNTAX        INTEGER (10..1000)
               ACCESS        read-write
               STATUS        mandatory
               DESCRIPTION
               "The max timeout in seconds to allow an FTP session to remain
               idle."
::= { expedDevServer 5 }

expedDevFTPState OBJECT-TYPE
               SYNTAX INTEGER {
                enable(1),
                disable(2)
                }
               ACCESS        read-write
               STATUS        mandatory
               DESCRIPTION
               "Enables/Disables FTP."
::= { expedDevServer 6 }

expedDevHostTraceAddress OBJECT-TYPE
               SYNTAX        DisplayString
               ACCESS        read-write
               STATUS        mandatory
               DESCRIPTION
               "The MAC address of the host to trace for debugging host
               traffic."
::= { expedDevServer 7 }

expedDevHostTraceFilter OBJECT-TYPE
               SYNTAX INTEGER {
                none(1),
                broadcast (2),
                upstream (3),
                downstream (4),
                broadcast-upstream(5),
                broadcast-downstream(6)
                }

               ACCESS        read-write
               STATUS        mandatory
               DESCRIPTION
               "This parameter allows a user to filter out host trace
               messages (i.e. discard them) for broadcast, or uplink or downlink
               frames."
::= { expedDevServer 8 }

expedDevHostTraceState OBJECT-TYPE
               SYNTAX INTEGER {
                enable(1),
                disable(2)
                }
               ACCESS        read-write
               STATUS        mandatory
               DESCRIPTION
               "Enable/Disable individual host syslog tracing."
::= { expedDevServer 9 }

expedDevTelnetPort OBJECT-TYPE
               SYNTAX        INTEGER (1..65535)
               ACCESS        read-write
               STATUS        mandatory
               DESCRIPTION
               "The port number that Telnet is listening on."
::= { expedDevServer 10 }

expedDevTelnetRemote OBJECT-TYPE
               SYNTAX        IpAddress
               ACCESS        read-write
               STATUS        mandatory
               DESCRIPTION
               "The IP address mask that is allowed access to Telnet.
               255.255.255.255 allows access to everyone."
::= { expedDevServer 11 }

expedDevTelnetTimeout OBJECT-TYPE
               SYNTAX        INTEGER (10..1000)
               ACCESS        read-write
               STATUS        mandatory
               DESCRIPTION
               "The max timeout in seconds to allow a Telnet session to remain
               idle."
::= { expedDevServer 12 }

expedDevTelnetState OBJECT-TYPE
               SYNTAX INTEGER {
                enable(1),
                disable(2)
                }
               ACCESS        read-write
               STATUS        mandatory
               DESCRIPTION
               "Enables/Disables Telnet."
::= { expedDevServer 13 }



expedDevWebPort OBJECT-TYPE
               SYNTAX        INTEGER (1..65535)
               ACCESS        read-write
               STATUS        obsolete
               DESCRIPTION
               "The port number that WEB is listening on.

                This object is obsolete as of base station software version 
                4.3 and has no replacement."
::= { expedDevServer 14 }

expedDevWebRemote OBJECT-TYPE
               SYNTAX        IpAddress
               ACCESS        read-write
               STATUS        obsolete
               DESCRIPTION
               "The IP address mask that is allowed access to Web.
                255.255.255.255 allows access to everyone.
               
                This object is obsolete as of base station software version 
                4.3 and has no replacement."
::= { expedDevServer 15 }

expedDevWebState OBJECT-TYPE
               SYNTAX INTEGER {
                enable(1),
                disable(2)
                }
               ACCESS        read-write
               STATUS        obsolete
               DESCRIPTION
               "Enables/Disables WEB.
               
                This object is obsolete as of base station software version 
                4.3 and has no replacement."
::= { expedDevServer 16 }

expedDevVTTimeout OBJECT-TYPE
               SYNTAX        INTEGER
               ACCESS        read-write
               STATUS        obsolete
               DESCRIPTION
               "The max timeout in seconds to allow a Virtual Telnet session
               to wait for a reponse.  This object is obsolete as of base
               station software version 4.3 and has no replacement."
::= { expedDevServer 17 }

expedDevSysSector OBJECT-TYPE
                    SYNTAX       DisplayString (SIZE (0..20))
                    ACCESS  read-write
                    STATUS      mandatory
                    DESCRIPTION
                    "The system sector."
::= { expedDevServer 18 }

expedDevSysCell OBJECT-TYPE
                    SYNTAX       DisplayString (SIZE (0..20))
                    ACCESS  read-write
                    STATUS      mandatory
                    DESCRIPTION
                    "The system cell."
::= { expedDevServer 19 }

expedDevVlanPortID OBJECT-TYPE
               SYNTAX        INTEGER (0..4094)
               ACCESS        read-write
               STATUS        mandatory
               DESCRIPTION
               "The Ethernet Port VLAN ID. The PVID
               is the VLAN ID that is applied to any received frames on the
               Ethernet port that are not tagged with a VLAN ID.  This
               parameter only takes effect following a reboot of the base
               station.  Setting to 0 disables this feature."
::= { expedDevServer 20 }

expedDevVlanLegacyID OBJECT-TYPE
               SYNTAX        INTEGER
               ACCESS        read-write
               STATUS        obsolete
               DESCRIPTION
               "The VLAN legacy ID. Selects the VLAN ID for all legacy CPEs
               that register with the base station.  This parameter only
               takes effect following a reboot of the base station.  A
               legacy CPE is defined as a CPE running 1.X code.  Note that
               this VLAN ID is applied to all CPE's when AAA Authority is
               local.
               
               This object is obsolete as of base station software version 4.3
               and is replaced by expedIfBssAAALocalVlan."
::= { expedDevServer 21 }

expedDevVlanMgmtID OBJECT-TYPE
               SYNTAX        INTEGER (1..4094)
               ACCESS        read-write
               STATUS        mandatory
               DESCRIPTION
               "The VLAN Management ID.  Selects the VLAN ID of the management VLAN,
               which is the VLAN used by the local IP stack of the base stations.
               This parameter only takes effect following a reboot of the base
               station."
::= { expedDevServer 22 }

expedDevVlanUntaggedID OBJECT-TYPE
               SYNTAX        INTEGER (0..4094)
               ACCESS        read-write
               STATUS        mandatory
               DESCRIPTION
               "The VLAN Untagged ID.  Configures the selected VLAN to transmit
               untagged frames (no 802.1Q tag).  This parameter only takes effect
               following a reboot of the base station.  Any Ethernet frames
               transmitted from the base station on this VLAN will be untagged.
               Setting to 0 disables this feature."
::= { expedDevServer 23 }

expedDevSysLocation OBJECT-TYPE
                    SYNTAX       DisplayString (SIZE (1..20))
                    ACCESS  read-write
                    STATUS      mandatory
                    DESCRIPTION
                    "The system location."
::= { expedDevServer 24 }


expedDevSysName OBJECT-TYPE
                    SYNTAX       DisplayString (SIZE (1..32))
                    ACCESS  read-write
                    STATUS      mandatory
                    DESCRIPTION
                    "The system name."
::= { expedDevServer 25 }

expedDevCpuUtilization OBJECT-TYPE
                    SYNTAX       INTEGER
                    ACCESS  read-only
                    STATUS      mandatory
                    DESCRIPTION
                    "The current base station CPU utilization, expressed as a
                    percentage."
::= { expedDevServer 26 }


--
--  Event Reporting - Traps
--

expedDevEvent OBJECT IDENTIFIER ::= { expedDevMIBObjects 4 }

expedDevEvSyslog OBJECT-TYPE
        SYNTAX      IpAddress
        ACCESS        read-write
        STATUS      mandatory
        DESCRIPTION
            "The IP address of the Syslog server. If 0.0.0.0, syslog
             transmission is inhibited."
::= { expedDevEvent 1 }

expedDevEvSyslogState OBJECT-TYPE
       SYNTAX INTEGER {
                enable(1),
                disable(2)
                }
        ACCESS        read-write
        STATUS      mandatory
        DESCRIPTION
            "Enables/Disables Syslog."
::= { expedDevEvent 2 }

--
-- The following table controls the reporting of the various classes of
-- events.
--

expedDevEvControlTable OBJECT-TYPE
        SYNTAX      SEQUENCE OF ExpedDevEvControlEntry
        ACCESS        not-accessible
        STATUS      mandatory
        DESCRIPTION
            "This table allows control of the reporting of event classes.
        For each event facility, the minimum level to send a syslog message and
        the minimum level to send a trap can be configured."
::= {  expedDevEvent 3 }

expedDevEvControlEntry OBJECT-TYPE
        SYNTAX      ExpedDevEvControlEntry
        ACCESS        not-accessible
        STATUS      mandatory
        DESCRIPTION
            "Allows configuration of the reporting mechanisms for a
             particular event priority."
        INDEX { expedDevEvFacility }
::= { expedDevEvControlTable 1 }

ExpedDevEvControlEntry ::= SEQUENCE {
            expedDevEvFacility        INTEGER,
            expedDevEvSyslogMin       INTEGER,
            expedDevEvTrapMin         INTEGER
        }

expedDevEvFacility OBJECT-TYPE
        SYNTAX INTEGER {
            log-fac-cfginit(16),
            log-fac-airlink-mac(17),
            log-fac-nnmgr(18),
            log-fac-relay(19),
            log-fac-stack(20),
            log-fac-aaa(21)
        }
        ACCESS        read-only
        STATUS      mandatory
        DESCRIPTION
            "The Facility Level to control for sending traps and syslog messages.
            log-fac-cfginit is used to control traps and syslog messagesfor configuration and initialization,
            log-fac-airlink-mac is used to control traps and syslog messagesfor the airlink mac,
            log-fac-nnmgr is used to control traps and syslog messages for the the airlink manager,
            log-fac-relay is used to control traps and syslog messages for the the relay,
            log-fac-stack is used to control traps and syslog messages for the the ip stack,
            log-fac-aaa is used to control traps and syslog messages for the aaa server,
            log-fac-ether-mac is used to control traps and syslog messages for the ethernet driver"

::= { expedDevEvControlEntry 1 }

expedDevEvSyslogMin OBJECT-TYPE
        SYNTAX INTEGER {
            log-priority-emergency(0),
            log-priority-alert(1),
            log-priority-critical(2),
            log-priority-error(3),
            log-priority-warning(4),
            log-priority-notice(5),
            log-priority-info(6),
            log-priority-debug(7)
        }
        ACCESS        read-write
        STATUS      mandatory
        DESCRIPTION
            "Defines the minimum level for sending a syslog message, all syslog messages
            at and above this level will be sent to the syslog server"
::= { expedDevEvControlEntry 2 }

expedDevEvTrapMin OBJECT-TYPE
        SYNTAX INTEGER {
            log-priority-emergency(0),
            log-priority-alert(1),
            log-priority-critical(2),
            log-priority-error(3),
            log-priority-warning(4),
            log-priority-notice(5),
            log-priority-info(6),
            log-priority-debug(7)
        }
        ACCESS        read-write
        STATUS      mandatory
        DESCRIPTION
            "Defines the minimum level for sending a syslog message, all syslog messages
            at and above this level will be sent to the SNMP manger as a trap"

::= { expedDevEvControlEntry 3 }


expedDevFilter OBJECT IDENTIFIER ::= { expedDevMIBObjects 5 }

--
-- Link Level Control Filtering
--
-- for future implementations
--

--
-- CPE IP Management and anti spoofing group.  Only implemented on
-- CPEs.
--

expedIfMibObjects  OBJECT IDENTIFIER ::= { expedDev 2 }
expedIfBaseObjects OBJECT IDENTIFIER ::= { expedIfMibObjects 1 }

--
-- BASE GROUP
--

--
-- The following table is implemented on both the Customer Premis Equipment (CPE)
-- and the Base Station System (BSS).
--
ExpedIfBaseInfo ::= SEQUENCE {
    expedIfAddress PhysAddress,
    expedIfAirlinkState   INTEGER,
    expedIfAirlinkTiming  INTEGER,
    expedIfAirlinkColorCode INTEGER,
    expedIfAirlinkExtRange INTEGER,
    expedIfBaseRegNotPref  INTEGER,
    expedIfBssDownChannelPower TenthdBmV,
    expedIfBssDownChannelPowerLimit TenthdBmV,
    expedIfBssDownlinkBias INTEGER,
    expedIfBssDownSlots INTEGER,
    expedIfBssUpSlots INTEGER,
    expedIfAirlinkPowerControl INTEGER, 
    expedIfMaxModLevel INTEGER,
    expedIfMaxModLevelString DisplayString,
    expedIfMaxModLevelLimit INTEGER,
    expedIfSoftRssi INTEGER,
    expedIfRadioFrequency DisplayString,
    expedIfMaxNumOfCPEs INTEGER,
    expedIfMaxNumOfCPEsLimit INTEGER,
    expedIfMaxNumOfHosts INTEGER
}

expedIfAddress OBJECT-TYPE
        SYNTAX      PhysAddress
        ACCESS        read-only
        STATUS      mandatory
        DESCRIPTION
            "The Device airlink MAC address"
        ::= { expedIfBaseObjects 1 }


expedIfChannelId OBJECT-TYPE
        SYNTAX      INTEGER (0..255)
        ACCESS      read-write
        STATUS      obsolete
        DESCRIPTION
            "The Base Station System identification
             of the channel within this particular MAC
             interface. If the interface is down, the object returns
             the most current value. If the channel ID is
             unknown, this object returns a value of 0.

             This object is obsolete as of base station software version
             4.3 and is replaced by expedIfRadioFrequency."
        ::= { expedIfBaseObjects 2 }

expedIfChannelFrequency  OBJECT-TYPE
        SYNTAX      INTEGER (0..50000000)
        ACCESS		read-only
        STATUS      obsolete
        DESCRIPTION
            "The center of the frequency associated with the channel
             in use, which is stored in expedIfChannelId.  The unit
             of this object is KHz.

             This object is obsolete as of base station software version
             4.3 and is replaced by expedIfRadioFrequency."
        ::= { expedIfBaseObjects 3 }

expedIfChannelWidth  OBJECT-TYPE
        SYNTAX      INTEGER (0..100000)
        ACCESS		read-only
        STATUS      obsolete
        DESCRIPTION
            "The width of the channel in use, which is stored in
             expedIfChannelId. Most implementations are expected to
             support a channel width of 6 MHz (North America) and/or
             8 MHz (Europe).  The unit of this object is KHz.

             This object is obsolete as of base station software version
             4.3 and is replaced by expedIfRadioFrequency."
        ::= { expedIfBaseObjects 4 }

expedIfTXAGC  OBJECT-TYPE
        SYNTAX      INTEGER
        ACCESS      read-only
        STATUS      obsolete
        DESCRIPTION
            "This specifies the automatic gain control (AGC) applied to
             the transmitter, for setting the maximum power output of the
             transmitter.  This object is obsolete as of base station
             software version 4.3 and has no replacement."
        ::= { expedIfBaseObjects 5 }

expedIfAirlinkState  OBJECT-TYPE
       SYNTAX INTEGER {
                enable(1),
                disable(2)
                }
        ACCESS        read-write
        STATUS      mandatory
        DESCRIPTION
            "This enables and disables the airlink"
        ::= { expedIfBaseObjects 6 }

expedIfRXAGC  OBJECT-TYPE
        SYNTAX      INTEGER
        ACCESS        read-only
        STATUS      obsolete
        DESCRIPTION
            "This specifies the the automatic gain control applied to the 
             receiver.  This object is obsolete as of base station software
             version 4.3 and has no replacement."
        ::= { expedIfBaseObjects 7 }

expedIfAirlinkTiming  OBJECT-TYPE
       SYNTAX INTEGER {
                external(1),
                internal(2),
                external-no-GPS(3)
                }
        ACCESS        read-write
        STATUS      mandatory
        DESCRIPTION
            "This selects the source for the one pulse-per-second.
            The source will either be external, meaning a GPS source,
            internal, or external pulse-per-second generated without a GPS
            unit.  The time synchronization signal is needed to ascertain
            the proper timing for TDD (Time Division Duplexing)."
        ::= { expedIfBaseObjects 9 }

expedIfAirlinkColorCode  OBJECT-TYPE
        SYNTAX      INTEGER (0..15)
        ACCESS        read-write
        STATUS      mandatory

        DESCRIPTION
            "This sets the home color code for this base station. 
            The color code is broadcasted to all CPE's."
        ::= { expedIfBaseObjects 10 }

expedIfAirlinkExtRange  OBJECT-TYPE
        SYNTAX      INTEGER (0..3)
        ACCESS        read-write
        STATUS      mandatory

        DESCRIPTION 
    " This sets the maximum cell size that is broadcasted to all CPE's.    
    Each step indicates a 5 mile radius cell size.  CPE's outside the 
    advertised cell size will not try to register with this base."
        ::= { expedIfBaseObjects 11 }
 
expedIfBaseRegNotPref OBJECT-TYPE
    SYNTAX INTEGER {
        enable(1),
        disable(2)
    }

    ACCESS        read-write
    STATUS        obsolete
    DESCRIPTION
        "Controls registration for this base.  If set to True then this Base
         is advertising to other CPE's that it is busy and should try other bases
         first.

         This object is obsolete as of base station software version 4.3
         and has no replacement."
    ::= { expedIfBaseObjects 12 }
 
expedIfBssDownChannelPower OBJECT-TYPE
        SYNTAX      TenthdBmV
--        UNITS       "dBmV"
        ACCESS        read-write
        STATUS      mandatory
        DESCRIPTION
            "The Base Station System operational transmit power.
             The range is 6 to 31 for 2 watts base, 10 to 31 for 2 watts base 
             and 16 to 31 for 0.5 watts base. If the interface is down, this 
             object either returns the configured value, the most current 
             value or the value of 0." 
        ::= { expedIfBaseObjects 13 }
 
expedIfBssDownChannelPowerLimit OBJECT-TYPE
        SYNTAX      TenthdBmV
--        UNITS       "dBmV"
        ACCESS        read-only
        STATUS      mandatory
        DESCRIPTION
            "The minimum limit of the Base Station System operational transmit 
             power. The value is 16 for 0.5 watts base, 10 for 2 watts base,
             and 6 for 5 watts base."
        ::= { expedIfBaseObjects 35 }

expedIfBssDownlinkBias OBJECT-TYPE
        SYNTAX      INTEGER (0..5)
--        UNITS       "dBmV"
        ACCESS        read-write
        STATUS      mandatory
        DESCRIPTION
            "The Base Station System Downlink Bias.  This Bias sets up the
            number of uplink and downlink slots."
        ::= { expedIfBaseObjects 14 }

expedIfBssDownSlots OBJECT-TYPE
        SYNTAX      INTEGER 
        ACCESS        read-only
        STATUS      mandatory
        DESCRIPTION
            "Directs the Base Station to transmit this number of down link
            symbols in each frame. Note that this number must be related to
            the number of up link symbols as follows:
            (Down Link Symbols) = (Up Link Symbols) + (Down Link Up Link Bias) * 4."
        ::= { expedIfBaseObjects 15 }

expedIfBssUpSlots OBJECT-TYPE
        SYNTAX      INTEGER 
        ACCESS        read-only
        STATUS      mandatory
        DESCRIPTION
            "Directs the Base Station to expect this number of up link symbols
            in each frame. This is the number of down link symbols that will
            contain an UCS field. A CPE determines the existence of an up link
            symbol slot by detecting this UCS. This is a system wide configuration
            number and is used by the CPEs to facilitate frame synchronization.
            This number is to be a multiple of three (0,3,6,x). If this number
            is 0 then the system will be set up for continuous down link operation,
            allowing no up link operation."
        ::= { expedIfBaseObjects 16 }

expedIfAirlinkPowerControl OBJECT-TYPE
       SYNTAX INTEGER {
                enable(1),
                disable(2)
                }
        ACCESS        read-only
        STATUS      mandatory
        DESCRIPTION
            "Enables and disables the airlink power control task.   This task when enabled
            will shut the airlink down when power goes below a pre-determined power level 
            or goes above a pre-determined power level."
        ::= { expedIfBaseObjects 17 }


expedIfUplinkSlotUsageTable OBJECT-TYPE
        SYNTAX      SEQUENCE OF ExpedIfUplinkSlotUsageEntry
        ACCESS        not-accessible
        STATUS      mandatory
        DESCRIPTION
            "At the CPE, describes the PHY signal quality of downstream
             channels. At the BSS, describes the PHY signal quality of
             upstream channels. "
        ::= { expedIfBaseObjects 18}


expedIfUplinkSlotUsageEntry OBJECT-TYPE
        SYNTAX      ExpedIfUplinkSlotUsageEntry
        ACCESS        not-accessible
        STATUS      mandatory
        DESCRIPTION
            "Status information for an uplink slot."
        INDEX { expedIfUplinkSlotUsageIndex  }
        ::= { expedIfUplinkSlotUsageTable 1 }

                
expedIfUplinkSlotUsageIndex OBJECT-TYPE
        SYNTAX      INTEGER (1..6)
        ACCESS        read-only
        STATUS      mandatory
        DESCRIPTION
            "Index value to uniquely identify an entry in this table, on a per-slot basis."
        ::= { expedIfUplinkSlotUsageEntry 1 }


expedIfUplinkSlotUsageUseCount OBJECT-TYPE
        SYNTAX      Counter
        ACCESS        read-only
        STATUS      mandatory
        DESCRIPTION
            "Number of good symbols in slot."
        ::= { expedIfUplinkSlotUsageEntry 2 }

expedIfUplinkSlotUsageFreeCount OBJECT-TYPE
        SYNTAX      Counter
        ACCESS        read-only
        STATUS      mandatory
        DESCRIPTION
            "Number of free slots."
        ::= { expedIfUplinkSlotUsageEntry 3 }

expedIfUplinkSlotUsageRetryCount OBJECT-TYPE
        SYNTAX      Counter
        ACCESS        read-only
        STATUS      mandatory
        DESCRIPTION
            "Number of symbols that had to be retried."
        ::= { expedIfUplinkSlotUsageEntry 4 }

expedIfUplinkSlotUsageBytesRecvd OBJECT-TYPE
        SYNTAX      Counter
        ACCESS        read-only
        STATUS      mandatory
        DESCRIPTION
            "Number of bytes in the received messages."
        ::= { expedIfUplinkSlotUsageEntry 5 }

expedIfUplinkSlotUsageMsgsRecvd OBJECT-TYPE
        SYNTAX      Counter
        ACCESS        read-only
        STATUS      mandatory
        DESCRIPTION
            "Number of received messages."
        ::= { expedIfUplinkSlotUsageEntry 6 }


expedIfUplinkSlotTotUseCount OBJECT-TYPE
        SYNTAX      Counter
        ACCESS        read-only
        STATUS      mandatory
        DESCRIPTION
            "Number of good symbols in all 6 slots combined."
        ::= { expedIfBaseObjects 19 }

expedIfUplinkSlotTotFreeCount OBJECT-TYPE
        SYNTAX      Counter
        ACCESS        read-only
        STATUS      mandatory
        DESCRIPTION
            "Number of free slots in all 6 slots combined."
        ::= { expedIfBaseObjects 20 }

expedIfUplinkSlotTotRetryCount OBJECT-TYPE
        SYNTAX      Counter
        ACCESS        read-only
        STATUS      mandatory
        DESCRIPTION
            "Number of symbols that had to be retried in all 6 slots combined."
        ::= { expedIfBaseObjects 21 }

expedIfUplinkSlotTotBytesRecvd OBJECT-TYPE
        SYNTAX      Counter
        ACCESS        read-only
        STATUS      mandatory
        DESCRIPTION
            "Number of bytes in the received messages in all 6 slots combined."
        ::= { expedIfBaseObjects 22 }

expedIfUplinkSlotTotMsgsRecvd OBJECT-TYPE
        SYNTAX      Counter
        ACCESS        read-only
        STATUS      mandatory
        DESCRIPTION
            "Number of received messages in all 6 slots combined."
        ::= { expedIfBaseObjects 23 }


expedIfDownlinkBytes OBJECT-TYPE
        SYNTAX      Counter
        ACCESS        read-only
        STATUS      mandatory
        DESCRIPTION
            "Number of bytes on the downlink."
        ::= { expedIfBaseObjects 24}

expedIfDownlinkSymbolsUsed OBJECT-TYPE
        SYNTAX      Counter
        ACCESS        read-only
        STATUS      mandatory
        DESCRIPTION
            "Number of symbols used on the downlink."
        ::= { expedIfBaseObjects 25}

expedIfDownlinkSymbolsFree OBJECT-TYPE
        SYNTAX      Counter
        ACCESS        read-only
        STATUS      mandatory
        DESCRIPTION
            "Number of symbols free on the downlink."
        ::= { expedIfBaseObjects 26}

expedIfDownlinkMsgsUnicast OBJECT-TYPE
        SYNTAX      Counter
        ACCESS        read-only
        STATUS      mandatory
        DESCRIPTION
            "Number of messages on the downlink that are unicast."
        ::= { expedIfBaseObjects 27}

expedIfDownlinkMsgsNUnicast OBJECT-TYPE
        SYNTAX      Counter
        ACCESS        read-only
        STATUS      mandatory
        DESCRIPTION
            "Number of messages on the downlink that are broadcast."
        ::= { expedIfBaseObjects 28}

expedIfDownlinkSaturation OBJECT-TYPE
        SYNTAX      INTEGER
        ACCESS        read-only
        STATUS      mandatory
        DESCRIPTION
            "Percent of slot usage on the downlink."
        ::= { expedIfBaseObjects 29}

expedIfUplinkSaturation OBJECT-TYPE
        SYNTAX      INTEGER
        ACCESS        read-only
        STATUS      mandatory
        DESCRIPTION
            "Percent of saturation on the uplink."
        ::= { expedIfBaseObjects 30}

expedIfMaxModLevel OBJECT-TYPE
        SYNTAX      INTEGER (0..5)
        ACCESS        read-write
        STATUS      mandatory
        DESCRIPTION
            "Maximum modulation level for base.  The acceptable values are
            0 (QPSK), 1 (16 QAM), 2 (64 QAM) and 5 (16 QAM Lite)."
        ::= { expedIfBaseObjects 31 }

expedIfMaxModLevelString OBJECT-TYPE
        SYNTAX      DisplayString
        ACCESS      read-only
        STATUS      mandatory
        DESCRIPTION
            "Maximum modulation level for base in string format."
        ::= { expedIfBaseObjects 32 }

expedIfMaxModLevelLimit OBJECT-TYPE
        SYNTAX      INTEGER (0..5)
        ACCESS      read-only
        STATUS      mandatory
        DESCRIPTION
            "The limit of the maximum modulation level for base. The acceptable
            values are 0 (QPSK), 1 (16 QAM), 2 (64 QAM) and 5 (16 QAM Lite)."
        ::= { expedIfBaseObjects 36 }

expedIfSoftRssi OBJECT-TYPE
        SYNTAX      INTEGER (42..66)
        ACCESS        read-write
        STATUS      mandatory
        DESCRIPTION
            "This setting represents a transmit limit on the registered CPEs.
             A CPE will reduce its transmit power if its downlink RSSI is greater
             than this value.  Transmit power will be reduced by the difference
             between the downlink RSSI and this value."
        ::= { expedIfBaseObjects 33 }

expedIfRadioFrequency OBJECT-TYPE
        SYNTAX      DisplayString
        ACCESS      read-write
        STATUS      mandatory
        DESCRIPTION
            "This object represents the configured frequency and bandwidth
             for the Airlink tranceiver in the target base station device.
             The format of this string is <frequency>-<bandwidth>[:<alias>].

             The frequency specifies the center frequency in KHz.  This
             value must be a multiple of 250, have exactly 7 decimal
             digits, and fall between the low and high frequency
             calibration points for the target base station device.

             The bandwidth specifies the width of the frequency in HKz.
             This value must be one of the following: 2500, 2750, 3000,
             3500, 4000, 5000, 5500, 6000, 7000, or 8000.
             Most implementations are expected to support a channel width
             of 6000 KHz (North America) and/or 8000 KHz (Europe).

             This object replaces the expedIfChannelId,
             expedIfChannelFrequency, and expedIfChannelWidth objects."
        ::= { expedIfBaseObjects 34 }

expedIfMaxNumOfCPEs OBJECT-TYPE
        SYNTAX      INTEGER (10..1000)
        ACCESS      read-write
        STATUS      mandatory
        DESCRIPTION
            "Maximum cpes supported by the base DB."
        ::= { expedIfBaseObjects 37 }

expedIfMaxNumOfCPEsLimit OBJECT-TYPE
        SYNTAX      INTEGER (10..1000)
        ACCESS      read-only
        STATUS      mandatory
        DESCRIPTION
            "The limit of the maximum cpes supported by the base DB."
        ::= { expedIfBaseObjects 38 }

expedIfMaxNumOfHosts OBJECT-TYPE
        SYNTAX      INTEGER (100..2000)
        ACCESS      read-write
        STATUS      mandatory
        DESCRIPTION
            "Maximum hosts supported by the base DB."
        ::= { expedIfBaseObjects 39 }
        
ExpedIfUplinkSlotUsageEntry ::= SEQUENCE {
            expedIfUplinkSlotUsageIndex               INTEGER,
            expedIfUplinkSlotUsageUseCount            Counter,
            expedIfUplinkSlotUsageFreeCount           Counter,
            expedIfUplinkSlotUsageRetryCount          Counter,
            expedIfUplinkSlotUsageBytesRecvd          Counter,
            expedIfUplinkSlotUsageMsgsRecvd           Counter
        }

ExpedIfUplinkSlotUsageTotals ::= SEQUENCE {
    expedIfUplinkSlotTotUseCount Counter,
    expedIfUplinkSlotTotFreeCount Counter,
    expedIfUplinkSlotTotRetryCount Counter,
    expedIfUplinkSlotTotBytesRecvd Counter,
    expedIfUplinkSlotTotMsgsRecvd Counter
}

ExpedIfDownlinkStats ::= SEQUENCE {
    expedIfDownlinkBytes Counter,
    expedIfDownlinkSymbolsUsed Counter,
    expedIfDownlinkSymbolsFree Counter,
    expedIfDownlinkMsgsUnicast Counter,
    expedIfDownlinkMsgsNUnicast Counter
}

ExpedIfAirlinkUtilization ::= SEQUENCE {
    expedIfDownlinkSaturation INTEGER,
    expedIfUplinkSaturation INTEGER
}



--
-- Base Station System GROUP
--

expedIfBssObjects  OBJECT IDENTIFIER ::= { expedIfMibObjects 2 }

--
-- The BSS MAC
--

expedIfBssCapabilities OBJECT-TYPE
        SYNTAX      INTEGER {
            packet(0),
            atmCells(1),
            voiceCells(2),
            concatenation-voiceCells(3),
            voiceCells-atmCells(4),
            voiceCells-atmCells-concat(5)
        }
        ACCESS        read-only
        STATUS      mandatory
        DESCRIPTION
            "Identifies the capabilities of the BSS MAC
             implementation at this interface. Note that packet
             transmission is always supported. Therefore, there
             is no specific bit required to explicitely indicate
             this capability."
        ::= { expedIfBssObjects 1 }

-- Relay Stats

ExpedIfBssRelayStats ::= SEQUENCE {
    expedIfBssNumOfCPEs INTEGER,
    expedIfBssNumOfHosts INTEGER,
    expedIfBssNumOfCPEsHighMark Counter,
    expedIfBssNumOfHostsHighMark Counter,
    expedIfBssRelayCpeIdleTime INTEGER,
    expedIfBssRelayDHCPAgentCircuitId TruthValue,
    expedIfBssRelayDHCPAgentRemoteId TruthValue,
    expedIfBssRelayDHCPNumAddAgentFail Counter,
    expedIfBssRelayDHCPNumDiscardExtraRelayInfo Counter,
    expedIfBssRelayDHCPNumDiscardNoEnd Counter,
    expedIfBssRelayDHCPTimeout INTEGER,
    expedIfBssRelayMaxSSTransit INTEGER,
    expedIfBssRelayMaxTransit INTEGER,
    expedIfBssRelayIPHosts INTEGER,
    expedIfBssRelayPPPOEHosts INTEGER
}

expedIfBssNumOfCPEs OBJECT-TYPE
        SYNTAX      INTEGER 
        ACCESS        read-only
        STATUS      mandatory
        DESCRIPTION
            "Number of CPE's currently registered on the Base station"
        ::= { expedIfBssObjects 2 }

expedIfBssNumOfHosts OBJECT-TYPE
        SYNTAX      INTEGER 
        ACCESS        read-only
        STATUS      mandatory
        DESCRIPTION
            "Number of Hosts currently registered on the Base station"
        ::= { expedIfBssObjects 3 }

expedIfBssNumOfCPEsHighMark OBJECT-TYPE
        SYNTAX      Counter 
        ACCESS        read-only
        STATUS      mandatory
        DESCRIPTION
            "Highest Number of CPE's that were registered on the Base station"
        ::= { expedIfBssObjects 4 }

expedIfBssNumOfHostsHighMark OBJECT-TYPE
        SYNTAX      Counter 
        ACCESS        read-only
        STATUS      mandatory
        DESCRIPTION
            "Highest Number of Hosts that were registered on the Base station"
        ::= { expedIfBssObjects 5 }

expedIfBssRelayCpeIdleTime OBJECT-TYPE
               SYNTAX        INTEGER (600..176400)
               ACCESS        read-write
               STATUS        mandatory
               DESCRIPTION
               "The amount of time in seconds that the CPE can be idle before it is deleted
               from the base station.  Idle time is defined as no uplink traffic from
               the CPE."
        ::= { expedIfBssObjects 6 }

expedIfBssRelayDHCPAgentCircuitId OBJECT-TYPE
               SYNTAX        TruthValue
               ACCESS        read-write
               STATUS        mandatory
               DESCRIPTION
               "Indicate whether a relay DHCP agent circuit id is attached to
               all the client-to-server DHCP messages."
        ::= { expedIfBssObjects 74 }
        
expedIfBssRelayDHCPAgentRemoteId OBJECT-TYPE
               SYNTAX        TruthValue
               ACCESS        read-write
               STATUS        mandatory
               DESCRIPTION
               "Indicate whether a relay DHCP agent remote id is attached to
               all the client-to-server DHCP messages."
        ::= { expedIfBssObjects 75 }

expedIfBssRelayDHCPNumAddAgentFail OBJECT-TYPE
               SYNTAX        Counter
               ACCESS        read-only
               STATUS        mandatory
               DESCRIPTION
               "The number of failing to add agent circuit id and/or remote id 
               in the client-to-server DHCP packets due to not enough space in 
               the packets."
        ::= { expedIfBssObjects 76 }

        
expedIfBssRelayDHCPNumDiscardExtraRelayInfo OBJECT-TYPE
               SYNTAX        Counter
               ACCESS        read-only
               STATUS        mandatory
               DESCRIPTION
               "The number of DHCP packets discarded due to the existing relay 
               agent information in the client-to-server DHCP packet when adding
               DHCP agent circuit id and/or remote id to it."
        ::= { expedIfBssObjects 77 }
        
expedIfBssRelayDHCPNumDiscardNoEnd OBJECT-TYPE
               SYNTAX        Counter
               ACCESS        read-only
               STATUS        mandatory
               DESCRIPTION
               "The number of DHCP packets discarded due to DHCP_END option
               missing when adding DHCP agent circuit id and/or remote id to 
               client-to-server DHCP packets."
        ::= { expedIfBssObjects 78 }
        
expedIfBssRelayDHCPTimeout OBJECT-TYPE
               SYNTAX        INTEGER (30..90)
               ACCESS        read-write
               STATUS        mandatory
               DESCRIPTION
               "The amount of time in seconds waiting for completion of the DHCP 
               conversation."
        ::= { expedIfBssObjects 7 }

expedIfBssRelayMaxSSTransit OBJECT-TYPE
               SYNTAX        INTEGER (1..10)
               ACCESS        read-write
               STATUS        mandatory
               DESCRIPTION
               "The max amount of time in 10ths of a second a sync session frame
               can live within the device before it is considered stale and is 
               deleted."
        ::= { expedIfBssObjects 73 }

expedIfBssRelayMaxTransit OBJECT-TYPE
               SYNTAX        INTEGER (10..40)
               ACCESS        read-write
               STATUS        mandatory
               DESCRIPTION
               "The max amount of time in 10ths of a second a datagram frame can
               live within the device before it is considered stale and is 
               deleted."
        ::= { expedIfBssObjects 8 }

expedIfBssRelayIPHosts OBJECT-TYPE
               SYNTAX        INTEGER
               ACCESS        read-only
               STATUS        mandatory
               DESCRIPTION
               "The current number of dynamic hosts that have IP access using DHCP."
        ::= { expedIfBssObjects 48 }

expedIfBssRelayPPPOEHosts OBJECT-TYPE
               SYNTAX        INTEGER
               ACCESS        read-only
               STATUS        mandatory
               DESCRIPTION
               "The current number of dynamic hosts that have PPPoE access.  This count does not
                include PPPoE access by static IP hosts."
        ::= { expedIfBssObjects 49 }

-- AAA Stats

ExpedIfBssAAAConfig ::= SEQUENCE {
    expedIfBssAAAState INTEGER,
    expedIfBssAAAConnectionTime DisplayString,
    expedIfBssAAAConnectionAttempts Counter,
    expedIfBssAAAConfigConnection DisplayString,
    expedIfBssAAACurrentConnection IpAddress,
    expedIfBssAAAAuthority INTEGER,
    expedIfBssAAAPort INTEGER,
    expedIfBssAAAHbInterval INTEGER
}

ExpedIfBssLocalConfig ::= SEQUENCE {
    expedIfBssLocalAllow INTEGER,
    expedIfBssLocalHosts INTEGER,
    expedIfBssLocalSla DisplayString,
    expedIfBssLocalVlan INTEGER,
    expedIfBssLocalVoipAddress IpAddress,
    expedIfBssLocalVoipState INTEGER
}

ExpedIfBssAAAStats ::= SEQUENCE {
    expedIfBssAAARegRequests Counter,
    expedIfBssAAACDRsSent Counter,
    expedIfBssAAARegConfirms Counter,
    expedIfBssAAARegDenys Counter,
    expedIfBssAAARegDuplicates Counter,
    expedIfBssAAANoAAAResponse Counter,
    expedIfBssAAAUnexpectedPV Counter,
    expedIfBssAAADroppedCDRS Counter,
    expedIfBssAAAPVsRecv Counter,
    expedIfBssAAAAllow Counter,
    expedIfBssAAADeny Counter,
    expedIfBssAAADeregCPE Counter,
    expedIfBssAAABindIP Counter,
    expedIfBssAAAPutConfig Counter,
    expedIfBssAAAFetchConfig Counter,
    expedIfBssAAAUnkBase Counter,
    expedIfBssAAAVlanAtts Counter,
    expedIfBssAAABaseAtts Counter,
    expedIfBssAAAReconnect Counter,
    expedIfBssAAAHbCdr Counter,
    expedIfBssAAAHbPv Counter,
    expedIfBssAAAHbDisconnects Counter
}

expedIfBssAAAState OBJECT-TYPE
        SYNTAX INTEGER {
            enable(1),
            disable(2)
        }
        ACCESS      read-write
        STATUS      mandatory
        DESCRIPTION
            "Enables/Disables AAA Server."
::= { expedIfBssObjects 9 }

expedIfBssAAAConnectionTime OBJECT-TYPE
        SYNTAX      DisplayString
        ACCESS      read-only
        STATUS      mandatory
        DESCRIPTION
            "Date and Time of the current AAA connection."
::= { expedIfBssObjects 10 }

expedIfBssAAAConnectionAttempts OBJECT-TYPE
        SYNTAX      Counter 
        ACCESS      read-only
        STATUS      mandatory
        DESCRIPTION
            "Number of attempts for the current AAA connection."
        ::= { expedIfBssObjects 11 }

expedIfBssAAAConfigConnection OBJECT-TYPE
        SYNTAX      DisplayString
        ACCESS      read-write
        STATUS      mandatory
        DESCRIPTION
            "The configuration parameter that controls the address of the AAA
            server(s).  This can be one or two IP addresses, separated by
            a space or comma, to specify a primary and a backup AAA server.
            expedIfBssAAACurrentConnection shows the IP address currently
            being used."
        ::= { expedIfBssObjects 12 }

expedIfBssAAACurrentConnection OBJECT-TYPE
        SYNTAX      IpAddress
        ACCESS      read-only
        STATUS      mandatory
        DESCRIPTION
            "IP address of the current AAA connection."
        ::= { expedIfBssObjects 13 }


expedIfBssAAAAuthority OBJECT-TYPE
        SYNTAX INTEGER {
            local(1),
            remote(2)
        }
        ACCESS        read-write
        STATUS        mandatory
        DESCRIPTION
            "The Authority can be either local or remote.  Local uses
            local authority parameters defined in ExpedIfBssLocalConfig
            for CPE permissions.  Remote looks for authority from a
            Remote AAA Server for CPE permissions."
        ::= { expedIfBssObjects 14 }

expedIfBssAAACaching OBJECT-TYPE
        SYNTAX INTEGER {
            enable(1),
            disable(2)
        }
        ACCESS        read-write
        STATUS        obsolete
        DESCRIPTION
            "Enables/Disables aaa caching during remote authority.   
             When enabled if the cpe is known by the base then the base
             will act as a cache and give authorization based on the
             last registration.
            
             This object is obsolete as of base station software version 4.3
             and has no replacement."
        ::= { expedIfBssObjects 15 }


expedIfBssAAAPort OBJECT-TYPE
               SYNTAX        INTEGER (1..65535)
               ACCESS        read-write
               STATUS        mandatory
               DESCRIPTION
               "The Port the AAA Server is listening on."
        ::= { expedIfBssObjects 16 }


-- Local Authority Config

expedIfBssLocalAllow OBJECT-TYPE
    SYNTAX INTEGER {
        enable(1),
        disable(2)
    }
    ACCESS read-write
    STATUS mandatory
    DESCRIPTION
        "The permission the Local Authority gives to each CPE, where 
        enable allows CPEs to register, and disable disallows CPEs to
        register.  Note:  When a CPE is disallowed the CPE must be
        rebooted in order to register with this base station again.
        This defaults to enable"
    ::= { expedIfBssObjects 50 }

expedIfBssLocalHosts OBJECT-TYPE
    SYNTAX INTEGER (0..15)
    ACCESS read-write
    STATUS mandatory
    DESCRIPTION
        "The number of hosts Local Authority allows behind each CPE.
        This defaults to 10"
    ::= { expedIfBssObjects 51 }

expedIfBssLocalSla OBJECT-TYPE
    SYNTAX DisplayString
    ACCESS read-write
    STATUS mandatory
    DESCRIPTION
        "The Service Level Agreement (SLA) parameters given to each CPE.
        This is of the form up-down, where up and down are decimal numbers
        between 0 and 10000, inclusive, separated by a dash character.
        This defaults to 100-100."
    ::= { expedIfBssObjects 52 }

expedIfBssLocalVlan OBJECT-TYPE
    SYNTAX INTEGER (1..4094)
    ACCESS read-write
    STATUS mandatory
    DESCRIPTION
        "The VLAN identifier Local Authority assigns to each CPE.
        This object replaces the expedDevVlanLegacyID object.
        This defaults to 1."
    ::= { expedIfBssObjects 53 }

expedIfBssLocalVoipAddress OBJECT-TYPE
    SYNTAX IpAddress
    ACCESS read-write
    STATUS mandatory
    DESCRIPTION
        "The VoIP server address Local Authority assigns to each CPE.
        allows the VoIP use through the CPE and disable disallows VoIP
        use through the CPE.  This defaults to 0.0.0.0."
    ::= { expedIfBssObjects 54 }

expedIfBssLocalVoipState OBJECT-TYPE
    SYNTAX INTEGER {
        enable(1),
        disable(2)
    }
    ACCESS read-write
    STATUS mandatory
    DESCRIPTION
        "The VoIP state Local Authority assigns to each CPE, where enable
        allows the VoIP use through the CPE and disable disallows VoIP
        use through the CPE.  This defaults to enable."
    ::= { expedIfBssObjects 55 }

-- end of Local Authority Config


expedIfBssAAARegRequests OBJECT-TYPE
        SYNTAX      Counter 
        ACCESS      read-only
        STATUS      mandatory
        DESCRIPTION
            "Number of CPE registration requests received over the air."
        ::= { expedIfBssObjects 17 }


expedIfBssAAARegDenys OBJECT-TYPE
        SYNTAX      Counter 
        ACCESS      read-only
        STATUS      mandatory
        DESCRIPTION
            "Number of permission vectors that indicate a deny for a CPE
             registration."
        ::= { expedIfBssObjects 18 }

    expedIfBssAAARegConfirms OBJECT-TYPE
        SYNTAX      Counter 
        ACCESS      read-only
        STATUS      mandatory
        DESCRIPTION
            "Number of permission vectors that indicate a confirm for a CPE
             registration."
        ::= { expedIfBssObjects 19 }

    expedIfBssAAARegCache OBJECT-TYPE
        SYNTAX      Counter 
        ACCESS      read-only
        STATUS      obsolete
        DESCRIPTION
            "Number of registration confirms due to caching.
            
             This object is obsolete as of base station software version 4.3
             and has no replacement."
        ::= { expedIfBssObjects 20 }

    expedIfBssAAARegDuplicates OBJECT-TYPE
        SYNTAX      Counter 
        ACCESS      read-only
        STATUS      mandatory
        DESCRIPTION
            "Number of registration requests that are duplicates of a current 
            registration request.   Indicates that a second registration was
            received for a given CPE before the permission vector was received from
            the AAA server."
        ::= { expedIfBssObjects 21 }

    expedIfBssAAANoAAAResponse OBJECT-TYPE
        SYNTAX      Counter 
        ACCESS      read-only
        STATUS      mandatory
        DESCRIPTION
            "Number of registration requests that never received a permission vector
            from the AAA server."
        ::= { expedIfBssObjects 22 }

    expedIfBssAAACDRsSent OBJECT-TYPE
        SYNTAX      Counter 
        ACCESS      read-only
        STATUS      mandatory
        DESCRIPTION
            "Number of CDR's sent to the AAA server."
        ::= { expedIfBssObjects 23 }

    expedIfBssAAAPVsRecv OBJECT-TYPE
        SYNTAX      Counter 
        ACCESS      read-only
        STATUS      mandatory
        DESCRIPTION
            "Number of PV's received from the AAA server."
        ::= { expedIfBssObjects 24 }

    expedIfBssAAAUnexpectedPV OBJECT-TYPE
        SYNTAX      Counter 
        ACCESS      read-only
        STATUS      mandatory
        DESCRIPTION
            "Number of PV's received from the AAA server, that were not expected."
        ::= { expedIfBssObjects 25 }

    expedIfBssAAADroppedCDRS OBJECT-TYPE
        SYNTAX      Counter
        ACCESS      read-only
        STATUS      mandatory
        DESCRIPTION
            "Number of CDR's dropped due to out of buffer condition."
        ::= { expedIfBssObjects 32 }


expedIfBssAAAAllow OBJECT-TYPE
        SYNTAX      Counter
        ACCESS      read-only
        STATUS      mandatory
        DESCRIPTION
            "Total number of allow PV's."
        ::= { expedIfBssObjects 59}

expedIfBssAAADeny OBJECT-TYPE
        SYNTAX      Counter
        ACCESS      read-only
        STATUS      mandatory
        DESCRIPTION
            "Total number of deny PV's."
        ::= { expedIfBssObjects 60}

expedIfBssAAADeregCPE OBJECT-TYPE
        SYNTAX      Counter
        ACCESS      read-only
        STATUS      mandatory
        DESCRIPTION
            "Total number of de-reg CPE PV's."
        ::= { expedIfBssObjects 61}

expedIfBssAAABindIP OBJECT-TYPE
        SYNTAX      Counter
        ACCESS      read-only
        STATUS      mandatory
        DESCRIPTION
            "Total number of bind IP PV's."
        ::= { expedIfBssObjects 62}

expedIfBssAAAPutConfig OBJECT-TYPE
        SYNTAX      Counter
        ACCESS      read-only
        STATUS      mandatory
        DESCRIPTION
            "Total number of put config PV's."
        ::= { expedIfBssObjects 63}

expedIfBssAAAFetchConfig OBJECT-TYPE
        SYNTAX      Counter
        ACCESS      read-only
        STATUS      mandatory
        DESCRIPTION
            "Total number of fetch config PV's."
        ::= { expedIfBssObjects 64}

expedIfBssAAAUnkBase OBJECT-TYPE
        SYNTAX      Counter
        ACCESS      read-only
        STATUS      mandatory
        DESCRIPTION
            "Total number of unknown base PV's."
        ::= { expedIfBssObjects 65}

expedIfBssAAAVlanAtts OBJECT-TYPE
        SYNTAX      Counter
        ACCESS      read-only
        STATUS      mandatory
        DESCRIPTION
            "Total number of VLAN attribute PV's."
        ::= { expedIfBssObjects 66}

expedIfBssAAABaseAtts OBJECT-TYPE
        SYNTAX      Counter
        ACCESS      read-only
        STATUS      mandatory
        DESCRIPTION
            "Total number of base attribute PV's."
        ::= { expedIfBssObjects 67}

expedIfBssAAAReconnect OBJECT-TYPE
        SYNTAX      Counter
        ACCESS      read-only
        STATUS      mandatory
        DESCRIPTION
            "Total number of reconnect to primary AAA PV's."
        ::= { expedIfBssObjects 68}

expedIfBssAAAHbCdr OBJECT-TYPE
        SYNTAX      Counter
        ACCESS      read-only
        STATUS      mandatory
        DESCRIPTION
            "Total number of heartbeat messages (CDRs) sent."
        ::= { expedIfBssObjects 69}

expedIfBssAAAHbPv OBJECT-TYPE
        SYNTAX      Counter
        ACCESS      read-only
        STATUS      mandatory
        DESCRIPTION
            "Total number of heartbeat messages (PVs) received."
        ::= { expedIfBssObjects 70}

expedIfBssAAAHbInterval OBJECT-TYPE
        SYNTAX      INTEGER
        ACCESS      read-only
        STATUS      mandatory
        DESCRIPTION
            "Heartbeat interval received on the AAA connection."
        ::= { expedIfBssObjects 71}

expedIfBssAAAHbDisconnects OBJECT-TYPE
        SYNTAX      Counter
        ACCESS      read-only
        STATUS      mandatory
        DESCRIPTION
            "Total number of times the heartbeat detector forced
             disconnection from AAA due to timeout."
        ::= { expedIfBssObjects 72}

--
--
--
-- BSS status
--

expedIfBssCpeStatusTable OBJECT-TYPE
        SYNTAX      SEQUENCE OF ExpedIfBssCpeStatusEntry
        ACCESS        not-accessible
        STATUS      mandatory
        DESCRIPTION
            "A set of objects in the BSS, maintained for each
             CPE connected to this base station."
        ::= { expedIfBssObjects 26 }

expedIfBssCpeStatusEntry OBJECT-TYPE
        SYNTAX      ExpedIfBssCpeStatusEntry
        ACCESS        not-accessible
        STATUS      mandatory
        DESCRIPTION
            "Status information for a single CPE.
             An entry in this table exists for each CPE
             that is connected to the BSS implementing this table."
        INDEX { expedIfBssCpeStatusIndex  }
        ::= { expedIfBssCpeStatusTable 1 }

ExpedIfBssCpeStatusEntry ::= SEQUENCE {
            expedIfBssCpeStatusIndex               INTEGER,
            expedIfBssCpeStatusMacAddress          DisplayString,
            expedIfBssCpeStatusBytesFrom           Counter,
            expedIfBssCpeStatusBytesTo             Counter,
            expedIfBssCpeStatusMsgsFrom            Counter,
            expedIfBssCpeStatusMsgsTo              Counter,
            expedIfBssCpeNumOfHosts                INTEGER,
            expedIfBssCpeISPId                     INTEGER,
            expedIfBssCpeVID                       INTEGER,
            expedIfBssCpeStatusLastTime            DateAndTime,
            expedIfBssDynamicIPAssignment          TruthValue,
            expedIfBssCpeSwVersion                 DisplayString,
            expedIfBssCpeNumOfCalls                INTEGER,
            expedIfBssCpeDataPolls                 Counter,
            expedIfBssCpeDryPolls                   Counter,
            expedIfBssCpeNoResponse                Counter,
            expedIfBssCpeCallEfficiency            INTEGER,
            expedIfBssCpeBWUsage                   INTEGER,
            expedIfBssCpeDownModulation            DisplayString,
            expedIfBssCpeDownLinkBandWidth         DisplayString,
            expedIfBssCpeUplinkBandWidth           DisplayString,
            expedIfBssCpeIdleTime                  Counter,
            expedIfBssCpeModelId                   DisplayString,
            expedIfBssNumStaticHosts               INTEGER
        }

expedIfBssCpeStatusIndex OBJECT-TYPE
        SYNTAX      INTEGER (1..2147483647)
        ACCESS      read-only
        STATUS      mandatory
        DESCRIPTION
            "Index value to uniquely identify an entry in this table.
             For an individual CPE, this index value should
             not change during BSS uptime."
        ::= { expedIfBssCpeStatusEntry 1 }

expedIfBssCpeStatusMacAddress OBJECT-TYPE
        SYNTAX      DisplayString
        ACCESS      read-only
        STATUS      mandatory
        DESCRIPTION
            "MAC address of this CPE. If the CPE has
             multiple MAC addresses, this is the MAC address associated
             with the Airlink interface."
        ::= { expedIfBssCpeStatusEntry 2 }

expedIfBssCpeStatusBytesFrom OBJECT-TYPE
        SYNTAX      Counter
        ACCESS      read-only
        STATUS      mandatory
        DESCRIPTION
            "Number of bytes in from this CPE."
        ::= { expedIfBssCpeStatusEntry 3 }

expedIfBssCpeStatusBytesTo OBJECT-TYPE
        SYNTAX      Counter
        ACCESS      read-only
        STATUS      mandatory
        DESCRIPTION
            "Number of bytes out to this CPE."
        ::= { expedIfBssCpeStatusEntry 4 }

expedIfBssCpeStatusMsgsFrom OBJECT-TYPE
        SYNTAX      Counter
        ACCESS      read-only
        STATUS      mandatory
        DESCRIPTION
            "Number of Msgs in from this CPE."
        ::= { expedIfBssCpeStatusEntry 5 }


expedIfBssCpeStatusMsgsTo OBJECT-TYPE
        SYNTAX      Counter
        ACCESS      read-only
        STATUS      mandatory
        DESCRIPTION
            "Number of Msgs out to this CPE."
        ::= { expedIfBssCpeStatusEntry 6 }

expedIfBssCpeNumOfHosts OBJECT-TYPE
        SYNTAX      INTEGER
        ACCESS      read-only
        STATUS      mandatory
        DESCRIPTION
            "Number of hosts allowed for this CPE."
        ::= { expedIfBssCpeStatusEntry 7 }

expedIfBssCpeISPId OBJECT-TYPE
        SYNTAX      INTEGER
        ACCESS      read-only
        STATUS      mandatory
        DESCRIPTION
            "This contains the ID of the ISP that owns this CPE ."
        ::= { expedIfBssCpeStatusEntry 8 }

expedIfBssCpeVID OBJECT-TYPE
        SYNTAX      INTEGER
        ACCESS      read-only
        STATUS      mandatory
        DESCRIPTION
            "This contains the VLAN ID the CPE has been assigned to."
        ::= { expedIfBssCpeStatusEntry 9 }

expedIfBssCpeStatusLastTime OBJECT-TYPE
    SYNTAX      DateAndTime
    ACCESS      read-only
    STATUS      mandatory
    DESCRIPTION
        "The date and time last heard from this CPE."
    ::= { expedIfBssCpeStatusEntry 10 }

expedIfBssDynamicIPAssignment OBJECT-TYPE
    SYNTAX      TruthValue
    ACCESS      read-only
    STATUS      obsolete
    DESCRIPTION
        "A true indicates that hosts behind this CPE acquire their IP
        Address via DHCP.   False indicates static IP assignment.

        This object is obsolete."

    ::= { expedIfBssCpeStatusEntry 11 }

expedIfBssCpeSwVersion OBJECT-TYPE
    SYNTAX      DisplayString
    ACCESS      read-only
    STATUS      mandatory
    DESCRIPTION
        "Version of software this CPE is running."

    ::= { expedIfBssCpeStatusEntry 12 }

expedIfBssCpeNumOfCalls OBJECT-TYPE
    SYNTAX      INTEGER
    ACCESS      read-only
    STATUS      mandatory
    DESCRIPTION
        "Number Of Current Calls on this CPE"

    ::= { expedIfBssCpeStatusEntry 13 }

expedIfBssCpeDataPolls OBJECT-TYPE
    SYNTAX      Counter
    ACCESS      read-only
    STATUS      mandatory
    DESCRIPTION
        "Number Of Data Polls from this CPE"

    ::= { expedIfBssCpeStatusEntry 14 }

expedIfBssCpeDryPolls OBJECT-TYPE
    SYNTAX      Counter
    ACCESS      read-only
    STATUS      mandatory
    DESCRIPTION
        "Number Of Dry Polls from this CPE"

    ::= { expedIfBssCpeStatusEntry 15 }

expedIfBssCpeNoResponse OBJECT-TYPE
    SYNTAX      Counter
    ACCESS      read-only
    STATUS      mandatory
    DESCRIPTION
        "Number Of No Response to Polls from this CPE"

    ::= { expedIfBssCpeStatusEntry 16 }

expedIfBssCpeCallEfficiency OBJECT-TYPE
    SYNTAX      INTEGER
    ACCESS      read-only
    STATUS      mandatory
    DESCRIPTION
        "Efficiency use of the Bandwidth for this CPE"

    ::= { expedIfBssCpeStatusEntry 17 }

expedIfBssCpeBWUsage OBJECT-TYPE
    SYNTAX      INTEGER
    ACCESS      read-only
    STATUS      mandatory
    DESCRIPTION
        "Sync Session Bandwidth Usage for all calls on this CPE from the  
         perspective of base"

    ::= { expedIfBssCpeStatusEntry 18 }

expedIfBssCpeDownModulation OBJECT-TYPE
    SYNTAX      DisplayString
    ACCESS      read-only
    STATUS      mandatory
    DESCRIPTION
        "Downlink Modulation Level"

    ::= { expedIfBssCpeStatusEntry 19 }

expedIfBssCpeDownLinkBandWidth OBJECT-TYPE
    SYNTAX      DisplayString
    ACCESS      read-only
    STATUS      mandatory
    DESCRIPTION
        "Provisioned Downlink BandWidth limit. Unit is kbps. 'none' means no 
         limit."

    ::= { expedIfBssCpeStatusEntry 20 }

expedIfBssCpeUplinkBandWidth OBJECT-TYPE
    SYNTAX      DisplayString
    ACCESS      read-only
    STATUS      mandatory
    DESCRIPTION
        "Provisioned Uplink BandWidth limit. Unit is kbps. 'none' means no 
         limit."

    ::= { expedIfBssCpeStatusEntry 21 }

expedIfBssCpeIdleTime OBJECT-TYPE
    SYNTAX      Counter
    ACCESS      read-only
    STATUS      mandatory
    DESCRIPTION
        "Amount of time the CPE has been idle"

    ::= { expedIfBssCpeStatusEntry 22 }

expedIfBssCpeModelId OBJECT-TYPE
        SYNTAX      DisplayString
        ACCESS      read-only
        STATUS      mandatory
        DESCRIPTION
            "Model Identifier for the subscriber unit.  The primary hardware
             features of the subscriber unit are specified by this string
             representation of a hexidecimal, 32-bit number with a range
             of 00000000 - FFFFFFFF and a format of ABCCDDEE.
                A => Model Category
                    0 => Outdoor Base Station
                    1 => Indoor CPE
                    2 => Outdoor CPE
                    3 => Indoor Base Station
                    4 => Mobile Subscriber Unit
                B => Reserved
                    0 => Default
                CC => Board Type
                    01 => FPGA Wedge
                    02 => Dual Board ASIC Wedge, Davicom
                    03 => Single Board ASIC Wedge, SMSC, Indoor
                    04 => Single Board ASIC, SMSC, Outdoor
                    05 => Slimline, ASIC
                    12 => AMOD Dual Board, ASIC
                    15 => AMOD Slimline, ASIC
                    16 => AMOD 5407 Coldfire, ASIC
                    17 => AMOD LX CPE
                    18 => AMOD LX SoC CPE
                    22 => AMOD 5484 Coldfire, ASIC Base
                DD => Reserved
                    00 => 2.6 GHz
                    01 => 3.3 GHz
                    02 => 3.5 GHz
                    03 => 2.4 GHz
                    04 => 2.3 GHz
                    05 => 700MHz
                    06 => 3.7 GHz
                EE => Special Options
                    00 => External Antenna
                    01 => Vertical Antenna
                    02 => Horizontal Antenna"
        ::= { expedIfBssCpeStatusEntry 23 }

expedIfBssNumStaticHosts OBJECT-TYPE
        SYNTAX      INTEGER
        ACCESS      read-only
        STATUS      mandatory
        DESCRIPTION
            "Number of static hosts allowed for this CPE."
        ::= { expedIfBssCpeStatusEntry 24 }


expedIfBssCpeHostTable OBJECT-TYPE
        SYNTAX      SEQUENCE OF ExpedIfBssCpeHostEntry
        ACCESS      not-accessible
        STATUS      mandatory
        DESCRIPTION
            "A set of objects in the BSS, maintained for each
             Host/CPE connected to this base station."
        ::= { expedIfBssObjects 27}

expedIfBssCpeHostEntry OBJECT-TYPE
        SYNTAX      ExpedIfBssCpeHostEntry
        ACCESS      not-accessible
        STATUS      mandatory
        DESCRIPTION
            "Host information for a single CPE.
             An entry in this table exists for each CPE/Host
             that is connected to the BSS implementing this table."
        INDEX { expedIfBssCpeHostIndex }
        ::= { expedIfBssCpeHostTable 1 }

ExpedIfBssCpeHostEntry ::= SEQUENCE {
            expedIfBssCpeHostIndex               INTEGER,
            expedIfBssCpeHostMacAddress          DisplayString,
            expedIfBssCpeAirlinkMacAddress       DisplayString,
            expedIfBssCpeHostIpAddress           IpAddress,
            expedIfBssCpeHostIpType              DisplayString,
            expedIfBssCpeHostPPPOE               DisplayString,
            expedIfBssCpeHostVLANID              INTEGER
        }

expedIfBssCpeHostIndex OBJECT-TYPE
        SYNTAX      INTEGER (1..2147483647)
        ACCESS      read-only
        STATUS      mandatory
        DESCRIPTION
            "Index value to uniquely identify an entry in this table."
        ::= { expedIfBssCpeHostEntry 1 }

expedIfBssCpeHostMacAddress OBJECT-TYPE
        SYNTAX      DisplayString
        ACCESS      read-only
        STATUS      mandatory
        DESCRIPTION
            "MAC address of this CPE/Host. "
        ::= { expedIfBssCpeHostEntry 2 }

expedIfBssCpeAirlinkMacAddress OBJECT-TYPE
        SYNTAX      DisplayString
        ACCESS      read-only
        STATUS      mandatory
        DESCRIPTION
            "Airlink MAC address of this CPE."
        ::= { expedIfBssCpeHostEntry 3 }


expedIfBssCpeHostIpAddress OBJECT-TYPE
        SYNTAX      IpAddress
        ACCESS      read-only
        STATUS      mandatory
        DESCRIPTION
            "IP address of this Host. "
        ::= { expedIfBssCpeHostEntry 4 }

expedIfBssCpeHostIpType OBJECT-TYPE
        SYNTAX      DisplayString
        ACCESS      read-only
        STATUS      mandatory
        DESCRIPTION
            "Indicates the type of host.  Either dynamic, static or bound
             CPE Host."
        ::= { expedIfBssCpeHostEntry 5 }

expedIfBssCpeHostPPPOE OBJECT-TYPE
        SYNTAX      DisplayString
        ACCESS      read-only
        STATUS      mandatory
        DESCRIPTION
            "Indicates status of any PPOE sessions."
        ::= { expedIfBssCpeHostEntry 6 }


expedIfBssCpeHostVLANID OBJECT-TYPE
        SYNTAX      INTEGER
        ACCESS      read-only
        STATUS      mandatory
        DESCRIPTION
            "Indicates VLAN ID the Host is on "
        ::= { expedIfBssCpeHostEntry 7 }


expedIfBssVlanTable OBJECT-TYPE
        SYNTAX      SEQUENCE OF ExpedIfBssVlanEntry
        ACCESS      not-accessible
        STATUS      mandatory
        DESCRIPTION
            "A set of objects in the BSS, maintained for each
             CPE connected to this base station."
        ::= { expedIfBssObjects 28 }

expedIfBssVlanEntry OBJECT-TYPE
        SYNTAX      ExpedIfBssVlanEntry
        ACCESS      not-accessible
        STATUS      mandatory
        DESCRIPTION
            "Stats information for a single VLAN ID.
             An entry in this table exists for each VLAN."
        INDEX { expedIfBssVlanIndex  }
        ::= { expedIfBssVlanTable 1 }

ExpedIfBssVlanEntry ::= SEQUENCE {
            expedIfBssVlanIndex             INTEGER,
            expedIfBssVlanNumOfCpes         INTEGER,
            expedIfBssVlanUpBytes           Counter,
            expedIfBssVlanUpUnicastPkts     Counter,
            expedIfBssVlanUpNUnicastPkts    Counter,
            expedIfBssVlanDnBytes           Counter,
            expedIfBssVlanDnUnicastPkts     Counter,
            expedIfBssVlanDnNUnicastPkts    Counter,
            expedIfBssVlanNumOfHosts        INTEGER
}

expedIfBssVlanIndex OBJECT-TYPE
        SYNTAX      INTEGER (1..2147483647)
        ACCESS      read-only
        STATUS      mandatory
        DESCRIPTION
            "Index value to uniquely identify an entry in this table.
             For an individual VLAN, this index value should
             not change during BSS uptime."
        ::= { expedIfBssVlanEntry 1 }

expedIfBssVlanNumOfCpes OBJECT-TYPE
        SYNTAX      INTEGER
        ACCESS      read-only
        STATUS      mandatory
        DESCRIPTION
            "Number of CPEs on this VLAN"
        ::= { expedIfBssVlanEntry 2 }

expedIfBssVlanUpBytes OBJECT-TYPE
        SYNTAX      Counter
        ACCESS      read-only
        STATUS      mandatory
        DESCRIPTION
            "Number of uplink bytes for this VLAN."
        ::= { expedIfBssVlanEntry 3 }

expedIfBssVlanUpUnicastPkts OBJECT-TYPE
        SYNTAX      Counter
        ACCESS      read-only
        STATUS      mandatory
        DESCRIPTION
            "Number of uplink unicast packets for this VLAN."
        ::= { expedIfBssVlanEntry 4 }

expedIfBssVlanUpNUnicastPkts OBJECT-TYPE
        SYNTAX      Counter
        ACCESS      read-only
        STATUS      mandatory
        DESCRIPTION
            "Number of uplink broadcast packets for this VLAN."
        ::= { expedIfBssVlanEntry 5 }

expedIfBssVlanDnBytes OBJECT-TYPE
        SYNTAX      Counter
        ACCESS      read-only
        STATUS      mandatory
        DESCRIPTION
            "Number of downlink bytes for this VLAN."
        ::= { expedIfBssVlanEntry 6 }

expedIfBssVlanDnUnicastPkts OBJECT-TYPE
        SYNTAX      Counter
        ACCESS      read-only
        STATUS      mandatory
        DESCRIPTION
            "Number of downlink unicast packets for this VLAN."
        ::= { expedIfBssVlanEntry 7 }

expedIfBssVlanDnNUnicastPkts OBJECT-TYPE
        SYNTAX      Counter
        ACCESS      read-only
        STATUS      mandatory
        DESCRIPTION
            "Number of downlink broadcast packets for this VLAN."
        ::= { expedIfBssVlanEntry 8 }

expedIfBssVlanNumOfHosts OBJECT-TYPE
        SYNTAX      INTEGER
        ACCESS      read-only
        STATUS      mandatory
        DESCRIPTION
            "Number of hosts on this VLAN"
        ::= { expedIfBssVlanEntry 9 }

expedIfBssCPERemoteStatsTable OBJECT-TYPE
        SYNTAX      SEQUENCE OF ExpedIfBssCPERemoteEntry
        ACCESS      not-accessible
        STATUS      mandatory
        DESCRIPTION
            "Table of remote snmp stats gatherered over the air from each CPE."
        ::= { expedIfBssObjects 29 }

expedIfBssCPERemoteEntry OBJECT-TYPE
        SYNTAX      ExpedIfBssCPERemoteEntry
        ACCESS      not-accessible
        STATUS      mandatory
        DESCRIPTION
            "Table of remote snmp stats gatherered over the air from each CPE."
        INDEX { expedIfBssRemoteCPEIndex  }
        ::= { expedIfBssCPERemoteStatsTable 1 }

ExpedIfBssCPERemoteEntry ::= SEQUENCE {
            expedIfBssRemoteCPEIndex        INTEGER,
            expedIfBssRemoteCPEMacAddress   DisplayString,
            expedIfBssRemoteCPEPollSuccess  TruthValue,
            expedIfBssRemoteSlot1-Success   Counter,
            expedIfBssRemoteSlot1-NoAccess  Counter,
            expedIfBssRemoteSlot1-Failed    Counter,
            expedIfBssRemoteSlot2-Success   Counter,
            expedIfBssRemoteSlot2-NoAccess  Counter,
            expedIfBssRemoteSlot2-Failed    Counter,
            expedIfBssRemoteSlot3-Success   Counter,
            expedIfBssRemoteSlot3-NoAccess   Counter,
            expedIfBssRemoteSlot3-Failed   Counter,
            expedIfBssRemoteSlot4-Success   Counter,
            expedIfBssRemoteSlot4-NoAccess   Counter,
            expedIfBssRemoteSlot4-Failed   Counter,
            expedIfBssRemoteSlot5-Success   Counter,
            expedIfBssRemoteSlot5-NoAccess   Counter,
            expedIfBssRemoteSlot5-Failed   Counter,
            expedIfBssRemoteSlot6-Success   Counter,
            expedIfBssRemoteSlot6-NoAccess   Counter,
            expedIfBssRemoteSlot6-Failed        Counter,
            expedIfBssRemoteSlot1-ACK           Counter,
            expedIfBssRemoteSlot1-NACK          Counter,
            expedIfBssRemoteSlot1-Busy          Counter,
            expedIfBssRemoteSlot1-Free          Counter,
            expedIfBssRemoteSlot1-Lost          Counter,
            expedIfBssRemoteSlot1-Attempt       Counter,
            expedIfBssRemoteSlot2-ACK           Counter,
            expedIfBssRemoteSlot2-NACK          Counter,
            expedIfBssRemoteSlot2-Busy          Counter,
            expedIfBssRemoteSlot2-Free          Counter,
            expedIfBssRemoteSlot2-Lost          Counter,
            expedIfBssRemoteSlot2-Attempt       Counter,
            expedIfBssRemoteSlot3-ACK           Counter,
            expedIfBssRemoteSlot3-NACK          Counter,
            expedIfBssRemoteSlot3-Busy          Counter,
            expedIfBssRemoteSlot3-Free          Counter,
            expedIfBssRemoteSlot3-Lost          Counter,
            expedIfBssRemoteSlot3-Attempt       Counter,
            expedIfBssRemoteSlot4-ACK           Counter,
            expedIfBssRemoteSlot4-NACK          Counter,
            expedIfBssRemoteSlot4-Busy          Counter,
            expedIfBssRemoteSlot4-Free          Counter,
            expedIfBssRemoteSlot4-Lost          Counter,
            expedIfBssRemoteSlot4-Attempt       Counter,
            expedIfBssRemoteSlot5-ACK           Counter,
            expedIfBssRemoteSlot5-NACK          Counter,
            expedIfBssRemoteSlot5-Busy          Counter,
            expedIfBssRemoteSlot5-Free          Counter,
            expedIfBssRemoteSlot5-Lost          Counter,
            expedIfBssRemoteSlot5-Attempt       Counter,
            expedIfBssRemoteSlot6-ACK           Counter,
            expedIfBssRemoteSlot6-NACK          Counter,
            expedIfBssRemoteSlot6-Busy          Counter,
            expedIfBssRemoteSlot6-Free          Counter,
            expedIfBssRemoteSlot6-Lost          Counter,
            expedIfBssRemoteSlot6-Attempt       Counter,
            expedIfBssRemoteGoodSymbols         Counter,
            expedIfBssRemoteBadSymbols          Counter,
            expedIfBssRemoteUnderFlows          Counter,
            expedIfBssRemoteOverFlows           Counter,
            expedIfBssRemoteSymbolCount         Counter,
            expedIfBssRemoteBadSymbolCount      Counter,
            expedIfBssRemoteBER                 INTEGER,
            expedIfBssRemoteAvRSSI              INTEGER,
            expedIfBssRemoteAvVT                INTEGER,
            expedIfBssRemoteAccumRS             Counter,
            expedIfBssRemoteScore               Counter,
            expedIfBssRemoteAirConnectTime      DisplayString,
            expedIfBssRemoteDiscDownlink        Counter,
            expedIfBssRemoteDisconnectUpLink    Counter,
            expedIfBssRemoteHomeColorCode       INTEGER,
            expedIfBssRemoteExtendedRange       TruthValue,
            expedIfBssRemoteRangingValue        INTEGER,
            expedIfBssRemoteTriggerValue        INTEGER,
            expedIfBssRemoteCPEBaseObsCh1       INTEGER,
            expedIfBssRemoteCPEBaseObsMac1      DisplayString,
            expedIfBssRemoteCPEBaseObsCC1       INTEGER,
            expedIfBssRemoteCPEBaseObsScore1    INTEGER,
            expedIfBssRemoteCPEBaseObsAuth1     TruthValue,
            expedIfBssRemoteCPEBaseObsBusy1     TruthValue,
            expedIfBssRemoteCPEBaseObsRang1     TruthValue,
            expedIfBssRemoteCPEBaseObsCh2       INTEGER,
            expedIfBssRemoteCPEBaseObsMac2      DisplayString,
            expedIfBssRemoteCPEBaseObsCC2       INTEGER,
            expedIfBssRemoteCPEBaseObsScore2    INTEGER,
            expedIfBssRemoteCPEBaseObsAuth2     TruthValue,
            expedIfBssRemoteCPEBaseObsBusy2     TruthValue,
            expedIfBssRemoteCPEBaseObsRang2     TruthValue,
            expedIfBssRemoteCPEBaseObsCh3       INTEGER,
            expedIfBssRemoteCPEBaseObsMac3      DisplayString,
            expedIfBssRemoteCPEBaseObsCC3       INTEGER,
            expedIfBssRemoteCPEBaseObsScore3    INTEGER,
            expedIfBssRemoteCPEBaseObsAuth3     TruthValue,
            expedIfBssRemoteCPEBaseObsBusy3     TruthValue,
            expedIfBssRemoteCPEBaseObsRang3     TruthValue,
            expedIfBssRemoteCPEBaseObsCh4       INTEGER,
            expedIfBssRemoteCPEBaseObsMac4      DisplayString,
            expedIfBssRemoteCPEBaseObsCC4       INTEGER,
            expedIfBssRemoteCPEBaseObsScore4    INTEGER,
            expedIfBssRemoteCPEBaseObsAuth4     TruthValue,
            expedIfBssRemoteCPEBaseObsBusy4     TruthValue,
            expedIfBssRemoteCPEBaseObsRang4     TruthValue,
            expedIfBssRemoteCPEBaseObsCh5       INTEGER,
            expedIfBssRemoteCPEBaseObsMac5      DisplayString,
            expedIfBssRemoteCPEBaseObsCC5       INTEGER,
            expedIfBssRemoteCPEBaseObsScore5    INTEGER,
            expedIfBssRemoteCPEBaseObsAuth5     TruthValue,
            expedIfBssRemoteCPEBaseObsBusy5     TruthValue,
            expedIfBssRemoteCPEBaseObsRang5     TruthValue,
            expedIfBssRemoteCPEBaseObsCh6       INTEGER,
            expedIfBssRemoteCPEBaseObsMac6      DisplayString,
            expedIfBssRemoteCPEBaseObsCC6       INTEGER,
            expedIfBssRemoteCPEBaseObsScore6    INTEGER,
            expedIfBssRemoteCPEBaseObsAuth6     TruthValue,
            expedIfBssRemoteCPEBaseObsBusy6     TruthValue,
            expedIfBssRemoteCPEBaseObsRang6     TruthValue,
            expedIfBssRemoteCPENumActCalls      INTEGER,
            expedIfBssRemoteCPEDataPolls        Counter,
            expedIfBssRemoteCPEDryPolls         Counter,
            expedIfBssRemoteCPEUnexpected       Counter,
            expedIfBssRemoteCPEBWUsage          INTEGER,
            expedIfBssRemoteCPEEfficiency       INTEGER,
            expedIfBssRemoteCPEHighWater        Counter,
            expedIfBssRemoteCPEVoiceFrRt        INTEGER,
            expedIfBssRemoteCPEAvgNPI           INTEGER,
            expedIfBssRemoteCPEConcatBuffers    Counter,
            expedIfBssRemoteCPENumBufConcat     Counter,
            expedIfBssRemoteCPECurrentTemp      INTEGER,
            expedIfBssRemoteCPETxPower          INTEGER,
            expedIfBssRemoteCPEQPSKUp           Counter,
            expedIfBssRemoteCPEQPSKDown         Counter,
            expedIfBssRemoteCPE16QUp            Counter,
            expedIfBssRemoteCPE16QDown          Counter,
            expedIfBssRemoteCPE64QUp            Counter,
            expedIfBssRemoteCPE64QDown          Counter,
            expedIfBssRemoteCPE16QLiteUp        Counter,
            expedIfBssRemoteCPE16QLiteDown      Counter,
            expedIfBssRemoteCurrentRxLevel      DisplayString,
            expedIfBssRemoteCurrentTxLevel      DisplayString
            }

ExpedIfBssCPERemoteEntry1 ::= SEQUENCE {
            expedIfBssRemoteCPEIndex        INTEGER,
            expedIfBssRemoteCPEMacAddress   DisplayString,
            expedIfBssRemoteCPEPollSuccess  TruthValue,
            expedIfBssRemoteSlot1-Success   Counter,
            expedIfBssRemoteSlot1-NoAccess  Counter,
            expedIfBssRemoteSlot1-Failed    Counter,
            expedIfBssRemoteSlot2-Success   Counter,
            expedIfBssRemoteSlot2-NoAccess  Counter,
            expedIfBssRemoteSlot2-Failed    Counter,
            expedIfBssRemoteSlot3-Success   Counter,
            expedIfBssRemoteSlot3-NoAccess   Counter,
            expedIfBssRemoteSlot3-Failed   Counter,
            expedIfBssRemoteSlot4-Success   Counter,
            expedIfBssRemoteSlot4-NoAccess   Counter,
            expedIfBssRemoteSlot4-Failed   Counter,
            expedIfBssRemoteSlot5-Success   Counter,
            expedIfBssRemoteSlot5-NoAccess   Counter,
            expedIfBssRemoteSlot5-Failed   Counter,
            expedIfBssRemoteSlot6-Success   Counter,
            expedIfBssRemoteSlot6-NoAccess   Counter,
            expedIfBssRemoteSlot6-Failed   Counter
}
ExpedIfBssCPERemoteEntry2 ::= SEQUENCE {
            expedIfBssRemoteCPEIndex        INTEGER,
            expedIfBssRemoteCPEMacAddress   DisplayString,
            expedIfBssRemoteCPEPollSuccess  TruthValue,
            expedIfBssRemoteSlot1-ACK   Counter,
            expedIfBssRemoteSlot1-NACK   Counter,
            expedIfBssRemoteSlot1-Busy   Counter,
            expedIfBssRemoteSlot1-Free   Counter,
            expedIfBssRemoteSlot1-Lost   Counter,
            expedIfBssRemoteSlot1-Attempt   Counter,
            expedIfBssRemoteSlot2-ACK   Counter,
            expedIfBssRemoteSlot2-NACK   Counter,
            expedIfBssRemoteSlot2-Busy   Counter,
            expedIfBssRemoteSlot2-Free   Counter,
            expedIfBssRemoteSlot2-Lost   Counter,
            expedIfBssRemoteSlot2-Attempt   Counter,
            expedIfBssRemoteSlot3-ACK   Counter,
            expedIfBssRemoteSlot3-NACK   Counter,
            expedIfBssRemoteSlot3-Busy   Counter,
            expedIfBssRemoteSlot3-Free   Counter,
            expedIfBssRemoteSlot3-Lost   Counter,
            expedIfBssRemoteSlot3-Attempt   Counter,
            expedIfBssRemoteSlot4-ACK   Counter,
            expedIfBssRemoteSlot4-NACK   Counter,
            expedIfBssRemoteSlot4-Busy   Counter,
            expedIfBssRemoteSlot4-Free   Counter,
            expedIfBssRemoteSlot4-Lost   Counter,
            expedIfBssRemoteSlot4-Attempt   Counter,
            expedIfBssRemoteSlot5-ACK   Counter,
            expedIfBssRemoteSlot5-NACK   Counter,
            expedIfBssRemoteSlot5-Busy   Counter,
            expedIfBssRemoteSlot5-Free   Counter,
            expedIfBssRemoteSlot5-Lost   Counter,
            expedIfBssRemoteSlot5-Attempt   Counter,
            expedIfBssRemoteSlot6-ACK   Counter,
            expedIfBssRemoteSlot6-NACK   Counter,
            expedIfBssRemoteSlot6-Busy   Counter,
            expedIfBssRemoteSlot6-Free   Counter,
            expedIfBssRemoteSlot6-Lost   Counter,
            expedIfBssRemoteSlot6-Attempt   Counter
}
ExpedIfBssCPERemoteEntry3 ::= SEQUENCE {
            expedIfBssRemoteCPEIndex        INTEGER,
            expedIfBssRemoteCPEMacAddress   DisplayString,
            expedIfBssRemoteCPEPollSuccess  TruthValue,
            expedIfBssRemoteGoodSymbols   Counter,
            expedIfBssRemoteBadSymbols   Counter,
            expedIfBssRemoteUnderFlows   Counter,
            expedIfBssRemoteOverFlows   Counter,
            expedIfBssRemoteSymbolCount   Counter,
            expedIfBssRemoteBadSymbolCount   Counter,
            expedIfBssRemoteBER   INTEGER,
            expedIfBssRemoteAvRSSI   INTEGER,
            expedIfBssRemoteAvVT   INTEGER,
            expedIfBssRemoteAccumRS   Counter,
            expedIfBssRemoteScore   Counter,
            expedIfBssRemoteAirConnectTime   DisplayString,
            expedIfBssRemoteDiscDownlink   Counter,
            expedIfBssRemoteDisconnectUpLink   Counter,
            expedIfBssRemoteHomeColorCode   INTEGER,
            expedIfBssRemoteExtendedRange   TruthValue,
            expedIfBssRemoteRangingValue   INTEGER,
            expedIfBssRemoteTriggerValue   INTEGER
}
ExpedIfBssCPERemoteEntry4 ::= SEQUENCE {
            expedIfBssRemoteCPEIndex        INTEGER,
            expedIfBssRemoteCPEMacAddress   DisplayString,
            expedIfBssRemoteCPEPollSuccess  TruthValue,
            expedIfBssRemoteCPEBaseObsCh1 INTEGER,
            expedIfBssRemoteCPEBaseObsMac1 DisplayString,
            expedIfBssRemoteCPEBaseObsCC1 INTEGER,
            expedIfBssRemoteCPEBaseObsScore1 INTEGER,
            expedIfBssRemoteCPEBaseObsAuth1 TruthValue,
            expedIfBssRemoteCPEBaseObsBusy1 TruthValue,
            expedIfBssRemoteCPEBaseObsRang1 TruthValue,
            expedIfBssRemoteCPEBaseObsCh2 INTEGER,
            expedIfBssRemoteCPEBaseObsMac2 DisplayString,
            expedIfBssRemoteCPEBaseObsCC2 INTEGER,
            expedIfBssRemoteCPEBaseObsScore2 INTEGER,
            expedIfBssRemoteCPEBaseObsAuth2 TruthValue,
            expedIfBssRemoteCPEBaseObsBusy2 TruthValue,
            expedIfBssRemoteCPEBaseObsRang2 TruthValue,
            expedIfBssRemoteCPEBaseObsCh3 INTEGER,
            expedIfBssRemoteCPEBaseObsMac3 DisplayString,
            expedIfBssRemoteCPEBaseObsCC3 INTEGER,
            expedIfBssRemoteCPEBaseObsScore3 INTEGER,
            expedIfBssRemoteCPEBaseObsAuth3 TruthValue,
            expedIfBssRemoteCPEBaseObsBusy3 TruthValue,
            expedIfBssRemoteCPEBaseObsRang3 TruthValue,
            expedIfBssRemoteCPEBaseObsCh4 INTEGER,
            expedIfBssRemoteCPEBaseObsMac4 DisplayString,
            expedIfBssRemoteCPEBaseObsCC4 INTEGER,
            expedIfBssRemoteCPEBaseObsScore4 INTEGER,
            expedIfBssRemoteCPEBaseObsAuth4 TruthValue,
            expedIfBssRemoteCPEBaseObsBusy4 TruthValue,
            expedIfBssRemoteCPEBaseObsRang4 TruthValue,
            expedIfBssRemoteCPEBaseObsCh5 INTEGER,
            expedIfBssRemoteCPEBaseObsMac5 DisplayString,
            expedIfBssRemoteCPEBaseObsCC5 INTEGER,
            expedIfBssRemoteCPEBaseObsScore5 INTEGER,
            expedIfBssRemoteCPEBaseObsAuth5 TruthValue,
            expedIfBssRemoteCPEBaseObsBusy5 TruthValue,
            expedIfBssRemoteCPEBaseObsRang5 TruthValue,
            expedIfBssRemoteCPEBaseObsCh6 INTEGER,
            expedIfBssRemoteCPEBaseObsMac6 DisplayString,
            expedIfBssRemoteCPEBaseObsCC6 INTEGER,
            expedIfBssRemoteCPEBaseObsScore6 INTEGER,
            expedIfBssRemoteCPEBaseObsAuth6 TruthValue,
            expedIfBssRemoteCPEBaseObsBusy6 TruthValue,
            expedIfBssRemoteCPEBaseObsRang6 TruthValue
}

ExpedIfBssCPERemoteEntry5 ::= SEQUENCE {
       expedIfBssRemoteCPEPollSuccess  TruthValue,
        expedIfBssRemoteCPENumActCalls  INTEGER,
        expedIfBssRemoteCPEDataPolls    Counter,
        expedIfBssRemoteCPEDryPolls     Counter,
        expedIfBssRemoteCPEUnexpected   Counter,
        expedIfBssRemoteCPEBWUsage      INTEGER,
        expedIfBssRemoteCPEEfficiency   INTEGER,
        expedIfBssRemoteCPEHighWater    Counter,
        expedIfBssRemoteCPEVoiceFrRt INTEGER,
        expedIfBssRemoteCPEAvgNPI       INTEGER

}

ExpedIfBssCPERemoteEntry6 ::= SEQUENCE {
        expedIfBssRemoteCPEPollSuccess  TruthValue,
        expedIfBssRemoteCPEConcatBuffers Counter,
        expedIfBssRemoteCPENumBufConcat Counter,
        expedIfBssRemoteCPECurrentTemp  INTEGER,
        expedIfBssRemoteCPETxPower      INTEGER,
        expedIfBssRemoteCPEQPSKUp      Counter,
        expedIfBssRemoteCPEQPSKDown      Counter,
        expedIfBssRemoteCPE16QUp      Counter,
        expedIfBssRemoteCPE16QDown      Counter,
        expedIfBssRemoteCPE64QUp      Counter,
        expedIfBssRemoteCPE64QDown      Counter,
        expedIfBssRemoteCPE16QLiteUp      Counter,
        expedIfBssRemoteCPE16QLiteDown      Counter,
        expedIfBssRemoteCurrentRxLevel      DisplayString,
	    expedIfBssRemoteCurrentTxLevel     DisplayString
        }

expedIfBssRemoteCPEIndex OBJECT-TYPE
        SYNTAX      INTEGER (1..2147483647)
        ACCESS      read-only
        STATUS      mandatory
        DESCRIPTION
            "Index value to uniquely identify an entry in this table.
             For an individual CPE, this index value should
             not change during BSS uptime."
        ::= { expedIfBssCPERemoteEntry 1 }

expedIfBssRemoteCPEMacAddress OBJECT-TYPE
        SYNTAX      DisplayString
        ACCESS      read-only
        STATUS      mandatory
        DESCRIPTION
            "Mac Address of the CPE being remotely monitored."
        ::= { expedIfBssCPERemoteEntry 2 }

expedIfBssRemoteCPEPollSuccess OBJECT-TYPE
        SYNTAX      TruthValue
        ACCESS      read-only
        STATUS      mandatory
        DESCRIPTION
            "Indicates the success of the last poll.   True indicates a succes,
            False indicates SNMP was not able to get stats from the CPE."
        ::= { expedIfBssCPERemoteEntry 3 }

expedIfBssRemoteSlot1-Success OBJECT-TYPE
        SYNTAX      Counter
        ACCESS      read-only
        STATUS      mandatory
        DESCRIPTION
            "Number of messages successful on slot."
        ::= { expedIfBssCPERemoteEntry 4 }

expedIfBssRemoteSlot1-NoAccess OBJECT-TYPE
        SYNTAX      Counter
        ACCESS      read-only
        STATUS      mandatory
        DESCRIPTION
            "Number of message send failures due to uplink slot acquisition failure on slot."
        ::= { expedIfBssCPERemoteEntry 5 }

expedIfBssRemoteSlot1-Failed OBJECT-TYPE
        SYNTAX      Counter
        ACCESS      read-only
        STATUS      mandatory
        DESCRIPTION
            "Number of message send failures due to loss of uplink slot."
        ::= { expedIfBssCPERemoteEntry 6 }


expedIfBssRemoteSlot2-Success OBJECT-TYPE
        SYNTAX      Counter
        ACCESS      read-only
        STATUS      mandatory
        DESCRIPTION
            "Number of messages successful on slot."
        ::= { expedIfBssCPERemoteEntry 7 }

expedIfBssRemoteSlot2-NoAccess OBJECT-TYPE
        SYNTAX      Counter
        ACCESS      read-only
        STATUS      mandatory
        DESCRIPTION
            "Number of message send failures due to uplink slot acquisition failure on slot."
        ::= { expedIfBssCPERemoteEntry 8 }

expedIfBssRemoteSlot2-Failed OBJECT-TYPE
        SYNTAX      Counter
        ACCESS      read-only
        STATUS      mandatory
        DESCRIPTION
            "Number of message send failures due to loss of uplink slot."
        ::= { expedIfBssCPERemoteEntry 9 }

expedIfBssRemoteSlot3-Success OBJECT-TYPE
        SYNTAX      Counter
        ACCESS      read-only
        STATUS      mandatory
        DESCRIPTION
            "Number of messages successful on slot."
        ::= { expedIfBssCPERemoteEntry 10 }

expedIfBssRemoteSlot3-NoAccess OBJECT-TYPE
        SYNTAX      Counter
        ACCESS      read-only
        STATUS      mandatory
        DESCRIPTION
            "Number of message send failures due to uplink slot acquisition failure on slot."
        ::= { expedIfBssCPERemoteEntry 11 }

expedIfBssRemoteSlot3-Failed OBJECT-TYPE
        SYNTAX      Counter
        ACCESS      read-only
        STATUS      mandatory
        DESCRIPTION
            "Number of message send failures due to loss of uplink slot."
        ::= { expedIfBssCPERemoteEntry 12 }

expedIfBssRemoteSlot4-Success OBJECT-TYPE
        SYNTAX      Counter
        ACCESS      read-only
        STATUS      mandatory
        DESCRIPTION
            "Number of messages successful on slot"
        ::= { expedIfBssCPERemoteEntry 13 }

expedIfBssRemoteSlot4-NoAccess OBJECT-TYPE
        SYNTAX      Counter
        ACCESS      read-only
        STATUS      mandatory
        DESCRIPTION
            "Number of message send failures due to uplink slot acquisition failure on slot."
        ::= { expedIfBssCPERemoteEntry 14}

expedIfBssRemoteSlot4-Failed OBJECT-TYPE
        SYNTAX      Counter
        ACCESS      read-only
        STATUS      mandatory
        DESCRIPTION
            "Number of message send failures due to loss of uplink slot."
        ::= { expedIfBssCPERemoteEntry 15 }

expedIfBssRemoteSlot5-Success OBJECT-TYPE
        SYNTAX      Counter
        ACCESS      read-only
        STATUS      mandatory
        DESCRIPTION
            "Number of messages successful on slot"
        ::= { expedIfBssCPERemoteEntry 16 }

expedIfBssRemoteSlot5-NoAccess OBJECT-TYPE
        SYNTAX      Counter
        ACCESS      read-only
        STATUS      mandatory
        DESCRIPTION
            "Number of message send failures due to uplink slot acquisition failure on slot."
        ::= { expedIfBssCPERemoteEntry 17 }

expedIfBssRemoteSlot5-Failed OBJECT-TYPE
        SYNTAX      Counter
        ACCESS      read-only
        STATUS      mandatory
        DESCRIPTION
            "Number of message send failures due to loss of uplink slot."
        ::= { expedIfBssCPERemoteEntry 18 }

expedIfBssRemoteSlot6-Success OBJECT-TYPE
        SYNTAX      Counter
        ACCESS      read-only
        STATUS      mandatory
        DESCRIPTION
            "Number of messages successful on slot."
        ::= { expedIfBssCPERemoteEntry 19 }

expedIfBssRemoteSlot6-NoAccess OBJECT-TYPE
        SYNTAX      Counter
        ACCESS      read-only
        STATUS      mandatory
        DESCRIPTION
            "Number of message send failures due to uplink slot acquisition failure on slot."
        ::= { expedIfBssCPERemoteEntry 20 }

expedIfBssRemoteSlot6-Failed OBJECT-TYPE
        SYNTAX      Counter
        ACCESS      read-only
        STATUS      mandatory
        DESCRIPTION
            "Number of message send failures due to loss of uplink slot."
        ::= { expedIfBssCPERemoteEntry 21 }


expedIfBssRemoteSlot1-ACK OBJECT-TYPE
        SYNTAX      Counter
        ACCESS      read-only
        STATUS      mandatory
        DESCRIPTION
            "Number of successful symbol transmissions."
        ::= { expedIfBssCPERemoteEntry 22 }

expedIfBssRemoteSlot1-NACK OBJECT-TYPE
        SYNTAX      Counter
        ACCESS      read-only
        STATUS      mandatory
        DESCRIPTION
            "Number of symbol retries."
        ::= { expedIfBssCPERemoteEntry 23 }

expedIfBssRemoteSlot1-Busy OBJECT-TYPE
        SYNTAX      Counter
        ACCESS      read-only 
        STATUS      mandatory
        DESCRIPTION
            "Number of slot acquisition backoff due to slot busy."
        ::= { expedIfBssCPERemoteEntry 24 }

expedIfBssRemoteSlot1-Free OBJECT-TYPE
        SYNTAX      Counter
        ACCESS      read-only
        STATUS      mandatory
        DESCRIPTION
            "Number of slot acquisition failures."
        ::= { expedIfBssCPERemoteEntry 25 }

expedIfBssRemoteSlot1-Lost OBJECT-TYPE
        SYNTAX      Counter
        ACCESS      read-only
        STATUS      mandatory
        DESCRIPTION
            "Number of slot failures due to lost contention."
        ::= { expedIfBssCPERemoteEntry 26 }

expedIfBssRemoteSlot1-Attempt OBJECT-TYPE
        SYNTAX      Counter
        ACCESS      read-only
        STATUS      mandatory
        DESCRIPTION
            "Number of slot acquisitions."
        ::= { expedIfBssCPERemoteEntry 27 }

expedIfBssRemoteSlot2-ACK OBJECT-TYPE
        SYNTAX      Counter
        ACCESS      read-only
        STATUS      mandatory
        DESCRIPTION
            "Number of successful symbol transmissions."
        ::= { expedIfBssCPERemoteEntry 28 }

expedIfBssRemoteSlot2-NACK OBJECT-TYPE
        SYNTAX      Counter
        ACCESS      read-only
        STATUS      mandatory
        DESCRIPTION
            "Number of symbol retries."
        ::= { expedIfBssCPERemoteEntry 29 }

expedIfBssRemoteSlot2-Busy OBJECT-TYPE
        SYNTAX      Counter
        ACCESS      read-only
        STATUS      mandatory
        DESCRIPTION
            "Number of slot acquisition backoff due to slot busy."
        ::= { expedIfBssCPERemoteEntry 30}

expedIfBssRemoteSlot2-Free OBJECT-TYPE
        SYNTAX      Counter
        ACCESS      read-only
        STATUS      mandatory
        DESCRIPTION
            "Number of slot acquisition failures."
        ::= { expedIfBssCPERemoteEntry 31 }

expedIfBssRemoteSlot2-Lost OBJECT-TYPE
        SYNTAX      Counter
        ACCESS      read-only
        STATUS      mandatory
        DESCRIPTION
            "Number of slot failures due to lost contention."
        ::= { expedIfBssCPERemoteEntry 32 }

expedIfBssRemoteSlot2-Attempt OBJECT-TYPE
        SYNTAX      Counter
        ACCESS      read-only
        STATUS      mandatory
        DESCRIPTION
            "Number of slot acquisitions."
        ::= { expedIfBssCPERemoteEntry 33 }

expedIfBssRemoteSlot3-ACK OBJECT-TYPE
        SYNTAX      Counter
        ACCESS      read-only
        STATUS      mandatory
        DESCRIPTION
            "Number of successful symbol transmissions."
        ::= { expedIfBssCPERemoteEntry 34 }

expedIfBssRemoteSlot3-NACK OBJECT-TYPE
        SYNTAX      Counter
        ACCESS      read-only
        STATUS      mandatory
        DESCRIPTION
            "Number of symbol retries."
        ::= { expedIfBssCPERemoteEntry 35 }

expedIfBssRemoteSlot3-Busy OBJECT-TYPE
        SYNTAX      Counter
        ACCESS      read-only
        STATUS      mandatory
        DESCRIPTION
            "Number of slot acquisition backoff due to slot busy."
        ::= { expedIfBssCPERemoteEntry 36 }

expedIfBssRemoteSlot3-Free OBJECT-TYPE
        SYNTAX      Counter
        ACCESS      read-only
        STATUS      mandatory
        DESCRIPTION
            "Number of slot acquisition failures."
        ::= { expedIfBssCPERemoteEntry 37 }

expedIfBssRemoteSlot3-Lost OBJECT-TYPE
        SYNTAX      Counter
        ACCESS      read-only
        STATUS      mandatory
        DESCRIPTION
            "Number of slot failures due to lost contention."
        ::= { expedIfBssCPERemoteEntry 38 }

expedIfBssRemoteSlot3-Attempt OBJECT-TYPE
        SYNTAX      Counter
        ACCESS      read-only
        STATUS      mandatory
        DESCRIPTION
            "Number of slot acquisitions."
        ::= { expedIfBssCPERemoteEntry 39 }


expedIfBssRemoteSlot4-ACK OBJECT-TYPE
        SYNTAX      Counter
        ACCESS      read-only
        STATUS      mandatory
        DESCRIPTION
            "Number of successful symbol transmissions."
        ::= { expedIfBssCPERemoteEntry 40 }

expedIfBssRemoteSlot4-NACK OBJECT-TYPE
        SYNTAX      Counter
        ACCESS      read-only
        STATUS      mandatory
        DESCRIPTION
            "Number of symbol retries."
        ::= { expedIfBssCPERemoteEntry 41 }

expedIfBssRemoteSlot4-Busy OBJECT-TYPE
        SYNTAX      Counter
        ACCESS      read-only
        STATUS      mandatory
        DESCRIPTION
            "Number of slot acquisition backoff due to slot busy."
        ::= { expedIfBssCPERemoteEntry 42 }

expedIfBssRemoteSlot4-Free OBJECT-TYPE
        SYNTAX      Counter
        ACCESS      read-only
        STATUS      mandatory
        DESCRIPTION
            "Number of slot acquisition failures."
        ::= { expedIfBssCPERemoteEntry 43 }

expedIfBssRemoteSlot4-Lost OBJECT-TYPE
        SYNTAX      Counter
        ACCESS      read-only
        STATUS      mandatory
        DESCRIPTION
            "Number of slot failures due to lost contention."
        ::= { expedIfBssCPERemoteEntry 44 }

expedIfBssRemoteSlot4-Attempt OBJECT-TYPE
        SYNTAX      Counter
        ACCESS      read-only
        STATUS      mandatory
        DESCRIPTION
            "Number of slot acquisitions."
        ::= { expedIfBssCPERemoteEntry 45 }

expedIfBssRemoteSlot5-ACK OBJECT-TYPE
        SYNTAX      Counter
        ACCESS      read-only
        STATUS      mandatory
        DESCRIPTION
            "Number of successful symbol transmissions."
        ::= { expedIfBssCPERemoteEntry 46 }

expedIfBssRemoteSlot5-NACK OBJECT-TYPE
        SYNTAX      Counter
        ACCESS      read-only
        STATUS      mandatory
        DESCRIPTION
            "Number of symbol retries."
        ::= { expedIfBssCPERemoteEntry 47 }

expedIfBssRemoteSlot5-Busy OBJECT-TYPE
        SYNTAX      Counter
        ACCESS      read-only
        STATUS      mandatory
        DESCRIPTION
            "Number of slot acquisition backoff due to slot busy."
        ::= { expedIfBssCPERemoteEntry 48 }

expedIfBssRemoteSlot5-Free OBJECT-TYPE
        SYNTAX      Counter
        ACCESS      read-only
        STATUS      mandatory
        DESCRIPTION
            "Number of slot acquisition failures."
        ::= { expedIfBssCPERemoteEntry 49 }

expedIfBssRemoteSlot5-Lost OBJECT-TYPE
        SYNTAX      Counter
        ACCESS      read-only
        STATUS      mandatory
        DESCRIPTION
            "Number of slot failures due to lost contention."
        ::= { expedIfBssCPERemoteEntry 50 }

expedIfBssRemoteSlot5-Attempt OBJECT-TYPE
        SYNTAX      Counter
        ACCESS      read-only
        STATUS      mandatory
        DESCRIPTION
            "Number of slot acquisitions."
        ::= { expedIfBssCPERemoteEntry 51 }


expedIfBssRemoteSlot6-ACK OBJECT-TYPE
        SYNTAX      Counter
        ACCESS      read-only
        STATUS      mandatory
        DESCRIPTION
            "Number of successful symbol transmissions."
        ::= { expedIfBssCPERemoteEntry 52 }

expedIfBssRemoteSlot6-NACK OBJECT-TYPE
        SYNTAX      Counter
        ACCESS      read-only
        STATUS      mandatory
        DESCRIPTION
            "Number of symbol retries."
        ::= { expedIfBssCPERemoteEntry 53 }

expedIfBssRemoteSlot6-Busy OBJECT-TYPE
        SYNTAX      Counter
        ACCESS      read-only
        STATUS      mandatory
        DESCRIPTION
            "Number of slot acquisition backoff due to slot busy."
        ::= { expedIfBssCPERemoteEntry 54 }

expedIfBssRemoteSlot6-Free OBJECT-TYPE
        SYNTAX      Counter
        ACCESS      read-only
        STATUS      mandatory
        DESCRIPTION
            "Number of slot acquisition failures."
        ::= { expedIfBssCPERemoteEntry 55 }

expedIfBssRemoteSlot6-Lost OBJECT-TYPE
        SYNTAX      Counter
        ACCESS      read-only
        STATUS      mandatory
        DESCRIPTION
            "Number of slot failures due to lost contention."
        ::= { expedIfBssCPERemoteEntry 56 }

expedIfBssRemoteSlot6-Attempt OBJECT-TYPE
        SYNTAX      Counter
        ACCESS      read-only
        STATUS      mandatory
        DESCRIPTION
            "Number of slot acquisitions."
        ::= { expedIfBssCPERemoteEntry 57 }


expedIfBssRemoteGoodSymbols OBJECT-TYPE
        SYNTAX      Counter
        ACCESS      read-only
        STATUS      mandatory
        DESCRIPTION
            "Number of good symbols received by the CPE."
        ::= { expedIfBssCPERemoteEntry 58 }

expedIfBssRemoteBadSymbols OBJECT-TYPE
        SYNTAX      Counter
        ACCESS      read-only
        STATUS      mandatory
        DESCRIPTION
            "Number of bad symbols received by the CPE."
        ::= { expedIfBssCPERemoteEntry 59 }

expedIfBssRemoteUnderFlows OBJECT-TYPE
        SYNTAX      Counter
        ACCESS      read-only
        STATUS      mandatory
        DESCRIPTION
            "Number of times the signal processor was in an underflow condition."
        ::= { expedIfBssCPERemoteEntry 60 }


expedIfBssRemoteOverFlows OBJECT-TYPE
        SYNTAX      Counter
        ACCESS      read-only
        STATUS      mandatory
        DESCRIPTION
            "Number of times the signal processor was in an overflow condition."
        ::= { expedIfBssCPERemoteEntry 61 }


expedIfBssRemoteSymbolCount OBJECT-TYPE
        SYNTAX      Counter
        ACCESS      read-only
        STATUS      mandatory
        DESCRIPTION
            "Number of symbols evaluated to accumulate the score."
        ::= { expedIfBssCPERemoteEntry 62 }


expedIfBssRemoteBadSymbolCount OBJECT-TYPE
        SYNTAX      Counter
        ACCESS      read-only
        STATUS      mandatory
        DESCRIPTION
            "Number of bad symbols in the evaluation of the score."
        ::= { expedIfBssCPERemoteEntry 63 }

expedIfBssRemoteBER OBJECT-TYPE
        SYNTAX      INTEGER
        ACCESS      read-only
        STATUS      mandatory
        DESCRIPTION
            "Bit Error rate calculated during the score evaluation."
        ::= { expedIfBssCPERemoteEntry 64 }

expedIfBssRemoteAvRSSI OBJECT-TYPE
        SYNTAX      INTEGER
        ACCESS      read-only
        STATUS      mandatory
        DESCRIPTION
            "Average RSSI calculated during the score evaluation."
        ::= { expedIfBssCPERemoteEntry 65 }

expedIfBssRemoteAvVT OBJECT-TYPE
        SYNTAX      INTEGER
        ACCESS      read-only
        STATUS      mandatory
        DESCRIPTION
            "Average Viterbi calculated during the score evaluation."
        ::= { expedIfBssCPERemoteEntry 66 }

expedIfBssRemoteAccumRS OBJECT-TYPE
        SYNTAX      Counter
        ACCESS      read-only
        STATUS      mandatory
        DESCRIPTION
            "Reed Solomon errors calculated during the score evaluation."
        ::= { expedIfBssCPERemoteEntry 67 }

expedIfBssRemoteScore OBJECT-TYPE
        SYNTAX      Counter
        ACCESS      read-only
        STATUS      mandatory
        DESCRIPTION
            "Accumulated calculated score."
        ::= { expedIfBssCPERemoteEntry 68 }


expedIfBssRemoteAirConnectTime OBJECT-TYPE
        SYNTAX      DisplayString
        ACCESS      read-only
        STATUS      mandatory
        DESCRIPTION
            "Indicates how long the CPE has been connected to a base station."
        ::= { expedIfBssCPERemoteEntry 69 }

expedIfBssRemoteDiscDownlink OBJECT-TYPE
        SYNTAX      Counter
        ACCESS      read-only
        STATUS      mandatory
        DESCRIPTION
            "Number of disconnects due to a downlink failure."
        ::= { expedIfBssCPERemoteEntry 70 }

expedIfBssRemoteDisconnectUpLink OBJECT-TYPE
        SYNTAX      Counter
        ACCESS      read-only
        STATUS      mandatory
        DESCRIPTION
            "Number of disconnects due to a uplink failure."
        ::= { expedIfBssCPERemoteEntry 71 }


expedIfBssRemoteHomeColorCode OBJECT-TYPE
        SYNTAX      INTEGER
        ACCESS      read-only
        STATUS      mandatory
        DESCRIPTION
            "Indicates the home color code assigned to this CPE."
        ::= { expedIfBssCPERemoteEntry 72 }

expedIfBssRemoteExtendedRange OBJECT-TYPE
        SYNTAX      TruthValue
        ACCESS      read-only
        STATUS      mandatory
        DESCRIPTION
            "Indicates whether the CPE is enabled for extended range or not."
        ::= { expedIfBssCPERemoteEntry 73 }

expedIfBssRemoteRangingValue OBJECT-TYPE
        SYNTAX      INTEGER
        ACCESS      read-only
        STATUS      mandatory
        DESCRIPTION
            "Indicates the maximum distance (range) the CPE will try to register at,
            before moving on to a different base."
        ::= { expedIfBssCPERemoteEntry 74 }

expedIfBssRemoteTriggerValue OBJECT-TYPE
        SYNTAX      INTEGER
        ACCESS      read-only
        STATUS      mandatory
        DESCRIPTION
            "The actual trigger value that the signal processor is programmed with."
        ::= { expedIfBssCPERemoteEntry 75 }


expedIfBssRemoteCPEBaseObsCh1 OBJECT-TYPE
        SYNTAX      INTEGER (1..32)
        ACCESS      read-only
        STATUS      mandatory
        DESCRIPTION
            "Channel of the base station observed by the CPE in the base observation table."
        ::= { expedIfBssCPERemoteEntry 76 }

expedIfBssRemoteCPEBaseObsMac1 OBJECT-TYPE
        SYNTAX      DisplayString
        ACCESS      read-only
        STATUS      mandatory
        DESCRIPTION
            "Mac address of the base station observed by the CPE in the observation table."
        ::= { expedIfBssCPERemoteEntry 77 }

expedIfBssRemoteCPEBaseObsCC1 OBJECT-TYPE
        SYNTAX      INTEGER (1..2147483647)
        ACCESS      read-only
        STATUS      mandatory
        DESCRIPTION
            "Color code of the base station observed by the CPE in the observation table."
        ::= { expedIfBssCPERemoteEntry 78 }


expedIfBssRemoteCPEBaseObsScore1 OBJECT-TYPE
        SYNTAX      INTEGER (1..2147483647)
        ACCESS      read-only
        STATUS      mandatory
        DESCRIPTION
            "Score of the base station observed by the CPE in the observation table."
        ::= { expedIfBssCPERemoteEntry 79 }

expedIfBssRemoteCPEBaseObsAuth1 OBJECT-TYPE
        SYNTAX      TruthValue
        ACCESS      read-only
        STATUS      mandatory
        DESCRIPTION
            "True indicates the CPE is authorized to use this base, False indicates that this CPE
            has been denied by this base."
        ::= { expedIfBssCPERemoteEntry 80 }

expedIfBssRemoteCPEBaseObsBusy1 OBJECT-TYPE
        SYNTAX      TruthValue
        ACCESS      read-only
        STATUS      mandatory
        DESCRIPTION
            "True indicates this base observed is busy and is not recommending registrations to it."
        ::= { expedIfBssCPERemoteEntry 81 }

expedIfBssRemoteCPEBaseObsRang1 OBJECT-TYPE
        SYNTAX      TruthValue
        ACCESS      read-only
        STATUS      mandatory
        DESCRIPTION
            "True indicates the CPE has completed extended ranging with this base station."
        ::= { expedIfBssCPERemoteEntry 82 }

expedIfBssRemoteCPEBaseObsCh2 OBJECT-TYPE
        SYNTAX      INTEGER (1..32)
        ACCESS      read-only
        STATUS      mandatory
        DESCRIPTION
            "Channel of the base station observed by the CPE in the base observation table."
        ::= { expedIfBssCPERemoteEntry 83 }

expedIfBssRemoteCPEBaseObsMac2 OBJECT-TYPE
        SYNTAX      DisplayString
        ACCESS      read-only
        STATUS      mandatory
        DESCRIPTION
            "Mac address of the base station observed by the CPE in the observation table."
        ::= { expedIfBssCPERemoteEntry 84 }

expedIfBssRemoteCPEBaseObsCC2 OBJECT-TYPE
        SYNTAX      INTEGER (1..2147483647)
        ACCESS      read-only
        STATUS      mandatory
        DESCRIPTION
            "Color code of the base station observed by the CPE in the observation table."
        ::= { expedIfBssCPERemoteEntry 85 }

expedIfBssRemoteCPEBaseObsScore2 OBJECT-TYPE
        SYNTAX      INTEGER (1..2147483647)
        ACCESS      read-only
        STATUS      mandatory
        DESCRIPTION
            "Score of the base station observed by the CPE in the observation table."
        ::= { expedIfBssCPERemoteEntry 86 }


expedIfBssRemoteCPEBaseObsAuth2 OBJECT-TYPE
        SYNTAX      TruthValue
        ACCESS      read-only
        STATUS      mandatory
        DESCRIPTION
            "True indicates the CPE is authorized to use this base, False indicates that this CPE
            has been denied by this base."
        ::= { expedIfBssCPERemoteEntry 87 }

expedIfBssRemoteCPEBaseObsBusy2 OBJECT-TYPE
        SYNTAX      TruthValue
        ACCESS      read-only
        STATUS      mandatory
        DESCRIPTION
            "True indicates this base observed is busy and is not recommending registrations to it."
        ::= { expedIfBssCPERemoteEntry 88 }

expedIfBssRemoteCPEBaseObsRang2 OBJECT-TYPE
        SYNTAX      TruthValue
        ACCESS      read-only
        STATUS      mandatory
        DESCRIPTION
            "True indicates the CPE has completed extended ranging with this base station."
        ::= { expedIfBssCPERemoteEntry 89 }

expedIfBssRemoteCPEBaseObsCh3 OBJECT-TYPE
        SYNTAX      INTEGER (1..32)
        ACCESS      read-only
        STATUS      mandatory
        DESCRIPTION
            "Channel of the base station observed by the CPE in the base observation table."
        ::= { expedIfBssCPERemoteEntry 90 }

expedIfBssRemoteCPEBaseObsMac3 OBJECT-TYPE
        SYNTAX      DisplayString
        ACCESS      read-only
        STATUS      mandatory
        DESCRIPTION
            "Mac address of the base station observed by the CPE in the observation table."
        ::= { expedIfBssCPERemoteEntry 91 }

expedIfBssRemoteCPEBaseObsCC3 OBJECT-TYPE
        SYNTAX      INTEGER (1..2147483647)
        ACCESS      read-only
        STATUS      mandatory
        DESCRIPTION
            "Color code of the base station observed by the CPE in the observation table."
        ::= { expedIfBssCPERemoteEntry 92 }

expedIfBssRemoteCPEBaseObsScore3 OBJECT-TYPE
        SYNTAX      INTEGER (1..2147483647)
        ACCESS      read-only
        STATUS      mandatory
        DESCRIPTION
            "Score of the base station observed by the CPE in the observation table."
        ::= { expedIfBssCPERemoteEntry 93 }

expedIfBssRemoteCPEBaseObsAuth3 OBJECT-TYPE
        SYNTAX      TruthValue
        ACCESS      read-only
        STATUS      mandatory
        DESCRIPTION
            "True indicates the CPE is authorized to use this base, False indicates that this CPE
            has been denied by this base."
        ::= { expedIfBssCPERemoteEntry 94 }

expedIfBssRemoteCPEBaseObsBusy3 OBJECT-TYPE
        SYNTAX      TruthValue
        ACCESS      read-only
        STATUS      mandatory
        DESCRIPTION
            "True indicates this base observed is busy and is not recommending registrations to it."
        ::= { expedIfBssCPERemoteEntry 95 }

expedIfBssRemoteCPEBaseObsRang3 OBJECT-TYPE
        SYNTAX      TruthValue
        ACCESS      read-only
        STATUS      mandatory
        DESCRIPTION
            "True indicates the CPE has completed extended ranging with this base station."
        ::= { expedIfBssCPERemoteEntry 96 }

expedIfBssRemoteCPEBaseObsCh4 OBJECT-TYPE
        SYNTAX      INTEGER (1..32)
        ACCESS      read-only
        STATUS      mandatory
        DESCRIPTION
            "Channel of the base station observed by the CPE in the base observation table."
        ::= { expedIfBssCPERemoteEntry 97 }

expedIfBssRemoteCPEBaseObsMac4 OBJECT-TYPE
        SYNTAX      DisplayString
        ACCESS      read-only
        STATUS      mandatory
        DESCRIPTION
            "Mac address of the base station observed by the CPE in the observation table."
        ::= { expedIfBssCPERemoteEntry 98 }

expedIfBssRemoteCPEBaseObsCC4 OBJECT-TYPE
        SYNTAX      INTEGER (1..2147483647)
        ACCESS      read-only
        STATUS      mandatory
        DESCRIPTION
            "Color code of the base station observed by the CPE in the observation table."
        ::= { expedIfBssCPERemoteEntry 99 }


expedIfBssRemoteCPEBaseObsScore4 OBJECT-TYPE
        SYNTAX      INTEGER (1..2147483647)
        ACCESS      read-only
        STATUS      mandatory
        DESCRIPTION
            "Score of the base station observed by the CPE in the observation table."
        ::= { expedIfBssCPERemoteEntry 100 }

expedIfBssRemoteCPEBaseObsAuth4 OBJECT-TYPE
        SYNTAX      TruthValue
        ACCESS      read-only
        STATUS      mandatory
        DESCRIPTION
            "True indicates the CPE is authorized to use this base, False indicates that this CPE
            has been denied by this base."
        ::= { expedIfBssCPERemoteEntry 101 }

expedIfBssRemoteCPEBaseObsBusy4 OBJECT-TYPE
        SYNTAX      TruthValue
        ACCESS      read-only
        STATUS      mandatory
        DESCRIPTION
            "True indicates this base is observed busy and is not recommending registrations to it."
        ::= { expedIfBssCPERemoteEntry 102 }

expedIfBssRemoteCPEBaseObsRang4 OBJECT-TYPE
        SYNTAX      TruthValue
        ACCESS      read-only
        STATUS      mandatory
        DESCRIPTION
            "True indicates the CPE has completed extended ranging with this base station."
        ::= { expedIfBssCPERemoteEntry 103 }

expedIfBssRemoteCPEBaseObsCh5 OBJECT-TYPE
        SYNTAX      INTEGER (1..32)
        ACCESS      read-only
        STATUS      mandatory
        DESCRIPTION
            "Channel of the base station observed by the CPE in the base observation table."
        ::= { expedIfBssCPERemoteEntry 104 }

expedIfBssRemoteCPEBaseObsMac5 OBJECT-TYPE
        SYNTAX      DisplayString
        ACCESS      read-only
        STATUS      mandatory
        DESCRIPTION
            "Mac address of the base station observed by the CPE in the observation table."
        ::= { expedIfBssCPERemoteEntry 105 }

expedIfBssRemoteCPEBaseObsCC5 OBJECT-TYPE
        SYNTAX      INTEGER (1..2147483647)
        ACCESS      read-only
        STATUS      mandatory
        DESCRIPTION
            "Color code of the base station observed by the CPE in the observation table."
        ::= { expedIfBssCPERemoteEntry 106 }

expedIfBssRemoteCPEBaseObsScore5 OBJECT-TYPE
        SYNTAX      INTEGER (1..2147483647)
        ACCESS      read-only
        STATUS      mandatory
        DESCRIPTION
            "Score of the base station observed by the CPE in the observation table."
        ::= { expedIfBssCPERemoteEntry 107 }

expedIfBssRemoteCPEBaseObsAuth5 OBJECT-TYPE
        SYNTAX      TruthValue
        ACCESS      read-only
        STATUS      mandatory
        DESCRIPTION
            "True indicates the CPE is authorized to use this base, False indicates that this CPE
            has been denied by this base."
        ::= { expedIfBssCPERemoteEntry 108 }

expedIfBssRemoteCPEBaseObsBusy5 OBJECT-TYPE
        SYNTAX      TruthValue
        ACCESS      read-only
        STATUS      mandatory
        DESCRIPTION
            "True indicates this base observed is busy and is not recommending registrations to it."
        ::= { expedIfBssCPERemoteEntry 109 }

expedIfBssRemoteCPEBaseObsRang5 OBJECT-TYPE
        SYNTAX      TruthValue
        ACCESS      read-only
        STATUS      mandatory
        DESCRIPTION
            "True indicates the CPE has completed extended ranging with this base station."
        ::= { expedIfBssCPERemoteEntry 110 }

expedIfBssRemoteCPEBaseObsCh6 OBJECT-TYPE
        SYNTAX      INTEGER (1..32)
        ACCESS      read-only
        STATUS      mandatory
        DESCRIPTION
            "Channel of the base station observed by the CPE in the base observation table."
        ::= { expedIfBssCPERemoteEntry 111 }

expedIfBssRemoteCPEBaseObsMac6 OBJECT-TYPE
        SYNTAX      DisplayString
        ACCESS      read-only
        STATUS      mandatory
        DESCRIPTION
            "Mac address of the base station observed by the CPE in the observation table."
        ::= { expedIfBssCPERemoteEntry 112 }

expedIfBssRemoteCPEBaseObsCC6 OBJECT-TYPE
        SYNTAX      INTEGER (1..2147483647)
        ACCESS      read-only
        STATUS      mandatory
        DESCRIPTION
            "Color code of the base station observed by the CPE in the observation table."
        ::= { expedIfBssCPERemoteEntry 113 }

expedIfBssRemoteCPEBaseObsScore6 OBJECT-TYPE
        SYNTAX      INTEGER (1..2147483647)
        ACCESS      read-only
        STATUS      mandatory
        DESCRIPTION
            "Score of the base station observed by the CPE in the observation table."
        ::= { expedIfBssCPERemoteEntry 114 }

expedIfBssRemoteCPEBaseObsAuth6 OBJECT-TYPE
        SYNTAX      TruthValue
        ACCESS      read-only
        STATUS      mandatory
        DESCRIPTION
            "True indicates the CPE is authorized to use this base, False indicates that this CPE
            has been denied by this base."
        ::= { expedIfBssCPERemoteEntry 115 }

expedIfBssRemoteCPEBaseObsBusy6 OBJECT-TYPE
        SYNTAX      TruthValue
        ACCESS      read-only
        STATUS      mandatory
        DESCRIPTION
            "True indicates this base observed is busy and is not recommending registrations to it."
        ::= { expedIfBssCPERemoteEntry 116 }

expedIfBssRemoteCPEBaseObsRang6 OBJECT-TYPE
        SYNTAX      TruthValue
        ACCESS      read-only
        STATUS      mandatory
        DESCRIPTION
            "True indicates the CPE has completed extended ranging with this base station."
        ::= { expedIfBssCPERemoteEntry 117 }

expedIfBssRemoteCPENumActCalls OBJECT-TYPE
        SYNTAX      INTEGER
        ACCESS      read-only
        STATUS      mandatory
        DESCRIPTION
            "Number of active calls on the CPE."
        ::= { expedIfBssCPERemoteEntry 118 }

expedIfBssRemoteCPEDataPolls OBJECT-TYPE
        SYNTAX      Counter
        ACCESS      read-only
        STATUS      mandatory
        DESCRIPTION
            "Number Of Data Polls for this CPE"
        ::= { expedIfBssCPERemoteEntry 119 }

expedIfBssRemoteCPEDryPolls OBJECT-TYPE
        SYNTAX      Counter
        ACCESS      read-only
        STATUS      mandatory
        DESCRIPTION
            "Number Of Dry Polls for this CPE"
        ::= { expedIfBssCPERemoteEntry 120 }

expedIfBssRemoteCPEUnexpected OBJECT-TYPE
        SYNTAX      Counter
        ACCESS      read-only
        STATUS      mandatory
        DESCRIPTION
            "Number Of Unexpected Polls for this CPE"
        ::= { expedIfBssCPERemoteEntry 121 }

expedIfBssRemoteCPEBWUsage OBJECT-TYPE
        SYNTAX      INTEGER
        ACCESS      read-only
        STATUS      mandatory
        DESCRIPTION
            "Sync Session Bandwidth Usage for all calls on this CPE from the 
             perspective of CPE"
        ::= { expedIfBssCPERemoteEntry 122 }

expedIfBssRemoteCPEEfficiency OBJECT-TYPE
        SYNTAX      INTEGER
        ACCESS      read-only
        STATUS      mandatory
        DESCRIPTION
            "Efficiency use of bandwidth for all calls on this CPE"
        ::= { expedIfBssCPERemoteEntry 123 }

expedIfBssRemoteCPEHighWater OBJECT-TYPE
        SYNTAX      Counter
        ACCESS      read-only
        STATUS      mandatory
        DESCRIPTION
            "Highest Queue Depth for call symbols."
        ::= { expedIfBssCPERemoteEntry 124 }

expedIfBssRemoteCPEVoiceFrRt OBJECT-TYPE
        SYNTAX      INTEGER
        ACCESS      read-only
        STATUS      mandatory
        DESCRIPTION
            "Rate of packets received over the Ethernet for Voice Call."
        ::= { expedIfBssCPERemoteEntry 125 }

expedIfBssRemoteCPEAvgNPI OBJECT-TYPE
        SYNTAX      INTEGER
        ACCESS      read-only
        STATUS      mandatory
        DESCRIPTION
            "Avg Next Poll Interval (NPI).  This tells the base
             how often the CPE wants to be polled."
        ::= { expedIfBssCPERemoteEntry 126 }

expedIfBssRemoteCPEConcatBuffers OBJECT-TYPE
        SYNTAX      Counter
        ACCESS      read-only
        STATUS      mandatory
        DESCRIPTION
            "Number of times concatenation took place on the uplink."
        ::= { expedIfBssCPERemoteEntry 127 }

expedIfBssRemoteCPENumBufConcat OBJECT-TYPE
        SYNTAX      Counter
        ACCESS      read-only
        STATUS      mandatory
        DESCRIPTION
            "Number of ethernet frames that were concatenated together."
        ::= { expedIfBssCPERemoteEntry 128 }

expedIfBssRemoteCPECurrentTemp OBJECT-TYPE
        SYNTAX      INTEGER
        ACCESS      read-only
        STATUS      mandatory
        DESCRIPTION
            "Current Temperature on the CPE in Celsius.  A value of -273
             indicates that the CPE has no temperature sensor."
        ::= { expedIfBssCPERemoteEntry 129 }

expedIfBssRemoteCPETxPower OBJECT-TYPE
        SYNTAX      INTEGER
        ACCESS      read-only
        STATUS      mandatory
        DESCRIPTION
            "Current Transmit power on the CPE in dB.  A value of 0
             indicates that the CPE has no power sensor."
        ::= { expedIfBssCPERemoteEntry 130 }

expedIfBssRemoteCPEQPSKUp OBJECT-TYPE
        SYNTAX      Counter
        ACCESS      read-only
        STATUS      mandatory
        DESCRIPTION
            "Number of bytes on the uplink at QPSK modulation level"
        ::= { expedIfBssCPERemoteEntry 131 }

expedIfBssRemoteCPEQPSKDown OBJECT-TYPE
        SYNTAX      Counter
        ACCESS      read-only
        STATUS      mandatory
        DESCRIPTION
            "Number of bytes on the downlink at QPSK modulation level"
        ::= { expedIfBssCPERemoteEntry 132 }

expedIfBssRemoteCPE16QUp OBJECT-TYPE
        SYNTAX      Counter
        ACCESS      read-only
        STATUS      mandatory
        DESCRIPTION
            "Number of bytes on the uplink at 16 QAM modulation level"
        ::= { expedIfBssCPERemoteEntry 133 }

expedIfBssRemoteCPE16QDown OBJECT-TYPE
        SYNTAX      Counter
        ACCESS      read-only
        STATUS      mandatory
        DESCRIPTION
            "Number of bytes on the downlink at 16 QAM modulation level"
        ::= { expedIfBssCPERemoteEntry 134 }

expedIfBssRemoteCPE64QUp OBJECT-TYPE
        SYNTAX      Counter
        ACCESS      read-only
        STATUS      mandatory
        DESCRIPTION
            "Number of bytes on the uplink at 64 QAM modulation level"
        ::= { expedIfBssCPERemoteEntry 135 }

expedIfBssRemoteCPE64QDown OBJECT-TYPE
        SYNTAX      Counter
        ACCESS      read-only
        STATUS      mandatory
        DESCRIPTION
            "Number of bytes on the downlink at 64 QAM modulation level"
        ::= { expedIfBssCPERemoteEntry 136 }

expedIfBssRemoteCPE16QLiteUp OBJECT-TYPE
        SYNTAX      Counter
        ACCESS      read-only
        STATUS      mandatory
        DESCRIPTION
            "Number of bytes on the uplink at 16 QAM Lite modulation level"
        ::= { expedIfBssCPERemoteEntry 137 }

expedIfBssRemoteCPE16QLiteDown OBJECT-TYPE
        SYNTAX      Counter
        ACCESS      read-only
        STATUS      mandatory
        DESCRIPTION
            "Number of bytes on the downlink at 16 QAM Lite modulation level"
        ::= { expedIfBssCPERemoteEntry 138 }

expedIfBssRemoteCurrentRxLevel OBJECT-TYPE
        SYNTAX      DisplayString
        ACCESS      read-only
        STATUS      mandatory
        DESCRIPTION
            "Current RX Modulation Level"
        ::= { expedIfBssCPERemoteEntry 139 }

expedIfBssRemoteCurrentTxLevel OBJECT-TYPE
        SYNTAX      DisplayString
        ACCESS      read-only
        STATUS      mandatory
        DESCRIPTION
            "Current TX Modulation Level"
        ::= { expedIfBssCPERemoteEntry 140 }

ExpedIfBssRemotePollConfig ::= SEQUENCE {
    expedIfBssRemotePollInterval INTEGER,
    expedIfBssRemotePollTimeout INTEGER
}

expedIfBssRemotePollInterval OBJECT-TYPE
        SYNTAX      INTEGER (15..50000)
        ACCESS      read-write
        STATUS      mandatory
        DESCRIPTION
            "Indicates how often each CPE in the BssRemoteCPE table will be queried for
            over the air SNMP stats."
        ::= { expedIfBssObjects 30}

expedIfBssRemotePollTimeout OBJECT-TYPE
        SYNTAX      INTEGER (1..20)
        ACCESS      read-write
        STATUS      mandatory
        DESCRIPTION
            "Indicates how long to wait for an over the air SNMP query to complete before 
            indicating that the Poll was unsuccessful."
        ::= { expedIfBssObjects 31 }

ExpedIfBssVOIPConfig ::= SEQUENCE {
    expedIfBssNoResToPollTimeout      INTEGER,
    expedIfBssMaxNumberOfCalls        INTEGER,
    expedIfBssCurrentNumberOfCalls    INTEGER,
    expedIfBssAdmissionCtrl           INTEGER,
    expedIfBssNumberOfReleaseRetries  INTEGER,
    expedIfBssHiModulation            INTEGER
}
expedIfBssNoResToPollTimeout OBJECT-TYPE
        SYNTAX      INTEGER (15..1000)
        ACCESS      read-write
        STATUS      mandatory
        DESCRIPTION
            "Number of seconds to wait for a Response to a Poll before
             tearing down the call."
        ::= { expedIfBssObjects 33}

expedIfBssMaxNumberOfCalls OBJECT-TYPE
        SYNTAX      INTEGER
        ACCESS      read-only
        STATUS      mandatory
        DESCRIPTION
            "Maximum number of calls this base has been provisioned for."
        ::= { expedIfBssObjects 34}

expedIfBssCurrentNumberOfCalls OBJECT-TYPE
        SYNTAX      INTEGER
        ACCESS      read-only
        STATUS      mandatory
        DESCRIPTION
            "Current number of active calls on this base."
        ::= { expedIfBssObjects 35}

expedIfBssAdmissionCtrl OBJECT-TYPE
        SYNTAX INTEGER {
                enable(1),
                disable(2)
                }
        ACCESS      read-write
        STATUS      mandatory
        DESCRIPTION
            "VoIP admission control. The enable of VoIP admission control 
            turns on the stream precedence and preemption capability."
        ::= { expedIfBssObjects 79}

expedIfBssNumberOfReleaseRetries OBJECT-TYPE
        SYNTAX      INTEGER (0..4)
        ACCESS      read-write
        STATUS      mandatory
        DESCRIPTION
            "Number of retransmission of Sync Session release message."
        ::= { expedIfBssObjects 80}

expedIfBssHiModulation OBJECT-TYPE
        SYNTAX INTEGER {
                enable(1),
                disable(2)
                }
        ACCESS      read-write
        STATUS      mandatory
        DESCRIPTION
            "Controls whether or not high modulation can be used to transport
             VoIP traffic on the uplink.  When enabled, a transmitting CPE is
             allowed to use a modulation higher than the basic QPSK modulation
             level.  When disabled, CPEs must use QPSK modulation for all
             uplink VoIP data.

             Note that this only controls uplink VoIP modulation."
        ::= { expedIfBssObjects 81}

ExpedIfBssVOIPStats ::= SEQUENCE {
    expedIfBssNumOfCallPri0             Counter,
    expedIfBssNumOfCallPri1             Counter,
    expedIfBssNumOfCallPri2             Counter,
    expedIfBssNumOfCallPri3             Counter,
    expedIfBssNumOfCallRoamPri0          Counter,
    expedIfBssNumOfCallRoamPri1          Counter,
    expedIfBssNumOfCallRoamPri2          Counter,
    expedIfBssNumOfCallRoamPri3          Counter,
    expedIfBssNumOfCallPreemptedPri0    Counter,
    expedIfBssNumOfCallPreemptedPri1    Counter,
    expedIfBssNumOfCallPreemptedPri2    Counter,
    expedIfBssNumOfBusyCallOrigPri0     Counter,
    expedIfBssNumOfBusyCallOrigPri1     Counter,
    expedIfBssNumOfBusyCallOrigPri2     Counter,
    expedIfBssNumOfBusyCallOrigPri3     Counter,
    expedIfBssNumOfBusyCallTermPri0     Counter,
    expedIfBssNumOfBusyCallTermPri1     Counter,
    expedIfBssNumOfBusyCallTermPri2     Counter,
    expedIfBssNumOfBusyCallTermPri3     Counter,
    expedIfBssNumOfVoIPNotAllowOrig     Counter,
    expedIfBssNumOfVoIPNotAllowTerm     Counter,
    expedIfBssNumOfVoIPNotAuthOrig      Counter,
    expedIfBssNumOfVoIPNotAuthTerm      Counter
}

expedIfBssNumOfCallPri0 OBJECT-TYPE
               SYNTAX        Counter
               ACCESS        read-only
               STATUS        mandatory
               DESCRIPTION
               "The total number of calls requested by a CPE on this base at 
               priority 0."
        ::= { expedIfBssObjects 82 }
        
expedIfBssNumOfCallPri1 OBJECT-TYPE
               SYNTAX        Counter
               ACCESS        read-only
               STATUS        mandatory
               DESCRIPTION
               "The total number of calls requested by a CPE on this base at 
               priority 1."
        ::= { expedIfBssObjects 83 }

expedIfBssNumOfCallPri2 OBJECT-TYPE
               SYNTAX        Counter
               ACCESS        read-only
               STATUS        mandatory
               DESCRIPTION
               "The total number of calls requested by a CPE on this base at 
               priority 2."
        ::= { expedIfBssObjects 84 }

expedIfBssNumOfCallPri3 OBJECT-TYPE
               SYNTAX        Counter
               ACCESS        read-only
               STATUS        mandatory
               DESCRIPTION
               "The total number of calls requested by a CPE on this base at 
               priority 3."
        ::= { expedIfBssObjects 85 }

expedIfBssNumOfCallRoamPri0 OBJECT-TYPE
               SYNTAX        Counter
               ACCESS        read-only
               STATUS        mandatory
               DESCRIPTION
               "The total number of calls roamed to this base at priority 0."
        ::= { expedIfBssObjects 101 }
        
expedIfBssNumOfCallRoamPri1 OBJECT-TYPE
               SYNTAX        Counter
               ACCESS        read-only
               STATUS        mandatory
               DESCRIPTION
               "The total number of calls roamed to this base at priority 1."
        ::= { expedIfBssObjects 102 }
        
expedIfBssNumOfCallRoamPri2 OBJECT-TYPE
               SYNTAX        Counter
               ACCESS        read-only
               STATUS        mandatory
               DESCRIPTION
               "The total number of calls roamed to this base at priority 2."
        ::= { expedIfBssObjects 103 }

expedIfBssNumOfCallRoamPri3 OBJECT-TYPE
               SYNTAX        Counter
               ACCESS        read-only
               STATUS        mandatory
               DESCRIPTION
               "The total number of calls roamed to this base at priority 3."
        ::= { expedIfBssObjects 104 }

expedIfBssNumOfCallPreemptedPri0 OBJECT-TYPE
               SYNTAX        Counter
               ACCESS        read-only
               STATUS        mandatory
               DESCRIPTION
               "The number of calls preempted at priority 0."
        ::= { expedIfBssObjects 86 }

expedIfBssNumOfCallPreemptedPri1 OBJECT-TYPE
               SYNTAX        Counter
               ACCESS        read-only
               STATUS        mandatory
               DESCRIPTION
               "The number of calls preempted at priority 1."
        ::= { expedIfBssObjects 87 }

expedIfBssNumOfCallPreemptedPri2 OBJECT-TYPE
               SYNTAX        Counter
               ACCESS        read-only
               STATUS        mandatory
               DESCRIPTION
               "The number of calls preempted at priority 2."
        ::= { expedIfBssObjects 88 }

expedIfBssNumOfBusyCallOrigPri0 OBJECT-TYPE
               SYNTAX        Counter
               ACCESS        read-only
               STATUS        mandatory
               DESCRIPTION
               "The number of calls at priority 0 that is failed to make 
               due to originator VoIP busy."
        ::= { expedIfBssObjects 89 }

expedIfBssNumOfBusyCallOrigPri1 OBJECT-TYPE
               SYNTAX        Counter
               ACCESS        read-only
               STATUS        mandatory
               DESCRIPTION
               "The number of calls at priority 1 that is failed to make 
               due to originator VoIP busy."
        ::= { expedIfBssObjects 90 }

expedIfBssNumOfBusyCallOrigPri2 OBJECT-TYPE
               SYNTAX        Counter
               ACCESS        read-only
               STATUS        mandatory
               DESCRIPTION
               "The number of calls at priority 2 that is failed to make 
               due to originator VoIP busy."
        ::= { expedIfBssObjects 91 }

expedIfBssNumOfBusyCallOrigPri3 OBJECT-TYPE
               SYNTAX        Counter
               ACCESS        read-only
               STATUS        mandatory
               DESCRIPTION
               "The number of calls at priority 3 that is failed to make 
               due to originator VoIP busy."
        ::= { expedIfBssObjects 92 }

expedIfBssNumOfBusyCallTermPri0 OBJECT-TYPE
               SYNTAX        Counter
               ACCESS        read-only
               STATUS        mandatory
               DESCRIPTION
               "The number of calls at priority 0 that is failed to make 
               due to terminator VoIP busy."
        ::= { expedIfBssObjects 93 }

expedIfBssNumOfBusyCallTermPri1 OBJECT-TYPE
               SYNTAX        Counter
               ACCESS        read-only
               STATUS        mandatory
               DESCRIPTION
               "The number of calls at priority 1 that is failed to make 
               due to terminator VoIP busy."
        ::= { expedIfBssObjects 94 }

expedIfBssNumOfBusyCallTermPri2 OBJECT-TYPE
               SYNTAX        Counter
               ACCESS        read-only
               STATUS        mandatory
               DESCRIPTION
               "The number of calls at priority 2 that is failed to make 
               due to terminator VoIP busy."
        ::= { expedIfBssObjects 95 }

expedIfBssNumOfBusyCallTermPri3 OBJECT-TYPE
               SYNTAX        Counter
               ACCESS        read-only
               STATUS        mandatory
               DESCRIPTION
               "The number of calls at priority 3 that is failed to make 
               due to terminator VoIP busy."
        ::= { expedIfBssObjects 96 }

expedIfBssNumOfVoIPNotAllowOrig OBJECT-TYPE
               SYNTAX        Counter
               ACCESS        read-only
               STATUS        mandatory
               DESCRIPTION
               "The number of calls that is failed to make due to 
               originator cpe not provisioned."
        ::= { expedIfBssObjects 97 }

expedIfBssNumOfVoIPNotAllowTerm OBJECT-TYPE
               SYNTAX        Counter
               ACCESS        read-only
               STATUS        mandatory
               DESCRIPTION
               "The number of calls that is failed to make due to 
               terminator cpe not provisioned."
        ::= { expedIfBssObjects 98 }

expedIfBssNumOfVoIPNotAuthOrig OBJECT-TYPE
               SYNTAX        Counter
               ACCESS        read-only
               STATUS        mandatory
               DESCRIPTION
               "The number of calls that is failed to make due to 
               originator cpe requesting a wrong SIP server."
        ::= { expedIfBssObjects 99 }

expedIfBssNumOfVoIPNotAuthTerm OBJECT-TYPE
               SYNTAX        Counter
               ACCESS        read-only
               STATUS        mandatory
               DESCRIPTION
               "The number of calls that is failed to make due to 
               terminator cpe requesting a wrong SIP server."
        ::= { expedIfBssObjects 100 }

expedIfBssQPSKCpes OBJECT-TYPE
        SYNTAX      Counter
        ACCESS      read-only
        STATUS      obsolete
        DESCRIPTION
            "Current number of CPEs with downlink modulation at QPSK.

             This object is obsolete as of base station software version 4.3
             and is replaced by expedIfBssModTbl."
        ::= { expedIfBssObjects 36}

expedIfBss16QAMCpes OBJECT-TYPE
        SYNTAX      Counter
        ACCESS      read-only
        STATUS      obsolete
        DESCRIPTION
            "Current number of CPEs with downlink modulation at 16 QAM.

             This object is obsolete as of base station software version 4.3
             and is replaced by expedIfBssModTbl."

        ::= { expedIfBssObjects 37}

expedIfBss64QAMCpes OBJECT-TYPE
        SYNTAX      Counter
        ACCESS      read-only
        STATUS      obsolete
        DESCRIPTION
            "Current number of CPEs with downlink modulation at 64 QAM.

             This object is obsolete as of base station software version 4.3
             and is replaced by expedIfBssModTbl."
        ::= { expedIfBssObjects 38}

expedIfBss16QAMLiteCpes OBJECT-TYPE
        SYNTAX      Counter
        ACCESS      read-only
        STATUS      obsolete
        DESCRIPTION
            "Current number of CPEs with downlink modulation at 16 QAMLite.

             This object is obsolete as of base station software version 4.3
             and is replaced by expedIfBssModTbl."

        ::= { expedIfBssObjects 39}

expedIfBssQPSKDownBytes OBJECT-TYPE
        SYNTAX      Counter
        ACCESS      read-only
        STATUS      obsolete
        DESCRIPTION
            "Total number of QPSK bytes sent from the base on the downlink.

             This object is obsolete as of base station software version 4.3
             and is replaced by expedIfBssModTbl."

        ::= { expedIfBssObjects 40}

expedIfBssQPSKUpBytes OBJECT-TYPE
        SYNTAX      Counter
        ACCESS      read-only
        STATUS      obsolete
        DESCRIPTION
            "Total number of QPSK bytes received by the base on the uplink.

             This object is obsolete as of base station software version 4.3
             and is replaced by expedIfBssModTbl."

        ::= { expedIfBssObjects 41}

expedIfBss16QAMDownBytes OBJECT-TYPE
        SYNTAX      Counter
        ACCESS      read-only
        STATUS      obsolete
        DESCRIPTION
            "Total number of 16 QAM bytes sent from the base on the downlink.

             This object is obsolete as of base station software version 4.3
             and is replaced by expedIfBssModTbl."

        ::= { expedIfBssObjects 42}

expedIfBss16QAMUpBytes OBJECT-TYPE
        SYNTAX      Counter
        ACCESS      read-only
        STATUS      obsolete
        DESCRIPTION
            "Total number of 16 QAM bytes received by the base on the uplink.

             This object is obsolete as of base station software version 4.3
             and is replaced by expedIfBssModTbl."

        ::= { expedIfBssObjects 43}

expedIfBss64QAMDownBytes OBJECT-TYPE
        SYNTAX      Counter
        ACCESS      read-only
        STATUS      obsolete
        DESCRIPTION
            "Total number of 64 QAM bytes sent from the base on the downlink.

             This object is obsolete as of base station software version 4.3
             and is replaced by expedIfBssModTbl."

        ::= { expedIfBssObjects 44}

expedIfBss64QAMUpBytes OBJECT-TYPE
        SYNTAX      Counter
        ACCESS      read-only
        STATUS      obsolete
        DESCRIPTION
            "Total number of 64 QAM bytes received by the base on the uplink.

             This object is obsolete as of base station software version 4.3
             and is replaced by expedIfBssModTbl."

        ::= { expedIfBssObjects 45}

expedIfBss16QAMLiteDownBytes OBJECT-TYPE
        SYNTAX      Counter
        ACCESS      read-only
        STATUS      obsolete
        DESCRIPTION
            "Total number of 16 QAM Lite bytes sent from the base on the
             downlink.

             This object is obsolete as of base station software version 4.3
             and is replaced by expedIfBssModTbl."

        ::= { expedIfBssObjects 46}

expedIfBss16QAMLiteUpBytes OBJECT-TYPE
        SYNTAX      Counter
        ACCESS      read-only
        STATUS      obsolete
        DESCRIPTION
            "Total number of 16 QAM Lite bytes received by the base on the
             uplink.

             This object is obsolete as of base station software version 4.3
             and is replaced by expedIfBssModTbl."

        ::= { expedIfBssObjects 47}


expedIfBssModTbl OBJECT-TYPE
        SYNTAX      SEQUENCE OF ExpedIfBssModTblEntry
        ACCESS      not-accessible
        STATUS      mandatory
        DESCRIPTION
            "Table of stats for throughput at each modulation."
        ::= { expedIfBssObjects 56 }

expedIfBssModTblEntry OBJECT-TYPE
        SYNTAX      ExpedIfBssModTblEntry
        ACCESS      not-accessible
        STATUS      mandatory
        DESCRIPTION
            "Table of stats for throughput at each modulation."
        INDEX { expedIfBssModTblIndex  }
        ::= { expedIfBssModTbl 1 }


ExpedIfBssModTblEntry ::= SEQUENCE {
            expedIfBssModTblIndex           INTEGER,
            expedIfBssModTblName            DisplayString,
            expedIfBssModTblUpSlotUsage     Counter,
            expedIfBssModTblUpSlotVOIP      Counter,
            expedIfBssModTblUpBytes         Counter,
            expedIfBssModTblUpMessages      Counter,
            expedIfBssModTblDownSlotUsage   Counter,
            expedIfBssModTblDownBytes       Counter,
            expedIfBssModTblNumCPES         INTEGER,
            expedIfBssModTblChgReqs         Counter,
            expedIfBssModTblDownBytesVOIP   Counter,
            expedIfBssModTblUpBytesVOIP     Counter
        }

expedIfBssModTblIndex OBJECT-TYPE
        SYNTAX      INTEGER (1..15)
        ACCESS        read-only
        STATUS      mandatory
        DESCRIPTION
            "Index for each modulation"
        ::= { expedIfBssModTblEntry 1 }


expedIfBssModTblName OBJECT-TYPE
        SYNTAX      DisplayString
        ACCESS        read-only
        STATUS      mandatory
        DESCRIPTION
            "Descriptive name for the modulation."
        ::= { expedIfBssModTblEntry 2 }

expedIfBssModTblUpSlotUsage OBJECT-TYPE
        SYNTAX      Counter 
        ACCESS        read-only
        STATUS      mandatory
        DESCRIPTION
            "Total uplink slots at each modulation."
        ::= { expedIfBssModTblEntry 3 }

expedIfBssModTblUpSlotVOIP OBJECT-TYPE
        SYNTAX        Counter
        ACCESS        read-only
        STATUS      mandatory
        DESCRIPTION
            "Total uplink slots for voip at each modulation."
        ::= { expedIfBssModTblEntry 4 }


expedIfBssModTblUpBytes OBJECT-TYPE
        SYNTAX      Counter 
        ACCESS        read-only
        STATUS      mandatory
        DESCRIPTION
            "Total uplink bytes at each modulation."
        ::= { expedIfBssModTblEntry 5 }


expedIfBssModTblUpMessages OBJECT-TYPE
        SYNTAX      Counter 
        ACCESS        read-only
        STATUS      mandatory
        DESCRIPTION
            "Total uplink messages at each modulation."
        ::= { expedIfBssModTblEntry 6 }


expedIfBssModTblDownSlotUsage OBJECT-TYPE
        SYNTAX      Counter 
        ACCESS        read-only
        STATUS      mandatory
        DESCRIPTION
            "Total downlink slot usage at each modulation."
        ::= { expedIfBssModTblEntry 7 }


expedIfBssModTblDownBytes OBJECT-TYPE
        SYNTAX      Counter 
        ACCESS        read-only
        STATUS      mandatory
        DESCRIPTION
            "Total downlink bytes at each modulation (includes VoIP bytes)."
        ::= { expedIfBssModTblEntry 8 }

expedIfBssModTblNumCPES OBJECT-TYPE
        SYNTAX      INTEGER 
        ACCESS        read-only
        STATUS      mandatory
        DESCRIPTION
            "Number CPEs at each modulation."
        ::= { expedIfBssModTblEntry 9 }


expedIfBssModTblChgReqs OBJECT-TYPE
        SYNTAX      Counter 
        ACCESS        read-only
        STATUS      mandatory
        DESCRIPTION
            "Number change modulation requests received for each modulation."
        ::= { expedIfBssModTblEntry 10 }

expedIfBssModTblDownBytesVOIP OBJECT-TYPE
        SYNTAX      Counter 
        ACCESS        read-only
        STATUS      mandatory
        DESCRIPTION
            "Total VoIP downlink bytes at each modulation."
        ::= { expedIfBssModTblEntry 11 }

expedIfBssModTblUpBytesVOIP OBJECT-TYPE
        SYNTAX      Counter 
        ACCESS        read-only
        STATUS      mandatory
        DESCRIPTION
            "Total VoIP uplink bytes at each modulation."
        ::= { expedIfBssModTblEntry 12 }


expedIfBssModUpSlotsPerSec OBJECT-TYPE
        SYNTAX      INTEGER
        ACCESS      read-only
        STATUS      mandatory
        DESCRIPTION
            "Total uplink slots per second."
        ::= { expedIfBssObjects 57}

expedIfBssModDownSlotsPerSec OBJECT-TYPE
        SYNTAX      INTEGER
        ACCESS      read-only
        STATUS      mandatory
        DESCRIPTION
            "Total down slots per second."
        ::= { expedIfBssObjects 58}


expedDevTrapVars OBJECT IDENTIFIER ::= {expedDevTrap 3}

ExpedDevTrapInfo ::= SEQUENCE {

    expedDevTrapBTSName DisplayString,
    expedDevTrapBTSLocation DisplayString,
    expedDevTrapBTSMessage  DisplayString
}

expedDevTrapBTSName OBJECT-TYPE
        SYNTAX      DisplayString(SIZE(0..255))
        ACCESS        read-only
        STATUS      obsolete
        DESCRIPTION
            "System name of the BTS sending the trap.

             This object is obsolete as of base station software version 4.3
             and has no replacement."
        ::= {expedDevTrapVars 1 }

expedDevTrapBTSLocation OBJECT-TYPE
        SYNTAX      DisplayString(SIZE(0..255))
        ACCESS        read-only
        STATUS      obsolete
        DESCRIPTION
            "System location of the BTS sending the trap.

             This object is obsolete as of base station software version 4.3
             and has no replacement."
        ::= {expedDevTrapVars 2 }

expedDevTrapBTSMessage OBJECT-TYPE
        SYNTAX      DisplayString(SIZE(0..255))
        ACCESS        read-only
        STATUS      obsolete
        DESCRIPTION
            "Message that is accompanying the trap.

             This object is obsolete as of base station software version 4.3
             and has no replacement."
        ::= {expedDevTrapVars 3 }


nextnetTraps TRAP-TYPE
    ENTERPRISE  nextnet
        VARIABLES {expedDevTrapBTSName,
         expedDevTrapBTSLocation,
    expedDevTrapBTSMessage
        }
          --&ACTIONS  { log, critical, clrdups }
        --&MESG " $3 "
    DESCRIPTION
    "Specifies the nextnet traps.

     This object is obsolete as of base station software version 4.3 and has no
     replacement."
    ::= 0


END



--5.  Security Considerations

--   This MIB relates to a system which will provide metropolitan public
--   internet access.  As such, improper manipulation of the objects
--   represented by this MIB may result in denial of service to a large
--   number of end-users.

--6.  Intellectual Property

--   The IETF takes no position regarding the validity or scope of any
--   intellectual property or other rights that might be claimed to
--   pertain to the implementation or use of the technology described in
--   this document or the extent to which any license under such rights
--   might or might not be available; neither does it represent that it
--   has made any effort to identify any such rights.  Information on the
--   IETF's procedures with respect to rights in standards-track and
--   standards-related documentation can be found in BCP-11.  Copies of
--   claims of rights made available for publication and any assurances of
--   licenses to be made available, or the result of an attempt made to
--   obtain a general license or permission for the use of such
--   proprietary rights by implementors or users of this specification can
--   be obtained from the IETF Secretariat.

--   The IETF invites any interested party to bring to its attention any
--   copyrights, patents or patent applications, or other proprietary
--   rights which may cover technology that may be required to practice
--   this standard.  Please address the information to the IETF Executive
--   Director.

--7.  Full Copyright Statement

--   Copyright (C) The Internet Society (1999).  All Rights Reserved.

--   This document and translations of it may be copied and furnished to
--   others, and derivative works that comment on or otherwise explain it
--   or assist in its implementation may be prepared, copied, published
--   and distributed, in whole or in part, without restriction of any
--   kind, provided that the above copyright notice and this paragraph are
--   included on all such copies and derivative works.  However, this
--   document itself may not be modified in any way, such as by removing
--   the copyright notice or references to the Internet Society or other
--   Internet organizations, except as needed for the purpose of
--   developing Internet standards in which case the procedures for
--   copyrights defined in the Internet Standards process must be
--   followed, or as required to translate it into languages other than
--   English.

--   The limited permissions granted above are perpetual and will not be
--   revoked by the Internet Society or its successors or assigns.

--   This document and the information contained herein is provided on an
--   "AS IS" basis and THE INTERNET SOCIETY AND THE INTERNET ENGINEERING
--   TASK FORCE DISCLAIMS ALL WARRANTIES, EXPRESS OR IMPLIED, INCLUDING
--   BUT NOT LIMITED TO ANY WARRANTY THAT THE USE OF THE INFORMATION
--   HEREIN WILL NOT INFRINGE ANY RIGHTS OR ANY IMPLIED WARRANTIES OF
--   MERCHANTABILITY OR FITNESS FOR A PARTICULAR PURPOSE.
