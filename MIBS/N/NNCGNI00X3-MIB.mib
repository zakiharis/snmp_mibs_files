-- @(#)NetSynch.mib	9.1 10/16/98
--------------------------------------------------------------------------------
-- file: NetSynch.mib
--
-- contents:
--	This file contains the Newbridge MIB extensions for standalone network
--	synchronization.
--
-- history:
--	0.1 / 92.08.25 / J. Watt / Creation
--	0.2 / 93.04.04 / J. Watt / Made OperStatus R/O
--
-- Copyright 1992 to 1993 Newbridge Networks Corporation.  All Rights Reserved.
--------------------------------------------------------------------------------

NNCGNI00X3-MIB DEFINITIONS ::= BEGIN

	IMPORTS	
		nncExtNetSynch
			FROM NNCGNI00X1-SMI
		
		OBJECT-TYPE
			FROM RFC-1212;
			
			
	NsCandidateIndex ::= INTEGER (1..5)
	PortIndex	 ::= INTEGER (1..32)
	NsSourcePriority ::= INTEGER (1..15)
	NsRecoveryKind   ::= INTEGER { manual(1), automatic(2), timed(3) }
	NsRecoveryTime	 ::= INTEGER (0..1800) -- seconds
	NsThreshold	 ::= INTEGER (0..31)   -- failures, 0 means infinity
	
	NsOperStatus	 ::= INTEGER { disabled(1), ready(2), current(3), 
				       timedRecovery(4), failed(5), shutDown(6), 
				       notReady(7), autoRecovery(8), 
				       cannotLock(9), enabled(10), 
				       illegalState(11), undefinedSource(12),
				       unavailable(13), acquiring(14) }
				  
	NsAdminStatus	 ::= INTEGER {
                               enable(1), disable(2), select(3), deselect(4)
                             }

	nncExtNsCurrentSource	OBJECT-TYPE
		SYNTAX	NsCandidateIndex
		ACCESS	read-only
		STATUS	mandatory
DESCRIPTION ""

		::= { nncExtNetSynch 1 }
	
	
	nncExtNsCurrentClass	OBJECT-TYPE
		SYNTAX	NsSourcePriority
		ACCESS	read-only
		STATUS	mandatory
DESCRIPTION ""

		::= { nncExtNetSynch 2 }
		
		
	nncExtNsCandidateTable	OBJECT-TYPE
		SYNTAX	SEQUENCE OF NncExtNsCandidateEntry
		ACCESS	not-accessible
		STATUS	mandatory
DESCRIPTION ""

		::= { nncExtNetSynch 3 }
		
	
	nncExtNsCandidateEntry	OBJECT-TYPE
		SYNTAX	NncExtNsCandidateEntry
		ACCESS	not-accessible
		STATUS	mandatory
DESCRIPTION ""

		INDEX { nncExtNsCandidateIndex }
		::= { nncExtNsCandidateTable 1 }
		
	
	NncExtNsCandidateEntry
		::= SEQUENCE {
			nncExtNsCandidateIndex
				NsCandidateIndex,
			nncExtNsCandidateSource
				PortIndex,
			nncExtNsCandidatePriority
				NsSourcePriority,
			nncExtNsCandidateRecoveryKind
				NsRecoveryKind,
			nncExtNsCandidateRecoveryTime
				NsRecoveryTime,
			nncExtNsCandidateFailureThreshold
				NsThreshold,
			nncExtNsCandidateAdminStatus
				NsAdminStatus,
			nncExtNsCandidateOperStatus
				NsOperStatus
		}
		
		
	nncExtNsCandidateIndex	OBJECT-TYPE
		SYNTAX	NsCandidateIndex
		ACCESS	read-only
		STATUS	mandatory
DESCRIPTION ""

		::= { nncExtNsCandidateEntry 1}
		
		
	nncExtNsCandidateSource	OBJECT-TYPE
		SYNTAX	PortIndex
		ACCESS	read-write
		STATUS	mandatory
DESCRIPTION ""

		::= { nncExtNsCandidateEntry 2}
		
		
	nncExtNsCandidatePriority	OBJECT-TYPE
		SYNTAX	NsSourcePriority
		ACCESS	read-write
		STATUS	mandatory
DESCRIPTION ""

		::= { nncExtNsCandidateEntry 3}
		
		
	nncExtNsCandidateRecoveryKind	OBJECT-TYPE
		SYNTAX	INTEGER { manual(1), automatic(2), timed(3) }
		ACCESS	read-write
		STATUS	mandatory
DESCRIPTION ""

		::= { nncExtNsCandidateEntry 4}
		
	
	nncExtNsCandidateRecoveryTime	OBJECT-TYPE
		SYNTAX	NsRecoveryTime
		ACCESS	read-write
		STATUS	mandatory
DESCRIPTION ""

		::= { nncExtNsCandidateEntry 5}


	nncExtNsCandidateFailureThreshold	OBJECT-TYPE
		SYNTAX	NsThreshold
		ACCESS	read-write
		STATUS	mandatory
DESCRIPTION ""

		::= { nncExtNsCandidateEntry 6}
		
		
	nncExtNsCandidateAdminStatus	OBJECT-TYPE
		SYNTAX	INTEGER {
                           enable(1), disable(2), select(3), deselect(4)
                        }
		ACCESS	read-write
		STATUS	mandatory
DESCRIPTION ""

		::= { nncExtNsCandidateEntry 7}
		
	
	nncExtNsCandidateOperStatus	OBJECT-TYPE
		SYNTAX	INTEGER { disabled(1), ready(2), current(3), 
                                  timedRecovery(4), failed(5), shutDown(6), 
                                  notReady(7), autoRecovery(8), 
                                  cannotLock(9), enabled(10), 
                                  illegalState(11), undefinedSource(12),
                                  unavailable(13), acquiring(14) }

		ACCESS	read-only
		STATUS	mandatory
DESCRIPTION ""

		::= { nncExtNsCandidateEntry 8}
		

END
