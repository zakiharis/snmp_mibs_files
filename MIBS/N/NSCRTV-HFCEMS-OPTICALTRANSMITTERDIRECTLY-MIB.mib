NSCRTV-HFCEMS-OPTICALTRANSMITTERDIRECTLY-MIB DEFINITIONS ::= BEGIN
-- *****************************************************************************
-- *****************************************************************************

IMPORTS
    OBJECT-TYPE
        FROM RFC-1212
    DisplayString
        FROM RFC1213-MIB
    otdIdent
        FROM NSCRTV-ROOT;

    otdVendorOID OBJECT-TYPE
        SYNTAX OBJECT IDENTIFIER
        ACCESS read-only
        STATUS optional
        DESCRIPTION
            ""
        ::= { otdIdent 1 }
    
    otdSlotNumber OBJECT-TYPE
        SYNTAX INTEGER ( 0..32767 )
        ACCESS read-only
        STATUS mandatory
        DESCRIPTION
            ""
        ::= { otdIdent 2 }
    
    otdOptDeviceTable OBJECT-TYPE
        SYNTAX SEQUENCE OF OtdOptDeviceEntry
        ACCESS not-accessible
        STATUS mandatory
        DESCRIPTION
            ""
        ::= { otdIdent 3 }
    
    otdOptDeviceEntry OBJECT-TYPE
        SYNTAX OtdOptDeviceEntry
        ACCESS not-accessible
        STATUS mandatory
        DESCRIPTION
            ""
        INDEX { otdIndex }
        ::= { otdOptDeviceTable 1 }
    
    OtdOptDeviceEntry ::= SEQUENCE
        {
        otdIndex
            INTEGER,
        otdLaserWavelength
            DisplayString,
        otdLaserType
            DisplayString,
        otdDriveLevel
            INTEGER,
        otdInputRFLevel
            INTEGER,
        otdInputRFAttenuationRange
            INTEGER,
        otdInputRFAttenuation
            INTEGER,
        otdLaserTemp
            INTEGER,
        otdLaserCurrent
            INTEGER,
        otdOpicalOutputPower
            INTEGER,
        otdTecCurrent
            INTEGER,
        otdAGCControl
            INTEGER, 
        otdConfigurationDriveLevel
            INTEGER,
        otdConfigurationRFAttenuation
            INTEGER,
        otdConfigurationRFChannels
            INTEGER
        }
        
        
    otdIndex OBJECT-TYPE
        SYNTAX INTEGER ( 0..32767 )
        ACCESS read-only
        STATUS mandatory
        DESCRIPTION
            ""
        ::= { otdOptDeviceEntry 1 }
    
    otdLaserWavelength OBJECT-TYPE
        SYNTAX DisplayString
        ACCESS read-only
        STATUS mandatory
        DESCRIPTION
            ""
        ::= { otdOptDeviceEntry 2 }
    
    otdLaserType OBJECT-TYPE
        SYNTAX DisplayString
        ACCESS read-only
        STATUS optional
        DESCRIPTION
            ""
        ::= { otdOptDeviceEntry 3 }
    
    otdDriveLevel OBJECT-TYPE
        SYNTAX INTEGER (0..127 )
        ACCESS read-only
        STATUS optional
        DESCRIPTION
            ""
        ::= { otdOptDeviceEntry 4 }
    
    otdInputRFLevel OBJECT-TYPE
        SYNTAX INTEGER (0..127 )
        ACCESS read-only
        STATUS optional
        DESCRIPTION
            ""
        ::= { otdOptDeviceEntry 5 }
    
    otdInputRFAttenuationRange OBJECT-TYPE
        SYNTAX INTEGER ( 0..32767 )
        ACCESS read-only
        STATUS optional
        DESCRIPTION
            ""
        ::= { otdOptDeviceEntry 6 }
    
    otdInputRFAttenuation OBJECT-TYPE
        SYNTAX INTEGER ( -32768..32767 )
        ACCESS read-write
        STATUS optional
        DESCRIPTION
            ""
        ::= { otdOptDeviceEntry 7 }
    
    otdLaserTemp OBJECT-TYPE
        SYNTAX INTEGER ( -32768..32767 )
        ACCESS read-only
        STATUS mandatory
        DESCRIPTION
            ""
        ::= { otdOptDeviceEntry 8 }
    
    otdLaserCurrent OBJECT-TYPE
        SYNTAX INTEGER (-32768..32767 )
        ACCESS read-only
        STATUS mandatory
        DESCRIPTION
            ""
        ::= { otdOptDeviceEntry 9 }
    
    otdOpicalOutputPower OBJECT-TYPE
        SYNTAX INTEGER ( 0..32767 )
        ACCESS read-only
        STATUS mandatory
        DESCRIPTION
            ""
        ::= { otdOptDeviceEntry 10 }
    
    otdTecCurrent OBJECT-TYPE
        SYNTAX INTEGER ( -32768..32767 )
        ACCESS read-only
        STATUS optional
        DESCRIPTION
            ""
        ::= { otdOptDeviceEntry 11 }
    
    otdAGCControl OBJECT-TYPE
        SYNTAX INTEGER {off(1),on(2)}
        ACCESS read-write
        STATUS optional
        DESCRIPTION
            ""
        ::= { otdOptDeviceEntry 12 }
    
    otdConfigurationDriveLevel OBJECT-TYPE
        SYNTAX INTEGER
        ACCESS read-write
        STATUS optional
        DESCRIPTION
            ""
        ::= { otdOptDeviceEntry 13 }
    
    otdConfigurationRFAttenuation OBJECT-TYPE
        SYNTAX INTEGER
        ACCESS read-write
        STATUS optional
        DESCRIPTION
            ""
        ::= { otdOptDeviceEntry 14 }
    
    otdConfigurationRFChannels OBJECT-TYPE
        SYNTAX INTEGER
        ACCESS read-write
        STATUS optional
        DESCRIPTION
            ""
        ::= { otdOptDeviceEntry 15 }
    
    otdFansNumber OBJECT-TYPE
        SYNTAX INTEGER
        ACCESS read-only
        STATUS mandatory
        DESCRIPTION
            ""
        ::= { otdIdent 4 }
    
    otdFansTable OBJECT-TYPE
        SYNTAX SEQUENCE OF OtdFansEntry
        ACCESS not-accessible
        STATUS optional
        DESCRIPTION
            ""
        ::= { otdIdent 5 }
    
    otdFansEntry OBJECT-TYPE
        SYNTAX OtdFansEntry
        ACCESS not-accessible
        STATUS optional
        DESCRIPTION
            ""
        INDEX { otdFansIndex }
        ::= { otdFansTable 1 }
    
    OtdFansEntry ::= SEQUENCE {
        otdFansIndex
            INTEGER,
        otdFansState
            INTEGER,
        otdFansSpeed
            INTEGER,
        otdFansControl
            INTEGER,
        otdFansName
            DisplayString
        }
        
        
    otdFansIndex OBJECT-TYPE
        SYNTAX INTEGER
        ACCESS read-only
        STATUS optional
        DESCRIPTION
            ""
        ::= { otdFansEntry 1 }
    
    otdFansState OBJECT-TYPE
        SYNTAX INTEGER {normal (1), fault (2), off (3) }
        ACCESS read-only
        STATUS optional
        DESCRIPTION
            ""
        ::= { otdFansEntry 2 }
    
    otdFansSpeed OBJECT-TYPE
        SYNTAX INTEGER
        ACCESS read-only
        STATUS optional
        DESCRIPTION
            ""
        ::= { otdFansEntry 3 }
    
    otdFansControl OBJECT-TYPE
        SYNTAX INTEGER { on(1), off(2) }
        ACCESS read-write
        STATUS optional
        DESCRIPTION
            ""
        ::= { otdFansEntry 4 }
    
    otdFansName OBJECT-TYPE
        SYNTAX DisplayString
        ACCESS read-only
        STATUS optional
        DESCRIPTION
            ""
        ::= { otdFansEntry 5 }

    otdNumberDCPowerSupply OBJECT-TYPE
        SYNTAX INTEGER ( 0..16 )
        ACCESS read-only
        STATUS mandatory
        DESCRIPTION
            ""
        ::= { otdIdent 6 }
    
    otdDCPowerSupplyMode OBJECT-TYPE
        SYNTAX INTEGER { loadsharing(1), switchedredundant(2),alonesupply(3) }
        ACCESS read-only
        STATUS optional
        DESCRIPTION
            ""
        ::= { otdIdent 7 }
    
    otdDCPowerTable OBJECT-TYPE
        SYNTAX SEQUENCE OF OtdDCPowerEntry
        ACCESS not-accessible
        STATUS mandatory
        DESCRIPTION
            ""
        ::= { otdIdent 8 }
    
    otdDCPowerEntry OBJECT-TYPE
        SYNTAX OtdDCPowerEntry
        ACCESS not-accessible
        STATUS mandatory
        DESCRIPTION
            ""
        INDEX { otdDCPowerIndex }
        ::= { otdDCPowerTable 1 }
    
    OtdDCPowerEntry ::= SEQUENCE
        {
        otdDCPowerIndex
            INTEGER,
        otdDCPowerVoltage
            INTEGER,
        otdDCPowerCurrent
            INTEGER,
        otdDCPowerName
            DisplayString
        }
    
    otdDCPowerIndex OBJECT-TYPE
        SYNTAX INTEGER
        ACCESS read-only
        STATUS mandatory
        DESCRIPTION
            ""
        ::= { otdDCPowerEntry 1 }
    
    otdDCPowerVoltage OBJECT-TYPE
        SYNTAX INTEGER (-32768..32767 )
        ACCESS read-only
        STATUS mandatory
        DESCRIPTION
            ""
        ::= { otdDCPowerEntry 2 }
    
    otdDCPowerCurrent OBJECT-TYPE
        SYNTAX INTEGER ( 0..65535 )
        ACCESS read-only
        STATUS optional
        DESCRIPTION
            ""
        ::= { otdDCPowerEntry 3 }
    
    otdDCPowerName OBJECT-TYPE
        SYNTAX DisplayString
        ACCESS read-only
        STATUS mandatory
        DESCRIPTION
            ""
        ::= { otdDCPowerEntry 4 }

-- *****************************************************************************
END
