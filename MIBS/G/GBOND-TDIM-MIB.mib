-- extracted from draft-ietf-adslmib-gbond-tdim-mib-00.txt
-- at Wed May  2 06:08:40 2007

   GBOND-TDIM-MIB DEFINITIONS ::= BEGIN

     IMPORTS
       MODULE-IDENTITY, OBJECT-TYPE, NOTIFICATION-TYPE,
       Unsigned32, Counter32
         FROM SNMPv2-SMI         -- RFC 2578
       TEXTUAL-CONVENTION, TruthValue
         FROM SNMPv2-TC          -- RFC 2579
       MODULE-COMPLIANCE, OBJECT-GROUP, NOTIFICATION-GROUP
         FROM SNMPv2-CONF        -- RFC 2580
       ifIndex, InterfaceIndex
         FROM IF-MIB             -- RFC 2863
       gBondMIB
         FROM GBOND-MIB          -- RFC YYYY
         -- EdNote: Replace YYYY with the actual RFC number &
         -- remove this note
       ;

     gBondTdimMIB MODULE-IDENTITY
       LAST-UPDATED "200704290000Z"  -- April 29, 2007
       ORGANIZATION "IETF ADSL MIB Working Group"
       CONTACT-INFO
         "WG charter:
           http://www.ietf.org/html.charters/adslmib-charter.html

         Mailing Lists:
           General Discussion: adslmib@ietf.org
           To Subscribe: adslmib-request@ietf.org
           In Body: subscribe your_email_address

          Chair: Menachem Dodge
         Postal: ECI Telecom, Ltd.
                 30 Hasivim St.,
                 Petach-Tikva 49517
                 Israel
          Phone: +972-3-926-8421
          EMail: menachem.dodge@ecitele.com

         Editor: Edward Beili
         Postal: Actelis Networks, Inc.
                 25 Bazel St., P.O.B. 10173
                 Petach-Tikva 10173
                 Israel
          Phone: +972-3-924-3491
          EMail: edward.beili@actelis.com

         Editor: Narendranath Nair
         Postal: Wipro Technologies
                 Keonics Electronics City
                 Bangalore 560 100
                 India
          Phone: +91-80-2852-0408 x85338
          EMail: narendranath.nair@wipro.com"

       DESCRIPTION
         "The objects in this MIB module are used to manage the
         multi-pair bonded xDSL Interfaces using time-division inverse
         multiplexing (TDIM), defined in ITU-T recommendation G.998.3
         (G.Bond/TDIM).

         This MIB module MUST be used in conjunction with GBOND-MIB
         module, common to all G.Bond technologies.

         The following references are used throughout this MIB module:

         [G.998.3] refers to:
           ITU-T Recommendation G.998.1: 'Multi-pair bonding using
           time-division inverse multiplexing', January 2005.

         [WT-159] refers to:
           DSL Forum Technical Report: 'Management Framework for xDSL
           Bonding', January 2007.

         Naming Conventions:
           BCE   - Bonding Channel Entity
           CO    - Central Office
           CPE   - Customer Premises Equipment
           GBS   - Generic Bonding Sublayer
           SNR   - Signal to Noise Ratio

         Copyright (C) The Internet Society (2007). This version of this
         MIB module is part of RFC XXXX; see the RFC itself for full
         legal notices."

       REVISION    "200704290000Z"  -- April 29, 2007
       DESCRIPTION "Initial version, published as RFC XXXX."

         -- EdNote: Replace XXXX with the actual RFC number &
         -- remove this note

       ::= { gBondMIB 3 }

      -- Sections of the module
      -- Structured as recommended by RFC 4181, Appendix D

      gBondTdimObjects     OBJECT IDENTIFIER ::= { gBondTdimMIB 1 }

      gBondTdimConformance OBJECT IDENTIFIER ::= { gBondTdimMIB 2 }

      -- Groups in the module

      gBondTdimPort        OBJECT IDENTIFIER ::= { gBondTdimObjects 1 }

      -- Textual Conventions

      GBondTdimServiceIndex ::= TEXTUAL-CONVENTION
        DISPLAY-HINT "d"
        STATUS       current
        DESCRIPTION
          "A unique value, greater than zero, for each Service defined
          in the managed G.Bond TDIM port, showing its relative position
          inside the G.Bond/TDIM frame.
          It is RECOMMENDED that values are assigned contiguously
          starting from 1. The value for each Service MUST remain
          constant at least from one re-initialization of the entity's
          network management system to the next re-initialization."
        SYNTAX       Unsigned32 (1..60)

     -- Port Notifications Group

      gBondTdimPortNotifications OBJECT IDENTIFIER
       ::= { gBondTdimPort 0 }

      gBondTdimServiceUp NOTIFICATION-TYPE
        OBJECTS {
          -- ifIndex is not needed here since we are under specific GBS
          gBondTdimServiceIfIdx,
          gBondTdimServiceOperState
        }
        STATUS      current
        DESCRIPTION
          "This notification indicates that a service indicated by the
          gBondTdimServiceIfIdx in a particular G.Bond TDIM port' is
          passing traffic.

          This notification MAY be send for the G.Bond TDIM port, while
          the port is Up, when the gBondTdimServiceOperState object has
          left the Down state.

          Generation of this notification is controlled by the
          gBondTdimServiceUpDownEnable object."
        ::= { gBondTdimPortNotifications 1 }

      gBondTdimServiceDown NOTIFICATION-TYPE
        OBJECTS {
          -- ifIndex is not needed here since we are under specific GBS
          gBondTdimServiceIfIdx,
          gBondTdimServiceOperState
        }
        STATUS      current
        DESCRIPTION
          "This notification indicates that a service indicated by the
          gBondTdimServiceIfIdx in a particular G.Bond TDIM port' has
          stopped passing the traffic.

          This notification MAY be send for the G.Bond TDIM port, while
          the port is Up, when the gBondTdimServiceOperState object has
          entered the Down state.

          Generation of this notification is controlled by the
          gBondTdimServiceUpDownEnable object."
        ::= { gBondTdimPortNotifications 2 }

      -- G.Bond TDIM Port group

      gBondTdimPortConfTable OBJECT-TYPE
        SYNTAX      SEQUENCE OF GBondTdimPortConfEntry
        MAX-ACCESS  not-accessible
        STATUS      current
        DESCRIPTION
          "Table for Configuration of G.Bond TDIM ports. Entries in
          this table MUST be maintained in a persistent manner"
        ::= { gBondTdimPort 1 }

      gBondTdimPortConfEntry OBJECT-TYPE
        SYNTAX      GBondTdimPortConfEntry
        MAX-ACCESS  not-accessible
        STATUS      current
        DESCRIPTION
          "An entry in the G.Bond TDIM Port Configuration table.
          Each entry represents an G.Bond TDIM port indexed by the
          ifIndex. Additional conifguration parameters are available
          via the gBondPortConfEntry of GBOND-MIB.
          Note that an G.Bond TDIM port runs on top of a single or
          multiple BCE port(s), which are also indexed by ifIndex."
        INDEX  { ifIndex }
        ::= { gBondTdimPortConfTable 1 }

      GBondTdimPortConfEntry ::=
        SEQUENCE {
          gBondTdimFecAdminState        TruthValue,
          gBondTdimFecWordSize          Unsigned32,
          gBondTdimFecRedundancySize    Unsigned32,
          gBondTdimFecInterleaverType   INTEGER,
          gBondTdimFecInterleaverDepth  Unsigned32,
          gBondTdimServiceUpDownEnable  TruthValue
        }

      gBondTdimFecAdminState  OBJECT-TYPE
        SYNTAX      TruthValue
        MAX-ACCESS  read-write
        STATUS      current
        DESCRIPTION
          "A desired state of the OPTIONAL Forward Error Correction
          (FEC) function of the G.Bond TDIM port.

          A value of 'false' indicates that the FEC function is
          disabled. A value of 'true' indicates that the FEC SHALL be
          enabled, if supported by the G.Bond TDIM port, as indicated
          by the gBondTdimFecSupported object.

          For the GBS-R ports, the value of this object cannot be
          changed directly. This value may be changed as a result of
          writing operation on the gBondTdimFecSupported object of a
          remote GBS-C.

          Modifications of this object MUST be performed when the link
          is Down.
          Attempts to change this object MUST be rejected (in case of
          SNMP with the error inconsistentValue), if the link is Up or
          Initializing or if it is an GBS-R.

          This object MUST be maintained in a persistent manner.

          This object maps to G.998.3 attribute aFECAdminState"
        REFERENCE
          "[G.998.3] Appendix II, B-X"
        ::= { gBondTdimPortConfEntry 1 }

      gBondTdimFecWordSize  OBJECT-TYPE
        SYNTAX      Unsigned32(0|20..255)
        UNITS       "octets"
        MAX-ACCESS  read-write
        STATUS      current
        DESCRIPTION
          "A FEC code word size in octets for the G.Bond TDIM ports
          supporting FEC function.

          This object is read-write for the GBS-C ports and read-only
          for the GBS-R.

          A value of zero SHALL be returned if the FEC is disabled
          (via gBondTdimFecAdminState) or not supported.

          Changing of the FEC code word size MUST be performed when the
          FEC enabled link is Down. Attempts to change this object MUST
          be rejected (In case of SNMP with the error
          inconsistentValue), if the link is Up or Initializing or the
          FEC function is disabled/not supported.

          This object MUST be maintained in a persistent manner.

          This object maps to G.998.3 attribute aFECWordSize"
        REFERENCE
          "[G.998.3] Appendix II, B-XI"
        ::= { gBondTdimPortConfEntry 2 }

      gBondTdimFecRedundancySize  OBJECT-TYPE
        SYNTAX      Unsigned32(0|2|4|8|16|20)
        UNITS       "octets"
        MAX-ACCESS  read-write
        STATUS      current
        DESCRIPTION
          "A FEC redundancy word size in octets for the G.Bond TDIM
          ports supporting FEC function.

          This object is read-write for the GBS-C ports and read-only
          for the GBS-R.

          A value of zero SHALL be returned if the FEC is disabled
          (via gBondTdimFecAdminState) or not supported.

          Changing of the FEC redundancy word size MUST be performed
          when the FEC enabled link is Down. Attempts to change this
          object MUST be rejected (In case of SNMP with the error
          inconsistentValue), if the link is Up or Initializing or the
          FEC function is disabled/not supported.

          This object MUST be maintained in a persistent manner.

          This object maps to G.998.3 attribute aFECRedundancySize"
        REFERENCE
          "[G.998.3] Appendix II, B-XII"
        ::= { gBondTdimPortConfEntry 3 }

      gBondTdimFecInterleaverType  OBJECT-TYPE
        SYNTAX      INTEGER {
          none(0),
          block(1),
          convolution(2)
        }
        MAX-ACCESS  read-write
        STATUS      current
        DESCRIPTION
          "An Interleaver type for the G.Bond TDIM ports supporting
          FEC function.

          This object is read-write for the GBS-C ports and read-only
          for the GBS-R.

          A value of none(0) SHALL be returned if the FEC is disabled
          (via gBondTdimFecAdminState) or not supported.

          Changing of the Interleaver type MUST be performed when the
          FEC enabled link is Down. Attempts to change this object MUST
          be rejected (In case of SNMP with the error
          inconsistentValue), if the link is Up or Initializing or the
          FEC function is disabled/not supported.

          This object MUST be maintained in a persistent manner.

          This object maps to G.998.3 attribute aFECInterleaverType"
        REFERENCE
          "[G.998.3] Appendix II, B-XIII"
        ::= { gBondTdimPortConfEntry 4 }

      gBondTdimFecInterleaverDepth  OBJECT-TYPE
        SYNTAX      Unsigned32(0|1|2|3|4|6|8|12|16|24|32|48|96)
        MAX-ACCESS  read-write
        STATUS      current
        DESCRIPTION
          "An Interleaver Depth for the G.Bond TDIM ports supporting
          FEC function.

          This object is read-write for the GBS-C ports and read-only
          for the GBS-R.

          A value of zero SHALL be returned if the FEC is disabled
          (via gBondTdimFecAdminState) or not supported.

          Changing of the Interleaver Depth MUST be performed when the
          FEC enabled link is Down. Attempts to change this object MUST
          be rejected (In case of SNMP with the error
          inconsistentValue), if the link is Up or Initializing or the
          FEC function is disabled/not supported.

          This object MUST be maintained in a persistent manner.

          This object maps to G.998.3 attribute aFECInterleaverDepth"
        REFERENCE
          "[G.998.3] Appendix II, B-XIV"
        ::= { gBondTdimPortConfEntry 5 }

      gBondTdimServiceUpDownEnable  OBJECT-TYPE
        SYNTAX      TruthValue
        MAX-ACCESS  read-write
        STATUS      current
        DESCRIPTION
          "Indicates whether gBondTdimServiceUp and gBondTdimServiceDown
          notifications should be generated for this interface.

          Value of true(1) indicates that the notifications are enabled.
          Value of false(2) indicates that the notifications are
          disabled.

          This object MUST be maintained in a persistent manner."
        ::= { gBondTdimPortConfEntry 6 }


      gBondTdimPortCapabilityTable OBJECT-TYPE
        SYNTAX      SEQUENCE OF GBondTdimPortCapabilityEntry
        MAX-ACCESS  not-accessible
        STATUS      current
        DESCRIPTION
          "Table for Capabilities of G.Bond TDIM ports. Entries in this
          table MUST be maintained in a persistent manner"
        ::= { gBondTdimPort 2 }

      gBondTdimPortCapabilityEntry OBJECT-TYPE
        SYNTAX      GBondTdimPortCapabilityEntry
        MAX-ACCESS  not-accessible
        STATUS      current
        DESCRIPTION
          "An entry in the G.Bond TDIM port Capability table.
          Each entry represents an G.Bond TDIM port indexed by the
          ifIndex. Additional capabilities are available via the
          gBondPortCapabilityEntry of GBOND-MIB.
          Note that a G.Bond TDIM port runs on top of a single
          or multiple BCE port(s), which are also indexed by ifIndex."
        INDEX  { ifIndex }
        ::= { gBondTdimPortCapabilityTable 1 }

      GBondTdimPortCapabilityEntry ::=
        SEQUENCE {
          gBondTdimFecSupported            TruthValue,
          gBondTdimFecMaxWordSize          Unsigned32,
          gBondTdimFecMaxRedundancySize    Unsigned32,
          gBondTdimFecInterleaverTypeSupported   INTEGER,
          gBondTdimFecMaxInterleaverDepth  Unsigned32
        }

      gBondTdimFecSupported  OBJECT-TYPE
        SYNTAX      TruthValue
        MAX-ACCESS  read-only
        STATUS      current
        DESCRIPTION
          "FEC and Interleaver Capability of the G.Bond/TDIM port.
          This object has a value of true(1) when the port supports the
          FEC and Interleaver function.
          A value of false(2) is returned when the port does not
          support the FEC and Interleaver function.

          This object maps to the G.998.3 attribute aFECSupported."
        REFERENCE
          "[G.998.3] Appendix II, B-VI"
        ::= { gBondTdimPortCapabilityEntry 1 }

      gBondTdimFecMaxWordSize  OBJECT-TYPE
        SYNTAX      Unsigned32(0|20..255)
        UNITS       "octets"
        MAX-ACCESS  read-only
        STATUS      current
        DESCRIPTION
          "A Maximum supported FEC code word size in octets for the
          G.Bond TDIM ports with FEC function.

          A value of zero SHALL be returned if the FEC is not supported.

          This object partially maps to G.998.3 attribute aFECWordSize"
        REFERENCE
          "[G.998.3] Appendix II, B-XI"
        ::= { gBondTdimPortCapabilityEntry 2 }

      gBondTdimFecMaxRedundancySize  OBJECT-TYPE
        SYNTAX      Unsigned32(0|2|4|8|16|20)
        UNITS       "octets"
        MAX-ACCESS  read-only
        STATUS      current
        DESCRIPTION
          "A Maximum supported FEC redundancy word size in octets for
          the G.Bond TDIM ports with FEC function.

          A value of zero SHALL be returned if the FEC is not supported.

          This object partially maps to G.998.3 attribute
          aFECRedundancySize"
        REFERENCE
          "[G.998.3] Appendix II, B-XII"
        ::= { gBondTdimPortCapabilityEntry 3 }

      gBondTdimFecInterleaverTypeSupported  OBJECT-TYPE
        SYNTAX      INTEGER {
          none(0),
          block(1),
          convolution(2),
          blockConvolution(3)
        }
        MAX-ACCESS  read-only
        STATUS      current
        DESCRIPTION
          "Suported Interleaver types for the G.Bond TDIM ports with
          FEC function.

          Possible values are:
            none             - the port does not support interleaving
            block            - the port supports Block Interleaver
            convolution      - the port supports Convolution Interleaver
            blockConvolution - the port supports both Block and
                               Convolution Interleaver

          This object partially maps to G.998.3 attribute
          aFECInterleaverType"
        REFERENCE
          "[G.998.3] Appendix II, B-XIII"
        ::= { gBondTdimPortCapabilityEntry 4 }

      gBondTdimFecMaxInterleaverDepth  OBJECT-TYPE
        SYNTAX      Unsigned32(0|1|2|3|4|6|8|12|16|24|32|48|96)
        MAX-ACCESS  read-only
        STATUS      current
        DESCRIPTION
          "A Maximum Interleaver Depth for the G.Bond TDIM ports with
          FEC function.

          A value of zero SHALL be returned if the Interleaver is not
          supported.

          This object partially maps to G.998.3 attribute
          aFECInterleaverDepth"
        REFERENCE
          "[G.998.3] Appendix II, B-XIV"
        ::= { gBondTdimPortCapabilityEntry 5 }


      gBondTdimPortStatusTable OBJECT-TYPE
        SYNTAX      SEQUENCE OF GBondTdimPortStatusEntry
        MAX-ACCESS  not-accessible
        STATUS      current
        DESCRIPTION
          "This table provides overall status information of G.Bond
          TDIM ports, complementing the generic status information from
          the ifTable of IF-MIB and gBondFltStatus of GBOND-MIB.
          Additional status information about connected BCEs is
          available from the relevant line MIBs

          This table contains live data from the equibcent. As such,
          it is NOT persistent."
        ::= { gBondTdimPort 3 }

      gBondTdimPortStatusEntry OBJECT-TYPE
        SYNTAX      GBondTdimPortStatusEntry
        MAX-ACCESS  not-accessible
        STATUS      current
        DESCRIPTION
          "An entry in the G.Bond TDIM port Status table.
          Each entry represents a G.Bond TDIM port indexed by the
          ifIndex.
          Note that an G.Bond GBS port runs on top of a single
          or multiple BCE port(s), which are also indexed by ifIndex."
        INDEX  { ifIndex }
        ::= { gBondTdimPortStatusTable 1 }

      GBondTdimPortStatusEntry ::=
        SEQUENCE {
          gBondTdimCrc4Errors              Counter32,
          gBondTdimCrc6Errors              Counter32,
          gBondTdimCrc8Errors              Counter32,
          gBondTdimFltStatus               BITS
        }

      gBondTdimCrc4Errors  OBJECT-TYPE
        SYNTAX      Counter32
        MAX-ACCESS  read-only
        STATUS      current
        DESCRIPTION
          "The total number of CRC-4 errors (frame header error) on all
          pairs in the G.Bond TDIM port. Simultaneous errors on M lines
          SHOULD be counted M times.

          This object maps to G.998.3 attribute aCRC4Errors.

          Discontinuities in the value of this counter can occur at
          re-initialization of the management system, and at other times
          as indicated by the value of ifCounterDiscontinuityTime,
          defined in IF-MIB."
        REFERENCE
          "[G.998.3] Appendix II, B-VII"
        ::= { gBondTdimPortStatusEntry 1 }

      gBondTdimCrc6Errors  OBJECT-TYPE
        SYNTAX      Counter32
        MAX-ACCESS  read-only
        STATUS      current
        DESCRIPTION
          "The total number of CRC-6 errors (super-frame error) on all
          pairs in the G.Bond TDIM port. Simultaneous errors on M lines
          SHOULD be counted 1 time.

          This object maps to G.998.3 attribute aCRC6Errors.

          Discontinuities in the value of this counter can occur at
          re-initialization of the management system, and at other times
          as indicated by the value of ifCounterDiscontinuityTime,
          defined in IF-MIB."
        REFERENCE
          "[G.998.3] Appendix II, B-VIII"
        ::= { gBondTdimPortStatusEntry 2 }

      gBondTdimCrc8Errors  OBJECT-TYPE
        SYNTAX      Counter32
        MAX-ACCESS  read-only
        STATUS      current
        DESCRIPTION
          "The total number of CRC-8 errors (event/message error) on all
          pairs in the G.Bond TDIM port. Simultaneous errors on M lines
          SHOULD be counted M times.

          This object maps to G.998.3 attribute aCRC8Errors.

          Discontinuities in the value of this counter can occur at
          re-initialization of the management system, and at other times
          as indicated by the value of ifCounterDiscontinuityTime,
          defined in IF-MIB."
        REFERENCE
          "[G.998.3] Appendix II, B-IX"
        ::= { gBondTdimPortStatusEntry 3 }

      gBondTdimFltStatus  OBJECT-TYPE
        SYNTAX      BITS {
          serviceDown(0),
          wrongConfig(1)
        }
        MAX-ACCESS  read-only
        STATUS      current
        DESCRIPTION
          "G.Bond TDIM port Fault Status. This is a bitmap of possible
          conditions. The various bit positions are:
            serviceDown         - at least one of the services defined
                                  for this aggregation group is down
                                  (due to low rate).
            wrongConfig         - at least one BCE at the remote GBS-R
                                  is already connected to another GBS.

          This object is intended to supplement ifOperStatus object
          in IF-MIB and gBondFltStatus in GBOND-MIB."
        REFERENCE
          "G.998.3 Section 6.3;
           IF-MIB, ifOperStatus; GBOND-MIB, gBondFltStatus"
        ::= { gBondTdimPortStatusEntry 4 }


      gBondTdimServiceTable OBJECT-TYPE
        SYNTAX      SEQUENCE OF GBondTdimServiceEntry
        MAX-ACCESS  not-accessible
        STATUS      current
        DESCRIPTION
          "Table of Services in G.Bond TDIM ports.
          Entries in this table MUST be maintained in a persistent
          manner"
        ::= { gBondTdimPort 4 }

      gBondTdimServiceEntry OBJECT-TYPE
        SYNTAX      GBondTdimServiceEntry
        MAX-ACCESS  not-accessible
        STATUS      current
        DESCRIPTION
          "An entry in the G.Bond TDIM Port Service table, containing
          the management information applicable to a particular Service
          in a G.Bond TDIM port, indexed by the gBondTdimServiceIdx."
        INDEX  { gBondTdimServiceIdx }
        ::= { gBondTdimServiceTable 1 }

      GBondTdimServiceEntry ::=
        SEQUENCE {
          gBondTdimServiceIdx           GBondTdimServiceIndex,
          gBondTdimServiceIfIdx         InterfaceIndex,
          gBondTdimServiceType          INTEGER,
          gBondTdimServiceSize          Unsigned32,
          gBondTdimServiceOperState     INTEGER
        }

      gBondTdimServiceIdx OBJECT-TYPE
        SYNTAX      GBondTdimServiceIndex
        MAX-ACCESS  not-accessible
        STATUS      current
        DESCRIPTION
          "G.Bond TDIM Service index - a unique index associated with
          a particular service entry, indicating relative placement of
          the service inside the G.Bond/TDIM frame.

          There can be up to 60 services defined over TDIM bonded
          facility. Services with lower indices have higher priority in
          case of bandwidth degradation.

          This objects maps to G.998.3 attribute aServiceID."
        REFERENCE
          "[G.998.3] Appendix II, C-I"
        ::= { gBondTdimServiceEntry 1 }

      gBondTdimServiceIfIdx OBJECT-TYPE
        SYNTAX      InterfaceIndex
        MAX-ACCESS  read-write
        STATUS      current
        DESCRIPTION
          "This is a unique index within the ifTable. It represents
          the interface index of a service to be transmitted over the
          G.Bond/TDIM service instance.

          This objects maps to WT-159 attribute aServiceIfIndex."
        REFERENCE
          "[WT-159] ZZZ"
          -- EdNote: update WT-159 and replace ZZZ and aServiceIfIndex
          -- with exact references
        ::= { gBondTdimServiceEntry 2 }

      gBondTdimServiceType  OBJECT-TYPE
        SYNTAX      INTEGER {
          ds1(0),
          e1(1),
          nxds0(2),
          nxe0(3),
          ds3(4),
          e3(5),
          clock(6),
          ethernet(7),
          atm(8),
          gfpNoFCS(9),
          gfp(10)
        }
        MAX-ACCESS  read-write
        STATUS      current
        DESCRIPTION
          "G.Bond TDIM Service Type.

          Possible values are:
            ds1            - Clear Channel DS1 (synchronous)
            e1             - Clear Channel E1 (synchronous)
            nxds0          - Fractional DS1 (synchronous)
            nxe0           - Fractional E1 (synchronous)
            ds3            - DS3 (synchronous)
            e3             - E3 (synchronous)
            clock          - Clock transfer (synchronous)
            ethernet       - Ethernet (asynchronous)
            atm            - ATM (asynchronous)
            gfpNoFCS       - GFP encapsulated without FCS (asynchronous)
            gfp            - GFP encapsulated with FCS (asynchronous)

          For the GBS-R ports, the value of this object cannot be
          changed directly. This value may be changed as a result of
          writing operation on the gBondTdimServiceType object of a
          remote GBS-C.

          Modifications of this object MUST be performed when the link
          is Down.
          Attempts to change this object MUST be rejected (in case of
          SNMP with the error inconsistentValue), if the link is Up or
          Initializing or if it is an GBS-R.

          This object MUST be maintained in a persistent manner.

          This object maps to G.998.3 attribute aServiceType"
        REFERENCE
          "[G.998.3] Appendix II, C-II"
        ::= { gBondTdimServiceEntry 3 }

      gBondTdimServiceSize  OBJECT-TYPE
        SYNTAX      Unsigned32(0|20..255)
        UNITS       "octets"
        MAX-ACCESS  read-write
        STATUS      current
        DESCRIPTION
          "Service size in octets per bonding sub-block for a specific
          service identified by gBondTdimServiceIdx.

          For TDM (synchronous) services with variable size
          e.g. fractional DS1/E1 - this object represents the number of
          DS0/E0 channels.
          For asynchronous services (Ethernet, ATM, GFPnoFCS or GFP) -
          this object represents max. number of octets.

          A GET operation returns current value.
          A SET operation, allowed on GBS-C only when the link is Down,
          changes the service size to the indicated value. If the link
          is not down or the service type is fixed rate TDM service
          (gBondTdimServiceType is NxDS0, NxE0, DS1, E1, DS3, E3 or
          Clock), the operation MUST be rejected (in case of SNMP with
          the error inconsistentValue).

          This object MUST be maintained in a persistent manner.

          This object maps to G.998.3 attribute aServiceSize"
        REFERENCE
          "[G.998.3] Appendix II, C-III"
        ::= { gBondTdimServiceEntry 4 }

      gBondTdimServiceOperState  OBJECT-TYPE
        SYNTAX      INTEGER {
          up(1),
          down(2)
        }
        MAX-ACCESS  read-only
        STATUS      current
        DESCRIPTION
          "G.Bond TDIM Service Operation State.

          Possible values are:
            up                  - Service is up passing traffic.
            down                - Service is down, due to a variety of
                                  reasons, e.g. G.Bond TDIM port is
                                  down, current link bandwidth is too
                                  low to support a particular service,
                                  etc."
        REFERENCE
          "[G.998.3] 10.2.3"
        ::= { gBondTdimServiceEntry 5 }


     --
     -- Conformance Statements
     --

      gBondTdimGroups      OBJECT IDENTIFIER
        ::= { gBondTdimConformance 1 }

      gBondTdimCompliances OBJECT IDENTIFIER
        ::= { gBondTdimConformance 2 }

      -- Object Groups

      gBondTdimBasicGroup OBJECT-GROUP
        OBJECTS {
          gBondTdimCrc4Errors,
          gBondTdimCrc6Errors,
          gBondTdimCrc8Errors,
          gBondTdimFecSupported,
          gBondTdimServiceIfIdx,
          gBondTdimServiceType,
          gBondTdimServiceSize,
          gBondTdimServiceOperState,
          gBondTdimServiceUpDownEnable,
          gBondTdimFltStatus
        }
        STATUS      current
        DESCRIPTION
          "A collection of objects representing management information
          for G.Bond TDIM ports."
        ::= { gBondTdimGroups 1 }

      gBondTdimFecGroup OBJECT-GROUP
        OBJECTS {
          gBondTdimFecSupported,
          gBondTdimFecAdminState,
          gBondTdimFecWordSize,
          gBondTdimFecRedundancySize,
          gBondTdimFecInterleaverType,
          gBondTdimFecInterleaverDepth,
          gBondTdimFecMaxWordSize,
          gBondTdimFecMaxRedundancySize,
          gBondTdimFecInterleaverTypeSupported,
          gBondTdimFecMaxInterleaverDepth
        }
        STATUS      current
        DESCRIPTION
          "A collection of objects supporting OPTIONAL Forward Error
          Correction (FEC) and Interleaver function in G.Bond TDIM
          ports."
        ::= { gBondTdimGroups 2 }

      gBondTdimAlarmConfGroup OBJECT-GROUP
        OBJECTS {
          gBondTdimServiceUpDownEnable
        }
        STATUS      current
        DESCRIPTION
          "A collection of objects required for configuration of alarm
          thresholds and notifications in G.Bond TDIM ports."
        ::= { gBondTdimGroups 3 }

      gBondTdimNotificationGroup NOTIFICATION-GROUP
        NOTIFICATIONS {
          gBondTdimServiceUp,
          gBondTdimServiceDown
        }
        STATUS      current
        DESCRIPTION
          "This group supports notifications of significant conditions
          associated with G.Bond TDIM ports."
        ::= { gBondTdimGroups 4 }

     -- Compliance Statements

      gBondTdimCompliance MODULE-COMPLIANCE
        STATUS      current
        DESCRIPTION
          "The compliance statement for G.Bond TDIM interfaces.
          Compliance with the following external compliance statements
          is REQUIRED:

          MIB Module             Compliance Statement
          ----------             --------------------
          IF-MIB                 ifCompliance3
          GBOND-MIB              gBondCompliance"

        MODULE  -- this module
          MANDATORY-GROUPS {
            gBondTdimBasicGroup,
            gBondTdimAlarmConfGroup,
            gBondTdimNotificationGroup
          }

          GROUP       gBondTdimFecGroup
          DESCRIPTION
            "Support for this group is only required for implementations
            supporting G.Bond FEC and Interleaver function."


        ::= { gBondTdimCompliances 1 }
   END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
