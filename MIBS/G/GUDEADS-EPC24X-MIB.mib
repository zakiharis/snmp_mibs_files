GUDEADS-EPC24X-MIB DEFINITIONS ::= BEGIN

IMPORTS
	enterprises,
	MODULE-IDENTITY,
	OBJECT-TYPE,
	Counter32,
	Integer32
		FROM SNMPv2-SMI
	OBJECT-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id: GUDEADS-EPC24X-MIB.txt,v 1.4 2007/10/12 13:30:02 petes1 Exp $"
	-- 1.3.6.1.4.1.28507
	::= { enterprises 28507 }


epc24Fuse1 OBJECT-TYPE
	SYNTAX  Integer32 (0..1)
	MAX-ACCESS read-only
	STATUS  current
	DESCRIPTION
		"State of Fuse1 (1 = ok)"
	-- 1.3.6.1.4.1.28507.5.1.1.3
	::= { epc24powerports 3 }


epc24Fuse2 OBJECT-TYPE
	SYNTAX  Integer32 (0..1)
	MAX-ACCESS read-only
	STATUS  current
	DESCRIPTION
		"State of Fuse2 (1 = ok)"
	-- 1.3.6.1.4.1.28507.5.1.1.4
	::= { epc24powerports 4 }


epc24Fuse3 OBJECT-TYPE
	SYNTAX  Integer32 (0..1)
	MAX-ACCESS read-only
	STATUS  current
	DESCRIPTION
		"State of Fuse3 (1 = ok)"
	-- 1.3.6.1.4.1.28507.5.1.1.5
	::= { epc24powerports 5 }


gadsEPC24 OBJECT IDENTIFIER 
	-- 1.3.6.1.4.1.28507.5
	::= { gudeads 5 }

-- Scalars and Tables
--

epc24Objects OBJECT IDENTIFIER 
	-- 1.3.6.1.4.1.28507.5.1
	::= { gadsEPC24 1 }

epc24powerports OBJECT IDENTIFIER 
	-- 1.3.6.1.4.1.28507.5.1.1
	::= { epc24Objects 1 }

epc24portNumber OBJECT-TYPE
	SYNTAX  Integer32 (1..24)
	MAX-ACCESS read-only
	STATUS  current
	DESCRIPTION
		"The number of PowerPorts"
	-- 1.3.6.1.4.1.28507.5.1.1.1
	::= { epc24powerports 1 }


-- the Interfaces table
-- The Interfaces table contains information on the entity's
-- interfaces.  Each sub-layer below the internetwork-layer
-- of a network interface is considered to be an interface.

epc24portTable OBJECT-TYPE
	SYNTAX  SEQUENCE OF Epc24portEntry
	MAX-ACCESS not-accessible
	STATUS  current
	DESCRIPTION
		"list of all EPC Powerports"
	-- 1.3.6.1.4.1.28507.5.1.1.2
	::= { epc24powerports 2 }


epc24portEntry OBJECT-TYPE
	SYNTAX  Epc24portEntry
	MAX-ACCESS not-accessible
	STATUS  current
	DESCRIPTION
		"An entry containing management information applicable to a
		particular powerport."
	INDEX {
		epc24PortIndex }
	-- 1.3.6.1.4.1.28507.5.1.1.2.1
	::= { epc24portTable 1 }


Epc24portEntry ::= SEQUENCE {

	epc24PortIndex       Integer32,
	epc24PortName        OCTET STRING,
	epc24PortState       INTEGER,
	epc24PortSwitchCount Counter32 }


epc24PortIndex OBJECT-TYPE
	SYNTAX  Integer32 (1..24)
	MAX-ACCESS not-accessible
	STATUS  current
	DESCRIPTION
		"A unique value, greater than zero, for each PowerPort."
	-- 1.3.6.1.4.1.28507.5.1.1.2.1.1
	::= { epc24portEntry 1 }


epc24PortName OBJECT-TYPE
	SYNTAX  OCTET STRING (SIZE (0..15))
	MAX-ACCESS read-only
	STATUS  current
	DESCRIPTION
		"A textual string containing name of a PowerPort."
	-- 1.3.6.1.4.1.28507.5.1.1.2.1.2
	::= { epc24portEntry 2 }


epc24PortState OBJECT-TYPE
	SYNTAX  INTEGER {
			off(0),
			on(1) }
	MAX-ACCESS read-write
	STATUS  current
	DESCRIPTION
		"current state a PowerPort"
	-- 1.3.6.1.4.1.28507.5.1.1.2.1.3
	::= { epc24portEntry 3 }


epc24PortSwitchCount OBJECT-TYPE
	SYNTAX  Counter32
	MAX-ACCESS read-only
	STATUS  current
	DESCRIPTION
		"The total number of switch actions ocurred on a PowerPort.
		Does not count switch commands which will not switch
		the ralay state, so just real relay switches are displayed here."
	-- 1.3.6.1.4.1.28507.5.1.1.2.1.4
	::= { epc24portEntry 4 }


-- Notification Types
--

epc24Events OBJECT IDENTIFIER 
	-- 1.3.6.1.4.1.28507.5.2
	::= { gadsEPC24 2 }

-- Conformance
--

epc24Conf OBJECT IDENTIFIER 
	-- 1.3.6.1.4.1.28507.5.3
	::= { gadsEPC24 3 }

-- Groups
--

epc24Groups OBJECT IDENTIFIER 
	-- 1.3.6.1.4.1.28507.5.3.1
	::= { epc24Conf 1 }

-- Compliance
--

epc24Compls OBJECT IDENTIFIER 
	-- 1.3.6.1.4.1.28507.5.3.2
	::= { epc24Conf 2 }

epc24BasicGroup OBJECT-GROUP
	OBJECTS {
		epc24portNumber,
		epc24PortName,
		epc24PortState,
		epc24PortSwitchCount,
		epc24Fuse1,
		epc24Fuse2,
		epc24Fuse3 }
	STATUS  current
	DESCRIPTION
		"Basic objects."
	-- 1.3.6.1.4.1.28507.5.3.1.1
	::= { epc24Groups 1 }

END
