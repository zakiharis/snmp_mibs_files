-- ****************************************************************************
--                             gdc5553.mib
-- ****************************************************************************

-- Copyright 1995 General DataComm Inc., All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- This MIB module uses the extended OBJECT-TYPE macro as
-- defined in RFC 1212.

-- Note:  All rows in all tables defined within this MIB module are
-- virtual.  They can neither be created or deleted by management
-- operations.


--
-- ****************************************************************************
--                        Revision History
-- ****************************************************************************

-- Version   Date	Name

-- 1.00A     19-Sep-95  R. Zawislak     Initial Revision
-- 1.00B     10-Oct-95  R. Zawislak     Remove 'other' from sc5553ChannelType
--                                      and delete sc5553AggDataRate
--                                      Update assignment of sc5553
-- 1.00C     22-Nov-95  S. Veillette	1) Compress the DS0 Allocation Table to
--                                         use OCTET STRING object for DS0
--                                         Allocation
--                                      2) Replace sc5553EIAtestLeads with
--                                         sc5553ExtLLCtrl & sc5553ExtRLCtrl
--                                      3) Add sc5553Alarms table
--                                      4) Add sc5553Version table
-- 1.00D     30-Nov-95  S. Veillette    
--
--           1) Remove sc5553AlarmHistory table
--           2) Remove sc5553ChanSigStat table
--           3) change object name sc5553SystemMibVersion -> sc5553MibVersion
--           4) remove sc5553ProductType from Version table
--           5) change sc5553Highway ACCESS to read-only
--           6) change sc5553DS0Allocation object format to bit mapped ds0's
--           7) complete updates to all objects in the sc5553Allocation &
--              sc5553Configuration tables
--           8) additional entries in the Alarm table
--
-- 1.00E     07-Dec-95  J. Costa
--
--           1) New diagnostics table
--           2) Description change in sc5553DS0Allocation
--
-- 1.00F     28-Dec-95  S. Veillette
--
--           1) Change enum definitions for sc5553ClockInvert & sc5553DataInvert
--              in the Configuration Table
--           2) Change enum definitions for sc5553DS0BaseRate, (DS0 Allocation table)
--           3) Correct DS0's 29-32 in the sc5553DS0Allocation object, (DS0 Allocation table)
--
-- 1.00G     02-Jan-96  C. Amorossi
--
--	     1) Changed comments for the following objects:  sc5553DiagTestResults,
--              sc5553DiagTestSelection, sc5553LedStatus.
--           2) Changed name of sc5553TestResults to sc5553DiagTestResults
--
-- 1.00H     30-Jan-96  C. Amorossi/S. Veillette TEAM
--
--	     1) added sc5553WakeUpRemote to the config table
--           2) modifications to the DTE Signal Status table:
--              changed enums for sc5553RXDstatus
--              changed enums for sc5553TXDstatus
--              added sc5553ALTestLeadStatus object
--              added sc5553RLTestLeadStatus object
--           3) modified description of LocalLoopBack with SelfTest in the Diag table
--           4) replace sc5553TelcoSNMPTestAlarm object with sc5553EIATestAlarm in the alarm table
--
-- 1.00J     28-Mar-96  C. Amorossi
--
--	     1) Changed comments for the following objects:  sc5553RXDstatus,
--              sc5553TXDstatus, sc5553LedStatus.
-- 1.00K     05-Mar-98  C. Amorossi
--           1) Added firmware downloading objects to sc5553VersionTable 
--           2) Made sc5553FirmwareRev obsolete
-- ****************************************************************************

--
-- ****************************************************************************
--                       mib definitions begin
-- ****************************************************************************


GDC-5553-MIB DEFINITIONS ::= BEGIN

IMPORTS	enterprises			FROM RFC1155-SMI
	OBJECT-TYPE			FROM RFC-1212
	DisplayString			FROM RFC1213-MIB
	SCinstance			FROM GDCMACRO-MIB;

gdc 	               OBJECT IDENTIFIER ::= { enterprises 498 }
dsx1                   OBJECT IDENTIFIER ::= { gdc 6 }
sc5553                 OBJECT IDENTIFIER ::= { dsx1 5 }

sc5553Version          OBJECT IDENTIFIER ::= { sc5553 1 }
sc5553Allocation       OBJECT IDENTIFIER ::= { sc5553 2 }
sc5553Configuration    OBJECT IDENTIFIER ::= { sc5553 3 }
sc5553DTEsignalStat    OBJECT IDENTIFIER ::= { sc5553 4 }
sc5553Diagnostics      OBJECT IDENTIFIER ::= { sc5553 5 }
sc5553Maintenance      OBJECT IDENTIFIER ::= { sc5553 6 }
sc5553Alarms           OBJECT IDENTIFIER ::= { sc5553 7 }


-- ****************************************************************************


sc5553MIBversion OBJECT-TYPE
    SYNTAX DisplayString (SIZE (5))
    ACCESS read-only
    STATUS mandatory
    DESCRIPTION
    "Identifies the version of the MIB. The format of the version
    is x.yzT, where 'x' identifies the major revision number, 'y'
    identifies the minor revision number, 'z' identifies the
    typographical revision, and T identifies the test revision.
    Upon formal release, no designation for the test revision will
    be present. Acceptable values for the individual revision
    components are as follows:
    x: 1 - 9,    y: 0 - 9,    z: 0 - 9,    T: A - Z"
    ::= { sc5553Version 1 }



--
-- ****************************************************************************
--                                Version Table
-- ****************************************************************************


sc5553VersionTable OBJECT-TYPE
    SYNTAX SEQUENCE OF Sc5553VersionEntry
    ACCESS not-accessible
    STATUS mandatory
    DESCRIPTION " "
    ::= { sc5553Version 2  }

sc5553VersionEntry OBJECT-TYPE
    SYNTAX Sc5553VersionEntry
    ACCESS not-accessible
    STATUS mandatory
    DESCRIPTION
    "An entry in the GDC Dsx1 Version Table."
    INDEX	{ sc5553VersionIndex }
    ::= { sc5553VersionTable 1 }

Sc5553VersionEntry ::=
    SEQUENCE {
        sc5553VersionIndex              SCinstance,
        sc5553FirmwareRev               DisplayString,
	sc5553ActiveFirmwareRev 	DisplayString,
	sc5553StoredFirmwareRev		DisplayString,
	sc5553StoredFirmwareStatus	INTEGER,
	sc5553SwitchActiveFirmware	INTEGER,
	sc5553DownloadingMode          	INTEGER
    }

sc5553VersionIndex OBJECT-TYPE
    SYNTAX SCinstance
    ACCESS read-only
    STATUS mandatory
    DESCRIPTION
    "Identifies Version parameters associated with the managed object."
    ::= { sc5553VersionEntry 1 }


sc5553FirmwareRev OBJECT-TYPE
    SYNTAX DisplayString (SIZE(2))
    ACCESS read-only
    STATUS obsolete
    DESCRIPTION
    "The version number of the firmware, to allow products to know which
    revision is installed.  The released version number is sequenced from
    --, A-, ... AA, ... ZZ.  Test versions are numerical from 01 to 99."
    ::= { sc5553VersionEntry 2 }

sc5553ActiveFirmwareRev OBJECT-TYPE
    SYNTAX  DisplayString (SIZE(8))
    ACCESS  read-only
    STATUS  mandatory
    DESCRIPTION
        "The version number of the firmware currently executing.
	 The format is MM.NN.BB where:
		MM: Major Revision (0-99)
		NN: Minor Revision (0-99)
		BB: Bug Fix Revision (0-99)
	 Valid [i]nterface = 0"
    ::= { sc5553VersionEntry 3 }

sc5553StoredFirmwareRev OBJECT-TYPE
    SYNTAX DisplayString (SIZE(8))
    ACCESS read-only
    STATUS mandatory
    DESCRIPTION
        "The version number of the firmware stored (in a compressed format) 
         but not currently executing.
		MM: Major Revision (0-99)
		NN: Minor Revision (0-99)
		BB: Bug Fix Revision (0-99)
	 Valid [i]nterface = 0"
    ::= { sc5553VersionEntry 4 }

sc5553StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

         statBlank(1)    	Factory Default                  
         statDownLoading(2)	In process of downloading firmware
	 statOK(3)		Zipped version checksum succesful (OK to switch)
				(can set sc5553SwitchActiveFirmware to	
				switchActive(2))
	 statCheckSumBad(4)    	Failed checksum after download
	 statUnZipping(5)	In process of uncompressing into active area
	 statBadUnZip(6)      	Failed last uncompress 
	 statDownloadAborted(7) Download aborted by user             

	 Valid [i]nterface = 0"
    ::= { sc5553VersionEntry 5 }


sc5553SwitchActiveFirmware OBJECT-TYPE
    SYNTAX INTEGER {
        switchNorm(1),                  -- Read only
        switchActive(2)			-- Write only
    }
    ACCESS read-write
    STATUS mandatory
    DESCRIPTION
        "This object is used to switch the active executing firmware from 
	 the version in sc5553ActiveFirmwareRev to the version in 
	 sc5553StoredFirmwareRev.

	 When a  switchActive(2) is set (write only) the element will:
		1) reboot
		2) uncompress stored code into active area
		3) perform checksum on active area
		4) Set sc5553StoredStatus object to indicate results
		5) If succesfull:
		    update sc5553ActiveFirmwareRev and sc5553StoredFirmwareRev
		    and begin executing
		   If failed: 
		    replace active area with previous revision

	 The switchNorm(1) enumeration will always be read. 

	 Setting switchActive(2) when the sc5553StoredFirmwareStatus is 
	 not statOK(3) will result in an error.
	 Valid [i]nterface = 0"
    ::= { sc5553VersionEntry 6 }


sc5553DownloadingMode OBJECT-TYPE
    SYNTAX INTEGER {
        disableAll(1),
        enableAndWait(2),
	enableAndSwitch(3)
    }
    ACCESS read-write
    STATUS mandatory
    DESCRIPTION
        "This object is used to configure the download mode:

         disableAll(1)	       Prevents any firmware downloading to GDCHDSL

         enableAndWait(2)      Allows downloading zipped code to be stored only!
								
	 enableAndSwitch(3)    Allows downloading and then unzips and begins executing
			       the new code
	 Valid [i]nterface = 0"
    ::= { sc5553VersionEntry 7 }


--
-- ****************************************************************************
--                     DS0 Allocation Scheme table
-- ****************************************************************************



sc5553Ds0AllocationTable OBJECT-TYPE
    SYNTAX SEQUENCE OF Ds05553AllocationEntry
    ACCESS not-accessible
    STATUS mandatory
    DESCRIPTION
    "The GDC 5553 DS0 allocation table"
    ::= { sc5553Allocation 1 }


sc5553Ds0AllocationEntry OBJECT-TYPE
    SYNTAX Ds05553AllocationEntry
    ACCESS not-accessible
    STATUS mandatory
    DESCRIPTION
    "The GDC SC5553 Configuration table entry."
    INDEX { sc5553Ds0AllocationIndex }
    ::= { sc5553Ds0AllocationTable 1 }


Ds05553AllocationEntry ::=
    SEQUENCE {
        sc5553Ds0AllocationIndex    SCinstance,
        sc5553DS0BaseRate           INTEGER,
        sc5553Highway               INTEGER,
	sc5553DccDs0                INTEGER,
        sc5553DS0Allocation         OCTET STRING
    }

sc5553Ds0AllocationIndex OBJECT-TYPE
    SYNTAX SCinstance
    ACCESS read-only
    STATUS mandatory
    DESCRIPTION
    "The index value: slot, line, drop, and interface"
    ::= { sc5553Ds0AllocationEntry 1 }


sc5553DS0BaseRate OBJECT-TYPE
    SYNTAX INTEGER
    {
    	nx56k(2),			-- N X 56K rate
    	nx64k(1)			-- N X 64K rate
    }
    ACCESS read-write
    STATUS mandatory
    DESCRIPTION
    "Indicates the DS0 base rate: either 56K or 64K bits per second.
    This is used in conjunction with the number of DS0s set to 'enabled'
    to determine the total bandwidth. The base rate of 64K defines the
    DS0 data format as clear channel in which all 8 bits of the DS0 are used.
    A base rate of 56K defines the DS0 as non-clear in which bits 1-7 are used
    for channel data and the 8th bit is either unused and forced to marks or
    used to pass signaling information."
    ::= { sc5553Ds0AllocationEntry 2 }


sc5553Highway OBJECT-TYPE
    SYNTAX INTEGER
    {
        highway1(1),    -- All DS0 are routed to Highway 1
    	highway2(2),    -- All DS0 are routed to Highway 2
    	highway3(3),    -- All DS0 are routed to Highway 3
    	highway4(4)     -- All DS0 are routed to Highway 4
    }
    ACCESS read-only
    STATUS mandatory
    DESCRIPTION
    "The highway used for ds0 traffic by this device"
    ::= { sc5553Ds0AllocationEntry 3 }


sc5553DccDs0 OBJECT-TYPE
    SYNTAX INTEGER
    {
        dccDs01(1),     dccDs02(2),     dccDs03(3),     dccDs04(4),
    	dccDs05(5),     dccDs06(6),     dccDs07(7),     dccDs08(8),
    	dccDs09(9),     dccDs010(10),   dccDs011(11),   dccDs012(12),
    	dccDs013(13),   dccDs014(14),   dccDs015(15),   dccDs016(16),
    	dccDs017(17),   dccDs018(18),   dccDs019(19),   dccDs020(20),
    	dccDs021(21),   dccDs022(22),   dccDs023(23),   dccDs024(24),
    	dccDs025(25),   dccDs026(26),   dccDs027(27),   dccDs028(28),
    	dccDs029(29),   dccDs030(30),   dccDs031(31),   dccDs032(32),
    	noDccDs0(33)
    }
    ACCESS read-write
    STATUS mandatory
    DESCRIPTION
    "The values 1-32 indicates Ds0 1 - DS0 32, is used for diagnostics
    communications. The value noDccDs0(33) indicates that diagnostics
    communications does not utilize a seperate Ds0, also see the related mib
    object: sc5553InbandDccMode in the Configuration table below."
    ::= { sc5553Ds0AllocationEntry 4 }


sc5553DS0Allocation OBJECT-TYPE
    SYNTAX OCTET STRING (SIZE(5))
    ACCESS read-only
    STATUS mandatory
    DESCRIPTION
    "A bitwise snapshot of the DS0 allocation as follows:
    first octet   second octet   third octet    fourth octet    fifth octet
    -----------   -------------  -------------  --------------  -----------
    bit0 - ds0 7  bit0 - ds0 14  bit0 - ds0 21  bit0 - ds0 28   bit0 - n/u
    bit1 - ds0 6  bit1 - ds0 13  bit1 - ds0 20  bit1 - ds0 27   bit1 - n/u
    bit2 - ds0 5  bit2 - ds0 12  bit2 - ds0 19  bit2 - ds0 26   bit2 - n/u
    bit3 - ds0 4  bit3 - ds0 11  bit3 - ds0 18  bit3 - ds0 25   bit3 - ds0 32
    bit4 - ds0 3  bit4 - ds0 10  bit4 - ds0 17  bit4 - ds0 24   bit4 - ds0 31
    bit5 - ds0 2  bit5 - ds0 9   bit5 - ds0 16  bit5 - ds0 23   bit5 - ds0 30
    bit6 - ds0 1  bit6 - ds0 8   bit6 - ds0 15  bit6 - ds0 22   bit6 - ds0 29
    bit7 - n/u    bit7 - n/u     bit7 - n/u     bit7 - n/u      bit7 - n/u 

    bit values are:  0 = disabled, 1 = enabled,
    Reservation of DS0's for this device is accomplished through the
    new shelf mib."
    ::= { sc5553Ds0AllocationEntry 5 }


--
-- ****************************************************************************
--                        Configuration table
-- ****************************************************************************


sc5553ConfigTable OBJECT-TYPE
    SYNTAX SEQUENCE OF Sc5553ConfigEntry
    ACCESS not-accessible
    STATUS mandatory
    DESCRIPTION
    "The GDC 5553 Configuration table."
    ::= { sc5553Configuration 1 }


sc5553ConfigEntry OBJECT-TYPE
    SYNTAX Sc5553ConfigEntry
    ACCESS not-accessible
    STATUS mandatory
    DESCRIPTION
    "The sc5553 Configuration table entry."
    INDEX { sc5553ConfigIndex }
    ::= { sc5553ConfigTable 1 }


Sc5553ConfigEntry ::=
    SEQUENCE {
        sc5553ConfigIndex       SCinstance,
        sc5553ExternalTiming    INTEGER,
        sc5553ChannelType       INTEGER,
        sc5553ClockInvert       INTEGER,
        sc5553DataInvert        INTEGER,
        sc5553ConstantDCD       INTEGER,
        sc5553ConstantDSR       INTEGER,
        sc5553RTSCTScontrol     INTEGER,
        sc5553ExtLLCtrl         INTEGER,
        sc5553ExtRLCtrl         INTEGER,
        sc5553InbandDccMode     INTEGER,
        sc5553InbandLoop        INTEGER,
        sc5553InbandLoopdown    INTEGER,
        sc5553WakeUpRemote      DisplayString
    }


sc5553ConfigIndex OBJECT-TYPE
    SYNTAX SCinstance
    ACCESS read-only
    STATUS mandatory
    DESCRIPTION
    "The index value: slot, line, drop, and interface"
    ::= { sc5553ConfigEntry 1 }


sc5553ExternalTiming OBJECT-TYPE
    SYNTAX INTEGER
    {
    	disabled(1),
    	enabled(2)
    }
    ACCESS read-write
    STATUS mandatory
    DESCRIPTION
    "Disabled indicates timing is provided by the 5553. 
    Enabled indicates timing is provided by the customer business equipment"
    ::= { sc5553ConfigEntry 2 }


sc5553ChannelType OBJECT-TYPE
    SYNTAX INTEGER
    {
   	v35(1),     -- V.35 interface
    	eia530(2)   -- 530 EIA interface
    }
    ACCESS read-only
    STATUS mandatory
    DESCRIPTION
    "The channel interface type"
    ::= { sc5553ConfigEntry 3 }


sc5553ClockInvert OBJECT-TYPE
    SYNTAX INTEGER
    {
    	txClockNormRxClockNorm(1),	-- Tx and Rx clock normal
    	txClockNormRxClockInvert(2),	-- Tx clock normal, Rx clock inverted
    	txClockInvertRxClockNorm(3),	-- Tx clock inv, Rx clock normal
    	txClockInvertRxClockInvert(4)	-- Tx and Rx clock inverted
    }
    ACCESS read-write
    STATUS mandatory
    DESCRIPTION
    "Clock invert option"
    ::= { sc5553ConfigEntry 4 }


sc5553DataInvert OBJECT-TYPE
    SYNTAX INTEGER
    {
    	txDataNormRxDataNorm(1),	-- Tx and Rx data normal
    	txDataNormRxDataInvert(2),	-- Tx data normal, Rx data inverted
    	txDataInvertRxDataNorm(3),	-- Tx data inverted, Rx data normal
    	txDataInvertRxDataInvert(4)    -- Tx and Rx data inverted   
    }
    ACCESS read-write
    STATUS mandatory
    DESCRIPTION
    "Data invert option"
    ::= { sc5553ConfigEntry 5 }


sc5553ConstantDCD OBJECT-TYPE
    SYNTAX INTEGER
    {
    	disabled(1),     -- local DCD follows inband CMI
    	enabled(2)       -- local DCD forced on
    }
    ACCESS read-write
    STATUS mandatory
    DESCRIPTION
    "Controls the operation of Data Carrier Detect (DCD) signal."
    ::= { sc5553ConfigEntry 6 }


sc5553ConstantDSR OBJECT-TYPE
    SYNTAX INTEGER
    {
    	disabled(1),     -- local DSR follows inband CMI
    	enabled(2)       -- local DSR forced on
    }
    ACCESS read-write
    STATUS mandatory
    DESCRIPTION
    "Controls the operation of the Data Set Ready (DSR) signal."
    ::= { sc5553ConfigEntry 7 }


sc5553RTSCTScontrol OBJECT-TYPE
    SYNTAX INTEGER
    {
        ctsOn(1),               -- CTS forced on
        ctsDelay10ms(2),        -- CTS delay 10 ms
        ctsDelayStandard(3)     -- CTS standard delay
    }
    ACCESS read-write
    STATUS mandatory
    DESCRIPTION
    "Controls the function of the channel's Request To Send and 
    and Clear To Send signals used for flow control. ctsOn indicates
    that CTS is forced on at all times, ctsDelay10ms indicates that
    CTS responds to RTS after a 10ms delay, and ctsDelayStandard 
    indicates that CTS responds to RTS after a delay of 40 bits times."
    ::= { sc5553ConfigEntry 8 }


sc5553ExtLLCtrl OBJECT-TYPE
    SYNTAX INTEGER
    {
    	disabled(1),
    	enabled(2)
    }
    ACCESS read-write
    STATUS mandatory
    DESCRIPTION
    "Enables/disables the ability to initiate a local loop test via the
     assertion of the EIA LL test lead at the DTE interface."
    ::= { sc5553ConfigEntry 9 }


sc5553ExtRLCtrl OBJECT-TYPE
    SYNTAX INTEGER
    {
    	disabled(1),
    	enabled(2)
    }
    ACCESS read-write
    STATUS mandatory
    DESCRIPTION
    "Enables/disables the ability to initiate a remote loop test via the
     assertion of the EIA RL test lead at the DTE interface."
    ::= { sc5553ConfigEntry 10 }


sc5553InbandDccMode OBJECT-TYPE
    SYNTAX INTEGER
    {
    	none(1),
    	embedded(2),
    	dccDs0(3)
    }
    ACCESS read-write
    STATUS mandatory
    DESCRIPTION
    "The mode of propagation of inband Diagnostics Communication Channel to
    the dedicated remote NMS553 unit. None specifies no inband DCC. Embedded
    is an allowed value when the mib object sc5553DS0BaseRate is set to Nx56K,
    and specifies that DCC is propagated in the 8th bit of the assigned DS0's.
    dccDs0 specifies that a DS0 is used for propagation of DCC, this value 
    would be selected if the sc5553DS0BaseRate is Nx64k (clear channel) since
    all data bits are used for user data,  a minimum of two DS0's must be 
    assigned to this device in this mode, the last ds0 should be set as the 
    sc5553DccDs0 when using this mode.  The DS0 allocation may be read
    from the mib object sc5553DS0Allocation."
    ::= { sc5553ConfigEntry 11 }


sc5553InbandLoop OBJECT-TYPE
    SYNTAX INTEGER
    {
    	disable(1),    -- disable detection of inband loop code
    	pn127(2)       -- PN127 random code
    }
    ACCESS read-write
    STATUS mandatory
    DESCRIPTION
    "This object is also referred to as RDL response. When enabled (pn127),
    the channel will enter a remote data loopback when an inband RDL code
    is detected. The required in-band code must conform to 
    CCITT V.54 PN-127 scrambled codes."
    ::= { sc5553ConfigEntry 12 }


sc5553InbandLoopdown OBJECT-TYPE
    SYNTAX INTEGER {
	disable(1),
	tenMinutes(2)
    }
    ACCESS read-write
    STATUS mandatory
    DESCRIPTION
    "This object is also referred to as RDL Auto Timeout.
    When enabled (tenMinutes), the loopback will be automatically terminated
    by the unit after ten minutes.  When disabled, the loopback must be
    terminated by an in-band loopdown code."
    ::= { sc5553ConfigEntry 13}


sc5553WakeUpRemote OBJECT-TYPE
	SYNTAX	  DisplayString (SIZE (16))
	ACCESS	  read-only
	STATUS	  mandatory
	DESCRIPTION
	"This object is requested to initiate the add remote process. The serial number
         of the associated remote is returned." 
	::= { sc5553ConfigEntry 14}






--
-- ****************************************************************************
--                      DTE Signal Status table
-- ****************************************************************************



sc5553SignalStatusTable OBJECT-TYPE
    SYNTAX SEQUENCE OF Sc5553SignalStatusEntry
    ACCESS not-accessible
    STATUS mandatory
    DESCRIPTION
    "The sc5553 DTE Signal Status table. Information in the
    entries of this table define the status of DSU channel
    interface leads.  There are entries in this table for each
    channel of the associated DSU."
    ::= { sc5553DTEsignalStat 1 }


sc5553SignalStatusEntry OBJECT-TYPE
    SYNTAX Sc5553SignalStatusEntry
    ACCESS not-accessible
    STATUS mandatory
    DESCRIPTION
    "The sc5553 DTE Signal Status table entry."
    INDEX { sc5553SignalStatusIndex }
    ::= { sc5553SignalStatusTable 1 }


Sc5553SignalStatusEntry ::=
    SEQUENCE {
        sc5553SignalStatusIndex SCinstance,
        sc5553CTSstatus        INTEGER,
        sc5553RTSstatus        INTEGER,
        sc5553DTRstatus        INTEGER,
        sc5553DSRstatus        INTEGER,
        sc5553DCDstatus        INTEGER,
        sc5553RXCstatus        INTEGER,
        sc5553TXCstatus        INTEGER,
        sc5553RXDstatus        INTEGER,
        sc5553TXDstatus        INTEGER,
        sc5553ALTestLeadStatus INTEGER,
        sc5553RLTestLeadStatus INTEGER
    }


sc5553SignalStatusIndex OBJECT-TYPE
    SYNTAX SCinstance
    ACCESS read-only
    STATUS mandatory
    DESCRIPTION
    "The index value: slot, line, drop, and interface"
    ::= { sc5553SignalStatusEntry 1 }


sc5553CTSstatus OBJECT-TYPE
    SYNTAX INTEGER
    {
    	off(1),	          -- CTS is off
    	on(2),	          -- CTS is on
    	transitions(3)    -- CTS is transitioning
    }
    ACCESS read-only
    STATUS mandatory
    DESCRIPTION
    "The state of the sc5553's Clear To Send (CTS) signal.
    The value transitions(3) indicates that the signal is
    alternating between the states off(1) and on(2)."
    ::= { sc5553SignalStatusEntry 2 }


sc5553RTSstatus OBJECT-TYPE
    SYNTAX INTEGER
    {
    	off(1),	          -- RTS is off
    	on(2),	          -- RTS is on
    	transitions(3)    -- RTS is transitioning
    }
    ACCESS read-only
    STATUS mandatory
    DESCRIPTION
    "The state of the sc5553's Request To Send (RTS) signal.
    The value transitions(3) indicates that the signal is
    alternating between the states off(1) and on(2)."
    ::= { sc5553SignalStatusEntry 3 }


sc5553DTRstatus OBJECT-TYPE
    SYNTAX INTEGER
    {
    	off(1),	   -- DTR is off
    	on(2)      -- DTR is on
    }
    ACCESS read-only
    STATUS mandatory
    DESCRIPTION
    "The state of the sc5553's Data Terminal Ready (DTR) signal."
    ::= { sc5553SignalStatusEntry 4 }


sc5553DSRstatus OBJECT-TYPE
    SYNTAX INTEGER 
    {
    	off(1),	  -- DSR is off
    	on(2)     -- DSR is on
    }
    ACCESS read-only
    STATUS mandatory
    DESCRIPTION
    "The state of the sc5553's Data Set Ready (DSR) signal."
    ::= { sc5553SignalStatusEntry 5 }


sc5553DCDstatus OBJECT-TYPE
    SYNTAX INTEGER
    {
    	off(1),           -- DCD is off
    	on(2),            -- DCD is on
    	transitions(3)    -- DCD is transitioning
    }
    ACCESS read-only
    STATUS mandatory
    DESCRIPTION
    "The state of the sc5553's Data Carrier Detect (DCD)
    signal. The value transitions(3) indicates that the signal
    is alternating between the states off(1) and on(2)."
    ::= { sc5553SignalStatusEntry 6 }


sc5553RXCstatus OBJECT-TYPE
    SYNTAX INTEGER
    {
    	off(1),	          -- RXC is off
    	transitions(2)    -- RXC is transitioning
    }
    ACCESS read-only
    STATUS mandatory
    DESCRIPTION
    "The state of the sc5553's receive clock (RXC) signal.
    The value transitions(2) indicates that the signal
    is alternating between states off(1) and on(2)."
    ::= { sc5553SignalStatusEntry 7 }


sc5553TXCstatus OBJECT-TYPE
    SYNTAX INTEGER
    {
    	off(1),	          -- TXC is off
    	transitions(2)    -- TXC is transitioning
    }
    ACCESS read-only
    STATUS mandatory
    DESCRIPTION
    "The state of the sc5553's Transmit Clock (TXC) signal.
    The value transitions(2) indicates that the signal is
    alternating between states off(1) and on(2)."
    ::= { sc5553SignalStatusEntry 8 }


sc5553RXDstatus OBJECT-TYPE
    SYNTAX INTEGER
    {
    	space(1),          -- RXD is on
    	mark(2),           -- RXD is off
    	transitions(3)     -- RXD is transitioning
    }
    ACCESS read-only
    STATUS mandatory
    DESCRIPTION
    "The state of the sc5553's Receive Data (RXD) signal."
    ::= { sc5553SignalStatusEntry 9 }


sc5553TXDstatus OBJECT-TYPE
    SYNTAX INTEGER
    {
    	space(1),          -- TXD is on
    	mark(2),           -- TXD is off
    	transitions(3)     -- TXD is transitioning
    }
    ACCESS read-only
    STATUS mandatory
    DESCRIPTION
    "The state of the sc5553's Transmit Data (TXD) signal."
    ::= { sc5553SignalStatusEntry 10 }


sc5553ALTestLeadStatus OBJECT-TYPE
    SYNTAX INTEGER 
    {
    	off(1),
    	on(2)
    }
    ACCESS read-only
    STATUS mandatory
    DESCRIPTION
    "Sets state of the AL Test lead."
    ::= { sc5553SignalStatusEntry 11 }


sc5553RLTestLeadStatus OBJECT-TYPE
    SYNTAX INTEGER 
    {
    	off(1),
    	on(2)
    }
    ACCESS read-only
    STATUS mandatory
    DESCRIPTION
    "Sets state of the RL Test lead."
    ::= { sc5553SignalStatusEntry 12 }



--
-- ****************************************************************************
--                        Diagnostics table
-- ****************************************************************************

sc5553DiagTable OBJECT-TYPE
    SYNTAX SEQUENCE OF Sc5553DiagEntry
    ACCESS not-accessible
    STATUS mandatory
    DESCRIPTION
    "The SC5553 Diagnostics Table." 
    ::= { sc5553Diagnostics 1 }

sc5553DiagEntry OBJECT-TYPE
    SYNTAX Sc5553DiagEntry
    ACCESS not-accessible
    STATUS mandatory
    DESCRIPTION
    "The SC5553 Diagnostics entry."
    INDEX { sc5553DiagIndex }
    ::= { sc5553DiagTable 1 }


Sc5553DiagEntry ::= 
    SEQUENCE {
        sc5553DiagIndex SCinstance,
        sc5553DiagPattern INTEGER,
        sc5553DiagTestResults INTEGER,
        sc5553DiagTestDuration INTEGER,
        sc5553DiagTestSelection INTEGER
    }

sc5553DiagIndex OBJECT-TYPE
    SYNTAX SCinstance
    ACCESS read-only
    STATUS mandatory
    DESCRIPTION
    "The index value: slot, line, drop, and interface"
    ::= { sc5553DiagEntry 1 }

sc5553DiagPattern OBJECT-TYPE
    SYNTAX INTEGER {
    	send511Pattern(1),		-- sending 511  test pattern only
    	send2047Pattern(2)		-- sending 2047 test pattern only
    }
    ACCESS read-write
    STATUS mandatory
    DESCRIPTION
    "Selects the test pattern for Remote and Local loopback tests."
    ::= { sc5553DiagEntry 2 }


sc5553DiagTestResults OBJECT-TYPE
    SYNTAX INTEGER
    ACCESS read-only
    STATUS mandatory
    DESCRIPTION
    "The results of the last diagnostic test. This can be the
    current test running or the last completed test.

    The units of the value of this object depend on the type of
    diagnostic test run.  For all cases except a network delay
    measurement, the units of the value of this object is the
    number of bit errors that occurred. Bit errors can be read at any
    time during the duration of the test.  The valid range for bit
    errors is 0 to 4,095.  65,535 will be returned if for any reason
    the test was terminated early.  32,770 will be returned if the
    number of bit errors exceeds 4,095. For a network delay measurement,
    the units of the value of this test are milliseconds.  If the test
    is terminated early than 65,535 will be returned and if the delay
    is greater than 4,095 milliseconds then 32,770 will be returned."
    ::= { sc5553DiagEntry 3 }

sc5553DiagTestDuration OBJECT-TYPE
     SYNTAX INTEGER {
        testTime30Secs(15),
        testTime1Min(1),
        testTime2Mins(2),
        testTime3Mins(3),
        testTime4Mins(4),
        testTime5Mins(5),
        testTime6Mins(6),
        testTime7Mins(7),
        testTime8Mins(8),
        testTime9Mins(9),
        testTime10Mins(10),
        testTime15Mins(11),
        testTime20Mins(12),
        testTime25Mins(13),
        testTime30Mins(14)
    }  
    ACCESS read-write
    STATUS mandatory
    DESCRIPTION
    "This specifies the test duration for the Remote and Local
    loopback tests."
    ::= { sc5553DiagEntry 4 }

sc5553DiagTestSelection OBJECT-TYPE
    SYNTAX INTEGER {
	 stopTestorNoTest(1),           -- A test is not running
         localloop(2),                  -- LocalLoopback test is running
         localloopselftest(3),          -- LocalLoopback with Self Test
                                        -- is running
	 digitalLoop(4),   		-- DigitalLoopback test is running
	 remoteloop(5),  		-- RemoteLoopback test is running
	 remoteloopselftest(6),         -- RemoteLoopback with Self Test
                                        -- is running
         networkdelay(7)                -- Network delay test is running
    }
    ACCESS read-write
    STATUS mandatory
    DESCRIPTION

    "To halt the execution of any and all diagnostic tests that may be
    running, SET this object to stopTestorNoTest(1).

    LocalLoopBack:
    To initiate a LocalLoopBack with no SelfTest, SET this object to
    localloop(2). Data from the DTE will be looped back to itself. 
    This loopback can be terminated by sending stopTestorNoTest(1).

    LocalLoopBack with SelfTest:
    To initiate a LocalLoopBack SelfTest, SET this object to
    localloopselftest(3).  The pattern specified in sc5553DiagPattern
    will be sent and checked for bit errors.  The test will run for the 
    time specified in sc5553DiagTestDuration, unless terminated by sending 
    stopTestorNoTest(1).  Test results can be checked by reading the
    sc5553DiagTestResults object.

    DigitalLoopback:
    To initiate a DigitalLoopback test SET this object to digitalLoop(4). 
    This will allow the data from the DTE attached to the far end unit
    (nms553) to be looped back to itself. This loopback can be terminated
    by sending stopTestorNoTest(1).

    RemoteLoopback:
    To initiate a RemoteLoopback test with no SelfTest, SET this object to
    remoteloop(5). The sc5553 DSE transmits an in-band command to
    its remote DSU, directing the remote to loop received signals back to
    the network. The DSE is configurable to send (and accept) a PN127
    remote loop command. The remote DSU must be configured to accept
    the same command the DSE transmits.  This loopback can be terminated
    by sending stopTestorNoTest(1).

    RemoteLoopback with SelfTest:
    To initiate a RemoteLoopback with SelfTest SET this object to 
    remoteloopselftest(6). The remote unit will go into remoteloopback and
    the master (sc5553) unit will go into Selftest. The sc5553 transmits an
    in-band command to its remote DSU, directing the remote to loop received
    signals back onto the network. The DSE is configurable to send
    (and accept) a PN127 remote loop command.  The remote DSU must be
    configured to accept the same command the DSE transmits. The sc5553
    enables its internal Test Pattern Generator to provide the signal for
    the Remote Loop and enables the Pattern Generator to verify the signal.
    The pattern specified in sc5553DiagPattern will be sent for this test.
    The test will run for the time specified in sc5553DiagTestDuration,
    unless terminated by sending stopTestorNoTest(1).  Test results can be checked
    by reading the sc5553DiagTestResults object.

    Network Delay:
    To initiate a Network Delay Test SET this object to networkdelay(7).
    The results are valid only after the test is completed which takes about
    10 seconds.  Network Delay Time can be checked by reading the sc5553DiagTestResults 
    object after completion of the test.

    For a GET, the value stopTestorNoTest(1) indicates there are no active 
    diagnostic tests currently running.  Any other value indicates which 
    test is currently active."
    ::= { sc5553DiagEntry 5 }

--
-- ****************************************************************************
--                        Maintenance Table
-- ****************************************************************************


sc5553MaintTable OBJECT-TYPE
    SYNTAX SEQUENCE OF Sc5553MaintEntry
    ACCESS not-accessible
    STATUS mandatory
    DESCRIPTION
    "The table describes the maintenance functions for the sc5553. "
    ::= { sc5553Maintenance 1 }


sc5553MaintEntry OBJECT-TYPE
    SYNTAX Sc5553MaintEntry
    ACCESS not-accessible
    STATUS mandatory
    DESCRIPTION
    "An entry in the GDC maintenance Table"
    INDEX { sc5553MaintIndex }
    ::= { sc5553MaintTable 1 }


Sc5553MaintEntry ::=
SEQUENCE {
	sc5553MaintIndex            SCinstance,
	sc5553LedStatus             OCTET STRING,
	sc5553SoftReset             INTEGER,
	sc5553FrontPanel            INTEGER,
	sc5553DefaultInit           INTEGER
    }


sc5553MaintIndex OBJECT-TYPE
    SYNTAX SCinstance
    ACCESS read-only
    STATUS mandatory
    DESCRIPTION
     "The index value: slot, line, drop, and interface"
    ::= { sc5553MaintEntry 1 }


sc5553LedStatus OBJECT-TYPE
    SYNTAX OCTET STRING (SIZE(4))
    ACCESS read-only
    STATUS mandatory
    DESCRIPTION
   "Returns a bitwise snapshot of the front panel LED state and front panel switches.
 		Octet 1 bit 7 - not used
				bit 6 - ON
				bit 5 - INSV
				bit 4 - RSP
				bit 3 - TMG
				bit 2 - future use
				bit 1 - future use
				bit 0 - future use
		Octet 2 bit 7 - not used
				bit 6 - SD transitions
				bit 5 - SD on/off
				bit 4 - RD transitions
				bit 3 - RD on/off
				bit 2 - RS transitions
				bit 1 - RS on/off
				bit 0 - future use
		Octet 3 bit 7 - not used
				bit 6 - CO transitions
				bit 5 - CO on/off
				bit 4 - ALM transitions
				bit 3 - ALM on/off
				bit 2 - TM transitions
				bit 1 - TM on/off
				bit 0 - future use
		Octet 4 bit 7 - not used
				bit 6 - ST (switch)
				bit 5 - LT (switch)
				bit 4 - RL (switch)
				bit 3 - DL (switch)
				bit 2 - future use
				bit 1 - future use
				bit 0 - future use"
    ::= { sc5553MaintEntry 2 }


sc5553SoftReset	OBJECT-TYPE
     SYNTAX INTEGER
     {
          reset(1),			-- write-only
          norm(2)           		-- read-only
     }
     ACCESS read-write
     STATUS mandatory
     DESCRIPTION
     "Supports the action of soft resetting the unit.  When this
     object is set to reset(1), then the unit performs a soft reset.
     The value norm will be returned when the reset is complete.
     The value of norm can not be set by management."
     ::= { sc5553MaintEntry 3 }


sc5553FrontPanel OBJECT-TYPE
     SYNTAX INTEGER
     {
         inhibit(1),
         enable(2)
     }
     ACCESS read-write
     STATUS mandatory
     DESCRIPTION
     "This variable is used to indicate whether the front
     panel switches are operational or not."
     ::= { sc5553MaintEntry 4 }


sc5553DefaultInit OBJECT-TYPE
     SYNTAX INTEGER
     {
         factoryDefault(1),		-- write-only
         normal(2)			-- read-only
     }
     ACCESS read-write
     STATUS mandatory
     DESCRIPTION
     "This is used to allow the NonVolatile Configuration to be set to
     a factory default state.  When this value is set to factoryDefault,
     the unit will reset to the default configuration. The value of normal
     will be returned when the initialization is complete. The value normal
     can not be set by management."
     ::= { sc5553MaintEntry 5 }


--
-- ****************************************************************************
--                 Alarm Object Identifier Definitions
-- ****************************************************************************

sc5553AlarmData	              OBJECT IDENTIFIER ::= { sc5553Alarms 1 }

sc5553NoResponseAlm           OBJECT IDENTIFIER ::= { sc5553AlarmData 1 }

sc5553DiagRxErrAlm            OBJECT IDENTIFIER ::= { sc5553AlarmData 2 }

sc5553PowerUpAlm              OBJECT IDENTIFIER ::= { sc5553AlarmData 3 }

sc5553DTRLossAlarm            OBJECT IDENTIFIER ::= { sc5553AlarmData 4 }

sc5553DSRLossAlarm            OBJECT IDENTIFIER ::= { sc5553AlarmData 5 }

sc5553DCDLossAlarm            OBJECT IDENTIFIER ::= { sc5553AlarmData 6 }

sc5553TxCLossAlarm            OBJECT IDENTIFIER ::= { sc5553AlarmData 7 }

sc5553TimingLoss              OBJECT IDENTIFIER ::= { sc5553AlarmData 8 }

sc5553EEPROMCheckAlarm        OBJECT IDENTIFIER ::= { sc5553AlarmData 9 }

sc5553EIATestAlarm            OBJECT IDENTIFIER ::= { sc5553AlarmData 10 }

sc5553FrontPanelTestAlarm     OBJECT IDENTIFIER ::= { sc5553AlarmData 11 }

sc5553TxDNoTransAlarm         OBJECT IDENTIFIER ::= { sc5553AlarmData 12 }

sc5553RxDNoTransAlarm         OBJECT IDENTIFIER ::= { sc5553AlarmData 13 }


END
