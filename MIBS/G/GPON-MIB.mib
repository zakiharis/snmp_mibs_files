------------------------------------------------------------------------------
--
--  File           : GPON-MIB.mi2
--  Description    : gpon configuration MIB
--  Version        : 1.0
--  Date           : Dec 3, 2007
--  Author         : Kevin
--  Copyright (c) 2007-2010 zyxel Systems, Inc.  All Rights Reserved.
--
------------------------------------------------------------------------------

GPON-MIB DEFINITIONS ::= BEGIN

IMPORTS
    MODULE-IDENTITY, OBJECT-TYPE,
    NOTIFICATION-TYPE,
    enterprises, IpAddress              FROM SNMPv2-SMI

    RowStatus, TruthValue,
--  DisplayString, MacAddress, IpAddress	FROM SNMPv2-TC;
    DisplayString, MacAddress	FROM SNMPv2-TC;
--  ifIndex, mib-2                          FROM RFC1213-MIB;
    zyxel MODULE-IDENTITY
        LAST-UPDATED    "200712050000Z"  -- Dec 5, 2000
        ORGANIZATION    "zyxel Systems, Inc."
        CONTACT-INFO    "zyxel Systems, Inc.
                         E-mail: support@zyxel.com.cn"

        DESCRIPTION     "ZYXEL Master MIB OID defines and documentation."

        REVISION        "200712050000Z"  -- Dec 5, 2000
        DESCRIPTION     "Initial MIB creation."
    	::= { enterprises 13464 }

--ZYXEL Products
datacom		OBJECT IDENTIFIER ::= { zyxel 1 }

-- DataCom Products
gpon		OBJECT IDENTIFIER ::= {datacom 11}

--gpon funtion
slot		OBJECT IDENTIFIER ::= { gpon 1 }
olt		OBJECT IDENTIFIER ::= { gpon 2 }
pon		OBJECT IDENTIFIER ::= { gpon 3 }
ont             OBJECT IDENTIFIER ::= { gpon 4 }
dba		OBJECT IDENTIFIER ::= { gpon 5 }
ontSip	        OBJECT IDENTIFIER ::= { gpon 6 }
oltPower        OBJECT IDENTIFIER ::= { gpon 7 }
--
-- slot table
--
slotTable 	OBJECT-TYPE
	SYNTAX  SEQUENCE OF SlotEntry
	MAX-ACCESS  not-accessible
	STATUS  current
	DESCRIPTION
		"slot table"
	::= {slot 1}

slotEntry	OBJECT-TYPE
	SYNTAX	 	SlotEntry
	MAX-ACCESS  not-accessible
	STATUS		current
	DESCRIPTION
		"OltEntry table"
	INDEX	{ slotIndex }
	::= { slotTable 1 }

SlotEntry	::= SEQUENCE {
		slotIndex               INTEGER(0..5),
		slotState               INTEGER(0..11),
		slotConfigType          INTEGER(0..11),
		slotTrueType	        INTEGER(0..11),
		slotHwVersion	        OCTET STRING (SIZE(0..255)),
		slotReset	        INTEGER(0..1)
}

slotIndex	OBJECT-TYPE
	SYNTAX	 	INTEGER(0..5)
	MAX-ACCESS  read-only
	STATUS		current
	DESCRIPTION
		"slotIndex, epon slot index rang is 0 to 5"
	::= { slotEntry 1 }

slotState	OBJECT-TYPE
	SYNTAX	 	INTEGER(0..10)
	MAX-ACCESS  read-only
	STATUS		current
	DESCRIPTION
	"typedef enum
	{
		STATUS_DOWN = 0,
		STATUS_INIT,
		STATUS_LOAD,
		STATUS_REG,
		STATUS_CONFIG,
		STATUS_ONLINE
	}SLOT_STATUS_ENUM;"
	::= { slotEntry 2 }
	
slotConfigType	OBJECT-TYPE
	SYNTAX	 	INTEGER(0..10)
	MAX-ACCESS  read-write
	STATUS		current
	DESCRIPTION
	"typedef enum tag_BOARD_TYPE
	{
		BOARD_TYPE_NULL = 0,
		BOARD_TYPE_CONTROL_BCM5670,
		BOARD_TYPE_LINE_24_GE_FIBER_BCM56504,
		BOARD_TYPE_LINE_24_GE_COPPER_BCM56504,
		BOARD_TYPE_LINE_24_GE_COPPER_BCM56524,    
		BOARD_TYPE_LINE_8_10GE_FIBER_BCM56820,
		BOARD_TYPE_LINE_8PON_6GE_BCM56524,
		BOARD_TYPE_CONTROL_BCM56720,  
		BOARD_TYPE_LINE_8GPON_8GE_BCM56684,
		BOARD_TYPE_LINE_4pon_4_10GE_BCM56821,
		BOARD_TYPE_NUM
	}BOARD_TYPE;
	"
	::= { slotEntry 3 }

slotTrueType	OBJECT-TYPE
	SYNTAX	 	INTEGER(0..10)
	MAX-ACCESS  read-only
	STATUS		current
	DESCRIPTION
	"typedef enum tag_BOARD_TYPE
	{
		BOARD_TYPE_NULL = 0,
		BOARD_TYPE_CONTROL_BCM5670,
		BOARD_TYPE_LINE_24_GE_FIBER_BCM56504,
		BOARD_TYPE_LINE_24_GE_COPPER_BCM56504,
		BOARD_TYPE_LINE_24_GE_COPPER_BCM56524,    
		BOARD_TYPE_LINE_8_10GE_FIBER_BCM56820,
		BOARD_TYPE_LINE_8PON_6GE_BCM56524,
		BOARD_TYPE_CONTROL_BCM56720,  
		BOARD_TYPE_LINE_8GPON_8GE_BCM56684,
		BOARD_TYPE_LINE_4pon_4_10GE_BCM56821,
		BOARD_TYPE_NUM
	}BOARD_TYPE;"
	::= { slotEntry 4 }
	
slotHwVersion	OBJECT-TYPE
	SYNTAX	 	OCTET STRING (SIZE(0..255))
	MAX-ACCESS  read-only
	STATUS		current
	DESCRIPTION
	"slotHwVersion"
	::= { slotEntry 5 }
	
slotReset	OBJECT-TYPE
	SYNTAX	 	INTEGER(0..1)
	MAX-ACCESS  read-write
	STATUS		current
	DESCRIPTION
		"slotReset"
	::= { slotEntry 6 }
	
--
-- olt table
--
oltTable 	OBJECT-TYPE
	SYNTAX  SEQUENCE OF OltEntry
	MAX-ACCESS  not-accessible
	STATUS  current
	DESCRIPTION
		"olt table"
	::= {olt 1}

oltEntry	OBJECT-TYPE
	SYNTAX	 	OltEntry
	MAX-ACCESS  not-accessible
	STATUS		current
	DESCRIPTION
		"oltEntry table"
	INDEX	{ oltIndex }
	::= { oltTable 1 }

OltEntry	::= SEQUENCE {
		oltIndex                INTEGER(1..5),
		oltValid                INTEGER (0..1),
		oltSlot                 INTEGER(1..5),
		oltMac                  MacAddress,
		oltSoftVersion	        OCTET STRING (SIZE(0..255)),
		oltHwVersion            OCTET STRING (SIZE(0..255))
}

oltIndex	OBJECT-TYPE
	SYNTAX	 	INTEGER(0..5)
	MAX-ACCESS  read-only
	STATUS		current
	DESCRIPTION
		"oltIndex, gpon olt index rang is 0 to 3"
	::= { oltEntry 1 }

oltValid	OBJECT-TYPE
	SYNTAX	 	INTEGER (0..1)
	MAX-ACCESS  read-only
	STATUS		current
	DESCRIPTION
		"olt valid
		 valid = 0 -- the olt device is not in the slot of oltIndex
		 valid = 1 -- the olt device is in the slot of oltIndex, and is register"
	::= {oltEntry 2}

oltSlot	OBJECT-TYPE
	SYNTAX	 	INTEGER(1..5)
	MAX-ACCESS  read-only
	STATUS		current
	DESCRIPTION
		"olt slot index, gpon olt index rang is 2 to 5"
	::= {oltEntry 3}
oltMac	OBJECT-TYPE
	SYNTAX	 	MacAddress
	MAX-ACCESS  read-only
	STATUS		current
	DESCRIPTION
		"olt mac address"
	::= {oltEntry 4}

oltSoftVersion	OBJECT-TYPE
	SYNTAX	 	OCTET STRING (SIZE(0..255))
	MAX-ACCESS  read-only
	STATUS		current
	DESCRIPTION
		"olt software version"
	::= {oltEntry 5}

oltHwVersion	OBJECT-TYPE
	SYNTAX	 	OCTET STRING (SIZE(0..255))
	MAX-ACCESS  read-only
	STATUS		current
	DESCRIPTION
		"olt hardware version"
	::= {oltEntry 6}

--
-- pon table
--

-- pon 1
ponTable 	OBJECT-TYPE
	SYNTAX  SEQUENCE OF PonEntry
	MAX-ACCESS  not-accessible
	STATUS  current
	DESCRIPTION
		"pon table"
	::= {pon 1}

ponEntry	OBJECT-TYPE
	SYNTAX	 	PonEntry
	MAX-ACCESS  not-accessible
	STATUS		current
	DESCRIPTION
		"ponEntry table"
	INDEX	{ oltIndex, ponIndex }
	::= {ponTable 1}

PonEntry	::=
	SEQUENCE
	{
		ponIndex                   INTEGER (1..8),
		ponValid                   INTEGER (1..2),
		ontAutoFindValid           INTEGER (0..1),
		ontAutoAuthValid           INTEGER (0..1),
		ontAutoFindIntervalTime    INTEGER (500..42949672),
		ontResponseTime            INTEGER (0..10000),
		ponPortLinkStatus          INTEGER (1..2),
		ontNoConfigAll             INTEGER (0..1),
		ontAutoConfigAll           INTEGER (0..1),
		ponTransceiverType                OCTET STRING (SIZE(0..255)),
		ponCompliance                     OCTET STRING (SIZE(0..255)),
		ponConnectorType                  OCTET STRING (SIZE(0..255)),
		ponWaveLength                     OCTET STRING (SIZE(0..255)),
		ponTransferDistance               OCTET STRING (SIZE(0..255)),
		ponDigitalDiagnosticMonitoring    OCTET STRING (SIZE(0..255)),
		ponManufacturingSerialNumber      OCTET STRING (SIZE(0..255)),
		ponManufacturingDate              OCTET STRING (SIZE(0..255)),
		ponVendorName                     OCTET STRING (SIZE(0..255)),
		ponTemperature                    OCTET STRING (SIZE(0..255)),
		ponVoltage                        OCTET STRING (SIZE(0..255)),
		ponBiasCurrent                    OCTET STRING (SIZE(0..255)),
		ponBiasHighThreshold              OCTET STRING (SIZE(0..255)),
		ponBiasLowThreshold               OCTET STRING (SIZE(0..255)),
		ponRXPower                        OCTET STRING (SIZE(0..255)),
		ponRXPowerHighThreshold           OCTET STRING (SIZE(0..255)),
		ponRXPowerLowThreshold            OCTET STRING (SIZE(0..255)),
		ponTXPower                        OCTET STRING (SIZE(0..255)),
		ponTXPowerHighThreshold           OCTET STRING (SIZE(0..255)),
		ponTXPowerLowThreshold            OCTET STRING (SIZE(0..255)),
		ontNoSNAll                        INTEGER (0..1)
	}

ponIndex	OBJECT-TYPE
	SYNTAX	 	INTEGER (1..8)
	MAX-ACCESS  read-only
	STATUS		current
	DESCRIPTION
		"ponIndex"
	::= {ponEntry 1}

ponValid	OBJECT-TYPE
	SYNTAX	 	INTEGER (1..2)
	MAX-ACCESS  read-write
	STATUS		current
	DESCRIPTION
		"
        GPON_PORT_OPER_DOWN = 1,
        GPON_PORT_OPER_UP = 2,
	  "
	::= {ponEntry 2}
	
ontAutoFindValid	OBJECT-TYPE
	SYNTAX	 	INTEGER (1..2)
	MAX-ACCESS  read-write
	STATUS		current
	DESCRIPTION
		"ont-auto-find_enable = 1,
		 ont-auto-find_disbale = 0,
		"
	::= {ponEntry 3}
	
ontAutoAuthValid	OBJECT-TYPE
	SYNTAX	 	INTEGER (1..2)
	MAX-ACCESS  read-write
	STATUS		current
	DESCRIPTION
		"ont-auto-auth_enable = 1,
		 ont-auto-auth_disable =0,
		"
	::= {ponEntry 4}

ontAutoFindIntervalTime	OBJECT-TYPE
	SYNTAX	 	INTEGER (500..42949672)
	MAX-ACCESS  read-write
	STATUS		current
	DESCRIPTION
		"ontAutoFindIntervalTime_default = 3000 "
	::= {ponEntry 5}

ontResponseTime	OBJECT-TYPE
	SYNTAX	 	INTEGER (0..10000)
	MAX-ACCESS  read-write
	STATUS		current
	DESCRIPTION
		"min-ont-response-time_defualt = 10 "
	::= {ponEntry 6}
	
ponPortLinkStatus	OBJECT-TYPE
	SYNTAX	 	INTEGER (1..2)
	MAX-ACCESS  read-only
	STATUS		current
	DESCRIPTION
	"ponPortLinkDown=1
	 ponPortLinkUp=2"
	::= {ponEntry 7}

ontNoConfigAll    OBJECT-TYPE
	SYNTAX	 	INTEGER (0..1)
	MAX-ACCESS  read-write
	STATUS		current
	DESCRIPTION
	"No ontConfig_all = 1"
	::= {ponEntry 8}

ontAutoConfigAll    OBJECT-TYPE
	SYNTAX	 	INTEGER (0..1)
	MAX-ACCESS  read-write
	STATUS		current
	DESCRIPTION
	"save ont-auto-config = 1
     no   ont-auto-config = 0"
	::= {ponEntry 9}

ponTransceiverType    OBJECT-TYPE
	SYNTAX	 	OCTET STRING (SIZE(0..255))
	MAX-ACCESS  read-only
	STATUS		current
	DESCRIPTION
	"ponTransceiverType"
	::= {ponEntry 10}
	
ponCompliance    OBJECT-TYPE
	SYNTAX	 	OCTET STRING (SIZE(0..255))
	MAX-ACCESS  read-only
	STATUS		current
	DESCRIPTION
	"ponCompliance"
	::= {ponEntry 11}

ponConnectorType    OBJECT-TYPE
	SYNTAX	 	OCTET STRING (SIZE(0..255))
	MAX-ACCESS  read-only
	STATUS		current
	DESCRIPTION
	"ponTransceiverType"
	::= {ponEntry 12}
	
ponWaveLength    OBJECT-TYPE
	SYNTAX	 	OCTET STRING (SIZE(0..255))
	MAX-ACCESS  read-only
	STATUS		current
	DESCRIPTION
	"unit: nm "
	::= {ponEntry 13}
	
ponTransferDistance    OBJECT-TYPE
	SYNTAX	 	OCTET STRING (SIZE(0..255))
	MAX-ACCESS  read-only
	STATUS		current
	DESCRIPTION
	"unit: m "
	::= {ponEntry 14}
	
ponDigitalDiagnosticMonitoring    OBJECT-TYPE
	SYNTAX	 	OCTET STRING (SIZE(0..255))
	MAX-ACCESS  read-only
	STATUS		current
	DESCRIPTION
	"ponDigitalDiagnosticMonitoring"
	::= {ponEntry 15}
	
ponManufacturingSerialNumber    OBJECT-TYPE
	SYNTAX	 	OCTET STRING (SIZE(0..255))
	MAX-ACCESS  read-only
	STATUS		current
	DESCRIPTION
	"ponManufacturingSerialNumber"
	::= {ponEntry 16}
	
ponManufacturingDate    OBJECT-TYPE
	SYNTAX	 	OCTET STRING (SIZE(0..255))
	MAX-ACCESS  read-only
	STATUS		current
	DESCRIPTION
	"year-month-day"
	::= {ponEntry 17}
	
ponVendorName    OBJECT-TYPE
	SYNTAX	 	OCTET STRING (SIZE(0..255))
	MAX-ACCESS  read-only
	STATUS		current
	DESCRIPTION
	"ponVendorName"
	::= {ponEntry 18}
	
ponTemperature    OBJECT-TYPE
	SYNTAX	 	OCTET STRING (SIZE(0..255))
	MAX-ACCESS  read-only
	STATUS		current
	DESCRIPTION
	"unit: C "
	::= {ponEntry 19}
	
ponVoltage    OBJECT-TYPE
	SYNTAX	 	OCTET STRING (SIZE(0..255))
	MAX-ACCESS  read-only
	STATUS		current
	DESCRIPTION
	"unit: V "
	::= {ponEntry 20}
	
ponBiasCurrent    OBJECT-TYPE
	SYNTAX	 	OCTET STRING (SIZE(0..255))
	MAX-ACCESS  read-only
	STATUS		current
	DESCRIPTION
	"unit: mA "
	::= {ponEntry 21}
	
ponBiasHighThreshold    OBJECT-TYPE
	SYNTAX	 	OCTET STRING (SIZE(0..255))
	MAX-ACCESS  read-only
	STATUS		current
	DESCRIPTION
	"unit: mA "
	::= {ponEntry 22}
	
ponBiasLowThreshold    OBJECT-TYPE
	SYNTAX	 	OCTET STRING (SIZE(0..255))
	MAX-ACCESS  read-only
	STATUS		current
	DESCRIPTION
	"unit: mA "
	::= {ponEntry 23}
	
ponRXPower    OBJECT-TYPE
	SYNTAX	 	OCTET STRING (SIZE(0..255))
	MAX-ACCESS  read-only
	STATUS		current
	DESCRIPTION
	"unit: dBm "
	::= {ponEntry 24}
	
ponRXPowerHighThreshold    OBJECT-TYPE
	SYNTAX	 	OCTET STRING (SIZE(0..255))
	MAX-ACCESS  read-only
	STATUS		current
	DESCRIPTION
	"unit: dBm "
	::= {ponEntry 25}
	
ponRXPowerLowThreshold    OBJECT-TYPE
	SYNTAX	 	OCTET STRING (SIZE(0..255))
	MAX-ACCESS  read-only
	STATUS		current
	DESCRIPTION
	"unit: dBm "
	::= {ponEntry 26}
	
ponTXPower    OBJECT-TYPE
	SYNTAX	 	OCTET STRING (SIZE(0..255))
	MAX-ACCESS  read-only
	STATUS		current
	DESCRIPTION
	"unit: dBm "
	::= {ponEntry 27}
	
ponTXPowerHighThreshold    OBJECT-TYPE
	SYNTAX	 	OCTET STRING (SIZE(0..255))
	MAX-ACCESS  read-only
	STATUS		current
	DESCRIPTION
	"unit: dBm "
	::= {ponEntry 28}
	
ponTXPowerLowThreshold    OBJECT-TYPE
	SYNTAX	 	OCTET STRING (SIZE(0..255))
	MAX-ACCESS  read-only
	STATUS		current
	DESCRIPTION
	"unit: dBm "
	::= {ponEntry 29}

ontNoSNAll    OBJECT-TYPE
	SYNTAX	 	INTEGER (0..1)
	MAX-ACCESS  read-write
	STATUS		current
	DESCRIPTION
	"No ontNoSN_all = 1"
	::= {ponEntry 30}
	
-- pon 2 
copyOntConfigTable OBJECT-IDENTITY
      STATUS current
      DESCRIPTION 
        ""
      ::= { pon 2}     
      
copyOntConfigEntry OBJECT IDENTIFIER ::= { copyOntConfigTable 1 }  
	
CopyOntConfigEntry	::=
	SEQUENCE
	{
        ponSrc                   OCTET STRING (SIZE(0..255)),
        ponDes                   OCTET STRING (SIZE(0..255)),
        ponCopyOntConfigRowstatus     RowStatus
    }

ponSrc	OBJECT-TYPE
	SYNTAX	 	OCTET STRING (SIZE(0..255))
	MAX-ACCESS  read-write
	STATUS		current
	DESCRIPTION
		"Source port:
		eg 0/1,2/1"
	::= {copyOntConfigEntry 1}

ponDes	OBJECT-TYPE
	SYNTAX	 	OCTET STRING (SIZE(0..255))
	MAX-ACCESS  read-write
	STATUS		current
	DESCRIPTION
		"Destination port:
		eg 0/2,2/2
		
		Destination port should not have ont configure!"
	::= {copyOntConfigEntry 2}
	
ponCopyOntConfigRowstatus	OBJECT-TYPE
	SYNTAX	 	RowStatus
	MAX-ACCESS  read-write
	STATUS		current
	DESCRIPTION
		"RowStatus"
	::= {copyOntConfigEntry 3}


--
-- ont table 
--

--ont 1
ontTable 	OBJECT-TYPE
	SYNTAX  SEQUENCE OF OntEntry
	MAX-ACCESS  not-accessible
	STATUS  current
	DESCRIPTION
		""
	::= {ont 1}

ontEntry	OBJECT-TYPE
	SYNTAX	 	OntEntry
	MAX-ACCESS  not-accessible
	STATUS		current
	DESCRIPTION
		""
	INDEX	{ oltIndex, ponIndex, ontIndex}
	::= {ontTable 1}

OntEntry	::=
	SEQUENCE
	{
        ontIndex                       INTEGER (1..128),
        ontSN                          OCTET STRING (SIZE(0..255)),    
        ontStatus                      INTEGER (0..1),
        ontFindState                   INTEGER (0..1),
        ontAuthState                   INTEGER (0..3),
        ontConfig                      INTEGER (0..3),
        ontReason                      INTEGER (1..20),
        ontDeviceType                  INTEGER (0..64),
        ontSNvenderId                  OCTET STRING (SIZE(0..255)),
        ontVersion                     OCTET STRING (SIZE(0..255)),
        ontEquipmentID                 OCTET STRING (SIZE(0..255)),
        ontMainSoftwareVersion         OCTET STRING (SIZE(0..255)),
        ontProductDescription	       OCTET STRING (SIZE(0..255)),
        ontNoCofing                    INTEGER (0..1),
        ontType                        OCTET STRING (SIZE(0..255)),
        ontReboot                      INTEGER (0..1),
        ontSecondarySoftwareVersion    OCTET STRING (SIZE(0..255)),
        ontOnlineTime                  OCTET STRING (SIZE(0..255)),
        ontUpTime                      OCTET STRING (SIZE(0..255)),
        ontPowerfeedVoltage            OCTET STRING (SIZE(0..255)),
        ontLaserBiasCurrent            OCTET STRING (SIZE(0..255)),
        ontReceivedOpticalPower        OCTET STRING (SIZE(0..255)),
        ontMeanOpticalLaunchPower      OCTET STRING (SIZE(0..255)),
        ontTemperature                 OCTET STRING (SIZE(0..255)),
        ontDescription                 OCTET STRING (SIZE(0..255)), 
        ontSNspecificVenderId          OCTET STRING (SIZE(0..255)),
        ontSNRowStatus                 RowStatus,
        ontStateActive                 INTEGER (0..1),
        ontUpdateOmci                  INTEGER (0..1),
        ontUpdateCommitOmci            INTEGER (0..1),
        ontAutoConfig                  INTEGER (0..1),
        ontDistance                    OCTET STRING (SIZE(0..255)),
        ontUplinkPONports              OCTET STRING (SIZE(0..255)),
        ontPOTSports                   OCTET STRING (SIZE(0..255)),
        ontETHports                    OCTET STRING (SIZE(0..255)),
        ontTDMports                    OCTET STRING (SIZE(0..255)),
        ontMOCAports                   OCTET STRING (SIZE(0..255)),
        ontCatvAniPorts                OCTET STRING (SIZE(0..255)),
        ontCatvUniPorts                OCTET STRING (SIZE(0..255)),
        ontGEMports                    OCTET STRING (SIZE(0..255)),
        ontIPconfiguration             OCTET STRING (SIZE(0..255)),
        ontTrafficSchedulers           OCTET STRING (SIZE(0..255)),
        ontTCONTs                      OCTET STRING (SIZE(0..255)),
        ontFlowControl                 OCTET STRING (SIZE(0..255)),
        ontTXpowerCutOff               OCTET STRING (SIZE(0..255)),
        ontMaxMacCount                 INTEGER (0..255)
	}
	
ontIndex	OBJECT-TYPE
	SYNTAX	 	INTEGER (1..128)
	MAX-ACCESS  read-write
	STATUS		current
	DESCRIPTION
		"GPON_SW_OLT_PORT_NUM_ONT = 128 "
	::= {ontEntry 1}

ontSN	OBJECT-TYPE
	SYNTAX	 	OCTET STRING (SIZE(0..255))
	MAX-ACCESS  read-only
	STATUS		current
	DESCRIPTION
		"ontSN"
	::= {ontEntry 2}
	
ontStatus	OBJECT-TYPE
	SYNTAX	 	INTEGER (0..1)
	MAX-ACCESS  read-only
	STATUS		current
	DESCRIPTION
		"ontStatus_online = 1,
		 ontStatus_offline = 0"
	::= {ontEntry 3}
	
ontFindState	OBJECT-TYPE
	SYNTAX	 	INTEGER (0..1)
	MAX-ACCESS  read-only
	STATUS		current
	DESCRIPTION
		"ontFind_manual = 0,
		 ontFind_auto = 1,
		"
	::= {ontEntry 4}
	
ontAuthState	OBJECT-TYPE
	SYNTAX	 	INTEGER (0..1)
	MAX-ACCESS  read-only
	STATUS		current
	DESCRIPTION
		"ontAuth = 1"
	::= {ontEntry 5}
	
ontConfig	OBJECT-TYPE
	SYNTAX	 	INTEGER (0..1)
	MAX-ACCESS  read-only
	STATUS		current
	DESCRIPTION
		"ontConfig = 1"
	::= {ontEntry 6}
	
ontReason	OBJECT-TYPE
	SYNTAX	 	INTEGER (1..3)
	MAX-ACCESS  read-only
	STATUS		current
	DESCRIPTION
		"ontReason:
		typedef enum REASON
		{
        case 0:
               power off;
        case 1:
               normal;
        case 2:
               los;
        case 3:
               losi;
        case 4:
               lofi;
        case 5:
               dow;
        case 6:
               sf;
        case 7:
               sd;
        case 8:
               lcdgi;
        case 9:
               rd;
        case 11:
                 suf;
        case 12:
                 loa;
        case 13:
                 dg;
        case 14:
                 df;
        case 15:
                 loami;
        case 16:
                 mem;
        case 17:
                 pee;
        case 18:
                 pst;
        case 19:
                 tiw;
        case 20:
                 lok;			 
        case 53:
                 link has been deactivated;
        case 212:
                 ONT has been deactivated;
        case 213:
                 ONT has been disable;
        case 672:
                 All of the ONT has been deactivated;
	   
		}REASON_TYPE;"
	::= {ontEntry 7}
	
ontDeviceType	OBJECT-TYPE
	SYNTAX	 	INTEGER (1..128)
	MAX-ACCESS  read-write
	STATUS		current
	DESCRIPTION
	"ontDeviceType:
    ONT_DEVICE_TYPE_NONE    = 0
    ONT_DEVICE_TYPE_T10_100 = 101
    ONT_DEVICE_TYPE_T10_420 = 102
    ONT_DEVICE_TYPE_T10_214 = 103
    ONT_DEVICE_TYPE_T10_423 = 104
    ONT_DEVICE_TYPE_T10_427 = 105
    ONT_DEVICE_TYPE_T10_403 = 106
    ONT_DEVICE_TYPE_T60_100 = 107
    
    ONT_DEVICE_TYPE_C40_100 = 201
    ONT_DEVICE_TYPE_C40_427 = 202
    ONT_DEVICE_TYPE_C30_401 = 203
    ONT_DEVICE_TYPE_C30_423 = 204
    ONT_DEVICE_TYPE_C30_420 = 205
    ONT_DEVICE_TYPE_C31_423 = 206/* db */
    ONT_DEVICE_TYPE_C30_214 = 207

    ONT_DEVICE_TYPE_M50_420 = 301

    ONT_DEVICE_TYPE_F10_427 = 401

    ONT_DEVICE_TYPE_H60_100 = 502 

    ONT_DEVICE_TYPE_N20_100 = 601
    ONT_DEVICE_TYPE_N20_400 = 602

    ONT_DEVICE_TYPE_S10_214 = 701

    c30-214 2ETH(1ETH+1iTV)+1POTS SFU
    c30-401 4ETH+WIFI HGU
    c30-420 4ETH+2POTS SFU
    c30-423 4ETH+2POTS+WIFI+USB HGU
    c31-423 4ETH+2POTS+WIFI+USB HGU+SFU
    c40-100 1ETH SFU
    c40-427 4ETH(3ETH+1iTV)+2POTS+WIFI+USB HGU
    f10-427 4ETH(3ETH+1iTV)+2POTS+WIFI+USB HGU
    h60-100 1ETH SFU
    m50-420 4ETH+2POTS SFU
    n20-100 1ETH SFU
    n20-400 4ETH SFU
    s10-214 2ETH(1ETH+1iTV)+1POTS HGU
    t10-100 1ETH SFU
    t10-214 2ETH(1ETH+1iTV)+1POTS SFU
    t10-403 4ETH+WIFI+USB HGU
    t10-420 4ETH+2POTS SFU
    t10-423 4ETH+2POTS+WIFI+USB HGU
    t10-427 4ETH(3ETH+1iTV)+2POTS+WIFI+USB HGU
    t60-100 1ETH SFU"
	::= {ontEntry 8}

ontSNvenderId	  OBJECT-TYPE
	SYNTAX        OCTET STRING (SIZE(0..255))
	MAX-ACCESS    read-write
	STATUS        current
	DESCRIPTION
		"sn:vendor id , factory mark like ABCD"
	::= {ontEntry 9}

ontVersion	OBJECT-TYPE
	SYNTAX	 	OCTET STRING (SIZE(0..255))
	MAX-ACCESS  read-only
	STATUS		current
	DESCRIPTION
		"ontVersion"
	::= {ontEntry 10}

ontEquipmentID	OBJECT-TYPE
	SYNTAX	 	OCTET STRING (SIZE(0..255))
	MAX-ACCESS  read-only
	STATUS		current
	DESCRIPTION
		"ontEquipmentID"
	::= {ontEntry 11}

ontMainSoftwareVersion	OBJECT-TYPE
	SYNTAX	 	OCTET STRING (SIZE(0..255))
	MAX-ACCESS  read-only
	STATUS		current
	DESCRIPTION
		"ontMainSoftwareVersion"
	::= {ontEntry 12}

ontProductDescription	OBJECT-TYPE
	SYNTAX	 	OCTET STRING (SIZE(0..255))
	MAX-ACCESS  read-only
	STATUS		current
	DESCRIPTION
		"ontProductDescription"
	::= {ontEntry 13}

ontNoCofing    OBJECT-TYPE
	SYNTAX	 	INTEGER (0..1)
	MAX-ACCESS  read-write
	STATUS		current
	DESCRIPTION
	"set_ont_NoCofing = 1,
	 Clear the ONT configure!"
	::= {ontEntry 14}

ontType	OBJECT-TYPE
	SYNTAX	 	OCTET STRING (SIZE(0..255))
	MAX-ACCESS  read-only
	STATUS		current
	DESCRIPTION
		"device type"
	::= {ontEntry 15}

ontReboot    OBJECT-TYPE
	SYNTAX	 	INTEGER (0..1)
	MAX-ACCESS  read-write
	STATUS		current
	DESCRIPTION
		"ontReboot:
		 ont_reboot = 1"
	::= {ontEntry 16}
	
ontSecondarySoftwareVersion	OBJECT-TYPE
	SYNTAX	 	OCTET STRING (SIZE(0..255))
	MAX-ACCESS  read-only
	STATUS		current
	DESCRIPTION
		"ontSecondarySoftwareVersion"
	::= {ontEntry 17}
	
ontOnlineTime    OBJECT-TYPE
	SYNTAX	 	OCTET STRING (SIZE(0..255))
	MAX-ACCESS  read-only
	STATUS		current
	DESCRIPTION
		"ontOnlineTime:
		 year/month/day hour:minute:second"
	::= {ontEntry 18}
	
ontUpTime    OBJECT-TYPE
	SYNTAX	 	OCTET STRING (SIZE(0..255))
	MAX-ACCESS  read-only
	STATUS		current
	DESCRIPTION
		"ontUpTime:
		 Day Hour Minute"
	::= {ontEntry 19}
	
ontPowerfeedVoltage	   OBJECT-TYPE
	SYNTAX	 	OCTET STRING (SIZE(0..255))
	MAX-ACCESS  read-only
	STATUS		current
	DESCRIPTION
		"unit: V "
	::= {ontEntry 20}

ontLaserBiasCurrent    OBJECT-TYPE
	SYNTAX	 	OCTET STRING (SIZE(0..255))
	MAX-ACCESS  read-only
	STATUS		current
	DESCRIPTION
		"unit: uA "
	::= {ontEntry 21}

ontReceivedOpticalPower    OBJECT-TYPE
	SYNTAX	 	OCTET STRING (SIZE(0..255))
	MAX-ACCESS  read-only
	STATUS		current
	DESCRIPTION
		"unit: dBm "
	::= {ontEntry 22}
	
ontMeanOpticalLaunchPower    OBJECT-TYPE
	SYNTAX	 	OCTET STRING (SIZE(0..255))
	MAX-ACCESS  read-only
	STATUS		current
	DESCRIPTION
		"unit: dBm "
	::= {ontEntry 23}
	
ontTemperature    OBJECT-TYPE
	SYNTAX	 	OCTET STRING (SIZE(0..255))
	MAX-ACCESS  read-only
	STATUS		current
	DESCRIPTION
		"unit: C "
	::= {ontEntry 24}

ontDescription    OBJECT-TYPE
	SYNTAX        OCTET STRING (SIZE(0..255))
	MAX-ACCESS    read-write
	STATUS        current
	DESCRIPTION
		"ontDescription:
		 STRING<1-32>"
	::= {ontEntry 25}

ontSNspecificVenderId    OBJECT-TYPE
	SYNTAX        OCTET STRING (SIZE(0..255))
	MAX-ACCESS    read-write
	STATUS        current
	DESCRIPTION
		"sn:specific vendor id (0x00000000-0xFFFFFFFF)"
	::= {ontEntry 26}
	
ontSNRowStatus    OBJECT-TYPE    
	SYNTAX        RowStatus
	MAX-ACCESS    read-write
	STATUS        current
	DESCRIPTION
		"Bind SN or remove offline ONT !"
	::= {ontEntry 27}

ontStateActive	   OBJECT-TYPE
	SYNTAX	 	INTEGER (0..1)
	MAX-ACCESS  read-write
	STATUS		current
	DESCRIPTION
		"ontStateDeactive = 0,
		 ontStateActive = 1"
	::= {ontEntry 28}

ontUpdateOmci	   OBJECT-TYPE
	SYNTAX	 	INTEGER (0..1)
	MAX-ACCESS  read-write
	STATUS		current
	DESCRIPTION
		"ontUpdateOmci:
		 set_ont_update_omci = 1"
	::= {ontEntry 29}

ontUpdateCommitOmci   OBJECT-TYPE
	SYNTAX	 	INTEGER (0..1)
	MAX-ACCESS  read-write
	STATUS		current
	DESCRIPTION
		"ontUpdateCommitOmci:
		 set_ont_update_commit_omci = 1"
	::= {ontEntry 30}

ontAutoConfig   OBJECT-TYPE
	SYNTAX	 	INTEGER (0..1)
	MAX-ACCESS  read-write
	STATUS		current
	DESCRIPTION
		"save ont-auto-config = 1
		 no   ont-auto-config = 0"
	::= {ontEntry 31}
	
ontDistance   OBJECT-TYPE
	SYNTAX	 	OCTET STRING (SIZE(0..255))
	MAX-ACCESS  read-only
	STATUS		current
	DESCRIPTION
		"unit: M "
	::= {ontEntry 32}

ontUplinkPONports   OBJECT-TYPE
	SYNTAX	 	OCTET STRING (SIZE(0..255))
	MAX-ACCESS  read-only
	STATUS		current
	DESCRIPTION
		"Number of uplink PON ports"
	::= {ontEntry 33}

ontPOTSports    OBJECT-TYPE
	SYNTAX	 	OCTET STRING (SIZE(0..255))
	MAX-ACCESS  read-only
	STATUS		current
	DESCRIPTION
		"Number of POTS ports"
	::= {ontEntry 34}

ontETHports     OBJECT-TYPE
	SYNTAX	 	OCTET STRING (SIZE(0..255))
	MAX-ACCESS  read-only
	STATUS		current
	DESCRIPTION
		"Number of ETH ports"
	::= {ontEntry 35}

ontTDMports     OBJECT-TYPE
	SYNTAX	 	OCTET STRING (SIZE(0..255))
	MAX-ACCESS  read-only
	STATUS		current
	DESCRIPTION
		"Number of TDM ports"
	::= {ontEntry 36}

ontMOCAports   OBJECT-TYPE
	SYNTAX	 	OCTET STRING (SIZE(0..255))
	MAX-ACCESS  read-only
	STATUS		current
	DESCRIPTION
		"Number of MOCA ports"
	::= {ontEntry 37}

ontCatvAniPorts   OBJECT-TYPE
	SYNTAX	 	OCTET STRING (SIZE(0..255))
	MAX-ACCESS  read-only
	STATUS		current
	DESCRIPTION
		"Number of CATV ANI ports"
	::= {ontEntry 38}

ontCatvUniPorts   OBJECT-TYPE
	SYNTAX	 	OCTET STRING (SIZE(0..255))
	MAX-ACCESS  read-only
	STATUS		current
	DESCRIPTION
		"Number of CATV UNI ports"
	::= {ontEntry 39}

ontGEMports   OBJECT-TYPE
	SYNTAX	 	OCTET STRING (SIZE(0..255))
	MAX-ACCESS  read-only
	STATUS		current
	DESCRIPTION
		"Number of GEM ports"
	::= {ontEntry 40}

ontIPconfiguration   OBJECT-TYPE
	SYNTAX	 	OCTET STRING (SIZE(0..255))
	MAX-ACCESS  read-only
	STATUS		current
	DESCRIPTION
		"IP configuration"
	::= {ontEntry 41}

ontTrafficSchedulers   OBJECT-TYPE
	SYNTAX	 	OCTET STRING (SIZE(0..255))
	MAX-ACCESS  read-only
	STATUS		current
	DESCRIPTION
		"Number of Traffic Schedulers"
	::= {ontEntry 42}

ontTCONTs   OBJECT-TYPE
	SYNTAX	 	OCTET STRING (SIZE(0..255))
	MAX-ACCESS  read-only
	STATUS		current
	DESCRIPTION
		"Number of T-CONTs"
	::= {ontEntry 43}

ontFlowControl   OBJECT-TYPE
	SYNTAX	 	OCTET STRING (SIZE(0..255))
	MAX-ACCESS  read-only
	STATUS		current
	DESCRIPTION
		"The type of flow control"
	::= {ontEntry 44}

ontTXpowerCutOff   OBJECT-TYPE
	SYNTAX	 	OCTET STRING (SIZE(0..255))
	MAX-ACCESS  read-only
	STATUS		current
	DESCRIPTION
		"TX power cut off"
	::= {ontEntry 45}

ontMaxMacCount  OBJECT-TYPE
	SYNTAX	 	INTEGER(0..255)
	MAX-ACCESS  read-write
	STATUS		current
	DESCRIPTION
		"This function is only applied to HGU."
	::= {ontEntry 46}

--ont 2
ontTcontTable         OBJECT-TYPE
	SYNTAX  SEQUENCE OF OntTcontEntry
	MAX-ACCESS    not-accessible
	STATUS        current
	DESCRIPTION
		""
	::= {ont 2}

ontTcontEntry         OBJECT-TYPE
	SYNTAX        OntTcontEntry
	MAX-ACCESS    not-accessible
	STATUS        current
	DESCRIPTION
		""
	INDEX	{ oltIndex, ponIndex, ontIndex , tcontIndex}
	::= {ontTcontTable 1}

OntTcontEntry	::=
	SEQUENCE
	{
		bindDBAbyName       OCTET STRING (SIZE(0..255)), 
		bindDBARowstatus    RowStatus,
		bindDBAbyIndex      INTEGER(1..256)
	}
	
bindDBAbyName     OBJECT-TYPE
	SYNTAX        OCTET STRING (SIZE(0..255))
	MAX-ACCESS    read-write
	STATUS        current
	DESCRIPTION
		"bindDBAbyName"
	::= { ontTcontEntry 1}
	
bindDBARowstatus      OBJECT-TYPE
	SYNTAX        RowStatus
	MAX-ACCESS    read-write
	STATUS        current
	DESCRIPTION
		"bindDBARowstatus"
	::= { ontTcontEntry 2}	

bindDBAbyIndex    OBJECT-TYPE
	SYNTAX        INTEGER(1..256)
	MAX-ACCESS    read-write
	STATUS        current
	DESCRIPTION
		"bindDBAbyIndex"
	::= { ontTcontEntry 3}
	
--ont 3
ontGemportTable       OBJECT-TYPE
	SYNTAX  SEQUENCE OF OntGemportEntry
	MAX-ACCESS    not-accessible
	STATUS        current
	DESCRIPTION
		""
	::= {ont 3}

ontGemportEntry       OBJECT-TYPE
	SYNTAX        OntGemportEntry
	MAX-ACCESS    not-accessible
	STATUS        current
	DESCRIPTION
		""
	INDEX	{ oltIndex, ponIndex, ontIndex, gemportIndex}
	::= {ontGemportTable 1}

OntGemportEntry	::=
	SEQUENCE
	{
		gemportId           INTEGER (256..4095),
		tcontId             INTEGER (1..3),
		gemportRowstatus    RowStatus
	}

gemportId             OBJECT-TYPE
	SYNTAX        INTEGER (256..4095)
	MAX-ACCESS    read-write
	STATUS        current
	DESCRIPTION
		"gemportId"
	::= { ontGemportEntry 1}

tcontId               OBJECT-TYPE
	SYNTAX        INTEGER (1..3)
	MAX-ACCESS    read-write
	STATUS        current
	DESCRIPTION
		"tcontId"
	::= { ontGemportEntry 2}
	
gemportRowstatus      OBJECT-TYPE
	SYNTAX        RowStatus
	MAX-ACCESS    read-write
	STATUS        current
	DESCRIPTION
		"gemportRowstatus"
	::= { ontGemportEntry 3}

--ont 4 
ontServiceportTableI    OBJECT-TYPE
	SYNTAX  SEQUENCE OF OntServiceportEntryI  
	MAX-ACCESS    not-accessible
	STATUS        current
	DESCRIPTION
		""
	::= {ont 4}

ontServiceportEntryI    OBJECT-TYPE
	SYNTAX          OntServiceportEntryI
	MAX-ACCESS      not-accessible
	STATUS          current
	DESCRIPTION
		""
	--INDEX	{ oltIndex, ponIndex, ontIndex , ServiceportIndex, priorityIndex}
	::= {ontServiceportTableI 1}
	
OntServiceportEntryI	::=
	SEQUENCE
	{
		mappingGemport             INTEGER (0..4095),
		mappingGemportRowStatus    RowStatus
	}		

mappingGemport        OBJECT-TYPE
	SYNTAX        INTEGER (0..4095)
	MAX-ACCESS    read-write
	STATUS        current
	DESCRIPTION
		"serviceport mappping gemport by one priority"
	::= { ontServiceportEntryI 1}	

mappingGemportRowStatus    OBJECT-TYPE
	SYNTAX             RowStatus
	MAX-ACCESS         read-write
	STATUS             current
	DESCRIPTION
		"mappingGemportRowStatus"
	::= { ontServiceportEntryI 2}  

--ont 5 --------------------------------------------------
ontServiceportTableII    OBJECT-TYPE
	SYNTAX  SEQUENCE OF OntServiceportEntryII  
	MAX-ACCESS    not-accessible
	STATUS        current
	DESCRIPTION
		""
	::= {ont 5}
	
ontServiceportEntryII    OBJECT-TYPE
	SYNTAX           OntServiceportEntryII
	MAX-ACCESS       not-accessible
	STATUS           current
	DESCRIPTION
		""
	--INDEX	{ oltIndex, ponIndex, ontIndex , ServiceportIndex}
	::= {ontServiceportTableII 1}
	
OntServiceportEntryII	::=
	SEQUENCE
	{
		serviceportMapGem                  INTEGER (256..4095),
		serviceportCreatedVlan             OCTET STRING (SIZE(0..24)),
		serviceportMapGemRowStatus         RowStatus,
		serviceportCreatedVlanRowStatus    RowStatus
	}
	
serviceportMapGem     OBJECT-TYPE
	SYNTAX        INTEGER (256..4095)
	MAX-ACCESS    read-write
	STATUS        current
	DESCRIPTION
		"serviceport mappping gemport by all priority"
	::= { ontServiceportEntryII 1}

serviceportCreatedVlan    OBJECT-TYPE
	SYNTAX            OCTET STRING (SIZE(0..24))
	MAX-ACCESS        read-write
	STATUS            current
	DESCRIPTION
		"serviceportCreatedVlan"
	::= { ontServiceportEntryII 2}

serviceportMapGemRowStatus    OBJECT-TYPE
	SYNTAX                RowStatus
	MAX-ACCESS            read-write
	STATUS                current
	DESCRIPTION
		"serviceportMapGemRowStatus"
	::= { ontServiceportEntryII 3}
	
serviceportCreatedVlanRowStatus    OBJECT-TYPE
	SYNTAX                     RowStatus
	MAX-ACCESS                 read-write
	STATUS                     current
	DESCRIPTION
		"serviceportCreatedVlanRowStatus"
	::= { ontServiceportEntryII 4}

--ont 6 --------------------------------------------------
ontPortTable		OBJECT-TYPE
	SYNTAX  SEQUENCE OF OntPortEntry
	MAX-ACCESS  not-accessible
	STATUS  current
	DESCRIPTION
		""
	::= {ont 6}

ontPortEntry	OBJECT-TYPE
	SYNTAX	 	OntPortEntry
	MAX-ACCESS  not-accessible
	STATUS		current
	DESCRIPTION
		""
	INDEX	{ oltIndex, ponIndex, ontIndex , ontPortIndex}
	::= {ontPortTable 1}
	
OntPortEntry	::=
	SEQUENCE
	{
        ontPortIndex              INTEGER (1..128),
        vlanMode                  INTEGER (1..4),
        tagVlan                   INTEGER (1..4094),
        ontPortLinkStatus         INTEGER (1..2),
        ontPortBandwidthEgress    INTEGER (64..1023936),
        ontPortSpeed              INTEGER (0..32),
        ontPortValid              INTEGER (1..2),
        ontPortMaxMacCount        INTEGER (0..255)
	}

ontPortIndex	OBJECT-TYPE
	SYNTAX	 	INTEGER (1..128)
	MAX-ACCESS  read-only
	STATUS		current
	DESCRIPTION
		"ontPortIndex"
	::= { ontPortEntry 1}	
	
vlanMode	OBJECT-TYPE
	SYNTAX	 	INTEGER (1..4)
	MAX-ACCESS  read-write
	STATUS		current
	DESCRIPTION
		"vlanMode:
		transparent = 0,
		tagged      = 1,
		translation = 2,
		aggregation = 3,
		trunk       = 4"
	::= { ontPortEntry 2}
	
tagVlan	OBJECT-TYPE
	SYNTAX	 	INTEGER (1..4094)
	MAX-ACCESS  read-write
	STATUS		current
	DESCRIPTION
		"tagVlan"
	::= { ontPortEntry 3}	

ontPortLinkStatus	OBJECT-TYPE
	SYNTAX	 	INTEGER (0..32)
	MAX-ACCESS  read-only
	STATUS		current
	DESCRIPTION
		"ontPortLinkStatus:
         linkup   = 2,
		 linkdown = 1 "
	::= { ontPortEntry 4}	
	
ontPortBandwidthEgress	OBJECT-TYPE
	SYNTAX	 	INTEGER (64..1023936)
	MAX-ACCESS  read-write
	STATUS		current
	DESCRIPTION
		"ontPortBandwidthEgress:
		max BW egress(kbps): must to be divisible by 64kbps,must 
                     not less than 64 kbps"
	::= { ontPortEntry 5}			

ontPortSpeed	OBJECT-TYPE
	SYNTAX	 	INTEGER (0..32)
	MAX-ACCESS  read-only
	STATUS		current
	DESCRIPTION
		"ontPortLinkStatus:
		case 1:
			     10BaseT full duplex
		case 2:
			     100BaseT full duplex
		case 3:
			     Gigabit Ethernet full duplex
		case 16:
			     10BaseT half duplex
		case 17:
			     100BaseT half duplex
		case 18:
			     Gigabit Ethernet half duplex
		case 0:
		         port is linkdown!"
	::= { ontPortEntry 6}

ontPortValid	OBJECT-TYPE
	SYNTAX	 	INTEGER (1..2)
	MAX-ACCESS  read-write
	STATUS		current
	DESCRIPTION
		"ontPortValid     = 2 
		 ontPortInvalid   = 1,"
	::= { ontPortEntry 7}

ontPortMaxMacCount  OBJECT-TYPE
	SYNTAX	 	    INTEGER (0..255)
	MAX-ACCESS      read-write
	STATUS          current
	DESCRIPTION
		"This function is only applied to SFU."
	::= { ontPortEntry 8}

--ont 7 --------------------------------------------------
ontPortTrunkTable		OBJECT-TYPE
	SYNTAX  SEQUENCE OF OntPortTrunkEntry
	MAX-ACCESS  not-accessible
	STATUS  current
	DESCRIPTION
		""
	::= {ont 7}

ontPortTrunkEntry	OBJECT-TYPE
	SYNTAX	 	OntPortTrunkEntry
	MAX-ACCESS  not-accessible
	STATUS		current
	DESCRIPTION
		""
	INDEX	{ oltIndex, ponIndex, ontIndex , ontPortIndex}
	::= {ontPortTrunkTable 1}
	
OntPortTrunkEntry	::=
	SEQUENCE
	{
		vlanList	     OCTET STRING (SIZE(0..24)),
		trunkDefalutVlan     INTEGER (1..4095),
		ontTrunkRowStatus    RowStatus
	}
	
vlanList	OBJECT-TYPE
	SYNTAX	 	OCTET STRING (SIZE(0..24))
	MAX-ACCESS  read-write
	STATUS		current
	DESCRIPTION
		"VLAN membership only 11 at most!"
	::= { ontPortTrunkEntry 1}

trunkDefalutVlan	OBJECT-TYPE
	SYNTAX	 	INTEGER (1..4095)
	MAX-ACCESS  read-write
	STATUS		current
	DESCRIPTION
		"defalutVlan should not be in the vlan list!"
	::= { ontPortTrunkEntry 2}
	
ontTrunkRowStatus	OBJECT-TYPE
	SYNTAX	 	RowStatus
	MAX-ACCESS  read-write
	STATUS		current
	DESCRIPTION
		"RowStatus"
	::= { ontPortTrunkEntry 3}

--ont 8 --------------------------------------------------
ontPortTranslationTable		OBJECT-TYPE
	SYNTAX  SEQUENCE OF OntPortTranslationEntry
	MAX-ACCESS  not-accessible
	STATUS  current
	DESCRIPTION
		""
	::= {ont 8}

ontPortTranslationEntry	OBJECT-TYPE
	SYNTAX	 	OntPortTranslationEntry
	MAX-ACCESS  not-accessible
	STATUS		current
	DESCRIPTION
		""
	INDEX	{ oltIndex, ponIndex, ontIndex, ontPortIndex, ontPortTranslationIndex}
	::= {ontPortTranslationTable 1}
	
OntPortTranslationEntry	::=
	SEQUENCE
	{
		translationIndex           INTEGER (1..11),
		translationDefalutVlan     INTEGER (1..4095),
		svid                       INTEGER (1..4095),
		dvid                       INTEGER (1..4095),
		ontTranslationRowStatus    RowStatus
	}
	
translationIndex	OBJECT-TYPE
	SYNTAX	 	INTEGER (1..11)
	MAX-ACCESS  read-write
	STATUS		current
	DESCRIPTION
		"translationIndex"
	::= { ontPortTranslationEntry 1}	

translationDefalutVlan	OBJECT-TYPE
	SYNTAX	 	INTEGER (1..4095)
	MAX-ACCESS  read-write
	STATUS		current
	DESCRIPTION
		"defalutVlan"
	::= { ontPortTranslationEntry 2}

svid	OBJECT-TYPE
	SYNTAX	 	INTEGER (1..4095)
	MAX-ACCESS  read-write
	STATUS		current
	DESCRIPTION
		"svid"
	::= { ontPortTranslationEntry 3}
	
dvid	OBJECT-TYPE
	SYNTAX	 	INTEGER (1..4095)
	MAX-ACCESS  read-write
	STATUS		current
	DESCRIPTION
		"dvid"
	::= { ontPortTranslationEntry 4}
	
ontTranslationRowStatus	OBJECT-TYPE
	SYNTAX	 	RowStatus
	MAX-ACCESS  read-write
	STATUS		current
	DESCRIPTION
		"RowStatus"
	::= { ontPortTranslationEntry 5}

--ont 9 --------------------------------------------------
ontEthStaTable		OBJECT-TYPE
	SYNTAX  SEQUENCE OF OntEthStaEntry
	MAX-ACCESS  not-accessible
	STATUS  current
	DESCRIPTION
		""
	::= {ont 9}

ontEthStaEntry	OBJECT-TYPE
	SYNTAX	 	OntEthStaEntry
	MAX-ACCESS  not-accessible
	STATUS		current
	DESCRIPTION
		""
	INDEX	{ oltIndex, ponIndex, ontIndex , ontPortIndex}
	::= {ontEthStaTable 1}
	
OntEthStaEntry	::=
	SEQUENCE
	{
        recframes            INTEGER (0..4294967295),
        recuniframes         INTEGER (0..4294967295),
        recmulframes         INTEGER (0..4294967295),
        recbroframes         INTEGER (0..4294967295),
        rec64frames          INTEGER (0..4294967295),
        rec65frames          INTEGER (0..4294967295),
        rec128frames         INTEGER (0..4294967295),
        rec256frames         INTEGER (0..4294967295),
        rec512frames         INTEGER (0..4294967295),
        rec1024frames        INTEGER (0..4294967295),
        recundframes         INTEGER (0..4294967295),
        recoveframes         INTEGER (0..4294967295),
        recfragments         INTEGER (0..4294967295),
        recjabbers           INTEGER (0..4294967295),
        recfcsframes         INTEGER (0..4294967295),
        disframes            INTEGER (0..4294967295),
        recaliframes         INTEGER (0..4294967295),
        macrecframes         INTEGER (0..4294967295),
        pppframes            INTEGER (0..4294967295),
        bufreceive           INTEGER (0..4294967295),
        recbytes             INTEGER (0..4294967295),
        senframes            INTEGER (0..4294967295),
        senuniframes         INTEGER (0..4294967295),
        senmulframes         INTEGER (0..4294967295),
        senbroframes         INTEGER (0..4294967295),
        carframes            INTEGER (0..4294967295),
        sqemessages          INTEGER (0..4294967295),
        sensinframes         INTEGER (0..4294967295),
        senmulcolframes      INTEGER (0..4294967295),
        senexcframes         INTEGER (0..4294967295),
        latframes            INTEGER (0..4294967295),
        macsenframes         INTEGER (0..4294967295),
        buftransmit          INTEGER (0..4294967295)
	}
	
recFrames         OBJECT-TYPE
	SYNTAX        INTEGER (0..4294967295)
	MAX-ACCESS    read-only
	STATUS        current
	DESCRIPTION
		"Received frames"
	::= { ontEthStaEntry 1}

recUniFrames	  OBJECT-TYPE
	SYNTAX        INTEGER (0..4294967295)
	MAX-ACCESS    read-only
	STATUS        current
	DESCRIPTION
		"Received unicast frames"
	::= { ontEthStaEntry 2}

recMulFrames      OBJECT-TYPE
	SYNTAX        INTEGER (0..4294967295)
	MAX-ACCESS    read-only
	STATUS        current
	DESCRIPTION
		"Received multicast frames"
	::= { ontEthStaEntry 3}

recBroframes      OBJECT-TYPE
	SYNTAX        INTEGER (0..4294967295)
	MAX-ACCESS    read-only
	STATUS        current
	DESCRIPTION
		"Received broadcast frames"
	::= { ontEthStaEntry 4}

rec64Frames       OBJECT-TYPE
	SYNTAX        INTEGER (0..4294967295)
	MAX-ACCESS    read-only
	STATUS        current
	DESCRIPTION
		"Received 64-byte frames"
	::= { ontEthStaEntry 5}

rec65Frames	      OBJECT-TYPE
	SYNTAX        INTEGER (0..4294967295)
	MAX-ACCESS    read-only
	STATUS        current
	DESCRIPTION
		"Received 65~127-byte frames"
	::= { ontEthStaEntry 6}

rec128Frames      OBJECT-TYPE
	SYNTAX        INTEGER (0..4294967295)
	MAX-ACCESS    read-only
	STATUS        current
	DESCRIPTION
		"Received 128~255-byte frames"
	::= { ontEthStaEntry 7}

rec256Frames      OBJECT-TYPE
	SYNTAX        INTEGER (0..4294967295)
	MAX-ACCESS    read-only
	STATUS        current
	DESCRIPTION
		"Received 256~511-byte frames"
	::= { ontEthStaEntry 8}

rec512Frames      OBJECT-TYPE
	SYNTAX        INTEGER (0..4294967295)
	MAX-ACCESS    read-only
	STATUS        current
	DESCRIPTION
		"Received 512~1023-byte frames"
	::= { ontEthStaEntry 9}

rec1024Frames     OBJECT-TYPE
	SYNTAX        INTEGER (0..4294967295)
	MAX-ACCESS    read-only
	STATUS        current
	DESCRIPTION
		"Received 1024~1518-byte frames"
	::= { ontEthStaEntry 10}

recUndFrames      OBJECT-TYPE
	SYNTAX        INTEGER (0..4294967295)
	MAX-ACCESS    read-only
	STATUS        current
	DESCRIPTION
		"Received undersize frames"
	::= { ontEthStaEntry 11}
	
recOveFrames      OBJECT-TYPE
	SYNTAX        INTEGER (0..4294967295)
	MAX-ACCESS    read-only
	STATUS        current
	DESCRIPTION
		"Received oversize frames"
	::= { ontEthStaEntry 12}

recFragments      OBJECT-TYPE
	SYNTAX        INTEGER (0..4294967295)
	MAX-ACCESS    read-only
	STATUS        current
	DESCRIPTION
		"Received fragments"
	::= { ontEthStaEntry 13}
	
recJabbers        OBJECT-TYPE
	SYNTAX        INTEGER (0..4294967295)
	MAX-ACCESS    read-only
	STATUS        current
	DESCRIPTION
		"Received jabbers"
	::= { ontEthStaEntry 14}

recFcsFrames      OBJECT-TYPE
	SYNTAX        INTEGER (0..4294967295)
	MAX-ACCESS    read-only
	STATUS        current
	DESCRIPTION
		"Received FCS error frames"
	::= { ontEthStaEntry 15}
	
disFrames         OBJECT-TYPE
	SYNTAX        INTEGER (0..4294967295)
	MAX-ACCESS    read-only
	STATUS        current
	DESCRIPTION
		"Discard frames"
	::= { ontEthStaEntry 16}

recAliFrames      OBJECT-TYPE
	SYNTAX        INTEGER (0..4294967295)
	MAX-ACCESS    read-only
	STATUS        current
	DESCRIPTION
		"Received alignment error frames"
	::= { ontEthStaEntry 17}

macRecFrames      OBJECT-TYPE
	SYNTAX        INTEGER (0..4294967295)
	MAX-ACCESS    read-only
	STATUS        current
	DESCRIPTION
		"MAC sub-layer received error frames"
	::= { ontEthStaEntry 18}

pppFrames         OBJECT-TYPE
	SYNTAX        INTEGER (0..4294967295)
	MAX-ACCESS    read-only
	STATUS        current
	DESCRIPTION
		"PPPOE filtered frames"
	::= { ontEthStaEntry 19}

bufReceive        OBJECT-TYPE
	SYNTAX        INTEGER (0..4294967295)
	MAX-ACCESS    read-only
	STATUS        current
	DESCRIPTION
		"Buffer overflows on receive"
	::= { ontEthStaEntry 20}

recBytes          OBJECT-TYPE
	SYNTAX        INTEGER (0..4294967295)
	MAX-ACCESS    read-only
	STATUS        current
	DESCRIPTION
		"Received bytes"
	::= { ontEthStaEntry 21}

senFrames         OBJECT-TYPE
	SYNTAX        INTEGER (0..4294967295)
	MAX-ACCESS    read-only
	STATUS        current
	DESCRIPTION
		"Sent frames"
	::= { ontEthStaEntry 22}

senUniFrames      OBJECT-TYPE
	SYNTAX        INTEGER (0..4294967295)
	MAX-ACCESS    read-only
	STATUS        current
	DESCRIPTION
		"Sent unicast frames"
	::= { ontEthStaEntry 23}

senMulFrames      OBJECT-TYPE
	SYNTAX        INTEGER (0..4294967295)
	MAX-ACCESS    read-only
	STATUS        current
	DESCRIPTION
		"Sent multicast frames"
	::= { ontEthStaEntry 24}

senBroFrames      OBJECT-TYPE
	SYNTAX        INTEGER (0..4294967295)
	MAX-ACCESS    read-only
	STATUS        current
	DESCRIPTION
		"Sent broadcast frames"
	::= { ontEthStaEntry 25}

carFrames         OBJECT-TYPE
	SYNTAX        INTEGER (0..4294967295)
	MAX-ACCESS    read-only
	STATUS        current
	DESCRIPTION
		"Carrier sense error frames"
	::= { ontEthStaEntry 26}

sqeMessages       OBJECT-TYPE
	SYNTAX        INTEGER (0..4294967295)
	MAX-ACCESS    read-only
	STATUS        current
	DESCRIPTION
		"SQE test error messages"
	::= { ontEthStaEntry 27}
	
senSinFrames      OBJECT-TYPE
	SYNTAX        INTEGER (0..4294967295)
	MAX-ACCESS    read-only
	STATUS        current
	DESCRIPTION
		"Sent single collision frames"
	::= { ontEthStaEntry 28}

senMulColFrames   OBJECT-TYPE
	SYNTAX        INTEGER (0..4294967295)
	MAX-ACCESS    read-only
	STATUS        current
	DESCRIPTION
		"Sent multiple collision frames"
	::= { ontEthStaEntry 29}

senExcFrames      OBJECT-TYPE
	SYNTAX        INTEGER (0..4294967295)
	MAX-ACCESS    read-only
	STATUS        current
	DESCRIPTION
		"Sent excessive collision frames"
	::= { ontEthStaEntry 30}
	
latFrames         OBJECT-TYPE
	SYNTAX        INTEGER (0..4294967295)
	MAX-ACCESS    read-only
	STATUS        current
	DESCRIPTION
		"Late collision frames"
	::= { ontEthStaEntry 31}

macSenFrames      OBJECT-TYPE
	SYNTAX        INTEGER (0..4294967295)
	MAX-ACCESS    read-only
	STATUS        current
	DESCRIPTION
		"MAC sub-layer sent error frames"
	::= { ontEthStaEntry 32}

bufTransmit       OBJECT-TYPE
	SYNTAX        INTEGER (0..4294967295)
	MAX-ACCESS    read-only
	STATUS        current
	DESCRIPTION
		"Buffer overflows on transmit"
	::= { ontEthStaEntry 33}

----------------------------------------------------------
-----------------------dba table--------------------------
----------------------------------------------------------
dbaTable 	OBJECT-TYPE
	SYNTAX  SEQUENCE OF DbaEntry
	MAX-ACCESS  not-accessible
	STATUS  current
	DESCRIPTION
		"dba table"
	::= {dba 1}

dbaEntry	OBJECT-TYPE
	SYNTAX	 	DbaEntry
	MAX-ACCESS  not-accessible
	STATUS		current
	DESCRIPTION
		"dbaEntry table"
	INDEX	{ dbaProfileIndex }
	::= { dbaTable 1 }

DbaEntry	::= 
        SEQUENCE 
        {
		dbaProfileIndex     INTEGER(1..128),
		dbaProfilename      OCTET STRING (SIZE(0..255)),
		dbaType		    INTEGER(1..5),
		fixBandwidth        INTEGER(128..1710720),
		assuredBandwidth    INTEGER(0..1710720),
		maxBandwidth        INTEGER(0..1710720),
		dbaRowStatus        RowStatus
        }

dbaProfileIndex OBJECT-TYPE    
        SYNTAX   INTEGER(1..128)
        MAX-ACCESS   read-only
        STATUS   current
        DESCRIPTION
            "dbaProfileIndex:
             The index should be inputed with <1-256>,
             because the index of system DBA profile is <1-10>,
             and the system DBA profile can't be changed or deleted."
        ::= { dbaEntry 1 }

dbaProfilename	OBJECT-TYPE
	SYNTAX	 	OCTET STRING (SIZE(0..255))
	MAX-ACCESS  read-write
	STATUS		current
	DESCRIPTION
		"dbaProfilename, profile name"
	::= { dbaEntry 2 }
	
dbaType	OBJECT-TYPE
	SYNTAX	 	INTEGER(1..5)
	MAX-ACCESS  read-write
	STATUS		current
	DESCRIPTION
		"dbaType, 
		1  fixed bandwidth
		2  assured bandwidth
		3  assured and max bandwidth
		4  max bandwidth
		5  fixed and assured and max bandwidth"
	::= { dbaEntry 3 }
	
fixBandwidth	OBJECT-TYPE
	SYNTAX	 	INTEGER(128..1710720)
	MAX-ACCESS  read-write
	STATUS		current
	DESCRIPTION
		"fixBandwidth:
		ust to be divisible by 64kbps,must not
                       less than 128 kbps."
	::= { dbaEntry 4 }

assuredBandwidth	OBJECT-TYPE
	SYNTAX	 	INTEGER(0..1710720)
	MAX-ACCESS  read-write
	STATUS		current
	DESCRIPTION
		"assuredBandwidth:
		must to be divisible by 64kbps, Can
                     be 0.  If not 0, it must be at least 256 kbps."
	::= { dbaEntry 5 }

maxBandwidth	OBJECT-TYPE
	SYNTAX	 	INTEGER(0..1710720)
	MAX-ACCESS  read-write
	STATUS		current
	DESCRIPTION
		"maxBandwidth,max bandwidth:
		must to be divisible by 64kbps, and 
		must not be less than the sum of assured BW plus fixedBW. 
		Must less than 1710720 kbps"
	::= { dbaEntry 6 }	

dbaRowStatus OBJECT-TYPE    
        SYNTAX   RowStatus
        MAX-ACCESS   read-write
        STATUS   current
        DESCRIPTION
            "RowStatus"
        ::= { dbaEntry 7 }
		
----------------------------------------------------------
------------------- ontSip table ------------------------
----------------------------------------------------------

-- ontSip table 1 
ontSipDialPlanTable    OBJECT-TYPE
	SYNTAX SEQUENCE OF OntSipDialPlanEntry
	MAX-ACCESS      not-accessible
	STATUS          current
	DESCRIPTION
		"ontVoIPTDialPlan table"
	::= {ontSip 1}

ontSipDialPlanEntry    OBJECT-TYPE
	SYNTAX          OntSipDialPlanEntry
	MAX-ACCESS      not-accessible
	STATUS          current
	DESCRIPTION
		"ontSipDialPlanEntry table"
	INDEX	{ oltIndex, ponIndex, ontIndex, ontVoIPDialPlanIndex }
	::= { ontSipDialPlanTable 1 }

OntSipDialPlanEntry	::= 
	SEQUENCE 
	{
	ontSipDialPlanID           INTEGER(1..10),
	ontSipDialPlanToken        OCTET STRING (SIZE(0..255)),
	ontSipDialPlanRowStatus    RowStatus
	}

ontSipDialPlanID     OBJECT-TYPE
	SYNTAX        INTEGER(1..10)
	MAX-ACCESS    read-only
	STATUS        current
	DESCRIPTION
		"ontSipDialPlanID:
		INTEGER<1-10>  id of dial plan <1-10>"
	::= { ontSipDialPlanEntry 1 }	

ontSipDialPlanToken    OBJECT-TYPE
	SYNTAX          OCTET STRING (SIZE(0..255))
	MAX-ACCESS      read-write
	STATUS          current
	DESCRIPTION
		"default: x.T   such as: [1-7]xxxxxxxxx#"
	::= { ontSipDialPlanEntry 2 }	

ontSipDialPlanRowStatus    OBJECT-TYPE    
	SYNTAX              RowStatus
	MAX-ACCESS          read-write
	STATUS              current
	DESCRIPTION
		"RowStatus"
	::= { ontSipDialPlanEntry 3 }
		
-- ontSip table 2 
ontSipProxyTable    OBJECT-TYPE
	SYNTAX SEQUENCE OF OntSipProxyEntry
	MAX-ACCESS   not-accessible
	STATUS       current
	DESCRIPTION
		"ontSipProxy table"
	::= {ontSip 2}

ontSipProxyEntry     OBJECT-TYPE
	SYNTAX        OntSipProxyEntry
	MAX-ACCESS    not-accessible
	STATUS        current
	DESCRIPTION
		"ontSipProxyEntry table"
	INDEX	{ oltIndex, ponIndex, ontIndex, ontVoIPProxyIndex }
	::= { ontSipProxyTable 1 }

OntSipProxyEntry	::= 
	SEQUENCE 
	{
	ontSipProxyID         INTEGER(1..2),
	ontSipProxyAddress    IpAddress,
	ontSipProxySignalPort        INTEGER(1..65535),
	ontSipProxyRowStatus         RowStatus
	}

ontSipProxyID     OBJECT-TYPE
	SYNTAX        INTEGER(1..2)
	MAX-ACCESS    read-only
	STATUS        current
	DESCRIPTION
		"ontSipProxyID:
        primary  primary = 1
        second   second  = 2"
	::= { ontSipProxyEntry 1 }	

ontSipProxyAddress    OBJECT-TYPE
	SYNTAX                IpAddress
    MAX-ACCESS            read-write
	STATUS                current
	DESCRIPTION
		"ontVoIPProxyAddress"
	::= { ontSipProxyEntry 2 }	

ontSipProxySignalPort    OBJECT-TYPE
	SYNTAX            INTEGER(1..65535)
	MAX-ACCESS        read-write
	STATUS            current
	DESCRIPTION
		"ontVoIPProxySignalPort"
	::= { ontSipProxyEntry 3 }	

ontSipProxyRowStatus    OBJECT-TYPE    
	SYNTAX           RowStatus
	MAX-ACCESS       read-write
	STATUS           current
	DESCRIPTION
		"RowStatus"
	::= { ontSipProxyEntry 4 }

-- ontSip table 3 
ontSipUserTableI    OBJECT-TYPE
	SYNTAX SEQUENCE OF OntSipUserEntryI
	MAX-ACCESS   not-accessible
	STATUS       current
	DESCRIPTION
		"ontVoIPTDialPlan table"
	::= {ontSip 3}

ontSipUserEntryI    OBJECT-TYPE
	SYNTAX       OntSipUserEntryI
	MAX-ACCESS   not-accessible
	STATUS       current
	DESCRIPTION
		"ontSipUserEntryI table"
	INDEX	{ oltIndex, ponIndex, ontIndex }
	::= { ontSipUserTableI 1 }

OntSipUserEntryI	::= 
	SEQUENCE 
	{
	ontSipUserIPaddress        IpAddress,
	ontSipUserIPaddressMask    IpAddress,
	ontSipUserVlan             INTEGER(1..4094),
	ontSipUserIPRowStatus      RowStatus
	}

ontSipUserIPaddress    OBJECT-TYPE
	SYNTAX          IpAddress
	MAX-ACCESS      read-write
	STATUS          current
	DESCRIPTION
		"ontSipUserIPaddress"
	::= { ontSipUserEntryI 1 }	

ontSipUserIPaddressMask    OBJECT-TYPE
	SYNTAX              IpAddress
	MAX-ACCESS          read-write
	STATUS              current
	DESCRIPTION
		"ontSipUserIPaddressMask"
	::= { ontSipUserEntryI 2 }	

ontSipUserVlan       OBJECT-TYPE
	SYNTAX        INTEGER(1..4094)
	MAX-ACCESS    read-write
	STATUS        current
	DESCRIPTION
		"ontSipUserVlan"
	::= { ontSipUserEntryI 3 }	

ontSipUserIPRowStatus    OBJECT-TYPE    
	SYNTAX           RowStatus
	MAX-ACCESS       read-write
	STATUS           current
	DESCRIPTION
		"RowStatus"
	::= { ontSipUserEntryI 4 }

-- ontSip table 4
ontSipUserTableII    OBJECT-TYPE
	SYNTAX SEQUENCE OF OntSipUserEntryII
	MAX-ACCESS    not-accessible
	STATUS        current
	DESCRIPTION
		"ontSipTDialPlan table"
	::= {ontSip 4}

ontSipUserEntryII    OBJECT-TYPE
	SYNTAX        OntSipUserEntryII
	MAX-ACCESS    not-accessible
	STATUS        current
	DESCRIPTION
		"ontSipUserEntryII table"
	INDEX	{ oltIndex, ponIndex, ontIndex, ontVoIPUserIndex }
	::= { ontSipUserTableII 1 }

OntSipUserEntryII	::= 
	SEQUENCE 
	{
	ontSipUserID                    INTEGER(1..2),
	ontSipUserName                  OCTET STRING (SIZE(0..255)),
	ontSipUserPassword              OCTET STRING (SIZE(0..255)),
	ontSipUserTelephoneNumber       OCTET STRING (SIZE(0..255)),
	ontSipUserNameRowStatus         RowStatus,
	ontSipUserTelephoneRowStatus    RowStatus
	}

ontSipUserID         OBJECT-TYPE
	SYNTAX        INTEGER(1..2)
	MAX-ACCESS    read-only
	STATUS        current
	DESCRIPTION
		"ontSipUserID:
		INTEGER<1-2>  user id <1-2>"
	::= { ontSipUserEntryII 1 }

ontSipUserName       OBJECT-TYPE
	SYNTAX        OCTET STRING (SIZE(0..255))
	MAX-ACCESS    read-write
	STATUS        current
	DESCRIPTION
		"ontSipUserName"
	::= { ontSipUserEntryII 2 }

ontSipUserPassword   OBJECT-TYPE
	SYNTAX        OCTET STRING (SIZE(0..255))
	MAX-ACCESS    read-write
	STATUS        current
	DESCRIPTION
		"ontSipUserPassword"
	::= { ontSipUserEntryII 3 }

ontSipUserTelephoneNumber    OBJECT-TYPE
	SYNTAX                OCTET STRING (SIZE(0..255))
	MAX-ACCESS            read-write
	STATUS                current
	DESCRIPTION
		"ontSipUserTelephoneNumber"
	::= { ontSipUserEntryII 4 }		

ontSipUserNameRowStatus    OBJECT-TYPE    
	SYNTAX            RowStatus
	MAX-ACCESS        read-write
	STATUS            current
	DESCRIPTION
		"RowStatus"
	::= { ontSipUserEntryII 5 }

ontSipUserTelephoneRowStatus    OBJECT-TYPE    
	SYNTAX            RowStatus
	MAX-ACCESS        read-write
	STATUS            current
	DESCRIPTION
		"RowStatus"
	::= { ontSipUserEntryII 6 }

--
-- oltPower table 
--

-- oltPower table
oltPowerTable    OBJECT-TYPE
	SYNTAX SEQUENCE OF OltPowerEntry
	MAX-ACCESS      not-accessible
	STATUS          current
	DESCRIPTION
		"oltPower Table"
	::= {oltPower 1}

oltPowerEntry    OBJECT-TYPE
	SYNTAX          OltPowerEntry
	MAX-ACCESS      not-accessible
	STATUS          current
	DESCRIPTION
		"oltPowerEntry table"
	INDEX	{ oltPowerIndex }
	::= { oltPowerTable 1 }

OltPowerEntry	::= 
	SEQUENCE 
	{
	oltPowerIndex        INTEGER(1..2),
	powerInsertState     INTEGER(0..1),
	powerRunningState    INTEGER(0..1)
	}

oltPowerIndex    OBJECT-TYPE
	SYNTAX                INTEGER(1..2)
	MAX-ACCESS            read-only
	STATUS                current
	DESCRIPTION
		"oltPowerIndex"
	::= { oltPowerEntry 1 }

powerInsertState    OBJECT-TYPE
	SYNTAX                INTEGER(0..1)
	MAX-ACCESS            read-only
	STATUS                current
	DESCRIPTION
		"INSERT = 1
         EMPTY  = 0"
	::= { oltPowerEntry 2 }
	
powerRunningState    OBJECT-TYPE
	SYNTAX                INTEGER(0..1)
	MAX-ACCESS            read-only
	STATUS                current
	DESCRIPTION
		"GOOD    = 1
         NO GOOD = 0"
	::= { oltPowerEntry 3 }

-- END 

END
