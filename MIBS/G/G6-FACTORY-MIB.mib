G6-FACTORY-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

device MODULE-IDENTITY --Category
	LAST-UPDATED "201505221059Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201505221059Z"
	DESCRIPTION
		"File creation"
	::= { g6 1 }

factory  OBJECT IDENTIFIER ::= { device 32 }



-- *************************** CONFIGURATION SECTION ********************************


factoryArticleNumber OBJECT-TYPE   -- article_number
	SYNTAX DisplayString
	MAX-ACCESS read-only
	STATUS current
	DESCRIPTION
	"This device article number."
	::= { factory 1 }


factorySerialNumber OBJECT-TYPE   -- serial_number
	SYNTAX DisplayString
	MAX-ACCESS read-only
	STATUS current
	DESCRIPTION
	"This device serial number."
	::= { factory 2 }


factoryDeviceMac OBJECT-TYPE   -- device_mac
	SYNTAX MacAddress
	MAX-ACCESS read-only
	STATUS current
	DESCRIPTION
	"This device MAC address."
	::= { factory 3 }


factoryNumberOfMacs OBJECT-TYPE   -- number_of_macs
	SYNTAX Integer32 (0..65535)
	MAX-ACCESS read-only
	STATUS current
	DESCRIPTION
	"Number of MAC addresses this device supports."
	::= { factory 4 }


factoryHardwareVersion OBJECT-TYPE   -- hardware_version
	SYNTAX DisplayString
	MAX-ACCESS read-only
	STATUS current
	DESCRIPTION
	"This device hardware revision number."
	::= { factory 5 }


factoryBoardId OBJECT-TYPE   -- board_id
	SYNTAX Unsigned32
	MAX-ACCESS read-only
	STATUS current
	DESCRIPTION
	"This identifies the basic hardware type for internal operation."
	::= { factory 6 }


factoryProjectNumber OBJECT-TYPE   -- project_number
	SYNTAX DisplayString
	MAX-ACCESS read-only
	STATUS current
	DESCRIPTION
	"Development project number."
	::= { factory 7 }


factoryMechanicalFeatures OBJECT-TYPE   -- mechanical_features
	SYNTAX BITS 
		{
		desktop (0),
		rail (1),
		ductVertical (2),
		ductHorizontal (3),
		rack (4),
		stackable (5),
		unused6 (6),
		unused7 (7),
		dc (8),
		ac (9),
		dualPwr (10),
		unused11 (11),
		extTemp (12),
		extSupply (13),
		exSecure (14),
		unused15 (15),
		unused16 (16),
		microSd (17),
		sdcard (18),
		internalMemory (19),
		unused20 (20),
		unused21 (21),
		ip30 (22),
		ip42 (23),
		ip44 (24),
		ip55 (25),
		ip67 (26),
		unused27 (27),
		unused28 (28),
		unused29 (29),
		unused30 (30),
		unused31 (31)
		}
	MAX-ACCESS read-only
	STATUS current
	DESCRIPTION
	"Bit mask which identifies mechanical features of this device."
	::= { factory 8 }


factoryHardwareFeatures OBJECT-TYPE   -- hardware_features
	SYNTAX BITS 
		{
		poePlus (0),
		poePse (1),
		poePd (2),
		unused3 (3),
		unused4 (4),
		unused5 (5),
		eee (6),
		synce (7),
		ms1588 (8),
		usb (9),
		relays (10),
		rtc (11),
		unused12 (12),
		unused13 (13),
		unused14 (14),
		csfp (15),
		sfp (16),
		lc (17),
		sc (18),
		st (19),
		e2000 (20),
		unused21 (21),
		unused22 (22),
		unused23 (23),
		unused24 (24),
		unused25 (25),
		unused26 (26),
		unused27 (27),
		unused28 (28),
		unused29 (29),
		unused30 (30),
		unused31 (31)
		}
	MAX-ACCESS read-only
	STATUS current
	DESCRIPTION
	"Bit mask which identifies installed hardware features of this device."
	::= { factory 9 }


factoryCompanyName OBJECT-TYPE   -- company_name
	SYNTAX DisplayString
	MAX-ACCESS read-only
	STATUS current
	DESCRIPTION
	"Complete name and address of the manufacturing company."
	::= { factory 10 }


factoryCompanyShort OBJECT-TYPE   -- company_short
	SYNTAX DisplayString
	MAX-ACCESS read-only
	STATUS current
	DESCRIPTION
	"Shorthand name of the manufacturing company."
	::= { factory 11 }


factoryWebLink OBJECT-TYPE   -- web_link
	SYNTAX DisplayString
	MAX-ACCESS read-only
	STATUS current
	DESCRIPTION
	"Link to company homepage."
	::= { factory 12 }


factoryWebDescription OBJECT-TYPE   -- web_description
	SYNTAX DisplayString
	MAX-ACCESS read-only
	STATUS current
	DESCRIPTION
	"Product feature summary."
	::= { factory 13 }


factoryCustomInfo OBJECT-TYPE   -- custom_info
	SYNTAX DisplayString
	MAX-ACCESS read-write
	STATUS current
	DESCRIPTION
	"This field can be used to permanently store custom inventory or location data. The data are stored within the device in unremovable storage and thus will persist even when the SD card or the entire configuration is changed."
	::= { factory 14 }



-- ****************************** STATUS SECTION ********************************



END
