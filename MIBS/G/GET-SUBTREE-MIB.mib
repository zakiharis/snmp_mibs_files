-- extracted from draft-irtf-nmrg-get-subtree-mib-01.txt
-- at Tue Dec  5 10:05:24 2000

GET-SUBTREE-MIB DEFINITIONS ::= BEGIN

IMPORTS
    MODULE-IDENTITY, OBJECT-TYPE,
    NOTIFICATION-TYPE, Unsigned32, mib-2,
    Counter32                 FROM SNMPv2-SMI
    RowStatus, TruthValue               FROM SNMPv2-TC
    MODULE-COMPLIANCE, OBJECT-GROUP,
    NOTIFICATION-GROUP                  FROM SNMPv2-CONF
    SnmpAdminString                     FROM SNMP-FRAMEWORK-MIB;


getSubtreeMIB MODULE-IDENTITY
    LAST-UPDATED "0010201200Z"
    ORGANIZATION "IRTF Network Management Research Group"
    CONTACT-INFO
            "Dave Thaler
             Microsoft Corporation
             One Microsoft Way
             Redmond, WA 98052-6399
             EMail: dthaler@microsoft.com

             Satyen Chandragiri
             Lucent Technologies, Inc.
             101 Crawfords Corner Road
             Holmdel, NJ 07733-3030
             EMail: satyen@lucent.com"
    DESCRIPTION
            "This MIB module provides the ability to retrieve
            arbitrary subtrees of OIDs (in parallel) by receiving
            traps."
    ::= { mib-2 1 }

getSubtreeMIBObjects OBJECT IDENTIFIER ::= { getSubtreeMIB 1 }

getSubtree       OBJECT IDENTIFIER ::= { getSubtreeMIBObjects 1 }
getSubtreeTraps      OBJECT IDENTIFIER ::= { getSubtreeMIBObjects 2 }

--
-- GetSubtree Root Table
--

getSubtreeRootTable OBJECT-TYPE
    SYNTAX     SEQUENCE OF GetSubtreeRootEntry
    MAX-ACCESS not-accessible
    STATUS     current
    DESCRIPTION
            "The (conceptual) table containing the root OID(s) of
            the MIB subtree(s) to be retrieved. Multiple rows with
            different values for getSubtreeRootOID may be created
            if the manager wishes to retrieve several subtrees
            simultaneously"
    ::= { getSubtree 1 }

getSubtreeRootEntry OBJECT-TYPE
    SYNTAX     GetSubtreeRootEntry
    MAX-ACCESS not-accessible
    STATUS     current
    DESCRIPTION
            "An entry (conceptual row) specifying the root OID of
            the MIB subtree to be retrieved"
    INDEX { getSubtreeRootOperationID, getSubtreeRootOIDIndex }
    ::=   { getSubtreeRootTable 1 }

GetSubtreeRootEntry ::= SEQUENCE {
    getSubtreeRootOperationID Unsigned32,
    getSubtreeRootOIDIndex    Unsigned32,
    getSubtreeRootOID         OBJECT IDENTIFIER,
    getSubtreeRootStatus RowStatus
}

getSubtreeRootOperationID OBJECT-TYPE
    SYNTAX          Unsigned32
    MAX-ACCESS      not-accessible
    STATUS          current
    DESCRIPTION
            "An integer uniquely identifying the GetSubtree
            operation in progress. This value should be randomly
            generated by a manager before attempting to create the
            row."
    ::= { getSubtreeRootEntry 1 }

getSubtreeRootOIDIndex OBJECT-TYPE
    SYNTAX          Unsigned32
    MAX-ACCESS      not-accessible
    STATUS          current
    DESCRIPTION
            "An index value used to associate various root OIDs
            with the same GetSubtree operation. This value should
            be one for the first entry associated with a
            particular retrieval operation and should be
            sequentially incremented for each additional entry."
    ::= { getSubtreeRootEntry 2 }

getSubtreeRootOID OBJECT-TYPE
    SYNTAX          OBJECT IDENTIFIER
    MAX-ACCESS      read-create
    STATUS          current
    DESCRIPTION
            "The root OID of the subtree to be retrieved."
    ::= { getSubtreeRootEntry 3 }

getSubtreeRootStatus OBJECT-TYPE
    SYNTAX     RowStatus
    MAX-ACCESS read-create
    STATUS     current
    DESCRIPTION
            "The status of this row. The manager should create one
            row for each subtree to be retrieved. After the entire
            subtree retrieval operation is completed (or if the
            operation is aborted by the user) all rows in this
            table corresponding to that operation are
            automatically deleted by the agent.

            Objects in this table cannot be modified while a
            GetSubtree retrieval operation is in progress."
    ::= { getSubtreeRootEntry 4 }


--
-- GetSubtree Control Table
--

getSubtreeControlTable OBJECT-TYPE
    SYNTAX          SEQUENCE OF GetSubtreeControlEntry
    MAX-ACCESS      not-accessible
    STATUS          current
    DESCRIPTION
            "The (conceptual) table used to control GetSubtree
            operations in progress. This table is used in
            conjunction with getSubtreeRootTable.

            A manager interested in retrieving a subtree of MIB
            objects must first create an entry in the
            getSubtreeRootTable specifying the root OID (s) of the
            subtree(s) to be retrieved. It must then make a
            corresponding entry in this table using the same
            getSubtreeRootOperationID value and identifying itself
            (via getSubtreeControlTarget) as the recipient of the
            traps.

            When the agent completes retrieval of all MIB
            instances within the specified subtree(s) this
            conceptual row will be automatically deleted."
    ::= { getSubtree 2 }

getSubtreeControlEntry OBJECT-TYPE
    SYNTAX          GetSubtreeControlEntry
    MAX-ACCESS      not-accessible
    STATUS          current
    DESCRIPTION
            "An entry (conceptual row) containing the information
            on a particular GetSubtree operation in progress."
    INDEX           { getSubtreeRootOperationID }
    ::= { getSubtreeControlTable 1 }

GetSubtreeControlEntry ::= SEQUENCE {
    getSubtreeControlTarget    SnmpAdminString,
    getSubtreeControlSeqNumber Counter32,
    getSubtreeControlCount     Counter32,
    getSubtreeControlDone      TruthValue,
    getSubtreeControlStatus    RowStatus
}

getSubtreeControlTarget OBJECT-TYPE
    SYNTAX          SnmpAdminString
    MAX-ACCESS      read-create
    STATUS          current
    DESCRIPTION
            "This object selects a management target defined in
            the snmpTargetAddrTable (in the SNMP-TARGET-MIB).  The
            selected target is defined by an entry in the
            snmpTargetAddrTable whose index value
            (snmpTargetAddrName) is equal to this object."
    ::= { getSubtreeControlEntry 2 }

getSubtreeControlSeqNumber OBJECT-TYPE
    SYNTAX          Counter32
    MAX-ACCESS      read-only
    STATUS          current
    DESCRIPTION
            "The number of trap responses previously sent for this
            GetSubtree request."
    ::= { getSubtreeControlEntry 3 }

getSubtreeControlCount OBJECT-TYPE
    SYNTAX          Counter32
    MAX-ACCESS      read-only
    STATUS          current
    DESCRIPTION
            "The number of repetitions transmitted thus far (up to
            and including those sent in the current trap)"
    ::= { getSubtreeControlEntry 4 }

getSubtreeControlDone OBJECT-TYPE
    SYNTAX          TruthValue
    MAX-ACCESS      read-only
    STATUS     current
    DESCRIPTION
            "This is set to true in the last trap sent, and is set
            to false otherwise."
    ::= { getSubtreeControlEntry 5 }

getSubtreeControlStatus OBJECT-TYPE
    SYNTAX          RowStatus
    MAX-ACCESS      read-create
    STATUS          current
    DESCRIPTION
            "The status of this row, by which new entries may be
            created, or old entries deleted from this table.  Once
            created, the row may be deleted, but other objects in
            the row may not be modified.  A row (and corresponding
            rows in the getSubtreeRootTable) will be deleted
            automatically by the agent once the operation has
            completed. A row may be created using an instance
            value for getSubtreeRootOperationID even if no entries
            exist in getSubtreeRootTable indexed by that value.

            Creating a row will cause the subtree retrieval
            operation to commence if there are entries in the
            getSubtreeRootTable indexed by the same value of
            getSubtreeRootOperationID as this row. If the agent
            allows aborting operations in progress, deleting a row
            will cause the operation to halt. If the operation is
            successfully aborted, the rows in the
            getSubtreeRootTable corresponding to this request will
            also be automatically deleted by the agent."
    ::= { getSubtreeControlEntry 6 }


-- traps

getSubtreeTrapPrefix OBJECT IDENTIFIER ::= { getSubtreeTraps 0 }

getSubtreeResponse NOTIFICATION-TYPE
    OBJECTS     {
                  getSubtreeControlSeqNumber,
                  getSubtreeControlCount,
                  getSubtreeControlDone
                }
    STATUS current
    DESCRIPTION
            "In addition to the three objects above, this trap
            also contains a series of varbinds containing the next
            chunk of the subtree.  The generating entity will
            append, in order, as many variables to the variable-
            bindings field as it can without exceeding the maximum
            message size, and without going beyond the subtree of
            OIDs requested.  A series of such traps will be
            generated until the end of the subtree is reached."
    ::= { getSubtreeTrapPrefix 1 }

-- conformance information

getSubtreeMIBConformance
                  OBJECT IDENTIFIER ::= { getSubtreeMIB 2 }
getSubtreeMIBCompliances
                  OBJECT IDENTIFIER ::= { getSubtreeMIBConformance 1 }
getSubtreeMIBGroups  OBJECT IDENTIFIER ::= { getSubtreeMIBConformance 2 }

-- compliance statements

getSubtreeMIBCompliance MODULE-COMPLIANCE
    STATUS  current
    DESCRIPTION
            "The compliance statement for the GetSubtree MIB."
    MODULE  -- this module
    MANDATORY-GROUPS {
            getSubtreeObjectGroup,
            getSubtreeNotificationGroup
                     }
   ::= { getSubtreeMIBCompliances 1 }

-- units of conformance

getSubtreeObjectGroup OBJECT-GROUP
    OBJECTS     {
                  getSubtreeRootOID,
                  getSubtreeRootStatus,
                  getSubtreeControlTarget,
                  getSubtreeControlSeqNumber,
                  getSubtreeControlCount,
                  getSubtreeControlDone,
                  getSubtreeControlStatus
                }
    STATUS  current
    DESCRIPTION
            "A collection of objects to support requests for
            subtree retrieval operations."
    ::= { getSubtreeMIBGroups 1 }

getSubtreeNotificationGroup NOTIFICATION-GROUP
    NOTIFICATIONS { getSubtreeResponse }
    STATUS  current
    DESCRIPTION
            "The notification which an entity is required to
            implement."
    ::= { getSubtreeMIBGroups 2 }

END

-- 
-- Copyright (C) The Internet Society (2000). All Rights Reserved.
-- 
-- This document and translations of it may be copied and furnished
-- to others, and derivative works that comment on or otherwise
-- explain it or assist in its implmentation may be prepared, copied,
-- published and distributed, in whole or in part, without
-- restriction of any kind, provided that the above copyright notice
-- and this paragraph are included on all such copies and derivative
-- works. However, this document itself may not be modified in any
-- way, such as by removing the copyright notice or references to the
-- Internet Society or other Internet organizations, except as needed
-- for the purpose of developing Internet standards in which case the
-- procedures for copyrights defined in the Internet Standards
-- process must be followed, or as required to translate it into
-- languages other than English.
-- 
-- The limited permissions granted above are perpetual and will not
-- be revoked by the Internet Society or its successors or assigns.
-- 
-- This document and the information contained herein is provided on
-- an "AS IS" basis and THE INTERNET SOCIETY AND THE INTERNET
-- ENGINEERING TASK FORCE DISCLAIMS ALL WARRANTIES, EXPRESS OR
-- IMPLIED, INCLUDING BUT NOT LIMITED TO ANY WARRANTY THAT THE USE OF
-- THE INFORMATION HEREIN WILL NOT INFRINGE ANY RIGHTS OR ANY IMPLIED
-- WARRANTIES OF MERCHANTABILITY OR FITNESS FOR A PARTICULAR PURPOSE.
