-- extracted from draft-ietf-adslmib-gbond-eth-mib-00.txt
-- at Thu Jun  7 06:08:24 2007

   GBOND-ETH-MIB DEFINITIONS ::= BEGIN

     IMPORTS
       MODULE-IDENTITY, OBJECT-TYPE, Counter32
         FROM SNMPv2-SMI         -- RFC 2578
       TEXTUAL-CONVENTION
         FROM SNMPv2-TC          -- RFC 2579
       MODULE-COMPLIANCE, OBJECT-GROUP
         FROM SNMPv2-CONF        -- RFC 2580
       ifIndex
         FROM IF-MIB             -- RFC 2863
       gBondMIB
         FROM GBOND-MIB          -- RFC YYYY
         -- EdNote: Replace YYYY with the actual RFC number &
         -- remove this note
       ;

     gBondEthMIB MODULE-IDENTITY
       LAST-UPDATED "200706050000Z"  -- June 05, 2007
       ORGANIZATION "IETF ADSL MIB Working Group"
       CONTACT-INFO
         "WG charter:
           http://www.ietf.org/html.charters/adslmib-charter.html

         Mailing Lists:
           General Discussion: adslmib@ietf.org
           To Subscribe: adslmib-request@ietf.org
           In Body: subscribe your_email_address

          Chair: Menachem Dodge
         Postal: ECI Telecom, Ltd.
                 30 Hasivim St.,
                 Petach-Tikva 49517
                 Israel
          Phone: +972-3-926-8421
          EMail: menachem.dodge@ecitele.com

         Editor: Edward Beili
         Postal: Actelis Networks, Inc.
                 25 Bazel St., P.O.B. 10173
                 Petach-Tikva 10173
                 Israel
          Phone: +972-3-924-3491
          EMail: edward.beili@actelis.com

         Editor: Moti Morgenstern
         Postal: ECI Telecom
                 30 Hasivim St.
                 Petach-Tikva 49517
                 Israel
          Phone: +972-3-926-6258
          EMail: moti.morgenstern@ecitele.com"

       DESCRIPTION
         "The objects in this MIB module are used to manage the
         Ethernet-based multi-pair bonded xDSL Interfaces, defined in
         ITU-T recommendation G.998.2 (G.Bond/Ethernet).
         This MIB module MUST be used in conjunction with GBOND-MIB
         module, common to all G.Bond technologies.

         The following references are used throughout this MIB module:

         [G.998.2] refers to:
           ITU-T Recommendation G.998.2: 'Ethernet-based multi-pair
           bonding', January 2005.

         [802.3] refers to:
           IEEE Std 802.3-2005: 'IEEE Standard for Information
           technology - Telecommunications and information exchange
           between systems - Local and metropolitan area networks -
           Specific requirements -
           Part 3: Carrier Sense Multiple Access with Collision
           Detection (CSMA/CD) Access Method and Physical Layer
           Specifications', December 2005.

         [WT-159] refers to:
           DSL Forum Technical Report: 'Management Framework for xDSL
           Bonding', May 2007.

         Naming Conventions:
           BCE    - Bonding Channel Entity
           CO     - Central Office
           CPE    - Customer Premises Equipment
           GBS    - Generic Bonding Sublayer
           HDLC   - High-level Data Link Control
           PTM-TC - Packet Transfer Mode Transmission Convergence
                    (sub-layer)
           SNR    - Signal to Noise Ratio
           TC     - Transmission Convergence (sub-layer)

         Copyright (C) The Internet Society (2007). This version of this
         MIB module is part of RFC XXXX;  see the RFC itself for full
         legal notices."

       REVISION    "200706050000Z"  -- June 05, 2007
       DESCRIPTION "Initial version, published as RFC XXXX."

         -- EdNote: Replace XXXX with the actual RFC number &
         -- remove this note

       ::= { gBondMIB 2 }

      -- Sections of the module
      -- Structured as recommended by RFC 4181, Appendix D
      gBondEthObjects     OBJECT IDENTIFIER ::= { gBondEthMIB 1 }

      gBondEthConformance OBJECT IDENTIFIER ::= { gBondEthMIB 2 }

      -- Groups in the module

      gBondEthPort        OBJECT IDENTIFIER ::= { gBondEthObjects 1 }

      gBondEthBce         OBJECT IDENTIFIER ::= { gBondEthObjects 2 }

      -- Textual Conventions

      GBondEthPtmTcType ::= TEXTUAL-CONVENTION
        STATUS       current
        DESCRIPTION
          "This textual convention represents possible PTM-TC types in
          G.bond/Eth ports. The following values are defined:
            tc6465         - 64/65-octet encapsulation, as defined in
                             [802.3] Clause 61.3.3
            tcHDLC         - HDLC encapsulation, as defined in [G.998.2]
                             Annex B"
        SYNTAX      INTEGER {
          tc6465(1),
          tcHDLC(2)
        }

      -- GBS Notifications group
        -- empty --

      -- GBS group

      gBondEthPortConfTable OBJECT-TYPE
        SYNTAX      SEQUENCE OF GBondEthPortConfEntry
        MAX-ACCESS  not-accessible
        STATUS      current
        DESCRIPTION
          "Table for Configuration of G.Bond/Eth GBS ports. Entries in
          this table MUST be maintained in a persistent manner"
        ::= { gBondEthPort 1 }

      gBondEthPortConfEntry OBJECT-TYPE
        SYNTAX      GBondEthPortConfEntry
        MAX-ACCESS  not-accessible
        STATUS      current
        DESCRIPTION
          "An entry in the G.Bond/Eth Port Configuration table.
          Each entry represents an G.Bond Ethernet port indexed by the
          ifIndex.
          Note that an G.Bond/Eth GBS port runs on top of a single
          or multiple BCE port(s), which are also indexed by ifIndex."
        INDEX  { ifIndex }
        ::= { gBondEthPortConfTable 1 }

      GBondEthPortConfEntry ::=
        SEQUENCE {
          gBondEthTcAdminType         GBondEthPtmTcType
        }

      gBondEthTcAdminType  OBJECT-TYPE
        SYNTAX      GBondEthPtmTcType
        MAX-ACCESS  read-write
        STATUS      current
        DESCRIPTION
          "Administrative (desired) PTM-TC encapsulation type of
          G.Bond/Eth port (GBS).
          Possible values are:
            tc6465(1)  - 64/65-octet encapsulation
            tcHDLC(2)  - HDLC encapsulation
          Attempts to set a port to a non-supported PTM-TC encapsulation
          type (see gBondEthTcTypesSupported) SHALL be rejected.

          Changing gBondEthTcAdminType is a traffic disruptive
          operation and as such SHALL be done when the link is Down.
          Attempts to cange this object SHALL be rejected if the link
          is Up or Initializing.

          This object maps to the WT-159 attribute aEthTcAdminType.

          This object MUST be maintained in a persistent manner."
        REFERENCE
          "[WT-159] 5.5.3.1"
        ::= { gBondEthPortConfEntry 1 }


      gBondEthPortCapabilityTable OBJECT-TYPE
        SYNTAX      SEQUENCE OF GBondEthPortCapabilityEntry
        MAX-ACCESS  not-accessible
        STATUS      current
        DESCRIPTION
          "Table for Capabilities of G.Bond/Eth Ports. Entries in this
          table MUST be maintained in a persistent manner"
        ::= { gBondEthPort 2 }

      gBondEthPortCapabilityEntry OBJECT-TYPE
        SYNTAX      GBondEthPortCapabilityEntry
        MAX-ACCESS  not-accessible
        STATUS      current
        DESCRIPTION
          "An entry in the G.Bond/Eth Port Capability table.
          Each entry represents an G.Bond port indexed by the ifIndex.
          Note that a G.Bond GBS port runs on top of a single
          or multiple BCE port(s), which are also indexed by ifIndex."
        INDEX  { ifIndex }
        ::= { gBondEthPortCapabilityTable 1 }

      GBondEthPortCapabilityEntry ::=
        SEQUENCE {
          gBondEthTcTypesSupported         BITS
        }

      gBondEthTcTypesSupported  OBJECT-TYPE
        SYNTAX      BITS {
          tc6465(0),
          tcHDLC(1)
        }
        MAX-ACCESS  read-only
        STATUS      current
        DESCRIPTION
          "PTM-TC Encapsulation types supported by the G.Bond/Eth port.
          This is a bitmap of possible encapsulation types. The various
          bit positions are:
            tc6465   - GBS is capable of 64/65-octet encapsulation
            tcHDLC   - GBS is capable of HDLC encapsulation

          A desired encapsulation is determined by
          gBondEthTcAdminType, while gBondEthTcOperType reflects the
          current operating mode.

          This object maps to the WT-159 attribute
          aEthTcTypesSupported."
        REFERENCE
          "[WT-159] 5.5.3.3"
        ::= { gBondEthPortCapabilityEntry 1 }


      gBondEthPortStatusTable OBJECT-TYPE
        SYNTAX      SEQUENCE OF GBondEthPortStatusEntry
        MAX-ACCESS  not-accessible
        STATUS      current
        DESCRIPTION
          "This table provides overall status information of G.Bond
          ports, complementing the generic status information from the
          ifTable of IF-MIB. Additional status information about
          connected BCEs is available from the relevant line MIBs
          This table contains live data from the equipment. As such,
          it is NOT persistent."
        ::= { gBondEthPort 3 }

      gBondEthPortStatusEntry OBJECT-TYPE
        SYNTAX      GBondEthPortStatusEntry
        MAX-ACCESS  not-accessible
        STATUS      current
        DESCRIPTION
          "An entry in the G.Bond/Eth Port Status table.
          Each entry represents an G.Bond/Eth port indexed by the
          ifIndex.
          Note that an G.Bond GBS port runs on top of a single
          or multiple BCE port(s), which are also indexed by ifIndex."
        INDEX  { ifIndex }
        ::= { gBondEthPortStatusTable 1 }

      GBondEthPortStatusEntry ::=
        SEQUENCE {
          gBondEthTcOperType            GBondEthPtmTcType,
          gBondEthInErrors              Counter32,
          gBondEthInSmallFragments      Counter32,
          gBondEthInLargeFragments      Counter32,
          gBondEthInBadFragments        Counter32,
          gBondEthInLostFragments       Counter32,
          gBondEthInLostStarts          Counter32,
          gBondEthInLostEnds            Counter32,
          gBondEthInOverflows           Counter32
        }

      gBondEthTcOperType  OBJECT-TYPE
        SYNTAX      GBondEthPtmTcType
        MAX-ACCESS  read-only
        STATUS      current
        DESCRIPTION
          "Current operational encapsulation type of the G.Bond/Eth
          port.
          Possible values are:
            tc6465(1)   - GBS uses 64/65-octet encapsulation
            tcHDLC(2)   - GBS uses HDLC encapsulation

          The operational PTM-TC encapsulation type can be configured
          via gBondEthTcAdminType variable.

          This objects maps to the WT-159 aEthTcOperType."
        REFERENCE
          "[WT-159] 5.5.3.2"
        ::= { gBondEthPortStatusEntry 1 }

      gBondEthInErrors OBJECT-TYPE
        SYNTAX      Counter32
        MAX-ACCESS  read-only
        STATUS      current
        DESCRIPTION
          "A number of fragments that have been received across the
          gamma interface and discarded.

          This object maps to the WT-159 attribute aEthRxErrors.

          Discontinuities in the value of this counter can occur at
          re-initialization of the management system, and at other times
          as indicated by the value of ifCounterDiscontinuityTime,
          defined in IF-MIB."
        REFERENCE
          "[WT-159] 5.5.3.4"
        ::= { gBondEthPortStatusEntry 2 }

      gBondEthInSmallFragments OBJECT-TYPE
        SYNTAX      Counter32
        MAX-ACCESS  read-only
        STATUS      current
        DESCRIPTION
          "A number of fragments smaller than minFragmentSize
          (64 Bytes), that have been received across the gamma
          interface and discarded.

          This object maps to the WT-159 attribute aEthRxSmallFragments.

          Discontinuities in the value of this counter can occur at
          re-initialization of the management system, and at other times
          as indicated by the value of ifCounterDiscontinuityTime,
          defined in IF-MIB."
        REFERENCE
          "[WT-159] 5.5.3.5"
        ::= { gBondEthPortStatusEntry 3 }

      gBondEthInLargeFragments OBJECT-TYPE
        SYNTAX      Counter32
        MAX-ACCESS  read-only
        STATUS      current
        DESCRIPTION
          "A number of fragments larger than maxFragmentSize
          (512 Bytes), which have been received across the gamma
          interface and discarded.

          This object maps to the WT-159 attribute aEthRxLargeFragments.
          Discontinuities in the value of this counter can occur at
          re-initialization of the management system, and at other times
          as indicated by the value of ifCounterDiscontinuityTime,
          defined in IF-MIB."
        REFERENCE
          "[WT-159] 5.5.3.6"
        ::= { gBondEthPortStatusEntry 4 }

      gBondEthInBadFragments OBJECT-TYPE
        SYNTAX      Counter32
        MAX-ACCESS  read-only
        STATUS      current
        DESCRIPTION
          "A number of fragments which do not fit into the sequence
          expected by the frame assembly function, that have been
          received across the gamma interface and discarded (the
          frame buffer is flushed to the next valid frame start).

          This object maps to the WT-159 attribute aEthRxBadFragments.

          Discontinuities in the value of this counter can occur at
          re-initialization of the management system, and at other times
          as indicated by the value of ifCounterDiscontinuityTime,
          defined in IF-MIB."
        REFERENCE
          "[WT-159] 5.5.3.7"
        ::= { gBondEthPortStatusEntry 5 }

      gBondEthInLostFragments OBJECT-TYPE
        SYNTAX      Counter32
        MAX-ACCESS  read-only
        STATUS      current
        DESCRIPTION
          "A number of gaps in the sequence of fragments, which have
          been received across the gamma interface (the frame buffer is
          flushed to the next valid frame start, when fragment/fragments
          expected by the frame assembly function is/are not received).

          This object maps to the WT-159 attribute aEthRxLostFragments.

          Discontinuities in the value of this counter can occur at
          re-initialization of the management system, and at other times
          as indicated by the value of ifCounterDiscontinuityTime,
          defined in IF-MIB."
        REFERENCE
          "[WT-159] 5.5.3.8"
        ::= { gBondEthPortStatusEntry 6 }

      gBondEthInLostStarts OBJECT-TYPE
        SYNTAX      Counter32
        MAX-ACCESS  read-only
        STATUS      current
        DESCRIPTION
          "A number of missing StartOfPacket indicators expected by the
          frame assembly function.

          This object maps to the WT-159 attribute aEthRxLostStarts.

          Discontinuities in the value of this counter can occur at
          re-initialization of the management system, and at other times
          as indicated by the value of ifCounterDiscontinuityTime,
          defined in IF-MIB."
        REFERENCE
          "[WT-159] 5.5.3.9"
        ::= { gBondEthPortStatusEntry 7 }

      gBondEthInLostEnds OBJECT-TYPE
        SYNTAX      Counter32
        MAX-ACCESS  read-only
        STATUS      current
        DESCRIPTION
          "A number of missing EndOfPacket indicators expected by the
          frame assembly function.

          This object maps to the WT-159 attribute aEthRxLostEnds.

          Discontinuities in the value of this counter can occur at
          re-initialization of the management system, and at other times
          as indicated by the value of ifCounterDiscontinuityTime,
          defined in IF-MIB."
        REFERENCE
          "[WT-159] 5.5.3.10"
        ::= { gBondEthPortStatusEntry 8 }

      gBondEthInOverflows OBJECT-TYPE
        SYNTAX      Counter32
        MAX-ACCESS  read-only
        STATUS      current
        DESCRIPTION
          "A number of fragments, received across the gamma interface
          and discarded, which would have caused the frame assembly
          buffer to overflow.

          This object maps to the WT-159 attribute aEthRxOverflows.

          Discontinuities in the value of this counter can occur at
          re-initialization of the management system, and at other times
          as indicated by the value of ifCounterDiscontinuityTime,
          defined in IF-MIB."
        REFERENCE
          "[WT-159] 5.5.3.11"
        ::= { gBondEthPortStatusEntry 9 }

     -- BCE group

      gBondEthBceStatusTable OBJECT-TYPE
        SYNTAX      SEQUENCE OF GBondEthBceStatusEntry
        MAX-ACCESS  not-accessible
        STATUS      current
        DESCRIPTION
          "This table provides common status information of G.Bond/Eth
          BCE ports.

          This table contains live data from the equipment. As such,
          it is NOT persistent."
        ::= { gBondEthBce 1 }

      gBondEthBceStatusEntry OBJECT-TYPE
        SYNTAX      GBondEthBceStatusEntry
        MAX-ACCESS  not-accessible
        STATUS      current
        DESCRIPTION
          "An entry in the G.Bond/Eth BCE Status table.
          Each entry represents common aspects of a G.Bond/Eth BCE port
          indexed by the ifIndex. Note that a BCE port can be stacked
          below a single GBS port, also indexed by ifIndex,
          possibly together with other BCE ports."
        INDEX  { ifIndex }
        ::= { gBondEthBceStatusTable 1 }

      GBondEthBceStatusEntry ::=
        SEQUENCE {
          gBondEthBceTcInCodingErrors        Counter32,
          gBondEthBceTcInCrcErrors           Counter32
        }

      gBondEthBceTcInCodingErrors OBJECT-TYPE
        SYNTAX      Counter32
        MAX-ACCESS  read-only
        STATUS      current
        DESCRIPTION
          "A number of PTM-TC encapsulation errors. This counter is
          incremented for each encapsulation error detected by the
          PTM-TC receive function.
          This object maps to WT-159 attribute
          aChannelPtmTcRxCodingViolations.

          Discontinuities in the value of this counter can occur at
          re-initialization of the management system, and at other times
          as indicated by the value of ifCounterDiscontinuityTime,
          defined in IF-MIB."
        REFERENCE
          "[WT-159] 5.5.7.5"
        ::= { gBondEthBceStatusEntry 1 }

      gBondEthBceTcInCrcErrors OBJECT-TYPE
        SYNTAX      Counter32
        MAX-ACCESS  read-only
        STATUS      current
        DESCRIPTION
          "A number of PTM-TC CRC errors. This counter is incremented
          for each CRC error detected by the PTM-TC receive function.

          This object maps to WT-159 attribute aChannelPtmTcRxCrcErrors.

          Discontinuities in the value of this counter can occur at
          re-initialization of the management system, and at other times
          as indicated by the value of ifCounterDiscontinuityTime,
          defined in IF-MIB."
        REFERENCE
          "[WT-159] 5.5.7.6"
        ::= { gBondEthBceStatusEntry 2 }


     --
     -- Conformance Statements
     --

      gBondEthGroups      OBJECT IDENTIFIER
        ::= { gBondEthConformance 1 }

      gBondEthCompliances OBJECT IDENTIFIER
        ::= { gBondEthConformance 2 }

      -- Object Groups

      gBondEthBasicGroup OBJECT-GROUP
        OBJECTS {
          gBondEthTcTypesSupported,
          gBondEthTcAdminType,
          gBondEthTcOperType,
          gBondEthInErrors,
          gBondEthInSmallFragments,
          gBondEthInLargeFragments,
          gBondEthInBadFragments,
          gBondEthInLostFragments,
          gBondEthInLostStarts,
          gBondEthInLostEnds,
          gBondEthInOverflows,
          gBondEthBceTcInCodingErrors,
          gBondEthBceTcInCrcErrors
        }
        STATUS      current
        DESCRIPTION
          "A collection of objects representing management information
          for G.Bond/Eth GBS ports."
        ::= { gBondEthGroups 1 }

      gBondEthBceGroup OBJECT-GROUP
        OBJECTS {
          gBondEthBceTcInCodingErrors,
          gBondEthBceTcInCrcErrors
        }
        STATUS      current
        DESCRIPTION
          "A collection of objects representing OPTIONAL management
          information for G.Bond/Eth BCE ports."
        ::= { gBondEthGroups 2 }

     -- Compliance Statements

      gBondEthCompliance MODULE-COMPLIANCE
        STATUS      current
        DESCRIPTION
          "The compliance statement for G.Bond Ethernet interfaces.
          Compliance with the following external compliance statements
          is REQUIRED:

          MIB Module             Compliance Statement
          ----------             --------------------
          IF-MIB                 ifCompliance3
          GBOND-MIB              gBondCompliance"

        MODULE  -- this module
          MANDATORY-GROUPS {
            gBondEthBasicGroup
          }

          GROUP       gBondEthBceGroup
          DESCRIPTION
            "Support for this group is OPTIONAL"

          OBJECT      gBondEthTcTypesSupported
          SYNTAX      BITS {
            tc6465(0),
            tcHDLC(1)
          }
          DESCRIPTION
            "Support for all TC types is not required. However at least
            one value SHALL be supported"

          OBJECT      gBondEthTcAdminType
          MIN-ACCESS  read-only
          DESCRIPTION
            "Write access is not required (needed only for GBS
            supporting more than a single TC encapsulation type, i.e.
            tc6465 and tcHDLC"

        ::= { gBondEthCompliances 1 }
   END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
