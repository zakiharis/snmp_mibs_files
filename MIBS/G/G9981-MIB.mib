G9981-MIB DEFINITIONS ::= BEGIN

  IMPORTS
    MODULE-IDENTITY,
    OBJECT-TYPE,
    NOTIFICATION-TYPE,
    mib-2,
    Unsigned32,
    Counter32
      FROM SNMPv2-SMI           -- RFC 2578
    TEXTUAL-CONVENTION,
    TruthValue
      FROM SNMPv2-TC            -- RFC 2579
    MODULE-COMPLIANCE,
    OBJECT-GROUP,
    NOTIFICATION-GROUP
      FROM SNMPv2-CONF          -- RFC 2580
    ifIndex
      FROM IF-MIB               -- RFC 2863
    HCPerfCurrentCount,
    HCPerfIntervalCount,
    HCPerfValidIntervals,
    HCPerfInvalidIntervals,
    HCPerfTimeElapsed
      FROM  HC-PerfHist-TC-MIB  -- RFC 3705
    ;
------------------------------------------------------------------------
  g9981MIB MODULE-IDENTITY
    LAST-UPDATED "201302200000Z"  -- 20 February 2013
    ORGANIZATION "IETF ADSL MIB Working Group"
    CONTACT-INFO
      "WG charter:
        http://datatracker.ietf.org/wg/adslmib/charter/

      Mailing Lists:
        General Discussion: adslmib@ietf.org
        To Subscribe: adslmib-request@ietf.org
        In Body: subscribe your_email_address

       Chair: Menachem Dodge
      Postal: ECI Telecom, Ltd.
              30 Hasivim St.,
              Petach-Tikva 4951169
              Israel
       Phone: +972-3-926-8421
       EMail: menachemdodge1@gmail.com

      Editor: Edward Beili
      Postal: Actelis Networks, Inc.
              25 Bazel St., P.O.B. 10173
              Petach-Tikva 49103
              Israel
       Phone: +972-3-924-3491
       EMail: edward.beili@actelis.com"
    DESCRIPTION
      "The objects in this MIB module are used to manage the
      multi-pair bonded xDSL interfaces using ATM inverse
      multiplexing, as defined in ITU-T Recommendation G.998.1
      (G.Bond/ATM).

      This MIB module MUST be used in conjunction with the GBOND-MIB
      module, common to all G.Bond technologies.

      The following references are used throughout this MIB module:

      [G.998.1] refers to:
        ITU-T Recommendation G.998.1: 'ATM-based multi-pair bonding',
        January 2005.

      [TR-159] refers to:
        Broadband Forum Technical Report: 'Management Framework for
        xDSL Bonding', December 2008.

      Naming Conventions:
        ATM   - Asynchronous Transfer Mode
        BCE   - Bonding Channel Entity
        BTU   - Bonding Terminating Unit
        CO    - Central Office
        CPE   - Customer Premises Equipment
        GBS   - Generic Bonding Sub-layer
        GBS-C - Generic Bonding Sub-layer, CO side
        GBS-R - Generic Bonding Sub-layer, RT (or CPE) side
        PM    - Performance Monitoring
        RT    - Remote Terminal

        SNR   - Signal to Noise Ratio
        SES   - Severely Errored Seconds
        UAS   - Unavailable Seconds

     Copyright (c) 2013 IETF Trust and the persons identified as
     authors of the code.  All rights reserved.

     Redistribution and use in source and binary forms, with or without
     modification, is permitted pursuant to, and subject to the license
     terms contained in, the Simplified BSD License set forth in Section
     4.c of the IETF Trust's Legal Provisions Relating to IETF Documents
     (http://trustee.ietf.org/license-info)."

    REVISION    "201302200000Z"  -- 20 February 2013
    DESCRIPTION "Initial version, published as RFC 6768."
    ::= { mib-2 208 }

   -- Sections of the module
   -- Structured as recommended by RFC 4181, Appendix D

   g9981Objects     OBJECT IDENTIFIER ::= { g9981MIB 1 }

   g9981Conformance OBJECT IDENTIFIER ::= { g9981MIB 2 }

   -- Groups in the module

   g9981Port        OBJECT IDENTIFIER ::= { g9981Objects 1 }

   -- Textual Conventions

   MilliSeconds ::= TEXTUAL-CONVENTION
     DISPLAY-HINT "d"
     STATUS      current
     DESCRIPTION
       "Represents time unit value in milliseconds."
     SYNTAX      Unsigned32

   -- Port Notifications group

   g9981PortNotifications OBJECT IDENTIFIER
     ::= { g9981Port 0 }

   g9981UpDiffDelayToleranceExceeded NOTIFICATION-TYPE
     OBJECTS {
       -- ifIndex is not needed here, since we are under specific GBS
       g9981PortConfUpDiffDelayTolerance,
       g9981PortStatMaxUpDiffDelay
     }
     STATUS      current
     DESCRIPTION
       "This notification indicates that the maximum upstream
       differential delay has exceeded the max upstream differential
       delay threshold, specified by
       g9981PortConfUpDiffDelayTolerance.

       This notification MAY be sent for the GBS-C ports while the
       port is 'up', on the crossing event in both directions: from
       normal (diff. delay is above the threshold) to low (diff.
       delay equals the threshold or is below it) and from low to
       normal.  This notification is not applicable to the GBS-R
       ports.

       Generation of this notification is controlled by the
       g9981PortConfDiffDelayToleranceExceededEnable attribute.

       This object maps to the TR-159 notification
       nIMAUpDiffDelayToleranceExceeded."
     REFERENCE
       "[TR-159], Section 5.5.2.8"
     ::= { g9981PortNotifications 1 }

   g9981DnDiffDelayToleranceExceeded NOTIFICATION-TYPE
     OBJECTS {
       -- ifIndex is not needed here, since we are under specific GBS
       g9981PortConfDnDiffDelayTolerance,
       g9981PortStatMaxDnDiffDelay
     }
     STATUS      current
     DESCRIPTION
       "This notification indicates that the maximum downstream
       differential delay has exceeded the max downstream
       differential delay threshold, specified by
       g9981PortConfDnDiffDelayTolerance.

       This notification MAY be sent for the GBS-C ports while the
       port is 'up', on the crossing event in both directions: from
       normal (diff. delay is above the threshold) to low (diff.
       delay equals the threshold or is below it) and from low to
       normal.  This notification is not applicable to the GBS-R
       ports.

       Generation of this notification is controlled by the
       g9981PortConfDiffDelayToleranceExceededEnable attribute.

       This object maps to the TR-159 notification
       nIMADownDiffDelayToleranceExceeded."
     REFERENCE
       "[TR-159], Section 5.5.2.9"
     ::= { g9981PortNotifications 2 }

   -- G.Bond/ATM Port group

   g9981PortConfTable OBJECT-TYPE
     SYNTAX      SEQUENCE OF G9981PortConfEntry
     MAX-ACCESS  not-accessible
     STATUS      current
     DESCRIPTION
       "Table for configuration of G.Bond/ATM ports.  Entries in
       this table MUST be maintained in a persistent manner."
     ::= { g9981Port 1 }

   g9981PortConfEntry OBJECT-TYPE
     SYNTAX      G9981PortConfEntry
     MAX-ACCESS  not-accessible
     STATUS      current
     DESCRIPTION
       "An entry in the G.Bond/ATM Port Configuration table.
       Each entry represents a G.Bond/ATM port indexed by the
       ifIndex.  Additional configuration parameters are available
       via the gBondPortConfEntry of the GBOND-MIB.
       Note that a G.Bond/ATM port runs on top of a single or
       multiple BCE port(s), which are also indexed by the ifIndex."
     INDEX  { ifIndex }
     ::= { g9981PortConfTable 1 }

   G9981PortConfEntry ::=
     SEQUENCE {
       g9981PortConfUpDiffDelayTolerance             MilliSeconds,
       g9981PortConfDnDiffDelayTolerance             MilliSeconds,
       g9981PortConfDiffDelayToleranceExceededEnable TruthValue
     }

   g9981PortConfUpDiffDelayTolerance  OBJECT-TYPE
     SYNTAX      MilliSeconds (0..2047)
     UNITS       "milliseconds"
     MAX-ACCESS  read-write
     STATUS      current
     DESCRIPTION
       "A maximum tolerated upstream differential delay (among
       the member BCEs) of a G.Bond/ATM port, expressed in ms.

       This object is read-write for the GBS-C ports.
       It is irrelevant for the GBS-R ports -- an attempt to read or
       change this object MUST be rejected (in the case of SNMP, with
       the error inconsistentValue).

       This object maps to the TR-159 attribute
       aIMAUpDiffDelayTolerance."
     REFERENCE
       "[TR-159], Section 5.5.2.5; [G.998.1], Section 11.4.1 (6)"
     ::= { g9981PortConfEntry 1 }

   g9981PortConfDnDiffDelayTolerance  OBJECT-TYPE
     SYNTAX      MilliSeconds (0..2047)
     UNITS       "milliseconds"
     MAX-ACCESS  read-write
     STATUS      current
     DESCRIPTION
       "A maximum tolerated downstream differential delay (among
       the member BCEs) of a G.Bond/ATM port, expressed in ms.

       This object is read-write for the GBS-C ports.
       It is irrelevant for the GBS-R ports -- an attempt to read or
       change this object MUST be rejected (in the case of SNMP, with
       the error inconsistentValue).

       This object maps to the TR-159 attribute
       aIMADownDiffDelayTolerance."
     REFERENCE
       "[TR-159], Section 5.5.2.6; [G.998.1], Section 11.4.1 (6)"
     ::= { g9981PortConfEntry 2 }

   g9981PortConfDiffDelayToleranceExceededEnable  OBJECT-TYPE
     SYNTAX      TruthValue
     MAX-ACCESS  read-write
     STATUS      current
     DESCRIPTION
       "Indicates whether g9981UpDiffDelayToleranceExceeded and
       g9981DnDiffDelayToleranceExceeded notifications should
       be generated for G.Bond/ATM port.

       A value of true(1) indicates that the notifications are enabled.
       A value of false(2) indicates that the notifications are
       disabled.

       This object is read-write for the GBS-C.
       It is irrelevant for the GBS-R ports -- an attempt to read or
       change this object MUST be rejected (in the case of SNMP, with
       the error inconsistentValue).

       This object maps to the TR-159 attribute
       aIMADiffDelayToleranceExceededEnable."
     REFERENCE
       "[TR-159], Section 5.5.5.7"
     ::= { g9981PortConfEntry 3 }

   g9981PortStatTable OBJECT-TYPE
     SYNTAX      SEQUENCE OF G9981PortStatEntry
     MAX-ACCESS  not-accessible
     STATUS      current
     DESCRIPTION
       "This table provides overall status information of G.Bond/ATM
       ports, complementing the generic status information from the
       ifTable of the IF-MIB and the gBondFltStatus of the GBOND-MIB.
       Additional status information about connected BCEs is available
       from the relevant line MIBs.

       This table contains live data from the equipment.  As such, it
       is NOT persistent."
     ::= { g9981Port 2 }

   g9981PortStatEntry OBJECT-TYPE
     SYNTAX      G9981PortStatEntry
     MAX-ACCESS  not-accessible
     STATUS      current
     DESCRIPTION
       "An entry in the G.Bond/ATM Port Status table.
       Each entry represents a G.Bond/ATM port indexed by the
       ifIndex.
       Note that a GBS port runs on top of a single or multiple BCE
       port(s), which are also indexed by the ifIndex."
     INDEX  { ifIndex }
     ::= { g9981PortStatTable 1 }

   G9981PortStatEntry ::=
     SEQUENCE {
       g9981PortStatRxLostCells      Counter32,
       g9981PortStatTxLostCells      Counter32,
       g9981PortStatMaxUpDiffDelay   Unsigned32,
       g9981PortStatMaxDnDiffDelay   Unsigned32
     }

   g9981PortStatRxLostCells  OBJECT-TYPE
     SYNTAX      Counter32
     UNITS       "cells"
     MAX-ACCESS  read-only
     STATUS      current
     DESCRIPTION
       "The number of lost ATM cells detected by the G.Bond/ATM port
       in the receive direction (e.g., upstream direction for
       a GBS-C port).

       Discontinuities in the value of this counter can occur at
       re-initialization of the management system, and at other times
       as indicated by the value of ifCounterDiscontinuityTime as
       defined in the IF-MIB.

       This object maps to the TR-159 attribute aIMARxLostCells."
     REFERENCE
       "[TR-159], Section 5.5.2.1; [G.998.1], Section 11.4.2 (4)"
     ::= { g9981PortStatEntry 1 }

   g9981PortStatTxLostCells  OBJECT-TYPE
     SYNTAX      Counter32
     UNITS       "cells"
     MAX-ACCESS  read-only
     STATUS      current
     DESCRIPTION
       "The number of lost ATM cells detected by the peer G.Bond/ATM
       port in the receive direction, i.e., downstream direction for a
       GBS-C port.

       This object is irrelevant for the GBS-R ports -- an attempt to
       read it MUST be rejected (in the case of SNMP, with the error
       inconsistentValue).

       Discontinuities in the value of this counter can occur at
       re-initialization of the management system, and at other times
       as indicated by the value of ifCounterDiscontinuityTime as
       defined in the IF-MIB.

       This object maps to the TR-159 attribute aIMAPeerRxLostCells."
     REFERENCE
       "[TR-159], Section 5.5.2.2; [G.998.1], Section 11.4.2 (4)"
     ::= { g9981PortStatEntry 2 }

   g9981PortStatMaxUpDiffDelay  OBJECT-TYPE
     SYNTAX      Unsigned32
     UNITS       "0.1 ms"
     MAX-ACCESS  read-only
     STATUS      current
     DESCRIPTION
       "Current maximum upstream differential delay between all
       operational BCEs in the G.Bond/ATM bonding group, measured in
       units of 0.1 ms.

       This object is read-only for the GBS-C ports.
       It is irrelevant for the GBS-R ports -- an attempt to read this
       object MUST be rejected (in the case of SNMP, with the error
       inconsistentValue).

       This object maps to the TR-159 attribute aIMAMaxUpDiffDelay."
     REFERENCE
       "[TR-159], Section 5.5.2.3"
     ::= { g9981PortStatEntry 3 }

   g9981PortStatMaxDnDiffDelay  OBJECT-TYPE
     SYNTAX      Unsigned32
     UNITS       "0.1 ms"
     MAX-ACCESS  read-only
     STATUS      current
     DESCRIPTION
       "Current maximum downstream differential delay between all
       operational BCEs in the G.Bond/ATM bonding group, measured in
       units of 0.1 ms.

       This object is read-only for the GBS-C ports.
       It is irrelevant for the GBS-R ports -- an attempt to read this
       object MUST be rejected (in the case of SNMP, with the error
       inconsistentValue).

       This object maps to the TR-159 attribute aIMAMaxDownDiffDelay."
     REFERENCE
       "[TR-159], Section 5.5.2.4"
     ::= { g9981PortStatEntry 4 }

   -------------------------------
   -- Performance Monitoring group
   -------------------------------

   g9981PM   OBJECT IDENTIFIER ::= { g9981Port 3 }

   g9981PortPmCurTable OBJECT-TYPE
     SYNTAX      SEQUENCE OF G9981PortPmCurEntry
     MAX-ACCESS  not-accessible
     STATUS      current
     DESCRIPTION
       "This table contains current Performance Monitoring information
       for a G.Bond/ATM port.  This table contains live data from the
       equipment and as such is NOT persistent."
     ::= { g9981PM 1 }

   g9981PortPmCurEntry OBJECT-TYPE
     SYNTAX      G9981PortPmCurEntry
     MAX-ACCESS  not-accessible
     STATUS      current
     DESCRIPTION
       "An entry in the G.Bond/ATM Port PM table.
       Each entry represents a G.Bond/ATM port indexed by the
       ifIndex."
     INDEX  { ifIndex }
     ::= { g9981PortPmCurTable 1 }

   G9981PortPmCurEntry ::=
     SEQUENCE {
       g9981PortPmCur15MinValidIntervals   HCPerfValidIntervals,
       g9981PortPmCur15MinInvalidIntervals HCPerfInvalidIntervals,
       g9981PortPmCur15MinTimeElapsed      HCPerfTimeElapsed,
       g9981PortPmCur15MinRxLostCells      HCPerfCurrentCount,
       g9981PortPmCur15MinTxLostCells      HCPerfCurrentCount,
       g9981PortPmCur15MinUpDiffDelay      HCPerfCurrentCount,
       g9981PortPmCur15MinDnDiffDelay      HCPerfCurrentCount,
       g9981PortPmCur1DayValidIntervals    Unsigned32,
       g9981PortPmCur1DayInvalidIntervals  Unsigned32,
       g9981PortPmCur1DayTimeElapsed       HCPerfTimeElapsed,
       g9981PortPmCur1DayRxLostCells       HCPerfCurrentCount,
       g9981PortPmCur1DayTxLostCells       HCPerfCurrentCount,
       g9981PortPmCur1DayUpDiffDelay       HCPerfCurrentCount,
       g9981PortPmCur1DayDnDiffDelay       HCPerfCurrentCount
     }

   g9981PortPmCur15MinValidIntervals  OBJECT-TYPE
     SYNTAX      HCPerfValidIntervals
     MAX-ACCESS  read-only
     STATUS      current
     DESCRIPTION
       "A read-only number of 15-minute intervals for which the
       performance data was collected.  The value of this object will
       be 96 or the maximum number of 15-minute history intervals
       collected by the implementation, unless the measurement was
       (re)started recently, in which case the value will be the
       number of complete 15-minute intervals for which there are at
       least some data.

       In certain cases, it is possible that some intervals are
       unavailable.  In this case, this object reports the maximum
       interval number for which data is available.

       This object partially maps to the TR-159 attribute
       aGroupPerf15MinValidIntervals."
     REFERENCE
       "[TR-159], Section 5.5.1.32"
     ::= { g9981PortPmCurEntry 1 }

   g9981PortPmCur15MinInvalidIntervals  OBJECT-TYPE
     SYNTAX      HCPerfInvalidIntervals
     MAX-ACCESS  read-only
     STATUS      current
     DESCRIPTION
       "A read-only number of 15-minute intervals for which the
       performance data was not always available.  The value will
       typically be zero, except in cases where the data for some
       intervals are not available.

       This object partially maps to the TR-159 attribute
       aGroupPerf15MinInvalidIntervals."
     REFERENCE
       "[TR-159], Section 5.5.1.33"
     ::= { g9981PortPmCurEntry 2 }

   g9981PortPmCur15MinTimeElapsed  OBJECT-TYPE
     SYNTAX      HCPerfTimeElapsed
     UNITS       "seconds"
     MAX-ACCESS  read-only
     STATUS      current
     DESCRIPTION
       "A read-only count of seconds that have elapsed since the
       beginning of the current 15-minute performance interval.

       This object partially maps to the TR-159 attribute
       aGroupPerfCurr15MinTimeElapsed."
     REFERENCE
       "[TR-159], Section 5.5.1.34"
     ::= { g9981PortPmCurEntry 3 }

   g9981PortPmCur15MinRxLostCells  OBJECT-TYPE
     SYNTAX      HCPerfCurrentCount
     UNITS       "cells"
     MAX-ACCESS  read-only
     STATUS      current
     DESCRIPTION
       "A read-only count of lost ATM cells detected by a G.Bond/ATM
       port (e.g., the GBS-C) in the receive direction, during the
       current 15-minute performance history interval.

       Note that the total number of lost ATM cells is indicated by the
       g9981PortStatRxLostCells object.

       This object is inhibited during Severely Errored Seconds (SES)
       or Unavailable Seconds (UAS)."
     REFERENCE
       "[TR-159], Section 5.5.2.1"
     ::= { g9981PortPmCurEntry 4}

   g9981PortPmCur15MinTxLostCells  OBJECT-TYPE
     SYNTAX      HCPerfCurrentCount
     UNITS       "cells"
     MAX-ACCESS  read-only
     STATUS      current
     DESCRIPTION
       "A read-only count of lost ATM cells detected by the peer
       G.Bond/ATM port (e.g., by the GBS-R for the GBS-C) during the
       current 15-minute performance history interval.

       Note that the total number of lost ATM cells is indicated by the
       g9981PortStatTxLostCells object.

       This object is inhibited during Unavailable Seconds (UAS)."
     REFERENCE
       "[TR-159], Section 5.5.2.2"
     ::= { g9981PortPmCurEntry 5}

   g9981PortPmCur15MinUpDiffDelay  OBJECT-TYPE
     SYNTAX      HCPerfCurrentCount
     UNITS       "0.1 ms"
     MAX-ACCESS  read-only
     STATUS      current
     DESCRIPTION
       "A read-only value specifying the maximum upstream differential
       delay between all operational BCEs in the GBS-C, measured in
       units of 0.1 ms, during the current 15-minute performance
       interval.

       Note that the current max upstream differential delay is
       indicated by the g9981PortStatMaxUpDiffDelay object.

       This object is inhibited during Unavailable Seconds (UAS)."
     REFERENCE
       "[TR-159], Section 5.5.2.3"
     ::= { g9981PortPmCurEntry 6}

   g9981PortPmCur15MinDnDiffDelay  OBJECT-TYPE
     SYNTAX      HCPerfCurrentCount
     UNITS       "0.1 ms"
     MAX-ACCESS  read-only
     STATUS      current
     DESCRIPTION
       "A read-only value specifying the maximum downstream
       differential delay between all operational BCEs in the GBS-C
       (as perceived by the GBS-R), measured in units of 0.1 ms,
       during the current 15-minute performance history interval.

       Note that the current max downstream differential delay is
       indicated by the g9981PortStatMaxDnDiffDelay object.

       This object is inhibited during Unavailable Seconds (UAS)."
     REFERENCE
       "[TR-159], Section 5.5.2.4"
     ::= { g9981PortPmCurEntry 7}

   g9981PortPmCur1DayValidIntervals  OBJECT-TYPE
     SYNTAX      Unsigned32 (0..7)
     UNITS       "days"
     MAX-ACCESS  read-only
     STATUS      current
     DESCRIPTION
       "A read-only number of 1-day intervals for which data was
       collected.  The value of this object will be 7 or the maximum
       number of 1-day history intervals collected by the
       implementation, unless the measurement was (re)started recently,
       in which case the value will be the number of complete 1-day
       intervals for which there are at least some data.
       In certain cases, it is possible that some intervals are
       unavailable.  In this case, this object reports the maximum
       interval number for which data is available."
     REFERENCE
       "[TR-159], Section 5.5.1.45"
     ::= { g9981PortPmCurEntry 8 }

   g9981PortPmCur1DayInvalidIntervals  OBJECT-TYPE
     SYNTAX      Unsigned32 (0..7)
     UNITS       "days"
     MAX-ACCESS  read-only
     STATUS      current
     DESCRIPTION
       "A read-only number of 1-day intervals for which data was
       not always available.  The value will typically be zero, except
       in cases where the data for some intervals are not available."
     REFERENCE
       "[TR-159], Section 5.5.1.46"
     ::= { g9981PortPmCurEntry 9 }

   g9981PortPmCur1DayTimeElapsed  OBJECT-TYPE
     SYNTAX      HCPerfTimeElapsed
     UNITS       "seconds"
     MAX-ACCESS  read-only
     STATUS      current
     DESCRIPTION
       "A read-only count of seconds that have elapsed since the
       beginning of the current 1-day performance interval."
     REFERENCE
       "[TR-159], Section 5.5.1.47"
     ::= { g9981PortPmCurEntry 10 }

   g9981PortPmCur1DayRxLostCells  OBJECT-TYPE
     SYNTAX      HCPerfCurrentCount
     UNITS       "cells"
     MAX-ACCESS  read-only
     STATUS      current
     DESCRIPTION
       "A read-only count of lost ATM cells detected by the G.Bond/ATM
       port (e.g., the GBS-C) during the current 1-day performance
       interval.

       This object is inhibited during Severely Errored Seconds (SES)
       and Unavailable Seconds (UAS)."
     ::= { g9981PortPmCurEntry 11 }

   g9981PortPmCur1DayTxLostCells OBJECT-TYPE
     SYNTAX      HCPerfCurrentCount
     UNITS       "cells"
     MAX-ACCESS  read-only
     STATUS      current
     DESCRIPTION
       "A read-only count of lost ATM cells detected by the peer
       G.Bond/ATM port (e.g., by the GBS-R for the GBS-C) during the
       current 1-day performance history interval.

       This object is inhibited during Unavailable Seconds (UAS)."
     ::= { g9981PortPmCurEntry 12 }

   g9981PortPmCur1DayUpDiffDelay  OBJECT-TYPE
     SYNTAX      HCPerfCurrentCount
     UNITS       "0.1 ms"
     MAX-ACCESS  read-only
     STATUS      current
     DESCRIPTION
       "A read-only value specifying the maximum upstream differential
       delay between all operational BCEs in the GBS-C, measured in
       units of 0.1 ms, during the current 1-day performance
       interval.

       This object is inhibited during Unavailable Seconds (UAS)."
     ::= { g9981PortPmCurEntry 13 }

   g9981PortPmCur1DayDnDiffDelay  OBJECT-TYPE
     SYNTAX      HCPerfCurrentCount
     UNITS       "0.1 ms"
     MAX-ACCESS  read-only
     STATUS      current
     DESCRIPTION
       "A read-only value specifying the maximum downstream
       differential delay between all operational BCEs in the GBS-C,
       measured in units of 0.1 ms, during the current 1-day
       performance interval.

       This object is inhibited during Unavailable Seconds (UAS)."
     ::= { g9981PortPmCurEntry 14 }

   -- Port PM history: 15-min buckets

   g9981PortPm15MinTable OBJECT-TYPE
     SYNTAX      SEQUENCE OF G9981PortPm15MinEntry
     MAX-ACCESS  not-accessible
     STATUS      current
     DESCRIPTION
       "This table contains historical 15-minute buckets of Performance
       Monitoring information for a G.Bond/ATM port (a row for each
       15-minute interval, up to 96 intervals).
       Entries in this table MUST be maintained in a persistent manner."
     ::= { g9981PM 2 }

   g9981PortPm15MinEntry OBJECT-TYPE
     SYNTAX      G9981PortPm15MinEntry
     MAX-ACCESS  not-accessible
     STATUS      current
     DESCRIPTION
       "An entry in the G.Bond/ATM Port historical 15-minute PM table.
       Each entry represents Performance Monitoring data for a

       G.Bond/ATM port, indexed by the ifIndex, collected during a
       particular 15-minute interval, indexed by the
       g9981PortPm15MinIntervalIndex."
     INDEX  { ifIndex, g9981PortPm15MinIntervalIndex }
     ::= { g9981PortPm15MinTable 1 }

   G9981PortPm15MinEntry ::=
     SEQUENCE {
       g9981PortPm15MinIntervalIndex       Unsigned32,
       g9981PortPm15MinIntervalMoniTime    HCPerfTimeElapsed,
       g9981PortPm15MinIntervalRxLostCells HCPerfIntervalCount,
       g9981PortPm15MinIntervalTxLostCells HCPerfIntervalCount,
       g9981PortPm15MinIntervalUpDiffDelay HCPerfIntervalCount,
       g9981PortPm15MinIntervalDnDiffDelay HCPerfIntervalCount,
       g9981PortPm15MinIntervalValid       TruthValue
     }

   g9981PortPm15MinIntervalIndex  OBJECT-TYPE
     SYNTAX      Unsigned32 (1..96)
     MAX-ACCESS  not-accessible
     STATUS      current
     DESCRIPTION
       "Performance data interval number.  1 is the most recent previous
       interval; interval 96 is 24 hours ago.
       Intervals 2..96 are OPTIONAL.

       This object partially maps to the TR-159 attribute
       aGroupPerf15MinIntervalNumber."
     REFERENCE
       "[TR-159], Section 5.5.1.57"
     ::= { g9981PortPm15MinEntry 1 }

   g9981PortPm15MinIntervalMoniTime  OBJECT-TYPE
     SYNTAX      HCPerfTimeElapsed
     UNITS       "seconds"
     MAX-ACCESS  read-only
     STATUS      current
     DESCRIPTION
       "A read-only count of seconds over which the performance data
       was actually monitored.  This value will be the same as the
       interval duration (900 seconds), except in a situation where
       performance data could not be collected for any reason."
     ::= { g9981PortPm15MinEntry 2 }

   g9981PortPm15MinIntervalRxLostCells  OBJECT-TYPE
     SYNTAX      HCPerfIntervalCount
     UNITS       "cells"
     MAX-ACCESS  read-only
     STATUS      current
     DESCRIPTION
       "A read-only count of lost ATM cells detected by a G.Bond/ATM
       port (e.g., the GBS-C) in the receive direction, during the
       15-minute performance history interval.

       Note that the total number of lost ATM cells is indicated by the
       g9981PortStatRxLostCells object.

       This object is inhibited during Severely Errored Seconds (SES)
       or Unavailable Seconds (UAS)."
     REFERENCE
       "[TR-159], Section 5.5.2.1"
     ::= { g9981PortPm15MinEntry 3 }

   g9981PortPm15MinIntervalTxLostCells  OBJECT-TYPE
     SYNTAX      HCPerfIntervalCount
     UNITS       "cells"
     MAX-ACCESS  read-only
     STATUS      current
     DESCRIPTION
       "A read-only count of lost ATM cells detected by the peer
       G.Bond/ATM port (e.g., by the GBS-R for the GBS-C) during the
       15-minute performance history interval.

       Note that the total number of lost ATM cells is indicated by the
       g9981PortStatTxLostCells object.

       This object is inhibited during Unavailable Seconds (UAS)."
     REFERENCE
       "[TR-159], Section 5.5.2.2"
     ::= { g9981PortPm15MinEntry 4 }

   g9981PortPm15MinIntervalUpDiffDelay  OBJECT-TYPE
     SYNTAX      HCPerfIntervalCount
     UNITS       "0.1 ms"
     MAX-ACCESS  read-only
     STATUS      current
     DESCRIPTION
       "A read-only value specifying the maximum upstream differential
       delay between all operational BCEs in the GBS, measured in
       units of 0.1 ms, during the 15-minute performance history
       interval.

       Note that the current max upstream differential delay is
       indicated by the g9981PortStatMaxUpDiffDelay object.

       This object is inhibited during Unavailable Seconds (UAS)."
     REFERENCE
       "[TR-159], Section 5.5.2.3"
     ::= { g9981PortPm15MinEntry 5 }

   g9981PortPm15MinIntervalDnDiffDelay  OBJECT-TYPE
     SYNTAX      HCPerfIntervalCount
     UNITS       "0.1 ms"
     MAX-ACCESS  read-only
     STATUS      current
     DESCRIPTION
       "A read-only value specifying the maximum downstream
       differential delay between all operational BCEs in the GBS,
       as perceived by its peer port, measured in units of 0.1 ms,
       during the 15-minute performance history interval.

       Note that the current max downstream differential delay is
       indicated by the g9981PortStatMaxDnDiffDelay object.

       This object is inhibited during Unavailable Seconds (UAS)."
     REFERENCE
       "[TR-159], Section 5.5.2.4"
     ::= { g9981PortPm15MinEntry 6 }

   g9981PortPm15MinIntervalValid  OBJECT-TYPE
     SYNTAX      TruthValue
     MAX-ACCESS  read-only
     STATUS      current
     DESCRIPTION
       "A read-only object indicating whether or not this history
       bucket contains valid data.  A valid bucket is reported as
       true(1) and an invalid bucket as false(2).
       If this history bucket is invalid, the BTU MUST NOT produce
       notifications based upon the value of the counters in this
       bucket.
       Note that an implementation may decide not to store invalid
       history buckets in its database.  In such a case, this object
       is not required, as only valid history buckets are available
       while invalid history buckets are simply not in the database.

       This object partially maps to the TR-159 attribute
       aGroupPerf15MinIntervalValid."
     REFERENCE
       "[TR-159], Section 5.5.1.58"
     ::= { g9981PortPm15MinEntry 7 }

   -- Port PM history: 1-day buckets

   g9981PortPm1DayTable OBJECT-TYPE
     SYNTAX      SEQUENCE OF G9981PortPm1DayEntry
     MAX-ACCESS  not-accessible
     STATUS      current
     DESCRIPTION
       "This table contains historical 1-day buckets of Performance
       Monitoring information for a G.Bond/ATM port (a row for each
       1-day interval, up to 7 intervals).
       Entries in this table MUST be maintained in a persistent manner."
     ::= { g9981PM 3 }

   g9981PortPm1DayEntry OBJECT-TYPE
     SYNTAX      G9981PortPm1DayEntry
     MAX-ACCESS  not-accessible
     STATUS      current
     DESCRIPTION
       "An entry in the G.Bond/ATM Port historical 1-day PM table.
       Each entry represents Performance Monitoring data for such a
       port, indexed by the ifIndex, collected during a particular
       1-day interval, indexed by the g9981PortPm1DayIntervalIndex."
     INDEX  { ifIndex, g9981PortPm1DayIntervalIndex }
     ::= { g9981PortPm1DayTable 1 }

   G9981PortPm1DayEntry ::=
     SEQUENCE {
       g9981PortPm1DayIntervalIndex        Unsigned32,
       g9981PortPm1DayIntervalMoniTime     HCPerfTimeElapsed,
       g9981PortPm1DayIntervalRxLostCells  HCPerfIntervalCount,
       g9981PortPm1DayIntervalTxLostCells  HCPerfIntervalCount,
       g9981PortPm1DayIntervalUpDiffDelay  HCPerfIntervalCount,
       g9981PortPm1DayIntervalDnDiffDelay  HCPerfIntervalCount,
       g9981PortPm1DayIntervalValid        TruthValue
     }

   g9981PortPm1DayIntervalIndex  OBJECT-TYPE
     SYNTAX      Unsigned32 (1..7)
     MAX-ACCESS  not-accessible
     STATUS      current
     DESCRIPTION
       "Performance data interval number.  1 is the most recent previous
       interval; interval 7 is 24 hours ago.
       Intervals 2..7 are OPTIONAL.

       This object partially maps to the TR-159 attribute
       aGroupPerf1DayIntervalNumber."
     REFERENCE
       "[TR-159], Section 5.5.1.62"
     ::= { g9981PortPm1DayEntry 1 }

   g9981PortPm1DayIntervalMoniTime  OBJECT-TYPE
     SYNTAX      HCPerfTimeElapsed
     UNITS       "seconds"
     MAX-ACCESS  read-only
     STATUS      current
     DESCRIPTION
       "A count of seconds over which the performance data was actually
       monitored.  This value will be the same as the interval duration
       (86400 seconds), except in a situation where performance data
       could not be collected for any reason.

       This object partially maps to the TR-159 attribute
       aGroupPerf1DayIntervalMoniSecs."
     REFERENCE
       "[TR-159], Section 5.5.1.64"
     ::= { g9981PortPm1DayEntry 2 }

   g9981PortPm1DayIntervalRxLostCells  OBJECT-TYPE
     SYNTAX      HCPerfIntervalCount
     UNITS       "cells"
     MAX-ACCESS  read-only
     STATUS      current
     DESCRIPTION
       "A count of lost ATM cells detected by the G.Bond/ATM port
       (e.g., the GBS-C) during the 1-day performance history interval.

       This object is inhibited during Severely Errored Seconds (SES)
       and Unavailable Seconds (UAS)."
     ::= { g9981PortPm1DayEntry 3 }

   g9981PortPm1DayIntervalTxLostCells  OBJECT-TYPE
     SYNTAX      HCPerfIntervalCount
     UNITS       "cells"
     MAX-ACCESS  read-only
     STATUS      current
     DESCRIPTION
       "A count of lost ATM cells detected by the peer G.Bond/ATM port
       (e.g., by the GBS-R for the GBS-C) during the 1-day performance
       history interval.

       This object is inhibited during Unavailable Seconds (UAS)."
     ::= { g9981PortPm1DayEntry 4 }

   g9981PortPm1DayIntervalUpDiffDelay  OBJECT-TYPE
     SYNTAX      HCPerfIntervalCount
     UNITS       "0.1 ms"
     MAX-ACCESS  read-only
     STATUS      current
     DESCRIPTION
       "A read-only value specifying the maximum upstream differential
       delay between all operational BCEs in the GBS-C, measured in
       units of 0.1 ms, during the 1-day performance history interval.

       This object is inhibited during Unavailable Seconds (UAS)."
     ::= { g9981PortPm1DayEntry 5 }

   g9981PortPm1DayIntervalDnDiffDelay  OBJECT-TYPE
     SYNTAX      HCPerfIntervalCount
     UNITS       "0.1 ms"
     MAX-ACCESS  read-only
     STATUS      current
     DESCRIPTION
       "A read-only value specifying the maximum downstream
       differential delay between all operational BCEs in the GBS-C,
       measured in units of 0.1 ms, during the 1-day performance
       history interval.

       This object is inhibited during Unavailable Seconds (UAS)."
     ::= { g9981PortPm1DayEntry 6 }

   g9981PortPm1DayIntervalValid  OBJECT-TYPE
     SYNTAX      TruthValue
     MAX-ACCESS  read-only
     STATUS      current
     DESCRIPTION
       "A read-only object indicating whether or not this history
       bucket contains valid data.  A valid bucket is reported as
       true(1) and an invalid bucket as false(2).
       If this history bucket is invalid, the BTU MUST NOT produce
       notifications based upon the value of the counters in this
       bucket.
       Note that an implementation may decide not to store invalid
       history buckets in its database.  In such a case, this object
       is not required, as only valid history buckets are available
       while invalid history buckets are simply not in the database.

       This object partially maps to the TR-159 attribute
       aGroupPerf1DayIntervalValid."
     REFERENCE
       "[TR-159], Section 5.5.1.63"
     ::= { g9981PortPm1DayEntry 7 }

  --
  -- Conformance Statements
  --

   g9981Groups      OBJECT IDENTIFIER
     ::= { g9981Conformance 1 }

   g9981Compliances OBJECT IDENTIFIER
     ::= { g9981Conformance 2 }

   -- Object Groups

   g9981BasicGroup OBJECT-GROUP
     OBJECTS {
       g9981PortStatRxLostCells,
       g9981PortStatTxLostCells,
       g9981PortStatMaxUpDiffDelay,
       g9981PortStatMaxDnDiffDelay
     }
     STATUS      current
     DESCRIPTION
       "A collection of objects representing management information
       for a G.Bond/ATM port."
     ::= { g9981Groups 1 }

   g9981AlarmConfGroup OBJECT-GROUP
     OBJECTS {
       g9981PortConfUpDiffDelayTolerance,
       g9981PortConfDnDiffDelayTolerance,
       g9981PortConfDiffDelayToleranceExceededEnable
     }
     STATUS      current
     DESCRIPTION
       "A collection of objects required for configuration of alarm
       thresholds and notifications in G.Bond/ATM ports."
     ::= { g9981Groups 2 }

   g9981NotificationGroup NOTIFICATION-GROUP
     NOTIFICATIONS {
       g9981UpDiffDelayToleranceExceeded,
       g9981DnDiffDelayToleranceExceeded
     }
     STATUS      current
     DESCRIPTION
       "This group supports notifications of significant conditions
       associated with G.Bond/ATM ports."
     ::= { g9981Groups 3 }

   g9981PerfCurrGroup OBJECT-GROUP
     OBJECTS {
       g9981PortPmCur15MinValidIntervals,
       g9981PortPmCur15MinInvalidIntervals,
       g9981PortPmCur15MinTimeElapsed,
       g9981PortPmCur15MinRxLostCells,
       g9981PortPmCur15MinTxLostCells,
       g9981PortPmCur15MinUpDiffDelay,
       g9981PortPmCur15MinDnDiffDelay,
       g9981PortPmCur1DayValidIntervals,
       g9981PortPmCur1DayInvalidIntervals,
       g9981PortPmCur1DayTimeElapsed,
       g9981PortPmCur1DayRxLostCells,
       g9981PortPmCur1DayTxLostCells,
       g9981PortPmCur1DayUpDiffDelay,
       g9981PortPmCur1DayDnDiffDelay
     }
     STATUS      current
     DESCRIPTION
       "A collection of objects supporting OPTIONAL current Performance
       Monitoring information for G.Bond/ATM ports."
     ::= { g9981Groups 4 }

   g9981Perf15MinGroup OBJECT-GROUP
     OBJECTS {
       g9981PortPm15MinIntervalMoniTime,
       g9981PortPm15MinIntervalRxLostCells,
       g9981PortPm15MinIntervalTxLostCells,
       g9981PortPm15MinIntervalUpDiffDelay,
       g9981PortPm15MinIntervalDnDiffDelay,
       g9981PortPm15MinIntervalValid
     }
     STATUS      current
     DESCRIPTION
       "A collection of objects supporting OPTIONAL historical
       Performance Monitoring information for G.Bond/ATM ports, during
       previous 15-minute intervals."
     ::= { g9981Groups 5 }

   g9981Perf1DayGroup OBJECT-GROUP
     OBJECTS {
       g9981PortPm1DayIntervalMoniTime,
       g9981PortPm1DayIntervalRxLostCells,
       g9981PortPm1DayIntervalTxLostCells,
       g9981PortPm1DayIntervalUpDiffDelay,
       g9981PortPm1DayIntervalDnDiffDelay,
       g9981PortPm1DayIntervalValid
     }
     STATUS      current
     DESCRIPTION
       "A collection of objects supporting OPTIONAL historical
       Performance Monitoring information for G.Bond/ATM ports, during
       previous 1-day intervals."
     ::= { g9981Groups 6 }

   -- Compliance Statements

   g9981Compliance MODULE-COMPLIANCE
     STATUS      current
     DESCRIPTION
       "The compliance statement for G.Bond/ATM interfaces.
       Compliance with the following external compliance statements
       is REQUIRED:

       MIB Module             Compliance Statement
       ----------             --------------------
       IF-MIB                 ifCompliance3
       GBOND-MIB              gBondCompliance"

     MODULE  -- this module
       MANDATORY-GROUPS {
         g9981BasicGroup,
         g9981AlarmConfGroup,
         g9981NotificationGroup
       }

       GROUP       g9981PerfCurrGroup
       DESCRIPTION
         "Support for this group is only required for implementations
         supporting Performance Monitoring."

       GROUP       g9981Perf15MinGroup
       DESCRIPTION
         "Support for this group is only required for implementations
         supporting historical Performance Monitoring."

       GROUP       g9981Perf1DayGroup
       DESCRIPTION
         "Support for this group is only required for implementations
         supporting 1-day historical Performance Monitoring."
     ::= { g9981Compliances 1 }
END
