-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- GDC MP7002 MIB
--
-- Revision History
-- Version		Date		Name			Description
-- 1.00A		20-Dec-95	D. Rosengrant	Initial Revision
--
-- 1.00B		31-Jan-96	D. Rosengrant	Changes after Eng/SCM review
--
-- 1.00C		13-Feb-96	D. Rosengrant	Changes after final Eng/SCM review
--
-- 1.00D		20-Feb-96	D. Rosengrant	Alarm config table needed to be 2 tables
--								Near End and Far End
--								Added Alarm Status object to Maintenance Table
--
-- 1.00E		02-Apr-96	D. Rosengrant	add "notAssigned" to Interface type and DCC
--								config bandwidth
--								add system timing gen source status to
--								Maintenance Table
-- 1.00F		16-May-96	C. Amorossi	Change enums for mp7002Framing
-- 1.00G                10-Jul-96       D. Baylis       Bump mp7002Alarms up one level (for mgt apps) 
-- 1.00H		16-Jul-96	W. Meltzer      Move page feeds inside comments (it confuses some compilers)
-- 1.00J                17-Jul-96       D. Baylis       Moved mp7002SysConfig OID from 6 to 7
-- 1.00K 		18-Jul-96	C. Amorossi	Changed description of mp7002ResetStats,
--							mp7002UnavailableTimeRegTable & mp7002SetRealTime
-- 							Added mp7002FarEndUnavailableTimeRegTable,
--							mp7002FarEndResetStats, mp7002NearEndStatLastInitialized,
--							mp7002FarEndStatLastInitialized
--                                                      Made mp7002ResetTestResults read-write
--							mp7002DiagTable is only Network Interface
-- 1.00L		20-Aug-96	C. Amorossi     Change mp7002Ais to mp7002AlarmIndSignal
-- 1.00M                07-Nov-96       C. Amorossi     Added comments to diagnostic table
-- 1.00N		06-Jan-97       C. Amorossi     Change description of mp7002SetRealTime
--                                                      Added alarm mp7002RAI
-- 1.00P		13-Jan-97       C. Amorossi     Added local alarm mp7002NtwkRAI
--
GDCMP7002-MIB DEFINITIONS ::= BEGIN

 IMPORTS
	 enterprises		FROM RFC1155-SMI
	 OBJECT-TYPE            FROM RFC-1212
	 DisplayString          FROM RFC1213-MIB
	 SCinstance             FROM GDCMACRO-MIB;

 gdc            OBJECT IDENTIFIER ::= { enterprises 498 }
 dsx1           OBJECT IDENTIFIER ::= { gdc 6 }
 mp7002System   OBJECT IDENTIFIER ::= { dsx1 6 }

 mp7002Alarms           OBJECT IDENTIFIER ::= { dsx1 9 } 

 mp7002Version          OBJECT IDENTIFIER ::= { mp7002System 1 }
 mp7002Maintenance     	OBJECT IDENTIFIER ::= { mp7002System 2 }
 mp7002Configuration	OBJECT IDENTIFIER ::= { mp7002System 3 }
 mp7002Diagnostics	OBJECT IDENTIFIER ::= { mp7002System 4 }
 mp7002Performance	OBJECT IDENTIFIER ::= { mp7002System 5 }
 mp7002SysConfig	OBJECT IDENTIFIER ::= { mp7002System 7 } 
 
 -- This MIB module uses the extended OBJECT-TYPE macro as
 -- defined in RFC 1212.

 -- The implementation of all groups is mandatory for all products that
 -- support a E1 interface.

 -- Note:  All rows in all tables defined within this MIB module are
 -- virtual.  They can neither be created or deleted by management
 -- operations.

 -- SCInstance: The interface part is defined as:
 --	0 - Unit
 --	1 - E1 interface
 --	2 - E1X interface

 -- The Version Group. This group identifies the version information
 -- for the MIB.
 --
mp7002MIBversion OBJECT-TYPE
     SYNTAX DisplayString (SIZE (5))
     ACCESS read-only
     STATUS mandatory
     DESCRIPTION
	 "Identifies the version of the MIB. The format of the version
	 is x.yzT, where 'x' identifies the major revision number, 'y'
	 identifies the minor revision number, 'z' identifies the
	 typographical revision, and T identifies the test revision.
	 Acceptable values for the individual revision components are
	 as follows:

		 x: 1 - 9
		 y: 0 - 9
		 z: 0 - 9
		 T: A - Z

	 Upon formal release, no designation for the test revision will
	 be present."
     ::= { mp7002Version 1 }

 --
mp7002VersionTable OBJECT-TYPE
	 SYNTAX SEQUENCE OF Mp7002VersionEntry
	 ACCESS not-accessible
	 STATUS mandatory
	 DESCRIPTION " "

	 ::= { mp7002Version 2  }

mp7002VersionEntry OBJECT-TYPE
	 SYNTAX Mp7002VersionEntry
	 ACCESS not-accessible
	 STATUS mandatory
	 DESCRIPTION
		 "An entry in the GDC Mp7002System Version Table."
	 INDEX  { mp7002VersionIndex }
	 ::= { mp7002VersionTable 1 }

Mp7002VersionEntry ::=
	 SEQUENCE {
		  mp7002VersionIndex
			 SCinstance,
		  mp7002FirmwareRev
			 DisplayString,
		  mp7002ModelNumber
			 DisplayString,
		  mp7002E1x
			 INTEGER
	 }

mp7002VersionIndex OBJECT-TYPE
	 SYNTAX SCinstance
	 ACCESS read-only
	 STATUS mandatory
	 DESCRIPTION
		 "This object identifies Version parameters associated
		 with the managed object."
	 ::= { mp7002VersionEntry 1 }

mp7002FirmwareRev 	OBJECT-TYPE
	 SYNTAX DisplayString (SIZE(2))
	 ACCESS read-only
	 STATUS mandatory
	 DESCRIPTION
		 "The version number of the firmware, to allow products to know which 
		 revision is installed.  The released version number is sequenced from 
		 --, A-, ... AA, ... ZZ.  Test versions are numerical from 01 to 99."
	 ::= { mp7002VersionEntry 2 }

mp7002ModelNumber	OBJECT-TYPE
	 SYNTAX DisplayString (SIZE(0..16))
	 ACCESS read-only
	 STATUS mandatory
	 DESCRIPTION
		 "This variable is used to determine the type
		 of card family installed ex. MP7002."
	 ::= { mp7002VersionEntry 3 }

mp7002E1x		OBJECT-TYPE
	SYNTAX  INTEGER {
			installed(1),
			notPresent(2)
		  	}
	ACCESS read-only
	STATUS mandatory
	DESCRIPTION
		"Indicates if the E1X Cascade Interface is installed."
	::= {mp7002VersionEntry 4}

 -- The GDC E1 Group.  This group contains objects that support the
 -- specific management requirements for products that support a GDC
 -- E1 interface.  
 -- If the E1 interface also supports alarm reporting, then the
 -- GDC Alarm Management MIB should be deployed for managing the alarm
 -- reporting of the E1 Interface.

 --
 -- ********************************************************************
 -- GDC E1 Maintenance Table
 -- ********************************************************************

mp7002MaintenanceTable OBJECT-TYPE
	 SYNTAX SEQUENCE OF Mp7002MaintenanceEntry
	 ACCESS not-accessible
	 STATUS mandatory
	 DESCRIPTION
		 "The table describes the maintenance objects for 
		 the unit and references the unit interface (cc = 00)."
	 ::= { mp7002Maintenance 1  }

mp7002MaintenanceEntry OBJECT-TYPE
	 SYNTAX Mp7002MaintenanceEntry
	 ACCESS not-accessible
	 STATUS mandatory
	 DESCRIPTION
		 "An entry in the GDC E1 Maintenance Table."
	 INDEX  { mp7002MaintenanceLineIndex }
	 ::= { mp7002MaintenanceTable 1 }

Mp7002MaintenanceEntry ::=
	 SEQUENCE {
		  mp7002MaintenanceLineIndex
			 SCinstance,
		  mp7002SoftReset
			 INTEGER,
		  mp7002SysUpTime
			 INTEGER,
		  mp7002DefaultInit
			 INTEGER,
		  mp7002ResetStats
			 INTEGER,
		  mp7002LedStatus
			 OCTET STRING,
	 	  mp7002E1Circuit
			 DisplayString,
		  mp7002E1XCircuit
			 DisplayString,
		  mp7002TSBundle1Name
			 DisplayString,
		  mp7002TSBundle2Name
			 DisplayString,
		  mp7002SetRealTime
			 INTEGER,
		  mp7002AlarmStatus
			 OCTET STRING,
		  mp7002SystemTimingGenStatus
			 INTEGER,
		  mp7002FarEndResetStats
			 INTEGER,
		  mp7002NearEndStatLastInitialized
			 INTEGER,
		  mp7002FarEndStatLastInitialized
			 INTEGER
		 }

mp7002MaintenanceLineIndex OBJECT-TYPE
	 SYNTAX SCinstance
	 ACCESS read-only
	 STATUS mandatory
	 DESCRIPTION
		 "This object identifies Maintenance parameters associated
		 with the managed object."
	 ::= { mp7002MaintenanceEntry 1 }

mp7002SoftReset		OBJECT-TYPE
	 SYNTAX INTEGER {
			 norm(1),
			 reset(2)
			 }
	 ACCESS read-write
	 STATUS mandatory
	 DESCRIPTION
		 "Supports the action of soft resetting the unit.  When this
		 object is set to reset(2), then the unit performs a soft
		 reset, whose meaning is specific to the type of unit being
		 managed. The value of norm(1) will be returned when 
		 the reset is complete.
		  
		 The value of norm(1) can not be set by management."

	 ::= { mp7002MaintenanceEntry 2 }

mp7002SysUpTime       	OBJECT-TYPE
	 SYNTAX INTEGER (1..2147483647)
	 ACCESS read-only
	 STATUS mandatory
	 DESCRIPTION
		 "This variable is used to report the elapsed system tick
		 time for conversion to real time at the controller and is
		 not related to the sysUpTime referenced in MIB-II.
		 Upon power-up of the unit, the elapsed time is cleared.
		 The elapsed time counter rolls over upon reaching the
		 maximum count."
	 ::= { mp7002MaintenanceEntry 3 }

mp7002DefaultInit     	OBJECT-TYPE
	 SYNTAX INTEGER {
			 normal(1),
			 factoryDefault(2)

		 }
	 ACCESS read-write
	 STATUS mandatory
	 DESCRIPTION
		 "This is used to allow the NonVolatile Configuration to 
		 be set to a factory default state.  When this value is set to
		 factoryDefault(1) the unit will perform
		 a reset to make the default configuration take affect. 
		 The value of normal(2) will be returned when the initialization
		 is complete.
		 The value of normal(2) can not be set by management."
	 ::= { mp7002MaintenanceEntry 4 }

mp7002ResetStats      	OBJECT-TYPE
	 SYNTAX  INTEGER        {
			 norm(1),
			 reset(2)
		 }
	 ACCESS  read-write
	 STATUS  mandatory
	 DESCRIPTION
		 "Supports the action of soft resetting the mp7002NearEndValidIntervals
		 object.  When this object is set to reset(2), then the unit
		 will reset the mp7002NearEndValidIntervals object to zero.
		 The value of norm(1) can not be set by management."
	 ::= { mp7002MaintenanceEntry 5 }

mp7002LedStatus 	OBJECT-TYPE
	 SYNTAX  OCTET STRING (SIZE(3))
	 ACCESS  read-only
	 STATUS  mandatory
	 DESCRIPTION
		 "Returns a bitwise snapshot of the front panel LED state.
		 Octet 1 bit 7 - not used
			 bit 6 - ON
			 bit 5 - INSV
			 bit 4 - RSP
			 bit 3 - TMG
			 bit 2 - NIU
			 bit 1 - D_I
			 bit 0 - future use

		 Octet 2 bit 7 - not used
			 bit 6 - future use
			 bit 5 - NTWK AIS
			 bit 4 - NTWK LCV
			 bit 3 - NTWK LOS
			 bit 2 - NTWK OOF
			 bit 1 - ALM
			 bit 0 - TM

		 Octet 3 bit 7 - not used
			 bit 6 - ST- future use
			 bit 5 - LT- future use
			 bit 4 - RL- future use
			 bit 3 - future use
			 bit 2 - future use
			 bit 1 - future use
			 bit 0 - future use"
	 ::= { mp7002MaintenanceEntry 6 }

mp7002E1Circuit		OBJECT-TYPE
	 SYNTAX  DisplayString (SIZE(16))
	 ACCESS  read-write
	 STATUS  mandatory
	 DESCRIPTION
		 "Circuit name E1 is connected to."

	 ::= { mp7002MaintenanceEntry 7 }

mp7002E1XCircuit	OBJECT-TYPE
	 SYNTAX  DisplayString (SIZE(16))
	 ACCESS  read-write
	 STATUS  mandatory
	 DESCRIPTION
		 "Circuit Name E1X is connected to"

	 ::= { mp7002MaintenanceEntry 8 }

mp7002TSBundle1Name	OBJECT-TYPE
	 SYNTAX  DisplayString (SIZE(16))
	 ACCESS  read-write
	 STATUS  mandatory
	 DESCRIPTION
		 "Name first Time Slot Bundle is assigned to. Only used when unit is 
		  configured for  drop side interface"

	 ::= { mp7002MaintenanceEntry 9 }

mp7002TSBundle2Name	OBJECT-TYPE
	 SYNTAX  DisplayString (SIZE(16))
	 ACCESS  read-write
	 STATUS  mandatory
	 DESCRIPTION
		 "Name second Time Slot Bundle is assigned to. Only used when unit is 
		  configured for drop side interface."

	 ::= { mp7002MaintenanceEntry 10 }

mp7002SetRealTime      	OBJECT-TYPE
	SYNTAX  INTEGER (1..2147483647)
	ACCESS  read-write
	STATUS  mandatory
	DESCRIPTION
		"Number of seconds from midnight Dec 31, 1969."
	::= {mp7002MaintenanceEntry 11}

mp7002AlarmStatus	OBJECT-TYPE
	SYNTAX OCTET STRING (SIZE(4))
	ACCESS read-only
	STATUS mandatory
	DESCRIPTION
		"Returns a bit-wise Status of alarms
		 Octet 1 bit 7 - not used
			 bit 6 - NWTK_LOS
			 bit 5 - NWTK_LOF
			 bit 4 - NWTK_AIS
			 bit 3 - NTWK_LCV
			 bit 2 - TIMING LOSS
			 bit 1 - NTWK_NE_ES
			 bit 0 - NTWK_NE_BBE

		 Octet 2 bit 7 - not used
			 bit 6 - NTWK_NE_SES
			 bit 5 - NTWK_NE_UAS
			 bit 4 - NTWK_FE_ES
			 bit 3 - NTWK_FE_BBE
			 bit 2 - NTWK_FE_SES
			 bit 1 - NTWK_FE_UAS
			 bit 0 - NTWK_RAI

		 Octet 3 bit 7 - not used
			 bit 6 - E1X_LOS
			 bit 5 - E1X_LOF
			 bit 4 - E1X_AIS
			 bit 3 - E1X_NE_ES
			 bit 2 - E1X_NE_BBE
			 bit 1 - E1X_NE_SES
			 bit 0 - E1X_NE_UAS
		
		 Octet 4 bit 7 - not used
			 bit 6 - E1X_FE_ES
			 bit 5 - E1X_FE_BBE
			 bit 4 - E1X_FE_SES
			 bit 3 - E1X_FE_UAS
			 bit 2 - NVRAM corrupted
			 bit 1 - unit failure
			 bit 0 - Power-up Alarm"
	::= {mp7002MaintenanceEntry 12}

mp7002SystemTimingGenStatus	OBJECT-TYPE
	SYNTAX INTEGER {
			none(1),
			clk8khz(2),
			clk4mhz(3),
			clk8khzand4mhz(4)
	}
	ACCESS read-only
	STATUS mandatory
	DESCRIPTION
		"Indicates if the units configured for primary or secondary system clock are
		actually supplying clock and if it is the 8hkz, 4mhz, or both."
	::= {mp7002MaintenanceEntry 13}

mp7002FarEndResetStats      	OBJECT-TYPE
	 SYNTAX  INTEGER        {
			 norm(1),
			 reset(2)
		 }
	 ACCESS  read-write
	 STATUS  mandatory
	 DESCRIPTION
		 "Supports the action of soft resetting the mp7002FarEndValidIntervals
		 object.  When this object is set to reset(2), then the unit
		 will reset the mp7002FarEndValidIntervals object to zero.
		 The value of norm(1) can not be set by management."
	::= { mp7002MaintenanceEntry 14 }

mp7002NearEndStatLastInitialized      	OBJECT-TYPE
	SYNTAX  INTEGER (1..2147483647)
	ACCESS  read-only
	STATUS  mandatory
	DESCRIPTION
		"Number of seconds from midnight Dec 31, 1969 up until
         mp7002NearEndValidIntervals was last initialized to zero"
	::= {mp7002MaintenanceEntry 15}

mp7002FarEndStatLastInitialized      	OBJECT-TYPE
	SYNTAX  INTEGER (1..2147483647)
	ACCESS  read-only
	STATUS  mandatory
	DESCRIPTION
		"Number of seconds from midnight Dec 31, 1969 up until
         mp7002FarEndValidIntervals was last initialized to zero"
	::= {mp7002MaintenanceEntry 16}

 --
 -- ********************************************************************
 -- The GDC E1 Configuration Table
 -- ********************************************************************


mp7002ConfigTable OBJECT-TYPE
     SYNTAX SEQUENCE OF Mp7002ConfigEntry
     ACCESS not-accessible
     STATUS mandatory
     DESCRIPTION
	 "The GDC E1 Configuration table."
     ::= { mp7002Configuration 1 }

mp7002ConfigEntry OBJECT-TYPE
     SYNTAX Mp7002ConfigEntry
     ACCESS not-accessible
     STATUS mandatory
     DESCRIPTION
	 "The GDC E1 Configuration table entry."
     INDEX { mp7002ConfigIndex }
     ::= { mp7002ConfigTable 1 }

Mp7002ConfigEntry ::= 
     SEQUENCE {
	 mp7002ConfigIndex SCinstance,
	 mp7002InterfaceType INTEGER,
	 mp7002RcvrRange INTEGER,
	 mp7002TransmitClockSource INTEGER,
	 mp7002FallbackClockSource INTEGER,
	 mp7002FacilityDataLink INTEGER,
	 mp7002NearEndValidIntervals INTEGER,
	 mp7002FarEndValidIntervals INTEGER,
	 mp7002NetworkConnection INTEGER,
	 mp7002Framing INTEGER,
	 mp7002LineCoding INTEGER
     }

mp7002ConfigIndex 	OBJECT-TYPE
     SYNTAX SCinstance
     ACCESS read-only
     STATUS mandatory
     DESCRIPTION
	 "The index value which uniquely identifies the interface to
	 which this entry is applicable.  This has the form of a
	 SCinstance which defines the slot, line, drop, and interface.
	 Interface can be Network or, when supported, E1X."
     ::= { mp7002ConfigEntry 1 }

mp7002InterfaceType 	OBJECT-TYPE
     SYNTAX INTEGER {
		diu(1),
		niu(2),
		notAssigned(3)
    		}
     ACCESS read-write
     STATUS mandatory
     DESCRIPTION 
	 "The operating mode of the interface to be either Network Side,
	  Drop Side or not assigned."
     ::= { mp7002ConfigEntry 2 }

mp7002RcvrRange   	OBJECT-TYPE
	 SYNTAX INTEGER {
			 short(1),
			 long(2)
		 }
	 ACCESS read-write
	 STATUS mandatory
	 DESCRIPTION
		"Sets the receiver range to short (6dB) or long (36dB)"
	 ::= { mp7002ConfigEntry 3 }

mp7002TransmitClockSource OBJECT-TYPE
     SYNTAX INTEGER {
		system(1),
		recovered(2),
		internal(3)
     }
     ACCESS read-write
     STATUS mandatory
     DESCRIPTION
		"Sets the transmit clock source."
     ::= { mp7002ConfigEntry 4 }

mp7002FallbackClockSource OBJECT-TYPE
     SYNTAX INTEGER {
		system(1),
		recovered(2),
		internal(3)
	}
     ACCESS read-write
     STATUS mandatory
     DESCRIPTION
	 "Identifies the fallback transmit clock source."

    ::= { mp7002ConfigEntry 5 }

mp7002FacilityDataLink OBJECT-TYPE
     SYNTAX INTEGER {
	 none(1),                    
	 active(2),
	 notActive(3)
     }
     ACCESS read-write
     STATUS mandatory
     DESCRIPTION
		""
     ::= { mp7002ConfigEntry 6 }

mp7002NearEndValidIntervals OBJECT-TYPE
	     SYNTAX  INTEGER (0..16)
	     ACCESS  read-only
	     STATUS  mandatory
	     DESCRIPTION
		"The number of  previous  intervals  for  which
		valid data was collected.  The value will be 16
		unless the interface was brought on-line within
		the last 4 hours, in which case the value will
		be the number of complete 15  minute  intervals
		the since interface has been online. This object
		is only valid for the E1 interface."
	    ::= { mp7002ConfigEntry 7 }

mp7002FarEndValidIntervals OBJECT-TYPE
	     SYNTAX  INTEGER (0..16)
	     ACCESS  read-only
	     STATUS  mandatory
	     DESCRIPTION
		"The number of  previous  intervals  for  which
		valid data was collected.  The value will be 16
		unless the interface was brought on-line within
		the last 4 hours, in which case the value will
		be the number of complete 15  minute  intervals
		the since interface has been online. This object
		is only valid for the E1 interface."
	    ::= { mp7002ConfigEntry 8 }

mp7002NetworkConnection        OBJECT-TYPE
		SYNTAX  INTEGER {
				onLine(1),
				standBy(2)
				}
		ACCESS  read-write
		STATUS  mandatory
		DESCRIPTION
			"Sets whether the network interface is standby or
			online.

			This only applies to the Network Interface."
		::= {mp7002ConfigEntry 9}

mp7002Framing                  OBJECT-TYPE
		SYNTAX  INTEGER {
				cCSwithoutCRC4(1),
				pCS0withoutCRC4(2),
				pCS1withoutCRC4(3),
				cCSwithCRC4(4),
				pCS0withCRC4(5),
				pCS1withCRC4(6)
				}
		ACCESS read-write
		STATUS mandatory
		DESCRIPTION
			"Set the framing for the interface.
			 Abbreviations are as follows:
				CCS  -  common-channel signaling
				PCS0 -  per channel signaling phase 0
				PCS1 -  per channel signaling phase 1"
		::= {mp7002ConfigEntry 10}

mp7002LineCoding               OBJECT-TYPE
		SYNTAX INTEGER {
				ami(1),
				hdb3(2)
				}
		ACCESS read-write
		STATUS mandatory
		DESCRIPTION
			"Sets the line coding for the interface."
		::= {mp7002ConfigEntry 11}
 
 --
 -- ********************************************************************
 -- The GDC E1 System Configuration Table
 -- ********************************************************************


 mp7002SysTimingTable OBJECT-TYPE
     SYNTAX SEQUENCE OF Mp7002SysTimingEntry
     ACCESS not-accessible
     STATUS mandatory
     DESCRIPTION
	 "The GDC System Timing table. These are unit options at the
	 system level."
     ::= { mp7002SysConfig 1 }

 mp7002SysTimingEntry OBJECT-TYPE
     SYNTAX Mp7002SysTimingEntry
     ACCESS not-accessible
     STATUS mandatory
     DESCRIPTION
	 "The GDC E1 Configuration table entry."
     INDEX { mp7002SysTimingIndex }
     ::= { mp7002SysTimingTable 1 }

 Mp7002SysTimingEntry ::= 
     SEQUENCE {
	 mp7002SysTimingIndex SCinstance,
	 mp7002SysTimingGen INTEGER
		}

 mp7002SysTimingIndex OBJECT-TYPE
     SYNTAX SCinstance
     ACCESS read-only
     STATUS mandatory
     DESCRIPTION
		"Index value into the system configuration table."
     ::= { mp7002SysTimingEntry 1 }

 mp7002SysTimingGen     OBJECT-TYPE 
	SYNTAX INTEGER {
			none(1),
			primary(2),
			secondary(3)
			}
	ACCESS read-write
	STATUS mandatory
	DESCRIPTION
		"Selects if the unit provides system timing.
		none(1) - does not provide Timing Generator
		primary(2) - unit is primary Timing Generator for the shelf.
		secondary(3) - unit is secondary Timig Generator for the 
			shelf.

		Only 1 unit in the shelf can the primary or secondary 
		timing generator. All other must be none."

	::= {mp7002SysTimingEntry 2}

 --
 -- *********************************************************************
 -- The GDC DCC Configuration Table
 -- *********************************************************************

 mp7002DCCConfigurationTable OBJECT-TYPE
     SYNTAX SEQUENCE OF Mp7002DCCConfigurationEntry
     ACCESS not-accessible
     STATUS mandatory
     DESCRIPTION
	 "The GDC DCC Configuration table. These are Diagnostic Channel 
		configuration options."
     ::= { mp7002Configuration 2}

 mp7002DCCConfigurationEntry OBJECT-TYPE
     SYNTAX Mp7002DCCConfigurationEntry
     ACCESS not-accessible
     STATUS mandatory
     DESCRIPTION
	 "The GDC Diagnostic Configuration table entry."
     INDEX { mp7002DCCConfigurationIndex }
     ::= { mp7002DCCConfigurationTable 1 }

 Mp7002DCCConfigurationEntry ::= 
     SEQUENCE {
	 mp7002DCCConfigurationIndex SCinstance,
	mp7002TimeSlot INTEGER,
	mp7002Bandwidth INTEGER
		}

 mp7002DCCConfigurationIndex OBJECT-TYPE
     SYNTAX SCinstance
     ACCESS read-only
     STATUS mandatory
     DESCRIPTION
		"Index value into the DCC Configuration table."
     ::= { mp7002DCCConfigurationEntry 1 }

 mp7002TimeSlot OBJECT-TYPE
	SYNTAX INTEGER(1..31)
	ACCESS read-write
	STATUS mandatory
	DESCRIPTION
		"Time Slot DCC goes in"
	::={ mp7002DCCConfigurationEntry 2}

 mp7002Bandwidth OBJECT-TYPE
	SYNTAX INTEGER {
		kbps8(1),
		kbps56(2),
		kbps64(3),
		notAssigned(4)
		}
	ACCESS read-write
	STATUS mandatory
	DESCRIPTION
		"Bandwidth to use:
			8 kbps - bit 7 only
			56 kbps - bits 0 - 6
			64 kbps - all 8 bits"
	::={ mp7002DCCConfigurationEntry 3}

 -- ********************************************************************
 -- The GDC E1 Highway Assignment Table
 -- ********************************************************************


 mp7002HighwayAssignTable OBJECT-TYPE
     SYNTAX SEQUENCE OF Mp7002HighwayAssignEntry
     ACCESS not-accessible
     STATUS mandatory
     DESCRIPTION
	 "The GDC System Configuration table. These are unit options at the
	 system level."
     ::= { mp7002SysConfig 2}

 mp7002HighwayAssignEntry OBJECT-TYPE
     SYNTAX Mp7002HighwayAssignEntry
     ACCESS not-accessible
     STATUS mandatory
     DESCRIPTION
	 "The GDC E1 Highway Assign table entry."
     INDEX { mp7002HighwayAssignIndex, mp7002TimeSlotBundle }
     ::= { mp7002HighwayAssignTable 1 }

 Mp7002HighwayAssignEntry ::= 
     SEQUENCE {
	 mp7002HighwayAssignIndex SCinstance,
	 mp7002TimeSlotBundle INTEGER,
	 mp7002StartTimeSlot INTEGER,
	 mp7002NumberOfTimeSlots INTEGER,
	 mp7002BundleDestination INTEGER,
	mp7002ExecuteAssign INTEGER
		}
 
 mp7002HighwayAssignIndex OBJECT-TYPE
     SYNTAX SCinstance
     ACCESS read-only
     STATUS mandatory
     DESCRIPTION
		"Index value into the Highway Assignment table."
     ::= { mp7002HighwayAssignEntry 1 }

 mp7002TimeSlotBundle   OBJECT-TYPE 
	SYNTAX INTEGER {
				bundle1(1),
				bundle2(2)
				}
	ACCESS read-only
	STATUS mandatory
	DESCRIPTION
		"Index for the bundle being assigned. A time slot bundle
		can be assigned to 1 or 2 of the 4 backplane highways. Bundle 1 is asigned in
 		the Aggregate starting at Time Slot 1. Bundle 2 starts at the next available Time
 		Slot. If only one bundle is needed, it must be bundle 1. The execute object
 		should be sent only after acknowlegement of al assignment PDUs."
	::= {mp7002HighwayAssignEntry 2 }

 mp7002StartTimeSlot    OBJECT-TYPE
	SYNTAX  INTEGER (1..31)
	ACCESS  read-write
	STATUS  mandatory
	DESCRIPTION
		"Starting time slot of the bundle. If only 1 bundle is
		being assigned, or the first of 2 is being assigned, 
		it must start at 1. The second of 2 must start at the next
		available time slot after the first bundle."
	::= {mp7002HighwayAssignEntry 3 }

 mp7002NumberOfTimeSlots        OBJECT-TYPE
	SYNTAX  INTEGER (1..31)
	ACCESS  read-write
	STATUS  mandatory
	DESCRIPTION
		"Number of time slots assigned to the bundle."
	::= {mp7002HighwayAssignEntry 4 }

 mp7002BundleDestination      OBJECT-TYPE
	SYNTAX  INTEGER {
			notAssigned(1),
			highway1(2),
			highway2(3),
			highway3(4),
			highway4(5)
			}
	ACCESS read-write
	STATUS mandatory
	DESCRIPTION
		"Defines the destination of the bundle."
	::= {mp7002HighwayAssignEntry 5 }

 mp7002ExecuteAssign OBJECT-TYPE
	SYNTAX  INTEGER {
			normal(1),
			execute(2)
			}
	ACCESS read-write
	STATUS mandatory
	DESCRIPTION
		"Causes the MP7002 to execute configuration of the assigned 
		 highway configuration. This object should be sent in a separate 
		 PDU after acknowlegement of the assign PDU(s) has been recieved."
	::= {mp7002HighwayAssignEntry 6 }

 -- ********************************************************************
 -- GDC E1 Diagnostics
 -- ********************************************************************
 mp7002DiagTable OBJECT-TYPE
     SYNTAX SEQUENCE OF Mp7002DiagEntry
     ACCESS not-accessible
     STATUS mandatory
     DESCRIPTION
	 "The GDC E1 Diagnostics table.  Information in the entries of
	 this table support diagnostics testing via loopbacks. 
	 Diagnostics are only supported when mp7002InterfaceType is set
	 to niu(2). This table applies to the Network Interface only."
     ::= { mp7002Diagnostics 1 }

 mp7002DiagEntry OBJECT-TYPE
     SYNTAX Mp7002DiagEntry
     ACCESS not-accessible
     STATUS mandatory
     DESCRIPTION
	 "The GDC E1 Diagnostics table entry."
     INDEX { mp7002DiagIndex }
     ::= { mp7002DiagTable 1 }

 Mp7002DiagEntry ::= 
     SEQUENCE {
	 mp7002DiagIndex SCinstance,
	 mp7002TestPattern INTEGER,
	 mp7002DiagConfig INTEGER,
	 mp7002TestLimit INTEGER,
	 mp7002TestExecutionStatus INTEGER,
	 mp7002TestExceptions INTEGER,
	 mp7002TestResults INTEGER,
	 mp7002ResetTestResults INTEGER
     }

 mp7002DiagIndex OBJECT-TYPE
     SYNTAX SCinstance
     ACCESS read-only
     STATUS mandatory
     DESCRIPTION
	 "The index value which uniquely identifies the interface to
	 which this entry is applicable.  This has the form of a
	 SCinstance which defines the slot, line, drop, and interface.
	 Interface can be Network or, when supported, E1X."
     ::= { mp7002DiagEntry 1 }

 mp7002TestPattern OBJECT-TYPE
     SYNTAX INTEGER {
		noCode(1),
		pat511(2),
		pat2047(3),
		pat1in4(4)
		}
     ACCESS read-write
     STATUS obsolete
     DESCRIPTION
		"Test pattern for tests that use the pattern generator.
		The value of this object is used when 
		mp7002DiagConfig.unitTest(5) or mp7002DiagConfig.patGenOn(6)
		is selected.

		NOT SUPPORTED BY THE MP7002."
     ::= { mp7002DiagEntry 2 }

 mp7002DiagConfig OBJECT-TYPE
     SYNTAX INTEGER {
		noLoop(1),
		lineLoopback(2),
		payloadLoopback(3),
		localTest(4),    -- not supported by the mp7002
		unitTest(5),     -- not supported by the mp7002
		patGenOn(6)      -- not supported by the mp7002
     }
     ACCESS read-write
     STATUS mandatory
     DESCRIPTION
		"Selects the test to run. noLoop(1) ends the test.

		Interoperates with mp7002TestPattern. When unitTest(2) or
		patGenOn(3) is selected, the pattern in mp7002TestPattern
		is used.

		payloadLoopback(4) and lineLoopback(5) are only valid when
		the unit is configured for a Network Side interface.

		localTest(6) is only valid when the unit is configured for
		a Drop Side interface."
     ::= { mp7002DiagEntry 3 }

 mp7002TestLimit OBJECT-TYPE
     SYNTAX INTEGER     {
			testTime10Mins(1),
			testTime20Mins(2),
			noLimit(3)
	     		}                  
     ACCESS read-write
     STATUS mandatory
     DESCRIPTION
	 "Selects the duration to run a diagnostic test.  The value(1)
	 noLimit signifies that the test should run indefinitely until
	 explicitly terminated. 

	 Default value: testTime10Mins(1)"
     	::= { mp7002DiagEntry 4 }

 mp7002TestExecutionStatus OBJECT-TYPE
     SYNTAX INTEGER {
	 notInTest(1),                  -- a test is not running
	 testInProgress(2),             -- the test is running
	 testCompleted(4),              -- the test is complete
	 testCompletedNotInTest(5)      -- a test has completed,nolonger in test
	 

     }
     ACCESS read-only
     STATUS mandatory
     DESCRIPTION
     "This variable reports the status of a test.  notInTest(1) indicates
      a test is not running.  testInProgress(2) indicates that a test is
      currently running.  testCompleted(4) indicates that a test has run
      and is completed. testCompletedNotInTest(5) indicates that a test has
      completed and it is no longer in test."
	::= { mp7002DiagEntry 5 }

 mp7002TestExceptions OBJECT-TYPE
     SYNTAX INTEGER (0..7)
     ACCESS read-only
     STATUS mandatory
     DESCRIPTION
	 "Indicates exceptions that have occurred that may affect
	 interpretation of the test results.

	 The value of this object is a sum.  This sum initially take
	 the value zero.  Then, for each exception, the value
	 associated with the exception is added to the sum.

	 The exception values are:

		 value  exception
		     1   a timed test was preempted so the result
			 cannot be viewed in relation to the test
			 duration
		     2   the results overflowed so the result cannot be
			 viewed as an absolute value
		     4   the test was performed while synchronization
			 could not be performed so the result may not
			 be accurate."
	::= { mp7002DiagEntry 6 }

 mp7002TestResults OBJECT-TYPE
     SYNTAX INTEGER(0..1048576)
     ACCESS read-only
     STATUS obsolete
     DESCRIPTION
	 "The results of the last diagnostic test.  This can be the
	 current test running or the last completed test.

	 Note that the interpretation of these results may be affected
	 by the value of the mp7002TestExceptions object.

	 Not supported by MP7002 since no pattern generating tests
	 are supported."
     ::= { mp7002DiagEntry 7 }

 mp7002ResetTestResults	OBJECT-TYPE
	SYNTAX INTEGER {
				norm(1),
				reset(2)
			     }
	ACCESS read-write
	STATUS obsolete
	DESCRIPTION
	"Resets the diagnostic error count.
	 Not supported by MP7002 since no pattern generating tests
	 are supported."
    ::= { mp7002DiagEntry 8 }

 --
 -- ********************************************************************
 -- Current 15 Near End Minute Performance Table
 -- ********************************************************************


 mp7002NearEndCurrent15MinTable    OBJECT-TYPE
	 SYNTAX  SEQUENCE OF Mp7002NearEndCurrent15MinEntry
	 ACCESS  not-accessible
	 STATUS  mandatory
	 DESCRIPTION
		 "The mp7002 Current table."
	 ::= { mp7002Performance 1 }


 mp7002NearEndCurrent15MinEntry    OBJECT-TYPE
	 SYNTAX  Mp7002NearEndCurrent15MinEntry
	 ACCESS  not-accessible
	 STATUS  mandatory
	 DESCRIPTION
		 "An entry in the mp7002 NearEnd Current table."
	 INDEX   { mp7002NearEndCurrent15MinIndex }
	 ::= { mp7002NearEndCurrent15MinTable 1 }

 Mp7002NearEndCurrent15MinEntry ::=
	 SEQUENCE {
		  mp7002NearEndCurrent15MinIndex
			 SCinstance,
		  mp7002NearEndCurrent15MinStat
			OCTET STRING
	  }

 mp7002NearEndCurrent15MinIndex    OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	    ::= { mp7002NearEndCurrent15MinEntry 1 }
 --

 mp7002NearEndCurrent15MinStat    OBJECT-TYPE
	SYNTAX OCTET STRING (SIZE(12))
	ACCESS read-only
	STATUS mandatory
	DESCRIPTION
		 "Returns a bitwise snapshot of the current 15Min statistics.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0
"

	::= {mp7002NearEndCurrent15MinEntry 2 }

 --
 -- ********************************************************************
 -- Interval Near End Performance Table
 -- ********************************************************************


 mp7002NearEndIntervalTable   OBJECT-TYPE
	 SYNTAX  SEQUENCE OF Mp7002NearEndIntervalEntry
	 ACCESS  not-accessible
	 STATUS  mandatory
	 DESCRIPTION
		 "The mp7002 Interval table."

	 ::= { mp7002Performance 2 }


 mp7002NearEndIntervalEntry   OBJECT-TYPE
	 SYNTAX  Mp7002NearEndIntervalEntry
	 ACCESS  not-accessible
	 STATUS  mandatory
	 DESCRIPTION
		 "An entry in the E1 Interval table."
	 INDEX   { mp7002NearEndIntervalIndex, mp7002NearEndIntervalNumber }
	 ::= { mp7002NearEndIntervalTable 1 }

 Mp7002NearEndIntervalEntry ::=
	 SEQUENCE {
		  mp7002NearEndIntervalIndex
			 SCinstance,
		  mp7002NearEndIntervalNumber
			 INTEGER,
		  mp7002NearEndIntervalStat
			 OCTET STRING
	  }

 mp7002NearEndIntervalIndex   OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002NearEndIntervalEntry 1 }

 mp7002NearEndIntervalNumber   OBJECT-TYPE
	 SYNTAX INTEGER (1..16)
	 ACCESS read-only
	 STATUS mandatory
	 DESCRIPTION
		 "The number of Errored Seconds encountered by an E1
		 interface in one of the previous 16, individual 15 minute,
		 intervals."
	 ::= {mp7002NearEndIntervalEntry 2 }

 --
 mp7002NearEndIntervalStat   OBJECT-TYPE
	 SYNTAX OCTET STRING (SIZE(12))
	 ACCESS read-only
	 STATUS mandatory
	 DESCRIPTION
		 "Returns a bitwise map of the
		 interface in one of the previous 16, individual 15 minute,
		 intervals.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0

"
	 ::= {mp7002NearEndIntervalEntry 3 }

 -- ********************************************************************
 -- Current 24 Hour Near End Performance Table
 -- ********************************************************************


 mp7002NearEndCurrent24HrTable              OBJECT-TYPE
	 SYNTAX  SEQUENCE OF Mp7002NearEndCurrent24HrEntry
	 ACCESS  not-accessible
	 STATUS  mandatory
	 DESCRIPTION
		 "The E1 Current24Hr table.  4 hour interval."

	 ::= { mp7002Performance 3}
 --

 mp7002NearEndCurrent24HrEntry              OBJECT-TYPE
	 SYNTAX  Mp7002NearEndCurrent24HrEntry
	 ACCESS  not-accessible
	 STATUS  mandatory
	 DESCRIPTION
		 "An entry in the E1 Total table."
	 INDEX   { mp7002NearEndCurrent24HrIndex }
	 ::= { mp7002NearEndCurrent24HrTable 1 }

 Mp7002NearEndCurrent24HrEntry ::=
	 SEQUENCE {
		  mp7002NearEndCurrent24HrIndex
			 SCinstance,
		  mp7002NearEndCurrent24HrStat
			 OCTET STRING
	  }

 mp7002NearEndCurrent24HrIndex              OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002NearEndCurrent24HrEntry 1 }

 --
 mp7002NearEndCurrent24HrStat              OBJECT-TYPE
	 SYNTAX OCTET STRING (SIZE (15))
	 ACCESS read-only
	 STATUS mandatory
	 DESCRIPTION
		 "Returns a bitwise map of the current 24 hour table

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0

"
	 ::= {mp7002NearEndCurrent24HrEntry 2 }
 --
 -- ********************************************************************
 -- Recent 24 Hour Near End Performance Table
 -- ********************************************************************


 mp7002NearEndRecent24HrTable              OBJECT-TYPE
	 SYNTAX  SEQUENCE OF Mp7002NearEndRecent24HrEntry
	 ACCESS  not-accessible
	 STATUS  mandatory
	 DESCRIPTION
		 "The E1 Recent24Hr table.  4 hour interval."

	 ::= { mp7002Performance 4}

 mp7002NearEndRecent24HrEntry              OBJECT-TYPE
	 SYNTAX  Mp7002NearEndRecent24HrEntry
	 ACCESS  not-accessible
	 STATUS  mandatory
	 DESCRIPTION
		 "An entry in the E1 Total table."
	 INDEX   { mp7002NearEndRecent24HrIndex }
	 ::= { mp7002NearEndRecent24HrTable 1 }

 Mp7002NearEndRecent24HrEntry ::=
	 SEQUENCE {
		  mp7002NearEndRecent24HrIndex
			 SCinstance,
		  mp7002NearEndRecent24HrStat
			 OCTET STRING
	  }

 mp7002NearEndRecent24HrIndex              OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."

	 ::= { mp7002NearEndRecent24HrEntry 1 }

 --
 mp7002NearEndRecent24HrStat              OBJECT-TYPE
	 SYNTAX OCTET STRING (SIZE (15))
	 ACCESS read-only
	 STATUS mandatory
	 DESCRIPTION
		 "Returns a bitwise map of the current 24 hour table

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0


"
	 ::= {mp7002NearEndRecent24HrEntry 2 }

 --
 -- ********************************************************************
 -- Far End Current 15 Minute Performance Table
 -- ********************************************************************


 mp7002FarEndCurrent15MinTable      OBJECT-TYPE
	 SYNTAX  SEQUENCE OF Mp7002FarEndCurrent15MinEntry
	 ACCESS  not-accessible
	 STATUS  mandatory
	 DESCRIPTION
		 "The mp7002FarEnd Current 15 minute table."
	 ::= { mp7002Performance 5 }


 mp7002FarEndCurrent15MinEntry      OBJECT-TYPE
	 SYNTAX  Mp7002FarEndCurrent15MinEntry
	 ACCESS  not-accessible
	 STATUS  mandatory
	 DESCRIPTION
		 "An entry in the mp7002FarEnd Current 15 Minute table."
	 INDEX   { mp7002FarEndCurrent15MinIndex }
	 ::= { mp7002FarEndCurrent15MinTable 1 }

 Mp7002FarEndCurrent15MinEntry ::=
	 SEQUENCE {
		  mp7002FarEndCurrent15MinIndex
			 SCinstance,
		  mp7002FarEndCurrent15MinStat
			 OCTET STRING
	  }

 mp7002FarEndCurrent15MinIndex      OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	    ::= { mp7002FarEndCurrent15MinEntry 1 }

 --
 mp7002FarEndCurrent15MinStat      OBJECT-TYPE
	SYNTAX OCTET STRING (SIZE(9))
	ACCESS read-only
	STATUS mandatory
	DESCRIPTION
		 "Returns a bitwise map of the far end
		 interface in one of the previous 16, individual 15 minute,
		 intervals.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0
"
	::= {mp7002FarEndCurrent15MinEntry 2 }


 --
 -- ********************************************************************
 -- Interval Far End Performance Table
 -- ********************************************************************


 mp7002FarEndIntervalTable     OBJECT-TYPE
	 SYNTAX  SEQUENCE OF Mp7002FarEndIntervalEntry
	 ACCESS  not-accessible
	 STATUS  mandatory
	 DESCRIPTION
		 "The mp7002FarEnd Interval table."

	 ::= { mp7002Performance 6 }


 mp7002FarEndIntervalEntry     OBJECT-TYPE
	 SYNTAX  Mp7002FarEndIntervalEntry
	 ACCESS  not-accessible
	 STATUS  mandatory
	 DESCRIPTION
		 "An entry in the Interval table."
	 INDEX   { mp7002FarEndIntervalIndex, mp7002FarEndIntervalNumber }
	 ::= { mp7002FarEndIntervalTable 1 }

 Mp7002FarEndIntervalEntry ::=
	 SEQUENCE {
		  mp7002FarEndIntervalIndex
			 SCinstance,
		  mp7002FarEndIntervalNumber
			 INTEGER,
		  mp7002FarEndIntervalStat
			 OCTET STRING
	  }

 mp7002FarEndIntervalIndex     OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002FarEndIntervalEntry 1 }

 mp7002FarEndIntervalNumber    OBJECT-TYPE
	 SYNTAX  INTEGER (1..16)
	 ACCESS  read-only
	 STATUS  mandatory
	 DESCRIPTION
		 "A number between 1 and 16, where 1 is the most recently completed 
		 15 minute interval and 16 is the least recently completed 15 minutes  
		 interval   (assuming   that  all  16  intervals  are valid)."
	 ::= { mp7002FarEndIntervalEntry 2 }

 mp7002FarEndIntervalStat     OBJECT-TYPE
	 SYNTAX OCTET STRING (SIZE(9))
	 ACCESS read-only
	 STATUS mandatory
	 DESCRIPTION
		 "Returns a bitwise map of statistics for the far end
		 interface in the current 15 minute interval.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0
"
	 ::= {mp7002FarEndIntervalEntry 3 }

 --
 -- ********************************************************************
 -- Current 24 Hour Far End Performance Table
 -- ********************************************************************


 mp7002CurrentFarEnd24HrTable                OBJECT-TYPE
	 SYNTAX  SEQUENCE OF Mp7002CurrentFarEnd24HrEntry
	 ACCESS  not-accessible
	 STATUS  mandatory
	 DESCRIPTION
		 "The Current 24 Hour table."

	 ::= { mp7002Performance 7 }

 mp7002CurrentFarEnd24HrEntry                OBJECT-TYPE
	 SYNTAX  Mp7002CurrentFarEnd24HrEntry
	 ACCESS  not-accessible
	 STATUS  mandatory
	 DESCRIPTION
		 "An entry in the Current 24 Hr table."
	 INDEX   { mp7002CurrentFarEnd24HrIndex }
	 ::= { mp7002CurrentFarEnd24HrTable 1 }

 Mp7002CurrentFarEnd24HrEntry ::=
	 SEQUENCE {
		  mp7002CurrentFarEnd24HrIndex
			 SCinstance,
		  mp7002CurrentFarEnd24HrStat
			 OCTET STRING
	  }

 --
 mp7002CurrentFarEnd24HrIndex                OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002CurrentFarEnd24HrEntry 1 }

 mp7002CurrentFarEnd24HrStat                OBJECT-TYPE
	 SYNTAX OCTET STRING (SIZE(12))
	 ACCESS read-only
	 STATUS mandatory
	 DESCRIPTION
		 "Returns a bitwise map of statistics for the
		 interface in the current 24 hour interval.
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
"
	 ::= {mp7002CurrentFarEnd24HrEntry 2 }

 --
 -- ********************************************************************
 -- Recent 24 Hour Far End Performance Table
 -- ********************************************************************


 mp7002RecentFarEnd24HrTable                OBJECT-TYPE
	 SYNTAX  SEQUENCE OF Mp7002RecentFarEnd24HrEntry
	 ACCESS  not-accessible
	 STATUS  mandatory
	 DESCRIPTION
		 "The Recent 24 Hour table."

	 ::= { mp7002Performance 8 }

 mp7002RecentFarEnd24HrEntry                OBJECT-TYPE
	 SYNTAX  Mp7002RecentFarEnd24HrEntry
	 ACCESS  not-accessible
	 STATUS  mandatory
	 DESCRIPTION
		 "An entry in the Recent 24 Hr table."
	 INDEX   { mp7002RecentFarEnd24HrIndex }
	 ::= { mp7002RecentFarEnd24HrTable 1 }

 Mp7002RecentFarEnd24HrEntry ::=
	 SEQUENCE {
		  mp7002RecentFarEnd24HrIndex
			 SCinstance,
		  mp7002RecentFarEnd24HrStat
			 OCTET STRING
	  }

 mp7002RecentFarEnd24HrIndex                OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002RecentFarEnd24HrEntry 1 }

 mp7002RecentFarEnd24HrStat                OBJECT-TYPE
	 SYNTAX OCTET STRING (SIZE(12))
	 ACCESS read-only
	 STATUS mandatory
	 DESCRIPTION
		 "Returns a bitwise map of statistics for the
		 interface in the Recent 24 hour interval.

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
"
	 ::= {mp7002RecentFarEnd24HrEntry 2 }

 --
 -- ********************************************************************
 -- Near End Unavailable Time Registers
 -- ********************************************************************

 mp7002UnavailableTimeRegTable     OBJECT-TYPE
	 SYNTAX  SEQUENCE OF Mp7002UnavailableTimeRegEntry
	 ACCESS  not-accessible
	 STATUS  mandatory
	 DESCRIPTION
		 "The mp7002 Near End Unavailable Time Register table."

	 ::= { mp7002Performance 9 }


 mp7002UnavailableTimeRegEntry     OBJECT-TYPE
	 SYNTAX  Mp7002UnavailableTimeRegEntry
	 ACCESS  not-accessible
	 STATUS  mandatory
	 DESCRIPTION
		 "An entry in the Unavailable Time Register table."
	 INDEX   { mp7002UnavailableTimeRegIndex, mp7002UnavailableTimeRegNumber }
	 ::= { mp7002UnavailableTimeRegTable 1 }

 Mp7002UnavailableTimeRegEntry ::=
	 SEQUENCE {
		  mp7002UnavailableTimeRegIndex
			 SCinstance,
		  mp7002UnavailableTimeRegNumber
			 INTEGER,
		  mp7002UnavailableTimeRegStart
			 INTEGER,
		  mp7002UnavailableTimeRegStop
			 INTEGER
	  }

 mp7002UnavailableTimeRegIndex     OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002UnavailableTimeRegEntry 1 }

 mp7002UnavailableTimeRegNumber    OBJECT-TYPE
	 SYNTAX  INTEGER (1..6)
	 ACCESS  read-only
	 STATUS  mandatory
	 DESCRIPTION
		 "A number between 1 and 6, where the number is the number of the 
		 Unavailable Time Register."
	 ::= { mp7002UnavailableTimeRegEntry 2 }

 mp7002UnavailableTimeRegStart          OBJECT-TYPE
	SYNTAX  INTEGER (1..2147483647)
	ACCESS  read-only
	STATUS  mandatory
	DESCRIPTION
		"Start time of one of the Unavailable Time Registers."
	::= {mp7002UnavailableTimeRegEntry 3}

 mp7002UnavailableTimeRegStop          OBJECT-TYPE
	SYNTAX  INTEGER (1..2147483647)
	ACCESS  read-only
	STATUS  mandatory
	DESCRIPTION
		"Stop time of one of the Unavailable Time Registers."
	::= {mp7002UnavailableTimeRegEntry 4}

 -- 
 -- ********************************************************************
 -- Far End Unavailable Time Registers
 -- ********************************************************************
 mp7002FarEndUnavailableTimeRegTable     OBJECT-TYPE
	 SYNTAX  SEQUENCE OF Mp7002FarEndUnavailableTimeRegEntry
	 ACCESS  not-accessible
	 STATUS  mandatory
	 DESCRIPTION
		 "The mp7002 Unavailable Time Register table."

	 ::= { mp7002Performance 10 }


 mp7002FarEndUnavailableTimeRegEntry     OBJECT-TYPE
	 SYNTAX  Mp7002FarEndUnavailableTimeRegEntry
	 ACCESS  not-accessible
	 STATUS  mandatory
	 DESCRIPTION
		 "An entry in the Unavailable Time Register table."
	 INDEX   { mp7002FarEndUnavailableTimeRegIndex, mp7002FarEndUnavailableTimeRegNumber }
	 ::= { mp7002FarEndUnavailableTimeRegTable 1 }

 Mp7002FarEndUnavailableTimeRegEntry ::=
	 SEQUENCE {
		  mp7002FarEndUnavailableTimeRegIndex
			 SCinstance,
		  mp7002FarEndUnavailableTimeRegNumber
			 INTEGER,
		  mp7002FarEndUnavailableTimeRegStart
			 INTEGER,
		  mp7002FarEndUnavailableTimeRegStop
			 INTEGER
	  }

 mp7002FarEndUnavailableTimeRegIndex     OBJECT-TYPE
	 SYNTAX  SCinstance
	 ACCESS  read-only
	 STATUS  mandatory
	 DESCRIPTION
	 "The index value which uniquely identifies the interface to
	 which this entry is applicable.  This has the form of a
	 SCinstance which defines the slot, line, drop, and interface.
	 Interface can be Network or, when supported, E1X."
	 ::= { mp7002FarEndUnavailableTimeRegEntry 1 }

 mp7002FarEndUnavailableTimeRegNumber    OBJECT-TYPE
	 SYNTAX  INTEGER (1..6)
	 ACCESS  read-only
	 STATUS  mandatory
	 DESCRIPTION
		 "A number between 1 and 6, where the number is the number of the 
		 Unavailable Time Register."
	 ::= { mp7002FarEndUnavailableTimeRegEntry 2 }

 mp7002FarEndUnavailableTimeRegStart          OBJECT-TYPE
	SYNTAX  INTEGER (1..2147483647)
	ACCESS  read-only
	STATUS  mandatory
	DESCRIPTION
		"Start time of one of the Unavailable Time Registers."
	::= {mp7002FarEndUnavailableTimeRegEntry 3}

 mp7002FarEndUnavailableTimeRegStop          OBJECT-TYPE
	SYNTAX  INTEGER (1..2147483647)
	ACCESS  read-only
	STATUS  mandatory
	DESCRIPTION
		"Stop time of one of the Unavailable Time Registers."
	::= {mp7002FarEndUnavailableTimeRegEntry 4}

 --
 -- ********************************************************************
 -- GDC Dsx-1 Alarm Object Identifier Definitions
 -- ********************************************************************

 mp7002AlarmData                	OBJECT IDENTIFIER ::= { mp7002Alarms 1 }

 mp7002NoResponseAlm	OBJECT IDENTIFIER ::= { mp7002AlarmData 1  }
 mp7002DiagRxErrAlm	OBJECT IDENTIFIER ::= { mp7002AlarmData 2  }
 mp7002PowerUpAlm	OBJECT IDENTIFIER ::= { mp7002AlarmData 3  }
 mp7002NvRamCorrupt	OBJECT IDENTIFIER ::= { mp7002AlarmData 4  }
 mp7002UnitFailure      OBJECT IDENTIFIER ::= { mp7002AlarmData 5  }
 mp7002TimingLoss       OBJECT IDENTIFIER ::= { mp7002AlarmData 6  }
 mp7002LCV		OBJECT IDENTIFIER ::= { mp7002AlarmData 7  }
 mp7002LossOfSignal     OBJECT IDENTIFIER ::= { mp7002AlarmData 8  }
 mp7002LossOfFrame      OBJECT IDENTIFIER ::= { mp7002AlarmData 9  }
 mp7002AlarmIndSignal	OBJECT IDENTIFIER ::= { mp7002AlarmData 10 }
 mp7002NEES		OBJECT IDENTIFIER ::= { mp7002AlarmData 11 }
 mp7002NEBBE		OBJECT IDENTIFIER ::= { mp7002AlarmData 12 }
 mp7002NESES		OBJECT IDENTIFIER ::= { mp7002AlarmData 13 }
 mp7002NEUAS		OBJECT IDENTIFIER ::= { mp7002AlarmData 14 }
 mp7002FEES		OBJECT IDENTIFIER ::= { mp7002AlarmData 15 }
 mp7002FEBBE		OBJECT IDENTIFIER ::= { mp7002AlarmData 16 }
 mp7002FESES		OBJECT IDENTIFIER ::= { mp7002AlarmData 17 }
 mp7002FEUAS		OBJECT IDENTIFIER ::= { mp7002AlarmData 18 }
 mp7002RAI		OBJECT IDENTIFIER ::= { mp7002AlarmData 19 }

 -- ALARM                     Maskable            Valid interfaces         window/thres
 -- ====================================================================================
 -- mp7002NoResponseAlm		no			unit			no
 -- mp7002DiagRxErrAlm		no			unit			no
 -- mp7002PowerUpAlm		no			unit			no
 -- mp7002NvRamCorrupt		no			unit			no
 -- mp7002UnitFailure		no			unit			no
 -- mp7002TimingLoss		yes			unit			no
 -- mp7002LCV			yes			E1			no
 -- mp7002LossofSignal		yes			E1/E1X			no
 -- mp7002LossOfFrame		yes			E1/E1X			no
 -- mp7002Ais			yes			E1/E1X			no
 -- mp7002NEES			yes			E1/E1X			yes
 -- mp7002NEBBE			yes			E1/E1X			yes
 -- mp7002NESES			yes			E1/E1X			yes
 -- mp7002NEUAS			yes			E1/E1X			yes
 -- mp7002FEES			yes			E1/E1X			yes
 -- mp7002FEBBE			yes			E1/E1X			yes
 -- mp7002FESES			yes			E1/E1X			yes
 -- mp7002FEUAS			yes			E1/E1X			yes
 -- mp7002RAI			yes			E1			no
 -- 
 --
 -- ********************************************************************
 -- GDC MP7002 Alarm Configuration
 -- ********************************************************************

 mp7002NearEndAlarmConfigTable OBJECT-TYPE
     SYNTAX SEQUENCE OF Mp7002NearEndAlarmConfigEntry
     ACCESS not-accessible
     STATUS mandatory
     DESCRIPTION
	 "The mp7002NearEndAlarmConfigTable contains entries that configure alarm
	 reporting.  The structure of the table is such that alarm
	 configuration is supported on a unit and interface basis, and
	 then on an alarm type basis within the interface.  For
	 simplicity sake alarms, be they unit or interface
	 related, are represented in one table."
     ::= { mp7002Alarms 2 }

 mp7002NearEndAlarmConfigEntry OBJECT-TYPE
     SYNTAX Mp7002NearEndAlarmConfigEntry
     ACCESS not-accessible
     STATUS mandatory
     DESCRIPTION
	 "An entry in the MP7002 Alarm Configuration table."
     INDEX { mp7002NearEndAlarmConfigIndex, mp7002NearEndAlarmConfigIdentifier }
     ::= { mp7002NearEndAlarmConfigTable 1 }

 Mp7002NearEndAlarmConfigEntry ::=
     SEQUENCE {
	 mp7002NearEndAlarmConfigIndex
	     SCinstance,
	 mp7002NearEndAlarmConfigIdentifier
	     OBJECT IDENTIFIER,
	 mp7002NearEndAlarmCountWindow
	     INTEGER,
	 mp7002NearEndAlarmCountThreshold
	     INTEGER
     }

 mp7002NearEndAlarmConfigIndex OBJECT-TYPE
     SYNTAX SCinstance
     ACCESS read-only
     STATUS mandatory
     DESCRIPTION
	 "The index value which uniquely identifies the interface to
	 which this entry is applicable."
     ::= { mp7002NearEndAlarmConfigEntry 1 }

 --
 mp7002NearEndAlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."

     ::= { mp7002NearEndAlarmConfigEntry 2 }

 mp7002NearEndAlarmCountWindow OBJECT-TYPE
     SYNTAX INTEGER{
			disabled(1),
			last1sec(2),
			last10sec(3),
			last30sec(4),
			last1min(5),
			last15min(6),
			last1hr(7),
			last24hr(8),
			infinite(9)
		}
	ACCESS  read-write
	STATUS  mandatory
	DESCRIPTION
		"This variable sets/reads the alarm window.

		This window is used with the alarm threshold to determine
		how long the alarm should be active before reporting.

		Default: disabled(1)"
    ::= { mp7002NearEndAlarmConfigEntry 3 }

 mp7002NearEndAlarmCountThreshold OBJECT-TYPE
    SYNTAX INTEGER {
			thresGT1(1),
			thresGT3(2),
			thresGT10(3),
			thresGT100(4),
			thresGT1000(5),
			thresGT10000(6)
		}
	ACCESS  read-write
	STATUS  mandatory
	DESCRIPTION
		"This function sets/reads the alarm threshold criteria.

		This threshold is used along with the the alarm window to 
		determine the number of instances in a given time frame for
		an alarm to occur before the alarm is considered active.

		Default: thresGT1(1)"
    ::= { mp7002NearEndAlarmConfigEntry 4 }

 mp7002FarEndAlarmConfigTable OBJECT-TYPE
     SYNTAX SEQUENCE OF Mp7002FarEndAlarmConfigEntry
     ACCESS not-accessible
     STATUS mandatory
     DESCRIPTION
	 "The mp7002FarEndAlarmConfigTable contains entries that configure alarm
	 reporting.  The structure of the table is such that alarm
	 configuration is supported on a unit and interface basis, and
	 then on an alarm type basis within the interface.  For
	 simplicity sake alarms, be they unit or interface
	 related, are represented in one table."
     ::= { mp7002Alarms 3 }

 mp7002FarEndAlarmConfigEntry OBJECT-TYPE
     SYNTAX Mp7002FarEndAlarmConfigEntry
     ACCESS not-accessible
     STATUS mandatory
     DESCRIPTION
	 "An entry in the MP7002 Alarm Configuration table."
     INDEX { mp7002FarEndAlarmConfigIndex, mp7002FarEndAlarmConfigIdentifier }
     ::= { mp7002FarEndAlarmConfigTable 1 }

 Mp7002FarEndAlarmConfigEntry ::=
     SEQUENCE {
	 mp7002FarEndAlarmConfigIndex
	     SCinstance,
	 mp7002FarEndAlarmConfigIdentifier
	     OBJECT IDENTIFIER,
	 mp7002FarEndAlarmCountWindow
	     INTEGER,
	 mp7002FarEndAlarmCountThreshold
	     INTEGER
     }

 --
 mp7002FarEndAlarmConfigIndex OBJECT-TYPE
     SYNTAX SCinstance
     ACCESS read-only
     STATUS mandatory
     DESCRIPTION
	 "The index value which uniquely identifies the interface to
	 which this entry is applicable."
     ::= { mp7002FarEndAlarmConfigEntry 1 }

 mp7002FarEndAlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."

     ::= { mp7002FarEndAlarmConfigEntry 2 }

 mp7002FarEndAlarmCountWindow OBJECT-TYPE
     SYNTAX INTEGER{
			disabled(1),
			last1sec(2),
			last10sec(3),
			last30sec(4),
			last1min(5),
			last15min(6),
			last1hr(7),
			last24hr(8),
			infinite(9)
		}
	ACCESS  read-write
	STATUS  mandatory
	DESCRIPTION
		"This variable sets/reads the alarm window.

		This window is used with the alarm threshold to determine
		how long the alarm should be active before reporting.

		Default: disabled(1)"
    ::= { mp7002FarEndAlarmConfigEntry 3 }

 --
mp7002FarEndAlarmCountThreshold OBJECT-TYPE
    SYNTAX INTEGER {
			thresGT1(1),
			thresGT3(2),
			thresGT10(3),
			thresGT100(4),
			thresGT1000(5),
			thresGT10000(6)
		}
	ACCESS  read-write
	STATUS  mandatory
	DESCRIPTION
		"This function sets/reads the alarm threshold criteria.

		This threshold is used along with the the alarm window to 
		determine the number of instances in a given time frame for
		an alarm to occur before the alarm is considered active.

		Default: thresGT1(1)"
    ::= { mp7002FarEndAlarmConfigEntry 4 }

 --
 -- ********************************************************************
 -- GDC Local MP7002 Alarm Configuration
 -- ********************************************************************

 mp7002LocalAlarmConfigTable OBJECT-TYPE
     SYNTAX SEQUENCE OF Mp7002LocalAlarmConfigEntry
     ACCESS not-accessible
     STATUS mandatory
     DESCRIPTION
	 "The mp7002LocalAlarmConfigTable contains entries that configure 
	 alarm
	 reporting.  The structure of the table is such that alarm
	 configuration is supported on a unit and interface basis, and
	 then on an alarm type basis within the interface.  For
	 simplicity sake alarms, be they unit or interface
	 related, are represented in one table."
     ::= { mp7002Alarms 4 }

 mp7002LocalAlarmConfigEntry OBJECT-TYPE
     SYNTAX Mp7002LocalAlarmConfigEntry
     ACCESS not-accessible
     STATUS mandatory
     DESCRIPTION
	 "An entry in the GDC Local Alarm Configuration table."
     INDEX { mp7002LocalAlarmConfigIndex }
     ::= { mp7002LocalAlarmConfigTable 1 }

 Mp7002LocalAlarmConfigEntry ::=
     SEQUENCE {
	 mp7002LocalAlarmConfigIndex
	     SCinstance,
	 mp7002UASNE
	     INTEGER,
	 mp7002SESNE
	     INTEGER,
	 mp7002BBENE
	     INTEGER,
	 mp7002ESNE
	     INTEGER,
	 mp7002UASFE
	     INTEGER,
	 mp7002SESFE
	     INTEGER,
	 mp7002BBEFE
	     INTEGER,
	 mp7002ESFE
	     INTEGER,
	 mp7002LOS
	     INTEGER,
	 mp7002LOF
	     INTEGER,
	 mp7002AIS
	     INTEGER,
	 mp7002TmgLoss
	     INTEGER,
	 mp7002LCVs
	     INTEGER,
	 mp7002NtwkRAI
	     INTEGER
     }

 mp7002LocalAlarmConfigIndex OBJECT-TYPE
     SYNTAX SCinstance
     ACCESS read-only
     STATUS mandatory
     DESCRIPTION
	 "The index value which uniquely identifies the interface to
	 which this entry is applicable."
     ::= { mp7002LocalAlarmConfigEntry 1 }

 mp7002UASNE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 2 }
 --

 mp7002SESNE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 3 }

 mp7002BBENE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 4 }

 mp7002ESNE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 5 }

 mp7002UASFE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 6 }
 --

 mp7002SESFE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 7 }

 mp7002BBEFE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 8 }

 mp7002ESFE       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 9 }

 mp7002LOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 10 }
 --

 mp7002LOF       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 11 }

 mp7002AIS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 12 }

 mp7002TmgLoss       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 13 }

 mp7002LCVs       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 14 }

 mp7002NtwkRAI    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7002LocalAlarmConfigEntry 15 }

END
